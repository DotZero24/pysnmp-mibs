--
-- file :a202v20.pkb
--
ACE202-MIB

			DEFINITIONS ::= BEGIN

--Title:     ACE2002E   MIB

-- Copyright 2201 RAD Data Communications, Ltd.
-- All Rights Reserved.

-- It is RAD's intent to encourage the widespread use of
-- this Specification in connection with the management of
-- RAD products. RAD grants vendors, end-users,
-- and other interested parties a non-exclusive license to
-- use this Specification in connection with the management
-- of RAD products.

-- This Specification is supplied "as is," and RAD makes
-- no warranty, either express or implied, as to the use,
-- operation, condition, or performance of the Specification.

IMPORTS
      TimeTicks,enterprises,
      IpAddress, OBJECT-TYPE, Integer32,
      Counter32, Gauge32, OBJECT-IDENTITY,
      NOTIFICATION-TYPE                     FROM SNMPv2-SMI
	  PerfCurrentCount,
	  PerfIntervalCount, PerfTotalCount     FROM PerfHist-TC-MIB
      InterfaceIndex, ifAlias, ifIndex      FROM IF-MIB
      dsx1LineStatus,
      dsx1LineStatusLastChange,
      dsx1CurrentIndex, dsx1LineIndex,
      dsx1IntervalIndex, dsx1IntervalNumber,
      dsx1LoopbackStatus,
      dsx1TotalIndex                        FROM DS1-MIB
      imaGroupIndex, imaLinkIfIndex,
      imaGroupFailureStatus  		        FROM IMA-MIB
      RowStatus, DisplayString, TimeStamp,
      DateAndTime                           FROM SNMPv2-TC
	  SnmpAdminString 		                FROM SNMP-FRAMEWORK-MIB
	  frAtmIwfConnectionEntry               FROM FR-ATM-PVC-SERVICE-IWF-MIB
	  isdnSignalingEntry                    FROM ISDN-MIB
	  atmVclEntry, aal5VccEntry,
	  atmVplVpi, atmVclVpi, atmVclVci       FROM ATM-MIB;


-- Some MIB compilers need those two lines:
-- enterprises OBJECT IDENTIFIER ::=
--		     { iso org(3) dod(6) internet(1) private(4) 1 }

 MacAddress ::= OCTET STRING (SIZE(6))

rad OBJECT IDENTIFIER ::= { enterprises 164 }
radTokenRing OBJECT IDENTIFIER ::= { rad 1 } -- RAD Token Ring tree
radFddi      OBJECT IDENTIFIER ::= { rad 2 } -- rad FDDI Tree
radWan       OBJECT IDENTIFIER ::= { rad 3 } -- rad WAN Tree
radBridges  OBJECT IDENTIFIER ::= {rad 4 }
radConverters OBJECT IDENTIFIER ::= { rad 5 }  -- RAD Converters products' tree
radGen        OBJECT IDENTIFIER ::= { rad 6} -- General information
radStkHub         OBJECT IDENTIFIER ::=  { rad 7 } -- stackable products
radAtm        OBJECT IDENTIFIER ::=  { rad 12} -- stackable products
wanGen  OBJECT IDENTIFIER  ::=  {radWan 1}
diverseIfWanGen  OBJECT IDENTIFIER  ::=  {wanGen 6}
--atmNte	 OBJECT IDENTIFIER ::= { radAtm 3 }
--atmNtePrt		OBJECT IDENTIFIER ::= { atmNte 2 }
--atmNtePrtConfig		OBJECT IDENTIFIER ::= { atmNtePrt 1 }
--dacsMux       OBJECT IDENTIFIER ::= {radWan 3}
--genDacsMux    OBJECT IDENTIFIER ::= {dacsMux 4}
radRouter     OBJECT IDENTIFIER ::= { rad 11 }
rtrBridge     OBJECT IDENTIFIER ::= { radRouter 7 }
radExperimental OBJECT IDENTIFIER ::= { rad 20 }  -- Drafts that have no MIB tree yet
-- igmpStdMIB MODULE-IDENTITY ::= { radExperimental 1 }
-- apsMIB  OBJECT IDENTIFIER  ::= { radExperimental 2 }


--
-- file :v:\doc\rdv\mib\ver480\radgen.txt
--

--Version:   4.80
--First Version Date:   25.01.99
--By:        Orly Nicklass
--File:      radgen.txt

--Last Update: 18-Feb-2002 by Smadar Tauber

systems OBJECT IDENTIFIER ::= { radGen 1}  --    list of RAD products

radSysTR  OBJECT IDENTIFIER ::= { systems 1 } -- RAD Token Ring

radRADring    OBJECT IDENTIFIER  ::= { radSysTR  1 }

radTMA  OBJECT IDENTIFIER  ::= { radSysTR  2 }

radRingMonitor    OBJECT IDENTIFIER  ::= { radSysTR  3 }

radSysFddi OBJECT IDENTIFIER ::= { systems 2 } -- RAD Fddi

radFDX100  OBJECT IDENTIFIER ::= { radSysFddi  1 } -- RAD Fddi

radSysWan OBJECT IDENTIFIER ::= { systems 3 }  -- RAD Wan products

radSysWanEvents OBJECT-IDENTITY
     STATUS  current
     DESCRIPTION
     "The events for RAD Wan products."
     ::= { radSysWan 0 }

radMP2100      OBJECT IDENTIFIER ::= { radSysWan  1 }
radMP2104      OBJECT IDENTIFIER ::= { radSysWan  2 }
radMP2100B     OBJECT IDENTIFIER ::= { radSysWan  3 }
radMP2100F     OBJECT IDENTIFIER ::= { radSysWan  4 }

radMP2100H      OBJECT IDENTIFIER ::= { radSysWan  5 }
radMP2104H      OBJECT IDENTIFIER ::= { radSysWan  6 }
radMP2200B      OBJECT IDENTIFIER ::= { radSysWan  7 }
radMP2200F      OBJECT IDENTIFIER ::= { radSysWan  8 }

radMX3000       OBJECT IDENTIFIER ::= { radSysWan  9 }
radMX3004       OBJECT IDENTIFIER ::= { radSysWan 10 }
radMX30			OBJECT IDENTIFIER ::= { radSysWan 11 }
radMX300		OBJECT IDENTIFIER ::= { radSysWan 12 }

radVOIP         OBJECT IDENTIFIER ::= { radSysWan 13 }

radKM2100	    OBJECT IDENTIFIER ::= { radSysWan 15 }
radKM2104		OBJECT IDENTIFIER ::= { radSysWan 16 }

radDXC30        OBJECT IDENTIFIER ::= { radSysWan 20 }
radDXC10A       OBJECT IDENTIFIER ::= { radSysWan 21 }
radDXC8R        OBJECT IDENTIFIER ::= { radSysWan 22 }
radDXC30E       OBJECT IDENTIFIER ::= { radSysWan 23 }
radDXC3000      OBJECT IDENTIFIER ::= { radSysWan 24 }
radDXC8RNew     OBJECT IDENTIFIER ::= { radSysWan 25 }

radFcdE1L        OBJECT IDENTIFIER ::= { radSysWan 29 }
radFcdT1         OBJECT IDENTIFIER ::= { radSysWan 30 }
radFcdE1         OBJECT IDENTIFIER ::= { radSysWan 31 }
radFcdE1I        OBJECT IDENTIFIER ::= { radSysWan 32 }
radFcdT1M        OBJECT IDENTIFIER ::= { radSysWan 33 }
radFcdE1M        OBJECT IDENTIFIER ::= { radSysWan 34 }
radFcdIP         OBJECT IDENTIFIER ::= { radSysWan 35}
radFcdT1A        OBJECT IDENTIFIER ::= { radSysWan 36 }
radFcdE1A        OBJECT IDENTIFIER ::= { radSysWan 37 }
radFcdW          OBJECT IDENTIFIER ::= { radSysWan 38 }
radFcdSTM        OBJECT IDENTIFIER ::= { radSysWan 39 }

radHtuE1Sa      OBJECT IDENTIFIER ::= { radSysWan 40 }
radHtuE1        OBJECT IDENTIFIER ::= { radSysWan 41 }	 --card
radHtu2Sa       OBJECT IDENTIFIER ::= { radSysWan 42 }
radHtu2         OBJECT IDENTIFIER ::= { radSysWan 43 }	 --card
radAsmi450R768Sa OBJECT IDENTIFIER ::= { radSysWan 44 }
radAsmi450R768  OBJECT IDENTIFIER ::= { radSysWan 45 }	 --card
radAsmi450R1152Sa  OBJECT IDENTIFIER ::= { radSysWan 46 }
radAsmi450R1152 OBJECT IDENTIFIER ::= { radSysWan 47 }	 --card

radLrs12F        OBJECT IDENTIFIER ::= { radSysWan 48 }
radLrs12B        OBJECT IDENTIFIER ::= { radSysWan 49 }

radHcdE1Sa       OBJECT IDENTIFIER ::= { radSysWan 51 }
radHcdE1         OBJECT IDENTIFIER ::= { radSysWan 52 }  --card
radHtuT1Sa       OBJECT IDENTIFIER ::= { radSysWan 53 }
radHtuT1         OBJECT IDENTIFIER ::= { radSysWan 54 }	 --card

radOptimux4E1         OBJECT IDENTIFIER ::= { radSysWan 55 }
radOptimux4T1         OBJECT IDENTIFIER ::= { radSysWan 56 }
radOptimuxXLE1         OBJECT IDENTIFIER ::= { radSysWan 57 }
radOptimuxXLT1         OBJECT IDENTIFIER ::= { radSysWan 58 }
radOptimuxXL16E1       OBJECT IDENTIFIER ::= { radSysWan 59 }

radImx64        OBJECT IDENTIFIER ::= { radSysWan 60 }
radImx6L        OBJECT IDENTIFIER ::= { radSysWan 61 }
radImx2         OBJECT IDENTIFIER ::= { radSysWan 62 }
radImx4T1       OBJECT IDENTIFIER ::= { radSysWan 63 }
radImx4E1       OBJECT IDENTIFIER ::= { radSysWan 64 }
radImx2T1E1     OBJECT IDENTIFIER ::= { radSysWan 65 }

radOptimux4T1L    OBJECT IDENTIFIER ::= { radSysWan 68 }  --SA Low Cost
radOptimux4E1L    OBJECT IDENTIFIER ::= { radSysWan 69 }  --SA Low Cost
radHtuE1SaV2      OBJECT IDENTIFIER ::= { radSysWan 70 }
radHtuE1V2        OBJECT IDENTIFIER ::= { radSysWan 71 }  --card
radFomiE3         OBJECT IDENTIFIER ::= { radSysWan 72 }  --card
radFomiT3         OBJECT IDENTIFIER ::= { radSysWan 73 }  --card
radOpt4E1C        OBJECT IDENTIFIER ::= { radSysWan 74 }  --card
radOpt4T1C        OBJECT IDENTIFIER ::= { radSysWan 75 }  --card
radPrbiE3         OBJECT IDENTIFIER ::= { radSysWan 76 }  --SA
radPrbiT3         OBJECT IDENTIFIER ::= { radSysWan 77 }  --SA
radHcd4Sa         OBJECT IDENTIFIER ::= { radSysWan 78 }  --SA
radOptimuxT3      OBJECT IDENTIFIER ::= { radSysWan 79 }  --SA

radFRmon          OBJECT IDENTIFIER ::= { radSysWan 80 }
radIpMux4         OBJECT IDENTIFIER ::= { radSysWan 81 }
radIpMux1         OBJECT IDENTIFIER ::= { radSysWan 82 }
radIpMux16        OBJECT IDENTIFIER ::= { radSysWan 83 }
radIpMux1E        OBJECT IDENTIFIER ::= { radSysWan 84 }
radVmux2100       OBJECT IDENTIFIER ::= { radSysWan 85 }

radSysBRG OBJECT IDENTIFIER ::= { systems 4 }  -- RAD Bridges products

radTRE1  OBJECT IDENTIFIER ::= { radSysBRG 1 }  -- RAD Bridges products

radTRE1D  OBJECT IDENTIFIER ::= { radSysBRG 2 }  -- RAD Bridges products

radTRE8  OBJECT IDENTIFIER ::= { radSysBRG 3 }  -- RAD Bridges products

radTRE8D  OBJECT IDENTIFIER ::= { radSysBRG 4 }  -- RAD Bridges products

radMBE1  OBJECT IDENTIFIER ::= { radSysBRG 5 }  -- RAD Bridges products

radMBE1D  OBJECT IDENTIFIER ::= { radSysBRG  6 }  -- RAD Bridges products

radMBE8  OBJECT IDENTIFIER ::= { radSysBRG  7 }  -- RAD Bridges products

radMBE8D  OBJECT IDENTIFIER ::= { radSysBRG  8 }  -- RAD Bridges products

radMLBT   OBJECT IDENTIFIER ::= { radSysBRG  9 }  -- RAD Bridges products

radFEB4DAS    OBJECT IDENTIFIER ::= { radSysBRG  10 }  -- RAD Bridges products

radTrimBrg10  OBJECT IDENTIFIER ::= { radSysBRG 11 }  -- RAD Bridges products

radTrimBrg16  OBJECT IDENTIFIER ::= { radSysBRG 12 }  -- RAD Bridges products

radRRTRE8  OBJECT IDENTIFIER ::= { radSysBRG 13 }  -- RAD Bridges products

radRRTRE8D  OBJECT IDENTIFIER ::= { radSysBRG 14 }  -- RAD Bridges products

radRRMLBT   OBJECT IDENTIFIER ::= { radSysBRG 15 }  -- RAD Bridges products

radRRMLBTF   OBJECT IDENTIFIER ::= { radSysBRG 16 }  -- RAD Bridges products

radRRTRE1D  OBJECT IDENTIFIER ::= { radSysBRG 17 }  -- RAD Bridges products

radTRERAS  OBJECT IDENTIFIER ::= { radSysBRG 18 }  -- RAD Bridges products

radTRERASa  OBJECT IDENTIFIER ::= { radSysBRG 19 }  -- RAD Bridges products

radMBERAS  OBJECT IDENTIFIER ::= { radSysBRG 20 }  -- RAD Bridges products

radMBERASa  OBJECT IDENTIFIER ::= { radSysBRG 21 }  -- RAD Bridges products

radFEB4FDX   OBJECT IDENTIFIER ::= { radSysBRG 22 }  -- RAD Bridges products

radFEB4SAS  OBJECT IDENTIFIER ::= { radSysBRG 23 }  -- RAD Bridges products

radRRFTBDAS  OBJECT IDENTIFIER ::= { radSysBRG 24 }  -- RAD Bridges products

radRRFTBSAS  OBJECT IDENTIFIER ::= { radSysBRG 25 }  -- RAD Bridges products

radFTBDAS    OBJECT IDENTIFIER ::= { radSysBRG 26 }  -- RAD Bridges products

radFTBSAS    OBJECT IDENTIFIER ::= { radSysBRG 27 }  -- RAD Bridges products

radFastWay100    OBJECT IDENTIFIER ::= { radSysBRG 28 }  -- RAD Bridges products

radSysCnvrtr OBJECT IDENTIFIER ::= { systems 5 }  -- RAD Converters products

radSTC1   OBJECT IDENTIFIER ::= { radSysCnvrtr 1 }  -- RAD Converters products

radSTC2   OBJECT IDENTIFIER ::= { radSysCnvrtr 3 }  -- RAD Converters products

radSTC1UDP  OBJECT IDENTIFIER ::= { radSysCnvrtr 4 }  -- RAD Converters products

radSTC2UDP  OBJECT IDENTIFIER ::= { radSysCnvrtr 6 }  -- RAD Converters products

radFTC1   OBJECT IDENTIFIER ::= { radSysCnvrtr 10 }  -- RAD Converters products

radFTC2   OBJECT IDENTIFIER ::= { radSysCnvrtr 12 }  -- RAD Converters products

radFTC1UDP    OBJECT IDENTIFIER ::= { radSysCnvrtr 13 }  -- RAD Converters products

radFTC2UDP    OBJECT IDENTIFIER ::= { radSysCnvrtr 15 }  -- RAD Converters products

radSEC1   OBJECT IDENTIFIER ::= { radSysCnvrtr 20 }  -- RAD Converters products

radSEC2   OBJECT IDENTIFIER ::= { radSysCnvrtr 22 }  -- RAD Converters products

radSEC1UDP   OBJECT IDENTIFIER ::= { radSysCnvrtr 23 }  -- RAD Converters products

radSEC2UDP   OBJECT IDENTIFIER ::= { radSysCnvrtr 25 }  -- RAD Converters products

radFEC1   OBJECT IDENTIFIER ::= { radSysCnvrtr 30 }  -- RAD Converters products

radFEC2   OBJECT IDENTIFIER ::= { radSysCnvrtr 32 }  -- RAD Converters products

radFEC1UDP   OBJECT IDENTIFIER ::= { radSysCnvrtr 33 }  -- RAD Converters products

radFEC2UDP   OBJECT IDENTIFIER ::= { radSysCnvrtr 35 }  -- RAD Converters products

radSysStkHub  OBJECT IDENTIFIER ::= { systems 7 }  -- RAD Stackable products

radRBHE    OBJECT IDENTIFIER ::= { radSysStkHub 1 }  -- RAD Stackable products

radRBHT    OBJECT IDENTIFIER ::= { radSysStkHub 2 }  -- RAD Stackable products

radRBHEEvents OBJECT-IDENTITY
     STATUS  current
     DESCRIPTION
     "The events for RAD Stackable products."
     ::= { radRBHE 0 }

radRBHTEvents OBJECT-IDENTITY
     STATUS  current
     DESCRIPTION
     "The events for RAD Stackable products."
     ::= { radRBHT 0 }

radETS4fddiDAS   OBJECT IDENTIFIER ::= { radSysStkHub 3 }  -- RAD Stackable products

radETS4fddiSAS   OBJECT IDENTIFIER ::= { radSysStkHub 4 }  -- RAD Stackable products

radSAHEMX  OBJECT IDENTIFIER ::= { radSysStkHub 5 }  -- RAD Stackable products

radSAHTM   OBJECT IDENTIFIER ::= { radSysStkHub 6 }  -- RAD Stackable products

radETS4   OBJECT IDENTIFIER ::= { radSysStkHub 7 }  -- RAD Stackable products

radSAHEMU  OBJECT IDENTIFIER ::= { radSysStkHub 8 }  -- RAD Stackable products


unknown    	OBJECT IDENTIFIER ::= { radSysStkHub 9 }  -- RAD Stackable products

radSAH16Eint   OBJECT IDENTIFIER ::= { radSysStkHub 10 }  -- RAD Stackable products

radSAH16Tint   OBJECT IDENTIFIER ::= { radSysStkHub 11 }  -- RAD Stackable products

radSAH16Eext   OBJECT IDENTIFIER ::= { radSysStkHub 12 }  -- RAD Stackable products

radSAH16Text   OBJECT IDENTIFIER ::= { radSysStkHub 13 }  -- RAD Stackable products



radSysPS OBJECT IDENTIFIER ::=  { systems 8 } -- RAD Packet Switch  (PS) products

radSysPSEvents OBJECT-IDENTITY
     STATUS  current
     DESCRIPTION
     "The events for RAD Packet Switch  (PS) products."
     ::= { radSysPS 0 }

radSPS2  OBJECT IDENTIFIER ::=  { radSysPS 1 } -- RAD Packet Switch  (PS) products

radSPS3  OBJECT IDENTIFIER ::=  { radSysPS 2 } -- RAD Packet Switch  (PS) products

radSPS6  OBJECT IDENTIFIER ::=  { radSysPS 3 } -- RAD Packet Switch  (PS) products

radSPS9  OBJECT IDENTIFIER ::=  { radSysPS 4 } -- RAD Packet Switch  (PS) products

radSPS12 OBJECT IDENTIFIER ::=  { radSysPS 5 } -- RAD Packet Switch  (PS) products

radAPD2  OBJECT IDENTIFIER ::=  { radSysPS 6 } -- RAD Packet Switch  (PS) products

radAPD8  OBJECT IDENTIFIER ::=  { radSysPS 7 } -- RAD Packet Switch  (PS) products

radAPS8  OBJECT IDENTIFIER ::=  { radSysPS 8 } -- RAD Packet Switch  (PS) products

radAPS16 OBJECT IDENTIFIER ::=  { radSysPS 9 } -- RAD Packet Switch  (PS) products

radAPS24 OBJECT IDENTIFIER ::=  { radSysPS 10 } -- RAD Packet Switch  (PS) products

radSPS3S  OBJECT IDENTIFIER ::=  { radSysPS 11} -- RAD Packet Switch  (PS) products

radFPS8  OBJECT IDENTIFIER ::=  { radSysPS 12} -- RAD Packet Switch  (PS) products

radFPS12  OBJECT IDENTIFIER ::=  { radSysPS 13} -- RAD Packet Switch  (PS) products

radSPS3ScSL  OBJECT IDENTIFIER ::= { radSysPS 14} -- RAD Packet Switch  (PS) products

radSPS3Sc2S  OBJECT IDENTIFIER ::=  { radSysPS 15} -- RAD Packet Switch  (PS) products

radFPS8c OBJECT IDENTIFIER ::=  { radSysPS 16} -- RAD Packet Switch  (PS) products

radFPS4 OBJECT IDENTIFIER ::=  { radSysPS 17} -- RAD Packet Switch  (PS) products



radSysEth  OBJECT IDENTIFIER ::= { systems 9 } -- RAD Ethernet products

radEP8T    OBJECT IDENTIFIER ::= {radSysEth 1} -- RAD Ethernet products

radEP4TAUI   OBJECT IDENTIFIER ::= {radSysEth 2} -- RAD Ethernet products

radEP4T2FL   OBJECT IDENTIFIER ::= {radSysEth 3} -- RAD Ethernet products

radEP4TFL    OBJECT IDENTIFIER ::= {radSysEth 4} -- RAD Ethernet products

radEP4FL     OBJECT IDENTIFIER ::= {radSysEth 5} -- RAD Ethernet products


radEPR8T   OBJECT IDENTIFIER ::= {radSysEth 7} -- RAD Ethernet products

radEPR4TAUI  OBJECT IDENTIFIER ::= {radSysEth 8} -- RAD Ethernet products

radEPR4T2FL  OBJECT IDENTIFIER ::= {radSysEth 9} -- RAD Ethernet products

radEPR4TFL   OBJECT IDENTIFIER ::= {radSysEth 10} -- RAD Ethernet products

radEPR4FL    OBJECT IDENTIFIER ::= {radSysEth 11} -- RAD Ethernet products



radSysRtr  OBJECT IDENTIFIER ::= { systems 11 } -- RAD Router products

radSysRtrEvents OBJECT-IDENTITY
     STATUS  current
     DESCRIPTION
     "The events for RAD Router products."
     ::= { radSysRtr 0 }

radRTED    OBJECT IDENTIFIER ::= {radSysRtr 1} -- RAD Router products

radRTEM    OBJECT IDENTIFIER ::= {radSysRtr 2} -- RAD Router products

radRTEC    OBJECT IDENTIFIER ::= {radSysRtr 3} -- RAD Router products

radWebRanger    OBJECT IDENTIFIER ::= {radSysRtr 4} -- RAD Router products

radTinyRouter   OBJECT IDENTIFIER ::= {radSysRtr 5} -- RAD Router products

radLA240	    OBJECT IDENTIFIER ::= {radSysRtr 6} -- RAD Router products

radSuperLan	    OBJECT IDENTIFIER ::= {radSysRtr 7} -- RAD Router products (LA-240)

radLA240I	    OBJECT IDENTIFIER ::= {radSysRtr 8} -- RAD Router products

radFcdIsdn      OBJECT IDENTIFIER ::= {radSysRtr 9} -- RAD Router products

radEFcdIp	    OBJECT IDENTIFIER ::= {radSysRtr 10} -- RAD Router products (FCD-IP/D)

radFcdIpD       OBJECT IDENTIFIER ::= {radSysRtr 11} -- RAD Router products

radFcdIpM       OBJECT IDENTIFIER ::= {radSysRtr 12} -- RAD Router products (LA-240)


radSysAtm  OBJECT IDENTIFIER ::= { systems 12 } -- RAD ATM products

radSysAtmEvents OBJECT-IDENTITY
     STATUS  current
     DESCRIPTION
     "The events for RAD ATM products."
     ::= { radSysAtm 0 }

radStarSwitch    OBJECT IDENTIFIER ::= {radSysAtm 1} --RAD StartSwitch products

radStarSwitchATM25    OBJECT IDENTIFIER ::= {radStarSwitch 1} --RAD StartSwitch products
radStarSwitchATM25L   OBJECT IDENTIFIER ::= {radStarSwitch 2} --RAD StartSwitch products
radStarSwitchATM155   OBJECT IDENTIFIER ::= {radStarSwitch 3} --RAD StartSwitch products


radAtmCsuDsu  OBJECT IDENTIFIER ::= {radSysAtm 2} --RAD CSU/DSU products

radAmcdE1  OBJECT IDENTIFIER ::= {radAtmCsuDsu 1} -- RAD CSU/DSU products
radAmcdT1  OBJECT IDENTIFIER ::= {radAtmCsuDsu 2} -- RAD CSU/DSU products
radAce20E  OBJECT IDENTIFIER ::= {radAtmCsuDsu 3} -- RAD CSU/DSU products
radAce20T  OBJECT IDENTIFIER ::= {radAtmCsuDsu 4} -- RAD CSU/DSU products

radAce2005 OBJECT IDENTIFIER ::= { radAtmCsuDsu 5} -- RAD ACE2005
radAce2002 OBJECT IDENTIFIER ::= { radAtmCsuDsu 6} -- RAD ACE2002
radAce2002E OBJECT IDENTIFIER ::= { radAtmCsuDsu 7} -- RAD ACE2002E

radAce2E  OBJECT IDENTIFIER ::= {radAtmCsuDsu 8} -- RAD CSU/DSU products
radAce2T  OBJECT IDENTIFIER ::= {radAtmCsuDsu 9} -- RAD CSU/DSU products

radMlAtmE1  OBJECT IDENTIFIER ::= {radAtmCsuDsu 10} -- RAD ATM Piggy
radMlAtmT1  OBJECT IDENTIFIER ::= {radAtmCsuDsu 11} -- RAD ATM Piggy

radAmc102  OBJECT IDENTIFIER ::= {radAtmCsuDsu 12} -- RAD AMC102
radAmc102c  OBJECT IDENTIFIER ::= {radAtmCsuDsu 13} -- RAD AMC102 CARD

radAce202 OBJECT IDENTIFIER ::= { radAtmCsuDsu 14} -- RAD ACE202

radAce  OBJECT IDENTIFIER ::= {radSysAtm 3} --RAD ACE products
radAce101  OBJECT IDENTIFIER ::= {radAce 1} -- RAD ACE101
radAce102  OBJECT IDENTIFIER ::= {radAce 2} -- RAD ACE102
radAce50  OBJECT IDENTIFIER ::= {radAce 3} -- RAD ACE50

radSysLA	  OBJECT IDENTIFIER ::= {systems 13} --RAD  IAD (Integrated Access Device) products
radLA140      OBJECT IDENTIFIER ::= {radSysLA 1} -- RAD LA-140
radLA110      OBJECT IDENTIFIER ::= {radSysLA 2} -- RAD LA-110


agnt OBJECT IDENTIFIER ::= { radGen 2}
-- agent general tree
-- Agent General
agnHwVersion OBJECT-TYPE
      SYNTAX  DisplayString
      MAX-ACCESS  read-write
      STATUS  current
      DESCRIPTION
      "ASCII string for description and display of the agent hardware version,
      as it is known by the agent software.The user can update the version
       upon request when he changes   components in the agent's module  "
      ::= { agnt 1 }

agnTrapMask OBJECT-TYPE
      SYNTAX  Integer32
      MAX-ACCESS  read-write
      STATUS  current
      DESCRIPTION
      "The value of this attribute determines the type of traps the
       agent should mask and not send to the management console. The
       value is differently determined for different products. There are
       mainly two methods:
       - an integer number, specifying the traps' severity.
       - a sum of 2**n, where n is a bit assigned to a certain
         masked trap group.
       User should consult the product specification, to find out
       the method employed."
      ::= { agnt 2 }

agnTrapValue OBJECT-TYPE
	SYNTAX  OCTET STRING
	MAX-ACCESS  read-only
	STATUS deprecated
	DESCRIPTION
	"The value of the trap decoded in internal RAD format. Full description is given
	  in the Trap definition file"
	::= {agnt 3}

agnChangeCnt OBJECT-TYPE
	SYNTAX  Counter32
	MAX-ACCESS  read-only
	STATUS current
	DESCRIPTION
	"The number of changes in system configuration that were  reported to the
	manager since last cold start"
	::= {agnt 4 }

agnSpecific OBJECT-TYPE
      SYNTAX  OBJECT IDENTIFIER
      MAX-ACCESS  read-only
      STATUS  current
      DESCRIPTION
      " Object identifier of entity containing additional information
      regarding this instance."
      ::= { agnt 5}

agnConfigMsg OBJECT-TYPE
      SYNTAX  OCTET STRING
      MAX-ACCESS  read-only
      STATUS  current
      DESCRIPTION
      "Full configuration message  coded in internal RAD application format.
       This entry describes agent's configuration.

       For MP-2200 R3, this object describes agent's support of the V5.1
       feature: 1 octet ; bit 0 (LSB).
       '1' - V5.1 feature is supported
       '0' - V5.1 feature is not supported."
      ::= { agnt 6 }

-- Manager table to record all IP addresses

mngTrapIpTable  OBJECT-TYPE
	SYNTAX  SEQUENCE OF MngEntry
	MAX-ACCESS  not-accessible
	STATUS current
	DESCRIPTION
	"This table indicates  the destination address of the traps.
	  Internally it will be limited to ten addresses. "
	::= { agnt 7 }

mngEntry OBJECT-TYPE
	SYNTAX  MngEntry
	MAX-ACCESS  not-accessible
	STATUS current
	DESCRIPTION  "An entry in table."
	INDEX {  mngID }
	::= { mngTrapIpTable 1 }


MngEntry  ::=
	    SEQUENCE {
	mngID
	  Integer32,
	mngIP
	  IpAddress,
	mngIPMask
	  IpAddress,
    mngTrapMask
      Integer32
    }

mngID OBJECT-TYPE
	SYNTAX  Integer32
	MAX-ACCESS  read-only
	STATUS current
	DESCRIPTION
	" This value indicates an index of a specific IP address"
	::= { mngEntry 1 }

mngIP OBJECT-TYPE
	SYNTAX  IpAddress
	MAX-ACCESS  read-write
	STATUS current
	DESCRIPTION
	"This value indicates  the  destination address of the traps. IP 0.0.0.0 removes the entry. "
	::= { mngEntry 2 }

mngIPMask OBJECT-TYPE
	SYNTAX  IpAddress
	MAX-ACCESS  read-write
	STATUS deprecated
	DESCRIPTION
	"This value indicates  the  mask of the destination addresses of the traps. "
	::= { mngEntry 3 }

mngTrapMask OBJECT-TYPE
	SYNTAX  Integer32
	MAX-ACCESS  read-write
	STATUS current
	DESCRIPTION
      "The value of this attribute determines the type of traps the
       agent should mask and not send to this NMS. The
       value is differently determined for different products. There are
       mainly two methods:
       - an integer number, specifying the traps' severity.
       - a sum of 2**n, where n is a bit assigned to a certain
         masked trap group.
       User should consult the product specification, to find out
       the method employed."
	::= { mngEntry 4 }

agnIndication OBJECT-TYPE
      SYNTAX  INTEGER {
		 faulty  (1), -- =major
		 warning (2),
		 normal  (3), -- off
		 minor   (4),
		 major   (5),
		 event   (6),
		 critical(7)
		}
      MAX-ACCESS  read-only
      STATUS  current
      DESCRIPTION
      "Attribute describing the state of the entity the agent is responsible for.
       In case of a modular entity, the value of this attribute will be according
       to the component which is in the worst state.
       The order of severity (from top to bottom) is:
       critical-> major (or faulty)-> minor-> event-> warning-> normal (off)."
      ::= { agnt 8 }


agnMonitorModeCmd OBJECT-TYPE
	SYNTAX  INTEGER {
	notApplicable(1),
	off(2),
	on(3)
	}
	MAX-ACCESS  read-write
	STATUS current
	DESCRIPTION
	"Setting this attribute to ON, will enforce the agent to change its mode of operation to
	 Monitor Mode"
	::= {agnt 9}

agnLed OBJECT-TYPE
	SYNTAX  OCTET STRING
	MAX-ACCESS  read-only
	STATUS current
	DESCRIPTION
	"This entry specifies  the LEDs status of the agent module . Each led will be represented by 4
	 bits  where the first 2 bits (left) will specify  the status :
	 (00=NA, 01=OFF, 10=ON, 11=BLINK),
     and the next two bits (right) will specify the color :
     (00=GREEN, 01=RED, 10=YELLOW, 11=GRAY)"
	::= {agnt 10}

trapTable  OBJECT-TYPE
	SYNTAX  SEQUENCE OF TrapEntry
	MAX-ACCESS  not-accessible
	STATUS current
	DESCRIPTION
	"This table includes the last few traps generated by the agent, for future retrieval. The table
	 has a limited capacity. If traps are not retrieved in proper time, they will be
	 over-written by new traps "
	::= {agnt 11}

trapEntry OBJECT-TYPE
	SYNTAX  TrapEntry
	MAX-ACCESS  not-accessible
	STATUS current
	DESCRIPTION  "An entry in table."
	INDEX {  trapID }
	::= { trapTable 1 }

TrapEntry  ::=
	    SEQUENCE {
	trapID
	  Integer32,
	trapVal
	  DisplayString,
	 trapTimeSinceOccurrence
	   TimeTicks
	}

trapID OBJECT-TYPE
	SYNTAX  Integer32
	MAX-ACCESS  read-only
	STATUS current
	DESCRIPTION
	" This value indicates an index of a specific trap "
	::= { trapEntry 1 }

trapVal OBJECT-TYPE
	SYNTAX  DisplayString
	MAX-ACCESS  read-only
	STATUS current
	DESCRIPTION
	"This value is the actual ASCII description  of the trap. "
	::= { trapEntry 2 }

trapTimeSinceOccurrence OBJECT-TYPE
	 SYNTAX    TimeTicks
	MAX-ACCESS  read-only
	STATUS current
	DESCRIPTION
	"This value indicates the amount of  time passed since the occurrence of the event that
	   trigger this trap. "
	::= { trapEntry 3 }

fileTransfer  OBJECT IDENTIFIER ::= { agnt 12 }

fileServerIP  OBJECT-TYPE
	SYNTAX  IpAddress
	MAX-ACCESS  read-write
	STATUS  current
	DESCRIPTION
	"The IP address of the server from which the file is loaded "
	::= { fileTransfer 1 }

fileName  OBJECT-TYPE
	SYNTAX  DisplayString
	MAX-ACCESS  read-write
	STATUS  current
	DESCRIPTION
	"The name of the file to be loaded. For protection, read returns
	 NULL. "
	::= { fileTransfer 2 }

fileTransCmd  OBJECT-TYPE
	SYNTAX  INTEGER {
	                 swDwnLoad     (1),
					 configDwnLoad (2),
					 configUpLoad  (3),
					 coProcDwnLoad (4),
					 stateUpLoad   (5),
					 dwnLoadUserFile   (6),
					 upLoadUserFile    (7),
					 swDwnLoadAndReset (8),
					 noOp            (255)
					}
	MAX-ACCESS  read-write
	STATUS  current
	DESCRIPTION
	"The command to be executed on fileName at fileServerIP."
	::= { fileTransfer 3 }

-- tftp  group

tftpRetryTimeOut OBJECT-TYPE
    SYNTAX  Integer32
    MAX-ACCESS  read-write
    STATUS  current
    DESCRIPTION
        " General Retransmission time-out value (seconds) "
    -- DEFVAL  { 15 }
    ::= { fileTransfer 4 }

tftpTotalTimeOut OBJECT-TYPE
    SYNTAX  Integer32
    MAX-ACCESS  read-write
    STATUS  current
    DESCRIPTION
        " Total Retransmission time-out value (seconds) "
    -- DEFVAL  { 60 }
    ::= { fileTransfer 5 }

tftpStatus OBJECT-TYPE
    SYNTAX  INTEGER {
		noOp(2),
		connecting(3),
		transferringData(4),
		endedTimeOut(5),
		endedOk(6),
		error(7)
	}
    MAX-ACCESS  read-write
    STATUS  current
    DESCRIPTION
    "Status of tftp session. When a session ended with success,
    the tftpStatus should be endedOk(6). Before restarting a
    tftp session, the NMS should set the tftpStatus to noOp(2).
    That's the reason of MAX-ACCESS read-write to this field."
    DEFVAL  { noOp}
    ::= { fileTransfer 6 }

tftpError OBJECT-TYPE
    SYNTAX  OCTET STRING ( SIZE(2) )
    MAX-ACCESS  read-only
    STATUS  current
    DESCRIPTION
    " The MSB represents the standard error code.
    The LSB represents the private error code.
    0x0000 is No Error
    0x0100 is File Not Found
    0x0400 is Illegal TFTP operation
    0x0500 is Unknown transfer ID
    0x0001 is Server Overflow
    0x0002 is No empty UDP port
    0x0003 is No empty connection
    0x0004 is Illegal File Mode
    0x0007 is Illegal PDU size "
    DEFVAL  { '0000'h }
    ::= { fileTransfer 7 }

fileTransferToSubSystems OBJECT-TYPE
    SYNTAX  OCTET STRING
    MAX-ACCESS  read-write
    STATUS  current
    DESCRIPTION
    " This object represents the sub-systems the fileTransCmd
      refers to. It should be used when a system is divided
      to sub-systems and each sub-system (or part of them) can
	  have a different SW/Configuration.

	  Each bit of this object will represent one of the sub-systems.
	  Bit='1' - APPLY to respective sub-system
	  Bit='0' - DO NOT APPLY to respective sub-system

	  For the meaning of each bit, see product's specification.
	  User will select the sub-systems envolved by filling-in the bits
      that represent these sub-systems.
      In this case, the file represented by 'fileName' will
	  include several parts, each representing one of the sub-systems.
	  The agent will refer only to the part/s indicated by this object.

      0 Octet Strings = not applicable
      DEFVAL = 0h	for  the products that support this object."
    ::= { fileTransfer 8 }


fileNameWithinProduct  OBJECT-TYPE
	SYNTAX  DisplayString
	MAX-ACCESS  read-write
	STATUS  current
	DESCRIPTION
	"The file name used by the product within the product file system."
	::= { fileTransfer 9 }

--Internal SW Download table

intSwdlTable  OBJECT-TYPE
      SYNTAX SEQUENCE OF IntSwdlEntry
      MAX-ACCESS not-accessible
      STATUS  current
      DESCRIPTION
      "This parameters table is for
       internal Software down load. It also includes data
       about all files contained in the Object from which
       down-load is performed."
      ::= { fileTransfer 10 }

intSwdlEntry OBJECT-TYPE
      SYNTAX IntSwdlEntry
      MAX-ACCESS not-accessible
      STATUS current
	DESCRIPTION  "An entry in table."
	INDEX {intSwdlObjIdx, intSwdlFileIdx }
      ::= { intSwdlTable 1}

IntSwdlEntry ::=
      SEQUENCE {
      intSwdlObjIdx            Integer32,
	  intSwdlFileIdx           Integer32,
	  intSwdlFileName		   DisplayString,
	  intSwdlFileSwVer		   DisplayString,
	  intSwdlSwDate			   DisplayString,
	  intSwdlSize			   DisplayString,
	  intSwdlCmd			   INTEGER,
	  intSwdlToSubSystem	   OCTET STRING
      }

intSwdlObjIdx OBJECT-TYPE
      SYNTAX  Integer32
      MAX-ACCESS  read-only
      STATUS  current
      DESCRIPTION
      "The index of the object from which down-load is performed."
      ::= {intSwdlEntry 1}

intSwdlFileIdx OBJECT-TYPE
      SYNTAX  Integer32
      MAX-ACCESS  read-only
      STATUS  current
      DESCRIPTION
      "The index of the files included in intSwdlObjIdx.
       One of these files can be selected to be internally
       downloaded."
      ::= {intSwdlEntry 2}

intSwdlFileName OBJECT-TYPE
      SYNTAX  	 DisplayString
      MAX-ACCESS  read-only
      STATUS  current
      DESCRIPTION
      "The name of the file."
      ::= {intSwdlEntry 3}

intSwdlFileSwVer OBJECT-TYPE
      SYNTAX  	 DisplayString
      MAX-ACCESS  read-only
      STATUS  current
      DESCRIPTION
      "The software version of the file."
      ::= {intSwdlEntry 4}

intSwdlSwDate OBJECT-TYPE
      SYNTAX  	 DisplayString
      MAX-ACCESS  read-only
      STATUS  current
      DESCRIPTION
      "The software version date of the file."
      ::= {intSwdlEntry 5}

intSwdlSize OBJECT-TYPE
      SYNTAX  	 DisplayString
      MAX-ACCESS  read-only
      STATUS  current
      DESCRIPTION
      "The size of the file."
      ::= {intSwdlEntry 6}

intSwdlCmd OBJECT-TYPE
      SYNTAX  	  INTEGER
	  				{
					notApplicable		(1),
					off		(2),
					on		(3)
					}
      MAX-ACCESS  read-write
      STATUS  current
      DESCRIPTION
      "The command to down-load a SW file to an object.
       The Agent will change the value of this MIB object to off(2)
	  automatically, after accepting the command."
      ::= {intSwdlEntry 7}

intSwdlToSubSystem	OBJECT-TYPE
      SYNTAX  OCTET STRING
      MAX-ACCESS  read-write
      STATUS  current
      DESCRIPTION
      " This object defines the subsystem for download.
       Bit='1'- APPLY to respective sub system.
       Bit='0'- DO NOT APPLY to respective sub system.
       For more details see product specification.
       For every octet bit0=LSB, bit7=MSB"
      ::= { intSwdlEntry  8 }

--SW Download Status table

swdlStatusTable  OBJECT-TYPE
      SYNTAX SEQUENCE OF SwdlStatusEntry
      MAX-ACCESS not-accessible
      STATUS  current
      DESCRIPTION
      "This parameters table is for software download status.
       It also includes data about the files down-loaded or
       attempted to be down-loaded."
      ::= { fileTransfer 11 }

swdlStatusEntry OBJECT-TYPE
      SYNTAX SwdlStatusEntry
      MAX-ACCESS not-accessible
      STATUS current
	DESCRIPTION  "An entry in table."
	INDEX {swdlStatusTypeIdx, swdlStatusIdx }
      ::= { swdlStatusTable 1}

SwdlStatusEntry ::=
      SEQUENCE {
      swdlStatusTypeIdx            Integer32,
	  swdlStatusIdx       		   Integer32,
	  swdlStatusFileName		   DisplayString,
	  swdlStatusSlot			   DisplayString,
	  swdlStatusSubSystem		   DisplayString,
	  swdlStatusStatus			   Integer32,
	  swdlStatusTime			   DisplayString
	       }

swdlStatusTypeIdx OBJECT-TYPE
      SYNTAX  Integer32
      MAX-ACCESS  read-only
      STATUS  current
      DESCRIPTION
      "The index of the down-load type (e.g. external (1) or internal (2))."
      ::= {swdlStatusEntry 1}

swdlStatusIdx OBJECT-TYPE
      SYNTAX  Integer32
      MAX-ACCESS  read-only
      STATUS  current
      DESCRIPTION
      "The index of the status rows."
      ::= {swdlStatusEntry 2}

swdlStatusFileName OBJECT-TYPE
      SYNTAX  	 DisplayString
      MAX-ACCESS  read-only
      STATUS  current
      DESCRIPTION
      "The name of the file."
      ::= {swdlStatusEntry 3}

swdlStatusSlot OBJECT-TYPE
      SYNTAX  	 DisplayString
      MAX-ACCESS  read-only
      STATUS  current
      DESCRIPTION
      "The slot of the updated (or attempted to be updated) object."
      ::= {swdlStatusEntry 4}

 swdlStatusSubSystem OBJECT-TYPE
      SYNTAX  	 DisplayString
      MAX-ACCESS  read-only
      STATUS  current
      DESCRIPTION
      "The subsystem that updated (or attempted to be updated)."
      ::= {swdlStatusEntry 5}

swdlStatusStatus  OBJECT-TYPE
      SYNTAX  	  Integer32
      MAX-ACCESS  read-only
      STATUS  current
      DESCRIPTION
      "The status of the down load process.
	  Value:  Fail (2), OK (3), InProcess (4)."
      ::= {swdlStatusEntry 6}

swdlStatusTime	   OBJECT-TYPE
          SYNTAX   DisplayString
          MAX-ACCESS  read-only
          STATUS  current
          DESCRIPTION
          "This MIB parameter indicates the time SW download was finished.
           The format shuld be YYYY-MM-DD, hh:mm:ss"

          ::= {swdlStatusEntry 7}

clearDwldStatusLog  OBJECT-TYPE
	SYNTAX  Integer32
	MAX-ACCESS  read-write
	STATUS  current
	DESCRIPTION
	"This object clears the status log.
	  Value: off(2), external(3), internal(4)
	  The Agent will change the value of this MIB object to off(2)
	  automatically, after accepting the command ."
	::= { fileTransfer 12 }


systemReset  OBJECT-TYPE
	SYNTAX  INTEGER	{
	                 off         (2),
					 on          (3), --HW
					 resetConfig (4)
				    }
	MAX-ACCESS  read-write
	STATUS  current
	DESCRIPTION
	"Reset action to be performed on the system."
	::= { agnt 13 }

systemTiming  OBJECT IDENTIFIER ::= { agnt 14 }

systemDate OBJECT-TYPE
        SYNTAX  DisplayString
        MAX-ACCESS  read-write
        STATUS  current
        DESCRIPTION
           "System date."
        ::= { systemTiming 1 }

systemTime OBJECT-TYPE
        SYNTAX  DisplayString
        MAX-ACCESS  read-write
        STATUS  current
        DESCRIPTION
           "System time."
        ::= { systemTiming 2 }


systemPort  OBJECT IDENTIFIER ::= { agnt 15 }

physicalConnectorTable OBJECT-TYPE
	SYNTAX  SEQUENCE OF PhysicalConnectorEntry
	MAX-ACCESS  not-accessible
	STATUS current
	DESCRIPTION
	"This table includes the connector type of ports or interfaces."
	::= {systemPort 1}

physicalConnectorEntry OBJECT-TYPE
	SYNTAX  PhysicalConnectorEntry
	MAX-ACCESS  not-accessible
	STATUS current
	DESCRIPTION  "An entry in table."
	INDEX {portIdx}
	::= { physicalConnectorTable 1 }

PhysicalConnectorEntry  ::=
	    SEQUENCE {
	portIdx
	  Integer32,
	physicalConnector
	  INTEGER,
	portOptWaveLength
	  INTEGER,
	portOptMode
	  INTEGER
	}

portIdx OBJECT-TYPE
	SYNTAX  Integer32
	MAX-ACCESS  read-only
	STATUS current
	DESCRIPTION
	"This object is an index of the specific port or interface.
	 For a port, the index will be as agreed between agent and
	 application.
	 For an interface, ifIndex may be used."
	::= { physicalConnectorEntry 1 }

physicalConnector OBJECT-TYPE
	SYNTAX  INTEGER
	        {
			other (1),
			v35   (2),	  --34 pin female
			rs530 (3),	  --DB25
			x21   (4),	  --DB15
			bnc   (5),
			utp   (6),	  --RJ45
			aui   (7),
			rs422 (8),	  --DB25
			crossUtp (9), --RJ45
			rj45    (10),
			v24     (11), --DB25
			g703    (12), --TB5
			termBlock3AndRj45 (13),
			terminalBlock3    (14),
			terminalBlock5    (15),
			terminalBlock7    (16),
			db25              (17),
			db15              (18),
			rj45ethernet      (19),
			termBlock5AndRj45 (20),
			db9               (21),
			g703E1            (22),  --BNC-RJ45-BNC
			g703E1-LTU        (23),  --BNC-RJ45-BNC
			sc                (24),	 --sc optical
			st                (25),	 --st optical
			stl               (26),
			fc                (27),	 --fc optical
			tb5w              (28),  --Term-Block-5-Wire (for HCD)
			termBlock6AndRj45 (29),
			ethBnc            (30),
			scsi26            (31),  --SCSI with 26 pins
			eth4381           (32),  --RJ45 with two embeded LEDs
			twoBnc			  (33),  --Two BNC
			scsi50            (34),  --SCSI with 50 pins
			twoMiniBnc        (35),  --Two mini BNC
			sf1               (36),  --sf1=single fiber optical
			terminalBlock4    (37),
			sf2         	  (38),  --sf2=single fiber optical
			db25Balanced      (39),  --DB25 Balanced
			v36               (40),
			block4W           (41),  --like in WR connector for Modems
			iripRj45          (42),
			irEthQRj45        (43),
			iripBnc           (44),
			rs530WA           (45),  --rs530/IR that solves a wander problem for SDH network
			v35WA             (46),  --v35/IR that solves a wander problem for SDH network
			irEthQBnc         (47),
			v35Db25           (48),  --V.35 with connector DB25
			rj11              (49),  --Used for FXS & FXO
			mtrj              (50),  --optical
			lc                (51),  --optical
			terminalBlock2    (52),
			irEth10s100       (53),  --IR-ETH 10/100
			scsi68            (54),  -- SCSI 68 pins
			none             (255)
			}
	MAX-ACCESS  read-only
	STATUS current
	DESCRIPTION
	"The connector of the port/interface.
	 other - none of the specified connectors
	 none -  no connector."
	::= { physicalConnectorEntry 2 }

portOptWaveLength OBJECT-TYPE
    SYNTAX  INTEGER {
		notApplicable(1),
		nm850(2),
		nm1300(3),
		nm1300Laser(4),
		nm1550Laser(5)
	}
    MAX-ACCESS  read-only
    STATUS  current
    DESCRIPTION
     "Wave Length of an Optical interface/port in [nm] and specification if
      Laser or not.
      notApplicable - for non-optical ports."
     ::= { physicalConnectorEntry 3 }

portOptMode OBJECT-TYPE
    SYNTAX  INTEGER {
		notApplicable(1),
		singleMode(2),
		multiMode(3)

	}
    MAX-ACCESS  read-only
    STATUS  current
    DESCRIPTION
     "Laser Mode of an Optical Laser interface/port.
       notApplicable - for non-Laser ports."
     ::= { physicalConnectorEntry 4 }



prtSupervisory  OBJECT IDENTIFIER ::= { systemPort 2 }


prtSpTable OBJECT-TYPE
      SYNTAX SEQUENCE OF PrtSpEntry
      MAX-ACCESS not-accessible
      STATUS current
	DESCRIPTION  "A table."
	::=  {prtSupervisory 1}

prtSpEntry OBJECT-TYPE
      SYNTAX PrtSpEntry
      MAX-ACCESS not-accessible
      STATUS current
      DESCRIPTION
      "Supervisory port parameter table."
      INDEX {prtSupervisoryIndex }
      ::= { prtSpTable 1}

PrtSpEntry ::=
      SEQUENCE {
      prtSupervisoryIndex       Integer32,
	  prtSupervisoryRate        INTEGER,
	  prtSupervisoryDataBits    INTEGER,
	  prtSupervisoryParity      INTEGER,
	  prtSupervisoryStopBits    INTEGER,
	  prtSupervisoryUsage       INTEGER,
	  prtSupervisoryInterface   INTEGER,
	  prtSupervisoryCTS		    INTEGER,
	  prtSupervisoryDcdDelay    INTEGER,
	  prtSupervisoryDSR		    INTEGER,
	  prtSupervisoryRoutProtocol   INTEGER
      }


prtSupervisoryIndex OBJECT-TYPE
      SYNTAX  Integer32
      MAX-ACCESS  read-only
      STATUS  current
      DESCRIPTION
      "The SP port index.
       The LS byte of the integer is the port index 1..255.
       The MS byte is different than 0 only if the port belongs to
       a module. In	that case it is the module number."
      ::= { prtSpEntry 1}

prtSupervisoryRate     OBJECT-TYPE
      SYNTAX  INTEGER
	      {
        auto      (1),
        s300bps   (2),
        s1200bps  (3),
        s2400bps  (4),
        s4800bps  (5),
        s9600bps  (6),
        s19200bps (7),
        s38400bps (8),
        s57600bps (9),
        s115200bps (10)
	      }
      MAX-ACCESS  read-write
      STATUS  current
      DESCRIPTION
      "This attribute indicates the operation rate (speed) of the
       port.
       auto - automatic rate selection, by the agent."
      ::= { prtSpEntry 2}

prtSupervisoryDataBits OBJECT-TYPE
      SYNTAX  INTEGER
	      {
        dataBits7 (1),
        dataBits8 (2)
	      }
      MAX-ACCESS  read-write
      STATUS  current
      DESCRIPTION
      "This attribute indicates the number of data bits in an async
       frame"
      ::= { prtSpEntry 3}

prtSupervisoryParity OBJECT-TYPE
      SYNTAX  INTEGER
	      {
        none  (1),
        odd   (2),
        even  (3)
	      }
      MAX-ACCESS  read-write
      STATUS  current
      DESCRIPTION
      "This attribute indicates the parity mode in an async frame"
      ::= { prtSpEntry 4}

prtSupervisoryStopBits OBJECT-TYPE
      SYNTAX  INTEGER
	      {
		notApplicable  (1),
        stopBits1      (2),
        stopBits1dot5  (3),
        stopBits2      (4)
	      }
      MAX-ACCESS  read-only
      STATUS  current
      DESCRIPTION
      "This attribute indicates the parity mode in an async frame."
      ::= { prtSpEntry 5}

prtSupervisoryUsage OBJECT-TYPE
      SYNTAX  INTEGER
	      {
		unknown (1),
		noUse   (2),
		terminal(3),
		nmsSlip (4),
		nmsPpp  (5),
		muxSlip (6),
		muxPpp  (7),
		dialOut (8)
	      }
      MAX-ACCESS  read-write
      STATUS  current
      DESCRIPTION
      "This attribute indicates the usage of the SP port."
      ::= { prtSpEntry 6}

prtSupervisoryInterface OBJECT-TYPE
      SYNTAX  INTEGER
	      {
		  notApplicable(1),
          dce  (2),
          dte  (3)
	      }
      MAX-ACCESS  read-write
      STATUS  current
      DESCRIPTION
      "This attribute indicates the supervisory port interface."
      ::= { prtSpEntry 7}

prtSupervisoryCTS OBJECT-TYPE
      SYNTAX  INTEGER
	      {
          	notApplicable   (1),
          	on            	(2),        --Old value for DCE.
			rts           	(3),        --Old value for DCE
			dteWait         (4),        --DTE will wait for CTS to become active before transmit date.
			dteIgnore       (5)         --DTE will Ignore CTS signal and will transmit date anyway.
	      }
      MAX-ACCESS  read-write
      STATUS  current
      DESCRIPTION
	  "CTS line state."
      ::= { prtSpEntry 8}

prtSupervisoryDcdDelay OBJECT-TYPE
      SYNTAX  INTEGER
	      {
          notApplicable (1),
          d0   (2),
          d10  (3),
		  d50  (4),
		  d100 (5),
		  d200 (6),
		  d300 (7)
	      }
      MAX-ACCESS  read-write
      STATUS  current
      DESCRIPTION
	  "DCD delay in msec."
      ::= { prtSpEntry 9}

prtSupervisoryDSR OBJECT-TYPE
      SYNTAX  INTEGER
	      {
          notApplicable (1),
          on   (2),
          dtr  (3)
	      }
      MAX-ACCESS  read-write
      STATUS  current
      DESCRIPTION
	  "DSR line state."
      ::= { prtSpEntry 10}

prtSupervisoryRoutProtocol OBJECT-TYPE
      SYNTAX  INTEGER
       {
        notApplicable (1),
  		none          (2),
        proprietary   (3),
        rip2          (4)
       }
      MAX-ACCESS  read-write
      STATUS  current
      DESCRIPTION
      "This attribute indicates the routing protocol of the port.
       notApplicable - for DP."
      ::= { prtSpEntry 11}

--Port Performance Data

prtPerformance  OBJECT IDENTIFIER ::= { systemPort 3 }

prtPerfTable OBJECT-TYPE
	SYNTAX  SEQUENCE OF PrtPerfEntry
	MAX-ACCESS  not-accessible
	STATUS current
	DESCRIPTION
	"This table includes G.826 ports or interfaces."
	::= {prtPerformance 1}

prtPerfEntry OBJECT-TYPE
	SYNTAX  PrtPerfEntry
	MAX-ACCESS  not-accessible
	STATUS current
	DESCRIPTION  "An entry in table."
	INDEX {prtPerfIdx, prtPerfPeriodRef}
	::= { prtPerfTable 1 }

PrtPerfEntry  ::=
	    SEQUENCE {
	prtPerfIdx
	  Integer32,
	prtPerfPeriodRef
	  INTEGER,
	prtPerfElapsedTime
	  Integer32,
	prtPerfUAS
	  Integer32,
	prtPerfES
	  Integer32,
	prtPerfSES
	  Integer32,
	prtPerfBBE
	  Integer32,
	prtPerfBlocksPerSec
	  Integer32,
	prtPerfTimeTag
	  TimeTicks,
	prtPerfSaveAndResetCmd
	  INTEGER
	  }

prtPerfIdx OBJECT-TYPE
	SYNTAX  Integer32
	MAX-ACCESS  read-only
	STATUS current
	DESCRIPTION
	"This object is an index of the specific port or interface.
	 For a port, the index will be as agreed between agent and
	 application.
	 For an interface, ifIndex may be used."
	::= { prtPerfEntry 1 }

prtPerfPeriodRef OBJECT-TYPE
	SYNTAX  INTEGER
	      {
          currentPeriod (1),
          lastPeriod    (2)
	      }
	MAX-ACCESS  read-only
	STATUS  current
	DESCRIPTION
	"This object is an index that specifies which period of time, the next
	 5 objects refer to.
	 currentPeriod - the period since last prtPerfSaveAndResetCmd received or
	           since Start-up (if no prtPerfSaveAndResetCmd was received since
	           Start-up) until now.
	 lastPeriod - the period between last two commands of prtPerfSaveAndResetCmd.
	           - If only one command occured since Start-up: the period between
	             Start-up and last command.
	           - If no command occured since Start-up: this period will not
	             actually exist. In this case, he following 5 objects will be 0."
	::= { prtPerfEntry 2 }

prtPerfElapsedTime OBJECT-TYPE
	SYNTAX  Integer32
	MAX-ACCESS  read-only
	STATUS  current
	DESCRIPTION
	"Elapsed Time in seconds.
	 - for prtPerfPeriodRef=currentPeriod:
	   The period since last prtPerfSaveAndResetCmd received or	since Start-up
	   (if no prtPerfSaveAndResetCmd was received since	Start-up) until now.
	 - for prtPerfPeriodRef=lastPeriod:
	   The value of prtPerfElapsedTime when last prtPerfSaveAndResetCmd
	   was received."
	::= { prtPerfEntry 3 }

prtPerfUAS OBJECT-TYPE
	SYNTAX  Integer32
	MAX-ACCESS  read-only
	STATUS  current
	DESCRIPTION
	"Number of Unavailable Seconds for the reference period (prtPerfPeriodRef)."
	::= { prtPerfEntry 4 }

prtPerfES OBJECT-TYPE
	SYNTAX  Integer32
	MAX-ACCESS  read-only
	STATUS  current
	DESCRIPTION
	"Number of Errored Seconds for the reference period (prtPerfPeriodRef)."
	::= { prtPerfEntry 5 }

prtPerfSES OBJECT-TYPE
	SYNTAX  Integer32
	MAX-ACCESS  read-only
	STATUS  current
	DESCRIPTION
	"Number of Severely Errored Seconds for the reference period (prtPerfPeriodRef)."
	::= { prtPerfEntry 6 }

prtPerfBBE OBJECT-TYPE
	SYNTAX  Integer32
	MAX-ACCESS  read-only
	STATUS  current
	DESCRIPTION
	"Number of Background Block (or Frame) Errors for the reference period
	 (prtPerfPeriodRef)."
	::= { prtPerfEntry 7 }

prtPerfBlocksPerSec OBJECT-TYPE
	SYNTAX  Integer32
	MAX-ACCESS  read-only
	STATUS  current
	DESCRIPTION
	"Blocks per second (or frames per second) of the port/interface indicated by
	 portIdx. This object is constant for a certain port/interface.
	 It is not affected by the prtPerfPeriodRef index."
	::= { prtPerfEntry 8 }

prtPerfTimeTag OBJECT-TYPE
	SYNTAX  TimeTicks
	MAX-ACCESS  read-only
	STATUS  current
	DESCRIPTION
	"Time Tag of Last Period: sysUpTime when last prtPerfSaveAndResetCmd was
	 executed.
	 This object is applicable only for prtPerfPeriodRef=lastPeriod.
	 For prtPerfPeriodRef=currentPeriod, the value will always be 0."
	::= { prtPerfEntry 9 }

prtPerfSaveAndResetCmd OBJECT-TYPE
    SYNTAX   INTEGER
	      {
    		off(2),
	    	on (3)
	      }
    MAX-ACCESS  read-write
    STATUS  current
    DESCRIPTION
    "A command per port/interface, to Save data of Current Period in Last Period
     data-set and start a new counting period for Current Period.
     This object is applicable only for prtPerfPeriodRef=currentPeriod.
     Setting this object to on(3) for prtPerfPeriodRef=last, will cause the agent
     to return: Bad Value response.
     When setting validly this object to on(3), agent will perform the required
     command and will reset automatically the value of this object to off(2).
     Setting this object to off(2), will do nothing."
    ::= { prtPerfEntry 10 }

--Port Test Data

prtTest OBJECT IDENTIFIER ::= { systemPort 4 }

prtTestTable OBJECT-TYPE
	SYNTAX  SEQUENCE OF PrtTestEntry
	MAX-ACCESS  not-accessible
	STATUS current
	DESCRIPTION
	"This table includes test data for ports or interfaces."
	::= {prtTest 1}

prtTestEntry OBJECT-TYPE
	SYNTAX  PrtTestEntry
	MAX-ACCESS  not-accessible
	STATUS current
	DESCRIPTION  "An entry in table."
	INDEX {prtTestIdx}
	::= { prtTestTable 1 }

PrtTestEntry  ::=
	    SEQUENCE {
     	prtTestIdx
	    Integer32,
    	prtTestCmdAndStatus
        Integer32,
    	prtBertCounter
        Integer32,
		prtTestInitiator
		INTEGER
        }

prtTestIdx OBJECT-TYPE
	SYNTAX  Integer32
	MAX-ACCESS  read-only
	STATUS current
	DESCRIPTION
	"This object is an index of the specific port or interface.
	 For a port, the index will be as agreed between agent and
	 application.
	 For an interface, ifIndex may be used."
	::= { prtTestEntry 1 }

prtTestCmdAndStatus OBJECT-TYPE
      SYNTAX  Integer32
      MAX-ACCESS  read-write
      STATUS  current
      DESCRIPTION
      "Setting this object to a value as detailed further on
       (except 0) will initiate a test on the specific port.
       The test/s requested will be set according to the respective
       bit. The value of this object will be a sum of (2**n), where n is
       the Bit:
         TEST                  BIT	                     VALUE
        -----------            ---						------
        reserved                0						   1
		PayloadLoop=RLB     	1 (=Remote Loopback)	   2
        LineLoop=DIG            2 (=Digital)			   4
        OtherLoop               3						   8
        InwardLoop=LLB          4 (=Local Loopback)       16
        BERT                    5						  32
        LC                      6                         64
		ToneInjection			7						 128


        e.g : If the requested value is 20 -> 010100  ->
              Bits 2 & 4 are set -> the requested tests are :
                                    LineLoopback=DIG
                                    InwardLoopback=LLB

       Not all tests combinations are valid.
	   For valid test combination, see each product's specification.

       The terminology and order of tests (except BERT) is according to
	   the one used for Test Status of DS1 and DS3 standards.
	   The notations : RLB, LLB, DIG are the most used in RAD's products, but they
	   can be different. For exact definition see product's spec.

       Setting this object to stop (value=0 ; all bits are 0),
       will stop all the user requested tests running on the
       selected port.

       When no test is running on the port, the Get value (test status)
	   will be 0.

	   PayloadLoop=RLB
	     The received signal at this interface is looped
	     through the device.  Typically the received signal
	     is looped back for retransmission after it has
	     passed through the device's framing function.

	   LineLoop=DIG
	     The received signal at this interface does not
	     go through the device (minimum penetration) but
	     is looped back out.

	   OtherLoop
	     Loopbacks that are not defined here.

	   InwardLoop=LLB
	     The sent signal at this interface is looped back
	     through the device.

	   LC
	     This loop is applicable only for HSSI interface, towards the router .

	   ToneInjection
		 This loop is applicable for analog voice (like FXS)."

   	  ::= { prtTestEntry 2 }

prtBertCounter   OBJECT-TYPE
      SYNTAX  Integer32
      MAX-ACCESS  read-only
      STATUS  current
      DESCRIPTION
      "This object indicates the number of BERT errors encountered
       during the BERT operation.
       It is valid only when BERT (Bit Error Rate Test) is active on the
       specific port.
       The Counter starts from zero (0) anytime BERT is initiated."
      ::= { prtTestEntry 3}

prtTestInitiator OBJECT-TYPE
    SYNTAX   INTEGER
	      {
    		unknown   (1),
    		user      (2),
	    	remoteUnit(3),
			dteRouter (4)
	      }
    MAX-ACCESS  read-only
    STATUS  current
    DESCRIPTION
    "This object indicates who initiated this port's test/s."
    ::= { prtTestEntry 4 }


--Port General Parameters

prtParam OBJECT IDENTIFIER ::= { systemPort 5 }

prtParamTable OBJECT-TYPE
	SYNTAX  SEQUENCE OF PrtParamEntry
	MAX-ACCESS  not-accessible
	STATUS current
	DESCRIPTION
	"This table includes general port parameters. The meaning is
	 different for every product that supports it due to a general
     parameter - prtControlCnfg.

	 For ACE2002:
	 This table is used as a mechanism to create the next interface index.
     The algorithm description:
     The NMS will send the agent the following get command: get(nextIfIndex.index),
     where index=interface on which the new index is dependent on.
     Upon this command the agent will generate and return the new index to the NMS."
	::= {prtParam 1}

prtParamEntry OBJECT-TYPE
	SYNTAX  PrtParamEntry
	MAX-ACCESS  not-accessible
	STATUS current
	DESCRIPTION  "An entry in table."
	INDEX {prtParamIdx}
	::= { prtParamTable 1 }

PrtParamEntry  ::=
	    SEQUENCE {
	prtParamIdx
	  Integer32,
	prtControlCnfg
	  Integer32,
    prtParamClkSrc
	  INTEGER,
    prtParamPhantom
	  INTEGER,
    prtParamResetStatsCmd
	  INTEGER,
	prtParamLastResetStatsTime
	  TimeStamp
	}

prtParamIdx OBJECT-TYPE
	SYNTAX  Integer32
	MAX-ACCESS  read-only
	STATUS current
	DESCRIPTION
	"This object is an index of the specific port or interface.
	 For a port, the index will be as agreed between agent and
	 application.
	 For an interface, ifIndex may be used.

	 For ACE2002:
	 This parameter is the physical layer ifIndex of the slot on
     which the NMS requires the next interface index."
	::= { prtParamEntry 1 }

prtControlCnfg OBJECT-TYPE
	SYNTAX  Integer32
	MAX-ACCESS  read-write
	STATUS current
	DESCRIPTION
	"This object may be used for port RW general parameter/s.
	 For detailed meaning, see product's spec.
	 Supported by: PRBi-E3/T3.

	 For ACE2002:
	 This parameter will include the value of the new index
	 generated by agent.

	 For Optimux-T3:
	 This parameter will be used for Release Remote LLB Command:
	 on=2= Set value only. Command to release LLB of Remote Unit.
	       Agent will return automatically to 'off' value after performing
	       the command.
	 off=3=Get value only.

	 For LA140
	 This parameter will be used as EchoCanceler per timeslot
	 off = 2 Echo Canceler is disabled
	 on =  3 Echo Canceler is enabled "
	::= { prtParamEntry 2 }

prtParamClkSrc OBJECT-TYPE
    SYNTAX  INTEGER {
       loopTiming    (1),
       localTiming   (2),
       throughTiming (3),
	   adaptive      (4),
	   notApplicable (255)
    }
    MAX-ACCESS  read-write
    STATUS  current
    DESCRIPTION
       "The source of Transmit Clock.
        'loopTiming' or 'loopback' indicates that the recovered receive clock
         is used as the transmit clock.

        'localTiming' or 'internal' indicates that a local clock
         source is used or when an external clock is
         attached to the box containing the interface.

        'throughTiming' or 'external' indicates that recovered receive clock
         from another card or interface is used as the transmit clock.

        'adaptive' indicates that the clock is recovered according
         to the received data flow rate. "
	::= { prtParamEntry 3 }


prtParamPhantom OBJECT-TYPE
    SYNTAX  INTEGER {
       notApplicable (1),
       disable       (2),
       enable        (3)
	}
	MAX-ACCESS  read-write
	STATUS current
	DESCRIPTION
	"Power feeding to another device."
	::= { prtParamEntry 4 }

prtParamResetStatsCmd OBJECT-TYPE
    SYNTAX  INTEGER {
       off(2),
	   on (3)
	}
    MAX-ACCESS  read-write
    STATUS  current
    DESCRIPTION
    "Reset statistics of the selected port."
    ::= { prtParamEntry 5 }

prtParamLastResetStatsTime OBJECT-TYPE
     SYNTAX  TimeStamp
     MAX-ACCESS  read-only
     STATUS  current
     DESCRIPTION
     "The value of MIB II's sysUpTime object at the last time that
      prtParamResetStatsCmd was Set to on(3) for this port.
      If prtParamResetStatsCmd was never Set to on(3) since last
      re-initialization of the agent, then this object contains a zero value.
      This object enables calculating the running time of Statistics
      counters for this port, by: [sysUpTime-prtParamLastResetStatsTime]."
     ::= { prtParamEntry 6 }


prtIP OBJECT IDENTIFIER ::= { systemPort 6 }

prtIpParamTable OBJECT-TYPE
	SYNTAX  SEQUENCE OF PrtIpParamEntry
	MAX-ACCESS  not-accessible
	STATUS current
	DESCRIPTION  "A table - Parameters for IP Ports."
	::= {prtIP 1}

prtIpParamEntry OBJECT-TYPE
	SYNTAX  PrtIpParamEntry
	MAX-ACCESS  not-accessible
	STATUS current
	DESCRIPTION  "An entry in table."
	INDEX { prtIpParamConfigIdx, prtIpParamSlotIdx, prtIpParamIdx }
	::= { prtIpParamTable 1 }

PrtIpParamEntry  ::=
    SEQUENCE {
    prtIpParamConfigIdx	      Integer32,
    prtIpParamSlotIdx  	      Integer32,
    prtIpParamIdx             Integer32,
	prtIpParamHostIP	      IpAddress,
	prtIpParamHostMask	      IpAddress,
	prtIpParamDefaultGateway  IpAddress,
	prtIpParamMediaMode		  INTEGER,
	prtIpParamMediaRate		  INTEGER,
	prtIpParamMngVlanSupport  INTEGER,
	prtIpParamMngVlanId       Integer32,
	prtIpParamMngVlanPriority Integer32,
	prtIpParamRingMode		  INTEGER
	}

prtIpParamConfigIdx OBJECT-TYPE
	SYNTAX  Integer32
	MAX-ACCESS  read-only
	STATUS current
	DESCRIPTION
	"This object indicates the Configuration number (1..255)
     referred.
     Value of 255 specifies the TmpCnfg (Scratch).
     For products having Agent and Edit configurations,
     Write operation for the table entries is allowed only to
     Config=255."
	::= { prtIpParamEntry 1 }

prtIpParamSlotIdx OBJECT-TYPE
    SYNTAX  Integer32
    MAX-ACCESS  read-only
    STATUS  current
    DESCRIPTION
    "This object indicates a unique number of the slot position
     in which the module is inserted.
     notApplicable = 255 (for products that don't have slots).

     For KM:
     kmxMlA (103),
     kmxMlB (104)."
    ::= { prtIpParamEntry 2 }

prtIpParamIdx OBJECT-TYPE
	SYNTAX  Integer32
	MAX-ACCESS  read-only
	STATUS current
	DESCRIPTION
	"This object indicates a unique Port Index."
	::= { prtIpParamEntry 3 }

prtIpParamHostIP OBJECT-TYPE
    SYNTAX  IpAddress
    MAX-ACCESS  read-write
    STATUS  current
    DESCRIPTION
    "The host interface IP address."
    ::= { prtIpParamEntry 4 }

prtIpParamHostMask OBJECT-TYPE
    SYNTAX  IpAddress
    MAX-ACCESS  read-write
    STATUS  current
    DESCRIPTION
    "The host interface subnet mask."
    ::= { prtIpParamEntry 5 }

prtIpParamDefaultGateway OBJECT-TYPE
    SYNTAX  IpAddress
    MAX-ACCESS  read-write
    STATUS  current
    DESCRIPTION
    "Default Gateway's IP Address."
    ::= { prtIpParamEntry 6 }

prtIpParamMediaMode OBJECT-TYPE
    SYNTAX  INTEGER
	{
       notApplicable (1),
       halfDuplex    (2),
       fullDuplex    (3)
    }
    MAX-ACCESS  read-only
    STATUS  current
    DESCRIPTION
    "This object indicates the real Media Mode."
    ::= { prtIpParamEntry 7 }

prtIpParamMediaRate OBJECT-TYPE
    SYNTAX  INTEGER
	{
       notApplicable (1),
       r10Mbps       (2),
       r100Mbps      (3)
    }
    MAX-ACCESS  read-only
    STATUS  current
    DESCRIPTION
    "This object indicates the real Media Rate (Mbps)."
    ::= { prtIpParamEntry 8 }

prtIpParamMngVlanSupport OBJECT-TYPE
    SYNTAX  INTEGER
    {
    notApplicable(1),
    no		(2),
    yes	    (3)
    }
    MAX-ACCESS  read-write
    STATUS  current
    DESCRIPTION
    "Management VLAN support (Tagging).
     no - No support of VLAN Tagging.
     yes - 4 VLAN bytes will be added to the frame."
    ::= { prtIpParamEntry 9 }

prtIpParamMngVlanId OBJECT-TYPE
     SYNTAX  Integer32
     MAX-ACCESS  read-write
     STATUS  current
     DESCRIPTION
     "Management VLAN ID."
     ::= { prtIpParamEntry 10 }

prtIpParamMngVlanPriority OBJECT-TYPE
     SYNTAX  Integer32
     MAX-ACCESS  read-write
     STATUS  current
     DESCRIPTION
     "Management VLAN Frame priority."
     ::= { prtIpParamEntry 11 }

prtIpParamRingMode OBJECT-TYPE
    SYNTAX  INTEGER
	{
       notApplicable (1),
       disable       (2),
       enable        (3)
    }
    MAX-ACCESS  read-write
    STATUS  current
    DESCRIPTION
    "This object indicates If Ring Mode is enabled or not."
    ::= { prtIpParamEntry 12 }


systemResetAllStatsCmd OBJECT-TYPE
      SYNTAX   INTEGER
	      {
    		off(2),
	    	on (3)
	      }
      MAX-ACCESS  read-write
      STATUS  current
      DESCRIPTION
       "Reset statistics of all ports and connections of the device."
      ::= { agnt 16 }

systemClearTablesCmd OBJECT-TYPE
      SYNTAX   INTEGER
	      {
    		off(2),
	    	tempCnfgTables (3)
	      }
      MAX-ACCESS  read-write
      STATUS  current
      DESCRIPTION
       "tempCnfgTables - Set *RowStatus = destroy for all entries of
                         some tables having *RowStatus object, for
                         temporary configuration only! (255).
                         For the relevant tables, see product's specification.
                         This object should be used by WAN product applications
                         before performing the Update operation, in order to clear
                         old entries of these tables.
        off - agent will automatically change to this value, after performing the
              command. "
      ::= { agnt 17 }

systemParameter OBJECT-TYPE
      SYNTAX   Integer32
      MAX-ACCESS  read-write
      STATUS  current
      DESCRIPTION
       "This parameter can be used for different purposes:
        - TELNET session time-out in seconds.
	   	- Ace20: when trying to create row in a table that already
				 has row with the same values, if set of values has to be unique
				 in table, this attribute is set to the index of the existing row.
		- Optimux-T3: when CH interfaces are RJ-45, user can select via this
		         object, the interface type for each Group of channels: T1 or E1:
		         The selection will be a sum of the following Bits.
		         '0' = T1
		         '1' = E1
		         Bit    Group               Value for each Bit having '1'
				  1		  1 (CH-1..CH-8)        	  1
				  2		  2 (CH-9..CH-12)       	  2
				  3		  3 (CH-13..CH-20)	          4
				  4		  4 (CH-21..CH-28)	          8
				 Examples:
				 15 = all Groups are selected to be E1
				  6 = Group 2 and Group 3 are selected to be E1
				     (Group 1 and Group 4 are T1).
		- FCD-A, FCD-M: user can select via this object the configuration
		         used for Get values of MSDSL parameters that don't have
		         configuration index.
		         1  =active configuration
		         255=temporary configuration.
		         Set of this object should be done before Getting the MSDSL
		         RW parameters.
		- Ace2002: This parameter indicates the number of intervals that
		         were successfully uploaded upon statistics collection session.

		- FCD-IP, WR, FCD-IPD, LA-240:
		         This parameter indicates whether Telnet Access is enabled/disabled:
		         Values:
				 2 - Telnet Access is Disabled.
				 3 - Telnet Access is Enabled. "
       ::= { agnt 18 }


agnGlobalAlarmMask OBJECT-TYPE
      SYNTAX OCTET STRING
      MAX-ACCESS  read-write
      STATUS  current
      DESCRIPTION
      "The value of this attribute determines the alarm traps the
       agent should mask and not send to the managers.
       Each bit from a certain octet represents a certain alarm."
      ::= { agnt 19 }

alarmSeverity   OBJECT-TYPE
      	SYNTAX   INTEGER
	      	{
			event		(3),
			minor		(4),
			major		(5),
	    	warning		(6),
			critical	(7)
	  		}
      	MAX-ACCESS  read-only
      	STATUS  current
      	DESCRIPTION
       	"This object specifies the severity of the alarms."
      ::= { agnt 20 }

alarmState   OBJECT-TYPE
      	SYNTAX   INTEGER
	      	{
			off (2), 	-- End,
			on  (3) 	-- Start.
	  		}
      	MAX-ACCESS  read-only
      	STATUS  current
      	DESCRIPTION
       "."
      ::= { agnt 21 }


agnTestStatus OBJECT-TYPE
	SYNTAX	INTEGER
		{
		 off			(2),
		 on 			(3)
		}

	MAX-ACCESS	read-only
	STATUS	current
	DESCRIPTION
	"Indicates the current test status (for all levels: system,
	   card, port).
       This attribute will be set to:
         on(3): when there is at least one test	in progress on the
                system/card/port
		 off(2): when there is NO test in progress on the
    	         system/card/port"
      ::= {agnt 22  }

systemSaveAndResetAllStatsCmd OBJECT-TYPE
      SYNTAX   INTEGER
	      {
    		off(2),
	    	on (3)
	      }
    MAX-ACCESS  read-write
    STATUS  current
    DESCRIPTION
    "on  - a command to Save data of Current Period in Last Period
           data-set and start a new counting period for Current Period.
     off - agent will automatically change to this value, after performing the
           command."
      ::= { agnt 23 }

systemDefaultGateway OBJECT-TYPE
      SYNTAX   IpAddress
    MAX-ACCESS  read-write
    STATUS  current
    DESCRIPTION
    "Default Gateway's IP Address."
      ::= { agnt 24 }

-- PS Table
systemPsTable OBJECT-TYPE
	SYNTAX  SEQUENCE OF SystemPsEntry
	MAX-ACCESS  not-accessible
	STATUS current
	DESCRIPTION
	"This table describes the PS types of a device.
	Usage of this table is specified in the device's NMS SRS"
	::= { agnt 25 }

systemPsEntry OBJECT-TYPE
	SYNTAX  SystemPsEntry
	MAX-ACCESS  not-accessible
	STATUS current
	DESCRIPTION  "An entry in table."
	INDEX {systemPsIndex1, systemPsIndex2}
	::= { systemPsTable 1 }

SystemPsEntry  ::=
	    SEQUENCE {
	systemPsIndex1
	  Integer32,
	systemPsIndex2
	  Integer32,
	systemPsType
	  INTEGER,
	systemPsStatus
	  INTEGER
	}

systemPsIndex1 OBJECT-TYPE
	SYNTAX  Integer32
	MAX-ACCESS  read-only
	STATUS current
	DESCRIPTION
	"First Index.
	In HUBs:
	1 = PS-A slot
	2 = PS-B slot.
	In SA units:
	1 = PS1
	2 = PS2
	Default = 1"
	::= { systemPsEntry 1 }

systemPsIndex2 OBJECT-TYPE
	SYNTAX  Integer32
	MAX-ACCESS  read-only
	STATUS current
	DESCRIPTION
	"Second Index.
	In HUBs:
	1 always.
    In SA units:
	1 = Local
	2 = Remote
	Default = 1."
	::= { systemPsEntry 2 }

systemPsType OBJECT-TYPE
      SYNTAX  INTEGER
	      {
		  none  (1),
	      ac    (2),
	      dc    (3),
		  acDc  (4),
		  acPF  (5),
		  dcPF  (6)
	      }
      MAX-ACCESS  read-only
      STATUS  current
      DESCRIPTION
      "The type of PS, for a stand-alone product.
      acDc - AC with rj45 DC.
      acPF - Power Feeding (phantom) box that is feeding another box by external AC.
      dcPF - Power Feeding (phantom) box that is feeding another box by external DC."
      ::= { systemPsEntry 3 }

systemPsStatus OBJECT-TYPE
      SYNTAX  INTEGER
	      {
		  notApplicable  (1),
	      failed         (2),
	      ok             (3)
	      }
      MAX-ACCESS  read-only
      STATUS  current
      DESCRIPTION
      "The Status of the PS unit."
      ::= { systemPsEntry 4 }

--agnt 26-29 are free for use

xcIndexNext  OBJECT-TYPE
          SYNTAX         Integer32 (0..2147483647)
          MAX-ACCESS         read-only
          STATUS         current
          DESCRIPTION
           "This object contains an appropriate value to
            be used for xcIndex when creating
            entries in the xcTable.  The value
            0 indicates that no unassigned entries are
            available. To obtain the xcIndex
            value for a new entry, the manager issues a
            management protocol retrieval operation to obtain
            the current value of this object.  After each
            retrieval, the agent should modify the value to
            the next unassigned index.
            After a manager retrieves a value the agent will
            determine through its local policy when this index
            value will be made available for reuse."
          ::= { agnt 30 }

--XC Table
xcTable OBJECT-TYPE
      SYNTAX SEQUENCE OF XcEntry
      MAX-ACCESS not-accessible
      STATUS current
      DESCRIPTION
      "Configuration of system cross-connect entries.
      The table follows the behavior described in RFC 2515,
      RFC 1604 regarding the creation deletion and modification
      of an entry within the table."
      ::= { agnt 31 }

xcEntry OBJECT-TYPE
      SYNTAX XcEntry
      MAX-ACCESS not-accessible
      STATUS current
	DESCRIPTION  "An entry in table."
	INDEX { xcIndex, xcIfIndex1, xcVpi, xcVci, xcIfIndex2 }
      ::= { xcTable 1}

XcEntry ::=
      SEQUENCE {
	 xcIndex        Integer32,
     xcIfIndex1   	Integer32,
     xcVpi 	        Integer32,
     xcVci 	        Integer32,
     xcIfIndex2   	Integer32,
	 xcRowStatus    RowStatus,
	 xcDescr        DisplayString,
     xcAdminStatus  INTEGER,
     xcOperStatus   INTEGER
      }

xcIndex OBJECT-TYPE
      SYNTAX  Integer32
      MAX-ACCESS  not-accessible
      STATUS  current
      DESCRIPTION
      "Cross Connect Identifier."
      ::= { xcEntry 1 }

xcIfIndex1 OBJECT-TYPE
      SYNTAX  Integer32
      MAX-ACCESS  not-accessible
      STATUS  current
      DESCRIPTION
      "The interface Index from the ifTable, which identify one side
      of the connection."
      ::= { xcEntry 2 }

xcVpi OBJECT-TYPE
      SYNTAX  Integer32
      MAX-ACCESS  read-create
      STATUS  current
      DESCRIPTION
      "."
      ::= { xcEntry 3 }

xcVci OBJECT-TYPE
      SYNTAX  Integer32
      MAX-ACCESS  read-create
      STATUS  current
      DESCRIPTION
      "."
      ::= { xcEntry 4 }

xcIfIndex2 OBJECT-TYPE
      SYNTAX  Integer32
      MAX-ACCESS  read-create
      STATUS  current
      DESCRIPTION
      "The interface Index from the ifTable, which identifies the other
      side of the connection."
      ::= { xcEntry 5 }

xcRowStatus  OBJECT-TYPE
      SYNTAX  RowStatus
     MAX-ACCESS   read-create
     STATUS   current
     DESCRIPTION
     "This parameter allows NMS to create/delete entries of this table."
     ::= { xcEntry 6 }

xcDescr  OBJECT-TYPE
     SYNTAX  DisplayString
     MAX-ACCESS   read-create
     STATUS   current
     DESCRIPTION
     "A textual string containing information about the
      xc entry."
     ::= { xcEntry 7 }


xcAdminStatus OBJECT-TYPE
        SYNTAX   INTEGER {
           up(1),
           down(2)
            }
      MAX-ACCESS  read-create
      STATUS  current
      DESCRIPTION
                 "The desired administrative status of this
            bi-directional cross-connect."
      ::= { xcEntry 8 }

xcOperStatus OBJECT-TYPE
        SYNTAX   INTEGER {
           up(1),
           down(2),
           unknown(3)
           }
      MAX-ACCESS  read-only
      STATUS  current
      DESCRIPTION
      "The operational status of this bi-directional
      cross-connect."
      ::= { xcEntry 9 }

systemModule  OBJECT IDENTIFIER ::= { agnt 32 }

modlParam  OBJECT IDENTIFIER ::= { systemModule 1 }

modlParamTable OBJECT-TYPE
      SYNTAX SEQUENCE OF ModlParamEntry
      MAX-ACCESS not-accessible
      STATUS current
      DESCRIPTION
      "This table include parameters for system modules."
      ::= { modlParam 1 }

modlParamEntry OBJECT-TYPE
      SYNTAX ModlParamEntry
      MAX-ACCESS not-accessible
      STATUS current
	DESCRIPTION  "An entry in table."
	INDEX { modlParamIndex }
      ::= { modlParamTable 1}

ModlParamEntry ::=
      SEQUENCE {
	 modlParamIndex        Integer32,
     modlParamReset 	    INTEGER,
     modlParamSwdlStatus	INTEGER
      }

modlParamIndex OBJECT-TYPE
      SYNTAX  Integer32
      MAX-ACCESS  read-only
      STATUS  current
      DESCRIPTION
      "The module index."
      ::= { modlParamEntry 1 }

modlParamReset  OBJECT-TYPE
	SYNTAX  INTEGER	{
	                 off         (2),
					 on          (3),
					 factory	 (4)
				    }
	MAX-ACCESS  read-write
	STATUS  current
	DESCRIPTION
	"Reset action to be performed on the module.
	 Set the parameter will be done always to on(3) or factory (4).
	 After performing the Reset operation, Agent will automatically set the parameter to off(2)."
	::= { modlParamEntry 2 }

 modlParamSwdlStatus  OBJECT-TYPE
      SYNTAX  	  INTEGER	{
	                 notApplicable	(1),
	                 off         	(2),
					 inProcess   	(3)
					 	    }
      MAX-ACCESS  read-only
      STATUS  current
      DESCRIPTION
      "This parameter indicates whatever the swdl is in process or not."
      ::= {modlParamEntry 3}


agnNearFarConnection OBJECT-TYPE
      SYNTAX  INTEGER {
		 notApplicable	(1),
		 disconnected  	(2),
		 connected 		(3)
		 		}
      MAX-ACCESS  read-only
      STATUS  current
      DESCRIPTION
      "This parameter describes the connection between near-end and far-end agents."
      ::= { agnt 33 }


--TRAPS

--NOTIFICATIONS

systemsEvents OBJECT-IDENTITY
     STATUS  current
     DESCRIPTION
     "The events for RAD products."
     ::= { systems 0 }

tftpStatusChangeTrap  NOTIFICATION-TYPE
     OBJECTS       { tftpStatus }
     STATUS current
     DESCRIPTION
     "This trap is sent whenever the status of tftp changed."
     ::= { systemsEvents 1 }

agnStatusChangeTrap  NOTIFICATION-TYPE
	OBJECTS		{agnIndication }
    STATUS current
	DESCRIPTION
	"This trap is sent whenever the state of the entity the agent is
	 responsible for changed.
	 TDM devices will send agnTestStatus variable to indicate the current test status."
	::= { systemsEvents 2 }

prtStatusChangeTrap  NOTIFICATION-TYPE
    STATUS current
	DESCRIPTION
	"This trap is sent whenever the state of a port changed.
	 Attached, will be parameter/s that indicate the new port status.
	 The attached variables will be specified in the specifications
	 of the products supporting this trap."
	::= { systemsEvents 3 }

swdlStatusResult	    NOTIFICATION-TYPE
	OBJECTS			{swdlStatusFileName}
    STATUS  current
	DESCRIPTION
	"This notification is sent when Software Down Load is finished.
	 The attached object indicates the File Name."
	::= { systemsEvents 4 }

intSwdlSlotFileMismatch	    NOTIFICATION-TYPE
	OBJECTS			{intSwdlFileName}
    STATUS  current
	DESCRIPTION
	"This notification is sent when the card in the chosen slot doesn't match
	 the chosen file.
	 The attached object indicates the File Name."
	::= { systemsEvents 5 }

agnCounterChange  NOTIFICATION-TYPE
    STATUS  current
	DESCRIPTION
	"This notification is sent when the value of a specific Counter is changed.
	 Agent can send as attached object the updated Counter.
	 For details about this Counter and attached object, see spec of the relevant
	 application."
	::= { systemsEvents 6 }

prtClkSrcChangeTrap NOTIFICATION-TYPE
      STATUS  current
      DESCRIPTION
	  "This trap is sent upon any port clock change."
    ::= { systemsEvents 7 }

moduleFailTrap NOTIFICATION-TYPE
      STATUS  current
      DESCRIPTION
	  "This trap is sent upon a module failure."
    ::= { systemsEvents 8 }

moduleInitFailTrap NOTIFICATION-TYPE
    STATUS current
      DESCRIPTION
	  "This trap is sent upon a module initialization failure."
	::= { systemsEvents 9 }

clkSrcChangeTrap NOTIFICATION-TYPE
      STATUS  current
      DESCRIPTION
	  "This trap is sent upon any change in Clock Source."
    ::= { systemsEvents 10 }

agnUploadDataTrap  NOTIFICATION-TYPE
     STATUS current
     DESCRIPTION
     "This trap is sent upon an upload data session termination.
     For more details see product specification."
     ::= { systemsEvents 11 }

enrollmentTrap  NOTIFICATION-TYPE
     STATUS current
     DESCRIPTION
     "This trap is a periodically trap, which sent to manager
     untill Agent get any response (Get or Set) from this manager."
     ::= { systemsEvents 12 }

agnPowerFailureTrap  NOTIFICATION-TYPE
     STATUS current
     DESCRIPTION
     "This trap is sent upon power failure. It is applicable for
     devices having one PS unit, which sense in advance the failure,
     and still have time to send this trap before it goes off."
     ::= { systemsEvents 13 }
--
-- file :v:\doc\rdv\mib\ver480\radds1.txt
--
-- RAD-DS1-MIB DEFINITIONS ::= BEGIN

--Title:    RAD-DS1   MIB
--
-- Copyright 1998 RAD Data Communications, Ltd.
-- All Rights Reserved.

-- IMPORTS
-- PerfCurrentCount, PerfIntervalCount	FROM PerfHist-TC-MIB;

--      OBJECT-TYPE                     FROM RFC-1212
 --     radWan                          FROM RAD-GEN-MIB;
--                RAD-DS1 MIB

--Title:     RAD's DS1 INTERFACE MIB
--Version:   1.0
--Date:      03.02.98
--By:        Ilana Schvetz
--File:      radds1.mib

-- Last updated by Shlomo Shoham 10-Jan-2002

ds1Interface  OBJECT IDENTIFIER  ::=  {diverseIfWanGen 4}
prtDs1PerfHistory  OBJECT IDENTIFIER  ::=  {ds1Interface 1}

  --   Extension to the dsx1 current table

dsx1XCurrentTable  OBJECT-TYPE
       SYNTAX      SEQUENCE OF Dsx1XCurrentEntry
       MAX-ACCESS  not-accessible
       STATUS      current
       DESCRIPTION
               "A list of current statistics entries.  This table
               contains additional objects for the current table."
       ::= { prtDs1PerfHistory 2 }

dsx1XCurrentEntry OBJECT-TYPE
       SYNTAX  Dsx1XCurrentEntry
       MAX-ACCESS  not-accessible
       STATUS      current
       DESCRIPTION
               "An entry containing additional statistical counters
               applicable to a particular current table."
 --      AUGMENTS    { dsx1CurrentEntry }
         INDEX   { dsx1CurrentIndex }
       ::= { dsx1XCurrentTable 1 }

Dsx1XCurrentEntry     ::=
      SEQUENCE {
        dsx1CurrentLOS		    PerfCurrentCount,
        dsx1CurrentLOF		    PerfCurrentCount,
        dsx1CurrentLOC			PerfCurrentCount,
        dsx1CurrentAIS		    PerfCurrentCount,
        dsx1CurrentRAI			PerfCurrentCount,
        dsx1CurrentLOMF			PerfCurrentCount,
        dsx1CurrentFEBE			PerfCurrentCount,
        dsx1CurrentStatus		OCTET STRING,
		dsx1CurrentBPV			PerfCurrentCount,
		dsx1CurrentLOCRCMF	    PerfCurrentCount,
		dsx1CurrentLOFC			PerfCurrentCount
}



dsx1CurrentLOS OBJECT-TYPE
              SYNTAX PerfCurrentCount
              MAX-ACCESS  read-only
              STATUS  current
              DESCRIPTION
                      "The counter associated with the number of LOS
                       seconds, encountered by a DS1 interface in
                      the current 15 minute interval."
              ::= { dsx1XCurrentEntry 1 }

dsx1CurrentLOF OBJECT-TYPE
              SYNTAX PerfCurrentCount
              MAX-ACCESS  read-only
              STATUS  current
              DESCRIPTION
                      "The counter associated with the number of LOF
                       seconds, encountered by a DS1
                       interface in the current 15 minute interval."
              ::= { dsx1XCurrentEntry 2 }


dsx1CurrentLOC OBJECT-TYPE
              SYNTAX PerfCurrentCount
              MAX-ACCESS  read-only
              STATUS  current
              DESCRIPTION
                      " Loss Of Cell delineation. Counts number of cells the ATM UNI cells receiver
                         lost cells delineation ."
              ::= { dsx1XCurrentEntry 3 }

dsx1CurrentAIS OBJECT-TYPE
              SYNTAX PerfCurrentCount
              MAX-ACCESS  read-only
              STATUS  current
              DESCRIPTION
                      "The counter associated with the number of AIS
                      seconds, encountered by a DS1
                      interface in the current 15 minute interval."
              ::= { dsx1XCurrentEntry 4 }

dsx1CurrentRAI OBJECT-TYPE
              SYNTAX PerfCurrentCount
              MAX-ACCESS  read-only
              STATUS  current
              DESCRIPTION
                      "Remote Alarm Indication: Transmitted  in the outgoing direction
	         (toward the PABX) over FDL bits when the DS1 device detected
                       an incoming Loss Of Frame. Received from the far end (PABX)
                       over FDL when it detects a Loss of frame."
              ::= { dsx1XCurrentEntry 5 }

dsx1CurrentLOMF OBJECT-TYPE
              SYNTAX PerfCurrentCount
              MAX-ACCESS  read-only
              STATUS  current
              DESCRIPTION
                      "Loss of Multi-Frame sequence  in E1 time slot 16."
              ::= { dsx1XCurrentEntry 6 }

dsx1CurrentFEBE OBJECT-TYPE
              SYNTAX PerfCurrentCount
              MAX-ACCESS  read-only
              STATUS  current
              DESCRIPTION
              "Far End Block Errors, as reported in the first bit
               of frames 13 and 15, on multiframe E1 lines with CRC4,
               in the current 15 minute interval."
              ::= { dsx1XCurrentEntry 7 }


dsx1CurrentStatus OBJECT-TYPE
	SYNTAX OCTET STRING  (SIZE (4))
              MAX-ACCESS  read-only
              STATUS  current
              DESCRIPTION
                      "The statuses of the current interval:
                        0 - Valid.
                        1 - redundantLinkSwitch - the link has been switched
                            by a redundancy mechanism.
                        2 - discontinuity - module was partialy out.
                        4 - notValid - module is out."
              ::= { dsx1XCurrentEntry 8 }

dsx1CurrentBPV OBJECT-TYPE
              SYNTAX PerfCurrentCount
              MAX-ACCESS  read-only
              STATUS  current
              DESCRIPTION
              "The counter associated with the number of BPVs (Bi-Polar Violations)
               encountered by a DS1	interface in the current 15 minute interval."
              ::= { dsx1XCurrentEntry 9 }

dsx1CurrentLOCRCMF OBJECT-TYPE
              SYNTAX PerfCurrentCount
              MAX-ACCESS  read-only
              STATUS  current
              DESCRIPTION
              "Loss of CRC4 Multi-Frame sequence in E1."
              ::= { dsx1XCurrentEntry 10 }

dsx1CurrentLOFC	OBJECT-TYPE
              SYNTAX PerfCurrentCount
              MAX-ACCESS  read-only
              STATUS  current
              DESCRIPTION
              "Counts the number of loss of frame events measured.
               encountered in the current 15 minute interval"
              ::= { dsx1XCurrentEntry 11 }


-- Interval table

dsx1XIntervalTable OBJECT-TYPE
              SYNTAX  SEQUENCE OF Dsx1XIntervalEntry
              MAX-ACCESS  not-accessible
              STATUS  current
              DESCRIPTION
                      " A list of Interval entries.  This table
                         contains additional objects for the interval table."
              ::= { prtDs1PerfHistory 3 }

dsx1XIntervalEntry OBJECT-TYPE
              SYNTAX  Dsx1XIntervalEntry
              MAX-ACCESS  not-accessible
              STATUS  current
              DESCRIPTION
                      "An entry containing additional statistical counters
                        applicable to a particular interval table."
   --	AUGMENTS    { dsx1IntervalEntry }
               INDEX   { dsx1IntervalIndex, dsx1IntervalNumber }
              ::= { dsx1XIntervalTable 1 }

Dsx1XIntervalEntry     ::=
          SEQUENCE {
        	dsx1IntervalLOS				PerfIntervalCount,
            dsx1IntervalLOF				PerfIntervalCount,
	        dsx1IntervalLOC             PerfIntervalCount,
        	dsx1IntervalAIS			    PerfIntervalCount,
	        dsx1IntervalRAI				PerfIntervalCount,
	        dsx1IntervalLOMF			PerfIntervalCount,
			dsx1IntervalFEBE			PerfIntervalCount,
            dsx1IntervalStatus		    OCTET STRING,
        	dsx1IntervalBPV				PerfIntervalCount,
			dsx1IntervalLOCRCMF         PerfIntervalCount,
			dsx1IntervalLOFC			PerfIntervalCount
}


dsx1IntervalLOS OBJECT-TYPE
              SYNTAX PerfIntervalCount
              MAX-ACCESS  read-only
              STATUS  current
              DESCRIPTION
                      "The counter associated with the number of LOS
                      seconds , encountered by a DS1 interface in
                      one of the previous 96, individual 15 minute,
                      intervals."
              ::= { dsx1XIntervalEntry 1 }

dsx1IntervalLOF OBJECT-TYPE
              SYNTAX PerfIntervalCount
              MAX-ACCESS  read-only
              STATUS  current
              DESCRIPTION
                      "The counter associated with the number of OOF
                      seconds, encountered by a DS1
                      interface in one of the previous 96, individual 15
                      minute, intervals."
              ::= { dsx1XIntervalEntry 2 }

dsx1IntervalLOC OBJECT-TYPE
              SYNTAX PerfIntervalCount
              MAX-ACCESS  read-only
              STATUS  current
              DESCRIPTION
                      " Loss Of Cell delineation. Counts number of cells the ATM UNI cells receiver
                         lost cells delineation ."
              ::= { dsx1XIntervalEntry 3 }

dsx1IntervalAIS OBJECT-TYPE
              SYNTAX PerfIntervalCount
              MAX-ACCESS  read-only
              STATUS  current
              DESCRIPTION
                      "The counter associated with the number of AIS
                      seconds, encountered by a SONET
                      interface in one of the previous 96, individual 15
                      minute, intervals."
              ::= { dsx1XIntervalEntry 4 }

dsx1IntervalRAI OBJECT-TYPE
              SYNTAX PerfIntervalCount
              MAX-ACCESS  read-only
              STATUS  current
              DESCRIPTION
                      "Remote Alarm Indication: Transmitted  in the outgoing direction
	         (toward the PABX) over FDL bits when the DS1 device detected
                       an incoming Loss Of Frame. Received from the far end (PABX)
                       over FDL when it detects a Loss of frame."
              ::= { dsx1XIntervalEntry 5 }

dsx1IntervalLOMF OBJECT-TYPE
              SYNTAX PerfIntervalCount
              MAX-ACCESS  read-only
              STATUS  current
              DESCRIPTION
                      "Loss of Multi-Frame sequence  in E1 time slot 16."
              ::= { dsx1XIntervalEntry 6 }

dsx1IntervalFEBE OBJECT-TYPE
              SYNTAX PerfIntervalCount
              MAX-ACCESS  read-only
              STATUS  current
              DESCRIPTION
                       "Far End Block Errors, as reported in the first bit
                        of frames 13 and 15, on multiframe E1 lines with CRC4,
                        in one of the previous 96, individual, 15 minute intervals."
              ::= { dsx1XIntervalEntry 7 }

dsx1IntervalStatus OBJECT-TYPE
	SYNTAX OCTET STRING  (SIZE (4))
              MAX-ACCESS  read-only
              STATUS  current
              DESCRIPTION
                      "The statuses of the current interval:
                        0 - Valid.
                        1 - redundantLinkSwitch - the link has been switched
                            by a redundancy mechanism.
                        2 - discontinuity - module was partialy out.
                        4 - notValid - module is out."
              ::= { dsx1XIntervalEntry 8 }

dsx1IntervalBPV OBJECT-TYPE
              SYNTAX PerfIntervalCount
              MAX-ACCESS  read-only
              STATUS  current
              DESCRIPTION
              "The counter associated with the number of BPV (Bi-Polar Violations)
               encountered by a DS1	interface in one of the previous 96,
               individual 15 minute, intervals."
              ::= { dsx1XIntervalEntry 9 }

dsx1IntervalLOCRCMF OBJECT-TYPE
              SYNTAX PerfIntervalCount
              MAX-ACCESS  read-only
              STATUS  current
              DESCRIPTION
              "Loss of CRC4 Multi-Frame sequence in E1."
              ::= { dsx1XIntervalEntry 10 }

dsx1IntervalLOFC OBJECT-TYPE
              SYNTAX PerfIntervalCount
              MAX-ACCESS  read-only
              STATUS  current
              DESCRIPTION
              "Counts the number of loss of frame events measured
              in one of the previous 96, individual 15 minute, intervals."
              ::= { dsx1XIntervalEntry 11 }


--   Extension to the dsx1 Total table

dsx1XTotalTable  OBJECT-TYPE
       SYNTAX      SEQUENCE OF Dsx1XTotalEntry
       MAX-ACCESS  not-accessible
       STATUS      current
       DESCRIPTION
       "A list of Total statistics entries.  This table
        contains additional objects for the Total table."
       ::= { prtDs1PerfHistory 4 }

dsx1XTotalEntry OBJECT-TYPE
       SYNTAX  Dsx1XTotalEntry
       MAX-ACCESS  not-accessible
       STATUS      current
       DESCRIPTION
       "An entry containing additional statistical counters
        applicable to a particular current table."
 --     AUGMENTS    { dsx1CurrentEntry }
        INDEX   { dsx1TotalIndex }
       ::= { dsx1XTotalTable 1 }

Dsx1XTotalEntry     ::=
      SEQUENCE {
	  dsx1TotalBPV			PerfTotalCount,
	  dsx1TotalLOFC			PerfTotalCount
      }

dsx1TotalBPV OBJECT-TYPE
      SYNTAX PerfTotalCount
      MAX-ACCESS  read-only
      STATUS  current
      DESCRIPTION
      "The counter associated with the number of BPV (Bi-Polar Violations)
       encountered by a DS1	interface in the previous 24 hour interval.
       Invalid 15 minute intervals count as 0."
      ::= { dsx1XTotalEntry 9 }

dsx1TotalLOFC OBJECT-TYPE
      SYNTAX PerfTotalCount
      MAX-ACCESS  read-only
      STATUS  current
      DESCRIPTION
      "The counter associated with the number loss of frames
       encountered by a DS1	interface in the previous 24 hour interval.
       Invalid 15 minute intervals count as 0."
      ::= { dsx1XTotalEntry 11 }



--   Extension to the DS1 Configuration Table

dsx1XConfigTable  OBJECT-TYPE
       SYNTAX      SEQUENCE OF Dsx1XConfigEntry
       MAX-ACCESS  not-accessible
       STATUS      current
       DESCRIPTION
               " An extension to the DS1 Configuration table."
       ::= { ds1Interface 2 }

dsx1XConfigEntry OBJECT-TYPE
       SYNTAX  Dsx1XConfigEntry
       MAX-ACCESS  not-accessible
       STATUS      current
       DESCRIPTION
               "An entry containing additional configuration
               parameters."
 --      AUGMENTS    { dsx1ConfigTable }
         INDEX   { dsx1LineIndex }
       ::= { dsx1XConfigTable 1 }

Dsx1XConfigEntry      ::=
       SEQUENCE {
         dsx1IdleCode		    	Integer32,
         dsx1LineMode		    	INTEGER,
         dsx1dBTxGain     			INTEGER,
         dsx1RxSensitivity			INTEGER,
         dsx1RestoreTime			INTEGER,
         dsx1TcFirstSignal			Integer32,
         dsx1TcSignal   			Integer32,
         dsx1TcPattern     			Integer32,
         dsx1Scramble     			INTEGER,
         dsx1LineAdaptiveTimingMode INTEGER,
		 dsx1TxClockSource          INTEGER,
		 dsx1AisEnable				INTEGER,
		 dsx1TsEchoCancel		   	OCTET STRING,
		 dsx1EchoCancelerModule INTEGER
       }

dsx1IdleCode OBJECT-TYPE
              SYNTAX  Integer32
              MAX-ACCESS   read-write
              STATUS  current
              DESCRIPTION
	                  "Byte pattern of the data received/transmitted in the
	                   E1T1 framer idle timeslots.
	                   Valid range: (0 - FF HEX)."
              ::= { dsx1XConfigEntry 1 }

dsx1LineMode OBJECT-TYPE
              SYNTAX  INTEGER {
                             csu(1),
                             dsu(2)
              }
              MAX-ACCESS  read-write
              STATUS  current
              DESCRIPTION
                      "T1 device operation mode.
                       Valid for T1 only."
              ::= { dsx1XConfigEntry 2 }

dsx1dBTxGain OBJECT-TYPE
              SYNTAX  INTEGER {
                             notApplicable (1),
                             neg75dB       (2),
                             neg15dB       (3),
                             neg225dB      (4),
							 zerodB	       (5)
              }
              MAX-ACCESS  read-write
              STATUS  current
              DESCRIPTION
                      "Transmit line Gain for T1 CSU line mode."
              ::= { dsx1XConfigEntry 3 }

dsx1RxSensitivity OBJECT-TYPE
              SYNTAX  INTEGER {
							 notApplicable  (1),
                             neg10dB        (2),
                             neg32dB        (3)
              }
              MAX-ACCESS  read-write
              STATUS  current
              DESCRIPTION
                      "Determine the maximum attenuation of the
                       receive signal that can be compensated for
                       by the interface receive path. Not applicable for T1."
              ::= { dsx1XConfigEntry 4 }

dsx1RestoreTime OBJECT-TYPE
              SYNTAX  INTEGER {
                             other(1),
                             sec1(2),
                             sec10(3)
              }
              MAX-ACCESS  read-write
              STATUS  current
              DESCRIPTION
                      "Used to change the sync. algorithms to reduce the time
                       required for the port to return to normal operation after
                       a RED alarm."
              ::= { dsx1XConfigEntry 5 }

dsx1TcFirstSignal OBJECT-TYPE
              SYNTAX  Integer32
              MAX-ACCESS  read-write
              STATUS  current
              DESCRIPTION
                      "Trunk conditioning signal - value to be sent as a signal
                       during the first 2.5 seconds after alarm detection.
					   Range is 0x0..0xF. 0xFF is a NULL value. Valid for T1 only."
              ::= { dsx1XConfigEntry 6 }

dsx1TcSignal OBJECT-TYPE
              SYNTAX  Integer32
              MAX-ACCESS  read-write
              STATUS  current
              DESCRIPTION
                      "Trunk conditioning signal value after alarm detection.
                      Range is 0x1..0xF for E1, and 0x0..0xF for T1."
              ::= { dsx1XConfigEntry 7 }

dsx1TcPattern OBJECT-TYPE
              SYNTAX  Integer32
              MAX-ACCESS  read-write
              STATUS  current
              DESCRIPTION
                      "Trunk conditioning data pattern to be sent upon a DS0 fail.
					  Range is 0x0..0xFF."
              ::= { dsx1XConfigEntry 8 }

dsx1Scramble  OBJECT-TYPE
              SYNTAX  INTEGER {
                             notApplicable (1),
                             notActive     (2),
                             active        (3)
              }
              MAX-ACCESS  read-write
              STATUS  current
              DESCRIPTION
                      "Scrambling is an operation that randomizes the bits
                       of the payload of the ATM cell by a polynom.
                       This operation helps with the error detection mechanism
                       of the HEC. Not applicable for E1.
                       active - will scramble/descramble the payload ATM cell
                       notactive - will not scramble/descramble. "
              ::= { dsx1XConfigEntry 9 }

dsx1LineAdaptiveTimingMode               OBJECT-TYPE
              SYNTAX  INTEGER {
                             off(1),
                             on(2)
              }
              MAX-ACCESS  read-write
              STATUS  current
              DESCRIPTION
                      "Enables end to end clock synchronization.
                       Default value - off."
              ::= { dsx1XConfigEntry 10 }

dsx1TxClockSource OBJECT-TYPE
       SYNTAX  INTEGER {
       loopTiming(1),
       localTiming(2),
       throughTiming(3),
	   adaptive(4)
       }
       MAX-ACCESS  read-write
       STATUS  current
       DESCRIPTION
       "The source of Transmit Clock.
        'loopTiming' indicates that the recovered receive clock
         is used as the transmit clock.

        'localTiming' indicates that a local clock
         source is used or when an external clock is
         attached to the box containing the interface.

        'throughTiming' indicates that recovered receive clock
         from another interface is used as the transmit clock.

        'adaptive' indicates that the clock is recovered according
         to the received data flow rate. "
       ::= { dsx1XConfigEntry 11 }

dsx1AisEnable  OBJECT-TYPE
       SYNTAX  INTEGER {
       notApplicable(1),
       disable(2),
       enable(3)
       }
       MAX-ACCESS  read-write
       STATUS  current
       DESCRIPTION
       "Enable/ disable AIS transmit when Ethernet cable (for TDMoIP) is out
       (disconnected)."
       ::= { dsx1XConfigEntry 12 }

dsx1TsEchoCancel OBJECT-TYPE
       SYNTAX OCTET STRING  (SIZE (4))
       MAX-ACCESS  read-write
       STATUS  current
       DESCRIPTION
       "This parameter defines for each TS whether Echo-Cancellation is on.
	  	Each bit represents one TS as follows:
		First octet bit'0'=not in use bit'1'= TS#1, bit'7' = TS#7, .. 2nd octet bit'0' = TS#8,..,
		4th octet bit'7' = TS#31.
		Octets and bits order is from left to right:
		[31,30,..24]      [23..16]    [15..8]      [7..0]
		MSB       LSB 	 MSB	LSB	 MSB   LSB	  MSB	LSB

	  	For each bit values are:
         0 - Echo-Cancellation off.
         1 - Echo-Cancellation on."
       ::= { dsx1XConfigEntry 13 }

dsx1EchoCancelerModule OBJECT-TYPE
       SYNTAX  INTEGER {
       notExist(2),
       exist(3)
       }
       MAX-ACCESS  read-only
       STATUS  current
       DESCRIPTION
       "This parameter indicates whether echo-cancellation module
        exists for this line."
       ::= { dsx1XConfigEntry 14 }





-- END
--
-- file :v:\doc\rdv\mib\Before~1\radds3.txt
--
-- RAD-DS3-MIB DEFINITIONS ::= BEGIN

--Title:    RAD-DS3   MIB
--
-- Copyright 1993 RAD Data Communications, Ltd.
-- All Rights Reserved.

-- It is RAD's intent to encourage the widespread use of
-- this Specification in connection with the management of
-- RAD products. RAD grants vendors, end-users,
-- and other interested parties a non-exclusive license to
-- use this Specification in connection with the management
-- of RAD products.
-- This Specification is supplied "as is," and RAD makes
-- no warranty, either express or implied, as to the use,
-- operation, condition, or performance of the Specification.

-- IMPORTS
--      Gauge32                           FROM SNMPv2-SMI
--      ifIndex                         FROM SNMPv2-TC
--      OBJECT-TYPE                     FROM SNMPv2-SMI
 --     radWan                          FROM RAD-GEN-MIB;



--                RAD-DS3 MIB

--Title:     RAD's DS3 INTERFACE MIB
--Version:   1.0
--Date:      13.10.96
--By:        Yair Arian
--File:      ds3.mib
--
--Last update: 27.01.98 by Ilana



ds3Interface  OBJECT IDENTIFIER  ::=  {diverseIfWanGen 3}

prtDs3PerfHistory  OBJECT IDENTIFIER  ::=  {ds3Interface 1}


          -- The DS3 Interface Table

          prtSDs3IfTable OBJECT-TYPE
              SYNTAX  SEQUENCE OF PrtDs3IfEntry
              MAX-ACCESS  not-accessible
              STATUS  current
              DESCRIPTION
                      "The DS3 interface table."
              ::= { prtDs3PerfHistory 1 }

          prtDs3IfEntry OBJECT-TYPE
              SYNTAX  PrtDs3IfEntry
              MAX-ACCESS  not-accessible
              STATUS  current
              DESCRIPTION
                      "An entry in the DS3 interface table."
              INDEX   { ifIndex }
              ::= { prtSDs3IfTable 1 }

          PrtDs3IfEntry ::=
              SEQUENCE {
                  prtDs3IfTimeElapsed
                      Integer32,
                  prtDs3IfValidIntervals
                      Integer32
                     }

           prtDs3IfTimeElapsed OBJECT-TYPE
               SYNTAX  Integer32 (0..899)
               MAX-ACCESS  read-only
               STATUS  current
               DESCRIPTION
                       "The number of seconds that have elapsed since
                       the beginning of the near end current error-
                       measurement period."
              ::= { prtDs3IfEntry 1 }

          prtDs3IfValidIntervals OBJECT-TYPE
              SYNTAX  Integer32 (0..96)
              MAX-ACCESS  read-only
              STATUS  current
              DESCRIPTION
                      "The number of previous near end intervals for
                      which valid data was collected.  The value will be
                      96 unless the interface was brought online within
                      the last 24 hours, in which case the value will be
                      the number of complete 15 minute near end
                      intervals since the interface has been online."
              ::= { prtDs3IfEntry 2 }


          -- The DS3 Current Table

          -- The DS3 Current table contains various statistics being
          -- collected for the current 15 minute interval.

          prtDs3CurrentTable OBJECT-TYPE
              SYNTAX  SEQUENCE OF PrtDs3CurrentEntry
              MAX-ACCESS  not-accessible
              STATUS  current
              DESCRIPTION
                      "The DS3 Current table."
              ::= { prtDs3PerfHistory 2 }

          prtDs3CurrentEntry OBJECT-TYPE
              SYNTAX  PrtDs3CurrentEntry
              MAX-ACCESS  not-accessible
              STATUS  current
              DESCRIPTION
                      "An entry in the DS3 Current table."
              INDEX   { ifIndex }
              ::= { prtDs3CurrentTable 1 }

          PrtDs3CurrentEntry ::=
              SEQUENCE {
                  prtDs3CurrentLOS
                      Gauge32,
                  prtDs3CurrentOOF
                      Gauge32,
                  prtDs3CurrentLOC
                      Gauge32,
                  prtDs3CurrentAIS
                      Gauge32,
                  prtDs3CurrentRDI
                      Gauge32,
                  prtDs3CurrentUAS
                      Gauge32,
	              prtDs3CurrentBIP
                      Gauge32,
                  prtDs3CurrentFEBE
	                  Gauge32,
	              prtDs3CurrentSLM
	                  Gauge32,
                  prtDs3CurrentSES
                      Gauge32,
                  prtDs3CurrentES
                      Gauge32,
                  prtDs3CurrentBitParity
                      Gauge32,
                  prtDs3CurrentPlcpLOF
                      Gauge32,
                  prtDs3CurrentPlcpRAI
                       Gauge32,
	              prtDs3CurrentPlcpBIP
                       Gauge32,
                  prtDs3CurrentPlcpFEBE
	                   Gauge32,
				 prtDs3CurrentBPV
				       Gauge32,
				 prtDs3CurrentLCE
				       Gauge32,
				  prtDs3CurrentStatus
				       OCTET STRING
}

          prtDs3CurrentLOS OBJECT-TYPE
              SYNTAX  Gauge32
              MAX-ACCESS  read-only
              STATUS  current
              DESCRIPTION
                      "The counter associated with the number of LOS
                       seconds, encountered by a DS3 interface in
                      the current 15 minute interval."
              ::= { prtDs3CurrentEntry 1 }

          prtDs3CurrentOOF OBJECT-TYPE
              SYNTAX  Gauge32
              MAX-ACCESS  read-only
              STATUS  current
              DESCRIPTION
                      "The counter associated with the number of OOF
                       seconds, encountered by a DS3
                       interface in the current 15 minute interval."
              ::= { prtDs3CurrentEntry 2 }

          prtDs3CurrentLOC OBJECT-TYPE
              SYNTAX  Gauge32
              MAX-ACCESS  read-only
              STATUS  current
              DESCRIPTION
                      "The counter associated with the number of LOC
                      seconds, encountered by a DS3
                      interface in the current 15 minute interval."
              ::= { prtDs3CurrentEntry 3 }

          prtDs3CurrentAIS OBJECT-TYPE
              SYNTAX  Gauge32
              MAX-ACCESS  read-only
              STATUS  current
              DESCRIPTION
                      "The counter associated with the number of AIS
                      seconds, encountered by a DS3
                      interface in the current 15 minute interval."
              ::= { prtDs3CurrentEntry 4 }

          prtDs3CurrentRDI OBJECT-TYPE
              SYNTAX  Gauge32
              MAX-ACCESS  read-only
              STATUS  current
              DESCRIPTION
                      "The counter associated with the number of RDI
                      seconds, encountered by a DS3
                      interface."
              ::= { prtDs3CurrentEntry 5 }

          prtDs3CurrentUAS OBJECT-TYPE
              SYNTAX  Gauge32
              MAX-ACCESS  read-only
              STATUS  current
              DESCRIPTION
                      "The counter associated with the number of UAS,
                      encountered by a SONET interface."
              ::= { prtDs3CurrentEntry 6 }

        prtDs3CurrentBIP OBJECT-TYPE
              SYNTAX  Gauge32
              MAX-ACCESS  read-only
              STATUS  current
              DESCRIPTION
                      "The counter associated with the number of
                      BIP errors, encountered by a DS3
                      interface in the current 15 minute interval."
              ::= { prtDs3CurrentEntry 7 }

          prtDs3CurrentFEBE OBJECT-TYPE
              SYNTAX  Gauge32
              MAX-ACCESS  read-only
              STATUS  current
              DESCRIPTION
                      "The counter associated with the number of
                      FEBE errors, encountered by a DS3
                      interface in the current 15 minute interval."
              ::= { prtDs3CurrentEntry 8 }

          prtDs3CurrentSLM OBJECT-TYPE
              SYNTAX  Gauge32
              MAX-ACCESS  read-only
              STATUS  current
              DESCRIPTION
                      "The counter associated with the number of SLM
                       seconds, encountered by an E3 (only )
                       interface in the current 15 minute interval."
              ::= { prtDs3CurrentEntry 9 }

        prtDs3CurrentSES OBJECT-TYPE
              SYNTAX  Gauge32
              MAX-ACCESS  read-only
              STATUS  current
              DESCRIPTION
                      "The counter associated with the number of SES
                       encountered by a E3
                       interface in the current 15 minute interval."
	     ::= { prtDs3CurrentEntry 10 }

	  prtDs3CurrentES OBJECT-TYPE
	SYNTAX Gauge32
              MAX-ACCESS  read-only
              STATUS  current
              DESCRIPTION
                      " The number of Errored Seconds, encountered  by a
                      DS3 interface in the current 15 minute interval."
	::= { prtDs3CurrentEntry 11 }

     prtDs3CurrentBitParity OBJECT-TYPE
              SYNTAX  Gauge32
              MAX-ACCESS  read-only
              STATUS  current
              DESCRIPTION
                      "Bit Parity Error counter. Relevant to T3 only."
              ::= { prtDs3CurrentEntry 12 }

        prtDs3CurrentPlcpLOF OBJECT-TYPE
              SYNTAX  Gauge32
              MAX-ACCESS  read-only
              STATUS  current
              DESCRIPTION
                      "The counter associated with the number of LOF
                      seconds, encountered by a DS3
                      interface in one of the previous 96, individual 15
                      minute, intervals. This counter is relevant for plcpInternal(5)
                       or plcpExternal(6) configuration If frame types only."
              ::= { prtDs3CurrentEntry 13 }

prtDs3CurrentPlcpRAI OBJECT-TYPE
              SYNTAX  Gauge32
              MAX-ACCESS  read-only
              STATUS  current
              DESCRIPTION
                    "Receiving Yellow/Remote Alarm Indication. This counter is
                      relevant for PLCP (external/internal) frame types only."
              ::= { prtDs3CurrentEntry 14 }

      prtDs3CurrentPlcpBIP OBJECT-TYPE
              SYNTAX  Gauge32
              MAX-ACCESS  read-only
              STATUS  current
              DESCRIPTION
                    " The counter associated with the number of BIP errors,
                      encountered by a DS3 interface in the current 15 minute
                      interval. This counter is relevant for PLCP (external/internal)
                      frame types only."
              ::= { prtDs3CurrentEntry 15 }

      prtDs3CurrentPlcpFEBE OBJECT-TYPE
              SYNTAX  Gauge32
              MAX-ACCESS  read-only
              STATUS  current
              DESCRIPTION
                    " The counter associated with the number of FEBE
                      errors, encountered by a DS3 interface in the current
                      15 minute interval. This counter is relevant for PLCP
                      (external/internal) frame types only."
              ::= { prtDs3CurrentEntry 16 }

      prtDs3CurrentBPV OBJECT-TYPE
              SYNTAX  Gauge32
              MAX-ACCESS  read-only
              STATUS  current
              DESCRIPTION
                    " Number of BPVs (Bi-Polar Violations) , encountered by a
                      DS3 interface in the current 15 minute interval.
                      This object is relevant only for Electrical Line
                      of Fomi-E3/T3."
              ::= { prtDs3CurrentEntry 17 }

      prtDs3CurrentLCE OBJECT-TYPE
              SYNTAX  Gauge32
              MAX-ACCESS  read-only
              STATUS  current
              DESCRIPTION
                    " Number of LCE (Link Code Errors)  encountered
                      by a DS3 interface in the current 15 minute interval.
                      This object is relevant only for Optical Links
                      of Fomi-E3/T3."
              ::= { prtDs3CurrentEntry 18 }

     prtDs3CurrentStatus OBJECT-TYPE
	          SYNTAX OCTET STRING  (SIZE (4))
              MAX-ACCESS  read-only
              STATUS  current
              DESCRIPTION
                      "The statuses of the current interval:
                        0 - Valid.
                        1 - redundantLinkSwitch - the link has been switched
                            by a redundancy mechanism.
                        2 - discontinuity - module was partialy out.
                        4 - notValid - module is out."
              ::= { prtDs3CurrentEntry 19 }

         -- The DS3 interface Interval

          -- The DS3 Interval Table contains various statistics
          -- collected by the Interface over the previous 24
          -- hours of operation.  The past 24 hours are broken into 96
          -- completed 15 minute intervals.

          prtDs3IntervalTable OBJECT-TYPE
              SYNTAX  SEQUENCE OF PrtDs3IntervalEntry
              MAX-ACCESS  not-accessible
              STATUS  current
              DESCRIPTION
                      "The DS3 Interval table."
              ::= { prtDs3PerfHistory 3 }

          prtDs3IntervalEntry OBJECT-TYPE
              SYNTAX  PrtDs3IntervalEntry
              MAX-ACCESS  not-accessible
              STATUS  current
              DESCRIPTION
                      "An entry in the DS3 Interval table."
              INDEX   { ifIndex, prtDs3IntervalNumber }
              ::= { prtDs3IntervalTable 1 }

          PrtDs3IntervalEntry ::=
              SEQUENCE {
                  prtDs3IntervalNumber
                      Integer32,
                  prtDs3IntervalLOS
                      Gauge32,
                  prtDs3IntervalOOF
                      Gauge32,
                  prtDs3IntervalLOC
                      Gauge32,
                  prtDs3IntervalAIS
                      Gauge32,
                  prtDs3IntervalRDI
                      Gauge32,
                  prtDs3IntervalUAS
                      Gauge32,
	              prtDs3IntervalBIP
                      Gauge32,
                  prtDs3IntervalFEBE
                      Gauge32,
	              prtDs3IntervalSLM
                      Gauge32,
                  prtDs3IntervalSES
                      Gauge32,
	              prtDs3IntervalES
                      Gauge32,
                  prtDs3IntervalBitParity
                      Gauge32,
                  prtDs3IntervalPlcpLOF
                      Gauge32,
                  prtDs3IntervalPlcpRAI
                      Gauge32,
	              prtDs3IntervalPlcpBIP
                      Gauge32,
                  prtDs3IntervalPlcpFEBE
	                  Gauge32,
				  prtDs3IntervalBPV
				       Gauge32,
				  prtDs3IntervalLCE
				       Gauge32,
				  prtDs3IntervalStatus
	                  OCTET STRING
}

          prtDs3IntervalNumber OBJECT-TYPE
              SYNTAX  Integer32 (1..96)
              MAX-ACCESS  read-only
              STATUS  current
              DESCRIPTION
                      "A number between 1 and 96, where 1 is the most
                      recently completed 15 minute interval and 96 is
                      the least recently completed 15 minutes interval
                      (assuming that all 96 intervals are valid)."
              ::= { prtDs3IntervalEntry 1 }

          prtDs3IntervalLOS OBJECT-TYPE
              SYNTAX  Gauge32
              MAX-ACCESS  read-only
              STATUS  current
              DESCRIPTION
                      "The counter associated with the number of LOS
                      seconds , encountered by a DS3 interface in
                      one of the previous 96, individual 15 minute,
                      intervals."
              ::= { prtDs3IntervalEntry 2 }

          prtDs3IntervalOOF OBJECT-TYPE
              SYNTAX  Gauge32
              MAX-ACCESS  read-only
              STATUS  current
              DESCRIPTION
                      "The counter associated with the number of OOF
                      seconds, encountered by a DS3
                      interface in one of the previous 96, individual 15
                      minute, intervals."
              ::= { prtDs3IntervalEntry 3 }

          prtDs3IntervalLOC OBJECT-TYPE
              SYNTAX  Gauge32
              MAX-ACCESS  read-only
              STATUS  current
              DESCRIPTION
                      "The counter associated with the number of LOC
                      seconds, encountered by a DS3
                      interface in one of the previous 96,
                      individual 15 minute, intervals."
              ::= { prtDs3IntervalEntry 4 }

          prtDs3IntervalAIS OBJECT-TYPE
              SYNTAX  Gauge32
              MAX-ACCESS  read-only
              STATUS  current
              DESCRIPTION
                      "The counter associated with the number of AIS
                      seconds, encountered by a SONET
                      interface in one of the previous 96, individual 15
                      minute, intervals."
              ::= { prtDs3IntervalEntry 5 }

          prtDs3IntervalRDI OBJECT-TYPE
              SYNTAX  Gauge32
              MAX-ACCESS  read-only
              STATUS  current
              DESCRIPTION
                      "The counter associated with the number of RDI
                      seconds, encountered by a DS3
                      interface in one of the previous 96, individual 15
                      minute, intervals."
              ::= { prtDs3IntervalEntry 6 }

          prtDs3IntervalUAS OBJECT-TYPE
              SYNTAX  Gauge32
              MAX-ACCESS  read-only
              STATUS  current
              DESCRIPTION
                      "The counter associated with the number of UAS,
                      encountered by a DS3
                      interface in one of the previous 96, individual 15
                      minute, intervals."
              ::= { prtDs3IntervalEntry 7 }

          prtDs3IntervalBIP OBJECT-TYPE
              SYNTAX  Gauge32
              MAX-ACCESS  read-only
              STATUS  current
              DESCRIPTION
                      "The counter associated with the number of
                      BIP errors, encountered by a DS3
                      interface in one of the previous 96, individual 15
                      minute, intervals."
              ::= { prtDs3IntervalEntry 8 }

          prtDs3IntervalFEBE OBJECT-TYPE
              SYNTAX  Gauge32
              MAX-ACCESS  read-only
              STATUS  current
              DESCRIPTION
                      "The counter associated with the number of
                      FEBE errors, encountered by a DS3
                      interface in one of the previous 96, individual 15
                      minute, intervals."
              ::= { prtDs3IntervalEntry 9 }

          prtDs3IntervalSLM OBJECT-TYPE
              SYNTAX  Gauge32
              MAX-ACCESS  read-only
              STATUS  current
              DESCRIPTION
                      "The counter associated with the number of SLM
                      seconds, encountered by an E3
                      interface in one of the previous 96, individual 15
                      minute, intervals."
              ::= { prtDs3IntervalEntry 10 }

	 prtDs3IntervalSES OBJECT-TYPE
              SYNTAX  Gauge32
              MAX-ACCESS  read-only
              STATUS  current
              DESCRIPTION
                      "The counter associated with the number of SES
                      encountered by a E3
                      interface in one of the previous 96, individual 15
                      minute, intervals."
	      ::= { prtDs3IntervalEntry 11 }

	 prtDs3IntervalES OBJECT-TYPE
	SYNTAX Gauge32
              MAX-ACCESS  read-only
              STATUS  current
              DESCRIPTION
                      " The number of Errored Seconds, encountered  by a
                      DS3 interface in one of the previous 96, individual 15
                      minute, intervals."
	::= { prtDs3IntervalEntry 12 }

prtDs3IntervalBitParity OBJECT-TYPE
              SYNTAX  Gauge32
              MAX-ACCESS  read-only
              STATUS  current
              DESCRIPTION
                      "Bit Parity Error counter. Relevant to T3 only."
              ::= { prtDs3IntervalEntry 13 }

        prtDs3IntervalPlcpLOF OBJECT-TYPE
              SYNTAX  Gauge32
              MAX-ACCESS  read-only
              STATUS  current
              DESCRIPTION
                      "The counter associated with the number of LOF
                      seconds, encountered by a DS3
                      interface in one of the previous 96, individual 15
                      minute, intervals. This counter is relevant for plcpInternal(5)
                       or plcpExternal(6) configuration If frame types only."
              ::= { prtDs3IntervalEntry 14 }

prtDs3IntervalPlcpRAI OBJECT-TYPE
              SYNTAX  Gauge32
              MAX-ACCESS  read-only
              STATUS  current
              DESCRIPTION
                    "Receiving Yellow/Remote Alarm Indication. This counter is
                      relevant for PLCP (external/internal) frame types only."
              ::= { prtDs3IntervalEntry 15 }

      prtDs3IntervalPlcpBIP OBJECT-TYPE
              SYNTAX  Gauge32
              MAX-ACCESS  read-only
              STATUS  current
              DESCRIPTION
                    " The counter associated with the number of BIP errors,
                      encountered by a DS3 interface in the current 15 minute
                      interval. This counter is relevant for PLCP (external/internal)
                      frame types only."
              ::= { prtDs3IntervalEntry 16 }

      prtDs3IntervalPlcpFEBE OBJECT-TYPE
              SYNTAX  Gauge32
              MAX-ACCESS  read-only
              STATUS  current
              DESCRIPTION
                    " The counter associated with the number of FEBE
                      errors, encountered by a DS3 interface in the current
                      15 minute interval. This counter is relevant for PLCP
                      (external/internal) frame types only."
              ::= { prtDs3IntervalEntry 17 }

      prtDs3IntervalBPV OBJECT-TYPE
              SYNTAX  Gauge32
              MAX-ACCESS  read-only
              STATUS  current
              DESCRIPTION
                    " Number of BPVs (Bi-Polar Violations) , encountered by a
                      DS3 interface in the specified 15 minute interval.
                      This object is relevant only for Electrical Line
                      of Fomi-E3/T3."
              ::= { prtDs3IntervalEntry 18 }

      prtDs3IntervalLCE OBJECT-TYPE
              SYNTAX  Gauge32
              MAX-ACCESS  read-only
              STATUS  current
              DESCRIPTION
                    " Number of LCE (Link Code Errors) encountered
                      by a DS3 interface in the specified 15 minute interval.
                      This object is relevant only for Optical Links
                      of Fomi-E3/T3."
              ::= { prtDs3IntervalEntry 19 }


     prtDs3IntervalStatus OBJECT-TYPE
	          SYNTAX OCTET STRING  (SIZE (4))
              MAX-ACCESS  read-only
              STATUS  current
              DESCRIPTION
                      "The statuses of the current interval:
                        0 - Valid.
                        1 - redundantLinkSwitch - the link has been switched
                            by a redundancy mechanism.
                        2 - discontinuity - module was partialy out.
                        4 - notValid - module is out."
              ::= { prtDs3IntervalEntry 20 }

-- the DS3 Total table

prtDs3TotalTable OBJECT-TYPE
              SYNTAX  SEQUENCE OF PrtDs3TotalEntry
              MAX-ACCESS  not-accessible
              STATUS  current
              DESCRIPTION
              " A list of Total entries."
              ::= { prtDs3PerfHistory 4 }

prtDs3TotalEntry OBJECT-TYPE
              SYNTAX  PrtDs3TotalEntry
              MAX-ACCESS  not-accessible
              STATUS  current
              DESCRIPTION
              "An entry of Total table."
              INDEX   { ifIndex }
              ::= { prtDs3TotalTable 1 }

PrtDs3TotalEntry     ::=
          SEQUENCE {
       	    prtDs3TotalUAS	Gauge32,
        	prtDs3TotalBPV	Gauge32,
            prtDs3TotalLCE  Gauge32
            }

prtDs3TotalUAS OBJECT-TYPE
              SYNTAX  Gauge32
              MAX-ACCESS  read-only
              STATUS  current
              DESCRIPTION
              "Number of UASs (Unavailable Seconds) , encountered by a
               DS3 interface in the previous 96 intervals.
               Invalid 15 minute intervals count as 0."
              ::= { prtDs3TotalEntry 6 }

prtDs3TotalBPV OBJECT-TYPE
              SYNTAX  Gauge32
              MAX-ACCESS  read-only
              STATUS  current
              DESCRIPTION
              "Number of BPVs (Bi-Polar Violations) , encountered by a
               DS3 interface in the previous 96 intervals.
               Invalid 15 minute intervals count as 0."
              ::= { prtDs3TotalEntry 17 }

prtDs3TotalLCE OBJECT-TYPE
              SYNTAX  Gauge32
              MAX-ACCESS  read-only
              STATUS  current
              DESCRIPTION
              "Number of LCE (Link Code Errors) encountered
               by a DS3 interface in the previous 96 intervals.
               Invalid 15 minute intervals count as 0."
              ::= { prtDs3TotalEntry 18 }
-- END
--
-- file :v:\doc\rdv\mib\Before~1\brggen.txt
--


--Version:   4.0
--Date:   16.10.94
--By:       Debby Koren &  Orly Nicklass
--File:       BRGgen.txt
--Updated to version 4.0: Riky and Smadar, 29.08.95.

genBridge      OBJECT IDENTIFIER ::= {radBridges 1 }

-- At the end of the MIB there is a definition of all RAD general traps for bridges.

radBridgeAction OBJECT-TYPE
    SYNTAX  INTEGER {
       reset(1),
       sendNetworkTab(2),
       deleteNetworkTab(3),
       sendRoutingTab(4),    -- Level II
       deleteRoutinTab(5),
       sendLanTab(6),
       deleteLanTab(7),
       deleteArpTab(8),
       sendArpTab(9),
       deleteRouteTab(10),   -- Level III
       sendRouteTab(11),
       deactivateAllMasks(12),
       saveAllActiveMasks(13),
       loadAndActivateAllMasksFromNVRAM(14),
       clearAllMasksFromNVRAM(15),
	   defaultConfig(16),
	   resetNVRAM(17),
	   clearIPNVRAM(18),
	noOp(255)
     }
    MAX-ACCESS  read-write
    STATUS  current
    DESCRIPTION
	"This variable enables the operator to perform one of the
	specified actions on the tables maintained by the network device.
	Send actions are not currently implemented.  Not all actions can
	be performed on all bridges."
   ::= { genBridge 1  }

radBridgeInactiveArpTimeOut OBJECT-TYPE
    SYNTAX Integer32
    MAX-ACCESS  read-write
    STATUS  current
    DESCRIPTION
	"This variable defines the maximum time period that can pass
	between ARP requests concerning an entry in the ARP table.
	After this time period, the entry is deleted from the table."
    ::= { genBridge 2  }


-- radBridgeMaskTab defines the format of  RAD Bridge OLD masking tables

radBridgeMaskTable    OBJECT-TYPE
    SYNTAX  SEQUENCE  OF RadBridgeMaskEntry
    MAX-ACCESS  not-accessible
    STATUS  current
    DESCRIPTION
	"Mask tables enable definition of forwarding restrictions and
	control of message flow in the internetwork. Each entry
	in this table defines a mask statement consisting of up to
	three mask definitions and an action defined by
	radBridgeMaskOper. Different types of mask entries are supported,
	as defined by radBridgeMaskType."
    ::=  { genBridge 3 }

radBridgeMaskEntry OBJECT-TYPE
    SYNTAX  RadBridgeMaskEntry
    MAX-ACCESS  not-accessible
    STATUS  current
    DESCRIPTION
    "An entry in table radBridgeMaskTable."
    INDEX   { radBridgeMaskType, radBridgeMaskIfIndex, radBridgeMaskNum  }
    ::=  { radBridgeMaskTable 1  }

RadBridgeMaskEntry ::= SEQUENCE {
    radBridgeMaskType
     INTEGER,
    radBridgeMaskIfIndex
     Integer32,
    radBridgeMaskNum
     Integer32,
    radBridgeMaskDest
     INTEGER,
    radBridgeMaskPat1
     OCTET STRING,
    radBridgeMaskActiveBit1
     OCTET STRING,
    radBridgeMaskFrom1
     INTEGER,
    radBridgeMaskOffset1
     Integer32,
    radBridgeMaskCond1
     INTEGER,
    radBridgeMaskPat2
     OCTET STRING,
    radBridgeMaskActiveBit2
     OCTET STRING,
    radBridgeMaskFrom2
     INTEGER,
    radBridgeMaskOffset2
     Integer32,
    radBridgeMaskCond2
     INTEGER,
    radBridgeMaskPat3
     OCTET STRING,
    radBridgeMaskActiveBit3
     OCTET STRING,
    radBridgeMaskFrom3
     INTEGER,
    radBridgeMaskOffset3
     Integer32,
    radBridgeMaskCond3
     INTEGER,
    radBridgeMaskOper
     INTEGER
    }

radBridgeMaskType  OBJECT-TYPE
    SYNTAX INTEGER {
       tx(1),
       rx(2),
       compress(3),
       priority(4),
       loadSharing(5),
       facs(6),
       codConnect(7),
	   codDisconnect(8)
      }
    MAX-ACCESS  read-write
    STATUS  current
    DESCRIPTION
	"Defines the type of mask entry."
    ::= { radBridgeMaskEntry 1  }

radBridgeMaskIfIndex  OBJECT-TYPE
    SYNTAX Integer32
    MAX-ACCESS  read-write
    STATUS  current
    DESCRIPTION
	"Specifies the if Index of the interface to which the mask is applied."
   ::= { radBridgeMaskEntry 2  }

radBridgeMaskNum  OBJECT-TYPE
    SYNTAX Integer32
    MAX-ACCESS  read-write
    STATUS  current
    DESCRIPTION
	"The Mask entry number, defined by its line number in the mask
	table."
   ::= {  radBridgeMaskEntry 3  }

radBridgeMaskDest  OBJECT-TYPE
    SYNTAX INTEGER {
       unassigned-cond (1),
       broadcast-msge (2),
       multicast-msge (3),
       all-msge(4),
   none(5)
    }

    MAX-ACCESS  read-write
    STATUS  current
    DESCRIPTION
	"Specifies the type of destination address carried by the frame
	to which the mask will be applied. Unassigned-condition
	deactivates the mask entry."
    ::= {  radBridgeMaskEntry 4   }


radBridgeMaskPat1 OBJECT-TYPE
    SYNTAX OCTET STRING  -- (SIZE (2))
    MAX-ACCESS  read-write
    STATUS  current
    DESCRIPTION
	"Describes the mask field which is either a 16 bit binary pattern,
	or four digit hexadecimal pattern."
    ::= { radBridgeMaskEntry 5  }

radBridgeMaskActiveBit1  OBJECT-TYPE
    SYNTAX OCTET STRING  -- (SIZE (2))
    MAX-ACCESS  read-write
    STATUS  current
    DESCRIPTION
	"Specifies the positions of the wild card characters (*)
	in the radBridgeMaskPat1 field."
    ::= { radBridgeMaskEntry 6  }

radBridgeMaskFrom1  OBJECT-TYPE
    SYNTAX INTEGER {
       mac(1),
       llc(2),
	   net(3)
    }
    MAX-ACCESS  read-write
    STATUS  current
    DESCRIPTION
	"Offset base of radBridgeMaskPat1 within the frame.
	 Net can be in some cases the data start point."
    ::= { radBridgeMaskEntry 7  }

radBridgeMaskOffset1  OBJECT-TYPE
    SYNTAX Integer32
    MAX-ACCESS  read-write
    STATUS  current
    DESCRIPTION
	"Specifies the radBridgeMaskPat1 offset within the frame (in bytes) from
	the base defined in by radBridgeMaskForm1.The mask offset is an even
	decimal number in the range of 0 to 1518."
    ::= { radBridgeMaskEntry 8  }

radBridgeMaskCond1 OBJECT-TYPE
    SYNTAX INTEGER {
       false (1),
       true (2)
    }
    MAX-ACCESS  read-write
    STATUS  current
    DESCRIPTION
	"Specifies the logical condition of the mask pattern:

	true  - Condition is valid if at the position specified by
		radBridgeMaskOffset1 the packet contains data that matches
		the content of radBridgeMaskPat1.

	false - Condition is valid if at the position specified by
		radBridgeMaskOffset1 the packet contains data that does not
		match the content of radBridgeMaskPat1."
    ::= {  radBridgeMaskEntry 9  }

radBridgeMaskPat2  OBJECT-TYPE
    SYNTAX OCTET STRING  --   (SIZE (2))
    MAX-ACCESS  read-write
    STATUS  current
    DESCRIPTION
	"Describes the mask field which is either a 16 bit binary pattern,
	 or four digit hexadecimal pattern."
    ::= {  radBridgeMaskEntry 10  }

radBridgeMaskActiveBit2  OBJECT-TYPE
    SYNTAX OCTET STRING  --   (SIZE (2))
    MAX-ACCESS  read-write
    STATUS  current
    DESCRIPTION
	"Specifies the positions of the wild card characters (*)
	in the radBridgeMaskPat2 field."
    ::= {  radBridgeMaskEntry 11  }

radBridgeMaskFrom2  OBJECT-TYPE
    SYNTAX INTEGER {
       mac (1),
       llc (2),
	   net(3)
    }
    MAX-ACCESS  read-write
    STATUS  current
    DESCRIPTION
	"Offset base of radBridgeMaskPat2 within the frame.
	 Net can be in some cases the data start point."
    ::= {  radBridgeMaskEntry 12  }

radBridgeMaskOffset2  OBJECT-TYPE
    SYNTAX Integer32
    MAX-ACCESS  read-write
    STATUS  current
    DESCRIPTION
	"Specifies the radBridgeMaskPat2 offset within the frame (in bytes) from
	the base defined in by radBridgeMaskForm2.The mask offset is an even
	decimal number in the range of 0 to 1518."
    ::= {  radBridgeMaskEntry 13  }

radBridgeMaskCond2 OBJECT-TYPE
    SYNTAX INTEGER {
       false (1),
       true (2)
    }
    MAX-ACCESS  read-write
    STATUS  current
    DESCRIPTION
	"Specifies the logical condition of the mask pattern:

	true  - Condition is valid if at the position specified by
		radBridgeMaskOffset2 the packet contains data that matches
		the content of radBridgeMaskPat2.

	false - Condition is valid if at the position specified by
		radBridgeMaskOffset2 the packet contains data that does not
		match the content of radBridgeMaskPat2."
    ::= {  radBridgeMaskEntry 14  }

radBridgeMaskPat3 OBJECT-TYPE
    SYNTAX OCTET STRING  --   (SIZE (2))
    MAX-ACCESS  read-write
    STATUS  current
    DESCRIPTION
	"Describes the mask field which is either a 16 bit binary pattern,
	or four digit hexadecimal pattern."
    ::= {  radBridgeMaskEntry 15  }

radBridgeMaskActiveBit3 OBJECT-TYPE
    SYNTAX OCTET STRING  --   (SIZE (2))
    MAX-ACCESS  read-write
    STATUS  current
    DESCRIPTION
	"Specifies the positions of the wild card characters (*)
	in the radBridgeMaskPat3 field."
    ::= {  radBridgeMaskEntry 16  }

radBridgeMaskFrom3 OBJECT-TYPE
    SYNTAX INTEGER {
       mac (1),
       llc (2),
	   net (3)
    }
    MAX-ACCESS  read-write
    STATUS  current
    DESCRIPTION
	"Offset base of radBridgeMaskPat3 within the frame.
	 Net can be in some cases the data start point."
    ::= {  radBridgeMaskEntry 17  }

radBridgeMaskOffset3 OBJECT-TYPE
    SYNTAX Integer32
    MAX-ACCESS  read-write
    STATUS  current
    DESCRIPTION
	"Specifies the radBridgeMaskPat3 offset within the frame (in bytes) from
	the base defined in by radBridgeMaskForm3. The mask offset is an even
	decimal number in the range of 0 to 1518."
    ::= {  radBridgeMaskEntry 18  }

radBridgeMaskCond3 OBJECT-TYPE
   SYNTAX INTEGER {
       false (1),
       true (2)
    }
    MAX-ACCESS  read-write
    STATUS  current
    DESCRIPTION
	"Specifies the logical condition of the mask pattern:

	true  - Condition is valid if at the position specified by
		radBridgeMaskOffset3 the packet contains data that matches
		the content of radBridgeMaskPat3

	false - Condition is valid if at the position specified by
		radBridgeMaskOffset3 the packet contains data that does not
		match the content of radBridgeMaskPat3."
    ::= {  radBridgeMaskEntry 19  }

radBridgeMaskOper OBJECT-TYPE
    SYNTAX INTEGER {
       block (1),
       forward (2),
       route (3),
       forward-route (4),
       high-priority (5),
       noOp(6),
       delete(7)
     }


    MAX-ACCESS read-write
    STATUS current
    DESCRIPTION
	"The type of action to be taken if the frame meets the
     conditions of the mask.
     noOp = disabled (mask remains on list, but is not active)
	 delete = mask is removed from the list. "
    ::= {  radBridgeMaskEntry 20 }

radBridgeCOD      OBJECT IDENTIFIER ::= {genBridge 4 }

radBridgeCODParamTable OBJECT-TYPE
	SYNTAX  SEQUENCE OF RadBridgeCODEntry
	MAX-ACCESS  not-accessible
	STATUS  current
	DESCRIPTION
	       "The table of COD parameters "
	::= { radBridgeCOD 1}


radBridgeCODEntry OBJECT-TYPE
	SYNTAX RadBridgeCODEntry
	MAX-ACCESS  not-accessible
	STATUS  current
	DESCRIPTION
	       "Each radBridgeCODEntry consists of the following parameters"
	INDEX   {radBridgeCODIfIndex}
	::= { radBridgeCODParamTable 1 }


RadBridgeCODEntry ::= SEQUENCE {
	  radBridgeCODIfIndex
		Integer32,
	  radBridgeCODManualConnect
		INTEGER,
	  radBridgeCODMode
		INTEGER,
	  radBridgeCODConnectDelay
		Integer32,
	  radBridgeCODisConnectDelay
		Integer32,
	  radBridgeCODImplicitSwitch
		INTEGER,
	  radBridgeCODNumAccess
		Counter32,
	  radBridgeCODTotalConnecTime
		Integer32
 }

radBridgeCODIfIndex OBJECT-TYPE
	SYNTAX  Integer32
	MAX-ACCESS  read-only
	STATUS  current
	DESCRIPTION
	       "The interface to which this COD entry is applicable."
	::= { radBridgeCODEntry 1 }

radBridgeCODManualConnect OBJECT-TYPE
	SYNTAX  INTEGER {
		connect(1),
		disconnect(2)
	     }
	MAX-ACCESS  read-write
	STATUS  current
	DESCRIPTION
	       "The management station can start connection manually
		by setting this parameter"
	::= { radBridgeCODEntry 2 }


radBridgeCODMode OBJECT-TYPE
	SYNTAX  INTEGER {
		answer(1),
		originate(2),
		disable(3),
	    answerAndOriginate(4)
	     }
	MAX-ACCESS  read-write
	STATUS  current
	DESCRIPTION
	     "In answer mode only one incoming call may be accepted at a time. Other nodes
	      attempting to access the local modem will receive a busy signal until the
	      connection is terminated. (Answer mode has no difficulty supporting multiple
	      remote connections to one local port, as blocking multiple incoming calls is
	      just a modem function. Originate mode, on the other
	      hand will only support a single local port to remote port connection).
	      The disable parameter disables the COD utility for this interface.
	      Choosing any other mode will enable the COD utility."
	::= { radBridgeCODEntry 3 }

radBridgeCODConnectDelay OBJECT-TYPE
	SYNTAX  Integer32
	MAX-ACCESS  read-write
	STATUS  current
	DESCRIPTION
     "The connect delay defines the minimum time period that
      the link must stay disconnected, between 2 succesive
      connections (in seconds)."
	::= { radBridgeCODEntry 4 }

radBridgeCODisConnectDelay OBJECT-TYPE
	SYNTAX  Integer32
	MAX-ACCESS  read-write
	STATUS  current
	DESCRIPTION
		"The disconnect delay defines the minimum time period
		 the link must stay connected, between 2 succesive
		 disconnections (in seconds)."
	::= { radBridgeCODEntry 5 }


radBridgeCODImplicitSwitch  OBJECT-TYPE
	SYNTAX  INTEGER  {
	      enable(1),
	      disable(2)
	}
	MAX-ACCESS  read-write
	STATUS  current
	DESCRIPTION
	     "The inplicit switch allows the user to ignore implicit triggers  provided
	      by the COD software."
--      DEFVAL  { 1 }
	::= { radBridgeCODEntry 6 }


radBridgeCODNumAccess  OBJECT-TYPE
	SYNTAX Counter32
	MAX-ACCESS read-only
	STATUS  current
	DESCRIPTION
	     "The number of successful connections that have been established since
	      the COD has been reset."
	::= { radBridgeCODEntry 7}

radBridgeCODTotalConnecTime  OBJECT-TYPE
	SYNTAX Integer32
	MAX-ACCESS read-only
	STATUS  current
	DESCRIPTION
	     "The sum of all the connect time intervals since the COD was reset."
	::= { radBridgeCODEntry 8}





radBridgeCODTimeTriggerTable OBJECT-TYPE
	SYNTAX  SEQUENCE OF RadBridgeCODTimeTriggerEntry
	MAX-ACCESS  not-accessible
	STATUS  current
	DESCRIPTION
		     "The table of COD parameters "
	::= { radBridgeCOD 2 }

radBridgeCODTimeTriggerEntry  OBJECT-TYPE
	SYNTAX RadBridgeCODTimeTriggerEntry
	MAX-ACCESS not-accessible
	STATUS current
	DESCRIPTION
	      "Each radBridgeCODTimeTriggerEntry consists of the following parameters"
	INDEX   { radBridgeCODTimeIfIndex, radBridgeCODDay, radBridgeCODTimeTriggerNum }
	::= { radBridgeCODTimeTriggerTable 1 }

RadBridgeCODTimeTriggerEntry ::= SEQUENCE {
	radBridgeCODTimeIfIndex
	      Integer32,
	radBridgeCODDay
	      INTEGER,
	radBridgeCODTimeTriggerNum
	      Integer32,
	radBridgeCODTimeTriggerFrom
	      DisplayString,
	radBridgeCODTimeTriggerTo
	      DisplayString,
	radBridgeCODTimeTriggerStatus
	      INTEGER
	}

radBridgeCODTimeIfIndex OBJECT-TYPE
    SYNTAX Integer32
    MAX-ACCESS read-only
    STATUS current
    DESCRIPTION
	       "The interface to which this COD  Time Trigger  entry is applicable."
	    ::= { radBridgeCODTimeTriggerEntry 1}

radBridgeCODDay  OBJECT-TYPE
    SYNTAX  INTEGER {
	  mon(1),
	  tue(2),
	  wed(3),
	  thu(4),
	  fri(5),
	  sat(6),
	  sun(7)
	 }
    MAX-ACCESS read-only
    STATUS current
    DESCRIPTION
       " The  day of the week in which  the dial up connection operates."
    ::= { radBridgeCODTimeTriggerEntry 2 }

radBridgeCODTimeTriggerNum  OBJECT-TYPE
    SYNTAX  Integer32  (1..3)
    MAX-ACCESS read-only
    STATUS current
    DESCRIPTION
       " Every day of the week the user can configure 3 dial up connections."
   ::= { radBridgeCODTimeTriggerEntry 3 }

radBridgeCODTimeTriggerFrom  OBJECT-TYPE
    SYNTAX DisplayString
    MAX-ACCESS read-write
    STATUS current
    DESCRIPTION
       "Time to start Dial Up connection, in format hh:mm."
    ::= {radBridgeCODTimeTriggerEntry 4 }

radBridgeCODTimeTriggerTo  OBJECT-TYPE
    SYNTAX DisplayString
    MAX-ACCESS read-write
    STATUS current
    DESCRIPTION
       "Time to terminate Dial Up connection, in format HH:MM."
 ::= {radBridgeCODTimeTriggerEntry 5 }

radBridgeCODTimeTriggerStatus OBJECT-TYPE
	     SYNTAX  INTEGER {
		  valid(1),
		  invalid(2)
	    }
	     MAX-ACCESS  read-write
	     STATUS  current
	     DESCRIPTION
	       "The status of a table entry."
   ::= { radBridgeCODTimeTriggerEntry  6 }

radBridgeCODTraffic  OBJECT IDENTIFIER ::= { radBridgeCOD 3}

radBridgeCODTrafficTable OBJECT-TYPE
	SYNTAX  SEQUENCE OF RadBridgeCODTrafficEntry
	MAX-ACCESS  not-accessible
	STATUS  current
	DESCRIPTION
	       "The table of COD Traffic trigger "
	::= { radBridgeCODTraffic 1 }

radBridgeCODTrafficEntry OBJECT-TYPE
	SYNTAX RadBridgeCODTrafficEntry
	MAX-ACCESS  not-accessible
	STATUS  current
	DESCRIPTION
	       "Each radBridgeCODTrafficEntry consists of the following parameters."
	INDEX {radBridgeCODProtocolType}
	::= { radBridgeCODTrafficTable 1}


RadBridgeCODTrafficEntry ::= SEQUENCE {
	  radBridgeCODProtocolType
		INTEGER,
	  radBridgeCODTrafficTriggerStatus
		INTEGER }


radBridgeCODProtocolType OBJECT-TYPE
	SYNTAX INTEGER {
		ip(1),
		ipx(2),
		other(3)
}

	MAX-ACCESS  read-write
	STATUS  current
	DESCRIPTION
		"The Protocol Type of the Traffic Table"
	::= { radBridgeCODTrafficEntry 1 }


radBridgeCODTrafficTriggerStatus OBJECT-TYPE
	SYNTAX INTEGER {
		enable(1),
		disable(2)
}
	MAX-ACCESS  read-write
	STATUS  current
	DESCRIPTION
		"Command of Status of the Protocol Traffic Trigger"
	::= { radBridgeCODTrafficEntry 2 }


radBridgeCODRemoteIPAddr  OBJECT-TYPE
	SYNTAX IpAddress
	MAX-ACCESS  read-write
	STATUS  current
	DESCRIPTION
		" This is the Remote IP Address"
	::= { radBridgeCODTraffic 2 }


radBridgeCODIPMask  OBJECT-TYPE
	SYNTAX IpAddress
	MAX-ACCESS  read-write
	STATUS  current
	DESCRIPTION
		" This is the Mask of the Remote IP Address"
	::= { radBridgeCODTraffic 3 }

radBridgeCODTrafficTriggerProtType OBJECT-TYPE
	SYNTAX  OCTET STRING
	MAX-ACCESS  read-write
	STATUS  current
	DESCRIPTION
		"Protocol Type for the User Defined Protocol Traffic Trigger (3)."
	::= { radBridgeCODTraffic 4 }


--COD Condition table

radBridgeCODCondTable OBJECT-TYPE
	SYNTAX  SEQUENCE OF RadBridgeCODCondEntry
	MAX-ACCESS  not-accessible
	STATUS  current
	DESCRIPTION
	       "The table of COD Condition parameters "
	::= { radBridgeCOD 4}


radBridgeCODCondEntry OBJECT-TYPE
	SYNTAX RadBridgeCODCondEntry
	MAX-ACCESS  not-accessible
	STATUS  current
	DESCRIPTION
	       "Each radBridgeCODCondEntry consists of the following parameters"
	INDEX   {radBridgeCODCondIfIndex}
	::= { radBridgeCODCondTable 1 }


RadBridgeCODCondEntry ::= SEQUENCE {
	  radBridgeCODCondIfIndex
	  	Integer32,
	  radBridgeCODOriginateConnectCondition
	  	INTEGER,
	  radBridgeCODOriginateDisConnectCondition
	  	INTEGER,
	  radBridgeCODOriginateDisConnectDelay
	  	Integer32,
	  radBridgeCODAnswerConnectCondition
	  	INTEGER,
      radBridgeCODSpecificOnTrafficOIDCondition
        OBJECT IDENTIFIER,
      radBridgeCODDisConnectMinimunFramesNumber
        Integer32



  }


radBridgeCODCondIfIndex OBJECT-TYPE
	SYNTAX  Integer32
	MAX-ACCESS  read-only
	STATUS  current
	DESCRIPTION
	"The interface, this COD entry is applicable to."
	::= { radBridgeCODCondEntry 1 }

radBridgeCODOriginateConnectCondition OBJECT-TYPE
	SYNTAX  INTEGER {
               onPowerOn           (1),
               whenAnyStationOnLan (2),
               onTraffic           (3),
               onManualConnect     (4)
               }
	MAX-ACCESS  read-write
	STATUS  current
	DESCRIPTION
	     " This condition, allows the user to specify the
	       condition under which the link is connected.
           The options are
                  onPowerOn           - On power on.
                  whenAnyStationOnLan - When any station on lan.
                  onTraffic           - On traffic. The user can specify the
                                        condition/s for connection.
                                        The connection will be defined in
                                        CODSpecificOnTrafficConditionOID .
                  onManualConnect     - depends on radBridgeCODManualConnect
                                        OBJECT-TYPE (=connect).
                  "
	::= { radBridgeCODCondEntry 2 }

radBridgeCODOriginateDisConnectCondition OBJECT-TYPE
	SYNTAX  INTEGER {
               noStationOnLan                 (1),
               onTraffic                      (2),
               onDelayFromConnectionOnRequest (3),
               onManualDisConnect             (4)
               }
	MAX-ACCESS  read-write
	STATUS  current
	DESCRIPTION
	     "This condition allows the user to specify the
	      condition under which the link is disconnected.
          The options are:
                  noStationOnLan - When there is no station on lan.
                                   Counts 15 minutes from the point the last
                                   frame from lan has been received. If no
                                   frame have been transmitted on lan by the
                                   end of this period, disconnect the connection.
                  onTraffic      - On traffic. The user can specify the
                                   condition/s for disconnection.
                                   The disconnection will be defined in
                                   CODSpecificOnTrafficConditionOID .
                  onDelayFromConnectionOnRequest -
                                   On Delay From Connection On Request .
                                   The delay time period will be defined in
                                   CODOriginateDisConnectDelay .
                  onManualDisConnect - depends on radBridgeCODManualConnect
                                    OBJECT-TYPE (=disconnect).
                  "
	::= { radBridgeCODCondEntry 3 }

radBridgeCODOriginateDisConnectDelay OBJECT-TYPE
	SYNTAX  Integer32
	MAX-ACCESS  read-write
	STATUS  current
	DESCRIPTION
             "Delay time in seconds. "
	::= { radBridgeCODCondEntry 4 }

radBridgeCODAnswerConnectCondition OBJECT-TYPE
	SYNTAX  INTEGER {
               onPowerOn           (1),
               whenAnyStationOnLan (2),
               onTraffic           (3),
               onManualConnect     (4)
               }
	MAX-ACCESS  read-write
	STATUS  current
	DESCRIPTION
	     "CODCondAnswerConnect allows the user to specify
	      the condition under which the link is connected.
          The options are:
                  onPowerOn           - On power on.
                  whenAnyStationOnLan - When any station on lan.
                  onTraffic           - On traffic. The user can specify the
                                        condition/s for connection.
                                        The connection will be defined in
                                        CODSpecificOnTrafficConditionOID .
                  onManualConnect     - depends on radBridgeCODManualConnect
                                        OBJECT-TYPE .
             "
	::= { radBridgeCODCondEntry 5 }


radBridgeCODSpecificOnTrafficOIDCondition OBJECT-TYPE
        SYNTAX  OBJECT IDENTIFIER
        MAX-ACCESS  read-only
        STATUS  current
        DESCRIPTION
             "A reference to a specific entry in the
			  radBridgeMaskTable, which describes the
              particular COD condition .
              If Connect or Disconnect Conditions are not
              onTraffic, its value should be set to the
              OBJECT IDENTIFIER { 0 0 }. "
	::= { radBridgeCODCondEntry 6 }


radBridgeCODDisConnectMinimunFramesNumber OBJECT-TYPE
        SYNTAX Integer32
        MAX-ACCESS  read-write
        STATUS  current
        DESCRIPTION
             "Frames rate."
	::= { radBridgeCODCondEntry 7 }

--The IPX following objects define the Spoofing

radBridgeIPX      OBJECT IDENTIFIER ::= {genBridge 5 }


radBridgeIPXdriver      OBJECT IDENTIFIER ::=  {radBridgeIPX 1 }
radBridgeIPXRip          OBJECT IDENTIFIER ::=  {radBridgeIPX 2 }
radBridgeIPXSap         OBJECT IDENTIFIER ::=  {radBridgeIPX 3 }

radBridgeIPXForwarding OBJECT-TYPE
    SYNTAX  INTEGER {
	forwarding(1),
       not-forwarding(2)
       }
    MAX-ACCESS  read-write
    STATUS  current
    DESCRIPTION
       "The indication of whether this entity is acting as an IPX
       gateway in respect to the forwarding of datagrams received by,
       but not addressed to, this entity.  IPX gateways forward
       datagrams.  IPX hosts do not.  Note that changing this parameter
       requiers RESET of the router."
--      DEFVAL  { 1 }
    ::= { radBridgeIPXdriver 1 }

radBridgeIPXRipOutPackets OBJECT-TYPE
    SYNTAX  Counter32
    MAX-ACCESS  read-only
    STATUS  current
    DESCRIPTION
       "The total number of packets transmitted by RIP."
    ::= { radBridgeIPXRip 1 }

radBridgeIPXRipInPackets OBJECT-TYPE
    SYNTAX  Counter32
    MAX-ACCESS  read-only
    STATUS  current
    DESCRIPTION
       "The total number of packets received by RIP.  This will include
       any packets that are subsequently discarded."
    ::= { radBridgeIPXRip 2 }

radBridgeIPXRipInDiscards OBJECT-TYPE
    SYNTAX  Counter32
    MAX-ACCESS  read-only
    STATUS  current
    DESCRIPTION
       "The number of received packets discarded by RIP."
    ::= { radBridgeIPXRip 3 }

radBridgeIPXRipTblNoOfEntries OBJECT-TYPE
    SYNTAX  Integer32
    MAX-ACCESS  read-only
    STATUS  current
    DESCRIPTION
       "The max number of entries that exist in the RIP routing table."
    ::= { radBridgeIPXRip 4 }

radBridgeIPXRipTblBcastTrigUpdateInterval OBJECT-TYPE
    SYNTAX  Integer32
    MAX-ACCESS  read-write
    STATUS  current
    DESCRIPTION
       "The default time interval (in seconds)between triggered RIP updates on
       a broadcast type interface.  A triggered update occurs when a change is
       detected in the routing database.  This time interval delays the
       broadcasting of these updates so that changes on the network will
       not result in a lot of triggered updates."
    ::= { radBridgeIPXRip 5 }



radBridgeIPXRipTable OBJECT-TYPE
    SYNTAX  SEQUENCE OF RadBridgeIPXRipTableEntry
    MAX-ACCESS  not-accessible
    STATUS  current
    DESCRIPTION
       "The routing table used by RIP to calculate routes to remote
       desination networks."
    ::= { radBridgeIPXRip 6 }

radBridgeIPXRipTableEntry OBJECT-TYPE
    SYNTAX  RadBridgeIPXRipTableEntry
    MAX-ACCESS  not-accessible
    STATUS  current
    DESCRIPTION
       "The routing information for one of this entity's destination networks."
    INDEX   { radBridgeIPXRipDestNetwork,
	      radBridgeIPXRipPolicy }
    ::= { radBridgeIPXRipTable 1 }

RadBridgeIPXRipTableEntry ::= SEQUENCE {
radBridgeIPXRipDestNetwork
     OCTET STRING (SIZE(4)),
radBridgeIPXRipPolicy
     INTEGER,
radBridgeIPXRipForwardingRouter
     OCTET STRING (SIZE(6)),
radBridgeIPXRipNIC
     Integer32,
radBridgeIPXRipTickMetric
     Integer32,
radBridgeIPXRipHopMetric
     Integer32,
radBridgeIPXRipAgingTime
     TimeTicks,
radBridgeIPXRipValueStatus
     INTEGER,
radBridgeIPXRipForwardType
     INTEGER
}

radBridgeIPXRipDestNetwork OBJECT-TYPE
    SYNTAX  OCTET STRING (SIZE(4))
    MAX-ACCESS  read-only
    STATUS  current
    DESCRIPTION
	 "The destination network address to which this entry's
	  routing information pertains."
    ::= {radBridgeIPXRipTableEntry 1 }

radBridgeIPXRipPolicy OBJECT-TYPE
    SYNTAX  INTEGER  {
	main(1),
	alternate(2)
    }
    MAX-ACCESS  read-only
    STATUS  current
    DESCRIPTION
       "A value specifying the precidence of the route.  A value of
       zero means that the route is the best route, a value of one
       means that the route is the second best route and so on."
    ::= { radBridgeIPXRipTableEntry 2 }

radBridgeIPXRipForwardingRouter OBJECT-TYPE
    SYNTAX  OCTET STRING (SIZE(6))
    MAX-ACCESS  read-write
    STATUS  current
    DESCRIPTION
       "The IPX node address of the next hop (router) for the
       entry's associated destination network."
    ::= { radBridgeIPXRipTableEntry 3 }

radBridgeIPXRipNIC OBJECT-TYPE
    SYNTAX  Integer32
    MAX-ACCESS  read-write
    STATUS  current
    DESCRIPTION
       "An interface identifier specifying what IPX interface the
       next hop can be found on."
    ::= { radBridgeIPXRipTableEntry 4 }

radBridgeIPXRipTickMetric OBJECT-TYPE
    SYNTAX  Integer32
    MAX-ACCESS  read-write
    STATUS  current
    DESCRIPTION
       "The metric, in terms of transit time, associated with the route
       given by the entry.  This time is in terms of 1/18ths of a
       second."
    ::= { radBridgeIPXRipTableEntry 5 }

radBridgeIPXRipHopMetric OBJECT-TYPE
    SYNTAX  Integer32
    MAX-ACCESS  read-write
    STATUS  current
    DESCRIPTION
       "The metric, in terms of distance , associated with the route
	given by the entry."
    ::= { radBridgeIPXRipTableEntry 6 }


radBridgeIPXRipAgingTime OBJECT-TYPE
    SYNTAX  TimeTicks
    MAX-ACCESS  read-only
    STATUS  current
    DESCRIPTION
      "The last time that the entry was updated.  The time will be
       provided in terms of the MIB-I object sysUpTime."
    ::= {radBridgeIPXRipTableEntry 7 }

radBridgeIPXRipValueStatus OBJECT-TYPE
    SYNTAX  INTEGER {
	static(1),
	dynamic(2),
	invalid(3),
	semiDynamic(4)
    }
    MAX-ACCESS  read-write
    STATUS  current
    DESCRIPTION
       "The entry status value; whether the entry is permanent (added
	statically), reachable or unreachable.  In the latter two cases
       it would be added by RIP. A semiDynamic entry is an entry
       enterd manualy by the user and can be updated by the router."
    ::= { radBridgeIPXRipTableEntry 8 }

radBridgeIPXRipForwardType  OBJECT-TYPE
    SYNTAX  INTEGER {
	 other    (1), -- not specified by this MIB
	 local    (2), -- local interface
	 remote   (3)  -- remote destination
     }
     MAX-ACCESS   read-write
     STATUS   current
     DESCRIPTION
	"The type of route. Note that local(2) refers to a route for which the
	 next hop is the final destination; remote(3) refers to  a  route
	 for which  the next  hop is not the final destination."
    ::= {radBridgeIPXRipTableEntry 9 }



radBridgeIPXRipInfTable OBJECT-TYPE
     SYNTAX  SEQUENCE OF RadBridgeIPXRipInfEntry
     MAX-ACCESS  not-accessible
     STATUS  current
     DESCRIPTION
     "The RIP interface table."
     ::= { radBridgeIPXRip 7 }

radBridgeIPXRipInfEntry OBJECT-TYPE
     SYNTAX  RadBridgeIPXRipInfEntry
     MAX-ACCESS  not-accessible
     STATUS  current
     DESCRIPTION
	  "Each entry corresponds to one ifindex."
     INDEX   { radBridgeIPXRipInfIfIndex}
     ::= { radBridgeIPXRipInfTable 1 }

RadBridgeIPXRipInfEntry ::= SEQUENCE {
     radBridgeIPXRipInfIfIndex
     Integer32,
     radBridgeIPXRipInfBcastUpdate
     Integer32,
     radBridgeIPXRipInfAgeMultiplier
     Integer32
     }

radBridgeIPXRipInfIfIndex OBJECT-TYPE
     SYNTAX  Integer32
     MAX-ACCESS  read-only
     STATUS  current
     DESCRIPTION
	  "This value of Ifindex is same as radBridgeIPXIfIndex in the
	   IPX Interface Table."
     ::= { radBridgeIPXRipInfEntry 1 }

radBridgeIPXRipInfBcastUpdate OBJECT-TYPE
     SYNTAX  Integer32
     MAX-ACCESS  read-write
     STATUS  current
     DESCRIPTION
	    "The RIP periodic update interval, in seconds. Zero value
	     corresponds to infinite interval."
--     DEFVAL {60}
     ::= { radBridgeIPXRipInfEntry 2 }

radBridgeIPXRipInfAgeMultiplier OBJECT-TYPE
     SYNTAX  Integer32
     MAX-ACCESS  read-write
     STATUS  current
     DESCRIPTION
       "The holding multiplier for information received in RIP
       periodic updates. Zero value corresponds to infinite aging time."
--     DEFVAL {3}
     ::= { radBridgeIPXRipInfEntry 3 }

radBridgeIPXSapOutPackets OBJECT-TYPE
    SYNTAX  Counter32
    MAX-ACCESS  read-only
    STATUS  current
    DESCRIPTION
	   "The total number of packets transmitted by SAP."
    ::= { radBridgeIPXSap 1 }

radBridgeIPXSapInPackets OBJECT-TYPE
    SYNTAX  Counter32
    MAX-ACCESS  read-only
    STATUS  current
    DESCRIPTION
      "The total number of packets received by SAP.  This will include
       any packets that are subsequently discarded."
    ::= { radBridgeIPXSap 2 }

radBridgeIPXSapInDiscards OBJECT-TYPE
    SYNTAX  Counter32
    MAX-ACCESS  read-only
    STATUS  current
    DESCRIPTION
	   "The number of received packets discarded by SAP."
    ::= { radBridgeIPXSap 3 }


radBridgeIPXSapTblNoOfEntries OBJECT-TYPE
    SYNTAX  Integer32
    MAX-ACCESS  read-only
    STATUS  current
    DESCRIPTION
	   "The max number of entries that exist in the SAP Server
    Information table."
    ::= { radBridgeIPXSap 4 }

radBridgeIPXSapTblBcastTrigUpdateInterval OBJECT-TYPE
    SYNTAX  Integer32
    MAX-ACCESS  read-write
    STATUS  current
    DESCRIPTION
       "The default time interval (in seconds) between triggered SAP updates on a
	broadcast style interface.  A triggered update occurs when a
	change is detected in the service database.  This time interval
	delays the transmission of these updates so that changes on the
	network will not result in a lot of triggered updates."
    ::= { radBridgeIPXSap 5 }



radBridgeIPXSapTable OBJECT-TYPE
    SYNTAX  SEQUENCE OF RadBridgeIPXSapTableEntry
    MAX-ACCESS  not-accessible
    STATUS  current
    DESCRIPTION
	   "The Server Information table is used by SAP to store information
	   of services which are available on the internetwork."
    ::= { radBridgeIPXSap 6 }

radBridgeIPXSapTableEntry OBJECT-TYPE
    SYNTAX  RadBridgeIPXSapTableEntry
    MAX-ACCESS  not-accessible
    STATUS  current
    DESCRIPTION
       "The server information for one of this entity's server entries."
    INDEX   { radBridgeIPXSapServerType,
	  radBridgeIPXSapName }
    ::= { radBridgeIPXSapTable 1 }

RadBridgeIPXSapTableEntry ::= SEQUENCE {
    radBridgeIPXSapServerType
	Integer32,
    radBridgeIPXSapName
	DisplayString (SIZE(48)),
    radBridgeIPXSapNetwork
	OCTET STRING (SIZE(4)),
    radBridgeIPXSapNode
	OCTET STRING (SIZE(6)),
    radBridgeIPXSapSocket
	Integer32,
    radBridgeIPXSapHopsToServer
	Integer32,
    radBridgeIPXSapNIC
	Integer32,
    radBridgeIPXSapAgingTime
	TimeTicks,
   radBridgeIPXSapStatus
	INTEGER
    }

radBridgeIPXSapServerType OBJECT-TYPE
    SYNTAX  Integer32
    MAX-ACCESS  read-only
    STATUS  current
    DESCRIPTION
	   "The type of the server for which this entry pertains."
    ::= { radBridgeIPXSapTableEntry 1 }

radBridgeIPXSapName OBJECT-TYPE
    SYNTAX  DisplayString (SIZE(48))
    MAX-ACCESS  read-only
    STATUS  current
    DESCRIPTION
	   "The name of the server for which this entry pertains."
    ::= { radBridgeIPXSapTableEntry 2 }

radBridgeIPXSapNetwork OBJECT-TYPE
    SYNTAX  OCTET STRING (SIZE(4))
    MAX-ACCESS  read-write
    STATUS  current
    DESCRIPTION
	   "The IPX network address of the host on which this server exists."
    ::= { radBridgeIPXSapTableEntry 3 }

radBridgeIPXSapNode OBJECT-TYPE
    SYNTAX  OCTET STRING (SIZE(6))
    MAX-ACCESS  read-write
    STATUS  current
    DESCRIPTION
	   "The IPX node address of the host on which this server exists."
    ::= { radBridgeIPXSapTableEntry 4 }

radBridgeIPXSapSocket OBJECT-TYPE
    SYNTAX  Integer32
    MAX-ACCESS  read-write
    STATUS  current
    DESCRIPTION
	   "The IPX socket number that is being used by the server to
	   which this entry pertains."
    ::= { radBridgeIPXSapTableEntry 5 }

radBridgeIPXSapHopsToServer OBJECT-TYPE
    SYNTAX  Integer32 (1..16)
    MAX-ACCESS  read-write
    STATUS  current
    DESCRIPTION
       "The number of hops to the entity on which this server exists."
    ::= { radBridgeIPXSapTableEntry 6 }

radBridgeIPXSapNIC OBJECT-TYPE
    SYNTAX  Integer32
    MAX-ACCESS  read-write
    STATUS  current
    DESCRIPTION
       "An Network Interface Card identifier specifying what IPX
	interface the next hop can be found on."
    ::= { radBridgeIPXSapTableEntry 7 }

radBridgeIPXSapAgingTime OBJECT-TYPE
    SYNTAX  TimeTicks
    MAX-ACCESS  read-only
    STATUS  current
    DESCRIPTION
       "The last time that the entry was updated.  The time will be
	provided in terms of the MIB-I object sysUpTime."
    ::= { radBridgeIPXSapTableEntry 8 }

radBridgeIPXSapStatus OBJECT-TYPE
    SYNTAX  INTEGER {
    permanent(1),
    dynamic(2),
    invalid(3),
    semiDynamic(4)
    }
    MAX-ACCESS  read-write
    STATUS  current
    DESCRIPTION
       "The status of the entry."
    ::= { radBridgeIPXSapTableEntry 9 }



radBridgeIPXSapInfTable OBJECT-TYPE
    SYNTAX  SEQUENCE OF RadBridgeIPXSapInfEntry
    MAX-ACCESS  not-accessible
    STATUS  current
    DESCRIPTION
    "The Sap interface table."
    ::= { radBridgeIPXSap 7 }

radBridgeIPXSapInfEntry OBJECT-TYPE
    SYNTAX  RadBridgeIPXSapInfEntry
    MAX-ACCESS  not-accessible
    STATUS  current
    DESCRIPTION
	 "Each entry corresponds to one ifindex."
    INDEX   {radBridgeIPXSapInfIfIndex}
    ::= { radBridgeIPXSapInfTable 1 }

RadBridgeIPXSapInfEntry ::= SEQUENCE {
    radBridgeIPXSapInfIfIndex
    Integer32,
    radBridgeIPXSapInfBcastUpdate
    Integer32,
    radBridgeIPXSapInfAgeMultiplier
    Integer32
    }

radBridgeIPXSapInfIfIndex OBJECT-TYPE
    SYNTAX  Integer32
    MAX-ACCESS  read-only
    STATUS  current
    DESCRIPTION
	 "This value of Ifindex is same as radBridgeIPXIfIndex in the
	  IPX Interface Table."
    ::= { radBridgeIPXSapInfEntry 1 }

radBridgeIPXSapInfBcastUpdate OBJECT-TYPE
    SYNTAX  Integer32
    MAX-ACCESS  read-write
    STATUS  current
    DESCRIPTION
       "The SAP periodic update interval, in seconds. Zero value
       corresponds to infinite interval."
--    DEFVAL {60}
    ::= { radBridgeIPXSapInfEntry 2 }

radBridgeIPXSapInfAgeMultiplier OBJECT-TYPE
    SYNTAX  Integer32
    MAX-ACCESS  read-write
    STATUS  current
    DESCRIPTION
       "The holding multiplier for information received in SAP
       periodic updates. Zero value corresponds to infinite aging time."
--    DEFVAL {3}
    ::= { radBridgeIPXSapInfEntry 3 }


-- radMaskingTab defines the new format of RAD Bridge masking tables


GenAddress ::= OCTET STRING (SIZE(12))

newMasking     OBJECT IDENTIFIER ::= {genBridge 6 }

maskingMaxEntries OBJECT-TYPE
    SYNTAX  Integer32
    MAX-ACCESS  read-only
    STATUS  current
    DESCRIPTION
        "The maximum number of entries in the masking table."
    ::=  { newMasking 1 }


maskingCurrentEntries OBJECT-TYPE
    SYNTAX  Integer32
    MAX-ACCESS  read-only
    STATUS  current
    DESCRIPTION
        "The number of entries in the mask table."
    ::=  { newMasking 2 }

maskingTable    OBJECT-TYPE
    SYNTAX  SEQUENCE  OF MaskingEntry
    MAX-ACCESS  not-accessible
    STATUS  current
    DESCRIPTION
	    "This is the new masking scheme.
	    Mask tables enable definition of forwarding restrictions and
	    control of message flow in the internetwork. Each entry
	    in this table defines a mask statement and an action defined by
	    maskingOperation."
    ::=  { newMasking 3 }

maskingEntry OBJECT-TYPE
    SYNTAX  MaskingEntry
    MAX-ACCESS  not-accessible
    STATUS  current
    DESCRIPTION
	    "Defines the contents of each line in the mask table."
    INDEX  { maskingType, maskingIfIndex, maskingIndex }
    ::=  { maskingTable 1 }

MaskingEntry ::= SEQUENCE {
                     maskingType
					  INTEGER,
                     maskingIfIndex
                      Integer32,
                     maskingIndex
                      Integer32,
                     maskingProtocolType
                      INTEGER,
					 maskingSmartMaskOID
					  OBJECT IDENTIFIER,
                     maskingFrameType
                      INTEGER,
                     maskingFrameTypeCondition
                      INTEGER,
                     maskingSourceAddress
                      GenAddress,
                     maskingSourceActiveBits
                      GenAddress,
                     maskingSourceMacOrNet
                        INTEGER,
                     maskingSourceCondition
                      INTEGER,
                     maskingDestAddress
                      GenAddress,
                     maskingDestActiveBits
                      GenAddress,
                     maskingDestMacOrNet
                        INTEGER,
                     maskingDestCondition
                      INTEGER,
                     maskingLowLevelProt
                      INTEGER,
                     maskingLowLevelProtCondition
                      INTEGER,
                     maskingHighLevelProt
                      Integer32,
                     maskingHighLevelProtCondition
                      INTEGER,
                     maskingPortNum
                      Integer32,
                     maskingPortNumCondition
                      INTEGER,
                     maskingOperation
                      INTEGER,
                     maskingSrcPortNum
                      Integer32,
                     maskingSrcPortNumCondition
                      INTEGER
                       }

   maskingType OBJECT-TYPE
    SYNTAX  INTEGER {
	  tx            (1),
	  rx            (2),
      compress(3),
      priority(4),
      loadSharing(5),
      facs(6),
      codConnect(7),
      codDisconnect(8)
     }
    MAX-ACCESS  read-write
    STATUS  current
    DESCRIPTION
        "Defines the type of mask entry. "
    ::= {    maskingEntry 1  }


   maskingIfIndex  OBJECT-TYPE
    SYNTAX Integer32
    MAX-ACCESS  read-write
    STATUS  current
    DESCRIPTION
	"Specifies the ifIndex of the interface to which the mask is applied."
	::= {    maskingEntry 2  }



   maskingIndex OBJECT-TYPE
    SYNTAX  Integer32
    MAX-ACCESS  read-write
    STATUS  current
    DESCRIPTION
        "An index to the masking table. This number should not be greater than maskingMaxEntries"
    ::= {    maskingEntry 3  }




   maskingProtocolType OBJECT-TYPE
    SYNTAX  INTEGER {
    unknown     (1),
    ip          (2),
	ipx         (3),
	sna         (4),
	netbios     (5),
              apple      (6),
              dec         (7),
    all         (255)
    }
    MAX-ACCESS  read-write
    STATUS  current
    DESCRIPTION
         "The base protocol for masking. IPX, IP, others."
    ::= {    maskingEntry 4  }


    maskingSmartMaskOID OBJECT-TYPE
	 SYNTAX  OBJECT IDENTIFIER
	 MAX-ACCESS  read-only
	 STATUS  current
	 DESCRIPTION
	      "A reference to a specific Smart mask table (old radBridgeMaskTable)
	       which enables a more specific mask type.
		   If this information is not available, its value
		   should be set to the OBJECT IDENTIFIER { 0 0 }. "
     ::= {  maskingEntry 5  }


    maskingFrameType OBJECT-TYPE
    SYNTAX  INTEGER {
    unknown     (1),
    all         (2),
    broadcast   (3),
    multicast   (4)
    }
    MAX-ACCESS  read-write
    STATUS  current
    DESCRIPTION
        "Enables the user to decide about frame type
          * all frame
          * just broadcast
          * just multicast."
    ::= {    maskingEntry 6  }

   maskingFrameTypeCondition OBJECT-TYPE
    SYNTAX  INTEGER {
    false      (1),
    true       (2)
    }
    MAX-ACCESS  read-write
    STATUS  current
    DESCRIPTION
	"Specifies the logical condition of the mask pattern:

	true  - Condition is valid if at the position specified by
   		   maskingFrameType the packet contains data that matches
  	the content of maskingFrameType.

	fa    lse - Condition is valid if at the position specified by
		   maskingFrameType the packet contains data that does not
    		match the content of maskingFrameType."
    ::= {    maskingEntry 7  }

   maskingSourceAddress OBJECT-TYPE
    SYNTAX  GenAddress
    MAX-ACCESS  read-write
    STATUS  current
    DESCRIPTION
       "The source address is according to the maskingMacOrNet and
        maskingProtocolType variables.
        In case of 'MAC' enter 6 bytes (48 bit) of source address.
        In case of 'NET'
            if the    maskingProtocolType is IP, this is the IP address
            if the    maskingProtocolType is IPX, this is the IPX address
                 (nnnnmmmmmmss)
                                nnnn   - IPX net address
                                mmmmmm - Node address (Mac)
                                ss     - IPX socket
        In case of 'Apple'
                                nn - net address (4 nibbles)
                                ss - socket (4 nibbles)."
    ::= {    maskingEntry 8  }

   maskingSourceActiveBits OBJECT-TYPE
    SYNTAX  GenAddress
    MAX-ACCESS  read-write
    STATUS  current
    DESCRIPTION
	   "Specifies the positions of the wild card characters (*)
	    in the    maskingSourceAddress field. Only the 1's bit will be taken in
        considerations."
    ::= {    maskingEntry 9  }

   maskingSourceMacOrNet OBJECT-TYPE
    SYNTAX  INTEGER {
    macAddress  (1),
    netAddress  (2),
    ipRange     (3),
    appleAddress(4)
    }
    MAX-ACCESS  read-write
    STATUS  current
    DESCRIPTION
	"The variable maskingSourceAddress and maskingSourceActiveBits
	 will be treated as MAC, or NET address.
	 -  If maskingProtocolType = 'all', 'sna', 'netbios', dec or
		'unknown', the maskingSourceMacOrNet can be macAddress only!
	 -  If maskingProtocolType = 'ip' the
		maskingSourceMacOrNet can be  macAddress or netAddress or
		appleAddress.
	 -  If maskingProtocolType = 'ipx', the
		maskingSourceMacOrNet can be either macAddress or netAddress.
	 -  If maskingProtocolType = 'apple', the
		maskingSourceMacOrNet can be either macAddress or appleAddress."
    ::= {    maskingEntry 10  }

   maskingSourceCondition OBJECT-TYPE
    SYNTAX  INTEGER {
    false (1),
    true (2)
    }
    MAX-ACCESS  read-write
    STATUS  current
    DESCRIPTION
	"Specifies the logical condition of the mask pattern:

	true  - Condition is valid if at the position specified by
	           maskingSourceAddress (in conjunction with maskingSourceActiveBits)
	        the packet contains data that matches the content of maskingSourceAddress.

	false - Condition is valid if at the position specified by
		   maskingSourceAddress (in conjunction with maskingSourceActiveBits)
	    	the packet contains data that does not match the content of
	        maskingSourceAddress."
    ::= {    maskingEntry 11 }

   maskingDestAddress OBJECT-TYPE
    SYNTAX  GenAddress
    MAX-ACCESS  read-write
    STATUS  current
    DESCRIPTION
       "If maskingFrameType = broadcast or multicast, this object
	    is NOT APPLICABLE.
	    If maskingFrameType = all or unknown, this object is
	    applicable.
        The destination address is according to the maskingMacOrNet and maskingProtocolType variables.
        In case of 'MAC' enter 6 bytes (48 bit) of source address.
        In case of 'NET'
            if the    maskingProtocolType is IP, this is the IP address
            if the    maskingProtocolType is IPX, this is the IPX address
                 (nnnnmmmmmmss)
                                nnnn   - IPX net address
                                mmmmmm - Node address (Mac)
                                ss     - IPX socket.
        In case of 'Apple'
                                nn - net address (4 nibbles)
                                ss - socket (4 nibbles).
        The IPX socket entered here has priority over the value of
        maskingLowLevelProt, when it is ipxRip, ipxSap or ipxSpx,
        unless the entered IPX socket is don't care. "
    ::= {    maskingEntry 12  }

   maskingDestActiveBits OBJECT-TYPE
    SYNTAX  GenAddress
    MAX-ACCESS  read-write
    STATUS  current
    DESCRIPTION
	   "If maskingFrameType = broadcast or multicast, this object
	    is NOT APPLICABLE.
	    If maskingFrameType = all or unknown, this object is
	    applicable.
	    Specifies the positions of the wild card characters (*)
	    in the    maskingDestAddress field. Only the 1's bit will be taken in
        considerations."
    ::= {    maskingEntry 13   }

   maskingDestMacOrNet OBJECT-TYPE
    SYNTAX  INTEGER {
    macAddress  (1),
    netAddress  (2),
    ipRange     (3),
    appleAddress(4)
    }
    MAX-ACCESS  read-write
    STATUS  current
    DESCRIPTION
	"If maskingFrameType = broadcast or multicast, this object
	 is NOT APPLICABLE.
	 If maskingFrameType = all or unknown, this object is
	 applicable.
	 -  If maskingProtocolType = 'all', 'sna', 'netbios', dec or
		'unknown', the maskingDestMacOrNet can be macAddress only!
	 -  If maskingProtocolType = 'ip' the
		maskingDestMacOrNet can be  macAddress or netAddress or
		appleAddress.
	 -  If maskingProtocolType = 'ipx', the
		maskingDestMacOrNet can be either macAddress or netAddress.
	 -  If maskingProtocolType = 'apple', the
		maskingDestMacOrNet can be either macAddress or appleAddress.
     The variable maskingDestAddress and maskingDestActiveBits will
	 be treated as MAC, or NET address.	"
    ::= {    maskingEntry 14  }

   maskingDestCondition OBJECT-TYPE
    SYNTAX  INTEGER {
    false (1),
    true (2)
    }
    MAX-ACCESS  read-write
    STATUS  current
    DESCRIPTION
	"If maskingFrameType = broadcast or multicast, this object
	 is NOT APPLICABLE.
	 If maskingFrameType = all or unknown, this object is
	 applicable.
	Specifies the logical condition of the mask pattern:

	true  - Condition is valid if at the position specified by
	           maskingDestAddress (in conjunction with maskingDestActiveBits)
	        the packet contains data that matches the content of maskingDestAddress.

	false - Condition is valid if at the position specified by
		   maskingDestAddress (in conjunction with maskingDestActiveBits)
		the packet contains data that does not match the content of maskingDestAddress."
    ::= {    maskingEntry 15  }

   maskingLowLevelProt OBJECT-TYPE
    SYNTAX  INTEGER {
      unknown (1), -- don't care
      ipxRip  (2), -- 0x51
      ipxSap  (3), -- 0x52
      ipxSpx  (4), -- 0x53
      ipUdp   (5), -- 0x54
      ipTcp   (6), -- 0x55
      ipIcmp  (7), -- 0x56
	ipxNcp  (8), -- 0x57
	ipxWan  (9), -- 0x58
	ipxEco (10), -- 0x59
	ipxErr (11), -- 0x5a
	ipxPep (12)  -- 0x5b
    }
    MAX-ACCESS  read-write
    STATUS  current
    DESCRIPTION
         "This field is set in conjunction with the maskingProtocolType variable.
          This variable specifies the low level protocol.
          The IPX socket entered in maskingDestAddress has priority
          over the value of maskingLowLevelProt, when it is ipxRip,
          ipxSap or ipxSpx, unless the entered IPX socket is don't
          care."
    ::= {    maskingEntry 16  }

   maskingLowLevelProtCondition OBJECT-TYPE
    SYNTAX  INTEGER {
    false  (1),
    true (2)
    }
    MAX-ACCESS  read-write
    STATUS  current
    DESCRIPTION
	"Specifies the logical condition of the mask pattern:

	true  - Condition is valid if at the position specified by
    	   maskingLowLevelProt the packet contains data that matches
		the content of maskingLowLevelProt.

	false - Condition is valid if at the position specified by
		   maskingLowLevelProt the packet contains data that does not
		match the content of maskingLowLevelProt."
    ::= {    maskingEntry 17  }

   maskingHighLevelProt OBJECT-TYPE
    SYNTAX  Integer32
    MAX-ACCESS  read-write
    STATUS  current
    DESCRIPTION
         "This field is set in connection to the maskingProtocolType variable.
          This variable specifies the high level protocols (application).
          As for today it supports just IP protocol stack.
          The object's value is a sum of the following instances values
          (selected by user):
                     none     (0), -- don't care
    			   ftp      (1),
    			   ftpC     (2),
    			   telnet   (4),
    			   smtp     (8),
    			   tftp     (16),
    			   snmp     (32),
    			   snmpTrap (64),
			       ipRip    (128),
			       www      (256),
			       email    (512),
			       dns      (1024),

                     For Apple Protocol only:
                     rtmp     (2048),
                     nbp      (4096),
                     atp      (8192),
                     aep      (16384),
                     zip      (32768),
                     adsp     (65536),
					 pap      (131072),
					 asp      (262144)

          Example: if ftp(1), snmp(32) and snmpTrap(64) instances
                   were selected, the value should be 97 (=1+32+64)."
    ::= {    maskingEntry 18  }

   maskingHighLevelProtCondition OBJECT-TYPE
    SYNTAX  INTEGER {
    false  (1),
    true (2)
    }
    MAX-ACCESS  read-write
    STATUS  current
    DESCRIPTION
	"Specifies the logical condition of the mask pattern:

	true  - Condition is valid if at the position specified by
		   maskingHighLevelProt the packet contains data that matches
		the content of    maskingHighLevelProt.

	false - Condition is valid if at the position specified by
		   maskingHighLevelProt the packet contains data that does not
		match the content of    maskingHighLevelProt."
    ::= {    maskingEntry 19  }

   maskingPortNum OBJECT-TYPE
    SYNTAX  Integer32
    MAX-ACCESS  read-write
    STATUS  current
    DESCRIPTION
        "The port number is the same as in high level protocol. It
         specifies the dest. port in IP case or the dest. socket
         in case of IPX & apple protocols.
		 IP  -  This object is applicable only if none (0) value was selected in
		        maskingHighLevelProt.
         IPX -  This object is applicable only if the socket
                entered in maskingDestAddress is 'don't care'(00) AND
			    maskingLowLevelProt is NOT ipxRip or ipxSap.
	     Apple - This option is applicable only if the socket
                entered in maskingDestAddress is 'don't care'(00)."
    ::= {    maskingEntry 20  }

   maskingPortNumCondition OBJECT-TYPE
    SYNTAX  INTEGER  {
    false  (1),
    true (2)
    }
    MAX-ACCESS  read-write
    STATUS  current
    DESCRIPTION
	"Specifies the logical condition of the mask pattern:

	true  - Condition is valid if at the position specified by
		   maskingPortNum the packet contains data that matches
		the content of    maskingPortNum.

	false - Condition is valid if at the position specified by
		   maskingPortNum the packet contains data that does not
		match the content of    maskingPortNum.
	 This object is applicable only when maskingPortNum is applicable."
    ::= {    maskingEntry 21  }


maskingOperation OBJECT-TYPE
    SYNTAX INTEGER {
       block         (1),
       forward       (2),
       route         (3),
       forward-route (4),
       high-priority (5),
       noOp          (6),
       delete        (7),
       smartMask     (8)
}
    MAX-ACCESS read-write
    STATUS current
    DESCRIPTION
	"The type of action to be taken if the frame meets the
     conditions of the mask.
       noOp = disabled (mask remains on list, but is not active)
	 delete = mask is removed from the list.
	 smartMask = the operation and destination of the mask will
	             be determined by the objects of the Smart Table
	             (old masking table: radBridgeMaskTable).
     If maskingType is codConnect, the 'block' value is NOT
     allowed.
     If maskingType is codDisconnect, the 'forward' value is NOT
     allowed."
     ::= {  maskingEntry 22 }

maskingSrcPortNum OBJECT-TYPE
    SYNTAX  Integer32
    MAX-ACCESS  read-write
    STATUS  current
    DESCRIPTION
        "The source port number.
         For IP:   No Condition.
         For IPX:  This object is applicable only if the socket entered in
                   maskingSourceAddress is don't care (00) and maskingLowLevelProt
                   is NOT ipxRip or ipxSap.
         For Apple:This object is applicable only if the socket entered in
                   maskingSourceAddress is don't care (00). "
    ::= {    maskingEntry 23  }

maskingSrcPortNumCondition OBJECT-TYPE
    SYNTAX  INTEGER  {
    false  (1),
    true (2)
    }
    MAX-ACCESS  read-write
    STATUS  current
    DESCRIPTION
	"The same as 'maskingPortNumCondition'.
       Relates to source port."
    ::= {    maskingEntry 24  }









--
-- file :v:\doc\rdv\mib\ver470\radsonet.txt
--
-- RAD-SONET-MIB DEFINITIONS ::= BEGIN

--Title:    RAD-SONET   MIB
--

--     IMPORTS
--     Gauge32                         FROM RFC1155-SMI
--     ifIndex                         FROM RFC1213-MIB
--     OBJECT-TYPE                     FROM RFC-1212
--     radWan                          FROM RAD-GEN-MIB;



--                RAD-SONET MIB

--Title:     RAD's SONET INTERFACE MIB
--Version:   1.0
--Date:      13.10.96
--By:        Yair Arian
--File:      sonet.mib
--
--Last update: 02-Apr-2001 by Smadar Tauber



sonetInterface  OBJECT IDENTIFIER  ::=  {diverseIfWanGen 2}

prtSonetPerfHistory  OBJECT IDENTIFIER  ::=  {sonetInterface 1}


          -- The SONET Medium Table

          prtSonetMediumTable OBJECT-TYPE
              SYNTAX  SEQUENCE OF PrtSonetMediumEntry
              MAX-ACCESS  not-accessible
              STATUS  current
              DESCRIPTION
                      "The SONET Medium table."
              ::= { prtSonetPerfHistory 1 }

          prtSonetMediumEntry OBJECT-TYPE
              SYNTAX  PrtSonetMediumEntry
              MAX-ACCESS  not-accessible
              STATUS  current
              DESCRIPTION
                      "An entry in the SONET Medium table. ifIndex of the
                       lowest SONET layer of type sonet(39)."
              INDEX   { ifIndex }
              ::= { prtSonetMediumTable 1 }

          PrtSonetMediumEntry ::=
              SEQUENCE {
                  prtSonetMediumTimeElapsed
                      Integer32,
                  prtSonetMediumValidIntervals
                      Integer32
                     }

           prtSonetMediumTimeElapsed OBJECT-TYPE
               SYNTAX  Integer32 (0..899)
               MAX-ACCESS  read-only
               STATUS  current
               DESCRIPTION
                       "The number of seconds that have elapsed since
                       the beginning of the near end current error-
                       measurement period."
              ::= { prtSonetMediumEntry 1 }

          prtSonetMediumValidIntervals OBJECT-TYPE
              SYNTAX  Integer32 (0..96)
              MAX-ACCESS  read-only
              STATUS  current
              DESCRIPTION
                      "The number of previous near end intervals for
                      which valid data was collected.  The value will be
                      96 unless the interface was brought online within
                      the last 24 hours, in which case the value will be
                      the number of complete 15 minute near end
                      intervals since the interface has been online."
              ::= { prtSonetMediumEntry 2 }


          -- The SONET Section/Line Current	Table

          -- The SONET Section/Line Current table contains various statistics being
          -- collected for the current 15 minute interval.

          prtSonetSectionLineCurrentTable OBJECT-TYPE
              SYNTAX  SEQUENCE OF PrtSectionLineCurrentEntry
              MAX-ACCESS  not-accessible
              STATUS  current
              DESCRIPTION
                      "The SONET Section/Line Current table."
              ::= { prtSonetPerfHistory 2 }

          prtSectionLineCurrentEntry OBJECT-TYPE
              SYNTAX  PrtSectionLineCurrentEntry
              MAX-ACCESS  not-accessible
              STATUS  current
              DESCRIPTION
                      "An entry in the SONET Section/Line Current table.
                       ifIndex of the section/line SONET layer of type
                       sonet(39)."
              INDEX   { ifIndex }
              ::= { prtSonetSectionLineCurrentTable 1 }

          PrtSectionLineCurrentEntry ::=
              SEQUENCE {
                  prtSonetCurrentLOS
                      Gauge32,
                  prtSonetCurrentLOF
                      Gauge32,
                  prtSonetCurrentLineAIS
                      Gauge32,
                  prtSonetCurrentLineFERF
                      Gauge32,
                  prtSonetCurrentSectionBIP
                      Gauge32,
                  prtSonetCurrentLineBIP
                      Gauge32,
                  prtSonetCurrentLineFEBE
                      Gauge32,
                  prtSonetCurrentUAS
	                  Gauge32,
                  prtSonetCurrentSES
                      Gauge32,
                  prtSonetCurrentES
                      Gauge32,
	              prtSonetCurrentStatus
                      OCTET STRING,
				  prtSonetCurrentLSV
                      Gauge32
              }

          prtSonetCurrentLOS OBJECT-TYPE
              SYNTAX  Gauge32
              MAX-ACCESS  read-only
              STATUS  current
              DESCRIPTION
                      "The counter associated with the number of LOS
                       seconds, encountered by a SONET interface in
                      the current 15 minute interval."
              ::= { prtSectionLineCurrentEntry 1 }

          prtSonetCurrentLOF OBJECT-TYPE
              SYNTAX  Gauge32
              MAX-ACCESS  read-only
              STATUS  current
              DESCRIPTION
                      "The counter associated with the number of LOF
                       seconds, encountered by a SONET
                       interface in the current 15 minute interval."
              ::= { prtSectionLineCurrentEntry 2 }

          prtSonetCurrentLineAIS OBJECT-TYPE
              SYNTAX  Gauge32
              MAX-ACCESS  read-only
              STATUS  current
              DESCRIPTION
                      "The counter associated with the number of Line AIS
                      seconds, encountered by a SONET
                      interface in the current 15 minute interval."
              ::= { prtSectionLineCurrentEntry 3 }

          prtSonetCurrentLineFERF OBJECT-TYPE
              SYNTAX  Gauge32
              MAX-ACCESS  read-only
              STATUS  current
              DESCRIPTION
                      "The counter associated with the number of Line
                      FERF seconds, encountered by a SONET
                      interface in the current 15 minute interval."
              ::= { prtSectionLineCurrentEntry 4 }

          prtSonetCurrentSectionBIP OBJECT-TYPE
              SYNTAX  Gauge32
              MAX-ACCESS  read-only
              STATUS  current
              DESCRIPTION
                      "The counter associated with the number of Section
                      BIP errors, encountered by a SONET
                      interface in the current 15 minute interval."
              ::= { prtSectionLineCurrentEntry 5 }

          prtSonetCurrentLineBIP OBJECT-TYPE
              SYNTAX  Gauge32
              MAX-ACCESS  read-only
              STATUS  current
              DESCRIPTION
                      "The counter associated with the number of Line
                      BIP errors, encountered by a SONET
                      interface in the current 15 minute interval."
              ::= { prtSectionLineCurrentEntry 6 }

          prtSonetCurrentLineFEBE OBJECT-TYPE
              SYNTAX  Gauge32
              MAX-ACCESS  read-only
              STATUS  current
              DESCRIPTION
                      "The counter associated with the number of Line
                      FEBE errors, encountered by a SONET
                      interface in the current 15 minute interval."
              ::= { prtSectionLineCurrentEntry 7 }

          prtSonetCurrentUAS OBJECT-TYPE
              SYNTAX  Gauge32
              MAX-ACCESS  read-only
              STATUS  current
              DESCRIPTION
                      "The counter associated with the number of UAS
                       encountered by a SONET
                       interface in the current 15 minute interval."
              ::= { prtSectionLineCurrentEntry 8 }

   		  prtSonetCurrentSES OBJECT-TYPE
              SYNTAX  Gauge32
              MAX-ACCESS  read-only
              STATUS  current
              DESCRIPTION
                      "The counter associated with the number of SES
                       encountered by a SONET
                       interface in the current 15 minute interval."
              ::= { prtSectionLineCurrentEntry 9 }

          prtSonetCurrentES OBJECT-TYPE
               SYNTAX Gauge32
               MAX-ACCESS  read-only
               STATUS  current
               DESCRIPTION
                      "The number of Errored Seconds, encountered  by a
                        SONET interface in the current 15 minute interval."
               ::= { prtSectionLineCurrentEntry 10 }

		  prtSonetCurrentStatus OBJECT-TYPE
		       SYNTAX OCTET STRING  (SIZE (4))
              MAX-ACCESS  read-only
              STATUS  current
              DESCRIPTION
                      "The statuses of the current interval:
                        0 - O.K.
                        1 - The link has been switched by a redundancy mechanism.
                        2 - Module is in/out.
                        4 - Empty - card is out."
              ::= { prtSectionLineCurrentEntry 11 }

		  prtSonetCurrentLSV OBJECT-TYPE
              SYNTAX  Gauge32
              MAX-ACCESS  read-only
              STATUS  current
              DESCRIPTION
                      "The counter associated with the number of LSV
                       seconds (Line Symbol Violation), encountered by a
                       SONET interface in the current 15 minute interval."
              ::= { prtSectionLineCurrentEntry 12 }


          -- The SONET Section/Line interface Interval

          -- The SONET Section/Line Interval Table contains various statistics
          -- collected by the Interface over the previous 24
          -- hours of operation.  The past 24 hours are broken into 96
          -- completed 15 minute intervals.

          prtSonetSectionLineIntervalTable OBJECT-TYPE
              SYNTAX  SEQUENCE OF PrtSectionLineIntervalEntry
              MAX-ACCESS  not-accessible
              STATUS  current
              DESCRIPTION
                      "The Section/Line Interval table."
              ::= { prtSonetPerfHistory 3 }

          prtSectionLineIntervalEntry OBJECT-TYPE
              SYNTAX  PrtSectionLineIntervalEntry
              MAX-ACCESS  not-accessible
              STATUS  current
              DESCRIPTION
                      "An entry in the SONET Section/Line Interval table.
                       ifIndex of the section/line SONET layer of type
                       sonet(39)."
              INDEX   { ifIndex, prtSonetLineIntervalNumber }
              ::= { prtSonetSectionLineIntervalTable 1 }

          PrtSectionLineIntervalEntry ::=
              SEQUENCE {
                  prtSonetLineIntervalNumber
                      Integer32,
                  prtSonetIntervalLOS
                      Gauge32,
                  prtSonetIntervalLOF
                      Gauge32,
                  prtSonetIntervalLineAIS
                      Gauge32,
                  prtSonetIntervalLineFERF
                      Gauge32,
                  prtSonetIntervalSectionBIP
                      Gauge32,
                  prtSonetIntervalLineBIP
                      Gauge32,
                  prtSonetIntervalLineFEBE
                      Gauge32,
                  prtSonetIntervalUAS
	                  Gauge32,
                  prtSonetIntervalSES
                      Gauge32,
                  prtSonetIntervalES
                      Gauge32,
 	    		  prtSonetIntervalStatus
                      OCTET STRING,
				  prtSonetIntervalLSV
                      Gauge32
             }

          prtSonetLineIntervalNumber OBJECT-TYPE
              SYNTAX  Integer32 (1..96)
              MAX-ACCESS  read-only
              STATUS  current
              DESCRIPTION
                      "A number between 1 and 96, where 1 is the most
                      recently completed 15 minute interval and 96 is
                      the least recently completed 15 minutes interval
                      (assuming that all 96 intervals are valid)."
              ::= { prtSectionLineIntervalEntry 1 }

          prtSonetIntervalLOS OBJECT-TYPE
              SYNTAX  Gauge32
              MAX-ACCESS  read-only
              STATUS  current
              DESCRIPTION
                      "The counter associated with the number of LOS
                      seconds , encountered by a SONET interface in
                      one of the previous 96, individual 15 minute,
                      intervals."
              ::= { prtSectionLineIntervalEntry 2 }

          prtSonetIntervalLOF OBJECT-TYPE
              SYNTAX  Gauge32
              MAX-ACCESS  read-only
              STATUS  current
              DESCRIPTION
                      "The counter associated with the number of LOF
                      seconds, encountered by a SONET
                      interface in one of the previous 96, individual 15
                      minute, intervals."
              ::= { prtSectionLineIntervalEntry 3 }

          prtSonetIntervalLineAIS OBJECT-TYPE
              SYNTAX  Gauge32
              MAX-ACCESS  read-only
              STATUS  current
              DESCRIPTION
                      "The counter associated with the number of Line
                      AIS seconds, encountered by a SONET
                      interface in one of the previous 96,
                      individual 15 minute, intervals."
              ::= { prtSectionLineIntervalEntry 4 }

          prtSonetIntervalLineFERF OBJECT-TYPE
              SYNTAX  Gauge32
              MAX-ACCESS  read-only
              STATUS  current
              DESCRIPTION
                      "The counter associated with the number of Line
                      FERF seconds, encountered by a SONET
                      interface in one of the previous 96, individual 15
                      minute, intervals."
              ::= { prtSectionLineIntervalEntry 5 }

          prtSonetIntervalSectionBIP OBJECT-TYPE
              SYNTAX  Gauge32
              MAX-ACCESS  read-only
              STATUS  current
              DESCRIPTION
                      "The counter associated with the number of Section
                      BIP errors, encountered by a SONET
                      interface in one of the previous 96, individual 15
                      minute, intervals."
              ::= { prtSectionLineIntervalEntry 6 }

          prtSonetIntervalLineBIP OBJECT-TYPE
              SYNTAX  Gauge32
              MAX-ACCESS  read-only
              STATUS  current
              DESCRIPTION
                      "The counter associated with the number of Line
                      BIP errors, encountered by a SONET
                      interface in one of the previous 96, individual 15
                      minute, intervals."
              ::= { prtSectionLineIntervalEntry 7 }

          prtSonetIntervalLineFEBE OBJECT-TYPE
              SYNTAX  Gauge32
              MAX-ACCESS  read-only
              STATUS  current
              DESCRIPTION
                      "The counter associated with the number of Line
                      FEBE errors, encountered by a SONET
                      interface in one of the previous 96, individual 15
                      minute, intervals."
              ::= { prtSectionLineIntervalEntry 8 }

          prtSonetIntervalUAS OBJECT-TYPE
              SYNTAX  Gauge32
              MAX-ACCESS  read-only
              STATUS  current
              DESCRIPTION
                      "The counter associated with the number of UAS
                      encountered by a SONET
                      interface in one of the previous 96, individual 15
                      minute, intervals."
              ::= { prtSectionLineIntervalEntry 9 }

         prtSonetIntervalSES OBJECT-TYPE
              SYNTAX  Gauge32
              MAX-ACCESS  read-only
              STATUS  current
              DESCRIPTION
                      "The counter associated with the number of SES
                      encountered by a SONET
                      interface in one of the previous 96, individual 15
                      minute, intervals."
              ::= { prtSectionLineIntervalEntry 10 }

          prtSonetIntervalES OBJECT-TYPE
               SYNTAX Gauge32
               MAX-ACCESS  read-only
               STATUS current
               DESCRIPTION
                      "The number of Errored Seconds, encountered  by a
                      SONET interface in one of the previous 96, individual 15
                      minute, intervals."
               ::= { prtSectionLineIntervalEntry 11 }

         prtSonetIntervalStatus OBJECT-TYPE
	          SYNTAX OCTET STRING  (SIZE (4))
              MAX-ACCESS  read-only
              STATUS  current
              DESCRIPTION
                      " The statuses of the current interval:
                        0 - O.K.
                        1 - The link has been switched by a redundancy mechanism.
                        2 - Module is in/out.
                        4 - Empty - card is out."
              ::= { prtSectionLineIntervalEntry 12 }

		 prtSonetIntervalLSV OBJECT-TYPE
              SYNTAX  Gauge32
              MAX-ACCESS  read-only
              STATUS  current
              DESCRIPTION
                      "The counter associated with the number of LSV seconds
                      (Line Symbol Violation), encountered by a SONET interface
                      in one of the previous 96, individual 15 minute, intervals."
              ::= { prtSectionLineIntervalEntry 13 }


  -- The SONET Path Current	Table

          -- The SONET Path Current table contains various statistics being
          -- collected for the current 15 minute interval.

          prtSonetPathCurrentTable OBJECT-TYPE
              SYNTAX  SEQUENCE OF PrtPathCurrentEntry
              MAX-ACCESS  not-accessible
              STATUS  current
              DESCRIPTION
                      "The SONET Path Current table."
              ::= { prtSonetPerfHistory 4 }

          prtPathCurrentEntry OBJECT-TYPE
              SYNTAX  PrtPathCurrentEntry
              MAX-ACCESS  not-accessible
              STATUS  current
              DESCRIPTION
                      "An entry in the SONET Path Current table.
                       ifIndex of the Path SONET layer of type
                       sonetPath(50)."
              INDEX   { ifIndex }
              ::= { prtSonetPathCurrentTable 1 }

          PrtPathCurrentEntry ::=
              SEQUENCE {
                  prtSonetCurrentPathAIS
                      Gauge32,
                  prtSonetCurrentPathFERF
                      Gauge32,
                  prtSonetCurrentLOP
                      Gauge32,
                  prtSonetCurrentSLM
                      Gauge32,
                  prtSonetCurrentLOC
                      Gauge32,
                  prtSonetCurrentPathBIP
                      Gauge32,
                  prtSonetCurrentPathFEBE
                      Gauge32
              }

          prtSonetCurrentPathAIS OBJECT-TYPE
              SYNTAX  Gauge32
              MAX-ACCESS  read-only
              STATUS  current
              DESCRIPTION
                      "The counter associated with the number of Path AIS
                       seconds, encountered by a SONET interface in
                      the current 15 minute interval."
              ::= { prtPathCurrentEntry 1 }

          prtSonetCurrentPathFERF OBJECT-TYPE
              SYNTAX  Gauge32
              MAX-ACCESS  read-only
              STATUS  current
              DESCRIPTION
                      "The counter associated with the number of Path FERF
                       seconds, encountered by a SONET
                       interface in the current 15 minute interval."
              ::= { prtPathCurrentEntry 2 }

          prtSonetCurrentLOP OBJECT-TYPE
              SYNTAX  Gauge32
              MAX-ACCESS  read-only
              STATUS  current
              DESCRIPTION
                      "The counter associated with the number LOP
                      seconds, encountered by a SONET
                      interface in the current 15 minute interval."
              ::= { prtPathCurrentEntry 3 }

          prtSonetCurrentSLM OBJECT-TYPE
              SYNTAX  Gauge32
              MAX-ACCESS  read-only
              STATUS  current
              DESCRIPTION
                      "The counter associated with the number of SLM
                       seconds, encountered by a SONET
                       interface in the current 15 minute interval."
              ::= { prtPathCurrentEntry 4 }

          prtSonetCurrentLOC OBJECT-TYPE
              SYNTAX  Gauge32
              MAX-ACCESS  read-only
              STATUS  current
              DESCRIPTION
                      "The counter associated with the number of LOC
                      seconds, encountered by a SONET
                      interface in the current 15 minute interval."
              ::= { prtPathCurrentEntry 5 }

          prtSonetCurrentPathBIP OBJECT-TYPE
              SYNTAX  Gauge32
              MAX-ACCESS  read-only
              STATUS  current
              DESCRIPTION
                      "The counter associated with the number of Path
                      BIP errors, encountered by a SONET
                      interface in the current 15 minute interval."
              ::= { prtPathCurrentEntry 6 }

          prtSonetCurrentPathFEBE OBJECT-TYPE
              SYNTAX  Gauge32
              MAX-ACCESS  read-only
              STATUS  current
              DESCRIPTION
                      "The counter associated with the number of Path
                      FEBE errors, encountered by a SONET
                      interface in the current 15 minute interval."
              ::= { prtPathCurrentEntry 7 }


          -- The SONET Path interface Interval

          -- The SONET Path Interval Table contains various statistics
          -- collected by the Interface over the previous 24
          -- hours of operation.  The past 24 hours are broken into 96
          -- completed 15 minute intervals.

          prtSonetPathIntervalTable OBJECT-TYPE
              SYNTAX  SEQUENCE OF PrtPathIntervalEntry
              MAX-ACCESS  not-accessible
              STATUS  current
              DESCRIPTION
                      "The Path Interval table."
              ::= { prtSonetPerfHistory 5 }

          prtPathIntervalEntry OBJECT-TYPE
              SYNTAX  PrtPathIntervalEntry
              MAX-ACCESS  not-accessible
              STATUS  current
              DESCRIPTION
                      "An entry in the SONET Path Interval table."
              INDEX   { ifIndex, prtSonetPathIntervalNumber }
              ::= { prtSonetPathIntervalTable 1 }

          PrtPathIntervalEntry ::=
              SEQUENCE {
                  prtSonetPathIntervalNumber
                      Integer32,
                  prtSonetIntervalPathAIS
                      Gauge32,
                  prtSonetIntervalPathFERF
                      Gauge32,
                  prtSonetIntervalLOP
                      Gauge32,
                  prtSonetIntervalSLM
                      Gauge32,
                  prtSonetIntervalLOC
                      Gauge32,
                  prtSonetIntervalPathBIP
                      Gauge32,
                  prtSonetIntervalPathFEBE
                      Gauge32
              }

          prtSonetPathIntervalNumber OBJECT-TYPE
              SYNTAX  Integer32 (1..96)
              MAX-ACCESS  read-only
              STATUS  current
              DESCRIPTION
                      "A number between 1 and 96, where 1 is the most
                      recently completed 15 minute interval and 96 is
                      the least recently completed 15 minutes interval
                      (assuming that all 96 intervals are valid)."
              ::= { prtPathIntervalEntry 1 }

          prtSonetIntervalPathAIS OBJECT-TYPE
              SYNTAX  Gauge32
              MAX-ACCESS  read-only
              STATUS  current
              DESCRIPTION
                      "The counter associated with the number of Path
                      AIS seconds , encountered by a SONET interface in
                      one of the previous 96, individual 15 minute,
                      intervals."
              ::= { prtPathIntervalEntry 2 }

          prtSonetIntervalPathFERF OBJECT-TYPE
              SYNTAX  Gauge32
              MAX-ACCESS  read-only
              STATUS  current
              DESCRIPTION
                      "The counter associated with the number of Path
                      FERF seconds, encountered by a SONET
                      interface in one of the previous 96, individual 15
                      minute, intervals."
              ::= { prtPathIntervalEntry 3 }

          prtSonetIntervalLOP OBJECT-TYPE
              SYNTAX  Gauge32
              MAX-ACCESS  read-only
              STATUS  current
              DESCRIPTION
                      "The counter associated with the number of LOP
                      seconds, encountered by a SONET
                      interface in one of the previous 96,
                      individual 15 minute, intervals."
              ::= { prtPathIntervalEntry 4 }

          prtSonetIntervalSLM OBJECT-TYPE
              SYNTAX  Gauge32
              MAX-ACCESS  read-only
              STATUS  current
              DESCRIPTION
                      "The counter associated with the number of SLM
                      seconds, encountered by a SONET
                      interface in one of the previous 96, individual 15
                      minute, intervals."
              ::= { prtPathIntervalEntry 5 }

          prtSonetIntervalLOC OBJECT-TYPE
              SYNTAX  Gauge32
              MAX-ACCESS  read-only
              STATUS  current
              DESCRIPTION
                      "The counter associated with the number of LOC
                      seconds, encountered by a SONET
                      interface in one of the previous 96, individual 15
                      minute, intervals."
              ::= { prtPathIntervalEntry 6 }

          prtSonetIntervalPathBIP OBJECT-TYPE
              SYNTAX  Gauge32
              MAX-ACCESS  read-only
              STATUS  current
              DESCRIPTION
                      "The counter associated with the number of Path
                      BIP errors, encountered by a SONET
                      interface in one of the previous 96, individual 15
                      minute, intervals."
              ::= { prtPathIntervalEntry 7 }

          prtSonetIntervalPathFEBE OBJECT-TYPE
              SYNTAX  Gauge32
              MAX-ACCESS  read-only
              STATUS  current
              DESCRIPTION
                      "The counter associated with the number of Path
                      FEBE errors, encountered by a SONET
                      interface in one of the previous 96, individual 15
                      minute, intervals."
              ::= { prtPathIntervalEntry 8 }


prtSonetConfig  OBJECT IDENTIFIER  ::=  {sonetInterface 2}

prtSonetGen  	OBJECT IDENTIFIER  ::=  {prtSonetConfig 1}

prtSonetGenTable OBJECT-TYPE
     SYNTAX  SEQUENCE OF PrtSonetGenEntry
     MAX-ACCESS  not-accessible
     STATUS  current
     DESCRIPTION
     "Sonet/SDH general port configuration table."
     ::= { prtSonetGen 1}

prtSonetGenEntry   OBJECT-TYPE
     SYNTAX  PrtSonetGenEntry
     MAX-ACCESS  not-accessible
     STATUS  current
     DESCRIPTION
     " An entry in the Sonet/SDH general port configuration table."
     INDEX { prtSonetGenCnfgIdx, prtSonetGenIdx }
     ::= { prtSonetGenTable 1}

PrtSonetGenEntry ::=
     SEQUENCE {
     prtSonetGenCnfgIdx
     Integer32,
     prtSonetGenIdx
     Integer32,
     prtSonetGenSdThreshold
     INTEGER,
     prtSonetGenEedThreshold
     INTEGER
     }

prtSonetGenCnfgIdx OBJECT-TYPE
     SYNTAX  Integer32 (1..255)
     MAX-ACCESS  read-only
     STATUS  current
     DESCRIPTION
     "This object indicates the Idx of the Config being accessed.
      Idx of 255 relates to the Temporary (Scratch) Config.
      For products that support several configurations, Set can be performed
      only to the Temporary Config (=255). "
     ::= { prtSonetGenEntry 1}

prtSonetGenIdx OBJECT-TYPE
     SYNTAX  Integer32
     MAX-ACCESS  read-only
     STATUS  current
     DESCRIPTION
     "This object indicates a unique  port or interface number.
	 For numbering, see product's spec.
     For some products, the numbering can equal ifIndex."
     ::= { prtSonetGenEntry 2}

prtSonetGenSdThreshold OBJECT-TYPE
     SYNTAX  INTEGER {
     notApplicable(1),
     n3           (3),
     n4           (4),
     n5           (5),
     n6			  (6),
     n7			  (7),
     n8			  (8),
     n9			  (9)
     }
     MAX-ACCESS  read-write
     STATUS  current
     DESCRIPTION
     "SD=Signal Degraded Threshold. Units: [10E-].
	  The threshold is 10E-x relative to the frequency of the data flow.
	  x=3, 4, 5, 6, 7, 8, 9.
      n3= 10E-3
      n4= 10E-4
      n5= 10E-5
      n6= 10E-6
      n7= 10E-7
      n8= 10E-8
      n9= 10E-9  ."
     ::= { prtSonetGenEntry 3 }

prtSonetGenEedThreshold OBJECT-TYPE
     SYNTAX  INTEGER {
     notApplicable(1),
	 n3			  (3),
	 n4			  (4),
	 n5			  (5),
     n6           (6),
     n7           (7),
     n8           (8),
     n9           (9)
     }
     MAX-ACCESS  read-write
     STATUS  current
     DESCRIPTION
     "EED=Excessive Error Defect Threshold. Units: [10E-].
	  The threshold is 10E-x relative to the frequency of the data flow.
	  x=3, 4, 5, 6, 7, 8, 9.
      n3= 10E-3
      n4= 10E-4
      n5= 10E-5
      n6= 10E-6
      n7= 10E-7
      n8= 10E-8
      n9= 10E-9 ."
     ::= { prtSonetGenEntry 4 }


--STM-1 ports

prtSonetStm1  	OBJECT IDENTIFIER  ::=  {prtSonetConfig 2}


prtSonetStm1Table OBJECT-TYPE
     SYNTAX  SEQUENCE OF PrtSonetStm1Entry
     MAX-ACCESS  not-accessible
     STATUS  current
     DESCRIPTION
     "Sonet/SDH STM-1 port configuration table."
     ::= { prtSonetStm1 1}

prtSonetStm1Entry   OBJECT-TYPE
     SYNTAX  PrtSonetStm1Entry
     MAX-ACCESS  not-accessible
     STATUS  current
     DESCRIPTION
     " An entry in the Sonet/SDH STM-1 port configuration table."
     INDEX { prtSonetStm1CnfgIdx, prtSonetStm1Idx }
     ::= { prtSonetStm1Table 1}

PrtSonetStm1Entry ::=
     SEQUENCE {
     prtSonetStm1CnfgIdx
     Integer32,
     prtSonetStm1Idx
     Integer32,
     prtSonetStm1ClockSrc
     INTEGER,
     prtSonetStm1DccMode
     INTEGER,
	 prtSonetStm1RoutingProt
	 INTEGER,
	 prtSonetStm1MngProt
	 INTEGER
     }

prtSonetStm1CnfgIdx OBJECT-TYPE
     SYNTAX  Integer32 (1..255)
     MAX-ACCESS  read-only
     STATUS  current
     DESCRIPTION
     "This object indicates the Idx of the Config being accessed.
      Idx of 255 relates to the Temporary (Scratch) Config.
      For products that support several configurations, Set can be performed
      only to the Temporary Config (=255). "
     ::= { prtSonetStm1Entry 1}

prtSonetStm1Idx OBJECT-TYPE
     SYNTAX  Integer32
     MAX-ACCESS  read-only
     STATUS  current
     DESCRIPTION
     "This object indicates a unique  port or interface number.
	 For numbering, see product's spec.
     For some products, the numbering can equal ifIndex."
     ::= { prtSonetStm1Entry 2}

prtSonetStm1ClockSrc OBJECT-TYPE
     SYNTAX  INTEGER {
     notApplicable(1),
     internal     (2),
     lbt          (3)
     }
     MAX-ACCESS  read-write
     STATUS  current
     DESCRIPTION
     "Clock Source of the STM-1 port.
      lbt = Loop Back Timing."
     ::= { prtSonetStm1Entry 3 }

prtSonetStm1DccMode OBJECT-TYPE
     SYNTAX  INTEGER {
     notApplicable(1),
     none         (2),
     d1ToD3       (3),
     d4ToD12      (4)
     }
     MAX-ACCESS  read-write
     STATUS  current
     DESCRIPTION
     "DCC Mode. DCC=Data Communication Channel.
	  d1ToD3 = D1-D3  bytes are used (RS=Regeneration Section).
	  d4ToD12= D4-D12 bytes are used (MS=Multiplexing Section)."
     ::= { prtSonetStm1Entry 4 }

prtSonetStm1RoutingProt OBJECT-TYPE
     SYNTAX  INTEGER {
      notApplicable (1),
      none          (2),
      proprietary   (3),
	  rip2          (4)
     }
     MAX-ACCESS  read-write
     STATUS  current
     DESCRIPTION
     "Routing Protocol."
     ::= { prtSonetStm1Entry 5 }


prtSonetStm1MngProt OBJECT-TYPE
     SYNTAX  INTEGER {
      notApplicable (1),
      -- none (2)
      proprietary   (3),
      -- rip2  (4)
      ppp           (5),
	  frameRelay    (6)
     }
     MAX-ACCESS  read-write
     STATUS  current
     DESCRIPTION
     "Management Protocol over DCC:  Proprietary, PPP or Frame Relay."
     ::= { prtSonetStm1Entry 6 }


--SONET/SDH VC-4 and VC-12 ports parameters

prtSonetVc  	OBJECT IDENTIFIER  ::=  {prtSonetConfig 3}


prtSonetVcTable OBJECT-TYPE
     SYNTAX  SEQUENCE OF PrtSonetVcEntry
     MAX-ACCESS  not-accessible
     STATUS  current
     DESCRIPTION
     "Sonet/SDH VC port configuration table."
     ::= { prtSonetVc 1}

prtSonetVcEntry   OBJECT-TYPE
     SYNTAX  PrtSonetVcEntry
     MAX-ACCESS  not-accessible
     STATUS  current
     DESCRIPTION
     " An entry in the Sonet/SDH VC port configuration table."
     INDEX { prtSonetVcCnfgIdx, prtSonetVcIdx }
     ::= { prtSonetVcTable 1}

PrtSonetVcEntry ::=
     SEQUENCE {
     prtSonetVcCnfgIdx
     Integer32,
     prtSonetVcIdx
     Integer32,
     prtSonetVcJTxPathTraceEnable
     INTEGER,
     prtSonetVcJRxPathTraceEnable
     INTEGER,
	 prtSonetVcJPathTrace
	 DisplayString,
	 prtSonetVcConnect
	 INTEGER
     }

prtSonetVcCnfgIdx OBJECT-TYPE
     SYNTAX  Integer32 (1..255)
     MAX-ACCESS  read-only
     STATUS  current
     DESCRIPTION
     "This object indicates the Idx of the Config being accessed.
      Idx of 255 relates to the Temporary (Scratch) Config.
      For products that support several configurations, Set can be performed
      only to the Temporary Config (=255). "
     ::= { prtSonetVcEntry 1}

prtSonetVcIdx OBJECT-TYPE
     SYNTAX  Integer32
     MAX-ACCESS  read-only
     STATUS  current
     DESCRIPTION
     "This object indicates a unique  port or interface number.
	 For numbering, see product's spec.
     For some products, the numbering can equal ifIndex."
     ::= { prtSonetVcEntry 2}

prtSonetVcJTxPathTraceEnable OBJECT-TYPE
     SYNTAX  INTEGER {
     notApplicable(1),
     disable      (2),
	 enable       (3)
     }
     MAX-ACCESS  read-write
     STATUS  current
     DESCRIPTION
     "Enable/Disable Transmitting Jy Path Trace. y=1, 2:
      J1 - for VC-4  layer
      J2 - for VC-12 layer."
     ::= { prtSonetVcEntry 3 }

prtSonetVcJRxPathTraceEnable OBJECT-TYPE
     SYNTAX  INTEGER {
     notApplicable(1),
     disable      (2),
	 enable       (3)
     }
     MAX-ACCESS  read-write
     STATUS  current
     DESCRIPTION
     "Enable/Disable checking Jy Path Trace. y=1, 2:
      J1 - for VC-4  layer
      J2 - for VC-12 layer."
     ::= { prtSonetVcEntry 4 }

prtSonetVcJPathTrace OBJECT-TYPE
     SYNTAX  DisplayString (SIZE(0..16))
     MAX-ACCESS  read-write
     STATUS  current
     DESCRIPTION
     "Jy Path Trace. y=1, 2:
      J1 - for VC-4  layer
      J2 - for VC-12 layer.
      This object is applicable only if one of the previous 2 objects is 'enable'."
     ::= { prtSonetVcEntry 5 }

prtSonetVcConnect  OBJECT-TYPE
      SYNTAX  INTEGER
      {
      notApplicable (1),
	  no (2),
	  yes (3)
      }
      MAX-ACCESS  read-write
      STATUS  current
      DESCRIPTION
      "Connect VCn (n - 11,12,2,3,4) port (yes/no)."
     ::= { prtSonetVcEntry 6 }


--TU-12 (within VC-4) Connect Table

prtSonetTuTable  OBJECT-TYPE
     SYNTAX SEQUENCE OF PrtSonetTuEntry
     MAX-ACCESS not-accessible
     STATUS  current
     DESCRIPTION
      "The write operation into the Table's Objects is valid only
       for the TmpCnfg entry (Scratch)."
  ::= { prtSonetVc 2}

prtSonetTuEntry OBJECT-TYPE
      SYNTAX PrtSonetTuEntry
      MAX-ACCESS not-accessible
      STATUS current
	DESCRIPTION  "An entry in table."
	INDEX {prtSonetTuCnfgIdx, prtSonetTuPrtIdx, prtSonetTuIdx, prtSonetTuConPrtIdx }
      ::= { prtSonetTuTable 1}

PrtSonetTuEntry ::=
      SEQUENCE {
      prtSonetTuCnfgIdx        Integer32,
      prtSonetTuPrtIdx         Integer32,
      prtSonetTuIdx            Integer32,
      prtSonetTuConPrtIdx      Integer32,
      prtSonetTuType           INTEGER,
      prtSonetTuMode           INTEGER,
	  prtSonetTuRowStatus      RowStatus
      }

prtSonetTuCnfgIdx OBJECT-TYPE
      SYNTAX  Integer32  (1..255)
      MAX-ACCESS  read-only
      STATUS  current
      DESCRIPTION
      "This object indicates the Idx of the Config being accessed.
      Idx of 255 relates to the Temporary (Scratch) Config.
      For products that support several configurations, Set can be performed
      only to the Temporary Config (=255). "
      ::= { prtSonetTuEntry 1}

prtSonetTuPrtIdx OBJECT-TYPE
      SYNTAX  Integer32
      MAX-ACCESS  read-only
      STATUS  current
      DESCRIPTION
      "This object indicates a unique  port or interface number.
	  For port numbering, see product's spec.
      For some products, the numbering can equal ifIndex."
      ::= { prtSonetTuEntry 2}

prtSonetTuIdx OBJECT-TYPE
      SYNTAX  Integer32
      MAX-ACCESS  read-only
      STATUS  current
      DESCRIPTION
      "This object indicates a unique TU (Tributary Unit) within VC-4.
	   The valid TUs are 1..63."
      ::= { prtSonetTuEntry 3}

prtSonetTuConPrtIdx OBJECT-TYPE
      SYNTAX  Integer32
      MAX-ACCESS  read-only
      STATUS  current
      DESCRIPTION
      "This object indicates the connected port, when prtSonetTuType=connect.
	   For port numbering, see product's spec.
       For some products, the numbering can equal ifIndex.
       notApplicable - will be indicated as 100."
      ::= {prtSonetTuEntry 4}

prtSonetTuType  OBJECT-TYPE
      SYNTAX  INTEGER
      {
      connect (2)
      }
      MAX-ACCESS  read-create
      STATUS  current
      DESCRIPTION
      "The type of TU (Tributary Unit).
       connect - connected to one of the E1 ports.
       TUs that are not connected will not exist in this table."
      ::= { prtSonetTuEntry 5}

prtSonetTuMode  OBJECT-TYPE
      SYNTAX  INTEGER
      {
      notApplicable(1),
      addAndDrop   (2),
      add          (3)
      }
      MAX-ACCESS  read-create
      STATUS  current
      DESCRIPTION
      "TU Mode of connection.
       addAndDrop    - Add & Drop
       add           - Add (TU receives from the E1 ports)."
      ::= { prtSonetTuEntry 6}

prtSonetTuRowStatus OBJECT-TYPE
      SYNTAX RowStatus
      MAX-ACCESS read-create
      STATUS current
      DESCRIPTION
      "Creation/Deletion of rows in the table."
      ::= { prtSonetTuEntry 7}


-- SDH Cross Connect Table
-- May be used also for SONET

prtSonetXConnect  OBJECT IDENTIFIER  ::= {sonetInterface 3}

prtSonetXConnectTable  OBJECT-TYPE
     SYNTAX SEQUENCE OF PrtSonetXConnectEntry
     MAX-ACCESS not-accessible
     STATUS  current
     DESCRIPTION
      "The write operation into the Table's Objects is valid only
       for the TmpCnfg entry (Scratch)."
     ::= { prtSonetXConnect 1}

prtSonetXConnectEntry OBJECT-TYPE
      SYNTAX PrtSonetXConnectEntry
      MAX-ACCESS not-accessible
      STATUS current
      DESCRIPTION  "An entry in table."
	  INDEX  {
	         prtSonetXConnectCnfgIdx,
	         prtSonetXConnectPrtIdx,
	         prtSonetXConnectConPrtIdx,
	         prtSonetXConnectAUGIdx,
	         prtSonetXConnectTUG3Idx,
	         prtSonetXConnectTUG2Idx,
	         prtSonetXConnectTUnIdx
	         }
	      ::= { prtSonetXConnectTable 1}

PrtSonetXConnectEntry ::=
      SEQUENCE {
      prtSonetXConnectCnfgIdx        Integer32,
      prtSonetXConnectPrtIdx         Integer32,
	  prtSonetXConnectConPrtIdx      Integer32,
      prtSonetXConnectAUGIdx         Integer32,
      prtSonetXConnectTUG3Idx        Integer32,
      prtSonetXConnectTUG2Idx        Integer32,
      prtSonetXConnectTUnIdx         Integer32,
	  prtSonetXConnectRowStatus      RowStatus,
	  prtSonetXConnectDirection      INTEGER,
      prtSonetXConnectTuNumber       INTEGER
      }

prtSonetXConnectCnfgIdx OBJECT-TYPE
      SYNTAX  Integer32  (1..255)
      MAX-ACCESS  read-only
      STATUS  current
      DESCRIPTION
      "This object indicates the Idx of the Config being accessed.
       Idx of 255 relates to the Temporary (Scratch) Config.
       For products that support several configurations, Set can be performed
       only to the Temporary Config (=255). "
      ::= { prtSonetXConnectEntry 1}

prtSonetXConnectPrtIdx OBJECT-TYPE
      SYNTAX  Integer32
      MAX-ACCESS  read-only
      STATUS  current
      DESCRIPTION
      "This object indicates a unique  port or interface number.
	   For port numbering, see product's spec.
       For some products, the numbering can equal ifIndex."
      ::= { prtSonetXConnectEntry 2}

prtSonetXConnectConPrtIdx OBJECT-TYPE
      SYNTAX  Integer32
      MAX-ACCESS  read-only
      STATUS  current
      DESCRIPTION
      "This object indicates the connected port.
	   For port numbering, see product's spec.
       For some products, the numbering can equal ifIndex.
       notApplicable - will be indicated as 255."
      ::= {prtSonetXConnectEntry 3}


prtSonetXConnectAUGIdx OBJECT-TYPE
      SYNTAX  Integer32
      MAX-ACCESS  read-only
      STATUS  current
      DESCRIPTION
      "This object indicates an  AUG (Administrative Unit Group) within STM-N.
	   The valid AUGs values are:
	   1 for STM-1
	   1...4 for STM-4,
	   1..16 for STM-16  and
	   1..64 for STM-64  (STM-64)
	   255 designates NA."
      ::= { prtSonetXConnectEntry 4}

prtSonetXConnectTUG3Idx OBJECT-TYPE
      SYNTAX  Integer32
      MAX-ACCESS  read-only
      STATUS  current
      DESCRIPTION
      "This object indicates a  TUG-3 (Tributary Unit Group 3) within VC-4.
	   The valid TUG3s are values are 1..3. and 255 which designates NA "
      ::= { prtSonetXConnectEntry 5}

prtSonetXConnectTUG2Idx OBJECT-TYPE
      SYNTAX  Integer32
      MAX-ACCESS  read-only
      STATUS  current
      DESCRIPTION
      "This object indicates a TUG2 (Tributary Unit Group 2 ) within VC-3.
	   The valid TUG2's values  are 1..7 and 255 which designates NA "
      ::= { prtSonetXConnectEntry 6}

prtSonetXConnectTUnIdx OBJECT-TYPE
      SYNTAX  Integer32
      MAX-ACCESS  read-only
      STATUS  current
      DESCRIPTION
      "This object indicates a TUn within TUG-2 or TUG-3
       (Tributary Unit n, where  n is 2, 12 or 11 within TUG-2,
       or 3 within TUG-3)
       valid values are
	   1 for TU-2
	   1 for TU-3
	   1..4  for TU-11
	   1..3  for TU-12
	   255 designates NA"
	   ::= { prtSonetXConnectEntry 7}


prtSonetXConnectRowStatus OBJECT-TYPE
      SYNTAX RowStatus
      MAX-ACCESS read-create
      STATUS current
      DESCRIPTION
      "Creation/Deletion of rows in the table."
      ::= { prtSonetXConnectEntry 8}


prtSonetXConnectDirection  OBJECT-TYPE
      SYNTAX  INTEGER
      {
      notApplicable(1),
      rx   (2),
      tx   (3),
	  both (4)
      }
      MAX-ACCESS  read-create
      STATUS  current
      DESCRIPTION
      "TU direction of connection.
      rx=Drop
      tx=Add
      both = Add & Drop "
      ::= { prtSonetXConnectEntry 9}

prtSonetXConnectTuNumber OBJECT-TYPE
      SYNTAX  INTEGER
      {
      notApplicable (1),
      tu2			(2),
      tu3           (3),
      tu11          (4),
	  tu12          (5)
      }
      MAX-ACCESS  read-create
      STATUS  current
      DESCRIPTION
       "This object indicates which TU is used in prtSonetXConnectTUnIdx "
      ::= { prtSonetXConnectEntry 10}

-- END
--
-- file :v:\doc\rdv\mib\ver480\atm\NtePrtConfg.txt
--
-- *************************
-- file  : NtePrtConfg.txt
--
--Version:   1.0
--Date:      12.11.97
--By:        Ilana Schvetz
--File:      v:\doc\rdv\mib\ver480\atm\NtePrtConfg.txt

--Last Update: 30-Sep-01 by Ilana Schvetz
-- Copyright 1997 RAD Data Communications, Ltd.
-- All Rights Reserved.

atmNte              OBJECT IDENTIFIER ::= { radAtm 3 }
atmNtePrt		    OBJECT IDENTIFIER ::= { atmNte 2 }
atmNtePrtConfig		OBJECT IDENTIFIER ::= { atmNtePrt 1 }

atmNteEvents OBJECT-IDENTITY
     STATUS  current
     DESCRIPTION
     "The events for RAD ATM products."
     ::= { atmNte 0 }

atmNteConfIfTable OBJECT-TYPE
              SYNTAX  SEQUENCE OF AtmNteConfIfEntry
              MAX-ACCESS  not-accessible
              STATUS  current
              DESCRIPTION
              "The Physical interface configuration table."
              ::= { atmNtePrtConfig 1 }

          atmNteConfIfEntry OBJECT-TYPE
              SYNTAX  AtmNteConfIfEntry
              MAX-ACCESS  not-accessible
              STATUS  current
              DESCRIPTION
              "An entry in the Physical interface configuration table.
               The ifIndex is of the lowest physical layer."
              INDEX   { ifIndex}
              ::= { atmNteConfIfTable 1 }

          AtmNteConfIfEntry ::=
              SEQUENCE {
				atmConfIfTransmitClk
				      INTEGER,
				atmConfIfLoopback
				      INTEGER,
				atmConfIfFrameType
				      INTEGER,
				atmConfIfCardType
				      INTEGER,
				atmConfAtmIfVpiVciLimit
				      INTEGER,
				atmConfIfHwFeatures
				      INTEGER,
				atmConfIfOutputRate
				      Integer32,
				atmConfIfInputRate
				      Integer32,
				atmConfAlarmForwarding
				      INTEGER
                 }

          atmConfIfTransmitClk OBJECT-TYPE
              SYNTAX  INTEGER { internal(2), external(3), loopback(4), adaptive(5) }
              MAX-ACCESS  read-write
              STATUS  current
              DESCRIPTION
              "The transmit clock of the port."
              ::= { atmNteConfIfEntry 1 }

          atmConfIfLoopback OBJECT-TYPE
              SYNTAX  INTEGER { internal(2), external(3), disable(4) }
              MAX-ACCESS  read-write
              STATUS  current
              DESCRIPTION
              "Interface Loopback."
              ::= { atmNteConfIfEntry 2 }

          atmConfIfFrameType OBJECT-TYPE
              SYNTAX  INTEGER {
              other        (1),
              sonet        (2),
			  sdh          (3),
			  direct       (4),
			  plcpInternal (5),
			  plcpExternal (6),
			  e3           (7),
			  ethCrcTrans  (8),
			  ethCrcNotTrans          (9),
	          directNoScrmbling       (10),
	          plcpInternalNoScrmbling (11),
	          plcpExternalNoScrmbling (12)
	          }
              MAX-ACCESS  read-write
              STATUS  current
              DESCRIPTION
              "The frame type. Valid values for a 155M interface:
               sonet(2), sdh(3). Valid values for a T3 interface:
               direct(4), plcpInternal(5), plcpExternal(6),
               directNoScrmbling(10), plcpInternalNoScrmbling(11),
               plcpExternalNoScrmbling(12). Valid values for Ethernet
               interface: ethCrcTrans (8), ethCrcNotTrans(9).
               (DS1 interfaces frame type is specified in the DSX1 mib)."
              ::= { atmNteConfIfEntry 3 }

          atmConfIfCardType OBJECT-TYPE
              SYNTAX  INTEGER {
		      notApplicable(1),
		      sc13m-155(2),
		      st13s-155(3),
		      st13l-155(4),
		      utp-155(5),
		      cx-bnc-155(6),
		      e3(7),
		      t3(8),
			  e1(9),
		      e1-ltu(10),
		      fc13l-155(11),
		      fc13lh-155(12),
		      fc15lh-155(13),
		      fc13l-e3(14),
	          fc13lh-e3(15),
		      fc15lh-e3(16),
		      fc13l-t3(17),
		      fc13lh-t3(18),
		      fc15lh-t3(19)
              }
         	  MAX-ACCESS  read-only
         	  STATUS  deprecated
         	  DESCRIPTION
         	          "The card type."
         	  ::= { atmNteConfIfEntry 4 }

         	  atmConfAtmIfVpiVciLimit OBJECT-TYPE
         	  SYNTAX  INTEGER {
         	  bits15(2),
			  bits17(3)
			   }
         	  MAX-ACCESS  read-only
         	  STATUS  current
         	  DESCRIPTION
         	  "The limit on the sum of the VPI+VCI bits for this interface."
         	  ::= { atmNteConfIfEntry 5 }

              atmConfIfHwFeatures  OBJECT-TYPE
              SYNTAX  INTEGER {
              disable(1),
			  enable(2)
			  }
              MAX-ACCESS  read-write
              STATUS  current
              DESCRIPTION
              "HW features command."
              ::= { atmNteConfIfEntry 6 }

              atmConfIfOutputRate  OBJECT-TYPE
              SYNTAX  Integer32
              MAX-ACCESS  read-write
              STATUS  current
              DESCRIPTION
              "This parameter indicates the output rate in cells/sec, which is
              supported per port. Successfully setting this parameter
              is dependent on all other ports values calculations,
              which are described in the NMS SRS."
              ::= { atmNteConfIfEntry 7 }

              atmConfIfInputRate  OBJECT-TYPE
              SYNTAX  Integer32
              MAX-ACCESS  read-write
              STATUS  current
              DESCRIPTION
              "This parameter indicates the input rate in cells/sec, which is
              supported per port. Successfully setting this parameter
              is dependent on all other ports values calculations,
              which are described in the NMS SRS."
              ::= { atmNteConfIfEntry 8 }

          atmConfAlarmForwarding OBJECT-TYPE
              SYNTAX  INTEGER { disable(2), enable(3) }
              MAX-ACCESS  read-write
              STATUS  current
              DESCRIPTION
              "Enables Path AIS Alarm forwarding upon a failure detection. The
			  following might be considered as a failure: LOS, LOF, LOC, SLM,
			  LOP, Path AIS and Line AIS.

              disable(2) -  will not forward an alarm upon a failure on this port.

              enable(3) - will forward an alarm upon a failure on this port."
              ::= { atmNteConfIfEntry 9 }


atmNteAlarmIfTable OBJECT-TYPE
              SYNTAX  SEQUENCE OF AtmNteAlarmIfEntry
              MAX-ACCESS  not-accessible
              STATUS  current
              DESCRIPTION
                      "The interface Alarm table."
              ::= { atmNtePrtConfig 2 }

          atmNteAlarmIfEntry OBJECT-TYPE
              SYNTAX  AtmNteAlarmIfEntry
              MAX-ACCESS  not-accessible
              STATUS  current
              DESCRIPTION
                      "An entry in the interface Alarm table."
              INDEX   { ifIndex}
              ::= { atmNteAlarmIfTable 1 }

          AtmNteAlarmIfEntry ::=
              SEQUENCE {
				atmInterfaceActiveAlarms
				      Integer32,
				atmThresholdSectionBIP
				      Integer32,
				atmThresholdLineBIP
				      Integer32,
				atmThresholdLineFEBE
				      Integer32,
				atmThresholdPathBIP
				      Integer32,
				atmThresholdPathFEBE
				      Integer32,
				atmThresholdErroredCells
				      Integer32,
				atmThresholdLostCells
				      Integer32,
				atmThresholdMisinsertedCells
				      Integer32,
			    atmInterfaceAlarmStatus
				      INTEGER,
                atmInterfaceMaskAlarms
				      Integer32
              }

          atmInterfaceActiveAlarms OBJECT-TYPE
              SYNTAX  Integer32
              MAX-ACCESS  read-only
              STATUS  current
              DESCRIPTION
                      "A Bit String of the active alarms on this interface.
					   An up bit (1) means there is an active alarm of this
					   type. A down bit (0) means there is no such alarm.
                       The meaning of the bits is as follows:
                       1 - LOS
                       2 - LOF
                       3 - Line AIS (SONET)/ PLCP LOF (DS3)
                       4 - LOP
                       5 - Path AIS
                       6 - SLM
                       7 - LCD
                       8 - Line RDI  (SONET)/ PLCP Yellow (DS3)
                       9 - Path RDI  (SONET)/ RDI (DS3)
					   10 - Section BIP (SONET)/ P1/P2 (DS3) > Threshold
					   11 -	Line BIP (SONET)/ PLCP BIP (DS3) > Threshold
					   12 - Line FEBE (SONET)/ PLCP FEBE (DS3) > Threshold
					   13 - Path BIP > Threshold
					   14 - Path FEBE > Threshold
                       "
              ::= { atmNteAlarmIfEntry 1 }

          atmThresholdSectionBIP OBJECT-TYPE
              SYNTAX  Integer32
              MAX-ACCESS  read-write
              STATUS  current
              DESCRIPTION
                      "When Section BIPs are greater than this threshold,
	an active alarm is raised. N/A for ds3/e3 interface."
              ::= { atmNteAlarmIfEntry 2 }

          atmThresholdLineBIP OBJECT-TYPE
              SYNTAX  Integer32
              MAX-ACCESS  read-write
              STATUS  current
              DESCRIPTION
                      "When Line BIPs are greater than this threshold,
	an active alarm is raised. N/A for ds3/e3 interface."
              ::= { atmNteAlarmIfEntry 3 }

          atmThresholdLineFEBE OBJECT-TYPE
              SYNTAX  Integer32
              MAX-ACCESS  read-write
              STATUS  current
              DESCRIPTION
                      "When Line FEBEs are greater than this threshold,
	an active alarm is raised. N/A for ds3/e3 interface."
              ::= { atmNteAlarmIfEntry 4 }

          atmThresholdPathBIP OBJECT-TYPE
              SYNTAX  Integer32
              MAX-ACCESS  read-write
              STATUS  current
              DESCRIPTION
                      "When Path BIPs are greater than this threshold,
					   an active alarm is raised."
              ::= { atmNteAlarmIfEntry 5 }

          atmThresholdPathFEBE OBJECT-TYPE
              SYNTAX  Integer32
              MAX-ACCESS  read-write
              STATUS  current
              DESCRIPTION
                      "When Path FEBEs are greater than this threshold,
					   an active alarm is raised."
              ::= { atmNteAlarmIfEntry 6 }

          atmThresholdErroredCells OBJECT-TYPE
              SYNTAX  Integer32
              MAX-ACCESS  read-write
              STATUS  current
              DESCRIPTION
                      "When Errored Cells are greater than this threshold,
					   an active alarm is raised."
              ::= { atmNteAlarmIfEntry 7 }

          atmThresholdLostCells OBJECT-TYPE
              SYNTAX  Integer32
              MAX-ACCESS  read-write
              STATUS  current
              DESCRIPTION
                      "When Lost Cells are greater than this threshold,
					   an active alarm is raised."
              ::= { atmNteAlarmIfEntry 8 }

          atmThresholdMisinsertedCells OBJECT-TYPE
              SYNTAX  Integer32
              MAX-ACCESS  read-write
              STATUS  current
              DESCRIPTION
                      "When Misinserted Cells are greater than this threshold,
					   an active alarm is raised."
              ::= { atmNteAlarmIfEntry 9 }



          atmInterfaceAlarmStatus OBJECT-TYPE
              SYNTAX  INTEGER { off(2),
			                    on(3) }
              MAX-ACCESS  read-only
              STATUS  current
              DESCRIPTION
                      "The variable is on(3) when there is any active alarm
                       on this interface."
              ::= { atmNteAlarmIfEntry 10 }

          atmInterfaceMaskAlarms OBJECT-TYPE
              SYNTAX  Integer32
              MAX-ACCESS  read-write
              STATUS  current
              DESCRIPTION
                      "A Bit String of alarms mask on this interface.
					   An up bit (1) means that the respective alarm is masked.
					   A down bit (0) means no mask.
                       The mask is supported for the following alarms:
                       1 - LOS
                       "
              ::= { atmNteAlarmIfEntry 11 }


          atmNteConfVpTable OBJECT-TYPE
              SYNTAX  SEQUENCE OF AtmNteConfVpEntry
              MAX-ACCESS  not-accessible
              STATUS  current
              DESCRIPTION
                      "The ATM VP configuration table.
                       The table is an extension to the atmVplTable of
                       RFC-1695."
              ::= { atmNtePrtConfig 3 }

          atmNteConfVpEntry OBJECT-TYPE
              SYNTAX  AtmNteConfVpEntry
              MAX-ACCESS  not-accessible
              STATUS  current
              DESCRIPTION
                      "An entry in the ATM VP configuration table.
                       ifIndex of the ATM layer."
              INDEX   { ifIndex, atmVplVpi }
              ::= { atmNteConfVpTable 1 }

          AtmNteConfVpEntry ::=
              SEQUENCE {
			atmConfVpPolicing            INTEGER,
			atmConfVpCCAdminStatus       INTEGER,
			atmConfVpLoopbackAdminStatus INTEGER,
			atmConfVpLoopbackSinkAddress OCTET STRING,
			atmConfVpCongestionControl   OCTET STRING,
			atmConfVpCCDirection         INTEGER,
            atmConfVpCreationTime        DateAndTime,
            atmConfVpOamSupport          INTEGER,
            atmConfVpCCOperStatus        INTEGER,
			atmConfVpLoopbackTraffic     INTEGER,
            atmConfVpLoopbackFailureInd	 INTEGER,
            atmConfVpLoopbackFailureThreshold	 Integer32,
			atmConfVpOamDirection         INTEGER
           }

 atmConfVpPolicing OBJECT-TYPE
              SYNTAX  INTEGER {
                 none(1),
                 police(2),
                 monitor(3),
                 shaping(4),
                 policingAndShaping(5)
              }
              MAX-ACCESS  read-write
              STATUS  current
              DESCRIPTION
                      "Policing method desired for this VPL."
              ::= { atmNteConfVpEntry 1 }

        atmConfVpCCAdminStatus OBJECT-TYPE
             SYNTAX INTEGER {
		            up    (2),
            		down  (3),
		            source(4),      -- agent send Oam CC cells
		            sink  (5),      -- agent check received Oam CC cells
                    listenToActivationCells (6),
                    originateActivationCells(7)
                            }
             MAX-ACCESS read-write
             STATUS current
             DESCRIPTION
                     	"up(2) - Activate Continuity Check (CC).
                      	down(3) - Deactivate CC.
		                source(4)      - Activate OAM CC(Continuity Check) of local agent
                        			( start sending Oam cells to the remote side ).
      		            sink(5)          - Activate CC of remote agent ( start receiving Oam cells from
      		             				remote 	side ).
                     listenToActivationCells (6) - Passive listener till gets an activation request
                     originateActivationCells(7) - Sands Activation cell according to atmConfVcCCDirection."
             ::= {atmNteConfVpEntry 2}

	atmConfVpLoopbackAdminStatus OBJECT-TYPE
                    SYNTAX INTEGER {
		            up(2),
		            down(3),
		            llid(4),
		            segment(5),
		            endToEnd(6),
		            segmentLlid(7),
		            endToEndLlid(8)
	                }
             		MAX-ACCESS read-write
             		STATUS current
             		DESCRIPTION
                        "up(2) - Start loopback OAM cells.
                         down(3) - Stop sending loopback OAM cells.

                         For ace2002:
                         up(2)   - Transmitting LB cells with llid all ones
                                   (i.e. FFFF..FF)
                         down(3) - Not transmitting LB cells.
                         llid(4) - Transmitting LB cells with llid indicated
                                    in the address field.
                         segment(5) - Transmitting Segment LB cells with llid
                                       all ones.
                         endToEnd(6) - Transmitting End to End LB cells with llid
                                        all ones.
                         segmentLlid(7) - Transmitting Segment LB cells with
                                           llid indicated in the address field.
                         endToEndLlid(8) - Transmitting LB cells with llid
                                            indicated in the address field.

                         This parameter value might be in conflict with
                         atmConfVpOamSupport value, since this parameter is for LB,
                         while atmConfVpOamSupport is for any other OAM cells."
             ::= {atmNteConfVpEntry 3}

	atmConfVpLoopbackSinkAddress OBJECT-TYPE
             		SYNTAX OCTET STRING  (SIZE(0..20))
             		MAX-ACCESS read-write
             		STATUS current
             		DESCRIPTION
                    	 "Destination address.
                    	 For ace101: 2 bytes are used.
                    	 For ace2002: 16 bytes are used."
             ::= {atmNteConfVpEntry 4}

	atmConfVpCongestionControl OBJECT-TYPE
             		SYNTAX OCTET STRING
             		MAX-ACCESS read-write
             		STATUS current
             		DESCRIPTION
                    	 "Each bit indicates a selection of one option
                               as the following description.  All combinations
                               are possible and legal.
                               The codes are:
                               1 - EPD
                               2 - CLP
                               4 - EFCI"
             ::= {atmNteConfVpEntry 5}

     atmConfVpCCDirection OBJECT-TYPE
             SYNTAX  INTEGER {
		            both  (2),
		            source(4),
		            sink  (5)
                            }
             MAX-ACCESS read-write
             STATUS current
             DESCRIPTION
                     	"both(2) - Agent send OAM CC cells and check received OAM CC cells
                        source(4)- Agent send OAM CC cells.
      		            sink(5)  - Agent checks received OAM CC cells."
             ::= {atmNteConfVpEntry 6}

     atmConfVpCreationTime OBJECT-TYPE
         SYNTAX   DateAndTime
         MAX-ACCESS   read-only
         STATUS   current
         DESCRIPTION
            "A date-time in which the VP was created."
         ::= { atmNteConfVpEntry 7 }

     atmConfVpOamSupport OBJECT-TYPE
               SYNTAX  INTEGER {
                          intermediate(1),
                          segmentTermination(2),
                          endToEndTermination(3)
                      }
               MAX-ACCESS  read-write
               STATUS  current
               DESCRIPTION
               "OAM support  mode, which determines the device location
                in a segment wise."
               ::= { atmNteConfVpEntry 8 }


	atmConfVpCCOperStatus OBJECT-TYPE
             SYNTAX INTEGER {
		             initial (1),
		             source(4),
		             sink  (5),
					 both  (8),
		 			 timeout (9),
				     denied (10),
					 conflict (11),
					 manual (12)
                            }
             MAX-ACCESS read-only
             STATUS current
             DESCRIPTION
                     	"
		                initial(1) - The CC activation process is not started.
		                source(4) - Agent sends OAM CC cells.
      		            sink(5)   - Agent checks received OAM CC cells.
						both (8) - OAM CC of local and remote agents activation.
		                timeout (9) - Timeout occured on receiving answer from
                                      the remote agent.
		                denied  (10) - CC activation process rejected by remote agent.
		                conflict (11) - local and remote sides requested activation
                                      simultaneously.
				        manual (12) - OAM CC of local agent activated manually.
                        "
             ::= {atmNteConfVpEntry 9}

	atmConfVpLoopbackTraffic OBJECT-TYPE
             		SYNTAX INTEGER { off(2), on(3) }
             		MAX-ACCESS read-write
             		STATUS current
             		DESCRIPTION
                    	 "This parameter has both command and status meanings:
                    	 off(2) - Set to 'Off' will Stop traffic loop. Getting this
                    	          value means that the loop is not running.
                      	 on (3) - Set to 'On' will start traffic loop. Getting
                      	          this value means that the loop is currently running."
             ::= {atmNteConfVpEntry 10}

	atmConfVpLoopbackFailureInd OBJECT-TYPE
             		SYNTAX INTEGER {
             		disabled(2),
             		segmentAis(3),
             		segmentRdi(4),
             		segmentAisAndRdi(5),
             		endToEndAis(6),
             		endToEndRdi(7),
             		endToEndAisAndRdi(8)
             		}
             		MAX-ACCESS read-write
             		STATUS current
             		DESCRIPTION
    "This object allows user to define the Indication that will be created upon
     a LB cell failure.
     disabled(2) - no indication will be created.
     segmentAis(3) - will cause Tx of a segment AIS.
     segmentRdi(4) - will cause Tx of a segment RDI.
     segmentAisAndRdi(5) - will cause Tx of a segment AIS & RDI.
     endToEndAis(6) - will cause Tx of an End to End AIS.
     endToEndRdi(7)	- will cause Tx of an End to End RDI.
     endToEndAisAndRdi(8) - will cause Tx of an End to End AIS & RDI.
     Default: disabled(2)."
             ::= {atmNteConfVpEntry 11}

	atmConfVpLoopbackFailureThreshold OBJECT-TYPE
             		SYNTAX Integer32
             		MAX-ACCESS read-write
             		STATUS current
             		DESCRIPTION
    "The number of the LB failures before starting transmission of the
    Indication defined by atmConfVcLoopbackFailureInd.
    Range: 1..16. Default: 1."
             ::= {atmNteConfVpEntry 12}

     atmConfVpOamDirection OBJECT-TYPE
             SYNTAX  INTEGER {
		            notApplicable  (1),
		            downStream     (2),
		            upStream       (3)
                            }
             MAX-ACCESS read-write
             STATUS current
             DESCRIPTION
     "The direction of OAM cell insertion.
	 downStream(2) - The OAM cell will be inserted in downStream.
	 upStream(3)   - The OAM cell will be inserted in upStream."
             ::= {atmNteConfVpEntry 13}


--Alarm Table
          atmNteAlarmVpTable OBJECT-TYPE
              SYNTAX  SEQUENCE OF AtmNteAlarmVpEntry
              MAX-ACCESS  not-accessible
              STATUS  current
              DESCRIPTION
                      "The ATM VP Alarm table."
              ::= { atmNtePrtConfig 5 }

          atmNteAlarmVpEntry OBJECT-TYPE
              SYNTAX  AtmNteAlarmVpEntry
              MAX-ACCESS  not-accessible
              STATUS  current
              DESCRIPTION
                      "An entry in the ATM VP Alarm table.
                       ifIndex of the ATM layer."
              INDEX   { ifIndex, atmNteVpAlarmVpi}
              ::= { atmNteAlarmVpTable 1 }

          AtmNteAlarmVpEntry ::=
              SEQUENCE {
			    atmNteVpAlarmVpi
				      Integer32,
			    atmNteVpActiveAlarms
				      Integer32
              }

          atmNteVpAlarmVpi OBJECT-TYPE
              SYNTAX  Integer32
              MAX-ACCESS  read-only
              STATUS  current
              DESCRIPTION
                      "The VPI on which there is an active alarm."
              ::= { atmNteAlarmVpEntry 1 }

          atmNteVpActiveAlarms OBJECT-TYPE
              SYNTAX  Integer32
              MAX-ACCESS  read-only
              STATUS  current
              DESCRIPTION
                      "A Bit String of the active alarms on this VP.
					   An up bit (1) means there is an active alarm of this
					   type. A down bit (0) means there is no such alarm.
                       The meaning of the bits is as follows:
                       1 -	VP AIS
                       2 -	VP Loss Of Continuity
					   3 -  VP RDI Reception
					   4 -	VP Errored Cells > Threshold
					   5 -	VP Lost Cells > Threshold
					   6 -	VP Misinserted Cells > Threshold
                       "
              ::= { atmNteAlarmVpEntry 2 }

          atmNteAlarmVcTable OBJECT-TYPE
              SYNTAX  SEQUENCE OF AtmNteAlarmVcEntry
              MAX-ACCESS  not-accessible
              STATUS  current
              DESCRIPTION
                      "The ATM VC Alarm table."
              ::= { atmNtePrtConfig 6 }

          atmNteAlarmVcEntry OBJECT-TYPE
              SYNTAX  AtmNteAlarmVcEntry
              MAX-ACCESS  not-accessible
              STATUS  current
              DESCRIPTION
                      "An entry in the ATM VC Alarm table.
                       ifIndex of the ATM layer."
              INDEX   { ifIndex, atmNteVcAlarmVpi, atmNteVcAlarmVci}
              ::= { atmNteAlarmVcTable 1 }

          AtmNteAlarmVcEntry ::=
              SEQUENCE {
			    atmNteVcAlarmVpi
				      Integer32,
			    atmNteVcAlarmVci
				      Integer32,
			    atmNteVcActiveAlarms
				      Integer32
              }

          atmNteVcAlarmVpi OBJECT-TYPE
              SYNTAX  Integer32
              MAX-ACCESS  read-only
              STATUS  current
              DESCRIPTION
                      "The VPI of the VC on which there is an active alarm."
              ::= { atmNteAlarmVcEntry 1 }

          atmNteVcAlarmVci OBJECT-TYPE
              SYNTAX  Integer32
              MAX-ACCESS  read-only
              STATUS  current
              DESCRIPTION
                      "The VCI of the VC on which there is an active alarm."
              ::= { atmNteAlarmVcEntry 2 }

atmNteVcActiveAlarms OBJECT-TYPE
              SYNTAX  Integer32
              MAX-ACCESS  read-only
              STATUS  current
              DESCRIPTION
                      "A Bit String of the active alarms on this VC.
					   An up bit (1) means there is an active alarm of this
					   type. A down bit (0) means there is no such alarm.
                       The meaning of the bits is as follows:
                       1 -	VC AIS
                       2 -	VC Loss Of Continuity
					   3 -  VC RDI
					   4 -	VC Errored Cells > Threshold
					   5 -	VC Lost Cells > Threshold
					   6 -	VC Misinserted Cells > Threshold
					   7 - 	Tx VC AIS
					   8 - 	Tx VC RDI
                       "
              ::= { atmNteAlarmVcEntry 3 }

--
-- file :v:\doc\rdv\mib\ver480\atm\confVcTable.txt
--
-- file  : ConfVcTable.txt
--
--Version:   1.0
--Date:      12.11.97
--By:        Ilana Schvetz
--File:      v:\doc\rdv\mib\ver480\atm\ConfVcTable.txt

--Last Update: 30-Sep-01 by Ilana.

-- *******************************************************
--          Configuration Vc Table
-- *******************************************************

--atmNte	 OBJECT IDENTIFIER ::= { radAtm 3 }
--atmNtePrt		OBJECT IDENTIFIER ::= { atmNte 2 }
--atmNtePrtConfig		OBJECT IDENTIFIER ::= { atmNtePrt 1 }


atmNteConfVcTable OBJECT-TYPE
              SYNTAX  SEQUENCE OF AtmNteConfVcEntry
              MAX-ACCESS  not-accessible
              STATUS  current
              DESCRIPTION
                      "The ATM VC configuration table.
                       The table is an extension to the atmVclTable of
                       RFC-1695."
              ::= { atmNtePrtConfig 4 }

          atmNteConfVcEntry OBJECT-TYPE
              SYNTAX  AtmNteConfVcEntry
              MAX-ACCESS  not-accessible
              STATUS  current
              DESCRIPTION
                      "An entry in the ATM VC configuration table.
                       ifIndex of the ATM layer."
              INDEX   { ifIndex , atmVclVpi, atmVclVci}
              ::= { atmNteConfVcTable 1 }

          AtmNteConfVcEntry ::=
              SEQUENCE {
				atmConfVcPolicing            INTEGER,
				atmConfVcCCAdminStatus       INTEGER,
				atmConfVcLoopbackAdminStatus INTEGER,
			    atmConfVcLoopbackSinkAddress OCTET STRING,
			    atmConfVcCongestionControl   OCTET STRING,
                atmConfVcCCDirection		 INTEGER,
                atmConfVcCreationTime        DateAndTime,
                atmConfVcOamSupport          INTEGER,
				atmConfVcCCActivationCtrl    INTEGER,
				atmConfVcCCOperStatus        INTEGER,
				atmConfVcLoopbackTraffic     INTEGER,
				atmConfVcLoopbackFailureInd	 INTEGER,
				atmConfVcLoopbackFailureThreshold	 Integer32,
			    atmConfVcOamDirection        INTEGER
              }

          atmConfVcPolicing OBJECT-TYPE
              SYNTAX  INTEGER {
		         none(1),
		         police(2),
		         monitor(3),
		         shaping(4),
                 policingAndShaping(5),
		         notApplicable(255)
	          }
              MAX-ACCESS  read-write
              STATUS  current
              DESCRIPTION
                      "Policing method desired for this VCL."
              ::= { atmNteConfVcEntry 1 }

     atmConfVcCCAdminStatus OBJECT-TYPE
             SYNTAX  INTEGER {
		            up(2),
            		down(3),
		            source(4),       -- agent send Oam CC cells
		            sink(5),         -- agent check received Oam CC cells
                    listenToActivationCells (6),
                    originateActivationCells(7)
                            }
             MAX-ACCESS read-write
             STATUS current
             DESCRIPTION
                     	"up(2) - Activate Continuity Check (CC).
                      	down(3) - Deactivate CC.
		                source(4)      - Activate OAM CC(Continuity Check) of local agent
                        			( start sending Oam cells to the remote side ).
      		            sink(5)          - Activate CC of remote agent ( start receiving Oam cells from
      		 				remote 	side ).
      		 			listenToActivationCells (6) - Passive listener till gets an activation request
                        originateActivationCells(7) - Sands Activation cell according to atmConfVcCCDirection."
             ::= {atmNteConfVcEntry 2}

     atmConfVcLoopbackAdminStatus OBJECT-TYPE
             SYNTAX INTEGER {
		      up(2),
		      down(3),
		      llid(4),
		      segment(5),
		      endToEnd(6),
		      segmentLlid(7),
		      endToEndLlid(8)
	         }
             MAX-ACCESS read-write
             STATUS current
             DESCRIPTION
                  "up(2) - Start loopback OAM cells.
                   down(3) - Stop sending loopback OAM cells.

                   For ace2002:
                   up(2)   - Transmitting LB cells with llid all ones
                             (i.e. FFFF..FF)
                   down(3) - Not transmitting LB cells.
                   llid(4) - Transmitting LB cells with llid indicated
                             in the address field.
                   segment(5) - Transmitting Segment LB cells with llid
                             all ones.
                   endToEnd(6) - Transmitting End to End LB cells with llid
                             all ones.
                   segmentLlid(7) - Transmitting Segment LB cells with
                             llid indicated in the address field.
                   endToEndLlid(8) - Transmitting LB cells with llid
                             indicated in the address field.

                   This parameter value might be in conflict with
                   atmConfVcOamSupport value, since this parameter is for LB,
                   while atmConfVcOamSupport is for any other OAM cells."
             ::= {atmNteConfVcEntry 3}

	atmConfVcLoopbackSinkAddress OBJECT-TYPE
             		SYNTAX OCTET STRING  (SIZE(2..20))
             		MAX-ACCESS read-write
             		STATUS current
             		DESCRIPTION
                    	 "Destination address.
                    	 For ace101: 2 bytes are used.
                    	 For ace2002: 16 bytes are used."
             ::= {atmNteConfVcEntry 4}

	atmConfVcCongestionControl OBJECT-TYPE
             		SYNTAX OCTET STRING
             		MAX-ACCESS read-write
             		STATUS current
             		DESCRIPTION
                    	 "Each bit indicates a selection of one option
                               as the following description.  All combinations
                               are possible and legal.
                               The codes are:
                               1 - EPD
                               2 - CLP
                               4 - EFCI.
                               For ace2002:
                               1 - Packet Discard."
             ::= {atmNteConfVcEntry 5}

     atmConfVcCCDirection OBJECT-TYPE
             SYNTAX  INTEGER {
		            both  (2),
		            source(4),
		            sink  (5)
                            }
             MAX-ACCESS read-write
             STATUS current
             DESCRIPTION
                     	"both(2) - Agent send OAM CC cells and check receivev OAM CC cells
                        source(4)- Agent send OAM CC cells.
      		            sink(5)  - Agent checks received OAM CC cells."
             ::= {atmNteConfVcEntry 6}

     atmConfVcCreationTime OBJECT-TYPE
         SYNTAX   DateAndTime
         MAX-ACCESS   read-only
         STATUS   current
         DESCRIPTION
            "A date-time in which the VC was created."
         ::= { atmNteConfVcEntry 7 }

     atmConfVcOamSupport OBJECT-TYPE
               SYNTAX  INTEGER {
                          intermediate(1),
                          segmentTermination(2),
                          endToEndTermination(3)
                      }
               MAX-ACCESS  read-write
               STATUS  current
               DESCRIPTION
               "OAM support mode, which determines the device location
                in a segment wise."
               ::= { atmNteConfVcEntry 8 }

    atmConfVcCCActivationCtrl OBJECT-TYPE
             SYNTAX  INTEGER {
		             manual(1),
                     activator(2),
		             listener(3)
                            }
             MAX-ACCESS read-write
             STATUS current
             DESCRIPTION
             "manual(1) - CC Activation process is disable
              activator(2) - ACE-101 initiate  CC Activation process
              listener(3) - ACE-101 wait to CC Activation request from remote side."
             ::= { atmNteConfVcEntry 9 }

     atmConfVcCCOperStatus OBJECT-TYPE
             SYNTAX  INTEGER {
					 initial(1),
		             up(2),
            	     down(3),
		             source(4),    -- agent send Oam CC cells
		             sink(5),       -- agent check received Oam CC cells
					 both (8),
		 			 timeout (9),
				     denied (10),
					 conflict (11),
					 manual (12)
                            }
             MAX-ACCESS read-only
             STATUS current
             DESCRIPTION
                     	"
                     	initial (1) - The CC activation process is not started.
                     	up (2) -  Continuity Check (CC) activated.
                      	down (3) - CC deactivated.
              	    	source (4)  -  OAM CC(Continuity Check) of local agent activated.
                     	sink (5)  -  OAM CC of remote agent activated.
						both (8) - OAM CC of local and remote agents activation.
		                timeout (9) - Timeout occured on receiving answer from
                                      the remote agent.
		                denied  (10) - CC activation process rejected by remote agent.
		                conflict (11) - local and remote sides requested activation
                                      simultaneously.
				        manual (12) - OAM CC of local agent activated manually.
						"
             ::= { atmNteConfVcEntry 10 }

	atmConfVcLoopbackTraffic OBJECT-TYPE
             		SYNTAX INTEGER { off(2), on(3) }
             		MAX-ACCESS read-write
             		STATUS current
             		DESCRIPTION
                    	 "This parameter has both command and status meanings:
                    	 off(2) - Set to 'Off' will Stop traffic loop. Getting this
                    	          value means that the loop is not running.
                      	 on (3) - Set to 'On' will start traffic loop. Getting
                      	          this value means that the loop is currently running."
             ::= {atmNteConfVcEntry 11}

	atmConfVcLoopbackFailureInd OBJECT-TYPE
             		SYNTAX INTEGER {
             		disabled(2),
             		segmentAis(3),
             		segmentRdi(4),
             		segmentAisAndRdi(5),
             		endToEndAis(6),
             		endToEndRdi(7),
             		endToEndAisAndRdi(8)
             		}
             		MAX-ACCESS read-write
             		STATUS current
             		DESCRIPTION
    "This object allows user to define the Indication that will be created upon
     a LB cell failure.
     disabled(2) - no indication will be created.
     segmentAis(3) - will cause Tx of a segment AIS.
     segmentRdi(4) - will cause Tx of a segment RDI.
     segmentAisAndRdi(5) - will cause Tx of a segment AIS & RDI.
     endToEndAis(6) - will cause Tx of an End to End AIS.
     endToEndRdi(7)	- will cause Tx of an End to End RDI.
     endToEndAisAndRdi(8) - will cause Tx of an End to End AIS & RDI.
     Default: disabled(2)."
             ::= {atmNteConfVcEntry 12}

	atmConfVcLoopbackFailureThreshold OBJECT-TYPE
             		SYNTAX Integer32
             		MAX-ACCESS read-write
             		STATUS current
             		DESCRIPTION
    "The number of the LB failures before starting transmission of the
    Indication defined by atmConfVcLoopbackFailureInd.
    Range: 1..16. Default: 1."
             ::= {atmNteConfVcEntry 13}

     atmConfVcOamDirection OBJECT-TYPE
             SYNTAX  INTEGER {
		            notApplicable  (1),
		            downStream     (2),
		            upStream       (3)
                            }
             MAX-ACCESS read-write
             STATUS current
             DESCRIPTION
    "The direction of OAM cell insertion.
	 downStream(2) - The OAM cell will be inserted in downStream.
	 upStream(3)   - The OAM cell will be inserted in upStream."
             ::= {atmNteConfVcEntry 14}

--
-- file :v:\doc\rdv\mib\ver470\atm\radima.txt
--
-- RAD-IMA-MIB DEFINITIONS ::= BEGIN

--Title:    RAD-IMA   MIB
--
-- Copyright 1998 RAD Data Communications, Ltd.
-- All Rights Reserved.

-- IMPORTS

--      OBJECT-TYPE                     FROM RFC-1212
 --     radWan                          FROM RAD-GEN-MIB;
--                RAD-IMA MIB

--Title:     RAD's IMA INTERFACE MIB
--Version:   1.0
--Date:      15.09.98
--By:        Ilana Schvetz
--File:      radima.mib

-- Last Update 03.04.01 by Ilana Schvetz


radAtmIma  OBJECT IDENTIFIER  ::=  {radAtm 5}

imaPrimaryClk     OBJECT-TYPE
              SYNTAX  INTEGER {
                             notApplicable(1),
		                     link1(2),
		                     link2(3),
		                     link3(4),
		                     link4(5),
		                     automatic(6)
              }
              MAX-ACCESS  read-write
              STATUS  current
              DESCRIPTION
                       "Clock source to be transmitted to the user side,
                        where user module is in 'External' clock source."
             ::= { radAtmIma 1 }

-- An extension to the Link Table


imaXLinkTable  OBJECT-TYPE
       SYNTAX      SEQUENCE OF ImaXLinkEntry
       MAX-ACCESS  	   not-accessible
       STATUS      current
       DESCRIPTION
               "The IMA Link Status and Configuration table.
                This table contains additional objects for the link table."
       ::= { radAtmIma 2 }

imaXLinkEntry  OBJECT-TYPE
       SYNTAX  	   ImaXLinkEntry
       MAX-ACCESS  	   not-accessible
       STATUS      current
       DESCRIPTION
               "An entry in the IMA Link table."
 --      AUGMENTS    { imaLinkTable }
         INDEX   { imaLinkIfIndex }
       ::= { imaXLinkTable 1 }

ImaXLinkEntry     ::=
      SEQUENCE {
        imaLinkDirection		    INTEGER,
        imaLinkItcLBClkSrc			INTEGER
}



imaLinkDirection  OBJECT-TYPE
              	SYNTAX  INTEGER {
	                    	rx(1),
							tx(2),
							both(3)
	 			}
              	MAX-ACCESS  read-write
              	STATUS  current
              	DESCRIPTION
                      "the Link direction."
--	        	DEFAULT { both }
              ::= { imaXLinkEntry 1 }

imaLinkItcLBClkSrc OBJECT-TYPE
              	SYNTAX  INTEGER {
							link1(1),
							link2(2),
							link3(3),
							link4(4),
							internal(5),
							external(6),
							automatic(7)
	 			}
              	MAX-ACCESS  read-write
              	STATUS  current
              	DESCRIPTION
              	 		"Clock source for the current Tx-line."
              ::= { imaXLinkEntry 2 }

-- An extension to the Group Table


imaXGroupTable  OBJECT-TYPE
       SYNTAX      SEQUENCE OF ImaXGroupEntry
       MAX-ACCESS  	   not-accessible
       STATUS      current
       DESCRIPTION
               "The IMA group Status and Configuration table.
                This table contains additional objects for the Group table."
       ::= { radAtmIma 3 }

imaXGroupEntry  OBJECT-TYPE
       SYNTAX  	   ImaXGroupEntry
       MAX-ACCESS  	   not-accessible
       STATUS      current
       DESCRIPTION
               "An entry in the IMA Group table."
 --      AUGMENTS    { imaGroupTable }
         INDEX   { imaGroupIndex }
       ::= { imaXGroupTable 1 }

ImaXGroupEntry     ::=
      SEQUENCE {
		imaGroupVersion				INTEGER,
        imaGroupCtcTxClkSrc			INTEGER
      }


imaGroupVersion     OBJECT-TYPE
              SYNTAX  INTEGER {
                             ver10(1),
		                     ver11(2)
              }
              MAX-ACCESS  read-write
              STATUS  current
              DESCRIPTION
                       "IMA Version."
             ::= { imaXGroupEntry 1 }

imaGroupCtcTxClkSrc OBJECT-TYPE
              	SYNTAX  INTEGER {
							link1(1),
							link2(2),
							link3(3),
							link4(4),
							internal(5),
							external(6),
							automatic(7),

							notApplicable(255)
	 			}
              	MAX-ACCESS  read-write
              	STATUS  current
              	DESCRIPTION
              	 		"The source of the transmited, common, Clock Source.
						 Applicable if imaGroupNeTxClkMode=ctc(1).
                         Automatic - Dynamic source, taken from the currently reference link.
                         Internal  - taken from the Internal clock on card.
                         Link N    - Clock will be looped from one of the links."
               ::= { imaXGroupEntry 2 }


-- IMA Traps

--NOTIFICATIONS

atmImaGroupStatusChangeTrap NOTIFICATION-TYPE
      OBJECTS  { imaGroupFailureStatus }
      STATUS  current
      DESCRIPTION
	  	"This trap indicates IMA Group status change."
	::= { radSysAtmEvents 80 }

--
-- file :v:\doc\rdv\mib\Before~1\radhdlc.txt
--
-- RAD-HDLC-MIB DEFINITIONS ::= BEGIN

--Title:    RAD-HDLC   MIB
--
-- Copyright 1998 RAD Data Communications, Ltd.
-- All Rights Reserved.


--Title:     RAD's HDLC MIB
--Version:   1.0
--Date:      15.09.98
--By:        Ilana Schvetz
--File:      radhdlc.mib
--

hdlcMibObjects  OBJECT IDENTIFIER  ::=  {diverseIfWanGen 5}

hdlcTable  OBJECT-TYPE
       SYNTAX      SEQUENCE OF HdlcEntry
       MAX-ACCESS  	   not-accessible
       STATUS      current
       DESCRIPTION
               	"The HDLC configuration table."
       ::= { hdlcMibObjects 1 }

hdlcEntry  OBJECT-TYPE
       SYNTAX  	   HdlcEntry
       MAX-ACCESS  	   not-accessible
       STATUS      current
       DESCRIPTION
				"Defines the contents of each line in the RAD HDLC Table."
       INDEX   { ifIndex }
       ::= { hdlcTable 1 }

HdlcEntry     ::=
      SEQUENCE {
        hdlcProtocol				INTEGER,
        hdlcRateResolution			INTEGER,
        hdlcTxClockSource			INTEGER,
        hdlcTerminalMode			INTEGER,
        hdlcLoopbackState			INTEGER,
        hdlcTxClockPolarity			INTEGER,
        hdlcFlowControl				INTEGER,
        hdlcLineRate				Integer32,
        hdlcRxClockMode				INTEGER,
        hdlcLOF						Gauge32,
        hdlcRxClockPolarity			INTEGER
}



hdlcProtocol     OBJECT-TYPE
              SYNTAX  INTEGER {
                             notApplicable(1),
		                     v35(2),
		                     x21(3),
		                     rs530(4)
              }
              MAX-ACCESS  read-write
              STATUS  current
              DESCRIPTION
                       "The HDLC protocol type
                        V35 - HDLC encapsulated over V35
                        X21 - HDLC encapsulated over X21
                        RS530 - HDLC encapsulated over RS530"
              ::= { hdlcEntry 1 }



hdlcRateResolution  OBJECT-TYPE
    		SYNTAX INTEGER {
       					notApplicable(1),
       					nx56Kbps(2),
       					nx64Kbps(3)
      		}
    		MAX-ACCESS  read-write
    		STATUS  current
    		DESCRIPTION
					"The baud rate of the internal clock."
    		::= { hdlcEntry 2 }


hdlcTxClockSource  OBJECT-TYPE
    		SYNTAX INTEGER {
       					internal(1),
       					external(2)
      		}
    		MAX-ACCESS  read-write
    		STATUS  current
    		DESCRIPTION
					"The baud rate of the internal clock."
    		::= { hdlcEntry 3 }

hdlcTerminalMode  OBJECT-TYPE
    		SYNTAX INTEGER {
       					dce(1),
       					dte(2)
      		}
    		MAX-ACCESS  read-write
    		STATUS  current
    		DESCRIPTION
					"."
    		::= { hdlcEntry 4 }

hdlcLoopbackState OBJECT-TYPE
            SYNTAX  INTEGER {
                            notApplicable(1),
            				internal(2),
            				external(3),
            				disable(4)
            }
            MAX-ACCESS  read-write
            STATUS  current
            DESCRIPTION
                    "internal - All data coming from the
                    			network port is looped back
                     external - All data comming from the line is
                     			looped back."
            ::= { hdlcEntry 5 }


hdlcTxClockPolarity  OBJECT-TYPE
    		SYNTAX INTEGER {
       					normal (1),
       					inverse(2)
      		}
    		MAX-ACCESS  read-write
    		STATUS  current
    		DESCRIPTION
					"normal  - The transmitted data is sampled at the middle of bit time
					 inverse - The transmitted data is sampled at the end of the bit time
					 			(high data rate/long cable)."
    		::= { hdlcEntry 6 }

hdlcFlowControl  OBJECT-TYPE
    		SYNTAX INTEGER {
       					disable(1),
       					enable (2)
      		}
    		MAX-ACCESS  read-write
    		STATUS  current
    		DESCRIPTION
					"Enable/Disable the CTS/RTS flow control signals."
    		::= { hdlcEntry 7 }


hdlcLineRate  OBJECT-TYPE
    		SYNTAX Integer32
    		MAX-ACCESS  read-write
    		STATUS  current
    		DESCRIPTION
					"The rate values for HDLC are n*56/64Kbps, where 1<=n<=32, 64, 128
					 and the following values: 1544, 3088, 6176.
					 The rate values for HSSI is nMbps, where 1<=n<=52."
    		::= { hdlcEntry 8 }


hdlcRxClockMode  OBJECT-TYPE
    		SYNTAX INTEGER {
						notApplicable(1),
       					internal     (2),
       					external     (3)
      		}
    		MAX-ACCESS  read-write
    		STATUS  current
    		DESCRIPTION
					"."
    		::= { hdlcEntry 9 }


hdlcLOF  OBJECT-TYPE
    		SYNTAX 	Gauge32
    		MAX-ACCESS  read-only
    		STATUS  current
    		DESCRIPTION
					"Total number of seconds the port is in Loss Of Frame state."
    		::= { hdlcEntry 10 }


hdlcRxClockPolarity  OBJECT-TYPE
    		SYNTAX INTEGER {
       					normal (1),
       					inverse(2)
      		}
    		MAX-ACCESS  read-write
    		STATUS  current
    		DESCRIPTION
					"normal  - The received data is sampled at the middle of bit time
					 inverse - The received data is sampled at the end of the bit time
					 			(high data rate/long cable)."
    		::= { hdlcEntry 11 }


--
-- file :v:\doc\rdv\mib\ver480\atm\ace101.txt
--


--
-- file :v:\doc\rdv\mib\ver480\ace101.txt

--RAD-ARC-MIB

--			DEFINITIONS ::= BEGIN

--Title:    RAD-ARC   MIB
--

-- IMPORTS
--      Gauge32, IpAddress                FROM RFC1155-SMI
--      ifIndex                         FROM IF-MIB
--      OBJECT-TYPE                     FROM RFC-1212
--      TRAP-TYPE                       FROM RFC-1215
--      radAtm, agnLed, agnIndication   FROM RAD-GEN-MIB
--	  RowStatus                         FROM SNMPv2-TC
--	  atmVplVpi, atmVclVpi, atmVclVci   FROM ATM-MIB;



--                RAD-ARC MIB

--Title:     RAD's ARC ATM PRODUCT MIB
--Version:   1.0
--Date:      24.9.96
--By:        Yair Arian
--File:      arc.mib
--
--Last update: 09-Jan-02 by Ilana Schvetz

atmGen  OBJECT IDENTIFIER  ::=  {radAtm 2}

atmPerfHistory  OBJECT IDENTIFIER  ::=  {atmGen 1}

atmIfPerformance  OBJECT IDENTIFIER  ::=  {atmPerfHistory 1}
-- aal5VccXTable  ::= { atmIfPerformance 4 }  in aal5.txt


          atmIfDataTable OBJECT-TYPE
              SYNTAX  SEQUENCE OF AtmIfDataEntry
              MAX-ACCESS  not-accessible
              STATUS  current
              DESCRIPTION
                      "The ATM interface Data table."
              ::= { atmIfPerformance 1 }

          atmIfDataEntry OBJECT-TYPE
              SYNTAX  AtmIfDataEntry
              MAX-ACCESS  not-accessible
              STATUS  current
              DESCRIPTION
                      "An entry in the ATM interface Data table."
              INDEX   { ifIndex }
              ::= { atmIfDataTable 1 }

          AtmIfDataEntry ::=
              SEQUENCE {
                  atmIfTimeElapsed
                      Integer32,
                  atmIfValidIntervals
                      Integer32
              }

           atmIfTimeElapsed OBJECT-TYPE
               SYNTAX  Integer32 (0..899)
               MAX-ACCESS  read-only
               STATUS  current
               DESCRIPTION
                       "The number of seconds that have elapsed since
                       the beginning of the near end current error-
                       measurement period."
              ::= { atmIfDataEntry 1 }

          atmIfValidIntervals OBJECT-TYPE
              SYNTAX  Integer32 (0..96)
              MAX-ACCESS  read-only
              STATUS  current
              DESCRIPTION
                      "The number of previous near end intervals for
                      which valid data was collected.  The value will be
                      96 unless the interface was brought online within
                      the last 24 hours, in which case the value will be
                      the number of complete 15 minute near end
                      intervals since the interface has been online."
              ::= { atmIfDataEntry 2 }


          -- the ATM interface Current

          -- The ATM interface current table contains various statistics being
          -- collected for the current 15 minute interval.

          atmIfCurrentTable OBJECT-TYPE
              SYNTAX  SEQUENCE OF AtmIfCurrentEntry
              MAX-ACCESS  not-accessible
              STATUS  current
              DESCRIPTION
                      "The ATM interface Current table."
              ::= { atmIfPerformance 2 }

          atmIfCurrentEntry OBJECT-TYPE
              SYNTAX  AtmIfCurrentEntry
              MAX-ACCESS  not-accessible
              STATUS  current
              DESCRIPTION
                      "An entry in the ATM interface Current table."
              INDEX   { ifIndex }
              ::= { atmIfCurrentTable 1 }

          AtmIfCurrentEntry ::=
              SEQUENCE {
                  atmIfCurrentTxCells
                      Gauge32,
                  atmIfCurrentRxCells
                      Gauge32,
                  atmIfCurrentCorrectedHecs
                      Gauge32,
                  atmIfCurrentUncorrectedHecs
                      Gauge32
              }

          atmIfCurrentTxCells OBJECT-TYPE
              SYNTAX  Gauge32
              MAX-ACCESS  read-only
              STATUS  current
              DESCRIPTION
                      "The counter associated with the number of transmitted
                      cells, encountered by an ATM interface in
                      the current 15 minute interval."
              ::= { atmIfCurrentEntry 1 }

          atmIfCurrentRxCells OBJECT-TYPE
              SYNTAX  Gauge32
              MAX-ACCESS  read-only
              STATUS  current
              DESCRIPTION
                      "The counter associated with the number of received
                      cells, encountered by an ATM
                      interface in the current 15 minute interval."
              ::= { atmIfCurrentEntry 2 }

          atmIfCurrentCorrectedHecs OBJECT-TYPE
              SYNTAX  Gauge32
              MAX-ACCESS  read-only
              STATUS  current
              DESCRIPTION
                      "The counter associated with the number of cells with
                      corrected HEC errors, encountered by an
                      ATM interface in the current 15 minute
                      interval."
              ::= { atmIfCurrentEntry 3 }

          atmIfCurrentUncorrectedHecs OBJECT-TYPE
              SYNTAX  Gauge32
              MAX-ACCESS  read-only
              STATUS  current
              DESCRIPTION
                      "The counter associated with the number of cells with
                      uncorrected HEC errors, encountered by an ATM
                      interface in the current 15 minute interval."
              ::= { atmIfCurrentEntry 4 }


          -- the ATM interface Interval

          -- The ATM interface Interval Table contains various statistics
          -- collected by each ATM Interface over the previous 24
          -- hours of operation.  The past 24 hours are broken into 96
          -- completed 15 minute intervals.

          atmIfIntervalTable OBJECT-TYPE
              SYNTAX  SEQUENCE OF AtmIfIntervalEntry
              MAX-ACCESS  not-accessible
              STATUS  current
              DESCRIPTION
                      "The ATM interface Interval table."
              ::= { atmIfPerformance 3 }

          atmIfIntervalEntry OBJECT-TYPE
              SYNTAX  AtmIfIntervalEntry
              MAX-ACCESS  not-accessible
              STATUS  current
              DESCRIPTION
                      "An entry in the ATM interface Interval table."
              INDEX   { ifIndex, atmIfIntervalNumber }
              ::= { atmIfIntervalTable 1 }

          AtmIfIntervalEntry ::=
              SEQUENCE {
                  atmIfIntervalNumber
                      Integer32,
                  atmIfIntervalTxCells
                      Gauge32,
                  atmIfIntervalRxCells
                      Gauge32,
                  atmIfIntervalCorrectedHecs
                      Gauge32,
                  atmIfIntervalUncorrectedHecs
                      Gauge32
              }

          atmIfIntervalNumber OBJECT-TYPE
              SYNTAX  Integer32 (1..96)
              MAX-ACCESS  read-only
              STATUS  current
              DESCRIPTION
                      "A number between 1 and 96, where 1 is the most
                      recently completed 15 minute interval and 96 is
                      the least recently completed 15 minutes interval
                      (assuming that all 96 intervals are valid)."
              ::= { atmIfIntervalEntry 1 }

          atmIfIntervalTxCells OBJECT-TYPE
              SYNTAX  Gauge32
              MAX-ACCESS  read-only
              STATUS  current
              DESCRIPTION
                      "The counter associated with the number of transmitted
                      cells , encountered by an ATM interface in
                      one of the previous 96, individual 15 minute,
                      intervals."
              ::= { atmIfIntervalEntry 2 }

          atmIfIntervalRxCells OBJECT-TYPE
              SYNTAX  Gauge32
              MAX-ACCESS  read-only
              STATUS  current
              DESCRIPTION
                      "The counter associated with the number of received
                      cells, encountered by an ATM
                      interface in one of the previous 96, individual 15
                      minute, intervals."
              ::= { atmIfIntervalEntry 3 }

          atmIfIntervalCorrectedHecs OBJECT-TYPE
              SYNTAX  Gauge32
              MAX-ACCESS  read-only
              STATUS  current
              DESCRIPTION
                      "The counter associated with the number of cells with
                      corrected HEC errors, encountered by an
                      ATM interface in one of the previous 96,
                      individual 15 minute, intervals."
              ::= { atmIfIntervalEntry 4 }

          atmIfIntervalUncorrectedHecs OBJECT-TYPE
              SYNTAX  Gauge32
              MAX-ACCESS  read-only
              STATUS  current
              DESCRIPTION
                      "The counter associated with the number of cells with
                      uncorrected HEC errors, encountered by an ATM
                      interface in one of the previous 96, individual 15
                      minute, intervals."
              ::= { atmIfIntervalEntry 5 }


atmPvcPerformance  OBJECT IDENTIFIER  ::=  {atmPerfHistory 2}

atmVpPerformance  OBJECT IDENTIFIER  ::=  {atmPvcPerformance 1}

          -- the ATM VP Current

          -- The ATM VP current table contains various statistics being
          -- collected for the current 15 minute interval.

          atmVpCurrentTable OBJECT-TYPE
              SYNTAX  SEQUENCE OF AtmVpCurrentEntry
              MAX-ACCESS  not-accessible
              STATUS  current
              DESCRIPTION
                      "The ATM VP Current table."
              ::= { atmVpPerformance 1 }

          atmVpCurrentEntry OBJECT-TYPE
              SYNTAX  AtmVpCurrentEntry
              MAX-ACCESS  not-accessible
              STATUS  current
              DESCRIPTION
                      "An entry in the ATM VP Current table."
              INDEX   { ifIndex, atmVpCurrentVpi }
              ::= { atmVpCurrentTable 1 }

          AtmVpCurrentEntry ::=
              SEQUENCE {
	     atmVpCurrentVpi
                      Integer32,
                  atmVpCurrentRxCellsClp01
                      Gauge32,
                  atmVpCurrentRxCellsClp0
                      Gauge32,
                  atmVpCurrentGcra0Violations
                      Gauge32,
                  atmVpCurrentGcra1Violations
                      Gauge32,
                  atmVpCurrentRxAIS
                      Gauge32,
                  atmVpCurrentTxAIS
                      Gauge32,
                  atmVpCurrentRxRDI
                      Gauge32,
                  atmVpCurrentTxRDI
                      Gauge32,
                  atmVpCurrentContinuityLoss
                      Gauge32,
                  atmVpCurrentUAS
                      Gauge32,
	              atmVpCurrentSES
	                  Gauge32,
	              atmVpCurrentCDC
	                  Gauge32,
                  atmVpCurrentTotalDiscards
                      Gauge32,
                  atmVpCurrentClp0Discards
                      Gauge32,
                  atmVpCurrentTotalCellOuts
                      Gauge32,
                  atmVpCurrentClp0CellOuts
                      Gauge32,
                  atmVpCurrentTaggedOuts
                      Gauge32,
	              atmVpCurrentPCR
	                  Gauge32,
	              atmVpCurrentSCR
	                  Gauge32,
	              atmVpCurrentMCR
	                  Gauge32
          }

          atmVpCurrentVpi OBJECT-TYPE
              SYNTAX  Integer32
              MAX-ACCESS  read-only
              STATUS  current
              DESCRIPTION
                      "The VPI of the VPL."
              ::= { atmVpCurrentEntry 1 }

          atmVpCurrentRxCellsClp01 OBJECT-TYPE
              SYNTAX  Gauge32
              MAX-ACCESS  read-only
              STATUS  current
              DESCRIPTION
                      "The counter associated with the number of transmitted
                      cells, encountered by the VPL of this ATM interface in
                      the current 15 minute interval."
              ::= { atmVpCurrentEntry 2 }

          atmVpCurrentRxCellsClp0 OBJECT-TYPE
              SYNTAX  Gauge32
              MAX-ACCESS  read-only
              STATUS  current
              DESCRIPTION
                      "The counter associated with the number of received
                      cells, encountered by the VPL of this ATM
                      interface in the current 15 minute interval."
              ::= { atmVpCurrentEntry 3 }

          atmVpCurrentGcra0Violations OBJECT-TYPE
              SYNTAX  Gauge32
              MAX-ACCESS  read-only
              STATUS  current
              DESCRIPTION
                      "The counter associated with the number of cells
                      violating GCRA0, encountered by the VPL of this
                      ATM interface in the current 15 minute
                      interval."
              ::= { atmVpCurrentEntry 4 }

          atmVpCurrentGcra1Violations OBJECT-TYPE
              SYNTAX  Gauge32
              MAX-ACCESS  read-only
              STATUS  current
              DESCRIPTION
                      "The counter associated with the number of cells
                      violating GCRA1, encountered by the VPL of this ATM
                      interface in the current 15 minute interval."
              ::= { atmVpCurrentEntry 5 }

          atmVpCurrentRxAIS OBJECT-TYPE
              SYNTAX  Gauge32
              MAX-ACCESS  read-only
              STATUS  current
              DESCRIPTION
                      "The counter associated with the number of received
                      AIS cells, encountered by the VPL of this ATM
                      interface in the current 15 minute interval."
              ::= { atmVpCurrentEntry 6 }

          atmVpCurrentTxAIS OBJECT-TYPE
              SYNTAX  Gauge32
              MAX-ACCESS  read-only
              STATUS  current
              DESCRIPTION
                      "The counter associated with the number of transmitted
                      AIS cells, encountered by the VPL of this ATM
                      interface in the current 15 minute interval. Not Supported
	        in the first phase."
              ::= { atmVpCurrentEntry 7 }

          atmVpCurrentRxRDI OBJECT-TYPE
              SYNTAX  Gauge32
              MAX-ACCESS  read-only
              STATUS  current
              DESCRIPTION
                      "The counter associated with the number of received
                      RDI cells, encountered by the VPL of this ATM
                      interface in the current 15 minute interval."
              ::= { atmVpCurrentEntry 8 }

          atmVpCurrentTxRDI OBJECT-TYPE
              SYNTAX  Gauge32
              MAX-ACCESS  read-only
              STATUS  current
              DESCRIPTION
                      "The counter associated with the number of transmitted
                      RDI cells, encountered by the VPL of this ATM
                      interface in the current 15 minute interval."
              ::= { atmVpCurrentEntry 9 }

          atmVpCurrentContinuityLoss OBJECT-TYPE
              SYNTAX  Gauge32
              MAX-ACCESS  read-only
              STATUS  current
              DESCRIPTION
                      "The counter associated with the number of loss of
                      continuity cells, encountered by the VPL of this ATM
                      interface in the current 15 minute interval."
              ::= { atmVpCurrentEntry 10 }

          atmVpCurrentUAS OBJECT-TYPE
              SYNTAX  Gauge32
              MAX-ACCESS  read-only
              STATUS  current
              DESCRIPTION
                      "The counter associated with the number of Unavailable
                      Seconds, encountered by the VPL of this ATM
                      interface in the current 15 minute interval."
              ::= { atmVpCurrentEntry 11 }

	atmVpCurrentSES OBJECT-TYPE
              SYNTAX  Gauge32
              MAX-ACCESS  read-only
              STATUS  current
              DESCRIPTION
                      "The counter associated with the number of Severerly Errored
                      Seconds, encountered by the VPL of this ATM
                      interface in the current 15 minute interval."
              ::= { atmVpCurrentEntry 12 }

 	atmVpCurrentCDC OBJECT-TYPE
              SYNTAX  Gauge32
              MAX-ACCESS  read-only
              STATUS  current
              DESCRIPTION
                      "Amount of cells dropped in the current 15 minute interval
                       of the VP connection."
              ::= { atmVpCurrentEntry 13 }

    atmVpCurrentTotalDiscards OBJECT-TYPE
              SYNTAX       Gauge32
              MAX-ACCESS       read-only
              STATUS       current
              DESCRIPTION
                      "The total number of valid ATM cells discarded by
                      the traffic policing entity.  This includes cells
                      originally received with CLP=0 and CLP=1."
              ::= { atmVpCurrentEntry 14 }

    atmVpCurrentClp0Discards OBJECT-TYPE
              SYNTAX       Gauge32
              MAX-ACCESS       read-only
              STATUS       current
              DESCRIPTION
                      "The total number of valid ATM cells received with
                      CLP=0 and discarded by the traffic policing
                      entity."
              ::= { atmVpCurrentEntry 15 }

    atmVpCurrentTotalCellOuts OBJECT-TYPE
              SYNTAX       Gauge32
              MAX-ACCESS       read-only
              STATUS       current
              DESCRIPTION
                      "The total number of valid ATM cells transmitted
                      by this VPL. This includes both CLP=0 and CLP=1
                      cells."
              ::= { atmVpCurrentEntry 16 }

    atmVpCurrentClp0CellOuts OBJECT-TYPE
              SYNTAX       Gauge32
              MAX-ACCESS       read-only
              STATUS       current
              DESCRIPTION
                      "The total number of valid ATM cells transmitted
                      with CLP=0 by this VPL."
              ::= { atmVpCurrentEntry 17 }

    atmVpCurrentTaggedOuts OBJECT-TYPE
              SYNTAX       Gauge32
              MAX-ACCESS       read-only
              STATUS       current
              DESCRIPTION
                      "The total number of valid ATM cells tagged by the
                      traffic policing entity from CLP=0 to CLP=1 and
                      transmitted by this VPL."
              ::= { atmVpCurrentEntry 18 }

	atmVpCurrentPCR OBJECT-TYPE
              SYNTAX  Gauge32
              MAX-ACCESS  read-only
              STATUS  current
              DESCRIPTION
                      "The maximum traffic rate encountered in the
                      last interval of the VP connection (monitored once a second)."
              ::= { atmVpCurrentEntry 19 }

	atmVpCurrentSCR OBJECT-TYPE
              SYNTAX  Gauge32
              MAX-ACCESS  read-only
              STATUS  current
              DESCRIPTION
                      "The average traffic rate during the last interval of the VP
                      connection."
              ::= { atmVpCurrentEntry 20 }

	atmVpCurrentMCR OBJECT-TYPE
              SYNTAX  Gauge32
              MAX-ACCESS  read-only
              STATUS  current
              DESCRIPTION
                      "MCR - The minimum traffic rate encountered in the last
                      interval of the VP connection (monitored once a second)."
              ::= { atmVpCurrentEntry 21 }


          -- The ATM VP current table for Performance Management
          -- which contains various statistics being
          -- collected for the current 15 minute interval.

          atmVpPMCurrentTable OBJECT-TYPE
              SYNTAX  SEQUENCE OF AtmVpPMCurrentEntry
              MAX-ACCESS  not-accessible
              STATUS  current
              DESCRIPTION
                      "The ATM VP Current table for Performance Management."
              ::= { atmVpPerformance 2 }

          atmVpPMCurrentEntry OBJECT-TYPE
              SYNTAX  AtmVpPMCurrentEntry
              MAX-ACCESS  not-accessible
              STATUS  current
              DESCRIPTION
                      "An entry in the ATM VP Current table for Performance
                       Management."
              INDEX   { ifIndex, atmVpPMCurrentVpi, atmVpPMCurrentDir }
              ::= { atmVpPMCurrentTable 1 }

          AtmVpPMCurrentEntry ::=
              SEQUENCE {
	atmVpPMCurrentDir
                      INTEGER,
	atmVpPMCurrentVpi
	        Integer32,
                  atmVpPMCurrentTxClp01
                      Gauge32,
                  atmVpPMCurrentTxClp0
                      Gauge32,
                  atmVpPMCurrentRxClp01
                      Gauge32,
                  atmVpPMCurrentRxClp0
                      Gauge32,
                  atmVpPMCurrentErroredCells
                      Gauge32,
                  atmVpPMCurrentLostCells
                      Gauge32,
                  atmVpPMCurrentMisinsertedCells
                      Gauge32,
                  atmVpPMCurrentECB
                      Gauge32,
                  atmVpPMCurrentSECB
                      Gauge32,
                  atmVpPMCurrentES
                      Gauge32,
                  atmVpPMCurrentSES
                      Gauge32,
                  atmVpPMCurrentUAS
                      Gauge32,
	              atmVpPMCurrentIntervalQuality
	                  INTEGER,
	              atmVpPMCurrentLastDayQuality
	                  INTEGER
              }

 	atmVpPMCurrentVpi OBJECT-TYPE
              SYNTAX  Integer32
              MAX-ACCESS  read-only
              STATUS  current
              DESCRIPTION
                      "The VPI of the VPL."
	::= { atmVpPMCurrentEntry 1 }

	atmVpPMCurrentDir OBJECT-TYPE
              SYNTAX  INTEGER {forward(2), backward(3) }
              MAX-ACCESS  read-only
              STATUS  current
              DESCRIPTION
                      "The direction of performance management."
	::= { atmVpPMCurrentEntry 2 }

          atmVpPMCurrentTxClp01 OBJECT-TYPE
              SYNTAX  Gauge32
              MAX-ACCESS  read-only
              STATUS  current
              DESCRIPTION
                      "The counter associated with the number of transmitted
                      CLP 0+1 cells, encountered by the VPL of this ATM
                      interface in the current 15 minute interval."
              ::= { atmVpPMCurrentEntry 3 }

          atmVpPMCurrentTxClp0 OBJECT-TYPE
              SYNTAX  Gauge32
              MAX-ACCESS  read-only
              STATUS  current
              DESCRIPTION
                      "The counter associated with the number of transmitted
                      CLP 0	cells, encountered by the VPL of this ATM
                      interface in the current 15 minute interval."
              ::= { atmVpPMCurrentEntry 4 }

          atmVpPMCurrentRxClp01 OBJECT-TYPE
              SYNTAX  Gauge32
              MAX-ACCESS  read-only
              STATUS  current
              DESCRIPTION
                      "The counter associated with the number of received
                      CLP 0+1 cells, encountered by the VPL of this ATM
                      interface in the current 15 minute interval."
              ::= { atmVpPMCurrentEntry 5 }

          atmVpPMCurrentRxClp0 OBJECT-TYPE
              SYNTAX  Gauge32
              MAX-ACCESS  read-only
              STATUS  current
              DESCRIPTION
                      "The counter associated with the number of received
                      CLP 0 cells, encountered by the VPL of this ATM
                      interface in the current 15 minute interval."
              ::= { atmVpPMCurrentEntry 6 }

          atmVpPMCurrentErroredCells OBJECT-TYPE
              SYNTAX  Gauge32
              MAX-ACCESS  read-only
              STATUS  current
              DESCRIPTION
                      "The counter associated with the number of errored
                      cells, encountered by the VPL of this ATM
                      interface in the current 15 minute interval."
              ::= { atmVpPMCurrentEntry 7 }

          atmVpPMCurrentLostCells OBJECT-TYPE
              SYNTAX  Gauge32
              MAX-ACCESS  read-only
              STATUS  current
              DESCRIPTION
                      "The counter associated with the number of lost
                      cells, encountered by the VPL of this ATM
                      interface in the current 15 minute interval."
              ::= { atmVpPMCurrentEntry 8 }

          atmVpPMCurrentMisinsertedCells OBJECT-TYPE
              SYNTAX  Gauge32
              MAX-ACCESS  read-only
              STATUS  current
              DESCRIPTION
                      "The counter associated with the number of misinserted
                      cells, encountered by the VPL of this ATM
                      interface in the current 15 minute interval."
              ::= { atmVpPMCurrentEntry 9 }

          atmVpPMCurrentECB OBJECT-TYPE
              SYNTAX  Gauge32
              MAX-ACCESS  read-only
              STATUS  current
              DESCRIPTION
                      "The counter associated with the number of ECB,
                      encountered by the VPL of this ATM
                      interface in the current 15 minute interval."
              ::= { atmVpPMCurrentEntry 10 }

          atmVpPMCurrentSECB OBJECT-TYPE
              SYNTAX  Gauge32
              MAX-ACCESS  read-only
              STATUS  current
              DESCRIPTION
                      "The counter associated with the number of SECB,
                      encountered by the VPL of this ATM
                      interface in the current 15 minute interval."
              ::= { atmVpPMCurrentEntry 11 }

          atmVpPMCurrentES OBJECT-TYPE
              SYNTAX  Gauge32
              MAX-ACCESS  read-only
              STATUS  current
              DESCRIPTION
                      "The counter associated with the number of
                      Errored Seconds, encountered by the VPL of this ATM
                      interface in the current 15 minute interval."
              ::= { atmVpPMCurrentEntry 12 }

          atmVpPMCurrentSES OBJECT-TYPE
              SYNTAX  Gauge32
              MAX-ACCESS  read-only
              STATUS  current
              DESCRIPTION
                      "The counter associated with the number of Severely
                      Errored Seconds, encountered by the VPL of this ATM
                      interface in the current 15 minute interval."
              ::= { atmVpPMCurrentEntry 13 }

          atmVpPMCurrentUAS OBJECT-TYPE
              SYNTAX  Gauge32
              MAX-ACCESS  read-only
              STATUS  current
              DESCRIPTION
                      "The counter associated with the number of Unavailable
                      Seconds, encountered by the VPL of this ATM
                      interface in the current 15 minute interval."
              ::= { atmVpPMCurrentEntry 14 }

	atmVpPMCurrentIntervalQuality OBJECT-TYPE
              SYNTAX  INTEGER { normal(2), unacceptable(3) }
	MAX-ACCESS read-only
	STATUS current
	DESCRIPTION
		" If the number of errors per interval is superior to
		the atmNteUPLTCR value, the quality of service of
		the interval is declared as unacceptable."
	DEFVAL { normal }
	::= { atmVpPMCurrentEntry 15 }

	    atmVpPMCurrentLastDayQuality OBJECT-TYPE
              SYNTAX  INTEGER { normal(2), degraded(4) }
	MAX-ACCESS read-only
	STATUS current
	DESCRIPTION
		" If the number of errors per 24 hours is superior to
		the atmNteDPLTCR value, the quality of service of
		the day is declared as degraded."
	DEFVAL { normal }
	::= { atmVpPMCurrentEntry 16 }


          -- the ATM VP Interval

          -- The ATM VP Interval Table contains various statistics
          -- collected by each ATM Interface/VP over the previous 24
          -- hours of operation.  The past 24 hours are broken into 96
          -- completed 15 minute intervals.

          atmVpIntervalTable OBJECT-TYPE
              SYNTAX  SEQUENCE OF AtmVpIntervalEntry
              MAX-ACCESS  not-accessible
              STATUS  current
              DESCRIPTION
                      "The ATM Vp Interval table."
              ::= { atmVpPerformance 3 }

          atmVpIntervalEntry OBJECT-TYPE
              SYNTAX  AtmVpIntervalEntry
              MAX-ACCESS  not-accessible
              STATUS  current
              DESCRIPTION
                      "An entry in the ATM Vp Interval table."
              INDEX   { ifIndex, atmVpIntervalVpi,
                        atmVpIntervalNumber }
              ::= { atmVpIntervalTable 1 }

          AtmVpIntervalEntry ::=
              SEQUENCE {
			      atmVpIntervalVpi
				      Integer32,
                  atmVpIntervalNumber
                      Integer32,
                  atmVpIntervalRxCellsClp01
                      Gauge32,
                  atmVpIntervalRxCellsClp0
                      Gauge32,
                  atmVpIntervalGcra0Violations
                      Gauge32,
                  atmVpIntervalGcra1Violations
                      Gauge32,
                  atmVpIntervalRxAIS
                      Gauge32,
                  atmVpIntervalTxAIS
                      Gauge32,
                  atmVpIntervalRxRDI
                      Gauge32,
                  atmVpIntervalTxRDI
                      Gauge32,
                  atmVpIntervalContinuityLoss
                      Gauge32,
                  atmVpIntervalUAS
                      Gauge32,
	              atmVpIntervalSES
	                  Gauge32,
	              atmVpIntervalCDC
	                  Gauge32,
                  atmVpIntervalTotalDiscards
                      Gauge32,
                  atmVpIntervalClp0Discards
                      Gauge32,
                  atmVpIntervalTotalCellOuts
                      Gauge32,
                  atmVpIntervalClp0CellOuts
                      Gauge32,
                  atmVpIntervalTaggedOuts
                      Gauge32,
	              atmVpIntervalPCR
	                  Gauge32,
	              atmVpIntervalSCR
	                  Gauge32,
	              atmVpIntervalMCR
	                  Gauge32
              }

          atmVpIntervalVpi OBJECT-TYPE
              SYNTAX  Integer32
              MAX-ACCESS  read-only
              STATUS  current
              DESCRIPTION
                      "The VPI of the VPL."
              ::= { atmVpIntervalEntry 1 }

          atmVpIntervalNumber OBJECT-TYPE
              SYNTAX  Integer32 (1..96)
              MAX-ACCESS  read-only
              STATUS  current
              DESCRIPTION
                      "A number between 1 and 96, where 1 is the most
                      recently completed 15 minute interval and 96 is
                      the least recently completed 15 minutes interval
                      (assuming that all 96 intervals are valid)."
              ::= { atmVpIntervalEntry 2 }

          atmVpIntervalRxCellsClp01 OBJECT-TYPE
              SYNTAX  Gauge32
              MAX-ACCESS  read-only
              STATUS  current
              DESCRIPTION
                      "The counter associated with the number of transmitted
                      cells , encountered by an ATM interface/VP in
                      one of the previous 96, individual 15 minute,
                      intervals."
              ::= { atmVpIntervalEntry 3 }

          atmVpIntervalRxCellsClp0 OBJECT-TYPE
              SYNTAX  Gauge32
              MAX-ACCESS  read-only
              STATUS  current
              DESCRIPTION
                      "The counter associated with the number of received
                      cells, encountered by an ATM
                      interface/VP in one of the previous 96, individual 15
                      minute, intervals."
              ::= { atmVpIntervalEntry 4 }

          atmVpIntervalGcra0Violations OBJECT-TYPE
              SYNTAX  Gauge32
              MAX-ACCESS  read-only
              STATUS  current
              DESCRIPTION
                      "The counter associated with the number of
                      cells violating GCRA0, encountered by an ATM
                      interface/VP in one of the previous 96, individual 15
                      minute, intervals."
              ::= { atmVpIntervalEntry 5 }

          atmVpIntervalGcra1Violations OBJECT-TYPE
              SYNTAX  Gauge32
              MAX-ACCESS  read-only
              STATUS  current
              DESCRIPTION
                      "The counter associated with the number of
                      cells violating GCRA1, encountered by an ATM
                      interface/VP in one of the previous 96, individual 15
                      minute, intervals."
              ::= { atmVpIntervalEntry 6 }

          atmVpIntervalRxAIS OBJECT-TYPE
              SYNTAX  Gauge32
              MAX-ACCESS  read-only
              STATUS  current
              DESCRIPTION
                      "The counter associated with the number of received
                      AIS cells, encountered by an ATM
                      interface/VP in one of the previous 96, individual 15
                      minute, intervals."
              ::= { atmVpIntervalEntry 7 }

          atmVpIntervalTxAIS OBJECT-TYPE
              SYNTAX  Gauge32
              MAX-ACCESS  read-only
              STATUS  current
              DESCRIPTION
                      "The counter associated with the number of transmitted
                      AIS cells, encountered by an ATM
                      interface/VP in one of the previous 96, individual 15
                      minute, intervals. Not supported in the first phase."
              ::= { atmVpIntervalEntry 8 }

          atmVpIntervalRxRDI OBJECT-TYPE
              SYNTAX  Gauge32
              MAX-ACCESS  read-only
              STATUS  current
              DESCRIPTION
                      "The counter associated with the number of received
                      RDI cells, encountered by an ATM
                      interface/VP in one of the previous 96, individual 15
                      minute, intervals."
              ::= { atmVpIntervalEntry 9 }

          atmVpIntervalTxRDI OBJECT-TYPE
              SYNTAX  Gauge32
              MAX-ACCESS  read-only
              STATUS  current
              DESCRIPTION
                      "The counter associated with the number of transmitted
                      RDI cells, encountered by an ATM
                      interface/VP in one of the previous 96, individual 15
                      minute, intervals."
              ::= { atmVpIntervalEntry 10 }

          atmVpIntervalContinuityLoss OBJECT-TYPE
              SYNTAX  Gauge32
              MAX-ACCESS  read-only
              STATUS  current
              DESCRIPTION
                      "The counter associated with the number of Continuity
                      Loss cells, encountered by an ATM
                      interface/VP in one of the previous 96, individual 15
                      minute, intervals."
              ::= { atmVpIntervalEntry 11 }

          atmVpIntervalUAS OBJECT-TYPE
              SYNTAX  Gauge32
              MAX-ACCESS  read-only
              STATUS  current
              DESCRIPTION
                      "The counter associated with the number of Unavailable
                      Seconds, encountered by an ATM
                      interface/VP in one of the previous 96, individual 15
                      minute, intervals."
              ::= { atmVpIntervalEntry 12 }

	atmVpIntervalSES OBJECT-TYPE
              SYNTAX  Gauge32
              MAX-ACCESS  read-only
              STATUS  current
              DESCRIPTION
                      "The counter associated with the number of Severerly Errored
                      Seconds, encountered by an ATM
                      interface/VP in one of the previous 96, individual 15
                      minute, intervals."
              ::= { atmVpIntervalEntry 13 }

	atmVpIntervalCDC OBJECT-TYPE
              SYNTAX  Gauge32
              MAX-ACCESS  read-only
              STATUS  current
              DESCRIPTION
                      "Amount of cells dropped in the 15 minute interval
                       of the VP connection."
              ::= { atmVpIntervalEntry 14 }

    atmVpIntervalTotalDiscards OBJECT-TYPE
              SYNTAX       Gauge32
              MAX-ACCESS       read-only
              STATUS       current
              DESCRIPTION
                      "The total number of valid ATM cells discarded by
                      the traffic policing entity.  This includes cells
                      originally received with CLP=0 and CLP=1."
              ::= { atmVpIntervalEntry 15 }

    atmVpIntervalClp0Discards OBJECT-TYPE
              SYNTAX       Gauge32
              MAX-ACCESS       read-only
              STATUS       current
              DESCRIPTION
                      "The total number of valid ATM cells received with
                      CLP=0 an  discarded by the traffic policing
                      entity."
              ::= { atmVpIntervalEntry 16 }

    atmVpIntervalTotalCellOuts OBJECT-TYPE
              SYNTAX       Gauge32
              MAX-ACCESS       read-only
              STATUS       current
              DESCRIPTION
                      "The total number of valid ATM cells transmitted
                      by this VPL.  This includes both CLP=0 and CLP=1
                      cells."
              ::= { atmVpIntervalEntry 17 }


    atmVpIntervalClp0CellOuts OBJECT-TYPE
              SYNTAX       Gauge32
              MAX-ACCESS       read-only
              STATUS       current
              DESCRIPTION
                      "The total number of valid ATM cells transmitted
                      with CLP=0 by this VPL."
              ::= { atmVpIntervalEntry 18 }

    atmVpIntervalTaggedOuts OBJECT-TYPE
              SYNTAX       Gauge32
              MAX-ACCESS       read-only
              STATUS       current
              DESCRIPTION
                      "The total number of valid ATM cells tagged by the
                      traffic policing entity from CLP=0 to CLP=1 and
                      transmitted by this VPL."
              ::= { atmVpIntervalEntry 19 }

	atmVpIntervalPCR OBJECT-TYPE
              SYNTAX  Gauge32
              MAX-ACCESS  read-only
              STATUS  current
              DESCRIPTION
                     "The maximum traffic rate encountered in the last
                     interval of the VP connection (monitored once a second)
                     encountered by an ATM interface/VP in one of the previous
                     96, individual 15 minute, intervals."
              ::= { atmVpIntervalEntry 20 }

	atmVpIntervalSCR OBJECT-TYPE
              SYNTAX  Gauge32
              MAX-ACCESS  read-only
              STATUS  current
              DESCRIPTION
                     "The average traffic rate during the last interval of the
                     VP connection , encountered by an ATM interface/VP in one
                     of the previous 96, individual 15 minute, intervals."
              ::= { atmVpIntervalEntry 21 }

	atmVpIntervalMCR OBJECT-TYPE
              SYNTAX  Gauge32
              MAX-ACCESS  read-only
              STATUS  current
              DESCRIPTION
                     "MCR - The minimum traffic rate encountered in the last
                     interval of the VP connection (monitored once a second)
                     encountered by an ATM interface/VP in one of the previous
                     96, individual 15 minute, intervals."
              ::= { atmVpIntervalEntry 22 }


          -- The ATM VP Interval Table for Performance Management
          -- contains various statistics
          -- collected by each ATM Interface/VP over the previous 24
          -- hours of operation.  The past 24 hours are broken into 96
          -- completed 15 minute intervals.

          atmVpPMIntervalTable OBJECT-TYPE
              SYNTAX  SEQUENCE OF AtmVpPMIntervalEntry
              MAX-ACCESS  not-accessible
              STATUS  current
              DESCRIPTION
                      "The ATM Vp Interval table for Performance Management."
              ::= { atmVpPerformance 4 }

          atmVpPMIntervalEntry OBJECT-TYPE
              SYNTAX  AtmVpPMIntervalEntry
              MAX-ACCESS  not-accessible
              STATUS  current
              DESCRIPTION
                      "An entry in the ATM Vp Interval table for Performance
                       Management."
              INDEX   { ifIndex, atmVpPMIntervalVpi, atmVpPMIntervalDir, atmVpPMIntervalNumber }
              ::= { atmVpPMIntervalTable 1 }

          AtmVpPMIntervalEntry ::=
              SEQUENCE {
	              atmVpPMIntervalVpi
	                  Integer32,
	              atmVpPMIntervalDir
	                  INTEGER,
 	              atmVpPMIntervalNumber
 	                  Integer32,
                  atmVpPMIntervalTxClp01
                      Gauge32,
                  atmVpPMIntervalTxClp0
                      Gauge32,
                  atmVpPMIntervalRxClp01
                      Gauge32,
                  atmVpPMIntervalRxClp0
                      Gauge32,
                  atmVpPMIntervalErroredCells
                      Gauge32,
                  atmVpPMIntervalLostCells
                      Gauge32,
                  atmVpPMIntervalMisinsertedCells
                      Gauge32,
                  atmVpPMIntervalECB
                      Gauge32,
                  atmVpPMIntervalSECB
                      Gauge32,
                  atmVpPMIntervalES
                      Gauge32,
                  atmVpPMIntervalSES
                      Gauge32,
                  atmVpPMIntervalUAS
                      Gauge32,
	              atmVpPMIntervalQuality
		              INTEGER,
	              atmVpPMIntervalLastDayQuality
		              INTEGER
              }

          atmVpPMIntervalVpi OBJECT-TYPE
              SYNTAX  Integer32
              MAX-ACCESS  read-only
              STATUS  current
              DESCRIPTION
                      "The VPI of the VPL."
              ::= { atmVpPMIntervalEntry 1 }

          atmVpPMIntervalDir OBJECT-TYPE
              SYNTAX  INTEGER {forward(2),
			                   backward(3) }
              MAX-ACCESS  read-only
              STATUS  current
              DESCRIPTION
                      "The direction of performance management."
              ::= { atmVpPMIntervalEntry 2 }

          atmVpPMIntervalNumber OBJECT-TYPE
              SYNTAX  Integer32 (1..96)
              MAX-ACCESS  read-only
              STATUS  current
              DESCRIPTION
                      "A number between 1 and 96, where 1 is the most
                      recently completed 15 minute interval and 96 is
                      the least recently completed 15 minutes interval
                      (assuming that all 96 intervals are valid)."
              ::= { atmVpPMIntervalEntry 3 }

          atmVpPMIntervalTxClp01 OBJECT-TYPE
              SYNTAX  Gauge32
              MAX-ACCESS  read-only
              STATUS  current
              DESCRIPTION
                      "The counter associated with the number of transmitted
                      CLP 0+1 cells, encountered by an ATM
                      interface/VP in one of the previous 96, individual 15
                      minute, intervals."
              ::= { atmVpPMIntervalEntry 4 }

          atmVpPMIntervalTxClp0 OBJECT-TYPE
              SYNTAX  Gauge32
              MAX-ACCESS  read-only
              STATUS  current
              DESCRIPTION
                      "The counter associated with the number of transmitted
                      CLP 0 cells, encountered by an ATM
                      interface/VP in one of the previous 96, individual 15
                      minute, intervals."
              ::= { atmVpPMIntervalEntry 5 }

          atmVpPMIntervalRxClp01 OBJECT-TYPE
              SYNTAX  Gauge32
              MAX-ACCESS  read-only
              STATUS  current
              DESCRIPTION
                      "The counter associated with the number of received
                      CLP 0+1 cells, encountered by an ATM
                      interface/VP in one of the previous 96, individual 15
                      minute, intervals."
              ::= { atmVpPMIntervalEntry 6 }

          atmVpPMIntervalRxClp0 OBJECT-TYPE
              SYNTAX  Gauge32
              MAX-ACCESS  read-only
              STATUS  current
              DESCRIPTION
                      "The counter associated with the number of received
                      CLP 0 cells, encountered by an ATM
                      interface/VP in one of the previous 96, individual 15
                      minute, intervals."
              ::= { atmVpPMIntervalEntry 7 }

          atmVpPMIntervalErroredCells OBJECT-TYPE
              SYNTAX  Gauge32
              MAX-ACCESS  read-only
              STATUS  current
              DESCRIPTION
                      "The counter associated with the number of Errored
                      cells, encountered by an ATM
                      interface/VP in one of the previous 96, individual 15
                      minute, intervals."
              ::= { atmVpPMIntervalEntry 8 }

          atmVpPMIntervalLostCells OBJECT-TYPE
              SYNTAX  Gauge32
              MAX-ACCESS  read-only
              STATUS  current
              DESCRIPTION
                      "The counter associated with the number of Lost
                      cells, encountered by an ATM
                      interface/VP in one of the previous 96, individual 15
                      minute, intervals."
              ::= { atmVpPMIntervalEntry 9 }

          atmVpPMIntervalMisinsertedCells OBJECT-TYPE
              SYNTAX  Gauge32
              MAX-ACCESS  read-only
              STATUS  current
              DESCRIPTION
                      "The counter associated with the number of Misinserted
                      cells, encountered by an ATM
                      interface/VP in one of the previous 96, individual 15
                      minute, intervals."
              ::= { atmVpPMIntervalEntry 10 }

          atmVpPMIntervalECB OBJECT-TYPE
              SYNTAX  Gauge32
              MAX-ACCESS  read-only
              STATUS  current
              DESCRIPTION
                      "The counter associated with the number of ECBs
                      encountered by an ATM
                      interface/VP in one of the previous 96, individual 15
                      minute, intervals."
              ::= { atmVpPMIntervalEntry 11 }

          atmVpPMIntervalSECB OBJECT-TYPE
              SYNTAX  Gauge32
              MAX-ACCESS  read-only
              STATUS  current
              DESCRIPTION
                      "The counter associated with the number of SECBs
                      encountered by an ATM
                      interface/VP in one of the previous 96, individual 15
                      minute, intervals."
              ::= { atmVpPMIntervalEntry 12 }

          atmVpPMIntervalES OBJECT-TYPE
              SYNTAX  Gauge32
              MAX-ACCESS  read-only
              STATUS  current
              DESCRIPTION
                      "The counter associated with the number of Errored
                      Seconds, encountered by an ATM
                      interface/VP in one of the previous 96, individual 15
                      minute, intervals."
              ::= { atmVpPMIntervalEntry 13 }

          atmVpPMIntervalSES OBJECT-TYPE
              SYNTAX  Gauge32
              MAX-ACCESS  read-only
              STATUS  current
              DESCRIPTION
                      "The counter associated with the number of Severely
                      Errored Seconds, encountered by an ATM
                      interface/VP in one of the previous 96, individual 15
                      minute, intervals."
              ::= { atmVpPMIntervalEntry 14 }

          atmVpPMIntervalUAS OBJECT-TYPE
              SYNTAX  Gauge32
              MAX-ACCESS  read-only
              STATUS  current
              DESCRIPTION
                      "The counter associated with the number of Unavailable
                      Seconds, encountered by an ATM
                      interface/VP in one of the previous 96, individual 15
                      minute, intervals."
              ::= { atmVpPMIntervalEntry 15 }

	atmVpPMIntervalQuality OBJECT-TYPE
              		SYNTAX  INTEGER { normal(2), unacceptable(3) }
		MAX-ACCESS read-only
		STATUS current
		DESCRIPTION
		" If the number of errors per interval is superior to
		the atmNteUPLTCR value, the quality of service of
		the interval is declared as unacceptable."
		DEFVAL { normal }
	::= { atmVpPMIntervalEntry 16}

	    atmVpPMIntervalLastDayQuality OBJECT-TYPE
              		SYNTAX  INTEGER { normal(2), degraded(4) }
		MAX-ACCESS read-only
		STATUS current
		DESCRIPTION
		" If the number of errors per 24 hours is superior to
		the atmNteDPLTCR value, the quality of service of
		the day is declared as degraded."
		DEFVAL { normal }
	::= { atmVpPMIntervalEntry 17}

-- VP QoS Table

atmVpQoSTable OBJECT-TYPE
    SYNTAX  SEQUENCE OF AtmVpQoSEntry
    MAX-ACCESS  not-accessible
    STATUS  current
    DESCRIPTION
        "The VP QoS table."
    ::= { atmVpPerformance 5 }

atmVpQoSEntry OBJECT-TYPE
    SYNTAX  AtmVpQoSEntry
    MAX-ACCESS  not-accessible
    STATUS  current
    DESCRIPTION
        "."
    INDEX   { ifIndex, atmVplVpi, atmVpQoSPeriodRef }
    ::= { atmVpQoSTable 1 }

AtmVpQoSEntry ::=
    SEQUENCE {
	          atmVpQoSPeriodRef     INTEGER,
	          atmVpQoSElapsedTime	Integer32,
	          atmVpQoSUAS		    Gauge32
             }

atmVpQoSPeriodRef OBJECT-TYPE
	SYNTAX  INTEGER {
	                 currentPeriod (1),
	                 lastPeriod    (2)
                 	}
	MAX-ACCESS  read-only
	STATUS  current
	DESCRIPTION
	    "This object is an index that specifies which period of time, the next
	     2 objects refer to.
	     currentPeriod - the period since last systemResetAllStatsCmd received or
	                     since Start-up (if no systemResetAllStatsCmd was received since
	                     Start-up) until now.
	     lastPeriod    - the period between last two commands of systemResetAllStatsCmd.
	                     - If only one command occurred since Start-up: the period between
	                       Start-up and last command.
	                     - If no command occurred since Start-up: this period will not
	                       actually exist. In this case, he following 5 objects will be 0."
	::= { atmVpQoSEntry 1 }

atmVpQoSElapsedTime OBJECT-TYPE
	SYNTAX  Integer32
	MAX-ACCESS  read-only
	STATUS  current
	DESCRIPTION
	    "Elapsed Time in seconds.
	     - for atmVpQoSPeriodRef = currentPeriod:
	       The period since last systemResetAllStatsCmd received or	since Start-up
	       (if no systemResetAllStatsCmd was received since	Start-up) until now.
	     - for atmVpQoSPeriodRef = lastPeriod:
	       The value of atmVpQoSElapsedTime when last systemResetAllStatsCmd
	       was received."
	::= { atmVpQoSEntry 2 }

atmVpQoSUAS OBJECT-TYPE
	SYNTAX  Gauge32
	MAX-ACCESS  read-only
	STATUS  current
	DESCRIPTION
	    "Number of Unavailable Seconds for the reference period (atmVpQoSPeriodRef)."
	::= { atmVpQoSEntry 3 }

-- VP PM QoS Table

atmVpPMQoSTable OBJECT-TYPE
     SYNTAX  SEQUENCE OF AtmVpPMQoSEntry
     MAX-ACCESS  not-accessible
     STATUS  current
     DESCRIPTION
         "The PM VP QoS table."
     ::= { atmVpPerformance 6 }

atmVpPMQoSEntry OBJECT-TYPE
     SYNTAX  AtmVpPMQoSEntry
     MAX-ACCESS  not-accessible
     STATUS  current
     DESCRIPTION
         "."
     INDEX   { ifIndex, atmVplVpi, atmVpPMQoSDirection ,atmVpPMQoSPeriodRef }
     ::= { atmVpPMQoSTable 1 }

AtmVpPMQoSEntry ::=
     SEQUENCE {
               atmVpPMQoSDirection	   INTEGER,
	           atmVpPMQoSPeriodRef	   INTEGER,
	           atmVpPMQoSCLR		   Gauge32,
	           atmVpPMQoSCER           Gauge32,
	           atmVpPMQoSCMR           Gauge32
              }

atmVpPMQoSDirection OBJECT-TYPE
     SYNTAX  INTEGER
           {
            forward  (2),
			backward (3)
		   }
     MAX-ACCESS  read-only
     STATUS  current
     DESCRIPTION
          "The direction of performance management."
      ::= { atmVpPMQoSEntry 1 }

atmVpPMQoSPeriodRef OBJECT-TYPE
	 SYNTAX  INTEGER
	      {
           currentPeriod  (1),
           lastPeriod     (2)
	      }
	 MAX-ACCESS  read-only
	 STATUS  current
	 DESCRIPTION
	     "This object is an index that specifies which period of time, the next
	      5 objects refer to.
	      currentPeriod - the period since last systemResetAllStatsCmd received or
	                      since Start-up (if no systemResetAllStatsCmd was received since
	                      Start-up) until now.
	      lastPeriod    - the period between last two commands of systemResetAllStatsCmd.
	                      - If only one command occurred since Start-up: the period between
	                        Start-up and last command.
	                      - If no command occurred since Start-up: this period will not
	                        actually exist. In this case, he following 5 objects will be 0."
	::= { atmVpPMQoSEntry 2 }


atmVpPMQoSCLR OBJECT-TYPE
	SYNTAX  Gauge32
	MAX-ACCESS  read-only
	STATUS  current
	DESCRIPTION
	"Cell Loss Ratio counter for the reference period (atmVpPMQoSPeriodRef)-
	defined in accordance with I.356 , in %.
	The value will be multipuled by 100."
	::= { atmVpPMQoSEntry 3 }

atmVpPMQoSCER OBJECT-TYPE
	SYNTAX  Gauge32
	MAX-ACCESS  read-only
	STATUS  current
	DESCRIPTION
	"Cell Error Ratio counter for the reference period (atmVpPMQoSPeriodRef)
	defined in accordance with I.356 , in %.
	The value will be multipuled by 100."
	::= { atmVpPMQoSEntry 4 }

atmVpPMQoSCMR OBJECT-TYPE
	SYNTAX  Gauge32
	MAX-ACCESS  read-only
	STATUS  current
	DESCRIPTION
	"Cell Misinsertion Ratio counter for the reference period (atmVpPMQoSPeriodRef)
	defined in accordance with I.356 , cells/sec ."
	::= { atmVpPMQoSEntry 5 }

--VP Shaper Statistics Table
atmVpShaperStatTable OBJECT-TYPE
              SYNTAX  SEQUENCE OF AtmVpShaperStatEntry
              MAX-ACCESS  not-accessible
              STATUS  current
              DESCRIPTION
                      "The ATM VP shaper statistics table."
              ::= { atmVpPerformance 7 }

          atmVpShaperStatEntry OBJECT-TYPE
              SYNTAX  AtmVpShaperStatEntry
              MAX-ACCESS  not-accessible
              STATUS  current
              DESCRIPTION
                      "An entry in the ATM VP shaper statistics table."
              INDEX   { ifIndex, atmVplVpi }
              ::= { atmVpShaperStatTable 1 }

AtmVpShaperStatEntry ::=
     SEQUENCE {
	           atmVpShaperDiscarded          Counter32,
               atmVpShaperOccupation         Integer32,
               atmVpShaperMaxOccupation 	 Integer32,
               atmVpShaperLevel 			 INTEGER,
               atmVpShaperEpdDropped 		 Counter32,
               atmVpShaperTotalEpdDropped 	 Counter32
              }


atmVpShaperDiscarded OBJECT-TYPE
              SYNTAX  Counter32
              MAX-ACCESS  read-only
              STATUS  current
              DESCRIPTION
                   "The number of Cells that were discarded in the shaper on that VPC due
                    to buffer overflow.
                    This counter counts till it reaches its MAX value (20 bits) and then
                    rolls over."
              ::= { atmVpShaperStatEntry 1 }

atmVpShaperOccupation OBJECT-TYPE
              SYNTAX  Integer32
              MAX-ACCESS  read-only
              STATUS  current
              DESCRIPTION
                   "The number of Cells that are currently stored in the buffer.
                   This parameter is limited to 20 bits."
              ::= { atmVpShaperStatEntry 2}

atmVpShaperMaxOccupation OBJECT-TYPE
              SYNTAX  Integer32
              MAX-ACCESS  read-only
              STATUS  current
              DESCRIPTION
                   "The Maximum number of Cells that were stored in the buffer,
                   since this VP was activated.	This parameter is limited to 20 bits."
              ::= { atmVpShaperStatEntry 3}

atmVpShaperLevel OBJECT-TYPE
	          SYNTAX  INTEGER {
	                 empty   (1),
	                 full    (2),
	                 below   (3),
	                 above   (4)
                 	}
              MAX-ACCESS  read-only
              STATUS  current
              DESCRIPTION
                   "The occupation of the buffer according to a predefined threshold.
                   empty - buffer is Empty
                   full  - buffer is Full
                   below - buffer is Below the threshold
                   above - buffer is Above the threshold. This is also the trigger to
                   start EPD\PPD mechanism, if set for the VPC."
              ::= { atmVpShaperStatEntry 4}

atmVpShaperEpdDropped OBJECT-TYPE
              SYNTAX  Counter32
              MAX-ACCESS  read-only
              STATUS  current
              DESCRIPTION
                   "The number of Cells that were dropped in the shaper on that VPC
                   due to EPD\PPD mechanism in the last second.
                   This parameter is limited to 24 bits.
                   Applicable for a EPD/PPD VP only."
              ::= { atmVpShaperStatEntry 5}

atmVpShaperTotalEpdDropped OBJECT-TYPE
              SYNTAX  Counter32
              MAX-ACCESS  read-only
              STATUS  current
              DESCRIPTION
                   "The Total number of Cells that were dropped in the shaper on that
                   VPC due to EPD\PPD mechanism in the last 15 minutes. This counter
                   automatically reset itself every 15 minutes.
                   Applicable for a EPD/PPD VP only."
              ::= { atmVpShaperStatEntry 6}


atmVcPerformance  OBJECT IDENTIFIER  ::=  {atmPvcPerformance 2}

          -- the ATM VC Current

          -- The ATM VC current table contains various statistics being
          -- collected for the current 15 minute interval.

          atmVcCurrentTable OBJECT-TYPE
              SYNTAX  SEQUENCE OF AtmVcCurrentEntry
              MAX-ACCESS  not-accessible
              STATUS  current
              DESCRIPTION
                      "The ATM VC Current table."
              ::= { atmVcPerformance 1 }

          atmVcCurrentEntry OBJECT-TYPE
              SYNTAX  AtmVcCurrentEntry
              MAX-ACCESS  not-accessible
              STATUS  current
              DESCRIPTION
                      "An entry in the ATM VC Current table."
              INDEX   { ifIndex, atmVcCurrentVpi, atmVcCurrentVci }
              ::= { atmVcCurrentTable 1 }

          AtmVcCurrentEntry ::=
              SEQUENCE {
				  atmVcCurrentVpi
                      Integer32,
				  atmVcCurrentVci
				      Integer32,
                  atmVcCurrentRxCellsClp01
                      Gauge32,
                  atmVcCurrentRxCellsClp0
                      Gauge32,
                  atmVcCurrentGcra0Violations
                      Gauge32,
                  atmVcCurrentGcra1Violations
                      Gauge32,
                  atmVcCurrentRxAIS
                      Gauge32,
                  atmVcCurrentTxAIS
                      Gauge32,
                  atmVcCurrentRxRDI
                      Gauge32,
                  atmVcCurrentTxRDI
                      Gauge32,
                  atmVcCurrentContinuityLoss
                      Gauge32,
                  atmVcCurrentUAS
                      Gauge32,
	              atmVcCurrentSES
	                  Gauge32,
	              atmVcCurrentCDC
	                  Gauge32,
                  atmVcCurrentTotalDiscards
                      Gauge32,
                  atmVcCurrentClp0Discards
                      Gauge32,
                  atmVcCurrentTotalCellOuts
                      Gauge32,
                  atmVcCurrentClp0CellOuts
                      Gauge32,
                  atmVcCurrentTaggedOuts
                      Gauge32,
	              atmVcCurrentPCR
	                  Gauge32,
	              atmVcCurrentSCR
	                  Gauge32,
	              atmVcCurrentMCR
	                  Gauge32
              }

          atmVcCurrentVpi OBJECT-TYPE
              SYNTAX  Integer32
              MAX-ACCESS  read-only
              STATUS  current
              DESCRIPTION
                      "The VPI of the VCL."
              ::= { atmVcCurrentEntry 1 }

          atmVcCurrentVci OBJECT-TYPE
              SYNTAX  Integer32
              MAX-ACCESS  read-only
              STATUS  current
              DESCRIPTION
                      "The VCI of the VCL."
              ::= { atmVcCurrentEntry 2 }

          atmVcCurrentRxCellsClp01 OBJECT-TYPE
              SYNTAX  Gauge32
              MAX-ACCESS  read-only
              STATUS  current
              DESCRIPTION
                      "The counter associated with the number of transmitted
                      cells, encountered by the VCL of this ATM interface in
                      the current 15 minute interval."
              ::= { atmVcCurrentEntry 3 }

          atmVcCurrentRxCellsClp0 OBJECT-TYPE
              SYNTAX  Gauge32
              MAX-ACCESS  read-only
              STATUS  current
              DESCRIPTION
                      "The counter associated with the number of received
                      cells, encountered by the VCL of this ATM
                      interface in the current 15 minute interval."
              ::= { atmVcCurrentEntry 4 }

          atmVcCurrentGcra0Violations OBJECT-TYPE
              SYNTAX  Gauge32
              MAX-ACCESS  read-only
              STATUS  current
              DESCRIPTION
                      "The counter associated with the number of cells
                      violating GCRA0, encountered by the VCL of this
                      ATM interface in the current 15 minute
                      interval."
              ::= { atmVcCurrentEntry 5 }

          atmVcCurrentGcra1Violations OBJECT-TYPE
              SYNTAX  Gauge32
              MAX-ACCESS  read-only
              STATUS  current
              DESCRIPTION
                      "The counter associated with the number of cells
                      violating GCRA1, encountered by the VCL of this ATM
                      interface in the current 15 minute interval."
              ::= { atmVcCurrentEntry 6 }

          atmVcCurrentRxAIS OBJECT-TYPE
              SYNTAX  Gauge32
              MAX-ACCESS  read-only
              STATUS  current
              DESCRIPTION
                      "The counter associated with the number of received
                      AIS cells, encountered by the VCL of this ATM
                      interface in the current 15 minute interval."
              ::= { atmVcCurrentEntry 7 }

          atmVcCurrentTxAIS OBJECT-TYPE
              SYNTAX  Gauge32
              MAX-ACCESS  read-only
              STATUS  current
              DESCRIPTION
                      "The counter associated with the number of transmitted
                      AIS cells, encountered by the VCL of this ATM
                      interface in the current 15 minute interval. Not Supported
	        in the first phase."
              ::= { atmVcCurrentEntry 8 }

          atmVcCurrentRxRDI OBJECT-TYPE
              SYNTAX  Gauge32
              MAX-ACCESS  read-only
              STATUS  current
              DESCRIPTION
                      "The counter associated with the number of received
                      RDI cells, encountered by the VCL of this ATM
                      interface in the current 15 minute interval."
              ::= { atmVcCurrentEntry 9 }

          atmVcCurrentTxRDI OBJECT-TYPE
              SYNTAX  Gauge32
              MAX-ACCESS  read-only
              STATUS  current
              DESCRIPTION
                      "The counter associated with the number of transmitted
                      RDI cells, encountered by the VCL of this ATM
                      interface in the current 15 minute interval."
              ::= { atmVcCurrentEntry 10 }

          atmVcCurrentContinuityLoss OBJECT-TYPE
              SYNTAX  Gauge32
              MAX-ACCESS  read-only
              STATUS  current
              DESCRIPTION
                      "The counter associated with the number of loss of
                      continuity cells, encountered by the VCL of this ATM
                      interface in the current 15 minute interval."
              ::= { atmVcCurrentEntry 11 }

          atmVcCurrentUAS OBJECT-TYPE
              SYNTAX  Gauge32
              MAX-ACCESS  read-only
              STATUS  current
              DESCRIPTION
                      "The counter associated with the number of Unavailable
                      Seconds, encountered by the VCL of this ATM
                      interface in the current 15 minute interval."
              ::= { atmVcCurrentEntry 12 }


 	atmVcCurrentSES OBJECT-TYPE
              SYNTAX  Gauge32
              MAX-ACCESS  read-only
              STATUS  current
              DESCRIPTION
                      "The counter associated with the number of Severerly Errored
                      Seconds, encountered by the VCL of this ATM
                      interface in the current 15 minute interval."
              ::= { atmVcCurrentEntry 13 }

	atmVcCurrentCDC OBJECT-TYPE
              SYNTAX  Gauge32
              MAX-ACCESS  read-only
              STATUS  current
              DESCRIPTION
                      "Amount of cells dropped in the current 15 minute interval
                       of the VC connection."
              ::= { atmVcCurrentEntry 14 }

    atmVcCurrentTotalDiscards OBJECT-TYPE
              SYNTAX       Gauge32
              MAX-ACCESS       read-only
              STATUS       current
              DESCRIPTION
                      "The total number of valid ATM cells discarded by
                      the traffic policing entity.  This includes cells
                      originally received with CLP=0 and CLP=1."
              ::= { atmVcCurrentEntry 15 }

    atmVcCurrentClp0Discards OBJECT-TYPE
              SYNTAX       Gauge32
              MAX-ACCESS       read-only
              STATUS       current
              DESCRIPTION
                      "The total number of valid ATM cells received with
                      CLP=0 an  discarded by the traffic policing
                      entity."
              ::= { atmVcCurrentEntry 16 }

    atmVcCurrentTotalCellOuts OBJECT-TYPE
              SYNTAX       Gauge32
              MAX-ACCESS       read-only
              STATUS       current
              DESCRIPTION
                      "The total number of valid ATM cells transmitted
                      by this VPL.  This includes both CLP=0 and CLP=1
                      cells."
              ::= { atmVcCurrentEntry 17 }

    atmVcCurrentClp0CellOuts OBJECT-TYPE
              SYNTAX       Gauge32
              MAX-ACCESS       read-only
              STATUS       current
              DESCRIPTION
                      "The total number of valid ATM cells transmitted
                      with CLP=0 by this VPL."
              ::= { atmVcCurrentEntry 18 }

    atmVcCurrentTaggedOuts OBJECT-TYPE
              SYNTAX       Gauge32
              MAX-ACCESS       read-only
              STATUS       current
              DESCRIPTION
                      "The total number of valid ATM cells tagged by the
                      traffic policing entity from CLP=0 to CLP=1 and
                      transmitted by this VPL."
              ::= { atmVcCurrentEntry 19 }

	atmVcCurrentPCR OBJECT-TYPE
              SYNTAX  Gauge32
              MAX-ACCESS  read-only
              STATUS  current
              DESCRIPTION
                      "The maximum traffic rate encountered in the last
                      interval of the VC connection (monitored once a second)."
              ::= { atmVcCurrentEntry 20 }

	atmVcCurrentSCR OBJECT-TYPE
              SYNTAX  Gauge32
              MAX-ACCESS  read-only
              STATUS  current
              DESCRIPTION
                      "The average traffic rate during the last interval
                      of the VC connection."
              ::= { atmVcCurrentEntry 21 }

	atmVcCurrentMCR OBJECT-TYPE
              SYNTAX  Gauge32
              MAX-ACCESS  read-only
              STATUS  current
              DESCRIPTION
                      "MCR - The minimum traffic rate encountered in the last
                      interval of the VC connection (monitored once a second)."
              ::= { atmVcCurrentEntry 22 }

          -- The ATM VC current table for Performance Management
          -- which contains various statistics being
          -- collected for the current 15 minute interval.

          atmVcPMCurrentTable OBJECT-TYPE
              SYNTAX  SEQUENCE OF AtmVcPMCurrentEntry
              MAX-ACCESS  not-accessible
              STATUS  current
              DESCRIPTION
                      "The ATM VC Current table for Performance Management."
              ::= { atmVcPerformance 2 }

          atmVcPMCurrentEntry OBJECT-TYPE
              SYNTAX  AtmVcPMCurrentEntry
              MAX-ACCESS  not-accessible
              STATUS  current
              DESCRIPTION
                      "An entry in the ATM VC Current table for Performance
                       Management."
              INDEX   { ifIndex, atmVcPMCurrentVpi,
                        atmVcPMCurrentVci, atmVcPMCurrentDir }
              ::= { atmVcPMCurrentTable 1 }

          AtmVcPMCurrentEntry ::=
              SEQUENCE {
	              atmVcPMCurrentVpi
                      Integer32,
	              atmVcPMCurrentVci
	                  Integer32,
	              atmVcPMCurrentDir
	                  Integer32,
                  atmVcPMCurrentTxClp01
                      Gauge32,
                  atmVcPMCurrentTxClp0
                      Gauge32,
                  atmVcPMCurrentRxClp01
                      Gauge32,
                  atmVcPMCurrentRxClp0
                      Gauge32,
                  atmVcPMCurrentErroredCells
                      Gauge32,
                  atmVcPMCurrentLostCells
                      Gauge32,
                  atmVcPMCurrentMisinsertedCells
                      Gauge32,
                  atmVcPMCurrentECB
                      Gauge32,
                  atmVcPMCurrentSECB
                      Gauge32,
                  atmVcPMCurrentES
                      Gauge32,
                  atmVcPMCurrentSES
                      Gauge32,
                  atmVcPMCurrentUAS
                      Gauge32,
	              atmVcPMCurrentIntervalQuality
	                  INTEGER,
	              atmVcPMCurrentLastDayQuality
	                  INTEGER
                  }

          atmVcPMCurrentVpi OBJECT-TYPE
              SYNTAX  Integer32
              MAX-ACCESS  read-only
              STATUS  current
              DESCRIPTION
                      "The VPI of the VCL."
              ::= { atmVcPMCurrentEntry 1 }

          atmVcPMCurrentVci OBJECT-TYPE
              SYNTAX  Integer32
              MAX-ACCESS  read-only
              STATUS  current
              DESCRIPTION
                      "The VCI of the VCL."
              ::= { atmVcPMCurrentEntry 2 }

          atmVcPMCurrentDir OBJECT-TYPE
              SYNTAX  Integer32
              MAX-ACCESS  read-only
              STATUS  current
              DESCRIPTION
                      "The direction of Performance Management."
              ::= { atmVcPMCurrentEntry 3 }

          atmVcPMCurrentTxClp01 OBJECT-TYPE
              SYNTAX  Gauge32
              MAX-ACCESS  read-only
              STATUS  current
              DESCRIPTION
                      "The counter associated with the number of transmitted
                      CLP 0+1 cells, encountered by the VCL of this ATM
                      interface in the current 15 minute interval."
              ::= { atmVcPMCurrentEntry 4 }

          atmVcPMCurrentTxClp0 OBJECT-TYPE
              SYNTAX  Gauge32
              MAX-ACCESS  read-only
              STATUS  current
              DESCRIPTION
                      "The counter associated with the number of transmitted
                      CLP 0	cells, encountered by the VCL of this ATM
                      interface in the current 15 minute interval."
              ::= { atmVcPMCurrentEntry 5 }

          atmVcPMCurrentRxClp01 OBJECT-TYPE
              SYNTAX  Gauge32
              MAX-ACCESS  read-only
              STATUS  current
              DESCRIPTION
                      "The counter associated with the number of received
                      CLP 0+1 cells, encountered by the VCL of this ATM
                      interface in the current 15 minute interval."
              ::= { atmVcPMCurrentEntry 6 }

          atmVcPMCurrentRxClp0 OBJECT-TYPE
              SYNTAX  Gauge32
              MAX-ACCESS  read-only
              STATUS  current
              DESCRIPTION
                      "The counter associated with the number of received
                      CLP 0 cells, encountered by the VCL of this ATM
                      interface in the current 15 minute interval."
              ::= { atmVcPMCurrentEntry 7 }

          atmVcPMCurrentErroredCells OBJECT-TYPE
              SYNTAX  Gauge32
              MAX-ACCESS  read-only
              STATUS  current
              DESCRIPTION
                      "The counter associated with the number of errored
                      cells, encountered by the VCL of this ATM
                      interface in the current 15 minute interval."
              ::= { atmVcPMCurrentEntry 8 }

          atmVcPMCurrentLostCells OBJECT-TYPE
              SYNTAX  Gauge32
              MAX-ACCESS  read-only
              STATUS  current
              DESCRIPTION
                      "The counter associated with the number of lost
                      cells, encountered by the VCL of this ATM
                      interface in the current 15 minute interval."
              ::= { atmVcPMCurrentEntry 9 }

          atmVcPMCurrentMisinsertedCells OBJECT-TYPE
              SYNTAX  Gauge32
              MAX-ACCESS  read-only
              STATUS  current
              DESCRIPTION
                      "The counter associated with the number of misinserted
                      cells, encountered by the VCL of this ATM
                      interface in the current 15 minute interval."
              ::= { atmVcPMCurrentEntry 10 }

          atmVcPMCurrentECB OBJECT-TYPE
              SYNTAX  Gauge32
              MAX-ACCESS  read-only
              STATUS  current
              DESCRIPTION
                      "The counter associated with the number of ECBs
                      encountered by the VCL of this ATM
                      interface in the current 15 minute interval."
              ::= { atmVcPMCurrentEntry 11 }

          atmVcPMCurrentSECB OBJECT-TYPE
              SYNTAX  Gauge32
              MAX-ACCESS  read-only
              STATUS  current
              DESCRIPTION
                      "The counter associated with the number of SECBs
                      encountered by the VCL of this ATM
                      interface in the current 15 minute interval."
              ::= { atmVcPMCurrentEntry 12 }

          atmVcPMCurrentES OBJECT-TYPE
              SYNTAX  Gauge32
              MAX-ACCESS  read-only
              STATUS  current
              DESCRIPTION
                      "The counter associated with the number of
                      Errored Seconds, encountered by the VCL of this ATM
                      interface in the current 15 minute interval."
              ::= { atmVcPMCurrentEntry 13 }

          atmVcPMCurrentSES OBJECT-TYPE
              SYNTAX  Gauge32
              MAX-ACCESS  read-only
              STATUS  current
              DESCRIPTION
                      "The counter associated with the number of Severely
                      Errored Seconds, encountered by the VCL of this ATM
                      interface in the current 15 minute interval."
              ::= { atmVcPMCurrentEntry 14 }

          atmVcPMCurrentUAS OBJECT-TYPE
              SYNTAX  Gauge32
              MAX-ACCESS  read-only
              STATUS  current
              DESCRIPTION
                      "The counter associated with the number of Severely
                      Errored Seconds, encountered by the VCL of this ATM
                      interface in the current 15 minute interval."
              ::= { atmVcPMCurrentEntry 15 }

atmVcPMCurrentIntervalQuality OBJECT-TYPE
              SYNTAX  INTEGER { normal(2), unacceptable(3) }
	MAX-ACCESS read-only
	STATUS current
	DESCRIPTION
		" If the number of errors per interval is superior to
		the atmNteUPLTCR value, the quality of service of
		the interval is declared as unacceptable."
	DEFVAL { normal }
	::= { atmVcPMCurrentEntry 16 }

	    atmVcPMCurrentLastDayQuality OBJECT-TYPE
              SYNTAX  INTEGER { normal(2), degraded(4) }
	MAX-ACCESS read-only
	STATUS current
	DESCRIPTION
		" If the number of errors per 24 hours is superior to
		the atmNteDPLTCR value, the quality of service of
		the day is declared as degraded."
	DEFVAL { normal }
	::= { atmVcPMCurrentEntry 17 }


          -- the ATM VC Interval

          -- The ATM VC Interval Table contains various statistics
          -- collected by each ATM Interface/VC over the previous 24
          -- hours of operation.  The past 24 hours are broken into 96
          -- completed 15 minute intervals.

          atmVcIntervalTable OBJECT-TYPE
              SYNTAX  SEQUENCE OF AtmVcIntervalEntry
              MAX-ACCESS  not-accessible
              STATUS  current
              DESCRIPTION
                      "The ATM Vc Interval table."
              ::= { atmVcPerformance 3 }

          atmVcIntervalEntry OBJECT-TYPE
              SYNTAX  AtmVcIntervalEntry
              MAX-ACCESS  not-accessible
              STATUS  current
              DESCRIPTION
                      "An entry in the ATM Vc Interval table."
              INDEX   { ifIndex, atmVcIntervalVpi,
                        atmVcIntervalVci, atmVcIntervalNumber }
              ::= { atmVcIntervalTable 1 }

          AtmVcIntervalEntry ::=
              SEQUENCE {
	    atmVcIntervalVpi
	      Integer32,
	    atmVcIntervalVci
	      Integer32,
                  atmVcIntervalNumber
                      Integer32,
                  atmVcIntervalRxCellsClp01
                      Gauge32,
                  atmVcIntervalRxCellsClp0
                      Gauge32,
                  atmVcIntervalGcra0Violations
                      Gauge32,
                  atmVcIntervalGcra1Violations
                      Gauge32,
                  atmVcIntervalRxAIS
                      Gauge32,
                  atmVcIntervalTxAIS
                      Gauge32,
                  atmVcIntervalRxRDI
                      Gauge32,
                  atmVcIntervalTxRDI
                      Gauge32,
                  atmVcIntervalContinuityLoss
                      Gauge32,
                  atmVcIntervalUAS
                      Gauge32,
	              atmVcIntervalSES
	                  Gauge32,
	              atmVcIntervalCDC
	                  Gauge32,
                  atmVcIntervalTotalDiscards
                      Gauge32,
                  atmVcIntervalClp0Discards
                      Gauge32,
                  atmVcIntervalTotalCellOuts
                      Gauge32,
                  atmVcIntervalClp0CellOuts
                      Gauge32,
                  atmVcIntervalTaggedOuts
                      Gauge32,
	              atmVcIntervalPCR
	                  Gauge32,
	              atmVcIntervalSCR
	                  Gauge32,
	              atmVcIntervalMCR
	                  Gauge32
          }

          atmVcIntervalVpi OBJECT-TYPE
              SYNTAX  Integer32
              MAX-ACCESS  read-only
              STATUS  current
              DESCRIPTION
                      "The VPI of the VCL."
              ::= { atmVcIntervalEntry 1 }

          atmVcIntervalVci OBJECT-TYPE
              SYNTAX  Integer32
              MAX-ACCESS  read-only
              STATUS  current
              DESCRIPTION
                      "The VCI of the VCL."
              ::= { atmVcIntervalEntry 2 }

          atmVcIntervalNumber OBJECT-TYPE
              SYNTAX  Integer32 (1..96)
              MAX-ACCESS  read-only
              STATUS  current
              DESCRIPTION
                      "A number between 1 and 96, where 1 is the most
                      recently completed 15 minute interval and 96 is
                      the least recently completed 15 minutes interval
                      (assuming that all 96 intervals are valid)."
              ::= { atmVcIntervalEntry 3 }

          atmVcIntervalRxCellsClp01 OBJECT-TYPE
              SYNTAX  Gauge32
              MAX-ACCESS  read-only
              STATUS  current
              DESCRIPTION
                      "The counter associated with the number of transmitted
                      cells , encountered by an ATM interface/VC in
                      one of the previous 96, individual 15 minute,
                      intervals."
              ::= { atmVcIntervalEntry 4 }

          atmVcIntervalRxCellsClp0 OBJECT-TYPE
              SYNTAX  Gauge32
              MAX-ACCESS  read-only
              STATUS  current
              DESCRIPTION
                      "The counter associated with the number of received
                      cells, encountered by an ATM
                      interface/VC in one of the previous 96, individual 15
                      minute, intervals."
              ::= { atmVcIntervalEntry 5 }

          atmVcIntervalGcra0Violations OBJECT-TYPE
              SYNTAX  Gauge32
              MAX-ACCESS  read-only
              STATUS  current
              DESCRIPTION
                      "The counter associated with the number of
                      cells violating GCRA0, encountered by an ATM
                      interface/VC in one of the previous 96, individual 15
                      minute, intervals."
              ::= { atmVcIntervalEntry 6 }

          atmVcIntervalGcra1Violations OBJECT-TYPE
              SYNTAX  Gauge32
              MAX-ACCESS  read-only
              STATUS  current
              DESCRIPTION
                      "The counter associated with the number of
                      cells violating GCRA1, encountered by an ATM
                      interface/VC in one of the previous 96, individual 15
                      minute, intervals."
              ::= { atmVcIntervalEntry 7 }

          atmVcIntervalRxAIS OBJECT-TYPE
              SYNTAX  Gauge32
              MAX-ACCESS  read-only
              STATUS  current
              DESCRIPTION
                      "The counter associated with the number of received
                      AIS cells, encountered by an ATM
                      interface/VC in one of the previous 96, individual 15
                      minute, intervals."
              ::= { atmVcIntervalEntry 8 }

          atmVcIntervalTxAIS OBJECT-TYPE
              SYNTAX  Gauge32
              MAX-ACCESS  read-only
              STATUS  current
              DESCRIPTION
                      "The counter associated with the number of transmitted
                      AIS cells, encountered by an ATM
                      interface/VC in one of the previous 96, individual 15
                      minute, intervals. Not supported  in the first phase."
              ::= { atmVcIntervalEntry 9 }

          atmVcIntervalRxRDI OBJECT-TYPE
              SYNTAX  Gauge32
              MAX-ACCESS  read-only
              STATUS  current
              DESCRIPTION
                      "The counter associated with the number of received
                      RDI cells, encountered by an ATM
                      interface/VC in one of the previous 96, individual 15
                      minute, intervals."
              ::= { atmVcIntervalEntry 10 }

          atmVcIntervalTxRDI OBJECT-TYPE
              SYNTAX  Gauge32
              MAX-ACCESS  read-only
              STATUS  current
              DESCRIPTION
                      "The counter associated with the number of transmitted
                      RDI cells, encountered by an ATM
                      interface/VC in one of the previous 96, individual 15
                      minute, intervals."
              ::= { atmVcIntervalEntry 11 }

          atmVcIntervalContinuityLoss OBJECT-TYPE
              SYNTAX  Gauge32
              MAX-ACCESS  read-only
              STATUS  current
              DESCRIPTION
                      "The counter associated with the number of Continuity
                      Loss cells, encountered by an ATM
                      interface/VC in one of the previous 96, individual 15
                      minute, intervals."
              ::= { atmVcIntervalEntry 12 }

          atmVcIntervalUAS OBJECT-TYPE
              SYNTAX  Gauge32
              MAX-ACCESS  read-only
              STATUS  current
              DESCRIPTION
                      "The counter associated with the number of Unavailable
                      Seconds, encountered by an ATM
                      interface/VC in one of the previous 96, individual 15
                      minute, intervals."
              ::= { atmVcIntervalEntry 13 }

          atmVcIntervalSES OBJECT-TYPE
              SYNTAX  Gauge32
              MAX-ACCESS  read-only
              STATUS  current
              DESCRIPTION
                      "The counter associated with the number of Severerly Errored
                      Seconds, encountered by an ATM
                      interface/VC in one of the previous 96, individual 15
                      minute, intervals."
              ::= { atmVcIntervalEntry 14 }

	atmVcIntervalCDC OBJECT-TYPE
              SYNTAX  Gauge32
              MAX-ACCESS  read-only
              STATUS  current
              DESCRIPTION
                      "Amount of cells dropped in the 15 minute interval
                       of the VC connection."
              ::= { atmVcIntervalEntry 15 }

    atmVcIntervalTotalDiscards OBJECT-TYPE
              SYNTAX       Gauge32
              MAX-ACCESS       read-only
              STATUS       current
              DESCRIPTION
                      "The total number of valid ATM cells discarded by
                      the traffic policing entity.  This includes cells
                      originally received with CLP=0 and CLP=1."
              ::= { atmVcIntervalEntry 16 }

    atmVcIntervalClp0Discards OBJECT-TYPE
              SYNTAX       Gauge32
              MAX-ACCESS       read-only
              STATUS       current
              DESCRIPTION
                      "The total number of valid ATM cells received with
                      CLP=0 an  discarded by the traffic policing
                      entity."
              ::= { atmVcIntervalEntry 17 }

    atmVcIntervalTotalCellOuts OBJECT-TYPE
              SYNTAX       Gauge32
              MAX-ACCESS       read-only
              STATUS       current
              DESCRIPTION
                      "The total number of valid ATM cells transmitted
                      by this VPL.  This includes both CLP=0 and CLP=1
                      cells."
              ::= { atmVcIntervalEntry 18 }


    atmVcIntervalClp0CellOuts OBJECT-TYPE
              SYNTAX       Gauge32
              MAX-ACCESS       read-only
              STATUS       current
              DESCRIPTION
                      "The total number of valid ATM cells transmitted
                      with CLP=0 by this VPL."
              ::= { atmVcIntervalEntry 19 }

    atmVcIntervalTaggedOuts OBJECT-TYPE
              SYNTAX       Gauge32
              MAX-ACCESS       read-only
              STATUS       current
              DESCRIPTION
                      "The total number of valid ATM cells tagged by the
                      traffic policing entity from CLP=0 to CLP=1 and
                      transmitted by this VPL."
              ::= { atmVcIntervalEntry 20 }

	atmVcIntervalPCR OBJECT-TYPE
              SYNTAX  Gauge32
              MAX-ACCESS  read-only
              STATUS  current
              DESCRIPTION
                      "The maximum traffic rate encountered in the
                      last interval of the VC connection (monitored once a second)
                      encountered by an ATM interface/VC in one of the previous 96,
                      individual 15  minute, intervals."
              ::= { atmVcIntervalEntry 21 }

	atmVcIntervalSCR OBJECT-TYPE
              SYNTAX  Gauge32
              MAX-ACCESS  read-only
              STATUS  current
              DESCRIPTION
                      "The average traffic rate during the last interval
                      of the VC connection, encountered by an ATM interface/VC
                      in one of the previous 96, individual 15 minute, intervals."
              ::= { atmVcIntervalEntry 22 }

	atmVcIntervalMCR OBJECT-TYPE
              SYNTAX  Gauge32
              MAX-ACCESS  read-only
              STATUS  current
              DESCRIPTION
                      "MCR - The minimum traffic rate encountered in the last
                      interval of the VC connection (monitored once a second)
                      encountered by an ATM interface/VC in one of the previous 96,
                      individual 15 minute, intervals."
              ::= { atmVcIntervalEntry 23 }


          -- The ATM VC Interval Table for Performance Management
          -- which contains various statistics
          -- collected by each ATM Interface/VC over the previous 24
          -- hours of operation.  The past 24 hours are broken into 96
          -- completed 15 minute intervals.

          atmVcPMIntervalTable OBJECT-TYPE
              SYNTAX  SEQUENCE OF AtmVcPMIntervalEntry
              MAX-ACCESS  not-accessible
              STATUS  current
              DESCRIPTION
                      "The ATM Vc Interval table for Performance Management."
              ::= { atmVcPerformance 4 }

--atmCESAAL1StatsTable OBJECT IDENTIFIER ::= {atmVcPerformance 5} (see hybCES.txt)

          atmVcPMIntervalEntry OBJECT-TYPE
              SYNTAX  AtmVcPMIntervalEntry
              MAX-ACCESS  not-accessible
              STATUS  current
              DESCRIPTION
                      "An entry in the ATM Vc Interval table for Performance
                       Management."
              INDEX   { ifIndex, atmVcPMIntervalVpi,
                        atmVcPMIntervalVci, atmVcPMIntervalDir, atmVcPMIntervalNumber }
              ::= { atmVcPMIntervalTable 1 }

          AtmVcPMIntervalEntry ::=
              SEQUENCE {
	              atmVcPMIntervalVpi
	                  Integer32,
	              atmVcPMIntervalVci
	                  Integer32,
	              atmVcPMIntervalDir
	                  INTEGER,
 	              atmVcPMIntervalNumber
                      Integer32,
                  atmVcPMIntervalTxClp01
                      Gauge32,
                  atmVcPMIntervalTxClp0
                      Gauge32,
                  atmVcPMIntervalRxClp01
                      Gauge32,
                  atmVcPMIntervalRxClp0
                      Gauge32,
                  atmVcPMIntervalErroredCells
                      Gauge32,
                  atmVcPMIntervalLostCells
                      Gauge32,
                  atmVcPMIntervalMisinsertedCells
                      Gauge32,
                  atmVcPMIntervalECB
                      Gauge32,
                  atmVcPMIntervalSECB
                      Gauge32,
                  atmVcPMIntervalES
                      Gauge32,
                  atmVcPMIntervalSES
                      Gauge32,
                  atmVcPMIntervalUAS
                      Gauge32,
	    atmVcPMIntervalQuality
	        INTEGER,
	    atmVcPMIntervalLastDayQuality
	        INTEGER
              }

          atmVcPMIntervalVpi OBJECT-TYPE
              SYNTAX  Integer32
              MAX-ACCESS  read-only
              STATUS  current
              DESCRIPTION
                      "The VPI of the VCL."
              ::= { atmVcPMIntervalEntry 1 }

          atmVcPMIntervalVci OBJECT-TYPE
              SYNTAX  Integer32
              MAX-ACCESS  read-only
              STATUS  current
              DESCRIPTION
                      "The VCI of the VCL."
              ::= { atmVcPMIntervalEntry 2 }

          atmVcPMIntervalDir OBJECT-TYPE
              SYNTAX  INTEGER {forward(2),
			                   backward(3) }
              MAX-ACCESS  read-only
              STATUS  current
              DESCRIPTION
                      "The direction of Performance Management."
              ::= { atmVcPMIntervalEntry 3 }

          atmVcPMIntervalNumber OBJECT-TYPE
              SYNTAX  Integer32 (1..96)
              MAX-ACCESS  read-only
              STATUS  current
              DESCRIPTION
                      "A number between 1 and 96, where 1 is the most
                      recently completed 15 minute interval and 96 is
                      the least recently completed 15 minutes interval
                      (assuming that all 96 intervals are valid)."
              ::= { atmVcPMIntervalEntry 4 }

          atmVcPMIntervalTxClp01 OBJECT-TYPE
              SYNTAX  Gauge32
              MAX-ACCESS  read-only
              STATUS  current
              DESCRIPTION
                      "The counter associated with the number of transmitted
                      CLP 0+1 cells, encountered by an ATM
                      interface/VC in one of the previous 96, individual 15
                      minute, intervals."
              ::= { atmVcPMIntervalEntry 5 }

          atmVcPMIntervalTxClp0 OBJECT-TYPE
              SYNTAX  Gauge32
              MAX-ACCESS  read-only
              STATUS  current
              DESCRIPTION
                      "The counter associated with the number of transmitted
                      CLP 0 cells, encountered by an ATM
                      interface/VC in one of the previous 96, individual 15
                      minute, intervals."
              ::= { atmVcPMIntervalEntry 6 }

          atmVcPMIntervalRxClp01 OBJECT-TYPE
              SYNTAX  Gauge32
              MAX-ACCESS  read-only
              STATUS  current
              DESCRIPTION
                      "The counter associated with the number of received
                      CLP 0+1 cells, encountered by an ATM
                      interface/VC in one of the previous 96, individual 15
                      minute, intervals."
              ::= { atmVcPMIntervalEntry 7 }

          atmVcPMIntervalRxClp0 OBJECT-TYPE
              SYNTAX  Gauge32
              MAX-ACCESS  read-only
              STATUS  current
              DESCRIPTION
                      "The counter associated with the number of received
                      CLP 0 cells, encountered by an ATM
                      interface/VC in one of the previous 96, individual 15
                      minute, intervals."
              ::= { atmVcPMIntervalEntry 8 }

          atmVcPMIntervalErroredCells OBJECT-TYPE
              SYNTAX  Gauge32
              MAX-ACCESS  read-only
              STATUS  current
              DESCRIPTION
                      "The counter associated with the number of Errored
                      cells, encountered by an ATM
                      interface/VC in one of the previous 96, individual 15
                      minute, intervals."
              ::= { atmVcPMIntervalEntry 9 }

          atmVcPMIntervalLostCells OBJECT-TYPE
              SYNTAX  Gauge32
              MAX-ACCESS  read-only
              STATUS  current
              DESCRIPTION
                      "The counter associated with the number of Lost
                      cells, encountered by an ATM
                      interface/VC in one of the previous 96, individual 15
                      minute, intervals."
              ::= { atmVcPMIntervalEntry 10 }

          atmVcPMIntervalMisinsertedCells OBJECT-TYPE
              SYNTAX  Gauge32
              MAX-ACCESS  read-only
              STATUS  current
              DESCRIPTION
                      "The counter associated with the number of Misinserted
                      cells, encountered by an ATM
                      interface/VC in one of the previous 96, individual 15
                      minute, intervals."
              ::= { atmVcPMIntervalEntry 11 }

          atmVcPMIntervalECB OBJECT-TYPE
              SYNTAX  Gauge32
              MAX-ACCESS  read-only
              STATUS  current
              DESCRIPTION
                      "The counter associated with the number of ECBs
                      encountered by an ATM
                      interface/VC in one of the previous 96, individual 15
                      minute, intervals."
              ::= { atmVcPMIntervalEntry 12 }

          atmVcPMIntervalSECB OBJECT-TYPE
              SYNTAX  Gauge32
              MAX-ACCESS  read-only
              STATUS  current
              DESCRIPTION
                      "The counter associated with the number of SECBs
                      encountered by an ATM
                      interface/VC in one of the previous 96, individual 15
                      minute, intervals."
              ::= { atmVcPMIntervalEntry 13 }

          atmVcPMIntervalES OBJECT-TYPE
              SYNTAX  Gauge32
              MAX-ACCESS  read-only
              STATUS  current
              DESCRIPTION
                      "The counter associated with the number of Errored
                      Seconds, encountered by an ATM
                      interface/VC in one of the previous 96, individual 15
                      minute, intervals."
              ::= { atmVcPMIntervalEntry 14 }

          atmVcPMIntervalSES OBJECT-TYPE
              SYNTAX  Gauge32
              MAX-ACCESS  read-only
              STATUS  current
              DESCRIPTION
                      "The counter associated with the number of Severely
                       Errored Seconds, encountered by an ATM
                       interface/VC in one of the previous 96, individual 15
                       minute, intervals."
              ::= { atmVcPMIntervalEntry 15 }

          atmVcPMIntervalUAS OBJECT-TYPE
              SYNTAX  Gauge32
              MAX-ACCESS  read-only
              STATUS  current
              DESCRIPTION
                      "The counter associated with the number of Unavailable
                       Seconds, encountered by an ATM
                       interface/VC in one of the previous 96, individual 15
                       minute, intervals."
              ::= { atmVcPMIntervalEntry 16 }

atmVcPMIntervalQuality OBJECT-TYPE
              		SYNTAX  INTEGER { normal(2), unacceptable(3) }
		MAX-ACCESS read-only
		STATUS current
		DESCRIPTION
		" If the number of errors per interval is superior to
		the atmNteUPLTCR value, the quality of service of
		the interval is declared as unacceptable."
		DEFVAL { normal }
	::= { atmVcPMIntervalEntry 17}

	    atmVcPMIntervalLastDayQuality OBJECT-TYPE
              		SYNTAX  INTEGER { normal(2), degraded(4) }
		MAX-ACCESS read-only
		STATUS current
		DESCRIPTION
		" If the number of errors per 24 hours is superior to
		the atmNteDPLTCR value, the quality of service of
		the day is declared as degraded."
		DEFVAL { normal }
	::= { atmVcPMIntervalEntry 18}




-- VC QoS Table

atmVcQoSTable OBJECT-TYPE
    SYNTAX  SEQUENCE OF AtmVcQoSEntry
    MAX-ACCESS  not-accessible
    STATUS  current
    DESCRIPTION
        "The ATM VP QoS table."
    ::= { atmVcPerformance 6 }

atmVcQoSEntry OBJECT-TYPE
    SYNTAX  AtmVcQoSEntry
    MAX-ACCESS  not-accessible
    STATUS  current
    DESCRIPTION
        "An entry in the ATM VP table."
    INDEX   { ifIndex, atmVclVpi, atmVclVci, atmVcQoSPeriodRef }
    ::= { atmVcQoSTable 1 }

AtmVcQoSEntry ::=
    SEQUENCE {
	          atmVcQoSPeriodRef     INTEGER,
	          atmVcQoSElapsedTime	Integer32,
	          atmVcQoSUAS		    Gauge32
             }


atmVcQoSPeriodRef OBJECT-TYPE
	SYNTAX  INTEGER
	      {
           currentPeriod  (1),
           lastPeriod     (2)
	      }
	MAX-ACCESS  read-only
	STATUS  current
	DESCRIPTION
	    "This object is an index that specifies which period of time, the next
	     2 objects refer to.
	     currentPeriod  - the period since last systemResetAllStatsCmd received or
	                      since Start-up (if no systemResetAllStatsCmd was received since
	                      Start-up) until now.
	     lastPeriod    - the period between last two commands of systemResetAllStatsCmd.
	                     - If only one command occurred since Start-up: the period between
	                       Start-up and last command.
	                     - If no command occurred since Start-up: this period will not
	                       actually exist. In this case, he following 5 objects will be 0."
	::= { atmVcQoSEntry 1 }

atmVcQoSElapsedTime OBJECT-TYPE
	SYNTAX  Integer32
	MAX-ACCESS  read-only
	STATUS  current
	DESCRIPTION
	    "Elapsed Time in seconds.
	     - for atmVcQoSPeriodRef = currentPeriod:
	       The period since last systemResetAllStatsCmd received or	since Start-up
	       (if no systemResetAllStatsCmd was received since	Start-up) until now.
	     - for atmVcQoSPeriodRef = lastPeriod:
	       The value of atmVcQoSElapsedTime when last systemResetAllStatsCmd
	       was received."
	::= { atmVcQoSEntry 2 }

atmVcQoSUAS OBJECT-TYPE
	SYNTAX  Gauge32
	MAX-ACCESS  read-only
	STATUS  current
	DESCRIPTION
	    "Number of Unavailable Seconds for the reference period (atmVcQoSPeriodRef)."
	::= { atmVcQoSEntry 3 }

-- VC PM QoS Table

atmVcPMQoSTable OBJECT-TYPE
     SYNTAX  SEQUENCE OF AtmVcPMQoSEntry
     MAX-ACCESS  not-accessible
     STATUS  current
     DESCRIPTION
         "The PM VC QoS table."
     ::= { atmVcPerformance 7 }

atmVcPMQoSEntry OBJECT-TYPE
     SYNTAX  AtmVcPMQoSEntry
     MAX-ACCESS  not-accessible
     STATUS  current
     DESCRIPTION
         "An entry in the VC PM QoS table."
     INDEX   { ifIndex, atmVclVpi, atmVclVci, atmVcPMQoSDirection ,atmVcPMQoSPeriodRef }
     ::= { atmVcPMQoSTable 1 }

AtmVcPMQoSEntry ::=
     SEQUENCE {
               atmVcPMQoSDirection	   INTEGER,
	           atmVcPMQoSPeriodRef	   INTEGER,
	           atmVcPMQoSCLR		   Gauge32,
	           atmVcPMQoSCER           Gauge32,
	           atmVcPMQoSCMR           Gauge32
              }

atmVcPMQoSDirection OBJECT-TYPE
     SYNTAX  INTEGER
         {
          forward(2),
		  backward(3)
		 }
      MAX-ACCESS  read-only
      STATUS  current
      DESCRIPTION
          "The direction of performance management."
      ::= { atmVcPMQoSEntry 1 }

atmVcPMQoSPeriodRef OBJECT-TYPE
	SYNTAX  INTEGER
	      {
           currentPeriod  (1),
           lastPeriod     (2)
	      }
	MAX-ACCESS  read-only
	STATUS  current
	DESCRIPTION
	"This object is an index that specifies which period of time, the next
	 5 objects refer to.
	 currentPeriod - the period since last systemResetAllStatsCmd received or
	                 since Start-up (if no systemResetAllStatsCmd was received since
	                 Start-up) until now.
	 lastPeriod    - the period between last two commands of systemResetAllStatsCmd.
	                 - If only one command occurred since Start-up: the period between
	                   Start-up and last command.
	                 - If no command occurred since Start-up: this period will not
	                   actually exist. In this case, he following 5 objects will be 0."
	::= { atmVcPMQoSEntry 2 }


atmVcPMQoSCLR OBJECT-TYPE
	SYNTAX  Gauge32
	MAX-ACCESS  read-only
	STATUS  current
	DESCRIPTION
	"Cell Loss Ratio counter for the reference period (atmVcPMQoSPeriodRef)-
	defined in accordance with I.356 , in %.
	The value will be multipuled by 100."
	::= { atmVcPMQoSEntry 3 }

atmVcPMQoSCER OBJECT-TYPE
	SYNTAX  Gauge32
	MAX-ACCESS  read-only
	STATUS  current
	DESCRIPTION
	"Cell Error Ratio counter for the reference period (atmVcPMQoSPeriodRef)
	defined in accordance with I.356 , in %.
	The value will be multipuled by 100."
	::= { atmVcPMQoSEntry 4 }

atmVcPMQoSCMR OBJECT-TYPE
	SYNTAX  Gauge32
	MAX-ACCESS  read-only
	STATUS  current
	DESCRIPTION
	"Cell Miss-insertion Ratio counter for the reference period (atmVcPMQoSPeriodRef)
	defined in accordance with I.356 , cells/sec ."
	::= { atmVcPMQoSEntry 5 }

--VC Shaper Statistics Table
atmVcShaperStatTable OBJECT-TYPE
              SYNTAX  SEQUENCE OF AtmVcShaperStatEntry
              MAX-ACCESS  not-accessible
              STATUS  current
              DESCRIPTION
                      "The ATM VC shaper statistics table."
              ::= { atmVcPerformance 8 }

          atmVcShaperStatEntry OBJECT-TYPE
              SYNTAX  AtmVcShaperStatEntry
              MAX-ACCESS  not-accessible
              STATUS  current
              DESCRIPTION
                      "An entry in the ATM VC shaper statistics table."
              INDEX   { ifIndex, atmVclVpi, atmVclVci }
              ::= { atmVcShaperStatTable 1 }

AtmVcShaperStatEntry ::=
     SEQUENCE {
	           atmVcShaperDiscarded          Counter32,
               atmVcShaperOccupation 		 Integer32,
               atmVcShaperMaxOccupation 	 Integer32,
               atmVcShaperLevel 			 INTEGER,
               atmVcShaperEpdDropped 		 Counter32,
               atmVcShaperTotalEpdDropped 	 Counter32
              }

atmVcShaperDiscarded  OBJECT-TYPE
              SYNTAX  Counter32
              MAX-ACCESS  read-only
              STATUS  current
              DESCRIPTION
                   "The number of Cells that were discarded in the shaper on that VCC due
                    to buffer overflow. This counter counts till it reaches its MAX value
                    (20 bits) and then rolls over."
              ::= { atmVcShaperStatEntry 1 }

atmVcShaperOccupation OBJECT-TYPE
              SYNTAX  Integer32
              MAX-ACCESS  read-only
              STATUS  current
              DESCRIPTION
                   "The number of Cells that are currently stored in the buffer.
                   This parameter is limited to 20 bits."
              ::= { atmVcShaperStatEntry 2}

atmVcShaperMaxOccupation OBJECT-TYPE
              SYNTAX  Integer32
              MAX-ACCESS  read-only
              STATUS  current
              DESCRIPTION
                   "The Maximum number of Cells that were stored in the buffer,
                   since this VC was activated.	This parameter is limited to 20 bits."
              ::= { atmVcShaperStatEntry 3}

atmVcShaperLevel OBJECT-TYPE
	          SYNTAX  INTEGER {
	                 empty   (1),
	                 full    (2),
	                 below   (3),
	                 above   (4)
                 	}
              MAX-ACCESS  read-only
              STATUS  current
              DESCRIPTION
                   "The occupation of the buffer according to a predefined threshold.
                   empty - buffer is Empty
                   full  - buffer is Full
                   below - buffer is Below the threshold
                   above - buffer is Above the threshold. This is also the trigger to
                   start EPD\PPD mechanism, if set for the VCC."
              ::= { atmVcShaperStatEntry 4}

atmVcShaperEpdDropped OBJECT-TYPE
              SYNTAX  Counter32
              MAX-ACCESS  read-only
              STATUS  current
              DESCRIPTION
                   "The number of Cells that were dropped in the shaper on that VCC
                   due to EPD\PPD mechanism in the last second.
                   This parameter is limited to 24 bits.
                   Applicable for a EPD/PPD VC only."
              ::= { atmVcShaperStatEntry 5}

atmVcShaperTotalEpdDropped OBJECT-TYPE
              SYNTAX  Counter32
              MAX-ACCESS  read-only
              STATUS  current
              DESCRIPTION
                   "The Total number of Cells that were dropped in the shaper on that
                   VPC due to EPD\PPD mechanism in the last 15 minutes. This counter
                   automatically reset itself every 15 minutes.
                   Applicable for a EPD/PPD VC only."
              ::= { atmVcShaperStatEntry 6}



-- New
-- The agent will keep in this group the date & time corresponding to each interval.
atmIntervalDateTable OBJECT-TYPE
	SYNTAX  SEQUENCE OF AtmIntervalDateEntry
	MAX-ACCESS  not-accessible
              STATUS  current
              DESCRIPTION
	"The agent will keep in this group the date & time
	 corresponding to each interval."
             ::=  {atmPerfHistory 3}

 atmIntervalDateEntry OBJECT-TYPE
              SYNTAX AtmIntervalDateEntry
              MAX-ACCESS  not-accessible
              STATUS  current
              DESCRIPTION
                      "The date & time for the given interval."
              INDEX   { atmIntervalDateInterval }
              ::= { atmIntervalDateTable 1 }

         AtmIntervalDateEntry ::=
              SEQUENCE {
 		atmIntervalDateInterval
                      		Integer32,
		atmIntervalDateDate
			DisplayString,
                  	atmIntervalDateTime
                      		DisplayString
	}

	atmIntervalDateInterval  OBJECT-TYPE
              		SYNTAX  Integer32 (1..96)
		MAX-ACCESS read-only
		STATUS current
		DESCRIPTION
		" The interval number defining this entry."
	::= { atmIntervalDateEntry 1}

	atmIntervalDateDate OBJECT-TYPE
              		SYNTAX DisplayString
		MAX-ACCESS read-only
		STATUS current
		DESCRIPTION
		"The date corresponding to this interval."
	::= { atmIntervalDateEntry 2}

	atmIntervalDateTime OBJECT-TYPE
              		SYNTAX DisplayString
		MAX-ACCESS read-only
		STATUS current
		DESCRIPTION
		"The time corresponding to this interval."
	::= { atmIntervalDateEntry 3}



--atmNte  OBJECT IDENTIFIER  ::=  {radAtm 3}

atmNteSys  OBJECT IDENTIFIER  ::=  {atmNte 1}

atmNteSysConfig  OBJECT IDENTIFIER  ::=  {atmNteSys 1}

          atmNteManagerTable OBJECT-TYPE
              SYNTAX  SEQUENCE OF AtmNteManagerEntry
              MAX-ACCESS  not-accessible
              STATUS  current
              DESCRIPTION
                      "The Manager Table includes all the NMSs that
                       receive traps from this agent. A single manager
                       can receive traps on more than one PVC. The PVCs
                       must be from the four allowed. The agent will set
                       implicitly the correct ifIndex, VPI, VCI values to
                       all relevant entries in the table when the user changes
                       them for one of the PVCs."
              ::= { atmNteSysConfig 1 }

          atmNteManagerEntry OBJECT-TYPE
              SYNTAX  AtmNteManagerEntry
              MAX-ACCESS  not-accessible
              STATUS  current
              DESCRIPTION
                      "A single manager and the PVC for receiving traps."
              INDEX   { atmNteManagerIP, atmNteManagerPvc}
              ::= { atmNteManagerTable 1 }

          AtmNteManagerEntry ::=
              SEQUENCE {
                  atmNteManagerIP
                      IpAddress,
				  atmNteManagerPvc
				      Integer32,
                  atmNteManagerIfIndex
                      Integer32,
                  atmNteManagerVpi
                      Integer32,
                  atmNteManagerVci
                      Integer32,
                  atmNteManagerTrapMask
                      Integer32,
                  atmNteManagerRowStatus
                      RowStatus,
                  atmNteManagerNextHop
                      IpAddress,
				  atmNteManagerVlanSupport
					  INTEGER,
				  atmNteManagerVlanIdentifier
					  Integer32,
				  atmNteManagerVlanFramePriority
					  Integer32
              }

          atmNteManagerIP OBJECT-TYPE
              SYNTAX  IpAddress
              MAX-ACCESS  read-only
              STATUS  current
              DESCRIPTION
                      "The IP address of the NMS."
              ::= { atmNteManagerEntry 1 }

          atmNteManagerPvc OBJECT-TYPE
              SYNTAX  Integer32
              MAX-ACCESS  read-only
              STATUS  current
              DESCRIPTION
                      "A PVC index. The range is 1..8. There are four PVCs
                       on the User Port and four PVCs on the Network Port.
                       The default VPI, VCI values are specified below."
              ::= { atmNteManagerEntry 2 }

          atmNteManagerIfIndex OBJECT-TYPE
              SYNTAX  Integer32
              MAX-ACCESS  read-create
              STATUS  current
              DESCRIPTION
                      "The ATM interface index of the management port."
              ::= { atmNteManagerEntry 3 }

          atmNteManagerVpi OBJECT-TYPE
              SYNTAX  Integer32
              MAX-ACCESS  read-create
              STATUS  current
              DESCRIPTION
                      "The VPI of the management VCL. Default: 0."
              ::= { atmNteManagerEntry 4 }

          atmNteManagerVci OBJECT-TYPE
              SYNTAX  Integer32
              MAX-ACCESS  read-create
              STATUS  current
              DESCRIPTION
                      "The VCI of the management VCL. Defaults: 32,33,34,35."
              ::= { atmNteManagerEntry 5 }

          atmNteManagerTrapMask OBJECT-TYPE
         	SYNTAX  Integer32
        	MAX-ACCESS  read-create
        	STATUS current
        	DESCRIPTION
               "The value of this attribute determines the type of traps the
                agent should mask and not send to this NMS. The
                value is differently determined for different products. There are
                mainly two methods:
              - an integer number, specifying the traps' severity.
              - a sum of 2**n, where n is a bit assigned to a certain
                masked trap group.
                User should consult the product specification, to find out
                the method employed."
        	::= { atmNteManagerEntry 6 }

atmNteManagerRowStatus OBJECT-TYPE
              SYNTAX RowStatus
              MAX-ACCESS read-create
              STATUS current
              DESCRIPTION
                 "Creation/Deletion of rows in the table."
              ::= {atmNteManagerEntry 7}

atmNteManagerNextHop OBJECT-TYPE
              SYNTAX  IpAddress
              MAX-ACCESS  read-create
              STATUS  current
              DESCRIPTION
                      "This parameter is relevant to Ethernet out of band
                      host only (PVC=10).
                      The Next Hop IP address of the entry route."
              ::= { atmNteManagerEntry 8 }

atmNteManagerVlanSupport OBJECT-TYPE
    		SYNTAX       INTEGER {
		    no		(2),
		    yes	    (3)
		    }
		    MAX-ACCESS  read-create
		    STATUS  current
		    DESCRIPTION
		    "VLAN support (Tagging).
		     no - No support to VLAN.
		     yes - 4 VLAN bytes will be added to the frame."
	    ::= { atmNteManagerEntry 9}

atmNteManagerVlanIdentifier OBJECT-TYPE
 		  SYNTAX  Integer32
 	      MAX-ACCESS  read-create
    	  STATUS  current
	      DESCRIPTION
    	  "VLAN ID. Range is 0..4095."
     	::= { atmNteManagerEntry 10 }

atmNteManagerVlanFramePriority OBJECT-TYPE
	     SYNTAX  Integer32
	     MAX-ACCESS  read-create
	     STATUS  current
	     DESCRIPTION
	     "VLAN Frame priority.Range is 0..7."
	     ::= { atmNteManagerEntry 11 }



atmNteUPLTCR OBJECT-TYPE
              SYNTAX Integer32
              MAX-ACCESS read-write
              STATUS current
              DESCRIPTION
                 "The Unacceptable ES Limit threshold for Performance Management."
              ::= {atmNteSysConfig 2}

atmNteDPLTCR OBJECT-TYPE
              SYNTAX Integer32
              MAX-ACCESS read-write
              STATUS current
              DESCRIPTION
                 "The Degraded ES Limit threshold for Performance Management."
              ::= {atmNteSysConfig 3}

atmNteSysLogClearAll OBJECT-TYPE
              SYNTAX INTEGER { off(2), clear(3) }
              MAX-ACCESS read-write
              STATUS current
              DESCRIPTION
                 "Setting the variable to clear(3) removes all entries in the
	              Log Buffer of the agent. The agent will immediately reset
	              the variable to off(2)."
              ::= {atmNteSysConfig 4}

atmNteUSESLTCR OBJECT-TYPE
              SYNTAX Integer32
              MAX-ACCESS read-write
              STATUS current
              DESCRIPTION
	             "The Unacceptable SES Limit threshold for Performance Management."
              ::= {atmNteSysConfig 5}

atmNteDSESLTCR OBJECT-TYPE
              SYNTAX Integer32
              MAX-ACCESS read-write
              STATUS current
              DESCRIPTION
                 "The Degraded ES Limit threshold for Performance Management."
              ::= {atmNteSysConfig 6}


atmNteProtection OBJECT IDENTIFIER  ::= { atmNteSysConfig  8 }

atmNteProtectionMode OBJECT-TYPE
               SYNTAX  INTEGER {
                          off       (1),
                          mspOn     (2),
						  pathOn    (3),
						  mspUniOn  (4),
						  mspOneToN (5)
                      }
               MAX-ACCESS  read-write
               STATUS  current
               DESCRIPTION
               "Protection  Mode.
               MspOn - Multiplex section protection.
               pathOn - High order path protection.
               mspUniOn - Multiplex section Uni-directional protection.
               mspOneToN - Multiplex section protection."
               ::= { atmNteProtection 1 }

atmNteProtectionWorkingLink OBJECT-TYPE
               SYNTAX  INTEGER {
                          trunk1(2),
                          trunk2(3)
                      }
               MAX-ACCESS  read-write
               STATUS  current
               DESCRIPTION
               "Selects the working link when atmNteProtectionMode is off."
               ::= { atmNteProtection 2 }

atmNteProtectionSwitchLink OBJECT-TYPE
               SYNTAX  INTEGER {
                          off(1),
                          forceSwitch(2)
                      }
               MAX-ACCESS  read-write
               STATUS  current
               DESCRIPTION
               "ForceSwitch - will force Switching from the working link to the backup link.
                Afterwards the agent will set atmNteProtectionSwitchLink back to off(1).
                atmNteProtectionMode must be either mspOn or pathOn."
               ::= { atmNteProtection 3 }

atmNteConfOam OBJECT IDENTIFIER  ::= { atmNteSysConfig  9 }

atmNteConfOamSupport OBJECT-TYPE
               SYNTAX  INTEGER {
                          intermediate(1),
                          segmentTermination(2),
                          endToEndTermination(3),
						  vpEndToEndVcSegment(4)
                      }
               MAX-ACCESS  read-write
               STATUS  current
               DESCRIPTION
               "OAM support  mode, which determines the device location
                in a segment wise."
               ::= { atmNteConfOam 1 }

atmNteConfOamTransmission OBJECT IDENTIFIER  ::= { atmNteConfOam  2 }

atmNteConfOamAIS OBJECT-TYPE
               SYNTAX  INTEGER {
                          none(1),
                          user(2),
                          network(3),
                          both(4)
                      }
               MAX-ACCESS  read-write
               STATUS  current
               DESCRIPTION
               "Defines if a F4 segment OAM cell is transmitted due
                to problems in the other port, i.e. physical layer
                alarm or F4 defect. This is valid only when the ACE101
                has ATM UNI interfaces in both sides and is configured
                for 'Non-Intrusive' mode.
                none - AIS is not sent to any of the ports.
                user - F4 AIS will be sent toward the user when defect
                       is detected in the network port.
                network - F4 AIS will be sent toward the network when
                          defect is detected in the user port.
                both - F4 AIS will be sent toward the network when defect
                       is detected in the user port and toward the user
                       when defect is detected in the network port."
               ::= { atmNteConfOamTransmission 1 }

atmNteConfOamRDI OBJECT-TYPE
               SYNTAX  INTEGER {
                          none(1),
                          user(2),
                          network(3),
                          both(4)
                      }
               MAX-ACCESS  read-write
               STATUS  current
               DESCRIPTION
               "Defines if an F4 OAM RDI cell is transmitted due to
                physical layer problems in the port (in addition to
                F4 RDI cells transmitted due to ATM layer problems).
                The type of F4 RDI (Segment or End-to-End) is according
                to the ACE-101 OAM mode.
                For example, If it is enabled for Network port, then
                physical layer defect will initiate the transmission
                of F4 RDI cell back to the trunk."
               ::= { atmNteConfOamTransmission 2 }

atmNteConfOamAddressing OBJECT IDENTIFIER  ::= { atmNteConfOam  3 }

atmNteConfLoopbackAddMode OBJECT-TYPE
             		SYNTAX INTEGER{
                          off(1),
                          on(2)
                      }
            	    MAX-ACCESS read-write
             		STATUS current
             		DESCRIPTION
                    	 "Loopback addressing mode.
                    	  on  - will enable  loopback addressing.
                    	  off - will disable loopback addressing."
             ::= { atmNteConfOamAddressing  1 }

atmNteConfLoopbackSourceAdd OBJECT-TYPE
             		SYNTAX OCTET STRING  (SIZE(2..20))
             		MAX-ACCESS read-write
             		STATUS current
             		DESCRIPTION
                    	 " Loopback source address. This field is relevant when
                                atmNteConfOamAddMode is on."
             ::= { atmNteConfOamAddressing  2 }

--OAM Table
atmNteConfOamIfTable OBJECT-TYPE
              SYNTAX  SEQUENCE OF AtmNteConfOamIfEntry
              MAX-ACCESS  not-accessible
              STATUS  current
              DESCRIPTION
                      "OAM support per ATM interface."
               ::= { atmNteConfOam 4 }

atmNteConfOamIfEntry OBJECT-TYPE
              SYNTAX  AtmNteConfOamIfEntry
              MAX-ACCESS  not-accessible
              STATUS  current
              DESCRIPTION
                      "."
              INDEX   { ifIndex }
              ::= { atmNteConfOamIfTable 1 }

AtmNteConfOamIfEntry ::=
            SEQUENCE {
                atmNteConfOamIfAisRdi   INTEGER
			    }

     atmNteConfOamIfAisRdi OBJECT-TYPE
                SYNTAX  INTEGER {
                           off(1),
                           on (2)
                }
                MAX-ACCESS  read-write
                STATUS  current
                DESCRIPTION
                "This parameter controls the generation of F4/F5
                AIS and RDI due to lower order problems such as physical
                layer problems.

                For AIS: Defines if F4/F5 AIS cell is transmitted due
                 to problems such as physical layer alarm or F4/F5 defect.
                 This is applicable for all  ports .
                 off - Problems in this port  will not trigger F4/F5 AIS
                       transmition to the ajacent port (e.g. from USER to
                       NETWORK) of a VPC/VCC.
                 on  - Problems in this port will trigger F4/F5 AIS
                       transmition to the ajacent port (e.g. from USER
                       to NETWORK) of a VPC/VCC.

                For RDI: Defines if F4/F5 RDI cell will be transmitted due to
                 physical layer problems in that port (in addition to
                 F4/F5 RDI cells transmitted due to ATM layer problems).
                 For example, If it is enabled for Network port, then
                 physical layer defect will initiate the transmission
                 of F4/F5 RDI cell back to the trunk.

                 The type of F4/F5 (Segment or End-to-End) is according
                 to the configuration of the VPC/VCC."
                 ::= { atmNteConfOamIfEntry 1 }


atmNteConfCAC OBJECT IDENTIFIER  ::= { atmNteSysConfig  10 }

atmNteConfCACMode OBJECT-TYPE
               SYNTAX  INTEGER {
 		disable(1),
		enable(2)
                }
               MAX-ACCESS  read-write
               STATUS  current
               DESCRIPTION
               "CAC support  mode.

               For ACE2002, the following are the applicable values:
               disable(1), enable(2), 10 - 1000."
               ::= { atmNteConfCAC 1 }

atmNteHostIfTable OBJECT-TYPE
              SYNTAX  SEQUENCE OF AtmNteHostIfEntry
              MAX-ACCESS  not-accessible
              STATUS  current
              DESCRIPTION
                      "Host IP interface table."
              ::= { atmNteSysConfig 11 }

atmNteHostIfEntry OBJECT-TYPE
              SYNTAX  AtmNteHostIfEntry
              MAX-ACCESS  not-accessible
              STATUS  current
              DESCRIPTION
                      "."
              INDEX   { atmNteHostPvcIndex }
              ::= { atmNteHostIfTable 1 }

AtmNteHostIfEntry ::=
            SEQUENCE {
              atmNteHostPvcIndex
                    Integer32,
              atmNteHostIP
                    IpAddress,
              atmNteHostMask
                    IpAddress,
              atmNteHostAtmIfIndex
                    Integer32,
              atmNteHostVpi
                    Integer32,
              atmNteHostVci
                    Integer32,
              atmNteHostRowStatus
                    RowStatus,
              atmNteHostRdnVpi
                    Integer32,
              atmNteHostRdnVci
                    Integer32
              }


atmNteHostPvcIndex OBJECT-TYPE
              SYNTAX  Integer32
              MAX-ACCESS  read-only
              STATUS  current
              DESCRIPTION
                      "A PVC index. The range is 1..8. There are four PVCs
                       on the User Port and four PVCs on the Network Port."
              ::= { atmNteHostIfEntry 1 }

atmNteHostIP OBJECT-TYPE
              SYNTAX  IpAddress
              MAX-ACCESS  read-create
              STATUS  current
              DESCRIPTION
                      "The host interface IP address."
              ::= { atmNteHostIfEntry 2 }

atmNteHostMask OBJECT-TYPE
              SYNTAX  IpAddress
              MAX-ACCESS  read-create
              STATUS  current
              DESCRIPTION
                      "The host interface subnet mask."
              ::= { atmNteHostIfEntry 3 }

atmNteHostAtmIfIndex OBJECT-TYPE
              SYNTAX  Integer32
              MAX-ACCESS  read-create
              STATUS  current
              DESCRIPTION
                      "ATM interface index. Will be 1
                       for user port, and 2 for network port."
              ::= { atmNteHostIfEntry 4 }

atmNteHostVpi OBJECT-TYPE
              SYNTAX  Integer32
              MAX-ACCESS  read-create
              STATUS  current
              DESCRIPTION
                      "VPI of the PVC connected to that host interface."
              ::= { atmNteHostIfEntry 5 }

atmNteHostVci OBJECT-TYPE
              SYNTAX  Integer32
              MAX-ACCESS  read-create
              STATUS  current
              DESCRIPTION
                      "VCI of the PVC connected to that host interface."
              ::= { atmNteHostIfEntry 6 }

atmNteHostRowStatus OBJECT-TYPE
              SYNTAX  RowStatus
              MAX-ACCESS  read-create
              STATUS  current
              DESCRIPTION
                 "Creation/Deletion of rows in the table."
              ::= { atmNteHostIfEntry 7 }

atmNteHostRdnVpi OBJECT-TYPE
              SYNTAX  Integer32
              MAX-ACCESS  read-create
              STATUS  current
              DESCRIPTION
                      "The VPI of the redundant management VCL.
                      This parameter is applicable only if atmNteRdnManagement=enable(3). "
              ::= { atmNteHostIfEntry 8 }

atmNteHostRdnVci OBJECT-TYPE
              SYNTAX  Integer32
              MAX-ACCESS  read-create
              STATUS  current
              DESCRIPTION
                      "The VCI of the redundant management VCL.
                      This parameter is applicable only if atmNteRdnManagement=enable(3). "
              ::= { atmNteHostIfEntry 9 }

atmNteShaperMode OBJECT-TYPE
               SYNTAX  INTEGER {
 		         normal		(1),
		         group		(2),
		         aggregate	(3),
				 vpInbandMng (4)
                }
               MAX-ACCESS  read-write
               STATUS  current
               DESCRIPTION
               "Shaper Mode.
               vpInbandMng - Vcc within a Vp for management."
               ::= { atmNteSysConfig 12 }


atmNteOutputRate OBJECT-TYPE
               SYNTAX  Integer32
               MAX-ACCESS  read-write
               STATUS  current
               DESCRIPTION
               "Aggregate shaping output rate in Cells per Seconds units.
               Default value is the Network port rate."
               ::= { atmNteSysConfig 13 }

atmNteTosMode OBJECT-TYPE
               SYNTAX  INTEGER {
 		         notApplicable   (1),
		         disable		 (2),
		         enable	         (3)
                }
               MAX-ACCESS  read-write
               STATUS  current
               DESCRIPTION
               "TOS Mode."
               ::= { atmNteSysConfig 14 }

atmNteTosMask OBJECT-TYPE
               SYNTAX  OCTET STRING	(SIZE(1))
               MAX-ACCESS  read-write
               STATUS  current
               DESCRIPTION
               "This parameter determines the seqence of bits that will be used for TOS.
               This parameter is applicable only if atmNteTosMode = enable.
               Valid only for IP-TOS process."
               ::= { atmNteSysConfig 15 }

atmNteTosHighPriority OBJECT-TYPE
               SYNTAX  OCTET STRING (SIZE(8))
               MAX-ACCESS  read-write
               STATUS  current
               DESCRIPTION
               "Priorities options are High or Low.
			   High priority will be represented by bit = 1.
			   Low  priority will be represented by bit = 0.
			   Each TOS value will be represented by the bit location.
			   For example, the string for TOS 2, 9, 15 with High priority,
			   will be:

			   |0000 0000|... ...|0000 0000|1000 0010|0000 0100|
												...98 7654 3210	  (Bit  #)

					8	   ...		  3			2		  1		  (Byte #)."
               ::= { atmNteSysConfig 16 }

atmNtePlugAndPlayActivity OBJECT-TYPE
               SYNTAX  INTEGER {
 		         disable   (1),
		         offline   (2),
		         online	   (3)
                }
               MAX-ACCESS  read-write
               STATUS  current
               DESCRIPTION
               "Activity control for Manager Plug And Play.
               disable - disable the feature.
               offline - Automatic learn IP address into offline memory.
               online  - Automatic learn IP address into online memory. "
               ::= { atmNteSysConfig 17 }

atmNteSlotUsage OBJECT-TYPE
               SYNTAX  INTEGER {
 		         notApplicable   (1),
		         user		     (2),
		         network	     (3)
                }
               MAX-ACCESS  read-write
               STATUS  current
               DESCRIPTION
               "Applicable to ace2002. Slot 2 might be configured
               as user slot or as network slot."
               ::= { atmNteSysConfig 18 }

atmNteConnectionsMaxNumber OBJECT-TYPE
               SYNTAX  INTEGER {
                       notApplicable(1),
                       max1024      (2),
                       max2048      (3)
               }
              MAX-ACCESS  read-write
              STATUS  current
              DESCRIPTION
                      "The MAX number of connections supported by system.
                       Setting this parameter will affect the number of MAX intervals supported.
                       This parameter will affect the system only after reset.
					   Changing this parameter from high value to a low value, will be accepted by agent
					   only if the actual used connection <= the desired connection Max number.
                       Applicable to ace2002. "
              ::= { atmNteSysConfig 19 }

atmNteDefaultVpi OBJECT-TYPE
               SYNTAX  Integer32
               MAX-ACCESS  read-write
               STATUS  current
               DESCRIPTION
                       "Default Vpi for management."
              ::= { atmNteSysConfig 20 }

atmNteDefaultVci OBJECT-TYPE
               SYNTAX  Integer32
               MAX-ACCESS  read-write
               STATUS  current
               DESCRIPTION
               "Default Vci for management."
               ::= { atmNteSysConfig 21 }

atmNteReservedVpi    OBJECT-TYPE
              SYNTAX    Integer32  (0..255)
              MAX-ACCESS    read-write
              STATUS    current
              DESCRIPTION
                   "Internal use VPI, where shaperMode=vpInbandMng."
              ::= { atmNteSysConfig 22 }

atmNteRdnManagement OBJECT-TYPE
                SYNTAX  INTEGER {
                      disabled (2),
                      enabled  (3)
                 }
                MAX-ACCESS  read-only
                STATUS  current
                DESCRIPTION
                "The redundancy management status."
              ::= { atmNteSysConfig 23 }

atmNtePlugAndPlayIfIndex OBJECT-TYPE
                SYNTAX  InterfaceIndex
                MAX-ACCESS  read-write
                STATUS  current
                DESCRIPTION
                "The ifIndex of the Plug and Play VCC."
              ::= { atmNteSysConfig 24 }

atmNteLoopbackTimeout OBJECT-TYPE
                SYNTAX  Integer32
                MAX-ACCESS  read-write
                STATUS  current
                DESCRIPTION
                "The Loopback state timeout in minutes. A value of
                zero means no timeout (for ever). Default is 5 min."
              ::= { atmNteSysConfig 25 }

atmNteOamTable OBJECT-TYPE
    SYNTAX  SEQUENCE OF AtmNteOamEntry
    MAX-ACCESS  not-accessible
    STATUS  current
    DESCRIPTION
    "This table is a static table, which is created by agent once
	upon initialization. The created entries are actually, only the
	supported OAM features.
	This table enables addition of new features by adding new entries
	rather than adding scalar parameters.
    An OAM feature is defined by the indexes values combination."
              ::= { atmNteSysConfig 26 }

atmNteOamEntry OBJECT-TYPE
    SYNTAX  AtmNteOamEntry
    MAX-ACCESS  not-accessible
    STATUS  current
    DESCRIPTION
    "An entry in the OAM table.
     Each entry in this table will indicate a special OAM."
    INDEX {atmNteOamMode, atmNteOamCellType, atmNteOamLevel}
    ::= { atmNteOamTable 1 }

AtmNteOamEntry ::=
    SEQUENCE {
    atmNteOamMode
    INTEGER,
    atmNteOamCellType
    INTEGER,
	atmNteOamLevel
	INTEGER,
	atmNteOamEnable
	INTEGER
    }

atmNteOamMode OBJECT-TYPE
    SYNTAX  INTEGER
    {
     endToEnd  (1)
    }
    MAX-ACCESS  read-only
    STATUS  current
    DESCRIPTION
    "The OAM cell path.
    endToEnd(1) - the entire path."
    ::= { atmNteOamEntry 1 }

atmNteOamCellType OBJECT-TYPE
    SYNTAX  INTEGER
    {
     aisAndRdi (1),
	 loopback  (2)
    }
    MAX-ACCESS  read-only
    STATUS  current
    DESCRIPTION
    "This object indicates a unique Indication Signal.
     aisAndRdi(1) - Alarm Indication Signal (AIS) and
                     Remote Defect Indication (RDI) cell.
     loopback(2) - Loopback cell."
    ::= { atmNteOamEntry 2 }

atmNteOamLevel OBJECT-TYPE
    SYNTAX  INTEGER
    {
--	 f4 (2),
	 f5 (3)
    }
    MAX-ACCESS  read-only
    STATUS  current
    DESCRIPTION
    "The level of the OAM cell.
--    	 f4 (2) - VP level,
	     f5 (3)	- VC level."
    ::= { atmNteOamEntry 3 }

atmNteOamEnable OBJECT-TYPE
    SYNTAX  INTEGER
    {
     disable      (2),
	 enable       (3)
    }
    MAX-ACCESS  read-write
    STATUS  current
    DESCRIPTION
    "This parameter determines if the specified OAM cells
    will be enabled."
    ::= { atmNteOamEntry 4 }


atmNteSysInfo  OBJECT IDENTIFIER  ::=  {atmNteSys 2}

          atmNteIdTable OBJECT-TYPE
              SYNTAX  SEQUENCE OF AtmNteIdEntry
              MAX-ACCESS  not-accessible
              STATUS  current
              DESCRIPTION
                      "The IDs of the cards and of the system."
              ::= { atmNteSysInfo 1 }

          atmNteIdEntry OBJECT-TYPE
              SYNTAX  AtmNteIdEntry
              MAX-ACCESS  not-accessible
              STATUS  current
              DESCRIPTION
                      "."
              INDEX   { atmNteIdIndex}
              ::= { atmNteIdTable 1 }

          AtmNteIdEntry ::=
              SEQUENCE {
	              atmNteIdIndex
	                  Integer32,
                  atmNteUnitId
                      Integer32,
                  atmNteUnitVersion
                      DisplayString,
                  atmNteCardType
                      INTEGER
              }

          atmNteIdIndex OBJECT-TYPE
              SYNTAX  Integer32
              MAX-ACCESS  read-only
              STATUS  current
              DESCRIPTION
                      "An Index of the Unit ID table.
                       The following units have IDs in this table:
                       1 - System
                       2 - ATM Board
                       3 - User Card
                       4 - Trunk 1 card
                       5 - Trunk 2 card
	                   6 - Shaper
                       7 - Clock Unit
                       8 -  Slot 1 card
                       9 -  Slot 2 card
                       10 - Slot 3 card
                       11 - Slot 4 card
                       12 - Fan1.
                       13 - Fan2."
              ::= { atmNteIdEntry 1 }

          atmNteUnitId OBJECT-TYPE
              SYNTAX  Integer32
              MAX-ACCESS  read-only
              STATUS  current
              DESCRIPTION
                      "The ID of the Unit.
                      For index = 6, the id will describe the validity
                       of a shaper in the system: 0 - Shaper Not exist
                                                  1 - Shaper exist.
                      For index = 7, the id will describe the validity
                       of a clock in the system: 0 - Clock Not exist
                                                  1 - Clock exist.
												  2- Clock exist but failed.
                      For index = 12,13 the id will describe the functionality
                       of a FAN1 : 0 - OK
                                  1 - Failed."
              ::= { atmNteIdEntry 2 }

         atmNteUnitVersion OBJECT-TYPE
              SYNTAX DisplayString
              MAX-ACCESS  read-only
              STATUS  current
              DESCRIPTION
                      "Hardware and Software version
                       of the module."
              ::= { atmNteIdEntry 3 }

       atmNteCardType OBJECT-TYPE
              SYNTAX  INTEGER {
		notApplicable	(1),
		sc13mR155		(2),
		st13sR155		(3),
		st13lR155		(4),
		utpR155			(5),
		cxBncR155		(6),
		e3				(7),
		t3				(8),
		e1				(9),
		e1Ltu			(10),
		fc13lR155		(11),
		fc13lhR155		(12),
		fc15lhR155		(13),
		fc13lE3		    (14),
		fc13lhE3		(15),
		fc15lhE3		(16),
		fc13lT3		    (17),
		fc13lhT3		(18),
		fc15lhT3		(19),
		t1				(20),
		eth				(21),
		ethE1CesBnc	    (22),
		ethE1CesRj45    (23),
		ethT1CesRj45	(24),
		e1CesRj45		(25),
		e1CesBnc		(26),
		t1CesRj45		(27),
		e14Ces			(28),
 		e14CesRj45  	(29),
		t14CesRj45  	(30),

		hdlc4port		(31),
		hdlcE14CesBnc   (32),
		hdlcE14CesRj45  (33),
		hdlcT14CesRj45  (34),
		e1Rj45	  		(35),
		e1Bnc			(36),

		ethE14CesBnc	(37),
		ethE14CesRj45   (38),
		ethT14CesRj45   (39),

		hdlc1portHssi	   (40),
		hdlcHssiE14CesBnc  (41),
		hdlcHssiE14CesRj45 (42),
		hdlcHssiT14CesRj45 (43),

		e14ImaRj45	    (44),
		e14ImaBnc		(45),
		t14ImaRj45	    (46),

		ethE3CesBnc     (47),
		ethT3CesBnc	    (48),

		smSf1R155		(49),
		smSf2R155		(50),

        sc13sR155		(51),
        sc13lR155		(52),

		utp25			(53),

        sc13lhR155		(54),
        sc15lhR155		(55),

        sc13ljR155		(56),
        sc13lhjR155  	(57),
        sc15lhjR155  	(58),

		e18Ces 	        (59),
		e18CesRj45      (60),
		t18CesRj45      (61),

        sc13mR622       (62),
--        st13sR622       (63),
--        st13lR622       (64),
--        utpR622         (65),
--        cxBncR622       (66),
--        fc13lR622       (67),
--        fc13lhR622      (68),
--        fc15lhR622      (69),
--        smSf1R622       (70),
--        smSf2R622       (71),
--        sc13sR622       (72),
        sc13lR622       (73),
        sc13lhR622      (74),
--        sc15lhR622      (75),

        fr4Port         (76),
		t3j				(77),
        fr1Port         (78),
        hdlc1Port       (79),

		empty			(255)
	}

              MAX-ACCESS  read-only
              STATUS current
              DESCRIPTION
                      "The card type."
              ::= { atmNteIdEntry 4 }

         atmSysPSunits OBJECT-TYPE
              SYNTAX  Integer32
              MAX-ACCESS  read-only
              STATUS  current
              DESCRIPTION
                      "The number of power supply units."
              ::= { atmNteSysInfo 2 }

          atmSysPSunitsInUse OBJECT-TYPE
              SYNTAX  INTEGER { ps1(2), ps2(3) }
              MAX-ACCESS  read-only
              STATUS  current
              DESCRIPTION
              "The main power supply in this unit."
              ::= { atmNteSysInfo 3 }

          atmSysFanUnits OBJECT-TYPE
              SYNTAX  Integer32
              MAX-ACCESS  read-only
              STATUS  current
              DESCRIPTION
                      "The number of fan units."
              ::= { atmNteSysInfo 4 }

          atmSysNetPrts OBJECT-TYPE
              SYNTAX  Integer32
              MAX-ACCESS  read-only
              STATUS  current
              DESCRIPTION
                      "The number of network ports."
              ::= { atmNteSysInfo 5 }

          atmSysNetPrtInUse OBJECT-TYPE
              SYNTAX  INTEGER {
                      trunk1(2),
			          trunk2(3)
			  }
              MAX-ACCESS  read-only
              STATUS  current
              DESCRIPTION
                      "The network port in use."
              ::= { atmNteSysInfo 6 }

          atmNteBridgingMode OBJECT-TYPE
               SYNTAX  INTEGER {
                       accessOnly(1),
                       accessAndSwitching (2)
               }
 	           MAX-ACCESS  read-write
               STATUS  current
               DESCRIPTION
               "Bridging mode can be one of the following:
	            ATM <> Ethernet - Bridging is between the Ethernet
	            port and the ATM port (there is no bridging between VCs).
	            ATM <> Ethernet + ATM - Bridging is done both between
	            the Ethernet port and the ATM port and also between VCs."
               ::= { atmNteSysInfo 7}

          atmSysStats OBJECT IDENTIFIER ::= { atmNteSysInfo 8 }

          atmSysCurrentCdc  OBJECT-TYPE
                SYNTAX  Gauge32
                MAX-ACCESS  read-only
                STATUS  current
                DESCRIPTION
                        "Seconds in which cells dropped was occured in
                        the current 15 minutes interval."
                ::= { atmSysStats 1 }

          atmSysIntervalTable OBJECT-TYPE
              SYNTAX  SEQUENCE OF AtmSysIntervalEntry
              MAX-ACCESS  not-accessible
              STATUS  current
              DESCRIPTION
                      "The system level Interval table."
              ::= { atmSysStats 2 }

          atmSysIntervalEntry OBJECT-TYPE
              SYNTAX  AtmSysIntervalEntry
              MAX-ACCESS  not-accessible
              STATUS  current
              DESCRIPTION
                      "."
              INDEX   { atmSysIntervalNumber }
              ::= { atmSysIntervalTable 1 }

          AtmSysIntervalEntry ::=
              SEQUENCE {
                  atmSysIntervalNumber
					  Integer32,
                  atmSysIntervalCdc
                      Gauge32
              }

          atmSysIntervalNumber OBJECT-TYPE
              SYNTAX  Integer32 (1..96)
              MAX-ACCESS  read-only
              STATUS  current
              DESCRIPTION
                      "A number between 1 and 96, where 1 is the most
                      recently completed 15 minute interval and 96 is
                      the least recently completed 15 minutes interval
                      (assuming that all 96 intervals are valid)."
              ::= { atmSysIntervalEntry 1 }

          atmSysIntervalCdc  OBJECT-TYPE
                SYNTAX  Gauge32
                MAX-ACCESS  read-only
                STATUS  current
                DESCRIPTION
                        "Seconds in which cells dropped was occured in
                        15 minutes interval."
                ::= { atmSysIntervalEntry 2 }

          atmNteEventType OBJECT-TYPE
               SYNTAX  INTEGER {
					ps1NotActive	(3),
					ps1Active		(4),
					ps2NotActive	(5),
					ps2Active		(6),
					heatAlarmOff	(7),
					heatAlarmOn		(8),
					inputAlarm1Off	(9),
					inputAlarm1On	(10),
					inputAlarm2Off	(11),
					inputAlarm2On	(12),
					inputAlarm3Off	(13),
					inputAlarm3On	(14),
					inputAlarm4Off	(15),
					inputAlarm4On	(16),
					fan1Ok	        (17),
					fan1Fail	    (18),
					fan2Ok	        (19),
					fan2Fail	    (20),
                    invalidLogin    (21),
                    validLogin      (22),
					powerFailure 	(23)
               }
 	           MAX-ACCESS  read-only
               STATUS  current
               DESCRIPTION
               "This parameter identifies the event.
               On  - the problem exist.
               Off - the problem not exist.
               InvalidLogin - Invalid login on local console.
               CorrectLogin - Successful login operation."
               ::= { atmNteSysInfo 9 }

         atmNteIntervalMaxNumber OBJECT-TYPE
              SYNTAX  Integer32 (1..96)
              MAX-ACCESS  read-only
              STATUS  current
              DESCRIPTION
                      "The MAX number of connections intervals supported by system.
					  This parameter value is a function of atmNteConnectionsMaxNumber
					  parameter.
					  This parameter should affect the threshold values selected by user.
                      Applicable to ace2002."
              ::= { atmNteSysInfo 10 }

        atmNteAlarmType OBJECT-TYPE
              SYNTAX INTEGER
              {
		          notApplicable(1),
		          ais(2),
                  rdi(3),
		          continuityLoss(4),
		          loopback(5)
              }
              MAX-ACCESS read-only
              STATUS  current
              DESCRIPTION
                "This object specifies the type of the alarm."
              ::= { atmNteSysInfo 11 }

        atmNteLevel OBJECT-TYPE
              SYNTAX INTEGER
              {
		          vp(2),
		          vc(3)
              }
              MAX-ACCESS read-only
              STATUS  current
              DESCRIPTION
                "This object specifies the ATM level."
              ::= { atmNteSysInfo 12 }

        atmNteConnectionsNumber OBJECT-TYPE
              SYNTAX Integer32
              MAX-ACCESS read-only
              STATUS  current
              DESCRIPTION
                "This object specifies a quantity of connections."
              ::= { atmNteSysInfo 13 }


--atmNtePrt  OBJECT IDENTIFIER  ::=  {atmNte 2}

-- Changed
atmNteLoopback  OBJECT IDENTIFIER  ::=  {atmNtePrt 2}
-- The loopback test consists of inserting special OAM cells. This test is started and stopped
-- upon operator request (by using MIB item atmVpConfLoopbackAdminStatus).
-- There are two tables per VP and two tables per VC: the measurements of the current 15 minutes,
-- and the measurement of the last 96 periods of 15 minutes.
atmLoopbackVpTable  OBJECT-TYPE
      SYNTAX SEQUENCE OF AtmLoopbackVpEntry
      MAX-ACCESS not-accessible
      STATUS  current
      DESCRIPTION
      "This table contains parameters for an OAM VP loopback test."
       ::= {atmNteLoopback 1 }

atmLoopbackVpEntry OBJECT-TYPE
      SYNTAX AtmLoopbackVpEntry
      MAX-ACCESS not-accessible
      STATUS current
	  DESCRIPTION "An entry in table atmLoopbackVpTable."
	  INDEX {atmLoopbackVpIfIndex,atmLoopbackVpVpi}
      ::= {atmLoopbackVpTable 1}

AtmLoopbackVpEntry ::=
      SEQUENCE {
	atmLoopbackVpIfIndex               Integer32,
	atmLoopbackVpVpi                   Integer32,
	atmLoopbackVpOperStatus            INTEGER,
	atmLoopbackVpCDV 		           Integer32,
	atmLoopbackVpAverageDelay          Integer32,
	atmLoopbackVpMaxDelay              Integer32,
	atmLoopbackVpMinDelay              Integer32,
	atmLoopbackVpErrSessions	       Integer32
	}

atmLoopbackVpIfIndex OBJECT-TYPE
      SYNTAX Integer32
      MAX-ACCESS read-only
      STATUS current
      DESCRIPTION
      "The interface index of the ATM layer."
      ::= {atmLoopbackVpEntry 1}

atmLoopbackVpVpi OBJECT-TYPE
      SYNTAX Integer32
      MAX-ACCESS read-only
      STATUS current
      DESCRIPTION
      "The VPI of the OAM VPL."
      ::= {atmLoopbackVpEntry 2}


atmLoopbackVpOperStatus OBJECT-TYPE
      SYNTAX INTEGER {
	noActive(1),
	inProgress(2),
              failed(3),
	endSuccessfully(4)
                     }
      MAX-ACCESS read-only
      STATUS current
      DESCRIPTION
      "-noActive(1) means that the loopback test has not been activated for this VP.
        -inProgress(2) means that the test has been activated and there is currently no problem.
        -failed(3) means there was problem during the test or after having stopped it
        -endSuccessfully(4) means that the test was stopped and all was OK."
      ::= {atmLoopbackVpEntry 3}

atmLoopbackVpCDV OBJECT-TYPE
      SYNTAX Integer32
      MAX-ACCESS read-only
      STATUS current
      DESCRIPTION
      "Cell Delay Variation for this sampling."
      ::= {atmLoopbackVpEntry 4}

atmLoopbackVpAverageDelay OBJECT-TYPE
      SYNTAX Integer32
      MAX-ACCESS read-only
      STATUS current
      DESCRIPTION
      " Average delay without including lost cells."
      ::= {atmLoopbackVpEntry 5}

atmLoopbackVpMaxDelay OBJECT-TYPE
      SYNTAX Integer32
      MAX-ACCESS read-only
      STATUS current
      DESCRIPTION
      "Maximum delay without including lost cells."
      ::= {atmLoopbackVpEntry 6}

atmLoopbackVpMinDelay OBJECT-TYPE
      SYNTAX Integer32
      MAX-ACCESS read-only
      STATUS current
      DESCRIPTION
      "Minimum delay."
      ::= {atmLoopbackVpEntry 7}

atmLoopbackVpErrSessions OBJECT-TYPE
      SYNTAX Integer32
      MAX-ACCESS read-only
      STATUS current
      DESCRIPTION
      "Errored Sessions. Will be updated once in 5 seconds."
      ::= {atmLoopbackVpEntry 8}

atmLoopbackVcTable  OBJECT-TYPE
      SYNTAX SEQUENCE OF AtmLoopbackVcEntry
      MAX-ACCESS not-accessible
      STATUS  current
      DESCRIPTION
      "This table contains parameters for an OAM VC loopback test."
       ::= {atmNteLoopback 2 }

atmLoopbackVcEntry OBJECT-TYPE
      SYNTAX AtmLoopbackVcEntry
      MAX-ACCESS not-accessible
      STATUS current
      DESCRIPTION  "An entry in table."
      INDEX {atmLoopbackVcIfIndex,atmLoopbackVcVpi,atmLoopbackVcVci}
      ::= {atmLoopbackVcTable 1}

AtmLoopbackVcEntry ::=
      SEQUENCE {
	atmLoopbackVcIfIndex               Integer32,
	atmLoopbackVcVpi                   Integer32,
	atmLoopbackVcVci                   Integer32,
	atmLoopbackVcOperStatus            INTEGER,
	atmLoopbackVcCDV	               Integer32,
	atmLoopbackVcAverageDelay          Integer32,
	atmLoopbackVcMaxDelay              Integer32,
	atmLoopbackVcMinDelay              Integer32,
	atmLoopbackVcErrSessions           Integer32
	}

atmLoopbackVcIfIndex OBJECT-TYPE
      SYNTAX Integer32
      MAX-ACCESS read-only
      STATUS current
      DESCRIPTION
      "The interface index of the ATM layer."
      ::= {atmLoopbackVcEntry 1}

atmLoopbackVcVpi OBJECT-TYPE
      SYNTAX Integer32
      MAX-ACCESS read-only
      STATUS current
      DESCRIPTION
      "The VPI of the OAM VCL."
      ::= {atmLoopbackVcEntry 2}

atmLoopbackVcVci OBJECT-TYPE
      SYNTAX Integer32
      MAX-ACCESS read-only
      STATUS current
      DESCRIPTION
      "The VCI of the OAM VCL."
      ::= {atmLoopbackVcEntry 3}


atmLoopbackVcOperStatus OBJECT-TYPE
      SYNTAX INTEGER {
	noActive(1),
	inProgress(2),
               failed(3),
	endSuccessfully(4)
                     }
      MAX-ACCESS read-only
      STATUS current
      DESCRIPTION
      "-noActive(1) means that the loopback test has not been activated for this VP.
        -inProgress(2) means that the test has been activated and there is currently no problem.
        -failed(3) means there was problem during the test or after having stopped it
        -endSuccessfully(4) means that the test was stopped and all was OK."
      ::= {atmLoopbackVcEntry 4}

atmLoopbackVcCDV OBJECT-TYPE
      SYNTAX Integer32
      MAX-ACCESS read-only
      STATUS current
      DESCRIPTION
      "Cell Delay Variation for this sampling."
      ::= {atmLoopbackVcEntry 5}


atmLoopbackVcAverageDelay OBJECT-TYPE
      SYNTAX Integer32
      MAX-ACCESS read-only
      STATUS current
      DESCRIPTION
      " Average delay without including lost cells."
      ::= {atmLoopbackVcEntry 6}

atmLoopbackVcMaxDelay OBJECT-TYPE
      SYNTAX Integer32
      MAX-ACCESS read-only
      STATUS current
      DESCRIPTION
      "The maximum delay without including lost cells."
      ::= {atmLoopbackVcEntry 7}

atmLoopbackVcMinDelay OBJECT-TYPE
      SYNTAX Integer32
      MAX-ACCESS read-only
      STATUS current
      DESCRIPTION
      "The minimum delay."
      ::= {atmLoopbackVcEntry 8}

atmLoopbackVcErrSessions OBJECT-TYPE
      SYNTAX Integer32
      MAX-ACCESS read-only
      STATUS current
      DESCRIPTION
      "Errored Sessions. Will be updated once in 5 seconds."
      ::= {atmLoopbackVcEntry 9}


-- Entirely New
atmLoopbackVpIvlTable  OBJECT-TYPE
      SYNTAX SEQUENCE OF AtmLoopbackVpIvlEntry
      MAX-ACCESS not-accessible
      STATUS  current
      DESCRIPTION
      "This table contains parameters for an OAM VP loopback test,
	according interval number."
       ::= {atmNteLoopback 3 }

atmLoopbackVpIvlEntry OBJECT-TYPE
      SYNTAX AtmLoopbackVpIvlEntry
      MAX-ACCESS not-accessible
      STATUS current
	DESCRIPTION  "An entry in table."
	INDEX { atmLoopbackVpIvlIfIndex, atmLoopbackVpIvlVpi, atmLoopbackVpIvlIvl }
      ::= { atmLoopbackVpIvlTable 1}

AtmLoopbackVpIvlEntry ::=
      SEQUENCE {
	atmLoopbackVpIvlIfIndex               Integer32,
	atmLoopbackVpIvlVpi                   Integer32,
	atmLoopbackVpIvlIvl 		          Integer32,
	atmLoopbackVpIvlOperStatus            INTEGER,
	atmLoopbackVpIvlCDV	                  Integer32,
	atmLoopbackVpIvlAverageDelay          Integer32,
	atmLoopbackVpIvlMaxDelay              Integer32,
	atmLoopbackVpIvlMinDelay              Integer32,
	atmLoopbackVpIvlErrSessions           Integer32
	}

atmLoopbackVpIvlIfIndex OBJECT-TYPE
      SYNTAX Integer32
      MAX-ACCESS read-only
      STATUS current
      DESCRIPTION
      "The interface index of the ATM layer."
      ::= { atmLoopbackVpIvlEntry 1}

atmLoopbackVpIvlVpi OBJECT-TYPE
      SYNTAX Integer32
      MAX-ACCESS read-only
      STATUS current
      DESCRIPTION
      "The VPI of the OAM VPL."
      ::= { atmLoopbackVpIvlEntry 2}


atmLoopbackVpIvlIvl OBJECT-TYPE
      SYNTAX Integer32(1..96)
      MAX-ACCESS read-only
      STATUS current
      DESCRIPTION
      "The relevant interval number."
      ::= { atmLoopbackVpIvlEntry 3}

atmLoopbackVpIvlOperStatus OBJECT-TYPE
      SYNTAX INTEGER {
	noActive(1),
	inProgress(2),
               failed(3),
	endSuccessfully(4)
                     }
      MAX-ACCESS read-only
      STATUS current
      DESCRIPTION
      "-noActive(1) means that the loopback test has not been activated for this VP during this interval.
        -inProgress(2) has no meaning for an ended interval.
        -failed(3) means there was problem during the test or after having stopped it
        -endSuccessfully(4) means that the test was OK."
      ::= { atmLoopbackVpIvlEntry 4}

atmLoopbackVpIvlCDV OBJECT-TYPE
      SYNTAX Integer32
      MAX-ACCESS read-only
      STATUS current
      DESCRIPTION
      "Cell Delay Variation for this interval."
      ::= { atmLoopbackVpIvlEntry 5}


atmLoopbackVpIvlAverageDelay OBJECT-TYPE
      SYNTAX Integer32
      MAX-ACCESS read-only
      STATUS current
      DESCRIPTION
      " Average delay without including lost cells for this interval."
      ::= { atmLoopbackVpIvlEntry 6}

atmLoopbackVpIvlMaxDelay OBJECT-TYPE
      SYNTAX Integer32
      MAX-ACCESS read-only
      STATUS current
      DESCRIPTION
      "The maximum delay without including lost cells for this interval."
      ::= { atmLoopbackVpIvlEntry 7}

atmLoopbackVpIvlMinDelay OBJECT-TYPE
      SYNTAX Integer32
      MAX-ACCESS read-only
      STATUS current
      DESCRIPTION
      "The minimum delay for this interval."
      ::= {atmLoopbackVpIvlEntry 8}

atmLoopbackVpIvlErrSessions OBJECT-TYPE
      SYNTAX Integer32
      MAX-ACCESS read-only
      STATUS current
      DESCRIPTION
      "Errored Sessions. Will be updated once in 5 seconds."
      ::= {atmLoopbackVpIvlEntry 9}


atmLoopbackVcIvlTable  OBJECT-TYPE
      SYNTAX SEQUENCE OF AtmLoopbackVcIvlEntry
      MAX-ACCESS not-accessible
      STATUS  current
      DESCRIPTION
      "This table contains parameters for an OAM VC loopback test."
       ::= {atmNteLoopback 4 }

atmLoopbackVcIvlEntry OBJECT-TYPE
      SYNTAX AtmLoopbackVcIvlEntry
      MAX-ACCESS not-accessible
      STATUS current
	DESCRIPTION  "An entry in table."
	INDEX {atmLoopbackVcIvlIfIndex, atmLoopbackVcIvlVpi, atmLoopbackVcIvlVci, atmLoopbackVcIvlIvl }
      ::= {atmLoopbackVcIvlTable 1}

AtmLoopbackVcIvlEntry ::=
      SEQUENCE {
	atmLoopbackVcIvlIfIndex               Integer32,
	atmLoopbackVcIvlVpi                   Integer32,
	atmLoopbackVcIvlVci                   Integer32,
	atmLoopbackVcIvlIvl 		          Integer32,
	atmLoopbackVcIvlOperStatus            INTEGER,
	atmLoopbackVcIvlCDV	                  Integer32,
	atmLoopbackVcIvlAverageDelay          Integer32,
	atmLoopbackVcIvlMaxDelay              Integer32,
	atmLoopbackVcIvlMinDelay              Integer32,
	atmLoopbackVcIvlErrSessions           Integer32
	}

atmLoopbackVcIvlIfIndex OBJECT-TYPE
      SYNTAX Integer32
      MAX-ACCESS read-only
      STATUS current
      DESCRIPTION
      "The interface index of the ATM layer."
      ::= {atmLoopbackVcIvlEntry 1}

atmLoopbackVcIvlVpi OBJECT-TYPE
      SYNTAX Integer32
      MAX-ACCESS read-only
      STATUS current
      DESCRIPTION
      "The VPI of the OAM VCL."
      ::= {atmLoopbackVcIvlEntry 2}

atmLoopbackVcIvlVci OBJECT-TYPE
      SYNTAX Integer32
      MAX-ACCESS read-only
      STATUS current
      DESCRIPTION
      "The VCI of the OAM VCL."
      ::= {atmLoopbackVcIvlEntry 3}

atmLoopbackVcIvlIvl OBJECT-TYPE
      SYNTAX Integer32(1..96)
      MAX-ACCESS read-only
      STATUS current
      DESCRIPTION
      "The relevant interval number."
      ::= {atmLoopbackVcIvlEntry 4}

atmLoopbackVcIvlOperStatus OBJECT-TYPE
      SYNTAX INTEGER {
	noActive(1),
	inProgress(2),
               failed(3),
	endSuccessfully(4)
                     }
      MAX-ACCESS read-only
      STATUS current
      DESCRIPTION
      "-noActive(1) means that the loopback test has not been activated for this VC during this interval.
        -inProgress(2) has no meaning per interval.
        -failed(3) means there was problem for this test during this interval.
        -endSuccessfully(4) means that the test was OK."
      ::= {atmLoopbackVcIvlEntry 5}

atmLoopbackVcIvlCDV OBJECT-TYPE
      SYNTAX Integer32
      MAX-ACCESS read-only
      STATUS current
      DESCRIPTION
      "Cell Delay Variation for this interval."
      ::= {atmLoopbackVcIvlEntry 6}


atmLoopbackVcIvlAverageDelay OBJECT-TYPE
      SYNTAX Integer32
      MAX-ACCESS read-only
      STATUS current
      DESCRIPTION
      " Average delay without including lost cells."
      ::= {atmLoopbackVcIvlEntry 7}

atmLoopbackVcIvlMaxDelay OBJECT-TYPE
      SYNTAX Integer32
      MAX-ACCESS read-only
      STATUS current
      DESCRIPTION
      "The maximum delay without including lost cells."
      ::= {atmLoopbackVcIvlEntry 8}

atmLoopbackVcIvlMinDelay OBJECT-TYPE
      SYNTAX Integer32
      MAX-ACCESS read-only
      STATUS current
      DESCRIPTION
      "The minimum delay."
      ::= {atmLoopbackVcIvlEntry 9}

atmLoopbackVcIvlErrSessions OBJECT-TYPE
      SYNTAX Integer32
      MAX-ACCESS read-only
      STATUS current
      DESCRIPTION
      "Errored Sessions. Will be updated once in 5 seconds."
      ::= {atmLoopbackVcIvlEntry 10}


atmNtePM  OBJECT IDENTIFIER  ::=  {atmNtePrt 3}

atmVpPmTable  OBJECT-TYPE
      SYNTAX SEQUENCE OF AtmVpPmEntry
      MAX-ACCESS not-accessible
      STATUS  current
      DESCRIPTION
      "This table contains parameters for VP performance monitoring."
       ::= {atmNtePM 1 }

atmVpPmEntry OBJECT-TYPE
      SYNTAX AtmVpPmEntry
      MAX-ACCESS not-accessible
      STATUS current
	DESCRIPTION  "An entry in table."
	INDEX {atmVpPmIfIndex,atmVpPmVpi}
      ::= {atmVpPmTable 1}

AtmVpPmEntry ::=
      SEQUENCE {
	atmVpPmIfIndex               Integer32,
	atmVpPmVpi                   Integer32,
	atmVpPmAdminStatus           INTEGER,
	atmVpPmDirection             INTEGER,
	atmVpPmBlockSize             Integer32,
	atmVpPmRowStatus             RowStatus,
	atmVpPmSink                  INTEGER,
	atmVpPmSource                INTEGER
      }

atmVpPmIfIndex OBJECT-TYPE
      SYNTAX Integer32
      MAX-ACCESS read-only
      STATUS current
      DESCRIPTION
      "The interface index of the ATM layer."
      ::= {atmVpPmEntry 1}

atmVpPmVpi OBJECT-TYPE
      SYNTAX Integer32
      MAX-ACCESS read-only
      STATUS current
      DESCRIPTION
      "The VPI of the Performance Monitoring VPL."
      ::= {atmVpPmEntry 2}

atmVpPmAdminStatus OBJECT-TYPE
      SYNTAX INTEGER {
             up  (2),
             down(3),
             listenToActivationCells (4),
             originateActivationCells (5)
      }
      MAX-ACCESS read-create
      STATUS current
      DESCRIPTION
      "up(2) - Activate PM.
       down(3) - Deactivate PM.
       listenToActivationCells(4) - .
       originateActivationCells(5) - ."
      ::= {atmVpPmEntry 3}

atmVpPmDirection OBJECT-TYPE
      SYNTAX INTEGER  {
             source(2),
             destination(3),
             bidirectional(4)
      }
      MAX-ACCESS read-create
      STATUS current
      DESCRIPTION
      "The direction of PM."
      ::= {atmVpPmEntry 4}

atmVpPmBlockSize OBJECT-TYPE
      SYNTAX Integer32
      MAX-ACCESS read-create
      STATUS current
      DESCRIPTION
      "Valid block sizes (in cells): 128, 256, 512, 1024, 2048, 4096,
       8192, 16384, 32768."
      ::= {atmVpPmEntry 5}

atmVpPmRowStatus OBJECT-TYPE
      SYNTAX RowStatus
      MAX-ACCESS read-create
      STATUS current
      DESCRIPTION
      "Creation/Deletion of rows in the table."
      ::= {atmVpPmEntry 6}

atmVpPmSink OBJECT-TYPE
      SYNTAX INTEGER {
             off  (1),
             fwd  (2),
             fwdAndBwdReport(3)
      }
      MAX-ACCESS read-create
      STATUS current
      DESCRIPTION
      "off (1) - Deactivate PM.
       fwd (2) - Activate Forward PM only.
       fwdAndBwdReport(3) - Activate Forward PM and Backward reporting."
      ::= {atmVpPmEntry 7}

atmVpPmSource OBJECT-TYPE
      SYNTAX INTEGER {
             off  (1),
             fwd  (2),
             fwdAndBwdReport(3)
      }
      MAX-ACCESS read-create
      STATUS current
      DESCRIPTION
      "off (1) - Deactivate PM.
       fwd (2) - Activate Forward PM only.
       fwdAndBwdReport(3) - Activate Forward PM and Backward reporting."
      ::= {atmVpPmEntry 8}



atmVcPmTable  OBJECT-TYPE
      SYNTAX SEQUENCE OF AtmVcPmEntry
      MAX-ACCESS not-accessible
      STATUS  current
      DESCRIPTION
      "This table contains parameters for VC performance monitoring."
       ::= {atmNtePM 2 }

atmVcPmEntry OBJECT-TYPE
      SYNTAX AtmVcPmEntry
      MAX-ACCESS not-accessible
      STATUS current
	DESCRIPTION  "An entry in table."
	INDEX {atmVcPmIfIndex,atmVcPmVpi,atmVcPmVci}
      ::= {atmVcPmTable 1}

AtmVcPmEntry ::=
      SEQUENCE {
	atmVcPmIfIndex               Integer32,
	atmVcPmVpi                   Integer32,
	atmVcPmVci                   Integer32,
	atmVcPmAdminStatus           INTEGER,
	atmVcPmDirection             INTEGER,
	atmVcPmBlockSize             Integer32,
	atmVcPmRowStatus             RowStatus,
	atmVcPmSink                  INTEGER,
	atmVcPmSource                INTEGER
      }

atmVcPmIfIndex OBJECT-TYPE
      SYNTAX Integer32
      MAX-ACCESS read-only
      STATUS current
      DESCRIPTION
      "The interface index of the ATM layer."
      ::= {atmVcPmEntry 1}

atmVcPmVpi OBJECT-TYPE
      SYNTAX Integer32
      MAX-ACCESS read-only
      STATUS current
      DESCRIPTION
      "The VPI of the Performance Monitoring VCL."
      ::= {atmVcPmEntry 2}

atmVcPmVci OBJECT-TYPE
      SYNTAX Integer32
      MAX-ACCESS read-only
      STATUS current
      DESCRIPTION
      "The VCI of the PM VCL."
      ::= {atmVcPmEntry 3}

atmVcPmAdminStatus OBJECT-TYPE
      SYNTAX INTEGER {
             up  (2),
             down(3),
             listenToActivationCells (4),
             originateActivationCells (5)
      }
      MAX-ACCESS read-create
      STATUS current
      DESCRIPTION
      "up(2) - Activate PM.
       down(3) - Deactivate PM.
       listenToActivationCells(4) - .
       originateActivationCells(5) - ."
      ::= {atmVcPmEntry 4}

atmVcPmDirection OBJECT-TYPE
      SYNTAX INTEGER  { source(2), destination(3), bidirectional(4)  }
      MAX-ACCESS read-create
      STATUS current
      DESCRIPTION
      "The direction of PM."
      ::= {atmVcPmEntry 5}

atmVcPmBlockSize OBJECT-TYPE
      SYNTAX Integer32
      MAX-ACCESS read-create
      STATUS current
      DESCRIPTION
      "Valid block sizes (in cells): 128, 256, 512, 1024, 2048, 4096,
       8192, 16384, 32768."
      ::= {atmVcPmEntry 6}

atmVcPmRowStatus OBJECT-TYPE
      SYNTAX RowStatus
      MAX-ACCESS read-create
      STATUS current
      DESCRIPTION
      "Creation/Deletion of rows in the table."
      ::= {atmVcPmEntry 7}

atmVcPmSink OBJECT-TYPE
      SYNTAX INTEGER {
             off  (1),
             fwd  (2),
             fwdAndBwdReport(3)
      }
      MAX-ACCESS read-create
      STATUS current
      DESCRIPTION
      "off (1) - Deactivate PM.
       fwd (2) - Activate Forward PM only.
       fwdAndBwdReport(3) - Activate Forward PM and Backward reporting."
      ::= {atmVcPmEntry 8}

atmVcPmSource OBJECT-TYPE
      SYNTAX INTEGER {
             off  (1),
             fwd  (2),
             fwdAndBwdReport(3)
      }
      MAX-ACCESS read-create
      STATUS current
      DESCRIPTION
      "off (1) - Deactivate PM.
       fwd (2) - Activate Forward PM only.
       fwdAndBwdReport(3) - Activate Forward PM and Backward reporting."
      ::= {atmVcPmEntry 9}



atmGenSystem  OBJECT IDENTIFIER  ::=  {atmGen 2}

--atmGenModules  OBJECT IDENTIFIER  ::=  {atmGen 3}	 located in ace2002.txt


atmGenSysGen  OBJECT IDENTIFIER  ::=  {atmGenSystem 1}

-- The self test table

atmGenSysSelfTestTable  OBJECT-TYPE
      SYNTAX SEQUENCE OF AtmGenSysSelfTestEntry
      MAX-ACCESS not-accessible
      STATUS  current
      DESCRIPTION
      "A table containing the results of the initial testing of the device."
       ::= { atmGenSysGen 1 }

atmGenSysSelfTestEntry OBJECT-TYPE
      SYNTAX AtmGenSysSelfTestEntry
      MAX-ACCESS not-accessible
      STATUS current
	DESCRIPTION  "An entry in table."
	INDEX {atmGenSysSelfTestIndex}
      ::= {atmGenSysSelfTestTable 1}

AtmGenSysSelfTestEntry ::=
      SEQUENCE {
	  atmGenSysSelfTestIndex   Integer32,
	  atmGenSysSelfTestResult DisplayString
      }

atmGenSysSelfTestIndex OBJECT-TYPE
      SYNTAX Integer32
      MAX-ACCESS read-only
      STATUS current
      DESCRIPTION
      "A running index for the table."
      ::= { atmGenSysSelfTestEntry 1}

atmGenSysSelfTestResult OBJECT-TYPE
      SYNTAX DisplayString
      MAX-ACCESS read-only
      STATUS current
      DESCRIPTION
      "The results of the initial testing of the device."
      ::= { atmGenSysSelfTestEntry 2}

-- The Log clear all

atmGenSysLogClearAll OBJECT-TYPE
      SYNTAX INTEGER { off(2),clear(3)}
      MAX-ACCESS read-write
      STATUS current
      DESCRIPTION
      "Setting the variable to clear(3) removes all entries in the
       Log Buffer of the agent. The agent will immediately
       reset the variable to off(2)."
      ::= { atmGenSysGen 2}

-- The Log table

atmGenSysLogTable  OBJECT-TYPE
      SYNTAX SEQUENCE OF AtmGenSysLogEntry
      MAX-ACCESS not-accessible
      STATUS  current
      DESCRIPTION
      "A copy of the log buffer."
       ::= { atmGenSysGen 3 }

atmGenSysLogEntry OBJECT-TYPE
      SYNTAX AtmGenSysLogEntry
      MAX-ACCESS not-accessible
      STATUS current
	DESCRIPTION  "An entry in table."
	INDEX {atmGenSysLogIndex}
      ::= {atmGenSysLogTable 1}

AtmGenSysLogEntry ::=
      SEQUENCE {
	  atmGenSysLogIndex   Integer32,
	  atmGenSysLogMessage DisplayString
      }

atmGenSysLogIndex OBJECT-TYPE
      SYNTAX Integer32 (1..2048)
      MAX-ACCESS read-only
      STATUS current
      DESCRIPTION
      "The index of the log buffer."
      ::= { atmGenSysLogEntry 1}

atmGenSysLogMessage OBJECT-TYPE
      SYNTAX DisplayString (SIZE(80))
      MAX-ACCESS read-only
      STATUS current
      DESCRIPTION
      "The log buffer entry message text."
      ::= { atmGenSysLogEntry 2}

-- Set to default configuration

atmGenSysSetDefaultConfg OBJECT-TYPE
      SYNTAX INTEGER { off(2), on(3) }
      MAX-ACCESS read-write
      STATUS current
      DESCRIPTION
      "When set to on(3), the agent will set all the configuration parameters
       to their default values. The variable is then reset to  off(2)
       by the agent. The agent must be reset for the default configuration
       to apply."
      ::=  {atmGenSysGen 4}

	-- A Cross Reference table for connections between tables.

 atmGenSysCxRefTable OBJECT-TYPE
              SYNTAX  SEQUENCE OF AtmGenSysCxRefEntry
              MAX-ACCESS  not-accessible
              STATUS  current
              DESCRIPTION
                   "A Cross Reference table. The table maintains
                    an index of an object which is also the table index,
                    and a counter that indicates how many times this
                    object was referenced.
                    When using this table for more than one referenced table,
					which uses the same range of indexes, then the index
					should be shifted by a unique offset per table.

                    In ACE2002 this table is used for TD and for FR Desc. Thus,
                    the index for FR Descriptor is: FR Descriptor index + offset.
                    The offset is described in the ACE2002 NMS SRS."
              ::= {atmGenSysGen 5}

 atmGenSysCxRefEntry OBJECT-TYPE
              SYNTAX AtmGenSysCxRefEntry
              MAX-ACCESS  not-accessible
              STATUS  current
              DESCRIPTION
                      "The entries will be added by the agent upon
                       an entry addition in the referenced tables
                       (TD table, FR Descriptor etc.)"
              INDEX   { atmGenSysCxRefIndex }
              ::= { atmGenSysCxRefTable 1 }

 	AtmGenSysCxRefEntry ::=
              SEQUENCE {
		 		atmGenSysCxRefIndex
                      	Integer32,
                atmGenSysCxRefCounter
                      	Gauge32
                }

 	atmGenSysCxRefIndex OBJECT-TYPE
              SYNTAX  Integer32
              MAX-ACCESS  read-only
              STATUS  current
              DESCRIPTION
                      "The index specifies an entry in the table of the object."
              ::= { atmGenSysCxRefEntry 1 }

 	atmGenSysCxRefCounter OBJECT-TYPE
              SYNTAX Gauge32
              MAX-ACCESS  read-only
              STATUS  current
              DESCRIPTION
                      "The counter counts the number of references
						that have been made to the object ."
              ::= { atmGenSysCxRefEntry 2 }



-- Traps

-- System Layer Traps

atmAceStatusChange NOTIFICATION-TYPE
      OBJECTS  {agnLed,agnIndication}
      STATUS  current
      DESCRIPTION
       "The trap is sent every time there is a change in
	    the state of one of the LEDs."
      ::= { atmNteEvents 1 }

atmAceAlarmTrap NOTIFICATION-TYPE
      OBJECTS  {atmInterfaceAlarmStatus}
      STATUS  current
      DESCRIPTION
	  "The trap is sent whenever there is a transition from a no alarm
	   state to a state with at least one active alarm. An active alarm
	   state exists if:
	   1) The atmInterfaceActiveAlarms vector is different than 0.
	   2) The atmNteAlarmVpTable contains entries.
	   3) The atmNteAlarmVcTable contains entries.
	   The trap is also sent when a transition into the no alarm state
	   occurs.
                 The second variable will be atmInterfaceActiveAlarms to
                 indicate the kind of the alarm.
                 The trap is not sent more than once in a 10 second interval."
      ::= { atmNteEvents 2 }

atmAceModuleChangeTrap NOTIFICATION-TYPE
      OBJECTS  {ifIndex}
      STATUS  current
      DESCRIPTION
	  "The trap is sent every time a module is changed (Hot swapping).
                  The second variable will be atmNteCardType to indicate the
                  type of card that was inserted. The value empty(255) indicates that
                  a card was taken out."
      ::= { atmNteEvents 3 }

atmAceRedundancyTrap NOTIFICATION-TYPE
      OBJECTS  {ifIndex }
      STATUS  current
      DESCRIPTION
	  	"The trap is sent upon change in link as a result of redundancy.
                  The ifIndex parameter indicates the current active link."
      ::= { atmNteEvents 4 }



atmAceSystemTrap NOTIFICATION-TYPE
      OBJECTS  { atmNteEventType, agnLed, alarmSeverity }
      STATUS  current
      DESCRIPTION
	  	"This trap alerts of major problems in the device."
      ::= { radSysAtmEvents  6 }

-- Alarms Traps
atmAceAlarmLOS NOTIFICATION-TYPE
      OBJECTS  { alarmSeverity, alarmState, ifAlias }
      STATUS  current
      DESCRIPTION
	  	"This trap indicates Loss Of Signal."
      ::= { radSysAtmEvents  16 }

atmAceAlarmLOF NOTIFICATION-TYPE
      OBJECTS  { alarmSeverity, alarmState, ifAlias }
      STATUS  current
      DESCRIPTION
	  	"This trap indicates Loss Of Frame."
      ::= { radSysAtmEvents  17 }

atmAceAlarmLCD NOTIFICATION-TYPE
      OBJECTS  { alarmSeverity, alarmState, ifAlias }
      STATUS  current
      DESCRIPTION
	  	"This trap indicates Loss of Cell Delineation."
      ::= { radSysAtmEvents  18 }

atmAceAlarmSLM NOTIFICATION-TYPE
      OBJECTS  { alarmSeverity, alarmState, ifAlias }
      STATUS  current
      DESCRIPTION
	  	"This trap indicates Signal Line Mismatch."
      ::= { radSysAtmEvents  19 }

atmAceAlarmLOP NOTIFICATION-TYPE
      OBJECTS  { alarmSeverity, alarmState, ifAlias }
      STATUS  current
      DESCRIPTION
	  	"This trap indicates Loss of Pointer."
      ::= { radSysAtmEvents  20 }

atmAceAlarmLineAIS NOTIFICATION-TYPE
      OBJECTS  { alarmSeverity, alarmState, ifAlias }
      STATUS  current
      DESCRIPTION
	  	"This trap indicates Line AIS."
      ::= { radSysAtmEvents  21 }

atmAceAlarmPathAIS NOTIFICATION-TYPE
      OBJECTS  { alarmSeverity, alarmState, ifAlias }
      STATUS  current
      DESCRIPTION
	  	"This trap indicates Path AIS."
      ::= { radSysAtmEvents  22 }

atmAceAlarmLineRDI NOTIFICATION-TYPE
      OBJECTS  { alarmSeverity, alarmState, ifAlias }
      STATUS  current
      DESCRIPTION
	  	"This trap indicates Line RDI."
      ::= { radSysAtmEvents  23 }

atmAceAlarmPathRDI NOTIFICATION-TYPE
      OBJECTS  { alarmSeverity, alarmState, ifAlias }
      STATUS  current
      DESCRIPTION
	  	"This trap indicates Path RDIand Path RAI(Yellow) for
	  	 DS1 interfaces."
      ::= { radSysAtmEvents  24 }

atmAceAlarmSectionBIP NOTIFICATION-TYPE
      OBJECTS  { alarmSeverity, alarmState, ifAlias }
      STATUS  current
      DESCRIPTION
	  	"This trap indicates Section Bit Interleave Parity."
      ::= { radSysAtmEvents  25 }

atmAceAlarmLineBIP NOTIFICATION-TYPE
      OBJECTS  { alarmSeverity, alarmState, ifAlias }
      STATUS  current
      DESCRIPTION
	  	"This trap indicates Line Bit Interleave Parity."
      ::= { radSysAtmEvents  26 }

atmAceAlarmPathBIP NOTIFICATION-TYPE
      OBJECTS  { alarmSeverity, alarmState, ifAlias }
      STATUS  current
      DESCRIPTION
	  	"This trap indicates Path Bit Interleave Parity."
      ::= { radSysAtmEvents  27 }

atmAceAlarmLineFEBE NOTIFICATION-TYPE
      OBJECTS  { alarmSeverity, alarmState, ifAlias }
      STATUS  current
      DESCRIPTION
	  	"This trap indicates Line Far End Block Error."
      ::= { radSysAtmEvents  28 }

atmAceAlarmPathFEBE NOTIFICATION-TYPE
      OBJECTS  { alarmSeverity, alarmState, ifAlias }
      STATUS  current
      DESCRIPTION
	  	"This trap indicates Path Far End Block Error."
      ::= { radSysAtmEvents  29 }

atmAceAlarmPlcpLOF NOTIFICATION-TYPE
      OBJECTS  { alarmSeverity, alarmState, ifAlias }
      STATUS  current
      DESCRIPTION
	  	"This trap indicates T3 PLCP Loss Of Frame."
      ::= { radSysAtmEvents  30 }


atmAceAlarmPlcpYELLOW NOTIFICATION-TYPE
      OBJECTS  { alarmSeverity, alarmState, ifAlias }
      STATUS  current
      DESCRIPTION
	  	"This trap indicates T3 Plcp Yellow."
      ::= { radSysAtmEvents  31 }

atmAceAlarmPlcpBIP NOTIFICATION-TYPE
      OBJECTS  { alarmSeverity, alarmState, ifAlias }
      STATUS  current
      DESCRIPTION
	  	"This trap indicates T3 Plcp Bit Interleave Parity."
      ::= { radSysAtmEvents  32 }

atmAceAlarmPlcpFEBE NOTIFICATION-TYPE
      OBJECTS  { alarmSeverity, alarmState, ifAlias }
      STATUS  current
      DESCRIPTION
	  	"This trap indicates T3 Plcp Far End Block Error."
      ::= { radSysAtmEvents  33 }

atmAceAlarmPlcpP1P2 NOTIFICATION-TYPE
      OBJECTS  { alarmSeverity, alarmState, ifAlias }
      STATUS  current
      DESCRIPTION
	  	"This trap indicates T3 Plcp Parity errors in P1/P2 bytes."
      ::= { radSysAtmEvents  34 }

atmAceAlarmUAS NOTIFICATION-TYPE
      OBJECTS  { alarmSeverity, alarmState, ifAlias }
      STATUS  current
      DESCRIPTION
	  	"This trap is sent upon UAS start or end per port."
      ::= { radSysAtmEvents  35 }

atmAceAlarmCluster NOTIFICATION-TYPE
      OBJECTS  { alarmSeverity, alarmState, atmNteAlarmType, atmNteLevel }
      STATUS  current
      DESCRIPTION
	  	"This trap is sent upon atmNteAlarmType start or end,
	  	for a cluster of VPs/VCs (according to atmNteLevel) with
	  	the same alarm on the same physical port.

	  	This trap replaces sending the same alarm for a big
	  	quantity (more than 20) of VPs/VCs in order to prevent
	  	flooding the NMS and the network with traps."
      ::= { radSysAtmEvents  36 }


-- VP Layer Traps

-- atmVplVpi have MAX-ACCESS "not-accessible"
-- and cannot be referenced from NOTIFICATION-TYPE clause
-- in SMIV2 so they where removed from following caluses.
-- Dovi Korngut (28/6/00).

atmAceAlarmVpContinuityLoss NOTIFICATION-TYPE
      OBJECTS  { alarmSeverity, alarmState, ifAlias }
      STATUS  current
      DESCRIPTION
	  	"This trap indicates Loss of Continuity Check on a VP Connection."
      ::= { radSysAtmEvents  40 }


atmAceAlarmVpAISReception NOTIFICATION-TYPE
      OBJECTS  { alarmSeverity, alarmState, ifAlias }
      STATUS  current
      DESCRIPTION
	  	"This trap indicates AIS Reception on a VP Connection."
      ::= { radSysAtmEvents  41 }


atmAceAlarmVpRDIReception NOTIFICATION-TYPE
      OBJECTS  { alarmSeverity, alarmState, ifAlias }
      STATUS  current
      DESCRIPTION
	  	"This trap indicates RDI Reception on a VP Connection."
      ::= { radSysAtmEvents  42 }


atmAceAlarmVpErroredCells NOTIFICATION-TYPE
      OBJECTS  { alarmSeverity, alarmState, ifAlias }
      STATUS  current
      DESCRIPTION
	  	"This trap indicates Errored Cells on a VP Connection reported by PM."
      ::= { radSysAtmEvents  43 }


atmAceAlarmVpLostCells NOTIFICATION-TYPE
      OBJECTS  { alarmSeverity, alarmState, ifAlias }
      STATUS  current
      DESCRIPTION
	  	"This trap indicates Lost Cells on a VP Connection reported by PM."
      ::= { radSysAtmEvents  44 }


atmAceAlarmVpMisinsertedCells NOTIFICATION-TYPE
      OBJECTS  { alarmSeverity, alarmState, ifAlias }
      STATUS  current
      DESCRIPTION
	  	"This trap indicates Misinserted Cells on a VP Connection
	  	reported by PM."
      ::= { radSysAtmEvents  45 }

atmAceAlarmVpUAS NOTIFICATION-TYPE
      OBJECTS  { alarmSeverity, alarmState, ifAlias }
      STATUS  current
      DESCRIPTION
	  	"This trap is sent upon UAS start or end per VP."
      ::= { radSysAtmEvents  46 }

atmAceAlarmVpLoopback NOTIFICATION-TYPE
      OBJECTS  { alarmSeverity, alarmState, ifAlias }
      STATUS  current
      DESCRIPTION
	  	"This trap is sent upon OAM LoopBack fail status per VP."
      ::= { radSysAtmEvents  47 }

atmAceAlarmVpGCRAViolation NOTIFICATION-TYPE
      OBJECTS  { alarmSeverity, alarmState, ifAlias }
      STATUS  current
      DESCRIPTION
	  	"This trap indicates GCRA violation on a VP Connection
		reported by UPC device."
      ::= { radSysAtmEvents  48 }


-- VC Layer Traps

-- atmVclVpi and atmVclVci have MAX-ACCESS "not-accessible"
-- and cannot be referenced from NOTIFICATION-TYPE clause
-- in SMIV2 so they where removed from following caluses.
-- Dovi Korngut (28/6/00).

atmAceAlarmVcContinuityLoss NOTIFICATION-TYPE
      OBJECTS  { alarmSeverity, alarmState, ifAlias }
      STATUS  current
      DESCRIPTION
	  	"This trap indicates  Loss of Continuity Check on a VC Connection."
      ::= { radSysAtmEvents  56 }

atmAceAlarmVcAISReception NOTIFICATION-TYPE
      OBJECTS  { alarmSeverity, alarmState, ifAlias }
      STATUS  current
      DESCRIPTION
	  	"This trap indicates AIS Reception on a VC."
      ::= { radSysAtmEvents  57 }

atmAceAlarmVcRDIReception NOTIFICATION-TYPE
      OBJECTS  { alarmSeverity, alarmState, ifAlias }
      STATUS  current
      DESCRIPTION
	  	"This trap indicates RDI Reception on a VC Connection."
      ::= { radSysAtmEvents  58 }

atmAceAlarmVcErroredCells NOTIFICATION-TYPE
      OBJECTS  { alarmSeverity, alarmState, ifAlias }
      STATUS  current
      DESCRIPTION
	  	"This trap indicates Errored Cells on a VC Connection reported by PM."
      ::= { radSysAtmEvents  59 }

atmAceAlarmVcLostCells NOTIFICATION-TYPE
      OBJECTS  { alarmSeverity, alarmState, ifAlias }
      STATUS  current
      DESCRIPTION
	  	"This trap indicates Lost Cells on a VC Connection reported by PM."
      ::= { radSysAtmEvents  60 }

atmAceAlarmVcMisinsertedCells NOTIFICATION-TYPE
      OBJECTS  { alarmSeverity, alarmState, ifAlias }
      STATUS  current
      DESCRIPTION
	  	"This trap indicates Misinserted Cells on a VC Connection reported
	  	by PM."
      ::= { radSysAtmEvents  61 }

atmAceAlarmVcUnexpectedCell NOTIFICATION-TYPE
      OBJECTS  { alarmSeverity, alarmState, ifAlias }
      STATUS  current
      DESCRIPTION
	  	"This trap indicates an unexpected cell from user or network port."
      ::= { radSysAtmEvents  62 }

atmAceAlarmVcUAS NOTIFICATION-TYPE
      OBJECTS  { alarmSeverity, alarmState, ifAlias }
      STATUS  current
      DESCRIPTION
	  	"This trap is sent upon UAS start or end per VC."
      ::= { radSysAtmEvents  63 }

atmAceAlarmVcLoopback NOTIFICATION-TYPE
      OBJECTS  { alarmSeverity, alarmState, ifAlias }
      STATUS  current
      DESCRIPTION
	  	"This trap is sent upon OAM LoopBack fail status per VC."
      ::= { radSysAtmEvents  64 }

atmAceAlarmVcGCRAViolation NOTIFICATION-TYPE
      OBJECTS  { alarmSeverity, alarmState, ifAlias }
      STATUS  current
      DESCRIPTION
	  	"This trap indicates GCRA violation on a VC Connection
		reported by UPC device."
      ::= { radSysAtmEvents  65 }

-- number 80 and up are saved for IMA traps

-- END

--
-- file :v:\doc\rdv\mib\ver465\router\ipRouter.txt
--


--Version:   1.0
--Date:      31.01.99
--By:        Ilana Schvetz
--File:      ipRouter.txt
--
--Last Update: Liora Gafni 18/09/00


--radRouter     OBJECT IDENTIFIER ::= { rad 11 }
--rtrBridge     OBJECT IDENTIFIER ::= { radRouter 7 }

ipRouter OBJECT IDENTIFIER ::= { rtrBridge 3 }



rtrIfIpTable OBJECT-TYPE
       SYNTAX SEQUENCE OF RtrIfIpEntry
       MAX-ACCESS not-accessible
       STATUS current
       DESCRIPTION
          "Router interfaces table."
       ::= { ipRouter 1 }

rtrIfIpEntry OBJECT-TYPE
       SYNTAX  RtrIfIpEntry
       MAX-ACCESS  not-accessible
       STATUS  current
       DESCRIPTION
	   "An entry in table rtrIfIpTable."
       INDEX   { rtrIfIp }
       ::= { rtrIfIpTable 1 }

RtrIfIpEntry ::=
       SEQUENCE {
              rtrIfIp         IpAddress,
			  rtrIfRowStatus  RowStatus,
              rtrIfIpMask     IpAddress,
			  rtrIfIndex      Integer32,
			  rtrIfMng        INTEGER
          }

rtrIfIp OBJECT-TYPE
       SYNTAX IpAddress
       MAX-ACCESS read-create
       STATUS current
       DESCRIPTION
           "IP Address."
       ::= { rtrIfIpEntry 1 }

rtrIfRowStatus OBJECT-TYPE
      SYNTAX  RowStatus
      MAX-ACCESS  read-create
      STATUS  current
      DESCRIPTION
          "."
      ::= { rtrIfIpEntry 2 }

rtrIfIpMask OBJECT-TYPE
       SYNTAX IpAddress
       MAX-ACCESS read-create
       STATUS current
       DESCRIPTION
           "IP mask Address."
       ::= { rtrIfIpEntry 3 }

rtrIfIndex OBJECT-TYPE
       SYNTAX Integer32
       MAX-ACCESS read-create
       STATUS current
       DESCRIPTION
           "The ifIndex connection, on which the IP is determined."
       ::= { rtrIfIpEntry 4 }

rtrIfMng OBJECT-TYPE
       SYNTAX INTEGER {
           no  (1),
           yes (2)
       }
       MAX-ACCESS read-create
       STATUS current
       DESCRIPTION
           "An IP interface might be determined as a management
           connection (under the product limitations)."
       ::= { rtrIfIpEntry 5 }

-- Brouter Table

brtrIfTable OBJECT-TYPE
       SYNTAX SEQUENCE OF BrtrIfEntry
       MAX-ACCESS not-accessible
       STATUS current
       DESCRIPTION
          "LAN interface table."
       ::= { ipRouter 2 }

brtrIfEntry OBJECT-TYPE
       SYNTAX  BrtrIfEntry
       MAX-ACCESS  not-accessible
       STATUS  current
       DESCRIPTION
           "The entries of this table will be created by agent ."
       INDEX   { brtrIfIndex }
       ::= { brtrIfTable 1 }


BrtrIfEntry ::=
       SEQUENCE {
              brtrIfIndex         Integer32,
			  brtrIfMode          INTEGER,
			  brtrIfMaxFrameSize  Integer32
  	    }

brtrIfIndex OBJECT-TYPE
       SYNTAX Integer32
       MAX-ACCESS read-only
       STATUS current
       DESCRIPTION
           "The index of the interface (LAN or ATM)."
       ::= { brtrIfEntry 1 }

brtrIfMode OBJECT-TYPE
       SYNTAX INTEGER {
           bridge    (1),
           router    (2),
           brouter   (3),
		   off       (4)
       }
       MAX-ACCESS read-write
       STATUS current
       DESCRIPTION
           "Connection Mode."
       ::= { brtrIfEntry 2 }

brtrIfMaxFrameSize OBJECT-TYPE
       SYNTAX Integer32
       MAX-ACCESS read-write
       STATUS current
       DESCRIPTION
           "Frame Max Size."
       ::= { brtrIfEntry 3 }



rtrArpAgingTime OBJECT-TYPE
       SYNTAX Integer32
       MAX-ACCESS read-write
       STATUS current
       DESCRIPTION
           "ARP Aging Time. Applicable for a Router Mode
           and for a Brouter Mode."
       ::= { ipRouter 3 }

-- Brouter LAN If table


brtrLanIfTable OBJECT-TYPE
       SYNTAX SEQUENCE OF BrtrLanIfEntry
       MAX-ACCESS not-accessible
       STATUS current
       DESCRIPTION
          "LAN interface table."
       ::= { ipRouter 4 }

brtrLanIfEntry OBJECT-TYPE
       SYNTAX  BrtrLanIfEntry
       MAX-ACCESS  not-accessible
       STATUS  current
       DESCRIPTION
           "The entries of this table will be created by agent ."
       INDEX   { brtrLanIfIndex }
       ::= { brtrLanIfTable 1 }


BrtrLanIfEntry ::=
       SEQUENCE {
              brtrLanIfIndex            Integer32,
			  brtrLanIpAddress          IpAddress,
			  brtrLanIpMask             IpAddress,
              brtrLanMaxRateEnable      INTEGER,
              brtrLanMaxRate            Integer32,
              brtrLanMng                INTEGER,
              brtrLanDefaultRouter      IpAddress
       }

brtrLanIfIndex OBJECT-TYPE
       SYNTAX Integer32
       MAX-ACCESS read-only
       STATUS current
       DESCRIPTION
           "The index of the LAN entity (physical interface)."
       ::= { brtrLanIfEntry 1 }

brtrLanIpAddress OBJECT-TYPE
       SYNTAX IpAddress
       MAX-ACCESS read-write
       STATUS current
       DESCRIPTION
           "Host IP address. Applicable for bridge mode connection only."
       ::= { brtrLanIfEntry 2 }

brtrLanIpMask OBJECT-TYPE
       SYNTAX IpAddress
       MAX-ACCESS read-write
       STATUS current
       DESCRIPTION
           "Host IP Mask. Applicable for bridge mode connection only."
       ::= { brtrLanIfEntry 3 }


brtrLanMaxRateEnable OBJECT-TYPE
       SYNTAX INTEGER {
          disable (1),
          enable  (2)
       }
       MAX-ACCESS read-only
       STATUS current
       DESCRIPTION
           "This parameter determines the HW ability of the LAN
           card according to HW."
       ::= { brtrLanIfEntry 4 }

brtrLanMaxRate OBJECT-TYPE
       SYNTAX Integer32
       MAX-ACCESS read-write
       STATUS current
       DESCRIPTION
           "Max Rate."
       ::= { brtrLanIfEntry 5 }

brtrLanMng OBJECT-TYPE
       SYNTAX INTEGER {
           no  (1),
           yes (2)
       }
       MAX-ACCESS read-write
       STATUS current
       DESCRIPTION
           "An IP interface might be determined as a management
           connection (under the product limitations)."
       ::= { brtrLanIfEntry 6 }

brtrLanDefaultRouter OBJECT-TYPE
       SYNTAX IpAddress
       MAX-ACCESS read-write
       STATUS current
       DESCRIPTION
           "Default Router's (Gateway's) IP Address.
            For each LAN interface there may be a different Default Router."
       ::= { brtrLanIfEntry 7 }



rtrIsdnIfTable OBJECT-TYPE
       SYNTAX SEQUENCE OF RtrIsdnIfEntry
       MAX-ACCESS not-accessible
       STATUS current
       DESCRIPTION
          "This table contains ISDN parameters that do not appear in the standard MIBs."
       ::= { ipRouter 5 }

rtrIsdnIfEntry OBJECT-TYPE
       SYNTAX  RtrIsdnIfEntry
       MAX-ACCESS  not-accessible
       STATUS  current
       DESCRIPTION
           "Entries for ISDN parameters that do not appear in the standard MIBs."
       AUGMENTS    { isdnSignalingEntry }
--        INDEX { isdnSignalingIndex }
       ::= { rtrIsdnIfTable 1 }


RtrIsdnIfEntry ::=
       SEQUENCE {
              rtrIsdnIfMinNumBchans            Integer32,
              rtrIsdnIfMaxNumBchans            Integer32
       }

rtrIsdnIfMinNumBchans OBJECT-TYPE
       SYNTAX Integer32
       MAX-ACCESS read-create
       STATUS current
       DESCRIPTION
           "Minimum number of B channels that the ISDN Dialer of the router will use
            for Dialing out.
            This parameter will be used for the BOD (Bandwidth On Demand) feature.
            Dial up on B channels is according to the need of bandwidth for router
            data transfer. Voice calls have a higher priority than router data.
            In case of few time slots the voice calls will cause disconnection of
            data channels up to the limit of minimum number of B channels."
       ::= { rtrIsdnIfEntry 1 }

rtrIsdnIfMaxNumBchans OBJECT-TYPE
       SYNTAX Integer32
       MAX-ACCESS read-create
       STATUS current
       DESCRIPTION
           "Maximum number of B channels that the ISDN Dialer of the router will use
            for Dialing out.
            This parameter will be used for the BOD (Bandwidth On Demand) feature.
            Dial up on B channels is according to the need of bandwidth for router
            data transfer. Voice calls have a higher priority than router data.
            No more than MAX B channels will be used by the ISDN dialer."
       ::= {rtrIsdnIfEntry  2 }


rtrLcrTable OBJECT-TYPE
       SYNTAX SEQUENCE OF RtrLcrEntry
       MAX-ACCESS not-accessible
       STATUS current
       DESCRIPTION
          "Least Cost Routing Table.
           The user will be able to set a prefix for an outgoing number
           that arrives with a predefined prefix in order to redirect
           the number for the LCR process to be achieved."
       ::= { ipRouter 6 }

rtrLcrEntry OBJECT-TYPE
       SYNTAX  RtrLcrEntry
       MAX-ACCESS  not-accessible
       STATUS  current
       DESCRIPTION
           "Least Cost Routing Entry."
       INDEX   { ifIndex, rtrLcrOutIfIndex }
       ::= { rtrLcrTable 1 }


RtrLcrEntry ::=
       SEQUENCE {
              rtrLcrOutIfIndex      InterfaceIndex,
			  rtrLcrRowStatus       RowStatus,
              rtrLcrInPrefix        DisplayString,
			  rtrLcrOutPrefix       DisplayString
       }

rtrLcrOutIfIndex OBJECT-TYPE
       SYNTAX InterfaceIndex
       MAX-ACCESS not-accessible
       STATUS current
       DESCRIPTION
           "The outgoing interface Number of the current route.
            The incoming interface number is the value of ifIndex."
       ::= { rtrLcrEntry 1 }

rtrLcrRowStatus OBJECT-TYPE
      SYNTAX  RowStatus
      MAX-ACCESS  read-create
      STATUS  current
      DESCRIPTION
          "Row Status for adding/destroying rows."
      ::= { rtrLcrEntry 2 }

rtrLcrInPrefix OBJECT-TYPE
       SYNTAX DisplayString
       MAX-ACCESS read-create
       STATUS current
       DESCRIPTION
           "This prefix is part of the called number existing in the incoming packet."
       ::= {rtrLcrEntry  3 }

rtrLcrOutPrefix OBJECT-TYPE
       SYNTAX DisplayString
       MAX-ACCESS read-create
       STATUS current
       DESCRIPTION
           "This prefix will be inserted into the outgoing packet."
       ::= {rtrLcrEntry  4 }




--radRouter     OBJECT IDENTIFIER ::= { rad 11 }

multicastGen    OBJECT IDENTIFIER ::= { radRouter 8 } -- General Multicast Parameters

multicastMode  OBJECT-TYPE
      SYNTAX INTEGER {
      disable  (2),
      wanToLan (3),
      wanToLanIgmp (4),
	  lanToWan (5),
      bidirectional(6),
      transparent(7)
      }
	  MAX-ACCESS read-write
      STATUS current
      DESCRIPTION
      "According to this mode the packets will be forwarded.
       If disable (2) is selected, there will be no multicast."
      ::= { multicastGen 1 }
--
-- file :v:\doc\rdv\mib\ver480\clksrc.txt
--
-- file  : clksrc.txt
--
-- available for ACE2002. This file is part of dxc.txt.
--Version:   1.0
--Date:      9.7.00
--By:        Ilana Schvetz
--File:      v:\doc\rdv\mib\ver480\clksrc.txt

--Last Update: 25.11.01 by Ilana
-- Copyright 1997 RAD Data Communications, Ltd.
-- All Rights Reserved.


dacsMux       OBJECT IDENTIFIER ::= {radWan 3}

systemDacsMux OBJECT IDENTIFIER ::= {dacsMux 1}

sysStatus     OBJECT IDENTIFIER ::= {systemDacsMux 3}
sysConfig     OBJECT IDENTIFIER ::= {systemDacsMux 6}


sysSClkSrc  OBJECT-TYPE
      SYNTAX  INTEGER
    {
        master  (1),
        fallback(2),
        internal(3),
        ml      (4)
    }
      MAX-ACCESS  read-only
      STATUS  current
      DESCRIPTION
     "This entry indicates the source of the system clock."
      ::= { sysStatus 7 }


--System Configuration Parameters

sysCClkSrcTable  OBJECT-TYPE
      SYNTAX SEQUENCE OF SysCClkSrcEntry
      MAX-ACCESS not-accessible
      STATUS  current
      DESCRIPTION
      "All the entries of this table are identical (have the
       same value) for all the configurations (1..255) except
       the TmpCnfg.
       The write operation into the Table Objects is valid only
       for the TmpCnfg entry."
       ::= { sysConfig 1}

sysCClkSrcEntry OBJECT-TYPE
      SYNTAX SysCClkSrcEntry
      MAX-ACCESS not-accessible
      STATUS current
	DESCRIPTION  "An entry in table."
	INDEX {sysCClkCnfgIdx, sysCClkSrcIdx}
      ::= { sysCClkSrcTable 1}

SysCClkSrcEntry ::=
      SEQUENCE {
   sysCClkCnfgIdx      Integer32,
   sysCClkSrcIdx       INTEGER,
   sysCClkSrcMode      INTEGER,
   sysCClkSrcPrt       Integer32,
   sysCClkStationFreq  INTEGER,
   sysCClkRevertiveTimeout  Integer32
	}

sysCClkCnfgIdx OBJECT-TYPE
      SYNTAX Integer32 (1..255)
      MAX-ACCESS read-only
      STATUS current
      DESCRIPTION
      "This attribute indicates the Idx of the Cnfg(1..255) being
       accessed ; Idx of 255 relates to the TmpCnfg."
      ::= { sysCClkSrcEntry 1}
-- In phase I of DXC and FCD, only the values 1 (Cnfg1) and 255
-- (temp) are valid.

sysCClkSrcIdx OBJECT-TYPE
      SYNTAX  INTEGER
       {
     master    (1),
     fallback  (2)
    }
      MAX-ACCESS  read-only
      STATUS  current
      DESCRIPTION
      "An index in the table. There are only two entries in the
       table.
       master   - refers Master clock parameters
       fallback - refers Fallback clock parameters"
      ::= { sysCClkSrcEntry 2}

sysCClkSrcMode OBJECT-TYPE
      SYNTAX  INTEGER
       {
     none            (1),
     internal        (2),
     rxClk           (3),
     station         (4),
     lbt             (5),
	 ntr             (6),
	 adaptive        (7),
     notApplicable (255)
       }
      MAX-ACCESS  read-write
      STATUS  current
      DESCRIPTION
      "This entry indicates the source the nodal timing is
       locked to.
       none     - is an invalid option for Master clock.
       internal - is an invalid option for Fallback clock .
       station  - is an invalid option for a stand-alone unit.
       lbt      - loop-back timing
	   ntr      - A system locked reference clock
	   adaptive - clcok locking is achieved by altering the clock
	              according to the data load
       notApplicable - for ML source of Kmux or ML Timing
                       combinations when Master/Fallback clock are
                       not applicable."
      ::= { sysCClkSrcEntry 3}


sysCClkSrcPrt OBJECT-TYPE
      SYNTAX  Integer32
      MAX-ACCESS  read-write
      STATUS  current
      DESCRIPTION
      "This entry is valid only when working in rxClk mode.
       For invalid entry the return value will be 9999.

       The valid port number depends on the IO slot no.,  the
       installed card type and the port type: outside, inside,
       SP.
    * The SP ports will be numbered as follows:
     - SP port 1 :  1
     - SP port 2 :  2
	   For external ports the convention used will be (for DXC):
         - first two digits will be: (IO slot number+10)
         - last one/two digits will be the port number within the
           card, in odd numbers:
           port1 = 1
           port2 = 3
           port3 = 5
           etc...
           Example: port2 of IO slot 11 will be: 213 .
       For internal ports the convention used will be (for DXC):
         - first two digits will be: (IO slot number+10)
         - last one/two digits will be the port number within the
           card, in even numbers:
           port1 = 2
           port2 = 4
           port3 = 6
           etc...
           Example: port2 of IO slot 11 will be: 214 .

      For Kmux, the port will be according to : Slot*100+Ch.

      For ACE2002 and LA140, the port will be ifIndex."
      ::= { sysCClkSrcEntry 4}

sysCClkStationFreq OBJECT-TYPE
      SYNTAX  INTEGER
       {
     notApplicable   (1),
     f1544Khz        (2),
     f2048Khz        (3)
       }
      MAX-ACCESS  read-write
      STATUS  current
      DESCRIPTION
      "This entry indicates the frequency of the station clock
       when the source is 'station'.
       The value will be applicable only when the sysCClkSrcMode is
       'station'. "
      ::= { sysCClkSrcEntry 5}

sysCClkRevertiveTimeout OBJECT-TYPE
      SYNTAX  Integer32
      MAX-ACCESS  read-write
      STATUS  current
      DESCRIPTION
      "The time in seconds in which the system will monitor the higher
       level clock source, before decision to revert to that clock.
       In case the time is zero, revertive mode will be disabled."
      ::= { sysCClkSrcEntry 6}

--#include        <v:\doc\rdv\mib\ver470\bdband.txt>
--#include        <v:\doc\rdv\mib\ver475\atm\sub_rtr.txt>
--
-- file :v:\doc\rdv\mib\ver470\atm\layer2.txt
--
--
-- file: v:\doc\rdv\mib\ver470\atm\layer2.txt
--
--RTR-MIB
--
--Last update: 24-Jan-2001
--By: Ilana Schvetz


-- ************************************************
-- Link Layer (layer 2)  MIB
-- ************************************************


atmLayer2  OBJECT IDENTIFIER  ::=  {radAtm 7}

 atmLayer2XVclTable OBJECT-TYPE
	SYNTAX SEQUENCE OF AtmLayer2XVclEntry
	MAX-ACCESS not-accessible
	STATUS current
	DESCRIPTION
    "This table is an extension of VCL table, which is created
    for each LAN VCC."
	::= { atmLayer2 1 }

 atmLayer2XVclEntry OBJECT-TYPE
	SYNTAX AtmLayer2XVclEntry
	MAX-ACCESS not-accessible
	STATUS current
	DESCRIPTION
    "Conceptual row in atmVclTable.
    This table augments the RFC2515 VCL table."
 AUGMENTS { atmVclEntry }
	::= { atmLayer2XVclTable 1 }

 AtmLayer2XVclEntry ::= SEQUENCE {
	atmLayer2XVclConnMode       INTEGER,
    atmLayer2XVclGroupIdx       Integer32
 }

 atmLayer2XVclConnMode OBJECT-TYPE
	SYNTAX INTEGER {
	              main   (1),
	              sub    (2)
				   }
	MAX-ACCESS read-create
	STATUS current
	DESCRIPTION
    "Each valid LAN VCC is either Main or Sub.
	This parameter is configured only once on creation of a LAN VCC.
	It can not be changed after creation. In order to change the Mode,
	user should delete the connection and create a new one.

    main - A LAN VCC, which holds its own bridge port.
           Bridge forwarding and Bridge learning is performed only on Main
	       VCCs.
	       For working on a transparent bridge, that doesn't perform
	       layer 2 priority mapping, a Main VCC should be opened, which
		   is the default connection Mode.
		   When working with layer 2 priority, a group of LAN VCCs should
		   be configured, where each group will be associated with only
		   one Main VCC.
		   A specific Main can not be used by more than one group.
	sub  - A LAN VCC is not part of the bridging mechanism.
		   A Sub VCC automatically inherit some general definitions from
		   Main VCC of its group: ATM Slot/Port and LAN Slot/Port.
		   Max number of Sub VCCs allowed per group is:
		   [Number of Priorities - 1]."
	::= { atmLayer2XVclEntry 1 }

 atmLayer2XVclGroupIdx OBJECT-TYPE
	SYNTAX Integer32
	MAX-ACCESS read-only
	STATUS current
	DESCRIPTION
	"The group identifier.
	A VCC Group identifier = 0 if the VCC was not associated with a
	group yet.
	This value is updated according to the group identifier set by
	atmLayer2GroupTable."
	::= { atmLayer2XVclEntry 2 }

 atmLayer2GroupTable OBJECT-TYPE
	SYNTAX SEQUENCE OF AtmLayer2GroupEntry
	MAX-ACCESS not-accessible
	STATUS current
	DESCRIPTION
	"This table contains groups and their members.
	A group is a bundle of VCCs, which acts as different queues.
	Main and Sub VCCs should have the same ATM slot and port,
	and the same LAN slot and port.
    Each group contains: 1 to <number of priorities> VCCs."
	::= { atmLayer2 2 }

 atmLayer2GroupEntry OBJECT-TYPE
	SYNTAX AtmLayer2GroupEntry
	MAX-ACCESS not-accessible
	STATUS current
	DESCRIPTION
	"Conceptual row in atmLayer2GroupTable.
	The indexes: ifIndex, atmVclVpi and atmVclVci indicate
	the Network ATM End-Point.
	Upon a group creation, one Main VCC must be added first.
	After the group was created, Sub VCCs may be added to the group."
 INDEX { atmLayer2GroupIdx, ifIndex, atmVclVpi, atmVclVci }
	::= { atmLayer2GroupTable 1 }

 AtmLayer2GroupEntry ::= SEQUENCE {
    atmLayer2GroupIdx          Integer32,
    atmLayer2GroupRowStatus    RowStatus,
    atmLayer2GroupConnMode     INTEGER,
    atmLayer2GroupConnPriority OCTET STRING,
    atmLayer2GroupName         SnmpAdminString
 }

 atmLayer2GroupIdx OBJECT-TYPE
	SYNTAX Integer32
	MAX-ACCESS read-only
	STATUS current
	DESCRIPTION
	"The group identifier.
	0 is not a valid index."
	::= { atmLayer2GroupEntry 1 }

 atmLayer2GroupRowStatus OBJECT-TYPE
	SYNTAX RowStatus
	MAX-ACCESS read-create
	STATUS current
	DESCRIPTION
	"Creation/Deletion of rows in the table, and indication of the
	entry's status."
	::= {atmLayer2GroupEntry 2 }

 atmLayer2GroupConnMode OBJECT-TYPE
	SYNTAX INTEGER {
	              main (1),
	              sub  (2)
				   }
	MAX-ACCESS read-only
	STATUS current
	DESCRIPTION
	"Each valid LAN VCC is either Main or Sub as configured in
	atmLayer2XVclTable."
	::= { atmLayer2GroupEntry 3 }

 atmLayer2GroupConnPriority OBJECT-TYPE
    SYNTAX OCTET STRING (SIZE (1))
	MAX-ACCESS read-only
	STATUS current
	DESCRIPTION
	"This parameter is configured by atmLayer2PriorityRx from
	atmLayer2PriorityTable.
	Each bit in the Octet represents a specific priority as follows:


             MSB 7  6  5  4  3  2  1  0 LSB	  -> Priorities
                 |____________________|
                 1  0  0  1  0  0  0  1		  ->	  Value

	In this example, a certain VCC has several priorities: 0, 4 and 7."
	::= { atmLayer2GroupEntry 4 }

 atmLayer2GroupName OBJECT-TYPE
	SYNTAX SnmpAdminString (SIZE (1..32))
	MAX-ACCESS read-create
	STATUS current
	DESCRIPTION
	"Group name. Configured by the user.
	The name is unique per system.
	For atmLayer2GroupIdx=0, the name will be null."
	::= { atmLayer2GroupEntry 5 }


 atmLayer2PriorityTable OBJECT-TYPE
	SYNTAX SEQUENCE OF AtmLayer2PriorityEntry
	MAX-ACCESS not-accessible
	STATUS current
	DESCRIPTION
	"This table maps all priorities inside a group.
	Several priorities might be mapped to the same VCC.
	Upon priority change, the agent will update the VCCs of the
	changed priority in this table, and will update	-
	atmLayer2GroupConnPriority parameter of both former and new owners
	of the changed priority.
	Changing a VCC value is actually a change of three parameters
	simultaneously: atmLayer2PriorityIfIndex, atmLayer2PriorityVclVpi
	and atmLayer2PriorityVclVci. Otherwise, the set will be rejected,
	since there might be that such VCC doesn't exist in the specific
	group."
	::= { atmLayer2 3 }

 atmLayer2PriorityEntry OBJECT-TYPE
	SYNTAX AtmLayer2PriorityEntry
	MAX-ACCESS not-accessible
	STATUS current
	DESCRIPTION
	"Conceptual row in atmLayer2PriorityTable.
	Each entry is a Network ATM End-Point per priority.
	Upon a group creation, all priorities are mapped to the Main VCC.
	Number of entries per group is according to the number of
	priorities enabled. (For example, for Max priorities = 8,
	the agent will create 8 entries)."
    INDEX { atmLayer2PriorityGroupIdx, atmLayer2PriorityRx }
	::= { atmLayer2PriorityTable 1 }

 AtmLayer2PriorityEntry ::= SEQUENCE {
    atmLayer2PriorityGroupIdx        Integer32,
    atmLayer2PriorityRx              INTEGER,
	atmLayer2PriorityIfIndex	     InterfaceIndex,
    atmLayer2PriorityVclVpi          Integer32,
    atmLayer2PriorityVclVci          Integer32
 }

 atmLayer2PriorityGroupIdx OBJECT-TYPE
	SYNTAX Integer32
	MAX-ACCESS read-only
	STATUS current
	DESCRIPTION
	"The group identifier."
	::= { atmLayer2PriorityEntry 1 }

 atmLayer2PriorityRx OBJECT-TYPE
	SYNTAX INTEGER (1..8)
	MAX-ACCESS read-only
	STATUS current
	DESCRIPTION
	"The priority values.
	The used values are 0-7, but since this value is part of the index
	of the table, and in order to avoid '0' as an index, the index syntax
	is 1..8, but the real value is atmLayer2PriorityRx-1:
		  0 - for Low priority.
		  7 - for High priority."
	::= { atmLayer2PriorityEntry 2 }

 atmLayer2PriorityIfIndex OBJECT-TYPE
	SYNTAX InterfaceIndex
	MAX-ACCESS read-create
	STATUS current
	DESCRIPTION
	"ATM ifIndex of the network End-Point."
	::= { atmLayer2PriorityEntry 3 }

 atmLayer2PriorityVclVpi OBJECT-TYPE
	SYNTAX Integer32
	MAX-ACCESS read-create
	STATUS current
	DESCRIPTION
	"Vpi of the network End-Point."
	::= { atmLayer2PriorityEntry 4 }

 atmLayer2PriorityVclVci OBJECT-TYPE
	SYNTAX Integer32
	MAX-ACCESS read-create
	STATUS current
	DESCRIPTION
	"Vci of the network End-Point."
	::= { atmLayer2PriorityEntry 5 }

atmLayer2GroupIndexNext  OBJECT-TYPE
          SYNTAX         Integer32 (0..2147483647)
          MAX-ACCESS     read-only
          STATUS         current
          DESCRIPTION
           "This object contains an appropriate value to
            be used for atmLayer2GroupIdx when creating
            entries in the atmLayer2GroupTable. The value
            0 indicates that no unassigned entries are
            available. To obtain the atmLayer2GroupIdx
            value for a new entry, the manager gets
            the current value of this object. The next index
            will be of the first unassigned entry. It will be
            provided by checking the assigned entries."
          ::= { atmLayer2 4 }
--
-- file :v:\doc\rdv\mib\ver470\atm\frAtm.txt
--
--
-- file: v:\doc\rdv\mib\ver470\atm\frAtm.txt
--
--FR-ATM-IWF-X-MIB
--
--Last update: 28-Feb-2001
--By: Ilana Schvetz


--atmSuPortFr     OBJECT IDENTIFIER ::= { atmSuPort 4 }
radAtmFr  OBJECT IDENTIFIER  ::=  {radAtm 8}

 frAtmIwfXConnectionTable OBJECT-TYPE
	SYNTAX SEQUENCE OF FrAtmIwfXConnectionEntry
	MAX-ACCESS not-accessible
	STATUS current
	DESCRIPTION
    "This table is an extension of frAtmIwfXConnectionTable from
    RFC2955."
	::= { radAtmFr 1 }

 frAtmIwfXConnectionEntry OBJECT-TYPE
	SYNTAX FrAtmIwfXConnectionEntry
	MAX-ACCESS not-accessible
	STATUS current
	DESCRIPTION
    "Conceptual row in frAtmIwfXConnectionTable.
    This table augments the RFC2955."
 AUGMENTS { frAtmIwfConnectionEntry }
	::= { frAtmIwfXConnectionTable 1 }

 FrAtmIwfXConnectionEntry ::= SEQUENCE {
                 frAtmIwfXConnMode         INTEGER,
                 frAtmIwfXConnSscsDlci     Integer32
 }

         frAtmIwfXConnMode OBJECT-TYPE
             SYNTAX      INTEGER { service(1), network(2) }
             MAX-ACCESS  read-create
             STATUS      current
             DESCRIPTION
                     "FR IWF Mode.
                     service - Service InterWorking (FRF.8),
                     network - Network InterWorking (FRF.5)."
	         ::= { frAtmIwfXConnectionEntry 1 }

         frAtmIwfXConnSscsDlci OBJECT-TYPE
             SYNTAX      Integer32
             MAX-ACCESS  read-create
             STATUS      current
             DESCRIPTION
                     "This parameter is relevant for
                     frAtmIwfXConnMode=network (FRF.5) only.
                     This parameter allow configuration of the
                     FR SSCS DLCI that is transferred to the
                     remote FR unit."
	         ::= { frAtmIwfXConnectionEntry 2 }

--
-- file :v:\doc\rdv\mib\ver470\atm\radaal5.txt
--
--
-- file :v:\doc\rdv\mib\ver470\atm\radaal5.txt
--


--     ATM-X-MIB DEFINITIONS ::= BEGIN
--
--atmGen  OBJECT IDENTIFIER  ::=  {radAtm 2}

--atmPerfHistory  OBJECT IDENTIFIER  ::=  {atmGen 1}

--atmIfPerformance  OBJECT IDENTIFIER  ::=  {atmPerfHistory 1}

     -- AAL5 Virtual Channel Connection Performance Statistics

     -- Table

     -- This table contains the AAL5 extension
     -- performance statistics of a VCC at the
     -- interface associated with an AAL5 entity in an ATM
     -- host or ATM switch.

     aal5VccXTable        OBJECT-TYPE
          SYNTAX         SEQUENCE OF Aal5VccXEntry
          MAX-ACCESS     not-accessible
          STATUS         current
          DESCRIPTION
           "This table is an extension to AAL5 VCC Table."
          ::= { atmIfPerformance 4 }

     aal5VccXEntry        OBJECT-TYPE
          SYNTAX         Aal5VccXEntry
          MAX-ACCESS     not-accessible
          STATUS         current
          DESCRIPTION
           "This list contains the additional AAL5 VCC
            performance parameters and is indexed
            by ifIndex values of AAL5 interfaces
            and the associated VPI/VCI values."
          AUGMENTS { aal5VccEntry }
          ::= { aal5VccXTable 1 }

     Aal5VccXEntry    ::= SEQUENCE  {
          aal5VccInFrames     Counter32,
          aal5VccOutFrames    Counter32,
		  aal5VccUnknownProtocolFrames	 Counter32
               }

     aal5VccInFrames  OBJECT-TYPE
          SYNTAX         Counter32
          MAX-ACCESS     read-only
          STATUS         current
          DESCRIPTION
           "The number of frames received via this interface."
          ::= { aal5VccXEntry 1 }

     aal5VccOutFrames OBJECT-TYPE
          SYNTAX         Counter32
          MAX-ACCESS     read-only
          STATUS         current
          DESCRIPTION
           "The total number of frames transmitted out of the
           interface."
          ::= { aal5VccXEntry 2 }

    aal5VccUnknownProtocolFrames OBJECT-TYPE
          SYNTAX         Counter32
          MAX-ACCESS     read-only
          STATUS         current
          DESCRIPTION
           "The number of frames that were discarded due to unsupported
            protocol  encapsulation on this VCC."
          ::= { aal5VccXEntry 3 }



-- END


-- clksrc.txt is the clock source table that was taken from dacs.txt for ace2002 use

END
