RAD-ds1Interface-MIB DEFINITIONS ::= BEGIN

-- It is RAD's intent to encourage the widespread use of
-- this Specification in connection with the management of
-- RAD products. RAD grants vendors, end-users,
-- and other interested parties a non-exclusive license to
-- use this Specification in connection with the management
-- of RAD products.

-- This Specification is supplied "as is," and RAD makes
-- no warranty, either express or implied, as to the use,
-- operation, condition, or performance of the Specification.


IMPORTS

       dsx1LineStatus, dsx1CurrentIndex, dsx1LineIndex,
       dsx1IntervalIndex, dsx1IntervalNumber, dsx1LoopbackStatus,
       dsx1TotalIndex, dsx1IntervalLESs, dsx1IntervalPCVs,
       dsx1IntervalESs, dsx1IntervalSESs, dsx1IntervalSEFSs,
       dsx1IntervalCSSs, dsx1IntervalUASs     FROM  DS1-MIB
       InterfaceIndex, ifAlias     FROM  IF-MIB
       PerfCurrentCount, PerfIntervalCount, PerfTotalCount     FROM  PerfHist-TC-MIB
       Integer32, Counter32, Gauge32,
       Unsigned32, OBJECT-TYPE, MODULE-IDENTITY,
       NOTIFICATION-TYPE     FROM  SNMPv2-SMI
       TruthValue     FROM  SNMPv2-TC
       diverseIfWanGen     FROM  RAD-SMI-MIB
       DayType     FROM  RAD-TC
       alarmEventLogSourceName, alarmEventLogAlarmOrEventId, alarmEventLogDescription,
       alarmEventLogSeverity, alarmEventLogDateAndTime, alarmEventReason     FROM  RAD-GEN-MIB;


    ds1Interface MODULE-IDENTITY
        LAST-UPDATED "201604211804Z"  -- April 21, 2016
        ORGANIZATION "RAD Data Communications Ltd."
        CONTACT-INFO
        "System Department

         Email:  mibs@rad.com
         Postal: RAD Data Communications Ltd.
                 24 Raoul Wallenberg St.
                 Tel-Aviv 6971920
                 Israel

         Phone:  +972-3-645-5421
         Fax:    +972-3-760-7844"
         DESCRIPTION
            "DS1 MIB."
    ::= { diverseIfWanGen 4 }


-- MIB is changed due to complilation problems:
-- As variable in the same name exists in DS1-MIB, dsx1LineMode is renamed to dsx1LineModeR.

prtDS1Events OBJECT IDENTIFIER       ::= {ds1Interface 0}

prtDs1PerfHistory  OBJECT IDENTIFIER  ::=  {ds1Interface 1}




--   Extension to the dsx1 current table

dsx1XCurrentTable  OBJECT-TYPE
       SYNTAX      SEQUENCE OF Dsx1XCurrentEntry
       MAX-ACCESS  not-accessible
       STATUS      current
       DESCRIPTION
       "A list of current statistics entries.  This table
        contains additional objects for the current table."
       ::= { prtDs1PerfHistory 2 }

dsx1XCurrentEntry OBJECT-TYPE
       SYNTAX  Dsx1XCurrentEntry
       MAX-ACCESS  not-accessible
       STATUS      current
       DESCRIPTION
       "An entry containing additional statistical counters
        applicable to a particular current table."
 --      AUGMENTS    { dsx1CurrentEntry }
         INDEX   { dsx1CurrentIndex }
       ::= { dsx1XCurrentTable 1 }

Dsx1XCurrentEntry ::= SEQUENCE {
    dsx1CurrentLOS          PerfCurrentCount,
    dsx1CurrentLOF          PerfCurrentCount,
    dsx1CurrentLOC          PerfCurrentCount,
    dsx1CurrentAIS          PerfCurrentCount,
    dsx1CurrentRAI          PerfCurrentCount,
    dsx1CurrentLOMF         PerfCurrentCount,
    dsx1CurrentFEBE         PerfCurrentCount,
    dsx1CurrentStatus       OCTET STRING,
    dsx1CurrentBPV          PerfCurrentCount,
    dsx1CurrentLOCRCMF      PerfCurrentCount,
    dsx1CurrentLOFC         PerfCurrentCount,
    dsx1CurrentCRCErrors    PerfCurrentCount,
    dsx1CurrentLSES         PerfCurrentCount,
    dsx1CurrentFC           PerfCurrentCount
 }

dsx1CurrentLOS OBJECT-TYPE
        SYNTAX PerfCurrentCount
        MAX-ACCESS  read-only
        STATUS  current
        DESCRIPTION
        "The counter associated with the number of LOS
         seconds, encountered by a DS1 interface in
         the current 15 minute interval."
        ::= { dsx1XCurrentEntry 1 }

dsx1CurrentLOF OBJECT-TYPE
        SYNTAX PerfCurrentCount
        MAX-ACCESS  read-only
        STATUS  current
        DESCRIPTION
        "The counter associated with the number of LOF
         seconds, encountered by a DS1
         interface in the current 15 minute interval."
        ::= { dsx1XCurrentEntry 2 }


dsx1CurrentLOC OBJECT-TYPE
         SYNTAX PerfCurrentCount
         MAX-ACCESS  read-only
         STATUS  current
         DESCRIPTION
         " Loss Of Cell delineation. Counts number of cells the ATM UNI cells receiver
           lost cells delineation ."
         ::= { dsx1XCurrentEntry 3 }

dsx1CurrentAIS OBJECT-TYPE
        SYNTAX PerfCurrentCount
        MAX-ACCESS  read-only
        STATUS  current
        DESCRIPTION
        "The counter associated with the number of AIS
         seconds, encountered by a DS1
         interface in the current 15 minute interval."
        ::= { dsx1XCurrentEntry 4 }

dsx1CurrentRAI OBJECT-TYPE
         SYNTAX PerfCurrentCount
         MAX-ACCESS  read-only
         STATUS  current
         DESCRIPTION
         "Remote Alarm Indication: Transmitted  in the outgoing direction
          (toward the PABX) over FDL bits when the DS1 device detected
          an incoming Loss Of Frame. Received from the far end (PABX)
          over FDL when it detects a Loss of frame."
         ::= { dsx1XCurrentEntry 5 }

dsx1CurrentLOMF OBJECT-TYPE
         SYNTAX PerfCurrentCount
         MAX-ACCESS  read-only
         STATUS  current
         DESCRIPTION
         "Loss of Multi-Frame sequence  in E1 time slot 16."
         ::= { dsx1XCurrentEntry 6 }

dsx1CurrentFEBE OBJECT-TYPE
         SYNTAX PerfCurrentCount
         MAX-ACCESS  read-only
         STATUS  current
         DESCRIPTION
         "Far End Block Errors, as reported in the first bit
          of frames 13 and 15, on multiframe E1 lines with CRC4,
          in the current 15 minute interval."
         ::= { dsx1XCurrentEntry 7 }

dsx1CurrentStatus OBJECT-TYPE
    SYNTAX OCTET STRING  (SIZE (4))
         MAX-ACCESS  read-only
         STATUS  current
         DESCRIPTION
         "The statuses of the current interval:
           0 - Valid.
           1 - redundantLinkSwitch - the link has been switched
               by a redundancy mechanism.
           2 - discontinuity - module was partialy out.
           4 - notValid - module is out."
         ::= { dsx1XCurrentEntry 8 }

dsx1CurrentBPV OBJECT-TYPE
         SYNTAX PerfCurrentCount
         MAX-ACCESS  read-only
         STATUS  current
         DESCRIPTION
         "The counter associated with the number of BPVs (Bi-Polar Violations)
          encountered by a DS1  interface in the current 15 minute interval."
         ::= { dsx1XCurrentEntry 9 }

dsx1CurrentLOCRCMF OBJECT-TYPE
         SYNTAX PerfCurrentCount
         MAX-ACCESS  read-only
         STATUS  current
         DESCRIPTION
         "Loss of CRC4 Multi-Frame sequence in E1.
          encountered in the current 15 minute interval"
         ::= { dsx1XCurrentEntry 10 }

dsx1CurrentLOFC OBJECT-TYPE
         SYNTAX PerfCurrentCount
         MAX-ACCESS  read-only
         STATUS  current
         DESCRIPTION
         "Counts the number of loss of frame events measured.
          encountered in the current 15 minute interval"
         ::= { dsx1XCurrentEntry 11 }

dsx1CurrentCRCErrors  OBJECT-TYPE
         SYNTAX PerfCurrentCount
         MAX-ACCESS  read-only
         STATUS  current
         DESCRIPTION
         "Counts the number of CRC error events,
          encountered in the current 15 minute interval."
         ::= { dsx1XCurrentEntry 12 }

dsx1CurrentLSES OBJECT-TYPE
    SYNTAX      PerfCurrentCount
    MAX-ACCESS  read-only
    STATUS      current
    DESCRIPTION
            "Counts the number of LSES (Line Severely Errored Seconds)
            encountered in the current 15 minute interval."
    ::= { dsx1XCurrentEntry 13 }

dsx1CurrentFC OBJECT-TYPE
    SYNTAX      PerfCurrentCount
    MAX-ACCESS  read-only
    STATUS      current
    DESCRIPTION
            "Counts the number of FC (Path failure events) encountered
            in the current 15 minute interval."
    ::= { dsx1XCurrentEntry 14 }


-- Interval table is deprecated, see dsx1IntervalNumTable

dsx1XIntervalTable OBJECT-TYPE
         SYNTAX  SEQUENCE OF Dsx1XIntervalEntry
         MAX-ACCESS  not-accessible
         STATUS  deprecated
         DESCRIPTION
         "A list of Interval entries.  This table
           contains additional objects for the interval table."
         ::= { prtDs1PerfHistory 3 }

dsx1XIntervalEntry OBJECT-TYPE
         SYNTAX  Dsx1XIntervalEntry
         MAX-ACCESS  not-accessible
         STATUS  deprecated
         DESCRIPTION
         "An entry containing additional statistical counters
          applicable to a particular interval table."
      -- AUGMENTS    { dsx1IntervalEntry }
         INDEX   { dsx1IntervalIndex, dsx1IntervalNumber }
         ::= { dsx1XIntervalTable 1 }

Dsx1XIntervalEntry ::= SEQUENCE {
    dsx1IntervalLOS         PerfIntervalCount,
    dsx1IntervalLOF         PerfIntervalCount,
	     dsx1IntervalLOC       PerfIntervalCount,
    dsx1IntervalAIS         PerfIntervalCount,
    dsx1IntervalRAI         PerfIntervalCount,
    	     dsx1IntervalLOMF	   PerfIntervalCount,
		 dsx1IntervalFEBE	   PerfIntervalCount,
         dsx1IntervalStatus	   OCTET STRING,
         dsx1IntervalBPV	   PerfIntervalCount,
		 dsx1IntervalLOCRCMF   PerfIntervalCount,
		 dsx1IntervalLOFC	   PerfIntervalCount,
    dsx1IntervalLSES        PerfIntervalCount,
    dsx1IntervalFC          PerfIntervalCount
 }

dsx1IntervalLOS OBJECT-TYPE
         SYNTAX PerfIntervalCount
         MAX-ACCESS  read-only
         STATUS  deprecated
         DESCRIPTION
          "The counter associated with the number of LOS
           seconds , encountered by a DS1 interface in
           one of the previous 96, individual 15 minute,
           intervals."
         ::= { dsx1XIntervalEntry 1 }

dsx1IntervalLOF OBJECT-TYPE
          SYNTAX PerfIntervalCount
          MAX-ACCESS  read-only
          STATUS  deprecated
          DESCRIPTION
           "The counter associated with the number of OOF
            seconds, encountered by a DS1
            interface in one of the previous 96, individual 15
            minute, intervals."
          ::= { dsx1XIntervalEntry 2 }

dsx1IntervalLOC OBJECT-TYPE
         SYNTAX PerfIntervalCount
         MAX-ACCESS  read-only
         STATUS  current
         DESCRIPTION
          " Loss Of Cell delineation. Counts number of cells the ATM UNI cells receiver
            lost cells delineation ."
         ::= { dsx1XIntervalEntry 3 }

dsx1IntervalAIS OBJECT-TYPE
          SYNTAX PerfIntervalCount
          MAX-ACCESS  read-only
          STATUS  deprecated
          DESCRIPTION
           "The counter associated with the number of AIS
            seconds, encountered by a SONET
            interface in one of the previous 96, individual 15
            minute, intervals."
          ::= { dsx1XIntervalEntry 4 }

dsx1IntervalRAI OBJECT-TYPE
           SYNTAX PerfIntervalCount
           MAX-ACCESS  read-only
           STATUS  deprecated
           DESCRIPTION
           "Remote Alarm Indication: Transmitted  in the outgoing direction
            (toward the PABX) over FDL bits when the DS1 device detected
            an incoming Loss Of Frame. Received from the far end (PABX)
            over FDL when it detects a Loss of frame."
           ::= { dsx1XIntervalEntry 5 }

dsx1IntervalLOMF OBJECT-TYPE
           SYNTAX PerfIntervalCount
           MAX-ACCESS  read-only
           STATUS  current
           DESCRIPTION
           "Loss of Multi-Frame sequence  in E1 time slot 16."
           ::= { dsx1XIntervalEntry 6 }

dsx1IntervalFEBE OBJECT-TYPE
          SYNTAX PerfIntervalCount
          MAX-ACCESS  read-only
          STATUS  current
          DESCRIPTION
          "Far End Block Errors, as reported in the first bit
           of frames 13 and 15, on multiframe E1 lines with CRC4,
           in one of the previous 96, individual, 15 minute intervals."
          ::= { dsx1XIntervalEntry 7 }

dsx1IntervalStatus OBJECT-TYPE
	SYNTAX OCTET STRING  (SIZE (4))
           MAX-ACCESS  read-only
           STATUS  current
           DESCRIPTION
            "The statuses of the current interval:
              0 - Valid.
              1 - redundantLinkSwitch - the link has been switched
                  by a redundancy mechanism.
              2 - discontinuity - module was partialy out.
              4 - notValid - module is out."
           ::= { dsx1XIntervalEntry 8 }

dsx1IntervalBPV OBJECT-TYPE
         SYNTAX PerfIntervalCount
         MAX-ACCESS  read-only
         STATUS  current
         DESCRIPTION
         "The counter associated with the number of BPV (Bi-Polar Violations)
          encountered by a DS1	interface in one of the previous 96,
          individual 15 minute, intervals."
         ::= { dsx1XIntervalEntry 9 }

dsx1IntervalLOCRCMF OBJECT-TYPE
         SYNTAX PerfIntervalCount
         MAX-ACCESS  read-only
         STATUS  current
         DESCRIPTION
         "Loss of CRC4 Multi-Frame sequence in E1."
         ::= { dsx1XIntervalEntry 10 }

dsx1IntervalLOFC OBJECT-TYPE
          SYNTAX PerfIntervalCount
          MAX-ACCESS  read-only
          STATUS  current
          DESCRIPTION
          "Counts the number of loss of frame events measured
          in one of the previous 96, individual 15 minute, intervals."
          ::= { dsx1XIntervalEntry 11 }

dsx1IntervalLSES OBJECT-TYPE
    SYNTAX      PerfIntervalCount
    MAX-ACCESS  read-only
    STATUS      deprecated
    DESCRIPTION
            "Counts the number of LSES (Line Severely Errored Seconds)
            encountered in the 15 minute interval."
    ::= { dsx1XIntervalEntry 13 }

dsx1IntervalFC OBJECT-TYPE
    SYNTAX      PerfIntervalCount
    MAX-ACCESS  read-only
    STATUS      deprecated
    DESCRIPTION
            "Counts the number of FC (Path failure events) encountered
            in the 15 minute interval."
    ::= { dsx1XIntervalEntry 14 }


--   Extension to the dsx1 Total table

dsx1XTotalTable  OBJECT-TYPE
       SYNTAX      SEQUENCE OF Dsx1XTotalEntry
       MAX-ACCESS  not-accessible
       STATUS      current
       DESCRIPTION
       "A list of Total statistics entries.  This table
        contains additional objects for the Total table."
       ::= { prtDs1PerfHistory 4 }

dsx1XTotalEntry OBJECT-TYPE
       SYNTAX  Dsx1XTotalEntry
       MAX-ACCESS  not-accessible
       STATUS      current
       DESCRIPTION
       "An entry containing additional statistical counters
        applicable to a particular total table."
 --     AUGMENTS    { dsx1TotalEntry }
        INDEX   { dsx1TotalIndex }
       ::= { dsx1XTotalTable 1 }

Dsx1XTotalEntry ::= SEQUENCE {
    dsx1TotalLOS            PerfTotalCount,
    dsx1TotalLOF            PerfTotalCount,
    dsx1TotalAIS            PerfTotalCount,
    dsx1TotalRAI            PerfTotalCount,
    	  dsx1TotalBPV			PerfTotalCount,
      dsx1TotalLOFC			PerfTotalCount,
    dsx1TotalLSES           PerfTotalCount,
    dsx1TotalFC             PerfTotalCount
 }

dsx1TotalLOS OBJECT-TYPE
    SYNTAX      PerfTotalCount
    MAX-ACCESS  read-only
    STATUS      current
    DESCRIPTION
            "The counter associated with the number of LOS (Loss of
            Signal) seconds encountered by a DS1 interface in the
            previous 24 hour interval. Invalid 15 minute intervals count
            as 0."
    ::= { dsx1XTotalEntry 1 }

dsx1TotalLOF OBJECT-TYPE
    SYNTAX      PerfTotalCount
    MAX-ACCESS  read-only
    STATUS      current
    DESCRIPTION
            "The counter associated with the number of LOF (Loss of
            Frame) seconds encountered by a DS1 interface in the
            previous 24 hour interval. Invalid 15 minute intervals count
            as 0."
    ::= { dsx1XTotalEntry 2 }

dsx1TotalAIS OBJECT-TYPE
    SYNTAX      PerfTotalCount
    MAX-ACCESS  read-only
    STATUS      current
    DESCRIPTION
            "The counter associated with the number of AIS (Alarm
            Indication Signal) seconds encountered by a DS1 interface
            in the previous 24 hour interval. Invalid 15 minute
            intervals count as 0."
    ::= { dsx1XTotalEntry 4 }

dsx1TotalRAI OBJECT-TYPE
    SYNTAX      PerfTotalCount
    MAX-ACCESS  read-only
    STATUS      current
    DESCRIPTION
            "The counter associated with the number of RAIS (Remote
            Alarm Indication) seconds encountered by a DS1 interface
            in the previous 24 hour interval. Invalid 15 minute
            intervals count as 0."
    ::= { dsx1XTotalEntry 5 }

dsx1TotalBPV OBJECT-TYPE
      SYNTAX PerfTotalCount
      MAX-ACCESS  read-only
      STATUS  current
      DESCRIPTION
      "The counter associated with the number of BPV (Bi-Polar Violations)
       encountered by a DS1	interface in the previous 24 hour interval.
       Invalid 15 minute intervals count as 0."
      ::= { dsx1XTotalEntry 9 }

dsx1TotalLOFC OBJECT-TYPE
      SYNTAX PerfTotalCount
      MAX-ACCESS  read-only
      STATUS  current
      DESCRIPTION
      "The counter associated with the number loss of frames
       encountered by a DS1	interface in the previous 24 hour interval.
       Invalid 15 minute intervals count as 0."
      ::= { dsx1XTotalEntry 11 }

dsx1TotalLSES OBJECT-TYPE
    SYNTAX      PerfTotalCount
    MAX-ACCESS  read-only
    STATUS      current
    DESCRIPTION
            "Counts the number of LSES (Line Severely Errored Seconds)
            encountered by a DS1 interface in the previous 24 hour
            interval. Invalid 15 minute intervals count as 0."
    ::= { dsx1XTotalEntry 13 }

dsx1TotalFC OBJECT-TYPE
    SYNTAX      PerfTotalCount
    MAX-ACCESS  read-only
    STATUS      current
    DESCRIPTION
            "Counts the number of FC (Path failure events) encountered
            by a DS1 interface in the previous 24 hour interval. Invalid
            15 minute intervals count as 0."
    ::= { dsx1XTotalEntry 14 }

-- DS1 Data Stream Statistics Table

dsx1DataStreamStatTable OBJECT-TYPE
      SYNTAX  SEQUENCE OF Dsx1DataStreamStatEntry
      MAX-ACCESS   not-accessible
      STATUS  current
      DESCRIPTION
      "The DS1 Data Stream Statistics table."
      ::= { prtDs1PerfHistory 5 }

dsx1DataStreamStatEntry OBJECT-TYPE
      SYNTAX  Dsx1DataStreamStatEntry
      MAX-ACCESS  not-accessible
      STATUS  current
      DESCRIPTION
      "An entry in the DS1 Data Stream Statistics table."
      INDEX   { dsx1DataStreamStatIfIndex, dsx1DataStreamStatIndex }
      ::= { dsx1DataStreamStatTable 1 }

Dsx1DataStreamStatEntry ::=
      SEQUENCE {
      dsx1DataStreamStatIfIndex			Integer32,
      dsx1DataStreamStatIndex			Integer32,
	  dsx1DataStreamStatValid			TruthValue,
      dsx1DataStreamStatInFrames		Counter32,
      dsx1DataStreamStatInBytes			Counter32,
      dsx1DataStreamStatInDiscards		Counter32,
      dsx1DataStreamStatInErrors		Counter32,
      dsx1DataStreamStatOutFrames		Counter32,
      dsx1DataStreamStatOutBytes		Counter32,
      dsx1DataStreamStatOutDiscards		Counter32,
	  dsx1DataStreamStatOutErrors		Counter32
      }

dsx1DataStreamStatIfIndex OBJECT-TYPE
    SYNTAX      Integer32
    MAX-ACCESS  not-accessible
    STATUS      current
    DESCRIPTION
    "The index of the DS1 interface.
     It may be ifIndex."
    ::= { dsx1DataStreamStatEntry 1 }

dsx1DataStreamStatIndex OBJECT-TYPE
    SYNTAX      Integer32
    MAX-ACCESS  not-accessible
    STATUS      current
    DESCRIPTION
    "The DS1 Data Stream Index.
     For Vmux - the following indices are used:
       1  for Transparent
	 2-3  for SS71-SS72 (respectively)
	 4-7  for Data1-Data4 (respectively)
	   8  for HDLC Ph2 Compatible
	9-16  for Sub-CH1-1...Sub-CH1-8 (respectively)."
    ::= { dsx1DataStreamStatEntry 2 }

dsx1DataStreamStatValid OBJECT-TYPE
    SYNTAX  TruthValue
    MAX-ACCESS  read-only
    STATUS      current
    DESCRIPTION
    "Indicates whether this Data Stream is valid or not.
     When invalid - all counters are irrelevant."
    ::= { dsx1DataStreamStatEntry 3 }

dsx1DataStreamStatInFrames OBJECT-TYPE
      SYNTAX  Counter32
      MAX-ACCESS  read-only
      STATUS  current
      DESCRIPTION
	  "The counter associated with the number of received frames,
	   encountered by the DS1 Data Stream."
      ::= { dsx1DataStreamStatEntry 4 }

dsx1DataStreamStatInBytes OBJECT-TYPE
      SYNTAX  Counter32
      MAX-ACCESS  read-only
      STATUS  current
      DESCRIPTION
	  "The counter associated with the number of received bytes,
	   encountered by the DS1 Data Stream."
      ::= { dsx1DataStreamStatEntry 5 }

dsx1DataStreamStatInDiscards OBJECT-TYPE
      SYNTAX  Counter32
      MAX-ACCESS  read-only
      STATUS  current
      DESCRIPTION
	  "The counter associated with the number of Discarded incoming frames,
	   encountered by the DS1 Data Stream."
      ::= { dsx1DataStreamStatEntry 6 }

dsx1DataStreamStatInErrors OBJECT-TYPE
      SYNTAX  Counter32
      MAX-ACCESS  read-only
      STATUS  current
      DESCRIPTION
	  "The counter associated with the number of received Errored frames,
	   encountered by the DS1 Data Stream."
      ::= { dsx1DataStreamStatEntry 7 }

dsx1DataStreamStatOutFrames OBJECT-TYPE
      SYNTAX  Counter32
      MAX-ACCESS  read-only
      STATUS  current
      DESCRIPTION
	  "The counter associated with the number of transmitted frames,
	   encountered by the DS1 Data Stream."
      ::= { dsx1DataStreamStatEntry 8 }

dsx1DataStreamStatOutBytes OBJECT-TYPE
      SYNTAX  Counter32
      MAX-ACCESS  read-only
      STATUS  current
      DESCRIPTION
	  "The counter associated with the number of transmitted bytes,
	   encountered by the DS1 Data Stream."
      ::= { dsx1DataStreamStatEntry 9 }

dsx1DataStreamStatOutDiscards OBJECT-TYPE
      SYNTAX  Counter32
      MAX-ACCESS  read-only
      STATUS  current
      DESCRIPTION
	  "The counter associated with the number of Discarded outgoing frames,
	   encountered by the DS1 Data Stream."
      ::= { dsx1DataStreamStatEntry 10 }

dsx1DataStreamStatOutErrors OBJECT-TYPE
      SYNTAX  Counter32
      MAX-ACCESS  read-only
      STATUS  current
      DESCRIPTION
	  "The counter associated with the number of errored transmitted frames,
	   encountered by the DS1 Data Stream."
      ::= { dsx1DataStreamStatEntry 11 }


--   Extension to the DS1 Configuration Table

dsx1XConfigTable  OBJECT-TYPE
       SYNTAX      SEQUENCE OF Dsx1XConfigEntry
       MAX-ACCESS  not-accessible
       STATUS      current
       DESCRIPTION
               " An extension to the DS1 Configuration table."
       ::= { ds1Interface 2 }

dsx1XConfigEntry OBJECT-TYPE
       SYNTAX  Dsx1XConfigEntry
       MAX-ACCESS  not-accessible
       STATUS      current
       DESCRIPTION
           "An entry containing additional configuration
           parameters."
 --      AUGMENTS    { dsx1ConfigTable }
         INDEX   { dsx1LineIndex }
       ::= { dsx1XConfigTable 1 }

Dsx1XConfigEntry ::= SEQUENCE {
    dsx1IdleCode                Integer32,
         dsx1LineMode		    	INTEGER,
         dsx1dBTxGain     			INTEGER,
    dsx1RxSensitivity           INTEGER,
         dsx1RestoreTime			INTEGER,
         dsx1TcFirstSignal			Integer32,
         dsx1TcSignal   			Integer32,
    dsx1TcPattern               Integer32,
         dsx1Scramble     			INTEGER,
         dsx1LineAdaptiveTimingMode INTEGER,
    dsx1TxClockSource           INTEGER,
    dsx1AisEnable               INTEGER,
		 dsx1TsEchoCancel			OCTET STRING,
		 dsx1EchoCancelerModule     INTEGER,
         dsx1PortFunction 		    INTEGER,
		 dsx1PortMultiplier			INTEGER,
		 dsx1LeasedLine				INTEGER,
    dsx1CsuLoop                 INTEGER,
		 dsx1ClockSource			Integer32,
		 dsx1OosSignal				INTEGER,
    dsx1BundleNextIndex         Integer32,
    		 dsx1CRC6CalcMode           INTEGER,
		 dsx1SendUponFail           INTEGER,
    dsx1InbandLoopSignal        INTEGER,
    dsx1InbandLoopUpCode        OCTET STRING,
    dsx1InbandLoopUpLength      Unsigned32,
    dsx1InbandLoopDownCode      OCTET STRING,
    dsx1InbandLoopDownLength    Unsigned32,
    dsx1TxClockInstance         Unsigned32,
    dsx1TxPortQuality           INTEGER
 }

dsx1IdleCode OBJECT-TYPE
         SYNTAX  Integer32
         MAX-ACCESS   read-write
         STATUS  current
         DESCRIPTION
         "Byte pattern of the data received/transmitted in the
          E1T1 framer idle timeslots.
          Valid range: (0 - FF HEX)."
         ::= { dsx1XConfigEntry 1 }

dsx1LineMode OBJECT-TYPE
          SYNTAX  INTEGER {
          csu(1),
          dsu(2)
          }
          MAX-ACCESS  read-write
          STATUS  current
          DESCRIPTION
                  "T1 device operation mode.
                   Valid for T1 only."
          ::= { dsx1XConfigEntry 2 }

dsx1dBTxGain OBJECT-TYPE
         SYNTAX  INTEGER {
         notApplicable (1),
         neg75dB       (2),
         neg15dB       (3),
         neg225dB      (4),
		 zerodB	       (5)
         }
         MAX-ACCESS  read-write
         STATUS  current
         DESCRIPTION
                 "Transmit line Gain for T1 CSU line mode."
         ::= { dsx1XConfigEntry 3 }

dsx1RxSensitivity OBJECT-TYPE
        SYNTAX  INTEGER {
        notApplicable  (1),
        longHaul       (2),
        shortHaul      (3),
        monitor        (4)
        }
        MAX-ACCESS  read-write
        STATUS  current
        DESCRIPTION
        "Low Sensitivity is considered Short Haul while High Sensitivity
         is considered Long Haul. The actual values depend on the LIU.
         Examples:
         - E1: -12dB is considered Short Haul ; -43dB is considered Long Haul
         - T1: -12dB is considered Short Haul ; -36dB is considered Long Haul.
         - monitor value applicable for M8E1/T1 ports"
        ::= { dsx1XConfigEntry 4 }

dsx1RestoreTime OBJECT-TYPE
        SYNTAX  INTEGER {
        other(1),
        sec1(2),
        sec10(3),
		immediate(4)
        }
        MAX-ACCESS  read-write
        STATUS  current
        DESCRIPTION
        "Used to change the sync. algorithms to reduce the time
         required for the port to return to normal operation after
         a RED alarm.
         'sec1' = Fast,
         'sec10' = TR-6211,
		 'immediate' = CCITT"
        ::= { dsx1XConfigEntry 5 }

dsx1TcFirstSignal OBJECT-TYPE
        SYNTAX  Integer32
        MAX-ACCESS  read-write
        STATUS  current
        DESCRIPTION
        "Trunk conditioning signal - value to be sent as a signal
         during the first 2.5 seconds after alarm detection.
		 Range is 0x0..0xF. 0xFF is a NULL value.
		 This variable is used also for Space Signaling Code (in this case
		 0xFF is not NULL)."
        ::= { dsx1XConfigEntry 6 }

dsx1TcSignal OBJECT-TYPE
        SYNTAX  Integer32
        MAX-ACCESS  read-write
        STATUS  current
        DESCRIPTION
        "Trunk conditioning signal value after alarm detection.
         Range is 0x1..0xF for E1, and 0x0..0xF for T1.
         This variable is used also for Space Signaling Code (E1 and T1)."
        ::= { dsx1XConfigEntry 7 }

dsx1TcPattern OBJECT-TYPE
       SYNTAX  Integer32
       MAX-ACCESS  read-write
       STATUS  current
       DESCRIPTION
       "Trunk conditioning data pattern to be sent upon a DS0 fail.
        Range is 0x0..0xFF.
        This variable used also for Out of Service Code."
       ::= { dsx1XConfigEntry 8 }

dsx1Scramble  OBJECT-TYPE
       SYNTAX  INTEGER {
       notApplicable (1),
       notActive     (2),
       active        (3)
       }
       MAX-ACCESS  read-write
       STATUS  current
       DESCRIPTION
       "Scrambling is an operation that randomizes the bits
        of the payload of the ATM cell by a polynom.
        This operation helps with the error detection mechanism
        of the HEC. Not applicable for E1.
        active - will scramble/descramble the payload ATM cell
        notActive - will not scramble/descramble. "
       ::= { dsx1XConfigEntry 9 }

dsx1LineAdaptiveTimingMode OBJECT-TYPE
       SYNTAX  INTEGER {
       off(1),
       on(2)
       }
       MAX-ACCESS  read-write
       STATUS  current
       DESCRIPTION
       "Enables end to end clock synchronization.
        Default value - off."
       ::= { dsx1XConfigEntry 10 }

dsx1TxClockSource OBJECT-TYPE
       SYNTAX  INTEGER {
       loopTiming(1),
       localTiming(2),
       throughTiming(3),
       adaptive(4),
       system(5)
       }
       MAX-ACCESS  read-write
       STATUS  current
       DESCRIPTION
       "The source of Transmit Clock.
        'loopTiming' indicates that the recovered receive clock
         is used as the transmit clock.

        'localTiming' indicates that a local clock
         source is used or when an external clock is
         attached to the box containing the interface.

        'throughTiming' indicates that recovered receive clock
         from another interface is used as the transmit clock.

        'adaptive' indicates that the clock is recovered according
         to the received data flow rate.

        'system' indicates that the system clock
         is used as the transmit clock."
       ::= { dsx1XConfigEntry 11 }

dsx1AisEnable  OBJECT-TYPE
       SYNTAX  INTEGER {
       notApplicable(1),
       disable(2),
       enable(3)
       }
       MAX-ACCESS  read-write
       STATUS  current
       DESCRIPTION
       "Enable/ disable AIS transmit when Ethernet cable (for TDMoIP) is out (disconnected)."
       ::= { dsx1XConfigEntry 12 }

dsx1TsEchoCancel OBJECT-TYPE
       SYNTAX OCTET STRING  (SIZE (4))
       MAX-ACCESS  read-write
       STATUS  current
       DESCRIPTION
       "This parameter defines for each TS whether Echo-Cancellation is on.
	  	Each bit represents one TS as follow:
		First octet bit'0' = TS#1, bit'7' = TS#8, .. 2nd octet bit'0' = TS#9,..,
		4th octet bit'7' = TS#32.
		Octets and bits order is from left to right:
		[31,30,..24]      [23..16]    [15..8]      [7..0]
		MSB       LSB 	 MSB	LSB	 MSB   LSB	  MSB	LSB

	  	For each bit values are:
         0 - Echo-Cancellation off.
         1 - Echo-Cancellation on."
       ::= { dsx1XConfigEntry 13 }

dsx1EchoCancelerModule OBJECT-TYPE
       SYNTAX  INTEGER {
       notExist(2),
       exist(3)
       }
       MAX-ACCESS  read-only
       STATUS  current
       DESCRIPTION
       "This parameter indicates whether echo-cancellation module
        exists for this line."
       ::= { dsx1XConfigEntry 14 }

dsx1PortFunction OBJECT-TYPE
       SYNTAX  INTEGER {
	    notApplicable	(1),
	  	uni				(2),
	  	ces				(3),
	  	ima				(4),
		cesPsn			(5),
		abis			(6)
	    }
       MAX-ACCESS  read-write
       STATUS  current
       DESCRIPTION
       "This object determines the ATM Mode over the
        physical port.
        uni  	- The port will function as an ATM UNI.
        ces  	- The port will function as a CES.
        ima  	- The port will function as an IMA-ATM.
        cesPsn  - The port will function as a CES-PSN.
		abis 	- The port will function as an Abis."
       ::= { dsx1XConfigEntry 15 }

dsx1PortMultiplier OBJECT-TYPE
       SYNTAX  INTEGER {
	    notApplicable (1),
	  	r56 (2),
	  	r64 (3)
	    }
       MAX-ACCESS  read-write
       STATUS  current
       DESCRIPTION
       "This object determines the data rate of each TS
        (Kbps units).
        This parameter is applicable for T1 only."
       ::= { dsx1XConfigEntry 16 }

dsx1LeasedLine OBJECT-TYPE
       SYNTAX  INTEGER {
	    notApplicable (1),
	  	disable (2),
	  	enable (3)
	    }
       MAX-ACCESS  read-write
       STATUS  current
       DESCRIPTION
       "This parameter defines whether Line mode is regular (non Leased Line mode)
       or transparent (Leased Line mode)."
       ::= { dsx1XConfigEntry 17 }

dsx1CsuLoop OBJECT-TYPE
       SYNTAX  INTEGER {
       notApplicable    (1),
       local            (2),
       transparent      (3),
       remote           (4)     }
       MAX-ACCESS  read-write
       STATUS  current
       DESCRIPTION
       "This parameter defines where the CSU loop will be done:
        local - locally (by IPmux) towards the TDM device
        transparent - transferred to Remote Device that will send it to its
                      connected TDM device.
        remote - Remote Device will close the loop towards the Local Device."
       ::= { dsx1XConfigEntry 18 }

dsx1ClockSource OBJECT-TYPE
    SYNTAX  Integer32
    MAX-ACCESS  read-write
    STATUS  current
    DESCRIPTION
    "This entry specifies the source from which the clock will be taken.
	 Refer to device specification for source Index"
      ::= { dsx1XConfigEntry 19 }

dsx1OosSignal OBJECT-TYPE
       SYNTAX  INTEGER {
	    notApplicable	(1),
        space    		(2),
	    mark	 		(3),
	    spaceMark		(4),
	    markSpace		(5)
	   					 }
       MAX-ACCESS  read-write
       STATUS  current
       DESCRIPTION
       " This parameter defines the value to be sent as a signal
         after alarm detection:
         'Space' = both A and B signaling bits are forced
                      to '0' during out-of-service periods.
		 'Mark' = both A and B signaling bits are forced
                      to '1' during out-of-service periods.
         'spaceMark' = A and B bits are forced to '0' for
                      2.5 seconds; then they are switched to '1'
                      until out-of-service condition disappears.
         'markSpace' = A and B bits are forced to '1' for
                      2.5 seconds; then they are switched to '0'
                      until out-of-service condition disappears.
       - '0'= 0 for T1, 1 for E1, or user defined value for Space
       - '1'= 1 for T1, 0 for E1, or user defined value for Mark."
       ::= { dsx1XConfigEntry 20 }

dsx1BundleNextIndex OBJECT-TYPE
       SYNTAX  Integer32
       MAX-ACCESS  read-only
       STATUS  current
       DESCRIPTION
       "This parameter indicates the Next free Bundle Index for this DS1 port."
       ::= { dsx1XConfigEntry 21 }

dsx1CRC6CalcMode OBJECT-TYPE
       SYNTAX  INTEGER {
	    jtG704 (1),
	  	ituG704(2)
	    }
       MAX-ACCESS  read-write
       STATUS  current
       DESCRIPTION
       "This object determines the CRC6 Calculation mode.
        jtG704 =JT-G704  = the Japanese standard
        ituG704=ITU-G704 = the International standard
        This parameter is applicable for J1 only."
       ::= { dsx1XConfigEntry 22 }

dsx1SendUponFail   OBJECT-TYPE
       SYNTAX      INTEGER
	   {
	       oosCode (2),
		   ais (3)
	   }
       MAX-ACCESS  read-write
       STATUS  current
       DESCRIPTION
       "This object determines which notification will be sent to the other side
       upon fail of another interface.
       In Ipmux14 the notification is sent upon failure of the Ethernet link."
       ::= { dsx1XConfigEntry 23 }

dsx1InbandLoopSignal OBJECT-TYPE
       SYNTAX  INTEGER {
       notApplicable  (1),
       csu            (2),
       fdlLine        (3),
       fdlNetwork     (4),
       niuFac1        (5),
       niuFac2        (6),
       program        (99)
       }
       MAX-ACCESS  read-write
       STATUS  current
       DESCRIPTION
       "This parameter defines the signal pattern for inband loopback
        activation and deactivation:

        csu
        Applicable only for SF (D4) and ESF line types
        Defined in AT&T TR54016 and ANSI T1.403.
        Loop-up pattern - 00001 detected for at least 5 seconds
        Loop-down pattern - 001 detected for at least 5 seconds

        fdlLine
        Applicable only for ESF line type.
        Defined in ANSI T1.403.
        Loop-up pattern - 00001110 11111111
        Loop-down pattern - 00111000 11111111 or 00100100 11111111 (universal deactivate)

        fdlNetwork
        Applicable only for ESF line type.
        Defined in ANSI T1.403.
        Loop-up pattern - 00010010 11111111
        Loop-down pattern - 00100100 11111111

        niuFac1
        Applicable for framed and unframed line types.
        Define in Telcordia (Bellcore) TR-TSY-0312.
        Loop-up pattern - 0011
        Loop-down pattern - 0111

        niuFac2
        Applicable for framed and unframed line types.
        Define in Telcordia (Bellcore) TR-TSY-0312.
        Loop-up pattern - 00011
        Loop-down pattern - 00111

        program
        User configurable loop-up and loop-down patterns.
        The patterns and their length are set in:
        dsx1InbandLoopUpCode
        dsx1InbandLoopUpLength
        dsx1InbandLoopDownCode
        dsx1InbandLoopDownLength

        The specified pattern is applicable only when the value of
        dsx1CsuLoop is local(2) or remote(4).

        This parameter is applicable only for T1."
       ::= { dsx1XConfigEntry 24 }

dsx1InbandLoopUpCode OBJECT-TYPE
       SYNTAX  OCTET STRING
       MAX-ACCESS  read-write
       STATUS  current
       DESCRIPTION
       "This parameter specifies the inband signal pattern that shall
        cause activation of a loopback.

        The specified pattern is applicable only when the value of
        dsx1CsuLoop is local(2) or remote(4), and the value of
        dsx1InbandLoopSignal is program(99)."
       ::= { dsx1XConfigEntry 25 }

dsx1InbandLoopUpLength OBJECT-TYPE
       SYNTAX  Unsigned32 (3..8)
       UNITS  "bits"
       MAX-ACCESS  read-write
       STATUS  current
       DESCRIPTION
       "This parameter specifies the length, in bits, of the inband
        signal pattern that shall cause activation of a loopback.

        The specified pattern is applicable only when the value of
        dsx1CsuLoop is local(2) or remote(4), and the value of
        dsx1InbandLoopSignal is program(99)."
       ::= { dsx1XConfigEntry 26 }

dsx1InbandLoopDownCode OBJECT-TYPE
       SYNTAX  OCTET STRING
       MAX-ACCESS  read-write
       STATUS  current
       DESCRIPTION
       "This parameter specifies the inband signal pattern that shall
        cause de-activation of a loopback.

        The specified pattern is applicable only when the value of
        dsx1CsuLoop is local(2) or remote(4), and the value of
        dsx1InbandLoopSignal is program(99)."
       ::= { dsx1XConfigEntry 27 }

dsx1InbandLoopDownLength OBJECT-TYPE
       SYNTAX  Unsigned32 (3..8)
       UNITS  "bits"
       MAX-ACCESS  read-write
       STATUS  current
       DESCRIPTION
       "This parameter specifies the length, in bits, of the inband
        signal pattern that shall cause de-activation of a loopback.

        The specified pattern is applicable only when the value of
        dsx1CsuLoop is local(2) or remote(4), and the value of
        dsx1InbandLoopSignal is program(99)."
       ::= { dsx1XConfigEntry 28 }

dsx1TxClockInstance OBJECT-TYPE
       SYNTAX  Unsigned32
       MAX-ACCESS  read-write
       STATUS  current
       DESCRIPTION
       "When dsx1TransmitClockSource is set to throughTiming(3) or
        adaptive(4), this parameter specifies the instance of the
        clock domain or recovered clock, respectively, that shall
        be used for transmission."
       ::= { dsx1XConfigEntry 29 }

dsx1TxPortQuality       OBJECT-TYPE
      SYNTAX  INTEGER
      {
        notApplicable       (1),
        stratum1            (2),
        stratum2            (3),
        stratum3            (4),
        stratum3e           (5),
        stratum4            (6)
      }
      MAX-ACCESS  read-write
      STATUS  current
      DESCRIPTION
      "This object indicates the port clock quality."
      ::= { dsx1XConfigEntry 30 }



--***************************
-- DS1 Statistics Thresholds
--***************************

dsx1XStatThresholdTable  OBJECT-TYPE
    SYNTAX      SEQUENCE OF Dsx1XStatThresholdEntry
    MAX-ACCESS  not-accessible
    STATUS      current
    DESCRIPTION
            "An extension to the DS1 Configuration table that defines
            DS1 statistics thresholds.
            'Line' means a physical transport of digital information at
                nominal rate of 2.048Mbps or 1.544Mbps.
            'Path' means a framed digital signal at nominal rate of
                2.048Mbps or 1.544Mbps independent of the specific
                transmission equipment."
    ::= { ds1Interface 3 }

dsx1XStatThresholdEntry OBJECT-TYPE
    SYNTAX      Dsx1XStatThresholdEntry
    MAX-ACCESS  not-accessible
    STATUS      current
    DESCRIPTION
           "An entry containing statistics thresholds for DS1 port."
    INDEX       { dsx1LineIndex }
    ::= { dsx1XStatThresholdTable 1 }

Dsx1XStatThresholdEntry ::= SEQUENCE {
    dsx1LineIntervalLesThreshold    Unsigned32,
    dsx1PathIntervalCvThreshold     Unsigned32,
    dsx1PathIntervalEsThreshold     Unsigned32,
    dsx1PathIntervalSesThreshold    Unsigned32,
    dsx1PathIntervalSefsThreshold   Unsigned32,
    dsx1PathIntervalCssThreshold    Unsigned32,
    dsx1PathIntervalUasThreshold    Unsigned32
 }

dsx1LineIntervalLesThreshold OBJECT-TYPE
    SYNTAX      Unsigned32  (0..900)
    MAX-ACCESS  read-write
    STATUS      current
    DESCRIPTION
            "This object configures the threshold for the number of
            Error Seconds (ES) within any given 15-minute performance
            Line data collection interval. If the value of Error Seconds
            in a particular 15-minute collection interval exceeded
            this value, a related Trap/Notification MAY be generated
            at the end of the interval. At most, one notification will
            be sent per interval per port."
       ::= { dsx1XStatThresholdEntry 1 }

dsx1PathIntervalCvThreshold OBJECT-TYPE
    SYNTAX      Unsigned32  (0..16383)
    MAX-ACCESS  read-write
    STATUS      current
    DESCRIPTION
            "This object configures the threshold for the number of
            Code Violations (CV) within any given 15-minute performance
            Path data collection interval. If the value of Error Seconds
            in a particular 15-minute collection interval exceeded
            this value, a related Trap/Notification MAY be generated
            at the end of the interval. At most, one notification will
            be sent per interval per port."
       ::= { dsx1XStatThresholdEntry 2 }

dsx1PathIntervalEsThreshold OBJECT-TYPE
    SYNTAX      Unsigned32  (0..900)
    MAX-ACCESS  read-write
    STATUS      current
    DESCRIPTION
            "This object configures the threshold for the number of
            Error Seconds (ES) within any given 15-minute performance
            Path data collection interval. If the value of Error Seconds
            in a particular 15-minute collection interval exceeded
            this value, a related Trap/Notification MAY be generated
            at the end of the interval. At most, one notification will
            be sent per interval per port."
       ::= { dsx1XStatThresholdEntry 3 }

dsx1PathIntervalSesThreshold OBJECT-TYPE
    SYNTAX      Unsigned32  (0..900)
    MAX-ACCESS  read-write
    STATUS      current
    DESCRIPTION
            "This object configures the threshold for the number of
            Severe Error Seconds (SES) within any given 15-minute
            performance Path data collection interval. If the value of
            Error Seconds in a particular 15-minute collection interval
            exceeded this value, a related Trap/Notification MAY be
            generated at the end of the interval. At most, one
            notification will be sent per interval per port."
       ::= { dsx1XStatThresholdEntry 4 }

dsx1PathIntervalSefsThreshold OBJECT-TYPE
    SYNTAX      Unsigned32  (0..900)
    MAX-ACCESS  read-write
    STATUS      current
    DESCRIPTION
            "This object configures the threshold for the number of
            Severely Errored Framing Seconds (SEFS) within any given
            15-minute performance Path data collection interval. If the
            value of Error Seconds in a particular 15-minute collection
            interval exceeded this value, a related Trap/Notification
            MAY be generated at the end of the interval. At most, one
            notification will be sent per interval per port."
       ::= { dsx1XStatThresholdEntry 5 }

dsx1PathIntervalCssThreshold OBJECT-TYPE
    SYNTAX      Unsigned32  (0..900)
    MAX-ACCESS  read-write
    STATUS      current
    DESCRIPTION
            "This object configures the threshold for the number of
            Controlled Slip Seconds (CSS) within any given 15-minute
            performance Path data collection interval. If the value of
            Error Seconds in a particular 15-minute collection interval
            exceeded this value, a related Trap/Notification MAY be
            generated at the end of the interval. At most, one
            notification will be sent per interval per port."
       ::= { dsx1XStatThresholdEntry 6 }

dsx1PathIntervalUasThreshold OBJECT-TYPE
    SYNTAX      Unsigned32  (0..900)
    MAX-ACCESS  read-write
    STATUS      current
    DESCRIPTION
            "This object configures the threshold for the number of
            Unavailable Seconds (UAS) within any given 15-minute
            performance Path data collection interval. If the value of
            Error Seconds in a particular 15-minute collection interval
            exceeded this value, a related Trap/Notification MAY be
            generated at the end of the interval. At most, one
            notification will be sent per interval per port."
       ::= { dsx1XStatThresholdEntry 7 }

-- ALARM INDICATION SIGNAL (AIS)

-- USER E1 LOCAL MULTIFRAME ALARM
ds1LocalMultiframeAlarmTrap  NOTIFICATION-TYPE
      OBJECTS  {alarmSeverity, ifAlias}
      STATUS  current
      DESCRIPTION
	    "This trap indicates near end (Local) Loss of
      Multiframe Alignment, of the user E1 interface."
      ::= { prtDS1Events  1 }

-- USER E1 REMOTE MULTIFRAME ALARM
ds1RemoteMultiframeAlarmTrap	  NOTIFICATION-TYPE
      OBJECTS  {alarmSeverity, ifAlias}
      STATUS  current
      DESCRIPTION
	    "This trap indicates that the far end (remote) unit,
      connected to the user E1 interface, reports
      Loss of Multiframe Alignment."
      ::= { prtDS1Events  2 }

-- USER DS1 LINK FRAME SLIP
ds1LinkFrameSlipTrap	  NOTIFICATION-TYPE
      OBJECTS  {alarmSeverity, ifAlias}
      STATUS  current
      DESCRIPTION
	  "This trap indicates that a Frame Slip occurred at the user
      DS1 interface. This usually indicates timing problems
      (incorrect selection of timing reference),
       on the user DS1 link."
      ::= { prtDS1Events  3 }

-- USER DS1 BPV ERROR
ds1BpvErrorTrap	NOTIFICATION-TYPE
      OBJECTS  {alarmSeverity, ifAlias}
      STATUS  current
      DESCRIPTION
	  "This trap indicates a Bipolar Violation (BPV)
      error has been detected at the user DS1 interface."
      ::= { prtDS1Events  4 }

-- USER DS1 EXCESSIVE BPV
ds1ExcessiveBpvTrap	NOTIFICATION-TYPE
      OBJECTS  {alarmSeverity, alarmState, ifAlias}
      STATUS  current
      DESCRIPTION
	  "This trap indicates excessive number of
      Bipolar Violation errors  (BPV)
      detected by the user DS1 interface"
      ::= { prtDS1Events  5 }

-- USER DS1 CRC-4 ERROR
ds1Crc4ErrorTrap	 NOTIFICATION-TYPE
      OBJECTS  {alarmSeverity, ifAlias}
      STATUS  current
      DESCRIPTION
	    "This trap indicates that a frame with CRC-4 error has been
      detected at the user DS1 interface."
      ::= { prtDS1Events  6 }

-- USER DS1 EXCESSIVE ERROR RATIO
ds1ExcessiveErrorRatioTrap  NOTIFICATION-TYPE
      OBJECTS  {alarmSeverity, alarmState, ifAlias}
      STATUS  current
      DESCRIPTION
	    "This trap indicates that the error rate, detected
      at the user DS1 interface, on the frame synchronization bits
      is high, as defined by ITU-T Rec. G.732."
     ::= { prtDS1Events  7 }

-- USER DS1 REMOTE SYNC LOSS
ds1RemoteSyncLossTrap  NOTIFICATION-TYPE
      OBJECTS  {alarmSeverity, alarmState, ifAlias}
      STATUS  current
      DESCRIPTION
	  "This trap indicates that the far-end (remote)
      unit, connected to user DS1 interface,
      reports Loss of Frame Alignment (Sync Loss)."
      ::= { prtDS1Events  8 }

-- USER DS1 LOCAL SYNC LOSS
ds1LocalSyncLossTrap NOTIFICATION-TYPE
      OBJECTS  {alarmSeverity, alarmState, ifAlias}
      STATUS  current
      DESCRIPTION
	  "This trap indicates near end (Local)
      Loss of Frame Alignment failure (Sync Loss),
      of the user DS1 interface"
      ::= { prtDS1Events  9 }

-- USER DS1 AIS SYNC LOSS
ds1AisSyncLossTrap  NOTIFICATION-TYPE
      OBJECTS  {alarmSeverity, ifAlias}
      STATUS  current
      DESCRIPTION
      "This trap indicates near end (Local)
      Loss of Frame Alignment (Sync Loss), caused by the reception
      of AIS at the user DS1 interface."
      ::= { prtDS1Events  10 }

-- USER DS1 AIS
ds1AisTrap  NOTIFICATION-TYPE
      OBJECTS  {alarmSeverity, alarmState, ifAlias}
      STATUS  current
      DESCRIPTION
	  "This trap indicates AIS  being received
      at the user DS1 interface."
      ::= { prtDS1Events  11 }

-- NETWORK REMOTE LOOP
 ds1NetworkRemoteLoopTrap NOTIFICATION-TYPE
       OBJECTS  {alarmSeverity, alarmState, ifAlias}
       STATUS  current
       DESCRIPTION
       "This trap indicates that a remote loopback
       has been activated, on the local uplink interface."
       ::= { prtDS1Events  12 }

-- USER SIDE REMOTE LOOP
ds1RemoteLoopTrap  NOTIFICATION-TYPE
      OBJECTS  {alarmSeverity, alarmState, ifAlias}
      STATUS  current
      DESCRIPTION
	  "This trap indicates that a remote loopback
      has been activated, on the local user port."
      ::= { prtDS1Events  13 }

-- USER SIDE LOCAL LOOP
ds1LocalLoopTrap	NOTIFICATION-TYPE
      OBJECTS  {alarmSeverity, alarmState, ifAlias}
      STATUS  current
      DESCRIPTION
	  "This trap indicates that a local loopback
      has been activated on the user port."
      ::= { prtDS1Events  14 }

-- DS1 EXCESSIVE FRAME SLIP
ds1ExcessiveFrameSlipTrap  NOTIFICATION-TYPE
      OBJECTS  {alarmSeverity, alarmState, ifAlias}
      STATUS  current
      DESCRIPTION
	  "This trap indicates that the number of Frame Slips
      detected at the user DS1 interface, during the last minute
      exceeds threshold. For LA-110, threshold value is 10.
      This usually indicates timing problems
      (incorrect selection of timing reference) on the user DS1."
      ::= { prtDS1Events  15 }

-- USER DS1 EXCESSIVE CRC 4 ERROR
ds1ExcessiveCrc4ErrorTrap  NOTIFICATION-TYPE
      OBJECTS  {alarmSeverity, alarmState, ifAlias}
      STATUS  current
      DESCRIPTION
	  "This trap indicates that the error rate
      detected on the CRC-4 bits at the
      user DS1 interface, is high."
      ::= { prtDS1Events  16 }

-- USER E1 EXCESSIVE LOCAL MULTIFRAME ALARM
ds1ExcessiveLocalMfAlarmTrap	 NOTIFICATION-TYPE
      OBJECTS  {alarmSeverity, alarmState, ifAlias}
      STATUS  current
      DESCRIPTION
	     "This trap indicates that the number of local
      Loss of Multiframe Alignment events, detected at
      the user E1 interface during the last minute exceeds threshold.
      For LA-110, threshold value is 10."
      ::= { prtDS1Events  17 }

-- USER E1 EXCESSIVE REMOTE MULTIFRAME ALARM
ds1ExcessiveRemoteMfAlarmTrap  NOTIFICATION-TYPE
      OBJECTS  {alarmSeverity, alarmState, ifAlias}
      STATUS  current
      DESCRIPTION
	  "This trap indicates that the number of
      Loss of multiframe alignment events reported
      by the remote unit connected to the user
      E1 interface during the last minute exceeds threshold.
      For LA-110, threshold value is 10."
      ::= { prtDS1Events  18 }

-- USER DS1 EXCESSIVE REMOTE SYNC LOSS
ds1ExcessiveRemoteSyncLossTrap	  NOTIFICATION-TYPE
      OBJECTS  {alarmSeverity, alarmState, ifAlias}
      STATUS  current
      DESCRIPTION
	  "This trap indicates that the number of far end
      (remote) Loss of Synchronization alarms,
      reported by the user DS1 interface
      during the last minute, exceeds threshold.
      For LA-110, threshold value is 10."
      ::= { prtDS1Events  19 }

-- USER DS1 EXCESSIVE LOCAL SYNC LOSS
ds1ExcessiveLocalSyncLossTrap	 NOTIFICATION-TYPE
      OBJECTS  {alarmSeverity, alarmState, ifAlias}
      STATUS  current
      DESCRIPTION
	  "This trap indicates that the number of
      Loss of local Synchronization alarms
      reported by the user DS1 interface
      during the last minute, exceeds threshold.
      For LA-110, threshold value is 10."
      ::= { prtDS1Events  20 }

-- USER DS1 SIGNAL LOSS
ds1SignalLossTrap	 NOTIFICATION-TYPE
      OBJECTS  {alarmSeverity, alarmState, ifAlias}
      STATUS  current
      DESCRIPTION
	  "This trap indicates Signal Loss.
	  (possible reason -  cable disconnection. etc.)"
      ::= { prtDS1Events  21 }

e1t1Ais  NOTIFICATION-TYPE
	OBJECTS { alarmEventLogSourceName, alarmEventLogAlarmOrEventId, alarmEventLogDescription,
     alarmEventLogSeverity, alarmEventLogDateAndTime, alarmEventReason,
     ifAlias, dsx1LineStatus }
      STATUS  current
      DESCRIPTION
      "This trap indicates that an Alarm Indication Signal (AIS) was detected
       on an E1/T1 interface.
      "
      ::= { prtDS1Events 25 }

-- LOSS OF FRAME (LOF)
e1t1Lof  NOTIFICATION-TYPE
	OBJECTS { alarmEventLogSourceName, alarmEventLogAlarmOrEventId, alarmEventLogDescription,
     alarmEventLogSeverity, alarmEventLogDateAndTime, alarmEventReason,
     ifAlias, dsx1LineStatus }
      STATUS  current
      DESCRIPTION
      "This trap indicates that a Loss of Frame (LOF) was detected on an E1/T1 interface.
      "
      ::= { prtDS1Events 26 }

-- REMOTE ALARM INDICATION (RAI)
e1t1Rai  NOTIFICATION-TYPE
	OBJECTS { alarmEventLogSourceName, alarmEventLogAlarmOrEventId, alarmEventLogDescription,
     alarmEventLogSeverity, alarmEventLogDateAndTime, alarmEventReason,
     ifAlias, dsx1LineStatus }
      STATUS  current
      DESCRIPTION
      "This trap shows that a Remote Alarm Indication (RAI) was detected by an E1/T1 interface.
      "
      ::= { prtDS1Events 27 }

-- LOSS OF MULTIFRAME (LOMF)
e1t1Lomf  NOTIFICATION-TYPE
	OBJECTS { alarmEventLogSourceName, alarmEventLogAlarmOrEventId, alarmEventLogDescription,
     alarmEventLogSeverity, alarmEventLogDateAndTime, alarmEventReason,
     ifAlias, dsx1LineStatus }
      STATUS  current
      DESCRIPTION
      "This trap indicates that a Loss of Multi-Frame was detected on an E1 interface.
      "
      ::= { prtDS1Events 28 }



-- LOSS OF SIGNAL (LOS)
e1t1Los  NOTIFICATION-TYPE
	OBJECTS { alarmEventLogSourceName, alarmEventLogAlarmOrEventId, alarmEventLogDescription,
     alarmEventLogSeverity, alarmEventLogDateAndTime, alarmEventReason,
     ifAlias, dsx1LineStatus }
      STATUS  current
      DESCRIPTION
      "This trap indicates that a Loss of signal was detected on an E1/T1 interface.
      "
      ::= { prtDS1Events 30 }

-- LOOPBACK
e1t1Loopback  NOTIFICATION-TYPE
	OBJECTS { alarmEventLogSourceName, alarmEventLogAlarmOrEventId, alarmEventLogDescription,
     alarmEventLogSeverity, alarmEventLogDateAndTime, alarmEventReason,
     ifAlias, dsx1LoopbackStatus }
      STATUS  current
      DESCRIPTION
      "This trap indicates that a Local or Remote Loopback has been activated on a T1/J1 interface.
      "
      ::= { prtDS1Events 36 }

-- LOOPBACK OFF
e1t1LoopbackOff  NOTIFICATION-TYPE
	OBJECTS { alarmEventLogSourceName, alarmEventLogAlarmOrEventId, alarmEventLogDescription,
     alarmEventLogSeverity, alarmEventLogDateAndTime, alarmEventReason,
     ifAlias }
      STATUS  current
      DESCRIPTION
      "This trap indicates that a Local or Remote Loopback has ended on a T1/J1 interface.
      "
      ::= { prtDS1Events 37 }

-- ES LINE TCA
e1t1EsLineTca   NOTIFICATION-TYPE
	OBJECTS { alarmEventLogSourceName, alarmEventLogAlarmOrEventId, alarmEventLogDescription,
     alarmEventLogSeverity, alarmEventLogDateAndTime, alarmEventReason,
     ifAlias, dsx1IntervalLESs, dsx1LineIntervalLesThreshold }
    STATUS      current
    DESCRIPTION
            "This trap indicates DS1 Line Errored Seconds (ES) threshold
            crossing alert"
    ::= { prtDS1Events 38 }

-- CV PATH TCA
e1t1CvPathTca   NOTIFICATION-TYPE
	OBJECTS { alarmEventLogSourceName, alarmEventLogAlarmOrEventId, alarmEventLogDescription,
     alarmEventLogSeverity, alarmEventLogDateAndTime, alarmEventReason,
     ifAlias, dsx1IntervalPCVs, dsx1PathIntervalCvThreshold }
    STATUS      current
    DESCRIPTION
            "This trap indicates DS1 Path Coding Violations (CV)
            threshold crossing alert"
    ::= { prtDS1Events 39 }

-- ES PATH TCA
e1t1EsPathTca   NOTIFICATION-TYPE
	OBJECTS { alarmEventLogSourceName, alarmEventLogAlarmOrEventId, alarmEventLogDescription,
     alarmEventLogSeverity, alarmEventLogDateAndTime, alarmEventReason,
     ifAlias, dsx1IntervalESs, dsx1PathIntervalEsThreshold }
    STATUS      current
    DESCRIPTION
            "This trap indicates DS1 Path Errored Seconds (ES) threshold
            crossing alert"
    ::= { prtDS1Events 40 }

-- SES PATH TCA
e1t1SesPathTca   NOTIFICATION-TYPE
	OBJECTS { alarmEventLogSourceName, alarmEventLogAlarmOrEventId, alarmEventLogDescription,
     alarmEventLogSeverity, alarmEventLogDateAndTime, alarmEventReason,
     ifAlias, dsx1IntervalSESs, dsx1PathIntervalSesThreshold }
    STATUS      current
    DESCRIPTION
            "This trap indicates DS1 Path Severely Errored Seconds (SES)
            threshold crossing alert"
    ::= { prtDS1Events 41 }

-- SEFS PATH TCA
e1t1SefsPathTca   NOTIFICATION-TYPE
	OBJECTS { alarmEventLogSourceName, alarmEventLogAlarmOrEventId, alarmEventLogDescription,
     alarmEventLogSeverity, alarmEventLogDateAndTime, alarmEventReason,
     ifAlias, dsx1IntervalSEFSs, dsx1PathIntervalSefsThreshold }
    STATUS      current
    DESCRIPTION
            "This trap indicates DS1 Path Severely Errored Framing
            Seconds (SEFS) threshold crossing alert"
    ::= { prtDS1Events 42 }

-- CSS PATH TCA
e1t1CssPathTca   NOTIFICATION-TYPE
	OBJECTS { alarmEventLogSourceName, alarmEventLogAlarmOrEventId, alarmEventLogDescription,
     alarmEventLogSeverity, alarmEventLogDateAndTime, alarmEventReason,
     ifAlias, dsx1IntervalCSSs, dsx1PathIntervalCssThreshold }
    STATUS      current
    DESCRIPTION
            "This trap indicates DS1 Path Controlled Slip Seconds (CSS)
            threshold crossing alert"
    ::= { prtDS1Events 43 }

-- UAS PATH TCA
e1t1UasPathTca   NOTIFICATION-TYPE
	OBJECTS { alarmEventLogSourceName, alarmEventLogAlarmOrEventId, alarmEventLogDescription,
     alarmEventLogSeverity, alarmEventLogDateAndTime, alarmEventReason,
     ifAlias, dsx1IntervalUASs, dsx1PathIntervalUasThreshold }
    STATUS      current
    DESCRIPTION
            "This trap indicates DS1 Path Unavailable Seconds (UAS)
            threshold crossing alert"
    ::= { prtDS1Events 44 }

END
