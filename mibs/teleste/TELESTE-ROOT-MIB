--
-- TELESTE-ROOT-MIB.mib
-- MIB generated by MG-SOFT Visual MIB Builder Version 4.0 Build 349
-- Friday, February 20, 2009 at 14:22:33
--

-- *****************************************************************************
-- Copyright (c) 2000-2009 by:
--
-- Teleste Corporation
-- Seponkatu 1
-- FIN-20660 Littoinen, Finland
-- tel. +358 2 2605 611
-- url: http://www.teleste.com
--
-- Description: Root module for Teleste enterprise MIBs
--
-- Revision History:
--
-- 1.71, 20.2.2009 Matti Susi
-- - added ntpcontrol functional group
-- - added Luminato root
--
-- 1.70, 26.3.2008 Matti Susi
-- - added pilotGenerator functional group
--
-- 1.69, 11.1.2008 Matti Susi
-- - added FTTH root
--
-- 1.68, 26.4.2007 Matti Susi
-- - added spectrum analyser functional group
--
-- 1.67, 12.4.2006 Matti Susi
-- - added ValueStatus type assignment
--
-- 1.66, 8.12.2005 Matti Susi
-- - moved functional group definitions up from functional MIBs
--
-- 1.65, 25.11.2005 Matti Susi
-- - added CFO root
--
-- 1.64, 11.8.2005 Matti Susi
-- - added HDO root
--
-- 1.63, 12.11.2004 Matti Susi
-- - added EttH root
--
-- 1.62, 17.3.2004 Matti Susi
-- - object groups functional and experimental added
--
-- 1.61, 2.4.2003 Matti Susi
-- - added ACx root
--
-- 1.6, 12.12.2002 Matti Susi
-- - object groups 'functional' and experimental' moved to
--   TELESTE-ROOT2-MIB
--
-- 1.5, 14.10.2002 Matti Susi
-- - object groups 'functional' and experimental' added
-- - recommended syntax fo DateAndTime changed
--
-- 1.4, 14.8.2002 Matti Susi
-- - added EMT root
--
-- 1.3, 02.07.2002 Pasi Pöri
-- - added EASI root
--
-- 1.2, 05.11.2001 Rainer Salminen
-- - changed the base type of DateAndTime
--   from Octetstring to DisplayString
--
-- 1.1, 24.10.2001 Rainer Salminen
-- - changed length of DateAndTime to 16..28
-- - added rules about DateAndTime format
--
-- 1.0, 11.10.2001 Rainer Salminen
-- - section gendata deprecated
-- - added section common(99) to replace gendata
-- - promoted to version 1.0
--
-- 0.4, 18.9.2001 Matti Susi
-- - added atmux section
--
-- 0.3, 5.2.2001 Matti Susi
-- - Removed all 'real' objects.
--
-- 0.2, 20.11.2000 Matti Susi
-- - More variables added to Gendata section
--
-- 0.1, 20.10.2000 Matti Susi
-- - Initial release
--
-- ****************************************************************************
--

TELESTE-ROOT-MIB DEFINITIONS ::= BEGIN

	IMPORTS
		enterprises
			FROM RFC1155-SMI
		DisplayString
			FROM RFC1213-MIB;


--
-- Type definitions
--

	TDisplayString ::= OCTET STRING (SIZE (0..255))

	TPhysAddress ::= OCTET STRING (SIZE (6))

	Int8 ::= INTEGER (-128..127)

	Int16 ::= INTEGER (-32768..32768)

	Uint8 ::= INTEGER (0..255)

	Uint16 ::= INTEGER (0..65536)

	Uint32 ::= INTEGER (0..2147483647)

-- A date-time specification. It is recommended to follow
-- the syntax in SNMPv2-TC MIB (RFC2579), as follows:
--
--     field  octets  contents                  range
--
--       1      1-2   year                      0..65536
--       2       3    month                     1..12
--       3       4    day                       1..31
--       4       5    hour                      0..23
--       5       6    minutes                   0..59
--       6       7    seconds                   0..60
--                    (use 60 for leap-second)
--       7       8    deci-seconds              0..9
--       8       9    direction from UTC        '+' / '-'
--       9      10    hours from UTC            0..11
--      10      11    minutes from UTC          0..59
--
--      For example, Tuesday May 26, 1992 at 1:30:15 PM EDT would be
--      displayed as:
--
--           1992-5-26,13:30:15.0,-4:0
--
--      Note that if only local time is known, then timezone
--      information (fields 8-10) is not present.
--
--
-- This is the original description not recommended for new
-- agent designs:
--
-- Date and time is represented in extended ISO time format:
--
--        CCYY-MM-DD HH:MM[:SS.ss][Zone]
--
-- Items in brackets are optional.
-- Zone is a character 'Z' for UTC-time or offset to UTC-time
-- in format +hh:mm or -hh:mm.
--
		DateAndTime ::= DisplayString (SIZE (16..28))

-- 'HMS style' value definition for status objects.
		ValueStatus ::= INTEGER {
			valueNormal(1),
			valueHIHI(2),
			valueHi(3),
			valueLo(4),
			valueLOLO(5)
		}

--
-- Node definitions
--

--
-- TELESTE root object identifier
--
		-- 1.3.6.1.4.1.3715
		teleste OBJECT IDENTIFIER ::= { enterprises 3715 }


--
-- EMS server objects (SNMP Wizard)
--
		-- 1.3.6.1.4.1.3715.1
		ems OBJECT IDENTIFIER ::= { teleste 1 }


--
-- Objects common to all teleste products/agents.
-- Deprecated 11.10.2001 and replaced with section Common.
--
		-- 1.3.6.1.4.1.3715.2
		gendata OBJECT IDENTIFIER ::= { teleste 2 }


--
-- BK product family specific objects
--
		-- 1.3.6.1.4.1.3715.3
		bk OBJECT IDENTIFIER ::= { teleste 3 }


--
-- BXX product family specific objects
--
		-- 1.3.6.1.4.1.3715.4
		bxx OBJECT IDENTIFIER ::= { teleste 4 }


--
-- DVO product family specific objects
--
		-- 1.3.6.1.4.1.3715.5
		dvo OBJECT IDENTIFIER ::= { teleste 5 }


--
-- DVX product family specific objects
--
		-- 1.3.6.1.4.1.3715.6
		dvx OBJECT IDENTIFIER ::= { teleste 6 }


--
-- INF product family specific objects
--
		-- 1.3.6.1.4.1.3715.7
		inf OBJECT IDENTIFIER ::= { teleste 7 }


--
-- ATMux product family specific objects
--
		-- 1.3.6.1.4.1.3715.8
		atmux OBJECT IDENTIFIER ::= { teleste 8 }


--
-- Edge Access System Interface products.
--
		-- 1.3.6.1.4.1.3715.9
		easi OBJECT IDENTIFIER ::= { teleste 9 }


--
-- EMT product family specific objects
--
		-- 1.3.6.1.4.1.3715.10
		emt OBJECT IDENTIFIER ::= { teleste 10 }


--
-- ACx product family specific objects
--
		-- 1.3.6.1.4.1.3715.11
		acx OBJECT IDENTIFIER ::= { teleste 11 }


--
-- EttH product family specific objects
--
		-- 1.3.6.1.4.1.3715.12
		etth OBJECT IDENTIFIER ::= { teleste 12 }


--
-- HDO product family specific objects
--
		-- 1.3.6.1.4.1.3715.14
		hdo OBJECT IDENTIFIER ::= { teleste 14 }


--
-- CFO product family specific objects
--
		-- 1.3.6.1.4.1.3715.15
		cfo OBJECT IDENTIFIER ::= { teleste 15 }


-- FTTH product family specific objects
		-- 1.3.6.1.4.1.3715.16
		ftth OBJECT IDENTIFIER ::= { teleste 16 }


		-- 1.3.6.1.4.1.3715.17
		luminato OBJECT IDENTIFIER ::= { teleste 17 }


--
-- Objects common to all teleste products/agents.
--
		-- 1.3.6.1.4.1.3715.99
		common OBJECT IDENTIFIER ::= { teleste 99 }


--
-- Functional object groups
--
		-- 1.3.6.1.4.1.3715.100
		functional OBJECT IDENTIFIER ::= { teleste 100 }


		-- 1.3.6.1.4.1.3715.100.1
		hmsModem OBJECT IDENTIFIER ::= { functional 1 }


		-- 1.3.6.1.4.1.3715.100.2
		spectrumAnalyser OBJECT IDENTIFIER ::= { functional 2 }


		-- 1.3.6.1.4.1.3715.100.3
		pilotGenerator OBJECT IDENTIFIER ::= { functional 3 }


		-- 1.3.6.1.4.1.3715.100.4
		ntpcontrol OBJECT IDENTIFIER ::= { functional 4 }


		-- 1.3.6.1.4.1.3715.100.10
		hfcOptics OBJECT IDENTIFIER ::= { functional 10 }


		-- 1.3.6.1.4.1.3715.100.20
		headEnd OBJECT IDENTIFIER ::= { functional 20 }


--
-- Placeholder experimental and preliminary MIB modules.
--
		-- 1.3.6.1.4.1.3715.999
		experimental OBJECT IDENTIFIER ::= { teleste 999 }



	END

--
-- TELESTE-ROOT-MIB.mib
--
