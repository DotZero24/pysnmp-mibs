CYAN-TC-MIB DEFINITIONS ::= BEGIN

IMPORTS
  MODULE-IDENTITY
                    FROM SNMPv2-SMI
  TEXTUAL-CONVENTION
                    FROM SNMPv2-TC
  cyanMibModules
		    FROM CYAN-MIB;

cyanTCModule MODULE-IDENTITY
    LAST-UPDATED "201412070545Z" -- Sun Dec  7 05:45:31 2014
    ORGANIZATION "Cyan, Inc."
    CONTACT-INFO
        "
        E-mail:  support@cyaninc.com

        Postal:  Cyan, Inc.
               1390 N. McDowell Blvd., # G-327
               Petaluma, CA  94954
               USA

        Tel:     +1-707-735-2300"

    DESCRIPTION    "MIB module for Textual Conventions"

    REVISION     "201412070545Z" -- Sun Dec  7 05:45:31 2014
    DESCRIPTION  "Release 6.0 build 1416362081"

    ::= { cyanMibModules 1 }



CyanActvStdbyTc ::= TEXTUAL-CONVENTION
      STATUS       current
      DESCRIPTION
      "CyanActvStdbyTc"
      SYNTAX	INTEGER {
          stdby (0), -- Standby
          active (1) -- Active
      }

CyanAdminStateTc ::= TEXTUAL-CONVENTION
      STATUS       current
      DESCRIPTION
      "CyanAdminStateTc"
      SYNTAX	INTEGER {
          adminunlocked (1), -- Unlocked
          adminautoinservice (2), -- Automatic In-Service
          adminlockedmat (3), -- Locked for Maint
          adminlockeddis (4) -- Locked to Disable
      }

CyanAugStructureTc ::= TEXTUAL-CONVENTION
      STATUS       current
      DESCRIPTION
      "CyanAugStructureTc"
      SYNTAX	INTEGER {
          notconfigured (0), -- Not Configured
          au464c (8), -- AU-4-64c
          aug16 (7), -- Transparent Line
          transparent (9) -- STS-48/AUG-16
      }

CyanChannelIdTc ::= TEXTUAL-CONVENTION
      STATUS       current
      DESCRIPTION
      "CyanChannelIdTc"
      SYNTAX	INTEGER {
          protect (0), -- Protect
          working (1) -- Working
      }

CyanEnDisabledTc ::= TEXTUAL-CONVENTION
      STATUS       current
      DESCRIPTION
      "CyanEnDisabledTc"
      SYNTAX	INTEGER {
          disabled (0), -- Disabled
          enabled (1) -- Enabled
      }

CyanFecModeTc ::= TEXTUAL-CONVENTION
      STATUS       current
      DESCRIPTION
      "CyanFecModeTc"
      SYNTAX	INTEGER {
          fecReedSolomon (1), -- Reed-Solomon G.975
          fecEnhanced (3) -- Enhanced G.975.1/App.4
      }

CyanFppSubTypeTc ::= TEXTUAL-CONVENTION
      STATUS       current
      DESCRIPTION
      "CyanFppSubTypeTc"
      SYNTAX	INTEGER {
          unconfigured (0), -- Unconfigured
          unitype1 (1), -- UNI Type 1
          unitype2 (2), -- UNI Type 2
          nnipbb (3), -- nniPbb
          nnimpls (4) -- nniMpls
      }

CyanFppTypeTc ::= TEXTUAL-CONVENTION
      STATUS       current
      DESCRIPTION
      "CyanFppTypeTc"
      SYNTAX	INTEGER {
          uni (1), -- UNI
          nni (2) -- NNI
      }

CyanGfpUpiTc ::= TEXTUAL-CONVENTION
      STATUS       current
      DESCRIPTION
      "CyanGfpUpiTc"
      SYNTAX	INTEGER {
          ethernetframe (1), -- EthernetFrame
          pppFrame (2), -- PPP_Frame
          fiberchannelTransparent (3), -- FiberChannel_Transparent
          ficonTransparent (4), -- FICON_Transparent
          esconTransparent (5), -- ESCON_Transparent
          gbeTransparent (6), -- GbE_Transparent
          maposFrame (8), -- MAPOS_Frame
          dvbAsiTransparent (9), -- DVB_ASI_Transparent
          ieee80217RprFrame (10), -- IEEE80217_RPR_Frame
          fiberchannelBbwFrame (11), -- FiberChannel_BBW_Frame
          fiberchannelAsyncTransparent (12), -- FiberChannel_Async_Transparent
          mplsFrame (13), -- MPLS_Frame
          osiFrame (15), -- OSI_Frame
          ipv4Frame (16), -- IPv4_Frame
          ipv6Frame (17), -- IPv6_Frame
          dvbAsiFrame (18), -- DVB_ASI_Frame
          ethernet64b66bFrame (19), -- Ethernet64B66B_Frame
          ethernet64b66bOrderedsetFrame (20), -- Ethernet64B66B_OrderedSet_Frame
          fc1200Transparent (21) -- FC1200_Transparent
      }

CyanLEDTc ::= TEXTUAL-CONVENTION
      STATUS       current
      DESCRIPTION
      "CyanLEDTc"
      SYNTAX	INTEGER {
          off (0), -- Off
          redBlinking (1), -- Blinking Red
          red (2), -- Red
          greenBlinking (3), -- Blinking Green
          green (4), -- Green
          amberBlinking (5), -- Blinking Amber
          amber (6), -- Amber
          blueBlinking (7), -- Blinking Blue
          blue (8), -- Blue
          redBlinkingSlow (9), -- Blinking Red (slow)
          greenBlinkingSlow (10), -- Blinking Green (slow)
          amberBlinkingSlow (11), -- Blinking Amber (slow)
          blueBlinkingSlow (12) -- Blinking Blue (slow)
      }

CyanLayerRateTc ::= TEXTUAL-CONVENTION
      STATUS       current
      DESCRIPTION
      "CyanLayerRateTc"
      SYNTAX	BITS {
          na (0), -- N/A
          fiber (1), -- Fiber
          electrical (2), -- Electrical
          och (3), -- OCh
          odu1 (4), -- ODU-1
          odu2 (5), -- ODU-2
          odu3 (6), -- ODU-3
          ethernet (7), -- Ethernet
          gigethernet (8), -- 1GE
          tengigethernet (9), -- 10GE
          gfp (10), -- Generic Frame
          ethernettunnel (11), -- Ethernet Tunnel
          ocgfiber (12), -- OCG Fiber
          odu2e (13), -- ODU-2e
          otu2 (14), -- OTU-2
          otu2e (15), -- OTU-2e
          otu1e (16), -- Otu1e
          odu1e (17), -- Odu1e
          odu0 (18), -- Odu0
          oduflex4 (19), -- Oduflex4
          otu4 (20), -- Otu4
          vc3 (21), -- STS-1/VC-3
          vc4 (22), -- STS-3c/VC-4
          vc44c (23), -- STS-12c/VC-4-4c
          vc416c (24), -- STS-48c/VC-4-16c
          vc464c (25), -- STS-192c/VC-4-64c
          odu4 (26), -- Odu4
          odu2f (27), -- Odu2f
          otu2f (28), -- Otu2f
          otu1f (29), -- Otu1f
          cgigethernet (30), -- CGigEthernet
          stm1ms (31), -- OC-3/STM-1
          stm4ms (32), -- OC-12/STM-4
          stm16ms (33), -- OC-48/STM-16
          stm64ms (34), -- STM64MS
          fiber100g (40), -- Fiber100G
          multifiber3 (41), -- MultiFiber3
          multifiber10g10 (42), -- MultiFiber10G10
          multifiber7 (43), -- MultiFiber7
          fiber100g4 (44), -- Fiber100G4
          fiber100g10 (45) -- Fiber100G10
      }

CyanLoopbackControlTc ::= TEXTUAL-CONVENTION
      STATUS       current
      DESCRIPTION
      "CyanLoopbackControlTc"
      SYNTAX	INTEGER {
          disabled (0), -- Disabled
          facilitylpbk (1), -- Facility LB
          terminallpbk (3) -- Terminal LB
      }

CyanNationalizationTc ::= TEXTUAL-CONVENTION
      STATUS       current
      DESCRIPTION
      "CyanNationalizationTc"
      SYNTAX	INTEGER {
          itu (1), -- ITU
          ansi (2) -- ANSI
      }

CyanNimTc ::= TEXTUAL-CONVENTION
      STATUS       current
      DESCRIPTION
      "CyanNimTc"
      SYNTAX	INTEGER {
          terminating (0), -- Terminating
          monitoring (1) -- Monitoring
      }

CyanNoYesTc ::= TEXTUAL-CONVENTION
      STATUS       current
      DESCRIPTION
      "CyanNoYesTc"
      SYNTAX	INTEGER {
          no (0), -- No
          yes (1) -- Yes
      }

CyanOffOnTc ::= TEXTUAL-CONVENTION
      STATUS       current
      DESCRIPTION
      "CyanOffOnTc"
      SYNTAX	INTEGER {
          off (0), -- Off
          on (1), -- On
          unknown (2) -- Unknown
      }

CyanOpStateQualTc ::= TEXTUAL-CONVENTION
      STATUS       current
      DESCRIPTION
      "CyanOpStateQualTc"
      SYNTAX	INTEGER {
          au (1), -- Autonomous
          ma (2), -- Management
          auma (3), -- Autonomous & Management
          aurst (4), -- Autonomous & Restricted
          maanr (5), -- Management & Abnormal
          nr (6), -- Normal
          anr (7), -- Abnormal
          rst (8), -- Restricted
          anrst (9) -- Abnormal & Restricted
      }

CyanOpStateTc ::= TEXTUAL-CONVENTION
      STATUS       current
      DESCRIPTION
      "CyanOpStateTc"
      SYNTAX	INTEGER {
          is (1), -- In-Service
          oos (2) -- Out-Of-Service
      }

CyanOpuPayloadTypeTc ::= TEXTUAL-CONVENTION
      STATUS       current
      DESCRIPTION
      "CyanOpuPayloadTypeTc"
      SYNTAX	INTEGER {
          experimental (0), -- experimental
          expmap (1), -- Experimental
          asynchcbrmap (2), -- Async CBR
          synchcbrmap (3), -- Sync CBR
          atmmap (4), -- ATM
          gfpmap (5), -- GFP
          vc (6), -- VC
          opu01000bxmap (7), -- opu01000bxMap
          fc1200mapodu2e (8), -- fc1200MapOdu2e
          gfpmapextendedopu2 (9), -- gfpMapExtendedOpu2
          stm1mapodu0 (10), -- stm1MapOdu0
          stm4mapodu0 (11), -- stm4MapOdu0
          fc100mapodu0 (12), -- fc100MapOdu0
          fc200mapodu1 (13), -- fc200MapOdu1
          fc400mapoduflex (14), -- fc400MapOduflex
          fc800mapoduflex (15), -- fc800MapOduflex
          bitstreamwithtiming (16), -- Bit Stream w/ Timning
          bitstreamwotiming (17), -- Bit Stream w/o Timning
          ibSdrIntoOduflex (18), -- IB_SDR_into_ODUflex
          ibDdrIntoOduflex (19), -- IB_DDR_into_ODUflex
          ibQdrIntoOduflex (20), -- IB_QDR_into_ODUflex
          sdiIntoOpu0 (21), -- SDI_into_OPU0
          sdi1g4851g001IntoOpu1 (22), -- SDI_1G485_1G001_into_OPU1
          sdi1g485IntoOpu1 (23), -- SDI_1G485_into_OPU1
          sdi2g9701g001IntoOpuflex (24), -- SDI_2G970_1G001_into_OPUflex
          sdi2g970IntoOpuflex (25), -- SDI_2G970_into_OPUflex
          sbconEsconIntoOpu0 (26), -- SBCON_ESCON_into_OPU0
          dvbAsiIntoOpu0 (27), -- DVB_ASI_into_OPU0
          fc1600mapoduflex (28), -- fc1600MapOduflex
          undef1d (29), -- 0x1D
          undef1e (30), -- 0x1E
          undef1f (31), -- 0x1F
          odumultiplex (32), -- ODU Multiplex
          odumultiplexgmp (33), -- oduMultiplexGmp
          undef22 (34), -- 0x22
          undef23 (35), -- 0x23
          undef24 (36), -- 0x24
          undef25 (37), -- 0x25
          undef26 (38), -- 0x26
          undef27 (39), -- 0x27
          undef28 (40), -- 0x28
          undef29 (41), -- 0x29
          undef2a (42), -- 0x2A
          undef2b (43), -- 0x2B
          undef2c (44), -- 0x2C
          undef2d (45), -- 0x2D
          undef2e (46), -- 0x2E
          undef2f (47), -- 0x2F
          undef30 (48), -- 0x30
          undef31 (49), -- 0x31
          undef32 (50), -- 0x32
          undef33 (51), -- 0x33
          undef34 (52), -- 0x34
          undef35 (53), -- 0x35
          undef36 (54), -- 0x36
          undef37 (55), -- 0x37
          undef38 (56), -- 0x38
          undef39 (57), -- 0x39
          undef3a (58), -- 0x3A
          undef3b (59), -- 0x3B
          undef3c (60), -- 0x3C
          undef3d (61), -- 0x3D
          undef3e (62), -- 0x3E
          undef3f (63), -- 0x3F
          undef40 (64), -- 0x40
          undef41 (65), -- 0x41
          undef42 (66), -- 0x42
          undef43 (67), -- 0x43
          undef44 (68), -- 0x44
          undef45 (69), -- 0x45
          undef46 (70), -- 0x46
          undef47 (71), -- 0x47
          undef48 (72), -- 0x48
          undef49 (73), -- 0x49
          undef4a (74), -- 0x4A
          undef4b (75), -- 0x4B
          undef4c (76), -- 0x4C
          undef4d (77), -- 0x4D
          undef4e (78), -- 0x4E
          undef4f (79), -- 0x4F
          undef50 (80), -- 0x50
          undef51 (81), -- 0x51
          undef52 (82), -- 0x52
          undef53 (83), -- 0x53
          undef54 (84), -- 0x54
          notavailablelck (85), -- Not Available: Locked
          undef56 (86), -- 0x56
          undef57 (87), -- 0x57
          undef58 (88), -- 0x58
          undef59 (89), -- 0x59
          undef5a (90), -- 0x5A
          undef5b (91), -- 0x5B
          undef5c (92), -- 0x5C
          undef5d (93), -- 0x5D
          undef5e (94), -- 0x5E
          undef5f (95), -- 0x5F
          undef60 (96), -- 0x60
          undef61 (97), -- 0x61
          undef62 (98), -- 0x62
          undef63 (99), -- 0x63
          undef64 (100), -- 0x64
          undef65 (101), -- 0x65
          notavailableoci (102), -- Not Available: OCI
          undef67 (103), -- 0x67
          undef68 (104), -- 0x68
          undef69 (105), -- 0x69
          undef6a (106), -- 0x6A
          undef6b (107), -- 0x6B
          undef6c (108), -- 0x6C
          undef6d (109), -- 0x6D
          undef6e (110), -- 0x6E
          undef6f (111), -- 0x6F
          undef70 (112), -- 0x70
          undef71 (113), -- 0x71
          undef72 (114), -- 0x72
          undef73 (115), -- 0x73
          undef74 (116), -- 0x74
          undef75 (117), -- 0x75
          undef76 (118), -- 0x76
          undef77 (119), -- 0x77
          undef78 (120), -- 0x78
          undef79 (121), -- 0x79
          undef7a (122), -- 0x7A
          undef7b (123), -- 0x7B
          undef7c (124), -- 0x7C
          undef7d (125), -- 0x7D
          undef7e (126), -- 0x7E
          undef7f (127), -- 0x7F
          reserved80 (128), -- 0x80
          reserved81 (129), -- 0x81
          reserved82 (130), -- 0x82
          reserved83 (131), -- 0x83
          reserved84 (132), -- 0x84
          reserved85 (133), -- 0x85
          reserved86 (134), -- 0x86
          reserved87 (135), -- 0x87
          reserved88 (136), -- 0x88
          reserved89 (137), -- 0x89
          reserved8a (138), -- 0x8A
          reserved8b (139), -- 0x8B
          reserved8c (140), -- 0x8C
          reserved8d (141), -- 0x8D
          fc800mapodu2 (142), -- fc800MapOdu2
          bittransparent (143), -- Bit Transparent
          undef90 (144), -- 0x90
          undef91 (145), -- 0x91
          undef92 (146), -- 0x92
          undef93 (147), -- 0x93
          undef94 (148), -- 0x94
          undef95 (149), -- 0x95
          undef96 (150), -- 0x96
          undef97 (151), -- 0x97
          undef98 (152), -- 0x98
          undef99 (153), -- 0x99
          undef9a (154), -- 0x9A
          undef9b (155), -- 0x9B
          undef9c (156), -- 0x9C
          undef9d (157), -- 0x9D
          undef9e (158), -- 0x9E
          undef9f (159), -- 0x9F
          undefA0 (160), -- 0xA0
          undefA1 (161), -- 0xA1
          undefA2 (162), -- 0xA2
          undefA3 (163), -- 0xA3
          undefA4 (164), -- 0xA4
          undefA5 (165), -- 0xA5
          undefA6 (166), -- 0xA6
          undefA7 (167), -- 0xA7
          undefA8 (168), -- 0xA8
          undefA9 (169), -- 0xA9
          undefAa (170), -- 0xAA
          undefAb (171), -- 0xAB
          undefAc (172), -- 0xAC
          undefAd (173), -- 0xAD
          undefAe (174), -- 0xAE
          undefAf (175), -- 0xAF
          undefB0 (176), -- 0xB0
          undefB1 (177), -- 0xB1
          undefB2 (178), -- 0xB2
          undefB3 (179), -- 0xB3
          undefB4 (180), -- 0xB4
          undefB5 (181), -- 0xB5
          undefB6 (182), -- 0xB6
          undefB7 (183), -- 0xB7
          undefB8 (184), -- 0xB8
          undefB9 (185), -- 0xB9
          undefBa (186), -- 0xBA
          undefBb (187), -- 0xBB
          undefBc (188), -- 0xBC
          undefBd (189), -- 0xBD
          undefBe (190), -- 0xBE
          undefBf (191), -- 0xBF
          undefC0 (192), -- 0xC0
          undefC1 (193), -- 0xC1
          undefC2 (194), -- 0xC2
          undefC3 (195), -- 0xC3
          undefC4 (196), -- 0xC4
          undefC5 (197), -- 0xC5
          undefC6 (198), -- 0xC6
          undefC7 (199), -- 0xC7
          undefC8 (200), -- 0xC8
          undefC9 (201), -- 0xC9
          undefCa (202), -- 0xCA
          undefCb (203), -- 0xCB
          undefCc (204), -- 0xCC
          undefCd (205), -- 0xCD
          undefCe (206), -- 0xCE
          undefCf (207), -- 0xCF
          undefD0 (208), -- 0xD0
          undefD1 (209), -- 0xD1
          undefD2 (210), -- 0xD2
          undefD3 (211), -- 0xD3
          undefD4 (212), -- 0xD4
          undefD5 (213), -- 0xD5
          undefD6 (214), -- 0xD6
          undefD7 (215), -- 0xD7
          undefD8 (216), -- 0xD8
          undefD9 (217), -- 0xD9
          undefDa (218), -- 0xDA
          undefDb (219), -- 0xDB
          undefDc (220), -- 0xDC
          undefDd (221), -- 0xDC
          undefDe (222), -- 0xDE
          undefDf (223), -- 0xFD
          undefE0 (224), -- 0xE0
          undefE1 (225), -- 0xE1
          undefE2 (226), -- 0xE2
          undefE3 (227), -- 0xE3
          undefE4 (228), -- 0xE4
          undefE5 (229), -- 0xE5
          undefE6 (230), -- 0xE6
          undefE7 (231), -- 0xE7
          undefE8 (232), -- 0xE8
          undefE9 (233), -- 0xE9
          undefEa (234), -- 0xEA
          undefEb (235), -- 0xEB
          undefEc (236), -- 0xEC
          undefEd (237), -- 0xED
          undefEe (238), -- 0xEE
          undefEf (239), -- 0xEF
          undefF0 (240), -- 0xF0
          undefF1 (241), -- 0xF1
          undefF2 (242), -- 0xF2
          undefF3 (243), -- 0xF3
          undefF4 (244), -- 0xF4
          undefF5 (245), -- 0xF5
          undefF6 (246), -- 0xF6
          undefF7 (247), -- 0xF7
          undefF8 (248), -- 0xF8
          undefF9 (249), -- 0xF9
          undefFa (250), -- 0xFA
          undefFb (251), -- 0xFB
          undefFc (252), -- 0xFC
          nulltest (253), -- NULL Test Signal
          prbstest (254), -- Random Bit Test Signal
          notavailableais (255), -- Not Available: AIS
          notavailablefault (256), -- Not Available: Fault
          unstable (257), -- Unstable
          nim (258) -- Non-intrusive Monitoring
      }

CyanPowerClassTc ::= TEXTUAL-CONVENTION
      STATUS       current
      DESCRIPTION
      "CyanPowerClassTc"
      SYNTAX	INTEGER {
          powerclass1 (0), -- PowerClass1
          powerclass2 (1), -- PowerClass2
          powerclass3 (2), -- PowerClass3
          powerclass4 (3) -- PowerClass4
      }

CyanRelayTc ::= TEXTUAL-CONVENTION
      STATUS       current
      DESCRIPTION
      "CyanRelayTc"
      SYNTAX	INTEGER {
          rsOpen (0), -- Relay Open
          rsClose (1) -- Relay Closed
      }

CyanSdhSnSignalLabelTc ::= TEXTUAL-CONVENTION
      STATUS       current
      DESCRIPTION
      "CyanSdhSnSignalLabelTc"
      SYNTAX	INTEGER {
          unequipped (0), -- Unequipped 0x00
          equippedNonspecific (1), -- Equipped Non-Specific 0x01
          vtStructured (2), -- TUG/VT Structure 0x02
          lockedVtMode (3), -- Locked TU/VT 0x03
          asyncDs3Mapping (4), -- Async DS3 0x04
          asyncDs4naMapping (18), -- Async DS4NA 0x12
          atmMapping (19), -- ATM 0x13
          dqdbMapping (20), -- DQDB 0x14
          asyncFddiMapping (21), -- Async FDDI 0x15
          hdlcOverSonetMapping (22), -- HDLC/PPP 0x16
          hdlcLapsMapping (24), -- HDLC/LAPS 0x18
          xgeWan (26), -- GFP 0x1B
          gfp (27), -- GFP 0x1B
          o181TestSignalMapping (254) -- O181 Test Signal 0xFE
      }

CyanSecServiceStateTc ::= TEXTUAL-CONVENTION
      STATUS       current
      DESCRIPTION
      "CyanSecServiceStateTc"
      SYNTAX	BITS {
          nalm (0), -- Not Alarmed
          act (1), -- Active
          ains (2), -- Automatic In-Service
          busy (3), -- Busy
          blkd (4), -- Blocked
          cema (5), -- Composite Entity OSS MA
          discd (6), -- Disconnected
          dsbld (7), -- Disabled
          ex (8), -- Exercise
          faf (9), -- Facility Fail
          flt (10), -- Fault
          frcd (11), -- Forced
          idle (12), -- Idle
          idlerx (13), -- Idle Receive
          idletx (14), -- Idle Transmit
          inhip (15), -- Inhibit In Progress
          lkdo (16), -- Locked Out
          mea (17), -- Equipment Mismatched
          mt (18), -- Maintenance
          lpbk (19), -- Loopback
          sdee (20), -- Supported Entity Exist
          sdea (21), -- Supported Entity Abnormal
          sder (22), -- Supported Entity Restricted
          sdeo (23), -- Supported Entity Out-Of-Service
          sdel (24), -- Supported Entity Locked
          sgel (25), -- Supporting Entity Locked
          sgeo (26), -- Supporting Entity Out-Of-Service
          sgea (27), -- Supporting Entity Abnormal
          sger (28), -- Supporting Entity Restricted
          swdl (29), -- Software Downloading
          swul (30), -- Software Uploading
          uas (31), -- Unassigned
          ueq (32), -- UnEquipped
          unavail (33), -- Unavailable
          sgml (41), -- Supported Member Locked
          sgmo (42), -- Supported Member Out-Of-Service
          sgma (43), -- Supporting Entity
          sgmr (44) -- Supported Member Restricted
      }

CyanSsBitsTc ::= TEXTUAL-CONVENTION
      STATUS       current
      DESCRIPTION
      "CyanSsBitsTc"
      SYNTAX	INTEGER {
          ss00 (0), -- 00
          ss10 (2) -- 10
      }

CyanTPConnectionStateTc ::= TEXTUAL-CONVENTION
      STATUS       current
      DESCRIPTION
      "CyanTPConnectionStateTc"
      SYNTAX	INTEGER {
          tpcsSourceConnected (1), -- Connected as Source
          tpcsSinkConnected (2), -- Connected as Sink
          tpcsBiConnected (3), -- Connected BiDir
          tpcsNotConnected (4) -- Not Connected
      }

CyanTimezoneTc ::= TEXTUAL-CONVENTION
      STATUS       current
      DESCRIPTION
      "CyanTimezoneTc"
      SYNTAX	INTEGER {
          utc (0), -- UTC
          americaNewYork (1), -- America - New York
          americaDetroit (2), -- America - Detroit
          americaKentuckyLouisville (3), -- America - Kentucky, Louisville
          americaKentuckyMonticello (4), -- America - Kentucky, Monticello
          americaIndianaIndianapolis (5), -- America - Indiana, Indianapolis
          americaIndianaVincennes (6), -- America - Indiana, Vincennes
          americaIndianaKnox (7), -- America - Indiana, Knox
          americaIndianaWinamac (8), -- America - Indiana, Winamac
          americaIndianaMarengo (9), -- America - Indiana, Marengo
          americaIndianaVevay (10), -- America - Indiana, Vevay
          americaChicago (11), -- America - Chicago
          americaIndianaTellCity (12), -- America - Indiana, Tell City
          americaIndianaPetersburg (13), -- America - Indiana, Petersburg
          americaMenominee (14), -- America - Menominee
          americaNorthDakotaCenter (15), -- America - North Dakota, Center
          americaNorthDakotaNewSalem (16), -- America - North Dakota, New Salem
          americaDenver (17), -- America - Denver
          americaBoise (18), -- America - Boise
          americaShiprock (19), -- America - Shiprock
          americaPhoenix (20), -- America - Phoenix
          americaLosAngeles (21), -- America - Los Angeles
          americaAnchorage (22), -- America - Anchorage
          americaJuneau (23), -- America - Juneau
          americaYakutat (24), -- America - Yakutat
          americaNome (25), -- America - Nome
          americaAdak (26), -- America - Adak
          pacificHonolulu (27) -- Pacific - Honolulu
      }

CyanTxControlTc ::= TEXTUAL-CONVENTION
      STATUS       current
      DESCRIPTION
      "CyanTxControlTc"
      SYNTAX	INTEGER {
          off (0), -- Off
          on (1), -- On
          als (2) -- ALS
      }

CyanWdmTypeTc ::= TEXTUAL-CONVENTION
      STATUS       current
      DESCRIPTION
      "CyanWdmTypeTc"
      SYNTAX	INTEGER {
          nonwdm (0), -- NonWDM
          cwdm (1), -- CWDM
          lanwdm (2), -- LANWDM
          dwdm200gGrid (3), -- DWDM200G_Grid
          dwdm100gGrid (4), -- DWDM100G_Grid
          dwdm50gGrid (5), -- DWDM50G_Grid
          dwdm25gGrid (6), -- DWDM25G_Grid
          otherwdm (7) -- OtherWDM
      }

CyanXGOSignalTypeTc ::= TEXTUAL-CONVENTION
      STATUS       current
      DESCRIPTION
      "CyanXGOSignalTypeTc"
      SYNTAX	INTEGER {
          otu2 (32), -- OTU-2
          otu2e (33), -- OTU-2e
          otu1e (34), -- OTU1e
          tp10gelan (22), -- 10GE LAN
          tp10gewan (23) -- 10GE WAN
      }

CyanXcvrConnectorCodeTc ::= TEXTUAL-CONVENTION
      STATUS       current
      DESCRIPTION
      "CyanXcvrConnectorCodeTc"
      SYNTAX	INTEGER {
          unknownorunspecified (0), -- Unknown/Unspecified
          sc (1), -- SC
          fibrechannelstyle1Copper (2), -- FibreChannelStyle1_Copper
          fibrechannelstyle2Copper (3), -- FibreChannelStyle2_Copper
          bncTnc (4), -- BNC_TNC
          fibrechannelcoax (5), -- FibreChannelCoax
          fiberjack (6), -- FiberJack
          lc (7), -- LC
          mtRj (8), -- MT_RJ
          mu (9), -- MU
          sg (10), -- SG
          opticalpigtail (11), -- OpticalPigtail
          mpoParalleloptic (12), -- MPO_ParallelOptic
          rj45 (34), -- RJ45
          hssdcIi (32), -- HSSDC_II
          copperpigtail (33) -- CopperPigtail
      }

CyanXcvrIdentifierTc ::= TEXTUAL-CONVENTION
      STATUS       current
      DESCRIPTION
      "CyanXcvrIdentifierTc"
      SYNTAX	INTEGER {
          unknownUnspecified (0), -- Unknown/UnSpecified
          gbic (1), -- GBIC
          modulesolderedtomotherboard (2), -- ModuleSolderedToMotherboard
          sfpOrSfpplus (3), -- SFP or SFP Plus
          xbi300pin (4), -- XBI 300Pin
          xenpak (5), -- Xenpak
          xfp (6), -- XFP
          xff (7), -- XFF
          xfpE (8), -- XFP-E
          xpak (9), -- XPak
          x2 (10), -- X2
          dwdmSfp (11), -- DWDM SFP
          qsfp (12), -- QSFP
          qsfpPlus (13), -- QSFP_Plus
          cfp (14), -- CFP
          cxp (15), -- CXP
          msa100glh (16), -- MSA_100GLH
          cfp2 (17), -- CFP2
          cfp4 (18) -- CFP4
      }

END
