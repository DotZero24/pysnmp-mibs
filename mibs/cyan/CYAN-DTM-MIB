CYAN-DTM-MIB DEFINITIONS ::= BEGIN
IMPORTS
    MODULE-IDENTITY,
    OBJECT-TYPE,
    Integer32,
    Unsigned32
                    FROM SNMPv2-SMI

    DisplayString
                    FROM SNMPv2-TC

    CyanLEDTc,
    CyanOffOnTc,
    CyanActvStdbyTc,
    CyanAdminStateTc,
    CyanOpStateQualTc,
    CyanSecServiceStateTc,
    CyanOpStateTc
                    FROM CYAN-TC-MIB

    CyanTypeTc,
    cyanEntityModules
		    FROM CYAN-MIB

    MODULE-COMPLIANCE,
    OBJECT-GROUP
	            FROM SNMPv2-CONF;


cyanDtmModule MODULE-IDENTITY
    LAST-UPDATED "201412070545Z" -- Sun Dec  7 05:45:27 2014
    ORGANIZATION "Cyan, Inc."
    CONTACT-INFO
        "
        E-mail:  support@cyaninc.com

        Postal:  Cyan, Inc.
               1390 N. McDowell Blvd., # G-327
               Petaluma, CA  94954
               USA

        Tel:     +1-707-735-2300"

    DESCRIPTION    "MIB module for Digital Transmission Module (DTM)"

    REVISION     "201412070545Z" -- Sun Dec  7 05:45:27 2014
    DESCRIPTION  "Release 6.0 build 1416362081"

    ::= { cyanEntityModules 120 }

cyanDtmMibObjects           OBJECT IDENTIFIER ::={ cyanDtmModule 1 }

cyanDtmTable    OBJECT-TYPE
    SYNTAX        SEQUENCE OF CyanDtmEntry
    MAX-ACCESS    not-accessible
    STATUS        current
    DESCRIPTION
        "A list of Dtm entries."
    ::= { cyanDtmMibObjects 1 }

cyanDtmEntry    OBJECT-TYPE
    SYNTAX        CyanDtmEntry
    MAX-ACCESS    not-accessible
    STATUS        current
    DESCRIPTION
        "An entry of Dtm."
    INDEX {
        cyanDtmShelfId ,
        cyanDtmDtmId
    }
    ::= { cyanDtmTable 1 }

CyanDtmEntry  ::=
    SEQUENCE {
        cyanDtmShelfId    Unsigned32,
        cyanDtmDtmId    Unsigned32,
        cyanDtmActiveLed    CyanLEDTc,
        cyanDtmActivestandbyState    CyanActvStdbyTc,
        cyanDtmAdminState    CyanAdminStateTc,
        cyanDtmAlarmLed    CyanLEDTc,
        cyanDtmAssetTag    DisplayString,
        cyanDtmAutoinserviceSoakTimeSec    Integer32,
        cyanDtmBaseMacAddress    DisplayString,
        cyanDtmCurrCyanSwBuildVersions    DisplayString,
        cyanDtmCurrCyanSwRelease    DisplayString,
        cyanDtmCurrent    Integer32,
        cyanDtmDescription    DisplayString,
        cyanDtmExhaustAirTemp    Integer32,
        cyanDtmExhaustTempAlarmHighThres    Integer32,
        cyanDtmExhaustTempAlarmLowThres    Integer32,
        cyanDtmExhaustTempWarnHighThres    Integer32,
        cyanDtmExhaustTempWarnLowThres    Integer32,
        cyanDtmExpectedTemperatureRise    Integer32,
        cyanDtmIdentifier    DisplayString,
        cyanDtmIntakeAirTemp    Integer32,
        cyanDtmIntakeTempAlarmHighThres    Integer32,
        cyanDtmIntakeTempAlarmLowThres    Integer32,
        cyanDtmIntakeTempWarnHighThres    Integer32,
        cyanDtmIntakeTempWarnLowThres    Integer32,
        cyanDtmLedTest    Unsigned32,
        cyanDtmMacBlockSize    Unsigned32,
        cyanDtmMfgCleiCode    DisplayString,
        cyanDtmMfgEciCode    DisplayString,
        cyanDtmMfgModuleId    Unsigned32,
        cyanDtmMfgPartNumber    DisplayString,
        cyanDtmMfgRevision    DisplayString,
        cyanDtmMfgSerialNumber    DisplayString,
        cyanDtmName    DisplayString,
        cyanDtmOidClass    DisplayString,
        cyanDtmOperState    CyanOpStateTc,
        cyanDtmOperStateQual    CyanOpStateQualTc,
        cyanDtmOssLabel    DisplayString,
        cyanDtmOvervoltageThreshold    Integer32,
        cyanDtmOwner    DisplayString,
        cyanDtmPartNumber    DisplayString,
        cyanDtmPowerLed    CyanLEDTc,
        cyanDtmPsuTemperature    Integer32,
        cyanDtmPwrFeedAStatus    CyanOffOnTc,
        cyanDtmPwrFeedAVoltage    Integer32,
        cyanDtmPwrFeedBStatus    CyanOffOnTc,
        cyanDtmPwrFeedBVoltage    Integer32,
        cyanDtmRevertCyanSwBuildVersions    DisplayString,
        cyanDtmRevertCyanSwRelease    DisplayString,
        cyanDtmSecServState    CyanSecServiceStateTc,
        cyanDtmSynchLed    CyanLEDTc,
        cyanDtmType    CyanTypeTc,
        cyanDtmUndervoltageThreshold    Integer32,
        cyanDtmUpgradeCyanSwBuildVersions    DisplayString,
        cyanDtmUpgradeCyanSwRelease    DisplayString
    }

cyanDtmShelfId OBJECT-TYPE
    SYNTAX       Unsigned32 (0..255)
    MAX-ACCESS   not-accessible
    STATUS       current
    DESCRIPTION
        "Shelf Id"

    ::= { cyanDtmEntry 1 }
cyanDtmDtmId OBJECT-TYPE
    SYNTAX       Unsigned32
    MAX-ACCESS   not-accessible
    STATUS       current
    DESCRIPTION
        "Dtm Module Id"

    ::= { cyanDtmEntry 2 }

cyanDtmActiveLed OBJECT-TYPE
    SYNTAX       CyanLEDTc
    MAX-ACCESS   read-only
    STATUS       current
    DESCRIPTION
        "Active LED status"

    ::= { cyanDtmEntry 3 }

cyanDtmActivestandbyState OBJECT-TYPE
    SYNTAX       CyanActvStdbyTc
    MAX-ACCESS   read-only
    STATUS       current
    DESCRIPTION
        "Active/standby state"

    ::= { cyanDtmEntry 4 }

cyanDtmAdminState OBJECT-TYPE
    SYNTAX       CyanAdminStateTc
    MAX-ACCESS   read-only
    STATUS       current
    DESCRIPTION
        "Administrative state"

    ::= { cyanDtmEntry 5 }

cyanDtmAlarmLed OBJECT-TYPE
    SYNTAX       CyanLEDTc
    MAX-ACCESS   read-only
    STATUS       current
    DESCRIPTION
        "Alarm LED status"

    ::= { cyanDtmEntry 6 }

cyanDtmAssetTag OBJECT-TYPE
    SYNTAX       DisplayString (SIZE(0..124))
    MAX-ACCESS   read-only
    STATUS       current
    DESCRIPTION
        "Asset Tag"

    ::= { cyanDtmEntry 7 }

cyanDtmAutoinserviceSoakTimeSec OBJECT-TYPE
    SYNTAX       Integer32
    MAX-ACCESS   read-only
    STATUS       current
    DESCRIPTION
        "Auto-In-Service soak time"

    ::= { cyanDtmEntry 8 }

cyanDtmBaseMacAddress OBJECT-TYPE
    SYNTAX       DisplayString
    MAX-ACCESS   read-only
    STATUS       current
    DESCRIPTION
        "Base MAC address of a range of addresses"

    ::= { cyanDtmEntry 9 }

cyanDtmCurrCyanSwBuildVersions OBJECT-TYPE
    SYNTAX       DisplayString
    MAX-ACCESS   read-only
    STATUS       current
    DESCRIPTION
        "Current Cyan software build versions"

    ::= { cyanDtmEntry 10 }

cyanDtmCurrCyanSwRelease OBJECT-TYPE
    SYNTAX       DisplayString
    MAX-ACCESS   read-only
    STATUS       current
    DESCRIPTION
        "Current Cyan software release"

    ::= { cyanDtmEntry 11 }

cyanDtmCurrent OBJECT-TYPE
    SYNTAX       Integer32 -- real32 * 1000
    MAX-ACCESS   read-only
    STATUS       current
    DESCRIPTION
        "Current Draw"

    ::= { cyanDtmEntry 12 }

cyanDtmDescription OBJECT-TYPE
    SYNTAX       DisplayString (SIZE(0..255))
    MAX-ACCESS   read-only
    STATUS       current
    DESCRIPTION
        "Description"

    ::= { cyanDtmEntry 13 }

cyanDtmExhaustAirTemp OBJECT-TYPE
    SYNTAX       Integer32 (-128000..128000) -- Float value * 1000
    MAX-ACCESS   read-only
    STATUS       current
    DESCRIPTION
        "Exhaust air temperature"

    ::= { cyanDtmEntry 14 }

cyanDtmExhaustTempAlarmHighThres OBJECT-TYPE
    SYNTAX       Integer32 (-128000..128000) -- Float value * 1000
    MAX-ACCESS   read-only
    STATUS       current
    DESCRIPTION
        "High alarm threshold for exhaust air temperature"

    ::= { cyanDtmEntry 15 }

cyanDtmExhaustTempAlarmLowThres OBJECT-TYPE
    SYNTAX       Integer32 (-128000..128000) -- Float value * 1000
    MAX-ACCESS   read-only
    STATUS       current
    DESCRIPTION
        "Low alarm threshold for exhaust air temperature"

    ::= { cyanDtmEntry 16 }

cyanDtmExhaustTempWarnHighThres OBJECT-TYPE
    SYNTAX       Integer32 (-128000..128000) -- Float value * 1000
    MAX-ACCESS   read-only
    STATUS       current
    DESCRIPTION
        "High warning threshold for exhaust air temperature"

    ::= { cyanDtmEntry 17 }

cyanDtmExhaustTempWarnLowThres OBJECT-TYPE
    SYNTAX       Integer32 (-128000..128000) -- Float value * 1000
    MAX-ACCESS   read-only
    STATUS       current
    DESCRIPTION
        "Low warning threshold for exhaust air temperature"

    ::= { cyanDtmEntry 18 }

cyanDtmExpectedTemperatureRise OBJECT-TYPE
    SYNTAX       Integer32 -- Float Value * 1000
    MAX-ACCESS   read-only
    STATUS       current
    DESCRIPTION
        "Expected temperature rise"

    ::= { cyanDtmEntry 19 }

cyanDtmIdentifier OBJECT-TYPE
    SYNTAX       DisplayString
    MAX-ACCESS   read-only
    STATUS       current
    DESCRIPTION
        "string OID"

    ::= { cyanDtmEntry 20 }

cyanDtmIntakeAirTemp OBJECT-TYPE
    SYNTAX       Integer32 (-128000..128000) -- Float value * 1000
    MAX-ACCESS   read-only
    STATUS       current
    DESCRIPTION
        "In-take air temperature"

    ::= { cyanDtmEntry 21 }

cyanDtmIntakeTempAlarmHighThres OBJECT-TYPE
    SYNTAX       Integer32 (-128000..128000) -- Float value * 1000
    MAX-ACCESS   read-only
    STATUS       current
    DESCRIPTION
        "High alarm threshold for in-take air temperature"

    ::= { cyanDtmEntry 22 }

cyanDtmIntakeTempAlarmLowThres OBJECT-TYPE
    SYNTAX       Integer32 (-128000..128000) -- Float value * 1000
    MAX-ACCESS   read-only
    STATUS       current
    DESCRIPTION
        "Low alarm threshold for in-take air temperature"

    ::= { cyanDtmEntry 23 }

cyanDtmIntakeTempWarnHighThres OBJECT-TYPE
    SYNTAX       Integer32 (-128000..128000) -- Float value * 1000
    MAX-ACCESS   read-only
    STATUS       current
    DESCRIPTION
        "High warning threshold for in-take air temperature"

    ::= { cyanDtmEntry 24 }

cyanDtmIntakeTempWarnLowThres OBJECT-TYPE
    SYNTAX       Integer32 (-128000..128000) -- Float value * 1000
    MAX-ACCESS   read-only
    STATUS       current
    DESCRIPTION
        "Low warning threshold for in-take air temperature"

    ::= { cyanDtmEntry 25 }

cyanDtmLedTest OBJECT-TYPE
    SYNTAX       Unsigned32
    MAX-ACCESS   read-only
    STATUS       current
    DESCRIPTION
        "Change value of this attribute to run LED test on this module"

    ::= { cyanDtmEntry 26 }

cyanDtmMacBlockSize OBJECT-TYPE
    SYNTAX       Unsigned32 (0..255)
    MAX-ACCESS   read-only
    STATUS       current
    DESCRIPTION
        "Number of MAC addresses allocated from the base MAC address"

    ::= { cyanDtmEntry 27 }

cyanDtmMfgCleiCode OBJECT-TYPE
    SYNTAX       DisplayString (SIZE(0..10))
    MAX-ACCESS   read-only
    STATUS       current
    DESCRIPTION
        "Common Language Equipment Identifier"

    ::= { cyanDtmEntry 28 }

cyanDtmMfgEciCode OBJECT-TYPE
    SYNTAX       DisplayString (SIZE(0..6))
    MAX-ACCESS   read-only
    STATUS       current
    DESCRIPTION
        "Equipment Catalog Item"

    ::= { cyanDtmEntry 29 }

cyanDtmMfgModuleId OBJECT-TYPE
    SYNTAX       Unsigned32
    MAX-ACCESS   read-only
    STATUS       current
    DESCRIPTION
        "Module ID"

    ::= { cyanDtmEntry 30 }

cyanDtmMfgPartNumber OBJECT-TYPE
    SYNTAX       DisplayString (SIZE(0..16))
    MAX-ACCESS   read-only
    STATUS       current
    DESCRIPTION
        "Manufacturing part number"

    ::= { cyanDtmEntry 31 }

cyanDtmMfgRevision OBJECT-TYPE
    SYNTAX       DisplayString (SIZE(0..4))
    MAX-ACCESS   read-only
    STATUS       current
    DESCRIPTION
        "Mfg revision number"

    ::= { cyanDtmEntry 32 }

cyanDtmMfgSerialNumber OBJECT-TYPE
    SYNTAX       DisplayString (SIZE(0..16))
    MAX-ACCESS   read-only
    STATUS       current
    DESCRIPTION
        "Mfg serial number"

    ::= { cyanDtmEntry 33 }

cyanDtmName OBJECT-TYPE
    SYNTAX       DisplayString
    MAX-ACCESS   read-only
    STATUS       current
    DESCRIPTION
        "Cyan name"

    ::= { cyanDtmEntry 34 }

cyanDtmOidClass OBJECT-TYPE
    SYNTAX       DisplayString
    MAX-ACCESS   read-only
    STATUS       current
    DESCRIPTION
        "OID Class"

    ::= { cyanDtmEntry 35 }

cyanDtmOperState OBJECT-TYPE
    SYNTAX       CyanOpStateTc
    MAX-ACCESS   read-only
    STATUS       current
    DESCRIPTION
        "Primary Operation State"

    ::= { cyanDtmEntry 36 }

cyanDtmOperStateQual OBJECT-TYPE
    SYNTAX       CyanOpStateQualTc
    MAX-ACCESS   read-only
    STATUS       current
    DESCRIPTION
        "Operation state qualifier"

    ::= { cyanDtmEntry 37 }

cyanDtmOssLabel OBJECT-TYPE
    SYNTAX       DisplayString (SIZE(0..80))
    MAX-ACCESS   read-only
    STATUS       current
    DESCRIPTION
        "CyMS label"

    ::= { cyanDtmEntry 38 }

cyanDtmOvervoltageThreshold OBJECT-TYPE
    SYNTAX       Integer32 -- real32 * 1000
    MAX-ACCESS   read-only
    STATUS       current
    DESCRIPTION
        "Over-voltage warning threshold"

    ::= { cyanDtmEntry 39 }

cyanDtmOwner OBJECT-TYPE
    SYNTAX       DisplayString (SIZE(0..80))
    MAX-ACCESS   read-only
    STATUS       current
    DESCRIPTION
        "Owner"

    ::= { cyanDtmEntry 40 }

cyanDtmPartNumber OBJECT-TYPE
    SYNTAX       DisplayString (SIZE(0..11))
    MAX-ACCESS   read-only
    STATUS       current
    DESCRIPTION
        "Cyan part number"

    ::= { cyanDtmEntry 41 }

cyanDtmPowerLed OBJECT-TYPE
    SYNTAX       CyanLEDTc
    MAX-ACCESS   read-only
    STATUS       current
    DESCRIPTION
        "Power LED status"

    ::= { cyanDtmEntry 42 }

cyanDtmPsuTemperature OBJECT-TYPE
    SYNTAX       Integer32 (-25000..85000) -- Float value * 1000
    MAX-ACCESS   read-only
    STATUS       current
    DESCRIPTION
        "Temperature reading in the power supply"

    ::= { cyanDtmEntry 43 }

cyanDtmPwrFeedAStatus OBJECT-TYPE
    SYNTAX       CyanOffOnTc
    MAX-ACCESS   read-only
    STATUS       current
    DESCRIPTION
        "Status of power supply A"

    ::= { cyanDtmEntry 44 }

cyanDtmPwrFeedAVoltage OBJECT-TYPE
    SYNTAX       Integer32 -- real32 * 1000
    MAX-ACCESS   read-only
    STATUS       current
    DESCRIPTION
        "Voltage level of power supply A"

    ::= { cyanDtmEntry 45 }

cyanDtmPwrFeedBStatus OBJECT-TYPE
    SYNTAX       CyanOffOnTc
    MAX-ACCESS   read-only
    STATUS       current
    DESCRIPTION
        "Status of power supply B"

    ::= { cyanDtmEntry 46 }

cyanDtmPwrFeedBVoltage OBJECT-TYPE
    SYNTAX       Integer32 -- real32 * 1000
    MAX-ACCESS   read-only
    STATUS       current
    DESCRIPTION
        "Voltage level of power supply B"

    ::= { cyanDtmEntry 47 }

cyanDtmRevertCyanSwBuildVersions OBJECT-TYPE
    SYNTAX       DisplayString
    MAX-ACCESS   read-only
    STATUS       current
    DESCRIPTION
        "Revert Cyan software build versions"

    ::= { cyanDtmEntry 48 }

cyanDtmRevertCyanSwRelease OBJECT-TYPE
    SYNTAX       DisplayString
    MAX-ACCESS   read-only
    STATUS       current
    DESCRIPTION
        "Revert Cyan software release"

    ::= { cyanDtmEntry 49 }

cyanDtmSecServState OBJECT-TYPE
    SYNTAX       CyanSecServiceStateTc
    MAX-ACCESS   read-only
    STATUS       current
    DESCRIPTION
        "Secondary service state"

    ::= { cyanDtmEntry 50 }

cyanDtmSynchLed OBJECT-TYPE
    SYNTAX       CyanLEDTc
    MAX-ACCESS   read-only
    STATUS       current
    DESCRIPTION
        "Synch LED status"

    ::= { cyanDtmEntry 51 }

cyanDtmType OBJECT-TYPE
    SYNTAX       CyanTypeTc
    MAX-ACCESS   read-only
    STATUS       current
    DESCRIPTION
        "Equipment type"

    ::= { cyanDtmEntry 52 }

cyanDtmUndervoltageThreshold OBJECT-TYPE
    SYNTAX       Integer32 -- real32 * 1000
    MAX-ACCESS   read-only
    STATUS       current
    DESCRIPTION
        "Under-voltage warning threshold"

    ::= { cyanDtmEntry 53 }

cyanDtmUpgradeCyanSwBuildVersions OBJECT-TYPE
    SYNTAX       DisplayString
    MAX-ACCESS   read-only
    STATUS       current
    DESCRIPTION
        "Upgrade Cyan software build versions"

    ::= { cyanDtmEntry 54 }

cyanDtmUpgradeCyanSwRelease OBJECT-TYPE
    SYNTAX       DisplayString
    MAX-ACCESS   read-only
    STATUS       current
    DESCRIPTION
        "Upgrade Cyan software release"

    ::= { cyanDtmEntry 55 }

cyanDtmObjectGroup OBJECT-GROUP
    OBJECTS {
        cyanDtmActiveLed,
        cyanDtmActivestandbyState,
        cyanDtmAdminState,
        cyanDtmAlarmLed,
        cyanDtmAssetTag,
        cyanDtmAutoinserviceSoakTimeSec,
        cyanDtmBaseMacAddress,
        cyanDtmCurrCyanSwBuildVersions,
        cyanDtmCurrCyanSwRelease,
        cyanDtmCurrent,
        cyanDtmDescription,
        cyanDtmExhaustAirTemp,
        cyanDtmExhaustTempAlarmHighThres,
        cyanDtmExhaustTempAlarmLowThres,
        cyanDtmExhaustTempWarnHighThres,
        cyanDtmExhaustTempWarnLowThres,
        cyanDtmExpectedTemperatureRise,
        cyanDtmIdentifier,
        cyanDtmIntakeAirTemp,
        cyanDtmIntakeTempAlarmHighThres,
        cyanDtmIntakeTempAlarmLowThres,
        cyanDtmIntakeTempWarnHighThres,
        cyanDtmIntakeTempWarnLowThres,
        cyanDtmLedTest,
        cyanDtmMacBlockSize,
        cyanDtmMfgCleiCode,
        cyanDtmMfgEciCode,
        cyanDtmMfgModuleId,
        cyanDtmMfgPartNumber,
        cyanDtmMfgRevision,
        cyanDtmMfgSerialNumber,
        cyanDtmName,
        cyanDtmOidClass,
        cyanDtmOperState,
        cyanDtmOperStateQual,
        cyanDtmOssLabel,
        cyanDtmOvervoltageThreshold,
        cyanDtmOwner,
        cyanDtmPartNumber,
        cyanDtmPowerLed,
        cyanDtmPsuTemperature,
        cyanDtmPwrFeedAStatus,
        cyanDtmPwrFeedAVoltage,
        cyanDtmPwrFeedBStatus,
        cyanDtmPwrFeedBVoltage,
        cyanDtmRevertCyanSwBuildVersions,
        cyanDtmRevertCyanSwRelease,
        cyanDtmSecServState,
        cyanDtmSynchLed,
        cyanDtmType,
        cyanDtmUndervoltageThreshold,
        cyanDtmUpgradeCyanSwBuildVersions,
        cyanDtmUpgradeCyanSwRelease
    }

    STATUS current
    DESCRIPTION        "Group of objects that comes with Dtm module"
    ::= {cyanDtmModule 20}

cyanDtmCompliance MODULE-COMPLIANCE
    STATUS current
    DESCRIPTION
        "The basic info needed to be a cyan Dtm"
    MODULE
    MANDATORY-GROUPS {
        cyanDtmObjectGroup
    }
    ::= { cyanDtmModule 30 }


END
