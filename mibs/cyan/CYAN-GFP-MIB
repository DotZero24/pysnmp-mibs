CYAN-GFP-MIB DEFINITIONS ::= BEGIN
IMPORTS
    MODULE-IDENTITY,
    OBJECT-TYPE,
    Integer32,
    Unsigned32
                    FROM SNMPv2-SMI


    CyanSecServiceStateTc,
    CyanOpStateTc,
    CyanGfpUpiTc,
    CyanOpStateQualTc,
    CyanAdminStateTc,
    CyanEnDisabledTc
                    FROM CYAN-TC-MIB

    cyanEntityModules
		    FROM CYAN-MIB

    MODULE-COMPLIANCE,
    OBJECT-GROUP
	            FROM SNMPv2-CONF;


cyanGFPModule MODULE-IDENTITY
    LAST-UPDATED "201412070545Z" -- Sun Dec  7 05:45:29 2014
    ORGANIZATION "Cyan, Inc."
    CONTACT-INFO
        "
        E-mail:  support@cyaninc.com

        Postal:  Cyan, Inc.
               1390 N. McDowell Blvd., # G-327
               Petaluma, CA  94954
               USA

        Tel:     +1-707-735-2300"

    DESCRIPTION    "MIB module for Generic Framing Protocol (GFP)"

    REVISION     "201412070545Z" -- Sun Dec  7 05:45:29 2014
    DESCRIPTION  "Release 6.0 build 1416362081"

    ::= { cyanEntityModules 210 }

cyanGFPMibObjects           OBJECT IDENTIFIER ::={ cyanGFPModule 1 }

cyanGFPTable    OBJECT-TYPE
    SYNTAX        SEQUENCE OF CyanGFPEntry
    MAX-ACCESS    not-accessible
    STATUS        current
    DESCRIPTION
        "A list of GFP entries."
    ::= { cyanGFPMibObjects 1 }

cyanGFPEntry    OBJECT-TYPE
    SYNTAX        CyanGFPEntry
    MAX-ACCESS    not-accessible
    STATUS        current
    DESCRIPTION
        "An entry of GFP."
    INDEX {
        cyanGFPShelfId ,
        cyanGFPModuleId ,
        cyanGFPGFPId
    }
    ::= { cyanGFPTable 1 }

CyanGFPEntry  ::=
    SEQUENCE {
        cyanGFPShelfId    Unsigned32,
        cyanGFPModuleId    Unsigned32,
        cyanGFPGFPId    Unsigned32,
        cyanGFPAcceptedPayloadFcs    Unsigned32,
        cyanGFPAcceptedPayloadType    Unsigned32,
        cyanGFPAcceptedUserPayload    Unsigned32,
        cyanGFPAdminState    CyanAdminStateTc,
        cyanGFPAutoinserviceSoakTimeSec    Integer32,
        cyanGFPClientSignalFail    CyanEnDisabledTc,
        cyanGFPDiscardErrorFrames    CyanEnDisabledTc,
        cyanGFPExpectedUserPayload    CyanGfpUpiTc,
        cyanGFPInsertPayloadFcs    CyanEnDisabledTc,
        cyanGFPInsertedUserPayload    CyanGfpUpiTc,
        cyanGFPOperState    CyanOpStateTc,
        cyanGFPOperStateQual    CyanOpStateQualTc,
        cyanGFPPayloadScrambling    CyanEnDisabledTc,
        cyanGFPSecServState    CyanSecServiceStateTc
    }

cyanGFPShelfId OBJECT-TYPE
    SYNTAX       Unsigned32 (0..255)
    MAX-ACCESS   not-accessible
    STATUS       current
    DESCRIPTION
        "Shelf Id"

    ::= { cyanGFPEntry 1 }
cyanGFPModuleId OBJECT-TYPE
    SYNTAX       Unsigned32
    MAX-ACCESS   not-accessible
    STATUS       current
    DESCRIPTION
        "Module Id"

    ::= { cyanGFPEntry 2 }
cyanGFPGFPId OBJECT-TYPE
    SYNTAX       Unsigned32
    MAX-ACCESS   not-accessible
    STATUS       current
    DESCRIPTION
        "GFP Termination Id"

    ::= { cyanGFPEntry 3 }

cyanGFPAcceptedPayloadFcs OBJECT-TYPE
    SYNTAX       Unsigned32 (0..255)
    MAX-ACCESS   read-only
    STATUS       current
    DESCRIPTION
        "Accepted payload FCS indicator"

    ::= { cyanGFPEntry 4 }

cyanGFPAcceptedPayloadType OBJECT-TYPE
    SYNTAX       Unsigned32 (0..255)
    MAX-ACCESS   read-only
    STATUS       current
    DESCRIPTION
        "Accepted Payload Type identifier"

    ::= { cyanGFPEntry 5 }

cyanGFPAcceptedUserPayload OBJECT-TYPE
    SYNTAX       Unsigned32 (0..255)
    MAX-ACCESS   read-only
    STATUS       current
    DESCRIPTION
        "Accepted User payload identifier"

    ::= { cyanGFPEntry 6 }

cyanGFPAdminState OBJECT-TYPE
    SYNTAX       CyanAdminStateTc
    MAX-ACCESS   read-only
    STATUS       current
    DESCRIPTION
        "Administrative state"

    ::= { cyanGFPEntry 7 }

cyanGFPAutoinserviceSoakTimeSec OBJECT-TYPE
    SYNTAX       Integer32
    MAX-ACCESS   read-only
    STATUS       current
    DESCRIPTION
        "Auto-In-Service soak time"

    ::= { cyanGFPEntry 8 }

cyanGFPClientSignalFail OBJECT-TYPE
    SYNTAX       CyanEnDisabledTc
    MAX-ACCESS   read-only
    STATUS       current
    DESCRIPTION
        "Client Signal Fail"

    ::= { cyanGFPEntry 9 }

cyanGFPDiscardErrorFrames OBJECT-TYPE
    SYNTAX       CyanEnDisabledTc
    MAX-ACCESS   read-only
    STATUS       current
    DESCRIPTION
        "Discard FCS errored frames"

    ::= { cyanGFPEntry 10 }

cyanGFPExpectedUserPayload OBJECT-TYPE
    SYNTAX       CyanGfpUpiTc
    MAX-ACCESS   read-only
    STATUS       current
    DESCRIPTION
        "Expected User payload identifier"

    ::= { cyanGFPEntry 11 }

cyanGFPInsertPayloadFcs OBJECT-TYPE
    SYNTAX       CyanEnDisabledTc
    MAX-ACCESS   read-only
    STATUS       current
    DESCRIPTION
        "Payload FCS generation"

    ::= { cyanGFPEntry 12 }

cyanGFPInsertedUserPayload OBJECT-TYPE
    SYNTAX       CyanGfpUpiTc
    MAX-ACCESS   read-only
    STATUS       current
    DESCRIPTION
        "Inserted User payload identifier"

    ::= { cyanGFPEntry 13 }

cyanGFPOperState OBJECT-TYPE
    SYNTAX       CyanOpStateTc
    MAX-ACCESS   read-only
    STATUS       current
    DESCRIPTION
        "Primary Operation State"

    ::= { cyanGFPEntry 14 }

cyanGFPOperStateQual OBJECT-TYPE
    SYNTAX       CyanOpStateQualTc
    MAX-ACCESS   read-only
    STATUS       current
    DESCRIPTION
        "Operation state qualifier"

    ::= { cyanGFPEntry 15 }

cyanGFPPayloadScrambling OBJECT-TYPE
    SYNTAX       CyanEnDisabledTc
    MAX-ACCESS   read-only
    STATUS       current
    DESCRIPTION
        "Payload scrambling"

    ::= { cyanGFPEntry 16 }

cyanGFPSecServState OBJECT-TYPE
    SYNTAX       CyanSecServiceStateTc
    MAX-ACCESS   read-only
    STATUS       current
    DESCRIPTION
        "Secondary service state"

    ::= { cyanGFPEntry 17 }

cyanGFPObjectGroup OBJECT-GROUP
    OBJECTS {
        cyanGFPAcceptedPayloadFcs,
        cyanGFPAcceptedPayloadType,
        cyanGFPAcceptedUserPayload,
        cyanGFPAdminState,
        cyanGFPAutoinserviceSoakTimeSec,
        cyanGFPClientSignalFail,
        cyanGFPDiscardErrorFrames,
        cyanGFPExpectedUserPayload,
        cyanGFPInsertPayloadFcs,
        cyanGFPInsertedUserPayload,
        cyanGFPOperState,
        cyanGFPOperStateQual,
        cyanGFPPayloadScrambling,
        cyanGFPSecServState
    }

    STATUS current
    DESCRIPTION        "Group of objects that comes with GFP module"
    ::= {cyanGFPModule 20}

cyanGFPCompliance MODULE-COMPLIANCE
    STATUS current
    DESCRIPTION
        "The basic info needed to be a cyan GFP"
    MODULE
    MANDATORY-GROUPS {
        cyanGFPObjectGroup
    }
    ::= { cyanGFPModule 30 }


END
