CYAN-BOSS-MIB DEFINITIONS ::= BEGIN
IMPORTS
    MODULE-IDENTITY,
    OBJECT-TYPE,
    Integer32,
    Unsigned32
                    FROM SNMPv2-SMI

    DisplayString
                    FROM SNMPv2-TC

    CyanLEDTc,
    CyanOffOnTc,
    CyanActvStdbyTc,
    CyanAdminStateTc,
    CyanOpStateQualTc,
    CyanSecServiceStateTc,
    CyanOpStateTc
                    FROM CYAN-TC-MIB

    CyanTypeTc,
    cyanEntityModules
		    FROM CYAN-MIB

    MODULE-COMPLIANCE,
    OBJECT-GROUP
	            FROM SNMPv2-CONF;


cyanBossModule MODULE-IDENTITY
    LAST-UPDATED "201412070545Z" -- Sun Dec  7 05:45:25 2014
    ORGANIZATION "Cyan, Inc."
    CONTACT-INFO
        "
        E-mail:  support@cyaninc.com

        Postal:  Cyan, Inc.
               1390 N. McDowell Blvd., # G-327
               Petaluma, CA  94954
               USA

        Tel:     +1-707-735-2300"

    DESCRIPTION    "MIB module for BOSS"

    REVISION     "201412070545Z" -- Sun Dec  7 05:45:25 2014
    DESCRIPTION  "Release 6.0 build 1416362081"

    ::= { cyanEntityModules 100 }

cyanBossMibObjects           OBJECT IDENTIFIER ::={ cyanBossModule 1 }

cyanBossTable    OBJECT-TYPE
    SYNTAX        SEQUENCE OF CyanBossEntry
    MAX-ACCESS    not-accessible
    STATUS        current
    DESCRIPTION
        "A list of Boss entries."
    ::= { cyanBossMibObjects 1 }

cyanBossEntry    OBJECT-TYPE
    SYNTAX        CyanBossEntry
    MAX-ACCESS    not-accessible
    STATUS        current
    DESCRIPTION
        "An entry of Boss."
    INDEX {
        cyanBossShelfId ,
        cyanBossBossId
    }
    ::= { cyanBossTable 1 }

CyanBossEntry  ::=
    SEQUENCE {
        cyanBossShelfId    Unsigned32,
        cyanBossBossId    Unsigned32,
        cyanBossActiveLed    CyanLEDTc,
        cyanBossActivestandbyState    CyanActvStdbyTc,
        cyanBossAdminState    CyanAdminStateTc,
        cyanBossAlarmLed    CyanLEDTc,
        cyanBossAssetTag    DisplayString,
        cyanBossAutoinserviceSoakTimeSec    Integer32,
        cyanBossBaseMacAddress    DisplayString,
        cyanBossCurrCyanSwBuildVersions    DisplayString,
        cyanBossCurrCyanSwRelease    DisplayString,
        cyanBossCurrent    Integer32,
        cyanBossDescription    DisplayString,
        cyanBossExhaustAirTemp    Integer32,
        cyanBossExhaustTempAlarmHighThres    Integer32,
        cyanBossExhaustTempAlarmLowThres    Integer32,
        cyanBossExhaustTempWarnHighThres    Integer32,
        cyanBossExhaustTempWarnLowThres    Integer32,
        cyanBossExpectedTemperatureRise    Integer32,
        cyanBossIdentifier    DisplayString,
        cyanBossIntakeAirTemp    Integer32,
        cyanBossIntakeTempAlarmHighThres    Integer32,
        cyanBossIntakeTempAlarmLowThres    Integer32,
        cyanBossIntakeTempWarnHighThres    Integer32,
        cyanBossIntakeTempWarnLowThres    Integer32,
        cyanBossLedTest    Unsigned32,
        cyanBossMacBlockSize    Unsigned32,
        cyanBossMfgCleiCode    DisplayString,
        cyanBossMfgEciCode    DisplayString,
        cyanBossMfgModuleId    Unsigned32,
        cyanBossMfgPartNumber    DisplayString,
        cyanBossMfgRevision    DisplayString,
        cyanBossMfgSerialNumber    DisplayString,
        cyanBossName    DisplayString,
        cyanBossOidClass    DisplayString,
        cyanBossOperState    CyanOpStateTc,
        cyanBossOperStateQual    CyanOpStateQualTc,
        cyanBossOssLabel    DisplayString,
        cyanBossOvervoltageThreshold    Integer32,
        cyanBossOwner    DisplayString,
        cyanBossPartNumber    DisplayString,
        cyanBossPowerLed    CyanLEDTc,
        cyanBossPsuTemperature    Integer32,
        cyanBossPwrFeedAStatus    CyanOffOnTc,
        cyanBossPwrFeedAVoltage    Integer32,
        cyanBossPwrFeedBStatus    CyanOffOnTc,
        cyanBossPwrFeedBVoltage    Integer32,
        cyanBossRevertCyanSwBuildVersions    DisplayString,
        cyanBossRevertCyanSwRelease    DisplayString,
        cyanBossSecServState    CyanSecServiceStateTc,
        cyanBossSynchLed    CyanLEDTc,
        cyanBossType    CyanTypeTc,
        cyanBossUndervoltageThreshold    Integer32,
        cyanBossUpgradeCyanSwBuildVersions    DisplayString,
        cyanBossUpgradeCyanSwRelease    DisplayString
    }

cyanBossShelfId OBJECT-TYPE
    SYNTAX       Unsigned32 (0..255)
    MAX-ACCESS   not-accessible
    STATUS       current
    DESCRIPTION
        "Shelf Id"

    ::= { cyanBossEntry 1 }
cyanBossBossId OBJECT-TYPE
    SYNTAX       Unsigned32
    MAX-ACCESS   not-accessible
    STATUS       current
    DESCRIPTION
        "Boss Module Id"

    ::= { cyanBossEntry 2 }

cyanBossActiveLed OBJECT-TYPE
    SYNTAX       CyanLEDTc
    MAX-ACCESS   read-only
    STATUS       current
    DESCRIPTION
        "Active LED status"

    ::= { cyanBossEntry 3 }

cyanBossActivestandbyState OBJECT-TYPE
    SYNTAX       CyanActvStdbyTc
    MAX-ACCESS   read-only
    STATUS       current
    DESCRIPTION
        "Active/standby state"

    ::= { cyanBossEntry 4 }

cyanBossAdminState OBJECT-TYPE
    SYNTAX       CyanAdminStateTc
    MAX-ACCESS   read-only
    STATUS       current
    DESCRIPTION
        "Administrative state"

    ::= { cyanBossEntry 5 }

cyanBossAlarmLed OBJECT-TYPE
    SYNTAX       CyanLEDTc
    MAX-ACCESS   read-only
    STATUS       current
    DESCRIPTION
        "Alarm LED status"

    ::= { cyanBossEntry 6 }

cyanBossAssetTag OBJECT-TYPE
    SYNTAX       DisplayString (SIZE(0..124))
    MAX-ACCESS   read-only
    STATUS       current
    DESCRIPTION
        "Asset Tag"

    ::= { cyanBossEntry 7 }

cyanBossAutoinserviceSoakTimeSec OBJECT-TYPE
    SYNTAX       Integer32
    MAX-ACCESS   read-only
    STATUS       current
    DESCRIPTION
        "Auto-In-Service soak time"

    ::= { cyanBossEntry 8 }

cyanBossBaseMacAddress OBJECT-TYPE
    SYNTAX       DisplayString
    MAX-ACCESS   read-only
    STATUS       current
    DESCRIPTION
        "Base MAC address of a range of addresses"

    ::= { cyanBossEntry 9 }

cyanBossCurrCyanSwBuildVersions OBJECT-TYPE
    SYNTAX       DisplayString
    MAX-ACCESS   read-only
    STATUS       current
    DESCRIPTION
        "Current Cyan software build versions"

    ::= { cyanBossEntry 10 }

cyanBossCurrCyanSwRelease OBJECT-TYPE
    SYNTAX       DisplayString
    MAX-ACCESS   read-only
    STATUS       current
    DESCRIPTION
        "Current Cyan software release"

    ::= { cyanBossEntry 11 }

cyanBossCurrent OBJECT-TYPE
    SYNTAX       Integer32 -- real32 * 1000
    MAX-ACCESS   read-only
    STATUS       current
    DESCRIPTION
        "Current Draw"

    ::= { cyanBossEntry 12 }

cyanBossDescription OBJECT-TYPE
    SYNTAX       DisplayString (SIZE(0..255))
    MAX-ACCESS   read-only
    STATUS       current
    DESCRIPTION
        "Description"

    ::= { cyanBossEntry 13 }

cyanBossExhaustAirTemp OBJECT-TYPE
    SYNTAX       Integer32 (-128000..128000) -- Float value * 1000
    MAX-ACCESS   read-only
    STATUS       current
    DESCRIPTION
        "Exhaust air temperature"

    ::= { cyanBossEntry 14 }

cyanBossExhaustTempAlarmHighThres OBJECT-TYPE
    SYNTAX       Integer32 (-128000..128000) -- Float value * 1000
    MAX-ACCESS   read-only
    STATUS       current
    DESCRIPTION
        "High alarm threshold for exhaust air temperature"

    ::= { cyanBossEntry 15 }

cyanBossExhaustTempAlarmLowThres OBJECT-TYPE
    SYNTAX       Integer32 (-128000..128000) -- Float value * 1000
    MAX-ACCESS   read-only
    STATUS       current
    DESCRIPTION
        "Low alarm threshold for exhaust air temperature"

    ::= { cyanBossEntry 16 }

cyanBossExhaustTempWarnHighThres OBJECT-TYPE
    SYNTAX       Integer32 (-128000..128000) -- Float value * 1000
    MAX-ACCESS   read-only
    STATUS       current
    DESCRIPTION
        "High warning threshold for exhaust air temperature"

    ::= { cyanBossEntry 17 }

cyanBossExhaustTempWarnLowThres OBJECT-TYPE
    SYNTAX       Integer32 (-128000..128000) -- Float value * 1000
    MAX-ACCESS   read-only
    STATUS       current
    DESCRIPTION
        "Low warning threshold for exhaust air temperature"

    ::= { cyanBossEntry 18 }

cyanBossExpectedTemperatureRise OBJECT-TYPE
    SYNTAX       Integer32 -- Float Value * 1000
    MAX-ACCESS   read-only
    STATUS       current
    DESCRIPTION
        "Expected temperature rise"

    ::= { cyanBossEntry 19 }

cyanBossIdentifier OBJECT-TYPE
    SYNTAX       DisplayString
    MAX-ACCESS   read-only
    STATUS       current
    DESCRIPTION
        "string OID"

    ::= { cyanBossEntry 20 }

cyanBossIntakeAirTemp OBJECT-TYPE
    SYNTAX       Integer32 (-128000..128000) -- Float value * 1000
    MAX-ACCESS   read-only
    STATUS       current
    DESCRIPTION
        "In-take air temperature"

    ::= { cyanBossEntry 21 }

cyanBossIntakeTempAlarmHighThres OBJECT-TYPE
    SYNTAX       Integer32 (-128000..128000) -- Float value * 1000
    MAX-ACCESS   read-only
    STATUS       current
    DESCRIPTION
        "High alarm threshold for in-take air temperature"

    ::= { cyanBossEntry 22 }

cyanBossIntakeTempAlarmLowThres OBJECT-TYPE
    SYNTAX       Integer32 (-128000..128000) -- Float value * 1000
    MAX-ACCESS   read-only
    STATUS       current
    DESCRIPTION
        "Low alarm threshold for in-take air temperature"

    ::= { cyanBossEntry 23 }

cyanBossIntakeTempWarnHighThres OBJECT-TYPE
    SYNTAX       Integer32 (-128000..128000) -- Float value * 1000
    MAX-ACCESS   read-only
    STATUS       current
    DESCRIPTION
        "High warning threshold for in-take air temperature"

    ::= { cyanBossEntry 24 }

cyanBossIntakeTempWarnLowThres OBJECT-TYPE
    SYNTAX       Integer32 (-128000..128000) -- Float value * 1000
    MAX-ACCESS   read-only
    STATUS       current
    DESCRIPTION
        "Low warning threshold for in-take air temperature"

    ::= { cyanBossEntry 25 }

cyanBossLedTest OBJECT-TYPE
    SYNTAX       Unsigned32
    MAX-ACCESS   read-only
    STATUS       current
    DESCRIPTION
        "Change value of this attribute to run LED test on this module"

    ::= { cyanBossEntry 26 }

cyanBossMacBlockSize OBJECT-TYPE
    SYNTAX       Unsigned32 (0..255)
    MAX-ACCESS   read-only
    STATUS       current
    DESCRIPTION
        "Number of MAC addresses allocated from the base MAC address"

    ::= { cyanBossEntry 27 }

cyanBossMfgCleiCode OBJECT-TYPE
    SYNTAX       DisplayString (SIZE(0..10))
    MAX-ACCESS   read-only
    STATUS       current
    DESCRIPTION
        "Common Language Equipment Identifier"

    ::= { cyanBossEntry 28 }

cyanBossMfgEciCode OBJECT-TYPE
    SYNTAX       DisplayString (SIZE(0..6))
    MAX-ACCESS   read-only
    STATUS       current
    DESCRIPTION
        "Equipment Catalog Item"

    ::= { cyanBossEntry 29 }

cyanBossMfgModuleId OBJECT-TYPE
    SYNTAX       Unsigned32
    MAX-ACCESS   read-only
    STATUS       current
    DESCRIPTION
        "Module ID"

    ::= { cyanBossEntry 30 }

cyanBossMfgPartNumber OBJECT-TYPE
    SYNTAX       DisplayString (SIZE(0..16))
    MAX-ACCESS   read-only
    STATUS       current
    DESCRIPTION
        "Manufacturing part number"

    ::= { cyanBossEntry 31 }

cyanBossMfgRevision OBJECT-TYPE
    SYNTAX       DisplayString (SIZE(0..4))
    MAX-ACCESS   read-only
    STATUS       current
    DESCRIPTION
        "Mfg revision number"

    ::= { cyanBossEntry 32 }

cyanBossMfgSerialNumber OBJECT-TYPE
    SYNTAX       DisplayString (SIZE(0..16))
    MAX-ACCESS   read-only
    STATUS       current
    DESCRIPTION
        "Mfg serial number"

    ::= { cyanBossEntry 33 }

cyanBossName OBJECT-TYPE
    SYNTAX       DisplayString
    MAX-ACCESS   read-only
    STATUS       current
    DESCRIPTION
        "Cyan name"

    ::= { cyanBossEntry 34 }

cyanBossOidClass OBJECT-TYPE
    SYNTAX       DisplayString
    MAX-ACCESS   read-only
    STATUS       current
    DESCRIPTION
        "OID Class"

    ::= { cyanBossEntry 35 }

cyanBossOperState OBJECT-TYPE
    SYNTAX       CyanOpStateTc
    MAX-ACCESS   read-only
    STATUS       current
    DESCRIPTION
        "Primary Operation State"

    ::= { cyanBossEntry 36 }

cyanBossOperStateQual OBJECT-TYPE
    SYNTAX       CyanOpStateQualTc
    MAX-ACCESS   read-only
    STATUS       current
    DESCRIPTION
        "Operation state qualifier"

    ::= { cyanBossEntry 37 }

cyanBossOssLabel OBJECT-TYPE
    SYNTAX       DisplayString (SIZE(0..80))
    MAX-ACCESS   read-only
    STATUS       current
    DESCRIPTION
        "CyMS label"

    ::= { cyanBossEntry 38 }

cyanBossOvervoltageThreshold OBJECT-TYPE
    SYNTAX       Integer32 -- real32 * 1000
    MAX-ACCESS   read-only
    STATUS       current
    DESCRIPTION
        "Over-voltage warning threshold"

    ::= { cyanBossEntry 39 }

cyanBossOwner OBJECT-TYPE
    SYNTAX       DisplayString (SIZE(0..80))
    MAX-ACCESS   read-only
    STATUS       current
    DESCRIPTION
        "Owner"

    ::= { cyanBossEntry 40 }

cyanBossPartNumber OBJECT-TYPE
    SYNTAX       DisplayString (SIZE(0..11))
    MAX-ACCESS   read-only
    STATUS       current
    DESCRIPTION
        "Cyan part number"

    ::= { cyanBossEntry 41 }

cyanBossPowerLed OBJECT-TYPE
    SYNTAX       CyanLEDTc
    MAX-ACCESS   read-only
    STATUS       current
    DESCRIPTION
        "Power LED status"

    ::= { cyanBossEntry 42 }

cyanBossPsuTemperature OBJECT-TYPE
    SYNTAX       Integer32 (-25000..85000) -- Float value * 1000
    MAX-ACCESS   read-only
    STATUS       current
    DESCRIPTION
        "Temperature reading in the power supply"

    ::= { cyanBossEntry 43 }

cyanBossPwrFeedAStatus OBJECT-TYPE
    SYNTAX       CyanOffOnTc
    MAX-ACCESS   read-only
    STATUS       current
    DESCRIPTION
        "Status of power supply A"

    ::= { cyanBossEntry 44 }

cyanBossPwrFeedAVoltage OBJECT-TYPE
    SYNTAX       Integer32 -- real32 * 1000
    MAX-ACCESS   read-only
    STATUS       current
    DESCRIPTION
        "Voltage level of power supply A"

    ::= { cyanBossEntry 45 }

cyanBossPwrFeedBStatus OBJECT-TYPE
    SYNTAX       CyanOffOnTc
    MAX-ACCESS   read-only
    STATUS       current
    DESCRIPTION
        "Status of power supply B"

    ::= { cyanBossEntry 46 }

cyanBossPwrFeedBVoltage OBJECT-TYPE
    SYNTAX       Integer32 -- real32 * 1000
    MAX-ACCESS   read-only
    STATUS       current
    DESCRIPTION
        "Voltage level of power supply B"

    ::= { cyanBossEntry 47 }

cyanBossRevertCyanSwBuildVersions OBJECT-TYPE
    SYNTAX       DisplayString
    MAX-ACCESS   read-only
    STATUS       current
    DESCRIPTION
        "Revert Cyan software build versions"

    ::= { cyanBossEntry 48 }

cyanBossRevertCyanSwRelease OBJECT-TYPE
    SYNTAX       DisplayString
    MAX-ACCESS   read-only
    STATUS       current
    DESCRIPTION
        "Revert Cyan software release"

    ::= { cyanBossEntry 49 }

cyanBossSecServState OBJECT-TYPE
    SYNTAX       CyanSecServiceStateTc
    MAX-ACCESS   read-only
    STATUS       current
    DESCRIPTION
        "Secondary service state"

    ::= { cyanBossEntry 50 }

cyanBossSynchLed OBJECT-TYPE
    SYNTAX       CyanLEDTc
    MAX-ACCESS   read-only
    STATUS       current
    DESCRIPTION
        "Synch LED status"

    ::= { cyanBossEntry 51 }

cyanBossType OBJECT-TYPE
    SYNTAX       CyanTypeTc
    MAX-ACCESS   read-only
    STATUS       current
    DESCRIPTION
        "Equipment type"

    ::= { cyanBossEntry 52 }

cyanBossUndervoltageThreshold OBJECT-TYPE
    SYNTAX       Integer32 -- real32 * 1000
    MAX-ACCESS   read-only
    STATUS       current
    DESCRIPTION
        "Under-voltage warning threshold"

    ::= { cyanBossEntry 53 }

cyanBossUpgradeCyanSwBuildVersions OBJECT-TYPE
    SYNTAX       DisplayString
    MAX-ACCESS   read-only
    STATUS       current
    DESCRIPTION
        "Upgrade Cyan software build versions"

    ::= { cyanBossEntry 54 }

cyanBossUpgradeCyanSwRelease OBJECT-TYPE
    SYNTAX       DisplayString
    MAX-ACCESS   read-only
    STATUS       current
    DESCRIPTION
        "Upgrade Cyan software release"

    ::= { cyanBossEntry 55 }

cyanBossObjectGroup OBJECT-GROUP
    OBJECTS {
        cyanBossActiveLed,
        cyanBossActivestandbyState,
        cyanBossAdminState,
        cyanBossAlarmLed,
        cyanBossAssetTag,
        cyanBossAutoinserviceSoakTimeSec,
        cyanBossBaseMacAddress,
        cyanBossCurrCyanSwBuildVersions,
        cyanBossCurrCyanSwRelease,
        cyanBossCurrent,
        cyanBossDescription,
        cyanBossExhaustAirTemp,
        cyanBossExhaustTempAlarmHighThres,
        cyanBossExhaustTempAlarmLowThres,
        cyanBossExhaustTempWarnHighThres,
        cyanBossExhaustTempWarnLowThres,
        cyanBossExpectedTemperatureRise,
        cyanBossIdentifier,
        cyanBossIntakeAirTemp,
        cyanBossIntakeTempAlarmHighThres,
        cyanBossIntakeTempAlarmLowThres,
        cyanBossIntakeTempWarnHighThres,
        cyanBossIntakeTempWarnLowThres,
        cyanBossLedTest,
        cyanBossMacBlockSize,
        cyanBossMfgCleiCode,
        cyanBossMfgEciCode,
        cyanBossMfgModuleId,
        cyanBossMfgPartNumber,
        cyanBossMfgRevision,
        cyanBossMfgSerialNumber,
        cyanBossName,
        cyanBossOidClass,
        cyanBossOperState,
        cyanBossOperStateQual,
        cyanBossOssLabel,
        cyanBossOvervoltageThreshold,
        cyanBossOwner,
        cyanBossPartNumber,
        cyanBossPowerLed,
        cyanBossPsuTemperature,
        cyanBossPwrFeedAStatus,
        cyanBossPwrFeedAVoltage,
        cyanBossPwrFeedBStatus,
        cyanBossPwrFeedBVoltage,
        cyanBossRevertCyanSwBuildVersions,
        cyanBossRevertCyanSwRelease,
        cyanBossSecServState,
        cyanBossSynchLed,
        cyanBossType,
        cyanBossUndervoltageThreshold,
        cyanBossUpgradeCyanSwBuildVersions,
        cyanBossUpgradeCyanSwRelease
    }

    STATUS current
    DESCRIPTION        "Group of objects that comes with Boss module"
    ::= {cyanBossModule 20}

cyanBossCompliance MODULE-COMPLIANCE
    STATUS current
    DESCRIPTION
        "The basic info needed to be a cyan Boss"
    MODULE
    MANDATORY-GROUPS {
        cyanBossObjectGroup
    }
    ::= { cyanBossModule 30 }


END
