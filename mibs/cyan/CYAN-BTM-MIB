CYAN-BTM-MIB DEFINITIONS ::= BEGIN
IMPORTS
    MODULE-IDENTITY,
    OBJECT-TYPE,
    Integer32,
    Unsigned32
                    FROM SNMPv2-SMI

    DisplayString
                    FROM SNMPv2-TC

    CyanRelayTc,
    CyanAdminStateTc,
    CyanOpStateQualTc,
    CyanOpStateTc,
    CyanSecServiceStateTc
                    FROM CYAN-TC-MIB

    CyanTypeTc,
    cyanEntityModules
		    FROM CYAN-MIB

    MODULE-COMPLIANCE,
    OBJECT-GROUP
	            FROM SNMPv2-CONF;


cyanBtmModule MODULE-IDENTITY
    LAST-UPDATED "201412070545Z" -- Sun Dec  7 05:45:30 2014
    ORGANIZATION "Cyan, Inc."
    CONTACT-INFO
        "
        E-mail:  support@cyaninc.com

        Postal:  Cyan, Inc.
               1390 N. McDowell Blvd., # G-327
               Petaluma, CA  94954
               USA

        Tel:     +1-707-735-2300"

    DESCRIPTION    "MIB module for BOSS Termination Module"

    REVISION     "201412070545Z" -- Sun Dec  7 05:45:30 2014
    DESCRIPTION  "Release 6.0 build 1416362081"

    ::= { cyanEntityModules 60 }

cyanBtmMibObjects           OBJECT IDENTIFIER ::={ cyanBtmModule 1 }

cyanBtmTable    OBJECT-TYPE
    SYNTAX        SEQUENCE OF CyanBtmEntry
    MAX-ACCESS    not-accessible
    STATUS        current
    DESCRIPTION
        "A list of Btm entries."
    ::= { cyanBtmMibObjects 1 }

cyanBtmEntry    OBJECT-TYPE
    SYNTAX        CyanBtmEntry
    MAX-ACCESS    not-accessible
    STATUS        current
    DESCRIPTION
        "An entry of Btm."
    INDEX {
        cyanBtmShelfId ,
        cyanBtmBtmId
    }
    ::= { cyanBtmTable 1 }

CyanBtmEntry  ::=
    SEQUENCE {
        cyanBtmShelfId    Unsigned32,
        cyanBtmBtmId    Unsigned32,
        cyanBtmAdminState    CyanAdminStateTc,
        cyanBtmAssetTag    DisplayString,
        cyanBtmAudible    CyanRelayTc,
        cyanBtmAutoinserviceSoakTimeSec    Integer32,
        cyanBtmBaseMacAddress    DisplayString,
        cyanBtmCritical    CyanRelayTc,
        cyanBtmDescription    DisplayString,
        cyanBtmIdentifier    DisplayString,
        cyanBtmMacBlockSize    Unsigned32,
        cyanBtmMajor    CyanRelayTc,
        cyanBtmMfgCleiCode    DisplayString,
        cyanBtmMfgEciCode    DisplayString,
        cyanBtmMfgModuleId    Unsigned32,
        cyanBtmMfgPartNumber    DisplayString,
        cyanBtmMfgRevision    DisplayString,
        cyanBtmMfgSerialNumber    DisplayString,
        cyanBtmMinor    CyanRelayTc,
        cyanBtmName    DisplayString,
        cyanBtmOidClass    DisplayString,
        cyanBtmOperState    CyanOpStateTc,
        cyanBtmOperStateQual    CyanOpStateQualTc,
        cyanBtmOssLabel    DisplayString,
        cyanBtmOwner    DisplayString,
        cyanBtmPartNumber    DisplayString,
        cyanBtmSecServState    CyanSecServiceStateTc,
        cyanBtmType    CyanTypeTc
    }

cyanBtmShelfId OBJECT-TYPE
    SYNTAX       Unsigned32 (0..255)
    MAX-ACCESS   not-accessible
    STATUS       current
    DESCRIPTION
        "Shelf Id"

    ::= { cyanBtmEntry 1 }
cyanBtmBtmId OBJECT-TYPE
    SYNTAX       Unsigned32
    MAX-ACCESS   not-accessible
    STATUS       current
    DESCRIPTION
        "BTM Module Id"

    ::= { cyanBtmEntry 2 }

cyanBtmAdminState OBJECT-TYPE
    SYNTAX       CyanAdminStateTc
    MAX-ACCESS   read-only
    STATUS       current
    DESCRIPTION
        "Administrative state"

    ::= { cyanBtmEntry 3 }

cyanBtmAssetTag OBJECT-TYPE
    SYNTAX       DisplayString (SIZE(0..124))
    MAX-ACCESS   read-only
    STATUS       current
    DESCRIPTION
        "Asset Tag"

    ::= { cyanBtmEntry 4 }

cyanBtmAudible OBJECT-TYPE
    SYNTAX       CyanRelayTc
    MAX-ACCESS   read-only
    STATUS       current
    DESCRIPTION
        "System closes this control upon Critical/Major/Minor alarms"

    ::= { cyanBtmEntry 5 }

cyanBtmAutoinserviceSoakTimeSec OBJECT-TYPE
    SYNTAX       Integer32
    MAX-ACCESS   read-only
    STATUS       current
    DESCRIPTION
        "Auto-In-Service soak time"

    ::= { cyanBtmEntry 6 }

cyanBtmBaseMacAddress OBJECT-TYPE
    SYNTAX       DisplayString
    MAX-ACCESS   read-only
    STATUS       current
    DESCRIPTION
        "Base MAC address of a range of addresses"

    ::= { cyanBtmEntry 7 }

cyanBtmCritical OBJECT-TYPE
    SYNTAX       CyanRelayTc
    MAX-ACCESS   read-only
    STATUS       current
    DESCRIPTION
        "System closes this control upon Critical alarms"

    ::= { cyanBtmEntry 8 }

cyanBtmDescription OBJECT-TYPE
    SYNTAX       DisplayString (SIZE(0..255))
    MAX-ACCESS   read-only
    STATUS       current
    DESCRIPTION
        "Description"

    ::= { cyanBtmEntry 9 }

cyanBtmIdentifier OBJECT-TYPE
    SYNTAX       DisplayString
    MAX-ACCESS   read-only
    STATUS       current
    DESCRIPTION
        "string OID"

    ::= { cyanBtmEntry 10 }

cyanBtmMacBlockSize OBJECT-TYPE
    SYNTAX       Unsigned32 (0..255)
    MAX-ACCESS   read-only
    STATUS       current
    DESCRIPTION
        "Number of MAC addresses allocated from the base MAC address"

    ::= { cyanBtmEntry 11 }

cyanBtmMajor OBJECT-TYPE
    SYNTAX       CyanRelayTc
    MAX-ACCESS   read-only
    STATUS       current
    DESCRIPTION
        "System closes this control upon Major alarms"

    ::= { cyanBtmEntry 12 }

cyanBtmMfgCleiCode OBJECT-TYPE
    SYNTAX       DisplayString (SIZE(0..10))
    MAX-ACCESS   read-only
    STATUS       current
    DESCRIPTION
        "Common Language Equipment Identifier"

    ::= { cyanBtmEntry 13 }

cyanBtmMfgEciCode OBJECT-TYPE
    SYNTAX       DisplayString (SIZE(0..6))
    MAX-ACCESS   read-only
    STATUS       current
    DESCRIPTION
        "Equipment Catalog Item"

    ::= { cyanBtmEntry 14 }

cyanBtmMfgModuleId OBJECT-TYPE
    SYNTAX       Unsigned32
    MAX-ACCESS   read-only
    STATUS       current
    DESCRIPTION
        "Module ID"

    ::= { cyanBtmEntry 15 }

cyanBtmMfgPartNumber OBJECT-TYPE
    SYNTAX       DisplayString (SIZE(0..16))
    MAX-ACCESS   read-only
    STATUS       current
    DESCRIPTION
        "Manufacturing part number"

    ::= { cyanBtmEntry 16 }

cyanBtmMfgRevision OBJECT-TYPE
    SYNTAX       DisplayString (SIZE(0..4))
    MAX-ACCESS   read-only
    STATUS       current
    DESCRIPTION
        "Mfg revision number"

    ::= { cyanBtmEntry 17 }

cyanBtmMfgSerialNumber OBJECT-TYPE
    SYNTAX       DisplayString (SIZE(0..16))
    MAX-ACCESS   read-only
    STATUS       current
    DESCRIPTION
        "Mfg serial number"

    ::= { cyanBtmEntry 18 }

cyanBtmMinor OBJECT-TYPE
    SYNTAX       CyanRelayTc
    MAX-ACCESS   read-only
    STATUS       current
    DESCRIPTION
        "System closes this control upon Minor alarms"

    ::= { cyanBtmEntry 19 }

cyanBtmName OBJECT-TYPE
    SYNTAX       DisplayString
    MAX-ACCESS   read-only
    STATUS       current
    DESCRIPTION
        "Cyan name"

    ::= { cyanBtmEntry 20 }

cyanBtmOidClass OBJECT-TYPE
    SYNTAX       DisplayString
    MAX-ACCESS   read-only
    STATUS       current
    DESCRIPTION
        "OID Class"

    ::= { cyanBtmEntry 21 }

cyanBtmOperState OBJECT-TYPE
    SYNTAX       CyanOpStateTc
    MAX-ACCESS   read-only
    STATUS       current
    DESCRIPTION
        "Primary Operation State"

    ::= { cyanBtmEntry 22 }

cyanBtmOperStateQual OBJECT-TYPE
    SYNTAX       CyanOpStateQualTc
    MAX-ACCESS   read-only
    STATUS       current
    DESCRIPTION
        "Operation state qualifier"

    ::= { cyanBtmEntry 23 }

cyanBtmOssLabel OBJECT-TYPE
    SYNTAX       DisplayString (SIZE(0..80))
    MAX-ACCESS   read-only
    STATUS       current
    DESCRIPTION
        "CyMS label"

    ::= { cyanBtmEntry 24 }

cyanBtmOwner OBJECT-TYPE
    SYNTAX       DisplayString (SIZE(0..80))
    MAX-ACCESS   read-only
    STATUS       current
    DESCRIPTION
        "Owner"

    ::= { cyanBtmEntry 25 }

cyanBtmPartNumber OBJECT-TYPE
    SYNTAX       DisplayString (SIZE(0..11))
    MAX-ACCESS   read-only
    STATUS       current
    DESCRIPTION
        "Cyan part number"

    ::= { cyanBtmEntry 26 }

cyanBtmSecServState OBJECT-TYPE
    SYNTAX       CyanSecServiceStateTc
    MAX-ACCESS   read-only
    STATUS       current
    DESCRIPTION
        "Secondary service state"

    ::= { cyanBtmEntry 27 }

cyanBtmType OBJECT-TYPE
    SYNTAX       CyanTypeTc
    MAX-ACCESS   read-only
    STATUS       current
    DESCRIPTION
        "Equipment type"

    ::= { cyanBtmEntry 28 }

cyanBtmObjectGroup OBJECT-GROUP
    OBJECTS {
        cyanBtmAdminState,
        cyanBtmAssetTag,
        cyanBtmAudible,
        cyanBtmAutoinserviceSoakTimeSec,
        cyanBtmBaseMacAddress,
        cyanBtmCritical,
        cyanBtmDescription,
        cyanBtmIdentifier,
        cyanBtmMacBlockSize,
        cyanBtmMajor,
        cyanBtmMfgCleiCode,
        cyanBtmMfgEciCode,
        cyanBtmMfgModuleId,
        cyanBtmMfgPartNumber,
        cyanBtmMfgRevision,
        cyanBtmMfgSerialNumber,
        cyanBtmMinor,
        cyanBtmName,
        cyanBtmOidClass,
        cyanBtmOperState,
        cyanBtmOperStateQual,
        cyanBtmOssLabel,
        cyanBtmOwner,
        cyanBtmPartNumber,
        cyanBtmSecServState,
        cyanBtmType
    }

    STATUS current
    DESCRIPTION        "Group of objects that comes with Btm module"
    ::= {cyanBtmModule 20}

cyanBtmCompliance MODULE-COMPLIANCE
    STATUS current
    DESCRIPTION
        "The basic info needed to be a cyan Btm"
    MODULE
    MANDATORY-GROUPS {
        cyanBtmObjectGroup
    }
    ::= { cyanBtmModule 30 }


END
