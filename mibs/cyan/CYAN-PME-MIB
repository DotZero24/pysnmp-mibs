CYAN-PME-MIB DEFINITIONS ::= BEGIN
IMPORTS
    MODULE-IDENTITY,
    OBJECT-TYPE,
    Integer32,
    Unsigned32
                    FROM SNMPv2-SMI

    DisplayString
                    FROM SNMPv2-TC

    CyanLEDTc,
    CyanOffOnTc,
    CyanActvStdbyTc,
    CyanAdminStateTc,
    CyanOpStateQualTc,
    CyanSecServiceStateTc,
    CyanOpStateTc
                    FROM CYAN-TC-MIB

    CyanTypeTc,
    cyanEntityModules
		    FROM CYAN-MIB

    MODULE-COMPLIANCE,
    OBJECT-GROUP
	            FROM SNMPv2-CONF;


cyanPmeModule MODULE-IDENTITY
    LAST-UPDATED "201412070545Z" -- Sun Dec  7 05:45:29 2014
    ORGANIZATION "Cyan, Inc."
    CONTACT-INFO
        "
        E-mail:  support@cyaninc.com

        Postal:  Cyan, Inc.
               1390 N. McDowell Blvd., # G-327
               Petaluma, CA  94954
               USA

        Tel:     +1-707-735-2300"

    DESCRIPTION    "MIB module for Packet Multiplexer Element(PME)"

    REVISION     "201412070545Z" -- Sun Dec  7 05:45:29 2014
    DESCRIPTION  "Release 6.0 build 1416362081"

    ::= { cyanEntityModules 110 }

cyanPmeMibObjects           OBJECT IDENTIFIER ::={ cyanPmeModule 1 }

cyanPmeTable    OBJECT-TYPE
    SYNTAX        SEQUENCE OF CyanPmeEntry
    MAX-ACCESS    not-accessible
    STATUS        current
    DESCRIPTION
        "A list of Pme entries."
    ::= { cyanPmeMibObjects 1 }

cyanPmeEntry    OBJECT-TYPE
    SYNTAX        CyanPmeEntry
    MAX-ACCESS    not-accessible
    STATUS        current
    DESCRIPTION
        "An entry of Pme."
    INDEX {
        cyanPmeShelfId ,
        cyanPmePmeId
    }
    ::= { cyanPmeTable 1 }

CyanPmeEntry  ::=
    SEQUENCE {
        cyanPmeShelfId    Unsigned32,
        cyanPmePmeId    Unsigned32,
        cyanPmeActiveLed    CyanLEDTc,
        cyanPmeActivestandbyState    CyanActvStdbyTc,
        cyanPmeAdminState    CyanAdminStateTc,
        cyanPmeAlarmLed    CyanLEDTc,
        cyanPmeAssetTag    DisplayString,
        cyanPmeAutoinserviceSoakTimeSec    Integer32,
        cyanPmeBaseMacAddress    DisplayString,
        cyanPmeCurrCyanSwBuildVersions    DisplayString,
        cyanPmeCurrCyanSwRelease    DisplayString,
        cyanPmeCurrent    Integer32,
        cyanPmeDescription    DisplayString,
        cyanPmeExhaustAirTemp    Integer32,
        cyanPmeExhaustTempAlarmHighThres    Integer32,
        cyanPmeExhaustTempAlarmLowThres    Integer32,
        cyanPmeExhaustTempWarnHighThres    Integer32,
        cyanPmeExhaustTempWarnLowThres    Integer32,
        cyanPmeExpectedTemperatureRise    Integer32,
        cyanPmeIdentifier    DisplayString,
        cyanPmeIntakeAirTemp    Integer32,
        cyanPmeIntakeTempAlarmHighThres    Integer32,
        cyanPmeIntakeTempAlarmLowThres    Integer32,
        cyanPmeIntakeTempWarnHighThres    Integer32,
        cyanPmeIntakeTempWarnLowThres    Integer32,
        cyanPmeLedTest    Unsigned32,
        cyanPmeMacBlockSize    Unsigned32,
        cyanPmeMfgCleiCode    DisplayString,
        cyanPmeMfgEciCode    DisplayString,
        cyanPmeMfgModuleId    Unsigned32,
        cyanPmeMfgPartNumber    DisplayString,
        cyanPmeMfgRevision    DisplayString,
        cyanPmeMfgSerialNumber    DisplayString,
        cyanPmeName    DisplayString,
        cyanPmeOidClass    DisplayString,
        cyanPmeOperState    CyanOpStateTc,
        cyanPmeOperStateQual    CyanOpStateQualTc,
        cyanPmeOssLabel    DisplayString,
        cyanPmeOvervoltageThreshold    Integer32,
        cyanPmeOwner    DisplayString,
        cyanPmePartNumber    DisplayString,
        cyanPmePowerLed    CyanLEDTc,
        cyanPmePsuTemperature    Integer32,
        cyanPmePwrFeedAStatus    CyanOffOnTc,
        cyanPmePwrFeedAVoltage    Integer32,
        cyanPmePwrFeedBStatus    CyanOffOnTc,
        cyanPmePwrFeedBVoltage    Integer32,
        cyanPmeResendEthlinkoamPdus    Unsigned32,
        cyanPmeRevertCyanSwBuildVersions    DisplayString,
        cyanPmeRevertCyanSwRelease    DisplayString,
        cyanPmeSecServState    CyanSecServiceStateTc,
        cyanPmeSynchLed    CyanLEDTc,
        cyanPmeType    CyanTypeTc,
        cyanPmeUndervoltageThreshold    Integer32,
        cyanPmeUpgradeCyanSwBuildVersions    DisplayString,
        cyanPmeUpgradeCyanSwRelease    DisplayString
    }

cyanPmeShelfId OBJECT-TYPE
    SYNTAX       Unsigned32 (0..255)
    MAX-ACCESS   not-accessible
    STATUS       current
    DESCRIPTION
        "Shelf Id"

    ::= { cyanPmeEntry 1 }
cyanPmePmeId OBJECT-TYPE
    SYNTAX       Unsigned32
    MAX-ACCESS   not-accessible
    STATUS       current
    DESCRIPTION
        "PME Module Id"

    ::= { cyanPmeEntry 2 }

cyanPmeActiveLed OBJECT-TYPE
    SYNTAX       CyanLEDTc
    MAX-ACCESS   read-only
    STATUS       current
    DESCRIPTION
        "Active LED status"

    ::= { cyanPmeEntry 3 }

cyanPmeActivestandbyState OBJECT-TYPE
    SYNTAX       CyanActvStdbyTc
    MAX-ACCESS   read-only
    STATUS       current
    DESCRIPTION
        "Active/standby state"

    ::= { cyanPmeEntry 4 }

cyanPmeAdminState OBJECT-TYPE
    SYNTAX       CyanAdminStateTc
    MAX-ACCESS   read-only
    STATUS       current
    DESCRIPTION
        "Administrative state"

    ::= { cyanPmeEntry 5 }

cyanPmeAlarmLed OBJECT-TYPE
    SYNTAX       CyanLEDTc
    MAX-ACCESS   read-only
    STATUS       current
    DESCRIPTION
        "Alarm LED status"

    ::= { cyanPmeEntry 6 }

cyanPmeAssetTag OBJECT-TYPE
    SYNTAX       DisplayString (SIZE(0..124))
    MAX-ACCESS   read-only
    STATUS       current
    DESCRIPTION
        "Asset Tag"

    ::= { cyanPmeEntry 7 }

cyanPmeAutoinserviceSoakTimeSec OBJECT-TYPE
    SYNTAX       Integer32
    MAX-ACCESS   read-only
    STATUS       current
    DESCRIPTION
        "Auto-In-Service soak time"

    ::= { cyanPmeEntry 8 }

cyanPmeBaseMacAddress OBJECT-TYPE
    SYNTAX       DisplayString
    MAX-ACCESS   read-only
    STATUS       current
    DESCRIPTION
        "Base MAC address of a range of addresses"

    ::= { cyanPmeEntry 9 }

cyanPmeCurrCyanSwBuildVersions OBJECT-TYPE
    SYNTAX       DisplayString
    MAX-ACCESS   read-only
    STATUS       current
    DESCRIPTION
        "Current Cyan software build versions"

    ::= { cyanPmeEntry 10 }

cyanPmeCurrCyanSwRelease OBJECT-TYPE
    SYNTAX       DisplayString
    MAX-ACCESS   read-only
    STATUS       current
    DESCRIPTION
        "Current Cyan software release"

    ::= { cyanPmeEntry 11 }

cyanPmeCurrent OBJECT-TYPE
    SYNTAX       Integer32 -- real32 * 1000
    MAX-ACCESS   read-only
    STATUS       current
    DESCRIPTION
        "Current Draw"

    ::= { cyanPmeEntry 12 }

cyanPmeDescription OBJECT-TYPE
    SYNTAX       DisplayString (SIZE(0..255))
    MAX-ACCESS   read-only
    STATUS       current
    DESCRIPTION
        "Description"

    ::= { cyanPmeEntry 13 }

cyanPmeExhaustAirTemp OBJECT-TYPE
    SYNTAX       Integer32 (-128000..128000) -- Float value * 1000
    MAX-ACCESS   read-only
    STATUS       current
    DESCRIPTION
        "Exhaust air temperature"

    ::= { cyanPmeEntry 14 }

cyanPmeExhaustTempAlarmHighThres OBJECT-TYPE
    SYNTAX       Integer32 (-128000..128000) -- Float value * 1000
    MAX-ACCESS   read-only
    STATUS       current
    DESCRIPTION
        "High alarm threshold for exhaust air temperature"

    ::= { cyanPmeEntry 15 }

cyanPmeExhaustTempAlarmLowThres OBJECT-TYPE
    SYNTAX       Integer32 (-128000..128000) -- Float value * 1000
    MAX-ACCESS   read-only
    STATUS       current
    DESCRIPTION
        "Low alarm threshold for exhaust air temperature"

    ::= { cyanPmeEntry 16 }

cyanPmeExhaustTempWarnHighThres OBJECT-TYPE
    SYNTAX       Integer32 (-128000..128000) -- Float value * 1000
    MAX-ACCESS   read-only
    STATUS       current
    DESCRIPTION
        "High warning threshold for exhaust air temperature"

    ::= { cyanPmeEntry 17 }

cyanPmeExhaustTempWarnLowThres OBJECT-TYPE
    SYNTAX       Integer32 (-128000..128000) -- Float value * 1000
    MAX-ACCESS   read-only
    STATUS       current
    DESCRIPTION
        "Low warning threshold for exhaust air temperature"

    ::= { cyanPmeEntry 18 }

cyanPmeExpectedTemperatureRise OBJECT-TYPE
    SYNTAX       Integer32 -- Float Value * 1000
    MAX-ACCESS   read-only
    STATUS       current
    DESCRIPTION
        "Expected temperature rise"

    ::= { cyanPmeEntry 19 }

cyanPmeIdentifier OBJECT-TYPE
    SYNTAX       DisplayString
    MAX-ACCESS   read-only
    STATUS       current
    DESCRIPTION
        "string OID"

    ::= { cyanPmeEntry 20 }

cyanPmeIntakeAirTemp OBJECT-TYPE
    SYNTAX       Integer32 (-128000..128000) -- Float value * 1000
    MAX-ACCESS   read-only
    STATUS       current
    DESCRIPTION
        "In-take air temperature"

    ::= { cyanPmeEntry 21 }

cyanPmeIntakeTempAlarmHighThres OBJECT-TYPE
    SYNTAX       Integer32 (-128000..128000) -- Float value * 1000
    MAX-ACCESS   read-only
    STATUS       current
    DESCRIPTION
        "High alarm threshold for in-take air temperature"

    ::= { cyanPmeEntry 22 }

cyanPmeIntakeTempAlarmLowThres OBJECT-TYPE
    SYNTAX       Integer32 (-128000..128000) -- Float value * 1000
    MAX-ACCESS   read-only
    STATUS       current
    DESCRIPTION
        "Low alarm threshold for in-take air temperature"

    ::= { cyanPmeEntry 23 }

cyanPmeIntakeTempWarnHighThres OBJECT-TYPE
    SYNTAX       Integer32 (-128000..128000) -- Float value * 1000
    MAX-ACCESS   read-only
    STATUS       current
    DESCRIPTION
        "High warning threshold for in-take air temperature"

    ::= { cyanPmeEntry 24 }

cyanPmeIntakeTempWarnLowThres OBJECT-TYPE
    SYNTAX       Integer32 (-128000..128000) -- Float value * 1000
    MAX-ACCESS   read-only
    STATUS       current
    DESCRIPTION
        "Low warning threshold for in-take air temperature"

    ::= { cyanPmeEntry 25 }

cyanPmeLedTest OBJECT-TYPE
    SYNTAX       Unsigned32
    MAX-ACCESS   read-only
    STATUS       current
    DESCRIPTION
        "Change value of this attribute to run LED test on this module"

    ::= { cyanPmeEntry 26 }

cyanPmeMacBlockSize OBJECT-TYPE
    SYNTAX       Unsigned32 (0..255)
    MAX-ACCESS   read-only
    STATUS       current
    DESCRIPTION
        "Number of MAC addresses allocated from the base MAC address"

    ::= { cyanPmeEntry 27 }

cyanPmeMfgCleiCode OBJECT-TYPE
    SYNTAX       DisplayString (SIZE(0..10))
    MAX-ACCESS   read-only
    STATUS       current
    DESCRIPTION
        "Common Language Equipment Identifier"

    ::= { cyanPmeEntry 28 }

cyanPmeMfgEciCode OBJECT-TYPE
    SYNTAX       DisplayString (SIZE(0..6))
    MAX-ACCESS   read-only
    STATUS       current
    DESCRIPTION
        "Equipment Catalog Item"

    ::= { cyanPmeEntry 29 }

cyanPmeMfgModuleId OBJECT-TYPE
    SYNTAX       Unsigned32
    MAX-ACCESS   read-only
    STATUS       current
    DESCRIPTION
        "Module ID"

    ::= { cyanPmeEntry 30 }

cyanPmeMfgPartNumber OBJECT-TYPE
    SYNTAX       DisplayString (SIZE(0..16))
    MAX-ACCESS   read-only
    STATUS       current
    DESCRIPTION
        "Manufacturing part number"

    ::= { cyanPmeEntry 31 }

cyanPmeMfgRevision OBJECT-TYPE
    SYNTAX       DisplayString (SIZE(0..4))
    MAX-ACCESS   read-only
    STATUS       current
    DESCRIPTION
        "Mfg revision number"

    ::= { cyanPmeEntry 32 }

cyanPmeMfgSerialNumber OBJECT-TYPE
    SYNTAX       DisplayString (SIZE(0..16))
    MAX-ACCESS   read-only
    STATUS       current
    DESCRIPTION
        "Mfg serial number"

    ::= { cyanPmeEntry 33 }

cyanPmeName OBJECT-TYPE
    SYNTAX       DisplayString
    MAX-ACCESS   read-only
    STATUS       current
    DESCRIPTION
        "Cyan name"

    ::= { cyanPmeEntry 34 }

cyanPmeOidClass OBJECT-TYPE
    SYNTAX       DisplayString
    MAX-ACCESS   read-only
    STATUS       current
    DESCRIPTION
        "OID Class"

    ::= { cyanPmeEntry 35 }

cyanPmeOperState OBJECT-TYPE
    SYNTAX       CyanOpStateTc
    MAX-ACCESS   read-only
    STATUS       current
    DESCRIPTION
        "Primary Operation State"

    ::= { cyanPmeEntry 36 }

cyanPmeOperStateQual OBJECT-TYPE
    SYNTAX       CyanOpStateQualTc
    MAX-ACCESS   read-only
    STATUS       current
    DESCRIPTION
        "Operation state qualifier"

    ::= { cyanPmeEntry 37 }

cyanPmeOssLabel OBJECT-TYPE
    SYNTAX       DisplayString (SIZE(0..80))
    MAX-ACCESS   read-only
    STATUS       current
    DESCRIPTION
        "CyMS label"

    ::= { cyanPmeEntry 38 }

cyanPmeOvervoltageThreshold OBJECT-TYPE
    SYNTAX       Integer32 -- real32 * 1000
    MAX-ACCESS   read-only
    STATUS       current
    DESCRIPTION
        "Over-voltage warning threshold"

    ::= { cyanPmeEntry 39 }

cyanPmeOwner OBJECT-TYPE
    SYNTAX       DisplayString (SIZE(0..80))
    MAX-ACCESS   read-only
    STATUS       current
    DESCRIPTION
        "Owner"

    ::= { cyanPmeEntry 40 }

cyanPmePartNumber OBJECT-TYPE
    SYNTAX       DisplayString (SIZE(0..11))
    MAX-ACCESS   read-only
    STATUS       current
    DESCRIPTION
        "Cyan part number"

    ::= { cyanPmeEntry 41 }

cyanPmePowerLed OBJECT-TYPE
    SYNTAX       CyanLEDTc
    MAX-ACCESS   read-only
    STATUS       current
    DESCRIPTION
        "Power LED status"

    ::= { cyanPmeEntry 42 }

cyanPmePsuTemperature OBJECT-TYPE
    SYNTAX       Integer32 (-25000..85000) -- Float value * 1000
    MAX-ACCESS   read-only
    STATUS       current
    DESCRIPTION
        "Temperature reading in the power supply"

    ::= { cyanPmeEntry 43 }

cyanPmePwrFeedAStatus OBJECT-TYPE
    SYNTAX       CyanOffOnTc
    MAX-ACCESS   read-only
    STATUS       current
    DESCRIPTION
        "Status of power supply A"

    ::= { cyanPmeEntry 44 }

cyanPmePwrFeedAVoltage OBJECT-TYPE
    SYNTAX       Integer32 -- real32 * 1000
    MAX-ACCESS   read-only
    STATUS       current
    DESCRIPTION
        "Voltage level of power supply A"

    ::= { cyanPmeEntry 45 }

cyanPmePwrFeedBStatus OBJECT-TYPE
    SYNTAX       CyanOffOnTc
    MAX-ACCESS   read-only
    STATUS       current
    DESCRIPTION
        "Status of power supply B"

    ::= { cyanPmeEntry 46 }

cyanPmePwrFeedBVoltage OBJECT-TYPE
    SYNTAX       Integer32 -- real32 * 1000
    MAX-ACCESS   read-only
    STATUS       current
    DESCRIPTION
        "Voltage level of power supply B"

    ::= { cyanPmeEntry 47 }

cyanPmeResendEthlinkoamPdus OBJECT-TYPE
    SYNTAX       Unsigned32 (1..100)
    MAX-ACCESS   read-only
    STATUS       current
    DESCRIPTION
        "802.3ah Clause 57 link OAM event resend count"

    ::= { cyanPmeEntry 48 }

cyanPmeRevertCyanSwBuildVersions OBJECT-TYPE
    SYNTAX       DisplayString
    MAX-ACCESS   read-only
    STATUS       current
    DESCRIPTION
        "Revert Cyan software build versions"

    ::= { cyanPmeEntry 49 }

cyanPmeRevertCyanSwRelease OBJECT-TYPE
    SYNTAX       DisplayString
    MAX-ACCESS   read-only
    STATUS       current
    DESCRIPTION
        "Revert Cyan software release"

    ::= { cyanPmeEntry 50 }

cyanPmeSecServState OBJECT-TYPE
    SYNTAX       CyanSecServiceStateTc
    MAX-ACCESS   read-only
    STATUS       current
    DESCRIPTION
        "Secondary service state"

    ::= { cyanPmeEntry 51 }

cyanPmeSynchLed OBJECT-TYPE
    SYNTAX       CyanLEDTc
    MAX-ACCESS   read-only
    STATUS       current
    DESCRIPTION
        "Synch LED status"

    ::= { cyanPmeEntry 52 }

cyanPmeType OBJECT-TYPE
    SYNTAX       CyanTypeTc
    MAX-ACCESS   read-only
    STATUS       current
    DESCRIPTION
        "Equipment type"

    ::= { cyanPmeEntry 53 }

cyanPmeUndervoltageThreshold OBJECT-TYPE
    SYNTAX       Integer32 -- real32 * 1000
    MAX-ACCESS   read-only
    STATUS       current
    DESCRIPTION
        "Under-voltage warning threshold"

    ::= { cyanPmeEntry 54 }

cyanPmeUpgradeCyanSwBuildVersions OBJECT-TYPE
    SYNTAX       DisplayString
    MAX-ACCESS   read-only
    STATUS       current
    DESCRIPTION
        "Upgrade Cyan software build versions"

    ::= { cyanPmeEntry 55 }

cyanPmeUpgradeCyanSwRelease OBJECT-TYPE
    SYNTAX       DisplayString
    MAX-ACCESS   read-only
    STATUS       current
    DESCRIPTION
        "Upgrade Cyan software release"

    ::= { cyanPmeEntry 56 }

cyanPmeObjectGroup OBJECT-GROUP
    OBJECTS {
        cyanPmeActiveLed,
        cyanPmeActivestandbyState,
        cyanPmeAdminState,
        cyanPmeAlarmLed,
        cyanPmeAssetTag,
        cyanPmeAutoinserviceSoakTimeSec,
        cyanPmeBaseMacAddress,
        cyanPmeCurrCyanSwBuildVersions,
        cyanPmeCurrCyanSwRelease,
        cyanPmeCurrent,
        cyanPmeDescription,
        cyanPmeExhaustAirTemp,
        cyanPmeExhaustTempAlarmHighThres,
        cyanPmeExhaustTempAlarmLowThres,
        cyanPmeExhaustTempWarnHighThres,
        cyanPmeExhaustTempWarnLowThres,
        cyanPmeExpectedTemperatureRise,
        cyanPmeIdentifier,
        cyanPmeIntakeAirTemp,
        cyanPmeIntakeTempAlarmHighThres,
        cyanPmeIntakeTempAlarmLowThres,
        cyanPmeIntakeTempWarnHighThres,
        cyanPmeIntakeTempWarnLowThres,
        cyanPmeLedTest,
        cyanPmeMacBlockSize,
        cyanPmeMfgCleiCode,
        cyanPmeMfgEciCode,
        cyanPmeMfgModuleId,
        cyanPmeMfgPartNumber,
        cyanPmeMfgRevision,
        cyanPmeMfgSerialNumber,
        cyanPmeName,
        cyanPmeOidClass,
        cyanPmeOperState,
        cyanPmeOperStateQual,
        cyanPmeOssLabel,
        cyanPmeOvervoltageThreshold,
        cyanPmeOwner,
        cyanPmePartNumber,
        cyanPmePowerLed,
        cyanPmePsuTemperature,
        cyanPmePwrFeedAStatus,
        cyanPmePwrFeedAVoltage,
        cyanPmePwrFeedBStatus,
        cyanPmePwrFeedBVoltage,
        cyanPmeResendEthlinkoamPdus,
        cyanPmeRevertCyanSwBuildVersions,
        cyanPmeRevertCyanSwRelease,
        cyanPmeSecServState,
        cyanPmeSynchLed,
        cyanPmeType,
        cyanPmeUndervoltageThreshold,
        cyanPmeUpgradeCyanSwBuildVersions,
        cyanPmeUpgradeCyanSwRelease
    }

    STATUS current
    DESCRIPTION        "Group of objects that comes with Pme module"
    ::= {cyanPmeModule 20}

cyanPmeCompliance MODULE-COMPLIANCE
    STATUS current
    DESCRIPTION
        "The basic info needed to be a cyan Pme"
    MODULE
    MANDATORY-GROUPS {
        cyanPmeObjectGroup
    }
    ::= { cyanPmeModule 30 }


END
