CYAN-AUG64-MIB DEFINITIONS ::= BEGIN
IMPORTS
    MODULE-IDENTITY,
    OBJECT-TYPE,
    Integer32,
    Unsigned32
                    FROM SNMPv2-SMI

    DisplayString
                    FROM SNMPv2-TC

    CyanAugStructureTc,
    CyanOpStateQualTc,
    CyanAdminStateTc,
    CyanSecServiceStateTc,
    CyanOpStateTc
                    FROM CYAN-TC-MIB

    cyanEntityModules
		    FROM CYAN-MIB

    MODULE-COMPLIANCE,
    OBJECT-GROUP
	            FROM SNMPv2-CONF;


cyanAUG64Module MODULE-IDENTITY
    LAST-UPDATED "201412070545Z" -- Sun Dec  7 05:45:29 2014
    ORGANIZATION "Cyan, Inc."
    CONTACT-INFO
        "
        E-mail:  support@cyaninc.com

        Postal:  Cyan, Inc.
               1390 N. McDowell Blvd., # G-327
               Petaluma, CA  94954
               USA

        Tel:     +1-707-735-2300"

    DESCRIPTION    "MIB module for STS-192/AUG-64 layer"

    REVISION     "201412070545Z" -- Sun Dec  7 05:45:29 2014
    DESCRIPTION  "Release 6.0 build 1416362081"

    ::= { cyanEntityModules 240 }

cyanAUG64MibObjects           OBJECT IDENTIFIER ::={ cyanAUG64Module 1 }

cyanAUG64Table    OBJECT-TYPE
    SYNTAX        SEQUENCE OF CyanAUG64Entry
    MAX-ACCESS    not-accessible
    STATUS        current
    DESCRIPTION
        "A list of AUG64 entries."
    ::= { cyanAUG64MibObjects 1 }

cyanAUG64Entry    OBJECT-TYPE
    SYNTAX        CyanAUG64Entry
    MAX-ACCESS    not-accessible
    STATUS        current
    DESCRIPTION
        "An entry of AUG64."
    INDEX {
        cyanAUG64ShelfId ,
        cyanAUG64ModuleId ,
        cyanAUG64AUG64Id
    }
    ::= { cyanAUG64Table 1 }

CyanAUG64Entry  ::=
    SEQUENCE {
        cyanAUG64ShelfId    Unsigned32,
        cyanAUG64ModuleId    Unsigned32,
        cyanAUG64AUG64Id    Unsigned32,
        cyanAUG64AdminState    CyanAdminStateTc,
        cyanAUG64AutoinserviceSoakTimeSec    Integer32,
        cyanAUG64Description    DisplayString,
        cyanAUG64OperState    CyanOpStateTc,
        cyanAUG64OperStateQual    CyanOpStateQualTc,
        cyanAUG64SecServState    CyanSecServiceStateTc,
        cyanAUG64StsaugStructure    CyanAugStructureTc
    }

cyanAUG64ShelfId OBJECT-TYPE
    SYNTAX       Unsigned32 (0..255)
    MAX-ACCESS   not-accessible
    STATUS       current
    DESCRIPTION
        "Shelf Id"

    ::= { cyanAUG64Entry 1 }
cyanAUG64ModuleId OBJECT-TYPE
    SYNTAX       Unsigned32
    MAX-ACCESS   not-accessible
    STATUS       current
    DESCRIPTION
        "Module Id"

    ::= { cyanAUG64Entry 2 }
cyanAUG64AUG64Id OBJECT-TYPE
    SYNTAX       Unsigned32
    MAX-ACCESS   not-accessible
    STATUS       current
    DESCRIPTION
        "AUG64 Termination Id"

    ::= { cyanAUG64Entry 3 }

cyanAUG64AdminState OBJECT-TYPE
    SYNTAX       CyanAdminStateTc
    MAX-ACCESS   read-only
    STATUS       current
    DESCRIPTION
        "Administrative state"

    ::= { cyanAUG64Entry 4 }

cyanAUG64AutoinserviceSoakTimeSec OBJECT-TYPE
    SYNTAX       Integer32
    MAX-ACCESS   read-only
    STATUS       current
    DESCRIPTION
        "Auto-In-Service soak time"

    ::= { cyanAUG64Entry 5 }

cyanAUG64Description OBJECT-TYPE
    SYNTAX       DisplayString (SIZE(0..255))
    MAX-ACCESS   read-only
    STATUS       current
    DESCRIPTION
        "Description"

    ::= { cyanAUG64Entry 6 }

cyanAUG64OperState OBJECT-TYPE
    SYNTAX       CyanOpStateTc
    MAX-ACCESS   read-only
    STATUS       current
    DESCRIPTION
        "Primary Operation State"

    ::= { cyanAUG64Entry 7 }

cyanAUG64OperStateQual OBJECT-TYPE
    SYNTAX       CyanOpStateQualTc
    MAX-ACCESS   read-only
    STATUS       current
    DESCRIPTION
        "Operation state qualifier"

    ::= { cyanAUG64Entry 8 }

cyanAUG64SecServState OBJECT-TYPE
    SYNTAX       CyanSecServiceStateTc
    MAX-ACCESS   read-only
    STATUS       current
    DESCRIPTION
        "Secondary service state"

    ::= { cyanAUG64Entry 9 }

cyanAUG64StsaugStructure OBJECT-TYPE
    SYNTAX       CyanAugStructureTc
    MAX-ACCESS   read-only
    STATUS       current
    DESCRIPTION
        "AUG structure"

    ::= { cyanAUG64Entry 10 }

cyanAUG64ObjectGroup OBJECT-GROUP
    OBJECTS {
        cyanAUG64AdminState,
        cyanAUG64AutoinserviceSoakTimeSec,
        cyanAUG64Description,
        cyanAUG64OperState,
        cyanAUG64OperStateQual,
        cyanAUG64SecServState,
        cyanAUG64StsaugStructure
    }

    STATUS current
    DESCRIPTION        "Group of objects that comes with AUG64 module"
    ::= {cyanAUG64Module 20}

cyanAUG64Compliance MODULE-COMPLIANCE
    STATUS current
    DESCRIPTION
        "The basic info needed to be a cyan AUG64"
    MODULE
    MANDATORY-GROUPS {
        cyanAUG64ObjectGroup
    }
    ::= { cyanAUG64Module 30 }


END
