CYAN-TENGPORT-MIB DEFINITIONS ::= BEGIN
IMPORTS
    MODULE-IDENTITY,
    OBJECT-TYPE,
    Integer32,
    Unsigned32
                    FROM SNMPv2-SMI

    DisplayString
                    FROM SNMPv2-TC

    CyanOffOnTc,
    CyanLoopbackControlTc,
    CyanOpStateQualTc,
    CyanTxControlTc,
    CyanOpStateTc,
    CyanSecServiceStateTc,
    CyanTPConnectionStateTc,
    CyanXGOSignalTypeTc,
    CyanAdminStateTc,
    CyanEnDisabledTc
                    FROM CYAN-TC-MIB

    cyanEntityModules
		    FROM CYAN-MIB

    MODULE-COMPLIANCE,
    OBJECT-GROUP
	            FROM SNMPv2-CONF;


cyanTENGPortModule MODULE-IDENTITY
    LAST-UPDATED "201412070545Z" -- Sun Dec  7 05:45:23 2014
    ORGANIZATION "Cyan, Inc."
    CONTACT-INFO
        "
        E-mail:  support@cyaninc.com

        Postal:  Cyan, Inc.
               1390 N. McDowell Blvd., # G-327
               Petaluma, CA  94954
               USA

        Tel:     +1-707-735-2300"

    DESCRIPTION    "MIB module for Ten Gig Port"

    REVISION     "201412070545Z" -- Sun Dec  7 05:45:23 2014
    DESCRIPTION  "Release 6.0 build 1416362081"

    ::= { cyanEntityModules 150 }

cyanTENGPortMibObjects           OBJECT IDENTIFIER ::={ cyanTENGPortModule 1 }

cyanTENGPortTable    OBJECT-TYPE
    SYNTAX        SEQUENCE OF CyanTENGPortEntry
    MAX-ACCESS    not-accessible
    STATUS        current
    DESCRIPTION
        "A list of TENGPort entries."
    ::= { cyanTENGPortMibObjects 1 }

cyanTENGPortEntry    OBJECT-TYPE
    SYNTAX        CyanTENGPortEntry
    MAX-ACCESS    not-accessible
    STATUS        current
    DESCRIPTION
        "An entry of TENGPort."
    INDEX {
        cyanTENGPortShelfId ,
        cyanTENGPortModuleId ,
        cyanTENGPortXcvrId ,
        cyanTENGPortPortId
    }
    ::= { cyanTENGPortTable 1 }

CyanTENGPortEntry  ::=
    SEQUENCE {
        cyanTENGPortShelfId    Unsigned32,
        cyanTENGPortModuleId    Unsigned32,
        cyanTENGPortXcvrId    Unsigned32,
        cyanTENGPortPortId    Unsigned32,
        cyanTENGPortAdminState    CyanAdminStateTc,
        cyanTENGPortAutoinserviceSoakTimeSec    Integer32,
        cyanTENGPortConnectionState    CyanTPConnectionStateTc,
        cyanTENGPortDescription    DisplayString,
        cyanTENGPortExternalFiberMultishelfLink    CyanEnDisabledTc,
        cyanTENGPortExternalFiberRemotePort    DisplayString,
        cyanTENGPortLoopbackControl    CyanLoopbackControlTc,
        cyanTENGPortOperState    CyanOpStateTc,
        cyanTENGPortOperStateQual    CyanOpStateQualTc,
        cyanTENGPortRxPwr    Integer32,
        cyanTENGPortSecServState    CyanSecServiceStateTc,
        cyanTENGPortSignalType    CyanXGOSignalTypeTc,
        cyanTENGPortTransmitControl    CyanTxControlTc,
        cyanTENGPortTxPwr    Integer32,
        cyanTENGPortTxStatus    CyanOffOnTc
    }

cyanTENGPortShelfId OBJECT-TYPE
    SYNTAX       Unsigned32 (0..255)
    MAX-ACCESS   not-accessible
    STATUS       current
    DESCRIPTION
        "Shelf Id"

    ::= { cyanTENGPortEntry 1 }
cyanTENGPortModuleId OBJECT-TYPE
    SYNTAX       Unsigned32
    MAX-ACCESS   not-accessible
    STATUS       current
    DESCRIPTION
        "Module Id"

    ::= { cyanTENGPortEntry 2 }
cyanTENGPortXcvrId OBJECT-TYPE
    SYNTAX       Unsigned32
    MAX-ACCESS   not-accessible
    STATUS       current
    DESCRIPTION
        "Transceiver Id"

    ::= { cyanTENGPortEntry 3 }
cyanTENGPortPortId OBJECT-TYPE
    SYNTAX       Unsigned32
    MAX-ACCESS   not-accessible
    STATUS       current
    DESCRIPTION
        "Port Id"

    ::= { cyanTENGPortEntry 4 }

cyanTENGPortAdminState OBJECT-TYPE
    SYNTAX       CyanAdminStateTc
    MAX-ACCESS   read-only
    STATUS       current
    DESCRIPTION
        "Administrative state"

    ::= { cyanTENGPortEntry 5 }

cyanTENGPortAutoinserviceSoakTimeSec OBJECT-TYPE
    SYNTAX       Integer32
    MAX-ACCESS   read-only
    STATUS       current
    DESCRIPTION
        "Auto-In-Service soak time"

    ::= { cyanTENGPortEntry 6 }

cyanTENGPortConnectionState OBJECT-TYPE
    SYNTAX       CyanTPConnectionStateTc
    MAX-ACCESS   read-only
    STATUS       current
    DESCRIPTION
        "Termination point connection state"

    ::= { cyanTENGPortEntry 7 }

cyanTENGPortDescription OBJECT-TYPE
    SYNTAX       DisplayString (SIZE(0..255))
    MAX-ACCESS   read-only
    STATUS       current
    DESCRIPTION
        "Description"

    ::= { cyanTENGPortEntry 8 }

cyanTENGPortExternalFiberMultishelfLink OBJECT-TYPE
    SYNTAX       CyanEnDisabledTc
    MAX-ACCESS   read-only
    STATUS       current
    DESCRIPTION
        "Assign a port to an inter-node link"

    ::= { cyanTENGPortEntry 9 }

cyanTENGPortExternalFiberRemotePort OBJECT-TYPE
    SYNTAX       DisplayString (SIZE(0..45))
    MAX-ACCESS   read-only
    STATUS       current
    DESCRIPTION
        "Remote connection point of the inter-node link"

    ::= { cyanTENGPortEntry 10 }

cyanTENGPortLoopbackControl OBJECT-TYPE
    SYNTAX       CyanLoopbackControlTc
    MAX-ACCESS   read-only
    STATUS       current
    DESCRIPTION
        "Port loopback control"

    ::= { cyanTENGPortEntry 11 }

cyanTENGPortOperState OBJECT-TYPE
    SYNTAX       CyanOpStateTc
    MAX-ACCESS   read-only
    STATUS       current
    DESCRIPTION
        "Primary Operation State"

    ::= { cyanTENGPortEntry 12 }

cyanTENGPortOperStateQual OBJECT-TYPE
    SYNTAX       CyanOpStateQualTc
    MAX-ACCESS   read-only
    STATUS       current
    DESCRIPTION
        "Operation state qualifier"

    ::= { cyanTENGPortEntry 13 }

cyanTENGPortRxPwr OBJECT-TYPE
    SYNTAX       Integer32 -- real32 * 1000
    MAX-ACCESS   read-only
    STATUS       current
    DESCRIPTION
        "RX Power"

    ::= { cyanTENGPortEntry 14 }

cyanTENGPortSecServState OBJECT-TYPE
    SYNTAX       CyanSecServiceStateTc
    MAX-ACCESS   read-only
    STATUS       current
    DESCRIPTION
        "Secondary service state"

    ::= { cyanTENGPortEntry 15 }

cyanTENGPortSignalType OBJECT-TYPE
    SYNTAX       CyanXGOSignalTypeTc
    MAX-ACCESS   read-only
    STATUS       current
    DESCRIPTION
        "Client signal type or port mode"

    ::= { cyanTENGPortEntry 16 }

cyanTENGPortTransmitControl OBJECT-TYPE
    SYNTAX       CyanTxControlTc
    MAX-ACCESS   read-only
    STATUS       current
    DESCRIPTION
        "Transmitter control"

    ::= { cyanTENGPortEntry 17 }

cyanTENGPortTxPwr OBJECT-TYPE
    SYNTAX       Integer32 -- real32 * 1000
    MAX-ACCESS   read-only
    STATUS       current
    DESCRIPTION
        "TX Power"

    ::= { cyanTENGPortEntry 18 }

cyanTENGPortTxStatus OBJECT-TYPE
    SYNTAX       CyanOffOnTc
    MAX-ACCESS   read-only
    STATUS       current
    DESCRIPTION
        "Transmitter status"

    ::= { cyanTENGPortEntry 19 }

cyanTENGPortObjectGroup OBJECT-GROUP
    OBJECTS {
        cyanTENGPortAdminState,
        cyanTENGPortAutoinserviceSoakTimeSec,
        cyanTENGPortConnectionState,
        cyanTENGPortDescription,
        cyanTENGPortExternalFiberMultishelfLink,
        cyanTENGPortExternalFiberRemotePort,
        cyanTENGPortLoopbackControl,
        cyanTENGPortOperState,
        cyanTENGPortOperStateQual,
        cyanTENGPortRxPwr,
        cyanTENGPortSecServState,
        cyanTENGPortSignalType,
        cyanTENGPortTransmitControl,
        cyanTENGPortTxPwr,
        cyanTENGPortTxStatus
    }

    STATUS current
    DESCRIPTION        "Group of objects that comes with TENGPort module"
    ::= {cyanTENGPortModule 20}

cyanTENGPortCompliance MODULE-COMPLIANCE
    STATUS current
    DESCRIPTION
        "The basic info needed to be a cyan TENGPort"
    MODULE
    MANDATORY-GROUPS {
        cyanTENGPortObjectGroup
    }
    ::= { cyanTENGPortModule 30 }


END
