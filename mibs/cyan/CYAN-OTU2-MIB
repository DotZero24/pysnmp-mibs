CYAN-OTU2-MIB DEFINITIONS ::= BEGIN
IMPORTS
    MODULE-IDENTITY,
    OBJECT-TYPE,
    Integer32,
    Unsigned32
                    FROM SNMPv2-SMI


    CyanLayerRateTc,
    CyanFecModeTc,
    CyanSecServiceStateTc,
    CyanEnDisabledTc,
    CyanOpStateQualTc,
    CyanAdminStateTc,
    CyanOpStateTc
                    FROM CYAN-TC-MIB

    cyanEntityModules
		    FROM CYAN-MIB

    MODULE-COMPLIANCE,
    OBJECT-GROUP
	            FROM SNMPv2-CONF;


cyanOTU2Module MODULE-IDENTITY
    LAST-UPDATED "201412070545Z" -- Sun Dec  7 05:45:28 2014
    ORGANIZATION "Cyan, Inc."
    CONTACT-INFO
        "
        E-mail:  support@cyaninc.com

        Postal:  Cyan, Inc.
               1390 N. McDowell Blvd., # G-327
               Petaluma, CA  94954
               USA

        Tel:     +1-707-735-2300"

    DESCRIPTION    "MIB module for OTU-2 Section layer"

    REVISION     "201412070545Z" -- Sun Dec  7 05:45:28 2014
    DESCRIPTION  "Release 6.0 build 1416362081"

    ::= { cyanEntityModules 190 }

cyanOTU2MibObjects           OBJECT IDENTIFIER ::={ cyanOTU2Module 1 }

cyanOTU2Table    OBJECT-TYPE
    SYNTAX        SEQUENCE OF CyanOTU2Entry
    MAX-ACCESS    not-accessible
    STATUS        current
    DESCRIPTION
        "A list of OTU2 entries."
    ::= { cyanOTU2MibObjects 1 }

cyanOTU2Entry    OBJECT-TYPE
    SYNTAX        CyanOTU2Entry
    MAX-ACCESS    not-accessible
    STATUS        current
    DESCRIPTION
        "An entry of OTU2."
    INDEX {
        cyanOTU2ShelfId ,
        cyanOTU2ModuleId ,
        cyanOTU2OTU2Id
    }
    ::= { cyanOTU2Table 1 }

CyanOTU2Entry  ::=
    SEQUENCE {
        cyanOTU2ShelfId    Unsigned32,
        cyanOTU2ModuleId    Unsigned32,
        cyanOTU2OTU2Id    Unsigned32,
        cyanOTU2AdminState    CyanAdminStateTc,
        cyanOTU2AutoinserviceSoakTimeSec    Integer32,
        cyanOTU2FecCorrectableBitErrorsCurrSec    Unsigned32,
        cyanOTU2ForwardErrorCoding    CyanFecModeTc,
        cyanOTU2OperState    CyanOpStateTc,
        cyanOTU2OperStateQual    CyanOpStateQualTc,
        cyanOTU2RxFecErrorCorrection    CyanEnDisabledTc,
        cyanOTU2SecServState    CyanSecServiceStateTc,
        cyanOTU2SupportedRates    CyanLayerRateTc
    }

cyanOTU2ShelfId OBJECT-TYPE
    SYNTAX       Unsigned32 (0..255)
    MAX-ACCESS   not-accessible
    STATUS       current
    DESCRIPTION
        "Shelf Id"

    ::= { cyanOTU2Entry 1 }
cyanOTU2ModuleId OBJECT-TYPE
    SYNTAX       Unsigned32
    MAX-ACCESS   not-accessible
    STATUS       current
    DESCRIPTION
        "Module Id"

    ::= { cyanOTU2Entry 2 }
cyanOTU2OTU2Id OBJECT-TYPE
    SYNTAX       Unsigned32
    MAX-ACCESS   not-accessible
    STATUS       current
    DESCRIPTION
        "OTU2 Termination Id"

    ::= { cyanOTU2Entry 3 }

cyanOTU2AdminState OBJECT-TYPE
    SYNTAX       CyanAdminStateTc
    MAX-ACCESS   read-only
    STATUS       current
    DESCRIPTION
        "Administrative state"

    ::= { cyanOTU2Entry 4 }

cyanOTU2AutoinserviceSoakTimeSec OBJECT-TYPE
    SYNTAX       Integer32
    MAX-ACCESS   read-only
    STATUS       current
    DESCRIPTION
        "Auto-In-Service soak time"

    ::= { cyanOTU2Entry 5 }

cyanOTU2FecCorrectableBitErrorsCurrSec OBJECT-TYPE
    SYNTAX       Unsigned32
    MAX-ACCESS   read-only
    STATUS       current
    DESCRIPTION
        "Current FEC corrected errors"

    ::= { cyanOTU2Entry 6 }

cyanOTU2ForwardErrorCoding OBJECT-TYPE
    SYNTAX       CyanFecModeTc
    MAX-ACCESS   read-only
    STATUS       current
    DESCRIPTION
        "Forward Error Coding"

    ::= { cyanOTU2Entry 7 }

cyanOTU2OperState OBJECT-TYPE
    SYNTAX       CyanOpStateTc
    MAX-ACCESS   read-only
    STATUS       current
    DESCRIPTION
        "Primary Operation State"

    ::= { cyanOTU2Entry 8 }

cyanOTU2OperStateQual OBJECT-TYPE
    SYNTAX       CyanOpStateQualTc
    MAX-ACCESS   read-only
    STATUS       current
    DESCRIPTION
        "Operation state qualifier"

    ::= { cyanOTU2Entry 9 }

cyanOTU2RxFecErrorCorrection OBJECT-TYPE
    SYNTAX       CyanEnDisabledTc
    MAX-ACCESS   read-only
    STATUS       current
    DESCRIPTION
        "Rx. FEC Error Correction"

    ::= { cyanOTU2Entry 10 }

cyanOTU2SecServState OBJECT-TYPE
    SYNTAX       CyanSecServiceStateTc
    MAX-ACCESS   read-only
    STATUS       current
    DESCRIPTION
        "Secondary service state"

    ::= { cyanOTU2Entry 11 }

cyanOTU2SupportedRates OBJECT-TYPE
    SYNTAX       CyanLayerRateTc
    MAX-ACCESS   read-only
    STATUS       current
    DESCRIPTION
        "Supported layer & rate"

    ::= { cyanOTU2Entry 12 }

cyanOTU2ObjectGroup OBJECT-GROUP
    OBJECTS {
        cyanOTU2AdminState,
        cyanOTU2AutoinserviceSoakTimeSec,
        cyanOTU2FecCorrectableBitErrorsCurrSec,
        cyanOTU2ForwardErrorCoding,
        cyanOTU2OperState,
        cyanOTU2OperStateQual,
        cyanOTU2RxFecErrorCorrection,
        cyanOTU2SecServState,
        cyanOTU2SupportedRates
    }

    STATUS current
    DESCRIPTION        "Group of objects that comes with OTU2 module"
    ::= {cyanOTU2Module 20}

cyanOTU2Compliance MODULE-COMPLIANCE
    STATUS current
    DESCRIPTION
        "The basic info needed to be a cyan OTU2"
    MODULE
    MANDATORY-GROUPS {
        cyanOTU2ObjectGroup
    }
    ::= { cyanOTU2Module 30 }


END
