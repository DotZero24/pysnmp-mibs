--=============================================================================
-- Copyright (c) 2016 Fujitsu Network Communications, Inc. All Rights Reserved.
--=============================================================================

FSS-COMMON-TC DEFINITIONS ::= BEGIN

IMPORTS
    MODULE-IDENTITY, Integer32, Unsigned32
        FROM SNMPv2-SMI
    TEXTUAL-CONVENTION
        FROM SNMPv2-TC
    fssCommon
        FROM FSS-COMMON-SMI
    DisplayString
        FROM SNMPv2-TC
    ;

fcTc MODULE-IDENTITY
    LAST-UPDATED "202201310000z"
    ORGANIZATION
        "Fujitsu Network Communications, Inc."
    CONTACT-INFO
        "Fujitsu Technical Assistance Center (FTAC),
         1-800-USE-FTAC (1-800-873-3822)"
    DESCRIPTION
        "This MIB module contains common textual conventions (TC)
         used throughout the Fujitsu Network Communications, Inc.
         enterprise MIB.  It contains only those generic
         TCs potentially used in more than one MIB module."
    REVISION      "202201310000z"
    DESCRIPTION
       "Moved following Event notification from Alarm(FCCondType)
        to Event(FCTcCondType) : manualSwitchAwayFromWork,
        manualSwitchAwayFromProtect, otuReceivedTraceChange,
        oduReceivedTraceChange, oduReceivedTraceChangeTcm1Up,
        oduReceivedTraceChangeTcm2Up, oduReceivedTraceChangeTcm3Up,
        oduReceivedTraceChangeTcm4Up, oduReceivedTraceChangeTcm5Up,
        oduReceivedTraceChangeTcm6Up, oduReceivedTraceChangeTcm1Down,
        oduReceivedTraceChangeTcm2Down, oduReceivedTraceChangeTcm3Down,
        oduReceivedTraceChangeTcm4Down, oduReceivedTraceChangeTcm5Down,
        oduReceivedTraceChangeTcm6Down, otucnReceivedTraceChange,
        oducnReceivedTraceChange, oducnReceivedTraceChangeTcm1Up,
        oducnReceivedTraceChangeTcm2Up, oducnReceivedTraceChangeTcm3Up,
        oducnReceivedTraceChangeTcm4Up, oducnReceivedTraceChangeTcm5Up,
        oducnReceivedTraceChangeTcm6Up, oducnReceivedTraceChangeTcm1Down,
        oducnReceivedTraceChangeTcm2Down, oducnReceivedTraceChangeTcm3Down,
        oducnReceivedTraceChangeTcm4Down, oducnReceivedTraceChangeTcm5Down,
        oducnReceivedTraceChangeTcm6Down, databaseActivationSuccess,
        databaseActivationCanceled, databaseCommitSuccess. "
    REVISION      "202108060000z"
    DESCRIPTION
       "Added Remote Defect Indication."
    REVISION      "202009250000z"
    DESCRIPTION
        "Added events for ODUCN TCM Trace change Notification"
    REVISION      "202009030000z"
    DESCRIPTION
        "Added events for IAE/BIAE Trace Notification"
    REVISION      "202006250000z"
    DESCRIPTION
        "Added events for autorx trace change receive"
    REVISION      "202006160000z"
    DESCRIPTION
       "Added Flexo support New alarms."
    REVISION      "202006100000z"
    DESCRIPTION
       "Added PCS FEC degraded SER, Local degraded SER and Remote degraded SER received."
    REVISION      "202006090000z"
    DESCRIPTION
       "Added systemRestart."
    REVISION      "202006080000z"
    DESCRIPTION
	      "Removed auto-logoff ip down event"
    REVISION      "202005150000z"
    DESCRIPTION
       "Added OSC PHY setting not matched to opposite node."
    REVISION      "202004070000Z"
    DESCRIPTION
       "Added equipmentPortGroupChange."
    REVISION      "202001090000Z"
    DESCRIPTION
       "Added hardwareConfigurationInProgress alarm."
    REVISION      "201911270000Z"
    DESCRIPTION
       "Added events and alarm for CHRD measurement."
    REVISION      "201910300000Z"
    DESCRIPTION
       "Added fiberTestPerDegreeNotification."
    REVISION      "201910070000Z"
    DESCRIPTION
      "Added highSER alarm type."
    REVISION      "201908300000Z"
    DESCRIPTION
      "Added laserDisabled alarm "
    REVISION      "201907160000Z"
    DESCRIPTION
      "Added selfTestFailure alarm "
    REVISION      "201907150000Z"
    DESCRIPTION
      "Added selfTestInProgress alarm "
    REVISION      "201904150000Z"
    DESCRIPTION
      "Added witness port mismatch alarm "
    REVISION      "201903290000Z"
    DESCRIPTION
      "Added alarm osnrModeMismatch"
    REVISION      "201903180000Z"
    DESCRIPTION
      "Added SWDL alarms swRepoIncomplete and redundantCfgSwRepoOutOfSync"
    REVISION      "201901280000Z"
    DESCRIPTION
      "Added RASIS Util Debug event and alarm"
    REVISION      "201812120000Z"
    DESCRIPTION
      "Added scripting feature events"
    REVISION      "201810300000Z"
    DESCRIPTION
      "Added auto-logoff ip down event"
    REVISION      "201810290000Z"
    DESCRIPTION
      "Added File sync events"
    REVISION      "201810220000Z"
    DESCRIPTION
      "Added wavelength contention group event."
    REVISION      "201808020000Z"
    DESCRIPTION
      "Added redundancy not provisioned alarm "
    REVISION      "201806010000Z"
    DESCRIPTION
      "Added epg alarms "
    REVISION      "201805310000Z"
    DESCRIPTION
      "Added SWDL and DB events: softwareActivationCanceled,
       databaseActivationSuccess, databaseActivationCanceled,
       databaseCommitSuccess"
    REVISION      "201805030000Z"
    DESCRIPTION
      "Added gnmi alarms "
    REVISION      "201804050000Z"
    DESCRIPTION
      "Added rstp events "
    REVISION      "201802240000Z"
    DESCRIPTION
      "Added autoPowerReductionDra for RAMAN port "
    REVISION      "201802060000Z"
    DESCRIPTION
      "Modified Tcm to TCM for TCM TCAs"
    REVISION      "201802010000Z"
    DESCRIPTION
      "Added YPG Alarms
       doNotSwitch,automaticSwitchAwayFromWorkingDueToBD,
       automaticSwitchAwayFromProtectDueToBD"
    REVISION      "201801220000Z"
    DESCRIPTION
      "Added sdfecub info for tca otu"
    REVISION      "201801190000Z"
    DESCRIPTION
      "Added Ethernet  TCA"
    REVISION      "201801160000Z"
    DESCRIPTION
      "Added event info autorx in odu"
    REVISION      "201801110000Z"
    DESCRIPTION
      "Added TCM TCA"
    REVISION      "201712130000Z"
    DESCRIPTION
      "Added event info autorx in otu"
    REVISION      "201712110000Z"
    DESCRIPTION
      "Added support for Sync switch events"
    REVISION      "201711220000Z"
    DESCRIPTION
      "Added support for Provisioned Tx Power Out of Device Range Alarm"
    REVISION      "201711160000Z"
    DESCRIPTION
      "Added support for OLEAF EQPT lossofclock Alarm"
    REVISION      "201711140000Z"
    DESCRIPTION
      "Added support for TCM  Alarms,zero touch boot alarms"
    REVISION      "201711030000Z"
    DESCRIPTION
      "Added support for OLEAF SYNC Alarms"
    REVISION      "201710250000Z"
    DESCRIPTION
      "add rasis util alarm and events"
    REVISION      "201710090000Z"
    DESCRIPTION
      "Added support for the new OLEAF ETH alarms
       errorCode, lanTransmitErrorCode, decapsulationFailure,
       decapsulationLossOfFrame,
       clientManagementFrameForwardDefectIndication,
       clientManagementFrameLossOfSignal, clientManagementFrameLossOfSync,
       clientManagementFrameReverseDefectIndication,
       protocolMiscabledConnection, protocolNeighborFailure"
    REVISION      "201709120000Z"
    DESCRIPTION
      "add new database alarm"
    REVISION      "201707270000Z"
    DESCRIPTION
       "add support for No Secondary Storage alarm"
    REVISION      "201707210000Z"
    DESCRIPTION
        "Added SNCP/SMR Alarms and SNCP/SMR TCs
         lockoutOfProtection, forcedSwitchAwayFromWorking, forcedSwitchAwayFromProtect,
         automaticSwitchAwayFromWorkingDueToSF, automaticSwitchAwayFromProtectDueToSF,
         automaticSwitchAwayFromWorkingDueToSD, automaticSwitchAwayFromProtectDueToSD,
         automaticSwitchDueToWTR, manualSwitchAwayFromWork, manualSwitchAwayFromProtect,
         smrDisabled, smrNeighborHelloFailure, smrActivationFailure,
         switchedToProtect, switchedBackToWorking,
         smrActivationSuccess, smrActivationFail"
    REVISION      "201707200000Z"
    DESCRIPTION
            "Added defaultSysName"
    REVISION      "201706090000Z"
    DESCRIPTION
        "Add channelPlanMismatch alarm"
    REVISION      "201706090000Z"
    DESCRIPTION
        "Add sysZeroizationFailed, sysZeroizationCompleted,
             dataEncZeroizationFailed, dataEncZeroizationCompleted"
    REVISION      "201705110000Z"
    DESCRIPTION
        "Add tCAErroredSecondEthernet, tCASeverelyErroredSecondEthernet,
             tCAUnavailableSecondEthernet and tCAInFramesErr"
    REVISION      "201705040000Z"
    DESCRIPTION
        "Add invalidUSB alarm and usbSafeToRemove"
    REVISION      "201704210000Z"
    DESCRIPTION
        "Add remoteApsd alarm"
    REVISION      "201704110000Z"
    DESCRIPTION
        "SDB new alarm updates"
    REVISION      "201704040000Z"
    DESCRIPTION
            "Added intRSTPdisabled"
    REVISION      "201704030000Z"
    DESCRIPTION
            "Added encryptSessionFailureNN (01~04) and encryptionHandshakeFailure
              alarms"
    REVISION      "201703300000Z"
    DESCRIPTION
            "Added encryptionSelfTestFailure and trafficSquelchedForEncryption"
    REVISION      "201703290000Z"
    DESCRIPTION
            "fix gretfailure enum name."
    REVISION      "201703290000Z"
    DESCRIPTION
            "SWDL event updates."
    REVISION      "201703270000Z"
    DESCRIPTION
            "Added GreT failure alarm."
    REVISION      "201601200000Z"
    DESCRIPTION
            "Initial version for release."
    ::= { fssCommon 1 } -- See FSS-COMMON-SMI.mib

--=====================================================================--
-- Textual Conventions                                                 --
--=====================================================================--

FCSeverity ::= TEXTUAL-CONVENTION
    STATUS      current
    DESCRIPTION
        "The severity of the standing condition."
    SYNTAX      INTEGER{
        other         (9999),  -- Other
        na            (0),     -- Not Applicable
        critical      (1),     -- Critical
        major         (2),     -- Major
        minor         (3),     -- Minor
        not-alarmed   (4),     -- Not Alarmed
        not-reported  (5),     -- Not Reported
        warning       (6),     -- Warning
        indeterminate (7)      -- Indeterminate
    }

FCCondEffect ::= TEXTUAL-CONVENTION
    STATUS      current
    DESCRIPTION
        "The effect of the condition."
    SYNTAX      INTEGER{
        other   (9999),      -- Other
        na      (0),         -- Not Applicable
        cl      (1),         -- Cleared
        sc      (2),         -- Standing Condition
        tc      (3)          -- Transient Condition
    }

FCServEffect ::= TEXTUAL-CONVENTION
    STATUS      current
    DESCRIPTION
        "The effect on service caused by a standing condition."
    SYNTAX      INTEGER{
        other   (9999),      -- Other
        na      (0),         -- Not Applicable
        sa      (1),         -- Service Affecting
        nsa     (2)          -- Non-Service Affecting
    }

FCLocation ::= TEXTUAL-CONVENTION
    STATUS      current
    DESCRIPTION
        "The location of the condition."
    SYNTAX      INTEGER{
        other (9999),     -- Other
        na    (0),        -- Not Applicable
        nend  (1),        -- Near End
        fend  (2)         -- Far End
    }

FCDirection ::= TEXTUAL-CONVENTION
    STATUS      current
    DESCRIPTION
        "The direction of the condition."
    SYNTAX      INTEGER{
        other    (9999),  -- Other
        na       (0),     -- Not Applicable
        receive  (1),     -- Receive
        transmit (2)      -- Transmit
    }

FCTimePeriod ::= TEXTUAL-CONVENTION
    STATUS      current
    DESCRIPTION
        "Indicates the time period for which the raised threshold
         crossing alert is associated with."
    SYNTAX      INTEGER{
        other    (9999),  -- Other
        na       (0),     -- Not Applicable
        min-15   (1),     -- 15 Minute
        hr-24    (2),     -- 24 Hour (1 Day)
        week-1   (3),     -- 1 Week
        month-1  (4)      -- 1 Month
    }


FCTrapType ::= TEXTUAL-CONVENTION
    STATUS      current
    DESCRIPTION
        "Indicates the type of notification that was generated.
         For every type of Trap emitted, there should be a corresponding
         Trap type defined."
    SYNTAX      INTEGER{
        other         (9999),   -- Other
        na            (0),      -- Not Applicable
        cond          (1),      -- Condition
        tca           (2),      -- Threshold Crossing Alert
        dbchg         (3)       -- Database Change Notification
    }

FCObjectName ::= TEXTUAL-CONVENTION
    STATUS      current
    DESCRIPTION
        "The name of the object generating the trap."
    SYNTAX      DisplayString (SIZE(1..80))

FCCondType ::= TEXTUAL-CONVENTION
    STATUS      current
    DESCRIPTION
        "The possible alarms/events that are supported by fcCondTrap.
         A value of prod-specific or qual-xxx, indicates that
         the condition type will be further qualified by the
         product specific condition qualifier object."
    SYNTAX      INTEGER {
        prod-specific                           (0),        -- Project Specific Condition (see Condition Qualifier)

-- EQPT Alarms
        equipmentFault                          (1),        -- EQUIPMENT - Fault
        equipmentRemoved                        (2),        -- EQUIPMENT - Removed
        equipmentMismatchAttributes             (3),        -- EQUIPMENT - Mismatch
        equipmentWarmup                         (4),        -- EQUIPMENT - Warmup
        equipmentLedOn                          (5),        -- EQUIPMENT - Equipment Common Visual LED Activated
        administrativeDown                      (6),        -- GENERAL - Adminstrative State Down
        administrativeTesting                   (7),        -- GENERAL - Adminstrative State Testing
        overTemperatureEquipment                (8),        -- EQUIPMENT - EQPT Temp Over Operating Spec
        incompatibleSffHardware                 (9),        -- EQUIPMENT - Incompatible Hardware
        configurationStandBy                    (10),       -- EQUIPMENT - Configuration Standby
        shelfProvisioningMode                   (11),       -- EQUIPMENT - Shelf Provisioning Mode
        equipmentInterConnectFailure            (12),       -- EQUIPMENT - Interconnection Failure
        equipmentMiscabledConnection            (13),       -- EQUIPMENT - Miscabled COnnection
        fanCoolingFail                          (14),       -- EQUIPMENT - Fan Cooling Failure
        equipmentCurrExceededFeed               (15),       -- EQUIPMENT - Current Exceeded on Feed
        interConnectFailureBladePiu             (16),       -- EQUIPMENT - Interconnection Failure Blade PIU
        lampTest                                (17),       -- EQUIPMENT - Lamp Test
        otdrScanInProgress                      (18),       -- EQUIPMENT - OTDR Scan In Progress
        equipmentReset                          (19),       -- EQUIPMENT - Reset
        equipmentLogTrigger                     (20),       -- EQUIPMENT - MB Log Trigger In Progress
        equipmentFwLogTrigger                   (21),       -- EQUIPMENT - FW Log Trigger In Progress
        equipmentPbcntLogTrigger                (22),       -- EQUIPMENT - PBCNT Log Trigger In Progress
        encryptionSelfTestFailure               (23),       -- EQUIPMENT - Encryption Self Test Failure
        lossOfClock                             (24),       -- EQUIPMENT - Loss of Clock
        hardwareConfigurationInProgress         (25),       -- EQUIPMENT - Hardware configuration in progress
        ifcvLaserEnable         (26),                       -- EQUIPMENT - fcvLaserEnable alarm


-- Common Alarms - Database
        databaseCorruption                         (100),
        databaseLockedSoftwareUpgradeInProgress    (101),
        databaseLockedDbRestoreInProgress          (102),
        databaseLockedSysInitInProgress            (103),
        databaseLockedDbAlarmPresent               (104),
        databaseLockedIlfViolation                 (105),
        databaseLockedShelfProvModePresent         (106),
        databaseVersionMismatch                    (107),
        databaseSystemSignatureMismatch            (108),
        noSecondaryDatabase                        (109),
        databaseLockedSecondarySoftwareCorruption  (110),
        databaseLockedSoftwareNotReady             (111),
        softwareNotReady                           (112),
        databaseLockedSoftwareVersionMismatch      (113),

-- Common - SWDL Alarms
        softwareVersionMismatch                 (200),
        softwareStageInProgress                 (201),
        softwareStageFail                       (202),
        bootloaderUpdateInProgress              (203),
        secondarySoftwareCorruption             (204),
        softwareSyncInProgress                  (205),
        noSecondaryStorage                      (206),
        swRepoIncomplete                        (207),
        redundantCfgSwRepoOutOfSync             (208),

-- Common - FWDL Alarms
        firmwareVersionMismatch                 (300),
        firmwareInitInProgress                  (301),
        firmwareBackwardCompatibleLimited       (302),
        firmwareBackwardCompatibleAll           (303),
      --firmwareActivation                      (304),
        firmwareDownloadOrActivationFailure     (305),
        incompatibleFirmware                    (306),
        incompatibleHardware                    (307),
        noFirmware                              (308),

-- Common - SWKEYS Alarms
        ilfViolation                            (350),
        ilfViolationCritical                    (351),
        ilfViolationMajor                       (352),

-- Common - System Alarms
        softwareReset                           (400),

-- Common - NTP Alarms
        sysNtpNotSynchronized                   (450),
        interConnectFailure                     (451),
        sysNameChanged                          (452),
        intRSTPdisabled                         (453),
        defaultSysName                          (454),
        ztpBootInProgress                       (455),
        ztpBootFailure                          (456),

-- Common - HTTPS Alarms
        certificateNotInstalled                 (470),

-- Common - GNMI Alarms
        gnmiCertificateNotInstalled             (471),
        gnmiCertificateValidityExpired          (472),

-- Common - FIPS Alarms
        selfTestInProgress                      (480),
        selfTestFailure                         (481),

-- Common - GCC Alarms
        generalCommunicationChannel0Failure     (500),

-- Power Module Alarms
        powerProblem                            (600),
        powerProblemA                           (601),
        powerProblemB                           (602),

-- Common - RASIS Util Alarms
        rasisUtilCreationInProgress             (700),
        rasisUtilDebugInProgress                (701),

-- Facility Alarms
        opticalPowerReceive                     (1001),
        opticalPowerTransmit                    (1002),
        lossOfSignal                            (1003),
        lossOfFrame                             (1004),
        lossOfMultiframe                        (1005),
        backwardDefectIndication                (1006),
        forwardDefectIndication                 (1007),
        signalDegrade                           (1008),
        trailTraceMismatch                      (1009),
        backwardIncomingAlignmentError          (1010),
        incomingAlignmentError                  (1011),
        alarmIndicationSignal                   (1012),
        openConnectionIndication                (1013),
        locked                                  (1014),
        lossofTandemConnection                  (1015),
        payloadMismatch                         (1016),
        clientSignalFailDefect                  (1017),
        multiplexStructureIdentifierMismatch    (1018),
        lossOfOmfIndication                     (1019),
        lossOfFrameAndLossOfMultiframe          (1020),
        cnOutOfRange                            (1021),
        cnLossOfSynchronization                 (1022),
        highBER                                 (1023),
        localFault                              (1024),
        remoteFault                             (1025),
        lossOfAlignment                         (1026),
        lossOfSynchronization                   (1027),
        lossOfFECAlignment                      (1028),
        remoteLANFault                          (1029),
        lanTransmitLocalFault                   (1030),
        lanTransmitRemoteFault                  (1031),
        lanTransmitOff                          (1032),
        facilityLoopbackActive                  (1033),
        facilityLoopback2Active                 (1034),
        terminalLoopbackActive                  (1035),
        facilityTestsignalActive                (1036),
        terminalTestsignalActive                (1037),
        linkDown                                (1038),
        powerOutOfSpecification                 (1039),
        powerOutOfSpecificationHigh             (1040),
        powerOutOfSpecificationHighL1           (1041),
        powerOutOfSpecificationHighL2           (1042),
        powerOutOfSpecificationHighL3           (1043),
        powerOutOfSpecificationHighL4           (1044),
        powerOutOfSpecificationLow              (1045),
        powerOutOfSpecificationLowL1            (1046),
        powerOutOfSpecificationLowL2            (1047),
        powerOutOfSpecificationLowL3            (1048),
        powerOutOfSpecificationLowL4            (1049),
        fanFilterShouldBeReplaced               (1050),
        fanFilterShouldBeCleaned                (1051),
        equipmentOverTemperature                (1052),
        portLossOfLight                         (1053),
        thresholdCrossingAlertSpanlossVariationTooLow        (1054),
        thresholdCrossingAlertSpanlossVariationTooHigh       (1055),
        thresholdCrossingAlertOscOpticalReceivePowerTooHigh  (1056),
        thresholdCrossingAlertOscOpticalReceivePowerTooLow   (1057),
        thresholdCrossingAlertOscOpticalTransmitPowerTooHigh (1058),
        thresholdCrossingAlertOscOpticalTransmitPowerTooLow  (1059),
        thresholdCrossingAlertOpticalReceivePowerTooHigh     (1060),
        thresholdCrossingAlertOpticalReceivePowerTooLow      (1061),
        thresholdCrossingAlertOpticalTransmitPowerTooHigh    (1062),
        thresholdCrossingAlertOpticalTransmitPowerTooLow     (1063),
        postBlockAutoLaserShutdown              (1064),
        postBlockAutoPowerReduction             (1065),
        postBlockManualLaserShutdown            (1066),
        preBlockSpanAdjustmentInProgress        (1067),
        postBlockSpanAdjustmentInProgress       (1068),
        payloadMissingIndication                (1069),
        manualOverrideActive                    (1070),
        unequippedIndication                    (1071),
        reflectionTooHigh                       (1072),
        oscPowerOutOfSpecificationHigh          (1073),
        oscPowerOutOfSpecificationLow           (1074),
        oscControlFailure                       (1075),
        modeMismatch                            (1076),
        omsPowerOutOfSpecificationHigh          (1077),
        omsPowerOutOfSpecificationLow           (1078),
        otsSpanlossPowerOutOfSpecificationHigh  (1079),
        otsSpanlossPowerOutOfSpecificationLow   (1080),
        autoPowerReduction                      (1081),
        postBlockAutoShutoffDisabled            (1082),
        totalpowerOutOfSpecificationHigh        (1083),
        totalpowerOutOfSpecificationLow         (1084),
        alarmIndicationSignalLine               (1085),
        remoteFailureIndicationLine             (1086),
        bitErrorRateSignalFailLine              (1087),
        bitErrorRateSignalDegradeLine           (1088),
        alarmIndicationSignalGeneric            (1089),
        frameAuthenticationFailure              (1090),
        encryptionSessionFailure01              (1091),
        encryptionSessionFailure02              (1092),
        encryptionSessionFailure03              (1093),
        encryptionSessionFailure04              (1094),
        encryptionHandshakeFailure              (1095),
        trafficSquelchedForEncryption           (1096),
        remoteApsd                              (1097),
        channelPlanMismatch                     (1098),
        errorCode                               (1099),
        lanTransmitErrorCode                    (1100),
        decapsulationFailure                    (1101),
        decapsulationLossOfFrame                (1102),
        clientManagementFrameForwardDefectIndication (1103),
        clientManagementFrameLossOfSignal       (1104),
        clientManagementFrameLossOfSync         (1105),
        clientManagementFrameReverseDefectIndication (1106),
        protocolMiscabledConnection             (1107),
        protocolNeighborFailure                 (1108),
        alarmIndicationSignalTCM1-up            (1109),
        alarmIndicationSignalTCM2-up            (1110),
        alarmIndicationSignalTCM3-up            (1111),
        alarmIndicationSignalTCM4-up            (1112),
        alarmIndicationSignalTCM5-up            (1113),
        alarmIndicationSignalTCM6-up            (1114),
        alarmIndicationSignalTCM1-down          (1115),
        alarmIndicationSignalTCM2-down          (1116),
        alarmIndicationSignalTCM3-down          (1117),
        alarmIndicationSignalTCM4-down          (1118),
        alarmIndicationSignalTCM5-down          (1119),
        alarmIndicationSignalTCM6-down          (1120),
        backwardDefectIndicationTCM1-up         (1121),
        backwardDefectIndicationTCM2-up         (1122),
        backwardDefectIndicationTCM3-up         (1123),
        backwardDefectIndicationTCM4-up         (1124),
        backwardDefectIndicationTCM5-up         (1125),
        backwardDefectIndicationTCM6-up         (1126),
        backwardDefectIndicationTCM1-down       (1127),
        backwardDefectIndicationTCM2-down       (1128),
        backwardDefectIndicationTCM3-down       (1129),
        backwardDefectIndicationTCM4-down       (1130),
        backwardDefectIndicationTCM5-down       (1131),
        backwardDefectIndicationTCM6-down       (1132),
        bitErrorRateSignalDegradeLineTCM1-up    (1133),
        bitErrorRateSignalDegradeLineTCM2-up    (1134),
        bitErrorRateSignalDegradeLineTCM3-up    (1135),
        bitErrorRateSignalDegradeLineTCM4-up    (1136),
        bitErrorRateSignalDegradeLineTCM5-up    (1137),
        bitErrorRateSignalDegradeLineTCM6-up    (1138),
        bitErrorRateSignalDegradeLineTCM1-down  (1139),
        bitErrorRateSignalDegradeLineTCM2-down  (1140),
        bitErrorRateSignalDegradeLineTCM3-down  (1141),
        bitErrorRateSignalDegradeLineTCM4-down  (1142),
        bitErrorRateSignalDegradeLineTCM5-down  (1143),
        bitErrorRateSignalDegradeLineTCM6-down  (1144),
        bitErrorRateSignalFailLineTCM1-up       (1145),
        bitErrorRateSignalFailLineTCM2-up       (1146),
        bitErrorRateSignalFailLineTCM3-up       (1147),
        bitErrorRateSignalFailLineTCM4-up       (1148),
        bitErrorRateSignalFailLineTCM5-up       (1149),
        bitErrorRateSignalFailLineTCM6-up       (1150),
        bitErrorRateSignalFailLineTCM1-down     (1151),
        bitErrorRateSignalFailLineTCM2-down     (1152),
        bitErrorRateSignalFailLineTCM3-down     (1153),
        bitErrorRateSignalFailLineTCM4-down     (1154),
        bitErrorRateSignalFailLineTCM5-down     (1155),
        bitErrorRateSignalFailLineTCM6-down     (1156),
        backwardIncomingAlignmentErrorTCM1-up   (1157),
        backwardIncomingAlignmentErrorTCM2-up   (1158),
        backwardIncomingAlignmentErrorTCM3-up   (1159),
        backwardIncomingAlignmentErrorTCM4-up   (1160),
        backwardIncomingAlignmentErrorTCM5-up   (1161),
        backwardIncomingAlignmentErrorTCM6-up   (1162),
        backwardIncomingAlignmentErrorTCM1-down (1163),
        backwardIncomingAlignmentErrorTCM2-down (1164),
        backwardIncomingAlignmentErrorTCM3-down (1165),
        backwardIncomingAlignmentErrorTCM4-down (1166),
        backwardIncomingAlignmentErrorTCM5-down (1167),
        backwardIncomingAlignmentErrorTCM6-down (1168),
        incomingAlignmentErrorTCM1-up           (1169),
        incomingAlignmentErrorTCM2-up           (1170),
        incomingAlignmentErrorTCM3-up           (1171),
        incomingAlignmentErrorTCM4-up           (1172),
        incomingAlignmentErrorTCM5-up           (1173),
        incomingAlignmentErrorTCM6-up           (1174),
        incomingAlignmentErrorTCM1-down         (1175),
        incomingAlignmentErrorTCM2-down         (1176),
        incomingAlignmentErrorTCM3-down         (1177),
        incomingAlignmentErrorTCM4-down         (1178),
        incomingAlignmentErrorTCM5-down         (1179),
        incomingAlignmentErrorTCM6-down         (1180),
        lossofTandemConnectionTCM1-up           (1181),
        lossofTandemConnectionTCM2-up           (1182),
        lossofTandemConnectionTCM3-up           (1183),
        lossofTandemConnectionTCM4-up           (1184),
        lossofTandemConnectionTCM5-up           (1185),
        lossofTandemConnectionTCM6-up           (1186),
        lossofTandemConnectionTCM1-down         (1187),
        lossofTandemConnectionTCM2-down         (1188),
        lossofTandemConnectionTCM3-down         (1189),
        lossofTandemConnectionTCM4-down         (1190),
        lossofTandemConnectionTCM5-down         (1191),
        lossofTandemConnectionTCM6-down         (1192),
        openConnectionIndicationTCM1-up         (1193),
        openConnectionIndicationTCM2-up         (1194),
        openConnectionIndicationTCM3-up         (1195),
        openConnectionIndicationTCM4-up         (1196),
        openConnectionIndicationTCM5-up         (1197),
        openConnectionIndicationTCM6-up         (1198),
        openConnectionIndicationTCM1-down       (1199),
        openConnectionIndicationTCM2-down       (1200),
        openConnectionIndicationTCM3-down       (1201),
        openConnectionIndicationTCM4-down       (1202),
        openConnectionIndicationTCM5-down       (1203),
        openConnectionIndicationTCM6-down       (1204),
        lockedTCM1-up                           (1205),
        lockedTCM2-up                           (1206),
        lockedTCM3-up                           (1207),
        lockedTCM4-up                           (1208),
        lockedTCM5-up                           (1209),
        lockedTCM6-up                           (1210),
        lockedTCM1-down                         (1211),
        lockedTCM2-down                         (1212),
        lockedTCM3-down                         (1213),
        lockedTCM4-down                         (1214),
        lockedTCM5-down                         (1215),
        lockedTCM6-down                         (1216),
        trailTraceMismatchTCM1-up               (1217),
        trailTraceMismatchTCM2-up               (1218),
        trailTraceMismatchTCM3-up               (1219),
        trailTraceMismatchTCM4-up               (1220),
        trailTraceMismatchTCM5-up               (1221),
        trailTraceMismatchTCM6-up               (1222),
        trailTraceMismatchTCM1-down             (1223),
        trailTraceMismatchTCM2-down             (1224),
        trailTraceMismatchTCM3-down             (1225),
        trailTraceMismatchTCM4-down             (1226),
        trailTraceMismatchTCM5-down             (1227),
        trailTraceMismatchTCM6-down             (1228),
        signalDegradeTCM1-up                    (1229),
        signalDegradeTCM2-up                    (1230),
        signalDegradeTCM3-up                    (1231),
        signalDegradeTCM4-up                    (1232),
        signalDegradeTCM5-up                    (1233),
        signalDegradeTCM6-up                    (1234),
        signalDegradeTCM1-down                  (1235),
        signalDegradeTCM2-down                  (1236),
        signalDegradeTCM3-down                  (1237),
        signalDegradeTCM4-down                  (1238),
        signalDegradeTCM5-down                  (1239),
        signalDegradeTCM6-down                  (1240),
        provisionedTxPowerOutofDeviceRange      (1241),
        autoPowerReductionDra                   (1256),
        osnrModeMismatch                        (1257),
        laserDisabled                           (1258),
        highSER                                 (1259),
        chrdMeasurementInProgress               (1260),
        oscModeMismatch                         (1261),
        pcsFECDegradedSERRx                     (1262),
        localDegradedSERRx                      (1263),
        remoteDegradedSERRx                     (1264),
        lossOfSignalPayload                     (1265),
        lossOfLaneAlignment                     (1266),
        groupIdMismatch                         (1267),
        flexoMapMismatch                        (1268),
        remoteDefectIndication                  (1283),

-- OTN SNCP Alarms
        lockoutOfProtection                     (1301),
        forcedSwitchAwayFromWorking             (1302),
        forcedSwitchAwayFromProtect             (1303),
        automaticSwitchAwayFromWorkingDueToSF   (1304),
        automaticSwitchAwayFromProtectDueToSF   (1305),
        automaticSwitchAwayFromWorkingDueToSD   (1306),
        automaticSwitchAwayFromProtectDueToSD   (1307),
        automaticSwitchDueToWTR                 (1308),
-- OTN SMR Alarms
        smrDisabled                             (1401),
        smrNeighborHelloFailure                 (1402),
        smrActivationFailure                    (1403),

-- DIP Alarms
        dipSessionActive                        (1500),

-- PPP Alarms
        pPPFailure                              (1600),

-- LLDP Alarms
       lldpFail                                 (1700),

-- GRET Alarms
       gretFailure                              (1800),

-- USB Alarms
       invalidUSB                               (1900),

-- EPG Alarms
       noProtectionSwitchPossible               (2000),

-- OTN YPG Alarms
       doNotSwitch                              (2001),
       automaticSwitchAwayFromWorkingDueToBD    (2002),
       automaticSwitchAwayFromProtectDueToBD    (2003),

-- Redundancy Not Provisioned Alarms
       redundancyNotProvisioned                 (2005),

-- Witness port mismatch Alarm
       witnessPortMismatch                      (2006)

    }

FCTcCondType ::= TEXTUAL-CONVENTION
    STATUS  current
    DESCRIPTION
        "The possible transient conditions that are supported by fcTcTrap."
    SYNTAX  INTEGER {
        prod-specific            (0),        -- Project Specific TC (see TC Qualifier)

-- OTN Protection Events
        switchedToProtect                       (10001),
        switchedBackToWorking                   (10002),
        manualSwitchAwayFromWork                (10003),
        manualSwitchAwayFromProtect             (10004),

-- OTN SMR Events
        smrActivationSuccess                    (10051),
        smrActivationFail                       (10052),

-- Database Activation Events
        databaseActivation                      (10100),
        databaseActivationFailure               (10101),
        databaseActivationReversion             (10102),
        databaseActivationSuccess               (10103),
        databaseActivationCanceled              (10104),
        databaseCommitSuccess                   (10105),


-- Firmware Activation Events
        firmwareActivation                      (10200),
        firmwareActivationComplete              (10201),
        firmwareActivationFailure               (10202),

-- SWDL
    -- Software Activation Events
        softwareActivation                      (10300),
        softwareActivationComplete              (10301),
        softwareActivationFailure               (10302),
        softwareReversion                       (10303),
    -- Cancel Validation Timer events
        cancelValidationTimerInProgress         (10304),
        cancelValidationTimerComplete           (10305),
        cancelValidationTimerFailed             (10306),
        uBootFailOver                           (10307),
        softwareFailOver                        (10308),
        bootloaderUpdateSuccess                 (10309),
        bootloaderUpdateFailure                 (10310),
        softwareStageSuccess                    (10311),
        softwareStageFailure                    (10312),
    -- softwareActivationFailure already defined above
        softwareActivationSuccess               (10313),
        softwareCommitSuccess                   (10314),
        softwareCommitFailure                   (10315),
        softwareActivationCanceled              (10316),

-- Date & Time Events
        daylightSavingTimeAdjustment            (10400),
        dateTimeModified                        (10401),

-- NTP Events
        sysNtpSynchronized                      (10500),
        sysNtpSwitchOver                        (10501),

-- System Restart Events
        systemRestartCold                       (10600),
        systemRestartWarm                       (10601),
        systemRestartDbInitialization           (10602),
        systemRestartShfprov                    (10603),
        systemRestart                           (10604),

-- Copy File Events
        copyFileInProgress                      (10700),
        copyFileComplete                        (10701),
        copyFileFailure                         (10702),
        copyFileFailureTransfer                 (10703),
        copyFileFailureMd5check                 (10704),
        copyFileFailureVerification             (10705),

-- File Sync Events
        fileSyncInProgress                      (10750),
        fileSyncCompleted                       (10751),
        fileSyncFailure                         (10752),
        fileAlreadyInSync                       (10753),

-- Equipment Status Events
        equipmentPlugin                         (10800),
        equipmentPlugout                        (10801),

-- Entity Oper Status Change Events
        entityOperStatusChangeToUp              (10900),
        entityOperStatusChangeToDown            (10901),
        entityOperStatusChangeToTesting         (10902),
        entityOperStatusChangeToUnknown         (10903),
        entityOperStatusChangeToDormant         (10904),
        entityOperStatusChangeToNotPresent      (10905),
        entityOperStatusChangeToLowerLayerDown  (10906),

-- Auto/Force Logoff Events
        autoLogoffAssociationCancellation       (11000),
        autoLogoffSessionTimeout                (11001),
        autoLogoffCableDisconnect               (11002),
        autoLogoffPasswordChanged               (11003),
        forcedLogoff                            (11004),

-- IP Events
        ipNotReachable                          (11100),
        ipReachable                             (11101),
        ipPingRequestTimedOut                   (11102),

-- Protocol Events
        lldpNbrInfoChanged                      (11200),

-- OTDR Events
        otdrScanComplete                        (11300),
        otdrScanFailure                         (11301),

-- USB Events
        usbSafeToRemove                         (11400),

-- System Events
        sysZeroizationFailed                    (11500),
        sysZeroizationCompleted                 (11501),

-- Data Encryption Events
        dataEncZeroizationFailed                (11600),
        dataEncZeroizationCompleted             (11601),

-- RASIS Util Events
        rasisUtilCreation                       (11700),
        rasisUtilCreationComplete               (11701),
        rasisUtilCreationFailure                (11702),
        rasisUtilDebug                          (11703),
        rasisUtilDebugComplete                  (11704),

-- SYNC Alarms
        fastStart                               (11800),
        freeRun                                 (11801),
        holdOver                                (11802),
        distShutDwn                             (11803),
        ctnEqptMate                             (11804),

-- SYNC Events
        manualSwitch                            (11900),
        autoSwitch                              (11901),

-- RSTP Events
        spanningTreeNewRoot                     (12000),
        spanningTreeTopologyChange              (12001),

-- WCG Event
        wavelengthContentionGroupChange         (13000),

-- Equipment Port Group Event
        equipmentPortGroupChange                (13001),

-- Scripting Automation Events
        scriptingSuccess                        (13100),
        scriptingFailure                        (13101),

-- Fiber Test Per Dgree Event
        fiberTestPerDegreeNotification          (14000),

-- OTN CHRD Events
        chrdMeasurementStarted                  (15000),
        chrdMeasurementCompleted                (15001),
        chrdProtectPresetSuccess                (15002),
        chrdWorkPresetSuccess                   (15003),
        chrdPresetFailed                        (15004),
        chrdAutoMeasurementSuccessful           (15005),

-- OTN Facility Events
        otuReceivedTraceChange                  (16000),
        oduReceivedTraceChange                  (16001),
        oduReceivedTraceChangeTcm1Up            (16002),
        oduReceivedTraceChangeTcm2Up            (16003),
        oduReceivedTraceChangeTcm3Up            (16004),
        oduReceivedTraceChangeTcm4Up            (16005),
        oduReceivedTraceChangeTcm5Up            (16006),
        oduReceivedTraceChangeTcm6Up            (16007),
        oduReceivedTraceChangeTcm1Down          (16008),
        oduReceivedTraceChangeTcm2Down          (16009),
        oduReceivedTraceChangeTcm3Down          (16010),
        oduReceivedTraceChangeTcm4Down          (16011),
        oduReceivedTraceChangeTcm5Down          (16012),
        oduReceivedTraceChangeTcm6Down          (16013),
        otucnReceivedTraceChange                (16014),
        oducnReceivedTraceChange                (16015),
        oducnReceivedTraceChangeTcm1Up          (16016),
        oducnReceivedTraceChangeTcm2Up          (16017),
        oducnReceivedTraceChangeTcm3Up          (16018),
        oducnReceivedTraceChangeTcm4Up          (16019),
        oducnReceivedTraceChangeTcm5Up          (16020),
        oducnReceivedTraceChangeTcm6Up          (16021),
        oducnReceivedTraceChangeTcm1Down        (16022),
        oducnReceivedTraceChangeTcm2Down        (16023),
        oducnReceivedTraceChangeTcm3Down        (16024),
        oducnReceivedTraceChangeTcm4Down        (16025),
        oducnReceivedTraceChangeTcm5Down        (16026),
        oducnReceivedTraceChangeTcm6Down        (16027)

    }

FCTcaCondType ::= TEXTUAL-CONVENTION
    STATUS  current
    DESCRIPTION
        "The possible threshold crossing alerts that are supported by fcTcaTrap."
    SYNTAX  INTEGER {
        prod-specific            (0),        -- Project Specific TCA (see TCA Qualifier)

-- Port TCA
        tCAOpticalReceivePowerTooLow            (1),
        tCAOpticalReceivePowerTooHigh           (2),
        tCAOpticalTransmitPowerTooLow           (3),
        tCAOpticalTransmitPowerTooHigh          (4),
        tCALaserBiasCurrentTooHigh              (5),
        -- Port Lane 1 TCA
        tCAOpticalReceivePowerLane1TooLow       (6),
        tCAOpticalReceivePowerLane1TooHigh      (7),
        tCAOpticalTransmitPowerLane1TooLow      (8),
        tCAOpticalTransmitPowerLane1TooHigh     (9),
        tCALaserBiasCurrentLane1TooHigh         (10),
        -- Port Lane 2 TCA
        tCAOpticalReceivePowerLane2TooLow       (11),
        tCAOpticalReceivePowerLane2TooHigh      (12),
        tCAOpticalTransmitPowerLane2TooLow      (13),
        tCAOpticalTransmitPowerLane2TooHigh     (14),
        tCALaserBiasCurrentLane2TooHigh         (15),
        -- Port Lane 3 TCA
        tCAOpticalReceivePowerLane3TooLow       (16),
        tCAOpticalReceivePowerLane3TooHigh      (17),
        tCAOpticalTransmitPowerLane3TooLow      (18),
        tCAOpticalTransmitPowerLane3TooHigh     (19),
        tCALaserBiasCurrentLane3TooHigh         (20),
        -- Port Lane 4 TCA
        tCAOpticalReceivePowerLane4TooLow       (21),
        tCAOpticalReceivePowerLane4TooHigh      (22),
        tCAOpticalTransmitPowerLane4TooLow      (23),
        tCAOpticalTransmitPowerLane4TooHigh     (24),
        tCALaserBiasCurrentLane4TooHigh         (25),

        tCATotalOpticalReceivePowerTooLow       (26),
        tCATotalOpticalReceivePowerTooHigh      (27),
        -- L0 specific Port TCA
        tCASpanlossVariationTooLow              (28),
        tCASpanlossVariationTooHigh             (29),
        tCAOpticalReceivePowerOscTooLow         (30),
        tCAOpticalReceivePowerOscTooHigh        (31),
        tCAOpticalTransmitPowerOscTooLow        (32),
        tCAOpticalTransmitPowerOscTooHigh       (33),


-- Facility TCA
        tCAFECCorrectedCodewords                (201),
        tCAFECUncorrectedCodewords              (202),
        tCAFECCorrectedSymbols                  (203),
        tCACodingViolations                     (204),
        tCAErroredSeconds                       (205),
        tCASeverelyErroredSeconds               (206),
        tCAFECUncorrectedBlocks                 (207),
        tCAFECCorrectedBits                     (208),
        tCASDFECCorrectedBits                   (209),
        tCABackgroundBlockErrors                (210),
        tCADelayMeasurement                     (211),
        tCAUnavailableSeconds                   (212),
        tCAErroredBlocks                        (213),
        tCACodingViolationSection               (214),
        tCAErroredSecondSection                 (215),
        tCASeverelyErroredSecondSection         (216),
        tCACodingViolationLine                  (217),
        tCAErroredSecondLine                    (218),
        tCASeverelyErroredSecondLine            (219),
        tCAUnavailableSecondLine                (220),
        tCAseverelyErroredFramingSecondSection  (221),
        tCAErroredSecondEthernet                (222),
        tCASeverelyErroredSecondEthernet        (223),
        tCAUnavailableSecondEthernet            (224),
        tCAInFramesErr                          (225),
        tCAErroredSecondsTCM1-up                (226),
        tCASeverelyErroredSecondsTCM1-up        (227),
        tCABackgroundBlockErrorsTCM1-up         (228),
        tCADelayMeasurementTCM1-up              (229),
        tCAUnavailableSecondsTCM1-up            (230),
        tCAErroredSecondsTCM1-down              (231),
        tCASeverelyErroredSecondsTCM1-down      (232),
        tCABackgroundBlockErrorsTCM1-down       (233),
        tCADelayMeasurementTCM1-down            (234),
        tCAUnavailableSecondsTCM1-down          (235),
        tCAErroredSecondsTCM2-up                (236),
        tCASeverelyErroredSecondsTCM2-up        (237),
        tCABackgroundBlockErrorsTCM2-up         (238),
        tCADelayMeasurementTCM2-up              (239),
        tCAUnavailableSecondsTCM2-up            (240),
        tCAErroredSecondsTCM2-down              (241),
        tCASeverelyErroredSecondsTCM2-down      (242),
        tCABackgroundBlockErrorsTCM2-down       (243),
        tCADelayMeasurementTCM2-down            (244),
        tCAUnavailableSecondsTCM2-down          (245),
        tCAErroredSecondsTCM3-up                (246),
        tCASeverelyErroredSecondsTCM3-up        (247),
        tCABackgroundBlockErrorsTCM3-up         (248),
        tCADelayMeasurementTCM3-up              (249),
        tCAUnavailableSecondsTCM3-up            (250),
        tCAErroredSecondsTCM3-down              (251),
        tCASeverelyErroredSecondsTCM3-down      (252),
        tCABackgroundBlockErrorsTCM3-down       (253),
        tCADelayMeasurementTCM3-down            (254),
        tCAUnavailableSecondsTCM3-down          (255),
        tCAErroredSecondsTCM4-up                (256),
        tCASeverelyErroredSecondsTCM4-up        (257),
        tCABackgroundBlockErrorsTCM4-up         (258),
        tCADelayMeasurementTCM4-up              (259),
        tCAUnavailableSecondsTCM4-up            (260),
        tCAErroredSecondsTCM4-down              (261),
        tCASeverelyErroredSecondsTCM4-down      (262),
        tCABackgroundBlockErrorsTCM4-down       (263),
        tCADelayMeasurementTCM4-down            (264),
        tCAUnavailableSecondsTCM4-down          (265),
        tCAErroredSecondsTCM5-up                (266),
        tCASeverelyErroredSecondsTCM5-up        (267),
        tCABackgroundBlockErrorsTCM5-up         (268),
        tCADelayMeasurementTCM5-up              (269),
        tCAUnavailableSecondsTCM5-up            (270),
        tCAErroredSecondsTCM5-down              (271),
        tCASeverelyErroredSecondsTCM5-down      (272),
        tCABackgroundBlockErrorsTCM5-down       (273),
        tCADelayMeasurementTCM5-down            (274),
        tCAUnavailableSecondsTCM5-down          (275),
        tCAErroredSecondsTCM6-up                (276),
        tCASeverelyErroredSecondsTCM6-up        (277),
        tCABackgroundBlockErrorsTCM6-up         (278),
        tCADelayMeasurementTCM6-up              (279),
        tCAUnavailableSecondsTCM6-up            (280),
        tCAErroredSecondsTCM6-down              (281),
        tCASeverelyErroredSecondsTCM6-down      (282),
        tCABackgroundBlockErrorsTCM6-down       (283),
        tCADelayMeasurementTCM6-down            (284),
        tCAUnavailableSecondsTCM6-down          (285),
        tCAErroredSecondsWAN                    (286),
        tCASeverelyErroredSecondsWAN            (287),
        tCAUnavailableSecondsWAN                (288),
        tCAErroredFramesWAN                     (289),
        tCAProtocolErroredSecond                (290),
        tCAErroredFrames                        (291),
        tCADiscards                             (292),
        tCAFrameCheckSumErrors                  (293),
        tCAOversizeFrames                       (294),
        tCAPauseFrames                          (295),
        tCASDFECUncorrectedBlocks               (296),
        tCAIncomingAlignmentErroredSecond      (297),
        tCABackwardIncomingAlignmentErroredSecond  (298),
        tCAIncomingAlignmentErroredSecondTCM1-down (299),
        tCAIncomingAlignmentErroredSecondTCM2-down (300),
        tCAIncomingAlignmentErroredSecondTCM3-down (301),
        tCAIncomingAlignmentErroredSecondTCM4-down (302),
        tCAIncomingAlignmentErroredSecondTCM5-down (303),
        tCAIncomingAlignmentErroredSecondTCM6-down (304),
        tCABackwardIncomingAlignmentErroredSecondTCM1-down (305),
        tCABackwardIncomingAlignmentErroredSecondTCM2-down (306),
        tCABackwardIncomingAlignmentErroredSecondTCM3-down (307),
        tCABackwardIncomingAlignmentErroredSecondTCM4-down (308),
        tCABackwardIncomingAlignmentErroredSecondTCM5-down (309),
        tCABackwardIncomingAlignmentErroredSecondTCM6-down (310),
        tCAIncomingAlignmentErroredSecondTCM1-up (311),
        tCAIncomingAlignmentErroredSecondTCM2-up (312),
        tCAIncomingAlignmentErroredSecondTCM3-up (313),
        tCAIncomingAlignmentErroredSecondTCM4-up (314),
        tCAIncomingAlignmentErroredSecondTCM5-up (315),
        tCAIncomingAlignmentErroredSecondTCM6-up (316),
        tCABackwardIncomingAlignmentErroredSecondTCM1-up (317),
        tCABackwardIncomingAlignmentErroredSecondTCM2-up (318),
        tCABackwardIncomingAlignmentErroredSecondTCM3-up (319),
        tCABackwardIncomingAlignmentErroredSecondTCM4-up (320),
        tCABackwardIncomingAlignmentErroredSecondTCM5-up (321),
        tCABackwardIncomingAlignmentErroredSecondTCM6-up (322)
    }

FCStdObjectIndex ::= TEXTUAL-CONVENTION
    STATUS      current
    DESCRIPTION
        "A sequencial index."
    SYNTAX      Unsigned32 (1..4294967295)

FCStdTypeIndex ::= TEXTUAL-CONVENTION
    STATUS      current
    DESCRIPTION
        "A sequencial subindex."
    SYNTAX      Unsigned32 (1..4294967295)

FCTrapHistIndex ::= TEXTUAL-CONVENTION
    STATUS      current
    DESCRIPTION
        "A sequencial Trap index."
    SYNTAX      Unsigned32 (1..4294967295)

END
