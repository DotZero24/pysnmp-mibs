ALCATEL-IND1-CONFIG-MGR-MIB DEFINITIONS ::= BEGIN


	IMPORTS
		OBJECT-TYPE,
		MODULE-IDENTITY,
		NOTIFICATION-TYPE,
		OBJECT-IDENTITY		FROM SNMPv2-SMI
		DisplayString		FROM SNMPv2-TC
		SnmpAdminString		FROM SNMP-FRAMEWORK-MIB
		NOTIFICATION-GROUP,
		MODULE-COMPLIANCE,
		OBJECT-GROUP		FROM SNMPv2-CONF
		softentIND1Confmgr	FROM ALCATEL-IND1-BASE
		;



	alcatelIND1ConfigMgrMIB   MODULE-IDENTITY
		LAST-UPDATED 	 "200704030000Z"
		ORGANIZATION 	 "Alcatel-Lucent"
		CONTACT-INFO
			"Please consult with Customer Service to ensure the most appropriate
	   	         version of this document is used with the products in question:

			 Alcatel-Lucent, Enterprise Solutions Division
		         (Formerly Alcatel Internetworking, Incorporated)
			       26801 West Agoura Road
			      Agoura Hills, CA  91301-5122
			      United States Of America

	    		 Telephone:        North America  +1 800 995 2696
				 	   Latin America  +1 877 919 9526
				           Europe         +31 23 556 0100
				           Asia           +65 394 7933
				           All Other      +1 818 878 4507

	    		 Electronic Mail:         support@ind.alcatel.com
	    		 World Wide Web:          http://alcatel-lucent.com/wps/portal/enterprise
	    	   	 File Transfer Protocol:  ftp://ftp.ind.alcatel.com/pub/products/mibs"

	DESCRIPTION
	    "This module describes an authoritative enterprise-specific Simple
             Network Management Protocol (SNMP) Management Information Base (MIB):

                 For the Birds Of Prey Product Line
                 Configuration Manager Subsystem.

             The right to make changes in specification and other information
             contained in this document without prior notice is reserved.

             No liability shall be assumed for any incidental, indirect, special, or
             consequential damages whatsoever arising from or related to this
             document or the information contained herein.

             Vendors, end-users, and other interested parties are granted
             non-exclusive license to use this specification in connection with
             management of the products for which it is intended to be used.

                         Copyright (C) 1995-2007 Alcatel-Lucent
                             ALL RIGHTS RESERVED WORLDWIDE"

	REVISION	 "200704030000Z"
	DESCRIPTION
		"The latest version of this MIB Module."

	::= { softentIND1Confmgr 1}


	alcatelIND1ConfigMgrMIBObjects  OBJECT-IDENTITY
        	STATUS  current
        	DESCRIPTION
            	    "Branch For Configuration Manager Subsystem Managed Objects."
        ::= { alcatelIND1ConfigMgrMIB 1 }


    	alcatelIND1ConfigMgrMIBConformance  OBJECT-IDENTITY
        	STATUS  current
        	DESCRIPTION
            	    "Branch For Configuration Manager Subsystem Conformance Information."
        ::= { alcatelIND1ConfigMgrMIB 2 }


    	alcatelIND1ConfigMgrMIBGroups  OBJECT-IDENTITY
        	STATUS  current
        	DESCRIPTION
            	    "Branch For Configuration Manager Subsystem Units Of Conformance."
        ::= { alcatelIND1ConfigMgrMIBConformance 1 }


    	alcatelIND1ConfigMgrMIBCompliances  OBJECT-IDENTITY
        	STATUS  current
        	DESCRIPTION
            	    "Branch For Configuration Manager Subsystem Compliance Statements."
        ::= { alcatelIND1ConfigMgrMIBConformance 2 }


--
-- Configuration Manager
--

	configManager	OBJECT IDENTIFIER ::= { alcatelIND1ConfigMgrMIBObjects 1 }


	configFileName		OBJECT-TYPE
		SYNTAX		DisplayString (SIZE (0..30))
		MAX-ACCESS	read-write
		STATUS		current
		DESCRIPTION
			"The name of the configuration file to be
			 read by the device. The file specified
			 should be present on the device."
		DEFVAL  { "" }
		::= { configManager 1 }


	configFileAction	OBJECT-TYPE
		SYNTAX		INTEGER {
				none(1),
				checkSyntaxOnly(2),
				apply(3)
				}
		MAX-ACCESS 	read-write
		STATUS		current
		DESCRIPTION
			"Triggers application of the configuration
			 file specified by the configInputFileName.
			 A value of checkSyntax causes configInputFile
			 to be checked for syntax, with no changes to
			 device configuration. A value of
			 checkSyntaxAndApply causes the configInputFile
			 to be applied to the device configuration.A value
			 of none indicates no action has been triggered."
		DEFVAL  { none }
		::= { configManager 2 }


	configErrorFileName	OBJECT-TYPE
		SYNTAX		DisplayString (SIZE (0..255))
		MAX-ACCESS	read-only
		STATUS		current
		DESCRIPTION
			"The name of the file containing the error
			 messages generated by the device during file
			 configuration."
		DEFVAL  { "" }
		::= { configManager 3 }


	configFileStatus	OBJECT-TYPE
		SYNTAX		INTEGER {
					noneAvail(1),
					inProgress(2),
					completeNoErrors(3),
					completeErrors(4)
					}
		MAX-ACCESS		read-only
		STATUS		current
		DESCRIPTION
			"Status of most recent application of configuration
			 file to the device."
		DEFVAL  { noneAvail }
		::= { configManager 4 }


	configFileMode		OBJECT-TYPE
		SYNTAX		INTEGER {
				none(1),
				verbose(2)
				}
		MAX-ACCESS	read-write
		STATUS		current
		DESCRIPTION
			"The verbose mode displays all configuration commands
			 and errors when the file is applied on the console
			 screen.  Ignored unless set from command line interface."
		DEFVAL  { none }
		::= { configManager 5 }


	configTimerFileName	OBJECT-TYPE
		SYNTAX		DisplayString (SIZE (0..30))
		MAX-ACCESS	read-write
		STATUS		current
		DESCRIPTION
			"The name of the configuration file to be read later
			 by the device."
		DEFVAL  { "" }
		::= { configManager 6 }


	configTimerFileTime	OBJECT-TYPE
		SYNTAX		DisplayString (SIZE (0..16))
		MAX-ACCESS	read-write
		STATUS		current
		DESCRIPTION
			"The local time when the configuration file
			 will be read by the device. This object is
			 only set if the configInputFile must be applied
			 at a later time.
			 The following formats are valid:

			  MM/DD/YYYY hh:mm

                          MM/DD/YY hh:mm

                          MM/DD hh:mm -  uses current year if
					 after current date and time,
					 next year otherwise.

                          hh:mm -  uses today's date if later
				   than current time,
			           tommorow's date otherwise.
                      where
                        YY - year   (0-38,99)
                        MM - month  (1-12)
                        DD - day    (1-31)
                        hh - hour   (0-23)
                        mm - minute (0-59)"
		DEFVAL  { "" }
		::= { configManager 7 }


	configTimerFileStatus	OBJECT-TYPE
		SYNTAX		INTEGER {
				idle(1),
				pending(2),
				inProgress(3)
				}
		MAX-ACCESS	read-only
		STATUS		current
		DESCRIPTION
			"The current status of the ASCII configuration
			 timer."
		DEFVAL  { idle }
		::= { configManager 8 }


	configTimerClear	OBJECT-TYPE
		SYNTAX		INTEGER (1..1)
		MAX-ACCESS	read-write
		STATUS		current
		DESCRIPTION
			"A set of this object causes the ASCII
			 configuration timer to be cleared."
		DEFVAL  { 1 }
		::= { configManager 9 }


	configSnapshotFileName	OBJECT-TYPE
		SYNTAX		DisplayString (SIZE (0..30))
		MAX-ACCESS	read-write
		STATUS		current
		DESCRIPTION
			"The name of the configuration snap-shot file
			 to be generated by the device."
		DEFVAL  { "" }
		::= { configManager 10 }


	configSnapshotAction	OBJECT-TYPE
		SYNTAX		INTEGER (1..1)
		MAX-ACCESS	read-write
		STATUS		current
		DESCRIPTION
			"A set of this object causes the configuration
			 snap-shot to be generated by the device."
		DEFVAL  { 1 }
		::= { configManager 11 }


	configSnapshotAllSelect			OBJECT-TYPE
		SYNTAX				INTEGER (0..1)
		MAX-ACCESS			read-write
		STATUS				current
		DESCRIPTION
			"A set of this object causes
			 all application configuration data to be
			 included in the snap-shot file generated by
			 the device."
		DEFVAL  { 0 }
		::= { configManager 12 }


	configSnapshotVlanSelect		OBJECT-TYPE
		SYNTAX				INTEGER (0..1)
		MAX-ACCESS			read-write
		STATUS				current
		DESCRIPTION
			"A set of this object causes
			 Vlan configuration data to be
			 included in the snap-shot file generated by
			 the device."
		DEFVAL  { 0 }
		::= { configManager 13 }


	configSnapshotSpanningTreeSelect	OBJECT-TYPE
		SYNTAX				INTEGER (0..1)
		MAX-ACCESS			read-write
		STATUS				current
		DESCRIPTION
			"A set of this object causes
			 Spanning Tree configuration data to be
			 included in the snap-shot file generated by
			 the device."
		DEFVAL  { 0 }
		::= { configManager 14 }


	configSnapshotQOSSelect		OBJECT-TYPE
		SYNTAX			INTEGER (0..1)
		MAX-ACCESS		read-write
		STATUS			current
		DESCRIPTION
			"A set of this object causes
			 QOS configuration data to be included
			 in the snap-shot file generated by the
			 the device."
		DEFVAL  { 0 }
		::= { configManager 15 }


	configSnapshotIPSelect		OBJECT-TYPE
		SYNTAX			INTEGER (0..1)
		MAX-ACCESS		read-write
		STATUS			current
		DESCRIPTION
			"A set of this object causes
			 IP configuration data to be included
			 in the snap-shot file generated by the
			 the device."
		DEFVAL  { 0 }
		::= { configManager 16 }


	configSnapshotIPXSelect		OBJECT-TYPE
		SYNTAX			INTEGER (0..1)
		MAX-ACCESS		read-write
		STATUS			current
		DESCRIPTION
			"A set of this object causes
			 IPX configuration data to be included
			 in the snap-shot file generated by the
			 the device."
		DEFVAL  { 0 }
		::= { configManager 17 }


	configSnapshotIPMSSelect	OBJECT-TYPE
		SYNTAX			INTEGER (0..1)
		MAX-ACCESS		read-write
		STATUS			current
		DESCRIPTION
			"A set of this object causes
			 IPMS configuration data to be included
			 in the snap-shot file generated by the
			 the device."
		DEFVAL  { 0 }
		::= { configManager 18 }

	configSnapshotAAASelect		OBJECT-TYPE
		SYNTAX			INTEGER (0..1)
		MAX-ACCESS		read-write
		STATUS			current
		DESCRIPTION
			"A set of this object causes
			 AAA configuration data to be included
			 in the snap-shot file generated by the
			 the device."
		DEFVAL  { 0 }
		::= { configManager 19 }


	configSnapshotSNMPSelect	OBJECT-TYPE
		SYNTAX			INTEGER (0..1)
		MAX-ACCESS		read-write
		STATUS			current
		DESCRIPTION
			"A set of this object causes
			 SNMP configuration data to be included
			 in the snap-shot file generated by the
			 the device."
		DEFVAL  { 0 }
		::= { configManager 20 }


	configSnapshot8021QSelect	OBJECT-TYPE
		SYNTAX			INTEGER (0..1)
		MAX-ACCESS		read-write
		STATUS			current
		DESCRIPTION
			"A set of this object causes
			 802.1Q configuration data to be included
			 in the snap-shot file generated by the
			 the device."
		DEFVAL  { 0 }
		::= { configManager 21 }


	configSnapshotLinkAggregateSelect	OBJECT-TYPE
		SYNTAX			INTEGER (0..1)
		MAX-ACCESS		read-write
		STATUS			current
		DESCRIPTION
			"A set of this object causes
			 link aggregation configuration data to
			 be included in the snap-shot file generated
			 by the device."
		DEFVAL  { 0 }
		::= { configManager 22 }


	configSnapshotPortMirrorSelect	OBJECT-TYPE
		SYNTAX			INTEGER (0..1)
		MAX-ACCESS		read-write
		STATUS			current
		DESCRIPTION
			"A set of this object causes
			 port mirroring configuration data to
			 be included in the snap-shot file generated
			 by the device."
		DEFVAL  { 0 }
		::= { configManager 23 }


	configSnapshotXIPSelect		OBJECT-TYPE
		SYNTAX			INTEGER (0..1)
		MAX-ACCESS		read-write
		STATUS			current
		DESCRIPTION
			"A set of this object causes
			 proprietary inter-switch protocol configuration
			 data to be included in the snap-shot file generated
			 by the device."
		DEFVAL  { 0 }
		::= { configManager 24 }


	configSnapshotHealthMonitorSelect	OBJECT-TYPE
		SYNTAX			INTEGER (0..1)
		MAX-ACCESS		read-write
		STATUS			current
		DESCRIPTION
			"A set of this object causes
			 health monitoring configuration data to
			 be included in the snap-shot file generated
			 by the device."
		DEFVAL  { 0 }
		::= { configManager 25 }


	configSnapshotBootPSelect	OBJECT-TYPE
		SYNTAX			INTEGER (0..1)
		MAX-ACCESS		read-write
		STATUS			current
		DESCRIPTION
			"A set of this object causes
			 bootp configuration data to
			 be included in the snap-shot file generated
			 by the device."
		DEFVAL  { 0 }
		::= { configManager 26 }


	configSnapshotBridgeSelect	OBJECT-TYPE
		SYNTAX			INTEGER (0..1)
		MAX-ACCESS		read-write
		STATUS			current
		DESCRIPTION
			"A set of this object causes
			 source-learning configuration data to
			 be included in the snap-shot file generated
			 by the device."
		DEFVAL  { 0 }
		::= { configManager 27 }


	configSnapshotChassisSelect	OBJECT-TYPE
		SYNTAX			INTEGER (0..1)
		MAX-ACCESS		read-write
		STATUS			current
		DESCRIPTION
			"A set of this object causes
			 the chassis configuration data to
			 be included in the snap-shot file generated
			 by the device."
		DEFVAL  { 0 }
		::= { configManager 28 }


	configSnapshotInterfaceSelect	OBJECT-TYPE
		SYNTAX			INTEGER (0..1)
		MAX-ACCESS		read-write
		STATUS			current
		DESCRIPTION
			"A set of this object causes
			 ethernet interface configuration data to
			 be included in the snap-shot file generated
			 by the device."
		DEFVAL  { 0 }
		::= { configManager 29 }


	configSnapshotPolicySelect	OBJECT-TYPE
		SYNTAX			INTEGER (0..1)
		MAX-ACCESS		read-write
		STATUS			current
		DESCRIPTION
			"A set of this object causes
			 policy manager configuration data to
			 be included in the snap-shot file generated
			 by the device."
		DEFVAL  { 0 }
		::= { configManager 30 }


	configSnapshotSessionSelect	OBJECT-TYPE
		SYNTAX			INTEGER (0..1)
		MAX-ACCESS		read-write
		STATUS			current
		DESCRIPTION
			"A set of this object causes
			 the user-session configuration data to
			 be included in the snap-shot file generated
			 by the device."
		DEFVAL  { 0 }
		::= { configManager 31 }


	configSnapshotServerLoadBalanceSelect	OBJECT-TYPE
		SYNTAX			INTEGER (0..1)
		MAX-ACCESS		read-write
		STATUS			current
		DESCRIPTION
			"A set of this object causes
			 server load balancing configuration data to
			 be included in the snap-shot file generated
			 by the device."
		DEFVAL  { 0 }
		::= { configManager 32 }


	configSnapshotSystemServiceSelect	OBJECT-TYPE
		SYNTAX			INTEGER (0..1)
		MAX-ACCESS		read-write
		STATUS			current
		DESCRIPTION
			"A set of this object causes
			 system services configuration data to
			 be included in the snap-shot file generated
			 by the device."
		DEFVAL  { 0 }
		::= { configManager 33 }


	configSnapshotVRRPSelect	OBJECT-TYPE
		SYNTAX			INTEGER (0..1)
		MAX-ACCESS		read-write
		STATUS			current
		DESCRIPTION
			"A set of this object causes
			 VRRP configuration data to
			 be included in the snap-shot file generated
			 by the device."
		DEFVAL  { 0 }
		::= { configManager 34 }


	configSnapshotWebSelect		OBJECT-TYPE
		SYNTAX			INTEGER (0..1)
		MAX-ACCESS		read-write
		STATUS			current
		DESCRIPTION
			"A set of this object causes
			 web manager configuration data to
			 be included in the snap-shot file generated
			 by the device."
		DEFVAL  { 0 }
		::= { configManager 35 }


	configSnapshotRIPSelect		OBJECT-TYPE
		SYNTAX			INTEGER (0..1)
		MAX-ACCESS		read-write
		STATUS			current
		DESCRIPTION
			"A set of this object causes
			 RIP configuration data to
			 be included in the snap-shot file generated
			 by the device."
		DEFVAL  { 0 }
		::= { configManager 36 }


	configSnapshotOSPFSelect	OBJECT-TYPE
		SYNTAX			INTEGER (0..1)
		MAX-ACCESS		read-write
		STATUS			current
		DESCRIPTION
			"A set of this object causes
			 OSPF configuration data to
			 be included in the snap-shot file generated
			 by the device."
		DEFVAL  { 0 }
		::= { configManager 37 }


	configSnapshotBGPSelect		OBJECT-TYPE
		SYNTAX			INTEGER (0..1)
		MAX-ACCESS		read-write
		STATUS			current
		DESCRIPTION
			"A set of this object causes
			 BGP configuration data to
			 be included in the snap-shot file generated
			 by the device."
		DEFVAL  { 0 }
		::= { configManager 38 }


	configSnapshotIPRMSelect	OBJECT-TYPE
		SYNTAX			INTEGER (0..1)
		MAX-ACCESS		read-write
		STATUS			current
		DESCRIPTION
			"A set of this object causes
			 IPRM routing configuration data to
			 be included in the snap-shot file generated
			 by the device."
		DEFVAL  { 0 }
		::= { configManager 39 }


	configSnapshotIPMRSelect	OBJECT-TYPE
		SYNTAX			INTEGER (0..1)
		MAX-ACCESS		read-write
		STATUS			current
		DESCRIPTION
			"A set of this object causes
			 IP multicast routing configuration data to
			 be included in the snap-shot file generated
			 by the device."
		DEFVAL  { 0 }
		::= { configManager 40 }


	configSnapshotModuleSelect	OBJECT-TYPE
		SYNTAX			INTEGER (0..1)
		MAX-ACCESS		read-write
		STATUS			current
		DESCRIPTION
			"A set of this object causes
			 module configuration data to
			 be included in the snap-shot file generated
			 by the device."
		DEFVAL  { 0 }
		::= { configManager 41 }

	configTechSupportLogAction	OBJECT-TYPE
		SYNTAX			INTEGER {
					   notSiginificant(0),
					   techSupportBasic(1),
					   techSupportL2(2),
					   techSupportL3(3),
					   techSupportL3Rip(4),
					   techSupportL3Ipx(5),
					   techSupportL3Ospf(6),
					   techSupportL3Bgp(7),
					   techSupportL3Pimsm(8),
					   techSupportL3Mroute(9),
					   techSupportL3Dvmrp(10),
					   techSupportL3IPv6(11),
                                           techSupportL3RIPng(12),
                                           techSupportL3OSPF3(13),
                                           techSupportL3Isis(14),
                                           techSupportL3Pim6(15)
                                        -- techSupportL3IPsec(16),
                                        -- techSupportL3Bfd(17)

				}
		MAX-ACCESS		read-write
		STATUS			current
		DESCRIPTION
			"A set of this object causes
			 a tech_support.log file to be created
			 containing switch information useful to
			 a technical support group."
		DEFVAL  { techSupportBasic }
		::= { configManager 42 }

	configWriteMemory		OBJECT-TYPE
		SYNTAX			INTEGER (0..1)
		MAX-ACCESS		read-write
		STATUS			current
		DESCRIPTION
			"A set of this object causes
			 the entire switch snap-shot configuration to
			 be stored in the boot.cfg file in the
			 working directory."
		DEFVAL  { 0 }
		::= { configManager 43 }

	configErrorFileMaximum		OBJECT-TYPE
		SYNTAX			INTEGER (1..25)
		MAX-ACCESS		read-write
		STATUS			current
		DESCRIPTION
			"The maximum number of error files which may be
			 present on a switch.  Each time a new error file
			 is created, all but the newest configErrorFileMaxNum
			 error files are deleted."
		DEFVAL  { 1 }
		::= { configManager 44 }

	configChangeStatus	OBJECT-TYPE
		SYNTAX		INTEGER {
				identical(1),
				different(2)
				}
		MAX-ACCESS	read-only
		STATUS		current
		DESCRIPTION
			"The current state of the running configuration with respect
			 to the saved configuration."
		DEFVAL  { identical }
		::= { configManager 45 }

	configSnapshotRDPSelect		OBJECT-TYPE
		SYNTAX			INTEGER (0..1)
		MAX-ACCESS		read-write
		STATUS			current
		DESCRIPTION
			"A set of this object causes
			 RDP configuration data to
			 be included in the snap-shot file generated
			 by the device."
		DEFVAL  { 0 }
		::= { configManager 46 }

	configSnapshotIPv6Select	OBJECT-TYPE
		SYNTAX			INTEGER (0..1)
		MAX-ACCESS		read-write
		STATUS			current
		DESCRIPTION
			"A set of this object causes
			 IPv6 configuration data to
			 be included in the snap-shot file generated
			 by the device."
		DEFVAL  { 0 }
		::= { configManager 47 }

	configSnapshotRIPngSelect	OBJECT-TYPE
		SYNTAX			INTEGER (0..1)
		MAX-ACCESS		read-write
		STATUS			current
		DESCRIPTION
			"A set of this object causes
			 RIPng configuration data to
			 be included in the snap-shot file generated
			 by the device."
		DEFVAL  { 0 }
		::= { configManager 48 }

	configSnapshotAtmSelect	OBJECT-TYPE
		SYNTAX			INTEGER (0..1)
		MAX-ACCESS		read-write
		STATUS			current
		DESCRIPTION
			"A set of this object causes
			 ATM configuration data to
			 be included in the snap-shot file generated
			 by the device. NOT SUPPORTED."
		DEFVAL  { 0 }
		::= { configManager 49 }


	configSnapshotSonetSelect	OBJECT-TYPE
		SYNTAX			INTEGER (0..1)
		MAX-ACCESS		read-write
		STATUS			current
		DESCRIPTION
			"A set of this object causes
			 Sonet configuration data to
			 be included in the snap-shot file generated
			 by the device. NOT SUPPORTED."
		DEFVAL  { 0 }
		::= { configManager 50 }

	configSnapshotNTPSelect	OBJECT-TYPE
		SYNTAX			INTEGER (0..1)
		MAX-ACCESS		read-write
		STATUS			current
		DESCRIPTION
			"A set of this object causes
			 NTP configuration data to
			 be included in the snap-shot file generated
			 by the device."
		DEFVAL  { 0 }
		::= { configManager 51 }


	configSnapshotPortMappingSelect	OBJECT-TYPE
		SYNTAX			INTEGER (0..1)
		MAX-ACCESS		read-write
		STATUS			current
		DESCRIPTION
			"A set of this object causes
			 Port Mapping configuration data to
			 be included in the snap-shot file generated
			 by the device."
		DEFVAL  { 0 }
		::= { configManager 52 }


	configSnapshotOSPF3Select	OBJECT-TYPE
		SYNTAX			INTEGER (0..1)
		MAX-ACCESS		read-write
		STATUS			current
		DESCRIPTION
			"A set of this object causes
			 OSPF3 configuration data to
			 be included in the snap-shot file generated
			 by the device."
		DEFVAL  { 0 }
		::= { configManager 53 }


	configWriteMemoryStatus	OBJECT-TYPE
		SYNTAX		INTEGER {
					noneAvail(1),
					inProgress(2),
					completeNoErrors(3),
					completeErrors(4)
					}
		MAX-ACCESS		read-only
		STATUS		current
		DESCRIPTION
			"Status of most recent wwrite memory action."
		DEFVAL  { noneAvail }
		::= { configManager 54 }


	configSnapshotStackSelect	OBJECT-TYPE
		SYNTAX			INTEGER (0..1)
		MAX-ACCESS		read-write
		STATUS			current
		DESCRIPTION
			"A set of this object causes
			 STack Manager configuration data to
			 be included in the snap-shot file generated
			 by the device."
		DEFVAL  { 0 }
		::= { configManager 55 }

       configSnapshotISISSelect	OBJECT-TYPE
		SYNTAX			INTEGER (0..1)
		MAX-ACCESS		read-write
		STATUS			current
		DESCRIPTION
			"A set of this object causes
			 ISIS configuration data to
			 be included in the snap-shot file generated
			 by the device."
		DEFVAL  { 0 }
		::= { configManager 56 }


 	configSnapshotEOAMSelect  OBJECT-TYPE
                SYNTAX                  INTEGER (0..1)
                MAX-ACCESS              read-write
                STATUS                  current
                DESCRIPTION
                        "A set of this object causes
                         Ethernet OAM configuration data to
                         be included in the snap-shot file generated
                         by the device."
                DEFVAL  { 0 }
                ::= { configManager 57 }


	configSnapshotUDLDSelect        OBJECT-TYPE
                SYNTAX                  INTEGER (0..1)
                MAX-ACCESS              read-write
                STATUS                  current
                DESCRIPTION
                        "A set of this object causes
                         UDLD configuration data to
                         be included in the snap-shot file generated
                         by the device."
                DEFVAL  { 0 }
                ::= { configManager 58 }

	configSnapshotNETSECSelect        OBJECT-TYPE
                SYNTAX                  INTEGER (0..1)
                MAX-ACCESS              read-write
                STATUS                  current
                DESCRIPTION
                        "A set of this object causes
                         NETSEC configuration data to
                         be included in the snap-shot file generated
                         by the device."
                DEFVAL  { 0 }
                ::= { configManager 59 }

	configSnapshotIPsecSelect        OBJECT-TYPE
                SYNTAX                  INTEGER (0..1)
                MAX-ACCESS              read-write
                STATUS                  current
                DESCRIPTION
                        "A set of this object causes
                         IP Security configuration data to
                         be included in the snap-shot file generated
                         by the device."
                DEFVAL  { 0 }
                ::= { configManager 60 }
	configSnapshotBFDSelect        OBJECT-TYPE
                SYNTAX                  INTEGER (0..1)
                MAX-ACCESS              read-write
                STATUS                  current
                DESCRIPTION
                        "A set of this object causes
                         BFD configuration data to
                         be included in the snap-shot file generated
                         by the device."
                DEFVAL  { 0 }
                ::= { configManager 61 }

	configSnapshotErpSelect        OBJECT-TYPE
		SYNTAX                  INTEGER (0..1)
		MAX-ACCESS              read-write
		STATUS                  current
		DESCRIPTION
			"A set of this object causes
			 ERP configuration data to
			 be included in the snap-shot file generated
			 by the device."
		DEFVAL  { 0 }
	::= { configManager 62 }

		configSnapshotMPLSSelect        OBJECT-TYPE
                SYNTAX                  INTEGER (0..1)
                MAX-ACCESS              read-write
                STATUS                  current
                DESCRIPTION
                        "A set of this object causes
                         MPLS configuration data to
                         be included in the snap-shot file generated
                         by the device."
                DEFVAL  { 0 }
                ::= { configManager 63 }

	configSnapshotEFMOAMSelect        OBJECT-TYPE
                SYNTAX                  INTEGER (0..1)
                MAX-ACCESS              read-write
                STATUS                  current
                DESCRIPTION
                        "A set of this object causes
                         EFMOAM configuration data to
                         be included in the snap-shot file generated
                         by the device."
                DEFVAL  { 0 }
                ::= { configManager 64 }

	configSnapshotLBDSelect        OBJECT-TYPE
		SYNTAX                  INTEGER (0..1)
		MAX-ACCESS              read-write
		STATUS                  current
		DESCRIPTION
			"A set of this object causes
			Loop Back Detection configuration data to
			be included in the snap-shot file generated
			by the device."
		DEFVAL  { 0 }
		::= { configManager 65 }

        configSnapshotSAASelect        OBJECT-TYPE
                SYNTAX                  INTEGER (0..1)
                MAX-ACCESS              read-write
                STATUS                  current
                DESCRIPTION
                        "A set of this object causes
                         SAA configuration data to
                         be included in the snap-shot file generated
                         by the device."
                DEFVAL  { 0 }
                ::= { configManager 66 }

	configSnapshotDhcpSrvSelect OBJECT-TYPE
                SYNTAX                  INTEGER (0..1)
                MAX-ACCESS              read-write
                STATUS                  current
                DESCRIPTION
                        "A set of this object causes
			DHCP Server configuration data to
			be included in the snap-shot file generated
                         by the device."
                DEFVAL  { 0 }
                ::= { configManager 67 }

	configSnapshotLLDPSelect OBJECT-TYPE
                 SYNTAX                  INTEGER (0..1)
                 MAX-ACCESS              read-write
                 STATUS                  current
                 DESCRIPTION
                         "A set of this object causes
 			LLDP configuration data to
 			be included in the snap-shot file generated
                         by the device."
                 DEFVAL  { 0 }
                 ::= { configManager 68 }

	configSnapshotLFPSelect OBJECT-TYPE
                SYNTAX                  INTEGER (0..1)
                MAX-ACCESS              read-write
                STATUS                  current
                DESCRIPTION
                        "A set of this object causes
			LFP configuration data to
			be included in the snap-shot file generated
                         by the device."
                DEFVAL  { 0 }
                ::= { configManager 69 }

	configSnapshotDHLSelect OBJECT-TYPE
                SYNTAX                  INTEGER (0..1)
                MAX-ACCESS              read-write
                STATUS                  current
                DESCRIPTION
                        "A set of this object causes
			DHL configuration data to
                        be included in the snap-shot file generated
                         by the device."
                DEFVAL  { 0 }
                ::= { configManager 70 }

		configSnapshotWccpSelect OBJECT-TYPE
                SYNTAX                  INTEGER (0..1)
                MAX-ACCESS              read-write
                STATUS                  current
                DESCRIPTION
                        "A set of this object causes
			WCCP configuration data to
                        be included in the snap-shot file generated
                         by the device."
                DEFVAL  { 0 }
                ::= { configManager 71 }

        configSnapshotPPPOEIASelect     OBJECT-TYPE
                SYNTAX                  INTEGER (0..1)
                MAX-ACCESS              read-write
                STATUS                  current
                DESCRIPTION
                        "A set of this object causes
                         PPPoE-IA configuration data to
                         be included in the snap-shot file generated
                         by the device."
                DEFVAL  { 0 }
                ::= { configManager 72 }

	configSnapshotTESTOAMSelect     OBJECT-TYPE
                SYNTAX                  INTEGER (0..1)
                MAX-ACCESS              read-write
                STATUS                  current
                DESCRIPTION
                        "A set of this object causes
                         TESTOAM configuration data to
                         be included in the snap-shot file generated
                         by the device."
                DEFVAL  { 0 }
                ::= { configManager 73 }

        configSnapshotSIPSelect OBJECT-TYPE

                SYNTAX                  INTEGER (0..1)
                 MAX-ACCESS              read-write
                 STATUS                  current
                 DESCRIPTION
                         "A set of this object causes
                         SIP configuration data to
                         be included in the snap-shot file generated
                          by the device."
                 DEFVAL  { 0 }
                 ::= { configManager 74 }

	configSnapshotUNPSelect     OBJECT-TYPE
                 SYNTAX                  INTEGER (0..1)
                 MAX-ACCESS              read-write
                 STATUS                  current
                 DESCRIPTION
                         "A set of this object causes
                          vNP configuration data to
                          be included in the snap-shot file generated
                          by the device."
                 DEFVAL  { 0 }
                 ::= { configManager 75 }
	configSnapshotMultiChassisSelect OBJECT-TYPE
                SYNTAX                  INTEGER (0..1)
                MAX-ACCESS              read-write
                STATUS                  current
                DESCRIPTION
                        "A set of this object causes
                        Multi-Chassis configuration data to
                        be included in the snap-shot file generated
                         by the device."
                DEFVAL  { 0 }
                ::= { configManager 76 }

	configSnapshotDhcpv6Select OBJECT-TYPE
                SYNTAX                  INTEGER (0..1)
                MAX-ACCESS              read-write
                STATUS                  current
                DESCRIPTION
                        "A set of this object causes
                        Dhcpv6 configuration data to
                        be included in the snap-shot file generated
                         by the device."
                DEFVAL  { 0 }
                ::= { configManager 77 }


        configSnapshotSspHelperSelect OBJECT-TYPE
                SYNTAX                  INTEGER (0..1)
                 MAX-ACCESS              read-write
                 STATUS                  current
                 DESCRIPTION
                         "A set of this object causes
                         Stack Split-Protection Helper configuration data to
                         be included in the snap-shot file generated
                          by the device."
                 DEFVAL  { 0 }
                 ::= { configManager 78 }

        configSnapshotOpenflowSelect    OBJECT-TYPE
                SYNTAX                  INTEGER (0..1)
                MAX-ACCESS              read-write
                STATUS                  current
                DESCRIPTION
                        "A set of this object causes
                         Openflow configuration data to be included
                         in the snap-shot file generated by the
                         the device."
                DEFVAL  { 0 }
                ::= { configManager 79 }

        configSnapshotTwampSelect    OBJECT-TYPE
               SYNTAX                  INTEGER (0..1)
               MAX-ACCESS              read-write
               STATUS                  current
               DESCRIPTION
                          "A set of this object causes
                          Twamp configuration data to be included
                          in the snap-shot file generated by the
                          the device."
               DEFVAL  { 0 }
               ::= { configManager 80 }

--
-- Trap description
--

   	alcatelIND1ConfigMgrTraps  OBJECT-IDENTITY
         	STATUS  current
         	DESCRIPTION
             	    "Branch For Configuration Manager Subsystem Trap Information."
         ::= { alcatelIND1ConfigMgrMIB 3 }

        alcatelIND1ConfigMgrTrapsRoot OBJECT IDENTIFIER   ::= { alcatelIND1ConfigMgrTraps 0 }
        alcatelIND1ConfigMgrTrapsObj  OBJECT IDENTIFIER   ::= { alcatelIND1ConfigMgrTraps 1 }
        configSaveSucceededTrap  NOTIFICATION-TYPE
                 OBJECTS {
                  configSaveSucceededTrapReason
                         }
                 STATUS  current
                 DESCRIPTION
                         "The save config succeeded event is generated when the saving of
                          configuration finishes without errors."
                 ::= {alcatelIND1ConfigMgrTrapsRoot 1}


-- Object used in the trap

    configSaveSucceededTrapReason  OBJECT-TYPE
	    SYNTAX  SnmpAdminString
	    MAX-ACCESS  accessible-for-notify
	    STATUS  current
	    DESCRIPTION
	        "The reason of trap for successful execution of write memory command"
	    ::= { alcatelIND1ConfigMgrTrapsObj 1 }
--
-- Compliance Statements
--

	alcatelIND1ConfigMgrMIBCompliance  MODULE-COMPLIANCE
		STATUS  current
		DESCRIPTION
		    "Compliance statement for Configuration Manager Subsystem."
		MODULE  -- this module

		    MANDATORY-GROUPS
		    {
			configFileGroup,
			configTimerFileGroup,
			configSnapshotGroup,
			configTechSupportLogGroup,
			configWriteMemoryGroup,
                        configMgrTrapsGroup,
			configMgrTrapReasonGroup
		    }

		::= { alcatelIND1ConfigMgrMIBCompliances  1 }


--
-- Units of Conformance
--

	configFileGroup  OBJECT-GROUP
		OBJECTS
		{
		  configFileName,
		  configFileAction,
		  configErrorFileName,
		  configFileStatus,
		  configFileMode,
	          configErrorFileMaximum,
		  configChangeStatus
		}
		STATUS  current
		DESCRIPTION
		    "Collection of objects for file configuration."
		::= { alcatelIND1ConfigMgrMIBGroups  1}


	configTimerFileGroup  OBJECT-GROUP
		OBJECTS
		{
	 	  configTimerFileName,
		  configTimerFileTime,
		  configTimerFileStatus,
		  configTimerClear
		}
		STATUS  current
		DESCRIPTION
		    "Collection of objects for timer file configuration."
		::= { alcatelIND1ConfigMgrMIBGroups  2}


	configSnapshotGroup  OBJECT-GROUP
		OBJECTS
		{
		  configSnapshotAllSelect,
		  configSnapshotVlanSelect,
		  configSnapshotSpanningTreeSelect,
		  configSnapshotQOSSelect,
		  configSnapshotIPSelect,
		  configSnapshotIPXSelect,
		  configSnapshotIPMSSelect,
		  configSnapshotAAASelect,
		  configSnapshotSNMPSelect,
		  configSnapshot8021QSelect,
		  configSnapshotLinkAggregateSelect,
		  configSnapshotPortMirrorSelect,
		  configSnapshotXIPSelect,
		  configSnapshotHealthMonitorSelect,
		  configSnapshotBootPSelect,
		  configSnapshotBridgeSelect,
		  configSnapshotChassisSelect,
		  configSnapshotInterfaceSelect,
		  configSnapshotPolicySelect,
		  configSnapshotSessionSelect,
		  configSnapshotServerLoadBalanceSelect,
		  configSnapshotSystemServiceSelect,
		  configSnapshotVRRPSelect,
		  configSnapshotWebSelect,
		  configSnapshotRIPSelect,
		  configSnapshotOSPFSelect,
		  configSnapshotBGPSelect,
		  configSnapshotIPRMSelect,
		  configSnapshotIPMRSelect,
		  configSnapshotModuleSelect,
		  configSnapshotRDPSelect,
		  configSnapshotIPv6Select,
		  configSnapshotOSPF3Select,
		  configSnapshotStackSelect,
                  configWriteMemoryStatus,
                  configSnapshotISISSelect,
		  configSnapshotEOAMSelect,
		  configSnapshotUDLDSelect,
		  configSnapshotNETSECSelect,
		  configSnapshotIPsecSelect,
		  configSnapshotBFDSelect,
		  configSnapshotErpSelect,
		  configSnapshotEFMOAMSelect,
		  configSnapshotLBDSelect,
		  configSnapshotSAASelect,
		  configSnapshotLFPSelect,
                  configSnapshotDHLSelect,
		  configSnapshotWccpSelect,
                  configSnapshotPPPOEIASelect,
		  configSnapshotTESTOAMSelect,
		  configSnapshotFileName,
		  configSnapshotAction,
		  configSnapshotAtmSelect,
		  configSnapshotDhcpSrvSelect,
		  configSnapshotMPLSSelect ,
		  configSnapshotNTPSelect,
		  configSnapshotPortMappingSelect,
		  configSnapshotRIPngSelect ,
		  configSnapshotSonetSelect,
		  configSnapshotSIPSelect,
		  configSnapshotUNPSelect,
                  configSnapshotDhcpv6Select,
		  configSnapshotOpenflowSelect
           	}
		STATUS  current
		DESCRIPTION
		    "Collection of objects for snapshot configuration."
		::=  { alcatelIND1ConfigMgrMIBGroups  3}


	configTechSupportLogGroup  OBJECT-GROUP
		OBJECTS
		{
		  configTechSupportLogAction
		}
		STATUS	current
		DESCRIPTION
		    "Collection of objects for technical support log file."
		::= { alcatelIND1ConfigMgrMIBGroups  4}


	configWriteMemoryGroup	OBJECT-GROUP
		OBJECTS
		{
		  configWriteMemory
		}
		STATUS  current
		DESCRIPTION
		    "Collection of objects for write memory."
		::= { alcatelIND1ConfigMgrMIBGroups  5}

        configMgrTrapsGroup NOTIFICATION-GROUP
        NOTIFICATIONS
        {
            configSaveSucceededTrap
        }
        STATUS  current
        DESCRIPTION
             "Collection of Traps for Configuration Manager."
        ::= { alcatelIND1ConfigMgrMIBGroups 6 }


       configMgrTrapReasonGroup OBJECT-GROUP
 	      OBJECTS
	      {
 	         configSaveSucceededTrapReason
 	      }
              STATUS  current
              DESCRIPTION
                   "Configurations are saved successfully by write memory command."
              ::= { alcatelIND1ConfigMgrMIBGroups 7 }

END
