ALCATEL-IND1-TWAMP-MIB DEFINITIONS ::= BEGIN

IMPORTS
	MODULE-IDENTITY, OBJECT-IDENTITY, OBJECT-TYPE, TimeTicks, IpAddress, Counter32, Gauge32, Unsigned32, Integer32
		FROM SNMPv2-SMI
        DisplayString,RowStatus
        FROM SNMPv2-TC
        SnmpAdminString
        FROM SNMP-FRAMEWORK-MIB
        MODULE-COMPLIANCE, OBJECT-GROUP
        FROM SNMPv2-CONF
        Ipv6Address
        FROM IPV6-TC
 	    softentIND1TWAMP
		FROM ALCATEL-IND1-BASE;

 alcatelIND1TWAMPMIB MODULE-IDENTITY
        LAST-UPDATED  "201410070000Z"
        ORGANIZATION  "Alcatel-Lucent"
        CONTACT-INFO
            "Please consult with Customer Service to ensure the most appropriate
             version of this document is used with the products in question:

                      Alcatel-Lucent, Enterprise Solutions Division
                    (Formerly Alcatel Internetworking, Incorporated)
                               26801 West Agoura Road
                            Agoura Hills, CA  91301-5122
                              United States Of America

            Telephone:               North America  +1 800 995 2696
                                     Latin America  +1 877 919 9526
                                     Europe         +31 23 556 0100
                                     Asia           +65 394 7933
                                     All Other      +1 818 878 4507

            Electronic Mail:         support@ind.alcatel.com
            World Wide Web:          http://alcatel-lucent.com/wps/portal/enterprise
            File Transfer Protocol:  ftp://ftp.ind.alcatel.com/pub/products/mibs"

        DESCRIPTION
            "This module describes an authoritative enterprise-specific Two Way Active
		Measurement Protocol (TWAMP) Management Information Base (MIB):


             The right to make changes in specification and other information
             contained in this document without prior notice is reserved.

             No liability shall be assumed for any incidental, indirect, special, or
             consequential damages whatsoever arising from or related to this
             document or the information contained herein.

             Vendors, end-users, and other interested parties are granted
             non-exclusive license to use this specification in connection with
             management of the products for which it is intended to be used.

                         Copyright (C) 1995-2007 Alcatel-Lucent
                             ALL RIGHTS RESERVED WORLDWIDE"

        REVISION      "201410070000Z"
        DESCRIPTION
            "The latest version of this MIB Module."

        ::= { softentIND1TWAMP 1 }

alcatelIND1TWAMPMIBObjects OBJECT-IDENTITY
  STATUS current
  DESCRIPTION
     "Branch For Two Way Active Measurement Protocol (TWAMP)
      Subsystem Managed Objects."
    ::= { alcatelIND1TWAMPMIB 1 }

alcatelIND1TWAMPMIBConformance OBJECT-IDENTITY
  STATUS current
  DESCRIPTION
     "Branch For Two Way Active Measurement Protocol (TWAMP)
      Subsystem Conformance Information."
    ::= { alcatelIND1TWAMPMIB 2 }


alcatelIND1TWAMPMIBGroups OBJECT-IDENTITY
  STATUS current
  DESCRIPTION
     "Branch For Two Way Active Measurement Protocol (TWAMP)
      Subsystem Units Of Conformance."
    ::= { alcatelIND1TWAMPMIBConformance 1 }

alcatelIND1TWAMPMIBCompliances OBJECT-IDENTITY
  STATUS current
  DESCRIPTION
     "Branch For Two Way Active Measurement Protocol (TWAMP)
      Subsystem Compliance Statements."
    ::= { alcatelIND1TWAMPMIBConformance 2 }

twampServerMIB    OBJECT IDENTIFIER ::= { alcatelIND1TWAMPMIBObjects 1 }


twampServerTable OBJECT-TYPE
SYNTAX           SEQUENCE OF TwampServerTableEntry
MAX-ACCESS       not-accessible
STATUS           current
DESCRIPTION
"twamp server information table."
::= {twampServerMIB 1 }

twampServerTableEntry  OBJECT-TYPE
SYNTAX                  TwampServerTableEntry
MAX-ACCESS               not-accessible
STATUS                   current
DESCRIPTION
"twampServer configuration."
INDEX  { twampClientIpaddress, twampClientIpaddressMask}
::= { twampServerTable 1 }

TwampServerTableEntry  ::= SEQUENCE
{
twampPortNumber   INTEGER,
twampInactivityTimeout   INTEGER,
twampClientIpaddress   IpAddress,
twampClientIpaddressMask   IpAddress,
twampRowStatus RowStatus
}

twampPortNumber OBJECT-TYPE
SYNTAX                      INTEGER ( 0 .. 1000 )
MAX-ACCESS                  read-create
STATUS                      current
DESCRIPTION
    "TCP port on which the server will be listening."
DEFVAL     { 862 }
      ::= { twampServerTableEntry 1}

twampInactivityTimeout  OBJECT-TYPE
SYNTAX                         INTEGER (0 .. 30)
MAX-ACCESS                     read-create
STATUS                         current
DESCRIPTION
	"Time to wait in mins if no packet associated with the connection is received."
DEFVAL     { 15 }
      ::= { twampServerTableEntry 2}

twampClientIpaddress  OBJECT-TYPE
SYNTAX                         IpAddress
MAX-ACCESS                     read-create
STATUS                         current
DESCRIPTION
	"Client IP or range and mask which shall be allowed to establish connection with the server."
      ::= { twampServerTableEntry 3}

twampClientIpaddressMask  OBJECT-TYPE
SYNTAX                         IpAddress
MAX-ACCESS                     read-create
STATUS                         current
DESCRIPTION
	"Mask for the corresponding Client IP ."
      ::= { twampServerTableEntry 4}

twampRowStatus	OBJECT-TYPE
SYNTAX               RowStatus
MAX-ACCESS           read-create
STATUS               current
DESCRIPTION
	"The Rowstatus of the twampServerTableEntry. ."
      ::= { twampServerTableEntry 5}

twampServerConnectionTable OBJECT-TYPE
SYNTAX        SEQUENCE OF TwampServerConnectionTableEntry
MAX-ACCESS    not-accessible
STATUS        current
DESCRIPTION
"This table is used to display the TWAMP server connection details."
::= { alcatelIND1TWAMPMIBObjects 2 }

twampServerConnectionTableEntry OBJECT-TYPE
SYNTAX         TwampServerConnectionTableEntry
MAX-ACCESS     not-accessible
STATUS         current
DESCRIPTION
"Entry to display client IP,Session ID, Time of Last Run, Packets sent, Packets Received."
INDEX { twampServerConnClientIP}
::= { twampServerConnectionTable 1 }

TwampServerConnectionTableEntry ::= SEQUENCE
{
  twampServerConnClientIP   IpAddress,
  twampServerConnSessionId SnmpAdminString,
  twampServerConnTimeOfLastRun DisplayString,
  twampServerConnPktsSent Integer32,
  twampServerConnPktsRecvd Integer32,
  twampServerConnectionStatus DisplayString
}

twampServerConnClientIP   OBJECT-TYPE
SYNTAX         IpAddress
MAX-ACCESS     read-only
STATUS         current
DESCRIPTION
"TWAMP Client IP"
::= { twampServerConnectionTableEntry 1 }

twampServerConnSessionId OBJECT-TYPE
SYNTAX         SnmpAdminString
MAX-ACCESS     read-only
STATUS         current
DESCRIPTION
"TWAMP Client Session ID"
::= { twampServerConnectionTableEntry 2 }

twampServerConnTimeOfLastRun OBJECT-TYPE
SYNTAX        DisplayString
MAX-ACCESS     read-only
STATUS         current
DESCRIPTION
"TWAMP Client Session Time Of Last Run"
::= { twampServerConnectionTableEntry 3 }

twampServerConnPktsSent OBJECT-TYPE
SYNTAX         Integer32
MAX-ACCESS     read-only
STATUS         current
DESCRIPTION
"TWAMP Client Session Packets Sent"
::= { twampServerConnectionTableEntry 4 }

twampServerConnPktsRecvd OBJECT-TYPE
SYNTAX         Integer32
MAX-ACCESS     read-only
STATUS         current
DESCRIPTION
"TWAMP Client Session Packets Received"
::= { twampServerConnectionTableEntry 5 }

twampServerConnectionStatus OBJECT-TYPE
SYNTAX         DisplayString
MAX-ACCESS     read-only
STATUS         current
DESCRIPTION
"TWAMP Client Connection Status"
::= { twampServerConnectionTableEntry 6 }

--
-- Compliance Statements
--

    alcatelIND1TWAMPMIBCompliance MODULE-COMPLIANCE
        STATUS  current
        DESCRIPTION
            "Compliance statement for
             Two Way Active Measurement Protocol (TWAMP) Subsystem."
        MODULE  -- this module

            MANDATORY-GROUPS
            {
                twampServerMIBGroup,
                twampServerConnGroup

            }

        ::= { alcatelIND1TWAMPMIBCompliances 1 }

--
-- Units Of Conformance
--

    twampServerMIBGroup OBJECT-GROUP
        OBJECTS
        {
		twampPortNumber,
		twampInactivityTimeout,
		twampClientIpaddress,
		twampClientIpaddressMask,
		twampRowStatus


        }
        STATUS  current
        DESCRIPTION
            "Collection of objects for management of TWAMP Server."
        ::= { alcatelIND1TWAMPMIBGroups 1 }

    twampServerConnGroup OBJECT-GROUP
	OBJECTS
	{
  		twampServerConnClientIP,
  		twampServerConnSessionId,
  		twampServerConnTimeOfLastRun,
  		twampServerConnPktsSent,
  		twampServerConnPktsRecvd,
		twampServerConnectionStatus
	}
	STATUS   current
	DESCRIPTION
		"TWAMP Server Connection Statistics Group."
	::= { alcatelIND1TWAMPMIBGroups 2 }
END
-- End of Twamp server MIB --
