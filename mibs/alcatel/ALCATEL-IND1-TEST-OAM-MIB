ALCATEL-IND1-TEST-OAM-MIB DEFINITIONS ::= BEGIN


IMPORTS
    MODULE-IDENTITY,
    OBJECT-TYPE,
    NOTIFICATION-TYPE,
    Integer32, Unsigned32,
    Counter64                 FROM SNMPv2-SMI    -- [RFC2578]
    RowStatus, MacAddress,
    DateAndTime,
    TruthValue                FROM SNMPv2-TC     -- [RFC2579]
    SnmpAdminString           FROM SNMP-FRAMEWORK-MIB
    MODULE-COMPLIANCE,
    NOTIFICATION-GROUP,
    OBJECT-GROUP              FROM SNMPv2-CONF   -- [RFC2580]
    InterfaceIndex            FROM IF-MIB        -- [RFC2863]
    VlanId                    FROM Q-BRIDGE-MIB  -- [RFC4363]
    softentIND1TestOam        FROM ALCATEL-IND1-BASE
    InetAddressType,
    InetAddress               FROM INET-ADDRESS-MIB
   ;

alcatelIND1TestOamMIB   MODULE-IDENTITY
    LAST-UPDATED "201003250000Z"    -- 25/03/2010 00:00GMT
    ORGANIZATION "Alcatel - Architects Of An Internet World"
    CONTACT-INFO
   "Please consult with Customer Service to insure the most appropriate
                 version of this document is used with the products in question:

                        Alcatel Internetworking, Incorporated
                       (Division 1, Formerly XYLAN Corporation)
                               26801 West Agoura Road
                            Agoura Hills, CA  91301-5122
                              United States Of America

                Telephone:           North America  +1 800 995 2696
                                     Latin America  +1 877 919 9526
                                     Europe         +31 23 556 0100
                                     Asia           +65 394 7933
                                     All Other      +1 818 878 4507

                Electronic Mail:         support@ind.alcatel.com
                World Wide Web:          http://www.ind.alcatel.com
                File Transfer Protocol:  ftp://ftp.ind.alcatel.com/pub/products/mibs"
    DESCRIPTION
    "This module describes an authoritative enterprise-
     specific Simple Network Management Protocol (SNMP) Management
     Information Base (MIB):

     For the Birds Of Prey Product Line
     CPE test head.


     The right to make changes in specification and other information
     contained in this document without prior notice is reserved.

     No liability shall be assumed for any incidental, indirect,
     special, or consequential damages whatsoever arising from or
     related to this document or the information contained herein.

     Vendors, end-users, and other interested parties are granted
     non-exclusive license to use this specification in connection with
     management of the products for which it is intended to be used.

     Copyright (C) 1995-2002 Alcatel Internetworking, Incorporated
                         ALL RIGHTS RESERVED WORLDWIDE"


    REVISION       "201003250000Z"    -- 25/03/2010 00:00GMT
    DESCRIPTION
           "The mib for Test OAM module."
                ::= { softentIND1TestOam 1}


alaTestOamNotifications OBJECT IDENTIFIER ::= { alcatelIND1TestOamMIB 0 }
alaTestOamMIBObjects OBJECT IDENTIFIER ::= { alcatelIND1TestOamMIB 1 }
alaTestOamConformance OBJECT IDENTIFIER ::= { alcatelIND1TestOamMIB 2 }

-- alaTestOamMIBObjects contains following groups
       alaTestOamClearStats          OBJECT IDENTIFIER ::= { alaTestOamMIBObjects 1 }
       alaTestOamStatus              OBJECT IDENTIFIER ::= { alaTestOamMIBObjects 2 }
       alaTestOamConfig              OBJECT IDENTIFIER ::= { alaTestOamMIBObjects 3 }
       alaTestOamStats               OBJECT IDENTIFIER ::= { alaTestOamMIBObjects 4 }
       alaTestOamGroupClearStats     OBJECT IDENTIFIER ::= { alaTestOamMIBObjects 5 }
       alaTestOamFeederPort          OBJECT IDENTIFIER ::= { alaTestOamMIBObjects 6 }
       alaTestOamGroupConfig         OBJECT IDENTIFIER ::= { alaTestOamMIBObjects 7 }
       alaTestOamGroupFlowConfig     OBJECT IDENTIFIER ::= { alaTestOamMIBObjects 8 }
       alaTestOamGroupFlowStats      OBJECT IDENTIFIER ::= { alaTestOamMIBObjects 9 }
       alaTestOamSaaConfig           OBJECT IDENTIFIER ::= { alaTestOamMIBObjects 10 }
       alaTestOamSaaStats            OBJECT IDENTIFIER ::= { alaTestOamMIBObjects 11 }
       alaTestOamGroupFlowSaaStats   OBJECT IDENTIFIER ::= { alaTestOamMIBObjects 12 }
       alaTestOamStatsFlashSave      OBJECT IDENTIFIER ::= { alaTestOamMIBObjects 13 }
       alaTestOamTrapObj             OBJECT IDENTIFIER ::= { alaTestOamMIBObjects 14 }

-- *******************************************************************
-- The Test Clear Statistics object
-- *******************************************************************
alaTestOamGlobalClearStats OBJECT-TYPE
        SYNTAX          INTEGER {
                        default(1),
                        reset(2)
                        }
        MAX-ACCESS      read-write
        STATUS          current
        DESCRIPTION
        "Defines the global clear statistics control for test OAM
        The value reset (2) indicates that clear all statistic counters."
        DEFVAL  { default }
        ::= { alaTestOamClearStats 1 }

-- ******************************************************************
-- The TEST OAM Config Table
-- ******************************************************************

alaTestOamConfigTable OBJECT-TYPE
    SYNTAX      SEQUENCE OF AlaTestOamConfigEntry
    MAX-ACCESS  not-accessible
    STATUS      current
    DESCRIPTION
       "Defines the test oam config table for providing, via SNMP, the
        capability of performing Test OAM operation."
    ::= { alaTestOamConfig 1 }

alaTestOamConfigEntry OBJECT-TYPE
    SYNTAX      AlaTestOamConfigEntry
    MAX-ACCESS  not-accessible
    STATUS      current
    DESCRIPTION
       "The Config table entry"
    INDEX { alaTestOamConfigTestId  }
    ::= { alaTestOamConfigTable 1 }

AlaTestOamConfigEntry ::= SEQUENCE {
      alaTestOamConfigTestId                    SnmpAdminString,
      alaTestOamConfigSourceEndpoint            SnmpAdminString,
      alaTestOamConfigDestinationEndpoint       SnmpAdminString,
      alaTestOamConfigTestDescription           SnmpAdminString,
      alaTestOamConfigGeneratorTestMode         INTEGER,
      alaTestOamConfigAnalyzerTestMode          INTEGER,
      alaTestOamConfigLoopbackTestMode          INTEGER,
      alaTestOamConfigDirection                 INTEGER,
      alaTestOamConfigFrameSrcMacAddress        MacAddress,
      alaTestOamConfigFrameDstMacAddress        MacAddress,
      alaTestOamConfigDuration                  Integer32,
      alaTestOamConfigVlan                      VlanId,
      alaTestOamConfigRole                      INTEGER,
      alaTestOamConfigPort                      InterfaceIndex,
      alaTestOamConfigSourceLearningStatus      INTEGER,
      alaTestOamConfigGeneratorMode             INTEGER,
      alaTestOamConfigGeneratorBandwidth        Integer32,
      alaTestOamConfigGeneratorPacketSize       Integer32,
      alaTestOamConfigTestIdState               INTEGER,
      alaTestOamConfigTestIdStatus              INTEGER,
      alaTestOamConfigFrameType                 INTEGER,
      alaTestOamConfigRowStatus                 RowStatus,
      alaTestOamConfigRemoteStatsFetchState     INTEGER,
      alaTestOamConfigRemoteSysMacAddress       MacAddress
    }

alaTestOamConfigTestId  OBJECT-TYPE
    SYNTAX      SnmpAdminString (SIZE(1..32))
    MAX-ACCESS  accessible-for-notify
    STATUS      current
    DESCRIPTION
       "Unique name to identify the entries in the table."

    ::= { alaTestOamConfigEntry 1 }

alaTestOamConfigSourceEndpoint OBJECT-TYPE
    SYNTAX      SnmpAdminString (SIZE(1..32))
    MAX-ACCESS  read-create
    STATUS      current
    DESCRIPTION
       "This Object is to identify the local or transmitting DUT.
        For bidirectional test, this also identifies the analyzer
	DUT."
    DEFVAL { "DEFAULT" }

    ::= { alaTestOamConfigEntry 2 }

alaTestOamConfigDestinationEndpoint OBJECT-TYPE
    SYNTAX      SnmpAdminString (SIZE(1..32))
    MAX-ACCESS  read-create
    STATUS      current
    DESCRIPTION
       "This Object is to identify the remote DUT. For unidirectional,
        this identifies the analyzer DUT. For bidirectional test, this
	identifies the DUT that needs to activate the loopback function.
       "
    DEFVAL { "DEFAULT" }

    ::= { alaTestOamConfigEntry 3 }

alaTestOamConfigTestDescription OBJECT-TYPE
    SYNTAX      SnmpAdminString (SIZE(1..32))
    MAX-ACCESS  read-create
    STATUS      current
    DESCRIPTION
       "Descprition of the test."
    DEFVAL { "DEFAULT" }

    ::= { alaTestOamConfigEntry 4 }

alaTestOamConfigGeneratorTestMode OBJECT-TYPE
    SYNTAX      INTEGER {
                    ingressUniOutOfService(1)
                    }

    MAX-ACCESS  read-create
    STATUS      current
    DESCRIPTION
       "Indicates the test mode for the generator.
       "
    DEFVAL { ingressUniOutOfService }

    ::= { alaTestOamConfigEntry 5 }

alaTestOamConfigAnalyzerTestMode OBJECT-TYPE
    SYNTAX      INTEGER {
                    ingressNni(1)
                    }

    MAX-ACCESS  read-create
    STATUS      current
    DESCRIPTION
       "Indicates the test mode for the analyzer."
    DEFVAL { ingressNni }

    ::= { alaTestOamConfigEntry 6 }

alaTestOamConfigLoopbackTestMode OBJECT-TYPE
    SYNTAX      INTEGER {
                    egressUni(1)
                    }
    MAX-ACCESS  read-create
    STATUS      current
    DESCRIPTION
       "Indicates the test mode for the loopback."
    DEFVAL { egressUni }

    ::= { alaTestOamConfigEntry 7 }

alaTestOamConfigDirection OBJECT-TYPE
    SYNTAX      INTEGER {
                     uniDirectional(1),
                     biDirectional (2)
                     }
    MAX-ACCESS  read-create
    STATUS      current
    DESCRIPTION
       "Identifies the test direction."
    DEFVAL { uniDirectional }

    ::= { alaTestOamConfigEntry 8 }

alaTestOamConfigFrameSrcMacAddress OBJECT-TYPE
    SYNTAX      MacAddress
    MAX-ACCESS  read-create
    STATUS      current
    DESCRIPTION
       "The source mac-address of the test frame."
    DEFVAL { "00:00:00:00:00:00" }

    ::= { alaTestOamConfigEntry 9 }

alaTestOamConfigFrameDstMacAddress OBJECT-TYPE
    SYNTAX      MacAddress
    MAX-ACCESS  read-create
    STATUS      current
    DESCRIPTION
       "The destination mac-address of the test frame."
    DEFVAL { "00:00:00:00:00:00" }

    ::= { alaTestOamConfigEntry 10 }

alaTestOamConfigDuration OBJECT-TYPE
    SYNTAX      Integer32 (5..3600)
    UNITS       "seconds"
    MAX-ACCESS  read-create
    STATUS      current
    DESCRIPTION
       "The duration of the test for which traffic generator shall be active."
    DEFVAL { 5 }
    ::= { alaTestOamConfigEntry 11 }

alaTestOamConfigVlan OBJECT-TYPE
    SYNTAX      VlanId
    MAX-ACCESS  read-create
    STATUS      current
    DESCRIPTION
       "The vlan required for traffic analysis and test frame accounting."

    ::= { alaTestOamConfigEntry 12 }

alaTestOamConfigRole OBJECT-TYPE
    SYNTAX      INTEGER {
		     none(0),
		     generator(1),
                     analyzer(2),
                     loopback(3)
                     }

    MAX-ACCESS  read-create
    STATUS      current
    DESCRIPTION
       "The role of the DUT based on the direction."
    DEFVAL { none }

    ::= { alaTestOamConfigEntry 13 }

alaTestOamConfigPort OBJECT-TYPE
    SYNTAX      InterfaceIndex
    MAX-ACCESS  read-create
    STATUS      current
    DESCRIPTION
       "The port to be used in the testing.Depending on the role this port
        shall have different interpretation.
	Generator - port generating the frame.
        Loopback  - This port shall be the port where Loopback of the traffic
	            shall take place.
        Analyzer  - Port configuration is not required.
        "

    ::= { alaTestOamConfigEntry 14 }

alaTestOamConfigSourceLearningStatus OBJECT-TYPE
    SYNTAX      INTEGER {
                    enable(1),
                    disable(2)
		    }
    MAX-ACCESS  read-only
    STATUS      current
    DESCRIPTION
       "Identify whether the Source Learning PDUs to be transmitted or not"
    DEFVAL { enable }

    ::= { alaTestOamConfigEntry 15 }

alaTestOamConfigGeneratorMode OBJECT-TYPE
    SYNTAX      INTEGER {
                    stream(1)
		    }
    MAX-ACCESS  read-create
    STATUS      current
    DESCRIPTION
       "The option of configuring traffic generator mode."
    DEFVAL { stream }

    ::= { alaTestOamConfigEntry 16 }

alaTestOamConfigGeneratorBandwidth OBJECT-TYPE
    SYNTAX      Integer32(8..1000000)
    MAX-ACCESS  read-create
    STATUS      current
    DESCRIPTION
       "The rate at which traffic generator shall generate the traffic.
        The Value specified should be a multiple of 8"
    DEFVAL { 8 }
    ::= { alaTestOamConfigEntry 17 }

alaTestOamConfigGeneratorPacketSize OBJECT-TYPE
    SYNTAX      Integer32(64..9212)
    MAX-ACCESS  read-create
    STATUS      current
    DESCRIPTION
       "The size of packets in bytes."
    DEFVAL { 64 }
    ::= { alaTestOamConfigEntry 18 }

alaTestOamConfigTestIdState OBJECT-TYPE
    SYNTAX      INTEGER {
                    start(1),
                    stop(2)
		    }
    MAX-ACCESS  read-create
    STATUS      current
    DESCRIPTION
       "Indicates whether to start or stop the OAM test."

    ::= { alaTestOamConfigEntry 19 }

alaTestOamConfigTestIdStatus OBJECT-TYPE
    SYNTAX      INTEGER {
                    notstarted(1),
                    running(2),
                    stopped(3),
                    ended(4)
                    }

    MAX-ACCESS  read-only
    STATUS      current
    DESCRIPTION
       "The Test status."
    DEFVAL { notstarted }

    ::= { alaTestOamConfigEntry 20 }

alaTestOamConfigFrameType OBJECT-TYPE
    SYNTAX      INTEGER {
		     none(0),
		     ether(1),
                     ipv4(2)
                   --ipv6(3)
		     }
    MAX-ACCESS  read-only
    STATUS      current
    DESCRIPTION
       "The type of frame."
    DEFVAL {none}

    ::= { alaTestOamConfigEntry 21 }

alaTestOamConfigRowStatus OBJECT-TYPE
    SYNTAX      RowStatus
    MAX-ACCESS  read-create
    STATUS      current
    DESCRIPTION
       "Row Status for initiating a MIB retrieval request."

    ::= { alaTestOamConfigEntry 23 }

alaTestOamConfigRemoteStatsFetchState OBJECT-TYPE
    SYNTAX      INTEGER {
                    set(1),
                    unset(2)
		    }
    MAX-ACCESS  read-create
    STATUS      current
    DESCRIPTION
       "Indicates whether to fetch remote stats for Test OAM test."

    ::= { alaTestOamConfigEntry 24 }

alaTestOamConfigRemoteSysMacAddress OBJECT-TYPE
    SYNTAX      MacAddress
    MAX-ACCESS  read-create
    STATUS      current
    DESCRIPTION
       "The Remote device's system mac-address "
    DEFVAL { "00:00:00:00:00:00" }

    ::= { alaTestOamConfigEntry 25 }

-- *******************************************************************
-- The Test OAM Ether Config Table
-- *******************************************************************

alaTestOamEtherConfigTable OBJECT-TYPE
   SYNTAX      SEQUENCE OF AlaTestOamEtherConfigEntry
   MAX-ACCESS  not-accessible
   STATUS      current
   DESCRIPTION
        "This table contains the configs which are specific to L2"
    ::= { alaTestOamConfig 2 }

alaTestOamEtherConfigEntry OBJECT-TYPE
   SYNTAX      AlaTestOamEtherConfigEntry
   MAX-ACCESS  not-accessible
   STATUS      current
   DESCRIPTION
        "The L2 packet configuration table."
   INDEX {
              alaTestOamConfigTestId
         }
    ::= { alaTestOamEtherConfigTable 1 }

AlaTestOamEtherConfigEntry ::=
    SEQUENCE {
                alaTestOamEtherConfigVlan         VlanId,
                alaTestOamEtherConfig8021p        Unsigned32,
                alaTestOamEtherConfigDataPattern  OCTET STRING,
                alaTestOamEtherConfigEtherType    Integer32,
                alaTestOamEtherConfigCfi          TruthValue,
                alaTestOamEtherConfigRowStatus    RowStatus
     }

alaTestOamEtherConfigVlan  OBJECT-TYPE
   SYNTAX		   VlanId
   MAX-ACCESS	           read-create
   STATUS      		   current
   DESCRIPTION
	"The customer vlan for the packet."
   ::= { alaTestOamEtherConfigEntry 1 }

alaTestOamEtherConfig8021p       OBJECT-TYPE
    SYNTAX     Unsigned32 (0..7)
    MAX-ACCESS read-create
    STATUS     current
    DESCRIPTION
       "Specifies the priority in the generated test frame."
    DEFVAL { 7}
    ::= { alaTestOamEtherConfigEntry 2 }

alaTestOamEtherConfigDataPattern   OBJECT-TYPE
    SYNTAX     OCTET STRING (SIZE(2))
    MAX-ACCESS read-create
    STATUS     current
    DESCRIPTION
        "The data pattern present in the generated test frame."
    ::= { alaTestOamEtherConfigEntry 3 }

alaTestOamEtherConfigEtherType       OBJECT-TYPE
    SYNTAX     Integer32 (0..65535)
    MAX-ACCESS read-create
    STATUS     current
    DESCRIPTION
       "Specifies the ether-type for the L2 packet."
    ::= { alaTestOamEtherConfigEntry 4 }

alaTestOamEtherConfigCfi     OBJECT-TYPE
    SYNTAX     TruthValue
    MAX-ACCESS read-create
    STATUS     current
    DESCRIPTION
        "Specifies the CFI bit present in the generated test frame."
    DEFVAL { false }
    ::= { alaTestOamEtherConfigEntry 5 }

alaTestOamEtherConfigRowStatus  OBJECT-TYPE
    SYNTAX     RowStatus
    MAX-ACCESS read-create
    STATUS     current
    DESCRIPTION
        "The status of the row.

        The writable columns in a row can not be changed if the row
        is active. All columns must have a valid value before a row
        can be activated.
       "

    ::= { alaTestOamEtherConfigEntry 6 }

-- *******************************************************************
-- The Test OAM  IPv4 Config Table
-- *******************************************************************

alaTestOamIpv4ConfigTable   OBJECT-TYPE
    SYNTAX     SEQUENCE OF AlaTestOamIpv4ConfigEntry
    MAX-ACCESS not-accessible
    STATUS     current
    DESCRIPTION
       "This table contains the configs which are specific to IPv4."
    ::= { alaTestOamConfig 3 }

alaTestOamIpv4ConfigEntry   OBJECT-TYPE
    SYNTAX     AlaTestOamIpv4ConfigEntry
    MAX-ACCESS not-accessible
    STATUS     current
    DESCRIPTION
       "The IPv4 packet configuration table."
    INDEX {
              alaTestOamConfigTestId
          }
    ::= { alaTestOamIpv4ConfigTable 1 }

AlaTestOamIpv4ConfigEntry   ::= SEQUENCE {
    alaTestOamIpv4ConfigVlan         VlanId,
    alaTestOamIpv4Config8021p        Unsigned32,
    alaTestOamIpv4ConfigDataPattern  OCTET STRING,
    alaTestOamIpv4ConfigCfi          TruthValue,
    alaTestOamIpv4ConfigSrcIpType    InetAddressType,
    alaTestOamIpv4ConfigSrcIp        InetAddress,
    alaTestOamIpv4ConfigDstIpType    InetAddressType,
    alaTestOamIpv4ConfigDstIp        InetAddress,
    alaTestOamIpv4ConfigSrcPort      Integer32,
    alaTestOamIpv4ConfigDstPort      Integer32,
    alaTestOamIpv4ConfigNxtHeader    INTEGER,
    alaTestOamIpv4ConfigTtl          Integer32,
    alaTestOamIpv4ConfigTos          Integer32,
    alaTestOamIpv4ConfigRowStatus    RowStatus,
    alaTestOamIPConfigFlowLabel    Integer32
}

alaTestOamIpv4ConfigVlan  OBJECT-TYPE
    SYNTAX     VlanId
    MAX-ACCESS read-create
    STATUS     current
    DESCRIPTION
        "Indicates the customer vlan for the packet."
    ::= { alaTestOamIpv4ConfigEntry 1 }

alaTestOamIpv4Config8021p    OBJECT-TYPE
    SYNTAX     Unsigned32 (0..7)
    MAX-ACCESS read-create
    STATUS     current
    DESCRIPTION
        "Specifies the priority in the alaTestOamStats generated test frame."
    DEFVAL { 7 }
    ::= { alaTestOamIpv4ConfigEntry 2 }

alaTestOamIpv4ConfigDataPattern   OBJECT-TYPE
    SYNTAX     OCTET STRING (SIZE(2))
    MAX-ACCESS read-create
    STATUS     current
    DESCRIPTION
        "The data pattern present in the generated test frame."
    ::= { alaTestOamIpv4ConfigEntry 3 }

alaTestOamIpv4ConfigCfi   OBJECT-TYPE
    SYNTAX     TruthValue
    MAX-ACCESS read-create
    STATUS     current
    DESCRIPTION
        "Specifies the CFI bit present in the generated test frame"
    DEFVAL { false }
    ::= { alaTestOamIpv4ConfigEntry 4 }

alaTestOamIpv4ConfigSrcIpType   OBJECT-TYPE
     SYNTAX      InetAddressType(1|2)
     MAX-ACCESS  read-create
     STATUS      current
     DESCRIPTION
          "Specifies the InetAddress type of host address to be used as the host
          for performing a ping operation."
     DEFVAL { 1 }
     ::= { alaTestOamIpv4ConfigEntry 5 }

alaTestOamIpv4ConfigSrcIp   OBJECT-TYPE
    SYNTAX     InetAddress
    MAX-ACCESS read-create
    STATUS     current
    DESCRIPTION
        "Specifies the source IP of the generated test frame"
    ::= { alaTestOamIpv4ConfigEntry 6 }

alaTestOamIpv4ConfigDstIpType   OBJECT-TYPE
     SYNTAX      InetAddressType(1|2)
     MAX-ACCESS  read-create
     STATUS      current
     DESCRIPTION
          "Specifies the InetAddress type of host address to be used as the destination
          for performing a ping operation."
     DEFVAL { 1 }
     ::= { alaTestOamIpv4ConfigEntry 7 }

alaTestOamIpv4ConfigDstIp   OBJECT-TYPE
    SYNTAX     InetAddress
    MAX-ACCESS read-create
    STATUS     current
    DESCRIPTION
        "Specifies the destination IP of the generated test frame."
    ::= { alaTestOamIpv4ConfigEntry 8 }

alaTestOamIpv4ConfigSrcPort   OBJECT-TYPE
    SYNTAX     Integer32 (0..65535)
    MAX-ACCESS read-create
    STATUS     current
    DESCRIPTION
        "Specifies the source port of the generated test frame."
    ::= { alaTestOamIpv4ConfigEntry 9 }

alaTestOamIpv4ConfigDstPort   OBJECT-TYPE
    SYNTAX     Integer32 (0..65535)
    MAX-ACCESS read-create
    STATUS     current
    DESCRIPTION
        "Specifies the destination port of the generated test frame."
    ::= { alaTestOamIpv4ConfigEntry 10 }

alaTestOamIpv4ConfigNxtHeader   OBJECT-TYPE
    SYNTAX     INTEGER  {
                    tcp (6),
                    udp (17),
		    reserved(255)
                  }
    MAX-ACCESS read-create
    STATUS     current
    DESCRIPTION
        "Specifies the information about the packet. Whether it is for
         TCP or UDP socket."

     DEFVAL { reserved }
    ::= { alaTestOamIpv4ConfigEntry 11 }

alaTestOamIpv4ConfigTtl   OBJECT-TYPE
    SYNTAX     Integer32 (0..255)
    MAX-ACCESS read-create
    STATUS     current
    DESCRIPTION
        "Indicates the Time to Live of the generated test frame."
     DEFVAL { 64 }
    ::= { alaTestOamIpv4ConfigEntry 12 }

alaTestOamIpv4ConfigTos   OBJECT-TYPE
    SYNTAX     Integer32 (0..255)
    MAX-ACCESS read-create
    STATUS     current
    DESCRIPTION
        "Indicates the Type of Service for the generated test frame."
    DEFVAL { ''H}
    ::= { alaTestOamIpv4ConfigEntry 13 }

alaTestOamIpv4ConfigRowStatus   OBJECT-TYPE
    SYNTAX     RowStatus
    MAX-ACCESS read-create
    STATUS     current
    DESCRIPTION
        "The status of the row.

        The writable columns in a row can not be changed if the row
        is active. All columns must have a valid value before a row
        can be activated.
       "
    ::= { alaTestOamIpv4ConfigEntry 14 }

alaTestOamIPConfigFlowLabel   OBJECT-TYPE
      SYNTAX     Integer32(0..1048575)
      MAX-ACCESS read-create
      STATUS     current
      DESCRIPTION
           "The flow identifier or Flow Label in an IPv6 packet header that
            may be used to discriminate traffic flows."
            DEFVAL { 0 }
      ::= { alaTestOamIpv4ConfigEntry 15 }


-- ******************************************************************
-- Test Oam Stats Table
-- ******************************************************************


alaTestOamStatsTable   OBJECT-TYPE
    SYNTAX     SEQUENCE OF AlaTestOamStatsEntry
    MAX-ACCESS not-accessible
    STATUS     current
    DESCRIPTION
       "This table contains the statisitics of the tests performed."
    ::= { alaTestOamStats 1 }

alaTestOamStatsEntry   OBJECT-TYPE
    SYNTAX     AlaTestOamStatsEntry
    MAX-ACCESS not-accessible
    STATUS     current
    DESCRIPTION
       "The test result's stats table."
    INDEX {
              alaTestOamConfigTestId
          }
    ::= { alaTestOamStatsTable 1 }

AlaTestOamStatsEntry   ::= SEQUENCE {
    alaTestOamStatsClearStats            INTEGER,
    alaTestOamTxIngressCounter           Counter64,
    alaTestOamTxEgressCounter            Counter64,
    alaTestOamRxIngressCounter           Counter64,
    alaTestOamRemoteStatsCounter         Counter64,
    alaTestOamBandwidthThroughput        Integer32,
    alaTestOamBandwidthThroughputStr     SnmpAdminString
}

alaTestOamStatsClearStats   OBJECT-TYPE
    SYNTAX     INTEGER {
                        default(1),
                        reset(2)
                       }
    MAX-ACCESS read-write
    STATUS     current
    DESCRIPTION
        "Defines the clear statistics control for test OAM for a particular
        test id. The value reset (2) indicates that clear all statistic counters."
    DEFVAL  { default }
    ::= { alaTestOamStatsEntry 1 }

alaTestOamTxIngressCounter  OBJECT-TYPE
    SYNTAX     Counter64
    MAX-ACCESS read-only
    STATUS     current
    DESCRIPTION
        "This counter represents the number of test frames that have
         been sent from the source port in the generator."
    ::= { alaTestOamStatsEntry 2 }

alaTestOamTxEgressCounter  OBJECT-TYPE
    SYNTAX     Counter64
    MAX-ACCESS read-only
    STATUS     current
    DESCRIPTION
        "This counter represents the number of test frames that have
         been sent out of the generator."
    ::= { alaTestOamStatsEntry 3 }

alaTestOamRxIngressCounter    OBJECT-TYPE
    SYNTAX     Counter64
    MAX-ACCESS read-only
    STATUS     current
    DESCRIPTION
        "This counter represents the number of test frames that have
         been received on the analyzer ."
    ::= { alaTestOamStatsEntry 4 }

alaTestOamRemoteStatsCounter   OBJECT-TYPE
     SYNTAX      Counter64
     MAX-ACCESS  read-only
     STATUS      current
     DESCRIPTION
         "This counter represents the number of test frames that have been received by the Analyzer and fetched by the sender device.
          iteration."
     ::= { alaTestOamStatsEntry 5 }

alaTestOamBandwidthThroughput   OBJECT-TYPE
     SYNTAX      Integer32
     MAX-ACCESS  read-only
     STATUS      current
     DESCRIPTION
         "The traffic throughput at the Generator"
     ::= { alaTestOamStatsEntry 6 }

alaTestOamBandwidthThroughputStr   OBJECT-TYPE
     SYNTAX      SnmpAdminString
     MAX-ACCESS  read-only
     STATUS      current
     DESCRIPTION
         "The traffic throughput at the Generator in String Format"
     ::= { alaTestOamStatsEntry 7 }

-- *******************************************************************
-- The Group Clear Statistics object
-- *******************************************************************
alaTestOamGlobalGroupClearStats OBJECT-TYPE
        SYNTAX          INTEGER {
                        default(1),
                        reset(2)
                        }
        MAX-ACCESS      read-write
        STATUS          current
        DESCRIPTION
        "Defines the global clear statistics control for Test OAM Group.
        The value reset (2) indicates that clear all Group statistic counters."
        DEFVAL  { default }
        ::= { alaTestOamGroupClearStats 1 }

-- *******************************************************************
-- The Feeder Port object
-- *******************************************************************
alaTestOamGlobalFeederPort OBJECT-TYPE
    	SYNTAX      InterfaceIndex
    	MAX-ACCESS  read-create
    	STATUS      current
    	DESCRIPTION
       "The port to be used to feed the test traffic only to generator port of a group.
	If the feeder port value is zero, it implies that feeder port is not created in the system."
    	::= { alaTestOamFeederPort 1 }

-- ******************************************************************
-- TEST OAM Group Config Table
-- ******************************************************************

alaTestOamGroupConfigTable OBJECT-TYPE
    SYNTAX      SEQUENCE OF AlaTestOamGroupConfigEntry
    MAX-ACCESS  not-accessible
    STATUS      current
    DESCRIPTION
       "Defines Test OAM Group Config Table For Providing SNMP
        Capability to Perform Test OAM operation."
    ::= { alaTestOamGroupConfig 1 }

alaTestOamGroupConfigEntry OBJECT-TYPE
    SYNTAX      AlaTestOamGroupConfigEntry
    MAX-ACCESS  not-accessible
    STATUS      current
    DESCRIPTION
       "The Test OAM Group Config Table Entry."
    INDEX { alaTestOamConfigGroupId  }
    ::= { alaTestOamGroupConfigTable 1 }

AlaTestOamGroupConfigEntry ::= SEQUENCE {
      alaTestOamConfigGroupId                        SnmpAdminString,
      alaTestOamGroupConfigSourceEndpoint            SnmpAdminString,
      alaTestOamGroupConfigDestinationEndpoint       SnmpAdminString,
      alaTestOamConfigGroupDescription               SnmpAdminString,
      alaTestOamGroupConfigDirection                 INTEGER,
      alaTestOamGroupConfigDuration                  Integer32,
      alaTestOamGroupConfigRole                      INTEGER,
      alaTestOamGroupConfigPort                      InterfaceIndex,
      alaTestOamGroupConfigGeneratorBandwidth        Integer32,
      alaTestOamGroupConfigState                     INTEGER,
      alaTestOamGroupConfigStatus                    INTEGER,
      alaTestOamGroupConfigFlowCount                 Integer32,
      alaTestOamGroupConfigStatsClear                INTEGER,
      alaTestOamGroupConfigRowStatus                 RowStatus,
      alaTestOamGroupConfigRemoteStatsFetchState     INTEGER,
      alaTestOamGroupConfigRemoteSysMacAddress       MacAddress
    }

alaTestOamConfigGroupId  OBJECT-TYPE
    SYNTAX      SnmpAdminString (SIZE(1..32))
    MAX-ACCESS  accessible-for-notify
    STATUS      current
    DESCRIPTION
       "Unique Name to Identify the Test OAM
        Group entries in the table."
    ::= { alaTestOamGroupConfigEntry 1 }

alaTestOamGroupConfigSourceEndpoint OBJECT-TYPE
    SYNTAX      SnmpAdminString (SIZE(1..32))
    MAX-ACCESS  read-create
    STATUS      current
    DESCRIPTION
       "This Object is to identify the local or transmitting DUT for test group.
        For bidirectional test, this also identifies the analyzer
	DUT."
    DEFVAL { "DEFAULT" }

    ::= { alaTestOamGroupConfigEntry 2 }

alaTestOamGroupConfigDestinationEndpoint OBJECT-TYPE
    SYNTAX      SnmpAdminString (SIZE(1..32))
    MAX-ACCESS  read-create
    STATUS      current
    DESCRIPTION
       "This Object is to identify the remote DUT for test group. For unidirectional,
        this identifies the analyzer DUT. For bidirectional test, this
	identifies the DUT that needs to activate the loopback function."
    DEFVAL { "DEFAULT" }

    ::= { alaTestOamGroupConfigEntry 3 }

alaTestOamConfigGroupDescription OBJECT-TYPE
    SYNTAX      SnmpAdminString (SIZE(1..32))
    MAX-ACCESS  read-create
    STATUS      current
    DESCRIPTION
       "Description of the Test OAM Group."
    DEFVAL { "DEFAULT" }

    ::= { alaTestOamGroupConfigEntry 4 }

alaTestOamGroupConfigDirection OBJECT-TYPE
    SYNTAX      INTEGER {
                            uniDirectional(1),
                            biDirectional (2)
                        }
    MAX-ACCESS  read-create
    STATUS      current
    DESCRIPTION
       "Indicates the Test OAM Group Direction."
    DEFVAL { uniDirectional }

    ::= { alaTestOamGroupConfigEntry 5 }

alaTestOamGroupConfigDuration OBJECT-TYPE
    SYNTAX      Integer32 (5..3600)
    UNITS       "seconds"
    MAX-ACCESS  read-create
    STATUS      current
    DESCRIPTION
       "The Duration of the Test of the Test OAM Group for Which Traffic Generator shall be active."
    DEFVAL { 5 }

    ::= { alaTestOamGroupConfigEntry 6 }

alaTestOamGroupConfigRole OBJECT-TYPE
    SYNTAX      INTEGER {
		            none(0),
		            generator(1),
                            analyzer(2),
                            loopback(3)
                        }
    MAX-ACCESS  read-create
    STATUS      current
    DESCRIPTION
       "The Role of the DUT Based On the Direction."
    DEFVAL { none }

    ::= { alaTestOamGroupConfigEntry 7 }

alaTestOamGroupConfigPort OBJECT-TYPE
    SYNTAX      InterfaceIndex
    MAX-ACCESS  read-create
    STATUS      current
    DESCRIPTION
       "The Port to be Used in the Testing.Depending on the Role this Port
        Shall have different interpretation.
	Generator - Port Generating the Frame.
        Loopback  - This Port Shall be the Port Where Loopback of the Traffic
	            Shall Take Place.
        Analyzer  - Port Configuration is not Required."

    ::= { alaTestOamGroupConfigEntry 8 }

alaTestOamGroupConfigGeneratorBandwidth OBJECT-TYPE
    SYNTAX      Integer32(0..1000000)
    MAX-ACCESS  read-create
    STATUS      current
    DESCRIPTION
       "The Rate at Which Traffic Generator Shall Generate the Traffic for the Test OAM Group.
        The Value specified should be a multiple of 8.

        The value '0' signifies flow bandwidth will be used for the group"
    DEFVAL { 0 }

    ::= { alaTestOamGroupConfigEntry 9 }

alaTestOamGroupConfigState OBJECT-TYPE
    SYNTAX      INTEGER {
                            start(1),
                            stop(2)
		        }
    MAX-ACCESS  read-create
    STATUS      current
    DESCRIPTION
       "Indicates Whether to Start or Stop the Test OAM Group."

    ::= { alaTestOamGroupConfigEntry 10 }

alaTestOamGroupConfigStatus OBJECT-TYPE
    SYNTAX      INTEGER {
                            notstarted(1),
                            running(2),
                            stopped(3),
                            ended(4)
                        }

    MAX-ACCESS  read-only
    STATUS      current
    DESCRIPTION
       "Test OAM Group Status."
    DEFVAL { notstarted }

    ::= { alaTestOamGroupConfigEntry 11 }

alaTestOamGroupConfigFlowCount OBJECT-TYPE
    SYNTAX      Integer32
    MAX-ACCESS  read-only
    STATUS      current
    DESCRIPTION
       "The number of test flows associated with the Test OAM Group."

    ::= { alaTestOamGroupConfigEntry 12 }

alaTestOamGroupConfigStatsClear   OBJECT-TYPE
    SYNTAX     INTEGER {
                            default(1),
                            reset(2)
                       }
    MAX-ACCESS read-create
    STATUS     current
    DESCRIPTION
        "Defines the Clear Statistics Control for a particular
         Test OAM Group. The Value reset (2) indicates that Clear
         All Statistic Counters."
    DEFVAL  { default }
    ::= { alaTestOamGroupConfigEntry 13 }

alaTestOamGroupConfigRowStatus OBJECT-TYPE
    SYNTAX      RowStatus
    MAX-ACCESS  read-create
    STATUS      current
    DESCRIPTION
       "Row Status for Creating or Deleting a Test OAM Group in the Table."

    ::= { alaTestOamGroupConfigEntry 14 }

alaTestOamGroupConfigRemoteStatsFetchState OBJECT-TYPE
    SYNTAX      INTEGER {
                    set(1),
                    unset(2)
		    }
    MAX-ACCESS  read-create
    STATUS      current
    DESCRIPTION
       "Indicates whether to fetch remote stats for Test OAM group test."

    ::= {  alaTestOamGroupConfigEntry 15 }

alaTestOamGroupConfigRemoteSysMacAddress OBJECT-TYPE
    SYNTAX      MacAddress
    MAX-ACCESS  read-create
    STATUS      current
    DESCRIPTION
       "The Remote device's system mac-address "
    DEFVAL { "00:00:00:00:00:00" }

    ::= {  alaTestOamGroupConfigEntry 16 }

-- ******************************************************************
-- Test OAM Group Flow Config Table
-- ******************************************************************

alaTestOamGroupFlowConfigTable   OBJECT-TYPE
    SYNTAX     SEQUENCE OF AlaTestOamGroupFlowConfigEntry
    MAX-ACCESS not-accessible
    STATUS     current
    DESCRIPTION
       "This Table Contains The Test Flows Associated To The
        Test OAM Group And the Test Flow Parameters."
    ::= { alaTestOamGroupFlowConfig 1 }

alaTestOamGroupFlowConfigEntry   OBJECT-TYPE
    SYNTAX     AlaTestOamGroupFlowConfigEntry
    MAX-ACCESS not-accessible
    STATUS     current
    DESCRIPTION
       "The Test OAM Group Flow Config Table Entry."
    INDEX {
              alaTestOamConfigGroupId,
              alaTestOamConfigTestId
          }
    ::= { alaTestOamGroupFlowConfigTable 1 }

AlaTestOamGroupFlowConfigEntry   ::= SEQUENCE {
    alaTestOamGroupFlowFrameSrcMacAddress           MacAddress,
    alaTestOamGroupFlowFrameDstMacAddress           MacAddress,
    alaTestOamGroupFlowVlan                         VlanId,
    alaTestOamGroupFlowGeneratorBandwidth           Integer32,
    alaTestOamGroupFlowGeneratorPacketSize          Integer32,
    alaTestOamGroupFlowConfigRowStatus              RowStatus
}

alaTestOamGroupFlowFrameSrcMacAddress OBJECT-TYPE
    SYNTAX      MacAddress
    MAX-ACCESS  read-only
    STATUS      current
    DESCRIPTION
       "The Source MAC Address Of The Test Frame."

    ::= { alaTestOamGroupFlowConfigEntry 1 }

alaTestOamGroupFlowFrameDstMacAddress OBJECT-TYPE
    SYNTAX      MacAddress
    MAX-ACCESS  read-only
    STATUS      current
    DESCRIPTION
       "The Destination MAC-Address Of The Test Frame."

    ::= { alaTestOamGroupFlowConfigEntry 2 }

alaTestOamGroupFlowVlan OBJECT-TYPE
    SYNTAX      VlanId
    MAX-ACCESS  read-only
    STATUS      current
    DESCRIPTION
       "The Vlan Required For Traffic Analysis And Test Frame Accounting."

    ::= { alaTestOamGroupFlowConfigEntry 3 }

alaTestOamGroupFlowGeneratorBandwidth OBJECT-TYPE
    SYNTAX      Integer32(8..1000000)
    MAX-ACCESS  read-only
    STATUS      current
    DESCRIPTION
       "The Rate at Which Traffic Generator Shall Generate the Traffic.
        The Value specified should be a multiple of 8."

    ::= { alaTestOamGroupFlowConfigEntry 4 }

alaTestOamGroupFlowGeneratorPacketSize OBJECT-TYPE
    SYNTAX      Integer32(64..9212)
    MAX-ACCESS  read-only
    STATUS      current
    DESCRIPTION
       "The Size Of Packets In Bytes."

    ::= { alaTestOamGroupFlowConfigEntry 5 }

alaTestOamGroupFlowConfigRowStatus OBJECT-TYPE
    SYNTAX      RowStatus
    MAX-ACCESS  read-create
    STATUS      current
    DESCRIPTION
       "Row Status for associating a flow to Group."

    ::= { alaTestOamGroupFlowConfigEntry 6 }

-- ******************************************************************
-- Test OAM Group Stats Table
-- ******************************************************************

alaTestOamGroupFlowStatsTable   OBJECT-TYPE
    SYNTAX     SEQUENCE OF AlaTestOamGroupFlowStatsEntry
    MAX-ACCESS not-accessible
    STATUS     current
    DESCRIPTION
       "This Table Contains the Statisitics Of the Test OAM Groups Executed."
    ::= { alaTestOamGroupFlowStats 1 }

alaTestOamGroupFlowStatsEntry   OBJECT-TYPE
    SYNTAX     AlaTestOamGroupFlowStatsEntry
    MAX-ACCESS not-accessible
    STATUS     current
    DESCRIPTION
       "The Test OAM Group Stats table."
    INDEX {
              alaTestOamConfigGroupId,
              alaTestOamConfigTestId
          }
    ::= { alaTestOamGroupFlowStatsTable 1 }

AlaTestOamGroupFlowStatsEntry   ::= SEQUENCE {
    alaTestOamGroupFlowTxIngressCounter           Counter64,
    alaTestOamGroupFlowTxEgressCounter            Counter64,
    alaTestOamGroupFlowRxIngressCounter           Counter64,
    alaTestOamGroupFlowRemoteStatsCounter         Counter64,
    alaTestOamGroupBandwidthThroughput		 Integer32,
    alaTestOamGroupBandwidthThroughputStr	        SnmpAdminString
}

alaTestOamGroupFlowTxIngressCounter  OBJECT-TYPE
    SYNTAX     Counter64
    MAX-ACCESS read-only
    STATUS     current
    DESCRIPTION
        "This Counter Represents the Number Of Test Frames for a Test OAM Group
         That Have Been Sent From The Source Port In The Generator."
    ::= { alaTestOamGroupFlowStatsEntry 1 }

alaTestOamGroupFlowTxEgressCounter  OBJECT-TYPE
    SYNTAX     Counter64
    MAX-ACCESS read-only
    STATUS     current
    DESCRIPTION
        "This Counter Represents the Number Of Test Frames That Have
         Been Sent Out Of the Generator."
    ::= { alaTestOamGroupFlowStatsEntry 2 }

alaTestOamGroupFlowRxIngressCounter    OBJECT-TYPE
    SYNTAX     Counter64
    MAX-ACCESS read-only
    STATUS     current
    DESCRIPTION
        "This Counter Represents The Number Of Test Frames That Have
         Been Received On The Analyzer ."
    ::= { alaTestOamGroupFlowStatsEntry 3 }

alaTestOamGroupFlowRemoteStatsCounter   OBJECT-TYPE
    SYNTAX      Counter64
    MAX-ACCESS  read-only
    STATUS      current
    DESCRIPTION
        "This counter represents the number of test frames that have been received by the Analyzer and fetched by the sender device."
    ::= { alaTestOamGroupFlowStatsEntry 4 }

alaTestOamGroupBandwidthThroughput   OBJECT-TYPE
    SYNTAX      Integer32
    MAX-ACCESS  read-only
    STATUS      current
    DESCRIPTION
        "The traffic throughput at the Generator"
    ::= { alaTestOamGroupFlowStatsEntry 5 }

alaTestOamGroupBandwidthThroughputStr   OBJECT-TYPE
    SYNTAX      SnmpAdminString
    MAX-ACCESS  read-only
    STATUS      current
    DESCRIPTION
        "The traffic throughput at the Generator in String Format"
    ::= { alaTestOamGroupFlowStatsEntry 6 }
-- *******************************************************************
-- The Test OAM Flash Save Object
-- *******************************************************************

alaTestOamGlobalStatsFlashSave         OBJECT-TYPE
    SYNTAX     INTEGER {
			enable(1),
			disable(2)
		       }
    MAX-ACCESS read-write
    STATUS     current
    DESCRIPTION
	"Defines the stats saving to the flash control for test OAM for a particular test id or group.
         The value enable (1) indicates that stats to be saved to flash after the test completion
         and value disable (2) indicates that stats will not be saved to flash file"
    DEFVAL     { disable }
    ::= { alaTestOamStatsFlashSave 1 }

-- *******************************************************************
-- The Test OAM Trap reason string object
-- *******************************************************************

alaTestOamStatsWriteDoneTrapStr OBJECT-TYPE
    SYNTAX     SnmpAdminString
    MAX-ACCESS accessible-for-notify
    STATUS     current
    DESCRIPTION
	"The string mentioning that the maximum of records have been writen on flash file"
    ::= { alaTestOamTrapObj  1 }

-- *******************************************************************
-- The Test OAM SAA Config Table
-- *******************************************************************

alaTestOamSaaConfigTable OBJECT-TYPE
   SYNTAX      SEQUENCE OF AlaTestOamSaaConfigEntry
   MAX-ACCESS  not-accessible
   STATUS      current
   DESCRIPTION
        "This table contains the SAA config for a particular test"
    ::= {   alaTestOamSaaConfig 1 }

alaTestOamSaaConfigEntry OBJECT-TYPE
   SYNTAX      AlaTestOamSaaConfigEntry
   MAX-ACCESS  not-accessible
   STATUS      current
   DESCRIPTION
        "The L2 SAA configuration table."
   INDEX {
                alaTestOamConfigTestId
         }
    ::= { alaTestOamSaaConfigTable 1 }

AlaTestOamSaaConfigEntry ::=
    SEQUENCE {
      alaTestOamSaaConfigDropEligible              TruthValue,
      alaTestOamSaaConfigPayloadSize               Integer32,
      alaTestOamSaaConfigNumPkts                   Integer32,
      alaTestOamSaaConfigInterPktDelay             Integer32,
      alaTestOamSaaConfigVlanPriority              Integer32,
      alaTestOamSaaConfigRowStatus                 RowStatus,
      alaTestOamSaaContinuous			   Integer32
     }


  alaTestOamSaaConfigDropEligible OBJECT-TYPE
      SYNTAX      TruthValue
      MAX-ACCESS  read-create
      STATUS      current
      DESCRIPTION
      "Drop Enable bit value to be used in the VLAN tag, if present
      in the transmitted frame."
      DEFVAL { false }
      ::= {   alaTestOamSaaConfigEntry 1 }

  alaTestOamSaaConfigPayloadSize        OBJECT-TYPE
      SYNTAX      Integer32 (32..1500)
      MAX-ACCESS  read-create
      STATUS      current
      DESCRIPTION
     "Specifies the size of the MAC-Ping payload to be used for the MAC-Ping operation."
	 DEFVAL { 36 }
      ::= {   alaTestOamSaaConfigEntry 2 }

  alaTestOamSaaConfigNumPkts        OBJECT-TYPE
      SYNTAX      Integer32 (1..10)
      MAX-ACCESS  read-create
      STATUS      current
      DESCRIPTION
      "Specifies the number of packets to be sent in one MAC-Ping iteration.
          "
	 DEFVAL { 5 }
      ::= {   alaTestOamSaaConfigEntry 3 }

  alaTestOamSaaConfigInterPktDelay     OBJECT-TYPE
     SYNTAX      Integer32 (100..1000)
	UNITS       "milli-seconds"
      MAX-ACCESS  read-create
      STATUS      current
      DESCRIPTION
      "Specifies the delay between two consecutive packets transmitted
      during a MAC-Ping iteration.The value specified should be a multiple
      of 100."
	 DEFVAL { 1000 }
      ::= {   alaTestOamSaaConfigEntry 4 }

  alaTestOamSaaConfigVlanPriority    OBJECT-TYPE
     SYNTAX      Integer32 (0..7)
	UNITS       "milli-seconds"
      MAX-ACCESS  read-create
      STATUS      current
      DESCRIPTION
      "Specifies both the internal priority of the Mac ping and
       the 802.1p value on the vlan tag header. Default is 0."
	 DEFVAL { 0 }
      ::= {   alaTestOamSaaConfigEntry 5 }

alaTestOamSaaConfigRowStatus OBJECT-TYPE
    SYNTAX      RowStatus
    MAX-ACCESS  read-create
    STATUS      current
    DESCRIPTION
       "Row Status for Creating or Deleting a SAA in the Table."

    ::= {     alaTestOamSaaConfigEntry 6 }

alaTestOamSaaContinuous OBJECT-TYPE
    SYNTAX      Integer32 (0..1)
    MAX-ACCESS  read-create
    STATUS	current
    DESCRIPTION
    "Specifies the SAA session will be run continuously until the testoam session ends"
	DEFVAL { 0 }
    ::= {     alaTestOamSaaConfigEntry 7 }

-- ******************************************************************
-- Test Oam Saa Stats Table
-- ******************************************************************

alaTestOamSaaStatsTable   OBJECT-TYPE
    SYNTAX     SEQUENCE OF AlaTestOamSaaStatsEntry
    MAX-ACCESS not-accessible
    STATUS     current
    DESCRIPTION
       "This table contains the SAA statistics for a particular test."
    ::= { alaTestOamSaaStats 1 }

alaTestOamSaaStatsEntry   OBJECT-TYPE
    SYNTAX     AlaTestOamSaaStatsEntry
    MAX-ACCESS not-accessible
    STATUS     current
    DESCRIPTION
       "The Saa test result's stats table."
    INDEX {
              alaTestOamConfigTestId
          }
    ::= { alaTestOamSaaStatsTable 1 }

AlaTestOamSaaStatsEntry   ::= SEQUENCE {
    alaTestOamSaaPktsSent                Unsigned32,
    alaTestOamSaaPktsRcvd                Unsigned32,
    alaTestOamSaaRunTime                 DateAndTime,
    alaTestOamSaaMinRTT                  Integer32,
    alaTestOamSaaAvgRTT                  Integer32,
    alaTestOamSaaMaxRTT                  Integer32,
    alaTestOamSaaMinJitter               Integer32,
    alaTestOamSaaAvgJitter               Integer32,
    alaTestOamSaaMaxJitter               Integer32
}

alaTestOamSaaPktsSent   OBJECT-TYPE
     SYNTAX      Unsigned32
     MAX-ACCESS  read-only
     STATUS      current
     DESCRIPTION
        "Specifies the number of packets sent during a single MAC-Ping
          iteration."
     ::= { alaTestOamSaaStatsEntry 1 }

alaTestOamSaaPktsRcvd  OBJECT-TYPE
     SYNTAX      Unsigned32
     MAX-ACCESS  read-only
     STATUS      current
     DESCRIPTION
        "Specifies the number of packets received during a single MAC-Ping
         iteration"
     ::= { alaTestOamSaaStatsEntry 2 }



 alaTestOamSaaRunTime  OBJECT-TYPE
     SYNTAX      DateAndTime
     MAX-ACCESS  read-only
     STATUS      current
     DESCRIPTION
        "The date and time at which the iteraton was run. "
     ::= { alaTestOamSaaStatsEntry 3}

 alaTestOamSaaMinRTT  OBJECT-TYPE
     SYNTAX      Integer32
     UNITS       "micro-seconds"
     MAX-ACCESS  read-only
     STATUS      current
     DESCRIPTION
     "The minimum round trip time."
     ::= { alaTestOamSaaStatsEntry 4 }

 alaTestOamSaaAvgRTT  OBJECT-TYPE
     SYNTAX      Integer32
     UNITS       "micro-seconds"
     MAX-ACCESS  read-only
     STATUS      current
     DESCRIPTION
       "The average round trip time. "
     ::= { alaTestOamSaaStatsEntry 5 }

 alaTestOamSaaMaxRTT  OBJECT-TYPE
     SYNTAX      Integer32
     UNITS       "micro-seconds"
     MAX-ACCESS read-only
     STATUS      current
     DESCRIPTION
       "The maximum round trip time."
     ::= { alaTestOamSaaStatsEntry 6}

alaTestOamSaaMinJitter  OBJECT-TYPE
     SYNTAX      Integer32
     MAX-ACCESS read-only
     STATUS      current
     DESCRIPTION
        "The minimum jitter value."
     ::= { alaTestOamSaaStatsEntry 7}

 alaTestOamSaaAvgJitter  OBJECT-TYPE
     SYNTAX      Integer32
     MAX-ACCESS read-only
     STATUS      current
     DESCRIPTION
        "The average jitter value."
    ::= { alaTestOamSaaStatsEntry 8 }

 alaTestOamSaaMaxJitter  OBJECT-TYPE
     SYNTAX      Integer32
     MAX-ACCESS read-only
     STATUS      current
     DESCRIPTION
     "The maximum jitter value."
    ::= { alaTestOamSaaStatsEntry 9 }


-- ******************************************************************
-- Test Oam Group Saa Stats Table
-- ******************************************************************

alaTestOamGroupFlowSaaStatsTable   OBJECT-TYPE
    SYNTAX     SEQUENCE OF AlaTestOamGroupFlowSaaStatsEntry
    MAX-ACCESS not-accessible
    STATUS     current
    DESCRIPTION
       "This Table Contains the SAA Statisitics Of the Test OAM Groups Executed."
    ::= { alaTestOamGroupFlowSaaStats 1 }

alaTestOamGroupFlowSaaStatsEntry   OBJECT-TYPE
    SYNTAX     AlaTestOamGroupFlowSaaStatsEntry
    MAX-ACCESS not-accessible
    STATUS     current
    DESCRIPTION
       "The Test OAM Group SAA Stats table."
    INDEX {
              alaTestOamConfigGroupId,
              alaTestOamConfigTestId
          }
    ::= { alaTestOamGroupFlowSaaStatsTable 1 }

AlaTestOamGroupFlowSaaStatsEntry   ::= SEQUENCE {
    alaTestOamGroupFlowSaaPktsSent                Unsigned32,
    alaTestOamGroupFlowSaaPktsRcvd                Unsigned32,
    alaTestOamGroupFlowSaaRunTime                 DateAndTime,
    alaTestOamGroupFlowSaaMinRTT                  Integer32,
    alaTestOamGroupFlowSaaAvgRTT                  Integer32,
    alaTestOamGroupFlowSaaMaxRTT                  Integer32,
    alaTestOamGroupFlowSaaMinJitter               Integer32,
    alaTestOamGroupFlowSaaAvgJitter               Integer32,
    alaTestOamGroupFlowSaaMaxJitter               Integer32
}

alaTestOamGroupFlowSaaPktsSent   OBJECT-TYPE
     SYNTAX      Unsigned32
     MAX-ACCESS  read-only
     STATUS      current
     DESCRIPTION
        "Specifies the number of packets sent during a single MAC-Ping
          iteration."
     ::= { alaTestOamGroupFlowSaaStatsEntry 1 }

alaTestOamGroupFlowSaaPktsRcvd  OBJECT-TYPE
     SYNTAX      Unsigned32
     MAX-ACCESS  read-only
     STATUS      current
     DESCRIPTION
        "Specifies the number of packets received during a single MAC-Ping
         iteration"
         ::= { alaTestOamGroupFlowSaaStatsEntry 2 }



 alaTestOamGroupFlowSaaRunTime  OBJECT-TYPE
     SYNTAX      DateAndTime
     MAX-ACCESS  read-only
     STATUS      current
     DESCRIPTION
        "The date and time at which the iteraton was run. "
     ::= { alaTestOamGroupFlowSaaStatsEntry 3}

 alaTestOamGroupFlowSaaMinRTT  OBJECT-TYPE
     SYNTAX      Integer32
     UNITS       "micro-seconds"
     MAX-ACCESS  read-only
     STATUS      current
     DESCRIPTION
     "The minimum round trip time."
     ::= { alaTestOamGroupFlowSaaStatsEntry 4 }

 alaTestOamGroupFlowSaaAvgRTT  OBJECT-TYPE
     SYNTAX      Integer32
     UNITS       "micro-seconds"
     MAX-ACCESS  read-only
     STATUS      current
     DESCRIPTION
       "The average round trip time. "
     ::= { alaTestOamGroupFlowSaaStatsEntry 5 }

 alaTestOamGroupFlowSaaMaxRTT  OBJECT-TYPE
     SYNTAX      Integer32
     UNITS       "micro-seconds"
     MAX-ACCESS read-only
     STATUS      current
     DESCRIPTION
       "The maximum round trip time."
     ::= { alaTestOamGroupFlowSaaStatsEntry 6}

alaTestOamGroupFlowSaaMinJitter  OBJECT-TYPE
     SYNTAX      Integer32
     MAX-ACCESS read-only
     STATUS      current
     DESCRIPTION
        "The minimum jitter value."
     ::= { alaTestOamGroupFlowSaaStatsEntry 7}

 alaTestOamGroupFlowSaaAvgJitter  OBJECT-TYPE
     SYNTAX      Integer32
     MAX-ACCESS read-only
     STATUS      current
     DESCRIPTION
        "The average jitter value."
    ::= { alaTestOamGroupFlowSaaStatsEntry 8 }

 alaTestOamGroupFlowSaaMaxJitter  OBJECT-TYPE
     SYNTAX      Integer32
     MAX-ACCESS read-only
     STATUS      current
     DESCRIPTION
     "The maximum jitter value."
     ::= { alaTestOamGroupFlowSaaStatsEntry 9 }

-- ******************************************************************
-- NOTIFICATIONS (TRAPS)
-- ******************************************************************

alaTestOamTxDoneTrap NOTIFICATION-TYPE
    OBJECTS  {
               alaTestOamConfigTestId,
               alaTestOamConfigSourceEndpoint,
               alaTestOamConfigTestIdStatus
             }
    STATUS        current
    DESCRIPTION
       "This trap shall be send to NMS from Generator DUT, once the
        test-duration has expired on it. Once the test-duration has
        expired the Generator DUT shall send this trap after some
        time interval to NMS (around 5 to 10 sec)."
    ::= { alaTestOamNotifications 1 }

alaTestOamRxReadyTrap NOTIFICATION-TYPE
    OBJECTS  {
               alaTestOamConfigTestId,
               alaTestOamConfigDestinationEndpoint,
               alaTestOamConfigTestIdStatus
             }
    STATUS        current
    DESCRIPTION
       "This trap shall be send to NMS once the DUT with Analyzer or
        Loopback Role is ready to receive the test traffic. Once this
        trap is received on NMS the Generator shall be activated for
        generating the test traffic."
    ::= { alaTestOamNotifications 2 }

alaTestOamTestAbortTrap NOTIFICATION-TYPE
    OBJECTS  {
               alaTestOamConfigTestId
             }
    STATUS        current
    DESCRIPTION
       "This trap shall be send to NMS from the DUT, if the
        Test is aborted during takeover or if any of the NI goes down."
    ::= { alaTestOamNotifications 3 }

alaTestOamGroupTxDoneTrap NOTIFICATION-TYPE
    OBJECTS  {
               alaTestOamConfigGroupId,
               alaTestOamGroupConfigSourceEndpoint,
               alaTestOamGroupConfigStatus
             }
    STATUS        current
    DESCRIPTION
       "This trap shall be send to NMS from Generator DUT, once the
        test-duration for the Test OAM Group has expired on it.
        Once the test-duration has expired the Generator DUT shall
        send this trap after some time interval to NMS (around 5 to 10 sec)."
    ::= { alaTestOamNotifications 4 }

alaTestOamGroupRxReadyTrap NOTIFICATION-TYPE
    OBJECTS  {
               alaTestOamConfigGroupId,
               alaTestOamGroupConfigDestinationEndpoint,
               alaTestOamGroupConfigStatus
             }
    STATUS        current
    DESCRIPTION
       "This trap shall be send to NMS once the DUT with Analyzer or
        Loopback Role is ready to receive the test traffic. Once this
        trap is received on NMS the Generator shall be activated for
        generating the test traffic for the Test OAM Group."
    ::= { alaTestOamNotifications 5 }

alaTestOamGroupAbortTrap NOTIFICATION-TYPE
    OBJECTS  {
               alaTestOamConfigGroupId
             }
    STATUS        current
    DESCRIPTION
       "This trap shall be send to NMS from the DUT, if the Test is aborted
        for Test OAM Group during takeover or if any of the NI goes down."
    ::= { alaTestOamNotifications 6 }

alaTestOamStatsWriteDoneTrap NOTIFICATION-TYPE
    OBJECTS  {
               alaTestOamStatsWriteDoneTrapStr
             }
    STATUS        current
    DESCRIPTION
       "This trap shall be send to NMS from the DUT, if the maximum number of stats records (64) have
        been written to the testoam stats file maintained in /flash"
    ::= { alaTestOamNotifications 7 }

-- ******************************************************************
-- Test OAM MIB Module - Conformance Information
-- ******************************************************************

alaTestOamMIBCompliances OBJECT IDENTIFIER ::= { alaTestOamConformance 1 }
alaTestOamMIBGroups      OBJECT IDENTIFIER ::= { alaTestOamConformance 2 }

-- ******************************************************************

-- ******************************************************************
-- MIB Module Compliance statements
-- ******************************************************************
alaTestOamCompliance MODULE-COMPLIANCE
        STATUS    current
        DESCRIPTION
                "Compliance statement for Test OAM."
        MODULE
        MANDATORY-GROUPS
        {
              alaTestOamGlobalClearStatsGroup,
              alaTestOamConfigGroup,
              alaTestOamStatsGroup,
              alaTestOamNotificationGroup,
              alaTestOamGlobalGroupClearStatsGroup,
              alaTestOamGlobalFeederPortGroup,
              alaTestOamGroupConfigGroup,
              alaTestOamGroupFlowConfigGroup,
              alaTestOamGroupFlowStatsGroup
        }
        ::= { alaTestOamMIBCompliances 1 }

-- ******************************************************************
-- MIB Grouping
-- ******************************************************************

alaTestOamGlobalClearStatsGroup OBJECT-GROUP
   OBJECTS
   {
        alaTestOamGlobalClearStats
   }
   STATUS      current
   DESCRIPTION
       "Objects for the Global clear statistics Group."
    ::={alaTestOamMIBGroups 1 }

alaTestOamConfigGroup OBJECT-GROUP
   OBJECTS
   {
        alaTestOamConfigSourceEndpoint,
        alaTestOamConfigDestinationEndpoint,
        alaTestOamConfigTestDescription,
        alaTestOamConfigGeneratorTestMode,
        alaTestOamConfigAnalyzerTestMode,
        alaTestOamConfigLoopbackTestMode,
        alaTestOamConfigDirection,
        alaTestOamConfigFrameSrcMacAddress,
        alaTestOamConfigFrameDstMacAddress,
        alaTestOamConfigDuration,
        alaTestOamConfigVlan,
        alaTestOamConfigRole,
        alaTestOamConfigPort,
        alaTestOamConfigSourceLearningStatus,
        alaTestOamConfigGeneratorMode,
        alaTestOamConfigGeneratorBandwidth,
        alaTestOamConfigGeneratorPacketSize,
        alaTestOamConfigTestIdState,
        alaTestOamConfigTestIdStatus,
        alaTestOamConfigFrameType,
        alaTestOamConfigRowStatus,
        alaTestOamEtherConfigVlan,
        alaTestOamEtherConfig8021p,
        alaTestOamEtherConfigDataPattern,
        alaTestOamEtherConfigEtherType,
        alaTestOamEtherConfigCfi,
        alaTestOamEtherConfigRowStatus,
        alaTestOamIpv4ConfigVlan,
        alaTestOamIpv4Config8021p,
        alaTestOamIpv4ConfigDataPattern,
        alaTestOamIpv4ConfigCfi,
	alaTestOamIpv4ConfigSrcIpType,
        alaTestOamIpv4ConfigSrcIp,
	alaTestOamIpv4ConfigDstIpType,
        alaTestOamIpv4ConfigDstIp,
        alaTestOamIpv4ConfigSrcPort,
        alaTestOamIpv4ConfigDstPort,
        alaTestOamIpv4ConfigNxtHeader,
        alaTestOamIpv4ConfigTtl,
        alaTestOamIpv4ConfigTos,
        alaTestOamIpv4ConfigRowStatus,
        alaTestOamIPConfigFlowLabel,
        alaTestOamSaaConfigDropEligible,
        alaTestOamSaaConfigPayloadSize,
        alaTestOamSaaConfigNumPkts,
        alaTestOamSaaConfigInterPktDelay,
        alaTestOamSaaConfigVlanPriority,
	alaTestOamSaaConfigRowStatus,
        alaTestOamSaaContinuous

   }
   STATUS      current
   DESCRIPTION
       "Objects for the Test OAM Group."
    ::={alaTestOamMIBGroups 2 }

alaTestOamStatsGroup OBJECT-GROUP
   OBJECTS
   {
        alaTestOamStatsClearStats,
        alaTestOamTxIngressCounter,
        alaTestOamTxEgressCounter,
        alaTestOamRxIngressCounter,
       alaTestOamRemoteStatsCounter
   }
   STATUS      current
   DESCRIPTION
       "Objects for the statistics group."
    ::={alaTestOamMIBGroups 3 }

alaTestOamNotificationGroup NOTIFICATION-GROUP
   NOTIFICATIONS
   {
        alaTestOamTxDoneTrap,
        alaTestOamRxReadyTrap,
        alaTestOamTestAbortTrap,
        alaTestOamGroupTxDoneTrap,
        alaTestOamGroupRxReadyTrap,
        alaTestOamGroupAbortTrap,
        alaTestOamStatsWriteDoneTrap
   }
   STATUS  current
   DESCRIPTION
        "Collection of notifications for Test OAM."
   ::= { alaTestOamMIBGroups 4 }

alaTestOamGlobalGroupClearStatsGroup OBJECT-GROUP
   OBJECTS
   {
        alaTestOamGlobalGroupClearStats
   }
   STATUS      current
   DESCRIPTION
       "Objects for the Global group clear statistics Group."
    ::={alaTestOamMIBGroups 5 }

alaTestOamGlobalFeederPortGroup OBJECT-GROUP
   OBJECTS
   {
        alaTestOamGlobalFeederPort
   }
   STATUS      current
   DESCRIPTION
       "Object for the Global feeder port Group."
    ::={alaTestOamMIBGroups 6 }

alaTestOamGroupConfigGroup OBJECT-GROUP
   OBJECTS
   {
        alaTestOamGroupConfigSourceEndpoint,
        alaTestOamGroupConfigDestinationEndpoint,
        alaTestOamConfigGroupDescription,
        alaTestOamGroupConfigDirection,
        alaTestOamGroupConfigDuration,
        alaTestOamGroupConfigRole,
        alaTestOamGroupConfigPort,
        alaTestOamGroupConfigGeneratorBandwidth,
        alaTestOamGroupConfigState,
        alaTestOamGroupConfigStatus,
        alaTestOamGroupConfigFlowCount,
        alaTestOamGroupConfigStatsClear,
        alaTestOamGroupConfigRowStatus
   }
   STATUS      current
   DESCRIPTION
       "Objects for the Test OAM Group."
    ::={alaTestOamMIBGroups 7 }

alaTestOamGroupFlowConfigGroup OBJECT-GROUP
   OBJECTS
   {
        alaTestOamGroupFlowFrameSrcMacAddress,
        alaTestOamGroupFlowFrameDstMacAddress,
        alaTestOamGroupFlowVlan,
        alaTestOamGroupFlowGeneratorBandwidth,
        alaTestOamGroupFlowGeneratorPacketSize,
        alaTestOamGroupFlowConfigRowStatus
   }
   STATUS      current
   DESCRIPTION
       "Objects for the Test OAM Flow Group."
    ::={alaTestOamMIBGroups 8 }

alaTestOamGroupFlowStatsGroup OBJECT-GROUP
   OBJECTS
   {
        alaTestOamGroupFlowTxIngressCounter,
        alaTestOamGroupFlowTxEgressCounter,
        alaTestOamGroupFlowRxIngressCounter,
        alaTestOamGroupFlowRemoteStatsCounter,
        alaTestOamGroupBandwidthThroughput,
        alaTestOamGroupBandwidthThroughputStr
   }
   STATUS      current
   DESCRIPTION
       "Objects for the Test OAM Group statistics group."
    ::={alaTestOamMIBGroups 9 }
alaTestOamSaaStatsGroup OBJECT-GROUP
   OBJECTS
   {
        alaTestOamSaaPktsSent,
        alaTestOamSaaPktsRcvd,
        alaTestOamSaaRunTime,
        alaTestOamSaaMinRTT,
        alaTestOamSaaAvgRTT,
        alaTestOamSaaMaxRTT,
        alaTestOamSaaMinJitter,
        alaTestOamSaaAvgJitter,
        alaTestOamSaaMaxJitter
   }
   STATUS      current
   DESCRIPTION
       "Objects for the Test OAM L2 SAA statistics group."
    ::={alaTestOamMIBGroups 10 }

alaTestOamGroupFlowSaaStatsGroup OBJECT-GROUP
   OBJECTS
   {
    alaTestOamGroupFlowSaaPktsSent,
    alaTestOamGroupFlowSaaPktsRcvd,
    alaTestOamGroupFlowSaaRunTime,
    alaTestOamGroupFlowSaaMinRTT,
    alaTestOamGroupFlowSaaAvgRTT,
    alaTestOamGroupFlowSaaMaxRTT ,
    alaTestOamGroupFlowSaaMinJitter,
    alaTestOamGroupFlowSaaAvgJitter,
    alaTestOamGroupFlowSaaMaxJitter
   }
   STATUS      current
   DESCRIPTION
       "Objects for the Test OAM L2 SAA statistics group."
    ::={alaTestOamMIBGroups 11 }

alaTestOamGlobalStatsFlashSaveGroup OBJECT-GROUP
   OBJECTS
   {
        alaTestOamGlobalStatsFlashSave
   }
   STATUS      current
   DESCRIPTION
       "Object for the Global Status Flash Save Group."
    ::={alaTestOamMIBGroups 12 }

END
