OXO-CALL-HANDLING-MIB DEFINITIONS ::= BEGIN
    IMPORTS
        MODULE-IDENTITY, NOTIFICATION-TYPE, OBJECT-TYPE, Integer32,TimeTicks
            FROM SNMPv2-SMI
        TEXTUAL-CONVENTION, DisplayString, DateAndTime
            FROM SNMPv2-TC
        oxoMIB, EventSeverity
            FROM OXO-MIB ;

    oxoCallHandlingMIB MODULE-IDENTITY
        LAST-UPDATED    "201503201424Z"
        ORGANIZATION    "ALE Communication"
        CONTACT-INFO    "ALE Communication
            67400 ILLKIRCH-GRAFFENSTADEN
            FRANCE"
        DESCRIPTION
            "This is ALE Communication implementation of
            enterprise specific MIB for the OmniPCX Office Call Handling."
        REVISION        "201503201424Z"
        DESCRIPTION
            "OXO R10.2"
        ::= { oxoMIB 2 }


    -- ===================
    -- Textual Conventions
    -- ===================

    AlarmProbableCause ::= TEXTUAL-CONVENTION
        STATUS current
        DESCRIPTION
            "Probable cause values for the alarms."
        SYNTAX          INTEGER
        {
            unknown (0),
            adapter-Error (1),
            application-Subsystem-Failure (2),
            band-Width-Reduced (3),
            call-Establishment-Error (4),
            communications-Protocol-Error (5),
            communications-Subsystem-Failure (6),
            configuration-Or-Customization-Error (7),
            congestion (8),
            corrupt-Data (9),
            cpu-Cycles-Limit-Exceeded (10),
            data-Set-Or-Modem-Error (11),
            degraded-Signal (12),
            dte-Dce-Interface-Error (13),
            enclosure-Door-Open (14),
            equipment-Mal-Function (15),
            excessive-Vibration (16),
            file-Error (17),
            fire-Detected (18),
            flood-Detected (19),
            framing-Error (20),
            heating-Ventilation-Cooling-System-Problem (21),
            humidity-Unacceptable (22),
            input-Output-Device-Error (23),
            input-Device-Error (24),
            lAN-Error (25),
            leak-Detected (26),
            local-Node-Transmission-Error (27),
            loss-Of-Frame (28),
            loss-Of-Signal (29),
            material-Supply-Exhausted (30),
            multiplexer-Problem (31),
            out-Of-Memory (32),
            output-Device-Error (33),
            performance-Degraded (34),
            power-Problem (35),
            pressure-Unacceptable (36),
            processor-Problem (37),
            pump-Failure (38),
            queue-Size-Exceeded (39),
            receive-Failure (40),
            receiver-Failure (41),
            remote-Node-Transmission-Failure (42),
            resource-At-Or-Nearing-Capacity (43),
            response-Time-Excessive (44),
            retransmission-Rate-Excessive (45),
            softwar-eError (46),
            software-Program-Ab-normally-Terminated (47),
            software-Program-Error (48),
            storage-Capacity-Problem (49),
            temperature-Unacceptable (50),
            threshold-Crossed (51),
            timing-Problem (52),
            toxic-Leak-Detected (53),
            transmit-Failure (54),
            transmitter-Failure (55),
            underlying-Resource-Unavailable (56),
            version-Mismatch (57)
        }

    AlarmEventType ::= TEXTUAL-CONVENTION
        STATUS         current
        DESCRIPTION
            "The event Type values."
        SYNTAX         INTEGER
        {
            unknown (0),
            change-Value (1),
            communication-Alarm (2),
            environmental-Alarm (3),
            equipment-Alarm (4),
            object-Creation (6),
            object-Deletion (7),
            processing-Error-Alarm (10),
            quality-Of-Service-Alarm (11),
            change-State (14)
        }


     AlarmTypeList ::= TEXTUAL-CONVENTION
        STATUS         current
        DESCRIPTION
            "The type of Alarm Event."
        SYNTAX         INTEGER
        {
            urgent (1),
            hardware (2),
            history (3)
        }

    -- ===============
    -- Scalars Objects
    -- ===============
    ochmObjects OBJECT IDENTIFIER
        ::= { oxoCallHandlingMIB 1 }

    ochmStatus OBJECT-TYPE
        SYNTAX          EventSeverity
        MAX-ACCESS      read-only
        STATUS          current
        DESCRIPTION
            "Global status of the OmniOfficePCX Call handling."
        ::= { ochmObjects 1 }


    -- =========
    -- Log Table
    -- =========
    ochmAlarmTable OBJECT-TYPE
        SYNTAX          SEQUENCE  OF  OchmAlarmEntry
        MAX-ACCESS      not-accessible
        STATUS          current
        DESCRIPTION
            "Alarm table."
        ::=  { oxoCallHandlingMIB  2 }

    ochmAlarmEntry OBJECT-TYPE
        SYNTAX          OchmAlarmEntry
        MAX-ACCESS      not-accessible
        STATUS          current
        DESCRIPTION
            "Each entry contains the description of one alarm."
        INDEX        {  ochmAlarmTypeINDEX , ochmAlarmIndex  }
        ::=  { ochmAlarmTable 1 }

    OchmAlarmEntry  ::=  SEQUENCE {
        ochmAlarmTypeINDEX INTEGER,
        ochmAlarmTableType   AlarmTypeList,
        ochmAlarmIndex       Integer32,
        ochmAlarmSystTime    TimeTicks,
        ochmAlarmDateTime    DateAndTime,
        ochmAlarmEvent       INTEGER, 		-- Alarm Event type NMC
        ochmAlarmSubEvent    INTEGER,
        ochmAlarmCabinetSlot INTEGER,
        ochmAlarmBoardSlot   INTEGER,
        ochmAlarmHalfBoard   INTEGER,
        ochmAlarmInfo1       INTEGER,
        ochmAlarmInfo2       INTEGER,
        ochmAlarmInfo3       INTEGER,
        ochmAlarmInfo4       INTEGER,
        ochmAlarmType        AlarmEventType,
        ochmAlarmSeverity    EventSeverity,
        ochmAlarmCause       AlarmProbableCause
        }


    ochmAlarmTypeINDEX OBJECT-TYPE
        SYNTAX         INTEGER
        {
            urgent (0),
            hardware (1),
            history (2)
        }
        MAX-ACCESS      read-only
        STATUS          current
        DESCRIPTION
            "To identify the related alarm table."
        ::=  {  ochmAlarmEntry  0  }


    ochmAlarmTableType OBJECT-TYPE
        SYNTAX          AlarmTypeList
        MAX-ACCESS      read-only
        STATUS          current
        DESCRIPTION
            "To identify the related alarm table."
        ::=  {  ochmAlarmEntry  1  }

    ochmAlarmIndex OBJECT-TYPE
        SYNTAX          INTEGER
        MAX-ACCESS      read-only
        STATUS          current
        DESCRIPTION
            "Index into alarmTable."
        ::=  {  ochmAlarmEntry  2  }

    ochmAlarmSystTime OBJECT-TYPE
        SYNTAX          TimeTicks
        MAX-ACCESS      read-only
        STATUS          current
        DESCRIPTION
            "The value of sysUpTime when the alarm occurs."
        ::=  {  ochmAlarmEntry  3  }

    ochmAlarmDateTime OBJECT-TYPE
        SYNTAX          DateAndTime
        MAX-ACCESS      read-only
        STATUS          current
        DESCRIPTION
            "The local date and time when the alarm occurs."
        ::=  {  ochmAlarmEntry  4  }

    ochmAlarmEvent OBJECT-TYPE
        SYNTAX          INTEGER
        MAX-ACCESS      read-only
        STATUS          current
        DESCRIPTION
            "An integer that acts as an alarm Id NMC
            to uniquely identify each alarm.(Different than OXO Id Event)"
        ::=  {  ochmAlarmEntry  5  }

    ochmAlarmSubEvent OBJECT-TYPE
        SYNTAX          INTEGER
        MAX-ACCESS      read-only
        STATUS          current
        DESCRIPTION
            "An integer used to give a particular"
        ::=  {  ochmAlarmEntry  6  }

    ochmAlarmCabinetSlot OBJECT-TYPE
        SYNTAX          INTEGER
        MAX-ACCESS      read-only
        STATUS          current
        DESCRIPTION
            "Cabinet slot to identify the board related to the
            alarm."
        ::=  {  ochmAlarmEntry  7  }

    ochmAlarmBoardSlot OBJECT-TYPE
        SYNTAX          INTEGER
        MAX-ACCESS      read-only
        STATUS          current
        DESCRIPTION
            "Board slot to identify the access related to the
            alarm."
        ::=  {  ochmAlarmEntry  8  }

    ochmAlarmHalfBoard OBJECT-TYPE
        SYNTAX          INTEGER
        MAX-ACCESS      read-only
        STATUS          current
        DESCRIPTION
            "Half board to identify the half board related to the
            alarm."
        ::=  {  ochmAlarmEntry  9  }

    ochmAlarmInfo1 OBJECT-TYPE
        SYNTAX          INTEGER
        MAX-ACCESS      read-only
        STATUS          current
        DESCRIPTION
            "First additionnal information byte."
        ::=  {  ochmAlarmEntry  10  }

    ochmAlarmInfo2 OBJECT-TYPE
        SYNTAX          INTEGER
        MAX-ACCESS      read-only
        STATUS          current
        DESCRIPTION
            "Second additionnal information byte."
        ::=  {  ochmAlarmEntry  11  }

    ochmAlarmInfo3 OBJECT-TYPE
        SYNTAX          INTEGER
        MAX-ACCESS      read-only
        STATUS          current
        DESCRIPTION
            "Third additionnal information byte."
        ::=  {  ochmAlarmEntry  12  }

    ochmAlarmInfo4 OBJECT-TYPE
        SYNTAX          INTEGER
        MAX-ACCESS      read-only
        STATUS          current
        DESCRIPTION
            "Fourth additionnal information byte."
        ::=  {  ochmAlarmEntry  13  }

    ochmAlarmType OBJECT-TYPE
        SYNTAX          AlarmEventType
        MAX-ACCESS      read-only
        STATUS          current
        DESCRIPTION
            "The event Type values."
        ::=  {  ochmAlarmEntry  14  }

    ochmAlarmSeverity OBJECT-TYPE
        SYNTAX          EventSeverity
        MAX-ACCESS      read-only
        STATUS          current
        DESCRIPTION
            "Perceived severity values."
        ::=  {  ochmAlarmEntry  15  }

    ochmAlarmCause OBJECT-TYPE
        SYNTAX          AlarmProbableCause
        MAX-ACCESS      read-only
        STATUS          current
        DESCRIPTION
            "Probable cause values for the alarms."
        ::=  {  ochmAlarmEntry  16  }




    -- =============
    -- Notifications
    -- ==================================================
    -- Note that we need ochmNotifications with the 0
    -- sub-identifier to make this MIB to translate to
    -- an SNMPv1 format in a reversible way. For example
    -- it is needed for proxies that convert SNMPv1 traps
    -- to SNMPv2 notifications without MIB knowledge.
    -- ==================================================
    ochmNotificationPrefix OBJECT IDENTIFIER
        ::= { oxoCallHandlingMIB 3 }

    ochmNotifications OBJECT IDENTIFIER
        ::= { ochmNotificationPrefix 0 }

    ochmSystemRestart NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "The call handling has started running.

             Correlation:
             ===========
               ochmSystemRestart and ochmSystemRestarted can be
               correlated when the variable ProblemId has the same value

               ochmSystemRestart: opening of the alarm
               ochmSystemRestarted: closing of the alarm
             "
        ::= { ochmNotifications 1 }

    ochmSystemRestarted NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "The call handling has finished its start.

             Correlation:
             ===========
               ochmSystemRestart and ochmSystemRestarted can be
               correlated when the variable ProblemId has the same value

               ochmSystemRestart: opening of the alarm
               ochmSystemRestarted: closing of the alarm
             "
        ::= { ochmNotifications 2 }

    ochmCabinetUnplugged NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "A cabinet has been plugged out.

             Correlation:
             ===========
               ochmCabinetUnplugged and ochmCabinetOperational can be
               correlated when the variable ProblemId has the same value

               ochmCabinetUnplugged: opening of the alarm
               ochmCabinetOperational: closing of the alarm
             "
        ::= { ochmNotifications 3 }

    ochmCabinetOperational NOTIFICATION-TYPE
        OBJECTS {
            ochmSenderType,
        	ochmSeverity,
			ochmAlarmTime,
			ochmAlarmName,
			ochmAlarmEvent,
			ochmEquipementInfo,
			ochmComplementInfo,
			ochmEventType,
			ochmProbableCause
        }
        STATUS          current
        DESCRIPTION
            "A cabinet is now operational.

             Correlation:
             ===========
               ochmCabinetUnplugged and ochmCabinetOperational can be
               correlated when the variable ProblemId has the same value

               ochmCabinetUnplugged: opening of the alarm
               ochmCabinetOperational: closing of the alarm
             "
        ::= { ochmNotifications 4 }

    ochmBoardFailure NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "A board has been plugged out.

             Correlation:
             ===========
              1/ First correlation
                 -----------------
               ochmBoardFailure and ochmBoardCleared can be
               correlated when the variable ProblemId has the same value

               ochmBoardFailure: opening of the alarm
               ochmBoardCleared: closing of the alarm

              2/ Second correlation
                 ------------------
               ochmBoardFailure and ochmBoardOperational can be
               correlated when the variable ProblemId has the same value

               ochmBoardFailure: opening of the alarm
               ochmBoardOperational: closing of the alarm
             "
        ::= { ochmNotifications 5 }

    ochmBoardCleared NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "A permanent reset has been performed on a board.

             Correlation:
             ===========
               ochmBoardFailure and ochmBoardCleared can be
               correlated when the variable ProblemId has the same value

               ochmBoardFailure: opening of the alarm
               ochmBoardCleared: closing of the alarm
             "
        ::= { ochmNotifications 6 }

    ochmBoardOperational NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "A board is now operational.

             Correlation:
             ===========
               ochmBoardFailure and ochmBoardOperational can be
               correlated when the variable ProblemId has the same value

               ochmBoardFailure: opening of the alarm
               ochmBoardOperational: closing of the alarm
             "
        ::= { ochmNotifications 7 }

    ochmPowerSupplyFailure NOTIFICATION-TYPE
        OBJECTS {
            ochmNmcTicketNumber,
            ochmProblemId
        }
        STATUS          current
        DESCRIPTION
            "The main power supply went down.

             Correlation:
             ===========
               ochmPowerSupplyFailure and ochmPowerSupplyOperational can be
               correlated when the variable ProblemId has the same value

               ochmPowerSupplyFailure: opening of the alarm
               ochmPowerSupplyOperational: closing of the alarm
             "
        ::= { ochmNotifications 8 }

    ochmPowerSupplyOperational NOTIFICATION-TYPE
        OBJECTS {
            ochmSenderType,
        	ochmSeverity,
			ochmAlarmTime,
			ochmAlarmName,
			ochmAlarmEvent,
			ochmEquipementInfo,
			ochmComplementInfo,
			ochmEventType,
			ochmProbableCause
        }
        STATUS          current
        DESCRIPTION
            "The main power supply is back in service.

             Correlation:
             ===========
               ochmPowerSupplyFailure and ochmPowerSupplyOperational can be
               correlated when the variable ProblemId has the same value

               ochmPowerSupplyFailure: opening of the alarm
               ochmPowerSupplyOperational: closing of the alarm
             "
        ::= { ochmNotifications 9 }

    ochmFanFailure NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "Fan status anomaly.

             Correlation:
             ===========
               ochmFanFailure and ochmFanOperational can be
               correlated when the variable ProblemId has the same value

               ochmFanFailure: opening of the alarm
               ochmFanOperational: closing of the alarm
             "
        ::= { ochmNotifications 10 }

    ochmFanOperational NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "Fan status is operational.

             Correlation:
             ===========
               ochmFanFailure and ochmFanOperational can be
               correlated when the variable ProblemId has the same value

               ochmFanFailure: opening of the alarm
               ochmFanOperational: closing of the alarm
             "
        ::= { ochmNotifications 11 }

    ochmIsdnFailure NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "A T2 access is out of service.

             Correlation:
             ===========
               ochmIsdnFailure and ochmIsdnOperational can be
               correlated when the variable ProblemId has the same value

               ochmIsdnFailure: opening of the alarm
               ochmIsdnOperational: closing of the alarm
             "
        ::= { ochmNotifications 12 }

    ochmIsdnOperational NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "A T2 access is back in service.

             Correlation:
             ===========
               ochmIsdnFailure and ochmIsdnOperational can be
               correlated when the variable ProblemId has the same value

               ochmIsdnFailure: opening of the alarm
               ochmIsdnOperational: closing of the alarm
             "
        ::= { ochmNotifications 13 }

    ochmVoipLinkDown NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "Ethernet interface of an IP-LAN board is down.

             Correlation:
             ===========
               ochmVoipLinkDown and ochmVoipLinkUp can be
               correlated when the variable ProblemId has the same value

               ochmVoipLinkDown: opening of the alarm
               ochmVoipLinkUp: closing of the alarm
             "
        ::= { ochmNotifications 14 }

    ochmVoipLinkUp NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "Ethernet interface of an IP-LAN board is up.

             Correlation:
             ===========
               ochmVoipLinkDown and ochmVoipLinkUp can be
               correlated when the variable ProblemId has the same value

               ochmVoipLinkDown: opening of the alarm
               ochmVoipLinkUp: closing of the alarm
             "
        ::= { ochmNotifications 15 }

    ochmIbsSynchroDown NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "IBS has lost synchronization on UA link: the link is down.

             Correlation:
             ===========
               ochmIbsSynchroDown and ochmIbsSynchroUp can be
               correlated when the variable ProblemId has the same value

               ochmIbsSynchroDown: opening of the alarm
               ochmIbsSynchroUp: closing of the alarm
             "
        ::= { ochmNotifications 16 }

    ochmIbsSynchroUp NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "IBS has lost synchronization on UA link: the link is up.

             Correlation:
             ===========
               ochmIbsSynchroDown and ochmIbsSynchroUp can be
               correlated when the variable ProblemId has the same value

               ochmIbsSynchroDown: opening of the alarm
               ochmIbsSynchroUp: closing of the alarm
             "
        ::= { ochmNotifications 17 }



    -- =====================
    -- OmniVista 4760 traps
    -- =====================
    ochmNotifUnknownIncident NOTIFICATION-TYPE
        OBJECTS {
            ochmSenderType,
            ochmNotifFaultId,
            ochmNotifPbxIncidentNumber,
            ochmNotifAlarmId,
            ochmProblemId,
            ochmNotifEventType,
            ochmNotifManagedObject,
            ochmNotifProbableCause,
            ochmNotifCorrelation,
            ochmNotifPbxReceptionTime
        }
        STATUS          current
        DESCRIPTION
         "A trap that notify a PABX incident with UNKNOWN severity "
        ::= { ochmNotifications 18 }

    ochmNotifCriticalIncident NOTIFICATION-TYPE
        OBJECTS {
            ochmSenderType,
            ochmNotifFaultId,
            ochmNotifPbxIncidentNumber,
            ochmNotifAlarmId,
            ochmProblemId,
            ochmNotifEventType,
            ochmNotifManagedObject,
            ochmNotifProbableCause,
            ochmNotifCorrelation,
            ochmNotifPbxReceptionTime
        }
        STATUS          current
        DESCRIPTION
         "A trap that notify a PABX incident with CRITICAL severity "
        ::= { ochmNotifications 19 }

    ochmNotifMajorIncident NOTIFICATION-TYPE
        OBJECTS {
            ochmSenderType,
            ochmNotifFaultId,
            ochmNotifPbxIncidentNumber,
            ochmNotifAlarmId,
            ochmProblemId,
            ochmNotifEventType,
            ochmNotifManagedObject,
            ochmNotifProbableCause,
            ochmNotifCorrelation,
            ochmNotifPbxReceptionTime
        }
        STATUS          current
        DESCRIPTION
         "A trap that notify a PABX incident with MAJOR severity "
        ::= { ochmNotifications 20 }

    ochmNotifMinorIncident NOTIFICATION-TYPE
        OBJECTS {
            ochmSenderType,
            ochmNotifFaultId,
            ochmNotifPbxIncidentNumber,
            ochmNotifAlarmId,
            ochmProblemId,
            ochmNotifEventType,
            ochmNotifManagedObject,
            ochmNotifProbableCause,
            ochmNotifCorrelation,
            ochmNotifPbxReceptionTime
        }
        STATUS          current
        DESCRIPTION
         "A trap that notify a PABX incident with MINOR severity "
        ::= { ochmNotifications 21 }

    ochmNotifWarningIncident NOTIFICATION-TYPE
        OBJECTS {
            ochmSenderType,
            ochmNotifFaultId,
            ochmNotifPbxIncidentNumber,
            ochmNotifAlarmId,
            ochmProblemId,
            ochmNotifEventType,
            ochmNotifManagedObject,
            ochmNotifProbableCause,
            ochmNotifCorrelation,
            ochmNotifPbxReceptionTime
        }
        STATUS          current
        DESCRIPTION
         "A trap that notify a PABX incident with WARNING severity "
        ::= { ochmNotifications 22 }

    ochmNotifIndeterminateIncident NOTIFICATION-TYPE
        OBJECTS {
            ochmSenderType,
            ochmNotifFaultId,
            ochmNotifPbxIncidentNumber,
            ochmNotifAlarmId,
            ochmProblemId,
            ochmNotifEventType,
            ochmNotifManagedObject,
            ochmNotifProbableCause,
            ochmNotifCorrelation,
            ochmNotifPbxReceptionTime
        }
        STATUS          current
        DESCRIPTION
         "A trap that notify a PABX incident with INDETERMINATE severity "
        ::= { ochmNotifications 23 }

    ochmNotifState NOTIFICATION-TYPE
        OBJECTS {
            ochmProblemId,
            ochmNotifProblemState
        }
        STATUS          current
        DESCRIPTION
         "A trap that notify a problem state change"
        ::= { ochmNotifications 24 }

    -- =====================
    -- New alarms traps
    -- =====================

    ochmAnoRegisterReject NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "SIP Registration rejected on OXO"
        ::= { ochmNotifications 25 }

     ochmRemoteAccessMbxLocked NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            ":the remote access to voice mail box is currently locked
            Correlation:
            ===========
               ochmRemoteAccessMbxLocked and ochmRemoteAccessMbxUnlocked can be
               correlated when the variable ProblemId has the same value

               ochmRemoteAccessMbxLocked: opening of the alarm
               ochmRemoteAccessMbxUnlocked: closing of the alarm
               "
        ::= { ochmNotifications 26 }

    ochmRemoteAccessMbxUnlocked NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "the remote access to voice mail box is currently unlocked
             Correlation:
             ===========
               ochmRemoteAccessMbxLocked and ochmRemoteAccessMbxUnlocked can be
               correlated when the variable ProblemId has the same value

               ochmRemoteAccessMbxLocked: opening of the alarm
               ochmRemoteAccessMbxUnlocked: closing of the alarm
               "
        ::= { ochmNotifications 27 }

    ochmRemoteAccessWsapiLocked NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "the remote access to web services API is currently locked
             Correlation:
             ===========
               ochmRemoteAccessWsapiLocked and ochmRemoteAccessWsapiUnlocked can be
               correlated when the variable ProblemId has the same value

               ochmRemoteAccessWsapiLocked: opening of the alarm
               ochmRemoteAccessWsapiUnlocked: closing of the alarm
               "
        ::= { ochmNotifications 28 }

    ochmRemoteAccessWsapiUnlocked NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "the remote access to web services API is currently unlocked
             Correlation:
             ===========
               ochmRemoteAccessWsapiLocked and ochmRemoteAccessWsapiUnlocked can be
               correlated when the variable ProblemId has the same value

               ochmRemoteAccessWsapiLocked: opening of the alarm
               ochmRemoteAccessWsapiUnlocked: closing of the alarm
               "
        ::= { ochmNotifications 29 }

    ochmArpSpoofInfo NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "ARP spoofing detected. Multiple ARP
            reply received within lock-time period"
        ::= { ochmNotifications 30 }

    ochmDefaultPasswordFound NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            " Default passwords found in Management/ SIP Phone Administrator passwords"
        ::= { ochmNotifications 31 }

    ochmEasyPasswordFound NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "Easy passwords found in Management/ User passwords"
        ::= { ochmNotifications 32 }

    ochmDhcpServerExited NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "Server exited due to bad configuration or option definition
            error or IP address not in subnet or restart failed"
        ::= { ochmNotifications 33 }

    ochmDhcpServerStatus NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "Server status changed"
        ::= { ochmNotifications 34 }

    ochmAnoQuarantineAlert NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            " An IP address is added in quarantine"
        ::= { ochmNotifications 35 }

    ochmMgtsrvLock NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            " Access to system management is locked due to 6 consecutive
			authentication failures with in 5 minutes"
        ::= { ochmNotifications 36 }

    ochmMgtsrvUnlock NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "Access to system management is unlocked after 6 consecutive
			authentication failures in 5 minutes"
        ::= { ochmNotifications 37 }

    ochmUnsupportedRamSize NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "Power CPU EE does not support RAM
             less than 512 MB"
			 "Power CPU EE C25 does not support RAM
			 less than 256 MB"
        ::= { ochmNotifications 38 }

    ochmMsdbHealthStatus NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            ": eMMC in MSDB is approaching its end of life
			due to increase in block erase count / bad blocks"
        ::= { ochmNotifications 39 }

    ochmAnoPrinterFault NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "Default TRAPThis error is reported by the Formatter
            every N unsuccessful attempts to print.
			Report of anomaly depends on the value attached to the
			nothworthly address, named «PrintFault»"
        ::= { ochmNotifications 40 }

    ochmAnoMemoryAvail NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "There is not enough memory to start an application
            (mailing, custo, ...). When this problem occurs,
            there is less than 15% of free memory"
        ::= { ochmNotifications 41 }

	ochmTermRebootOrResetOfUserData NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "Reboot of IP terminal or reset of user data."
        ::= { ochmNotifications 42 }

	ochmBoardTempReset	NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "A temporary reset has been performed on a board (selective maintenance).
            The reset reason is either a hardware anomaly, or the board
            is not responding anymore. (Not used in wall mounted)"
        ::= { ochmNotifications 43 }

	ochmThresholdHardwareTBL	NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "The critical threshold of the hardware anomaly table is reached (80% full)."
        ::= { ochmNotifications 44 }

	ochmThresholdHistoryTBL	NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "The critical threshold of the history events table is reached (80% full)."
        ::= { ochmNotifications 45 }

	ochmThresholdMeteringTBL	NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "The critical threshold of the metering table is reached (80% full)."
        ::= { ochmNotifications 46 }

	ochmThresholdUrgentTBL	NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "The critical threshold of the urgent alarm table is reached (80% full)."
        ::= { ochmNotifications 47 }

	ochmNmcMeteringTblFull	NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "The metering table is full (100%) "
        ::= { ochmNotifications 48 }

	ochmAnoNoeDLDFail	NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "This event is sent when a NOE TDM terminal downloading fails"
        ::= { ochmNotifications 49 }

	ochmAnoPraAlarm	NOTIFICATION-TYPE
        OBJECTS {
        	ochmSenderType,
        	ochmSeverity,
			ochmAlarmTime,
			ochmAlarmName,
			ochmAlarmEvent,
			ochmEquipementInfo,
			ochmComplementInfo,
			ochmEventType,
			ochmProbableCause
        }
        STATUS          current
        DESCRIPTION
            "An alarm has been detected on a primary rate access"
        ::= { ochmNotifications 50 }


	ohcmPasswordAuthenticationLocked  NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "User password authentication is locked"
        ::= { ochmNotifications 51 }

	ohcmPasswordAuthenticationUnlocked  NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "User password authentication is unlocked"
        ::= { ochmNotifications 52 }

    ochmLocalMgtPwdReset NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "All the management passwords have been locally reset to
             a random value.
             These management passwords MUST be modified within the
             limited time frame (in minute) indicated in the first byte
             of the ochmComplementInfo field.

             Correlation:
             ===========
               ochmLocalMgtPwdReset and ochmLocalMgtPwdOperational can be
               correlated when the variable ProblemId has the same value

               ochmLocalMgtPwdReset opening of the alarm
               ochmLocalMgtPwdOperational closing of the alarm
             "
        ::= { ochmNotifications 53 }

    ochmLocalMgtPwdOperational NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "All the management passwords are now operationals. The sub-event
             information given in ochmAlarmEvent field indicates the action
             which solves this problem:
                2 - they have been restored to their previous values after
                    expiration of the limited time frame
                3 - they have been updated on time

             Correlation:
             ===========
               ochmLocalMgtPwdReset and ochmLocalMgtPwdOperational can be
               correlated when the variable ProblemId has the same value

               ochmLocalMgtPwdReset opening of the alarm
               ochmLocalMgtPwdOperational closing of the alarm
             "
        ::= { ochmNotifications 54 }

    ochmAnoCCStatusConnectionSuccess NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Change in the CC connection state:
             CC connection success
             -------------
             Byte 1: Cause
             0x00: No cause
             0x01: First OXO startup      0x02: OXO startup
             0x03: CC Agent startup       0x04: FTR done
             0x05: CC disabled            0x06: CC enabled
             0x07: CC reconnection after a disconnection due to network troubles
             0x08: CC reconnection after a disconnection due to a ping timeout
             -----------------------
             Byte 2: CC account type
             00: No param
             01: Activation account     02: Final account
            "
        ::= { ochmNotifications 55 }

    ochmAnoCCStatusDisconnectionSuccess NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Change in the CC connection state:
             CC disconnection success
             -------------
             Byte 1: Cause
             00: No cause
             0x01: First OXO startup      0x02: OXO startup
             0x03: CC Agent startup       0x04: FTR done
             0x05: CC disabled            0x06: CC enabled
             0x07: CC reconnection after a disconnection due to network troubles
             0x08: CC reconnection after a disconnection due to a ping timeout
             -----------------------
             Byte 2: CC account type
             00: No param
             01: Activation account     02: Final account
            "
        ::= { ochmNotifications 56 }

    ochmAnoCCStatusFTRDone NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Change in the CC connection state:
             FTR Done
             -------------
             Byte 1: Cause
             00: No cause
             0x01: First OXO startup      0x02: OXO startup
             0x03: CC Agent startup       0x04: FTR done
             0x05: CC disabled            0x06: CC enabled
             0x07: CC reconnection after a disconnection due to network troubles
             0x08: CC reconnection after a disconnection due to a ping timeout
             -----------------------
             Byte 2: CC account type
             00: No param
             01: Activation account     02: Final account
            "
        ::= { ochmNotifications 57 }

    ochmAnoCCFailureConnectionFailed NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Failure on CC connection
             CC connection failed
             -------------
             Byte 1: Cause
             0x00: No cause
             0x09: Stream version error                             0x0A: Stream close
             0x0B: Proxy authentication required                    0x0C: Proxy authentication failed
             0x0D: Proxy no supported authentication                0x0E: Connection refused
             0x0F: DNS error                                        0x10: No supported authentication
             0x11: TLS failed                                       0x12: TLS not available
             0x13: Connection compression failed                    0x14: Input/Output error
             0x15: Parse error                                      0x16: Out of memory
             0x17: Authentication failed                            0x18: Service unreachable
             0x19: Service non respondind                           0x1A: Invalid input
             0x1B: Inconsistent product state                       0x1C: Service internal failure
             0x1D: Bad version                                      0x1E: Bad format
             0x1F: OXO not subscribed to the Pubsub node            0X20: No persistent item on the Pubsub node
             0x21: Item retrieval not supported on the Pubsub node  0X22: OXO is not in the Pubsub node white list
             0X23: OXO has a bad affiliation for the Pubsub node    0x24: Pubsub node does not exist
             -------------------------------------
             Byte 2: CC account type or CC service
             0x00: No type
             0x01: Activation account        0x02: Final account
             0x03: FTR Service               0x04: SA Service
             ------------------------
             Byte 3: Other parameters
             0x00: No param                  0x01: SA Pubsub node for service list
            "
        ::= { ochmNotifications 58 }

    ochmAnoCCFailureIntAgentError NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Failure on CC connection
             Internal CC Agent error
             -------------
             Byte 1: Cause
             0x00: No cause
             0x0A: Stream version error                             0x09: Stream close
             0x0B: Proxy authentication required                    0x0C: Proxy authentication failed
             0x0D: Proxy no supported authentication                0x0E: Connection refused
             0x0F: DNS error                                        0x10: No supported authentication
             0x11: TLS failed                                       0x12: TLS not available
             0x13: Connection compression failed                    0x14: Input/Output error
             0x15: Parse error                                      0x16: Out of memory
             0x17: Authentication failed                            0x18: Service unreachable
             0x19: Service non respondind                           0x1A: Invalid input
             0x1B: Inconsistent product state                       0x1C: Service internal failure
             0x1D: Bad version                                      0x1E: Bad format
             0x1F: OXO not subscribed to the Pubsub node            0X20: No persistent item on the Pubsub node
             0x21: Item retrieval not supported on the Pubsub node  0X22: OXO is not in the Pubsub node white list
             0X23: OXO has a bad affiliation for the Pubsub node    0x24: Pubsub node does not exist
             -------------------------------------
             Byte 2: CC account type or CC service
             0x00: No type
             0x01: Activation account        0x02: Final account
             0x03: FTR Service               0x04: SA Service
             ------------------------
             Byte 3: Other parameters
             0x00: No param                  0x01: SA Pubsub node for service list
            "
        ::= { ochmNotifications 59 }

    ochmAnoCCFailureConnectionLost NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Failure on CC connection
             CC connection lost
             -------------
             Byte 1: Cause
             0x00: No cause
             0x09: Stream version error                             0x0A: Stream close
             0x0B: Proxy authentication required                    0x0C: Proxy authentication failed
             0x0D: Proxy no supported authentication                0x0E: Connection refused
             0x0F: DNS error                                        0x10: No supported authentication
             0x11: TLS failed                                       0x12: TLS not available
             0x13: Connection compression failed                    0x14: Input/Output error
             0x15: Parse error                                      0x16: Out of memory
             0x17: Authentication failed                            0x18: Service unreachable
             0x19: Service non respondind                           0x1A: Invalid input
             0x1B: Inconsistent product state                       0x1C: Service internal failure
             0x1D: Bad version                                      0x1E: Bad format
             0x1F: OXO not subscribed to the Pubsub node            0X20: No persistent item on the Pubsub node
             0x21: Item retrieval not supported on the Pubsub node  0X22: OXO is not in the Pubsub node white list
             0X23: OXO has a bad affiliation for the Pubsub node    0x24: Pubsub node does not exist
             -------------------------------------
             Byte 2: CC account type or CC service
             0x00: No type
             0x01: Activation account        0x02: Final account
             0x03: FTR Service               0x04: SA Service
             ------------------------
             Byte 3: Other parameters
             0x00: No param                  0x01: SA Pubsub node for service list
            "
        ::= { ochmNotifications 60 }

    ochmAnoCCFailureBadCredential NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Failure on CC connection
             Bad credential
             -------------
             Byte 1: Cause
             0x00: No cause
             0x09: Stream version error                             0x0A: Stream close
             0x0B: Proxy authentication required                    0x0C: Proxy authentication failed
             0x0D: Proxy no supported authentication                0x0E: Connection refused
             0x0F: DNS error                                        0x10: No supported authentication
             0x11: TLS failed                                       0x12: TLS not available
             0x13: Connection compression failed                    0x14: Input/Output error
             0x15: Parse error                                      0x16: Out of memory
             0x17: Authentication failed                            0x18: Service unreachable
             0x19: Service non respondind                           0x1A: Invalid input
             0x1B: Inconsistent product state                       0x1C: Service internal failure
             0x1D: Bad version                                      0x1E: Bad format
             0x1F: OXO not subscribed to the Pubsub node            0X20: No persistent item on the Pubsub node
             0x21: Item retrieval not supported on the Pubsub node  0X22: OXO is not in the Pubsub node white list
             0X23: OXO has a bad affiliation for the Pubsub node    0x24: Pubsub node does not exist
             -------------------------------------
             Byte 2: CC account type or CC service
             0x00: No type
             0x01: Activation account        0x02: Final account
             0x03: FTR Service               0x04: SA Service
             ------------------------
             Byte 3: Other parameters
             0x00: No param                  0x01: SA Pubsub node for service list
            "
        ::= { ochmNotifications 61 }

    ochmAnoCCFailureServUnreachable NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Failure on CC connection
             Service unreachable
             -------------
             Byte 1: Cause
             0x00: No cause
             0x09: Stream version error                             0x0A: Stream close
             0x0B: Proxy authentication required                    0x0C: Proxy authentication failed
             0x0D: Proxy no supported authentication                0x0E: Connection refused
             0x0F: DNS error                                        0x10: No supported authentication
             0x11: TLS failed                                       0x12: TLS not available
             0x13: Connection compression failed                    0x14: Input/Output error
             0x15: Parse error                                      0x16: Out of memory
             0x17: Authentication failed                            0x18: Service unreachable
             0x19: Service non respondind                           0x1A: Invalid input
             0x1B: Inconsistent product state                       0x1C: Service internal failure
             0x1D: Bad version                                      0x1E: Bad format
             0x1F: OXO not subscribed to the Pubsub node            0X20: No persistent item on the Pubsub node
             0x21: Item retrieval not supported on the Pubsub node  0X22: OXO is not in the Pubsub node white list
             0X23: OXO has a bad affiliation for the Pubsub node    0x24: Pubsub node does not exist
             -------------------------------------
             Byte 2: CC account type or CC service
             0x00: No type
             0x01: Activation account        0x02: Final account
             0x03: FTR Service               0x04: SA Service
             ------------------------
             Byte 3: Other parameters
             0x00: No param                  0x01: SA Pubsub node for service list
            "
        ::= { ochmNotifications 62 }

    ochmAnoCCFailureFinalAccountGetting NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Failure on CC connection
             Final account getting
             -------------
             Byte 1: Cause
             0x00: No cause
             0x09: Stream version error                             0x0A: Stream close
             0x0B: Proxy authentication required                    0x0C: Proxy authentication failed
             0x0D: Proxy no supported authentication                0x0E: Connection refused
             0x0F: DNS error                                        0x10: No supported authentication
             0x11: TLS failed                                       0x12: TLS not available
             0x13: Connection compression failed                    0x14: Input/Output error
             0x15: Parse error                                      0x16: Out of memory
             0x17: Authentication failed                            0x18: Service unreachable
             0x19: Service non respondind                           0x1A: Invalid input
             0x1B: Inconsistent product state                       0x1C: Service internal failure
             0x1D: Bad version                                      0x1E: Bad format
             0x1F: OXO not subscribed to the Pubsub node            0X20: No persistent item on the Pubsub node
             0x21: Item retrieval not supported on the Pubsub node  0X22: OXO is not in the Pubsub node white list
             0X23: OXO has a bad affiliation for the Pubsub node    0x24: Pubsub node does not exist
             -------------------------------------
             Byte 2: CC account type or CC service
             0x00: No type
             0x01: Activation account        0x02: Final account
             0x03: FTR Service               0x04: SA Service
             ------------------------
             Byte 3: Other parameters
             0x00: No param                  0x01: SA Pubsub node for service list
            "
        ::= { ochmNotifications 63 }

    ochmAnoCCFailureFinalAccountACK NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Failure on CC connection
             Final account acknowledgement
             -------------
             Byte 1: Cause
             0x00: No cause
             0x09: Stream version error                             0x0A: Stream close
             0x0B: Proxy authentication required                    0x0C: Proxy authentication failed
             0x0D: Proxy no supported authentication                0x0E: Connection refused
             0x0F: DNS error                                        0x10: No supported authentication
             0x11: TLS failed                                       0x12: TLS not available
             0x13: Connection compression failed                    0x14: Input/Output error
             0x15: Parse error                                      0x16: Out of memory
             0x17: Authentication failed                            0x18: Service unreachable
             0x19: Service non respondind                           0x1A: Invalid input
             0x1B: Inconsistent product state                       0x1C: Service internal failure
             0x1D: Bad version                                      0x1E: Bad format
             0x1F: OXO not subscribed to the Pubsub node            0X20: No persistent item on the Pubsub node
             0x21: Item retrieval not supported on the Pubsub node  0X22: OXO is not in the Pubsub node white list
             0X23: OXO has a bad affiliation for the Pubsub node    0x24: Pubsub node does not exist
             -------------------------------------
             Byte 2: CC account type or CC service
             0x00: No type
             0x01: Activation account        0x02: Final account
             0x03: FTR Service               0x04: SA Service
             ------------------------
             Byte 3: Other parameters
             0x00: No param                  0x01: SA Pubsub node for service list
            "
        ::= { ochmNotifications 64 }

    ochmAnoCCFailureInconsistentRecData NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Failure on CC connection
             Inconsistent received data
             -------------
             Byte 1: Cause
             0x00: No cause
             0x09: Stream version error                             0x0A: Stream close
             0x0B: Proxy authentication required                    0x0C: Proxy authentication failed
             0x0D: Proxy no supported authentication                0x0E: Connection refused
             0x0F: DNS error                                        0x10: No supported authentication
             0x11: TLS failed                                       0x12: TLS not available
             0x13: Connection compression failed                    0x14: Input/Output error
             0x15: Parse error                                      0x16: Out of memory
             0x17: Authentication failed                            0x18: Service unreachable
             0x19: Service non respondind                           0x1A: Invalid input
             0x1B: Inconsistent product state                       0x1C: Service internal failure
             0x1D: Bad version                                      0x1E: Bad format
             0x1F: OXO not subscribed to the Pubsub node            0X20: No persistent item on the Pubsub node
             0x21: Item retrieval not supported on the Pubsub node  0X22: OXO is not in the Pubsub node white list
             0X23: OXO has a bad affiliation for the Pubsub node    0x24: Pubsub node does not exist
             -------------------------------------
             Byte 2: CC account type or CC service
             0x00: No type
             0x01: Activation account        0x02: Final account
             0x03: FTR Service               0x04: SA Service
             ------------------------
             Byte 3: Other parameters
             0x00: No param                  0x01: SA Pubsub node for service list
            "
        ::= { ochmNotifications 65 }

    ochmAnoCCFailureEventNodeError NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Failure on CC connection
             Event node error
             -------------
             Byte 1: Cause
             0x00: No cause
             0x09: Stream version error                             0x0A: Stream close
             0x0B: Proxy authentication required                    0x0C: Proxy authentication failed
             0x0D: Proxy no supported authentication                0x0E: Connection refused
             0x0F: DNS error                                        0x10: No supported authentication
             0x11: TLS failed                                       0x12: TLS not available
             0x13: Connection compression failed                    0x14: Input/Output error
             0x15: Parse error                                      0x16: Out of memory
             0x17: Authentication failed                            0x18: Service unreachable
             0x19: Service non respondind                           0x1A: Invalid input
             0x1B: Inconsistent product state                       0x1C: Service internal failure
             0x1D: Bad version                                      0x1E: Bad format
             0x1F: OXO not subscribed to the Pubsub node            0X20: No persistent item on the Pubsub node
             0x21: Item retrieval not supported on the Pubsub node  0X22: OXO is not in the Pubsub node white list
             0X23: OXO has a bad affiliation for the Pubsub node    0x24: Pubsub node does not exist
             -------------------------------------
             Byte 2: CC account type or CC service
             0x00: No type
             0x01: Activation account        0x02: Final account
             0x03: FTR Service               0x04: SA Service
             ------------------------
             Byte 3: Other parameters
             0x00: No param                  0x01: SA Pubsub node for service list
            "
        ::= { ochmNotifications 66 }

    ochmAnoCCVPNStatus NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Change in VPN connection state
             ---------------
             Byte 1: Request
             0x01: start
             0x02: stop
             0x03: all stopall
             --------------
             Byte 2:  Cause
             0x00: Undefined       0x01: User request
             0x02: CC disabled     0x03: CC agent stop
             0x04: CC agent start  0x05: Connection supervision
             -------
             Byte 3: Connection id
             -------
             Byte 4: Tunnel id
            "
        ::= { ochmNotifications 67 }

    ochmAnoCCVPNFailure NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "A remote user initiated a request to start or stop a VPN.
             The request failed.
             ---------------
             Byte 1: Request
             0x01: Start
             0x02: Stop
             0x03: Stop all
             -------------
             Byte 2: Cause
             0x00: Undefined                0x08: Wrong parameter
             0x09: Max connection reached   0x0A: Max tunnel reached
             0x0B: Internal error           0x0C: Error during Phase1 establishment
             0x0C: Error during Phase2 establishment
             ----------------------------
             Byte 3: Additional parameter
             0x00: Undefined              0x01: Query header
             0x02: Query version          0x03: Requester
             0x04: Organization           0x05: User
             0x06: Gateway                0x07: Login
             0x08: Password               0x09: Pre Shared Key
             0x0A: Connection identifier  0x0B: IKE authentication method
             0x0C: IKE port               0xOD: NAT port
             0x0E: CA certificate         0x0F: Certificate subject
             0x10: Peer id                0x11: Phase1 encryption
             0x12: Phase1 hash            0x13: Phase1 DH group
             0x14: Phase2 encryption      0x15: Phase2 authentication
             0x16: Phase2 PFS group       0x17: Phase2 inativity timer
             -----------------
             Byte 4: Tunnel id
            "
        ::= { ochmNotifications 68 }

    ochmAnoEmergencyConfig NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "No device configured to receive emergency call notification"
        ::= { ochmNotifications 69 }

 ochmSystemAutoProvision NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Auto Provisioning is Activated/Deactivated"
        ::= { ochmNotifications 70 }
    ochmAnoRBStatusConnectionSuccess NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Change in the RB connection state:
             RB connection success
             -------------
             Byte 1: Cause
             0x00: No cause
             0x01: First OXO startup      0x02: OXO startup
             0x03: RB Agent startup
             0x04: RB disabled            0x05: RB enabled
             0x06: RB reconnection after a disconnection due to network troubles
             0x07: RB reconnection after a disconnection due to a ping timeout
             0x08: RB Agent stop
             -----------------------
             Byte 2: RB account type
             00: No type
             01: Activation account     02: Final account
            "
        ::= { ochmNotifications 72 }

    ochmAnoRBStatusDisconnectionSuccess NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Change in the RB connection state:
             RB disconnection success
             -------------
             Byte 1: Cause
             00: No cause
             0x01: First OXO startup      0x02: OXO startup
             0x03: RB Agent startup
             0x04: RB disabled            0x05: RB enabled
             0x06: RB reconnection after a disconnection due to network troubles
             0x07: RB reconnection after a disconnection due to a ping timeout
             0x08: RB Agent stop
             -----------------------
             Byte 2: RB account type
             00: No type
             01: Activation account     02: Final account
            "
        ::= { ochmNotifications 73 }

    ochmAnoRBFailureConnectionFailed NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Failure on RB connection
             RB connection failed
             -------------
             Byte 1: Cause
             0x00: No cause
             0x01: Stream version error                             0x02: Stream close
             0x03: Proxy authentication required                    0x04: Proxy authentication failed
             0x05: Proxy no supported authentication                0x06: Connection refused
             0x07: DNS error                                        0x08: No supported authentication
             0x09: TLS failed                                       0x0A: TLS not available
             0x0B: Connection compression failed                    0x0C: Input/Output error
             0x0D: Parse error                                      0x0E: Out of memory
             0x0F: Authentication failed                            0x10: Service unreachable
             0x11: Service non respondind                           0x12: Invalid input
             0x13: Inconsistent product state                       0x14: Service internal failure
             0x15: Bad version                                      0x16: Bad format
             -------------------------------------
             Byte 2: RB account type
             0x00: No type
             0x01: Activation account        0x02: Final account
            "
        ::= { ochmNotifications 74 }

    ochmAnoRBFailureIntAgentError NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Failure on RB connection
             Internal RB Agent error
             -------------
             Byte 1: Cause
             0x00: No cause
             0x01: Stream version error                             0x02: Stream close
             0x03: Proxy authentication required                    0x04: Proxy authentication failed
             0x05: Proxy no supported authentication                0x06: Connection refused
             0x07: DNS error                                        0x08: No supported authentication
             0x09: TLS failed                                       0x0A: TLS not available
             0x0B: Connection compression failed                    0x0C: Input/Output error
             0x0D: Parse error                                      0x0E: Out of memory
             0x0F: Authentication failed                            0x10: Service unreachable
             0x11: Service non respondind                           0x12: Invalid input
             0x13: Inconsistent product state                       0x14: Service internal failure
             0x15: Bad version                                      0x16: Bad format
             -------------------------------------
             Byte 2: RB account type
             0x00: No type
             0x01: Activation account        0x02: Final account
            "
        ::= { ochmNotifications 75 }

    ochmAnoRBFailureConnectionLost NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Failure on RB connection
             RB connection lost
             -------------
             Byte 1: Cause
             0x00: No cause
             0x01: Stream version error                             0x02: Stream close
             0x03: Proxy authentication required                    0x04: Proxy authentication failed
             0x05: Proxy no supported authentication                0x06: Connection refused
             0x07: DNS error                                        0x08: No supported authentication
             0x09: TLS failed                                       0x0A: TLS not available
             0x0B: Connection compression failed                    0x0C: Input/Output error
             0x0D: Parse error                                      0x0E: Out of memory
             0x0F: Authentication failed                            0x10: Service unreachable
             0x11: Service non respondind                           0x12: Invalid input
             0x13: Inconsistent product state                       0x14: Service internal failure
             0x15: Bad version                                      0x16: Bad format
             -------------------------------------
             Byte 2: RB account type
             0x00: No type
             0x01: Activation account        0x02: Final account
            "
        ::= { ochmNotifications 76 }

    ochmAnoRBFailureBadCredential NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Failure on RB connection
             Bad credential
             -------------
             Byte 1: Cause
             0x00: No cause
             0x01: Stream version error                             0x02: Stream close
             0x03: Proxy authentication required                    0x04: Proxy authentication failed
             0x05: Proxy no supported authentication                0x06: Connection refused
             0x07: DNS error                                        0x08: No supported authentication
             0x09: TLS failed                                       0x0A: TLS not available
             0x0B: Connection compression failed                    0x0C: Input/Output error
             0x0D: Parse error                                      0x0E: Out of memory
             0x0F: Authentication failed                            0x10: Service unreachable
             0x11: Service non respondind                           0x12: Invalid input
             0x13: Inconsistent product state                       0x14: Service internal failure
             0x15: Bad version                                      0x16: Bad format
             -------------------------------------
             Byte 2: RB account type
             0x00: No type
             0x01: Activation account        0x02: Final account
            "
        ::= { ochmNotifications 77 }

    ochmAnoRBFailureServUnreachable NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Failure on RB connection
             Service unreachable
             -------------
             Byte 1: Cause
             0x00: No cause
             0x01: Stream version error                             0x02: Stream close
             0x03: Proxy authentication required                    0x04: Proxy authentication failed
             0x05: Proxy no supported authentication                0x06: Connection refused
             0x07: DNS error                                        0x08: No supported authentication
             0x09: TLS failed                                       0x0A: TLS not available
             0x0B: Connection compression failed                    0x0C: Input/Output error
             0x0D: Parse error                                      0x0E: Out of memory
             0x0F: Authentication failed                            0x10: Service unreachable
             0x11: Service non respondind                           0x12: Invalid input
             0x13: Inconsistent product state                       0x14: Service internal failure
             0x15: Bad version                                      0x16: Bad format
             -------------------------------------
             Byte 2: RB account type
             0x00: No type
             0x01: Activation account        0x02: Final account
            "
        ::= { ochmNotifications 78 }

    ochmAnoRBFailureFinalAccountGetting NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Failure on RB connection
             Final account getting
             -------------
             Byte 1: Cause
             0x00: No cause
             0x01: Stream version error                             0x02: Stream close
             0x03: Proxy authentication required                    0x04: Proxy authentication failed
             0x05: Proxy no supported authentication                0x06: Connection refused
             0x07: DNS error                                        0x08: No supported authentication
             0x09: TLS failed                                       0x0A: TLS not available
             0x0B: Connection compression failed                    0x0C: Input/Output error
             0x0D: Parse error                                      0x0E: Out of memory
             0x0F: Authentication failed                            0x10: Service unreachable
             0x11: Service non respondind                           0x12: Invalid input
             0x13: Inconsistent product state                       0x14: Service internal failure
             0x15: Bad version                                      0x16: Bad format
             -------------------------------------
             Byte 2: RB account type
             0x00: No type
             0x01: Activation account        0x02: Final account
            "
        ::= { ochmNotifications 79 }

    ochmAnoRBFailureFinalAccountACK NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Failure on RB connection
             Final account acknowledgement
             -------------
             Byte 1: Cause
             0x00: No cause
             0x01: Stream version error                             0x02: Stream close
             0x03: Proxy authentication required                    0x04: Proxy authentication failed
             0x05: Proxy no supported authentication                0x06: Connection refused
             0x07: DNS error                                        0x08: No supported authentication
             0x09: TLS failed                                       0x0A: TLS not available
             0x0B: Connection compression failed                    0x0C: Input/Output error
             0x0D: Parse error                                      0x0E: Out of memory
             0x0F: Authentication failed                            0x10: Service unreachable
             0x11: Service non respondind                           0x12: Invalid input
             0x13: Inconsistent product state                       0x14: Service internal failure
             0x15: Bad version                                      0x16: Bad format
             -------------------------------------
             Byte 2: RB account type
             0x00: No type
             0x01: Activation account        0x02: Final account
            "
        ::= { ochmNotifications 80 }

    ochmAnoRBFailureInconsistentRecData NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Failure on RB connection
             Inconsistent received data
             -------------
             Byte 1: Cause
             0x00: No cause
             0x01: Stream version error                             0x02: Stream close
             0x03: Proxy authentication required                    0x04: Proxy authentication failed
             0x05: Proxy no supported authentication                0x06: Connection refused
             0x07: DNS error                                        0x08: No supported authentication
             0x09: TLS failed                                       0x0A: TLS not available
             0x0B: Connection compression failed                    0x0C: Input/Output error
             0x0D: Parse error                                      0x0E: Out of memory
             0x0F: Authentication failed                            0x10: Service unreachable
             0x11: Service non respondind                           0x12: Invalid input
             0x13: Inconsistent product state                       0x14: Service internal failure
             0x15: Bad version                                      0x16: Bad format
             -------------------------------------
             Byte 2: RB account type
             0x00: No type
             0x01: Activation account        0x02: Final account
            "
        ::= { ochmNotifications 81 }

    ochmAnoRBFailureEventNodeError NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Failure on RB connection
             Event node error
             -------------
             Byte 1: Cause
             0x00: No cause
             0x01: Stream version error                             0x02: Stream close
             0x03: Proxy authentication required                    0x04: Proxy authentication failed
             0x05: Proxy no supported authentication                0x06: Connection refused
             0x07: DNS error                                        0x08: No supported authentication
             0x09: TLS failed                                       0x0A: TLS not available
             0x0B: Connection compression failed                    0x0C: Input/Output error
             0x0D: Parse error                                      0x0E: Out of memory
             0x0F: Authentication failed                            0x10: Service unreachable
             0x11: Service non respondind                           0x12: Invalid input
             0x13: Inconsistent product state                       0x14: Service internal failure
             0x15: Bad version                                      0x16: Bad format
             -------------------------------------
             Byte 2: RB account type
             0x00: No type
             0x01: Activation account        0x02: Final account
            "
        ::= { ochmNotifications 82 }

    ochmAnoTempMax NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Max temperature reached.
             -------------
             Byte 1: temperature
            "
        ::= { ochmNotifications 83 }

    ochmDectSyncTreeKo NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Impossible to build the synchronization tree of xBS: the master is ko.
             The DECT site is given by the board parameter.
             Correlation:
             ===========
              1/ First correlation
                 -----------------
               ochmDectSyncTreeKo and ochmDectSyncTreeOk can be
               correlated when the variable ProblemId has the same value

               ochmDectSyncTreeKo: opening of the alarm
               ochmDectSyncTreeOk: closing of the alarm

              2/ Second correlation
                 ------------------
               ochmDectSyncTreeKo and ochmDectSyncAutomatic can be
               correlated when the variable ProblemId has the same value

               ochmDectSyncTreeKo: opening of the alarm
               ochmDectSyncAutomatic: closing of the alarm
            "
        ::= { ochmNotifications 84 }

    ochmDectSyncTreeOk NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Impossible to build the synchronization tree of xBS: the master is ok.
             The DECT site is given by the board parameter.
             Correlation:
             ===========
               ochmDectSyncTreeKo and ochmDectSyncTreeOk can be
               correlated when the variable ProblemId has the same value

               ochmDectSyncTreeKo: opening of the alarm
               ochmDectSyncTreeOk: closing of the alarm
            "
        ::= { ochmNotifications 85 }

    ochmDectSyncManual NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Synchronization mode for xBS: manual.
             The DECT site is given by the board parameter.
            "
        ::= { ochmNotifications 86 }

    ochmDectSyncAutomatic NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "Synchronization mode for xBS: automatic.
             The DECT site is given by the board parameter.
             Correlation:
             ===========
               ochmDectSyncTreeKo and ochmDectSyncAutomatic can be
               correlated when the variable ProblemId has the same value

               ochmDectSyncTreeKo: opening of the alarm
               ochmDectSyncAutomatic: closing of the alarm
            "
        ::= { ochmNotifications 87 }

    ochmDectSyncIslandsChanged NOTIFICATION-TYPE
        OBJECTS {
            ochmSenderType,
            ochmSeverity,
            ochmAlarmTime,
            ochmAlarmName,
            ochmAlarmEvent,
            ochmEquipementInfo,
            ochmComplementInfo,
            ochmEventType,
            ochmProbableCause
        }
        STATUS          current
        DESCRIPTION
            "The number of islands in the synchronization tree has changed.
             The DECT site is given by the board parameter.
             The number of islands is given by the byte 1.
             The normal value is 0.
             When the number gets greater than 0, the DECT synchronization tree in the site has to be analyzed.
             Configuration of clusters has to be considered to get in a normal situation.
            "
        ::= { ochmNotifications 88 }

    -- =====================
    -- Notifications Objects
    -- =====================
    ochmNotificationObjects OBJECT IDENTIFIER
        ::= { ochmNotificationPrefix 1 }

    ochmProblemId OBJECT-TYPE
    	SYNTAX INTEGER
        MAX-ACCESS      accessible-for-notify
        STATUS          current
        DESCRIPTION
            "The value of this object identifies the equipment for
            correlation purpose."
        ::= { ochmNotificationObjects 1 }

    ochmCabinetIndex OBJECT-TYPE
        SYNTAX INTEGER
        MAX-ACCESS      accessible-for-notify
        STATUS          current
        DESCRIPTION
            "Index to access the cabinet in the OXO hardware MIB."
        ::= { ochmNotificationObjects 2 }

    ochmBoardIndex OBJECT-TYPE
        SYNTAX INTEGER
        MAX-ACCESS      accessible-for-notify
        STATUS          current
        DESCRIPTION
            "Index to access the board in the OXO hardware MIB."
        ::= { ochmNotificationObjects 3 }

    ochmFanId OBJECT-TYPE
        SYNTAX INTEGER
        MAX-ACCESS      accessible-for-notify
        STATUS          current
        DESCRIPTION
            "Identifier of the fan in the OXO cabinet."
        ::= { ochmNotificationObjects 4 }

    ochmAccessIndex OBJECT-TYPE
        SYNTAX INTEGER
        MAX-ACCESS      accessible-for-notify
        STATUS          current
        DESCRIPTION
            "Index of the access on an OxO board."
        ::= { ochmNotificationObjects 5 }

    ochmInterfaceNumber OBJECT-TYPE
        SYNTAX INTEGER
        MAX-ACCESS      accessible-for-notify
        STATUS          current
        DESCRIPTION
            "Number of the interface on an IP-LAN board."
        ::= { ochmNotificationObjects 6 }

    ochmSenderType OBJECT-TYPE
        SYNTAX INTEGER {
            type-4760(0),
            type-4400(1),
            type-OXE(2),
            type-OXO(3)
        }
        MAX-ACCESS      accessible-for-notify
        STATUS          current
        DESCRIPTION
         "Type of notification sender"
        ::= { ochmNotificationObjects 7 }

    ochmNotifFaultId OBJECT-TYPE
        SYNTAX INTEGER
        MAX-ACCESS      accessible-for-notify
        STATUS          current
        DESCRIPTION
         "Fault Id sent into an incident notification"
        ::= { ochmNotificationObjects 8 }

    ochmNotifProblemState OBJECT-TYPE
        SYNTAX INTEGER
        MAX-ACCESS      accessible-for-notify
        STATUS          current
        DESCRIPTION
         "Problem state sent into a state notification"
        ::= { ochmNotificationObjects 9 }

    ochmNotifPbxIncidentNumber OBJECT-TYPE
        SYNTAX INTEGER
        MAX-ACCESS      accessible-for-notify
        STATUS          current
        DESCRIPTION
         "Incident Id from the PABX sent into an incident notification"
        ::= { ochmNotificationObjects 10 }

    ochmNotifAlarmId OBJECT-TYPE
        SYNTAX INTEGER
        MAX-ACCESS      accessible-for-notify
        STATUS          current
        DESCRIPTION
         "Incident Id from the Fault Manager sent into an incident
         ochmNotification"
     ::= { ochmNotificationObjects 11 }

    ochmNotifEventType OBJECT-TYPE
        SYNTAX INTEGER
        MAX-ACCESS      accessible-for-notify
        STATUS          current
        DESCRIPTION
         "OSI Type sent into an incident notification"
        ::= { ochmNotificationObjects 12 }

    ochmNotifManagedObject OBJECT-TYPE
        SYNTAX DisplayString (SIZE (0..255))
        MAX-ACCESS      accessible-for-notify
        STATUS          current
        DESCRIPTION
         "Managed object sent into an incident notification"
        ::= { ochmNotificationObjects 13 }

    ochmNotifProbableCause OBJECT-TYPE
        SYNTAX INTEGER
        MAX-ACCESS      accessible-for-notify
        STATUS          current
        DESCRIPTION
         "Cause of alarm sent into an incident notification"
        ::= { ochmNotificationObjects 14 }

    ochmNotifCorrelation OBJECT-TYPE
        SYNTAX INTEGER
        MAX-ACCESS      accessible-for-notify
        STATUS          current
        DESCRIPTION
         "Correlation sent into an incident notification"
        ::= { ochmNotificationObjects 15 }

    ochmNotifPbxReceptionTime OBJECT-TYPE
        SYNTAX OCTET STRING
        MAX-ACCESS      accessible-for-notify
        STATUS          current
        DESCRIPTION
         "Time of reception of an incident from a PABX sent into an incident
          notification"
        ::= { ochmNotificationObjects 16 }

    ochmNmcTicketNumber OBJECT-TYPE
        SYNTAX INTEGER
        MAX-ACCESS      accessible-for-notify
        STATUS          current
        DESCRIPTION
         "Number of NMC Alarm value"
        ::= { ochmNotificationObjects 17 }

	ochmAlarmTime OBJECT-TYPE
        SYNTAX DisplayString (SIZE (0..255))
        MAX-ACCESS      accessible-for-notify
        STATUS          current
        DESCRIPTION
         "Date of Alarm Ticket"
        ::= { ochmNotificationObjects 18 }

    ochmAlarmNumberEvent OBJECT-TYPE
        SYNTAX DisplayString (SIZE (0..255))
        MAX-ACCESS      accessible-for-notify
        STATUS          current
        DESCRIPTION
         "Number of Alarm Event and Sub Event"
        ::= { ochmNotificationObjects 19 }

    ochmEquipementInfo OBJECT-TYPE
        SYNTAX DisplayString (SIZE (0..255))
        MAX-ACCESS      accessible-for-notify
        STATUS          current
        DESCRIPTION
         "Information about Board, Half-board and Slot"
        ::= { ochmNotificationObjects 20 }

    ochmComplementInfo OBJECT-TYPE
        SYNTAX DisplayString (SIZE (0..255))
        MAX-ACCESS      accessible-for-notify
        STATUS          current
        DESCRIPTION
         "Complement information of Alarm Ticket"
        ::= { ochmNotificationObjects 21 }

    ochmEventType OBJECT-TYPE
        SYNTAX INTEGER {
            unknown (0),
            change-Value (1),
            communication-Alarm (2),
            environmental-Alarm (3),
            equipment-Alarm (4),
            object-Creation (6),
            object-Deletion (7),
            processing-Error-Alarm (10),
            quality-Of-Service-Alarm (11),
            change-State (14)
        }
        MAX-ACCESS      accessible-for-notify
        STATUS          current
        DESCRIPTION
         "Type of Event"
        ::= { ochmNotificationObjects 22 }

    ochmProbableCause OBJECT-TYPE
        SYNTAX INTEGER {
            unknown (0),
            adapter-Error (1),
            application-Subsystem-Failure (2),
            band-Width-Reduced (3),
            call-Establishment-Error (4),
            communications-Protocol-Error (5),
            communications-Subsystem-Failure (6),
            configuration-Or-Customization-Error (7),
            congestion (8),
            corruptData (9),
            cpu-Cycles-Limit-Exceeded (10),
            data-Set-Or-Modem-Error (11),
            degraded-Signal (12),
            dte-Dce-Interface-Error (13),
            enclosure-Door-Open (14),
            equipment-Mal-Function (15),
            excessive-Vibration (16),
            file-Error (17),
            fire-Detected (18),
            flood-Detected (19),
            framing-Error (20),
            heating-Ventilation-Cooling-System-Problem (21),
            humidity-Unacceptable (22),
            input-Output-Device-Error (23),
            input-Device-Error (24),
            lAN-Error (25),
            leak-Detected (26),
            local-Node-Transmission-Error (27),
            loss-Of-Frame (28),
            loss-Of-Signal (29),
            material-Supply-Exhausted (30),
            multiplexer-Problem (31),
            out-Of-Memory (32),
            output-Device-Error (33),
            performance-Degraded (34),
            power-Problem (35),
            pressure-Unacceptable (36),
            processor-Problem (37),
            pump-Failure (38),
            queue-Size-Exceeded (39),
            receive-Failure (40),
            receiver-Failure (41),
            remote-Node-Transmission-Failure (42),
            resource-At-Or-Nearing-Capacity (43),
            response-Time-Excessive (44),
            retransmission-Rate-Excessive (45),
            software-Error (46),
            software-Program-Ab-normally-Terminated (47),
            software-Program-Error (48),
            storage-Capacity-Problem (49),
            temperature-Unacceptable (50),
            threshold-Crossed (51),
            timing-Problem (52),
            toxic-Leak-Detected (53),
            transmit-Failure (54),
            transmitter-Failure (55),
            underlying-Resource-Unavailable (56),
            version-Mismatch (57)
        }
        MAX-ACCESS      accessible-for-notify
        STATUS          current
        DESCRIPTION
         "Probable cause of incident"
        ::= { ochmNotificationObjects 23 }

    ochmSeverity OBJECT-TYPE
        SYNTAX INTEGER {
            reserved (0),
            critical (1),
            major (2),
            minor (3),
            warning (4),
            indeterminate (5),
            clear (6)
        }
        MAX-ACCESS      accessible-for-notify
        STATUS          current
        DESCRIPTION
         "Severity of incident"
        ::= { ochmNotificationObjects 24 }

    ochmAlarmName OBJECT-TYPE
        SYNTAX INTEGER {
			fan-status (21),
			power-saving (22),
			board-power-off (23),
			fan-status-210 (25),
			server-certificate-status (26),
			msdb-health-status (27),
			unsupported-ram-size (28),
			ano-register-unregistration (30),
			ano-register-ok (31),
			ano-register-500 (32),
			ano-register-423 (33),
			ano-register-400 (34),
			ano-register-403 (35),
			ano-register-404 (36),
			ano-register-timeout (37),
			ano-register-failed (38),
			remote-access-mbx-locked (39),
			ano-register-reject (40),
			remote-access-mbx-unlocked (41),
			remote-access-wsapi-locked (42),
			remote-access-wsapi-unlocked (43),
			arp-spoof-info (44),
			mgtsrv-lock (45),
			term-reboot-or-reset-of-user-data (46),
			public-ddi-registration-limit-exceed (47),
			default-password-found (48),
			easy-password-found (49),
			ano-quarantine-alert (50),
			ano-clock (51),
			ano-link (52),
			ano-pra-alarm (53),
			ano-isdn-layer1 (58),
			ano-vowlan-access (59),
			ano-mem-flow-ctrl (62),
			ano-ext-s0 (70),
			ano-s0-access (71),
			ano-printer-ko (72),
			ano-printer-ok (73),
			ano-printer-fault (74),
			ano-isdn-access (76),
			ano-restart-failed (77),
			dhcp-server-exited (80),
			dhcp-server-status (81),
			system-auto-provision (84),
			msg-buff-full (91),
			obc-anomaly (92),
			ctrl-dsp-resource-ko (94),
			ctrl-dsp-result-codes (95),
			ctrl-dsp-ko (96),
			ano-dbms-suicide (97),
			cpu-ko (98),
			ano-boost-ko (99),
			board-oper (100),
			board-unplugged (101),
			board-not-opered (102),
			board-cleared (103),
			board-temp-reset (104),
			board-perm-reset (105),
			board-refused (106),
			dev-refused (107),
			dev-error (108),
			itf-refused (109),
			system-restart (110),
			ano-swl-reduced (111),
			mmc-board-reset (112),
			dev-accepted (113),
			change-swl-state (114),
			system-restart-210 (115),
			system-oper-210 (116),
			cabinet-oper (117),
			cabinet-unplugged (118),
			cabinet-refused (119),
			main-failure (125),
			mmc-start (130),
			mmc-stop (131),
            local-mgt-pwd-reset (132),
			tei-delete (135),
			ano-data-sav-option (140),
			ano-active-mmc-session (141),
			dect-unknown-ipui (142),
			ano-restore-ko (145),
			ano-backup-ok (146),
			ano-restore-ok (147),
			ano-backup-ko (148),
			ano-memory-avail (150),
			download (151),
			swap (152),
			nmc-threshold-hardware-tbl (160),
			nmc-threshold-history-tbl (161),
			nmc-threshold-metering-tbl (162),
			nmc-threshold-urgent-tbl (163),
			nmc-hardware-tbl-full (164),
			nmc-history-tbl-full (165),
			nmc-metering-tbl-full (166),
			nmc-urgent-tbl-full (167),
			nmc-connexion-start (168),
			nmc-connexion-end (169),
			nmc-erroneous-call (171),
			nmc-non-answered-call (172),
			nmc-info-timeout (173),
			nmc-put-data-timeout (174),
			nmc-wait-ack-timeout (175),
			nmc-phone-nb-missing (176),
			nmc-ano-adr-not-registered (177),
			nmc-unexpected-alarm (179),
			nmc-not-allowed-call (180),
			priority-call (181),
			no-voice-msg-available (182),
			vmu-mem-threshold (183),
			vp-open-failed (184),
			vp-close-failed (185),
			vp-read-failed (186),
			vp-write-failed (187),
			vp-lseek-failed (188),
			vp-truncate-failed (189),
			dect-sync-status (191),
			ano-save-started (200),
			ano-restore-started (201),
			ano-ibs-sync-ua0 (202),
			ano-ibs-sync-ua1 (203),
			ano-ibs-dsp-alive (204),
			ano-ibs-dsp-serial (205),
			ano-ibs-init-boot (206),
			ano-ibs-download (207),
			ano-ibs-up-buffer-full (208),
			ano-ibs-down-buffer-full (209),
			ano-ibs-wrong-link-id (210),
			ano-ibs-invalid-slave-access (211),
			ibs-decm-conflict (212),
			ibs-freq-reject (213),
			curconv (214),
			ano-ibs-ua-length-pb (215),
			ano-ibs-unwanted-msg (216),
			ano-ibs-wrong-freq-selection (217),
			ano-ibs-sync-ua0-210 (218),
			ano-ibs-sync-ua1-210 (219),
			ano-voip-dsp-ko (220),
			ano-ethernet-down (221),
			ano-ethernet-up (222),
			ano-gateway-down (223),
			ano-gateway-up (224),
			ano-gateway-traffic (225),
			ano-ext-gatekeeper (226),
			ano-not-enough-ip-trunk (227),
			ano-not-enough-dsp (228),
			ano-no-more-tscip-dyn-addr (229),
			ano-ext-gatekeeper-rej (230),
			ano-mass-storage-medium (236),
			ano-erased-cmos (237),
			ano-failsafe-mode (238),
			email (239),
			security (240),
			network (241),
			access (242),
			remote-access (243),
			data-config (244),
			ano-startup-script (231),
			noe-dld-success (251),
			ano-noe-dld-fail (252),
			swl-soon-expired (253),
			remote-access-mbx-locked (254),
			busy-trunk-call-failed (255)
        }
        MAX-ACCESS      accessible-for-notify
        STATUS          current
        DESCRIPTION
         "Alarm name incident"
        ::= { ochmNotificationObjects 25 }

END
