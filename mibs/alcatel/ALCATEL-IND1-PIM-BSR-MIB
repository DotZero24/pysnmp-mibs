ALCATEL-IND1-PIM-BSR-MIB DEFINITIONS ::= BEGIN

IMPORTS
    routingIND1Pim                   FROM ALCATEL-IND1-BASE
    MODULE-IDENTITY, OBJECT-TYPE,
    NOTIFICATION-TYPE,
    Unsigned32, TimeTicks            FROM SNMPv2-SMI
    RowStatus, TruthValue            FROM SNMPv2-TC
    MODULE-COMPLIANCE, OBJECT-GROUP,
    NOTIFICATION-GROUP               FROM SNMPv2-CONF
    InetAddressType,
    InetAddressPrefixLength,
    InetAddress                      FROM INET-ADDRESS-MIB;

alaPimBsrMIB MODULE-IDENTITY
    LAST-UPDATED "200707020000Z"
    ORGANIZATION "Alcatel-Lucent"
    CONTACT-INFO
        "Please consult with Customer Service to insure the most appropriate
         version of this document is used with the products in question:

                 Alcatel-Lucent, Enterprise Solutions Division
                (Formerly Alcatel Internetworking, Incorporated)
                           26801 West Agoura Road
                        Agoura Hills, CA  91301-5122
                          United States Of America

        Telephone:               North America  +1 800 995 2696
                                 Latin America  +1 877 919 9526
                                 Europe         +31 23 556 0100
                                 Asia           +65 394 7933
                                 All Other      +1 818 878 4507

        Electronic Mail:         support@ind.alcatel.com
        World Wide Web:          http://alcatel-lucent.com/wps/portal/enterprise
        File Transfer Protocol:  ftp://ftp.ind.alcatel.com/pub/products/mibs"
    DESCRIPTION
        "This module describes an authoritative enterprise-specific Simple
         Network Management Protocol (SNMP) Management Information Base (MIB):

             This proprietary MIB contains management information for
             the Bootstrap Router (BSR) mechanism for PIM routers.
             This MIB is based on the Internet Draft
             <draft-ietf-pim-bsr-mib-02.txt> developed by
             the IETF PIM Working Group.

         The right to make changes in specification and other information
         contained in this document without prior notice is reserved.

         No liability shall be assumed for any incidental, indirect, special, or
         consequential damages whatsoever arising from or related to this
         document or the information contained herein.

         Vendors, end-users, and other interested parties are granted
         non-exclusive license to use this specification in connection with
         management of the products for which it is intended to be used.

           Copyright (C) 1995-2007 Alcatel-Lucent
                         ALL RIGHTS RESERVED WORLDWIDE"
    REVISION     "200707020000Z"
    DESCRIPTION  "The latest version of this MIB Module."
    ::= { routingIND1Pim 3 }

--
-- Top-level structure
--

alaPimBsrNotifications OBJECT IDENTIFIER ::= { alaPimBsrMIB 0 }
alaPimBsrObjects       OBJECT IDENTIFIER ::= { alaPimBsrMIB 1 }

--
-- Conformance Information
--

alaPimBsrConformance OBJECT IDENTIFIER ::= { alaPimBsrMIB 2 }
alaPimBsrCompliances OBJECT IDENTIFIER ::= { alaPimBsrConformance 1 }
alaPimBsrGroups      OBJECT IDENTIFIER ::= { alaPimBsrConformance 2 }

--
-- The BSR Candidate-RP Table
--

alaPimBsrCandidateRPTable OBJECT-TYPE
    SYNTAX     SEQUENCE OF AlaPimBsrCandidateRPEntry
    MAX-ACCESS not-accessible
    STATUS     current
    DESCRIPTION
            "The (conceptual) table listing the IP multicast group
            prefixes for which the local router is to advertise
            itself as a Candidate-RP."
    ::= { alaPimBsrObjects 1 }

alaPimBsrCandidateRPEntry OBJECT-TYPE
    SYNTAX     AlaPimBsrCandidateRPEntry
    MAX-ACCESS not-accessible
    STATUS     current
    DESCRIPTION
            "An entry (conceptual row) in the alaBsrCandidateRPTable."
    INDEX      { alaPimBsrCandidateRPAddressType,
                 alaPimBsrCandidateRPAddress,
                 alaPimBsrCandidateRPGroupAddress,
                 alaPimBsrCandidateRPGroupPrefixLength }
    ::= { alaPimBsrCandidateRPTable 1 }

AlaPimBsrCandidateRPEntry ::= SEQUENCE {
    alaPimBsrCandidateRPAddressType       InetAddressType,
    alaPimBsrCandidateRPAddress           InetAddress,
    alaPimBsrCandidateRPGroupAddress      InetAddress,
    alaPimBsrCandidateRPGroupPrefixLength InetAddressPrefixLength,
    alaPimBsrCandidateRPBidir             TruthValue,
    alaPimBsrCandidateRPAdvTimer          TimeTicks,
    alaPimBsrCandidateRPPriority          Unsigned32,
    alaPimBsrCandidateRPAdvInterval       Unsigned32,
    alaPimBsrCandidateRPHoldtime          Unsigned32,
    alaPimBsrCandidateRPStatus            RowStatus
}

alaPimBsrCandidateRPAddressType OBJECT-TYPE
    SYNTAX     InetAddressType
    MAX-ACCESS not-accessible
    STATUS     current
    DESCRIPTION
            "The Inet address type of the Candidate-RP."
    ::= { alaPimBsrCandidateRPEntry 1 }

alaPimBsrCandidateRPAddress OBJECT-TYPE
    SYNTAX     InetAddress (SIZE (4|8|16|20))
    MAX-ACCESS not-accessible
    STATUS     current
    DESCRIPTION
            "The (unicast) address which will be advertised as a
            Candidate-RP.  The InetAddressType is given by the
            alaPimBsrCandidateRPAddressType object."
    ::= { alaPimBsrCandidateRPEntry 2 }

alaPimBsrCandidateRPGroupAddress OBJECT-TYPE
    SYNTAX     InetAddress (SIZE (4|8|16|20))
    MAX-ACCESS not-accessible
    STATUS     current
    DESCRIPTION
            "The IP multicast group address which, when combined with
            the corresponding value of
            alaPimBsrCandidateRPGroupPrefixLength, identifies a group
            prefix for which the local router will advertise itself
            as a Candidate-RP. The InetAddressType is given by the
            alaPimBsrCandidateRPAddressType object."
    ::= { alaPimBsrCandidateRPEntry 3 }

alaPimBsrCandidateRPGroupPrefixLength OBJECT-TYPE
    SYNTAX     InetAddressPrefixLength (4..128)
    MAX-ACCESS not-accessible
    STATUS     current
    DESCRIPTION
            "The multicast group address mask which, when combined
            with the corresponding value of
            alaPimBsrCandidateRPGroupAddress, identifies a group prefix
            for which the local router will advertise itself as a
            Candidate-RP.  The InetAddressType is given by the
            alaPimBsrCandidateRPAddressType object."
    ::= { alaPimBsrCandidateRPEntry 4 }

alaPimBsrCandidateRPBidir OBJECT-TYPE
    SYNTAX     TruthValue
    MAX-ACCESS read-create
    STATUS     current
    DESCRIPTION
            "If this object is set to TRUE, this group range is
            advertised with this RP as a BIDIR-PIM group range. If
            it is set to FALSE, it is advertised as a PIM-SM group
            range."
    DEFVAL { false }
    ::= { alaPimBsrCandidateRPEntry 5 }

alaPimBsrCandidateRPAdvTimer OBJECT-TYPE
    SYNTAX     TimeTicks
    MAX-ACCESS read-only
    STATUS     current
    DESCRIPTION
            "The time remaining before the local router next sends
            a Candidate-RP-Advertisement to the elected BSR for
            this address type."
    ::= { alaPimBsrCandidateRPEntry 6 }

alaPimBsrCandidateRPPriority OBJECT-TYPE
    SYNTAX     Unsigned32 (0..255)
    MAX-ACCESS read-create
    STATUS     current
    DESCRIPTION
            "The priority for this Candidate RP advertised in
             Candidate-RP-Advertisements."
    REFERENCE "I-D.ietf-pim-sm-bsr section 3.2"
    DEFVAL { 192 }
    ::= { alaPimBsrCandidateRPEntry 7 }

alaPimBsrCandidateRPAdvInterval OBJECT-TYPE
    SYNTAX     Unsigned32 (0..26214)
    MAX-ACCESS read-create
    STATUS     current
    DESCRIPTION
            "A Candidate RP generates Candidate-RP-Advertisements
            periodically. This object represents the time interval
            in seconds between two consecutive advertisements."
    REFERENCE "I-D.ietf-pim-sm-bsr section 3.2 and section 5"
    DEFVAL { 60 }
    ::= { alaPimBsrCandidateRPEntry 8 }

alaPimBsrCandidateRPHoldtime OBJECT-TYPE
    SYNTAX     Unsigned32 (0..65535)
    MAX-ACCESS read-create
    STATUS     current
    DESCRIPTION
         "Holdtime for this Candidate RP. The amount of time (in
         seconds) this Candidate-RP entry is valid."
    REFERENCE "I-D.ietf-pim-sm-bsr section 4.2"
    DEFVAL { 150 }
    ::= { alaPimBsrCandidateRPEntry 9 }

alaPimBsrCandidateRPStatus OBJECT-TYPE
    SYNTAX     RowStatus
    MAX-ACCESS read-create
    STATUS     current
    DESCRIPTION
            "The status of this row, by which new entries may be
            created, or old entries deleted from this table."
    ::= { alaPimBsrCandidateRPEntry 10 }

--
-- The BSR Elected BSR RP-Set Table
--

alaPimBsrElectedBSRRPSetTable OBJECT-TYPE
    SYNTAX     SEQUENCE OF AlaPimBsrElectedBSRRPSetEntry
    MAX-ACCESS not-accessible
    STATUS     current
    DESCRIPTION
            "The (conceptual) table listing BSR-specific information
            about PIM group mappings learned via C-RP advertisements
            or created locally using configurations. This table is
            maintained only on the Elected BSR.

            An Elected BSR uses this table to create Bootstrap
            Messages after applying a local policy to include some
            or all of the group mappings in this table."

    ::= { alaPimBsrObjects 2 }

alaPimBsrElectedBSRRPSetEntry OBJECT-TYPE
    SYNTAX     AlaPimBsrElectedBSRRPSetEntry
    MAX-ACCESS not-accessible
    STATUS     current
    DESCRIPTION
            "An entry (conceptual row) in the
             alaPimBsrElectedBSRRPSetTable."
    INDEX      { alaPimBsrElectedBSRGrpMappingAddrType,
                 alaPimBsrElectedBSRGrpMappingGrpAddr,
                 alaPimBsrElectedBSRGrpMappingGrpPrefixLen,
                 alaPimBsrElectedBSRGrpMappingRPAddr }
    ::= { alaPimBsrElectedBSRRPSetTable 1 }

AlaPimBsrElectedBSRRPSetEntry ::= SEQUENCE {
    alaPimBsrElectedBSRGrpMappingAddrType      InetAddressType,
    alaPimBsrElectedBSRGrpMappingGrpAddr       InetAddress,
    alaPimBsrElectedBSRGrpMappingGrpPrefixLen  InetAddressPrefixLength,
    alaPimBsrElectedBSRGrpMappingRPAddr        InetAddress,
    alaPimBsrElectedBSRRPSetPriority           Unsigned32,
    alaPimBsrElectedBSRRPSetHoldtime           Unsigned32,
    alaPimBsrElectedBSRRPSetExpiryTime         TimeTicks,
    alaPimBsrElectedBSRRPSetGrpBidir           TruthValue
}

alaPimBsrElectedBSRGrpMappingAddrType OBJECT-TYPE
    SYNTAX     InetAddressType
    MAX-ACCESS not-accessible
    STATUS     current
    DESCRIPTION
            "The Inet address type of the IP multicast group
            prefix."
    ::= { alaPimBsrElectedBSRRPSetEntry 2 }

alaPimBsrElectedBSRGrpMappingGrpAddr OBJECT-TYPE
    SYNTAX     InetAddress (SIZE (4|8|16|20))
    MAX-ACCESS not-accessible
    STATUS     current
    DESCRIPTION
         "The IP multicast group address which, when combined
         with alaPimBsrElectedBSRGrpMappingGrpPrefixLen, gives the
         group prefix for this mapping.  The InetAddressType is
         given by the alaPimBsrElectedBSRGrpMappingAddrType object.

         This address object is only significant up to
         alaPimBsrElectedBSRGrpMappingGrpPrefixLen bits. The
         remainder of the address bits are zero.  This is
         especially important for this field, which is part of
         the index of this entry.  Any non-zero bits would
         signify an entirely different entry."
    ::= { alaPimBsrElectedBSRRPSetEntry 3 }

alaPimBsrElectedBSRGrpMappingGrpPrefixLen OBJECT-TYPE
    SYNTAX     InetAddressPrefixLength (4..128)
    MAX-ACCESS not-accessible
    STATUS     current
    DESCRIPTION
            "The multicast group prefix length that, when combined
            with alaPimBsrElectedBSRGrpMappingGrpAddr, gives the group
            prefix for this mapping.  The InetAddressType is given by
            the alaPimBsrElectedBSRGrpMappingAddrType object.  If
            alaPimBsrElectedBSRGrpMappingAddrType is 'ipv4' or 'ipv4z',
            this object must be in the range 4..32.  If
            alaPimBsrElectedBSRGrpMappingAddrType is 'ipv6' or 'ipv6z',
            this object must be in the range 8..128."
    ::= { alaPimBsrElectedBSRRPSetEntry 4 }

alaPimBsrElectedBSRGrpMappingRPAddr OBJECT-TYPE
    SYNTAX     InetAddress (SIZE (4|8|16|20))
    MAX-ACCESS not-accessible
    STATUS     current
    DESCRIPTION
            "The IP address of the RP to be used for groups within
            this group prefix. The InetAddressType is given by the
            alaPimBsrElectedBSRGrpMappingAddrType object."
    ::= { alaPimBsrElectedBSRRPSetEntry 5 }

alaPimBsrElectedBSRRPSetPriority OBJECT-TYPE
    SYNTAX     Unsigned32 (0..255)
    MAX-ACCESS read-only
    STATUS     current
    DESCRIPTION
            "The priority for RP. Numerically higher values for
            this object indicate lower priorities, with the value
            zero denoting the highest priority."
    REFERENCE "I-D.ietf-pim-sm-bsr section 4.1"
    ::= { alaPimBsrElectedBSRRPSetEntry 6 }

alaPimBsrElectedBSRRPSetHoldtime OBJECT-TYPE
    SYNTAX     Unsigned32 (0..65535)
    UNITS      "seconds"
    MAX-ACCESS read-only
    STATUS     current
    DESCRIPTION
            "The holdtime for RP"
    REFERENCE "I-D.ietf-pim-sm-bsr section 4.1"
    ::= { alaPimBsrElectedBSRRPSetEntry 7 }

alaPimBsrElectedBSRRPSetExpiryTime OBJECT-TYPE
    SYNTAX     TimeTicks
    MAX-ACCESS read-only
    STATUS     current
    DESCRIPTION
            "The minimum time remaining before this entry will be
            aged out.  The value zero indicates that this entry will
            never be aged out."
    ::= { alaPimBsrElectedBSRRPSetEntry 8 }

alaPimBsrElectedBSRRPSetGrpBidir OBJECT-TYPE
    SYNTAX     TruthValue
    MAX-ACCESS read-only
    STATUS     current
    DESCRIPTION
            "If this object is TRUE, this group range with this
            RP is a BIDIR-PIM group range. If it is set to FALSE,
            it is a PIM-SM group range."
    ::= { alaPimBsrElectedBSRRPSetEntry 9 }

--
-- The BSR Candidate-BSR Table
--

alaPimBsrCandidateBSRTable OBJECT-TYPE
    SYNTAX     SEQUENCE OF AlaPimBsrCandidateBSREntry
    MAX-ACCESS not-accessible
    STATUS     current
    DESCRIPTION
            "The (conceptual) table containing Candidate-BSR
            configuration for the local router.  The table contains
            one row for each address family for which the local
            router is to advertise itself as a Candidate-BSR."
    ::= { alaPimBsrObjects 3 }

alaPimBsrCandidateBSREntry OBJECT-TYPE
    SYNTAX     AlaPimBsrCandidateBSREntry
    MAX-ACCESS not-accessible
    STATUS     current
    DESCRIPTION
            "An entry (conceptual row) in the alaPimBsrCandidateBSRTable."
    INDEX      { alaPimBsrCandidateBSRAddressType }
    ::= { alaPimBsrCandidateBSRTable 1 }

AlaPimBsrCandidateBSREntry ::= SEQUENCE {
    alaPimBsrCandidateBSRAddressType      InetAddressType,
    alaPimBsrCandidateBSRAddress          InetAddress,
    alaPimBsrCandidateBSRPriority         Unsigned32,
    alaPimBsrCandidateBSRHashMaskLength   Unsigned32,
    alaPimBsrCandidateBSRElectedBSR       TruthValue,
    alaPimBsrCandidateBSRBootstrapTimer   TimeTicks,
    alaPimBsrCandidateBSRStatus           RowStatus
}

alaPimBsrCandidateBSRAddressType OBJECT-TYPE
    SYNTAX     InetAddressType
    MAX-ACCESS not-accessible
    STATUS     current
    DESCRIPTION
            "The address type of the Candidate-BSR."
    ::= { alaPimBsrCandidateBSREntry 1 }

alaPimBsrCandidateBSRAddress OBJECT-TYPE
    SYNTAX     InetAddress
    MAX-ACCESS read-create
    STATUS     current
    DESCRIPTION
            "The (unicast) address which the local router will
            use to advertise itself as a Candidate-BSR.  The
            InetAddressType is given by the
            alaPimBsrCandidateBSRAddressType object."
    ::= { alaPimBsrCandidateBSREntry 2 }

alaPimBsrCandidateBSRPriority OBJECT-TYPE
    SYNTAX     Unsigned32 (0..255)
    MAX-ACCESS read-create
    STATUS     current
    DESCRIPTION
            "The priority value for the local router as a
            Candidate-BSR for this address type. Numerically higher
            values for this object indicate higher priorities."
    DEFVAL { 64 }
    ::= { alaPimBsrCandidateBSREntry 3 }

alaPimBsrCandidateBSRHashMaskLength OBJECT-TYPE
    SYNTAX     Unsigned32 (0..128)
    MAX-ACCESS read-create
    STATUS     current
    DESCRIPTION
            "The hash mask length (used in the RP hash function)
            that the local router will advertise in its Bootstrap
            messages for this address type.  This object defaults
            to 30 if alaPimBsrCandidateBSRAddressType is 'ipv4' or 'ipv4z'
            , and defaults to 126 if alaPimBsrCandidateBSRAddressType is
            'ipv6' or 'ipv6z'."
    -- DEFVAL { 30 or 126 }
    ::= { alaPimBsrCandidateBSREntry 4 }

alaPimBsrCandidateBSRElectedBSR OBJECT-TYPE
    SYNTAX     TruthValue
    MAX-ACCESS read-only
    STATUS     current
    DESCRIPTION
            "Whether the local router is the elected BSR for this
            address type."
    ::= { alaPimBsrCandidateBSREntry 5 }

alaPimBsrCandidateBSRBootstrapTimer OBJECT-TYPE
    SYNTAX     TimeTicks
    MAX-ACCESS read-only
    STATUS     current
    DESCRIPTION
            "The time remaining before the local router next
            originates a Bootstrap message for this address type.
            Value of this object is zero if
            alaPimBsrCandidateBSRElectedBSR is 'FALSE'."
    ::= { alaPimBsrCandidateBSREntry 6 }

alaPimBsrCandidateBSRStatus OBJECT-TYPE
    SYNTAX     RowStatus
    MAX-ACCESS read-create
    STATUS     current
    DESCRIPTION
            "The status of this row, by which new entries may
            be created, or old entries deleted from this table."
    ::= { alaPimBsrCandidateBSREntry 7 }

--
-- The BSR Elected-BSR Table
--

alaPimBsrElectedBSRTable OBJECT-TYPE
    SYNTAX     SEQUENCE OF AlaPimBsrElectedBSREntry
    MAX-ACCESS not-accessible
    STATUS     current
    DESCRIPTION
            "The (conceptual) table containing information about
            elected BSRs.  The table contains one row for each
            address family for which there is an elected BSR."
    ::= { alaPimBsrObjects 4 }

alaPimBsrElectedBSREntry OBJECT-TYPE
    SYNTAX     AlaPimBsrElectedBSREntry
    MAX-ACCESS not-accessible
    STATUS     current
    DESCRIPTION
            "An entry (conceptual row) in the alaPimBsrElectedBSRTable."
    INDEX      { alaPimBsrElectedBSRAddressType }
    ::= { alaPimBsrElectedBSRTable 1 }

AlaPimBsrElectedBSREntry ::= SEQUENCE {
    alaPimBsrElectedBSRAddressType      InetAddressType,
    alaPimBsrElectedBSRAddress          InetAddress,
    alaPimBsrElectedBSRPriority         Unsigned32,
    alaPimBsrElectedBSRHashMaskLength   Unsigned32,
    alaPimBsrElectedBSRExpiryTime       TimeTicks
}

alaPimBsrElectedBSRAddressType OBJECT-TYPE
    SYNTAX     InetAddressType
    MAX-ACCESS not-accessible
    STATUS     current
    DESCRIPTION
            "The address type of the elected BSR."
    ::= { alaPimBsrElectedBSREntry 1 }

alaPimBsrElectedBSRAddress OBJECT-TYPE
    SYNTAX     InetAddress (SIZE (4|8|16|20))
    MAX-ACCESS read-only
    STATUS     current
    DESCRIPTION
            "The (unicast) address of the elected BSR.  The
            InetAddressType is given by the alaPimBsrElectedBSRAddressType
            object."
    ::= { alaPimBsrElectedBSREntry 2 }

alaPimBsrElectedBSRPriority OBJECT-TYPE
    SYNTAX     Unsigned32 (0..255)
    MAX-ACCESS read-only
    STATUS     current
    DESCRIPTION
            "The priority value for the elected BSR for this address
            type.  Numerically higher values for this object indicate
            higher priorities."
    ::= { alaPimBsrElectedBSREntry 3 }

alaPimBsrElectedBSRHashMaskLength OBJECT-TYPE
    SYNTAX     Unsigned32 (0..128)
    MAX-ACCESS read-only
    STATUS     current
    DESCRIPTION
            "The hash mask length (used in the RP hash function)
            advertised by the elected BSR for this address type."
    ::= { alaPimBsrElectedBSREntry 4 }

alaPimBsrElectedBSRExpiryTime OBJECT-TYPE
    SYNTAX     TimeTicks
    MAX-ACCESS read-only
    STATUS     current
    DESCRIPTION
            "The minimum time remaining before the elected BSR for
            this address type will be declared down."
    ::= { alaPimBsrElectedBSREntry 5 }

--
-- PIM BSR Notifications
--

alaPimBsrElectedBSRLostElection   NOTIFICATION-TYPE
    OBJECTS { alaPimBsrCandidateBSRElectedBSR }
    STATUS     current
    DESCRIPTION
            "A alaPimBsrElectedBSRLostElection trap should be generated
            when current E-BSR lost election to a new Candidate
            BSR
            current E-BSR, start sending BootStrap Messages. Only
            an E-BSR should generate this trap.

            This notification is generated when
            alaPimBsrCandidateBSRElectedBSR becomes FALSE."
    REFERENCE "I-D.ietf-pim-sm-bsr section 3.1"
    ::= { alaPimBsrNotifications 1 }

alaPimBsrCandidateBSRWinElection   NOTIFICATION-TYPE
    OBJECTS { alaPimBsrCandidateBSRElectedBSR }
    STATUS     current
    DESCRIPTION
            "A alaPimBsrCandidateBSRWinElection trap should be generated
            when a C-BSR wins BSR Election. Only an E-BSR should
            generate this trap.

            This notification is generated when
            alaPimBsrCandidateBSRElectedBSR becomes TRUE"

    REFERENCE "I-D.ietf-pim-sm-bsr section 3.1"
    ::= { alaPimBsrNotifications 2 }

--
-- Compliance Statements
--

alaPimBsrCompliance MODULE-COMPLIANCE
    STATUS  current
    DESCRIPTION
            "The compliance statement for PIM routers that implement
            the Bootstrap Router (BSR) mechanism."
    MODULE  -- this module
    MANDATORY-GROUPS { alaPimBsrObjectGroup }

      GROUP   alaPimBsrDiagnosticsGroup
      DESCRIPTION
          "This group is optional."

    ::= { alaPimBsrCompliances 1 }

--
-- Units of Conformance
--

alaPimBsrObjectGroup OBJECT-GROUP
    OBJECTS { alaPimBsrCandidateRPBidir,
              alaPimBsrCandidateRPAdvTimer,
              alaPimBsrCandidateRPPriority,
              alaPimBsrCandidateRPAdvInterval,
              alaPimBsrCandidateRPHoldtime,
              alaPimBsrCandidateRPStatus,
              alaPimBsrElectedBSRRPSetPriority,
              alaPimBsrElectedBSRRPSetHoldtime,
              alaPimBsrElectedBSRRPSetExpiryTime,
              alaPimBsrElectedBSRRPSetGrpBidir,
              alaPimBsrCandidateBSRAddress,
              alaPimBsrCandidateBSRPriority,
              alaPimBsrCandidateBSRHashMaskLength,
              alaPimBsrCandidateBSRElectedBSR,
              alaPimBsrCandidateBSRBootstrapTimer,
              alaPimBsrCandidateBSRStatus,
              alaPimBsrElectedBSRAddress,
              alaPimBsrElectedBSRPriority,
              alaPimBsrElectedBSRHashMaskLength,
              alaPimBsrElectedBSRExpiryTime }
    STATUS  current
    DESCRIPTION
            "A collection of objects for managing PIM routers."
    ::= { alaPimBsrGroups 1 }

alaPimBsrDiagnosticsGroup NOTIFICATION-GROUP
    NOTIFICATIONS { alaPimBsrElectedBSRLostElection,
                    alaPimBsrCandidateBSRWinElection }
    STATUS  current
    DESCRIPTION
            "Objects providing additonal diagnostics related to BSR
            mechanism of PIM router."
    ::= { alaPimBsrGroups 2 }

END
