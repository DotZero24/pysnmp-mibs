C-PRODUCT-E3-MIB DEFINITIONS ::= BEGIN


IMPORTS
    e3card                            FROM C-PRODUCT-GROUP-MIB
    portSlot, portNumber, TimeAndDate FROM C-PRODUCT-BASE-MIB
    Gauge                             FROM RFC1155-SMI
    OBJECT-TYPE                       FROM RFC-1212;

-- E3 groups

e3Port      OBJECT IDENTIFIER ::= { e3card 1 }
e3PortStats OBJECT IDENTIFIER ::= { e3card 2 }
e3PortClearStats OBJECT IDENTIFIER ::= { e3card 3 }

-- E3 Port Group (e3Port)

e3PortTable OBJECT-TYPE
    SYNTAX SEQUENCE OF E3PortEntry
    ACCESS not-accessible
    STATUS mandatory
    DESCRIPTION
            "The E3 port information table."
    ::= { e3Port 1 }

e3PortEntry OBJECT-TYPE
    SYNTAX E3PortEntry
    ACCESS not-accessible
    STATUS mandatory
    DESCRIPTION
            "Information about a E3 port."
    INDEX { portSlot, portNumber }
    ::= { e3PortTable 1 }

E3PortEntry ::=
    SEQUENCE {
        e3PortLoopbackType
            INTEGER,
        e3PortPeakRate
            INTEGER,
        e3PortCellMap
            INTEGER,
        e3PortScramble
            INTEGER,
        e3PortTiming
            INTEGER,
        e3PortPlcpTiming
            INTEGER,
        e3PortCtxTiming
            INTEGER,
        e3PortLineRate
            INTEGER
    }

e3PortLoopbackType OBJECT-TYPE
    SYNTAX INTEGER { none        (1), -- no loopback
                     networkLine (2),
                     localCard   (3),
                     networkCard (4) }
    ACCESS read-write
    STATUS mandatory
    DESCRIPTION
            "Loopback type of the E3 port."
    DEFVAL { none }
    ::= { e3PortEntry 1 }

e3PortPeakRate OBJECT-TYPE
    SYNTAX INTEGER (5..34)
    ACCESS read-write
    STATUS mandatory
    DESCRIPTION
            "Peak data transfer rate of the E3 port.  Unit: Mbps."
    ::= { e3PortEntry 2 }

e3PortCellMap OBJECT-TYPE
    SYNTAX INTEGER { clear(1),
                     plcp(2) }
    ACCESS read-write
    STATUS mandatory
    DESCRIPTION
            "ATM cell mapping for the E3 port."
    DEFVAL { clear }
    ::= { e3PortEntry 3 }

e3PortScramble OBJECT-TYPE
    SYNTAX INTEGER { no(1),
                     yes(2) }
    ACCESS read-write
    STATUS mandatory
    DESCRIPTION
            "ATM payload scrambling for the E3 port."
    DEFVAL { yes }
    ::= { e3PortEntry 4 }

e3PortTiming OBJECT-TYPE
    SYNTAX INTEGER { loop(1),
                     system(2) }
    ACCESS read-write
    STATUS mandatory
    DESCRIPTION
            "E3 timing source."
    DEFVAL { system }
    ::= { e3PortEntry 5 }

e3PortPlcpTiming OBJECT-TYPE
    SYNTAX INTEGER { e3Timing(1),
                     systemClock(2) }
    ACCESS read-write
    STATUS mandatory
    DESCRIPTION
            "PLCP timing source for the E3 port."
    DEFVAL { e3Timing }
    ::= { e3PortEntry 6 }

e3PortCtxTiming OBJECT-TYPE
    SYNTAX INTEGER { e3plcpClock(1),
                     e3rxClock(2) }
    ACCESS read-write
    STATUS mandatory
    DESCRIPTION
            "CTX timing source for the E3 port."
    DEFVAL { e3rxClock }
    ::= { e3PortEntry 7 }

e3PortLineRate OBJECT-TYPE
    SYNTAX INTEGER
    ACCESS read-only
    STATUS mandatory
    DESCRIPTION
            "Physical Line data transfer rate of the E3 port. Unit: CPS."
    ::= { e3PortEntry 8 }

-- E3 Port Stats Group (e3PortStats)

e3PortStatsTable OBJECT-TYPE
    SYNTAX SEQUENCE OF E3PortStatsEntry
    ACCESS not-accessible
    STATUS mandatory
    DESCRIPTION
            "The E3 port stats information table."
    ::= { e3PortStats 1 }

e3PortStatsEntry OBJECT-TYPE
    SYNTAX E3PortStatsEntry
    ACCESS not-accessible
    STATUS mandatory
    DESCRIPTION
            "Information about a E3 port stats."
    INDEX { portSlot, portNumber }
    ::= { e3PortStatsTable 1 }

E3PortStatsEntry ::=
    SEQUENCE {
        e3PortRxCells
            Gauge,
        e3PortTxCells
            Gauge,
        e3PortIdleUnassignedCells
            Gauge,
        e3PortHCSErrorCells
            Gauge,
        e3PortResetTimeDate
            TimeAndDate,
        e3PortResetStats
            INTEGER,
        e3PortUtilRxCells
            INTEGER,
        e3PortUtilTxCells
            INTEGER
    }

e3PortRxCells OBJECT-TYPE
    SYNTAX  Gauge
    ACCESS  read-only
    STATUS  mandatory
    DESCRIPTION
            "The counter associated with the received cells, encountered
            on the ATM interface."
    ::= { e3PortStatsEntry 1 }

e3PortTxCells OBJECT-TYPE
    SYNTAX  Gauge
    ACCESS  read-only
    STATUS  mandatory
    DESCRIPTION
            "The counter associated with the transmitted cells, encountered
            on the ATM interface."
    ::= { e3PortStatsEntry 2 }

e3PortIdleUnassignedCells OBJECT-TYPE
    SYNTAX  Gauge
    ACCESS  read-only
    STATUS  mandatory
    DESCRIPTION
            "The counter associated with the idle/unassigned cells, encountered
            on the ATM interface."
    ::= { e3PortStatsEntry 3 }

e3PortHCSErrorCells OBJECT-TYPE
    SYNTAX  Gauge
    ACCESS  read-only
    STATUS  mandatory
    DESCRIPTION
            "The counter associated with the HCS errored cells, encountered
            on the ATM interface."
    ::= { e3PortStatsEntry 4 }

e3PortResetTimeDate OBJECT-TYPE
    SYNTAX  TimeAndDate
    ACCESS  read-only
    STATUS  mandatory
    DESCRIPTION
            "The reset time and date of ATM stats on this ATM interface."
    ::= { e3PortStatsEntry 5 }

e3PortResetStats OBJECT-TYPE
    SYNTAX  INTEGER { reset (1) }
    ACCESS  write-only
    STATUS  mandatory
    DESCRIPTION
            "This field is used to reset the atm statistics for the e3 port.
             If a get is performed on this command, the result will always
             be zero"
    ::= { e3PortStatsEntry 6 }

e3PortUtilRxCells OBJECT-TYPE
    SYNTAX  INTEGER
    ACCESS  read-only
    STATUS  mandatory
    DESCRIPTION
            "The Utilization of received Cell is calculcated as
             received cells divided by Line Rate.  "
    ::= { e3PortStatsEntry 7 }

e3PortUtilTxCells OBJECT-TYPE
    SYNTAX  INTEGER
    ACCESS  read-only
    STATUS  mandatory
    DESCRIPTION
            "The Utilization of transmitted Cell is calculcated as
             transmitted cells divided by Line Rate.  "
   ::= { e3PortStatsEntry 8 }

e3PortClearStatsTable OBJECT-TYPE
	SYNTAX SEQUENCE OF E3PortClearStatsEntry
    	ACCESS not-accessible
    	STATUS mandatory
    	DESCRIPTION
            "The E3 reset statistics for peformance monitoring data."
	::= {e3PortClearStats 1 }

e3PortClearStatsEntry OBJECT-TYPE
    SYNTAX E3PortClearStatsEntry
    ACCESS not-accessible
    STATUS mandatory
    DESCRIPTION
            "Information about E3 port reset performance monitoring."
    INDEX { portSlot, portNumber }
	::= { e3PortClearStatsTable 1 }

E3PortClearStatsEntry ::=
     SEQUENCE {
          e3PortResetPMData
		INTEGER
	}

e3PortResetPMData OBJECT-TYPE
    SYNTAX  INTEGER { reset (1) }
    ACCESS  write-only
    STATUS  mandatory
    DESCRIPTION
            "This field is used to reset the performance monitoring
             data for the e3 port.  If a get is performed on this command,
             the result will always be zero"
    ::= { e3PortClearStatsEntry 1 }

END
