-- @(#)dvmrpMIB	3.2 11/28/95
--
-- This MIB defines 3Com's Proprietary DVMRP service
--
A3Com-Dvmrp-r1-MIB DEFINITIONS ::= BEGIN

          IMPORTS
                  enterprises, IpAddress
                      FROM RFC1155-SMI
                  PhysAddress
                      FROM RFC1213-MIB
                  OBJECT-TYPE
                          FROM RFC-1212;

          --
          -- This MIB is for General 3Com Systems.
          --

a3Com           OBJECT IDENTIFIER ::= { enterprises 43 }
brouterMIB      OBJECT IDENTIFIER ::= { a3Com 2 }
a3ComDVMRP    	    OBJECT IDENTIFIER ::= { brouterMIB 28 }
a3ComDvmrpSConfig   OBJECT IDENTIFIER ::= { a3ComDVMRP 1 }
a3ComDvmrpCConfig   OBJECT IDENTIFIER ::= { a3ComDVMRP 2 }
a3ComDvmrpData	    OBJECT IDENTIFIER ::= { a3ComDVMRP 3 }

      RowStatus ::= INTEGER {
                         active(1),
                         notInService(2),
                         notReady(3),
                         createAndGo(4),
                         createAndWait(5),
                         destroy(6)
      }

      --This data type, which has the same semantics as the rowStatus
      --textual convention used in SNMPv2, is used to add and
      --delete entries from a table.

      --The tables in this MIB allow a subset of the functionality
      --provided by the rowStatus textual convention.  In particular
      --row creation is allowed using only the createAndGo method.

      --That is, when adding entries to this table, this object
      --must be set to createAndGo(4).  The instance identifier
      --for this object will define the values of the columns
      --that make up the index.

      --In the same PDU, the appropriate remaining columns
      --of that row must be set as well.  The agent
      --will immediately set the value of this object to
      --active(1) if the row is correct.  If not, the agent
      --will refuse the SET request and return an
      --error code.

      --To modify an existing entry, it must be removed
      --and another entry with the desired changes added.

      --To remove an entry, set the value of this object
      --to destroy(6).

--
-- The following objects contain parameters applied to the whole system
--

a3ComDvmrpCacheTime OBJECT-TYPE
    SYNTAX  INTEGER (300 .. 86400)
    ACCESS  read-write
    STATUS  mandatory
    DESCRIPTION
    	"This object specifies the time in seconds a (source, group) entry is
    	kept in the forwarding table. The entry can be kept within 5 minutes to
    	1 day."
    DEFVAL  { 300 }
    ::= { a3ComDvmrpSConfig 1 }

a3ComDvmrpPrune	OBJECT-TYPE
    SYNTAX  INTEGER {
    	    	enabled (1),
    	    	disabled (2)
    }
    ACCESS  read-write
    STATUS  mandatory
    DESCRIPTION
    	"If this object is set to enabled(1), then prune is on when running
    	multicast routing with DVMRP protocol. If is is set to disabled(2),
    	then prune is turned off."
    DEFVAL  { enabled }
    ::= { a3ComDvmrpSConfig 2 }

a3ComDvmrpUpdateTime	OBJECT-TYPE
    SYNTAX  INTEGER (5 .. 5400)
    ACCESS  read-write
    STATUS  mandatory
    DESCRIPTION
    	"This object specifies the time interval in seconds that Route Report
    	containing complete routing table is sent. It also derives Route
    	Expiration time which is set to three times value of this object,
    	Garbage Collection time which is set to five times value of this object,
    	Neighbor Expiration time which is set to two times value of this object
    	plus 20 seconds and Leaf Confirmation time which is set to three times
    	value of this object plus 20 seconds."
    DEFVAL  { 60 }
    ::= { a3ComDvmrpSConfig 3 }

a3ComDvmrpMospfPolicy	OBJECT-TYPE
    SYNTAX  INTEGER {
    	    	mospf (1),
    	    	noMospf (2)
    }
    ACCESS  read-write
    STATUS  mandatory
    DESCRIPTION
    	"If this object is set to mospf(1), the system will import the route
    	source from MOSPF domain into DVMRP. The route source is controlled
    	by the object a3ComDvmrpMospfTable"
    DEFVAL  { noMospf }
    ::= { a3ComDvmrpSConfig 4 }

a3ComDvmrpDestGroupPolicy   OBJECT-TYPE
    SYNTAX  INTEGER {
    	    	destGroup (1),
    	    	noDestGroup (2)
    }
    ACCESS  read-write
    STATUS  mandatory
    DESCRIPTION
    	"This object is used to control data packets forward to MOSPF domain.
    	If this object is set to destGroup(1), data packet will be checked
    	with object a3ComDvmrpDestGroupTable, which function as a filter,
    	 before being forwarded to MOSPF domain. If this object is set to
    	noDestGroup(2), data packet is forwarded to MOSPF domain without any
    	checking."
    DEFVAL  { noDestGroup }
    ::= { a3ComDvmrpSConfig 5 }

--
-- The following table contain parameters applied to a specific port or tunnel.
--

a3ComDvmrpPortTable OBJECT-TYPE
    SYNTAX  SEQUENCE OF A3ComDvmrpPortEntry
    ACCESS  not-accessible
    STATUS  mandatory
    DESCRIPTION
    	"This table contains entries of parameters associated with every port
    	or tunnel."
    ::= { a3ComDvmrpCConfig 1 }

a3ComDvmrpPortEntry OBJECT-TYPE
    SYNTAX  A3ComDvmrpPortEntry
    ACCESS  not-accessible
    STATUS  mandatory
    DESCRIPTION
    	"Each entry contains information for a spcified port or tunnel."
    INDEX   { a3ComDvmrpPortIndex }
    ::= { a3ComDvmrpPortTable 1 }

A3ComDvmrpPortEntry ::=
    SEQUENCE {
    	a3ComDvmrpPortIndex 	    INTEGER,
    	a3ComDvmrpPortControl	    INTEGER,
    	a3ComDvmrpPortMetric	    INTEGER,
    	a3ComDvmrpPortRateLimit	    INTEGER,
    	a3ComDvmrpPortAggregateCtrl INTEGER
    }

    a3ComDvmrpPortIndex	OBJECT-TYPE
    	SYNTAX	INTEGER
    	ACCESS	read-only
    	STATUS	mandatory
    	DESCRIPTION
    	    "The port number or tunnel ID of which this entry applies. The
    	    tunnel ID starts with 1025 and end with 1056, i.e. total tunnel
    	    number is limited to 32."
    	::= { a3ComDvmrpPortEntry 1 }

    a3ComDvmrpPortControl   OBJECT-TYPE
    	SYNTAX	INTEGER {
    	    	    enabled (1),
    	    	    disabled (2)
    	}
    	ACCESS	read-write
    	STATUS	mandatory
    	DESCRIPTION
    	    "This object allows the multicast routing to run with DVMRP or not."
    	DEFVAL	{ disabled }
    	::= { a3ComDvmrpPortEntry 2 }

    a3ComDvmrpPortMetric    OBJECT-TYPE
    	SYNTAX	INTEGER (1 .. 31)
    	ACCESS	read-write
    	STATUS	mandatory
    	DESCRIPTION
    	    "This object specifies the cost to the given port or tunnel. A value
    	    of 32 is considered 'infinity'."
    	DEFVAL	{ 1 }
    	::= { a3ComDvmrpPortEntry 3 }

    a3ComDvmrpPortRateLimit   OBJECT-TYPE
    	SYNTAX	INTEGER (0 .. 100000)
    	ACCESS	read-write
    	STATUS	mandatory
    	DESCRIPTION
    	    "This object specifies the bandwidth in Kbits/second that will be
    	    allocated for the multicast datagrams traffic. If set the value to
    	    0 then the full bandwidth of the port will be applied."
    	DEFVAL	{ 0 }
    	::= { a3ComDvmrpPortEntry 4 }

    a3ComDvmrpPortAggregateCtrl	OBJECT-TYPE
    	SYNTAX	INTEGER {
    	    	    enabled (1),
    	    	    disabled (2)
    	}
    	ACCESS	read-write
    	STATUS	mandatory
    	DESCRIPTION
    	    "This object controls the way to advertise routes."
    	DEFVAL	{ disabled }
    	::= { a3ComDvmrpPortEntry 5 }

--
-- The following table contains boundary addresses.
--

a3ComDvmrpBoundaryAddrTable OBJECT-TYPE
    SYNTAX  SEQUENCE OF A3ComDvmrpBoundaryAddrEntry
    ACCESS  not-accessible
    STATUS  mandatory
    DESCRIPTION
    	"This table contains multicast addresses to be scoped for each port or
    	tunnel."
    ::= { a3ComDvmrpCConfig 2 }

a3ComDvmrpBoundaryAddrEntry OBJECT-TYPE
    SYNTAX  A3ComDvmrpBoundaryAddrEntry
    ACCESS  not-accessible
    STATUS  mandatory
    DESCRIPTION
    	"Each entry contains a single or a range of multicast addresses to be
    	scoped over a specific port or tunnel."
    INDEX   { a3ComDvmrpBoundaryAddrPort, a3ComDvmrpBoundaryAddrIpAddr }
    ::= { a3ComDvmrpBoundaryAddrTable 1 }

A3ComDvmrpBoundaryAddrEntry ::=
    SEQUENCE {
    	a3ComDvmrpBoundaryAddrPort  	INTEGER,
    	a3ComDvmrpBoundaryAddrIpAddr	IpAddress,
    	a3ComDvmrpBoundaryAddrMask  	IpAddress,
    	a3ComDvmrpBoundaryAddrStatus	RowStatus
    }

    a3ComDvmrpBoundaryAddrPort	OBJECT-TYPE
    	SYNTAX	INTEGER
    	ACCESS	read-only
    	STATUS	mandatory
    	DESCRIPTION
    	    "The port or tunnel number to which this entry applies."
    	::= { a3ComDvmrpBoundaryAddrEntry 1 }

    a3ComDvmrpBoundaryAddrIpAddr    OBJECT-TYPE
    	SYNTAX	IpAddress
    	ACCESS	read-only
    	STATUS	mandatory
    	DESCRIPTION
    	    "This allows you to configure a single or a set of multicast
    	    addresses to be scoped that they do not get forwarded beyond a
    	    boundary router."
    	::= { a3ComDvmrpBoundaryAddrEntry 2 }

    a3ComDvmrpBoundaryAddrMask	OBJECT-TYPE
    	SYNTAX	IpAddress
    	ACCESS	read-write
    	STATUS	mandatory
    	DESCRIPTION
    	    "This is the subnet mask associated with a3ComDvmrpBoundaryIpAddr of
    	    this entry. If this is not specified, the value 255.255.255.255 is
    	    used."
    	::= { a3ComDvmrpBoundaryAddrEntry 3 }


    a3ComDvmrpBoundaryAddrStatus    OBJECT-TYPE
    	SYNTAX	RowStatus
    	ACCESS	read-write
    	STATUS	mandatory
    	DESCRIPTION
    	    "This object is used to add and delete entries in this table. See
    	    the definition of RowStatus for detail."
    	::= { a3ComDvmrpBoundaryAddrEntry 4 }

--
-- The following table contains MOSPF sources.
--

a3ComDvmrpMospfTable	OBJECT-TYPE
    SYNTAX  SEQUENCE OF A3ComDvmrpMospfEntry
    ACCESS  not-accessible
    STATUS  mandatory
    DESCRIPTION
    	"This table contains a list of source subnet in MOSPF domain."
    ::= { a3ComDvmrpCConfig 3 }

a3ComDvmrpMospfEntry	OBJECT-TYPE
    SYNTAX  A3ComDvmrpMospfEntry
    ACCESS  not-accessible
    STATUS  mandatory
    DESCRIPTION
    	"Each entry contains a source subnet in MOSPF domain to be advertised
    	or not to be advertised to the DVMRP domain."
    INDEX   { a3ComDvmrpMospfIpAddr, a3ComDvmrpMospfIpMask }
    ::= { a3ComDvmrpMospfTable 1 }

A3ComDvmrpMospfEntry ::=
    SEQUENCE {
    	a3ComDvmrpMospfIpAddr	IpAddress,
    	a3ComDvmrpMospfIpMask	INTEGER,
    	a3ComDvmrpMospfMetric	INTEGER,
    	a3ComDvmrpMospfAction	INTEGER,
    	a3ComDvmrpMospfStatus	RowStatus
    }

    a3ComDvmrpMospfIpAddr   OBJECT-TYPE
    	SYNTAX	IpAddress
    	ACCESS	read-only
    	STATUS	mandatory
    	DESCRIPTION
    	    "Source subnet's IP address."
    	::= { a3ComDvmrpMospfEntry 1 }

    a3ComDvmrpMospfIpMask   OBJECT-TYPE
    	SYNTAX	INTEGER
    	ACCESS	read-only
    	STATUS	mandatory
    	DESCRIPTION
    	    "This is subnet mask associated with a3ComDvmrpMospfIpAddr. It is
    	    a number of contiguous leading 1s, i.e. if the value is 1, it
    	    indicates the subnet mask is 128.0.0.0, or if the value is 8 then
    	    the subnet mask is 255.0.0.0."
    	::= { a3ComDvmrpMospfEntry 2 }

    a3ComDvmrpMospfMetric   OBJECT-TYPE
    	SYNTAX	INTEGER
    	ACCESS	read-write
    	STATUS	mandatory
    	DESCRIPTION
    	    "The routing metric to this source subnet. It ranges from 1 to 31."
    	DEFVAL	{ 1 }
    	::= { a3ComDvmrpMospfEntry 3 }

    a3ComDvmrpMospfAction   OBJECT-TYPE
    	SYNTAX	INTEGER {
    	    	    aggregate(1),
    	    	    individual(2),
    	    	    reject(3)
    	}
    	ACCESS	read-write
    	STATUS	mandatory
    	DESCRIPTION
    	    "If this object is set to aggregate(1), then this source subnet, if
    	    learned from MOSPF, is advertised to DVMRP domain in aggregate form.
    	    If this object is set to individual(2), then this source subnet, if
    	    learned from MOSPF, is advertised to DVMRP domain as it is. Otherwise,
    	    the route will not be advertised if the object is set to reject(3)."
    	DEFVAL	{ aggregate }
    	::= { a3ComDvmrpMospfEntry 4 }

    a3ComDvmrpMospfStatus   OBJECT-TYPE
    	SYNTAX	RowStatus
    	ACCESS	read-write
    	STATUS	mandatory
    	DESCRIPTION
    	    "This object is used to add and delete entries in this table. See
    	    the definition of RowStatus for detail."
    	::= { a3ComDvmrpMospfEntry 5 }

--
-- The following table contains neighbors addresses.
--

a3ComDvmrpNeighborTable	OBJECT-TYPE
    SYNTAX  SEQUENCE OF A3ComDvmrpNeighborEntry
    ACCESS  not-accessible
    STATUS  mandatory
    DESCRIPTION
    	"This table contains a list of neighbors entries for each X.25 or
    	 Frame-Relay networks."
    ::= { a3ComDvmrpCConfig 4 }

a3ComDvmrpNeighborEntry	OBJECT-TYPE
    SYNTAX  A3ComDvmrpNeighborEntry
    ACCESS  not-accessible
    STATUS  mandatory
    DESCRIPTION
    	"Each entry contains a single X.25 DTE address or a Frame-Relay DLCI."
    INDEX   { a3ComDvmrpNeighborPort, a3ComDvmrpNeighborType,
	      a3ComDvmrpNeighborAddr }
    ::= { a3ComDvmrpNeighborTable 1 }

A3ComDvmrpNeighborEntry ::=
    SEQUENCE {
    	a3ComDvmrpNeighborPort	    INTEGER,
    	a3ComDvmrpNeighborType	    INTEGER,
    	a3ComDvmrpNeighborAddr	    PhysAddress,
    	a3ComDvmrpNeighborStatus    RowStatus
    }

    a3ComDvmrpNeighborPort  OBJECT-TYPE
    	SYNTAX	INTEGER
    	ACCESS	read-only
    	STATUS	mandatory
    	DESCRIPTION
    	    "The port number to which this entry applies."
    	::= { a3ComDvmrpNeighborEntry 1 }

    a3ComDvmrpNeighborType  OBJECT-TYPE
    	SYNTAX	INTEGER {
    	    	    x25 (2),
    	    	    frame-relay (4)
    	    	}
    	ACCESS	read-only
    	STATUS	mandatory
    	DESCRIPTION
    	    "This object specifies the media type of the port."
    	::= { a3ComDvmrpNeighborEntry 2 }

    a3ComDvmrpNeighborAddr  OBJECT-TYPE
    	SYNTAX	PhysAddress
    	ACCESS	read-only
    	STATUS	mandatory
    	DESCRIPTION
    	    "This object specifies an X.25 DTE address or a Frame-Relay DLCI."
    	::= { a3ComDvmrpNeighborEntry 3 }

    a3ComDvmrpNeighborStatus	OBJECT-TYPE
    	SYNTAX	RowStatus
    	ACCESS	read-write
    	STATUS	mandatory
    	DESCRIPTION
    	    "This object is used to add and delete entries in this table. See
    	    the definition of RowStatus for detail."
    	::= { a3ComDvmrpNeighborEntry 4 }

--
-- The following table contains tunnel information of the system.
--

a3ComDvmrpTunnelTable	OBJECT-TYPE
    SYNTAX  SEQUENCE OF A3ComDvmrpTunnelEntry
    ACCESS  not-accessible
    STATUS  mandatory
    DESCRIPTION
    	"This table contains entries of tunnel."
    ::= { a3ComDvmrpCConfig 5 }

a3ComDvmrpTunnelEntry	OBJECT-TYPE
    SYNTAX  A3ComDvmrpTunnelEntry
    ACCESS  not-accessible
    STATUS  mandatory
    DESCRIPTION
    	"Each entry contains parameters associated with a specific tunnel."
    INDEX   { a3ComDvmrpTunnelId }
    ::= { a3ComDvmrpTunnelTable 1 }

A3ComDvmrpTunnelEntry ::=
    SEQUENCE {
    	a3ComDvmrpTunnelId  	    INTEGER,
    	a3ComDvmrpTunnelLocalIp	    IpAddress,
    	a3ComDvmrpTunnelRemoteIp    IpAddress,
    	a3ComDvmrpTunnelTtl 	    INTEGER,
    	a3ComDvmrpTunnelStatus	    RowStatus
}

    a3ComDvmrpTunnelId	OBJECT-TYPE
    	SYNTAX	INTEGER
    	ACCESS	read-only
    	STATUS	mandatory
    	DESCRIPTION
    	    "The ID number of which this entry applies. Tunnel ID starts with
    	    1025 and ends with 1056."
    	::= { a3ComDvmrpTunnelEntry 1 }

    a3ComDvmrpTunnelLocalIp OBJECT-TYPE
    	SYNTAX	IpAddress
    	ACCESS	read-write
    	STATUS	mandatory
    	DESCRIPTION
    	    "This object specifies the IP address of local end of a tunnel. It
    	    must be one of system's directly connected subnet."
    	::= { a3ComDvmrpTunnelEntry 2 }

    a3ComDvmrpTunnelRemoteIp	OBJECT-TYPE
    	SYNTAX	IpAddress
    	ACCESS	read-write
    	STATUS	mandatory
    	DESCRIPTION
    	    "This object specifies the IP address of remote end of a tunnel."
    	::= { a3ComDvmrpTunnelEntry 3 }

    a3ComDvmrpTunnelTtl	OBJECT-TYPE
    	SYNTAX	INTEGER (1 .. 255)
    	ACCESS	read-write
    	STATUS	mandatory
    	DESCRIPTION
    	    "This object specifies the value to be put in IP packet's TTL field
    	    when transmits packets through a tunnel."
    	DEFVAL   { 64 }
    	::= { a3ComDvmrpTunnelEntry 4 }

    a3ComDvmrpTunnelStatus  OBJECT-TYPE
    	SYNTAX	RowStatus
    	ACCESS	read-write
    	STATUS	mandatory
    	DESCRIPTION
    	    "This object is used to add and delete entries in this table. See
    	    the definition of RowStatus for detail."
    	::= { a3ComDvmrpTunnelEntry 5 }

--
-- The following table is used to configure a list of aggregate except.
--

a3ComDvmrpAggreExceptTable  OBJECT-TYPE
    SYNTAX  SEQUENCE OF A3ComDvmrpAggreExceptEntry
    ACCESS  not-accessible
    STATUS  mandatory
    DESCRIPTION
    	"The table contains list of subnets not to be aggregated."
    ::= { a3ComDvmrpCConfig 6 }

a3ComDvmrpAggreExceptEntry  OBJECT-TYPE
    SYNTAX  A3ComDvmrpAggreExceptEntry
    ACCESS  not-accessible
    STATUS  mandatory
    DESCRIPTION
    	"Each entry contains a range of subnets."
    INDEX { a3ComDvmrpAggreExceptIpAddr, a3ComDvmrpAggreExceptIpMask }
    ::= { a3ComDvmrpAggreExceptTable 1 }

A3ComDvmrpAggreExceptEntry ::=
    SEQUENCE {
    	a3ComDvmrpAggreExceptIpAddr IpAddress,
    	a3ComDvmrpAggreExceptIpMask INTEGER,
    	a3ComDvmrpAggreExceptStatus RowStatus
    }

    a3ComDvmrpAggreExceptIpAddr	OBJECT-TYPE
    	SYNTAX	IpAddress
    	ACCESS	read-write
    	STATUS	mandatory
    	DESCRIPTION
    	    "This object specifies the IP subnet address."
    	::= { a3ComDvmrpAggreExceptEntry 1 }

    a3ComDvmrpAggreExceptIpMask	OBJECT-TYPE
    	SYNTAX	INTEGER (0 .. 32)
    	ACCESS	read-write
    	STATUS	mandatory
    	DESCRIPTION
    	    "The subnet mask of ccsIpDvmrpAggreExceptIpAddr. It is an
    	    integer value representing number of consecutive leading 1s. i.e.
    	    if the value is 1, then the subnet mask is 128.0.0.0, if the value
    	    is 8 then the subnet mask is 255.0.0.0."
    	::= { a3ComDvmrpAggreExceptEntry 2 }

    a3ComDvmrpAggreExceptStatus	OBJECT-TYPE
    	SYNTAX	RowStatus
    	ACCESS	read-write
    	STATUS	mandatory
    	DESCRIPTION
    	    "This object is used to add and delete entries in this table. See
    	    the definition of RowStatus for detail."
    	::= { a3ComDvmrpAggreExceptEntry 3 }

--
-- The following table is used to configure a list of aggregate range.
--

a3ComDvmrpAggreRangeTable   OBJECT-TYPE
    SYNTAX  SEQUENCE OF A3ComDvmrpAggreRangeEntry
    ACCESS  not-accessible
    STATUS  mandatory
    DESCRIPTION
    	"The table contains range of routes to be aggregated."
    ::= { a3ComDvmrpCConfig 7 }

a3ComDvmrpAggreRangeEntry   OBJECT-TYPE
    SYNTAX  A3ComDvmrpAggreRangeEntry
    ACCESS  not-accessible
    STATUS  mandatory
    DESCRIPTION
    	"Each entry contains a range of routes."
    INDEX { a3ComDvmrpAggreRangeIpAddr, a3ComDvmrpAggreRangeIpMask }
    ::= { a3ComDvmrpAggreRangeTable 1 }

A3ComDvmrpAggreRangeEntry ::=
    SEQUENCE {
    	a3ComDvmrpAggreRangeIpAddr  IpAddress,
    	a3ComDvmrpAggreRangeIpMask  INTEGER,
    	a3ComDvmrpAggreRangeMetric  INTEGER,
    	a3ComDvmrpAggreRangeStatus  RowStatus
    }

    a3ComDvmrpAggreRangeIpAddr	OBJECT-TYPE
    	SYNTAX	IpAddress
    	ACCESS	read-write
    	STATUS	mandatory
    	DESCRIPTION
    	    "This object specifies the IP subnet address."
    	::= { a3ComDvmrpAggreRangeEntry 1 }

    a3ComDvmrpAggreRangeIpMask	OBJECT-TYPE
    	SYNTAX	INTEGER (0 .. 32)
    	ACCESS	read-write
    	STATUS	mandatory
    	DESCRIPTION
    	    "The subnet mask of ccsIpDvmrpAggreRangeIpAddr. It is an
    	    integer value representing number of consecutive leading 1s. i.e.
    	    if the value is 1, then the subnet mask is 128.0.0.0, if the value
    	    is 8 then the subnet mask is 255.0.0.0."
    	::= { a3ComDvmrpAggreRangeEntry 2 }

    a3ComDvmrpAggreRangeMetric	OBJECT-TYPE
    	SYNTAX	INTEGER (0 .. 31)
    	ACCESS	read-write
    	STATUS	mandatory
    	DESCRIPTION
    	    "This object specifies the cost to the above subnet. If set this
    	    object to value 0, the metric associated with the aggregate route
    	    to be advertised will pick up the best one among all the aggregated
    	    routes."
    	DEFVAL	{ 0 }
    	::= { a3ComDvmrpAggreRangeEntry 3 }

    a3ComDvmrpAggreRangeStatus	OBJECT-TYPE
    	SYNTAX	RowStatus
    	ACCESS	read-write
    	STATUS	mandatory
    	DESCRIPTION
    	    "This object is used to add and delete entries in this table. See
    	    the definition of RowStatus for detail."
    	::= { a3ComDvmrpAggreRangeEntry 4 }

--
-- The following table is used to configure a list of destination groups
-- to be or not to be forwarded to MOSPF domain.
--

a3ComDvmrpDestGroupTable    OBJECT-TYPE
    SYNTAX  SEQUENCE OF A3ComDvmrpDestGroupEntry
    ACCESS  not-accessible
    STATUS  mandatory
    DESCRIPTION
    	"The table contains destination groups to be or not to be forwarded
    	to MOSPF domain. This table will take effect only if object
    	a3ComDvmrpDestGroupPolicy is set to 'destGroup (1)'."
    ::= { a3ComDvmrpCConfig 8 }

a3ComDvmrpDestGroupEntry    OBJECT-TYPE
    SYNTAX  A3ComDvmrpDestGroupEntry
    ACCESS  not-accessible
    STATUS  mandatory
    DESCRIPTION
    	"Each entry contains a destination group to be or not to be forwarded
    	to MOSPF domain."
    INDEX   { a3ComDvmrpDestGroupIpAddr, a3ComDvmrpDestGroupIpMask }
    ::= { a3ComDvmrpDestGroupTable 1 }

A3ComDvmrpDestGroupEntry ::=
    SEQUENCE {
    	a3ComDvmrpDestGroupIpAddr   IpAddress,
    	a3ComDvmrpDestGroupIpMask   INTEGER,
    	a3ComDvmrpDestGroupAction   INTEGER,
    	a3ComDvmrpDestGroupStatus   RowStatus
    }

    a3ComDvmrpDestGroupIpAddr	OBJECT-TYPE
    	SYNTAX	IpAddress
    	ACCESS	read-only
    	STATUS	mandatory
    	DESCRIPTION
    	    "This object specifies the destination group IP address, the first
    	    byte in decimal must be in the range of 224 to 239."
    	::= { a3ComDvmrpDestGroupEntry 1 }

    a3ComDvmrpDestGroupIpMask	OBJECT-TYPE
    	SYNTAX	INTEGER
    	ACCESS	read-only
    	STATUS	mandatory
    	DESCRIPTION
    	    "This is subnet mask associated with a3ComDvmrpDestGroupIpAddr. It is
    	    a number of contiguous leading 1s, i.e. if the value is 1, it
    	    indicates the subnet mask is 128.0.0.0, or if the value is 8 then
    	    the subnet mask is 255.0.0.0."
    	::= { a3ComDvmrpDestGroupEntry 2 }

    a3ComDvmrpDestGroupAction	OBJECT-TYPE
    	SYNTAX	INTEGER {
    	    	    accept(1),
    	    	    reject(2)
    	}
    	ACCESS	read-write
    	STATUS	mandatory
    	DESCRIPTION
    	    "This object specifies if this destination group needs to be
    	    forwarded to MOSPF domain. If set to 'accept (1)', the group is
    	    forwarded to MOSPF domain; if set to 'reject (2)' then the group
    	    is filtered out."
    	DEFVAL	{ accept }
    	::= { a3ComDvmrpDestGroupEntry 3 }

    a3ComDvmrpDestGroupStatus	OBJECT-TYPE
    	SYNTAX	RowStatus
    	ACCESS	read-write
    	STATUS	mandatory
    	DESCRIPTION
    	    "This object is used to add and delete entries in this table. See
    	    the definition of RowStatus for detail."
    	::= { a3ComDvmrpDestGroupEntry 4 }

--
-- the following table contains multicast route information
--

a3ComDvmrpRouteTable	OBJECT-TYPE
    SYNTAX  SEQUENCE OF A3ComDvmrpRouteEntry
    ACCESS  not-accessible
    STATUS  mandatory
    DESCRIPTION
    	"This table contains multicast route information."
    ::= { a3ComDvmrpData 1 }

a3ComDvmrpRouteEntry	OBJECT-TYPE
    SYNTAX  A3ComDvmrpRouteEntry
    ACCESS  not-accessible
    STATUS  mandatory
    DESCRIPTION
    	"Each entry contains route information to a specific subnet or source."
    INDEX   { a3ComDvmrpRouteSource }
    ::= { a3ComDvmrpRouteTable 1 }

A3ComDvmrpRouteEntry ::=
    SEQUENCE {
    	a3ComDvmrpRouteSource 	    IpAddress,
    	a3ComDvmrpRouteMask   	    IpAddress,
    	a3ComDvmrpRoutePreHop	    IpAddress,
    	a3ComDvmrpRouteMetric 	    INTEGER,
    	a3ComDvmrpRoutePort   	    INTEGER,
    	a3ComDvmrpRouteType   	    INTEGER,
    	a3ComDvmrpRouteStatus 	    INTEGER,
    	a3ComDvmrpRouteProtocol	    INTEGER,
    	a3ComDvmrpRouteTtl    	    INTEGER,
    	a3ComDvmrpRouteChild  	    OCTET STRING,
    	a3ComDvmrpRouteChildTunnel  OCTET STRING,
    	a3ComDvmrpRouteLeaf 	    OCTET STRING,
    	a3ComDvmrpRouteLeafTunnel   OCTET STRING
    }

    a3ComDvmrpRouteSource   OBJECT-TYPE
    	SYNTAX	IpAddress
    	ACCESS	read-only
    	STATUS	mandatory
    	DESCRIPTION
    	    "The source IP address of this route."
    	::= { a3ComDvmrpRouteEntry 1 }

    a3ComDvmrpRouteMask	OBJECT-TYPE
    	SYNTAX	IpAddress
    	ACCESS	read-only
    	STATUS	mandatory
    	DESCRIPTION
    	    "This object is logical-anded with the source address before
    	    comparing to the value in previous object a3ComDvmrpRouteSource."
    	::= { a3ComDvmrpRouteEntry 2 }

    a3ComDvmrpRoutePreHop   OBJECT-TYPE
    	SYNTAX	IpAddress
    	ACCESS	read-only
    	STATUS	mandatory
    	DESCRIPTION
    	    "The IP address of the upstream router of this route."
    	::= { a3ComDvmrpRouteEntry 3 }

    a3ComDvmrpRouteMetric   OBJECT-TYPE
    	SYNTAX	INTEGER
    	ACCESS	read-only
    	STATUS	mandatory
    	DESCRIPTION
    	    "The routing metric of this route. It's routing-protocol
    	    dependenable, for DVMRP, the metric should be in range 1 to 31.
    	    The value 32 is considered 'infinity' or unreachable."
    	::= { a3ComDvmrpRouteEntry 4 }

    a3ComDvmrpRoutePort	OBJECT-TYPE
    	SYNTAX	INTEGER
    	ACCESS	read-only
    	STATUS	mandatory
    	DESCRIPTION
    	    "The port number identifies from which this route comes."
    	::= { a3ComDvmrpRouteEntry 5 }

    a3ComDvmrpRouteType	OBJECT-TYPE
    	SYNTAX	INTEGER {
    	    	    other(1),	-- none of the following
    	    	    direct(2),	-- directly connected subnet
    	    	    remote(3)	-- non-local subnet
    	}
    	ACCESS	read-only
    	STATUS	mandatory
    	DESCRIPTION
    	    "The type of route."
    	::= { a3ComDvmrpRouteEntry 6 }

    a3ComDvmrpRouteStatus   OBJECT-TYPE
    	SYNTAX	INTEGER {
    	    	    other(1),	-- none of the following
    	    	    up(2),
    	    	    down(3),
    	    	    hold-down(4),
    	    	    garbage-collection(5)
    	}
    	ACCESS	read-only
    	STATUS	mandatory
    	DESCRIPTION
    	    "The status of route."
    	::= { a3ComDvmrpRouteEntry 7 }

    a3ComDvmrpRouteProtocol OBJECT-TYPE
    	SYNTAX	INTEGER {
    	    	    other(1),	-- none of the following
    	    	    static(2),
    	    	    dvmrp(3),
    	    	    mospf(4),
    	    	    cbt(5),
    	    	    pim(6)
    	}
    	ACCESS	read-only
    	STATUS	mandatory
    	DESCRIPTION
    	    "The routing algorithm to which this route applies."
    	::= { a3ComDvmrpRouteEntry 8 }

    a3ComDvmrpRouteTtl	OBJECT-TYPE
    	SYNTAX  INTEGER
    	ACCESS  read-only
    	STATUS  mandatory
    	DESCRIPTION
    	    "The time in seconds this route was last updated."
    	::= { a3ComDvmrpRouteEntry 9 }

    a3ComDvmrpRouteChild    OBJECT-TYPE
    	SYNTAX	OCTET STRING
    	ACCESS	read-only
    	STATUS	mandatory
    	DESCRIPTION
    	    "This object identifies ports that connect to child subtree of the
    	    multicast tree rooted at a3ComDvmrpRouteSource. Each octet, except
    	    the first one which contains a value specified length of this
    	    object, contains a bit map of 8 ports. The first (should say the
    	    second) octet specifies ports from 1 to 8, the next octet specifies
    	    ports 9 to 16, ... etc. The most significant bit in each octet
    	    represents the lowest port, the least significant bit represents
    	    the highest port among those 8 ports. If the bit is set then the
    	    corresponding port connects to a child subtree, otherwise the
    	    corresponding port does not connect to a child subtree. The tunnel
    	    ports does not include in this object, it is specified in next,
    	    a3ComDvmrpRouteChildTunnel object."
    	::= { a3ComDvmrpRouteEntry 10 }

    a3ComDvmrpRouteChildTunnel	OBJECT-TYPE
    	SYNTAX	OCTET STRING
    	ACCESS	read-only
    	STATUS	mandatory
    	DESCRIPTION
    	    "This object is the same as above but includes tunnel ports only.
    	    The first (should say the second) octet specifies ports from 1025
    	    (for tunnel port 1) to 1032, the next octet specifies ports 1033 to
    	    1040, ... etc."
    	::= { a3ComDvmrpRouteEntry 11 }

    a3ComDvmrpRouteLeaf	OBJECT-TYPE
    	SYNTAX	OCTET STRING
    	ACCESS	read-only
    	STATUS	mandatory
    	DESCRIPTION
    	    "This objec identifies ports that connect to leaf subnet of the
    	    multicast tree rooted at a3ComDvmrpRouteSource. The value meaning
    	    within each octet is the same as that of a3ComDvmrpRouteChild, except
    	    the bit set means the corresponding port connects to a leaf. This
    	    object does not include tunnel ports too."
    	::= { a3ComDvmrpRouteEntry 12 }

    a3ComDvmrpRouteLeafTunnel	OBJECT-TYPE
    	SYNTAX	OCTET STRING
    	ACCESS	read-only
    	STATUS	mandatory
    	DESCRIPTION
    	    "This objec is the same as a3ComDvmrpRouteLeaf object but includes
    	    tunnel ports only."
    	::= { a3ComDvmrpRouteEntry 13 }

--
-- The following table contains forwarding information of each (source, group).
--

a3ComDvmrpForwardTable	OBJECT-TYPE
    SYNTAX  SEQUENCE OF A3ComDvmrpForwardEntry
    ACCESS  not-accessible
    STATUS  mandatory
    DESCRIPTION
    	"This table contains information of each (source, group) pair."
    ::= { a3ComDvmrpData 2 }

a3ComDvmrpForwardEntry	OBJECT-TYPE
    SYNTAX  A3ComDvmrpForwardEntry
    ACCESS  not-accessible
    STATUS  mandatory
    DESCRIPTION
    	"Each entry contains forwarding information for a specific (source,
    	group) pair."
    INDEX   { a3ComDvmrpForwardSource, a3ComDvmrpForwardGroup }
    ::= { a3ComDvmrpForwardTable 1 }

A3ComDvmrpForwardEntry ::=
    SEQUENCE {
    	a3ComDvmrpForwardSource	    	IpAddress,
    	a3ComDvmrpForwardGroup	    	IpAddress,
    	a3ComDvmrpForwardTtl  	    	INTEGER,
    	a3ComDvmrpForwardInPort	    	INTEGER,
    	a3ComDvmrpForwardOutPorts   	OCTET STRING,
    	a3ComDvmrpForwardOutPortsTunnel	OCTET STRING,
    	a3ComDvmrpForwardScoped	    	INTEGER,
    	a3ComDvmrpForwardPruneSent    	INTEGER
    }

    a3ComDvmrpForwardSource OBJECT-TYPE
    	SYNTAX	IpAddress
    	ACCESS	read-only
    	STATUS	mandatory
    	DESCRIPTION
    	    "This object specifies root's IP address of this (source, group)
    	    multicast distribution tree."
    	::= { a3ComDvmrpForwardEntry 1 }

    a3ComDvmrpForwardGroup  OBJECT-TYPE
    	SYNTAX	IpAddress
    	ACCESS	read-only
    	STATUS	mandatory
    	DESCRIPTION
    	    "This object specifies the destination multicast group address of
    	    this (source, group) multicast distribution tree."
    	::= { a3ComDvmrpForwardEntry 2 }

    a3ComDvmrpForwardTtl    OBJECT-TYPE
    	SYNTAX	INTEGER
    	ACCESS	read-only
    	STATUS	mandatory
    	DESCRIPTION
    	    "This object specifies the time in seconds left for this (source,
    	    group) entry to stay in the forwarding table. When this value
    	    reaches 0, this (source, group) entry is deleted from the table."
    	::= { a3ComDvmrpForwardEntry 3 }

    a3ComDvmrpForwardInPort OBJECT-TYPE
    	SYNTAX	INTEGER
    	ACCESS	read-only
    	STATUS	mandatory
    	DESCRIPTION
    	    "This object specifies the incoming port for the multicast
    	    datagrams from the source a3ComDvmrpForwardSource."
    	::= { a3ComDvmrpForwardEntry 4 }

    a3ComDvmrpForwardOutPorts	OBJECT-TYPE
    	SYNTAX	OCTET STRING
    	ACCESS	read-only
    	STATUS	mandatory
    	DESCRIPTION
    	    "This object specifies ports to which multicast datagrams
    	    belonging to this (source, group) pair to be forwarded. The value
    	    in each octet contains a bit maps of 8 ports, that the significant
    	    bit represents the lowest port and the least significant bit
    	    represent the highest port. The first octet represents ports 1 to 8,
    	    the next octet represents ports 9 to 16, ..., etc. If the bit value
    	    is set then the corresponding port will have multicast datagrams to
    	    be forwarded. The tunnel ports mapping is put in the next
    	    a3ComDvmrpForwardOutPortsTunnel object."
    	::= { a3ComDvmrpForwardEntry 5 }

    a3ComDvmrpForwardOutPortsTunnel OBJECT-TYPE
    	SYNTAX	OCTET STRING
    	ACCESS	read-only
    	STATUS	mandatory
    	DESCRIPTION
    	    "This object is the same as a3ComDvmrpForwardOutPorts object but
    	    includes tunnel ports mapping only."
    	::= { a3ComDvmrpForwardEntry 6 }

    a3ComDvmrpForwardScoped OBJECT-TYPE
    	SYNTAX	INTEGER {
    	    	    yes (1),
    	    	    no (2)
    	    	}
    	ACCESS	read-only
    	STATUS	mandatory
    	DESCRIPTION
    	    "This object specifies if it is a boundary port. If the value of
    	    this object is yes(1), it means multicast traffic will not be
    	    forwarded on the scoped address, specified in 3ComDvmrpForwardGroup,
    	    on this port."
    	::= { a3ComDvmrpForwardEntry 7 }

    a3ComDvmrpForwardPruneSent	OBJECT-TYPE
    	SYNTAX	INTEGER {
    	    	    yes (1),
    	    	    no (2)
    	}
    	ACCESS	read-only
    	STATUS	mandatory
    	DESCRIPTION
    	    "This object specifies if a Prune message has been sent to its
    	    upstream router. A prune message is sent when router wants to leave
    	    the multicast delivery tree associated with this (source, group)
    	    pair."
    	::= { a3ComDvmrpForwardEntry 8 }

--
-- The following table contains neighbor routers information of each port.
--

a3ComDvmrpNbrRouterTable    OBJECT-TYPE
    SYNTAX  SEQUENCE OF A3ComDvmrpNbrRouterEntry
    ACCESS  not-accessible
    STATUS  mandatory
    DESCRIPTION
    	"This table contains information of each neighboring router."
    ::= { a3ComDvmrpData 3 }

a3ComDvmrpNbrRouterEntry    OBJECT-TYPE
    SYNTAX  A3ComDvmrpNbrRouterEntry
    ACCESS  not-accessible
    STATUS  mandatory
    DESCRIPTION
    	"Each entry contains neighboring router's IP address, DVMRP version,
    	generation ID, expiration time and status."
    INDEX   { a3ComDvmrpNbrRouterPort, a3ComDvmrpNbrRouterIpAddr }
    ::= { a3ComDvmrpNbrRouterTable 1 }

A3ComDvmrpNbrRouterEntry ::=
    SEQUENCE {
    	a3ComDvmrpNbrRouterPort	    	INTEGER,
    	a3ComDvmrpNbrRouterIpAddr   	IpAddress,
    	a3ComDvmrpNbrRouterGenId    	INTEGER,
    	a3ComDvmrpNbrRouterVerProtocol	INTEGER,
    	a3ComDvmrpNbrRouterVerMrouted	INTEGER,
    	a3ComDvmrpNbrRouterTtl	    	INTEGER,
    	a3ComDvmrpNbrRouterLeafStatus	INTEGER,
    	a3ComDvmrpNbrRouterPruneStatus	INTEGER,
    	a3ComDvmrpNbrRouterGenIdStatus	INTEGER,
    	a3ComDvmrpNbrRouterMtraceStatus	INTEGER
    }

    a3ComDvmrpNbrRouterPort OBJECT-TYPE
    	SYNTAX	INTEGER
    	ACCESS	read-only
    	STATUS	mandatory
    	DESCRIPTION
    	    "The port number or tunnel ID of which this entry applies."
    	::= { a3ComDvmrpNbrRouterEntry 1 }

    a3ComDvmrpNbrRouterIpAddr	OBJECT-TYPE
    	SYNTAX	IpAddress
    	ACCESS	read-only
    	STATUS	mandatory
    	DESCRIPTION
    	    "The IP address of this neighboring router."
    	::= { a3ComDvmrpNbrRouterEntry 2 }

    a3ComDvmrpNbrRouterGenId	OBJECT-TYPE
    	SYNTAX	INTEGER
    	ACCESS	read-only
    	STATUS	mandatory
    	DESCRIPTION
    	    "The generation ID of this neighboring router."
    	::= { a3ComDvmrpNbrRouterEntry 3 }

    a3ComDvmrpNbrRouterVerProtocol  OBJECT-TYPE
    	SYNTAX	INTEGER
    	ACCESS	read-only
    	STATUS	mandatory
    	DESCRIPTION
    	    "The version of DVMRP protocol that this neighboring router is
    	    running."
    	::= { a3ComDvmrpNbrRouterEntry 4 }

    a3ComDvmrpNbrRouterVerMrouted   OBJECT-TYPE
    	SYNTAX	INTEGER
    	ACCESS	read-only
    	STATUS	mandatory
    	DESCRIPTION
    	    "The version of 'mrouted' that this neighboring router is running."
    	::= { a3ComDvmrpNbrRouterEntry 5 }

    a3ComDvmrpNbrRouterTtl  OBJECT-TYPE
    	SYNTAX	INTEGER
    	ACCESS	read-only
    	STATUS	mandatory
    	DESCRIPTION
    	    "The time in seconds left for this neighboring router. When the
    	    value reaches 0, this entry is deleted from the table."
    	::= { a3ComDvmrpNbrRouterEntry 6 }

    a3ComDvmrpNbrRouterLeafStatus   OBJECT-TYPE
    	SYNTAX	INTEGER {
    	    	    yes (1),
    	    	    no (2)
    	}
    	ACCESS	read-only
    	STATUS	mandatory
    	DESCRIPTION
    	    "This object specifies if this neighboring router is a leaf node."
    	::= { a3ComDvmrpNbrRouterEntry 7 }

    a3ComDvmrpNbrRouterPruneStatus  OBJECT-TYPE
    	SYNTAX	INTEGER {
    	    	    yes (1),
    	    	    no (2)
    	}
    	ACCESS	read-only
    	STATUS	mandatory
    	DESCRIPTION
    	    "This object specifies if this neighboring router supports DVMRP
    	    prune."
    	::= { a3ComDvmrpNbrRouterEntry 8 }

    a3ComDvmrpNbrRouterGenIdStatus  OBJECT-TYPE
    	SYNTAX	INTEGER {
    	    	    yes (1),
    	    	    no (2)
    	}
    	ACCESS	read-only
    	STATUS	mandatory
    	DESCRIPTION
    	    "This object specifies if this neighboring router provides generation
    	    ID and its router list in the DVMRP probe packet."
    	::= { a3ComDvmrpNbrRouterEntry 9 }

    a3ComDvmrpNbrRouterMtraceStatus OBJECT-TYPE
    	SYNTAX	INTEGER {
    	    	    yes (1),
    	    	    no (2)
    	}
    	ACCESS	read-only
    	STATUS	mandatory
    	DESCRIPTION
    	    "This object specifies if this neighboring router supports multicast
    	    trace route."
    	::= { a3ComDvmrpNbrRouterEntry 10 }

END
