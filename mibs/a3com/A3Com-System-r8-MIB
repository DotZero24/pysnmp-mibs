-- This MIB is for 3Com intermediate systems to provide general
-- systems level information.
-- The 3Com Enterprise Products Proprietary MIB Extensions
-- Copyright 3Com Corporation, 1993. All rights reserved.


          A3Com-System-r8-MIB DEFINITIONS ::= BEGIN

          IMPORTS
                  enterprises, IpAddress, Counter, TimeTicks
                      FROM RFC1155-SMI
                  DisplayString
                      FROM RFC1213-MIB
                  MacAddress
                      FROM RFC1286-MIB
                  TRAP-TYPE
                      FROM RFC-1215
                  OBJECT-TYPE
                          FROM RFC-1212;

          --
          -- This MIB is for General 3Com Systems.
          --

          a3Com         OBJECT IDENTIFIER ::= { enterprises 43 }
          brouterMIB    OBJECT IDENTIFIER ::= { a3Com 2 }
          a3ComSys      OBJECT IDENTIFIER ::= { brouterMIB 13 }
          a3ComSysID    OBJECT IDENTIFIER ::= { a3ComSys 1 }
          a3ComChip     OBJECT IDENTIFIER ::= { a3ComSys 2 }
          a3ComMem      OBJECT IDENTIFIER ::= { a3ComSys 3 }
          a3ComBrd      OBJECT IDENTIFIER ::= { a3ComSys 4 }
          a3ComAudit    OBJECT IDENTIFIER ::= { a3ComSys 5 }
          a3ComTime     OBJECT IDENTIFIER ::= { a3ComSys 6 }
          a3ComAccCtl   OBJECT IDENTIFIER ::= { a3ComSys 7 }
          a3ComSysMisc  OBJECT IDENTIFIER ::= { a3ComSys 8 }
          a3ComFW       OBJECT IDENTIFIER ::= { a3ComSys 9 }
          a3ComBoot     OBJECT IDENTIFIER ::= { a3ComSys 10 }
          a3ComLastBoot OBJECT IDENTIFIER ::= { a3ComSys 11 }
          a3ComFileMgmt OBJECT IDENTIFIER ::= { a3ComSys 12 }
              a3ComFileList OBJECT IDENTIFIER ::= { a3ComFileMgmt 9 }
              a3ComFmCksum  OBJECT IDENTIFIER ::= { a3ComFileMgmt 10 }
              a3ComFileInfo   OBJECT IDENTIFIER ::= { a3ComFileMgmt 11 }
          a3ComRecovery OBJECT IDENTIFIER ::= { a3ComSys 13 }



      RowStatus ::= INTEGER {
                         active(1),
                         notInService(2),
                         notReady(3),
                         createAndGo(4),
                         createAndWait(5),
                         destroy(6)
      }

      --This data type, which has the same semantics as the rowStatus
      --textual convention used in SNMPv2, is used to add and
      --delete entries from a table.

      --The tables in this MIB allow a subset of the functionality
      --provided by the rowStatus textual convention.  In particular
      --row creation is allowed using only the createAndGo method.

      --That is, when adding entries to this table, this object
      --must be set to createAndGo(4).  The instance identifier
      --for this object will define the values of the columns
      --that make up the index.

      --In the same PDU, the appropriate remaining columns
      --of that row must be set as well.  The agent
      --will immediately set the value of this object to
      --active(1) if the row is correct.  If not, the agent
      --will refuse the SET request and return an
      --error code.

      --To modify an existing entry, it must be removed
      --and another entry with the desired changes added.

      --To remove an entry, set the value of this object
      --to destroy(6).

--
-- The ID Group
--

           a3sysVersion OBJECT-TYPE
               SYNTAX  DisplayString
               ACCESS  read-only
               STATUS  mandatory
               DESCRIPTION
                       "A text string containing general system information,
                       including the package identifier and the system's
                       software release number."
               ::= { a3ComSysID 1 }

           a3sysPlatformDescr OBJECT-TYPE
               SYNTAX  DisplayString
               ACCESS  read-only
               STATUS  mandatory
               DESCRIPTION
                       "A text string describing the physical platform
                       or chassis on which the system is running."
               ::= { a3ComSysID 2 }

           a3sysPlatformID OBJECT-TYPE
               SYNTAX  OBJECT IDENTIFIER
               ACCESS  read-only
               STATUS  mandatory
               DESCRIPTION
                       "An OID defining the system platform."
               ::= { a3ComSysID 3 }

           a3sysCallerID OBJECT-TYPE
               SYNTAX  DisplayString (SIZE(0..31))
               ACCESS  read-write
               STATUS  mandatory
               DESCRIPTION
                       "A text string defined by the user. This
                       string can be used by a system running PPP
                       as a unique identification of itself to
                       its peer when communicating over a PPP link. "
               ::= { a3ComSysID 4 }


--
-- The Chip group
--

          a3sysChipTable OBJECT-TYPE
              SYNTAX  SEQUENCE OF A3sysChipEntry
              ACCESS  not-accessible
              STATUS  mandatory
              DESCRIPTION
                      "This table contains information about the
                      chips that are used in the CPU board of the
                      system."
              REFERENCE
                      "NetBuilderII Ref. Guide: System Service
                      Parameters:  CPUboardInfo"
              ::= { a3ComChip 1 }

          a3sysChipEntry OBJECT-TYPE
              SYNTAX  A3sysChipEntry
              ACCESS  not-accessible
              STATUS  mandatory
              DESCRIPTION
                      "Each entry in this table contains information
                      about one of the chips installed in the CPU
                      module."
              REFERENCE
                      "NetBuilderII Ref. Guide: System Service
                      Parameters:  CPUboardInfo"
              INDEX { a3sysChipSlotIndex, a3sysChipIndex }
              ::= { a3sysChipTable 1 }

          A3sysChipEntry ::=
              SEQUENCE {
                  a3sysChipSlotIndex      INTEGER,
                  a3sysChipIndex          INTEGER,
                  a3sysChipName           DisplayString,
                  a3sysChipDescr          DisplayString
              }

          a3sysChipSlotIndex OBJECT-TYPE
              SYNTAX  INTEGER
              ACCESS  read-only
              STATUS  mandatory
              DESCRIPTION
                      "This identifies a specific slot (and
                      hence, a specific board).  All the Chips
                      described with this index are located
                      on a single board."
              ::= { a3sysChipEntry 1 }

          a3sysChipIndex OBJECT-TYPE
              SYNTAX  INTEGER
              ACCESS  read-only
              STATUS  mandatory
              DESCRIPTION
                      "This identifies a specific chip on the board
                      identified by a3sysChipSlotIndex."
              ::= { a3sysChipEntry 2 }

          a3sysChipName OBJECT-TYPE
              SYNTAX  DisplayString
              ACCESS  read-only
              STATUS  mandatory
              DESCRIPTION
                      "This provides a readable name for the chip."
              ::= { a3sysChipEntry 3 }

          a3sysChipDescr OBJECT-TYPE
              SYNTAX  DisplayString
              ACCESS  read-only
              STATUS  mandatory
              DESCRIPTION
                      "This provides general information about
                      the chip, including its part number and
                      revision number."
              ::= { a3sysChipEntry 4 }

--
-- The Memory group
--

          a3sysMemTable OBJECT-TYPE
              SYNTAX  SEQUENCE OF A3sysMemEntry
              ACCESS  not-accessible
              STATUS  mandatory
              DESCRIPTION
                      "This table contains information about the
                      system's memory configurations."
              ::= { a3ComMem 1 }

          a3sysMemEntry OBJECT-TYPE
              SYNTAX  A3sysMemEntry
              ACCESS  not-accessible
              STATUS  mandatory
              DESCRIPTION
                      "Each entry in this table contains information
                      about a specific memory component.  The
                      information includes the memory type, its
                      starting address and its size."
              INDEX  { a3sysMemSlotIndex, a3sysMemIndex}
              ::= { a3sysMemTable 1 }

          A3sysMemEntry ::=
              SEQUENCE {
                  a3sysMemSlotIndex
                      INTEGER,
                  a3sysMemIndex
                      INTEGER,
                  a3sysMemType
                      INTEGER,
                  a3sysMemStartAdd
                      INTEGER,
                  a3sysMemSize
                      INTEGER
              }

          a3sysMemSlotIndex OBJECT-TYPE
              SYNTAX  INTEGER
              ACCESS  read-only
              STATUS  mandatory
              DESCRIPTION
                      "This identifies the slot (and hence the board)
                      that supports the memory elements identified
                      by this entry in the table."
              ::= { a3sysMemEntry 1 }

          a3sysMemIndex OBJECT-TYPE
              SYNTAX  INTEGER
              ACCESS  read-only
              STATUS  mandatory
              DESCRIPTION
                      "The index into this table.  Each memory component
                      is identified by a unique value of this object.
                      This is specific to the board identified by
                      a3sysMemSlotIndex."
              ::= { a3sysMemEntry 2 }

          a3sysMemType OBJECT-TYPE
              SYNTAX  INTEGER {
                   other           (1),
                   ram-instruction (2),
                   ram-data        (3),
                   ram-shared      (4),
                   rom-fprom       (5),
                   rom-eeprom      (6),
		   ram-total       (7)
              }
              ACCESS  read-only
              STATUS  mandatory
              DESCRIPTION
                      "This object identifies the type of the memory
                      component."
              ::= { a3sysMemEntry 3 }

          a3sysMemStartAdd OBJECT-TYPE
              SYNTAX  INTEGER
              ACCESS  read-only
              STATUS  mandatory
              DESCRIPTION
                      "The starting address of the memory component."
              ::= { a3sysMemEntry 4 }

          a3sysMemSize OBJECT-TYPE
              SYNTAX  INTEGER
              ACCESS  read-only
              STATUS  mandatory
              DESCRIPTION
                      "The size of the memory component, in bytes."
              ::= { a3sysMemEntry 5 }

--
-- The Board group
--
--   This group contains information about all the boards installed
--   on the system.  This includes IO boards and CPU boards.
--
--  (The objects relating to boards may migrate to the Chassis MIB
--  once it's defined.)
--
          a3sysSlotNumber OBJECT-TYPE
              SYNTAX  INTEGER
              ACCESS  read-only
              STATUS  mandatory
              DESCRIPTION
                      "The number of slots (empty or not) in the system"
              ::= { a3ComBrd 1 }

          a3sysBrdTable  OBJECT-TYPE
              SYNTAX  SEQUENCE OF A3sysBrdEntry
              ACCESS  not-accessible
              STATUS  mandatory
              DESCRIPTION
                      "A table that contains information about the IO boards
                      in this system."
              ::= { a3ComBrd 2 }

          a3sysBrdEntry OBJECT-TYPE
              SYNTAX  A3sysBrdEntry
              ACCESS  not-accessible
              STATUS  mandatory
              DESCRIPTION
                      "A list of information for each IO board in the
                      system."
              INDEX  { a3sysSlotIndex }
              ::= { a3sysBrdTable 1 }

          A3sysBrdEntry ::=
              SEQUENCE {
                  a3sysSlotIndex
                      INTEGER,
                  a3sysBrdDescr
                      DisplayString,
                  a3sysBrdPathCapacity
                      INTEGER,
                  a3sysBrdOID
                      OBJECT IDENTIFIER,
                  a3sysBrdReset
                      INTEGER,
                  a3sysBrdFwVers
                      OBJECT IDENTIFIER
                  }

           a3sysSlotIndex OBJECT-TYPE
               SYNTAX  INTEGER
               ACCESS  read-only
               STATUS  mandatory
               DESCRIPTION
                       "The slot number which this board occupies."
               ::= { a3sysBrdEntry 1 }

           a3sysBrdDescr OBJECT-TYPE
               SYNTAX  DisplayString
               ACCESS  read-only
               STATUS  mandatory
               DESCRIPTION
                       "This contains general information about the
                       Board, including the model type, the serial
                       number, and manufacturing information."
               ::= { a3sysBrdEntry 2 }

          a3sysBrdPathCapacity OBJECT-TYPE
               SYNTAX  INTEGER
               ACCESS  read-only
               STATUS  mandatory
               DESCRIPTION
                       "The number of physical ports supported by
                       this board."
               ::= { a3sysBrdEntry 3 }

          a3sysBrdOID OBJECT-TYPE
               SYNTAX  OBJECT IDENTIFIER
               ACCESS  read-only
               STATUS  mandatory
               DESCRIPTION
                       "The Object Identifier assigned to this
                       Board."
               ::= { a3sysBrdEntry 4 }

          a3sysBrdReset OBJECT-TYPE
               SYNTAX  INTEGER {
                    other (1),
                    reset (2)
               }
               ACCESS  read-write
               STATUS  mandatory
               DESCRIPTION
                       "When this object is set to reset(2), the IO
                       board in the slot specified by this instance
                       identifier of this object is reset.  If a GET
                       request is sent for the value of this object,
                       other(1) is returned."
               ::= { a3sysBrdEntry 5 }

          a3sysBrdFwVers OBJECT-TYPE
               SYNTAX  OBJECT IDENTIFIER
               ACCESS  read-only
               STATUS  mandatory
               DESCRIPTION
                       "This object returns the version of the firmware
                       that is running on this network interface board.
		       A list of all the OIDs assigned to 3Com router
		       firmware can be ftp'd from ftp.3com.com."
               ::= { a3sysBrdEntry 6 }

--
-- Audit trail group
--

          a3sysAuditTrailType OBJECT-TYPE
              SYNTAX  INTEGER {
                   local     (1),   -- use local time
                   universal (2) -- use universal or GMT
              }
              ACCESS  read-write
              STATUS  mandatory
              DESCRIPTION
                      "This object allows the user to determine the format
                      of the time/date stamp that is included with each
                      audit trail message the system generates.  This
                      only applies if there is a Network Control Server
                      for the IBM PC/AT (NCS/AT) or Remote Boot and
                      Configuration Services (RBCS) server on the attached
                      network.  Audit trail messages are generated by
                      various network events and are displayed on the
                      NCS or RBCS console."
              ::= { a3ComAudit 1 }

          a3sysLogServerAddress OBJECT-TYPE
              SYNTAX  IpAddress
              ACCESS  read-write
              STATUS  deprecated
              DESCRIPTION
                      "The address of the NCS or the RBCS that serves
                      as the log server for the system.  The log server
                      receives all of the system's audit trail messages."
              ::= { a3ComAudit 2 }

--
--  The Time group
--

           a3sysDate OBJECT-TYPE
              SYNTAX  DisplayString
              ACCESS  read-write
              STATUS  mandatory
              DESCRIPTION
                      "The current date and time as reflected by the
                      system clock.  The date is displayed via the User
                      interface and Audit Trail Messages as
                      yy/mm/dd hh:mm[:ss].  This same format must be
                      used when setting the Date."
              ::= { a3ComTime 1 }

           a3sysDSTime OBJECT-TYPE
              SYNTAX  INTEGER (-120..120)
              ACCESS  read-write
              STATUS  mandatory
              DESCRIPTION
                      "This parameter specifies the displacement, in
                      minutes, from non-daylight savings time.  The
                      a3sysDSTime object, along with the a3sysTimeZone
                      object, allows the system to support Universal
                      time for network communications spanning different
                      time zones."
              ::= { a3ComTime 2 }

           a3sysTimeZone OBJECT-TYPE
              SYNTAX  INTEGER (-720..720)
              ACCESS  read-write
              STATUS  mandatory
              DESCRIPTION
                      "This object specifies the number of minutes
                      displacement west of Greenwich the system's site
                      is located.  A negative number for this parameter
                      indicates how many minutes displacement east of
                      Greenwich the site is located.  A positive number
                      indicates the number of minutes west of Greenwich."
              ::= { a3ComTime 3 }

--
-- The Access Control Group
--

           a3sysRemoteAccess OBJECT-TYPE
               SYNTAX  INTEGER {
                    enabled  (1),
                    disabled (2)
               }
               ACCESS  read-write
               STATUS  mandatory
               DESCRIPTION
                       "This object determines whether another device
                       can access this system via REMOTE"
              ::= { a3ComAccCtl 1 }

           a3sysTelnetAccess OBJECT-TYPE
               SYNTAX  INTEGER {
                    enabled  (1),
                    disabled (2)
               }
               ACCESS  read-write
               STATUS  mandatory
               DESCRIPTION
                       "This object determines whether another device
                       can access this system via TELNET"
              ::= { a3ComAccCtl 2 }

           a3sysConsoleAccess OBJECT-TYPE
               SYNTAX  INTEGER {
                    enabled  (1),
                    disabled (2)
               }
               ACCESS  read-write
               STATUS  mandatory
               DESCRIPTION
                       "This object determines whether another device
                       can access this system via the Console"
              ::= { a3ComAccCtl 3 }

           a3sysSNMPAccess OBJECT-TYPE
               SYNTAX  INTEGER {
                    enabledTraps    (1),
                    enabledNoTraps  (2),
                    disabledTraps   (3),
                    disabledNoTraps (4)
               }
               ACCESS  read-write
               STATUS  mandatory
               DESCRIPTION
                       "This object determines whether another device
                       can access this system via SNMP.  Note, once
                       SNMP access is disabled, the NMS will no longer
                       be able to access this system via SNMP.

                       If this is set to enabledTraps(1), the system
                       allows SNMP access and will send traps when
                       appropriate.

                       If this is set to enabledNoTraps(2), the system
                       allows SNMP access, but no traps will be sent.

                       If this is set to disabledTraps, the system
                       does not allow SNMP access, but will send
                       traps when appropriate.

                       If this is set to disabledNoTraps(4), the system
                       does not allow SNMP access and does not
                       send any traps."
              ::= { a3ComAccCtl 4 }

--
-- This table contains the SNMPv1 Community Strings
--

           a3sysSNMPCommTable OBJECT-TYPE
              SYNTAX  SEQUENCE OF A3sysSNMPCommEntry
              ACCESS  not-accessible
              STATUS  mandatory
              DESCRIPTION
                      "This table contains all the community strings
                      known to the SNMP agent."
              ::= { a3ComAccCtl 5 }

           a3sysSNMPCommEntry OBJECT-TYPE
              SYNTAX  A3sysSNMPCommEntry
              ACCESS  not-accessible
              STATUS  mandatory
              DESCRIPTION
                      "Each entry in the table contains information
                      about a single community string. "
              INDEX { a3sysSNMPCommString }
              ::= { a3sysSNMPCommTable 1 }

           A3sysSNMPCommEntry ::=
              SEQUENCE {
                  a3sysSNMPCommString         DisplayString (SIZE(1..15)),
                  a3sysSNMPCommAccess         INTEGER,
                  a3sysSNMPCommTrap           INTEGER,
                  a3sysSNMPCommStatus         RowStatus
              }

           a3sysSNMPCommString OBJECT-TYPE
              SYNTAX  DisplayString (SIZE(1..15))
              ACCESS  read-only
              STATUS  mandatory
              DESCRIPTION
                      "This identifies a specific community string."
              ::= { a3sysSNMPCommEntry 1 }

           a3sysSNMPCommAccess OBJECT-TYPE
              SYNTAX  INTEGER {
                   readOnly  (1),
                   readWrite (2)
              }
              ACCESS  read-write
              STATUS  mandatory
              DESCRIPTION
                      "This identifies the level of access allowed
                      for this community string."
              DEFVAL { readOnly }
              ::= { a3sysSNMPCommEntry 2 }

           a3sysSNMPCommTrap OBJECT-TYPE
              SYNTAX  INTEGER {
                   genericOnly  (1),    -- coldStart, warmStart, linkDown/Up
                   authenOnly   (2),    -- authenticationFailure
                   allTraps     (3),
                   noTraps      (4)
              }
              ACCESS  read-write
              STATUS  mandatory
              DESCRIPTION
                      "This specifies which traps get sent to the
                      managers specified by this community string."
              DEFVAL { noTraps }
              ::= { a3sysSNMPCommEntry 3 }

           a3sysSNMPCommStatus OBJECT-TYPE
              SYNTAX  RowStatus
              ACCESS  read-write
              STATUS  mandatory
              DESCRIPTION
                      "This object is used to add and delete
                      entries in this table.  See the notes
                      describing RowStatus at the beginning
                      of this MIB."
              ::= { a3sysSNMPCommEntry 4 }

--
-- This table contains the Managers that are allowed to use
-- each of the community strings identified above.
--

           a3sysSNMPMgrTable OBJECT-TYPE
              SYNTAX  SEQUENCE OF A3sysSNMPMgrEntry
              ACCESS  not-accessible
              STATUS  mandatory
              DESCRIPTION
                      "This table contains the Managers that
                      are allowed to use the community strings
                      identified in a3sysSNMPCommTable.  Each
                      Manager is identified by its IP address."
              ::= { a3ComAccCtl 6 }

           a3sysSNMPMgrEntry OBJECT-TYPE
              SYNTAX  A3sysSNMPMgrEntry
              ACCESS  not-accessible
              STATUS  mandatory
              DESCRIPTION
                      "Each entry identifies a single Manager,
                      community string pair."
              INDEX { a3sysSNMPMgrCommString, a3sysSNMPMgrAddress }
              ::= { a3sysSNMPMgrTable 1 }

           A3sysSNMPMgrEntry ::=
              SEQUENCE {
                  a3sysSNMPMgrCommString      DisplayString (SIZE(1..15)),
                  a3sysSNMPMgrAddress         IpAddress,
                  a3sysSNMPMgrMask            IpAddress,
                  a3sysSNMPMgrStatus          RowStatus
              }

           a3sysSNMPMgrCommString OBJECT-TYPE
              SYNTAX  DisplayString (SIZE(1..15))
              ACCESS  read-only
              STATUS  mandatory
              DESCRIPTION
                      "This identifies a specific community string."
              ::= { a3sysSNMPMgrEntry 1 }

           a3sysSNMPMgrAddress OBJECT-TYPE
              SYNTAX  IpAddress
              ACCESS  read-only
              STATUS  mandatory
              DESCRIPTION
                      "This identifies a single Management station
                      that is allowed to use the community string
                      associated with this entry.  The set of all
                      entries with same value of a3sysSNMPMgrCommString
                      identifies all the Managers that are allowed
                      to use that community string."
              ::= { a3sysSNMPMgrEntry 2 }

           a3sysSNMPMgrMask OBJECT-TYPE
              SYNTAX  IpAddress
              ACCESS  read-write
              STATUS  mandatory
              DESCRIPTION
                      "This object can be used to mask part of the
                      IP address specified by a3sysSNMPMgrAddress.
                      The use of this mask can then be used to identify
                      a range of addresses that are allowed to use
                      this community string."
              ::= { a3sysSNMPMgrEntry 3 }

           a3sysSNMPMgrStatus OBJECT-TYPE
              SYNTAX  RowStatus
              ACCESS  read-write
              STATUS  mandatory
              DESCRIPTION
                      "This object is used to add and delete entries
                      in this table.  See the notes describing
                      RowStatus at the beginning of this MIB for
                      specific instructions on how to do this."
              ::= { a3sysSNMPMgrEntry 4 }

--
-- This table contains the IP addresses of
-- stations that are allowed to access the NetBuilder
-- via Telnet
--

           a3sysTelnetMgrTable OBJECT-TYPE
              SYNTAX  SEQUENCE OF A3sysTelnetMgrEntry
              ACCESS  not-accessible
              STATUS  mandatory
              DESCRIPTION
                      "This table contains the IP addresses that
                      are allowed to use Telnet to access to
		      the NetBuilder in the TelnetManager table."
              ::= { a3ComAccCtl 7 }

           a3sysTelnetMgrEntry OBJECT-TYPE
              SYNTAX  A3sysTelnetMgrEntry
              ACCESS  not-accessible
              STATUS  mandatory
              DESCRIPTION
                      "Each entry identifies a single Manager,
                      community string pair."
              INDEX { a3sysTelnetMgrAddress }
              ::= { a3sysTelnetMgrTable 1 }

           A3sysTelnetMgrEntry ::=
              SEQUENCE {
                  a3sysTelnetMgrAddress	IpAddress,
                  a3sysTelnetMgrStatus	RowStatus
              }

           a3sysTelnetMgrAddress OBJECT-TYPE
              SYNTAX  IpAddress
              ACCESS  read-only
              STATUS  mandatory
              DESCRIPTION
                      "This identifies a single Management station
                      that is allowed to use the Telnet to manage
                      the NetBuilder.  Maximally, six (6)
		      IP addresses can be configured in each NB."
              ::= { a3sysTelnetMgrEntry 1 }

           a3sysTelnetMgrStatus OBJECT-TYPE
              SYNTAX  RowStatus
              ACCESS  read-write
              STATUS  mandatory
              DESCRIPTION
                      "This object is used to add and delete entries
                      in this table.  See the notes describing
                      RowStatus at the beginning of this MIB for
                      specific instructions on how to do this."
              ::= { a3sysTelnetMgrEntry 2 }


           a3sysPasswordTable OBJECT-TYPE
              SYNTAX  SEQUENCE OF A3sysPasswordEntry
              ACCESS  not-accessible
              STATUS  mandatory
              DESCRIPTION
                      "This table contains the system's passwords."
              ::= { a3ComAccCtl 8 }

           a3sysPasswordEntry OBJECT-TYPE
              SYNTAX  A3sysPasswordEntry
              ACCESS  not-accessible
              STATUS  mandatory
              DESCRIPTION
                      "Each entry identifies a single system password."
              INDEX { a3sysUserName, a3sysOldPassword }
              ::= { a3sysPasswordTable 1 }

           A3sysPasswordEntry ::=
              SEQUENCE {
                  a3sysPwStatus         INTEGER,
                  a3sysUserName         DisplayString,
                  a3sysUserLevel        INTEGER,
                  a3sysOldPassword	DisplayString,
                  a3sysNewPassword	DisplayString
              }

           a3sysPwStatus OBJECT-TYPE
              SYNTAX  INTEGER {
                      valid(1),
                      invalid(2)
              }
              ACCESS  read-write
              STATUS  mandatory
              DESCRIPTION
                "User Status.  `invalid' is used to indicate this user
                is no longer allowed to access this device, and the
                table entry may subsequently be re-used. Note that
                the Status of default Users cannot be set to invalid."
              ::= { a3sysPasswordEntry 1 }

           a3sysUserName OBJECT-TYPE
              SYNTAX  DisplayString (SIZE (1..10))
              ACCESS  read-only
              STATUS  mandatory
              DESCRIPTION
                "An ASCII string for the User Name.  Empty strings are
                not allowed.  The index column for the User Table.  There
                are two default users defined, 'root' and 'user'."
              ::= { a3sysPasswordEntry 2 }

           a3sysUserLevel       OBJECT-TYPE
              SYNTAX  INTEGER {
                      monitor(1),
                      secureMonitor(2),
                      manager(3),
                      specialist(4),
                      security(5)
                }
              ACCESS  read-write
              STATUS  mandatory
              DESCRIPTION
                "User Access Level defining the scope of management allowed
                for this user.  Note that the access level of default Users
                cannot be changed."
              ::= { a3sysPasswordEntry 3 }


           a3sysOldPassword OBJECT-TYPE
              SYNTAX  DisplayString
              ACCESS  read-only
              STATUS  mandatory
              DESCRIPTION
                      "The current password."
              ::= { a3sysPasswordEntry 4 }

           a3sysNewPassword OBJECT-TYPE
              SYNTAX  DisplayString
              ACCESS  read-write
              STATUS  mandatory
              DESCRIPTION
                      "The new password."
              ::= { a3sysPasswordEntry 5 }


           a3sysSnmpPasswordCtl OBJECT-TYPE
              SYNTAX  INTEGER {
                    enabled  (1),
                    disabled (2)
               }
              ACCESS  read-write
              STATUS  mandatory
              DESCRIPTION
                      "This object indicates whether this system's passwords
                      can be changed via snmp."
              ::= { a3ComAccCtl 9 }

--
-- The Misc System Group
--

           a3sysNetMapTime OBJECT-TYPE
               SYNTAX  INTEGER (0..120)
               ACCESS  read-write
               STATUS  mandatory
               DESCRIPTION
                       "The number of seconds between broadcasts of the
                       system's address on the attached network.  This
                       only applies to 3Com's NETMap protocol.  If this
                       object is set to 0, the broadcasting of the system's
                       address is disabled."
               DEFVAL { 0 }
               ::= { a3ComSysMisc 1 }

           a3sysUIBinary OBJECT-TYPE
               SYNTAX  INTEGER {
                    on  (1),
                    off (2)
               }
               ACCESS  read-write
               STATUS  mandatory
               DESCRIPTION
                       "If on, the system is allowed to negotiate for
                       binary transmission when a Telnet connection is
                       made."
               DEFVAL { off }
               ::= { a3ComSysMisc 2 }

           a3sysChangeTimestamp OBJECT-TYPE
               SYNTAX  TimeTicks
               ACCESS  read-only
               STATUS  mandatory
               DESCRIPTION
                       "This object contains the value of sysUpTime
                       when the most recent change was made to this
                       system, either via the Console, TELNET, or
                       through SNMP."
               ::= { a3ComSysMisc 3 }

           a3sysCpuUtil OBJECT-TYPE
               SYNTAX  INTEGER (0..100)
               ACCESS  read-only
               STATUS  mandatory
               DESCRIPTION
                       "This object provides a measure of the
                       current utilization of the CPU on this
                       system."
               ::= { a3ComSysMisc 4 }

           a3sysCpuBrdMacAddr OBJECT-TYPE
               SYNTAX  MacAddress
               ACCESS  read-only
               STATUS  mandatory
               DESCRIPTION
                       "The system's MAC address.  For those devices
                       whose CPU boards contain a MAC address, this
                       object provides the value of that address (NB2's).
                       For those devices whose CPU boards don't contain a
                       MAC address (NB1's), this provides the MAC address
                       of the first interface."
               ::= { a3ComSysMisc 5 }

           a3sysExpMacAddr OBJECT-TYPE
               SYNTAX  MacAddress
               ACCESS  read-only
               STATUS  mandatory
               DESCRIPTION
                       "This identifies the MAC address to which the @m
                       symbol is expanded when doing file copies."
               ::= { a3ComSysMisc 6 }

           a3sysVportTimestamp OBJECT-TYPE
               SYNTAX  TimeTicks
               ACCESS  read-only
               STATUS  mandatory
               DESCRIPTION
                       "This specifies the value of sysUpTime when the last
                       virtual port was added or deleted.  This object should
                       be used to determine if and when the set of virtual ports
                       supported by this system has changed."
               ::= { a3ComSysMisc 7 }

           a3sysDefDrive OBJECT-TYPE
               SYNTAX  INTEGER {
                   driveA (1),
                   driveB (2)
               }
               ACCESS  read-only
               STATUS  mandatory
               DESCRIPTION
                   "This object identifies the current default drive
                   for this system."
               ::= { a3ComSysMisc 8 }

           a3sysDefDriveType OBJECT-TYPE
               SYNTAX  INTEGER {
                   floppy (1),
                   flash  (2),
                   unknown (3),
                   noDrive (4)
               }
               ACCESS  read-only
               STATUS  mandatory
               DESCRIPTION
                   "This object identifies the current default
                   drive type for this system."
               ::= { a3ComSysMisc 9 }

           a3sysDriveStatus OBJECT-TYPE
               SYNTAX  INTEGER {
                   noDrives  (1),
                   driveA    (2),
                   driveB    (3),
                   driveAB   (4)
               }
               ACCESS  read-only
               STATUS  mandatory
               DESCRIPTION
                   "This object identifies which disk drives are supported
                   by this system.  noDrives(1) means no disk drives are
                   supported.  driveA means only drive A is supported.
                   driveB means only drive B is supported, while driveAB(4)
                   means both drives A and B are supported."
               ::= { a3ComSysMisc 10 }

           a3sysBogusDhcpSvr OBJECT-TYPE
               SYNTAX IpAddress
               ACCESS read-only
               STATUS mandatory
               DESCRIPTION
                   "This object has the IP address of the last seen
                   bogus DHCP or BOOTP server."
               ::= { a3ComSysMisc 11 }

           a3sysNb2EepromVers OBJECT-TYPE
               SYNTAX INTEGER
               ACCESS read-only
               STATUS mandatory
               DESCRIPTION
                   "This object returns the version number of the EEPROM
                   on a NetBuilderII.  Various features are dependent on
                   having the correct version of EEPROM resident on the
                   NetBuilderII."
               ::= { a3ComSysMisc 12 }

           a3sysX25Conns OBJECT-TYPE
               SYNTAX INTEGER
               ACCESS read-only
               STATUS mandatory
               DESCRIPTION
                   "This object returns the number of active X25 connections
                   currently maintained by the NetBuilder."
               ::= { a3ComSysMisc 13 }



--
--
-- this group controls Firmware related parameters
--

           a3sysFwSerBaudCons OBJECT-TYPE
               SYNTAX  INTEGER {
                    unknown  (1),
                    bps110   (2),
                    bps300   (3),
                    bps600   (4),
                    bps1200  (5),
                    bps2400  (6),
                    bps4800  (7),
                    bps9600  (8),
                    bps19200 (9),
                    bps38400 (10),
                    bps57600 (11)
               }
               ACCESS  read-write
               STATUS  mandatory
               DESCRIPTION
                       "This object sets the baud rate for the
                       console port, which is located on the CEC
                       module's connector/LEDC panel."
               REFERENCE
                       "NBII CEC Module Installation Guide: Serial Port
                       Parameter."
               ::= { a3ComFW 1 }

           a3sysFwSerBaudAux OBJECT-TYPE
               SYNTAX  INTEGER {
                    unknown  (1),
                    bps110   (2),
                    bps300   (3),
                    bps600   (4),
                    bps1200  (5),
                    bps2400  (6),
                    bps4800  (7),
                    bps9600  (8),
                    bps19200 (9)
               }
               ACCESS  read-write
               STATUS  mandatory
               DESCRIPTION
                       "This object sets the baud rate for the
                       auxiliary port, which is located on the CEC
                       module's connector/LEDC panel."
               REFERENCE
                       "NBII CEC Module Installation Guide: Serial Port
                       Parameter."
               ::= { a3ComFW 2 }

           a3sysFwSelfTest OBJECT-TYPE
               SYNTAX  INTEGER {
                    skip              (1),
                    testOnce          (2),
                    other             (3),
                    loop              (4)
               }
               ACCESS  read-write
               STATUS  mandatory
               DESCRIPTION
                       "This parameter determines how the system handles
                       self tests when the system is powered on or
                       reset.  The system can be configured to skip its
                       self tests, run self tests once, or run self
                       tests continuously (loop)."
               REFERENCE
                       "NBII CEC Module Installation Guide: Self Test
                       Parameter."
               ::= { a3ComFW 3 }

--
-- this group controls Booting related Firmware parameters
--

           a3sysReBoot OBJECT-TYPE
               SYNTAX  INTEGER {
                    other      (1),
                    stdReboot  (2)
               }
               ACCESS  read-write
               STATUS  mandatory
               DESCRIPTION
                       "This object can be used to reboot the system.
                       If this object is set to stdReboot(2), the
                       system's action is determined by the value of
                       a3sysStartUpAction.  If that object has the value
                       monitor(1), the system will go into monitor
                       mode.  If that object has the value userListOnce(2)
                       or userListForever(3), the system will attempt to
                       reboot from the sources identified by the User Boot List.

                       If this object is read, the value, other (1),
                       will be returned."
               REFERENCE
                       "NBII Ref. Guide, Commands: ReBoot."
               ::= { a3ComBoot 1 }

           a3sysTestBootTime OBJECT-TYPE
               SYNTAX  INTEGER
               ACCESS  read-write
               STATUS  mandatory
               DESCRIPTION
                       "The Test Boot Time indicates the number of seconds
                       after a test reboot the system will automatically
                       reboot.  Upon reboot, the system will start up a timer
                       initialized to the value of this object.  The object
                       a3sysTestRecoveryTimer contains the real time value of
                       this timer.  The timer will automatically start counting
                       down after the system comes up.  If this timer expires,
                       the system will automatically reboot using the Primary Boot
                       Source.

                       To cancel the timer, the object a3sysTestRecoveryTimer must
                       be set to zero.  This provides a recovery mechanism for a
                       system under test that loses management connectivity."
                ::= { a3ComBoot 2 }

           a3sysStartUpAction OBJECT-TYPE
               SYNTAX  INTEGER {
                    monitor         (1),
                    userListOnce    (2),
                    userListForever (3),
                    local           (4)
               }
               ACCESS  read-write
               STATUS  mandatory
               DESCRIPTION
                       "This parameter determines the boot source
                       when the system is powered on or reset.  If
                       monitor (1) is chosen, the system enters
                       monitor mode immediately.  If userListOnce (2)
                       is chosen, the system attempts to boot from
                       primary and secondary sources defined by the
                       User Boot List.  (Specifics about the use of the
                       secondary boot source are provided by a3sysBootSources.)
                       This list may identify network boot sources or local
                       floppy sources, or both.
                       If userListForever (3) is chosen, the system
                       will keep trying the sources listed in the
                       User Boot List until one of them is successful.
                       If local(4) is chosen, the system will boot from
                       the local floppy.  The name of the file used is
                       identified by the value of a3sysUblFileName for the
                       Primary Boot Source."
               REFERENCE
                       "NBII CEC Module Installation Guide: Initial Boot
                       Type Parameter."
               ::= { a3ComBoot 3 }

           a3sysTestRecoveryTimer OBJECT-TYPE
               SYNTAX  INTEGER
               ACCESS  read-write
               STATUS  mandatory
               DESCRIPTION
                       "This object contains the real time value of the
                       Test Recovery Timer.  When the system is performing
                       a 'test boot' (ie, a boot when a3sysBootSources equals
                       testWithPrimaryBackup (3)), the system will start a
                       countdown timer initialized to the value of a3sysBootTime.
                       If this timer is allowed to count down to zero, the
                       system will reboot, this time using the primary boot source
                       instead of the test boot source.  If the timer is disabled, however,
                       before it counts down (the timer is disabled by setting
                       the value of this object to zero), the system won't reboot
                       and will continue to run the test boot source's software.

                       This timer is part of a comprehensive software update
                       strategy.  See the relevant 3Com manuals for more
                       details."
               ::= { a3ComBoot 4 }

           a3sysDirectedReBoots OBJECT-TYPE
               SYNTAX  Counter
               ACCESS  read-only
               STATUS  mandatory
               DESCRIPTION
                       "This is a counter that tracks the number of times the
                       system has completed successfully a boot, no matter
                       how the boot was initiated (power-on, front-panel-button
                       reset, command line, or exception)."
               ::= { a3ComBoot 5 }

           a3sysExceptionReBoots OBJECT-TYPE
               SYNTAX  Counter
               ACCESS  read-only
               STATUS  mandatory
               DESCRIPTION
                       "This is a counter that tracks the number of times
                       the system has crashed and a reboot sequence is begun
                       by the exception handler.  Note, some type of crashes
                       are not able to update this counter due to various
                       hardware lockups.  Also note, this counter will be
                       incremented when a user resets the system from the
                       command line (RS).  This will not be incremented,
                       however, when the user reboots the system from the
                       command line (RB)."
               ::= { a3ComBoot 6 }

           a3sysBootDump OBJECT-TYPE
               SYNTAX  INTEGER {
                    noDump      (1),
                    monitor     (2),
                    localDevice (3),
                    userList    (4),
                    network     (5)
               }
               ACCESS  read-write
               STATUS  mandatory
               DESCRIPTION
                       "This determines whether or not a memory dump
                       is performed if the system fails due to a
                       software problem.  If noDump (1) is selected,
                       the system will not attempt to perform a memory
                       dump.  If monitor (2) is selected, the system
                       goes directly into monitor mode and waits for
                       further commands.  If localDevice (3) is selected,
                       the system dumps its memory to the local storage
                       device.  Since the memory dump will require several
                       floppy disks, the system will prompt the user via the
                       User Interface to change disks.  If userList (4) is
                       selected, the system will upload its memory to the
                       source specified in the User Boot List.

                       Only the NetBuilder Remote Office and NetBuilder II support
                       the network(5) option.  If this is set, the parameters in entry
                       four (dump) of a3sysUserBootListTable identify the destination."
               REFERENCE
                       "NBII CEC Module Installation Guide: Dump Destination
                       Parameter."
               ::= { a3ComBoot 7 }

           a3sysBootSources OBJECT-TYPE
               SYNTAX  INTEGER {
                    primary               (1),
                    primaryAndSecondary   (2),
                    testWithPrimaryBackup (3),
                    secondary             (4)
               }
               ACCESS  read-write
               STATUS  mandatory
               DESCRIPTION
                       "This parameter is used to specify how the entries
                       in this table are used.

                       If this object is set to primary(1), the system
                       will use only the primary boot source when
                       rebooting.  (note, this is the entry where
                       a3sysUblSource = primary(1)).

                       If this object is set to primaryAndSecondary(2),
                       the system will attempt to boot first from the
                       primary boot source, and, if that fails (after
                       a3sysUblMaxRetries attemps), the system will
                       try the secondary boot source.

                       If this object has the value testWithPrimaryBackup(3),
                       the system, when rebooting, will perform a test boot
                       using the 'test' boot source.  Note, the NetBuilder Remote
                       Office and NetBuilder II use entry 3 in a3sysUserBootListTable
                       as the 'test' boot source (a3sysUblSource = test(3)),
                       while other 3Com routers (NetBuilder Remote, NetBuilder
                       Remote Control, NetBuilder Local, and NetBuilder Remote
                       Access) don't support all 4 rows in a3sysUserBootListTable,
                       and simply use the secondary boot source (a3sysUblSource = secondary(2))
                       to identify the 'test' boot source.

                       After booting from the 'test' boot source, if the
                       Test Recovery Timer (a3sysTestRecoveryTimer) is
                       allowed to count down to zero, the system will
                       reboot using the primary boot source.  (see the
                       reference guide for details about test booting).
                       When in this mode, to prevent the system from rebooting
                       using the primary boot source, the Test Recovery Timer
                       (a3sysTestRecoveryTimer) must be set to zero.

                       Note, this object cannot be set to testWithPrimaryBackup(3)
                       explicitly.  Instead, by setting a3sysTestBootTimer to a
                       non-zero value, the system will automatically go into
                       'Test Boot' mode and this object will be given the
                       value testWithPrimaryBackup(3).

                       If this object has the value secondary(4), the system will
                       use only the secondary boot source when rebooting."
               ::= { a3ComBoot 8 }

           a3sysUserBootListTable OBJECT-TYPE
               SYNTAX  SEQUENCE OF A3sysUserBootListEntry
               ACCESS  not-accessible
               STATUS  mandatory
               DESCRIPTION
                       "This table defines a list of boot sources (and for the
                       NetBuilder Remote Office -- memory dump destinations).

                       There are two other parameters that dictate how the
                       contents of this table are used.  These parameters
                       are represented by a3sysStartUpAction and a3sysBootSources.

                       a3sysStartUpAction specifies what this system does when it
                       first comes up. If a3sysStartUpAction is set to userListOnce (2),
                       the system will make a single attempt to use the entries in
                       this table to identify how it should boot.  If a3sysStartUpAction
                       is set to userListForever (3), the system will make repeated
                       attempts at using the entries in this table.

                       If a3sysStartUpAction indicates that the system is to use this
                       table, the order in which the entries are used is dictated by
                       a3sysBootSources.  If a3sysBootSources has the value primary (1),
                       the system will attempt to boot only from the source identified by
                       entry 1 in this table.  If a3sysBootSources has the value
                       primaryAndSecondary(2), the system will attempt to boot first
                       from the source identified by entry 1, and, if that source fails,
                       the system will try the source identified by entry 2 (the secondary
                       source).  If a3sysBootSources has the value testWithPrimaryBackup(3),
                       the system will perform a test boot using the test boot source.  Note,
                       for the NetBuilder Remote Office, this is the third entry (test) in this
                       table.  For the NetBuilder II and the NetBuilder I family( NetBuilder Local,
                       NetBuilder Remote, NetBuilder RemoteAccess, and NetBuilder RemoteControl),
                       the test boot source is identified by entry 2 (secondary) in this table.
                       If the test boot source fails (see the Reference Guide for more details
                       on test booting), the system will revert back to the source identified
                       by entry 1 (primary) in this table.

                       The NetBuilder Remote Office supports a fourth entry in this table,
                       which identifies where over the network memory is to be dumped in the
                       case of a system crash.  Note, the destination device (a3sysUblDevice)
                       must be set to network (3), in this case.  Also note that many
                       of the columns in this row will be irrelevant and won't affect
                       where the memory gets dumped.

                       Note, all entries in this table apply only to future
                       boots.  They don't necessarily provide information
                       about previous boots."
               REFERENCE
                       "NBII CEC Module Installation Guide: User Boot List
                       Parameter."
               ::= { a3ComBoot 9 }

           a3sysUserBootListEntry OBJECT-TYPE
               SYNTAX  A3sysUserBootListEntry
               ACCESS  not-accessible
               STATUS  mandatory
               DESCRIPTION
                       "Each entry in this table contains a single boot source."
               INDEX { a3sysUblSource }
               ::= { a3sysUserBootListTable 1 }

           A3sysUserBootListEntry ::=
               SEQUENCE {
                   a3sysUblSource           INTEGER,
                   a3sysUblDevice           INTEGER,
                   a3sysUblFileName         DisplayString,
                   a3sysUblNetFile          DisplayString,
                   a3sysUblSlot             INTEGER,
                   a3sysUblInterface        INTEGER,
                   a3sysUblMaxRetries       INTEGER,
                   a3sysUblConfigFileDevice INTEGER,
                   a3sysUblConfigFilePath   DisplayString,
                   a3sysUblConfigProt       INTEGER,
                   a3sysUblConfigUserName   DisplayString (SIZE(0..20)),
                   a3sysUblConfigPassword   DisplayString (SIZE(0..20)),
                   a3sysUblConfigAcct       DisplayString (SIZE(0..30)),
                   a3sysUblMacAddress       INTEGER,
                   a3sysUblCanonicalFlag    INTEGER,
                   a3sysUblRemoteProt       INTEGER,
                   a3sysUblBaudRate         INTEGER,
                   a3sysUblClockSource      INTEGER,
                   a3sysUblConnectorType    INTEGER,
                   a3sysUblWanAddress       DisplayString (SIZE(0..80)),
                   a3sysUblClientIpAddr     IpAddress,
                   a3sysUblServerIpAddr     IpAddress,
                   a3sysUblGwIpAddr         IpAddress,
                   a3sysUblConfigFileIpAddr IpAddress,
                   a3sysUblIpMask           IpAddress,
                   a3sysUblAddressDiscovery INTEGER,
                   a3sysUblPassword         DisplayString
               }

           a3sysUblSource OBJECT-TYPE
               SYNTAX  INTEGER {
                    primary   (1),
                    secondary (2),
                    test      (3),
                    dump      (4)
               }
               ACCESS  read-only
               STATUS  mandatory
               DESCRIPTION
                       "This identifies the entry number in this table.
                       Currently, the table is limited to two entries.
                       The first entry is labelled primary(1), the next
                       has the label secondary(2).

                       The NetBuilder RemoteOffice and NetBuilder II (as of
                       sw version 8.0) supports two additional entries.
                       Entry three (test) identifies a separate
                       boot block which is used when doing a test boot.
                       Entry four (dump) identifies where memory is to
                       be dumped.  Note, only a subset of the columns in
                       this entry are relevant.  Specifically, a3sysUblDevice
                       must have the value network(3) (ie, memory dumps are
                       preformed only over the network by the NBRO)."
               REFERENCE
                       "NBII CEC Module Installation Guide: User Boot List"
               ::= { a3sysUserBootListEntry 1 }

           a3sysUblDevice OBJECT-TYPE
               SYNTAX  INTEGER {
                    localMediaA  (1),
                    localMediaB  (2),
                    network      (3),
                    monitor      (4),
                    other        (5),
                    auto         (6)
               }
               ACCESS  read-write
               STATUS  mandatory
               DESCRIPTION
                       "This object identifies the source from which the
                       system attempts to boot.  If this object is set to
                       localMediaA(1), the system will attempt to boot from
                       drive A of the local storage media (A is the flash drive
                       for those systems with both flash and floppy drives),
                       using the filename identified by a3sysUblFileName.
                       If this is set to localMediaB(2), the system will
                       boot from drive B.

                       If this object is set to network (3), the system will
                       attempt to boot from a BOOTP/TFTP server attached to
                       the network.  The network interface that is used in the
                       booting is identified by both a3sysUblSlot and
                       a3sysUblInterface.

                       The name of the boot file on the remote system is
                       identified by a3sysUblFileName.

                       monitor(4) is no longer supported.

                       If this object has the value other(5), nothing has
                       been specified."
               REFERENCE
                       "NBII CEC Module Installation Guide: User Boot List:
                       Boot Source Parameter."
               ::= { a3sysUserBootListEntry 2 }

           a3sysUblFileName OBJECT-TYPE
               SYNTAX  DisplayString
               ACCESS  read-write
               STATUS  mandatory
               DESCRIPTION
                       "This specifies the path and name of the boot
                       file.  For example, to specify the file boot.29k in
                       the root directory, this object should
                       have the value 'boot.29k'"
               REFERENCE
                       "NBII CEC Module Installation Guide: User Boot List:
                       Boot Filename Parameter."
               ::= { a3sysUserBootListEntry 3 }

           a3sysUblNetFile OBJECT-TYPE
               SYNTAX  DisplayString
               ACCESS  read-write
               STATUS  deprecated
               DESCRIPTION
                       "This object has been deprecated. (use a3sysUblFileName
                       regardless of whether it's local or remote)."
               REFERENCE
                       "NBII CEC Module Installation Guide: User Boot List:
                       Network Boot String Parameter."
               ::= { a3sysUserBootListEntry 4 }

           a3sysUblSlot OBJECT-TYPE
               SYNTAX  INTEGER
               ACCESS  read-write
               STATUS  mandatory
               DESCRIPTION
                       "This specifies the physical slot where the IO module
                       from which the system will be booting is installed.
                       This only applies when a3sysUblDevice is set to
                       network(2)"
               REFERENCE
                       "NBII CEC Module Installation Guide: User Boot List:
                       Boot Source Parameter."
               ::= { a3sysUserBootListEntry 5 }

           a3sysUblInterface OBJECT-TYPE
               SYNTAX  INTEGER {
                    unknown(1),
                    interfaceA (2),
                    interfaceB (3)
               }
               ACCESS  read-write
               STATUS  mandatory
               DESCRIPTION
                       "This specifies the physical port on the IO
                       module (installed in the slot identified by a3sysUblSlot)
                       that the system will be booting from.  This only applies
                       when a3sysUblDevice is set to network(2).  If there
                       is only one connector in the module, this object should
                       have the value: interfaceA(2)."
               REFERENCE
                       "NBII CEC Module Installation Guide: User Boot List:
                       Boot Source Parameter."
               DEFVAL { interfaceA }
               ::= { a3sysUserBootListEntry 6 }

           a3sysUblMaxRetries OBJECT-TYPE
               SYNTAX  INTEGER (0..255)
               ACCESS  read-write
               STATUS  mandatory
               DESCRIPTION
                       "This object determines the number of times the
                       system will try to boot from the source identified
                       by this table entry before going to the next entry."
               REFERENCE
                       "NBII CEC Module Installation Guide: User Boot List:
                       Maximum Retries Parameter."
               ::= { a3sysUserBootListEntry 7 }

           a3sysUblConfigFileDevice OBJECT-TYPE
               SYNTAX  INTEGER {
                    bootDevice   (1),
                    local        (2),
                    network      (3),
                    other        (4)
               }
               ACCESS  read-write
               STATUS  mandatory
               DESCRIPTION
                       "This specifies the device used to access the
                       configuration files needed by this system.  If
                       this object has the value bootDevice(1), the
                       system will look for its configuration files on
                       the same device as its boot files.  This device is
                       specified by a3sysUblDevice.  If this object has
                       the value network(3), the system will look for
                       its configuration files on the device specified
                       by a3sysUblConfigIpAddr.  If this object has the
                       value local(2), the system will look for its
                       configuration files on the local storage media.
                       If this object has the value other(4), nothing
                       has been specified.

                       In all the cases listed above, the path for the
                       configuration files is specified by
                       a3sysUblConfigFilePath."
               ::= { a3sysUserBootListEntry 8 }

           a3sysUblConfigFilePath OBJECT-TYPE
               SYNTAX  DisplayString
               ACCESS  read-write
               STATUS  mandatory
               DESCRIPTION
                       "This object specifies the path to the configuration
                       files needed by this system."
               ::= { a3sysUserBootListEntry 9 }

           a3sysUblConfigProt OBJECT-TYPE
               SYNTAX  INTEGER {
                    fap   (1),
                    ftp   (2),
                    other (3)
               }
               ACCESS  read-only
               STATUS  mandatory
               DESCRIPTION
                       "This object specifies the protocol to use
                       to get the configuration files if they
                       are stored across the network.  Note, this
                       applies only if the value of
                       a3sysUblConfigFileDevice is network(3) or
                       bootDevice(1).  If a3sysUblConfigFileDevice
                       has the value bootDevice(1), then the
                       corresponding instance of a3sysUblDevice
                       must be network(2) for this object to have relevance.

		       This object has been changed to read-only in
		       9.0.  The only valid value for this object is
		       ftp(2)."
               ::= { a3sysUserBootListEntry 10 }

           a3sysUblConfigUserName OBJECT-TYPE
               SYNTAX  DisplayString (SIZE(0..20))
               ACCESS  read-write
               STATUS  mandatory
               DESCRIPTION
                       "This object indicates the Username to be
                       used by the file service protocol identified
                       the corresponding instance of a3sysUblConfigProt."
               ::= { a3sysUserBootListEntry 11 }

           a3sysUblConfigPassword OBJECT-TYPE
               SYNTAX  DisplayString (SIZE(0..20))
               ACCESS  read-write
               STATUS  mandatory
               DESCRIPTION
                       "This specifies the Password to be used
                       by the file service protocol identified by
                       the corresponding instance of a3sysUblConfigProt.
                       Note, for reasons of security, the value of this
                       object will be hidden.  A string of 4 stars (*)
                       will be returned in response to any GET or GETNEXT
                       request."
               ::= { a3sysUserBootListEntry 12 }

           a3sysUblConfigAcct OBJECT-TYPE
               SYNTAX  DisplayString (SIZE(0..30))
               ACCESS  read-write
               STATUS  mandatory
               DESCRIPTION
                       "This specifies the Account Name used
                       by the file service protocol.
                       Note, for reasons of security, the value of this
                       object will be hidden.  A string of 4 stars (*)
                       will be returned in response to any GET or GETNEXT
                       request."
               ::= { a3sysUserBootListEntry 13 }

           a3sysUblMacAddress OBJECT-TYPE
               SYNTAX  INTEGER {
                    cpu-module (1),
                    io-module  (2),
                    other      (3)
               }
               ACCESS  read-write
               STATUS  mandatory
               DESCRIPTION
                       "The MAC address to be used for booting over the
                       network.  This can be configured to use either the
                       MAC address assigned to the CPU module or the MAC
                       address assigned to the I/O module over which the boot
                       is being performed."
               REFERENCE
                       "NBII CEC Module Installation Guide: System IP Addresses:
                       Boot MAC Address Parameter."
               ::= { a3sysUserBootListEntry 14 }

           a3sysUblCanonicalFlag OBJECT-TYPE
               SYNTAX  INTEGER {
                    other        (1),
                    canonical    (2),
                    nonCanonical (3)
               }
               ACCESS  read-write
               STATUS  mandatory
               DESCRIPTION
                       "This controls the format of addresses within
                       ARP packets sent by this system."
               ::= { a3sysUserBootListEntry 15 }

           a3sysUblRemoteProt OBJECT-TYPE
               SYNTAX  INTEGER {
                    notApplicable    (1),
                    ppp              (2),
                    frameRelay       (3),
                    auto             (4)
               }
               ACCESS  read-write
               STATUS  mandatory
               DESCRIPTION
                       "This object specifies which serial link
                       protocol to use if a3sysUblSlot identifies
                       a slot with a High Speed Serial board.
                       If this is set to auto (4), the system
                       will try all supported protocols until
                       the serial line is active.

                       If there is a different kind of board in that
                       slot, the value of this object is ignored."
               ::= { a3sysUserBootListEntry 16 }

           a3sysUblBaudRate OBJECT-TYPE
               SYNTAX  INTEGER {
                    unknown      (1),
                    bps9600      (2),
                    kbps19       (3),
                    kbps38       (4),
                    kbps56       (5),
                    kbps64       (6),
                    kbps128      (7),
                    kbps256      (8),
                    kbps448      (9),
                    kbps1536     (10),
                    kbps2048     (11),
                    mbps4        (12),
                    mbps16       (13)
               }
               ACCESS  read-write
               STATUS  mandatory
               DESCRIPTION
                       "This object specifies the serial line or
                       Token Ring baud rate.  For all other types
                       of ports, this object will be ignored."
               ::= { a3sysUserBootListEntry 17 }

           a3sysUblClockSource OBJECT-TYPE
               SYNTAX  INTEGER {
                    internal     (1),
                    external     (2),
                    unknown      (3)
               }
               ACCESS  read-write
               STATUS  mandatory
               DESCRIPTION
                       "This specifies whether to use an internal
                       or external clock source.  This applies only
                       to High Speed Serial ports."
               ::= { a3sysUserBootListEntry 18 }

           a3sysUblConnectorType OBJECT-TYPE
               SYNTAX  INTEGER {
                    unknown         (1),
                    rs232           (2),
                    v35             (3)
               }
               ACCESS  read-write
               STATUS  mandatory
               DESCRIPTION
                       "This object specifies the serial line
                       connector type."
               ::= { a3sysUserBootListEntry 19 }

           a3sysUblWanAddress OBJECT-TYPE
               SYNTAX  DisplayString (SIZE(0..80))
               ACCESS  read-write
               STATUS  mandatory
               DESCRIPTION
                       "This specifies a string to initiate a
                       WAN connection.  The specified string required
                       is interface and protocol specific.  The maximum
                       string length is 80 bytes.  Note, this applies
                       only to High Speed Serial ports."
               ::= { a3sysUserBootListEntry 20 }

           a3sysUblClientIpAddr OBJECT-TYPE
               SYNTAX  IpAddress
               ACCESS  read-write
               STATUS  mandatory
               DESCRIPTION
                       "The IP Address of this system used in packets
                       when booting over the network."
               REFERENCE
                       "NBII CEC Module Installation Guide: System IP Addresses:
                       Client IP address Parameter."
               ::= { a3sysUserBootListEntry 21 }

           a3sysUblServerIpAddr OBJECT-TYPE
               SYNTAX  IpAddress
               ACCESS  read-write
               STATUS  mandatory
               DESCRIPTION
                       "The IP address of the Boot Server."
               REFERENCE
                       "NBII CEC Module Installation Guide: System IP Addresses:
                       Server IP Address Parameter."
               ::= { a3sysUserBootListEntry 22 }

           a3sysUblGwIpAddr OBJECT-TYPE
               SYNTAX  IpAddress
               ACCESS  read-write
               STATUS  mandatory
               DESCRIPTION
                       "The IP address of the gateway that will forward
                       packets to the Boot Server."
               REFERENCE
                       "NBII CEC Module Installation Guide: System IP Addresses:
                       Gateway IP Address Parameter."
               ::= { a3sysUserBootListEntry 23 }

           a3sysUblConfigFileIpAddr OBJECT-TYPE
               SYNTAX  IpAddress
               ACCESS  read-write
               STATUS  mandatory
               DESCRIPTION
                       "The IP address of the configuration files Server,
                       if needed."
               REFERENCE
                       "NBII CEC Module Installation Guide: System IP Addresses:
                       FAP Server IP Address Parameter."
               ::= { a3sysUserBootListEntry 24 }

           a3sysUblIpMask OBJECT-TYPE
               SYNTAX  IpAddress
               ACCESS  read-write
               STATUS  mandatory
               DESCRIPTION
                       "The mask to be applied to the addresses specified
                       above."
               ::= { a3sysUserBootListEntry 25 }

           a3sysUblAddressDiscovery OBJECT-TYPE
               SYNTAX  INTEGER {
                    other      (1),
                    bootp      (2),
                    configAddr (3),
                    bootpRarp  (4),
                    rarp       (5),
                    rarpBootp  (6)
               }
               ACCESS  read-write
               STATUS  mandatory
               DESCRIPTION
                       "This specifies the address discovery protocol
                       to use for booting from the network.  If configAddr(3)
                       is specified, then the configured addresses are
                       used.  If nothing has been specified, other(1) is
                       returned."
               ::= { a3sysUserBootListEntry 26 }

           a3sysUblPassword OBJECT-TYPE
               SYNTAX  DisplayString (SIZE(0..5))
               ACCESS  read-write
               STATUS  mandatory
               DESCRIPTION
                       "This is needed when booting over a port that
                       uses a protocol that requires a password, e.g,
                       PPP."
               ::= { a3sysUserBootListEntry 27 }



--
-- The next table controls the booting of the Intelligent IO
-- Boards.  As of 8.0, IIO boards must boot from either
-- local storage or from the location where the config files
-- are stored (which may be from local storage).
--

           a3sysIioBootTable OBJECT-TYPE
               SYNTAX  SEQUENCE OF A3sysIioBootEntry
               ACCESS  not-accessible
               STATUS  mandatory
               DESCRIPTION
                       "This table specifies where each IIO card
                       obtains its boot image."
               ::= { a3ComBoot 10 }

           a3sysIioBootEntry OBJECT-TYPE
               SYNTAX  A3sysIioBootEntry
               ACCESS  not-accessible
               STATUS  mandatory
               DESCRIPTION
                       "Each entry in this table corresponds to a
                       specific slot in the NetBuilder chassis.  If
                       an IIO board is in that slot, that entry
                       determines where that IIO board obtains its
                       boot image."
               INDEX { a3sysIioBootSlot }
               ::= { a3sysIioBootTable 1 }

           A3sysIioBootEntry ::=
               SEQUENCE {
                   a3sysIioBootSlot        INTEGER,
                   a3sysIioBootFileName    DisplayString,
                   a3sysIioBootState       INTEGER,
                   a3sysIioBootTime        TimeTicks,
                   a3sysIioBootImage       OBJECT IDENTIFIER
               }


           a3sysIioBootSlot OBJECT-TYPE
               SYNTAX  INTEGER
               ACCESS  read-only
               STATUS  mandatory
               DESCRIPTION
                       "This object specifies the slot into which
                       the IIO board corresponding to this entry
                       is placed."
               ::= { a3sysIioBootEntry 1 }


           a3sysIioBootFileName OBJECT-TYPE
               SYNTAX  DisplayString
               ACCESS  read-write
               STATUS  mandatory
               DESCRIPTION
                       "This object specifies the path and name of the
                       IIO board's boot image.  If the value of
                       this object specifies a drive, the path is assumed
                       to start from root.  If the value of this object does
                       not specify a drive number, this object specifies the
                       path starting from the config file directory specified by
                       a3sysUblConfigFilePath.  In this case, the value of this
                       object must not begin with a slash '/'."
               ::= { a3sysIioBootEntry 2 }

           a3sysIioBootState OBJECT-TYPE
               SYNTAX  INTEGER {
                    empty        (1), -- card not available for use
                    up           (2), -- card is up and running
                    booting      (3), -- card is in the process of booting
                    recovering   (4), -- card is recovering from a failed boot
                    dumping      (5), -- while recovering, card is dumping image
                    halted       (6), -- card has halted after failed boot
                    selfTestFail (7), -- self test failed
                    error        (8)  -- card's in unrecoverable errored state
               }
               ACCESS  read-only
               STATUS  mandatory
               DESCRIPTION
                      "This object provides the current state of the IIO
                      card installed in this slot.  If there is no IIO
                      card in the slot, this object will have the value
                      empty(1).  If the card is up and running, this object
                      will have the value up(2).  If the card is booting,
                      this object will have the value booting(3).  If the
                      boot has failed, and the card is in the process of
                      recovering from the failed boot, this object will have
                      the value recovering(4).  If in the process of
                      recovering, the IIO dumps its image, this object will
                      have the value dumping(5).  Note that this is simply
                      a sub-state within the more general recovering state.
                      If after recovering, the IIO card goes into a halted
                      state, this object will have the value halted(6).  If
                      the IIO card gets into an unrecoverable state, this
                      object will have the value error(8)."
               ::= { a3sysIioBootEntry 3 }

           a3sysIioBootTime OBJECT-TYPE
               SYNTAX TimeTicks
               ACCESS read-only
               STATUS mandatory
               DESCRIPTION
                      "The value of sysUpTime when the IIO board last
                      went into the UP state."
               ::= { a3sysIioBootEntry 4 }

           a3sysIioBootImage OBJECT-TYPE
               SYNTAX OBJECT IDENTIFIER
               ACCESS read-only
               STATUS mandatory
               DESCRIPTION
                      "The OID assigned to this version of Iio Software."
               ::= { a3sysIioBootEntry 5 }

--
-- The Last Boot Group.  This group contains information about the
-- most recent boot of the system
--

           a3sysLastBootSource OBJECT-TYPE
               SYNTAX  INTEGER {
                    primary   (1),
                    secondary (2),
                    monitor   (3),
		    test      (4)
               }
               ACCESS  read-only
               STATUS  mandatory
               DESCRIPTION
                       "This object identifies the source from which the
                       system last booted.

                       The specifics of the boot source can be found
                       from the corresponding User Boot List entry."
               REFERENCE
                       "NBII CEC Module Installation Guide: User Boot List:
                       Boot Source Parameter."
               ::= { a3ComLastBoot 1 }

           a3sysLastBootError OBJECT-TYPE
               SYNTAX  INTEGER {
                    none                  (1), -- there have been no known
                                               -- failures
                    unknownLocalAddress   (2),
                    unknownServerAddress  (3),
                    noServerResponse      (4),
                    fileTransferFailed    (5),
                    imageNotFound         (6),
                    imageInvalid          (7)
               }
               ACCESS  read-only
               STATUS  mandatory
               DESCRIPTION
                       "This object identifies the reason for the
                       most recent boot failure."
               ::= { a3ComLastBoot 2 }

           a3sysLastBootDate OBJECT-TYPE
               SYNTAX  DisplayString
               ACCESS  read-only
               STATUS  mandatory
               DESCRIPTION
                      "The date and time as reflected by the system
                      clock at the time the system last rebooted.
                      The date has the format yy/mm/dd hh:mm[:ss]."
               ::= { a3ComLastBoot 3 }

           a3sysLbConfigFileIpAddr OBJECT-TYPE
               SYNTAX  IpAddress
               ACCESS  read-only
               STATUS  mandatory
               DESCRIPTION
                      "The IP address of the configuration file server
                      used during the most recent boot.  Note, even
                      if the configuration files were obtained locally,
                      an address may have been configured.  This is the
                      address used when performing all ftp PUT and GET
                      operations."
               ::= { a3ComLastBoot 4 }

           a3sysLbGwIpAddr OBJECT-TYPE
               SYNTAX  IpAddress
               ACCESS  read-only
               STATUS  mandatory
               DESCRIPTION
                      "The IP address of the gateway that was used to
                      forward packets to the boot server or configuration file
                      server during the last boot."
               ::= { a3ComLastBoot 5 }

           a3sysLbIpMask OBJECT-TYPE
               SYNTAX  IpAddress
               ACCESS  read-only
               STATUS  mandatory
               DESCRIPTION
                      "The IP subnet mask configured during the last boot."
               ::= { a3ComLastBoot 6 }

           a3sysLbConfigDevice OBJECT-TYPE
               SYNTAX  INTEGER {
                    bootDevice   (1),
                    local        (2),
                    network      (3),
                    other        (4)
               }
               ACCESS  read-only
               STATUS  mandatory
               DESCRIPTION
                      "The config file device used during the last boot."
               ::= { a3ComLastBoot 7 }

           a3sysLbConfigFilePath OBJECT-TYPE
               SYNTAX  DisplayString (SIZE(0..80))
               ACCESS  read-only
               STATUS  mandatory
               DESCRIPTION
                      "The config file path used during the last boot."
               ::= { a3ComLastBoot 8 }

           a3sysLbConfigUserName OBJECT-TYPE
               SYNTAX  DisplayString (SIZE(0..20))
               ACCESS  read-only
               STATUS  mandatory
               DESCRIPTION
                      "If the config files were obtained from a file server
                      during the last boot, this object contains the user
                      name used during the ftp transfer of those files."
               ::= { a3ComLastBoot 9 }


--
-- The File Management group
--

           a3sysFmOperation OBJECT-TYPE
               SYNTAX  INTEGER {
                    other       (1),
                    copy        (2),
                    do          (3),
                    delete      (4),
                    rename      (5),
                    directory   (6),
                    format      (7),
                    copySystem  (8),
                    checksum    (9),
                    abortCopy   (10),
                    makeDir     (11),
                    rmDir       (12),
                    getFileInfo (13),
                    ftpGet      (14),
                    ftpPut      (15),
		    cleanFlash  (16)
               }
               ACCESS  read-write
               STATUS  mandatory
               DESCRIPTION
                       "This object is used to initiate a file
                       management operation.  When set to copy(2), the
                       system will get the file from the Source device
                       (identified by a3sysFmSourceIpAddr and
                       a3sysFmSourceFile) and copy it to the
                       Target device (identified by a3sysFmTargetIpAddr
                       and a3sysFmTargetFile).  Note, both the
                       Source and Target devices cannot be
                       remote systems.  At least one must be
                       the local system.

                       All information about the file
                       and the server is taken from the values
                       of the other objects in this group.  To
                       avoid unnecessary errors, the relevant objects
                       in this group should be examined and
                       their values validated before setting this object
                       to copy(2).

                       Currently, the do(3) enumeration is not supported.

                       If this object is set to delete(4), the system
                       will delete a single file on the local storage
                       device.  The file is identified by a3sysFmTargetFile.

                       For software release 6.2, the rename(5) enumeration
                       is not supported.  This is supported, however, by
                       release 7.0.

                       If this object is directory(6), the system will list
                       the file in the directory identified by a3sysFmTargetFile.
                       The resulting list can be obtained by examining
                       a3sysDfTable.

                       For software release 6.2, enumerations 7 through 9
                       are not supported.  Enumeration 7 and 9 are supported
                       by release 7.0.

                       If this object is set to abortCopy(10), the
                       system will abort any file copy process in
                       progress.

                       If this object is set to makeDir(11), the system
                       will create a directory off the root directory. The
                       name of this directory is specified by a3sysFmTargetFile.

                       If this object is set to rmDir(12), the system will
                       remove the directory identified by a3sysFmTargetFile.

                       If this object is set to getFileInfo(13), the system
                       will retrieve information about the file identified
                       by a3sysFmTargetFile and return that information via
                       the a3ComFileInfo group.  (ie, examine the contents
                       of that group after this object is set to getFileInfo(13)).

                       If this object is set to ftpGet(14), the system
                       will retrieve the file identified by a3sysFmSourceFile.
                       It will retrieve the file from the device from
                       which the configuration files were originally obtained.
                       That device can be identified by
                       a3sysLbConfigFileIpAddr.  Note, even if the config
                       files were obtained locally, a valid IP address may
                       have been configured.  That is the device used for
                       future ftp operations.

                       If a path is not specified, the file will be taken
                       from the configuration file directory.  The config
                       file directory cay be identified by
                       a3sysLbConfigFilePath.  If a relative
                       path is specified, and the configuration files were
                       originally obtained (ie, at last boot) from the
                       network, the path is interpreted relative to the
                       configuration file directory.  If a relative path
                       is specified and the configuration files were originally
                       obtained locally, the path is interpreted relative
                       to the login directory.  Absolute paths are allowed.
                       Once obtained, the file will be placed in the location
                       identified by a3sysFmTargetFile.  Note, this must be
                       on one of the local storage devices.

                       If this object is set to ftpPut(15), the system
                       will place the file identified by a3sysFmSourceFile
                       and place it on the device from which the config
                       files were obtained originally.  The path and
                       filename of the placed file is identified by
                       a3sysFmTargetFile.  As with ftpGet(14), if a relative
                       path is specified, and the configuration files were
                       originally obtained from the network, the path is
                       interpreted relative to the configuration file
                       directory.  If a relative path is specified and the
                       configuration files were originally obtained locally,
                       the path is interpreted relative to the login
                       directory.  Absolut paths are allowed.  Note, the
                       source file must be on one of the local storage devices.

                       If this object is read, other(1) will be
                       returned."
               ::= { a3ComFileMgmt 1 }

           a3sysFmSourceIpAddr OBJECT-TYPE
               SYNTAX  IpAddress
               ACCESS  read-write
               STATUS  mandatory
               DESCRIPTION
                       "This object specifies the IP address of
                       the Source device from which files are
                       obtained.

                       If this is set to zero's, the local storage
                       device is assumed."
               ::= { a3ComFileMgmt 2 }

           a3sysFmSourceFile OBJECT-TYPE
               SYNTAX  DisplayString
               ACCESS  read-write
               STATUS  mandatory
               DESCRIPTION
                       "This specifies the path and name of
                       a source file.  For example, if the
                       action specified by a3sysFmOperation is
                       copy(2) or rename(5), this identifies the
                       path and name of the file to be copied or
                       renamed.

                       If there is no leading path string, the
                       source file will be accessed from the root
                       directory.  For devices with multiple disk
                       drives, the drive will be identified by appending
                       a prefix to the path.  For example, a:/path/name"
               ::= { a3ComFileMgmt 3 }

           a3sysFmTargetIpAddr OBJECT-TYPE
               SYNTAX  IpAddress
               ACCESS  read-write
               STATUS  mandatory
               DESCRIPTION
                       "This object specifies the IP address of
                       the target device to which files are
                       copied, renamed, etc."
               ::= { a3ComFileMgmt 4 }

           a3sysFmTargetFile OBJECT-TYPE
               SYNTAX  DisplayString
               ACCESS  read-write
               STATUS  mandatory
               DESCRIPTION
                       "This specifies the path and name of
                       the target file on the target system.
                       (The filename may contain the string '@M'
                       which will be expanded to the system MAC address.
                       Alternatively, the filename may contain
                       the string '@m'  which will be expanded to
                       the last six characters of the system MAC address.
                       This provides a mechanism for a remote system to
                       generate system specific filenames automatically.)
                       If there is no leading path string, the
                       file will be accessed from the root directory.
                       For devices with multiple disk drives, the drive
                       will be identified by appending a prefix to the path.
                       For example, a:/path/name.

                       If the action specified by a3sysFmOperation is copy(2),
                       this identifies where, on the target system (identified
                       by a3sysFmTargetIpAddr) the file is to be placed and the
                       name to give it.

                       If the action specified by a3sysFmOperation is
                       delete(4), this identifies the path and
                       name of the local file which is to be
                       deleted.

                       If the action specified by a3sysFmOperation is
                       directory(6), this identifies the full path
                       of the directory that is to be listed."
               ::= { a3ComFileMgmt 5 }

           a3sysFmStatus OBJECT-TYPE
               SYNTAX  INTEGER {
                    inactive   (1),
                    inProgress (2)
               }
               ACCESS  read-only
               STATUS  mandatory
               DESCRIPTION
                       "This identifies the current status
                       of the file management operation.  This applies
                       to the following operations: copy(2),
                       and directory(6).  If there
                       is an operation in progress, this object
                       will have the value inProgress(2).  Otherwise
                       inactive(1) will be returned."
               ::= { a3ComFileMgmt 6 }

           a3sysFmTimeStamp OBJECT-TYPE
               SYNTAX  TimeTicks
               ACCESS  read-only
               STATUS  mandatory
               DESCRIPTION
                       "This specifies the value of sysUpTime when
                       the most recent file management operation was
                       initiated."
               ::= { a3ComFileMgmt 7 }

           a3sysFmError OBJECT-TYPE
               SYNTAX  INTEGER {
                    none          (1), -- no operations since initialization
                    successful    (2), -- the most recent operation was
                                       -- successful
                    inProgress    (3), -- another operation was already in
                                       -- progress
                    badSourceAddr (4), -- the Source IP Address is invalid
                    badSourceFile (5), -- the Source file is invalid
                    badTargetAddr (6), -- the Target IP Address is invalid
                    badTargetFile (7), -- the Target file is invalid
                    noResponse    (8), -- no response from the server
                    noFile        (9), -- the file or dir. could not be found
                    noSpace       (10), -- no space on destination system
                    noPermission  (11), -- destination device is write protected
                    writeError    (12), -- error encountered when writing
                    timeout       (13), -- timeout during transfer
                    badChecksum   (14), -- invalid file checksum computed
                    badOperation  (15), -- invalid file operation
                    aborted       (16), -- operation aborted by user
                    other         (17), -- an error not listed here
                    badDefaultDrv (18), -- the Default Drive is not Local
		    badTargetPort (19)  -- the Target Udp/Tcp port is unreachable
               }
               ACCESS  read-only
               STATUS  mandatory
               DESCRIPTION
                      "This object identifies the results of the
                      most recent attempt at a file operation.  If no
                      file operations have been attempted since the
                      system was initialized, this object will have the
                      value none(1).

                      If the last operation was successful, this object
                      will have the value successful(2).

                      If the last operation could not be initiated
                      because there was another operation in progress,
                      this object will have the value inProgress (3).

                      If the source IP Address is invalid, this object
                      will have the value badSourceAddr(4).

                      If the source file name contains a syntax error,
                      this object will have the value badSourceFile(5).

                      If the target IP Address is invalid, this object
                      will have the value badTargetAddr(6).

                      If there was a syntax error in the identification
                      of the target file (a3sysFmTargetFile), this
                      object will have the value badTargetFile(7).

                      If the remote server does not respond, this
                      object will have the value noResponse(8).

                      If either the source file or target file could
                      not be found, this object will have the value
                      noFile(9).

                      If there is no space on the destination system
                      this object will have the value noSpace(10).

                      If the destination file location is write protected,
                      this object will have the value noPermission(11).

                      If there is an error encountered while
                      writing the file to its destination, this object
                      will have the value writeError(12).

                      If the transfer took too much time and exceeded
                      its limits, this object will have the value timeout(13).

                      If the verify operation failed, this object will have
                      the value badChecksum(14).

                      If the operation requested is not supported by this
                      platform or software version, this object will have
                      the value badOperation(15).

                      If the opereration was aborted by a user, this object
                      will have the value aborted(16).

                      If no drive is indicated in either the source or target
                      files, and the default drive is not local (this will be
                      the case when the system obtained its config files over
                      the network the last time it booted), this object will
                      have the value badDefaultDrv(18).

                      This object will have the value other(17) if an error
                      occured that is not listed here."
               ::= { a3ComFileMgmt 8 }

--
-- Disk File List Group
--
          a3sysDfTime OBJECT-TYPE
              SYNTAX TimeTicks
              ACCESS read-only
              STATUS mandatory
              DESCRIPTION
                     "This object specifies the value of sysUpTime when
                     the list of files on the system disk was last updated.
                     This list is updated by setting a3sysFmOperation to
                     directory(6)."
              ::= { a3ComFileList 1 }

          a3sysDfPath OBJECT-TYPE
              SYNTAX DisplayString
              ACCESS read-only
              STATUS mandatory
              DESCRIPTION
                     "This object identifies the directory path under which
                     the files listed in a3sysDfTable were obtained.  Where
                     necessary, this object also identifies the disk drive
                     where the files are stored."
              ::= { a3ComFileList 2 }

          a3sysDfTable OBJECT-TYPE
              SYNTAX SEQUENCE OF A3sysDfEntry
              ACCESS not-accessible
              STATUS mandatory
              DESCRIPTION
                     "This table contains a listing of all the files in a
                     specific directory on one of the systems disks.  The
                     directory and disk are identified by a3sysDfPath.
                     Each entry in this table contains information about
                     a single file."
              ::= { a3ComFileList 3 }

          a3sysDfEntry OBJECT-TYPE
              SYNTAX A3sysDfEntry
              ACCESS not-accessible
              STATUS mandatory
              DESCRIPTION
                     "Each entry in this table describes a single disk file."
              INDEX { a3sysDfName }
              ::= { a3sysDfTable 1 }

          A3sysDfEntry ::=
              SEQUENCE {
                 a3sysDfName      DisplayString,
                 a3sysDfDir       INTEGER
              }

          a3sysDfName OBJECT-TYPE
              SYNTAX DisplayString
              ACCESS read-only
              STATUS mandatory
              DESCRIPTION
                     "This contains the name of a single file on the disk."
              ::= { a3sysDfEntry 1 }

          a3sysDfDir OBJECT-TYPE
              SYNTAX INTEGER {
                   file      (1),
                   directory (2)
              }
              ACCESS read-only
              STATUS mandatory
              DESCRIPTION
                     "This specifies whether the file identified by the
                     corresponding instance of a3sysDfName is a regular
                     file or a directory."
              ::= { a3sysDfEntry 2 }

          a3ComDfTotalSpace OBJECT-TYPE
              SYNTAX INTEGER
              ACCESS read-only
              STATUS mandatory
              DESCRIPTION
                     "The total size (in bytes) of the drive identified by
                     a3sysDfPath"
              ::= { a3ComFileList 4 }

          a3ComDfAvailableSpace OBJECT-TYPE
              SYNTAX INTEGER
              ACCESS read-only
              STATUS mandatory
              DESCRIPTION
                     "The available space (in bytes) of the drive identified
                     by a3sysDfPath."
              ::= { a3ComFileList 5 }

--
-- FM Cksum Group
--
-- This group provides information related to the checksums associated with
-- files kept by the system
--

          a3sysFmCksum OBJECT-TYPE
              SYNTAX INTEGER
              ACCESS read-only
              STATUS mandatory
              DESCRIPTION
                     "This object specifies the results of a ccitt crc16
                     cyclic redundancy check performed on the file specified
                     by a3sysTargetFile.  The value of a3sysTargetFile at
                     the time this crc was performed is provided by a3sysFmCksumFile."
              ::= { a3ComFmCksum 1 }

          a3sysFmCksumFile OBJECT-TYPE
              SYNTAX DisplayString
              ACCESS read-only
              STATUS mandatory
              DESCRIPTION
                     "This object specifies the file upon which the last ccitt crc16
                     cyclic redundancy check was performed.  The results of this operation
                     are specified by a3sysFmCksum."
              ::= { a3ComFmCksum 2 }

          a3sysFmCksumTime OBJECT-TYPE
              SYNTAX TimeTicks
              ACCESS read-only
              STATUS mandatory
              DESCRIPTION
                     "This object specifies the value of sysUpTime when the last ccitt crc16
                     cyclic redundancy check was performed.  The results of this operation
                     are specified by a3sysFmCksum."
              ::= { a3ComFmCksum 3 }

--
-- FM General Info Group
--
-- This group provides general information related to a specific
-- file kept by the system.  In order to get infomation about
-- a specific file, set a3sysFmTargetFile to the desired file,
-- and set a3sysFmOperation to 13.  After a3sysFmStatus returns
-- to inactive, and assuming no errors have been encountered (check
-- the value of a3sysFmError, the objects in this group will provide
-- information about the desired file.
--

          a3sysFiName OBJECT-TYPE
              SYNTAX DisplayString
              ACCESS read-only
              STATUS mandatory
              DESCRIPTION
                     "This object specifies the name of the file to which
                     the rest of this group refers."
              ::= { a3ComFileInfo 1 }

          a3sysFiDate OBJECT-TYPE
              SYNTAX DisplayString
              ACCESS read-only
              STATUS mandatory
              DESCRIPTION
                     "This object specifies the date when the file (specified by
                     a3sysFiName was last updated.  The format of the date is
                     yy/mm/dd hh:min:sec."
              ::= { a3ComFileInfo 2 }

          a3sysFiTimeStamp OBJECT-TYPE
              SYNTAX TimeTicks
              ACCESS read-only
              STATUS mandatory
              DESCRIPTION
                     "This object specifies the value of sysUpTime when this group of
                     objects was last updated.  To update this group, set a3sysFmTargetFile
                     to the desired file, and set a3sysFmOperation to getFileInfo(13)."
              ::= { a3ComFileInfo 3 }

          a3sysFmSize OBJECT-TYPE
              SYNTAX INTEGER
              ACCESS read-only
              STATUS mandatory
              DESCRIPTION
                     "This object specifies the size of the file (specified by a3sysFiName)
                     in bytes."
              ::= { a3ComFileInfo 4 }


--
-- This next section specifies the behavior of this system in the event
-- of a crash.
--

--
-- The first table in this group specifies how this system recovers
-- if a specific IIO board or the CEC board crashes.
--

           a3sysIioRecoveryTable OBJECT-TYPE
               SYNTAX  SEQUENCE OF A3sysIioRecoveryEntry
               ACCESS  not-accessible
               STATUS  mandatory
               DESCRIPTION
                       "This table specifies the recovery procedure
                       for each Intelligent IO board in the system.
                       This also specifies the recovery procedure
                       for the CEC card.  Note, the eeprom version
                       must be 5 or greater for this table to operate
                       properly."
               ::= { a3ComRecovery 1 }

           a3sysIioRecoveryEntry OBJECT-TYPE
               SYNTAX  A3sysIioRecoveryEntry
               ACCESS  not-accessible
               STATUS  mandatory
               DESCRIPTION
                       "Each entry in this table corresponds to a
                       specific slot in the NetBuilder chassis.  If
                       an IIO board is in that slot, that entry
                       determines the action taken by that IIO
                       board in the event it crashes.  There is also
                       an entry in this table for the CEC board."
               INDEX { a3sysIioRecoverySlot }
               ::= { a3sysIioRecoveryTable 1 }

           A3sysIioRecoveryEntry ::=
               SEQUENCE {
                   a3sysIioRecoverySlot        INTEGER,
                   a3sysIioRecoveryProcedure  INTEGER,
                   a3sysIioRecoverySelect      INTEGER
               }


           a3sysIioRecoverySlot OBJECT-TYPE
               SYNTAX  INTEGER (0..8)
               ACCESS  read-only
               STATUS  mandatory
               DESCRIPTION
                       "This object specifies the slot into which
                       the IIO (or CEC) board corresponding to this
                       entry is placed."
               ::= { a3sysIioRecoveryEntry 1 }

           a3sysIioRecoveryProcedure OBJECT-TYPE
               SYNTAX  INTEGER {
                    halt                   (1),
                    haltSystem             (2),
                    reboot                 (3),
                    rebootSystem           (4),
                    dumpAndReboot          (5),
                    selectiveDumpAndReboot (6)
               }
               ACCESS  read-write
               STATUS  mandatory
               DESCRIPTION
                       "The value of this object determines the
                       action taken if the IIO (or CEC) crashes.
                       If the value of this object is
                       selectiveDumpAndReboot (5), the value of
                       a3sysIioRecoverySelect determines which
                       IIO (or CEC) boards will dump and reboot
                       in the event that this IIO board crashes."
               ::= { a3sysIioRecoveryEntry 2 }

           a3sysIioRecoverySelect OBJECT-TYPE
               SYNTAX  INTEGER
               ACCESS  read-write
               STATUS  mandatory
               DESCRIPTION
                       "This object specifies the IIO or CEC
                       boards that will dump and reboot in the event
                       this IIO or CEC board crashes.  This
                       object is relevant only if the value of
                       a3sysIioRecoveryProcedure is
                       selectiveDumpAndReboot (6).

                       The boards are specified by their slot.  Each
                       slot is represented by a single bit in the
                       value of this object.  If that bit is set (to
                       1), then that board will dump and reboot.

                       Slot 0 is used to identify the CEC board, and
                       corresponds to the least significant bit in
                       this object.

                       Slot 1 is used to identify the IIO board in
                       that slot and corresponds to the next
                       significant bit in this object.  The identification
                       of all other boards follows this convention."
               ::= { a3sysIioRecoveryEntry 3 }


--
-- Trap Defines
--
   a3BogusDhcpSvr       TRAP-TYPE
        ENTERPRISE      a3Com
        VARIABLES       { a3sysBogusDhcpSvr }
        DESCRIPTION     "A a3BogusDhcpSvr trap signifies that an unauthorized
                         DHCP or BOOTP server has been detected on the network."
        ::= 100


END
