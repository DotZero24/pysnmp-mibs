C-PRODUCT-QSIM-MIB DEFINITIONS ::= BEGIN


IMPORTS
    qsim                 FROM C-PRODUCT-GROUP-MIB
    cardSlot,
    portSlot,
    portNumber,
    vcpSideId FROM C-PRODUCT-BASE-MIB
    OBJECT-TYPE          FROM RFC-1212;

-- Data Types

-- Pin status for V.35 ports

PinStatus ::= INTEGER { off(1), on(2) }

--
-- MIB Groups
--

qsimCard         OBJECT IDENTIFIER ::= { qsim   1 }
qsimPort         OBJECT IDENTIFIER ::= { qsim   2 }
hsimPort         OBJECT IDENTIFIER ::= { qsim   3 }
-- The next  statement apply only for Lodi Rel1.4 only
qsimVc           OBJECT IDENTIFIER ::= { qsim   4 }
qsimLmi          OBJECT IDENTIFIER ::= { qsim   6 }
qsimNewVc        OBJECT IDENTIFIER ::= { qsim   9 }

-- The next 3 statements apply for Lodi Rel1.4 only
qsimSdlcVc       OBJECT IDENTIFIER ::= { qsimVc 1 }
qsimDxiVc        OBJECT IDENTIFIER ::= { qsimVc 2 }
qsimFrameRelayVc OBJECT IDENTIFIER ::= { qsimVc 3 }

-- The next 3 statements apply for Baja &Lodi Rel2.0 only
qsimNewSdlcVc       OBJECT IDENTIFIER ::= { qsimNewVc 1 }
qsimNewDxiVc        OBJECT IDENTIFIER ::= { qsimNewVc 2 }
qsimNewFrameRelayVc OBJECT IDENTIFIER ::= { qsimNewVc 3 }

--
-- Card Group (qsimCard)
--

qsimCardTable OBJECT-TYPE
    SYNTAX SEQUENCE OF QsimCardEntry
    ACCESS not-accessible
    STATUS mandatory
    DESCRIPTION
            "Card configuration table."
    ::= { qsimCard 1 }

qsimCardEntry OBJECT-TYPE
    SYNTAX QsimCardEntry
    ACCESS not-accessible
    STATUS mandatory
    DESCRIPTION
            "Card configuration entry."
    INDEX { cardSlot }
    ::= { qsimCardTable 1 }

QsimCardEntry ::=
    SEQUENCE {
        qsimCardMaxFrameSize
            INTEGER
    }

qsimCardMaxFrameSize OBJECT-TYPE
    SYNTAX INTEGER { mfs-2kb (1),
                     mfs-4kb (2),
                     mfs-8kb (3) }
    ACCESS read-write
    STATUS mandatory
    DESCRIPTION
            "Maximum frame size for SDLC, DXI and Frame Relay frames.
             WARNING: Change of the Maximum Frame Size will
                      cause Disruption of Service provided
                      by the card."
    DEFVAL { mfs-2kb }
    ::= { qsimCardEntry 1 }

--
-- QSIM-specific Port Group (qsimPortTable)
--

qsimPortTable OBJECT-TYPE
    SYNTAX SEQUENCE OF QsimPortEntry
    ACCESS not-accessible
    STATUS mandatory
    DESCRIPTION
            "QSIM port configuration table."
    ::= { qsimPort 1 }

qsimPortEntry OBJECT-TYPE
    SYNTAX QsimPortEntry
    ACCESS not-accessible
    STATUS mandatory
    DESCRIPTION
            "QSIM port configuration entry.  The slot number (portSlot)
             of this card can be from 4 to 6.  The port number (portNumber)
             can be from 1 to 4."
    INDEX { portSlot, portNumber }
    ::= { qsimPortTable 1 }

QsimPortEntry ::=
    SEQUENCE {
        qsimPortLinkType
            INTEGER,
        qsimPortCableType
            INTEGER,
        qsimPortTermTimingSource
            INTEGER,
        qsimPortReceiveTimingPhase
            INTEGER,
        qsimPortDataRate
            INTEGER,
        qsimPortMinFlagBytes
            INTEGER,
        qsimPortFcsSize
            INTEGER,
        qsimPortRts
            PinStatus,
        qsimPortCts
            PinStatus,
        qsimPortDcd
            PinStatus,
        qsimPortDsr
            PinStatus
    }

qsimPortLinkType OBJECT-TYPE
    SYNTAX INTEGER { dxi         (1),
                     sdlc        (2),
                     frame-relay (3) }
    ACCESS read-write
    STATUS mandatory
    DESCRIPTION
            "Link layer protocol supported by the port."
    DEFVAL { dxi }
    ::= { qsimPortEntry 1 }

qsimPortCableType OBJECT-TYPE
    SYNTAX INTEGER { none (1),  -- cable not detected
                     dte  (2),  -- dte cable is detected
                     dce  (3) } -- dce cable is detected
    ACCESS read-only
    STATUS mandatory
    DESCRIPTION
            "Type of cable connected to the port."
    ::= { qsimPortEntry 2 }

qsimPortTermTimingSource OBJECT-TYPE
    SYNTAX INTEGER { internal (1),
                     external (2) }
    ACCESS read-write
    STATUS mandatory
    DESCRIPTION
            "Terminal timing source.  This object applies ONLY
             when a DCE cable is connected to the port. If cable
             type is 'none' or 'dce', this object can be read
             and written.  If cable type is 'dte', a get request
             returns whatever value currently stored in the
             managed node for this port and a set request returns
             genErr."
    DEFVAL { internal }
    ::= { qsimPortEntry 3 }

qsimPortReceiveTimingPhase OBJECT-TYPE
    SYNTAX INTEGER { normal   (1),
                     inverted (2) }
    ACCESS read-write
    STATUS mandatory
    DESCRIPTION
            "Receive timing phase control.  This object applies ONLY
             when a DCE cable is connected to the port. If cable
             type is 'none' or 'dce', this object can be read and
             written.  If cable type is 'dte', a get request returns
             whatever value currently stored in the managed node for
             this port and a set request returns genErr."
    DEFVAL { normal }
    ::= { qsimPortEntry 4 }

qsimPortDataRate OBJECT-TYPE
    SYNTAX INTEGER { dr-64k  (1),
                     dr-128k (2),
                     dr-256k (3),
                     dr-512k (4),
                     dr-1m   (5),
                     dr-2m   (6),
                     dr-4m   (7),
                     dr-8m   (8) }
    ACCESS read-write
    STATUS mandatory
    DESCRIPTION
            "Data rate supported by the port."
    DEFVAL { dr-2m }
    ::= { qsimPortEntry 5 }

qsimPortMinFlagBytes OBJECT-TYPE
    SYNTAX INTEGER { fb-1 (1),  -- 1 flag byte
                     fb-2 (2) } -- 2 flag bytes
    ACCESS read-write
    STATUS mandatory
    DESCRIPTION
            "Minimum flag bytes required to distinguish a frame."
    DEFVAL { fb-1 }
    ::= { qsimPortEntry 6 }

qsimPortFcsSize OBJECT-TYPE
    SYNTAX INTEGER { fcs-2 (1),  -- 2-byte FCS field
                     fcs-4 (2) } -- 4-byte FCS field
    ACCESS read-write
    STATUS mandatory
    DESCRIPTION
            "Number of bytes in the FCS field of a frame."
    DEFVAL { fcs-2 }
    ::= { qsimPortEntry 7 }

qsimPortRts OBJECT-TYPE
    SYNTAX PinStatus
    ACCESS read-only
    STATUS mandatory
    DESCRIPTION
            "RTS pin status."
    ::= { qsimPortEntry 8 }

qsimPortCts OBJECT-TYPE
    SYNTAX PinStatus
    ACCESS read-only
    STATUS mandatory
    DESCRIPTION
            "CTS pin status."
    ::= { qsimPortEntry 9 }

qsimPortDcd OBJECT-TYPE
    SYNTAX PinStatus
    ACCESS read-only
    STATUS mandatory
    DESCRIPTION
            "DCD pin status."
    ::= { qsimPortEntry 10 }

qsimPortDsr OBJECT-TYPE
    SYNTAX PinStatus
    ACCESS read-only
    STATUS mandatory
    DESCRIPTION
            "DSR pin status."
    ::= { qsimPortEntry 11 }

--
-- HSIM-specific Port Group (hsimPortTable)
--

hsimPortTable OBJECT-TYPE
    SYNTAX SEQUENCE OF HsimPortEntry
    ACCESS not-accessible
    STATUS mandatory
    DESCRIPTION
            "HSIM port configuration table."
    ::= { hsimPort 1 }

hsimPortEntry OBJECT-TYPE
    SYNTAX HsimPortEntry
    ACCESS not-accessible
    STATUS mandatory
    DESCRIPTION
            "HSIM port configuration entry.  The slot number (portSlot)
             of this card can be from 4 to 6.  The port number (portNumber)
             of this card is always 1."
    INDEX { portSlot, portNumber }
    ::= { hsimPortTable 1 }

HsimPortEntry ::=
    SEQUENCE {
        hsimPortLinkType
            INTEGER,
        hsimPortDceDteMode
            INTEGER,
        hsimPortDataRate
            INTEGER,
        hsimPortMinFlagBytes
            INTEGER,
        hsimPortFcsSize
            INTEGER,
        hsimPortTa
            PinStatus,
        hsimPortCa
            PinStatus
    }

hsimPortLinkType OBJECT-TYPE
    SYNTAX INTEGER { dxi         (1),
                     sdlc        (2),
                     frame-relay (3) }
    ACCESS read-write
    STATUS mandatory
    DESCRIPTION
            "Link layer protocol supported by the port."
    DEFVAL { dxi }
    ::= { hsimPortEntry 1 }

hsimPortDceDteMode OBJECT-TYPE
    SYNTAX INTEGER { dce (1),
                     dte (2) }
    ACCESS read-write
    STATUS mandatory
    DESCRIPTION
            "DCE/DTE mode of the port."
    DEFVAL { dce }
    ::= { hsimPortEntry 2 }

hsimPortDataRate OBJECT-TYPE
    SYNTAX INTEGER { dr-20m  (1) }
    ACCESS read-only
    STATUS mandatory
    DESCRIPTION
            "Data rate supported by the port."
    ::= { hsimPortEntry 3 }

hsimPortMinFlagBytes OBJECT-TYPE
    SYNTAX INTEGER { fb-1 (1),  -- 1 flag byte
                     fb-2 (2) } -- 2 flag bytes
    ACCESS read-write
    STATUS mandatory
    DESCRIPTION
            "Minimum flag bytes required to distinguish a frame."
    DEFVAL { fb-1 }
    ::= { hsimPortEntry 4 }

hsimPortFcsSize OBJECT-TYPE
    SYNTAX INTEGER { fcs-2 (1),  -- 2-byte FCS field
                     fcs-4 (2) } -- 4-byte FCS field
    ACCESS read-write
    STATUS mandatory
    DESCRIPTION
            "Number of bytes in the FCS field of a frame."
    DEFVAL { fcs-2 }
    ::= { hsimPortEntry 5 }

hsimPortTa OBJECT-TYPE
    SYNTAX PinStatus
    ACCESS read-only
    STATUS mandatory
    DESCRIPTION
            "TA pin status."
    ::= { hsimPortEntry 6 }

hsimPortCa OBJECT-TYPE
    SYNTAX PinStatus
    ACCESS read-only
    STATUS mandatory
    DESCRIPTION
            "CA pin status."
    ::= { hsimPortEntry 7 }

-- This method is only used for Lodi 1.4 & is not applicable for
-- future releases as it will become obsolete.
-- SDLC VC Group (qsimSdlcVc)
-- DXI VC Group (qsimDxiVc)
-- Frame Relay VC Group (qsimFrameRelayVc)

--
-- LMI Group (qsimLmiTable)
--

qsimLmiTable OBJECT-TYPE
    SYNTAX SEQUENCE OF QsimLmiEntry
    ACCESS not-accessible
    STATUS mandatory
    DESCRIPTION
            "LMI configuration table."
    ::= { qsimLmi 1 }

qsimLmiEntry OBJECT-TYPE
    SYNTAX QsimLmiEntry
    ACCESS not-accessible
    STATUS mandatory
    DESCRIPTION
            "LMI configuration entry.  The slot number (portSlot)
             should be from 4 to 6.  The port number (portNumber)
             is from 1 to 4 for QSIM card, 1 to 8 for FAM card, and
             1 for HSIM card."
    INDEX { portSlot, portNumber }
    ::= { qsimLmiTable 1 }

QsimLmiEntry ::=
    SEQUENCE {
        qsimLmiProtocol
            INTEGER,
        qsimLmiProcedure
            INTEGER,
        qsimLmiUserT391
            INTEGER,
        qsimLmiUserN391
            INTEGER,
        qsimLmiUserN392
            INTEGER,
        qsimLmiUserN393
            INTEGER,
        qsimLmiNetworkT392
            INTEGER,
        qsimLmiNetworkN392
            INTEGER,
        qsimLmiNetworkN393
            INTEGER
    }

qsimLmiProtocol OBJECT-TYPE
    SYNTAX INTEGER { none    (1),
                     q-933a  (2),
                     t1-617d (3) }
    ACCESS read-write
    STATUS mandatory
    DESCRIPTION
            "LMI protocol supported by the port."
    DEFVAL { none }
    ::= { qsimLmiEntry 1 }

qsimLmiProcedure OBJECT-TYPE
    SYNTAX INTEGER { user-side     (1),
                     network-side  (2),
                     bidirectional (3) }
    ACCESS read-write
    STATUS mandatory
    DESCRIPTION
            "LMI procedure supported by the port.  This object applies
             when LMI Q.933 Annex A or T1.617 Annex D protocol is selected."
    DEFVAL { network-side }
    ::= { qsimLmiEntry 2 }

qsimLmiUserT391 OBJECT-TYPE
    SYNTAX INTEGER (5..180)
    ACCESS read-write
    STATUS mandatory
    DESCRIPTION
            "User-side link integrity verification (LIV) polling timer. This
             object applies when LMI user-side or bidirectional procedure
             is selected."
    DEFVAL { 10 }
    ::= { qsimLmiEntry 3 }

qsimLmiUserN391 OBJECT-TYPE
    SYNTAX INTEGER (1..255)
    ACCESS read-write
    STATUS mandatory
    DESCRIPTION
            "User-side full status polling counter.  This object applies
             when LMI user-side or bidirectional procedure is selected."
    DEFVAL { 6 }
    ::= { qsimLmiEntry 4 }

qsimLmiUserN392 OBJECT-TYPE
    SYNTAX INTEGER (1..10)
    ACCESS read-write
    STATUS mandatory
    DESCRIPTION
            "User-side error threshold.  This object applies when
             LMI user-side or bidirectional procedure is selected.
             User-side N392 should be less than or equal to user-
             side N393."
    DEFVAL { 3 }
    ::= { qsimLmiEntry 5 }

qsimLmiUserN393 OBJECT-TYPE
    SYNTAX INTEGER (1..10)
    ACCESS read-write
    STATUS mandatory
    DESCRIPTION
            "User-side monitored events count.  This object applies when
             LMI user-side or bidirectional procedure is selected."
    DEFVAL { 4 }
    ::= { qsimLmiEntry 6 }

qsimLmiNetworkT392 OBJECT-TYPE
    SYNTAX INTEGER (5..200)
    ACCESS read-write
    STATUS mandatory
    DESCRIPTION
            "Network-side polling verification timer.  This object applies
             when LMI network-side or bidirectional procedure is selected."
    DEFVAL { 15 }
    ::= { qsimLmiEntry 7 }

qsimLmiNetworkN392 OBJECT-TYPE
    SYNTAX INTEGER (1..10)
    ACCESS read-write
    STATUS mandatory
    DESCRIPTION
            "Network-side error threshold.  This object applies when
             LMI network-side or bidirectional procedure is selected.
             Network-side N392 should be less than or equal to Network-
             side N393."
    DEFVAL { 3 }
    ::= { qsimLmiEntry 8 }

qsimLmiNetworkN393 OBJECT-TYPE
    SYNTAX INTEGER (1..10)
    ACCESS read-write
    STATUS mandatory
    DESCRIPTION
            "Network-side monitored events count.  This object applies
             when LMI network-side or bidirectional procedure is selected."
    DEFVAL { 4 }
    ::= { qsimLmiEntry 9 }

-- New SDLC VC Group (qsimNewSdlcVc)
-- Is only aplicable for Baja & Lodi Release 2.0 onwards
-- This table is used to access the VC's on the ports whose link type is SDLC.
--

qsimNewSdlcVcTable OBJECT-TYPE
    SYNTAX SEQUENCE OF QsimNewSdlcVcEntry
    ACCESS not-accessible
    STATUS mandatory
    DESCRIPTION
            "SDLC VC configuration table."
    ::= { qsimNewSdlcVc 1 }

qsimNewSdlcVcEntry OBJECT-TYPE
    SYNTAX QsimNewSdlcVcEntry
    ACCESS not-accessible
    STATUS mandatory
    DESCRIPTION
            "SDLC VC configuration entry.  The slot number (vcPortSlot)
             of the VC can be from 4 to maxslots. The port number (vcPortPort)
             can be from 1 to 4."
    INDEX { vcpSideId }
    ::= { qsimNewSdlcVcTable 1 }

QsimNewSdlcVcEntry ::=
    SEQUENCE {
        qsimNewSdlcVcShapper
            INTEGER
    }

qsimNewSdlcVcShapper OBJECT-TYPE
    SYNTAX INTEGER (1..13)
    ACCESS read-write
    STATUS mandatory
    DESCRIPTION
            "Data rate supported by the SDLC VC.  Depending on the type
             of card a VC is configured, the shapper numbers are assigned
             as follows:

               HSIM              QSIM
             data rate         data rate     shapper number
             ---------         ---------     --------------
                1.5m              64k              1
                3m                128k             2
                4.5m              192k             3
                6m                256k             4
                7.5m              384k             5
                9m                512k             6
                10.5m             640k             7
                12m               768k             8
                13.5m             1m               9
                15m               1.5m             10
                16.5m             2m               11
                18m               4m               12
                20m               8m               13
            "
    ::= { qsimNewSdlcVcEntry 1 }

--
-- DXI VC Group (qsimNewDxiVc)
--
-- This table is used to access the VC's on the ports whose link type is DXI.
--

qsimNewDxiVcTable OBJECT-TYPE
    SYNTAX SEQUENCE OF QsimNewDxiVcEntry
    ACCESS not-accessible
    STATUS mandatory
    DESCRIPTION
            "DXI VC configuration table."
    ::= { qsimNewDxiVc 1 }

qsimNewDxiVcEntry OBJECT-TYPE
    SYNTAX QsimNewDxiVcEntry
    ACCESS not-accessible
    STATUS mandatory
    DESCRIPTION
            "DXI VC configuration entry.  The slot number (vcPortSlot)
             of the VC can be from 4 to 6. The port number (vcPortPort)
             can be from 1 to 4."
    INDEX { vcpSideId }
    ::= { qsimNewDxiVcTable 1 }

QsimNewDxiVcEntry ::=
    SEQUENCE {
        qsimNewDxiVcDfaVpi
            INTEGER,
        qsimNewDxiVcDfaVci
            INTEGER,
        qsimNewDxiVcDfaVciRange
            INTEGER,
        qsimNewDxiVcShapper
            INTEGER
    }

qsimNewDxiVcDfaVpi OBJECT-TYPE
    SYNTAX INTEGER (0..15)
    ACCESS read-write
    STATUS mandatory
    DESCRIPTION
            "DXI DFA VPI."
    ::= { qsimNewDxiVcEntry 1 }

qsimNewDxiVcDfaVci OBJECT-TYPE
    SYNTAX INTEGER (0..63)
    ACCESS read-write
    STATUS mandatory
    DESCRIPTION
            "DXI DFA VCI."
    ::= { qsimNewDxiVcEntry 2 }

qsimNewDxiVcDfaVciRange OBJECT-TYPE
    SYNTAX INTEGER (1..64)
    ACCESS read-write
    STATUS mandatory
    DESCRIPTION
            "DXI VCI range.  This object is used to create a set
             of VCs whose VPI equals to the value of the instance
             of qsimDxiVcDfaVpi and whose VCIs are in the range
             FROM 'the value of the instance of qsimDxiVcDfaVci'
             TO 'the value of the instance of this object PLUS the
             value of the instance of qsiDxiVcDfaVci MINUS 1'.  A
             successful set request will generate 1 to N VC entries
             in this table.  Where N equals to the value of the
             instance of this object.  A get request always returns
             1."
    DEFVAL { 1 }
    ::= { qsimNewDxiVcEntry 3 }

qsimNewDxiVcShapper OBJECT-TYPE
    SYNTAX INTEGER (1..13)
    ACCESS read-write
    STATUS mandatory
    DESCRIPTION
            "Data rate supported by the DXI VC.  Depending on the type
             of card a VC is configured, the shapper numbers are assigned
             as follows:

               HSIM              QSIM
             data rate         data rate     shapper number
             ---------         ---------     --------------
                1.5m              64k              1
                3m                128k             2
                4.5m              192k             3
                6m                256k             4
                7.5m              384k             5
                9m                512k             6
                10.5m             640k             7
                12m               768k             8
                13.5m             1m               9
                15m               1.5m             10
                16.5m             2m               11
                18m               4m               12
                20m               8m               13
            "
    ::= { qsimNewDxiVcEntry 4 }

--
-- Frame Relay VC Group (qsimNewFrameRelayVc)
--
-- This table is used to access the VC's on the ports whose link type is
-- frame relay.
--

qsimNewFrameRelayVcTable OBJECT-TYPE
    SYNTAX SEQUENCE OF QsimNewFrameRelayVcEntry
    ACCESS not-accessible
    STATUS mandatory
    DESCRIPTION
            "Frame relay VC configuration table."
    ::= { qsimNewFrameRelayVc 1 }

qsimNewFrameRelayVcEntry OBJECT-TYPE
    SYNTAX QsimNewFrameRelayVcEntry
    ACCESS not-accessible
    STATUS mandatory
    DESCRIPTION
            "Frame relay VC configuration entry.  The slot number
             (vcPortSlot) of the VC can be from 4 to maxslots. The port
             number (vcPortPort) can be from 1 to 4."
    INDEX { vcpSideId }
    ::= { qsimNewFrameRelayVcTable 1 }

QsimNewFrameRelayVcEntry ::=
    SEQUENCE {
        qsimNewFrameRelayVcInterworking
            INTEGER,
        qsimNewFrameRelayVcEncapsulation
            INTEGER,
        qsimNewFrameRelayVcDe2Clp
            INTEGER,
        qsimNewFrameRelayVcClp2De
            INTEGER,
        qsimNewFrameRelayVcFecnToEfci
            INTEGER,
        qsimNewFrameRelayVcShapper
            INTEGER,
        qsimNewFrameRelayVcDlci
            INTEGER,
        qsimNewFrameRelayVcFrSscsDlci
            INTEGER,
        qsimNewFrameRelayVcStatus
            INTEGER
    }

qsimNewFrameRelayVcInterworking OBJECT-TYPE
    SYNTAX INTEGER { network (1),  -- network interworking
                     service (2) } -- service interworking
    ACCESS read-write
    STATUS mandatory
    DESCRIPTION
            "Frame Relay/ATM interworking mode."
    ::= { qsimNewFrameRelayVcEntry 1 }

qsimNewFrameRelayVcEncapsulation OBJECT-TYPE
    SYNTAX INTEGER { transparent (1),
                     translation (2) }
    ACCESS read-write
    STATUS mandatory
    DESCRIPTION
            "Encapsulation type.  This object applies ONLY to service
             interworking."
    ::= { qsimNewFrameRelayVcEntry 2 }

qsimNewFrameRelayVcDe2Clp OBJECT-TYPE
    SYNTAX INTEGER { direct   (1),
                     always-0 (2),
                     always-1 (3) }
    ACCESS read-write
    STATUS mandatory
    DESCRIPTION
            "If mode 1 mapping is desirable, the user shall select
             direct mapping.  If mode 2 mapping is desirable, the
             user shall select always-0 or always-1 to map the CLP
             field to a constant value (0 or 1)."
    ::= { qsimNewFrameRelayVcEntry 3 }

qsimNewFrameRelayVcClp2De OBJECT-TYPE
    SYNTAX INTEGER { none     (1),
                     direct   (2),
                     always-0 (3),
                     always-1 (4) }
    ACCESS read-write
    STATUS mandatory
    DESCRIPTION
            "For network interworking -

             The options are none and direct.  If mode 1 mapping
             is desirable, the user shall select direct mapping.
             If mode 2 mapping is desirable, the user shall select
             none.  The none option maps the DE field in FR-SSCS
             PDU to the core-Q.922 frame DE field and ignores the
             CLP field in the ATM cells.

             For service interworking -

             The options are direct, always-0 and always-1.  If mode
             1 mapping is desirable, the user shall select direct
             mapping.  If mode 2 mapping is desirable, the user shall
             select always-0 or always-1 to map the DE field to a
             constant value (0 or 1)."
    ::= { qsimNewFrameRelayVcEntry 4 }

qsimNewFrameRelayVcFecnToEfci OBJECT-TYPE
    SYNTAX INTEGER { direct   (1),
                     always-0 (2) }
    ACCESS read-write
    STATUS mandatory
    DESCRIPTION
            "This object applies ONLY to service interworking.  If
             mode 1 mapping is desirable, direct mapping should be
             selected.  If mode 2 mapping is desirable, always-0
             should be selected to set the EFCI field to 'congestion
             not experienced'."
    ::= { qsimNewFrameRelayVcEntry 5 }

qsimNewFrameRelayVcShapper OBJECT-TYPE
    SYNTAX INTEGER (1..13)
    ACCESS read-write
    STATUS mandatory
    DESCRIPTION
            "Data rate supported by the frame relay VC.  Depending on the type
             of card a VC is configured, the shapper numbers are assigned
             as follows:

               HSIM              QSIM
             data rate         data rate     shapper number
             ---------         ---------     --------------
                1.5m              64k              1
                3m                128k             2
                4.5m              192k             3
                6m                256k             4
                7.5m              384k             5
                9m                512k             6
                10.5m             640k             7
                12m               768k             8
                13.5m             1m               9
                15m               1.5m             10
                16.5m             2m               11
                18m               4m               12
                20m               8m               13
            "
    ::= { qsimNewFrameRelayVcEntry 6 }

qsimNewFrameRelayVcDlci OBJECT-TYPE
    SYNTAX INTEGER (16..991)
    ACCESS read-write
    STATUS mandatory
    DESCRIPTION
            "Frame relay DLCI."
    ::= { qsimNewFrameRelayVcEntry 7 }

qsimNewFrameRelayVcFrSscsDlci OBJECT-TYPE
    SYNTAX INTEGER
    ACCESS read-write
    STATUS mandatory
    DESCRIPTION
            "This object applies ONLY to network interworking.
             Its valid value is 16..991 and 1022."
    ::= { qsimNewFrameRelayVcEntry 8 }

qsimNewFrameRelayVcStatus OBJECT-TYPE
    SYNTAX INTEGER { out-of-service (1),
                     in-service     (2),
                     not-configured (3) }
    ACCESS read-only
    STATUS mandatory
    DESCRIPTION
            "Frame relay PVC operational status."
    ::= { qsimNewFrameRelayVcEntry 9 }


END
