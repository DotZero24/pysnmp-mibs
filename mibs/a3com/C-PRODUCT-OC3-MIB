C-PRODUCT-OC3-MIB DEFINITIONS ::= BEGIN


IMPORTS
    oc3card                           FROM C-PRODUCT-GROUP-MIB
    portSlot, portNumber, TimeAndDate FROM C-PRODUCT-BASE-MIB
    Counter                           FROM RFC1155-SMI
    DisplayString                     FROM RFC1213-MIB
    OBJECT-TYPE                       FROM RFC-1212;

-- OC3 groups

oc3Port           OBJECT IDENTIFIER ::= { oc3card 1 }
oc3PortStats      OBJECT IDENTIFIER ::= { oc3card 2 }
oc3PortResetStats OBJECT IDENTIFIER ::= { oc3card 3 }

-- OC3 Port Group (oc3Port)

oc3PortTable OBJECT-TYPE
    SYNTAX SEQUENCE OF Oc3PortEntry
    ACCESS not-accessible
    STATUS mandatory
    DESCRIPTION
            "The OC3 port information table."
    ::= { oc3Port 1 }

oc3PortEntry OBJECT-TYPE
    SYNTAX Oc3PortEntry
    ACCESS not-accessible
    STATUS mandatory
    DESCRIPTION
            "Information about a OC3 port."
    INDEX { portSlot, portNumber }
    ::= { oc3PortTable 1 }

Oc3PortEntry ::=
    SEQUENCE {
        oc3PortLoopbackType
            INTEGER,
        oc3PortPeakRate
            INTEGER,
        oc3PortScramble
            INTEGER,
        oc3PortTiming
            INTEGER,
        oc3PortSonetMode
            INTEGER,
        oc3PortXmtCktId
            DisplayString,
        oc3PortRcvCktId
            DisplayString
    }

oc3PortLoopbackType OBJECT-TYPE
    SYNTAX INTEGER { none        (1), -- no loopback
                     networkLine (2),
                     localCard   (3)}
    ACCESS read-write
    STATUS mandatory
    DESCRIPTION
            "Loopback type of the OC3 port."
    DEFVAL { none }
    ::= { oc3PortEntry 1 }

oc3PortPeakRate OBJECT-TYPE
    SYNTAX INTEGER (1..155)
    ACCESS read-write
    STATUS mandatory
    DESCRIPTION
            "Peak data transfer rate of the OC3 port.  Unit: Mbps.
	    This field doesn't apply AB9100/AB9300 devices."
    ::= { oc3PortEntry 2 }

oc3PortScramble OBJECT-TYPE
    SYNTAX INTEGER { no(1),
                     yes(2) }
    ACCESS read-write
    STATUS mandatory
    DESCRIPTION
            "ATM payload scrambling for the OC3 port."
    DEFVAL { yes }
    ::= { oc3PortEntry 3 }

oc3PortTiming OBJECT-TYPE
    SYNTAX INTEGER { loop(1),
                     system(2) }
    ACCESS read-write
    STATUS mandatory
    DESCRIPTION
            "OC3 timing source."
    DEFVAL { system }
    ::= { oc3PortEntry 4 }

oc3PortSonetMode OBJECT-TYPE
    SYNTAX INTEGER { oc3(1),
                     stm1(2) }
    ACCESS read-write
    STATUS mandatory
    DESCRIPTION
            "Sonet mode of operation, either OC3 or STM1"
    DEFVAL { oc3 }
    ::= { oc3PortEntry 5 }

oc3PortXmtCktId OBJECT-TYPE
    SYNTAX DisplayString
    ACCESS read-write
    STATUS mandatory
    DESCRIPTION
            "This is the string to be inserted in the J1 bytes of the sonet stream.
             It is the path trace buffer string being sent to the far end.
	     This field doesn't apply AB9100/AB9300 device. "
    ::= { oc3PortEntry 6 }

oc3PortRcvCktId OBJECT-TYPE
    SYNTAX DisplayString
    ACCESS read-only
    STATUS mandatory
    DESCRIPTION
            "This is the string being received in the J1 bytes of the sonet stream.
             It is the path trace buffer string coming from the far end.
	     This field doesn't apply AB9100/AB9300 device. "
    ::= { oc3PortEntry 7 }


-- OC3 Port Stats Group (oc3PortStats)


oc3PortStatsTable OBJECT-TYPE
    SYNTAX SEQUENCE OF Oc3PortStatsEntry
    ACCESS not-accessible
    STATUS mandatory
    DESCRIPTION
            "The OC3 port information table."
    ::= { oc3PortStats 1 }

oc3PortStatsEntry OBJECT-TYPE
    SYNTAX Oc3PortStatsEntry
    ACCESS not-accessible
    STATUS mandatory
    DESCRIPTION
            "Information about a OC3 port."
    INDEX { portSlot, portNumber }
    ::= { oc3PortStatsTable 1 }

Oc3PortStatsEntry ::=
    SEQUENCE {
        oc3PortRxCells
            Counter,
        oc3PortTxCells
            Counter,
        oc3PortCorrectedHCSErrorCells
            Counter,
        oc3PortUncorrectedHCSErrorCells
            Counter,
        oc3PortResetTimeDate
            TimeAndDate
    }

oc3PortRxCells OBJECT-TYPE
    SYNTAX  Counter
    ACCESS  read-only
    STATUS  mandatory
    DESCRIPTION
            "The counter associated with the received cells, encountered
            on the ATM interface."
    ::= { oc3PortStatsEntry 1 }

oc3PortTxCells OBJECT-TYPE
    SYNTAX  Counter
    ACCESS  read-only
    STATUS  mandatory
    DESCRIPTION
            "The counter associated with the transmitted cells, encountered
            on the ATM interface."
    ::= { oc3PortStatsEntry 2 }

oc3PortCorrectedHCSErrorCells OBJECT-TYPE
    SYNTAX  Counter
    ACCESS  read-only
    STATUS  mandatory
    DESCRIPTION
            "The counter associated with the HCS errored cells whose errors were
            correctable, encountered on the ATM interface."
    ::= { oc3PortStatsEntry 3 }

oc3PortUncorrectedHCSErrorCells OBJECT-TYPE
    SYNTAX  Counter
    ACCESS  read-only
    STATUS  mandatory
    DESCRIPTION
            "The counter associated with the HCS errored cells whose errors were
            uncorrectable, encountered on the ATM interface."
    ::= { oc3PortStatsEntry 4 }

oc3PortResetTimeDate OBJECT-TYPE
    SYNTAX  TimeAndDate
    ACCESS  read-only
    STATUS  mandatory
    DESCRIPTION
            "The reset time and date of ATM stats on this ATM interface."
    ::= { oc3PortStatsEntry 5 }


-- OC3 Port Reset Stats Group (oc3PortResetStats)

oc3PortResetAtmStats OBJECT-TYPE
    SYNTAX  INTEGER { reset (1) }
    ACCESS  read-write
    STATUS  mandatory
    DESCRIPTION
            "This field is used to reset the atm statistics for the oc3 port.
             If a get is performed on this command, the result will always be zero"
    ::= { oc3PortResetStats 1 }


END
