C-PRODUCT-CBR-V35-MIB DEFINITIONS ::= BEGIN

IMPORTS
   cbr			FROM C-PRODUCT-GROUP-MIB
   portSlot,
   portNumber		FROM C-PRODUCT-BASE-MIB
   OBJECT-TYPE		FROM RFC-1212;

-- Data Types

-- CBR groups

cbrV35PortConfig	OBJECT IDENTIFIER ::= {cbr 5}

-- CBR V.35 Port Configuration Group (cbrV35PortConfig)

cbrV35PortConfTable OBJECT-TYPE
    SYNTAX SEQUENCE OF CbrV35PortEntry
    ACCESS not-accessible
    STATUS mandatory
    DESCRIPTION
	"This object contains the CBR's V.35 specific port Configuration table.
	There is one cbrV35PortConfEntry associated for each provisioned
	CBR port interface within the shelf.  This table uses portSlot and
	portNumber as an index which is defined in the portBaseTable of the
	C-PRODUCT BASE MIB. This index value uniquely identifies the CBR port
	interface to which this entry is applicable."
    ::= {cbrV35PortConfig 1}

cbrV35PortConfEntry OBJECT-TYPE
    SYNTAX CbrV35PortEntry
    ACCESS not-accessible
    STATUS mandatory
    DESCRIPTION
	    "An entry in the CBR specific port Configuration table."
    INDEX { portSlot, portNumber }
    ::= { cbrV35PortConfTable 1 }

CbrV35PortEntry ::=
    SEQUENCE {
	cbrV35PortConfCableType
	    INTEGER,
	cbrV35PortConfScrClockSource
	    INTEGER,
	cbrV35PortConfTxClockPhase
	    INTEGER,
	cbrV35PortConfRts
	    INTEGER,
	cbrV35PortConfCts
	    INTEGER,
	cbrV35PortConfDcd
	    INTEGER,
	cbrV35PortConfDsr
	    INTEGER,
	cbrV35PortConfSctClockSource
	    INTEGER,
	cbrV35PortConfRxTimingSource
	    INTEGER,
	cbrV35PortConfCableID
	    INTEGER,
	cbrV35PortConfLoopBackType
	    INTEGER
    }

cbrV35PortConfCableType OBJECT-TYPE
    SYNTAX INTEGER {
	       none (1), -- cable not detected
	       dte (2),	 -- dte cable detected
	       dce (3)	 -- dce cable detected
	   }
    ACCESS read-only
    STATUS mandatory
    DESCRIPTION
	"This object indicates the type of cable connected to the port.
	An error is returned if an access is attempted on
	a physical interface other than a V.35 port interface.  The default
	value is none (1)."
    DEFVAL { none }
    ::= {cbrV35PortConfEntry 1}

cbrV35PortConfScrClockSource OBJECT-TYPE
    SYNTAX INTEGER {
	       internal (1),
               adaptive (2)
	   }
    ACCESS read-write
    STATUS mandatory
    DESCRIPTION
	"This object indicates the SCR clock source.  This is
	aplicable for both DCE & DTE cable types.
	If the cable type is 'none', a get request returns
	whatever the value currently stored in the managed node for this
	port and a set request stores the value."
    ::= {cbrV35PortConfEntry 2}

cbrV35PortConfTxClockPhase OBJECT-TYPE
    SYNTAX INTEGER {
	       normal (1),
	       inverted (2)
	   }
    ACCESS read-write
    STATUS mandatory
    DESCRIPTION
	"This object indicates the type of Transmit clock phase needed to
	correct the clock out of phase problem.  This is aplicable ONLY when
	a 'dte' cable is connected to the port.
	The default value is normal (1)."

    DEFVAL { normal }
    ::= { cbrV35PortConfEntry 3 }

cbrV35PortConfRts OBJECT-TYPE
    SYNTAX INTEGER {
	       off (1),
	       on (2)
	   }
    ACCESS read-only
    STATUS mandatory
    DESCRIPTION
	"This object indicates RTS pin status.   Default value is off (1)."
    DEFVAL { off }
    ::= { cbrV35PortConfEntry 4 }

cbrV35PortConfCts OBJECT-TYPE
    SYNTAX INTEGER {
	       off (1),
	       on (2)
	   }
    ACCESS read-only
    STATUS mandatory
    DESCRIPTION
	"This object indicates CTS pin status.   Default value is off (1)."
    DEFVAL { off }
    ::= { cbrV35PortConfEntry 5 }

cbrV35PortConfDcd OBJECT-TYPE
    SYNTAX INTEGER {
	       off (1),
	       on (2)
	   }
    ACCESS read-only
    STATUS mandatory
    DESCRIPTION
	"This object indicates DCD pin status.   Default value is off (1)."
    DEFVAL { off }
    ::= { cbrV35PortConfEntry 6 }

cbrV35PortConfDsr OBJECT-TYPE
    SYNTAX INTEGER {
	       off (1),
	       on (2)
	   }
    ACCESS read-only
    STATUS mandatory
    DESCRIPTION
	"This object indicates DSR pin status.   Default value is off (1)."
    DEFVAL { off }
    ::= { cbrV35PortConfEntry 7 }

cbrV35PortConfSctClockSource OBJECT-TYPE
    SYNTAX INTEGER {
               recovered(1),
               internal (2)
           }
    ACCESS read-write
    STATUS mandatory
    DESCRIPTION
        "This object indicates the type of SCT clock source.  This is
	aplicable for both 'DCE' & 'DTE' cable types.  If no cable
	is attached then it just reflects the value stored in the database.
        The default value is internal (2)."
    DEFVAL { internal }

    ::= { cbrV35PortConfEntry 8 }

cbrV35PortConfRxTimingSource OBJECT-TYPE
    SYNTAX INTEGER {
	       echo-clock-from-dte (1),
	       dce-transmit-clock (2)
	   }
    ACCESS read-write
    STATUS mandatory
    DESCRIPTION
	"This object indicates the Serial interface Recieive Timing Source.
	The default value is dce-transmit-clock."
    DEFVAL { dce-transmit-clock }
    ::= { cbrV35PortConfEntry 9 }

cbrV35PortConfCableID OBJECT-TYPE
    SYNTAX INTEGER {
	       none (1),
	       v35 (2),
	       rs422 (3)
	   }
    ACCESS read-only
    STATUS mandatory
    DESCRIPTION
	"This object indicates the type of physical interface."
    DEFVAL { v35 }
    ::= { cbrV35PortConfEntry 10 }

cbrV35PortConfLoopBackType OBJECT-TYPE
    SYNTAX INTEGER {
               no-loopback(1),
               local-card(3),
               network-card(4),
               no-response(5)
           }
    ACCESS read-write
    STATUS mandatory
    DESCRIPTION
        "This object indicates the type of loopback configured for the
        specified T1/E1 port interface. Network-line (2) redirects incoming
        remote traffic back into the network interface at the external edge of
        the card interface. Network-card (4) regenerates framing information
        prior to redirecting incoming remote traffic back into the network
        interface.  Local-card (3) redirects local incoming traffic back into
        the local system.  The default value is no-loopback (1)."
    DEFVAL { no-loopback }
    ::= { cbrV35PortConfEntry 11 }

END
