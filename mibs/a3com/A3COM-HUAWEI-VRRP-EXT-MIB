-- =========================================================================
-- Copyright (C) 2001,2002 by  HUAWEI TECHNOLOGIES. All rights reserved.
--
-- Description: This file describes various common MIB objects implemented
-- by both Routers and Switches.
-- Reference: VRRP-MIB
-- Version: V1.0
-- History:
--      V1.0 2004-12-09
--        Initial version
-- =========================================================================
A3COM-HUAWEI-VRRP-EXT-MIB DEFINITIONS ::= BEGIN

 IMPORTS
     MODULE-IDENTITY, OBJECT-TYPE, Integer32
         FROM SNMPv2-SMI

     RowStatus
         FROM SNMPv2-TC

     ifIndex
         FROM IF-MIB

     vrrpOperVrId
         FROM VRRP-MIB

     h3cCommon
         FROM A3COM-HUAWEI-OID-MIB;


 h3cVrrpExt MODULE-IDENTITY
     LAST-UPDATED
         "200412090000Z"
     ORGANIZATION
         "Huawei-3Com Technologies Co.,Ltd."
     CONTACT-INFO
         "Huawei-3Com Technologies Co.,Ltd.
         Shang-Di Information Industry Base,
         Hai-Dian District Beijing P.R. China
         Zip:100085
         Http://www.huawei-3com.com"
     DESCRIPTION
         "This MIB describes objects used for managing Virtual Router
         Redundancy Protocol (VRRP) routers."
     ::= { h3cCommon 24 }


-- ===================================================================
--  Start of MIB objects
-- ===================================================================

 h3cVrrpExtMibObject      OBJECT IDENTIFIER ::= { h3cVrrpExt 1 }

-- ===================================================================
--  VRRP EXT Table
-- ===================================================================

 h3cVrrpExtTable OBJECT-TYPE
     SYNTAX       SEQUENCE OF H3cVrrpExtEntry
     MAX-ACCESS   not-accessible
     STATUS       current
     DESCRIPTION
         "Table extends for a VRRP router which consists of a
         sequence (i.e., one or more conceptual rows) of
         h3cVrrpExtEntry items."
     ::= { h3cVrrpExtMibObject 1 }

 h3cVrrpExtEntry OBJECT-TYPE
     SYNTAX       H3cVrrpExtEntry
     MAX-ACCESS   not-accessible
     STATUS       current
     DESCRIPTION
         "An entry in the h3cVrrpExtTable containing the status
         values of a virtual router."
     INDEX    { ifIndex, vrrpOperVrId, h3cVrrpExtTrackInterface }
     ::= { h3cVrrpExtTable 1 }

 H3cVrrpExtEntry ::=
     SEQUENCE {
         h3cVrrpExtTrackInterface
             INTEGER,
         h3cVrrpExtPriorityReduce
             Integer32,
         h3cVrrpExtRowStatus
             RowStatus
 }

 h3cVrrpExtTrackInterface OBJECT-TYPE
     SYNTAX INTEGER (0..2147483647)
     MAX-ACCESS not-accessible
     STATUS current
     DESCRIPTION
         "This value is the ifIndex that identifies which interface
         the virtual router tracked."
     ::= { h3cVrrpExtEntry 1 }

 h3cVrrpExtPriorityReduce  OBJECT-TYPE
     SYNTAX       Integer32 (1..255)
     MAX-ACCESS   read-create
     STATUS       current
     DESCRIPTION
         "This value identifies how much priority of a virtual router
         will be reduced/increased when the interface tracked is down/up."
     DEFVAL { 10 }
     ::= { h3cVrrpExtEntry 2 }

 h3cVrrpExtRowStatus OBJECT-TYPE
     SYNTAX       RowStatus
     MAX-ACCESS   read-create
     STATUS       current
     DESCRIPTION
         "The row status variable, used according to installation
         and removal conventions for conceptual rows. Setting this
         object to active(1) or createAndGo(4) results in the
         addition of the ifIndex tracked by a virtual router.
         Destroying the entry removes the tracked ifIndex from the
         virtual router. Other values is not supported now."
     ::= { h3cVrrpExtEntry 3 }

END
