-- ============================================================================
-- Copyright (C) 2009 by H3C Technologies. All rights reserved.
--
-- Description: There are three standard MIB definitions, "LLDP-MIB", "LLDP-EXT-
--     DOT1-MIB", "LLDP-EXT-DOT3-MIB", define almost all MIB objects of LLDP.
--     This document defines more MIB objects privately For LLDP implementation.
--      1)LLDP default global status is disabled, a management object needed to
--        enable it.
--      2)LLDP needs to be compliable with CDP (Non standard IEEE link layer di-
--        scovery protocol). A management object needed to enable or disable co-
--        mpliance.
--      3)For compliance with CDP, port based control management object is need-
--        ed.
--
-- Reference:
-- Version: V1.0
-- History:
-- V1.0 created by qizhenglin 2009-03-20
-- ============================================================================
A3COM-HUAWEI-LLDP-EXT-MIB DEFINITIONS ::= BEGIN

IMPORTS
    MODULE-IDENTITY, OBJECT-TYPE, Integer32, Counter32
        FROM SNMPv2-SMI
    TruthValue
        FROM SNMPv2-TC
    h3cCommon
        FROM  A3COM-HUAWEI-OID-MIB
    LldpPortNumber
        FROM LLDP-MIB;

h3clldp MODULE-IDENTITY
    LAST-UPDATED "200903210000Z"
    ORGANIZATION
       "Hangzhou H3C Tech. Co., Ltd."
    CONTACT-INFO
        "Platform Team H3C Technologies Co.,Ltd.
        Hai-Dian District Beijing P.R. China
        http://www.h3c.com
        Zip:100085
        "
    DESCRIPTION
        "LLDP extended management infomation."
    REVISION  "200903210000Z"
    DESCRIPTION ""
    ::= { h3cCommon 100 }

h3clldpObjects                    OBJECT IDENTIFIER ::= { h3clldp 1 }

--
-- LLDP extended MIB Objects
--
h3clldpConfiguration              OBJECT IDENTIFIER ::= { h3clldpObjects 1 }

--
-- LLDP extended global configuration
--
h3clldpAdminStatus OBJECT-TYPE
    SYNTAX TruthValue
    MAX-ACCESS  read-write
    STATUS      current
    DESCRIPTION
        "The global administratively desired status of the local LLDP agent."
    ::= { h3clldpConfiguration 1 }

h3clldpComplianceCDPStatus OBJECT-TYPE
    SYNTAX TruthValue
    MAX-ACCESS  read-write
    STATUS      current
    DESCRIPTION
        "The global administratively desired status of CDP Compliance."
    ::= { h3clldpConfiguration 2 }

--
-- h3clldpPortConfigTable: LLDP configuration on a per port basis
--

h3clldpPortConfigTable   OBJECT-TYPE
    SYNTAX      SEQUENCE OF H3clldpPortConfigEntry
    MAX-ACCESS  not-accessible
    STATUS      current
    DESCRIPTION
        "The port-based table that controls extended functions."
    ::= { h3clldpConfiguration 3 }

h3clldpPortConfigEntry   OBJECT-TYPE
    SYNTAX      H3clldpPortConfigEntry
    MAX-ACCESS  not-accessible
    STATUS      current
    DESCRIPTION
        "LLDP extended configuration information for a particular port. This co-
        nfiguration parameter controls compliance with other non-standard link
        layer discovery protocol such as CDP."
    INDEX  { h3clldpPortConfigPortNum }
    ::= { h3clldpPortConfigTable 1 }

H3clldpPortConfigEntry ::= SEQUENCE {
    h3clldpPortConfigPortNum         LldpPortNumber,
    h3clldpPortConfigCDPComplianceStatus        INTEGER }

h3clldpPortConfigPortNum   OBJECT-TYPE
    SYNTAX      LldpPortNumber
    MAX-ACCESS  not-accessible
    STATUS      current
    DESCRIPTION
        "The index value used to identify the port component associated with th-
         is entry."
    ::= { h3clldpPortConfigEntry 1 }

h3clldpPortConfigCDPComplianceStatus  OBJECT-TYPE
    SYNTAX INTEGER {
       txAndRx(1),
       disabled(2)
    }
    MAX-ACCESS read-write
    STATUS     current
    DESCRIPTION
        "The administratively desired CDP Compliance status of the local LLDP a-
        gent. If the associated h3clldpPortConfigCDPComplianceStatus object has
        a value of 'txAndRx', then the LLDP agent will receive CDP frames on th-
        is port, and will transmit CDP frames only after receive a CDP frames.
        If the associated lldpPortConfigAdminStatus object has a value of 'disa-
        bled', LLDP agent will not transmit or receive CDP frames on this port."
   DEFVAL  { disabled }
   ::= { h3clldpPortConfigEntry 2 }

END
