--
-- SNMP MIB for 3Com Audit Log Service
--
-- This SNMP MIB defines 3Com Audit Log service parameters
--

        A3COM-AUDL-r1-MIB DEFINITIONS ::= BEGIN

        IMPORTS
              	enterprises, IpAddress
                  FROM RFC1155-SMI
          	OBJECT-TYPE
                  FROM RFC-1212;

	a3Com		OBJECT IDENTIFIER ::= { enterprises 43 }
	brouterMIB	OBJECT IDENTIFIER ::= { a3Com 2 }
	a3ComAuditLog	OBJECT IDENTIFIER ::= { brouterMIB 29 }
	a3ComAudlControl	OBJECT IDENTIFIER ::= { a3ComAuditLog 1 }
	a3ComAudlConfig		OBJECT IDENTIFIER ::= { a3ComAuditLog 2 }

--
--	CONTrol Categories
--

	a3ComAudlControlAuditTrail	OBJECT-TYPE
	    SYNTAX INTEGER {
                auditTrail 	(1),
		noAuditTrail	(2)
	    }
            ACCESS  read-write
            STATUS  mandatory
            DESCRIPTION
                "This parameter enables/disables the log message AuditTrail
		category which logs the AuditTrail messages. A default
		value of 2 means no AuditTrail."
	    DEFVAL{ noAuditTrail }
	    ::= { a3ComAudlControl 1 }

	a3ComAudlControlConfig 		OBJECT-TYPE
            SYNTAX INTEGER {
		config		(1),
		noConfig	(2)
	    }
	    ACCESS  read-write
            STATUS  mandatory
            DESCRIPTION
                "This parameter enables/disables the log message COnfig
		category which logs the SET/SETD/ADD/DELETE commands and
		other commands such as SysPassWord, SU, Login, Listen etc.
		The default value of 2 means no COnfig."
	    DEFVAL { noConfig }
	    ::= { a3ComAudlControl 2 }

	a3ComAudlControlMessages 	OBJECT-TYPE
            SYNTAX INTEGER {
		messages	(1),
		noMessages	(2)
	    }
	    ACCESS  read-write
            STATUS  mandatory
            DESCRIPTION
                "This parameter enables/disables the log message MEssages
		category which log System Message and Dial History. The
		default value of 2 means no MEssages."
	    DEFVAL { noMessages }
	    ::= { a3ComAudlControl 3 }

	a3ComAudlControlSecurity 	OBJECT-TYPE
	    SYNTAX INTEGER {
		 security	(1),
		 noSecurity	(2)
	    }
	    ACCESS  read-write
            STATUS  mandatory
            DESCRIPTION
                "This parameter enables/disables the log message SEcurity
		category which logs faulted set privilege, failed login and
		invalid community string. The default 2 means no SEcurity."
	    DEFVAL { noSecurity }
	    ::= { a3ComAudlControl 4 }

--
--	Configurations
--
--
--	LogServerAddr
--

        a3ComAudlLogServerAddr OBJECT-TYPE
	    SYNTAX IpAddress
	    ACCESS  read-write
            STATUS  mandatory
            DESCRIPTION
                "This is the IP address of a log server which has syslog
		daemon active with proper syslog configuration."
	    ::= { a3ComAudlConfig 1 }

--
--	PriorityLevel
--

	a3ComAudlPriorityLevel OBJECT-TYPE
            SYNTAX INTEGER {
		log-EMERG	(1),
		log-ALERT	(2),
		log-CRITICAL	(3),
		log-ERROR	(4),
		log-WARNING	(5),
		log-NOTICE 	(6),
		log-INFO	(7),
		log-DEBUG	(8)
	    }
	    ACCESS  read-write
            STATUS  mandatory
            DESCRIPTION
                "The level is used with facility to format a priority
		which used as a tag in log message before sending it
		to syslog daemon. It also controls the log sending
		operation, a log message with higher Level will be
		be sent together with what has been in Audit Log
		buffer, to a LogServerAddr immediately."
	    DEFVAL { log-INFO }
	    ::= { a3ComAudlConfig 2 }

--
--	MaxLog
--

	a3ComAudlMaxLog OBJECT-TYPE
            SYNTAX INTEGER (1..30)
	    ACCESS  read-write
            STATUS  mandatory
            DESCRIPTION
                "It decides the maximum number of log commands/messages
		could accumulate in Audit Log buffer before sending to
		a LogServerAddr. Value 1 means send each log without
		buffering."
	    DEFVAL { 10 }
	    ::= { a3ComAudlConfig 3 }

--
--	IdleTime
--

	a3ComAudlIdleTime OBJECT-TYPE
            SYNTAX INTEGER (0..480)
	    ACCESS  read-write
            STATUS  mandatory
            DESCRIPTION
                "This controls the idle time in minute till sending
		Audit log buffer if it has data. Value of 0 means
		this idle time is disabled."
	    DEFVAL { 5 }
	    ::= { a3ComAudlConfig 4 }

END
