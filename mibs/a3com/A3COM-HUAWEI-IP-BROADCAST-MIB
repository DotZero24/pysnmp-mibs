-- =================================================================
-- Copyright (C) 2002 by HUAWEI-3COM TECHNOLOGIES.  All rights reserved.
--
-- Description: ip broadcast mib
-- Reference:huawei-3com enterprise mib
-- Version: V1.0
-- History:
--   V1.0 Created by Gao Long and Zhou Xin
--     Initial version 2004-12-13
-- =================================================================
A3COM-HUAWEI-IP-BROADCAST-MIB DEFINITIONS ::= BEGIN

	IMPORTS
		h3cCommon
			FROM A3COM-HUAWEI-OID-MIB
		Integer32, Unsigned32, OBJECT-TYPE, MODULE-IDENTITY, NOTIFICATION-TYPE
			FROM SNMPv2-SMI;

		h3cIpBroadcast MODULE-IDENTITY
		LAST-UPDATED "200412131936Z"		-- December 13, 2004 at 19:36 GMT
		ORGANIZATION
			"Huawei 3Com Technologies Co., Ltd."
		CONTACT-INFO
			"Platform Team Huawei 3Com Technologies Co., Ltd.
			Hai-Dian District Beijing P.R. China
			http://www.huawei-3com.com
			Zip:100085
			"
		DESCRIPTION
			"This MIB is objects used to describe IP broadcast features or
			functions.

			Some objects in this may be used only for some specific products,
			so users should refer to the related documents to acquire more
			detail information.
			"
		REVISION "200412131936Z"		-- December 13, 2004 at 19:36 GMT
		DESCRIPTION
			"The initial revision of this MIB module."
		::= { h3cCommon 33 }


--
-- Node definitions
--

-- Scalar MIB objects, which are considered as global variables
-- in a device, are defined in this section.
	h3cIpBdstScalarGroup OBJECT IDENTIFIER ::= { h3cIpBroadcast 1 }

	h3cIpBdstForwardBroadcast OBJECT-TYPE
	SYNTAX	INTEGER
		{
			forwarding(1),    -- forwarding direct broadcast
			notForwarding(2)  -- not forwarding direct broadcast
		}
	MAX-ACCESS	read-write
	STATUS	current
	DESCRIPTION	"This object indicates whether a device forwards direct
			broadcast datagrams or not.
			More details of this object, please refers to RFC2644.
			"
	::= { h3cIpBdstScalarGroup 1 }

	h3cIpReceiveBroadcast OBJECT-TYPE
	SYNTAX	INTEGER
		{
			receive(1),    -- receiving direct broadcast
			notReceive(2)  -- not receiving direct broadcast
		}
	MAX-ACCESS	read-write
	STATUS	current
	DESCRIPTION	"This objects indicates whether a device receives direct
			broadcast datagrams or not.
			More details of this object, please refers to RFC2644.
			"
	::= { h3cIpBdstScalarGroup 2 }


-- =================================================================
-- All other groups are defined below. Of course, scalar objects can
-- also be defined in a sub section, but they must be one part of
-- that sub section.
-- Note that a scalar group should be defined firstly and all
-- scalar objects are placed under that group when doing so.
	h3cIpBdstGroup OBJECT IDENTIFIER ::= { h3cIpBroadcast 2 }


-- =================================================================
-- Traps are defined below.
	h3cIpBdstTrap OBJECT IDENTIFIER ::= { h3cIpBroadcast 3 }

-- All traps should be placed under this object.
	h3cIpBdstTrapPrex OBJECT IDENTIFIER ::= { h3cIpBdstTrap 0 }


END
