-- ======================================================================
--
--  3Com Switching Systems Web Server Management Information Base
--  Version 1.0.0
--  May 7, 1998

--  3Com Corporation
--  80 Central Street
--  Boxborough, MA 01719
--  (978) 264-1400
--
--  Change History:
--  Oct 22, 1998 - dfa      Adding Mibs to switchingSystems for Imports.
--  Oct  7. 1998 - tmeiczin  formatted, fixed syntax errors
--  May  8, 1998 - gute      edits from first review.
--
--   Revision 1.0.0 Initially created by Flavio Fernandes
--
-- ======================================================================

   A3COM-SWITCHING-SYSTEMS-WEBSERVER-MIB DEFINITIONS ::= BEGIN

   IMPORTS
        enterprises
                FROM RFC1155-SMI
        OBJECT-TYPE
                FROM RFC-1212
        DisplayString
                FROM RFC1213-MIB;

a3Com                               OBJECT IDENTIFIER ::= { enterprises 43 }
switchingSystemsMibs                OBJECT IDENTIFIER ::= { a3Com 29 }
a3ComSwitchingSystemsMib            OBJECT IDENTIFIER ::= { switchingSystemsMibs 4 }

   -- Structure of MIB
   --
   -- The objects are arranged into the following groups:
   --
   -- 3Com switchingSystems-Mib switchingSystemsMib a3ComPolicyGroup

a3ComWebConfig                      OBJECT IDENTIFIER ::= { a3ComSwitchingSystemsMib 24 }

   -- The 3COM Switching Web Server Interface Table
   --
   -- This table is implemented by the 3Com network devices that support
   -- built in web server.

a3ComWebConfigHelpServer  OBJECT-TYPE
    SYNTAX  DisplayString (SIZE(0..85))
    ACCESS  read-write
    STATUS  mandatory
    DESCRIPTION
            "The server's URL where help pages are taken from upon http
            requests.
            Example:   http://0.0.0.0/3Com/help"
::= { a3ComWebConfig 1 }

a3ComWebConfigEmailServerAddress  OBJECT-TYPE
    SYNTAX  DisplayString (SIZE(0..85))
    ACCESS  read-write
    STATUS  mandatory
    DESCRIPTION
            "The mail server that you want the system to use for mailing
            status changes to the addresses specified under
            a3ComWebConfigEmailAddresses. This object may be an ip address
            or a machine's name assuming the managed device has client DNS
            capabilities."
::= { a3ComWebConfig 2 }

a3ComWebConfigEmailAddresses  OBJECT-TYPE
    SYNTAX  DisplayString (SIZE(0..255))
    ACCESS  read-write
    STATUS  mandatory
    DESCRIPTION
            "The email addresses to which you wish to mail status changes,
            adding a semicolon after each address, including cases where
            only one address is specified."
::= { a3ComWebConfig 3 }

END
