--	3Com Switching Systems Filter Management Information Base
--	Version 1.0.0
--	February 13, 1998

--	3Com Corporation
--	80 Central Street
--	Boxborough, MA 01719
--	(508) 264-1400

----------------------------------------------------------------------------------------
--
--  08/12/98 - tmeiczin Fixed syntax to compiled with SMICng
--                      Changed a3ComFilterAddressGroupId in the Address Table
--      	        to a3ComFilterAddressId to avoid a duplicate name
--  02/13/98 - iwolf    Originally created
--
----------------------------------------------------------------------------------------

A3COM-SWITCHING-SYSTEMS-FILTER-MIB DEFINITIONS ::= BEGIN

     	IMPORTS
          	enterprises
	       		FROM RFC1155-SMI
          	OBJECT-TYPE
              	        FROM RFC-1212
          	DisplayString,PhysAddress
			FROM RFC1213-MIB;

-- The Following was removed to allow compiling with SunNet Manager
--                RowStatus
--                        FROM SNMPv2-TC;

		RowStatus ::= INTEGER {

                -- the following two values are states:
                -- these values may be read or written
                active(1),
                notInService(2),

                -- the following value is a state:
                -- this value may be read, but not written
                notReady(3),

                -- the following three values are
                -- actions: these values may be written,
                --   but are never read
                createAndGo(4),
                createAndWait(5),
                destroy(6)
                }

		-- Object identifiers

a3Com                               OBJECT IDENTIFIER ::= { enterprises 43 }
switchingSystemsMibs                OBJECT IDENTIFIER ::= { a3Com 29 }
a3ComSwitchingSystemsMib            OBJECT IDENTIFIER ::= { switchingSystemsMibs 4 }
a3ComFilterGroup                    OBJECT IDENTIFIER ::= { a3ComSwitchingSystemsMib 20 }

	--
     	-- Filter Groups
     	--

a3ComFilterAddressGroup             OBJECT IDENTIFIER ::= { a3ComFilterGroup 1 }
a3ComFilterPortGroup                OBJECT IDENTIFIER ::= { a3ComFilterGroup 2 }
a3ComBridgeFilterGroup              OBJECT IDENTIFIER ::= { a3ComFilterGroup 3 }


     	--
     	-- STRUCTURE OF THE FILTER MIB BY TABLE
     	--
     	-- a3ComFilterAddressGroupTable
     	--
     	-- INDEX { a3ComFilterAddressGroupId }
     	--
     	--   The a3ComFilterAddressGroupTable allows address group creation and
 	--   naming; and storage at designated bridge(s).  Up to 32 address
 	--   groups can be created in a bridge.  Each address group in a bridge
	--   has an unique a3ComFilterAddressGroupMaskId, its value range from 1 to 32.
	--
     	-- a3ComFilterAddressTable
     	--
     	-- INDEX { a3ComFilterAddressId, a3ComFilterAddressAddress }
     	--
     	--   The a3ComFilterAddressTable allows for the specification of addresses and
     	--   assignment to address groups defined in a3ComFilterAddressGroupTable.
     	--
--  OBJECT-TYPE
     	--
     	-- INDEX { a3ComFilterPortGroupId }
     	--
     	--    The a3ComFilterPortGroupTable allows port group creation and naming;
     	--    and storage at the designated bridge. A maximum number of 32 port
	--    groups can be created in a bridge.  Each port group has an unique
	--    a3ComFilterPortGroupMaskId in the bridge.
     	--
     	-- a3ComFilterPortTable
     	--
     	-- INDEX { a3ComFilterPortId, a3ComFilterPortType, a3ComFilterPortPort }
     	--
     	--    The a3ComFilterPortTable allows for the specification of ports and the
     	--    assignment to port groups previously defined in the
     	--    a3ComFilterPortGroupTable.
     	--
     	-- a3ComBridgeFilterTable
     	--
     	-- INDEX { a3ComBridgeFilterId, a3ComBridgeFilterBridgeNumber }
     	--
     	--    Creation of bridge filter programs can be performed
     	--    by:
     	--        1.  Using the built-in editor of the AdminConsole.
     	--
     	--        2.  Using your own line editor on an external host
     	--            and then transferring the filter program via the
     	--            AdminConsole.
     	--
     	--        3.  Using the filter program creation tool on an
     	--            external host, which builds the filter program and
     	--            then transfers it to the LANPlex using SNMP.  The
     	--            transfer is done using the file transfer MIB defined
     	--            elsewhere in the LANPlex system MIB."
     	--
     	--    Regardless of the method used to create the bridge filter program,
     	--    the a3ComBridgeFilterTable lists the stored bridge filter programs
     	--    by bridge.  Additionally, this table can be used to:
     	--
     	--        1.  Add or delete a bridge filter programs to or from bridge(s)
     	--        2.  Temporarily disable a bridge filter program
     	--        3.  Retrieve a bridge filter name or program
     	--
     	-- a3ComPortFilterTable
     	--
     	-- INDEX  { a3ComBridgeFilterId, a3ComBridgeFilterBridgeNumber,
	--	    a3ComBridgeFilterBridgePortType, a3ComBridgeFilterBridgePortPort }
     	--
     	--    a3ComPortFilterTable is used to assign and unassign bridge filter
	--    program to or from bridge port(s) and processing path(s) of
	--    a bridge.
     	--

       A3ComFilterPortType ::= INTEGER (1..5)
        --	portEthernet(1),
	--	portFDDI(2),
	--	portTokenRing(3),
	--	port100Ethernet(4),
	--	portLEC(5)

 	--
     	-- Index Of next available address group
     	--

a3ComFilterAddressGroupNextAvailableIndex  OBJECT-TYPE
    SYNTAX  INTEGER
    ACCESS  read-only
    STATUS  mandatory
    DESCRIPTION
            "The value of next available a3ComFilterAddressGroupId.
            This object is used for index value to create a new
            address group."
::= { a3ComFilterAddressGroup 1 }

	--
     	-- Count Of Defined Address Groups
     	--

a3ComFilterAddressGroupCount  OBJECT-TYPE
    SYNTAX  INTEGER
    ACCESS  read-only
    STATUS  mandatory
    DESCRIPTION
            "The count of defined address groups."
::= { a3ComFilterAddressGroup 2 }

     	--
     	-- The LANPlex Address Group Table
     	--

a3ComFilterAddressGroupTable  OBJECT-TYPE
    SYNTAX  SEQUENCE OF A3ComFilterAddressGroupEntry
    ACCESS  not-accessible
    STATUS  mandatory
    DESCRIPTION
            "A list of address group entries.  A single
            entry exists in this list for each defined
            address group in the system."
::= { a3ComFilterAddressGroup 3 }

a3ComFilterAddressGroupEntry  OBJECT-TYPE
    SYNTAX  A3ComFilterAddressGroupEntry
    ACCESS  not-accessible
    STATUS  mandatory
    DESCRIPTION
            "An individual address group entry."
    INDEX  { a3ComFilterAddressGroupId }
::= { a3ComFilterAddressGroupTable 1 }

A3ComFilterAddressGroupEntry ::=
    SEQUENCE {
		a3ComFilterAddressGroupId	INTEGER,
     		a3ComFilterAddressGroupMaskId 	INTEGER,
     		a3ComFilterAddressGroupBridgeMask OCTET STRING,
     		a3ComFilterAddressGroupName	DisplayString,
     		a3ComFilterAddressGroupStatus 	RowStatus
    }

a3ComFilterAddressGroupId  OBJECT-TYPE
    SYNTAX  INTEGER (1..65535)
    ACCESS  read-only
    STATUS  mandatory
    DESCRIPTION
            "This object uniquely identifies an address group in the
            systems. Its value, successively increases starting from 0,
            will change only if the system is rebooted.  This object is
            obtained from a3ComFilterAddressGroupNextAvailableIndex
            when a new address group is created."
::= { a3ComFilterAddressGroupEntry 1 }

a3ComFilterAddressGroupMaskId  OBJECT-TYPE
    SYNTAX  INTEGER
    ACCESS  read-write
    STATUS  mandatory
    DESCRIPTION
            "This object identifies an address group in a bridge. Each
            address group has an unique mask identifier, range from 1 to 32,
            associated with it in a bridge. This field has to be set in
            order to create a new address group in the desired bridge(s)."
::= { a3ComFilterAddressGroupEntry 2 }

a3ComFilterAddressGroupBridgeMask  OBJECT-TYPE
    SYNTAX  OCTET STRING (SIZE (4))
    ACCESS  read-write
    STATUS  mandatory
    DESCRIPTION
            "A mask that uniquely identifies the bridge value(s)
            associated with this address group entry. For example,
            0x0000 0000 0000 0003 represents the address group entry in
            bridge number 1 and 2."
::= { a3ComFilterAddressGroupEntry 3 }

a3ComFilterAddressGroupName  OBJECT-TYPE
    SYNTAX  DisplayString (SIZE (0..31))
    ACCESS  read-write
    STATUS  mandatory
    DESCRIPTION
            "The name of an address group. Each address group
            has an unique name in a system."
::= { a3ComFilterAddressGroupEntry 4 }

a3ComFilterAddressGroupStatus  OBJECT-TYPE
    SYNTAX  RowStatus
    ACCESS  read-write
    STATUS  mandatory
    DESCRIPTION
            "The status column for this address group entry.  This OBJECT
            can be set to:
            createAndGo(4)
            destroy(6)

            The following values may be read:
            active(1)

            Setting this object to createAndGo(4) will result in the agent attempt
            to create and commit the row based on the contents of the objects in
            the row. If all the necessary information is presented in the row and the
            values are acceptible to the agent, the agent will change the status to
            active(1).  If there are any necessary objects are not set, the agent will
            reject the creation request.


            Setting this object to destroy(6) will delete the corresponding
            address group and all the attributes of the table."
::= { a3ComFilterAddressGroupEntry 5 }

     	--
     	-- The LANPlex Address Table
     	--

a3ComFilterAddressTable  OBJECT-TYPE
    SYNTAX  SEQUENCE OF A3ComFilterAddressEntry
    ACCESS  not-accessible
    STATUS  mandatory
    DESCRIPTION
            "A list of address entries."
::= { a3ComFilterAddressGroup 4 }

a3ComFilterAddressEntry  OBJECT-TYPE
    SYNTAX  A3ComFilterAddressEntry
    ACCESS  not-accessible
    STATUS  mandatory
    DESCRIPTION
            "A set of parameters for a particular address entry."
    INDEX  { a3ComFilterAddressId, a3ComFilterAddressAddress }
::= { a3ComFilterAddressTable 1 }

A3ComFilterAddressEntry ::=
    SEQUENCE {
     		a3ComFilterAddressId	         	INTEGER,
     		a3ComFilterAddressAddress		PhysAddress,
     		a3ComFilterAddressStatus		RowStatus
    }

a3ComFilterAddressId  OBJECT-TYPE
    SYNTAX  INTEGER (1..65535)
    ACCESS  read-only
    STATUS  mandatory
    DESCRIPTION
            "This object uniquely identifies an address group as
            defined in a3ComFilterAddressGroupTable.  It is obtained
            from a3ComFilterAddressGroupNextAvailableIndex."
::= { a3ComFilterAddressEntry 1 }

a3ComFilterAddressAddress  OBJECT-TYPE
    SYNTAX  PhysAddress
    ACCESS  read-only
    STATUS  mandatory
    DESCRIPTION
            "The physical address of this entry."
::= { a3ComFilterAddressEntry 2 }

a3ComFilterAddressStatus  OBJECT-TYPE
    SYNTAX  RowStatus
    ACCESS  read-write
    STATUS  mandatory
    DESCRIPTION
            "The status column for this address group entry.  This
            OBJECT can be set to:
            createAndGo(4)
            destroy(6)

            The following values may be read:
            active(1)

            Setting this object to createAndGo(4) will result in the agent attempt
            to create and commit the row based on the contents of the objects in the row.
            If all the necessary information is presented in the row and the
            values are acceptible to the agent, the agent will change the status to
            active(1).  If there are any necessary objects are not set, the
            agent will reject the creation request.

            When the state of the row translates to active(1), the agent add the
            corresponding address to the specified address group.

            Setting this object to destroy(6) will remove the corresponding
            address from the indicated address group."
::= { a3ComFilterAddressEntry 3 }

	--
	--  id of next available port group
	--

a3ComFilterPortGroupNextAvailableIndex  OBJECT-TYPE
    SYNTAX  INTEGER
    ACCESS  read-only
    STATUS  mandatory
    DESCRIPTION
            "The value of next available a3ComFilterPortGroupId.
            This object is used for index value to create a new
            port group."

::= { a3ComFilterPortGroup 1 }

     --
     -- Count Of Defined Port Groups
     --

a3ComFilterPortGroupCount  OBJECT-TYPE
    SYNTAX  INTEGER
    ACCESS  read-only
    STATUS  mandatory
    DESCRIPTION
            "The count of defined port groups in the system."
::= { a3ComFilterPortGroup 2 }

     --
     -- The LANPlex Port Group Table
     --

a3ComFilterPortGroupTable  OBJECT-TYPE
    SYNTAX  SEQUENCE OF A3ComFilterPortGroupEntry
    ACCESS  not-accessible
    STATUS  mandatory
    DESCRIPTION
            "A list of port group entries.  A single
            entry exists in this list for each defined
            port group in the system."
::= { a3ComFilterPortGroup 3 }

a3ComFilterPortGroupEntry  OBJECT-TYPE
    SYNTAX  A3ComFilterPortGroupEntry
    ACCESS  not-accessible
    STATUS  mandatory
    DESCRIPTION
            "A set of parameters for an individual port
            group entry."
    INDEX  { a3ComFilterPortGroupId }
::= { a3ComFilterPortGroupTable 1 }

A3ComFilterPortGroupEntry ::=
    SEQUENCE {
	    	a3ComFilterPortGroupId			INTEGER,
     		a3ComFilterPortGroupMaskId		INTEGER,
     		a3ComFilterPortGroupBridgeNumber	INTEGER,
     		a3ComFilterPortGroupName			DisplayString,
     		a3ComFilterPortGroupStatus		RowStatus
    }

a3ComFilterPortGroupId  OBJECT-TYPE
    SYNTAX  INTEGER (1..65535)
    ACCESS  read-only
    STATUS  mandatory
    DESCRIPTION
            "This object uniquely identifies a port group in the
            systems. Its value, successively increases starting from 0,
            will change only if the system is rebooted.  This object is
            obtained from a3ComFilterPortGroupNextAvailableIndex
            when a new port group is created."
::= { a3ComFilterPortGroupEntry 1 }

a3ComFilterPortGroupMaskId  OBJECT-TYPE
    SYNTAX  INTEGER
    ACCESS  read-write
    STATUS  mandatory
    DESCRIPTION
            "This object identifies a port group in a bridge. Each
            port group has an unique mask identifier, range from 1 to 32,
            associated with it in a bridge. This field has to be set in
            order to create a new port group in a bridge."
::= { a3ComFilterPortGroupEntry 2 }


a3ComFilterPortGroupBridgeNumber  OBJECT-TYPE
    SYNTAX  INTEGER
    ACCESS  read-write
    STATUS  mandatory
    DESCRIPTION
            "The bridge index associated with this port group."
::= { a3ComFilterPortGroupEntry 3 }

a3ComFilterPortGroupName  OBJECT-TYPE
    SYNTAX  DisplayString (SIZE (0..31))
    ACCESS  read-write
    STATUS  mandatory
    DESCRIPTION
            "The name of this port group. This object has be
            unique in a system."
::= { a3ComFilterPortGroupEntry 4 }

a3ComFilterPortGroupStatus  OBJECT-TYPE
    SYNTAX  RowStatus
    ACCESS  read-write
    STATUS  mandatory
    DESCRIPTION
            "The status column for this port group entry.  This OBJECT
            can be set to:
            createAndGo(4)
            destroy(6)

            The following values may be read:
            active(1)


            Setting this object to createAndGo(4) will result in the agent attempting
            to create and commit the row based on the contents of the objects in the row.
            If all the necessary information is presented in the row and the
            values are acceptible to the agent, the agent will change the status to
            active(1).  If there are any necessary objects are not set, the
            agent will reject the creation request.

            When the state of the row translates to active(1), the agent add the
            corresponding port to the specified port group.

            Setting this object to destroy(6) will remove the corresponding port
            group and its mask from the port group table."
::= { a3ComFilterPortGroupEntry 5 }


     --
     -- The LANPlex Port Table
     --

a3ComFilterPortTable  OBJECT-TYPE
    SYNTAX  SEQUENCE OF A3ComFilterPortEntry
    ACCESS  not-accessible
    STATUS  mandatory
    DESCRIPTION
            "A list of port entries."
::= { a3ComFilterPortGroup 4 }

a3ComFilterPortEntry  OBJECT-TYPE
    SYNTAX  A3ComFilterPortEntry
    ACCESS  not-accessible
    STATUS  mandatory
    DESCRIPTION
            "An individual port entry."
    INDEX  { a3ComFilterPortId, a3ComFilterPortType, a3ComFilterPortPort }
::= { a3ComFilterPortTable 1 }

A3ComFilterPortEntry ::=
    SEQUENCE {
    		a3ComFilterPortId		INTEGER,
		a3ComFilterPortType		A3ComFilterPortType,
     		a3ComFilterPortPort		INTEGER,
     		a3ComFilterPortStatus		RowStatus
    }

a3ComFilterPortId  OBJECT-TYPE
    SYNTAX  INTEGER (1..65535)
    ACCESS  read-only
    STATUS  mandatory
    DESCRIPTION
            "This object uniquely identify an address group in the systems.
            It successively increases starting from 1. This value is
            obtained through a3ComFilterPortGroupNextAvailableIndex when
            a new port group needs to be created."
::= { a3ComFilterPortEntry 1 }

a3ComFilterPortType  OBJECT-TYPE
    SYNTAX  A3ComFilterPortType
    ACCESS  read-only
    STATUS  mandatory
    DESCRIPTION
            "This indicates interface port type(s) that are currently
            supported by LanPlex modules."
::= { a3ComFilterPortEntry 2 }

a3ComFilterPortPort  OBJECT-TYPE
    SYNTAX  INTEGER (1..65535)
    ACCESS  read-only
    STATUS  mandatory
    DESCRIPTION
            "The port on the bridge identified by port type."
::= { a3ComFilterPortEntry 3 }

a3ComFilterPortStatus  OBJECT-TYPE
    SYNTAX  RowStatus
    ACCESS  read-write
    STATUS  mandatory
    DESCRIPTION
            "The status column for this port group entry.
            This OBJECT can be set to:

            createAndGo(4)
            destroy(6)

            The following values may be read:
            active(1)

            Setting this object to createAndGo(4) will result in the agent attempting
            to create and commit the row based on the contents of the objects in the row.
            If all the necessary information is presented in the row and the
            values are acceptible to the agent, the agent will change the status to
            active(1).  If there are any necessary objects are not set, the
            agent will reject the creation request.

            When the state of the row translates to active(1), the agent will add
            the corresponding port to the indicated port group.

            Setting this object to destroy(6) will remove this port from
            corresponding port group."
::= { a3ComFilterPortEntry 4 }


 	 --
     -- Index Of next available bridge filter id
     --

a3ComBridgeFilterNextAvailableIndex  OBJECT-TYPE
    SYNTAX  INTEGER
    ACCESS  read-only
    STATUS  mandatory
    DESCRIPTION
            "The value of next available a3ComBridgeFilterId.
            This object indicates filter id when a new bridge filter
            is created through console or ftp download."
::= { a3ComBridgeFilterGroup 1 }

     --
     -- Count Of Defined Bridge Filter Programs
     --

a3ComBridgeFilterCount  OBJECT-TYPE
    SYNTAX  INTEGER
    ACCESS  read-only
    STATUS  mandatory
    DESCRIPTION
            "The count of stored bridge packet filter programs on the
            bridge."
::= { a3ComBridgeFilterGroup 2 }

     --
     -- The Bridge Filter Table
     --


a3ComBridgeFilterTable  OBJECT-TYPE
    SYNTAX  SEQUENCE OF A3ComBridgeFilterEntry
    ACCESS  not-accessible
    STATUS  mandatory
    DESCRIPTION
            "The list of stored bridge packet filter programs on
            bridge(s), bridge port(s) and port processing path."
::= { a3ComBridgeFilterGroup 3 }

a3ComBridgeFilterEntry  OBJECT-TYPE
    SYNTAX  A3ComBridgeFilterEntry
    ACCESS  not-accessible
    STATUS  mandatory
    DESCRIPTION
            "The set of parameters for an individual bridge packet filter
            program."
    INDEX  { a3ComBridgeFilterId, a3ComBridgeFilterBridgeNumber }
::= { a3ComBridgeFilterTable 1 }

A3ComBridgeFilterEntry ::=
    SEQUENCE {
     		a3ComBridgeFilterId				INTEGER,
     		a3ComBridgeFilterBridgeNumber 		INTEGER,
     		a3ComBridgeFilterName				DisplayString,
     		a3ComBridgeFilterProgram			DisplayString,
     		a3ComBridgeFilterStatus			RowStatus
    }

a3ComBridgeFilterId  OBJECT-TYPE
    SYNTAX  INTEGER (1..65535)
    ACCESS  read-only
    STATUS  mandatory
    DESCRIPTION
            "An index that uniquely identifies a bridge filter in a system.
            Its value will change only if the system is rebooted."
::= { a3ComBridgeFilterEntry 1 }


a3ComBridgeFilterBridgeNumber  OBJECT-TYPE
    SYNTAX  INTEGER (1..65535)
    ACCESS  read-only
    STATUS  mandatory
    DESCRIPTION
            "The bridge index associated with this bridge
            filter program."
::= { a3ComBridgeFilterEntry 2 }

a3ComBridgeFilterName  OBJECT-TYPE
    SYNTAX  DisplayString (SIZE (32))
    ACCESS  read-only
    STATUS  mandatory
    DESCRIPTION
            "The filter name associated with this entry."
::= { a3ComBridgeFilterEntry 3 }

a3ComBridgeFilterProgram  OBJECT-TYPE
    SYNTAX  DisplayString (SIZE (255))
    ACCESS  read-only
    STATUS  mandatory
    DESCRIPTION
            "The bridge filter program."
::= { a3ComBridgeFilterEntry 4 }

a3ComBridgeFilterStatus  OBJECT-TYPE
    SYNTAX  RowStatus
    ACCESS  read-write
    STATUS  mandatory
    DESCRIPTION
            "The status column for this filter definition entry.
            This OBJECT can be set to:

            createAndGo(4)
            destroy(6)

            The following values may be read:
            active(1)

            Creation of bridge filter programs can be performed by:
            1. Using the build-in editor of the AdminConsole.

            2. Using your own line on an external host, and transferring the
            filter program via the AdminConsole.

            3. Using the filter program creation tool on an external host, which
            builds the filter and transfers it to the LANPlex using SNMP.  The
            transfer is accomplished using the file transfer MIB in the
            LANPlex system MIB.

            Setting this object to createAndGo(4) will result in the agent attempting
            to create and commit the row based on the contents of the objects in the row.
            If all the necessary information is presented in the row and the
            values are acceptible to the agent, the agent will change the status to
            active(1).  If there are any necessary  objects are not set, the
            agent will reject the creation request.

            When the state of the row translates to active(1), the agent will add
            the corresponding filter to the specified packet processing
            path(s) of the bridge port(s) in a bridge.

            Setting this object to destroy(6) will remove all corresponding
            attributes of the  filter table."
::= { a3ComBridgeFilterEntry 5 }

a3ComPortFilterTable  OBJECT-TYPE
    SYNTAX  SEQUENCE OF A3ComPortFilterEntry
    ACCESS  not-accessible
    STATUS  mandatory
    DESCRIPTION
            "The list of stored bridge packet filter programs on
            bridge(s), bridge port(s) and port processing path."
::= { a3ComBridgeFilterGroup 4 }

a3ComPortFilterEntry  OBJECT-TYPE
    SYNTAX  A3ComPortFilterEntry
    ACCESS  not-accessible
    STATUS  mandatory
    DESCRIPTION
            "The set of parameters for an individual bridge packet filter
            program."
    INDEX  { a3ComPortFilterId, a3ComPortFilterBridgeNumber,
            a3ComPortFilterBridgePortType, a3ComPortFilterBridgePortPort }
::= { a3ComPortFilterTable 1 }

A3ComPortFilterEntry ::=
    SEQUENCE {
     		a3ComPortFilterId				INTEGER,
     		a3ComPortFilterBridgeNumber 	INTEGER,
	 	a3ComPortFilterBridgePortType	A3ComFilterPortType,
	 	a3ComPortFilterBridgePortPort	INTEGER,
     		a3ComPortFilterPktProcessPath	INTEGER,
     		a3ComPortFilterStatus			RowStatus
    }

a3ComPortFilterId  OBJECT-TYPE
    SYNTAX  INTEGER (1..65535)
    ACCESS  read-only
    STATUS  mandatory
    DESCRIPTION
            "An index that uniquely identifies a bridge filter on the bridge."
::= { a3ComPortFilterEntry 1 }

a3ComPortFilterBridgeNumber  OBJECT-TYPE
    SYNTAX  INTEGER (1..65535)
    ACCESS  read-only
    STATUS  mandatory
    DESCRIPTION
            "The bridge index associated with this bridge
            filter program. "
::= { a3ComPortFilterEntry 2 }

a3ComPortFilterBridgePortType  OBJECT-TYPE
    SYNTAX  A3ComFilterPortType
    ACCESS  read-only
    STATUS  mandatory
    DESCRIPTION
            "This indicates interface port type(s) that are currently
            supported by LanPlex modules."
::= { a3ComPortFilterEntry 3 }

a3ComPortFilterBridgePortPort  OBJECT-TYPE
    SYNTAX  INTEGER (1..65535)
    ACCESS  read-only
    STATUS  mandatory
    DESCRIPTION
            "The port on the bridge identified by this row's a3ComPortFilterBridgeNumber."
::= { a3ComPortFilterEntry 4 }

a3ComPortFilterPktProcessPath  OBJECT-TYPE
    SYNTAX  INTEGER
    ACCESS  read-write
    STATUS  mandatory
    DESCRIPTION
            "The packet processing path to apply the filter.  The value
            is a bit mask defined as follows:

            Mask Value	  Path	          Description
            0x1	    Xmit All       	All frames xmitted to segment
            connected to the port

            0x2	    Xmit Multicast 	Multicast+broadcast frames
            xmitted to the segment
            connected to the port

            0x4	    Recv All	 	All frame received by the
            port from the segment
            connected to the port

            0x8	    Recv Multicast	Multicast+broadcast frames
            received by the port from the
            segement connected to the
            port.
            If mask value is set to 0x10, the packet filter will be loaded to
            both transmit multicast and receive multicast paths.  Once a bridge
            filter program has been downloaded to a bridge port path, this
            object can be applied to change its value."

::= { a3ComPortFilterEntry 5 }


a3ComPortFilterStatus  OBJECT-TYPE
    SYNTAX  RowStatus
    ACCESS  read-write
    STATUS  mandatory
    DESCRIPTION
            "The status column for this filter definition entry.
            This OBJECT can be set to:

            active(1)
            createAndGo(4)
            createAndWait(5)
            destroy(6)

            The following values may be read:
            active(1)
            notInService(2)
            netReady(3).

            Creation of bridge filter programs can be performed by:
            1. Using the build-in editor of the AdminConsole.

            2. Using your own line on an external host, and transferring the
            filter program via the AdminConsole.

            3. Using the filter program creation tool on an external host, which
            builds the filter and transfers it to the LANPlex using SNMP.  The
            transfer is accomplished using the file transfer MIB in the
            LANPlex system MIB.

            Setting this object to active(1) is only valid when the current status
            is active or notInService(2).

            Setting this object to createAndGo(4) will result in the agent attempt
            to create and commit the row based on the contents of the objects in the row.
            If all the necessary information is presented in the row and the
            values are acceptible to the agent, the agent will change the status to
            active(1).  If there are any necessary objects are not set, the
            agent will reject the creation request.

            Setting this object to createAndWait(5) will cause the agent to create
            a row in this table.  This object will change to notInService(2) if
            all the information is present in the row and the values are
            acceptible to the agent; otherwise, the agent will set the
            status to notReady(3).

            When the state of the row translates to active(1), the agent will add
            the corresponding filter to the specified packet processing
            path(s) of the bridge port(s) in a bridge.

            Setting this object to destroy(6) will remove all corresponding
            attributes of the  filter table."
::= { a3ComPortFilterEntry 6 }
END
