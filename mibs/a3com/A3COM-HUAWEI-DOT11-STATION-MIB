-- =============================================================================
-- Copyright (c) 2004-2011 Hangzhou H3C Tech. Co., Ltd. All rights reserved.
--
-- Description:
--   The file defines a MIB to provide 802.11 MAC information such
--   as station statistic and notification events.
-- Reference:
-- Version: V2.2
-- History:
--   V1.0 created by shiyang (Richard)
--     Initial version 2006-05-10
--   V1.1 2007-04-27 modified by shiyang(Richard)
--        The data type of object h3cDot11StationRxFrameBytes,
--        h3cDot11StationTxFrameBytes and h3cDot11StationDropFrameBytes
--        was changed from counter32 to counter64.
--   V1.2 2007-06-21 modified by Vikas K
--        Added 4 new Station Traps and also new objects for the traps.
--   V1.3 2007-12-21 modified by wanghao (Kumar)
--        Added h3cDot11StationRxSNR, h3cDot11StationTxRate,
--        h3cDot11StationRxRate to h3cDot11StationAssociateTable.
--        Added h3cDot11StationSessionDuration to h3cDot11StationDeAssocTrap
--        Added h3cDot11StationSessionDuration to h3cDot11StationTrapVarObjects.
--        Added h3cDot11StationVendorName and h3cDot11StationRadioMode to
--        H3cDot11StationAssociateEntry.
--   V1.4 2008-02-25 modified by wanghao (Kumar)
--        Add h3cDot11StationRoamingTrap and add h3cDot11StationRxNoise to
--        h3cDot11StationAssociateTable.
--   V1.5 2008-08-01 modified by Wang Lu
--        Change description of h3cDot11StationMAC, h3cDot11CurrWlanID and
--        h3cDot11StationAid.
--        Change SYNTAX of h3cDot11StationSessionStartTime
--        Change OBJECTS of h3cDot11StationAuthorFailTrap,
--        h3cDot11StationAssocFailTrap, h3cDot11StationDeAssocTrap and
--        h3cDot11StationAuthorSuccTrap
--   V1.6 2008-11-07 modified by Wang Lu and Li Yugang
--        Add h3cDot11StationRxRetryPkts, h3cDot11StationTxRetryPkts,
--        h3cDot11StationRxRetryBytes and h3cDot11StationTxRetryBytes
--        to h3cDot11StationStatisTable.
--        Add new variable bindings h3cDot11StationAPName and
--        h3cDot11StationBSSID to h3cDot11StationAuthorSuccTrap and
--        h3cDot11StationDeAssocTrap.
--        Add new notification h3cDot11StationDisconnectTrap.
--        Add h3cDot11StationThroughput to h3cDot11StationStatisTable.
--   V1.7 2009-05-07 modified by Wang Shaojie
--        Add h3cDot11StationMACAddress to h3cDot11StationAssociateTable
--   V1.8 2009-04-14 modified by Heziqi
--        Add new node h3cDot11StationSuccessTxCnt, h3cDot11StationRxFragCnt
--        and h3cDot11StationSuccessTxDataCnt for h3cDot11StationStatisTable.
--        Add new node h3cDot11StationTxSpeed, h3cDot11StationRxSpeed
--        and h3cDot11StationWmmMode for h3cDot11StationAssociateTable.
--        Add new node h3cDot11StationRxDataFrameCnt,
--        h3cDot11StationTxDataFrameCnt, h3cDot11StationRxDataFrameBytes
--        h3cDot11StationTxDataFrameBytes for h3cDot11StationAssociateTable.
--   V1.9 2009-08-07 modified by Wang Shaojie
--        Modify description of h3cDot11StationTxSpeed, h3cDot11StationRxSpeed
--   V2.0 2010-02-23 Add new node h3cDot11StaRxErrDataFrameCnt and
--        h3cDot11StaTxRetryDataFrameCnt to h3cDot11StationStatisTable.
--        Add new node h3cDot11StationUpTimeTicks, h3cDot11StationSecIEStatus
--        to h3cDot11StationAssociateTable.
--        Add h3cDot11StationAuthMode to h3cDot11StationTrapVarObjects.
--        2010-08-07 modified by Wang Shaojie
--        Add h3cDot11StationACIPv6Add to h3cDot11StationTrapVarObjects.
--        2010-09-02 modified by Yin junjie
--        Modify h3cDot11StationDisconnectTrap.
--   V2.1 2011-08-10 modified by limingjin
--        Add h3cDot11StationRadioMode2 to h3cDot11StationAssociateTable
--   V2.2 2011-09-28 modified by zhanghu
--        Add h3cDot11StaTxDataRatePkts, h3cDot11StaRxDataRatePkts,
--        h3cDot11StaTxSignalStrengthPkts to h3cDot11StationStatisTable
--        2012-02-08 modified by d07436
--        Add h3cDot11StationAssTime to  h3cDot11StationAssociateEntry
--        Add h3cDot11UserDisconnectTrap to h3cDot11StationTraps
--        Add h3cDot11UserName to h3cDot11StationTrapVarObjects
-- =============================================================================
A3COM-HUAWEI-DOT11-STATION-MIB DEFINITIONS ::= BEGIN

IMPORTS
        MacAddress, DateAndTime
    FROM SNMPv2-TC
        MODULE-IDENTITY,
        OBJECT-TYPE,
        NOTIFICATION-TYPE,
        Integer32,
        Unsigned32,
        Counter32,
        Counter64,
        IpAddress,
        TimeTicks
    FROM SNMPv2-SMI
        h3cDot11,
        H3cDot11RadioType,
        H3cDot11ObjectIDType,
        H3cDot11ChannelScopeType,
        H3cDot11SSIDStringType,
        H3cDot11AuthenType,
        H3cDot11AKMType,
        H3cDot11CipherType,
        H3cDot11RadioScopeType,
        H3cDot11SSIDEncryptModeType,
        H3cDot11AssocFailType,
        H3cDot11AuthorFailType,
        H3cDot11SecIEStatusType,
        H3cDot11RadioType2
    FROM A3COM-HUAWEI-DOT11-REF-MIB;

h3cDot11STATION MODULE-IDENTITY
    LAST-UPDATED "201009021800Z"        -- Sep 2, 2010 at 18:00 GMT
    ORGANIZATION
        "Hangzhou H3C Technologies Co., Ltd."
    CONTACT-INFO
        "Platform Team H3C Technologies Co., Ltd.
         Hai-Dian District Beijing P.R. China
         http://www.h3c.com
         Zip: 100085"
    DESCRIPTION
        "This MIB defines the configuration and statistic information of
        stations.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Control And Provisioning of Wireless Access Points Protocol
        The short name of protocol is CAPWAP. AC will control
        and manage AP by CAPWAP tunnel protocol defined by IETF.
        Also, a data tunnel will be set up between AC and AP.

        BSS
        IEEE 802.11 Basic Service Set (Radio Cell).  The
        BSS of an AP comprises of the stations directly
        associated with the AP.

        station (Client Station)
        A wireless device in a wireless network
        associated with an access point.

        MIC
        Message Integrity Check.  A MIC can, optionally,
        be added to WEP-encrypted 802.11 frames.

        SSID
        Radio Service Set ID.  It is used for identification
        during association.

        STA  (WSTA)
        A non-AP 802.11 wireless station.

        WEP
        Wired Equivalent Privacy.  'WEP' is generally used
        to refer to 802.11 encryption.

        RSSI
        It is the received signal strength indication.
        It suggests the quality of received signal.

        RTS
        Request to Send, it is used to gain control of the medium
        for the transmission of 'large' frames, in which 'large'
        is defined by the RTS threshold in the network card driver.

        CTS
        Clear to Send, it is used to answer RTS frames.

        AKM
        The authentication and key management method defined by
        802.11i, and which includes 802.1x and pre-shared key."

    REVISION "201009021800Z"        -- Sep 2, 2010 at 18:00 GMT
    DESCRIPTION
        "Modify h3cDot11StationDisconnectTrap."
    REVISION "201002231800Z"        -- Feb 23, 2010 at 18:00 GMT
    DESCRIPTION
        "Add new node h3cDot11StationUpTimeTicks, h3cDot11StationSecIEStatus
         to h3cDot11StationAssociateTable."
    REVISION "200912011800Z"        -- Aug 07, 2009 at 18:00 GMT
    DESCRIPTION
        "Add new node h3cDot11StaRxErrDataFrameCnt and h3cDot11StaTxRetryDataFrameCnt
         to h3cDot11StationStatisTable"
    REVISION "200908071800Z"        -- Aug 07, 2009 at 18:00 GMT
    DESCRIPTION
        "Modify description of h3cDot11StationTxSpeed, h3cDot11StationRxSpeed"
    REVISION "200907291800Z"        -- Jul 29, 2009 at 18:00 GMT
    DESCRIPTION
        "Modified to add new nodes."
    REVISION "200905072000Z"        -- May 7, 2009 at 20:00 GMT
    DESCRIPTION
        "Modified to add new nodes."
    REVISION "200811071730Z"        -- Nov 07, 2008 at 17:30 GMT
    DESCRIPTION
        "Modified to add new nodes."
    REVISION "200802251800Z"        -- Feb 25, 2008 at 18:00 GMT
    DESCRIPTION
        "Modified to add new trap and add h3cDot11StationRxNoise to h3cDot11StationAssociateTable."
    REVISION "200712211800Z"        -- Dec 21, 2007 at 18:00 GMT
    DESCRIPTION
        "Modified to add new nodes."
    REVISION "200706212000Z"        -- Jun 21, 2007 at 20:00 GMT
    DESCRIPTION
        "Changes made for new requirements."
    REVISION "200704272000Z"        -- Apr 27, 2007 at 20:00 GMT
    DESCRIPTION
        "Modified to fix some issue."
    REVISION "200605101600Z"        -- May 10, 2006 at 19:00 GMT
    DESCRIPTION
        "The initial revision of this MIB module."
    ::= { h3cDot11 3 }

-- *****************************************************************************
-- *  Major sections
-- *****************************************************************************
--  Station Management Group
--  DEFINED AS "The group to provide the basic information for station,
--  for example, associated station, performance data and so on."

h3cDot11StationMtGroup OBJECT IDENTIFIER     ::= { h3cDot11STATION 1 }
--  Station Management Group has the following children:
--  h3cDot11StationAssociateTable            ::= { h3cDot11APMtGroup 1 }
--  h3cDot11StationAPRelationTable           ::= { h3cDot11APMtGroup 2 }
--  h3cDot11StationStatisTable               ::= { h3cDot11APMtGroup 3 }

--  MAC Event Notification
--  DEFINED AS "The group to provide station notification information"
h3cDot11StationNotifyGroup OBJECT IDENTIFIER ::= { h3cDot11STATION 2 }

-- *****************************************************************************
-- *  h3cDot11StaAssociateTable Definition
-- *****************************************************************************
h3cDot11StationAssociateTable OBJECT-TYPE
    SYNTAX      SEQUENCE OF H3cDot11StationAssociateEntry
    MAX-ACCESS  not-accessible
    STATUS      current
    DESCRIPTION
        "This table contains the information of stations which are
        associating with the wireless network (current AC)."
    ::= { h3cDot11StationMtGroup 1 }

h3cDot11StationAssociateEntry OBJECT-TYPE
    SYNTAX      H3cDot11StationAssociateEntry
    MAX-ACCESS  not-accessible
    STATUS      current
    DESCRIPTION
        "Each entry contains association information of each station."
    INDEX
        {
            h3cDot11StationMAC
        }
    ::= { h3cDot11StationAssociateTable 1 }

H3cDot11StationAssociateEntry ::= SEQUENCE
    {
        h3cDot11StationMAC                MacAddress,
        h3cDot11StationIPAddress          IpAddress,
        h3cDot11StationUserName           OCTET STRING,
        h3cDot11StationTxRateSet          OCTET STRING,
        h3cDot11StationUpTime             Unsigned32,
        h3cDot11StationSignalStrength     Integer32,
        h3cDot11StationRSSI               Integer32,
        h3cDot11StationChannel            H3cDot11ChannelScopeType,
        h3cDot11StationPowerSaveMode      INTEGER,
        h3cDot11StationAid                Integer32,
        h3cDot11StationVlanId             Integer32,
        h3cDot11StationSSIDName           H3cDot11SSIDStringType,
        h3cDot11StationAuthenMode         H3cDot11AuthenType,
        h3cDot11StationAKMMode            H3cDot11AKMType,
        h3cDot11StationSecurityCiphers    H3cDot11CipherType,
        h3cDot11StationSSIDEncryptMode    H3cDot11SSIDEncryptModeType,
        h3cDot11StationRxSNR              Integer32,
        h3cDot11StationTxRate             Integer32,
        h3cDot11StationRxRate             Integer32,
        h3cDot11StationVendorName         OCTET STRING,
        h3cDot11StationRadioMode          H3cDot11RadioType,
        h3cDot11StationRxNoise            Integer32,
        h3cDot11StationMACAddress         MacAddress,
        h3cDot11StationTxSpeed            Integer32,
        h3cDot11StationRxSpeed            Integer32,
        h3cDot11StationWmmMode            INTEGER,
        h3cDot11StationSecIEStatus        H3cDot11SecIEStatusType,
        h3cDot11StationUpTimeTicks        TimeTicks,
        h3cDot11StationRadioMode2         H3cDot11RadioType2,
        h3cDot11StationAssTime            DateAndTime
    }

h3cDot11StationMAC OBJECT-TYPE
    SYNTAX      MacAddress
    MAX-ACCESS  not-accessible
    STATUS      current
    DESCRIPTION
        "Represents the unique MAC Address of station."
    ::= { h3cDot11StationAssociateEntry 1 }

h3cDot11StationIPAddress OBJECT-TYPE
    SYNTAX      IpAddress
    MAX-ACCESS  read-only
    STATUS      current
    DESCRIPTION
        "Represents the IP address of the station."
    ::= { h3cDot11StationAssociateEntry 2 }

h3cDot11StationUserName OBJECT-TYPE
    SYNTAX      OCTET STRING
    MAX-ACCESS  read-only
    STATUS      current
    DESCRIPTION
        "Represents the user name of the station."
    ::= { h3cDot11StationAssociateEntry 3 }

h3cDot11StationTxRateSet OBJECT-TYPE
    SYNTAX      OCTET STRING
    UNITS       "Mbps"
    MAX-ACCESS  read-only
    STATUS      current
    DESCRIPTION
        "Represents the current transmit data rates for this station.
        Each byte will represent one rate. If the MSB(Most significant bit)
        is set, then this rate is a mandantory rate. Otherwise,
        it is optional."
    ::= { h3cDot11StationAssociateEntry 4 }

h3cDot11StationUpTime OBJECT-TYPE
    SYNTAX      Unsigned32
    UNITS       "second"
    MAX-ACCESS  read-only
    STATUS      current
    DESCRIPTION
        "The time in seconds, how long this station has been associated
        with this device."
    ::= { h3cDot11StationAssociateEntry 5 }

h3cDot11StationSignalStrength OBJECT-TYPE
    SYNTAX      Integer32
    UNITS       "dBm"
    MAX-ACCESS  read-only
    STATUS      current
    DESCRIPTION
        "Represents a device-dependent measure of the signal strength
        of latest packet received from this station."
    ::= { h3cDot11StationAssociateEntry 6 }

h3cDot11StationRSSI OBJECT-TYPE
    SYNTAX      Integer32
    MAX-ACCESS  read-only
    STATUS      current
    DESCRIPTION
        "Represents a device-dependent measure of the RSSI.
        It is the received signal strength indication.
        The maximum value is defined by chip set vendors"
    ::= { h3cDot11StationAssociateEntry 7 }

h3cDot11StationChannel OBJECT-TYPE
    SYNTAX      H3cDot11ChannelScopeType
    MAX-ACCESS  read-only
    STATUS      current
    DESCRIPTION
        "Represents current radio channel used by station."
    ::= { h3cDot11StationAssociateEntry 8 }

h3cDot11StationPowerSaveMode OBJECT-TYPE
    SYNTAX      INTEGER
        {
            active(1),
            powersave(2)
        }
    MAX-ACCESS  read-only
    STATUS      current
    DESCRIPTION
        "Represents the power management mode of this station.
        The following values are supported:
        active(1)    - This station is not in power-save
        mode and it is actively sending or
        receiving data.
        powersave(2) - This station is in power-save mode and
        it wakes up after sometime to check for
        buffer data."
    DEFVAL      { active }
    ::= { h3cDot11StationAssociateEntry 9 }

h3cDot11StationAid OBJECT-TYPE
    SYNTAX      Integer32
    MAX-ACCESS  read-only
    STATUS      current
    DESCRIPTION
        "Represents the association identification number of station."
    ::= { h3cDot11StationAssociateEntry 10 }

h3cDot11StationVlanId OBJECT-TYPE
    SYNTAX      Integer32
    MAX-ACCESS  read-only
    STATUS      current
    DESCRIPTION
        "Represents Vlan ID to which the station is associated."
    ::= { h3cDot11StationAssociateEntry 11 }

h3cDot11StationSSIDName OBJECT-TYPE
    SYNTAX      H3cDot11SSIDStringType
    MAX-ACCESS  read-only
    STATUS      current
    DESCRIPTION
        "Represents the ESS name."
    ::= { h3cDot11StationAssociateEntry 12 }

h3cDot11StationAuthenMode OBJECT-TYPE
    SYNTAX      H3cDot11AuthenType
    MAX-ACCESS  read-only
    STATUS      current
    DESCRIPTION
        "Represents the Authentication mode defined by 802.11."
    ::= { h3cDot11StationAssociateEntry 13 }

h3cDot11StationAKMMode OBJECT-TYPE
    SYNTAX      H3cDot11AKMType
    MAX-ACCESS  read-only
    STATUS      current
    DESCRIPTION
        "Represents the key management mode defined by 802.11i."
    ::= { h3cDot11StationAssociateEntry 14 }

h3cDot11StationSecurityCiphers OBJECT-TYPE
    SYNTAX      H3cDot11CipherType
    MAX-ACCESS  read-only
    STATUS      current
    DESCRIPTION
        "Represents the frame encryption cipher type used by
        station."
    ::= { h3cDot11StationAssociateEntry 15 }

h3cDot11StationSSIDEncryptMode OBJECT-TYPE
    SYNTAX      H3cDot11SSIDEncryptModeType
    MAX-ACCESS  read-only
    STATUS      current
    DESCRIPTION
        "Represents the encryption mode for this ESS."
    DEFVAL      { cipher }
    ::= { h3cDot11StationAssociateEntry 16 }

h3cDot11StationRxSNR OBJECT-TYPE
    SYNTAX      Integer32
    UNITS       "One Percent"
    MAX-ACCESS  read-only
    STATUS      current
    DESCRIPTION
        "Represents the signal and noise strength ratio of frame reception."
    ::= { h3cDot11StationAssociateEntry 17 }

h3cDot11StationTxRate OBJECT-TYPE
    SYNTAX      Integer32
    UNITS       "Mbps"
    MAX-ACCESS  read-only
    STATUS      current
    DESCRIPTION
        "Represents the transmission rate of frame."
    ::= { h3cDot11StationAssociateEntry 18 }

h3cDot11StationRxRate OBJECT-TYPE
    SYNTAX      Integer32
    UNITS       "Mbps"
    MAX-ACCESS  read-only
    STATUS      current
    DESCRIPTION
        "Represents the reception rate of frame."
    ::= { h3cDot11StationAssociateEntry 19 }

h3cDot11StationVendorName OBJECT-TYPE
    SYNTAX      OCTET STRING(SIZE(0..127))
    MAX-ACCESS  read-only
    STATUS      current
    DESCRIPTION
        "Represents the vendor name of the station."
    ::= { h3cDot11StationAssociateEntry 20 }

h3cDot11StationRadioMode OBJECT-TYPE
    SYNTAX      H3cDot11RadioType
    MAX-ACCESS  read-only
    STATUS      current
    DESCRIPTION
        "Represents which radio type supported by the station.
        The WLAN system support the following possible radio types.
        dot11a(1),
        dot11b(2),
        dot11g(4),
        dot11n(8)
        For a station,it could support only one radio type at
        the same time."
    ::= { h3cDot11StationAssociateEntry 21 }

h3cDot11StationRxNoise OBJECT-TYPE
    SYNTAX      Integer32
    MAX-ACCESS  read-only
    STATUS      current
    DESCRIPTION
        "Represents the received noise of the station."
    ::= { h3cDot11StationAssociateEntry 22 }


h3cDot11StationMACAddress OBJECT-TYPE
    SYNTAX      MacAddress
    MAX-ACCESS  read-only
    STATUS      current
    DESCRIPTION
        "Represents MAC Address of station."
    ::= { h3cDot11StationAssociateEntry 23 }

h3cDot11StationTxSpeed OBJECT-TYPE
    SYNTAX      Integer32
    UNITS       "byte/s"
    MAX-ACCESS  read-only
    STATUS      current
    DESCRIPTION
        "Represents the bytes of transmitted data frames to the
        station per second in sample interval."
    ::= { h3cDot11StationAssociateEntry 24 }

h3cDot11StationRxSpeed OBJECT-TYPE
    SYNTAX      Integer32
    UNITS       "byte/s"
    MAX-ACCESS  read-only
    STATUS      current
    DESCRIPTION
        "Represents the bytes of received data frames from the
        station per second in sample interval."
    ::= { h3cDot11StationAssociateEntry 25 }

h3cDot11StationWmmMode  OBJECT-TYPE
    SYNTAX      INTEGER
        {
            wmm(1),
            nonwmm(2)
        }
    MAX-ACCESS  read-only
    STATUS      current
    DESCRIPTION
        "Represents the QoS mode of station.
        The following values are supported:
        wmm(1)    - This QoS function is supported by this station.
        nonwmm(2) - This QoS function is not supported by this station."
    ::= { h3cDot11StationAssociateEntry 26 }

h3cDot11StationSecIEStatus OBJECT-TYPE
    SYNTAX      H3cDot11SecIEStatusType
    MAX-ACCESS  read-only
    STATUS      current
    DESCRIPTION
        "Represents the security Information element for this station."
    ::= { h3cDot11StationAssociateEntry 27 }

h3cDot11StationUpTimeTicks OBJECT-TYPE
    SYNTAX      TimeTicks
    MAX-ACCESS  read-only
    STATUS      current
    DESCRIPTION
        "Represents how long this station has been associated
         with this device."
    ::= { h3cDot11StationAssociateEntry 28 }

h3cDot11StationRadioMode2 OBJECT-TYPE
    SYNTAX      H3cDot11RadioType2
    MAX-ACCESS  read-only
    STATUS      current
    DESCRIPTION
        "Represents which radio type supported by the station.
        The WLAN system support the following possible radio types.
        dot11a(1),
        dot11b(2),
        dot11g(4),
        dot11an(8),
        dot11gn(16)
        For a station,it could support only one radio type at
        the same time."
    ::= { h3cDot11StationAssociateEntry 29 }

h3cDot11StationAssTime OBJECT-TYPE
    SYNTAX      DateAndTime
    MAX-ACCESS  read-only
    STATUS      current
    DESCRIPTION
        "Represents the time at which the station connected."
    ::= { h3cDot11StationAssociateEntry 30 }
-- *****************************************************************************
-- *  End of h3cDot11StaAssociateTable Definition
-- *****************************************************************************

-- *****************************************************************************
-- *  h3cDot11StationAPRelationTable Definition
-- *****************************************************************************
h3cDot11StationAPRelationTable OBJECT-TYPE
    SYNTAX      SEQUENCE OF H3cDot11StationAPRelationEntry
    MAX-ACCESS  not-accessible
    STATUS      current
    DESCRIPTION
        "This table contains relation-ship between station, AP, Radio
        and WLANID, and the detailed information of station is kept in
        the h3cDot11StaAssociateTable table."
    ::= { h3cDot11StationMtGroup 2 }

h3cDot11StationAPRelationEntry OBJECT-TYPE
    SYNTAX      H3cDot11StationAPRelationEntry
    MAX-ACCESS  not-accessible
    STATUS      current
    DESCRIPTION
        "Each entry contains relation-ship information
        with AP, Radio and WLANID of each station."
    INDEX
        {
            h3cDot11StationMAC
        }
    ::= { h3cDot11StationAPRelationTable 1 }

H3cDot11StationAPRelationEntry ::= SEQUENCE
    {
        h3cDot11CurrAPID       H3cDot11ObjectIDType,
        h3cDot11CurrRadioID    H3cDot11RadioScopeType,
        h3cDot11CurrWlanID     Integer32
    }

h3cDot11CurrAPID OBJECT-TYPE
    SYNTAX      H3cDot11ObjectIDType
    MAX-ACCESS  read-only
    STATUS      current
    DESCRIPTION
        "To uniquely identify each AP, and relation-ship
        between h3cDot11CurrAPID and AP device will be static."
    ::= { h3cDot11StationAPRelationEntry 1 }

h3cDot11CurrRadioID OBJECT-TYPE
    SYNTAX      H3cDot11RadioScopeType
    MAX-ACCESS  read-only
    STATUS      current
    DESCRIPTION
        "Represents each radio."
    ::= { h3cDot11StationAPRelationEntry 2 }

h3cDot11CurrWlanID OBJECT-TYPE
    SYNTAX      Integer32
    MAX-ACCESS  read-only
    STATUS      current
    DESCRIPTION
        "Represents WLAN ID of the BSS the station associated to."
    ::= { h3cDot11StationAPRelationEntry 3 }
-- *****************************************************************************
-- *  End of h3cDot11StationAPRelationTable Definition
-- *****************************************************************************

-- *****************************************************************************
-- *  h3cDot11StationStatisTable Definition
-- *****************************************************************************
h3cDot11StationStatisTable OBJECT-TYPE
    SYNTAX      SEQUENCE OF H3cDot11StationStatisEntry
    MAX-ACCESS  not-accessible
    STATUS      current
    DESCRIPTION
        "This table contains statistics and status of all
        stations in the h3cDot11StaAssociateTable."
    ::= { h3cDot11StationMtGroup 3 }

h3cDot11StationStatisEntry OBJECT-TYPE
    SYNTAX      H3cDot11StationStatisEntry
    MAX-ACCESS  not-accessible
    STATUS      current
    DESCRIPTION
        "This entry contains statistics and status for each station."
    INDEX
        {
            h3cDot11StationMAC
        }
    ::= { h3cDot11StationStatisTable 1 }

H3cDot11StationStatisEntry ::= SEQUENCE
    {
        h3cDot11StationRxFrameCnt        Counter32,
        h3cDot11StationTxFrameCnt        Counter32,
        h3cDot11StationDropFrameCnt      Counter32,
        h3cDot11StationRxFrameBytes      Counter64,
        h3cDot11StationTxFrameBytes      Counter64,
        h3cDot11StationDropFrameBytes    Counter64,
        h3cDot11StationRxRetryPkts       Counter32,
        h3cDot11StationTxRetryPkts       Counter32,
        h3cDot11StationRxRetryBytes      Counter64,
        h3cDot11StationTxRetryBytes      Counter64,
        h3cDot11StationThroughput        Counter64,
        h3cDot11StationSuccessTxCnt      Counter32,
        h3cDot11StationSuccessTxDataCnt  Counter32,
        h3cDot11StationRxDataFrameCnt    Counter32,
        h3cDot11StationTxDataFrameCnt    Counter32,
        h3cDot11StationRxDataFrameBytes  Counter64,
        h3cDot11StationTxDataFrameBytes  Counter64,
        h3cDot11StationRxFragCnt         Counter32,
        h3cDot11StaRxErrDataFrameCnt     Counter64,
        h3cDot11StaTxRetryDataFrameCnt   Counter64,
        h3cDot11StaTxDataRatePkts        OCTET STRING,
        h3cDot11StaRxDataRatePkts        OCTET STRING,
        h3cDot11StaTxSignalStrengthPkts  OCTET STRING
    }

h3cDot11StationRxFrameCnt OBJECT-TYPE
    SYNTAX      Counter32
    MAX-ACCESS  read-only
    STATUS      current
    DESCRIPTION
        "Represents the count of frames that are received by AP from station."
    ::= { h3cDot11StationStatisEntry 1 }

h3cDot11StationTxFrameCnt OBJECT-TYPE
    SYNTAX      Counter32
    MAX-ACCESS  read-only
    STATUS      current
    DESCRIPTION
        "Represents the count of frames that are sent to station from AP."
    ::= { h3cDot11StationStatisEntry 2 }

h3cDot11StationDropFrameCnt OBJECT-TYPE
    SYNTAX      Counter32
    MAX-ACCESS  read-only
    STATUS      current
    DESCRIPTION
        "Represents the count of frames that are dropped."
    ::= { h3cDot11StationStatisEntry 3 }

h3cDot11StationRxFrameBytes OBJECT-TYPE
    SYNTAX      Counter64
    UNITS       "bytes"
    MAX-ACCESS  read-only
    STATUS      current
    DESCRIPTION
        "Represents the count of bytes that are received by AP from station."
    ::= { h3cDot11StationStatisEntry 4 }

h3cDot11StationTxFrameBytes OBJECT-TYPE
    SYNTAX      Counter64
    UNITS       "bytes"
    MAX-ACCESS  read-only
    STATUS      current
    DESCRIPTION
        "Represents the count of bytes that are sent to station from AP."
    ::= { h3cDot11StationStatisEntry 5 }

h3cDot11StationDropFrameBytes OBJECT-TYPE
    SYNTAX      Counter64
    UNITS       "bytes"
    MAX-ACCESS  read-only
    STATUS      current
    DESCRIPTION
        "Represents how many bytes are dropped."
    ::= { h3cDot11StationStatisEntry 6 }

h3cDot11StationRxRetryPkts OBJECT-TYPE
    SYNTAX      Counter32
    MAX-ACCESS  read-only
    STATUS      current
    DESCRIPTION
        "Represents the count of frames that are retransmitted to AP from station."
    ::= { h3cDot11StationStatisEntry 7 }

h3cDot11StationTxRetryPkts OBJECT-TYPE
    SYNTAX      Counter32
    MAX-ACCESS  read-only
    STATUS      current
    DESCRIPTION
        "Represents the count of frames that are retransmitted to station from AP."
    ::= { h3cDot11StationStatisEntry 8 }

h3cDot11StationRxRetryBytes OBJECT-TYPE
    SYNTAX      Counter64
    MAX-ACCESS  read-only
    STATUS      current
    DESCRIPTION
        "Represents the count of bytes that are retransmitted to AP from station."
    ::= { h3cDot11StationStatisEntry 9 }

h3cDot11StationTxRetryBytes OBJECT-TYPE
    SYNTAX      Counter64
    MAX-ACCESS  read-only
    STATUS      current
    DESCRIPTION
        "Represents the count of bytes that are retransmitted to station from AP."
    ::= { h3cDot11StationStatisEntry 10 }

h3cDot11StationThroughput OBJECT-TYPE
    SYNTAX      Counter64
    UNITS       "bytes"
    MAX-ACCESS  read-only
    STATUS      current
    DESCRIPTION
        "Represents how many payload bytes of data frame are sent and received
         by station."
    ::= { h3cDot11StationStatisEntry 11 }

h3cDot11StationSuccessTxCnt OBJECT-TYPE
    SYNTAX      Counter32
    MAX-ACCESS  read-only
    STATUS      current
    DESCRIPTION
        "Represents how many frames have been successfully sent to station."
    ::= { h3cDot11StationStatisEntry 12 }

h3cDot11StationSuccessTxDataCnt  OBJECT-TYPE
    SYNTAX      Counter32
    MAX-ACCESS  read-only
    STATUS      current
    DESCRIPTION
        "Represents how many data frames have been successfully sent to
        station."
    ::= { h3cDot11StationStatisEntry 13 }

h3cDot11StationRxDataFrameCnt OBJECT-TYPE
    SYNTAX      Counter32
    MAX-ACCESS  read-only
    STATUS      current
    DESCRIPTION
        "Represents how many data frames have been received from station."
    ::= { h3cDot11StationStatisEntry 14 }

h3cDot11StationTxDataFrameCnt OBJECT-TYPE
    SYNTAX      Counter32
    MAX-ACCESS  read-only
    STATUS      current
    DESCRIPTION
        "Represents how many data frames have been sent to station."
    ::= { h3cDot11StationStatisEntry 15 }

h3cDot11StationRxDataFrameBytes OBJECT-TYPE
    SYNTAX      Counter64
    MAX-ACCESS  read-only
    STATUS      current
    DESCRIPTION
        "Represents how many bytes of data frames have been received
        from station."
    ::= { h3cDot11StationStatisEntry 16 }

h3cDot11StationTxDataFrameBytes OBJECT-TYPE
    SYNTAX      Counter64
    MAX-ACCESS  read-only
    STATUS      current
    DESCRIPTION
        "Represents how many bytes of data frames have been sent to
        station."
    ::= { h3cDot11StationStatisEntry 17 }

h3cDot11StationRxFragCnt  OBJECT-TYPE
    SYNTAX      Counter32
    MAX-ACCESS  read-only
    STATUS      current
    DESCRIPTION
        "Represents the number of fragmented data frames that received
         from station."
    ::= { h3cDot11StationStatisEntry 18 }

h3cDot11StaRxErrDataFrameCnt  OBJECT-TYPE
        SYNTAX      Counter64
        MAX-ACCESS  read-only
        STATUS      current
        DESCRIPTION
                "Represents the count of error data frames that are received by AP
                 from station."
    ::= { h3cDot11StationStatisEntry 19 }

h3cDot11StaTxRetryDataFrameCnt  OBJECT-TYPE
        SYNTAX      Counter64
        MAX-ACCESS  read-only
        STATUS      current
        DESCRIPTION
                "Represents the count of data frames that are retransmitted to station
                 from AP."
    ::= { h3cDot11StationStatisEntry 20 }
h3cDot11StaTxDataRatePkts  OBJECT-TYPE
        SYNTAX      OCTET STRING
        MAX-ACCESS  read-only
        STATUS      current
        DESCRIPTION
                "Represents how many data frames of each rate have been received
                from station."
    ::= { h3cDot11StationStatisEntry 21 }

h3cDot11StaRxDataRatePkts  OBJECT-TYPE
        SYNTAX      OCTET STRING
        MAX-ACCESS  read-only
        STATUS      current
        DESCRIPTION
                "Represents how many data frames of each rate have been sent to
                station."
    ::= { h3cDot11StationStatisEntry 22 }

h3cDot11StaTxSignalStrengthPkts  OBJECT-TYPE
        SYNTAX      OCTET STRING
        MAX-ACCESS  read-only
        STATUS      current
        DESCRIPTION
                "Represents how many data frames of different signal strength have been
                 received from station."
    ::= { h3cDot11StationStatisEntry 23 }
-- *****************************************************************************
-- *  End of h3cDot11StationStatisTable Definition
-- *****************************************************************************

-- *****************************************************************************
-- *     Notifications OF h3cDot11StationNotifyGroup
-- *****************************************************************************
-- 802.11 MAC Notification

h3cDot11StationTraps OBJECT IDENTIFIER    ::= { h3cDot11StationNotifyGroup 0 }

h3cDot11StationMICErrorTrap NOTIFICATION-TYPE
    OBJECTS
        {
            h3cDot11CurrAPID,
            h3cDot11CurrRadioID,
            h3cDot11StationTrapBSSID,
            h3cDot11StationSSIDName,
            h3cDot11StationTrapStaMAC
        }
    STATUS      current
    DESCRIPTION
        "This notification is to indicate the occurrence of a MIC
        failure in a certain station."
    ::= { h3cDot11StationTraps 1 }

h3cDot11StationAuthenErrorTrap NOTIFICATION-TYPE
    OBJECTS
        {
            h3cDot11CurrAPID,
            h3cDot11CurrRadioID,
            h3cDot11StationTrapBSSID,
            h3cDot11StationSSIDName,
            h3cDot11StationTrapStaMAC,
            h3cDot11StationAuthenMode,
            h3cDot11StationAKMMode
        }
    STATUS      current
    DESCRIPTION
        "This notification is to indicate which station happened
        authentication failure."
    ::= { h3cDot11StationTraps 2 }

h3cDot11StationAuthorFailTrap NOTIFICATION-TYPE
    OBJECTS
        {
            h3cDot11StationUserName,
            h3cDot11StationTrapStaMAC,
            h3cDot11CurrRadioID,
            h3cDot11StationSSIDName,
            h3cDot11StationAuthorFailCause,
            h3cDot11StationFailCauseDesc,
            h3cDot11CurrAPID,
            h3cDot11StationBSSID,
            h3cDot11StationAuthMode
        }
    STATUS      current
    DESCRIPTION
        "This trap is sent if a station authorization fails."
    ::= { h3cDot11StationTraps 3 }

h3cDot11StationAssocFailTrap NOTIFICATION-TYPE
    OBJECTS
        {
            h3cDot11StationTrapStaMAC,
            h3cDot11CurrRadioID,
            h3cDot11StationSSIDName,
            h3cDot11StationAssocFailCause,
            h3cDot11StationFailCauseDesc,
            h3cDot11CurrAPID
        }
    STATUS      current
    DESCRIPTION
        "This trap is sent if a station association fails."
    ::= { h3cDot11StationTraps 4 }

h3cDot11StationDeAssocTrap NOTIFICATION-TYPE
    OBJECTS
        {
            h3cDot11StationUserName,
            h3cDot11StationTrapStaMAC,
            h3cDot11StationVlanId,
            h3cDot11CurrRadioID,
            h3cDot11StationSSIDName,
            h3cDot11StationSessionDuration,
            h3cDot11CurrAPID,
            h3cDot11StationAPName,
            h3cDot11StationBSSID
        }
    STATUS      current
    DESCRIPTION
        "This trap is sent if a station de-association occurred."
    ::= { h3cDot11StationTraps 5 }

h3cDot11StationAuthorSuccTrap NOTIFICATION-TYPE
    OBJECTS
        {
            h3cDot11StationUserName,
            h3cDot11StationTrapStaMAC,
            h3cDot11StationVlanId,
            h3cDot11StationSessionStartTime,
            h3cDot11CurrRadioID,
            h3cDot11StationSSIDName,
            h3cDot11CurrAPID,
            h3cDot11StationAPName,
            h3cDot11StationBSSID
        }
    STATUS      current
    DESCRIPTION
        "This trap is sent when a station is authorized successfully."
    ::= { h3cDot11StationTraps 6 }

h3cDot11StationRoamingTrap NOTIFICATION-TYPE
    OBJECTS
        {
            h3cDot11CurrAPID,
            h3cDot11StationUserName,
            h3cDot11StationTrapStaMAC,
            h3cDot11StationVlanId,
            h3cDot11StationRoamingTime,
            h3cDot11CurrRadioID,
            h3cDot11StationSSIDName,
            h3cDot11StationACIPAddress,
            h3cDot11StationACIPv6Add
        }
    STATUS      current
    DESCRIPTION
        "This trap is sent when a station roamed successfully."
    ::= { h3cDot11StationTraps 7 }

h3cDot11StationDisconnectTrap NOTIFICATION-TYPE
    OBJECTS
        {
            h3cDot11StationAPName,
            h3cDot11StationBSSID,
            h3cDot11StationSSIDName,
            h3cDot11StationSessionDuration,
            h3cDot11StationVlanId,
            h3cDot11CurrAPID,
            h3cDot11CurrRadioID,
            h3cDot11StaDisconnectReason,
            h3cDot11StationTrapStaMAC
        }
    STATUS      current
    DESCRIPTION
        "This notification is sent when station disconnects with AP."
    ::= { h3cDot11StationTraps 8 }

h3cDot11UserDisconnectTrap NOTIFICATION-TYPE
    OBJECTS
        {
            h3cDot11StationAPName,
            h3cDot11StationTrapStaMAC,
            h3cDot11UserName
        }
    STATUS      current
    DESCRIPTION
        "This notification is sent when user disconnects with AP."
    ::= { h3cDot11StationTraps 9 }

-- 802.11 station Notify variable object

        h3cDot11StationTrapVarObjects OBJECT IDENTIFIER
    ::= { h3cDot11StationNotifyGroup 1 }

h3cDot11StationTrapBSSID OBJECT-TYPE
    SYNTAX      MacAddress
    MAX-ACCESS  accessible-for-notify
    STATUS      current
    DESCRIPTION
        "Represents on which BSSID of AP the event happened."
    ::= { h3cDot11StationTrapVarObjects 1 }

h3cDot11StationTrapStaMAC OBJECT-TYPE
    SYNTAX      MacAddress
    MAX-ACCESS  accessible-for-notify
    STATUS      current
    DESCRIPTION
        "Represents the MAC address of station which happened message
        integrity check (MIC) errors."
    ::= { h3cDot11StationTrapVarObjects 2 }

h3cDot11StationSessionStartTime OBJECT-TYPE
    SYNTAX      DateAndTime
    MAX-ACCESS  accessible-for-notify
    STATUS      current
    DESCRIPTION
        "Represents the time at which the station connected."
    ::= { h3cDot11StationTrapVarObjects 3 }

h3cDot11StationAssocFailCause OBJECT-TYPE
    SYNTAX      H3cDot11AssocFailType
    MAX-ACCESS  accessible-for-notify
    STATUS      current
    DESCRIPTION
        "Represents the cause of the station association failure."
    ::= { h3cDot11StationTrapVarObjects 4 }

h3cDot11StationAuthorFailCause OBJECT-TYPE
    SYNTAX      H3cDot11AuthorFailType
    MAX-ACCESS  accessible-for-notify
    STATUS      current
    DESCRIPTION
        "Represents the cause of the station authorization failure."
    ::= { h3cDot11StationTrapVarObjects 5 }

h3cDot11StationFailCauseDesc OBJECT-TYPE
    SYNTAX      OCTET STRING(SIZE(0..255))
    MAX-ACCESS  accessible-for-notify
    STATUS      current
    DESCRIPTION
        "Represents the failure description of the station."
    ::= { h3cDot11StationTrapVarObjects 6 }

h3cDot11StationSessionDuration OBJECT-TYPE
    SYNTAX      Unsigned32
    UNITS       "second"
    MAX-ACCESS  accessible-for-notify
    STATUS      current
    DESCRIPTION
        "Represents the duration of the station sesssion."
    ::= { h3cDot11StationTrapVarObjects 7 }

h3cDot11StationRoamingTime OBJECT-TYPE
    SYNTAX      Unsigned32
    UNITS       "second"
    MAX-ACCESS  accessible-for-notify
    STATUS      current
    DESCRIPTION
        "Represents the time at which the station roamed."
    ::= { h3cDot11StationTrapVarObjects 8 }

h3cDot11StationACIPAddress OBJECT-TYPE
    SYNTAX      IpAddress
    MAX-ACCESS  accessible-for-notify
    STATUS      current
    DESCRIPTION
        "For roam-in station, it represents the ip address of home AC.
         For roam-out station, it represents the ip address of foreign AC."
    ::= { h3cDot11StationTrapVarObjects 9 }

h3cDot11StationAPName OBJECT-TYPE
    SYNTAX      OCTET STRING
    MAX-ACCESS  accessible-for-notify
    STATUS      current
    DESCRIPTION
        "Name of the AP which the station connects to."
    ::= { h3cDot11StationTrapVarObjects 10 }

h3cDot11StationBSSID OBJECT-TYPE
    SYNTAX      MacAddress
    MAX-ACCESS  accessible-for-notify
    STATUS      current
    DESCRIPTION
        "BSSID which the station connects to."
    ::= { h3cDot11StationTrapVarObjects 11 }

h3cDot11StaDisconnectReason OBJECT-TYPE
    SYNTAX      OCTET STRING
    MAX-ACCESS  accessible-for-notify
    STATUS      current
    DESCRIPTION
        "Reason why the station disconnects with the AP."
    ::= { h3cDot11StationTrapVarObjects 12 }

h3cDot11StationAuthMode OBJECT-TYPE
    SYNTAX      INTEGER
    {
        opensystem(1),
        sharedkey(2)
    }
    MAX-ACCESS  accessible-for-notify
    STATUS      current
    DESCRIPTION
        "Represents station's authentication mode."
    ::= { h3cDot11StationTrapVarObjects 13 }

h3cDot11StationACIPv6Add OBJECT-TYPE
    SYNTAX      OCTET STRING
    MAX-ACCESS  accessible-for-notify
    STATUS      current
    DESCRIPTION
        "For roam-in station, it represents the IPv6 address of home AC.
         For roam-out station, it represents the IPv6 address of foreign AC."
    ::= { h3cDot11StationTrapVarObjects 14 }

h3cDot11UserName OBJECT-TYPE
    SYNTAX      OCTET STRING
    MAX-ACCESS  accessible-for-notify
    STATUS      current
    DESCRIPTION
        "Represents the user name."
    ::= { h3cDot11StationTrapVarObjects 15 }

-- *****************************************************************************
-- *     End OF NotifyGroup
-- *****************************************************************************
END
