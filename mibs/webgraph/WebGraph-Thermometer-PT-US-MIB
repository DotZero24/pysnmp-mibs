WebGraph-Thermometer-PT-US-MIB DEFINITIONS ::= BEGIN
----------------------------------------------------------------
-- Revison: 1.36
----------------------------------------------------------------
-- 09.03.2017 	New: wtWebioAn1GraphNtcAlarmSensorLostSelection
--		     		 wtWebioAn1GraphNtcAlarmLimitWindow
----------------------------------------------------------------
-- Revison: 1.35
----------------------------------------------------------------
-- 09.11.2016 	New: wtWebioAn1GraphPtMQTT group
--		     HTTP Request, MQTT Alarm, REST
----------------------------------------------------------------
-- Revison: 1.34
----------------------------------------------------------------
-- 24.09.2015 	Anpassung an neue Navigation (__JB__)
--
----------------------------------------------------------------
-- Revison: 1.33
----------------------------------------------------------------
-- 15.07.2015 	Changes for new Navigation (__JB__)
----------------------------------------------------------------
-- Revison: 1.32
----------------------------------------------------------------
-- 14.09.2014 	Neu: Reports
--
----------------------------------------------------------------
-- Revison: 1.31
----------------------------------------------------------------
-- 14.01.2014 	New: Language select
--
----------------------------------------------------------------
-- Revison: 1.30
----------------------------------------------------------------
-- 22.06.2010 	Output with decimal point
--
----------------------------------------------------------------
-- Revison: 1.29
----------------------------------------------------------------
-- 18.12.2008 	57616
--		Web-Thermograph Relais
----------------------------------------------------------------
-- Revison: 1.28
----------------------------------------------------------------
-- 09.05.2007 	Webio
--		New Graphics java script base parameter
----------------------------------------------------------------
-- Revison: 1.27
----------------------------------------------------------------
-- 09.11.2006 	Webio
--		DHCP enable
--		New: wtWebioAn1GraphPtAlarmDeltaTemp
----------------------------------------------------------------
-- Revison: 1.26
----------------------------------------------------------------
-- 28.06.2006 	New: Community String Trap
--
----------------------------------------------------------------
-- Revison: 1.25
----------------------------------------------------------------
-- 22.05.2006 	Table entry names changed
--
----------------------------------------------------------------
-- Revison: 1.24
----------------------------------------------------------------
-- 26.07.2005 	#57605, WebGraph Thermometer
--		CRON timer function
----------------------------------------------------------------
-- Revison: 1.23
----------------------------------------------------------------
-- 14.07.2005 	#57605, WebGraph Thermometer
--		FTP functions
----------------------------------------------------------------
-- Revison: 1.22
----------------------------------------------------------------
-- 02.06.2005 	#57605, WebGraph Thermometer
--		Trap NMS annotations
----------------------------------------------------------------
-- Revison: 1.21
----------------------------------------------------------------
-- 19.04.2005 	#57605, WebGraph Themometer
--		Mail Authentication
----------------------------------------------------------------
-- Revison: 1.20
----------------------------------------------------------------
-- 05.11.2004 	#57605, WebGraph
--		New: Syslog
--
----------------------------------------------------------------
-- Revison: 1.19
----------------------------------------------------------------
-- 27.09.2004 	#57601/3/4, Webio Digital
--		New:
--		     Entry AlarmHysteresis corrected
----------------------------------------------------------------
-- Revison: 1.18
----------------------------------------------------------------
-- 21.07.2004 	#57601/3/4, Webio Anx
--		New:
--		     Diagnosis
----------------------------------------------------------------
-- Revison: 1.17
----------------------------------------------------------------
-- 28.06.2004 	#57630/1/2, Webio Digital
--		Neu: Puls Mode
----------------------------------------------------------------
-- Revison: 1.16
----------------------------------------------------------------
-- 16.04.2004 	New: #57632, Webio Digital EA24x24
--
--		#57630/1, Webio Digital EA12x12
--		New:
--			wtWebioAn1GraphPtInputCounterClear
----------------------------------------------------------------
-- Revison: 1.15
----------------------------------------------------------------
-- 27.02.2004 	#57630/1, Webio Digital EA12x12
--		New:
--		Length changed to 32 Bit:
--			wtWebioEA12x12InputValue
--			wtWebioEA12x12OutputValue
--			wtWebioEA12x12LoadControlView
--			wtWebioEA12x12LCShutDownView
--			wtWebioEA12x12SetOutput
--			wtWebioEA12x12AlarmInputTrigger
--			wtWebioEA12x12AlarmOutputTrigger
--			wtWebioEA12x12PortOutputSafetyState
----------------------------------------------------------------
-- Revison: 1.14
----------------------------------------------------------------
-- 16.02.2004 	#57630/1, Webio Digital EA12x12
--		New:
--		Text: Location, Contact
--		SNMP: ColdStart, WarmStart, ComunityString Read/RW
--		Alarm: ColdStart / WarmStart trigger
--
-- 	 	#57601, 1xWebThermometer
--		#57603, 2xWebThermometer
--		#57604, 8xWebThermometer
--		New:
--		Alarm Hysteresis
--		Alarm Clear Traps and Mails
----------------------------------------------------------------
-- Revison: 1.13
----------------------------------------------------------------
-- 05.02.2004 	#57601, 1xWebThermometer
--		#57603, 2xWebThermometer
--		#57604, 8xWebThermometer
--		New:
--		Text: Location, Contact
--		SNMP: ColdStart, WarmStart, ComunityString Read/RW
--		Alarm: ColdStart / WarmStart trigger
----------------------------------------------------------------
-- Revison: 1.12
----------------------------------------------------------------
-- 05.11.2003 	#57601, 1xWebThermometer
--		#57603, 2xWebThermometer
--		#57604, 8xWebThermometer
--		New features:
--		Mail  : Option CSV attachment
--		Port  : Offset calibration
--		Alarm : TCP Client mode
----------------------------------------------------------------
-- Revison: 1.11
----------------------------------------------------------------
-- 28.10.2003 	#57630/1, Webio Digital EA12x12
--		New features:
--		Alarm : TCP Client mode
--		Inputs: Puls filter
----------------------------------------------------------------
-- Revison: 1.10
----------------------------------------------------------------
-- 22.07.2003 	#57630, Webio Digital EA12x12
--		New navigation tree, new binary modes
--
----------------------------------------------------------------
-- Revison: 1.09
----------------------------------------------------------------
-- 24.03.2003 	Trap Enterprise (Type 1, 2) corrected
----------------------------------------------------------------
-- Revison: 1.08
----------------------------------------------------------------
-- 04.03.2003 	reconciled the language versions DE/US
----------------------------------------------------------------
-- Revison: 1.07
----------------------------------------------------------------
-- 25.02.2003 	Correction: wtWebioEA12x12LoadControl
----------------------------------------------------------------
-- Revison: 1.06
----------------------------------------------------------------
-- 24.02.2003 	New:
--		#57630, Webio EA12x12, LoadControl Group
--		Correction: Trap variable names
----------------------------------------------------------------
-- Revison: 1.05
----------------------------------------------------------------
-- 21.01.2003 	New:
--		#57630, Webio EA12x12
----------------------------------------------------------------
-- Revison: 1.04
----------------------------------------------------------------
-- 02.01.2003 	New:
--		#57601, 1xWebThermometer
--		#57603, 2xWebThermometer, 8 alarms
----------------------------------------------------------------
-- Revison: 1.03
----------------------------------------------------------------
-- 21.11.2002 	New:
--		#57604, 2xWebThermometer, BOOTP, StartupSite
--		#57603, 8xWebThermometer, BOOTP, StartupSite
----------------------------------------------------------------
-- Revison: 1.02
----------------------------------------------------------------
-- 26.07.2002 	New:
--		#57604, 2xWebThermometer
--		#57603, 8xWebThermometer
--


    IMPORTS

    OBJECT-TYPE                                        FROM RFC-1212
    TRAP-TYPE                                          FROM RFC-1215
    DisplayString, PhysAddress                         FROM RFC1213-MIB
    enterprises, TimeTicks, IpAddress, NetworkAddress  FROM RFC1155-SMI;


--    IpAddress ::=
--        [APPLICATION 0]
--            IMPLICIT OCTET STRING (SIZE (4))
--    Counter ::=
--        [APPLICATION 1]
--            IMPLICIT INTEGER (0..4294967295)
--    Gauge ::=
--        [APPLICATION 2]
--            IMPLICIT INTEGER (0..4294967295)
--    TimeTicks ::=
--        [APPLICATION 3]
--            IMPLICIT INTEGER (0..4294967295)


--    DisplayString ::= OCTET STRING
--    PhysAddress   ::= OCTET STRING

--    internet         OBJECT IDENTIFIER ::= { iso org(3) dod(6) 1 }
--    privat           OBJECT IDENTIFIER ::= { internet 4 }
--    enterprises      OBJECT IDENTIFIER ::= { privat 1 }



--  Wiesemann & Theis Com-Server MIB

    wut                			OBJECT IDENTIFIER ::= { enterprises 5040 }
    wtComServer        			OBJECT IDENTIFIER ::= { wut 1 }
    wtWebio            			OBJECT IDENTIFIER ::= { wtComServer 2 }

--  wtWebio Tree

    wtWebioAn1GraphPt    		OBJECT IDENTIFIER ::= { wtWebio 39 }
    wtWebioAn1GraphPtSw    		OBJECT IDENTIFIER ::= { wtWebio 40 }

--  wtWebioAn1GraphPt Tree

    wtWebioAn1GraphPtTemp      		OBJECT IDENTIFIER ::= { wtWebioAn1GraphPt 1 }
    wtWebioAn1GraphPtSessCntrl 		OBJECT IDENTIFIER ::= { wtWebioAn1GraphPt 2 }
    wtWebioAn1GraphPtConfig    		OBJECT IDENTIFIER ::= { wtWebioAn1GraphPt 3 }
    wtWebioAn1GraphPtDiag    		OBJECT IDENTIFIER ::= { wtWebioAn1GraphPt 4 }

--  wtWebioAn1GraphPtConfig Tree

    wtWebioAn1GraphPtDevice    		OBJECT IDENTIFIER ::= { wtWebioAn1GraphPtConfig 1 }
    wtWebioAn1GraphPtPorts     		OBJECT IDENTIFIER ::= { wtWebioAn1GraphPtConfig 2 }
    wtWebioAn1GraphPtManufact  		OBJECT IDENTIFIER ::= { wtWebioAn1GraphPtConfig 3 }

--  wtWebioAn1GraphPtDevice Tree

    wtWebioAn1GraphPtText		OBJECT IDENTIFIER ::= { wtWebioAn1GraphPtDevice 1 }
    wtWebioAn1GraphPtTimeDate 		OBJECT IDENTIFIER ::= { wtWebioAn1GraphPtDevice 2 }
    wtWebioAn1GraphPtBasic		OBJECT IDENTIFIER ::= { wtWebioAn1GraphPtDevice 3 }
    wtWebioAn1GraphPtDatalogger		OBJECT IDENTIFIER ::= { wtWebioAn1GraphPtDevice 4 }
    wtWebioAn1GraphPtAlarm		OBJECT IDENTIFIER ::= { wtWebioAn1GraphPtDevice 5 }
    wtWebioAn1GraphPtGraphics 		OBJECT IDENTIFIER ::= { wtWebioAn1GraphPtDevice 6 }

--  wtWebioAn1GraphPtTimeDate Tree

    wtWebioAn1GraphPtTimeZone		OBJECT IDENTIFIER ::= { wtWebioAn1GraphPtTimeDate 1 }
    wtWebioAn1GraphPtTimeServer		OBJECT IDENTIFIER ::= { wtWebioAn1GraphPtTimeDate 2 }
    wtWebioAn1GraphPtDeviceClock	OBJECT IDENTIFIER ::= { wtWebioAn1GraphPtTimeDate 3 }

--  wtWebioAn1GraphPtBasic Tree

    wtWebioAn1GraphPtNetwork		OBJECT IDENTIFIER ::= { wtWebioAn1GraphPtBasic 1 }
    wtWebioAn1GraphPtHTTP		OBJECT IDENTIFIER ::= { wtWebioAn1GraphPtBasic 2 }
    wtWebioAn1GraphPtMail		OBJECT IDENTIFIER ::= { wtWebioAn1GraphPtBasic 3 }
    wtWebioAn1GraphPtSNMP		OBJECT IDENTIFIER ::= { wtWebioAn1GraphPtBasic 4 }
    wtWebioAn1GraphPtUDP		OBJECT IDENTIFIER ::= { wtWebioAn1GraphPtBasic 5 }
    wtWebioAn1GraphPtSyslog		OBJECT IDENTIFIER ::= { wtWebioAn1GraphPtBasic 6 }
    wtWebioAn1GraphPtFTP		OBJECT IDENTIFIER ::= { wtWebioAn1GraphPtBasic 7 }
    wtWebioAn1GraphPtLanguage		OBJECT IDENTIFIER ::= { wtWebioAn1GraphPtBasic 9 }
    wtWebioAn1GraphPtMQTT			OBJECT IDENTIFIER ::= { wtWebioAn1GraphPtBasic 12 }
    wtWebioAn1GraphPtREST			OBJECT IDENTIFIER ::= { wtWebioAn1GraphPtBasic 13 }


 --  wtWebioAn1GraphPtGraphics Tree

    wtWebioAn1GraphPtGraphicsBase 	OBJECT IDENTIFIER ::= { wtWebioAn1GraphPtGraphics 1 }
    wtWebioAn1GraphPtGraphicsSelect 	OBJECT IDENTIFIER ::= { wtWebioAn1GraphPtGraphics 2 }
    wtWebioAn1GraphPtGraphicsScale 	OBJECT IDENTIFIER ::= { wtWebioAn1GraphPtGraphics 3 }

------------------------

--  wtWebioAn1GraphPtSw Tree

    wtWebioAn1GraphPtSwTemp      	OBJECT IDENTIFIER ::= { wtWebioAn1GraphPtSw 1 }
    wtWebioAn1GraphPtSwSessCntrl 	OBJECT IDENTIFIER ::= { wtWebioAn1GraphPtSw 2 }
    wtWebioAn1GraphPtSwConfig    	OBJECT IDENTIFIER ::= { wtWebioAn1GraphPtSw 3 }
    wtWebioAn1GraphPtSwDiag    		OBJECT IDENTIFIER ::= { wtWebioAn1GraphPtSw 4 }

--  wtWebioAn1GraphPtSwConfig Tree

    wtWebioAn1GraphPtSwDevice    	OBJECT IDENTIFIER ::= { wtWebioAn1GraphPtSwConfig 1 }
    wtWebioAn1GraphPtSwPorts     	OBJECT IDENTIFIER ::= { wtWebioAn1GraphPtSwConfig 2 }
    wtWebioAn1GraphPtSwManufact  	OBJECT IDENTIFIER ::= { wtWebioAn1GraphPtSwConfig 3 }

--  wtWebioAn1GraphPtSwDevice Tree

    wtWebioAn1GraphPtSwText		OBJECT IDENTIFIER ::= { wtWebioAn1GraphPtSwDevice 1 }
    wtWebioAn1GraphPtSwTimeDate 	OBJECT IDENTIFIER ::= { wtWebioAn1GraphPtSwDevice 2 }
    wtWebioAn1GraphPtSwBasic		OBJECT IDENTIFIER ::= { wtWebioAn1GraphPtSwDevice 3 }
    wtWebioAn1GraphPtSwDatalogger	OBJECT IDENTIFIER ::= { wtWebioAn1GraphPtSwDevice 4 }
    wtWebioAn1GraphPtSwAlarm		OBJECT IDENTIFIER ::= { wtWebioAn1GraphPtSwDevice 5 }
    wtWebioAn1GraphPtSwGraphics 	OBJECT IDENTIFIER ::= { wtWebioAn1GraphPtSwDevice 6 }
    wtWebioAn1GraphPtSwReport		OBJECT IDENTIFIER ::= { wtWebioAn1GraphPtSwDevice 7 }

--  wtWebioAn1GraphPtSwTimeDate Tree

    wtWebioAn1GraphPtSwTimeZone		OBJECT IDENTIFIER ::= { wtWebioAn1GraphPtSwTimeDate 1 }
    wtWebioAn1GraphPtSwTimeServer	OBJECT IDENTIFIER ::= { wtWebioAn1GraphPtSwTimeDate 2 }
    wtWebioAn1GraphPtSwDeviceClock	OBJECT IDENTIFIER ::= { wtWebioAn1GraphPtSwTimeDate 3 }

--  wtWebioAn1GraphPtSwBasic Tree

    wtWebioAn1GraphPtSwNetwork		OBJECT IDENTIFIER ::= { wtWebioAn1GraphPtSwBasic 1 }
    wtWebioAn1GraphPtSwHTTP		OBJECT IDENTIFIER ::= { wtWebioAn1GraphPtSwBasic 2 }
    wtWebioAn1GraphPtSwMail		OBJECT IDENTIFIER ::= { wtWebioAn1GraphPtSwBasic 3 }
    wtWebioAn1GraphPtSwSNMP		OBJECT IDENTIFIER ::= { wtWebioAn1GraphPtSwBasic 4 }
    wtWebioAn1GraphPtSwUDP		OBJECT IDENTIFIER ::= { wtWebioAn1GraphPtSwBasic 5 }
    wtWebioAn1GraphPtSwSyslog		OBJECT IDENTIFIER ::= { wtWebioAn1GraphPtSwBasic 6 }
    wtWebioAn1GraphPtSwFTP		OBJECT IDENTIFIER ::= { wtWebioAn1GraphPtSwBasic 7 }
    wtWebioAn1GraphPtSwLanguage		OBJECT IDENTIFIER ::= { wtWebioAn1GraphPtSwBasic 9 }
    wtWebioAn1GraphPtSwMQTT			OBJECT IDENTIFIER ::= { wtWebioAn1GraphPtSwBasic 12 }
    wtWebioAn1GraphPtSwREST			OBJECT IDENTIFIER ::= { wtWebioAn1GraphPtSwBasic 13 }


--  wtWebioAn1GraphPtSwGraphics Tree

    wtWebioAn1GraphPtSwGraphicsBase 	OBJECT IDENTIFIER ::= { wtWebioAn1GraphPtSwGraphics 1 }
    wtWebioAn1GraphPtSwGraphicsSelect 	OBJECT IDENTIFIER ::= { wtWebioAn1GraphPtSwGraphics 2 }
    wtWebioAn1GraphPtSwGraphicsScale 	OBJECT IDENTIFIER ::= { wtWebioAn1GraphPtSwGraphics 3 }

-- wtWebioAn1GraphPtTemp Group
------------------------

wtWebioAn1GraphPtSensors OBJECT-TYPE
    SYNTAX INTEGER (1)
    ACCESS read-only
    STATUS mandatory
    DESCRIPTION
        "Number of temperature sensors"
    ::= { wtWebioAn1GraphPtTemp 1 }

-- Interface Table

wtWebioAn1GraphPtSensorTable OBJECT-TYPE
    SYNTAX SEQUENCE OF WtWebioAn1GraphPtSensorEntry
    ACCESS not-accessible
    STATUS mandatory
    DESCRIPTION
        "List of sensors."
    ::= { wtWebioAn1GraphPtTemp 2 }

wtWebioAn1GraphPtSensorEntry OBJECT-TYPE
    SYNTAX WtWebioAn1GraphPtSensorEntry
    ACCESS not-accessible
    STATUS mandatory
    DESCRIPTION
        "Temperature sensor numbers."
    INDEX  { wtWebioAn1GraphPtSensorNo }
    ::= { wtWebioAn1GraphPtSensorTable 1 }

WtWebioAn1GraphPtSensorEntry ::= SEQUENCE {
    wtWebioAn1GraphPtSensorNo INTEGER
}

wtWebioAn1GraphPtSensorNo OBJECT-TYPE
    SYNTAX INTEGER (1)
    ACCESS read-only
    STATUS mandatory
    DESCRIPTION
        "Temperature sensor number."
    ::= { wtWebioAn1GraphPtSensorEntry 1 }


-- wtWebioAn1GraphPtTempValue Table

wtWebioAn1GraphPtTempValueTable OBJECT-TYPE
    SYNTAX SEQUENCE OF WtWebioAn1GraphPtTempValueEntry
    ACCESS not-accessible
    STATUS mandatory
    DESCRIPTION
        "List of temperature values corresponding to the channel numbers."
    ::= { wtWebioAn1GraphPtTemp 3 }

wtWebioAn1GraphPtTempValueEntry OBJECT-TYPE
    SYNTAX WtWebioAn1GraphPtTempValueEntry
    ACCESS not-accessible
    STATUS mandatory
    DESCRIPTION
        "Temperatures of the sensors."
    INDEX  { wtWebioAn1GraphPtSensorNo }
    ::= { wtWebioAn1GraphPtTempValueTable 1 }

WtWebioAn1GraphPtTempValueEntry ::= SEQUENCE{
    wtWebioAn1GraphPtTempValue OCTET STRING
}

wtWebioAn1GraphPtTempValue OBJECT-TYPE
    SYNTAX OCTET STRING (SIZE (5))
    ACCESS read-only
    STATUS mandatory
    DESCRIPTION
        "Temperature value of the sensor, ASCII, 5 characters in length."
    ::= { wtWebioAn1GraphPtTempValueEntry 1 }

-- wtWebioAn1GraphPtBinaryTempValue Table

wtWebioAn1GraphPtBinaryTempValueTable OBJECT-TYPE
    SYNTAX SEQUENCE OF WtWebioAn1GraphPtBinaryTempValueEntry
    ACCESS not-accessible
    STATUS mandatory
    DESCRIPTION
        "List of binary temperature values corresponding to the channel numbers."
    ::= { wtWebioAn1GraphPtTemp 4 }

wtWebioAn1GraphPtBinaryTempValueEntry OBJECT-TYPE
    SYNTAX WtWebioAn1GraphPtBinaryTempValueEntry
    ACCESS not-accessible
    STATUS mandatory
    DESCRIPTION
        "Binary temperature values of the sensors."
    INDEX  { wtWebioAn1GraphPtSensorNo }
    ::= { wtWebioAn1GraphPtBinaryTempValueTable 1 }

WtWebioAn1GraphPtBinaryTempValueEntry ::= SEQUENCE{
    wtWebioAn1GraphPtBinaryTempValue INTEGER
}

wtWebioAn1GraphPtBinaryTempValue OBJECT-TYPE
    SYNTAX INTEGER
    ACCESS read-only
    STATUS mandatory
    DESCRIPTION
        "Binary temperature value of the sensor in 1/10 degrees Celsius,
        signed number, 0x7FFF indicates an
        invalid measured value."
    ::= { wtWebioAn1GraphPtBinaryTempValueEntry 1 }

-- wtWebioAn1GraphPtTempValuePkt Table

wtWebioAn1GraphPtTempValuePktTable OBJECT-TYPE
    SYNTAX SEQUENCE OF WtWebioAn1GraphPtTempValuePktEntry
    ACCESS not-accessible
    STATUS mandatory
    DESCRIPTION
        "List of temperature values corresponding to the channel numbers."
    ::= { wtWebioAn1GraphPtTemp 8 }

wtWebioAn1GraphPtTempValuePktEntry OBJECT-TYPE
    SYNTAX WtWebioAn1GraphPtTempValuePktEntry
    ACCESS not-accessible
    STATUS mandatory
    DESCRIPTION
        "Temperatures of the sensors."
    INDEX  { wtWebioAn1GraphPtSensorNo }
    ::= { wtWebioAn1GraphPtTempValuePktTable 1 }

WtWebioAn1GraphPtTempValuePktEntry ::= SEQUENCE{
    wtWebioAn1GraphPtTempValuePkt OCTET STRING
}

wtWebioAn1GraphPtTempValuePkt OBJECT-TYPE
    SYNTAX OCTET STRING (SIZE (5))
    ACCESS read-only
    STATUS mandatory
    DESCRIPTION
        "Temperature value of the sensor, ASCII, 5 characters in length, decimal point."
    ::= { wtWebioAn1GraphPtTempValuePktEntry 1 }

-- wtWebioAn1GraphPtSessCntrl Group
--------------------------------

wtWebioAn1GraphPtSessCntrlPassword OBJECT-TYPE
    SYNTAX OCTET STRING
    ACCESS read-write
    STATUS mandatory
    DESCRIPTION
        "Entering this password opens a session which is ended by writing a 1 to
        wtWebioAn1GraphPtSessCntrlLogout. When read this variable provides a string of
        length zero."
    ::= { wtWebioAn1GraphPtSessCntrl 1 }

wtWebioAn1GraphPtSessCntrlConfigMode OBJECT-TYPE
    SYNTAX INTEGER {
    wtWebioAn1GraphPtSessCntrl-NoSession(0),
    wtWebioAn1GraphPtSessCntrl-Session(1)
    }
    ACCESS read-only
    STATUS mandatory
    DESCRIPTION
        "When the device is in SNMP configuration mode, the value 1 is
        returned, otherwise 0. If the read value is 0 even though the
        password was written, the device is already in config mode and the
        variables can only be read."
    ::= { wtWebioAn1GraphPtSessCntrl 2 }

wtWebioAn1GraphPtSessCntrlLogout OBJECT-TYPE
    SYNTAX INTEGER
    ACCESS read-write
    STATUS mandatory
    DESCRIPTION
        "If the device is in configuration mode and the session was opened by
        this SNMP Manager, writing a 1 to this variable will end the session
        and all parameters are stored.
        Writing a 2 discards all entries again.
        When read this variable provides the value 0."
    ::= { wtWebioAn1GraphPtSessCntrl 3 }

wtWebioAn1GraphPtSessCntrlAdminPassword OBJECT-TYPE
    SYNTAX OCTET STRING
    ACCESS read-write
    STATUS mandatory
    DESCRIPTION
        "This password protects access to the variables with administrator rights.
        It can only be changed by the administrator. If no password was assigned,
        the valid password is public."
    ::= { wtWebioAn1GraphPtSessCntrl 4 }

wtWebioAn1GraphPtSessCntrlConfigPassword OBJECT-TYPE
    SYNTAX OCTET STRING
    ACCESS read-write
    STATUS mandatory
    DESCRIPTION
        "This password protects access to the variables with configurator rights. It can
        be changed by the administrator and by the configurator. If no password was assigned,
        the valid password is public. When read this variable provides a null-pointer."
    ::= { wtWebioAn1GraphPtSessCntrl 5 }


-- wtWebioAn1GraphPtText Group
------------------------

wtWebioAn1GraphPtDeviceName OBJECT-TYPE
    SYNTAX OCTET STRING
    ACCESS read-write
    STATUS mandatory
    DESCRIPTION
        "Name of the Webio, which is user definable."
    ::= { wtWebioAn1GraphPtText 1 }

wtWebioAn1GraphPtDeviceText OBJECT-TYPE
    SYNTAX OCTET STRING
    ACCESS read-write
    STATUS mandatory
    DESCRIPTION
        "Description of the Webio, which is user definable."
    ::= { wtWebioAn1GraphPtText 2 }

wtWebioAn1GraphPtDeviceLocation OBJECT-TYPE
    SYNTAX OCTET STRING
    ACCESS read-write
    STATUS mandatory
    DESCRIPTION
        "Description of the location of the Webio, which is user definable."
    ::= { wtWebioAn1GraphPtText 3 }

wtWebioAn1GraphPtDeviceContact OBJECT-TYPE
    SYNTAX OCTET STRING
    ACCESS read-write
    STATUS mandatory
    DESCRIPTION
        "Contact address of the system operator of the Webio, which is user definable."
    ::= { wtWebioAn1GraphPtText 4 }

-- wtWebioAn1GraphPtTimeZone Group
----------------------------

wtWebioAn1GraphPtTzOffsetHrs OBJECT-TYPE
    SYNTAX INTEGER
    ACCESS read-write
    STATUS mandatory
    DESCRIPTION
        "Offset hours for the time zone (winter time) with respect to UTC."
    ::= { wtWebioAn1GraphPtTimeZone 1 }

wtWebioAn1GraphPtTzOffsetMin OBJECT-TYPE
    SYNTAX INTEGER
    ACCESS read-write
    STATUS mandatory
    DESCRIPTION
        "Offset minutes for the time zone (winter time) with respect to UTC."
    ::= { wtWebioAn1GraphPtTimeZone 2 }

wtWebioAn1GraphPtTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebioAn1GraphPtTimeZone 3 }

wtWebioAn1GraphPtStTzOffsetHrs OBJECT-TYPE
    SYNTAX INTEGER
    ACCESS read-write
    STATUS mandatory
    DESCRIPTION
        "Offset hours of the time zone (summer time) with respect to UTC."
    ::= { wtWebioAn1GraphPtTimeZone 4 }

wtWebioAn1GraphPtStTzOffsetMin OBJECT-TYPE
    SYNTAX INTEGER
    ACCESS read-write
    STATUS mandatory
    DESCRIPTION
        "Offset minutes of the time zone (summer time) with respect to UTC."
    ::= { wtWebioAn1GraphPtTimeZone 5 }

wtWebioAn1GraphPtStTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebioAn1GraphPtTimeZone 6 }

wtWebioAn1GraphPtStTzStartMonth OBJECT-TYPE
    SYNTAX INTEGER {
    	wtWebioAn1GraphPtStartMonth-January(1),
    	wtWebioAn1GraphPtStartMonth-February(2),
    	wtWebioAn1GraphPtStartMonth-March(3),
    	wtWebioAn1GraphPtStartMonth-April(4),
    	wtWebioAn1GraphPtStartMonth-May(5),
    	wtWebioAn1GraphPtStartMonth-June(6),
    	wtWebioAn1GraphPtStartMonth-July(7),
    	wtWebioAn1GraphPtStartMonth-August(8),
    	wtWebioAn1GraphPtStartMonth-September(9),
    	wtWebioAn1GraphPtStartMonth-October(10),
    	wtWebioAn1GraphPtStartMonth-November(11),
    	wtWebioAn1GraphPtStartMonth-December(12)
    	}

    ACCESS read-write
    STATUS mandatory
    DESCRIPTION
        "Month in which the change is made from winter time to summer time."
    ::= { wtWebioAn1GraphPtTimeZone 7 }

wtWebioAn1GraphPtStTzStartMode OBJECT-TYPE
    SYNTAX INTEGER {
    	wtWebioAn1GraphPtStartMode-first(1),
    	wtWebioAn1GraphPtStartMode-second(2),
    	wtWebioAn1GraphPtStartMode-third(3),
    	wtWebioAn1GraphPtStartMode-fourth(4),
    	wtWebioAn1GraphPtStartMode-last(5)
    	}

    ACCESS read-write
    STATUS mandatory
    DESCRIPTION
        "Mode of the day of the week for which the change is made from winter time to summer time."
    ::= { wtWebioAn1GraphPtTimeZone 8 }

wtWebioAn1GraphPtStTzStartWday OBJECT-TYPE
    SYNTAX INTEGER {
    	wtWebioAn1GraphPtStartWday-Sunday(1),
    	wtWebioAn1GraphPtStartWday-Monday(2),
    	wtWebioAn1GraphPtStartWday-Tuesday(3),
    	wtWebioAn1GraphPtStartWday-Thursday(4),
    	wtWebioAn1GraphPtStartWday-Wednesday(5),
    	wtWebioAn1GraphPtStartWday-Friday(6),
    	wtWebioAn1GraphPtStartWday-Saturday(7)
    	}

    ACCESS read-write
    STATUS mandatory
    DESCRIPTION
        "Day of the week on which the change is made from winter time to summer time"
    ::= { wtWebioAn1GraphPtTimeZone 9 }

wtWebioAn1GraphPtStTzStartHrs OBJECT-TYPE
    SYNTAX INTEGER
    ACCESS read-write
    STATUS mandatory
    DESCRIPTION
        "Hour in which the time zone is changed from winter to summer time with
        respect to UTC."
    ::= { wtWebioAn1GraphPtTimeZone 10 }

wtWebioAn1GraphPtStTzStartMin OBJECT-TYPE
    SYNTAX INTEGER
    ACCESS read-write
    STATUS mandatory
    DESCRIPTION
        "Minute in which the time zone is changed from winter to summer time with
        respect to UTC."
    ::= { wtWebioAn1GraphPtTimeZone 11 }

wtWebioAn1GraphPtStTzStopMonth OBJECT-TYPE
    SYNTAX INTEGER {
    	wtWebioAn1GraphPtStopMonth-January(1),
    	wtWebioAn1GraphPtStopMonth-February(2),
    	wtWebioAn1GraphPtStopMonth-March(3),
    	wtWebioAn1GraphPtStopMonth-April(4),
    	wtWebioAn1GraphPtStopMonth-May(5),
    	wtWebioAn1GraphPtStopMonth-June(6),
    	wtWebioAn1GraphPtStopMonth-July(7),
    	wtWebioAn1GraphPtStopMonth-August(8),
    	wtWebioAn1GraphPtStopMonth-September(9),
    	wtWebioAn1GraphPtStopMonth-October(10),
    	wtWebioAn1GraphPtStopMonth-November(11),
    	wtWebioAn1GraphPtStopMonth-December(12)
    	}
    ACCESS read-write
    STATUS mandatory
    DESCRIPTION
        "Month in which the change is made from summer time to winter time."
   ::= { wtWebioAn1GraphPtTimeZone 12 }

wtWebioAn1GraphPtStTzStopMode OBJECT-TYPE
    SYNTAX INTEGER {
    	wtWebioAn1GraphPtStopMode-first(1),
    	wtWebioAn1GraphPtStopMode-second(2),
    	wtWebioAn1GraphPtStopMode-third(3),
    	wtWebioAn1GraphPtStopMode-fourth(4),
    	wtWebioAn1GraphPtStopMode-last(5)
    	}
    ACCESS read-write
    STATUS mandatory
    DESCRIPTION
        "Mode of the week day on which the change is made from summer time to winter time."
    ::= { wtWebioAn1GraphPtTimeZone 13 }

wtWebioAn1GraphPtStTzStopWday OBJECT-TYPE
    SYNTAX INTEGER {
    	wtWebioAn1GraphPtStopWday-Sunday(1),
    	wtWebioAn1GraphPtStopWday-Monday(2),
    	wtWebioAn1GraphPtStopWday-Tuesday(3),
    	wtWebioAn1GraphPtStopWday-Thursday(4),
    	wtWebioAn1GraphPtStopWday-Wednesday(5),
    	wtWebioAn1GraphPtStopWday-Friday(6),
    	wtWebioAn1GraphPtStopWday-Saturday(7)
    	}
    ACCESS read-write
    STATUS mandatory
    DESCRIPTION
        "Day of the week on which the change is made from summer time to winter time."
    ::= { wtWebioAn1GraphPtTimeZone 14 }

wtWebioAn1GraphPtStTzStopHrs OBJECT-TYPE
    SYNTAX INTEGER
    ACCESS read-write
    STATUS mandatory
    DESCRIPTION
        "Hour at which the time zone is changed from summer to winter time with
        respect to UTC."
    ::= { wtWebioAn1GraphPtTimeZone 15 }

wtWebioAn1GraphPtStTzStopMin OBJECT-TYPE
    SYNTAX INTEGER
    ACCESS read-write
    STATUS mandatory
    DESCRIPTION
        "Minute at which the time zone is changed from summer to winter time with
        respect to UTC."
    ::= { wtWebioAn1GraphPtTimeZone 16 }

-- wtWebioAn1GraphPtTimeServer Group
----------------------------

wtWebioAn1GraphPtTimeServer1 OBJECT-TYPE
    SYNTAX OCTET STRING
    ACCESS read-write
    STATUS mandatory
    DESCRIPTION
        "IP address or name of the 1st time server in ASCII"
    ::= { wtWebioAn1GraphPtTimeServer 1 }

wtWebioAn1GraphPtTimeServer2 OBJECT-TYPE
    SYNTAX OCTET STRING
    ACCESS read-write
    STATUS mandatory
    DESCRIPTION
        "IP address or name of the 2nd time server in ASCII"
    ::= { wtWebioAn1GraphPtTimeServer 2 }

wtWebioAn1GraphPtTsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebioAn1GraphPtTimeServer 3 }

wtWebioAn1GraphPtTsSyncTime OBJECT-TYPE
    SYNTAX INTEGER
    ACCESS read-write
    STATUS mandatory
    DESCRIPTION
        "Daily synchronisation time with the time server (hour: 0-23)."
    ::= { wtWebioAn1GraphPtTimeServer 4 }

-- wtWebioAn1GraphPtDeviceClock Group
----------------------------

wtWebioAn1GraphPtClockHrs OBJECT-TYPE
    SYNTAX INTEGER (0..23)
    ACCESS read-write
    STATUS mandatory
    DESCRIPTION
        "Clock hours taking into account the time zone settings."
    ::= { wtWebioAn1GraphPtDeviceClock 1 }

wtWebioAn1GraphPtClockMin OBJECT-TYPE
    SYNTAX INTEGER (0..59)
    ACCESS read-write
    STATUS mandatory
    DESCRIPTION
        "Clock minutes taking into account the time zone settings."
    ::= { wtWebioAn1GraphPtDeviceClock 2 }

wtWebioAn1GraphPtClockDay OBJECT-TYPE
    SYNTAX INTEGER (1..31)
    ACCESS read-write
    STATUS mandatory
    DESCRIPTION
        "Date: Day of the month, taking into account the time zone settings."
    ::= { wtWebioAn1GraphPtDeviceClock 3 }

wtWebioAn1GraphPtClockMonth OBJECT-TYPE
   SYNTAX INTEGER {
    	wtWebioAn1GraphPtClockMonth-January(1),
    	wtWebioAn1GraphPtClockMonth-February(2),
    	wtWebioAn1GraphPtClockMonth-March(3),
    	wtWebioAn1GraphPtClockMonth-April(4),
    	wtWebioAn1GraphPtClockMonth-May(5),
    	wtWebioAn1GraphPtClockMonth-June(6),
    	wtWebioAn1GraphPtClockMonth-July(7),
    	wtWebioAn1GraphPtClockMonth-August(8),
    	wtWebioAn1GraphPtClockMonth-September(9),
    	wtWebioAn1GraphPtClockMonth-October(10),
    	wtWebioAn1GraphPtClockMonth-November(11),
    	wtWebioAn1GraphPtClockMonth-December(12)
    	}
    ACCESS read-write
    STATUS mandatory
    DESCRIPTION
        "Date: Month, taking into account the time zone settings."
    ::= { wtWebioAn1GraphPtDeviceClock 4 }

wtWebioAn1GraphPtClockYear OBJECT-TYPE
    SYNTAX INTEGER (0..65535)
    ACCESS read-write
    STATUS mandatory
    DESCRIPTION
        "Date: Year, taking into account the time zone settings."
    ::= { wtWebioAn1GraphPtDeviceClock 5 }


-- wtWebioAn1GraphPtNetwork Group
------------------------

wtWebioAn1GraphPtIpAddress OBJECT-TYPE
    SYNTAX IpAddress
    ACCESS read-write
    STATUS mandatory
    DESCRIPTION
        "IP address of the Webio"
    ::= { wtWebioAn1GraphPtNetwork 1 }

wtWebioAn1GraphPtSubnetMask OBJECT-TYPE
    SYNTAX IpAddress
    ACCESS read-write
    STATUS mandatory
    DESCRIPTION
        "Subnet mask of the Webio"
    ::= { wtWebioAn1GraphPtNetwork 2 }

wtWebioAn1GraphPtGateway OBJECT-TYPE
    SYNTAX IpAddress
    ACCESS read-write
    STATUS mandatory
    DESCRIPTION
        "Gateway of the Webio"
    ::= { wtWebioAn1GraphPtNetwork 3 }

wtWebioAn1GraphPtDnsServer1 OBJECT-TYPE
    SYNTAX OCTET STRING
    ACCESS read-write
    STATUS mandatory
    DESCRIPTION
        "IP address of the 1st DNS server in ASCII"
    ::= { wtWebioAn1GraphPtNetwork 4 }

wtWebioAn1GraphPtDnsServer2 OBJECT-TYPE
    SYNTAX OCTET STRING
    ACCESS read-write
    STATUS mandatory
    DESCRIPTION
        "IP address of the 2nd DNS server in ASCII"
    ::= { wtWebioAn1GraphPtNetwork 5 }

wtWebioAn1GraphPtAddConfig OBJECT-TYPE
    SYNTAX OCTET STRING
    ACCESS read-write
    STATUS mandatory
    DESCRIPTION
        "Additional configuration (1=ON):
        Octet 1: unused
        Octet 2: unused
        Octet 3: unused
        Octet 4:
	        Bit 1: DHCP disable
	        Bit 0: BOOTP disable
	        "
    ::= { wtWebioAn1GraphPtNetwork 6 }

--  wtWebioAn1GraphPtHTTP Group
--------------------------------

wtWebioAn1GraphPtStartup OBJECT-TYPE
    SYNTAX OCTET STRING
    ACCESS read-write
    STATUS mandatory
    DESCRIPTION
        "Binary coded start page:
        Octet 1: unused
        Octet 2: unused
        Octet 3: unused
        Octet 4:
	        Bit 1: Index.htm
	        Bit 2: Home.htm
	        Bit 3: User.htm
	Only one page may be selected at a time."
    ::= { wtWebioAn1GraphPtHTTP 1 }

wtWebioAn1GraphPtGetHeaderEnable OBJECT-TYPE
    SYNTAX OCTET STRING
    ACCESS read-write
    STATUS mandatory
    DESCRIPTION
        "If these bits are set, every answer of a short form GET question will be lead
        by the IP-address and name of the device and/or a HTTP header:
        Octet 1: unused
        Octet 2: unused
        Octet 3: unused
        Octet 4:
        	Bit 1-6: unused
        	Bit 1  : GET HTTP enable
                Bit 0  : GET Header enable"
    ::= { wtWebioAn1GraphPtHTTP 2 }

wtWebioAn1GraphPtHttpPort OBJECT-TYPE
    SYNTAX INTEGER (1..65535)
    ACCESS read-write
    STATUS mandatory
    DESCRIPTION
        "Definition of the standard HTML port (Default: 80)."
    ::= { wtWebioAn1GraphPtHTTP 3 }


-- wtWebioAn1GraphPtMail Group
--------------------------------

wtWebioAn1GraphPtMailAdName OBJECT-TYPE
    SYNTAX OCTET STRING
    ACCESS read-write
    STATUS mandatory
    DESCRIPTION
        "Device name for mail administration."
    ::= { wtWebioAn1GraphPtMail 1 }

wtWebioAn1GraphPtMailReply OBJECT-TYPE
    SYNTAX OCTET STRING
    ACCESS read-write
    STATUS mandatory
    DESCRIPTION
        "Reply address for the mail server."
    ::= { wtWebioAn1GraphPtMail 2 }

wtWebioAn1GraphPtMailServer OBJECT-TYPE
    SYNTAX OCTET STRING
    ACCESS read-write
    STATUS mandatory
    DESCRIPTION
        "Name or IP address of the mail server."
    ::= { wtWebioAn1GraphPtMail 3 }

wtWebioAn1GraphPtMailEnable OBJECT-TYPE
    SYNTAX OCTET STRING
    ACCESS read-write
    STATUS mandatory
    DESCRIPTION
        "Set this bit to enable the sending of mails:
        Octet 1: unused
        Octet 2: unused
        Octet 3: unused
        Octet 4:
        	Bit 1-7: unused
                Bit 0  : Mail enable"
    ::= { wtWebioAn1GraphPtMail 4 }

wtWebioAn1GraphPtMailAuthentication OBJECT-TYPE
    SYNTAX OCTET STRING (SIZE (4))
    ACCESS read-write
    STATUS mandatory
    DESCRIPTION
        "Selection of the authentication modi:
        The OCTETS are interpreted bit-by-bit, with each bit corresponding to an output.
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebioAn1GraphPtMail 5 }

wtWebioAn1GraphPtMailAuthUser OBJECT-TYPE
    SYNTAX OCTET STRING
    ACCESS read-write
    STATUS mandatory
    DESCRIPTION
        "Name of the user to be authenticated."
    ::= { wtWebioAn1GraphPtMail 6 }

wtWebioAn1GraphPtMailAuthPassword OBJECT-TYPE
    SYNTAX OCTET STRING
    ACCESS read-write
    STATUS mandatory
    DESCRIPTION
        "Authentication password."
    ::= { wtWebioAn1GraphPtMail 7 }

wtWebioAn1GraphPtMailPop3Server OBJECT-TYPE
    SYNTAX OCTET STRING
    ACCESS read-write
    STATUS mandatory
    DESCRIPTION
        "Name or Ip-address of the POP3 Servers."
    ::= { wtWebioAn1GraphPtMail 8 }


-- wtWebioAn1GraphPtSNMP Group
--------------------------------

wtWebioAn1GraphPtSnmpCommunityStringRead OBJECT-TYPE
    SYNTAX OCTET STRING
    ACCESS read-write
    STATUS mandatory
    DESCRIPTION
        "Community string read only"
    ::= { wtWebioAn1GraphPtSNMP 1 }

wtWebioAn1GraphPtSnmpCommunityStringReadWrite OBJECT-TYPE
    SYNTAX OCTET STRING
    ACCESS read-write
    STATUS mandatory
    DESCRIPTION
        "Community string read / write"
    ::= { wtWebioAn1GraphPtSNMP 2 }

wtWebioAn1GraphPtSystemTrapManagerIP OBJECT-TYPE
    SYNTAX OCTET STRING
    ACCESS read-write
    STATUS mandatory
    DESCRIPTION
        "Name or IP address of the TCP server which accepts the system trap."
    ::= { wtWebioAn1GraphPtSNMP 3 }

wtWebioAn1GraphPtSystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2-7: unused"
    ::= { wtWebioAn1GraphPtSNMP 4 }

wtWebioAn1GraphPtSnmpEnable OBJECT-TYPE
    SYNTAX OCTET STRING
    ACCESS read-write
    STATUS mandatory
    DESCRIPTION
        "Set bit 0 to enable SNMP.
        If disabled, the device did not respond to any SNMP requests.
        Bit 1 decided wether the community string of read operations
        is compared with the system password or not:
        Octet 1: unused
        Octet 2: unused
        Octet 3: unused
        Octet 4:
        	Bit 1-7: unused
        	Bit 0  : SNMP enable"
    ::= { wtWebioAn1GraphPtSNMP 5 }

wtWebioAn1GraphPtSnmpCommunityStringTrap OBJECT-TYPE
    SYNTAX OCTET STRING
    ACCESS read-write
    STATUS mandatory
    DESCRIPTION
        "Community string send within traps."
    ::= { wtWebioAn1GraphPtSNMP 6 }

-- wtWebioAn1GraphPtUDP Group
--------------------------------

wtWebioAn1GraphPtUdpPort OBJECT-TYPE
    SYNTAX INTEGER (1..65535)
    ACCESS read-write
    STATUS mandatory
    DESCRIPTION
        "Udp port to which the Udp queries ( short form GET requests) can be sent. This
        port number must be unique within the device."
    ::= { wtWebioAn1GraphPtUDP 1 }

wtWebioAn1GraphPtUdpEnable OBJECT-TYPE
    SYNTAX OCTET STRING
    ACCESS read-write
    STATUS mandatory
    DESCRIPTION
        "Set this bit to enable UDP support:
        Octet 1: unused
        Octet 2: unused
        Octet 3: unused
        Octet 4:
        	Bit 1-7: unused
                Bit 0  : UDP enable"
    ::= { wtWebioAn1GraphPtUDP 2 }


--  wtWebioAn1GraphPtSyslog Group
--------------------------------

wtWebioAn1GraphPtSyslogServerIP OBJECT-TYPE
    SYNTAX OCTET STRING
    ACCESS read-write
    STATUS mandatory
    DESCRIPTION
        "Name or IP address of the Syslog server, which accepts the Syslog messgaes."
    ::= { wtWebioAn1GraphPtSyslog 1 }

wtWebioAn1GraphPtSyslogServerPort OBJECT-TYPE
    SYNTAX INTEGER
    ACCESS read-write
    STATUS mandatory
    DESCRIPTION
        "Portnumber of the Syslog servers, default 514."
    ::= { wtWebioAn1GraphPtSyslog 2 }

wtWebioAn1GraphPtSyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebioAn1GraphPtSyslog 3 }

wtWebioAn1GraphPtSyslogEnable OBJECT-TYPE
    SYNTAX OCTET STRING
    ACCESS read-write
    STATUS mandatory
    DESCRIPTION
        "Set bit 0 to enable Syslog:
        Octet 1: unused
        Octet 2: unused
        Octet 3: unused
        Octet 4:
        	Bit 1-7: unused
                Bit 0  : Syslog enable"
    ::= { wtWebioAn1GraphPtSyslog 4 }

--  wtWebioAn1GraphPtFTP Group
--------------------------------

wtWebioAn1GraphPtFTPServerIP OBJECT-TYPE
    SYNTAX OCTET STRING
    ACCESS read-write
    STATUS mandatory
    DESCRIPTION
        "Name or IP address of the FTP server, which accepts the FTP messages."
    ::= { wtWebioAn1GraphPtFTP 1 }

wtWebioAn1GraphPtFTPServerControlPort OBJECT-TYPE
    SYNTAX INTEGER
    ACCESS read-write
    STATUS mandatory
    DESCRIPTION
        "Portnumber of the control port of the FTP server, default 21."
    ::= { wtWebioAn1GraphPtFTP 2 }

wtWebioAn1GraphPtFTPUserName OBJECT-TYPE
    SYNTAX OCTET STRING
    ACCESS read-write
    STATUS mandatory
    DESCRIPTION
        "FTP Loggin: user name."
    ::= { wtWebioAn1GraphPtFTP 3 }

wtWebioAn1GraphPtFTPPassword OBJECT-TYPE
    SYNTAX OCTET STRING
    ACCESS read-write
    STATUS mandatory
    DESCRIPTION
        "FTP Loggin: user password."
    ::= { wtWebioAn1GraphPtFTP 4 }

wtWebioAn1GraphPtFTPAccount OBJECT-TYPE
    SYNTAX OCTET STRING
    ACCESS read-write
    STATUS mandatory
    DESCRIPTION
        "FTP Loggin: name of account."
    ::= { wtWebioAn1GraphPtFTP 5 }

wtWebioAn1GraphPtFTPOption OBJECT-TYPE
    SYNTAX OCTET STRING
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebioAn1GraphPtFTP 6 }

wtWebioAn1GraphPtFTPEnable OBJECT-TYPE
    SYNTAX OCTET STRING
    ACCESS read-write
    STATUS mandatory
    DESCRIPTION
        "Set Bit 0 to enable FTP:
        Octet 1: unused
        Octet 2: unused
        Octet 3: unused
        Octet 4:
        	Bit 1-7: unused
                Bit 0  : FTP enable"
    ::= { wtWebioAn1GraphPtFTP 7 }

--  wtWebioAn1GraphPtLanguage Group
--------------------------------

wtWebioAn1GraphPtLanguageSelect OBJECT-TYPE
    SYNTAX OCTET STRING
    ACCESS read-write
    STATUS mandatory
    DESCRIPTION
        "Language selection:
        Octet 1: unused
        Octet 2: unused
        Octet 3: unused
        Octet 4:
        	Bit 2-7: unused
        	Bit 1  : english
                Bit 0  : german"
    ::= { wtWebioAn1GraphPtLanguage 1 }

-- wtWebioAn1GraphPtDatalogger Group
--------------------------------

wtWebioAn1GraphPtLoggerTimebase OBJECT-TYPE
    SYNTAX INTEGER {
    wtWebioAn1GraphPtDatalogger-1Min(1),
    wtWebioAn1GraphPtDatalogger-5Min(2),
    wtWebioAn1GraphPtDatalogger-15Min(3),
    wtWebioAn1GraphPtDatalogger-60Min(4)
    }
    ACCESS read-write
    STATUS mandatory
    DESCRIPTION
        "Time base of the data logger"
    ::= { wtWebioAn1GraphPtDatalogger 1 }

wtWebioAn1GraphPtLoggerSensorSel OBJECT-TYPE
    SYNTAX OCTET STRING (SIZE(4))
    ACCESS read-write
    STATUS mandatory
    DESCRIPTION
        "Binary coded sensor selection:
        only selected sensors will be logged.
        Octet 1: unused
        Octet 2: unused
        Octet 3: unused
        Octet 4:
        	Bit 0: Sensor 1
        	Bit 1-7: unused"
    ::= { wtWebioAn1GraphPtDatalogger 2 }

wtWebioAn1GraphPtDisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1-7: unused"
    ::= { wtWebioAn1GraphPtDatalogger 3 }

-- Graph Sensor Color Table
-- This group defines the grahical appearance of "pic.png"
--------------------------------

wtWebioAn1GraphPtSensorColorTable OBJECT-TYPE
    SYNTAX SEQUENCE OF WtWebioAn1GraphPtSensorColorEntry
    ACCESS not-accessible
    STATUS mandatory
    DESCRIPTION
        "List of sensor colors for the praphical presentation."
    ::= { wtWebioAn1GraphPtDatalogger 4 }

wtWebioAn1GraphPtSensorColorEntry OBJECT-TYPE
    SYNTAX WtWebioAn1GraphPtSensorColorEntry
    ACCESS not-accessible
    STATUS mandatory
    DESCRIPTION
        "Index numbers of the sensors."
    INDEX  { wtWebioAn1GraphPtSensorNo }
    ::= { wtWebioAn1GraphPtSensorColorTable 1 }

WtWebioAn1GraphPtSensorColorEntry ::= SEQUENCE {
    wtWebioAn1GraphPtSensorColor OCTET STRING
}

wtWebioAn1GraphPtSensorColor OBJECT-TYPE
    SYNTAX OCTET STRING (SIZE(3))
    ACCESS read-write
    STATUS mandatory
    DESCRIPTION
        "Color of the sensors at the praphical presention."
    ::= { wtWebioAn1GraphPtSensorColorEntry 1 }

wtWebioAn1GraphPtAutoScaleEnable OBJECT-TYPE
    SYNTAX OCTET STRING
    ACCESS read-write
    STATUS mandatory
    DESCRIPTION
        "If bit 0 is set, vertical auto scale is enabled:
        Octet 1: unused
        Octet 2: unused
        Octet 3: unused
        Octet 4:
        	Bit 1-7: unused
                Bit 0  : Auto Scale enable"
    ::= { wtWebioAn1GraphPtDatalogger 5 }

wtWebioAn1GraphPtVerticalUpperLimit OBJECT-TYPE
    SYNTAX OCTET STRING
    ACCESS read-write
    STATUS mandatory
    DESCRIPTION
        "This value defines the maximum temperature shown in the graphical presentation,
        if no auto scaling is selected.
        Temperature in degrees with maximum 2 decimal places."
    ::= { wtWebioAn1GraphPtDatalogger 6 }

wtWebioAn1GraphPtVerticalLowerLimit OBJECT-TYPE
    SYNTAX OCTET STRING
    ACCESS read-write
    STATUS mandatory
    DESCRIPTION
        "This value defines the minimum temperature shown in the graphical presentation,
        if no auto scaling is selected.
        Temperature in degrees with maximum 2 decimal places."
    ::= { wtWebioAn1GraphPtDatalogger 7 }

wtWebioAn1GraphPtHorizontalZoom OBJECT-TYPE
    SYNTAX INTEGER {
    wtWebioAn1GraphPtZoom-25min(1),
    wtWebioAn1GraphPtZoom-75min(2),
    wtWebioAn1GraphPtZoom-5hrs(3),
    wtWebioAn1GraphPtZoom-30hrs(4),
    wtWebioAn1GraphPtZoom-5days(5),
    wtWebioAn1GraphPtZoom-25days(6)
    }
    ACCESS read-write
    STATUS mandatory
    DESCRIPTION
        "Defines the default zoom stage, if no auto scaling is selected."
    ::= { wtWebioAn1GraphPtDatalogger 8 }

-- wtWebioAn1GraphPtAlarm Group
----------------------------

wtWebioAn1GraphPtAlarmCount OBJECT-TYPE
    SYNTAX INTEGER (1..8)
    ACCESS read-only
    STATUS mandatory
    DESCRIPTION
        "Number of independent alarms."
    ::= { wtWebioAn1GraphPtAlarm 1 }

-- Alarm Interface Table

wtWebioAn1GraphPtAlarmIfTable OBJECT-TYPE
    SYNTAX SEQUENCE OF WtWebioAn1GraphPtAlarmIfEntry
    ACCESS not-accessible
    STATUS mandatory
    DESCRIPTION
        "List of alarm indices."
    ::= { wtWebioAn1GraphPtAlarm 2 }

wtWebioAn1GraphPtAlarmIfEntry OBJECT-TYPE
    SYNTAX WtWebioAn1GraphPtAlarmIfEntry
    ACCESS not-accessible
    STATUS mandatory
    DESCRIPTION
        "Numbers of the alarms."
    INDEX  { wtWebioAn1GraphPtAlarmNo }
    ::= { wtWebioAn1GraphPtAlarmIfTable 1 }

WtWebioAn1GraphPtAlarmIfEntry ::= SEQUENCE {
    wtWebioAn1GraphPtAlarmNo INTEGER
}

wtWebioAn1GraphPtAlarmNo OBJECT-TYPE
    SYNTAX INTEGER (1..8)
    ACCESS read-only
    STATUS mandatory
    DESCRIPTION
        "Alarm number."
    ::= { wtWebioAn1GraphPtAlarmIfEntry 1 }

-- Alarm Table

wtWebioAn1GraphPtAlarmTable OBJECT-TYPE
    SYNTAX SEQUENCE OF WtWebioAn1GraphPtAlarmEntry
    ACCESS not-accessible
    STATUS mandatory
    DESCRIPTION
        "List of settings depending on the alarm number."
    ::= { wtWebioAn1GraphPtAlarm 3 }

wtWebioAn1GraphPtAlarmEntry OBJECT-TYPE
    SYNTAX WtWebioAn1GraphPtAlarmEntry
    ACCESS not-accessible
    STATUS mandatory
    DESCRIPTION
        "Alarm parameters of the individual alarms."
    INDEX  { wtWebioAn1GraphPtAlarmNo }
    ::= { wtWebioAn1GraphPtAlarmTable 1 }

WtWebioAn1GraphPtAlarmEntry ::= SEQUENCE {
    wtWebioAn1GraphPtAlarmTrigger			OCTET STRING,
    wtWebioAn1GraphPtAlarmMin				OCTET STRING,
    wtWebioAn1GraphPtAlarmMax				OCTET STRING,
    wtWebioAn1GraphPtAlarmHysteresis			OCTET STRING,
    wtWebioAn1GraphPtAlarmDelay				OCTET STRING,
    wtWebioAn1GraphPtAlarmInterval			OCTET STRING,
    wtWebioAn1GraphPtAlarmEnable			OCTET STRING,
    wtWebioAn1GraphPtAlarmEMailAddr			OCTET STRING,
    wtWebioAn1GraphPtAlarmMailSubject			OCTET STRING,
    wtWebioAn1GraphPtAlarmMailText			OCTET STRING,
    wtWebioAn1GraphPtAlarmManagerIP			OCTET STRING,
    wtWebioAn1GraphPtAlarmTrapText			OCTET STRING,
    wtWebioAn1GraphPtAlarmMailOptions			OCTET STRING,
    wtWebioAn1GraphPtAlarmTcpIpAddr			OCTET STRING,
    wtWebioAn1GraphPtAlarmTcpPort			INTEGER,
    wtWebioAn1GraphPtAlarmTcpText			OCTET STRING,
    wtWebioAn1GraphPtAlarmClearMailSubject		OCTET STRING,
    wtWebioAn1GraphPtAlarmClearMailText			OCTET STRING,
    wtWebioAn1GraphPtAlarmClearTrapText			OCTET STRING,
    wtWebioAn1GraphPtAlarmClearTcpText			OCTET STRING,
    wtWebioAn1GraphPtAlarmSyslogIpAddr			OCTET STRING,
    wtWebioAn1GraphPtAlarmSyslogPort			INTEGER,
    wtWebioAn1GraphPtAlarmSyslogText			OCTET STRING,
    wtWebioAn1GraphPtAlarmFtpDataPort			OCTET STRING,
    wtWebioAn1GraphPtAlarmFtpFileName			OCTET STRING,
    wtWebioAn1GraphPtAlarmFtpText			OCTET STRING,
    wtWebioAn1GraphPtAlarmFtpClearText			OCTET STRING,
    wtWebioAn1GraphPtAlarmFtpOption			OCTET STRING,
    wtWebioAn1GraphPtAlarmTimerCron			OCTET STRING,
    wtWebioAn1GraphPtAlarmDeltaTemp			OCTET STRING,
    wtWebioAn1GraphPtAlarmName 				OCTET STRING,
    wtWebioAn1GraphPtAlarmActive 			OCTET STRING,
    wtWebioAn1GraphPtAlarmHttpReqAuthEnable		OCTET STRING,
    wtWebioAn1GraphPtAlarmHttpReqAuthUser		OCTET STRING,
    wtWebioAn1GraphPtAlarmHttpReqAuthPassword		OCTET STRING,
    wtWebioAn1GraphPtAlarmHttpReqSetUrl			OCTET STRING,
    wtWebioAn1GraphPtAlarmHttpReqClearUrl		OCTET STRING,
    wtWebioAn1GraphPtAlarmHttpReqServerPort		OCTET STRING,
    wtWebioAn1GraphPtAlarmMqttTopicPath			OCTET STRING,
    wtWebioAn1GraphPtAlarmMqttTopicSetTopic		OCTET STRING,
    wtWebioAn1GraphPtAlarmMqttTopicClear		OCTET STRING,
    wtWebioAn1GraphPtAlarmSensorLostSelection	OCTET STRING,
    wtWebioAn1GraphPtAlarmLimitWindow			OCTET STRING

}

wtWebioAn1GraphPtAlarmTrigger OBJECT-TYPE
    SYNTAX OCTET STRING (SIZE(4))
    ACCESS read-write
    STATUS mandatory
    DESCRIPTION
        "Binary coded trigger conditions:
        Octet 1: unused
        Octet 2: unused
        Octet 3:
        	Bit 0  : Timer
        	Bit 1  : ColdStart
        	Bit 2  : WarmStart
        	Bit 3  : Sensor lost
        	Bit 4-7: unused

        Octet 4:
        	Bit 0  : Sensor 1
        	Bit 1-7: unused"
    ::= { wtWebioAn1GraphPtAlarmEntry 1 }

wtWebioAn1GraphPtAlarmMin OBJECT-TYPE
    SYNTAX OCTET STRING
    ACCESS read-write
    STATUS mandatory
    DESCRIPTION
        "Minimum temperature in degrees with maximum 2 decimal places."
    ::= { wtWebioAn1GraphPtAlarmEntry 2 }

wtWebioAn1GraphPtAlarmMax OBJECT-TYPE
    SYNTAX OCTET STRING
    ACCESS read-write
    STATUS mandatory
    DESCRIPTION
        "Maximum temperature in degrees with maximum 2 decimal places."
    ::= { wtWebioAn1GraphPtAlarmEntry 3 }

wtWebioAn1GraphPtAlarmHysteresis OBJECT-TYPE
    SYNTAX OCTET STRING
    ACCESS read-write
    STATUS mandatory
    DESCRIPTION
        "Temperature changes of this size clears the alarm state (MAX-hyst, MIN+hyst.)
        , in degrees with maximum 2 decimal places."
    ::= { wtWebioAn1GraphPtAlarmEntry 4 }

wtWebioAn1GraphPtAlarmDelay OBJECT-TYPE
    SYNTAX OCTET STRING
    ACCESS read-write
    STATUS mandatory
    DESCRIPTION
        "Alarm will be delayed by setting this time while stable alarm
        condition occur (time in minutes)."
    ::= { wtWebioAn1GraphPtAlarmEntry 5 }


wtWebioAn1GraphPtAlarmInterval OBJECT-TYPE
    SYNTAX OCTET STRING
    ACCESS read-write
    STATUS mandatory
    DESCRIPTION
        "Send interval for alarm messages."
    ::= { wtWebioAn1GraphPtAlarmEntry 6 }

wtWebioAn1GraphPtAlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0  : Mail Enable
        	Bit 1  : SNMP Trap enable
        	Bit 2  : TCP Client enable
        	Bit 3  : Syslog Messages enable
        	Bit 4  : FTP enable
        	Bit 5-7: unused"

    ::= { wtWebioAn1GraphPtAlarmEntry 7 }

wtWebioAn1GraphPtAlarmEMailAddr OBJECT-TYPE
    SYNTAX OCTET STRING
    ACCESS read-write
    STATUS mandatory
    DESCRIPTION
        "E-Mail address for sending the alarm mail to."
    ::= { wtWebioAn1GraphPtAlarmEntry 8 }

wtWebioAn1GraphPtAlarmMailSubject OBJECT-TYPE
    SYNTAX OCTET STRING
    ACCESS read-write
    STATUS mandatory
    DESCRIPTION
        "Subject line for alarm mail."
    ::= { wtWebioAn1GraphPtAlarmEntry 9 }

wtWebioAn1GraphPtAlarmMailText OBJECT-TYPE
    SYNTAX OCTET STRING
    ACCESS read-write
    STATUS mandatory
    DESCRIPTION
        "Alarm mail text: <Tn> provides the current temperature; n = 1..8.
        <Z> provides the current time."
    ::= { wtWebioAn1GraphPtAlarmEntry 10 }

wtWebioAn1GraphPtAlarmManagerIP OBJECT-TYPE
    SYNTAX OCTET STRING
    ACCESS read-write
    STATUS mandatory
    DESCRIPTION
        "Name or IP address of the SNMP Manager which accepts the trap."
    ::= { wtWebioAn1GraphPtAlarmEntry 11 }

wtWebioAn1GraphPtAlarmTrapText OBJECT-TYPE
    SYNTAX OCTET STRING
    ACCESS read-write
    STATUS mandatory
    DESCRIPTION
        "This text is sent in the trap body."
    ::= { wtWebioAn1GraphPtAlarmEntry 12 }

wtWebioAn1GraphPtAlarmMailOptions OBJECT-TYPE
    SYNTAX OCTET STRING (SIZE(4))
    ACCESS read-write
    STATUS mandatory
    DESCRIPTION
        "Binary coded options:
        Octet 1: unused
        Octet 2: unused
        Octet 3: unused
        Octet 4:
		Bit 0  :	Attach Thermo.csv Enable
		Bit 1  :	CSV-Data_since_last_report
        	Bit 2-7:	unused"
    ::= { wtWebioAn1GraphPtAlarmEntry 13 }

wtWebioAn1GraphPtAlarmTcpIpAddr OBJECT-TYPE
    SYNTAX OCTET STRING
    ACCESS read-write
    STATUS mandatory
    DESCRIPTION
        "Name or IP address of the TCP server which accepts the trap."
    ::= { wtWebioAn1GraphPtAlarmEntry 14 }

wtWebioAn1GraphPtAlarmTcpPort OBJECT-TYPE
    SYNTAX INTEGER (1..65535)
    ACCESS read-write
    STATUS mandatory
    DESCRIPTION
        "Port number of the TCP server which accepts the trap."
    ::= { wtWebioAn1GraphPtAlarmEntry 15 }

wtWebioAn1GraphPtAlarmTcpText OBJECT-TYPE
    SYNTAX OCTET STRING
    ACCESS read-write
    STATUS mandatory
    DESCRIPTION
        "This text is sent in the TCP trap body."
    ::= { wtWebioAn1GraphPtAlarmEntry 16 }

wtWebioAn1GraphPtAlarmClearMailSubject OBJECT-TYPE
    SYNTAX OCTET STRING
    ACCESS read-write
    STATUS mandatory
    DESCRIPTION
        "Subject line for alarm clear mail."
    ::= { wtWebioAn1GraphPtAlarmEntry 17 }

wtWebioAn1GraphPtAlarmClearMailText OBJECT-TYPE
    SYNTAX OCTET STRING
    ACCESS read-write
    STATUS mandatory
    DESCRIPTION
        " Alarm clear mail text: <Tn> provides the current temperature; n = 1..8. <Z> provides the current time."
    ::= { wtWebioAn1GraphPtAlarmEntry 18 }

wtWebioAn1GraphPtAlarmClearTrapText OBJECT-TYPE
    SYNTAX OCTET STRING
    ACCESS read-write
    STATUS mandatory
    DESCRIPTION
        "This text is sent in the trap body."
    ::= { wtWebioAn1GraphPtAlarmEntry 19 }

wtWebioAn1GraphPtAlarmClearTcpText OBJECT-TYPE
    SYNTAX OCTET STRING
    ACCESS read-write
    STATUS mandatory
    DESCRIPTION
        "This text is sent in the TCP trap body."
    ::= { wtWebioAn1GraphPtAlarmEntry 20 }

wtWebioAn1GraphPtAlarmSyslogIpAddr OBJECT-TYPE
    SYNTAX IpAddress
    ACCESS read-write
    STATUS mandatory
    DESCRIPTION
        "IP address of the syslog server to which the Webio device should send syslog messages."
    ::= { wtWebioAn1GraphPtAlarmEntry 21 }

wtWebioAn1GraphPtAlarmSyslogPort OBJECT-TYPE
    SYNTAX INTEGER (1..65535)
    ACCESS read-write
    STATUS mandatory
    DESCRIPTION
        "Port number of the syslog server to which the Webio device should send syslog messages."
    ::= { wtWebioAn1GraphPtAlarmEntry 22 }

wtWebioAn1GraphPtAlarmSyslogText OBJECT-TYPE
    SYNTAX OCTET STRING
    ACCESS read-write
    STATUS mandatory
    DESCRIPTION
        "Every message starts with the priority key, a time stamp and the host ip address, according RFC3164.
        This text appears in the following syslog message body."
    ::= { wtWebioAn1GraphPtAlarmEntry 23 }

wtWebioAn1GraphPtAlarmSyslogClearText OBJECT-TYPE
    SYNTAX OCTET STRING
    ACCESS read-write
    STATUS mandatory
    DESCRIPTION
        "Every message starts with the priority key, a time stamp and the host ip address, according RFC3164.
        This text appears in the following syslog message body."
    ::= { wtWebioAn1GraphPtAlarmEntry 24 }

wtWebioAn1GraphPtAlarmFtpDataPort OBJECT-TYPE
    SYNTAX OCTET STRING
    ACCESS read-write
    STATUS mandatory
    DESCRIPTION
        "Local data port: 1..65535 or AUTO: the next free port will be assigned."
    ::= { wtWebioAn1GraphPtAlarmEntry 25 }

wtWebioAn1GraphPtAlarmFtpFileName OBJECT-TYPE
    SYNTAX OCTET STRING
    ACCESS read-write
    STATUS mandatory
    DESCRIPTION
        "Name of the file including path informations."
    ::= { wtWebioAn1GraphPtAlarmEntry 26 }

wtWebioAn1GraphPtAlarmFtpText OBJECT-TYPE
    SYNTAX OCTET STRING
    ACCESS read-write
    STATUS mandatory
    DESCRIPTION
        "Message text to store on the FTP server."
    ::= { wtWebioAn1GraphPtAlarmEntry 27 }

wtWebioAn1GraphPtAlarmFtpClearText OBJECT-TYPE
    SYNTAX OCTET STRING
    ACCESS read-write
    STATUS mandatory
    DESCRIPTION
        "Alarm clear message to store on the FTP server."
    ::= { wtWebioAn1GraphPtAlarmEntry 28 }

wtWebioAn1GraphPtAlarmFtpOption OBJECT-TYPE
    SYNTAX OCTET STRING (SIZE(4))
    ACCESS read-write
    STATUS mandatory
    DESCRIPTION
        "Binary coded options, select only one option at the same time:
        STORE  = replace file
        APPEND = append message at the end of the file

        Octet 1: unused
        Octet 2: unused
        Octet 3: unused
        Octet 4:
		Bit 0  :	STORE
		Bit 1  :	APPEND
        	Bit 2-7:	unused"
    ::= { wtWebioAn1GraphPtAlarmEntry 29 }

wtWebioAn1GraphPtAlarmTimerCron OBJECT-TYPE
    SYNTAX OCTET STRING
    ACCESS read-write
    STATUS mandatory
    DESCRIPTION
        "This entry defines a time window for alarm 1-8 and a activation time for the report.
        A time window is definied by start and stop time stamp, seperated by a space or tab.
        The activation time of the report is defined by a single start time stamp.
        Each time stamp contains 5 space or tab seperated text fields for time trigger definition.
        Each field must match with the actual time to trigger an action, weekday and day of month
        are interpreted separatley.
        1: Minutes	Range 0-59
        2. Hours	Range 0-23, 0 is midnight
        3: Day of month	Range 1-31
        4: Month	Range 1-12
        5: Weekday	Range 0-6, 0 is sunday

        Syntax for every field:
         - an asterix (*) enables every possible setting of a field
         - single numbers seperated by commas (i.e.: 2,14,22)
         - a partition within the allowed range (i.e.: 1-5)
         - step size within a partition of the allowed range (i.e.: 0-59/2  every second minute)."
    ::= { wtWebioAn1GraphPtAlarmEntry 30 }

wtWebioAn1GraphPtAlarmDeltaTemp OBJECT-TYPE
    SYNTAX OCTET STRING
    ACCESS read-write
    STATUS mandatory
    DESCRIPTION
        "Maximum rate of change  degrees/min with maximum 2 decimal places.
        Compared with the average of a period of 5 minutes."
    ::= { wtWebioAn1GraphPtAlarmEntry 31 }

-- __JB__
wtWebioAn1GraphPtAlarmName OBJECT-TYPE
    SYNTAX OCTET STRING
    ACCESS read-write
    STATUS mandatory
    DESCRIPTION
        "Alert name"
    ::= { wtWebioAn1GraphPtAlarmEntry 39 }

-- __JB__
wtWebioAn1GraphPtAlarmActive OBJECT-TYPE
    SYNTAX OCTET STRING
    ACCESS read-write
    STATUS mandatory
    DESCRIPTION
        "Alert active
			1 = ON
			0 = OFF"
    ::= { wtWebioAn1GraphPtAlarmEntry 40 }

wtWebioAn1GraphPtAlarmHttpReqAuthEnable OBJECT-TYPE
    SYNTAX OCTET STRING
    ACCESS read-write
    STATUS mandatory
    DESCRIPTION
        "Binary coded options, select only one option at the same time:
        OCTET 1: unused
        OCTET 2: unused
        OCTET 3: unused
        OCTET 4, Bit 1-7: unused
        Bit 0  : HHTP Request Authentication enable"
    ::= { wtWebioAn1GraphPtAlarmEntry 61 }

wtWebioAn1GraphPtAlarmHttpReqAuthUser OBJECT-TYPE
    SYNTAX OCTET STRING
    ACCESS read-write
    STATUS mandatory
    DESCRIPTION
	"HTTP Request: User"
    ::= { wtWebioAn1GraphPtAlarmEntry 62 }

wtWebioAn1GraphPtAlarmHttpReqAuthPassword OBJECT-TYPE
    SYNTAX OCTET STRING
    ACCESS read-write
    STATUS mandatory
    DESCRIPTION
	"HTTP Request: Password"
    ::= { wtWebioAn1GraphPtAlarmEntry 63 }

wtWebioAn1GraphPtAlarmHttpReqSetUrl OBJECT-TYPE
    SYNTAX OCTET STRING
    ACCESS read-write
    STATUS mandatory
    DESCRIPTION
	"HTTP Request: Set URL"
    ::= { wtWebioAn1GraphPtAlarmEntry 64 }

wtWebioAn1GraphPtAlarmHttpReqClearUrl OBJECT-TYPE
    SYNTAX OCTET STRING
    ACCESS read-write
    STATUS mandatory
    DESCRIPTION
	"HTTP Request: Clear URL"
    ::= { wtWebioAn1GraphPtAlarmEntry 65 }

wtWebioAn1GraphPtAlarmHttpReqServerPort OBJECT-TYPE
    SYNTAX INTEGER (1..65535)
    ACCESS read-write
    STATUS mandatory
    DESCRIPTION
	"HTTP Request: Server Port"
    ::= { wtWebioAn1GraphPtAlarmEntry 66 }

wtWebioAn1GraphPtAlarmMqttTopicPath OBJECT-TYPE
    SYNTAX OCTET STRING
    ACCESS read-write
    STATUS mandatory
    DESCRIPTION
	"MQTT Publish: Topic path"
    ::= { wtWebioAn1GraphPtAlarmEntry 67 }

wtWebioAn1GraphPtAlarmMqttTopicSetTopic OBJECT-TYPE
    SYNTAX OCTET STRING
    ACCESS read-write
    STATUS mandatory
    DESCRIPTION
	"MQTT Publish: Topic SET message"
    ::= { wtWebioAn1GraphPtAlarmEntry 68 }

wtWebioAn1GraphPtAlarmMqttTopicClear OBJECT-TYPE
    SYNTAX OCTET STRING
    ACCESS read-write
    STATUS mandatory
    DESCRIPTION
	"MQTT Publish: Topic CLEAR message"
    ::= { wtWebioAn1GraphPtAlarmEntry 69 }

wtWebioAn1GraphPtAlarmSensorLostSelection OBJECT-TYPE
    SYNTAX OCTET STRING
    ACCESS read-write
    STATUS mandatory
    DESCRIPTION
        "Binary coded options:
        OCTET 1: unused
        OCTET 2: unused
        OCTET 3: unused
        OCTET 4, Bit 1-7: unused
        Bit 0  : Sensor 0"
    ::= { wtWebioAn1GraphPtAlarmEntry 70 }

wtWebioAn1GraphPtAlarmLimitWindow OBJECT-TYPE
    SYNTAX OCTET STRING
    ACCESS read-write
    STATUS mandatory
    DESCRIPTION
        "If window type is INSIDE the alarm is genereted when the temperature
        is greater minumum value and lower than maximum value. If window type is OUTSIDE
        the alarm is generated when the measured value is lower than the minimum value
        or greater than the maximum value.
		Binary coded options, select only one option at the same time:
        OCTET 1: unused
        OCTET 2: unused
        OCTET 3: unused
        OCTET 4, Bit 2-7: unused
		Bit 1  : inside window
        Bit 0  : outside window"
    ::= { wtWebioAn1GraphPtAlarmEntry 71 }

-- wtWebioAn1GraphPtGraphicsBase Group
----------------------------

wtWebioAn1GraphPtGraphicsBaseEnable OBJECT-TYPE
    SYNTAX OCTET STRING
    ACCESS read-write
    STATUS mandatory
    DESCRIPTION
        "Defines the viewing options of the graphic:
        Octet 1: unused
        Octet 2: unused
        Octet 3: unused
        Octet 4:
                Bit 0  : Auto scroll enable
                Bit 1  : Show table
                Bit 2  : Show graph
                Bit 3  : Show control buttons
                Bit 4  : Show config menu
                Bit 5  : Show Logo
                Bit 6-7: unused"
    ::= { wtWebioAn1GraphPtGraphicsBase 1 }

wtWebioAn1GraphPtGraphicsBaseWidth OBJECT-TYPE
    SYNTAX INTEGER
    ACCESS read-write
    STATUS mandatory
    DESCRIPTION
        "Defines the width of the graphic in pixels."
    ::= { wtWebioAn1GraphPtGraphicsBase 2 }

wtWebioAn1GraphPtGraphicsBaseHeight OBJECT-TYPE
        SYNTAX INTEGER
        ACCESS read-write
        STATUS mandatory
        DESCRIPTION
            "Defines the height of the graphic in pixels."
        ::= { wtWebioAn1GraphPtGraphicsBase 3 }

wtWebioAn1GraphPtGraphicsBaseFrameColor OBJECT-TYPE
    SYNTAX OCTET STRING (SIZE(3))
    ACCESS read-write
    STATUS mandatory
    DESCRIPTION
        "Frame color definition in RGB."
    ::= { wtWebioAn1GraphPtGraphicsBase 4 }

wtWebioAn1GraphPtGraphicsBaseBackgroundColor OBJECT-TYPE
    SYNTAX OCTET STRING (SIZE(3))
    ACCESS read-write
    STATUS mandatory
    DESCRIPTION
        "Background color definition in RGB."
    ::= { wtWebioAn1GraphPtGraphicsBase 5 }

wtWebioAn1GraphPtGraphicsBasePollingrate OBJECT-TYPE
        SYNTAX INTEGER
        ACCESS read-write
        STATUS mandatory
        DESCRIPTION
            "Defines the pollingrate in seconds,
            which defines the refreshing intervall of the graphic."
        ::= { wtWebioAn1GraphPtGraphicsBase 6 }

-- wtWebioAn1GraphPtGraphicsSelect Group
----------------------------

wtWebioAn1GraphPtGraphicsSelectDisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0  : Sensor 1
		Bit 1-7: unused"
    ::= { wtWebioAn1GraphPtGraphicsSelect 1 }

wtWebioAn1GraphPtGraphicsSelectDisplayShowExtrem OBJECT-TYPE
    SYNTAX OCTET STRING (SIZE(4))
    ACCESS read-write
    STATUS mandatory
    DESCRIPTION
        "Binary coded sensor selection:
        only selected sensors will be shown with minima and maxima:
        Octet 1: unused
        Octet 2: unused
        Octet 3: unused
        Octet 4:
        	Bit 0  : Sensor 1
		Bit 1-7: unused"
    ::= { wtWebioAn1GraphPtGraphicsSelect 2 }

-- Graph Sensor Color Table

wtWebioAn1GraphPt2SensorColorTable OBJECT-TYPE
    SYNTAX SEQUENCE OF WtWebioAn1GraphPt2SensorColorEntry
    ACCESS not-accessible
    STATUS mandatory
    DESCRIPTION
        "List of sensor colors for the praphical presentation."
    ::= { wtWebioAn1GraphPtGraphicsSelect 3 }

wtWebioAn1GraphPt2SensorColorEntry OBJECT-TYPE
    SYNTAX WtWebioAn1GraphPt2SensorColorEntry
    ACCESS not-accessible
    STATUS mandatory
    DESCRIPTION
        "Numbers of the sensors."
    INDEX  { wtWebioAn1GraphPtSensorNo }
    ::= { wtWebioAn1GraphPt2SensorColorTable 1 }

WtWebioAn1GraphPt2SensorColorEntry ::= SEQUENCE {
    wtWebioAn1GraphPt2GraphicsSensorColor OCTET STRING,
    wtWebioAn1GraphPt2GraphicsSelectScale OCTET STRING
}

wtWebioAn1GraphPt2GraphicsSensorColor OBJECT-TYPE
    SYNTAX OCTET STRING (SIZE(3))
    ACCESS read-write
    STATUS mandatory
    DESCRIPTION
        "Color of the sensors at the praphical presention."
    ::= { wtWebioAn1GraphPt2SensorColorEntry 1 }

wtWebioAn1GraphPt2GraphicsSelectScale OBJECT-TYPE
    SYNTAX OCTET STRING
    ACCESS read-write
    STATUS mandatory
    DESCRIPTION
        "Assignes one of 4 scales to a sensor:
        Octet 1: unused
        Octet 2: unused
        Octet 3: unused
        Octet 4:
                Bit 0  : Use Scale 1
                Bit 1-7: unused"
    ::= { wtWebioAn1GraphPt2SensorColorEntry 2 }

-- wtWebioAn1GraphPtGraphicsScale Group
----------------------------

wtWebioAn1GraphPtGraphicsScaleAutoScaleEnable OBJECT-TYPE
    SYNTAX OCTET STRING
    ACCESS read-write
    STATUS mandatory
    DESCRIPTION
        "Select the Auto Scale Mode:
        Octet 1: unused
        Octet 2: unused
        Octet 3: unused
        Octet 4:
                Bit 0  : Scale 1 Auto scale enable
                Bit 1-7: unused"
    ::= { wtWebioAn1GraphPtGraphicsScale 1 }

wtWebioAn1GraphPtGraphicsScaleAutoFitEnable OBJECT-TYPE
    SYNTAX OCTET STRING
    ACCESS read-write
    STATUS mandatory
    DESCRIPTION
        "Select the Auto Fit Mode::
        Octet 1: unused
        Octet 2: unused
        Octet 3: unused
        Octet 4:
                Bit 0  : Scale 1 Auto fit enable
                Bit 1-7: unused"
    ::= { wtWebioAn1GraphPtGraphicsScale 2 }

wtWebioAn1GraphPtGraphicsScale1Min OBJECT-TYPE
    SYNTAX INTEGER
    ACCESS read-only
    STATUS mandatory
    DESCRIPTION
        "Scale 1: Minimum."
    ::= { wtWebioAn1GraphPtGraphicsScale 3 }

wtWebioAn1GraphPtGraphicsScale2Min OBJECT-TYPE
    SYNTAX INTEGER
    ACCESS read-only
    STATUS mandatory
    DESCRIPTION
        "Scale 2: Minimum."
    ::= { wtWebioAn1GraphPtGraphicsScale 4 }

wtWebioAn1GraphPtGraphicsScale3Min OBJECT-TYPE
    SYNTAX INTEGER
    ACCESS read-only
    STATUS mandatory
    DESCRIPTION
        "Scale 3: Minimum."
    ::= { wtWebioAn1GraphPtGraphicsScale 5 }

wtWebioAn1GraphPtGraphicsScale4Min OBJECT-TYPE
    SYNTAX INTEGER
    ACCESS read-only
    STATUS mandatory
    DESCRIPTION
        "Scale 4: Minimum."
    ::= { wtWebioAn1GraphPtGraphicsScale 6 }

wtWebioAn1GraphPtGraphicsScale1Max OBJECT-TYPE
    SYNTAX INTEGER
    ACCESS read-only
    STATUS mandatory
    DESCRIPTION
        "Scale 1: Maximum."
    ::= { wtWebioAn1GraphPtGraphicsScale 7 }

wtWebioAn1GraphPtGraphicsScale2Max OBJECT-TYPE
    SYNTAX INTEGER
    ACCESS read-only
    STATUS mandatory
    DESCRIPTION
        "Scale 2: Maximum."
    ::= { wtWebioAn1GraphPtGraphicsScale 8 }

wtWebioAn1GraphPtGraphicsScale3Max OBJECT-TYPE
    SYNTAX INTEGER
    ACCESS read-only
    STATUS mandatory
    DESCRIPTION
        "Scale 3: Maximum."
    ::= { wtWebioAn1GraphPtGraphicsScale 9 }

wtWebioAn1GraphPtGraphicsScale4Max OBJECT-TYPE
    SYNTAX INTEGER
    ACCESS read-only
    STATUS mandatory
    DESCRIPTION
        "Scale 4: Maximum."
    ::= { wtWebioAn1GraphPtGraphicsScale 10 }

wtWebioAn1GraphPtGraphicsScale1Unit OBJECT-TYPE
    SYNTAX OCTET STRING
    ACCESS read-only
    STATUS mandatory
    DESCRIPTION
        "Scale 1: Unit."
    ::= { wtWebioAn1GraphPtGraphicsScale 11 }

wtWebioAn1GraphPtGraphicsScale2Unit OBJECT-TYPE
    SYNTAX OCTET STRING
    ACCESS read-only
    STATUS mandatory
    DESCRIPTION
        "Scale 2: Unit."
    ::= { wtWebioAn1GraphPtGraphicsScale 12 }

wtWebioAn1GraphPtGraphicsScale3Unit OBJECT-TYPE
    SYNTAX OCTET STRING
    ACCESS read-only
    STATUS mandatory
    DESCRIPTION
        "Scale 3: Unit."
    ::= { wtWebioAn1GraphPtGraphicsScale 13 }

wtWebioAn1GraphPtGraphicsScale4Unit OBJECT-TYPE
    SYNTAX OCTET STRING
    ACCESS read-only
    STATUS mandatory
    DESCRIPTION
        "Scale 4: Unit."
    ::= { wtWebioAn1GraphPtGraphicsScale 14 }

-- wtWebioAn1GraphPtPorts Group
----------------------------

-- Table

wtWebioAn1GraphPtPortTable OBJECT-TYPE
    SYNTAX SEQUENCE OF WtWebioAn1GraphPtPortEntry
    ACCESS not-accessible
    STATUS mandatory
    DESCRIPTION
        "List of settings depending on the sensor number."
    ::= { wtWebioAn1GraphPtPorts 1 }

wtWebioAn1GraphPtPortEntry OBJECT-TYPE
    SYNTAX WtWebioAn1GraphPtPortEntry
    ACCESS not-accessible
    STATUS mandatory
    DESCRIPTION
        "Sensor parameters for the individual sensors."
    INDEX  { wtWebioAn1GraphPtSensorNo }
    ::= { wtWebioAn1GraphPtPortTable 1 }

WtWebioAn1GraphPtPortEntry ::= SEQUENCE {
    wtWebioAn1GraphPtPortName		OCTET STRING,
    wtWebioAn1GraphPtPortText		OCTET STRING,
    wtWebioAn1GraphPtPortOffset1	OCTET STRING,
    wtWebioAn1GraphPtPortTemperature1	OCTET STRING,
    wtWebioAn1GraphPtPortOffset2	OCTET STRING,
    wtWebioAn1GraphPtPortTemperature2	OCTET STRING,
    wtWebioAn1GraphPtPortComment	OCTET STRING,
    wtWebioAn1GraphPtPortSensorSelect	OCTET STRING

}

wtWebioAn1GraphPtPortName OBJECT-TYPE
    SYNTAX OCTET STRING
    ACCESS read-write
    STATUS mandatory
    DESCRIPTION
        "Name of the sensor."
    ::= { wtWebioAn1GraphPtPortEntry 1 }

wtWebioAn1GraphPtPortText OBJECT-TYPE
    SYNTAX OCTET STRING
    ACCESS read-write
    STATUS mandatory
    DESCRIPTION
        "Description of the sensor."
    ::= { wtWebioAn1GraphPtPortEntry 2 }

wtWebioAn1GraphPtPortOffset1 OBJECT-TYPE
    SYNTAX OCTET STRING
    ACCESS read-write
    STATUS mandatory
    DESCRIPTION
        "Offset calibration: Offset in degrees with maximum 2 decimal places at temperature 1."
    ::= { wtWebioAn1GraphPtPortEntry 3 }

wtWebioAn1GraphPtPortTemperature1 OBJECT-TYPE
    SYNTAX OCTET STRING
    ACCESS read-write
    STATUS mandatory
    DESCRIPTION
        "Offset calibration: Reference temperature 1 in degrees with maximum 2 decimal places."
    ::= { wtWebioAn1GraphPtPortEntry 4 }

wtWebioAn1GraphPtPortOffset2 OBJECT-TYPE
    SYNTAX OCTET STRING
    ACCESS read-write
    STATUS mandatory
    DESCRIPTION
        "Offset calibration: Offset in degrees with maximum 2 decimal places at temperature 2."
    ::= { wtWebioAn1GraphPtPortEntry 5 }

wtWebioAn1GraphPtPortTemperature2 OBJECT-TYPE
    SYNTAX OCTET STRING
    ACCESS read-write
    STATUS mandatory
    DESCRIPTION
        "Offset calibration: Reference temperature 1 in degrees with maximum 2 decimal places."
    ::= { wtWebioAn1GraphPtPortEntry 6 }

wtWebioAn1GraphPtPortComment OBJECT-TYPE
    SYNTAX OCTET STRING
    ACCESS read-write
    STATUS mandatory
    DESCRIPTION
        "Offset calibration: informations of date, name of operator, reference devices."
    ::= { wtWebioAn1GraphPtPortEntry 7 }

wtWebioAn1GraphPtPortSensorSelect OBJECT-TYPE
    SYNTAX OCTET STRING (SIZE(4))
    ACCESS read-write
    STATUS mandatory
    DESCRIPTION
        "Binary coded options of the sensor:
        Octet 1: unused
        Octet 2: unused
        Octet 3: unused
        Octet 4:
		Bit 0  :	PT100 (default)
		Bit 1  :	PT1000
        	Bit 2-7:	unused"
    ::= { wtWebioAn1GraphPtPortEntry 8 }

-- wtWebioAn1GraphPtManufact Group
----------------------------

wtWebioAn1GraphPtMfName OBJECT-TYPE
    SYNTAX OCTET STRING
    ACCESS read-write
    STATUS mandatory
    DESCRIPTION
        "Manufacturer company name"
    ::= { wtWebioAn1GraphPtManufact 1 }

wtWebioAn1GraphPtMfAddr OBJECT-TYPE
    SYNTAX OCTET STRING
    ACCESS read-write
    STATUS mandatory
    DESCRIPTION
        "Manufacturer address."
    ::= { wtWebioAn1GraphPtManufact 2 }

wtWebioAn1GraphPtMfHotline OBJECT-TYPE
    SYNTAX OCTET STRING
    ACCESS read-write
    STATUS mandatory
    DESCRIPTION
        "Manufacturer hotline."
    ::= { wtWebioAn1GraphPtManufact 3 }

wtWebioAn1GraphPtMfInternet OBJECT-TYPE
    SYNTAX OCTET STRING
    ACCESS read-write
    STATUS mandatory
    DESCRIPTION
        "Manufacturer Internet address."
    ::= { wtWebioAn1GraphPtManufact 4 }

wtWebioAn1GraphPtMfDeviceTyp OBJECT-TYPE
    SYNTAX OCTET STRING
    ACCESS read-write
    STATUS mandatory
    DESCRIPTION
        "Manufacturer device name (model number)."
    ::= { wtWebioAn1GraphPtManufact 5 }

wtWebioAn1GraphPtMfOrderNo OBJECT-TYPE
    SYNTAX OCTET STRING
    ACCESS read-write
    STATUS mandatory
    DESCRIPTION
        "Manufacturer part number."
    ::= { wtWebioAn1GraphPtManufact 6 }

-- wtWebioAn1GraphPtDiag Group
----------------------------

wtWebioAn1GraphPtDiagErrorCount OBJECT-TYPE
    SYNTAX INTEGER
    ACCESS read-only
    STATUS mandatory
    DESCRIPTION
        "Number of entries in the error memory."
    ::= { wtWebioAn1GraphPtDiag 1 }

wtWebioAn1GraphPtDiagBinaryError OBJECT-TYPE
    SYNTAX OCTET STRING
    ACCESS read-only
    STATUS mandatory
    DESCRIPTION
        "Error causes coded bit-by-bit."
    ::= { wtWebioAn1GraphPtDiag 2 }

wtWebioAn1GraphPtDiagErrorIndex OBJECT-TYPE
    SYNTAX INTEGER
    ACCESS read-write
    STATUS mandatory
    DESCRIPTION
        "The value of this variable is used as an index to read
        an error massege from wtWebioAn1GraphPtDiagErrorMessage.
        Errors are numbered from 1 to wtWebioAn1GraphPtDiagErrorCount.
        Writing a valid value into this variable, making the appropriate
        message readable from wtWebioAn1GraphPtDiagErrorMessage."
    ::= { wtWebioAn1GraphPtDiag 3 }

wtWebioAn1GraphPtDiagErrorMessage OBJECT-TYPE
    SYNTAX OCTET STRING
    ACCESS read-only
    STATUS mandatory
    DESCRIPTION
        "Using wtWebioAn1GraphPtDiagErrorIndex as an index, the appropriate message is available."
    ::= { wtWebioAn1GraphPtDiag 4 }

wtWebioAn1GraphPtDiagErrorClear OBJECT-TYPE
    SYNTAX INTEGER
    ACCESS write-only
    STATUS mandatory
    DESCRIPTION
        "Writing 1 into this variable clears all diagnosis messages."
    ::= { wtWebioAn1GraphPtDiag 5 }

-- TRAP DEFINITIONS

-- Diese SNMP-Traps werden gesendet, wenn die Alarmtriggerbedingungen zutreffen

wtWebioAn1GraphPtAlert1 TRAP-TYPE
    ENTERPRISE  wtWebioAn1GraphPt
    VARIABLES   { wtWebioAn1GraphPtAlarmTrapText }
    DESCRIPTION
        "This SNMP trap is generated when Alarm 1 was triggered,
        SNMP trap enable is set and
        SNMP is enabled."
    -- NMS trap annotation
    --#TYPE "Web-Thermograph Alarm 1"
    --#SUMMARY "Alarm 1: %s"
    --#ARGUMENTS {0}
    --#SEVERITY INFORMATIONAL
    --#TIMEINDEX 99
    --#STATE OPERATIONAL
    ::= 31

wtWebioAn1GraphPtAlert2 TRAP-TYPE
    ENTERPRISE  wtWebioAn1GraphPt
    VARIABLES   { wtWebioAn1GraphPtAlarmTrapText }
    DESCRIPTION
        "This SNMP trap is generated when Alarm 2 was triggered,
        SNMP trap enable is set and
        SNMP is enabled."
    -- NMS trap annotation
    --#TYPE "Web-Thermograph Alarm 2"
    --#SUMMARY "Alarm 2: %s"
    --#ARGUMENTS {0}
    --#SEVERITY INFORMATIONAL
    --#TIMEINDEX 99
    --#STATE OPERATIONAL
    ::= 32

wtWebioAn1GraphPtAlert3 TRAP-TYPE
    ENTERPRISE  wtWebioAn1GraphPt
    VARIABLES   { wtWebioAn1GraphPtAlarmTrapText }
    DESCRIPTION
        "This SNMP trap is generated when Alarm 3 was triggered,
        SNMP trap enable is set and
        SNMP is enabled."
    -- NMS trap annotation
    --#TYPE "Web-Thermograph Alarm 3"
    --#SUMMARY "Alarm 3: %s"
    --#ARGUMENTS {0}
    --#SEVERITY INFORMATIONAL
    --#TIMEINDEX 99
    --#STATE OPERATIONAL
    ::= 33

wtWebioAn1GraphPtAlert4 TRAP-TYPE
    ENTERPRISE  wtWebioAn1GraphPt
    VARIABLES   { wtWebioAn1GraphPtAlarmTrapText }
    DESCRIPTION
        "This SNMP trap is generated when Alarm 4 was triggered,
        SNMP trap enable is set and
        SNMP is enabled."
    -- NMS trap annotation
    --#TYPE "Web-Thermograph Alarm 4"
    --#SUMMARY "Alarm 4: %s"
    --#ARGUMENTS {0}
    --#SEVERITY INFORMATIONAL
    --#TIMEINDEX 99
    --#STATE OPERATIONAL
    ::= 34

wtWebioAn1GraphPtAlert5 TRAP-TYPE
    ENTERPRISE  wtWebioAn1GraphPt
    VARIABLES   { wtWebioAn1GraphPtAlarmTrapText }
    DESCRIPTION
        "This SNMP trap is generated when Alarm 5 was triggered,
        SNMP trap enable is set and
        SNMP is enabled."
    -- NMS trap annotation
    --#TYPE "Web-Thermograph Alarm 5"
    --#SUMMARY "Alarm 5: %s"
    --#ARGUMENTS {0}
    --#SEVERITY INFORMATIONAL
    --#TIMEINDEX 99
    --#STATE OPERATIONAL
    ::= 35

wtWebioAn1GraphPtAlert6 TRAP-TYPE
    ENTERPRISE  wtWebioAn1GraphPt
    VARIABLES   { wtWebioAn1GraphPtAlarmTrapText }
    DESCRIPTION
        "This SNMP trap is generated when Alarm 6 was triggered,
        SNMP trap enable is set and
        SNMP is enabled."
    -- NMS trap annotation
    --#TYPE "Web-Thermograph Alarm 6"
    --#SUMMARY "Alarm 6: %s"
    --#ARGUMENTS {0}
    --#SEVERITY INFORMATIONAL
    --#TIMEINDEX 99
    --#STATE OPERATIONAL
    ::= 36

wtWebioAn1GraphPtAlert7 TRAP-TYPE
    ENTERPRISE  wtWebioAn1GraphPt
    VARIABLES   { wtWebioAn1GraphPtAlarmTrapText }
    DESCRIPTION
        "This SNMP trap is generated when Alarm 7 was triggered,
        SNMP trap enable is set and
        SNMP is enabled."
    -- NMS trap annotation
    --#TYPE "Web-Thermograph Alarm 7"
    --#SUMMARY "Alarm 7: %s"
    --#ARGUMENTS {0}
    --#SEVERITY INFORMATIONAL
    --#TIMEINDEX 99
    --#STATE OPERATIONAL
    ::= 37

wtWebioAn1GraphPtAlert8 TRAP-TYPE
    ENTERPRISE  wtWebioAn1GraphPt
    VARIABLES   { wtWebioAn1GraphPtAlarmTrapText }
    DESCRIPTION
        "This SNMP trap is generated when Alarm 8 was triggered,
        SNMP trap enable is set and
        SNMP is enabled."
    -- NMS trap annotation
    --#TYPE "Web-Thermograph Alarm 8"
    --#SUMMARY "Alarm 8: %s"
    --#ARGUMENTS {0}
    --#SEVERITY INFORMATIONAL
    --#TIMEINDEX 99
    --#STATE OPERATIONAL
    ::= 38


wtWebioAn1GraphPtAlert9 TRAP-TYPE
    ENTERPRISE  wtWebioAn1GraphPt
    VARIABLES   { wtWebioAn1GraphPtAlarmClearTrapText }
    DESCRIPTION
        "This SNMP trap is generated when Alarm 1 was cleared,
        SNMP trap enable is set and
        SNMP is enabled."
    -- NMS trap annotation
    --#TYPE "Web-Thermograph Release Alarm 1"
    --#SUMMARY "Release Alarm 1: %s"
    --#ARGUMENTS {0}
    --#SEVERITY INFORMATIONAL
    --#TIMEINDEX 99
    --#STATE OPERATIONAL
    ::= 91

wtWebioAn1GraphPtAlert10 TRAP-TYPE
    ENTERPRISE  wtWebioAn1GraphPt
    VARIABLES   { wtWebioAn1GraphPtAlarmClearTrapText }
    DESCRIPTION
        "This SNMP trap is generated when Alarm 2 was cleared,
        SNMP trap enable is set and
        SNMP is enabled."
    -- NMS trap annotation
    --#TYPE "Web-Thermograph Release Alarm 2"
    --#SUMMARY "Release Alarm 2: %s"
    --#ARGUMENTS {0}
    --#SEVERITY INFORMATIONAL
    --#TIMEINDEX 99
    --#STATE OPERATIONAL
    ::= 92

wtWebioAn1GraphPtAlert11 TRAP-TYPE
    ENTERPRISE  wtWebioAn1GraphPt
    VARIABLES   { wtWebioAn1GraphPtAlarmClearTrapText }
    DESCRIPTION
        "This SNMP trap is generated when Alarm 3 was cleared,
        SNMP trap enable is set and
        SNMP is enabled."
    -- NMS trap annotation
    --#TYPE "Web-Thermograph Release Alarm 3"
    --#SUMMARY "Release Alarm 3: %s"
    --#ARGUMENTS {0}
    --#SEVERITY INFORMATIONAL
    --#TIMEINDEX 99
    --#STATE OPERATIONAL
    ::= 93

wtWebioAn1GraphPtAlert12 TRAP-TYPE
    ENTERPRISE  wtWebioAn1GraphPt
    VARIABLES   { wtWebioAn1GraphPtAlarmClearTrapText }
    DESCRIPTION
        "This SNMP trap is generated when Alarm 4 was cleared,
        SNMP trap enable is set and
        SNMP is enabled."
    -- NMS trap annotation
    --#TYPE "Web-Thermograph Release Alarm 4"
    --#SUMMARY "Release Alarm 4: %s"
    --#ARGUMENTS {0}
    --#SEVERITY INFORMATIONAL
    --#TIMEINDEX 99
    --#STATE OPERATIONAL
    ::= 94

wtWebioAn1GraphPtAlert13 TRAP-TYPE
    ENTERPRISE  wtWebioAn1GraphPt
    VARIABLES   { wtWebioAn1GraphPtAlarmClearTrapText }
    DESCRIPTION
        "This SNMP trap is generated when Alarm 5 was cleared,
        SNMP trap enable is set and
        SNMP is enabled."
    -- NMS trap annotation
    --#TYPE "Web-Thermograph Release Alarm 5"
    --#SUMMARY "Release Alarm 5: %s"
    --#ARGUMENTS {0}
    --#SEVERITY INFORMATIONAL
    --#TIMEINDEX 99
    --#STATE OPERATIONAL
    ::= 95

wtWebioAn1GraphPtAlert14 TRAP-TYPE
    ENTERPRISE  wtWebioAn1GraphPt
    VARIABLES   { wtWebioAn1GraphPtAlarmClearTrapText }
    DESCRIPTION
        "This SNMP trap is generated when Alarm 6 was cleared,
        SNMP trap enable is set and
        SNMP is enabled."
    -- NMS trap annotation
    --#TYPE "Web-Thermograph Release Alarm 6"
    --#SUMMARY "Release Alarm 6: %s"
    --#ARGUMENTS {0}
    --#SEVERITY INFORMATIONAL
    --#TIMEINDEX 99
    --#STATE OPERATIONAL
    ::= 96

wtWebioAn1GraphPtAlert15 TRAP-TYPE
    ENTERPRISE  wtWebioAn1GraphPt
    VARIABLES   { wtWebioAn1GraphPtAlarmClearTrapText }
    DESCRIPTION
        "This SNMP trap is generated when Alarm 7 was cleared,
        SNMP trap enable is set and
        SNMP is enabled."
    -- NMS trap annotation
    --#TYPE "Web-Thermograph Release Alarm 7"
    --#SUMMARY "Release Alarm 7: %s"
    --#ARGUMENTS {0}
    --#SEVERITY INFORMATIONAL
    --#TIMEINDEX 99
    --#STATE OPERATIONAL
    ::= 97

wtWebioAn1GraphPtAlert16 TRAP-TYPE
    ENTERPRISE  wtWebioAn1GraphPt
    VARIABLES   { wtWebioAn1GraphPtAlarmClearTrapText }
    DESCRIPTION
        "This SNMP trap is generated when Alarm 8 was cleared,
        SNMP trap enable is set and
        SNMP is enabled."
    -- NMS trap annotation
    --#TYPE "Web-Thermograph Release Alarm 8"
    --#SUMMARY "Release Alarm 8: %s"
    --#ARGUMENTS {0}
    --#SEVERITY INFORMATIONAL
    --#TIMEINDEX 99
    --#STATE OPERATIONAL
    ::= 98

wtWebioAn1GraphPtAlertDiag TRAP-TYPE
    ENTERPRISE  wtWebioAn1GraphPt
    VARIABLES   {
    		wtWebioAn1GraphPtDiagErrorIndex,
    	  	wtWebioAn1GraphPtDiagErrorMessage
    		}
    DESCRIPTION
        "This SNMP trap is generated when a diagnosis/error message was triggered,
        SNMP trap enable is set and
        SNMP is enabled."
    -- NMS trap annotation
    --#TYPE "Web-Thermograph Diagnose Error"
    --#SUMMARY "Diagnose error index: %d, Message: %s."
    --#ARGUMENTS {0,1}
    --#SEVERITY MAJOR
    --#TIMEINDEX 99
    --#STATE DEGRADED
    ::= 110

--------------------------------------------------------------------------------
--------------------------------------------------------------------------------
--------------------------------------------------------------------------------

-- wtWebioAn1GraphPtSwTemp Group
------------------------

wtWebioAn1GraphPtSwSensors OBJECT-TYPE
    SYNTAX INTEGER (1)
    ACCESS read-only
    STATUS mandatory
    DESCRIPTION
        "Number of temperature sensors"
    ::= { wtWebioAn1GraphPtSwTemp 1 }

-- Interface Table

wtWebioAn1GraphPtSwSensorTable OBJECT-TYPE
    SYNTAX SEQUENCE OF WtWebioAn1GraphPtSwSensorEntry
    ACCESS not-accessible
    STATUS mandatory
    DESCRIPTION
        "List of sensors."
    ::= { wtWebioAn1GraphPtSwTemp 2 }

wtWebioAn1GraphPtSwSensorEntry OBJECT-TYPE
    SYNTAX WtWebioAn1GraphPtSwSensorEntry
    ACCESS not-accessible
    STATUS mandatory
    DESCRIPTION
        "Temperature sensor numbers."
    INDEX  { wtWebioAn1GraphPtSwSensorNo }
    ::= { wtWebioAn1GraphPtSwSensorTable 1 }

WtWebioAn1GraphPtSwSensorEntry ::= SEQUENCE {
    wtWebioAn1GraphPtSwSensorNo INTEGER
}

wtWebioAn1GraphPtSwSensorNo OBJECT-TYPE
    SYNTAX INTEGER (1)
    ACCESS read-only
    STATUS mandatory
    DESCRIPTION
        "Temperature sensor number."
    ::= { wtWebioAn1GraphPtSwSensorEntry 1 }


-- wtWebioAn1GraphPtSwTempValue Table

wtWebioAn1GraphPtSwTempValueTable OBJECT-TYPE
    SYNTAX SEQUENCE OF WtWebioAn1GraphPtSwTempValueEntry
    ACCESS not-accessible
    STATUS mandatory
    DESCRIPTION
        "List of temperature values corresponding to the channel numbers."
    ::= { wtWebioAn1GraphPtSwTemp 3 }

wtWebioAn1GraphPtSwTempValueEntry OBJECT-TYPE
    SYNTAX WtWebioAn1GraphPtSwTempValueEntry
    ACCESS not-accessible
    STATUS mandatory
    DESCRIPTION
        "Temperatures of the sensors."
    INDEX  { wtWebioAn1GraphPtSwSensorNo }
    ::= { wtWebioAn1GraphPtSwTempValueTable 1 }

WtWebioAn1GraphPtSwTempValueEntry ::= SEQUENCE{
    wtWebioAn1GraphPtSwTempValue OCTET STRING
}

wtWebioAn1GraphPtSwTempValue OBJECT-TYPE
    SYNTAX OCTET STRING (SIZE (5))
    ACCESS read-only
    STATUS mandatory
    DESCRIPTION
        "Temperature value of the sensor, ASCII, 5 characters in length."
    ::= { wtWebioAn1GraphPtSwTempValueEntry 1 }

-- wtWebioAn1GraphPtSwBinaryTempValue Table

wtWebioAn1GraphPtSwBinaryTempValueTable OBJECT-TYPE
    SYNTAX SEQUENCE OF WtWebioAn1GraphPtSwBinaryTempValueEntry
    ACCESS not-accessible
    STATUS mandatory
    DESCRIPTION
        "List of binary temperature values corresponding to the channel numbers."
    ::= { wtWebioAn1GraphPtSwTemp 4 }

wtWebioAn1GraphPtSwBinaryTempValueEntry OBJECT-TYPE
    SYNTAX WtWebioAn1GraphPtSwBinaryTempValueEntry
    ACCESS not-accessible
    STATUS mandatory
    DESCRIPTION
        "Binary temperature values of the sensors."
    INDEX  { wtWebioAn1GraphPtSwSensorNo }
    ::= { wtWebioAn1GraphPtSwBinaryTempValueTable 1 }

WtWebioAn1GraphPtSwBinaryTempValueEntry ::= SEQUENCE{
    wtWebioAn1GraphPtSwBinaryTempValue INTEGER
}

wtWebioAn1GraphPtSwBinaryTempValue OBJECT-TYPE
    SYNTAX INTEGER
    ACCESS read-only
    STATUS mandatory
    DESCRIPTION
        "Binary temperature value of the sensor in 1/10 degrees Celsius,
        signed number, 0x7FFF indicates an
        invalid measured value."
    ::= { wtWebioAn1GraphPtSwBinaryTempValueEntry 1 }

wtWebioAn1GraphPtSwOutputs OBJECT-TYPE
    SYNTAX INTEGER (1)
    ACCESS read-only
    STATUS mandatory
    DESCRIPTION
        "Number of outputs."
    ::= { wtWebioAn1GraphPtSwTemp 5 }

-- Interface Table

wtWebioAn1GraphPtSwOutputTable OBJECT-TYPE
    SYNTAX SEQUENCE OF WtWebioAn1GraphPtSwOutputEntry
    ACCESS not-accessible
    STATUS mandatory
    DESCRIPTION
        "List of outputs."
    ::= { wtWebioAn1GraphPtSwTemp 6 }

wtWebioAn1GraphPtSwOutputEntry OBJECT-TYPE
    SYNTAX WtWebioAn1GraphPtSwSensorEntry
    ACCESS not-accessible
    STATUS mandatory
    DESCRIPTION
        "Output numbers."
    INDEX  { wtWebioAn1GraphPtSwOutputNo }
    ::= { wtWebioAn1GraphPtSwOutputTable 1 }

WtWebioAn1GraphPtSwOutputEntry ::= SEQUENCE {
    wtWebioAn1GraphPtSwOutputNo INTEGER
}

wtWebioAn1GraphPtSwOutputNo OBJECT-TYPE
    SYNTAX INTEGER (1)
    ACCESS read-only
    STATUS mandatory
    DESCRIPTION
        "Output number."
    ::= { wtWebioAn1GraphPtSwOutputEntry 1 }

-- wtWebioAn1GraphPtSwBinaryOutputValue Table

wtWebioAn1GraphPtSwBinaryOutputValueTable OBJECT-TYPE
    SYNTAX SEQUENCE OF WtWebioAn1GraphPtSwBinaryOutputValueEntry
    ACCESS not-accessible
    STATUS mandatory
    DESCRIPTION
        "List of binary ouput values corresponding to the channel numbers."
    ::= { wtWebioAn1GraphPtSwTemp 7 }

wtWebioAn1GraphPtSwBinaryOutputValueEntry OBJECT-TYPE
    SYNTAX WtWebioAn1GraphPtSwBinaryOutputValueEntry
    ACCESS not-accessible
    STATUS mandatory
    DESCRIPTION
        "Binary states of the outputs."
    INDEX  { wtWebioAn1GraphPtSwOutputNo }
    ::= { wtWebioAn1GraphPtSwBinaryOutputValueTable 1 }

WtWebioAn1GraphPtSwBinaryOutputValueEntry ::= SEQUENCE{
    wtWebioAn1GraphPtSwBinaryOutputValue INTEGER
}

wtWebioAn1GraphPtSwBinaryOutputValue OBJECT-TYPE
    SYNTAX INTEGER {
    wtWebioAn1GraphPtSwBinaryOutput-OFF(0),
    wtWebioAn1GraphPtSwBinaryOutput-ON(1)
    }
    ACCESS read-only
    STATUS mandatory
    DESCRIPTION
        "Binary state of the output."
    ::= { wtWebioAn1GraphPtSwBinaryOutputValueEntry 1 }

-- wtWebioAn1GraphPtSwTempValuePkt Table

wtWebioAn1GraphPtSwTempValuePktTable OBJECT-TYPE
    SYNTAX SEQUENCE OF WtWebioAn1GraphPtSwTempValuePktEntry
    ACCESS not-accessible
    STATUS mandatory
    DESCRIPTION
        "List of temperature values corresponding to the channel numbers."
    ::= { wtWebioAn1GraphPtSwTemp 8 }

wtWebioAn1GraphPtSwTempValuePktEntry OBJECT-TYPE
    SYNTAX WtWebioAn1GraphPtSwTempValuePktEntry
    ACCESS not-accessible
    STATUS mandatory
    DESCRIPTION
        "Temperatures of the sensors."
    INDEX  { wtWebioAn1GraphPtSwSensorNo }
    ::= { wtWebioAn1GraphPtSwTempValuePktTable 1 }

WtWebioAn1GraphPtSwTempValuePktEntry ::= SEQUENCE{
    wtWebioAn1GraphPtSwTempValuePkt OCTET STRING
}

wtWebioAn1GraphPtSwTempValuePkt OBJECT-TYPE
    SYNTAX OCTET STRING (SIZE (5))
    ACCESS read-only
    STATUS mandatory
    DESCRIPTION
        "Temperature value of the sensor, ASCII, 5 characters in length, decimal point."
    ::= { wtWebioAn1GraphPtSwTempValuePktEntry 1 }

-- wtWebioAn1GraphPtSwSessCntrl Group
--------------------------------

wtWebioAn1GraphPtSwSessCntrlPassword OBJECT-TYPE
    SYNTAX OCTET STRING
    ACCESS read-write
    STATUS mandatory
    DESCRIPTION
        "Entering this password opens a session which is ended by writing a 1 to
        wtWebioAn1GraphPtSwSessCntrlLogout. When read this variable provides a string of
        length zero."
    ::= { wtWebioAn1GraphPtSwSessCntrl 1 }

wtWebioAn1GraphPtSwSessCntrlConfigMode OBJECT-TYPE
    SYNTAX INTEGER {
    wtWebioAn1GraphPtSwSessCntrl-NoSession(0),
    wtWebioAn1GraphPtSwSessCntrl-Session(1)
    }
    ACCESS read-only
    STATUS mandatory
    DESCRIPTION
        "When the device is in SNMP configuration mode, the value 1 is
        returned, otherwise 0. If the read value is 0 even though the
        password was written, the device is already in config mode and the
        variables can only be read."
    ::= { wtWebioAn1GraphPtSwSessCntrl 2 }

wtWebioAn1GraphPtSwSessCntrlLogout OBJECT-TYPE
    SYNTAX INTEGER
    ACCESS read-write
    STATUS mandatory
    DESCRIPTION
        "If the device is in configuration mode and the session was opened by
        this SNMP Manager, writing a 1 to this variable will end the session
        and all parameters are stored.
        Writing a 2 discards all entries again.
        When read this variable provides the value 0."
    ::= { wtWebioAn1GraphPtSwSessCntrl 3 }

wtWebioAn1GraphPtSwSessCntrlAdminPassword OBJECT-TYPE
    SYNTAX OCTET STRING
    ACCESS read-write
    STATUS mandatory
    DESCRIPTION
        "This password protects access to the variables with administrator rights.
        It can only be changed by the administrator. If no password was assigned,
        the valid password is public."
    ::= { wtWebioAn1GraphPtSwSessCntrl 4 }

wtWebioAn1GraphPtSwSessCntrlConfigPassword OBJECT-TYPE
    SYNTAX OCTET STRING
    ACCESS read-write
    STATUS mandatory
    DESCRIPTION
        "This password protects access to the variables with configurator rights. It can
        be changed by the administrator and by the configurator. If no password was assigned,
        the valid password is public. When read this variable provides a null-pointer."
    ::= { wtWebioAn1GraphPtSwSessCntrl 5 }


-- wtWebioAn1GraphPtSwText Group
------------------------

wtWebioAn1GraphPtSwDeviceName OBJECT-TYPE
    SYNTAX OCTET STRING
    ACCESS read-write
    STATUS mandatory
    DESCRIPTION
        "Name of the Webio, which is user definable."
    ::= { wtWebioAn1GraphPtSwText 1 }

wtWebioAn1GraphPtSwDeviceText OBJECT-TYPE
    SYNTAX OCTET STRING
    ACCESS read-write
    STATUS mandatory
    DESCRIPTION
        "Description of the Webio, which is user definable."
    ::= { wtWebioAn1GraphPtSwText 2 }

wtWebioAn1GraphPtSwDeviceLocation OBJECT-TYPE
    SYNTAX OCTET STRING
    ACCESS read-write
    STATUS mandatory
    DESCRIPTION
        "Description of the location of the Webio, which is user definable."
    ::= { wtWebioAn1GraphPtSwText 3 }

wtWebioAn1GraphPtSwDeviceContact OBJECT-TYPE
    SYNTAX OCTET STRING
    ACCESS read-write
    STATUS mandatory
    DESCRIPTION
        "Contact address of the system operator of the Webio, which is user definable."
    ::= { wtWebioAn1GraphPtSwText 4 }

-- wtWebioAn1GraphPtSwTimeZone Group
----------------------------

wtWebioAn1GraphPtSwTzOffsetHrs OBJECT-TYPE
    SYNTAX INTEGER
    ACCESS read-write
    STATUS mandatory
    DESCRIPTION
        "Offset hours for the time zone (winter time) with respect to UTC."
    ::= { wtWebioAn1GraphPtSwTimeZone 1 }

wtWebioAn1GraphPtSwTzOffsetMin OBJECT-TYPE
    SYNTAX INTEGER
    ACCESS read-write
    STATUS mandatory
    DESCRIPTION
        "Offset minutes for the time zone (winter time) with respect to UTC."
    ::= { wtWebioAn1GraphPtSwTimeZone 2 }

wtWebioAn1GraphPtSwTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebioAn1GraphPtSwTimeZone 3 }

wtWebioAn1GraphPtSwStTzOffsetHrs OBJECT-TYPE
    SYNTAX INTEGER
    ACCESS read-write
    STATUS mandatory
    DESCRIPTION
        "Offset hours of the time zone (summer time) with respect to UTC."
    ::= { wtWebioAn1GraphPtSwTimeZone 4 }

wtWebioAn1GraphPtSwStTzOffsetMin OBJECT-TYPE
    SYNTAX INTEGER
    ACCESS read-write
    STATUS mandatory
    DESCRIPTION
        "Offset minutes of the time zone (summer time) with respect to UTC."
    ::= { wtWebioAn1GraphPtSwTimeZone 5 }

wtWebioAn1GraphPtSwStTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebioAn1GraphPtSwTimeZone 6 }

wtWebioAn1GraphPtSwStTzStartMonth OBJECT-TYPE
    SYNTAX INTEGER {
    	wtWebioAn1GraphPtSwStartMonth-January(1),
    	wtWebioAn1GraphPtSwStartMonth-February(2),
    	wtWebioAn1GraphPtSwStartMonth-March(3),
    	wtWebioAn1GraphPtSwStartMonth-April(4),
    	wtWebioAn1GraphPtSwStartMonth-May(5),
    	wtWebioAn1GraphPtSwStartMonth-June(6),
    	wtWebioAn1GraphPtSwStartMonth-July(7),
    	wtWebioAn1GraphPtSwStartMonth-August(8),
    	wtWebioAn1GraphPtSwStartMonth-September(9),
    	wtWebioAn1GraphPtSwStartMonth-October(10),
    	wtWebioAn1GraphPtSwStartMonth-November(11),
    	wtWebioAn1GraphPtSwStartMonth-December(12)
    	}

    ACCESS read-write
    STATUS mandatory
    DESCRIPTION
        "Month in which the change is made from winter time to summer time."
    ::= { wtWebioAn1GraphPtSwTimeZone 7 }

wtWebioAn1GraphPtSwStTzStartMode OBJECT-TYPE
    SYNTAX INTEGER {
    	wtWebioAn1GraphPtSwStartMode-first(1),
    	wtWebioAn1GraphPtSwStartMode-second(2),
    	wtWebioAn1GraphPtSwStartMode-third(3),
    	wtWebioAn1GraphPtSwStartMode-fourth(4),
    	wtWebioAn1GraphPtSwStartMode-last(5)
    	}

    ACCESS read-write
    STATUS mandatory
    DESCRIPTION
        "Mode of the day of the week for which the change is made from winter time to summer time."
    ::= { wtWebioAn1GraphPtSwTimeZone 8 }

wtWebioAn1GraphPtSwStTzStartWday OBJECT-TYPE
    SYNTAX INTEGER {
    	wtWebioAn1GraphPtSwStartWday-Sunday(1),
    	wtWebioAn1GraphPtSwStartWday-Monday(2),
    	wtWebioAn1GraphPtSwStartWday-Tuesday(3),
    	wtWebioAn1GraphPtSwStartWday-Thursday(4),
    	wtWebioAn1GraphPtSwStartWday-Wednesday(5),
    	wtWebioAn1GraphPtSwStartWday-Friday(6),
    	wtWebioAn1GraphPtSwStartWday-Saturday(7)
    	}

    ACCESS read-write
    STATUS mandatory
    DESCRIPTION
        "Day of the week on which the change is made from winter time to summer time"
    ::= { wtWebioAn1GraphPtSwTimeZone 9 }

wtWebioAn1GraphPtSwStTzStartHrs OBJECT-TYPE
    SYNTAX INTEGER
    ACCESS read-write
    STATUS mandatory
    DESCRIPTION
        "Hour in which the time zone is changed from winter to summer time with
        respect to UTC."
    ::= { wtWebioAn1GraphPtSwTimeZone 10 }

wtWebioAn1GraphPtSwStTzStartMin OBJECT-TYPE
    SYNTAX INTEGER
    ACCESS read-write
    STATUS mandatory
    DESCRIPTION
        "Minute in which the time zone is changed from winter to summer time with
        respect to UTC."
    ::= { wtWebioAn1GraphPtSwTimeZone 11 }

wtWebioAn1GraphPtSwStTzStopMonth OBJECT-TYPE
    SYNTAX INTEGER {
    	wtWebioAn1GraphPtSwStopMonth-January(1),
    	wtWebioAn1GraphPtSwStopMonth-February(2),
    	wtWebioAn1GraphPtSwStopMonth-March(3),
    	wtWebioAn1GraphPtSwStopMonth-April(4),
    	wtWebioAn1GraphPtSwStopMonth-May(5),
    	wtWebioAn1GraphPtSwStopMonth-June(6),
    	wtWebioAn1GraphPtSwStopMonth-July(7),
    	wtWebioAn1GraphPtSwStopMonth-August(8),
    	wtWebioAn1GraphPtSwStopMonth-September(9),
    	wtWebioAn1GraphPtSwStopMonth-October(10),
    	wtWebioAn1GraphPtSwStopMonth-November(11),
    	wtWebioAn1GraphPtSwStopMonth-December(12)
    	}
    ACCESS read-write
    STATUS mandatory
    DESCRIPTION
        "Month in which the change is made from summer time to winter time."
   ::= { wtWebioAn1GraphPtSwTimeZone 12 }

wtWebioAn1GraphPtSwStTzStopMode OBJECT-TYPE
    SYNTAX INTEGER {
    	wtWebioAn1GraphPtSwStopMode-first(1),
    	wtWebioAn1GraphPtSwStopMode-second(2),
    	wtWebioAn1GraphPtSwStopMode-third(3),
    	wtWebioAn1GraphPtSwStopMode-fourth(4),
    	wtWebioAn1GraphPtSwStopMode-last(5)
    	}
    ACCESS read-write
    STATUS mandatory
    DESCRIPTION
        "Mode of the week day on which the change is made from summer time to winter time."
    ::= { wtWebioAn1GraphPtSwTimeZone 13 }

wtWebioAn1GraphPtSwStTzStopWday OBJECT-TYPE
    SYNTAX INTEGER {
    	wtWebioAn1GraphPtSwStopWday-Sunday(1),
    	wtWebioAn1GraphPtSwStopWday-Monday(2),
    	wtWebioAn1GraphPtSwStopWday-Tuesday(3),
    	wtWebioAn1GraphPtSwStopWday-Thursday(4),
    	wtWebioAn1GraphPtSwStopWday-Wednesday(5),
    	wtWebioAn1GraphPtSwStopWday-Friday(6),
    	wtWebioAn1GraphPtSwStopWday-Saturday(7)
    	}
    ACCESS read-write
    STATUS mandatory
    DESCRIPTION
        "Day of the week on which the change is made from summer time to winter time."
    ::= { wtWebioAn1GraphPtSwTimeZone 14 }

wtWebioAn1GraphPtSwStTzStopHrs OBJECT-TYPE
    SYNTAX INTEGER
    ACCESS read-write
    STATUS mandatory
    DESCRIPTION
        "Hour at which the time zone is changed from summer to winter time with
        respect to UTC."
    ::= { wtWebioAn1GraphPtSwTimeZone 15 }

wtWebioAn1GraphPtSwStTzStopMin OBJECT-TYPE
    SYNTAX INTEGER
    ACCESS read-write
    STATUS mandatory
    DESCRIPTION
        "Minute at which the time zone is changed from summer to winter time with
        respect to UTC."
    ::= { wtWebioAn1GraphPtSwTimeZone 16 }

-- wtWebioAn1GraphPtSwTimeServer Group
----------------------------

wtWebioAn1GraphPtSwTimeServer1 OBJECT-TYPE
    SYNTAX OCTET STRING
    ACCESS read-write
    STATUS mandatory
    DESCRIPTION
        "IP address or name of the 1st time server in ASCII"
    ::= { wtWebioAn1GraphPtSwTimeServer 1 }

wtWebioAn1GraphPtSwTimeServer2 OBJECT-TYPE
    SYNTAX OCTET STRING
    ACCESS read-write
    STATUS mandatory
    DESCRIPTION
        "IP address or name of the 2nd time server in ASCII"
    ::= { wtWebioAn1GraphPtSwTimeServer 2 }

wtWebioAn1GraphPtSwTsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebioAn1GraphPtSwTimeServer 3 }

wtWebioAn1GraphPtSwTsSyncTime OBJECT-TYPE
    SYNTAX INTEGER
    ACCESS read-write
    STATUS mandatory
    DESCRIPTION
        "Daily synchronisation time with the time server (hour: 0-23)."
    ::= { wtWebioAn1GraphPtSwTimeServer 4 }

-- wtWebioAn1GraphPtSwDeviceClock Group
----------------------------

wtWebioAn1GraphPtSwClockHrs OBJECT-TYPE
    SYNTAX INTEGER (0..23)
    ACCESS read-write
    STATUS mandatory
    DESCRIPTION
        "Clock hours taking into account the time zone settings."
    ::= { wtWebioAn1GraphPtSwDeviceClock 1 }

wtWebioAn1GraphPtSwClockMin OBJECT-TYPE
    SYNTAX INTEGER (0..59)
    ACCESS read-write
    STATUS mandatory
    DESCRIPTION
        "Clock minutes taking into account the time zone settings."
    ::= { wtWebioAn1GraphPtSwDeviceClock 2 }

wtWebioAn1GraphPtSwClockDay OBJECT-TYPE
    SYNTAX INTEGER (1..31)
    ACCESS read-write
    STATUS mandatory
    DESCRIPTION
        "Date: Day of the month, taking into account the time zone settings."
    ::= { wtWebioAn1GraphPtSwDeviceClock 3 }

wtWebioAn1GraphPtSwClockMonth OBJECT-TYPE
   SYNTAX INTEGER {
    	wtWebioAn1GraphPtSwClockMonth-January(1),
    	wtWebioAn1GraphPtSwClockMonth-February(2),
    	wtWebioAn1GraphPtSwClockMonth-March(3),
    	wtWebioAn1GraphPtSwClockMonth-April(4),
    	wtWebioAn1GraphPtSwClockMonth-May(5),
    	wtWebioAn1GraphPtSwClockMonth-June(6),
    	wtWebioAn1GraphPtSwClockMonth-July(7),
    	wtWebioAn1GraphPtSwClockMonth-August(8),
    	wtWebioAn1GraphPtSwClockMonth-September(9),
    	wtWebioAn1GraphPtSwClockMonth-October(10),
    	wtWebioAn1GraphPtSwClockMonth-November(11),
    	wtWebioAn1GraphPtSwClockMonth-December(12)
    	}
    ACCESS read-write
    STATUS mandatory
    DESCRIPTION
        "Date: Month, taking into account the time zone settings."
    ::= { wtWebioAn1GraphPtSwDeviceClock 4 }

wtWebioAn1GraphPtSwClockYear OBJECT-TYPE
    SYNTAX INTEGER (0..65535)
    ACCESS read-write
    STATUS mandatory
    DESCRIPTION
        "Date: Year, taking into account the time zone settings."
    ::= { wtWebioAn1GraphPtSwDeviceClock 5 }


-- wtWebioAn1GraphPtSwNetwork Group
------------------------

wtWebioAn1GraphPtSwIpAddress OBJECT-TYPE
    SYNTAX IpAddress
    ACCESS read-write
    STATUS mandatory
    DESCRIPTION
        "IP address of the Webio"
    ::= { wtWebioAn1GraphPtSwNetwork 1 }

wtWebioAn1GraphPtSwSubnetMask OBJECT-TYPE
    SYNTAX IpAddress
    ACCESS read-write
    STATUS mandatory
    DESCRIPTION
        "Subnet mask of the Webio"
    ::= { wtWebioAn1GraphPtSwNetwork 2 }

wtWebioAn1GraphPtSwGateway OBJECT-TYPE
    SYNTAX IpAddress
    ACCESS read-write
    STATUS mandatory
    DESCRIPTION
        "Gateway of the Webio"
    ::= { wtWebioAn1GraphPtSwNetwork 3 }

wtWebioAn1GraphPtSwDnsServer1 OBJECT-TYPE
    SYNTAX OCTET STRING
    ACCESS read-write
    STATUS mandatory
    DESCRIPTION
        "IP address of the 1st DNS server in ASCII"
    ::= { wtWebioAn1GraphPtSwNetwork 4 }

wtWebioAn1GraphPtSwDnsServer2 OBJECT-TYPE
    SYNTAX OCTET STRING
    ACCESS read-write
    STATUS mandatory
    DESCRIPTION
        "IP address of the 2nd DNS server in ASCII"
    ::= { wtWebioAn1GraphPtSwNetwork 5 }

wtWebioAn1GraphPtSwAddConfig OBJECT-TYPE
    SYNTAX OCTET STRING
    ACCESS read-write
    STATUS mandatory
    DESCRIPTION
        "Additional configuration (1=ON):
        Octet 1: unused
        Octet 2: unused
        Octet 3: unused
        Octet 4:
	        Bit 1: DHCP disable
	        Bit 0: BOOTP disable
	        "
    ::= { wtWebioAn1GraphPtSwNetwork 6 }

--  wtWebioAn1GraphPtSwHTTP Group
--------------------------------

wtWebioAn1GraphPtSwStartup OBJECT-TYPE
    SYNTAX OCTET STRING
    ACCESS read-write
    STATUS mandatory
    DESCRIPTION
        "Binary coded start page:
        Octet 1: unused
        Octet 2: unused
        Octet 3: unused
        Octet 4:
	        Bit 1: Index.htm
	        Bit 2: Home.htm
	        Bit 3: User.htm
	Only one page may be selected at a time."
    ::= { wtWebioAn1GraphPtSwHTTP 1 }

wtWebioAn1GraphPtSwGetHeaderEnable OBJECT-TYPE
    SYNTAX OCTET STRING
    ACCESS read-write
    STATUS mandatory
    DESCRIPTION
        "If these bits are set, every answer of a short form GET question will be lead
        by the IP-address and name of the device and/or a HTTP header:
        Octet 1: unused
        Octet 2: unused
        Octet 3: unused
        Octet 4:
        	Bit 1-6: unused
        	Bit 1  : GET HTTP enable
                Bit 0  : GET Header enable"
    ::= { wtWebioAn1GraphPtSwHTTP 2 }

wtWebioAn1GraphPtSwHttpPort OBJECT-TYPE
    SYNTAX INTEGER (1..65535)
    ACCESS read-write
    STATUS mandatory
    DESCRIPTION
        "Definition of the standard HTML port (Default: 80)."
    ::= { wtWebioAn1GraphPtSwHTTP 3 }


-- wtWebioAn1GraphPtSwMail Group
--------------------------------

wtWebioAn1GraphPtSwMailAdName OBJECT-TYPE
    SYNTAX OCTET STRING
    ACCESS read-write
    STATUS mandatory
    DESCRIPTION
        "Device name for mail administration."
    ::= { wtWebioAn1GraphPtSwMail 1 }

wtWebioAn1GraphPtSwMailReply OBJECT-TYPE
    SYNTAX OCTET STRING
    ACCESS read-write
    STATUS mandatory
    DESCRIPTION
        "Reply address for the mail server."
    ::= { wtWebioAn1GraphPtSwMail 2 }

wtWebioAn1GraphPtSwMailServer OBJECT-TYPE
    SYNTAX OCTET STRING
    ACCESS read-write
    STATUS mandatory
    DESCRIPTION
        "Name or IP address of the mail server."
    ::= { wtWebioAn1GraphPtSwMail 3 }

wtWebioAn1MailEnable OBJECT-TYPE
    SYNTAX OCTET STRING
    ACCESS read-write
    STATUS mandatory
    DESCRIPTION
        "Set this bit to enable the sending of mails:
        Octet 1: unused
        Octet 2: unused
        Octet 3: unused
        Octet 4:
        	Bit 1-7: unused
                Bit 0  : Mail enable"
    ::= { wtWebioAn1GraphPtSwMail 4 }

wtWebioAn1GraphPtSwMailAuthentication OBJECT-TYPE
    SYNTAX OCTET STRING (SIZE (4))
    ACCESS read-write
    STATUS mandatory
    DESCRIPTION
        "Selection of the authentication modi:
        The OCTETS are interpreted bit-by-bit, with each bit corresponding to an output.
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebioAn1GraphPtSwMail 5 }

wtWebioAn1GraphPtSwMailAuthUser OBJECT-TYPE
    SYNTAX OCTET STRING
    ACCESS read-write
    STATUS mandatory
    DESCRIPTION
        "Name of the user to be authenticated."
    ::= { wtWebioAn1GraphPtSwMail 6 }

wtWebioAn1GraphPtSwMailAuthPassword OBJECT-TYPE
    SYNTAX OCTET STRING
    ACCESS read-write
    STATUS mandatory
    DESCRIPTION
        "Authentication password."
    ::= { wtWebioAn1GraphPtSwMail 7 }

wtWebioAn1GraphPtSwMailPop3Server OBJECT-TYPE
    SYNTAX OCTET STRING
    ACCESS read-write
    STATUS mandatory
    DESCRIPTION
        "Name or Ip-address of the POP3 Servers."
    ::= { wtWebioAn1GraphPtSwMail 8 }


-- wtWebioAn1GraphPtSwSNMP Group
--------------------------------

wtWebioAn1GraphPtSwSnmpCommunityStringRead OBJECT-TYPE
    SYNTAX OCTET STRING
    ACCESS read-write
    STATUS mandatory
    DESCRIPTION
        "Community string read only"
    ::= { wtWebioAn1GraphPtSwSNMP 1 }

wtWebioAn1GraphPtSwSnmpCommunityStringReadWrite OBJECT-TYPE
    SYNTAX OCTET STRING
    ACCESS read-write
    STATUS mandatory
    DESCRIPTION
        "Community string read / write"
    ::= { wtWebioAn1GraphPtSwSNMP 2 }

wtWebioAn1GraphPtSwSystemTrapManagerIP OBJECT-TYPE
    SYNTAX OCTET STRING
    ACCESS read-write
    STATUS mandatory
    DESCRIPTION
        "Name or IP address of the TCP server which accepts the system trap."
    ::= { wtWebioAn1GraphPtSwSNMP 3 }

wtWebioAn1GraphPtSwSystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2-7: unused"
    ::= { wtWebioAn1GraphPtSwSNMP 4 }

wtWebioAn1GraphPtSwSnmpEnable OBJECT-TYPE
    SYNTAX OCTET STRING
    ACCESS read-write
    STATUS mandatory
    DESCRIPTION
        "Set bit 0 to enable SNMP.
        If disabled, the device did not respond to any SNMP requests.
        Bit 1 decided wether the community string of read operations
        is compared with the system password or not:
        Octet 1: unused
        Octet 2: unused
        Octet 3: unused
        Octet 4:
        	Bit 1-7: unused
        	Bit 0  : SNMP enable"
    ::= { wtWebioAn1GraphPtSwSNMP 5 }

wtWebioAn1GraphPtSwSnmpCommunityStringTrap OBJECT-TYPE
    SYNTAX OCTET STRING
    ACCESS read-write
    STATUS mandatory
    DESCRIPTION
        "Community string send within traps."
    ::= { wtWebioAn1GraphPtSwSNMP 6 }

-- wtWebioAn1GraphPtSwUDP Group
--------------------------------

wtWebioAn1GraphPtSwUdpPort OBJECT-TYPE
    SYNTAX INTEGER (1..65535)
    ACCESS read-write
    STATUS mandatory
    DESCRIPTION
        "Udp port to which the Udp queries ( short form GET requests) can be sent. This
        port number must be unique within the device."
    ::= { wtWebioAn1GraphPtSwUDP 1 }

wtWebioAn1GraphPtSwUdpEnable OBJECT-TYPE
    SYNTAX OCTET STRING
    ACCESS read-write
    STATUS mandatory
    DESCRIPTION
        "Set this bit to enable UDP support:
        Octet 1: unused
        Octet 2: unused
        Octet 3: unused
        Octet 4:
        	Bit 1-7: unused
                Bit 0  : UDP enable"
    ::= { wtWebioAn1GraphPtSwUDP 2 }


--  wtWebioAn1GraphPtSwSyslog Group
--------------------------------

wtWebioAn1GraphPtSwSyslogServerIP OBJECT-TYPE
    SYNTAX OCTET STRING
    ACCESS read-write
    STATUS mandatory
    DESCRIPTION
        "Name or IP address of the Syslog server, which accepts the Syslog messgaes."
    ::= { wtWebioAn1GraphPtSwSyslog 1 }

wtWebioAn1GraphPtSwSyslogServerPort OBJECT-TYPE
    SYNTAX INTEGER
    ACCESS read-write
    STATUS mandatory
    DESCRIPTION
        "Portnumber of the Syslog servers, default 514."
    ::= { wtWebioAn1GraphPtSwSyslog 2 }

wtWebioAn1GraphPtSwSyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebioAn1GraphPtSwSyslog 3 }

wtWebioAn1GraphPtSwSyslogEnable OBJECT-TYPE
    SYNTAX OCTET STRING
    ACCESS read-write
    STATUS mandatory
    DESCRIPTION
        "Set bit 0 to enable Syslog:
        Octet 1: unused
        Octet 2: unused
        Octet 3: unused
        Octet 4:
        	Bit 1-7: unused
                Bit 0  : Syslog enable"
    ::= { wtWebioAn1GraphPtSwSyslog 4 }

--  wtWebioAn1GraphPtSwFTP Group
--------------------------------

wtWebioAn1GraphPtSwFTPServerIP OBJECT-TYPE
    SYNTAX OCTET STRING
    ACCESS read-write
    STATUS mandatory
    DESCRIPTION
        "Name or IP address of the FTP server, which accepts the FTP messages."
    ::= { wtWebioAn1GraphPtSwFTP 1 }

wtWebioAn1GraphPtSwFTPServerControlPort OBJECT-TYPE
    SYNTAX INTEGER
    ACCESS read-write
    STATUS mandatory
    DESCRIPTION
        "Portnumber of the control port of the FTP server, default 21."
    ::= { wtWebioAn1GraphPtSwFTP 2 }

wtWebioAn1GraphPtSwFTPUserName OBJECT-TYPE
    SYNTAX OCTET STRING
    ACCESS read-write
    STATUS mandatory
    DESCRIPTION
        "FTP Loggin: user name."
    ::= { wtWebioAn1GraphPtSwFTP 3 }

wtWebioAn1GraphPtSwFTPPassword OBJECT-TYPE
    SYNTAX OCTET STRING
    ACCESS read-write
    STATUS mandatory
    DESCRIPTION
        "FTP Loggin: user password."
    ::= { wtWebioAn1GraphPtSwFTP 4 }

wtWebioAn1GraphPtSwFTPAccount OBJECT-TYPE
    SYNTAX OCTET STRING
    ACCESS read-write
    STATUS mandatory
    DESCRIPTION
        "FTP Loggin: name of account."
    ::= { wtWebioAn1GraphPtSwFTP 5 }

wtWebioAn1GraphPtSwFTPOption OBJECT-TYPE
    SYNTAX OCTET STRING
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebioAn1GraphPtSwFTP 6 }

wtWebioAn1GraphPtSwFTPEnable OBJECT-TYPE
    SYNTAX OCTET STRING
    ACCESS read-write
    STATUS mandatory
    DESCRIPTION
        "Set Bit 0 to enable FTP:
        Octet 1: unused
        Octet 2: unused
        Octet 3: unused
        Octet 4:
        	Bit 1-7: unused
                Bit 0  : FTP enable"
    ::= { wtWebioAn1GraphPtSwFTP 7 }

--  wtWebioAn1GraphPtSwLanguage Group
--------------------------------

wtWebioAn1GraphPtSwLanguageSelect OBJECT-TYPE
    SYNTAX OCTET STRING
    ACCESS read-write
    STATUS mandatory
    DESCRIPTION
        "Language selection:
        Octet 1: unused
        Octet 2: unused
        Octet 3: unused
        Octet 4:
        	Bit 2-7: unused
        	Bit 1  : English
                Bit 0  : German"
    ::= { wtWebioAn1GraphPtSwLanguage 1 }

--  wtWebioAn1GraphPtSwMQTT Group
--------------------------------

wtWebioAn1GraphPtSwMQTTEnable OBJECT-TYPE
    SYNTAX OCTET STRING
    ACCESS read-write
    STATUS mandatory
    DESCRIPTION
        "Bit 7 schaltet MQTT frei:
        Octet 1: ungenutzt
        Octet 2: ungenutzt
        Octet 3: ungenutzt
        Octet 4:
        	Bit 0-6: ungenutzt
                Bit 7  : MQTT enable"
    ::= { wtWebioAn1GraphPtSwMQTT 1 }

wtWebioAn1GraphPtSwMQTTBrockerIP OBJECT-TYPE
    SYNTAX OCTET STRING
    ACCESS read-write
    STATUS mandatory
    DESCRIPTION
        "Name or IP-address of the MQTT-Server."
    ::= { wtWebioAn1GraphPtSwMQTT 2 }

wtWebioAn1GraphPtSwMQTTUserName OBJECT-TYPE
    SYNTAX OCTET STRING
    ACCESS read-write
    STATUS mandatory
    DESCRIPTION
        "MQTT login  user name."
    ::= { wtWebioAn1GraphPtSwMQTT 3 }

wtWebioAn1GraphPtSwMQTTPassword OBJECT-TYPE
    SYNTAX OCTET STRING
    ACCESS read-write
    STATUS mandatory
    DESCRIPTION
        "MQTT login password."
    ::= { wtWebioAn1GraphPtSwMQTT 4 }

wtWebioAn1GraphPtSwMQTTLocalPort OBJECT-TYPE
    SYNTAX INTEGER
    ACCESS read-write
    STATUS mandatory
    DESCRIPTION
        "Local port number."
    ::= { wtWebioAn1GraphPtSwMQTT 5 }

wtWebioAn1GraphPtSwMQTTBrokerServerPort OBJECT-TYPE
    SYNTAX INTEGER
    ACCESS read-write
    STATUS mandatory
    DESCRIPTION
        "MQTT Server port number."
    ::= { wtWebioAn1GraphPtSwMQTT 6 }

wtWebioAn1GraphPtSwMQTTInterval OBJECT-TYPE
    SYNTAX INTEGER
    ACCESS read-write
    STATUS mandatory
    DESCRIPTION
        "Ping intervall, if no data has to be send: time in seconds."
    ::= { wtWebioAn1GraphPtSwMQTT 7 }

--  wtWebioAn1GraphPtSwREST Group
--------------------------------

wtWebioAn1GraphPtSwRESTEnable OBJECT-TYPE
    SYNTAX OCTET STRING
    ACCESS read-write
    STATUS mandatory
    DESCRIPTION
        "Bit 0 activates REST :
        Octet 1: unused
        Octet 2: unused
        Octet 3: unused
        Octet 4:
        	Bit 1-7: unused
            Bit 0  : REST enable"
    ::= { wtWebioAn1GraphPtSwREST 1 }

wtWebioAn1GraphPtSwRESTDigestAuthEnable OBJECT-TYPE
    SYNTAX OCTET STRING
    ACCESS read-write
    STATUS mandatory
    DESCRIPTION
        "Bit 0 activates Digest-Authentification:
        Octet 1: unused
        Octet 2: unused
        Octet 3: unused
        Octet 4:
        	Bit 1-7: unused
            Bit 0  : Digest Auth enable"
    ::= { wtWebioAn1GraphPtSwREST 2 }

-- wtWebioAn1GraphPtSwDatalogger Group
--------------------------------

wtWebioAn1GraphPtSwLoggerTimebase OBJECT-TYPE
    SYNTAX INTEGER {
    wtWebioAn1GraphPtSwDatalogger-1Min(1),
    wtWebioAn1GraphPtSwDatalogger-5Min(2),
    wtWebioAn1GraphPtSwDatalogger-15Min(3),
    wtWebioAn1GraphPtSwDatalogger-60Min(4)
    }
    ACCESS read-write
    STATUS mandatory
    DESCRIPTION
        "Time base of the data logger"
    ::= { wtWebioAn1GraphPtSwDatalogger 1 }

wtWebioAn1GraphPtSwLoggerSensorSel OBJECT-TYPE
    SYNTAX OCTET STRING (SIZE(4))
    ACCESS read-write
    STATUS mandatory
    DESCRIPTION
        "Binary coded sensor / output selection:
        Octet 1: unused
        Octet 2: unused
        Octet 3: unused
        Octet 4:
        	Bit 0: Sensor 1
        	Bit 1: Output 1
        	Bit 2-7: unused"
    ::= { wtWebioAn1GraphPtSwDatalogger 2 }

wtWebioAn1GraphPtSwDisplaySensorSel OBJECT-TYPE
    SYNTAX OCTET STRING (SIZE(4))
    ACCESS read-write
    STATUS mandatory
    DESCRIPTION
        "Binary coded sensor selection:
        only selected sensors / outputs will be shown in the graphical presentation:
        Octet 1: unused
        Octet 2: unused
        Octet 3: unused
        Octet 4:
        	Bit 0: Sensor 1
        	Bit 1: Output 1
        	Bit 2-7: unused"
    ::= { wtWebioAn1GraphPtSwDatalogger 3 }

-- Graph Sensor Color Table

wtWebioAn1GraphPtSwSensorColorTable OBJECT-TYPE
    SYNTAX SEQUENCE OF WtWebioAn1GraphPtSwSensorColorEntry
    ACCESS not-accessible
    STATUS mandatory
    DESCRIPTION
        "List of sensor colors for the praphical presentation."
    ::= { wtWebioAn1GraphPtSwDatalogger 4 }

wtWebioAn1GraphPtSwSensorColorEntry OBJECT-TYPE
    SYNTAX WtWebioAn1GraphPtSwSensorColorEntry
    ACCESS not-accessible
    STATUS mandatory
    DESCRIPTION
        "Index numbers of the sensors."
    INDEX  { wtWebioAn1GraphPtSwSensorNo }
    ::= { wtWebioAn1GraphPtSwSensorColorTable 1 }

WtWebioAn1GraphPtSwSensorColorEntry ::= SEQUENCE {
    wtWebioAn1GraphPtSwSensorColor OCTET STRING
}

wtWebioAn1GraphPtSwSensorColor OBJECT-TYPE
    SYNTAX OCTET STRING (SIZE(3))
    ACCESS read-write
    STATUS mandatory
    DESCRIPTION
        "Color of the sensors at the praphical presention."
    ::= { wtWebioAn1GraphPtSwSensorColorEntry 1 }

wtWebioAn1GraphPtSwAutoScaleEnable OBJECT-TYPE
    SYNTAX OCTET STRING
    ACCESS read-write
    STATUS mandatory
    DESCRIPTION
        "If bit 0 is set, vertical auto scale is enabled:
        Octet 1: unused
        Octet 2: unused
        Octet 3: unused
        Octet 4:
        	Bit 1-7: unused
                Bit 0  : Auto Scale enable"
    ::= { wtWebioAn1GraphPtSwDatalogger 5 }

wtWebioAn1GraphPtSwVerticalUpperLimit OBJECT-TYPE
    SYNTAX OCTET STRING
    ACCESS read-write
    STATUS mandatory
    DESCRIPTION
        "This value defines the maximum temperature shown in the graphical presentation,
        if no auto scaling is selected.
        Temperature in degrees with maximum 2 decimal places."
    ::= { wtWebioAn1GraphPtSwDatalogger 6 }

wtWebioAn1GraphPtSwVerticalLowerLimit OBJECT-TYPE
    SYNTAX OCTET STRING
    ACCESS read-write
    STATUS mandatory
    DESCRIPTION
        "This value defines the minimum temperature shown in the graphical presentation,
        if no auto scaling is selected.
        Temperature in degrees with maximum 2 decimal places."
    ::= { wtWebioAn1GraphPtSwDatalogger 7 }

wtWebioAn1GraphPtSwHorizontalZoom OBJECT-TYPE
    SYNTAX INTEGER {
    wtWebioAn1GraphPtSwZoom-25min(1),
    wtWebioAn1GraphPtSwZoom-75min(2),
    wtWebioAn1GraphPtSwZoom-5hrs(3),
    wtWebioAn1GraphPtSwZoom-30hrs(4),
    wtWebioAn1GraphPtSwZoom-5days(5),
    wtWebioAn1GraphPtSwZoom-25days(6)
    }
    ACCESS read-write
    STATUS mandatory
    DESCRIPTION
        "Defines the default zoom stage, if no auto scaling is selected."
    ::= { wtWebioAn1GraphPtSwDatalogger 8 }

-- wtWebioAn1GraphPtSwAlarm Group
----------------------------

wtWebioAn1GraphPtSwAlarmCount OBJECT-TYPE
    SYNTAX INTEGER (1..8)
    ACCESS read-only
    STATUS mandatory
    DESCRIPTION
        "Number of independent alarms."
    ::= { wtWebioAn1GraphPtSwAlarm 1 }

-- Alarm Interface Table

wtWebioAn1GraphPtSwAlarmIfTable OBJECT-TYPE
    SYNTAX SEQUENCE OF WtWebioAn1GraphPtSwAlarmIfEntry
    ACCESS not-accessible
    STATUS mandatory
    DESCRIPTION
        "List of alarm indices."
    ::= { wtWebioAn1GraphPtSwAlarm 2 }

wtWebioAn1GraphPtSwAlarmIfEntry OBJECT-TYPE
    SYNTAX WtWebioAn1GraphPtSwAlarmIfEntry
    ACCESS not-accessible
    STATUS mandatory
    DESCRIPTION
        "Numbers of the alarms."
    INDEX  { wtWebioAn1GraphPtSwAlarmNo }
    ::= { wtWebioAn1GraphPtSwAlarmIfTable 1 }

WtWebioAn1GraphPtSwAlarmIfEntry ::= SEQUENCE {
    wtWebioAn1GraphPtSwAlarmNo INTEGER
}

wtWebioAn1GraphPtSwAlarmNo OBJECT-TYPE
    SYNTAX INTEGER (1..8)
    ACCESS read-only
    STATUS mandatory
    DESCRIPTION
        "Alarm number."
    ::= { wtWebioAn1GraphPtSwAlarmIfEntry 1 }

-- Alarm Table

wtWebioAn1GraphPtSwAlarmTable OBJECT-TYPE
    SYNTAX SEQUENCE OF WtWebioAn1GraphPtSwAlarmEntry
    ACCESS not-accessible
    STATUS mandatory
    DESCRIPTION
        "List of settings depending on the alarm number."
    ::= { wtWebioAn1GraphPtSwAlarm 3 }

wtWebioAn1GraphPtSwAlarmEntry OBJECT-TYPE
    SYNTAX WtWebioAn1GraphPtSwAlarmEntry
    ACCESS not-accessible
    STATUS mandatory
    DESCRIPTION
        "Alarm parameters of the individual alarms."
    INDEX  { wtWebioAn1GraphPtSwAlarmNo }
    ::= { wtWebioAn1GraphPtSwAlarmTable 1 }

WtWebioAn1GraphPtSwAlarmEntry ::= SEQUENCE {
    wtWebioAn1GraphPtSwAlarmTrigger			OCTET STRING,
    wtWebioAn1GraphPtSwAlarmMin				OCTET STRING,
    wtWebioAn1GraphPtSwAlarmMax				OCTET STRING,
    wtWebioAn1GraphPtSwAlarmHysteresis			OCTET STRING,
    wtWebioAn1GraphPtSwAlarmDelay			OCTET STRING,
    wtWebioAn1GraphPtSwAlarmInterval			OCTET STRING,
    wtWebioAn1GraphPtSwAlarmEnable			OCTET STRING,
    wtWebioAn1GraphPtSwAlarmEMailAddr			OCTET STRING,
    wtWebioAn1GraphPtSwAlarmMailSubject			OCTET STRING,
    wtWebioAn1GraphPtSwAlarmMailText			OCTET STRING,
    wtWebioAn1GraphPtSwAlarmManagerIP			OCTET STRING,
    wtWebioAn1GraphPtSwAlarmTrapText			OCTET STRING,
    wtWebioAn1GraphPtSwAlarmMailOptions			OCTET STRING,
    wtWebioAn1GraphPtSwAlarmTcpIpAddr			OCTET STRING,
    wtWebioAn1GraphPtSwAlarmTcpPort			INTEGER,
    wtWebioAn1GraphPtSwAlarmTcpText			OCTET STRING,
    wtWebioAn1GraphPtSwAlarmClearMailSubject		OCTET STRING,
    wtWebioAn1GraphPtSwAlarmClearMailText		OCTET STRING,
    wtWebioAn1GraphPtSwAlarmClearTrapText		OCTET STRING,
    wtWebioAn1GraphPtSwAlarmClearTcpText		OCTET STRING,
    wtWebioAn1GraphPtSwAlarmSyslogIpAddr		OCTET STRING,
    wtWebioAn1GraphPtSwAlarmSyslogPort			INTEGER,
    wtWebioAn1GraphPtSwAlarmSyslogText			OCTET STRING,
    wtWebioAn1GraphPtSwAlarmFtpDataPort			OCTET STRING,
    wtWebioAn1GraphPtSwAlarmFtpFileName			OCTET STRING,
    wtWebioAn1GraphPtSwAlarmFtpText			OCTET STRING,
    wtWebioAn1GraphPtSwAlarmFtpClearText		OCTET STRING,
    wtWebioAn1GraphPtSwAlarmFtpOption			OCTET STRING,
    wtWebioAn1GraphPtSwAlarmTimerCron			OCTET STRING,
    wtWebioAn1GraphPtSwAlarmDeltaTemp			OCTET STRING,
    wtWebioAn1GraphPtSwAlarmName 			OCTET STRING,
    wtWebioAn1GraphPtSwAlarmActive 			OCTET STRING,
    wtWebioAn1GraphPtSwAlarmHttpReqAuthEnable		OCTET STRING,
    wtWebioAn1GraphPtSwAlarmHttpReqAuthUser		OCTET STRING,
    wtWebioAn1GraphPtSwAlarmHttpReqAuthPassword	OCTET STRING,
    wtWebioAn1GraphPtSwAlarmHttpReqSetUrl		OCTET STRING,
    wtWebioAn1GraphPtSwAlarmHttpReqClearUrl		OCTET STRING,
    wtWebioAn1GraphPtSwAlarmHttpReqServerPort		OCTET STRING,
    wtWebioAn1GraphPtSwAlarmMqttTopicPath		OCTET STRING,
    wtWebioAn1GraphPtSwAlarmMqttTopicSetTopic		OCTET STRING,
    wtWebioAn1GraphPtSwAlarmMqttTopicClear		OCTET STRING,
    wtWebioAn1GraphPtSwAlarmSensorLostSelection	OCTET STRING,
    wtWebioAn1GraphPtSwAlarmLimitWindow			OCTET STRING

}

wtWebioAn1GraphPtSwAlarmTrigger OBJECT-TYPE
    SYNTAX OCTET STRING (SIZE(4))
    ACCESS read-write
    STATUS mandatory
    DESCRIPTION
        "Binary coded trigger conditions:
        Octet 1: unused
        Octet 2: unused
        Octet 3:
        	Bit 0  : Timer
        	Bit 1  : ColdStart
        	Bit 2  : WarmStart
        	Bit 3  : Sensor lost
        	Bit 4-7: unused
        Octet 4:
        	Bit 0  : Sensor 1
        	Bit 1-7: unused"
    ::= { wtWebioAn1GraphPtSwAlarmEntry 1 }

wtWebioAn1GraphPtSwAlarmMin OBJECT-TYPE
    SYNTAX OCTET STRING
    ACCESS read-write
    STATUS mandatory
    DESCRIPTION
        "Minimum temperature in degrees with maximum 2 decimal places."
    ::= { wtWebioAn1GraphPtSwAlarmEntry 2 }

wtWebioAn1GraphPtSwAlarmMax OBJECT-TYPE
    SYNTAX OCTET STRING
    ACCESS read-write
    STATUS mandatory
    DESCRIPTION
        "Maximum temperature in degrees with maximum 2 decimal places."
    ::= { wtWebioAn1GraphPtSwAlarmEntry 3 }

wtWebioAn1GraphPtSwAlarmHysteresis OBJECT-TYPE
    SYNTAX OCTET STRING
    ACCESS read-write
    STATUS mandatory
    DESCRIPTION
        "Temperature changes of this size clears the alarm state (MAX-hyst, MIN+hyst.)
        , in degrees with maximum 2 decimal places."
    ::= { wtWebioAn1GraphPtSwAlarmEntry 4 }

wtWebioAn1GraphPtSwAlarmDelay OBJECT-TYPE
    SYNTAX OCTET STRING
    ACCESS read-write
    STATUS mandatory
    DESCRIPTION
        "Alarm will be delayed by setting this time while stable alarm
        condition occur (time in minutes)."
    ::= { wtWebioAn1GraphPtSwAlarmEntry 5 }


wtWebioAn1GraphPtSwAlarmInterval OBJECT-TYPE
    SYNTAX OCTET STRING
    ACCESS read-write
    STATUS mandatory
    DESCRIPTION
        "Send interval for alarm messages."
    ::= { wtWebioAn1GraphPtSwAlarmEntry 6 }

wtWebioAn1GraphPtSwAlarmEnable OBJECT-TYPE
    SYNTAX OCTET STRING (SIZE(4))
    ACCESS read-write
    STATUS mandatory
    DESCRIPTION
        "Binary coded alarm enable:
        Octet 1: unused
        Octet 2: unused
        Octet 3: unused
        Octet 4:
        	Bit 0  : Output switch enable
		Bit 1  : Mail Enable
        	Bit 2  : SNMP Trap enable
        	Bit 3  : TCP Client enable
        	Bit 4  : Syslog Messages enable
        	Bit 5  : FTP enable
        	Bit 6-7: unused"
    ::= { wtWebioAn1GraphPtSwAlarmEntry 7 }

wtWebioAn1GraphPtSwAlarmEMailAddr OBJECT-TYPE
    SYNTAX OCTET STRING
    ACCESS read-write
    STATUS mandatory
    DESCRIPTION
        "E-Mail address for sending the alarm mail to."
    ::= { wtWebioAn1GraphPtSwAlarmEntry 8 }

wtWebioAn1GraphPtSwAlarmMailSubject OBJECT-TYPE
    SYNTAX OCTET STRING
    ACCESS read-write
    STATUS mandatory
    DESCRIPTION
        "Subject line for alarm mail."
    ::= { wtWebioAn1GraphPtSwAlarmEntry 9 }

wtWebioAn1GraphPtSwAlarmMailText OBJECT-TYPE
    SYNTAX OCTET STRING
    ACCESS read-write
    STATUS mandatory
    DESCRIPTION
        "Alarm mail text: <Tn> provides the current temperature; n = 1..8.
        <Z> provides the current time."
    ::= { wtWebioAn1GraphPtSwAlarmEntry 10 }

wtWebioAn1GraphPtSwAlarmManagerIP OBJECT-TYPE
    SYNTAX OCTET STRING
    ACCESS read-write
    STATUS mandatory
    DESCRIPTION
        "Name or IP address of the SNMP Manager which accepts the trap."
    ::= { wtWebioAn1GraphPtSwAlarmEntry 11 }

wtWebioAn1GraphPtSwAlarmTrapText OBJECT-TYPE
    SYNTAX OCTET STRING
    ACCESS read-write
    STATUS mandatory
    DESCRIPTION
        "This text is sent in the trap body."
    ::= { wtWebioAn1GraphPtSwAlarmEntry 12 }

wtWebioAn1GraphPtSwAlarmMailOptions OBJECT-TYPE
    SYNTAX OCTET STRING (SIZE(4))
    ACCESS read-write
    STATUS mandatory
    DESCRIPTION
        "Binary coded options:
        Octet 1: unused
        Octet 2: unused
        Octet 3: unused
        Octet 4:
		Bit 0  :	Attach Thermo.csv Enable
		Bit 1  :	CSV-Data_since_last_report
        	Bit 2-7:	unused"
    ::= { wtWebioAn1GraphPtSwAlarmEntry 13 }

wtWebioAn1GraphPtSwAlarmTcpIpAddr OBJECT-TYPE
    SYNTAX OCTET STRING
    ACCESS read-write
    STATUS mandatory
    DESCRIPTION
        "Name or IP address of the TCP server which accepts the trap."
    ::= { wtWebioAn1GraphPtSwAlarmEntry 14 }

wtWebioAn1GraphPtSwAlarmTcpPort OBJECT-TYPE
    SYNTAX INTEGER (1..65535)
    ACCESS read-write
    STATUS mandatory
    DESCRIPTION
        "Port number of the TCP server which accepts the trap."
    ::= { wtWebioAn1GraphPtSwAlarmEntry 15 }

wtWebioAn1GraphPtSwAlarmTcpText OBJECT-TYPE
    SYNTAX OCTET STRING
    ACCESS read-write
    STATUS mandatory
    DESCRIPTION
        "This text is sent in the TCP trap body."
    ::= { wtWebioAn1GraphPtSwAlarmEntry 16 }

wtWebioAn1GraphPtSwAlarmClearMailSubject OBJECT-TYPE
    SYNTAX OCTET STRING
    ACCESS read-write
    STATUS mandatory
    DESCRIPTION
        "Subject line for alarm clear mail."
    ::= { wtWebioAn1GraphPtSwAlarmEntry 17 }

wtWebioAn1GraphPtSwAlarmClearMailText OBJECT-TYPE
    SYNTAX OCTET STRING
    ACCESS read-write
    STATUS mandatory
    DESCRIPTION
        " Alarm clear mail text: <Tn> provides the current temperature; n = 1..8. <Z> provides the current time."
    ::= { wtWebioAn1GraphPtSwAlarmEntry 18 }

wtWebioAn1GraphPtSwAlarmClearTrapText OBJECT-TYPE
    SYNTAX OCTET STRING
    ACCESS read-write
    STATUS mandatory
    DESCRIPTION
        "This text is sent in the trap body."
    ::= { wtWebioAn1GraphPtSwAlarmEntry 19 }

wtWebioAn1GraphPtSwAlarmClearTcpText OBJECT-TYPE
    SYNTAX OCTET STRING
    ACCESS read-write
    STATUS mandatory
    DESCRIPTION
        "This text is sent in the TCP trap body."
    ::= { wtWebioAn1GraphPtSwAlarmEntry 20 }

wtWebioAn1GraphPtSwAlarmSyslogIpAddr OBJECT-TYPE
    SYNTAX IpAddress
    ACCESS read-write
    STATUS mandatory
    DESCRIPTION
        "IP address of the syslog server to which the Webio device should send syslog messages."
    ::= { wtWebioAn1GraphPtSwAlarmEntry 21 }

wtWebioAn1GraphPtSwAlarmSyslogPort OBJECT-TYPE
    SYNTAX INTEGER (1..65535)
    ACCESS read-write
    STATUS mandatory
    DESCRIPTION
        "Port number of the syslog server to which the Webio device should send syslog messages."
    ::= { wtWebioAn1GraphPtSwAlarmEntry 22 }

wtWebioAn1GraphPtSwAlarmSyslogText OBJECT-TYPE
    SYNTAX OCTET STRING
    ACCESS read-write
    STATUS mandatory
    DESCRIPTION
        "Every message starts with the priority key, a time stamp and the host ip address, according RFC3164.
        This text appears in the following syslog message body."
    ::= { wtWebioAn1GraphPtSwAlarmEntry 23 }

wtWebioAn1GraphPtSwAlarmSyslogClearText OBJECT-TYPE
    SYNTAX OCTET STRING
    ACCESS read-write
    STATUS mandatory
    DESCRIPTION
        "Every message starts with the priority key, a time stamp and the host ip address, according RFC3164.
        This text appears in the following syslog message body."
    ::= { wtWebioAn1GraphPtSwAlarmEntry 24 }

wtWebioAn1GraphPtSwAlarmFtpDataPort OBJECT-TYPE
    SYNTAX OCTET STRING
    ACCESS read-write
    STATUS mandatory
    DESCRIPTION
        "Local data port: 1..65535 or AUTO: the next free port will be assigned."
    ::= { wtWebioAn1GraphPtSwAlarmEntry 25 }

wtWebioAn1GraphPtSwAlarmFtpFileName OBJECT-TYPE
    SYNTAX OCTET STRING
    ACCESS read-write
    STATUS mandatory
    DESCRIPTION
        "Name of the file including path informations."
    ::= { wtWebioAn1GraphPtSwAlarmEntry 26 }

wtWebioAn1GraphPtSwAlarmFtpText OBJECT-TYPE
    SYNTAX OCTET STRING
    ACCESS read-write
    STATUS mandatory
    DESCRIPTION
        "Message text to store on the FTP server."
    ::= { wtWebioAn1GraphPtSwAlarmEntry 27 }

wtWebioAn1GraphPtSwAlarmFtpClearText OBJECT-TYPE
    SYNTAX OCTET STRING
    ACCESS read-write
    STATUS mandatory
    DESCRIPTION
        "Alarm clear message to store on the FTP server."
    ::= { wtWebioAn1GraphPtSwAlarmEntry 28 }

wtWebioAn1GraphPtSwAlarmFtpOptions OBJECT-TYPE
    SYNTAX OCTET STRING (SIZE(4))
    ACCESS read-write
    STATUS mandatory
    DESCRIPTION
        "Binary coded options, select only one option at the same time:
        STORE  = replace file
        APPEND = append message at the end of the file

        Octet 1: unused
        Octet 2: unused
        Octet 3: unused
        Octet 4:
		Bit 0  :	STORE
		Bit 1  :	APPEND
        	Bit 2-7:	unused"
    ::= { wtWebioAn1GraphPtSwAlarmEntry 29 }

wtWebioAn1GraphPtSwAlarmTimerCron OBJECT-TYPE
    SYNTAX OCTET STRING
    ACCESS read-write
    STATUS mandatory
    DESCRIPTION
        "This entry contains 5 text fields space or tab seperated for time trigger definition.
        Each field must match with the actual time to trigger a message, weekday and day of month
        are interpreted separately.
        1: Minutes	Range 0-59
        2. Hours	Range 0-23, 0 is midnight
        3: Day of month	Range 1-31
        4: Month	Range 1-12
        5: Weekday	Range 0-6, 0 is sunday

        Syntax for every field:
         - an asterix (*) enables every possible setting of a field
         - single numbers seperated by commas
         - a partition within the allowed range (1-5)
         - step size within an partition of the allowed range (0-59/2: every second minute)."
    ::= { wtWebioAn1GraphPtSwAlarmEntry 30 }

wtWebioAn1GraphPtSwAlarmDeltaTemp OBJECT-TYPE
    SYNTAX OCTET STRING
    ACCESS read-write
    STATUS mandatory
    DESCRIPTION
        "Maximum rate of change  degrees/min with maximum 2 decimal places.
        Compared with the average of a period of 5 minutes."
    ::= { wtWebioAn1GraphPtSwAlarmEntry 31 }

-- __JB__
wtWebioAn1GraphPtSwAlarmName OBJECT-TYPE
    SYNTAX OCTET STRING
    ACCESS read-write
    STATUS mandatory
    DESCRIPTION
        "Alert name"
    ::= { wtWebioAn1GraphPtSwAlarmEntry 39 }

-- __JB__
wtWebioAn1GraphPtSwAlarmActive OBJECT-TYPE
    SYNTAX OCTET STRING
    ACCESS read-write
    STATUS mandatory
    DESCRIPTION
        "Alert active
			1 = ON
			0 = OFF"
    ::= { wtWebioAn1GraphPtSwAlarmEntry 40 }

wtWebioAn1GraphPtSwAlarmHttpReqAuthEnable OBJECT-TYPE
    SYNTAX OCTET STRING
    ACCESS read-write
    STATUS mandatory
    DESCRIPTION
        "Binary coded options, select only one option at the same time:
        OCTET 1: unused
        OCTET 2: unused
        OCTET 3: unused
        OCTET 4, Bit 1-7: unused
        Bit 0  : HHTP Request Authentication enable"
    ::= { wtWebioAn1GraphPtSwAlarmEntry 61 }

wtWebioAn1GraphPtSwAlarmHttpReqAuthUser OBJECT-TYPE
    SYNTAX OCTET STRING
    ACCESS read-write
    STATUS mandatory
    DESCRIPTION
	"HTTP Request: User"
    ::= { wtWebioAn1GraphPtSwAlarmEntry 62 }

wtWebioAn1GraphPtSwAlarmHttpReqAuthPassword OBJECT-TYPE
    SYNTAX OCTET STRING
    ACCESS read-write
    STATUS mandatory
    DESCRIPTION
	"HTTP Request: Password"
    ::= { wtWebioAn1GraphPtSwAlarmEntry 63 }

wtWebioAn1GraphPtSwAlarmHttpReqSetUrl OBJECT-TYPE
    SYNTAX OCTET STRING
    ACCESS read-write
    STATUS mandatory
    DESCRIPTION
	"HTTP Request: Set URL"
    ::= { wtWebioAn1GraphPtSwAlarmEntry 64 }

wtWebioAn1GraphPtSwAlarmHttpReqClearUrl OBJECT-TYPE
    SYNTAX OCTET STRING
    ACCESS read-write
    STATUS mandatory
    DESCRIPTION
	"HTTP Request: Clear URL"
    ::= { wtWebioAn1GraphPtSwAlarmEntry 65 }

wtWebioAn1GraphPtSwAlarmHttpReqServerPort OBJECT-TYPE
    SYNTAX INTEGER (1..65535)
    ACCESS read-write
    STATUS mandatory
    DESCRIPTION
	"HTTP Request: Server Port"
    ::= { wtWebioAn1GraphPtSwAlarmEntry 66 }

wtWebioAn1GraphPtSwAlarmMqttTopicPath OBJECT-TYPE
    SYNTAX OCTET STRING
    ACCESS read-write
    STATUS mandatory
    DESCRIPTION
	"MQTT Publish: Topic path"
    ::= { wtWebioAn1GraphPtSwAlarmEntry 67 }

wtWebioAn1GraphPtSwAlarmMqttTopicSetTopic OBJECT-TYPE
    SYNTAX OCTET STRING
    ACCESS read-write
    STATUS mandatory
    DESCRIPTION
	"MQTT Publish: Topic SET message"
    ::= { wtWebioAn1GraphPtSwAlarmEntry 68 }

wtWebioAn1GraphPtSwAlarmMqttTopicClear OBJECT-TYPE
    SYNTAX OCTET STRING
    ACCESS read-write
    STATUS mandatory
    DESCRIPTION
	"MQTT Publish: Topic CLEAR message"
    ::= { wtWebioAn1GraphPtSwAlarmEntry 69 }

wtWebioAn1GraphPtSwAlarmSensorLostSelection OBJECT-TYPE
    SYNTAX OCTET STRING
    ACCESS read-write
    STATUS mandatory
    DESCRIPTION
        "Binary coded options:
        OCTET 1: unused
        OCTET 2: unused
        OCTET 3: unused
        OCTET 4, Bit 1-7: unused
        Bit 0  : Sensor 0"
    ::= { wtWebioAn1GraphPtSwAlarmEntry 70 }

wtWebioAn1GraphPtSwAlarmLimitWindow OBJECT-TYPE
    SYNTAX OCTET STRING
    ACCESS read-write
    STATUS mandatory
    DESCRIPTION
        "If window type is INSIDE the alarm is genereted when the temperature
        is greater minumum value and lower than maximum value. If window type is OUTSIDE
        the alarm is generated when the measured value is lower than the minimum value
        or greater than the maximum value.
		Binary coded options, select only one option at the same time:
        OCTET 1: unused
        OCTET 2: unused
        OCTET 3: unused
        OCTET 4, Bit 2-7: unused
		Bit 1  : inside window
        Bit 0  : outside window"
    ::= { wtWebioAn1GraphPtSwAlarmEntry 71 }


-- wtWebioAn1GraphPtSwGraphicsBase Group
----------------------------

wtWebioAn1GraphPtSwGraphicsBaseEnable OBJECT-TYPE
    SYNTAX OCTET STRING
    ACCESS read-write
    STATUS mandatory
    DESCRIPTION
        "Defines the viewing options of the graphic:
        Octet 1: unused
        Octet 2: unused
        Octet 3: unused
        Octet 4:
                Bit 0  : Auto scroll enable
                Bit 1  : Show table
                Bit 2  : Show graph
                Bit 3  : Show control buttons
                Bit 4  : Show config menu
                Bit 5  : Show alarm monitor
                Bit 6-7: unused"
    ::= { wtWebioAn1GraphPtSwGraphicsBase 1 }

wtWebioAn1GraphPtSwGraphicsBaseWidth OBJECT-TYPE
    SYNTAX INTEGER
    ACCESS read-write
    STATUS mandatory
    DESCRIPTION
        "Defines the width of the graphic in pixels."
    ::= { wtWebioAn1GraphPtSwGraphicsBase 2 }

wtWebioAn1GraphPtSwGraphicsBaseHeight OBJECT-TYPE
        SYNTAX INTEGER
        ACCESS read-write
        STATUS mandatory
        DESCRIPTION
            "Defines the height of the graphic in pixels."
        ::= { wtWebioAn1GraphPtSwGraphicsBase 3 }

wtWebioAn1GraphPtSwGraphicsBaseFrameColor OBJECT-TYPE
    SYNTAX OCTET STRING (SIZE(3))
    ACCESS read-write
    STATUS mandatory
    DESCRIPTION
        "Frame color definition in RGB."
    ::= { wtWebioAn1GraphPtSwGraphicsBase 4 }

wtWebioAn1GraphPtSwGraphicsBaseBackgroundColor OBJECT-TYPE
    SYNTAX OCTET STRING (SIZE(3))
    ACCESS read-write
    STATUS mandatory
    DESCRIPTION
        "Background color definition in RGB."
    ::= { wtWebioAn1GraphPtSwGraphicsBase 5 }

wtWebioAn1GraphPtSwGraphicsBasePollingrate OBJECT-TYPE
        SYNTAX INTEGER
        ACCESS read-write
        STATUS mandatory
        DESCRIPTION
            "Defines the pollingrate in seconds,
            which defines the refreshing intervall of the graphic."
        ::= { wtWebioAn1GraphPtSwGraphicsBase 6 }

-- wtWebioAn1GraphPtSwGraphicsSelect Group
----------------------------

wtWebioAn1GraphPtSwGraphicsSelectDisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0  : Sensor 1
		Bit 1-7: unused"
    ::= { wtWebioAn1GraphPtSwGraphicsSelect 1 }

wtWebioAn1GraphPtSwGraphicsSelectDisplayShowExtrem OBJECT-TYPE
    SYNTAX OCTET STRING (SIZE(4))
    ACCESS read-write
    STATUS mandatory
    DESCRIPTION
        "Binary coded sensor selection:
        only selected sensors will be shown with minima and maxima:
        Octet 1: unused
        Octet 2: unused
        Octet 3: unused
        Octet 4:
        	Bit 0  : Sensor 1
		Bit 1-7: unused"
    ::= { wtWebioAn1GraphPtSwGraphicsSelect 2 }

-- Graph Sensor Color Table

wtWebioAn1GraphPtSw2SensorColorTable OBJECT-TYPE
    SYNTAX SEQUENCE OF WtWebioAn1GraphPtSw2SensorColorEntry
    ACCESS not-accessible
    STATUS mandatory
    DESCRIPTION
        "List of sensor colors for the praphical presentation."
    ::= { wtWebioAn1GraphPtSwGraphicsSelect 3 }

wtWebioAn1GraphPtSw2SensorColorEntry OBJECT-TYPE
    SYNTAX WtWebioAn1GraphPtSw2SensorColorEntry
    ACCESS not-accessible
    STATUS mandatory
    DESCRIPTION
        "Numbers of the sensors."
    INDEX  { wtWebioAn1GraphPtSwSensorNo }
    ::= { wtWebioAn1GraphPtSw2SensorColorTable 1 }

WtWebioAn1GraphPtSw2SensorColorEntry ::= SEQUENCE {
    wtWebioAn1GraphPtSw2GraphicsSensorColor OCTET STRING,
    wtWebioAn1GraphPtSw2GraphicsSelectScale OCTET STRING
}

wtWebioAn1GraphPtSw2GraphicsSensorColor OBJECT-TYPE
    SYNTAX OCTET STRING (SIZE(3))
    ACCESS read-write
    STATUS mandatory
    DESCRIPTION
        "Color of the sensors at the praphical presention."
    ::= { wtWebioAn1GraphPtSw2SensorColorEntry 1 }

wtWebioAn1GraphPtSw2GraphicsSelectScale OBJECT-TYPE
    SYNTAX OCTET STRING
    ACCESS read-write
    STATUS mandatory
    DESCRIPTION
        "Assignes one of 4 scales to a sensor:
        Octet 1: unused
        Octet 2: unused
        Octet 3: unused
        Octet 4:
                Bit 0  : Use Scale 1
                Bit 1-7: unused"
    ::= { wtWebioAn1GraphPtSw2SensorColorEntry 2 }

-- wtWebioAn1GraphPtSwGraphicsScale Group
----------------------------

wtWebioAn1GraphPtSwGraphicsScaleAutoScaleEnable OBJECT-TYPE
    SYNTAX OCTET STRING
    ACCESS read-write
    STATUS mandatory
    DESCRIPTION
        "Select the Auto Scale Mode:
        Octet 1: unused
        Octet 2: unused
        Octet 3: unused
        Octet 4:
                Bit 0  : Scale 1 Auto scale enable
                Bit 1-7: unused"
    ::= { wtWebioAn1GraphPtSwGraphicsScale 1 }

wtWebioAn1GraphPtSwGraphicsScaleAutoFitEnable OBJECT-TYPE
    SYNTAX OCTET STRING
    ACCESS read-write
    STATUS mandatory
    DESCRIPTION
        "Select the Auto Fit Mode::
        Octet 1: unused
        Octet 2: unused
        Octet 3: unused
        Octet 4:
                Bit 0  : Scale 1 Auto fit enable
                Bit 1-7: unused"
    ::= { wtWebioAn1GraphPtSwGraphicsScale 2 }

wtWebioAn1GraphPtSwGraphicsScale1Min OBJECT-TYPE
    SYNTAX INTEGER
    ACCESS read-only
    STATUS mandatory
    DESCRIPTION
        "Scale 1: Minimum."
    ::= { wtWebioAn1GraphPtSwGraphicsScale 3 }

wtWebioAn1GraphPtSwGraphicsScale2Min OBJECT-TYPE
    SYNTAX INTEGER
    ACCESS read-only
    STATUS mandatory
    DESCRIPTION
        "Scale 2: Minimum."
    ::= { wtWebioAn1GraphPtSwGraphicsScale 4 }

wtWebioAn1GraphPtSwGraphicsScale3Min OBJECT-TYPE
    SYNTAX INTEGER
    ACCESS read-only
    STATUS mandatory
    DESCRIPTION
        "Scale 3: Minimum."
    ::= { wtWebioAn1GraphPtSwGraphicsScale 5 }

wtWebioAn1GraphPtSwGraphicsScale4Min OBJECT-TYPE
    SYNTAX INTEGER
    ACCESS read-only
    STATUS mandatory
    DESCRIPTION
        "Scale 4: Minimum."
    ::= { wtWebioAn1GraphPtSwGraphicsScale 6 }

wtWebioAn1GraphPtSwGraphicsScale1Max OBJECT-TYPE
    SYNTAX INTEGER
    ACCESS read-only
    STATUS mandatory
    DESCRIPTION
        "Scale 1: Maximum."
    ::= { wtWebioAn1GraphPtSwGraphicsScale 7 }

wtWebioAn1GraphPtSwGraphicsScale2Max OBJECT-TYPE
    SYNTAX INTEGER
    ACCESS read-only
    STATUS mandatory
    DESCRIPTION
        "Scale 2: Maximum."
    ::= { wtWebioAn1GraphPtSwGraphicsScale 8 }

wtWebioAn1GraphPtSwGraphicsScale3Max OBJECT-TYPE
    SYNTAX INTEGER
    ACCESS read-only
    STATUS mandatory
    DESCRIPTION
        "Scale 3: Maximum."
    ::= { wtWebioAn1GraphPtSwGraphicsScale 9 }

wtWebioAn1GraphPtSwGraphicsScale4Max OBJECT-TYPE
    SYNTAX INTEGER
    ACCESS read-only
    STATUS mandatory
    DESCRIPTION
        "Scale 4: Maximum."
    ::= { wtWebioAn1GraphPtSwGraphicsScale 10 }

wtWebioAn1GraphPtSwGraphicsScale1Unit OBJECT-TYPE
    SYNTAX OCTET STRING
    ACCESS read-only
    STATUS mandatory
    DESCRIPTION
        "Scale 1: Unit."
    ::= { wtWebioAn1GraphPtSwGraphicsScale 11 }

wtWebioAn1GraphPtSwGraphicsScale2Unit OBJECT-TYPE
    SYNTAX OCTET STRING
    ACCESS read-only
    STATUS mandatory
    DESCRIPTION
        "Scale 2: Unit."
    ::= { wtWebioAn1GraphPtSwGraphicsScale 12 }

wtWebioAn1GraphPtSwGraphicsScale3Unit OBJECT-TYPE
    SYNTAX OCTET STRING
    ACCESS read-only
    STATUS mandatory
    DESCRIPTION
        "Scale 3: Unit."
    ::= { wtWebioAn1GraphPtSwGraphicsScale 13 }

wtWebioAn1GraphPtSwGraphicsScale4Unit OBJECT-TYPE
    SYNTAX OCTET STRING
    ACCESS read-only
    STATUS mandatory
    DESCRIPTION
        "Scale 4: Unit."
    ::= { wtWebioAn1GraphPtSwGraphicsScale 14 }

-- wtWebioAn1GraphPtSwReport Group
----------------------------

wtWebioAn1GraphPtSwReportCount OBJECT-TYPE
    SYNTAX INTEGER (1..8)
    ACCESS read-only
    STATUS mandatory
    DESCRIPTION
        "Number of independent Reports."
    ::= { wtWebioAn1GraphPtSwReport 1 }

-- Report Interface Table

wtWebioAn1GraphPtSwReportIfTable OBJECT-TYPE
    SYNTAX SEQUENCE OF WtWebioAn1GraphPtSwReportIfEntry
    ACCESS not-accessible
    STATUS mandatory
    DESCRIPTION
        "List of Report indices."
    ::= { wtWebioAn1GraphPtSwReport 2 }

wtWebioAn1GraphPtSwReportIfEntry OBJECT-TYPE
    SYNTAX WtWebioAn1GraphPtSwReportIfEntry
    ACCESS not-accessible
    STATUS mandatory
    DESCRIPTION
        "Numbers of the Reports."
    INDEX  { wtWebioAn1GraphPtSwReportNo }
    ::= { wtWebioAn1GraphPtSwReportIfTable 1 }

WtWebioAn1GraphPtSwReportIfEntry ::= SEQUENCE {
    wtWebioAn1GraphPtSwReportNo INTEGER
}

wtWebioAn1GraphPtSwReportNo OBJECT-TYPE
    SYNTAX INTEGER
    ACCESS read-only
    STATUS mandatory
    DESCRIPTION
        "Report number."
    ::= { wtWebioAn1GraphPtSwReportIfEntry 1 }

-- Report Table

wtWebioAn1GraphPtSwReportTable OBJECT-TYPE
    SYNTAX SEQUENCE OF WtWebioAn1GraphPtSwReportEntry
    ACCESS not-accessible
    STATUS mandatory
    DESCRIPTION
        "List of settings depending on the Report number."
    ::= { wtWebioAn1GraphPtSwReport 3 }

wtWebioAn1GraphPtSwReportEntry OBJECT-TYPE
    SYNTAX WtWebioAn1GraphPtSwReportEntry
    ACCESS not-accessible
    STATUS mandatory
    DESCRIPTION
        "Report parameters of the individual Reports."
    INDEX  { wtWebioAn1GraphPtSwReportNo }
    ::= { wtWebioAn1GraphPtSwReportTable 1 }

WtWebioAn1GraphPtSwReportEntry ::= SEQUENCE {
    wtWebioAn1GraphPtSwReportEnable			OCTET STRING,
    wtWebioAn1GraphPtSwReportTimerCron			OCTET STRING,
    wtWebioAn1GraphPtSwReportMethodeEnable		OCTET STRING,
    wtWebioAn1GraphPtSwReportEMailAddr			OCTET STRING,
    wtWebioAn1GraphPtSwReportMailSubject		OCTET STRING,
    wtWebioAn1GraphPtSwReportMailText			OCTET STRING,
    wtWebioAn1GraphPtSwReportManagerIP			OCTET STRING,
    wtWebioAn1GraphPtSwReportTrapText			OCTET STRING,
    wtWebioAn1GraphPtSwReportMailOptions		OCTET STRING,
    wtWebioAn1GraphPtSwReportTcpIpAddr			OCTET STRING,
    wtWebioAn1GraphPtSwReportTcpPort			INTEGER,
    wtWebioAn1GraphPtSwReportTcpText			OCTET STRING,
    wtWebioAn1GraphPtSwReportClearMailSubject		OCTET STRING,
    wtWebioAn1GraphPtSwReportClearMailText		OCTET STRING,
    wtWebioAn1GraphPtSwReportClearTrapText		OCTET STRING,
    wtWebioAn1GraphPtSwReportClearTcpText		OCTET STRING,
    wtWebioAn1GraphPtSwReportSyslogIpAddr		OCTET STRING,
    wtWebioAn1GraphPtSwReportSyslogPort			INTEGER,
    wtWebioAn1GraphPtSwReportSyslogText			OCTET STRING,
    wtWebioAn1GraphPtSwReportSyslogClearText		OCTET STRING,
    wtWebioAn1GraphPtSwReportFtpDataPort		OCTET STRING,
    wtWebioAn1GraphPtSwReportFtpFileName		OCTET STRING,
    wtWebioAn1GraphPtSwReportFtpText			OCTET STRING,
    wtWebioAn1GraphPtSwReportFtpClearText		OCTET STRING,
    wtWebioAn1GraphPtSwReportFtpOption			OCTET STRING
}

wtWebioAn1GraphPtSwReportEnable OBJECT-TYPE
    SYNTAX OCTET STRING (SIZE(4))
    ACCESS read-write
    STATUS mandatory
    DESCRIPTION
        "Binär kodierte Triggerbedingungen:
        Octet 1: unused
        Octet 2: unused
        Octet 3: unused
        Octet 4:
        	Bit 0: Report enable
        	Bit 1-7: unused"
    ::= { wtWebioAn1GraphPtSwReportEntry 1 }

wtWebioAn1GraphPtSwReportTimerCron OBJECT-TYPE
    SYNTAX OCTET STRING
    ACCESS read-write
    STATUS mandatory
    DESCRIPTION
        "This entry defines a time window for alarm 1-8 and a activation time for the report.
        A time window is definied by start and stop time stamp, seperated by a space or tab.
        The activation time of the report is defined by a single start time stamp.
        Each time stamp contains 5 space or tab seperated text fields for time trigger definition.
        Each field must match with the actual time to trigger an action, weekday and day of month
        are interpreted separatley.
        1: Minutes	Range 0-59
        2. Hours	Range 0-23, 0 is midnight
        3: Day of month	Range 1-31
        4: Month	Range 1-12
        5: Weekday	Range 0-6, 0 is sunday

        Syntax for every field:
         - an asterix (*) enables every possible setting of a field
         - single numbers seperated by commas (i.e.: 2,14,22)
         - a partition within the allowed range (i.e.: 1-5)
         - step size within a partition of the allowed range (i.e.: 0-59/2  every second minute)."
    ::= { wtWebioAn1GraphPtSwReportEntry 2 }

wtWebioAn1GraphPtSwReportMethodeEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  TCP Client enable
        	Bit 3:	Syslog enable
        	Bit 4:  FTP Client enable"
    ::= { wtWebioAn1GraphPtSwReportEntry 3 }

wtWebioAn1GraphPtSwReportEMailAddr OBJECT-TYPE
    SYNTAX OCTET STRING
    ACCESS read-write
    STATUS mandatory
    DESCRIPTION
        "E-Mail address for sending the alarm mail to."
    ::= { wtWebioAn1GraphPtSwReportEntry 8 }

wtWebioAn1GraphPtSwReportMailSubject OBJECT-TYPE
    SYNTAX OCTET STRING
    ACCESS read-write
    STATUS mandatory
    DESCRIPTION
        "Subject line for alarm mail."
    ::= { wtWebioAn1GraphPtSwReportEntry 9 }

wtWebioAn1GraphPtSwReportMailText OBJECT-TYPE
    SYNTAX OCTET STRING
    ACCESS read-write
    STATUS mandatory
    DESCRIPTION
        "Report mail text: <Mn> provides the current temperature; n = 1..2.
        <Z> provides the current time."
    ::= { wtWebioAn1GraphPtSwReportEntry 10 }

wtWebioAn1GraphPtSwReportManagerIP OBJECT-TYPE
    SYNTAX OCTET STRING
    ACCESS read-write
    STATUS mandatory
    DESCRIPTION
        "Name or IP address of the SNMP Manager which accepts the trap."
    ::= { wtWebioAn1GraphPtSwReportEntry 11 }

wtWebioAn1GraphPtSwReportTrapText OBJECT-TYPE
    SYNTAX OCTET STRING
    ACCESS read-write
    STATUS mandatory
    DESCRIPTION
        "This text is sent in the trap body."
    ::= { wtWebioAn1GraphPtSwReportEntry 12 }

wtWebioAn1GraphPtSwReportMailOptions OBJECT-TYPE
    SYNTAX OCTET STRING (SIZE(4))
    ACCESS read-write
    STATUS mandatory
    DESCRIPTION
        "Binary coded options:
        Octet 1: unused
        Octet 2: unused
        Octet 3: unused
        Octet 4:
		Bit 0  :	Attach Logger.csv Enable
		Bit 1  :	CSV-Data_since_last_report
        	Bit 2-7:	unused"
    ::= { wtWebioAn1GraphPtSwReportEntry 13 }

wtWebioAn1GraphPtSwReportTcpIpAddr OBJECT-TYPE
    SYNTAX OCTET STRING
    ACCESS read-write
    STATUS mandatory
    DESCRIPTION
        "Name or IP address of the TCP server which accepts the trap."
    ::= { wtWebioAn1GraphPtSwReportEntry 14 }

wtWebioAn1GraphPtSwReportTcpPort OBJECT-TYPE
    SYNTAX INTEGER (1..65535)
    ACCESS read-write
    STATUS mandatory
    DESCRIPTION
        "Port number of the TCP server which accepts the trap."
    ::= { wtWebioAn1GraphPtSwReportEntry 15 }

wtWebioAn1GraphPtSwReportTcpText OBJECT-TYPE
    SYNTAX OCTET STRING
    ACCESS read-write
    STATUS mandatory
    DESCRIPTION
        "This text is sent in the TCP trap body."
    ::= { wtWebioAn1GraphPtSwReportEntry 16 }

wtWebioAn1GraphPtSwReportClearMailSubject OBJECT-TYPE
    SYNTAX OCTET STRING
    ACCESS read-write
    STATUS mandatory
    DESCRIPTION
        "Subject line for alarm clear mail."
    ::= { wtWebioAn1GraphPtSwReportEntry 17 }

wtWebioAn1GraphPtSwReportClearMailText OBJECT-TYPE
    SYNTAX OCTET STRING
    ACCESS read-write
    STATUS mandatory
    DESCRIPTION
        "Report clear mail text: <Mn> provides the current temperature; n = 1..2.
        <Z> provides the current time."
    ::= { wtWebioAn1GraphPtSwReportEntry 18 }

wtWebioAn1GraphPtSwReportClearTrapText OBJECT-TYPE
    SYNTAX OCTET STRING
    ACCESS read-write
    STATUS mandatory
    DESCRIPTION
        "This text is sent in the trap body."
    ::= { wtWebioAn1GraphPtSwReportEntry 19 }

wtWebioAn1GraphPtSwReportClearTcpText OBJECT-TYPE
    SYNTAX OCTET STRING
    ACCESS read-write
    STATUS mandatory
    DESCRIPTION
        "This text is sent in the TCP trap body."
    ::= { wtWebioAn1GraphPtSwReportEntry 20 }

wtWebioAn1GraphPtSwReportSyslogIpAddr OBJECT-TYPE
    SYNTAX OCTET STRING
    ACCESS read-write
    STATUS mandatory
    DESCRIPTION
        "IP address of the syslog server to which the Webio device should send syslog messages."
    ::= { wtWebioAn1GraphPtSwReportEntry 24 }

wtWebioAn1GraphPtSwReportSyslogPort OBJECT-TYPE
    SYNTAX INTEGER (1..65535)
    ACCESS read-write
    STATUS mandatory
    DESCRIPTION
        "Port number of the syslog server to which the Webio device should send syslog messages."
    ::= { wtWebioAn1GraphPtSwReportEntry 25 }

wtWebioAn1GraphPtSwReportSyslogText OBJECT-TYPE
    SYNTAX OCTET STRING
    ACCESS read-write
    STATUS mandatory
    DESCRIPTION
        "Every message starts with the priority key, a time stamp and the host ip address, according RFC3164.
        This text appears in the following syslog message body."
    ::= { wtWebioAn1GraphPtSwReportEntry 26 }

wtWebioAn1GraphPtSwReportSyslogClearText OBJECT-TYPE
    SYNTAX OCTET STRING
    ACCESS read-write
    STATUS mandatory
    DESCRIPTION
        "Every message starts with the priority key, a time stamp and the host ip address, according RFC3164.
        This text appears in the following syslog message body of a alarm clear message."
    ::= { wtWebioAn1GraphPtSwReportEntry 27 }

wtWebioAn1GraphPtSwReportFtpDataPort OBJECT-TYPE
    SYNTAX OCTET STRING
    ACCESS read-write
    STATUS mandatory
    DESCRIPTION
        "Local data port: 1..65535 or AUTO: the next free port will be assigned."
    ::= { wtWebioAn1GraphPtSwReportEntry 28 }

wtWebioAn1GraphPtSwReportFtpFileName OBJECT-TYPE
    SYNTAX OCTET STRING
    ACCESS read-write
    STATUS mandatory
    DESCRIPTION
        "Name of the file including path informations."
    ::= { wtWebioAn1GraphPtSwReportEntry 29 }

wtWebioAn1GraphPtSwReportFtpText OBJECT-TYPE
    SYNTAX OCTET STRING
    ACCESS read-write
    STATUS mandatory
    DESCRIPTION
        "Message text to store on the FTP server."
    ::= { wtWebioAn1GraphPtSwReportEntry 30 }

wtWebioAn1GraphPtSwReportFtpClearText OBJECT-TYPE
    SYNTAX OCTET STRING
    ACCESS read-write
    STATUS mandatory
    DESCRIPTION
        "Report clear message to store on the FTP server."
    ::= { wtWebioAn1GraphPtSwReportEntry 31 }

wtWebioAn1GraphPtSwReportFtpOption OBJECT-TYPE
    SYNTAX OCTET STRING (SIZE(4))
    ACCESS read-write
    STATUS mandatory
    DESCRIPTION
        "Binary coded options, select only one option at the same time:
        STORE  = replace file
        APPEND = append message at the end of the file

        Octet 1: unused
        Octet 2: unused
        Octet 3: unused
        Octet 4:
		Bit 0  :	STORE
		Bit 1  :	APPEND
        	Bit 2-7:	unused"
    ::= { wtWebioAn1GraphPtSwReportEntry 32 }

-- wtWebioAn1GraphPtSwPorts Group
----------------------------

-- Table

wtWebioAn1GraphPtSwPortTable OBJECT-TYPE
    SYNTAX SEQUENCE OF WtWebioAn1GraphPtSwPortEntry
    ACCESS not-accessible
    STATUS mandatory
    DESCRIPTION
        "List of settings depending on the sensor number."
    ::= { wtWebioAn1GraphPtSwPorts 1 }

wtWebioAn1GraphPtSwPortEntry OBJECT-TYPE
    SYNTAX WtWebioAn1GraphPtSwPortEntry
    ACCESS not-accessible
    STATUS mandatory
    DESCRIPTION
        "Sensor parameters for the individual sensors."
    INDEX  { wtWebioAn1GraphPtSwSensorNo }
    ::= { wtWebioAn1GraphPtSwPortTable 1 }

WtWebioAn1GraphPtSwPortEntry ::= SEQUENCE {
    wtWebioAn1GraphPtSwPortName			OCTET STRING,
    wtWebioAn1GraphPtSwPortText			OCTET STRING,
    wtWebioAn1GraphPtSwPortOffset1		OCTET STRING,
    wtWebioAn1GraphPtSwPortTemperature1		OCTET STRING,
    wtWebioAn1GraphPtSwPortOffset2		OCTET STRING,
    wtWebioAn1GraphPtSwPortTemperature2		OCTET STRING,
    wtWebioAn1GraphPtSwPortComment		OCTET STRING,
    wtWebioAn1GraphPtSwPortSensorUnit		OCTET STRING,
    wtWebioAn1GraphPtPortSensorUnit		OCTET STRING
}

wtWebioAn1GraphPtSwPortName OBJECT-TYPE
    SYNTAX OCTET STRING
    ACCESS read-write
    STATUS mandatory
    DESCRIPTION
        "Name of the sensor."
    ::= { wtWebioAn1GraphPtSwPortEntry 1 }

wtWebioAn1GraphPtSwPortText OBJECT-TYPE
    SYNTAX OCTET STRING
    ACCESS read-write
    STATUS mandatory
    DESCRIPTION
        "Description of the sensor."
    ::= { wtWebioAn1GraphPtSwPortEntry 2 }

wtWebioAn1GraphPtSwPortOffset1 OBJECT-TYPE
    SYNTAX OCTET STRING
    ACCESS read-write
    STATUS mandatory
    DESCRIPTION
        "Offset calibration: Offset in degrees with maximum 2 decimal places at temperature 1."
    ::= { wtWebioAn1GraphPtSwPortEntry 3 }

wtWebioAn1GraphPtSwPortTemperature1 OBJECT-TYPE
    SYNTAX OCTET STRING
    ACCESS read-write
    STATUS mandatory
    DESCRIPTION
        "Offset calibration: Reference temperature 1 in degrees with maximum 2 decimal places."
    ::= { wtWebioAn1GraphPtSwPortEntry 4 }

wtWebioAn1GraphPtSwPortOffset2 OBJECT-TYPE
    SYNTAX OCTET STRING
    ACCESS read-write
    STATUS mandatory
    DESCRIPTION
        "Offset calibration: Offset in degrees with maximum 2 decimal places at temperature 2."
    ::= { wtWebioAn1GraphPtSwPortEntry 5 }

wtWebioAn1GraphPtSwPortTemperature2 OBJECT-TYPE
    SYNTAX OCTET STRING
    ACCESS read-write
    STATUS mandatory
    DESCRIPTION
        "Offset calibration: Reference temperature 1 in degrees with maximum 2 decimal places."
    ::= { wtWebioAn1GraphPtSwPortEntry 6 }

wtWebioAn1GraphPtSwPortComment OBJECT-TYPE
    SYNTAX OCTET STRING
    ACCESS read-write
    STATUS mandatory
    DESCRIPTION
        "Offset calibration: informations of date, name of operator, reference devices."
    ::= { wtWebioAn1GraphPtSwPortEntry 7 }

wtWebioAn1GraphPtSwPortSensorSelect OBJECT-TYPE
    SYNTAX OCTET STRING (SIZE(4))
    ACCESS read-write
    STATUS mandatory
    DESCRIPTION
        "Binary coded options of the sensor:
        Octet 1: unused
        Octet 2: unused
        Octet 3: unused
        Octet 4:
		Bit 0  :	PT100 (default)
		Bit 1  :	PT1000
        	Bit 2-7:	unused"
    ::= { wtWebioAn1GraphPtSwPortEntry 8 }

wtWebioAn1GraphPtSwPortSensorUnit OBJECT-TYPE
    SYNTAX OCTET STRING (SIZE(4))
    ACCESS read-write
    STATUS mandatory
    DESCRIPTION
        "Binary coded options of the sensor:
        Octet 1: unused
        Octet 2: unused
        Octet 3: unused
        Octet 4:
		Bit 0  : Celsius (default)
		Bit 1  : Fahrenheit
		Bit 2  : Kelvin
        	Bit 3-7: unused"
    ::= { wtWebioAn1GraphPtSwPortEntry 9 }

wtWebioAn1GraphPtSwPortOutputTable OBJECT-TYPE
    SYNTAX SEQUENCE OF WtWebioAn1GraphPtSwPortOutputEntry
    ACCESS not-accessible
    STATUS mandatory
    DESCRIPTION
        "List of settings depending on the sensor number."
    ::= { wtWebioAn1GraphPtSwPorts 3 }

wtWebioAn1GraphPtSwPortOutputEntry OBJECT-TYPE
    SYNTAX WtWebioAn1GraphPtSwPortOutputEntry
    ACCESS not-accessible
    STATUS mandatory
    DESCRIPTION
        "Parameters for the individual outputs."
    INDEX  { wtWebioAn1GraphPtSwOutputNo }
    ::= { wtWebioAn1GraphPtSwPortOutputTable 1 }

WtWebioAn1GraphPtSwPortOutputEntry ::= SEQUENCE {
    wtWebioAn1GraphPtSwPortOutputName		OCTET STRING,
    wtWebioAn1GraphPtSwPortOutputText		OCTET STRING,
    wtWebioAn1GraphPtSwPortOutputPolarity	OCTET STRING,
    wtWebioAn1GraphPtSwPortOutputComment	OCTET STRING,
    wtWebioAn1GraphPortOutputResetEnable	OCTET STRING
}

wtWebioAn1GraphPtSwPortOutputName OBJECT-TYPE
    SYNTAX OCTET STRING
    ACCESS read-write
    STATUS mandatory
    DESCRIPTION
        "Name of the output."
    ::= { wtWebioAn1GraphPtSwPortOutputEntry 1 }

wtWebioAn1GraphPtSwPortOutputText OBJECT-TYPE
    SYNTAX OCTET STRING
    ACCESS read-write
    STATUS mandatory
    DESCRIPTION
        "Description of the output."
    ::= { wtWebioAn1GraphPtSwPortOutputEntry 2 }

wtWebioAn1GraphPtSwPortOutputPolarity OBJECT-TYPE
    SYNTAX OCTET STRING (SIZE(4))
    ACCESS read-write
    STATUS mandatory
    DESCRIPTION
        "Binary coded options of the output:
        Octet 1: unused
        Octet 2: unused
        Octet 3: unused
        Octet 4:
		Bit 0  : Normally open (default)
		Bit 1  : Normally closed
        	Bit 2-7: unused"
    ::= { wtWebioAn1GraphPtSwPortOutputEntry 3 }

wtWebioAn1GraphPtSwPortOutputComment OBJECT-TYPE
    SYNTAX OCTET STRING
    ACCESS read-write
    STATUS mandatory
    DESCRIPTION
        "Additional informations of date, name of operator, reference devices."
    ::= { wtWebioAn1GraphPtSwPortOutputEntry 4 }

wtWebioAn1GraphPortOutputResetEnable OBJECT-TYPE
    SYNTAX OCTET STRING (SIZE(4))
    ACCESS read-write
    STATUS mandatory
    DESCRIPTION
        "Binary coded options of the output:
        Octet 1: unused
        Octet 2: unused
        Octet 3: unused
        Octet 4:
		Bit 0  : Manual Reset enable (default off)
        	Bit 1-7: unused"
    ::= { wtWebioAn1GraphPtSwPortOutputEntry 5 }


-- wtWebioAn1GraphPtSwManufact Group
----------------------------

wtWebioAn1GraphPtSwMfName OBJECT-TYPE
    SYNTAX OCTET STRING
    ACCESS read-write
    STATUS mandatory
    DESCRIPTION
        "Manufacturer company name"
    ::= { wtWebioAn1GraphPtSwManufact 1 }

wtWebioAn1GraphPtSwMfAddr OBJECT-TYPE
    SYNTAX OCTET STRING
    ACCESS read-write
    STATUS mandatory
    DESCRIPTION
        "Manufacturer address."
    ::= { wtWebioAn1GraphPtSwManufact 2 }

wtWebioAn1GraphPtSwMfHotline OBJECT-TYPE
    SYNTAX OCTET STRING
    ACCESS read-write
    STATUS mandatory
    DESCRIPTION
        "Manufacturer hotline."
    ::= { wtWebioAn1GraphPtSwManufact 3 }

wtWebioAn1GraphPtSwMfInternet OBJECT-TYPE
    SYNTAX OCTET STRING
    ACCESS read-write
    STATUS mandatory
    DESCRIPTION
        "Manufacturer Internet address."
    ::= { wtWebioAn1GraphPtSwManufact 4 }

wtWebioAn1GraphPtSwMfDeviceTyp OBJECT-TYPE
    SYNTAX OCTET STRING
    ACCESS read-write
    STATUS mandatory
    DESCRIPTION
        "Manufacturer device name (model number)."
    ::= { wtWebioAn1GraphPtSwManufact 5 }

wtWebioAn1GraphPtSwMfOrderNo OBJECT-TYPE
    SYNTAX OCTET STRING
    ACCESS read-write
    STATUS mandatory
    DESCRIPTION
        "Manufacturer part number."
    ::= { wtWebioAn1GraphPtSwManufact 6 }

-- wtWebioAn1GraphPtSwDiag Group
----------------------------

wtWebioAn1GraphPtSwDiagErrorCount OBJECT-TYPE
    SYNTAX INTEGER
    ACCESS read-only
    STATUS mandatory
    DESCRIPTION
        "Number of entries in the error memory."
    ::= { wtWebioAn1GraphPtSwDiag 1 }

wtWebioAn1GraphPtSwDiagBinaryError OBJECT-TYPE
    SYNTAX OCTET STRING
    ACCESS read-only
    STATUS mandatory
    DESCRIPTION
        "Error causes coded bit-by-bit."
    ::= { wtWebioAn1GraphPtSwDiag 2 }

wtWebioAn1GraphPtSwDiagErrorIndex OBJECT-TYPE
    SYNTAX INTEGER
    ACCESS read-write
    STATUS mandatory
    DESCRIPTION
        "The value of this variable is used as an index to read
        an error massege from wtWebioAn1GraphPtSwDiagErrorMessage.
        Errors are numbered from 1 to wtWebioAn1GraphPtSwDiagErrorCount.
        Writing a valid value into this variable, making the appropriate
        message readable from wtWebioAn1GraphPtSwDiagErrorMessage."
    ::= { wtWebioAn1GraphPtSwDiag 3 }

wtWebioAn1GraphPtSwDiagErrorMessage OBJECT-TYPE
    SYNTAX OCTET STRING
    ACCESS read-only
    STATUS mandatory
    DESCRIPTION
        "Using wtWebioAn1GraphPtSwDiagErrorIndex as an index, the appropriate message is available."
    ::= { wtWebioAn1GraphPtSwDiag 4 }

wtWebioAn1GraphPtSwDiagErrorClear OBJECT-TYPE
    SYNTAX INTEGER
    ACCESS write-only
    STATUS mandatory
    DESCRIPTION
        "Writing 1 into this variable clears all diagnosis messages."
    ::= { wtWebioAn1GraphPtSwDiag 5 }

-- TRAP DEFINITIONS

-- Diese SNMP-Traps werden gesendet, wenn die Alarmtriggerbedingungen zutreffen

wtWebioAn1GraphPtSwAlert1 TRAP-TYPE
    ENTERPRISE  wtWebioAn1GraphPtSw
    VARIABLES   { wtWebioAn1GraphPtSwAlarmTrapText }
    DESCRIPTION
        "This SNMP trap is generated when Alarm 1 was triggered,
        SNMP trap enable is set and
        SNMP is enabled."
    -- NMS trap annotation
    --#TYPE "Web-Thermograph Alarm 1"
    --#SUMMARY "Alarm 1: %s"
    --#ARGUMENTS {0}
    --#SEVERITY INFORMATIONAL
    --#TIMEINDEX 99
    --#STATE OPERATIONAL
    ::= 31

wtWebioAn1GraphPtSwAlert2 TRAP-TYPE
    ENTERPRISE  wtWebioAn1GraphPtSw
    VARIABLES   { wtWebioAn1GraphPtSwAlarmTrapText }
    DESCRIPTION
        "This SNMP trap is generated when Alarm 2 was triggered,
        SNMP trap enable is set and
        SNMP is enabled."
    -- NMS trap annotation
    --#TYPE "Web-Thermograph Alarm 2"
    --#SUMMARY "Alarm 2: %s"
    --#ARGUMENTS {0}
    --#SEVERITY INFORMATIONAL
    --#TIMEINDEX 99
    --#STATE OPERATIONAL
    ::= 32

wtWebioAn1GraphPtSwAlert3 TRAP-TYPE
    ENTERPRISE  wtWebioAn1GraphPtSw
    VARIABLES   { wtWebioAn1GraphPtSwAlarmTrapText }
    DESCRIPTION
        "This SNMP trap is generated when Alarm 3 was triggered,
        SNMP trap enable is set and
        SNMP is enabled."
    -- NMS trap annotation
    --#TYPE "Web-Thermograph Alarm 3"
    --#SUMMARY "Alarm 3: %s"
    --#ARGUMENTS {0}
    --#SEVERITY INFORMATIONAL
    --#TIMEINDEX 99
    --#STATE OPERATIONAL
    ::= 33

wtWebioAn1GraphPtSwAlert4 TRAP-TYPE
    ENTERPRISE  wtWebioAn1GraphPtSw
    VARIABLES   { wtWebioAn1GraphPtSwAlarmTrapText }
    DESCRIPTION
        "This SNMP trap is generated when Alarm 4 was triggered,
        SNMP trap enable is set and
        SNMP is enabled."
    -- NMS trap annotation
    --#TYPE "Web-Thermograph Alarm 4"
    --#SUMMARY "Alarm 4: %s"
    --#ARGUMENTS {0}
    --#SEVERITY INFORMATIONAL
    --#TIMEINDEX 99
    --#STATE OPERATIONAL
    ::= 34

wtWebioAn1GraphPtSwAlert5 TRAP-TYPE
    ENTERPRISE  wtWebioAn1GraphPtSw
    VARIABLES   { wtWebioAn1GraphPtSwAlarmTrapText }
    DESCRIPTION
        "This SNMP trap is generated when Alarm 5 was triggered,
        SNMP trap enable is set and
        SNMP is enabled."
    -- NMS trap annotation
    --#TYPE "Web-Thermograph Alarm 5"
    --#SUMMARY "Alarm 5: %s"
    --#ARGUMENTS {0}
    --#SEVERITY INFORMATIONAL
    --#TIMEINDEX 99
    --#STATE OPERATIONAL
    ::= 35

wtWebioAn1GraphPtSwAlert6 TRAP-TYPE
    ENTERPRISE  wtWebioAn1GraphPtSw
    VARIABLES   { wtWebioAn1GraphPtSwAlarmTrapText }
    DESCRIPTION
        "This SNMP trap is generated when Alarm 6 was triggered,
        SNMP trap enable is set and
        SNMP is enabled."
    -- NMS trap annotation
    --#TYPE "Web-Thermograph Alarm 6"
    --#SUMMARY "Alarm 6: %s"
    --#ARGUMENTS {0}
    --#SEVERITY INFORMATIONAL
    --#TIMEINDEX 99
    --#STATE OPERATIONAL
    ::= 36

wtWebioAn1GraphPtSwAlert7 TRAP-TYPE
    ENTERPRISE  wtWebioAn1GraphPtSw
    VARIABLES   { wtWebioAn1GraphPtSwAlarmTrapText }
    DESCRIPTION
        "This SNMP trap is generated when Alarm 7 was triggered,
        SNMP trap enable is set and
        SNMP is enabled."
    -- NMS trap annotation
    --#TYPE "Web-Thermograph Alarm 7"
    --#SUMMARY "Alarm 7: %s"
    --#ARGUMENTS {0}
    --#SEVERITY INFORMATIONAL
    --#TIMEINDEX 99
    --#STATE OPERATIONAL
    ::= 37

wtWebioAn1GraphPtSwAlert8 TRAP-TYPE
    ENTERPRISE  wtWebioAn1GraphPtSw
    VARIABLES   { wtWebioAn1GraphPtSwAlarmTrapText }
    DESCRIPTION
        "This SNMP trap is generated when Alarm 8 was triggered,
        SNMP trap enable is set and
        SNMP is enabled."
    -- NMS trap annotation
    --#TYPE "Web-Thermograph Alarm 8"
    --#SUMMARY "Alarm 8: %s"
    --#ARGUMENTS {0}
    --#SEVERITY INFORMATIONAL
    --#TIMEINDEX 99
    --#STATE OPERATIONAL
    ::= 38


wtWebioAn1GraphPtSwAlert9 TRAP-TYPE
    ENTERPRISE  wtWebioAn1GraphPtSw
    VARIABLES   { wtWebioAn1GraphPtSwAlarmClearTrapText }
    DESCRIPTION
        "This SNMP trap is generated when Alarm 1 was cleared,
        SNMP trap enable is set and
        SNMP is enabled."
    -- NMS trap annotation
    --#TYPE "Web-Thermograph Release Alarm 1"
    --#SUMMARY "Release Alarm 1: %s"
    --#ARGUMENTS {0}
    --#SEVERITY INFORMATIONAL
    --#TIMEINDEX 99
    --#STATE OPERATIONAL
    ::= 91

wtWebioAn1GraphPtSwAlert10 TRAP-TYPE
    ENTERPRISE  wtWebioAn1GraphPtSw
    VARIABLES   { wtWebioAn1GraphPtSwAlarmClearTrapText }
    DESCRIPTION
        "This SNMP trap is generated when Alarm 2 was cleared,
        SNMP trap enable is set and
        SNMP is enabled."
    -- NMS trap annotation
    --#TYPE "Web-Thermograph Release Alarm 2"
    --#SUMMARY "Release Alarm 2: %s"
    --#ARGUMENTS {0}
    --#SEVERITY INFORMATIONAL
    --#TIMEINDEX 99
    --#STATE OPERATIONAL
    ::= 92

wtWebioAn1GraphPtSwAlert11 TRAP-TYPE
    ENTERPRISE  wtWebioAn1GraphPtSw
    VARIABLES   { wtWebioAn1GraphPtSwAlarmClearTrapText }
    DESCRIPTION
        "This SNMP trap is generated when Alarm 3 was cleared,
        SNMP trap enable is set and
        SNMP is enabled."
    -- NMS trap annotation
    --#TYPE "Web-Thermograph Release Alarm 3"
    --#SUMMARY "Release Alarm 3: %s"
    --#ARGUMENTS {0}
    --#SEVERITY INFORMATIONAL
    --#TIMEINDEX 99
    --#STATE OPERATIONAL
    ::= 93

wtWebioAn1GraphPtSwAlert12 TRAP-TYPE
    ENTERPRISE  wtWebioAn1GraphPtSw
    VARIABLES   { wtWebioAn1GraphPtSwAlarmClearTrapText }
    DESCRIPTION
        "This SNMP trap is generated when Alarm 4 was cleared,
        SNMP trap enable is set and
        SNMP is enabled."
    -- NMS trap annotation
    --#TYPE "Web-Thermograph Release Alarm 4"
    --#SUMMARY "Release Alarm 4: %s"
    --#ARGUMENTS {0}
    --#SEVERITY INFORMATIONAL
    --#TIMEINDEX 99
    --#STATE OPERATIONAL
    ::= 94

wtWebioAn1GraphPtSwAlert13 TRAP-TYPE
    ENTERPRISE  wtWebioAn1GraphPtSw
    VARIABLES   { wtWebioAn1GraphPtSwAlarmClearTrapText }
    DESCRIPTION
        "This SNMP trap is generated when Alarm 5 was cleared,
        SNMP trap enable is set and
        SNMP is enabled."
    -- NMS trap annotation
    --#TYPE "Web-Thermograph Release Alarm 5"
    --#SUMMARY "Release Alarm 5: %s"
    --#ARGUMENTS {0}
    --#SEVERITY INFORMATIONAL
    --#TIMEINDEX 99
    --#STATE OPERATIONAL
    ::= 95

wtWebioAn1GraphPtSwAlert14 TRAP-TYPE
    ENTERPRISE  wtWebioAn1GraphPtSw
    VARIABLES   { wtWebioAn1GraphPtSwAlarmClearTrapText }
    DESCRIPTION
        "This SNMP trap is generated when Alarm 6 was cleared,
        SNMP trap enable is set and
        SNMP is enabled."
    -- NMS trap annotation
    --#TYPE "Web-Thermograph Release Alarm 6"
    --#SUMMARY "Release Alarm 6: %s"
    --#ARGUMENTS {0}
    --#SEVERITY INFORMATIONAL
    --#TIMEINDEX 99
    --#STATE OPERATIONAL
    ::= 96

wtWebioAn1GraphPtSwAlert15 TRAP-TYPE
    ENTERPRISE  wtWebioAn1GraphPtSw
    VARIABLES   { wtWebioAn1GraphPtSwAlarmClearTrapText }
    DESCRIPTION
        "This SNMP trap is generated when Alarm 7 was cleared,
        SNMP trap enable is set and
        SNMP is enabled."
    -- NMS trap annotation
    --#TYPE "Web-Thermograph Release Alarm 7"
    --#SUMMARY "Release Alarm 7: %s"
    --#ARGUMENTS {0}
    --#SEVERITY INFORMATIONAL
    --#TIMEINDEX 99
    --#STATE OPERATIONAL
    ::= 97

wtWebioAn1GraphPtSwAlert16 TRAP-TYPE
    ENTERPRISE  wtWebioAn1GraphPtSw
    VARIABLES   { wtWebioAn1GraphPtSwAlarmClearTrapText }
    DESCRIPTION
        "This SNMP trap is generated when Alarm 8 was cleared,
        SNMP trap enable is set and
        SNMP is enabled."
    -- NMS trap annotation
    --#TYPE "Web-Thermograph Release Alarm 8"
    --#SUMMARY "Release Alarm 8: %s"
    --#ARGUMENTS {0}
    --#SEVERITY INFORMATIONAL
    --#TIMEINDEX 99
    --#STATE OPERATIONAL
    ::= 98

wtWebioAn1GraphPtSwAlertDiag TRAP-TYPE
    ENTERPRISE  wtWebioAn1GraphPtSw
    VARIABLES   {
    		wtWebioAn1GraphPtSwDiagErrorIndex,
    	  	wtWebioAn1GraphPtSwDiagErrorMessage
    		}
    DESCRIPTION
        "This SNMP trap is generated when a diagnosis/error message was triggered,
        SNMP trap enable is set and
        SNMP is enabled."
    -- NMS trap annotation
    --#TYPE "Web-Thermograph Diagnose Error"
    --#SUMMARY "Diagnose error index: %d, Message: %s."
    --#ARGUMENTS {0,1}
    --#SEVERITY MAJOR
    --#TIMEINDEX 99
    --#STATE DEGRADED
    ::= 110



END
