WebGraph-Thermometer-NTC-US-MIB DEFINITIONS ::= BEGIN
----------------------------------------------------------------
-- Revison: 1.34
----------------------------------------------------------------
-- 09.03.2017 	New: wtWebioAn1GraphNtcAlarmSensorLostSelection
--		     		 wtWebioAn1GraphNtcAlarmLimitWindow
----------------------------------------------------------------
-- Revison: 1.33
----------------------------------------------------------------
-- 09.11.2016 	New: wtWebioAn1GraphNtcMQTT group
--		     HTTP Request, MQTT Alarm, REST
----------------------------------------------------------------
-- Revison: 1.32
----------------------------------------------------------------
-- 15.07.2015 	Changes for new Navigation (__JB__)
----------------------------------------------------------------
-- Revison: 1.31
----------------------------------------------------------------
-- 15.07.2015 	Changes for new Navigation (__JB__)
----------------------------------------------------------------
-- Revison: 1.30
----------------------------------------------------------------
-- 06.02.2012 	WebIO
-- 		New: wtWebioAn1GraphPtAlarmDeltaTemp
----------------------------------------------------------------
-- Revison: 1.29
----------------------------------------------------------------
-- 22.06.2010 	Output with decimal point
--
----------------------------------------------------------------
-- Revison: 1.28
----------------------------------------------------------------
-- 09.05.2007 	Webio
--		New Graphics java script base parameter
----------------------------------------------------------------
-- Revison: 1.27
----------------------------------------------------------------
-- 09.11.2006 	Webio
--		DHCP enable
----------------------------------------------------------------
-- Revison: 1.26
----------------------------------------------------------------
-- 28.06.2006 	New: Community String Trap
--
----------------------------------------------------------------
-- Revison: 1.25
----------------------------------------------------------------
-- 22.05.2006 	Table entry names changed
--
----------------------------------------------------------------
-- Revison: 1.24
----------------------------------------------------------------
-- 26.07.2005 	#57605, WebGraph Thermometer
--		CRON timer function
----------------------------------------------------------------
-- Revison: 1.23
----------------------------------------------------------------
-- 14.07.2005 	#57605, WebGraph Thermometer
--		FTP functions
----------------------------------------------------------------
-- Revison: 1.22
----------------------------------------------------------------
-- 02.06.2005 	#57605, WebGraph Thermometer
--		Trap NMS annotations
----------------------------------------------------------------
-- Revison: 1.21
----------------------------------------------------------------
-- 19.04.2005 	#57605, WebGraph Themometer
--		Mail Authentication
----------------------------------------------------------------
-- Revison: 1.20
----------------------------------------------------------------
-- 05.11.2004 	#57605, WebGraph
--		New: Syslog
--
----------------------------------------------------------------
-- Revison: 1.19
----------------------------------------------------------------
-- 27.09.2004 	#57601/3/4, Webio Digital
--		New:
--		     Entry AlarmHysteresis corrected
----------------------------------------------------------------
-- Revison: 1.18
----------------------------------------------------------------
-- 21.07.2004 	#57601/3/4, Webio Anx
--		New:
--		     Diagnosis
----------------------------------------------------------------
-- Revison: 1.17
----------------------------------------------------------------
-- 28.06.2004 	#57630/1/2, Webio Digital
--		Neu: Puls Mode
----------------------------------------------------------------
-- Revison: 1.16
----------------------------------------------------------------
-- 16.04.2004 	New: #57632, Webio Digital EA24x24
--
--		#57630/1, Webio Digital EA12x12
--		New:
--			wtWebioAn1GraphNtcInputCounterClear
----------------------------------------------------------------
-- Revison: 1.15
----------------------------------------------------------------
-- 27.02.2004 	#57630/1, Webio Digital EA12x12
--		New:
--		Length changed to 32 Bit:
--			wtWebioEA12x12InputValue
--			wtWebioEA12x12OutputValue
--			wtWebioEA12x12LoadControlView
--			wtWebioEA12x12LCShutDownView
--			wtWebioEA12x12SetOutput
--			wtWebioEA12x12AlarmInputTrigger
--			wtWebioEA12x12AlarmOutputTrigger
--			wtWebioEA12x12PortOutputSafetyState
----------------------------------------------------------------
-- Revison: 1.14
----------------------------------------------------------------
-- 16.02.2004 	#57630/1, Webio Digital EA12x12
--		New:
--		Text: Location, Contact
--		SNMP: ColdStart, WarmStart, ComunityString Read/RW
--		Alarm: ColdStart / WarmStart trigger
--
-- 	 	#57601, 1xWebThermometer
--		#57603, 2xWebThermometer
--		#57604, 8xWebThermometer
--		New:
--		Alarm Hysteresis
--		Alarm Clear Traps and Mails
----------------------------------------------------------------
-- Revison: 1.13
----------------------------------------------------------------
-- 05.02.2004 	#57601, 1xWebThermometer
--		#57603, 2xWebThermometer
--		#57604, 8xWebThermometer
--		New:
--		Text: Location, Contact
--		SNMP: ColdStart, WarmStart, ComunityString Read/RW
--		Alarm: ColdStart / WarmStart trigger
----------------------------------------------------------------
-- Revison: 1.12
----------------------------------------------------------------
-- 05.11.2003 	#57601, 1xWebThermometer
--		#57603, 2xWebThermometer
--		#57604, 8xWebThermometer
--		New features:
--		Mail  : Option CSV attachment
--		Port  : Offset calibration
--		Alarm : TCP Client mode
----------------------------------------------------------------
-- Revison: 1.11
----------------------------------------------------------------
-- 28.10.2003 	#57630/1, Webio Digital EA12x12
--		New features:
--		Alarm : TCP Client mode
--		Inputs: Puls filter
----------------------------------------------------------------
-- Revison: 1.10
----------------------------------------------------------------
-- 22.07.2003 	#57630, Webio Digital EA12x12
--		New navigation tree, new binary modes
--
----------------------------------------------------------------
-- Revison: 1.09
----------------------------------------------------------------
-- 24.03.2003 	Trap Enterprise (Type 1, 2) corrected
----------------------------------------------------------------
-- Revison: 1.08
----------------------------------------------------------------
-- 04.03.2003 	reconciled the language versions DE/US
----------------------------------------------------------------
-- Revison: 1.07
----------------------------------------------------------------
-- 25.02.2003 	Correction: wtWebioEA12x12LoadControl
----------------------------------------------------------------
-- Revison: 1.06
----------------------------------------------------------------
-- 24.02.2003 	New:
--		#57630, Webio EA12x12, LoadControl Group
--		Correction: Trap variable names
----------------------------------------------------------------
-- Revison: 1.05
----------------------------------------------------------------
-- 21.01.2003 	New:
--		#57630, Webio EA12x12
----------------------------------------------------------------
-- Revison: 1.04
----------------------------------------------------------------
-- 02.01.2003 	New:
--		#57601, 1xWebThermometer
--		#57603, 2xWebThermometer, 8 alarms
----------------------------------------------------------------
-- Revison: 1.03
----------------------------------------------------------------
-- 21.11.2002 	New:
--		#57604, 2xWebThermometer, BOOTP, StartupSite
--		#57603, 8xWebThermometer, BOOTP, StartupSite
----------------------------------------------------------------
-- Revison: 1.02
----------------------------------------------------------------
-- 26.07.2002 	New:
--		#57604, 2xWebThermometer
--		#57603, 8xWebThermometer
--


    IMPORTS

    OBJECT-TYPE                                        FROM RFC-1212
    TRAP-TYPE                                          FROM RFC-1215
    DisplayString, PhysAddress                         FROM RFC1213-MIB
    enterprises, TimeTicks, IpAddress, NetworkAddress  FROM RFC1155-SMI;


--    IpAddress ::=
--        [APPLICATION 0]
--            IMPLICIT OCTET STRING (SIZE (4))
--    Counter ::=
--        [APPLICATION 1]
--            IMPLICIT INTEGER (0..4294967295)
--    Gauge ::=
--        [APPLICATION 2]
--            IMPLICIT INTEGER (0..4294967295)
--    TimeTicks ::=
--        [APPLICATION 3]
--            IMPLICIT INTEGER (0..4294967295)


--    DisplayString ::= OCTET STRING
--    PhysAddress   ::= OCTET STRING

--    internet         OBJECT IDENTIFIER ::= { iso org(3) dod(6) 1 }
--    privat           OBJECT IDENTIFIER ::= { internet 4 }
--    enterprises      OBJECT IDENTIFIER ::= { privat 1 }



--  Wiesemann & Theis Com-Server MIB

    wut                			OBJECT IDENTIFIER ::= { enterprises 5040 }
    wtComServer        			OBJECT IDENTIFIER ::= { wut 1 }
    wtWebio            			OBJECT IDENTIFIER ::= { wtComServer 2 }

--  wtWebio Tree

    wtWebioAn1GraphNtc    		OBJECT IDENTIFIER ::= { wtWebio 38 }

--  wtWebioAn1GraphNtc Tree

    wtWebioAn1GraphNtcTemp      	OBJECT IDENTIFIER ::= { wtWebioAn1GraphNtc 1 }
    wtWebioAn1GraphNtcSessCntrl 	OBJECT IDENTIFIER ::= { wtWebioAn1GraphNtc 2 }
    wtWebioAn1GraphNtcConfig    	OBJECT IDENTIFIER ::= { wtWebioAn1GraphNtc 3 }

--  wtWebioAn1GraphNtcConfig Tree

    wtWebioAn1GraphNtcDevice    	OBJECT IDENTIFIER ::= { wtWebioAn1GraphNtcConfig 1 }
    wtWebioAn1GraphNtcPorts     	OBJECT IDENTIFIER ::= { wtWebioAn1GraphNtcConfig 2 }
    wtWebioAn1GraphNtcManufact  	OBJECT IDENTIFIER ::= { wtWebioAn1GraphNtcConfig 3 }

--  wtWebioAn1GraphNtcDevice Tree

    wtWebioAn1GraphNtcText		OBJECT IDENTIFIER ::= { wtWebioAn1GraphNtcDevice 1 }
    wtWebioAn1GraphNtcTimeDate 		OBJECT IDENTIFIER ::= { wtWebioAn1GraphNtcDevice 2 }
    wtWebioAn1GraphNtcBasic		OBJECT IDENTIFIER ::= { wtWebioAn1GraphNtcDevice 3 }
    wtWebioAn1GraphNtcDatalogger	OBJECT IDENTIFIER ::= { wtWebioAn1GraphNtcDevice 4 }
    wtWebioAn1GraphNtcAlarm		OBJECT IDENTIFIER ::= { wtWebioAn1GraphNtcDevice 5 }
    wtWebioAn1GraphNtcGraphics 		OBJECT IDENTIFIER ::= { wtWebioAn1GraphNtcDevice 6 }


--  wtWebioAn1GraphNtcTimeDate Tree

    wtWebioAn1GraphNtcTimeZone		OBJECT IDENTIFIER ::= { wtWebioAn1GraphNtcTimeDate 1 }
    wtWebioAn1GraphNtcTimeServer	OBJECT IDENTIFIER ::= { wtWebioAn1GraphNtcTimeDate 2 }
    wtWebioAn1GraphNtcDeviceClock	OBJECT IDENTIFIER ::= { wtWebioAn1GraphNtcTimeDate 3 }

--  wtWebioAn1GraphNtcBasic Tree

    wtWebioAn1GraphNtcNetwork		OBJECT IDENTIFIER ::= { wtWebioAn1GraphNtcBasic 1 }
    wtWebioAn1GraphNtcHTTP		OBJECT IDENTIFIER ::= { wtWebioAn1GraphNtcBasic 2 }
    wtWebioAn1GraphNtcMail		OBJECT IDENTIFIER ::= { wtWebioAn1GraphNtcBasic 3 }
    wtWebioAn1GraphNtcSNMP		OBJECT IDENTIFIER ::= { wtWebioAn1GraphNtcBasic 4 }
    wtWebioAn1GraphNtcUDP		OBJECT IDENTIFIER ::= { wtWebioAn1GraphNtcBasic 5 }
    wtWebioAn1GraphNtcSyslog		OBJECT IDENTIFIER ::= { wtWebioAn1GraphNtcBasic 6 }
    wtWebioAn1GraphNtcFTP		OBJECT IDENTIFIER ::= { wtWebioAn1GraphNtcBasic 7 }
    wtWebioAn1GraphNtcMQTT			OBJECT IDENTIFIER ::= { wtWebioAn1GraphNtcBasic 12 }
    wtWebioAn1GraphNtcREST			OBJECT IDENTIFIER ::= { wtWebioAn1GraphNtcBasic 13 }


--  wtWebioAn1GraphNtcGraphics Tree

    wtWebioAn1GraphNtcGraphicsBase 	OBJECT IDENTIFIER ::= { wtWebioAn1GraphNtcGraphics 1 }
    wtWebioAn1GraphNtcGraphicsSelect 	OBJECT IDENTIFIER ::= { wtWebioAn1GraphNtcGraphics 2 }
    wtWebioAn1GraphNtcGraphicsScale 	OBJECT IDENTIFIER ::= { wtWebioAn1GraphNtcGraphics 3 }

-- wtWebioAn1GraphNtcTemp Group
------------------------

wtWebioAn1GraphNtcSensors OBJECT-TYPE
    SYNTAX INTEGER (1)
    ACCESS read-only
    STATUS mandatory
    DESCRIPTION
        "Number of temperature sensors"
    ::= { wtWebioAn1GraphNtcTemp 1 }

-- Interface Table

wtWebioAn1GraphNtcSensorTable OBJECT-TYPE
    SYNTAX SEQUENCE OF WtWebioAn1GraphNtcSensorEntry
    ACCESS not-accessible
    STATUS mandatory
    DESCRIPTION
        "List of sensors."
    ::= { wtWebioAn1GraphNtcTemp 2 }

wtWebioAn1GraphNtcSensorEntry OBJECT-TYPE
    SYNTAX WtWebioAn1GraphNtcSensorEntry
    ACCESS not-accessible
    STATUS mandatory
    DESCRIPTION
        "Temperature sensor numbers."
    INDEX  { wtWebioAn1GraphNtcSensorNo }
    ::= { wtWebioAn1GraphNtcSensorTable 1 }

WtWebioAn1GraphNtcSensorEntry ::= SEQUENCE {
    wtWebioAn1GraphNtcSensorNo INTEGER
}

wtWebioAn1GraphNtcSensorNo OBJECT-TYPE
    SYNTAX INTEGER (1)
    ACCESS read-only
    STATUS mandatory
    DESCRIPTION
        "Temperature sensor number."
    ::= { wtWebioAn1GraphNtcSensorEntry 1 }


-- wtWebioAn1GraphNtcTempValue Table

wtWebioAn1GraphNtcTempValueTable OBJECT-TYPE
    SYNTAX SEQUENCE OF WtWebioAn1GraphNtcTempValueEntry
    ACCESS not-accessible
    STATUS mandatory
    DESCRIPTION
        "List of temperature values corresponding to the channel numbers."
    ::= { wtWebioAn1GraphNtcTemp 3 }

wtWebioAn1GraphNtcTempValueEntry OBJECT-TYPE
    SYNTAX WtWebioAn1GraphNtcTempValueEntry
    ACCESS not-accessible
    STATUS mandatory
    DESCRIPTION
        "Temperatures of the sensors."
    INDEX  { wtWebioAn1GraphNtcSensorNo }
    ::= { wtWebioAn1GraphNtcTempValueTable 1 }

WtWebioAn1GraphNtcTempValueEntry ::= SEQUENCE{
    wtWebioAn1GraphNtcTempValue OCTET STRING
}

wtWebioAn1GraphNtcTempValue OBJECT-TYPE
    SYNTAX OCTET STRING (SIZE (5))
    ACCESS read-only
    STATUS mandatory
    DESCRIPTION
        "Temperature value of the sensor, ASCII, 5 characters in length."
    ::= { wtWebioAn1GraphNtcTempValueEntry 1 }

-- wtWebioAn1GraphNtcBinaryTempValue Table

wtWebioAn1GraphNtcBinaryTempValueTable OBJECT-TYPE
    SYNTAX SEQUENCE OF WtWebioAn1GraphNtcBinaryTempValueEntry
    ACCESS not-accessible
    STATUS mandatory
    DESCRIPTION
        "List of binary temperature values corresponding to the channel numbers."
    ::= { wtWebioAn1GraphNtcTemp 4 }

wtWebioAn1GraphNtcBinaryTempValueEntry OBJECT-TYPE
    SYNTAX WtWebioAn1GraphNtcBinaryTempValueEntry
    ACCESS not-accessible
    STATUS mandatory
    DESCRIPTION
        "Binary temperature values of the sensors."
    INDEX  { wtWebioAn1GraphNtcSensorNo }
    ::= { wtWebioAn1GraphNtcBinaryTempValueTable 1 }

WtWebioAn1GraphNtcBinaryTempValueEntry ::= SEQUENCE{
    wtWebioAn1GraphNtcBinaryTempValue INTEGER
}

wtWebioAn1GraphNtcBinaryTempValue OBJECT-TYPE
    SYNTAX INTEGER
    ACCESS read-only
    STATUS mandatory
    DESCRIPTION
        "Binary temperature value of the sensor in 1/10 degrees Celsius,
        signed number, 0x7FFF indicates an
        invalid measured value."
    ::= { wtWebioAn1GraphNtcBinaryTempValueEntry 1 }

-- wtWebioAn1GraphNtcTempValuePkt Table

wtWebioAn1GraphNtcTempValuePktTable OBJECT-TYPE
    SYNTAX SEQUENCE OF WtWebioAn1GraphNtcTempValuePktEntry
    ACCESS not-accessible
    STATUS mandatory
    DESCRIPTION
        "List of temperature values corresponding to the channel numbers."
    ::= { wtWebioAn1GraphNtcTemp 8 }

wtWebioAn1GraphNtcTempValuePktEntry OBJECT-TYPE
    SYNTAX WtWebioAn1GraphNtcTempValuePktEntry
    ACCESS not-accessible
    STATUS mandatory
    DESCRIPTION
        "Temperatures of the sensors."
    INDEX  { wtWebioAn1GraphNtcSensorNo }
    ::= { wtWebioAn1GraphNtcTempValuePktTable 1 }

WtWebioAn1GraphNtcTempValuePktEntry ::= SEQUENCE{
    wtWebioAn1GraphNtcTempValuePkt OCTET STRING
}

wtWebioAn1GraphNtcTempValuePkt OBJECT-TYPE
    SYNTAX OCTET STRING (SIZE (5))
    ACCESS read-only
    STATUS mandatory
    DESCRIPTION
        "Temperature value of the sensor, ASCII, 5 characters in length, decimal point."
    ::= { wtWebioAn1GraphNtcTempValuePktEntry 1 }


-- wtWebioAn1GraphNtcSessCntrl Group
--------------------------------

wtWebioAn1GraphNtcSessCntrlPassword OBJECT-TYPE
    SYNTAX OCTET STRING
    ACCESS read-write
    STATUS mandatory
    DESCRIPTION
        "Entering this password opens a session which is ended by writing a 1 to
        wtWebioAn1GraphNtcSessCntrlLogout. When read this variable provides a string of
        length zero."
    ::= { wtWebioAn1GraphNtcSessCntrl 1 }

wtWebioAn1GraphNtcSessCntrlConfigMode OBJECT-TYPE
    SYNTAX INTEGER {
    wtWebioAn1GraphNtcSessCntrl-NoSession(0),
    wtWebioAn1GraphNtcSessCntrl-Session(1)
    }
    ACCESS read-only
    STATUS mandatory
    DESCRIPTION
        "When the device is in SNMP configuration mode, the value 1 is
        returned, otherwise 0. If the read value is 0 even though the
        password was written, the device is already in config mode and the
        variables can only be read."
    ::= { wtWebioAn1GraphNtcSessCntrl 2 }

wtWebioAn1GraphNtcSessCntrlLogout OBJECT-TYPE
    SYNTAX INTEGER
    ACCESS read-write
    STATUS mandatory
    DESCRIPTION
        "If the device is in configuration mode and the session was opened by
        this SNMP Manager, writing a 1 to this variable will end the session
        and all parameters are stored.
        Writing a 2 discards all entries again.
        When read this variable provides the value 0."
    ::= { wtWebioAn1GraphNtcSessCntrl 3 }

wtWebioAn1GraphNtcSessCntrlAdminPassword OBJECT-TYPE
    SYNTAX OCTET STRING
    ACCESS read-write
    STATUS mandatory
    DESCRIPTION
        "This password protects access to the variables with administrator rights.
        It can only be changed by the administrator. If no password was assigned,
        the valid password is public."
    ::= { wtWebioAn1GraphNtcSessCntrl 4 }

wtWebioAn1GraphNtcSessCntrlConfigPassword OBJECT-TYPE
    SYNTAX OCTET STRING
    ACCESS read-write
    STATUS mandatory
    DESCRIPTION
        "This password protects access to the variables with configurator rights. It can
        be changed by the administrator and by the configurator. If no password was assigned,
        the valid password is public. When read this variable provides a null-pointer."
    ::= { wtWebioAn1GraphNtcSessCntrl 5 }


-- wtWebioAn1GraphNtcText Group
------------------------

wtWebioAn1GraphNtcDeviceName OBJECT-TYPE
    SYNTAX OCTET STRING
    ACCESS read-write
    STATUS mandatory
    DESCRIPTION
        "Name of the Webio, which is user definable."
    ::= { wtWebioAn1GraphNtcText 1 }

wtWebioAn1GraphNtcDeviceText OBJECT-TYPE
    SYNTAX OCTET STRING
    ACCESS read-write
    STATUS mandatory
    DESCRIPTION
        "Description of the Webio, which is user definable."
    ::= { wtWebioAn1GraphNtcText 2 }

wtWebioAn1GraphNtcDeviceLocation OBJECT-TYPE
    SYNTAX OCTET STRING
    ACCESS read-write
    STATUS mandatory
    DESCRIPTION
        "Description of the location of the Webio, which is user definable."
    ::= { wtWebioAn1GraphNtcText 3 }

wtWebioAn1GraphNtcDeviceContact OBJECT-TYPE
    SYNTAX OCTET STRING
    ACCESS read-write
    STATUS mandatory
    DESCRIPTION
        "Contact address of the system operator of the Webio, which is user definable."
    ::= { wtWebioAn1GraphNtcText 4 }

-- wtWebioAn1GraphNtcTimeZone Group
----------------------------

wtWebioAn1GraphNtcTzOffsetHrs OBJECT-TYPE
    SYNTAX INTEGER
    ACCESS read-write
    STATUS mandatory
    DESCRIPTION
        "Offset hours for the time zone (winter time) with respect to UTC."
    ::= { wtWebioAn1GraphNtcTimeZone 1 }

wtWebioAn1GraphNtcTzOffsetMin OBJECT-TYPE
    SYNTAX INTEGER
    ACCESS read-write
    STATUS mandatory
    DESCRIPTION
        "Offset minutes for the time zone (winter time) with respect to UTC."
    ::= { wtWebioAn1GraphNtcTimeZone 2 }

wtWebioAn1GraphNtcTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebioAn1GraphNtcTimeZone 3 }

wtWebioAn1GraphNtcStTzOffsetHrs OBJECT-TYPE
    SYNTAX INTEGER
    ACCESS read-write
    STATUS mandatory
    DESCRIPTION
        "Offset hours of the time zone (summer time) with respect to UTC."
    ::= { wtWebioAn1GraphNtcTimeZone 4 }

wtWebioAn1GraphNtcStTzOffsetMin OBJECT-TYPE
    SYNTAX INTEGER
    ACCESS read-write
    STATUS mandatory
    DESCRIPTION
        "Offset minutes of the time zone (summer time) with respect to UTC."
    ::= { wtWebioAn1GraphNtcTimeZone 5 }

wtWebioAn1GraphNtcStTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebioAn1GraphNtcTimeZone 6 }

wtWebioAn1GraphNtcStTzStartMonth OBJECT-TYPE
    SYNTAX INTEGER {
    	wtWebioAn1GraphNtcStartMonth-January(1),
    	wtWebioAn1GraphNtcStartMonth-February(2),
    	wtWebioAn1GraphNtcStartMonth-March(3),
    	wtWebioAn1GraphNtcStartMonth-April(4),
    	wtWebioAn1GraphNtcStartMonth-May(5),
    	wtWebioAn1GraphNtcStartMonth-June(6),
    	wtWebioAn1GraphNtcStartMonth-July(7),
    	wtWebioAn1GraphNtcStartMonth-August(8),
    	wtWebioAn1GraphNtcStartMonth-September(9),
    	wtWebioAn1GraphNtcStartMonth-October(10),
    	wtWebioAn1GraphNtcStartMonth-November(11),
    	wtWebioAn1GraphNtcStartMonth-December(12)
    	}

    ACCESS read-write
    STATUS mandatory
    DESCRIPTION
        "Month in which the change is made from winter time to summer time."
    ::= { wtWebioAn1GraphNtcTimeZone 7 }

wtWebioAn1GraphNtcStTzStartMode OBJECT-TYPE
    SYNTAX INTEGER {
    	wtWebioAn1GraphNtcStartMode-first(1),
    	wtWebioAn1GraphNtcStartMode-second(2),
    	wtWebioAn1GraphNtcStartMode-third(3),
    	wtWebioAn1GraphNtcStartMode-fourth(4),
    	wtWebioAn1GraphNtcStartMode-last(5)
    	}

    ACCESS read-write
    STATUS mandatory
    DESCRIPTION
        "Mode of the day of the week for which the change is made from winter time to summer time."
    ::= { wtWebioAn1GraphNtcTimeZone 8 }

wtWebioAn1GraphNtcStTzStartWday OBJECT-TYPE
    SYNTAX INTEGER {
    	wtWebioAn1GraphNtcStartWday-Sunday(1),
    	wtWebioAn1GraphNtcStartWday-Monday(2),
    	wtWebioAn1GraphNtcStartWday-Tuesday(3),
    	wtWebioAn1GraphNtcStartWday-Thursday(4),
    	wtWebioAn1GraphNtcStartWday-Wednesday(5),
    	wtWebioAn1GraphNtcStartWday-Friday(6),
    	wtWebioAn1GraphNtcStartWday-Saturday(7)
    	}

    ACCESS read-write
    STATUS mandatory
    DESCRIPTION
        "Day of the week on which the change is made from winter time to summer time"
    ::= { wtWebioAn1GraphNtcTimeZone 9 }

wtWebioAn1GraphNtcStTzStartHrs OBJECT-TYPE
    SYNTAX INTEGER
    ACCESS read-write
    STATUS mandatory
    DESCRIPTION
        "Hour in which the time zone is changed from winter to summer time with
        respect to UTC."
    ::= { wtWebioAn1GraphNtcTimeZone 10 }

wtWebioAn1GraphNtcStTzStartMin OBJECT-TYPE
    SYNTAX INTEGER
    ACCESS read-write
    STATUS mandatory
    DESCRIPTION
        "Minute in which the time zone is changed from winter to summer time with
        respect to UTC."
    ::= { wtWebioAn1GraphNtcTimeZone 11 }

wtWebioAn1GraphNtcStTzStopMonth OBJECT-TYPE
    SYNTAX INTEGER {
    	wtWebioAn1GraphNtcStopMonth-January(1),
    	wtWebioAn1GraphNtcStopMonth-February(2),
    	wtWebioAn1GraphNtcStopMonth-March(3),
    	wtWebioAn1GraphNtcStopMonth-April(4),
    	wtWebioAn1GraphNtcStopMonth-May(5),
    	wtWebioAn1GraphNtcStopMonth-June(6),
    	wtWebioAn1GraphNtcStopMonth-July(7),
    	wtWebioAn1GraphNtcStopMonth-August(8),
    	wtWebioAn1GraphNtcStopMonth-September(9),
    	wtWebioAn1GraphNtcStopMonth-October(10),
    	wtWebioAn1GraphNtcStopMonth-November(11),
    	wtWebioAn1GraphNtcStopMonth-December(12)
    	}
    ACCESS read-write
    STATUS mandatory
    DESCRIPTION
        "Month in which the change is made from summer time to winter time."
   ::= { wtWebioAn1GraphNtcTimeZone 12 }

wtWebioAn1GraphNtcStTzStopMode OBJECT-TYPE
    SYNTAX INTEGER {
    	wtWebioAn1GraphNtcStopMode-first(1),
    	wtWebioAn1GraphNtcStopMode-second(2),
    	wtWebioAn1GraphNtcStopMode-third(3),
    	wtWebioAn1GraphNtcStopMode-fourth(4),
    	wtWebioAn1GraphNtcStopMode-last(5)
    	}
    ACCESS read-write
    STATUS mandatory
    DESCRIPTION
        "Mode of the week day on which the change is made from summer time to winter time."
    ::= { wtWebioAn1GraphNtcTimeZone 13 }

wtWebioAn1GraphNtcStTzStopWday OBJECT-TYPE
    SYNTAX INTEGER {
    	wtWebioAn1GraphNtcStopWday-Sunday(1),
    	wtWebioAn1GraphNtcStopWday-Monday(2),
    	wtWebioAn1GraphNtcStopWday-Tuesday(3),
    	wtWebioAn1GraphNtcStopWday-Thursday(4),
    	wtWebioAn1GraphNtcStopWday-Wednesday(5),
    	wtWebioAn1GraphNtcStopWday-Friday(6),
    	wtWebioAn1GraphNtcStopWday-Saturday(7)
    	}
    ACCESS read-write
    STATUS mandatory
    DESCRIPTION
        "Day of the week on which the change is made from summer time to winter time."
    ::= { wtWebioAn1GraphNtcTimeZone 14 }

wtWebioAn1GraphNtcStTzStopHrs OBJECT-TYPE
    SYNTAX INTEGER
    ACCESS read-write
    STATUS mandatory
    DESCRIPTION
        "Hour at which the time zone is changed from summer to winter time with
        respect to UTC."
    ::= { wtWebioAn1GraphNtcTimeZone 15 }

wtWebioAn1GraphNtcStTzStopMin OBJECT-TYPE
    SYNTAX INTEGER
    ACCESS read-write
    STATUS mandatory
    DESCRIPTION
        "Minute at which the time zone is changed from summer to winter time with
        respect to UTC."
    ::= { wtWebioAn1GraphNtcTimeZone 16 }

-- wtWebioAn1GraphNtcTimeServer Group
----------------------------

wtWebioAn1GraphNtcTimeServer1 OBJECT-TYPE
    SYNTAX OCTET STRING
    ACCESS read-write
    STATUS mandatory
    DESCRIPTION
        "IP address or name of the 1st time server in ASCII"
    ::= { wtWebioAn1GraphNtcTimeServer 1 }

wtWebioAn1GraphNtcTimeServer2 OBJECT-TYPE
    SYNTAX OCTET STRING
    ACCESS read-write
    STATUS mandatory
    DESCRIPTION
        "IP address or name of the 2nd time server in ASCII"
    ::= { wtWebioAn1GraphNtcTimeServer 2 }

wtWebioAn1GraphNtcTsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebioAn1GraphNtcTimeServer 3 }

wtWebioAn1GraphNtcTsSyncTime OBJECT-TYPE
    SYNTAX INTEGER
    ACCESS read-write
    STATUS mandatory
    DESCRIPTION
        "Daily synchronisation time with the time server (hour: 0-23)."
    ::= { wtWebioAn1GraphNtcTimeServer 4 }

-- wtWebioAn1GraphNtcDeviceClock Group
----------------------------

wtWebioAn1GraphNtcClockHrs OBJECT-TYPE
    SYNTAX INTEGER (0..23)
    ACCESS read-write
    STATUS mandatory
    DESCRIPTION
        "Clock hours taking into account the time zone settings."
    ::= { wtWebioAn1GraphNtcDeviceClock 1 }

wtWebioAn1GraphNtcClockMin OBJECT-TYPE
    SYNTAX INTEGER (0..59)
    ACCESS read-write
    STATUS mandatory
    DESCRIPTION
        "Clock minutes taking into account the time zone settings."
    ::= { wtWebioAn1GraphNtcDeviceClock 2 }

wtWebioAn1GraphNtcClockDay OBJECT-TYPE
    SYNTAX INTEGER (1..31)
    ACCESS read-write
    STATUS mandatory
    DESCRIPTION
        "Date: Day of the month, taking into account the time zone settings."
    ::= { wtWebioAn1GraphNtcDeviceClock 3 }

wtWebioAn1GraphNtcClockMonth OBJECT-TYPE
   SYNTAX INTEGER {
    	wtWebioAn1GraphNtcClockMonth-January(1),
    	wtWebioAn1GraphNtcClockMonth-February(2),
    	wtWebioAn1GraphNtcClockMonth-March(3),
    	wtWebioAn1GraphNtcClockMonth-April(4),
    	wtWebioAn1GraphNtcClockMonth-May(5),
    	wtWebioAn1GraphNtcClockMonth-June(6),
    	wtWebioAn1GraphNtcClockMonth-July(7),
    	wtWebioAn1GraphNtcClockMonth-August(8),
    	wtWebioAn1GraphNtcClockMonth-September(9),
    	wtWebioAn1GraphNtcClockMonth-October(10),
    	wtWebioAn1GraphNtcClockMonth-November(11),
    	wtWebioAn1GraphNtcClockMonth-December(12)
    	}
    ACCESS read-write
    STATUS mandatory
    DESCRIPTION
        "Date: Month, taking into account the time zone settings."
    ::= { wtWebioAn1GraphNtcDeviceClock 4 }

wtWebioAn1GraphNtcClockYear OBJECT-TYPE
    SYNTAX INTEGER (0..65535)
    ACCESS read-write
    STATUS mandatory
    DESCRIPTION
        "Date: Year, taking into account the time zone settings."
    ::= { wtWebioAn1GraphNtcDeviceClock 5 }


-- wtWebioAn1GraphNtcNetwork Group
------------------------

wtWebioAn1GraphNtcIpAddress OBJECT-TYPE
    SYNTAX IpAddress
    ACCESS read-write
    STATUS mandatory
    DESCRIPTION
        "IP address of the Webio"
    ::= { wtWebioAn1GraphNtcNetwork 1 }

wtWebioAn1GraphNtcSubnetMask OBJECT-TYPE
    SYNTAX IpAddress
    ACCESS read-write
    STATUS mandatory
    DESCRIPTION
        "Subnet mask of the Webio"
    ::= { wtWebioAn1GraphNtcNetwork 2 }

wtWebioAn1GraphNtcGateway OBJECT-TYPE
    SYNTAX IpAddress
    ACCESS read-write
    STATUS mandatory
    DESCRIPTION
        "Gateway of the Webio"
    ::= { wtWebioAn1GraphNtcNetwork 3 }

wtWebioAn1GraphNtcDnsServer1 OBJECT-TYPE
    SYNTAX OCTET STRING
    ACCESS read-write
    STATUS mandatory
    DESCRIPTION
        "IP address of the 1st DNS server in ASCII"
    ::= { wtWebioAn1GraphNtcNetwork 4 }

wtWebioAn1GraphNtcDnsServer2 OBJECT-TYPE
    SYNTAX OCTET STRING
    ACCESS read-write
    STATUS mandatory
    DESCRIPTION
        "IP address of the 2nd DNS server in ASCII"
    ::= { wtWebioAn1GraphNtcNetwork 5 }

wtWebioAn1GraphNtcAddConfig OBJECT-TYPE
    SYNTAX OCTET STRING
    ACCESS read-write
    STATUS mandatory
    DESCRIPTION
        "Additional configuration (1=ON):
        Octet 1: unused
        Octet 2: unused
        Octet 3: unused
        Octet 4:
	        Bit 1: DHCP disable
	        Bit 0: BOOTP disable
	        "
    ::= { wtWebioAn1GraphNtcNetwork 6 }

--  wtWebioAn1GraphNtcHTTP Group
--------------------------------

wtWebioAn1GraphNtcStartup OBJECT-TYPE
    SYNTAX OCTET STRING
    ACCESS read-write
    STATUS mandatory
    DESCRIPTION
        "Binary coded start page:
        Octet 1: unused
        Octet 2: unused
        Octet 3: unused
        Octet 4:
	        Bit 1: Index.htm
	        Bit 2: Home.htm
	        Bit 3: User.htm
	Only one page may be selected at a time."
    ::= { wtWebioAn1GraphNtcHTTP 1 }

wtWebioAn1GraphNtcGetHeaderEnable OBJECT-TYPE
    SYNTAX OCTET STRING
    ACCESS read-write
    STATUS mandatory
    DESCRIPTION
        "If these bits are set, every answer of a short form GET question will be lead
        by the IP-address and name of the device and/or a HTTP header:
        Octet 1: unused
        Octet 2: unused
        Octet 3: unused
        Octet 4:
        	Bit 1-6: unused
        	Bit 1  : GET HTTP enable
                Bit 0  : GET Header enable"
    ::= { wtWebioAn1GraphNtcHTTP 2 }

wtWebioAn1GraphNtcHttpPort OBJECT-TYPE
    SYNTAX INTEGER (1..65535)
    ACCESS read-write
    STATUS mandatory
    DESCRIPTION
        "Definition of the standard HTML port (Default: 80)."
    ::= { wtWebioAn1GraphNtcHTTP 3 }


-- wtWebioAn1GraphNtcMail Group
--------------------------------

wtWebioAn1GraphNtcMailAdName OBJECT-TYPE
    SYNTAX OCTET STRING
    ACCESS read-write
    STATUS mandatory
    DESCRIPTION
        "Device name for mail administration."
    ::= { wtWebioAn1GraphNtcMail 1 }

wtWebioAn1GraphNtcMailReply OBJECT-TYPE
    SYNTAX OCTET STRING
    ACCESS read-write
    STATUS mandatory
    DESCRIPTION
        "Reply address for the mail server."
    ::= { wtWebioAn1GraphNtcMail 2 }

wtWebioAn1GraphNtcMailServer OBJECT-TYPE
    SYNTAX OCTET STRING
    ACCESS read-write
    STATUS mandatory
    DESCRIPTION
        "Name or IP address of the mail server."
    ::= { wtWebioAn1GraphNtcMail 3 }

wtWebioAn1MailEnable OBJECT-TYPE
    SYNTAX OCTET STRING
    ACCESS read-write
    STATUS mandatory
    DESCRIPTION
        "Set this bit to enable the sending of mails:
        Octet 1: unused
        Octet 2: unused
        Octet 3: unused
        Octet 4:
        	Bit 1-7: unused
                Bit 0  : Mail enable"
    ::= { wtWebioAn1GraphNtcMail 4 }

wtWebioAn1GraphNtcMailAuthentication OBJECT-TYPE
    SYNTAX OCTET STRING (SIZE (4))
    ACCESS read-write
    STATUS mandatory
    DESCRIPTION
        "Selection of the authentication modi:
        The OCTETS are interpreted bit-by-bit, with each bit corresponding to an output.
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebioAn1GraphNtcMail 5 }

wtWebioAn1GraphNtcMailAuthUser OBJECT-TYPE
    SYNTAX OCTET STRING
    ACCESS read-write
    STATUS mandatory
    DESCRIPTION
        "Name of the user to be authenticated."
    ::= { wtWebioAn1GraphNtcMail 6 }

wtWebioAn1GraphNtcMailAuthPassword OBJECT-TYPE
    SYNTAX OCTET STRING
    ACCESS read-write
    STATUS mandatory
    DESCRIPTION
        "Authentication password."
    ::= { wtWebioAn1GraphNtcMail 7 }

wtWebioAn1GraphNtcMailPop3Server OBJECT-TYPE
    SYNTAX OCTET STRING
    ACCESS read-write
    STATUS mandatory
    DESCRIPTION
        "Name or Ip-address of the POP3 Servers."
    ::= { wtWebioAn1GraphNtcMail 8 }


-- wtWebioAn1GraphNtcSNMP Group
--------------------------------

wtWebioAn1GraphNtcSnmpCommunityStringRead OBJECT-TYPE
    SYNTAX OCTET STRING
    ACCESS read-write
    STATUS mandatory
    DESCRIPTION
        "Community string read only"
    ::= { wtWebioAn1GraphNtcSNMP 1 }

wtWebioAn1GraphNtcSnmpCommunityStringReadWrite OBJECT-TYPE
    SYNTAX OCTET STRING
    ACCESS read-write
    STATUS mandatory
    DESCRIPTION
        "Community string read / write"
    ::= { wtWebioAn1GraphNtcSNMP 2 }

wtWebioAn1GraphNtcSystemTrapManagerIP OBJECT-TYPE
    SYNTAX OCTET STRING
    ACCESS read-write
    STATUS mandatory
    DESCRIPTION
        "Name or IP address of the TCP server which accepts the system trap."
    ::= { wtWebioAn1GraphNtcSNMP 3 }

wtWebioAn1GraphNtcSystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2-7: unused"
    ::= { wtWebioAn1GraphNtcSNMP 4 }

wtWebioAn1GraphNtcSnmpEnable OBJECT-TYPE
    SYNTAX OCTET STRING
    ACCESS read-write
    STATUS mandatory
    DESCRIPTION
        "Set bit 0 to enable SNMP.
        If disabled, the device did not respond to any SNMP requests.
        Bit 1 decided wether the community string of read operations
        is compared with the system password or not:
        Octet 1: unused
        Octet 2: unused
        Octet 3: unused
        Octet 4:
        	Bit 1-7: unused
        	Bit 0  : SNMP enable"
    ::= { wtWebioAn1GraphNtcSNMP 5 }

wtWebioAn1GraphNtcSnmpCommunityStringTrap OBJECT-TYPE
    SYNTAX OCTET STRING
    ACCESS read-write
    STATUS mandatory
    DESCRIPTION
        "Community string send within traps."
    ::= { wtWebioAn1GraphNtcSNMP 6 }

-- wtWebioAn1GraphNtcUDP Group
--------------------------------

wtWebioAn1GraphNtcUdpPort OBJECT-TYPE
    SYNTAX INTEGER (1..65535)
    ACCESS read-write
    STATUS mandatory
    DESCRIPTION
        "Udp port to which the Udp queries ( short form GET requests) can be sent. This
        port number must be unique within the device."
    ::= { wtWebioAn1GraphNtcUDP 1 }

wtWebioAn1GraphNtcUdpEnable OBJECT-TYPE
    SYNTAX OCTET STRING
    ACCESS read-write
    STATUS mandatory
    DESCRIPTION
        "Set this bit to enable UDP support:
        Octet 1: unused
        Octet 2: unused
        Octet 3: unused
        Octet 4:
        	Bit 1-7: unused
                Bit 0  : UDP enable"
    ::= { wtWebioAn1GraphNtcUDP 2 }


--  wtWebioAn1GraphNtcSyslog Group
--------------------------------

wtWebioAn1GraphNtcSyslogServerIP OBJECT-TYPE
    SYNTAX OCTET STRING
    ACCESS read-write
    STATUS mandatory
    DESCRIPTION
        "Name or IP address of the Syslog server, which accepts the Syslog messgaes."
    ::= { wtWebioAn1GraphNtcSyslog 1 }

wtWebioAn1GraphNtcSyslogServerPort OBJECT-TYPE
    SYNTAX INTEGER
    ACCESS read-write
    STATUS mandatory
    DESCRIPTION
        "Portnumber of the Syslog servers, default 514."
    ::= { wtWebioAn1GraphNtcSyslog 2 }

wtWebioAn1GraphNtcSyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebioAn1GraphNtcSyslog 3 }

wtWebioAn1GraphNtcSyslogEnable OBJECT-TYPE
    SYNTAX OCTET STRING
    ACCESS read-write
    STATUS mandatory
    DESCRIPTION
        "Set bit 0 to enable Syslog:
        Octet 1: unused
        Octet 2: unused
        Octet 3: unused
        Octet 4:
        	Bit 1-7: unused
                Bit 0  : Syslog enable"
    ::= { wtWebioAn1GraphNtcSyslog 4 }

--  wtWebioAn1GraphNtcFTP Group
--------------------------------

wtWebioAn1GraphNtcFTPServerIP OBJECT-TYPE
    SYNTAX OCTET STRING
    ACCESS read-write
    STATUS mandatory
    DESCRIPTION
        "Name or IP address of the FTP server, which accepts the FTP messages."
    ::= { wtWebioAn1GraphNtcFTP 1 }

wtWebioAn1GraphNtcFTPServerControlPort OBJECT-TYPE
    SYNTAX INTEGER
    ACCESS read-write
    STATUS mandatory
    DESCRIPTION
        "Portnumber of the control port of the FTP server, default 21."
    ::= { wtWebioAn1GraphNtcFTP 2 }

wtWebioAn1GraphNtcFTPUserName OBJECT-TYPE
    SYNTAX OCTET STRING
    ACCESS read-write
    STATUS mandatory
    DESCRIPTION
        "FTP Loggin: user name."
    ::= { wtWebioAn1GraphNtcFTP 3 }

wtWebioAn1GraphNtcFTPPassword OBJECT-TYPE
    SYNTAX OCTET STRING
    ACCESS read-write
    STATUS mandatory
    DESCRIPTION
        "FTP Loggin: user password."
    ::= { wtWebioAn1GraphNtcFTP 4 }

wtWebioAn1GraphNtcFTPAccount OBJECT-TYPE
    SYNTAX OCTET STRING
    ACCESS read-write
    STATUS mandatory
    DESCRIPTION
        "FTP Loggin: name of account."
    ::= { wtWebioAn1GraphNtcFTP 5 }

wtWebioAn1GraphNtcFTPOption OBJECT-TYPE
    SYNTAX OCTET STRING
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebioAn1GraphNtcFTP 6 }

wtWebioAn1GraphNtcFTPEnable OBJECT-TYPE
    SYNTAX OCTET STRING
    ACCESS read-write
    STATUS mandatory
    DESCRIPTION
        "Set Bit 0 to enable FTP:
        Octet 1: unused
        Octet 2: unused
        Octet 3: unused
        Octet 4:
        	Bit 1-7: unused
                Bit 0  : FTP enable"
    ::= { wtWebioAn1GraphNtcFTP 7 }

--  wtWebioAn1GraphNtcMQTT Group
--------------------------------

wtWebioAn1GraphNtcMQTTEnable OBJECT-TYPE
    SYNTAX OCTET STRING
    ACCESS read-write
    STATUS mandatory
    DESCRIPTION
        "Bit 7 schaltet MQTT frei:
        Octet 1: ungenutzt
        Octet 2: ungenutzt
        Octet 3: ungenutzt
        Octet 4:
        	Bit 0-6: ungenutzt
                Bit 7  : MQTT enable"
    ::= { wtWebioAn1GraphNtcMQTT 1 }

wtWebioAn1GraphNtcMQTTBrockerIP OBJECT-TYPE
    SYNTAX OCTET STRING
    ACCESS read-write
    STATUS mandatory
    DESCRIPTION
        "Name or IP-address of the MQTT-Server."
    ::= { wtWebioAn1GraphNtcMQTT 2 }

wtWebioAn1GraphNtcMQTTUserName OBJECT-TYPE
    SYNTAX OCTET STRING
    ACCESS read-write
    STATUS mandatory
    DESCRIPTION
        "MQTT login  user name."
    ::= { wtWebioAn1GraphNtcMQTT 3 }

wtWebioAn1GraphNtcMQTTPassword OBJECT-TYPE
    SYNTAX OCTET STRING
    ACCESS read-write
    STATUS mandatory
    DESCRIPTION
        "MQTT login password."
    ::= { wtWebioAn1GraphNtcMQTT 4 }

wtWebioAn1GraphNtcMQTTLocalPort OBJECT-TYPE
    SYNTAX INTEGER
    ACCESS read-write
    STATUS mandatory
    DESCRIPTION
        "Local port number."
    ::= { wtWebioAn1GraphNtcMQTT 5 }

wtWebioAn1GraphNtcMQTTBrokerServerPort OBJECT-TYPE
    SYNTAX INTEGER
    ACCESS read-write
    STATUS mandatory
    DESCRIPTION
        "MQTT Server port number."
    ::= { wtWebioAn1GraphNtcMQTT 6 }

wtWebioAn1GraphNtcMQTTInterval OBJECT-TYPE
    SYNTAX INTEGER
    ACCESS read-write
    STATUS mandatory
    DESCRIPTION
        "Ping intervall, if no data has to be send: time in seconds."
    ::= { wtWebioAn1GraphNtcMQTT 7 }

--  wtWebioAn1GraphNtcREST Group
--------------------------------

wtWebioAn1GraphNtcRESTEnable OBJECT-TYPE
    SYNTAX OCTET STRING
    ACCESS read-write
    STATUS mandatory
    DESCRIPTION
        "Bit 0 activates REST :
        Octet 1: unused
        Octet 2: unused
        Octet 3: unused
        Octet 4:
        	Bit 1-7: unused
            Bit 0  : REST enable"
    ::= { wtWebioAn1GraphNtcREST 1 }

wtWebioAn1GraphNtcRESTDigestAuthEnable OBJECT-TYPE
    SYNTAX OCTET STRING
    ACCESS read-write
    STATUS mandatory
    DESCRIPTION
        "Bit 0 activates Digest-Authentification:
        Octet 1: unused
        Octet 2: unused
        Octet 3: unused
        Octet 4:
        	Bit 1-7: unused
            Bit 0  : Digest Auth enable"
    ::= { wtWebioAn1GraphNtcREST 2 }

-- wtWebioAn1GraphNtcDatalogger Group
--------------------------------

wtWebioAn1GraphNtcLoggerTimebase OBJECT-TYPE
    SYNTAX INTEGER {
    wtWebioAn1GraphNtcDatalogger-1Min(1),
    wtWebioAn1GraphNtcDatalogger-5Min(2),
    wtWebioAn1GraphNtcDatalogger-15Min(3),
    wtWebioAn1GraphNtcDatalogger-60Min(4)
    }
    ACCESS read-write
    STATUS mandatory
    DESCRIPTION
        "Time base of the data logger"
    ::= { wtWebioAn1GraphNtcDatalogger 1 }

wtWebioAn1GraphNtcLoggerSensorSel OBJECT-TYPE
    SYNTAX OCTET STRING (SIZE(4))
    ACCESS read-write
    STATUS mandatory
    DESCRIPTION
        "Binary coded trigger conditions:
        Octet 1: unused
        Octet 2: unused
        Octet 3: unused
        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
    ::= { wtWebioAn1GraphNtcDatalogger 2 }

wtWebioAn1GraphNtcDisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
    ::= { wtWebioAn1GraphNtcDatalogger 3 }

-- Graph Sensor Color Table

wtWebioAn1GraphNtcSensorColorTable OBJECT-TYPE
    SYNTAX SEQUENCE OF WtWebioAn1GraphNtcSensorColorEntry
    ACCESS not-accessible
    STATUS mandatory
    DESCRIPTION
        "List of sensor colors for the praphical presentation."
    ::= { wtWebioAn1GraphNtcDatalogger 4 }

wtWebioAn1GraphNtcSensorColorEntry OBJECT-TYPE
    SYNTAX WtWebioAn1GraphNtcSensorColorEntry
    ACCESS not-accessible
    STATUS mandatory
    DESCRIPTION
        "Index numbers of the sensors."
    INDEX  { wtWebioAn1GraphNtcSensorNo }
    ::= { wtWebioAn1GraphNtcSensorColorTable 1 }

WtWebioAn1GraphNtcSensorColorEntry ::= SEQUENCE {
    wtWebioAn1GraphNtcSensorColor OCTET STRING
}

wtWebioAn1GraphNtcSensorColor OBJECT-TYPE
    SYNTAX OCTET STRING (SIZE(3))
    ACCESS read-write
    STATUS mandatory
    DESCRIPTION
        "Color of the sensors at the praphical presention."
    ::= { wtWebioAn1GraphNtcSensorColorEntry 1 }

wtWebioAn1GraphNtcAutoScaleEnable OBJECT-TYPE
    SYNTAX OCTET STRING
    ACCESS read-write
    STATUS mandatory
    DESCRIPTION
        "If bit 0 is set, vertical auto scale is enabled:
        Octet 1: unused
        Octet 2: unused
        Octet 3: unused
        Octet 4:
        	Bit 1-7: unused
                Bit 0  : Auto Scale enable"
    ::= { wtWebioAn1GraphNtcDatalogger 5 }

wtWebioAn1GraphNtcVerticalUpperLimit OBJECT-TYPE
    SYNTAX OCTET STRING
    ACCESS read-write
    STATUS mandatory
    DESCRIPTION
        "This value defines the maximum temperature shown in the graphical presentation,
        if no auto scaling is selected.
        Temperature in degrees with maximum 2 decimal places."
    ::= { wtWebioAn1GraphNtcDatalogger 6 }

wtWebioAn1GraphNtcVerticalLowerLimit OBJECT-TYPE
    SYNTAX OCTET STRING
    ACCESS read-write
    STATUS mandatory
    DESCRIPTION
        "This value defines the minimum temperature shown in the graphical presentation,
        if no auto scaling is selected.
        Temperature in degrees with maximum 2 decimal places."
    ::= { wtWebioAn1GraphNtcDatalogger 7 }

wtWebioAn1GraphNtcHorizontalZoom OBJECT-TYPE
    SYNTAX INTEGER {
    wtWebioAn1GraphNtcZoom-25min(1),
    wtWebioAn1GraphNtcZoom-75min(2),
    wtWebioAn1GraphNtcZoom-5hrs(3),
    wtWebioAn1GraphNtcZoom-30hrs(4),
    wtWebioAn1GraphNtcZoom-5days(5),
    wtWebioAn1GraphNtcZoom-25days(6)
    }
    ACCESS read-write
    STATUS mandatory
    DESCRIPTION
        "Defines the default zoom stage, if no auto scaling is selected."
    ::= { wtWebioAn1GraphNtcDatalogger 8 }

-- wtWebioAn1GraphNtcAlarm Group
----------------------------

wtWebioAn1GraphNtcAlarmCount OBJECT-TYPE
    SYNTAX INTEGER (1..8)
    ACCESS read-only
    STATUS mandatory
    DESCRIPTION
        "Number of independent alarms."
    ::= { wtWebioAn1GraphNtcAlarm 1 }

-- Alarm Interface Table

wtWebioAn1GraphNtcAlarmIfTable OBJECT-TYPE
    SYNTAX SEQUENCE OF WtWebioAn1GraphNtcAlarmIfEntry
    ACCESS not-accessible
    STATUS mandatory
    DESCRIPTION
        "List of alarm indices."
    ::= { wtWebioAn1GraphNtcAlarm 2 }

wtWebioAn1GraphNtcAlarmIfEntry OBJECT-TYPE
    SYNTAX WtWebioAn1GraphNtcAlarmIfEntry
    ACCESS not-accessible
    STATUS mandatory
    DESCRIPTION
        "Numbers of the alarms."
    INDEX  { wtWebioAn1GraphNtcAlarmNo }
    ::= { wtWebioAn1GraphNtcAlarmIfTable 1 }

WtWebioAn1GraphNtcAlarmIfEntry ::= SEQUENCE {
    wtWebioAn1GraphNtcAlarmNo INTEGER
}

wtWebioAn1GraphNtcAlarmNo OBJECT-TYPE
    SYNTAX INTEGER (1..8)
    ACCESS read-only
    STATUS mandatory
    DESCRIPTION
        "Alarm number."
    ::= { wtWebioAn1GraphNtcAlarmIfEntry 1 }

-- Alarm Table

wtWebioAn1GraphNtcAlarmTable OBJECT-TYPE
    SYNTAX SEQUENCE OF WtWebioAn1GraphNtcAlarmEntry
    ACCESS not-accessible
    STATUS mandatory
    DESCRIPTION
        "List of settings depending on the alarm number."
    ::= { wtWebioAn1GraphNtcAlarm 3 }

wtWebioAn1GraphNtcAlarmEntry OBJECT-TYPE
    SYNTAX WtWebioAn1GraphNtcAlarmEntry
    ACCESS not-accessible
    STATUS mandatory
    DESCRIPTION
        "Alarm parameters of the individual alarms."
    INDEX  { wtWebioAn1GraphNtcAlarmNo }
    ::= { wtWebioAn1GraphNtcAlarmTable 1 }

WtWebioAn1GraphNtcAlarmEntry ::= SEQUENCE {
    wtWebioAn1GraphNtcAlarmTrigger				OCTET STRING,
    wtWebioAn1GraphNtcAlarmMin					OCTET STRING,
    wtWebioAn1GraphNtcAlarmMax					OCTET STRING,
    wtWebioAn1GraphNtcAlarmHysteresis			OCTET STRING,
    wtWebioAn1GraphNtcAlarmDelay				OCTET STRING,
    wtWebioAn1GraphNtcAlarmInterval				OCTET STRING,
    wtWebioAn1GraphNtcAlarmEnable				OCTET STRING,
    wtWebioAn1GraphNtcAlarmEMailAddr			OCTET STRING,
    wtWebioAn1GraphNtcAlarmMailSubject			OCTET STRING,
    wtWebioAn1GraphNtcAlarmMailText				OCTET STRING,
    wtWebioAn1GraphNtcAlarmManagerIP			OCTET STRING,
    wtWebioAn1GraphNtcAlarmTrapText				OCTET STRING,
    wtWebioAn1GraphNtcAlarmMailOptions			OCTET STRING,
    wtWebioAn1GraphNtcAlarmTcpIpAddr			OCTET STRING,
    wtWebioAn1GraphNtcAlarmTcpPort				INTEGER,
    wtWebioAn1GraphNtcAlarmTcpText				OCTET STRING,
    wtWebioAn1GraphNtcAlarmClearMailSubject		OCTET STRING,
    wtWebioAn1GraphNtcAlarmClearMailText		OCTET STRING,
    wtWebioAn1GraphNtcAlarmClearTrapText		OCTET STRING,
    wtWebioAn1GraphNtcAlarmClearTcpText			OCTET STRING,
    wtWebioAn1GraphNtcAlarmSyslogIpAddr			OCTET STRING,
    wtWebioAn1GraphNtcAlarmSyslogPort			INTEGER,
    wtWebioAn1GraphNtcAlarmSyslogText			OCTET STRING,
    wtWebioAn1GraphNtcAlarmFtpDataPort			OCTET STRING,
    wtWebioAn1GraphNtcAlarmFtpFileName			OCTET STRING,
    wtWebioAn1GraphNtcAlarmFtpText				OCTET STRING,
    wtWebioAn1GraphNtcAlarmFtpClearText			OCTET STRING,
    wtWebioAn1GraphNtcAlarmFtpOption			OCTET STRING,
    wtWebioAn1GraphNtcAlarmTimerCron			OCTET STRING,
    wtWebioAn1GraphNtcAlarmDeltaTemp			OCTET STRING,
    wtWebioAn1GraphNtcAlarmName 				OCTET STRING,
    wtWebioAn1GraphNtcAlarmActive 				OCTET STRING
    wtWebioAn1GraphNtcAlarmHttpReqAuthEnable	OCTET STRING,
    wtWebioAn1GraphNtcAlarmHttpReqAuthUser		OCTET STRING,
    wtWebioAn1GraphNtcAlarmHttpReqAuthPassword	OCTET STRING,
    wtWebioAn1GraphNtcAlarmHttpReqSetUrl		OCTET STRING,
    wtWebioAn1GraphNtcAlarmHttpReqClearUrl		OCTET STRING,
    wtWebioAn1GraphNtcAlarmHttpReqServerPort	OCTET STRING,
    wtWebioAn1GraphNtcAlarmMqttTopicPath		OCTET STRING,
    wtWebioAn1GraphNtcAlarmMqttTopicSetTopic	OCTET STRING,
    wtWebioAn1GraphNtcAlarmMqttTopicClear		OCTET STRING,
	wtWebioAn1GraphNtcAlarmSensorLostSelection	OCTET STRING,
	wtWebioAn1GraphNtcAlarmLimitWindow			INTEGER
}

wtWebioAn1GraphNtcAlarmTrigger OBJECT-TYPE
    SYNTAX OCTET STRING (SIZE(4))
    ACCESS read-write
    STATUS mandatory
    DESCRIPTION
        "Binary coded trigger conditions:
        Octet 1: unused
        Octet 2: unused
        Octet 3:
        	Bit 0: Timer
        	Bit 1: ColdStart
        	Bit 2: WarmStart

        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
    ::= { wtWebioAn1GraphNtcAlarmEntry 1 }

wtWebioAn1GraphNtcAlarmMin OBJECT-TYPE
    SYNTAX OCTET STRING
    ACCESS read-write
    STATUS mandatory
    DESCRIPTION
        "Minimum temperature in degrees with maximum 2 decimal places."
    ::= { wtWebioAn1GraphNtcAlarmEntry 2 }

wtWebioAn1GraphNtcAlarmMax OBJECT-TYPE
    SYNTAX OCTET STRING
    ACCESS read-write
    STATUS mandatory
    DESCRIPTION
        "Maximum temperature in degrees with maximum 2 decimal places."
    ::= { wtWebioAn1GraphNtcAlarmEntry 3 }

wtWebioAn1GraphNtcAlarmHysteresis OBJECT-TYPE
    SYNTAX OCTET STRING
    ACCESS read-write
    STATUS mandatory
    DESCRIPTION
        "Temperature changes of this size clears the alarm state (MAX-hyst, MIN+hyst.)
        , in degrees with maximum 2 decimal places."
    ::= { wtWebioAn1GraphNtcAlarmEntry 4 }

wtWebioAn1GraphNtcAlarmDelay OBJECT-TYPE
    SYNTAX OCTET STRING
    ACCESS read-write
    STATUS mandatory
    DESCRIPTION
        "Alarm will be delayed by setting this time while stable alarm
        condition occur (time in minutes)."
    ::= { wtWebioAn1GraphNtcAlarmEntry 5 }


wtWebioAn1GraphNtcAlarmInterval OBJECT-TYPE
    SYNTAX OCTET STRING
    ACCESS read-write
    STATUS mandatory
    DESCRIPTION
        "Send interval for alarm messages."
    ::= { wtWebioAn1GraphNtcAlarmEntry 6 }

wtWebioAn1GraphNtcAlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  TCP Client enable"
    ::= { wtWebioAn1GraphNtcAlarmEntry 7 }

wtWebioAn1GraphNtcAlarmEMailAddr OBJECT-TYPE
    SYNTAX OCTET STRING
    ACCESS read-write
    STATUS mandatory
    DESCRIPTION
        "E-Mail address for sending the alarm mail to."
    ::= { wtWebioAn1GraphNtcAlarmEntry 8 }

wtWebioAn1GraphNtcAlarmMailSubject OBJECT-TYPE
    SYNTAX OCTET STRING
    ACCESS read-write
    STATUS mandatory
    DESCRIPTION
        "Subject line for alarm mail."
    ::= { wtWebioAn1GraphNtcAlarmEntry 9 }

wtWebioAn1GraphNtcAlarmMailText OBJECT-TYPE
    SYNTAX OCTET STRING
    ACCESS read-write
    STATUS mandatory
    DESCRIPTION
        "Alarm mail text: <Tn> provides the current temperature; n = 1..8.
        <Z> provides the current time."
    ::= { wtWebioAn1GraphNtcAlarmEntry 10 }

wtWebioAn1GraphNtcAlarmManagerIP OBJECT-TYPE
    SYNTAX OCTET STRING
    ACCESS read-write
    STATUS mandatory
    DESCRIPTION
        "Name or IP address of the SNMP Manager which accepts the trap."
    ::= { wtWebioAn1GraphNtcAlarmEntry 11 }

wtWebioAn1GraphNtcAlarmTrapText OBJECT-TYPE
    SYNTAX OCTET STRING
    ACCESS read-write
    STATUS mandatory
    DESCRIPTION
        "This text is sent in the trap body."
    ::= { wtWebioAn1GraphNtcAlarmEntry 12 }

wtWebioAn1GraphNtcAlarmMailOptions OBJECT-TYPE
    SYNTAX OCTET STRING (SIZE(4))
    ACCESS read-write
    STATUS mandatory
    DESCRIPTION
        "Binary coded options:
        Octet 1: unused
        Octet 2: unused
        Octet 3: unused
        Octet 4:
		Bit 0  :	Attach Thermo.csv Enable
		Bit 1  :	CSV-Data_since_last_report
        	Bit 2-7:	unused"
    ::= { wtWebioAn1GraphNtcAlarmEntry 13 }

wtWebioAn1GraphNtcAlarmTcpIpAddr OBJECT-TYPE
    SYNTAX OCTET STRING
    ACCESS read-write
    STATUS mandatory
    DESCRIPTION
        "Name or IP address of the TCP server which accepts the trap."
    ::= { wtWebioAn1GraphNtcAlarmEntry 14 }

wtWebioAn1GraphNtcAlarmTcpPort OBJECT-TYPE
    SYNTAX INTEGER (1..65535)
    ACCESS read-write
    STATUS mandatory
    DESCRIPTION
        "Port number of the TCP server which accepts the trap."
    ::= { wtWebioAn1GraphNtcAlarmEntry 15 }

wtWebioAn1GraphNtcAlarmTcpText OBJECT-TYPE
    SYNTAX OCTET STRING
    ACCESS read-write
    STATUS mandatory
    DESCRIPTION
        "This text is sent in the TCP trap body."
    ::= { wtWebioAn1GraphNtcAlarmEntry 16 }

wtWebioAn1GraphNtcAlarmClearMailSubject OBJECT-TYPE
    SYNTAX OCTET STRING
    ACCESS read-write
    STATUS mandatory
    DESCRIPTION
        "Subject line for alarm clear mail."
    ::= { wtWebioAn1GraphNtcAlarmEntry 17 }

wtWebioAn1GraphNtcAlarmClearMailText OBJECT-TYPE
    SYNTAX OCTET STRING
    ACCESS read-write
    STATUS mandatory
    DESCRIPTION
        " Alarm clear mail text: <Tn> provides the current temperature; n = 1..8. <Z> provides the current time."
    ::= { wtWebioAn1GraphNtcAlarmEntry 18 }

wtWebioAn1GraphNtcAlarmClearTrapText OBJECT-TYPE
    SYNTAX OCTET STRING
    ACCESS read-write
    STATUS mandatory
    DESCRIPTION
        "This text is sent in the trap body."
    ::= { wtWebioAn1GraphNtcAlarmEntry 19 }

wtWebioAn1GraphNtcAlarmClearTcpText OBJECT-TYPE
    SYNTAX OCTET STRING
    ACCESS read-write
    STATUS mandatory
    DESCRIPTION
        "This text is sent in the TCP trap body."
    ::= { wtWebioAn1GraphNtcAlarmEntry 20 }

wtWebioAn1GraphNtcAlarmSyslogIpAddr OBJECT-TYPE
    SYNTAX IpAddress
    ACCESS read-write
    STATUS mandatory
    DESCRIPTION
        "IP address of the syslog server to which the Webio device should send syslog messages."
    ::= { wtWebioAn1GraphNtcAlarmEntry 21 }

wtWebioAn1GraphNtcAlarmSyslogPort OBJECT-TYPE
    SYNTAX INTEGER (1..65535)
    ACCESS read-write
    STATUS mandatory
    DESCRIPTION
        "Port number of the syslog server to which the Webio device should send syslog messages."
    ::= { wtWebioAn1GraphNtcAlarmEntry 22 }

wtWebioAn1GraphNtcAlarmSyslogText OBJECT-TYPE
    SYNTAX OCTET STRING
    ACCESS read-write
    STATUS mandatory
    DESCRIPTION
        "Every message starts with the priority key, a time stamp and the host ip address, according RFC3164.
        This text appears in the following syslog message body."
    ::= { wtWebioAn1GraphNtcAlarmEntry 23 }

wtWebioAn1GraphNtcAlarmSyslogClearText OBJECT-TYPE
    SYNTAX OCTET STRING
    ACCESS read-write
    STATUS mandatory
    DESCRIPTION
        "Every message starts with the priority key, a time stamp and the host ip address, according RFC3164.
        This text appears in the following syslog message body."
    ::= { wtWebioAn1GraphNtcAlarmEntry 24 }

wtWebioAn1GraphNtcAlarmFtpDataPort OBJECT-TYPE
    SYNTAX OCTET STRING
    ACCESS read-write
    STATUS mandatory
    DESCRIPTION
        "Local data port: 1..65535 or AUTO: the next free port will be assigned."
    ::= { wtWebioAn1GraphNtcAlarmEntry 25 }

wtWebioAn1GraphNtcAlarmFtpFileName OBJECT-TYPE
    SYNTAX OCTET STRING
    ACCESS read-write
    STATUS mandatory
    DESCRIPTION
        "Name of the file including path informations."
    ::= { wtWebioAn1GraphNtcAlarmEntry 26 }

wtWebioAn1GraphNtcAlarmFtpText OBJECT-TYPE
    SYNTAX OCTET STRING
    ACCESS read-write
    STATUS mandatory
    DESCRIPTION
        "Message text to store on the FTP server."
    ::= { wtWebioAn1GraphNtcAlarmEntry 27 }

wtWebioAn1GraphNtcAlarmFtpClearText OBJECT-TYPE
    SYNTAX OCTET STRING
    ACCESS read-write
    STATUS mandatory
    DESCRIPTION
        "Alarm clear message to store on the FTP server."
    ::= { wtWebioAn1GraphNtcAlarmEntry 28 }

wtWebioAn1GraphNtcAlarmFtpOption OBJECT-TYPE
    SYNTAX OCTET STRING (SIZE(4))
    ACCESS read-write
    STATUS mandatory
    DESCRIPTION
        "Binary coded options, select only one option at the same time:
        STORE  = replace file
        APPEND = append message at the end of the file

        Octet 1: unused
        Octet 2: unused
        Octet 3: unused
        Octet 4:
		Bit 0  :	STORE
		Bit 1  :	APPEND
        	Bit 2-7:	unused"
    ::= { wtWebioAn1GraphNtcAlarmEntry 29 }

wtWebioAn1GraphNtcAlarmTimerCron OBJECT-TYPE
    SYNTAX OCTET STRING
    ACCESS read-write
    STATUS mandatory
    DESCRIPTION
        "This entry contains 5 text fields space or tab seperated for time trigger definition.
        Each field must match with the actual time to trigger a message, weekday and day of month
        are interpreted separately.
        1: Minutes	Range 0-59
        2. Hours	Range 0-23, 0 is midnight
        3: Day of month	Range 1-31
        4: Month	Range 1-12
        5: Weekday	Range 0-6, 0 is sunday

        Syntax for every field:
         - an asterix (*) enables every possible setting of a field
         - single numbers seperated by commas
         - a partition within the allowed range (1-5)
         - step size within an partition of the allowed range (0-59/2: every second minute)."
    ::= { wtWebioAn1GraphNtcAlarmEntry 30 }

wtWebioAn1GraphNtcAlarmDeltaTemp OBJECT-TYPE
    SYNTAX OCTET STRING
    ACCESS read-write
    STATUS mandatory
    DESCRIPTION
        "Maximum rate of change  degrees/min with maximum 2 decimal places.
        Compared with the average of a period of 5 minutes."
    ::= { wtWebioAn1GraphNtcAlarmEntry 31 }

-- __JB__
wtWebioAn1GraphNtcAlarmName OBJECT-TYPE
    SYNTAX OCTET STRING
    ACCESS read-write
    STATUS mandatory
    DESCRIPTION
        "Alert name"
    ::= { wtWebioAn1GraphNtcAlarmEntry 39 }

-- __JB__
wtWebioAn1GraphNtcAlarmActive OBJECT-TYPE
    SYNTAX OCTET STRING
    ACCESS read-write
    STATUS mandatory
    DESCRIPTION
        "Alert active
			1 = ON
			0 = OFF"
    ::= { wtWebioAn1GraphNtcAlarmEntry 40 }

wtWebioAn1GraphNtcAlarmHttpReqAuthEnable OBJECT-TYPE
    SYNTAX OCTET STRING
    ACCESS read-write
    STATUS mandatory
    DESCRIPTION
        "Binary coded options, select only one option at the same time:
        OCTET 1: unused
        OCTET 2: unused
        OCTET 3: unused
        OCTET 4, Bit 1-7: unused
        Bit 0  : HHTP Request Authentication enable"
    ::= { wtWebioAn1GraphNtcAlarmEntry 61 }

wtWebioAn1GraphNtcAlarmHttpReqAuthUser OBJECT-TYPE
    SYNTAX OCTET STRING
    ACCESS read-write
    STATUS mandatory
    DESCRIPTION
	"HTTP Request: User"
    ::= { wtWebioAn1GraphNtcAlarmEntry 62 }

wtWebioAn1GraphNtcAlarmHttpReqAuthPassword OBJECT-TYPE
    SYNTAX OCTET STRING
    ACCESS read-write
    STATUS mandatory
    DESCRIPTION
	"HTTP Request: Password"
    ::= { wtWebioAn1GraphNtcAlarmEntry 63 }

wtWebioAn1GraphNtcAlarmHttpReqSetUrl OBJECT-TYPE
    SYNTAX OCTET STRING
    ACCESS read-write
    STATUS mandatory
    DESCRIPTION
	"HTTP Request: Set URL"
    ::= { wtWebioAn1GraphNtcAlarmEntry 64 }

wtWebioAn1GraphNtcAlarmHttpReqClearUrl OBJECT-TYPE
    SYNTAX OCTET STRING
    ACCESS read-write
    STATUS mandatory
    DESCRIPTION
	"HTTP Request: Clear URL"
    ::= { wtWebioAn1GraphNtcAlarmEntry 65 }

wtWebioAn1GraphNtcAlarmHttpReqServerPort OBJECT-TYPE
    SYNTAX INTEGER (1..65535)
    ACCESS read-write
    STATUS mandatory
    DESCRIPTION
	"HTTP Request: Server Port"
    ::= { wtWebioAn1GraphNtcAlarmEntry 66 }

wtWebioAn1GraphNtcAlarmMqttTopicPath OBJECT-TYPE
    SYNTAX OCTET STRING
    ACCESS read-write
    STATUS mandatory
    DESCRIPTION
	"MQTT Publish: Topic path"
    ::= { wtWebioAn1GraphNtcAlarmEntry 67 }

wtWebioAn1GraphNtcAlarmMqttTopicSetTopic OBJECT-TYPE
    SYNTAX OCTET STRING
    ACCESS read-write
    STATUS mandatory
    DESCRIPTION
	"MQTT Publish: Topic SET message"
    ::= { wtWebioAn1GraphNtcAlarmEntry 68 }

wtWebioAn1GraphNtcAlarmMqttTopicClear OBJECT-TYPE
    SYNTAX OCTET STRING
    ACCESS read-write
    STATUS mandatory
    DESCRIPTION
	"MQTT Publish: Topic CLEAR message"
    ::= { wtWebioAn1GraphNtcAlarmEntry 69 }

wtWebioAn1GraphNtcAlarmSensorLostSelection OBJECT-TYPE
    SYNTAX OCTET STRING
    ACCESS read-write
    STATUS mandatory
    DESCRIPTION
        "Binary coded options:
        OCTET 1: unused
        OCTET 2: unused
        OCTET 3: unused
        OCTET 4, Bit 1-7: unused
        Bit 0  : Sensor 0"
    ::= { wtWebioAn1GraphNtcAlarmEntry 70 }

wtWebioAn1GraphNtcAlarmLimitWindow OBJECT-TYPE
    SYNTAX OCTET STRING
    ACCESS read-write
    STATUS mandatory
    DESCRIPTION
        "If window type is INSIDE the alarm is genereted when the temperature
        is greater minumum value and lower than maximum value. If window type is OUTSIDE
        the alarm is generated when the measured value is lower than the minimum value
        or greater than the maximum value.
		Binary coded options, select only one option at the same time:
        OCTET 1: unused
        OCTET 2: unused
        OCTET 3: unused
        OCTET 4, Bit 2-7: unused
		Bit 1  : inside window
        Bit 0  : outside window"
    ::= { wtWebioAn1GraphNtcAlarmEntry 71 }

-- wtWebioAn1GraphNtcGraphicsBase Group
----------------------------

wtWebioAn1GraphNtcGraphicsBaseEnable OBJECT-TYPE
    SYNTAX OCTET STRING
    ACCESS read-write
    STATUS mandatory
    DESCRIPTION
        "Defines the viewing options of the graphic:
        Octet 1: unused
        Octet 2: unused
        Octet 3: unused
        Octet 4:
                Bit 0  : Auto scroll enable
                Bit 1  : Show table
                Bit 2  : Show graph
                Bit 3  : Show control buttons
                Bit 4  : Show config menu
                Bit 5  : Show Logo
                Bit 6-7: unused"
    ::= { wtWebioAn1GraphNtcGraphicsBase 1 }

wtWebioAn1GraphNtcGraphicsBaseWidth OBJECT-TYPE
    SYNTAX INTEGER
    ACCESS read-write
    STATUS mandatory
    DESCRIPTION
        "Defines the width of the graphic in pixels."
    ::= { wtWebioAn1GraphNtcGraphicsBase 2 }

wtWebioAn1GraphNtcGraphicsBaseHeight OBJECT-TYPE
        SYNTAX INTEGER
        ACCESS read-write
        STATUS mandatory
        DESCRIPTION
            "Defines the height of the graphic in pixels."
        ::= { wtWebioAn1GraphNtcGraphicsBase 3 }

wtWebioAn1GraphNtcGraphicsBaseFrameColor OBJECT-TYPE
    SYNTAX OCTET STRING (SIZE(3))
    ACCESS read-write
    STATUS mandatory
    DESCRIPTION
        "Frame color definition in RGB."
    ::= { wtWebioAn1GraphNtcGraphicsBase 4 }

wtWebioAn1GraphNtcGraphicsBaseBackgroundColor OBJECT-TYPE
    SYNTAX OCTET STRING (SIZE(3))
    ACCESS read-write
    STATUS mandatory
    DESCRIPTION
        "Background color definition in RGB."
    ::= { wtWebioAn1GraphNtcGraphicsBase 5 }

wtWebioAn1GraphNtcGraphicsBasePollingrate OBJECT-TYPE
        SYNTAX INTEGER
        ACCESS read-write
        STATUS mandatory
        DESCRIPTION
            "Defines the pollingrate in seconds,
            which defines the refreshing intervall of the graphic."
        ::= { wtWebioAn1GraphNtcGraphicsBase 6 }

-- wtWebioAn1GraphNtcGraphicsSelect Group
----------------------------

wtWebioAn1GraphNtcGraphicsSelectDisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0  : Sensor 1
		Bit 1-7: unused"
    ::= { wtWebioAn1GraphNtcGraphicsSelect 1 }

wtWebioAn1GraphNtcGraphicsSelectDisplayShowExtrem OBJECT-TYPE
    SYNTAX OCTET STRING (SIZE(4))
    ACCESS read-write
    STATUS mandatory
    DESCRIPTION
        "Binary coded sensor selection:
        only selected sensors will be shown with minima and maxima:
        Octet 1: unused
        Octet 2: unused
        Octet 3: unused
        Octet 4:
        	Bit 0  : Sensor 1
		Bit 1-7: unused"
    ::= { wtWebioAn1GraphNtcGraphicsSelect 2 }

-- Graph Sensor Color Table

wtWebioAn1GraphNtc2SensorColorTable OBJECT-TYPE
    SYNTAX SEQUENCE OF WtWebioAn1GraphNtc2SensorColorEntry
    ACCESS not-accessible
    STATUS mandatory
    DESCRIPTION
        "List of sensor colors for the praphical presentation."
    ::= { wtWebioAn1GraphNtcGraphicsSelect 3 }

wtWebioAn1GraphNtc2SensorColorEntry OBJECT-TYPE
    SYNTAX WtWebioAn1GraphNtc2SensorColorEntry
    ACCESS not-accessible
    STATUS mandatory
    DESCRIPTION
        "Numbers of the sensors."
    INDEX  { wtWebioAn1GraphNtcSensorNo }
    ::= { wtWebioAn1GraphNtc2SensorColorTable 1 }

WtWebioAn1GraphNtc2SensorColorEntry ::= SEQUENCE {
    wtWebioAn1GraphNtcGraphicsSensorColor OCTET STRING,
    wtWebioAn1GraphNtcGraphicsSelectScale OCTET STRING
}

wtWebioAn1GraphNtcGraphicsSensorColor OBJECT-TYPE
    SYNTAX OCTET STRING (SIZE(3))
    ACCESS read-write
    STATUS mandatory
    DESCRIPTION
        "Color of the sensors at the praphical presention."
    ::= { wtWebioAn1GraphNtc2SensorColorEntry 1 }

wtWebioAn1GraphNtcGraphicsSelectScale OBJECT-TYPE
    SYNTAX OCTET STRING
    ACCESS read-write
    STATUS mandatory
    DESCRIPTION
        "Assignes one of 4 scales to a sensor:
        Octet 1: unused
        Octet 2: unused
        Octet 3: unused
        Octet 4:
                Bit 0  : Use Scale 1
                Bit 1-7: unused"
    ::= { wtWebioAn1GraphNtc2SensorColorEntry 2 }

-- wtWebioAn1GraphNtcGraphicsScale Group
----------------------------

wtWebioAn1GraphNtcGraphicsScaleAutoScaleEnable OBJECT-TYPE
    SYNTAX OCTET STRING
    ACCESS read-write
    STATUS mandatory
    DESCRIPTION
        "Select the Auto Scale Mode:
        Octet 1: unused
        Octet 2: unused
        Octet 3: unused
        Octet 4:
                Bit 0  : Scale 1 Auto scale enable
                Bit 1-7: unused"
    ::= { wtWebioAn1GraphNtcGraphicsScale 1 }

wtWebioAn1GraphNtcGraphicsScaleAutoFitEnable OBJECT-TYPE
    SYNTAX OCTET STRING
    ACCESS read-write
    STATUS mandatory
    DESCRIPTION
        "Select the Auto Fit Mode::
        Octet 1: unused
        Octet 2: unused
        Octet 3: unused
        Octet 4:
                Bit 0  : Scale 1 Auto fit enable
                Bit 1-7: unused"
    ::= { wtWebioAn1GraphNtcGraphicsScale 2 }

wtWebioAn1GraphNtcGraphicsScale1Min OBJECT-TYPE
    SYNTAX INTEGER
    ACCESS read-only
    STATUS mandatory
    DESCRIPTION
        "Scale 1: Minimum."
    ::= { wtWebioAn1GraphNtcGraphicsScale 3 }

wtWebioAn1GraphNtcGraphicsScale2Min OBJECT-TYPE
    SYNTAX INTEGER
    ACCESS read-only
    STATUS mandatory
    DESCRIPTION
        "Scale 2: Minimum."
    ::= { wtWebioAn1GraphNtcGraphicsScale 4 }

wtWebioAn1GraphNtcGraphicsScale3Min OBJECT-TYPE
    SYNTAX INTEGER
    ACCESS read-only
    STATUS mandatory
    DESCRIPTION
        "Scale 3: Minimum."
    ::= { wtWebioAn1GraphNtcGraphicsScale 5 }

wtWebioAn1GraphNtcGraphicsScale4Min OBJECT-TYPE
    SYNTAX INTEGER
    ACCESS read-only
    STATUS mandatory
    DESCRIPTION
        "Scale 4: Minimum."
    ::= { wtWebioAn1GraphNtcGraphicsScale 6 }

wtWebioAn1GraphNtcGraphicsScale1Max OBJECT-TYPE
    SYNTAX INTEGER
    ACCESS read-only
    STATUS mandatory
    DESCRIPTION
        "Scale 1: Maximum."
    ::= { wtWebioAn1GraphNtcGraphicsScale 7 }

wtWebioAn1GraphNtcGraphicsScale2Max OBJECT-TYPE
    SYNTAX INTEGER
    ACCESS read-only
    STATUS mandatory
    DESCRIPTION
        "Scale 2: Maximum."
    ::= { wtWebioAn1GraphNtcGraphicsScale 8 }

wtWebioAn1GraphNtcGraphicsScale3Max OBJECT-TYPE
    SYNTAX INTEGER
    ACCESS read-only
    STATUS mandatory
    DESCRIPTION
        "Scale 3: Maximum."
    ::= { wtWebioAn1GraphNtcGraphicsScale 9 }

wtWebioAn1GraphNtcGraphicsScale4Max OBJECT-TYPE
    SYNTAX INTEGER
    ACCESS read-only
    STATUS mandatory
    DESCRIPTION
        "Scale 4: Maximum."
    ::= { wtWebioAn1GraphNtcGraphicsScale 10 }

wtWebioAn1GraphNtcGraphicsScale1Unit OBJECT-TYPE
    SYNTAX OCTET STRING
    ACCESS read-only
    STATUS mandatory
    DESCRIPTION
        "Scale 1: Unit."
    ::= { wtWebioAn1GraphNtcGraphicsScale 11 }

wtWebioAn1GraphNtcGraphicsScale2Unit OBJECT-TYPE
    SYNTAX OCTET STRING
    ACCESS read-only
    STATUS mandatory
    DESCRIPTION
        "Scale 2: Unit."
    ::= { wtWebioAn1GraphNtcGraphicsScale 12 }

wtWebioAn1GraphNtcGraphicsScale3Unit OBJECT-TYPE
    SYNTAX OCTET STRING
    ACCESS read-only
    STATUS mandatory
    DESCRIPTION
        "Scale 3: Unit."
    ::= { wtWebioAn1GraphNtcGraphicsScale 13 }

wtWebioAn1GraphNtcGraphicsScale4Unit OBJECT-TYPE
    SYNTAX OCTET STRING
    ACCESS read-only
    STATUS mandatory
    DESCRIPTION
        "Scale 4: Unit."
    ::= { wtWebioAn1GraphNtcGraphicsScale 14 }

-- wtWebioAn1GraphNtcPorts Group
----------------------------

-- Table

wtWebioAn1GraphNtcPortTable OBJECT-TYPE
    SYNTAX SEQUENCE OF WtWebioAn1GraphNtcPortEntry
    ACCESS not-accessible
    STATUS mandatory
    DESCRIPTION
        "List of settings depending on the sensor number."
    ::= { wtWebioAn1GraphNtcPorts 1 }

wtWebioAn1GraphNtcPortEntry OBJECT-TYPE
    SYNTAX WtWebioAn1GraphNtcPortEntry
    ACCESS not-accessible
    STATUS mandatory
    DESCRIPTION
        "Sensor parameters for the individual sensors."
    INDEX  { wtWebioAn1GraphNtcSensorNo }
    ::= { wtWebioAn1GraphNtcPortTable 1 }

WtWebioAn1GraphNtcPortEntry ::= SEQUENCE {
    wtWebioAn1GraphNtcPortName		OCTET STRING,
    wtWebioAn1GraphNtcPortText		OCTET STRING,
    wtWebioAn1GraphNtcPortOffset1		OCTET STRING,
    wtWebioAn1GraphNtcPortTemperature1	OCTET STRING,
    wtWebioAn1GraphNtcPortOffset2		OCTET STRING,
    wtWebioAn1GraphNtcPortTemperature2	OCTET STRING,
    wtWebioAn1GraphNtcPortComment		OCTET STRING

}

wtWebioAn1GraphNtcPortName OBJECT-TYPE
    SYNTAX OCTET STRING
    ACCESS read-write
    STATUS mandatory
    DESCRIPTION
        "Name of the sensor."
    ::= { wtWebioAn1GraphNtcPortEntry 1 }

wtWebioAn1GraphNtcPortText OBJECT-TYPE
    SYNTAX OCTET STRING
    ACCESS read-write
    STATUS mandatory
    DESCRIPTION
        "Description of the sensor."
    ::= { wtWebioAn1GraphNtcPortEntry 2 }

wtWebioAn1GraphNtcPortOffset1 OBJECT-TYPE
    SYNTAX OCTET STRING
    ACCESS read-write
    STATUS mandatory
    DESCRIPTION
        "Offset calibration: Offset in degrees with maximum 2 decimal places at temperature 1."
    ::= { wtWebioAn1GraphNtcPortEntry 3 }

wtWebioAn1GraphNtcPortTemperature1 OBJECT-TYPE
    SYNTAX OCTET STRING
    ACCESS read-write
    STATUS mandatory
    DESCRIPTION
        "Offset calibration: Reference temperature 1 in degrees with maximum 2 decimal places."
    ::= { wtWebioAn1GraphNtcPortEntry 4 }

wtWebioAn1GraphNtcPortOffset2 OBJECT-TYPE
    SYNTAX OCTET STRING
    ACCESS read-write
    STATUS mandatory
    DESCRIPTION
        "Offset calibration: Offset in degrees with maximum 2 decimal places at temperature 2."
    ::= { wtWebioAn1GraphNtcPortEntry 5 }

wtWebioAn1GraphNtcPortTemperature2 OBJECT-TYPE
    SYNTAX OCTET STRING
    ACCESS read-write
    STATUS mandatory
    DESCRIPTION
        "Offset calibration: Reference temperature 1 in degrees with maximum 2 decimal places."
    ::= { wtWebioAn1GraphNtcPortEntry 6 }

wtWebioAn1GraphNtcPortComment OBJECT-TYPE
    SYNTAX OCTET STRING
    ACCESS read-write
    STATUS mandatory
    DESCRIPTION
        "Offset calibration: informations of date, name of operator, reference devices."
    ::= { wtWebioAn1GraphNtcPortEntry 7 }

-- wtWebioAn1GraphNtcManufact Group
----------------------------

wtWebioAn1GraphNtcMfName OBJECT-TYPE
    SYNTAX OCTET STRING
    ACCESS read-write
    STATUS mandatory
    DESCRIPTION
        "Manufacturer company name"
    ::= { wtWebioAn1GraphNtcManufact 1 }

wtWebioAn1GraphNtcMfAddr OBJECT-TYPE
    SYNTAX OCTET STRING
    ACCESS read-write
    STATUS mandatory
    DESCRIPTION
        "Manufacturer address."
    ::= { wtWebioAn1GraphNtcManufact 2 }

wtWebioAn1GraphNtcMfHotline OBJECT-TYPE
    SYNTAX OCTET STRING
    ACCESS read-write
    STATUS mandatory
    DESCRIPTION
        "Manufacturer hotline."
    ::= { wtWebioAn1GraphNtcManufact 3 }

wtWebioAn1GraphNtcMfInternet OBJECT-TYPE
    SYNTAX OCTET STRING
    ACCESS read-write
    STATUS mandatory
    DESCRIPTION
        "Manufacturer Internet address."
    ::= { wtWebioAn1GraphNtcManufact 4 }

wtWebioAn1GraphNtcMfDeviceTyp OBJECT-TYPE
    SYNTAX OCTET STRING
    ACCESS read-write
    STATUS mandatory
    DESCRIPTION
        "Manufacturer device name (model number)."
    ::= { wtWebioAn1GraphNtcManufact 5 }

wtWebioAn1GraphNtcMfOrderNo OBJECT-TYPE
    SYNTAX OCTET STRING
    ACCESS read-write
    STATUS mandatory
    DESCRIPTION
        "Manufacturer part number."
    ::= { wtWebioAn1GraphNtcManufact 6 }

-- wtWebioAn1GraphNtcDiag Group
----------------------------

wtWebioAn1GraphNtcDiagErrorCount OBJECT-TYPE
    SYNTAX INTEGER
    ACCESS read-only
    STATUS mandatory
    DESCRIPTION
        "Number of entries in the error memory."
    ::= { wtWebioAn1GraphNtcDiag 1 }

wtWebioAn1GraphNtcDiagBinaryError OBJECT-TYPE
    SYNTAX OCTET STRING
    ACCESS read-only
    STATUS mandatory
    DESCRIPTION
        "Error causes coded bit-by-bit."
    ::= { wtWebioAn1GraphNtcDiag 2 }

wtWebioAn1GraphNtcDiagErrorIndex OBJECT-TYPE
    SYNTAX INTEGER
    ACCESS read-write
    STATUS mandatory
    DESCRIPTION
        "The value of this variable is used as an index to read
        an error massege from wtWebioAn1GraphNtcDiagErrorMessage.
        Errors are numbered from 1 to wtWebioAn1GraphNtcDiagErrorCount.
        Writing a valid value into this variable, making the appropriate
        message readable from wtWebioAn1GraphNtcDiagErrorMessage."
    ::= { wtWebioAn1GraphNtcDiag 3 }

wtWebioAn1GraphNtcDiagErrorMessage OBJECT-TYPE
    SYNTAX OCTET STRING
    ACCESS read-only
    STATUS mandatory
    DESCRIPTION
        "Using wtWebioAn1GraphNtcDiagErrorIndex as an index, the appropriate message is available."
    ::= { wtWebioAn1GraphNtcDiag 4 }

wtWebioAn1GraphNtcDiagErrorClear OBJECT-TYPE
    SYNTAX INTEGER
    ACCESS write-only
    STATUS mandatory
    DESCRIPTION
        "Writing 1 into this variable clears all diagnosis messages."
    ::= { wtWebioAn1GraphNtcDiag 5 }

-- TRAP DEFINITIONS

-- Diese SNMP-Traps werden gesendet, wenn die Alarmtriggerbedingungen zutreffen

wtWebioAn1GraphNtcAlert1 TRAP-TYPE
    ENTERPRISE  wtWebioAn1GraphNtc
    VARIABLES   { wtWebioAn1GraphNtcAlarmTrapText }
    DESCRIPTION
        "This SNMP trap is generated when Alarm 1 was triggered,
        SNMP trap enable is set and
        SNMP is enabled."
    -- NMS trap annotation
    --#TYPE "Web-Thermograph Alarm 1"
    --#SUMMARY "Alarm 1: %s"
    --#ARGUMENTS {0}
    --#SEVERITY INFORMATIONAL
    --#TIMEINDEX 99
    --#STATE OPERATIONAL
    ::= 31

wtWebioAn1GraphNtcAlert2 TRAP-TYPE
    ENTERPRISE  wtWebioAn1GraphNtc
    VARIABLES   { wtWebioAn1GraphNtcAlarmTrapText }
    DESCRIPTION
        "This SNMP trap is generated when Alarm 2 was triggered,
        SNMP trap enable is set and
        SNMP is enabled."
    -- NMS trap annotation
    --#TYPE "Web-Thermograph Alarm 2"
    --#SUMMARY "Alarm 2: %s"
    --#ARGUMENTS {0}
    --#SEVERITY INFORMATIONAL
    --#TIMEINDEX 99
    --#STATE OPERATIONAL
    ::= 32

wtWebioAn1GraphNtcAlert3 TRAP-TYPE
    ENTERPRISE  wtWebioAn1GraphNtc
    VARIABLES   { wtWebioAn1GraphNtcAlarmTrapText }
    DESCRIPTION
        "This SNMP trap is generated when Alarm 3 was triggered,
        SNMP trap enable is set and
        SNMP is enabled."
    -- NMS trap annotation
    --#TYPE "Web-Thermograph Alarm 3"
    --#SUMMARY "Alarm 3: %s"
    --#ARGUMENTS {0}
    --#SEVERITY INFORMATIONAL
    --#TIMEINDEX 99
    --#STATE OPERATIONAL
    ::= 33

wtWebioAn1GraphNtcAlert4 TRAP-TYPE
    ENTERPRISE  wtWebioAn1GraphNtc
    VARIABLES   { wtWebioAn1GraphNtcAlarmTrapText }
    DESCRIPTION
        "This SNMP trap is generated when Alarm 4 was triggered,
        SNMP trap enable is set and
        SNMP is enabled."
    -- NMS trap annotation
    --#TYPE "Web-Thermograph Alarm 4"
    --#SUMMARY "Alarm 4: %s"
    --#ARGUMENTS {0}
    --#SEVERITY INFORMATIONAL
    --#TIMEINDEX 99
    --#STATE OPERATIONAL
    ::= 34

wtWebioAn1GraphNtcAlert5 TRAP-TYPE
    ENTERPRISE  wtWebioAn1GraphNtc
    VARIABLES   { wtWebioAn1GraphNtcAlarmTrapText }
    DESCRIPTION
        "This SNMP trap is generated when Alarm 5 was triggered,
        SNMP trap enable is set and
        SNMP is enabled."
    -- NMS trap annotation
    --#TYPE "Web-Thermograph Alarm 5"
    --#SUMMARY "Alarm 5: %s"
    --#ARGUMENTS {0}
    --#SEVERITY INFORMATIONAL
    --#TIMEINDEX 99
    --#STATE OPERATIONAL
    ::= 35

wtWebioAn1GraphNtcAlert6 TRAP-TYPE
    ENTERPRISE  wtWebioAn1GraphNtc
    VARIABLES   { wtWebioAn1GraphNtcAlarmTrapText }
    DESCRIPTION
        "This SNMP trap is generated when Alarm 6 was triggered,
        SNMP trap enable is set and
        SNMP is enabled."
    -- NMS trap annotation
    --#TYPE "Web-Thermograph Alarm 6"
    --#SUMMARY "Alarm 6: %s"
    --#ARGUMENTS {0}
    --#SEVERITY INFORMATIONAL
    --#TIMEINDEX 99
    --#STATE OPERATIONAL
    ::= 36

wtWebioAn1GraphNtcAlert7 TRAP-TYPE
    ENTERPRISE  wtWebioAn1GraphNtc
    VARIABLES   { wtWebioAn1GraphNtcAlarmTrapText }
    DESCRIPTION
        "This SNMP trap is generated when Alarm 7 was triggered,
        SNMP trap enable is set and
        SNMP is enabled."
    -- NMS trap annotation
    --#TYPE "Web-Thermograph Alarm 7"
    --#SUMMARY "Alarm 7: %s"
    --#ARGUMENTS {0}
    --#SEVERITY INFORMATIONAL
    --#TIMEINDEX 99
    --#STATE OPERATIONAL
    ::= 37

wtWebioAn1GraphNtcAlert8 TRAP-TYPE
    ENTERPRISE  wtWebioAn1GraphNtc
    VARIABLES   { wtWebioAn1GraphNtcAlarmTrapText }
    DESCRIPTION
        "This SNMP trap is generated when Alarm 8 was triggered,
        SNMP trap enable is set and
        SNMP is enabled."
    -- NMS trap annotation
    --#TYPE "Web-Thermograph Alarm 8"
    --#SUMMARY "Alarm 8: %s"
    --#ARGUMENTS {0}
    --#SEVERITY INFORMATIONAL
    --#TIMEINDEX 99
    --#STATE OPERATIONAL
    ::= 38


wtWebioAn1GraphNtcAlert9 TRAP-TYPE
    ENTERPRISE  wtWebioAn1GraphNtc
    VARIABLES   { wtWebioAn1GraphNtcAlarmClearTrapText }
    DESCRIPTION
        "This SNMP trap is generated when Alarm 1 was cleared,
        SNMP trap enable is set and
        SNMP is enabled."
    -- NMS trap annotation
    --#TYPE "Web-Thermograph Release Alarm 1"
    --#SUMMARY "Release Alarm 1: %s"
    --#ARGUMENTS {0}
    --#SEVERITY INFORMATIONAL
    --#TIMEINDEX 99
    --#STATE OPERATIONAL
    ::= 91

wtWebioAn1GraphNtcAlert10 TRAP-TYPE
    ENTERPRISE  wtWebioAn1GraphNtc
    VARIABLES   { wtWebioAn1GraphNtcAlarmClearTrapText }
    DESCRIPTION
        "This SNMP trap is generated when Alarm 2 was cleared,
        SNMP trap enable is set and
        SNMP is enabled."
    -- NMS trap annotation
    --#TYPE "Web-Thermograph Release Alarm 2"
    --#SUMMARY "Release Alarm 2: %s"
    --#ARGUMENTS {0}
    --#SEVERITY INFORMATIONAL
    --#TIMEINDEX 99
    --#STATE OPERATIONAL
    ::= 92

wtWebioAn1GraphNtcAlert11 TRAP-TYPE
    ENTERPRISE  wtWebioAn1GraphNtc
    VARIABLES   { wtWebioAn1GraphNtcAlarmClearTrapText }
    DESCRIPTION
        "This SNMP trap is generated when Alarm 3 was cleared,
        SNMP trap enable is set and
        SNMP is enabled."
    -- NMS trap annotation
    --#TYPE "Web-Thermograph Release Alarm 3"
    --#SUMMARY "Release Alarm 3: %s"
    --#ARGUMENTS {0}
    --#SEVERITY INFORMATIONAL
    --#TIMEINDEX 99
    --#STATE OPERATIONAL
    ::= 93

wtWebioAn1GraphNtcAlert12 TRAP-TYPE
    ENTERPRISE  wtWebioAn1GraphNtc
    VARIABLES   { wtWebioAn1GraphNtcAlarmClearTrapText }
    DESCRIPTION
        "This SNMP trap is generated when Alarm 4 was cleared,
        SNMP trap enable is set and
        SNMP is enabled."
    -- NMS trap annotation
    --#TYPE "Web-Thermograph Release Alarm 4"
    --#SUMMARY "Release Alarm 4: %s"
    --#ARGUMENTS {0}
    --#SEVERITY INFORMATIONAL
    --#TIMEINDEX 99
    --#STATE OPERATIONAL
    ::= 94

wtWebioAn1GraphNtcAlert13 TRAP-TYPE
    ENTERPRISE  wtWebioAn1GraphNtc
    VARIABLES   { wtWebioAn1GraphNtcAlarmClearTrapText }
    DESCRIPTION
        "This SNMP trap is generated when Alarm 5 was cleared,
        SNMP trap enable is set and
        SNMP is enabled."
    -- NMS trap annotation
    --#TYPE "Web-Thermograph Release Alarm 5"
    --#SUMMARY "Release Alarm 5: %s"
    --#ARGUMENTS {0}
    --#SEVERITY INFORMATIONAL
    --#TIMEINDEX 99
    --#STATE OPERATIONAL
    ::= 95

wtWebioAn1GraphNtcAlert14 TRAP-TYPE
    ENTERPRISE  wtWebioAn1GraphNtc
    VARIABLES   { wtWebioAn1GraphNtcAlarmClearTrapText }
    DESCRIPTION
        "This SNMP trap is generated when Alarm 6 was cleared,
        SNMP trap enable is set and
        SNMP is enabled."
    -- NMS trap annotation
    --#TYPE "Web-Thermograph Release Alarm 6"
    --#SUMMARY "Release Alarm 6: %s"
    --#ARGUMENTS {0}
    --#SEVERITY INFORMATIONAL
    --#TIMEINDEX 99
    --#STATE OPERATIONAL
    ::= 96

wtWebioAn1GraphNtcAlert15 TRAP-TYPE
    ENTERPRISE  wtWebioAn1GraphNtc
    VARIABLES   { wtWebioAn1GraphNtcAlarmClearTrapText }
    DESCRIPTION
        "This SNMP trap is generated when Alarm 7 was cleared,
        SNMP trap enable is set and
        SNMP is enabled."
    -- NMS trap annotation
    --#TYPE "Web-Thermograph Release Alarm 7"
    --#SUMMARY "Release Alarm 7: %s"
    --#ARGUMENTS {0}
    --#SEVERITY INFORMATIONAL
    --#TIMEINDEX 99
    --#STATE OPERATIONAL
    ::= 97

wtWebioAn1GraphNtcAlert16 TRAP-TYPE
    ENTERPRISE  wtWebioAn1GraphNtc
    VARIABLES   { wtWebioAn1GraphNtcAlarmClearTrapText }
    DESCRIPTION
        "This SNMP trap is generated when Alarm 8 was cleared,
        SNMP trap enable is set and
        SNMP is enabled."
    -- NMS trap annotation
    --#TYPE "Web-Thermograph Release Alarm 8"
    --#SUMMARY "Release Alarm 8: %s"
    --#ARGUMENTS {0}
    --#SEVERITY INFORMATIONAL
    --#TIMEINDEX 99
    --#STATE OPERATIONAL
    ::= 98

wtWebioAn1GraphNtcAlertDiag TRAP-TYPE
    ENTERPRISE  wtWebioAn1GraphNtc
    VARIABLES   {
    		wtWebioAn1GraphNtcDiagErrorIndex,
    	  	wtWebioAn1GraphNtcDiagErrorMessage
    		}
    DESCRIPTION
        "This SNMP trap is generated when a diagnosis/error message was triggered,
        SNMP trap enable is set and
        SNMP is enabled."
    -- NMS trap annotation
    --#TYPE "Web-Thermograph Diagnose Error"
    --#SUMMARY "Diagnose error index: %d, Message: %s."
    --#ARGUMENTS {0,1}
    --#SEVERITY MAJOR
    --#TIMEINDEX 99
    --#STATE DEGRADED
    ::= 110

END
