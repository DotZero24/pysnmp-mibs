WebGraph-AnalogIO-57761-US-MIB DEFINITIONS ::= BEGIN
----------------------------------------------------------------
-- Revison: 1.31
----------------------------------------------------------------
-- 27.03.2018 	New: Mail Auth, SNMP destination port
--		     Binary HttpPort, time base report
--		     MQTT, REST
----------------------------------------------------------------
-- Revison: 1.30
----------------------------------------------------------------
-- 08.01.2010 	New: Reports
--
----------------------------------------------------------------
-- Revison: 1.29
----------------------------------------------------------------
-- 01.10.2009 	Webio
--		New Analog Out: 57761
----------------------------------------------------------------
-- Revison: 1.28
----------------------------------------------------------------
-- 02.12.2008 	Webio
--		New Graphics java script base parameter
----------------------------------------------------------------
-- Revison: 1.27
----------------------------------------------------------------
-- 09.11.2006 	Webio
--		DHCP enable
----------------------------------------------------------------
-- Revison: 1.26
----------------------------------------------------------------
-- 28.06.2006 	New: Community String Trap
--
----------------------------------------------------------------
-- Revison: 1.25
----------------------------------------------------------------
-- 25.11.2005 	#57641, WebGraph AnalogIn
--		OID correction
----------------------------------------------------------------
-- Revison: 1.24
----------------------------------------------------------------
-- 26.07.2005 	#57641, WebGraph AnalogIn
--		CRON timer function
----------------------------------------------------------------
-- Revison: 1.23
----------------------------------------------------------------
-- 14.07.2005 	#57641, WebGraph AnalogIn
--		FTP functions
----------------------------------------------------------------
-- Revison: 1.22
----------------------------------------------------------------
-- 17.05.2005 	#57641, WebGraph AnalogIn
--		Trap NMS annotations
----------------------------------------------------------------
-- Revison: 1.21
----------------------------------------------------------------
-- 19.04.2005 	#57605, WebGraph Themometer
--		Mail Authentication
----------------------------------------------------------------
-- Revison: 1.20
----------------------------------------------------------------
-- 05.11.2004 	#57606, WebGraph Thermo-Hygrometer
--		New: Syslog
--
----------------------------------------------------------------
-- Revison: 1.19
----------------------------------------------------------------
-- 08.09.2004 	#57606 WebGraph Thermo-Hygrometer
--		New:
--			wtWebGraphThermHygroAlarmRHMin
--			wtWebGraphThermHygroAlarmRHMax
--			wtWebGraphThermHygroAlarmRHHysteresis
--			wtWebGraphThermHygroPortSensorSelect
--			wtWebGraphThermHygroAlarmDeltaTemp
--			wtWebGraphThermHygroAlarmAHMin
--			wtWebGraphThermHygroAlarmAHMax
----------------------------------------------------------------
-- Revison: 1.18
----------------------------------------------------------------
-- 21.07.2004 	#57601/3/4, Webio Anx
--		New:
--		     Diagnosis
----------------------------------------------------------------
-- Revison: 1.17
----------------------------------------------------------------
-- 28.06.2004 	#57630/1/2, Webio Digital
--		Neu: Puls Mode
----------------------------------------------------------------
-- Revison: 1.16
----------------------------------------------------------------
-- 16.04.2004 	New: #57632, Webio Digital EA24x24
--
--		#57630/1, Webio Digital EA12x12
--		New:
--			wtWebioEA12x12InputCounterClear
----------------------------------------------------------------
-- Revison: 1.15
----------------------------------------------------------------
-- 27.02.2004 	#57630/1, Webio Digital EA12x12
--		New:
--		Length changed to 32 Bit:
--			wtWebioEA12x12InputValue
--			wtWebioEA12x12OutputValue
--			wtWebioEA12x12LoadControlView
--			wtWebioEA12x12LCShutDownView
--			wtWebioEA12x12SetOutput
--			wtWebioEA12x12AlarmInputTrigger
--			wtWebioEA12x12AlarmOutputTrigger
--			wtWebioEA12x12PortOutputSafetyState
----------------------------------------------------------------
-- Revison: 1.14
----------------------------------------------------------------
-- 16.02.2004 	#57630/1, Webio Digital EA12x12
--		New:
--		Text: Location, Contact
--		SNMP: ColdStart, WarmStart, ComunityString Read/RW
--		Alarm: ColdStart / WarmStart trigger
--
-- 	 	#57601, 1xWebThermometer
--		#57603, 2xWebThermometer
--		#57604, 8xWebThermometer
--		New:
--		Alarm Hysteresis
--		Alarm Clear Traps and Mails
----------------------------------------------------------------
-- Revison: 1.13
----------------------------------------------------------------
-- 05.02.2004 	#57601, 1xWebThermometer
--		#57603, 2xWebThermometer
--		#57604, 8xWebThermometer
--		New:
--		Text: Location, Contact
--		SNMP: ColdStart, WarmStart, ComunityString Read/RW
--		Alarm: ColdStart / WarmStart trigger
----------------------------------------------------------------
-- Revison: 1.12
----------------------------------------------------------------
-- 05.11.2003 	#57601, 1xWebThermometer
--		#57603, 2xWebThermometer
--		#57604, 8xWebThermometer
--		New features:
--		Mail  : Option CSV attachment
--		Port  : Offset calibration
--		Alarm : TCP Client mode
----------------------------------------------------------------
-- Revison: 1.11
----------------------------------------------------------------
-- 28.10.2003 	#57630/1, Webio Digital EA12x12
--		New features:
--		Alarm : TCP Client mode
--		Inputs: Puls filter
----------------------------------------------------------------
-- Revison: 1.10
----------------------------------------------------------------
-- 22.07.2003 	#57630, Webio Digital EA12x12
--		New navigation tree, new binary modes
--
----------------------------------------------------------------
-- Revison: 1.09
----------------------------------------------------------------
-- 24.03.2003 	Trap Enterprise (Type 1, 2) corrected
----------------------------------------------------------------
-- Revison: 1.08
----------------------------------------------------------------
-- 04.03.2003 	reconciled the language versions DE/US
----------------------------------------------------------------
-- Revison: 1.07
----------------------------------------------------------------
-- 25.02.2003 	Correction: wtWebioEA12x12LoadControl
----------------------------------------------------------------
-- Revison: 1.06
----------------------------------------------------------------
-- 24.02.2003 	New:
--		#57630, Webio EA12x12, LoadControl Group
--		Correction: Trap variable names
----------------------------------------------------------------
-- Revison: 1.05
----------------------------------------------------------------
-- 21.01.2003 	New:
--		#57630, Webio EA12x12
----------------------------------------------------------------
-- Revison: 1.04
----------------------------------------------------------------
-- 02.01.2003 	New:
--		#57601, 1xWebThermometer
--		#57603, 2xWebThermometer, 8 alarms
----------------------------------------------------------------
-- Revison: 1.03
----------------------------------------------------------------
-- 21.11.2002 	New:
--		#57604, 2xWebThermometer, BOOTP, StartupSite
--		#57603, 8xWebThermometer, BOOTP, StartupSite
----------------------------------------------------------------
-- Revison: 1.02
----------------------------------------------------------------
-- 26.07.2002 	New:
--		#57604, 2xWebThermometer
--		#57603, 8xWebThermometer
--


    IMPORTS

    OBJECT-TYPE                                        FROM RFC-1212
    TRAP-TYPE                                          FROM RFC-1215
    DisplayString, PhysAddress                         FROM RFC1213-MIB
    enterprises, TimeTicks, IpAddress, NetworkAddress  FROM RFC1155-SMI;


--    IpAddress ::=
--        [APPLICATION 0]
--            IMPLICIT OCTET STRING (SIZE (4))
--    Counter ::=
--        [APPLICATION 1]
--            IMPLICIT INTEGER (0..4294967295)
--    Gauge ::=
--        [APPLICATION 2]
--            IMPLICIT INTEGER (0..4294967295)
--    TimeTicks ::=
--        [APPLICATION 3]
--            IMPLICIT INTEGER (0..4294967295)


--    DisplayString ::= OCTET STRING
--    PhysAddress   ::= OCTET STRING

--    internet         OBJECT IDENTIFIER ::= { iso org(3) dod(6) 1 }
--    privat           OBJECT IDENTIFIER ::= { internet 4 }
--    enterprises      OBJECT IDENTIFIER ::= { privat 1 }



--  Wiesemann & Theis Com-Server MIB

    wut                				OBJECT IDENTIFIER ::= { enterprises 5040 }
    wtComServer        				OBJECT IDENTIFIER ::= { wut 1 }
    wtWebio            				OBJECT IDENTIFIER ::= { wtComServer 2 }

--  wtWebGraph Tree

    wtWebGraphAnalog57761  			OBJECT IDENTIFIER ::= { wtWebio 28 }

--  wtWebGraphAnalog57761 Tree

    wtWebGraphAnalog57761Inventory   		OBJECT IDENTIFIER ::= { wtWebGraphAnalog57761 1 }
    wtWebGraphAnalog57761SessCntrl 		OBJECT IDENTIFIER ::= { wtWebGraphAnalog57761 2 }
    wtWebGraphAnalog57761Config    		OBJECT IDENTIFIER ::= { wtWebGraphAnalog57761 3 }
    wtWebGraphAnalog57761Diag    		OBJECT IDENTIFIER ::= { wtWebGraphAnalog57761 4 }

--  wtWebGraphAnalog57761Config Tree

    wtWebGraphAnalog57761Device    		OBJECT IDENTIFIER ::= { wtWebGraphAnalog57761Config 1 }
    wtWebGraphAnalog57761Ports     		OBJECT IDENTIFIER ::= { wtWebGraphAnalog57761Config 2 }
    wtWebGraphAnalog57761Manufact  		OBJECT IDENTIFIER ::= { wtWebGraphAnalog57761Config 3 }

--  wtWebGraphAnalog57761Device Tree

    wtWebGraphAnalog57761Text			OBJECT IDENTIFIER ::= { wtWebGraphAnalog57761Device 1 }
    wtWebGraphAnalog57761TimeDate 		OBJECT IDENTIFIER ::= { wtWebGraphAnalog57761Device 2 }
    wtWebGraphAnalog57761Basic			OBJECT IDENTIFIER ::= { wtWebGraphAnalog57761Device 3 }
    wtWebGraphAnalog57761Datalogger		OBJECT IDENTIFIER ::= { wtWebGraphAnalog57761Device 4 }
    wtWebGraphAnalog57761Alarm			OBJECT IDENTIFIER ::= { wtWebGraphAnalog57761Device 5 }
    wtWebGraphAnalog57761Graphics 		OBJECT IDENTIFIER ::= { wtWebGraphAnalog57761Device 6 }

--  wtWebGraphAnalog57761TimeDate Tree

    wtWebGraphAnalog57761TimeZone		OBJECT IDENTIFIER ::= { wtWebGraphAnalog57761TimeDate 1 }
    wtWebGraphAnalog57761TimeServer		OBJECT IDENTIFIER ::= { wtWebGraphAnalog57761TimeDate 2 }
    wtWebGraphAnalog57761DeviceClock		OBJECT IDENTIFIER ::= { wtWebGraphAnalog57761TimeDate 3 }

--  wtWebGraphAnalog57761Basic Tree

    wtWebGraphAnalog57761Network		OBJECT IDENTIFIER ::= { wtWebGraphAnalog57761Basic 1 }
    wtWebGraphAnalog57761HTTP			OBJECT IDENTIFIER ::= { wtWebGraphAnalog57761Basic 2 }
    wtWebGraphAnalog57761Mail			OBJECT IDENTIFIER ::= { wtWebGraphAnalog57761Basic 3 }
    wtWebGraphAnalog57761SNMP			OBJECT IDENTIFIER ::= { wtWebGraphAnalog57761Basic 4 }
    wtWebGraphAnalog57761UDP			OBJECT IDENTIFIER ::= { wtWebGraphAnalog57761Basic 5 }
    wtWebGraphAnalog57761Syslog			OBJECT IDENTIFIER ::= { wtWebGraphAnalog57761Basic 6 }
    wtWebGraphAnalog57761FTP			OBJECT IDENTIFIER ::= { wtWebGraphAnalog57761Basic 7 }
    wtWebGraphAnalog57761Language		OBJECT IDENTIFIER ::= { wtWebGraphAnalog57761Basic 8 }
    wtWebGraphAnalog57761Binary			OBJECT IDENTIFIER ::= { wtWebGraphAnalog57761Basic 9 }
    wtWebGraphAnalog57761MQTT			OBJECT IDENTIFIER ::= { wtWebGraphAnalog57761Basic 12 }
    wtWebGraphAnalog57761REST			OBJECT IDENTIFIER ::= { wtWebGraphAnalog57761Basic 13 }

--  wtWebGraphAnalog57761Graphics Tree

    wtWebGraphAnalog57761GraphicsBase 		OBJECT IDENTIFIER ::= { wtWebGraphAnalog57761Graphics 1 }
    wtWebGraphAnalog57761GraphicsSelect 	OBJECT IDENTIFIER ::= { wtWebGraphAnalog57761Graphics 2 }
    wtWebGraphAnalog57761GraphicsScale 		OBJECT IDENTIFIER ::= { wtWebGraphAnalog57761Graphics 3 }

-- wtWebGraphAnalog57761Inventory Group
------------------------

wtWebGraphAnalog57761Sensors OBJECT-TYPE
    SYNTAX INTEGER (1..2)
    ACCESS read-only
    STATUS mandatory
    DESCRIPTION
        "Number of sensors"
    ::= { wtWebGraphAnalog57761Inventory 1 }

-- Interface Table

wtWebGraphAnalog57761SensorTable OBJECT-TYPE
    SYNTAX SEQUENCE OF WtWebGraphAnalog57761SensorEntry
    ACCESS not-accessible
    STATUS mandatory
    DESCRIPTION
        "List of sensors."
    ::= { wtWebGraphAnalog57761Inventory 2 }

wtWebGraphAnalog57761SensorEntry OBJECT-TYPE
    SYNTAX WtWebGraphAnalog57761SensorEntry
    ACCESS not-accessible
    STATUS mandatory
    DESCRIPTION
        "List of sensor numbers."
    INDEX  { wtWebGraphAnalog57761SensorNo }
    ::= { wtWebGraphAnalog57761SensorTable 1 }

WtWebGraphAnalog57761SensorEntry ::= SEQUENCE {
    wtWebGraphAnalog57761SensorNo INTEGER
}

wtWebGraphAnalog57761SensorNo OBJECT-TYPE
    SYNTAX INTEGER (1..2)
    ACCESS read-only
    STATUS mandatory
    DESCRIPTION
        "Sensor number."
    ::= { wtWebGraphAnalog57761SensorEntry 1 }

    -- wtWebGraphAnalog57761Values Table

wtWebGraphAnalog57761ValuesTable OBJECT-TYPE
    SYNTAX SEQUENCE OF WtWebGraphAnalog57761ValuesEntry
    ACCESS not-accessible
    STATUS mandatory
    DESCRIPTION
        "List of measurement values corresponding to the channel numbers."
    ::= { wtWebGraphAnalog57761Inventory 3 }

wtWebGraphAnalog57761ValuesEntry OBJECT-TYPE
    SYNTAX WtWebGraphAnalog57761ValuesEntry
    ACCESS not-accessible
    STATUS mandatory
    DESCRIPTION
        "Measurement values of the sensors."
    INDEX  { wtWebGraphAnalog57761SensorNo }
    ::= { wtWebGraphAnalog57761ValuesTable 1 }

WtWebGraphAnalog57761ValuesEntry ::= SEQUENCE{
    wtWebGraphAnalog57761Values OCTET STRING
}

wtWebGraphAnalog57761Values OBJECT-TYPE
    SYNTAX OCTET STRING (SIZE (5))
    ACCESS read-write
    STATUS mandatory
    DESCRIPTION
        "Measurement value of the sensor, ASCII.
        This value will be translated according to the ports settings
        for the read and write operations."
    ::= { wtWebGraphAnalog57761ValuesEntry 1 }

-- wtWebGraphAnalog57761BinaryValues Table

wtWebGraphAnalog57761BinaryValuesTable OBJECT-TYPE
    SYNTAX SEQUENCE OF WtWebGraphAnalog57761BinaryValuesEntry
    ACCESS not-accessible
    STATUS mandatory
    DESCRIPTION
        "List of binary measurement values corresponding to the channel numbers."
    ::= { wtWebGraphAnalog57761Inventory 4 }

wtWebGraphAnalog57761BinaryValuesEntry OBJECT-TYPE
    SYNTAX WtWebGraphAnalog57761BinaryValuesEntry
    ACCESS not-accessible
    STATUS mandatory
    DESCRIPTION
        "Binary measurement values of the sensors."
    INDEX  { wtWebGraphAnalog57761SensorNo }
    ::= { wtWebGraphAnalog57761BinaryValuesTable 1 }

WtWebGraphAnalog57761BinaryValuesEntry ::= SEQUENCE{
    wtWebGraphAnalog57761BinaryValues INTEGER
}

wtWebGraphAnalog57761BinaryValues OBJECT-TYPE
    SYNTAX INTEGER
    ACCESS read-write
    STATUS mandatory
    DESCRIPTION
        "Binary measurement value of the sensor in 1/1000,
        signed number, 0x7FFFFFFF indicates an invalid value.
        This value will be translated according to the ports settings
        for the read and write operations."
    ::= { wtWebGraphAnalog57761BinaryValuesEntry 1 }

-- wtWebGraphAnalog57761ValuesPoint Table

wtWebGraphAnalog57761ValuesPointTable OBJECT-TYPE
    SYNTAX SEQUENCE OF WtWebGraphAnalog57761ValuesPointEntry
    ACCESS not-accessible
    STATUS mandatory
    DESCRIPTION
        "List of measurement values corresponding to the channel numbers."
    ::= { wtWebGraphAnalog57761Inventory 8 }

wtWebGraphAnalog57761ValuesPointEntry OBJECT-TYPE
    SYNTAX WtWebGraphAnalog57761ValuesPointEntry
    ACCESS not-accessible
    STATUS mandatory
    DESCRIPTION
        "Measurement values of the sensors."
    INDEX  { wtWebGraphAnalog57761SensorNo }
    ::= { wtWebGraphAnalog57761ValuesPointTable 1 }

WtWebGraphAnalog57761ValuesPointEntry ::= SEQUENCE{
    wtWebGraphAnalog57761ValuesPoint OCTET STRING
}

wtWebGraphAnalog57761ValuesPoint OBJECT-TYPE
    SYNTAX OCTET STRING (SIZE (5))
    ACCESS read-write
    STATUS mandatory
    DESCRIPTION
        "Measurement value of the sensor, ASCII.
        This value will be translated according to the ports settings
        for the read and write operations."
    ::= { wtWebGraphAnalog57761ValuesPointEntry 1 }


-- wtWebGraphAnalog57761SessCntrl Group
--------------------------------

wtWebGraphAnalog57761SessCntrlPassword OBJECT-TYPE
    SYNTAX OCTET STRING
    ACCESS read-write
    STATUS mandatory
    DESCRIPTION
        "Entering this password opens a session which is ended by writing a 1 to
        wtWebGraphAnalog57761SessCntrlLogout. When read this variable provides a string of
        length zero."
    ::= { wtWebGraphAnalog57761SessCntrl 1 }

wtWebGraphAnalog57761SessCntrlConfigMode OBJECT-TYPE
    SYNTAX INTEGER {
    wtWebGraphAnalog57761SessCntrl-NoSession(0),
    wtWebGraphAnalog57761SessCntrl-Session(1)
    }
    ACCESS read-only
    STATUS mandatory
    DESCRIPTION
        "When the device is in SNMP configuration mode, the value 1 is
        returned, otherwise 0. If the read value is 0 even though the
        password was written, the device is already in config mode and the
        variables can only be read."
    ::= { wtWebGraphAnalog57761SessCntrl 2 }

wtWebGraphAnalog57761SessCntrlLogout OBJECT-TYPE
    SYNTAX INTEGER
    ACCESS read-write
    STATUS mandatory
    DESCRIPTION
        "If the device is in configuration mode and the session was opened by
        this SNMP Manager, writing a 1 to this variable will end the session
        and all parameters are stored.
        Writing a 2 discards all entries again.
        When read this variable provides the value 0."
    ::= { wtWebGraphAnalog57761SessCntrl 3 }

wtWebGraphAnalog57761SessCntrlAdminPassword OBJECT-TYPE
    SYNTAX OCTET STRING
    ACCESS read-write
    STATUS mandatory
    DESCRIPTION
        "This password protects access to the variables with administrator rights.
        It can only be changed by the administrator. If no password was assigned,
        the valid password is public."
    ::= { wtWebGraphAnalog57761SessCntrl 4 }

wtWebGraphAnalog57761SessCntrlConfigPassword OBJECT-TYPE
    SYNTAX OCTET STRING
    ACCESS read-write
    STATUS mandatory
    DESCRIPTION
        "This password protects access to the variables with configurator rights. It can
        be changed by the administrator and by the configurator. If no password was assigned,
        the valid password is public. When read this variable provides a null-pointer."
    ::= { wtWebGraphAnalog57761SessCntrl 5 }


-- wtWebGraphAnalog57761Text Group
------------------------

wtWebGraphAnalog57761DeviceName OBJECT-TYPE
    SYNTAX OCTET STRING
    ACCESS read-write
    STATUS mandatory
    DESCRIPTION
        "Name of the Webio, which is user definable."
    ::= { wtWebGraphAnalog57761Text 1 }

wtWebGraphAnalog57761DeviceText OBJECT-TYPE
    SYNTAX OCTET STRING
    ACCESS read-write
    STATUS mandatory
    DESCRIPTION
        "Description of the Webio, which is user definable."
    ::= { wtWebGraphAnalog57761Text 2 }

wtWebGraphAnalog57761DeviceLocation OBJECT-TYPE
    SYNTAX OCTET STRING
    ACCESS read-write
    STATUS mandatory
    DESCRIPTION
        "Description of the location of the Webio, which is user definable."
    ::= { wtWebGraphAnalog57761Text 3 }

wtWebGraphAnalog57761DeviceContact OBJECT-TYPE
    SYNTAX OCTET STRING
    ACCESS read-write
    STATUS mandatory
    DESCRIPTION
        "Contact address of the system operator of the Webio, which is user definable."
    ::= { wtWebGraphAnalog57761Text 4 }

-- wtWebGraphAnalog57761TimeZone Group
----------------------------

wtWebGraphAnalog57761TzOffsetHrs OBJECT-TYPE
    SYNTAX INTEGER
    ACCESS read-write
    STATUS mandatory
    DESCRIPTION
        "Offset hours for the time zone (winter time) with respect to UTC."
    ::= { wtWebGraphAnalog57761TimeZone 1 }

wtWebGraphAnalog57761TzOffsetMin OBJECT-TYPE
    SYNTAX INTEGER
    ACCESS read-write
    STATUS mandatory
    DESCRIPTION
        "Offset minutes for the time zone (winter time) with respect to UTC."
    ::= { wtWebGraphAnalog57761TimeZone 2 }

wtWebGraphAnalog57761TzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebGraphAnalog57761TimeZone 3 }

wtWebGraphAnalog57761StTzOffsetHrs OBJECT-TYPE
    SYNTAX INTEGER
    ACCESS read-write
    STATUS mandatory
    DESCRIPTION
        "Offset hours of the time zone (summer time) with respect to UTC."
    ::= { wtWebGraphAnalog57761TimeZone 4 }

wtWebGraphAnalog57761StTzOffsetMin OBJECT-TYPE
    SYNTAX INTEGER
    ACCESS read-write
    STATUS mandatory
    DESCRIPTION
        "Offset minutes of the time zone (summer time) with respect to UTC."
    ::= { wtWebGraphAnalog57761TimeZone 5 }

wtWebGraphAnalog57761StTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebGraphAnalog57761TimeZone 6 }

wtWebGraphAnalog57761StTzStartMonth OBJECT-TYPE
    SYNTAX INTEGER {
    	wtWebGraphAnalog57761StartMonth-January(1),
    	wtWebGraphAnalog57761StartMonth-February(2),
    	wtWebGraphAnalog57761StartMonth-March(3),
    	wtWebGraphAnalog57761StartMonth-April(4),
    	wtWebGraphAnalog57761StartMonth-May(5),
    	wtWebGraphAnalog57761StartMonth-June(6),
    	wtWebGraphAnalog57761StartMonth-July(7),
    	wtWebGraphAnalog57761StartMonth-August(8),
    	wtWebGraphAnalog57761StartMonth-September(9),
    	wtWebGraphAnalog57761StartMonth-October(10),
    	wtWebGraphAnalog57761StartMonth-November(11),
    	wtWebGraphAnalog57761StartMonth-December(12)
    	}

    ACCESS read-write
    STATUS mandatory
    DESCRIPTION
        "Month in which the change is made from winter time to summer time."
    ::= { wtWebGraphAnalog57761TimeZone 7 }

wtWebGraphAnalog57761StTzStartMode OBJECT-TYPE
    SYNTAX INTEGER {
    	wtWebGraphAnalog57761StartMode-first(1),
    	wtWebGraphAnalog57761StartMode-second(2),
    	wtWebGraphAnalog57761StartMode-third(3),
    	wtWebGraphAnalog57761StartMode-fourth(4),
    	wtWebGraphAnalog57761StartMode-last(5)
    	}

    ACCESS read-write
    STATUS mandatory
    DESCRIPTION
        "Mode of the day of the week for which the change is made from winter time to summer time."
    ::= { wtWebGraphAnalog57761TimeZone 8 }

wtWebGraphAnalog57761StTzStartWday OBJECT-TYPE
    SYNTAX INTEGER {
    	wtWebGraphAnalog57761StartWday-Sunday(1),
    	wtWebGraphAnalog57761StartWday-Monday(2),
    	wtWebGraphAnalog57761StartWday-Tuesday(3),
    	wtWebGraphAnalog57761StartWday-Thursday(4),
    	wtWebGraphAnalog57761StartWday-Wednesday(5),
    	wtWebGraphAnalog57761StartWday-Friday(6),
    	wtWebGraphAnalog57761StartWday-Saturday(7)
    	}

    ACCESS read-write
    STATUS mandatory
    DESCRIPTION
        "Day of the week on which the change is made from winter time to summer time"
    ::= { wtWebGraphAnalog57761TimeZone 9 }

wtWebGraphAnalog57761StTzStartHrs OBJECT-TYPE
    SYNTAX INTEGER
    ACCESS read-write
    STATUS mandatory
    DESCRIPTION
        "Hour in which the time zone is changed from winter to summer time with
        respect to UTC."
    ::= { wtWebGraphAnalog57761TimeZone 10 }

wtWebGraphAnalog57761StTzStartMin OBJECT-TYPE
    SYNTAX INTEGER
    ACCESS read-write
    STATUS mandatory
    DESCRIPTION
        "Minute in which the time zone is changed from winter to summer time with
        respect to UTC."
    ::= { wtWebGraphAnalog57761TimeZone 11 }

wtWebGraphAnalog57761StTzStopMonth OBJECT-TYPE
    SYNTAX INTEGER {
    	wtWebGraphAnalog57761StopMonth-January(1),
    	wtWebGraphAnalog57761StopMonth-February(2),
    	wtWebGraphAnalog57761StopMonth-March(3),
    	wtWebGraphAnalog57761StopMonth-April(4),
    	wtWebGraphAnalog57761StopMonth-May(5),
    	wtWebGraphAnalog57761StopMonth-June(6),
    	wtWebGraphAnalog57761StopMonth-July(7),
    	wtWebGraphAnalog57761StopMonth-August(8),
    	wtWebGraphAnalog57761StopMonth-September(9),
    	wtWebGraphAnalog57761StopMonth-October(10),
    	wtWebGraphAnalog57761StopMonth-November(11),
    	wtWebGraphAnalog57761StopMonth-December(12)
    	}
    ACCESS read-write
    STATUS mandatory
    DESCRIPTION
        "Month in which the change is made from summer time to winter time."
   ::= { wtWebGraphAnalog57761TimeZone 12 }

wtWebGraphAnalog57761StTzStopMode OBJECT-TYPE
    SYNTAX INTEGER {
    	wtWebGraphAnalog57761StopMode-first(1),
    	wtWebGraphAnalog57761StopMode-second(2),
    	wtWebGraphAnalog57761StopMode-third(3),
    	wtWebGraphAnalog57761StopMode-fourth(4),
    	wtWebGraphAnalog57761StopMode-last(5)
    	}
    ACCESS read-write
    STATUS mandatory
    DESCRIPTION
        "Mode of the week day on which the change is made from summer time to winter time."
    ::= { wtWebGraphAnalog57761TimeZone 13 }

wtWebGraphAnalog57761StTzStopWday OBJECT-TYPE
    SYNTAX INTEGER {
    	wtWebGraphAnalog57761StopWday-Sunday(1),
    	wtWebGraphAnalog57761StopWday-Monday(2),
    	wtWebGraphAnalog57761StopWday-Tuesday(3),
    	wtWebGraphAnalog57761StopWday-Thursday(4),
    	wtWebGraphAnalog57761StopWday-Wednesday(5),
    	wtWebGraphAnalog57761StopWday-Friday(6),
    	wtWebGraphAnalog57761StopWday-Saturday(7)
    	}
    ACCESS read-write
    STATUS mandatory
    DESCRIPTION
        "Day of the week on which the change is made from summer time to winter time."
    ::= { wtWebGraphAnalog57761TimeZone 14 }

wtWebGraphAnalog57761StTzStopHrs OBJECT-TYPE
    SYNTAX INTEGER
    ACCESS read-write
    STATUS mandatory
    DESCRIPTION
        "Hour at which the time zone is changed from summer to winter time with
        respect to UTC."
    ::= { wtWebGraphAnalog57761TimeZone 15 }

wtWebGraphAnalog57761StTzStopMin OBJECT-TYPE
    SYNTAX INTEGER
    ACCESS read-write
    STATUS mandatory
    DESCRIPTION
        "Minute at which the time zone is changed from summer to winter time with
        respect to UTC."
    ::= { wtWebGraphAnalog57761TimeZone 16 }

-- wtWebGraphAnalog57761TimeServer Group
----------------------------

wtWebGraphAnalog57761TimeServer1 OBJECT-TYPE
    SYNTAX OCTET STRING
    ACCESS read-write
    STATUS mandatory
    DESCRIPTION
        "IP address or name of the 1st time server in ASCII"
    ::= { wtWebGraphAnalog57761TimeServer 1 }

wtWebGraphAnalog57761TimeServer2 OBJECT-TYPE
    SYNTAX OCTET STRING
    ACCESS read-write
    STATUS mandatory
    DESCRIPTION
        "IP address or name of the 2nd time server in ASCII"
    ::= { wtWebGraphAnalog57761TimeServer 2 }

wtWebGraphAnalog57761TsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebGraphAnalog57761TimeServer 3 }

wtWebGraphAnalog57761TsSyncTime OBJECT-TYPE
    SYNTAX INTEGER
    ACCESS read-write
    STATUS mandatory
    DESCRIPTION
        "Daily synchronisation time with the time server (hour: 0-23)."
    ::= { wtWebGraphAnalog57761TimeServer 4 }

-- wtWebGraphAnalog57761DeviceClock Group
----------------------------

wtWebGraphAnalog57761ClockHrs OBJECT-TYPE
    SYNTAX INTEGER (0..23)
    ACCESS read-write
    STATUS mandatory
    DESCRIPTION
        "Clock hours taking into account the time zone settings."
    ::= { wtWebGraphAnalog57761DeviceClock 1 }

wtWebGraphAnalog57761ClockMin OBJECT-TYPE
    SYNTAX INTEGER (0..59)
    ACCESS read-write
    STATUS mandatory
    DESCRIPTION
        "Clock minutes taking into account the time zone settings."
    ::= { wtWebGraphAnalog57761DeviceClock 2 }

wtWebGraphAnalog57761ClockDay OBJECT-TYPE
    SYNTAX INTEGER (1..31)
    ACCESS read-write
    STATUS mandatory
    DESCRIPTION
        "Date: Day of the month, taking into account the time zone settings."
    ::= { wtWebGraphAnalog57761DeviceClock 3 }

wtWebGraphAnalog57761ClockMonth OBJECT-TYPE
   SYNTAX INTEGER {
    	wtWebGraphAnalog57761ClockMonth-January(1),
    	wtWebGraphAnalog57761ClockMonth-February(2),
    	wtWebGraphAnalog57761ClockMonth-March(3),
    	wtWebGraphAnalog57761ClockMonth-April(4),
    	wtWebGraphAnalog57761ClockMonth-May(5),
    	wtWebGraphAnalog57761ClockMonth-June(6),
    	wtWebGraphAnalog57761ClockMonth-July(7),
    	wtWebGraphAnalog57761ClockMonth-August(8),
    	wtWebGraphAnalog57761ClockMonth-September(9),
    	wtWebGraphAnalog57761ClockMonth-October(10),
    	wtWebGraphAnalog57761ClockMonth-November(11),
    	wtWebGraphAnalog57761ClockMonth-December(12)
    	}
    ACCESS read-write
    STATUS mandatory
    DESCRIPTION
        "Date: Month, taking into account the time zone settings."
    ::= { wtWebGraphAnalog57761DeviceClock 4 }

wtWebGraphAnalog57761ClockYear OBJECT-TYPE
    SYNTAX INTEGER (0..65535)
    ACCESS read-write
    STATUS mandatory
    DESCRIPTION
        "Date: Year, taking into account the time zone settings."
    ::= { wtWebGraphAnalog57761DeviceClock 5 }


-- wtWebGraphAnalog57761Network Group
------------------------

wtWebGraphAnalog57761IpAddress OBJECT-TYPE
    SYNTAX IpAddress
    ACCESS read-write
    STATUS mandatory
    DESCRIPTION
        "IP address of the Webio"
    ::= { wtWebGraphAnalog57761Network 1 }

wtWebGraphAnalog57761SubnetMask OBJECT-TYPE
    SYNTAX IpAddress
    ACCESS read-write
    STATUS mandatory
    DESCRIPTION
        "Subnet mask of the Webio"
    ::= { wtWebGraphAnalog57761Network 2 }

wtWebGraphAnalog57761Gateway OBJECT-TYPE
    SYNTAX IpAddress
    ACCESS read-write
    STATUS mandatory
    DESCRIPTION
        "Gateway of the Webio"
    ::= { wtWebGraphAnalog57761Network 3 }

wtWebGraphAnalog57761DnsServer1 OBJECT-TYPE
    SYNTAX OCTET STRING
    ACCESS read-write
    STATUS mandatory
    DESCRIPTION
        "IP address of the 1st DNS server in ASCII"
    ::= { wtWebGraphAnalog57761Network 4 }

wtWebGraphAnalog57761DnsServer2 OBJECT-TYPE
    SYNTAX OCTET STRING
    ACCESS read-write
    STATUS mandatory
    DESCRIPTION
        "IP address of the 2nd DNS server in ASCII"
    ::= { wtWebGraphAnalog57761Network 5 }

wtWebGraphAnalog57761AddConfig OBJECT-TYPE
    SYNTAX OCTET STRING
    ACCESS read-write
    STATUS mandatory
    DESCRIPTION
        "Additional configuration (1=ON):
        Octet 1: unused
        Octet 2: unused
        Octet 3: unused
        Octet 4:
	        Bit 1: DHCP disable
	        Bit 0: BOOTP disable
	        "
    ::= { wtWebGraphAnalog57761Network 6 }

--  wtWebGraphAnalog57761HTTP Group
--------------------------------

wtWebGraphAnalog57761Startup OBJECT-TYPE
    SYNTAX OCTET STRING
    ACCESS read-write
    STATUS mandatory
    DESCRIPTION
        "Binary coded start page:
        Octet 1: unused
        Octet 2: unused
        Octet 3: unused
        Octet 4:
	        Bit 1: Index.htm
	        Bit 2: Home.htm
	        Bit 3: User.htm
	Only one page may be selected at a time."
    ::= { wtWebGraphAnalog57761HTTP 1 }

wtWebGraphAnalog57761GetHeaderEnable OBJECT-TYPE
    SYNTAX OCTET STRING
    ACCESS read-write
    STATUS mandatory
    DESCRIPTION
        "If these bits are set, every answer of a short form GET question will be lead
        by the IP-address and name of the device and/or a HTTP header:
        Octet 1: unused
        Octet 2: unused
        Octet 3: unused
        Octet 4:
        	Bit 1-6: unused
        	Bit 1  : GET HTTP enable
                Bit 0  : GET Header enable"
    ::= { wtWebGraphAnalog57761HTTP 2 }

wtWebGraphAnalog57761HttpPort OBJECT-TYPE
    SYNTAX INTEGER (1..65535)
    ACCESS read-write
    STATUS mandatory
    DESCRIPTION
        "Definition of the standard HTML port (Default: 80)."
    ::= { wtWebGraphAnalog57761HTTP 3 }


-- wtWebGraphAnalog57761Mail Group
--------------------------------

wtWebGraphAnalog57761MailAdName OBJECT-TYPE
    SYNTAX OCTET STRING
    ACCESS read-write
    STATUS mandatory
    DESCRIPTION
        "Device name for mail administration."
    ::= { wtWebGraphAnalog57761Mail 1 }

wtWebGraphAnalog57761MailReply OBJECT-TYPE
    SYNTAX OCTET STRING
    ACCESS read-write
    STATUS mandatory
    DESCRIPTION
        "Reply address for the mail server."
    ::= { wtWebGraphAnalog57761Mail 2 }

wtWebGraphAnalog57761MailServer OBJECT-TYPE
    SYNTAX OCTET STRING
    ACCESS read-write
    STATUS mandatory
    DESCRIPTION
        "Name or IP address of the mail server."
    ::= { wtWebGraphAnalog57761Mail 3 }

wtWebioAn1MailEnable OBJECT-TYPE
    SYNTAX OCTET STRING
    ACCESS read-write
    STATUS mandatory
    DESCRIPTION
        "Set this bit to enable the sending of mails:
        Octet 1: unused
        Octet 2: unused
        Octet 3: unused
        Octet 4:
        	Bit 1-7: unused
                Bit 0  : Mail enable"
    ::= { wtWebGraphAnalog57761Mail 4 }

wtWebGraphAnalog57761MailAuthentication OBJECT-TYPE
    SYNTAX OCTET STRING (SIZE (4))
    ACCESS read-write
    STATUS mandatory
    DESCRIPTION
        "Selection of the authentication modi:
        The OCTETS are interpreted bit-by-bit, with each bit corresponding to an output.
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebGraphAnalog57761Mail 5 }

wtWebGraphAnalog57761MailAuthUser OBJECT-TYPE
    SYNTAX OCTET STRING
    ACCESS read-write
    STATUS mandatory
    DESCRIPTION
        "Name of the user to be authenticated."
    ::= { wtWebGraphAnalog57761Mail 6 }

wtWebGraphAnalog57761MailAuthPassword OBJECT-TYPE
    SYNTAX OCTET STRING
    ACCESS read-write
    STATUS mandatory
    DESCRIPTION
        "Authentication password."
    ::= { wtWebGraphAnalog57761Mail 7 }

wtWebGraphAnalog57761MailPop3Server OBJECT-TYPE
    SYNTAX OCTET STRING
    ACCESS read-write
    STATUS mandatory
    DESCRIPTION
        "Name or Ip-address of the POP3 Servers."
    ::= { wtWebGraphAnalog57761Mail 8 }

-- wtWebGraphAnalog57761SNMP Group
--------------------------------

wtWebGraphAnalog57761SnmpCommunityStringRead OBJECT-TYPE
    SYNTAX OCTET STRING
    ACCESS read-write
    STATUS mandatory
    DESCRIPTION
        "Community string read only"
    ::= { wtWebGraphAnalog57761SNMP 1 }

wtWebGraphAnalog57761SnmpCommunityStringReadWrite OBJECT-TYPE
    SYNTAX OCTET STRING
    ACCESS read-write
    STATUS mandatory
    DESCRIPTION
        "Community string read / write"
    ::= { wtWebGraphAnalog57761SNMP 2 }

wtWebGraphAnalog57761SystemTrapManagerIP OBJECT-TYPE
    SYNTAX OCTET STRING
    ACCESS read-write
    STATUS mandatory
    DESCRIPTION
        "Name or IP address of the TCP server which accepts the system trap."
    ::= { wtWebGraphAnalog57761SNMP 3 }

wtWebGraphAnalog57761SystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2-7: unused"
    ::= { wtWebGraphAnalog57761SNMP 4 }

wtWebGraphAnalog57761SnmpEnable OBJECT-TYPE
    SYNTAX OCTET STRING
    ACCESS read-write
    STATUS mandatory
    DESCRIPTION
        "Set bit 0 to enable SNMP.
        If disabled, the device did not respond to any SNMP requests.
        Bit 1 decided wether the community string of read operations
        is compared with the system password or not:
        Octet 1: unused
        Octet 2: unused
        Octet 3: unused
        Octet 4:
        	Bit 1-7: unused
        	Bit 0  : SNMP enable"
    ::= { wtWebGraphAnalog57761SNMP 5 }

wtWebGraphAnalog57761SnmpCommunityStringTrap OBJECT-TYPE
    SYNTAX OCTET STRING
    ACCESS read-write
    STATUS mandatory
    DESCRIPTION
        "Community string send within traps."
    ::= { wtWebGraphAnalog57761SNMP 6 }

wtWebGraphAnalog57761SnmpSystemTrapManagerPort OBJECT-TYPE
    SYNTAX INTEGER
    ACCESS read-write
    STATUS mandatory
    DESCRIPTION
        "Port number of the TCP server which accepts the system trap."
    ::= { wtWebGraphAnalog57761SNMP 7 }


-- wtWebGraphAnalog57761UDP Group
--------------------------------

wtWebGraphAnalog57761UdpPort OBJECT-TYPE
    SYNTAX INTEGER (1..65535)
    ACCESS read-write
    STATUS mandatory
    DESCRIPTION
        "Udp port to which the Udp queries ( short form GET requests) can be sent. This
        port number must be unique within the device."
    ::= { wtWebGraphAnalog57761UDP 1 }

wtWebGraphAnalog57761UdpEnable OBJECT-TYPE
    SYNTAX OCTET STRING
    ACCESS read-write
    STATUS mandatory
    DESCRIPTION
        "Set this bit to enable UDP support:
        Octet 1: unused
        Octet 2: unused
        Octet 3: unused
        Octet 4:
        	Bit 1-7: unused
                Bit 0  : UDP enable"
    ::= { wtWebGraphAnalog57761UDP 2 }

--  wtWebGraphAnalog57761Syslog Group
--------------------------------

wtWebGraphAnalog57761SyslogServerIP OBJECT-TYPE
    SYNTAX OCTET STRING
    ACCESS read-write
    STATUS mandatory
    DESCRIPTION
        "Name or IP address of the Syslog server, which accepts the Syslog messgaes."
    ::= { wtWebGraphAnalog57761Syslog 1 }

wtWebGraphAnalog57761SyslogServerPort OBJECT-TYPE
    SYNTAX INTEGER
    ACCESS read-write
    STATUS mandatory
    DESCRIPTION
        "Portnumber of the Syslog servers, default 514."
    ::= { wtWebGraphAnalog57761Syslog 2 }

wtWebGraphAnalog57761SyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebGraphAnalog57761Syslog 3 }

wtWebGraphAnalog57761SyslogEnable OBJECT-TYPE
    SYNTAX OCTET STRING
    ACCESS read-write
    STATUS mandatory
    DESCRIPTION
        "Set bit 0to enable Syslog:
        Octet 1: unused
        Octet 2: unused
        Octet 3: unused
        Octet 4:
        	Bit 1-7: unused
                Bit 0  : Syslog enable"
    ::= { wtWebGraphAnalog57761Syslog 4 }

--  wtWebGraphAnalog57761FTP Group
--------------------------------

wtWebGraphAnalog57761FTPServerIP OBJECT-TYPE
    SYNTAX OCTET STRING
    ACCESS read-write
    STATUS mandatory
    DESCRIPTION
        "Name or IP address of the FTP server, which accepts the FTP messages."
    ::= { wtWebGraphAnalog57761FTP 1 }

wtWebGraphAnalog57761FTPServerControlPort OBJECT-TYPE
    SYNTAX INTEGER
    ACCESS read-write
    STATUS mandatory
    DESCRIPTION
        "Portnumber of the control port of the FTP server, default 21."
    ::= { wtWebGraphAnalog57761FTP 2 }

wtWebGraphAnalog57761FTPUserName OBJECT-TYPE
    SYNTAX OCTET STRING
    ACCESS read-write
    STATUS mandatory
    DESCRIPTION
        "FTP Loggin: user name."
    ::= { wtWebGraphAnalog57761FTP 3 }

wtWebGraphAnalog57761FTPPassword OBJECT-TYPE
    SYNTAX OCTET STRING
    ACCESS read-write
    STATUS mandatory
    DESCRIPTION
        "FTP Loggin: user password."
    ::= { wtWebGraphAnalog57761FTP 4 }

wtWebGraphAnalog57761FTPAccount OBJECT-TYPE
    SYNTAX OCTET STRING
    ACCESS read-write
    STATUS mandatory
    DESCRIPTION
        "FTP Loggin: name of account."
    ::= { wtWebGraphAnalog57761FTP 5 }

wtWebGraphAnalog57761FTPOption OBJECT-TYPE
    SYNTAX OCTET STRING
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebGraphAnalog57761FTP 6 }

wtWebGraphAnalog57761FTPEnable OBJECT-TYPE
    SYNTAX OCTET STRING
    ACCESS read-write
    STATUS mandatory
    DESCRIPTION
        "Set Bit 0 to enable FTP:
        Octet 1: unused
        Octet 2: unused
        Octet 3: unused
        Octet 4:
        	Bit 1-7: unused
                Bit 0  : FTP enable"
    ::= { wtWebGraphAnalog57761FTP 7 }

--  wtWebGraphAnalog57761Language Group
--------------------------------

wtWebGraphAnalog57761LanguageSelect OBJECT-TYPE
    SYNTAX OCTET STRING
    ACCESS read-write
    STATUS mandatory
    DESCRIPTION
        "Language selection:
        Octet 1: unused
        Octet 2: unused
        Octet 3: unused
        Octet 4:
        	Bit 2-7: unused
        	Bit 1  : English
                Bit 0  : German"
    ::= { wtWebGraphAnalog57761Language 1 }

--  wtWebGraphAnalog57761Binary Group
--------------------------------

wtWebGraphAnalog57761BinaryModeCount OBJECT-TYPE
    SYNTAX INTEGER (1..2)
    ACCESS read-only
    STATUS mandatory
    DESCRIPTION
        "Number of independent binary channels."
    ::= { wtWebGraphAnalog57761Binary 1 }

-- Binary Interface Table

wtWebGraphAnalog57761BinaryIfTable OBJECT-TYPE
    SYNTAX SEQUENCE OF WtWebGraphAnalog57761BinaryIfEntry
    ACCESS not-accessible
    STATUS mandatory
    DESCRIPTION
        "Table of indices."
    ::= { wtWebGraphAnalog57761Binary 2 }

wtWebGraphAnalog57761BinaryIfEntry OBJECT-TYPE
    SYNTAX WtWebGraphAnalog57761BinaryIfEntry
    ACCESS not-accessible
    STATUS mandatory
    DESCRIPTION
        "Indices of the binary channels."
    INDEX  { wtWebGraphAnalog57761BinaryModeNo }
    ::= { wtWebGraphAnalog57761BinaryIfTable 1 }

WtWebGraphAnalog57761BinaryIfEntry ::= SEQUENCE {
    wtWebGraphAnalog57761BinaryModeNo INTEGER
}

wtWebGraphAnalog57761BinaryModeNo OBJECT-TYPE
    SYNTAX INTEGER (1..2)
    ACCESS read-only
    STATUS mandatory
    DESCRIPTION
        "Number of the binary channel."
    ::= { wtWebGraphAnalog57761BinaryIfEntry 1 }

-- Binary Table
--------------------------------

wtWebGraphAnalog57761BinaryTable OBJECT-TYPE
    SYNTAX SEQUENCE OF WtWebGraphAnalog57761BinaryEntry
    ACCESS not-accessible
    STATUS mandatory
    DESCRIPTION
        "Table of properties of the binary mode."
    ::= { wtWebGraphAnalog57761Binary 3 }

wtWebGraphAnalog57761BinaryEntry OBJECT-TYPE
    SYNTAX WtWebGraphAnalog57761BinaryEntry
    ACCESS not-accessible
    STATUS mandatory
    DESCRIPTION
        "Binary properties."
    INDEX  { wtWebGraphAnalog57761BinaryModeNo }
    ::= { wtWebGraphAnalog57761BinaryTable 1 }

WtWebGraphAnalog57761BinaryEntry ::= SEQUENCE {
    wtWebGraphAnalog57761BinaryOperationMode			OCTET STRING,
    wtWebGraphAnalog57761BinaryTcpServerLocalPort		INTEGER,
    wtWebGraphAnalog57761BinaryTcpServerInputTrigger		OCTET STRING,
    wtWebGraphAnalog57761BinaryTcpServerApplicationMode		OCTET STRING,
    wtWebGraphAnalog57761BinaryTcpClientLocalPort		INTEGER,
    wtWebGraphAnalog57761BinaryTcpClientServerPort		INTEGER,
    wtWebGraphAnalog57761BinaryTcpClientServerIpAddr		OCTET STRING,
    wtWebGraphAnalog57761BinaryTcpClientServerPassword		OCTET STRING,
    wtWebGraphAnalog57761BinaryTcpClientInactivity		INTEGER,
    wtWebGraphAnalog57761BinaryTcpClientInputTrigger		OCTET STRING,
    wtWebGraphAnalog57761BinaryTcpClientInterval		INTEGER,
    wtWebGraphAnalog57761BinaryTcpClientApplicationMode		OCTET STRING,
    wtWebGraphAnalog57761BinaryUdpPeerLocalPort			INTEGER,
    wtWebGraphAnalog57761BinaryUdpPeerRemotePort		INTEGER,
    wtWebGraphAnalog57761BinaryUdpPeerRemoteIpAddr		OCTET STRING,
    wtWebGraphAnalog57761BinaryUdpPeerInputTrigger		OCTET STRING,
    wtWebGraphAnalog57761BinaryUdpPeerInterval			INTEGER,
    wtWebGraphAnalog57761BinaryUdpPeerApplicationMode		OCTET STRING,
    wtWebGraphAnalog57761BinaryConnectedPort			INTEGER,
    wtWebGraphAnalog57761BinaryConnectedIpAddr			IpAddress,
    wtWebGraphAnalog57761BinaryTcpServerClientHttpPort		INTEGER,
    wtWebGraphAnalog57761BinaryTcpClientServerHttpPort		INTEGER,
    wtWebGraphAnalog57761BinaryTcpServerHysteresis1		OCTET STRING,
    wtWebGraphAnalog57761BinaryTcpServerHysteresis2		OCTET STRING,
    wtWebGraphAnalog57761BinaryTcpClientHysteresis1		OCTET STRING,
    wtWebGraphAnalog57761BinaryTcpClientHysteresis2		OCTET STRING,
    wtWebGraphAnalog57761BinaryUdpPeerHysteresis1		OCTET STRING,
    wtWebGraphAnalog57761BinaryUdpPeerHysteresis2		OCTET STRING,
    wtWebGraphAnalog57761BinaryTcpClientServerUserName		OCTET STRING
}

wtWebGraphAnalog57761BinaryOperationMode OBJECT-TYPE
    SYNTAX OCTET STRING (SIZE (4))
    ACCESS read-write
    STATUS mandatory
    DESCRIPTION
        "Selection of the operation mode:
        The OCTETS are interpreted bit-by-bit,
        Bit 0 corresponds to the LSB.
        OCTET 1: unused
        OCTET 2: unused
        OCTET 3: unused
        OCTET 4: Bit 3-7: unused
        	 Bit 2  : UDP Peer
        	 Bit 1  : TCP Client
        	 Bit 0  : TCP Server"
    ::= { wtWebGraphAnalog57761BinaryEntry 1 }

wtWebGraphAnalog57761BinaryTcpServerLocalPort OBJECT-TYPE
    SYNTAX INTEGER (1..65535)
    ACCESS read-write
    STATUS mandatory
    DESCRIPTION
        "Local TCP port for data exchange in this server mode.
        This port number must be unique within the device.
	Reserved port number must not be used (refere to the manual)."
    ::= { wtWebGraphAnalog57761BinaryEntry 2 }

wtWebGraphAnalog57761BinaryTcpServerInputTrigger OBJECT-TYPE
    SYNTAX OCTET STRING (SIZE (4))
    ACCESS read-write
    STATUS mandatory
    DESCRIPTION
        "Every change on the inputs causes their state to be transmitted to the
        remote device. To minimize data traffic, individual inputs may be exempted
        from this rule. Nevertheless every transmission will contain all input states.
        If a bit is set (1), a change of state on the corresponding input
        triggers a transmission. If the bit is not set (0), no transmission
        takes place.
        The OCTETS are interpreted bit-by-bit, with each bit corresponding to an input.
        Bit 0 corresponds to the LSB.
        OCTET 1: unused
        OCTET 2: unused
        OCTET 3: unused
        OCTET 4, Bit 0-1: Analog inputs 0-1"
    ::= { wtWebGraphAnalog57761BinaryEntry 3 }

wtWebGraphAnalog57761BinaryTcpServerApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 4-7: unused
        	 Bit 3  : OPC Device
        	 Bit 2  : Box2Box Slave
        	 Bit 1  : Compatible 50xxx
        	 Bit 0  : Default"
    ::= { wtWebGraphAnalog57761BinaryEntry 4 }

wtWebGraphAnalog57761BinaryTcpClientLocalPort OBJECT-TYPE
    SYNTAX INTEGER (1..65535)
    ACCESS read-write
    STATUS mandatory
    DESCRIPTION
        "Local TCP port for data exchange in this client mode.
        This port number must be unique within the device.
	Reserved port number must not be used (refere to the manual)."
    ::= { wtWebGraphAnalog57761BinaryEntry 5 }

wtWebGraphAnalog57761BinaryTcpClientServerPort OBJECT-TYPE
    SYNTAX INTEGER (1..65535)
    ACCESS read-write
    STATUS mandatory
    DESCRIPTION
        "Port number of the server. A complete set of port number, IP address
        and a valid input/output mask starts this mode.
        No data exchange take place when setting the server port to zero."
    ::= { wtWebGraphAnalog57761BinaryEntry 6 }

wtWebGraphAnalog57761BinaryTcpClientServerIpAddr OBJECT-TYPE
    SYNTAX OCTET STRING
    ACCESS read-write
    STATUS mandatory
    DESCRIPTION
        "Ip address of the server. A complete set of port number, IP address
        and a valid input/output mask starts this mode.
        No data exchange take place when setting the server IP address to 0.0.0.0."
    ::= { wtWebGraphAnalog57761BinaryEntry 7 }

wtWebGraphAnalog57761BinaryTcpClientServerPassword OBJECT-TYPE
    SYNTAX OCTET STRING
    ACCESS read-write
    STATUS mandatory
    DESCRIPTION
        "Building a connection may be protected by the
        administrator password of the server. Enter the server password
        to establish the connection, if a server administrator password
        exists."
    ::= { wtWebGraphAnalog57761BinaryEntry 8 }

wtWebGraphAnalog57761BinaryTcpClientInactivity OBJECT-TYPE
    SYNTAX INTEGER
    ACCESS read-write
    STATUS mandatory
    DESCRIPTION
        "Connection timeout in 100ms. If no data are exchanged within the specified
        time, the device closes the connection to the server.
        The value 0 deactivates the timer. Using the Box2Box mode this function is
        disabled."
    ::= { wtWebGraphAnalog57761BinaryEntry 9 }

wtWebGraphAnalog57761BinaryTcpClientInputTrigger OBJECT-TYPE
    SYNTAX OCTET STRING (SIZE (4))
    ACCESS read-write
    STATUS mandatory
    DESCRIPTION
        "Every change on the inputs causes their state to be transmitted to the
        remote device. To minimize data traffic, individual inputs may be exempted
        from this rule. Nevertheless every transmission will contain all input states.
        If a bit is set (1), a change of state on the corresponding input
        triggers a transmission. If the bit is not set (0), no transmission
        takes place.
        The OCTETS are interpreted bit-by-bit, with each bit corresponding to an input.
        Bit 0 corresponds to the LSB.
        OCTET 1: unused
        OCTET 2: unused
        OCTET 3: unused
        OCTET 4, Bit 0-1: Analog inputs 0-1"
    ::= { wtWebGraphAnalog57761BinaryEntry 10 }

wtWebGraphAnalog57761BinaryTcpClientInterval OBJECT-TYPE
    SYNTAX INTEGER (0..65535)
    ACCESS read-write
    STATUS mandatory
    DESCRIPTION
        "Configurable interval with a 100ms base, in which the Webio device sends
        data to the configured application. A interval of zero stopps the
        periodical sending."
    ::= { wtWebGraphAnalog57761BinaryEntry 11 }

wtWebGraphAnalog57761BinaryTcpClientApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebGraphAnalog57761BinaryEntry 12 }

wtWebGraphAnalog57761BinaryUdpPeerLocalPort OBJECT-TYPE
    SYNTAX INTEGER (1..65535)
    ACCESS read-write
    STATUS mandatory
    DESCRIPTION
        "Local UDP port for data exchange in this peer to peer mode.
        This port number must be unique within the device.
	Reserved port number must not be used (refere to the manual)."
    ::= { wtWebGraphAnalog57761BinaryEntry 13 }

wtWebGraphAnalog57761BinaryUdpPeerRemotePort OBJECT-TYPE
    SYNTAX INTEGER (1..65535)
    ACCESS read-write
    STATUS mandatory
    DESCRIPTION
        "Port number of the remote device. A complete set of port number, IP address
        and a valid input/output mask starts this mode.
        No data exchange take place when setting the remote port to zero."
    ::= { wtWebGraphAnalog57761BinaryEntry 14 }

wtWebGraphAnalog57761BinaryUdpPeerRemoteIpAddr OBJECT-TYPE
    SYNTAX OCTET STRING
    ACCESS read-write
    STATUS mandatory
    DESCRIPTION
        "Ip address of the remote device. A complete set of port number, IP address
        and a valid input/output mask starts this mode.
        No data exchange take place when setting the remote device IP address to 0.0.0.0."
    ::= { wtWebGraphAnalog57761BinaryEntry 15 }

wtWebGraphAnalog57761BinaryUdpPeerInputTrigger OBJECT-TYPE
    SYNTAX OCTET STRING (SIZE (4))
    ACCESS read-write
    STATUS mandatory
    DESCRIPTION
        "Every change on the inputs causes their state to be transmitted to the
        remote device. To minimize data traffic, individual inputs may be exempted
        from this rule. Nevertheless every transmission will contain all input states.
        If a bit is set (1), a change of state on the corresponding input
        triggers a transmission. If the bit is not set (0), no transmission
        takes place.
        The OCTETS are interpreted bit-by-bit, with each bit corresponding to an input.
        Bit 0 corresponds to the LSB.
        OCTET 1: unused
        OCTET 2: unused
        OCTET 3: unused
        OCTET 4, Bit 0-1: Analog inputs 0-1"
    ::= { wtWebGraphAnalog57761BinaryEntry 16 }

wtWebGraphAnalog57761BinaryUdpPeerInterval OBJECT-TYPE
    SYNTAX INTEGER (0..65535)
    ACCESS read-write
    STATUS mandatory
    DESCRIPTION
        "Configurable interval with a 100ms base, in which the Webio device sends
        data to the configured remote device. A interval of zero stopps the
        periodical sending."
    ::= { wtWebGraphAnalog57761BinaryEntry 17 }

wtWebGraphAnalog57761BinaryUdpPeerApplicationMode OBJECT-TYPE
    SYNTAX OCTET STRING (SIZE (4))
    ACCESS read-write
    STATUS mandatory
    DESCRIPTION
        "Selection of the application mode:
        The OCTETS are interpreted bit-by-bit, with each bit corresponding to an output.
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebGraphAnalog57761BinaryEntry 18 }

wtWebGraphAnalog57761BinaryConnectedPort OBJECT-TYPE
    SYNTAX INTEGER (1..65535)
    ACCESS read-only
    STATUS mandatory
    DESCRIPTION
        "Port number of the remote device, after connection has been established.
        In case of no connection or missing port informations a zero will be read."
    ::= { wtWebGraphAnalog57761BinaryEntry 19 }

wtWebGraphAnalog57761BinaryConnectedIpAddr OBJECT-TYPE
    SYNTAX IpAddress
    ACCESS read-only
    STATUS mandatory
    DESCRIPTION
        "IP address of the remote device, after connection has been established.
        In case of no connection or missing port informations 0.0.0.0 will be read."
    ::= { wtWebGraphAnalog57761BinaryEntry 20 }

wtWebGraphAnalog57761BinaryTcpServerClientHttpPort OBJECT-TYPE
    SYNTAX INTEGER (1..65535)
    ACCESS read-write
    STATUS mandatory
    DESCRIPTION
        "HTTP port number of the remote device at TCP Server Mode. If an mailfunction occurs
        status informations will be send to this port.
        Not used at mode Compatible 50xxx."
    ::= { wtWebGraphAnalog57761BinaryEntry 21 }

wtWebGraphAnalog57761BinaryTcpClientServerHttpPort OBJECT-TYPE
    SYNTAX INTEGER (1..65535)
    ACCESS read-write
    STATUS mandatory
    DESCRIPTION
        "HTTP port number of the remote device at TCP Client Mode. In the operating mode
        Box2Box connection status informations will be exchanged through this port."
    ::= { wtWebGraphAnalog57761BinaryEntry 22 }

wtWebGraphAnalog57761BinaryTcpServerHysteresis1 OBJECT-TYPE
    SYNTAX OCTET STRING
    ACCESS read-write
    STATUS mandatory
    DESCRIPTION
        "A change greater than this value initiate a transmission of the corresponding input value.
        The input 1 must be selected at wtWebGraphAnalog57761BinaryTcpServerInputTrigger.
        With a hysteresis of zero any change will be transmitted."
    ::= { wtWebGraphAnalog57761BinaryEntry 23 }

wtWebGraphAnalog57761BinaryTcpServerHysteresis2 OBJECT-TYPE
    SYNTAX OCTET STRING
    ACCESS read-write
    STATUS mandatory
    DESCRIPTION
        "A change greater than this value initiate a transmission of the corresponding input value.
        The input 2 must be selected at wtWebGraphAnalog57761BinaryTcpServerInputTrigger.
        With a hysteresis of zero any change will be transmitted."
    ::= { wtWebGraphAnalog57761BinaryEntry 24 }

wtWebGraphAnalog57761BinaryTcpClientHysteresis1 OBJECT-TYPE
    SYNTAX OCTET STRING
    ACCESS read-write
    STATUS mandatory
    DESCRIPTION
        "A change greater than this value initiate a transmission of the corresponding input value.
        The input 1 must be selected at wtWebGraphAnalog57761BinaryTcpClientInputTrigger.
        With a hysteresis of zero any change will be transmitted."

      ::= { wtWebGraphAnalog57761BinaryEntry 25 }

wtWebGraphAnalog57761BinaryTcpClientHysteresis2 OBJECT-TYPE
    SYNTAX OCTET STRING
    ACCESS read-write
    STATUS mandatory
    DESCRIPTION
        "A change greater than this value initiate a transmission of the corresponding input value.
        The input 2 must be selected at wtWebGraphAnalog57761BinaryTcpClientInputTrigger.
        With a hysteresis of zero any change will be transmitted."

      ::= { wtWebGraphAnalog57761BinaryEntry 26 }

wtWebGraphAnalog57761BinaryUdpPeerHysteresis1 OBJECT-TYPE
    SYNTAX OCTET STRING
    ACCESS read-write
    STATUS mandatory
    DESCRIPTION
        "A change greater than this value initiate a transmission of the corresponding input value.
        The input 1 must be selected at wtWebGraphAnalog57761BinaryUdpPeerInputTrigger.
        With a hysteresis of zero any change will be transmitted."
    ::= { wtWebGraphAnalog57761BinaryEntry 27 }

wtWebGraphAnalog57761BinaryUdpPeerHysteresis2 OBJECT-TYPE
    SYNTAX OCTET STRING
    ACCESS read-write
    STATUS mandatory
    DESCRIPTION
        "A change greater than this value initiate a transmission of the corresponding input value.
        The input 2 must be selected at wtWebGraphAnalog57761BinaryUdpPeerInputTrigger.
        With a hysteresis of zero any change will be transmitted."
    ::= { wtWebGraphAnalog57761BinaryEntry 28 }

wtWebGraphAnalog57761BinaryTcpClientServerUserName OBJECT-TYPE
    SYNTAX OCTET STRING
    ACCESS read-write
    STATUS mandatory
    DESCRIPTION
        "Building a connection may be protected by a specific
        user name within the server. Enter the user name
        to establish the connection, if a user name entry
        exists."
    ::= { wtWebGraphAnalog57761BinaryEntry 29 }

--  wtWebGraphAnalog57761MQTT Group
--------------------------------

wtWebGraphAnalog57761MQTTEnable OBJECT-TYPE
    SYNTAX OCTET STRING
    ACCESS read-write
    STATUS mandatory
    DESCRIPTION
        "Bit 7 schaltet MQTT frei:
        Octet 1: ungenutzt
        Octet 2: ungenutzt
        Octet 3: ungenutzt
        Octet 4:
        	Bit 0-6: ungenutzt
                Bit 7  : MQTT enable"
    ::= { wtWebGraphAnalog57761MQTT 1 }

wtWebGraphAnalog57761MQTTBrockerIP OBJECT-TYPE
    SYNTAX OCTET STRING
    ACCESS read-write
    STATUS mandatory
    DESCRIPTION
        "Name or IP-address of the MQTT-Server."
    ::= { wtWebGraphAnalog57761MQTT 2 }

wtWebGraphAnalog57761MQTTUserName OBJECT-TYPE
    SYNTAX OCTET STRING
    ACCESS read-write
    STATUS mandatory
    DESCRIPTION
        "MQTT login  user name."
    ::= { wtWebGraphAnalog57761MQTT 3 }

wtWebGraphAnalog57761MQTTPassword OBJECT-TYPE
    SYNTAX OCTET STRING
    ACCESS read-write
    STATUS mandatory
    DESCRIPTION
        "MQTT login password."
    ::= { wtWebGraphAnalog57761MQTT 4 }

wtWebGraphAnalog57761MQTTLocalPort OBJECT-TYPE
    SYNTAX INTEGER
    ACCESS read-write
    STATUS mandatory
    DESCRIPTION
        "Local port number."
    ::= { wtWebGraphAnalog57761MQTT 5 }

wtWebGraphAnalog57761MQTTBrokerServerPort OBJECT-TYPE
    SYNTAX INTEGER
    ACCESS read-write
    STATUS mandatory
    DESCRIPTION
        "MQTT Server port number."
    ::= { wtWebGraphAnalog57761MQTT 6 }

wtWebGraphAnalog57761MQTTInterval OBJECT-TYPE
    SYNTAX INTEGER
    ACCESS read-write
    STATUS mandatory
    DESCRIPTION
        "Ping intervall, if no data has to be send: time in seconds."
    ::= { wtWebGraphAnalog57761MQTT 7 }

wtWebGraphAnalog57761MQTTLastWillEnable OBJECT-TYPE
    SYNTAX OCTET STRING
    ACCESS read-write
    STATUS mandatory
    DESCRIPTION
        "Bit 0 activate MQTT LastWill message:
        Octet 1: unused
        Octet 2: unused
        Octet 3: unused
        Octet 4:
        	Bit 1-7: unused
            Bit 0  : MQTT Last will enable"
    ::= { wtWebGraphAnalog57761MQTT 8 }

wtWebGraphAnalog57761MQTTLastWillTopic OBJECT-TYPE
    SYNTAX OCTET STRING
    ACCESS read-write
    STATUS mandatory
    DESCRIPTION
        "MQTT Last Will Topic."
    ::= { wtWebGraphAnalog57761MQTT 9 }

wtWebGraphAnalog57761MQTTLastWillMsg OBJECT-TYPE
    SYNTAX OCTET STRING
    ACCESS read-write
    STATUS mandatory
    DESCRIPTION
        "MQTT Last Will message."
    ::= { wtWebGraphAnalog57761MQTT 10 }

wtWebGraphAnalog57761MQTTLastWillQoS OBJECT-TYPE
    SYNTAX OCTET STRING (SIZE(4))
    ACCESS read-write
    STATUS mandatory
    DESCRIPTION
        "Binary coded MQTT Publish QoS:
        Octet 1: unused
        Octet 2: unused
        Octet 3: unused
        Octet 4:
		Bit 0:	QoS 0
        Bit 1:	QoS 1
        Bit 2:  QoS 2
        Bit 3-7:unused"
    ::= { wtWebGraphAnalog57761MQTT 11 }

wtWebGraphAnalog57761MQTTLastWillRetain OBJECT-TYPE
    SYNTAX OCTET STRING (SIZE(4))
    ACCESS read-write
    STATUS mandatory
    DESCRIPTION
        "Binary coded MQTT Publish Retain properties:
        Octet 1: unused
        Octet 2: unused
        Octet 3: unused
        Octet 4:
		Bit 0	: retain enable
        Bit 1-7	: unused"
    ::= { wtWebGraphAnalog57761MQTT 12 }

wtWebGraphAnalog57761MQTTLastWillConnectEnable OBJECT-TYPE
    SYNTAX OCTET STRING
    ACCESS read-write
    STATUS mandatory
    DESCRIPTION
        "Bit 0 activate MQTT LastWill Connect message:
        Octet 1: unused
        Octet 2: unused
        Octet 3: unused
        Octet 4:
        	Bit 1-7: unused
            Bit 0  : MQTT Last will connect message enable"
    ::= { wtWebGraphAnalog57761MQTT 13 }

wtWebGraphAnalog57761MQTTLastWillConnectMsg OBJECT-TYPE
    SYNTAX OCTET STRING
    ACCESS read-write
    STATUS mandatory
    DESCRIPTION
        "MQTT Last Will Connect message will be send with the QoS and Retain settings
		of the LastWill message."
    ::= { wtWebGraphAnalog57761MQTT 14 }

--  wtWebGraphAnalog57761REST Group
--------------------------------

wtWebGraphAnalog57761RESTEnable OBJECT-TYPE
    SYNTAX OCTET STRING
    ACCESS read-write
    STATUS mandatory
    DESCRIPTION
        "Bit 0 activates REST :
        Octet 1: unused
        Octet 2: unused
        Octet 3: unused
        Octet 4:
        	Bit 1-7: unused
            Bit 0  : REST enable"
    ::= { wtWebGraphAnalog57761REST 1 }

wtWebGraphAnalog57761RESTDigestAuthEnable OBJECT-TYPE
    SYNTAX OCTET STRING
    ACCESS read-write
    STATUS mandatory
    DESCRIPTION
        "Bit 0 activates Digest-Authentification:
        Octet 1: unused
        Octet 2: unused
        Octet 3: unused
        Octet 4:
        	Bit 1-7: unused
            Bit 0  : Digest Auth enable"
    ::= { wtWebGraphAnalog57761REST 2 }

-- wtWebGraphAnalog57761Datalogger Group
--------------------------------

wtWebGraphAnalog57761LoggerTimebase OBJECT-TYPE
    SYNTAX INTEGER {
    wtWebGraphAnalog57761Datalogger-15Sec(1),
    wtWebGraphAnalog57761Datalogger-30Sec(2),
    wtWebGraphAnalog57761Datalogger-1Min(3),
    wtWebGraphAnalog57761Datalogger-5Min(4),
    wtWebGraphAnalog57761Datalogger-15Min(5),
    wtWebGraphAnalog57761Datalogger-60Min(6)
    }
    ACCESS read-write
    STATUS mandatory
    DESCRIPTION
        "Time base of the data logger"
    ::= { wtWebGraphAnalog57761Datalogger 1 }

wtWebGraphAnalog57761LoggerSensorSel OBJECT-TYPE
    SYNTAX OCTET STRING (SIZE(4))
    ACCESS read-write
    STATUS mandatory
    DESCRIPTION
        "Binary coded trigger conditions:
        Octet 1: unused
        Octet 2: unused
        Octet 3: unused
        Octet 4:
        	Bit 0: Sensor 1
        	Bit 1: Sensor 2
        	Bit 2-7: unused"
    ::= { wtWebGraphAnalog57761Datalogger 2 }

-- wtWebGraphAnalog57761Alarm Group
----------------------------

wtWebGraphAnalog57761AlarmCount OBJECT-TYPE
    SYNTAX INTEGER (1..8)
    ACCESS read-only
    STATUS mandatory
    DESCRIPTION
        "Number of independent alarms."
    ::= { wtWebGraphAnalog57761Alarm 1 }

-- Alarm Interface Table

wtWebGraphAnalog57761AlarmIfTable OBJECT-TYPE
    SYNTAX SEQUENCE OF WtWebGraphAnalog57761AlarmIfEntry
    ACCESS not-accessible
    STATUS mandatory
    DESCRIPTION
        "List of alarm indices."
    ::= { wtWebGraphAnalog57761Alarm 2 }

wtWebGraphAnalog57761AlarmIfEntry OBJECT-TYPE
    SYNTAX WtWebGraphAnalog57761AlarmIfEntry
    ACCESS not-accessible
    STATUS mandatory
    DESCRIPTION
        "Numbers of the alarms."
    INDEX  { wtWebGraphAnalog57761AlarmNo }
    ::= { wtWebGraphAnalog57761AlarmIfTable 1 }

WtWebGraphAnalog57761AlarmIfEntry ::= SEQUENCE {
    wtWebGraphAnalog57761AlarmNo INTEGER
}

wtWebGraphAnalog57761AlarmNo OBJECT-TYPE
    SYNTAX INTEGER (1..8)
    ACCESS read-only
    STATUS mandatory
    DESCRIPTION
        "Alarm number."
    ::= { wtWebGraphAnalog57761AlarmIfEntry 1 }

-- Alarm Table

wtWebGraphAnalog57761AlarmTable OBJECT-TYPE
    SYNTAX SEQUENCE OF WtWebGraphAnalog57761AlarmEntry
    ACCESS not-accessible
    STATUS mandatory
    DESCRIPTION
        "List of settings depending on the alarm number."
    ::= { wtWebGraphAnalog57761Alarm 3 }

wtWebGraphAnalog57761AlarmEntry OBJECT-TYPE
    SYNTAX WtWebGraphAnalog57761AlarmEntry
    ACCESS not-accessible
    STATUS mandatory
    DESCRIPTION
        "Alarm parameters of the individual alarms."
    INDEX  { wtWebGraphAnalog57761AlarmNo }
    ::= { wtWebGraphAnalog57761AlarmTable 1 }

WtWebGraphAnalog57761AlarmEntry ::= SEQUENCE {
    wtWebGraphAnalog57761AlarmTrigger			OCTET STRING,
    wtWebGraphAnalog57761AlarmMin1			OCTET STRING,
    wtWebGraphAnalog57761AlarmMax1			OCTET STRING,
    wtWebGraphAnalog57761AlarmHysteresis1		OCTET STRING,
    wtWebGraphAnalog57761AlarmDelay			OCTET STRING,
    wtWebGraphAnalog57761AlarmInterval			OCTET STRING,
    wtWebGraphAnalog57761AlarmEnable			OCTET STRING,
    wtWebGraphAnalog57761AlarmEMailAddr			OCTET STRING,
    wtWebGraphAnalog57761AlarmMailSubject		OCTET STRING,
    wtWebGraphAnalog57761AlarmMailText			OCTET STRING,
    wtWebGraphAnalog57761AlarmManagerIP			OCTET STRING,
    wtWebGraphAnalog57761AlarmTrapText			OCTET STRING,
    wtWebGraphAnalog57761AlarmMailOptions		OCTET STRING,
    wtWebGraphAnalog57761AlarmTcpIpAddr			OCTET STRING,
    wtWebGraphAnalog57761AlarmTcpPort			INTEGER,
    wtWebGraphAnalog57761AlarmTcpText			OCTET STRING,
    wtWebGraphAnalog57761AlarmClearMailSubject		OCTET STRING,
    wtWebGraphAnalog57761AlarmClearMailText		OCTET STRING,
    wtWebGraphAnalog57761AlarmClearTrapText		OCTET STRING,
    wtWebGraphAnalog57761AlarmClearTcpText		OCTET STRING,
    wtWebGraphAnalog57761AlarmMin2			OCTET STRING,
    wtWebGraphAnalog57761AlarmMax2			OCTET STRING,
    wtWebGraphAnalog57761AlarmHysteresis2		OCTET STRING,
    wtWebGraphAnalog57761AlarmSyslogIpAddr		OCTET STRING,
    wtWebGraphAnalog57761AlarmSyslogPort		INTEGER,
    wtWebGraphAnalog57761AlarmSyslogText		OCTET STRING,
    wtWebGraphAnalog57761AlarmSyslogClearText		OCTET STRING,
    wtWebGraphAnalog57761AlarmFtpDataPort		OCTET STRING,
    wtWebGraphAnalog57761AlarmFtpFileName		OCTET STRING,
    wtWebGraphAnalog57761AlarmFtpText			OCTET STRING,
    wtWebGraphAnalog57761AlarmFtpClearText		OCTET STRING,
    wtWebGraphAnalog57761AlarmFtpOption			OCTET STRING,
    wtWebGraphAnalog57761AlarmTimerCron			OCTET STRING,
    wtWebGraphAnalog57761AlarmDeltaTemp			OCTET STRING,
    wtWebGraphAnalog57761AlarmName 				OCTET STRING,
    wtWebGraphAnalog57761AlarmActive 			OCTET STRING,
    wtWebGraphAnalog57761AlarmHttpReqAuthEnable		OCTET STRING,
    wtWebGraphAnalog57761AlarmHttpReqAuthUser		OCTET STRING,
    wtWebGraphAnalog57761AlarmHttpReqAuthPassword		OCTET STRING,
    wtWebGraphAnalog57761AlarmHttpReqSetUrl			OCTET STRING,
    wtWebGraphAnalog57761AlarmHttpReqClearUrl		OCTET STRING,
    wtWebGraphAnalog57761AlarmHttpReqServerPort		INTEGER,
    wtWebGraphAnalog57761AlarmMqttTopicPath			OCTET STRING,
    wtWebGraphAnalog57761AlarmMqttTopicSetTopic		OCTET STRING,
    wtWebGraphAnalog57761AlarmMqttTopicClear		OCTET STRING,
    wtWebGraphAnalog57761AlarmSensorLostSelection		OCTET STRING,
    wtWebGraphAnalog57761AlarmLimitWindow			OCTET STRING,
    wtWebGraphAnalog57761AlarmSnmpManagerPort		INTEGER,
    wtWebGraphAnalog57761AlarmMqttQoS			OCTET STRING,
    wtWebGraphAnalog57761AlarmMqttRetain			OCTET STRING

}

wtWebGraphAnalog57761AlarmTrigger OBJECT-TYPE
    SYNTAX OCTET STRING (SIZE(4))
    ACCESS read-write
    STATUS mandatory
    DESCRIPTION
        "Binary coded trigger conditions:
        Octet 1: unused
        Octet 2: unused
        Octet 3:
        	Bit 0: Timer
        	Bit 1: ColdStart
        	Bit 2: WarmStart

        Octet 4:
        	Bit 0: Sensor 1
        	Bit 1: Sensor 2
        	Bit 2-7: unused"
    ::= { wtWebGraphAnalog57761AlarmEntry 1 }

wtWebGraphAnalog57761AlarmMin1 OBJECT-TYPE
    SYNTAX OCTET STRING
    ACCESS read-write
    STATUS mandatory
    DESCRIPTION
        "Minimum sensor 1 with maximum 3 decimal places."
    ::= { wtWebGraphAnalog57761AlarmEntry 2 }

wtWebGraphAnalog57761AlarmMax1 OBJECT-TYPE
    SYNTAX OCTET STRING
    ACCESS read-write
    STATUS mandatory
    DESCRIPTION
        "Maximum sensor 1 with maximum 3 decimal places."
    ::= { wtWebGraphAnalog57761AlarmEntry 3 }

wtWebGraphAnalog57761AlarmHysteresis1 OBJECT-TYPE
    SYNTAX OCTET STRING
    ACCESS read-write
    STATUS mandatory
    DESCRIPTION
        "Reading changes of this size clears the alarm state (MAX-hyst, MIN+hyst.)
        with maximum 3 decimal places."
    ::= { wtWebGraphAnalog57761AlarmEntry 4 }

wtWebGraphAnalog57761AlarmDelay OBJECT-TYPE
    SYNTAX OCTET STRING
    ACCESS read-write
    STATUS mandatory
    DESCRIPTION
        "Alarm will be delayed by setting this time while stable alarm
        condition occur (time in minutes)."
    ::= { wtWebGraphAnalog57761AlarmEntry 5 }


wtWebGraphAnalog57761AlarmInterval OBJECT-TYPE
    SYNTAX OCTET STRING
    ACCESS read-write
    STATUS mandatory
    DESCRIPTION
        "Send interval for alarm messages."
    ::= { wtWebGraphAnalog57761AlarmEntry 6 }

wtWebGraphAnalog57761AlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  TCP Client enable
        	Bit 3:	Syslog enable
        	Bit 4:  FTP Client enable"
    ::= { wtWebGraphAnalog57761AlarmEntry 7 }

wtWebGraphAnalog57761AlarmEMailAddr OBJECT-TYPE
    SYNTAX OCTET STRING
    ACCESS read-write
    STATUS mandatory
    DESCRIPTION
        "E-Mail address for sending the alarm mail to."
    ::= { wtWebGraphAnalog57761AlarmEntry 8 }

wtWebGraphAnalog57761AlarmMailSubject OBJECT-TYPE
    SYNTAX OCTET STRING
    ACCESS read-write
    STATUS mandatory
    DESCRIPTION
        "Subject line for alarm mail."
    ::= { wtWebGraphAnalog57761AlarmEntry 9 }

wtWebGraphAnalog57761AlarmMailText OBJECT-TYPE
    SYNTAX OCTET STRING
    ACCESS read-write
    STATUS mandatory
    DESCRIPTION
        "Alarm mail text: <Mn> provides the current temperature; n = 1..2.
        <Z> provides the current time."
    ::= { wtWebGraphAnalog57761AlarmEntry 10 }

wtWebGraphAnalog57761AlarmManagerIP OBJECT-TYPE
    SYNTAX OCTET STRING
    ACCESS read-write
    STATUS mandatory
    DESCRIPTION
        "Name or IP address of the SNMP Manager which accepts the trap."
    ::= { wtWebGraphAnalog57761AlarmEntry 11 }

wtWebGraphAnalog57761AlarmTrapText OBJECT-TYPE
    SYNTAX OCTET STRING
    ACCESS read-write
    STATUS mandatory
    DESCRIPTION
        "This text is sent in the trap body."
    ::= { wtWebGraphAnalog57761AlarmEntry 12 }

wtWebGraphAnalog57761AlarmMailOptions OBJECT-TYPE
    SYNTAX OCTET STRING (SIZE(4))
    ACCESS read-write
    STATUS mandatory
    DESCRIPTION
        "Binary coded options:
        Octet 1: unused
        Octet 2: unused
        Octet 3: unused
        Octet 4:
		Bit 0  :	Attach Logger.csv Enable
		Bit 1  :	CSV-Data_since_last_report
        	Bit 2-7:	unused"
    ::= { wtWebGraphAnalog57761AlarmEntry 13 }

wtWebGraphAnalog57761AlarmTcpIpAddr OBJECT-TYPE
    SYNTAX OCTET STRING
    ACCESS read-write
    STATUS mandatory
    DESCRIPTION
        "Name or IP address of the TCP server which accepts the trap."
    ::= { wtWebGraphAnalog57761AlarmEntry 14 }

wtWebGraphAnalog57761AlarmTcpPort OBJECT-TYPE
    SYNTAX INTEGER (1..65535)
    ACCESS read-write
    STATUS mandatory
    DESCRIPTION
        "Port number of the TCP server which accepts the trap."
    ::= { wtWebGraphAnalog57761AlarmEntry 15 }

wtWebGraphAnalog57761AlarmTcpText OBJECT-TYPE
    SYNTAX OCTET STRING
    ACCESS read-write
    STATUS mandatory
    DESCRIPTION
        "This text is sent in the TCP trap body."
    ::= { wtWebGraphAnalog57761AlarmEntry 16 }

wtWebGraphAnalog57761AlarmClearMailSubject OBJECT-TYPE
    SYNTAX OCTET STRING
    ACCESS read-write
    STATUS mandatory
    DESCRIPTION
        "Subject line for alarm clear mail."
    ::= { wtWebGraphAnalog57761AlarmEntry 17 }

wtWebGraphAnalog57761AlarmClearMailText OBJECT-TYPE
    SYNTAX OCTET STRING
    ACCESS read-write
    STATUS mandatory
    DESCRIPTION
        "Alarm clear mail text: <Mn> provides the current temperature; n = 1..2.
        <Z> provides the current time."
    ::= { wtWebGraphAnalog57761AlarmEntry 18 }

wtWebGraphAnalog57761AlarmClearTrapText OBJECT-TYPE
    SYNTAX OCTET STRING
    ACCESS read-write
    STATUS mandatory
    DESCRIPTION
        "This text is sent in the trap body."
    ::= { wtWebGraphAnalog57761AlarmEntry 19 }

wtWebGraphAnalog57761AlarmClearTcpText OBJECT-TYPE
    SYNTAX OCTET STRING
    ACCESS read-write
    STATUS mandatory
    DESCRIPTION
        "This text is sent in the TCP trap body."
    ::= { wtWebGraphAnalog57761AlarmEntry 20 }

wtWebGraphAnalog57761AlarmMin2 OBJECT-TYPE
    SYNTAX OCTET STRING
    ACCESS read-write
    STATUS mandatory
    DESCRIPTION
        "Minimum sensor 2 with maximum 3 decimal places."
    ::= { wtWebGraphAnalog57761AlarmEntry 21 }

wtWebGraphAnalog57761AlarmMax2 OBJECT-TYPE
    SYNTAX OCTET STRING
    ACCESS read-write
    STATUS mandatory
    DESCRIPTION
        "Maximum sensor 2 with maximum 2 decimal places."
    ::= { wtWebGraphAnalog57761AlarmEntry 22 }

wtWebGraphAnalog57761AlarmHysteresis2 OBJECT-TYPE
    SYNTAX OCTET STRING
    ACCESS read-write
    STATUS mandatory
    DESCRIPTION
        "Hysterese rel. sensor 2 with maximum 3 decimal places."
    ::= { wtWebGraphAnalog57761AlarmEntry 23 }

wtWebGraphAnalog57761AlarmSyslogIpAddr OBJECT-TYPE
    SYNTAX OCTET STRING
    ACCESS read-write
    STATUS mandatory
    DESCRIPTION
        "IP address of the syslog server to which the Webio device should send syslog messages."
    ::= { wtWebGraphAnalog57761AlarmEntry 24 }

wtWebGraphAnalog57761AlarmSyslogPort OBJECT-TYPE
    SYNTAX INTEGER (1..65535)
    ACCESS read-write
    STATUS mandatory
    DESCRIPTION
        "Port number of the syslog server to which the Webio device should send syslog messages."
    ::= { wtWebGraphAnalog57761AlarmEntry 25 }

wtWebGraphAnalog57761AlarmSyslogText OBJECT-TYPE
    SYNTAX OCTET STRING
    ACCESS read-write
    STATUS mandatory
    DESCRIPTION
        "Every message starts with the priority key, a time stamp and the host ip address, according RFC3164.
        This text appears in the following syslog message body."
    ::= { wtWebGraphAnalog57761AlarmEntry 26 }

wtWebGraphAnalog57761AlarmSyslogClearText OBJECT-TYPE
    SYNTAX OCTET STRING
    ACCESS read-write
    STATUS mandatory
    DESCRIPTION
        "Every message starts with the priority key, a time stamp and the host ip address, according RFC3164.
        This text appears in the following syslog message body of a alarm clear message."
    ::= { wtWebGraphAnalog57761AlarmEntry 27 }

wtWebGraphAnalog57761AlarmFtpDataPort OBJECT-TYPE
    SYNTAX OCTET STRING
    ACCESS read-write
    STATUS mandatory
    DESCRIPTION
        "Local data port: 1..65535 or AUTO: the next free port will be assigned."
    ::= { wtWebGraphAnalog57761AlarmEntry 28 }

wtWebGraphAnalog57761AlarmFtpFileName OBJECT-TYPE
    SYNTAX OCTET STRING
    ACCESS read-write
    STATUS mandatory
    DESCRIPTION
        "Name of the file including path informations."
    ::= { wtWebGraphAnalog57761AlarmEntry 29 }

wtWebGraphAnalog57761AlarmFtpText OBJECT-TYPE
    SYNTAX OCTET STRING
    ACCESS read-write
    STATUS mandatory
    DESCRIPTION
        "Message text to store on the FTP server."
    ::= { wtWebGraphAnalog57761AlarmEntry 30 }

wtWebGraphAnalog57761AlarmFtpClearText OBJECT-TYPE
    SYNTAX OCTET STRING
    ACCESS read-write
    STATUS mandatory
    DESCRIPTION
        "Alarm clear message to store on the FTP server."
    ::= { wtWebGraphAnalog57761AlarmEntry 31 }

wtWebGraphAnalog57761AlarmFtpOption OBJECT-TYPE
    SYNTAX OCTET STRING (SIZE(4))
    ACCESS read-write
    STATUS mandatory
    DESCRIPTION
        "Binary coded options, select only one option at the same time:
        STORE  = replace file
        APPEND = append message at the end of the file

        Octet 1: unused
        Octet 2: unused
        Octet 3: unused
        Octet 4:
		Bit 0  :	STORE
		Bit 1  :	APPEND
        	Bit 2-7:	unused"
    ::= { wtWebGraphAnalog57761AlarmEntry 32 }

wtWebGraphAnalog57761AlarmTimerCron OBJECT-TYPE
    SYNTAX OCTET STRING
    ACCESS read-write
    STATUS mandatory
    DESCRIPTION
        "This entry defines a time window for alarm 1-8 and a activation time for the report.
        A time window is definied by start and stop time stamp, seperated by a space or tab.
        The activation time of the report is defined by a single start time stamp.
        Each time stamp contains 5 space or tab seperated text fields for time trigger definition.
        Each field must match with the actual time to trigger an action, weekday and day of month
        are interpreted separatley.
        1: Minutes	Range 0-59
        2. Hours	Range 0-23, 0 is midnight
        3: Day of month	Range 1-31
        4: Month	Range 1-12
        5: Weekday	Range 0-6, 0 is sunday

        Syntax for every field:
         - an asterix (*) enables every possible setting of a field
         - single numbers seperated by commas (i.e.: 2,14,22)
         - a partition within the allowed range (i.e.: 1-5)
         - step size within a partition of the allowed range (i.e.: 0-59/2  every second minute)."
    ::= { wtWebGraphAnalog57761AlarmEntry 33 }

-- __JB__
wtWebGraphAnalog57761AlarmName OBJECT-TYPE
    SYNTAX OCTET STRING
    ACCESS read-write
    STATUS mandatory
    DESCRIPTION
        "Alert name"
    ::= { wtWebGraphAnalog57761AlarmEntry 39 }

-- __JB__
wtWebGraphAnalog57761AlarmActive OBJECT-TYPE
    SYNTAX OCTET STRING
    ACCESS read-write
    STATUS mandatory
    DESCRIPTION
        "Alert active
			1 = ON
			0 = OFF"
    ::= { wtWebGraphAnalog57761AlarmEntry 40 }

wtWebGraphAnalog57761AlarmHttpReqAuthEnable OBJECT-TYPE
    SYNTAX OCTET STRING
    ACCESS read-write
    STATUS mandatory
    DESCRIPTION
        "Binary coded options, select only one option at the same time:
        OCTET 1: unused
        OCTET 2: unused
        OCTET 3: unused
        OCTET 4, Bit 1-7: unused
        Bit 0  : HHTP Request Authentication enable"
    ::= { wtWebGraphAnalog57761AlarmEntry 61 }

wtWebGraphAnalog57761AlarmHttpReqAuthUser OBJECT-TYPE
    SYNTAX OCTET STRING
    ACCESS read-write
    STATUS mandatory
    DESCRIPTION
	"HTTP Request: User"
    ::= { wtWebGraphAnalog57761AlarmEntry 62 }

wtWebGraphAnalog57761AlarmHttpReqAuthPassword OBJECT-TYPE
    SYNTAX OCTET STRING
    ACCESS read-write
    STATUS mandatory
    DESCRIPTION
	"HTTP Request: Password"
    ::= { wtWebGraphAnalog57761AlarmEntry 63 }

wtWebGraphAnalog57761AlarmHttpReqSetUrl OBJECT-TYPE
    SYNTAX OCTET STRING
    ACCESS read-write
    STATUS mandatory
    DESCRIPTION
	"HTTP Request: Set URL"
    ::= { wtWebGraphAnalog57761AlarmEntry 64 }

wtWebGraphAnalog57761AlarmHttpReqClearUrl OBJECT-TYPE
    SYNTAX OCTET STRING
    ACCESS read-write
    STATUS mandatory
    DESCRIPTION
	"HTTP Request: Clear URL"
    ::= { wtWebGraphAnalog57761AlarmEntry 65 }

wtWebGraphAnalog57761AlarmHttpReqServerPort OBJECT-TYPE
    SYNTAX INTEGER (1..65535)
    ACCESS read-write
    STATUS mandatory
    DESCRIPTION
	"HTTP Request: Server Port"
    ::= { wtWebGraphAnalog57761AlarmEntry 66 }

wtWebGraphAnalog57761AlarmMqttTopicPath OBJECT-TYPE
    SYNTAX OCTET STRING
    ACCESS read-write
    STATUS mandatory
    DESCRIPTION
	"MQTT Publish: Topic path"
    ::= { wtWebGraphAnalog57761AlarmEntry 67 }

wtWebGraphAnalog57761AlarmMqttTopicSetTopic OBJECT-TYPE
    SYNTAX OCTET STRING
    ACCESS read-write
    STATUS mandatory
    DESCRIPTION
	"MQTT Publish: Topic SET message"
    ::= { wtWebGraphAnalog57761AlarmEntry 68 }

wtWebGraphAnalog57761AlarmMqttTopicClear OBJECT-TYPE
    SYNTAX OCTET STRING
    ACCESS read-write
    STATUS mandatory
    DESCRIPTION
	"MQTT Publish: Topic CLEAR message"
    ::= { wtWebGraphAnalog57761AlarmEntry 69 }

wtWebGraphAnalog57761AlarmSensorLostSelection OBJECT-TYPE
    SYNTAX OCTET STRING
    ACCESS read-write
    STATUS mandatory
    DESCRIPTION
        "Binary coded options:
        OCTET 1: unused
        OCTET 2: unused
        OCTET 3: unused
        OCTET 4, Bit 1-7: unused
        Bit 0  : Sensor 0"
    ::= { wtWebGraphAnalog57761AlarmEntry 70 }

wtWebGraphAnalog57761AlarmLimitWindow OBJECT-TYPE
    SYNTAX OCTET STRING
    ACCESS read-write
    STATUS mandatory
    DESCRIPTION
        "If window type is INSIDE the alarm is genereted when the temperature
        is greater minumum value and lower than maximum value. If window type is OUTSIDE
        the alarm is generated when the measured value is lower than the minimum value
        or greater than the maximum value.
		Binary coded options, select only one option at the same time:
        OCTET 1: unused
        OCTET 2: unused
        OCTET 3: unused
        OCTET 4, Bit 2-7: unused
		Bit 1  : inside window
        Bit 0  : outside window"
    ::= { wtWebGraphAnalog57761AlarmEntry 71 }

wtWebGraphAnalog57761AlarmSnmpManagerPort OBJECT-TYPE
    SYNTAX INTEGER
    ACCESS read-write
    STATUS mandatory
    DESCRIPTION
        "Port number of the SNMP Manager to which the Webio device should send SNMP traps."
    ::= { wtWebGraphAnalog57761AlarmEntry 76 }

wtWebGraphAnalog57761AlarmMqttQoS OBJECT-TYPE
    SYNTAX OCTET STRING (SIZE(4))
    ACCESS read-write
    STATUS mandatory
    DESCRIPTION
        "Binary coded value:
        Octet 1: unused
        Octet 2: unused
        Octet 3: unused
        Octet 4:
		Bit 0:	QoS 0
        	Bit 1:	QoS 1
        	Bit 2:  QoS 2
        	Bit 3-7:unused"
    ::= { wtWebGraphAnalog57761AlarmEntry 77 }

wtWebGraphAnalog57761AlarmMqttRetain OBJECT-TYPE
    SYNTAX OCTET STRING (SIZE(4))
    ACCESS read-write
    STATUS mandatory
    DESCRIPTION
        "Binary coded value:
        Octet 1: unused
        Octet 2: unused
        Octet 3: unused
        Octet 4:
		Bit 0	: retain enable
        	Bit 1-7	: unused"
    ::= { wtWebGraphAnalog57761AlarmEntry 78 }

-- wtWebGraphAnalog57761GraphicsBase Group
----------------------------

wtWebGraphAnalog57761GraphicsBaseEnable OBJECT-TYPE
    SYNTAX OCTET STRING
    ACCESS read-write
    STATUS mandatory
    DESCRIPTION
        "Defines the viewing options of the graphic:
        Octet 1: unused
        Octet 2: unused
        Octet 3: unused
        Octet 4:
                Bit 0  : Auto scroll enable
                Bit 1  : Show table
                Bit 2  : Show graph
                Bit 3  : Show control buttons
                Bit 4  : Show config menu
                Bit 5-7: unused"
    ::= { wtWebGraphAnalog57761GraphicsBase 1 }

wtWebGraphAnalog57761GraphicsBaseWidth OBJECT-TYPE
    SYNTAX INTEGER
    ACCESS read-write
    STATUS mandatory
    DESCRIPTION
        "Defines the width of the graphic in pixels."
    ::= { wtWebGraphAnalog57761GraphicsBase 2 }

wtWebGraphAnalog57761GraphicsBaseHeight OBJECT-TYPE
        SYNTAX INTEGER
        ACCESS read-write
        STATUS mandatory
        DESCRIPTION
            "Defines the height of the graphic in pixels."
        ::= { wtWebGraphAnalog57761GraphicsBase 3 }

wtWebGraphAnalog57761GraphicsBaseFrameColor OBJECT-TYPE
    SYNTAX OCTET STRING (SIZE(3))
    ACCESS read-write
    STATUS mandatory
    DESCRIPTION
        "Frame color definition in RGB."
    ::= { wtWebGraphAnalog57761GraphicsBase 4 }

wtWebGraphAnalog57761GraphicsBaseBackgroundColor OBJECT-TYPE
    SYNTAX OCTET STRING (SIZE(3))
    ACCESS read-write
    STATUS mandatory
    DESCRIPTION
        "Background color definition in RGB."
    ::= { wtWebGraphAnalog57761GraphicsBase 5 }

wtWebGraphAnalog57761GraphicsBasePollingrate OBJECT-TYPE
        SYNTAX INTEGER
        ACCESS read-write
        STATUS mandatory
        DESCRIPTION
            "Defines the pollingrate in seconds,
            which defines the refreshing intervall of the graphic."
        ::= { wtWebGraphAnalog57761GraphicsBase 6 }

-- wtWebGraphAnalog57761GraphicsSelect Group
----------------------------

wtWebGraphAnalog57761GraphicsSelectDisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1: Sensor 2
        	Bit 2-7: unused"
    ::= { wtWebGraphAnalog57761GraphicsSelect 1 }

wtWebGraphAnalog57761GraphicsSelectDisplayShowExtrem OBJECT-TYPE
    SYNTAX OCTET STRING (SIZE(4))
    ACCESS read-write
    STATUS mandatory
    DESCRIPTION
        "Binary coded sensor selection:
        only selected sensors will be shown with minima and maxima:
        Octet 1: unused
        Octet 2: unused
        Octet 3: unused
        Octet 4:
        	Bit 0: Sensor 1
        	Bit 1: Sensor 2
        	Bit 2-7: unused"
     ::= { wtWebGraphAnalog57761GraphicsSelect 2 }

-- Graph Sensor Color Table

wtWebGraphAnalog57761SensorColor2Table OBJECT-TYPE
    SYNTAX SEQUENCE OF WtWebGraphAnalog57761SensorColor2Entry
    ACCESS not-accessible
    STATUS mandatory
    DESCRIPTION
        "List of sensor colors for the praphical presentation."
    ::= { wtWebGraphAnalog57761GraphicsSelect 3 }

wtWebGraphAnalog57761SensorColor2Entry OBJECT-TYPE
    SYNTAX WtWebGraphAnalog57761SensorColor2Entry
    ACCESS not-accessible
    STATUS mandatory
    DESCRIPTION
        "Numbers of the sensors."
    INDEX  { wtWebGraphAnalog57761SensorNo }
    ::= { wtWebGraphAnalog57761SensorColor2Table 1 }

WtWebGraphAnalog57761SensorColor2Entry ::= SEQUENCE {
    wtWebGraphAnalog57761GraphicsSensorColor OCTET STRING,
    wtWebGraphAnalog57761GraphicsSelectScale OCTET STRING
}

wtWebGraphAnalog57761GraphicsSensorColor OBJECT-TYPE
    SYNTAX OCTET STRING (SIZE(3))
    ACCESS read-write
    STATUS mandatory
    DESCRIPTION
        "Color of the sensors at the praphical presention."
    ::= { wtWebGraphAnalog57761SensorColor2Entry 1 }

wtWebGraphAnalog57761GraphicsSelectScale OBJECT-TYPE
    SYNTAX OCTET STRING
    ACCESS read-write
    STATUS mandatory
    DESCRIPTION
        "Assignes one of 4 scales to a sensor:
        Octet 1: unused
        Octet 2: unused
        Octet 3: unused
        Octet 4:
                Bit 0  : Use Scale 1
                Bit 1  : Use Scale 2
                Bit 2-7: unused"
    ::= { wtWebGraphAnalog57761SensorColor2Entry 2 }

-- wtWebGraphAnalog57761GraphicsScale Group
----------------------------

wtWebGraphAnalog57761GraphicsScaleAutoScaleEnable OBJECT-TYPE
    SYNTAX OCTET STRING
    ACCESS read-write
    STATUS mandatory
    DESCRIPTION
        "Select the Auto Scale Mode:
        Octet 1: unused
        Octet 2: unused
        Octet 3: unused
        Octet 4:
                Bit 0  : Scale 1 Auto scale enable
                Bit 1  : Scale 2 Auto scale enable
                Bit 2-7: unused"
    ::= { wtWebGraphAnalog57761GraphicsScale 1 }


wtWebGraphAnalog57761GraphicsScaleAutoFitEnable OBJECT-TYPE
    SYNTAX OCTET STRING
    ACCESS read-write
    STATUS mandatory
    DESCRIPTION
        "Select the Auto Fit Mode::
        Octet 1: unused
        Octet 2: unused
        Octet 3: unused
        Octet 4:
                Bit 0  : Scale 1 Auto fit enable
                Bit 1  : Scale 2 Auto fit enable
                Bit 2-7: unused"
    ::= { wtWebGraphAnalog57761GraphicsScale 2 }

wtWebGraphAnalog57761GraphicsScale1Min OBJECT-TYPE
    SYNTAX INTEGER
    ACCESS read-only
    STATUS mandatory
    DESCRIPTION
        "Scale 1: Minimum."
    ::= { wtWebGraphAnalog57761GraphicsScale 3 }

wtWebGraphAnalog57761GraphicsScale2Min OBJECT-TYPE
    SYNTAX INTEGER
    ACCESS read-only
    STATUS mandatory
    DESCRIPTION
        "Scale 2: Minimum."
    ::= { wtWebGraphAnalog57761GraphicsScale 4 }

wtWebGraphAnalog57761GraphicsScale1Max OBJECT-TYPE
    SYNTAX INTEGER
    ACCESS read-only
    STATUS mandatory
    DESCRIPTION
        "Scale 1: Maximum."
    ::= { wtWebGraphAnalog57761GraphicsScale 7 }

wtWebGraphAnalog57761GraphicsScale2Max OBJECT-TYPE
    SYNTAX INTEGER
    ACCESS read-only
    STATUS mandatory
    DESCRIPTION
        "Scale 2: Maximum."
    ::= { wtWebGraphAnalog57761GraphicsScale 8 }

wtWebGraphAnalog57761GraphicsScale1Unit OBJECT-TYPE
    SYNTAX OCTET STRING
    ACCESS read-only
    STATUS mandatory
    DESCRIPTION
        "Scale 1: Unit."
    ::= { wtWebGraphAnalog57761GraphicsScale 11 }

wtWebGraphAnalog57761GraphicsScale2Unit OBJECT-TYPE
    SYNTAX OCTET STRING
    ACCESS read-only
    STATUS mandatory
    DESCRIPTION
        "Scale 2: Unit."
    ::= { wtWebGraphAnalog57761GraphicsScale 12 }

-- wtWebGraphAnalog57761Ports Group
----------------------------

-- Table

wtWebGraphAnalog57761PortTable OBJECT-TYPE
    SYNTAX SEQUENCE OF WtWebGraphAnalog57761PortEntry
    ACCESS not-accessible
    STATUS mandatory
    DESCRIPTION
        "List of settings depending on the sensor number."
    ::= { wtWebGraphAnalog57761Ports 1 }

wtWebGraphAnalog57761PortEntry OBJECT-TYPE
    SYNTAX WtWebGraphAnalog57761PortEntry
    ACCESS not-accessible
    STATUS mandatory
    DESCRIPTION
        "Sensor parameters for the individual sensors."
    INDEX  { wtWebGraphAnalog57761SensorNo }
    ::= { wtWebGraphAnalog57761PortTable 1 }

WtWebGraphAnalog57761PortEntry ::= SEQUENCE {
    wtWebGraphAnalog57761PortName		OCTET STRING,
    wtWebGraphAnalog57761PortText		OCTET STRING,
    wtWebGraphAnalog57761PortOffset1		OCTET STRING,
    wtWebGraphAnalog57761SetPoint1		OCTET STRING,
    wtWebGraphAnalog57761PortOffset2		OCTET STRING,
    wtWebGraphAnalog57761SetPoint2		OCTET STRING,
    wtWebGraphAnalog57761PortComment		OCTET STRING,
    wtWebGraphAnalog57761PortSensorSelect	OCTET STRING,
    wtWebGraphAnalog57761PortUnit		OCTET STRING,
    wtWebGraphAnalog57761PortScale0		OCTET STRING,
    wtWebGraphAnalog57761PortScale100		OCTET STRING,
    wtWebGraphAnalog57761PortOutputMode		OCTET STRING,
    wtWebGraphAnalog57761PortInputMode		OCTET STRING,
    wtWebGraphAnalog57761PortPresetValue	OCTET STRING
}

wtWebGraphAnalog57761PortName OBJECT-TYPE
    SYNTAX OCTET STRING
    ACCESS read-write
    STATUS mandatory
    DESCRIPTION
        "Name of the sensor."
    ::= { wtWebGraphAnalog57761PortEntry 1 }

wtWebGraphAnalog57761PortText OBJECT-TYPE
    SYNTAX OCTET STRING
    ACCESS read-write
    STATUS mandatory
    DESCRIPTION
        "Description of the sensor."
    ::= { wtWebGraphAnalog57761PortEntry 2 }

wtWebGraphAnalog57761PortOffset1 OBJECT-TYPE
    SYNTAX OCTET STRING
    ACCESS read-write
    STATUS mandatory
    DESCRIPTION
        "Offset calibration: Offset in degrees with maximum 3 decimal places at set point 1."
    ::= { wtWebGraphAnalog57761PortEntry 3 }

wtWebGraphAnalog57761SetPoint1 OBJECT-TYPE
    SYNTAX OCTET STRING
    ACCESS read-write
    STATUS mandatory
    DESCRIPTION
        "Offset calibration: Reference set point 1 in degrees with maximum 3 decimal places."
    ::= { wtWebGraphAnalog57761PortEntry 4 }

wtWebGraphAnalog57761PortOffset2 OBJECT-TYPE
    SYNTAX OCTET STRING
    ACCESS read-write
    STATUS mandatory
    DESCRIPTION
        "Offset calibration: Offset in degrees with maximum 3 decimal places at set point 2."
    ::= { wtWebGraphAnalog57761PortEntry 5 }

wtWebGraphAnalog57761SetPoint2 OBJECT-TYPE
    SYNTAX OCTET STRING
    ACCESS read-write
    STATUS mandatory
    DESCRIPTION
        "Offset calibration: Reference set point 2 in degrees with maximum 3 decimal places."
    ::= { wtWebGraphAnalog57761PortEntry 6 }

wtWebGraphAnalog57761PortComment OBJECT-TYPE
    SYNTAX OCTET STRING
    ACCESS read-write
    STATUS mandatory
    DESCRIPTION
        "Offset calibration: informations of date, name of operator, reference devices."
    ::= { wtWebGraphAnalog57761PortEntry 7 }

wtWebGraphAnalog57761PortSensorSelect OBJECT-TYPE
    SYNTAX OCTET STRING (SIZE(4))
    ACCESS read-write
    STATUS mandatory
    DESCRIPTION
        "Binary coded options for sensor 1:
        Octet 1: unused
        Octet 2: unused
        Octet 3: unused
        Octet 4:
		Bit 0  :	0-20mA (default)
		Bit 1  :	4-20mA
		Bit 2  :	Disconnect
        	Bit 3-7:	unused"
    ::= { wtWebGraphAnalog57761PortEntry 8 }

wtWebGraphAnalog57761PortUnit OBJECT-TYPE
    SYNTAX OCTET STRING
    ACCESS read-write
    STATUS mandatory
    DESCRIPTION
        "User scale: displayed unit."
    ::= { wtWebGraphAnalog57761PortEntry 9 }

wtWebGraphAnalog57761PortScale0 OBJECT-TYPE
    SYNTAX OCTET STRING
    ACCESS read-write
    STATUS mandatory
    DESCRIPTION
        "User scale: displayed value in 1/1000 at 0% full scale range.
        Range: -999999.999 to 999999.999"
    ::= { wtWebGraphAnalog57761PortEntry 10 }

wtWebGraphAnalog57761PortScale100 OBJECT-TYPE
    SYNTAX OCTET STRING
    ACCESS read-write
    STATUS mandatory
    DESCRIPTION
        "User scale: displayed value in 1/1000 at 100% full scale range.
        Range: -999999.999 to 999999.999"
    ::= { wtWebGraphAnalog57761PortEntry 11 }

wtWebGraphAnalog57761PortOutputMode OBJECT-TYPE
    SYNTAX OCTET STRING (SIZE (4))
    ACCESS read-write
    STATUS mandatory
    DESCRIPTION
        "This binary coded output mode defines the individual operation mode for any
        output. More than one mode must not be selected. If an output mode is selected,
        Bit 2 in wtWebGraphAnalog57761PortInputMode will be set automatically.
        The OCTETS are interpreted bit-by-bit, Bit 0 corresponds to the LSB.
        OCTET 1: unused
        OCTET 2: unused
        OCTET 3: unused
        OCTET 4: Bit 6-7: unused
        	 Bit 5  : Output OFF
        	 Bit 4  : Binary 2
        	 Bit 3  : Binary 1
        	 Bit 2  : SNMP
        	 Bit 1  : UDP ASCII
        	 Bit 0  : HTTP"
    ::= { wtWebGraphAnalog57761PortEntry 12 }

wtWebGraphAnalog57761PortInputMode OBJECT-TYPE
    SYNTAX OCTET STRING (SIZE (4))
    ACCESS read-write
    STATUS mandatory
    DESCRIPTION
        "This binary coded input mode defines the individual operation mode for any
        input. More than one mode must not be selected. If an input mode is selected,
        Bit 5 in wtWebGraphAnalog57761PortOutputMode will be set automatically.
        The OCTETS are interpreted bit-by-bit,Bit 0 corresponds to the LSB.
        OCTET 1: ungenutzt
        OCTET 2: ungenutzt
        OCTET 3: ungenutzt
        OCTET 4: Bit 3-7: unused
        	 Bit 2  : I-Output
        	 Bit 1  : I-Input, active
        	 Bit 0  : I-Input, passive"
    ::= { wtWebGraphAnalog57761PortEntry 13 }

wtWebGraphAnalog57761PortPresetValue OBJECT-TYPE
    SYNTAX OCTET STRING
    ACCESS read-write
    STATUS mandatory
    DESCRIPTION
        "This value will be set after reset or initialisation."
    ::= { wtWebGraphAnalog57761PortEntry 16 }

-- wtWebGraphAnalog57761Manufact Group
----------------------------

wtWebGraphAnalog57761MfName OBJECT-TYPE
    SYNTAX OCTET STRING
    ACCESS read-write
    STATUS mandatory
    DESCRIPTION
        "Manufacturer company name"
    ::= { wtWebGraphAnalog57761Manufact 1 }

wtWebGraphAnalog57761MfAddr OBJECT-TYPE
    SYNTAX OCTET STRING
    ACCESS read-write
    STATUS mandatory
    DESCRIPTION
        "Manufacturer address."
    ::= { wtWebGraphAnalog57761Manufact 2 }

wtWebGraphAnalog57761MfHotline OBJECT-TYPE
    SYNTAX OCTET STRING
    ACCESS read-write
    STATUS mandatory
    DESCRIPTION
        "Manufacturer hotline."
    ::= { wtWebGraphAnalog57761Manufact 3 }

wtWebGraphAnalog57761MfInternet OBJECT-TYPE
    SYNTAX OCTET STRING
    ACCESS read-write
    STATUS mandatory
    DESCRIPTION
        "Manufacturer Internet address."
    ::= { wtWebGraphAnalog57761Manufact 4 }

wtWebGraphAnalog57761MfDeviceTyp OBJECT-TYPE
    SYNTAX OCTET STRING
    ACCESS read-write
    STATUS mandatory
    DESCRIPTION
        "Manufacturer device name (model number)."
    ::= { wtWebGraphAnalog57761Manufact 5 }

wtWebGraphAnalog57761MfOrderNo OBJECT-TYPE
    SYNTAX OCTET STRING
    ACCESS read-write
    STATUS mandatory
    DESCRIPTION
        "Manufacturer part number."
    ::= { wtWebGraphAnalog57761Manufact 6 }

-- wtWebGraphAnalog57761Diag Group
----------------------------

wtWebGraphAnalog57761DiagErrorCount OBJECT-TYPE
    SYNTAX INTEGER
    ACCESS read-only
    STATUS mandatory
    DESCRIPTION
        "Number of entries in the error memory."
    ::= { wtWebGraphAnalog57761Diag 1 }

wtWebGraphAnalog57761DiagBinaryError OBJECT-TYPE
    SYNTAX OCTET STRING
    ACCESS read-only
    STATUS mandatory
    DESCRIPTION
        "Error causes coded bit-by-bit."
    ::= { wtWebGraphAnalog57761Diag 2 }

wtWebGraphAnalog57761DiagErrorIndex OBJECT-TYPE
    SYNTAX INTEGER
    ACCESS read-write
    STATUS mandatory
    DESCRIPTION
        "The value of this variable is used as an index to read
        an error massege from wtWebGraphAnalog57761DiagErrorMessage.
        Errors are numbered from 1 to wtWebGraphAnalog57761DiagErrorCount.
        Writing a valid value into this variable, making the appropriate
        message readable from wtWebGraphAnalog57761DiagErrorMessage."
    ::= { wtWebGraphAnalog57761Diag 3 }

wtWebGraphAnalog57761DiagErrorMessage OBJECT-TYPE
    SYNTAX OCTET STRING
    ACCESS read-only
    STATUS mandatory
    DESCRIPTION
        "Using wtWebGraphAnalog57761DiagErrorIndex as an index, the appropriate message is available."
    ::= { wtWebGraphAnalog57761Diag 4 }

wtWebGraphAnalog57761DiagErrorClear OBJECT-TYPE
    SYNTAX INTEGER
    ACCESS write-only
    STATUS mandatory
    DESCRIPTION
        "Writing 1 into this variable clears all diagnosis messages."
    ::= { wtWebGraphAnalog57761Diag 5 }

-- TRAP DEFINITIONS

-- Diese SNMP-Traps werden gesendet, wenn die Alarmtriggerbedingungen zutreffen

wtWebGraphAnalog57761Alert1 TRAP-TYPE
    ENTERPRISE  wtWebGraphAnalog57761
    VARIABLES   { wtWebGraphAnalog57761AlarmTrapText }
    DESCRIPTION
        "This SNMP trap is generated when Alarm 1 was triggered,
        SNMP trap enable is set and
        SNMP is enabled."
    -- NMS trap annotation
    --#TYPE "Web-IO Analog-InOut Alarm 1"
    --#SUMMARY "Alarm 1: %s"
    --#ARGUMENTS {0}
    --#SEVERITY INFORMATIONAL
    --#TIMEINDEX 99
    --#STATE OPERATIONAL
    ::= 31

wtWebGraphAnalog57761Alert2 TRAP-TYPE
    ENTERPRISE  wtWebGraphAnalog57761
    VARIABLES   { wtWebGraphAnalog57761AlarmTrapText }
    DESCRIPTION
        "This SNMP trap is generated when Alarm 2 was triggered,
        SNMP trap enable is set and
        SNMP is enabled."
    -- NMS trap annotation
    --#TYPE "Web-IO Analog-InOut Alarm 2"
    --#SUMMARY "Alarm 2: %s"
    --#ARGUMENTS {0}
    --#SEVERITY INFORMATIONAL
    --#TIMEINDEX 99
    --#STATE OPERATIONAL
    ::= 32

wtWebGraphAnalog57761Alert3 TRAP-TYPE
    ENTERPRISE  wtWebGraphAnalog57761
    VARIABLES   { wtWebGraphAnalog57761AlarmTrapText }
    DESCRIPTION
        "This SNMP trap is generated when Alarm 3 was triggered,
        SNMP trap enable is set and
        SNMP is enabled."
    -- NMS trap annotation
    --#TYPE "Web-IO Analog-InOut Alarm 3"
    --#SUMMARY "Alarm 3: %s"
    --#ARGUMENTS {0}
    --#SEVERITY INFORMATIONAL
    --#TIMEINDEX 99
    --#STATE OPERATIONAL
    ::= 33

wtWebGraphAnalog57761Alert4 TRAP-TYPE
    ENTERPRISE  wtWebGraphAnalog57761
    VARIABLES   { wtWebGraphAnalog57761AlarmTrapText }
    DESCRIPTION
        "This SNMP trap is generated when Alarm 4 was triggered,
        SNMP trap enable is set and
        SNMP is enabled."
    -- NMS trap annotation
    --#TYPE "Web-IO Analog-InOut Alarm 4"
    --#SUMMARY "Alarm 4: %s"
    --#ARGUMENTS {0}
    --#SEVERITY INFORMATIONAL
    --#TIMEINDEX 99
    --#STATE OPERATIONAL
    ::= 34

wtWebGraphAnalog57761Alert5 TRAP-TYPE
    ENTERPRISE  wtWebGraphAnalog57761
    VARIABLES   { wtWebGraphAnalog57761AlarmTrapText }
    DESCRIPTION
        "This SNMP trap is generated when Alarm 5 was triggered,
        SNMP trap enable is set and
        SNMP is enabled."
    -- NMS trap annotation
    --#TYPE "Web-IO Analog-InOut Alarm 5"
    --#SUMMARY "Alarm 5: %s"
    --#ARGUMENTS {0}
    --#SEVERITY INFORMATIONAL
    --#TIMEINDEX 99
    --#STATE OPERATIONAL
    ::= 35

wtWebGraphAnalog57761Alert6 TRAP-TYPE
    ENTERPRISE  wtWebGraphAnalog57761
    VARIABLES   { wtWebGraphAnalog57761AlarmTrapText }
    DESCRIPTION
        "This SNMP trap is generated when Alarm 6 was triggered,
        SNMP trap enable is set and
        SNMP is enabled."
    -- NMS trap annotation
    --#TYPE "Web-IO Analog-InOut Alarm 6"
    --#SUMMARY "Alarm 6: %s"
    --#ARGUMENTS {0}
    --#SEVERITY INFORMATIONAL
    --#TIMEINDEX 99
    --#STATE OPERATIONAL
    ::= 36

wtWebGraphAnalog57761Alert7 TRAP-TYPE
    ENTERPRISE  wtWebGraphAnalog57761
    VARIABLES   { wtWebGraphAnalog57761AlarmTrapText }
    DESCRIPTION
        "This SNMP trap is generated when Alarm 7 was triggered,
        SNMP trap enable is set and
        SNMP is enabled."
    -- NMS trap annotation
    --#TYPE "Web-IO Analog-InOut Alarm 7"
    --#SUMMARY "Alarm 7: %s"
    --#ARGUMENTS {0}
    --#SEVERITY INFORMATIONAL
    --#TIMEINDEX 99
    --#STATE OPERATIONAL
    ::= 37

wtWebGraphAnalog57761Alert8 TRAP-TYPE
    ENTERPRISE  wtWebGraphAnalog57761
    VARIABLES   { wtWebGraphAnalog57761AlarmTrapText }
    DESCRIPTION
        "This SNMP trap is generated when Alarm 8 was triggered,
        SNMP trap enable is set and
        SNMP is enabled."
    -- NMS trap annotation
    --#TYPE "Web-IO Analog-InOut Alarm 8"
    --#SUMMARY "Alarm 8: %s"
    --#ARGUMENTS {0}
    --#SEVERITY INFORMATIONAL
    --#TIMEINDEX 99
    --#STATE OPERATIONAL
    ::= 38

wtWebGraphAnalog57761Alert9 TRAP-TYPE
    ENTERPRISE  wtWebGraphAnalog57761
    VARIABLES   { wtWebGraphAnalog57761AlarmClearTrapText }
    DESCRIPTION
        "This SNMP trap is generated when Alarm 1 was cleared,
        SNMP trap enable is set and
        SNMP is enabled."
    -- NMS trap annotation
    --#TYPE "Web-IO Analog-InOut Release Alarm 1"
    --#SUMMARY "Release Alarm 1: %s"
    --#ARGUMENTS {0}
    --#SEVERITY INFORMATIONAL
    --#TIMEINDEX 99
    --#STATE OPERATIONAL
    ::= 91

wtWebGraphAnalog57761Alert10 TRAP-TYPE
    ENTERPRISE  wtWebGraphAnalog57761
    VARIABLES   { wtWebGraphAnalog57761AlarmClearTrapText }
    DESCRIPTION
        "This SNMP trap is generated when Alarm 2 was cleared,
        SNMP trap enable is set and
        SNMP is enabled."
    -- NMS trap annotation
    --#TYPE "Web-IO Analog-InOut Release Alarm 2"
    --#SUMMARY "Release Alarm 2: %s"
    --#ARGUMENTS {0}
    --#SEVERITY INFORMATIONAL
    --#TIMEINDEX 99
    --#STATE OPERATIONAL
    ::= 92

wtWebGraphAnalog57761Alert11 TRAP-TYPE
    ENTERPRISE  wtWebGraphAnalog57761
    VARIABLES   { wtWebGraphAnalog57761AlarmClearTrapText }
    DESCRIPTION
        "This SNMP trap is generated when Alarm 3 was cleared,
        SNMP trap enable is set and
        SNMP is enabled."
    -- NMS trap annotation
    --#TYPE "Web-IO Analog-InOut Release Alarm 3"
    --#SUMMARY "Release Alarm 3: %s"
    --#ARGUMENTS {0}
    --#SEVERITY INFORMATIONAL
    --#TIMEINDEX 99
    --#STATE OPERATIONAL
    ::= 93

wtWebGraphAnalog57761Alert12 TRAP-TYPE
    ENTERPRISE  wtWebGraphAnalog57761
    VARIABLES   { wtWebGraphAnalog57761AlarmClearTrapText }
    DESCRIPTION
        "This SNMP trap is generated when Alarm 4 was cleared,
        SNMP trap enable is set and
        SNMP is enabled."
    -- NMS trap annotation
    --#TYPE "Web-IO Analog-InOut Release Alarm 4"
    --#SUMMARY "Release Alarm 4: %s"
    --#ARGUMENTS {0}
    --#SEVERITY INFORMATIONAL
    --#TIMEINDEX 99
    --#STATE OPERATIONAL
    ::= 94

wtWebGraphAnalog57761Alert13 TRAP-TYPE
    ENTERPRISE  wtWebGraphAnalog57761
    VARIABLES   { wtWebGraphAnalog57761AlarmClearTrapText }
    DESCRIPTION
        "This SNMP trap is generated when Alarm 5 was cleared,
        SNMP trap enable is set and
        SNMP is enabled."
    -- NMS trap annotation
    --#TYPE "Web-IO Analog-InOut Release Alarm 5"
    --#SUMMARY "Release Alarm 5: %s"
    --#ARGUMENTS {0}
    --#SEVERITY INFORMATIONAL
    --#TIMEINDEX 99
    --#STATE OPERATIONAL
    ::= 95

wtWebGraphAnalog57761Alert14 TRAP-TYPE
    ENTERPRISE  wtWebGraphAnalog57761
    VARIABLES   { wtWebGraphAnalog57761AlarmClearTrapText }
    DESCRIPTION
        "This SNMP trap is generated when Alarm 6 was cleared,
        SNMP trap enable is set and
        SNMP is enabled."
    -- NMS trap annotation
    --#TYPE "Web-IO Analog-InOut Release Alarm 6"
    --#SUMMARY "Release Alarm 6: %s"
    --#ARGUMENTS {0}
    --#SEVERITY INFORMATIONAL
    --#TIMEINDEX 99
    --#STATE OPERATIONAL
    ::= 96

wtWebGraphAnalog57761Alert15 TRAP-TYPE
    ENTERPRISE  wtWebGraphAnalog57761
    VARIABLES   { wtWebGraphAnalog57761AlarmClearTrapText }
    DESCRIPTION
        "This SNMP trap is generated when Alarm 7 was cleared,
        SNMP trap enable is set and
        SNMP is enabled."
    -- NMS trap annotation
    --#TYPE "Web-IO Analog-InOut Release Alarm 7"
    --#SUMMARY "Release Alarm 7: %s"
    --#ARGUMENTS {0}
    --#SEVERITY INFORMATIONAL
    --#TIMEINDEX 99
    --#STATE OPERATIONAL
    ::= 97

wtWebGraphAnalog57761Alert16 TRAP-TYPE
    ENTERPRISE  wtWebGraphAnalog57761
    VARIABLES   { wtWebGraphAnalog57761AlarmClearTrapText }
    DESCRIPTION
        "This SNMP trap is generated when Alarm 8 was cleared,
        SNMP trap enable is set and
        SNMP is enabled."
    -- NMS trap annotation
    --#TYPE "Web-IO Analog-InOut Release Alarm 8"
    --#SUMMARY "Release Alarm 8: %s"
    --#ARGUMENTS {0}
    --#SEVERITY INFORMATIONAL
    --#TIMEINDEX 99
    --#STATE OPERATIONAL
    ::= 98

wtWebGraphAnalog57761AlertReport TRAP-TYPE
    ENTERPRISE  wtWebGraphAnalog57761
    VARIABLES   { wtWebGraphAnalog57761AlarmTrapText }
    DESCRIPTION
        "This SNMP trap is generated when the report was triggered,
        SNMP trap enable is set and
        SNMP is enabled."
    -- NMS trap annotation
    --#TYPE "Web-IO Analog-InOut Report"
    --#SUMMARY "Report: %s"
    --#ARGUMENTS {0}
    --#SEVERITY INFORMATIONAL
    --#TIMEINDEX 99
    --#STATE OPERATIONAL
    ::= 39

wtWebGraphAnalog57761AlertDiag TRAP-TYPE
    ENTERPRISE  wtWebGraphAnalog57761
    VARIABLES   {
    		wtWebGraphAnalog57761DiagErrorIndex,
    	  	wtWebGraphAnalog57761DiagErrorMessage
    		}
    DESCRIPTION
        "This SNMP trap is generated when a diagnosis/error message was triggered,
        SNMP trap enable is set and
        SNMP is enabled."
    -- NMS trap annotation
    --#TYPE "Web-IO Analog-InOut Diagnose Error"
    --#SUMMARY "Diagnose error index: %d, Message: %s."
    --#ARGUMENTS {0,1}
    --#SEVERITY MAJOR
    --#TIMEINDEX 99
    --#STATE DEGRADED
    ::= 110

END
