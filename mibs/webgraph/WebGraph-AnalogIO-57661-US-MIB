WebGraph-AnalogIO-57661-US-MIB DEFINITIONS ::= BEGIN
----------------------------------------------------------------
-- Revison: 1.30
----------------------------------------------------------------
-- 08.01.2010 	New: Reports
--
----------------------------------------------------------------
-- Revison: 1.29
----------------------------------------------------------------
-- 01.10.2009 	Webio
--		New Analog Out: 57661
----------------------------------------------------------------
-- Revison: 1.28
----------------------------------------------------------------
-- 02.12.2008 	Webio
--		New Graphics java script base parameter
----------------------------------------------------------------
-- Revison: 1.27
----------------------------------------------------------------
-- 09.11.2006 	Webio
--		DHCP enable
----------------------------------------------------------------
-- Revison: 1.26
----------------------------------------------------------------
-- 28.06.2006 	New: Community String Trap
--
----------------------------------------------------------------
-- Revison: 1.25
----------------------------------------------------------------
-- 25.11.2005 	#57641, WebGraph AnalogIn
--		OID correction
----------------------------------------------------------------
-- Revison: 1.24
----------------------------------------------------------------
-- 26.07.2005 	#57641, WebGraph AnalogIn
--		CRON timer function
----------------------------------------------------------------
-- Revison: 1.23
----------------------------------------------------------------
-- 14.07.2005 	#57641, WebGraph AnalogIn
--		FTP functions
----------------------------------------------------------------
-- Revison: 1.22
----------------------------------------------------------------
-- 17.05.2005 	#57641, WebGraph AnalogIn
--		Trap NMS annotations
----------------------------------------------------------------
-- Revison: 1.21
----------------------------------------------------------------
-- 19.04.2005 	#57605, WebGraph Themometer
--		Mail Authentication
----------------------------------------------------------------
-- Revison: 1.20
----------------------------------------------------------------
-- 05.11.2004 	#57606, WebGraph Thermo-Hygrometer
--		New: Syslog
--
----------------------------------------------------------------
-- Revison: 1.19
----------------------------------------------------------------
-- 08.09.2004 	#57606 WebGraph Thermo-Hygrometer
--		New:
--			wtWebGraphThermHygroAlarmRHMin
--			wtWebGraphThermHygroAlarmRHMax
--			wtWebGraphThermHygroAlarmRHHysteresis
--			wtWebGraphThermHygroPortSensorSelect
--			wtWebGraphThermHygroAlarmDeltaTemp
--			wtWebGraphThermHygroAlarmAHMin
--			wtWebGraphThermHygroAlarmAHMax
----------------------------------------------------------------
-- Revison: 1.18
----------------------------------------------------------------
-- 21.07.2004 	#57601/3/4, Webio Anx
--		New:
--		     Diagnosis
----------------------------------------------------------------
-- Revison: 1.17
----------------------------------------------------------------
-- 28.06.2004 	#57630/1/2, Webio Digital
--		Neu: Puls Mode
----------------------------------------------------------------
-- Revison: 1.16
----------------------------------------------------------------
-- 16.04.2004 	New: #57632, Webio Digital EA24x24
--
--		#57630/1, Webio Digital EA12x12
--		New:
--			wtWebioEA12x12InputCounterClear
----------------------------------------------------------------
-- Revison: 1.15
----------------------------------------------------------------
-- 27.02.2004 	#57630/1, Webio Digital EA12x12
--		New:
--		Length changed to 32 Bit:
--			wtWebioEA12x12InputValue
--			wtWebioEA12x12OutputValue
--			wtWebioEA12x12LoadControlView
--			wtWebioEA12x12LCShutDownView
--			wtWebioEA12x12SetOutput
--			wtWebioEA12x12AlarmInputTrigger
--			wtWebioEA12x12AlarmOutputTrigger
--			wtWebioEA12x12PortOutputSafetyState
----------------------------------------------------------------
-- Revison: 1.14
----------------------------------------------------------------
-- 16.02.2004 	#57630/1, Webio Digital EA12x12
--		New:
--		Text: Location, Contact
--		SNMP: ColdStart, WarmStart, ComunityString Read/RW
--		Alarm: ColdStart / WarmStart trigger
--
-- 	 	#57601, 1xWebThermometer
--		#57603, 2xWebThermometer
--		#57604, 8xWebThermometer
--		New:
--		Alarm Hysteresis
--		Alarm Clear Traps and Mails
----------------------------------------------------------------
-- Revison: 1.13
----------------------------------------------------------------
-- 05.02.2004 	#57601, 1xWebThermometer
--		#57603, 2xWebThermometer
--		#57604, 8xWebThermometer
--		New:
--		Text: Location, Contact
--		SNMP: ColdStart, WarmStart, ComunityString Read/RW
--		Alarm: ColdStart / WarmStart trigger
----------------------------------------------------------------
-- Revison: 1.12
----------------------------------------------------------------
-- 05.11.2003 	#57601, 1xWebThermometer
--		#57603, 2xWebThermometer
--		#57604, 8xWebThermometer
--		New features:
--		Mail  : Option CSV attachment
--		Port  : Offset calibration
--		Alarm : TCP Client mode
----------------------------------------------------------------
-- Revison: 1.11
----------------------------------------------------------------
-- 28.10.2003 	#57630/1, Webio Digital EA12x12
--		New features:
--		Alarm : TCP Client mode
--		Inputs: Puls filter
----------------------------------------------------------------
-- Revison: 1.10
----------------------------------------------------------------
-- 22.07.2003 	#57630, Webio Digital EA12x12
--		New navigation tree, new binary modes
--
----------------------------------------------------------------
-- Revison: 1.09
----------------------------------------------------------------
-- 24.03.2003 	Trap Enterprise (Type 1, 2) corrected
----------------------------------------------------------------
-- Revison: 1.08
----------------------------------------------------------------
-- 04.03.2003 	reconciled the language versions DE/US
----------------------------------------------------------------
-- Revison: 1.07
----------------------------------------------------------------
-- 25.02.2003 	Correction: wtWebioEA12x12LoadControl
----------------------------------------------------------------
-- Revison: 1.06
----------------------------------------------------------------
-- 24.02.2003 	New:
--		#57630, Webio EA12x12, LoadControl Group
--		Correction: Trap variable names
----------------------------------------------------------------
-- Revison: 1.05
----------------------------------------------------------------
-- 21.01.2003 	New:
--		#57630, Webio EA12x12
----------------------------------------------------------------
-- Revison: 1.04
----------------------------------------------------------------
-- 02.01.2003 	New:
--		#57601, 1xWebThermometer
--		#57603, 2xWebThermometer, 8 alarms
----------------------------------------------------------------
-- Revison: 1.03
----------------------------------------------------------------
-- 21.11.2002 	New:
--		#57604, 2xWebThermometer, BOOTP, StartupSite
--		#57603, 8xWebThermometer, BOOTP, StartupSite
----------------------------------------------------------------
-- Revison: 1.02
----------------------------------------------------------------
-- 26.07.2002 	New:
--		#57604, 2xWebThermometer
--		#57603, 8xWebThermometer
--


    IMPORTS

    OBJECT-TYPE                                        FROM RFC-1212
    TRAP-TYPE                                          FROM RFC-1215
    DisplayString, PhysAddress                         FROM RFC1213-MIB
    enterprises, TimeTicks, IpAddress, NetworkAddress  FROM RFC1155-SMI;


--    IpAddress ::=
--        [APPLICATION 0]
--            IMPLICIT OCTET STRING (SIZE (4))
--    Counter ::=
--        [APPLICATION 1]
--            IMPLICIT INTEGER (0..4294967295)
--    Gauge ::=
--        [APPLICATION 2]
--            IMPLICIT INTEGER (0..4294967295)
--    TimeTicks ::=
--        [APPLICATION 3]
--            IMPLICIT INTEGER (0..4294967295)


--    DisplayString ::= OCTET STRING
--    PhysAddress   ::= OCTET STRING

--    internet         OBJECT IDENTIFIER ::= { iso org(3) dod(6) 1 }
--    privat           OBJECT IDENTIFIER ::= { internet 4 }
--    enterprises      OBJECT IDENTIFIER ::= { privat 1 }



--  Wiesemann & Theis Com-Server MIB

    wut                				OBJECT IDENTIFIER ::= { enterprises 5040 }
    wtComServer        				OBJECT IDENTIFIER ::= { wut 1 }
    wtWebio            				OBJECT IDENTIFIER ::= { wtComServer 2 }

--  wtWebGraph Tree

    wtWebGraphAnalog57661  			OBJECT IDENTIFIER ::= { wtWebio 28 }

--  wtWebGraphAnalog57661 Tree

    wtWebGraphAnalog57661Inventory   		OBJECT IDENTIFIER ::= { wtWebGraphAnalog57661 1 }
    wtWebGraphAnalog57661SessCntrl 		OBJECT IDENTIFIER ::= { wtWebGraphAnalog57661 2 }
    wtWebGraphAnalog57661Config    		OBJECT IDENTIFIER ::= { wtWebGraphAnalog57661 3 }
    wtWebGraphAnalog57661Diag    		OBJECT IDENTIFIER ::= { wtWebGraphAnalog57661 4 }

--  wtWebGraphAnalog57661Config Tree

    wtWebGraphAnalog57661Device    		OBJECT IDENTIFIER ::= { wtWebGraphAnalog57661Config 1 }
    wtWebGraphAnalog57661Ports     		OBJECT IDENTIFIER ::= { wtWebGraphAnalog57661Config 2 }
    wtWebGraphAnalog57661Manufact  		OBJECT IDENTIFIER ::= { wtWebGraphAnalog57661Config 3 }

--  wtWebGraphAnalog57661Device Tree

    wtWebGraphAnalog57661Text			OBJECT IDENTIFIER ::= { wtWebGraphAnalog57661Device 1 }
    wtWebGraphAnalog57661TimeDate 		OBJECT IDENTIFIER ::= { wtWebGraphAnalog57661Device 2 }
    wtWebGraphAnalog57661Basic			OBJECT IDENTIFIER ::= { wtWebGraphAnalog57661Device 3 }
    wtWebGraphAnalog57661Datalogger		OBJECT IDENTIFIER ::= { wtWebGraphAnalog57661Device 4 }
    wtWebGraphAnalog57661Alarm			OBJECT IDENTIFIER ::= { wtWebGraphAnalog57661Device 5 }
    wtWebGraphAnalog57661Graphics 		OBJECT IDENTIFIER ::= { wtWebGraphAnalog57661Device 6 }
    wtWebGraphAnalog57661Report			OBJECT IDENTIFIER ::= { wtWebGraphAnalog57661Device 7 }

--  wtWebGraphAnalog57661TimeDate Tree

    wtWebGraphAnalog57661TimeZone		OBJECT IDENTIFIER ::= { wtWebGraphAnalog57661TimeDate 1 }
    wtWebGraphAnalog57661TimeServer		OBJECT IDENTIFIER ::= { wtWebGraphAnalog57661TimeDate 2 }
    wtWebGraphAnalog57661DeviceClock		OBJECT IDENTIFIER ::= { wtWebGraphAnalog57661TimeDate 3 }

--  wtWebGraphAnalog57661Basic Tree

    wtWebGraphAnalog57661Network		OBJECT IDENTIFIER ::= { wtWebGraphAnalog57661Basic 1 }
    wtWebGraphAnalog57661HTTP			OBJECT IDENTIFIER ::= { wtWebGraphAnalog57661Basic 2 }
    wtWebGraphAnalog57661Mail			OBJECT IDENTIFIER ::= { wtWebGraphAnalog57661Basic 3 }
    wtWebGraphAnalog57661SNMP			OBJECT IDENTIFIER ::= { wtWebGraphAnalog57661Basic 4 }
    wtWebGraphAnalog57661UDP			OBJECT IDENTIFIER ::= { wtWebGraphAnalog57661Basic 5 }
    wtWebGraphAnalog57661Syslog			OBJECT IDENTIFIER ::= { wtWebGraphAnalog57661Basic 6 }
    wtWebGraphAnalog57661FTP			OBJECT IDENTIFIER ::= { wtWebGraphAnalog57661Basic 7 }
    wtWebGraphAnalog57661Language		OBJECT IDENTIFIER ::= { wtWebGraphAnalog57661Basic 8 }
    wtWebGraphAnalog57661Binary			OBJECT IDENTIFIER ::= { wtWebGraphAnalog57661Basic 9 }

--  wtWebGraphAnalog57661Graphics Tree

    wtWebGraphAnalog57661GraphicsBase 		OBJECT IDENTIFIER ::= { wtWebGraphAnalog57661Graphics 1 }
    wtWebGraphAnalog57661GraphicsSelect 	OBJECT IDENTIFIER ::= { wtWebGraphAnalog57661Graphics 2 }
    wtWebGraphAnalog57661GraphicsScale 		OBJECT IDENTIFIER ::= { wtWebGraphAnalog57661Graphics 3 }

-- wtWebGraphAnalog57661Inventory Group
------------------------

wtWebGraphAnalog57661Sensors OBJECT-TYPE
    SYNTAX INTEGER (1..2)
    ACCESS read-only
    STATUS mandatory
    DESCRIPTION
        "Number of sensors"
    ::= { wtWebGraphAnalog57661Inventory 1 }

-- Interface Table

wtWebGraphAnalog57661SensorTable OBJECT-TYPE
    SYNTAX SEQUENCE OF WtWebGraphAnalog57661SensorEntry
    ACCESS not-accessible
    STATUS mandatory
    DESCRIPTION
        "List of sensors."
    ::= { wtWebGraphAnalog57661Inventory 2 }

wtWebGraphAnalog57661SensorEntry OBJECT-TYPE
    SYNTAX WtWebGraphAnalog57661SensorEntry
    ACCESS not-accessible
    STATUS mandatory
    DESCRIPTION
        "List of sensor numbers."
    INDEX  { wtWebGraphAnalog57661SensorNo }
    ::= { wtWebGraphAnalog57661SensorTable 1 }

WtWebGraphAnalog57661SensorEntry ::= SEQUENCE {
    wtWebGraphAnalog57661SensorNo INTEGER
}

wtWebGraphAnalog57661SensorNo OBJECT-TYPE
    SYNTAX INTEGER (1..2)
    ACCESS read-only
    STATUS mandatory
    DESCRIPTION
        "Sensor number."
    ::= { wtWebGraphAnalog57661SensorEntry 1 }


-- wtWebGraphAnalog57661Values Table

wtWebGraphAnalog57661ValuesTable OBJECT-TYPE
    SYNTAX SEQUENCE OF WtWebGraphAnalog57661ValuesEntry
    ACCESS not-accessible
    STATUS mandatory
    DESCRIPTION
        "List of measurement values corresponding to the channel numbers."
    ::= { wtWebGraphAnalog57661Inventory 3 }

wtWebGraphAnalog57661ValuesEntry OBJECT-TYPE
    SYNTAX WtWebGraphAnalog57661ValuesEntry
    ACCESS not-accessible
    STATUS mandatory
    DESCRIPTION
        "Measurement values of the sensors."
    INDEX  { wtWebGraphAnalog57661SensorNo }
    ::= { wtWebGraphAnalog57661ValuesTable 1 }

WtWebGraphAnalog57661ValuesEntry ::= SEQUENCE{
    wtWebGraphAnalog57661Values OCTET STRING
}

wtWebGraphAnalog57661Values OBJECT-TYPE
    SYNTAX OCTET STRING (SIZE (5))
    ACCESS read-write
    STATUS mandatory
    DESCRIPTION
        "Measurement value of the sensor, ASCII.
        This value will be translated according to the ports settings
        for the read and write operations."
    ::= { wtWebGraphAnalog57661ValuesEntry 1 }

-- wtWebGraphAnalog57661BinaryValues Table

wtWebGraphAnalog57661BinaryValuesTable OBJECT-TYPE
    SYNTAX SEQUENCE OF WtWebGraphAnalog57661BinaryValuesEntry
    ACCESS not-accessible
    STATUS mandatory
    DESCRIPTION
        "List of binary measurement values corresponding to the channel numbers."
    ::= { wtWebGraphAnalog57661Inventory 4 }

wtWebGraphAnalog57661BinaryValuesEntry OBJECT-TYPE
    SYNTAX WtWebGraphAnalog57661BinaryValuesEntry
    ACCESS not-accessible
    STATUS mandatory
    DESCRIPTION
        "Binary measurement values of the sensors."
    INDEX  { wtWebGraphAnalog57661SensorNo }
    ::= { wtWebGraphAnalog57661BinaryValuesTable 1 }

WtWebGraphAnalog57661BinaryValuesEntry ::= SEQUENCE{
    wtWebGraphAnalog57661BinaryValues INTEGER
}

wtWebGraphAnalog57661BinaryValues OBJECT-TYPE
    SYNTAX INTEGER
    ACCESS read-write
    STATUS mandatory
    DESCRIPTION
        "Binary measurement value of the sensor in 1/1000,
        signed number, 0x7FFFFFFF indicates an invalid value.
        This value will be translated according to the ports settings
        for the read and write operations."
    ::= { wtWebGraphAnalog57661BinaryValuesEntry 1 }

-- wtWebGraphAnalog57661SessCntrl Group
--------------------------------

wtWebGraphAnalog57661SessCntrlPassword OBJECT-TYPE
    SYNTAX OCTET STRING
    ACCESS read-write
    STATUS mandatory
    DESCRIPTION
        "Entering this password opens a session which is ended by writing a 1 to
        wtWebGraphAnalog57661SessCntrlLogout. When read this variable provides a string of
        length zero."
    ::= { wtWebGraphAnalog57661SessCntrl 1 }

wtWebGraphAnalog57661SessCntrlConfigMode OBJECT-TYPE
    SYNTAX INTEGER {
    wtWebGraphAnalog57661SessCntrl-NoSession(0),
    wtWebGraphAnalog57661SessCntrl-Session(1)
    }
    ACCESS read-only
    STATUS mandatory
    DESCRIPTION
        "When the device is in SNMP configuration mode, the value 1 is
        returned, otherwise 0. If the read value is 0 even though the
        password was written, the device is already in config mode and the
        variables can only be read."
    ::= { wtWebGraphAnalog57661SessCntrl 2 }

wtWebGraphAnalog57661SessCntrlLogout OBJECT-TYPE
    SYNTAX INTEGER
    ACCESS read-write
    STATUS mandatory
    DESCRIPTION
        "If the device is in configuration mode and the session was opened by
        this SNMP Manager, writing a 1 to this variable will end the session
        and all parameters are stored.
        Writing a 2 discards all entries again.
        When read this variable provides the value 0."
    ::= { wtWebGraphAnalog57661SessCntrl 3 }

wtWebGraphAnalog57661SessCntrlAdminPassword OBJECT-TYPE
    SYNTAX OCTET STRING
    ACCESS read-write
    STATUS mandatory
    DESCRIPTION
        "This password protects access to the variables with administrator rights.
        It can only be changed by the administrator. If no password was assigned,
        the valid password is public."
    ::= { wtWebGraphAnalog57661SessCntrl 4 }

wtWebGraphAnalog57661SessCntrlConfigPassword OBJECT-TYPE
    SYNTAX OCTET STRING
    ACCESS read-write
    STATUS mandatory
    DESCRIPTION
        "This password protects access to the variables with configurator rights. It can
        be changed by the administrator and by the configurator. If no password was assigned,
        the valid password is public. When read this variable provides a null-pointer."
    ::= { wtWebGraphAnalog57661SessCntrl 5 }


-- wtWebGraphAnalog57661Text Group
------------------------

wtWebGraphAnalog57661DeviceName OBJECT-TYPE
    SYNTAX OCTET STRING
    ACCESS read-write
    STATUS mandatory
    DESCRIPTION
        "Name of the Webio, which is user definable."
    ::= { wtWebGraphAnalog57661Text 1 }

wtWebGraphAnalog57661DeviceText OBJECT-TYPE
    SYNTAX OCTET STRING
    ACCESS read-write
    STATUS mandatory
    DESCRIPTION
        "Description of the Webio, which is user definable."
    ::= { wtWebGraphAnalog57661Text 2 }

wtWebGraphAnalog57661DeviceLocation OBJECT-TYPE
    SYNTAX OCTET STRING
    ACCESS read-write
    STATUS mandatory
    DESCRIPTION
        "Description of the location of the Webio, which is user definable."
    ::= { wtWebGraphAnalog57661Text 3 }

wtWebGraphAnalog57661DeviceContact OBJECT-TYPE
    SYNTAX OCTET STRING
    ACCESS read-write
    STATUS mandatory
    DESCRIPTION
        "Contact address of the system operator of the Webio, which is user definable."
    ::= { wtWebGraphAnalog57661Text 4 }

-- wtWebGraphAnalog57661TimeZone Group
----------------------------

wtWebGraphAnalog57661TzOffsetHrs OBJECT-TYPE
    SYNTAX INTEGER
    ACCESS read-write
    STATUS mandatory
    DESCRIPTION
        "Offset hours for the time zone (winter time) with respect to UTC."
    ::= { wtWebGraphAnalog57661TimeZone 1 }

wtWebGraphAnalog57661TzOffsetMin OBJECT-TYPE
    SYNTAX INTEGER
    ACCESS read-write
    STATUS mandatory
    DESCRIPTION
        "Offset minutes for the time zone (winter time) with respect to UTC."
    ::= { wtWebGraphAnalog57661TimeZone 2 }

wtWebGraphAnalog57661TzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebGraphAnalog57661TimeZone 3 }

wtWebGraphAnalog57661StTzOffsetHrs OBJECT-TYPE
    SYNTAX INTEGER
    ACCESS read-write
    STATUS mandatory
    DESCRIPTION
        "Offset hours of the time zone (summer time) with respect to UTC."
    ::= { wtWebGraphAnalog57661TimeZone 4 }

wtWebGraphAnalog57661StTzOffsetMin OBJECT-TYPE
    SYNTAX INTEGER
    ACCESS read-write
    STATUS mandatory
    DESCRIPTION
        "Offset minutes of the time zone (summer time) with respect to UTC."
    ::= { wtWebGraphAnalog57661TimeZone 5 }

wtWebGraphAnalog57661StTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebGraphAnalog57661TimeZone 6 }

wtWebGraphAnalog57661StTzStartMonth OBJECT-TYPE
    SYNTAX INTEGER {
    	wtWebGraphAnalog57661StartMonth-January(1),
    	wtWebGraphAnalog57661StartMonth-February(2),
    	wtWebGraphAnalog57661StartMonth-March(3),
    	wtWebGraphAnalog57661StartMonth-April(4),
    	wtWebGraphAnalog57661StartMonth-May(5),
    	wtWebGraphAnalog57661StartMonth-June(6),
    	wtWebGraphAnalog57661StartMonth-July(7),
    	wtWebGraphAnalog57661StartMonth-August(8),
    	wtWebGraphAnalog57661StartMonth-September(9),
    	wtWebGraphAnalog57661StartMonth-October(10),
    	wtWebGraphAnalog57661StartMonth-November(11),
    	wtWebGraphAnalog57661StartMonth-December(12)
    	}

    ACCESS read-write
    STATUS mandatory
    DESCRIPTION
        "Month in which the change is made from winter time to summer time."
    ::= { wtWebGraphAnalog57661TimeZone 7 }

wtWebGraphAnalog57661StTzStartMode OBJECT-TYPE
    SYNTAX INTEGER {
    	wtWebGraphAnalog57661StartMode-first(1),
    	wtWebGraphAnalog57661StartMode-second(2),
    	wtWebGraphAnalog57661StartMode-third(3),
    	wtWebGraphAnalog57661StartMode-fourth(4),
    	wtWebGraphAnalog57661StartMode-last(5)
    	}

    ACCESS read-write
    STATUS mandatory
    DESCRIPTION
        "Mode of the day of the week for which the change is made from winter time to summer time."
    ::= { wtWebGraphAnalog57661TimeZone 8 }

wtWebGraphAnalog57661StTzStartWday OBJECT-TYPE
    SYNTAX INTEGER {
    	wtWebGraphAnalog57661StartWday-Sunday(1),
    	wtWebGraphAnalog57661StartWday-Monday(2),
    	wtWebGraphAnalog57661StartWday-Tuesday(3),
    	wtWebGraphAnalog57661StartWday-Thursday(4),
    	wtWebGraphAnalog57661StartWday-Wednesday(5),
    	wtWebGraphAnalog57661StartWday-Friday(6),
    	wtWebGraphAnalog57661StartWday-Saturday(7)
    	}

    ACCESS read-write
    STATUS mandatory
    DESCRIPTION
        "Day of the week on which the change is made from winter time to summer time"
    ::= { wtWebGraphAnalog57661TimeZone 9 }

wtWebGraphAnalog57661StTzStartHrs OBJECT-TYPE
    SYNTAX INTEGER
    ACCESS read-write
    STATUS mandatory
    DESCRIPTION
        "Hour in which the time zone is changed from winter to summer time with
        respect to UTC."
    ::= { wtWebGraphAnalog57661TimeZone 10 }

wtWebGraphAnalog57661StTzStartMin OBJECT-TYPE
    SYNTAX INTEGER
    ACCESS read-write
    STATUS mandatory
    DESCRIPTION
        "Minute in which the time zone is changed from winter to summer time with
        respect to UTC."
    ::= { wtWebGraphAnalog57661TimeZone 11 }

wtWebGraphAnalog57661StTzStopMonth OBJECT-TYPE
    SYNTAX INTEGER {
    	wtWebGraphAnalog57661StopMonth-January(1),
    	wtWebGraphAnalog57661StopMonth-February(2),
    	wtWebGraphAnalog57661StopMonth-March(3),
    	wtWebGraphAnalog57661StopMonth-April(4),
    	wtWebGraphAnalog57661StopMonth-May(5),
    	wtWebGraphAnalog57661StopMonth-June(6),
    	wtWebGraphAnalog57661StopMonth-July(7),
    	wtWebGraphAnalog57661StopMonth-August(8),
    	wtWebGraphAnalog57661StopMonth-September(9),
    	wtWebGraphAnalog57661StopMonth-October(10),
    	wtWebGraphAnalog57661StopMonth-November(11),
    	wtWebGraphAnalog57661StopMonth-December(12)
    	}
    ACCESS read-write
    STATUS mandatory
    DESCRIPTION
        "Month in which the change is made from summer time to winter time."
   ::= { wtWebGraphAnalog57661TimeZone 12 }

wtWebGraphAnalog57661StTzStopMode OBJECT-TYPE
    SYNTAX INTEGER {
    	wtWebGraphAnalog57661StopMode-first(1),
    	wtWebGraphAnalog57661StopMode-second(2),
    	wtWebGraphAnalog57661StopMode-third(3),
    	wtWebGraphAnalog57661StopMode-fourth(4),
    	wtWebGraphAnalog57661StopMode-last(5)
    	}
    ACCESS read-write
    STATUS mandatory
    DESCRIPTION
        "Mode of the week day on which the change is made from summer time to winter time."
    ::= { wtWebGraphAnalog57661TimeZone 13 }

wtWebGraphAnalog57661StTzStopWday OBJECT-TYPE
    SYNTAX INTEGER {
    	wtWebGraphAnalog57661StopWday-Sunday(1),
    	wtWebGraphAnalog57661StopWday-Monday(2),
    	wtWebGraphAnalog57661StopWday-Tuesday(3),
    	wtWebGraphAnalog57661StopWday-Thursday(4),
    	wtWebGraphAnalog57661StopWday-Wednesday(5),
    	wtWebGraphAnalog57661StopWday-Friday(6),
    	wtWebGraphAnalog57661StopWday-Saturday(7)
    	}
    ACCESS read-write
    STATUS mandatory
    DESCRIPTION
        "Day of the week on which the change is made from summer time to winter time."
    ::= { wtWebGraphAnalog57661TimeZone 14 }

wtWebGraphAnalog57661StTzStopHrs OBJECT-TYPE
    SYNTAX INTEGER
    ACCESS read-write
    STATUS mandatory
    DESCRIPTION
        "Hour at which the time zone is changed from summer to winter time with
        respect to UTC."
    ::= { wtWebGraphAnalog57661TimeZone 15 }

wtWebGraphAnalog57661StTzStopMin OBJECT-TYPE
    SYNTAX INTEGER
    ACCESS read-write
    STATUS mandatory
    DESCRIPTION
        "Minute at which the time zone is changed from summer to winter time with
        respect to UTC."
    ::= { wtWebGraphAnalog57661TimeZone 16 }

-- wtWebGraphAnalog57661TimeServer Group
----------------------------

wtWebGraphAnalog57661TimeServer1 OBJECT-TYPE
    SYNTAX OCTET STRING
    ACCESS read-write
    STATUS mandatory
    DESCRIPTION
        "IP address or name of the 1st time server in ASCII"
    ::= { wtWebGraphAnalog57661TimeServer 1 }

wtWebGraphAnalog57661TimeServer2 OBJECT-TYPE
    SYNTAX OCTET STRING
    ACCESS read-write
    STATUS mandatory
    DESCRIPTION
        "IP address or name of the 2nd time server in ASCII"
    ::= { wtWebGraphAnalog57661TimeServer 2 }

wtWebGraphAnalog57661TsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebGraphAnalog57661TimeServer 3 }

wtWebGraphAnalog57661TsSyncTime OBJECT-TYPE
    SYNTAX INTEGER
    ACCESS read-write
    STATUS mandatory
    DESCRIPTION
        "Daily synchronisation time with the time server (hour: 0-23)."
    ::= { wtWebGraphAnalog57661TimeServer 4 }

-- wtWebGraphAnalog57661DeviceClock Group
----------------------------

wtWebGraphAnalog57661ClockHrs OBJECT-TYPE
    SYNTAX INTEGER (0..23)
    ACCESS read-write
    STATUS mandatory
    DESCRIPTION
        "Clock hours taking into account the time zone settings."
    ::= { wtWebGraphAnalog57661DeviceClock 1 }

wtWebGraphAnalog57661ClockMin OBJECT-TYPE
    SYNTAX INTEGER (0..59)
    ACCESS read-write
    STATUS mandatory
    DESCRIPTION
        "Clock minutes taking into account the time zone settings."
    ::= { wtWebGraphAnalog57661DeviceClock 2 }

wtWebGraphAnalog57661ClockDay OBJECT-TYPE
    SYNTAX INTEGER (1..31)
    ACCESS read-write
    STATUS mandatory
    DESCRIPTION
        "Date: Day of the month, taking into account the time zone settings."
    ::= { wtWebGraphAnalog57661DeviceClock 3 }

wtWebGraphAnalog57661ClockMonth OBJECT-TYPE
   SYNTAX INTEGER {
    	wtWebGraphAnalog57661ClockMonth-January(1),
    	wtWebGraphAnalog57661ClockMonth-February(2),
    	wtWebGraphAnalog57661ClockMonth-March(3),
    	wtWebGraphAnalog57661ClockMonth-April(4),
    	wtWebGraphAnalog57661ClockMonth-May(5),
    	wtWebGraphAnalog57661ClockMonth-June(6),
    	wtWebGraphAnalog57661ClockMonth-July(7),
    	wtWebGraphAnalog57661ClockMonth-August(8),
    	wtWebGraphAnalog57661ClockMonth-September(9),
    	wtWebGraphAnalog57661ClockMonth-October(10),
    	wtWebGraphAnalog57661ClockMonth-November(11),
    	wtWebGraphAnalog57661ClockMonth-December(12)
    	}
    ACCESS read-write
    STATUS mandatory
    DESCRIPTION
        "Date: Month, taking into account the time zone settings."
    ::= { wtWebGraphAnalog57661DeviceClock 4 }

wtWebGraphAnalog57661ClockYear OBJECT-TYPE
    SYNTAX INTEGER (0..65535)
    ACCESS read-write
    STATUS mandatory
    DESCRIPTION
        "Date: Year, taking into account the time zone settings."
    ::= { wtWebGraphAnalog57661DeviceClock 5 }


-- wtWebGraphAnalog57661Network Group
------------------------

wtWebGraphAnalog57661IpAddress OBJECT-TYPE
    SYNTAX IpAddress
    ACCESS read-write
    STATUS mandatory
    DESCRIPTION
        "IP address of the Webio"
    ::= { wtWebGraphAnalog57661Network 1 }

wtWebGraphAnalog57661SubnetMask OBJECT-TYPE
    SYNTAX IpAddress
    ACCESS read-write
    STATUS mandatory
    DESCRIPTION
        "Subnet mask of the Webio"
    ::= { wtWebGraphAnalog57661Network 2 }

wtWebGraphAnalog57661Gateway OBJECT-TYPE
    SYNTAX IpAddress
    ACCESS read-write
    STATUS mandatory
    DESCRIPTION
        "Gateway of the Webio"
    ::= { wtWebGraphAnalog57661Network 3 }

wtWebGraphAnalog57661DnsServer1 OBJECT-TYPE
    SYNTAX OCTET STRING
    ACCESS read-write
    STATUS mandatory
    DESCRIPTION
        "IP address of the 1st DNS server in ASCII"
    ::= { wtWebGraphAnalog57661Network 4 }

wtWebGraphAnalog57661DnsServer2 OBJECT-TYPE
    SYNTAX OCTET STRING
    ACCESS read-write
    STATUS mandatory
    DESCRIPTION
        "IP address of the 2nd DNS server in ASCII"
    ::= { wtWebGraphAnalog57661Network 5 }

wtWebGraphAnalog57661AddConfig OBJECT-TYPE
    SYNTAX OCTET STRING
    ACCESS read-write
    STATUS mandatory
    DESCRIPTION
        "Additional configuration (1=ON):
        Octet 1: unused
        Octet 2: unused
        Octet 3: unused
        Octet 4:
	        Bit 1: DHCP disable
	        Bit 0: BOOTP disable
	        "
    ::= { wtWebGraphAnalog57661Network 6 }

--  wtWebGraphAnalog57661HTTP Group
--------------------------------

wtWebGraphAnalog57661Startup OBJECT-TYPE
    SYNTAX OCTET STRING
    ACCESS read-write
    STATUS mandatory
    DESCRIPTION
        "Binary coded start page:
        Octet 1: unused
        Octet 2: unused
        Octet 3: unused
        Octet 4:
	        Bit 1: Index.htm
	        Bit 2: Home.htm
	        Bit 3: User.htm
	Only one page may be selected at a time."
    ::= { wtWebGraphAnalog57661HTTP 1 }

wtWebGraphAnalog57661GetHeaderEnable OBJECT-TYPE
    SYNTAX OCTET STRING
    ACCESS read-write
    STATUS mandatory
    DESCRIPTION
        "If these bits are set, every answer of a short form GET question will be lead
        by the IP-address and name of the device and/or a HTTP header:
        Octet 1: unused
        Octet 2: unused
        Octet 3: unused
        Octet 4:
        	Bit 1-6: unused
        	Bit 1  : GET HTTP enable
                Bit 0  : GET Header enable"
    ::= { wtWebGraphAnalog57661HTTP 2 }

wtWebGraphAnalog57661HttpPort OBJECT-TYPE
    SYNTAX INTEGER (1..65535)
    ACCESS read-write
    STATUS mandatory
    DESCRIPTION
        "Definition of the standard HTML port (Default: 80)."
    ::= { wtWebGraphAnalog57661HTTP 3 }


-- wtWebGraphAnalog57661Mail Group
--------------------------------

wtWebGraphAnalog57661MailAdName OBJECT-TYPE
    SYNTAX OCTET STRING
    ACCESS read-write
    STATUS mandatory
    DESCRIPTION
        "Device name for mail administration."
    ::= { wtWebGraphAnalog57661Mail 1 }

wtWebGraphAnalog57661MailReply OBJECT-TYPE
    SYNTAX OCTET STRING
    ACCESS read-write
    STATUS mandatory
    DESCRIPTION
        "Reply address for the mail server."
    ::= { wtWebGraphAnalog57661Mail 2 }

wtWebGraphAnalog57661MailServer OBJECT-TYPE
    SYNTAX OCTET STRING
    ACCESS read-write
    STATUS mandatory
    DESCRIPTION
        "Name or IP address of the mail server."
    ::= { wtWebGraphAnalog57661Mail 3 }

wtWebioAn1MailEnable OBJECT-TYPE
    SYNTAX OCTET STRING
    ACCESS read-write
    STATUS mandatory
    DESCRIPTION
        "Set this bit to enable the sending of mails:
        Octet 1: unused
        Octet 2: unused
        Octet 3: unused
        Octet 4:
        	Bit 1-7: unused
                Bit 0  : Mail enable"
    ::= { wtWebGraphAnalog57661Mail 4 }

wtWebGraphAnalog57661MailAuthentication OBJECT-TYPE
    SYNTAX OCTET STRING (SIZE (4))
    ACCESS read-write
    STATUS mandatory
    DESCRIPTION
        "Selection of the authentication modi:
        The OCTETS are interpreted bit-by-bit, with each bit corresponding to an output.
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebGraphAnalog57661Mail 5 }

wtWebGraphAnalog57661MailAuthUser OBJECT-TYPE
    SYNTAX OCTET STRING
    ACCESS read-write
    STATUS mandatory
    DESCRIPTION
        "Name of the user to be authenticated."
    ::= { wtWebGraphAnalog57661Mail 6 }

wtWebGraphAnalog57661MailAuthPassword OBJECT-TYPE
    SYNTAX OCTET STRING
    ACCESS read-write
    STATUS mandatory
    DESCRIPTION
        "Authentication password."
    ::= { wtWebGraphAnalog57661Mail 7 }

wtWebGraphAnalog57661MailPop3Server OBJECT-TYPE
    SYNTAX OCTET STRING
    ACCESS read-write
    STATUS mandatory
    DESCRIPTION
        "Name or Ip-address of the POP3 Servers."
    ::= { wtWebGraphAnalog57661Mail 8 }

-- wtWebGraphAnalog57661SNMP Group
--------------------------------

wtWebGraphAnalog57661SnmpCommunityStringRead OBJECT-TYPE
    SYNTAX OCTET STRING
    ACCESS read-write
    STATUS mandatory
    DESCRIPTION
        "Community string read only"
    ::= { wtWebGraphAnalog57661SNMP 1 }

wtWebGraphAnalog57661SnmpCommunityStringReadWrite OBJECT-TYPE
    SYNTAX OCTET STRING
    ACCESS read-write
    STATUS mandatory
    DESCRIPTION
        "Community string read / write"
    ::= { wtWebGraphAnalog57661SNMP 2 }

wtWebGraphAnalog57661SystemTrapManagerIP OBJECT-TYPE
    SYNTAX OCTET STRING
    ACCESS read-write
    STATUS mandatory
    DESCRIPTION
        "Name or IP address of the TCP server which accepts the system trap."
    ::= { wtWebGraphAnalog57661SNMP 3 }

wtWebGraphAnalog57661SystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2-7: unused"
    ::= { wtWebGraphAnalog57661SNMP 4 }

wtWebGraphAnalog57661SnmpEnable OBJECT-TYPE
    SYNTAX OCTET STRING
    ACCESS read-write
    STATUS mandatory
    DESCRIPTION
        "Set bit 0 to enable SNMP.
        If disabled, the device did not respond to any SNMP requests.
        Bit 1 decided wether the community string of read operations
        is compared with the system password or not:
        Octet 1: unused
        Octet 2: unused
        Octet 3: unused
        Octet 4:
        	Bit 1-7: unused
        	Bit 0  : SNMP enable"
    ::= { wtWebGraphAnalog57661SNMP 5 }

wtWebGraphAnalog57661SnmpCommunityStringTrap OBJECT-TYPE
    SYNTAX OCTET STRING
    ACCESS read-write
    STATUS mandatory
    DESCRIPTION
        "Community string send within traps."
    ::= { wtWebGraphAnalog57661SNMP 6 }


-- wtWebGraphAnalog57661UDP Group
--------------------------------

wtWebGraphAnalog57661UdpPort OBJECT-TYPE
    SYNTAX INTEGER (1..65535)
    ACCESS read-write
    STATUS mandatory
    DESCRIPTION
        "Udp port to which the Udp queries ( short form GET requests) can be sent. This
        port number must be unique within the device."
    ::= { wtWebGraphAnalog57661UDP 1 }

wtWebGraphAnalog57661UdpEnable OBJECT-TYPE
    SYNTAX OCTET STRING
    ACCESS read-write
    STATUS mandatory
    DESCRIPTION
        "Set this bit to enable UDP support:
        Octet 1: unused
        Octet 2: unused
        Octet 3: unused
        Octet 4:
        	Bit 1-7: unused
                Bit 0  : UDP enable"
    ::= { wtWebGraphAnalog57661UDP 2 }

--  wtWebGraphAnalog57661Syslog Group
--------------------------------

wtWebGraphAnalog57661SyslogServerIP OBJECT-TYPE
    SYNTAX OCTET STRING
    ACCESS read-write
    STATUS mandatory
    DESCRIPTION
        "Name or IP address of the Syslog server, which accepts the Syslog messgaes."
    ::= { wtWebGraphAnalog57661Syslog 1 }

wtWebGraphAnalog57661SyslogServerPort OBJECT-TYPE
    SYNTAX INTEGER
    ACCESS read-write
    STATUS mandatory
    DESCRIPTION
        "Portnumber of the Syslog servers, default 514."
    ::= { wtWebGraphAnalog57661Syslog 2 }

wtWebGraphAnalog57661SyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebGraphAnalog57661Syslog 3 }

wtWebGraphAnalog57661SyslogEnable OBJECT-TYPE
    SYNTAX OCTET STRING
    ACCESS read-write
    STATUS mandatory
    DESCRIPTION
        "Set bit 0to enable Syslog:
        Octet 1: unused
        Octet 2: unused
        Octet 3: unused
        Octet 4:
        	Bit 1-7: unused
                Bit 0  : Syslog enable"
    ::= { wtWebGraphAnalog57661Syslog 4 }

--  wtWebGraphAnalog57661FTP Group
--------------------------------

wtWebGraphAnalog57661FTPServerIP OBJECT-TYPE
    SYNTAX OCTET STRING
    ACCESS read-write
    STATUS mandatory
    DESCRIPTION
        "Name or IP address of the FTP server, which accepts the FTP messages."
    ::= { wtWebGraphAnalog57661FTP 1 }

wtWebGraphAnalog57661FTPServerControlPort OBJECT-TYPE
    SYNTAX INTEGER
    ACCESS read-write
    STATUS mandatory
    DESCRIPTION
        "Portnumber of the control port of the FTP server, default 21."
    ::= { wtWebGraphAnalog57661FTP 2 }

wtWebGraphAnalog57661FTPUserName OBJECT-TYPE
    SYNTAX OCTET STRING
    ACCESS read-write
    STATUS mandatory
    DESCRIPTION
        "FTP Loggin: user name."
    ::= { wtWebGraphAnalog57661FTP 3 }

wtWebGraphAnalog57661FTPPassword OBJECT-TYPE
    SYNTAX OCTET STRING
    ACCESS read-write
    STATUS mandatory
    DESCRIPTION
        "FTP Loggin: user password."
    ::= { wtWebGraphAnalog57661FTP 4 }

wtWebGraphAnalog57661FTPAccount OBJECT-TYPE
    SYNTAX OCTET STRING
    ACCESS read-write
    STATUS mandatory
    DESCRIPTION
        "FTP Loggin: name of account."
    ::= { wtWebGraphAnalog57661FTP 5 }

wtWebGraphAnalog57661FTPOption OBJECT-TYPE
    SYNTAX OCTET STRING
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebGraphAnalog57661FTP 6 }

wtWebGraphAnalog57661FTPEnable OBJECT-TYPE
    SYNTAX OCTET STRING
    ACCESS read-write
    STATUS mandatory
    DESCRIPTION
        "Set Bit 0 to enable FTP:
        Octet 1: unused
        Octet 2: unused
        Octet 3: unused
        Octet 4:
        	Bit 1-7: unused
                Bit 0  : FTP enable"
    ::= { wtWebGraphAnalog57661FTP 7 }

--  wtWebGraphAnalog57661Language Group
--------------------------------

wtWebGraphAnalog57661LanguageSelect OBJECT-TYPE
    SYNTAX OCTET STRING
    ACCESS read-write
    STATUS mandatory
    DESCRIPTION
        "Language selection:
        Octet 1: unused
        Octet 2: unused
        Octet 3: unused
        Octet 4:
        	Bit 2-7: unused
        	Bit 1  : English
                Bit 0  : German"
    ::= { wtWebGraphAnalog57661Language 1 }

--  wtWebGraphAnalog57661Binary Group
--------------------------------

wtWebGraphAnalog57661BinaryModeCount OBJECT-TYPE
    SYNTAX INTEGER (1..2)
    ACCESS read-only
    STATUS mandatory
    DESCRIPTION
        "Number of independent binary channels."
    ::= { wtWebGraphAnalog57661Binary 1 }

-- Binary Interface Table

wtWebGraphAnalog57661BinaryIfTable OBJECT-TYPE
    SYNTAX SEQUENCE OF WtWebGraphAnalog57661BinaryIfEntry
    ACCESS not-accessible
    STATUS mandatory
    DESCRIPTION
        "Table of indices."
    ::= { wtWebGraphAnalog57661Binary 2 }

wtWebGraphAnalog57661BinaryIfEntry OBJECT-TYPE
    SYNTAX WtWebGraphAnalog57661BinaryIfEntry
    ACCESS not-accessible
    STATUS mandatory
    DESCRIPTION
        "Indices of the binary channels."
    INDEX  { wtWebGraphAnalog57661BinaryModeNo }
    ::= { wtWebGraphAnalog57661BinaryIfTable 1 }

WtWebGraphAnalog57661BinaryIfEntry ::= SEQUENCE {
    wtWebGraphAnalog57661BinaryModeNo INTEGER
}

wtWebGraphAnalog57661BinaryModeNo OBJECT-TYPE
    SYNTAX INTEGER (1..2)
    ACCESS read-only
    STATUS mandatory
    DESCRIPTION
        "Number of the binary channel."
    ::= { wtWebGraphAnalog57661BinaryIfEntry 1 }

-- Binary Table
--------------------------------

wtWebGraphAnalog57661BinaryTable OBJECT-TYPE
    SYNTAX SEQUENCE OF WtWebGraphAnalog57661BinaryEntry
    ACCESS not-accessible
    STATUS mandatory
    DESCRIPTION
        "Table of properties of the binary mode."
    ::= { wtWebGraphAnalog57661Binary 3 }

wtWebGraphAnalog57661BinaryEntry OBJECT-TYPE
    SYNTAX WtWebGraphAnalog57661BinaryEntry
    ACCESS not-accessible
    STATUS mandatory
    DESCRIPTION
        "Binary properties."
    INDEX  { wtWebGraphAnalog57661BinaryModeNo }
    ::= { wtWebGraphAnalog57661BinaryTable 1 }

WtWebGraphAnalog57661BinaryEntry ::= SEQUENCE {
    wtWebGraphAnalog57661BinaryOperationMode			OCTET STRING,
    wtWebGraphAnalog57661BinaryTcpServerLocalPort		INTEGER,
    wtWebGraphAnalog57661BinaryTcpServerInputTrigger		OCTET STRING,
    wtWebGraphAnalog57661BinaryTcpServerApplicationMode		OCTET STRING,
    wtWebGraphAnalog57661BinaryTcpClientLocalPort		INTEGER,
    wtWebGraphAnalog57661BinaryTcpClientServerPort		INTEGER,
    wtWebGraphAnalog57661BinaryTcpClientServerIpAddr		OCTET STRING,
    wtWebGraphAnalog57661BinaryTcpClientServerPassword		OCTET STRING,
    wtWebGraphAnalog57661BinaryTcpClientInactivity		INTEGER,
    wtWebGraphAnalog57661BinaryTcpClientInputTrigger		OCTET STRING,
    wtWebGraphAnalog57661BinaryTcpClientInterval		INTEGER,
    wtWebGraphAnalog57661BinaryTcpClientApplicationMode		OCTET STRING,
    wtWebGraphAnalog57661BinaryUdpPeerLocalPort			INTEGER,
    wtWebGraphAnalog57661BinaryUdpPeerRemotePort		INTEGER,
    wtWebGraphAnalog57661BinaryUdpPeerRemoteIpAddr		OCTET STRING,
    wtWebGraphAnalog57661BinaryUdpPeerInputTrigger		OCTET STRING,
    wtWebGraphAnalog57661BinaryUdpPeerInterval			INTEGER,
    wtWebGraphAnalog57661BinaryUdpPeerApplicationMode		OCTET STRING,
    wtWebGraphAnalog57661BinaryConnectedPort			INTEGER,
    wtWebGraphAnalog57661BinaryConnectedIpAddr			IpAddress,
    wtWebGraphAnalog57661BinaryTcpServerClientHttpPort		INTEGER,
    wtWebGraphAnalog57661BinaryTcpClientServerHttpPort		INTEGER,
    wtWebGraphAnalog57661BinaryTcpServerHysteresis1		OCTET STRING,
    wtWebGraphAnalog57661BinaryTcpServerHysteresis2		OCTET STRING,
    wtWebGraphAnalog57661BinaryTcpClientHysteresis1		OCTET STRING,
    wtWebGraphAnalog57661BinaryTcpClientHysteresis2		OCTET STRING,
    wtWebGraphAnalog57661BinaryUdpPeerHysteresis1		OCTET STRING,
    wtWebGraphAnalog57661BinaryUdpPeerHysteresis2		OCTET STRING

}

wtWebGraphAnalog57661BinaryOperationMode OBJECT-TYPE
    SYNTAX OCTET STRING (SIZE (4))
    ACCESS read-write
    STATUS mandatory
    DESCRIPTION
        "Selection of the operation mode:
        The OCTETS are interpreted bit-by-bit,
        Bit 0 corresponds to the LSB.
        OCTET 1: unused
        OCTET 2: unused
        OCTET 3: unused
        OCTET 4: Bit 3-7: unused
        	 Bit 2  : UDP Peer
        	 Bit 1  : TCP Client
        	 Bit 0  : TCP Server"
    ::= { wtWebGraphAnalog57661BinaryEntry 1 }

wtWebGraphAnalog57661BinaryTcpServerLocalPort OBJECT-TYPE
    SYNTAX INTEGER (1..65535)
    ACCESS read-write
    STATUS mandatory
    DESCRIPTION
        "Local TCP port for data exchange in this server mode.
        This port number must be unique within the device.
	Reserved port number must not be used (refere to the manual)."
    ::= { wtWebGraphAnalog57661BinaryEntry 2 }

wtWebGraphAnalog57661BinaryTcpServerInputTrigger OBJECT-TYPE
    SYNTAX OCTET STRING (SIZE (4))
    ACCESS read-write
    STATUS mandatory
    DESCRIPTION
        "Every change on the inputs causes their state to be transmitted to the
        remote device. To minimize data traffic, individual inputs may be exempted
        from this rule. Nevertheless every transmission will contain all input states.
        If a bit is set (1), a change of state on the corresponding input
        triggers a transmission. If the bit is not set (0), no transmission
        takes place.
        The OCTETS are interpreted bit-by-bit, with each bit corresponding to an input.
        Bit 0 corresponds to the LSB.
        OCTET 1: unused
        OCTET 2: unused
        OCTET 3: unused
        OCTET 4, Bit 0-1: Analog inputs 0-1"
    ::= { wtWebGraphAnalog57661BinaryEntry 3 }

wtWebGraphAnalog57661BinaryTcpServerApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 4-7: unused
        	 Bit 3  : OPC Device
        	 Bit 2  : Box2Box Slave
        	 Bit 1  : Compatible 50xxx
        	 Bit 0  : Default"
    ::= { wtWebGraphAnalog57661BinaryEntry 4 }

wtWebGraphAnalog57661BinaryTcpClientLocalPort OBJECT-TYPE
    SYNTAX INTEGER (1..65535)
    ACCESS read-write
    STATUS mandatory
    DESCRIPTION
        "Local TCP port for data exchange in this client mode.
        This port number must be unique within the device.
	Reserved port number must not be used (refere to the manual)."
    ::= { wtWebGraphAnalog57661BinaryEntry 5 }

wtWebGraphAnalog57661BinaryTcpClientServerPort OBJECT-TYPE
    SYNTAX INTEGER (1..65535)
    ACCESS read-write
    STATUS mandatory
    DESCRIPTION
        "Port number of the server. A complete set of port number, IP address
        and a valid input/output mask starts this mode.
        No data exchange take place when setting the server port to zero."
    ::= { wtWebGraphAnalog57661BinaryEntry 6 }

wtWebGraphAnalog57661BinaryTcpClientServerIpAddr OBJECT-TYPE
    SYNTAX OCTET STRING
    ACCESS read-write
    STATUS mandatory
    DESCRIPTION
        "Ip address of the server. A complete set of port number, IP address
        and a valid input/output mask starts this mode.
        No data exchange take place when setting the server IP address to 0.0.0.0."
    ::= { wtWebGraphAnalog57661BinaryEntry 7 }

wtWebGraphAnalog57661BinaryTcpClientServerPassword OBJECT-TYPE
    SYNTAX OCTET STRING
    ACCESS read-write
    STATUS mandatory
    DESCRIPTION
        "Building a connection may be protected by the
        administrator password of the server. Enter the server password
        to establish the connection, if a server administrator password
        exists."
    ::= { wtWebGraphAnalog57661BinaryEntry 8 }

wtWebGraphAnalog57661BinaryTcpClientInactivity OBJECT-TYPE
    SYNTAX INTEGER
    ACCESS read-write
    STATUS mandatory
    DESCRIPTION
        "Connection timeout in 100ms. If no data are exchanged within the specified
        time, the device closes the connection to the server.
        The value 0 deactivates the timer. Using the Box2Box mode this function is
        disabled."
    ::= { wtWebGraphAnalog57661BinaryEntry 9 }

wtWebGraphAnalog57661BinaryTcpClientInputTrigger OBJECT-TYPE
    SYNTAX OCTET STRING (SIZE (4))
    ACCESS read-write
    STATUS mandatory
    DESCRIPTION
        "Every change on the inputs causes their state to be transmitted to the
        remote device. To minimize data traffic, individual inputs may be exempted
        from this rule. Nevertheless every transmission will contain all input states.
        If a bit is set (1), a change of state on the corresponding input
        triggers a transmission. If the bit is not set (0), no transmission
        takes place.
        The OCTETS are interpreted bit-by-bit, with each bit corresponding to an input.
        Bit 0 corresponds to the LSB.
        OCTET 1: unused
        OCTET 2: unused
        OCTET 3: unused
        OCTET 4, Bit 0-1: Analog inputs 0-1"
    ::= { wtWebGraphAnalog57661BinaryEntry 10 }

wtWebGraphAnalog57661BinaryTcpClientInterval OBJECT-TYPE
    SYNTAX INTEGER (0..65535)
    ACCESS read-write
    STATUS mandatory
    DESCRIPTION
        "Configurable interval with a 100ms base, in which the Webio device sends
        data to the configured application. A interval of zero stopps the
        periodical sending."
    ::= { wtWebGraphAnalog57661BinaryEntry 11 }

wtWebGraphAnalog57661BinaryTcpClientApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebGraphAnalog57661BinaryEntry 12 }

wtWebGraphAnalog57661BinaryUdpPeerLocalPort OBJECT-TYPE
    SYNTAX INTEGER (1..65535)
    ACCESS read-write
    STATUS mandatory
    DESCRIPTION
        "Local UDP port for data exchange in this peer to peer mode.
        This port number must be unique within the device.
	Reserved port number must not be used (refere to the manual)."
    ::= { wtWebGraphAnalog57661BinaryEntry 13 }

wtWebGraphAnalog57661BinaryUdpPeerRemotePort OBJECT-TYPE
    SYNTAX INTEGER (1..65535)
    ACCESS read-write
    STATUS mandatory
    DESCRIPTION
        "Port number of the remote device. A complete set of port number, IP address
        and a valid input/output mask starts this mode.
        No data exchange take place when setting the remote port to zero."
    ::= { wtWebGraphAnalog57661BinaryEntry 14 }

wtWebGraphAnalog57661BinaryUdpPeerRemoteIpAddr OBJECT-TYPE
    SYNTAX OCTET STRING
    ACCESS read-write
    STATUS mandatory
    DESCRIPTION
        "Ip address of the remote device. A complete set of port number, IP address
        and a valid input/output mask starts this mode.
        No data exchange take place when setting the remote device IP address to 0.0.0.0."
    ::= { wtWebGraphAnalog57661BinaryEntry 15 }

wtWebGraphAnalog57661BinaryUdpPeerInputTrigger OBJECT-TYPE
    SYNTAX OCTET STRING (SIZE (4))
    ACCESS read-write
    STATUS mandatory
    DESCRIPTION
        "Every change on the inputs causes their state to be transmitted to the
        remote device. To minimize data traffic, individual inputs may be exempted
        from this rule. Nevertheless every transmission will contain all input states.
        If a bit is set (1), a change of state on the corresponding input
        triggers a transmission. If the bit is not set (0), no transmission
        takes place.
        The OCTETS are interpreted bit-by-bit, with each bit corresponding to an input.
        Bit 0 corresponds to the LSB.
        OCTET 1: unused
        OCTET 2: unused
        OCTET 3: unused
        OCTET 4, Bit 0-1: Analog inputs 0-1"
    ::= { wtWebGraphAnalog57661BinaryEntry 16 }

wtWebGraphAnalog57661BinaryUdpPeerInterval OBJECT-TYPE
    SYNTAX INTEGER (0..65535)
    ACCESS read-write
    STATUS mandatory
    DESCRIPTION
        "Configurable interval with a 100ms base, in which the Webio device sends
        data to the configured remote device. A interval of zero stopps the
        periodical sending."
    ::= { wtWebGraphAnalog57661BinaryEntry 17 }

wtWebGraphAnalog57661BinaryUdpPeerApplicationMode OBJECT-TYPE
    SYNTAX OCTET STRING (SIZE (4))
    ACCESS read-write
    STATUS mandatory
    DESCRIPTION
        "Selection of the application mode:
        The OCTETS are interpreted bit-by-bit, with each bit corresponding to an output.
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebGraphAnalog57661BinaryEntry 18 }

wtWebGraphAnalog57661BinaryConnectedPort OBJECT-TYPE
    SYNTAX INTEGER (1..65535)
    ACCESS read-only
    STATUS mandatory
    DESCRIPTION
        "Port number of the remote device, after connection has been established.
        In case of no connection or missing port informations a zero will be read."
    ::= { wtWebGraphAnalog57661BinaryEntry 19 }

wtWebGraphAnalog57661BinaryConnectedIpAddr OBJECT-TYPE
    SYNTAX IpAddress
    ACCESS read-only
    STATUS mandatory
    DESCRIPTION
        "IP address of the remote device, after connection has been established.
        In case of no connection or missing port informations 0.0.0.0 will be read."
    ::= { wtWebGraphAnalog57661BinaryEntry 20 }

wtWebGraphAnalog57661BinaryTcpServerClientHttpPort OBJECT-TYPE
    SYNTAX INTEGER (1..65535)
    ACCESS read-write
    STATUS mandatory
    DESCRIPTION
        "HTTP port number of the remote device at TCP Server Mode. If an mailfunction occurs
        status informations will be send to this port.
        Not used at mode Compatible 50xxx."
    ::= { wtWebGraphAnalog57661BinaryEntry 21 }

wtWebGraphAnalog57661BinaryTcpClientServerHttpPort OBJECT-TYPE
    SYNTAX INTEGER (1..65535)
    ACCESS read-write
    STATUS mandatory
    DESCRIPTION
        "HTTP port number of the remote device at TCP Client Mode. In the operating mode
        Box2Box connection status informations will be exchanged through this port."
    ::= { wtWebGraphAnalog57661BinaryEntry 22 }

wtWebGraphAnalog57661BinaryTcpServerHysteresis1 OBJECT-TYPE
    SYNTAX OCTET STRING
    ACCESS read-write
    STATUS mandatory
    DESCRIPTION
        "A change greater than this value initiate a transmission of the corresponding input value.
        The input 1 must be selected at wtWebGraphAnalog57661BinaryTcpServerInputTrigger.
        With a hysteresis of zero any change will be transmitted."
    ::= { wtWebGraphAnalog57661BinaryEntry 23 }

wtWebGraphAnalog57661BinaryTcpServerHysteresis2 OBJECT-TYPE
    SYNTAX OCTET STRING
    ACCESS read-write
    STATUS mandatory
    DESCRIPTION
        "A change greater than this value initiate a transmission of the corresponding input value.
        The input 2 must be selected at wtWebGraphAnalog57661BinaryTcpServerInputTrigger.
        With a hysteresis of zero any change will be transmitted."
    ::= { wtWebGraphAnalog57661BinaryEntry 24 }

wtWebGraphAnalog57661BinaryTcpClientHysteresis1 OBJECT-TYPE
    SYNTAX OCTET STRING
    ACCESS read-write
    STATUS mandatory
    DESCRIPTION
        "A change greater than this value initiate a transmission of the corresponding input value.
        The input 1 must be selected at wtWebGraphAnalog57661BinaryTcpClientInputTrigger.
        With a hysteresis of zero any change will be transmitted."

      ::= { wtWebGraphAnalog57661BinaryEntry 25 }

wtWebGraphAnalog57661BinaryTcpClientHysteresis2 OBJECT-TYPE
    SYNTAX OCTET STRING
    ACCESS read-write
    STATUS mandatory
    DESCRIPTION
        "A change greater than this value initiate a transmission of the corresponding input value.
        The input 2 must be selected at wtWebGraphAnalog57661BinaryTcpClientInputTrigger.
        With a hysteresis of zero any change will be transmitted."

      ::= { wtWebGraphAnalog57661BinaryEntry 26 }

wtWebGraphAnalog57661BinaryUdpPeerHysteresis1 OBJECT-TYPE
    SYNTAX OCTET STRING
    ACCESS read-write
    STATUS mandatory
    DESCRIPTION
        "A change greater than this value initiate a transmission of the corresponding input value.
        The input 1 must be selected at wtWebGraphAnalog57661BinaryUdpPeerInputTrigger.
        With a hysteresis of zero any change will be transmitted."
    ::= { wtWebGraphAnalog57661BinaryEntry 27 }

wtWebGraphAnalog57661BinaryUdpPeerHysteresis2 OBJECT-TYPE
    SYNTAX OCTET STRING
    ACCESS read-write
    STATUS mandatory
    DESCRIPTION
        "A change greater than this value initiate a transmission of the corresponding input value.
        The input 2 must be selected at wtWebGraphAnalog57661BinaryUdpPeerInputTrigger.
        With a hysteresis of zero any change will be transmitted."
    ::= { wtWebGraphAnalog57661BinaryEntry 28 }

-- wtWebGraphAnalog57661Datalogger Group
--------------------------------

wtWebGraphAnalog57661LoggerTimebase OBJECT-TYPE
    SYNTAX INTEGER {
    wtWebGraphAnalog57661Datalogger-15Sec(1),
    wtWebGraphAnalog57661Datalogger-30Sec(2),
    wtWebGraphAnalog57661Datalogger-1Min(3),
    wtWebGraphAnalog57661Datalogger-5Min(4),
    wtWebGraphAnalog57661Datalogger-15Min(5),
    wtWebGraphAnalog57661Datalogger-60Min(6)
    }
    ACCESS read-write
    STATUS mandatory
    DESCRIPTION
        "Time base of the data logger"
    ::= { wtWebGraphAnalog57661Datalogger 1 }

wtWebGraphAnalog57661LoggerSensorSel OBJECT-TYPE
    SYNTAX OCTET STRING (SIZE(4))
    ACCESS read-write
    STATUS mandatory
    DESCRIPTION
        "Binary coded trigger conditions:
        Octet 1: unused
        Octet 2: unused
        Octet 3: unused
        Octet 4:
        	Bit 0: Sensor 1
        	Bit 1: Sensor 2
        	Bit 2-7: unused"
    ::= { wtWebGraphAnalog57661Datalogger 2 }

wtWebGraphAnalog57661DisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1: Sensor 2
        	Bit 2-7: unused"
    ::= { wtWebGraphAnalog57661Datalogger 3 }

-- Graph Sensor Color Table

wtWebGraphAnalog57661SensorColorTable OBJECT-TYPE
    SYNTAX SEQUENCE OF WtWebGraphAnalog57661SensorColorEntry
    ACCESS not-accessible
    STATUS mandatory
    DESCRIPTION
        "List of sensor colors for the praphical presentation."
    ::= { wtWebGraphAnalog57661Datalogger 4 }

wtWebGraphAnalog57661SensorColorEntry OBJECT-TYPE
    SYNTAX WtWebGraphAnalog57661SensorColorEntry
    ACCESS not-accessible
    STATUS mandatory
    DESCRIPTION
        "Index numbers of the sensors."
    INDEX  { wtWebGraphAnalog57661SensorNo }
    ::= { wtWebGraphAnalog57661SensorColorTable 1 }

WtWebGraphAnalog57661SensorColorEntry ::= SEQUENCE {
    wtWebGraphAnalog57661SensorColor OCTET STRING
}

wtWebGraphAnalog57661SensorColor OBJECT-TYPE
    SYNTAX OCTET STRING (SIZE(3))
    ACCESS read-write
    STATUS mandatory
    DESCRIPTION
        "Color of the sensors at the praphical presention."
    ::= { wtWebGraphAnalog57661SensorColorEntry 1 }

wtWebGraphAnalog57661AutoScaleEnable OBJECT-TYPE
    SYNTAX OCTET STRING
    ACCESS read-write
    STATUS mandatory
    DESCRIPTION
        "If bit 0 is set, vertical auto scale is enabled:
        Octet 1: unused
        Octet 2: unused
        Octet 3: unused
        Octet 4:
        	Bit 1-7: unused
                Bit 0  : Auto Scale enable"
    ::= { wtWebGraphAnalog57661Datalogger 5 }

wtWebGraphAnalog57661VerticalUpperLimit OBJECT-TYPE
    SYNTAX OCTET STRING
    ACCESS read-write
    STATUS mandatory
    DESCRIPTION
        "This value defines the maximum temperature shown in the graphical presentation,
        if no auto scaling is selected.
        Temperature in degrees with maximum 2 decimal places."
    ::= { wtWebGraphAnalog57661Datalogger 6 }

wtWebGraphAnalog57661VerticalLowerLimit OBJECT-TYPE
    SYNTAX OCTET STRING
    ACCESS read-write
    STATUS mandatory
    DESCRIPTION
        "This value defines the minimum temperature shown in the graphical presentation,
        if no auto scaling is selected.
        Temperature in degrees with maximum 2 decimal places."
    ::= { wtWebGraphAnalog57661Datalogger 7 }

wtWebGraphAnalog57661HorizontalZoom OBJECT-TYPE
    SYNTAX INTEGER {
    wtWebGraphAnalog57661Zoom-25min(1),
    wtWebGraphAnalog57661Zoom-75min(2),
    wtWebGraphAnalog57661Zoom-5hrs(3),
    wtWebGraphAnalog57661Zoom-30hrs(4),
    wtWebGraphAnalog57661Zoom-5days(5),
    wtWebGraphAnalog57661Zoom-25days(6)
    }
    ACCESS read-write
    STATUS mandatory
    DESCRIPTION
        "Defines the default zoom stage, if no auto scaling is selected."
    ::= { wtWebGraphAnalog57661Datalogger 8 }

-- wtWebGraphAnalog57661Alarm Group
----------------------------

wtWebGraphAnalog57661AlarmCount OBJECT-TYPE
    SYNTAX INTEGER (1..8)
    ACCESS read-only
    STATUS mandatory
    DESCRIPTION
        "Number of independent alarms."
    ::= { wtWebGraphAnalog57661Alarm 1 }

-- Alarm Interface Table

wtWebGraphAnalog57661AlarmIfTable OBJECT-TYPE
    SYNTAX SEQUENCE OF WtWebGraphAnalog57661AlarmIfEntry
    ACCESS not-accessible
    STATUS mandatory
    DESCRIPTION
        "List of alarm indices."
    ::= { wtWebGraphAnalog57661Alarm 2 }

wtWebGraphAnalog57661AlarmIfEntry OBJECT-TYPE
    SYNTAX WtWebGraphAnalog57661AlarmIfEntry
    ACCESS not-accessible
    STATUS mandatory
    DESCRIPTION
        "Numbers of the alarms."
    INDEX  { wtWebGraphAnalog57661AlarmNo }
    ::= { wtWebGraphAnalog57661AlarmIfTable 1 }

WtWebGraphAnalog57661AlarmIfEntry ::= SEQUENCE {
    wtWebGraphAnalog57661AlarmNo INTEGER
}

wtWebGraphAnalog57661AlarmNo OBJECT-TYPE
    SYNTAX INTEGER (1..8)
    ACCESS read-only
    STATUS mandatory
    DESCRIPTION
        "Alarm number."
    ::= { wtWebGraphAnalog57661AlarmIfEntry 1 }

-- Alarm Table

wtWebGraphAnalog57661AlarmTable OBJECT-TYPE
    SYNTAX SEQUENCE OF WtWebGraphAnalog57661AlarmEntry
    ACCESS not-accessible
    STATUS mandatory
    DESCRIPTION
        "List of settings depending on the alarm number."
    ::= { wtWebGraphAnalog57661Alarm 3 }

wtWebGraphAnalog57661AlarmEntry OBJECT-TYPE
    SYNTAX WtWebGraphAnalog57661AlarmEntry
    ACCESS not-accessible
    STATUS mandatory
    DESCRIPTION
        "Alarm parameters of the individual alarms."
    INDEX  { wtWebGraphAnalog57661AlarmNo }
    ::= { wtWebGraphAnalog57661AlarmTable 1 }

WtWebGraphAnalog57661AlarmEntry ::= SEQUENCE {
    wtWebGraphAnalog57661AlarmTrigger			OCTET STRING,
    wtWebGraphAnalog57661AlarmMin1			OCTET STRING,
    wtWebGraphAnalog57661AlarmMax1			OCTET STRING,
    wtWebGraphAnalog57661AlarmHysteresis1		OCTET STRING,
    wtWebGraphAnalog57661AlarmDelay			OCTET STRING,
    wtWebGraphAnalog57661AlarmInterval			OCTET STRING,
    wtWebGraphAnalog57661AlarmEnable			OCTET STRING,
    wtWebGraphAnalog57661AlarmEMailAddr			OCTET STRING,
    wtWebGraphAnalog57661AlarmMailSubject		OCTET STRING,
    wtWebGraphAnalog57661AlarmMailText			OCTET STRING,
    wtWebGraphAnalog57661AlarmManagerIP			OCTET STRING,
    wtWebGraphAnalog57661AlarmTrapText			OCTET STRING,
    wtWebGraphAnalog57661AlarmMailOptions		OCTET STRING,
    wtWebGraphAnalog57661AlarmTcpIpAddr			OCTET STRING,
    wtWebGraphAnalog57661AlarmTcpPort			INTEGER,
    wtWebGraphAnalog57661AlarmTcpText			OCTET STRING,
    wtWebGraphAnalog57661AlarmClearMailSubject		OCTET STRING,
    wtWebGraphAnalog57661AlarmClearMailText		OCTET STRING,
    wtWebGraphAnalog57661AlarmClearTrapText		OCTET STRING,
    wtWebGraphAnalog57661AlarmClearTcpText		OCTET STRING,
    wtWebGraphAnalog57661AlarmMin2			OCTET STRING,
    wtWebGraphAnalog57661AlarmMax2			OCTET STRING,
    wtWebGraphAnalog57661AlarmHysteresis2		OCTET STRING,
    wtWebGraphAnalog57661AlarmSyslogIpAddr		OCTET STRING,
    wtWebGraphAnalog57661AlarmSyslogPort		INTEGER,
    wtWebGraphAnalog57661AlarmSyslogText		OCTET STRING,
    wtWebGraphAnalog57661AlarmSyslogClearText		OCTET STRING,
    wtWebGraphAnalog57661AlarmFtpDataPort		OCTET STRING,
    wtWebGraphAnalog57661AlarmFtpFileName		OCTET STRING,
    wtWebGraphAnalog57661AlarmFtpText			OCTET STRING,
    wtWebGraphAnalog57661AlarmFtpClearText		OCTET STRING,
    wtWebGraphAnalog57661AlarmFtpOption			OCTET STRING,
    wtWebGraphAnalog57661AlarmTimerCron			OCTET STRING

}

wtWebGraphAnalog57661AlarmTrigger OBJECT-TYPE
    SYNTAX OCTET STRING (SIZE(4))
    ACCESS read-write
    STATUS mandatory
    DESCRIPTION
        "Binary coded trigger conditions:
        Octet 1: unused
        Octet 2: unused
        Octet 3:
        	Bit 0: Timer
        	Bit 1: ColdStart
        	Bit 2: WarmStart

        Octet 4:
        	Bit 0: Sensor 1
        	Bit 1: Sensor 2
        	Bit 2-7: unused"
    ::= { wtWebGraphAnalog57661AlarmEntry 1 }

wtWebGraphAnalog57661AlarmMin1 OBJECT-TYPE
    SYNTAX OCTET STRING
    ACCESS read-write
    STATUS mandatory
    DESCRIPTION
        "Minimum sensor 1 with maximum 3 decimal places."
    ::= { wtWebGraphAnalog57661AlarmEntry 2 }

wtWebGraphAnalog57661AlarmMax1 OBJECT-TYPE
    SYNTAX OCTET STRING
    ACCESS read-write
    STATUS mandatory
    DESCRIPTION
        "Maximum sensor 1 with maximum 3 decimal places."
    ::= { wtWebGraphAnalog57661AlarmEntry 3 }

wtWebGraphAnalog57661AlarmHysteresis1 OBJECT-TYPE
    SYNTAX OCTET STRING
    ACCESS read-write
    STATUS mandatory
    DESCRIPTION
        "Reading changes of this size clears the alarm state (MAX-hyst, MIN+hyst.)
        with maximum 3 decimal places."
    ::= { wtWebGraphAnalog57661AlarmEntry 4 }

wtWebGraphAnalog57661AlarmDelay OBJECT-TYPE
    SYNTAX OCTET STRING
    ACCESS read-write
    STATUS mandatory
    DESCRIPTION
        "Alarm will be delayed by setting this time while stable alarm
        condition occur (time in minutes)."
    ::= { wtWebGraphAnalog57661AlarmEntry 5 }


wtWebGraphAnalog57661AlarmInterval OBJECT-TYPE
    SYNTAX OCTET STRING
    ACCESS read-write
    STATUS mandatory
    DESCRIPTION
        "Send interval for alarm messages."
    ::= { wtWebGraphAnalog57661AlarmEntry 6 }

wtWebGraphAnalog57661AlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  TCP Client enable
        	Bit 3:	Syslog enable
        	Bit 4:  FTP Client enable"
    ::= { wtWebGraphAnalog57661AlarmEntry 7 }

wtWebGraphAnalog57661AlarmEMailAddr OBJECT-TYPE
    SYNTAX OCTET STRING
    ACCESS read-write
    STATUS mandatory
    DESCRIPTION
        "E-Mail address for sending the alarm mail to."
    ::= { wtWebGraphAnalog57661AlarmEntry 8 }

wtWebGraphAnalog57661AlarmMailSubject OBJECT-TYPE
    SYNTAX OCTET STRING
    ACCESS read-write
    STATUS mandatory
    DESCRIPTION
        "Subject line for alarm mail."
    ::= { wtWebGraphAnalog57661AlarmEntry 9 }

wtWebGraphAnalog57661AlarmMailText OBJECT-TYPE
    SYNTAX OCTET STRING
    ACCESS read-write
    STATUS mandatory
    DESCRIPTION
        "Alarm mail text: <Mn> provides the current temperature; n = 1..2.
        <Z> provides the current time."
    ::= { wtWebGraphAnalog57661AlarmEntry 10 }

wtWebGraphAnalog57661AlarmManagerIP OBJECT-TYPE
    SYNTAX OCTET STRING
    ACCESS read-write
    STATUS mandatory
    DESCRIPTION
        "Name or IP address of the SNMP Manager which accepts the trap."
    ::= { wtWebGraphAnalog57661AlarmEntry 11 }

wtWebGraphAnalog57661AlarmTrapText OBJECT-TYPE
    SYNTAX OCTET STRING
    ACCESS read-write
    STATUS mandatory
    DESCRIPTION
        "This text is sent in the trap body."
    ::= { wtWebGraphAnalog57661AlarmEntry 12 }

wtWebGraphAnalog57661AlarmMailOptions OBJECT-TYPE
    SYNTAX OCTET STRING (SIZE(4))
    ACCESS read-write
    STATUS mandatory
    DESCRIPTION
        "Binary coded options:
        Octet 1: unused
        Octet 2: unused
        Octet 3: unused
        Octet 4:
		Bit 0  :	Attach Logger.csv Enable
		Bit 1  :	CSV-Data_since_last_report
        	Bit 2-7:	unused"
    ::= { wtWebGraphAnalog57661AlarmEntry 13 }

wtWebGraphAnalog57661AlarmTcpIpAddr OBJECT-TYPE
    SYNTAX OCTET STRING
    ACCESS read-write
    STATUS mandatory
    DESCRIPTION
        "Name or IP address of the TCP server which accepts the trap."
    ::= { wtWebGraphAnalog57661AlarmEntry 14 }

wtWebGraphAnalog57661AlarmTcpPort OBJECT-TYPE
    SYNTAX INTEGER (1..65535)
    ACCESS read-write
    STATUS mandatory
    DESCRIPTION
        "Port number of the TCP server which accepts the trap."
    ::= { wtWebGraphAnalog57661AlarmEntry 15 }

wtWebGraphAnalog57661AlarmTcpText OBJECT-TYPE
    SYNTAX OCTET STRING
    ACCESS read-write
    STATUS mandatory
    DESCRIPTION
        "This text is sent in the TCP trap body."
    ::= { wtWebGraphAnalog57661AlarmEntry 16 }

wtWebGraphAnalog57661AlarmClearMailSubject OBJECT-TYPE
    SYNTAX OCTET STRING
    ACCESS read-write
    STATUS mandatory
    DESCRIPTION
        "Subject line for alarm clear mail."
    ::= { wtWebGraphAnalog57661AlarmEntry 17 }

wtWebGraphAnalog57661AlarmClearMailText OBJECT-TYPE
    SYNTAX OCTET STRING
    ACCESS read-write
    STATUS mandatory
    DESCRIPTION
        "Alarm clear mail text: <Mn> provides the current temperature; n = 1..2.
        <Z> provides the current time."
    ::= { wtWebGraphAnalog57661AlarmEntry 18 }

wtWebGraphAnalog57661AlarmClearTrapText OBJECT-TYPE
    SYNTAX OCTET STRING
    ACCESS read-write
    STATUS mandatory
    DESCRIPTION
        "This text is sent in the trap body."
    ::= { wtWebGraphAnalog57661AlarmEntry 19 }

wtWebGraphAnalog57661AlarmClearTcpText OBJECT-TYPE
    SYNTAX OCTET STRING
    ACCESS read-write
    STATUS mandatory
    DESCRIPTION
        "This text is sent in the TCP trap body."
    ::= { wtWebGraphAnalog57661AlarmEntry 20 }

wtWebGraphAnalog57661AlarmMin2 OBJECT-TYPE
    SYNTAX OCTET STRING
    ACCESS read-write
    STATUS mandatory
    DESCRIPTION
        "Minimum sensor 2 with maximum 3 decimal places."
    ::= { wtWebGraphAnalog57661AlarmEntry 21 }

wtWebGraphAnalog57661AlarmMax2 OBJECT-TYPE
    SYNTAX OCTET STRING
    ACCESS read-write
    STATUS mandatory
    DESCRIPTION
        "Maximum sensor 2 with maximum 2 decimal places."
    ::= { wtWebGraphAnalog57661AlarmEntry 22 }

wtWebGraphAnalog57661AlarmHysteresis2 OBJECT-TYPE
    SYNTAX OCTET STRING
    ACCESS read-write
    STATUS mandatory
    DESCRIPTION
        "Hysterese rel. sensor 2 with maximum 3 decimal places."
    ::= { wtWebGraphAnalog57661AlarmEntry 23 }

wtWebGraphAnalog57661AlarmSyslogIpAddr OBJECT-TYPE
    SYNTAX OCTET STRING
    ACCESS read-write
    STATUS mandatory
    DESCRIPTION
        "IP address of the syslog server to which the Webio device should send syslog messages."
    ::= { wtWebGraphAnalog57661AlarmEntry 24 }

wtWebGraphAnalog57661AlarmSyslogPort OBJECT-TYPE
    SYNTAX INTEGER (1..65535)
    ACCESS read-write
    STATUS mandatory
    DESCRIPTION
        "Port number of the syslog server to which the Webio device should send syslog messages."
    ::= { wtWebGraphAnalog57661AlarmEntry 25 }

wtWebGraphAnalog57661AlarmSyslogText OBJECT-TYPE
    SYNTAX OCTET STRING
    ACCESS read-write
    STATUS mandatory
    DESCRIPTION
        "Every message starts with the priority key, a time stamp and the host ip address, according RFC3164.
        This text appears in the following syslog message body."
    ::= { wtWebGraphAnalog57661AlarmEntry 26 }

wtWebGraphAnalog57661AlarmSyslogClearText OBJECT-TYPE
    SYNTAX OCTET STRING
    ACCESS read-write
    STATUS mandatory
    DESCRIPTION
        "Every message starts with the priority key, a time stamp and the host ip address, according RFC3164.
        This text appears in the following syslog message body of a alarm clear message."
    ::= { wtWebGraphAnalog57661AlarmEntry 27 }

wtWebGraphAnalog57661AlarmFtpDataPort OBJECT-TYPE
    SYNTAX OCTET STRING
    ACCESS read-write
    STATUS mandatory
    DESCRIPTION
        "Local data port: 1..65535 or AUTO: the next free port will be assigned."
    ::= { wtWebGraphAnalog57661AlarmEntry 28 }

wtWebGraphAnalog57661AlarmFtpFileName OBJECT-TYPE
    SYNTAX OCTET STRING
    ACCESS read-write
    STATUS mandatory
    DESCRIPTION
        "Name of the file including path informations."
    ::= { wtWebGraphAnalog57661AlarmEntry 29 }

wtWebGraphAnalog57661AlarmFtpText OBJECT-TYPE
    SYNTAX OCTET STRING
    ACCESS read-write
    STATUS mandatory
    DESCRIPTION
        "Message text to store on the FTP server."
    ::= { wtWebGraphAnalog57661AlarmEntry 30 }

wtWebGraphAnalog57661AlarmFtpClearText OBJECT-TYPE
    SYNTAX OCTET STRING
    ACCESS read-write
    STATUS mandatory
    DESCRIPTION
        "Alarm clear message to store on the FTP server."
    ::= { wtWebGraphAnalog57661AlarmEntry 31 }

wtWebGraphAnalog57661AlarmFtpOption OBJECT-TYPE
    SYNTAX OCTET STRING (SIZE(4))
    ACCESS read-write
    STATUS mandatory
    DESCRIPTION
        "Binary coded options, select only one option at the same time:
        STORE  = replace file
        APPEND = append message at the end of the file

        Octet 1: unused
        Octet 2: unused
        Octet 3: unused
        Octet 4:
		Bit 0  :	STORE
		Bit 1  :	APPEND
        	Bit 2-7:	unused"
    ::= { wtWebGraphAnalog57661AlarmEntry 32 }

wtWebGraphAnalog57661AlarmTimerCron OBJECT-TYPE
    SYNTAX OCTET STRING
    ACCESS read-write
    STATUS mandatory
    DESCRIPTION
        "This entry defines a time window for alarm 1-8 and a activation time for the report.
        A time window is definied by start and stop time stamp, seperated by a space or tab.
        The activation time of the report is defined by a single start time stamp.
        Each time stamp contains 5 space or tab seperated text fields for time trigger definition.
        Each field must match with the actual time to trigger an action, weekday and day of month
        are interpreted separatley.
        1: Minutes	Range 0-59
        2. Hours	Range 0-23, 0 is midnight
        3: Day of month	Range 1-31
        4: Month	Range 1-12
        5: Weekday	Range 0-6, 0 is sunday

        Syntax for every field:
         - an asterix (*) enables every possible setting of a field
         - single numbers seperated by commas (i.e.: 2,14,22)
         - a partition within the allowed range (i.e.: 1-5)
         - step size within a partition of the allowed range (i.e.: 0-59/2  every second minute)."
    ::= { wtWebGraphAnalog57661AlarmEntry 33 }

-- wtWebGraphAnalog57661GraphicsBase Group
----------------------------

wtWebGraphAnalog57661GraphicsBaseEnable OBJECT-TYPE
    SYNTAX OCTET STRING
    ACCESS read-write
    STATUS mandatory
    DESCRIPTION
        "Defines the viewing options of the graphic:
        Octet 1: unused
        Octet 2: unused
        Octet 3: unused
        Octet 4:
                Bit 0  : Auto scroll enable
                Bit 1  : Show table
                Bit 2  : Show graph
                Bit 3  : Show control buttons
                Bit 4  : Show config menu
                Bit 5-7: unused"
    ::= { wtWebGraphAnalog57661GraphicsBase 1 }

wtWebGraphAnalog57661GraphicsBaseWidth OBJECT-TYPE
    SYNTAX INTEGER
    ACCESS read-write
    STATUS mandatory
    DESCRIPTION
        "Defines the width of the graphic in pixels."
    ::= { wtWebGraphAnalog57661GraphicsBase 2 }

wtWebGraphAnalog57661GraphicsBaseHeight OBJECT-TYPE
        SYNTAX INTEGER
        ACCESS read-write
        STATUS mandatory
        DESCRIPTION
            "Defines the height of the graphic in pixels."
        ::= { wtWebGraphAnalog57661GraphicsBase 3 }

wtWebGraphAnalog57661GraphicsBaseFrameColor OBJECT-TYPE
    SYNTAX OCTET STRING (SIZE(3))
    ACCESS read-write
    STATUS mandatory
    DESCRIPTION
        "Frame color definition in RGB."
    ::= { wtWebGraphAnalog57661GraphicsBase 4 }

wtWebGraphAnalog57661GraphicsBaseBackgroundColor OBJECT-TYPE
    SYNTAX OCTET STRING (SIZE(3))
    ACCESS read-write
    STATUS mandatory
    DESCRIPTION
        "Background color definition in RGB."
    ::= { wtWebGraphAnalog57661GraphicsBase 5 }

wtWebGraphAnalog57661GraphicsBasePollingrate OBJECT-TYPE
        SYNTAX INTEGER
        ACCESS read-write
        STATUS mandatory
        DESCRIPTION
            "Defines the pollingrate in seconds,
            which defines the refreshing intervall of the graphic."
        ::= { wtWebGraphAnalog57661GraphicsBase 6 }

-- wtWebGraphAnalog57661GraphicsSelect Group
----------------------------

wtWebGraphAnalog57661GraphicsSelectDisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1: Sensor 2
        	Bit 2-7: unused"
    ::= { wtWebGraphAnalog57661GraphicsSelect 1 }

wtWebGraphAnalog57661GraphicsSelectDisplayShowExtrem OBJECT-TYPE
    SYNTAX OCTET STRING (SIZE(4))
    ACCESS read-write
    STATUS mandatory
    DESCRIPTION
        "Binary coded sensor selection:
        only selected sensors will be shown with minima and maxima:
        Octet 1: unused
        Octet 2: unused
        Octet 3: unused
        Octet 4:
        	Bit 0: Sensor 1
        	Bit 1: Sensor 2
        	Bit 2-7: unused"
     ::= { wtWebGraphAnalog57661GraphicsSelect 2 }

-- Graph Sensor Color Table

wtWebGraphAnalog57661SensorColor2Table OBJECT-TYPE
    SYNTAX SEQUENCE OF WtWebGraphAnalog57661SensorColor2Entry
    ACCESS not-accessible
    STATUS mandatory
    DESCRIPTION
        "List of sensor colors for the praphical presentation."
    ::= { wtWebGraphAnalog57661GraphicsSelect 3 }

wtWebGraphAnalog57661SensorColor2Entry OBJECT-TYPE
    SYNTAX WtWebGraphAnalog57661SensorColor2Entry
    ACCESS not-accessible
    STATUS mandatory
    DESCRIPTION
        "Numbers of the sensors."
    INDEX  { wtWebGraphAnalog57661SensorNo }
    ::= { wtWebGraphAnalog57661SensorColor2Table 1 }

WtWebGraphAnalog57661SensorColor2Entry ::= SEQUENCE {
    wtWebGraphAnalog57661GraphicsSensorColor OCTET STRING,
    wtWebGraphAnalog57661GraphicsSelectScale OCTET STRING
}

wtWebGraphAnalog57661GraphicsSensorColor OBJECT-TYPE
    SYNTAX OCTET STRING (SIZE(3))
    ACCESS read-write
    STATUS mandatory
    DESCRIPTION
        "Color of the sensors at the praphical presention."
    ::= { wtWebGraphAnalog57661SensorColor2Entry 1 }

wtWebGraphAnalog57661GraphicsSelectScale OBJECT-TYPE
    SYNTAX OCTET STRING
    ACCESS read-write
    STATUS mandatory
    DESCRIPTION
        "Assignes one of 4 scales to a sensor:
        Octet 1: unused
        Octet 2: unused
        Octet 3: unused
        Octet 4:
                Bit 0  : Use Scale 1
                Bit 1  : Use Scale 2
                Bit 2-7: unused"
    ::= { wtWebGraphAnalog57661SensorColor2Entry 2 }

-- wtWebGraphAnalog57661GraphicsScale Group
----------------------------

wtWebGraphAnalog57661GraphicsScaleAutoScaleEnable OBJECT-TYPE
    SYNTAX OCTET STRING
    ACCESS read-write
    STATUS mandatory
    DESCRIPTION
        "Select the Auto Scale Mode:
        Octet 1: unused
        Octet 2: unused
        Octet 3: unused
        Octet 4:
                Bit 0  : Scale 1 Auto scale enable
                Bit 1  : Scale 2 Auto scale enable
                Bit 2-7: unused"
    ::= { wtWebGraphAnalog57661GraphicsScale 1 }


wtWebGraphAnalog57661GraphicsScaleAutoFitEnable OBJECT-TYPE
    SYNTAX OCTET STRING
    ACCESS read-write
    STATUS mandatory
    DESCRIPTION
        "Select the Auto Fit Mode::
        Octet 1: unused
        Octet 2: unused
        Octet 3: unused
        Octet 4:
                Bit 0  : Scale 1 Auto fit enable
                Bit 1  : Scale 2 Auto fit enable
                Bit 2-7: unused"
    ::= { wtWebGraphAnalog57661GraphicsScale 2 }

wtWebGraphAnalog57661GraphicsScale1Min OBJECT-TYPE
    SYNTAX INTEGER
    ACCESS read-only
    STATUS mandatory
    DESCRIPTION
        "Scale 1: Minimum."
    ::= { wtWebGraphAnalog57661GraphicsScale 3 }

wtWebGraphAnalog57661GraphicsScale2Min OBJECT-TYPE
    SYNTAX INTEGER
    ACCESS read-only
    STATUS mandatory
    DESCRIPTION
        "Scale 2: Minimum."
    ::= { wtWebGraphAnalog57661GraphicsScale 4 }

wtWebGraphAnalog57661GraphicsScale1Max OBJECT-TYPE
    SYNTAX INTEGER
    ACCESS read-only
    STATUS mandatory
    DESCRIPTION
        "Scale 1: Maximum."
    ::= { wtWebGraphAnalog57661GraphicsScale 7 }

wtWebGraphAnalog57661GraphicsScale2Max OBJECT-TYPE
    SYNTAX INTEGER
    ACCESS read-only
    STATUS mandatory
    DESCRIPTION
        "Scale 2: Maximum."
    ::= { wtWebGraphAnalog57661GraphicsScale 8 }

wtWebGraphAnalog57661GraphicsScale1Unit OBJECT-TYPE
    SYNTAX OCTET STRING
    ACCESS read-only
    STATUS mandatory
    DESCRIPTION
        "Scale 1: Unit."
    ::= { wtWebGraphAnalog57661GraphicsScale 11 }

wtWebGraphAnalog57661GraphicsScale2Unit OBJECT-TYPE
    SYNTAX OCTET STRING
    ACCESS read-only
    STATUS mandatory
    DESCRIPTION
        "Scale 2: Unit."
    ::= { wtWebGraphAnalog57661GraphicsScale 12 }

-- wtWebGraphAnalog57661Report Group
----------------------------

wtWebGraphAnalog57661ReportCount OBJECT-TYPE
    SYNTAX INTEGER (1..8)
    ACCESS read-only
    STATUS mandatory
    DESCRIPTION
        "Number of independent Reports."
    ::= { wtWebGraphAnalog57661Report 1 }

-- Report Interface Table

wtWebGraphAnalog57661ReportIfTable OBJECT-TYPE
    SYNTAX SEQUENCE OF WtWebGraphAnalog57661ReportIfEntry
    ACCESS not-accessible
    STATUS mandatory
    DESCRIPTION
        "List of Report indices."
    ::= { wtWebGraphAnalog57661Report 2 }

wtWebGraphAnalog57661ReportIfEntry OBJECT-TYPE
    SYNTAX WtWebGraphAnalog57661ReportIfEntry
    ACCESS not-accessible
    STATUS mandatory
    DESCRIPTION
        "Numbers of the Reports."
    INDEX  { wtWebGraphAnalog57661ReportNo }
    ::= { wtWebGraphAnalog57661ReportIfTable 1 }

WtWebGraphAnalog57661ReportIfEntry ::= SEQUENCE {
    wtWebGraphAnalog57661ReportNo INTEGER
}

wtWebGraphAnalog57661ReportNo OBJECT-TYPE
    SYNTAX INTEGER
    ACCESS read-only
    STATUS mandatory
    DESCRIPTION
        "Report number."
    ::= { wtWebGraphAnalog57661ReportIfEntry 1 }

-- Report Table

wtWebGraphAnalog57661ReportTable OBJECT-TYPE
    SYNTAX SEQUENCE OF WtWebGraphAnalog57661ReportEntry
    ACCESS not-accessible
    STATUS mandatory
    DESCRIPTION
        "List of settings depending on the Report number."
    ::= { wtWebGraphAnalog57661Report 3 }

wtWebGraphAnalog57661ReportEntry OBJECT-TYPE
    SYNTAX WtWebGraphAnalog57661ReportEntry
    ACCESS not-accessible
    STATUS mandatory
    DESCRIPTION
        "Report parameters of the individual Reports."
    INDEX  { wtWebGraphAnalog57661ReportNo }
    ::= { wtWebGraphAnalog57661ReportTable 1 }

WtWebGraphAnalog57661ReportEntry ::= SEQUENCE {
    wtWebGraphAnalog57661ReportEnable			OCTET STRING,
    wtWebGraphAnalog57661ReportTimerCron		OCTET STRING,
    wtWebGraphAnalog57661ReportMethodeEnable		OCTET STRING,
    wtWebGraphAnalog57661ReportEMailAddr			OCTET STRING,
    wtWebGraphAnalog57661ReportMailSubject		OCTET STRING,
    wtWebGraphAnalog57661ReportMailText			OCTET STRING,
    wtWebGraphAnalog57661ReportManagerIP		OCTET STRING,
    wtWebGraphAnalog57661ReportTrapText			OCTET STRING,
    wtWebGraphAnalog57661ReportMailOptions		OCTET STRING,
    wtWebGraphAnalog57661ReportTcpIpAddr		OCTET STRING,
    wtWebGraphAnalog57661ReportTcpPort			INTEGER,
    wtWebGraphAnalog57661ReportTcpText			OCTET STRING,
    wtWebGraphAnalog57661ReportClearMailSubject		OCTET STRING,
    wtWebGraphAnalog57661ReportClearMailText		OCTET STRING,
    wtWebGraphAnalog57661ReportClearTrapText		OCTET STRING,
    wtWebGraphAnalog57661ReportClearTcpText		OCTET STRING,
    wtWebGraphAnalog57661ReportSyslogIpAddr		OCTET STRING,
    wtWebGraphAnalog57661ReportSyslogPort		INTEGER,
    wtWebGraphAnalog57661ReportSyslogText		OCTET STRING,
    wtWebGraphAnalog57661ReportSyslogClearText		OCTET STRING,
    wtWebGraphAnalog57661ReportFtpDataPort		OCTET STRING,
    wtWebGraphAnalog57661ReportFtpFileName		OCTET STRING,
    wtWebGraphAnalog57661ReportFtpText			OCTET STRING,
    wtWebGraphAnalog57661ReportFtpClearText		OCTET STRING,
    wtWebGraphAnalog57661ReportFtpOption		OCTET STRING
}

wtWebGraphAnalog57661ReportEnable OBJECT-TYPE
    SYNTAX OCTET STRING (SIZE(4))
    ACCESS read-write
    STATUS mandatory
    DESCRIPTION
        "Binär kodierte Triggerbedingungen:
        Octet 1: unused
        Octet 2: unused
        Octet 3: unused
        Octet 4:
        	Bit 0: Report enable
        	Bit 1-7: unused"
    ::= { wtWebGraphAnalog57661ReportEntry 1 }

wtWebGraphAnalog57661ReportTimerCron OBJECT-TYPE
    SYNTAX OCTET STRING
    ACCESS read-write
    STATUS mandatory
    DESCRIPTION
        "This entry defines a time window for alarm 1-8 and a activation time for the report.
        A time window is definied by start and stop time stamp, seperated by a space or tab.
        The activation time of the report is defined by a single start time stamp.
        Each time stamp contains 5 space or tab seperated text fields for time trigger definition.
        Each field must match with the actual time to trigger an action, weekday and day of month
        are interpreted separatley.
        1: Minutes	Range 0-59
        2. Hours	Range 0-23, 0 is midnight
        3: Day of month	Range 1-31
        4: Month	Range 1-12
        5: Weekday	Range 0-6, 0 is sunday

        Syntax for every field:
         - an asterix (*) enables every possible setting of a field
         - single numbers seperated by commas (i.e.: 2,14,22)
         - a partition within the allowed range (i.e.: 1-5)
         - step size within a partition of the allowed range (i.e.: 0-59/2  every second minute)."
    ::= { wtWebGraphAnalog57661ReportEntry 2 }

wtWebGraphAnalog57661ReportMethodeEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  TCP Client enable
        	Bit 3:	Syslog enable
        	Bit 4:  FTP Client enable"
    ::= { wtWebGraphAnalog57661ReportEntry 3 }

wtWebGraphAnalog57661ReportEMailAddr OBJECT-TYPE
    SYNTAX OCTET STRING
    ACCESS read-write
    STATUS mandatory
    DESCRIPTION
        "E-Mail address for sending the alarm mail to."
    ::= { wtWebGraphAnalog57661ReportEntry 8 }

wtWebGraphAnalog57661ReportMailSubject OBJECT-TYPE
    SYNTAX OCTET STRING
    ACCESS read-write
    STATUS mandatory
    DESCRIPTION
        "Subject line for alarm mail."
    ::= { wtWebGraphAnalog57661ReportEntry 9 }

wtWebGraphAnalog57661ReportMailText OBJECT-TYPE
    SYNTAX OCTET STRING
    ACCESS read-write
    STATUS mandatory
    DESCRIPTION
        "Report mail text: <Mn> provides the current temperature; n = 1..2.
        <Z> provides the current time."
    ::= { wtWebGraphAnalog57661ReportEntry 10 }

wtWebGraphAnalog57661ReportManagerIP OBJECT-TYPE
    SYNTAX OCTET STRING
    ACCESS read-write
    STATUS mandatory
    DESCRIPTION
        "Name or IP address of the SNMP Manager which accepts the trap."
    ::= { wtWebGraphAnalog57661ReportEntry 11 }

wtWebGraphAnalog57661ReportTrapText OBJECT-TYPE
    SYNTAX OCTET STRING
    ACCESS read-write
    STATUS mandatory
    DESCRIPTION
        "This text is sent in the trap body."
    ::= { wtWebGraphAnalog57661ReportEntry 12 }

wtWebGraphAnalog57661ReportMailOptions OBJECT-TYPE
    SYNTAX OCTET STRING (SIZE(4))
    ACCESS read-write
    STATUS mandatory
    DESCRIPTION
        "Binary coded options:
        Octet 1: unused
        Octet 2: unused
        Octet 3: unused
        Octet 4:
		Bit 0  :	Attach Logger.csv Enable
		Bit 1  :	CSV-Data_since_last_report
        	Bit 2-7:	unused"
    ::= { wtWebGraphAnalog57661ReportEntry 13 }

wtWebGraphAnalog57661ReportTcpIpAddr OBJECT-TYPE
    SYNTAX OCTET STRING
    ACCESS read-write
    STATUS mandatory
    DESCRIPTION
        "Name or IP address of the TCP server which accepts the trap."
    ::= { wtWebGraphAnalog57661ReportEntry 14 }

wtWebGraphAnalog57661ReportTcpPort OBJECT-TYPE
    SYNTAX INTEGER (1..65535)
    ACCESS read-write
    STATUS mandatory
    DESCRIPTION
        "Port number of the TCP server which accepts the trap."
    ::= { wtWebGraphAnalog57661ReportEntry 15 }

wtWebGraphAnalog57661ReportTcpText OBJECT-TYPE
    SYNTAX OCTET STRING
    ACCESS read-write
    STATUS mandatory
    DESCRIPTION
        "This text is sent in the TCP trap body."
    ::= { wtWebGraphAnalog57661ReportEntry 16 }

wtWebGraphAnalog57661ReportClearMailSubject OBJECT-TYPE
    SYNTAX OCTET STRING
    ACCESS read-write
    STATUS mandatory
    DESCRIPTION
        "Subject line for alarm clear mail."
    ::= { wtWebGraphAnalog57661ReportEntry 17 }

wtWebGraphAnalog57661ReportClearMailText OBJECT-TYPE
    SYNTAX OCTET STRING
    ACCESS read-write
    STATUS mandatory
    DESCRIPTION
        "Report clear mail text: <Mn> provides the current temperature; n = 1..2.
        <Z> provides the current time."
    ::= { wtWebGraphAnalog57661ReportEntry 18 }

wtWebGraphAnalog57661ReportClearTrapText OBJECT-TYPE
    SYNTAX OCTET STRING
    ACCESS read-write
    STATUS mandatory
    DESCRIPTION
        "This text is sent in the trap body."
    ::= { wtWebGraphAnalog57661ReportEntry 19 }

wtWebGraphAnalog57661ReportClearTcpText OBJECT-TYPE
    SYNTAX OCTET STRING
    ACCESS read-write
    STATUS mandatory
    DESCRIPTION
        "This text is sent in the TCP trap body."
    ::= { wtWebGraphAnalog57661ReportEntry 20 }

wtWebGraphAnalog57661ReportSyslogIpAddr OBJECT-TYPE
    SYNTAX OCTET STRING
    ACCESS read-write
    STATUS mandatory
    DESCRIPTION
        "IP address of the syslog server to which the Webio device should send syslog messages."
    ::= { wtWebGraphAnalog57661ReportEntry 24 }

wtWebGraphAnalog57661ReportSyslogPort OBJECT-TYPE
    SYNTAX INTEGER (1..65535)
    ACCESS read-write
    STATUS mandatory
    DESCRIPTION
        "Port number of the syslog server to which the Webio device should send syslog messages."
    ::= { wtWebGraphAnalog57661ReportEntry 25 }

wtWebGraphAnalog57661ReportSyslogText OBJECT-TYPE
    SYNTAX OCTET STRING
    ACCESS read-write
    STATUS mandatory
    DESCRIPTION
        "Every message starts with the priority key, a time stamp and the host ip address, according RFC3164.
        This text appears in the following syslog message body."
    ::= { wtWebGraphAnalog57661ReportEntry 26 }

wtWebGraphAnalog57661ReportSyslogClearText OBJECT-TYPE
    SYNTAX OCTET STRING
    ACCESS read-write
    STATUS mandatory
    DESCRIPTION
        "Every message starts with the priority key, a time stamp and the host ip address, according RFC3164.
        This text appears in the following syslog message body of a alarm clear message."
    ::= { wtWebGraphAnalog57661ReportEntry 27 }

wtWebGraphAnalog57661ReportFtpDataPort OBJECT-TYPE
    SYNTAX OCTET STRING
    ACCESS read-write
    STATUS mandatory
    DESCRIPTION
        "Local data port: 1..65535 or AUTO: the next free port will be assigned."
    ::= { wtWebGraphAnalog57661ReportEntry 28 }

wtWebGraphAnalog57661ReportFtpFileName OBJECT-TYPE
    SYNTAX OCTET STRING
    ACCESS read-write
    STATUS mandatory
    DESCRIPTION
        "Name of the file including path informations."
    ::= { wtWebGraphAnalog57661ReportEntry 29 }

wtWebGraphAnalog57661ReportFtpText OBJECT-TYPE
    SYNTAX OCTET STRING
    ACCESS read-write
    STATUS mandatory
    DESCRIPTION
        "Message text to store on the FTP server."
    ::= { wtWebGraphAnalog57661ReportEntry 30 }

wtWebGraphAnalog57661ReportFtpClearText OBJECT-TYPE
    SYNTAX OCTET STRING
    ACCESS read-write
    STATUS mandatory
    DESCRIPTION
        "Report clear message to store on the FTP server."
    ::= { wtWebGraphAnalog57661ReportEntry 31 }

wtWebGraphAnalog57661ReportFtpOption OBJECT-TYPE
    SYNTAX OCTET STRING (SIZE(4))
    ACCESS read-write
    STATUS mandatory
    DESCRIPTION
        "Binary coded options, select only one option at the same time:
        STORE  = replace file
        APPEND = append message at the end of the file

        Octet 1: unused
        Octet 2: unused
        Octet 3: unused
        Octet 4:
		Bit 0  :	STORE
		Bit 1  :	APPEND
        	Bit 2-7:	unused"
    ::= { wtWebGraphAnalog57661ReportEntry 32 }

-- wtWebGraphAnalog57661Ports Group
----------------------------

-- Table

wtWebGraphAnalog57661PortTable OBJECT-TYPE
    SYNTAX SEQUENCE OF WtWebGraphAnalog57661PortEntry
    ACCESS not-accessible
    STATUS mandatory
    DESCRIPTION
        "List of settings depending on the sensor number."
    ::= { wtWebGraphAnalog57661Ports 1 }

wtWebGraphAnalog57661PortEntry OBJECT-TYPE
    SYNTAX WtWebGraphAnalog57661PortEntry
    ACCESS not-accessible
    STATUS mandatory
    DESCRIPTION
        "Sensor parameters for the individual sensors."
    INDEX  { wtWebGraphAnalog57661SensorNo }
    ::= { wtWebGraphAnalog57661PortTable 1 }

WtWebGraphAnalog57661PortEntry ::= SEQUENCE {
    wtWebGraphAnalog57661PortName		OCTET STRING,
    wtWebGraphAnalog57661PortText		OCTET STRING,
    wtWebGraphAnalog57661PortOffset1		OCTET STRING,
    wtWebGraphAnalog57661SetPoint1		OCTET STRING,
    wtWebGraphAnalog57661PortOffset2		OCTET STRING,
    wtWebGraphAnalog57661SetPoint2		OCTET STRING,
    wtWebGraphAnalog57661PortComment		OCTET STRING,
    wtWebGraphAnalog57661PortSensorSelect	OCTET STRING,
    wtWebGraphAnalog57661PortUnit		OCTET STRING,
    wtWebGraphAnalog57661PortScale0		OCTET STRING,
    wtWebGraphAnalog57661PortScale100		OCTET STRING,
    wtWebGraphAnalog57661PortOutputMode		OCTET STRING,
    wtWebGraphAnalog57661PortInputMode		OCTET STRING
}

wtWebGraphAnalog57661PortName OBJECT-TYPE
    SYNTAX OCTET STRING
    ACCESS read-write
    STATUS mandatory
    DESCRIPTION
        "Name of the sensor."
    ::= { wtWebGraphAnalog57661PortEntry 1 }

wtWebGraphAnalog57661PortText OBJECT-TYPE
    SYNTAX OCTET STRING
    ACCESS read-write
    STATUS mandatory
    DESCRIPTION
        "Description of the sensor."
    ::= { wtWebGraphAnalog57661PortEntry 2 }

wtWebGraphAnalog57661PortOffset1 OBJECT-TYPE
    SYNTAX OCTET STRING
    ACCESS read-write
    STATUS mandatory
    DESCRIPTION
        "Offset calibration: Offset in degrees with maximum 3 decimal places at set point 1."
    ::= { wtWebGraphAnalog57661PortEntry 3 }

wtWebGraphAnalog57661SetPoint1 OBJECT-TYPE
    SYNTAX OCTET STRING
    ACCESS read-write
    STATUS mandatory
    DESCRIPTION
        "Offset calibration: Reference set point 1 in degrees with maximum 3 decimal places."
    ::= { wtWebGraphAnalog57661PortEntry 4 }

wtWebGraphAnalog57661PortOffset2 OBJECT-TYPE
    SYNTAX OCTET STRING
    ACCESS read-write
    STATUS mandatory
    DESCRIPTION
        "Offset calibration: Offset in degrees with maximum 3 decimal places at set point 2."
    ::= { wtWebGraphAnalog57661PortEntry 5 }

wtWebGraphAnalog57661SetPoint2 OBJECT-TYPE
    SYNTAX OCTET STRING
    ACCESS read-write
    STATUS mandatory
    DESCRIPTION
        "Offset calibration: Reference set point 2 in degrees with maximum 3 decimal places."
    ::= { wtWebGraphAnalog57661PortEntry 6 }

wtWebGraphAnalog57661PortComment OBJECT-TYPE
    SYNTAX OCTET STRING
    ACCESS read-write
    STATUS mandatory
    DESCRIPTION
        "Offset calibration: informations of date, name of operator, reference devices."
    ::= { wtWebGraphAnalog57661PortEntry 7 }

wtWebGraphAnalog57661PortSensorSelect OBJECT-TYPE
    SYNTAX OCTET STRING (SIZE(4))
    ACCESS read-write
    STATUS mandatory
    DESCRIPTION
        "Binary coded options for sensor 1:
        Octet 1: unused
        Octet 2: unused
        Octet 3: unused
        Octet 4:
		Bit 0  :	0-20mA (default)
		Bit 1  :	4-20mA
		Bit 2  :	Disconnect
        	Bit 3-7:	unused"
    ::= { wtWebGraphAnalog57661PortEntry 8 }

wtWebGraphAnalog57661PortUnit OBJECT-TYPE
    SYNTAX OCTET STRING
    ACCESS read-write
    STATUS mandatory
    DESCRIPTION
        "User scale: displayed unit."
    ::= { wtWebGraphAnalog57661PortEntry 9 }

wtWebGraphAnalog57661PortScale0 OBJECT-TYPE
    SYNTAX OCTET STRING
    ACCESS read-write
    STATUS mandatory
    DESCRIPTION
        "User scale: displayed value in 1/1000 at 0% full scale range.
        Range: -999999.999 to 999999.999"
    ::= { wtWebGraphAnalog57661PortEntry 10 }

wtWebGraphAnalog57661PortScale100 OBJECT-TYPE
    SYNTAX OCTET STRING
    ACCESS read-write
    STATUS mandatory
    DESCRIPTION
        "User scale: displayed value in 1/1000 at 100% full scale range.
        Range: -999999.999 to 999999.999"
    ::= { wtWebGraphAnalog57661PortEntry 11 }

wtWebGraphAnalog57661PortOutputMode OBJECT-TYPE
    SYNTAX OCTET STRING (SIZE (4))
    ACCESS read-write
    STATUS mandatory
    DESCRIPTION
        "This binary coded output mode defines the individual operation mode for any
        output. More than one mode must not be selected. If an output mode is selected,
        Bit 2 in wtWebGraphAnalog57661PortInputMode will be set automatically.
        The OCTETS are interpreted bit-by-bit, Bit 0 corresponds to the LSB.
        OCTET 1: unused
        OCTET 2: unused
        OCTET 3: unused
        OCTET 4: Bit 6-7: unused
        	 Bit 5  : Output OFF
        	 Bit 4  : Binary 2
        	 Bit 3  : Binary 1
        	 Bit 2  : SNMP
        	 Bit 1  : UDP ASCII
        	 Bit 0  : HTTP"
    ::= { wtWebGraphAnalog57661PortEntry 12 }

wtWebGraphAnalog57661PortInputMode OBJECT-TYPE
    SYNTAX OCTET STRING (SIZE (4))
    ACCESS read-write
    STATUS mandatory
    DESCRIPTION
        "This binary coded input mode defines the individual operation mode for any
        input. More than one mode must not be selected. If an input mode is selected,
        Bit 5 in wtWebGraphAnalog57661PortOutputMode will be set automatically.
        The OCTETS are interpreted bit-by-bit,Bit 0 corresponds to the LSB.
        OCTET 1: ungenutzt
        OCTET 2: ungenutzt
        OCTET 3: ungenutzt
        OCTET 4: Bit 3-7: unused
        	 Bit 2  : I-Output
        	 Bit 1  : I-Input, active
        	 Bit 0  : I-Input, passive"
    ::= { wtWebGraphAnalog57661PortEntry 13 }

-- wtWebGraphAnalog57661Manufact Group
----------------------------

wtWebGraphAnalog57661MfName OBJECT-TYPE
    SYNTAX OCTET STRING
    ACCESS read-write
    STATUS mandatory
    DESCRIPTION
        "Manufacturer company name"
    ::= { wtWebGraphAnalog57661Manufact 1 }

wtWebGraphAnalog57661MfAddr OBJECT-TYPE
    SYNTAX OCTET STRING
    ACCESS read-write
    STATUS mandatory
    DESCRIPTION
        "Manufacturer address."
    ::= { wtWebGraphAnalog57661Manufact 2 }

wtWebGraphAnalog57661MfHotline OBJECT-TYPE
    SYNTAX OCTET STRING
    ACCESS read-write
    STATUS mandatory
    DESCRIPTION
        "Manufacturer hotline."
    ::= { wtWebGraphAnalog57661Manufact 3 }

wtWebGraphAnalog57661MfInternet OBJECT-TYPE
    SYNTAX OCTET STRING
    ACCESS read-write
    STATUS mandatory
    DESCRIPTION
        "Manufacturer Internet address."
    ::= { wtWebGraphAnalog57661Manufact 4 }

wtWebGraphAnalog57661MfDeviceTyp OBJECT-TYPE
    SYNTAX OCTET STRING
    ACCESS read-write
    STATUS mandatory
    DESCRIPTION
        "Manufacturer device name (model number)."
    ::= { wtWebGraphAnalog57661Manufact 5 }

wtWebGraphAnalog57661MfOrderNo OBJECT-TYPE
    SYNTAX OCTET STRING
    ACCESS read-write
    STATUS mandatory
    DESCRIPTION
        "Manufacturer part number."
    ::= { wtWebGraphAnalog57661Manufact 6 }

-- wtWebGraphAnalog57661Diag Group
----------------------------

wtWebGraphAnalog57661DiagErrorCount OBJECT-TYPE
    SYNTAX INTEGER
    ACCESS read-only
    STATUS mandatory
    DESCRIPTION
        "Number of entries in the error memory."
    ::= { wtWebGraphAnalog57661Diag 1 }

wtWebGraphAnalog57661DiagBinaryError OBJECT-TYPE
    SYNTAX OCTET STRING
    ACCESS read-only
    STATUS mandatory
    DESCRIPTION
        "Error causes coded bit-by-bit."
    ::= { wtWebGraphAnalog57661Diag 2 }

wtWebGraphAnalog57661DiagErrorIndex OBJECT-TYPE
    SYNTAX INTEGER
    ACCESS read-write
    STATUS mandatory
    DESCRIPTION
        "The value of this variable is used as an index to read
        an error massege from wtWebGraphAnalog57661DiagErrorMessage.
        Errors are numbered from 1 to wtWebGraphAnalog57661DiagErrorCount.
        Writing a valid value into this variable, making the appropriate
        message readable from wtWebGraphAnalog57661DiagErrorMessage."
    ::= { wtWebGraphAnalog57661Diag 3 }

wtWebGraphAnalog57661DiagErrorMessage OBJECT-TYPE
    SYNTAX OCTET STRING
    ACCESS read-only
    STATUS mandatory
    DESCRIPTION
        "Using wtWebGraphAnalog57661DiagErrorIndex as an index, the appropriate message is available."
    ::= { wtWebGraphAnalog57661Diag 4 }

wtWebGraphAnalog57661DiagErrorClear OBJECT-TYPE
    SYNTAX INTEGER
    ACCESS write-only
    STATUS mandatory
    DESCRIPTION
        "Writing 1 into this variable clears all diagnosis messages."
    ::= { wtWebGraphAnalog57661Diag 5 }

-- TRAP DEFINITIONS

-- Diese SNMP-Traps werden gesendet, wenn die Alarmtriggerbedingungen zutreffen

wtWebGraphAnalog57661Alert1 TRAP-TYPE
    ENTERPRISE  wtWebGraphAnalog57661
    VARIABLES   { wtWebGraphAnalog57661AlarmTrapText }
    DESCRIPTION
        "This SNMP trap is generated when Alarm 1 was triggered,
        SNMP trap enable is set and
        SNMP is enabled."
    -- NMS trap annotation
    --#TYPE "Web-IO Analog-InOut Alarm 1"
    --#SUMMARY "Alarm 1: %s"
    --#ARGUMENTS {0}
    --#SEVERITY INFORMATIONAL
    --#TIMEINDEX 99
    --#STATE OPERATIONAL
    ::= 31

wtWebGraphAnalog57661Alert2 TRAP-TYPE
    ENTERPRISE  wtWebGraphAnalog57661
    VARIABLES   { wtWebGraphAnalog57661AlarmTrapText }
    DESCRIPTION
        "This SNMP trap is generated when Alarm 2 was triggered,
        SNMP trap enable is set and
        SNMP is enabled."
    -- NMS trap annotation
    --#TYPE "Web-IO Analog-InOut Alarm 2"
    --#SUMMARY "Alarm 2: %s"
    --#ARGUMENTS {0}
    --#SEVERITY INFORMATIONAL
    --#TIMEINDEX 99
    --#STATE OPERATIONAL
    ::= 32

wtWebGraphAnalog57661Alert3 TRAP-TYPE
    ENTERPRISE  wtWebGraphAnalog57661
    VARIABLES   { wtWebGraphAnalog57661AlarmTrapText }
    DESCRIPTION
        "This SNMP trap is generated when Alarm 3 was triggered,
        SNMP trap enable is set and
        SNMP is enabled."
    -- NMS trap annotation
    --#TYPE "Web-IO Analog-InOut Alarm 3"
    --#SUMMARY "Alarm 3: %s"
    --#ARGUMENTS {0}
    --#SEVERITY INFORMATIONAL
    --#TIMEINDEX 99
    --#STATE OPERATIONAL
    ::= 33

wtWebGraphAnalog57661Alert4 TRAP-TYPE
    ENTERPRISE  wtWebGraphAnalog57661
    VARIABLES   { wtWebGraphAnalog57661AlarmTrapText }
    DESCRIPTION
        "This SNMP trap is generated when Alarm 4 was triggered,
        SNMP trap enable is set and
        SNMP is enabled."
    -- NMS trap annotation
    --#TYPE "Web-IO Analog-InOut Alarm 4"
    --#SUMMARY "Alarm 4: %s"
    --#ARGUMENTS {0}
    --#SEVERITY INFORMATIONAL
    --#TIMEINDEX 99
    --#STATE OPERATIONAL
    ::= 34

wtWebGraphAnalog57661Alert5 TRAP-TYPE
    ENTERPRISE  wtWebGraphAnalog57661
    VARIABLES   { wtWebGraphAnalog57661AlarmTrapText }
    DESCRIPTION
        "This SNMP trap is generated when Alarm 5 was triggered,
        SNMP trap enable is set and
        SNMP is enabled."
    -- NMS trap annotation
    --#TYPE "Web-IO Analog-InOut Alarm 5"
    --#SUMMARY "Alarm 5: %s"
    --#ARGUMENTS {0}
    --#SEVERITY INFORMATIONAL
    --#TIMEINDEX 99
    --#STATE OPERATIONAL
    ::= 35

wtWebGraphAnalog57661Alert6 TRAP-TYPE
    ENTERPRISE  wtWebGraphAnalog57661
    VARIABLES   { wtWebGraphAnalog57661AlarmTrapText }
    DESCRIPTION
        "This SNMP trap is generated when Alarm 6 was triggered,
        SNMP trap enable is set and
        SNMP is enabled."
    -- NMS trap annotation
    --#TYPE "Web-IO Analog-InOut Alarm 6"
    --#SUMMARY "Alarm 6: %s"
    --#ARGUMENTS {0}
    --#SEVERITY INFORMATIONAL
    --#TIMEINDEX 99
    --#STATE OPERATIONAL
    ::= 36

wtWebGraphAnalog57661Alert7 TRAP-TYPE
    ENTERPRISE  wtWebGraphAnalog57661
    VARIABLES   { wtWebGraphAnalog57661AlarmTrapText }
    DESCRIPTION
        "This SNMP trap is generated when Alarm 7 was triggered,
        SNMP trap enable is set and
        SNMP is enabled."
    -- NMS trap annotation
    --#TYPE "Web-IO Analog-InOut Alarm 7"
    --#SUMMARY "Alarm 7: %s"
    --#ARGUMENTS {0}
    --#SEVERITY INFORMATIONAL
    --#TIMEINDEX 99
    --#STATE OPERATIONAL
    ::= 37

wtWebGraphAnalog57661Alert8 TRAP-TYPE
    ENTERPRISE  wtWebGraphAnalog57661
    VARIABLES   { wtWebGraphAnalog57661AlarmTrapText }
    DESCRIPTION
        "This SNMP trap is generated when Alarm 8 was triggered,
        SNMP trap enable is set and
        SNMP is enabled."
    -- NMS trap annotation
    --#TYPE "Web-IO Analog-InOut Alarm 8"
    --#SUMMARY "Alarm 8: %s"
    --#ARGUMENTS {0}
    --#SEVERITY INFORMATIONAL
    --#TIMEINDEX 99
    --#STATE OPERATIONAL
    ::= 38

wtWebGraphAnalog57661Alert9 TRAP-TYPE
    ENTERPRISE  wtWebGraphAnalog57661
    VARIABLES   { wtWebGraphAnalog57661AlarmClearTrapText }
    DESCRIPTION
        "This SNMP trap is generated when Alarm 1 was cleared,
        SNMP trap enable is set and
        SNMP is enabled."
    -- NMS trap annotation
    --#TYPE "Web-IO Analog-InOut Release Alarm 1"
    --#SUMMARY "Release Alarm 1: %s"
    --#ARGUMENTS {0}
    --#SEVERITY INFORMATIONAL
    --#TIMEINDEX 99
    --#STATE OPERATIONAL
    ::= 91

wtWebGraphAnalog57661Alert10 TRAP-TYPE
    ENTERPRISE  wtWebGraphAnalog57661
    VARIABLES   { wtWebGraphAnalog57661AlarmClearTrapText }
    DESCRIPTION
        "This SNMP trap is generated when Alarm 2 was cleared,
        SNMP trap enable is set and
        SNMP is enabled."
    -- NMS trap annotation
    --#TYPE "Web-IO Analog-InOut Release Alarm 2"
    --#SUMMARY "Release Alarm 2: %s"
    --#ARGUMENTS {0}
    --#SEVERITY INFORMATIONAL
    --#TIMEINDEX 99
    --#STATE OPERATIONAL
    ::= 92

wtWebGraphAnalog57661Alert11 TRAP-TYPE
    ENTERPRISE  wtWebGraphAnalog57661
    VARIABLES   { wtWebGraphAnalog57661AlarmClearTrapText }
    DESCRIPTION
        "This SNMP trap is generated when Alarm 3 was cleared,
        SNMP trap enable is set and
        SNMP is enabled."
    -- NMS trap annotation
    --#TYPE "Web-IO Analog-InOut Release Alarm 3"
    --#SUMMARY "Release Alarm 3: %s"
    --#ARGUMENTS {0}
    --#SEVERITY INFORMATIONAL
    --#TIMEINDEX 99
    --#STATE OPERATIONAL
    ::= 93

wtWebGraphAnalog57661Alert12 TRAP-TYPE
    ENTERPRISE  wtWebGraphAnalog57661
    VARIABLES   { wtWebGraphAnalog57661AlarmClearTrapText }
    DESCRIPTION
        "This SNMP trap is generated when Alarm 4 was cleared,
        SNMP trap enable is set and
        SNMP is enabled."
    -- NMS trap annotation
    --#TYPE "Web-IO Analog-InOut Release Alarm 4"
    --#SUMMARY "Release Alarm 4: %s"
    --#ARGUMENTS {0}
    --#SEVERITY INFORMATIONAL
    --#TIMEINDEX 99
    --#STATE OPERATIONAL
    ::= 94

wtWebGraphAnalog57661Alert13 TRAP-TYPE
    ENTERPRISE  wtWebGraphAnalog57661
    VARIABLES   { wtWebGraphAnalog57661AlarmClearTrapText }
    DESCRIPTION
        "This SNMP trap is generated when Alarm 5 was cleared,
        SNMP trap enable is set and
        SNMP is enabled."
    -- NMS trap annotation
    --#TYPE "Web-IO Analog-InOut Release Alarm 5"
    --#SUMMARY "Release Alarm 5: %s"
    --#ARGUMENTS {0}
    --#SEVERITY INFORMATIONAL
    --#TIMEINDEX 99
    --#STATE OPERATIONAL
    ::= 95

wtWebGraphAnalog57661Alert14 TRAP-TYPE
    ENTERPRISE  wtWebGraphAnalog57661
    VARIABLES   { wtWebGraphAnalog57661AlarmClearTrapText }
    DESCRIPTION
        "This SNMP trap is generated when Alarm 6 was cleared,
        SNMP trap enable is set and
        SNMP is enabled."
    -- NMS trap annotation
    --#TYPE "Web-IO Analog-InOut Release Alarm 6"
    --#SUMMARY "Release Alarm 6: %s"
    --#ARGUMENTS {0}
    --#SEVERITY INFORMATIONAL
    --#TIMEINDEX 99
    --#STATE OPERATIONAL
    ::= 96

wtWebGraphAnalog57661Alert15 TRAP-TYPE
    ENTERPRISE  wtWebGraphAnalog57661
    VARIABLES   { wtWebGraphAnalog57661AlarmClearTrapText }
    DESCRIPTION
        "This SNMP trap is generated when Alarm 7 was cleared,
        SNMP trap enable is set and
        SNMP is enabled."
    -- NMS trap annotation
    --#TYPE "Web-IO Analog-InOut Release Alarm 7"
    --#SUMMARY "Release Alarm 7: %s"
    --#ARGUMENTS {0}
    --#SEVERITY INFORMATIONAL
    --#TIMEINDEX 99
    --#STATE OPERATIONAL
    ::= 97

wtWebGraphAnalog57661Alert16 TRAP-TYPE
    ENTERPRISE  wtWebGraphAnalog57661
    VARIABLES   { wtWebGraphAnalog57661AlarmClearTrapText }
    DESCRIPTION
        "This SNMP trap is generated when Alarm 8 was cleared,
        SNMP trap enable is set and
        SNMP is enabled."
    -- NMS trap annotation
    --#TYPE "Web-IO Analog-InOut Release Alarm 8"
    --#SUMMARY "Release Alarm 8: %s"
    --#ARGUMENTS {0}
    --#SEVERITY INFORMATIONAL
    --#TIMEINDEX 99
    --#STATE OPERATIONAL
    ::= 98

wtWebGraphAnalog57661AlertReport TRAP-TYPE
    ENTERPRISE  wtWebGraphAnalog57661
    VARIABLES   { wtWebGraphAnalog57661AlarmTrapText }
    DESCRIPTION
        "This SNMP trap is generated when the report was triggered,
        SNMP trap enable is set and
        SNMP is enabled."
    -- NMS trap annotation
    --#TYPE "Web-IO Analog-InOut Report"
    --#SUMMARY "Report: %s"
    --#ARGUMENTS {0}
    --#SEVERITY INFORMATIONAL
    --#TIMEINDEX 99
    --#STATE OPERATIONAL
    ::= 39

wtWebGraphAnalog57661AlertDiag TRAP-TYPE
    ENTERPRISE  wtWebGraphAnalog57661
    VARIABLES   {
    		wtWebGraphAnalog57661DiagErrorIndex,
    	  	wtWebGraphAnalog57661DiagErrorMessage
    		}
    DESCRIPTION
        "This SNMP trap is generated when a diagnosis/error message was triggered,
        SNMP trap enable is set and
        SNMP is enabled."
    -- NMS trap annotation
    --#TYPE "Web-IO Analog-InOut Diagnose Error"
    --#SUMMARY "Diagnose error index: %d, Message: %s."
    --#ARGUMENTS {0,1}
    --#SEVERITY MAJOR
    --#TIMEINDEX 99
    --#STATE DEGRADED
    ::= 110

END
