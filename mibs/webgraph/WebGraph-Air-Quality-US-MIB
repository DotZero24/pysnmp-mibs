WebGraph-Air-Quality-US-MIB DEFINITIONS ::= BEGIN
----------------------------------------------------------------
-- Revison: 1.36
----------------------------------------------------------------
-- 09.03.2017 	New: wtWebGraphAirQualityAlarmSensorLostSelection
--		     		 wtWebGraphAirQualityAlarmLimitWindow
----------------------------------------------------------------
-- Revison: 1.35
----------------------------------------------------------------
-- 09.11.2016 	New: wtWebGraphAirQualityMQTT group
--		     HTTP Request, MQTT Alarm, REST
----------------------------------------------------------------
-- Revison: 1.34
----------------------------------------------------------------
-- 15.07.2015 	Changes for new Navigation (__JB__)
----------------------------------------------------------------
-- Revison: 1.33
----------------------------------------------------------------
-- 26.04.2013 	New 57618 Sensor VOC
--
----------------------------------------------------------------
--

    IMPORTS

    OBJECT-TYPE                                        FROM RFC-1212
    TRAP-TYPE                                          FROM RFC-1215
    DisplayString, PhysAddress                         FROM RFC1213-MIB
    enterprises, TimeTicks, IpAddress, NetworkAddress  FROM RFC1155-SMI;


--    IpAddress ::=
--        [APPLICATION 0]
--            IMPLICIT OCTET STRING (SIZE (4))
--    Counter ::=
--        [APPLICATION 1]
--            IMPLICIT INTEGER (0..4294967295)
--    Gauge ::=
--        [APPLICATION 2]
--            IMPLICIT INTEGER (0..4294967295)
--    TimeTicks ::=
--        [APPLICATION 3]
--            IMPLICIT INTEGER (0..4294967295)


--    DisplayString ::= OCTET STRING
--    PhysAddress   ::= OCTET STRING

--    internet         OBJECT IDENTIFIER ::= { iso org(3) dod(6) 1 }
--    privat           OBJECT IDENTIFIER ::= { internet 4 }
--    enterprises      OBJECT IDENTIFIER ::= { privat 1 }



--  Wiesemann & Theis Com-Server MIB

    wut                				OBJECT IDENTIFIER ::= { enterprises 5040 }
    wtComServer        				OBJECT IDENTIFIER ::= { wut 1 }
    wtWebio            				OBJECT IDENTIFIER ::= { wtComServer 2 }

--  wtWebGraph Tree

    wtWebGraphAirQuality  			OBJECT IDENTIFIER ::= { wtWebio 41 }

--  wtWebGraphAirQuality Tree

    wtWebGraphAirQualityTemp      		OBJECT IDENTIFIER ::= { wtWebGraphAirQuality 1 }
    wtWebGraphAirQualitySessCntrl 		OBJECT IDENTIFIER ::= { wtWebGraphAirQuality 2 }
    wtWebGraphAirQualityConfig    		OBJECT IDENTIFIER ::= { wtWebGraphAirQuality 3 }
    wtWebGraphAirQualityDiag    		OBJECT IDENTIFIER ::= { wtWebGraphAirQuality 4 }

--  wtWebGraphAirQualityConfig Tree

    wtWebGraphAirQualityDevice    		OBJECT IDENTIFIER ::= { wtWebGraphAirQualityConfig 1 }
    wtWebGraphAirQualityPorts     		OBJECT IDENTIFIER ::= { wtWebGraphAirQualityConfig 2 }
    wtWebGraphAirQualityManufact  		OBJECT IDENTIFIER ::= { wtWebGraphAirQualityConfig 3 }

--  wtWebGraphAirQualityDevice Tree

    wtWebGraphAirQualityText			OBJECT IDENTIFIER ::= { wtWebGraphAirQualityDevice 1 }
    wtWebGraphAirQualityTimeDate 		OBJECT IDENTIFIER ::= { wtWebGraphAirQualityDevice 2 }
    wtWebGraphAirQualityBasic			OBJECT IDENTIFIER ::= { wtWebGraphAirQualityDevice 3 }
    wtWebGraphAirQualityDatalogger		OBJECT IDENTIFIER ::= { wtWebGraphAirQualityDevice 4 }
    wtWebGraphAirQualityAlarm			OBJECT IDENTIFIER ::= { wtWebGraphAirQualityDevice 5 }
    wtWebGraphAirQualityGraphics 		OBJECT IDENTIFIER ::= { wtWebGraphAirQualityDevice 6 }

--  wtWebGraphAirQualityTimeDate Tree

    wtWebGraphAirQualityTimeZone		OBJECT IDENTIFIER ::= { wtWebGraphAirQualityTimeDate 1 }
    wtWebGraphAirQualityTimeServer		OBJECT IDENTIFIER ::= { wtWebGraphAirQualityTimeDate 2 }
    wtWebGraphAirQualityDeviceClock		OBJECT IDENTIFIER ::= { wtWebGraphAirQualityTimeDate 3 }

--  wtWebGraphAirQualityBasic Tree

    wtWebGraphAirQualityNetwork			OBJECT IDENTIFIER ::= { wtWebGraphAirQualityBasic 1 }
    wtWebGraphAirQualityHTTP			OBJECT IDENTIFIER ::= { wtWebGraphAirQualityBasic 2 }
    wtWebGraphAirQualityMail			OBJECT IDENTIFIER ::= { wtWebGraphAirQualityBasic 3 }
    wtWebGraphAirQualitySNMP			OBJECT IDENTIFIER ::= { wtWebGraphAirQualityBasic 4 }
    wtWebGraphAirQualityUDP			OBJECT IDENTIFIER ::= { wtWebGraphAirQualityBasic 5 }
    wtWebGraphAirQualitySyslog			OBJECT IDENTIFIER ::= { wtWebGraphAirQualityBasic 6 }
    wtWebGraphAirQualityFTP			OBJECT IDENTIFIER ::= { wtWebGraphAirQualityBasic 7 }
    wtWebGraphAirQualityRSS			OBJECT IDENTIFIER ::= { wtWebGraphAirQualityBasic 8 }
    wtWebGraphAirQualityLedLights		OBJECT IDENTIFIER ::= { wtWebGraphAirQualityBasic 9 }
    wtWebGraphAirQualityMQTT			OBJECT IDENTIFIER ::= { wtWebGraphAirQualityBasic 12 }
    wtWebGraphAirQualityREST			OBJECT IDENTIFIER ::= { wtWebGraphAirQualityBasic 13 }


--  wtWebGraphAirQualityGraphics Tree

    wtWebGraphAirQualityGraphicsBase 		OBJECT IDENTIFIER ::= { wtWebGraphAirQualityGraphics 1 }
    wtWebGraphAirQualityGraphicsSelect 		OBJECT IDENTIFIER ::= { wtWebGraphAirQualityGraphics 2 }
    wtWebGraphAirQualityGraphicsScale 		OBJECT IDENTIFIER ::= { wtWebGraphAirQualityGraphics 3 }

-- wtWebGraphAirQualityTemp Group
------------------------

wtWebGraphAirQualitySensors OBJECT-TYPE
    SYNTAX INTEGER (1..3)
    ACCESS read-only
    STATUS mandatory
    DESCRIPTION
        "Number of sensors"
    ::= { wtWebGraphAirQualityTemp 1 }

-- Interface Table

wtWebGraphAirQualitySensorTable OBJECT-TYPE
    SYNTAX SEQUENCE OF WtWebGraphAirQualitySensorEntry
    ACCESS not-accessible
    STATUS mandatory
    DESCRIPTION
        "List of sensors."
    ::= { wtWebGraphAirQualityTemp 2 }

wtWebGraphAirQualitySensorEntry OBJECT-TYPE
    SYNTAX WtWebGraphAirQualitySensorEntry
    ACCESS not-accessible
    STATUS mandatory
    DESCRIPTION
        "List of sensor numbers."
    INDEX  { wtWebGraphAirQualitySensorNo }
    ::= { wtWebGraphAirQualitySensorTable 1 }

WtWebGraphAirQualitySensorEntry ::= SEQUENCE {
    wtWebGraphAirQualitySensorNo INTEGER
}

wtWebGraphAirQualitySensorNo OBJECT-TYPE
    SYNTAX INTEGER (1..2)
    ACCESS read-only
    STATUS mandatory
    DESCRIPTION
        "Sensor number."
    ::= { wtWebGraphAirQualitySensorEntry 1 }


-- wtWebGraphAirQualityTempValue Table

wtWebGraphAirQualityTempValueTable OBJECT-TYPE
    SYNTAX SEQUENCE OF WtWebGraphAirQualityTempValueEntry
    ACCESS not-accessible
    STATUS mandatory
    DESCRIPTION
        "List of measurement values corresponding to the channel numbers."
    ::= { wtWebGraphAirQualityTemp 3 }

wtWebGraphAirQualityTempValueEntry OBJECT-TYPE
    SYNTAX WtWebGraphAirQualityTempValueEntry
    ACCESS not-accessible
    STATUS mandatory
    DESCRIPTION
        "Measurement values of the sensors."
    INDEX  { wtWebGraphAirQualitySensorNo }
    ::= { wtWebGraphAirQualityTempValueTable 1 }

WtWebGraphAirQualityTempValueEntry ::= SEQUENCE{
    wtWebGraphAirQualityTempValue OCTET STRING
}

wtWebGraphAirQualityTempValue OBJECT-TYPE
    SYNTAX OCTET STRING (SIZE (5))
    ACCESS read-only
    STATUS mandatory
    DESCRIPTION
        "Measurement value of the sensor, ASCII, 5 characters in length."
    ::= { wtWebGraphAirQualityTempValueEntry 1 }

-- wtWebGraphAirQualityBinaryTempValue Table

wtWebGraphAirQualityBinaryTempValueTable OBJECT-TYPE
    SYNTAX SEQUENCE OF WtWebGraphAirQualityBinaryTempValueEntry
    ACCESS not-accessible
    STATUS mandatory
    DESCRIPTION
        "List of binary measurement values corresponding to the channel numbers."
    ::= { wtWebGraphAirQualityTemp 4 }

wtWebGraphAirQualityBinaryTempValueEntry OBJECT-TYPE
    SYNTAX WtWebGraphAirQualityBinaryTempValueEntry
    ACCESS not-accessible
    STATUS mandatory
    DESCRIPTION
        "Binary measurement values of the sensors."
    INDEX  { wtWebGraphAirQualitySensorNo }
    ::= { wtWebGraphAirQualityBinaryTempValueTable 1 }

WtWebGraphAirQualityBinaryTempValueEntry ::= SEQUENCE{
    wtWebGraphAirQualityBinaryTempValue INTEGER
}

wtWebGraphAirQualityBinaryTempValue OBJECT-TYPE
    SYNTAX INTEGER
    ACCESS read-only
    STATUS mandatory
    DESCRIPTION
        "Binary measurement value of the sensor in 1/10 degrees Celsius, 1/10 per cent
        or 1/10 ppm, signed number, 0x7FFFFFFF indicates an
        invalid measured value."
    ::= { wtWebGraphAirQualityBinaryTempValueEntry 1 }

-- wtWebGraphAirQualityTempValuePkt Table

wtWebGraphAirQualityTempValuePktTable OBJECT-TYPE
    SYNTAX SEQUENCE OF WtWebGraphAirQualityTempValuePktEntry
    ACCESS not-accessible
    STATUS mandatory
    DESCRIPTION
        "List of measurement values corresponding to the channel numbers."
    ::= { wtWebGraphAirQualityTemp 8 }

wtWebGraphAirQualityTempValuePktEntry OBJECT-TYPE
    SYNTAX WtWebGraphAirQualityTempValuePktEntry
    ACCESS not-accessible
    STATUS mandatory
    DESCRIPTION
        "Measurement values of the sensors."
    INDEX  { wtWebGraphAirQualitySensorNo }
    ::= { wtWebGraphAirQualityTempValuePktTable 1 }

WtWebGraphAirQualityTempValuePktEntry ::= SEQUENCE{
    wtWebGraphAirQualityTempValuePkt OCTET STRING
}

wtWebGraphAirQualityTempValuePkt OBJECT-TYPE
    SYNTAX OCTET STRING (SIZE (5))
    ACCESS read-only
    STATUS mandatory
    DESCRIPTION
        "Measurement value of the sensor, ASCII, 5 characters in length, delimeter is decimal point."
    ::= { wtWebGraphAirQualityTempValuePktEntry 1 }

-- wtWebGraphAirQualitySessCntrl Group
--------------------------------

wtWebGraphAirQualitySessCntrlPassword OBJECT-TYPE
    SYNTAX OCTET STRING
    ACCESS read-write
    STATUS mandatory
    DESCRIPTION
        "Entering this password opens a session which is ended by writing a 1 to
        wtWebGraphAirQualitySessCntrlLogout. When read this variable provides a string of
        length zero."
    ::= { wtWebGraphAirQualitySessCntrl 1 }

wtWebGraphAirQualitySessCntrlConfigMode OBJECT-TYPE
    SYNTAX INTEGER {
    wtWebGraphAirQualitySessCntrl-NoSession(0),
    wtWebGraphAirQualitySessCntrl-Session(1)
    }
    ACCESS read-only
    STATUS mandatory
    DESCRIPTION
        "When the device is in SNMP configuration mode, the value 1 is
        returned, otherwise 0. If the read value is 0 even though the
        password was written, the device is already in config mode and the
        variables can only be read."
    ::= { wtWebGraphAirQualitySessCntrl 2 }

wtWebGraphAirQualitySessCntrlLogout OBJECT-TYPE
    SYNTAX INTEGER
    ACCESS read-write
    STATUS mandatory
    DESCRIPTION
        "If the device is in configuration mode and the session was opened by
        this SNMP Manager, writing a 1 to this variable will end the session
        and all parameters are stored.
        Writing a 2 discards all entries again.
        When read this variable provides the value 0."
    ::= { wtWebGraphAirQualitySessCntrl 3 }

wtWebGraphAirQualitySessCntrlAdminPassword OBJECT-TYPE
    SYNTAX OCTET STRING
    ACCESS read-write
    STATUS mandatory
    DESCRIPTION
        "This password protects access to the variables with administrator rights.
        It can only be changed by the administrator. If no password was assigned,
        the valid password is public."
    ::= { wtWebGraphAirQualitySessCntrl 4 }

wtWebGraphAirQualitySessCntrlConfigPassword OBJECT-TYPE
    SYNTAX OCTET STRING
    ACCESS read-write
    STATUS mandatory
    DESCRIPTION
        "This password protects access to the variables with configurator rights. It can
        be changed by the administrator and by the configurator. If no password was assigned,
        the valid password is public. When read this variable provides a null-pointer."
    ::= { wtWebGraphAirQualitySessCntrl 5 }


-- wtWebGraphAirQualityText Group
------------------------

wtWebGraphAirQualityDeviceName OBJECT-TYPE
    SYNTAX OCTET STRING
    ACCESS read-write
    STATUS mandatory
    DESCRIPTION
        "Name of the Webio, which is user definable."
    ::= { wtWebGraphAirQualityText 1 }

wtWebGraphAirQualityDeviceText OBJECT-TYPE
    SYNTAX OCTET STRING
    ACCESS read-write
    STATUS mandatory
    DESCRIPTION
        "Description of the Webio, which is user definable."
    ::= { wtWebGraphAirQualityText 2 }

wtWebGraphAirQualityDeviceLocation OBJECT-TYPE
    SYNTAX OCTET STRING
    ACCESS read-write
    STATUS mandatory
    DESCRIPTION
        "Description of the location of the Webio, which is user definable."
    ::= { wtWebGraphAirQualityText 3 }

wtWebGraphAirQualityDeviceContact OBJECT-TYPE
    SYNTAX OCTET STRING
    ACCESS read-write
    STATUS mandatory
    DESCRIPTION
        "Contact address of the system operator of the Webio, which is user definable."
    ::= { wtWebGraphAirQualityText 4 }

-- wtWebGraphAirQualityTimeZone Group
----------------------------

wtWebGraphAirQualityTzOffsetHrs OBJECT-TYPE
    SYNTAX INTEGER
    ACCESS read-write
    STATUS mandatory
    DESCRIPTION
        "Offset hours for the time zone (winter time) with respect to UTC."
    ::= { wtWebGraphAirQualityTimeZone 1 }

wtWebGraphAirQualityTzOffsetMin OBJECT-TYPE
    SYNTAX INTEGER
    ACCESS read-write
    STATUS mandatory
    DESCRIPTION
        "Offset minutes for the time zone (winter time) with respect to UTC."
    ::= { wtWebGraphAirQualityTimeZone 2 }

wtWebGraphAirQualityTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebGraphAirQualityTimeZone 3 }

wtWebGraphAirQualityStTzOffsetHrs OBJECT-TYPE
    SYNTAX INTEGER
    ACCESS read-write
    STATUS mandatory
    DESCRIPTION
        "Offset hours of the time zone (summer time) with respect to UTC."
    ::= { wtWebGraphAirQualityTimeZone 4 }

wtWebGraphAirQualityStTzOffsetMin OBJECT-TYPE
    SYNTAX INTEGER
    ACCESS read-write
    STATUS mandatory
    DESCRIPTION
        "Offset minutes of the time zone (summer time) with respect to UTC."
    ::= { wtWebGraphAirQualityTimeZone 5 }

wtWebGraphAirQualityStTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebGraphAirQualityTimeZone 6 }

wtWebGraphAirQualityStTzStartMonth OBJECT-TYPE
    SYNTAX INTEGER {
    	wtWebGraphAirQualityStartMonth-January(1),
    	wtWebGraphAirQualityStartMonth-February(2),
    	wtWebGraphAirQualityStartMonth-March(3),
    	wtWebGraphAirQualityStartMonth-April(4),
    	wtWebGraphAirQualityStartMonth-May(5),
    	wtWebGraphAirQualityStartMonth-June(6),
    	wtWebGraphAirQualityStartMonth-July(7),
    	wtWebGraphAirQualityStartMonth-August(8),
    	wtWebGraphAirQualityStartMonth-September(9),
    	wtWebGraphAirQualityStartMonth-October(10),
    	wtWebGraphAirQualityStartMonth-November(11),
    	wtWebGraphAirQualityStartMonth-December(12)
    	}

    ACCESS read-write
    STATUS mandatory
    DESCRIPTION
        "Month in which the change is made from winter time to summer time."
    ::= { wtWebGraphAirQualityTimeZone 7 }

wtWebGraphAirQualityStTzStartMode OBJECT-TYPE
    SYNTAX INTEGER {
    	wtWebGraphAirQualityStartMode-first(1),
    	wtWebGraphAirQualityStartMode-second(2),
    	wtWebGraphAirQualityStartMode-third(3),
    	wtWebGraphAirQualityStartMode-fourth(4),
    	wtWebGraphAirQualityStartMode-last(5)
    	}

    ACCESS read-write
    STATUS mandatory
    DESCRIPTION
        "Mode of the day of the week for which the change is made from winter time to summer time."
    ::= { wtWebGraphAirQualityTimeZone 8 }

wtWebGraphAirQualityStTzStartWday OBJECT-TYPE
    SYNTAX INTEGER {
    	wtWebGraphAirQualityStartWday-Sunday(1),
    	wtWebGraphAirQualityStartWday-Monday(2),
    	wtWebGraphAirQualityStartWday-Tuesday(3),
    	wtWebGraphAirQualityStartWday-Thursday(4),
    	wtWebGraphAirQualityStartWday-Wednesday(5),
    	wtWebGraphAirQualityStartWday-Friday(6),
    	wtWebGraphAirQualityStartWday-Saturday(7)
    	}

    ACCESS read-write
    STATUS mandatory
    DESCRIPTION
        "Day of the week on which the change is made from winter time to summer time"
    ::= { wtWebGraphAirQualityTimeZone 9 }

wtWebGraphAirQualityStTzStartHrs OBJECT-TYPE
    SYNTAX INTEGER
    ACCESS read-write
    STATUS mandatory
    DESCRIPTION
        "Hour in which the time zone is changed from winter to summer time with
        respect to UTC."
    ::= { wtWebGraphAirQualityTimeZone 10 }

wtWebGraphAirQualityStTzStartMin OBJECT-TYPE
    SYNTAX INTEGER
    ACCESS read-write
    STATUS mandatory
    DESCRIPTION
        "Minute in which the time zone is changed from winter to summer time with
        respect to UTC."
    ::= { wtWebGraphAirQualityTimeZone 11 }

wtWebGraphAirQualityStTzStopMonth OBJECT-TYPE
    SYNTAX INTEGER {
    	wtWebGraphAirQualityStopMonth-January(1),
    	wtWebGraphAirQualityStopMonth-February(2),
    	wtWebGraphAirQualityStopMonth-March(3),
    	wtWebGraphAirQualityStopMonth-April(4),
    	wtWebGraphAirQualityStopMonth-May(5),
    	wtWebGraphAirQualityStopMonth-June(6),
    	wtWebGraphAirQualityStopMonth-July(7),
    	wtWebGraphAirQualityStopMonth-August(8),
    	wtWebGraphAirQualityStopMonth-September(9),
    	wtWebGraphAirQualityStopMonth-October(10),
    	wtWebGraphAirQualityStopMonth-November(11),
    	wtWebGraphAirQualityStopMonth-December(12)
    	}
    ACCESS read-write
    STATUS mandatory
    DESCRIPTION
        "Month in which the change is made from summer time to winter time."
   ::= { wtWebGraphAirQualityTimeZone 12 }

wtWebGraphAirQualityStTzStopMode OBJECT-TYPE
    SYNTAX INTEGER {
    	wtWebGraphAirQualityStopMode-first(1),
    	wtWebGraphAirQualityStopMode-second(2),
    	wtWebGraphAirQualityStopMode-third(3),
    	wtWebGraphAirQualityStopMode-fourth(4),
    	wtWebGraphAirQualityStopMode-last(5)
    	}
    ACCESS read-write
    STATUS mandatory
    DESCRIPTION
        "Mode of the week day on which the change is made from summer time to winter time."
    ::= { wtWebGraphAirQualityTimeZone 13 }

wtWebGraphAirQualityStTzStopWday OBJECT-TYPE
    SYNTAX INTEGER {
    	wtWebGraphAirQualityStopWday-Sunday(1),
    	wtWebGraphAirQualityStopWday-Monday(2),
    	wtWebGraphAirQualityStopWday-Tuesday(3),
    	wtWebGraphAirQualityStopWday-Thursday(4),
    	wtWebGraphAirQualityStopWday-Wednesday(5),
    	wtWebGraphAirQualityStopWday-Friday(6),
    	wtWebGraphAirQualityStopWday-Saturday(7)
    	}
    ACCESS read-write
    STATUS mandatory
    DESCRIPTION
        "Day of the week on which the change is made from summer time to winter time."
    ::= { wtWebGraphAirQualityTimeZone 14 }

wtWebGraphAirQualityStTzStopHrs OBJECT-TYPE
    SYNTAX INTEGER
    ACCESS read-write
    STATUS mandatory
    DESCRIPTION
        "Hour at which the time zone is changed from summer to winter time with
        respect to UTC."
    ::= { wtWebGraphAirQualityTimeZone 15 }

wtWebGraphAirQualityStTzStopMin OBJECT-TYPE
    SYNTAX INTEGER
    ACCESS read-write
    STATUS mandatory
    DESCRIPTION
        "Minute at which the time zone is changed from summer to winter time with
        respect to UTC."
    ::= { wtWebGraphAirQualityTimeZone 16 }

-- wtWebGraphAirQualityTimeServer Group
----------------------------

wtWebGraphAirQualityTimeServer1 OBJECT-TYPE
    SYNTAX OCTET STRING
    ACCESS read-write
    STATUS mandatory
    DESCRIPTION
        "IP address or name of the 1st time server in ASCII"
    ::= { wtWebGraphAirQualityTimeServer 1 }

wtWebGraphAirQualityTimeServer2 OBJECT-TYPE
    SYNTAX OCTET STRING
    ACCESS read-write
    STATUS mandatory
    DESCRIPTION
        "IP address or name of the 2nd time server in ASCII"
    ::= { wtWebGraphAirQualityTimeServer 2 }

wtWebGraphAirQualityTsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebGraphAirQualityTimeServer 3 }

wtWebGraphAirQualityTsSyncTime OBJECT-TYPE
    SYNTAX INTEGER
    ACCESS read-write
    STATUS mandatory
    DESCRIPTION
        "Daily synchronisation time with the time server (hour: 0-23)."
    ::= { wtWebGraphAirQualityTimeServer 4 }

-- wtWebGraphAirQualityDeviceClock Group
----------------------------

wtWebGraphAirQualityClockHrs OBJECT-TYPE
    SYNTAX INTEGER (0..23)
    ACCESS read-write
    STATUS mandatory
    DESCRIPTION
        "Clock hours taking into account the time zone settings."
    ::= { wtWebGraphAirQualityDeviceClock 1 }

wtWebGraphAirQualityClockMin OBJECT-TYPE
    SYNTAX INTEGER (0..59)
    ACCESS read-write
    STATUS mandatory
    DESCRIPTION
        "Clock minutes taking into account the time zone settings."
    ::= { wtWebGraphAirQualityDeviceClock 2 }

wtWebGraphAirQualityClockDay OBJECT-TYPE
    SYNTAX INTEGER (1..31)
    ACCESS read-write
    STATUS mandatory
    DESCRIPTION
        "Date: Day of the month, taking into account the time zone settings."
    ::= { wtWebGraphAirQualityDeviceClock 3 }

wtWebGraphAirQualityClockMonth OBJECT-TYPE
   SYNTAX INTEGER {
    	wtWebGraphAirQualityClockMonth-January(1),
    	wtWebGraphAirQualityClockMonth-February(2),
    	wtWebGraphAirQualityClockMonth-March(3),
    	wtWebGraphAirQualityClockMonth-April(4),
    	wtWebGraphAirQualityClockMonth-May(5),
    	wtWebGraphAirQualityClockMonth-June(6),
    	wtWebGraphAirQualityClockMonth-July(7),
    	wtWebGraphAirQualityClockMonth-August(8),
    	wtWebGraphAirQualityClockMonth-September(9),
    	wtWebGraphAirQualityClockMonth-October(10),
    	wtWebGraphAirQualityClockMonth-November(11),
    	wtWebGraphAirQualityClockMonth-December(12)
    	}
    ACCESS read-write
    STATUS mandatory
    DESCRIPTION
        "Date: Month, taking into account the time zone settings."
    ::= { wtWebGraphAirQualityDeviceClock 4 }

wtWebGraphAirQualityClockYear OBJECT-TYPE
    SYNTAX INTEGER (0..65535)
    ACCESS read-write
    STATUS mandatory
    DESCRIPTION
        "Date: Year, taking into account the time zone settings."
    ::= { wtWebGraphAirQualityDeviceClock 5 }


-- wtWebGraphAirQualityNetwork Group
------------------------

wtWebGraphAirQualityIpAddress OBJECT-TYPE
    SYNTAX IpAddress
    ACCESS read-write
    STATUS mandatory
    DESCRIPTION
        "IP address of the Webio"
    ::= { wtWebGraphAirQualityNetwork 1 }

wtWebGraphAirQualitySubnetMask OBJECT-TYPE
    SYNTAX IpAddress
    ACCESS read-write
    STATUS mandatory
    DESCRIPTION
        "Subnet mask of the Webio"
    ::= { wtWebGraphAirQualityNetwork 2 }

wtWebGraphAirQualityGateway OBJECT-TYPE
    SYNTAX IpAddress
    ACCESS read-write
    STATUS mandatory
    DESCRIPTION
        "Gateway of the Webio"
    ::= { wtWebGraphAirQualityNetwork 3 }

wtWebGraphAirQualityDnsServer1 OBJECT-TYPE
    SYNTAX OCTET STRING
    ACCESS read-write
    STATUS mandatory
    DESCRIPTION
        "IP address of the 1st DNS server in ASCII"
    ::= { wtWebGraphAirQualityNetwork 4 }

wtWebGraphAirQualityDnsServer2 OBJECT-TYPE
    SYNTAX OCTET STRING
    ACCESS read-write
    STATUS mandatory
    DESCRIPTION
        "IP address of the 2nd DNS server in ASCII"
    ::= { wtWebGraphAirQualityNetwork 5 }

wtWebGraphAirQualityAddConfig OBJECT-TYPE
    SYNTAX OCTET STRING
    ACCESS read-write
    STATUS mandatory
    DESCRIPTION
        "Additional configuration (1=ON):
        Octet 1: unused
        Octet 2: unused
        Octet 3: unused
        Octet 4:
	        Bit 1: DHCP disable
	        Bit 0: BOOTP disable
	        "
    ::= { wtWebGraphAirQualityNetwork 6 }

--  wtWebGraphAirQualityHTTP Group
--------------------------------

wtWebGraphAirQualityStartup OBJECT-TYPE
    SYNTAX OCTET STRING
    ACCESS read-write
    STATUS mandatory
    DESCRIPTION
        "Binary coded start page:
        Octet 1: unused
        Octet 2: unused
        Octet 3: unused
        Octet 4:
        	Bit 3: smart.htm
        	Bit 2: user.htm
        	Bit 1: home.htm
	        Bit 0: index.htm
	Only one page may be selected at a time."
    ::= { wtWebGraphAirQualityHTTP 1 }

wtWebGraphAirQualityGetHeaderEnable OBJECT-TYPE
    SYNTAX OCTET STRING
    ACCESS read-write
    STATUS mandatory
    DESCRIPTION
        "If these bits are set, every answer of a short form GET question will be lead
        by the IP-address and name of the device and/or a HTTP header:
        Octet 1: unused
        Octet 2: unused
        Octet 3: unused
        Octet 4:
        	Bit 1-6: unused
        	Bit 1  : GET HTTP enable
                Bit 0  : GET Header enable"
    ::= { wtWebGraphAirQualityHTTP 2 }

wtWebGraphAirQualityHttpPort OBJECT-TYPE
    SYNTAX INTEGER (1..65535)
    ACCESS read-write
    STATUS mandatory
    DESCRIPTION
        "Definition of the standard HTML port (Default: 80)."
    ::= { wtWebGraphAirQualityHTTP 3 }


-- wtWebGraphAirQualityMail Group
--------------------------------

wtWebGraphAirQualityMailAdName OBJECT-TYPE
    SYNTAX OCTET STRING
    ACCESS read-write
    STATUS mandatory
    DESCRIPTION
        "Device name for mail administration."
    ::= { wtWebGraphAirQualityMail 1 }

wtWebGraphAirQualityMailReply OBJECT-TYPE
    SYNTAX OCTET STRING
    ACCESS read-write
    STATUS mandatory
    DESCRIPTION
        "Reply address for the mail server."
    ::= { wtWebGraphAirQualityMail 2 }

wtWebGraphAirQualityMailServer OBJECT-TYPE
    SYNTAX OCTET STRING
    ACCESS read-write
    STATUS mandatory
    DESCRIPTION
        "Name or IP address of the mail server."
    ::= { wtWebGraphAirQualityMail 3 }

wtWebioAn1MailEnable OBJECT-TYPE
    SYNTAX OCTET STRING
    ACCESS read-write
    STATUS mandatory
    DESCRIPTION
        "Set this bit to enable the sending of mails:
        Octet 1: unused
        Octet 2: unused
        Octet 3: unused
        Octet 4:
        	Bit 1-7: unused
                Bit 0  : Mail enable"
    ::= { wtWebGraphAirQualityMail 4 }

wtWebGraphAirQualityMailAuthentication OBJECT-TYPE
    SYNTAX OCTET STRING (SIZE (4))
    ACCESS read-write
    STATUS mandatory
    DESCRIPTION
        "Selection of the authentication modi:
        The OCTETS are interpreted bit-by-bit, with each bit corresponding to an output.
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebGraphAirQualityMail 5 }

wtWebGraphAirQualityMailAuthUser OBJECT-TYPE
    SYNTAX OCTET STRING
    ACCESS read-write
    STATUS mandatory
    DESCRIPTION
        "Name of the user to be authenticated."
    ::= { wtWebGraphAirQualityMail 6 }

wtWebGraphAirQualityMailAuthPassword OBJECT-TYPE
    SYNTAX OCTET STRING
    ACCESS read-write
    STATUS mandatory
    DESCRIPTION
        "Authentication password."
    ::= { wtWebGraphAirQualityMail 7 }

wtWebGraphAirQualityMailPop3Server OBJECT-TYPE
    SYNTAX OCTET STRING
    ACCESS read-write
    STATUS mandatory
    DESCRIPTION
        "Name or Ip-address of the POP3 Servers."
    ::= { wtWebGraphAirQualityMail 8 }

-- wtWebGraphAirQualitySNMP Group
--------------------------------

wtWebGraphAirQualitySnmpCommunityStringRead OBJECT-TYPE
    SYNTAX OCTET STRING
    ACCESS read-write
    STATUS mandatory
    DESCRIPTION
        "Community string read only"
    ::= { wtWebGraphAirQualitySNMP 1 }

wtWebGraphAirQualitySnmpCommunityStringReadWrite OBJECT-TYPE
    SYNTAX OCTET STRING
    ACCESS read-write
    STATUS mandatory
    DESCRIPTION
        "Community string read / write"
    ::= { wtWebGraphAirQualitySNMP 2 }

wtWebGraphAirQualitySystemTrapManagerIP OBJECT-TYPE
    SYNTAX OCTET STRING
    ACCESS read-write
    STATUS mandatory
    DESCRIPTION
        "Name or IP address of the TCP server which accepts the system trap."
    ::= { wtWebGraphAirQualitySNMP 3 }

wtWebGraphAirQualitySystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2-7: unused"
    ::= { wtWebGraphAirQualitySNMP 4 }

wtWebGraphAirQualitySnmpEnable OBJECT-TYPE
    SYNTAX OCTET STRING
    ACCESS read-write
    STATUS mandatory
    DESCRIPTION
        "Set bit 0 to enable SNMP.
        If disabled, the device did not respond to any SNMP requests.
        Bit 1 decided wether the community string of read operations
        is compared with the system password or not:
        Octet 1: unused
        Octet 2: unused
        Octet 3: unused
        Octet 4:
        	Bit 1-7: unused
        	Bit 0  : SNMP enable"
    ::= { wtWebGraphAirQualitySNMP 5 }

wtWebGraphAirQualitySnmpCommunityStringTrap OBJECT-TYPE
    SYNTAX OCTET STRING
    ACCESS read-write
    STATUS mandatory
    DESCRIPTION
        "Community string send within traps."
    ::= { wtWebGraphAirQualitySNMP 6 }


-- wtWebGraphAirQualityUDP Group
--------------------------------

wtWebGraphAirQualityUdpPort OBJECT-TYPE
    SYNTAX INTEGER (1..65535)
    ACCESS read-write
    STATUS mandatory
    DESCRIPTION
        "Udp port to which the Udp queries ( short form GET requests) can be sent. This
        port number must be unique within the device."
    ::= { wtWebGraphAirQualityUDP 1 }

wtWebGraphAirQualityUdpEnable OBJECT-TYPE
    SYNTAX OCTET STRING
    ACCESS read-write
    STATUS mandatory
    DESCRIPTION
        "Set this bit to enable UDP support:
        Octet 1: unused
        Octet 2: unused
        Octet 3: unused
        Octet 4:
        	Bit 1-7: unused
                Bit 0  : UDP enable"
    ::= { wtWebGraphAirQualityUDP 2 }

--  wtWebGraphAirQualitySyslog Group
--------------------------------

wtWebGraphAirQualitySyslogServerIP OBJECT-TYPE
    SYNTAX OCTET STRING
    ACCESS read-write
    STATUS mandatory
    DESCRIPTION
        "Name or IP address of the Syslog server, which accepts the Syslog messgaes."
    ::= { wtWebGraphAirQualitySyslog 1 }

wtWebGraphAirQualitySyslogServerPort OBJECT-TYPE
    SYNTAX INTEGER
    ACCESS read-write
    STATUS mandatory
    DESCRIPTION
        "Portnumber of the Syslog servers, default 514."
    ::= { wtWebGraphAirQualitySyslog 2 }

wtWebGraphAirQualitySyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebGraphAirQualitySyslog 3 }

wtWebGraphAirQualitySyslogEnable OBJECT-TYPE
    SYNTAX OCTET STRING
    ACCESS read-write
    STATUS mandatory
    DESCRIPTION
        "Set bit 0to enable Syslog:
        Octet 1: unused
        Octet 2: unused
        Octet 3: unused
        Octet 4:
        	Bit 1-7: unused
                Bit 0  : Syslog enable"
    ::= { wtWebGraphAirQualitySyslog 4 }

--  wtWebGraphAirQualityFTP Group
--------------------------------

wtWebGraphAirQualityFTPServerIP OBJECT-TYPE
    SYNTAX OCTET STRING
    ACCESS read-write
    STATUS mandatory
    DESCRIPTION
        "Name or IP address of the FTP server, which accepts the FTP messages."
    ::= { wtWebGraphAirQualityFTP 1 }

wtWebGraphAirQualityFTPServerControlPort OBJECT-TYPE
    SYNTAX INTEGER
    ACCESS read-write
    STATUS mandatory
    DESCRIPTION
        "Portnumber of the control port of the FTP server, default 21."
    ::= { wtWebGraphAirQualityFTP 2 }

wtWebGraphAirQualityFTPUserName OBJECT-TYPE
    SYNTAX OCTET STRING
    ACCESS read-write
    STATUS mandatory
    DESCRIPTION
        "FTP Loggin: user name."
    ::= { wtWebGraphAirQualityFTP 3 }

wtWebGraphAirQualityFTPPassword OBJECT-TYPE
    SYNTAX OCTET STRING
    ACCESS read-write
    STATUS mandatory
    DESCRIPTION
        "FTP Loggin: user password."
    ::= { wtWebGraphAirQualityFTP 4 }

wtWebGraphAirQualityFTPAccount OBJECT-TYPE
    SYNTAX OCTET STRING
    ACCESS read-write
    STATUS mandatory
    DESCRIPTION
        "FTP Loggin: name of account."
    ::= { wtWebGraphAirQualityFTP 5 }

wtWebGraphAirQualityFTPOption OBJECT-TYPE
    SYNTAX OCTET STRING
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebGraphAirQualityFTP 6 }

wtWebGraphAirQualityFTPEnable OBJECT-TYPE
    SYNTAX OCTET STRING
    ACCESS read-write
    STATUS mandatory
    DESCRIPTION
        "Set Bit 0 to enable FTP:
        Octet 1: unused
        Octet 2: unused
        Octet 3: unused
        Octet 4:
        	Bit 1-7: unused
                Bit 0  : FTP enable"
    ::= { wtWebGraphAirQualityFTP 7 }


--  wtWebGraphAirQualityRSS Group
--------------------------------

wtWebGraphAirQualityRSSChannelTitle OBJECT-TYPE
    SYNTAX OCTET STRING
    ACCESS read-write
    STATUS mandatory
    DESCRIPTION
        "Name of the RSS Feed."
    ::= { wtWebGraphAirQualityRSS 1 }

wtWebGraphAirQualityRSSChannelLink OBJECT-TYPE
    SYNTAX OCTET STRING
    ACCESS read-write
    STATUS mandatory
    DESCRIPTION
        "Link of the RSS Feed."
    ::= { wtWebGraphAirQualityRSS 2 }

wtWebGraphAirQualityRSSChannelDescription OBJECT-TYPE
    SYNTAX OCTET STRING
    ACCESS read-write
    STATUS mandatory
    DESCRIPTION
        "Description of the RSS Feed."
    ::= { wtWebGraphAirQualityRSS 3 }

wtWebGraphAirQualityRSSChannelImage OBJECT-TYPE
    SYNTAX OCTET STRING
    ACCESS read-write
    STATUS mandatory
    DESCRIPTION
        "Link of a picture, which will be shown at the headline of the output window."
    ::= { wtWebGraphAirQualityRSS 4 }

wtWebGraphAirQualityRSSChannelImageTitle OBJECT-TYPE
    SYNTAX OCTET STRING
    ACCESS read-write
    STATUS mandatory
    DESCRIPTION
        "Alias Name of the picture."
    ::= { wtWebGraphAirQualityRSS 5 }

wtWebGraphAirQualityRSSChannelImageLink OBJECT-TYPE
    SYNTAX OCTET STRING
    ACCESS read-write
    STATUS mandatory
    DESCRIPTION
        "Link, which can be selected by clicking on the picture."
    ::= { wtWebGraphAirQualityRSS 6 }

wtWebGraphAirQualityRSSChannelItemTitle OBJECT-TYPE
    SYNTAX OCTET STRING
    ACCESS read-write
    STATUS mandatory
    DESCRIPTION
        "Title of the RSS Feed."
    ::= { wtWebGraphAirQualityRSS 7 }

wtWebGraphAirQualityRSSChannelItemLink OBJECT-TYPE
    SYNTAX OCTET STRING
    ACCESS read-write
    STATUS mandatory
    DESCRIPTION
        "Link of the RSS Feed."
    ::= { wtWebGraphAirQualityRSS 8 }

wtWebGraphAirQualityRSSChannelItemDescription OBJECT-TYPE
    SYNTAX OCTET STRING
    ACCESS read-write
    STATUS mandatory
    DESCRIPTION
        "Text of the RSS Feed."
    ::= { wtWebGraphAirQualityRSS 9 }

wtWebGraphAirQualityRSSChannelItemQuantity OBJECT-TYPE
    SYNTAX OCTET STRING
    ACCESS read-write
    STATUS mandatory
    DESCRIPTION
        "Number of lines."
    ::= { wtWebGraphAirQualityRSS 10 }

-- wtWebGraphAirQualityLedLights Group
--------------------------------

wtWebGraphAirQualityLedLightsSensorSel OBJECT-TYPE
    SYNTAX OCTET STRING (SIZE(4))
    ACCESS read-write
    STATUS mandatory
    DESCRIPTION
        "Binary coded trigger conditions, only one sensor
        may be selected at a time:
        Octet 1: unused
        Octet 2: unused
        Octet 3: unused
        Octet 4:
        	Bit 0  : Sensor 1 Temperature
        	Bit 1  : Sensor 2 Humidity
        	Bit 2  : Sensor 3 VOC
        	Bit 3-7: unused"
    ::= { wtWebGraphAirQualityLedLights 1 }

wtWebGraphAirQualityLedLightsLimitGreen OBJECT-TYPE
    SYNTAX OCTET STRING (SIZE(4))
    ACCESS read-write
    STATUS mandatory
    DESCRIPTION
        "Limit to switch on green LED"
    ::= { wtWebGraphAirQualityLedLights 2 }

wtWebGraphAirQualityLedLightsLimitYellow OBJECT-TYPE
    SYNTAX OCTET STRING (SIZE(4))
    ACCESS read-write
    STATUS mandatory
    DESCRIPTION
        "Limit to switch on yellow LED"
    ::= { wtWebGraphAirQualityLedLights 3 }

wtWebGraphAirQualityLedLightsLimitRed OBJECT-TYPE
    SYNTAX OCTET STRING (SIZE(4))
    ACCESS read-write
    STATUS mandatory
    DESCRIPTION
        "Limit to switch on red LED"
    ::= { wtWebGraphAirQualityLedLights 4 }

--  wtWebGraphAirQualityMQTT Group
--------------------------------

wtWebGraphAirQualityMQTTEnable OBJECT-TYPE
    SYNTAX OCTET STRING
    ACCESS read-write
    STATUS mandatory
    DESCRIPTION
        "Bit 7 schaltet MQTT frei:
        Octet 1: ungenutzt
        Octet 2: ungenutzt
        Octet 3: ungenutzt
        Octet 4:
        	Bit 0-6: ungenutzt
                Bit 7  : MQTT enable"
    ::= { wtWebGraphAirQualityMQTT 1 }

wtWebGraphAirQualityMQTTBrockerIP OBJECT-TYPE
    SYNTAX OCTET STRING
    ACCESS read-write
    STATUS mandatory
    DESCRIPTION
        "Name or IP-address of the MQTT-Server."
    ::= { wtWebGraphAirQualityMQTT 2 }

wtWebGraphAirQualityMQTTUserName OBJECT-TYPE
    SYNTAX OCTET STRING
    ACCESS read-write
    STATUS mandatory
    DESCRIPTION
        "MQTT login  user name."
    ::= { wtWebGraphAirQualityMQTT 3 }

wtWebGraphAirQualityMQTTPassword OBJECT-TYPE
    SYNTAX OCTET STRING
    ACCESS read-write
    STATUS mandatory
    DESCRIPTION
        "MQTT login password."
    ::= { wtWebGraphAirQualityMQTT 4 }

wtWebGraphAirQualityMQTTLocalPort OBJECT-TYPE
    SYNTAX INTEGER
    ACCESS read-write
    STATUS mandatory
    DESCRIPTION
        "Local port number."
    ::= { wtWebGraphAirQualityMQTT 5 }

wtWebGraphAirQualityMQTTBrokerServerPort OBJECT-TYPE
    SYNTAX INTEGER
    ACCESS read-write
    STATUS mandatory
    DESCRIPTION
        "MQTT Server port number."
    ::= { wtWebGraphAirQualityMQTT 6 }

wtWebGraphAirQualityMQTTInterval OBJECT-TYPE
    SYNTAX INTEGER
    ACCESS read-write
    STATUS mandatory
    DESCRIPTION
        "Ping intervall, if no data has to be send: time in seconds."
    ::= { wtWebGraphAirQualityMQTT 7 }

--  wtWebGraphAirQualityREST Group
--------------------------------

wtWebGraphAirQualityRESTEnable OBJECT-TYPE
    SYNTAX OCTET STRING
    ACCESS read-write
    STATUS mandatory
    DESCRIPTION
        "Bit 0 activates REST :
        Octet 1: unused
        Octet 2: unused
        Octet 3: unused
        Octet 4:
        	Bit 1-7: unused
            Bit 0  : REST enable"
    ::= { wtWebGraphAirQualityREST 1 }

wtWebGraphAirQualityRESTDigestAuthEnable OBJECT-TYPE
    SYNTAX OCTET STRING
    ACCESS read-write
    STATUS mandatory
    DESCRIPTION
        "Bit 0 activates Digest-Authentification:
        Octet 1: unused
        Octet 2: unused
        Octet 3: unused
        Octet 4:
        	Bit 1-7: unused
            Bit 0  : Digest Auth enable"
    ::= { wtWebGraphAirQualityREST 2 }

-- wtWebGraphAirQualityDatalogger Group
--------------------------------

wtWebGraphAirQualityLoggerTimebase OBJECT-TYPE
    SYNTAX INTEGER {
    wtWebGraphAirQualityDatalogger-1Min(1),
    wtWebGraphAirQualityDatalogger-5Min(2),
    wtWebGraphAirQualityDatalogger-15Min(3),
    wtWebGraphAirQualityDatalogger-60Min(4)
    }
    ACCESS read-write
    STATUS mandatory
    DESCRIPTION
        "Time base of the data logger"
    ::= { wtWebGraphAirQualityDatalogger 1 }

wtWebGraphAirQualityLoggerSensorSel OBJECT-TYPE
    SYNTAX OCTET STRING (SIZE(4))
    ACCESS read-write
    STATUS mandatory
    DESCRIPTION
        "Binary coded trigger conditions:
        Octet 1: unused
        Octet 2: unused
        Octet 3: unused
        Octet 4:
        	Bit 0  : Sensor 1 Temperature
        	Bit 1  : Sensor 2 Humidity
        	Bit 2  : Sensor 3 VOC
        	Bit 3-7: unused"
    ::= { wtWebGraphAirQualityDatalogger 2 }

-- wtWebGraphAirQualityAlarm Group
----------------------------

wtWebGraphAirQualityAlarmCount OBJECT-TYPE
    SYNTAX INTEGER (1..8)
    ACCESS read-only
    STATUS mandatory
    DESCRIPTION
        "Number of independent alarms."
    ::= { wtWebGraphAirQualityAlarm 1 }

-- Alarm Interface Table

wtWebGraphAirQualityAlarmIfTable OBJECT-TYPE
    SYNTAX SEQUENCE OF WtWebGraphAirQualityAlarmIfEntry
    ACCESS not-accessible
    STATUS mandatory
    DESCRIPTION
        "List of alarm indices."
    ::= { wtWebGraphAirQualityAlarm 2 }

wtWebGraphAirQualityAlarmIfEntry OBJECT-TYPE
    SYNTAX WtWebGraphAirQualityAlarmIfEntry
    ACCESS not-accessible
    STATUS mandatory
    DESCRIPTION
        "Numbers of the alarms."
    INDEX  { wtWebGraphAirQualityAlarmNo }
    ::= { wtWebGraphAirQualityAlarmIfTable 1 }

WtWebGraphAirQualityAlarmIfEntry ::= SEQUENCE {
    wtWebGraphAirQualityAlarmNo INTEGER
}

wtWebGraphAirQualityAlarmNo OBJECT-TYPE
    SYNTAX INTEGER (1..8)
    ACCESS read-only
    STATUS mandatory
    DESCRIPTION
        "Alarm number."
    ::= { wtWebGraphAirQualityAlarmIfEntry 1 }

-- Alarm Table

wtWebGraphAirQualityAlarmTable OBJECT-TYPE
    SYNTAX SEQUENCE OF WtWebGraphAirQualityAlarmEntry
    ACCESS not-accessible
    STATUS mandatory
    DESCRIPTION
        "List of settings depending on the alarm number."
    ::= { wtWebGraphAirQualityAlarm 3 }

wtWebGraphAirQualityAlarmEntry OBJECT-TYPE
    SYNTAX WtWebGraphAirQualityAlarmEntry
    ACCESS not-accessible
    STATUS mandatory
    DESCRIPTION
        "Alarm parameters of the individual alarms."
    INDEX  { wtWebGraphAirQualityAlarmNo }
    ::= { wtWebGraphAirQualityAlarmTable 1 }

WtWebGraphAirQualityAlarmEntry ::= SEQUENCE {
    wtWebGraphAirQualityAlarmTrigger			OCTET STRING,
    wtWebGraphAirQualityAlarmMin			OCTET STRING,
    wtWebGraphAirQualityAlarmMax			OCTET STRING,
    wtWebGraphAirQualityAlarmHysteresis			OCTET STRING,
    wtWebGraphAirQualityAlarmDelay			OCTET STRING,
    wtWebGraphAirQualityAlarmInterval			OCTET STRING,
    wtWebGraphAirQualityAlarmEnable			OCTET STRING,
    wtWebGraphAirQualityAlarmEMailAddr			OCTET STRING,
    wtWebGraphAirQualityAlarmMailSubject		OCTET STRING,
    wtWebGraphAirQualityAlarmMailText			OCTET STRING,
    wtWebGraphAirQualityAlarmManagerIP			OCTET STRING,
    wtWebGraphAirQualityAlarmTrapText			OCTET STRING,
    wtWebGraphAirQualityAlarmMailOptions		OCTET STRING,
    wtWebGraphAirQualityAlarmTcpIpAddr			OCTET STRING,
    wtWebGraphAirQualityAlarmTcpPort			INTEGER,
    wtWebGraphAirQualityAlarmTcpText			OCTET STRING,
    wtWebGraphAirQualityAlarmClearMailSubject		OCTET STRING,
    wtWebGraphAirQualityAlarmClearMailText		OCTET STRING,
    wtWebGraphAirQualityAlarmClearTrapText		OCTET STRING,
    wtWebGraphAirQualityAlarmClearTcpText		OCTET STRING,
    wtWebGraphAirQualityAlarmDeltaTemp			OCTET STRING,
    wtWebGraphAirQualityAlarmRHMin			OCTET STRING,
    wtWebGraphAirQualityAlarmRHMax			OCTET STRING,
    wtWebGraphAirQualityAlarmRHHysteresis		OCTET STRING,
    wtWebGraphAirQualityAlarmAHMin			OCTET STRING,
    wtWebGraphAirQualityAlarmAHMax			OCTET STRING,
    wtWebGraphAirQualityAlarmSyslogIpAddr		OCTET STRING,
    wtWebGraphAirQualityAlarmSyslogPort			INTEGER,
    wtWebGraphAirQualityAlarmSyslogText			OCTET STRING,
    wtWebGraphAirQualityAlarmSyslogClearText		OCTET STRING,
    wtWebGraphAirQualityAlarmFtpDataPort		OCTET STRING,
    wtWebGraphAirQualityAlarmFtpFileName		OCTET STRING,
    wtWebGraphAirQualityAlarmFtpText			OCTET STRING,
    wtWebGraphAirQualityAlarmFtpClearText		OCTET STRING,
    wtWebGraphAirQualityAlarmFtpOption			OCTET STRING,
    wtWebGraphAirQualityAlarmTimerCron			OCTET STRING,
    wtWebGraphAirQualityAlarmVocMax			OCTET STRING,
    wtWebGraphAirQualityAlarmVocHysteresis		OCTET STRING,
    wtWebGraphAirQualityAlarmName 			OCTET STRING,
    wtWebGraphAirQualityAlarmActive 			OCTET STRING  ,
    wtWebGraphAirQualityAlarmHttpReqAuthEnable		OCTET STRING,
    wtWebGraphAirQualityAlarmHttpReqAuthUser		OCTET STRING,
    wtWebGraphAirQualityAlarmHttpReqAuthPassword	OCTET STRING,
    wtWebGraphAirQualityAlarmHttpReqSetUrl		OCTET STRING,
    wtWebGraphAirQualityAlarmHttpReqClearUrl		OCTET STRING,
    wtWebGraphAirQualityAlarmHttpReqServerPort		OCTET STRING,
    wtWebGraphAirQualityAlarmMqttTopicPath		OCTET STRING,
    wtWebGraphAirQualityAlarmMqttTopicSetTopic		OCTET STRING,
    wtWebGraphAirQualityAlarmMqttTopicClear		OCTET STRING,
	wtWebGraphAirQualityAlarmSensorLostSelection	OCTET STRING,
	wtWebGraphAirQualityAlarmLimitWindow			OCTET STRING
}

wtWebGraphAirQualityAlarmTrigger OBJECT-TYPE
    SYNTAX OCTET STRING (SIZE(4))
    ACCESS read-write
    STATUS mandatory
    DESCRIPTION
        "Binary coded trigger conditions:
        Octet 1: unused
        Octet 2: unused
        Octet 3:
        	Bit 0: Timer
        	Bit 1: ColdStart
        	Bit 2: WarmStart

        Octet 4:
        	Bit 0: Sensor 1
        	Bit 1: Sensor 2
        	Bit 2-7: unused"
    ::= { wtWebGraphAirQualityAlarmEntry 1 }

wtWebGraphAirQualityAlarmMin OBJECT-TYPE
    SYNTAX OCTET STRING
    ACCESS read-write
    STATUS mandatory
    DESCRIPTION
        "Minimum temperature in degrees with maximum 2 decimal places."
    ::= { wtWebGraphAirQualityAlarmEntry 2 }

wtWebGraphAirQualityAlarmMax OBJECT-TYPE
    SYNTAX OCTET STRING
    ACCESS read-write
    STATUS mandatory
    DESCRIPTION
        "Maximum temperature in degrees with maximum 2 decimal places."
    ::= { wtWebGraphAirQualityAlarmEntry 3 }

wtWebGraphAirQualityAlarmHysteresis OBJECT-TYPE
    SYNTAX OCTET STRING
    ACCESS read-write
    STATUS mandatory
    DESCRIPTION
        "Temperature changes of this size clears the alarm state (MAX-hyst, MIN+hyst.)
        , in degrees with maximum 2 decimal places."
    ::= { wtWebGraphAirQualityAlarmEntry 4 }

wtWebGraphAirQualityAlarmDelay OBJECT-TYPE
    SYNTAX OCTET STRING
    ACCESS read-write
    STATUS mandatory
    DESCRIPTION
        "Alarm will be delayed by setting this time while stable alarm
        condition occur (time in minutes)."
    ::= { wtWebGraphAirQualityAlarmEntry 5 }


wtWebGraphAirQualityAlarmInterval OBJECT-TYPE
    SYNTAX OCTET STRING
    ACCESS read-write
    STATUS mandatory
    DESCRIPTION
        "Send interval for alarm messages."
    ::= { wtWebGraphAirQualityAlarmEntry 6 }

wtWebGraphAirQualityAlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  TCP Client enable"
    ::= { wtWebGraphAirQualityAlarmEntry 7 }

wtWebGraphAirQualityAlarmEMailAddr OBJECT-TYPE
    SYNTAX OCTET STRING
    ACCESS read-write
    STATUS mandatory
    DESCRIPTION
        "E-Mail address for sending the alarm mail to."
    ::= { wtWebGraphAirQualityAlarmEntry 8 }

wtWebGraphAirQualityAlarmMailSubject OBJECT-TYPE
    SYNTAX OCTET STRING
    ACCESS read-write
    STATUS mandatory
    DESCRIPTION
        "Subject line for alarm mail."
    ::= { wtWebGraphAirQualityAlarmEntry 9 }

wtWebGraphAirQualityAlarmMailText OBJECT-TYPE
    SYNTAX OCTET STRING
    ACCESS read-write
    STATUS mandatory
    DESCRIPTION
        "Alarm mail text: <Tn> provides the current temperature; n = 1..8.
        <Z> provides the current time."
    ::= { wtWebGraphAirQualityAlarmEntry 10 }

wtWebGraphAirQualityAlarmManagerIP OBJECT-TYPE
    SYNTAX OCTET STRING
    ACCESS read-write
    STATUS mandatory
    DESCRIPTION
        "Name or IP address of the SNMP Manager which accepts the trap."
    ::= { wtWebGraphAirQualityAlarmEntry 11 }

wtWebGraphAirQualityAlarmTrapText OBJECT-TYPE
    SYNTAX OCTET STRING
    ACCESS read-write
    STATUS mandatory
    DESCRIPTION
        "This text is sent in the trap body."
    ::= { wtWebGraphAirQualityAlarmEntry 12 }

wtWebGraphAirQualityAlarmMailOptions OBJECT-TYPE
    SYNTAX OCTET STRING (SIZE(4))
    ACCESS read-write
    STATUS mandatory
    DESCRIPTION
        "Binary coded options:
        Octet 1: unused
        Octet 2: unused
        Octet 3: unused
        Octet 4:
		Bit 0  :	Attach Thermo.csv Enable
		Bit 1  :	CSV-Data_since_last_report
        	Bit 2-7:	unused"
    ::= { wtWebGraphAirQualityAlarmEntry 13 }

wtWebGraphAirQualityAlarmTcpIpAddr OBJECT-TYPE
    SYNTAX OCTET STRING
    ACCESS read-write
    STATUS mandatory
    DESCRIPTION
        "Name or IP address of the TCP server which accepts the trap."
    ::= { wtWebGraphAirQualityAlarmEntry 14 }

wtWebGraphAirQualityAlarmTcpPort OBJECT-TYPE
    SYNTAX INTEGER (1..65535)
    ACCESS read-write
    STATUS mandatory
    DESCRIPTION
        "Port number of the TCP server which accepts the trap."
    ::= { wtWebGraphAirQualityAlarmEntry 15 }

wtWebGraphAirQualityAlarmTcpText OBJECT-TYPE
    SYNTAX OCTET STRING
    ACCESS read-write
    STATUS mandatory
    DESCRIPTION
        "This text is sent in the TCP trap body."
    ::= { wtWebGraphAirQualityAlarmEntry 16 }

wtWebGraphAirQualityAlarmClearMailSubject OBJECT-TYPE
    SYNTAX OCTET STRING
    ACCESS read-write
    STATUS mandatory
    DESCRIPTION
        "Subject line for alarm clear mail."
    ::= { wtWebGraphAirQualityAlarmEntry 17 }

wtWebGraphAirQualityAlarmClearMailText OBJECT-TYPE
    SYNTAX OCTET STRING
    ACCESS read-write
    STATUS mandatory
    DESCRIPTION
        "Alarm clear mail text: <Tn> provides the current temperature; n = 1..8.
        <Z> provides the current time."
    ::= { wtWebGraphAirQualityAlarmEntry 18 }

wtWebGraphAirQualityAlarmClearTrapText OBJECT-TYPE
    SYNTAX OCTET STRING
    ACCESS read-write
    STATUS mandatory
    DESCRIPTION
        "This text is sent in the trap body."
    ::= { wtWebGraphAirQualityAlarmEntry 19 }

wtWebGraphAirQualityAlarmClearTcpText OBJECT-TYPE
    SYNTAX OCTET STRING
    ACCESS read-write
    STATUS mandatory
    DESCRIPTION
        "This text is sent in the TCP trap body."
    ::= { wtWebGraphAirQualityAlarmEntry 20 }

wtWebGraphAirQualityAlarmDeltaTemp OBJECT-TYPE
    SYNTAX OCTET STRING
    ACCESS read-write
    STATUS mandatory
    DESCRIPTION
        "Maximum rate of change  degrees/min with maximum 2 decimal places.
        Compared with the average of a period of 5 minutes."
    ::= { wtWebGraphAirQualityAlarmEntry 21 }

wtWebGraphAirQualityAlarmRHMin OBJECT-TYPE
    SYNTAX OCTET STRING
    ACCESS read-write
    STATUS mandatory
    DESCRIPTION
        "Minimum rel. Humidity in percent with maximum 2 decimal places."
    ::= { wtWebGraphAirQualityAlarmEntry 22 }

wtWebGraphAirQualityAlarmRHMax OBJECT-TYPE
    SYNTAX OCTET STRING
    ACCESS read-write
    STATUS mandatory
    DESCRIPTION
        "Maximum rel.Humidity in percent with maximum 2 decimal places."
    ::= { wtWebGraphAirQualityAlarmEntry 23 }

wtWebGraphAirQualityAlarmRHHysteresis OBJECT-TYPE
    SYNTAX OCTET STRING
    ACCESS read-write
    STATUS mandatory
    DESCRIPTION
        "Hysteresis of rel. Humidity in percent with maximum 2 decimal places."
    ::= { wtWebGraphAirQualityAlarmEntry 24 }

wtWebGraphAirQualityAlarmAHMin OBJECT-TYPE
    SYNTAX OCTET STRING
    ACCESS read-write
    STATUS mandatory
    DESCRIPTION
        "Minimum abs. Humidity in g/(m*m*m) with maximum 2 decimal places."
    ::= { wtWebGraphAirQualityAlarmEntry 25 }

wtWebGraphAirQualityAlarmAHMax OBJECT-TYPE
    SYNTAX OCTET STRING
    ACCESS read-write
    STATUS mandatory
    DESCRIPTION
        "Maximum abs. Humidity in g/(m*m*m) with maximum 2 decimal places."
    ::= { wtWebGraphAirQualityAlarmEntry 26 }

wtWebGraphAirQualityAlarmSyslogIpAddr OBJECT-TYPE
    SYNTAX IpAddress
    ACCESS read-write
    STATUS mandatory
    DESCRIPTION
        "IP address of the syslog server to which the Webio device should send syslog messages."
    ::= { wtWebGraphAirQualityAlarmEntry 27 }

wtWebGraphAirQualityAlarmSyslogPort OBJECT-TYPE
    SYNTAX INTEGER (1..65535)
    ACCESS read-write
    STATUS mandatory
    DESCRIPTION
        "Port number of the syslog server to which the Webio device should send syslog messages."
    ::= { wtWebGraphAirQualityAlarmEntry 28 }

wtWebGraphAirQualityAlarmSyslogText OBJECT-TYPE
    SYNTAX OCTET STRING
    ACCESS read-write
    STATUS mandatory
    DESCRIPTION
        "Every message starts with the priority key, a time stamp and the host ip address, according RFC3164.
        This text appears in the following syslog message body."
    ::= { wtWebGraphAirQualityAlarmEntry 29 }

wtWebGraphAirQualityAlarmSyslogClearText OBJECT-TYPE
    SYNTAX OCTET STRING
    ACCESS read-write
    STATUS mandatory
    DESCRIPTION
        "Every message starts with the priority key, a time stamp and the host ip address, according RFC3164.
        This text appears in the following syslog message body."
    ::= { wtWebGraphAirQualityAlarmEntry 30 }

wtWebGraphAirQualityAlarmFtpDataPort OBJECT-TYPE
    SYNTAX OCTET STRING
    ACCESS read-write
    STATUS mandatory
    DESCRIPTION
        "Local data port: 1..65535 or AUTO: the next free port will be assigned."
    ::= { wtWebGraphAirQualityAlarmEntry 31 }

wtWebGraphAirQualityAlarmFtpFileName OBJECT-TYPE
    SYNTAX OCTET STRING
    ACCESS read-write
    STATUS mandatory
    DESCRIPTION
        "Name of the file including path informations."
    ::= { wtWebGraphAirQualityAlarmEntry 32 }

wtWebGraphAirQualityAlarmFtpText OBJECT-TYPE
    SYNTAX OCTET STRING
    ACCESS read-write
    STATUS mandatory
    DESCRIPTION
        "Message text to store on the FTP server."
    ::= { wtWebGraphAirQualityAlarmEntry 33 }

wtWebGraphAirQualityAlarmFtpClearText OBJECT-TYPE
    SYNTAX OCTET STRING
    ACCESS read-write
    STATUS mandatory
    DESCRIPTION
        "Alarm clear message to store on the FTP server."
    ::= { wtWebGraphAirQualityAlarmEntry 34 }

wtWebGraphAirQualityAlarmFtpOption OBJECT-TYPE
    SYNTAX OCTET STRING (SIZE(4))
    ACCESS read-write
    STATUS mandatory
    DESCRIPTION
        "Binary coded options, select only one option at the same time:
        STORE  = replace file
        APPEND = append message at the end of the file

        Octet 1: unused
        Octet 2: unused
        Octet 3: unused
        Octet 4:
		Bit 0  :	STORE
		Bit 1  :	APPEND
        	Bit 2-7:	unused"
    ::= { wtWebGraphAirQualityAlarmEntry 35 }

wtWebGraphAirQualityAlarmTimerCron OBJECT-TYPE
    SYNTAX OCTET STRING
    ACCESS read-write
    STATUS mandatory
    DESCRIPTION
        "This entry contains 5 space or tab seperated text fields for time trigger definition.
        Each field must match with the actual time to trigger a message, weekday and day of month
        are interpreted separatley.
        1: Minutes	Range 0-59
        2. Hours	Range 0-23, 0 is midnight
        3: Day of month	Range 1-31
        4: Month	Range 1-12
        5: Weekday	Range 0-6, 0 is sunday

        Syntax for every field:
         - an asterix (*) enables every possible setting of a field
         - single numbers seperated by commas
         - a partition within the allowed range (1-5)
         - step size within an partition of the allowed range (0-59/2: every second minute)."
    ::= { wtWebGraphAirQualityAlarmEntry 36 }

wtWebGraphAirQualityAlarmVocMax OBJECT-TYPE
    SYNTAX OCTET STRING
    ACCESS read-write
    STATUS mandatory
    DESCRIPTION
        "Maximum VOC in ppm with maximum 2 decimal places."
    ::= { wtWebGraphAirQualityAlarmEntry 37 }

wtWebGraphAirQualityAlarmVocHysteresis OBJECT-TYPE
    SYNTAX OCTET STRING
    ACCESS read-write
    STATUS mandatory
    DESCRIPTION
        "Hysteresis of VOC in ppm with maximum 2 decimal places."
    ::= { wtWebGraphAirQualityAlarmEntry 38 }

-- __JB__
wtWebGraphAirQualityAlarmName OBJECT-TYPE
    SYNTAX OCTET STRING
    ACCESS read-write
    STATUS mandatory
    DESCRIPTION
        "Alert name"
    ::= { wtWebGraphAirQualityAlarmEntry 39 }

-- __JB__
wtWebGraphAirQualityAlarmActive OBJECT-TYPE
    SYNTAX OCTET STRING
    ACCESS read-write
    STATUS mandatory
    DESCRIPTION
        "Alert active
			1 = ON
			0 = OFF"
    ::= { wtWebGraphAirQualityAlarmEntry 40 }

wtWebGraphAirQualityAlarmHttpReqAuthEnable OBJECT-TYPE
    SYNTAX OCTET STRING
    ACCESS read-write
    STATUS mandatory
    DESCRIPTION
        "Binary coded options, select only one option at the same time:
        OCTET 1: unused
        OCTET 2: unused
        OCTET 3: unused
        OCTET 4, Bit 1-7: unused
        Bit 0  : HHTP Request Authentication enable"
    ::= { wtWebGraphAirQualityAlarmEntry 61 }

wtWebGraphAirQualityAlarmHttpReqAuthUser OBJECT-TYPE
    SYNTAX OCTET STRING
    ACCESS read-write
    STATUS mandatory
    DESCRIPTION
	"HTTP Request: User"
    ::= { wtWebGraphAirQualityAlarmEntry 62 }

wtWebGraphAirQualityAlarmHttpReqAuthPassword OBJECT-TYPE
    SYNTAX OCTET STRING
    ACCESS read-write
    STATUS mandatory
    DESCRIPTION
	"HTTP Request: Password"
    ::= { wtWebGraphAirQualityAlarmEntry 63 }

wtWebGraphAirQualityAlarmHttpReqSetUrl OBJECT-TYPE
    SYNTAX OCTET STRING
    ACCESS read-write
    STATUS mandatory
    DESCRIPTION
	"HTTP Request: Set URL"
    ::= { wtWebGraphAirQualityAlarmEntry 64 }

wtWebGraphAirQualityAlarmHttpReqClearUrl OBJECT-TYPE
    SYNTAX OCTET STRING
    ACCESS read-write
    STATUS mandatory
    DESCRIPTION
	"HTTP Request: Clear URL"
    ::= { wtWebGraphAirQualityAlarmEntry 65 }

wtWebGraphAirQualityAlarmHttpReqServerPort OBJECT-TYPE
    SYNTAX INTEGER (1..65535)
    ACCESS read-write
    STATUS mandatory
    DESCRIPTION
	"HTTP Request: Server Port"
    ::= { wtWebGraphAirQualityAlarmEntry 66 }

wtWebGraphAirQualityAlarmMqttTopicPath OBJECT-TYPE
    SYNTAX OCTET STRING
    ACCESS read-write
    STATUS mandatory
    DESCRIPTION
	"MQTT Publish: Topic path"
    ::= { wtWebGraphAirQualityAlarmEntry 67 }

wtWebGraphAirQualityAlarmMqttTopicSetTopic OBJECT-TYPE
    SYNTAX OCTET STRING
    ACCESS read-write
    STATUS mandatory
    DESCRIPTION
	"MQTT Publish: Topic SET message"
    ::= { wtWebGraphAirQualityAlarmEntry 68 }

wtWebGraphAirQualityAlarmMqttTopicClear OBJECT-TYPE
    SYNTAX OCTET STRING
    ACCESS read-write
    STATUS mandatory
    DESCRIPTION
	"MQTT Publish: Topic CLEAR message"
    ::= { wtWebGraphAirQualityAlarmEntry 69 }

wtWebGraphAirQualityAlarmSensorLostSelection OBJECT-TYPE
    SYNTAX OCTET STRING
    ACCESS read-write
    STATUS mandatory
    DESCRIPTION
        "Binary coded options:
        OCTET 1: unused
        OCTET 2: unused
        OCTET 3: unused
        OCTET 4, Bit 3-7: unused
		Bit 2  : Sensor 2
		Bit 1  : Sensor 1
        Bit 0  : Sensor 0"
    ::= { wtWebGraphAirQualityAlarmEntry 70 }

wtWebGraphAirQualityAlarmLimitWindow OBJECT-TYPE
    SYNTAX OCTET STRING
    ACCESS read-write
    STATUS mandatory
    DESCRIPTION
        "If window type is INSIDE the alarm is genereted when the temperature
        is greater minumum value and lower than maximum value. If window type is OUTSIDE
        the alarm is generated when the measured value is lower than the minimum value
        or greater than the maximum value.
		Binary coded options, select only one option at the same time:
        OCTET 1: unused
        OCTET 2: unused
        OCTET 3: unused
        OCTET 4, Bit 2-7: unused
		Bit 1  : inside window
        Bit 0  : outside window"
    ::= { wtWebGraphAirQualityAlarmEntry 71 }

-- wtWebGraphAirQualityGraphicsBase Group
----------------------------

wtWebGraphAirQualityGraphicsBaseEnable OBJECT-TYPE
    SYNTAX OCTET STRING
    ACCESS read-write
    STATUS mandatory
    DESCRIPTION
        "Defines the viewing options of the graphic:
        Octet 1: unused
        Octet 2: unused
        Octet 3: unused
        Octet 4:
                Bit 0  : Auto scroll enable
                Bit 1  : Show table
                Bit 2  : Show graph
                Bit 3  : Show control buttons
                Bit 4  : Show config menu
                Bit 5-7: unused"
    ::= { wtWebGraphAirQualityGraphicsBase 1 }

wtWebGraphAirQualityGraphicsBaseWidth OBJECT-TYPE
    SYNTAX INTEGER
    ACCESS read-write
    STATUS mandatory
    DESCRIPTION
        "Defines the width of the graphic in pixels."
    ::= { wtWebGraphAirQualityGraphicsBase 2 }

wtWebGraphAirQualityGraphicsBaseHeight OBJECT-TYPE
        SYNTAX INTEGER
        ACCESS read-write
        STATUS mandatory
        DESCRIPTION
            "Defines the height of the graphic in pixels."
        ::= { wtWebGraphAirQualityGraphicsBase 3 }

wtWebGraphAirQualityGraphicsBaseFrameColor OBJECT-TYPE
    SYNTAX OCTET STRING (SIZE(3))
    ACCESS read-write
    STATUS mandatory
    DESCRIPTION
        "Frame color definition in RGB."
    ::= { wtWebGraphAirQualityGraphicsBase 4 }

wtWebGraphAirQualityGraphicsBaseBackgroundColor OBJECT-TYPE
    SYNTAX OCTET STRING (SIZE(3))
    ACCESS read-write
    STATUS mandatory
    DESCRIPTION
        "Background color definition in RGB."
    ::= { wtWebGraphAirQualityGraphicsBase 5 }

wtWebGraphAirQualityGraphicsBasePollingrate OBJECT-TYPE
        SYNTAX INTEGER
        ACCESS read-write
        STATUS mandatory
        DESCRIPTION
            "Defines the pollingrate in seconds,
            which defines the refreshing intervall of the graphic."
        ::= { wtWebGraphAirQualityGraphicsBase 6 }

-- wtWebGraphAirQualityGraphicsSelect Group
----------------------------

wtWebGraphAirQualityGraphicsSelectDisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1: Sensor 2
        	Bit 2: Sensor 3
        	Bit 3-7: unused"
    ::= { wtWebGraphAirQualityGraphicsSelect 1 }

wtWebGraphAirQualityGraphicsSelectDisplayShowExtrem OBJECT-TYPE
    SYNTAX OCTET STRING (SIZE(4))
    ACCESS read-write
    STATUS mandatory
    DESCRIPTION
        "Binary coded sensor selection:
        only selected sensors will be shown with minima and maxima:
        Octet 1: unused
        Octet 2: unused
        Octet 3: unused
        Octet 4:
        	Bit 0: Sensor 1
        	Bit 1: Sensor 2
        	Bit 2: Sensor 3
        	Bit 3-7: unused"
     ::= { wtWebGraphAirQualityGraphicsSelect 2 }

-- Graph Sensor Color Table

wtWebGraphAirQualitySensorColorTable OBJECT-TYPE
    SYNTAX SEQUENCE OF WtWebGraphAirQualitySensorColorEntry
    ACCESS not-accessible
    STATUS mandatory
    DESCRIPTION
        "List of sensor colors for the praphical presentation."
    ::= { wtWebGraphAirQualityGraphicsSelect 3 }

wtWebGraphAirQualitySensorColorEntry OBJECT-TYPE
    SYNTAX WtWebGraphAirQualitySensorColorEntry
    ACCESS not-accessible
    STATUS mandatory
    DESCRIPTION
        "Numbers of the sensors."
    INDEX  { wtWebGraphAirQualitySensorNo }
    ::= { wtWebGraphAirQualitySensorColorTable 1 }

WtWebGraphAirQualitySensorColorEntry ::= SEQUENCE {
    wtWebGraphAirQualityGraphicsSensorColor OCTET STRING,
    wtWebGraphAirQualityGraphicsSelectScale OCTET STRING
}

wtWebGraphAirQualityGraphicsSensorColor OBJECT-TYPE
    SYNTAX OCTET STRING (SIZE(3))
    ACCESS read-write
    STATUS mandatory
    DESCRIPTION
        "Color of the sensors at the praphical presention."
    ::= { wtWebGraphAirQualitySensorColorEntry 1 }

wtWebGraphAirQualityGraphicsSelectScale OBJECT-TYPE
    SYNTAX OCTET STRING
    ACCESS read-write
    STATUS mandatory
    DESCRIPTION
        "Assignes one of 4 scales to a sensor:
        Octet 1: unused
        Octet 2: unused
        Octet 3: unused
        Octet 4:
                Bit 0  : Use Scale 1
                Bit 1  : Use Scale 2
                Bit 2  : Use Scale 3
                Bit 3-7: unused"
    ::= { wtWebGraphAirQualitySensorColorEntry 2 }

-- wtWebGraphAirQualityGraphicsScale Group
----------------------------

wtWebGraphAirQualityGraphicsScaleAutoScaleEnable OBJECT-TYPE
    SYNTAX OCTET STRING
    ACCESS read-write
    STATUS mandatory
    DESCRIPTION
        "Select the Auto Scale Mode:
        Octet 1: unused
        Octet 2: unused
        Octet 3: unused
        Octet 4:
                Bit 0  : Scale 1 Auto scale enable
                Bit 1  : Scale 2 Auto scale enable
                Bit 2  : Scale 3 Auto scale enable
                Bit 3-7: unused"
    ::= { wtWebGraphAirQualityGraphicsScale 1 }


wtWebGraphAirQualityGraphicsScaleAutoFitEnable OBJECT-TYPE
    SYNTAX OCTET STRING
    ACCESS read-write
    STATUS mandatory
    DESCRIPTION
        "Select the Auto Fit Mode::
        Octet 1: unused
        Octet 2: unused
        Octet 3: unused
        Octet 4:
                Bit 0  : Scale 1 Auto fit enable
                Bit 1  : Scale 2 Auto fit enable
                Bit 2  : Scale 3 Auto fit enable
                Bit 3-7: unused"
    ::= { wtWebGraphAirQualityGraphicsScale 2 }

wtWebGraphAirQualityGraphicsScale1Min OBJECT-TYPE
    SYNTAX INTEGER
    ACCESS read-only
    STATUS mandatory
    DESCRIPTION
        "Scale 1: Minimum."
    ::= { wtWebGraphAirQualityGraphicsScale 3 }

wtWebGraphAirQualityGraphicsScale2Min OBJECT-TYPE
    SYNTAX INTEGER
    ACCESS read-only
    STATUS mandatory
    DESCRIPTION
        "Scale 2: Minimum."
    ::= { wtWebGraphAirQualityGraphicsScale 4 }

wtWebGraphAirQualityGraphicsScale3Min OBJECT-TYPE
    SYNTAX INTEGER
    ACCESS read-only
    STATUS mandatory
    DESCRIPTION
        "Scale 3: Minimum."
    ::= { wtWebGraphAirQualityGraphicsScale 5 }

wtWebGraphAirQualityGraphicsScale4Min OBJECT-TYPE
    SYNTAX INTEGER
    ACCESS read-only
    STATUS mandatory
    DESCRIPTION
        "Scale 4: Minimum."
    ::= { wtWebGraphAirQualityGraphicsScale 6 }

wtWebGraphAirQualityGraphicsScale1Max OBJECT-TYPE
    SYNTAX INTEGER
    ACCESS read-only
    STATUS mandatory
    DESCRIPTION
        "Scale 1: Maximum."
    ::= { wtWebGraphAirQualityGraphicsScale 7 }

wtWebGraphAirQualityGraphicsScale2Max OBJECT-TYPE
    SYNTAX INTEGER
    ACCESS read-only
    STATUS mandatory
    DESCRIPTION
        "Scale 2: Maximum."
    ::= { wtWebGraphAirQualityGraphicsScale 8 }

wtWebGraphAirQualityGraphicsScale3Max OBJECT-TYPE
    SYNTAX INTEGER
    ACCESS read-only
    STATUS mandatory
    DESCRIPTION
        "Scale 3: Maximum."
    ::= { wtWebGraphAirQualityGraphicsScale 9 }

wtWebGraphAirQualityGraphicsScale4Max OBJECT-TYPE
    SYNTAX INTEGER
    ACCESS read-only
    STATUS mandatory
    DESCRIPTION
        "Scale 4: Maximum."
    ::= { wtWebGraphAirQualityGraphicsScale 10 }

wtWebGraphAirQualityGraphicsScale1Unit OBJECT-TYPE
    SYNTAX OCTET STRING
    ACCESS read-only
    STATUS mandatory
    DESCRIPTION
        "Scale 1: Unit."
    ::= { wtWebGraphAirQualityGraphicsScale 11 }

wtWebGraphAirQualityGraphicsScale2Unit OBJECT-TYPE
    SYNTAX OCTET STRING
    ACCESS read-only
    STATUS mandatory
    DESCRIPTION
        "Scale 2: Unit."
    ::= { wtWebGraphAirQualityGraphicsScale 12 }

wtWebGraphAirQualityGraphicsScale3Unit OBJECT-TYPE
    SYNTAX OCTET STRING
    ACCESS read-only
    STATUS mandatory
    DESCRIPTION
        "Scale 3: Unit."
    ::= { wtWebGraphAirQualityGraphicsScale 13 }

wtWebGraphAirQualityGraphicsScale4Unit OBJECT-TYPE
    SYNTAX OCTET STRING
    ACCESS read-only
    STATUS mandatory
    DESCRIPTION
        "Scale 4: Unit."
    ::= { wtWebGraphAirQualityGraphicsScale 14 }


-- wtWebGraphAirQualityPorts Group
----------------------------

-- Table

wtWebGraphAirQualityPortTable OBJECT-TYPE
    SYNTAX SEQUENCE OF WtWebGraphAirQualityPortEntry
    ACCESS not-accessible
    STATUS mandatory
    DESCRIPTION
        "List of settings depending on the sensor number."
    ::= { wtWebGraphAirQualityPorts 1 }

wtWebGraphAirQualityPortEntry OBJECT-TYPE
    SYNTAX WtWebGraphAirQualityPortEntry
    ACCESS not-accessible
    STATUS mandatory
    DESCRIPTION
        "Sensor parameters for the individual sensors."
    INDEX  { wtWebGraphAirQualitySensorNo }
    ::= { wtWebGraphAirQualityPortTable 1 }

WtWebGraphAirQualityPortEntry ::= SEQUENCE {
    wtWebGraphAirQualityPortName		OCTET STRING,
    wtWebGraphAirQualityPortText		OCTET STRING,
    wtWebGraphAirQualityPortOffset1		OCTET STRING,
    wtWebGraphAirQualityPortTemperature1	OCTET STRING,
    wtWebGraphAirQualityPortOffset2		OCTET STRING,
    wtWebGraphAirQualityPortTemperature2	OCTET STRING,
    wtWebGraphAirQualityPortComment		OCTET STRING
}

wtWebGraphAirQualityPortName OBJECT-TYPE
    SYNTAX OCTET STRING
    ACCESS read-write
    STATUS mandatory
    DESCRIPTION
        "Name of the sensor."
    ::= { wtWebGraphAirQualityPortEntry 1 }

wtWebGraphAirQualityPortText OBJECT-TYPE
    SYNTAX OCTET STRING
    ACCESS read-write
    STATUS mandatory
    DESCRIPTION
        "Description of the sensor."
    ::= { wtWebGraphAirQualityPortEntry 2 }

wtWebGraphAirQualityPortOffset1 OBJECT-TYPE
    SYNTAX OCTET STRING
    ACCESS read-write
    STATUS mandatory
    DESCRIPTION
        "Offset calibration: Offset in degrees with maximum 2 decimal places at temperature 1."
    ::= { wtWebGraphAirQualityPortEntry 3 }

wtWebGraphAirQualityPortTemperature1 OBJECT-TYPE
    SYNTAX OCTET STRING
    ACCESS read-write
    STATUS mandatory
    DESCRIPTION
        "Offset calibration: Reference temperature 1 in degrees with maximum 2 decimal places."
    ::= { wtWebGraphAirQualityPortEntry 4 }

wtWebGraphAirQualityPortOffset2 OBJECT-TYPE
    SYNTAX OCTET STRING
    ACCESS read-write
    STATUS mandatory
    DESCRIPTION
        "Offset calibration: Offset in degrees with maximum 2 decimal places at temperature 2."
    ::= { wtWebGraphAirQualityPortEntry 5 }

wtWebGraphAirQualityPortTemperature2 OBJECT-TYPE
    SYNTAX OCTET STRING
    ACCESS read-write
    STATUS mandatory
    DESCRIPTION
        "Offset calibration: Reference temperature 1 in degrees with maximum 2 decimal places."
    ::= { wtWebGraphAirQualityPortEntry 6 }

wtWebGraphAirQualityPortComment OBJECT-TYPE
    SYNTAX OCTET STRING
    ACCESS read-write
    STATUS mandatory
    DESCRIPTION
        "Offset calibration: informations of date, name of operator, reference devices."
    ::= { wtWebGraphAirQualityPortEntry 7 }

-- wtWebGraphAirQualityManufact Group
----------------------------

wtWebGraphAirQualityMfName OBJECT-TYPE
    SYNTAX OCTET STRING
    ACCESS read-write
    STATUS mandatory
    DESCRIPTION
        "Manufacturer company name"
    ::= { wtWebGraphAirQualityManufact 1 }

wtWebGraphAirQualityMfAddr OBJECT-TYPE
    SYNTAX OCTET STRING
    ACCESS read-write
    STATUS mandatory
    DESCRIPTION
        "Manufacturer address."
    ::= { wtWebGraphAirQualityManufact 2 }

wtWebGraphAirQualityMfHotline OBJECT-TYPE
    SYNTAX OCTET STRING
    ACCESS read-write
    STATUS mandatory
    DESCRIPTION
        "Manufacturer hotline."
    ::= { wtWebGraphAirQualityManufact 3 }

wtWebGraphAirQualityMfInternet OBJECT-TYPE
    SYNTAX OCTET STRING
    ACCESS read-write
    STATUS mandatory
    DESCRIPTION
        "Manufacturer Internet address."
    ::= { wtWebGraphAirQualityManufact 4 }

wtWebGraphAirQualityMfDeviceTyp OBJECT-TYPE
    SYNTAX OCTET STRING
    ACCESS read-write
    STATUS mandatory
    DESCRIPTION
        "Manufacturer device name (model number)."
    ::= { wtWebGraphAirQualityManufact 5 }

wtWebGraphAirQualityMfOrderNo OBJECT-TYPE
    SYNTAX OCTET STRING
    ACCESS read-write
    STATUS mandatory
    DESCRIPTION
        "Manufacturer part number."
    ::= { wtWebGraphAirQualityManufact 6 }

-- wtWebGraphAirQualityDiag Group
----------------------------

wtWebGraphAirQualityDiagErrorCount OBJECT-TYPE
    SYNTAX INTEGER
    ACCESS read-only
    STATUS mandatory
    DESCRIPTION
        "Number of entries in the error memory."
    ::= { wtWebGraphAirQualityDiag 1 }

wtWebGraphAirQualityDiagBinaryError OBJECT-TYPE
    SYNTAX OCTET STRING
    ACCESS read-only
    STATUS mandatory
    DESCRIPTION
        "Error causes coded bit-by-bit."
    ::= { wtWebGraphAirQualityDiag 2 }

wtWebGraphAirQualityDiagErrorIndex OBJECT-TYPE
    SYNTAX INTEGER
    ACCESS read-write
    STATUS mandatory
    DESCRIPTION
        "The value of this variable is used as an index to read
        an error massege from wtWebGraphAirQualityDiagErrorMessage.
        Errors are numbered from 1 to wtWebGraphAirQualityDiagErrorCount.
        Writing a valid value into this variable, making the appropriate
        message readable from wtWebGraphAirQualityDiagErrorMessage."
    ::= { wtWebGraphAirQualityDiag 3 }

wtWebGraphAirQualityDiagErrorMessage OBJECT-TYPE
    SYNTAX OCTET STRING
    ACCESS read-only
    STATUS mandatory
    DESCRIPTION
        "Using wtWebGraphAirQualityDiagErrorIndex as an index, the appropriate message is available."
    ::= { wtWebGraphAirQualityDiag 4 }

wtWebGraphAirQualityDiagErrorClear OBJECT-TYPE
    SYNTAX INTEGER
    ACCESS write-only
    STATUS mandatory
    DESCRIPTION
        "Writing 1 into this variable clears all diagnosis messages."
    ::= { wtWebGraphAirQualityDiag 5 }

-- TRAP DEFINITIONS

-- Diese SNMP-Traps werden gesendet, wenn die Alarmtriggerbedingungen zutreffen

wtWebGraphAirQualityAlert1 TRAP-TYPE
    ENTERPRISE  wtWebGraphAirQuality
    VARIABLES   { wtWebGraphAirQualityAlarmTrapText }
    DESCRIPTION
        "This SNMP trap is generated when Alarm 1 was triggered,
        SNMP trap enable is set and
        SNMP is enabled."
    -- NMS trap annotation
    --#TYPE "Thermo-Hygrometer Alarm 1"
    --#SUMMARY "Alarm 1: %s"
    --#ARGUMENTS {0}
    --#SEVERITY INFORMATIONAL
    --#TIMEINDEX 99
    --#STATE OPERATIONAL
    ::= 31

wtWebGraphAirQualityAlert2 TRAP-TYPE
    ENTERPRISE  wtWebGraphAirQuality
    VARIABLES   { wtWebGraphAirQualityAlarmTrapText }
    DESCRIPTION
        "This SNMP trap is generated when Alarm 2 was triggered,
        SNMP trap enable is set and
        SNMP is enabled."
    -- NMS trap annotation
    --#TYPE "Thermo-Hygrometer Alarm 2"
    --#SUMMARY "Alarm 2: %s"
    --#ARGUMENTS {0}
    --#SEVERITY INFORMATIONAL
    --#TIMEINDEX 99
    --#STATE OPERATIONAL
    ::= 32

wtWebGraphAirQualityAlert3 TRAP-TYPE
    ENTERPRISE  wtWebGraphAirQuality
    VARIABLES   { wtWebGraphAirQualityAlarmTrapText }
    DESCRIPTION
        "This SNMP trap is generated when Alarm 3 was triggered,
        SNMP trap enable is set and
        SNMP is enabled."
    -- NMS trap annotation
    --#TYPE "Thermo-Hygrometer Alarm 3"
    --#SUMMARY "Alarm 3: %s"
    --#ARGUMENTS {0}
    --#SEVERITY INFORMATIONAL
    --#TIMEINDEX 99
    --#STATE OPERATIONAL
    ::= 33

wtWebGraphAirQualityAlert4 TRAP-TYPE
    ENTERPRISE  wtWebGraphAirQuality
    VARIABLES   { wtWebGraphAirQualityAlarmTrapText }
    DESCRIPTION
        "This SNMP trap is generated when Alarm 4 was triggered,
        SNMP trap enable is set and
        SNMP is enabled."
    -- NMS trap annotation
    --#TYPE "Thermo-Hygrometer Alarm 4"
    --#SUMMARY "Alarm 4: %s"
    --#ARGUMENTS {0}
    --#SEVERITY INFORMATIONAL
    --#TIMEINDEX 99
    --#STATE OPERATIONAL
    ::= 34

wtWebGraphAirQualityAlert5 TRAP-TYPE
    ENTERPRISE  wtWebGraphAirQuality
    VARIABLES   { wtWebGraphAirQualityAlarmTrapText }
    DESCRIPTION
        "This SNMP trap is generated when Alarm 5 was triggered,
        SNMP trap enable is set and
        SNMP is enabled."
    -- NMS trap annotation
    --#TYPE "Thermo-Hygrometer Alarm 5"
    --#SUMMARY "Alarm 5: %s"
    --#ARGUMENTS {0}
    --#SEVERITY INFORMATIONAL
    --#TIMEINDEX 99
    --#STATE OPERATIONAL
    ::= 35

wtWebGraphAirQualityAlert6 TRAP-TYPE
    ENTERPRISE  wtWebGraphAirQuality
    VARIABLES   { wtWebGraphAirQualityAlarmTrapText }
    DESCRIPTION
        "This SNMP trap is generated when Alarm 6 was triggered,
        SNMP trap enable is set and
        SNMP is enabled."
    -- NMS trap annotation
    --#TYPE "Thermo-Hygrometer Alarm 6"
    --#SUMMARY "Alarm 6: %s"
    --#ARGUMENTS {0}
    --#SEVERITY INFORMATIONAL
    --#TIMEINDEX 99
    --#STATE OPERATIONAL
    ::= 36

wtWebGraphAirQualityAlert7 TRAP-TYPE
    ENTERPRISE  wtWebGraphAirQuality
    VARIABLES   { wtWebGraphAirQualityAlarmTrapText }
    DESCRIPTION
        "This SNMP trap is generated when Alarm 7 was triggered,
        SNMP trap enable is set and
        SNMP is enabled."
    -- NMS trap annotation
    --#TYPE "Thermo-Hygrometer Alarm 7"
    --#SUMMARY "Alarm 7: %s"
    --#ARGUMENTS {0}
    --#SEVERITY INFORMATIONAL
    --#TIMEINDEX 99
    --#STATE OPERATIONAL
    ::= 37

wtWebGraphAirQualityAlert8 TRAP-TYPE
    ENTERPRISE  wtWebGraphAirQuality
    VARIABLES   { wtWebGraphAirQualityAlarmTrapText }
    DESCRIPTION
        "This SNMP trap is generated when Alarm 8 was triggered,
        SNMP trap enable is set and
        SNMP is enabled."
    -- NMS trap annotation
    --#TYPE "Thermo-Hygrometer Alarm 8"
    --#SUMMARY "Alarm 8: %s"
    --#ARGUMENTS {0}
    --#SEVERITY INFORMATIONAL
    --#TIMEINDEX 99
    --#STATE OPERATIONAL
    ::= 38


wtWebGraphAirQualityAlert9 TRAP-TYPE
    ENTERPRISE  wtWebGraphAirQuality
    VARIABLES   { wtWebGraphAirQualityAlarmClearTrapText }
    DESCRIPTION
        "This SNMP trap is generated when Alarm 1 was cleared,
        SNMP trap enable is set and
        SNMP is enabled."
    -- NMS trap annotation
    --#TYPE "Thermo-Hygrometer Release Alarm 1"
    --#SUMMARY "Release Alarm 1: %s"
    --#ARGUMENTS {0}
    --#SEVERITY INFORMATIONAL
    --#TIMEINDEX 99
    --#STATE OPERATIONAL
    ::= 91

wtWebGraphAirQualityAlert10 TRAP-TYPE
    ENTERPRISE  wtWebGraphAirQuality
    VARIABLES   { wtWebGraphAirQualityAlarmClearTrapText }
    DESCRIPTION
        "This SNMP trap is generated when Alarm 2 was cleared,
        SNMP trap enable is set and
        SNMP is enabled."
    -- NMS trap annotation
    --#TYPE "Thermo-Hygrometer Release Alarm 2"
    --#SUMMARY "Release Alarm 2: %s"
    --#ARGUMENTS {0}
    --#SEVERITY INFORMATIONAL
    --#TIMEINDEX 99
    --#STATE OPERATIONAL
    ::= 92

wtWebGraphAirQualityAlert11 TRAP-TYPE
    ENTERPRISE  wtWebGraphAirQuality
    VARIABLES   { wtWebGraphAirQualityAlarmClearTrapText }
    DESCRIPTION
        "This SNMP trap is generated when Alarm 3 was cleared,
        SNMP trap enable is set and
        SNMP is enabled."
    -- NMS trap annotation
    --#TYPE "Thermo-Hygrometer Release Alarm 3"
    --#SUMMARY "Release Alarm 3: %s"
    --#ARGUMENTS {0}
    --#SEVERITY INFORMATIONAL
    --#TIMEINDEX 99
    --#STATE OPERATIONAL
    ::= 93

wtWebGraphAirQualityAlert12 TRAP-TYPE
    ENTERPRISE  wtWebGraphAirQuality
    VARIABLES   { wtWebGraphAirQualityAlarmClearTrapText }
    DESCRIPTION
        "This SNMP trap is generated when Alarm 4 was cleared,
        SNMP trap enable is set and
        SNMP is enabled."
    -- NMS trap annotation
    --#TYPE "Thermo-Hygrometer Release Alarm 4"
    --#SUMMARY "Release Alarm 4: %s"
    --#ARGUMENTS {0}
    --#SEVERITY INFORMATIONAL
    --#TIMEINDEX 99
    --#STATE OPERATIONAL
    ::= 94

wtWebGraphAirQualityAlert13 TRAP-TYPE
    ENTERPRISE  wtWebGraphAirQuality
    VARIABLES   { wtWebGraphAirQualityAlarmClearTrapText }
    DESCRIPTION
        "This SNMP trap is generated when Alarm 5 was cleared,
        SNMP trap enable is set and
        SNMP is enabled."
    -- NMS trap annotation
    --#TYPE "Thermo-Hygrometer Release Alarm 5"
    --#SUMMARY "Release Alarm 5: %s"
    --#ARGUMENTS {0}
    --#SEVERITY INFORMATIONAL
    --#TIMEINDEX 99
    --#STATE OPERATIONAL
    ::= 95

wtWebGraphAirQualityAlert14 TRAP-TYPE
    ENTERPRISE  wtWebGraphAirQuality
    VARIABLES   { wtWebGraphAirQualityAlarmClearTrapText }
    DESCRIPTION
        "This SNMP trap is generated when Alarm 6 was cleared,
        SNMP trap enable is set and
        SNMP is enabled."
    -- NMS trap annotation
    --#TYPE "Thermo-Hygrometer Release Alarm 6"
    --#SUMMARY "Release Alarm 6: %s"
    --#ARGUMENTS {0}
    --#SEVERITY INFORMATIONAL
    --#TIMEINDEX 99
    --#STATE OPERATIONAL
    ::= 96

wtWebGraphAirQualityAlert15 TRAP-TYPE
    ENTERPRISE  wtWebGraphAirQuality
    VARIABLES   { wtWebGraphAirQualityAlarmClearTrapText }
    DESCRIPTION
        "This SNMP trap is generated when Alarm 7 was cleared,
        SNMP trap enable is set and
        SNMP is enabled."
    -- NMS trap annotation
    --#TYPE "Thermo-Hygrometer Release Alarm 7"
    --#SUMMARY "Release Alarm 7: %s"
    --#ARGUMENTS {0}
    --#SEVERITY INFORMATIONAL
    --#TIMEINDEX 99
    --#STATE OPERATIONAL
    ::= 97

wtWebGraphAirQualityAlert16 TRAP-TYPE
    ENTERPRISE  wtWebGraphAirQuality
    VARIABLES   { wtWebGraphAirQualityAlarmClearTrapText }
    DESCRIPTION
        "This SNMP trap is generated when Alarm 8 was cleared,
        SNMP trap enable is set and
        SNMP is enabled."
    -- NMS trap annotation
    --#TYPE "Thermo-Hygrometer Release Alarm 8"
    --#SUMMARY "Release Alarm 8: %s"
    --#ARGUMENTS {0}
    --#SEVERITY INFORMATIONAL
    --#TIMEINDEX 99
    --#STATE OPERATIONAL
    ::= 98

wtWebGraphAirQualityAlertDiag TRAP-TYPE
    ENTERPRISE  wtWebGraphAirQuality
    VARIABLES   {
    		wtWebGraphAirQualityDiagErrorIndex,
    	  	wtWebGraphAirQualityDiagErrorMessage
    		}
    DESCRIPTION
        "This SNMP trap is generated when a diagnosis/error message was triggered,
        SNMP trap enable is set and
        SNMP is enabled."
    -- NMS trap annotation
    --#TYPE "Thermo-Hygrometer Diagnose Error"
    --#SUMMARY "Diagnose error index: %d, Message: %s."
    --#ARGUMENTS {0,1}
    --#SEVERITY MAJOR
    --#TIMEINDEX 99
    --#STATE DEGRADED
    ::= 110

END
