WebGraph-OLD-8xThermometer-US-MIB DEFINITIONS ::= BEGIN
----------------------------------------------------------------
-- Revison: 1.30
----------------------------------------------------------------
-- 22.06.2010 	Output with decimal point
--
----------------------------------------------------------------
-- Revison: 1.29
----------------------------------------------------------------
-- 12.01.2009 	Webio
--		Trap number
----------------------------------------------------------------
-- Revison: 1.28
----------------------------------------------------------------
-- 19.01.2007 	Webio
--		New Graphics java script base parameter
----------------------------------------------------------------
-- Revison: 1.27
----------------------------------------------------------------
-- 09.11.2006 	Webio
--		DHCP enable
----------------------------------------------------------------
-- Revison: 1.25
----------------------------------------------------------------
-- 28.06.2006 	New: Community String Trap
--
----------------------------------------------------------------
-- Revison: 1.24
----------------------------------------------------------------
-- 23.12.2005 	#5760x, WebGraph 8x Thermometer
--


    IMPORTS

    OBJECT-TYPE                                        FROM RFC-1212
    TRAP-TYPE                                          FROM RFC-1215
    DisplayString, PhysAddress                         FROM RFC1213-MIB
    enterprises, TimeTicks, IpAddress, NetworkAddress  FROM RFC1155-SMI;


--    IpAddress ::=
--        [APPLICATION 0]
--            IMPLICIT OCTET STRING (SIZE (4))
--    Counter ::=
--        [APPLICATION 1]
--            IMPLICIT INTEGER (0..4294967295)
--    Gauge ::=
--        [APPLICATION 2]
--            IMPLICIT INTEGER (0..4294967295)
--    TimeTicks ::=
--        [APPLICATION 3]
--            IMPLICIT INTEGER (0..4294967295)


--    DisplayString ::= OCTET STRING
--    PhysAddress   ::= OCTET STRING

--    internet         OBJECT IDENTIFIER ::= { iso org(3) dod(6) 1 }
--    privat           OBJECT IDENTIFIER ::= { internet 4 }
--    enterprises      OBJECT IDENTIFIER ::= { privat 1 }



--  Wiesemann & Theis Com-Server MIB

    wut                			OBJECT IDENTIFIER ::= { enterprises 5040 }
    wtComServer        			OBJECT IDENTIFIER ::= { wut 1 }
    wtWebio            			OBJECT IDENTIFIER ::= { wtComServer 2 }

--  wtWebio Tree

    wtWebioAn8Graph    			OBJECT IDENTIFIER ::= { wtWebio 6 }

--  wtWebioAn8Graph Tree

    wtWebioAn8GraphTemp      		OBJECT IDENTIFIER ::= { wtWebioAn8Graph 1 }
    wtWebioAn8GraphSessCntrl 		OBJECT IDENTIFIER ::= { wtWebioAn8Graph 2 }
    wtWebioAn8GraphConfig    		OBJECT IDENTIFIER ::= { wtWebioAn8Graph 3 }
    wtWebioAn8GraphDiag    		OBJECT IDENTIFIER ::= { wtWebioAn8Graph 4 }

--  wtWebioAn8GraphConfig Tree

    wtWebioAn8GraphDevice    		OBJECT IDENTIFIER ::= { wtWebioAn8GraphConfig 1 }
    wtWebioAn8GraphPorts     		OBJECT IDENTIFIER ::= { wtWebioAn8GraphConfig 2 }
    wtWebioAn8GraphManufact  		OBJECT IDENTIFIER ::= { wtWebioAn8GraphConfig 3 }

--  wtWebioAn8GraphDevice Tree

    wtWebioAn8GraphText			OBJECT IDENTIFIER ::= { wtWebioAn8GraphDevice 1 }
    wtWebioAn8GraphTimeDate 		OBJECT IDENTIFIER ::= { wtWebioAn8GraphDevice 2 }
    wtWebioAn8GraphBasic		OBJECT IDENTIFIER ::= { wtWebioAn8GraphDevice 3 }
    wtWebioAn8GraphDatalogger		OBJECT IDENTIFIER ::= { wtWebioAn8GraphDevice 4 }
    wtWebioAn8GraphAlarm		OBJECT IDENTIFIER ::= { wtWebioAn8GraphDevice 5 }
    wtWebioAn8GraphGraphics 		OBJECT IDENTIFIER ::= { wtWebioAn8GraphDevice 6 }

--  wtWebioAn8GraphTimeDate Tree

    wtWebioAn8GraphTimeZone		OBJECT IDENTIFIER ::= { wtWebioAn8GraphTimeDate 1 }
    wtWebioAn8GraphTimeServer		OBJECT IDENTIFIER ::= { wtWebioAn8GraphTimeDate 2 }
    wtWebioAn8GraphDeviceClock		OBJECT IDENTIFIER ::= { wtWebioAn8GraphTimeDate 3 }

--  wtWebioAn8GraphBasic Tree

    wtWebioAn8GraphNetwork		OBJECT IDENTIFIER ::= { wtWebioAn8GraphBasic 1 }
    wtWebioAn8GraphHTTP			OBJECT IDENTIFIER ::= { wtWebioAn8GraphBasic 2 }
    wtWebioAn8GraphMail			OBJECT IDENTIFIER ::= { wtWebioAn8GraphBasic 3 }
    wtWebioAn8GraphSNMP			OBJECT IDENTIFIER ::= { wtWebioAn8GraphBasic 4 }
    wtWebioAn8GraphUDP			OBJECT IDENTIFIER ::= { wtWebioAn8GraphBasic 5 }
    wtWebioAn8GraphSyslog		OBJECT IDENTIFIER ::= { wtWebioAn8GraphBasic 6 }
    wtWebioAn8GraphFTP			OBJECT IDENTIFIER ::= { wtWebioAn8GraphBasic 7 }

--  wtWebioAn8GraphGraphics Tree

    wtWebioAn8GraphGraphicsBase 	OBJECT IDENTIFIER ::= { wtWebioAn8GraphGraphics 1 }
    wtWebioAn8GraphGraphicsSelect 	OBJECT IDENTIFIER ::= { wtWebioAn8GraphGraphics 2 }
    wtWebioAn8GraphGraphicsScale 	OBJECT IDENTIFIER ::= { wtWebioAn8GraphGraphics 3 }


-- wtWebioAn8GraphTemp Group
------------------------

wtWebioAn8GraphSensors OBJECT-TYPE
    SYNTAX INTEGER (1..8)
    ACCESS read-only
    STATUS mandatory
    DESCRIPTION
        "Number of temperature sensors"
    ::= { wtWebioAn8GraphTemp 1 }

-- Interface Table

wtWebioAn8GraphSensorTable OBJECT-TYPE
    SYNTAX SEQUENCE OF WtWebioAn8GraphSensorEntry
    ACCESS not-accessible
    STATUS mandatory
    DESCRIPTION
        "List of sensors."
    ::= { wtWebioAn8GraphTemp 2 }

wtWebioAn8GraphSensorEntry OBJECT-TYPE
    SYNTAX WtWebioAn8GraphSensorEntry
    ACCESS not-accessible
    STATUS mandatory
    DESCRIPTION
        "Temperature sensor numbers."
    INDEX  { wtWebioAn8GraphSensorNo }
    ::= { wtWebioAn8GraphSensorTable 1 }

WtWebioAn8GraphSensorEntry ::= SEQUENCE {
    wtWebioAn8GraphSensorNo INTEGER
}

wtWebioAn8GraphSensorNo OBJECT-TYPE
    SYNTAX INTEGER (1..8)
    ACCESS read-only
    STATUS mandatory
    DESCRIPTION
        "Temperature sensor number."
    ::= { wtWebioAn8GraphSensorEntry 1 }


-- wtWebioAn8GraphTempValue Table

wtWebioAn8GraphTempValueTable OBJECT-TYPE
    SYNTAX SEQUENCE OF WtWebioAn8GraphTempValueEntry
    ACCESS not-accessible
    STATUS mandatory
    DESCRIPTION
        "List of temperature values corresponding to the channel numbers."
    ::= { wtWebioAn8GraphTemp 3 }

wtWebioAn8GraphTempValueEntry OBJECT-TYPE
    SYNTAX WtWebioAn8GraphTempValueEntry
    ACCESS not-accessible
    STATUS mandatory
    DESCRIPTION
        "Temperatures of the sensors."
    INDEX  { wtWebioAn8GraphSensorNo }
    ::= { wtWebioAn8GraphTempValueTable 1 }

WtWebioAn8GraphTempValueEntry ::= SEQUENCE{
    wtWebioAn8GraphTempValue OCTET STRING
}

wtWebioAn8GraphTempValue OBJECT-TYPE
    SYNTAX OCTET STRING (SIZE (5))
    ACCESS read-only
    STATUS mandatory
    DESCRIPTION
        "Temperature value of the sensor, ASCII, 5 characters in length."
    ::= { wtWebioAn8GraphTempValueEntry 1 }

-- wtWebioAn8GraphBinaryTempValue Table

wtWebioAn8GraphBinaryTempValueTable OBJECT-TYPE
    SYNTAX SEQUENCE OF WtWebioAn8GraphBinaryTempValueEntry
    ACCESS not-accessible
    STATUS mandatory
    DESCRIPTION
        "List of binary temperature values corresponding to the channel numbers."
    ::= { wtWebioAn8GraphTemp 4 }

wtWebioAn8GraphBinaryTempValueEntry OBJECT-TYPE
    SYNTAX WtWebioAn8GraphBinaryTempValueEntry
    ACCESS not-accessible
    STATUS mandatory
    DESCRIPTION
        "Binary temperature values of the sensors."
    INDEX  { wtWebioAn8GraphSensorNo }
    ::= { wtWebioAn8GraphBinaryTempValueTable 1 }

WtWebioAn8GraphBinaryTempValueEntry ::= SEQUENCE{
    wtWebioAn8GraphBinaryTempValue INTEGER
}

wtWebioAn8GraphBinaryTempValue OBJECT-TYPE
    SYNTAX INTEGER
    ACCESS read-only
    STATUS mandatory
    DESCRIPTION
        "Binary temperature value of the sensor in 1/10 degrees Celsius,
        signed number, 0x4FFF6 indicates an
        invalid measured value."
    ::= { wtWebioAn8GraphBinaryTempValueEntry 1 }

-- wtWebioAn8GraphTempValuePkt Table

wtWebioAn8GraphTempValuePktTable OBJECT-TYPE
    SYNTAX SEQUENCE OF WtWebioAn8GraphTempValuePktEntry
    ACCESS not-accessible
    STATUS mandatory
    DESCRIPTION
        "List of temperature values corresponding to the channel numbers."
    ::= { wtWebioAn8GraphTemp 8 }

wtWebioAn8GraphTempValuePktEntry OBJECT-TYPE
    SYNTAX WtWebioAn8GraphTempValuePktEntry
    ACCESS not-accessible
    STATUS mandatory
    DESCRIPTION
        "Temperatures of the sensors."
    INDEX  { wtWebioAn8GraphSensorNo }
    ::= { wtWebioAn8GraphTempValuePktTable 1 }

WtWebioAn8GraphTempValuePktEntry ::= SEQUENCE{
    wtWebioAn8GraphTempValuePkt OCTET STRING
}

wtWebioAn8GraphTempValuePkt OBJECT-TYPE
    SYNTAX OCTET STRING (SIZE (5))
    ACCESS read-only
    STATUS mandatory
    DESCRIPTION
        "Temperature value of the sensor, ASCII, 5 characters in length, decimal point."
    ::= { wtWebioAn8GraphTempValuePktEntry 1 }

-- wtWebioAn8GraphSessCntrl Group
--------------------------------

wtWebioAn8GraphSessCntrlPassword OBJECT-TYPE
    SYNTAX OCTET STRING
    ACCESS read-write
    STATUS mandatory
    DESCRIPTION
        "Entering this password opens a session which is ended by writing a 1 to
        wtWebioAn8GraphSessCntrlLogout. When read this variable provides a string of
        length zero."
    ::= { wtWebioAn8GraphSessCntrl 1 }

wtWebioAn8GraphSessCntrlConfigMode OBJECT-TYPE
    SYNTAX INTEGER {
    wtWebioAn8GraphSessCntrl-NoSession(0),
    wtWebioAn8GraphSessCntrl-Session(1)
    }
    ACCESS read-only
    STATUS mandatory
    DESCRIPTION
        "When the device is in SNMP configuration mode, the value 1 is
        returned, otherwise 0. If the read value is 0 even though the
        password was written, the device is already in config mode and the
        variables can only be read."
    ::= { wtWebioAn8GraphSessCntrl 2 }

wtWebioAn8GraphSessCntrlLogout OBJECT-TYPE
    SYNTAX INTEGER
    ACCESS read-write
    STATUS mandatory
    DESCRIPTION
        "If the device is in configuration mode and the session was opened by
        this SNMP Manager, writing a 1 to this variable will end the session
        and all parameters are stored.
        Writing a 2 discards all entries again.
        When read this variable provides the value 0."
    ::= { wtWebioAn8GraphSessCntrl 3 }

wtWebioAn8GraphSessCntrlAdminPassword OBJECT-TYPE
    SYNTAX OCTET STRING
    ACCESS read-write
    STATUS mandatory
    DESCRIPTION
        "This password protects access to the variables with administrator rights.
        It can only be changed by the administrator. If no password was assigned,
        the valid password is public."
    ::= { wtWebioAn8GraphSessCntrl 4 }

wtWebioAn8GraphSessCntrlConfigPassword OBJECT-TYPE
    SYNTAX OCTET STRING
    ACCESS read-write
    STATUS mandatory
    DESCRIPTION
        "This password protects access to the variables with configurator rights. It can
        be changed by the administrator and by the configurator. If no password was assigned,
        the valid password is public. When read this variable provides a null-pointer."
    ::= { wtWebioAn8GraphSessCntrl 5 }


-- wtWebioAn8GraphText Group
------------------------

wtWebioAn8GraphDeviceName OBJECT-TYPE
    SYNTAX OCTET STRING
    ACCESS read-write
    STATUS mandatory
    DESCRIPTION
        "Name of the Webio, which is user definable."
    ::= { wtWebioAn8GraphText 1 }

wtWebioAn8GraphDeviceText OBJECT-TYPE
    SYNTAX OCTET STRING
    ACCESS read-write
    STATUS mandatory
    DESCRIPTION
        "Description of the Webio, which is user definable."
    ::= { wtWebioAn8GraphText 2 }

wtWebioAn8GraphDeviceLocation OBJECT-TYPE
    SYNTAX OCTET STRING
    ACCESS read-write
    STATUS mandatory
    DESCRIPTION
        "Description of the location of the Webio, which is user definable."
    ::= { wtWebioAn8GraphText 3 }

wtWebioAn8GraphDeviceContact OBJECT-TYPE
    SYNTAX OCTET STRING
    ACCESS read-write
    STATUS mandatory
    DESCRIPTION
        "Contact address of the system operator of the Webio, which is user definable."
    ::= { wtWebioAn8GraphText 4 }

-- wtWebioAn8GraphTimeZone Group
----------------------------

wtWebioAn8GraphTzOffsetHrs OBJECT-TYPE
    SYNTAX INTEGER
    ACCESS read-write
    STATUS mandatory
    DESCRIPTION
        "Offset hours for the time zone (winter time) with respect to UTC."
    ::= { wtWebioAn8GraphTimeZone 1 }

wtWebioAn8GraphTzOffsetMin OBJECT-TYPE
    SYNTAX INTEGER
    ACCESS read-write
    STATUS mandatory
    DESCRIPTION
        "Offset minutes for the time zone (winter time) with respect to UTC."
    ::= { wtWebioAn8GraphTimeZone 2 }

wtWebioAn8GraphTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebioAn8GraphTimeZone 3 }

wtWebioAn8GraphStTzOffsetHrs OBJECT-TYPE
    SYNTAX INTEGER
    ACCESS read-write
    STATUS mandatory
    DESCRIPTION
        "Offset hours of the time zone (summer time) with respect to UTC."
    ::= { wtWebioAn8GraphTimeZone 4 }

wtWebioAn8GraphStTzOffsetMin OBJECT-TYPE
    SYNTAX INTEGER
    ACCESS read-write
    STATUS mandatory
    DESCRIPTION
        "Offset minutes of the time zone (summer time) with respect to UTC."
    ::= { wtWebioAn8GraphTimeZone 5 }

wtWebioAn8GraphStTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebioAn8GraphTimeZone 6 }

wtWebioAn8GraphStTzStartMonth OBJECT-TYPE
    SYNTAX INTEGER {
    	wtWebioAn8GraphStartMonth-January(1),
    	wtWebioAn8GraphStartMonth-February(2),
    	wtWebioAn8GraphStartMonth-March(3),
    	wtWebioAn8GraphStartMonth-April(4),
    	wtWebioAn8GraphStartMonth-May(5),
    	wtWebioAn8GraphStartMonth-June(6),
    	wtWebioAn8GraphStartMonth-July(7),
    	wtWebioAn8GraphStartMonth-August(8),
    	wtWebioAn8GraphStartMonth-September(9),
    	wtWebioAn8GraphStartMonth-October(10),
    	wtWebioAn8GraphStartMonth-November(11),
    	wtWebioAn8GraphStartMonth-December(12)
    	}

    ACCESS read-write
    STATUS mandatory
    DESCRIPTION
        "Month in which the change is made from winter time to summer time."
    ::= { wtWebioAn8GraphTimeZone 7 }

wtWebioAn8GraphStTzStartMode OBJECT-TYPE
    SYNTAX INTEGER {
    	wtWebioAn8GraphStartMode-first(1),
    	wtWebioAn8GraphStartMode-second(2),
    	wtWebioAn8GraphStartMode-third(3),
    	wtWebioAn8GraphStartMode-fourth(4),
    	wtWebioAn8GraphStartMode-last(5)
    	}

    ACCESS read-write
    STATUS mandatory
    DESCRIPTION
        "Mode of the day of the week for which the change is made from winter time to summer time."
    ::= { wtWebioAn8GraphTimeZone 8 }

wtWebioAn8GraphStTzStartWday OBJECT-TYPE
    SYNTAX INTEGER {
    	wtWebioAn8GraphStartWday-Sunday(1),
    	wtWebioAn8GraphStartWday-Monday(2),
    	wtWebioAn8GraphStartWday-Tuesday(3),
    	wtWebioAn8GraphStartWday-Thursday(4),
    	wtWebioAn8GraphStartWday-Wednesday(5),
    	wtWebioAn8GraphStartWday-Friday(6),
    	wtWebioAn8GraphStartWday-Saturday(7)
    	}

    ACCESS read-write
    STATUS mandatory
    DESCRIPTION
        "Day of the week on which the change is made from winter time to summer time"
    ::= { wtWebioAn8GraphTimeZone 9 }

wtWebioAn8GraphStTzStartHrs OBJECT-TYPE
    SYNTAX INTEGER
    ACCESS read-write
    STATUS mandatory
    DESCRIPTION
        "Hour in which the time zone is changed from winter to summer time with
        respect to UTC."
    ::= { wtWebioAn8GraphTimeZone 10 }

wtWebioAn8GraphStTzStartMin OBJECT-TYPE
    SYNTAX INTEGER
    ACCESS read-write
    STATUS mandatory
    DESCRIPTION
        "Minute in which the time zone is changed from winter to summer time with
        respect to UTC."
    ::= { wtWebioAn8GraphTimeZone 11 }

wtWebioAn8GraphStTzStopMonth OBJECT-TYPE
    SYNTAX INTEGER {
    	wtWebioAn8GraphStopMonth-January(1),
    	wtWebioAn8GraphStopMonth-February(2),
    	wtWebioAn8GraphStopMonth-March(3),
    	wtWebioAn8GraphStopMonth-April(4),
    	wtWebioAn8GraphStopMonth-May(5),
    	wtWebioAn8GraphStopMonth-June(6),
    	wtWebioAn8GraphStopMonth-July(7),
    	wtWebioAn8GraphStopMonth-August(8),
    	wtWebioAn8GraphStopMonth-September(9),
    	wtWebioAn8GraphStopMonth-October(10),
    	wtWebioAn8GraphStopMonth-November(11),
    	wtWebioAn8GraphStopMonth-December(12)
    	}
    ACCESS read-write
    STATUS mandatory
    DESCRIPTION
        "Month in which the change is made from summer time to winter time."
   ::= { wtWebioAn8GraphTimeZone 12 }

wtWebioAn8GraphStTzStopMode OBJECT-TYPE
    SYNTAX INTEGER {
    	wtWebioAn8GraphStopMode-first(1),
    	wtWebioAn8GraphStopMode-second(2),
    	wtWebioAn8GraphStopMode-third(3),
    	wtWebioAn8GraphStopMode-fourth(4),
    	wtWebioAn8GraphStopMode-last(5)
    	}
    ACCESS read-write
    STATUS mandatory
    DESCRIPTION
        "Mode of the week day on which the change is made from summer time to winter time."
    ::= { wtWebioAn8GraphTimeZone 13 }

wtWebioAn8GraphStTzStopWday OBJECT-TYPE
    SYNTAX INTEGER {
    	wtWebioAn8GraphStopWday-Sunday(1),
    	wtWebioAn8GraphStopWday-Monday(2),
    	wtWebioAn8GraphStopWday-Tuesday(3),
    	wtWebioAn8GraphStopWday-Thursday(4),
    	wtWebioAn8GraphStopWday-Wednesday(5),
    	wtWebioAn8GraphStopWday-Friday(6),
    	wtWebioAn8GraphStopWday-Saturday(7)
    	}
    ACCESS read-write
    STATUS mandatory
    DESCRIPTION
        "Day of the week on which the change is made from summer time to winter time."
    ::= { wtWebioAn8GraphTimeZone 14 }

wtWebioAn8GraphStTzStopHrs OBJECT-TYPE
    SYNTAX INTEGER
    ACCESS read-write
    STATUS mandatory
    DESCRIPTION
        "Hour at which the time zone is changed from summer to winter time with
        respect to UTC."
    ::= { wtWebioAn8GraphTimeZone 15 }

wtWebioAn8GraphStTzStopMin OBJECT-TYPE
    SYNTAX INTEGER
    ACCESS read-write
    STATUS mandatory
    DESCRIPTION
        "Minute at which the time zone is changed from summer to winter time with
        respect to UTC."
    ::= { wtWebioAn8GraphTimeZone 16 }

-- wtWebioAn8GraphTimeServer Group
----------------------------

wtWebioAn8GraphTimeServer1 OBJECT-TYPE
    SYNTAX OCTET STRING
    ACCESS read-write
    STATUS mandatory
    DESCRIPTION
        "IP address or name of the 1st time server in ASCII"
    ::= { wtWebioAn8GraphTimeServer 1 }

wtWebioAn8GraphTimeServer2 OBJECT-TYPE
    SYNTAX OCTET STRING
    ACCESS read-write
    STATUS mandatory
    DESCRIPTION
        "IP address or name of the 2nd time server in ASCII"
    ::= { wtWebioAn8GraphTimeServer 2 }

wtWebioAn8GraphTsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebioAn8GraphTimeServer 3 }

wtWebioAn8GraphTsSyncTime OBJECT-TYPE
    SYNTAX INTEGER
    ACCESS read-write
    STATUS mandatory
    DESCRIPTION
        "Daily synchronisation time with the time server (hour: 0-23)."
    ::= { wtWebioAn8GraphTimeServer 4 }

-- wtWebioAn8GraphDeviceClock Group
----------------------------

wtWebioAn8GraphClockHrs OBJECT-TYPE
    SYNTAX INTEGER (0..23)
    ACCESS read-write
    STATUS mandatory
    DESCRIPTION
        "Clock hours taking into account the time zone settings."
    ::= { wtWebioAn8GraphDeviceClock 1 }

wtWebioAn8GraphClockMin OBJECT-TYPE
    SYNTAX INTEGER (0..59)
    ACCESS read-write
    STATUS mandatory
    DESCRIPTION
        "Clock minutes taking into account the time zone settings."
    ::= { wtWebioAn8GraphDeviceClock 2 }

wtWebioAn8GraphClockDay OBJECT-TYPE
    SYNTAX INTEGER (1..31)
    ACCESS read-write
    STATUS mandatory
    DESCRIPTION
        "Date: Day of the month, taking into account the time zone settings."
    ::= { wtWebioAn8GraphDeviceClock 3 }

wtWebioAn8GraphClockMonth OBJECT-TYPE
   SYNTAX INTEGER {
    	wtWebioAn8GraphClockMonth-January(1),
    	wtWebioAn8GraphClockMonth-February(2),
    	wtWebioAn8GraphClockMonth-March(3),
    	wtWebioAn8GraphClockMonth-April(4),
    	wtWebioAn8GraphClockMonth-May(5),
    	wtWebioAn8GraphClockMonth-June(6),
    	wtWebioAn8GraphClockMonth-July(7),
    	wtWebioAn8GraphClockMonth-August(8),
    	wtWebioAn8GraphClockMonth-September(9),
    	wtWebioAn8GraphClockMonth-October(10),
    	wtWebioAn8GraphClockMonth-November(11),
    	wtWebioAn8GraphClockMonth-December(12)
    	}
    ACCESS read-write
    STATUS mandatory
    DESCRIPTION
        "Date: Month, taking into account the time zone settings."
    ::= { wtWebioAn8GraphDeviceClock 4 }

wtWebioAn8GraphClockYear OBJECT-TYPE
    SYNTAX INTEGER (0..65535)
    ACCESS read-write
    STATUS mandatory
    DESCRIPTION
        "Date: Year, taking into account the time zone settings."
    ::= { wtWebioAn8GraphDeviceClock 5 }


-- wtWebioAn8GraphNetwork Group
------------------------

wtWebioAn8GraphIpAddress OBJECT-TYPE
    SYNTAX IpAddress
    ACCESS read-write
    STATUS mandatory
    DESCRIPTION
        "IP address of the Webio"
    ::= { wtWebioAn8GraphNetwork 1 }

wtWebioAn8GraphSubnetMask OBJECT-TYPE
    SYNTAX IpAddress
    ACCESS read-write
    STATUS mandatory
    DESCRIPTION
        "Subnet mask of the Webio"
    ::= { wtWebioAn8GraphNetwork 2 }

wtWebioAn8GraphGateway OBJECT-TYPE
    SYNTAX IpAddress
    ACCESS read-write
    STATUS mandatory
    DESCRIPTION
        "Gateway of the Webio"
    ::= { wtWebioAn8GraphNetwork 3 }

wtWebioAn8GraphDnsServer1 OBJECT-TYPE
    SYNTAX OCTET STRING
    ACCESS read-write
    STATUS mandatory
    DESCRIPTION
        "IP address of the 1st DNS server in ASCII"
    ::= { wtWebioAn8GraphNetwork 4 }

wtWebioAn8GraphDnsServer2 OBJECT-TYPE
    SYNTAX OCTET STRING
    ACCESS read-write
    STATUS mandatory
    DESCRIPTION
        "IP address of the 2nd DNS server in ASCII"
    ::= { wtWebioAn8GraphNetwork 5 }

wtWebioAn8GraphAddConfig OBJECT-TYPE
    SYNTAX OCTET STRING
    ACCESS read-write
    STATUS mandatory
    DESCRIPTION
        "Additional configuration (1=ON):
        Octet 1: unused
        Octet 2: unused
        Octet 3: unused
        Octet 4:
	        Bit 0: BOOTP disable
	        Bit 1: DHCP disable
	        "
    ::= { wtWebioAn8GraphNetwork 6 }

--  wtWebioAn8GraphHTTP Group
--------------------------------

wtWebioAn8GraphStartup OBJECT-TYPE
    SYNTAX OCTET STRING
    ACCESS read-write
    STATUS mandatory
    DESCRIPTION
        "Binary coded start page:
        Octet 1: unused
        Octet 2: unused
        Octet 3: unused
        Octet 4:
	        Bit 1: Index.htm
	        Bit 2: Home.htm
	        Bit 3: User.htm
	Only one page may be selected at a time."
    ::= { wtWebioAn8GraphHTTP 1 }

wtWebioAn8GraphGetHeaderEnable OBJECT-TYPE
    SYNTAX OCTET STRING
    ACCESS read-write
    STATUS mandatory
    DESCRIPTION
        "If these bits are set, every answer of a short form GET question will be lead
        by the IP-address and name of the device and/or a HTTP header:
        Octet 1: unused
        Octet 2: unused
        Octet 3: unused
        Octet 4:
        	Bit 1-6: unused
        	Bit 1  : GET HTTP enable
                Bit 0  : GET Header enable"
    ::= { wtWebioAn8GraphHTTP 2 }

wtWebioAn8GraphHttpPort OBJECT-TYPE
    SYNTAX INTEGER (1..65535)
    ACCESS read-write
    STATUS mandatory
    DESCRIPTION
        "Definition of the standard HTML port (Default: 80)."
    ::= { wtWebioAn8GraphHTTP 3 }


-- wtWebioAn8GraphMail Group
--------------------------------

wtWebioAn8GraphMailAdName OBJECT-TYPE
    SYNTAX OCTET STRING
    ACCESS read-write
    STATUS mandatory
    DESCRIPTION
        "Device name for mail administration."
    ::= { wtWebioAn8GraphMail 1 }

wtWebioAn8GraphMailReply OBJECT-TYPE
    SYNTAX OCTET STRING
    ACCESS read-write
    STATUS mandatory
    DESCRIPTION
        "Reply address for the mail server."
    ::= { wtWebioAn8GraphMail 2 }

wtWebioAn8GraphMailServer OBJECT-TYPE
    SYNTAX OCTET STRING
    ACCESS read-write
    STATUS mandatory
    DESCRIPTION
        "Name or IP address of the mail server."
    ::= { wtWebioAn8GraphMail 3 }

wtWebioAn1MailEnable OBJECT-TYPE
    SYNTAX OCTET STRING
    ACCESS read-write
    STATUS mandatory
    DESCRIPTION
        "Set this bit to enable the sending of mails:
        Octet 1: unused
        Octet 2: unused
        Octet 3: unused
        Octet 4:
        	Bit 1-7: unused
                Bit 0  : Mail enable"
    ::= { wtWebioAn8GraphMail 4 }

wtWebioAn8GraphMailAuthentication OBJECT-TYPE
    SYNTAX OCTET STRING (SIZE (4))
    ACCESS read-write
    STATUS mandatory
    DESCRIPTION
        "Selection of the authentication modi:
        The OCTETS are interpreted bit-by-bit, with each bit corresponding to an output.
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebioAn8GraphMail 5 }

wtWebioAn8GraphMailAuthUser OBJECT-TYPE
    SYNTAX OCTET STRING
    ACCESS read-write
    STATUS mandatory
    DESCRIPTION
        "Name of the user to be authenticated."
    ::= { wtWebioAn8GraphMail 6 }

wtWebioAn8GraphMailAuthPassword OBJECT-TYPE
    SYNTAX OCTET STRING
    ACCESS read-write
    STATUS mandatory
    DESCRIPTION
        "Authentication password."
    ::= { wtWebioAn8GraphMail 7 }

wtWebioAn8GraphMailPop3Server OBJECT-TYPE
    SYNTAX OCTET STRING
    ACCESS read-write
    STATUS mandatory
    DESCRIPTION
        "Name or Ip-address of the POP3 Servers."
    ::= { wtWebioAn8GraphMail 8 }


-- wtWebioAn8GraphSNMP Group
--------------------------------

wtWebioAn8GraphSnmpCommunityStringRead OBJECT-TYPE
    SYNTAX OCTET STRING
    ACCESS read-write
    STATUS mandatory
    DESCRIPTION
        "Community string read only"
    ::= { wtWebioAn8GraphSNMP 1 }

wtWebioAn8GraphSnmpCommunityStringReadWrite OBJECT-TYPE
    SYNTAX OCTET STRING
    ACCESS read-write
    STATUS mandatory
    DESCRIPTION
        "Community string read / write"
    ::= { wtWebioAn8GraphSNMP 2 }

wtWebioAn8GraphSystemTrapManagerIP OBJECT-TYPE
    SYNTAX OCTET STRING
    ACCESS read-write
    STATUS mandatory
    DESCRIPTION
        "Name or IP address of the TCP server which accepts the system trap."
    ::= { wtWebioAn8GraphSNMP 3 }

wtWebioAn8GraphSystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2-7: unused"
    ::= { wtWebioAn8GraphSNMP 4 }

wtWebioAn8GraphSnmpEnable OBJECT-TYPE
    SYNTAX OCTET STRING
    ACCESS read-write
    STATUS mandatory
    DESCRIPTION
        "Set bit 0 to enable SNMP.
        If disabled, the device did not respond to any SNMP requests.
        Bit 1 decided wether the community string of read operations
        is compared with the system password or not:
        Octet 1: unused
        Octet 2: unused
        Octet 3: unused
        Octet 4:
        	Bit 1-7: unused
        	Bit 0  : SNMP enable"
    ::= { wtWebioAn8GraphSNMP 5 }

wtWebioAn8GraphSnmpCommunityStringTrap OBJECT-TYPE
    SYNTAX OCTET STRING
    ACCESS read-write
    STATUS mandatory
    DESCRIPTION
        "Community string send within traps."
    ::= { wtWebioAn8GraphSNMP 6 }

-- wtWebioAn8GraphUDP Group
--------------------------------

wtWebioAn8GraphUdpPort OBJECT-TYPE
    SYNTAX INTEGER (1..65535)
    ACCESS read-write
    STATUS mandatory
    DESCRIPTION
        "Udp port to which the Udp queries ( short form GET requests) can be sent. This
        port number must be unique within the device."
    ::= { wtWebioAn8GraphUDP 1 }

wtWebioAn8GraphUdpEnable OBJECT-TYPE
    SYNTAX OCTET STRING
    ACCESS read-write
    STATUS mandatory
    DESCRIPTION
        "Set this bit to enable UDP support:
        Octet 1: unused
        Octet 2: unused
        Octet 3: unused
        Octet 4:
        	Bit 1-7: unused
                Bit 0  : UDP enable"
    ::= { wtWebioAn8GraphUDP 2 }


--  wtWebioAn8GraphSyslog Group
--------------------------------

wtWebioAn8GraphSyslogServerIP OBJECT-TYPE
    SYNTAX OCTET STRING
    ACCESS read-write
    STATUS mandatory
    DESCRIPTION
        "Name or IP address of the Syslog server, which accepts the Syslog messgaes."
    ::= { wtWebioAn8GraphSyslog 1 }

wtWebioAn8GraphSyslogServerPort OBJECT-TYPE
    SYNTAX INTEGER
    ACCESS read-write
    STATUS mandatory
    DESCRIPTION
        "Portnumber of the Syslog servers, default 514."
    ::= { wtWebioAn8GraphSyslog 2 }

wtWebioAn8GraphSyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebioAn8GraphSyslog 3 }

wtWebioAn8GraphSyslogEnable OBJECT-TYPE
    SYNTAX OCTET STRING
    ACCESS read-write
    STATUS mandatory
    DESCRIPTION
        "Set bit 0 to enable Syslog:
        Octet 1: unused
        Octet 2: unused
        Octet 3: unused
        Octet 4:
        	Bit 1-7: unused
                Bit 0  : Syslog enable"
    ::= { wtWebioAn8GraphSyslog 4 }

--  wtWebioAn8GraphFTP Group
--------------------------------

wtWebioAn8GraphFTPServerIP OBJECT-TYPE
    SYNTAX OCTET STRING
    ACCESS read-write
    STATUS mandatory
    DESCRIPTION
        "Name or IP address of the FTP server, which accepts the FTP messages."
    ::= { wtWebioAn8GraphFTP 1 }

wtWebioAn8GraphFTPServerControlPort OBJECT-TYPE
    SYNTAX INTEGER
    ACCESS read-write
    STATUS mandatory
    DESCRIPTION
        "Portnumber of the control port of the FTP server, default 21."
    ::= { wtWebioAn8GraphFTP 2 }

wtWebioAn8GraphFTPUserName OBJECT-TYPE
    SYNTAX OCTET STRING
    ACCESS read-write
    STATUS mandatory
    DESCRIPTION
        "FTP Loggin: user name."
    ::= { wtWebioAn8GraphFTP 3 }

wtWebioAn8GraphFTPPassword OBJECT-TYPE
    SYNTAX OCTET STRING
    ACCESS read-write
    STATUS mandatory
    DESCRIPTION
        "FTP Loggin: user password."
    ::= { wtWebioAn8GraphFTP 4 }

wtWebioAn8GraphFTPAccount OBJECT-TYPE
    SYNTAX OCTET STRING
    ACCESS read-write
    STATUS mandatory
    DESCRIPTION
        "FTP Loggin: name of account."
    ::= { wtWebioAn8GraphFTP 5 }

wtWebioAn8GraphFTPOption OBJECT-TYPE
    SYNTAX OCTET STRING
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebioAn8GraphFTP 6 }

wtWebioAn8GraphFTPEnable OBJECT-TYPE
    SYNTAX OCTET STRING
    ACCESS read-write
    STATUS mandatory
    DESCRIPTION
        "Set Bit 0 to enable FTP:
        Octet 1: unused
        Octet 2: unused
        Octet 3: unused
        Octet 4:
        	Bit 1-7: unused
                Bit 0  : FTP enable"
    ::= { wtWebioAn8GraphFTP 7 }

-- wtWebioAn8GraphDatalogger Group
--------------------------------

wtWebioAn8GraphLoggerTimebase OBJECT-TYPE
    SYNTAX INTEGER {
    wtWebioAn8GraphDatalogger-1Min(1),
    wtWebioAn8GraphDatalogger-5Min(2),
    wtWebioAn8GraphDatalogger-15Min(3),
    wtWebioAn8GraphDatalogger-60Min(4)
    }
    ACCESS read-write
    STATUS mandatory
    DESCRIPTION
        "Time base of the data logger"
    ::= { wtWebioAn8GraphDatalogger 1 }

wtWebioAn8GraphLoggerSensorSel OBJECT-TYPE
    SYNTAX OCTET STRING (SIZE(4))
    ACCESS read-write
    STATUS mandatory
    DESCRIPTION
        "Binary coded trigger conditions:
        Octet 1: unused
        Octet 2: unused
        Octet 3: unused
        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
    ::= { wtWebioAn8GraphDatalogger 2 }

wtWebioAn8GraphDisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
    ::= { wtWebioAn8GraphDatalogger 3 }

-- Graph Sensor Color Table

wtWebioAn8GraphSensorColorTable OBJECT-TYPE
    SYNTAX SEQUENCE OF WtWebioAn8GraphSensorColorEntry
    ACCESS not-accessible
    STATUS mandatory
    DESCRIPTION
        "List of sensor colors for the praphical presentation."
    ::= { wtWebioAn8GraphDatalogger 4 }

wtWebioAn8GraphSensorColorEntry OBJECT-TYPE
    SYNTAX WtWebioAn8GraphSensorColorEntry
    ACCESS not-accessible
    STATUS mandatory
    DESCRIPTION
        "Index numbers of the sensors."
    INDEX  { wtWebioAn8GraphSensorNo }
    ::= { wtWebioAn8GraphSensorColorTable 1 }

WtWebioAn8GraphSensorColorEntry ::= SEQUENCE {
    wtWebioAn8GraphSensorColor OCTET STRING
}

wtWebioAn8GraphSensorColor OBJECT-TYPE
    SYNTAX OCTET STRING (SIZE(3))
    ACCESS read-write
    STATUS mandatory
    DESCRIPTION
        "Color of the sensors at the praphical presention."
    ::= { wtWebioAn8GraphSensorColorEntry 1 }

wtWebioAn8GraphAutoScaleEnable OBJECT-TYPE
    SYNTAX OCTET STRING
    ACCESS read-write
    STATUS mandatory
    DESCRIPTION
        "If bit 0 is set, vertical auto scale is enabled:
        Octet 1: unused
        Octet 2: unused
        Octet 3: unused
        Octet 4:
        	Bit 1-7: unused
                Bit 0  : Auto Scale enable"
    ::= { wtWebioAn8GraphDatalogger 5 }

wtWebioAn8GraphVerticalUpperLimit OBJECT-TYPE
    SYNTAX OCTET STRING
    ACCESS read-write
    STATUS mandatory
    DESCRIPTION
        "This value defines the maximum temperature shown in the graphical presentation,
        if no auto scaling is selected.
        Temperature in degrees with maximum 2 decimal places."
    ::= { wtWebioAn8GraphDatalogger 6 }

wtWebioAn8GraphVerticalLowerLimit OBJECT-TYPE
    SYNTAX OCTET STRING
    ACCESS read-write
    STATUS mandatory
    DESCRIPTION
        "This value defines the minimum temperature shown in the graphical presentation,
        if no auto scaling is selected.
        Temperature in degrees with maximum 2 decimal places."
    ::= { wtWebioAn8GraphDatalogger 7 }

wtWebioAn8GraphHorizontalZoom OBJECT-TYPE
    SYNTAX INTEGER {
    wtWebioAn8GraphZoom-25min(1),
    wtWebioAn8GraphZoom-75min(2),
    wtWebioAn8GraphZoom-5hrs(3),
    wtWebioAn8GraphZoom-30hrs(4),
    wtWebioAn8GraphZoom-5days(5),
    wtWebioAn8GraphZoom-25days(6)
    }
    ACCESS read-write
    STATUS mandatory
    DESCRIPTION
        "Defines the default zoom stage, if no auto scaling is selected."
    ::= { wtWebioAn8GraphDatalogger 8 }

-- wtWebioAn8GraphAlarm Group
----------------------------

wtWebioAn8GraphAlarmCount OBJECT-TYPE
    SYNTAX INTEGER (1..8)
    ACCESS read-only
    STATUS mandatory
    DESCRIPTION
        "Number of independent alarms."
    ::= { wtWebioAn8GraphAlarm 1 }

-- Alarm Interface Table

wtWebioAn8GraphAlarmIfTable OBJECT-TYPE
    SYNTAX SEQUENCE OF WtWebioAn8GraphAlarmIfEntry
    ACCESS not-accessible
    STATUS mandatory
    DESCRIPTION
        "List of alarm indices."
    ::= { wtWebioAn8GraphAlarm 2 }

wtWebioAn8GraphAlarmIfEntry OBJECT-TYPE
    SYNTAX WtWebioAn8GraphAlarmIfEntry
    ACCESS not-accessible
    STATUS mandatory
    DESCRIPTION
        "Numbers of the alarms."
    INDEX  { wtWebioAn8GraphAlarmNo }
    ::= { wtWebioAn8GraphAlarmIfTable 1 }

WtWebioAn8GraphAlarmIfEntry ::= SEQUENCE {
    wtWebioAn8GraphAlarmNo INTEGER
}

wtWebioAn8GraphAlarmNo OBJECT-TYPE
    SYNTAX INTEGER (1..8)
    ACCESS read-only
    STATUS mandatory
    DESCRIPTION
        "Alarm number."
    ::= { wtWebioAn8GraphAlarmIfEntry 1 }

-- Alarm Table

wtWebioAn8GraphAlarmTable OBJECT-TYPE
    SYNTAX SEQUENCE OF WtWebioAn8GraphAlarmEntry
    ACCESS not-accessible
    STATUS mandatory
    DESCRIPTION
        "List of settings depending on the alarm number."
    ::= { wtWebioAn8GraphAlarm 3 }

wtWebioAn8GraphAlarmEntry OBJECT-TYPE
    SYNTAX WtWebioAn8GraphAlarmEntry
    ACCESS not-accessible
    STATUS mandatory
    DESCRIPTION
        "Alarm parameters of the individual alarms."
    INDEX  { wtWebioAn8GraphAlarmNo }
    ::= { wtWebioAn8GraphAlarmTable 1 }

WtWebioAn8GraphAlarmEntry ::= SEQUENCE {
    wtWebioAn8GraphAlarmTrigger			OCTET STRING,
    wtWebioAn8GraphAlarmMin			OCTET STRING,
    wtWebioAn8GraphAlarmMax			OCTET STRING,
    wtWebioAn8GraphAlarmHysteresis		OCTET STRING,
    wtWebioAn8GraphAlarmDelay			OCTET STRING,
    wtWebioAn8GraphAlarmInterval		OCTET STRING,
    wtWebioAn8GraphAlarmEnable			OCTET STRING,
    wtWebioAn8GraphAlarmEMailAddr		OCTET STRING,
    wtWebioAn8GraphAlarmMailSubject		OCTET STRING,
    wtWebioAn8GraphAlarmMailText		OCTET STRING,
    wtWebioAn8GraphAlarmManagerIP		OCTET STRING,
    wtWebioAn8GraphAlarmTrapText		OCTET STRING,
    wtWebioAn8GraphAlarmMailOptions		OCTET STRING,
    wtWebioAn8GraphAlarmTcpIpAddr		OCTET STRING,
    wtWebioAn8GraphAlarmTcpPort			INTEGER,
    wtWebioAn8GraphAlarmTcpText			OCTET STRING,
    wtWebioAn8GraphAlarmClearMailSubject	OCTET STRING,
    wtWebioAn8GraphAlarmClearMailText		OCTET STRING,
    wtWebioAn8GraphAlarmClearTrapText		OCTET STRING,
    wtWebioAn8GraphAlarmClearTcpText		OCTET STRING,
    wtWebioAn8GraphAlarmSyslogIpAddr		OCTET STRING,
    wtWebioAn8GraphAlarmSyslogPort		INTEGER,
    wtWebioAn8GraphAlarmSyslogText		OCTET STRING,
    wtWebioAn8GraphAlarmFtpDataPort		OCTET STRING,
    wtWebioAn8GraphAlarmFtpFileName		OCTET STRING,
    wtWebioAn8GraphAlarmFtpText			OCTET STRING,
    wtWebioAn8GraphAlarmFtpClearText		OCTET STRING,
    wtWebioAn8GraphAlarmFtpOption		OCTET STRING,
    wtWebioAn8GraphAlarmTimerCron		OCTET STRING

}

wtWebioAn8GraphAlarmTrigger OBJECT-TYPE
    SYNTAX OCTET STRING (SIZE(4))
    ACCESS read-write
    STATUS mandatory
    DESCRIPTION
        "Binary coded trigger conditions:
        Octet 1: unused
        Octet 2: unused
        Octet 3:
        	Bit 0: Timer
        	Bit 1: ColdStart
        	Bit 2: WarmStart

        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
    ::= { wtWebioAn8GraphAlarmEntry 1 }

wtWebioAn8GraphAlarmMin OBJECT-TYPE
    SYNTAX OCTET STRING
    ACCESS read-write
    STATUS mandatory
    DESCRIPTION
        "Minimum temperature in degrees with maximum 2 decimal places."
    ::= { wtWebioAn8GraphAlarmEntry 2 }

wtWebioAn8GraphAlarmMax OBJECT-TYPE
    SYNTAX OCTET STRING
    ACCESS read-write
    STATUS mandatory
    DESCRIPTION
        "Maximum temperature in degrees with maximum 2 decimal places."
    ::= { wtWebioAn8GraphAlarmEntry 3 }

wtWebioAn8GraphAlarmHysteresis OBJECT-TYPE
    SYNTAX OCTET STRING
    ACCESS read-write
    STATUS mandatory
    DESCRIPTION
        "Temperature changes of this size clears the alarm state (MAX-hyst, MIN+hyst.)
        , in degrees with maximum 2 decimal places."
    ::= { wtWebioAn8GraphAlarmEntry 4 }

wtWebioAn8GraphAlarmDelay OBJECT-TYPE
    SYNTAX OCTET STRING
    ACCESS read-write
    STATUS mandatory
    DESCRIPTION
        "Alarm will be delayed by setting this time while stable alarm
        condition occur (time in minutes)."
    ::= { wtWebioAn8GraphAlarmEntry 5 }


wtWebioAn8GraphAlarmInterval OBJECT-TYPE
    SYNTAX OCTET STRING
    ACCESS read-write
    STATUS mandatory
    DESCRIPTION
        "Send interval for alarm messages."
    ::= { wtWebioAn8GraphAlarmEntry 6 }

wtWebioAn8GraphAlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  TCP Client enable"
    ::= { wtWebioAn8GraphAlarmEntry 7 }

wtWebioAn8GraphAlarmEMailAddr OBJECT-TYPE
    SYNTAX OCTET STRING
    ACCESS read-write
    STATUS mandatory
    DESCRIPTION
        "E-Mail address for sending the alarm mail to."
    ::= { wtWebioAn8GraphAlarmEntry 8 }

wtWebioAn8GraphAlarmMailSubject OBJECT-TYPE
    SYNTAX OCTET STRING
    ACCESS read-write
    STATUS mandatory
    DESCRIPTION
        "Subject line for alarm mail."
    ::= { wtWebioAn8GraphAlarmEntry 9 }

wtWebioAn8GraphAlarmMailText OBJECT-TYPE
    SYNTAX OCTET STRING
    ACCESS read-write
    STATUS mandatory
    DESCRIPTION
        "Alarm mail text: <Tn> provides the current temperature; n = 1..8.
        <Z> provides the current time."
    ::= { wtWebioAn8GraphAlarmEntry 10 }

wtWebioAn8GraphAlarmManagerIP OBJECT-TYPE
    SYNTAX OCTET STRING
    ACCESS read-write
    STATUS mandatory
    DESCRIPTION
        "Name or IP address of the SNMP Manager which accepts the trap."
    ::= { wtWebioAn8GraphAlarmEntry 11 }

wtWebioAn8GraphAlarmTrapText OBJECT-TYPE
    SYNTAX OCTET STRING
    ACCESS read-write
    STATUS mandatory
    DESCRIPTION
        "This text is sent in the trap body."
    ::= { wtWebioAn8GraphAlarmEntry 12 }

wtWebioAn8GraphAlarmMailOptions OBJECT-TYPE
    SYNTAX OCTET STRING (SIZE(4))
    ACCESS read-write
    STATUS mandatory
    DESCRIPTION
        "Binary coded options:
        Octet 1: unused
        Octet 2: unused
        Octet 3: unused
        Octet 4:
		Bit 0  :	Attach Thermo.csv Enable
		Bit 1  :	CSV-Data_since_last_report
        	Bit 2-7:	unused"
    ::= { wtWebioAn8GraphAlarmEntry 13 }

wtWebioAn8GraphAlarmTcpIpAddr OBJECT-TYPE
    SYNTAX OCTET STRING
    ACCESS read-write
    STATUS mandatory
    DESCRIPTION
        "Name or IP address of the TCP server which accepts the trap."
    ::= { wtWebioAn8GraphAlarmEntry 14 }

wtWebioAn8GraphAlarmTcpPort OBJECT-TYPE
    SYNTAX INTEGER (1..65535)
    ACCESS read-write
    STATUS mandatory
    DESCRIPTION
        "Port number of the TCP server which accepts the trap."
    ::= { wtWebioAn8GraphAlarmEntry 15 }

wtWebioAn8GraphAlarmTcpText OBJECT-TYPE
    SYNTAX OCTET STRING
    ACCESS read-write
    STATUS mandatory
    DESCRIPTION
        "This text is sent in the TCP trap body."
    ::= { wtWebioAn8GraphAlarmEntry 16 }

wtWebioAn8GraphAlarmClearMailSubject OBJECT-TYPE
    SYNTAX OCTET STRING
    ACCESS read-write
    STATUS mandatory
    DESCRIPTION
        "Subject line for alarm clear mail."
    ::= { wtWebioAn8GraphAlarmEntry 17 }

wtWebioAn8GraphAlarmClearMailText OBJECT-TYPE
    SYNTAX OCTET STRING
    ACCESS read-write
    STATUS mandatory
    DESCRIPTION
        "Alarm clear mail text: <Tn> provides the current temperature; n = 1..8.
        <Z> provides the current time."
    ::= { wtWebioAn8GraphAlarmEntry 18 }

wtWebioAn8GraphAlarmClearTrapText OBJECT-TYPE
    SYNTAX OCTET STRING
    ACCESS read-write
    STATUS mandatory
    DESCRIPTION
        "This text is sent in the trap body."
    ::= { wtWebioAn8GraphAlarmEntry 19 }

wtWebioAn8GraphAlarmClearTcpText OBJECT-TYPE
    SYNTAX OCTET STRING
    ACCESS read-write
    STATUS mandatory
    DESCRIPTION
        "This text is sent in the TCP trap body."
    ::= { wtWebioAn8GraphAlarmEntry 20 }

wtWebioAn8GraphAlarmSyslogIpAddr OBJECT-TYPE
    SYNTAX IpAddress
    ACCESS read-write
    STATUS mandatory
    DESCRIPTION
        "IP address of the syslog server to which the Webio device should send syslog messages."
    ::= { wtWebioAn8GraphAlarmEntry 21 }

wtWebioAn8GraphAlarmSyslogPort OBJECT-TYPE
    SYNTAX INTEGER (1..65535)
    ACCESS read-write
    STATUS mandatory
    DESCRIPTION
        "Port number of the syslog server to which the Webio device should send syslog messages."
    ::= { wtWebioAn8GraphAlarmEntry 22 }

wtWebioAn8GraphAlarmSyslogText OBJECT-TYPE
    SYNTAX OCTET STRING
    ACCESS read-write
    STATUS mandatory
    DESCRIPTION
        "Every message starts with the priority key, a time stamp and the host ip address, according RFC3164.
        This text appears in the following syslog message body."
    ::= { wtWebioAn8GraphAlarmEntry 23 }

wtWebioAn8GraphAlarmSyslogClearText OBJECT-TYPE
    SYNTAX OCTET STRING
    ACCESS read-write
    STATUS mandatory
    DESCRIPTION
        "Every message starts with the priority key, a time stamp and the host ip address, according RFC3164.
        This text appears in the following syslog message body."
    ::= { wtWebioAn8GraphAlarmEntry 24 }

wtWebioAn8GraphAlarmFtpDataPort OBJECT-TYPE
    SYNTAX OCTET STRING
    ACCESS read-write
    STATUS mandatory
    DESCRIPTION
        "Local data port: 1..65535 or AUTO: the next free port will be assigned."
    ::= { wtWebioAn8GraphAlarmEntry 25 }

wtWebioAn8GraphAlarmFtpFileName OBJECT-TYPE
    SYNTAX OCTET STRING
    ACCESS read-write
    STATUS mandatory
    DESCRIPTION
        "Name of the file including path informations."
    ::= { wtWebioAn8GraphAlarmEntry 26 }

wtWebioAn8GraphAlarmFtpText OBJECT-TYPE
    SYNTAX OCTET STRING
    ACCESS read-write
    STATUS mandatory
    DESCRIPTION
        "Message text to store on the FTP server."
    ::= { wtWebioAn8GraphAlarmEntry 27 }

wtWebioAn8GraphAlarmFtpClearText OBJECT-TYPE
    SYNTAX OCTET STRING
    ACCESS read-write
    STATUS mandatory
    DESCRIPTION
        "Alarm clear message to store on the FTP server."
    ::= { wtWebioAn8GraphAlarmEntry 28 }

wtWebioAn8GraphAlarmFtpOptions OBJECT-TYPE
    SYNTAX OCTET STRING (SIZE(4))
    ACCESS read-write
    STATUS mandatory
    DESCRIPTION
        "Binary coded options, select only one option at the same time:
        STORE  = replace file
        APPEND = append message at the end of the file

        Octet 1: unused
        Octet 2: unused
        Octet 3: unused
        Octet 4:
		Bit 0  :	STORE
		Bit 1  :	APPEND
        	Bit 2-7:	unused"
    ::= { wtWebioAn8GraphAlarmEntry 29 }

wtWebioAn8GraphAlarmTimerCron OBJECT-TYPE
    SYNTAX OCTET STRING
    ACCESS read-write
    STATUS mandatory
    DESCRIPTION
        "This entry contains 5 text fields space or tab seperated for time trigger definition.
        Each field must match with the actual time to trigger a message, weekday and day of month
        are interpreted separatley.
        1: Minutes	Range 0-59
        2. Hours	Range 0-23, 0 is midnight
        3: Day of month	Range 1-31
        4: Month	Range 1-12
        5: Weekday	Range 0-6, 0 is sunday

        Syntax for every field:
         - an asterix (*) enables every possible setting of a field
         - single numbers seperated by commas
         - a partition within the allowed range (1-5)
         - step size within an partition of the allowed range (0-59/2: every second minute)."
    ::= { wtWebioAn8GraphAlarmEntry 30 }

-- wtWebioAn8GraphGraphicsBase Group
----------------------------

wtWebioAn8GraphGraphicsBaseEnable OBJECT-TYPE
    SYNTAX OCTET STRING
    ACCESS read-write
    STATUS mandatory
    DESCRIPTION
        "Defines the viewing options of the graphic:
        Octet 1: unused
        Octet 2: unused
        Octet 3: unused
        Octet 4:
                Bit 0  : Auto scroll enable
                Bit 1  : Show table
                Bit 2  : Show graph
                Bit 3  : Show control buttons
                Bit 4  : Show config menu
                Bit 5-7: unused"
    ::= { wtWebioAn8GraphGraphicsBase 1 }

wtWebioAn8GraphGraphicsBaseWidth OBJECT-TYPE
    SYNTAX INTEGER
    ACCESS read-write
    STATUS mandatory
    DESCRIPTION
        "Defines the width of the graphic in pixels."
    ::= { wtWebioAn8GraphGraphicsBase 2 }

wtWebioAn8GraphGraphicsBaseHeight OBJECT-TYPE
        SYNTAX INTEGER
        ACCESS read-write
        STATUS mandatory
        DESCRIPTION
            "Defines the height of the graphic in pixels."
        ::= { wtWebioAn8GraphGraphicsBase 3 }

wtWebioAn8GraphGraphicsBaseFrameColor OBJECT-TYPE
    SYNTAX OCTET STRING (SIZE(3))
    ACCESS read-write
    STATUS mandatory
    DESCRIPTION
        "Frame color definition in RGB."
    ::= { wtWebioAn8GraphGraphicsBase 4 }

wtWebioAn8GraphGraphicsBaseBackgroundColor OBJECT-TYPE
    SYNTAX OCTET STRING (SIZE(3))
    ACCESS read-write
    STATUS mandatory
    DESCRIPTION
        "Background color definition in RGB."
    ::= { wtWebioAn8GraphGraphicsBase 5 }

wtWebioAn8GraphGraphicsBasePollingrate OBJECT-TYPE
        SYNTAX INTEGER
        ACCESS read-write
        STATUS mandatory
        DESCRIPTION
            "Defines the pollingrate in seconds,
            which defines the refreshing intervall of the graphic."
        ::= { wtWebioAn8GraphGraphicsBase 6 }

-- wtWebioAn8GraphGraphicsSelect Group
----------------------------

wtWebioAn8GraphGraphicsSelectDisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
    ::= { wtWebioAn8GraphGraphicsSelect 1 }

wtWebioAn8GraphGraphicsSelectDisplayShowExtrem OBJECT-TYPE
    SYNTAX OCTET STRING (SIZE(4))
    ACCESS read-write
    STATUS mandatory
    DESCRIPTION
        "Binary coded sensor selection:
        only selected sensors will be shown with minima and maxima:
        Octet 1: unused
        Octet 2: unused
        Octet 3: unused
        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
     ::= { wtWebioAn8GraphGraphicsSelect 2 }

-- Graph Sensor Color Table

wtWebioAn8GraphSensorColorTable OBJECT-TYPE
    SYNTAX SEQUENCE OF WtWebioAn8GraphSensorColorEntry
    ACCESS not-accessible
    STATUS mandatory
    DESCRIPTION
        "List of sensor colors for the praphical presentation."
    ::= { wtWebioAn8GraphGraphicsSelect 3 }

wtWebioAn8GraphSensorColorEntry OBJECT-TYPE
    SYNTAX WtWebioAn8GraphSensorColorEntry
    ACCESS not-accessible
    STATUS mandatory
    DESCRIPTION
        "Numbers of the sensors."
    INDEX  { wtWebioAn8GraphSensorNo }
    ::= { wtWebioAn8GraphSensorColorTable 1 }

WtWebioAn8GraphSensorColorEntry ::= SEQUENCE {
    wtWebioAn8GraphGraphicsSensorColor OCTET STRING,
    wtWebioAn8GraphGraphicsSelectScale OCTET STRING
}

wtWebioAn8GraphGraphicsSensorColor OBJECT-TYPE
    SYNTAX OCTET STRING (SIZE(3))
    ACCESS read-write
    STATUS mandatory
    DESCRIPTION
        "Color of the sensors at the praphical presention."
    ::= { wtWebioAn8GraphSensorColorEntry 1 }

wtWebioAn8GraphGraphicsSelectScale OBJECT-TYPE
    SYNTAX OCTET STRING
    ACCESS read-write
    STATUS mandatory
    DESCRIPTION
        "Assignes one of 4 scales to a sensor:
        Octet 1: unused
        Octet 2: unused
        Octet 3: unused
        Octet 4:
                Bit 0  : Use Scale 1
                Bit 1  : Use Scale 2
                Bit 2  : Use Scale 3
                Bit 3  : Use Scale 4
                Bit 4-7: unused"
    ::= { wtWebioAn8GraphSensorColorEntry 2 }

-- wtWebioAn8GraphGraphicsScale Group
----------------------------

wtWebioAn8GraphGraphicsScaleAutoScaleEnable OBJECT-TYPE
    SYNTAX OCTET STRING
    ACCESS read-write
    STATUS mandatory
    DESCRIPTION
        "Select the Auto Scale Mode:
        Octet 1: unused
        Octet 2: unused
        Octet 3: unused
        Octet 4:
                Bit 0  : Scale 1 Auto scale enable
                Bit 1  : Scale 2 Auto scale enable
                Bit 2  : Scale 3 Auto scale enable
                Bit 3  : Scale 4 Auto scale enable
                Bit 4-7: unused"
    ::= { wtWebioAn8GraphGraphicsScale 1 }


wtWebioAn8GraphGraphicsScaleAutoFitEnable OBJECT-TYPE
    SYNTAX OCTET STRING
    ACCESS read-write
    STATUS mandatory
    DESCRIPTION
        "Select the Auto Fit Mode::
        Octet 1: unused
        Octet 2: unused
        Octet 3: unused
        Octet 4:
                Bit 0  : Scale 1 Auto fit enable
                Bit 1  : Scale 2 Auto fit enable
                Bit 2  : Scale 3 Auto fit enable
                Bit 3  : Scale 4 Auto fit enable
                Bit 4-7: unused"
    ::= { wtWebioAn8GraphGraphicsScale 2 }

wtWebioAn8GraphGraphicsScale1Min OBJECT-TYPE
    SYNTAX INTEGER
    ACCESS read-only
    STATUS mandatory
    DESCRIPTION
        "Scale 1: Minimum."
    ::= { wtWebioAn8GraphGraphicsScale 3 }

wtWebioAn8GraphGraphicsScale2Min OBJECT-TYPE
    SYNTAX INTEGER
    ACCESS read-only
    STATUS mandatory
    DESCRIPTION
        "Scale 2: Minimum."
    ::= { wtWebioAn8GraphGraphicsScale 4 }

wtWebioAn8GraphGraphicsScale3Min OBJECT-TYPE
    SYNTAX INTEGER
    ACCESS read-only
    STATUS mandatory
    DESCRIPTION
        "Scale 3: Minimum."
    ::= { wtWebioAn8GraphGraphicsScale 5 }

wtWebioAn8GraphGraphicsScale4Min OBJECT-TYPE
    SYNTAX INTEGER
    ACCESS read-only
    STATUS mandatory
    DESCRIPTION
        "Scale 4: Minimum."
    ::= { wtWebioAn8GraphGraphicsScale 6 }

wtWebioAn8GraphGraphicsScale1Max OBJECT-TYPE
    SYNTAX INTEGER
    ACCESS read-only
    STATUS mandatory
    DESCRIPTION
        "Scale 1: Maximum."
    ::= { wtWebioAn8GraphGraphicsScale 7 }

wtWebioAn8GraphGraphicsScale2Max OBJECT-TYPE
    SYNTAX INTEGER
    ACCESS read-only
    STATUS mandatory
    DESCRIPTION
        "Scale 2: Maximum."
    ::= { wtWebioAn8GraphGraphicsScale 8 }

wtWebioAn8GraphGraphicsScale3Max OBJECT-TYPE
    SYNTAX INTEGER
    ACCESS read-only
    STATUS mandatory
    DESCRIPTION
        "Scale 3: Maximum."
    ::= { wtWebioAn8GraphGraphicsScale 9 }

wtWebioAn8GraphGraphicsScale4Max OBJECT-TYPE
    SYNTAX INTEGER
    ACCESS read-only
    STATUS mandatory
    DESCRIPTION
        "Scale 4: Maximum."
    ::= { wtWebioAn8GraphGraphicsScale 10 }

wtWebioAn8GraphGraphicsScale1Unit OBJECT-TYPE
    SYNTAX OCTET STRING
    ACCESS read-only
    STATUS mandatory
    DESCRIPTION
        "Scale 1: Unit."
    ::= { wtWebioAn8GraphGraphicsScale 11 }

wtWebioAn8GraphGraphicsScale2Unit OBJECT-TYPE
    SYNTAX OCTET STRING
    ACCESS read-only
    STATUS mandatory
    DESCRIPTION
        "Scale 2: Unit."
    ::= { wtWebioAn8GraphGraphicsScale 12 }

wtWebioAn8GraphGraphicsScale3Unit OBJECT-TYPE
    SYNTAX OCTET STRING
    ACCESS read-only
    STATUS mandatory
    DESCRIPTION
        "Scale 3: Unit."
    ::= { wtWebioAn8GraphGraphicsScale 13 }

wtWebioAn8GraphGraphicsScale4Unit OBJECT-TYPE
    SYNTAX OCTET STRING
    ACCESS read-only
    STATUS mandatory
    DESCRIPTION
        "Scale 4: Unit."
    ::= { wtWebioAn8GraphGraphicsScale 14 }

-- wtWebioAn8GraphPorts Group
----------------------------

-- Table

wtWebioAn8GraphPortTable OBJECT-TYPE
    SYNTAX SEQUENCE OF WtWebioAn8GraphPortEntry
    ACCESS not-accessible
    STATUS mandatory
    DESCRIPTION
        "List of settings depending on the sensor number."
    ::= { wtWebioAn8GraphPorts 1 }

wtWebioAn8GraphPortEntry OBJECT-TYPE
    SYNTAX WtWebioAn8GraphPortEntry
    ACCESS not-accessible
    STATUS mandatory
    DESCRIPTION
        "Sensor parameters for the individual sensors."
    INDEX  { wtWebioAn8GraphSensorNo }
    ::= { wtWebioAn8GraphPortTable 1 }

WtWebioAn8GraphPortEntry ::= SEQUENCE {
    wtWebioAn8GraphPortName		OCTET STRING,
    wtWebioAn8GraphPortText		OCTET STRING,
    wtWebioAn8GraphPortOffset1		OCTET STRING,
    wtWebioAn8GraphPortTemperature1	OCTET STRING,
    wtWebioAn8GraphPortOffset2		OCTET STRING,
    wtWebioAn8GraphPortTemperature2	OCTET STRING,
    wtWebioAn8GraphPortComment		OCTET STRING,
    wtWebioAn8GraphPortSensorSelect	OCTET STRING


}

wtWebioAn8GraphPortName OBJECT-TYPE
    SYNTAX OCTET STRING
    ACCESS read-write
    STATUS mandatory
    DESCRIPTION
        "Name of the sensor."
    ::= { wtWebioAn8GraphPortEntry 1 }

wtWebioAn8GraphPortText OBJECT-TYPE
    SYNTAX OCTET STRING
    ACCESS read-write
    STATUS mandatory
    DESCRIPTION
        "Description of the sensor."
    ::= { wtWebioAn8GraphPortEntry 2 }

wtWebioAn8GraphPortOffset1 OBJECT-TYPE
    SYNTAX OCTET STRING
    ACCESS read-write
    STATUS mandatory
    DESCRIPTION
        "Offset calibration: Offset in degrees with maximum 2 decimal places at temperature 1."
    ::= { wtWebioAn8GraphPortEntry 3 }

wtWebioAn8GraphPortTemperature1 OBJECT-TYPE
    SYNTAX OCTET STRING
    ACCESS read-write
    STATUS mandatory
    DESCRIPTION
        "Offset calibration: Reference temperature 1 in degrees with maximum 2 decimal places."
    ::= { wtWebioAn8GraphPortEntry 4 }

wtWebioAn8GraphPortOffset2 OBJECT-TYPE
    SYNTAX OCTET STRING
    ACCESS read-write
    STATUS mandatory
    DESCRIPTION
        "Offset calibration: Offset in degrees with maximum 2 decimal places at temperature 2."
    ::= { wtWebioAn8GraphPortEntry 5 }

wtWebioAn8GraphPortTemperature2 OBJECT-TYPE
    SYNTAX OCTET STRING
    ACCESS read-write
    STATUS mandatory
    DESCRIPTION
        "Offset calibration: Reference temperature 1 in degrees with maximum 2 decimal places."
    ::= { wtWebioAn8GraphPortEntry 6 }

wtWebioAn8GraphPortComment OBJECT-TYPE
    SYNTAX OCTET STRING
    ACCESS read-write
    STATUS mandatory
    DESCRIPTION
        "Offset calibration: informations of date, name of operator, reference devices."
    ::= { wtWebioAn8GraphPortEntry 7 }

wtWebioAn8GraphPortSensorSelect OBJECT-TYPE
    SYNTAX OCTET STRING (SIZE(4))
    ACCESS read-write
    STATUS mandatory
    DESCRIPTION
        "Binär kodierte Optionen f?r Sensor:
        Octet 1: ungenutzt
        Octet 2: ungenutzt
        Octet 3: ungenutzt
        Octet 4:
		Bit 0  :	PT100
		Bit 1  :	PT1000 (default)
        	Bit 2-7:	ungenutzt"
    ::= { wtWebioAn8GraphPortEntry 8 }

-- wtWebioAn8GraphManufact Group
----------------------------

wtWebioAn8GraphMfName OBJECT-TYPE
    SYNTAX OCTET STRING
    ACCESS read-write
    STATUS mandatory
    DESCRIPTION
        "Manufacturer company name"
    ::= { wtWebioAn8GraphManufact 1 }

wtWebioAn8GraphMfAddr OBJECT-TYPE
    SYNTAX OCTET STRING
    ACCESS read-write
    STATUS mandatory
    DESCRIPTION
        "Manufacturer address."
    ::= { wtWebioAn8GraphManufact 2 }

wtWebioAn8GraphMfHotline OBJECT-TYPE
    SYNTAX OCTET STRING
    ACCESS read-write
    STATUS mandatory
    DESCRIPTION
        "Manufacturer hotline."
    ::= { wtWebioAn8GraphManufact 3 }

wtWebioAn8GraphMfInternet OBJECT-TYPE
    SYNTAX OCTET STRING
    ACCESS read-write
    STATUS mandatory
    DESCRIPTION
        "Manufacturer Internet address."
    ::= { wtWebioAn8GraphManufact 4 }

wtWebioAn8GraphMfDeviceTyp OBJECT-TYPE
    SYNTAX OCTET STRING
    ACCESS read-write
    STATUS mandatory
    DESCRIPTION
        "Manufacturer device name (model number)."
    ::= { wtWebioAn8GraphManufact 5 }

wtWebioAn8GraphMfOrderNo OBJECT-TYPE
    SYNTAX OCTET STRING
    ACCESS read-write
    STATUS mandatory
    DESCRIPTION
        "Manufacturer part number."
    ::= { wtWebioAn8GraphManufact 6 }

-- wtWebioAn8GraphDiag Group
----------------------------

wtWebioAn8GraphDiagErrorCount OBJECT-TYPE
    SYNTAX INTEGER
    ACCESS read-only
    STATUS mandatory
    DESCRIPTION
        "Number of entries in the error memory."
    ::= { wtWebioAn8GraphDiag 1 }

wtWebioAn8GraphDiagBinaryError OBJECT-TYPE
    SYNTAX OCTET STRING
    ACCESS read-only
    STATUS mandatory
    DESCRIPTION
        "Error causes coded bit-by-bit."
    ::= { wtWebioAn8GraphDiag 2 }

wtWebioAn8GraphDiagErrorIndex OBJECT-TYPE
    SYNTAX INTEGER
    ACCESS read-write
    STATUS mandatory
    DESCRIPTION
        "The value of this variable is used as an index to read
        an error massege from wtWebioAn8GraphDiagErrorMessage.
        Errors are numbered from 1 to wtWebioAn8GraphDiagErrorCount.
        Writing a valid value into this variable, making the appropriate
        message readable from wtWebioAn8GraphDiagErrorMessage."
    ::= { wtWebioAn8GraphDiag 3 }

wtWebioAn8GraphDiagErrorMessage OBJECT-TYPE
    SYNTAX OCTET STRING
    ACCESS read-only
    STATUS mandatory
    DESCRIPTION
        "Using wtWebioAn8GraphDiagErrorIndex as an index, the appropriate message is available."
    ::= { wtWebioAn8GraphDiag 4 }

wtWebioAn8GraphDiagErrorClear OBJECT-TYPE
    SYNTAX INTEGER
    ACCESS write-only
    STATUS mandatory
    DESCRIPTION
        "Writing 1 into this variable clears all diagnosis messages."
    ::= { wtWebioAn8GraphDiag 5 }

-- TRAP DEFINITIONS

-- Diese SNMP-Traps werden gesendet, wenn die Alarmtriggerbedingungen zutreffen

wtWebioAn8GraphAlert1 TRAP-TYPE
    ENTERPRISE  wtWebioAn8Graph
    VARIABLES   { wtWebioAn8GraphAlarmTrapText }
    DESCRIPTION
        "This SNMP trap is generated when Alarm 1 was triggered,
        SNMP trap enable is set and
        SNMP is enabled."
    -- NMS trap annotation
    --#TYPE "Web-Thermograph Alarm 1"
    --#SUMMARY "Alarm 1: %s"
    --#ARGUMENTS {0}
    --#SEVERITY INFORMATIONAL
    --#TIMEINDEX 99
    --#STATE OPERATIONAL
    ::= 11

wtWebioAn8GraphAlert2 TRAP-TYPE
    ENTERPRISE  wtWebioAn8Graph
    VARIABLES   { wtWebioAn8GraphAlarmTrapText }
    DESCRIPTION
        "This SNMP trap is generated when Alarm 2 was triggered,
        SNMP trap enable is set and
        SNMP is enabled."
    -- NMS trap annotation
    --#TYPE "Web-Thermograph Alarm 2"
    --#SUMMARY "Alarm 2: %s"
    --#ARGUMENTS {0}
    --#SEVERITY INFORMATIONAL
    --#TIMEINDEX 99
    --#STATE OPERATIONAL
    ::= 12

wtWebioAn8GraphAlert3 TRAP-TYPE
    ENTERPRISE  wtWebioAn8Graph
    VARIABLES   { wtWebioAn8GraphAlarmTrapText }
    DESCRIPTION
        "This SNMP trap is generated when Alarm 3 was triggered,
        SNMP trap enable is set and
        SNMP is enabled."
    -- NMS trap annotation
    --#TYPE "Web-Thermograph Alarm 3"
    --#SUMMARY "Alarm 3: %s"
    --#ARGUMENTS {0}
    --#SEVERITY INFORMATIONAL
    --#TIMEINDEX 99
    --#STATE OPERATIONAL
    ::= 13

wtWebioAn8GraphAlert4 TRAP-TYPE
    ENTERPRISE  wtWebioAn8Graph
    VARIABLES   { wtWebioAn8GraphAlarmTrapText }
    DESCRIPTION
        "This SNMP trap is generated when Alarm 4 was triggered,
        SNMP trap enable is set and
        SNMP is enabled."
    -- NMS trap annotation
    --#TYPE "Web-Thermograph Alarm 4"
    --#SUMMARY "Alarm 4: %s"
    --#ARGUMENTS {0}
    --#SEVERITY INFORMATIONAL
    --#TIMEINDEX 99
    --#STATE OPERATIONAL
    ::= 14

wtWebioAn8GraphAlert5 TRAP-TYPE
    ENTERPRISE  wtWebioAn8Graph
    VARIABLES   { wtWebioAn8GraphAlarmTrapText }
    DESCRIPTION
        "This SNMP trap is generated when Alarm 5 was triggered,
        SNMP trap enable is set and
        SNMP is enabled."
    -- NMS trap annotation
    --#TYPE "Web-Thermograph Alarm 5"
    --#SUMMARY "Alarm 5: %s"
    --#ARGUMENTS {0}
    --#SEVERITY INFORMATIONAL
    --#TIMEINDEX 99
    --#STATE OPERATIONAL
    ::= 15

wtWebioAn8GraphAlert6 TRAP-TYPE
    ENTERPRISE  wtWebioAn8Graph
    VARIABLES   { wtWebioAn8GraphAlarmTrapText }
    DESCRIPTION
        "This SNMP trap is generated when Alarm 6 was triggered,
        SNMP trap enable is set and
        SNMP is enabled."
    -- NMS trap annotation
    --#TYPE "Web-Thermograph Alarm 6"
    --#SUMMARY "Alarm 6: %s"
    --#ARGUMENTS {0}
    --#SEVERITY INFORMATIONAL
    --#TIMEINDEX 99
    --#STATE OPERATIONAL
    ::= 16

wtWebioAn8GraphAlert7 TRAP-TYPE
    ENTERPRISE  wtWebioAn8Graph
    VARIABLES   { wtWebioAn8GraphAlarmTrapText }
    DESCRIPTION
        "This SNMP trap is generated when Alarm 7 was triggered,
        SNMP trap enable is set and
        SNMP is enabled."
    -- NMS trap annotation
    --#TYPE "Web-Thermograph Alarm 7"
    --#SUMMARY "Alarm 7: %s"
    --#ARGUMENTS {0}
    --#SEVERITY INFORMATIONAL
    --#TIMEINDEX 99
    --#STATE OPERATIONAL
    ::= 17

wtWebioAn8GraphAlert8 TRAP-TYPE
    ENTERPRISE  wtWebioAn8Graph
    VARIABLES   { wtWebioAn8GraphAlarmTrapText }
    DESCRIPTION
        "This SNMP trap is generated when Alarm 8 was triggered,
        SNMP trap enable is set and
        SNMP is enabled."
    -- NMS trap annotation
    --#TYPE "Web-Thermograph Alarm 8"
    --#SUMMARY "Alarm 8: %s"
    --#ARGUMENTS {0}
    --#SEVERITY INFORMATIONAL
    --#TIMEINDEX 99
    --#STATE OPERATIONAL
    ::= 18


wtWebioAn8GraphAlert9 TRAP-TYPE
    ENTERPRISE  wtWebioAn8Graph
    VARIABLES   { wtWebioAn8GraphAlarmClearTrapText }
    DESCRIPTION
        "This SNMP trap is generated when Alarm 1 was cleared,
        SNMP trap enable is set and
        SNMP is enabled."
    -- NMS trap annotation
    --#TYPE "Web-Thermograph Release Alarm 1"
    --#SUMMARY "Release Alarm 1: %s"
    --#ARGUMENTS {0}
    --#SEVERITY INFORMATIONAL
    --#TIMEINDEX 99
    --#STATE OPERATIONAL
    ::= 71

wtWebioAn8GraphAlert10 TRAP-TYPE
    ENTERPRISE  wtWebioAn8Graph
    VARIABLES   { wtWebioAn8GraphAlarmClearTrapText }
    DESCRIPTION
        "This SNMP trap is generated when Alarm 2 was cleared,
        SNMP trap enable is set and
        SNMP is enabled."
    -- NMS trap annotation
    --#TYPE "Web-Thermograph Release Alarm 2"
    --#SUMMARY "Release Alarm 2: %s"
    --#ARGUMENTS {0}
    --#SEVERITY INFORMATIONAL
    --#TIMEINDEX 99
    --#STATE OPERATIONAL
    ::= 72

wtWebioAn8GraphAlert11 TRAP-TYPE
    ENTERPRISE  wtWebioAn8Graph
    VARIABLES   { wtWebioAn8GraphAlarmClearTrapText }
    DESCRIPTION
        "This SNMP trap is generated when Alarm 3 was cleared,
        SNMP trap enable is set and
        SNMP is enabled."
    -- NMS trap annotation
    --#TYPE "Web-Thermograph Release Alarm 3"
    --#SUMMARY "Release Alarm 3: %s"
    --#ARGUMENTS {0}
    --#SEVERITY INFORMATIONAL
    --#TIMEINDEX 99
    --#STATE OPERATIONAL
    ::= 73

wtWebioAn8GraphAlert12 TRAP-TYPE
    ENTERPRISE  wtWebioAn8Graph
    VARIABLES   { wtWebioAn8GraphAlarmClearTrapText }
    DESCRIPTION
        "This SNMP trap is generated when Alarm 4 was cleared,
        SNMP trap enable is set and
        SNMP is enabled."
    -- NMS trap annotation
    --#TYPE "Web-Thermograph Release Alarm 4"
    --#SUMMARY "Release Alarm 4: %s"
    --#ARGUMENTS {0}
    --#SEVERITY INFORMATIONAL
    --#TIMEINDEX 99
    --#STATE OPERATIONAL
    ::= 74

wtWebioAn8GraphAlert13 TRAP-TYPE
    ENTERPRISE  wtWebioAn8Graph
    VARIABLES   { wtWebioAn8GraphAlarmClearTrapText }
    DESCRIPTION
        "This SNMP trap is generated when Alarm 5 was cleared,
        SNMP trap enable is set and
        SNMP is enabled."
    -- NMS trap annotation
    --#TYPE "Web-Thermograph Release Alarm 5"
    --#SUMMARY "Release Alarm 5: %s"
    --#ARGUMENTS {0}
    --#SEVERITY INFORMATIONAL
    --#TIMEINDEX 99
    --#STATE OPERATIONAL
    ::= 75

wtWebioAn8GraphAlert14 TRAP-TYPE
    ENTERPRISE  wtWebioAn8Graph
    VARIABLES   { wtWebioAn8GraphAlarmClearTrapText }
    DESCRIPTION
        "This SNMP trap is generated when Alarm 6 was cleared,
        SNMP trap enable is set and
        SNMP is enabled."
    -- NMS trap annotation
    --#TYPE "Web-Thermograph Release Alarm 6"
    --#SUMMARY "Release Alarm 6: %s"
    --#ARGUMENTS {0}
    --#SEVERITY INFORMATIONAL
    --#TIMEINDEX 99
    --#STATE OPERATIONAL
    ::= 76

wtWebioAn8GraphAlert15 TRAP-TYPE
    ENTERPRISE  wtWebioAn8Graph
    VARIABLES   { wtWebioAn8GraphAlarmClearTrapText }
    DESCRIPTION
        "This SNMP trap is generated when Alarm 7 was cleared,
        SNMP trap enable is set and
        SNMP is enabled."
    -- NMS trap annotation
    --#TYPE "Web-Thermograph Release Alarm 7"
    --#SUMMARY "Release Alarm 7: %s"
    --#ARGUMENTS {0}
    --#SEVERITY INFORMATIONAL
    --#TIMEINDEX 99
    --#STATE OPERATIONAL
    ::= 77

wtWebioAn8GraphAlert16 TRAP-TYPE
    ENTERPRISE  wtWebioAn8Graph
    VARIABLES   { wtWebioAn8GraphAlarmClearTrapText }
    DESCRIPTION
        "This SNMP trap is generated when Alarm 8 was cleared,
        SNMP trap enable is set and
        SNMP is enabled."
    -- NMS trap annotation
    --#TYPE "Web-Thermograph Release Alarm 8"
    --#SUMMARY "Release Alarm 8: %s"
    --#ARGUMENTS {0}
    --#SEVERITY INFORMATIONAL
    --#TIMEINDEX 99
    --#STATE OPERATIONAL
    ::= 78

wtWebioAn8GraphAlertDiag TRAP-TYPE
    ENTERPRISE  wtWebioAn8Graph
    VARIABLES   {
    		wtWebioAn8GraphDiagErrorIndex,
    	  	wtWebioAn8GraphDiagErrorMessage
    		}
    DESCRIPTION
        "This SNMP trap is generated when a diagnosis/error message was triggered,
        SNMP trap enable is set and
        SNMP is enabled."
    -- NMS trap annotation
    --#TYPE "Web-Thermograph Diagnose Error"
    --#SUMMARY "Diagnose error index: %d, Message: %s."
    --#ARGUMENTS {0,1}
    --#SEVERITY MAJOR
    --#TIMEINDEX 99
    --#STATE DEGRADED
    ::= 110

END
