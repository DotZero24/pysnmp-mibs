WebGraph-AnalogIO-57762-US-MIB DEFINITIONS ::= BEGIN
----------------------------------------------------------------
-- Revison: 1.31
----------------------------------------------------------------
-- 27.03.2018 	New: Mail Auth, SNMP destination port
--		     Binary HttpPort, time base report
--		     MQTT, REST
----------------------------------------------------------------
-- Revison: 1.30
----------------------------------------------------------------
-- 08.01.2010 	New: Reports
--
----------------------------------------------------------------
-- Revison: 1.29
----------------------------------------------------------------
-- 01.10.2009 	Webio
--		New Analog Out: 57762
----------------------------------------------------------------
-- Revison: 1.28
----------------------------------------------------------------
-- 02.12.2008 	Webio
--		New Graphics java script base parameter
----------------------------------------------------------------
-- Revison: 1.27
----------------------------------------------------------------
-- 09.11.2006 	Webio
--		DHCP enable
----------------------------------------------------------------
-- Revison: 1.26
----------------------------------------------------------------
-- 28.06.2006 	New: Community String Trap
--
----------------------------------------------------------------
-- Revison: 1.25
----------------------------------------------------------------
-- 25.11.2005 	#57641, WebGraph AnalogIn
--		OID correction
----------------------------------------------------------------
-- Revison: 1.24
----------------------------------------------------------------
-- 26.07.2005 	#57641, WebGraph AnalogIn
--		CRON timer function
----------------------------------------------------------------
-- Revison: 1.23
----------------------------------------------------------------
-- 14.07.2005 	#57641, WebGraph AnalogIn
--		FTP functions
----------------------------------------------------------------
-- Revison: 1.22
----------------------------------------------------------------
-- 17.05.2005 	#57641, WebGraph AnalogIn
--		Trap NMS annotations
----------------------------------------------------------------
-- Revison: 1.21
----------------------------------------------------------------
-- 19.04.2005 	#57605, WebGraph Themometer
--		Mail Authentication
----------------------------------------------------------------
-- Revison: 1.20
----------------------------------------------------------------
-- 05.11.2004 	#57606, WebGraph Thermo-Hygrometer
--		New: Syslog
--
----------------------------------------------------------------
-- Revison: 1.19
----------------------------------------------------------------
-- 08.09.2004 	#57606 WebGraph Thermo-Hygrometer
--		New:
--			wtWebGraphThermHygroAlarmRHMin
--			wtWebGraphThermHygroAlarmRHMax
--			wtWebGraphThermHygroAlarmRHHysteresis
--			wtWebGraphThermHygroPortSensorSelect
--			wtWebGraphThermHygroAlarmDeltaTemp
--			wtWebGraphThermHygroAlarmAHMin
--			wtWebGraphThermHygroAlarmAHMax
----------------------------------------------------------------
-- Revison: 1.18
----------------------------------------------------------------
-- 21.07.2004 	#57601/3/4, Webio Anx
--		New:
--		     Diagnosis
----------------------------------------------------------------
-- Revison: 1.17
----------------------------------------------------------------
-- 28.06.2004 	#57630/1/2, Webio Digital
--		Neu: Puls Mode
----------------------------------------------------------------
-- Revison: 1.16
----------------------------------------------------------------
-- 16.04.2004 	New: #57632, Webio Digital EA24x24
--
--		#57630/1, Webio Digital EA12x12
--		New:
--			wtWebioEA12x12InputCounterClear
----------------------------------------------------------------
-- Revison: 1.15
----------------------------------------------------------------
-- 27.02.2004 	#57630/1, Webio Digital EA12x12
--		New:
--		Length changed to 32 Bit:
--			wtWebioEA12x12InputValue
--			wtWebioEA12x12OutputValue
--			wtWebioEA12x12LoadControlView
--			wtWebioEA12x12LCShutDownView
--			wtWebioEA12x12SetOutput
--			wtWebioEA12x12AlarmInputTrigger
--			wtWebioEA12x12AlarmOutputTrigger
--			wtWebioEA12x12PortOutputSafetyState
----------------------------------------------------------------
-- Revison: 1.14
----------------------------------------------------------------
-- 16.02.2004 	#57630/1, Webio Digital EA12x12
--		New:
--		Text: Location, Contact
--		SNMP: ColdStart, WarmStart, ComunityString Read/RW
--		Alarm: ColdStart / WarmStart trigger
--
-- 	 	#57601, 1xWebThermometer
--		#57603, 2xWebThermometer
--		#57604, 8xWebThermometer
--		New:
--		Alarm Hysteresis
--		Alarm Clear Traps and Mails
----------------------------------------------------------------
-- Revison: 1.13
----------------------------------------------------------------
-- 05.02.2004 	#57601, 1xWebThermometer
--		#57603, 2xWebThermometer
--		#57604, 8xWebThermometer
--		New:
--		Text: Location, Contact
--		SNMP: ColdStart, WarmStart, ComunityString Read/RW
--		Alarm: ColdStart / WarmStart trigger
----------------------------------------------------------------
-- Revison: 1.12
----------------------------------------------------------------
-- 05.11.2003 	#57601, 1xWebThermometer
--		#57603, 2xWebThermometer
--		#57604, 8xWebThermometer
--		New features:
--		Mail  : Option CSV attachment
--		Port  : Offset calibration
--		Alarm : TCP Client mode
----------------------------------------------------------------
-- Revison: 1.11
----------------------------------------------------------------
-- 28.10.2003 	#57630/1, Webio Digital EA12x12
--		New features:
--		Alarm : TCP Client mode
--		Inputs: Puls filter
----------------------------------------------------------------
-- Revison: 1.10
----------------------------------------------------------------
-- 22.07.2003 	#57630, Webio Digital EA12x12
--		New navigation tree, new binary modes
--
----------------------------------------------------------------
-- Revison: 1.09
----------------------------------------------------------------
-- 24.03.2003 	Trap Enterprise (Type 1, 2) corrected
----------------------------------------------------------------
-- Revison: 1.08
----------------------------------------------------------------
-- 04.03.2003 	reconciled the language versions DE/US
----------------------------------------------------------------
-- Revison: 1.07
----------------------------------------------------------------
-- 25.02.2003 	Correction: wtWebioEA12x12LoadControl
----------------------------------------------------------------
-- Revison: 1.06
----------------------------------------------------------------
-- 24.02.2003 	New:
--		#57630, Webio EA12x12, LoadControl Group
--		Correction: Trap variable names
----------------------------------------------------------------
-- Revison: 1.05
----------------------------------------------------------------
-- 21.01.2003 	New:
--		#57630, Webio EA12x12
----------------------------------------------------------------
-- Revison: 1.04
----------------------------------------------------------------
-- 02.01.2003 	New:
--		#57601, 1xWebThermometer
--		#57603, 2xWebThermometer, 8 alarms
----------------------------------------------------------------
-- Revison: 1.03
----------------------------------------------------------------
-- 21.11.2002 	New:
--		#57604, 2xWebThermometer, BOOTP, StartupSite
--		#57603, 8xWebThermometer, BOOTP, StartupSite
----------------------------------------------------------------
-- Revison: 1.02
----------------------------------------------------------------
-- 26.07.2002 	New:
--		#57604, 2xWebThermometer
--		#57603, 8xWebThermometer
--


    IMPORTS

    OBJECT-TYPE                                        FROM RFC-1212
    TRAP-TYPE                                          FROM RFC-1215
    DisplayString, PhysAddress                         FROM RFC1213-MIB
    enterprises, TimeTicks, IpAddress, NetworkAddress  FROM RFC1155-SMI;


--    IpAddress ::=
--        [APPLICATION 0]
--            IMPLICIT OCTET STRING (SIZE (4))
--    Counter ::=
--        [APPLICATION 1]
--            IMPLICIT INTEGER (0..4294967295)
--    Gauge ::=
--        [APPLICATION 2]
--            IMPLICIT INTEGER (0..4294967295)
--    TimeTicks ::=
--        [APPLICATION 3]
--            IMPLICIT INTEGER (0..4294967295)


--    DisplayString ::= OCTET STRING
--    PhysAddress   ::= OCTET STRING

--    internet         OBJECT IDENTIFIER ::= { iso org(3) dod(6) 1 }
--    privat           OBJECT IDENTIFIER ::= { internet 4 }
--    enterprises      OBJECT IDENTIFIER ::= { privat 1 }



--  Wiesemann & Theis Com-Server MIB

    wut                				OBJECT IDENTIFIER ::= { enterprises 5040 }
    wtComServer        				OBJECT IDENTIFIER ::= { wut 1 }
    wtWebio            				OBJECT IDENTIFIER ::= { wtComServer 2 }

--  wtWebGraph Tree

    wtWebGraphAnalog57762  			OBJECT IDENTIFIER ::= { wtWebio 29 }

--  wtWebGraphAnalog57762 Tree

    wtWebGraphAnalog57762Inventory   		OBJECT IDENTIFIER ::= { wtWebGraphAnalog57762 1 }
    wtWebGraphAnalog57762SessCntrl 		OBJECT IDENTIFIER ::= { wtWebGraphAnalog57762 2 }
    wtWebGraphAnalog57762Config    		OBJECT IDENTIFIER ::= { wtWebGraphAnalog57762 3 }
    wtWebGraphAnalog57762Diag    		OBJECT IDENTIFIER ::= { wtWebGraphAnalog57762 4 }

--  wtWebGraphAnalog57762Config Tree

    wtWebGraphAnalog57762Device    		OBJECT IDENTIFIER ::= { wtWebGraphAnalog57762Config 1 }
    wtWebGraphAnalog57762Ports     		OBJECT IDENTIFIER ::= { wtWebGraphAnalog57762Config 2 }
    wtWebGraphAnalog57762Manufact  		OBJECT IDENTIFIER ::= { wtWebGraphAnalog57762Config 3 }

--  wtWebGraphAnalog57762Device Tree

    wtWebGraphAnalog57762Text			OBJECT IDENTIFIER ::= { wtWebGraphAnalog57762Device 1 }
    wtWebGraphAnalog57762TimeDate 		OBJECT IDENTIFIER ::= { wtWebGraphAnalog57762Device 2 }
    wtWebGraphAnalog57762Basic			OBJECT IDENTIFIER ::= { wtWebGraphAnalog57762Device 3 }
    wtWebGraphAnalog57762Datalogger		OBJECT IDENTIFIER ::= { wtWebGraphAnalog57762Device 4 }
    wtWebGraphAnalog57762Alarm			OBJECT IDENTIFIER ::= { wtWebGraphAnalog57762Device 5 }
    wtWebGraphAnalog57762Graphics 		OBJECT IDENTIFIER ::= { wtWebGraphAnalog57762Device 6 }

--  wtWebGraphAnalog57762TimeDate Tree

    wtWebGraphAnalog57762TimeZone		OBJECT IDENTIFIER ::= { wtWebGraphAnalog57762TimeDate 1 }
    wtWebGraphAnalog57762TimeServer		OBJECT IDENTIFIER ::= { wtWebGraphAnalog57762TimeDate 2 }
    wtWebGraphAnalog57762DeviceClock		OBJECT IDENTIFIER ::= { wtWebGraphAnalog57762TimeDate 3 }

--  wtWebGraphAnalog57762Basic Tree

    wtWebGraphAnalog57762Network		OBJECT IDENTIFIER ::= { wtWebGraphAnalog57762Basic 1 }
    wtWebGraphAnalog57762HTTP			OBJECT IDENTIFIER ::= { wtWebGraphAnalog57762Basic 2 }
    wtWebGraphAnalog57762Mail			OBJECT IDENTIFIER ::= { wtWebGraphAnalog57762Basic 3 }
    wtWebGraphAnalog57762SNMP			OBJECT IDENTIFIER ::= { wtWebGraphAnalog57762Basic 4 }
    wtWebGraphAnalog57762UDP			OBJECT IDENTIFIER ::= { wtWebGraphAnalog57762Basic 5 }
    wtWebGraphAnalog57762Syslog			OBJECT IDENTIFIER ::= { wtWebGraphAnalog57762Basic 6 }
    wtWebGraphAnalog57762FTP			OBJECT IDENTIFIER ::= { wtWebGraphAnalog57762Basic 7 }
    wtWebGraphAnalog57762Language		OBJECT IDENTIFIER ::= { wtWebGraphAnalog57762Basic 8 }
    wtWebGraphAnalog57762Binary			OBJECT IDENTIFIER ::= { wtWebGraphAnalog57762Basic 9 }
    wtWebGraphAnalog57762MQTT			OBJECT IDENTIFIER ::= { wtWebGraphAnalog57762Basic 12 }
    wtWebGraphAnalog57762REST			OBJECT IDENTIFIER ::= { wtWebGraphAnalog57762Basic 13 }

--  wtWebGraphAnalog57762Graphics Tree

    wtWebGraphAnalog57762GraphicsBase 		OBJECT IDENTIFIER ::= { wtWebGraphAnalog57762Graphics 1 }
    wtWebGraphAnalog57762GraphicsSelect 	OBJECT IDENTIFIER ::= { wtWebGraphAnalog57762Graphics 2 }
    wtWebGraphAnalog57762GraphicsScale 		OBJECT IDENTIFIER ::= { wtWebGraphAnalog57762Graphics 3 }

-- wtWebGraphAnalog57762Inventory Group
------------------------

wtWebGraphAnalog57762Sensors OBJECT-TYPE
    SYNTAX INTEGER (1..2)
    ACCESS read-only
    STATUS mandatory
    DESCRIPTION
        "Number of sensors"
    ::= { wtWebGraphAnalog57762Inventory 1 }

-- Interface Table

wtWebGraphAnalog57762SensorTable OBJECT-TYPE
    SYNTAX SEQUENCE OF WtWebGraphAnalog57762SensorEntry
    ACCESS not-accessible
    STATUS mandatory
    DESCRIPTION
        "List of sensors."
    ::= { wtWebGraphAnalog57762Inventory 2 }

wtWebGraphAnalog57762SensorEntry OBJECT-TYPE
    SYNTAX WtWebGraphAnalog57762SensorEntry
    ACCESS not-accessible
    STATUS mandatory
    DESCRIPTION
        "List of sensor numbers."
    INDEX  { wtWebGraphAnalog57762SensorNo }
    ::= { wtWebGraphAnalog57762SensorTable 1 }

WtWebGraphAnalog57762SensorEntry ::= SEQUENCE {
    wtWebGraphAnalog57762SensorNo INTEGER
}

wtWebGraphAnalog57762SensorNo OBJECT-TYPE
    SYNTAX INTEGER (1..2)
    ACCESS read-only
    STATUS mandatory
    DESCRIPTION
        "Sensor number."
    ::= { wtWebGraphAnalog57762SensorEntry 1 }

    -- wtWebGraphAnalog57762Values Table

wtWebGraphAnalog57762ValuesTable OBJECT-TYPE
    SYNTAX SEQUENCE OF WtWebGraphAnalog57762ValuesEntry
    ACCESS not-accessible
    STATUS mandatory
    DESCRIPTION
        "List of measurement values corresponding to the channel numbers."
    ::= { wtWebGraphAnalog57762Inventory 3 }

wtWebGraphAnalog57762ValuesEntry OBJECT-TYPE
    SYNTAX WtWebGraphAnalog57762ValuesEntry
    ACCESS not-accessible
    STATUS mandatory
    DESCRIPTION
        "Measurement values of the sensors."
    INDEX  { wtWebGraphAnalog57762SensorNo }
    ::= { wtWebGraphAnalog57762ValuesTable 1 }

WtWebGraphAnalog57762ValuesEntry ::= SEQUENCE{
    wtWebGraphAnalog57762Values OCTET STRING
}

wtWebGraphAnalog57762Values OBJECT-TYPE
    SYNTAX OCTET STRING (SIZE (5))
    ACCESS read-write
    STATUS mandatory
    DESCRIPTION
        "Measurement value of the sensor, ASCII.
        This value will be translated according to the ports settings
        for the read and write operations."
    ::= { wtWebGraphAnalog57762ValuesEntry 1 }


-- wtWebGraphAnalog57762BinaryValues Table

wtWebGraphAnalog57762BinaryValuesTable OBJECT-TYPE
    SYNTAX SEQUENCE OF WtWebGraphAnalog57762BinaryValuesEntry
    ACCESS not-accessible
    STATUS mandatory
    DESCRIPTION
        "List of binary measurement values corresponding to the channel numbers."
    ::= { wtWebGraphAnalog57762Inventory 4 }

wtWebGraphAnalog57762BinaryValuesEntry OBJECT-TYPE
    SYNTAX WtWebGraphAnalog57762BinaryValuesEntry
    ACCESS not-accessible
    STATUS mandatory
    DESCRIPTION
        "Binary measurement values of the sensors."
    INDEX  { wtWebGraphAnalog57762SensorNo }
    ::= { wtWebGraphAnalog57762BinaryValuesTable 1 }

WtWebGraphAnalog57762BinaryValuesEntry ::= SEQUENCE{
    wtWebGraphAnalog57762BinaryValues INTEGER
}

wtWebGraphAnalog57762BinaryValues OBJECT-TYPE
    SYNTAX INTEGER
    ACCESS read-write
    STATUS mandatory
    DESCRIPTION
        "Binary measurement value of the sensor in 1/1000,
        signed number, 0x7FFFFFFF indicates an invalid value.
        This value will be translated according to the ports settings
        for the read and write operations."
    ::= { wtWebGraphAnalog57762BinaryValuesEntry 1 }

-- wtWebGraphAnalog57762ValuesPoint Table

wtWebGraphAnalog57762ValuesPointTable OBJECT-TYPE
    SYNTAX SEQUENCE OF WtWebGraphAnalog57762ValuesPointEntry
    ACCESS not-accessible
    STATUS mandatory
    DESCRIPTION
        "List of measurement values corresponding to the channel numbers."
    ::= { wtWebGraphAnalog57762Inventory 8 }

wtWebGraphAnalog57762ValuesPointEntry OBJECT-TYPE
    SYNTAX WtWebGraphAnalog57762ValuesPointEntry
    ACCESS not-accessible
    STATUS mandatory
    DESCRIPTION
        "Measurement values of the sensors."
    INDEX  { wtWebGraphAnalog57762SensorNo }
    ::= { wtWebGraphAnalog57762ValuesPointTable 1 }

WtWebGraphAnalog57762ValuesPointEntry ::= SEQUENCE{
    wtWebGraphAnalog57762ValuesPoint OCTET STRING
}

wtWebGraphAnalog57762ValuesPoint OBJECT-TYPE
    SYNTAX OCTET STRING (SIZE (5))
    ACCESS read-write
    STATUS mandatory
    DESCRIPTION
        "Measurement value of the sensor, ASCII.
        This value will be translated according to the ports settings
        for the read and write operations."
    ::= { wtWebGraphAnalog57762ValuesPointEntry 1 }


-- wtWebGraphAnalog57762SessCntrl Group
--------------------------------

wtWebGraphAnalog57762SessCntrlPassword OBJECT-TYPE
    SYNTAX OCTET STRING
    ACCESS read-write
    STATUS mandatory
    DESCRIPTION
        "Entering this password opens a session which is ended by writing a 1 to
        wtWebGraphAnalog57762SessCntrlLogout. When read this variable provides a string of
        length zero."
    ::= { wtWebGraphAnalog57762SessCntrl 1 }

wtWebGraphAnalog57762SessCntrlConfigMode OBJECT-TYPE
    SYNTAX INTEGER {
    wtWebGraphAnalog57762SessCntrl-NoSession(0),
    wtWebGraphAnalog57762SessCntrl-Session(1)
    }
    ACCESS read-only
    STATUS mandatory
    DESCRIPTION
        "When the device is in SNMP configuration mode, the value 1 is
        returned, otherwise 0. If the read value is 0 even though the
        password was written, the device is already in config mode and the
        variables can only be read."
    ::= { wtWebGraphAnalog57762SessCntrl 2 }

wtWebGraphAnalog57762SessCntrlLogout OBJECT-TYPE
    SYNTAX INTEGER
    ACCESS read-write
    STATUS mandatory
    DESCRIPTION
        "If the device is in configuration mode and the session was opened by
        this SNMP Manager, writing a 1 to this variable will end the session
        and all parameters are stored.
        Writing a 2 discards all entries again.
        When read this variable provides the value 0."
    ::= { wtWebGraphAnalog57762SessCntrl 3 }

wtWebGraphAnalog57762SessCntrlAdminPassword OBJECT-TYPE
    SYNTAX OCTET STRING
    ACCESS read-write
    STATUS mandatory
    DESCRIPTION
        "This password protects access to the variables with administrator rights.
        It can only be changed by the administrator. If no password was assigned,
        the valid password is public."
    ::= { wtWebGraphAnalog57762SessCntrl 4 }

wtWebGraphAnalog57762SessCntrlConfigPassword OBJECT-TYPE
    SYNTAX OCTET STRING
    ACCESS read-write
    STATUS mandatory
    DESCRIPTION
        "This password protects access to the variables with configurator rights. It can
        be changed by the administrator and by the configurator. If no password was assigned,
        the valid password is public. When read this variable provides a null-pointer."
    ::= { wtWebGraphAnalog57762SessCntrl 5 }


-- wtWebGraphAnalog57762Text Group
------------------------

wtWebGraphAnalog57762DeviceName OBJECT-TYPE
    SYNTAX OCTET STRING
    ACCESS read-write
    STATUS mandatory
    DESCRIPTION
        "Name of the Webio, which is user definable."
    ::= { wtWebGraphAnalog57762Text 1 }

wtWebGraphAnalog57762DeviceText OBJECT-TYPE
    SYNTAX OCTET STRING
    ACCESS read-write
    STATUS mandatory
    DESCRIPTION
        "Description of the Webio, which is user definable."
    ::= { wtWebGraphAnalog57762Text 2 }

wtWebGraphAnalog57762DeviceLocation OBJECT-TYPE
    SYNTAX OCTET STRING
    ACCESS read-write
    STATUS mandatory
    DESCRIPTION
        "Description of the location of the Webio, which is user definable."
    ::= { wtWebGraphAnalog57762Text 3 }

wtWebGraphAnalog57762DeviceContact OBJECT-TYPE
    SYNTAX OCTET STRING
    ACCESS read-write
    STATUS mandatory
    DESCRIPTION
        "Contact address of the system operator of the Webio, which is user definable."
    ::= { wtWebGraphAnalog57762Text 4 }

-- wtWebGraphAnalog57762TimeZone Group
----------------------------

wtWebGraphAnalog57762TzOffsetHrs OBJECT-TYPE
    SYNTAX INTEGER
    ACCESS read-write
    STATUS mandatory
    DESCRIPTION
        "Offset hours for the time zone (winter time) with respect to UTC."
    ::= { wtWebGraphAnalog57762TimeZone 1 }

wtWebGraphAnalog57762TzOffsetMin OBJECT-TYPE
    SYNTAX INTEGER
    ACCESS read-write
    STATUS mandatory
    DESCRIPTION
        "Offset minutes for the time zone (winter time) with respect to UTC."
    ::= { wtWebGraphAnalog57762TimeZone 2 }

wtWebGraphAnalog57762TzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebGraphAnalog57762TimeZone 3 }

wtWebGraphAnalog57762StTzOffsetHrs OBJECT-TYPE
    SYNTAX INTEGER
    ACCESS read-write
    STATUS mandatory
    DESCRIPTION
        "Offset hours of the time zone (summer time) with respect to UTC."
    ::= { wtWebGraphAnalog57762TimeZone 4 }

wtWebGraphAnalog57762StTzOffsetMin OBJECT-TYPE
    SYNTAX INTEGER
    ACCESS read-write
    STATUS mandatory
    DESCRIPTION
        "Offset minutes of the time zone (summer time) with respect to UTC."
    ::= { wtWebGraphAnalog57762TimeZone 5 }

wtWebGraphAnalog57762StTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebGraphAnalog57762TimeZone 6 }

wtWebGraphAnalog57762StTzStartMonth OBJECT-TYPE
    SYNTAX INTEGER {
    	wtWebGraphAnalog57762StartMonth-January(1),
    	wtWebGraphAnalog57762StartMonth-February(2),
    	wtWebGraphAnalog57762StartMonth-March(3),
    	wtWebGraphAnalog57762StartMonth-April(4),
    	wtWebGraphAnalog57762StartMonth-May(5),
    	wtWebGraphAnalog57762StartMonth-June(6),
    	wtWebGraphAnalog57762StartMonth-July(7),
    	wtWebGraphAnalog57762StartMonth-August(8),
    	wtWebGraphAnalog57762StartMonth-September(9),
    	wtWebGraphAnalog57762StartMonth-October(10),
    	wtWebGraphAnalog57762StartMonth-November(11),
    	wtWebGraphAnalog57762StartMonth-December(12)
    	}

    ACCESS read-write
    STATUS mandatory
    DESCRIPTION
        "Month in which the change is made from winter time to summer time."
    ::= { wtWebGraphAnalog57762TimeZone 7 }

wtWebGraphAnalog57762StTzStartMode OBJECT-TYPE
    SYNTAX INTEGER {
    	wtWebGraphAnalog57762StartMode-first(1),
    	wtWebGraphAnalog57762StartMode-second(2),
    	wtWebGraphAnalog57762StartMode-third(3),
    	wtWebGraphAnalog57762StartMode-fourth(4),
    	wtWebGraphAnalog57762StartMode-last(5)
    	}

    ACCESS read-write
    STATUS mandatory
    DESCRIPTION
        "Mode of the day of the week for which the change is made from winter time to summer time."
    ::= { wtWebGraphAnalog57762TimeZone 8 }

wtWebGraphAnalog57762StTzStartWday OBJECT-TYPE
    SYNTAX INTEGER {
    	wtWebGraphAnalog57762StartWday-Sunday(1),
    	wtWebGraphAnalog57762StartWday-Monday(2),
    	wtWebGraphAnalog57762StartWday-Tuesday(3),
    	wtWebGraphAnalog57762StartWday-Thursday(4),
    	wtWebGraphAnalog57762StartWday-Wednesday(5),
    	wtWebGraphAnalog57762StartWday-Friday(6),
    	wtWebGraphAnalog57762StartWday-Saturday(7)
    	}

    ACCESS read-write
    STATUS mandatory
    DESCRIPTION
        "Day of the week on which the change is made from winter time to summer time"
    ::= { wtWebGraphAnalog57762TimeZone 9 }

wtWebGraphAnalog57762StTzStartHrs OBJECT-TYPE
    SYNTAX INTEGER
    ACCESS read-write
    STATUS mandatory
    DESCRIPTION
        "Hour in which the time zone is changed from winter to summer time with
        respect to UTC."
    ::= { wtWebGraphAnalog57762TimeZone 10 }

wtWebGraphAnalog57762StTzStartMin OBJECT-TYPE
    SYNTAX INTEGER
    ACCESS read-write
    STATUS mandatory
    DESCRIPTION
        "Minute in which the time zone is changed from winter to summer time with
        respect to UTC."
    ::= { wtWebGraphAnalog57762TimeZone 11 }

wtWebGraphAnalog57762StTzStopMonth OBJECT-TYPE
    SYNTAX INTEGER {
    	wtWebGraphAnalog57762StopMonth-January(1),
    	wtWebGraphAnalog57762StopMonth-February(2),
    	wtWebGraphAnalog57762StopMonth-March(3),
    	wtWebGraphAnalog57762StopMonth-April(4),
    	wtWebGraphAnalog57762StopMonth-May(5),
    	wtWebGraphAnalog57762StopMonth-June(6),
    	wtWebGraphAnalog57762StopMonth-July(7),
    	wtWebGraphAnalog57762StopMonth-August(8),
    	wtWebGraphAnalog57762StopMonth-September(9),
    	wtWebGraphAnalog57762StopMonth-October(10),
    	wtWebGraphAnalog57762StopMonth-November(11),
    	wtWebGraphAnalog57762StopMonth-December(12)
    	}
    ACCESS read-write
    STATUS mandatory
    DESCRIPTION
        "Month in which the change is made from summer time to winter time."
   ::= { wtWebGraphAnalog57762TimeZone 12 }

wtWebGraphAnalog57762StTzStopMode OBJECT-TYPE
    SYNTAX INTEGER {
    	wtWebGraphAnalog57762StopMode-first(1),
    	wtWebGraphAnalog57762StopMode-second(2),
    	wtWebGraphAnalog57762StopMode-third(3),
    	wtWebGraphAnalog57762StopMode-fourth(4),
    	wtWebGraphAnalog57762StopMode-last(5)
    	}
    ACCESS read-write
    STATUS mandatory
    DESCRIPTION
        "Mode of the week day on which the change is made from summer time to winter time."
    ::= { wtWebGraphAnalog57762TimeZone 13 }

wtWebGraphAnalog57762StTzStopWday OBJECT-TYPE
    SYNTAX INTEGER {
    	wtWebGraphAnalog57762StopWday-Sunday(1),
    	wtWebGraphAnalog57762StopWday-Monday(2),
    	wtWebGraphAnalog57762StopWday-Tuesday(3),
    	wtWebGraphAnalog57762StopWday-Thursday(4),
    	wtWebGraphAnalog57762StopWday-Wednesday(5),
    	wtWebGraphAnalog57762StopWday-Friday(6),
    	wtWebGraphAnalog57762StopWday-Saturday(7)
    	}
    ACCESS read-write
    STATUS mandatory
    DESCRIPTION
        "Day of the week on which the change is made from summer time to winter time."
    ::= { wtWebGraphAnalog57762TimeZone 14 }

wtWebGraphAnalog57762StTzStopHrs OBJECT-TYPE
    SYNTAX INTEGER
    ACCESS read-write
    STATUS mandatory
    DESCRIPTION
        "Hour at which the time zone is changed from summer to winter time with
        respect to UTC."
    ::= { wtWebGraphAnalog57762TimeZone 15 }

wtWebGraphAnalog57762StTzStopMin OBJECT-TYPE
    SYNTAX INTEGER
    ACCESS read-write
    STATUS mandatory
    DESCRIPTION
        "Minute at which the time zone is changed from summer to winter time with
        respect to UTC."
    ::= { wtWebGraphAnalog57762TimeZone 16 }

-- wtWebGraphAnalog57762TimeServer Group
----------------------------

wtWebGraphAnalog57762TimeServer1 OBJECT-TYPE
    SYNTAX OCTET STRING
    ACCESS read-write
    STATUS mandatory
    DESCRIPTION
        "IP address or name of the 1st time server in ASCII"
    ::= { wtWebGraphAnalog57762TimeServer 1 }

wtWebGraphAnalog57762TimeServer2 OBJECT-TYPE
    SYNTAX OCTET STRING
    ACCESS read-write
    STATUS mandatory
    DESCRIPTION
        "IP address or name of the 2nd time server in ASCII"
    ::= { wtWebGraphAnalog57762TimeServer 2 }

wtWebGraphAnalog57762TsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebGraphAnalog57762TimeServer 3 }

wtWebGraphAnalog57762TsSyncTime OBJECT-TYPE
    SYNTAX INTEGER
    ACCESS read-write
    STATUS mandatory
    DESCRIPTION
        "Daily synchronisation time with the time server (hour: 0-23)."
    ::= { wtWebGraphAnalog57762TimeServer 4 }

-- wtWebGraphAnalog57762DeviceClock Group
----------------------------

wtWebGraphAnalog57762ClockHrs OBJECT-TYPE
    SYNTAX INTEGER (0..23)
    ACCESS read-write
    STATUS mandatory
    DESCRIPTION
        "Clock hours taking into account the time zone settings."
    ::= { wtWebGraphAnalog57762DeviceClock 1 }

wtWebGraphAnalog57762ClockMin OBJECT-TYPE
    SYNTAX INTEGER (0..59)
    ACCESS read-write
    STATUS mandatory
    DESCRIPTION
        "Clock minutes taking into account the time zone settings."
    ::= { wtWebGraphAnalog57762DeviceClock 2 }

wtWebGraphAnalog57762ClockDay OBJECT-TYPE
    SYNTAX INTEGER (1..31)
    ACCESS read-write
    STATUS mandatory
    DESCRIPTION
        "Date: Day of the month, taking into account the time zone settings."
    ::= { wtWebGraphAnalog57762DeviceClock 3 }

wtWebGraphAnalog57762ClockMonth OBJECT-TYPE
   SYNTAX INTEGER {
    	wtWebGraphAnalog57762ClockMonth-January(1),
    	wtWebGraphAnalog57762ClockMonth-February(2),
    	wtWebGraphAnalog57762ClockMonth-March(3),
    	wtWebGraphAnalog57762ClockMonth-April(4),
    	wtWebGraphAnalog57762ClockMonth-May(5),
    	wtWebGraphAnalog57762ClockMonth-June(6),
    	wtWebGraphAnalog57762ClockMonth-July(7),
    	wtWebGraphAnalog57762ClockMonth-August(8),
    	wtWebGraphAnalog57762ClockMonth-September(9),
    	wtWebGraphAnalog57762ClockMonth-October(10),
    	wtWebGraphAnalog57762ClockMonth-November(11),
    	wtWebGraphAnalog57762ClockMonth-December(12)
    	}
    ACCESS read-write
    STATUS mandatory
    DESCRIPTION
        "Date: Month, taking into account the time zone settings."
    ::= { wtWebGraphAnalog57762DeviceClock 4 }

wtWebGraphAnalog57762ClockYear OBJECT-TYPE
    SYNTAX INTEGER (0..65535)
    ACCESS read-write
    STATUS mandatory
    DESCRIPTION
        "Date: Year, taking into account the time zone settings."
    ::= { wtWebGraphAnalog57762DeviceClock 5 }


-- wtWebGraphAnalog57762Network Group
------------------------

wtWebGraphAnalog57762IpAddress OBJECT-TYPE
    SYNTAX IpAddress
    ACCESS read-write
    STATUS mandatory
    DESCRIPTION
        "IP address of the Webio"
    ::= { wtWebGraphAnalog57762Network 1 }

wtWebGraphAnalog57762SubnetMask OBJECT-TYPE
    SYNTAX IpAddress
    ACCESS read-write
    STATUS mandatory
    DESCRIPTION
        "Subnet mask of the Webio"
    ::= { wtWebGraphAnalog57762Network 2 }

wtWebGraphAnalog57762Gateway OBJECT-TYPE
    SYNTAX IpAddress
    ACCESS read-write
    STATUS mandatory
    DESCRIPTION
        "Gateway of the Webio"
    ::= { wtWebGraphAnalog57762Network 3 }

wtWebGraphAnalog57762DnsServer1 OBJECT-TYPE
    SYNTAX OCTET STRING
    ACCESS read-write
    STATUS mandatory
    DESCRIPTION
        "IP address of the 1st DNS server in ASCII"
    ::= { wtWebGraphAnalog57762Network 4 }

wtWebGraphAnalog57762DnsServer2 OBJECT-TYPE
    SYNTAX OCTET STRING
    ACCESS read-write
    STATUS mandatory
    DESCRIPTION
        "IP address of the 2nd DNS server in ASCII"
    ::= { wtWebGraphAnalog57762Network 5 }

wtWebGraphAnalog57762AddConfig OBJECT-TYPE
    SYNTAX OCTET STRING
    ACCESS read-write
    STATUS mandatory
    DESCRIPTION
        "Additional configuration (1=ON):
        Octet 1: unused
        Octet 2: unused
        Octet 3: unused
        Octet 4:
	        Bit 1: DHCP disable
	        Bit 0: BOOTP disable
	        "
    ::= { wtWebGraphAnalog57762Network 6 }

--  wtWebGraphAnalog57762HTTP Group
--------------------------------

wtWebGraphAnalog57762Startup OBJECT-TYPE
    SYNTAX OCTET STRING
    ACCESS read-write
    STATUS mandatory
    DESCRIPTION
        "Binary coded start page:
        Octet 1: unused
        Octet 2: unused
        Octet 3: unused
        Octet 4:
	        Bit 1: Index.htm
	        Bit 2: Home.htm
	        Bit 3: User.htm
	Only one page may be selected at a time."
    ::= { wtWebGraphAnalog57762HTTP 1 }

wtWebGraphAnalog57762GetHeaderEnable OBJECT-TYPE
    SYNTAX OCTET STRING
    ACCESS read-write
    STATUS mandatory
    DESCRIPTION
        "If these bits are set, every answer of a short form GET question will be lead
        by the IP-address and name of the device and/or a HTTP header:
        Octet 1: unused
        Octet 2: unused
        Octet 3: unused
        Octet 4:
        	Bit 1-6: unused
        	Bit 1  : GET HTTP enable
                Bit 0  : GET Header enable"
    ::= { wtWebGraphAnalog57762HTTP 2 }

wtWebGraphAnalog57762HttpPort OBJECT-TYPE
    SYNTAX INTEGER (1..65535)
    ACCESS read-write
    STATUS mandatory
    DESCRIPTION
        "Definition of the standard HTML port (Default: 80)."
    ::= { wtWebGraphAnalog57762HTTP 3 }


-- wtWebGraphAnalog57762Mail Group
--------------------------------

wtWebGraphAnalog57762MailAdName OBJECT-TYPE
    SYNTAX OCTET STRING
    ACCESS read-write
    STATUS mandatory
    DESCRIPTION
        "Device name for mail administration."
    ::= { wtWebGraphAnalog57762Mail 1 }

wtWebGraphAnalog57762MailReply OBJECT-TYPE
    SYNTAX OCTET STRING
    ACCESS read-write
    STATUS mandatory
    DESCRIPTION
        "Reply address for the mail server."
    ::= { wtWebGraphAnalog57762Mail 2 }

wtWebGraphAnalog57762MailServer OBJECT-TYPE
    SYNTAX OCTET STRING
    ACCESS read-write
    STATUS mandatory
    DESCRIPTION
        "Name or IP address of the mail server."
    ::= { wtWebGraphAnalog57762Mail 3 }

wtWebioAn1MailEnable OBJECT-TYPE
    SYNTAX OCTET STRING
    ACCESS read-write
    STATUS mandatory
    DESCRIPTION
        "Set this bit to enable the sending of mails:
        Octet 1: unused
        Octet 2: unused
        Octet 3: unused
        Octet 4:
        	Bit 1-7: unused
                Bit 0  : Mail enable"
    ::= { wtWebGraphAnalog57762Mail 4 }

wtWebGraphAnalog57762MailAuthentication OBJECT-TYPE
    SYNTAX OCTET STRING (SIZE (4))
    ACCESS read-write
    STATUS mandatory
    DESCRIPTION
        "Selection of the authentication modi:
        The OCTETS are interpreted bit-by-bit, with each bit corresponding to an output.
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebGraphAnalog57762Mail 5 }

wtWebGraphAnalog57762MailAuthUser OBJECT-TYPE
    SYNTAX OCTET STRING
    ACCESS read-write
    STATUS mandatory
    DESCRIPTION
        "Name of the user to be authenticated."
    ::= { wtWebGraphAnalog57762Mail 6 }

wtWebGraphAnalog57762MailAuthPassword OBJECT-TYPE
    SYNTAX OCTET STRING
    ACCESS read-write
    STATUS mandatory
    DESCRIPTION
        "Authentication password."
    ::= { wtWebGraphAnalog57762Mail 7 }

wtWebGraphAnalog57762MailPop3Server OBJECT-TYPE
    SYNTAX OCTET STRING
    ACCESS read-write
    STATUS mandatory
    DESCRIPTION
        "Name or Ip-address of the POP3 Servers."
    ::= { wtWebGraphAnalog57762Mail 8 }

-- wtWebGraphAnalog57762SNMP Group
--------------------------------

wtWebGraphAnalog57762SnmpCommunityStringRead OBJECT-TYPE
    SYNTAX OCTET STRING
    ACCESS read-write
    STATUS mandatory
    DESCRIPTION
        "Community string read only"
    ::= { wtWebGraphAnalog57762SNMP 1 }

wtWebGraphAnalog57762SnmpCommunityStringReadWrite OBJECT-TYPE
    SYNTAX OCTET STRING
    ACCESS read-write
    STATUS mandatory
    DESCRIPTION
        "Community string read / write"
    ::= { wtWebGraphAnalog57762SNMP 2 }

wtWebGraphAnalog57762SystemTrapManagerIP OBJECT-TYPE
    SYNTAX OCTET STRING
    ACCESS read-write
    STATUS mandatory
    DESCRIPTION
        "Name or IP address of the TCP server which accepts the system trap."
    ::= { wtWebGraphAnalog57762SNMP 3 }

wtWebGraphAnalog57762SystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2-7: unused"
    ::= { wtWebGraphAnalog57762SNMP 4 }

wtWebGraphAnalog57762SnmpEnable OBJECT-TYPE
    SYNTAX OCTET STRING
    ACCESS read-write
    STATUS mandatory
    DESCRIPTION
        "Set bit 0 to enable SNMP.
        If disabled, the device did not respond to any SNMP requests.
        Bit 1 decided wether the community string of read operations
        is compared with the system password or not:
        Octet 1: unused
        Octet 2: unused
        Octet 3: unused
        Octet 4:
        	Bit 1-7: unused
        	Bit 0  : SNMP enable"
    ::= { wtWebGraphAnalog57762SNMP 5 }

wtWebGraphAnalog57762SnmpCommunityStringTrap OBJECT-TYPE
    SYNTAX OCTET STRING
    ACCESS read-write
    STATUS mandatory
    DESCRIPTION
        "Community string send within traps."
    ::= { wtWebGraphAnalog57762SNMP 6 }

wtWebGraphAnalog57762SnmpSystemTrapManagerPort OBJECT-TYPE
    SYNTAX INTEGER
    ACCESS read-write
    STATUS mandatory
    DESCRIPTION
        "Port number of the TCP server which accepts the system trap."
    ::= { wtWebGraphAnalog57762SNMP 7 }


-- wtWebGraphAnalog57762UDP Group
--------------------------------

wtWebGraphAnalog57762UdpPort OBJECT-TYPE
    SYNTAX INTEGER (1..65535)
    ACCESS read-write
    STATUS mandatory
    DESCRIPTION
        "Udp port to which the Udp queries ( short form GET requests) can be sent. This
        port number must be unique within the device."
    ::= { wtWebGraphAnalog57762UDP 1 }

wtWebGraphAnalog57762UdpEnable OBJECT-TYPE
    SYNTAX OCTET STRING
    ACCESS read-write
    STATUS mandatory
    DESCRIPTION
        "Set this bit to enable UDP support:
        Octet 1: unused
        Octet 2: unused
        Octet 3: unused
        Octet 4:
        	Bit 1-7: unused
                Bit 0  : UDP enable"
    ::= { wtWebGraphAnalog57762UDP 2 }

--  wtWebGraphAnalog57762Syslog Group
--------------------------------

wtWebGraphAnalog57762SyslogServerIP OBJECT-TYPE
    SYNTAX OCTET STRING
    ACCESS read-write
    STATUS mandatory
    DESCRIPTION
        "Name or IP address of the Syslog server, which accepts the Syslog messgaes."
    ::= { wtWebGraphAnalog57762Syslog 1 }

wtWebGraphAnalog57762SyslogServerPort OBJECT-TYPE
    SYNTAX INTEGER
    ACCESS read-write
    STATUS mandatory
    DESCRIPTION
        "Portnumber of the Syslog servers, default 514."
    ::= { wtWebGraphAnalog57762Syslog 2 }

wtWebGraphAnalog57762SyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebGraphAnalog57762Syslog 3 }

wtWebGraphAnalog57762SyslogEnable OBJECT-TYPE
    SYNTAX OCTET STRING
    ACCESS read-write
    STATUS mandatory
    DESCRIPTION
        "Set bit 0to enable Syslog:
        Octet 1: unused
        Octet 2: unused
        Octet 3: unused
        Octet 4:
        	Bit 1-7: unused
                Bit 0  : Syslog enable"
    ::= { wtWebGraphAnalog57762Syslog 4 }

--  wtWebGraphAnalog57762FTP Group
--------------------------------

wtWebGraphAnalog57762FTPServerIP OBJECT-TYPE
    SYNTAX OCTET STRING
    ACCESS read-write
    STATUS mandatory
    DESCRIPTION
        "Name or IP address of the FTP server, which accepts the FTP messages."
    ::= { wtWebGraphAnalog57762FTP 1 }

wtWebGraphAnalog57762FTPServerControlPort OBJECT-TYPE
    SYNTAX INTEGER
    ACCESS read-write
    STATUS mandatory
    DESCRIPTION
        "Portnumber of the control port of the FTP server, default 21."
    ::= { wtWebGraphAnalog57762FTP 2 }

wtWebGraphAnalog57762FTPUserName OBJECT-TYPE
    SYNTAX OCTET STRING
    ACCESS read-write
    STATUS mandatory
    DESCRIPTION
        "FTP Loggin: user name."
    ::= { wtWebGraphAnalog57762FTP 3 }

wtWebGraphAnalog57762FTPPassword OBJECT-TYPE
    SYNTAX OCTET STRING
    ACCESS read-write
    STATUS mandatory
    DESCRIPTION
        "FTP Loggin: user password."
    ::= { wtWebGraphAnalog57762FTP 4 }

wtWebGraphAnalog57762FTPAccount OBJECT-TYPE
    SYNTAX OCTET STRING
    ACCESS read-write
    STATUS mandatory
    DESCRIPTION
        "FTP Loggin: name of account."
    ::= { wtWebGraphAnalog57762FTP 5 }

wtWebGraphAnalog57762FTPOption OBJECT-TYPE
    SYNTAX OCTET STRING
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebGraphAnalog57762FTP 6 }

wtWebGraphAnalog57762FTPEnable OBJECT-TYPE
    SYNTAX OCTET STRING
    ACCESS read-write
    STATUS mandatory
    DESCRIPTION
        "Set Bit 0 to enable FTP:
        Octet 1: unused
        Octet 2: unused
        Octet 3: unused
        Octet 4:
        	Bit 1-7: unused
                Bit 0  : FTP enable"
    ::= { wtWebGraphAnalog57762FTP 7 }

--  wtWebGraphAnalog57762Language Group
--------------------------------

wtWebGraphAnalog57762LanguageSelect OBJECT-TYPE
    SYNTAX OCTET STRING
    ACCESS read-write
    STATUS mandatory
    DESCRIPTION
        "Language selection:
        Octet 1: unused
        Octet 2: unused
        Octet 3: unused
        Octet 4:
        	Bit 2-7: unused
        	Bit 1  : English
                Bit 0  : German"
    ::= { wtWebGraphAnalog57762Language 1 }

--  wtWebGraphAnalog57762Binary Group
--------------------------------

wtWebGraphAnalog57762BinaryModeCount OBJECT-TYPE
    SYNTAX INTEGER (1..2)
    ACCESS read-only
    STATUS mandatory
    DESCRIPTION
        "Number of independent binary channels."
    ::= { wtWebGraphAnalog57762Binary 1 }

-- Binary Interface Table

wtWebGraphAnalog57762BinaryIfTable OBJECT-TYPE
    SYNTAX SEQUENCE OF WtWebGraphAnalog57762BinaryIfEntry
    ACCESS not-accessible
    STATUS mandatory
    DESCRIPTION
        "Table of indices."
    ::= { wtWebGraphAnalog57762Binary 2 }

wtWebGraphAnalog57762BinaryIfEntry OBJECT-TYPE
    SYNTAX WtWebGraphAnalog57762BinaryIfEntry
    ACCESS not-accessible
    STATUS mandatory
    DESCRIPTION
        "Indices of the binary channels."
    INDEX  { wtWebGraphAnalog57762BinaryModeNo }
    ::= { wtWebGraphAnalog57762BinaryIfTable 1 }

WtWebGraphAnalog57762BinaryIfEntry ::= SEQUENCE {
    wtWebGraphAnalog57762BinaryModeNo INTEGER
}

wtWebGraphAnalog57762BinaryModeNo OBJECT-TYPE
    SYNTAX INTEGER (1..2)
    ACCESS read-only
    STATUS mandatory
    DESCRIPTION
        "Number of the binary channel."
    ::= { wtWebGraphAnalog57762BinaryIfEntry 1 }

-- Binary Table
--------------------------------

wtWebGraphAnalog57762BinaryTable OBJECT-TYPE
    SYNTAX SEQUENCE OF WtWebGraphAnalog57762BinaryEntry
    ACCESS not-accessible
    STATUS mandatory
    DESCRIPTION
        "Table of properties of the binary mode."
    ::= { wtWebGraphAnalog57762Binary 3 }

wtWebGraphAnalog57762BinaryEntry OBJECT-TYPE
    SYNTAX WtWebGraphAnalog57762BinaryEntry
    ACCESS not-accessible
    STATUS mandatory
    DESCRIPTION
        "Binary properties."
    INDEX  { wtWebGraphAnalog57762BinaryModeNo }
    ::= { wtWebGraphAnalog57762BinaryTable 1 }

WtWebGraphAnalog57762BinaryEntry ::= SEQUENCE {
    wtWebGraphAnalog57762BinaryOperationMode			OCTET STRING,
    wtWebGraphAnalog57762BinaryTcpServerLocalPort		INTEGER,
    wtWebGraphAnalog57762BinaryTcpServerInputTrigger		OCTET STRING,
    wtWebGraphAnalog57762BinaryTcpServerApplicationMode		OCTET STRING,
    wtWebGraphAnalog57762BinaryTcpClientLocalPort		INTEGER,
    wtWebGraphAnalog57762BinaryTcpClientServerPort		INTEGER,
    wtWebGraphAnalog57762BinaryTcpClientServerIpAddr		OCTET STRING,
    wtWebGraphAnalog57762BinaryTcpClientServerPassword		OCTET STRING,
    wtWebGraphAnalog57762BinaryTcpClientInactivity		INTEGER,
    wtWebGraphAnalog57762BinaryTcpClientInputTrigger		OCTET STRING,
    wtWebGraphAnalog57762BinaryTcpClientInterval		INTEGER,
    wtWebGraphAnalog57762BinaryTcpClientApplicationMode		OCTET STRING,
    wtWebGraphAnalog57762BinaryUdpPeerLocalPort			INTEGER,
    wtWebGraphAnalog57762BinaryUdpPeerRemotePort		INTEGER,
    wtWebGraphAnalog57762BinaryUdpPeerRemoteIpAddr		OCTET STRING,
    wtWebGraphAnalog57762BinaryUdpPeerInputTrigger		OCTET STRING,
    wtWebGraphAnalog57762BinaryUdpPeerInterval			INTEGER,
    wtWebGraphAnalog57762BinaryUdpPeerApplicationMode		OCTET STRING,
    wtWebGraphAnalog57762BinaryConnectedPort			INTEGER,
    wtWebGraphAnalog57762BinaryConnectedIpAddr			IpAddress,
    wtWebGraphAnalog57762BinaryTcpServerClientHttpPort		INTEGER,
    wtWebGraphAnalog57762BinaryTcpClientServerHttpPort		INTEGER,
    wtWebGraphAnalog57762BinaryTcpServerHysteresis1		OCTET STRING,
    wtWebGraphAnalog57762BinaryTcpServerHysteresis2		OCTET STRING,
    wtWebGraphAnalog57762BinaryTcpClientHysteresis1		OCTET STRING,
    wtWebGraphAnalog57762BinaryTcpClientHysteresis2		OCTET STRING,
    wtWebGraphAnalog57762BinaryUdpPeerHysteresis1		OCTET STRING,
    wtWebGraphAnalog57762BinaryUdpPeerHysteresis2		OCTET STRING,
    wtWebGraphAnalog57762BinaryTcpClientServerUserName		OCTET STRING
}

wtWebGraphAnalog57762BinaryOperationMode OBJECT-TYPE
    SYNTAX OCTET STRING (SIZE (4))
    ACCESS read-write
    STATUS mandatory
    DESCRIPTION
        "Selection of the operation mode:
        The OCTETS are interpreted bit-by-bit,
        Bit 0 corresponds to the LSB.
        OCTET 1: unused
        OCTET 2: unused
        OCTET 3: unused
        OCTET 4: Bit 3-7: unused
        	 Bit 2  : UDP Peer
        	 Bit 1  : TCP Client
        	 Bit 0  : TCP Server"
    ::= { wtWebGraphAnalog57762BinaryEntry 1 }

wtWebGraphAnalog57762BinaryTcpServerLocalPort OBJECT-TYPE
    SYNTAX INTEGER (1..65535)
    ACCESS read-write
    STATUS mandatory
    DESCRIPTION
        "Local TCP port for data exchange in this server mode.
        This port number must be unique within the device.
	Reserved port number must not be used (refere to the manual)."
    ::= { wtWebGraphAnalog57762BinaryEntry 2 }

wtWebGraphAnalog57762BinaryTcpServerInputTrigger OBJECT-TYPE
    SYNTAX OCTET STRING (SIZE (4))
    ACCESS read-write
    STATUS mandatory
    DESCRIPTION
        "Every change on the inputs causes their state to be transmitted to the
        remote device. To minimize data traffic, individual inputs may be exempted
        from this rule. Nevertheless every transmission will contain all input states.
        If a bit is set (1), a change of state on the corresponding input
        triggers a transmission. If the bit is not set (0), no transmission
        takes place.
        The OCTETS are interpreted bit-by-bit, with each bit corresponding to an input.
        Bit 0 corresponds to the LSB.
        OCTET 1: unused
        OCTET 2: unused
        OCTET 3: unused
        OCTET 4, Bit 0-1: Analog inputs 0-1"
    ::= { wtWebGraphAnalog57762BinaryEntry 3 }

wtWebGraphAnalog57762BinaryTcpServerApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 4-7: unused
        	 Bit 3  : OPC Device
        	 Bit 2  : Box2Box Slave
        	 Bit 1  : Compatible 50xxx
        	 Bit 0  : Default"
    ::= { wtWebGraphAnalog57762BinaryEntry 4 }

wtWebGraphAnalog57762BinaryTcpClientLocalPort OBJECT-TYPE
    SYNTAX INTEGER (1..65535)
    ACCESS read-write
    STATUS mandatory
    DESCRIPTION
        "Local TCP port for data exchange in this client mode.
        This port number must be unique within the device.
	Reserved port number must not be used (refere to the manual)."
    ::= { wtWebGraphAnalog57762BinaryEntry 5 }

wtWebGraphAnalog57762BinaryTcpClientServerPort OBJECT-TYPE
    SYNTAX INTEGER (1..65535)
    ACCESS read-write
    STATUS mandatory
    DESCRIPTION
        "Port number of the server. A complete set of port number, IP address
        and a valid input/output mask starts this mode.
        No data exchange take place when setting the server port to zero."
    ::= { wtWebGraphAnalog57762BinaryEntry 6 }

wtWebGraphAnalog57762BinaryTcpClientServerIpAddr OBJECT-TYPE
    SYNTAX OCTET STRING
    ACCESS read-write
    STATUS mandatory
    DESCRIPTION
        "Ip address of the server. A complete set of port number, IP address
        and a valid input/output mask starts this mode.
        No data exchange take place when setting the server IP address to 0.0.0.0."
    ::= { wtWebGraphAnalog57762BinaryEntry 7 }

wtWebGraphAnalog57762BinaryTcpClientServerPassword OBJECT-TYPE
    SYNTAX OCTET STRING
    ACCESS read-write
    STATUS mandatory
    DESCRIPTION
        "Building a connection may be protected by the
        administrator password of the server. Enter the server password
        to establish the connection, if a server administrator password
        exists."
    ::= { wtWebGraphAnalog57762BinaryEntry 8 }

wtWebGraphAnalog57762BinaryTcpClientInactivity OBJECT-TYPE
    SYNTAX INTEGER
    ACCESS read-write
    STATUS mandatory
    DESCRIPTION
        "Connection timeout in 100ms. If no data are exchanged within the specified
        time, the device closes the connection to the server.
        The value 0 deactivates the timer. Using the Box2Box mode this function is
        disabled."
    ::= { wtWebGraphAnalog57762BinaryEntry 9 }

wtWebGraphAnalog57762BinaryTcpClientInputTrigger OBJECT-TYPE
    SYNTAX OCTET STRING (SIZE (4))
    ACCESS read-write
    STATUS mandatory
    DESCRIPTION
        "Every change on the inputs causes their state to be transmitted to the
        remote device. To minimize data traffic, individual inputs may be exempted
        from this rule. Nevertheless every transmission will contain all input states.
        If a bit is set (1), a change of state on the corresponding input
        triggers a transmission. If the bit is not set (0), no transmission
        takes place.
        The OCTETS are interpreted bit-by-bit, with each bit corresponding to an input.
        Bit 0 corresponds to the LSB.
        OCTET 1: unused
        OCTET 2: unused
        OCTET 3: unused
        OCTET 4, Bit 0-1: Analog inputs 0-1"
    ::= { wtWebGraphAnalog57762BinaryEntry 10 }

wtWebGraphAnalog57762BinaryTcpClientInterval OBJECT-TYPE
    SYNTAX INTEGER (0..65535)
    ACCESS read-write
    STATUS mandatory
    DESCRIPTION
        "Configurable interval with a 100ms base, in which the Webio device sends
        data to the configured application. A interval of zero stopps the
        periodical sending."
    ::= { wtWebGraphAnalog57762BinaryEntry 11 }

wtWebGraphAnalog57762BinaryTcpClientApplicationMode OBJECT-TYPE
    SYNTAX OCTET STRING (SIZE (4))
    ACCESS read-write
    STATUS mandatory
    DESCRIPTION
        "Selection of the application mode:
        The OCTETS are interpreted bit-by-bit,
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebGraphAnalog57762BinaryEntry 12 }

wtWebGraphAnalog57762BinaryUdpPeerLocalPort OBJECT-TYPE
    SYNTAX INTEGER (1..65535)
    ACCESS read-write
    STATUS mandatory
    DESCRIPTION
        "Local UDP port for data exchange in this peer to peer mode.
        This port number must be unique within the device.
	Reserved port number must not be used (refere to the manual)."
    ::= { wtWebGraphAnalog57762BinaryEntry 13 }

wtWebGraphAnalog57762BinaryUdpPeerRemotePort OBJECT-TYPE
    SYNTAX INTEGER (1..65535)
    ACCESS read-write
    STATUS mandatory
    DESCRIPTION
        "Port number of the remote device. A complete set of port number, IP address
        and a valid input/output mask starts this mode.
        No data exchange take place when setting the remote port to zero."
    ::= { wtWebGraphAnalog57762BinaryEntry 14 }

wtWebGraphAnalog57762BinaryUdpPeerRemoteIpAddr OBJECT-TYPE
    SYNTAX OCTET STRING
    ACCESS read-write
    STATUS mandatory
    DESCRIPTION
        "Ip address of the remote device. A complete set of port number, IP address
        and a valid input/output mask starts this mode.
        No data exchange take place when setting the remote device IP address to 0.0.0.0."
    ::= { wtWebGraphAnalog57762BinaryEntry 15 }

wtWebGraphAnalog57762BinaryUdpPeerInputTrigger OBJECT-TYPE
    SYNTAX OCTET STRING (SIZE (4))
    ACCESS read-write
    STATUS mandatory
    DESCRIPTION
        "Every change on the inputs causes their state to be transmitted to the
        remote device. To minimize data traffic, individual inputs may be exempted
        from this rule. Nevertheless every transmission will contain all input states.
        If a bit is set (1), a change of state on the corresponding input
        triggers a transmission. If the bit is not set (0), no transmission
        takes place.
        The OCTETS are interpreted bit-by-bit, with each bit corresponding to an input.
        Bit 0 corresponds to the LSB.
        OCTET 1: unused
        OCTET 2: unused
        OCTET 3: unused
        OCTET 4, Bit 0-1: Analog inputs 0-1"
    ::= { wtWebGraphAnalog57762BinaryEntry 16 }

wtWebGraphAnalog57762BinaryUdpPeerInterval OBJECT-TYPE
    SYNTAX INTEGER (0..65535)
    ACCESS read-write
    STATUS mandatory
    DESCRIPTION
        "Configurable interval with a 100ms base, in which the Webio device sends
        data to the configured remote device. A interval of zero stopps the
        periodical sending."
    ::= { wtWebGraphAnalog57762BinaryEntry 17 }

wtWebGraphAnalog57762BinaryUdpPeerApplicationMode OBJECT-TYPE
    SYNTAX OCTET STRING (SIZE (4))
    ACCESS read-write
    STATUS mandatory
    DESCRIPTION
        "Selection of the application mode:
        The OCTETS are interpreted bit-by-bit, with each bit corresponding to an output.
        Bit 0 corresponds to the LSB.
        OCTET 1: unused
        OCTET 2: unused
        OCTET 3: unused
        OCTET 4: Bit 3-7: unused
        	 Bit 2  : Box2Box Slave
        	 Bit 1  : Compatible 50xxx
        	 Bit 0  : Default"
    ::= { wtWebGraphAnalog57762BinaryEntry 18 }

wtWebGraphAnalog57762BinaryConnectedPort OBJECT-TYPE
    SYNTAX INTEGER (1..65535)
    ACCESS read-only
    STATUS mandatory
    DESCRIPTION
        "Port number of the remote device, after connection has been established.
        In case of no connection or missing port informations a zero will be read."
    ::= { wtWebGraphAnalog57762BinaryEntry 19 }

wtWebGraphAnalog57762BinaryConnectedIpAddr OBJECT-TYPE
    SYNTAX IpAddress
    ACCESS read-only
    STATUS mandatory
    DESCRIPTION
        "IP address of the remote device, after connection has been established.
        In case of no connection or missing port informations 0.0.0.0 will be read."
    ::= { wtWebGraphAnalog57762BinaryEntry 20 }

wtWebGraphAnalog57762BinaryTcpServerClientHttpPort OBJECT-TYPE
    SYNTAX INTEGER (1..65535)
    ACCESS read-write
    STATUS mandatory
    DESCRIPTION
        "HTTP port number of the remote device at TCP Server Mode. If an mailfunction occurs
        status informations will be send to this port.
        Not used at mode Compatible 50xxx."
    ::= { wtWebGraphAnalog57762BinaryEntry 21 }

wtWebGraphAnalog57762BinaryTcpClientServerHttpPort OBJECT-TYPE
    SYNTAX INTEGER (1..65535)
    ACCESS read-write
    STATUS mandatory
    DESCRIPTION
        "HTTP port number of the remote device at TCP Client Mode. In the operating mode
        Box2Box connection status informations will be exchanged through this port."
    ::= { wtWebGraphAnalog57762BinaryEntry 22 }

wtWebGraphAnalog57762BinaryTcpServerHysteresis1 OBJECT-TYPE
    SYNTAX OCTET STRING
    ACCESS read-write
    STATUS mandatory
    DESCRIPTION
        "A change greater than this value initiate a transmission of the corresponding input value.
        The input 1 must be selected at wtWebGraphAnalog57762BinaryTcpServerInputTrigger.
        With a hysteresis of zero any change will be transmitted."
    ::= { wtWebGraphAnalog57762BinaryEntry 23 }

wtWebGraphAnalog57762BinaryTcpServerHysteresis2 OBJECT-TYPE
    SYNTAX OCTET STRING
    ACCESS read-write
    STATUS mandatory
    DESCRIPTION
        "A change greater than this value initiate a transmission of the corresponding input value.
        The input 2 must be selected at wtWebGraphAnalog57762BinaryTcpServerInputTrigger.
        With a hysteresis of zero any change will be transmitted."
    ::= { wtWebGraphAnalog57762BinaryEntry 24 }

wtWebGraphAnalog57762BinaryTcpClientHysteresis1 OBJECT-TYPE
    SYNTAX OCTET STRING
    ACCESS read-write
    STATUS mandatory
    DESCRIPTION
        "A change greater than this value initiate a transmission of the corresponding input value.
        The input 1 must be selected at wtWebGraphAnalog57762BinaryTcpClientInputTrigger.
        With a hysteresis of zero any change will be transmitted."

      ::= { wtWebGraphAnalog57762BinaryEntry 25 }

wtWebGraphAnalog57762BinaryTcpClientHysteresis2 OBJECT-TYPE
    SYNTAX OCTET STRING
    ACCESS read-write
    STATUS mandatory
    DESCRIPTION
        "A change greater than this value initiate a transmission of the corresponding input value.
        The input 2 must be selected at wtWebGraphAnalog57762BinaryTcpClientInputTrigger.
        With a hysteresis of zero any change will be transmitted."

      ::= { wtWebGraphAnalog57762BinaryEntry 26 }

wtWebGraphAnalog57762BinaryUdpPeerHysteresis1 OBJECT-TYPE
    SYNTAX OCTET STRING
    ACCESS read-write
    STATUS mandatory
    DESCRIPTION
        "A change greater than this value initiate a transmission of the corresponding input value.
        The input 1 must be selected at wtWebGraphAnalog57762BinaryUdpPeerInputTrigger.
        With a hysteresis of zero any change will be transmitted."
    ::= { wtWebGraphAnalog57762BinaryEntry 27 }

wtWebGraphAnalog57762BinaryUdpPeerHysteresis2 OBJECT-TYPE
    SYNTAX OCTET STRING
    ACCESS read-write
    STATUS mandatory
    DESCRIPTION
        "A change greater than this value initiate a transmission of the corresponding input value.
        The input 2 must be selected at wtWebGraphAnalog57762BinaryUdpPeerInputTrigger.
        With a hysteresis of zero any change will be transmitted."
    ::= { wtWebGraphAnalog57762BinaryEntry 28 }

wtWebGraphAnalog57762BinaryTcpClientServerUserName OBJECT-TYPE
    SYNTAX OCTET STRING
    ACCESS read-write
    STATUS mandatory
    DESCRIPTION
        "Building a connection may be protected by a specific
        user name within the server. Enter the user name
        to establish the connection, if a user name entry
        exists."
    ::= { wtWebGraphAnalog57762BinaryEntry 29 }

--  wtWebGraphAnalog57762MQTT Group
--------------------------------

wtWebGraphAnalog57762MQTTEnable OBJECT-TYPE
    SYNTAX OCTET STRING
    ACCESS read-write
    STATUS mandatory
    DESCRIPTION
        "Bit 7 schaltet MQTT frei:
        Octet 1: ungenutzt
        Octet 2: ungenutzt
        Octet 3: ungenutzt
        Octet 4:
        	Bit 0-6: ungenutzt
                Bit 7  : MQTT enable"
    ::= { wtWebGraphAnalog57762MQTT 1 }

wtWebGraphAnalog57762MQTTBrockerIP OBJECT-TYPE
    SYNTAX OCTET STRING
    ACCESS read-write
    STATUS mandatory
    DESCRIPTION
        "Name or IP-address of the MQTT-Server."
    ::= { wtWebGraphAnalog57762MQTT 2 }

wtWebGraphAnalog57762MQTTUserName OBJECT-TYPE
    SYNTAX OCTET STRING
    ACCESS read-write
    STATUS mandatory
    DESCRIPTION
        "MQTT login  user name."
    ::= { wtWebGraphAnalog57762MQTT 3 }

wtWebGraphAnalog57762MQTTPassword OBJECT-TYPE
    SYNTAX OCTET STRING
    ACCESS read-write
    STATUS mandatory
    DESCRIPTION
        "MQTT login password."
    ::= { wtWebGraphAnalog57762MQTT 4 }

wtWebGraphAnalog57762MQTTLocalPort OBJECT-TYPE
    SYNTAX INTEGER
    ACCESS read-write
    STATUS mandatory
    DESCRIPTION
        "Local port number."
    ::= { wtWebGraphAnalog57762MQTT 5 }

wtWebGraphAnalog57762MQTTBrokerServerPort OBJECT-TYPE
    SYNTAX INTEGER
    ACCESS read-write
    STATUS mandatory
    DESCRIPTION
        "MQTT Server port number."
    ::= { wtWebGraphAnalog57762MQTT 6 }

wtWebGraphAnalog57762MQTTInterval OBJECT-TYPE
    SYNTAX INTEGER
    ACCESS read-write
    STATUS mandatory
    DESCRIPTION
        "Ping intervall, if no data has to be send: time in seconds."
    ::= { wtWebGraphAnalog57762MQTT 7 }

wtWebGraphAnalog57762MQTTLastWillEnable OBJECT-TYPE
    SYNTAX OCTET STRING
    ACCESS read-write
    STATUS mandatory
    DESCRIPTION
        "Bit 0 activate MQTT LastWill message:
        Octet 1: unused
        Octet 2: unused
        Octet 3: unused
        Octet 4:
        	Bit 1-7: unused
            Bit 0  : MQTT Last will enable"
    ::= { wtWebGraphAnalog57762MQTT 8 }

wtWebGraphAnalog57762MQTTLastWillTopic OBJECT-TYPE
    SYNTAX OCTET STRING
    ACCESS read-write
    STATUS mandatory
    DESCRIPTION
        "MQTT Last Will Topic."
    ::= { wtWebGraphAnalog57762MQTT 9 }

wtWebGraphAnalog57762MQTTLastWillMsg OBJECT-TYPE
    SYNTAX OCTET STRING
    ACCESS read-write
    STATUS mandatory
    DESCRIPTION
        "MQTT Last Will message."
    ::= { wtWebGraphAnalog57762MQTT 10 }

wtWebGraphAnalog57762MQTTLastWillQoS OBJECT-TYPE
    SYNTAX OCTET STRING (SIZE(4))
    ACCESS read-write
    STATUS mandatory
    DESCRIPTION
        "Binary coded MQTT Publish QoS:
        Octet 1: unused
        Octet 2: unused
        Octet 3: unused
        Octet 4:
		Bit 0:	QoS 0
        Bit 1:	QoS 1
        Bit 2:  QoS 2
        Bit 3-7:unused"
    ::= { wtWebGraphAnalog57762MQTT 11 }

wtWebGraphAnalog57762MQTTLastWillRetain OBJECT-TYPE
    SYNTAX OCTET STRING (SIZE(4))
    ACCESS read-write
    STATUS mandatory
    DESCRIPTION
        "Binary coded MQTT Publish Retain properties:
        Octet 1: unused
        Octet 2: unused
        Octet 3: unused
        Octet 4:
		Bit 0	: retain enable
        Bit 1-7	: unused"
    ::= { wtWebGraphAnalog57762MQTT 12 }

wtWebGraphAnalog57762MQTTLastWillConnectEnable OBJECT-TYPE
    SYNTAX OCTET STRING
    ACCESS read-write
    STATUS mandatory
    DESCRIPTION
        "Bit 0 activate MQTT LastWill Connect message:
        Octet 1: unused
        Octet 2: unused
        Octet 3: unused
        Octet 4:
        	Bit 1-7: unused
            Bit 0  : MQTT Last will connect message enable"
    ::= { wtWebGraphAnalog57762MQTT 13 }

wtWebGraphAnalog57762MQTTLastWillConnectMsg OBJECT-TYPE
    SYNTAX OCTET STRING
    ACCESS read-write
    STATUS mandatory
    DESCRIPTION
        "MQTT Last Will Connect message will be send with the QoS and Retain settings
		of the LastWill message."
    ::= { wtWebGraphAnalog57762MQTT 14 }

--  wtWebGraphAnalog57762REST Group
--------------------------------

wtWebGraphAnalog57762RESTEnable OBJECT-TYPE
    SYNTAX OCTET STRING
    ACCESS read-write
    STATUS mandatory
    DESCRIPTION
        "Bit 0 activates REST :
        Octet 1: unused
        Octet 2: unused
        Octet 3: unused
        Octet 4:
        	Bit 1-7: unused
            Bit 0  : REST enable"
    ::= { wtWebGraphAnalog57762REST 1 }

wtWebGraphAnalog57762RESTDigestAuthEnable OBJECT-TYPE
    SYNTAX OCTET STRING
    ACCESS read-write
    STATUS mandatory
    DESCRIPTION
        "Bit 0 activates Digest-Authentification:
        Octet 1: unused
        Octet 2: unused
        Octet 3: unused
        Octet 4:
        	Bit 1-7: unused
            Bit 0  : Digest Auth enable"
    ::= { wtWebGraphAnalog57762REST 2 }

-- wtWebGraphAnalog57762Datalogger Group
--------------------------------

wtWebGraphAnalog57762LoggerTimebase OBJECT-TYPE
    SYNTAX INTEGER {
    wtWebGraphAnalog57762Datalogger-15Sec(1),
    wtWebGraphAnalog57762Datalogger-30Sec(2),
    wtWebGraphAnalog57762Datalogger-1Min(3),
    wtWebGraphAnalog57762Datalogger-5Min(4),
    wtWebGraphAnalog57762Datalogger-15Min(5),
    wtWebGraphAnalog57762Datalogger-60Min(6)
    }
    ACCESS read-write
    STATUS mandatory
    DESCRIPTION
        "Time base of the data logger"
    ::= { wtWebGraphAnalog57762Datalogger 1 }

wtWebGraphAnalog57762LoggerSensorSel OBJECT-TYPE
    SYNTAX OCTET STRING (SIZE(4))
    ACCESS read-write
    STATUS mandatory
    DESCRIPTION
        "Binary coded trigger conditions:
        Octet 1: unused
        Octet 2: unused
        Octet 3: unused
        Octet 4:
        	Bit 0: Sensor 1
        	Bit 1: Sensor 2
        	Bit 2-7: unused"
    ::= { wtWebGraphAnalog57762Datalogger 2 }

-- wtWebGraphAnalog57762Alarm Group
----------------------------

wtWebGraphAnalog57762AlarmCount OBJECT-TYPE
    SYNTAX INTEGER (1..8)
    ACCESS read-only
    STATUS mandatory
    DESCRIPTION
        "Number of independent alarms."
    ::= { wtWebGraphAnalog57762Alarm 1 }

-- Alarm Interface Table

wtWebGraphAnalog57762AlarmIfTable OBJECT-TYPE
    SYNTAX SEQUENCE OF WtWebGraphAnalog57762AlarmIfEntry
    ACCESS not-accessible
    STATUS mandatory
    DESCRIPTION
        "List of alarm indices."
    ::= { wtWebGraphAnalog57762Alarm 2 }

wtWebGraphAnalog57762AlarmIfEntry OBJECT-TYPE
    SYNTAX WtWebGraphAnalog57762AlarmIfEntry
    ACCESS not-accessible
    STATUS mandatory
    DESCRIPTION
        "Numbers of the alarms."
    INDEX  { wtWebGraphAnalog57762AlarmNo }
    ::= { wtWebGraphAnalog57762AlarmIfTable 1 }

WtWebGraphAnalog57762AlarmIfEntry ::= SEQUENCE {
    wtWebGraphAnalog57762AlarmNo INTEGER
}

wtWebGraphAnalog57762AlarmNo OBJECT-TYPE
    SYNTAX INTEGER (1..8)
    ACCESS read-only
    STATUS mandatory
    DESCRIPTION
        "Alarm number."
    ::= { wtWebGraphAnalog57762AlarmIfEntry 1 }

-- Alarm Table

wtWebGraphAnalog57762AlarmTable OBJECT-TYPE
    SYNTAX SEQUENCE OF WtWebGraphAnalog57762AlarmEntry
    ACCESS not-accessible
    STATUS mandatory
    DESCRIPTION
        "List of settings depending on the alarm number."
    ::= { wtWebGraphAnalog57762Alarm 3 }

wtWebGraphAnalog57762AlarmEntry OBJECT-TYPE
    SYNTAX WtWebGraphAnalog57762AlarmEntry
    ACCESS not-accessible
    STATUS mandatory
    DESCRIPTION
        "Alarm parameters of the individual alarms."
    INDEX  { wtWebGraphAnalog57762AlarmNo }
    ::= { wtWebGraphAnalog57762AlarmTable 1 }

WtWebGraphAnalog57762AlarmEntry ::= SEQUENCE {
    wtWebGraphAnalog57762AlarmTrigger			OCTET STRING,
    wtWebGraphAnalog57762AlarmMin1			OCTET STRING,
    wtWebGraphAnalog57762AlarmMax1			OCTET STRING,
    wtWebGraphAnalog57762AlarmHysteresis1		OCTET STRING,
    wtWebGraphAnalog57762AlarmDelay			OCTET STRING,
    wtWebGraphAnalog57762AlarmInterval			OCTET STRING,
    wtWebGraphAnalog57762AlarmEnable			OCTET STRING,
    wtWebGraphAnalog57762AlarmEMailAddr			OCTET STRING,
    wtWebGraphAnalog57762AlarmMailSubject		OCTET STRING,
    wtWebGraphAnalog57762AlarmMailText			OCTET STRING,
    wtWebGraphAnalog57762AlarmManagerIP			OCTET STRING,
    wtWebGraphAnalog57762AlarmTrapText			OCTET STRING,
    wtWebGraphAnalog57762AlarmMailOptions		OCTET STRING,
    wtWebGraphAnalog57762AlarmTcpIpAddr			OCTET STRING,
    wtWebGraphAnalog57762AlarmTcpPort			INTEGER,
    wtWebGraphAnalog57762AlarmTcpText			OCTET STRING,
    wtWebGraphAnalog57762AlarmClearMailSubject		OCTET STRING,
    wtWebGraphAnalog57762AlarmClearMailText		OCTET STRING,
    wtWebGraphAnalog57762AlarmClearTrapText		OCTET STRING,
    wtWebGraphAnalog57762AlarmClearTcpText		OCTET STRING,
    wtWebGraphAnalog57762AlarmMin2			OCTET STRING,
    wtWebGraphAnalog57762AlarmMax2			OCTET STRING,
    wtWebGraphAnalog57762AlarmHysteresis2		OCTET STRING,
    wtWebGraphAnalog57762AlarmSyslogIpAddr		OCTET STRING,
    wtWebGraphAnalog57762AlarmSyslogPort		INTEGER,
    wtWebGraphAnalog57762AlarmSyslogText		OCTET STRING,
    wtWebGraphAnalog57762AlarmSyslogClearText		OCTET STRING,
    wtWebGraphAnalog57762AlarmFtpDataPort		OCTET STRING,
    wtWebGraphAnalog57762AlarmFtpFileName		OCTET STRING,
    wtWebGraphAnalog57762AlarmFtpText			OCTET STRING,
    wtWebGraphAnalog57762AlarmFtpClearText		OCTET STRING,
    wtWebGraphAnalog57762AlarmFtpOption			OCTET STRING,
    wtWebGraphAnalog57762AlarmTimerCron			OCTET STRING,
    wtWebGraphAnalog57762AlarmDeltaTemp			OCTET STRING,
    wtWebGraphAnalog57762AlarmName 				OCTET STRING,
    wtWebGraphAnalog57762AlarmActive 			OCTET STRING,
    wtWebGraphAnalog57762AlarmHttpReqAuthEnable		OCTET STRING,
    wtWebGraphAnalog57762AlarmHttpReqAuthUser		OCTET STRING,
    wtWebGraphAnalog57762AlarmHttpReqAuthPassword		OCTET STRING,
    wtWebGraphAnalog57762AlarmHttpReqSetUrl			OCTET STRING,
    wtWebGraphAnalog57762AlarmHttpReqClearUrl		OCTET STRING,
    wtWebGraphAnalog57762AlarmHttpReqServerPort		INTEGER,
    wtWebGraphAnalog57762AlarmMqttTopicPath			OCTET STRING,
    wtWebGraphAnalog57762AlarmMqttTopicSetTopic		OCTET STRING,
    wtWebGraphAnalog57762AlarmMqttTopicClear		OCTET STRING,
    wtWebGraphAnalog57762AlarmSensorLostSelection		OCTET STRING,
    wtWebGraphAnalog57762AlarmLimitWindow			OCTET STRING,
    wtWebGraphAnalog57762AlarmSnmpManagerPort		INTEGER,
    wtWebGraphAnalog57762AlarmMqttQoS			OCTET STRING,
    wtWebGraphAnalog57762AlarmMqttRetain			OCTET STRING

}

wtWebGraphAnalog57762AlarmTrigger OBJECT-TYPE
    SYNTAX OCTET STRING (SIZE(4))
    ACCESS read-write
    STATUS mandatory
    DESCRIPTION
        "Binary coded trigger conditions:
        Octet 1: unused
        Octet 2: unused
        Octet 3:
        	Bit 0: Timer
        	Bit 1: ColdStart
        	Bit 2: WarmStart

        Octet 4:
        	Bit 0: Sensor 1
        	Bit 1: Sensor 2
        	Bit 2-7: unused"
    ::= { wtWebGraphAnalog57762AlarmEntry 1 }

wtWebGraphAnalog57762AlarmMin1 OBJECT-TYPE
    SYNTAX OCTET STRING
    ACCESS read-write
    STATUS mandatory
    DESCRIPTION
        "Minimum sensor 1 with maximum 3 decimal places."
    ::= { wtWebGraphAnalog57762AlarmEntry 2 }

wtWebGraphAnalog57762AlarmMax1 OBJECT-TYPE
    SYNTAX OCTET STRING
    ACCESS read-write
    STATUS mandatory
    DESCRIPTION
        "Maximum sensor 1 with maximum 3 decimal places."
    ::= { wtWebGraphAnalog57762AlarmEntry 3 }

wtWebGraphAnalog57762AlarmHysteresis1 OBJECT-TYPE
    SYNTAX OCTET STRING
    ACCESS read-write
    STATUS mandatory
    DESCRIPTION
        "Reading changes of this size clears the alarm state (MAX-hyst, MIN+hyst.)
        with maximum 3 decimal places."
    ::= { wtWebGraphAnalog57762AlarmEntry 4 }

wtWebGraphAnalog57762AlarmDelay OBJECT-TYPE
    SYNTAX OCTET STRING
    ACCESS read-write
    STATUS mandatory
    DESCRIPTION
        "Alarm will be delayed by setting this time while stable alarm
        condition occur (time in minutes)."
    ::= { wtWebGraphAnalog57762AlarmEntry 5 }


wtWebGraphAnalog57762AlarmInterval OBJECT-TYPE
    SYNTAX OCTET STRING
    ACCESS read-write
    STATUS mandatory
    DESCRIPTION
        "Send interval for alarm messages."
    ::= { wtWebGraphAnalog57762AlarmEntry 6 }

wtWebGraphAnalog57762AlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  TCP Client enable"
    ::= { wtWebGraphAnalog57762AlarmEntry 7 }

wtWebGraphAnalog57762AlarmEMailAddr OBJECT-TYPE
    SYNTAX OCTET STRING
    ACCESS read-write
    STATUS mandatory
    DESCRIPTION
        "E-Mail address for sending the alarm mail to."
    ::= { wtWebGraphAnalog57762AlarmEntry 8 }

wtWebGraphAnalog57762AlarmMailSubject OBJECT-TYPE
    SYNTAX OCTET STRING
    ACCESS read-write
    STATUS mandatory
    DESCRIPTION
        "Subject line for alarm mail."
    ::= { wtWebGraphAnalog57762AlarmEntry 9 }

wtWebGraphAnalog57762AlarmMailText OBJECT-TYPE
    SYNTAX OCTET STRING
    ACCESS read-write
    STATUS mandatory
    DESCRIPTION
        "Alarm mail text: <Mn> provides the current temperature; n = 1..2.
        <Z> provides the current time."
    ::= { wtWebGraphAnalog57762AlarmEntry 10 }

wtWebGraphAnalog57762AlarmManagerIP OBJECT-TYPE
    SYNTAX OCTET STRING
    ACCESS read-write
    STATUS mandatory
    DESCRIPTION
        "Name or IP address of the SNMP Manager which accepts the trap."
    ::= { wtWebGraphAnalog57762AlarmEntry 11 }

wtWebGraphAnalog57762AlarmTrapText OBJECT-TYPE
    SYNTAX OCTET STRING
    ACCESS read-write
    STATUS mandatory
    DESCRIPTION
        "This text is sent in the trap body."
    ::= { wtWebGraphAnalog57762AlarmEntry 12 }

wtWebGraphAnalog57762AlarmMailOptions OBJECT-TYPE
    SYNTAX OCTET STRING (SIZE(4))
    ACCESS read-write
    STATUS mandatory
    DESCRIPTION
        "Binary coded options:
        Octet 1: unused
        Octet 2: unused
        Octet 3: unused
        Octet 4:
		Bit 0  :	Attach Thermo.csv Enable
		Bit 1  :	CSV-Data_since_last_report
        	Bit 2-7:	unused"
    ::= { wtWebGraphAnalog57762AlarmEntry 13 }

wtWebGraphAnalog57762AlarmTcpIpAddr OBJECT-TYPE
    SYNTAX OCTET STRING
    ACCESS read-write
    STATUS mandatory
    DESCRIPTION
        "Name or IP address of the TCP server which accepts the trap."
    ::= { wtWebGraphAnalog57762AlarmEntry 14 }

wtWebGraphAnalog57762AlarmTcpPort OBJECT-TYPE
    SYNTAX INTEGER (1..65535)
    ACCESS read-write
    STATUS mandatory
    DESCRIPTION
        "Port number of the TCP server which accepts the trap."
    ::= { wtWebGraphAnalog57762AlarmEntry 15 }

wtWebGraphAnalog57762AlarmTcpText OBJECT-TYPE
    SYNTAX OCTET STRING
    ACCESS read-write
    STATUS mandatory
    DESCRIPTION
        "This text is sent in the TCP trap body."
    ::= { wtWebGraphAnalog57762AlarmEntry 16 }

wtWebGraphAnalog57762AlarmClearMailSubject OBJECT-TYPE
    SYNTAX OCTET STRING
    ACCESS read-write
    STATUS mandatory
    DESCRIPTION
        "Subject line for alarm clear mail."
    ::= { wtWebGraphAnalog57762AlarmEntry 17 }

wtWebGraphAnalog57762AlarmClearMailText OBJECT-TYPE
    SYNTAX OCTET STRING
    ACCESS read-write
    STATUS mandatory
    DESCRIPTION
        "Alarm clear mail text: <Mn> provides the current temperature; n = 1..2.
        <Z> provides the current time."
    ::= { wtWebGraphAnalog57762AlarmEntry 18 }

wtWebGraphAnalog57762AlarmClearTrapText OBJECT-TYPE
    SYNTAX OCTET STRING
    ACCESS read-write
    STATUS mandatory
    DESCRIPTION
        "This text is sent in the trap body."
    ::= { wtWebGraphAnalog57762AlarmEntry 19 }

wtWebGraphAnalog57762AlarmClearTcpText OBJECT-TYPE
    SYNTAX OCTET STRING
    ACCESS read-write
    STATUS mandatory
    DESCRIPTION
        "This text is sent in the TCP trap body."
    ::= { wtWebGraphAnalog57762AlarmEntry 20 }

wtWebGraphAnalog57762AlarmMin2 OBJECT-TYPE
    SYNTAX OCTET STRING
    ACCESS read-write
    STATUS mandatory
    DESCRIPTION
        "Minimum sensor 2 with maximum 3 decimal places."
    ::= { wtWebGraphAnalog57762AlarmEntry 21 }

wtWebGraphAnalog57762AlarmMax2 OBJECT-TYPE
    SYNTAX OCTET STRING
    ACCESS read-write
    STATUS mandatory
    DESCRIPTION
        "Maximum sensor 2 with maximum 2 decimal places."
    ::= { wtWebGraphAnalog57762AlarmEntry 22 }

wtWebGraphAnalog57762AlarmHysteresis2 OBJECT-TYPE
    SYNTAX OCTET STRING
    ACCESS read-write
    STATUS mandatory
    DESCRIPTION
        "Hysterese rel. sensor 2 with maximum 3 decimal places."
    ::= { wtWebGraphAnalog57762AlarmEntry 23 }

wtWebGraphAnalog57762AlarmSyslogIpAddr OBJECT-TYPE
    SYNTAX OCTET STRING
    ACCESS read-write
    STATUS mandatory
    DESCRIPTION
        "IP address of the syslog server to which the Webio device should send syslog messages."
    ::= { wtWebGraphAnalog57762AlarmEntry 24 }

wtWebGraphAnalog57762AlarmSyslogPort OBJECT-TYPE
    SYNTAX INTEGER (1..65535)
    ACCESS read-write
    STATUS mandatory
    DESCRIPTION
        "Port number of the syslog server to which the Webio device should send syslog messages."
    ::= { wtWebGraphAnalog57762AlarmEntry 25 }

wtWebGraphAnalog57762AlarmSyslogText OBJECT-TYPE
    SYNTAX OCTET STRING
    ACCESS read-write
    STATUS mandatory
    DESCRIPTION
        "Every message starts with the priority key, a time stamp and the host ip address, according RFC3164.
        This text appears in the following syslog message body."
    ::= { wtWebGraphAnalog57762AlarmEntry 26 }

wtWebGraphAnalog57762AlarmSyslogClearText OBJECT-TYPE
    SYNTAX OCTET STRING
    ACCESS read-write
    STATUS mandatory
    DESCRIPTION
        "Every message starts with the priority key, a time stamp and the host ip address, according RFC3164.
        This text appears in the following syslog message body of a alarm clear message."
    ::= { wtWebGraphAnalog57762AlarmEntry 27 }

wtWebGraphAnalog57762AlarmFtpDataPort OBJECT-TYPE
    SYNTAX OCTET STRING
    ACCESS read-write
    STATUS mandatory
    DESCRIPTION
        "Local data port: 1..65535 or AUTO: the next free port will be assigned."
    ::= { wtWebGraphAnalog57762AlarmEntry 28 }

wtWebGraphAnalog57762AlarmFtpFileName OBJECT-TYPE
    SYNTAX OCTET STRING
    ACCESS read-write
    STATUS mandatory
    DESCRIPTION
        "Name of the file including path informations."
    ::= { wtWebGraphAnalog57762AlarmEntry 29 }

wtWebGraphAnalog57762AlarmFtpText OBJECT-TYPE
    SYNTAX OCTET STRING
    ACCESS read-write
    STATUS mandatory
    DESCRIPTION
        "Message text to store on the FTP server."
    ::= { wtWebGraphAnalog57762AlarmEntry 30 }

wtWebGraphAnalog57762AlarmFtpClearText OBJECT-TYPE
    SYNTAX OCTET STRING
    ACCESS read-write
    STATUS mandatory
    DESCRIPTION
        "Alarm clear message to store on the FTP server."
    ::= { wtWebGraphAnalog57762AlarmEntry 31 }

wtWebGraphAnalog57762AlarmFtpOption OBJECT-TYPE
    SYNTAX OCTET STRING (SIZE(4))
    ACCESS read-write
    STATUS mandatory
    DESCRIPTION
        "Binary coded options, select only one option at the same time:
        STORE  = replace file
        APPEND = append message at the end of the file

        Octet 1: unused
        Octet 2: unused
        Octet 3: unused
        Octet 4:
		Bit 0  :	STORE
		Bit 1  :	APPEND
        	Bit 2-7:	unused"
    ::= { wtWebGraphAnalog57762AlarmEntry 32 }

wtWebGraphAnalog57762AlarmTimerCron OBJECT-TYPE
    SYNTAX OCTET STRING
    ACCESS read-write
    STATUS mandatory
    DESCRIPTION
        "This entry defines a time window for alarm 1-8 and a activation time for the report.
        A time window is definied by start and stop time stamp, seperated by a space or tab.
        The activation time of the report is defined by a single start time stamp.
        Each time stamp contains 5 space or tab seperated text fields for time trigger definition.
        Each field must match with the actual time to trigger an action, weekday and day of month
        are interpreted separatley.
        1: Minutes	Range 0-59
        2. Hours	Range 0-23, 0 is midnight
        3: Day of month	Range 1-31
        4: Month	Range 1-12
        5: Weekday	Range 0-6, 0 is sunday

        Syntax for every field:
         - an asterix (*) enables every possible setting of a field
         - single numbers seperated by commas (i.e.: 2,14,22)
         - a partition within the allowed range (i.e.: 1-5)
         - step size within a partition of the allowed range (i.e.: 0-59/2  every second minute)."
    ::= { wtWebGraphAnalog57762AlarmEntry 33 }

-- __JB__
wtWebGraphAnalog57762AlarmName OBJECT-TYPE
    SYNTAX OCTET STRING
    ACCESS read-write
    STATUS mandatory
    DESCRIPTION
        "Alert name"
    ::= { wtWebGraphAnalog57762AlarmEntry 39 }

-- __JB__
wtWebGraphAnalog57762AlarmActive OBJECT-TYPE
    SYNTAX OCTET STRING
    ACCESS read-write
    STATUS mandatory
    DESCRIPTION
        "Alert active
			1 = ON
			0 = OFF"
    ::= { wtWebGraphAnalog57762AlarmEntry 40 }

wtWebGraphAnalog57762AlarmHttpReqAuthEnable OBJECT-TYPE
    SYNTAX OCTET STRING
    ACCESS read-write
    STATUS mandatory
    DESCRIPTION
        "Binary coded options, select only one option at the same time:
        OCTET 1: unused
        OCTET 2: unused
        OCTET 3: unused
        OCTET 4, Bit 1-7: unused
        Bit 0  : HHTP Request Authentication enable"
    ::= { wtWebGraphAnalog57762AlarmEntry 61 }

wtWebGraphAnalog57762AlarmHttpReqAuthUser OBJECT-TYPE
    SYNTAX OCTET STRING
    ACCESS read-write
    STATUS mandatory
    DESCRIPTION
	"HTTP Request: User"
    ::= { wtWebGraphAnalog57762AlarmEntry 62 }

wtWebGraphAnalog57762AlarmHttpReqAuthPassword OBJECT-TYPE
    SYNTAX OCTET STRING
    ACCESS read-write
    STATUS mandatory
    DESCRIPTION
	"HTTP Request: Password"
    ::= { wtWebGraphAnalog57762AlarmEntry 63 }

wtWebGraphAnalog57762AlarmHttpReqSetUrl OBJECT-TYPE
    SYNTAX OCTET STRING
    ACCESS read-write
    STATUS mandatory
    DESCRIPTION
	"HTTP Request: Set URL"
    ::= { wtWebGraphAnalog57762AlarmEntry 64 }

wtWebGraphAnalog57762AlarmHttpReqClearUrl OBJECT-TYPE
    SYNTAX OCTET STRING
    ACCESS read-write
    STATUS mandatory
    DESCRIPTION
	"HTTP Request: Clear URL"
    ::= { wtWebGraphAnalog57762AlarmEntry 65 }

wtWebGraphAnalog57762AlarmHttpReqServerPort OBJECT-TYPE
    SYNTAX INTEGER (1..65535)
    ACCESS read-write
    STATUS mandatory
    DESCRIPTION
	"HTTP Request: Server Port"
    ::= { wtWebGraphAnalog57762AlarmEntry 66 }

wtWebGraphAnalog57762AlarmMqttTopicPath OBJECT-TYPE
    SYNTAX OCTET STRING
    ACCESS read-write
    STATUS mandatory
    DESCRIPTION
	"MQTT Publish: Topic path"
    ::= { wtWebGraphAnalog57762AlarmEntry 67 }

wtWebGraphAnalog57762AlarmMqttTopicSetTopic OBJECT-TYPE
    SYNTAX OCTET STRING
    ACCESS read-write
    STATUS mandatory
    DESCRIPTION
	"MQTT Publish: Topic SET message"
    ::= { wtWebGraphAnalog57762AlarmEntry 68 }

wtWebGraphAnalog57762AlarmMqttTopicClear OBJECT-TYPE
    SYNTAX OCTET STRING
    ACCESS read-write
    STATUS mandatory
    DESCRIPTION
	"MQTT Publish: Topic CLEAR message"
    ::= { wtWebGraphAnalog57762AlarmEntry 69 }

wtWebGraphAnalog57762AlarmSensorLostSelection OBJECT-TYPE
    SYNTAX OCTET STRING
    ACCESS read-write
    STATUS mandatory
    DESCRIPTION
        "Binary coded options:
        OCTET 1: unused
        OCTET 2: unused
        OCTET 3: unused
        OCTET 4, Bit 1-7: unused
        Bit 0  : Sensor 0"
    ::= { wtWebGraphAnalog57762AlarmEntry 70 }

wtWebGraphAnalog57762AlarmLimitWindow OBJECT-TYPE
    SYNTAX OCTET STRING
    ACCESS read-write
    STATUS mandatory
    DESCRIPTION
        "If window type is INSIDE the alarm is genereted when the temperature
        is greater minumum value and lower than maximum value. If window type is OUTSIDE
        the alarm is generated when the measured value is lower than the minimum value
        or greater than the maximum value.
		Binary coded options, select only one option at the same time:
        OCTET 1: unused
        OCTET 2: unused
        OCTET 3: unused
        OCTET 4, Bit 2-7: unused
		Bit 1  : inside window
        Bit 0  : outside window"
    ::= { wtWebGraphAnalog57762AlarmEntry 71 }

wtWebGraphAnalog57762AlarmSnmpManagerPort OBJECT-TYPE
    SYNTAX INTEGER
    ACCESS read-write
    STATUS mandatory
    DESCRIPTION
        "Port number of the SNMP Manager to which the Webio device should send SNMP traps."
    ::= { wtWebGraphAnalog57762AlarmEntry 76 }

wtWebGraphAnalog57762AlarmMqttQoS OBJECT-TYPE
    SYNTAX OCTET STRING (SIZE(4))
    ACCESS read-write
    STATUS mandatory
    DESCRIPTION
        "Binary coded value:
        Octet 1: unused
        Octet 2: unused
        Octet 3: unused
        Octet 4:
		Bit 0:	QoS 0
        	Bit 1:	QoS 1
        	Bit 2:  QoS 2
        	Bit 3-7:unused"
    ::= { wtWebGraphAnalog57762AlarmEntry 77 }

wtWebGraphAnalog57762AlarmMqttRetain OBJECT-TYPE
    SYNTAX OCTET STRING (SIZE(4))
    ACCESS read-write
    STATUS mandatory
    DESCRIPTION
        "Binary coded value:
        Octet 1: unused
        Octet 2: unused
        Octet 3: unused
        Octet 4:
		Bit 0	: retain enable
        	Bit 1-7	: unused"
    ::= { wtWebGraphAnalog57762AlarmEntry 78 }

-- wtWebGraphAnalog57762GraphicsBase Group
----------------------------

wtWebGraphAnalog57762GraphicsBaseEnable OBJECT-TYPE
    SYNTAX OCTET STRING
    ACCESS read-write
    STATUS mandatory
    DESCRIPTION
        "Defines the viewing options of the graphic:
        Octet 1: unused
        Octet 2: unused
        Octet 3: unused
        Octet 4:
                Bit 0  : Auto scroll enable
                Bit 1  : Show table
                Bit 2  : Show graph
                Bit 3  : Show control buttons
                Bit 4  : Show config menu
                Bit 5-7: unused"
    ::= { wtWebGraphAnalog57762GraphicsBase 1 }

wtWebGraphAnalog57762GraphicsBaseWidth OBJECT-TYPE
    SYNTAX INTEGER
    ACCESS read-write
    STATUS mandatory
    DESCRIPTION
        "Defines the width of the graphic in pixels."
    ::= { wtWebGraphAnalog57762GraphicsBase 2 }

wtWebGraphAnalog57762GraphicsBaseHeight OBJECT-TYPE
        SYNTAX INTEGER
        ACCESS read-write
        STATUS mandatory
        DESCRIPTION
            "Defines the height of the graphic in pixels."
        ::= { wtWebGraphAnalog57762GraphicsBase 3 }

wtWebGraphAnalog57762GraphicsBaseFrameColor OBJECT-TYPE
    SYNTAX OCTET STRING (SIZE(3))
    ACCESS read-write
    STATUS mandatory
    DESCRIPTION
        "Frame color definition in RGB."
    ::= { wtWebGraphAnalog57762GraphicsBase 4 }

wtWebGraphAnalog57762GraphicsBaseBackgroundColor OBJECT-TYPE
    SYNTAX OCTET STRING (SIZE(3))
    ACCESS read-write
    STATUS mandatory
    DESCRIPTION
        "Background color definition in RGB."
    ::= { wtWebGraphAnalog57762GraphicsBase 5 }

wtWebGraphAnalog57762GraphicsBasePollingrate OBJECT-TYPE
        SYNTAX INTEGER
        ACCESS read-write
        STATUS mandatory
        DESCRIPTION
            "Defines the pollingrate in seconds,
            which defines the refreshing intervall of the graphic."
        ::= { wtWebGraphAnalog57762GraphicsBase 6 }

-- wtWebGraphAnalog57762GraphicsSelect Group
----------------------------

wtWebGraphAnalog57762GraphicsSelectDisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1: Sensor 2
        	Bit 2-7: unused"
    ::= { wtWebGraphAnalog57762GraphicsSelect 1 }

wtWebGraphAnalog57762GraphicsSelectDisplayShowExtrem OBJECT-TYPE
    SYNTAX OCTET STRING (SIZE(4))
    ACCESS read-write
    STATUS mandatory
    DESCRIPTION
        "Binary coded sensor selection:
        only selected sensors will be shown with minima and maxima:
        Octet 1: unused
        Octet 2: unused
        Octet 3: unused
        Octet 4:
        	Bit 0: Sensor 1
        	Bit 1: Sensor 2
        	Bit 2-7: unused"
     ::= { wtWebGraphAnalog57762GraphicsSelect 2 }

-- Graph Sensor Color Table

wtWebGraphAnalog57762SensorColor2Table OBJECT-TYPE
    SYNTAX SEQUENCE OF WtWebGraphAnalog57762SensorColor2Entry
    ACCESS not-accessible
    STATUS mandatory
    DESCRIPTION
        "List of sensor colors for the praphical presentation."
    ::= { wtWebGraphAnalog57762GraphicsSelect 3 }

wtWebGraphAnalog57762SensorColor2Entry OBJECT-TYPE
    SYNTAX WtWebGraphAnalog57762SensorColor2Entry
    ACCESS not-accessible
    STATUS mandatory
    DESCRIPTION
        "Numbers of the sensors."
    INDEX  { wtWebGraphAnalog57762SensorNo }
    ::= { wtWebGraphAnalog57762SensorColor2Table 1 }

WtWebGraphAnalog57762SensorColor2Entry ::= SEQUENCE {
    wtWebGraphAnalog57762GraphicsSensorColor OCTET STRING,
    wtWebGraphAnalog57762GraphicsSelectScale OCTET STRING
}

wtWebGraphAnalog57762GraphicsSensorColor OBJECT-TYPE
    SYNTAX OCTET STRING (SIZE(3))
    ACCESS read-write
    STATUS mandatory
    DESCRIPTION
        "Color of the sensors at the praphical presention."
    ::= { wtWebGraphAnalog57762SensorColor2Entry 1 }

wtWebGraphAnalog57762GraphicsSelectScale OBJECT-TYPE
    SYNTAX OCTET STRING
    ACCESS read-write
    STATUS mandatory
    DESCRIPTION
        "Assignes one of 4 scales to a sensor:
        Octet 1: unused
        Octet 2: unused
        Octet 3: unused
        Octet 4:
                Bit 0  : Use Scale 1
                Bit 1  : Use Scale 2
                Bit 2-7: unused"
    ::= { wtWebGraphAnalog57762SensorColor2Entry 2 }

-- wtWebGraphAnalog57762GraphicsScale Group
----------------------------

wtWebGraphAnalog57762GraphicsScaleAutoScaleEnable OBJECT-TYPE
    SYNTAX OCTET STRING
    ACCESS read-write
    STATUS mandatory
    DESCRIPTION
        "Select the Auto Scale Mode:
        Octet 1: unused
        Octet 2: unused
        Octet 3: unused
        Octet 4:
                Bit 0  : Scale 1 Auto scale enable
                Bit 1  : Scale 2 Auto scale enable
                Bit 2-7: unused"
    ::= { wtWebGraphAnalog57762GraphicsScale 1 }


wtWebGraphAnalog57762GraphicsScaleAutoFitEnable OBJECT-TYPE
    SYNTAX OCTET STRING
    ACCESS read-write
    STATUS mandatory
    DESCRIPTION
        "Select the Auto Fit Mode::
        Octet 1: unused
        Octet 2: unused
        Octet 3: unused
        Octet 4:
                Bit 0  : Scale 1 Auto fit enable
                Bit 1  : Scale 2 Auto fit enable
                Bit 2-7: unused"
    ::= { wtWebGraphAnalog57762GraphicsScale 2 }

wtWebGraphAnalog57762GraphicsScale1Min OBJECT-TYPE
    SYNTAX INTEGER
    ACCESS read-only
    STATUS mandatory
    DESCRIPTION
        "Scale 1: Minimum."
    ::= { wtWebGraphAnalog57762GraphicsScale 3 }

wtWebGraphAnalog57762GraphicsScale2Min OBJECT-TYPE
    SYNTAX INTEGER
    ACCESS read-only
    STATUS mandatory
    DESCRIPTION
        "Scale 2: Minimum."
    ::= { wtWebGraphAnalog57762GraphicsScale 4 }

wtWebGraphAnalog57762GraphicsScale1Max OBJECT-TYPE
    SYNTAX INTEGER
    ACCESS read-only
    STATUS mandatory
    DESCRIPTION
        "Scale 1: Maximum."
    ::= { wtWebGraphAnalog57762GraphicsScale 7 }

wtWebGraphAnalog57762GraphicsScale2Max OBJECT-TYPE
    SYNTAX INTEGER
    ACCESS read-only
    STATUS mandatory
    DESCRIPTION
        "Scale 2: Maximum."
    ::= { wtWebGraphAnalog57762GraphicsScale 8 }

wtWebGraphAnalog57762GraphicsScale1Unit OBJECT-TYPE
    SYNTAX OCTET STRING
    ACCESS read-only
    STATUS mandatory
    DESCRIPTION
        "Scale 1: Unit."
    ::= { wtWebGraphAnalog57762GraphicsScale 11 }

wtWebGraphAnalog57762GraphicsScale2Unit OBJECT-TYPE
    SYNTAX OCTET STRING
    ACCESS read-only
    STATUS mandatory
    DESCRIPTION
        "Scale 2: Unit."
    ::= { wtWebGraphAnalog57762GraphicsScale 12 }

-- wtWebGraphAnalog57762Ports Group
----------------------------

-- Table

wtWebGraphAnalog57762PortTable OBJECT-TYPE
    SYNTAX SEQUENCE OF WtWebGraphAnalog57762PortEntry
    ACCESS not-accessible
    STATUS mandatory
    DESCRIPTION
        "List of settings depending on the sensor number."
    ::= { wtWebGraphAnalog57762Ports 1 }

wtWebGraphAnalog57762PortEntry OBJECT-TYPE
    SYNTAX WtWebGraphAnalog57762PortEntry
    ACCESS not-accessible
    STATUS mandatory
    DESCRIPTION
        "Sensor parameters for the individual sensors."
    INDEX  { wtWebGraphAnalog57762SensorNo }
    ::= { wtWebGraphAnalog57762PortTable 1 }

WtWebGraphAnalog57762PortEntry ::= SEQUENCE {
    wtWebGraphAnalog57762PortName		OCTET STRING,
    wtWebGraphAnalog57762PortText		OCTET STRING,
    wtWebGraphAnalog57762PortOffset1		OCTET STRING,
    wtWebGraphAnalog57762SetPoint1		OCTET STRING,
    wtWebGraphAnalog57762PortOffset2		OCTET STRING,
    wtWebGraphAnalog57762SetPoint2		OCTET STRING,
    wtWebGraphAnalog57762PortComment		OCTET STRING,
    wtWebGraphAnalog57762PortSensorSelect	OCTET STRING,
    wtWebGraphAnalog57762PortUnit		OCTET STRING,
    wtWebGraphAnalog57762PortScale0		OCTET STRING,
    wtWebGraphAnalog57762PortScale100		OCTET STRING,
    wtWebGraphAnalog57762PortOutputMode		OCTET STRING,
    wtWebGraphAnalog57762PortInputMode		OCTET STRING,
    wtWebGraphAnalog57762PortPresetValue	OCTET STRING
}

wtWebGraphAnalog57762PortName OBJECT-TYPE
    SYNTAX OCTET STRING
    ACCESS read-write
    STATUS mandatory
    DESCRIPTION
        "Name of the sensor."
    ::= { wtWebGraphAnalog57762PortEntry 1 }

wtWebGraphAnalog57762PortText OBJECT-TYPE
    SYNTAX OCTET STRING
    ACCESS read-write
    STATUS mandatory
    DESCRIPTION
        "Description of the sensor."
    ::= { wtWebGraphAnalog57762PortEntry 2 }

wtWebGraphAnalog57762PortOffset1 OBJECT-TYPE
    SYNTAX OCTET STRING
    ACCESS read-write
    STATUS mandatory
    DESCRIPTION
        "Offset calibration: Offset in degrees with maximum 3 decimal places at set point 1."
    ::= { wtWebGraphAnalog57762PortEntry 3 }

wtWebGraphAnalog57762SetPoint1 OBJECT-TYPE
    SYNTAX OCTET STRING
    ACCESS read-write
    STATUS mandatory
    DESCRIPTION
        "Offset calibration: Reference set point 1 in degrees with maximum 3 decimal places."
    ::= { wtWebGraphAnalog57762PortEntry 4 }

wtWebGraphAnalog57762PortOffset2 OBJECT-TYPE
    SYNTAX OCTET STRING
    ACCESS read-write
    STATUS mandatory
    DESCRIPTION
        "Offset calibration: Offset in degrees with maximum 3 decimal places at set point 2."
    ::= { wtWebGraphAnalog57762PortEntry 5 }

wtWebGraphAnalog57762SetPoint2 OBJECT-TYPE
    SYNTAX OCTET STRING
    ACCESS read-write
    STATUS mandatory
    DESCRIPTION
        "Offset calibration: Reference set point 2 in degrees with maximum 3 decimal places."
    ::= { wtWebGraphAnalog57762PortEntry 6 }

wtWebGraphAnalog57762PortComment OBJECT-TYPE
    SYNTAX OCTET STRING
    ACCESS read-write
    STATUS mandatory
    DESCRIPTION
        "Offset calibration: informations of date, name of operator, reference devices."
    ::= { wtWebGraphAnalog57762PortEntry 7 }

wtWebGraphAnalog57762PortSensorSelect OBJECT-TYPE
    SYNTAX OCTET STRING (SIZE(4))
    ACCESS read-write
    STATUS mandatory
    DESCRIPTION
        "Binary coded options for sensor 1:
        Octet 1: unused
        Octet 2: unused
        Octet 3: unused
        Octet 4:
		Bit 0  :	0-20mA (default)
		Bit 1  :	4-20mA
		Bit 2  :	Disconnect
        	Bit 3-7:	unused"
    ::= { wtWebGraphAnalog57762PortEntry 8 }

wtWebGraphAnalog57762PortUnit OBJECT-TYPE
    SYNTAX OCTET STRING
    ACCESS read-write
    STATUS mandatory
    DESCRIPTION
        "User scale: displayed unit."
    ::= { wtWebGraphAnalog57762PortEntry 9 }

wtWebGraphAnalog57762PortScale0 OBJECT-TYPE
    SYNTAX OCTET STRING
    ACCESS read-write
    STATUS mandatory
    DESCRIPTION
        "User scale: displayed value in 1/1000 at 0% full scale range.
        Range: -999999.999 to 999999.999"
    ::= { wtWebGraphAnalog57762PortEntry 10 }

wtWebGraphAnalog57762PortScale100 OBJECT-TYPE
    SYNTAX OCTET STRING
    ACCESS read-write
    STATUS mandatory
    DESCRIPTION
        "User scale: displayed value in 1/1000 at 100% full scale range.
        Range: -999999.999 to 999999.999"
    ::= { wtWebGraphAnalog57762PortEntry 11 }

wtWebGraphAnalog57762PortOutputMode OBJECT-TYPE
    SYNTAX OCTET STRING (SIZE (4))
    ACCESS read-write
    STATUS mandatory
    DESCRIPTION
        "This binary coded output mode defines the individual operation mode for any
        output. More than one mode must not be selected. If an output mode is selected,
        Bit 2 in wtWebGraphAnalog57762PortInputMode will be set automatically.
        The OCTETS are interpreted bit-by-bit, Bit 0 corresponds to the LSB.
        OCTET 1: unused
        OCTET 2: unused
        OCTET 3: unused
        OCTET 4: Bit 6-7: unused
        	 Bit 5  : Output OFF
        	 Bit 4  : Binary 2
        	 Bit 3  : Binary 1
        	 Bit 2  : SNMP
        	 Bit 1  : UDP ASCII
        	 Bit 0  : HTTP"
    ::= { wtWebGraphAnalog57762PortEntry 12 }

wtWebGraphAnalog57762PortInputMode OBJECT-TYPE
    SYNTAX OCTET STRING (SIZE (4))
    ACCESS read-write
    STATUS mandatory
    DESCRIPTION
        "This binary coded input mode defines the individual operation mode for any
        input. More than one mode must not be selected. If an input mode is selected,
        Bit 5 in wtWebGraphAnalog57762PortOutputMode will be set automatically.
        The OCTETS are interpreted bit-by-bit,Bit 0 corresponds to the LSB.
        OCTET 1: ungenutzt
        OCTET 2: ungenutzt
        OCTET 3: ungenutzt
        OCTET 4: Bit 3-7: unused
        	 Bit 2  : I-Output
        	 Bit 1  : I-Input, active
        	 Bit 0  : I-Input, passive"
    ::= { wtWebGraphAnalog57762PortEntry 13 }

wtWebGraphAnalog57762PortPresetValue OBJECT-TYPE
    SYNTAX OCTET STRING
    ACCESS read-write
    STATUS mandatory
    DESCRIPTION
        "This value will be set after reset or initialisation."
    ::= { wtWebGraphAnalog57762PortEntry 16 }

-- wtWebGraphAnalog57762Manufact Group
----------------------------

wtWebGraphAnalog57762MfName OBJECT-TYPE
    SYNTAX OCTET STRING
    ACCESS read-write
    STATUS mandatory
    DESCRIPTION
        "Manufacturer company name"
    ::= { wtWebGraphAnalog57762Manufact 1 }

wtWebGraphAnalog57762MfAddr OBJECT-TYPE
    SYNTAX OCTET STRING
    ACCESS read-write
    STATUS mandatory
    DESCRIPTION
        "Manufacturer address."
    ::= { wtWebGraphAnalog57762Manufact 2 }

wtWebGraphAnalog57762MfHotline OBJECT-TYPE
    SYNTAX OCTET STRING
    ACCESS read-write
    STATUS mandatory
    DESCRIPTION
        "Manufacturer hotline."
    ::= { wtWebGraphAnalog57762Manufact 3 }

wtWebGraphAnalog57762MfInternet OBJECT-TYPE
    SYNTAX OCTET STRING
    ACCESS read-write
    STATUS mandatory
    DESCRIPTION
        "Manufacturer Internet address."
    ::= { wtWebGraphAnalog57762Manufact 4 }

wtWebGraphAnalog57762MfDeviceTyp OBJECT-TYPE
    SYNTAX OCTET STRING
    ACCESS read-write
    STATUS mandatory
    DESCRIPTION
        "Manufacturer device name (model number)."
    ::= { wtWebGraphAnalog57762Manufact 5 }

wtWebGraphAnalog57762MfOrderNo OBJECT-TYPE
    SYNTAX OCTET STRING
    ACCESS read-write
    STATUS mandatory
    DESCRIPTION
        "Manufacturer part number."
    ::= { wtWebGraphAnalog57762Manufact 6 }

-- wtWebGraphAnalog57762Diag Group
----------------------------

wtWebGraphAnalog57762DiagErrorCount OBJECT-TYPE
    SYNTAX INTEGER
    ACCESS read-only
    STATUS mandatory
    DESCRIPTION
        "Number of entries in the error memory."
    ::= { wtWebGraphAnalog57762Diag 1 }

wtWebGraphAnalog57762DiagBinaryError OBJECT-TYPE
    SYNTAX OCTET STRING
    ACCESS read-only
    STATUS mandatory
    DESCRIPTION
        "Error causes coded bit-by-bit."
    ::= { wtWebGraphAnalog57762Diag 2 }

wtWebGraphAnalog57762DiagErrorIndex OBJECT-TYPE
    SYNTAX INTEGER
    ACCESS read-write
    STATUS mandatory
    DESCRIPTION
        "The value of this variable is used as an index to read
        an error massege from wtWebGraphAnalog57762DiagErrorMessage.
        Errors are numbered from 1 to wtWebGraphAnalog57762DiagErrorCount.
        Writing a valid value into this variable, making the appropriate
        message readable from wtWebGraphAnalog57762DiagErrorMessage."
    ::= { wtWebGraphAnalog57762Diag 3 }

wtWebGraphAnalog57762DiagErrorMessage OBJECT-TYPE
    SYNTAX OCTET STRING
    ACCESS read-only
    STATUS mandatory
    DESCRIPTION
        "Using wtWebGraphAnalog57762DiagErrorIndex as an index, the appropriate message is available."
    ::= { wtWebGraphAnalog57762Diag 4 }

wtWebGraphAnalog57762DiagErrorClear OBJECT-TYPE
    SYNTAX INTEGER
    ACCESS write-only
    STATUS mandatory
    DESCRIPTION
        "Writing 1 into this variable clears all diagnosis messages."
    ::= { wtWebGraphAnalog57762Diag 5 }

-- TRAP DEFINITIONS

-- Diese SNMP-Traps werden gesendet, wenn die Alarmtriggerbedingungen zutreffen

wtWebGraphAnalog57762Alert1 TRAP-TYPE
    ENTERPRISE  wtWebGraphAnalog57762
    VARIABLES   { wtWebGraphAnalog57762AlarmTrapText }
    DESCRIPTION
        "This SNMP trap is generated when Alarm 1 was triggered,
        SNMP trap enable is set and
        SNMP is enabled."
    -- NMS trap annotation
    --#TYPE "Web-IO Analog-InOut Alarm 1"
    --#SUMMARY "Alarm 1: %s"
    --#ARGUMENTS {0}
    --#SEVERITY INFORMATIONAL
    --#TIMEINDEX 99
    --#STATE OPERATIONAL
    ::= 31

wtWebGraphAnalog57762Alert2 TRAP-TYPE
    ENTERPRISE  wtWebGraphAnalog57762
    VARIABLES   { wtWebGraphAnalog57762AlarmTrapText }
    DESCRIPTION
        "This SNMP trap is generated when Alarm 2 was triggered,
        SNMP trap enable is set and
        SNMP is enabled."
    -- NMS trap annotation
    --#TYPE "Web-IO Analog-InOut Alarm 2"
    --#SUMMARY "Alarm 2: %s"
    --#ARGUMENTS {0}
    --#SEVERITY INFORMATIONAL
    --#TIMEINDEX 99
    --#STATE OPERATIONAL
    ::= 32

wtWebGraphAnalog57762Alert3 TRAP-TYPE
    ENTERPRISE  wtWebGraphAnalog57762
    VARIABLES   { wtWebGraphAnalog57762AlarmTrapText }
    DESCRIPTION
        "This SNMP trap is generated when Alarm 3 was triggered,
        SNMP trap enable is set and
        SNMP is enabled."
    -- NMS trap annotation
    --#TYPE "Web-IO Analog-InOut Alarm 3"
    --#SUMMARY "Alarm 3: %s"
    --#ARGUMENTS {0}
    --#SEVERITY INFORMATIONAL
    --#TIMEINDEX 99
    --#STATE OPERATIONAL
    ::= 33

wtWebGraphAnalog57762Alert4 TRAP-TYPE
    ENTERPRISE  wtWebGraphAnalog57762
    VARIABLES   { wtWebGraphAnalog57762AlarmTrapText }
    DESCRIPTION
        "This SNMP trap is generated when Alarm 4 was triggered,
        SNMP trap enable is set and
        SNMP is enabled."
    -- NMS trap annotation
    --#TYPE "Web-IO Analog-InOut Alarm 4"
    --#SUMMARY "Alarm 4: %s"
    --#ARGUMENTS {0}
    --#SEVERITY INFORMATIONAL
    --#TIMEINDEX 99
    --#STATE OPERATIONAL
    ::= 34

wtWebGraphAnalog57762Alert5 TRAP-TYPE
    ENTERPRISE  wtWebGraphAnalog57762
    VARIABLES   { wtWebGraphAnalog57762AlarmTrapText }
    DESCRIPTION
        "This SNMP trap is generated when Alarm 5 was triggered,
        SNMP trap enable is set and
        SNMP is enabled."
    -- NMS trap annotation
    --#TYPE "Web-IO Analog-InOut Alarm 5"
    --#SUMMARY "Alarm 5: %s"
    --#ARGUMENTS {0}
    --#SEVERITY INFORMATIONAL
    --#TIMEINDEX 99
    --#STATE OPERATIONAL
    ::= 35

wtWebGraphAnalog57762Alert6 TRAP-TYPE
    ENTERPRISE  wtWebGraphAnalog57762
    VARIABLES   { wtWebGraphAnalog57762AlarmTrapText }
    DESCRIPTION
        "This SNMP trap is generated when Alarm 6 was triggered,
        SNMP trap enable is set and
        SNMP is enabled."
    -- NMS trap annotation
    --#TYPE "Web-IO Analog-InOut Alarm 6"
    --#SUMMARY "Alarm 6: %s"
    --#ARGUMENTS {0}
    --#SEVERITY INFORMATIONAL
    --#TIMEINDEX 99
    --#STATE OPERATIONAL
    ::= 36

wtWebGraphAnalog57762Alert7 TRAP-TYPE
    ENTERPRISE  wtWebGraphAnalog57762
    VARIABLES   { wtWebGraphAnalog57762AlarmTrapText }
    DESCRIPTION
        "This SNMP trap is generated when Alarm 7 was triggered,
        SNMP trap enable is set and
        SNMP is enabled."
    -- NMS trap annotation
    --#TYPE "Web-IO Analog-InOut Alarm 7"
    --#SUMMARY "Alarm 7: %s"
    --#ARGUMENTS {0}
    --#SEVERITY INFORMATIONAL
    --#TIMEINDEX 99
    --#STATE OPERATIONAL
    ::= 37

wtWebGraphAnalog57762Alert8 TRAP-TYPE
    ENTERPRISE  wtWebGraphAnalog57762
    VARIABLES   { wtWebGraphAnalog57762AlarmTrapText }
    DESCRIPTION
        "This SNMP trap is generated when Alarm 8 was triggered,
        SNMP trap enable is set and
        SNMP is enabled."
    -- NMS trap annotation
    --#TYPE "Web-IO Analog-InOut Alarm 8"
    --#SUMMARY "Alarm 8: %s"
    --#ARGUMENTS {0}
    --#SEVERITY INFORMATIONAL
    --#TIMEINDEX 99
    --#STATE OPERATIONAL
    ::= 38

wtWebGraphAnalog57762Alert9 TRAP-TYPE
    ENTERPRISE  wtWebGraphAnalog57762
    VARIABLES   { wtWebGraphAnalog57762AlarmClearTrapText }
    DESCRIPTION
        "This SNMP trap is generated when Alarm 1 was cleared,
        SNMP trap enable is set and
        SNMP is enabled."
    -- NMS trap annotation
    --#TYPE "Web-IO Analog-InOut Release Alarm 1"
    --#SUMMARY "Release Alarm 1: %s"
    --#ARGUMENTS {0}
    --#SEVERITY INFORMATIONAL
    --#TIMEINDEX 99
    --#STATE OPERATIONAL
    ::= 91

wtWebGraphAnalog57762Alert10 TRAP-TYPE
    ENTERPRISE  wtWebGraphAnalog57762
    VARIABLES   { wtWebGraphAnalog57762AlarmClearTrapText }
    DESCRIPTION
        "This SNMP trap is generated when Alarm 2 was cleared,
        SNMP trap enable is set and
        SNMP is enabled."
    -- NMS trap annotation
    --#TYPE "Web-IO Analog-InOut Release Alarm 2"
    --#SUMMARY "Release Alarm 2: %s"
    --#ARGUMENTS {0}
    --#SEVERITY INFORMATIONAL
    --#TIMEINDEX 99
    --#STATE OPERATIONAL
    ::= 92

wtWebGraphAnalog57762Alert11 TRAP-TYPE
    ENTERPRISE  wtWebGraphAnalog57762
    VARIABLES   { wtWebGraphAnalog57762AlarmClearTrapText }
    DESCRIPTION
        "This SNMP trap is generated when Alarm 3 was cleared,
        SNMP trap enable is set and
        SNMP is enabled."
    -- NMS trap annotation
    --#TYPE "Web-IO Analog-InOut Release Alarm 3"
    --#SUMMARY "Release Alarm 3: %s"
    --#ARGUMENTS {0}
    --#SEVERITY INFORMATIONAL
    --#TIMEINDEX 99
    --#STATE OPERATIONAL
    ::= 93

wtWebGraphAnalog57762Alert12 TRAP-TYPE
    ENTERPRISE  wtWebGraphAnalog57762
    VARIABLES   { wtWebGraphAnalog57762AlarmClearTrapText }
    DESCRIPTION
        "This SNMP trap is generated when Alarm 4 was cleared,
        SNMP trap enable is set and
        SNMP is enabled."
    -- NMS trap annotation
    --#TYPE "Web-IO Analog-InOut Release Alarm 4"
    --#SUMMARY "Release Alarm 4: %s"
    --#ARGUMENTS {0}
    --#SEVERITY INFORMATIONAL
    --#TIMEINDEX 99
    --#STATE OPERATIONAL
    ::= 94

wtWebGraphAnalog57762Alert13 TRAP-TYPE
    ENTERPRISE  wtWebGraphAnalog57762
    VARIABLES   { wtWebGraphAnalog57762AlarmClearTrapText }
    DESCRIPTION
        "This SNMP trap is generated when Alarm 5 was cleared,
        SNMP trap enable is set and
        SNMP is enabled."
    -- NMS trap annotation
    --#TYPE "Web-IO Analog-InOut Release Alarm 5"
    --#SUMMARY "Release Alarm 5: %s"
    --#ARGUMENTS {0}
    --#SEVERITY INFORMATIONAL
    --#TIMEINDEX 99
    --#STATE OPERATIONAL
    ::= 95

wtWebGraphAnalog57762Alert14 TRAP-TYPE
    ENTERPRISE  wtWebGraphAnalog57762
    VARIABLES   { wtWebGraphAnalog57762AlarmClearTrapText }
    DESCRIPTION
        "This SNMP trap is generated when Alarm 6 was cleared,
        SNMP trap enable is set and
        SNMP is enabled."
    -- NMS trap annotation
    --#TYPE "Web-IO Analog-InOut Release Alarm 6"
    --#SUMMARY "Release Alarm 6: %s"
    --#ARGUMENTS {0}
    --#SEVERITY INFORMATIONAL
    --#TIMEINDEX 99
    --#STATE OPERATIONAL
    ::= 96

wtWebGraphAnalog57762Alert15 TRAP-TYPE
    ENTERPRISE  wtWebGraphAnalog57762
    VARIABLES   { wtWebGraphAnalog57762AlarmClearTrapText }
    DESCRIPTION
        "This SNMP trap is generated when Alarm 7 was cleared,
        SNMP trap enable is set and
        SNMP is enabled."
    -- NMS trap annotation
    --#TYPE "Web-IO Analog-InOut Release Alarm 7"
    --#SUMMARY "Release Alarm 7: %s"
    --#ARGUMENTS {0}
    --#SEVERITY INFORMATIONAL
    --#TIMEINDEX 99
    --#STATE OPERATIONAL
    ::= 97

wtWebGraphAnalog57762Alert16 TRAP-TYPE
    ENTERPRISE  wtWebGraphAnalog57762
    VARIABLES   { wtWebGraphAnalog57762AlarmClearTrapText }
    DESCRIPTION
        "This SNMP trap is generated when Alarm 8 was cleared,
        SNMP trap enable is set and
        SNMP is enabled."
    -- NMS trap annotation
    --#TYPE "Web-IO Analog-InOut Release Alarm 8"
    --#SUMMARY "Release Alarm 8: %s"
    --#ARGUMENTS {0}
    --#SEVERITY INFORMATIONAL
    --#TIMEINDEX 99
    --#STATE OPERATIONAL
    ::= 98

wtWebGraphAnalog57762AlertReport TRAP-TYPE
    ENTERPRISE  wtWebGraphAnalog57762
    VARIABLES   { wtWebGraphAnalog57762AlarmTrapText }
    DESCRIPTION
        "This SNMP trap is generated when the report was triggered,
        SNMP trap enable is set and
        SNMP is enabled."
    -- NMS trap annotation
    --#TYPE "Web-IO Analog-InOut Report"
    --#SUMMARY "Report: %s"
    --#ARGUMENTS {0}
    --#SEVERITY INFORMATIONAL
    --#TIMEINDEX 99
    --#STATE OPERATIONAL
    ::= 39

wtWebGraphAnalog57762AlertDiag TRAP-TYPE
    ENTERPRISE  wtWebGraphAnalog57762
    VARIABLES   {
    		wtWebGraphAnalog57762DiagErrorIndex,
    	  	wtWebGraphAnalog57762DiagErrorMessage
    		}
    DESCRIPTION
        "This SNMP trap is generated when a diagnosis/error message was triggered,
        SNMP trap enable is set and
        SNMP is enabled."
    -- NMS trap annotation
    --#TYPE "Web-IO Analog-InOut Diagnose Error"
    --#SUMMARY "Diagnose error index: %d, Message: %s."
    --#ARGUMENTS {0,1}
    --#SEVERITY MAJOR
    --#TIMEINDEX 99
    --#STATE DEGRADED
    ::= 110

END
