-----------------------------------------------------------------------
-- MIB table for P8631
--
-- v4.0 for firmware 4-5-8.x, 2015-09-08
-----------------------------------------------------------------------
P8631-MIB DEFINITIONS ::= BEGIN


IMPORTS
	enterprises
		FROM RFC1155-SMI
	OBJECT-TYPE
		FROM RFC-1212
	TRAP-TYPE
		FROM RFC-1215;

  DisplayString ::= OCTET STRING


comet         OBJECT IDENTIFIER ::= { enterprises 22626 }
products      OBJECT IDENTIFIER ::= { comet 1 }
p8631         OBJECT IDENTIFIER ::= { products 5 }
global        OBJECT IDENTIFIER ::= { p8631 1 }
channels      OBJECT IDENTIFIER ::= { p8631 2 }
channel1      OBJECT IDENTIFIER ::= { channels 1 }
channel2      OBJECT IDENTIFIER ::= { channels 2 }
channel3      OBJECT IDENTIFIER ::= { channels 3 }
traps         OBJECT IDENTIFIER ::= { p8631 3 }
tables	      OBJECT IDENTIFIER ::= { p8631 4 }


-----------------------------------------------------------------------
-- global
-----------------------------------------------------------------------
sensorName OBJECT-TYPE
	SYNTAX		DisplayString (SIZE (0..68))
	ACCESS		read-only
	STATUS		mandatory
	DESCRIPTION	"Device name"
::= { global 1 }

serialNumber OBJECT-TYPE
	SYNTAX		DisplayString (SIZE (0..16))
	ACCESS		read-only
	STATUS		mandatory
	DESCRIPTION	"Serial number"
::= { global 2 }

deviceType OBJECT-TYPE
	SYNTAX		INTEGER (0..65534)
	ACCESS		read-only
	STATUS		mandatory
	DESCRIPTION	"Device type"
::= { global 3 }


-----------------------------------------------------------------------
-- channels
-----------------------------------------------------------------------

-----------------------------------------------------------------------
-- channel1
-----------------------------------------------------------------------
ch1Name OBJECT-TYPE
	SYNTAX		DisplayString (SIZE (0..16))
	ACCESS		read-only
	STATUS		mandatory
	DESCRIPTION	"Channel 1 name"
::= { channel1 1 }

ch1Val OBJECT-TYPE
	SYNTAX		DisplayString (SIZE (0..8))
	ACCESS		read-only
	STATUS		mandatory
	DESCRIPTION	"Channel 1 value"
::= { channel1 2 }

ch1IntVal OBJECT-TYPE
	SYNTAX		INTEGER (-550..1250)
	ACCESS		read-only
	STATUS		mandatory
	DESCRIPTION	"Channel 1 value * 10 (12.5 dgr C = 125)"
::= { channel1 3 }

ch1Alarm OBJECT-TYPE
	SYNTAX		INTEGER (0..2)
	ACCESS		read-only
	STATUS		mandatory
	DESCRIPTION	"Alarm on channel 1; 0 - No alarm, 1 - Alarm High, 2 - Alarm Low"
::= { channel1 4 }

ch1LimHi OBJECT-TYPE
	SYNTAX		INTEGER (-550..1250)
	ACCESS		read-only
	STATUS		mandatory
	DESCRIPTION	"Channel 1 upper alarm limit (value * 10)"
::= { channel1 5 }

ch1LimLo OBJECT-TYPE
	SYNTAX		INTEGER (-550..1250)
	ACCESS		read-only
	STATUS		mandatory
	DESCRIPTION	"Channel 1 low alarm limit (value * 10)"
::= { channel1 6 }

ch1LimHyst OBJECT-TYPE
	SYNTAX		INTEGER (-550..1250)
	ACCESS		read-only
	STATUS		mandatory
	DESCRIPTION	"Channel 1 hysteressis (value * 10)"
::= { channel1 7 }

ch1LimDelay OBJECT-TYPE
	SYNTAX		INTEGER (0..65534)
	ACCESS		read-only
	STATUS		mandatory
	DESCRIPTION	"Channel 1 delay [sec]"
::= { channel1 8 }

ch1Unit OBJECT-TYPE
	SYNTAX		DisplayString (SIZE (0..8))
	ACCESS		read-only
	STATUS		mandatory
	DESCRIPTION	"Unit on channel 1; °C, °F, %RH"
::= { channel1 9 }

ch1AlarmStr OBJECT-TYPE
	SYNTAX		DisplayString (SIZE (0..8))
	ACCESS		read-only
	STATUS		mandatory
	DESCRIPTION	"Alarm on channel 1; none, high, low"
::= { channel1 10 }

ch1Min OBJECT-TYPE
	SYNTAX		DisplayString (SIZE (0..8))
	ACCESS		read-only
	STATUS		mandatory
	DESCRIPTION	"Channel 1 minimal value"
::= { channel1 11 }

ch1Max OBJECT-TYPE
	SYNTAX		DisplayString (SIZE (0..8))
	ACCESS		read-only
	STATUS		mandatory
	DESCRIPTION	"Channel 1 maximal value"
::= { channel1 12 }


-----------------------------------------------------------------------
-- channel2
-----------------------------------------------------------------------
ch2Name OBJECT-TYPE
	SYNTAX		DisplayString (SIZE (0..16))
	ACCESS		read-only
	STATUS		mandatory
	DESCRIPTION	"Channel 2 name"
::= { channel2 1 }

ch2Val OBJECT-TYPE
	SYNTAX		DisplayString (SIZE (0..8))
	ACCESS		read-only
	STATUS		mandatory
	DESCRIPTION	"Channel 2 value"
::= { channel2 2 }

ch2IntVal OBJECT-TYPE
	SYNTAX		INTEGER (-550..1250)
	ACCESS		read-only
	STATUS		mandatory
	DESCRIPTION	"Channel 2 value * 10 (12.5 dgr C = 125)"
::= { channel2 3 }

ch2Alarm OBJECT-TYPE
	SYNTAX		INTEGER (0..2)
	ACCESS		read-only
	STATUS		mandatory
	DESCRIPTION	"Alarm on channel 2; 0 - No alarm, 1 - Alarm High, 2 - Alarm Low"
::= { channel2 4 }

ch2LimHi OBJECT-TYPE
	SYNTAX		INTEGER (-550..1250)
	ACCESS		read-only
	STATUS		mandatory
	DESCRIPTION	"Channel 2 upper alarm limit (value * 10)"
::= { channel2 5 }

ch2LimLo OBJECT-TYPE
	SYNTAX		INTEGER (-550..1250)
	ACCESS		read-only
	STATUS		mandatory
	DESCRIPTION	"Channel 2 low alarm limit (value * 10)"
::= { channel2 6 }

ch2LimHyst OBJECT-TYPE
	SYNTAX		INTEGER (-550..1250)
	ACCESS		read-only
	STATUS		mandatory
	DESCRIPTION	"Channel 2 hysteressis (value * 10)"
::= { channel2 7 }

ch2LimDelay OBJECT-TYPE
	SYNTAX		INTEGER (0..65534)
	ACCESS		read-only
	STATUS		mandatory
	DESCRIPTION	"Channel 2 delay [sec]"
::= { channel2 8 }

ch2Unit OBJECT-TYPE
	SYNTAX		DisplayString (SIZE (0..8))
	ACCESS		read-only
	STATUS		mandatory
	DESCRIPTION	"Unit on channel 2; °C, °F, %RH"
::= { channel2 9 }

ch2AlarmStr OBJECT-TYPE
	SYNTAX		DisplayString (SIZE (0..8))
	ACCESS		read-only
	STATUS		mandatory
	DESCRIPTION	"Alarm on channel 2; none, high, low"
::= { channel2 10 }

ch2Min OBJECT-TYPE
	SYNTAX		DisplayString (SIZE (0..8))
	ACCESS		read-only
	STATUS		mandatory
	DESCRIPTION	"Channel 2 minimal value"
::= { channel2 11 }

ch2Max OBJECT-TYPE
	SYNTAX		DisplayString (SIZE (0..8))
	ACCESS		read-only
	STATUS		mandatory
	DESCRIPTION	"Channel 2 maximal value"
::= { channel2 12 }


-----------------------------------------------------------------------
-- channel3
-----------------------------------------------------------------------
ch3Name OBJECT-TYPE
	SYNTAX		DisplayString (SIZE (0..16))
	ACCESS		read-only
	STATUS		mandatory
	DESCRIPTION	"Channel 3 name"
::= { channel3 1 }

ch3Val OBJECT-TYPE
	SYNTAX		DisplayString (SIZE (0..8))
	ACCESS		read-only
	STATUS		mandatory
	DESCRIPTION	"Channel 3 value"
::= { channel3 2 }

ch3IntVal OBJECT-TYPE
	SYNTAX		INTEGER (-550..1250)
	ACCESS		read-only
	STATUS		mandatory
	DESCRIPTION	"Channel 3 value * 10 (12.5 dgr C = 125)"
::= { channel3 3 }

ch3Alarm OBJECT-TYPE
	SYNTAX		INTEGER (0..2)
	ACCESS		read-only
	STATUS		mandatory
	DESCRIPTION	"Alarm on channel 3; 0 - No alarm, 1 - Alarm High, 2 - Alarm Low"
::= { channel3 4 }

ch3LimHi OBJECT-TYPE
	SYNTAX		INTEGER (-550..1250)
	ACCESS		read-only
	STATUS		mandatory
	DESCRIPTION	"Channel 3 upper alarm limit (value * 10)"
::= { channel3 5 }

ch3LimLo OBJECT-TYPE
	SYNTAX		INTEGER (-550..1250)
	ACCESS		read-only
	STATUS		mandatory
	DESCRIPTION	"Channel 3 low alarm limit (value * 10)"
::= { channel3 6 }

ch3LimHyst OBJECT-TYPE
	SYNTAX		INTEGER (-550..1250)
	ACCESS		read-only
	STATUS		mandatory
	DESCRIPTION	"Channel 3 hysteressis (value * 10)"
::= { channel3 7 }

ch3LimDelay OBJECT-TYPE
	SYNTAX		INTEGER (0..65534)
	ACCESS		read-only
	STATUS		mandatory
	DESCRIPTION	"Channel 3 delay [sec]"
::= { channel3 8 }

ch3Unit OBJECT-TYPE
	SYNTAX		DisplayString (SIZE (0..8))
	ACCESS		read-only
	STATUS		mandatory
	DESCRIPTION	"Unit on channel 3; °C, °F, %RH"
::= { channel3 9 }

ch3AlarmStr OBJECT-TYPE
	SYNTAX		DisplayString (SIZE (0..8))
	ACCESS		read-only
	STATUS		mandatory
	DESCRIPTION	"Alarm on channel 3; none, high, low"
::= { channel3 10 }

ch3Min OBJECT-TYPE
	SYNTAX		DisplayString (SIZE (0..8))
	ACCESS		read-only
	STATUS		mandatory
	DESCRIPTION	"Channel 3 minimal value"
::= { channel3 11 }

ch3Max OBJECT-TYPE
	SYNTAX		DisplayString (SIZE (0..8))
	ACCESS		read-only
	STATUS		mandatory
	DESCRIPTION	"Channel 3 maximal value"
::= { channel3 12 }


-----------------------------------------------------------------------
-- traps string
-----------------------------------------------------------------------
messageString OBJECT-TYPE
	SYNTAX		DisplayString (SIZE (0..32))
	ACCESS		read-only
	STATUS		mandatory
	DESCRIPTION	"Message giving more detailed information on alarms"
::= { traps 1 }


-----------------------------------------------------------------------
-- tables
-----------------------------------------------------------------------
historyTable OBJECT-TYPE
	SYNTAX  SEQUENCE OF HistoryEntry
	ACCESS  not-accessible
	STATUS  mandatory
	DESCRIPTION	"Table of the history values"
::= { tables 1 }

historyEntry OBJECT-TYPE
	SYNTAX  HistoryEntry
	ACCESS  not-accessible
	STATUS  optional
	DESCRIPTION	"History values entries"
	INDEX   { ch1value }
::= { historyTable 1 }

HistoryEntry ::=
	SEQUENCE {
		ch1value
			INTEGER,
		ch2value
			INTEGER,
		ch3value
			INTEGER
		}

ch1value OBJECT-TYPE
	SYNTAX  INTEGER (-550..1250)
	ACCESS  read-only
	STATUS  mandatory
	DESCRIPTION	"Channel 1 history reading"
::= { historyEntry 1 }

ch2value OBJECT-TYPE
	SYNTAX  INTEGER (-550..1250)
	ACCESS  read-only
	STATUS  mandatory
	DESCRIPTION	"Channel 2 history reading"
::= { historyEntry 2 }

ch3value OBJECT-TYPE
	SYNTAX  INTEGER (-550..1250)
	ACCESS  read-only
	STATUS  mandatory
	DESCRIPTION	"Channel 3 history reading"
::= { historyEntry 3 }


-----------------------------------------------------------------------
-- traps definition
-----------------------------------------------------------------------
trapTest TRAP-TYPE
	ENTERPRISE	comet
	VARIABLES	{ sensorName, messageString }
	DESCRIPTION
		"Testing trap, testing trap by TSensor software"
	::= 0

trapNTPError TRAP-TYPE
	ENTERPRISE	comet
	VARIABLES	{ sensorName, messageString }
	DESCRIPTION
		"Error on time synchronisation via NTP"
	::= 1

trapEmailErrLogin TRAP-TYPE
	ENTERPRISE	comet
	VARIABLES	{ sensorName, messageString }
	DESCRIPTION
		"SMTP error - unknown server"
	::= 2

trapEmailErrAuth TRAP-TYPE
	ENTERPRISE	comet
	VARIABLES	{ sensorName, messageString }
	DESCRIPTION
		"SMTP error - authentication error"
	::= 3

trapEmailErrSome TRAP-TYPE
	ENTERPRISE	comet
	VARIABLES	{ sensorName, messageString }
	DESCRIPTION
		"SMTP error - error during communication with server, unexpected return code"
	::= 4

trapEmailErrSocket TRAP-TYPE
	ENTERPRISE	comet
	VARIABLES	{ sensorName, messageString }
	DESCRIPTION
		"SMTP error - socket error, server is not available"
	::= 5

trapEmailErrDNS TRAP-TYPE
	ENTERPRISE	comet
	VARIABLES	{ sensorName, messageString }
	DESCRIPTION
		"SMTP error - DNS error"
	::= 6

trapSOAPErrFile TRAP-TYPE
	ENTERPRISE	comet
	VARIABLES	{ sensorName, messageString }
	DESCRIPTION
		"SOAP error - file SOAP not found"
	::= 7

trapSOAPErrDNS TRAP-TYPE
	ENTERPRISE	comet
	VARIABLES	{ sensorName, messageString }
	DESCRIPTION
		"SOAP error - DNS error"
	::= 8

trapSOAPErrSocket TRAP-TYPE
	ENTERPRISE	comet
	VARIABLES	{ sensorName, messageString }
	DESCRIPTION
		"SOAP error - socket error, server is not available"
	::= 9

trapSOAPErrDelivery TRAP-TYPE
	ENTERPRISE	comet
	VARIABLES	{ sensorName, messageString }
	DESCRIPTION
		"SOAP error - delivery error, wrong return code from server"
	::= 10

trapCh1HighAlarm TRAP-TYPE
	ENTERPRISE	comet
	VARIABLES	{ ch1Name, ch1Val, ch1Alarm, sensorName, messageString }
	DESCRIPTION
		"Trap for high alarm on Channel 1"
	::= 11

trapCh2HighAlarm TRAP-TYPE
	ENTERPRISE	comet
	VARIABLES	{ ch2Name, ch2Val, ch2Alarm, sensorName, messageString }
	DESCRIPTION
		"Trap for high alarm on Channel 2"
	::= 12

trapCh3HighAlarm TRAP-TYPE
	ENTERPRISE	comet
	VARIABLES	{ ch3Name, ch3Val, ch3Alarm, sensorName, messageString }
	DESCRIPTION
		"Trap for high alarm on Channel 3"
	::= 13

trapCh1LowAlarm TRAP-TYPE
	ENTERPRISE	comet
	VARIABLES	{ ch1Name, ch1Val, ch1Alarm, sensorName, messageString }
	DESCRIPTION
		"Trap for low alarm on Channel 1"
	::= 21

trapCh2LowAlarm TRAP-TYPE
	ENTERPRISE	comet
	VARIABLES	{ ch2Name, ch2Val, ch2Alarm, sensorName, messageString }
	DESCRIPTION
		"Trap for low alarm on Channel 2"
	::= 22

trapCh3LowAlarm TRAP-TYPE
	ENTERPRISE	comet
	VARIABLES	{ ch3Name, ch3Val, ch3Alarm, sensorName, messageString }
	DESCRIPTION
		"Trap for low alarm on Channel 3"
	::= 23

trapCh1ClrAlarm TRAP-TYPE
	ENTERPRISE	comet
	VARIABLES	{ ch1Name, ch1Val, ch1Alarm, sensorName, messageString }
	DESCRIPTION
		"Trap for clearing alarm on Channel 1"
	::= 31

trapCh2ClrAlarm TRAP-TYPE
	ENTERPRISE	comet
	VARIABLES	{ ch2Name, ch2Val, ch2Alarm, sensorName, messageString }
	DESCRIPTION
		"Trap for clearing alarm on Channel 2"
	::= 32

trapCh3ClrAlarm TRAP-TYPE
	ENTERPRISE	comet
	VARIABLES	{ ch3Name, ch3Val, ch3Alarm, sensorName, messageString }
	DESCRIPTION
		"Trap for clearing alarm on Channel 3"
	::= 33

trapCh1Error TRAP-TYPE
	ENTERPRISE	comet
	VARIABLES	{ ch1Name, ch1Val, ch1Alarm, sensorName, messageString }
	DESCRIPTION
		"Trap for error on Channel 1"
	::= 41

trapCh2Error TRAP-TYPE
	ENTERPRISE	comet
	VARIABLES	{ ch2Name, ch2Val, ch2Alarm, sensorName, messageString }
	DESCRIPTION
		"Trap for error on Channel 2"
	::= 42

trapCh3Error TRAP-TYPE
	ENTERPRISE	comet
	VARIABLES	{ ch3Name, ch3Val, ch3Alarm, sensorName, messageString }
	DESCRIPTION
		"Trap for error on Channel 3"
	::= 43


END
