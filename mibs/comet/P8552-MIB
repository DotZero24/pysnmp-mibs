-----------------------------------------------------------------------
-- MIB table for P8552
--
-- v4.0 for firmware 4-5-8.x, 2015-09-08
-----------------------------------------------------------------------
P8552-MIB DEFINITIONS ::= BEGIN


IMPORTS
	enterprises
		FROM RFC1155-SMI
	OBJECT-TYPE
		FROM RFC-1212
	TRAP-TYPE
		FROM RFC-1215;

  DisplayString ::= OCTET STRING


comet         OBJECT IDENTIFIER ::= { enterprises 22626 }
products      OBJECT IDENTIFIER ::= { comet 1 }
p8552         OBJECT IDENTIFIER ::= { products 5 }
global        OBJECT IDENTIFIER ::= { p8552 1 }
channels      OBJECT IDENTIFIER ::= { p8552 2 }
channel1      OBJECT IDENTIFIER ::= { channels 1 }
channel2      OBJECT IDENTIFIER ::= { channels 2 }
channel3      OBJECT IDENTIFIER ::= { channels 3 }
channel4      OBJECT IDENTIFIER ::= { channels 4 }
bin1          OBJECT IDENTIFIER ::= { channels 6 }
bin2          OBJECT IDENTIFIER ::= { channels 7 }
bin3          OBJECT IDENTIFIER ::= { channels 8 }
traps         OBJECT IDENTIFIER ::= { p8552 3 }
tables	      OBJECT IDENTIFIER ::= { p8552 4 }


-----------------------------------------------------------------------
-- global
-----------------------------------------------------------------------
sensorName OBJECT-TYPE
	SYNTAX		DisplayString (SIZE (0..68))
	ACCESS		read-only
	STATUS		mandatory
	DESCRIPTION	"Device name"
::= { global 1 }

serialNumber OBJECT-TYPE
	SYNTAX		DisplayString (SIZE (0..16))
	ACCESS		read-only
	STATUS		mandatory
	DESCRIPTION	"Serial number"
::= { global 2 }

deviceType OBJECT-TYPE
	SYNTAX		INTEGER (0..65534)
	ACCESS		read-only
	STATUS		mandatory
	DESCRIPTION	"Device type"
::= { global 3 }


-----------------------------------------------------------------------
-- channels
-----------------------------------------------------------------------

-----------------------------------------------------------------------
-- channel1
-----------------------------------------------------------------------
ch1Name OBJECT-TYPE
	SYNTAX		DisplayString (SIZE (0..16))
	ACCESS		read-only
	STATUS		mandatory
	DESCRIPTION	"Channel 1 name"
::= { channel1 1 }

ch1Val OBJECT-TYPE
	SYNTAX		DisplayString (SIZE (0..8))
	ACCESS		read-only
	STATUS		mandatory
	DESCRIPTION	"Channel 1 value"
::= { channel1 2 }

ch1IntVal OBJECT-TYPE
	SYNTAX		INTEGER (-550..1250)
	ACCESS		read-only
	STATUS		mandatory
	DESCRIPTION	"Channel 1 value * 10 (12.5 dgr C = 125)"
::= { channel1 3 }

ch1Alarm OBJECT-TYPE
	SYNTAX		INTEGER (0..2)
	ACCESS		read-only
	STATUS		mandatory
	DESCRIPTION	"Alarm on channel 1; 0 - No alarm, 1 - Alarm High, 2 - Alarm Low"
::= { channel1 4 }

ch1LimHi OBJECT-TYPE
	SYNTAX		INTEGER (-550..1250)
	ACCESS		read-only
	STATUS		mandatory
	DESCRIPTION	"Channel 1 upper alarm limit (value * 10)"
::= { channel1 5 }

ch1LimLo OBJECT-TYPE
	SYNTAX		INTEGER (-550..1250)
	ACCESS		read-only
	STATUS		mandatory
	DESCRIPTION	"Channel 1 low alarm limit (value * 10)"
::= { channel1 6 }

ch1LimHyst OBJECT-TYPE
	SYNTAX		INTEGER (-550..1250)
	ACCESS		read-only
	STATUS		mandatory
	DESCRIPTION	"Channel 1 hysteressis (value * 10)"
::= { channel1 7 }

ch1LimDelay OBJECT-TYPE
	SYNTAX		INTEGER (0..65534)
	ACCESS		read-only
	STATUS		mandatory
	DESCRIPTION	"Channel 1 delay [sec]"
::= { channel1 8 }

ch1Unit OBJECT-TYPE
	SYNTAX		DisplayString (SIZE (0..8))
	ACCESS		read-only
	STATUS		mandatory
	DESCRIPTION	"Unit on channel 1; °C, °F, %RH"
::= { channel1 9 }

ch1AlarmStr OBJECT-TYPE
	SYNTAX		DisplayString (SIZE (0..8))
	ACCESS		read-only
	STATUS		mandatory
	DESCRIPTION	"Alarm on channel 1; none, high, low"
::= { channel1 10 }

ch1Min OBJECT-TYPE
	SYNTAX		DisplayString (SIZE (0..8))
	ACCESS		read-only
	STATUS		mandatory
	DESCRIPTION	"Channel 1 minimal value"
::= { channel1 11 }

ch1Max OBJECT-TYPE
	SYNTAX		DisplayString (SIZE (0..8))
	ACCESS		read-only
	STATUS		mandatory
	DESCRIPTION	"Channel 1 maximal value"
::= { channel1 12 }


-----------------------------------------------------------------------
-- channel2
-----------------------------------------------------------------------
ch2Name OBJECT-TYPE
	SYNTAX		DisplayString (SIZE (0..16))
	ACCESS		read-only
	STATUS		mandatory
	DESCRIPTION	"Channel 2 name"
::= { channel2 1 }

ch2Val OBJECT-TYPE
	SYNTAX		DisplayString (SIZE (0..8))
	ACCESS		read-only
	STATUS		mandatory
	DESCRIPTION	"Channel 2 value"
::= { channel2 2 }

ch2IntVal OBJECT-TYPE
	SYNTAX		INTEGER (-550..1250)
	ACCESS		read-only
	STATUS		mandatory
	DESCRIPTION	"Channel 2 value * 10 (12.5 dgr C = 125)"
::= { channel2 3 }

ch2Alarm OBJECT-TYPE
	SYNTAX		INTEGER (0..2)
	ACCESS		read-only
	STATUS		mandatory
	DESCRIPTION	"Alarm on channel 2; 0 - No alarm, 1 - Alarm High, 2 - Alarm Low"
::= { channel2 4 }

ch2LimHi OBJECT-TYPE
	SYNTAX		INTEGER (-550..1250)
	ACCESS		read-only
	STATUS		mandatory
	DESCRIPTION	"Channel 2 upper alarm limit (value * 10)"
::= { channel2 5 }

ch2LimLo OBJECT-TYPE
	SYNTAX		INTEGER (-550..1250)
	ACCESS		read-only
	STATUS		mandatory
	DESCRIPTION	"Channel 2 low alarm limit (value * 10)"
::= { channel2 6 }

ch2LimHyst OBJECT-TYPE
	SYNTAX		INTEGER (-550..1250)
	ACCESS		read-only
	STATUS		mandatory
	DESCRIPTION	"Channel 2 hysteressis (value * 10)"
::= { channel2 7 }

ch2LimDelay OBJECT-TYPE
	SYNTAX		INTEGER (0..65534)
	ACCESS		read-only
	STATUS		mandatory
	DESCRIPTION	"Channel 2 delay [sec]"
::= { channel2 8 }

ch2Unit OBJECT-TYPE
	SYNTAX		DisplayString (SIZE (0..8))
	ACCESS		read-only
	STATUS		mandatory
	DESCRIPTION	"Unit on channel 2; °C, °F, %RH"
::= { channel2 9 }

ch2AlarmStr OBJECT-TYPE
	SYNTAX		DisplayString (SIZE (0..8))
	ACCESS		read-only
	STATUS		mandatory
	DESCRIPTION	"Alarm on channel 2; none, high, low"
::= { channel2 10 }

ch2Min OBJECT-TYPE
	SYNTAX		DisplayString (SIZE (0..8))
	ACCESS		read-only
	STATUS		mandatory
	DESCRIPTION	"Channel 2 minimal value"
::= { channel2 11 }

ch2Max OBJECT-TYPE
	SYNTAX		DisplayString (SIZE (0..8))
	ACCESS		read-only
	STATUS		mandatory
	DESCRIPTION	"Channel 2 maximal value"
::= { channel2 12 }


-----------------------------------------------------------------------
-- channel3
-----------------------------------------------------------------------
ch3Name OBJECT-TYPE
	SYNTAX		DisplayString (SIZE (0..16))
	ACCESS		read-only
	STATUS		mandatory
	DESCRIPTION	"Channel 3 name"
::= { channel3 1 }

ch3Val OBJECT-TYPE
	SYNTAX		DisplayString (SIZE (0..8))
	ACCESS		read-only
	STATUS		mandatory
	DESCRIPTION	"Channel 3 value"
::= { channel3 2 }

ch3IntVal OBJECT-TYPE
	SYNTAX		INTEGER (-550..1250)
	ACCESS		read-only
	STATUS		mandatory
	DESCRIPTION	"Channel 3 value * 10 (12.5 dgr C = 125)"
::= { channel3 3 }

ch3Alarm OBJECT-TYPE
	SYNTAX		INTEGER (0..2)
	ACCESS		read-only
	STATUS		mandatory
	DESCRIPTION	"Alarm on channel 3; 0 - No alarm, 1 - Alarm High, 2 - Alarm Low"
::= { channel3 4 }

ch3LimHi OBJECT-TYPE
	SYNTAX		INTEGER (-550..1250)
	ACCESS		read-only
	STATUS		mandatory
	DESCRIPTION	"Channel 3 upper alarm limit (value * 10)"
::= { channel3 5 }

ch3LimLo OBJECT-TYPE
	SYNTAX		INTEGER (-550..1250)
	ACCESS		read-only
	STATUS		mandatory
	DESCRIPTION	"Channel 3 low alarm limit (value * 10)"
::= { channel3 6 }

ch3LimHyst OBJECT-TYPE
	SYNTAX		INTEGER (-550..1250)
	ACCESS		read-only
	STATUS		mandatory
	DESCRIPTION	"Channel 3 hysteressis (value * 10)"
::= { channel3 7 }

ch3LimDelay OBJECT-TYPE
	SYNTAX		INTEGER (0..65534)
	ACCESS		read-only
	STATUS		mandatory
	DESCRIPTION	"Channel 3 delay [sec]"
::= { channel3 8 }

ch3Unit OBJECT-TYPE
	SYNTAX		DisplayString (SIZE (0..8))
	ACCESS		read-only
	STATUS		mandatory
	DESCRIPTION	"Unit on channel 3; °C, °F, %RH"
::= { channel3 9 }

ch3AlarmStr OBJECT-TYPE
	SYNTAX		DisplayString (SIZE (0..8))
	ACCESS		read-only
	STATUS		mandatory
	DESCRIPTION	"Alarm on channel 3; none, high, low"
::= { channel3 10 }

ch3Min OBJECT-TYPE
	SYNTAX		DisplayString (SIZE (0..8))
	ACCESS		read-only
	STATUS		mandatory
	DESCRIPTION	"Channel 3 minimal value"
::= { channel3 11 }

ch3Max OBJECT-TYPE
	SYNTAX		DisplayString (SIZE (0..8))
	ACCESS		read-only
	STATUS		mandatory
	DESCRIPTION	"Channel 3 maximal value"
::= { channel3 12 }


-----------------------------------------------------------------------
-- channel4
-----------------------------------------------------------------------
ch4Name OBJECT-TYPE
	SYNTAX		DisplayString (SIZE (0..16))
	ACCESS		read-only
	STATUS		mandatory
	DESCRIPTION	"Channel 4 name"
::= { channel4 1 }

ch4Val OBJECT-TYPE
	SYNTAX		DisplayString (SIZE (0..8))
	ACCESS		read-only
	STATUS		mandatory
	DESCRIPTION	"Channel 4 value"
::= { channel4 2 }

ch4IntVal OBJECT-TYPE
	SYNTAX		INTEGER (-550..1250)
	ACCESS		read-only
	STATUS		mandatory
	DESCRIPTION	"Channel 4 value * 10 (12.5 dgr C = 125)"
::= { channel4 3 }

ch4Alarm OBJECT-TYPE
	SYNTAX		INTEGER (0..2)
	ACCESS		read-only
	STATUS		mandatory
	DESCRIPTION	"Alarm on channel 4; 0 - No alarm, 1 - Alarm High, 2 - Alarm Low"
::= { channel4 4 }

ch4LimHi OBJECT-TYPE
	SYNTAX		INTEGER (-550..1250)
	ACCESS		read-only
	STATUS		mandatory
	DESCRIPTION	"Channel 4 upper alarm limit (value * 10)"
::= { channel4 5 }

ch4LimLo OBJECT-TYPE
	SYNTAX		INTEGER (-550..1250)
	ACCESS		read-only
	STATUS		mandatory
	DESCRIPTION	"Channel 4 low alarm limit (value * 10)"
::= { channel4 6 }

ch4LimHyst OBJECT-TYPE
	SYNTAX		INTEGER (-550..1250)
	ACCESS		read-only
	STATUS		mandatory
	DESCRIPTION	"Channel 4 hysteressis (value * 10)"
::= { channel4 7 }

ch4LimDelay OBJECT-TYPE
	SYNTAX		INTEGER (0..65534)
	ACCESS		read-only
	STATUS		mandatory
	DESCRIPTION	"Channel 4 delay [sec]"
::= { channel4 8 }

ch4Unit OBJECT-TYPE
	SYNTAX		DisplayString (SIZE (0..8))
	ACCESS		read-only
	STATUS		mandatory
	DESCRIPTION	"Unit on channel 4; °C, °F, %RH"
::= { channel4 9 }

ch4AlarmStr OBJECT-TYPE
	SYNTAX		DisplayString (SIZE (0..8))
	ACCESS		read-only
	STATUS		mandatory
	DESCRIPTION	"Alarm on channel 4; none, high, low"
::= { channel4 10 }

ch4Min OBJECT-TYPE
	SYNTAX		DisplayString (SIZE (0..8))
	ACCESS		read-only
	STATUS		mandatory
	DESCRIPTION	"Channel 4 minimal value"
::= { channel4 11 }

ch4Max OBJECT-TYPE
	SYNTAX		DisplayString (SIZE (0..8))
	ACCESS		read-only
	STATUS		mandatory
	DESCRIPTION	"Channel 4 maximal value"
::= { channel4 12 }


-----------------------------------------------------------------------
-- bin1
-----------------------------------------------------------------------
bin1Name OBJECT-TYPE
	SYNTAX		DisplayString (SIZE (0..16))
	ACCESS		read-only
	STATUS		mandatory
	DESCRIPTION	"BIN Input 1 name"
::= { bin1 1 }

bin1Val OBJECT-TYPE
	SYNTAX		DisplayString (SIZE (0..8))
	ACCESS		read-only
	STATUS		mandatory
	DESCRIPTION	"BIN Input 1 value"
::= { bin1 2 }

bin1IntVal OBJECT-TYPE
	SYNTAX		INTEGER (-550..1250)
	ACCESS		read-only
	STATUS		mandatory
	DESCRIPTION	"BIN Input 1 value - Integer"
::= { bin1 3 }

bin1AlarmStr OBJECT-TYPE
	SYNTAX		DisplayString (SIZE (0..8))
	ACCESS		read-only
	STATUS		mandatory
	DESCRIPTION	"Alarm on BIN Input 1; none, active"
::= { bin1 4 }

bin1Alarm OBJECT-TYPE
	SYNTAX		INTEGER (0..1)
	ACCESS		read-only
	STATUS		mandatory
	DESCRIPTION	"Alarm on BIN Input 1; 0 - No alarm, 1 - Alarm active"
::= { bin1 5 }


-----------------------------------------------------------------------
-- bin2
-----------------------------------------------------------------------
bin2Name OBJECT-TYPE
	SYNTAX		DisplayString (SIZE (0..16))
	ACCESS		read-only
	STATUS		mandatory
	DESCRIPTION	"BIN Input 2 name"
::= { bin2 1 }

bin2Val OBJECT-TYPE
	SYNTAX		DisplayString (SIZE (0..8))
	ACCESS		read-only
	STATUS		mandatory
	DESCRIPTION	"BIN Input 2 value"
::= { bin2 2 }

bin2IntVal OBJECT-TYPE
	SYNTAX		INTEGER (-550..1250)
	ACCESS		read-only
	STATUS		mandatory
	DESCRIPTION	"BIN Input 2 value - Integer"
::= { bin2 3 }

bin2AlarmStr OBJECT-TYPE
	SYNTAX		DisplayString (SIZE (0..8))
	ACCESS		read-only
	STATUS		mandatory
	DESCRIPTION	"Alarm on BIN Input 2; none, active"
::= { bin2 4 }

bin2Alarm OBJECT-TYPE
	SYNTAX		INTEGER (0..1)
	ACCESS		read-only
	STATUS		mandatory
	DESCRIPTION	"Alarm on BIN Input 2; 0 - No alarm, 1 - Alarm active"
::= { bin2 5 }


-----------------------------------------------------------------------
-- bin3
-----------------------------------------------------------------------
bin3Name OBJECT-TYPE
	SYNTAX		DisplayString (SIZE (0..16))
	ACCESS		read-only
	STATUS		mandatory
	DESCRIPTION	"BIN Input 3 name"
::= { bin3 1 }

bin3Val OBJECT-TYPE
	SYNTAX		DisplayString (SIZE (0..8))
	ACCESS		read-only
	STATUS		mandatory
	DESCRIPTION	"BIN Input 3 value"
::= { bin3 2 }

bin3IntVal OBJECT-TYPE
	SYNTAX		INTEGER (-550..1250)
	ACCESS		read-only
	STATUS		mandatory
	DESCRIPTION	"BIN Input 3 value - Integer"
::= { bin3 3 }

bin3AlarmStr OBJECT-TYPE
	SYNTAX		DisplayString (SIZE (0..8))
	ACCESS		read-only
	STATUS		mandatory
	DESCRIPTION	"Alarm on BIN Input 3; none, active"
::= { bin3 4 }

bin3Alarm OBJECT-TYPE
	SYNTAX		INTEGER (0..1)
	ACCESS		read-only
	STATUS		mandatory
	DESCRIPTION	"Alarm on BIN Input 3; 0 - No alarm, 1 - Alarm active"
::= { bin3 5 }


-----------------------------------------------------------------------
-- traps string
-----------------------------------------------------------------------
messageString OBJECT-TYPE
	SYNTAX		DisplayString (SIZE (0..32))
	ACCESS		read-only
	STATUS		mandatory
	DESCRIPTION	"Message giving more detailed information on alarms"
::= { traps 1 }


-----------------------------------------------------------------------
-- tables
-----------------------------------------------------------------------
historyTable OBJECT-TYPE
	SYNTAX  SEQUENCE OF HistoryEntry
	ACCESS  not-accessible
	STATUS  mandatory
	DESCRIPTION	"Table of the history values"
::= { tables 1 }

historyEntry OBJECT-TYPE
	SYNTAX  HistoryEntry
	ACCESS  not-accessible
	STATUS  optional
	DESCRIPTION	"History values entries"
	INDEX   { ch1value }
::= { historyTable 1 }

HistoryEntry ::=
	SEQUENCE {
		ch1value
			INTEGER,
		ch2value
			INTEGER,
		ch3value
			INTEGER,
		ch4value
			INTEGER
		}

ch1value OBJECT-TYPE
	SYNTAX  INTEGER (-550..1250)
	ACCESS  read-only
	STATUS  mandatory
	DESCRIPTION	"Channel 1 history reading"
::= { historyEntry 1 }

ch2value OBJECT-TYPE
	SYNTAX  INTEGER (-550..1250)
	ACCESS  read-only
	STATUS  mandatory
	DESCRIPTION	"Channel 2 history reading"
::= { historyEntry 2 }

ch3value OBJECT-TYPE
	SYNTAX  INTEGER (-550..1250)
	ACCESS  read-only
	STATUS  mandatory
	DESCRIPTION	"Channel 3 history reading"
::= { historyEntry 3 }

ch4value OBJECT-TYPE
	SYNTAX  INTEGER (-550..1250)
	ACCESS  read-only
	STATUS  mandatory
	DESCRIPTION	"Channel 4 history reading"
::= { historyEntry 4 }


-----------------------------------------------------------------------
-- traps definition
-----------------------------------------------------------------------
trapTest TRAP-TYPE
	ENTERPRISE	comet
	VARIABLES	{ sensorName, messageString }
	DESCRIPTION
		"Testing trap, testing trap by TSensor software"
	::= 0

trapNTPError TRAP-TYPE
	ENTERPRISE	comet
	VARIABLES	{ sensorName, messageString }
	DESCRIPTION
		"Error on time synchronisation via NTP"
	::= 1

trapEmailErrLogin TRAP-TYPE
	ENTERPRISE	comet
	VARIABLES	{ sensorName, messageString }
	DESCRIPTION
		"SMTP error - unknown server"
	::= 2

trapEmailErrAuth TRAP-TYPE
	ENTERPRISE	comet
	VARIABLES	{ sensorName, messageString }
	DESCRIPTION
		"SMTP error - authentication error"
	::= 3

trapEmailErrSome TRAP-TYPE
	ENTERPRISE	comet
	VARIABLES	{ sensorName, messageString }
	DESCRIPTION
		"SMTP error - error during communication with server, unexpected return code"
	::= 4

trapEmailErrSocket TRAP-TYPE
	ENTERPRISE	comet
	VARIABLES	{ sensorName, messageString }
	DESCRIPTION
		"SMTP error - socket error, server is not available"
	::= 5

trapEmailErrDNS TRAP-TYPE
	ENTERPRISE	comet
	VARIABLES	{ sensorName, messageString }
	DESCRIPTION
		"SMTP error - DNS error"
	::= 6

trapSOAPErrFile TRAP-TYPE
	ENTERPRISE	comet
	VARIABLES	{ sensorName, messageString }
	DESCRIPTION
		"SOAP error - file SOAP not found"
	::= 7

trapSOAPErrDNS TRAP-TYPE
	ENTERPRISE	comet
	VARIABLES	{ sensorName, messageString }
	DESCRIPTION
		"SOAP error - DNS error"
	::= 8

trapSOAPErrSocket TRAP-TYPE
	ENTERPRISE	comet
	VARIABLES	{ sensorName, messageString }
	DESCRIPTION
		"SOAP error - socket error, server is not available"
	::= 9

trapSOAPErrDelivery TRAP-TYPE
	ENTERPRISE	comet
	VARIABLES	{ sensorName, messageString }
	DESCRIPTION
		"SOAP error - delivery error, wrong return code from server"
	::= 10

trapCh1HighAlarm TRAP-TYPE
	ENTERPRISE	comet
	VARIABLES	{ ch1Name, ch1Val, ch1Alarm, sensorName, messageString }
	DESCRIPTION
		"Trap for high alarm on Channel 1"
	::= 11

trapCh2HighAlarm TRAP-TYPE
	ENTERPRISE	comet
	VARIABLES	{ ch2Name, ch2Val, ch2Alarm, sensorName, messageString }
	DESCRIPTION
		"Trap for high alarm on Channel 2"
	::= 12

trapCh3HighAlarm TRAP-TYPE
	ENTERPRISE	comet
	VARIABLES	{ ch3Name, ch3Val, ch3Alarm, sensorName, messageString }
	DESCRIPTION
		"Trap for high alarm on Channel 3"
	::= 13

trapCh4HighAlarm TRAP-TYPE
	ENTERPRISE	comet
	VARIABLES	{ ch4Name, ch4Val, ch4Alarm, sensorName, messageString }
	DESCRIPTION
		"Trap for high alarm on Channel 4"
	::= 14

trapCh1LowAlarm TRAP-TYPE
	ENTERPRISE	comet
	VARIABLES	{ ch1Name, ch1Val, ch1Alarm, sensorName, messageString }
	DESCRIPTION
		"Trap for low alarm on Channel 1"
	::= 21

trapCh2LowAlarm TRAP-TYPE
	ENTERPRISE	comet
	VARIABLES	{ ch2Name, ch2Val, ch2Alarm, sensorName, messageString }
	DESCRIPTION
		"Trap for low alarm on Channel 2"
	::= 22

trapCh3LowAlarm TRAP-TYPE
	ENTERPRISE	comet
	VARIABLES	{ ch3Name, ch3Val, ch3Alarm, sensorName, messageString }
	DESCRIPTION
		"Trap for low alarm on Channel 3"
	::= 23

trapCh4LowAlarm TRAP-TYPE
	ENTERPRISE	comet
	VARIABLES	{ ch4Name, ch4Val, ch4Alarm, sensorName, messageString }
	DESCRIPTION
		"Trap for low alarm on Channel 4"
	::= 24

trapCh1ClrAlarm TRAP-TYPE
	ENTERPRISE	comet
	VARIABLES	{ ch1Name, ch1Val, ch1Alarm, sensorName, messageString }
	DESCRIPTION
		"Trap for clearing alarm on Channel 1"
	::= 31

trapCh2ClrAlarm TRAP-TYPE
	ENTERPRISE	comet
	VARIABLES	{ ch2Name, ch2Val, ch2Alarm, sensorName, messageString }
	DESCRIPTION
		"Trap for clearing alarm on Channel 2"
	::= 32

trapCh3ClrAlarm TRAP-TYPE
	ENTERPRISE	comet
	VARIABLES	{ ch3Name, ch3Val, ch3Alarm, sensorName, messageString }
	DESCRIPTION
		"Trap for clearing alarm on Channel 3"
	::= 33

trapCh4ClrAlarm TRAP-TYPE
	ENTERPRISE	comet
	VARIABLES	{ ch4Name, ch4Val, ch4Alarm, sensorName, messageString }
	DESCRIPTION
		"Trap for clearing alarm on Channel 4"
	::= 34

trapCh1Error TRAP-TYPE
	ENTERPRISE	comet
	VARIABLES	{ ch1Name, ch1Val, ch1Alarm, sensorName, messageString }
	DESCRIPTION
		"Trap for error on Channel 1"
	::= 41

trapCh2Error TRAP-TYPE
	ENTERPRISE	comet
	VARIABLES	{ ch2Name, ch2Val, ch2Alarm, sensorName, messageString }
	DESCRIPTION
		"Trap for error on Channel 2"
	::= 42

trapCh3Error TRAP-TYPE
	ENTERPRISE	comet
	VARIABLES	{ ch3Name, ch3Val, ch3Alarm, sensorName, messageString }
	DESCRIPTION
		"Trap for error on Channel 3"
	::= 43

trapCh4Error TRAP-TYPE
	ENTERPRISE	comet
	VARIABLES	{ ch4Name, ch4Val, ch4Alarm, sensorName, messageString }
	DESCRIPTION
		"Trap for error on Channel 4"
	::= 44

trapBin1Alarm TRAP-TYPE
	ENTERPRISE	comet
	VARIABLES	{ bin1Name, bin1Val, bin1Alarm, sensorName, messageString }
	DESCRIPTION
		"Trap for alarm on Bin 1"
	::= 51

trapBin2Alarm TRAP-TYPE
	ENTERPRISE	comet
	VARIABLES	{ bin2Name, bin2Val, bin2Alarm, sensorName, messageString }
	DESCRIPTION
		"Trap for alarm on Bin 2"
	::= 52

trapBin3Alarm TRAP-TYPE
	ENTERPRISE	comet
	VARIABLES	{ bin3Name, bin3Val, bin3Alarm, sensorName, messageString }
	DESCRIPTION
		"Trap for alarm on Bin 3"
	::= 53

trapBin1ClrAlarm TRAP-TYPE
	ENTERPRISE	comet
	VARIABLES	{ bin1Name, bin1Val, bin1Alarm, sensorName, messageString }
	DESCRIPTION
		"Trap for clearing alarm on Bin 1"
	::= 61

trapBin2ClrAlarm TRAP-TYPE
	ENTERPRISE	comet
	VARIABLES	{ bin2Name, bin2Val, bin2Alarm, sensorName, messageString }
	DESCRIPTION
		"Trap for clearing alarm on Bin 2"
	::= 62

trapBin3ClrAlarm TRAP-TYPE
	ENTERPRISE	comet
	VARIABLES	{ bin3Name, bin3Val, bin3Alarm, sensorName, messageString }
	DESCRIPTION
		"Trap for clearing alarm on Bin 3"
	::= 63


END
