LANADPTER-MIB DEFINITIONS ::= BEGIN


IMPORTS
	enterprises
		FROM RFC1155-SMI
	OBJECT-TYPE
		FROM RFC-1212;

  DisplayString ::= OCTET STRING


comet         OBJECT IDENTIFIER ::= { enterprises 22626 }
products      OBJECT IDENTIFIER ::= { comet 1 }
lanadapter    OBJECT IDENTIFIER ::= { products 3 }
traps         OBJECT IDENTIFIER ::= { lanadapter 1 }
channels      OBJECT IDENTIFIER ::= { lanadapter 2 }
channel1      OBJECT IDENTIFIER ::= { channels 1 }
channel2      OBJECT IDENTIFIER ::= { channels 2 }
channel3      OBJECT IDENTIFIER ::= { channels 3 }
channel4      OBJECT IDENTIFIER ::= { channels 4 }
channel5      OBJECT IDENTIFIER ::= { channels 5 }
channel6      OBJECT IDENTIFIER ::= { channels 6 }


-- Power Source MIB
-- Parameters (Prefix ps)

messageString OBJECT-TYPE
	SYNTAX		DisplayString (SIZE (0..30))
	ACCESS		read-only
	STATUS		mandatory
	DESCRIPTION	"Message giving more detailed information on alarms."
::= { traps 1 }

channelAlarm OBJECT-TYPE
	SYNTAX		INTEGER (0..1)
	ACCESS		read-only
	STATUS		mandatory
	DESCRIPTION	"Alarm on Channel is Occured. 0 - No alarm, 1 - Alarm. "
::= { traps 2 }

memmory90Full OBJECT-TYPE
	SYNTAX		INTEGER (0..1)
	ACCESS		read-only
	STATUS		mandatory
	DESCRIPTION	"Logger memmory is from 90% full. 0 - No alarm, 1 - Alarm."
::= { traps 3 }

memmory100Full OBJECT-TYPE
	SYNTAX		INTEGER (0..1)
	ACCESS		read-only
	STATUS		mandatory
	DESCRIPTION	"Logger memmory is 100% full. 0 - No alarm, 1 - Alarm."
::= { traps 4 }

vccLow OBJECT-TYPE
	SYNTAX		INTEGER (0..1)
	ACCESS		read-only
	STATUS		mandatory
	DESCRIPTION	"Vcc is low. 0 - No alarm, 1 - Alarm."
::= { traps 5 }

batteryEnd OBJECT-TYPE
	SYNTAX		INTEGER (0..1)
	ACCESS		read-only
	STATUS		mandatory
	DESCRIPTION	"Calculated battery livetime is over. 0 - No alarm, 1 - Alarm."
::= { traps 6 }

batteryLow OBJECT-TYPE
	SYNTAX		INTEGER (0..1)
	ACCESS		read-only
	STATUS		mandatory
	DESCRIPTION	"Battery voltage is too low. 0 - No alarm, 1 - Alarm."
::= { traps 7 }

communicationError OBJECT-TYPE
	SYNTAX		INTEGER (0..1)
	ACCESS		read-only
	STATUS		mandatory
	DESCRIPTION	"Communication with Logger failed. 0 - OK, 1 - Alarm."
::= { traps 8 }

loggerOff OBJECT-TYPE
	SYNTAX		INTEGER (0..1)
	ACCESS		read-only
	STATUS		mandatory
	DESCRIPTION	"Logger is Off. 0 - Logger is on; 1 - Logger is off"
::= { traps 9 }

-----------------------------------------------------------------------
-- channels
-----------------------------------------------------------------------

-----------------------------------------------------------------------
-- channel1
-----------------------------------------------------------------------

ch1Alarm OBJECT-TYPE
	SYNTAX		INTEGER (0..1)
	ACCESS		read-only
	STATUS		mandatory
	DESCRIPTION	"Alarm on channel 1; 0 - No alarm, 1 - Alarm."
::= { channel1 1 }

-----------------------------------------------------------------------
-- channel2
-----------------------------------------------------------------------

ch2Alarm OBJECT-TYPE
	SYNTAX		INTEGER (0..1)
	ACCESS		read-only
	STATUS		mandatory
	DESCRIPTION	"Alarm on channel 2; 0 - No alarm, 1 - Alarm."
::= { channel2 1 }

-----------------------------------------------------------------------
-- channel3
-----------------------------------------------------------------------

ch3Alarm OBJECT-TYPE
	SYNTAX		INTEGER (0..1)
	ACCESS		read-only
	STATUS		mandatory
	DESCRIPTION	"Alarm on channel 3; 0 - No alarm, 1 - Alarm."
::= { channel3 1 }

-----------------------------------------------------------------------
-- channel4
-----------------------------------------------------------------------

ch4Alarm OBJECT-TYPE
	SYNTAX		INTEGER (0..1)
	ACCESS		read-only
	STATUS		mandatory
	DESCRIPTION	"Alarm on channel 4; 0 - No alarm, 1 - Alarm."
::= { channel4 1 }

-----------------------------------------------------------------------
-- channel5
-----------------------------------------------------------------------

ch5Alarm OBJECT-TYPE
	SYNTAX		INTEGER (0..1)
	ACCESS		read-only
	STATUS		mandatory
	DESCRIPTION	"Alarm on channel 5; 0 - No alarm, 1 - Alarm."
::= { channel5 1 }

-----------------------------------------------------------------------
-- channel6
-----------------------------------------------------------------------

ch6Alarm OBJECT-TYPE
	SYNTAX		INTEGER (0..1)
	ACCESS		read-only
	STATUS		mandatory
	DESCRIPTION	"Alarm on channel 6; 0 - No alarm, 1 - Alarm."
::= { channel6 1 }

END
