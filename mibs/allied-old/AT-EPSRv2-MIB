-- ============================================================================
-- AT-ESPRv2-MIB, Allied Telesis enterprise MIB: Ethernet Protection Switching Ring
--
-- Copyright (c) 2008 by Allied Telesis, Inc.
-- All rights reserved.
--
-- ============================================================================


	AT-EPSRv2-MIB DEFINITIONS ::= BEGIN

		IMPORTS
			sysinfo, modules, DisplayStringUnsized
				FROM AT-SMI-MIB
			InterfaceIndex
				FROM IF-MIB
			OBJECT-TYPE, MODULE-IDENTITY, NOTIFICATION-TYPE
				FROM SNMPv2-SMI
			TEXTUAL-CONVENTION
				FROM SNMPv2-TC;


		-- 1.3.6.1.4.1.207.8.4.4.4.536
		atEpsrv2 MODULE-IDENTITY
			LAST-UPDATED "200812230130Z"		-- December 23, 2008 at 01:30 GMT
			ORGANIZATION
				"Allied Telesis, Inc"
			CONTACT-INFO
				"http://www.alliedtelesis.com"
			DESCRIPTION
				"Convert epsrv2Variables into a table entry, so variable of multiple
				EPSRv2 domains can be obtained."
			REVISION "200812230130Z"		-- December 23, 2008 at 01:30 GMT
			DESCRIPTION
				"Initial Revision"
			::= { modules 536 }



--
-- Textual conventions
--

		AtEpsrv2NodeState ::= TEXTUAL-CONVENTION
			STATUS current
			DESCRIPTION
				"Defines the node states that can be passed around
				in EPSRv2 Node Traps."
			SYNTAX INTEGER
				{
				idle(0),
				complete(1),
				failed(2),
				linksUp(3),
				linksDown(4),
				preForward(5),
				unknown(6)
				}

		AtEpsrv2InterfaceState ::= TEXTUAL-CONVENTION
			STATUS current
			DESCRIPTION
				"Defines the interface states that can be passed around
				in EPSRv2 Node Traps."
			SYNTAX INTEGER
				{
				unknown(1),
				down(2),
				blocked(3),
				forward(4)
				}


--
-- Node definitions
--

		-- 1.3.6.1.4.1.207.8.4.4.4.536.1
		atEpsrv2Events OBJECT IDENTIFIER::= { atEpsrv2 1 }


		-- 1.3.6.1.4.1.207.8.4.4.4.536.1.1
		atEpsrv2NodeTrap NOTIFICATION-TYPE
			OBJECTS { 	atEpsrv2NodeType, atEpsrv2DomainName, atEpsrv2DomainID,
						atEpsrv2FromState, atEpsrv2CurrentState,
						atEpsrv2ControlVlanId, atEpsrv2PrimaryIfIndex,
						atEpsrv2PrimaryIfState, atEpsrv2SecondaryIfIndex,
						atEpsrv2SecondaryIfState }
			STATUS current
			DESCRIPTION
				"EPSRv2 Master/Transit node state transition trap."
			::= { atEpsrv2Events 1 }


		-- 1.3.6.1.4.1.207.8.4.4.4.536.2
		atEpsrv2VariablesTable OBJECT-TYPE
			SYNTAX SEQUENCE OF AtEpsrv2VariablesEntry
			MAX-ACCESS not-accessible
			STATUS current
			DESCRIPTION
				"This table contains rows of epsrv2VariablesEntry."
			::= { atEpsrv2 2 }


		-- 1.3.6.1.4.1.207.8.4.4.4.536.2.1
		atEpsrv2VariablesEntry OBJECT-TYPE
			SYNTAX AtEpsrv2VariablesEntry
			MAX-ACCESS not-accessible
			STATUS current
			DESCRIPTION
				"An entry in the ATL enterprise epsrv2VariablesTable."
			INDEX { atEpsrv2DomainID }
			::= { atEpsrv2VariablesTable 1 }


		AtEpsrv2VariablesEntry ::=
			SEQUENCE {
				atEpsrv2NodeType
					INTEGER,
				atEpsrv2DomainName
					DisplayStringUnsized,
				atEpsrv2DomainID
					INTEGER,
				atEpsrv2FromState
					AtEpsrv2NodeState,
				atEpsrv2CurrentState
					AtEpsrv2NodeState,
				atEpsrv2ControlVlanId
					INTEGER,
				atEpsrv2PrimaryIfIndex
					InterfaceIndex,
				atEpsrv2PrimaryIfState
					AtEpsrv2InterfaceState,
				atEpsrv2SecondaryIfIndex
					InterfaceIndex,
				atEpsrv2SecondaryIfState
					AtEpsrv2InterfaceState
			 }

		-- 1.3.6.1.4.1.207.8.4.4.4.536.2.1.1
		atEpsrv2NodeType OBJECT-TYPE
			SYNTAX INTEGER
				{
				masterNode(1),
				transitNode(2)
				}
			MAX-ACCESS read-only
			STATUS current
			DESCRIPTION
				"This is the type of the EPSRv2 node (master/transit)."
			::= { atEpsrv2VariablesEntry 1 }


		-- 1.3.6.1.4.1.207.8.4.4.4.536.2.1.2
		atEpsrv2DomainName OBJECT-TYPE
			SYNTAX DisplayStringUnsized (SIZE (1..16))
			MAX-ACCESS read-only
			STATUS current
			DESCRIPTION
				"Assigned name of the EPSRv2 domain."
			::= { atEpsrv2VariablesEntry 2 }


		-- 1.3.6.1.4.1.207.8.4.4.4.536.2.1.3
		atEpsrv2DomainID OBJECT-TYPE
			SYNTAX INTEGER
			MAX-ACCESS read-only
			STATUS current
			DESCRIPTION
				"Assigned ID of the EPSRv2 domain."
			::= { atEpsrv2VariablesEntry 3 }


		-- 1.3.6.1.4.1.207.8.4.4.4.536.2.1.4
		atEpsrv2FromState OBJECT-TYPE
			SYNTAX AtEpsrv2NodeState
			MAX-ACCESS read-only
			STATUS current
			DESCRIPTION
				"Defined state that an EPSR domain is transitioning from."
			::= { atEpsrv2VariablesEntry 4 }


		-- 1.3.6.1.4.1.207.8.4.4.4.536.2.1.5
		atEpsrv2CurrentState OBJECT-TYPE
			SYNTAX AtEpsrv2NodeState
			MAX-ACCESS read-only
			STATUS current
			DESCRIPTION
				"Defined the current state of an EPSRv2 domain."
			::= { atEpsrv2VariablesEntry 5 }


		-- 1.3.6.1.4.1.207.8.4.4.4.536.2.1.6
		atEpsrv2ControlVlanId OBJECT-TYPE
			SYNTAX INTEGER
			MAX-ACCESS read-only
			STATUS current
			DESCRIPTION
				"VLAN identifier for the control VLAN."
			::= { atEpsrv2VariablesEntry 6 }


		-- 1.3.6.1.4.1.207.8.4.4.4.536.2.1.7
		atEpsrv2PrimaryIfIndex OBJECT-TYPE
			SYNTAX InterfaceIndex
			MAX-ACCESS read-only
			STATUS current
			DESCRIPTION
				"IfIndex of the primary interface."
			::= { atEpsrv2VariablesEntry 7 }


		-- 1.3.6.1.4.1.207.8.4.4.4.536.2.1.8
		atEpsrv2PrimaryIfState OBJECT-TYPE
			SYNTAX AtEpsrv2InterfaceState
			MAX-ACCESS read-only
			STATUS current
			DESCRIPTION
				"Defined current state of the primary interface."
			::= { atEpsrv2VariablesEntry 8 }


		-- 1.3.6.1.4.1.207.8.4.4.4.536.2.1.9
		atEpsrv2SecondaryIfIndex OBJECT-TYPE
			SYNTAX InterfaceIndex
			MAX-ACCESS read-only
			STATUS current
			DESCRIPTION
				"IfIndex of the secondary interface."
			::= { atEpsrv2VariablesEntry 9 }


		-- 1.3.6.1.4.1.207.8.4.4.4.536.2.1.10
		atEpsrv2SecondaryIfState OBJECT-TYPE
			SYNTAX AtEpsrv2InterfaceState
			MAX-ACCESS read-only
			STATUS current
			DESCRIPTION
				"Defined current state of the secondary interface."
			::= { atEpsrv2VariablesEntry 10 }



	END

--
-- AT-EPSRv2-MIB.MIB
--
