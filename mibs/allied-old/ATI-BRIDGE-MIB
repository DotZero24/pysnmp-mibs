--VERSION 3.0
-- History :
--       *    06-26-97 Supports versions:
--                            2.3 to 2.4 (s13)
--                            2.3 to 2.4 (s16)
--                            1.1 to 1.2 (s6)
--
--       * [07-01-97:Nutan] Changed the version number from 1.2 to 3.0.
--
-- This mib is basically the same as the standard Bridge MIB
-- (RFC 1493), except that all variables now have an additional
-- index, namely LAN Id.  This allows the represenation of
-- multiple bridges for multiples LANs within the same box.
-- The object descriptors have been kept similar to the original
-- ones, except "dot1d" has been changed to "atbr"
--
          ATI-BRIDGE-MIB DEFINITIONS ::= BEGIN

          IMPORTS
                     Counter, TimeTicks, enterprises
                             FROM RFC1155-SMI
                     OBJECT-TYPE
                             FROM RFC-1212
                     TRAP-TYPE
                             FROM RFC-1215;

          -- All representations of MAC addresses in this MIB Module
          -- use, as a textual convention (i.e. this convention does
          -- not affect their encoding), the data type:

          MacAddress ::= OCTET STRING (SIZE (6))    -- a 6 octet address
                                                    -- in the
                                                    -- "canonical"
                                                    -- order
          -- defined by IEEE 802.1a, i.e., as if it were transmitted
          -- least significant bit first, even though 802.5 (in
          -- contrast to other n802.x protocols) requires MAC
          -- addresses to be transmitted most significant bit first.
          --
          -- 16-bit addresses, if needed, are represented by setting
          -- their upper 4 octets to all 0's, i.e., AAFF would be
          -- represented as 00000000AAFF.


          -- Similarly, all representations of Bridge-Id in this MIB
          -- Module use, as a textual convention (i.e. this
          -- convention does not affect their encoding), the data
          -- type:

          BridgeId ::= OCTET STRING (SIZE (8))   -- the
                                                 -- Bridge-Identifier
                                                 -- as used in the
                                                 -- Spanning Tree
          -- Protocol to uniquely identify a bridge.  Its first two
          -- octets (in network byte order) contain a priority
          -- value and its last 6 octets contain the MAC address
          -- used to refer to a bridge in a unique fashion
          -- (typically, the numerically smallest MAC address
          -- of all ports on the bridge).

          -- Several objects in this MIB module represent values of
          -- timers used by the Spanning Tree Protocol.  In this
          -- MIB, these timers have values in units of hundreths of
          -- a second (i.e. 1/100 secs).
          -- These timers, when stored in a Spanning Tree Protocol's
          -- BPDU, are in units of 1/256 seconds.  Note, however,
          -- that 802.1D-1990 specifies a settable granularity of
          -- no more than 1 second for these timers.  To avoid
          -- ambiguity, a data type is defined here as a textual
          -- convention and all representation of these timers
          -- in this MIB module are defined using this data type.  An
          -- algorithm is also defined for converting between the
          -- different units, to ensure a timer's value is not
          -- distorted by multiple conversions.
          -- The data type is:

          Timeout ::= INTEGER -- a STP timer in units of 1/100 seconds

          -- To convert a Timeout value into a value in units of
          -- 1/256 seconds, the following algorithm should be used:
          --
          --      b  = floor( (n * 256) / 100)
          --
          -- where:
          --      floor   =  quotient [ignore remainder]
          --      n is the value in 1/100 second units
          --      b is the value in 1/256 second units
          --
          -- To convert the value from 1/256 second units back to
          -- 1/100 seconds, the following algorithm should be used:
          --
          --      n = ceiling( (b * 100) / 256)
          --
          -- where:
          --      ceiling =  quotient [if remainder is 0], or
          --                 quotient + 1 [if remainder is non-zero]
          --      n is the value in 1/100 second units
          --      b is the value in 1/256 second units
          --
          -- Note: it is important that the arithmetic operations are
          -- done in the order specified (i.e., multiply first, divide
          -- second).


          alliedTelesyn    OBJECT IDENTIFIER ::= { enterprises 207 }
          mibObject        OBJECT IDENTIFIER ::= { alliedTelesyn 8 }
          switchMib        OBJECT IDENTIFIER ::= { mibObject 5 }
          atiBridgeMib     OBJECT IDENTIFIER ::= { switchMib 10 }



          -- groups in the Bridge MIB

          atbrBase     OBJECT IDENTIFIER ::= { atiBridgeMib 1 }

          atbrStp      OBJECT IDENTIFIER ::= { atiBridgeMib 2 }

          atbrSr       OBJECT IDENTIFIER ::= { atiBridgeMib 3 }
          -- separately documented

          atbrTp       OBJECT IDENTIFIER ::= { atiBridgeMib 4 }

          atbrStatic   OBJECT IDENTIFIER ::= { atiBridgeMib 5 }


          -- the atbrBase Table

          -- Implementation of the atbrBase table is mandatory for all
          -- bridges.

          atbrBaseTable  OBJECT-TYPE
              SYNTAX    SEQUENCE OF AtbrBaseEntry
              ACCESS    not-accessible
              STATUS    mandatory
              DESCRIPTION
                      "Table of basic bridge information."
              ::= { atbrBase 1 }

          atbrBaseEntry  OBJECT-TYPE
              SYNTAX    AtbrBaseEntry
              ACCESS    not-accessible
              STATUS    mandatory
              DESCRIPTION
                        "An entry in the atbrBaseTable."
              INDEX   { atbrBaseLanId }
              ::= { atbrBaseTable 1 }

          AtbrBaseEntry  ::=
              SEQUENCE {
                  atbrBaseLanId
                      INTEGER,
                  atbrBaseBridgeAddress
                      MacAddress,
                  atbrBaseNumPorts
                      INTEGER,
                  atbrBaseType
                      INTEGER
              }

          atbrBaseLanId OBJECT-TYPE
              SYNTAX  INTEGER
              ACCESS  read-only
              STATUS  mandatory
              DESCRIPTION
                      "This object uniquely identifies the lan or
              emulated lan."
              ::= { atbrBaseEntry 1 }

          atbrBaseBridgeAddress OBJECT-TYPE
              SYNTAX  MacAddress
              ACCESS  read-only
              STATUS  mandatory
              DESCRIPTION
                      "The MAC address used by this bridge when it must
                      be referred to in a unique fashion.   It is
                      recommended that this be the numerically smallest
                      MAC address of all ports that belong to this
                      bridge.  However it is only required to be unique.
                      When concatenated with atbrStpPriority a unique
                      BridgeIdentifier is formed which is used in the
                      Spanning Tree Protocol."
              REFERENCE
                      "IEEE 802.1D-1990: Sections 6.4.1.1.3 and 3.12.5"
              ::= { atbrBaseEntry 2 }

          atbrBaseNumPorts OBJECT-TYPE
              SYNTAX  INTEGER
              ACCESS  read-only
              STATUS  mandatory
              DESCRIPTION
                      "The number of ports controlled by this bridging
                      entity."
              REFERENCE
                      "IEEE 802.1D-1990: Section 6.4.1.1.3"
              ::= { atbrBaseEntry 3 }

          atbrBaseType OBJECT-TYPE
              SYNTAX  INTEGER {
                          unknown(1),
                          transparent-only(2),
                          sourceroute-only(3),
                          srt(4)
                      }
              ACCESS  read-only
              STATUS  mandatory
              DESCRIPTION
                      "Indicates what type of bridging this bridge can
                      perform.  If a bridge is actually performing a
                      certain type of bridging this will be indicated by
                      entries in the port table for the given type."
              ::= { atbrBaseEntry 4 }

          -- The Generic Bridge Port Table

          atbrBasePortTable OBJECT-TYPE
              SYNTAX  SEQUENCE OF AtbrBasePortEntry
              ACCESS  not-accessible
              STATUS  mandatory
              DESCRIPTION
                      "A table that contains generic information about
                      every port that is associated with this bridge.
                      Transparent, source-route, and srt ports are
                      included."
              ::= { atbrBase 4 }

          atbrBasePortEntry OBJECT-TYPE
              SYNTAX  AtbrBasePortEntry
              ACCESS  not-accessible
              STATUS  mandatory
              DESCRIPTION
                      "A list of information for each port of the
                      bridge."
              REFERENCE
                      "IEEE 802.1D-1990: Section 6.4.2, 6.6.1"
              INDEX  { atbrBasePortLanId, atbrBasePort }
              ::= { atbrBasePortTable 1 }


          AtbrBasePortEntry ::=
              SEQUENCE {
                  atbrBasePortLanId
                      INTEGER,
                  atbrBasePort
                      INTEGER,
                  atbrBasePortIfIndex
                      INTEGER,
                  atbrBasePortCircuit
                      OBJECT IDENTIFIER,
                  atbrBasePortDelayExceededDiscards
                      Counter,
                  atbrBasePortMtuExceededDiscards
                      Counter
              }

          atbrBasePortLanId OBJECT-TYPE
              SYNTAX  INTEGER
              ACCESS  read-only
              STATUS  mandatory
              DESCRIPTION
                      "This object uniquely identifies the lan or
              emulated lan."
              ::= { atbrBasePortEntry 1 }

          atbrBasePort OBJECT-TYPE
              SYNTAX  INTEGER (1..65535)
              ACCESS  read-only
              STATUS  mandatory
              DESCRIPTION
                      "The port number of the port for which this entry
                      contains bridge management information."
              ::= { atbrBasePortEntry 2 }

          atbrBasePortIfIndex OBJECT-TYPE
              SYNTAX  INTEGER
              ACCESS  read-only
              STATUS  mandatory
              DESCRIPTION
                      "The value of the instance of the ifIndex object,
                      defined in MIB-II, for the interface corresponding
                      to this port."
              ::= { atbrBasePortEntry 3 }

          atbrBasePortCircuit OBJECT-TYPE
              SYNTAX  OBJECT IDENTIFIER
              ACCESS  read-only
              STATUS  mandatory
              DESCRIPTION
                      "For a port which (potentially) has the same value
                      of atbrBasePortIfIndex as another port on the
                      same bridge, this object contains the name of an
                      object instance unique to this port.  For example,
                      in the case where multiple ports correspond one-
                      to-one with multiple X.25 virtual circuits, this
                      value might identify an (e.g., the first) object
                      instance associated with the X.25 virtual circuit
                      corresponding to this port.

                      For a port which has a unique value of
                      atbrBasePortIfIndex, this object can have the
                      value { 0 0 }."
              ::= { atbrBasePortEntry 4 }

          atbrBasePortDelayExceededDiscards OBJECT-TYPE
              SYNTAX  Counter
              ACCESS  read-only
              STATUS  mandatory
              DESCRIPTION
                      "The number of frames discarded by this port due
                      to excessive transit delay through the bridge.  It
                      is incremented by both transparent and source
                      route bridges."
              REFERENCE
                       "IEEE 802.1D-1990: Section 6.6.1.1.3"
              ::= { atbrBasePortEntry 5 }

          atbrBasePortMtuExceededDiscards OBJECT-TYPE
              SYNTAX  Counter
              ACCESS  read-only
              STATUS  mandatory
              DESCRIPTION
                      "The number of frames discarded by this port due
                      to an excessive size.  It is incremented by both
                      transparent and source route bridges."
              REFERENCE
                      "IEEE 802.1D-1990: Section 6.6.1.1.3"
              ::= { atbrBasePortEntry 6 }


          -- the atbrStp group

          -- Implementation of the atbrStp group is optional.  It is
          -- implemented by those bridges that support the Spanning Tree
          -- Protocol.


          atbrStpTable  OBJECT-TYPE
              SYNTAX    SEQUENCE OF AtbrStpEntry
              ACCESS    not-accessible
              STATUS    mandatory
              DESCRIPTION
                      "Table of bridge spanning tree information."
              ::= { atbrStp 1 }

          atbrStpEntry  OBJECT-TYPE
              SYNTAX    AtbrStpEntry
              ACCESS    not-accessible
              STATUS    mandatory
              DESCRIPTION
                        "An entry in the atbrStpTable."
              INDEX   { atbrStpLanId }
              ::= { atbrStpTable 1 }

          AtbrStpEntry  ::=
              SEQUENCE {
                  atbrStpLanId
                      INTEGER,
                  atbrStpProtocolSpecification
                      INTEGER,
                  atbrStpPriority
                      INTEGER,
                  atbrStpTimeSinceTopologyChange
                      TimeTicks,
                  atbrStpTopChanges
                      Counter,
                  atbrStpDesignatedRoot
                      BridgeId,
                  atbrStpRootCost
                      INTEGER,
                  atbrStpRootPort
                      INTEGER,
                  atbrStpMaxAge
                      Timeout,
                  atbrStpHelloTime
                      Timeout,
                  atbrStpHoldTime
                      INTEGER,
                  atbrStpForwardDelay
                      Timeout,
                  atbrStpBridgeMaxAge
                      Timeout,
                  atbrStpBridgeHelloTime
                      Timeout,
                  atbrStpBridgeForwardDelay
                      Timeout
              }

          atbrStpLanId OBJECT-TYPE
              SYNTAX  INTEGER
              ACCESS  read-only
              STATUS  mandatory
              DESCRIPTION
                      "This object uniquely identifies the lan or
              emulated lan."
              ::= { atbrStpEntry 1 }

          atbrStpProtocolSpecification OBJECT-TYPE
              SYNTAX  INTEGER {
                          unknown(1),
                          decLb100(2),
                          ieee8021d(3)
                      }
              ACCESS  read-only
              STATUS  mandatory
              DESCRIPTION
                      "An indication of what version of the Spanning
                      Tree Protocol is being run.  The value
                      'decLb100(2)' indicates the DEC LANbridge 100
                      Spanning Tree protocol.  IEEE 802.1d
                      implementations will return 'ieee8021d(3)'.  If
                      future versions of the IEEE Spanning Tree Protocol
                      are released that are incompatible with the
                      current version a new value will be defined."
              ::= { atbrStpEntry 2 }

          atbrStpPriority OBJECT-TYPE
              SYNTAX  INTEGER (0..65535)
              ACCESS  read-write
              STATUS  mandatory
              DESCRIPTION
                      "The value of the write-able portion of the Bridge
                      ID, i.e., the first two octets of the (8 octet
                      long) Bridge ID.  The other (last) 6 octets of the
                      Bridge ID are given by the value of
                      atbrBaseBridgeAddress."
              REFERENCE
                      "IEEE 802.1D-1990: Section 4.5.3.7"
              ::= { atbrStpEntry 3 }

          atbrStpTimeSinceTopologyChange OBJECT-TYPE
              SYNTAX  TimeTicks
              ACCESS  read-only
              STATUS  mandatory
              DESCRIPTION
                      "The time (in hundredths of a second) since the
                      last time a topology change was detected by the
                      bridge entity."
              REFERENCE
                      "IEEE 802.1D-1990: Section 6.8.1.1.3"
              ::= { atbrStpEntry 4 }

          atbrStpTopChanges OBJECT-TYPE
              SYNTAX  Counter
              ACCESS  read-only
              STATUS  mandatory
              DESCRIPTION
                      "The total number of topology changes detected by
                      this bridge since the management entity was last
                      reset or initialized."
              REFERENCE
                      "IEEE 802.1D-1990: Section 6.8.1.1.3"
              ::= { atbrStpEntry 5 }

          atbrStpDesignatedRoot OBJECT-TYPE
              SYNTAX  BridgeId
              ACCESS  read-only
              STATUS  mandatory
              DESCRIPTION
                      "The bridge identifier of the root of the spanning
                      tree as determined by the Spanning Tree Protocol
                      as executed by this node.  This value is used as
                      the Root Identifier parameter in all Configuration
                      Bridge PDUs originated by this node."
              REFERENCE
                      "IEEE 802.1D-1990: Section 4.5.3.1"
              ::= { atbrStpEntry 6 }

          atbrStpRootCost OBJECT-TYPE
              SYNTAX  INTEGER
              ACCESS  read-only
              STATUS  mandatory
              DESCRIPTION
                      "The cost of the path to the root as seen from
                      this bridge."
              REFERENCE
                      "IEEE 802.1D-1990: Section 4.5.3.2"
              ::= { atbrStpEntry 7 }

          atbrStpRootPort OBJECT-TYPE
              SYNTAX  INTEGER
              ACCESS  read-only
              STATUS  mandatory
              DESCRIPTION
                      "The port number of the port which offers the
                      lowest cost path from this bridge to the root
                      bridge."
              REFERENCE
                      "IEEE 802.1D-1990: Section 4.5.3.3"
              ::= { atbrStpEntry 8 }

          atbrStpMaxAge OBJECT-TYPE
              SYNTAX  Timeout
              ACCESS  read-only
              STATUS  mandatory
              DESCRIPTION
                      "The maximum age of Spanning Tree Protocol
                      information learned from the network on any port
                      before it is discarded, in units of hundredths of
                      a second.  This is the actual value that this
                      bridge is currently using."
              REFERENCE
                      "IEEE 802.1D-1990: Section 4.5.3.4"
              ::= { atbrStpEntry 9 }

          atbrStpHelloTime OBJECT-TYPE
              SYNTAX  Timeout
              ACCESS  read-only
              STATUS  mandatory
              DESCRIPTION
                      "The amount of time between the transmission of
                      Configuration bridge PDUs by this node on any port
                      when it is the root of the spanning tree or trying
                      to become so, in units of hundredths of a second.
                      This is the actual value that this bridge is
                      currently using."
              REFERENCE
                      "IEEE 802.1D-1990: Section 4.5.3.5"
              ::= { atbrStpEntry 10 }

          atbrStpHoldTime OBJECT-TYPE
              SYNTAX  INTEGER
              ACCESS  read-only
              STATUS  mandatory
              DESCRIPTION
                      "This time value determines the interval length
                      during which no more than two Configuration bridge
                      PDUs shall be transmitted by this node, in units
                      of hundredths of a second."
              REFERENCE
                      "IEEE 802.1D-1990: Section 4.5.3.14"
              ::= { atbrStpEntry 11 }

          atbrStpForwardDelay OBJECT-TYPE
              SYNTAX  Timeout
              ACCESS  read-only
              STATUS  mandatory
              DESCRIPTION
                      "This time value, measured in units of hundredths
                      of a second, controls how fast a port changes its
                      spanning state when moving towards the Forwarding
                      state.  The value determines how long the port
                      stays in each of the Listening and Learning
                      states, which precede the Forwarding state.  This
                      value is also used, when a topology change has
                      been detected and is underway, to age all dynamic
                      entries in the Forwarding Database.  [Note that
                      this value is the one that this bridge is
                      currently using, in contrast to
                      atbrStpBridgeForwardDelay which is the value that
                      this bridge and all others would start using
                      if/when this bridge were to become the root.]"
              REFERENCE
                      "IEEE 802.1D-1990: Section 4.5.3.6"
              ::= { atbrStpEntry 12 }

          atbrStpBridgeMaxAge OBJECT-TYPE
              SYNTAX  Timeout (600..4000)
              ACCESS  read-write
              STATUS  mandatory
              DESCRIPTION
                      "The value that all bridges use for MaxAge when
                      this bridge is acting as the root.  Note that
                      802.1D-1990 specifies that the range for this
                      parameter is related to the value of
                      atbrStpBridgeHelloTime. The granularity of this
                      timer is specified by 802.1D-1990 to be 1 second.
                      An agent may return a badValue error if a set is
                      attempted to a value which is not a whole number
                      of seconds."
              REFERENCE
                      "IEEE 802.1D-1990: Section 4.5.3.8"
              ::= { atbrStpEntry 13 }

          atbrStpBridgeHelloTime OBJECT-TYPE
              SYNTAX  Timeout (100..1000)
              ACCESS  read-write
              STATUS  mandatory
              DESCRIPTION
                      "The value that all bridges use for HelloTime when
                      this bridge is acting as the root.  The
                      granularity of this timer is specified by 802.1D-
                      1990 to be 1 second.  An agent may return a
                      badValue error if a set is attempted to a value
                      which is not a whole number of seconds."
              REFERENCE
                      "IEEE 802.1D-1990: Section 4.5.3.9"
              ::= { atbrStpEntry 14 }

          atbrStpBridgeForwardDelay OBJECT-TYPE
              SYNTAX  Timeout (400..3000)
              ACCESS  read-write
              STATUS  mandatory
              DESCRIPTION
                      "The value that all bridges use for ForwardDelay
                      when this bridge is acting as the root.  Note that
                      802.1D-1990 specifies that the range for this
                      parameter is related to the value of
                      atbrStpBridgeMaxAge.  The granularity of this
                      timer is specified by 802.1D-1990 to be 1 second.
                      An agent may return a badValue error if a set is
                      attempted to a value which is not a whole number
                      of seconds."
              REFERENCE
                      "IEEE 802.1D-1990: Section 4.5.3.10"
              ::= { atbrStpEntry 15 }


          -- The Spanning Tree Port Table

          atbrStpPortTable OBJECT-TYPE
              SYNTAX  SEQUENCE OF AtbrStpPortEntry
              ACCESS  not-accessible
              STATUS  mandatory
              DESCRIPTION
                      "A table that contains port-specific information
                      for the Spanning Tree Protocol."
              ::= { atbrStp 15 }

          atbrStpPortEntry OBJECT-TYPE
              SYNTAX  AtbrStpPortEntry
              ACCESS  not-accessible
              STATUS  mandatory
              DESCRIPTION
                      "A list of information maintained by every port
                      about the Spanning Tree Protocol state for that
                      port."
              INDEX   { atbrStpPortLanId, atbrStpPort }
              ::= { atbrStpPortTable 1 }

          AtbrStpPortEntry ::=
              SEQUENCE {
                  atbrStpPortLanId
                      INTEGER,
                  atbrStpPort
                      INTEGER,
                  atbrStpPortPriority
                      INTEGER,
                  atbrStpPortState
                      INTEGER,
                  atbrStpPortEnable
                      INTEGER,
                  atbrStpPortPathCost
                      INTEGER,
                  atbrStpPortDesignatedRoot
                      BridgeId,
                  atbrStpPortDesignatedCost
                      INTEGER,
                  atbrStpPortDesignatedBridge
                      BridgeId,
                  atbrStpPortDesignatedPort
                      OCTET STRING,
                  atbrStpPortForwardTransitions
                      Counter
              }

          atbrStpPortLanId OBJECT-TYPE
              SYNTAX  INTEGER
              ACCESS  read-only
              STATUS  mandatory
              DESCRIPTION
                      "This object uniquely identifies the lan or
              emulated lan."
              ::= { atbrStpPortEntry 1 }

          atbrStpPort OBJECT-TYPE
              SYNTAX  INTEGER (1..65535)
              ACCESS  read-only
              STATUS  mandatory
              DESCRIPTION
                      "The port number of the port for which this entry
                      contains Spanning Tree Protocol management
                      information."
              REFERENCE
                      "IEEE 802.1D-1990: Section 6.8.2.1.2"
              ::= { atbrStpPortEntry 2 }

          atbrStpPortPriority OBJECT-TYPE
              SYNTAX  INTEGER (0..255)
              ACCESS  read-write
              STATUS  mandatory
              DESCRIPTION
                      "The value of the priority field which is
                      contained in the first (in network byte order)
                      octet of the (2 octet long) Port ID.  The other
                      octet of the Port ID is given by the value of
                      atbrStpPort."
              REFERENCE
                      "IEEE 802.1D-1990: Section 4.5.5.1"
              ::= { atbrStpPortEntry 3 }

          atbrStpPortState OBJECT-TYPE
              SYNTAX  INTEGER {
                          disabled(1),
                          blocking(2),
                          listening(3),
                          learning(4),
                          forwarding(5),
                          broken(6)
                      }
              ACCESS  read-only
              STATUS  mandatory
              DESCRIPTION
                      "The port's current state as defined by
                      application of the Spanning Tree Protocol.  This
                      state controls what action a port takes on
                      reception of a frame.  If the bridge has detected
                      a port that is malfunctioning it will place that
                      port into the broken(6) state.  For ports which
                      are disabled (see atbrStpPortEnable), this object
                      will have a value of disabled(1)."
              REFERENCE
                      "IEEE 802.1D-1990: Section 4.5.5.2"
              ::= { atbrStpPortEntry 4 }

          atbrStpPortEnable OBJECT-TYPE
              SYNTAX  INTEGER {
                          enabled(1),
                          disabled(2)
                      }
              ACCESS  read-write
              STATUS  mandatory
              DESCRIPTION
                      "The enabled/disabled status of the port."
              REFERENCE
                      "IEEE 802.1D-1990: Section 4.5.5.2"
              ::= { atbrStpPortEntry 5 }

          atbrStpPortPathCost OBJECT-TYPE
              SYNTAX  INTEGER (1..65535)
              ACCESS  read-write
              STATUS  mandatory
              DESCRIPTION
                      "The contribution of this port to the path cost of
                      paths towards the spanning tree root which include
                      this port.  802.1D-1990 recommends that the
                      default value of this parameter be in inverse
                      proportion to the speed of the attached LAN."
              REFERENCE
                      "IEEE 802.1D-1990: Section 4.5.5.3"
              ::= { atbrStpPortEntry 6 }

          atbrStpPortDesignatedRoot OBJECT-TYPE
              SYNTAX  BridgeId
              ACCESS  read-only
              STATUS  mandatory
              DESCRIPTION
                      "The unique Bridge Identifier of the Bridge
                      recorded as the Root in the Configuration BPDUs
                      transmitted by the Designated Bridge for the
                      segment to which the port is attached."
              REFERENCE
                      "IEEE 802.1D-1990: Section 4.5.5.4"
              ::= { atbrStpPortEntry 7 }

          atbrStpPortDesignatedCost OBJECT-TYPE
              SYNTAX  INTEGER
              ACCESS  read-only
              STATUS  mandatory
              DESCRIPTION
                      "The path cost of the Designated Port of the
                      segment connected to this port.  This value is
                      compared to the Root Path Cost field in received
                      bridge PDUs."
              REFERENCE
                      "IEEE 802.1D-1990: Section 4.5.5.5"
              ::= { atbrStpPortEntry 8 }

          atbrStpPortDesignatedBridge OBJECT-TYPE
              SYNTAX  BridgeId
              ACCESS  read-only
              STATUS  mandatory
              DESCRIPTION
                      "The Bridge Identifier of the bridge which this
                      port considers to be the Designated Bridge for
                      this port's segment."
              REFERENCE
                      "IEEE 802.1D-1990: Section 4.5.5.6"
              ::= { atbrStpPortEntry 9 }

          atbrStpPortDesignatedPort OBJECT-TYPE
              SYNTAX  OCTET STRING (SIZE (2))
              ACCESS  read-only
              STATUS  mandatory
              DESCRIPTION
                      "The Port Identifier of the port on the Designated
                      Bridge for this port's segment."
              REFERENCE
                      "IEEE 802.1D-1990: Section 4.5.5.7"
              ::= { atbrStpPortEntry 10 }

          atbrStpPortForwardTransitions OBJECT-TYPE
              SYNTAX  Counter
              ACCESS  read-only
              STATUS  mandatory
              DESCRIPTION
                      "The number of times this port has transitioned
                      from the Learning state to the Forwarding state."
              ::= { atbrStpPortEntry 11 }


          -- the atbrTp group

          -- Implementation of the atbrTp group is optional.  It is
          -- implemented by those bridges that support the transparent
          -- bridging mode.  A transparent or SRT bridge will implement
          -- this group.


          atbrTpTable  OBJECT-TYPE
              SYNTAX    SEQUENCE OF AtbrTpEntry
              ACCESS    not-accessible
              STATUS    mandatory
              DESCRIPTION
                        "Table of transparent bridging information."
              ::= { atbrTp 1 }

          atbrTpEntry  OBJECT-TYPE
              SYNTAX    AtbrTpEntry
              ACCESS    not-accessible
              STATUS    mandatory
              DESCRIPTION
                        "An entry in the atbrTpTable."
              INDEX   { atbrTpLanId }
              ::= { atbrTpTable 1 }

          AtbrTpEntry  ::=
              SEQUENCE {
                  atbrTpLanId
                      INTEGER,
                  atbrTpLearnedEntryDiscards
                      Counter,
                  atbrTpAgingTime
                      INTEGER
              }

          atbrTpLanId OBJECT-TYPE
              SYNTAX  INTEGER
              ACCESS  read-only
              STATUS  mandatory
              DESCRIPTION
                      "This object uniquely identifies the lan or
              emulated lan."
              ::= { atbrTpEntry 1 }

          atbrTpLearnedEntryDiscards OBJECT-TYPE
              SYNTAX  Counter
              ACCESS  read-only
              STATUS  mandatory
              DESCRIPTION
                      "The total number of Forwarding Database entries,
                      which have been or would have been learnt, but
                      have been discarded due to a lack of space to
                      store them in the Forwarding Database.  If this
                      counter is increasing, it indicates that the
                      Forwarding Database is regularly becoming full (a
                      condition which has unpleasant performance effects
                      on the subnetwork).  If this counter has a
                      significant value but is not presently increasing,
                      it indicates that the problem has been occurring
                      but is not persistent."
              REFERENCE
                      "IEEE 802.1D-1990: Section 6.7.1.1.3"
              ::= { atbrTpEntry 2 }

          atbrTpAgingTime OBJECT-TYPE
              SYNTAX   INTEGER (10..1000000)
              ACCESS   read-write
              STATUS   mandatory
              DESCRIPTION
                      "The timeout period in seconds for aging out
                      dynamically learned forwarding information.
                      802.1D-1990 recommends a default of 300 seconds."
              REFERENCE
                      "IEEE 802.1D-1990: Section 6.7.1.1.3"
              ::= { atbrTpEntry 3 }


          --  The Forwarding Database for Transparent Bridges

          atbrTpFdbTable OBJECT-TYPE
              SYNTAX  SEQUENCE OF AtbrTpFdbEntry
              ACCESS  not-accessible
              STATUS  mandatory
              DESCRIPTION
                      "A table that contains information about unicast
                      entries for which the bridge has forwarding and/or
                      filtering information.  This information is used
                      by the transparent bridging function in
                      determining how to propagate a received frame."
              ::= { atbrTp 3 }

          atbrTpFdbEntry OBJECT-TYPE
              SYNTAX  AtbrTpFdbEntry
              ACCESS  not-accessible
              STATUS  mandatory
              DESCRIPTION
                      "Information about a specific unicast MAC address
                      for which the bridge has some forwarding and/or
                      filtering information."
              INDEX   { atbrTpFdbLanId, atbrTpFdbAddress }
              ::= { atbrTpFdbTable 1 }

          AtbrTpFdbEntry ::=
              SEQUENCE {
                  atbrTpFdbLanId
                      INTEGER,
                  atbrTpFdbAddress
                      MacAddress,
                  atbrTpFdbPort
                      INTEGER,
                  atbrTpFdbStatus
                      INTEGER
--			,
--		  atbrTpFdbAge
--		      INTEGER,
--		  atbrTpFdbVci
--		      INTEGER
              }

          atbrTpFdbLanId OBJECT-TYPE
              SYNTAX  INTEGER
              ACCESS  read-only
              STATUS  mandatory
              DESCRIPTION
                      "This object uniquely identifies the lan or
              emulated lan."
              ::= { atbrTpFdbEntry 1 }

          atbrTpFdbAddress OBJECT-TYPE
              SYNTAX  MacAddress
              ACCESS  read-only
              STATUS  mandatory
              DESCRIPTION
                      "A unicast MAC address for which the bridge has
                      forwarding and/or filtering information."
              REFERENCE
                      "IEEE 802.1D-1990: Section 3.9.1, 3.9.2"
              ::= { atbrTpFdbEntry 2 }

          atbrTpFdbPort OBJECT-TYPE
              SYNTAX  INTEGER
              ACCESS  read-only
              STATUS  mandatory
              DESCRIPTION
                      "Either the value '0', or the port number of the
                      port on which a frame having a source address
                      equal to the value of the corresponding instance
                      of atbrTpFdbAddress has been seen.  A value of
                      '0' indicates that the port number has not been
                      learned but that the bridge does have some
                      forwarding/filtering information about this
                      address (e.g. in the atbrStaticTable).
                      Implementors are encouraged to assign the port
                      value to this object whenever it is learned even
                      for addresses for which the corresponding value of
                      atbrTpFdbStatus is not learned(3)."
              ::= { atbrTpFdbEntry 3 }

          atbrTpFdbStatus OBJECT-TYPE
              SYNTAX  INTEGER {
                          inactive(1),
                          le-arp-pending(2),
			  vcc-setup-pending (3),
			  vlan-resolve-pending (4),
			  join-pending (5),
			  active (6),
			  other (7)
                      }
              ACCESS  read-only
              STATUS  mandatory
              DESCRIPTION
                      "The status of this entry. please note, some of the
		       status is specific for At4016 and At3695.
		       The meanings of the values are:

                        inactive(1) : this entry is not longer valid
                                     (e.g., it was learned but has since
                                     aged-out), but has not yet been
                                     flushed from the table.

			le-arp-pending(2):Waiting for the le-arp to be resolved.
					 This is only for AT4016/3695.

			vcc-setup-pending (3) : Waiting for VCC to be setup.
					 This is only for AT4016/3695.

			vlan-resolve-pending(4) : Waiting for the Vlan to be
					       resolved by communicating with
					       the LECS.
					 This is only for AT4016/3695.

			join-pending(5) : LEC in te stage of joining to the ELans.
					 This is only for AT4016/3695.

                        active(6) : the value of the corresponding
                                     instance of atbrTpFdbPort was
                                     active, and is being used.

                        other(7)   : none of the following.  This would
                                     include the case where some other
                                     MIB object (not the corresponding
                                     instance of atbrTpFdbPort, nor an
                                     entry in the atbrStaticTable) is
                                     being used to determine if and how
                                     frames addressed to the value of
                                     the corresponding instance of
                                     atbrTpFdbAddress are being
                                     forwarded.

---                        self(4)    : the value of the corresponding
---                                     instance of atbrTpFdbAddress
---                                     represents one of the bridge's
---                                     addresses.  The corresponding
---                                     instance of atbrTpFdbPort
---                                     indicates which of the bridge's
---                                     ports has this address.
---
---                        mgmt(5)    : the value of the corresponding
---                                     instance of atbrTpFdbAddress is
---                                     also the value of an existing
---                                     instance of atbrStaticAddress."
              ::= { atbrTpFdbEntry 4 }

--	   atbrTpFdbAge OBJECT-TYPE
--		SYNTAX	INTEGER
--		ACCESS	read-only
--		STATUS	mandatory
--		DESCRIPTION
--		"Current Age of the MACAddr in the Forwarding Table.It Starts
--		 with 0 and if not heard it increments to some value until it
--		 hears from it  and if not heard before reaching Max value, it 			 will purge this entry.
--		"
--             ::= { atbrTpFdbEntry 5 }


--	   atbrTpFdbVci OBJECT-TYPE
--		SYNTAX	INTEGER
--		ACCESS	read-only
--		STATUS	mandatory
--		DESCRIPTION
--		" The Virtual Lan to which this Entry in the table belongs.
--		"
--		::= { atbrTpFdbEntry 6 }

          --  Port Table for Transparent Bridges

          atbrTpPortTable OBJECT-TYPE
              SYNTAX  SEQUENCE OF AtbrTpPortEntry
              ACCESS  not-accessible
              STATUS  mandatory
              DESCRIPTION
                      "A table that contains information about every
                      port that is associated with this transparent
                      bridge."
              ::= { atbrTp 4 }

          atbrTpPortEntry OBJECT-TYPE
              SYNTAX  AtbrTpPortEntry
              ACCESS  not-accessible
              STATUS  mandatory
              DESCRIPTION
                      "A list of information for each port of a
                      transparent bridge."
              INDEX   { atbrTpPortLanId, atbrTpPort }
              ::= { atbrTpPortTable 1 }

          AtbrTpPortEntry ::=
              SEQUENCE {
                  atbrTpPortLanId
                      INTEGER,
                  atbrTpPort
                      INTEGER,
                  atbrTpPortMaxInfo
                      INTEGER,
                  atbrTpPortInFrames
                      Counter,
                  atbrTpPortOutFrames
                      Counter,
                  atbrTpPortInDiscards
                      Counter
              }

          atbrTpPortLanId OBJECT-TYPE
              SYNTAX  INTEGER
              ACCESS  read-only
              STATUS  mandatory
              DESCRIPTION
                      "This object uniquely identifies the lan or
              emulated lan."
              ::= { atbrTpPortEntry 1 }

          atbrTpPort OBJECT-TYPE
              SYNTAX  INTEGER (1..65535)
              ACCESS  read-only
              STATUS  mandatory
              DESCRIPTION
                      "The port number of the port for which this entry
                      contains Transparent bridging management
                      information."
              ::= { atbrTpPortEntry 2 }

          -- It would be nice if we could use ifMtu as the size of the
          -- largest INFO field, but we can't because ifMtu is defined
          -- to be the size that the (inter-)network layer can use which
          -- can differ from the MAC layer (especially if several layers
          -- of encapsulation are used).

          atbrTpPortMaxInfo OBJECT-TYPE
              SYNTAX  INTEGER
              ACCESS  read-only
              STATUS  mandatory
              DESCRIPTION
                      "The maximum size of the INFO (non-MAC) field that
                      this port will receive or transmit."
              ::= { atbrTpPortEntry 3 }

          atbrTpPortInFrames OBJECT-TYPE
              SYNTAX  Counter
              ACCESS  read-only
              STATUS  mandatory
              DESCRIPTION
                      "The number of frames that have been received by
                      this port from its segment. Note that a frame
                      received on the interface corresponding to this
                      port is only counted by this object if and only if
                      it is for a protocol being processed by the local
                      bridging function, including bridge management
                      frames."
              REFERENCE
                      "IEEE 802.1D-1990: Section 6.6.1.1.3"
              ::= { atbrTpPortEntry 4 }

          atbrTpPortOutFrames OBJECT-TYPE
              SYNTAX  Counter
              ACCESS  read-only
              STATUS  mandatory
              DESCRIPTION
                      "The number of frames that have been transmitted
                      by this port to its segment.  Note that a frame
                      transmitted on the interface corresponding to this
                      port is only counted by this object if and only if
                      it is for a protocol being processed by the local
                      bridging function, including bridge management
                      frames."
              REFERENCE
                      "IEEE 802.1D-1990: Section 6.6.1.1.3"
              ::= { atbrTpPortEntry 5 }

          atbrTpPortInDiscards OBJECT-TYPE
              SYNTAX   Counter
              ACCESS   read-only
              STATUS   mandatory
              DESCRIPTION
                      "Count of valid frames received which were
                      discarded (i.e., filtered) by the Forwarding
                      Process."
              REFERENCE
                      "IEEE 802.1D-1990: Section 6.6.1.1.3"
              ::= { atbrTpPortEntry 6 }


          -- The Static (Destination-Address Filtering) Database

          -- Implementation of this group is optional.


          atbrStaticTable OBJECT-TYPE
              SYNTAX  SEQUENCE OF AtbrStaticEntry
              ACCESS  not-accessible
              STATUS  mandatory
              DESCRIPTION
                      "A table containing filtering information
                      configured into the bridge by (local or network)
                      management specifying the set of ports to which
                      frames received from specific ports and containing
                      specific destination addresses are allowed to be
                      forwarded.  The value of zero in this table as the
                      port number from which frames with a specific
                      destination address are received, is used to
                      specify all ports for which there is no specific
                      entry in this table for that particular
                      destination address.  Entries are valid for
                      unicast and for group/broadcast addresses."
              REFERENCE
                      "IEEE 802.1D-1990: Section 6.7.2"
              ::= { atbrStatic 1 }

          atbrStaticEntry OBJECT-TYPE
              SYNTAX  AtbrStaticEntry
              ACCESS  not-accessible
              STATUS  mandatory
              DESCRIPTION
                      "Filtering information configured into the bridge
                      by (local or network) management specifying the
                      set of ports to which frames received from a
                      specific port and containing a specific
                      destination address are allowed to be forwarded."
              REFERENCE
                      "IEEE 802.1D-1990: Section 6.7.2"
              INDEX   { atbrStaticLanId,
                        atbrStaticAddress, atbrStaticReceivePort }
              ::= { atbrStaticTable 1 }

          AtbrStaticEntry ::=
              SEQUENCE {
                  atbrStaticLanId
                      INTEGER,
                  atbrStaticAddress
                      MacAddress,
                  atbrStaticReceivePort
                      INTEGER,
                  atbrStaticAllowedToGoTo
                      OCTET STRING,
                  atbrStaticStatus
                      INTEGER
              }

          atbrStaticLanId OBJECT-TYPE
              SYNTAX  INTEGER
              ACCESS  read-only
              STATUS  mandatory
              DESCRIPTION
                      "This object uniquely identifies the lan or
              emulated lan."
              ::= { atbrStaticEntry 1 }

          atbrStaticAddress OBJECT-TYPE
              SYNTAX  MacAddress
              ACCESS  read-write
              STATUS  mandatory
              DESCRIPTION
                      "The destination MAC address in a frame to which
                      this entry's filtering information applies.  This
                      object can take the value of a unicast address, a
                      group address or the broadcast address."
              REFERENCE
                      "IEEE 802.1D-1990: Section 3.9.1, 3.9.2"
              ::= { atbrStaticEntry 2 }

          atbrStaticReceivePort OBJECT-TYPE
              SYNTAX  INTEGER
              ACCESS  read-write
              STATUS  mandatory
              DESCRIPTION
                      "Either the value '0', or the port number of the
                      port from which a frame must be received in order
                      for this entry's filtering information to apply.
                      A value of zero indicates that this entry applies
                      on all ports of the bridge for which there is no
                      other applicable entry."
              ::= { atbrStaticEntry 3 }

          atbrStaticAllowedToGoTo OBJECT-TYPE
              SYNTAX  OCTET STRING
              ACCESS  read-write
              STATUS  mandatory
              DESCRIPTION
                      "The set of ports to which frames received from a
                      specific port and destined for a specific MAC
                      address, are allowed to be forwarded.  Each octet
                      within the value of this object specifies a set of
                      eight ports, with the first octet specifying ports
                      1 through 8, the second octet specifying ports 9
                      through 16, etc.  Within each octet, the most
                      significant bit represents the lowest numbered
                      port, and the least significant bit represents the
                      highest numbered port.  Thus, each port of the
                      bridge is represented by a single bit within the
                      value of this object.  If that bit has a value of
                      '1' then that port is included in the set of
                      ports; the port is not included if its bit has a
                      value of '0'.  (Note that the setting of the bit
                      corresponding to the port from which a frame is
                      received is irrelevant.)  The default value of
                      this object is a string of ones of appropriate
                      length."
              ::= { atbrStaticEntry 4 }

          atbrStaticStatus OBJECT-TYPE
              SYNTAX  INTEGER {
                          other(1),
                          invalid(2),
                          permanent(3),
                          deleteOnReset(4),
                          deleteOnTimeout(5)
                      }
              ACCESS  read-write
              STATUS  mandatory
              DESCRIPTION
                      "This object indicates the status of this entry.
                      The default value is permanent(3).

                           other(1) - this entry is currently in use but
                                the conditions under which it will
                                remain so are different from each of the
                                following values.
                           invalid(2) - writing this value to the object
                                removes the corresponding entry.
                           permanent(3) - this entry is currently in use
                                and will remain so after the next reset
                                of the bridge.
                           deleteOnReset(4) - this entry is currently in
                                use and will remain so until the next
                                reset of the bridge.
                           deleteOnTimeout(5) - this entry is currently
                                in use and will remain so until it is
                                aged out."
              ::= { atbrStaticEntry 5 }


          -- Traps for use by Bridges

          -- Traps for the Spanning Tree Protocol

          newRoot TRAP-TYPE
              ENTERPRISE  alliedTelesyn
              DESCRIPTION
                      "The newRoot trap indicates that the sending agent
                      has become the new root of the Spanning Tree; the
                      trap is sent by a bridge soon after its election
                      as the new root, e.g., upon expiration of the
                      Topology Change Timer immediately subsequent to
                      its election.  Implementation of this trap is
                      optional."
              ::= 101

          topologyChange TRAP-TYPE
              ENTERPRISE  alliedTelesyn
              DESCRIPTION
                      "A topologyChange trap is sent by a bridge when
                      any of its configured ports transitions from the
                      Learning state to the Forwarding state, or from
                      the Forwarding state to the Blocking state.  The
                      trap is not sent if a newRoot trap is sent for the
                      same transition.  Implementation of this trap is
                      optional."
              ::= 102

          END
