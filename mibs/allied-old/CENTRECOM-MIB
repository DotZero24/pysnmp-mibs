--/*
-- * $RCSfile: atkkext.mib $ - ATKK Model CentreCOM 8500 and 9100 Enterprise MIB
-- *
-- * Copyright (c) 1997-8 by Extreme Networks Inc.
-- *
-- *	  Allied Telesis K.K
-- *      http://www1.allied-telesis.co.jp/GIGA
-- *
-- *
-- * Revision control history
-- * ------------------------
-- * $Id: atkkext.mib 1.4 1998/11/12 22:30:11 abhatt PR3811 abhatt $ $Name: PR3811 $ $ProjectRevision: 1.118.1.9 $
-- *
-- * modification history
-- * --------------------
-- * $Log: atkkext.mib $
-- * Revision 1.4  1998/11/12 22:30:11  abhatt
-- * Revision 1.3  1998/11/12 22:28:49  abhatt
-- * Modified the enterprise-name, www-site-address, etc. globally.
-- * Revision 1.2  1998/11/09 22:48:16  abhatt
-- * Changed file name from atkk.mib to atkkext.mib upon request.
-- * Revision 1.1  1998/11/09 22:41:34  abhatt
-- * Initial revision
-- * Revision 1.4  1998/10/20 00:56:06  abhatt
-- * Revision 1.3  1998/10/20 00:52:51  abhatt
-- * PR3715
-- * Revision 1.2  1998/04/15 20:41:04  asmith
-- * add <CR> to make HPOV happy
-- * Revision 1.1  1998/02/19 23:02:51  asmith
-- * Initial revision
-- */

CENTRECOM-MIB DEFINITIONS ::= BEGIN

	IMPORTS
		enterprises
    	  FROM RFC1155-SMI
		sysUpTime, sysDescr
    	  FROM RFC1213-MIB
		TRAP-TYPE
    	  FROM RFC-1215;


	--  Organization & Product branches

        ati			OBJECT IDENTIFIER ::= { enterprises 207 }

	products                OBJECT IDENTIFIER ::= { ati 1 }
	mibObjects              OBJECT IDENTIFIER ::= { ati 8 }

        atkkSwitchMIB           OBJECT IDENTIFIER ::= { mibObjects 12 }
        extSwitchMIB            OBJECT IDENTIFIER ::= { atkkSwitchMIB 2 }
        centreCom               OBJECT IDENTIFIER ::= { products 4 }

        --
        -- ATKK Products
        --
        centrecom8500sx		OBJECT IDENTIFIER ::= { centreCom 16 }
        centrecom8500lx		OBJECT IDENTIFIER ::= { centreCom 17 }
        centrecom9100sx		OBJECT IDENTIFIER ::= { centreCom 18 }
        centrecom9100lx		OBJECT IDENTIFIER ::= { centreCom 19 }

END
