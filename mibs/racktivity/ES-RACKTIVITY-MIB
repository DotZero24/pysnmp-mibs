--********************************************************************************
--* Racktivity n.v. 2011                                                         *
--* This is autogenerated code with RTS0019: RMCP Code Generator V0.3.2          *
--* This code is generated on : 23/04/2014 15:33:37(UTC)                         *
--* With parameters: <version> <arguments> <gen Master code>                     *
--********************************************************************************


ES-RACKTIVITY-MIB DEFINITIONS ::= BEGIN

IMPORTS
    TimeTicks, Unsigned32, Integer32, IpAddress, MODULE-IDENTITY, NOTIFICATION-TYPE,
    OBJECT-TYPE, enterprises
        FROM SNMPv2-SMI
		OBJECT-GROUP, MODULE-COMPLIANCE, NOTIFICATION-GROUP
				FROM SNMPv2-CONF
    TEXTUAL-CONVENTION, DisplayString, MacAddress
        FROM SNMPv2-TC;


esRACKTIVITYMIB MODULE-IDENTITY
	LAST-UPDATED "201404230333Z"
	ORGANIZATION "Racktivity"
	CONTACT-INFO "http://www.racktivity.com"
	DESCRIPTION  "The MIB module for the Racktivity Devices"

	REVISION     "201404230333Z"
	DESCRIPTION  "Initial version"
	::= { enterprises 34097 9 }



Version ::= TEXTUAL-CONVENTION
	DISPLAY-HINT "1d.1d.1d.1d"
	STATUS       current
	DESCRIPTION "Displays a version number"
	SYNTAX      OCTET STRING (SIZE (4))

racktivity OBJECT IDENTIFIER
    ::= { enterprises 34097 }

racktivityNotif OBJECT IDENTIFIER
    ::= { esRACKTIVITYMIB 0 }


Utenth ::= TEXTUAL-CONVENTION
	DISPLAY-HINT "d-1"
	STATUS       current
	DESCRIPTION "0.1"
	SYNTAX     Unsigned32

Uhundredth ::= TEXTUAL-CONVENTION
	DISPLAY-HINT "d-2"
	STATUS       current
	DESCRIPTION "0.01"
	SYNTAX     Unsigned32

Uthousandth ::= TEXTUAL-CONVENTION
	DISPLAY-HINT "d-3"
	STATUS       current
	DESCRIPTION "0.001"
	SYNTAX     Unsigned32


Stenth ::= TEXTUAL-CONVENTION
	DISPLAY-HINT "d-1"
	STATUS       current
	DESCRIPTION "0.1"
	SYNTAX     Integer32

Shundredth ::= TEXTUAL-CONVENTION
	DISPLAY-HINT "d-2"
	STATUS       current
	DESCRIPTION "0.01"
	SYNTAX     Integer32

Sthousandth ::= TEXTUAL-CONVENTION
	DISPLAY-HINT "d-3"
	STATUS       current
	DESCRIPTION "0.001"
	SYNTAX     Integer32


EVENTFLAGS ::= TEXTUAL-CONVENTION
	STATUS       current
	DESCRIPTION "enumeration of all eventflags possible"
	SYNTAX     	INTEGER {
					sNMPTrapOff(0),
					sNMPTrapOn(1)
				}

CURPORTSTATE ::= TEXTUAL-CONVENTION
	STATUS       current
	DESCRIPTION "enumeration of all port states possible"
	SYNTAX     	INTEGER {
					portOff(0),
					portOnNoWarning(1),
					portOff1(2),
					portOnWithWarningCurrent(3),
					portOff2(4),
					portOnWithWarningPower(5),
					portOff3(6),
					portOnWithWarningCurrentAndPower(7),
					portOffWithError(8),
					portOnNoWarning1(9),
					portOffWithError1(10),
					portOnWithWarningCurrent1(11),
					portOffWithError2(12),
					portOnWithWarningPower1(13),
					portOffWithError3(14),
					portOnWithWarnCurrentAndPower1(15),
					portOffWithDelayOn(16),
					portOnNoWarning2(17),
					portOffWithDelayOn1(18),
					portOnWithWarningCurrent2(19),
					portOffWithDelayOn2(20),
					portOnWithWarningPower2(21),
					portOffWithDelayOn3(22),
					portOnWithWarnCurrentAndPower2(23)
				}



masterModule OBJECT IDENTIFIER
	::= { esRACKTIVITYMIB 77 }

eMasterTable OBJECT-TYPE
	SYNTAX      SEQUENCE OF EMasterEntry
	MAX-ACCESS  not-accessible
	STATUS      current
	DESCRIPTION
		"NO_INFO"
	::= { masterModule 1 }

eMasterEntry OBJECT-TYPE
	SYNTAX      EMasterEntry
	MAX-ACCESS  not-accessible
	STATUS      current
	DESCRIPTION
		"NO_INFO"
	INDEX       { masterModuleIndex, masterIndex }
	::= { eMasterTable 1 }

EMasterEntry ::= SEQUENCE {
	mGeneralModuleStatus          Unsigned32,
	mSpecificModuleStatus         Unsigned32,
	mCurrentTime                  TimeTicks,
	mVoltage                      Uhundredth,
	mTemperature                  Utenth,
	mCurrentIP                    IpAddress,
	mTotalCurrent                 Uthousandth,
	mTotalRealPower               Unsigned32,
	mTotalActiveEnergy            Uthousandth,
	mLineCurrent                  Uthousandth,
	mFuseCurrent                  Uthousandth,
	mCurrentSubNetMask            IpAddress,
	mCurrentDNSServer             IpAddress,
	mCurrentStdGateway            IpAddress,
	mUPSPresent                   Unsigned32,
	mUPSStatus                    Unsigned32,
	mUPSEstimatedRunTime          Unsigned32,
	mUPSBatteryLevel              Utenth,
	mHighCurrent                  Stenth,
	mUpsCommunicationStatus       Unsigned32,
	mHighPower                    Shundredth,
	mTotalHighCurrent             Stenth,
	mTotalHighPower               Shundredth,
	mPositiveEnergy               Uthousandth,
	mNegativeEnergy               Uthousandth,
	mTotalPositiveEnergy          Uthousandth,
	mTotalNegativeEnergy          Uthousandth,
	mCloudStatus                  Unsigned32,
	mStatus                       Unsigned32,
	mModuleName                   DisplayString,
	mFirmwareVersion              Version,
	mHardwareVersion              Version,
	mFirmwareID                   DisplayString,
	mHardwareID                   DisplayString,
	mRackName                     DisplayString,
	mRackPosition                 DisplayString,
	mIPAddress                    IpAddress,
	mSubNetMask                   IpAddress,
	mStdGateWay                   IpAddress,
	mDnsServer                    IpAddress,
	mMAC                          MacAddress,
	mDHCPEnable                   Unsigned32,
	mNTPServer                    IpAddress,
	mUseDefaultNTPServer          Unsigned32,
	mUseNTP                       Unsigned32,
	mSNMPTrapRecvIP               IpAddress,
	mSNMPTrapRecvPort             Unsigned32,
	mSNMPControl                  Unsigned32,
	mECSServer                    IpAddress,
	mUseECSServer                 Unsigned32,
	mDisplayLock                  Unsigned32,
	mDisplayTimeOn                Unsigned32,
	mMaxVoltageWarning            Uhundredth,
	mMinVoltageWarning            Uhundredth,
	mMinTemperatureWarning        Utenth,
	mMaxTemperatureWarning        Utenth,
	mGeneralEventEnable           EVENTFLAGS,
	mSNMPSysContact               DisplayString,
	mCurrentWarningEvent          EVENTFLAGS,
	mPowerWarningEvent            EVENTFLAGS,
	mTotalCurrentWarningEvent     EVENTFLAGS,
	mTotalPowerWarningEvent       EVENTFLAGS,
	mVoltageWarningEvent          EVENTFLAGS,
	mTemperatureWarningEvent      EVENTFLAGS,
	mDisplayBrightness            Unsigned32,
	mECSServerPort                Unsigned32,
	mExternalSensorLabel          DisplayString,
	mHttpsOnly                    Unsigned32,
	mTelnetSsl                    Unsigned32,
	mCookieTimeToLive             Unsigned32,
	mLineCurrentWarningThreshold  Uthousandth,
	mLineCurrentOffThreshold      Uthousandth,
	mLineCurrentWarningEvent      EVENTFLAGS,
	mLineCurrentOffEvent          EVENTFLAGS,
	mFuseCurrentWarningThreshold  Uthousandth,
	mFuseCurrentOffThreshold      Uthousandth,
	mFuseCurrentWarningEvent      EVENTFLAGS,
	mFuseCurrentOffEvent          EVENTFLAGS,
	mDeviceID                     DisplayString,
	mDeviceVersion                Version,
	mSysName                      DisplayString,
	mElectricalTopology           Unsigned32,
	mFusePortTopology             Unsigned32,
	mLineFuseTopology             Unsigned32,
	mSSOIPAddress                 IpAddress,
	mSSOLoginCredentials          DisplayString,
	mSSOGracefullShutdown         DisplayString,
	mUPSWarningLevel              Utenth,
	mUPSOffLevel                  Utenth,
	mMaxHighCurrentWarning        Stenth,
	mUpsMonitoringProtocol        Unsigned32,
	mUpsEmergencyThreshold        Utenth,
	mUpsRecoveryThreshold         Utenth,
	mUpsEventFlags                EVENTFLAGS,
	mRecoveryPowerThreshold       Unsigned32,
	mMinHighCurrentWarning        Stenth,
	mMinHighPowerWarning          Shundredth,
	mMaxHighPowerWarning          Shundredth,
	mHeartbeatInterval            Unsigned32,
	mMinTotalHighCurrentWarning   Stenth,
	mMaxTotalHighCurrentWarning   Stenth,
	mMinTotalHighPowerWarning     Shundredth,
	mMaxTotalHighPowerWarning     Shundredth,
	mCloudState                   Unsigned32,
	mSensorBias                   Integer32,
	mDaisyChainDeviceMode         Unsigned32,
	mSNMPTrapUser                 Unsigned32,
	mUSMUser                      DisplayString,
	mUSMAuthPassphrase            DisplayString,
	mUSMPrivPassphrase            DisplayString,
	mSNMPV2GetSetEnable           Unsigned32,
	mSNMPV3GetSetEnable           Unsigned32,
	mUSMAuthPassphraseLength      Unsigned32,
	mUSMPrivPassphraseLength      Unsigned32,
	mSNMPTrapEnable               Unsigned32,
	mLDAPAttribute                DisplayString,
	mLDAPPath                     DisplayString,
	mLDAPAdminGroupName           DisplayString,
	mLDAPRestrictedGroupName      DisplayString,
	mLDAPGuestGroupName           DisplayString,
	mLDAPEnable                   Unsigned32,
	mLDAPLoginWrapper             DisplayString,
	mLDAPServer                   DisplayString,
	mLocalAuthEnable              Unsigned32,
	masterIndex                   Integer32,
	masterModuleIndex             Integer32
}

masterIndex OBJECT-TYPE
	SYNTAX      Integer32 (1..8)
	MAX-ACCESS  not-accessible
	STATUS      current
	DESCRIPTION
		"Index for the selected Master Module"
	::= { eMasterEntry 65537 }

masterModuleIndex OBJECT-TYPE
	SYNTAX      Integer32 (1..8)
	MAX-ACCESS  not-accessible
	STATUS      current
	DESCRIPTION
		"Selected Master Module"
	::= { eMasterEntry 65538 }

mGeneralModuleStatus OBJECT-TYPE
	SYNTAX      Unsigned32
	MAX-ACCESS  read-only
	STATUS      current
	DESCRIPTION
		"General status of a module."
	::= { eMasterEntry 1 }

mSpecificModuleStatus OBJECT-TYPE
	SYNTAX      Unsigned32
	MAX-ACCESS  read-only
	STATUS      current
	DESCRIPTION
		"Specific status of a module."
	::= { eMasterEntry 2 }

mCurrentTime OBJECT-TYPE
	SYNTAX      TimeTicks
	UNITS       "UNIX"
	MAX-ACCESS  read-write
	STATUS      current
	DESCRIPTION
		"Gets or sets the current time (not possible when NTP is enabled). (unit: UNIX)"
	::= { eMasterEntry 3 }

mVoltage OBJECT-TYPE
	SYNTAX      Uhundredth
	UNITS       "V"
	MAX-ACCESS  read-only
	STATUS      current
	DESCRIPTION
		"Gets the voltage of a power module. (unit: 0.01V)"
	::= { eMasterEntry 4 }

mTemperature OBJECT-TYPE
	SYNTAX      Utenth
	UNITS       "K"
	MAX-ACCESS  read-only
	STATUS      current
	DESCRIPTION
		"Gets the current temperature of a temperature sensor. (unit: 0.1K)"
	::= { eMasterEntry 11 }

mCurrentIP OBJECT-TYPE
	SYNTAX      IpAddress
	MAX-ACCESS  read-only
	STATUS      current
	DESCRIPTION
		"Gets the current IP address. To set the IP address, use IPADDR instead."
	::= { eMasterEntry 14 }

mTotalCurrent OBJECT-TYPE
	SYNTAX      Uthousandth
	UNITS       "A"
	MAX-ACCESS  read-only
	STATUS      current
	DESCRIPTION
		"Gets the total current of a power module. (unit: 0.001A)"
	::= { eMasterEntry 17 }

mTotalRealPower OBJECT-TYPE
	SYNTAX      Unsigned32
	UNITS       "W"
	MAX-ACCESS  read-only
	STATUS      current
	DESCRIPTION
		"Gets the total power level of a power module. (unit: W)"
	::= { eMasterEntry 18 }

mTotalActiveEnergy OBJECT-TYPE
	SYNTAX      Uthousandth
	UNITS       "kWh"
	MAX-ACCESS  read-only
	STATUS      current
	DESCRIPTION
		"Gets the total energy of a power module. (unit: 0.001kWh)"
	::= { eMasterEntry 20 }

mLineCurrent OBJECT-TYPE
	SYNTAX      Uthousandth (0..65535)
	UNITS       "A"
	MAX-ACCESS  read-only
	STATUS      current
	DESCRIPTION
		"Gets the current line current. (unit: 0.001A)"
	::= { eMasterEntry 32 }

mFuseCurrent OBJECT-TYPE
	SYNTAX      Uthousandth (0..65535)
	UNITS       "A"
	MAX-ACCESS  read-only
	STATUS      current
	DESCRIPTION
		"Gets the current through a fuse. (unit: 0.001A)"
	::= { eMasterEntry 33 }

mCurrentSubNetMask OBJECT-TYPE
	SYNTAX      IpAddress
	MAX-ACCESS  read-only
	STATUS      current
	DESCRIPTION
		"Gets the current subnet mask. To set the subnet mask use SNMSK instead."
	::= { eMasterEntry 34 }

mCurrentDNSServer OBJECT-TYPE
	SYNTAX      IpAddress
	MAX-ACCESS  read-only
	STATUS      current
	DESCRIPTION
		"Gets the current DNS server. To set the DNS server use DNSSRV instead."
	::= { eMasterEntry 35 }

mCurrentStdGateway OBJECT-TYPE
	SYNTAX      IpAddress
	MAX-ACCESS  read-only
	STATUS      current
	DESCRIPTION
		"Gets the current standard gateway. To set the standard gateway use STDGW instead."
	::= { eMasterEntry 36 }

mUPSPresent OBJECT-TYPE
	SYNTAX      Unsigned32 (0..1)
	MAX-ACCESS  read-only
	STATUS      current
	DESCRIPTION
		"Checks if a UPS is present."
	::= { eMasterEntry 37 }

mUPSStatus OBJECT-TYPE
	SYNTAX      Unsigned32
	MAX-ACCESS  read-only
	STATUS      current
	DESCRIPTION
		"Gets the working status of a UPS (if its working on its batteries or not)."
	::= { eMasterEntry 38 }

mUPSEstimatedRunTime OBJECT-TYPE
	SYNTAX      Unsigned32 (0..65535)
	UNITS       "min"
	MAX-ACCESS  read-only
	STATUS      current
	DESCRIPTION
		"Gets the estimated run time of a UPS. (unit: min)"
	::= { eMasterEntry 39 }

mUPSBatteryLevel OBJECT-TYPE
	SYNTAX      Utenth (0..1000)
	UNITS       "%"
	MAX-ACCESS  read-only
	STATUS      current
	DESCRIPTION
		"The current UPS battery level. (unit: 0.1%)"
	::= { eMasterEntry 40 }

mHighCurrent OBJECT-TYPE
	SYNTAX      Stenth
	UNITS       "A"
	MAX-ACCESS  read-only
	STATUS      current
	DESCRIPTION
		"The current for high values (unit: 0.1A)"
	::= { eMasterEntry 41 }

mUpsCommunicationStatus OBJECT-TYPE
	SYNTAX      Unsigned32 (0..1)
	MAX-ACCESS  read-only
	STATUS      current
	DESCRIPTION
		"Status information of communication with the UPS"
	::= { eMasterEntry 42 }

mHighPower OBJECT-TYPE
	SYNTAX      Shundredth (-32768..32767)
	UNITS       "kW"
	MAX-ACCESS  read-only
	STATUS      current
	DESCRIPTION
		"The power for high values (unit: 0.01kW)"
	::= { eMasterEntry 43 }

mTotalHighCurrent OBJECT-TYPE
	SYNTAX      Stenth (0..65535)
	UNITS       "A"
	MAX-ACCESS  read-only
	STATUS      current
	DESCRIPTION
		"The current for high values (unit: 0.1A)"
	::= { eMasterEntry 44 }

mTotalHighPower OBJECT-TYPE
	SYNTAX      Shundredth (-32768..32767)
	UNITS       "kW"
	MAX-ACCESS  read-only
	STATUS      current
	DESCRIPTION
		"The power for high values (unit: 0.01kW)"
	::= { eMasterEntry 45 }

mPositiveEnergy OBJECT-TYPE
	SYNTAX      Uthousandth (0..4294967295)
	UNITS       "kWh"
	MAX-ACCESS  read-only
	STATUS      current
	DESCRIPTION
		"Gets the positive energy used by an outlet. (unit: 0.001kWh)"
	::= { eMasterEntry 46 }

mNegativeEnergy OBJECT-TYPE
	SYNTAX      Uthousandth (0..4294967295)
	UNITS       "kWh"
	MAX-ACCESS  read-only
	STATUS      current
	DESCRIPTION
		"Gets the negative energy used by an outlet. (unit: 0.001kWh)"
	::= { eMasterEntry 47 }

mTotalPositiveEnergy OBJECT-TYPE
	SYNTAX      Uthousandth (0..4294967295)
	UNITS       "kWh"
	MAX-ACCESS  read-only
	STATUS      current
	DESCRIPTION
		"Gets the positive energy of the module. (unit: 0.001kWh)"
	::= { eMasterEntry 48 }

mTotalNegativeEnergy OBJECT-TYPE
	SYNTAX      Uthousandth (0..4294967295)
	UNITS       "kWh"
	MAX-ACCESS  read-only
	STATUS      current
	DESCRIPTION
		"Gets the negative energy of the module. (unit: 0.001kWh)"
	::= { eMasterEntry 49 }

mCloudStatus OBJECT-TYPE
	SYNTAX      Unsigned32 (0..255)
	MAX-ACCESS  read-only
	STATUS      current
	DESCRIPTION
		"Gets the status of the connection with the cloud. 0 = Idle state; 1 = Disabled; 2 = Initialising; 3 = Initialising - No connection; 4 = Initialising - No key; 5 = Connection Ok; 6 = Connection Failed; 7 = Connection Failed - No key."
	::= { eMasterEntry 56 }

mStatus OBJECT-TYPE
	SYNTAX      Unsigned32 (0..65535)
	MAX-ACCESS  read-only
	STATUS      current
	DESCRIPTION
		"status of a module"
	::= { eMasterEntry 1000 }

mModuleName OBJECT-TYPE
	SYNTAX      DisplayString
	MAX-ACCESS  read-write
	STATUS      current
	DESCRIPTION
		"Gets, sets or defaults the module name."
	::= { eMasterEntry 10001 }

mFirmwareVersion OBJECT-TYPE
	SYNTAX      Version
	MAX-ACCESS  read-only
	STATUS      current
	DESCRIPTION
		"Gets the version of the module's firmware."
	::= { eMasterEntry 10002 }

mHardwareVersion OBJECT-TYPE
	SYNTAX      Version
	MAX-ACCESS  read-only
	STATUS      current
	DESCRIPTION
		"Gets the version of a module's hardware."
	::= { eMasterEntry 10003 }

mFirmwareID OBJECT-TYPE
	SYNTAX      DisplayString
	MAX-ACCESS  read-only
	STATUS      current
	DESCRIPTION
		"Gets the ID of the module's firmware."
	::= { eMasterEntry 10004 }

mHardwareID OBJECT-TYPE
	SYNTAX      DisplayString
	MAX-ACCESS  read-only
	STATUS      current
	DESCRIPTION
		"Gets the ID of a module's hardware."
	::= { eMasterEntry 10005 }

mRackName OBJECT-TYPE
	SYNTAX      DisplayString
	MAX-ACCESS  read-write
	STATUS      current
	DESCRIPTION
		"Gets, sets or defaults the name of the rack."
	::= { eMasterEntry 10006 }

mRackPosition OBJECT-TYPE
	SYNTAX      DisplayString
	MAX-ACCESS  read-write
	STATUS      current
	DESCRIPTION
		"Gets, sets or defaults the position in the rack."
	::= { eMasterEntry 10007 }

mIPAddress OBJECT-TYPE
	SYNTAX      IpAddress
	MAX-ACCESS  read-write
	STATUS      current
	DESCRIPTION
		"Gets, sets or defaults the IP address (when DHCP is disabled)."
	::= { eMasterEntry 10011 }

mSubNetMask OBJECT-TYPE
	SYNTAX      IpAddress
	MAX-ACCESS  read-write
	STATUS      current
	DESCRIPTION
		"Gets, sets or defaults the subnet mask (when DHCP is disabled)."
	::= { eMasterEntry 10012 }

mStdGateWay OBJECT-TYPE
	SYNTAX      IpAddress
	MAX-ACCESS  read-write
	STATUS      current
	DESCRIPTION
		"Gets, sets or defaults the standard gateway (when DHCP is disabled)."
	::= { eMasterEntry 10013 }

mDnsServer OBJECT-TYPE
	SYNTAX      IpAddress
	MAX-ACCESS  read-write
	STATUS      current
	DESCRIPTION
		"Gets, sets or defaults the IP address of the used DNS server (when DHCP is disabled)."
	::= { eMasterEntry 10014 }

mMAC OBJECT-TYPE
	SYNTAX      MacAddress
	MAX-ACCESS  read-only
	STATUS      current
	DESCRIPTION
		"Gets the MAC address of a master module."
	::= { eMasterEntry 10015 }

mDHCPEnable OBJECT-TYPE
	SYNTAX      Unsigned32 (0..1)
	MAX-ACCESS  read-write
	STATUS      current
	DESCRIPTION
		"Enables, disables or defaults DHCP. Set to 1 to enable DHCP, or 0 to disable DHCP."
	::= { eMasterEntry 10016 }

mNTPServer OBJECT-TYPE
	SYNTAX      IpAddress
	MAX-ACCESS  read-write
	STATUS      current
	DESCRIPTION
		"Gets, sets or defaults the NTP (Network Time Protocol) server IP address."
	::= { eMasterEntry 10017 }

mUseDefaultNTPServer OBJECT-TYPE
	SYNTAX      Unsigned32 (0..1)
	MAX-ACCESS  read-write
	STATUS      current
	DESCRIPTION
		"Enables, disables or defaults the usage of the default NTP (Network Time Protocol) server (pool.ntp.org)."
	::= { eMasterEntry 10018 }

mUseNTP OBJECT-TYPE
	SYNTAX      Unsigned32 (0..1)
	MAX-ACCESS  read-write
	STATUS      current
	DESCRIPTION
		"Enables, disables or defaults NTP (Network Time Protocol). Set to 1 to enable NTP, or 0 to disable NTP."
	::= { eMasterEntry 10019 }

mSNMPTrapRecvIP OBJECT-TYPE
	SYNTAX      IpAddress
	MAX-ACCESS  read-write
	STATUS      current
	DESCRIPTION
		"Gets, sets or defaults the SNMP trap receiver IP address."
	::= { eMasterEntry 10020 }

mSNMPTrapRecvPort OBJECT-TYPE
	SYNTAX      Unsigned32 (0..65535)
	MAX-ACCESS  read-write
	STATUS      current
	DESCRIPTION
		"Gets, sets or defaults the SNMP tap receiver port."
	::= { eMasterEntry 10021 }

mSNMPControl OBJECT-TYPE
	SYNTAX      Unsigned32 (0..1)
	MAX-ACCESS  read-write
	STATUS      current
	DESCRIPTION
		"Enables, disables or defaults write access over SNMP. Set to 1 to disable write access, or 0 to enable write access."
	::= { eMasterEntry 10024 }

mECSServer OBJECT-TYPE
	SYNTAX      IpAddress
	MAX-ACCESS  read-write
	STATUS      current
	DESCRIPTION
		"Gets, sets or defaults the ECS (Energy Cloud Sentinel) server IP address."
	::= { eMasterEntry 10028 }

mUseECSServer OBJECT-TYPE
	SYNTAX      Unsigned32 (0..1)
	MAX-ACCESS  read-write
	STATUS      current
	DESCRIPTION
		"Enables, disables or defaults the use of an ECS (Energy Cloud Sentinel) server. Set to 1 to enable or 0 to disable."
	::= { eMasterEntry 10029 }

mDisplayLock OBJECT-TYPE
	SYNTAX      Unsigned32 (0..255)
	MAX-ACCESS  read-write
	STATUS      current
	DESCRIPTION
		"Gets, sets or defaults the display lock. If the display is locked, you can still view information on the display, but you are not allowed to change settings through the menu system."
	::= { eMasterEntry 10031 }

mDisplayTimeOn OBJECT-TYPE
	SYNTAX      Unsigned32 (0..255)
	UNITS       "min"
	MAX-ACCESS  read-write
	STATUS      current
	DESCRIPTION
		"Gets, sets or defaults the display sleep timer. If the display is inactive for longer than this time, the display turns off to save power. Time is in minutes. (unit: min)"
	::= { eMasterEntry 10032 }

mMaxVoltageWarning OBJECT-TYPE
	SYNTAX      Uhundredth (0..65535)
	UNITS       "V"
	MAX-ACCESS  read-write
	STATUS      current
	DESCRIPTION
		"Gets, sets or defaults the maximum voltage warning level. (unit: 0.01V)"
	::= { eMasterEntry 10047 }

mMinVoltageWarning OBJECT-TYPE
	SYNTAX      Uhundredth (0..65535)
	UNITS       "V"
	MAX-ACCESS  read-write
	STATUS      current
	DESCRIPTION
		"Gets, sets or defaults the minimum voltage warning level. (unit: 0.01V)"
	::= { eMasterEntry 10049 }

mMinTemperatureWarning OBJECT-TYPE
	SYNTAX      Utenth (2232..4732)
	UNITS       "K"
	MAX-ACCESS  read-write
	STATUS      current
	DESCRIPTION
		"Gets, sets or defaults the minimum temperature warning level (use DEF accessor to reset). (unit: 0.1K)"
	::= { eMasterEntry 10052 }

mMaxTemperatureWarning OBJECT-TYPE
	SYNTAX      Utenth (2232..4732)
	UNITS       "K"
	MAX-ACCESS  read-write
	STATUS      current
	DESCRIPTION
		"Gets, sets or defaults the maximum temperature warning level (use DEF accessor to reset). (unit: 0.1K)"
	::= { eMasterEntry 10053 }

mGeneralEventEnable OBJECT-TYPE
	SYNTAX      EVENTFLAGS
	MAX-ACCESS  read-write
	STATUS      current
	DESCRIPTION
		"Gets, sets or defaults general events. If set to 0, no events will be generated. Set to 1 to generate events on media indicated by the event bitfields."
	::= { eMasterEntry 10074 }

mSNMPSysContact OBJECT-TYPE
	SYNTAX      DisplayString
	MAX-ACCESS  read-write
	STATUS      current
	DESCRIPTION
		"Gets, sets or defaults the SNMP contact information."
	::= { eMasterEntry 10075 }

mCurrentWarningEvent OBJECT-TYPE
	SYNTAX      EVENTFLAGS
	MAX-ACCESS  read-write
	STATUS      current
	DESCRIPTION
		"Enables or disables the SNMP trap if the outlet current warning level is exceeded."
	::= { eMasterEntry 10078 }

mPowerWarningEvent OBJECT-TYPE
	SYNTAX      EVENTFLAGS
	MAX-ACCESS  read-write
	STATUS      current
	DESCRIPTION
		"Enables or disables the SNMP trap if the power warning level is exceeded."
	::= { eMasterEntry 10080 }

mTotalCurrentWarningEvent OBJECT-TYPE
	SYNTAX      EVENTFLAGS
	MAX-ACCESS  read-write
	STATUS      current
	DESCRIPTION
		"Enables or disables the SNMP trap if the total outlet current warning level is exceeded."
	::= { eMasterEntry 10082 }

mTotalPowerWarningEvent OBJECT-TYPE
	SYNTAX      EVENTFLAGS
	MAX-ACCESS  read-write
	STATUS      current
	DESCRIPTION
		"Enables or disables the SNMP trap if the total power warning level is exceeded."
	::= { eMasterEntry 10084 }

mVoltageWarningEvent OBJECT-TYPE
	SYNTAX      EVENTFLAGS
	MAX-ACCESS  read-write
	STATUS      current
	DESCRIPTION
		"Enables or disables the SNMP trap if the voltage warning level is exceeded."
	::= { eMasterEntry 10086 }

mTemperatureWarningEvent OBJECT-TYPE
	SYNTAX      EVENTFLAGS
	MAX-ACCESS  read-write
	STATUS      current
	DESCRIPTION
		"Enables or disables the SNMP trap if the temperature warning level is exceeded."
	::= { eMasterEntry 10087 }

mDisplayBrightness OBJECT-TYPE
	SYNTAX      Unsigned32 (0..255)
	MAX-ACCESS  read-write
	STATUS      current
	DESCRIPTION
		"Gets, sets or defaults the display brightness (if supported)."
	::= { eMasterEntry 10098 }

mECSServerPort OBJECT-TYPE
	SYNTAX      Unsigned32 (0..65535)
	MAX-ACCESS  read-write
	STATUS      current
	DESCRIPTION
		"Gets, sets or defaults the ECS (Energy Cloud Sentinel) server port."
	::= { eMasterEntry 10106 }

mExternalSensorLabel OBJECT-TYPE
	SYNTAX      DisplayString
	MAX-ACCESS  read-write
	STATUS      current
	DESCRIPTION
		"Gets, sets or defaults the external sensor label. External sensors can be connected to Energy Sensors."
	::= { eMasterEntry 10109 }

mHttpsOnly OBJECT-TYPE
	SYNTAX      Unsigned32 (0..1)
	MAX-ACCESS  read-write
	STATUS      current
	DESCRIPTION
		"Enables or disables the use of HTTPS (secure HTTP). Set to 1 to enable HTTPS only, or 0 to also enable HTTP."
	::= { eMasterEntry 10127 }

mTelnetSsl OBJECT-TYPE
	SYNTAX      Unsigned32 (0..1)
	MAX-ACCESS  read-write
	STATUS      current
	DESCRIPTION
		"Enables or disables the use of Telnet SSL (secure Telnet). Set to 1 to enable Telnet SSL, or 0 to disable Telnet SSL)."
	::= { eMasterEntry 10128 }

mCookieTimeToLive OBJECT-TYPE
	SYNTAX      Unsigned32 (0..65535)
	UNITS       "min"
	MAX-ACCESS  read-write
	STATUS      current
	DESCRIPTION
		"The TTL (Time To Live) of the website cookie. (unit: min)"
	::= { eMasterEntry 10130 }

mLineCurrentWarningThreshold OBJECT-TYPE
	SYNTAX      Uthousandth (0..65535)
	UNITS       "A"
	MAX-ACCESS  read-write
	STATUS      current
	DESCRIPTION
		"Gets, sets the warning threshold of the linecurrent. (unit: 0.001A)"
	::= { eMasterEntry 10131 }

mLineCurrentOffThreshold OBJECT-TYPE
	SYNTAX      Uthousandth (0..65535)
	UNITS       "A"
	MAX-ACCESS  read-write
	STATUS      current
	DESCRIPTION
		"Gets, sets the off threshold of the linecurrent. (unit: 0.001A)"
	::= { eMasterEntry 10132 }

mLineCurrentWarningEvent OBJECT-TYPE
	SYNTAX      EVENTFLAGS
	MAX-ACCESS  read-write
	STATUS      current
	DESCRIPTION
		"Enables or disables the SNMP trap if the linecurrent warning level is exceeded."
	::= { eMasterEntry 10133 }

mLineCurrentOffEvent OBJECT-TYPE
	SYNTAX      EVENTFLAGS
	MAX-ACCESS  read-write
	STATUS      current
	DESCRIPTION
		"Enables or disables the SNMP trap if the linecurrent off level is exceeded."
	::= { eMasterEntry 10134 }

mFuseCurrentWarningThreshold OBJECT-TYPE
	SYNTAX      Uthousandth (0..32000)
	UNITS       "A"
	MAX-ACCESS  read-write
	STATUS      current
	DESCRIPTION
		"Gets, sets or defaults the maximum current warning threshold per fuse. (unit: 0.001A)"
	::= { eMasterEntry 10142 }

mFuseCurrentOffThreshold OBJECT-TYPE
	SYNTAX      Uthousandth (0..32000)
	UNITS       "A"
	MAX-ACCESS  read-write
	STATUS      current
	DESCRIPTION
		"Gets, sets or defaults the maximum current off threshold per fuse. (unit: 0.001A)"
	::= { eMasterEntry 10143 }

mFuseCurrentWarningEvent OBJECT-TYPE
	SYNTAX      EVENTFLAGS
	MAX-ACCESS  read-write
	STATUS      current
	DESCRIPTION
		"Enables or disables the SNMP trap if the fusecurrent warning threshold is exceeded."
	::= { eMasterEntry 10144 }

mFuseCurrentOffEvent OBJECT-TYPE
	SYNTAX      EVENTFLAGS
	MAX-ACCESS  read-write
	STATUS      current
	DESCRIPTION
		"Enables or disables the SNMP trap if the fusecurrent off threshold is exceeded."
	::= { eMasterEntry 10145 }

mDeviceID OBJECT-TYPE
	SYNTAX      DisplayString
	MAX-ACCESS  read-only
	STATUS      current
	DESCRIPTION
		"The ID of the device."
	::= { eMasterEntry 10150 }

mDeviceVersion OBJECT-TYPE
	SYNTAX      Version
	MAX-ACCESS  read-only
	STATUS      current
	DESCRIPTION
		"The version of the device."
	::= { eMasterEntry 10151 }

mSysName OBJECT-TYPE
	SYNTAX      DisplayString
	MAX-ACCESS  read-only
	STATUS      current
	DESCRIPTION
		"The full name of the device."
	::= { eMasterEntry 10152 }

mElectricalTopology OBJECT-TYPE
	SYNTAX      Unsigned32 (0..2)
	MAX-ACCESS  read-only
	STATUS      current
	DESCRIPTION
		"Gets the electrical topology of the unit."
	::= { eMasterEntry 10153 }

mFusePortTopology OBJECT-TYPE
	SYNTAX      Unsigned32 (0..6)
	MAX-ACCESS  read-only
	STATUS      current
	DESCRIPTION
		"Gets the topology between the outlets and fuses."
	::= { eMasterEntry 10154 }

mLineFuseTopology OBJECT-TYPE
	SYNTAX      Unsigned32 (0..3)
	MAX-ACCESS  read-only
	STATUS      current
	DESCRIPTION
		"Gets the topology between the inlet (cable or connection) and the fuses."
	::= { eMasterEntry 10155 }

mSSOIPAddress OBJECT-TYPE
	SYNTAX      IpAddress
	MAX-ACCESS  read-write
	STATUS      current
	DESCRIPTION
		"Gets, sets the IP address of an SSO (Smart Style Office)."
	::= { eMasterEntry 10156 }

mSSOLoginCredentials OBJECT-TYPE
	SYNTAX      DisplayString
	MAX-ACCESS  read-write
	STATUS      current
	DESCRIPTION
		"Gets, sets the login credentials of an SSO (Smart Style Office)."
	::= { eMasterEntry 10157 }

mSSOGracefullShutdown OBJECT-TYPE
	SYNTAX      DisplayString
	MAX-ACCESS  read-write
	STATUS      current
	DESCRIPTION
		"Gets, sets the string to send if the UPS' battery level is below the set threshold."
	::= { eMasterEntry 10158 }

mUPSWarningLevel OBJECT-TYPE
	SYNTAX      Utenth (0..1000)
	MAX-ACCESS  read-write
	STATUS      current
	DESCRIPTION
		"Gets, sets or defaults the graceful shutdown threshold of a UPS."
	::= { eMasterEntry 10159 }

mUPSOffLevel OBJECT-TYPE
	SYNTAX      Utenth (0..1000)
	MAX-ACCESS  read-write
	STATUS      current
	DESCRIPTION
		"Gets, sets or defaults the threshold of a UPS to set outlets off."
	::= { eMasterEntry 10160 }

mMaxHighCurrentWarning OBJECT-TYPE
	SYNTAX      Stenth (-32768..32767)
	UNITS       "A"
	MAX-ACCESS  read-write
	STATUS      current
	DESCRIPTION
		"Gets sets or defaults the maximum high current warning level. (unit: 0.1A)"
	::= { eMasterEntry 10165 }

mUpsMonitoringProtocol OBJECT-TYPE
	SYNTAX      Unsigned32 (0..1)
	MAX-ACCESS  read-write
	STATUS      current
	DESCRIPTION
		"Disables/Enables UPS monitoring and selects the protocol used for UPS monitoring. 0 = Disabled; 1 = Use old APC protocol"
	::= { eMasterEntry 10167 }

mUpsEmergencyThreshold OBJECT-TYPE
	SYNTAX      Utenth (0..1000)
	UNITS       "%"
	MAX-ACCESS  read-write
	STATUS      current
	DESCRIPTION
		"When the UPS battery level goes below this threshold a shutdown request will be sent to all agents (unit: 0.1%)"
	::= { eMasterEntry 10168 }

mUpsRecoveryThreshold OBJECT-TYPE
	SYNTAX      Utenth (0..1000)
	UNITS       "%"
	MAX-ACCESS  read-write
	STATUS      current
	DESCRIPTION
		"When the UPS battery level goes above this threshold a outlets will be powered on as configured by the user (unit: 0.1%)"
	::= { eMasterEntry 10169 }

mUpsEventFlags OBJECT-TYPE
	SYNTAX      EVENTFLAGS
	MAX-ACCESS  read-write
	STATUS      current
	DESCRIPTION
		"Event flags for events related to the UPS monitoring"
	::= { eMasterEntry 10170 }

mRecoveryPowerThreshold OBJECT-TYPE
	SYNTAX      Unsigned32 (20..4000)
	UNITS       "W"
	MAX-ACCESS  read-write
	STATUS      current
	DESCRIPTION
		"When the UPS was on battery and it went below UPSEMERGTHRES, the outlets that have a load below the RECOVPOWERTHRES will be power cycled once the UPS is back on mains power and exceeds UPSRECOVTHRES (unit: W)"
	::= { eMasterEntry 10171 }

mMinHighCurrentWarning OBJECT-TYPE
	SYNTAX      Stenth (-32768..32767)
	UNITS       "A"
	MAX-ACCESS  read-write
	STATUS      current
	DESCRIPTION
		"Gets sets or defaults the minimum high current warning level. (unit: 0.1A)"
	::= { eMasterEntry 10176 }

mMinHighPowerWarning OBJECT-TYPE
	SYNTAX      Shundredth (-32768..32767)
	UNITS       "kW"
	MAX-ACCESS  read-write
	STATUS      current
	DESCRIPTION
		"Gets sets or defaults the power min high current warning level. (unit: 0.01kW)"
	::= { eMasterEntry 10177 }

mMaxHighPowerWarning OBJECT-TYPE
	SYNTAX      Shundredth (-32768..32767)
	UNITS       "kW"
	MAX-ACCESS  read-write
	STATUS      current
	DESCRIPTION
		"Gets sets or defaults the power max high current warning level. (unit: 0.01kW)"
	::= { eMasterEntry 10178 }

mHeartbeatInterval OBJECT-TYPE
	SYNTAX      Unsigned32 (0..255)
	UNITS       "s"
	MAX-ACCESS  read-write
	STATUS      current
	DESCRIPTION
		"Interval (in seconds) between 2 heartbeat SNMP traps, Set to 0 to disable (unit: s)"
	::= { eMasterEntry 10179 }

mMinTotalHighCurrentWarning OBJECT-TYPE
	SYNTAX      Stenth (-32768..32767)
	UNITS       "A"
	MAX-ACCESS  read-write
	STATUS      current
	DESCRIPTION
		"Gets sets or defaults the maximum high current warning level. (unit: 0.1A)"
	::= { eMasterEntry 10180 }

mMaxTotalHighCurrentWarning OBJECT-TYPE
	SYNTAX      Stenth (-32768..32767)
	UNITS       "A"
	MAX-ACCESS  read-write
	STATUS      current
	DESCRIPTION
		"Gets sets or defaults the maximum high current warning level. (unit: 0.1A)"
	::= { eMasterEntry 10181 }

mMinTotalHighPowerWarning OBJECT-TYPE
	SYNTAX      Shundredth (-32768..32767)
	UNITS       "kW"
	MAX-ACCESS  read-write
	STATUS      current
	DESCRIPTION
		"Gets sets or defaults the power min high current warning level. (unit: 0.01kW)"
	::= { eMasterEntry 10182 }

mMaxTotalHighPowerWarning OBJECT-TYPE
	SYNTAX      Shundredth (-32768..32767)
	UNITS       "kW"
	MAX-ACCESS  read-write
	STATUS      current
	DESCRIPTION
		"Gets sets or defaults the power max high current warning level. (unit: 0.01kW)"
	::= { eMasterEntry 10183 }

mCloudState OBJECT-TYPE
	SYNTAX      Unsigned32 (0..2)
	MAX-ACCESS  read-write
	STATUS      current
	DESCRIPTION
		"Set if the device needs to push info to the init cloud (val=0) or to the normal cloud (val=1)"
	::= { eMasterEntry 10208 }

mSensorBias OBJECT-TYPE
	SYNTAX      Integer32 (-32768..32767)
	UNITS       "mV"
	MAX-ACCESS  read-write
	STATUS      current
	DESCRIPTION
		"get or set the DC sensor bias (unit: mV)"
	::= { eMasterEntry 10210 }

mDaisyChainDeviceMode OBJECT-TYPE
	SYNTAX      Unsigned32 (0..4)
	MAX-ACCESS  read-write
	STATUS      current
	DESCRIPTION
		"allowed modes: 0: standalone (master without daisy chain slaves) 1: daisy chain master 2: daisy chain slave 1 3: daisy chain slave 2 4: daisy chain slave 3"
	::= { eMasterEntry 10211 }

mSNMPTrapUser OBJECT-TYPE
	SYNTAX      Unsigned32 (0..4)
	MAX-ACCESS  read-write
	STATUS      current
	DESCRIPTION
		"Gets, sets or defaults the SNMP tap user out of the user list."
	::= { eMasterEntry 10212 }

mUSMUser OBJECT-TYPE
	SYNTAX      DisplayString
	MAX-ACCESS  read-write
	STATUS      current
	DESCRIPTION
		"Gets, sets or defaults the SNMP USM security user"
	::= { eMasterEntry 10213 }

mUSMAuthPassphrase OBJECT-TYPE
	SYNTAX      DisplayString
	MAX-ACCESS  read-write
	STATUS      current
	DESCRIPTION
		"Gets, sets or defaults the SNMP USM authentication passphrase (Always MD5)"
	::= { eMasterEntry 10214 }

mUSMPrivPassphrase OBJECT-TYPE
	SYNTAX      DisplayString
	MAX-ACCESS  read-write
	STATUS      current
	DESCRIPTION
		"Gets, sets or defaults the SNMP USM private passphrase (Always AES)"
	::= { eMasterEntry 10215 }

mSNMPV2GetSetEnable OBJECT-TYPE
	SYNTAX      Unsigned32 (0..1)
	MAX-ACCESS  read-write
	STATUS      current
	DESCRIPTION
		"Gets, sets or defaults the SNMP V2 Enable for get ,set or walk but not for traps."
	::= { eMasterEntry 10216 }

mSNMPV3GetSetEnable OBJECT-TYPE
	SYNTAX      Unsigned32 (0..1)
	MAX-ACCESS  read-write
	STATUS      current
	DESCRIPTION
		"Gets, sets or defaults the SNMP V3 Enable for get ,set or walk but not for traps."
	::= { eMasterEntry 10217 }

mUSMAuthPassphraseLength OBJECT-TYPE
	SYNTAX      Unsigned32 (0..16)
	MAX-ACCESS  read-write
	STATUS      current
	DESCRIPTION
		"Gets, sets or defaults the SNMP USM authentication passphrase length"
	::= { eMasterEntry 10218 }

mUSMPrivPassphraseLength OBJECT-TYPE
	SYNTAX      Unsigned32 (0..16)
	MAX-ACCESS  read-write
	STATUS      current
	DESCRIPTION
		"Gets, sets or defaults the SNMP USM private passphrase length"
	::= { eMasterEntry 10219 }

mSNMPTrapEnable OBJECT-TYPE
	SYNTAX      Unsigned32 (0..1)
	MAX-ACCESS  read-write
	STATUS      current
	DESCRIPTION
		"Gets, sets or defaults the SNMP Trap Enable per trap account"
	::= { eMasterEntry 10222 }

mLDAPAttribute OBJECT-TYPE
	SYNTAX      DisplayString
	MAX-ACCESS  read-write
	STATUS      current
	DESCRIPTION
		"Attribute linked to the LDAPFilter"
	::= { eMasterEntry 10227 }

mLDAPPath OBJECT-TYPE
	SYNTAX      DisplayString
	MAX-ACCESS  read-write
	STATUS      current
	DESCRIPTION
		"Relative Path to be used for the LDAPFilter"
	::= { eMasterEntry 10228 }

mLDAPAdminGroupName OBJECT-TYPE
	SYNTAX      DisplayString
	MAX-ACCESS  read-write
	STATUS      current
	DESCRIPTION
		"GroupName for Admin Credentials in LDAP"
	::= { eMasterEntry 10229 }

mLDAPRestrictedGroupName OBJECT-TYPE
	SYNTAX      DisplayString
	MAX-ACCESS  read-write
	STATUS      current
	DESCRIPTION
		"GroupName for Restricted Credentials in LDAP"
	::= { eMasterEntry 10230 }

mLDAPGuestGroupName OBJECT-TYPE
	SYNTAX      DisplayString
	MAX-ACCESS  read-write
	STATUS      current
	DESCRIPTION
		"GroupName for Guest Credentials in LDAP"
	::= { eMasterEntry 10231 }

mLDAPEnable OBJECT-TYPE
	SYNTAX      Unsigned32 (0..1)
	MAX-ACCESS  read-write
	STATUS      current
	DESCRIPTION
		"Enable or disable login via LDAP credentials"
	::= { eMasterEntry 10232 }

mLDAPLoginWrapper OBJECT-TYPE
	SYNTAX      DisplayString
	MAX-ACCESS  read-write
	STATUS      current
	DESCRIPTION
		"Wrapper for login in with LDAP"
	::= { eMasterEntry 10233 }

mLDAPServer OBJECT-TYPE
	SYNTAX      DisplayString
	MAX-ACCESS  read-write
	STATUS      current
	DESCRIPTION
		"NO_INFO"
	::= { eMasterEntry 10235 }

mLocalAuthEnable OBJECT-TYPE
	SYNTAX      Unsigned32 (0..1)
	MAX-ACCESS  read-write
	STATUS      current
	DESCRIPTION
		"Set if local authentication is still possible if LDAP is enabled"
	::= { eMasterEntry 10236 }

powerModule OBJECT IDENTIFIER
	::= { esRACKTIVITYMIB 80 }

ePowerTable OBJECT-TYPE
	SYNTAX      SEQUENCE OF EPowerEntry
	MAX-ACCESS  not-accessible
	STATUS      current
	DESCRIPTION
		"NO_INFO"
	::= { powerModule 1 }

ePowerEntry OBJECT-TYPE
	SYNTAX      EPowerEntry
	MAX-ACCESS  not-accessible
	STATUS      current
	DESCRIPTION
		"NO_INFO"
	INDEX       { powerModuleIndex, powerIndex }
	::= { ePowerTable 1 }

EPowerEntry ::= SEQUENCE {
	pGeneralModuleStatus          Unsigned32,
	pSpecificModuleStatus         Unsigned32,
	pCurrentTime                  TimeTicks,
	pVoltage                      Uhundredth,
	pFrequency                    Uthousandth,
	pCurrent                      Uthousandth,
	pPower                        Unsigned32,
	pStatePortCur                 CURPORTSTATE,
	pActiveEnergy                 Uthousandth,
	pApparentEnergy               Uthousandth,
	pTemperature                  Utenth,
	pApparentPower                Unsigned32,
	pPowerFactor                  Unsigned32,
	pTotalCurrent                 Uthousandth,
	pTotalRealPower               Unsigned32,
	pTotalApparentPower           Unsigned32,
	pTotalActiveEnergy            Uthousandth,
	pTotalApparentEnergy          Uthousandth,
	pTotalPowerFactor             Unsigned32,
	pTimeOnline                   Unsigned32,
	pTotalHarmonicDistortion      Utenth,
	pPhase                        Unsigned32,
	pBigCurrent                   Unsigned32,
	pBigPower                     Uthousandth,
	pBigApparentPower             Uthousandth,
	pDetectedPhase                Unsigned32,
	pModuleName                   DisplayString,
	pFirmwareVersion              Version,
	pHardwareVersion              Version,
	pFirmwareID                   DisplayString,
	pHardwareID                   DisplayString,
	pPortName                     DisplayString,
	pPortState                    Unsigned32,
	pCurrentPriorOff              Unsigned32,
	pDelayOn                      Unsigned32,
	pMaxCurrentOff                Uthousandth,
	pMaxCurrentWarning            Uthousandth,
	pMaxPowerOff                  Unsigned32,
	pMaxPowerWarning              Unsigned32,
	pMaxTotalCurrentOff           Uthousandth,
	pMaxTotalCurrentWarning       Uthousandth,
	pMaxTotalPowerOff             Unsigned32,
	pMaxTotalPowerWarning         Unsigned32,
	pMaxVoltageWarning            Uhundredth,
	pMinVoltageWarning            Uhundredth,
	pMinTemperatureWarning        Utenth,
	pMaxTemperatureWarning        Utenth,
	pPortStateEvent               EVENTFLAGS,
	pCurrentOffEvent              EVENTFLAGS,
	pCurrentWarningEvent          EVENTFLAGS,
	pPowerOffEvent                EVENTFLAGS,
	pPowerWarningEvent            EVENTFLAGS,
	pTotalCurrentOffEvent         EVENTFLAGS,
	pTotalCurrentWarningEvent     EVENTFLAGS,
	pTotalPowerOffEvent           EVENTFLAGS,
	pTotalPowerWarningEvent       EVENTFLAGS,
	pVoltageWarningEvent          EVENTFLAGS,
	pTemperatureWarningEvent      EVENTFLAGS,
	pMaxOverheatingOff            Utenth,
	pOverheatingOffEvent          EVENTFLAGS,
	pPowerCycleTime               Unsigned32,
	pExternalSensorLabel          DisplayString,
	pMaxOverheatingWarning        Utenth,
	pOverheatingWarningEvent      EVENTFLAGS,
	pMicroIntTimeThreshold        Utenth,
	pMicroIntEvent                EVENTFLAGS,
	pSoftFuseCurrentThreshold     Unsigned32,
	pSoftFuseDelay                Unsigned32,
	pSoftFuseEvent                EVENTFLAGS,
	pPhaseShiftEvent              EVENTFLAGS,
	pSchedulePortOnTime           Unsigned32,
	pSchedulePortOffTime          Unsigned32,
	pEnableSchedulePort           Unsigned32,
	pBlockSetPortOff              Unsigned32,
	pSchedulePortChangeEvent      EVENTFLAGS,
	pAgentIP                      IpAddress,
	pAgentPort                    Unsigned32,
	pAgentCommunicationEventFlags EVENTFLAGS,
	pAlwaysOn                     Unsigned32,
	pGenericTransducerParameters  Integer32,
	pMaxBigCurrentWarning         Unsigned32,
	pMaxBigPowerWarning           Uthousandth,
	pGroupNumber                  Unsigned32,
	pPhaseLink                    Unsigned32,
	pCurrentSensorSelector        Unsigned32,
	pMinBigCurrentWarning         Unsigned32,
	powerIndex                    Integer32,
	powerModuleIndex              Integer32
}

powerIndex OBJECT-TYPE
	SYNTAX      Integer32 (1..8)
	MAX-ACCESS  not-accessible
	STATUS      current
	DESCRIPTION
		"Index for the selected Power Module"
	::= { ePowerEntry 65537 }

powerModuleIndex OBJECT-TYPE
	SYNTAX      Integer32 (1..8)
	MAX-ACCESS  not-accessible
	STATUS      current
	DESCRIPTION
		"Selected Power Module"
	::= { ePowerEntry 65538 }

pGeneralModuleStatus OBJECT-TYPE
	SYNTAX      Unsigned32
	MAX-ACCESS  read-only
	STATUS      current
	DESCRIPTION
		"General status of a module."
	::= { ePowerEntry 1 }

pSpecificModuleStatus OBJECT-TYPE
	SYNTAX      Unsigned32
	MAX-ACCESS  read-only
	STATUS      current
	DESCRIPTION
		"Specific status of a module."
	::= { ePowerEntry 2 }

pCurrentTime OBJECT-TYPE
	SYNTAX      TimeTicks
	UNITS       "UNIX"
	MAX-ACCESS  read-write
	STATUS      current
	DESCRIPTION
		"Gets or sets the current time (not possible when NTP is enabled). (unit: UNIX)"
	::= { ePowerEntry 3 }

pVoltage OBJECT-TYPE
	SYNTAX      Uhundredth
	UNITS       "V"
	MAX-ACCESS  read-only
	STATUS      current
	DESCRIPTION
		"Gets the voltage of a power module. (unit: 0.01V)"
	::= { ePowerEntry 4 }

pFrequency OBJECT-TYPE
	SYNTAX      Uthousandth
	UNITS       "Hz"
	MAX-ACCESS  read-only
	STATUS      current
	DESCRIPTION
		"Gets the frequency of the input voltage of a power module. (unit: 0.001Hz)"
	::= { ePowerEntry 5 }

pCurrent OBJECT-TYPE
	SYNTAX      Uthousandth
	UNITS       "A"
	MAX-ACCESS  read-only
	STATUS      current
	DESCRIPTION
		"Gets the current of an outlet. (unit: 0.001A)"
	::= { ePowerEntry 6 }

pPower OBJECT-TYPE
	SYNTAX      Unsigned32
	UNITS       "W"
	MAX-ACCESS  read-only
	STATUS      current
	DESCRIPTION
		"Gets the power of an outlet. (unit: W)"
	::= { ePowerEntry 7 }

pStatePortCur OBJECT-TYPE
	SYNTAX      CURPORTSTATE
	MAX-ACCESS  read-only
	STATUS      current
	DESCRIPTION
		"Gets the current state of an outlet. To toggle an outlet use PORTSTAT (CLI) or pPortstate (SNMP) (GUID 10035) instead."
	::= { ePowerEntry 8 }

pActiveEnergy OBJECT-TYPE
	SYNTAX      Uthousandth
	UNITS       "kWh"
	MAX-ACCESS  read-only
	STATUS      current
	DESCRIPTION
		"Gets the energy used by an outlet. (unit: 0.001kWh)"
	::= { ePowerEntry 9 }

pApparentEnergy OBJECT-TYPE
	SYNTAX      Uthousandth
	UNITS       "kVAh"
	MAX-ACCESS  read-only
	STATUS      current
	DESCRIPTION
		"Gets the apparent energy used by an outlet. (unit: 0.001kVAh)"
	::= { ePowerEntry 10 }

pTemperature OBJECT-TYPE
	SYNTAX      Utenth
	UNITS       "K"
	MAX-ACCESS  read-only
	STATUS      current
	DESCRIPTION
		"Gets the current temperature of a temperature sensor. (unit: 0.1K)"
	::= { ePowerEntry 11 }

pApparentPower OBJECT-TYPE
	SYNTAX      Unsigned32
	UNITS       "VA"
	MAX-ACCESS  read-only
	STATUS      current
	DESCRIPTION
		"Gets the apparent power of an outlet. (unit: VA)"
	::= { ePowerEntry 15 }

pPowerFactor OBJECT-TYPE
	SYNTAX      Unsigned32
	UNITS       "%"
	MAX-ACCESS  read-only
	STATUS      current
	DESCRIPTION
		"Gets the power factor of an outlet. (unit: %)"
	::= { ePowerEntry 16 }

pTotalCurrent OBJECT-TYPE
	SYNTAX      Uthousandth
	UNITS       "A"
	MAX-ACCESS  read-only
	STATUS      current
	DESCRIPTION
		"Gets the total current of a power module. (unit: 0.001A)"
	::= { ePowerEntry 17 }

pTotalRealPower OBJECT-TYPE
	SYNTAX      Unsigned32
	UNITS       "W"
	MAX-ACCESS  read-only
	STATUS      current
	DESCRIPTION
		"Gets the total power level of a power module. (unit: W)"
	::= { ePowerEntry 18 }

pTotalApparentPower OBJECT-TYPE
	SYNTAX      Unsigned32
	UNITS       "VA"
	MAX-ACCESS  read-only
	STATUS      current
	DESCRIPTION
		"Gets the total apparent power of a power module. (unit: VA)"
	::= { ePowerEntry 19 }

pTotalActiveEnergy OBJECT-TYPE
	SYNTAX      Uthousandth
	UNITS       "kWh"
	MAX-ACCESS  read-only
	STATUS      current
	DESCRIPTION
		"Gets the total energy of a power module. (unit: 0.001kWh)"
	::= { ePowerEntry 20 }

pTotalApparentEnergy OBJECT-TYPE
	SYNTAX      Uthousandth
	UNITS       "kVAh"
	MAX-ACCESS  read-only
	STATUS      current
	DESCRIPTION
		"Gets the total apparent energy of a power module. (unit: 0.001kVAh)"
	::= { ePowerEntry 21 }

pTotalPowerFactor OBJECT-TYPE
	SYNTAX      Unsigned32
	UNITS       "%"
	MAX-ACCESS  read-only
	STATUS      current
	DESCRIPTION
		"Gets the total power factor of a power module. (unit: %)"
	::= { ePowerEntry 22 }

pTimeOnline OBJECT-TYPE
	SYNTAX      Unsigned32
	UNITS       "s"
	MAX-ACCESS  read-only
	STATUS      current
	DESCRIPTION
		"Gets the amount of seconds since the last reset. (unit: s)"
	::= { ePowerEntry 24 }

pTotalHarmonicDistortion OBJECT-TYPE
	SYNTAX      Utenth (0..1000)
	UNITS       "%"
	MAX-ACCESS  read-only
	STATUS      current
	DESCRIPTION
		"total harmonic distortion - outlet (unit: 0.1%)"
	::= { ePowerEntry 50 }

pPhase OBJECT-TYPE
	SYNTAX      Unsigned32 (0..65535)
	UNITS       "degr"
	MAX-ACCESS  read-only
	STATUS      current
	DESCRIPTION
		"the phase between 2 waves (unit: degr)"
	::= { ePowerEntry 51 }

pBigCurrent OBJECT-TYPE
	SYNTAX      Unsigned32
	UNITS       "A"
	MAX-ACCESS  read-only
	STATUS      current
	DESCRIPTION
		"Gets the current of an outlet. (unit: 0.0001A)"
	::= { ePowerEntry 52 }

pBigPower OBJECT-TYPE
	SYNTAX      Uthousandth
	UNITS       "W"
	MAX-ACCESS  read-only
	STATUS      current
	DESCRIPTION
		"Gets the power of an outlet. (unit: 0.001W)"
	::= { ePowerEntry 53 }

pBigApparentPower OBJECT-TYPE
	SYNTAX      Uthousandth
	UNITS       "VA"
	MAX-ACCESS  read-only
	STATUS      current
	DESCRIPTION
		"Gets the apparent power of an outlet. (unit: 0.001VA)"
	::= { ePowerEntry 54 }

pDetectedPhase OBJECT-TYPE
	SYNTAX      Unsigned32 (0..255)
	MAX-ACCESS  read-only
	STATUS      current
	DESCRIPTION
		"Gives the best matching Phase per currentsensor. Updated every 8s. returnes 255 if no good phaselink is found"
	::= { ePowerEntry 55 }

pModuleName OBJECT-TYPE
	SYNTAX      DisplayString
	MAX-ACCESS  read-write
	STATUS      current
	DESCRIPTION
		"Gets, sets or defaults the module name."
	::= { ePowerEntry 10001 }

pFirmwareVersion OBJECT-TYPE
	SYNTAX      Version
	MAX-ACCESS  read-only
	STATUS      current
	DESCRIPTION
		"Gets the version of the module's firmware."
	::= { ePowerEntry 10002 }

pHardwareVersion OBJECT-TYPE
	SYNTAX      Version
	MAX-ACCESS  read-only
	STATUS      current
	DESCRIPTION
		"Gets the version of a module's hardware."
	::= { ePowerEntry 10003 }

pFirmwareID OBJECT-TYPE
	SYNTAX      DisplayString
	MAX-ACCESS  read-only
	STATUS      current
	DESCRIPTION
		"Gets the ID of the module's firmware."
	::= { ePowerEntry 10004 }

pHardwareID OBJECT-TYPE
	SYNTAX      DisplayString
	MAX-ACCESS  read-only
	STATUS      current
	DESCRIPTION
		"Gets the ID of a module's hardware."
	::= { ePowerEntry 10005 }

pPortName OBJECT-TYPE
	SYNTAX      DisplayString
	MAX-ACCESS  read-write
	STATUS      current
	DESCRIPTION
		"Gets, sets or defaults the name of an outlet."
	::= { ePowerEntry 10034 }

pPortState OBJECT-TYPE
	SYNTAX      Unsigned32 (0..2)
	MAX-ACCESS  read-write
	STATUS      current
	DESCRIPTION
		"Sets the state of an outlet: 0=OFF, 1=ON, 2=POWER CYCLE. To get the state of an outlet use CPORTSTAT (CLI) or pStatePortCur (SNMP) (GUID 8) instead."
	::= { ePowerEntry 10035 }

pCurrentPriorOff OBJECT-TYPE
	SYNTAX      Unsigned32 (1..8)
	MAX-ACCESS  read-write
	STATUS      current
	DESCRIPTION
		"Gets, sets or defaults the priority of an outlet. Priority settings are used when 1 or more outlets must be turned off because the total current of a power module was exceeded."
	::= { ePowerEntry 10036 }

pDelayOn OBJECT-TYPE
	SYNTAX      Unsigned32 (0..65535)
	UNITS       "s"
	MAX-ACCESS  read-write
	STATUS      current
	DESCRIPTION
		"Gets, sets or defaults the outlet turn-on delay. Use this to reduce inrush current when the Energy Switch boots. (unit: s)"
	::= { ePowerEntry 10037 }

pMaxCurrentOff OBJECT-TYPE
	SYNTAX      Uthousandth (100..8000)
	UNITS       "A"
	MAX-ACCESS  read-write
	STATUS      current
	DESCRIPTION
		"Gets, sets or defaults the maximum current off level of an outlet. (unit: 0.001A)"
	::= { ePowerEntry 10038 }

pMaxCurrentWarning OBJECT-TYPE
	SYNTAX      Uthousandth (100..8000)
	UNITS       "A"
	MAX-ACCESS  read-write
	STATUS      current
	DESCRIPTION
		"Gets, sets or defaults the maximum current warning level of an outlet. (unit: 0.001A)"
	::= { ePowerEntry 10039 }

pMaxPowerOff OBJECT-TYPE
	SYNTAX      Unsigned32 (20..2000)
	UNITS       "W"
	MAX-ACCESS  read-write
	STATUS      current
	DESCRIPTION
		"Gets, sets or defaults the maximum power off level of an outlet. (unit: W)"
	::= { ePowerEntry 10040 }

pMaxPowerWarning OBJECT-TYPE
	SYNTAX      Unsigned32 (20..2000)
	UNITS       "W"
	MAX-ACCESS  read-write
	STATUS      current
	DESCRIPTION
		"Gets, sets or defaults the maximum power warning level of an outlet. (unit: W)"
	::= { ePowerEntry 10041 }

pMaxTotalCurrentOff OBJECT-TYPE
	SYNTAX      Uthousandth (100..16000)
	UNITS       "A"
	MAX-ACCESS  read-write
	STATUS      current
	DESCRIPTION
		"Gets, sets or defaults the total maximum current off level of a power module. (unit: 0.001A)"
	::= { ePowerEntry 10042 }

pMaxTotalCurrentWarning OBJECT-TYPE
	SYNTAX      Uthousandth (100..16000)
	UNITS       "A"
	MAX-ACCESS  read-write
	STATUS      current
	DESCRIPTION
		"Gets, sets or defaults the total maximum current warning level of a power module. (unit: 0.001A)"
	::= { ePowerEntry 10043 }

pMaxTotalPowerOff OBJECT-TYPE
	SYNTAX      Unsigned32 (20..4000)
	UNITS       "W"
	MAX-ACCESS  read-write
	STATUS      current
	DESCRIPTION
		"Gets, sets or defaults the maximum total power off level. (unit: W)"
	::= { ePowerEntry 10044 }

pMaxTotalPowerWarning OBJECT-TYPE
	SYNTAX      Unsigned32 (20..4000)
	UNITS       "W"
	MAX-ACCESS  read-write
	STATUS      current
	DESCRIPTION
		"Gets, sets or defaults the maximum total power warning level. (unit: W)"
	::= { ePowerEntry 10045 }

pMaxVoltageWarning OBJECT-TYPE
	SYNTAX      Uhundredth (5000..30000)
	UNITS       "V"
	MAX-ACCESS  read-write
	STATUS      current
	DESCRIPTION
		"Gets, sets or defaults the maximum voltage warning level. (unit: 0.01V)"
	::= { ePowerEntry 10047 }

pMinVoltageWarning OBJECT-TYPE
	SYNTAX      Uhundredth (5000..30000)
	UNITS       "V"
	MAX-ACCESS  read-write
	STATUS      current
	DESCRIPTION
		"Gets, sets or defaults the minimum voltage warning level. (unit: 0.01V)"
	::= { ePowerEntry 10049 }

pMinTemperatureWarning OBJECT-TYPE
	SYNTAX      Utenth (2232..4732)
	UNITS       "K"
	MAX-ACCESS  read-write
	STATUS      current
	DESCRIPTION
		"Gets, sets or defaults the minimum temperature warning level (use DEF accessor to reset). (unit: 0.1K)"
	::= { ePowerEntry 10052 }

pMaxTemperatureWarning OBJECT-TYPE
	SYNTAX      Utenth (2232..4732)
	UNITS       "K"
	MAX-ACCESS  read-write
	STATUS      current
	DESCRIPTION
		"Gets, sets or defaults the maximum temperature warning level (use DEF accessor to reset). (unit: 0.1K)"
	::= { ePowerEntry 10053 }

pPortStateEvent OBJECT-TYPE
	SYNTAX      EVENTFLAGS
	MAX-ACCESS  read-write
	STATUS      current
	DESCRIPTION
		"Enables or disables the SNMP trap if the state of an outlet is changed."
	::= { ePowerEntry 10076 }

pCurrentOffEvent OBJECT-TYPE
	SYNTAX      EVENTFLAGS
	MAX-ACCESS  read-write
	STATUS      current
	DESCRIPTION
		"Enables or disables the SNMP trap if the outlet current off level is exceeded."
	::= { ePowerEntry 10077 }

pCurrentWarningEvent OBJECT-TYPE
	SYNTAX      EVENTFLAGS
	MAX-ACCESS  read-write
	STATUS      current
	DESCRIPTION
		"Enables or disables the SNMP trap if the outlet current warning level is exceeded."
	::= { ePowerEntry 10078 }

pPowerOffEvent OBJECT-TYPE
	SYNTAX      EVENTFLAGS
	MAX-ACCESS  read-write
	STATUS      current
	DESCRIPTION
		"Enables or disables the SNMP trap if the power off level is exceeded."
	::= { ePowerEntry 10079 }

pPowerWarningEvent OBJECT-TYPE
	SYNTAX      EVENTFLAGS
	MAX-ACCESS  read-write
	STATUS      current
	DESCRIPTION
		"Enables or disables the SNMP trap if the power warning level is exceeded."
	::= { ePowerEntry 10080 }

pTotalCurrentOffEvent OBJECT-TYPE
	SYNTAX      EVENTFLAGS
	MAX-ACCESS  read-write
	STATUS      current
	DESCRIPTION
		"Enables or disables the SNMP trap if the total outlet current off level is exceeded."
	::= { ePowerEntry 10081 }

pTotalCurrentWarningEvent OBJECT-TYPE
	SYNTAX      EVENTFLAGS
	MAX-ACCESS  read-write
	STATUS      current
	DESCRIPTION
		"Enables or disables the SNMP trap if the total outlet current warning level is exceeded."
	::= { ePowerEntry 10082 }

pTotalPowerOffEvent OBJECT-TYPE
	SYNTAX      EVENTFLAGS
	MAX-ACCESS  read-write
	STATUS      current
	DESCRIPTION
		"Enables or disables the SNMP trap if the total power off level is exceeded."
	::= { ePowerEntry 10083 }

pTotalPowerWarningEvent OBJECT-TYPE
	SYNTAX      EVENTFLAGS
	MAX-ACCESS  read-write
	STATUS      current
	DESCRIPTION
		"Enables or disables the SNMP trap if the total power warning level is exceeded."
	::= { ePowerEntry 10084 }

pVoltageWarningEvent OBJECT-TYPE
	SYNTAX      EVENTFLAGS
	MAX-ACCESS  read-write
	STATUS      current
	DESCRIPTION
		"Enables or disables the SNMP trap if the voltage warning level is exceeded."
	::= { ePowerEntry 10086 }

pTemperatureWarningEvent OBJECT-TYPE
	SYNTAX      EVENTFLAGS
	MAX-ACCESS  read-write
	STATUS      current
	DESCRIPTION
		"Enables or disables the SNMP trap if the temperature warning level is exceeded."
	::= { ePowerEntry 10087 }

pMaxOverheatingOff OBJECT-TYPE
	SYNTAX      Utenth (2232..4732)
	UNITS       "K"
	MAX-ACCESS  read-write
	STATUS      current
	DESCRIPTION
		"Gets, sets or defaults the maximum overheat temperature off level. (unit: 0.1K)"
	::= { ePowerEntry 10090 }

pOverheatingOffEvent OBJECT-TYPE
	SYNTAX      EVENTFLAGS
	MAX-ACCESS  read-write
	STATUS      current
	DESCRIPTION
		"Enables or disables the SNMP trap if the overtemperature off level is exceeded."
	::= { ePowerEntry 10091 }

pPowerCycleTime OBJECT-TYPE
	SYNTAX      Unsigned32 (0..255)
	UNITS       "s"
	MAX-ACCESS  read-write
	STATUS      current
	DESCRIPTION
		"Gets, sets or defaults the time interval that is used to do a power cycle of an outlet. (unit: s)"
	::= { ePowerEntry 10099 }

pExternalSensorLabel OBJECT-TYPE
	SYNTAX      DisplayString
	MAX-ACCESS  read-write
	STATUS      current
	DESCRIPTION
		"Gets, sets or defaults the external sensor label. External sensors can be connected to Energy Sensors."
	::= { ePowerEntry 10109 }

pMaxOverheatingWarning OBJECT-TYPE
	SYNTAX      Utenth (2232..4732)
	UNITS       "K"
	MAX-ACCESS  read-write
	STATUS      current
	DESCRIPTION
		"Gets, sets or defaults the overheating temperature warning level. (unit: 0.1K)"
	::= { ePowerEntry 10121 }

pOverheatingWarningEvent OBJECT-TYPE
	SYNTAX      EVENTFLAGS
	MAX-ACCESS  read-write
	STATUS      current
	DESCRIPTION
		"Enables or disables the SNMP trap if the overheat warning level is exceeded."
	::= { ePowerEntry 10122 }

pMicroIntTimeThreshold OBJECT-TYPE
	SYNTAX      Utenth (10..65535)
	UNITS       "ms"
	MAX-ACCESS  read-write
	STATUS      current
	DESCRIPTION
		"The minimum time the voltage must be interrupted before it is seen as a micro interruption (unit: 0.1ms)"
	::= { ePowerEntry 10135 }

pMicroIntEvent OBJECT-TYPE
	SYNTAX      EVENTFLAGS
	MAX-ACCESS  read-write
	STATUS      current
	DESCRIPTION
		"Enables or disables the SNMP trap if a microinterruption on the voltage is detected."
	::= { ePowerEntry 10136 }

pSoftFuseCurrentThreshold OBJECT-TYPE
	SYNTAX      Unsigned32 (0..255)
	UNITS       "A"
	MAX-ACCESS  read-write
	STATUS      current
	DESCRIPTION
		"The threshold of the soft fuse is a factor of the maximum nominal current off (unit: A)"
	::= { ePowerEntry 10137 }

pSoftFuseDelay OBJECT-TYPE
	SYNTAX      Unsigned32 (0..65535)
	UNITS       "ms"
	MAX-ACCESS  read-write
	STATUS      current
	DESCRIPTION
		"The minimum time the current of an outlet must be above the soft fuse current threshold to switch it off. (unit: ms)"
	::= { ePowerEntry 10138 }

pSoftFuseEvent OBJECT-TYPE
	SYNTAX      EVENTFLAGS
	MAX-ACCESS  read-write
	STATUS      current
	DESCRIPTION
		"Enables or disables the SNMP trap if a soft fuse is triggered."
	::= { ePowerEntry 10139 }

pPhaseShiftEvent OBJECT-TYPE
	SYNTAX      EVENTFLAGS
	MAX-ACCESS  read-write
	STATUS      current
	DESCRIPTION
		"Enables or disables the SNMP trap if a phase shift on the voltage is detected."
	::= { ePowerEntry 10140 }

pSchedulePortOnTime OBJECT-TYPE
	SYNTAX      Unsigned32 (0..1439)
	UNITS       "min"
	MAX-ACCESS  read-write
	STATUS      current
	DESCRIPTION
		"Gets, sets or defaults the time for the scheduler to turn on an outlet. (unit: min)"
	::= { ePowerEntry 10146 }

pSchedulePortOffTime OBJECT-TYPE
	SYNTAX      Unsigned32 (0..1439)
	UNITS       "min"
	MAX-ACCESS  read-write
	STATUS      current
	DESCRIPTION
		"Gets, sets or defaults the time for the scheduler to turn off an outlet. (unit: min)"
	::= { ePowerEntry 10147 }

pEnableSchedulePort OBJECT-TYPE
	SYNTAX      Unsigned32 (0..1)
	MAX-ACCESS  read-write
	STATUS      current
	DESCRIPTION
		"Enables or disables the scheduler on an outlet. When enabled the scheduling is repeated daily."
	::= { ePowerEntry 10148 }

pBlockSetPortOff OBJECT-TYPE
	SYNTAX      Unsigned32 (0..1)
	MAX-ACCESS  read-write
	STATUS      current
	DESCRIPTION
		"Prevent outlets to be set off (only delay on and powercycle are still possible)."
	::= { ePowerEntry 10161 }

pSchedulePortChangeEvent OBJECT-TYPE
	SYNTAX      EVENTFLAGS
	MAX-ACCESS  read-write
	STATUS      current
	DESCRIPTION
		"event if a port has changed state because of the scheduler"
	::= { ePowerEntry 10166 }

pAgentIP OBJECT-TYPE
	SYNTAX      IpAddress
	MAX-ACCESS  read-write
	STATUS      current
	DESCRIPTION
		"IP address of the agent associated to this outlet"
	::= { ePowerEntry 10172 }

pAgentPort OBJECT-TYPE
	SYNTAX      Unsigned32 (0..65535)
	MAX-ACCESS  read-write
	STATUS      current
	DESCRIPTION
		"Network port on which the associated agent will listen"
	::= { ePowerEntry 10173 }

pAgentCommunicationEventFlags OBJECT-TYPE
	SYNTAX      EVENTFLAGS
	MAX-ACCESS  read-write
	STATUS      current
	DESCRIPTION
		"Event flags for events related to agent communication"
	::= { ePowerEntry 10174 }

pAlwaysOn OBJECT-TYPE
	SYNTAX      Unsigned32 (0..1)
	MAX-ACCESS  read-write
	STATUS      current
	DESCRIPTION
		"Outlets marked as Always On can only be power cycled by the user"
	::= { ePowerEntry 10175 }

pGenericTransducerParameters OBJECT-TYPE
	SYNTAX      Integer32 (2000..2000000000)
	UNITS       "mA/V"
	MAX-ACCESS  read-write
	STATUS      current
	DESCRIPTION
		"sets the slope of the transducer transfer function when the generic transducer type is selected (unit: mA/V)"
	::= { ePowerEntry 10190 }

pMaxBigCurrentWarning OBJECT-TYPE
	SYNTAX      Unsigned32 (100..400000000)
	UNITS       "A"
	MAX-ACCESS  read-write
	STATUS      current
	DESCRIPTION
		"Gets, sets or defaults the maximum current warning level of an outlet. (unit: 0.0001A)"
	::= { ePowerEntry 10193 }

pMaxBigPowerWarning OBJECT-TYPE
	SYNTAX      Uthousandth (2000..2000000000)
	UNITS       "W"
	MAX-ACCESS  read-write
	STATUS      current
	DESCRIPTION
		"Gets, sets or defaults the maximum power warning level of an outlet. (unit: 0.001W)"
	::= { ePowerEntry 10194 }

pGroupNumber OBJECT-TYPE
	SYNTAX      Unsigned32 (0..5)
	MAX-ACCESS  read-write
	STATUS      current
	DESCRIPTION
		"Group number per port to group ports"
	::= { ePowerEntry 10195 }

pPhaseLink OBJECT-TYPE
	SYNTAX      Unsigned32 (0..8)
	MAX-ACCESS  read-write
	STATUS      current
	DESCRIPTION
		"Link the current port with a voltage phase"
	::= { ePowerEntry 10196 }

pCurrentSensorSelector OBJECT-TYPE
	SYNTAX      Unsigned32 (0..255)
	MAX-ACCESS  read-write
	STATUS      current
	DESCRIPTION
		"Selection of the currentsensor connected to port. To enter your own value you need to use 255 and fill in guid 10190."
	::= { ePowerEntry 10197 }

pMinBigCurrentWarning OBJECT-TYPE
	SYNTAX      Unsigned32 (0..400000000)
	UNITS       "A"
	MAX-ACCESS  read-write
	STATUS      current
	DESCRIPTION
		"Gets, sets or defaults the minimum current warning level of a port. (unit: 0.0001A)"
	::= { ePowerEntry 10209 }

esnModule OBJECT IDENTIFIER
	::= { esRACKTIVITYMIB 65 }

eESNTable OBJECT-TYPE
	SYNTAX      SEQUENCE OF EESNEntry
	MAX-ACCESS  not-accessible
	STATUS      current
	DESCRIPTION
		"Temperature Humidity Presure Airflow Waterleak"
	::= { esnModule 1 }

eESNEntry OBJECT-TYPE
	SYNTAX      EESNEntry
	MAX-ACCESS  not-accessible
	STATUS      current
	DESCRIPTION
		"Temperature Humidity Presure Airflow Waterleak"
	INDEX       { esnModuleIndex, esnIndex }
	::= { eESNTable 1 }

EESNEntry ::= SEQUENCE {
	aGeneralModuleStatus          Unsigned32,
	aSpecificModuleStatus         Unsigned32,
	aCurrentTime                  TimeTicks,
	aVoltage                      Uhundredth,
	aStatePortCur                 CURPORTSTATE,
	aTemperature                  Utenth,
	aHumidity                     Utenth,
	aAirflow                      Utenth,
	aDewPoint                     Utenth,
	aPressure                     Utenth,
	aAnalogueInput                Unsigned32,
	aWaterleak                    Unsigned32,
	aMotionDetected               Unsigned32,
	aIOPort                       Unsigned32,
	aHighCurrent                  Stenth,
	aHighPower                    Shundredth,
	aModuleName                   DisplayString,
	aFirmwareVersion              Version,
	aHardwareVersion              Version,
	aFirmwareID                   DisplayString,
	aHardwareID                   DisplayString,
	aDisplayTimeOn                Unsigned32,
	aMaxVoltageWarning            Uhundredth,
	aMinVoltageWarning            Uhundredth,
	aMinTemperatureWarning        Utenth,
	aMaxTemperatureWarning        Utenth,
	aMinHumidityWarning           Utenth,
	aMaxHumidityWarning           Utenth,
	aCurrentWarningEvent          EVENTFLAGS,
	aPowerWarningEvent            EVENTFLAGS,
	aVoltageWarningEvent          EVENTFLAGS,
	aTemperatureWarningEvent      EVENTFLAGS,
	aHumidityWarningEvent         EVENTFLAGS,
	aDewPointWarning              Utenth,
	aDewPointWarningEvent         EVENTFLAGS,
	aDewPointViolationEvent       EVENTFLAGS,
	aPressureWarningEvent         EVENTFLAGS,
	aMinPressureWarning           Utenth,
	aMaxPressureWarning           Utenth,
	aDisplayBrightness            Unsigned32,
	aMotionSensitivity            Unsigned32,
	aExternalSensorLabel          DisplayString,
	aRelayLabel                   DisplayString,
	aMinAnalogueInputWarning      Unsigned32,
	aMaxAnalogueInputWarning      Unsigned32,
	aWaterleakWarning             Unsigned32,
	aMinAirflowWarning            Unsigned32,
	aMaxAirflowWarning            Unsigned32,
	aAnalogueInputWarningEvent    EVENTFLAGS,
	aWaterleakWarningEvent        EVENTFLAGS,
	aAirflowWarningEvent          EVENTFLAGS,
	aRelayAssertActionEvent       EVENTFLAGS,
	aRelayDeassertActionEvent     EVENTFLAGS,
	aMotionWarning                Unsigned32,
	aMotionWarningEvent           EVENTFLAGS,
	aDeviceID                     DisplayString,
	aDeviceVersion                Version,
	aSysName                      DisplayString,
	aMaxHighCurrentWarning        Stenth,
	aMinHighCurrentWarning        Stenth,
	aMinHighPowerWarning          Shundredth,
	aMaxHighPowerWarning          Shundredth,
	aIOPortWarningEvent           EVENTFLAGS,
	esnIndex                      Integer32,
	esnModuleIndex                Integer32
}

esnIndex OBJECT-TYPE
	SYNTAX      Integer32 (1..8)
	MAX-ACCESS  not-accessible
	STATUS      current
	DESCRIPTION
		"Index for the selected ESN Module"
	::= { eESNEntry 65537 }

esnModuleIndex OBJECT-TYPE
	SYNTAX      Integer32 (1..8)
	MAX-ACCESS  not-accessible
	STATUS      current
	DESCRIPTION
		"Selected ESN Module"
	::= { eESNEntry 65538 }

aGeneralModuleStatus OBJECT-TYPE
	SYNTAX      Unsigned32
	MAX-ACCESS  read-only
	STATUS      current
	DESCRIPTION
		"General status of a module."
	::= { eESNEntry 1 }

aSpecificModuleStatus OBJECT-TYPE
	SYNTAX      Unsigned32
	MAX-ACCESS  read-only
	STATUS      current
	DESCRIPTION
		"Specific status of a module."
	::= { eESNEntry 2 }

aCurrentTime OBJECT-TYPE
	SYNTAX      TimeTicks
	UNITS       "UNIX"
	MAX-ACCESS  read-write
	STATUS      current
	DESCRIPTION
		"Gets or sets the current time (not possible when NTP is enabled). (unit: UNIX)"
	::= { eESNEntry 3 }

aVoltage OBJECT-TYPE
	SYNTAX      Uhundredth
	UNITS       "V"
	MAX-ACCESS  read-only
	STATUS      current
	DESCRIPTION
		"Gets the voltage of a power module. (unit: 0.01V)"
	::= { eESNEntry 4 }

aStatePortCur OBJECT-TYPE
	SYNTAX      CURPORTSTATE
	MAX-ACCESS  read-only
	STATUS      current
	DESCRIPTION
		"Gets the current state of an outlet. To toggle an outlet use PORTSTAT (CLI) or pPortstate (SNMP) (GUID 10035) instead."
	::= { eESNEntry 8 }

aTemperature OBJECT-TYPE
	SYNTAX      Utenth
	UNITS       "K"
	MAX-ACCESS  read-only
	STATUS      current
	DESCRIPTION
		"Gets the current temperature of a temperature sensor. (unit: 0.1K)"
	::= { eESNEntry 11 }

aHumidity OBJECT-TYPE
	SYNTAX      Utenth
	UNITS       "RH"
	MAX-ACCESS  read-only
	STATUS      current
	DESCRIPTION
		"Gets the relative humidity. (unit: 0.1RH)"
	::= { eESNEntry 12 }

aAirflow OBJECT-TYPE
	SYNTAX      Utenth
	UNITS       "m/s"
	MAX-ACCESS  read-only
	STATUS      current
	DESCRIPTION
		"Gets the current airflow level. (unit: 0.1m/s)"
	::= { eESNEntry 23 }

aDewPoint OBJECT-TYPE
	SYNTAX      Utenth (0..65535)
	UNITS       "K"
	MAX-ACCESS  read-only
	STATUS      current
	DESCRIPTION
		"Gets the current dewpoint. Taking the current humidity into consideration, condensation will occur if the temperature drops below this level. (unit: 0.1K)"
	::= { eESNEntry 25 }

aPressure OBJECT-TYPE
	SYNTAX      Utenth
	UNITS       "hPa"
	MAX-ACCESS  read-only
	STATUS      current
	DESCRIPTION
		"Gets the atmospheric pressure. (unit: 0.1hPa)"
	::= { eESNEntry 26 }

aAnalogueInput OBJECT-TYPE
	SYNTAX      Unsigned32
	UNITS       "mV"
	MAX-ACCESS  read-only
	STATUS      current
	DESCRIPTION
		"Gets the value of an analog input (voltage). (unit: mV)"
	::= { eESNEntry 27 }

aWaterleak OBJECT-TYPE
	SYNTAX      Unsigned32
	MAX-ACCESS  read-only
	STATUS      current
	DESCRIPTION
		"Gets the current state of the water leak sensor."
	::= { eESNEntry 28 }

aMotionDetected OBJECT-TYPE
	SYNTAX      Unsigned32
	MAX-ACCESS  read-only
	STATUS      current
	DESCRIPTION
		"Gets or resets whether motion has been detected."
	::= { eESNEntry 29 }

aIOPort OBJECT-TYPE
	SYNTAX      Unsigned32 (0..1)
	MAX-ACCESS  read-only
	STATUS      current
	DESCRIPTION
		"Gets the state of a digital input."
	::= { eESNEntry 30 }

aHighCurrent OBJECT-TYPE
	SYNTAX      Stenth (-32768..32767)
	UNITS       "A"
	MAX-ACCESS  read-only
	STATUS      current
	DESCRIPTION
		"The current for high values (unit: 0.1A)"
	::= { eESNEntry 41 }

aHighPower OBJECT-TYPE
	SYNTAX      Shundredth (-32768..32767)
	UNITS       "kW"
	MAX-ACCESS  read-only
	STATUS      current
	DESCRIPTION
		"The power for high values (unit: 0.01kW)"
	::= { eESNEntry 43 }

aModuleName OBJECT-TYPE
	SYNTAX      DisplayString
	MAX-ACCESS  read-write
	STATUS      current
	DESCRIPTION
		"Gets, sets or defaults the module name."
	::= { eESNEntry 10001 }

aFirmwareVersion OBJECT-TYPE
	SYNTAX      Version
	MAX-ACCESS  read-only
	STATUS      current
	DESCRIPTION
		"Gets the version of the module's firmware."
	::= { eESNEntry 10002 }

aHardwareVersion OBJECT-TYPE
	SYNTAX      Version
	MAX-ACCESS  read-only
	STATUS      current
	DESCRIPTION
		"Gets the version of a module's hardware."
	::= { eESNEntry 10003 }

aFirmwareID OBJECT-TYPE
	SYNTAX      DisplayString
	MAX-ACCESS  read-only
	STATUS      current
	DESCRIPTION
		"Gets the ID of the module's firmware."
	::= { eESNEntry 10004 }

aHardwareID OBJECT-TYPE
	SYNTAX      DisplayString
	MAX-ACCESS  read-only
	STATUS      current
	DESCRIPTION
		"Gets the ID of a module's hardware."
	::= { eESNEntry 10005 }

aDisplayTimeOn OBJECT-TYPE
	SYNTAX      Unsigned32 (0..255)
	UNITS       "min"
	MAX-ACCESS  read-write
	STATUS      current
	DESCRIPTION
		"Gets, sets or defaults the display sleep timer. If the display is inactive for longer than this time, the display turns off to save power. Time is in minutes. (unit: min)"
	::= { eESNEntry 10032 }

aMaxVoltageWarning OBJECT-TYPE
	SYNTAX      Uhundredth (0..65535)
	UNITS       "V"
	MAX-ACCESS  read-write
	STATUS      current
	DESCRIPTION
		"Gets, sets or defaults the maximum voltage warning level. (unit: 0.01V)"
	::= { eESNEntry 10047 }

aMinVoltageWarning OBJECT-TYPE
	SYNTAX      Uhundredth (0..65535)
	UNITS       "V"
	MAX-ACCESS  read-write
	STATUS      current
	DESCRIPTION
		"Gets, sets or defaults the minimum voltage warning level. (unit: 0.01V)"
	::= { eESNEntry 10049 }

aMinTemperatureWarning OBJECT-TYPE
	SYNTAX      Utenth (2232..4732)
	UNITS       "K"
	MAX-ACCESS  read-write
	STATUS      current
	DESCRIPTION
		"Gets, sets or defaults the minimum temperature warning level (use DEF accessor to reset). (unit: 0.1K)"
	::= { eESNEntry 10052 }

aMaxTemperatureWarning OBJECT-TYPE
	SYNTAX      Utenth (2232..4732)
	UNITS       "K"
	MAX-ACCESS  read-write
	STATUS      current
	DESCRIPTION
		"Gets, sets or defaults the maximum temperature warning level (use DEF accessor to reset). (unit: 0.1K)"
	::= { eESNEntry 10053 }

aMinHumidityWarning OBJECT-TYPE
	SYNTAX      Utenth (0..1000)
	UNITS       "RH"
	MAX-ACCESS  read-write
	STATUS      current
	DESCRIPTION
		"Gets, sets or defaults the minimum relative humidity warning level (use DEF accessor to reset). (unit: 0.1RH)"
	::= { eESNEntry 10054 }

aMaxHumidityWarning OBJECT-TYPE
	SYNTAX      Utenth (0..1000)
	UNITS       "RH"
	MAX-ACCESS  read-write
	STATUS      current
	DESCRIPTION
		"Gets, sets or defaults the maximum relative humidity warning level (use DEF accessor to reset). (unit: 0.1RH)"
	::= { eESNEntry 10055 }

aCurrentWarningEvent OBJECT-TYPE
	SYNTAX      EVENTFLAGS
	MAX-ACCESS  read-write
	STATUS      current
	DESCRIPTION
		"Enables or disables the SNMP trap if the outlet current warning level is exceeded."
	::= { eESNEntry 10078 }

aPowerWarningEvent OBJECT-TYPE
	SYNTAX      EVENTFLAGS
	MAX-ACCESS  read-write
	STATUS      current
	DESCRIPTION
		"Enables or disables the SNMP trap if the power warning level is exceeded."
	::= { eESNEntry 10080 }

aVoltageWarningEvent OBJECT-TYPE
	SYNTAX      EVENTFLAGS
	MAX-ACCESS  read-write
	STATUS      current
	DESCRIPTION
		"Enables or disables the SNMP trap if the voltage warning level is exceeded."
	::= { eESNEntry 10086 }

aTemperatureWarningEvent OBJECT-TYPE
	SYNTAX      EVENTFLAGS
	MAX-ACCESS  read-write
	STATUS      current
	DESCRIPTION
		"Enables or disables the SNMP trap if the temperature warning level is exceeded."
	::= { eESNEntry 10087 }

aHumidityWarningEvent OBJECT-TYPE
	SYNTAX      EVENTFLAGS
	MAX-ACCESS  read-write
	STATUS      current
	DESCRIPTION
		"Enables or disables the SNMP trap if the humidity warning level is exceeded."
	::= { eESNEntry 10088 }

aDewPointWarning OBJECT-TYPE
	SYNTAX      Utenth (0..65535)
	UNITS       "K"
	MAX-ACCESS  read-write
	STATUS      current
	DESCRIPTION
		"Gets, sets or defaults the dewpoint warning level. If the temperature difference between the current temperature and the dewpoint temperature drops below this value, an event is generated. (unit: 0.1K)"
	::= { eESNEntry 10092 }

aDewPointWarningEvent OBJECT-TYPE
	SYNTAX      EVENTFLAGS
	MAX-ACCESS  read-write
	STATUS      current
	DESCRIPTION
		"Enables or disables the SNMP trap if the dewpoint warning level is exceeded."
	::= { eESNEntry 10093 }

aDewPointViolationEvent OBJECT-TYPE
	SYNTAX      EVENTFLAGS
	MAX-ACCESS  read-write
	STATUS      current
	DESCRIPTION
		"Enables or disables the SNMP trap if the dewpoint temperature is reached."
	::= { eESNEntry 10094 }

aPressureWarningEvent OBJECT-TYPE
	SYNTAX      EVENTFLAGS
	MAX-ACCESS  read-write
	STATUS      current
	DESCRIPTION
		"Enables or disables the SNMP trap if the atmospheric pressure warning level is exceeded."
	::= { eESNEntry 10095 }

aMinPressureWarning OBJECT-TYPE
	SYNTAX      Utenth (0..65535)
	UNITS       "hPa"
	MAX-ACCESS  read-write
	STATUS      current
	DESCRIPTION
		"Gets, sets or defaults the minimum atmospheric pressure warning level. (unit: 0.1hPa)"
	::= { eESNEntry 10096 }

aMaxPressureWarning OBJECT-TYPE
	SYNTAX      Utenth (0..65535)
	UNITS       "hPa"
	MAX-ACCESS  read-write
	STATUS      current
	DESCRIPTION
		"Gets, sets or defaults the maximum atmospheric pressure warning level. (unit: 0.1hPa)"
	::= { eESNEntry 10097 }

aDisplayBrightness OBJECT-TYPE
	SYNTAX      Unsigned32 (0..255)
	MAX-ACCESS  read-write
	STATUS      current
	DESCRIPTION
		"Gets, sets or defaults the display brightness (if supported)."
	::= { eESNEntry 10098 }

aMotionSensitivity OBJECT-TYPE
	SYNTAX      Unsigned32 (0..127)
	MAX-ACCESS  read-write
	STATUS      current
	DESCRIPTION
		"Gets, sets or defaults the sensitivity of a motion sensor."
	::= { eESNEntry 10107 }

aExternalSensorLabel OBJECT-TYPE
	SYNTAX      DisplayString
	MAX-ACCESS  read-write
	STATUS      current
	DESCRIPTION
		"Gets, sets or defaults the external sensor label. External sensors can be connected to Energy Sensors."
	::= { eESNEntry 10109 }

aRelayLabel OBJECT-TYPE
	SYNTAX      DisplayString
	MAX-ACCESS  read-write
	STATUS      current
	DESCRIPTION
		"Gets, sets or defaults an Energy Sensor relay label."
	::= { eESNEntry 10110 }

aMinAnalogueInputWarning OBJECT-TYPE
	SYNTAX      Unsigned32 (0..65535)
	UNITS       "mV"
	MAX-ACCESS  read-write
	STATUS      current
	DESCRIPTION
		"Gets, sets or defaults the lower warning level for an analog input. A warning is generated if this level is exceeded. (unit: mV)"
	::= { eESNEntry 10111 }

aMaxAnalogueInputWarning OBJECT-TYPE
	SYNTAX      Unsigned32 (0..65535)
	MAX-ACCESS  read-write
	STATUS      current
	DESCRIPTION
		"Gets, sets or defaults the upper warning level for an analog input. A warning is generated if this level is exceeded."
	::= { eESNEntry 10112 }

aWaterleakWarning OBJECT-TYPE
	SYNTAX      Unsigned32 (0..65535)
	MAX-ACCESS  read-write
	STATUS      current
	DESCRIPTION
		"Gets, sets or defaults the water leak detection state (0 = disabled, other values = enabled)."
	::= { eESNEntry 10113 }

aMinAirflowWarning OBJECT-TYPE
	SYNTAX      Unsigned32 (0..65535)
	MAX-ACCESS  read-write
	STATUS      current
	DESCRIPTION
		"Gets, sets or defaults the minimum warning level for an airflow sensor. A warning is generated if this level is exceeded."
	::= { eESNEntry 10114 }

aMaxAirflowWarning OBJECT-TYPE
	SYNTAX      Unsigned32 (0..65535)
	MAX-ACCESS  read-write
	STATUS      current
	DESCRIPTION
		"Gets, sets or defaults the maximum warning level for an airflow sensor. A warning is generated if this level is exceeded."
	::= { eESNEntry 10115 }

aAnalogueInputWarningEvent OBJECT-TYPE
	SYNTAX      EVENTFLAGS
	MAX-ACCESS  read-write
	STATUS      current
	DESCRIPTION
		"Enables or disables the SNMP trap if the analog input warning level is exceeded."
	::= { eESNEntry 10116 }

aWaterleakWarningEvent OBJECT-TYPE
	SYNTAX      EVENTFLAGS
	MAX-ACCESS  read-write
	STATUS      current
	DESCRIPTION
		"Enables or disables the SNMP trap if a water leak is detected."
	::= { eESNEntry 10117 }

aAirflowWarningEvent OBJECT-TYPE
	SYNTAX      EVENTFLAGS
	MAX-ACCESS  read-write
	STATUS      current
	DESCRIPTION
		"Enables or disables the SNMP trap if the airflow warning level is exceeded."
	::= { eESNEntry 10118 }

aRelayAssertActionEvent OBJECT-TYPE
	SYNTAX      EVENTFLAGS
	MAX-ACCESS  read-write
	STATUS      current
	DESCRIPTION
		"Enables or disables the SNMP trap if an Energy Sensor relay is asserted."
	::= { eESNEntry 10119 }

aRelayDeassertActionEvent OBJECT-TYPE
	SYNTAX      EVENTFLAGS
	MAX-ACCESS  read-write
	STATUS      current
	DESCRIPTION
		"Enables or disables the  SNMP trap if an Energy Sensor relay is deasserted."
	::= { eESNEntry 10120 }

aMotionWarning OBJECT-TYPE
	SYNTAX      Unsigned32 (0..127)
	MAX-ACCESS  read-write
	STATUS      current
	DESCRIPTION
		"Gets, sets or defaults the motion warning threshold."
	::= { eESNEntry 10141 }

aMotionWarningEvent OBJECT-TYPE
	SYNTAX      EVENTFLAGS
	MAX-ACCESS  read-write
	STATUS      current
	DESCRIPTION
		"Enables or disables the SNMP trap if the motion warning threshold is exceeded."
	::= { eESNEntry 10149 }

aDeviceID OBJECT-TYPE
	SYNTAX      DisplayString
	MAX-ACCESS  read-only
	STATUS      current
	DESCRIPTION
		"The ID of the device."
	::= { eESNEntry 10150 }

aDeviceVersion OBJECT-TYPE
	SYNTAX      Version
	MAX-ACCESS  read-only
	STATUS      current
	DESCRIPTION
		"The version of the device."
	::= { eESNEntry 10151 }

aSysName OBJECT-TYPE
	SYNTAX      DisplayString
	MAX-ACCESS  read-only
	STATUS      current
	DESCRIPTION
		"The full name of the device."
	::= { eESNEntry 10152 }

aMaxHighCurrentWarning OBJECT-TYPE
	SYNTAX      Stenth (-32768..32767)
	UNITS       "A"
	MAX-ACCESS  read-write
	STATUS      current
	DESCRIPTION
		"Gets sets or defaults the maximum high current warning level. (unit: 0.1A)"
	::= { eESNEntry 10165 }

aMinHighCurrentWarning OBJECT-TYPE
	SYNTAX      Stenth (-32768..32767)
	UNITS       "A"
	MAX-ACCESS  read-write
	STATUS      current
	DESCRIPTION
		"Gets sets or defaults the minimum high current warning level. (unit: 0.1A)"
	::= { eESNEntry 10176 }

aMinHighPowerWarning OBJECT-TYPE
	SYNTAX      Shundredth (-32768..32767)
	UNITS       "kW"
	MAX-ACCESS  read-write
	STATUS      current
	DESCRIPTION
		"Gets sets or defaults the power min high current warning level. (unit: 0.01kW)"
	::= { eESNEntry 10177 }

aMaxHighPowerWarning OBJECT-TYPE
	SYNTAX      Shundredth (-32768..32767)
	UNITS       "kW"
	MAX-ACCESS  read-write
	STATUS      current
	DESCRIPTION
		"Gets sets or defaults the power max high current warning level. (unit: 0.01kW)"
	::= { eESNEntry 10178 }

aIOPortWarningEvent OBJECT-TYPE
	SYNTAX      EVENTFLAGS
	MAX-ACCESS  read-write
	STATUS      current
	DESCRIPTION
		"Enables or disables the SNMP trap if the IO Port change state."
	::= { eESNEntry 10192 }

testmoduleModule OBJECT IDENTIFIER
	::= { esRACKTIVITYMIB 89 }

eTestModuleTable OBJECT-TYPE
	SYNTAX      SEQUENCE OF ETestModuleEntry
	MAX-ACCESS  not-accessible
	STATUS      current
	DESCRIPTION
		"Module to test the R-bus"
	::= { testmoduleModule 1 }

eTestModuleEntry OBJECT-TYPE
	SYNTAX      ETestModuleEntry
	MAX-ACCESS  not-accessible
	STATUS      current
	DESCRIPTION
		"Module to test the R-bus"
	INDEX       { testmoduleModuleIndex, testmoduleIndex }
	::= { eTestModuleTable 1 }

ETestModuleEntry ::= SEQUENCE {
	yGeneralModuleStatus          Unsigned32,
	ySpecificModuleStatus         Unsigned32,
	yCurrentTime                  TimeTicks,
	yCurrent                      Uthousandth,
	yStatePortCur                 CURPORTSTATE,
	yAnalogueInput                Unsigned32,
	yModuleName                   DisplayString,
	yFirmwareVersion              Version,
	yHardwareVersion              Version,
	yFirmwareID                   DisplayString,
	yHardwareID                   DisplayString,
	testmoduleIndex               Integer32,
	testmoduleModuleIndex         Integer32
}

testmoduleIndex OBJECT-TYPE
	SYNTAX      Integer32 (1..8)
	MAX-ACCESS  not-accessible
	STATUS      current
	DESCRIPTION
		"Index for the selected TestModule Module"
	::= { eTestModuleEntry 65537 }

testmoduleModuleIndex OBJECT-TYPE
	SYNTAX      Integer32 (1..8)
	MAX-ACCESS  not-accessible
	STATUS      current
	DESCRIPTION
		"Selected TestModule Module"
	::= { eTestModuleEntry 65538 }

yGeneralModuleStatus OBJECT-TYPE
	SYNTAX      Unsigned32
	MAX-ACCESS  read-only
	STATUS      current
	DESCRIPTION
		"General status of a module."
	::= { eTestModuleEntry 1 }

ySpecificModuleStatus OBJECT-TYPE
	SYNTAX      Unsigned32
	MAX-ACCESS  read-only
	STATUS      current
	DESCRIPTION
		"Specific status of a module."
	::= { eTestModuleEntry 2 }

yCurrentTime OBJECT-TYPE
	SYNTAX      TimeTicks
	UNITS       "UNIX"
	MAX-ACCESS  read-write
	STATUS      current
	DESCRIPTION
		"Gets or sets the current time (not possible when NTP is enabled). (unit: UNIX)"
	::= { eTestModuleEntry 3 }

yCurrent OBJECT-TYPE
	SYNTAX      Uthousandth
	UNITS       "A"
	MAX-ACCESS  read-only
	STATUS      current
	DESCRIPTION
		"Gets the current of an outlet. (unit: 0.001A)"
	::= { eTestModuleEntry 6 }

yStatePortCur OBJECT-TYPE
	SYNTAX      CURPORTSTATE
	MAX-ACCESS  read-only
	STATUS      current
	DESCRIPTION
		"Gets the current state of an outlet. To toggle an outlet use PORTSTAT (CLI) or pPortstate (SNMP) (GUID 10035) instead."
	::= { eTestModuleEntry 8 }

yAnalogueInput OBJECT-TYPE
	SYNTAX      Unsigned32
	UNITS       "mV"
	MAX-ACCESS  read-only
	STATUS      current
	DESCRIPTION
		"Gets the value of an analog input (voltage). (unit: mV)"
	::= { eTestModuleEntry 27 }

yModuleName OBJECT-TYPE
	SYNTAX      DisplayString
	MAX-ACCESS  read-write
	STATUS      current
	DESCRIPTION
		"Gets, sets or defaults the module name."
	::= { eTestModuleEntry 10001 }

yFirmwareVersion OBJECT-TYPE
	SYNTAX      Version
	MAX-ACCESS  read-only
	STATUS      current
	DESCRIPTION
		"Gets the version of the module's firmware."
	::= { eTestModuleEntry 10002 }

yHardwareVersion OBJECT-TYPE
	SYNTAX      Version
	MAX-ACCESS  read-only
	STATUS      current
	DESCRIPTION
		"Gets the version of a module's hardware."
	::= { eTestModuleEntry 10003 }

yFirmwareID OBJECT-TYPE
	SYNTAX      DisplayString
	MAX-ACCESS  read-only
	STATUS      current
	DESCRIPTION
		"Gets the ID of the module's firmware."
	::= { eTestModuleEntry 10004 }

yHardwareID OBJECT-TYPE
	SYNTAX      DisplayString
	MAX-ACCESS  read-only
	STATUS      current
	DESCRIPTION
		"Gets the ID of a module's hardware."
	::= { eTestModuleEntry 10005 }

pcModule OBJECT IDENTIFIER
	::= { esRACKTIVITYMIB 85 }

ePCTable OBJECT-TYPE
	SYNTAX      SEQUENCE OF EPCEntry
	MAX-ACCESS  not-accessible
	STATUS      current
	DESCRIPTION
		"NO_INFO"
	::= { pcModule 1 }

ePCEntry OBJECT-TYPE
	SYNTAX      EPCEntry
	MAX-ACCESS  not-accessible
	STATUS      current
	DESCRIPTION
		"NO_INFO"
	INDEX       { pcModuleIndex, pcIndex }
	::= { ePCTable 1 }

EPCEntry ::= SEQUENCE {
	uGeneralModuleStatus          Unsigned32,
	uSpecificModuleStatus         Unsigned32,
	uCurrentTime                  TimeTicks,
	uVoltage                      Uhundredth,
	uCurrent                      Uthousandth,
	uStatePortCur                 CURPORTSTATE,
	uTemperature                  Utenth,
	uHumidity                     Utenth,
	uModuleName                   DisplayString,
	uFirmwareVersion              Version,
	uHardwareVersion              Version,
	uFirmwareID                   DisplayString,
	uHardwareID                   DisplayString,
	uPortState                    Unsigned32,
	pcIndex                       Integer32,
	pcModuleIndex                 Integer32
}

pcIndex OBJECT-TYPE
	SYNTAX      Integer32 (1..8)
	MAX-ACCESS  not-accessible
	STATUS      current
	DESCRIPTION
		"Index for the selected PC Module"
	::= { ePCEntry 65537 }

pcModuleIndex OBJECT-TYPE
	SYNTAX      Integer32 (1..8)
	MAX-ACCESS  not-accessible
	STATUS      current
	DESCRIPTION
		"Selected PC Module"
	::= { ePCEntry 65538 }

uGeneralModuleStatus OBJECT-TYPE
	SYNTAX      Unsigned32
	MAX-ACCESS  read-only
	STATUS      current
	DESCRIPTION
		"General status of a module."
	::= { ePCEntry 1 }

uSpecificModuleStatus OBJECT-TYPE
	SYNTAX      Unsigned32
	MAX-ACCESS  read-only
	STATUS      current
	DESCRIPTION
		"Specific status of a module."
	::= { ePCEntry 2 }

uCurrentTime OBJECT-TYPE
	SYNTAX      TimeTicks
	UNITS       "UNIX"
	MAX-ACCESS  read-write
	STATUS      current
	DESCRIPTION
		"Gets or sets the current time (not possible when NTP is enabled). (unit: UNIX)"
	::= { ePCEntry 3 }

uVoltage OBJECT-TYPE
	SYNTAX      Uhundredth (0..65535)
	UNITS       "V"
	MAX-ACCESS  read-only
	STATUS      current
	DESCRIPTION
		"Gets the voltage of a power module. (unit: 0.01V)"
	::= { ePCEntry 4 }

uCurrent OBJECT-TYPE
	SYNTAX      Uthousandth (0..65535)
	UNITS       "A"
	MAX-ACCESS  read-only
	STATUS      current
	DESCRIPTION
		"Gets the current of an outlet. (unit: 0.001A)"
	::= { ePCEntry 6 }

uStatePortCur OBJECT-TYPE
	SYNTAX      CURPORTSTATE
	MAX-ACCESS  read-only
	STATUS      current
	DESCRIPTION
		"Gets the current state of an outlet. To toggle an outlet use PORTSTAT (CLI) or pPortstate (SNMP) (GUID 10035) instead."
	::= { ePCEntry 8 }

uTemperature OBJECT-TYPE
	SYNTAX      Utenth (2232..4732)
	UNITS       "K"
	MAX-ACCESS  read-only
	STATUS      current
	DESCRIPTION
		"Gets the current temperature of a temperature sensor. (unit: 0.1K)"
	::= { ePCEntry 11 }

uHumidity OBJECT-TYPE
	SYNTAX      Utenth (0..1000)
	UNITS       "RH"
	MAX-ACCESS  read-only
	STATUS      current
	DESCRIPTION
		"Gets the relative humidity. (unit: 0.1RH)"
	::= { ePCEntry 12 }

uModuleName OBJECT-TYPE
	SYNTAX      DisplayString
	MAX-ACCESS  read-write
	STATUS      current
	DESCRIPTION
		"Gets, sets or defaults the module name."
	::= { ePCEntry 10001 }

uFirmwareVersion OBJECT-TYPE
	SYNTAX      Version
	MAX-ACCESS  read-only
	STATUS      current
	DESCRIPTION
		"Gets the version of the module's firmware."
	::= { ePCEntry 10002 }

uHardwareVersion OBJECT-TYPE
	SYNTAX      Version
	MAX-ACCESS  read-only
	STATUS      current
	DESCRIPTION
		"Gets the version of a module's hardware."
	::= { ePCEntry 10003 }

uFirmwareID OBJECT-TYPE
	SYNTAX      DisplayString
	MAX-ACCESS  read-only
	STATUS      current
	DESCRIPTION
		"Gets the ID of the module's firmware."
	::= { ePCEntry 10004 }

uHardwareID OBJECT-TYPE
	SYNTAX      DisplayString
	MAX-ACCESS  read-only
	STATUS      current
	DESCRIPTION
		"Gets the ID of a module's hardware."
	::= { ePCEntry 10005 }

uPortState OBJECT-TYPE
	SYNTAX      Unsigned32 (0..1)
	MAX-ACCESS  read-write
	STATUS      current
	DESCRIPTION
		"Sets the state of an outlet: 0=OFF, 1=ON, 2=POWER CYCLE. To get the state of an outlet use CPORTSTAT (CLI) or pStatePortCur (SNMP) (GUID 8) instead."
	::= { ePCEntry 10035 }

energymonitorModule OBJECT IDENTIFIER
	::= { esRACKTIVITYMIB 69 }

eEnergyMonitorTable OBJECT-TYPE
	SYNTAX      SEQUENCE OF EEnergyMonitorEntry
	MAX-ACCESS  not-accessible
	STATUS      current
	DESCRIPTION
		"NO_INFO"
	::= { energymonitorModule 1 }

eEnergyMonitorEntry OBJECT-TYPE
	SYNTAX      EEnergyMonitorEntry
	MAX-ACCESS  not-accessible
	STATUS      current
	DESCRIPTION
		"NO_INFO"
	INDEX       { energymonitorModuleIndex, energymonitorIndex }
	::= { eEnergyMonitorTable 1 }

EEnergyMonitorEntry ::= SEQUENCE {
	eGeneralModuleStatus          Unsigned32,
	eSpecificModuleStatus         Unsigned32,
	eCurrentTime                  TimeTicks,
	eVoltage                      Uhundredth,
	eFrequency                    Uthousandth,
	eCurrent                      Uthousandth,
	ePower                        Unsigned32,
	eActiveEnergy                 Uthousandth,
	eApparentEnergy               Uthousandth,
	eTemperature                  Utenth,
	eApparentPower                Unsigned32,
	ePowerFactor                  Unsigned32,
	eTotalCurrent                 Uthousandth,
	eTotalRealPower               Unsigned32,
	eTotalApparentPower           Unsigned32,
	eTotalActiveEnergy            Uthousandth,
	eTotalApparentEnergy          Uthousandth,
	eTotalPowerFactor             Unsigned32,
	eTimeOnline                   Unsigned32,
	eTotalHarmonicDistortion      Utenth,
	eModuleName                   DisplayString,
	eFirmwareVersion              Version,
	eHardwareVersion              Version,
	eFirmwareID                   DisplayString,
	eHardwareID                   DisplayString,
	eMaxCurrentWarning            Uthousandth,
	eMaxPowerWarning              Unsigned32,
	eMaxTotalCurrentWarning       Uthousandth,
	eMaxTotalPowerWarning         Unsigned32,
	eMaxVoltageWarning            Uhundredth,
	eMinVoltageWarning            Uhundredth,
	eMinTemperatureWarning        Utenth,
	eMaxTemperatureWarning        Utenth,
	eCurrentWarningEvent          EVENTFLAGS,
	ePowerWarningEvent            EVENTFLAGS,
	eTotalCurrentWarningEvent     EVENTFLAGS,
	eTotalPowerWarningEvent       EVENTFLAGS,
	eVoltageWarningEvent          EVENTFLAGS,
	eTemperatureWarningEvent      EVENTFLAGS,
	eMicroIntTimeThreshold        Utenth,
	eMicroIntEvent                EVENTFLAGS,
	energymonitorIndex            Integer32,
	energymonitorModuleIndex      Integer32
}

energymonitorIndex OBJECT-TYPE
	SYNTAX      Integer32 (1..8)
	MAX-ACCESS  not-accessible
	STATUS      current
	DESCRIPTION
		"Index for the selected EnergyMonitor Module"
	::= { eEnergyMonitorEntry 65537 }

energymonitorModuleIndex OBJECT-TYPE
	SYNTAX      Integer32 (1..8)
	MAX-ACCESS  not-accessible
	STATUS      current
	DESCRIPTION
		"Selected EnergyMonitor Module"
	::= { eEnergyMonitorEntry 65538 }

eGeneralModuleStatus OBJECT-TYPE
	SYNTAX      Unsigned32
	MAX-ACCESS  read-only
	STATUS      current
	DESCRIPTION
		"General status of a module."
	::= { eEnergyMonitorEntry 1 }

eSpecificModuleStatus OBJECT-TYPE
	SYNTAX      Unsigned32
	MAX-ACCESS  read-only
	STATUS      current
	DESCRIPTION
		"Specific status of a module."
	::= { eEnergyMonitorEntry 2 }

eCurrentTime OBJECT-TYPE
	SYNTAX      TimeTicks
	UNITS       "UNIX"
	MAX-ACCESS  read-write
	STATUS      current
	DESCRIPTION
		"Gets or sets the current time (not possible when NTP is enabled). (unit: UNIX)"
	::= { eEnergyMonitorEntry 3 }

eVoltage OBJECT-TYPE
	SYNTAX      Uhundredth
	UNITS       "V"
	MAX-ACCESS  read-only
	STATUS      current
	DESCRIPTION
		"Gets the voltage of a power module. (unit: 0.01V)"
	::= { eEnergyMonitorEntry 4 }

eFrequency OBJECT-TYPE
	SYNTAX      Uthousandth
	UNITS       "Hz"
	MAX-ACCESS  read-only
	STATUS      current
	DESCRIPTION
		"Gets the frequency of the input voltage of a power module. (unit: 0.001Hz)"
	::= { eEnergyMonitorEntry 5 }

eCurrent OBJECT-TYPE
	SYNTAX      Uthousandth
	UNITS       "A"
	MAX-ACCESS  read-only
	STATUS      current
	DESCRIPTION
		"Gets the current of an outlet. (unit: 0.001A)"
	::= { eEnergyMonitorEntry 6 }

ePower OBJECT-TYPE
	SYNTAX      Unsigned32
	UNITS       "W"
	MAX-ACCESS  read-only
	STATUS      current
	DESCRIPTION
		"Gets the power of an outlet. (unit: W)"
	::= { eEnergyMonitorEntry 7 }

eActiveEnergy OBJECT-TYPE
	SYNTAX      Uthousandth
	UNITS       "kWh"
	MAX-ACCESS  read-only
	STATUS      current
	DESCRIPTION
		"Gets the energy used by an outlet. (unit: 0.001kWh)"
	::= { eEnergyMonitorEntry 9 }

eApparentEnergy OBJECT-TYPE
	SYNTAX      Uthousandth
	UNITS       "kVAh"
	MAX-ACCESS  read-only
	STATUS      current
	DESCRIPTION
		"Gets the apparent energy used by an outlet. (unit: 0.001kVAh)"
	::= { eEnergyMonitorEntry 10 }

eTemperature OBJECT-TYPE
	SYNTAX      Utenth
	UNITS       "K"
	MAX-ACCESS  read-only
	STATUS      current
	DESCRIPTION
		"Gets the current temperature of a temperature sensor. (unit: 0.1K)"
	::= { eEnergyMonitorEntry 11 }

eApparentPower OBJECT-TYPE
	SYNTAX      Unsigned32
	UNITS       "VA"
	MAX-ACCESS  read-only
	STATUS      current
	DESCRIPTION
		"Gets the apparent power of an outlet. (unit: VA)"
	::= { eEnergyMonitorEntry 15 }

ePowerFactor OBJECT-TYPE
	SYNTAX      Unsigned32
	UNITS       "%"
	MAX-ACCESS  read-only
	STATUS      current
	DESCRIPTION
		"Gets the power factor of an outlet. (unit: %)"
	::= { eEnergyMonitorEntry 16 }

eTotalCurrent OBJECT-TYPE
	SYNTAX      Uthousandth
	UNITS       "A"
	MAX-ACCESS  read-only
	STATUS      current
	DESCRIPTION
		"Gets the total current of a power module. (unit: 0.001A)"
	::= { eEnergyMonitorEntry 17 }

eTotalRealPower OBJECT-TYPE
	SYNTAX      Unsigned32
	UNITS       "W"
	MAX-ACCESS  read-only
	STATUS      current
	DESCRIPTION
		"Gets the total power level of a power module. (unit: W)"
	::= { eEnergyMonitorEntry 18 }

eTotalApparentPower OBJECT-TYPE
	SYNTAX      Unsigned32
	UNITS       "VA"
	MAX-ACCESS  read-only
	STATUS      current
	DESCRIPTION
		"Gets the total apparent power of a power module. (unit: VA)"
	::= { eEnergyMonitorEntry 19 }

eTotalActiveEnergy OBJECT-TYPE
	SYNTAX      Uthousandth
	UNITS       "kWh"
	MAX-ACCESS  read-only
	STATUS      current
	DESCRIPTION
		"Gets the total energy of a power module. (unit: 0.001kWh)"
	::= { eEnergyMonitorEntry 20 }

eTotalApparentEnergy OBJECT-TYPE
	SYNTAX      Uthousandth
	UNITS       "kVAh"
	MAX-ACCESS  read-only
	STATUS      current
	DESCRIPTION
		"Gets the total apparent energy of a power module. (unit: 0.001kVAh)"
	::= { eEnergyMonitorEntry 21 }

eTotalPowerFactor OBJECT-TYPE
	SYNTAX      Unsigned32
	UNITS       "%"
	MAX-ACCESS  read-only
	STATUS      current
	DESCRIPTION
		"Gets the total power factor of a power module. (unit: %)"
	::= { eEnergyMonitorEntry 22 }

eTimeOnline OBJECT-TYPE
	SYNTAX      Unsigned32
	UNITS       "s"
	MAX-ACCESS  read-only
	STATUS      current
	DESCRIPTION
		"Gets the amount of seconds since the last reset. (unit: s)"
	::= { eEnergyMonitorEntry 24 }

eTotalHarmonicDistortion OBJECT-TYPE
	SYNTAX      Utenth (0..1000)
	UNITS       "%"
	MAX-ACCESS  read-only
	STATUS      current
	DESCRIPTION
		"total harmonic distortion - outlet (unit: 0.1%)"
	::= { eEnergyMonitorEntry 50 }

eModuleName OBJECT-TYPE
	SYNTAX      DisplayString
	MAX-ACCESS  read-write
	STATUS      current
	DESCRIPTION
		"Gets, sets or defaults the module name."
	::= { eEnergyMonitorEntry 10001 }

eFirmwareVersion OBJECT-TYPE
	SYNTAX      Version
	MAX-ACCESS  read-only
	STATUS      current
	DESCRIPTION
		"Gets the version of the module's firmware."
	::= { eEnergyMonitorEntry 10002 }

eHardwareVersion OBJECT-TYPE
	SYNTAX      Version
	MAX-ACCESS  read-only
	STATUS      current
	DESCRIPTION
		"Gets the version of a module's hardware."
	::= { eEnergyMonitorEntry 10003 }

eFirmwareID OBJECT-TYPE
	SYNTAX      DisplayString
	MAX-ACCESS  read-only
	STATUS      current
	DESCRIPTION
		"Gets the ID of the module's firmware."
	::= { eEnergyMonitorEntry 10004 }

eHardwareID OBJECT-TYPE
	SYNTAX      DisplayString
	MAX-ACCESS  read-only
	STATUS      current
	DESCRIPTION
		"Gets the ID of a module's hardware."
	::= { eEnergyMonitorEntry 10005 }

eMaxCurrentWarning OBJECT-TYPE
	SYNTAX      Uthousandth (100..8000)
	UNITS       "A"
	MAX-ACCESS  read-write
	STATUS      current
	DESCRIPTION
		"Gets, sets or defaults the maximum current warning level of an outlet. (unit: 0.001A)"
	::= { eEnergyMonitorEntry 10039 }

eMaxPowerWarning OBJECT-TYPE
	SYNTAX      Unsigned32 (20..2000)
	UNITS       "W"
	MAX-ACCESS  read-write
	STATUS      current
	DESCRIPTION
		"Gets, sets or defaults the maximum power warning level of an outlet. (unit: W)"
	::= { eEnergyMonitorEntry 10041 }

eMaxTotalCurrentWarning OBJECT-TYPE
	SYNTAX      Uthousandth (100..16000)
	UNITS       "A"
	MAX-ACCESS  read-write
	STATUS      current
	DESCRIPTION
		"Gets, sets or defaults the total maximum current warning level of a power module. (unit: 0.001A)"
	::= { eEnergyMonitorEntry 10043 }

eMaxTotalPowerWarning OBJECT-TYPE
	SYNTAX      Unsigned32 (20..4000)
	UNITS       "W"
	MAX-ACCESS  read-write
	STATUS      current
	DESCRIPTION
		"Gets, sets or defaults the maximum total power warning level. (unit: W)"
	::= { eEnergyMonitorEntry 10045 }

eMaxVoltageWarning OBJECT-TYPE
	SYNTAX      Uhundredth (5000..30000)
	UNITS       "V"
	MAX-ACCESS  read-write
	STATUS      current
	DESCRIPTION
		"Gets, sets or defaults the maximum voltage warning level. (unit: 0.01V)"
	::= { eEnergyMonitorEntry 10047 }

eMinVoltageWarning OBJECT-TYPE
	SYNTAX      Uhundredth (5000..30000)
	UNITS       "V"
	MAX-ACCESS  read-write
	STATUS      current
	DESCRIPTION
		"Gets, sets or defaults the minimum voltage warning level. (unit: 0.01V)"
	::= { eEnergyMonitorEntry 10049 }

eMinTemperatureWarning OBJECT-TYPE
	SYNTAX      Utenth (2232..4732)
	UNITS       "K"
	MAX-ACCESS  read-write
	STATUS      current
	DESCRIPTION
		"Gets, sets or defaults the minimum temperature warning level (use DEF accessor to reset). (unit: 0.1K)"
	::= { eEnergyMonitorEntry 10052 }

eMaxTemperatureWarning OBJECT-TYPE
	SYNTAX      Utenth (2232..4732)
	UNITS       "K"
	MAX-ACCESS  read-write
	STATUS      current
	DESCRIPTION
		"Gets, sets or defaults the maximum temperature warning level (use DEF accessor to reset). (unit: 0.1K)"
	::= { eEnergyMonitorEntry 10053 }

eCurrentWarningEvent OBJECT-TYPE
	SYNTAX      EVENTFLAGS
	MAX-ACCESS  read-write
	STATUS      current
	DESCRIPTION
		"Enables or disables the SNMP trap if the outlet current warning level is exceeded."
	::= { eEnergyMonitorEntry 10078 }

ePowerWarningEvent OBJECT-TYPE
	SYNTAX      EVENTFLAGS
	MAX-ACCESS  read-write
	STATUS      current
	DESCRIPTION
		"Enables or disables the SNMP trap if the power warning level is exceeded."
	::= { eEnergyMonitorEntry 10080 }

eTotalCurrentWarningEvent OBJECT-TYPE
	SYNTAX      EVENTFLAGS
	MAX-ACCESS  read-write
	STATUS      current
	DESCRIPTION
		"Enables or disables the SNMP trap if the total outlet current warning level is exceeded."
	::= { eEnergyMonitorEntry 10082 }

eTotalPowerWarningEvent OBJECT-TYPE
	SYNTAX      EVENTFLAGS
	MAX-ACCESS  read-write
	STATUS      current
	DESCRIPTION
		"Enables or disables the SNMP trap if the total power warning level is exceeded."
	::= { eEnergyMonitorEntry 10084 }

eVoltageWarningEvent OBJECT-TYPE
	SYNTAX      EVENTFLAGS
	MAX-ACCESS  read-write
	STATUS      current
	DESCRIPTION
		"Enables or disables the SNMP trap if the voltage warning level is exceeded."
	::= { eEnergyMonitorEntry 10086 }

eTemperatureWarningEvent OBJECT-TYPE
	SYNTAX      EVENTFLAGS
	MAX-ACCESS  read-write
	STATUS      current
	DESCRIPTION
		"Enables or disables the SNMP trap if the temperature warning level is exceeded."
	::= { eEnergyMonitorEntry 10087 }

eMicroIntTimeThreshold OBJECT-TYPE
	SYNTAX      Utenth (10..65535)
	UNITS       "ms"
	MAX-ACCESS  read-write
	STATUS      current
	DESCRIPTION
		"The minimum time the voltage must be interrupted before it is seen as a micro interruption (unit: 0.1ms)"
	::= { eEnergyMonitorEntry 10135 }

eMicroIntEvent OBJECT-TYPE
	SYNTAX      EVENTFLAGS
	MAX-ACCESS  read-write
	STATUS      current
	DESCRIPTION
		"Enables or disables the SNMP trap if a microinterruption on the voltage is detected."
	::= { eEnergyMonitorEntry 10136 }

threephasepowerModule OBJECT IDENTIFIER
	::= { esRACKTIVITYMIB 66 }

eThreePhasePowerTable OBJECT-TYPE
	SYNTAX      SEQUENCE OF EThreePhasePowerEntry
	MAX-ACCESS  not-accessible
	STATUS      current
	DESCRIPTION
		"NO_INFO"
	::= { threephasepowerModule 1 }

eThreePhasePowerEntry OBJECT-TYPE
	SYNTAX      EThreePhasePowerEntry
	MAX-ACCESS  not-accessible
	STATUS      current
	DESCRIPTION
		"NO_INFO"
	INDEX       { threephasepowerModuleIndex, threephasepowerIndex }
	::= { eThreePhasePowerTable 1 }

EThreePhasePowerEntry ::= SEQUENCE {
	threephasepowerIndex          Integer32,
	threephasepowerModuleIndex    Integer32
}

threephasepowerIndex OBJECT-TYPE
	SYNTAX      Integer32 (1..8)
	MAX-ACCESS  not-accessible
	STATUS      current
	DESCRIPTION
		"Index for the selected ThreePhasePower Module"
	::= { eThreePhasePowerEntry 65537 }

threephasepowerModuleIndex OBJECT-TYPE
	SYNTAX      Integer32 (1..8)
	MAX-ACCESS  not-accessible
	STATUS      current
	DESCRIPTION
		"Selected ThreePhasePower Module"
	::= { eThreePhasePowerEntry 65538 }

measuring3phaseModule OBJECT IDENTIFIER
	::= { esRACKTIVITYMIB 81 }

eMeasuring3PhaseTable OBJECT-TYPE
	SYNTAX      SEQUENCE OF EMeasuring3PhaseEntry
	MAX-ACCESS  not-accessible
	STATUS      current
	DESCRIPTION
		"NO_INFO"
	::= { measuring3phaseModule 1 }

eMeasuring3PhaseEntry OBJECT-TYPE
	SYNTAX      EMeasuring3PhaseEntry
	MAX-ACCESS  not-accessible
	STATUS      current
	DESCRIPTION
		"NO_INFO"
	INDEX       { measuring3phaseModuleIndex, measuring3phaseIndex }
	::= { eMeasuring3PhaseTable 1 }

EMeasuring3PhaseEntry ::= SEQUENCE {
	qGeneralModuleStatus          Unsigned32,
	qSpecificModuleStatus         Unsigned32,
	qCurrentTime                  TimeTicks,
	qVoltage                      Uhundredth,
	qFrequency                    Uthousandth,
	qActiveEnergy                 Uthousandth,
	qApparentEnergy               Uthousandth,
	qTemperature                  Utenth,
	qPowerFactor                  Unsigned32,
	qTimeOnline                   Unsigned32,
	qIOPort                       Unsigned32,
	qTotalHarmonicDistortion      Utenth,
	qPhase                        Unsigned32,
	qBigCurrent                   Unsigned32,
	qBigPower                     Uthousandth,
	qBigApparentPower             Uthousandth,
	qStatus                       Unsigned32,
	qModuleName                   DisplayString,
	qFirmwareVersion              Version,
	qHardwareVersion              Version,
	qFirmwareID                   DisplayString,
	qHardwareID                   DisplayString,
	qPortState                    Unsigned32,
	qMaxVoltageWarning            Uhundredth,
	qMinVoltageWarning            Uhundredth,
	qMinTemperatureWarning        Utenth,
	qMaxTemperatureWarning        Utenth,
	qPortStateEvent               EVENTFLAGS,
	qCurrentWarningEvent          EVENTFLAGS,
	qPowerWarningEvent            EVENTFLAGS,
	qVoltageWarningEvent          EVENTFLAGS,
	qTemperatureWarningEvent      EVENTFLAGS,
	qMicroIntTimeThreshold        Utenth,
	qMicroIntEvent                EVENTFLAGS,
	qDeviceID                     DisplayString,
	qDeviceVersion                Version,
	qMaxBigCurrentWarning         Unsigned32,
	qMaxBigPowerWarning           Uthousandth,
	qCurrentSensorSelector        Unsigned32,
	qMinBigCurrentWarning         Unsigned32,
	qkWhMode                      Unsigned32,
	measuring3phaseIndex          Integer32,
	measuring3phaseModuleIndex    Integer32
}

measuring3phaseIndex OBJECT-TYPE
	SYNTAX      Integer32 (1..8)
	MAX-ACCESS  not-accessible
	STATUS      current
	DESCRIPTION
		"Index for the selected Measuring3Phase Module"
	::= { eMeasuring3PhaseEntry 65537 }

measuring3phaseModuleIndex OBJECT-TYPE
	SYNTAX      Integer32 (1..8)
	MAX-ACCESS  not-accessible
	STATUS      current
	DESCRIPTION
		"Selected Measuring3Phase Module"
	::= { eMeasuring3PhaseEntry 65538 }

qGeneralModuleStatus OBJECT-TYPE
	SYNTAX      Unsigned32
	MAX-ACCESS  read-only
	STATUS      current
	DESCRIPTION
		"General status of a module."
	::= { eMeasuring3PhaseEntry 1 }

qSpecificModuleStatus OBJECT-TYPE
	SYNTAX      Unsigned32
	MAX-ACCESS  read-only
	STATUS      current
	DESCRIPTION
		"Specific status of a module."
	::= { eMeasuring3PhaseEntry 2 }

qCurrentTime OBJECT-TYPE
	SYNTAX      TimeTicks
	UNITS       "UNIX"
	MAX-ACCESS  read-write
	STATUS      current
	DESCRIPTION
		"Gets or sets the current time (not possible when NTP is enabled). (unit: UNIX)"
	::= { eMeasuring3PhaseEntry 3 }

qVoltage OBJECT-TYPE
	SYNTAX      Uhundredth
	UNITS       "V"
	MAX-ACCESS  read-only
	STATUS      current
	DESCRIPTION
		"Gets the voltage of a power module. (unit: 0.01V)"
	::= { eMeasuring3PhaseEntry 4 }

qFrequency OBJECT-TYPE
	SYNTAX      Uthousandth
	UNITS       "Hz"
	MAX-ACCESS  read-only
	STATUS      current
	DESCRIPTION
		"Gets the frequency of the input voltage of a power module. (unit: 0.001Hz)"
	::= { eMeasuring3PhaseEntry 5 }

qActiveEnergy OBJECT-TYPE
	SYNTAX      Uthousandth
	UNITS       "kWh"
	MAX-ACCESS  read-only
	STATUS      current
	DESCRIPTION
		"Gets the energy used by an outlet. (unit: 0.001kWh)"
	::= { eMeasuring3PhaseEntry 9 }

qApparentEnergy OBJECT-TYPE
	SYNTAX      Uthousandth
	UNITS       "kVAh"
	MAX-ACCESS  read-only
	STATUS      current
	DESCRIPTION
		"Gets the apparent energy used by an outlet. (unit: 0.001kVAh)"
	::= { eMeasuring3PhaseEntry 10 }

qTemperature OBJECT-TYPE
	SYNTAX      Utenth
	UNITS       "K"
	MAX-ACCESS  read-only
	STATUS      current
	DESCRIPTION
		"Gets the current temperature of a temperature sensor. (unit: 0.1K)"
	::= { eMeasuring3PhaseEntry 11 }

qPowerFactor OBJECT-TYPE
	SYNTAX      Unsigned32
	UNITS       "%"
	MAX-ACCESS  read-only
	STATUS      current
	DESCRIPTION
		"Gets the power factor of an outlet. (unit: %)"
	::= { eMeasuring3PhaseEntry 16 }

qTimeOnline OBJECT-TYPE
	SYNTAX      Unsigned32
	UNITS       "s"
	MAX-ACCESS  read-only
	STATUS      current
	DESCRIPTION
		"Gets the amount of seconds since the last reset. (unit: s)"
	::= { eMeasuring3PhaseEntry 24 }

qIOPort OBJECT-TYPE
	SYNTAX      Unsigned32 (0..1)
	MAX-ACCESS  read-only
	STATUS      current
	DESCRIPTION
		"Gets the state of a digital input."
	::= { eMeasuring3PhaseEntry 30 }

qTotalHarmonicDistortion OBJECT-TYPE
	SYNTAX      Utenth (0..1000)
	UNITS       "%"
	MAX-ACCESS  read-only
	STATUS      current
	DESCRIPTION
		"total harmonic distortion - outlet (unit: 0.1%)"
	::= { eMeasuring3PhaseEntry 50 }

qPhase OBJECT-TYPE
	SYNTAX      Unsigned32 (0..65535)
	UNITS       "degr"
	MAX-ACCESS  read-only
	STATUS      current
	DESCRIPTION
		"the phase between 2 waves (unit: degr)"
	::= { eMeasuring3PhaseEntry 51 }

qBigCurrent OBJECT-TYPE
	SYNTAX      Unsigned32
	UNITS       "A"
	MAX-ACCESS  read-only
	STATUS      current
	DESCRIPTION
		"Gets the current of an outlet. (unit: 0.0001A)"
	::= { eMeasuring3PhaseEntry 52 }

qBigPower OBJECT-TYPE
	SYNTAX      Uthousandth
	UNITS       "W"
	MAX-ACCESS  read-only
	STATUS      current
	DESCRIPTION
		"Gets the power of an outlet. (unit: 0.001W)"
	::= { eMeasuring3PhaseEntry 53 }

qBigApparentPower OBJECT-TYPE
	SYNTAX      Uthousandth
	UNITS       "VA"
	MAX-ACCESS  read-only
	STATUS      current
	DESCRIPTION
		"Gets the apparent power of an outlet. (unit: 0.001VA)"
	::= { eMeasuring3PhaseEntry 54 }

qStatus OBJECT-TYPE
	SYNTAX      Unsigned32 (0..65535)
	MAX-ACCESS  read-only
	STATUS      current
	DESCRIPTION
		"status of a module"
	::= { eMeasuring3PhaseEntry 1000 }

qModuleName OBJECT-TYPE
	SYNTAX      DisplayString
	MAX-ACCESS  read-write
	STATUS      current
	DESCRIPTION
		"Gets, sets or defaults the module name."
	::= { eMeasuring3PhaseEntry 10001 }

qFirmwareVersion OBJECT-TYPE
	SYNTAX      Version
	MAX-ACCESS  read-only
	STATUS      current
	DESCRIPTION
		"Gets the version of the module's firmware."
	::= { eMeasuring3PhaseEntry 10002 }

qHardwareVersion OBJECT-TYPE
	SYNTAX      Version
	MAX-ACCESS  read-only
	STATUS      current
	DESCRIPTION
		"Gets the version of a module's hardware."
	::= { eMeasuring3PhaseEntry 10003 }

qFirmwareID OBJECT-TYPE
	SYNTAX      DisplayString
	MAX-ACCESS  read-only
	STATUS      current
	DESCRIPTION
		"Gets the ID of the module's firmware."
	::= { eMeasuring3PhaseEntry 10004 }

qHardwareID OBJECT-TYPE
	SYNTAX      DisplayString
	MAX-ACCESS  read-only
	STATUS      current
	DESCRIPTION
		"Gets the ID of a module's hardware."
	::= { eMeasuring3PhaseEntry 10005 }

qPortState OBJECT-TYPE
	SYNTAX      Unsigned32 (0..1)
	MAX-ACCESS  read-write
	STATUS      current
	DESCRIPTION
		"Sets the state of an outlet: 0=OFF, 1=ON, 2=POWER CYCLE. To get the state of an outlet use CPORTSTAT (CLI) or pStatePortCur (SNMP) (GUID 8) instead."
	::= { eMeasuring3PhaseEntry 10035 }

qMaxVoltageWarning OBJECT-TYPE
	SYNTAX      Uhundredth (5000..30000)
	UNITS       "V"
	MAX-ACCESS  read-write
	STATUS      current
	DESCRIPTION
		"Gets, sets or defaults the maximum voltage warning level. (unit: 0.01V)"
	::= { eMeasuring3PhaseEntry 10047 }

qMinVoltageWarning OBJECT-TYPE
	SYNTAX      Uhundredth (5000..30000)
	UNITS       "V"
	MAX-ACCESS  read-write
	STATUS      current
	DESCRIPTION
		"Gets, sets or defaults the minimum voltage warning level. (unit: 0.01V)"
	::= { eMeasuring3PhaseEntry 10049 }

qMinTemperatureWarning OBJECT-TYPE
	SYNTAX      Utenth (2232..4732)
	UNITS       "K"
	MAX-ACCESS  read-write
	STATUS      current
	DESCRIPTION
		"Gets, sets or defaults the minimum temperature warning level (use DEF accessor to reset). (unit: 0.1K)"
	::= { eMeasuring3PhaseEntry 10052 }

qMaxTemperatureWarning OBJECT-TYPE
	SYNTAX      Utenth (2232..4732)
	UNITS       "K"
	MAX-ACCESS  read-write
	STATUS      current
	DESCRIPTION
		"Gets, sets or defaults the maximum temperature warning level (use DEF accessor to reset). (unit: 0.1K)"
	::= { eMeasuring3PhaseEntry 10053 }

qPortStateEvent OBJECT-TYPE
	SYNTAX      EVENTFLAGS
	MAX-ACCESS  read-write
	STATUS      current
	DESCRIPTION
		"Enables or disables the SNMP trap if the state of an outlet is changed."
	::= { eMeasuring3PhaseEntry 10076 }

qCurrentWarningEvent OBJECT-TYPE
	SYNTAX      EVENTFLAGS
	MAX-ACCESS  read-write
	STATUS      current
	DESCRIPTION
		"Enables or disables the SNMP trap if the outlet current warning level is exceeded."
	::= { eMeasuring3PhaseEntry 10078 }

qPowerWarningEvent OBJECT-TYPE
	SYNTAX      EVENTFLAGS
	MAX-ACCESS  read-write
	STATUS      current
	DESCRIPTION
		"Enables or disables the SNMP trap if the power warning level is exceeded."
	::= { eMeasuring3PhaseEntry 10080 }

qVoltageWarningEvent OBJECT-TYPE
	SYNTAX      EVENTFLAGS
	MAX-ACCESS  read-write
	STATUS      current
	DESCRIPTION
		"Enables or disables the SNMP trap if the voltage warning level is exceeded."
	::= { eMeasuring3PhaseEntry 10086 }

qTemperatureWarningEvent OBJECT-TYPE
	SYNTAX      EVENTFLAGS
	MAX-ACCESS  read-write
	STATUS      current
	DESCRIPTION
		"Enables or disables the SNMP trap if the temperature warning level is exceeded."
	::= { eMeasuring3PhaseEntry 10087 }

qMicroIntTimeThreshold OBJECT-TYPE
	SYNTAX      Utenth (10..65535)
	UNITS       "ms"
	MAX-ACCESS  read-write
	STATUS      current
	DESCRIPTION
		"The minimum time the voltage must be interrupted before it is seen as a micro interruption (unit: 0.1ms)"
	::= { eMeasuring3PhaseEntry 10135 }

qMicroIntEvent OBJECT-TYPE
	SYNTAX      EVENTFLAGS
	MAX-ACCESS  read-write
	STATUS      current
	DESCRIPTION
		"Enables or disables the SNMP trap if a microinterruption on the voltage is detected."
	::= { eMeasuring3PhaseEntry 10136 }

qDeviceID OBJECT-TYPE
	SYNTAX      DisplayString
	MAX-ACCESS  read-only
	STATUS      current
	DESCRIPTION
		"The ID of the device."
	::= { eMeasuring3PhaseEntry 10150 }

qDeviceVersion OBJECT-TYPE
	SYNTAX      Version
	MAX-ACCESS  read-only
	STATUS      current
	DESCRIPTION
		"The version of the device."
	::= { eMeasuring3PhaseEntry 10151 }

qMaxBigCurrentWarning OBJECT-TYPE
	SYNTAX      Unsigned32 (100..400000000)
	UNITS       "A"
	MAX-ACCESS  read-write
	STATUS      current
	DESCRIPTION
		"Gets, sets or defaults the maximum current warning level of an outlet. (unit: 0.0001A)"
	::= { eMeasuring3PhaseEntry 10193 }

qMaxBigPowerWarning OBJECT-TYPE
	SYNTAX      Uthousandth (2000..2000000000)
	UNITS       "W"
	MAX-ACCESS  read-write
	STATUS      current
	DESCRIPTION
		"Gets, sets or defaults the maximum power warning level of an outlet. (unit: 0.001W)"
	::= { eMeasuring3PhaseEntry 10194 }

qCurrentSensorSelector OBJECT-TYPE
	SYNTAX      Unsigned32 (0..255)
	MAX-ACCESS  read-write
	STATUS      current
	DESCRIPTION
		"Selection of the currentsensor connected to port. To enter your own value you need to use 255 and fill in guid 10190."
	::= { eMeasuring3PhaseEntry 10197 }

qMinBigCurrentWarning OBJECT-TYPE
	SYNTAX      Unsigned32 (0..400000000)
	UNITS       "A"
	MAX-ACCESS  read-write
	STATUS      current
	DESCRIPTION
		"Gets, sets or defaults the minimum current warning level of a port. (unit: 0.0001A)"
	::= { eMeasuring3PhaseEntry 10209 }

qkWhMode OBJECT-TYPE
	SYNTAX      Unsigned32 (0..2)
	MAX-ACCESS  read-write
	STATUS      current
	DESCRIPTION
		"Set the mode when to count kWh, 0 = always, 1 = only positive, 2= only negative"
	::= { eMeasuring3PhaseEntry 10234 }

displaymoduleModule OBJECT IDENTIFIER
	::= { esRACKTIVITYMIB 68 }

eDisplayModuleTable OBJECT-TYPE
	SYNTAX      SEQUENCE OF EDisplayModuleEntry
	MAX-ACCESS  not-accessible
	STATUS      current
	DESCRIPTION
		"NO_INFO"
	::= { displaymoduleModule 1 }

eDisplayModuleEntry OBJECT-TYPE
	SYNTAX      EDisplayModuleEntry
	MAX-ACCESS  not-accessible
	STATUS      current
	DESCRIPTION
		"NO_INFO"
	INDEX       { displaymoduleModuleIndex, displaymoduleIndex }
	::= { eDisplayModuleTable 1 }

EDisplayModuleEntry ::= SEQUENCE {
	dGeneralModuleStatus          Unsigned32,
	dSpecificModuleStatus         Unsigned32,
	dCurrentTime                  TimeTicks,
	dTemperature                  Utenth,
	dTimeOnline                   Unsigned32,
	dModuleName                   DisplayString,
	dFirmwareVersion              Version,
	dHardwareVersion              Version,
	dFirmwareID                   DisplayString,
	dHardwareID                   DisplayString,
	dMinTemperatureWarning        Utenth,
	dMaxTemperatureWarning        Utenth,
	dDisplayAllDevices            Unsigned32,
	displaymoduleIndex            Integer32,
	displaymoduleModuleIndex      Integer32
}

displaymoduleIndex OBJECT-TYPE
	SYNTAX      Integer32 (1..8)
	MAX-ACCESS  not-accessible
	STATUS      current
	DESCRIPTION
		"Index for the selected DisplayModule Module"
	::= { eDisplayModuleEntry 65537 }

displaymoduleModuleIndex OBJECT-TYPE
	SYNTAX      Integer32 (1..8)
	MAX-ACCESS  not-accessible
	STATUS      current
	DESCRIPTION
		"Selected DisplayModule Module"
	::= { eDisplayModuleEntry 65538 }

dGeneralModuleStatus OBJECT-TYPE
	SYNTAX      Unsigned32
	MAX-ACCESS  read-only
	STATUS      current
	DESCRIPTION
		"General status of a module."
	::= { eDisplayModuleEntry 1 }

dSpecificModuleStatus OBJECT-TYPE
	SYNTAX      Unsigned32
	MAX-ACCESS  read-only
	STATUS      current
	DESCRIPTION
		"Specific status of a module."
	::= { eDisplayModuleEntry 2 }

dCurrentTime OBJECT-TYPE
	SYNTAX      TimeTicks
	UNITS       "UNIX"
	MAX-ACCESS  read-write
	STATUS      current
	DESCRIPTION
		"Gets or sets the current time (not possible when NTP is enabled). (unit: UNIX)"
	::= { eDisplayModuleEntry 3 }

dTemperature OBJECT-TYPE
	SYNTAX      Utenth
	UNITS       "K"
	MAX-ACCESS  read-only
	STATUS      current
	DESCRIPTION
		"Gets the current temperature of a temperature sensor. (unit: 0.1K)"
	::= { eDisplayModuleEntry 11 }

dTimeOnline OBJECT-TYPE
	SYNTAX      Unsigned32
	UNITS       "s"
	MAX-ACCESS  read-only
	STATUS      current
	DESCRIPTION
		"Gets the amount of seconds since the last reset. (unit: s)"
	::= { eDisplayModuleEntry 24 }

dModuleName OBJECT-TYPE
	SYNTAX      DisplayString
	MAX-ACCESS  read-write
	STATUS      current
	DESCRIPTION
		"Gets, sets or defaults the module name."
	::= { eDisplayModuleEntry 10001 }

dFirmwareVersion OBJECT-TYPE
	SYNTAX      Version
	MAX-ACCESS  read-only
	STATUS      current
	DESCRIPTION
		"Gets the version of the module's firmware."
	::= { eDisplayModuleEntry 10002 }

dHardwareVersion OBJECT-TYPE
	SYNTAX      Version
	MAX-ACCESS  read-only
	STATUS      current
	DESCRIPTION
		"Gets the version of a module's hardware."
	::= { eDisplayModuleEntry 10003 }

dFirmwareID OBJECT-TYPE
	SYNTAX      DisplayString
	MAX-ACCESS  read-only
	STATUS      current
	DESCRIPTION
		"Gets the ID of the module's firmware."
	::= { eDisplayModuleEntry 10004 }

dHardwareID OBJECT-TYPE
	SYNTAX      DisplayString
	MAX-ACCESS  read-only
	STATUS      current
	DESCRIPTION
		"Gets the ID of a module's hardware."
	::= { eDisplayModuleEntry 10005 }

dMinTemperatureWarning OBJECT-TYPE
	SYNTAX      Utenth (2232..4732)
	UNITS       "K"
	MAX-ACCESS  read-write
	STATUS      current
	DESCRIPTION
		"Gets, sets or defaults the minimum temperature warning level (use DEF accessor to reset). (unit: 0.1K)"
	::= { eDisplayModuleEntry 10052 }

dMaxTemperatureWarning OBJECT-TYPE
	SYNTAX      Utenth (2232..4732)
	UNITS       "K"
	MAX-ACCESS  read-write
	STATUS      current
	DESCRIPTION
		"Gets, sets or defaults the maximum temperature warning level (use DEF accessor to reset). (unit: 0.1K)"
	::= { eDisplayModuleEntry 10053 }

dDisplayAllDevices OBJECT-TYPE
	SYNTAX      Unsigned32 (0..1)
	MAX-ACCESS  read-write
	STATUS      current
	DESCRIPTION
		"If a display need to show all devices or just a small list"
	::= { eDisplayModuleEntry 10237 }

errorValueTooHighRaised NOTIFICATION-TYPE
	STATUS current
	DESCRIPTION
		"This trap is sent when an element goes above the specified error threshold indicating the maximum value for this element"
	::= { racktivityNotif 16 }

errorValueTooLowRaised NOTIFICATION-TYPE
	STATUS current
	DESCRIPTION
		"This trap is sent when an element goes below the specified error threshold indicating the minimum value for this element"
	::= { racktivityNotif 17 }

errorRaised NOTIFICATION-TYPE
	STATUS current
	DESCRIPTION
		"This trap is sent when an element gets into an error state"
	::= { racktivityNotif 18 }

errorValueTooHighCleared NOTIFICATION-TYPE
	STATUS current
	DESCRIPTION
		"This trap is sent when an element goes below the specified error threshold indicating the maximum value for this element"
	::= { racktivityNotif 19 }

errorValueTooLowCleared NOTIFICATION-TYPE
	STATUS current
	DESCRIPTION
		"This trap is sent when an element goes above the specified error threshold indicating the minimum value for this element"
	::= { racktivityNotif 20 }

errorCleared NOTIFICATION-TYPE
	STATUS current
	DESCRIPTION
		"This trap is sent when an element recovers from an error state"
	::= { racktivityNotif 21 }

warningValueTooHighRaised NOTIFICATION-TYPE
	STATUS current
	DESCRIPTION
		"This trap is sent when an element goes above the specified warning threshold indicating the  maximum value for this element"
	::= { racktivityNotif 48 }

warningValueTooLowRaised NOTIFICATION-TYPE
	STATUS current
	DESCRIPTION
		"This trap is sent when an element goes below the specified warning threshold indicating the minimum value for this element"
	::= { racktivityNotif 49 }

warningRaised NOTIFICATION-TYPE
	STATUS current
	DESCRIPTION
		"This trap is sent when an element gets into an warning state"
	::= { racktivityNotif 50 }

warningValueTooHighCleared NOTIFICATION-TYPE
	STATUS current
	DESCRIPTION
		"This trap is sent when an element goes below the specified warning threshold indicating the maximum value for this element"
	::= { racktivityNotif 51 }

warningValueTooLowCleared NOTIFICATION-TYPE
	STATUS current
	DESCRIPTION
		"This trap is sent when an element goes above the specified warning threshold indicating the minimum value for this element"
	::= { racktivityNotif 52 }

warningCleared NOTIFICATION-TYPE
	STATUS current
	DESCRIPTION
		"This trap is sent when an element recovers from an warning state"
	::= { racktivityNotif 53 }

infoValueTooHighRaised NOTIFICATION-TYPE
	STATUS current
	DESCRIPTION
		"This trap is sent when an element goes above a specified threshold indicating the maximum value for this element"
	::= { racktivityNotif 80 }

infoPortStateChanged NOTIFICATION-TYPE
	STATUS current
	DESCRIPTION
		"This trap is sent when a port changes state for any reason"
	::= { racktivityNotif 96 }

infoReset NOTIFICATION-TYPE
	STATUS current
	DESCRIPTION
		"This trap is sent when a module is reboot"
	::= { racktivityNotif 97 }

infoValueTooLowRaised NOTIFICATION-TYPE
	STATUS current
	DESCRIPTION
		"This trap is sent when an element goes below a specified threshold indicating the minimum value for this element"
	::= { racktivityNotif 81 }

infoRaised NOTIFICATION-TYPE
	STATUS current
	DESCRIPTION
		"This trap is sent when an element gets into a specific state"
	::= { racktivityNotif 82 }

infoValueTooHighCleared NOTIFICATION-TYPE
	STATUS current
	DESCRIPTION
		"This trap is sent when an element goes below a specified threshold indicating the maximum value for this element"
	::= { racktivityNotif 83 }

infoValueTooLowCleared NOTIFICATION-TYPE
	STATUS current
	DESCRIPTION
		"This trap is sent when an element goes above a specified threshold indicating the minimum value for this element"
	::= { racktivityNotif 84 }

infoCleared NOTIFICATION-TYPE
	STATUS current
	DESCRIPTION
		"This trap is sent when an element recovers from a specific state"
	::= { racktivityNotif 85 }

infoUpgrade NOTIFICATION-TYPE
	STATUS current
	DESCRIPTION
		"This trap is sent when upgrade or downgrade of firmware is completed"
	::= { racktivityNotif 98 }

warningMicroInterruption NOTIFICATION-TYPE
	STATUS current
	DESCRIPTION
		"This event is raised when a micro interruption is detected above a threshold time"
	::= { racktivityNotif 54 }

warningPhaseShift NOTIFICATION-TYPE
	STATUS current
	DESCRIPTION
		"This event is raised when a phase shift is detected above a threshold"
	::= { racktivityNotif 55 }

infoPortSchedule NOTIFICATION-TYPE
	STATUS current
	DESCRIPTION
		"This trap is sent when a port changes state because of a scheduling"
	::= { racktivityNotif 99 }

infoHeartbeat NOTIFICATION-TYPE
	STATUS current
	DESCRIPTION
		"This trap is sent when a heartbeat has occurred"
	::= { racktivityNotif 100 }

-- conformance statements
esRacktivityConformance      OBJECT IDENTIFIER ::= { esRACKTIVITYMIB 2 }
esRacktivityMIBGroups        OBJECT IDENTIFIER ::= { esRacktivityConformance 1 }
esRacktivityMIBCompliances   OBJECT IDENTIFIER ::= { esRacktivityConformance 2 }

esRacktivityConpliance MODULE-COMPLIANCE
	STATUS current
	DESCRIPTION
		"The compliance statements for a Racktivity device."
	MODULE
		MANDATORY-GROUPS { esRacktivityMIBGroup, esRacktivityNotificationGroup }
	::= { esRacktivityMIBCompliances 1 }

esRacktivityMIBGroup OBJECT-GROUP
	OBJECTS {
		mGeneralModuleStatus,
		mSpecificModuleStatus,
		mCurrentTime,
		mVoltage,
		mTemperature,
		mCurrentIP,
		mTotalCurrent,
		mTotalRealPower,
		mTotalActiveEnergy,
		mLineCurrent,
		mFuseCurrent,
		mCurrentSubNetMask,
		mCurrentDNSServer,
		mCurrentStdGateway,
		mUPSPresent,
		mUPSStatus,
		mUPSEstimatedRunTime,
		mUPSBatteryLevel,
		mHighCurrent,
		mUpsCommunicationStatus,
		mHighPower,
		mTotalHighCurrent,
		mTotalHighPower,
		mPositiveEnergy,
		mNegativeEnergy,
		mTotalPositiveEnergy,
		mTotalNegativeEnergy,
		mCloudStatus,
		mStatus,
		mModuleName,
		mFirmwareVersion,
		mHardwareVersion,
		mFirmwareID,
		mHardwareID,
		mRackName,
		mRackPosition,
		mIPAddress,
		mSubNetMask,
		mStdGateWay,
		mDnsServer,
		mMAC,
		mDHCPEnable,
		mNTPServer,
		mUseDefaultNTPServer,
		mUseNTP,
		mSNMPTrapRecvIP,
		mSNMPTrapRecvPort,
		mSNMPControl,
		mECSServer,
		mUseECSServer,
		mDisplayLock,
		mDisplayTimeOn,
		mMaxVoltageWarning,
		mMinVoltageWarning,
		mMinTemperatureWarning,
		mMaxTemperatureWarning,
		mGeneralEventEnable,
		mSNMPSysContact,
		mCurrentWarningEvent,
		mPowerWarningEvent,
		mTotalCurrentWarningEvent,
		mTotalPowerWarningEvent,
		mVoltageWarningEvent,
		mTemperatureWarningEvent,
		mDisplayBrightness,
		mECSServerPort,
		mExternalSensorLabel,
		mHttpsOnly,
		mTelnetSsl,
		mCookieTimeToLive,
		mLineCurrentWarningThreshold,
		mLineCurrentOffThreshold,
		mLineCurrentWarningEvent,
		mLineCurrentOffEvent,
		mFuseCurrentWarningThreshold,
		mFuseCurrentOffThreshold,
		mFuseCurrentWarningEvent,
		mFuseCurrentOffEvent,
		mDeviceID,
		mDeviceVersion,
		mSysName,
		mElectricalTopology,
		mFusePortTopology,
		mLineFuseTopology,
		mSSOIPAddress,
		mSSOLoginCredentials,
		mSSOGracefullShutdown,
		mUPSWarningLevel,
		mUPSOffLevel,
		mMaxHighCurrentWarning,
		mUpsMonitoringProtocol,
		mUpsEmergencyThreshold,
		mUpsRecoveryThreshold,
		mUpsEventFlags,
		mRecoveryPowerThreshold,
		mMinHighCurrentWarning,
		mMinHighPowerWarning,
		mMaxHighPowerWarning,
		mHeartbeatInterval,
		mMinTotalHighCurrentWarning,
		mMaxTotalHighCurrentWarning,
		mMinTotalHighPowerWarning,
		mMaxTotalHighPowerWarning,
		mCloudState,
		mSensorBias,
		mDaisyChainDeviceMode,
		mSNMPTrapUser,
		mUSMUser,
		mUSMAuthPassphrase,
		mUSMPrivPassphrase,
		mSNMPV2GetSetEnable,
		mSNMPV3GetSetEnable,
		mUSMAuthPassphraseLength,
		mUSMPrivPassphraseLength,
		mSNMPTrapEnable,
		mLDAPAttribute,
		mLDAPPath,
		mLDAPAdminGroupName,
		mLDAPRestrictedGroupName,
		mLDAPGuestGroupName,
		mLDAPEnable,
		mLDAPLoginWrapper,
		mLDAPServer,
		mLocalAuthEnable,
		pGeneralModuleStatus,
		pSpecificModuleStatus,
		pCurrentTime,
		pVoltage,
		pFrequency,
		pCurrent,
		pPower,
		pStatePortCur,
		pActiveEnergy,
		pApparentEnergy,
		pTemperature,
		pApparentPower,
		pPowerFactor,
		pTotalCurrent,
		pTotalRealPower,
		pTotalApparentPower,
		pTotalActiveEnergy,
		pTotalApparentEnergy,
		pTotalPowerFactor,
		pTimeOnline,
		pTotalHarmonicDistortion,
		pPhase,
		pBigCurrent,
		pBigPower,
		pBigApparentPower,
		pDetectedPhase,
		pModuleName,
		pFirmwareVersion,
		pHardwareVersion,
		pFirmwareID,
		pHardwareID,
		pPortName,
		pPortState,
		pCurrentPriorOff,
		pDelayOn,
		pMaxCurrentOff,
		pMaxCurrentWarning,
		pMaxPowerOff,
		pMaxPowerWarning,
		pMaxTotalCurrentOff,
		pMaxTotalCurrentWarning,
		pMaxTotalPowerOff,
		pMaxTotalPowerWarning,
		pMaxVoltageWarning,
		pMinVoltageWarning,
		pMinTemperatureWarning,
		pMaxTemperatureWarning,
		pPortStateEvent,
		pCurrentOffEvent,
		pCurrentWarningEvent,
		pPowerOffEvent,
		pPowerWarningEvent,
		pTotalCurrentOffEvent,
		pTotalCurrentWarningEvent,
		pTotalPowerOffEvent,
		pTotalPowerWarningEvent,
		pVoltageWarningEvent,
		pTemperatureWarningEvent,
		pMaxOverheatingOff,
		pOverheatingOffEvent,
		pPowerCycleTime,
		pExternalSensorLabel,
		pMaxOverheatingWarning,
		pOverheatingWarningEvent,
		pMicroIntTimeThreshold,
		pMicroIntEvent,
		pSoftFuseCurrentThreshold,
		pSoftFuseDelay,
		pSoftFuseEvent,
		pPhaseShiftEvent,
		pSchedulePortOnTime,
		pSchedulePortOffTime,
		pEnableSchedulePort,
		pBlockSetPortOff,
		pSchedulePortChangeEvent,
		pAgentIP,
		pAgentPort,
		pAgentCommunicationEventFlags,
		pAlwaysOn,
		pGenericTransducerParameters,
		pMaxBigCurrentWarning,
		pMaxBigPowerWarning,
		pGroupNumber,
		pPhaseLink,
		pCurrentSensorSelector,
		pMinBigCurrentWarning,
		aGeneralModuleStatus,
		aSpecificModuleStatus,
		aCurrentTime,
		aVoltage,
		aStatePortCur,
		aTemperature,
		aHumidity,
		aAirflow,
		aDewPoint,
		aPressure,
		aAnalogueInput,
		aWaterleak,
		aMotionDetected,
		aIOPort,
		aHighCurrent,
		aHighPower,
		aModuleName,
		aFirmwareVersion,
		aHardwareVersion,
		aFirmwareID,
		aHardwareID,
		aDisplayTimeOn,
		aMaxVoltageWarning,
		aMinVoltageWarning,
		aMinTemperatureWarning,
		aMaxTemperatureWarning,
		aMinHumidityWarning,
		aMaxHumidityWarning,
		aCurrentWarningEvent,
		aPowerWarningEvent,
		aVoltageWarningEvent,
		aTemperatureWarningEvent,
		aHumidityWarningEvent,
		aDewPointWarning,
		aDewPointWarningEvent,
		aDewPointViolationEvent,
		aPressureWarningEvent,
		aMinPressureWarning,
		aMaxPressureWarning,
		aDisplayBrightness,
		aMotionSensitivity,
		aExternalSensorLabel,
		aRelayLabel,
		aMinAnalogueInputWarning,
		aMaxAnalogueInputWarning,
		aWaterleakWarning,
		aMinAirflowWarning,
		aMaxAirflowWarning,
		aAnalogueInputWarningEvent,
		aWaterleakWarningEvent,
		aAirflowWarningEvent,
		aRelayAssertActionEvent,
		aRelayDeassertActionEvent,
		aMotionWarning,
		aMotionWarningEvent,
		aDeviceID,
		aDeviceVersion,
		aSysName,
		aMaxHighCurrentWarning,
		aMinHighCurrentWarning,
		aMinHighPowerWarning,
		aMaxHighPowerWarning,
		aIOPortWarningEvent,
		yGeneralModuleStatus,
		ySpecificModuleStatus,
		yCurrentTime,
		yCurrent,
		yStatePortCur,
		yAnalogueInput,
		yModuleName,
		yFirmwareVersion,
		yHardwareVersion,
		yFirmwareID,
		yHardwareID,
		uGeneralModuleStatus,
		uSpecificModuleStatus,
		uCurrentTime,
		uVoltage,
		uCurrent,
		uStatePortCur,
		uTemperature,
		uHumidity,
		uModuleName,
		uFirmwareVersion,
		uHardwareVersion,
		uFirmwareID,
		uHardwareID,
		uPortState,
		eGeneralModuleStatus,
		eSpecificModuleStatus,
		eCurrentTime,
		eVoltage,
		eFrequency,
		eCurrent,
		ePower,
		eActiveEnergy,
		eApparentEnergy,
		eTemperature,
		eApparentPower,
		ePowerFactor,
		eTotalCurrent,
		eTotalRealPower,
		eTotalApparentPower,
		eTotalActiveEnergy,
		eTotalApparentEnergy,
		eTotalPowerFactor,
		eTimeOnline,
		eTotalHarmonicDistortion,
		eModuleName,
		eFirmwareVersion,
		eHardwareVersion,
		eFirmwareID,
		eHardwareID,
		eMaxCurrentWarning,
		eMaxPowerWarning,
		eMaxTotalCurrentWarning,
		eMaxTotalPowerWarning,
		eMaxVoltageWarning,
		eMinVoltageWarning,
		eMinTemperatureWarning,
		eMaxTemperatureWarning,
		eCurrentWarningEvent,
		ePowerWarningEvent,
		eTotalCurrentWarningEvent,
		eTotalPowerWarningEvent,
		eVoltageWarningEvent,
		eTemperatureWarningEvent,
		eMicroIntTimeThreshold,
		eMicroIntEvent,
		qGeneralModuleStatus,
		qSpecificModuleStatus,
		qCurrentTime,
		qVoltage,
		qFrequency,
		qActiveEnergy,
		qApparentEnergy,
		qTemperature,
		qPowerFactor,
		qTimeOnline,
		qIOPort,
		qTotalHarmonicDistortion,
		qPhase,
		qBigCurrent,
		qBigPower,
		qBigApparentPower,
		qStatus,
		qModuleName,
		qFirmwareVersion,
		qHardwareVersion,
		qFirmwareID,
		qHardwareID,
		qPortState,
		qMaxVoltageWarning,
		qMinVoltageWarning,
		qMinTemperatureWarning,
		qMaxTemperatureWarning,
		qPortStateEvent,
		qCurrentWarningEvent,
		qPowerWarningEvent,
		qVoltageWarningEvent,
		qTemperatureWarningEvent,
		qMicroIntTimeThreshold,
		qMicroIntEvent,
		qDeviceID,
		qDeviceVersion,
		qMaxBigCurrentWarning,
		qMaxBigPowerWarning,
		qCurrentSensorSelector,
		qMinBigCurrentWarning,
		qkWhMode,
		dGeneralModuleStatus,
		dSpecificModuleStatus,
		dCurrentTime,
		dTemperature,
		dTimeOnline,
		dModuleName,
		dFirmwareVersion,
		dHardwareVersion,
		dFirmwareID,
		dHardwareID,
		dMinTemperatureWarning,
		dMaxTemperatureWarning,
		dDisplayAllDevices
	}
	STATUS current
	DESCRIPTION
		"All accessible objects in a Racktivity device"
	::= { esRacktivityMIBGroups 1 }

esRacktivityNotificationGroup	NOTIFICATION-GROUP
	NOTIFICATIONS
	{
		errorValueTooHighRaised,
		errorValueTooLowRaised,
		errorRaised,
		errorValueTooHighCleared,
		errorValueTooLowCleared,
		errorCleared,
		warningValueTooHighRaised,
		warningValueTooLowRaised,
		warningRaised,
		warningValueTooHighCleared,
		warningValueTooLowCleared,
		warningCleared,
		infoValueTooHighRaised,
		infoPortStateChanged,
		infoReset,
		infoValueTooLowRaised,
		infoRaised,
		infoValueTooHighCleared,
		infoValueTooLowCleared,
		infoCleared,
		infoUpgrade,
		warningMicroInterruption,
		warningPhaseShift,
		infoPortSchedule,
		infoHeartbeat
	}
	STATUS current
	DESCRIPTION
		"All notification that can be sent out by a Racktivity device"
	::= { esRacktivityMIBGroups 2 }

END -- end of module esRACKTIVITY.
