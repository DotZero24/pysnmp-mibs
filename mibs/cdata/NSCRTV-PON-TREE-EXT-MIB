--
-- NSCRTV-PON-TREE-EXT-MIB.my
-- MIB generated by MG-SOFT Visual MIB Builder Version 6.0  Build 88
-- Wednesday, September 05, 2018 at 15:05:38
--

	NSCRTV-PON-TREE-EXT-MIB DEFINITIONS ::= BEGIN

		IMPORTS
			IpAddress, Integer32, Unsigned32, OBJECT-TYPE, MODULE-IDENTITY,
			OBJECT-IDENTITY
				FROM SNMPv2-SMI
			TruthValue, RowStatus, MacAddress
				FROM SNMPv2-TC
			pon
				FROM VENDOR-COMMON-MIB;


		-- 1.3.6.1.4.1.34592.1.3.100
		nscrtvPonTreeExt MODULE-IDENTITY
			LAST-UPDATED "201706051636Z"		-- June 05, 2017 at 16:36 GMT
			ORGANIZATION
				"Organization."
			CONTACT-INFO
				"Contact-info."
			DESCRIPTION
				"Description."
			::= { pon 100 }

		-- Textual conventions
--
		NscrtvPonExtDeviceIndex ::= TEXTUAL-CONVENTION
			STATUS current
			DESCRIPTION
				"olt/onu Device Index
				Four byte,include:
				         Olt device-8bit OLT Card-8bit Pon port-8bit OnuNUM-8bit
				         Note:
				   ----
				   1. OLT device must not be 0.
				   2. Card here shall confirm the last byte definition of NscrtvPonExtCardIndex
				      to indicate the main-slot and sub-slot index.
				   3. Pon port must not be 0.
				   4. The useful ONU logical ID MUST never be set to 0, where NUM of 0 has
				      another meaning, to indicate that the ONU logical ID is meaningless,
				      or said to not applied.

				   Usage guide:
				   -----------
				   This TC could be used for OLT SNI, OLT PON port, OLT ONU ID
				   OLT device, trunk.
				   If the refered MIB object does not have clear definition,
				   refer to the following:
				   Applied Obj  - Descriptions of Index
				   ------------------------------------------------------------------
				   OLT Pon Port - OnuNum shall be set to 0,
				   OLT SNI    - Same as OLT Pon Port
				   OLT onu ID   - Set OnuNUM to corresponding ONU logical ID
				   OLT device   - Set card, pon port and OnuNUM to 0
				   Trunk    - Card to 0x3F, pon port to trunk ID, OnuNUM to 0
				            Olt device to corresponding ONU device
				        "
			SYNTAX Unsigned32

--     Textual conventions
--
		NscrtvPonExtCardIndex ::= TEXTUAL-CONVENTION
			STATUS current
			DESCRIPTION
				"Card Index
				For easy presenting the chassis view by NMS, bCardIndex shall be formatted
				in a following manner:
				Four bytes of INTEGER, from the most significant byte to the least significant bytes
				-----------------------------------------------------------------------------
				Reserved byte Reserved byte   Reserved byte Sub-slot 2-bit Main-slot 6-bit
				Notes:
				-----
				1. Reserved bytes shall be set to 0.
				2. The main-slot shall be started from 1, and shall be in a consecutive manner,
				   for all slots, including service slots, control slots, switch slots, power
				   slots,FAN slots, etc.For example, 1, 2, 3
				3. The sub-slot shall be started from 1, and shall be in a consecutive manner.
				   For example, 1, 2. If no sub-slot concept of a main-slot, set to 0.
				4. For fixed device, if no slot concept, NE shall set both main-slot and sub-slot
				   to 0, to indicate this is meaningless. For modulized device, they MUST not be
				   set to 0.This definition shall applied to both OLT and ONU.
				5. For trunk, since there is no slot concept, set main-slot to all-1 and sub-slot
				   to 0. This definition shall applied to both OLT and ONU.

				For example,
				0x00 00 00 0A, represents main-slot 10, no sub-slot
				0x00 00 00 42, represents main-slot 2, sub-slot 1
				0x00 00 00 3F, represents a trunk
				"
			SYNTAX Unsigned32

		NscrtvPonPortIndex ::= TEXTUAL-CONVENTION
			STATUS current
			DESCRIPTION
				"Port Index
				The device port number shall start from 1. Nunber 0 had specific meaning, stands
				for portIndex is meaningless, for the situation defined.
				"
			SYNTAX Unsigned32 (0..255)

		NscrtvPonExtEtherType ::= TEXTUAL-CONVENTION
			STATUS current
			DESCRIPTION
				"Description."
			SYNTAX INTEGER
				{
				ipv4(1),
				ipv6(2),
				pppoe(3)
				}

		NscrtvPonExtAdminStatus ::= TEXTUAL-CONVENTION
			STATUS current
			DESCRIPTION
				"Description."
			SYNTAX INTEGER
				{
				disable(0),
				enable(1)
				}

		NscrtvPonExtOnuOnlineState ::= TEXTUAL-CONVENTION
			STATUS current
			DESCRIPTION
				"Description."
			SYNTAX INTEGER
				{
				offline(0),
				online(1)
				}

		NscrtvPonExtVlanTagAction ::= TEXTUAL-CONVENTION
			STATUS current
			DESCRIPTION
				"Description."
			SYNTAX INTEGER
				{
				default(0),
				translate(1),
				translate-and-add(2),
				add-double(3),
				transparent(4)
				}

		NscrtvPonExtPerfStat ::= TEXTUAL-CONVENTION
			STATUS current
			DESCRIPTION
				"Description."
			SYNTAX INTEGER
				{
				disable(0),
				enable(1)
				}

		NscrtvPonExtAutoMode ::= TEXTUAL-CONVENTION
			STATUS current
			DESCRIPTION
				"Description."
			SYNTAX INTEGER
				{
				auto(0),
				manual(1)
				}

		NscrtvPonExtCurPerfStatClear ::= TEXTUAL-CONVENTION
			STATUS current
			DESCRIPTION
				"Description."
			SYNTAX INTEGER
				{
				no-clear(0),
				clear(1)
				}


				EponDeviceIndex ::= TEXTUAL-CONVENTION
			STATUS current
			DESCRIPTION
				""
			SYNTAX Unsigned32

		EponCardIndex ::= TEXTUAL-CONVENTION
			STATUS current
			DESCRIPTION
				""
			SYNTAX Unsigned32
--
-- Node definitions
--
		-- 1.3.6.1.4.1.34592.1.3.100.1
		systemObjects OBJECT IDENTIFIER ::= { nscrtvPonTreeExt 1 }


		-- 1.3.6.1.4.1.34592.1.3.100.1.1
		configManagementObjects OBJECT-IDENTITY
			STATUS current
			DESCRIPTION
				""
			::= { systemObjects 1 }


		-- 1.3.6.1.4.1.34592.1.3.100.1.1.1
		configOperation OBJECT-TYPE
			SYNTAX INTEGER
				{
				import(1),
				export(2),
				default(3)
				}
			MAX-ACCESS read-write
			STATUS current
			DESCRIPTION
				"
				import device configuration when set value to 1.
				export device configuration when set value to 2.
				default device configuration when set value to 3.
				"
			::= { configManagementObjects 1 }


		-- 1.3.6.1.4.1.34592.1.3.100.1.1.2
		configfile OBJECT-TYPE
			SYNTAX OCTET STRING
			MAX-ACCESS read-write
			STATUS current
			DESCRIPTION
				" configuration file name"
			::= { configManagementObjects 2 }


		-- 1.3.6.1.4.1.34592.1.3.100.1.1.3
		configStatus OBJECT-TYPE
			SYNTAX INTEGER
				{
				fail(0),
				idle(1),
				inProcess(2),
				success(3)
				}
			MAX-ACCESS read-only
			STATUS current
			DESCRIPTION
				"
				import device configuration status "
			::= { configManagementObjects 3 }


		-- 1.3.6.1.4.1.34592.1.3.100.1.2
		interfaceManagementObjects OBJECT-IDENTITY
			STATUS current
			DESCRIPTION
				""
			::= { systemObjects 2 }


		-- 1.3.6.1.4.1.34592.1.3.100.1.2.1
		inBandInterfaceTable OBJECT-TYPE
			SYNTAX SEQUENCE OF InBandInterfaceEntry
			MAX-ACCESS not-accessible
			STATUS current
			DESCRIPTION
				"Description."
			::= { interfaceManagementObjects 1 }


		-- 1.3.6.1.4.1.34592.1.3.100.1.2.1.1
		inBandInterfaceEntry OBJECT-TYPE
			SYNTAX InBandInterfaceEntry
			MAX-ACCESS not-accessible
			STATUS current
			DESCRIPTION
				"Description."
			INDEX { inBandInterfaceVlanIdIndex }
			::= { inBandInterfaceTable 1 }


		InBandInterfaceEntry ::=
			SEQUENCE {
				inBandInterfaceVlanIdIndex
					INTEGER,
				inBandInterfaceIP
					IpAddress,
				inBandInterfaceMask
					IpAddress,
				inBandInterfaceGateway
					IpAddress,
				inBandInterfaceLinkStatus
					INTEGER,
				inBandInterfaceEnable
					TruthValue,
				inBandInterfaceDesc
					OCTET STRING,
				inBandInterfaceRowStatus
					RowStatus
			 }

		-- 1.3.6.1.4.1.34592.1.3.100.1.2.1.1.1
		inBandInterfaceVlanIdIndex OBJECT-TYPE
			SYNTAX INTEGER
			MAX-ACCESS not-accessible
			STATUS current
			DESCRIPTION
				""
			::= { inBandInterfaceEntry 1 }


		-- 1.3.6.1.4.1.34592.1.3.100.1.2.1.1.2
		inBandInterfaceIP OBJECT-TYPE
			SYNTAX IpAddress
			MAX-ACCESS read-create
			STATUS current
			DESCRIPTION
				""
			::= { inBandInterfaceEntry 2 }


		-- 1.3.6.1.4.1.34592.1.3.100.1.2.1.1.3
		inBandInterfaceMask OBJECT-TYPE
			SYNTAX IpAddress
			MAX-ACCESS read-create
			STATUS current
			DESCRIPTION
				""
			::= { inBandInterfaceEntry 3 }


		-- 1.3.6.1.4.1.34592.1.3.100.1.2.1.1.4
		inBandInterfaceGateway OBJECT-TYPE
			SYNTAX IpAddress
			MAX-ACCESS read-create
			STATUS current
			DESCRIPTION
				""
			::= { inBandInterfaceEntry 4 }


		-- 1.3.6.1.4.1.34592.1.3.100.1.2.1.1.5
		inBandInterfaceLinkStatus OBJECT-TYPE
			SYNTAX INTEGER
				{
				up(1),
				down(2)
				}
			MAX-ACCESS read-only
			STATUS current
			DESCRIPTION
				" link status "
			::= { inBandInterfaceEntry 5 }


		-- 1.3.6.1.4.1.34592.1.3.100.1.2.1.1.6
		inBandInterfaceEnable OBJECT-TYPE
			SYNTAX TruthValue
			MAX-ACCESS read-create
			STATUS current
			DESCRIPTION
				"Description."
			::= { inBandInterfaceEntry 6 }


		-- 1.3.6.1.4.1.34592.1.3.100.1.2.1.1.7
		inBandInterfaceDesc OBJECT-TYPE
			SYNTAX OCTET STRING
			MAX-ACCESS read-create
			STATUS current
			DESCRIPTION
				" Description "
			::= { inBandInterfaceEntry 7 }


		-- 1.3.6.1.4.1.34592.1.3.100.1.2.1.1.8
		inBandInterfaceRowStatus OBJECT-TYPE
			SYNTAX RowStatus
			MAX-ACCESS read-create
			STATUS current
			DESCRIPTION
				"RowStatus."
			::= { inBandInterfaceEntry 8 }


		-- 1.3.6.1.4.1.34592.1.3.100.1.2.2
		outBandInterfaceTable OBJECT-TYPE
			SYNTAX SEQUENCE OF OutBandInterfaceEntry
			MAX-ACCESS not-accessible
			STATUS current
			DESCRIPTION
				"Description."
			::= { interfaceManagementObjects 2 }


		-- 1.3.6.1.4.1.34592.1.3.100.1.2.2.1
		outBandInterfaceEntry OBJECT-TYPE
			SYNTAX OutBandInterfaceEntry
			MAX-ACCESS not-accessible
			STATUS current
			DESCRIPTION
				"Description."
			INDEX { outBandInterfaceDeviceIndex }
			::= { outBandInterfaceTable 1 }


		OutBandInterfaceEntry ::=
			SEQUENCE {
				outBandInterfaceDeviceIndex
					NscrtvPonExtDeviceIndex,
				outBandInterfaceIP
					IpAddress,
				outBandInterfaceMask
					IpAddress,
				outBandInterfaceEnable
					TruthValue,
				outBandInterfaceDesc
					OCTET STRING
			 }

		-- 1.3.6.1.4.1.34592.1.3.100.1.2.2.1.1
		outBandInterfaceDeviceIndex OBJECT-TYPE
			SYNTAX NscrtvPonExtDeviceIndex
			MAX-ACCESS not-accessible
			STATUS current
			DESCRIPTION
				"Description."
			::= { outBandInterfaceEntry 1 }


		-- 1.3.6.1.4.1.34592.1.3.100.1.2.2.1.2
		outBandInterfaceIP OBJECT-TYPE
			SYNTAX IpAddress
			MAX-ACCESS read-write
			STATUS current
			DESCRIPTION
				"Description."
			::= { outBandInterfaceEntry 2 }


		-- 1.3.6.1.4.1.34592.1.3.100.1.2.2.1.3
		outBandInterfaceMask OBJECT-TYPE
			SYNTAX IpAddress
			MAX-ACCESS read-write
			STATUS current
			DESCRIPTION
				"Description."
			::= { outBandInterfaceEntry 3 }


		-- 1.3.6.1.4.1.34592.1.3.100.1.2.2.1.4
		outBandInterfaceEnable OBJECT-TYPE
			SYNTAX TruthValue
			MAX-ACCESS read-write
			STATUS current
			DESCRIPTION
				"Description."
			::= { outBandInterfaceEntry 4 }


		-- 1.3.6.1.4.1.34592.1.3.100.1.2.2.1.5
		outBandInterfaceDesc OBJECT-TYPE
			SYNTAX OCTET STRING
			MAX-ACCESS read-write
			STATUS current
			DESCRIPTION
				" Description "
			::= { outBandInterfaceEntry 5 }


		-- 1.3.6.1.4.1.34592.1.3.100.1.3
		syslogConfigObjects OBJECT IDENTIFIER ::= { systemObjects 3 }


		-- 1.3.6.1.4.1.34592.1.3.100.1.3.1
		syslogConfigOperLogEnable OBJECT-TYPE
			SYNTAX TruthValue
			MAX-ACCESS read-write
			STATUS current
			DESCRIPTION
				"Description."
			::= { syslogConfigObjects 1 }


		-- 1.3.6.1.4.1.34592.1.3.100.1.3.2
		syslogConfigAlarmLogEnable OBJECT-TYPE
			SYNTAX TruthValue
			MAX-ACCESS read-write
			STATUS current
			DESCRIPTION
				"Description."
			::= { syslogConfigObjects 2 }


		-- 1.3.6.1.4.1.34592.1.3.100.1.3.3
		syslogConfigTable OBJECT-TYPE
			SYNTAX SEQUENCE OF SyslogConfigEntry
			MAX-ACCESS not-accessible
			STATUS current
			DESCRIPTION
				"Description."
			::= { syslogConfigObjects 3 }


		-- 1.3.6.1.4.1.34592.1.3.100.1.3.3.1
		syslogConfigEntry OBJECT-TYPE
			SYNTAX SyslogConfigEntry
			MAX-ACCESS not-accessible
			STATUS current
			DESCRIPTION
				"Description."
			INDEX { syslogIndex }
			::= { syslogConfigTable 1 }


		SyslogConfigEntry ::=
			SEQUENCE {
				syslogIndex
					INTEGER,
				syslogServerIpaddress
					IpAddress,
				syslogConfigName
					OCTET STRING,
				syslogConfigActive
					TruthValue,
				syslogServerIpaddressRowStatus
					RowStatus
			 }

		-- 1.3.6.1.4.1.34592.1.3.100.1.3.3.1.1
		syslogIndex OBJECT-TYPE
			SYNTAX INTEGER
			MAX-ACCESS read-write
			STATUS current
			DESCRIPTION
				"Description."
			::= { syslogConfigEntry 1 }


		-- 1.3.6.1.4.1.34592.1.3.100.1.3.3.1.2
		syslogServerIpaddress OBJECT-TYPE
			SYNTAX IpAddress
			MAX-ACCESS read-write
			STATUS current
			DESCRIPTION
				"Description."
			::= { syslogConfigEntry 2 }


		-- 1.3.6.1.4.1.34592.1.3.100.1.3.3.1.3
		syslogConfigName OBJECT-TYPE
			SYNTAX OCTET STRING
			MAX-ACCESS read-write
			STATUS current
			DESCRIPTION
				"Description."
			::= { syslogConfigEntry 3 }


		-- 1.3.6.1.4.1.34592.1.3.100.1.3.3.1.4
		syslogConfigActive OBJECT-TYPE
			SYNTAX TruthValue
			MAX-ACCESS read-write
			STATUS current
			DESCRIPTION
				"Description."
			::= { syslogConfigEntry 4 }


		-- 1.3.6.1.4.1.34592.1.3.100.1.3.3.1.5
		syslogServerIpaddressRowStatus OBJECT-TYPE
			SYNTAX RowStatus
			MAX-ACCESS read-create
			STATUS current
			DESCRIPTION
				"Description."
			::= { syslogConfigEntry 5 }


		-- 1.3.6.1.4.1.34592.1.3.100.1.4
		alarmManagementObjects OBJECT IDENTIFIER ::= { systemObjects 4 }


		-- 1.3.6.1.4.1.34592.1.3.100.1.4.1
		alarmOutputDetailEnable OBJECT-TYPE
			SYNTAX TruthValue
			MAX-ACCESS read-write
			STATUS current
			DESCRIPTION
				"Description."
			::= { alarmManagementObjects 1 }


		-- 1.3.6.1.4.1.34592.1.3.100.1.4.2
		alarmOutputLimitEnable OBJECT-TYPE
			SYNTAX TruthValue
			MAX-ACCESS read-write
			STATUS current
			DESCRIPTION
				"Description."
			::= { alarmManagementObjects 2 }


		-- 1.3.6.1.4.1.34592.1.3.100.1.4.3
		alarmOutputLimit OBJECT-TYPE
			SYNTAX Integer32
			MAX-ACCESS read-write
			STATUS current
			DESCRIPTION
				"max alarm output counts period."
			::= { alarmManagementObjects 3 }


		-- 1.3.6.1.4.1.34592.1.3.100.1.4.4
		alarmJitterProofInterval OBJECT-TYPE
			SYNTAX Integer32
			MAX-ACCESS read-write
			STATUS current
			DESCRIPTION
				"time interval"
			::= { alarmManagementObjects 4 }


		-- 1.3.6.1.4.1.34592.1.3.100.1.4.5
		alarmJitterProof OBJECT-TYPE
			SYNTAX TruthValue
			MAX-ACCESS read-write
			STATUS current
			DESCRIPTION
				"enable or disable proof"
			::= { alarmManagementObjects 5 }


		-- 1.3.6.1.4.1.34592.1.3.100.1.4.6
		alarmIdConfigTable OBJECT-TYPE
			SYNTAX SEQUENCE OF AlarmIdConfigEntry
			MAX-ACCESS not-accessible
			STATUS current
			DESCRIPTION
				"Description."
			::= { alarmManagementObjects 6 }


		-- 1.3.6.1.4.1.34592.1.3.100.1.4.6.1
		alarmIdConfigEntry OBJECT-TYPE
			SYNTAX AlarmIdConfigEntry
			MAX-ACCESS not-accessible
			STATUS current
			DESCRIPTION
				"Description."
			INDEX { alarmId }
			::= { alarmIdConfigTable 1 }


		AlarmIdConfigEntry ::=
			SEQUENCE {
				alarmId
					Unsigned32,
				alarmIdLevel
					Integer32,
				alarmIdOuputEnable
					TruthValue
			 }

		-- 1.3.6.1.4.1.34592.1.3.100.1.4.6.1.1
		alarmId OBJECT-TYPE
			SYNTAX Unsigned32
			MAX-ACCESS read-write
			STATUS current
			DESCRIPTION
				"Description."
			::= { alarmIdConfigEntry 1 }


		-- 1.3.6.1.4.1.34592.1.3.100.1.4.6.1.2
		alarmIdLevel OBJECT-TYPE
			SYNTAX Integer32
			MAX-ACCESS read-write
			STATUS current
			DESCRIPTION
				"Description."
			::= { alarmIdConfigEntry 2 }


		-- 1.3.6.1.4.1.34592.1.3.100.1.4.6.1.3
		alarmIdOuputEnable OBJECT-TYPE
			SYNTAX TruthValue
			MAX-ACCESS read-write
			STATUS current
			DESCRIPTION
				"Description."
			::= { alarmIdConfigEntry 3 }


		-- 1.3.6.1.4.1.34592.1.3.100.1.5
		eventManagementObjects OBJECT IDENTIFIER ::= { systemObjects 5 }


		-- 1.3.6.1.4.1.34592.1.3.100.1.5.1
		eventOutputDetailEnable OBJECT-TYPE
			SYNTAX TruthValue
			MAX-ACCESS read-write
			STATUS current
			DESCRIPTION
				"Description."
			::= { eventManagementObjects 1 }


		-- 1.3.6.1.4.1.34592.1.3.100.1.5.2
		eventConfigTable OBJECT-TYPE
			SYNTAX SEQUENCE OF EventConfigEntry
			MAX-ACCESS not-accessible
			STATUS current
			DESCRIPTION
				"Description."
			::= { eventManagementObjects 2 }


		-- 1.3.6.1.4.1.34592.1.3.100.1.5.2.1
		eventConfigEntry OBJECT-TYPE
			SYNTAX EventConfigEntry
			MAX-ACCESS not-accessible
			STATUS current
			DESCRIPTION
				"Description."
			INDEX { eventId }
			::= { eventConfigTable 1 }


		EventConfigEntry ::=
			SEQUENCE {
				eventId
					Integer32,
				eventIdLevel
					Integer32,
				eventIdOutPutEnable
					TruthValue
			 }

		-- 1.3.6.1.4.1.34592.1.3.100.1.5.2.1.1
		eventId OBJECT-TYPE
			SYNTAX Integer32
			MAX-ACCESS read-write
			STATUS current
			DESCRIPTION
				"Description."
			::= { eventConfigEntry 1 }


		-- 1.3.6.1.4.1.34592.1.3.100.1.5.2.1.2
		eventIdLevel OBJECT-TYPE
			SYNTAX Integer32
			MAX-ACCESS read-write
			STATUS current
			DESCRIPTION
				"Description."
			::= { eventConfigEntry 2 }


		-- 1.3.6.1.4.1.34592.1.3.100.1.5.2.1.3
		eventIdOutPutEnable OBJECT-TYPE
			SYNTAX TruthValue
			MAX-ACCESS read-write
			STATUS current
			DESCRIPTION
				"Description."
			::= { eventConfigEntry 3 }


		-- 1.3.6.1.4.1.34592.1.3.100.1.8
		systemGlobalExtObjects OBJECT IDENTIFIER ::= { systemObjects 8 }


		-- 1.3.6.1.4.1.34592.1.3.100.1.8.1
		cpuUsage OBJECT-TYPE
			SYNTAX Integer32
			MAX-ACCESS read-only
			STATUS current
			DESCRIPTION
				"Description."
			::= { systemGlobalExtObjects 1 }


		-- 1.3.6.1.4.1.34592.1.3.100.1.8.2
		memTotalSize OBJECT-TYPE
			SYNTAX Integer32
			MAX-ACCESS read-only
			STATUS current
			DESCRIPTION
				"Description.(unit:MByte)"
			::= { systemGlobalExtObjects 2 }


		-- 1.3.6.1.4.1.34592.1.3.100.1.8.3
		memFreeSize OBJECT-TYPE
			SYNTAX Integer32
			MAX-ACCESS read-only
			STATUS current
			DESCRIPTION
				"Description.(unit:MByte)"
			::= { systemGlobalExtObjects 3 }


		-- 1.3.6.1.4.1.34592.1.3.100.1.8.4
		flashTotalSize OBJECT-TYPE
			SYNTAX Integer32
			MAX-ACCESS read-only
			STATUS current
			DESCRIPTION
				"Description.(unit:Byte)"
			::= { systemGlobalExtObjects 4 }


		-- 1.3.6.1.4.1.34592.1.3.100.1.8.5
		flashAvailableSize OBJECT-TYPE
			SYNTAX Integer32
			MAX-ACCESS read-only
			STATUS current
			DESCRIPTION
				"Description.(unit:Byte)"
			::= { systemGlobalExtObjects 5 }


		-- 1.3.6.1.4.1.34592.1.3.100.1.8.6
		temperature OBJECT-TYPE
			SYNTAX Integer32
			MAX-ACCESS read-only
			STATUS current
			DESCRIPTION
				"Description."
			::= { systemGlobalExtObjects 6 }


		-- 1.3.6.1.4.1.34592.1.3.100.1.8.7
		temperatureThreshold OBJECT-TYPE
			SYNTAX Integer32
			MAX-ACCESS read-write
			STATUS current
			DESCRIPTION
				"Description."
			::= { systemGlobalExtObjects 7 }



		-- 1.3.6.1.4.1.34592.1.3.100.2
		sniObjects OBJECT IDENTIFIER ::= { nscrtvPonTreeExt 2 }


		-- 1.3.6.1.4.1.34592.1.3.100.2.1
		sniAttributeExtTable OBJECT-TYPE
			SYNTAX SEQUENCE OF SniAttributeExtEntry
			MAX-ACCESS not-accessible
			STATUS current
			DESCRIPTION
				"Description."
			::= { sniObjects 1 }


		-- 1.3.6.1.4.1.34592.1.3.100.2.1.1
		sniAttributeExtEntry OBJECT-TYPE
			SYNTAX SniAttributeExtEntry
			MAX-ACCESS not-accessible
			STATUS current
			DESCRIPTION
				"Description."
			INDEX { sniAttributeExtDeviceIndex, sniAttributeExtCardIndex, sniAttributeExtPortIndex }
			::= { sniAttributeExtTable 1 }


		SniAttributeExtEntry ::=
			SEQUENCE {
				sniAttributeExtDeviceIndex
					NscrtvPonExtDeviceIndex,
				sniAttributeExtCardIndex
					NscrtvPonExtCardIndex,
				sniAttributeExtPortIndex
					NscrtvPonPortIndex,
				sniFlowControlEnable
					TruthValue,
				sniMaxTransmissionUnit
					Unsigned32,
				sniMaxFrameSize
					Unsigned32,
				sniMacLearnEnable
					TruthValue
			 }

		-- 1.3.6.1.4.1.34592.1.3.100.2.1.1.1
		sniAttributeExtDeviceIndex OBJECT-TYPE
			SYNTAX NscrtvPonExtDeviceIndex
			MAX-ACCESS not-accessible
			STATUS current
			DESCRIPTION
				"Description."
			::= { sniAttributeExtEntry 1 }


		-- 1.3.6.1.4.1.34592.1.3.100.2.1.1.2
		sniAttributeExtCardIndex OBJECT-TYPE
			SYNTAX NscrtvPonExtCardIndex
			MAX-ACCESS not-accessible
			STATUS current
			DESCRIPTION
				"Description."
			::= { sniAttributeExtEntry 2 }


		-- 1.3.6.1.4.1.34592.1.3.100.2.1.1.3
		sniAttributeExtPortIndex OBJECT-TYPE
			SYNTAX NscrtvPonPortIndex
			MAX-ACCESS not-accessible
			STATUS current
			DESCRIPTION
				"Description."
			::= { sniAttributeExtEntry 3 }


		-- 1.3.6.1.4.1.34592.1.3.100.2.1.1.4
		sniFlowControlEnable OBJECT-TYPE
			SYNTAX TruthValue
			MAX-ACCESS read-write
			STATUS current
			DESCRIPTION
				"Description."
			::= { sniAttributeExtEntry 4 }


		-- 1.3.6.1.4.1.34592.1.3.100.2.1.1.5
		sniMaxTransmissionUnit OBJECT-TYPE
			SYNTAX Unsigned32
			MAX-ACCESS read-write
			STATUS current
			DESCRIPTION
				"Description."
			::= { sniAttributeExtEntry 5 }


		-- 1.3.6.1.4.1.34592.1.3.100.2.1.1.6
		sniMaxFrameSize OBJECT-TYPE
			SYNTAX Unsigned32
			MAX-ACCESS read-write
			STATUS current
			DESCRIPTION
				"Description."
			::= { sniAttributeExtEntry 6 }


		-- 1.3.6.1.4.1.34592.1.3.100.2.1.1.7
		sniMacLearnEnable OBJECT-TYPE
			SYNTAX TruthValue
			MAX-ACCESS read-write
			STATUS current
			DESCRIPTION
				"Description."
			::= { sniAttributeExtEntry 7 }


		-- 1.3.6.1.4.1.34592.1.3.100.2.2
		sniPortOpticalTransmissionPropertyTable OBJECT-TYPE
			SYNTAX SEQUENCE OF SniPortOpticalTransmissionPropertyEntry
			MAX-ACCESS not-accessible
			STATUS current
			DESCRIPTION
				"Description."
			::= { sniObjects 2 }


		-- 1.3.6.1.4.1.34592.1.3.100.2.2.1
		sniPortOpticalTransmissionPropertyEntry OBJECT-TYPE
			SYNTAX SniPortOpticalTransmissionPropertyEntry
			MAX-ACCESS not-accessible
			STATUS current
			DESCRIPTION
				"Description."
			INDEX { sniOpDeviceIndex, sniOpCardIndex, sniOpPortIndex }
			::= { sniPortOpticalTransmissionPropertyTable 1 }


		SniPortOpticalTransmissionPropertyEntry ::=
			SEQUENCE {
				sniOpDeviceIndex
					NscrtvPonExtDeviceIndex,
				sniOpCardIndex
					NscrtvPonExtCardIndex,
				sniOpPortIndex
					NscrtvPonPortIndex,
				sniOpTemperature
					Integer32,
				sniOpVcc
					Unsigned32,
				sniOpBias
					Unsigned32,
				sniOpTxPower
					Integer32,
				sniOpRxPower
					Integer32
			 }

		-- 1.3.6.1.4.1.34592.1.3.100.2.2.1.1
		sniOpDeviceIndex OBJECT-TYPE
			SYNTAX NscrtvPonExtDeviceIndex
			MAX-ACCESS not-accessible
			STATUS current
			DESCRIPTION
				"Description."
			::= { sniPortOpticalTransmissionPropertyEntry 1 }


		-- 1.3.6.1.4.1.34592.1.3.100.2.2.1.2
		sniOpCardIndex OBJECT-TYPE
			SYNTAX NscrtvPonExtCardIndex
			MAX-ACCESS not-accessible
			STATUS current
			DESCRIPTION
				"Description."
			::= { sniPortOpticalTransmissionPropertyEntry 2 }


		-- 1.3.6.1.4.1.34592.1.3.100.2.2.1.3
		sniOpPortIndex OBJECT-TYPE
			SYNTAX NscrtvPonPortIndex
			MAX-ACCESS not-accessible
			STATUS current
			DESCRIPTION
				"Description."
			::= { sniPortOpticalTransmissionPropertyEntry 3 }


		-- 1.3.6.1.4.1.34592.1.3.100.2.2.1.4
		sniOpTemperature OBJECT-TYPE
			SYNTAX Integer32
			UNITS "Centi-degree centigrade"
			MAX-ACCESS read-only
			STATUS current
			DESCRIPTION
				"Description."
			::= { sniPortOpticalTransmissionPropertyEntry 4 }


		-- 1.3.6.1.4.1.34592.1.3.100.2.2.1.5
		sniOpVcc OBJECT-TYPE
			SYNTAX Unsigned32
			UNITS "centi-mV"
			MAX-ACCESS read-only
			STATUS current
			DESCRIPTION
				"Description."
			::= { sniPortOpticalTransmissionPropertyEntry 5 }


		-- 1.3.6.1.4.1.34592.1.3.100.2.2.1.6
		sniOpBias OBJECT-TYPE
			SYNTAX Unsigned32
			UNITS "centi-mA"
			MAX-ACCESS read-only
			STATUS current
			DESCRIPTION
				"Description."
			::= { sniPortOpticalTransmissionPropertyEntry 6 }


		-- 1.3.6.1.4.1.34592.1.3.100.2.2.1.7
		sniOpTxPower OBJECT-TYPE
			SYNTAX Integer32
			UNITS "centi-dBm"
			MAX-ACCESS read-only
			STATUS current
			DESCRIPTION
				"Description."
			::= { sniPortOpticalTransmissionPropertyEntry 7 }


		-- 1.3.6.1.4.1.34592.1.3.100.2.2.1.8
		sniOpRxPower OBJECT-TYPE
			SYNTAX Integer32
			UNITS "centi-dBm"
			MAX-ACCESS read-only
			STATUS current
			DESCRIPTION
				"Description."
			::= { sniPortOpticalTransmissionPropertyEntry 8 }


		-- 1.3.6.1.4.1.34592.1.3.100.2.3
		sniPortRateLimitTable OBJECT-TYPE
			SYNTAX SEQUENCE OF SniPortRateLimitEntry
			MAX-ACCESS not-accessible
			STATUS current
			DESCRIPTION
				"Description."
			::= { sniObjects 3 }


		-- 1.3.6.1.4.1.34592.1.3.100.2.3.1
		sniPortRateLimitEntry OBJECT-TYPE
			SYNTAX SniPortRateLimitEntry
			MAX-ACCESS not-accessible
			STATUS current
			DESCRIPTION
				"Description."
			INDEX { sniPortRateLimitDeviceIndex, sniPortRateLimitCardIndex, sniPortRateLimitPortIndex }
			::= { sniPortRateLimitTable 1 }


		SniPortRateLimitEntry ::=
			SEQUENCE {
				sniPortRateLimitDeviceIndex
					NscrtvPonExtDeviceIndex,
				sniPortRateLimitCardIndex
					NscrtvPonExtCardIndex,
				sniPortRateLimitPortIndex
					NscrtvPonPortIndex,
				sniPortInRate
					Unsigned32,
				sniPortOutRate
					Unsigned32,
				sniPortInRateLimitEnable
					TruthValue,
				sniPortOutRateLimitEnable
					TruthValue
			 }

		-- 1.3.6.1.4.1.34592.1.3.100.2.3.1.1
		sniPortRateLimitDeviceIndex OBJECT-TYPE
			SYNTAX NscrtvPonExtDeviceIndex
			MAX-ACCESS not-accessible
			STATUS current
			DESCRIPTION
				"Description."
			::= { sniPortRateLimitEntry 1 }


		-- 1.3.6.1.4.1.34592.1.3.100.2.3.1.2
		sniPortRateLimitCardIndex OBJECT-TYPE
			SYNTAX NscrtvPonExtCardIndex
			MAX-ACCESS not-accessible
			STATUS current
			DESCRIPTION
				"Description."
			::= { sniPortRateLimitEntry 2 }


		-- 1.3.6.1.4.1.34592.1.3.100.2.3.1.3
		sniPortRateLimitPortIndex OBJECT-TYPE
			SYNTAX NscrtvPonPortIndex
			MAX-ACCESS not-accessible
			STATUS current
			DESCRIPTION
				"Description."
			::= { sniPortRateLimitEntry 3 }


		-- 1.3.6.1.4.1.34592.1.3.100.2.3.1.4
		sniPortInRate OBJECT-TYPE
			SYNTAX Unsigned32
			UNITS "kbps"
			MAX-ACCESS read-write
			STATUS current
			DESCRIPTION
				"Description."
			::= { sniPortRateLimitEntry 4 }


		-- 1.3.6.1.4.1.34592.1.3.100.2.3.1.5
		sniPortOutRate OBJECT-TYPE
			SYNTAX Unsigned32
			UNITS "kbps"
			MAX-ACCESS read-write
			STATUS current
			DESCRIPTION
				"Description."
			::= { sniPortRateLimitEntry 5 }


		-- 1.3.6.1.4.1.34592.1.3.100.2.3.1.6
		sniPortInRateLimitEnable OBJECT-TYPE
			SYNTAX TruthValue
			MAX-ACCESS read-write
			STATUS current
			DESCRIPTION
				"Description."
			::= { sniPortRateLimitEntry 6 }


		-- 1.3.6.1.4.1.34592.1.3.100.2.3.1.7
		sniPortOutRateLimitEnable OBJECT-TYPE
			SYNTAX TruthValue
			MAX-ACCESS read-write
			STATUS current
			DESCRIPTION
				"Description."
			::= { sniPortRateLimitEntry 7 }


		-- 1.3.6.1.4.1.34592.1.3.100.3
		ponPortObjects OBJECT IDENTIFIER ::= { nscrtvPonTreeExt 3 }


		-- 1.3.6.1.4.1.34592.1.3.100.3.1
		ponPortInfoExtTable OBJECT-TYPE
			SYNTAX SEQUENCE OF PonPortInfoExtEntry
			MAX-ACCESS not-accessible
			STATUS current
			DESCRIPTION
				"Description."
			::= { ponPortObjects 1 }


		-- 1.3.6.1.4.1.34592.1.3.100.3.1.1
		ponPortInfoExtEntry OBJECT-TYPE
			SYNTAX PonPortInfoExtEntry
			MAX-ACCESS not-accessible
			STATUS current
			DESCRIPTION
				"Description."
			INDEX { ponInfoExtDeviceIndex, ponInfoExtCardIndex, ponInfoExtPortIndex }
			::= { ponPortInfoExtTable 1 }


		PonPortInfoExtEntry ::=
			SEQUENCE {
				ponInfoExtDeviceIndex
					NscrtvPonExtDeviceIndex,
				ponInfoExtCardIndex
					NscrtvPonExtCardIndex,
				ponInfoExtPortIndex
					NscrtvPonPortIndex,
				ponFlowControlEnable
					TruthValue,
				ponMaxTransmissionUnit
					Unsigned32,
				ponMaxFrameSize
					Unsigned32,
				ponMacLearnEnable
					TruthValue
			 }

		-- 1.3.6.1.4.1.34592.1.3.100.3.1.1.1
		ponInfoExtDeviceIndex OBJECT-TYPE
			SYNTAX NscrtvPonExtDeviceIndex
			MAX-ACCESS not-accessible
			STATUS current
			DESCRIPTION
				"Description."
			::= { ponPortInfoExtEntry 1 }


		-- 1.3.6.1.4.1.34592.1.3.100.3.1.1.2
		ponInfoExtCardIndex OBJECT-TYPE
			SYNTAX NscrtvPonExtCardIndex
			MAX-ACCESS not-accessible
			STATUS current
			DESCRIPTION
				"Description."
			::= { ponPortInfoExtEntry 2 }


		-- 1.3.6.1.4.1.34592.1.3.100.3.1.1.3
		ponInfoExtPortIndex OBJECT-TYPE
			SYNTAX NscrtvPonPortIndex
			MAX-ACCESS not-accessible
			STATUS current
			DESCRIPTION
				"Description."
			::= { ponPortInfoExtEntry 3 }


		-- 1.3.6.1.4.1.34592.1.3.100.3.1.1.4
		ponFlowControlEnable OBJECT-TYPE
			SYNTAX TruthValue
			MAX-ACCESS read-write
			STATUS current
			DESCRIPTION
				"Description."
			::= { ponPortInfoExtEntry 4 }


		-- 1.3.6.1.4.1.34592.1.3.100.3.1.1.5
		ponMaxTransmissionUnit OBJECT-TYPE
			SYNTAX Unsigned32
			MAX-ACCESS read-write
			STATUS current
			DESCRIPTION
				"Description."
			::= { ponPortInfoExtEntry 5 }


		-- 1.3.6.1.4.1.34592.1.3.100.3.1.1.6
		ponMaxFrameSize OBJECT-TYPE
			SYNTAX Unsigned32
			MAX-ACCESS read-write
			STATUS current
			DESCRIPTION
				"Description."
			::= { ponPortInfoExtEntry 6 }


		-- 1.3.6.1.4.1.34592.1.3.100.3.1.1.7
		ponMacLearnEnable OBJECT-TYPE
			SYNTAX TruthValue
			MAX-ACCESS read-write
			STATUS current
			DESCRIPTION
				"Description."
			::= { ponPortInfoExtEntry 7 }


		-- 1.3.6.1.4.1.34592.1.3.100.3.2
		ponPortRateLimitTable OBJECT-TYPE
			SYNTAX SEQUENCE OF PonPortRateLimitEntry
			MAX-ACCESS not-accessible
			STATUS current
			DESCRIPTION
				"Description."
			::= { ponPortObjects 2 }


		-- 1.3.6.1.4.1.34592.1.3.100.3.2.1
		ponPortRateLimitEntry OBJECT-TYPE
			SYNTAX PonPortRateLimitEntry
			MAX-ACCESS not-accessible
			STATUS current
			DESCRIPTION
				"Description."
			INDEX { ponPortRateLimitDeviceIndex, ponPortRateLimitCardIndex, ponPortRateLimitPortIndex }
			::= { ponPortRateLimitTable 1 }


		PonPortRateLimitEntry ::=
			SEQUENCE {
				ponPortRateLimitDeviceIndex
					NscrtvPonExtDeviceIndex,
				ponPortRateLimitCardIndex
					NscrtvPonExtCardIndex,
				ponPortRateLimitPortIndex
					NscrtvPonPortIndex,
				ponPortInRate
					Unsigned32,
				ponPortOutRate
					Unsigned32,
				ponPortInRateLimitEnable
					TruthValue,
				ponPortOutRateLimitEnable
					TruthValue
			 }

		-- 1.3.6.1.4.1.34592.1.3.100.3.2.1.1
		ponPortRateLimitDeviceIndex OBJECT-TYPE
			SYNTAX NscrtvPonExtDeviceIndex
			MAX-ACCESS not-accessible
			STATUS current
			DESCRIPTION
				"Description."
			::= { ponPortRateLimitEntry 1 }


		-- 1.3.6.1.4.1.34592.1.3.100.3.2.1.2
		ponPortRateLimitCardIndex OBJECT-TYPE
			SYNTAX NscrtvPonExtCardIndex
			MAX-ACCESS not-accessible
			STATUS current
			DESCRIPTION
				"Description."
			::= { ponPortRateLimitEntry 2 }


		-- 1.3.6.1.4.1.34592.1.3.100.3.2.1.3
		ponPortRateLimitPortIndex OBJECT-TYPE
			SYNTAX NscrtvPonPortIndex
			MAX-ACCESS not-accessible
			STATUS current
			DESCRIPTION
				"Description."
			::= { ponPortRateLimitEntry 3 }


		-- 1.3.6.1.4.1.34592.1.3.100.3.2.1.4
		ponPortInRate OBJECT-TYPE
			SYNTAX Unsigned32
			UNITS "kbps"
			MAX-ACCESS read-write
			STATUS current
			DESCRIPTION
				"Description."
			::= { ponPortRateLimitEntry 4 }


		-- 1.3.6.1.4.1.34592.1.3.100.3.2.1.5
		ponPortOutRate OBJECT-TYPE
			SYNTAX Unsigned32
			UNITS "kbps"
			MAX-ACCESS read-write
			STATUS current
			DESCRIPTION
				"Description."
			::= { ponPortRateLimitEntry 5 }


		-- 1.3.6.1.4.1.34592.1.3.100.3.2.1.6
		ponPortInRateLimitEnable OBJECT-TYPE
			SYNTAX TruthValue
			MAX-ACCESS read-write
			STATUS current
			DESCRIPTION
				"Description."
			::= { ponPortRateLimitEntry 6 }


		-- 1.3.6.1.4.1.34592.1.3.100.3.2.1.7
		ponPortOutRateLimitEnable OBJECT-TYPE
			SYNTAX TruthValue
			MAX-ACCESS read-write
			STATUS current
			DESCRIPTION
				"Description."
			::= { ponPortRateLimitEntry 7 }


		-- 1.3.6.1.4.1.34592.1.3.100.4
		vlanManagementObjects OBJECT IDENTIFIER ::= { nscrtvPonTreeExt 4 }


		-- 1.3.6.1.4.1.34592.1.3.100.4.1
		macVlanTable OBJECT-TYPE
			SYNTAX SEQUENCE OF MacVlanEntry
			MAX-ACCESS not-accessible
			STATUS current
			DESCRIPTION
				"Description."
			::= { vlanManagementObjects 1 }


		-- 1.3.6.1.4.1.34592.1.3.100.4.1.1
		macVlanEntry OBJECT-TYPE
			SYNTAX MacVlanEntry
			MAX-ACCESS not-accessible
			STATUS current
			DESCRIPTION
				"Description."
			INDEX { macVlanMacAddrIndex }
			::= { macVlanTable 1 }


		MacVlanEntry ::=
			SEQUENCE {
				macVlanMacAddrIndex
					MacAddress,
				macVlanVid
					Unsigned32,
				macVlanPriority
					Unsigned32,
				macVlanRowStatus
					RowStatus
			 }

		-- 1.3.6.1.4.1.34592.1.3.100.4.1.1.1
		macVlanMacAddrIndex OBJECT-TYPE
			SYNTAX MacAddress
			MAX-ACCESS not-accessible
			STATUS current
			DESCRIPTION
				"Description."
			::= { macVlanEntry 1 }


		-- 1.3.6.1.4.1.34592.1.3.100.4.1.1.2
		macVlanVid OBJECT-TYPE
			SYNTAX Unsigned32 (0..4095)
			MAX-ACCESS read-create
			STATUS current
			DESCRIPTION
				"Description."
			::= { macVlanEntry 2 }


		-- 1.3.6.1.4.1.34592.1.3.100.4.1.1.3
		macVlanPriority OBJECT-TYPE
			SYNTAX Unsigned32 (0..7)
			MAX-ACCESS read-create
			STATUS current
			DESCRIPTION
				"Description."
			::= { macVlanEntry 3 }


		-- 1.3.6.1.4.1.34592.1.3.100.4.1.1.4
		macVlanRowStatus OBJECT-TYPE
			SYNTAX RowStatus
			MAX-ACCESS read-create
			STATUS current
			DESCRIPTION
				"Description."
			::= { macVlanEntry 4 }


		-- 1.3.6.1.4.1.34592.1.3.100.4.2
		ipSubnetVlanTable OBJECT-TYPE
			SYNTAX SEQUENCE OF IpSubnetVlanEntry
			MAX-ACCESS not-accessible
			STATUS current
			DESCRIPTION
				"Description."
			::= { vlanManagementObjects 2 }


		-- 1.3.6.1.4.1.34592.1.3.100.4.2.1
		ipSubnetVlanEntry OBJECT-TYPE
			SYNTAX IpSubnetVlanEntry
			MAX-ACCESS not-accessible
			STATUS current
			DESCRIPTION
				"Description."
			INDEX { ipSubnetVlanIpAddressIndex, ipSubnetVlanNetMaskIndex }
			::= { ipSubnetVlanTable 1 }


		IpSubnetVlanEntry ::=
			SEQUENCE {
				ipSubnetVlanIpAddressIndex
					IpAddress,
				ipSubnetVlanNetMaskIndex
					IpAddress,
				ipSubnetVlanVid
					Unsigned32,
				ipSubnetVlanPriority
					Unsigned32,
				ipSubnetVlanRowStatus
					RowStatus
			 }

		-- 1.3.6.1.4.1.34592.1.3.100.4.2.1.1
		ipSubnetVlanIpAddressIndex OBJECT-TYPE
			SYNTAX IpAddress
			MAX-ACCESS not-accessible
			STATUS current
			DESCRIPTION
				"Description."
			::= { ipSubnetVlanEntry 1 }


		-- 1.3.6.1.4.1.34592.1.3.100.4.2.1.2
		ipSubnetVlanNetMaskIndex OBJECT-TYPE
			SYNTAX IpAddress
			MAX-ACCESS not-accessible
			STATUS current
			DESCRIPTION
				"Description."
			::= { ipSubnetVlanEntry 2 }


		-- 1.3.6.1.4.1.34592.1.3.100.4.2.1.3
		ipSubnetVlanVid OBJECT-TYPE
			SYNTAX Unsigned32 (0..4095)
			MAX-ACCESS read-create
			STATUS current
			DESCRIPTION
				"Description."
			::= { ipSubnetVlanEntry 3 }


		-- 1.3.6.1.4.1.34592.1.3.100.4.2.1.4
		ipSubnetVlanPriority OBJECT-TYPE
			SYNTAX Unsigned32 (0..7)
			MAX-ACCESS read-create
			STATUS current
			DESCRIPTION
				"Description."
			::= { ipSubnetVlanEntry 4 }


		-- 1.3.6.1.4.1.34592.1.3.100.4.2.1.5
		ipSubnetVlanRowStatus OBJECT-TYPE
			SYNTAX RowStatus
			MAX-ACCESS read-create
			STATUS current
			DESCRIPTION
				"Description."
			::= { ipSubnetVlanEntry 5 }


		-- 1.3.6.1.4.1.34592.1.3.100.4.3
		protocolVlanManagement OBJECT IDENTIFIER ::= { vlanManagementObjects 3 }


		-- 1.3.6.1.4.1.34592.1.3.100.4.3.1
		protocolVlanProfileTable OBJECT-TYPE
			SYNTAX SEQUENCE OF ProtocolVlanProfileEntry
			MAX-ACCESS not-accessible
			STATUS current
			DESCRIPTION
				"Description."
			::= { protocolVlanManagement 1 }


		-- 1.3.6.1.4.1.34592.1.3.100.4.3.1.1
		protocolVlanProfileEntry OBJECT-TYPE
			SYNTAX ProtocolVlanProfileEntry
			MAX-ACCESS not-accessible
			STATUS current
			DESCRIPTION
				"Description."
			INDEX { protocolVlanProfileIndex }
			::= { protocolVlanProfileTable 1 }


		ProtocolVlanProfileEntry ::=
			SEQUENCE {
				protocolVlanProfileIndex
					Unsigned32,
				protocolVlanProfileEtherType
					OCTET STRING,
				protocolVlanProfileFrameType
					INTEGER,
				protocolVlanProfileRowStatus
					RowStatus
			 }

		-- 1.3.6.1.4.1.34592.1.3.100.4.3.1.1.1
		protocolVlanProfileIndex OBJECT-TYPE
			SYNTAX Unsigned32 (1..16)
			MAX-ACCESS not-accessible
			STATUS current
			DESCRIPTION
				"Description."
			::= { protocolVlanProfileEntry 1 }


		-- 1.3.6.1.4.1.34592.1.3.100.4.3.1.1.2
		protocolVlanProfileEtherType OBJECT-TYPE
			SYNTAX OCTET STRING
			MAX-ACCESS read-create
			STATUS current
			DESCRIPTION
				"Ether type (0x0600-0xffff)."
			::= { protocolVlanProfileEntry 2 }


		-- 1.3.6.1.4.1.34592.1.3.100.4.3.1.1.3
		protocolVlanProfileFrameType OBJECT-TYPE
			SYNTAX INTEGER
				{
				ethernetII(1),
				raw(2),
				llc(3),
				snap(4)
				}
			MAX-ACCESS read-create
			STATUS current
			DESCRIPTION
				"Description."
			::= { protocolVlanProfileEntry 3 }


		-- 1.3.6.1.4.1.34592.1.3.100.4.3.1.1.4
		protocolVlanProfileRowStatus OBJECT-TYPE
			SYNTAX RowStatus
			MAX-ACCESS read-create
			STATUS current
			DESCRIPTION
				"Description."
			::= { protocolVlanProfileEntry 4 }


		-- 1.3.6.1.4.1.34592.1.3.100.4.3.2
		portProtocolVlanTable OBJECT-TYPE
			SYNTAX SEQUENCE OF PortProtocolVlanEntry
			MAX-ACCESS not-accessible
			STATUS current
			DESCRIPTION
				"Description."
			::= { protocolVlanManagement 2 }


		-- 1.3.6.1.4.1.34592.1.3.100.4.3.2.1
		portProtocolVlanEntry OBJECT-TYPE
			SYNTAX PortProtocolVlanEntry
			MAX-ACCESS not-accessible
			STATUS current
			DESCRIPTION
				"Description."
			INDEX { portProtocolVlanDeviceIndex, portProtocolVlanCardIndex, portProtocolVlanPortIndex, portProtocolVlanProfileIndex }
			::= { portProtocolVlanTable 1 }


		PortProtocolVlanEntry ::=
			SEQUENCE {
				portProtocolVlanDeviceIndex
					NscrtvPonExtDeviceIndex,
				portProtocolVlanCardIndex
					NscrtvPonExtCardIndex,
				portProtocolVlanPortIndex
					NscrtvPonPortIndex,
				portProtocolVlanProfileIndex
					Unsigned32,
				portProtocolVlanVid
					Unsigned32,
				portProtocolVlanRowStatus
					RowStatus
			 }

		-- 1.3.6.1.4.1.34592.1.3.100.4.3.2.1.1
		portProtocolVlanDeviceIndex OBJECT-TYPE
			SYNTAX NscrtvPonExtDeviceIndex
			MAX-ACCESS not-accessible
			STATUS current
			DESCRIPTION
				"Description."
			::= { portProtocolVlanEntry 1 }


		-- 1.3.6.1.4.1.34592.1.3.100.4.3.2.1.2
		portProtocolVlanCardIndex OBJECT-TYPE
			SYNTAX NscrtvPonExtCardIndex
			MAX-ACCESS not-accessible
			STATUS current
			DESCRIPTION
				"Description."
			::= { portProtocolVlanEntry 2 }


		-- 1.3.6.1.4.1.34592.1.3.100.4.3.2.1.3
		portProtocolVlanPortIndex OBJECT-TYPE
			SYNTAX NscrtvPonPortIndex
			MAX-ACCESS not-accessible
			STATUS current
			DESCRIPTION
				"Description."
			::= { portProtocolVlanEntry 3 }


		-- 1.3.6.1.4.1.34592.1.3.100.4.3.2.1.4
		portProtocolVlanProfileIndex OBJECT-TYPE
			SYNTAX Unsigned32 (1..16)
			MAX-ACCESS not-accessible
			STATUS current
			DESCRIPTION
				"Description."
			::= { portProtocolVlanEntry 4 }


		-- 1.3.6.1.4.1.34592.1.3.100.4.3.2.1.5
		portProtocolVlanVid OBJECT-TYPE
			SYNTAX Unsigned32 (0..4095)
			MAX-ACCESS read-create
			STATUS current
			DESCRIPTION
				"Description."
			::= { portProtocolVlanEntry 5 }


		-- 1.3.6.1.4.1.34592.1.3.100.4.3.2.1.6
		portProtocolVlanRowStatus OBJECT-TYPE
			SYNTAX RowStatus
			MAX-ACCESS read-create
			STATUS current
			DESCRIPTION
				"Description."
			::= { portProtocolVlanEntry 6 }

		-- 1.3.6.1.4.1.34592.1.3.100.4.4
		portVlanHybridTable OBJECT-TYPE
			SYNTAX SEQUENCE OF PortVlanHybridEntry
			MAX-ACCESS not-accessible
			STATUS current
			DESCRIPTION
				"Description."
			::= { vlanManagementObjects 4 }


		-- 1.3.6.1.4.1.34592.1.3.100.4.4.1
		portVlanHybridEntry OBJECT-TYPE
			SYNTAX PortVlanHybridEntry
			MAX-ACCESS not-accessible
			STATUS current
			DESCRIPTION
				"Description."
			INDEX { hybridDeviceIndex, hybridCardIndex, hybridPortIndex }
			::= { portVlanHybridTable 1 }


		PortVlanHybridEntry ::=
			SEQUENCE {
				hybridDeviceIndex
					EponDeviceIndex,
				hybridCardIndex
					EponCardIndex,
				hybridPortIndex
					INTEGER,
				hybridVidTaggedList
					OCTET STRING,
				hybridVidUntaggedList
					OCTET STRING,
				portVlanHybridRowStatus
					RowStatus
			 }

		-- 1.3.6.1.4.1.34592.1.3.100.4.4.1.1
		hybridDeviceIndex OBJECT-TYPE
			SYNTAX EponDeviceIndex
			MAX-ACCESS not-accessible
			STATUS current
			DESCRIPTION
				"Description."
			::= { portVlanHybridEntry 1 }


		-- 1.3.6.1.4.1.34592.1.3.100.4.4.1.2
		hybridCardIndex OBJECT-TYPE
			SYNTAX EponCardIndex
			MAX-ACCESS not-accessible
			STATUS current
			DESCRIPTION
				"Description."
			::= { portVlanHybridEntry 2 }


		-- 1.3.6.1.4.1.34592.1.3.100.4.4.1.3
		hybridPortIndex OBJECT-TYPE
			SYNTAX INTEGER
			MAX-ACCESS not-accessible
			STATUS current
			DESCRIPTION
				"Description."
			::= { portVlanHybridEntry 3 }


		-- 1.3.6.1.4.1.34592.1.3.100.4.4.1.4
		hybridVidTaggedList OBJECT-TYPE
			SYNTAX OCTET STRING (SIZE (512))
			MAX-ACCESS read-create
			STATUS current
			DESCRIPTION
				"Description."
			::= { portVlanHybridEntry 4 }


		-- 1.3.6.1.4.1.34592.1.3.100.4.4.1.5
		hybridVidUntaggedList OBJECT-TYPE
			SYNTAX OCTET STRING (SIZE (512))
			MAX-ACCESS read-create
			STATUS current
			DESCRIPTION
				"Description."
			::= { portVlanHybridEntry 5 }


		-- 1.3.6.1.4.1.34592.1.3.100.4.4.1.6
		portVlanHybridRowStatus OBJECT-TYPE
			SYNTAX RowStatus
			MAX-ACCESS read-create
			STATUS current
			DESCRIPTION
				"Description."
			::= { portVlanHybridEntry 6 }

		-- 1.3.6.1.4.1.34592.1.3.100.5
		dhcpManagementObjects OBJECT IDENTIFIER ::= { nscrtvPonTreeExt 5 }


		-- 1.3.6.1.4.1.34592.1.3.100.5.1
		dhcpSnoopingGlobalSetTable OBJECT-TYPE
			SYNTAX SEQUENCE OF DhcpSnoopingGlobalSetEntry
			MAX-ACCESS not-accessible
			STATUS current
			DESCRIPTION
				"Description."
			::= { dhcpManagementObjects 1 }


		-- 1.3.6.1.4.1.34592.1.3.100.5.1.1
		dhcpSnoopingGlobalSetEntry OBJECT-TYPE
			SYNTAX DhcpSnoopingGlobalSetEntry
			MAX-ACCESS not-accessible
			STATUS current
			DESCRIPTION
				"Description."
			INDEX { dhcpSnGlobalSetDeviceIndex }
			::= { dhcpSnoopingGlobalSetTable 1 }


		DhcpSnoopingGlobalSetEntry ::=
			SEQUENCE {
				dhcpSnGlobalSetDeviceIndex
					NscrtvPonExtDeviceIndex,
				dhcpSnGlobalSetEnable
					TruthValue,
				dhcpSnGlobalSetChaddrCheckEnable
					TruthValue,
				dhcpSnGlobalSetVlanList
					OCTET STRING,
				dhcpSnGlobalSetOption82Enable
					TruthValue,
				dhcpSnGlobalSetOption82Policy
					INTEGER,
				dhcpSnGlobalSetOption82Format
					INTEGER
			 }

		-- 1.3.6.1.4.1.34592.1.3.100.5.1.1.1
		dhcpSnGlobalSetDeviceIndex OBJECT-TYPE
			SYNTAX NscrtvPonExtDeviceIndex
			MAX-ACCESS not-accessible
			STATUS current
			DESCRIPTION
				"Description."
			::= { dhcpSnoopingGlobalSetEntry 1 }


		-- 1.3.6.1.4.1.34592.1.3.100.5.1.1.2
		dhcpSnGlobalSetEnable OBJECT-TYPE
			SYNTAX TruthValue
			MAX-ACCESS read-write
			STATUS current
			DESCRIPTION
				"Description."
			::= { dhcpSnoopingGlobalSetEntry 2 }


		-- 1.3.6.1.4.1.34592.1.3.100.5.1.1.3
		dhcpSnGlobalSetChaddrCheckEnable OBJECT-TYPE
			SYNTAX TruthValue
			MAX-ACCESS read-write
			STATUS current
			DESCRIPTION
				"Description."
			::= { dhcpSnoopingGlobalSetEntry 3 }


		-- 1.3.6.1.4.1.34592.1.3.100.5.1.1.4
		dhcpSnGlobalSetVlanList OBJECT-TYPE
			SYNTAX OCTET STRING (SIZE (512))
			MAX-ACCESS read-write
			STATUS current
			DESCRIPTION
				""
			::= { dhcpSnoopingGlobalSetEntry 4 }


		-- 1.3.6.1.4.1.34592.1.3.100.5.1.1.5
		dhcpSnGlobalSetOption82Enable OBJECT-TYPE
			SYNTAX TruthValue
			MAX-ACCESS read-write
			STATUS current
			DESCRIPTION
				"Description."
			::= { dhcpSnoopingGlobalSetEntry 5 }


		-- 1.3.6.1.4.1.34592.1.3.100.5.1.1.6
		dhcpSnGlobalSetOption82Policy OBJECT-TYPE
			SYNTAX INTEGER
				{
				keep(1),
				drop(2),
				replace(3)
				}
			MAX-ACCESS read-write
			STATUS current
			DESCRIPTION
				"Description."
			::= { dhcpSnoopingGlobalSetEntry 6 }


		-- 1.3.6.1.4.1.34592.1.3.100.5.1.1.7
		dhcpSnGlobalSetOption82Format OBJECT-TYPE
			SYNTAX INTEGER
				{
				type1(1),
				type2(2),
				type3(3),
				type4(4),
				type5(5)
				}
			MAX-ACCESS read-write
			STATUS current
			DESCRIPTION
				"type1                - UNI+ONU MAC
				type2                - UNI+OLT MAC
				type3                - ONU+ONU MAC
				type4                - ONU+OLT MAC
				type5                - PON+OLT MAC
				  "
			::= { dhcpSnoopingGlobalSetEntry 7 }


		-- 1.3.6.1.4.1.34592.1.3.100.5.2
		dhcpSnoopingPortSetTable OBJECT-TYPE
			SYNTAX SEQUENCE OF DhcpSnoopingPortSetEntry
			MAX-ACCESS not-accessible
			STATUS current
			DESCRIPTION
				"Description."
			::= { dhcpManagementObjects 2 }


		-- 1.3.6.1.4.1.34592.1.3.100.5.2.1
		dhcpSnoopingPortSetEntry OBJECT-TYPE
			SYNTAX DhcpSnoopingPortSetEntry
			MAX-ACCESS not-accessible
			STATUS current
			DESCRIPTION
				"Description."
			INDEX { dhcpSnPortSetDeviceIndex, dhcpSnPortSetCardIndex, dhcpSnPortSetPortIndex }
			::= { dhcpSnoopingPortSetTable 1 }


		DhcpSnoopingPortSetEntry ::=
			SEQUENCE {
				dhcpSnPortSetDeviceIndex
					NscrtvPonExtDeviceIndex,
				dhcpSnPortSetCardIndex
					NscrtvPonExtCardIndex,
				dhcpSnPortSetPortIndex
					NscrtvPonPortIndex,
				dhcpSnPortSetTrust
					TruthValue,
				dhcpSnPortSetRequestPktLimitRate
					Unsigned32
			 }

		-- 1.3.6.1.4.1.34592.1.3.100.5.2.1.1
		dhcpSnPortSetDeviceIndex OBJECT-TYPE
			SYNTAX NscrtvPonExtDeviceIndex
			MAX-ACCESS not-accessible
			STATUS current
			DESCRIPTION
				"Description."
			::= { dhcpSnoopingPortSetEntry 1 }


		-- 1.3.6.1.4.1.34592.1.3.100.5.2.1.2
		dhcpSnPortSetCardIndex OBJECT-TYPE
			SYNTAX NscrtvPonExtCardIndex
			MAX-ACCESS not-accessible
			STATUS current
			DESCRIPTION
				"Description."
			::= { dhcpSnoopingPortSetEntry 2 }


		-- 1.3.6.1.4.1.34592.1.3.100.5.2.1.3
		dhcpSnPortSetPortIndex OBJECT-TYPE
			SYNTAX NscrtvPonPortIndex
			MAX-ACCESS not-accessible
			STATUS current
			DESCRIPTION
				"Description."
			::= { dhcpSnoopingPortSetEntry 3 }


		-- 1.3.6.1.4.1.34592.1.3.100.5.2.1.4
		dhcpSnPortSetTrust OBJECT-TYPE
			SYNTAX TruthValue
			MAX-ACCESS read-write
			STATUS current
			DESCRIPTION
				"Description."
			::= { dhcpSnoopingPortSetEntry 4 }


		-- 1.3.6.1.4.1.34592.1.3.100.5.2.1.5
		dhcpSnPortSetRequestPktLimitRate OBJECT-TYPE
			SYNTAX Unsigned32 (1..2048)
			UNITS "pps"
			MAX-ACCESS read-write
			STATUS current
			DESCRIPTION
				"Description."
			::= { dhcpSnoopingPortSetEntry 5 }


		-- 1.3.6.1.4.1.34592.1.3.100.5.3
		dhcpSnoopingBindManagementTable OBJECT-TYPE
			SYNTAX SEQUENCE OF DhcpSnoopingBindManagementEntry
			MAX-ACCESS not-accessible
			STATUS current
			DESCRIPTION
				"Description."
			::= { dhcpManagementObjects 3 }


		-- 1.3.6.1.4.1.34592.1.3.100.5.3.1
		dhcpSnoopingBindManagementEntry OBJECT-TYPE
			SYNTAX DhcpSnoopingBindManagementEntry
			MAX-ACCESS not-accessible
			STATUS current
			DESCRIPTION
				"Description."
			INDEX { dhcpSnBindManagemenDeviceIndex }
			::= { dhcpSnoopingBindManagementTable 1 }


		DhcpSnoopingBindManagementEntry ::=
			SEQUENCE {
				dhcpSnBindManagemenDeviceIndex
					NscrtvPonExtDeviceIndex,
				dhcpSnBindEntryDeleteTime
					Unsigned32,
				dhcpSnBindTableWriteDelay
					Unsigned32,
				dhcpSnBindTableWriteToFlashAction
					TruthValue,
				dhcpSnBindTableSaveToTftpIpAddress
					IpAddress,
				dhcpSnBindTableSaveToTftpAction
					TruthValue,
				dhcpSnBindTableClearByType
					INTEGER,
				dhcpSnBindTableClearByVlan
					Unsigned32
			 }

		-- 1.3.6.1.4.1.34592.1.3.100.5.3.1.1
		dhcpSnBindManagemenDeviceIndex OBJECT-TYPE
			SYNTAX NscrtvPonExtDeviceIndex
			MAX-ACCESS not-accessible
			STATUS current
			DESCRIPTION
				"Description."
			::= { dhcpSnoopingBindManagementEntry 1 }


		-- 1.3.6.1.4.1.34592.1.3.100.5.3.1.2
		dhcpSnBindEntryDeleteTime OBJECT-TYPE
			SYNTAX Unsigned32 (1..86400)
			UNITS "s"
			MAX-ACCESS read-write
			STATUS current
			DESCRIPTION
				"Description."
			::= { dhcpSnoopingBindManagementEntry 2 }


		-- 1.3.6.1.4.1.34592.1.3.100.5.3.1.3
		dhcpSnBindTableWriteDelay OBJECT-TYPE
			SYNTAX Unsigned32 (240..86400)
			UNITS "s"
			MAX-ACCESS read-write
			STATUS current
			DESCRIPTION
				"Description."
			::= { dhcpSnoopingBindManagementEntry 3 }

		-- 1.3.6.1.4.1.34592.1.3.100.5.3.1.4
		dhcpSnBindTableWriteToFlashAction OBJECT-TYPE
			SYNTAX TruthValue
			MAX-ACCESS read-write
			STATUS current
			DESCRIPTION
				"Description."
			::= { dhcpSnoopingBindManagementEntry 4 }


		-- 1.3.6.1.4.1.34592.1.3.100.5.3.1.5
		dhcpSnBindTableSaveToTftpIpAddress OBJECT-TYPE
			SYNTAX IpAddress
			MAX-ACCESS read-write
			STATUS current
			DESCRIPTION
				"Description."
			::= { dhcpSnoopingBindManagementEntry 5 }


		-- 1.3.6.1.4.1.34592.1.3.100.5.3.1.6
		dhcpSnBindTableSaveToTftpAction OBJECT-TYPE
			SYNTAX TruthValue
			MAX-ACCESS read-write
			STATUS current
			DESCRIPTION
				"Description."
			::= { dhcpSnoopingBindManagementEntry 6 }


		-- 1.3.6.1.4.1.34592.1.3.100.5.3.1.7
		dhcpSnBindTableClearByType OBJECT-TYPE
			SYNTAX INTEGER
				{
				all(1),
				dynamic(2),
				static(3)
				}
			MAX-ACCESS read-write
			STATUS current
			DESCRIPTION
				"Description."
			::= { dhcpSnoopingBindManagementEntry 7 }


		-- 1.3.6.1.4.1.34592.1.3.100.5.3.1.8
		dhcpSnBindTableClearByVlan OBJECT-TYPE
			SYNTAX Unsigned32 (0..4095)
			MAX-ACCESS read-write
			STATUS current
			DESCRIPTION
				"Description."
			::= { dhcpSnoopingBindManagementEntry 8 }


		-- 1.3.6.1.4.1.34592.1.3.100.5.4
		dhcpSnoopingBindTable OBJECT-TYPE
			SYNTAX SEQUENCE OF DhcpSnoopingBindEntry
			MAX-ACCESS not-accessible
			STATUS current
			DESCRIPTION
				"Description."
			::= { dhcpManagementObjects 4 }


		-- 1.3.6.1.4.1.34592.1.3.100.5.4.1
		dhcpSnoopingBindEntry OBJECT-TYPE
			SYNTAX DhcpSnoopingBindEntry
			MAX-ACCESS not-accessible
			STATUS current
			DESCRIPTION
				"Description."
			INDEX { dhcpSnBindIpAddrIndex, dhcpSnBindVlanIndex }
			::= { dhcpSnoopingBindTable 1 }


		DhcpSnoopingBindEntry ::=
			SEQUENCE {
				dhcpSnBindIpAddrIndex
					IpAddress,
				dhcpSnBindVlanIndex
					Unsigned32,
				dhcpSnBindMacAddress
					MacAddress,
				dhcpSnBindPortId
					NscrtvPonExtDeviceIndex,
				dhcpSnBindType
					INTEGER,
				dhcpSnBindRowStatus
					RowStatus
			 }

		-- 1.3.6.1.4.1.34592.1.3.100.5.4.1.1
		dhcpSnBindIpAddrIndex OBJECT-TYPE
			SYNTAX IpAddress
			MAX-ACCESS not-accessible
			STATUS current
			DESCRIPTION
				"Description."
			::= { dhcpSnoopingBindEntry 1 }


		-- 1.3.6.1.4.1.34592.1.3.100.5.4.1.2
		dhcpSnBindVlanIndex OBJECT-TYPE
			SYNTAX Unsigned32 (0..4095)
			MAX-ACCESS not-accessible
			STATUS current
			DESCRIPTION
				"Description."
			::= { dhcpSnoopingBindEntry 2 }


		-- 1.3.6.1.4.1.34592.1.3.100.5.4.1.3
		dhcpSnBindMacAddress OBJECT-TYPE
			SYNTAX MacAddress
			MAX-ACCESS read-create
			STATUS current
			DESCRIPTION
				"Description."
			::= { dhcpSnoopingBindEntry 3 }


		-- 1.3.6.1.4.1.34592.1.3.100.5.4.1.4
		dhcpSnBindPortId OBJECT-TYPE
			SYNTAX NscrtvPonExtDeviceIndex
			MAX-ACCESS read-create
			STATUS current
			DESCRIPTION
				"Description."
			::= { dhcpSnoopingBindEntry 4 }


		-- 1.3.6.1.4.1.34592.1.3.100.5.4.1.5
		dhcpSnBindType OBJECT-TYPE
			SYNTAX INTEGER
				{
				dynamic(1),
				static(2)
				}
			MAX-ACCESS read-create
			STATUS current
			DESCRIPTION
				"Description."
			::= { dhcpSnoopingBindEntry 5 }


		-- 1.3.6.1.4.1.34592.1.3.100.5.4.1.6
		dhcpSnBindRowStatus OBJECT-TYPE
			SYNTAX RowStatus
			MAX-ACCESS read-create
			STATUS current
			DESCRIPTION
				"Description."
			::= { dhcpSnoopingBindEntry 6 }


		-- 1.3.6.1.4.1.34592.1.3.100.5.5
		dhcpRelayTable OBJECT-TYPE
			SYNTAX SEQUENCE OF DhcpRelayEntry
			MAX-ACCESS not-accessible
			STATUS current
			DESCRIPTION
				"Description."
			::= { dhcpManagementObjects 5 }


		-- 1.3.6.1.4.1.34592.1.3.100.5.5.1
		dhcpRelayEntry OBJECT-TYPE
			SYNTAX DhcpRelayEntry
			MAX-ACCESS not-accessible
			STATUS current
			DESCRIPTION
				"Description."
			INDEX { dhcpRelayDeviceIndex }
			::= { dhcpRelayTable 1 }


		DhcpRelayEntry ::=
			SEQUENCE {
				dhcpRelayDeviceIndex
					NscrtvPonExtDeviceIndex,
				dhcpRelayEnable
					TruthValue
			 }

		-- 1.3.6.1.4.1.34592.1.3.100.5.5.1.1
		dhcpRelayDeviceIndex OBJECT-TYPE
			SYNTAX NscrtvPonExtDeviceIndex
			MAX-ACCESS not-accessible
			STATUS current
			DESCRIPTION
				"Description."
			::= { dhcpRelayEntry 1 }


		-- 1.3.6.1.4.1.34592.1.3.100.5.5.1.2
		dhcpRelayEnable OBJECT-TYPE
			SYNTAX TruthValue
			MAX-ACCESS read-write
			STATUS current
			DESCRIPTION
				"Description."
			::= { dhcpRelayEntry 2 }


		-- 1.3.6.1.4.1.34592.1.3.100.5.6
		dhcpRelayServerConfigTable OBJECT-TYPE
			SYNTAX SEQUENCE OF DhcpRelayServerConfigEntry
			MAX-ACCESS not-accessible
			STATUS current
			DESCRIPTION
				"Description."
			::= { dhcpManagementObjects 6 }


		-- 1.3.6.1.4.1.34592.1.3.100.5.6.1
		dhcpRelayServerConfigEntry OBJECT-TYPE
			SYNTAX DhcpRelayServerConfigEntry
			MAX-ACCESS not-accessible
			STATUS current
			DESCRIPTION
				"Description."
			INDEX { dhcpRelayServerConfigDeviceIndex, dhcpRelayVlanIfIndex }
			::= { dhcpRelayServerConfigTable 1 }


		DhcpRelayServerConfigEntry ::=
			SEQUENCE {
				dhcpRelayServerConfigDeviceIndex
					NscrtvPonExtDeviceIndex,
				dhcpRelayVlanIfIndex
					Unsigned32,
				dhcpRelayVlanIfIpAddress
					IpAddress,
				dhcpRelayVlanIfNetmask
					IpAddress,
				dhcpRelayServerIpAddress
					IpAddress,
				dhcpRelayServerConfigRowStatus
					RowStatus
			 }

		-- 1.3.6.1.4.1.34592.1.3.100.5.6.1.1
		dhcpRelayServerConfigDeviceIndex OBJECT-TYPE
			SYNTAX NscrtvPonExtDeviceIndex
			MAX-ACCESS not-accessible
			STATUS current
			DESCRIPTION
				"Description."
			::= { dhcpRelayServerConfigEntry 1 }


		-- 1.3.6.1.4.1.34592.1.3.100.5.6.1.2
		dhcpRelayVlanIfIndex OBJECT-TYPE
			SYNTAX Unsigned32 (0..4095)
			MAX-ACCESS read-write
			STATUS current
			DESCRIPTION
				"Description."
			::= { dhcpRelayServerConfigEntry 2 }


		-- 1.3.6.1.4.1.34592.1.3.100.5.6.1.3
		dhcpRelayVlanIfIpAddress OBJECT-TYPE
			SYNTAX IpAddress
			MAX-ACCESS read-only
			STATUS current
			DESCRIPTION
				"Description."
			::= { dhcpRelayServerConfigEntry 3 }


		-- 1.3.6.1.4.1.34592.1.3.100.5.6.1.4
		dhcpRelayVlanIfNetmask OBJECT-TYPE
			SYNTAX IpAddress
			MAX-ACCESS read-only
			STATUS current
			DESCRIPTION
				"Description."
			::= { dhcpRelayServerConfigEntry 4 }


		-- 1.3.6.1.4.1.34592.1.3.100.5.6.1.5
		dhcpRelayServerIpAddress OBJECT-TYPE
			SYNTAX IpAddress
			MAX-ACCESS read-create
			STATUS current
			DESCRIPTION
				"Description."
			::= { dhcpRelayServerConfigEntry 5 }


		-- 1.3.6.1.4.1.34592.1.3.100.5.6.1.6
		dhcpRelayServerConfigRowStatus OBJECT-TYPE
			SYNTAX RowStatus
			MAX-ACCESS read-create
			STATUS current
			DESCRIPTION
				"Description."
			::= { dhcpRelayServerConfigEntry 6 }


		-- 1.3.6.1.4.1.34592.1.3.100.6
		arpManagementObjects OBJECT IDENTIFIER ::= { nscrtvPonTreeExt 6 }


		-- 1.3.6.1.4.1.34592.1.3.100.6.1
		arpConfigTable OBJECT-TYPE
			SYNTAX SEQUENCE OF ArpConfigEntry
			MAX-ACCESS not-accessible
			STATUS current
			DESCRIPTION
				"Description."
			::= { arpManagementObjects 1 }


		-- 1.3.6.1.4.1.34592.1.3.100.6.1.1
		arpConfigEntry OBJECT-TYPE
			SYNTAX ArpConfigEntry
			MAX-ACCESS not-accessible
			STATUS current
			DESCRIPTION
				"Description."
			INDEX { arpConfigDeviceIndex }
			::= { arpConfigTable 1 }


		ArpConfigEntry ::=
			SEQUENCE {
				arpConfigDeviceIndex
					NscrtvPonExtDeviceIndex,
				arpConfigMaxLearnNum
					Unsigned32,
				arpConfigCurrentLearnNum
					Unsigned32,
				arpConfigQuickUpdateEnable
					TruthValue,
				arpConfigReplyFastEnable
					TruthValue,
				arpConfigDetectEnable
					TruthValue,
				arpConfigAgeTime
					Unsigned32,
				arpConfigGratuitousArpSendTime
					Integer32,
				arpConfigGratuitousArpLearnEnable
					TruthValue,
				arpConfigArpClear
					INTEGER
			 }

		-- 1.3.6.1.4.1.34592.1.3.100.6.1.1.1
		arpConfigDeviceIndex OBJECT-TYPE
			SYNTAX NscrtvPonExtDeviceIndex
			MAX-ACCESS not-accessible
			STATUS current
			DESCRIPTION
				"Description."
			::= { arpConfigEntry 1 }


		-- 1.3.6.1.4.1.34592.1.3.100.6.1.1.2
		arpConfigMaxLearnNum OBJECT-TYPE
			SYNTAX Unsigned32
			MAX-ACCESS read-only
			STATUS current
			DESCRIPTION
				"Description."
			::= { arpConfigEntry 2 }


		-- 1.3.6.1.4.1.34592.1.3.100.6.1.1.3
		arpConfigCurrentLearnNum OBJECT-TYPE
			SYNTAX Unsigned32
			MAX-ACCESS read-only
			STATUS current
			DESCRIPTION
				"Description."
			::= { arpConfigEntry 3 }


		-- 1.3.6.1.4.1.34592.1.3.100.6.1.1.4
		arpConfigQuickUpdateEnable OBJECT-TYPE
			SYNTAX TruthValue
			MAX-ACCESS read-write
			STATUS current
			DESCRIPTION
				"Description."
			::= { arpConfigEntry 4 }


		-- 1.3.6.1.4.1.34592.1.3.100.6.1.1.5
		arpConfigReplyFastEnable OBJECT-TYPE
			SYNTAX TruthValue
			MAX-ACCESS read-write
			STATUS current
			DESCRIPTION
				"Description."
			::= { arpConfigEntry 5 }


		-- 1.3.6.1.4.1.34592.1.3.100.6.1.1.6
		arpConfigDetectEnable OBJECT-TYPE
			SYNTAX TruthValue
			MAX-ACCESS read-write
			STATUS current
			DESCRIPTION
				"Description."
			::= { arpConfigEntry 6 }


		-- 1.3.6.1.4.1.34592.1.3.100.6.1.1.8
		arpConfigAgeTime OBJECT-TYPE
			SYNTAX Unsigned32 (60..300)
			MAX-ACCESS read-write
			STATUS current
			DESCRIPTION
				"Description."
			::= { arpConfigEntry 8 }


		-- 1.3.6.1.4.1.34592.1.3.100.6.1.1.9
		arpConfigGratuitousArpSendTime OBJECT-TYPE
			SYNTAX Integer32 (1..60)
			MAX-ACCESS read-write
			STATUS current
			DESCRIPTION
				"Description."
			::= { arpConfigEntry 9 }


		-- 1.3.6.1.4.1.34592.1.3.100.6.1.1.10
		arpConfigGratuitousArpLearnEnable OBJECT-TYPE
			SYNTAX TruthValue
			MAX-ACCESS read-write
			STATUS current
			DESCRIPTION
				"Description."
			::= { arpConfigEntry 10 }


		-- 1.3.6.1.4.1.34592.1.3.100.6.1.1.11
		arpConfigArpClear OBJECT-TYPE
			SYNTAX INTEGER
				{
				allDynamic(1),
				allStatic(2),
				none(3)
				}
			MAX-ACCESS read-write
			STATUS current
			DESCRIPTION
				"Description."
			::= { arpConfigEntry 11 }


--        1.3.6.1.4.1.34592.1.3.100.6.2
-- 1.3.6.1.4.1.34592.1.3.100.6.2
-- 1.3.6.1.4.1.34592.1.3.100.6.2
-- 1.3.6.1.4.1.34592.1.3.100.6.2
-- 1.3.6.1.4.1.34592.1.3.100.6.2
-- 1.3.6.1.4.1.34592.1.3.100.6.2
-- 1.3.6.1.4.1.34592.1.3.100.6.2
		-- 1.3.6.1.4.1.34592.1.3.100.6.2
		arpTable OBJECT-TYPE
			SYNTAX SEQUENCE OF ArpEntry
			MAX-ACCESS not-accessible
			STATUS current
			DESCRIPTION
				"Description."
			::= { arpManagementObjects 2 }


--        1.3.6.1.4.1.34592.1.3.100.6.2.1
-- 1.3.6.1.4.1.34592.1.3.100.6.2.1
-- 1.3.6.1.4.1.34592.1.3.100.6.2.1
-- 1.3.6.1.4.1.34592.1.3.100.6.2.1
-- 1.3.6.1.4.1.34592.1.3.100.6.2.1
-- 1.3.6.1.4.1.34592.1.3.100.6.2.1
-- 1.3.6.1.4.1.34592.1.3.100.6.2.1
		-- 1.3.6.1.4.1.34592.1.3.100.6.2.1
		arpEntry OBJECT-TYPE
			SYNTAX ArpEntry
			MAX-ACCESS not-accessible
			STATUS current
			DESCRIPTION
				"Description."
			INDEX { arpTableIpAddressIndex, arpTableVlanIndex }
			::= { arpTable 1 }


		ArpEntry ::=
			SEQUENCE {
				arpTableIpAddressIndex
					IpAddress,
				arpTableVlanIndex
					Unsigned32,
				arpTableMacAddress
					MacAddress,
				arpTablePortId
					NscrtvPonExtDeviceIndex,
				arpTableType
					INTEGER,
				arpTableRowStatus
					RowStatus
			 }

--        1.3.6.1.4.1.34592.1.3.100.6.2.1.1
-- 1.3.6.1.4.1.34592.1.3.100.6.2.1.1
-- 1.3.6.1.4.1.34592.1.3.100.6.2.1.1
-- 1.3.6.1.4.1.34592.1.3.100.6.2.1.1
-- 1.3.6.1.4.1.34592.1.3.100.6.2.1.1
-- 1.3.6.1.4.1.34592.1.3.100.6.2.1.1
-- 1.3.6.1.4.1.34592.1.3.100.6.2.1.1
		-- 1.3.6.1.4.1.34592.1.3.100.6.2.1.1
		arpTableIpAddressIndex OBJECT-TYPE
			SYNTAX IpAddress
			MAX-ACCESS not-accessible
			STATUS current
			DESCRIPTION
				"Description."
			::= { arpEntry 1 }


--        1.3.6.1.4.1.34592.1.3.100.6.2.1.2
-- 1.3.6.1.4.1.34592.1.3.100.6.2.1.2
-- 1.3.6.1.4.1.34592.1.3.100.6.2.1.2
-- 1.3.6.1.4.1.34592.1.3.100.6.2.1.2
-- 1.3.6.1.4.1.34592.1.3.100.6.2.1.2
-- 1.3.6.1.4.1.34592.1.3.100.6.2.1.2
-- 1.3.6.1.4.1.34592.1.3.100.6.2.1.2
		-- 1.3.6.1.4.1.34592.1.3.100.6.2.1.2
		arpTableVlanIndex OBJECT-TYPE
			SYNTAX Unsigned32
			MAX-ACCESS not-accessible
			STATUS current
			DESCRIPTION
				"Description."
			::= { arpEntry 2 }


--        1.3.6.1.4.1.34592.1.3.100.6.2.1.3
-- 1.3.6.1.4.1.34592.1.3.100.6.2.1.3
-- 1.3.6.1.4.1.34592.1.3.100.6.2.1.3
-- 1.3.6.1.4.1.34592.1.3.100.6.2.1.3
-- 1.3.6.1.4.1.34592.1.3.100.6.2.1.3
-- 1.3.6.1.4.1.34592.1.3.100.6.2.1.3
-- 1.3.6.1.4.1.34592.1.3.100.6.2.1.3
		-- 1.3.6.1.4.1.34592.1.3.100.6.2.1.3
		arpTableMacAddress OBJECT-TYPE
			SYNTAX MacAddress
			MAX-ACCESS read-create
			STATUS current
			DESCRIPTION
				"Description."
			::= { arpEntry 3 }


--        1.3.6.1.4.1.34592.1.3.100.6.2.1.4
-- 1.3.6.1.4.1.34592.1.3.100.6.2.1.4
-- 1.3.6.1.4.1.34592.1.3.100.6.2.1.4
-- 1.3.6.1.4.1.34592.1.3.100.6.2.1.4
-- 1.3.6.1.4.1.34592.1.3.100.6.2.1.4
-- 1.3.6.1.4.1.34592.1.3.100.6.2.1.4
-- 1.3.6.1.4.1.34592.1.3.100.6.2.1.4
		-- 1.3.6.1.4.1.34592.1.3.100.6.2.1.4
		arpTablePortId OBJECT-TYPE
			SYNTAX NscrtvPonExtDeviceIndex
			MAX-ACCESS read-create
			STATUS current
			DESCRIPTION
				"Description."
			::= { arpEntry 4 }


--        1.3.6.1.4.1.34592.1.3.100.6.2.1.5
-- 1.3.6.1.4.1.34592.1.3.100.6.2.1.5
-- 1.3.6.1.4.1.34592.1.3.100.6.2.1.5
-- 1.3.6.1.4.1.34592.1.3.100.6.2.1.5
-- 1.3.6.1.4.1.34592.1.3.100.6.2.1.5
-- 1.3.6.1.4.1.34592.1.3.100.6.2.1.5
-- 1.3.6.1.4.1.34592.1.3.100.6.2.1.5
		-- 1.3.6.1.4.1.34592.1.3.100.6.2.1.5
		arpTableType OBJECT-TYPE
			SYNTAX INTEGER
				{
				dynamic(1),
				static(2)
				}
			MAX-ACCESS read-create
			STATUS current
			DESCRIPTION
				"Description."
			::= { arpEntry 5 }


--        1.3.6.1.4.1.34592.1.3.100.6.2.1.6
-- 1.3.6.1.4.1.34592.1.3.100.6.2.1.6
-- 1.3.6.1.4.1.34592.1.3.100.6.2.1.6
-- 1.3.6.1.4.1.34592.1.3.100.6.2.1.6
-- 1.3.6.1.4.1.34592.1.3.100.6.2.1.6
-- 1.3.6.1.4.1.34592.1.3.100.6.2.1.6
-- 1.3.6.1.4.1.34592.1.3.100.6.2.1.6
		-- 1.3.6.1.4.1.34592.1.3.100.6.2.1.6
		arpTableRowStatus OBJECT-TYPE
			SYNTAX RowStatus
			MAX-ACCESS read-create
			STATUS current
			DESCRIPTION
				"Description."
			::= { arpEntry 6 }


--        1.3.6.1.4.1.34592.1.3.100.6.3
-- 1.3.6.1.4.1.34592.1.3.100.6.3
-- 1.3.6.1.4.1.34592.1.3.100.6.3
-- 1.3.6.1.4.1.34592.1.3.100.6.3
-- 1.3.6.1.4.1.34592.1.3.100.6.3
-- 1.3.6.1.4.1.34592.1.3.100.6.3
-- 1.3.6.1.4.1.34592.1.3.100.6.3
		-- 1.3.6.1.4.1.34592.1.3.100.6.3
		arpVlanIfConfigTable OBJECT-TYPE
			SYNTAX SEQUENCE OF ArpVlanIfConfigEntry
			MAX-ACCESS not-accessible
			STATUS current
			DESCRIPTION
				"Description."
			::= { arpManagementObjects 3 }


--        1.3.6.1.4.1.34592.1.3.100.6.3.1
-- 1.3.6.1.4.1.34592.1.3.100.6.3.1
-- 1.3.6.1.4.1.34592.1.3.100.6.3.1
-- 1.3.6.1.4.1.34592.1.3.100.6.3.1
-- 1.3.6.1.4.1.34592.1.3.100.6.3.1
-- 1.3.6.1.4.1.34592.1.3.100.6.3.1
-- 1.3.6.1.4.1.34592.1.3.100.6.3.1
		-- 1.3.6.1.4.1.34592.1.3.100.6.3.1
		arpVlanIfConfigEntry OBJECT-TYPE
			SYNTAX ArpVlanIfConfigEntry
			MAX-ACCESS not-accessible
			STATUS current
			DESCRIPTION
				"Description."
			INDEX { arpVlanIfConfigDeviceIndex, arpVlanIfConfigVlanIfIndex }
			::= { arpVlanIfConfigTable 1 }


		ArpVlanIfConfigEntry ::=
			SEQUENCE {
				arpVlanIfConfigDeviceIndex
					NscrtvPonExtDeviceIndex,
				arpVlanIfConfigVlanIfIndex
					Unsigned32,
				arpVlanIfConfigAgeTime
					Unsigned32,
				arpVlanIfConfigMaxLearnNum
					Unsigned32,
				arpVlanIfConfigCurrentLearnNum
					Unsigned32,
				arpVlanIfConfigArpClear
					INTEGER,
				arpVlanifConfigProxyEnable
					TruthValue,
				arpVlanifConfigInnerVlanArpProxyEnable
					TruthValue,
				arpVlanifConfigGratuitousArpEnable
					TruthValue,
				arpVlanIfConfigGratuitousArpSendTime
					Integer32,
				arpVlanIfConfigGratuitousArpLearnEnable
					TruthValue
			 }

--        1.3.6.1.4.1.34592.1.3.100.6.3.1.1
-- 1.3.6.1.4.1.34592.1.3.100.6.3.1.1
-- 1.3.6.1.4.1.34592.1.3.100.6.3.1.1
-- 1.3.6.1.4.1.34592.1.3.100.6.3.1.1
-- 1.3.6.1.4.1.34592.1.3.100.6.3.1.1
-- 1.3.6.1.4.1.34592.1.3.100.6.3.1.1
-- 1.3.6.1.4.1.34592.1.3.100.6.3.1.1
		-- 1.3.6.1.4.1.34592.1.3.100.6.3.1.1
		arpVlanIfConfigDeviceIndex OBJECT-TYPE
			SYNTAX NscrtvPonExtDeviceIndex
			MAX-ACCESS not-accessible
			STATUS current
			DESCRIPTION
				"Description."
			::= { arpVlanIfConfigEntry 1 }


--        1.3.6.1.4.1.34592.1.3.100.6.3.1.2
-- 1.3.6.1.4.1.34592.1.3.100.6.3.1.2
-- 1.3.6.1.4.1.34592.1.3.100.6.3.1.2
-- 1.3.6.1.4.1.34592.1.3.100.6.3.1.2
-- 1.3.6.1.4.1.34592.1.3.100.6.3.1.2
-- 1.3.6.1.4.1.34592.1.3.100.6.3.1.2
-- 1.3.6.1.4.1.34592.1.3.100.6.3.1.2
		-- 1.3.6.1.4.1.34592.1.3.100.6.3.1.2
		arpVlanIfConfigVlanIfIndex OBJECT-TYPE
			SYNTAX Unsigned32
			MAX-ACCESS not-accessible
			STATUS current
			DESCRIPTION
				"Description."
			::= { arpVlanIfConfigEntry 2 }


--        1.3.6.1.4.1.34592.1.3.100.6.3.1.3
-- 1.3.6.1.4.1.34592.1.3.100.6.3.1.3
-- 1.3.6.1.4.1.34592.1.3.100.6.3.1.3
-- 1.3.6.1.4.1.34592.1.3.100.6.3.1.3
-- 1.3.6.1.4.1.34592.1.3.100.6.3.1.3
-- 1.3.6.1.4.1.34592.1.3.100.6.3.1.3
-- 1.3.6.1.4.1.34592.1.3.100.6.3.1.3
		-- 1.3.6.1.4.1.34592.1.3.100.6.3.1.3
		arpVlanIfConfigAgeTime OBJECT-TYPE
			SYNTAX Unsigned32
			MAX-ACCESS read-write
			STATUS current
			DESCRIPTION
				"Description."
			::= { arpVlanIfConfigEntry 3 }


--        1.3.6.1.4.1.34592.1.3.100.6.3.1.4
-- 1.3.6.1.4.1.34592.1.3.100.6.3.1.4
-- 1.3.6.1.4.1.34592.1.3.100.6.3.1.4
-- 1.3.6.1.4.1.34592.1.3.100.6.3.1.4
-- 1.3.6.1.4.1.34592.1.3.100.6.3.1.4
-- 1.3.6.1.4.1.34592.1.3.100.6.3.1.4
-- 1.3.6.1.4.1.34592.1.3.100.6.3.1.4
		-- 1.3.6.1.4.1.34592.1.3.100.6.3.1.4
		arpVlanIfConfigMaxLearnNum OBJECT-TYPE
			SYNTAX Unsigned32
			MAX-ACCESS read-write
			STATUS current
			DESCRIPTION
				"Description."
			::= { arpVlanIfConfigEntry 4 }


--        1.3.6.1.4.1.34592.1.3.100.6.3.1.5
-- 1.3.6.1.4.1.34592.1.3.100.6.3.1.5
-- 1.3.6.1.4.1.34592.1.3.100.6.3.1.5
-- 1.3.6.1.4.1.34592.1.3.100.6.3.1.5
-- 1.3.6.1.4.1.34592.1.3.100.6.3.1.5
-- 1.3.6.1.4.1.34592.1.3.100.6.3.1.5
-- 1.3.6.1.4.1.34592.1.3.100.6.3.1.5
		-- 1.3.6.1.4.1.34592.1.3.100.6.3.1.5
		arpVlanIfConfigCurrentLearnNum OBJECT-TYPE
			SYNTAX Unsigned32
			MAX-ACCESS read-only
			STATUS current
			DESCRIPTION
				"Description."
			::= { arpVlanIfConfigEntry 5 }


--        1.3.6.1.4.1.34592.1.3.100.6.3.1.6
-- 1.3.6.1.4.1.34592.1.3.100.6.3.1.6
-- 1.3.6.1.4.1.34592.1.3.100.6.3.1.6
-- 1.3.6.1.4.1.34592.1.3.100.6.3.1.6
-- 1.3.6.1.4.1.34592.1.3.100.6.3.1.6
-- 1.3.6.1.4.1.34592.1.3.100.6.3.1.6
-- 1.3.6.1.4.1.34592.1.3.100.6.3.1.6
		-- 1.3.6.1.4.1.34592.1.3.100.6.3.1.6
		arpVlanIfConfigArpClear OBJECT-TYPE
			SYNTAX INTEGER
				{
				dynamic(1),
				static(2),
				none(3)
				}
			MAX-ACCESS read-write
			STATUS current
			DESCRIPTION
				"Description."
			::= { arpVlanIfConfigEntry 6 }


--     1.3.6.1.4.1.34592.1.3.100.6.3.1.7
-- 1.3.6.1.4.1.34592.1.3.100.6.3.1.7
-- 1.3.6.1.4.1.34592.1.3.100.6.3.1.7
-- 1.3.6.1.4.1.34592.1.3.100.6.3.1.7
		-- 1.3.6.1.4.1.34592.1.3.100.6.3.1.7
		arpVlanifConfigProxyEnable OBJECT-TYPE
			SYNTAX TruthValue
			MAX-ACCESS read-write
			STATUS current
			DESCRIPTION
				"Description."
			::= { arpVlanIfConfigEntry 7 }


--     1.3.6.1.4.1.34592.1.3.100.6.3.1.8
-- 1.3.6.1.4.1.34592.1.3.100.6.3.1.8
-- 1.3.6.1.4.1.34592.1.3.100.6.3.1.8
-- 1.3.6.1.4.1.34592.1.3.100.6.3.1.8
		-- 1.3.6.1.4.1.34592.1.3.100.6.3.1.8
		arpVlanifConfigInnerVlanArpProxyEnable OBJECT-TYPE
			SYNTAX TruthValue
			MAX-ACCESS read-write
			STATUS current
			DESCRIPTION
				"Description."
			::= { arpVlanIfConfigEntry 8 }


--     1.3.6.1.4.1.34592.1.3.100.6.3.1.9
-- 1.3.6.1.4.1.34592.1.3.100.6.3.1.9
-- 1.3.6.1.4.1.34592.1.3.100.6.3.1.9
-- 1.3.6.1.4.1.34592.1.3.100.6.3.1.9
		-- 1.3.6.1.4.1.34592.1.3.100.6.3.1.9
		arpVlanifConfigGratuitousArpEnable OBJECT-TYPE
			SYNTAX TruthValue
			MAX-ACCESS read-write
			STATUS current
			DESCRIPTION
				"Description."
			::= { arpVlanIfConfigEntry 9 }


--     1.3.6.1.4.1.34592.1.3.100.6.3.1.10
-- 1.3.6.1.4.1.34592.1.3.100.6.3.1.10
-- 1.3.6.1.4.1.34592.1.3.100.6.3.1.10
-- 1.3.6.1.4.1.34592.1.3.100.6.3.1.10
		-- 1.3.6.1.4.1.34592.1.3.100.6.3.1.10
		arpVlanIfConfigGratuitousArpSendTime OBJECT-TYPE
			SYNTAX Integer32 (1..60)
			MAX-ACCESS read-write
			STATUS current
			DESCRIPTION
				"Description."
			::= { arpVlanIfConfigEntry 10 }


--     1.3.6.1.4.1.34592.1.3.100.6.3.1.11
-- 1.3.6.1.4.1.34592.1.3.100.6.3.1.11
-- 1.3.6.1.4.1.34592.1.3.100.6.3.1.11
-- 1.3.6.1.4.1.34592.1.3.100.6.3.1.11
		-- 1.3.6.1.4.1.34592.1.3.100.6.3.1.11
		arpVlanIfConfigGratuitousArpLearnEnable OBJECT-TYPE
			SYNTAX TruthValue
			MAX-ACCESS read-write
			STATUS current
			DESCRIPTION
				"Description."
			::= { arpVlanIfConfigEntry 11 }

		-- 1.3.6.1.4.1.34592.1.3.100.7
		layer3ManagementObjects OBJECT IDENTIFIER ::= { nscrtvPonTreeExt 7 }


		-- 1.3.6.1.4.1.34592.1.3.100.7.1
		staticManagement OBJECT IDENTIFIER ::= { layer3ManagementObjects 1 }


		-- 1.3.6.1.4.1.34592.1.3.100.7.1.1
		ipRouteTable OBJECT-TYPE
			SYNTAX SEQUENCE OF IpRouteEntry
			MAX-ACCESS not-accessible
			STATUS current
			DESCRIPTION
				"Description."
			::= { staticManagement 1 }


		-- 1.3.6.1.4.1.34592.1.3.100.7.1.1.1
		ipRouteEntry OBJECT-TYPE
			SYNTAX IpRouteEntry
			MAX-ACCESS not-accessible
			STATUS current
			DESCRIPTION
				"Description."
			INDEX { ipRouteDestinationIpAddrIndex, ipRouteNetMaskIndex, ipRouteProtoIndex, ipRouteNextHopIndex }
			::= { ipRouteTable 1 }


		IpRouteEntry ::=
			SEQUENCE {
				ipRouteDestinationIpAddrIndex
					IpAddress,
				ipRouteNetMaskIndex
					IpAddress,
				ipRouteProtoIndex
					INTEGER,
				ipRouteNextHopIndex
					IpAddress,
				ipRoutePreference
					Unsigned32,
				ipRouteMetric
					Unsigned32,
				ipRouteInterface
					Unsigned32,
				ipRouteRowStatus
					RowStatus
			 }

		-- 1.3.6.1.4.1.34592.1.3.100.7.1.1.1.1
		ipRouteDestinationIpAddrIndex OBJECT-TYPE
			SYNTAX IpAddress
			MAX-ACCESS not-accessible
			STATUS current
			DESCRIPTION
				"Description."
			::= { ipRouteEntry 1 }


		-- 1.3.6.1.4.1.34592.1.3.100.7.1.1.1.2
		ipRouteNetMaskIndex OBJECT-TYPE
			SYNTAX IpAddress
			MAX-ACCESS not-accessible
			STATUS current
			DESCRIPTION
				"Description."
			::= { ipRouteEntry 2 }


		-- 1.3.6.1.4.1.34592.1.3.100.7.1.1.1.3
		ipRouteProtoIndex OBJECT-TYPE
			SYNTAX INTEGER
				{
				direct(1),
				static(2),
				rip(3),
				ospf(4),
				pimsm(5),
				bgp(6),
				mbgp(7)
				}
			MAX-ACCESS not-accessible
			STATUS current
			DESCRIPTION
				"Description."
			::= { ipRouteEntry 3 }


		-- 1.3.6.1.4.1.34592.1.3.100.7.1.1.1.4
		ipRouteNextHopIndex OBJECT-TYPE
			SYNTAX IpAddress
			MAX-ACCESS not-accessible
			STATUS current
			DESCRIPTION
				"Description."
			::= { ipRouteEntry 4 }


		-- 1.3.6.1.4.1.34592.1.3.100.7.1.1.1.5
		ipRoutePreference OBJECT-TYPE
			SYNTAX Unsigned32 (1..255)
			MAX-ACCESS read-create
			STATUS current
			DESCRIPTION
				"Description."
			::= { ipRouteEntry 5 }


		-- 1.3.6.1.4.1.34592.1.3.100.7.1.1.1.6
		ipRouteMetric OBJECT-TYPE
			SYNTAX Unsigned32
			MAX-ACCESS read-only
			STATUS current
			DESCRIPTION
				"Description."
			::= { ipRouteEntry 6 }


		-- 1.3.6.1.4.1.34592.1.3.100.7.1.1.1.7
		ipRouteInterface OBJECT-TYPE
			SYNTAX Unsigned32
			MAX-ACCESS read-only
			STATUS current
			DESCRIPTION
				"If this value is 0,it indicates that next hop is unreachable,and the others are
				considered normal."
			::= { ipRouteEntry 7 }


		-- 1.3.6.1.4.1.34592.1.3.100.7.1.1.1.8
		ipRouteRowStatus OBJECT-TYPE
			SYNTAX RowStatus
			MAX-ACCESS read-create
			STATUS current
			DESCRIPTION
				"Description."
			::= { ipRouteEntry 8 }


		-- 1.3.6.1.4.1.34592.1.3.100.7.2
		ripManagement OBJECT IDENTIFIER ::= { layer3ManagementObjects 2 }


		-- 1.3.6.1.4.1.34592.1.3.100.7.2.1
		ripGlobalMixedTable OBJECT-TYPE
			SYNTAX SEQUENCE OF RipGlobalMixedEntry
			MAX-ACCESS not-accessible
			STATUS current
			DESCRIPTION
				"vty command:router rip"
			::= { ripManagement 1 }


		-- 1.3.6.1.4.1.34592.1.3.100.7.2.1.1
		ripGlobalMixedEntry OBJECT-TYPE
			SYNTAX RipGlobalMixedEntry
			MAX-ACCESS not-accessible
			STATUS current
			DESCRIPTION
				"Description."
			INDEX { ripGlobalMixedDeviceIndex }
			::= { ripGlobalMixedTable 1 }


		RipGlobalMixedEntry ::=
			SEQUENCE {
				ripGlobalMixedDeviceIndex
					NscrtvPonExtDeviceIndex,
				ripGlobalMixedEnable
					TruthValue,
				ripGlobalMixedDefaultMetric
					Unsigned32,
				ripGlobalMixedDistance
					Unsigned32,
				ripGlobalMixedTimerUpdate
					Unsigned32,
				ripGlobalMixedTimerTimeout
					Unsigned32,
				ripGlobalMixedTimerGarbage
					Unsigned32,
				ripGlobalMixedTimerReset
					TruthValue,
				ripGlobalMixedVersion
					INTEGER
			 }

		-- 1.3.6.1.4.1.34592.1.3.100.7.2.1.1.1
		ripGlobalMixedDeviceIndex OBJECT-TYPE
			SYNTAX NscrtvPonExtDeviceIndex
			MAX-ACCESS not-accessible
			STATUS current
			DESCRIPTION
				"Description."
			::= { ripGlobalMixedEntry 1 }


		-- 1.3.6.1.4.1.34592.1.3.100.7.2.1.1.2
		ripGlobalMixedEnable OBJECT-TYPE
			SYNTAX TruthValue
			MAX-ACCESS read-write
			STATUS current
			DESCRIPTION
				"Description."
			::= { ripGlobalMixedEntry 2 }


		-- 1.3.6.1.4.1.34592.1.3.100.7.2.1.1.4
		ripGlobalMixedDefaultMetric OBJECT-TYPE
			SYNTAX Unsigned32 (1..16)
			MAX-ACCESS read-write
			STATUS current
			DESCRIPTION
				"Description."
			::= { ripGlobalMixedEntry 4 }


		-- 1.3.6.1.4.1.34592.1.3.100.7.2.1.1.5
		ripGlobalMixedDistance OBJECT-TYPE
			SYNTAX Unsigned32 (1..255)
			MAX-ACCESS read-write
			STATUS current
			DESCRIPTION
				"Description."
			::= { ripGlobalMixedEntry 5 }


		-- 1.3.6.1.4.1.34592.1.3.100.7.2.1.1.7
		ripGlobalMixedTimerUpdate OBJECT-TYPE
			SYNTAX Unsigned32 (5..16777215)
			MAX-ACCESS read-write
			STATUS current
			DESCRIPTION
				"Description."
			::= { ripGlobalMixedEntry 7 }


		-- 1.3.6.1.4.1.34592.1.3.100.7.2.1.1.8
		ripGlobalMixedTimerTimeout OBJECT-TYPE
			SYNTAX Unsigned32 (5..16777215)
			MAX-ACCESS read-write
			STATUS current
			DESCRIPTION
				"Description."
			::= { ripGlobalMixedEntry 8 }


		-- 1.3.6.1.4.1.34592.1.3.100.7.2.1.1.9
		ripGlobalMixedTimerGarbage OBJECT-TYPE
			SYNTAX Unsigned32 (5..16777215)
			MAX-ACCESS read-write
			STATUS current
			DESCRIPTION
				"Description."
			::= { ripGlobalMixedEntry 9 }


		-- 1.3.6.1.4.1.34592.1.3.100.7.2.1.1.10
		ripGlobalMixedTimerReset OBJECT-TYPE
			SYNTAX TruthValue
			MAX-ACCESS read-write
			STATUS current
			DESCRIPTION
				"Description."
			::= { ripGlobalMixedEntry 10 }


		-- 1.3.6.1.4.1.34592.1.3.100.7.2.1.1.11
		ripGlobalMixedVersion OBJECT-TYPE
			SYNTAX INTEGER
				{
				reset(0),
				version1(1),
				version2(2)
				}
			MAX-ACCESS read-write
			STATUS current
			DESCRIPTION
				"Description."
			::= { ripGlobalMixedEntry 11 }


		-- 1.3.6.1.4.1.34592.1.3.100.7.2.4
		ripGlobalNeighborTable OBJECT-TYPE
			SYNTAX SEQUENCE OF RipGlobalNeighborEntry
			MAX-ACCESS not-accessible
			STATUS current
			DESCRIPTION
				"Description."
			::= { ripManagement 4 }


		-- 1.3.6.1.4.1.34592.1.3.100.7.2.4.1
		ripGlobalNeighborEntry OBJECT-TYPE
			SYNTAX RipGlobalNeighborEntry
			MAX-ACCESS not-accessible
			STATUS current
			DESCRIPTION
				"Description."
			INDEX { ripGlobalNeighborIpAddrIndex }
			::= { ripGlobalNeighborTable 1 }


		RipGlobalNeighborEntry ::=
			SEQUENCE {
				ripGlobalNeighborIpAddrIndex
					IpAddress,
				ripGlobalNeighborRowStatus
					RowStatus
			 }

		-- 1.3.6.1.4.1.34592.1.3.100.7.2.4.1.1
		ripGlobalNeighborIpAddrIndex OBJECT-TYPE
			SYNTAX IpAddress
			MAX-ACCESS not-accessible
			STATUS current
			DESCRIPTION
				"Description."
			::= { ripGlobalNeighborEntry 1 }


		-- 1.3.6.1.4.1.34592.1.3.100.7.2.4.1.6
		ripGlobalNeighborRowStatus OBJECT-TYPE
			SYNTAX RowStatus
			MAX-ACCESS read-create
			STATUS current
			DESCRIPTION
				"Description."
			::= { ripGlobalNeighborEntry 6 }


		-- 1.3.6.1.4.1.34592.1.3.100.7.2.6
		ripGlobalNetworkIpTable OBJECT-TYPE
			SYNTAX SEQUENCE OF RipGlobalNetworkIpEntry
			MAX-ACCESS not-accessible
			STATUS current
			DESCRIPTION
				"Description."
			::= { ripManagement 6 }


		-- 1.3.6.1.4.1.34592.1.3.100.7.2.6.1
		ripGlobalNetworkIpEntry OBJECT-TYPE
			SYNTAX RipGlobalNetworkIpEntry
			MAX-ACCESS not-accessible
			STATUS current
			DESCRIPTION
				"Description."
			INDEX { ripGlobalNetworkIpAddrIndex, ripGlobalNetworkMaskLenIndex }
			::= { ripGlobalNetworkIpTable 1 }


		RipGlobalNetworkIpEntry ::=
			SEQUENCE {
				ripGlobalNetworkIpAddrIndex
					IpAddress,
				ripGlobalNetworkMaskLenIndex
					Unsigned32,
				ripGlobalNetworkIpRowStatus
					RowStatus
			 }

		-- 1.3.6.1.4.1.34592.1.3.100.7.2.6.1.2
		ripGlobalNetworkIpAddrIndex OBJECT-TYPE
			SYNTAX IpAddress
			MAX-ACCESS not-accessible
			STATUS current
			DESCRIPTION
				"Description."
			::= { ripGlobalNetworkIpEntry 2 }


		-- 1.3.6.1.4.1.34592.1.3.100.7.2.6.1.3
		ripGlobalNetworkMaskLenIndex OBJECT-TYPE
			SYNTAX Unsigned32 (0..32)
			MAX-ACCESS not-accessible
			STATUS current
			DESCRIPTION
				"Description."
			::= { ripGlobalNetworkIpEntry 3 }


		-- 1.3.6.1.4.1.34592.1.3.100.7.2.6.1.6
		ripGlobalNetworkIpRowStatus OBJECT-TYPE
			SYNTAX RowStatus
			MAX-ACCESS read-create
			STATUS current
			DESCRIPTION
				"Description."
			::= { ripGlobalNetworkIpEntry 6 }


		-- 1.3.6.1.4.1.34592.1.3.100.7.2.8
		ripGlobalRedistributeTable OBJECT-TYPE
			SYNTAX SEQUENCE OF RipGlobalRedistributeEntry
			MAX-ACCESS not-accessible
			STATUS current
			DESCRIPTION
				"Description."
			::= { ripManagement 8 }


		-- 1.3.6.1.4.1.34592.1.3.100.7.2.8.1
		ripGlobalRedistributeEntry OBJECT-TYPE
			SYNTAX RipGlobalRedistributeEntry
			MAX-ACCESS not-accessible
			STATUS current
			DESCRIPTION
				"Description."
			INDEX { ripGlobalRedistributeProtocolIndex }
			::= { ripGlobalRedistributeTable 1 }


		RipGlobalRedistributeEntry ::=
			SEQUENCE {
				ripGlobalRedistributeProtocolIndex
					INTEGER,
				ripGlobalRedistributeMetric
					Unsigned32,
				ripGlobalRedistributeRowStatus
					RowStatus
			 }

		-- 1.3.6.1.4.1.34592.1.3.100.7.2.8.1.2
		ripGlobalRedistributeProtocolIndex OBJECT-TYPE
			SYNTAX INTEGER
				{
				babel(1),
				bgp(2),
				connected(3),
				isis(4),
				kernel(5),
				ospf(6),
				pim(7),
				static(8),
				default(9)
				}
			MAX-ACCESS not-accessible
			STATUS current
			DESCRIPTION
				"Description."
			::= { ripGlobalRedistributeEntry 2 }


		-- 1.3.6.1.4.1.34592.1.3.100.7.2.8.1.3
		ripGlobalRedistributeMetric OBJECT-TYPE
			SYNTAX Unsigned32 (0..16)
			MAX-ACCESS read-create
			STATUS current
			DESCRIPTION
				"Description."
			::= { ripGlobalRedistributeEntry 3 }


		-- 1.3.6.1.4.1.34592.1.3.100.7.2.8.1.6
		ripGlobalRedistributeRowStatus OBJECT-TYPE
			SYNTAX RowStatus
			MAX-ACCESS read-create
			STATUS current
			DESCRIPTION
				"Description."
			::= { ripGlobalRedistributeEntry 6 }


		-- 1.3.6.1.4.1.34592.1.3.100.7.2.9
		ripGlobalRouteTable OBJECT-TYPE
			SYNTAX SEQUENCE OF RipGlobalRouteEntry
			MAX-ACCESS not-accessible
			STATUS current
			DESCRIPTION
				"Description."
			::= { ripManagement 9 }


		-- 1.3.6.1.4.1.34592.1.3.100.7.2.9.1
		ripGlobalRouteEntry OBJECT-TYPE
			SYNTAX RipGlobalRouteEntry
			MAX-ACCESS not-accessible
			STATUS current
			DESCRIPTION
				"Description."
			INDEX { ripGlobalRouteIpAddrIndex, ripGlobalRouteMaskLenIndex }
			::= { ripGlobalRouteTable 1 }


		RipGlobalRouteEntry ::=
			SEQUENCE {
				ripGlobalRouteIpAddrIndex
					IpAddress,
				ripGlobalRouteMaskLenIndex
					Unsigned32,
				ripGlobalRouteRowStatus
					RowStatus
			 }

		-- 1.3.6.1.4.1.34592.1.3.100.7.2.9.1.2
		ripGlobalRouteIpAddrIndex OBJECT-TYPE
			SYNTAX IpAddress
			MAX-ACCESS not-accessible
			STATUS current
			DESCRIPTION
				"Description."
			::= { ripGlobalRouteEntry 2 }


		-- 1.3.6.1.4.1.34592.1.3.100.7.2.9.1.3
		ripGlobalRouteMaskLenIndex OBJECT-TYPE
			SYNTAX Unsigned32 (0..32)
			MAX-ACCESS not-accessible
			STATUS current
			DESCRIPTION
				"Description."
			::= { ripGlobalRouteEntry 3 }


		-- 1.3.6.1.4.1.34592.1.3.100.7.2.9.1.4
		ripGlobalRouteRowStatus OBJECT-TYPE
			SYNTAX RowStatus
			MAX-ACCESS read-create
			STATUS current
			DESCRIPTION
				"Description."
			::= { ripGlobalRouteEntry 4 }


		-- 1.3.6.1.4.1.34592.1.3.100.7.2.10
		ripVlanifTable OBJECT-TYPE
			SYNTAX SEQUENCE OF RipVlanifEntry
			MAX-ACCESS not-accessible
			STATUS current
			DESCRIPTION
				"Description."
			::= { ripManagement 10 }


		-- 1.3.6.1.4.1.34592.1.3.100.7.2.10.1
		ripVlanifEntry OBJECT-TYPE
			SYNTAX RipVlanifEntry
			MAX-ACCESS not-accessible
			STATUS current
			DESCRIPTION
				"Description."
			INDEX { ripVlanifVlanIfIndex }
			::= { ripVlanifTable 1 }


		RipVlanifEntry ::=
			SEQUENCE {
				ripVlanifVlanIfIndex
					Unsigned32,
				ripVlanifAuthMode
					INTEGER,
				ripVlanifNoStringOrKeychain
					INTEGER,
				ripVlanifAuthString
					OCTET STRING,
				ripVlanifAuthKeychain
					OCTET STRING,
				ripVlanifRcvVersion
					INTEGER,
				ripVlanifSndVersion
					INTEGER,
				ripVlanifSplit
					TruthValue,
				ripVlanifSplitPoison
					TruthValue,
				ripVlanifPassive
					TruthValue,
				ripVlanifNetwork
					TruthValue
			 }

		-- 1.3.6.1.4.1.34592.1.3.100.7.2.10.1.1
		ripVlanifVlanIfIndex OBJECT-TYPE
			SYNTAX Unsigned32 (1..4094)
			MAX-ACCESS not-accessible
			STATUS current
			DESCRIPTION
				"Description."
			::= { ripVlanifEntry 1 }


		-- 1.3.6.1.4.1.34592.1.3.100.7.2.10.1.2
		ripVlanifAuthMode OBJECT-TYPE
			SYNTAX INTEGER
				{
				reset(0),
				text(1),
				md5(2)
				}
			MAX-ACCESS read-write
			STATUS current
			DESCRIPTION
				"Description."
			::= { ripVlanifEntry 2 }


		-- 1.3.6.1.4.1.34592.1.3.100.7.2.10.1.3
		ripVlanifNoStringOrKeychain OBJECT-TYPE
			SYNTAX INTEGER
				{
				reset(0),
				string(1),
				keychain(2)
				}
			MAX-ACCESS read-write
			STATUS current
			DESCRIPTION
				"Description."
			::= { ripVlanifEntry 3 }


		-- 1.3.6.1.4.1.34592.1.3.100.7.2.10.1.4
		ripVlanifAuthString OBJECT-TYPE
			SYNTAX OCTET STRING (SIZE (1..16))
			MAX-ACCESS read-write
			STATUS current
			DESCRIPTION
				"Description."
			::= { ripVlanifEntry 4 }


		-- 1.3.6.1.4.1.34592.1.3.100.7.2.10.1.5
		ripVlanifAuthKeychain OBJECT-TYPE
			SYNTAX OCTET STRING
			MAX-ACCESS read-write
			STATUS current
			DESCRIPTION
				"Description."
			::= { ripVlanifEntry 5 }


		-- 1.3.6.1.4.1.34592.1.3.100.7.2.10.1.6
		ripVlanifRcvVersion OBJECT-TYPE
			SYNTAX INTEGER
				{
				reset(0),
				version1(1),
				version2(2),
				version1And2(3)
				}
			MAX-ACCESS read-write
			STATUS current
			DESCRIPTION
				"Description.
				"
			::= { ripVlanifEntry 6 }


		-- 1.3.6.1.4.1.34592.1.3.100.7.2.10.1.7
		ripVlanifSndVersion OBJECT-TYPE
			SYNTAX INTEGER
				{
				reset(0),
				version1(1),
				version2(2),
				version1And2(3)
				}
			MAX-ACCESS read-write
			STATUS current
			DESCRIPTION
				"Description."
			::= { ripVlanifEntry 7 }


		-- 1.3.6.1.4.1.34592.1.3.100.7.2.10.1.8
		ripVlanifSplit OBJECT-TYPE
			SYNTAX TruthValue
			MAX-ACCESS read-write
			STATUS current
			DESCRIPTION
				"Description."
			::= { ripVlanifEntry 8 }


		-- 1.3.6.1.4.1.34592.1.3.100.7.2.10.1.9
		ripVlanifSplitPoison OBJECT-TYPE
			SYNTAX TruthValue
			MAX-ACCESS read-write
			STATUS current
			DESCRIPTION
				"Description."
			::= { ripVlanifEntry 9 }


		-- 1.3.6.1.4.1.34592.1.3.100.7.2.10.1.10
		ripVlanifPassive OBJECT-TYPE
			SYNTAX TruthValue
			MAX-ACCESS read-write
			STATUS current
			DESCRIPTION
				"Description."
			::= { ripVlanifEntry 10 }


		-- 1.3.6.1.4.1.34592.1.3.100.7.2.10.1.11
		ripVlanifNetwork OBJECT-TYPE
			SYNTAX TruthValue
			MAX-ACCESS read-write
			STATUS current
			DESCRIPTION
				"Description."
			::= { ripVlanifEntry 11 }


		-- 1.3.6.1.4.1.34592.1.3.100.7.2.12
		ripKeychainTable OBJECT-TYPE
			SYNTAX SEQUENCE OF RipKeychainEntry
			MAX-ACCESS not-accessible
			STATUS current
			DESCRIPTION
				"Description."
			::= { ripManagement 12 }


		-- 1.3.6.1.4.1.34592.1.3.100.7.2.12.1
		ripKeychainEntry OBJECT-TYPE
			SYNTAX RipKeychainEntry
			MAX-ACCESS not-accessible
			STATUS current
			DESCRIPTION
				"Description."
			INDEX { ripKeychainNameIndex, ripKeychainKeyIdIndex }
			::= { ripKeychainTable 1 }


		RipKeychainEntry ::=
			SEQUENCE {
				ripKeychainNameIndex
					OCTET STRING,
				ripKeychainKeyIdIndex
					Unsigned32,
				ripKeychainKeyString
					OCTET STRING,
				ripKeychainKeyNoAccOrSndLifeTime
					INTEGER,
				ripKeychainKeyAccLifeTimeStart
					DateAndTime,
				ripKeychainKeyAccLifeTimeEnd
					DateAndTime,
				ripKeychainKeyAccLifeTimeEndDuration
					Unsigned32,
				ripKeychainKeyAccLifeTimeEndInfinite
					TruthValue,
				ripKeychainKeySndLifeTimeStart
					DateAndTime,
				ripKeychainKeySndLifeTimeEnd
					DateAndTime,
				ripKeychainKeySndLifeTimeEndDuration
					Unsigned32,
				ripKeychainKeySndLifeTimeEndInfinite
					TruthValue,
				ripKeychainRowStatus
					RowStatus
			 }

		-- 1.3.6.1.4.1.34592.1.3.100.7.2.12.1.1
		ripKeychainNameIndex OBJECT-TYPE
			SYNTAX OCTET STRING
			MAX-ACCESS not-accessible
			STATUS current
			DESCRIPTION
				"Description."
			::= { ripKeychainEntry 1 }


		-- 1.3.6.1.4.1.34592.1.3.100.7.2.12.1.2
		ripKeychainKeyIdIndex OBJECT-TYPE
			SYNTAX Unsigned32 (0..2147483647)
			MAX-ACCESS not-accessible
			STATUS current
			DESCRIPTION
				"Description."
			::= { ripKeychainEntry 2 }


		-- 1.3.6.1.4.1.34592.1.3.100.7.2.12.1.3
		ripKeychainKeyString OBJECT-TYPE
			SYNTAX OCTET STRING
			MAX-ACCESS read-create
			STATUS current
			DESCRIPTION
				"Description."
			::= { ripKeychainEntry 3 }


		-- 1.3.6.1.4.1.34592.1.3.100.7.2.12.1.4
		ripKeychainKeyNoAccOrSndLifeTime OBJECT-TYPE
			SYNTAX INTEGER
				{
				reset(0),
				accept(1),
				send(2)
				}
			MAX-ACCESS read-create
			STATUS current
			DESCRIPTION
				"Description."
			::= { ripKeychainEntry 4 }


		-- 1.3.6.1.4.1.34592.1.3.100.7.2.12.1.5
		ripKeychainKeyAccLifeTimeStart OBJECT-TYPE
			SYNTAX DateAndTime
			MAX-ACCESS read-create
			STATUS current
			DESCRIPTION
				"Description."
			::= { ripKeychainEntry 5 }


		-- 1.3.6.1.4.1.34592.1.3.100.7.2.12.1.6
		ripKeychainKeyAccLifeTimeEnd OBJECT-TYPE
			SYNTAX DateAndTime
			MAX-ACCESS read-create
			STATUS current
			DESCRIPTION
				"Description."
			::= { ripKeychainEntry 6 }


		-- 1.3.6.1.4.1.34592.1.3.100.7.2.12.1.7
		ripKeychainKeyAccLifeTimeEndDuration OBJECT-TYPE
			SYNTAX Unsigned32 (1..2147483646)
			MAX-ACCESS read-create
			STATUS current
			DESCRIPTION
				"Description."
			::= { ripKeychainEntry 7 }


		-- 1.3.6.1.4.1.34592.1.3.100.7.2.12.1.8
		ripKeychainKeyAccLifeTimeEndInfinite OBJECT-TYPE
			SYNTAX TruthValue
			MAX-ACCESS read-create
			STATUS current
			DESCRIPTION
				"Description."
			::= { ripKeychainEntry 8 }


		-- 1.3.6.1.4.1.34592.1.3.100.7.2.12.1.9
		ripKeychainKeySndLifeTimeStart OBJECT-TYPE
			SYNTAX DateAndTime
			MAX-ACCESS read-create
			STATUS current
			DESCRIPTION
				"Description."
			::= { ripKeychainEntry 9 }


		-- 1.3.6.1.4.1.34592.1.3.100.7.2.12.1.10
		ripKeychainKeySndLifeTimeEnd OBJECT-TYPE
			SYNTAX DateAndTime
			MAX-ACCESS read-create
			STATUS current
			DESCRIPTION
				"Description."
			::= { ripKeychainEntry 10 }


		-- 1.3.6.1.4.1.34592.1.3.100.7.2.12.1.11
		ripKeychainKeySndLifeTimeEndDuration OBJECT-TYPE
			SYNTAX Unsigned32 (1..2147483646)
			MAX-ACCESS read-create
			STATUS current
			DESCRIPTION
				"Description."
			::= { ripKeychainEntry 11 }


		-- 1.3.6.1.4.1.34592.1.3.100.7.2.12.1.12
		ripKeychainKeySndLifeTimeEndInfinite OBJECT-TYPE
			SYNTAX TruthValue
			MAX-ACCESS read-create
			STATUS current
			DESCRIPTION
				"Description."
			::= { ripKeychainEntry 12 }


		-- 1.3.6.1.4.1.34592.1.3.100.7.2.12.1.13
		ripKeychainRowStatus OBJECT-TYPE
			SYNTAX RowStatus
			MAX-ACCESS read-create
			STATUS current
			DESCRIPTION
				"Description."
			::= { ripKeychainEntry 13 }


		-- 1.3.6.1.4.1.34592.1.3.100.7.2.13
		ripStatusRouteNumTable OBJECT-TYPE
			SYNTAX SEQUENCE OF RipStatusRouteNumEntry
			MAX-ACCESS not-accessible
			STATUS current
			DESCRIPTION
				"Description."
			::= { ripManagement 13 }


		-- 1.3.6.1.4.1.34592.1.3.100.7.2.13.1
		ripStatusRouteNumEntry OBJECT-TYPE
			SYNTAX RipStatusRouteNumEntry
			MAX-ACCESS not-accessible
			STATUS current
			DESCRIPTION
				"Description."
			INDEX { ripStatusRouteNumDeviceIndex }
			::= { ripStatusRouteNumTable 1 }


		RipStatusRouteNumEntry ::=
			SEQUENCE {
				ripStatusRouteNumDeviceIndex
					NscrtvPonExtDeviceIndex,
				ripStatusRouteHostNumMax
					INTEGER,
				ripStatusRouteHostNumCurrent
					INTEGER,
				ripStatusRouteNetNumMax
					INTEGER,
				ripStatusRouteNetNumCurrent
					INTEGER
			 }

		-- 1.3.6.1.4.1.34592.1.3.100.7.2.13.1.1
		ripStatusRouteNumDeviceIndex OBJECT-TYPE
			SYNTAX NscrtvPonExtDeviceIndex
			MAX-ACCESS not-accessible
			STATUS current
			DESCRIPTION
				"Description."
			::= { ripStatusRouteNumEntry 1 }


		-- 1.3.6.1.4.1.34592.1.3.100.7.2.13.1.2
		ripStatusRouteHostNumMax OBJECT-TYPE
			SYNTAX INTEGER
			MAX-ACCESS read-only
			STATUS current
			DESCRIPTION
				"Description."
			::= { ripStatusRouteNumEntry 2 }


		-- 1.3.6.1.4.1.34592.1.3.100.7.2.13.1.3
		ripStatusRouteHostNumCurrent OBJECT-TYPE
			SYNTAX INTEGER
			MAX-ACCESS read-only
			STATUS current
			DESCRIPTION
				"Description."
			::= { ripStatusRouteNumEntry 3 }


		-- 1.3.6.1.4.1.34592.1.3.100.7.2.13.1.4
		ripStatusRouteNetNumMax OBJECT-TYPE
			SYNTAX INTEGER
			MAX-ACCESS read-only
			STATUS current
			DESCRIPTION
				"Description."
			::= { ripStatusRouteNumEntry 4 }


		-- 1.3.6.1.4.1.34592.1.3.100.7.2.13.1.5
		ripStatusRouteNetNumCurrent OBJECT-TYPE
			SYNTAX INTEGER
			MAX-ACCESS read-only
			STATUS current
			DESCRIPTION
				"Description."
			::= { ripStatusRouteNumEntry 5 }


		-- 1.3.6.1.4.1.34592.1.3.100.7.2.14
		ripStatusRouteEntryTable OBJECT-TYPE
			SYNTAX SEQUENCE OF RipStatusRouteEntryEntry
			MAX-ACCESS not-accessible
			STATUS current
			DESCRIPTION
				"Description."
			::= { ripManagement 14 }


		-- 1.3.6.1.4.1.34592.1.3.100.7.2.14.1
		ripStatusRouteEntryEntry OBJECT-TYPE
			SYNTAX RipStatusRouteEntryEntry
			MAX-ACCESS not-accessible
			STATUS current
			DESCRIPTION
				"Description."
			INDEX { ripStatusRouteEntryIpAddrIndex, ripStatusRouteEntryMaskLenIndex, ripStatusRouteEntryNextHopIndex }
			::= { ripStatusRouteEntryTable 1 }


		RipStatusRouteEntryEntry ::=
			SEQUENCE {
				ripStatusRouteEntryIpAddrIndex
					IpAddress,
				ripStatusRouteEntryMaskLenIndex
					Unsigned32,
				ripStatusRouteEntryNextHopIndex
					IpAddress,
				ripStatusRouteEntryMetric
					Unsigned32,
				ripStatusRouteEntryFlag
					OCTET STRING,
				ripStatusRouteEntryFrom
					OCTET STRING,
				ripStatusRouteEntryTag
					INTEGER,
				ripStatusRouteEntryTime
					OCTET STRING
			 }

		-- 1.3.6.1.4.1.34592.1.3.100.7.2.14.1.4
		ripStatusRouteEntryIpAddrIndex OBJECT-TYPE
			SYNTAX IpAddress
			MAX-ACCESS not-accessible
			STATUS current
			DESCRIPTION
				"Description."
			::= { ripStatusRouteEntryEntry 4 }


		-- 1.3.6.1.4.1.34592.1.3.100.7.2.14.1.5
		ripStatusRouteEntryMaskLenIndex OBJECT-TYPE
			SYNTAX Unsigned32 (0..32)
			MAX-ACCESS not-accessible
			STATUS current
			DESCRIPTION
				"Description."
			::= { ripStatusRouteEntryEntry 5 }


		-- 1.3.6.1.4.1.34592.1.3.100.7.2.14.1.6
		ripStatusRouteEntryNextHopIndex OBJECT-TYPE
			SYNTAX IpAddress
			MAX-ACCESS not-accessible
			STATUS current
			DESCRIPTION
				"Description."
			::= { ripStatusRouteEntryEntry 6 }


		-- 1.3.6.1.4.1.34592.1.3.100.7.2.14.1.7
		ripStatusRouteEntryMetric OBJECT-TYPE
			SYNTAX Unsigned32 (0..16)
			MAX-ACCESS read-only
			STATUS current
			DESCRIPTION
				"Description."
			::= { ripStatusRouteEntryEntry 7 }


		-- 1.3.6.1.4.1.34592.1.3.100.7.2.14.1.8
		ripStatusRouteEntryFlag OBJECT-TYPE
			SYNTAX OCTET STRING
			MAX-ACCESS read-only
			STATUS current
			DESCRIPTION
				"Codes: R - RIP, C - connected, S - Static, O - OSPF, B - BGP
				Sub-codes:
				      (n) - normal, (s) - static, (d) - default, (r) - redistribute,
				      (i) - interface"
			::= { ripStatusRouteEntryEntry 8 }


		-- 1.3.6.1.4.1.34592.1.3.100.7.2.14.1.9
		ripStatusRouteEntryFrom OBJECT-TYPE
			SYNTAX OCTET STRING
			MAX-ACCESS read-only
			STATUS current
			DESCRIPTION
				"Description."
			::= { ripStatusRouteEntryEntry 9 }


		-- 1.3.6.1.4.1.34592.1.3.100.7.2.14.1.10
		ripStatusRouteEntryTag OBJECT-TYPE
			SYNTAX INTEGER
			MAX-ACCESS read-only
			STATUS current
			DESCRIPTION
				"Description."
			::= { ripStatusRouteEntryEntry 10 }


		-- 1.3.6.1.4.1.34592.1.3.100.7.2.14.1.11
		ripStatusRouteEntryTime OBJECT-TYPE
			SYNTAX OCTET STRING
			MAX-ACCESS read-only
			STATUS current
			DESCRIPTION
				"Description."
			::= { ripStatusRouteEntryEntry 11 }


--        1.3.6.1.4.1.34592.1.3.100.8
-- 1.3.6.1.4.1.34592.1.3.100.8
-- 1.3.6.1.4.1.34592.1.3.100.8
-- 1.3.6.1.4.1.34592.1.3.100.8
-- 1.3.6.1.4.1.34592.1.3.100.8
-- 1.3.6.1.4.1.34592.1.3.100.8
-- 1.3.6.1.4.1.34592.1.3.100.8
		-- 1.3.6.1.4.1.34592.1.3.100.8
		ppoeManagementObjects OBJECT IDENTIFIER ::= { nscrtvPonTreeExt 8 }


--        1.3.6.1.4.1.34592.1.3.100.8.1
-- 1.3.6.1.4.1.34592.1.3.100.8.1
-- 1.3.6.1.4.1.34592.1.3.100.8.1
-- 1.3.6.1.4.1.34592.1.3.100.8.1
-- 1.3.6.1.4.1.34592.1.3.100.8.1
-- 1.3.6.1.4.1.34592.1.3.100.8.1
-- 1.3.6.1.4.1.34592.1.3.100.8.1
		-- 1.3.6.1.4.1.34592.1.3.100.8.1
		ppoePlusConfigTable OBJECT-TYPE
			SYNTAX SEQUENCE OF PpoePlusConfigEntry
			MAX-ACCESS not-accessible
			STATUS current
			DESCRIPTION
				"Description."
			::= { ppoeManagementObjects 1 }


--        1.3.6.1.4.1.34592.1.3.100.8.1.1
-- 1.3.6.1.4.1.34592.1.3.100.8.1.1
-- 1.3.6.1.4.1.34592.1.3.100.8.1.1
-- 1.3.6.1.4.1.34592.1.3.100.8.1.1
-- 1.3.6.1.4.1.34592.1.3.100.8.1.1
-- 1.3.6.1.4.1.34592.1.3.100.8.1.1
-- 1.3.6.1.4.1.34592.1.3.100.8.1.1
		-- 1.3.6.1.4.1.34592.1.3.100.8.1.1
		ppoePlusConfigEntry OBJECT-TYPE
			SYNTAX PpoePlusConfigEntry
			MAX-ACCESS not-accessible
			STATUS current
			DESCRIPTION
				"Description."
			INDEX { ppoePlusConfigDeviceIndex }
			::= { ppoePlusConfigTable 1 }


		PpoePlusConfigEntry ::=
			SEQUENCE {
				ppoePlusConfigDeviceIndex
					NscrtvPonExtDeviceIndex,
				ppoePlusConfigEnable
					TruthValue,
				ppoePlusConfigPolicy
					INTEGER,
				ppoePlusConfigFormat
					INTEGER
			 }

--        1.3.6.1.4.1.34592.1.3.100.8.1.1.1
-- 1.3.6.1.4.1.34592.1.3.100.8.1.1.1
-- 1.3.6.1.4.1.34592.1.3.100.8.1.1.1
-- 1.3.6.1.4.1.34592.1.3.100.8.1.1.1
-- 1.3.6.1.4.1.34592.1.3.100.8.1.1.1
-- 1.3.6.1.4.1.34592.1.3.100.8.1.1.1
-- 1.3.6.1.4.1.34592.1.3.100.8.1.1.1
		-- 1.3.6.1.4.1.34592.1.3.100.8.1.1.1
		ppoePlusConfigDeviceIndex OBJECT-TYPE
			SYNTAX NscrtvPonExtDeviceIndex
			MAX-ACCESS not-accessible
			STATUS current
			DESCRIPTION
				"Description."
			::= { ppoePlusConfigEntry 1 }


--        1.3.6.1.4.1.34592.1.3.100.8.1.1.2
-- 1.3.6.1.4.1.34592.1.3.100.8.1.1.2
-- 1.3.6.1.4.1.34592.1.3.100.8.1.1.2
-- 1.3.6.1.4.1.34592.1.3.100.8.1.1.2
-- 1.3.6.1.4.1.34592.1.3.100.8.1.1.2
-- 1.3.6.1.4.1.34592.1.3.100.8.1.1.2
-- 1.3.6.1.4.1.34592.1.3.100.8.1.1.2
		-- 1.3.6.1.4.1.34592.1.3.100.8.1.1.2
		ppoePlusConfigEnable OBJECT-TYPE
			SYNTAX TruthValue
			MAX-ACCESS read-write
			STATUS current
			DESCRIPTION
				"Description."
			::= { ppoePlusConfigEntry 2 }


--        1.3.6.1.4.1.34592.1.3.100.8.1.1.3
-- 1.3.6.1.4.1.34592.1.3.100.8.1.1.3
-- 1.3.6.1.4.1.34592.1.3.100.8.1.1.3
-- 1.3.6.1.4.1.34592.1.3.100.8.1.1.3
-- 1.3.6.1.4.1.34592.1.3.100.8.1.1.3
-- 1.3.6.1.4.1.34592.1.3.100.8.1.1.3
-- 1.3.6.1.4.1.34592.1.3.100.8.1.1.3
		-- 1.3.6.1.4.1.34592.1.3.100.8.1.1.3
		ppoePlusConfigPolicy OBJECT-TYPE
			SYNTAX INTEGER
				{
				keep(1),
				drop(2),
				replace(3)
				}
			MAX-ACCESS read-write
			STATUS current
			DESCRIPTION
				"Description."
			::= { ppoePlusConfigEntry 3 }


--     1.3.6.1.4.1.34592.1.3.100.8.1.1.4
-- 1.3.6.1.4.1.34592.1.3.100.8.1.1.4
-- 1.3.6.1.4.1.34592.1.3.100.8.1.1.4
-- 1.3.6.1.4.1.34592.1.3.100.8.1.1.4
		-- 1.3.6.1.4.1.34592.1.3.100.8.1.1.4
		ppoePlusConfigFormat OBJECT-TYPE
			SYNTAX INTEGER
				{
				type1(1),
				type2(2),
				type3(3),
				type4(4),
				type5(5)
				}
			MAX-ACCESS read-write
			STATUS current
			DESCRIPTION
				"type1                - UNI+ONU MAC
				type2                - UNI+OLT MAC
				type3                - ONU+ONU MAC
				type4                - ONU+OLT MAC
				type5                - PON+OLT MAC
				  "
			::= { ppoePlusConfigEntry 4 }

			--       1.3.6.1.4.1.34592.1.3.100.9
-- 1.3.6.1.4.1.34592.1.3.100.9
-- 1.3.6.1.4.1.34592.1.3.100.9
-- 1.3.6.1.4.1.34592.1.3.100.9
-- 1.3.6.1.4.1.34592.1.3.100.9
-- 1.3.6.1.4.1.34592.1.3.100.9
		-- 1.3.6.1.4.1.34592.1.3.100.9
		servicePortObjects OBJECT IDENTIFIER ::= { nscrtvPonTreeExt 9 }


--       1.3.6.1.4.1.34592.1.3.100.9.1
-- 1.3.6.1.4.1.34592.1.3.100.9.1
-- 1.3.6.1.4.1.34592.1.3.100.9.1
-- 1.3.6.1.4.1.34592.1.3.100.9.1
-- 1.3.6.1.4.1.34592.1.3.100.9.1
-- 1.3.6.1.4.1.34592.1.3.100.9.1
		-- 1.3.6.1.4.1.34592.1.3.100.9.1
		servicePortGlobalInfoTable OBJECT-TYPE
			SYNTAX SEQUENCE OF ServicePortGlobalInfoEntry
			MAX-ACCESS not-accessible
			STATUS current
			DESCRIPTION
				"Description."
			::= { servicePortObjects 1 }


--       1.3.6.1.4.1.34592.1.3.100.9.1.1
-- 1.3.6.1.4.1.34592.1.3.100.9.1.1
-- 1.3.6.1.4.1.34592.1.3.100.9.1.1
-- 1.3.6.1.4.1.34592.1.3.100.9.1.1
-- 1.3.6.1.4.1.34592.1.3.100.9.1.1
-- 1.3.6.1.4.1.34592.1.3.100.9.1.1
		-- 1.3.6.1.4.1.34592.1.3.100.9.1.1
		servicePortGlobalInfoEntry OBJECT-TYPE
			SYNTAX ServicePortGlobalInfoEntry
			MAX-ACCESS not-accessible
			STATUS current
			DESCRIPTION
				"Description."
			INDEX { servicePortGlobalInfoDeviceIndex, servicePortGlobalInfoCardIndex }
			::= { servicePortGlobalInfoTable 1 }


		ServicePortGlobalInfoEntry ::=
			SEQUENCE {
				servicePortGlobalInfoDeviceIndex
					NscrtvPonExtDeviceIndex,
				servicePortGlobalInfoCardIndex
					NscrtvPonExtCardIndex,
				servicePortCfgInfoMaxId
					Unsigned32,
				servicePortGlobalInfoMaxSupportNumber
					Unsigned32,
				servicePortGlobalInfoCreatedNumber
					Unsigned32
			 }

--       1.3.6.1.4.1.34592.1.3.100.9.1.1.1
-- 1.3.6.1.4.1.34592.1.3.100.9.1.1.1
-- 1.3.6.1.4.1.34592.1.3.100.9.1.1.1
-- 1.3.6.1.4.1.34592.1.3.100.9.1.1.1
-- 1.3.6.1.4.1.34592.1.3.100.9.1.1.1
-- 1.3.6.1.4.1.34592.1.3.100.9.1.1.1
		-- 1.3.6.1.4.1.34592.1.3.100.9.1.1.1
		servicePortGlobalInfoDeviceIndex OBJECT-TYPE
			SYNTAX NscrtvPonExtDeviceIndex
			MAX-ACCESS not-accessible
			STATUS current
			DESCRIPTION
				"Description."
			::= { servicePortGlobalInfoEntry 1 }


--       1.3.6.1.4.1.34592.1.3.100.9.1.1.2
-- 1.3.6.1.4.1.34592.1.3.100.9.1.1.2
-- 1.3.6.1.4.1.34592.1.3.100.9.1.1.2
-- 1.3.6.1.4.1.34592.1.3.100.9.1.1.2
-- 1.3.6.1.4.1.34592.1.3.100.9.1.1.2
-- 1.3.6.1.4.1.34592.1.3.100.9.1.1.2
		-- 1.3.6.1.4.1.34592.1.3.100.9.1.1.2
		servicePortGlobalInfoCardIndex OBJECT-TYPE
			SYNTAX NscrtvPonExtCardIndex
			MAX-ACCESS not-accessible
			STATUS current
			DESCRIPTION
				"Description."
			::= { servicePortGlobalInfoEntry 2 }


--       1.3.6.1.4.1.34592.1.3.100.9.1.1.3
-- 1.3.6.1.4.1.34592.1.3.100.9.1.1.3
-- 1.3.6.1.4.1.34592.1.3.100.9.1.1.3
-- 1.3.6.1.4.1.34592.1.3.100.9.1.1.3
-- 1.3.6.1.4.1.34592.1.3.100.9.1.1.3
-- 1.3.6.1.4.1.34592.1.3.100.9.1.1.3
		-- 1.3.6.1.4.1.34592.1.3.100.9.1.1.3
		servicePortCfgInfoMaxId OBJECT-TYPE
			SYNTAX Unsigned32
			MAX-ACCESS read-only
			STATUS current
			DESCRIPTION
				"Description."
			::= { servicePortGlobalInfoEntry 3 }


--       1.3.6.1.4.1.34592.1.3.100.9.1.1.4
-- 1.3.6.1.4.1.34592.1.3.100.9.1.1.4
-- 1.3.6.1.4.1.34592.1.3.100.9.1.1.4
-- 1.3.6.1.4.1.34592.1.3.100.9.1.1.4
-- 1.3.6.1.4.1.34592.1.3.100.9.1.1.4
-- 1.3.6.1.4.1.34592.1.3.100.9.1.1.4
		-- 1.3.6.1.4.1.34592.1.3.100.9.1.1.4
		servicePortGlobalInfoMaxSupportNumber OBJECT-TYPE
			SYNTAX Unsigned32
			MAX-ACCESS read-only
			STATUS current
			DESCRIPTION
				"Description."
			::= { servicePortGlobalInfoEntry 4 }


--       1.3.6.1.4.1.34592.1.3.100.9.1.1.5
-- 1.3.6.1.4.1.34592.1.3.100.9.1.1.5
-- 1.3.6.1.4.1.34592.1.3.100.9.1.1.5
-- 1.3.6.1.4.1.34592.1.3.100.9.1.1.5
-- 1.3.6.1.4.1.34592.1.3.100.9.1.1.5
-- 1.3.6.1.4.1.34592.1.3.100.9.1.1.5
		-- 1.3.6.1.4.1.34592.1.3.100.9.1.1.5
		servicePortGlobalInfoCreatedNumber OBJECT-TYPE
			SYNTAX Unsigned32
			MAX-ACCESS read-only
			STATUS current
			DESCRIPTION
				"Description."
			::= { servicePortGlobalInfoEntry 5 }


--       1.3.6.1.4.1.34592.1.3.100.9.2
-- 1.3.6.1.4.1.34592.1.3.100.9.2
-- 1.3.6.1.4.1.34592.1.3.100.9.2
-- 1.3.6.1.4.1.34592.1.3.100.9.2
-- 1.3.6.1.4.1.34592.1.3.100.9.2
-- 1.3.6.1.4.1.34592.1.3.100.9.2
		-- 1.3.6.1.4.1.34592.1.3.100.9.2
		servicePortCfgInfoTable OBJECT-TYPE
			SYNTAX SEQUENCE OF ServicePortCfgInfoEntry
			MAX-ACCESS not-accessible
			STATUS current
			DESCRIPTION
				"Description."
			::= { servicePortObjects 2 }


--       1.3.6.1.4.1.34592.1.3.100.9.2.1
-- 1.3.6.1.4.1.34592.1.3.100.9.2.1
-- 1.3.6.1.4.1.34592.1.3.100.9.2.1
-- 1.3.6.1.4.1.34592.1.3.100.9.2.1
-- 1.3.6.1.4.1.34592.1.3.100.9.2.1
-- 1.3.6.1.4.1.34592.1.3.100.9.2.1
		-- 1.3.6.1.4.1.34592.1.3.100.9.2.1
		servicePortCfgInfoEntry OBJECT-TYPE
			SYNTAX ServicePortCfgInfoEntry
			MAX-ACCESS not-accessible
			STATUS current
			DESCRIPTION
				"Description."
			INDEX { servicePortCfgInfoDeviceIndex, servicePortCfgInfoCardIndex, servicePortCfgInfoIndex }
			::= { servicePortCfgInfoTable 1 }


		ServicePortCfgInfoEntry ::=
			SEQUENCE {
				servicePortCfgInfoDeviceIndex
					NscrtvPonExtDeviceIndex,
				servicePortCfgInfoCardIndex
					NscrtvPonExtCardIndex,
				servicePortCfgInfoIndex
					Unsigned32,
				servicePortCfgInfoSvlanId
					Unsigned32,
				servicePortCfgInfoPonPortId
					Unsigned32,
				servicePortCfgInfoOnuId
					Unsigned32,
				servicePortCfgInfoGemId
					Unsigned32,
				servicePortCfgInfoUserVlanId
					Unsigned32,
				servicePortCfgInfoUserVlanPri
					Unsigned32,
				servicePortCfgInfoEhterType
					NscrtvPonExtEtherType,
				servicePortCfgInfoUpTrafficProfileId
					Unsigned32,
				servicePortCfgInfoDownTrafficProfileId
					Unsigned32,
				servicePortCfgInfoAdminStatus
					NscrtvPonExtAdminStatus,
				servicePortCfgInfoOnuOnlineState
					NscrtvPonExtOnuOnlineState,
				servicePortCfgInfoVlanTagAction
					NscrtvPonExtVlanTagAction,
				servicePortCfgInfoVlanInnerVid
					Unsigned32,
				servicePortCfgInfoVlanInnerPri
					Unsigned32,
				servicePortCfgInfoDescription
					OCTET STRING,
				servicePortCfgInfoPerfStat
					NscrtvPonExtPerfStat,
				servicePortCfgInfoRowStatus
					RowStatus
			 }

--       1.3.6.1.4.1.34592.1.3.100.9.2.1.1
-- 1.3.6.1.4.1.34592.1.3.100.9.2.1.1
-- 1.3.6.1.4.1.34592.1.3.100.9.2.1.1
-- 1.3.6.1.4.1.34592.1.3.100.9.2.1.1
-- 1.3.6.1.4.1.34592.1.3.100.9.2.1.1
-- 1.3.6.1.4.1.34592.1.3.100.9.2.1.1
		-- 1.3.6.1.4.1.34592.1.3.100.9.2.1.1
		servicePortCfgInfoDeviceIndex OBJECT-TYPE
			SYNTAX NscrtvPonExtDeviceIndex
			MAX-ACCESS not-accessible
			STATUS current
			DESCRIPTION
				"Description."
			::= { servicePortCfgInfoEntry 1 }


--       1.3.6.1.4.1.34592.1.3.100.9.2.1.2
-- 1.3.6.1.4.1.34592.1.3.100.9.2.1.2
-- 1.3.6.1.4.1.34592.1.3.100.9.2.1.2
-- 1.3.6.1.4.1.34592.1.3.100.9.2.1.2
-- 1.3.6.1.4.1.34592.1.3.100.9.2.1.2
-- 1.3.6.1.4.1.34592.1.3.100.9.2.1.2
		-- 1.3.6.1.4.1.34592.1.3.100.9.2.1.2
		servicePortCfgInfoCardIndex OBJECT-TYPE
			SYNTAX NscrtvPonExtCardIndex
			MAX-ACCESS not-accessible
			STATUS current
			DESCRIPTION
				"Description."
			::= { servicePortCfgInfoEntry 2 }


--       1.3.6.1.4.1.34592.1.3.100.9.2.1.3
-- 1.3.6.1.4.1.34592.1.3.100.9.2.1.3
-- 1.3.6.1.4.1.34592.1.3.100.9.2.1.3
-- 1.3.6.1.4.1.34592.1.3.100.9.2.1.3
-- 1.3.6.1.4.1.34592.1.3.100.9.2.1.3
-- 1.3.6.1.4.1.34592.1.3.100.9.2.1.3
		-- 1.3.6.1.4.1.34592.1.3.100.9.2.1.3
		servicePortCfgInfoIndex OBJECT-TYPE
			SYNTAX Unsigned32
			MAX-ACCESS not-accessible
			STATUS current
			DESCRIPTION
				"Description."
			::= { servicePortCfgInfoEntry 3 }


--       1.3.6.1.4.1.34592.1.3.100.9.2.1.4
-- 1.3.6.1.4.1.34592.1.3.100.9.2.1.4
-- 1.3.6.1.4.1.34592.1.3.100.9.2.1.4
-- 1.3.6.1.4.1.34592.1.3.100.9.2.1.4
-- 1.3.6.1.4.1.34592.1.3.100.9.2.1.4
-- 1.3.6.1.4.1.34592.1.3.100.9.2.1.4
		-- 1.3.6.1.4.1.34592.1.3.100.9.2.1.4
		servicePortCfgInfoSvlanId OBJECT-TYPE
			SYNTAX Unsigned32 (0..4094)
			MAX-ACCESS read-create
			STATUS current
			DESCRIPTION
				"Description."
			::= { servicePortCfgInfoEntry 4 }


--       1.3.6.1.4.1.34592.1.3.100.9.2.1.5
-- 1.3.6.1.4.1.34592.1.3.100.9.2.1.5
-- 1.3.6.1.4.1.34592.1.3.100.9.2.1.5
-- 1.3.6.1.4.1.34592.1.3.100.9.2.1.5
-- 1.3.6.1.4.1.34592.1.3.100.9.2.1.5
-- 1.3.6.1.4.1.34592.1.3.100.9.2.1.5
		-- 1.3.6.1.4.1.34592.1.3.100.9.2.1.5
		servicePortCfgInfoPonPortId OBJECT-TYPE
			SYNTAX Unsigned32 (1..8)
			MAX-ACCESS read-create
			STATUS current
			DESCRIPTION
				"Description."
			::= { servicePortCfgInfoEntry 5 }


--       1.3.6.1.4.1.34592.1.3.100.9.2.1.6
-- 1.3.6.1.4.1.34592.1.3.100.9.2.1.6
-- 1.3.6.1.4.1.34592.1.3.100.9.2.1.6
-- 1.3.6.1.4.1.34592.1.3.100.9.2.1.6
-- 1.3.6.1.4.1.34592.1.3.100.9.2.1.6
-- 1.3.6.1.4.1.34592.1.3.100.9.2.1.6
		-- 1.3.6.1.4.1.34592.1.3.100.9.2.1.6
		servicePortCfgInfoOnuId OBJECT-TYPE
			SYNTAX Unsigned32 (1..128)
			MAX-ACCESS read-create
			STATUS current
			DESCRIPTION
				"Description."
			::= { servicePortCfgInfoEntry 6 }


--       1.3.6.1.4.1.34592.1.3.100.9.2.1.7
-- 1.3.6.1.4.1.34592.1.3.100.9.2.1.7
-- 1.3.6.1.4.1.34592.1.3.100.9.2.1.7
-- 1.3.6.1.4.1.34592.1.3.100.9.2.1.7
-- 1.3.6.1.4.1.34592.1.3.100.9.2.1.7
-- 1.3.6.1.4.1.34592.1.3.100.9.2.1.7
		-- 1.3.6.1.4.1.34592.1.3.100.9.2.1.7
		servicePortCfgInfoGemId OBJECT-TYPE
			SYNTAX Unsigned32 (1..30)
			MAX-ACCESS read-create
			STATUS current
			DESCRIPTION
				"Description."
			::= { servicePortCfgInfoEntry 7 }


--       1.3.6.1.4.1.34592.1.3.100.9.2.1.8
-- 1.3.6.1.4.1.34592.1.3.100.9.2.1.8
-- 1.3.6.1.4.1.34592.1.3.100.9.2.1.8
-- 1.3.6.1.4.1.34592.1.3.100.9.2.1.8
-- 1.3.6.1.4.1.34592.1.3.100.9.2.1.8
-- 1.3.6.1.4.1.34592.1.3.100.9.2.1.8
		-- 1.3.6.1.4.1.34592.1.3.100.9.2.1.8
		servicePortCfgInfoUserVlanId OBJECT-TYPE
			SYNTAX Unsigned32 (1..4094)
			MAX-ACCESS read-create
			STATUS current
			DESCRIPTION
				"Description."
			::= { servicePortCfgInfoEntry 8 }


--       1.3.6.1.4.1.34592.1.3.100.9.2.1.9
-- 1.3.6.1.4.1.34592.1.3.100.9.2.1.9
-- 1.3.6.1.4.1.34592.1.3.100.9.2.1.9
-- 1.3.6.1.4.1.34592.1.3.100.9.2.1.9
-- 1.3.6.1.4.1.34592.1.3.100.9.2.1.9
-- 1.3.6.1.4.1.34592.1.3.100.9.2.1.9
		-- 1.3.6.1.4.1.34592.1.3.100.9.2.1.9
		servicePortCfgInfoUserVlanPri OBJECT-TYPE
			SYNTAX Unsigned32 (0..7)
			MAX-ACCESS read-create
			STATUS current
			DESCRIPTION
				"Description."
			::= { servicePortCfgInfoEntry 9 }


--       1.3.6.1.4.1.34592.1.3.100.9.2.1.10
-- 1.3.6.1.4.1.34592.1.3.100.9.2.1.10
-- 1.3.6.1.4.1.34592.1.3.100.9.2.1.10
-- 1.3.6.1.4.1.34592.1.3.100.9.2.1.10
-- 1.3.6.1.4.1.34592.1.3.100.9.2.1.10
-- 1.3.6.1.4.1.34592.1.3.100.9.2.1.10
		-- 1.3.6.1.4.1.34592.1.3.100.9.2.1.10
		servicePortCfgInfoEhterType OBJECT-TYPE
			SYNTAX NscrtvPonExtEtherType
			MAX-ACCESS read-create
			STATUS current
			DESCRIPTION
				"Description."
			::= { servicePortCfgInfoEntry 10 }


--       1.3.6.1.4.1.34592.1.3.100.9.2.1.11
-- 1.3.6.1.4.1.34592.1.3.100.9.2.1.11
-- 1.3.6.1.4.1.34592.1.3.100.9.2.1.11
-- 1.3.6.1.4.1.34592.1.3.100.9.2.1.11
-- 1.3.6.1.4.1.34592.1.3.100.9.2.1.11
-- 1.3.6.1.4.1.34592.1.3.100.9.2.1.11
		-- 1.3.6.1.4.1.34592.1.3.100.9.2.1.11
		servicePortCfgInfoUpTrafficProfileId OBJECT-TYPE
			SYNTAX Unsigned32 (0..256)
			MAX-ACCESS read-create
			STATUS current
			DESCRIPTION
				"Description."
			::= { servicePortCfgInfoEntry 11 }


--       1.3.6.1.4.1.34592.1.3.100.9.2.1.12
-- 1.3.6.1.4.1.34592.1.3.100.9.2.1.12
-- 1.3.6.1.4.1.34592.1.3.100.9.2.1.12
-- 1.3.6.1.4.1.34592.1.3.100.9.2.1.12
-- 1.3.6.1.4.1.34592.1.3.100.9.2.1.12
-- 1.3.6.1.4.1.34592.1.3.100.9.2.1.12
		-- 1.3.6.1.4.1.34592.1.3.100.9.2.1.12
		servicePortCfgInfoDownTrafficProfileId OBJECT-TYPE
			SYNTAX Unsigned32 (0..256)
			MAX-ACCESS read-create
			STATUS current
			DESCRIPTION
				"Description."
			::= { servicePortCfgInfoEntry 12 }


--       1.3.6.1.4.1.34592.1.3.100.9.2.1.14
-- 1.3.6.1.4.1.34592.1.3.100.9.2.1.13
-- 1.3.6.1.4.1.34592.1.3.100.9.2.1.13
-- 1.3.6.1.4.1.34592.1.3.100.9.2.1.13
-- 1.3.6.1.4.1.34592.1.3.100.9.2.1.13
-- 1.3.6.1.4.1.34592.1.3.100.9.2.1.13
		-- 1.3.6.1.4.1.34592.1.3.100.9.2.1.13
		servicePortCfgInfoAdminStatus OBJECT-TYPE
			SYNTAX NscrtvPonExtAdminStatus
			MAX-ACCESS read-write
			STATUS current
			DESCRIPTION
				"Description."
			::= { servicePortCfgInfoEntry 13 }


--       1.3.6.1.4.1.34592.1.3.100.9.2.1.15
-- 1.3.6.1.4.1.34592.1.3.100.9.2.1.14
-- 1.3.6.1.4.1.34592.1.3.100.9.2.1.14
-- 1.3.6.1.4.1.34592.1.3.100.9.2.1.14
-- 1.3.6.1.4.1.34592.1.3.100.9.2.1.14
-- 1.3.6.1.4.1.34592.1.3.100.9.2.1.14
		-- 1.3.6.1.4.1.34592.1.3.100.9.2.1.14
		servicePortCfgInfoOnuOnlineState OBJECT-TYPE
			SYNTAX NscrtvPonExtOnuOnlineState
			MAX-ACCESS read-only
			STATUS current
			DESCRIPTION
				"Description."
			::= { servicePortCfgInfoEntry 14 }


--       1.3.6.1.4.1.34592.1.3.100.9.2.1.16
-- 1.3.6.1.4.1.34592.1.3.100.9.2.1.15
-- 1.3.6.1.4.1.34592.1.3.100.9.2.1.15
-- 1.3.6.1.4.1.34592.1.3.100.9.2.1.15
-- 1.3.6.1.4.1.34592.1.3.100.9.2.1.15
-- 1.3.6.1.4.1.34592.1.3.100.9.2.1.15
		-- 1.3.6.1.4.1.34592.1.3.100.9.2.1.15
		servicePortCfgInfoVlanTagAction OBJECT-TYPE
			SYNTAX NscrtvPonExtVlanTagAction
			MAX-ACCESS read-create
			STATUS current
			DESCRIPTION
				"Description."
			::= { servicePortCfgInfoEntry 15 }


--       1.3.6.1.4.1.34592.1.3.100.9.2.1.17
-- 1.3.6.1.4.1.34592.1.3.100.9.2.1.16
-- 1.3.6.1.4.1.34592.1.3.100.9.2.1.16
-- 1.3.6.1.4.1.34592.1.3.100.9.2.1.16
-- 1.3.6.1.4.1.34592.1.3.100.9.2.1.16
-- 1.3.6.1.4.1.34592.1.3.100.9.2.1.16
		-- 1.3.6.1.4.1.34592.1.3.100.9.2.1.16
		servicePortCfgInfoVlanInnerVid OBJECT-TYPE
			SYNTAX Unsigned32 (1..4094)
			MAX-ACCESS read-create
			STATUS current
			DESCRIPTION
				"Description."
			::= { servicePortCfgInfoEntry 16 }


--       1.3.6.1.4.1.34592.1.3.100.9.2.1.18
-- 1.3.6.1.4.1.34592.1.3.100.9.2.1.17
-- 1.3.6.1.4.1.34592.1.3.100.9.2.1.17
-- 1.3.6.1.4.1.34592.1.3.100.9.2.1.17
-- 1.3.6.1.4.1.34592.1.3.100.9.2.1.17
-- 1.3.6.1.4.1.34592.1.3.100.9.2.1.17
		-- 1.3.6.1.4.1.34592.1.3.100.9.2.1.17
		servicePortCfgInfoVlanInnerPri OBJECT-TYPE
			SYNTAX Unsigned32 (0..7)
			MAX-ACCESS read-create
			STATUS current
			DESCRIPTION
				"Description."
			::= { servicePortCfgInfoEntry 17 }


--       1.3.6.1.4.1.34592.1.3.100.9.2.1.19
-- 1.3.6.1.4.1.34592.1.3.100.9.2.1.18
-- 1.3.6.1.4.1.34592.1.3.100.9.2.1.18
-- 1.3.6.1.4.1.34592.1.3.100.9.2.1.18
-- 1.3.6.1.4.1.34592.1.3.100.9.2.1.18
-- 1.3.6.1.4.1.34592.1.3.100.9.2.1.18
		-- 1.3.6.1.4.1.34592.1.3.100.9.2.1.18
		servicePortCfgInfoDescription OBJECT-TYPE
			SYNTAX OCTET STRING (SIZE (0..64))
			MAX-ACCESS read-write
			STATUS current
			DESCRIPTION
				"Description."
			::= { servicePortCfgInfoEntry 18 }


--       1.3.6.1.4.1.34592.1.3.100.9.2.1.20
-- 1.3.6.1.4.1.34592.1.3.100.9.2.1.19
-- 1.3.6.1.4.1.34592.1.3.100.9.2.1.19
-- 1.3.6.1.4.1.34592.1.3.100.9.2.1.19
-- 1.3.6.1.4.1.34592.1.3.100.9.2.1.19
-- 1.3.6.1.4.1.34592.1.3.100.9.2.1.19
		-- 1.3.6.1.4.1.34592.1.3.100.9.2.1.19
		servicePortCfgInfoPerfStat OBJECT-TYPE
			SYNTAX NscrtvPonExtPerfStat
			MAX-ACCESS read-write
			STATUS current
			DESCRIPTION
				"Description."
			::= { servicePortCfgInfoEntry 19 }


--    1.3.6.1.4.1.34592.1.3.100.9.2.1.20
-- 1.3.6.1.4.1.34592.1.3.100.9.2.1.20
-- 1.3.6.1.4.1.34592.1.3.100.9.2.1.20
		-- 1.3.6.1.4.1.34592.1.3.100.9.2.1.20
		servicePortCfgInfoRowStatus OBJECT-TYPE
			SYNTAX RowStatus
			MAX-ACCESS read-create
			STATUS current
			DESCRIPTION
				"Description."
			::= { servicePortCfgInfoEntry 20 }


--       1.3.6.1.4.1.34592.1.3.100.9.3
-- 1.3.6.1.4.1.34592.1.3.100.9.3
-- 1.3.6.1.4.1.34592.1.3.100.9.3
-- 1.3.6.1.4.1.34592.1.3.100.9.3
-- 1.3.6.1.4.1.34592.1.3.100.9.3
-- 1.3.6.1.4.1.34592.1.3.100.9.3
		-- 1.3.6.1.4.1.34592.1.3.100.9.3
		servicePortAutoCfgInfoTable OBJECT-TYPE
			SYNTAX SEQUENCE OF ServicePortAutoCfgInfoEntry
			MAX-ACCESS not-accessible
			STATUS current
			DESCRIPTION
				"Description."
			::= { servicePortObjects 3 }


--       1.3.6.1.4.1.34592.1.3.100.9.3.1
-- 1.3.6.1.4.1.34592.1.3.100.9.3.1
-- 1.3.6.1.4.1.34592.1.3.100.9.3.1
-- 1.3.6.1.4.1.34592.1.3.100.9.3.1
-- 1.3.6.1.4.1.34592.1.3.100.9.3.1
-- 1.3.6.1.4.1.34592.1.3.100.9.3.1
		-- 1.3.6.1.4.1.34592.1.3.100.9.3.1
		servicePortAutoCfgInfoEntry OBJECT-TYPE
			SYNTAX ServicePortAutoCfgInfoEntry
			MAX-ACCESS not-accessible
			STATUS current
			DESCRIPTION
				"Description."
			INDEX { servicePortAutoCfgInfoDeviceIndex, servicePortAutoCfgInfoCardIndex, servicePortAutoCfgInfoPonPortIndex }
			::= { servicePortAutoCfgInfoTable 1 }


		ServicePortAutoCfgInfoEntry ::=
			SEQUENCE {
				servicePortAutoCfgInfoDeviceIndex
					NscrtvPonExtDeviceIndex,
				servicePortAutoCfgInfoCardIndex
					NscrtvPonExtCardIndex,
				servicePortAutoCfgInfoPonPortIndex
					Unsigned32,
				servicePortAutoCfgInfoSvlanId
					Unsigned32,
				servicePortAutoCfgInfoGemId
					Unsigned32,
				servicePortAutoCfgInfoUserVlanId
					Unsigned32,
				servicePortAutoCfgInfoVlanTagAction
					NscrtvPonExtVlanTagAction,
				servicePortAutoCfgInfoVlanInnerVid
					Unsigned32,
				servicePortAutoCfgInfoVlanInnerPri
					Unsigned32,
				servicePortAutoCfgInfoUpTrafficProfileId
					Unsigned32,
				servicePortAutoCfgInfoDownTrafficProfileId
					Unsigned32,
				servicePortAutoCfgInfoMode
					NscrtvPonExtAutoMode
			 }

--       1.3.6.1.4.1.34592.1.3.100.9.3.1.1
-- 1.3.6.1.4.1.34592.1.3.100.9.3.1.1
-- 1.3.6.1.4.1.34592.1.3.100.9.3.1.1
-- 1.3.6.1.4.1.34592.1.3.100.9.3.1.1
-- 1.3.6.1.4.1.34592.1.3.100.9.3.1.1
-- 1.3.6.1.4.1.34592.1.3.100.9.3.1.1
		-- 1.3.6.1.4.1.34592.1.3.100.9.3.1.1
		servicePortAutoCfgInfoDeviceIndex OBJECT-TYPE
			SYNTAX NscrtvPonExtDeviceIndex
			MAX-ACCESS not-accessible
			STATUS current
			DESCRIPTION
				"Description."
			::= { servicePortAutoCfgInfoEntry 1 }


--       1.3.6.1.4.1.34592.1.3.100.9.3.1.2
-- 1.3.6.1.4.1.34592.1.3.100.9.3.1.2
-- 1.3.6.1.4.1.34592.1.3.100.9.3.1.2
-- 1.3.6.1.4.1.34592.1.3.100.9.3.1.2
-- 1.3.6.1.4.1.34592.1.3.100.9.3.1.2
-- 1.3.6.1.4.1.34592.1.3.100.9.3.1.2
		-- 1.3.6.1.4.1.34592.1.3.100.9.3.1.2
		servicePortAutoCfgInfoCardIndex OBJECT-TYPE
			SYNTAX NscrtvPonExtCardIndex
			MAX-ACCESS not-accessible
			STATUS current
			DESCRIPTION
				"Description."
			::= { servicePortAutoCfgInfoEntry 2 }


--       1.3.6.1.4.1.34592.1.3.100.9.3.1.3
-- 1.3.6.1.4.1.34592.1.3.100.9.3.1.3
-- 1.3.6.1.4.1.34592.1.3.100.9.3.1.3
-- 1.3.6.1.4.1.34592.1.3.100.9.3.1.3
-- 1.3.6.1.4.1.34592.1.3.100.9.3.1.3
-- 1.3.6.1.4.1.34592.1.3.100.9.3.1.3
		-- 1.3.6.1.4.1.34592.1.3.100.9.3.1.3
		servicePortAutoCfgInfoPonPortIndex OBJECT-TYPE
			SYNTAX Unsigned32
			MAX-ACCESS not-accessible
			STATUS current
			DESCRIPTION
				"Description."
			::= { servicePortAutoCfgInfoEntry 3 }


--       1.3.6.1.4.1.34592.1.3.100.9.3.1.4
-- 1.3.6.1.4.1.34592.1.3.100.9.3.1.4
-- 1.3.6.1.4.1.34592.1.3.100.9.3.1.4
-- 1.3.6.1.4.1.34592.1.3.100.9.3.1.4
-- 1.3.6.1.4.1.34592.1.3.100.9.3.1.4
-- 1.3.6.1.4.1.34592.1.3.100.9.3.1.4
		-- 1.3.6.1.4.1.34592.1.3.100.9.3.1.4
		servicePortAutoCfgInfoSvlanId OBJECT-TYPE
			SYNTAX Unsigned32 (1..4094)
			MAX-ACCESS read-write
			STATUS current
			DESCRIPTION
				"Description."
			::= { servicePortAutoCfgInfoEntry 4 }


--       1.3.6.1.4.1.34592.1.3.100.9.3.1.5
-- 1.3.6.1.4.1.34592.1.3.100.9.3.1.5
-- 1.3.6.1.4.1.34592.1.3.100.9.3.1.5
-- 1.3.6.1.4.1.34592.1.3.100.9.3.1.5
-- 1.3.6.1.4.1.34592.1.3.100.9.3.1.5
-- 1.3.6.1.4.1.34592.1.3.100.9.3.1.5
		-- 1.3.6.1.4.1.34592.1.3.100.9.3.1.5
		servicePortAutoCfgInfoGemId OBJECT-TYPE
			SYNTAX Unsigned32 (1..30)
			MAX-ACCESS read-write
			STATUS current
			DESCRIPTION
				"Description."
			::= { servicePortAutoCfgInfoEntry 5 }


--       1.3.6.1.4.1.34592.1.3.100.9.3.1.6
-- 1.3.6.1.4.1.34592.1.3.100.9.3.1.6
-- 1.3.6.1.4.1.34592.1.3.100.9.3.1.6
-- 1.3.6.1.4.1.34592.1.3.100.9.3.1.6
-- 1.3.6.1.4.1.34592.1.3.100.9.3.1.6
-- 1.3.6.1.4.1.34592.1.3.100.9.3.1.6
		-- 1.3.6.1.4.1.34592.1.3.100.9.3.1.6
		servicePortAutoCfgInfoUserVlanId OBJECT-TYPE
			SYNTAX Unsigned32 (0..4094)
			MAX-ACCESS read-write
			STATUS current
			DESCRIPTION
				"Description."
			::= { servicePortAutoCfgInfoEntry 6 }


--       1.3.6.1.4.1.34592.1.3.100.9.3.1.8
-- 1.3.6.1.4.1.34592.1.3.100.9.3.1.7
-- 1.3.6.1.4.1.34592.1.3.100.9.3.1.7
-- 1.3.6.1.4.1.34592.1.3.100.9.3.1.7
-- 1.3.6.1.4.1.34592.1.3.100.9.3.1.7
-- 1.3.6.1.4.1.34592.1.3.100.9.3.1.7
		-- 1.3.6.1.4.1.34592.1.3.100.9.3.1.7
		servicePortAutoCfgInfoVlanTagAction OBJECT-TYPE
			SYNTAX NscrtvPonExtVlanTagAction
			MAX-ACCESS read-write
			STATUS current
			DESCRIPTION
				"Description."
			::= { servicePortAutoCfgInfoEntry 7 }


--       1.3.6.1.4.1.34592.1.3.100.9.3.1.9
-- 1.3.6.1.4.1.34592.1.3.100.9.3.1.8
-- 1.3.6.1.4.1.34592.1.3.100.9.3.1.8
-- 1.3.6.1.4.1.34592.1.3.100.9.3.1.8
-- 1.3.6.1.4.1.34592.1.3.100.9.3.1.8
-- 1.3.6.1.4.1.34592.1.3.100.9.3.1.8
		-- 1.3.6.1.4.1.34592.1.3.100.9.3.1.8
		servicePortAutoCfgInfoVlanInnerVid OBJECT-TYPE
			SYNTAX Unsigned32 (1..4094)
			MAX-ACCESS read-write
			STATUS current
			DESCRIPTION
				"Description."
			::= { servicePortAutoCfgInfoEntry 8 }


--       1.3.6.1.4.1.34592.1.3.100.9.3.1.10
-- 1.3.6.1.4.1.34592.1.3.100.9.3.1.9
-- 1.3.6.1.4.1.34592.1.3.100.9.3.1.9
-- 1.3.6.1.4.1.34592.1.3.100.9.3.1.9
-- 1.3.6.1.4.1.34592.1.3.100.9.3.1.9
-- 1.3.6.1.4.1.34592.1.3.100.9.3.1.9
		-- 1.3.6.1.4.1.34592.1.3.100.9.3.1.9
		servicePortAutoCfgInfoVlanInnerPri OBJECT-TYPE
			SYNTAX Unsigned32 (0..7)
			MAX-ACCESS read-write
			STATUS current
			DESCRIPTION
				"Description."
			::= { servicePortAutoCfgInfoEntry 9 }


--       1.3.6.1.4.1.34592.1.3.100.9.3.1.11
-- 1.3.6.1.4.1.34592.1.3.100.9.3.1.10
-- 1.3.6.1.4.1.34592.1.3.100.9.3.1.10
-- 1.3.6.1.4.1.34592.1.3.100.9.3.1.10
-- 1.3.6.1.4.1.34592.1.3.100.9.3.1.10
-- 1.3.6.1.4.1.34592.1.3.100.9.3.1.10
		-- 1.3.6.1.4.1.34592.1.3.100.9.3.1.10
		servicePortAutoCfgInfoUpTrafficProfileId OBJECT-TYPE
			SYNTAX Unsigned32 (0..256)
			MAX-ACCESS read-write
			STATUS current
			DESCRIPTION
				"Description."
			::= { servicePortAutoCfgInfoEntry 10 }


--       1.3.6.1.4.1.34592.1.3.100.9.3.1.13
-- 1.3.6.1.4.1.34592.1.3.100.9.3.1.11
-- 1.3.6.1.4.1.34592.1.3.100.9.3.1.11
-- 1.3.6.1.4.1.34592.1.3.100.9.3.1.11
-- 1.3.6.1.4.1.34592.1.3.100.9.3.1.11
-- 1.3.6.1.4.1.34592.1.3.100.9.3.1.11
		-- 1.3.6.1.4.1.34592.1.3.100.9.3.1.11
		servicePortAutoCfgInfoDownTrafficProfileId OBJECT-TYPE
			SYNTAX Unsigned32 (0..256)
			MAX-ACCESS read-write
			STATUS current
			DESCRIPTION
				"Description."
			::= { servicePortAutoCfgInfoEntry 11 }


--       1.3.6.1.4.1.34592.1.3.100.9.3.1.15
-- 1.3.6.1.4.1.34592.1.3.100.9.3.1.12
-- 1.3.6.1.4.1.34592.1.3.100.9.3.1.12
-- 1.3.6.1.4.1.34592.1.3.100.9.3.1.12
-- 1.3.6.1.4.1.34592.1.3.100.9.3.1.12
-- 1.3.6.1.4.1.34592.1.3.100.9.3.1.12
		-- 1.3.6.1.4.1.34592.1.3.100.9.3.1.12
		servicePortAutoCfgInfoMode OBJECT-TYPE
			SYNTAX NscrtvPonExtAutoMode
			MAX-ACCESS read-write
			STATUS current
			DESCRIPTION
				"Description."
			::= { servicePortAutoCfgInfoEntry 12 }


--       1.3.6.1.4.1.34592.1.3.100.9.4
-- 1.3.6.1.4.1.34592.1.3.100.9.4
-- 1.3.6.1.4.1.34592.1.3.100.9.4
-- 1.3.6.1.4.1.34592.1.3.100.9.4
-- 1.3.6.1.4.1.34592.1.3.100.9.4
-- 1.3.6.1.4.1.34592.1.3.100.9.4
		-- 1.3.6.1.4.1.34592.1.3.100.9.4
		servicePortCurPerfStatTable OBJECT-TYPE
			SYNTAX SEQUENCE OF ServicePortCurPerfStatEntry
			MAX-ACCESS not-accessible
			STATUS current
			DESCRIPTION
				"Description."
			::= { servicePortObjects 4 }


--       1.3.6.1.4.1.34592.1.3.100.9.4.1
-- 1.3.6.1.4.1.34592.1.3.100.9.4.1
-- 1.3.6.1.4.1.34592.1.3.100.9.4.1
-- 1.3.6.1.4.1.34592.1.3.100.9.4.1
-- 1.3.6.1.4.1.34592.1.3.100.9.4.1
-- 1.3.6.1.4.1.34592.1.3.100.9.4.1
		-- 1.3.6.1.4.1.34592.1.3.100.9.4.1
		servicePortCurPerfStatEntry OBJECT-TYPE
			SYNTAX ServicePortCurPerfStatEntry
			MAX-ACCESS not-accessible
			STATUS current
			DESCRIPTION
				"Description."
			INDEX { servicePortCurPerfStatDeviceIndex, servicePortCurPerfStatCardIndex, servicePortCurPerfStatIndex }
			::= { servicePortCurPerfStatTable 1 }


		ServicePortCurPerfStatEntry ::=
			SEQUENCE {
				servicePortCurPerfStatDeviceIndex
					NscrtvPonExtDeviceIndex,
				servicePortCurPerfStatCardIndex
					NscrtvPonExtCardIndex,
				servicePortCurPerfStatIndex
					Unsigned32,
				servicePortCurPerfStatOutOctets
					Counter64,
				servicePortCurPerfStatOutPkts
					Counter64,
				servicePortCurPerfStatInOctets
					Counter64,
				servicePortCurPerfStatInPkts
					Counter64,
				servicePortCurPerfStatClear
					NscrtvPonExtCurPerfStatClear
			 }

--       1.3.6.1.4.1.34592.1.3.100.9.4.1.1
-- 1.3.6.1.4.1.34592.1.3.100.9.4.1.1
-- 1.3.6.1.4.1.34592.1.3.100.9.4.1.1
-- 1.3.6.1.4.1.34592.1.3.100.9.4.1.1
-- 1.3.6.1.4.1.34592.1.3.100.9.4.1.1
-- 1.3.6.1.4.1.34592.1.3.100.9.4.1.1
		-- 1.3.6.1.4.1.34592.1.3.100.9.4.1.1
		servicePortCurPerfStatDeviceIndex OBJECT-TYPE
			SYNTAX NscrtvPonExtDeviceIndex
			MAX-ACCESS not-accessible
			STATUS current
			DESCRIPTION
				"Description."
			::= { servicePortCurPerfStatEntry 1 }


--       1.3.6.1.4.1.34592.1.3.100.9.4.1.2
-- 1.3.6.1.4.1.34592.1.3.100.9.4.1.2
-- 1.3.6.1.4.1.34592.1.3.100.9.4.1.2
-- 1.3.6.1.4.1.34592.1.3.100.9.4.1.2
-- 1.3.6.1.4.1.34592.1.3.100.9.4.1.2
-- 1.3.6.1.4.1.34592.1.3.100.9.4.1.2
		-- 1.3.6.1.4.1.34592.1.3.100.9.4.1.2
		servicePortCurPerfStatCardIndex OBJECT-TYPE
			SYNTAX NscrtvPonExtCardIndex
			MAX-ACCESS not-accessible
			STATUS current
			DESCRIPTION
				"Description."
			::= { servicePortCurPerfStatEntry 2 }


--       1.3.6.1.4.1.34592.1.3.100.9.4.1.3
-- 1.3.6.1.4.1.34592.1.3.100.9.4.1.3
-- 1.3.6.1.4.1.34592.1.3.100.9.4.1.3
-- 1.3.6.1.4.1.34592.1.3.100.9.4.1.3
-- 1.3.6.1.4.1.34592.1.3.100.9.4.1.3
-- 1.3.6.1.4.1.34592.1.3.100.9.4.1.3
		-- 1.3.6.1.4.1.34592.1.3.100.9.4.1.3
		servicePortCurPerfStatIndex OBJECT-TYPE
			SYNTAX Unsigned32
			MAX-ACCESS not-accessible
			STATUS current
			DESCRIPTION
				"Description."
			::= { servicePortCurPerfStatEntry 3 }


--       1.3.6.1.4.1.34592.1.3.100.9.4.1.4
-- 1.3.6.1.4.1.34592.1.3.100.9.4.1.4
-- 1.3.6.1.4.1.34592.1.3.100.9.4.1.4
-- 1.3.6.1.4.1.34592.1.3.100.9.4.1.4
-- 1.3.6.1.4.1.34592.1.3.100.9.4.1.4
-- 1.3.6.1.4.1.34592.1.3.100.9.4.1.4
		-- 1.3.6.1.4.1.34592.1.3.100.9.4.1.4
		servicePortCurPerfStatOutOctets OBJECT-TYPE
			SYNTAX Counter64
			UNITS "bytes"
			MAX-ACCESS read-only
			STATUS current
			DESCRIPTION
				"Description."
			::= { servicePortCurPerfStatEntry 4 }


--       1.3.6.1.4.1.34592.1.3.100.9.4.1.5
-- 1.3.6.1.4.1.34592.1.3.100.9.4.1.5
-- 1.3.6.1.4.1.34592.1.3.100.9.4.1.5
-- 1.3.6.1.4.1.34592.1.3.100.9.4.1.5
-- 1.3.6.1.4.1.34592.1.3.100.9.4.1.5
-- 1.3.6.1.4.1.34592.1.3.100.9.4.1.5
		-- 1.3.6.1.4.1.34592.1.3.100.9.4.1.5
		servicePortCurPerfStatOutPkts OBJECT-TYPE
			SYNTAX Counter64
			MAX-ACCESS read-only
			STATUS current
			DESCRIPTION
				"Description."
			::= { servicePortCurPerfStatEntry 5 }


--       1.3.6.1.4.1.34592.1.3.100.9.4.1.6
-- 1.3.6.1.4.1.34592.1.3.100.9.4.1.6
-- 1.3.6.1.4.1.34592.1.3.100.9.4.1.6
-- 1.3.6.1.4.1.34592.1.3.100.9.4.1.6
-- 1.3.6.1.4.1.34592.1.3.100.9.4.1.6
-- 1.3.6.1.4.1.34592.1.3.100.9.4.1.6
		-- 1.3.6.1.4.1.34592.1.3.100.9.4.1.6
		servicePortCurPerfStatInOctets OBJECT-TYPE
			SYNTAX Counter64
			UNITS "bytes"
			MAX-ACCESS read-only
			STATUS current
			DESCRIPTION
				"Description."
			::= { servicePortCurPerfStatEntry 6 }


--       1.3.6.1.4.1.34592.1.3.100.9.4.1.7
-- 1.3.6.1.4.1.34592.1.3.100.9.4.1.7
-- 1.3.6.1.4.1.34592.1.3.100.9.4.1.7
-- 1.3.6.1.4.1.34592.1.3.100.9.4.1.7
-- 1.3.6.1.4.1.34592.1.3.100.9.4.1.7
-- 1.3.6.1.4.1.34592.1.3.100.9.4.1.7
		-- 1.3.6.1.4.1.34592.1.3.100.9.4.1.7
		servicePortCurPerfStatInPkts OBJECT-TYPE
			SYNTAX Counter64
			MAX-ACCESS read-only
			STATUS current
			DESCRIPTION
				"Description."
			::= { servicePortCurPerfStatEntry 7 }


--      1.3.6.1.4.1.34592.1.3.100.9.4.1.8
-- 1.3.6.1.4.1.34592.1.3.100.9.4.1.8
-- 1.3.6.1.4.1.34592.1.3.100.9.4.1.8
-- 1.3.6.1.4.1.34592.1.3.100.9.4.1.8
-- 1.3.6.1.4.1.34592.1.3.100.9.4.1.8
		-- 1.3.6.1.4.1.34592.1.3.100.9.4.1.8
		servicePortCurPerfStatClear OBJECT-TYPE
			SYNTAX NscrtvPonExtCurPerfStatClear
			MAX-ACCESS read-write
			STATUS current
			DESCRIPTION
				"Description."
			::= { servicePortCurPerfStatEntry 8 }


--     1.3.6.1.4.1.34592.1.3.100.10
-- 1.3.6.1.4.1.34592.1.3.100.10
-- 1.3.6.1.4.1.34592.1.3.100.10
-- 1.3.6.1.4.1.34592.1.3.100.10
		-- 1.3.6.1.4.1.34592.1.3.100.10
		loopBackDetectionManagementObjects OBJECT IDENTIFIER ::= { nscrtvPonTreeExt 10 }


--     1.3.6.1.4.1.34592.1.3.100.10.1
-- 1.3.6.1.4.1.34592.1.3.100.10.1
-- 1.3.6.1.4.1.34592.1.3.100.10.1
-- 1.3.6.1.4.1.34592.1.3.100.10.1
		-- 1.3.6.1.4.1.34592.1.3.100.10.1
		loopBackDetectionGlobalSetTable OBJECT-TYPE
			SYNTAX SEQUENCE OF LoopBackDetectionGlobalSetEntry
			MAX-ACCESS not-accessible
			STATUS current
			DESCRIPTION
				"Description."
			::= { loopBackDetectionManagementObjects 1 }


--     1.3.6.1.4.1.34592.1.3.100.10.1.1
-- 1.3.6.1.4.1.34592.1.3.100.10.1.1
-- 1.3.6.1.4.1.34592.1.3.100.10.1.1
-- 1.3.6.1.4.1.34592.1.3.100.10.1.1
		-- 1.3.6.1.4.1.34592.1.3.100.10.1.1
		loopBackDetectionGlobalSetEntry OBJECT-TYPE
			SYNTAX LoopBackDetectionGlobalSetEntry
			MAX-ACCESS not-accessible
			STATUS current
			DESCRIPTION
				"Description."
			INDEX { loopBackDetectionGloabDeviceIndex }
			::= { loopBackDetectionGlobalSetTable 1 }


		LoopBackDetectionGlobalSetEntry ::=
			SEQUENCE {
				loopBackDetectionGloabDeviceIndex
					NscrtvPonExtDeviceIndex,
				loopBackDetectionGlobalEnable
					TruthValue,
				loopBackDetectionGlobalInterval
					Unsigned32
			 }

--     1.3.6.1.4.1.34592.1.3.100.10.1.1.1
-- 1.3.6.1.4.1.34592.1.3.100.10.1.1.1
-- 1.3.6.1.4.1.34592.1.3.100.10.1.1.1
-- 1.3.6.1.4.1.34592.1.3.100.10.1.1.1
		-- 1.3.6.1.4.1.34592.1.3.100.10.1.1.1
		loopBackDetectionGloabDeviceIndex OBJECT-TYPE
			SYNTAX NscrtvPonExtDeviceIndex
			MAX-ACCESS not-accessible
			STATUS current
			DESCRIPTION
				"Description."
			::= { loopBackDetectionGlobalSetEntry 1 }


--     1.3.6.1.4.1.34592.1.3.100.10.1.1.2
-- 1.3.6.1.4.1.34592.1.3.100.10.1.1.2
-- 1.3.6.1.4.1.34592.1.3.100.10.1.1.2
-- 1.3.6.1.4.1.34592.1.3.100.10.1.1.2
		-- 1.3.6.1.4.1.34592.1.3.100.10.1.1.2
		loopBackDetectionGlobalEnable OBJECT-TYPE
			SYNTAX TruthValue
			MAX-ACCESS read-write
			STATUS current
			DESCRIPTION
				"Description."
			::= { loopBackDetectionGlobalSetEntry 2 }


--     1.3.6.1.4.1.34592.1.3.100.10.1.1.3
-- 1.3.6.1.4.1.34592.1.3.100.10.1.1.3
-- 1.3.6.1.4.1.34592.1.3.100.10.1.1.3
-- 1.3.6.1.4.1.34592.1.3.100.10.1.1.3
		-- 1.3.6.1.4.1.34592.1.3.100.10.1.1.3
		loopBackDetectionGlobalInterval OBJECT-TYPE
			SYNTAX Unsigned32 (5..300)
			MAX-ACCESS read-write
			STATUS current
			DESCRIPTION
				"Description."
			::= { loopBackDetectionGlobalSetEntry 3 }


--     1.3.6.1.4.1.34592.1.3.100.10.2
-- 1.3.6.1.4.1.34592.1.3.100.10.2
-- 1.3.6.1.4.1.34592.1.3.100.10.2
-- 1.3.6.1.4.1.34592.1.3.100.10.2
		-- 1.3.6.1.4.1.34592.1.3.100.10.2
		loopBackDetectionPortConfigTable OBJECT-TYPE
			SYNTAX SEQUENCE OF LoopBackDetectionPortConfigEntry
			MAX-ACCESS not-accessible
			STATUS current
			DESCRIPTION
				"Description."
			::= { loopBackDetectionManagementObjects 2 }


--     1.3.6.1.4.1.34592.1.3.100.10.2.1
-- 1.3.6.1.4.1.34592.1.3.100.10.2.1
-- 1.3.6.1.4.1.34592.1.3.100.10.2.1
-- 1.3.6.1.4.1.34592.1.3.100.10.2.1
		-- 1.3.6.1.4.1.34592.1.3.100.10.2.1
		loopBackDetectionPortConfigEntry OBJECT-TYPE
			SYNTAX LoopBackDetectionPortConfigEntry
			MAX-ACCESS not-accessible
			STATUS current
			DESCRIPTION
				"Description."
			INDEX { loopBackDetectionPortConfigDeviceIndex, loopBackDetectionPortConfigCardIndex, loopBackDetectionPortConfigPortIndex }
			::= { loopBackDetectionPortConfigTable 1 }


		LoopBackDetectionPortConfigEntry ::=
			SEQUENCE {
				loopBackDetectionPortConfigDeviceIndex
					NscrtvPonExtDeviceIndex,
				loopBackDetectionPortConfigCardIndex
					NscrtvPonExtCardIndex,
				loopBackDetectionPortConfigPortIndex
					NscrtvPonPortIndex,
				loopBackDetectionPortConfigEnable
					TruthValue,
				loopBackDetectionPortConfigPerVlanEnable
					TruthValue,
				loopBackDetectionPortConfigControlEnable
					TruthValue,
				loopBackDetectionPortStatus
					INTEGER
			 }

--     1.3.6.1.4.1.34592.1.3.100.10.2.1.1
-- 1.3.6.1.4.1.34592.1.3.100.10.2.1.1
-- 1.3.6.1.4.1.34592.1.3.100.10.2.1.1
-- 1.3.6.1.4.1.34592.1.3.100.10.2.1.1
		-- 1.3.6.1.4.1.34592.1.3.100.10.2.1.1
		loopBackDetectionPortConfigDeviceIndex OBJECT-TYPE
			SYNTAX NscrtvPonExtDeviceIndex
			MAX-ACCESS not-accessible
			STATUS current
			DESCRIPTION
				"Description."
			::= { loopBackDetectionPortConfigEntry 1 }


--     1.3.6.1.4.1.34592.1.3.100.10.2.1.2
-- 1.3.6.1.4.1.34592.1.3.100.10.2.1.2
-- 1.3.6.1.4.1.34592.1.3.100.10.2.1.2
-- 1.3.6.1.4.1.34592.1.3.100.10.2.1.2
		-- 1.3.6.1.4.1.34592.1.3.100.10.2.1.2
		loopBackDetectionPortConfigCardIndex OBJECT-TYPE
			SYNTAX NscrtvPonExtCardIndex
			MAX-ACCESS not-accessible
			STATUS current
			DESCRIPTION
				"Description."
			::= { loopBackDetectionPortConfigEntry 2 }


--     1.3.6.1.4.1.34592.1.3.100.10.2.1.3
-- 1.3.6.1.4.1.34592.1.3.100.10.2.1.3
-- 1.3.6.1.4.1.34592.1.3.100.10.2.1.3
-- 1.3.6.1.4.1.34592.1.3.100.10.2.1.3
		-- 1.3.6.1.4.1.34592.1.3.100.10.2.1.3
		loopBackDetectionPortConfigPortIndex OBJECT-TYPE
			SYNTAX NscrtvPonPortIndex
			MAX-ACCESS not-accessible
			STATUS current
			DESCRIPTION
				"Description."
			::= { loopBackDetectionPortConfigEntry 3 }


--     1.3.6.1.4.1.34592.1.3.100.10.2.1.4
-- 1.3.6.1.4.1.34592.1.3.100.10.2.1.4
-- 1.3.6.1.4.1.34592.1.3.100.10.2.1.4
-- 1.3.6.1.4.1.34592.1.3.100.10.2.1.4
		-- 1.3.6.1.4.1.34592.1.3.100.10.2.1.4
		loopBackDetectionPortConfigEnable OBJECT-TYPE
			SYNTAX TruthValue
			MAX-ACCESS read-write
			STATUS current
			DESCRIPTION
				"Description."
			::= { loopBackDetectionPortConfigEntry 4 }


--     1.3.6.1.4.1.34592.1.3.100.10.2.1.5
-- 1.3.6.1.4.1.34592.1.3.100.10.2.1.5
-- 1.3.6.1.4.1.34592.1.3.100.10.2.1.5
-- 1.3.6.1.4.1.34592.1.3.100.10.2.1.5
		-- 1.3.6.1.4.1.34592.1.3.100.10.2.1.5
		loopBackDetectionPortConfigPerVlanEnable OBJECT-TYPE
			SYNTAX TruthValue
			MAX-ACCESS read-write
			STATUS current
			DESCRIPTION
				"Description."
			::= { loopBackDetectionPortConfigEntry 5 }


--     1.3.6.1.4.1.34592.1.3.100.10.2.1.6
-- 1.3.6.1.4.1.34592.1.3.100.10.2.1.6
-- 1.3.6.1.4.1.34592.1.3.100.10.2.1.6
-- 1.3.6.1.4.1.34592.1.3.100.10.2.1.6
		-- 1.3.6.1.4.1.34592.1.3.100.10.2.1.6
		loopBackDetectionPortConfigControlEnable OBJECT-TYPE
			SYNTAX TruthValue
			MAX-ACCESS read-write
			STATUS current
			DESCRIPTION
				"Description."
			::= { loopBackDetectionPortConfigEntry 6 }


--     1.3.6.1.4.1.34592.1.3.100.10.2.1.7
-- 1.3.6.1.4.1.34592.1.3.100.10.2.1.7
-- 1.3.6.1.4.1.34592.1.3.100.10.2.1.7
-- 1.3.6.1.4.1.34592.1.3.100.10.2.1.7
		-- 1.3.6.1.4.1.34592.1.3.100.10.2.1.7
		loopBackDetectionPortStatus OBJECT-TYPE
			SYNTAX INTEGER
				{
				detected(1),
				undetected(2)
				}
			MAX-ACCESS read-only
			STATUS current
			DESCRIPTION
				"Description."
			::= { loopBackDetectionPortConfigEntry 7 }


--    1.3.6.1.4.1.34592.1.3.100.11
-- 1.3.6.1.4.1.34592.1.3.100.11
-- 1.3.6.1.4.1.34592.1.3.100.11
		-- 1.3.6.1.4.1.34592.1.3.100.11
		igmpMemberPortObjects OBJECT IDENTIFIER ::= { nscrtvPonTreeExt 11 }


--    1.3.6.1.4.1.34592.1.3.100.11.1
-- 1.3.6.1.4.1.34592.1.3.100.11.1
-- 1.3.6.1.4.1.34592.1.3.100.11.1
		-- 1.3.6.1.4.1.34592.1.3.100.11.1
		igmpMemberPortTable OBJECT-TYPE
			SYNTAX SEQUENCE OF IgmpMemberPortEntry
			MAX-ACCESS not-accessible
			STATUS current
			DESCRIPTION
				"Description."
			::= { igmpMemberPortObjects 1 }


--    1.3.6.1.4.1.34592.1.3.100.11.1.1
-- 1.3.6.1.4.1.34592.1.3.100.11.1.1
-- 1.3.6.1.4.1.34592.1.3.100.11.1.1
		-- 1.3.6.1.4.1.34592.1.3.100.11.1.1
		igmpMemberPortEntry OBJECT-TYPE
			SYNTAX IgmpMemberPortEntry
			MAX-ACCESS not-accessible
			STATUS current
			DESCRIPTION
				"Description."
			INDEX { igmpMemberPortVid, igmpMemberPortDeviceIndex }
			::= { igmpMemberPortTable 1 }


		IgmpMemberPortEntry ::=
			SEQUENCE {
				igmpMemberPortVid
					INTEGER,
				igmpMemberPortDeviceIndex
					NscrtvPonExtDeviceIndex,
				igmpMemberPortRowStatus
					INTEGER
			 }

--    1.3.6.1.4.1.34592.1.3.100.11.1.1.1
-- 1.3.6.1.4.1.34592.1.3.100.11.1.1.1
-- 1.3.6.1.4.1.34592.1.3.100.11.1.1.1
		-- 1.3.6.1.4.1.34592.1.3.100.11.1.1.1
		igmpMemberPortVid OBJECT-TYPE
			SYNTAX INTEGER (1..4094)
			MAX-ACCESS not-accessible
			STATUS current
			DESCRIPTION
				"Description."
			::= { igmpMemberPortEntry 1 }


--    1.3.6.1.4.1.34592.1.3.100.11.1.1.2
-- 1.3.6.1.4.1.34592.1.3.100.11.1.1.2
-- 1.3.6.1.4.1.34592.1.3.100.11.1.1.2
		-- 1.3.6.1.4.1.34592.1.3.100.11.1.1.2
		igmpMemberPortDeviceIndex OBJECT-TYPE
			SYNTAX NscrtvPonExtDeviceIndex
			MAX-ACCESS not-accessible
			STATUS current
			DESCRIPTION
				"Description."
			::= { igmpMemberPortEntry 2 }


--    1.3.6.1.4.1.34592.1.3.100.11.1.1.3
-- 1.3.6.1.4.1.34592.1.3.100.11.1.1.3
-- 1.3.6.1.4.1.34592.1.3.100.11.1.1.3
		-- 1.3.6.1.4.1.34592.1.3.100.11.1.1.3
		igmpMemberPortRowStatus OBJECT-TYPE
			SYNTAX INTEGER
			MAX-ACCESS read-create
			STATUS current
			DESCRIPTION
				"Description."
			::= { igmpMemberPortEntry 3 }


		-- 1.3.6.1.4.1.34592.1.3.100.12
		onuObjects OBJECT IDENTIFIER ::= { nscrtvPonTreeExt 12 }


		-- 1.3.6.1.4.1.34592.1.3.100.12.1
		onuVoiceManagementObjects OBJECT IDENTIFIER ::= { onuObjects 1 }


		-- 1.3.6.1.4.1.34592.1.3.100.12.1.1
		onuIadInfoTable OBJECT-TYPE
			SYNTAX SEQUENCE OF OnuIadInfoEntry
			MAX-ACCESS not-accessible
			STATUS current
			DESCRIPTION
				"Description."
			::= { onuVoiceManagementObjects 1 }


		-- 1.3.6.1.4.1.34592.1.3.100.12.1.1.1
		onuIadInfoEntry OBJECT-TYPE
			SYNTAX OnuIadInfoEntry
			MAX-ACCESS not-accessible
			STATUS current
			DESCRIPTION
				"Description."
			INDEX { onuIadInfoDeviceIndex }
			::= { onuIadInfoTable 1 }


		OnuIadInfoEntry ::=
			SEQUENCE {
				onuIadInfoDeviceIndex
					NscrtvPonExtDeviceIndex,
				onuIadMac
					MacAddress,
				onuIadProtocol
					INTEGER,
				onuIadSwVersion
					OCTET STRING,
				onuIadSwTime
					OCTET STRING,
				onuIadVoipNum
					Integer32,
				onuIadVoiceFaxMode
					INTEGER,
				onuIadVoiceFaxControl
					INTEGER,
				onuIadOperation
					INTEGER,
				onuIadOperStatus
					INTEGER
			 }

		-- 1.3.6.1.4.1.34592.1.3.100.12.1.1.1.1
		onuIadInfoDeviceIndex OBJECT-TYPE
			SYNTAX NscrtvPonExtDeviceIndex
			MAX-ACCESS not-accessible
			STATUS current
			DESCRIPTION
				"Description."
			::= { onuIadInfoEntry 1 }


		-- 1.3.6.1.4.1.34592.1.3.100.12.1.1.1.2
		onuIadMac OBJECT-TYPE
			SYNTAX MacAddress
			MAX-ACCESS read-only
			STATUS current
			DESCRIPTION
				"Description."
			::= { onuIadInfoEntry 2 }


		-- 1.3.6.1.4.1.34592.1.3.100.12.1.1.1.3
		onuIadProtocol OBJECT-TYPE
			SYNTAX INTEGER
				{
				h248(0),
				sip(1)
				}
			MAX-ACCESS read-only
			STATUS current
			DESCRIPTION
				"Description."
			::= { onuIadInfoEntry 3 }


		-- 1.3.6.1.4.1.34592.1.3.100.12.1.1.1.4
		onuIadSwVersion OBJECT-TYPE
			SYNTAX OCTET STRING (SIZE (0..32))
			MAX-ACCESS read-only
			STATUS current
			DESCRIPTION
				"Description."
			::= { onuIadInfoEntry 4 }


		-- 1.3.6.1.4.1.34592.1.3.100.12.1.1.1.5
		onuIadSwTime OBJECT-TYPE
			SYNTAX OCTET STRING (SIZE (0..32))
			MAX-ACCESS read-only
			STATUS current
			DESCRIPTION
				"Description."
			::= { onuIadInfoEntry 5 }


		-- 1.3.6.1.4.1.34592.1.3.100.12.1.1.1.6
		onuIadVoipNum OBJECT-TYPE
			SYNTAX Integer32
			MAX-ACCESS read-only
			STATUS current
			DESCRIPTION
				"Description."
			::= { onuIadInfoEntry 6 }


		-- 1.3.6.1.4.1.34592.1.3.100.12.1.1.1.7
		onuIadVoiceFaxMode OBJECT-TYPE
			SYNTAX INTEGER
				{
				t30(0),
				t38(1)
				}
			MAX-ACCESS read-write
			STATUS current
			DESCRIPTION
				"Description."
			::= { onuIadInfoEntry 7 }


		-- 1.3.6.1.4.1.34592.1.3.100.12.1.1.1.8
		onuIadVoiceFaxControl OBJECT-TYPE
			SYNTAX INTEGER
				{
				negotiation(0),
				autoVBD(1)
				}
			MAX-ACCESS read-write
			STATUS current
			DESCRIPTION
				"Description."
			::= { onuIadInfoEntry 8 }


		-- 1.3.6.1.4.1.34592.1.3.100.12.1.1.1.9
		onuIadOperation OBJECT-TYPE
			SYNTAX INTEGER
				{
				reregister(0),
				logout(1),
				reset(2)
				}
			MAX-ACCESS read-write
			STATUS current
			DESCRIPTION
				"Description."
			::= { onuIadInfoEntry 9 }


		-- 1.3.6.1.4.1.34592.1.3.100.12.1.1.1.10
		onuIadOperStatus OBJECT-TYPE
			SYNTAX INTEGER
				{
				registering(0),
				regSuccess(1),
				iadFault(2),
				logout(3),
				iadRestarting(4)
				}
			MAX-ACCESS read-only
			STATUS current
			DESCRIPTION
				"Description."
			::= { onuIadInfoEntry 10 }


		-- 1.3.6.1.4.1.34592.1.3.100.12.1.2
		onuIadParamCfgTable OBJECT-TYPE
			SYNTAX SEQUENCE OF OnuIadParamCfgEntry
			MAX-ACCESS not-accessible
			STATUS current
			DESCRIPTION
				"Description."
			::= { onuVoiceManagementObjects 2 }


		-- 1.3.6.1.4.1.34592.1.3.100.12.1.2.1
		onuIadParamCfgEntry OBJECT-TYPE
			SYNTAX OnuIadParamCfgEntry
			MAX-ACCESS not-accessible
			STATUS current
			DESCRIPTION
				"Description."
			INDEX { onuIadParamCfgDeviceIndex }
			::= { onuIadParamCfgTable 1 }


		OnuIadParamCfgEntry ::=
			SEQUENCE {
				onuIadParamCfgDeviceIndex
					NscrtvPonExtDeviceIndex,
				onuIadMode
					INTEGER,
				onuIadIpAddr
					IpAddress,
				onuIadNetMask
					IpAddress,
				onuIadDefaultGw
					IpAddress,
				onuIadPppoeMode
					INTEGER,
				onuIadPppoeUsrnm
					OCTET STRING,
				onuIadPppoePw
					OCTET STRING,
				onuIadTagMode
					INTEGER,
				onuIadVoiceCVlan
					Integer32,
				onuIadVoiceSVlan
					Integer32,
				onuIadVoicePriority
					Integer32
			 }

		-- 1.3.6.1.4.1.34592.1.3.100.12.1.2.1.1
		onuIadParamCfgDeviceIndex OBJECT-TYPE
			SYNTAX NscrtvPonExtDeviceIndex
			MAX-ACCESS not-accessible
			STATUS current
			DESCRIPTION
				"Description."
			::= { onuIadParamCfgEntry 1 }


		-- 1.3.6.1.4.1.34592.1.3.100.12.1.2.1.2
		onuIadMode OBJECT-TYPE
			SYNTAX INTEGER
				{
				static(0),
				dhcp(1),
				pppoe(2)
				}
			MAX-ACCESS read-write
			STATUS current
			DESCRIPTION
				"Description."
			::= { onuIadParamCfgEntry 2 }


		-- 1.3.6.1.4.1.34592.1.3.100.12.1.2.1.3
		onuIadIpAddr OBJECT-TYPE
			SYNTAX IpAddress
			MAX-ACCESS read-write
			STATUS current
			DESCRIPTION
				"Description."
			::= { onuIadParamCfgEntry 3 }


		-- 1.3.6.1.4.1.34592.1.3.100.12.1.2.1.4
		onuIadNetMask OBJECT-TYPE
			SYNTAX IpAddress
			MAX-ACCESS read-write
			STATUS current
			DESCRIPTION
				"Description."
			::= { onuIadParamCfgEntry 4 }


		-- 1.3.6.1.4.1.34592.1.3.100.12.1.2.1.5
		onuIadDefaultGw OBJECT-TYPE
			SYNTAX IpAddress
			MAX-ACCESS read-write
			STATUS current
			DESCRIPTION
				"Description."
			::= { onuIadParamCfgEntry 5 }


		-- 1.3.6.1.4.1.34592.1.3.100.12.1.2.1.6
		onuIadPppoeMode OBJECT-TYPE
			SYNTAX INTEGER
				{
				auto(0),
				chap(1),
				pap(2)
				}
			MAX-ACCESS read-write
			STATUS current
			DESCRIPTION
				"Description."
			::= { onuIadParamCfgEntry 6 }


		-- 1.3.6.1.4.1.34592.1.3.100.12.1.2.1.7
		onuIadPppoeUsrnm OBJECT-TYPE
			SYNTAX OCTET STRING (SIZE (0..32))
			MAX-ACCESS read-write
			STATUS current
			DESCRIPTION
				"Description."
			::= { onuIadParamCfgEntry 7 }


		-- 1.3.6.1.4.1.34592.1.3.100.12.1.2.1.8
		onuIadPppoePw OBJECT-TYPE
			SYNTAX OCTET STRING (SIZE (0..32))
			MAX-ACCESS read-write
			STATUS current
			DESCRIPTION
				"Description."
			::= { onuIadParamCfgEntry 8 }


		-- 1.3.6.1.4.1.34592.1.3.100.12.1.2.1.9
		onuIadTagMode OBJECT-TYPE
			SYNTAX INTEGER
				{
				passThrough(0),
				tag(1),
				vlanStack(2)
				}
			MAX-ACCESS read-write
			STATUS current
			DESCRIPTION
				"Description."
			::= { onuIadParamCfgEntry 9 }


		-- 1.3.6.1.4.1.34592.1.3.100.12.1.2.1.10
		onuIadVoiceCVlan OBJECT-TYPE
			SYNTAX Integer32 (0..4094)
			MAX-ACCESS read-write
			STATUS current
			DESCRIPTION
				"Description."
			::= { onuIadParamCfgEntry 10 }


		-- 1.3.6.1.4.1.34592.1.3.100.12.1.2.1.11
		onuIadVoiceSVlan OBJECT-TYPE
			SYNTAX Integer32 (0..4094)
			MAX-ACCESS read-write
			STATUS current
			DESCRIPTION
				"Description."
			::= { onuIadParamCfgEntry 11 }


		-- 1.3.6.1.4.1.34592.1.3.100.12.1.2.1.12
		onuIadVoicePriority OBJECT-TYPE
			SYNTAX Integer32 (0..7)
			MAX-ACCESS read-write
			STATUS current
			DESCRIPTION
				"Description."
			::= { onuIadParamCfgEntry 12 }


		-- 1.3.6.1.4.1.34592.1.3.100.12.1.3
		onuIadH248Mangement OBJECT IDENTIFIER ::= { onuVoiceManagementObjects 3 }


		-- 1.3.6.1.4.1.34592.1.3.100.12.1.3.1
		h248ParamCfgTable OBJECT-TYPE
			SYNTAX SEQUENCE OF H248ParamCfgEntry
			MAX-ACCESS not-accessible
			STATUS current
			DESCRIPTION
				"Description."
			::= { onuIadH248Mangement 1 }


		-- 1.3.6.1.4.1.34592.1.3.100.12.1.3.1.1
		h248ParamCfgEntry OBJECT-TYPE
			SYNTAX H248ParamCfgEntry
			MAX-ACCESS not-accessible
			STATUS current
			DESCRIPTION
				"Description."
			INDEX { h248ParamCfgDeviceIndex }
			::= { h248ParamCfgTable 1 }


		H248ParamCfgEntry ::=
			SEQUENCE {
				h248ParamCfgDeviceIndex
					NscrtvPonExtDeviceIndex,
				h248MgPort
					Integer32,
				h248MgcIp
					IpAddress,
				h248MgcPort
					Integer32,
				h248BakMacIp
					IpAddress,
				h248BakMgcPort
					Integer32,
				h248ActiveMgc
					INTEGER,
				h248RegMode
					INTEGER,
				h248MID
					OCTET STRING,
				h248HbMode
					INTEGER,
				h248HbCycle
					Integer32,
				h248HbCount
					Integer32
			 }

		-- 1.3.6.1.4.1.34592.1.3.100.12.1.3.1.1.1
		h248ParamCfgDeviceIndex OBJECT-TYPE
			SYNTAX NscrtvPonExtDeviceIndex
			MAX-ACCESS not-accessible
			STATUS current
			DESCRIPTION
				"Description."
			::= { h248ParamCfgEntry 1 }


		-- 1.3.6.1.4.1.34592.1.3.100.12.1.3.1.1.2
		h248MgPort OBJECT-TYPE
			SYNTAX Integer32 (1024..65535)
			MAX-ACCESS read-write
			STATUS current
			DESCRIPTION
				"Description."
			::= { h248ParamCfgEntry 2 }


		-- 1.3.6.1.4.1.34592.1.3.100.12.1.3.1.1.3
		h248MgcIp OBJECT-TYPE
			SYNTAX IpAddress
			MAX-ACCESS read-write
			STATUS current
			DESCRIPTION
				"Description."
			::= { h248ParamCfgEntry 3 }


		-- 1.3.6.1.4.1.34592.1.3.100.12.1.3.1.1.4
		h248MgcPort OBJECT-TYPE
			SYNTAX Integer32 (1024..65535)
			MAX-ACCESS read-write
			STATUS current
			DESCRIPTION
				"Description."
			::= { h248ParamCfgEntry 4 }


		-- 1.3.6.1.4.1.34592.1.3.100.12.1.3.1.1.5
		h248BakMacIp OBJECT-TYPE
			SYNTAX IpAddress
			MAX-ACCESS read-write
			STATUS current
			DESCRIPTION
				"Description."
			::= { h248ParamCfgEntry 5 }


		-- 1.3.6.1.4.1.34592.1.3.100.12.1.3.1.1.6
		h248BakMgcPort OBJECT-TYPE
			SYNTAX Integer32 (1024..65535)
			MAX-ACCESS read-write
			STATUS current
			DESCRIPTION
				"Description."
			::= { h248ParamCfgEntry 6 }


		-- 1.3.6.1.4.1.34592.1.3.100.12.1.3.1.1.7
		h248ActiveMgc OBJECT-TYPE
			SYNTAX INTEGER
				{
				backup(0),
				active(1)
				}
			MAX-ACCESS read-only
			STATUS current
			DESCRIPTION
				"Description."
			::= { h248ParamCfgEntry 7 }


		-- 1.3.6.1.4.1.34592.1.3.100.12.1.3.1.1.8
		h248RegMode OBJECT-TYPE
			SYNTAX INTEGER
				{
				ipAddress(0),
				domainName(1),
				deviceName(2)
				}
			MAX-ACCESS read-write
			STATUS current
			DESCRIPTION
				"Description."
			::= { h248ParamCfgEntry 8 }


		-- 1.3.6.1.4.1.34592.1.3.100.12.1.3.1.1.9
		h248MID OBJECT-TYPE
			SYNTAX OCTET STRING (SIZE (0..64))
			MAX-ACCESS read-write
			STATUS current
			DESCRIPTION
				"Description."
			::= { h248ParamCfgEntry 9 }


		-- 1.3.6.1.4.1.34592.1.3.100.12.1.3.1.1.10
		h248HbMode OBJECT-TYPE
			SYNTAX INTEGER
				{
				close(0),
				h248ctc(1)
				}
			MAX-ACCESS read-write
			STATUS current
			DESCRIPTION
				"Description."
			::= { h248ParamCfgEntry 10 }


		-- 1.3.6.1.4.1.34592.1.3.100.12.1.3.1.1.11
		h248HbCycle OBJECT-TYPE
			SYNTAX Integer32 (10..600)
			MAX-ACCESS read-write
			STATUS current
			DESCRIPTION
				"Description."
			::= { h248ParamCfgEntry 11 }


		-- 1.3.6.1.4.1.34592.1.3.100.12.1.3.1.1.12
		h248HbCount OBJECT-TYPE
			SYNTAX Integer32 (1..10)
			MAX-ACCESS read-write
			STATUS current
			DESCRIPTION
				"Description."
			::= { h248ParamCfgEntry 12 }


		-- 1.3.6.1.4.1.34592.1.3.100.12.1.3.2
		h248RtpTIDInfoTable OBJECT-TYPE
			SYNTAX SEQUENCE OF H248RtpTIDInfoEntry
			MAX-ACCESS not-accessible
			STATUS current
			DESCRIPTION
				"Description."
			::= { onuIadH248Mangement 2 }


		-- 1.3.6.1.4.1.34592.1.3.100.12.1.3.2.1
		h248RtpTIDInfoEntry OBJECT-TYPE
			SYNTAX H248RtpTIDInfoEntry
			MAX-ACCESS not-accessible
			STATUS current
			DESCRIPTION
				"Description."
			INDEX { h248RtpTIDInfoDeviceIndex }
			::= { h248RtpTIDInfoTable 1 }


		H248RtpTIDInfoEntry ::=
			SEQUENCE {
				h248RtpTIDInfoDeviceIndex
					NscrtvPonExtDeviceIndex,
				h248RtpTIDCount
					Integer32,
				h248FstRtpTIDName
					OCTET STRING,
				h248RtpTIDNum
					Integer32,
				h248RtpTIDPrefix
					OCTET STRING,
				h248RtpTIDDigitBegin
					Integer32,
				h248RtpTIDMode
					INTEGER,
				h248RtpTIDDigitLen
					Integer32
			 }

		-- 1.3.6.1.4.1.34592.1.3.100.12.1.3.2.1.1
		h248RtpTIDInfoDeviceIndex OBJECT-TYPE
			SYNTAX NscrtvPonExtDeviceIndex
			MAX-ACCESS not-accessible
			STATUS current
			DESCRIPTION
				"Description."
			::= { h248RtpTIDInfoEntry 1 }


		-- 1.3.6.1.4.1.34592.1.3.100.12.1.3.2.1.2
		h248RtpTIDCount OBJECT-TYPE
			SYNTAX Integer32 (0..255)
			MAX-ACCESS read-only
			STATUS current
			DESCRIPTION
				"Description."
			::= { h248RtpTIDInfoEntry 2 }


		-- 1.3.6.1.4.1.34592.1.3.100.12.1.3.2.1.3
		h248FstRtpTIDName OBJECT-TYPE
			SYNTAX OCTET STRING (SIZE (0..32))
			MAX-ACCESS read-only
			STATUS current
			DESCRIPTION
				"Description."
			::= { h248RtpTIDInfoEntry 3 }


		-- 1.3.6.1.4.1.34592.1.3.100.12.1.3.2.1.4
		h248RtpTIDNum OBJECT-TYPE
			SYNTAX Integer32 (1..10)
			MAX-ACCESS read-write
			STATUS current
			DESCRIPTION
				"Description."
			::= { h248RtpTIDInfoEntry 4 }


		-- 1.3.6.1.4.1.34592.1.3.100.12.1.3.2.1.5
		h248RtpTIDPrefix OBJECT-TYPE
			SYNTAX OCTET STRING (SIZE (0..16))
			MAX-ACCESS read-write
			STATUS current
			DESCRIPTION
				"Description."
			::= { h248RtpTIDInfoEntry 5 }


		-- 1.3.6.1.4.1.34592.1.3.100.12.1.3.2.1.6
		h248RtpTIDDigitBegin OBJECT-TYPE
			SYNTAX Integer32
			MAX-ACCESS read-write
			STATUS current
			DESCRIPTION
				"Description."
			::= { h248RtpTIDInfoEntry 6 }


		-- 1.3.6.1.4.1.34592.1.3.100.12.1.3.2.1.7
		h248RtpTIDMode OBJECT-TYPE
			SYNTAX INTEGER
				{
				align(0),
				nonAlign(1)
				}
			MAX-ACCESS read-write
			STATUS current
			DESCRIPTION
				"Description."
			::= { h248RtpTIDInfoEntry 7 }


		-- 1.3.6.1.4.1.34592.1.3.100.12.1.3.2.1.8
		h248RtpTIDDigitLen OBJECT-TYPE
			SYNTAX Integer32 (1..8)
			MAX-ACCESS read-write
			STATUS current
			DESCRIPTION
				"Description."
			::= { h248RtpTIDInfoEntry 8 }


		-- 1.3.6.1.4.1.34592.1.3.100.12.1.3.3
		h248UserTIDTable OBJECT-TYPE
			SYNTAX SEQUENCE OF H248UserTIDEntry
			MAX-ACCESS not-accessible
			STATUS current
			DESCRIPTION
				"Description."
			::= { onuIadH248Mangement 3 }


		-- 1.3.6.1.4.1.34592.1.3.100.12.1.3.3.1
		h248UserTIDEntry OBJECT-TYPE
			SYNTAX H248UserTIDEntry
			MAX-ACCESS not-accessible
			STATUS current
			DESCRIPTION
				"Description."
			INDEX { h248UserTIDDeviceIndex, h248UserTIDCardIndex, h248UserTIDPortIndex }
			::= { h248UserTIDTable 1 }


		H248UserTIDEntry ::=
			SEQUENCE {
				h248UserTIDDeviceIndex
					NscrtvPonExtDeviceIndex,
				h248UserTIDCardIndex
					NscrtvPonExtCardIndex,
				h248UserTIDPortIndex
					NscrtvPonPortIndex,
				h248UserTIDName
					OCTET STRING
			 }

		-- 1.3.6.1.4.1.34592.1.3.100.12.1.3.3.1.1
		h248UserTIDDeviceIndex OBJECT-TYPE
			SYNTAX NscrtvPonExtDeviceIndex
			MAX-ACCESS not-accessible
			STATUS current
			DESCRIPTION
				"Description."
			::= { h248UserTIDEntry 1 }


		-- 1.3.6.1.4.1.34592.1.3.100.12.1.3.3.1.2
		h248UserTIDCardIndex OBJECT-TYPE
			SYNTAX NscrtvPonExtCardIndex
			MAX-ACCESS not-accessible
			STATUS current
			DESCRIPTION
				"Description."
			::= { h248UserTIDEntry 2 }


		-- 1.3.6.1.4.1.34592.1.3.100.12.1.3.3.1.3
		h248UserTIDPortIndex OBJECT-TYPE
			SYNTAX NscrtvPonPortIndex
			MAX-ACCESS not-accessible
			STATUS current
			DESCRIPTION
				"Description."
			::= { h248UserTIDEntry 3 }


		-- 1.3.6.1.4.1.34592.1.3.100.12.1.3.3.1.4
		h248UserTIDName OBJECT-TYPE
			SYNTAX OCTET STRING (SIZE (0..32))
			MAX-ACCESS read-write
			STATUS current
			DESCRIPTION
				"Description."
			::= { h248UserTIDEntry 4 }


		-- 1.3.6.1.4.1.34592.1.3.100.12.1.4
		onuIadSipMangement OBJECT IDENTIFIER ::= { onuVoiceManagementObjects 4 }


		-- 1.3.6.1.4.1.34592.1.3.100.12.1.4.1
		sipParamCfgTable OBJECT-TYPE
			SYNTAX SEQUENCE OF SipParamCfgEntry
			MAX-ACCESS not-accessible
			STATUS current
			DESCRIPTION
				"Description."
			::= { onuIadSipMangement 1 }


		-- 1.3.6.1.4.1.34592.1.3.100.12.1.4.1.1
		sipParamCfgEntry OBJECT-TYPE
			SYNTAX SipParamCfgEntry
			MAX-ACCESS not-accessible
			STATUS current
			DESCRIPTION
				"Description."
			INDEX { sipParamCfgDeviceIndex }
			::= { sipParamCfgTable 1 }


		SipParamCfgEntry ::=
			SEQUENCE {
				sipParamCfgDeviceIndex
					NscrtvPonExtDeviceIndex,
				sipMgPort
					Integer32,
				sipProxySvrIp
					IpAddress,
				sipProxySvrPort
					Integer32,
				sipBakProxySvrIp
					IpAddress,
				sipBakProxySvrPort
					Integer32,
				sipActiveProxySvr
					IpAddress,
				sipRegSvrIp
					IpAddress,
				sipRegSvrPort
					Integer32,
				sipBakRegSvrIp
					IpAddress,
				sipBakRegSvrPort
					Integer32,
				sipOutBoundSvrIp
					IpAddress,
				sipOutBoundSvrPort
					Integer32,
				sipRegInterval
					Integer32,
				sipHbSwitch
					INTEGER,
				sipHbCycle
					Integer32,
				sipHbCount
					Integer32
			 }

		-- 1.3.6.1.4.1.34592.1.3.100.12.1.4.1.1.1
		sipParamCfgDeviceIndex OBJECT-TYPE
			SYNTAX NscrtvPonExtDeviceIndex
			MAX-ACCESS not-accessible
			STATUS current
			DESCRIPTION
				"Description."
			::= { sipParamCfgEntry 1 }


		-- 1.3.6.1.4.1.34592.1.3.100.12.1.4.1.1.2
		sipMgPort OBJECT-TYPE
			SYNTAX Integer32 (1024..65535)
			MAX-ACCESS read-write
			STATUS current
			DESCRIPTION
				"Description."
			::= { sipParamCfgEntry 2 }


		-- 1.3.6.1.4.1.34592.1.3.100.12.1.4.1.1.3
		sipProxySvrIp OBJECT-TYPE
			SYNTAX IpAddress
			MAX-ACCESS read-write
			STATUS current
			DESCRIPTION
				"Description."
			::= { sipParamCfgEntry 3 }


		-- 1.3.6.1.4.1.34592.1.3.100.12.1.4.1.1.4
		sipProxySvrPort OBJECT-TYPE
			SYNTAX Integer32 (1024..65535)
			MAX-ACCESS read-write
			STATUS current
			DESCRIPTION
				"Description."
			::= { sipParamCfgEntry 4 }


		-- 1.3.6.1.4.1.34592.1.3.100.12.1.4.1.1.5
		sipBakProxySvrIp OBJECT-TYPE
			SYNTAX IpAddress
			MAX-ACCESS read-write
			STATUS current
			DESCRIPTION
				"Description."
			::= { sipParamCfgEntry 5 }


		-- 1.3.6.1.4.1.34592.1.3.100.12.1.4.1.1.6
		sipBakProxySvrPort OBJECT-TYPE
			SYNTAX Integer32 (1024..65535)
			MAX-ACCESS read-write
			STATUS current
			DESCRIPTION
				"Description."
			::= { sipParamCfgEntry 6 }


		-- 1.3.6.1.4.1.34592.1.3.100.12.1.4.1.1.7
		sipActiveProxySvr OBJECT-TYPE
			SYNTAX IpAddress
			MAX-ACCESS read-only
			STATUS current
			DESCRIPTION
				"Description."
			::= { sipParamCfgEntry 7 }


		-- 1.3.6.1.4.1.34592.1.3.100.12.1.4.1.1.8
		sipRegSvrIp OBJECT-TYPE
			SYNTAX IpAddress
			MAX-ACCESS read-write
			STATUS current
			DESCRIPTION
				"Description."
			::= { sipParamCfgEntry 8 }


		-- 1.3.6.1.4.1.34592.1.3.100.12.1.4.1.1.9
		sipRegSvrPort OBJECT-TYPE
			SYNTAX Integer32 (1024..65535)
			MAX-ACCESS read-write
			STATUS current
			DESCRIPTION
				"Description."
			::= { sipParamCfgEntry 9 }


		-- 1.3.6.1.4.1.34592.1.3.100.12.1.4.1.1.10
		sipBakRegSvrIp OBJECT-TYPE
			SYNTAX IpAddress
			MAX-ACCESS read-write
			STATUS current
			DESCRIPTION
				"Description."
			::= { sipParamCfgEntry 10 }


		-- 1.3.6.1.4.1.34592.1.3.100.12.1.4.1.1.11
		sipBakRegSvrPort OBJECT-TYPE
			SYNTAX Integer32 (1024..65535)
			MAX-ACCESS read-write
			STATUS current
			DESCRIPTION
				"Description."
			::= { sipParamCfgEntry 11 }


		-- 1.3.6.1.4.1.34592.1.3.100.12.1.4.1.1.12
		sipOutBoundSvrIp OBJECT-TYPE
			SYNTAX IpAddress
			MAX-ACCESS read-write
			STATUS current
			DESCRIPTION
				"Description."
			::= { sipParamCfgEntry 12 }


		-- 1.3.6.1.4.1.34592.1.3.100.12.1.4.1.1.13
		sipOutBoundSvrPort OBJECT-TYPE
			SYNTAX Integer32 (1024..65535)
			MAX-ACCESS read-write
			STATUS current
			DESCRIPTION
				"Description."
			::= { sipParamCfgEntry 13 }


		-- 1.3.6.1.4.1.34592.1.3.100.12.1.4.1.1.14
		sipRegInterval OBJECT-TYPE
			SYNTAX Integer32
			MAX-ACCESS read-write
			STATUS current
			DESCRIPTION
				"Description."
			::= { sipParamCfgEntry 14 }


		-- 1.3.6.1.4.1.34592.1.3.100.12.1.4.1.1.15
		sipHbSwitch OBJECT-TYPE
			SYNTAX INTEGER
				{
				enable(0),
				disable(1)
				}
			MAX-ACCESS read-write
			STATUS current
			DESCRIPTION
				"Description."
			::= { sipParamCfgEntry 15 }


		-- 1.3.6.1.4.1.34592.1.3.100.12.1.4.1.1.16
		sipHbCycle OBJECT-TYPE
			SYNTAX Integer32 (10..600)
			MAX-ACCESS read-write
			STATUS current
			DESCRIPTION
				"Description."
			::= { sipParamCfgEntry 16 }


		-- 1.3.6.1.4.1.34592.1.3.100.12.1.4.1.1.17
		sipHbCount OBJECT-TYPE
			SYNTAX Integer32 (1..10)
			MAX-ACCESS read-write
			STATUS current
			DESCRIPTION
				"Description."
			::= { sipParamCfgEntry 17 }


		-- 1.3.6.1.4.1.34592.1.3.100.12.1.4.2
		sipUserCfgTable OBJECT-TYPE
			SYNTAX SEQUENCE OF SipUserCfgEntry
			MAX-ACCESS not-accessible
			STATUS current
			DESCRIPTION
				"Description."
			::= { onuIadSipMangement 2 }


		-- 1.3.6.1.4.1.34592.1.3.100.12.1.4.2.1
		sipUserCfgEntry OBJECT-TYPE
			SYNTAX SipUserCfgEntry
			MAX-ACCESS not-accessible
			STATUS current
			DESCRIPTION
				"Description."
			INDEX { sipUserCfgDeviceIndex, sipUserCfgCardIndex, sipUserCfgPotsIndex }
			::= { sipUserCfgTable 1 }


		SipUserCfgEntry ::=
			SEQUENCE {
				sipUserCfgDeviceIndex
					NscrtvPonExtDeviceIndex,
				sipUserCfgCardIndex
					NscrtvPonExtCardIndex,
				sipUserCfgPotsIndex
					NscrtvPonPortIndex,
				sipUserAccount
					OCTET STRING,
				sipUserName
					OCTET STRING,
				sipUserPasswd
					OCTET STRING
			 }

		-- 1.3.6.1.4.1.34592.1.3.100.12.1.4.2.1.1
		sipUserCfgDeviceIndex OBJECT-TYPE
			SYNTAX NscrtvPonExtDeviceIndex
			MAX-ACCESS not-accessible
			STATUS current
			DESCRIPTION
				"Description."
			::= { sipUserCfgEntry 1 }


		-- 1.3.6.1.4.1.34592.1.3.100.12.1.4.2.1.2
		sipUserCfgCardIndex OBJECT-TYPE
			SYNTAX NscrtvPonExtCardIndex
			MAX-ACCESS not-accessible
			STATUS current
			DESCRIPTION
				"Description."
			::= { sipUserCfgEntry 2 }


		-- 1.3.6.1.4.1.34592.1.3.100.12.1.4.2.1.3
		sipUserCfgPotsIndex OBJECT-TYPE
			SYNTAX NscrtvPonPortIndex
			MAX-ACCESS not-accessible
			STATUS current
			DESCRIPTION
				"Description."
			::= { sipUserCfgEntry 3 }


		-- 1.3.6.1.4.1.34592.1.3.100.12.1.4.2.1.4
		sipUserAccount OBJECT-TYPE
			SYNTAX OCTET STRING (SIZE (0..16))
			MAX-ACCESS read-write
			STATUS current
			DESCRIPTION
				"Description."
			::= { sipUserCfgEntry 4 }


		-- 1.3.6.1.4.1.34592.1.3.100.12.1.4.2.1.5
		sipUserName OBJECT-TYPE
			SYNTAX OCTET STRING (SIZE (0..32))
			MAX-ACCESS read-write
			STATUS current
			DESCRIPTION
				"Description."
			::= { sipUserCfgEntry 5 }


		-- 1.3.6.1.4.1.34592.1.3.100.12.1.4.2.1.6
		sipUserPasswd OBJECT-TYPE
			SYNTAX OCTET STRING (SIZE (0..16))
			MAX-ACCESS read-write
			STATUS current
			DESCRIPTION
				"Description."
			::= { sipUserCfgEntry 6 }


		-- 1.3.6.1.4.1.34592.1.3.100.12.1.5
		onuIadPotsInfoTable OBJECT-TYPE
			SYNTAX SEQUENCE OF OnuIadPotsInfoEntry
			MAX-ACCESS not-accessible
			STATUS current
			DESCRIPTION
				"Description."
			::= { onuVoiceManagementObjects 5 }


		-- 1.3.6.1.4.1.34592.1.3.100.12.1.5.1
		onuIadPotsInfoEntry OBJECT-TYPE
			SYNTAX OnuIadPotsInfoEntry
			MAX-ACCESS not-accessible
			STATUS current
			DESCRIPTION
				"Description."
			INDEX { potsInfoDeviceIndex, potsInfoCardIndex, potsInfoPortIndex }
			::= { onuIadPotsInfoTable 1 }


		OnuIadPotsInfoEntry ::=
			SEQUENCE {
				potsInfoDeviceIndex
					NscrtvPonExtDeviceIndex,
				potsInfoCardIndex
					NscrtvPonExtCardIndex,
				potsInfoPortIndex
					NscrtvPonPortIndex,
				onuIadPotsEnable
					INTEGER,
				onuIadPotsStatus
					INTEGER,
				onuIadPotsServiceState
					INTEGER,
				onuIadPotsCodeMode
					INTEGER
			 }

		-- 1.3.6.1.4.1.34592.1.3.100.12.1.5.1.1
		potsInfoDeviceIndex OBJECT-TYPE
			SYNTAX NscrtvPonExtDeviceIndex
			MAX-ACCESS not-accessible
			STATUS current
			DESCRIPTION
				"Description."
			::= { onuIadPotsInfoEntry 1 }


		-- 1.3.6.1.4.1.34592.1.3.100.12.1.5.1.2
		potsInfoCardIndex OBJECT-TYPE
			SYNTAX NscrtvPonExtCardIndex
			MAX-ACCESS not-accessible
			STATUS current
			DESCRIPTION
				"Description."
			::= { onuIadPotsInfoEntry 2 }


		-- 1.3.6.1.4.1.34592.1.3.100.12.1.5.1.3
		potsInfoPortIndex OBJECT-TYPE
			SYNTAX NscrtvPonPortIndex
			MAX-ACCESS not-accessible
			STATUS current
			DESCRIPTION
				"Description."
			::= { onuIadPotsInfoEntry 3 }


		-- 1.3.6.1.4.1.34592.1.3.100.12.1.5.1.4
		onuIadPotsEnable OBJECT-TYPE
			SYNTAX INTEGER
				{
				disable(1),
				enable(2)
				}
			MAX-ACCESS read-write
			STATUS current
			DESCRIPTION
				"Description."
			::= { onuIadPotsInfoEntry 4 }


		-- 1.3.6.1.4.1.34592.1.3.100.12.1.5.1.5
		onuIadPotsStatus OBJECT-TYPE
			SYNTAX INTEGER
				{
				registering(0),
				idle(1),
				pickUp(2),
				dialing(3),
				ringing(4),
				ringBack(5),
				connecting(6),
				connected(7),
				releasing(8),
				regFailure(9),
				notActivated(10)
				}
			MAX-ACCESS read-only
			STATUS current
			DESCRIPTION
				"Description."
			::= { onuIadPotsInfoEntry 5 }


		-- 1.3.6.1.4.1.34592.1.3.100.12.1.5.1.6
		onuIadPotsServiceState OBJECT-TYPE
			SYNTAX INTEGER
				{
				endLocal(0),
				endRemote(1),
				endAuto(2),
				normal(3)
				}
			MAX-ACCESS read-only
			STATUS current
			DESCRIPTION
				"Description."
			::= { onuIadPotsInfoEntry 6 }


		-- 1.3.6.1.4.1.34592.1.3.100.12.1.5.1.7
		onuIadPotsCodeMode OBJECT-TYPE
			SYNTAX INTEGER
				{
				g711a(0),
				g729(1),
				g711u(2),
				g723(3),
				g726(4),
				t38(5)
				}
			MAX-ACCESS read-only
			STATUS current
			DESCRIPTION
				"Description."
			::= { onuIadPotsInfoEntry 7 }


		-- 1.3.6.1.4.1.34592.1.3.100.12.2
		onuMacAddressObjects OBJECT IDENTIFIER ::= { onuObjects 2 }


		-- 1.3.6.1.4.1.34592.1.3.100.12.2.1
		onuMacAddressTable OBJECT-TYPE
			SYNTAX SEQUENCE OF OnuMacAddressEntry
			MAX-ACCESS not-accessible
			STATUS current
			DESCRIPTION
				"Description."
			::= { onuMacAddressObjects 1 }


		-- 1.3.6.1.4.1.34592.1.3.100.12.2.1.1
		onuMacAddressEntry OBJECT-TYPE
			SYNTAX OnuMacAddressEntry
			MAX-ACCESS not-accessible
			STATUS current
			DESCRIPTION
				"Description."
			INDEX { onuMacAddrIndex, onuMacAddrVlanIdIndex }
			::= { onuMacAddressTable 1 }


		OnuMacAddressEntry ::=
			SEQUENCE {
				onuMacAddrIndex
					MacAddress,
				onuMacAddrVlanIdIndex
					Integer32,
				onuMacAddrDeviceIndex
					NscrtvPonExtDeviceIndex,
				onuMacAddr
					MacAddress
			 }

		-- 1.3.6.1.4.1.34592.1.3.100.12.2.1.1.1
		onuMacAddrIndex OBJECT-TYPE
			SYNTAX MacAddress
			MAX-ACCESS not-accessible
			STATUS current
			DESCRIPTION
				"Description."
			::= { onuMacAddressEntry 1 }


		-- 1.3.6.1.4.1.34592.1.3.100.12.2.1.1.2
		onuMacAddrVlanIdIndex OBJECT-TYPE
			SYNTAX Integer32
			MAX-ACCESS not-accessible
			STATUS current
			DESCRIPTION
				"Description."
			::= { onuMacAddressEntry 2 }


		-- 1.3.6.1.4.1.34592.1.3.100.12.2.1.1.3
		onuMacAddrDeviceIndex OBJECT-TYPE
			SYNTAX NscrtvPonExtDeviceIndex
			MAX-ACCESS read-only
			STATUS current
			DESCRIPTION
				"Description."
			::= { onuMacAddressEntry 3 }


		-- 1.3.6.1.4.1.34592.1.3.100.12.2.1.1.4
		onuMacAddr OBJECT-TYPE
			SYNTAX MacAddress
			MAX-ACCESS read-only
			STATUS current
			DESCRIPTION
				"Description."
			::= { onuMacAddressEntry 4 }


		-- 1.3.6.1.4.1.34592.1.3.100.12.3
		onuRegInfoObjects OBJECT IDENTIFIER ::= { onuObjects 3 }


		-- 1.3.6.1.4.1.34592.1.3.100.12.3.1
		onuRegInfoTable OBJECT-TYPE
			SYNTAX SEQUENCE OF OnuRegInfoEntry
			MAX-ACCESS not-accessible
			STATUS current
			DESCRIPTION
				"Description."
			::= { onuRegInfoObjects 1 }


		-- 1.3.6.1.4.1.34592.1.3.100.12.3.1.1
		onuRegInfoEntry OBJECT-TYPE
			SYNTAX OnuRegInfoEntry
			MAX-ACCESS not-accessible
			STATUS current
			DESCRIPTION
				"Description."
			INDEX { onuRegInfoDeviceIndex }
			::= { onuRegInfoTable 1 }


		OnuRegInfoEntry ::=
			SEQUENCE {
				onuRegInfoDeviceIndex
					NscrtvPonExtDeviceIndex,
				onuRegInfoRegTimes
					Unsigned32,
				onuRegInfoDeregTimes
					Unsigned32,
				onuRegInfoOnlineDate
					DateAndTime,
				onuRegInfoOfflineDate
					DateAndTime,
				onuRegInfoOnlineDuration
					Unsigned32,
				onuRegInfoOfflineReason
					OCTET STRING,
				onuRegInfoModelId
					DisplayString,
				onuPortLoopDetectSwitch
					INTEGER,
				onuPortAutoShutdown
					INTEGER
			 }

		-- 1.3.6.1.4.1.34592.1.3.100.12.3.1.1.1
		onuRegInfoDeviceIndex OBJECT-TYPE
			SYNTAX NscrtvPonExtDeviceIndex
			MAX-ACCESS not-accessible
			STATUS current
			DESCRIPTION
				"Description."
			::= { onuRegInfoEntry 1 }


		-- 1.3.6.1.4.1.34592.1.3.100.12.3.1.1.2
		onuRegInfoRegTimes OBJECT-TYPE
			SYNTAX Unsigned32
			MAX-ACCESS read-only
			STATUS current
			DESCRIPTION
				"Description."
			::= { onuRegInfoEntry 2 }


		-- 1.3.6.1.4.1.34592.1.3.100.12.3.1.1.3
		onuRegInfoDeregTimes OBJECT-TYPE
			SYNTAX Unsigned32
			MAX-ACCESS read-only
			STATUS current
			DESCRIPTION
				"Description."
			::= { onuRegInfoEntry 3 }


		-- 1.3.6.1.4.1.34592.1.3.100.12.3.1.1.4
		onuRegInfoOnlineDate OBJECT-TYPE
			SYNTAX DateAndTime
			MAX-ACCESS read-only
			STATUS current
			DESCRIPTION
				"Description."
			::= { onuRegInfoEntry 4 }


		-- 1.3.6.1.4.1.34592.1.3.100.12.3.1.1.5
		onuRegInfoOfflineDate OBJECT-TYPE
			SYNTAX DateAndTime
			MAX-ACCESS read-only
			STATUS current
			DESCRIPTION
				"Description."
			::= { onuRegInfoEntry 5 }


		-- 1.3.6.1.4.1.34592.1.3.100.12.3.1.1.6
		onuRegInfoOnlineDuration OBJECT-TYPE
			SYNTAX Unsigned32
			MAX-ACCESS read-only
			STATUS current
			DESCRIPTION
				"Description."
			::= { onuRegInfoEntry 6 }


		-- 1.3.6.1.4.1.34592.1.3.100.12.3.1.1.7
		onuRegInfoOfflineReason OBJECT-TYPE
			SYNTAX OCTET STRING
			MAX-ACCESS read-only
			STATUS current
			DESCRIPTION
				"Description."
			::= { onuRegInfoEntry 7 }

		-- 1.3.6.1.4.1.34592.1.3.100.12.3.1.1.8
		onuRegInfoModelId OBJECT-TYPE
			SYNTAX DisplayString
			MAX-ACCESS read-only
			STATUS current
			DESCRIPTION
				"Description."
			::= { onuRegInfoEntry 8 }

		-- 1.3.6.1.4.1.34592.1.3.100.12.3.1.1.9
		onuPortLoopDetectSwitch OBJECT-TYPE
			SYNTAX INTEGER
				{
				disable(1),
				enable(2)
				}
			MAX-ACCESS read-write
			STATUS current
			DESCRIPTION
				"Description."
			::= { onuRegInfoEntry 9 }

		-- 1.3.6.1.4.1.34592.1.3.100.12.3.1.1.10
		onuPortAutoShutdown OBJECT-TYPE
			SYNTAX INTEGER
				{
				disable(0),
				enable(1),
				enableButNoRecovery(2)
				}
			MAX-ACCESS read-write
			STATUS current
			DESCRIPTION
				"Description."
			::= { onuRegInfoEntry 10 }

		-- 1.3.6.1.4.1.34592.1.3.100.12.4
		onuUpdateTimerObjects OBJECT IDENTIFIER ::= { onuObjects 4 }

		-- 1.3.6.1.4.1.34592.1.3.100.12.4.1
		onuUpdateTimerTable OBJECT-TYPE
			SYNTAX SEQUENCE OF OnuUpdateTimerEntry
			MAX-ACCESS not-accessible
			STATUS current
			DESCRIPTION
				"Description."
			::= { onuUpdateTimerObjects 1 }


		-- 1.3.6.1.4.1.34592.1.3.100.12.4.1.1
		onuUpdateTimerEntry OBJECT-TYPE
			SYNTAX OnuUpdateTimerEntry
			MAX-ACCESS not-accessible
			STATUS current
			DESCRIPTION
				"Description."
			INDEX { onuUpdateTimerDeviceIndex }
			::= { onuUpdateTimerTable 1 }


		OnuUpdateTimerEntry ::=
			SEQUENCE {
				onuUpdateTimerDeviceIndex
					NscrtvPonExtDeviceIndex,
				onuUpdateTimerSwitch
					INTEGER,
				onuUpdateTimerImageName
					DisplayString,
				onuUpdateTimerSelectType
					INTEGER,
				onuUpdateTimerModelId
					OCTET STRING,
				onuUpdateTimerPortList
					OCTET STRING,
				onuUpdateTimerOntList
					OCTET STRING,
				onuUpdateTimerSystemTime
					DateAndTime,
				onuUpdateTimerConfigTime
					DateAndTime,
				onuUpdateTimerGlobalStatus
					DisplayString,
				onuUpdateTimerTotalNum
					Unsigned32,
				onuUpdateTimerSuccessNum
					Unsigned32,
				onuUpdateTimerFailureNum
					Unsigned32,
				onuUpdateTimerOntStatus
					OCTET STRING
			 }

		-- 1.3.6.1.4.1.34592.1.3.100.12.4.1.1.1
		onuUpdateTimerDeviceIndex OBJECT-TYPE
			SYNTAX NscrtvPonExtDeviceIndex
			MAX-ACCESS not-accessible
			STATUS current
			DESCRIPTION
				"Description."
			::= { onuUpdateTimerEntry 1 }


		-- 1.3.6.1.4.1.34592.1.3.100.12.4.1.1.2
		onuUpdateTimerSwitch OBJECT-TYPE
			SYNTAX INTEGER
				{
				disable(0),
				enable(1)
				}
			MAX-ACCESS read-write
			STATUS current
			DESCRIPTION
				"Description."
			::= { onuUpdateTimerEntry 2 }


		-- 1.3.6.1.4.1.34592.1.3.100.12.4.1.1.3
		onuUpdateTimerImageName OBJECT-TYPE
			SYNTAX DisplayString
			MAX-ACCESS read-write
			STATUS current
			DESCRIPTION
				""
			::= { onuUpdateTimerEntry 3 }


		-- 1.3.6.1.4.1.34592.1.3.100.12.4.1.1.4
		onuUpdateTimerSelectType OBJECT-TYPE
			SYNTAX INTEGER
				{
				oltBased(0),
				modelIdBased(1),
				portBased(2),
				ontBased(3),
				portModelIdBased(4),
				ontModelIdBased(5)
				}
			MAX-ACCESS read-write
			STATUS current
			DESCRIPTION
				""
			::= { onuUpdateTimerEntry 4 }


		-- 1.3.6.1.4.1.34592.1.3.100.12.4.1.1.5
		onuUpdateTimerModelId OBJECT-TYPE
			SYNTAX OCTET STRING
			MAX-ACCESS read-write
			STATUS current
			DESCRIPTION
				"Hexadecimal model ID(SIZE:4).(e.g.:0x31 30 30 53)"
			::= { onuUpdateTimerEntry 5 }


		-- 1.3.6.1.4.1.34592.1.3.100.12.4.1.1.6
		onuUpdateTimerPortList OBJECT-TYPE
			SYNTAX OCTET STRING
			MAX-ACCESS read-write
			STATUS current
			DESCRIPTION
				""
			::= { onuUpdateTimerEntry 6 }


		-- 1.3.6.1.4.1.34592.1.3.100.12.4.1.1.7
		onuUpdateTimerOntList OBJECT-TYPE
			SYNTAX OCTET STRING
			MAX-ACCESS read-write
			STATUS current
			DESCRIPTION
				""
			::= { onuUpdateTimerEntry 7 }


		-- 1.3.6.1.4.1.34592.1.3.100.12.4.1.1.8
		onuUpdateTimerSystemTime OBJECT-TYPE
			SYNTAX DateAndTime
			MAX-ACCESS read-only
			STATUS current
			DESCRIPTION
				"Description."
			::= { onuUpdateTimerEntry 8 }


		-- 1.3.6.1.4.1.34592.1.3.100.12.4.1.1.9
		onuUpdateTimerConfigTime OBJECT-TYPE
			SYNTAX DateAndTime
			MAX-ACCESS read-write
			STATUS current
			DESCRIPTION
				""
			::= { onuUpdateTimerEntry 9 }


		-- 1.3.6.1.4.1.34592.1.3.100.12.4.1.1.10
		onuUpdateTimerGlobalStatus OBJECT-TYPE
			SYNTAX DisplayString
			MAX-ACCESS read-only
			STATUS current
			DESCRIPTION
				"Description."
			::= { onuUpdateTimerEntry 10 }


		-- 1.3.6.1.4.1.34592.1.3.100.12.4.1.1.11
		onuUpdateTimerTotalNum OBJECT-TYPE
			SYNTAX Unsigned32
			MAX-ACCESS read-only
			STATUS current
			DESCRIPTION
				"Description."
			::= { onuUpdateTimerEntry 11 }


		-- 1.3.6.1.4.1.34592.1.3.100.12.4.1.1.12
		onuUpdateTimerSuccessNum OBJECT-TYPE
			SYNTAX Unsigned32
			MAX-ACCESS read-only
			STATUS current
			DESCRIPTION
				"Description."
			::= { onuUpdateTimerEntry 12 }


		-- 1.3.6.1.4.1.34592.1.3.100.12.4.1.1.13
		onuUpdateTimerFailureNum OBJECT-TYPE
			SYNTAX Unsigned32
			MAX-ACCESS read-only
			STATUS current
			DESCRIPTION
				"Description."
			::= { onuUpdateTimerEntry 13 }


		-- 1.3.6.1.4.1.34592.1.3.100.12.4.1.1.14
		onuUpdateTimerOntStatus OBJECT-TYPE
			SYNTAX OCTET STRING
			MAX-ACCESS read-only
			STATUS current
			DESCRIPTION
				""
			::= { onuUpdateTimerEntry 14 }

		-- 1.3.6.1.4.1.34592.1.3.100.13
		uniObjects OBJECT IDENTIFIER ::= { nscrtvPonTreeExt 13 }


		-- 1.3.6.1.4.1.34592.1.3.100.13.1
		uniLearnedMacAddrTable OBJECT-TYPE
			SYNTAX SEQUENCE OF UniLearnedMacAddrEntry
			MAX-ACCESS not-accessible
			STATUS current
			DESCRIPTION
				"Description."
			::= { uniObjects 1 }


		-- 1.3.6.1.4.1.34592.1.3.100.13.1.1
		uniLearnedMacAddrEntry OBJECT-TYPE
			SYNTAX UniLearnedMacAddrEntry
			MAX-ACCESS not-accessible
			STATUS current
			DESCRIPTION
				"Description."
			INDEX { uniLearnedMacAddrDeviceIndex, uniLearnedMacAddrCardIndex, uniLearnedMacAddrPortIndex, uniLearnedMacAddrIndex }
			::= { uniLearnedMacAddrTable 1 }


		UniLearnedMacAddrEntry ::=
			SEQUENCE {
				uniLearnedMacAddrDeviceIndex
					NscrtvPonExtDeviceIndex,
				uniLearnedMacAddrCardIndex
					NscrtvPonExtCardIndex,
				uniLearnedMacAddrPortIndex
					NscrtvPonPortIndex,
				uniLearnedMacAddrIndex
					Integer32,
				uniLearnedMacAddr
					MacAddress
			 }

		-- 1.3.6.1.4.1.34592.1.3.100.13.1.1.1
		uniLearnedMacAddrDeviceIndex OBJECT-TYPE
			SYNTAX NscrtvPonExtDeviceIndex
			MAX-ACCESS not-accessible
			STATUS current
			DESCRIPTION
				"Description."
			::= { uniLearnedMacAddrEntry 1 }


		-- 1.3.6.1.4.1.34592.1.3.100.13.1.1.2
		uniLearnedMacAddrCardIndex OBJECT-TYPE
			SYNTAX NscrtvPonExtCardIndex
			MAX-ACCESS not-accessible
			STATUS current
			DESCRIPTION
				"Description."
			::= { uniLearnedMacAddrEntry 2 }


		-- 1.3.6.1.4.1.34592.1.3.100.13.1.1.3
		uniLearnedMacAddrPortIndex OBJECT-TYPE
			SYNTAX NscrtvPonPortIndex
			MAX-ACCESS not-accessible
			STATUS current
			DESCRIPTION
				"Description."
			::= { uniLearnedMacAddrEntry 3 }


		-- 1.3.6.1.4.1.34592.1.3.100.13.1.1.4
		uniLearnedMacAddrIndex OBJECT-TYPE
			SYNTAX Integer32
			MAX-ACCESS not-accessible
			STATUS current
			DESCRIPTION
				"Description."
			::= { uniLearnedMacAddrEntry 4 }


		-- 1.3.6.1.4.1.34592.1.3.100.13.1.1.5
		uniLearnedMacAddr OBJECT-TYPE
			SYNTAX MacAddress
			MAX-ACCESS read-only
			STATUS current
			DESCRIPTION
				"Description."
			::= { uniLearnedMacAddrEntry 5 }

		-- 1.3.6.1.4.1.34592.1.3.100.14
		aclManagementObjects OBJECT IDENTIFIER ::= { nscrtvPonTreeExt 14 }


		-- 1.3.6.1.4.1.34592.1.3.100.14.1
		timeRangeTable OBJECT-TYPE
			SYNTAX SEQUENCE OF TimeRangeEntry
			MAX-ACCESS not-accessible
			STATUS current
			DESCRIPTION
				"Description."
			::= { aclManagementObjects 1 }


		-- 1.3.6.1.4.1.34592.1.3.100.14.1.1
		timeRangeEntry OBJECT-TYPE
			SYNTAX TimeRangeEntry
			MAX-ACCESS not-accessible
			STATUS current
			DESCRIPTION
				"Description."
			INDEX { timeRangeIndex }
			::= { timeRangeTable 1 }


		TimeRangeEntry ::=
			SEQUENCE {
				timeRangeIndex
					INTEGER,
				timeRangeName
					DisplayString,
				timeRangeType
					INTEGER,
				timeRangeState
					DisplayString,
				relativeTimeStart
					DisplayString,
				relativeTimeEnd
					DisplayString,
				relativeTimeCycle
					INTEGER,
				absoluteTimeStart
					DisplayString,
				absoluteTimeEnd
					DisplayString,
				timeRangeRowStatus
					RowStatus
			 }

		-- 1.3.6.1.4.1.34592.1.3.100.14.1.1.1
		timeRangeIndex OBJECT-TYPE
			SYNTAX INTEGER (1..256)
			MAX-ACCESS not-accessible
			STATUS current
			DESCRIPTION
				"Index: 1-256"
			::= { timeRangeEntry 1 }


		-- 1.3.6.1.4.1.34592.1.3.100.14.1.1.2
		timeRangeName OBJECT-TYPE
			SYNTAX DisplayString (SIZE (1..10))
			MAX-ACCESS read-create
			STATUS current
			DESCRIPTION
				"LONGEST SIZE: 10"
			::= { timeRangeEntry 2 }


		-- 1.3.6.1.4.1.34592.1.3.100.14.1.1.3
		timeRangeType OBJECT-TYPE
			SYNTAX INTEGER
				{
				absoluteTime(1),
				relativeTime(2)
				}
			MAX-ACCESS read-create
			STATUS current
			DESCRIPTION
				"Description."
			::= { timeRangeEntry 3 }


		-- 1.3.6.1.4.1.34592.1.3.100.14.1.1.4
		timeRangeState OBJECT-TYPE
			SYNTAX DisplayString
			MAX-ACCESS read-only
			STATUS current
			DESCRIPTION
				"Description."
			::= { timeRangeEntry 4 }


		-- 1.3.6.1.4.1.34592.1.3.100.14.1.1.5
		relativeTimeStart OBJECT-TYPE
			SYNTAX DisplayString (SIZE (5))
			MAX-ACCESS read-create
			STATUS current
			DESCRIPTION
				"Format: HH:MM
				For exmaple: 08:01"
			::= { timeRangeEntry 5 }


		-- 1.3.6.1.4.1.34592.1.3.100.14.1.1.6
		relativeTimeEnd OBJECT-TYPE
			SYNTAX DisplayString (SIZE (5))
			MAX-ACCESS read-create
			STATUS current
			DESCRIPTION
				"Format: HH:MM
				For exmaple: 23:10"
			::= { timeRangeEntry 6 }


		-- 1.3.6.1.4.1.34592.1.3.100.14.1.1.7
		relativeTimeCycle OBJECT-TYPE
			SYNTAX INTEGER
				{
				Sunday(1),
				Monday(2),
				Tuesday(3),
				Wednesday(4),
				Thurday(5),
				Friday(6),
				Saturday(7),
				Daily(8),
				Weekend(9),
				WorkingDay(10)
				}
			MAX-ACCESS read-create
			STATUS current
			DESCRIPTION
				"Description."
			::= { timeRangeEntry 7 }


		-- 1.3.6.1.4.1.34592.1.3.100.14.1.1.8
		absoluteTimeStart OBJECT-TYPE
			SYNTAX DisplayString (SIZE (16))
			MAX-ACCESS read-create
			STATUS current
			DESCRIPTION
				"Format: YYYY/MM/DD HH:MM
				For exmaple: 2019/01/02 08:01"
			::= { timeRangeEntry 8 }


		-- 1.3.6.1.4.1.34592.1.3.100.14.1.1.9
		absoluteTimeEnd OBJECT-TYPE
			SYNTAX DisplayString (SIZE (16))
			MAX-ACCESS read-create
			STATUS current
			DESCRIPTION
				"Format: YYYY/MM/DD HH:MM
				For exmaple: 2019/10/28 23:10"
			::= { timeRangeEntry 9 }


		-- 1.3.6.1.4.1.34592.1.3.100.14.1.1.10
		timeRangeRowStatus OBJECT-TYPE
			SYNTAX RowStatus
			MAX-ACCESS read-create
			STATUS current
			DESCRIPTION
				"Description."
			::= { timeRangeEntry 10 }


		-- 1.3.6.1.4.1.34592.1.3.100.14.2
		bindConfigTable OBJECT-TYPE
			SYNTAX SEQUENCE OF BindConfigEntry
			MAX-ACCESS not-accessible
			STATUS current
			DESCRIPTION
				"Description."
			::= { aclManagementObjects 2 }


		-- 1.3.6.1.4.1.34592.1.3.100.14.2.1
		bindConfigEntry OBJECT-TYPE
			SYNTAX BindConfigEntry
			MAX-ACCESS not-accessible
			STATUS current
			DESCRIPTION
				"Description."
			INDEX { bindConfigAclId, bindConfigRuleId }
			::= { bindConfigTable 1 }


		BindConfigEntry ::=
			SEQUENCE {
				bindConfigAclId
					INTEGER,
				bindConfigRuleId
					INTEGER,
				bindConfigName
					DisplayString,
				bindConfigRowStatus
					RowStatus
			 }

		-- 1.3.6.1.4.1.34592.1.3.100.14.2.1.1
		bindConfigAclId OBJECT-TYPE
			SYNTAX INTEGER
			MAX-ACCESS not-accessible
			STATUS current
			DESCRIPTION
				"Description."
			::= { bindConfigEntry 1 }


		-- 1.3.6.1.4.1.34592.1.3.100.14.2.1.2
		bindConfigRuleId OBJECT-TYPE
			SYNTAX INTEGER
			MAX-ACCESS not-accessible
			STATUS current
			DESCRIPTION
				"Description."
			::= { bindConfigEntry 2 }


		-- 1.3.6.1.4.1.34592.1.3.100.14.2.1.3
		bindConfigName OBJECT-TYPE
			SYNTAX DisplayString (SIZE (1..10))
			MAX-ACCESS read-create
			STATUS current
			DESCRIPTION
				"LONGEST SIZE: 10"
			::= { bindConfigEntry 3 }


		-- 1.3.6.1.4.1.34592.1.3.100.14.2.1.4
		bindConfigRowStatus OBJECT-TYPE
			SYNTAX RowStatus
			MAX-ACCESS read-create
			STATUS current
			DESCRIPTION
				"Description."
			::= { bindConfigEntry 4 }

	END

--
-- NSCRTV-PON-TREE-EXT-MIB.my
--
