--
-- FD-OLT-MIB.my
-- MIB generated by MG-SOFT Visual MIB Builder Version 6.0  Build 88
-- Friday, May 19, 2017 at 17:25:13
--

--  FD-OLT-MIB.my
-- MIB generated by MG-SOFT Visual MIB Builder Version 6.0  Build 88
-- Wednesday, May 17, 2017 at 18:10:21
--
--  FD-OLT-MIB.my
-- MIB generated by MG-SOFT Visual MIB Builder Version 6.0  Build 88
-- Wednesday, January 18, 2017 at 10:40:43
--
--  FD-OLT-MIB.my
-- MIB generated by MG-SOFT Visual MIB Builder Version 6.0  Build 88
-- Tuesday, December 27, 2016 at 17:42:41
--
--  FD-OLT-MIB.my
-- MIB generated by MG-SOFT Visual MIB Builder Version 6.0  Build 88
-- Tuesday, July 14, 2015 at 17:04:02
--
--  FD-OLT-MIB.my
-- MIB generated by MG-SOFT Visual MIB Builder Version 6.0  Build 88
-- Friday, May 15, 2015 at 11:07:43
--
--  FD-OLT-MIB.my
-- MIB generated by MG-SOFT Visual MIB Builder Version 3.0 Build 253
-- Wednesday, March 13, 2013 at 09:01:23
--
--  FD-OLT-MIB.my
-- MIB generated by MG-SOFT Visual MIB Builder Version 3.0 Build 253
-- Tuesday, February 26, 2013 at 14:11:24
--
--  FD-OLT-MIB1.my
-- MIB generated by MG-SOFT Visual MIB Builder Version 3.0 Build 253
-- Tuesday, February 26, 2013 at 10:56:55
--
--  FD-OLT-MIB.my
-- MIB generated by MG-SOFT Visual MIB Builder Version 3.0 Build 253
-- Monday, October 29, 2012 at 17:56:58
--
--  FD-OLT-MIB.my
-- MIB generated by MG-SOFT Visual MIB Builder Version 3.0 Build 253
-- Thursday, August 30, 2012 at 20:49:49
--
--  FD-OLT-MIB.my
-- MIB generated by MG-SOFT Visual MIB Builder Version 3.0 Build 253
-- Tuesday, July 12, 2011 at 19:14:06
--
--  FD-OLT-MIB.mib
-- MIB generated by MG-SOFT Visual MIB Builder Version 3.0 Build 253
-- Monday, May 31, 2010 at 16:33:30
--

	FD-OLT-MIB DEFINITIONS ::= BEGIN

		IMPORTS
			epon, DeviceStatus, OperSwitch, DeviceOperation, DataDirection
				FROM EPON-EOC-MIB
			ponCardSlotId
				FROM FD-SYSTEM-MIB
			OBJECT-GROUP, MODULE-COMPLIANCE
				FROM SNMPv2-CONF
			IpAddress, Integer32, Unsigned32, OBJECT-TYPE, MODULE-IDENTITY
				FROM SNMPv2-SMI
			MacAddress, TruthValue, RowStatus
				FROM SNMPv2-TC;


--     1.3.6.1.4.1.34592.1.3.3
-- May 27, 2010 at 10:56 GMT
-- 1.3.6.1.4.1.34592.1.3.3
-- May 27, 2010 at 10:56 GMT
-- 1.3.6.1.4.1.34592.1.3.3
-- May 27, 2010 at 10:56 GMT
-- 1.3.6.1.4.1.34592.1.3.3
-- May 27, 2010 at 10:56 GMT
		-- 1.3.6.1.4.1.34592.1.3.3
		fdOlt MODULE-IDENTITY
			LAST-UPDATED "201005271056Z"		-- May 27, 2010 at 10:56 GMT
			ORGANIZATION
				"epon eoc factory."
			CONTACT-INFO
				" "
			DESCRIPTION
				"OLT mib module"
			::= { epon 3 }




--
-- Node definitions
--

--  Node definitions
--
-- Node definitions
--
-- Node definitions
--
-- Node definitions
-- 1.3.6.1.4.1.34592.1.3.3.1
-- 1.3.6.1.4.1.34592.1.3.3.1
-- 1.3.6.1.4.1.34592.1.3.3.1
-- 1.3.6.1.4.1.34592.1.3.3.1
		-- 1.3.6.1.4.1.34592.1.3.3.1
		oltBaseManageTable OBJECT-TYPE
			SYNTAX SEQUENCE OF OltBaseManageEntry
			MAX-ACCESS not-accessible
			STATUS current
			DESCRIPTION
				"OLT base management information table"
			::= { fdOlt 1 }


--      1.3.6.1.4.1.34592.1.3.3.1.1
-- 1.3.6.1.4.1.34592.1.3.3.1.1
-- 1.3.6.1.4.1.34592.1.3.3.1.1
-- 1.3.6.1.4.1.34592.1.3.3.1.1
		-- 1.3.6.1.4.1.34592.1.3.3.1.1
		oltBaseManageEntry OBJECT-TYPE
			SYNTAX OltBaseManageEntry
			MAX-ACCESS not-accessible
			STATUS current
			DESCRIPTION
				"Each entry in this table contain the info for one OLT (
				that is also called one PON port)"
			INDEX { ponCardSlotId, oltId }
			::= { oltBaseManageTable 1 }


		OltBaseManageEntry ::=
			SEQUENCE {
				oltId
					Integer32,
				oltMacAddr
					MacAddress,
				oltWorkState
					DeviceStatus,
				oltEnable
					OperSwitch,
				maxPermitLLIDNumber
					Unsigned32,
				registeredLLIDNumber
					Unsigned32,
				accessedOnuNumber
					Unsigned32,
				linkIdExhaust
					TruthValue,
				onuIdExhaust
					TruthValue,
				linkIdOverWrite
					TruthValue,
				onuIdOverWrite
					TruthValue,
				oltOperate
					DeviceOperation,
				oltUpgradeStat
					INTEGER,
				onuMgmtDefType
					INTEGER,
				oltPortBandwidth
					Integer32
			 }

--      1.3.6.1.4.1.34592.1.3.3.1.1.1
-- 1.3.6.1.4.1.34592.1.3.3.1.1.1
-- 1.3.6.1.4.1.34592.1.3.3.1.1.1
-- 1.3.6.1.4.1.34592.1.3.3.1.1.1
		-- 1.3.6.1.4.1.34592.1.3.3.1.1.1
		oltId OBJECT-TYPE
			SYNTAX INTEGER{	ponIf1(1),
				ponIf2(2),
				ponIf3(3),
				ponIf4(4),
				ponIf5(5),
				ponIf6(6),
				ponIf7(7),
				ponIf8(8),
				ponIf9(9),
				ponIf10(10),
				ponIf11(11),
				ponIf12(12),
				ponIf13(13),
				ponIf14(14),
				ponIf15(15),
				ponIf16(16)
				}
			MAX-ACCESS not-accessible
			STATUS current
			DESCRIPTION
				"Administratorly assigned identifier value"
			::= { oltBaseManageEntry 1 }


--      1.3.6.1.4.1.34592.1.3.3.1.1.2
-- 1.3.6.1.4.1.34592.1.3.3.1.1.2
-- 1.3.6.1.4.1.34592.1.3.3.1.1.2
-- 1.3.6.1.4.1.34592.1.3.3.1.1.2
		-- 1.3.6.1.4.1.34592.1.3.3.1.1.2
		oltMacAddr OBJECT-TYPE
			SYNTAX MacAddress
			MAX-ACCESS read-only
			STATUS current
			DESCRIPTION
				"OLT MAC address"
			::= { oltBaseManageEntry 2 }


--      1.3.6.1.4.1.34592.1.3.3.1.1.3
-- 1.3.6.1.4.1.34592.1.3.3.1.1.3
-- 1.3.6.1.4.1.34592.1.3.3.1.1.3
-- 1.3.6.1.4.1.34592.1.3.3.1.1.3
		-- 1.3.6.1.4.1.34592.1.3.3.1.1.3
		oltWorkState OBJECT-TYPE
			SYNTAX DeviceStatus
			MAX-ACCESS read-only
			STATUS current
			DESCRIPTION
				"work status of the OLT"
			::= { oltBaseManageEntry 3 }


--      1.3.6.1.4.1.34592.1.3.3.1.1.4
-- 1.3.6.1.4.1.34592.1.3.3.1.1.4
-- 1.3.6.1.4.1.34592.1.3.3.1.1.4
-- 1.3.6.1.4.1.34592.1.3.3.1.1.4
		-- 1.3.6.1.4.1.34592.1.3.3.1.1.4
		oltEnable OBJECT-TYPE
			SYNTAX OperSwitch
			MAX-ACCESS read-write
			STATUS current
			DESCRIPTION
				"This object is used to enable or disable the OLT.
				When enabled, the olt will pass user traffic;
				When disabled,the olt will turning off the EPON port
				and blocking all traffic in both directions"
			::= { oltBaseManageEntry 4 }


--      1.3.6.1.4.1.34592.1.3.3.1.1.5
-- 1.3.6.1.4.1.34592.1.3.3.1.1.5
-- 1.3.6.1.4.1.34592.1.3.3.1.1.5
-- 1.3.6.1.4.1.34592.1.3.3.1.1.5
		-- 1.3.6.1.4.1.34592.1.3.3.1.1.5
		maxPermitLLIDNumber OBJECT-TYPE
			SYNTAX Unsigned32 (0..256)
			MAX-ACCESS read-write
			STATUS current
			DESCRIPTION
				"LLID number that the olt allow to register, this value can only
				be changed when the olt is disabled."
			::= { oltBaseManageEntry 5 }


--      1.3.6.1.4.1.34592.1.3.3.1.1.6
-- 1.3.6.1.4.1.34592.1.3.3.1.1.6
-- 1.3.6.1.4.1.34592.1.3.3.1.1.6
-- 1.3.6.1.4.1.34592.1.3.3.1.1.6
		-- 1.3.6.1.4.1.34592.1.3.3.1.1.6
		registeredLLIDNumber OBJECT-TYPE
			SYNTAX Unsigned32 (0..256)
			MAX-ACCESS read-only
			STATUS current
			DESCRIPTION
				"LLID number that registered now on this OLT"
			::= { oltBaseManageEntry 6 }


--      1.3.6.1.4.1.34592.1.3.3.1.1.7
-- 1.3.6.1.4.1.34592.1.3.3.1.1.7
-- 1.3.6.1.4.1.34592.1.3.3.1.1.7
-- 1.3.6.1.4.1.34592.1.3.3.1.1.7
		-- 1.3.6.1.4.1.34592.1.3.3.1.1.7
		accessedOnuNumber OBJECT-TYPE
			SYNTAX Unsigned32 (1..64)
			MAX-ACCESS read-only
			STATUS current
			DESCRIPTION
				"The accessed physical ONU number, 'physical' is opposite to
				'dummy', a 'Logical Link' is also called a dummy ONU to the OLT
				"
			::= { oltBaseManageEntry 7 }


--      1.3.6.1.4.1.34592.1.3.3.1.1.8
-- 1.3.6.1.4.1.34592.1.3.3.1.1.8
-- 1.3.6.1.4.1.34592.1.3.3.1.1.8
-- 1.3.6.1.4.1.34592.1.3.3.1.1.8
		-- 1.3.6.1.4.1.34592.1.3.3.1.1.8
		linkIdExhaust OBJECT-TYPE
			SYNTAX TruthValue
			MAX-ACCESS read-only
			STATUS current
			DESCRIPTION
				"Indicate if there is available linkId which can be allocated
				to new registered Logical Link"
			::= { oltBaseManageEntry 8 }


--      1.3.6.1.4.1.34592.1.3.3.1.1.9
-- 1.3.6.1.4.1.34592.1.3.3.1.1.9
-- 1.3.6.1.4.1.34592.1.3.3.1.1.9
-- 1.3.6.1.4.1.34592.1.3.3.1.1.9
		-- 1.3.6.1.4.1.34592.1.3.3.1.1.9
		onuIdExhaust OBJECT-TYPE
			SYNTAX TruthValue
			MAX-ACCESS read-only
			STATUS current
			DESCRIPTION
				"Refer to linkIdExhaust desc"
			::= { oltBaseManageEntry 9 }


--      1.3.6.1.4.1.34592.1.3.3.1.1.10
-- 1.3.6.1.4.1.34592.1.3.3.1.1.10
-- 1.3.6.1.4.1.34592.1.3.3.1.1.10
-- 1.3.6.1.4.1.34592.1.3.3.1.1.10
		-- 1.3.6.1.4.1.34592.1.3.3.1.1.10
		linkIdOverWrite OBJECT-TYPE
			SYNTAX TruthValue
			MAX-ACCESS read-write
			STATUS current
			DESCRIPTION
				"Description. This object is used to config linkId overwrite
				operation. LinkId is system resource managed by PON card
				firmware and used to identify each Logical Link.

				When a new Link register, a LinkId will be assigned.
				When the registered Link off-line or de-register,the
				assigned LinkId will still be reserved. Such a policy
				will lead a result that is the allowed linkId resource
				exhaust. When this occurred, the device manager can have
				two choices, delete the off-line linkId entry manually
				or permit the device firmware itself to overwrite the
				oldest assigned linkId by seting the value of this object
				to 'yes'.

				Generally, the choice will be made based on if the user
				care the off-line Links' configurations and status. If don't
				care, set this value to 'yes' will be a better choice.

				 "
			::= { oltBaseManageEntry 10 }


--      1.3.6.1.4.1.34592.1.3.3.1.1.11
-- 1.3.6.1.4.1.34592.1.3.3.1.1.11
-- 1.3.6.1.4.1.34592.1.3.3.1.1.11
-- 1.3.6.1.4.1.34592.1.3.3.1.1.11
		-- 1.3.6.1.4.1.34592.1.3.3.1.1.11
		onuIdOverWrite OBJECT-TYPE
			SYNTAX TruthValue
			MAX-ACCESS read-write
			STATUS current
			DESCRIPTION
				"Refer to 'linkIdOverWrite' description"
			::= { oltBaseManageEntry 11 }


--      1.3.6.1.4.1.34592.1.3.3.1.1.20
-- 1.3.6.1.4.1.34592.1.3.3.1.1.20
-- 1.3.6.1.4.1.34592.1.3.3.1.1.20
-- 1.3.6.1.4.1.34592.1.3.3.1.1.20
		-- 1.3.6.1.4.1.34592.1.3.3.1.1.20
		oltOperate OBJECT-TYPE
			SYNTAX DeviceOperation
			MAX-ACCESS read-write
			STATUS current
			DESCRIPTION
				"This object define a collection of operate actions which
				can be apply on olt device"
			::= { oltBaseManageEntry 20 }


--      1.3.6.1.4.1.34592.1.3.3.1.1.21
-- 1.3.6.1.4.1.34592.1.3.3.1.1.21
-- 1.3.6.1.4.1.34592.1.3.3.1.1.21
-- 1.3.6.1.4.1.34592.1.3.3.1.1.21
		-- 1.3.6.1.4.1.34592.1.3.3.1.1.21
		oltUpgradeStat OBJECT-TYPE
			SYNTAX INTEGER
				{
				booting(1),
				normalRun(2),
				upgrading(6),
				upgradeOk(7),
				upgradeErr(8),
				upgradeOnu(10)
				}
			MAX-ACCESS read-only
			STATUS current
			DESCRIPTION
				"Description."
			::= { oltBaseManageEntry 21 }


--      1.3.6.1.4.1.34592.1.3.3.1.1.22
-- 1.3.6.1.4.1.34592.1.3.3.1.1.22
-- 1.3.6.1.4.1.34592.1.3.3.1.1.22
-- 1.3.6.1.4.1.34592.1.3.3.1.1.22
		-- 1.3.6.1.4.1.34592.1.3.3.1.1.22
		onuMgmtDefType OBJECT-TYPE
			SYNTAX INTEGER
				{
				onuMgmtTk(1),
				onuMgmtCtc(2)
				}
			MAX-ACCESS read-write
			STATUS current
			DESCRIPTION
				"Description."
			::= { oltBaseManageEntry 22 }


		-- 1.3.6.1.4.1.34592.1.3.3.1.1.23
		oltPortBandwidth OBJECT-TYPE
			SYNTAX Integer32
			MAX-ACCESS read-only
			STATUS current
			DESCRIPTION
				"Description."
			::= { oltBaseManageEntry 23 }


--      1.3.6.1.4.1.34592.1.3.3.4
-- 1.3.6.1.4.1.34592.1.3.3.4
-- 1.3.6.1.4.1.34592.1.3.3.4
-- 1.3.6.1.4.1.34592.1.3.3.4
		-- 1.3.6.1.4.1.34592.1.3.3.4
		oltAdvancedManage OBJECT IDENTIFIER ::= { fdOlt 4 }


--      1.3.6.1.4.1.34592.1.3.3.4.1
-- 1.3.6.1.4.1.34592.1.3.3.4.1
-- 1.3.6.1.4.1.34592.1.3.3.4.1
-- 1.3.6.1.4.1.34592.1.3.3.4.1
		-- 1.3.6.1.4.1.34592.1.3.3.4.1
		oltChipInfoTable OBJECT-TYPE
			SYNTAX SEQUENCE OF OltChipInfoEntry
			MAX-ACCESS not-accessible
			STATUS current
			DESCRIPTION
				"Description. reserved, may or may not support"
			::= { oltAdvancedManage 1 }


--      1.3.6.1.4.1.34592.1.3.3.4.1.1
-- 1.3.6.1.4.1.34592.1.3.3.4.1.1
-- 1.3.6.1.4.1.34592.1.3.3.4.1.1
-- 1.3.6.1.4.1.34592.1.3.3.4.1.1
		-- 1.3.6.1.4.1.34592.1.3.3.4.1.1
		oltChipInfoEntry OBJECT-TYPE
			SYNTAX OltChipInfoEntry
			MAX-ACCESS not-accessible
			STATUS current
			DESCRIPTION
				"Each entry in this table contain an olt info"
			INDEX { ponCardSlotId, oltId }
			::= { oltChipInfoTable 1 }


		OltChipInfoEntry ::=
			SEQUENCE {
				oltChipProCode
					Unsigned32,
				oltChipVer
					Unsigned32,
				oltChipFirmVer
					Unsigned32,
				oltChipBootVer
					Unsigned32,
				oltChipPersVer
					Unsigned32,
				oltChipApp0Ver
					Unsigned32,
				oltChipApp1Ver
					Unsigned32,
				oltChipDiagVer
					Unsigned32
			 }

--      1.3.6.1.4.1.34592.1.3.3.4.1.1.1
-- 1.3.6.1.4.1.34592.1.3.3.4.1.1.1
-- 1.3.6.1.4.1.34592.1.3.3.4.1.1.1
-- 1.3.6.1.4.1.34592.1.3.3.4.1.1.1
		-- 1.3.6.1.4.1.34592.1.3.3.4.1.1.1
		oltChipProCode OBJECT-TYPE
			SYNTAX Unsigned32
			MAX-ACCESS read-only
			STATUS current
			DESCRIPTION
				"Description. olt chip product code"
			::= { oltChipInfoEntry 1 }


--      1.3.6.1.4.1.34592.1.3.3.4.1.1.2
-- 1.3.6.1.4.1.34592.1.3.3.4.1.1.2
-- 1.3.6.1.4.1.34592.1.3.3.4.1.1.2
-- 1.3.6.1.4.1.34592.1.3.3.4.1.1.2
		-- 1.3.6.1.4.1.34592.1.3.3.4.1.1.2
		oltChipVer OBJECT-TYPE
			SYNTAX Unsigned32
			MAX-ACCESS read-only
			STATUS current
			DESCRIPTION
				"Description.olt chip version"
			::= { oltChipInfoEntry 2 }


--      1.3.6.1.4.1.34592.1.3.3.4.1.1.3
-- 1.3.6.1.4.1.34592.1.3.3.4.1.1.3
-- 1.3.6.1.4.1.34592.1.3.3.4.1.1.3
-- 1.3.6.1.4.1.34592.1.3.3.4.1.1.3
		-- 1.3.6.1.4.1.34592.1.3.3.4.1.1.3
		oltChipFirmVer OBJECT-TYPE
			SYNTAX Unsigned32
			MAX-ACCESS read-only
			STATUS current
			DESCRIPTION
				"Description.olt chip frimware version"
			::= { oltChipInfoEntry 3 }


--      1.3.6.1.4.1.34592.1.3.3.4.1.1.4
-- 1.3.6.1.4.1.34592.1.3.3.4.1.1.4
-- 1.3.6.1.4.1.34592.1.3.3.4.1.1.4
-- 1.3.6.1.4.1.34592.1.3.3.4.1.1.4
		-- 1.3.6.1.4.1.34592.1.3.3.4.1.1.4
		oltChipBootVer OBJECT-TYPE
			SYNTAX Unsigned32
			MAX-ACCESS read-only
			STATUS current
			DESCRIPTION
				"olt chip boot firmware version"
			::= { oltChipInfoEntry 4 }


--      1.3.6.1.4.1.34592.1.3.3.4.1.1.5
-- 1.3.6.1.4.1.34592.1.3.3.4.1.1.5
-- 1.3.6.1.4.1.34592.1.3.3.4.1.1.5
-- 1.3.6.1.4.1.34592.1.3.3.4.1.1.5
		-- 1.3.6.1.4.1.34592.1.3.3.4.1.1.5
		oltChipPersVer OBJECT-TYPE
			SYNTAX Unsigned32
			MAX-ACCESS read-only
			STATUS current
			DESCRIPTION
				"olt chip's personality file version"
			::= { oltChipInfoEntry 5 }


--      1.3.6.1.4.1.34592.1.3.3.4.1.1.6
-- 1.3.6.1.4.1.34592.1.3.3.4.1.1.6
-- 1.3.6.1.4.1.34592.1.3.3.4.1.1.6
-- 1.3.6.1.4.1.34592.1.3.3.4.1.1.6
		-- 1.3.6.1.4.1.34592.1.3.3.4.1.1.6
		oltChipApp0Ver OBJECT-TYPE
			SYNTAX Unsigned32
			MAX-ACCESS read-only
			STATUS current
			DESCRIPTION
				"olt chip application file version"
			::= { oltChipInfoEntry 6 }


--      1.3.6.1.4.1.34592.1.3.3.4.1.1.7
-- 1.3.6.1.4.1.34592.1.3.3.4.1.1.7
-- 1.3.6.1.4.1.34592.1.3.3.4.1.1.7
-- 1.3.6.1.4.1.34592.1.3.3.4.1.1.7
		-- 1.3.6.1.4.1.34592.1.3.3.4.1.1.7
		oltChipApp1Ver OBJECT-TYPE
			SYNTAX Unsigned32
			MAX-ACCESS read-only
			STATUS current
			DESCRIPTION
				"olt chip application file version"
			::= { oltChipInfoEntry 7 }


--      1.3.6.1.4.1.34592.1.3.3.4.1.1.8
-- 1.3.6.1.4.1.34592.1.3.3.4.1.1.8
-- 1.3.6.1.4.1.34592.1.3.3.4.1.1.8
-- 1.3.6.1.4.1.34592.1.3.3.4.1.1.8
		-- 1.3.6.1.4.1.34592.1.3.3.4.1.1.8
		oltChipDiagVer OBJECT-TYPE
			SYNTAX Unsigned32
			MAX-ACCESS read-only
			STATUS current
			DESCRIPTION
				"olt chip diagnostic file version"
			::= { oltChipInfoEntry 8 }


--      1.3.6.1.4.1.34592.1.3.3.4.2
-- 1.3.6.1.4.1.34592.1.3.3.4.2
-- 1.3.6.1.4.1.34592.1.3.3.4.2
-- 1.3.6.1.4.1.34592.1.3.3.4.2
		-- 1.3.6.1.4.1.34592.1.3.3.4.2
		oltOamRateTable OBJECT-TYPE
			SYNTAX SEQUENCE OF OltOamRateEntry
			MAX-ACCESS not-accessible
			STATUS current
			DESCRIPTION
				"olt oam rate configurations"
			::= { oltAdvancedManage 2 }


--      1.3.6.1.4.1.34592.1.3.3.4.2.1
-- 1.3.6.1.4.1.34592.1.3.3.4.2.1
-- 1.3.6.1.4.1.34592.1.3.3.4.2.1
-- 1.3.6.1.4.1.34592.1.3.3.4.2.1
		-- 1.3.6.1.4.1.34592.1.3.3.4.2.1
		oltOamRateEntry OBJECT-TYPE
			SYNTAX OltOamRateEntry
			MAX-ACCESS not-accessible
			STATUS current
			DESCRIPTION
				"Each entry in this table contain configurations for each OLT"
			INDEX { ponCardSlotId, oltId }
			::= { oltOamRateTable 1 }


		OltOamRateEntry ::=
			SEQUENCE {
				minOamRate
					Integer32,
				maxOamRate
					Integer32,
				oamRspTimeout
					Integer32
			 }

--      1.3.6.1.4.1.34592.1.3.3.4.2.1.1
-- 1.3.6.1.4.1.34592.1.3.3.4.2.1.1
-- 1.3.6.1.4.1.34592.1.3.3.4.2.1.1
-- 1.3.6.1.4.1.34592.1.3.3.4.2.1.1
		-- 1.3.6.1.4.1.34592.1.3.3.4.2.1.1
		minOamRate OBJECT-TYPE
			SYNTAX Integer32 (0..255)
			UNITS "sec/PDU"
			MAX-ACCESS read-write
			STATUS current
			DESCRIPTION
				"Description. Reserved, EMS may not be support"
			::= { oltOamRateEntry 1 }


--      1.3.6.1.4.1.34592.1.3.3.4.2.1.2
-- 1.3.6.1.4.1.34592.1.3.3.4.2.1.2
-- 1.3.6.1.4.1.34592.1.3.3.4.2.1.2
-- 1.3.6.1.4.1.34592.1.3.3.4.2.1.2
		-- 1.3.6.1.4.1.34592.1.3.3.4.2.1.2
		maxOamRate OBJECT-TYPE
			SYNTAX Integer32 (0..255)
			UNITS "PDUs/sec"
			MAX-ACCESS read-write
			STATUS current
			DESCRIPTION
				"Description. Reserved, EMS may not be support"
			::= { oltOamRateEntry 2 }


--      1.3.6.1.4.1.34592.1.3.3.4.2.1.3
-- 1.3.6.1.4.1.34592.1.3.3.4.2.1.3
-- 1.3.6.1.4.1.34592.1.3.3.4.2.1.3
-- 1.3.6.1.4.1.34592.1.3.3.4.2.1.3
		-- 1.3.6.1.4.1.34592.1.3.3.4.2.1.3
		oamRspTimeout OBJECT-TYPE
			SYNTAX Integer32 (1..255)
			UNITS "sec"
			MAX-ACCESS read-write
			STATUS current
			DESCRIPTION
				"Description. Reserved, EMS may not be support"
			::= { oltOamRateEntry 3 }


--      1.3.6.1.4.1.34592.1.3.3.4.3
-- 1.3.6.1.4.1.34592.1.3.3.4.3
-- 1.3.6.1.4.1.34592.1.3.3.4.3
-- 1.3.6.1.4.1.34592.1.3.3.4.3
		-- 1.3.6.1.4.1.34592.1.3.3.4.3
		discoveryParaTable OBJECT-TYPE
			SYNTAX SEQUENCE OF DiscoveryParaEntry
			MAX-ACCESS not-accessible
			STATUS current
			DESCRIPTION
				"Description. Reserved.
				ONU discovery process parameters. These parameters are
				associated with the transmit distance"
			::= { oltAdvancedManage 3 }


--      1.3.6.1.4.1.34592.1.3.3.4.3.1
-- 1.3.6.1.4.1.34592.1.3.3.4.3.1
-- 1.3.6.1.4.1.34592.1.3.3.4.3.1
-- 1.3.6.1.4.1.34592.1.3.3.4.3.1
		-- 1.3.6.1.4.1.34592.1.3.3.4.3.1
		discoveryParaEntry OBJECT-TYPE
			SYNTAX DiscoveryParaEntry
			MAX-ACCESS not-accessible
			STATUS current
			DESCRIPTION
				"Each entry in this table contain configurations for each OLT"
			INDEX { ponCardSlotId, oltId }
			::= { discoveryParaTable 1 }


		DiscoveryParaEntry ::=
			SEQUENCE {
				discoverPeriod
					Integer32,
				discoverWindow
					Integer32,
				discoverTimeoutVal
					Integer32
			 }

--      1.3.6.1.4.1.34592.1.3.3.4.3.1.1
-- 1.3.6.1.4.1.34592.1.3.3.4.3.1.1
-- 1.3.6.1.4.1.34592.1.3.3.4.3.1.1
-- 1.3.6.1.4.1.34592.1.3.3.4.3.1.1
		-- 1.3.6.1.4.1.34592.1.3.3.4.3.1.1
		discoverPeriod OBJECT-TYPE
			SYNTAX Integer32 (10..65535)
			UNITS "ms"
			MAX-ACCESS read-write
			STATUS current
			DESCRIPTION
				"Discovery process parameters"
			DEFVAL { 1000 }
			::= { discoveryParaEntry 1 }


--      1.3.6.1.4.1.34592.1.3.3.4.3.1.2
-- 1.3.6.1.4.1.34592.1.3.3.4.3.1.2
-- 1.3.6.1.4.1.34592.1.3.3.4.3.1.2
-- 1.3.6.1.4.1.34592.1.3.3.4.3.1.2
		-- 1.3.6.1.4.1.34592.1.3.3.4.3.1.2
		discoverWindow OBJECT-TYPE
			SYNTAX Integer32 (84..131070)
			UNITS "bytes"
			MAX-ACCESS read-write
			STATUS current
			DESCRIPTION
				"Discovery process parameters"
			DEFVAL { 16319 }
			::= { discoveryParaEntry 2 }


--      1.3.6.1.4.1.34592.1.3.3.4.3.1.3
-- 1.3.6.1.4.1.34592.1.3.3.4.3.1.3
-- 1.3.6.1.4.1.34592.1.3.3.4.3.1.3
-- 1.3.6.1.4.1.34592.1.3.3.4.3.1.3
		-- 1.3.6.1.4.1.34592.1.3.3.4.3.1.3
		discoverTimeoutVal OBJECT-TYPE
			SYNTAX Integer32 (1..65535)
			UNITS "100ms"
			MAX-ACCESS read-write
			STATUS current
			DESCRIPTION
				"Discovery process parameters"
			DEFVAL { 600 }
			::= { discoveryParaEntry 3 }


--      1.3.6.1.4.1.34592.1.3.3.4.4
-- 1.3.6.1.4.1.34592.1.3.3.4.4
-- 1.3.6.1.4.1.34592.1.3.3.4.4
-- 1.3.6.1.4.1.34592.1.3.3.4.4
		-- 1.3.6.1.4.1.34592.1.3.3.4.4
		oltAdvancedConfigTable OBJECT-TYPE
			SYNTAX SEQUENCE OF OltAdvancedConfigEntry
			MAX-ACCESS not-accessible
			STATUS current
			DESCRIPTION
				"This table contain the information which is not normally
				used but may be usefull in some special circumstance "
			::= { oltAdvancedManage 4 }


--      1.3.6.1.4.1.34592.1.3.3.4.4.1
-- 1.3.6.1.4.1.34592.1.3.3.4.4.1
-- 1.3.6.1.4.1.34592.1.3.3.4.4.1
-- 1.3.6.1.4.1.34592.1.3.3.4.4.1
		-- 1.3.6.1.4.1.34592.1.3.3.4.4.1
		oltAdvancedConfigEntry OBJECT-TYPE
			SYNTAX OltAdvancedConfigEntry
			MAX-ACCESS not-accessible
			STATUS current
			DESCRIPTION
				"Each entry in this table contain the information for one OLT "
			INDEX { ponCardSlotId, oltId }
			::= { oltAdvancedConfigTable 1 }


		OltAdvancedConfigEntry ::=
			SEQUENCE {
				oltAddiVlanEthType
					OCTET STRING,
				onuUltraLongDistanceTrans
					OperSwitch,
				oltBroadCastRateCtl
					OperSwitch,
				oltMultiCastRateCtl
					OperSwitch,
				oltUnkUcCastRateCtl
					OperSwitch,
				oltBroadCastRate
					Integer32
			 }

--      1.3.6.1.4.1.34592.1.3.3.4.4.1.1
-- 1.3.6.1.4.1.34592.1.3.3.4.4.1.1
-- 1.3.6.1.4.1.34592.1.3.3.4.4.1.1
-- 1.3.6.1.4.1.34592.1.3.3.4.4.1.1
		-- 1.3.6.1.4.1.34592.1.3.3.4.4.1.1
		oltAddiVlanEthType OBJECT-TYPE
			SYNTAX OCTET STRING (SIZE (4))
			MAX-ACCESS read-write
			STATUS current
			DESCRIPTION
				"Additional Ethernet type to identify vlan frames.

				0     1           2                3
				---------------------------------------------
				vlan EthType| tag upstream | tag downstream |
				---------------------------------------------
				  2byte         1byte            1byte

				vlan EthType: default 0x8100
				tag upstream: 1->use this type to tag upstream, 0->untag
				tag downstream: 1->use this type to tag downstream, 0->untag"
			::= { oltAdvancedConfigEntry 1 }


--      1.3.6.1.4.1.34592.1.3.3.4.4.1.2
-- 1.3.6.1.4.1.34592.1.3.3.4.4.1.2
-- 1.3.6.1.4.1.34592.1.3.3.4.4.1.2
-- 1.3.6.1.4.1.34592.1.3.3.4.4.1.2
		-- 1.3.6.1.4.1.34592.1.3.3.4.4.1.2
		onuUltraLongDistanceTrans OBJECT-TYPE
			SYNTAX OperSwitch
			MAX-ACCESS read-write
			STATUS current
			DESCRIPTION
				"Description.Reserved.

				This object is used for enable the ultra-long distance
				transmission of PON.

				Normally, this object should not be changed, the disable
				allowwed transmit distance is 20KM for PON standard.
				But,if some user want it transmit more longer than standard
				for some special case, he can set this value to true.

				When change this configuration, several parameters should be
				changed internally. Detail operations will not be descripted
				here.

				"
			::= { oltAdvancedConfigEntry 2 }


--      1.3.6.1.4.1.34592.1.3.3.4.4.1.3
-- 1.3.6.1.4.1.34592.1.3.3.4.4.1.3
-- 1.3.6.1.4.1.34592.1.3.3.4.4.1.3
-- 1.3.6.1.4.1.34592.1.3.3.4.4.1.3
		-- 1.3.6.1.4.1.34592.1.3.3.4.4.1.3
		oltBroadCastRateCtl OBJECT-TYPE
			SYNTAX OperSwitch
			MAX-ACCESS read-write
			STATUS current
			DESCRIPTION
				"Description."
			::= { oltAdvancedConfigEntry 3 }


--      1.3.6.1.4.1.34592.1.3.3.4.4.1.4
-- 1.3.6.1.4.1.34592.1.3.3.4.4.1.4
-- 1.3.6.1.4.1.34592.1.3.3.4.4.1.4
-- 1.3.6.1.4.1.34592.1.3.3.4.4.1.4
		-- 1.3.6.1.4.1.34592.1.3.3.4.4.1.4
		oltMultiCastRateCtl OBJECT-TYPE
			SYNTAX OperSwitch
			MAX-ACCESS read-write
			STATUS current
			DESCRIPTION
				"Description."
			::= { oltAdvancedConfigEntry 4 }


--      1.3.6.1.4.1.34592.1.3.3.4.4.1.5
-- 1.3.6.1.4.1.34592.1.3.3.4.4.1.5
-- 1.3.6.1.4.1.34592.1.3.3.4.4.1.5
-- 1.3.6.1.4.1.34592.1.3.3.4.4.1.5
		-- 1.3.6.1.4.1.34592.1.3.3.4.4.1.5
		oltUnkUcCastRateCtl OBJECT-TYPE
			SYNTAX OperSwitch
			MAX-ACCESS read-write
			STATUS current
			DESCRIPTION
				"Description."
			::= { oltAdvancedConfigEntry 5 }


--      1.3.6.1.4.1.34592.1.3.3.4.4.1.6
-- 1.3.6.1.4.1.34592.1.3.3.4.4.1.6
-- 1.3.6.1.4.1.34592.1.3.3.4.4.1.6
-- 1.3.6.1.4.1.34592.1.3.3.4.4.1.6
		-- 1.3.6.1.4.1.34592.1.3.3.4.4.1.6
		oltBroadCastRate OBJECT-TYPE
			SYNTAX Integer32 (0..1000000)
			MAX-ACCESS read-write
			STATUS current
			DESCRIPTION
				"Description."
			::= { oltAdvancedConfigEntry 6 }


--  1.3.6.1.4.1.34592.1.3.3.4.5
		-- 1.3.6.1.4.1.34592.1.3.3.4.5
		oltDdmInfoTable OBJECT-TYPE
			SYNTAX SEQUENCE OF OltDdmInfoEntry
			MAX-ACCESS not-accessible
			STATUS current
			DESCRIPTION
				"Description."
			::= { oltAdvancedManage 5 }


--  1.3.6.1.4.1.34592.1.3.3.4.5.1
		-- 1.3.6.1.4.1.34592.1.3.3.4.5.1
		oltDdmInfoEntry OBJECT-TYPE
			SYNTAX OltDdmInfoEntry
			MAX-ACCESS not-accessible
			STATUS current
			DESCRIPTION
				"Description."
			INDEX { ponCardSlotId, oltId }
			::= { oltDdmInfoTable 1 }


		OltDdmInfoEntry ::=
			SEQUENCE {
				oltDdmInfoTemperature
					Integer32,
				oltDdmInfoVoltage
					Integer32,
				oltDdmInfoTxBias
					Integer32,
				oltDdmInfoTxPower
					Integer32,
				oltDdmInfoRxPower
					Integer32,
				oltDdmInfoVendor
					Integer32,
				oltDdmInfoProductName
					Integer32,
				oltDdmInfoVersion
					Integer32,
				oltDdmInfoSn
					Integer32
			 }

--  1.3.6.1.4.1.34592.1.3.3.4.5.1.1
		-- 1.3.6.1.4.1.34592.1.3.3.4.5.1.1
		oltDdmInfoTemperature OBJECT-TYPE
			SYNTAX Integer32
			MAX-ACCESS read-only
			STATUS current
			DESCRIPTION
				"Description.
				OLT DDM Info Temperature(unit:0.01C). "
			::= { oltDdmInfoEntry 1 }


--  1.3.6.1.4.1.34592.1.3.3.4.5.1.2
		-- 1.3.6.1.4.1.34592.1.3.3.4.5.1.2
		oltDdmInfoVoltage OBJECT-TYPE
			SYNTAX Integer32
			MAX-ACCESS read-only
			STATUS current
			DESCRIPTION
				"Description.
				OLT DDM Info Voltage(unit:0.01V)."
			::= { oltDdmInfoEntry 2 }


--  1.3.6.1.4.1.34592.1.3.3.4.5.1.3
		-- 1.3.6.1.4.1.34592.1.3.3.4.5.1.3
		oltDdmInfoTxBias OBJECT-TYPE
			SYNTAX Integer32
			MAX-ACCESS read-only
			STATUS current
			DESCRIPTION
				"Description.
				OLT DDM Info TX Bias(unit:0.01mA)."
			::= { oltDdmInfoEntry 3 }


--  1.3.6.1.4.1.34592.1.3.3.4.5.1.4
		-- 1.3.6.1.4.1.34592.1.3.3.4.5.1.4
		oltDdmInfoTxPower OBJECT-TYPE
			SYNTAX Integer32
			MAX-ACCESS read-only
			STATUS current
			DESCRIPTION
				"Description.
				OLT DDM Info TX power(unit:0.01dBm)."
			::= { oltDdmInfoEntry 4 }


--  1.3.6.1.4.1.34592.1.3.3.4.5.1.5
		-- 1.3.6.1.4.1.34592.1.3.3.4.5.1.5
		oltDdmInfoRxPower OBJECT-TYPE
			SYNTAX Integer32
			MAX-ACCESS read-only
			STATUS current
			DESCRIPTION
				"Description.
				OLT DDM Info RX power(unit:0.01dBm)."
			::= { oltDdmInfoEntry 5 }


--  1.3.6.1.4.1.34592.1.3.3.4.5.1.6
		-- 1.3.6.1.4.1.34592.1.3.3.4.5.1.6
		oltDdmInfoVendor OBJECT-TYPE
			SYNTAX Integer32
			MAX-ACCESS read-only
			STATUS current
			DESCRIPTION
				"Description.
				OLT DDM Info Vendor."
			::= { oltDdmInfoEntry 6 }


--  1.3.6.1.4.1.34592.1.3.3.4.5.1.7
		-- 1.3.6.1.4.1.34592.1.3.3.4.5.1.7
		oltDdmInfoProductName OBJECT-TYPE
			SYNTAX Integer32
			MAX-ACCESS read-only
			STATUS current
			DESCRIPTION
				"Description.
				OLT DDM Info Product name."
			::= { oltDdmInfoEntry 7 }


--  1.3.6.1.4.1.34592.1.3.3.4.5.1.8
		-- 1.3.6.1.4.1.34592.1.3.3.4.5.1.8
		oltDdmInfoVersion OBJECT-TYPE
			SYNTAX Integer32
			MAX-ACCESS read-only
			STATUS current
			DESCRIPTION
				"Description.
				OLT DDM Info Version."
			::= { oltDdmInfoEntry 8 }


--  1.3.6.1.4.1.34592.1.3.3.4.5.1.9
		-- 1.3.6.1.4.1.34592.1.3.3.4.5.1.9
		oltDdmInfoSn OBJECT-TYPE
			SYNTAX Integer32
			MAX-ACCESS read-only
			STATUS current
			DESCRIPTION
				"Description.
				OLT DDM Info Serial number."
			::= { oltDdmInfoEntry 9 }

--  1.3.6.1.4.1.34592.1.3.3.4.6
		-- 1.3.6.1.4.1.34592.1.3.3.4.6
		oltEncryptTable OBJECT-TYPE
			SYNTAX SEQUENCE OF OltEncryptEntry
			MAX-ACCESS not-accessible
			STATUS current
			DESCRIPTION
				"Description."
			::= { oltAdvancedManage 6 }

--    1.3.6.1.4.1.34592.1.3.3.4.6.1
-- 1.3.6.1.4.1.34592.1.3.3.4.6.1
-- 1.3.6.1.4.1.34592.1.3.3.4.6.1
		-- 1.3.6.1.4.1.34592.1.3.3.4.6.1
		OltEncryptEntry OBJECT-TYPE
			SYNTAX OltEncryptEntry
			MAX-ACCESS not-accessible
			STATUS current
			DESCRIPTION
				"Description."
			INDEX { ponCardSlotId, oltId}
			::= { oltEncryptTable 1 }


		OltEncryptEntry ::=
			SEQUENCE {
				oltEncryptData
					OCTET STRING
			 }

--    1.3.6.1.4.1.34592.1.3.3.4.6.1.1
-- 1.3.6.1.4.1.34592.1.3.3.4.6.1.1
-- 1.3.6.1.4.1.34592.1.3.3.4.6.1.1
		-- 1.3.6.1.4.1.34592.1.3.3.4.6.1.1
		oltEncryptData OBJECT-TYPE
			SYNTAX OCTET STRING
			MAX-ACCESS read-write
			STATUS current
			DESCRIPTION
				"Description: "
			::= { OltEncryptEntry 1 }

--      1.3.6.1.4.1.34592.1.3.3.5
-- 1.3.6.1.4.1.34592.1.3.3.5
-- 1.3.6.1.4.1.34592.1.3.3.5
-- 1.3.6.1.4.1.34592.1.3.3.5
		-- 1.3.6.1.4.1.34592.1.3.3.5
		oltBridgeConfigTable OBJECT-TYPE
			SYNTAX SEQUENCE OF OltBridgeConfigEntry
			MAX-ACCESS not-accessible
			STATUS current
			DESCRIPTION
				" "
			::= { fdOlt 5 }


--      1.3.6.1.4.1.34592.1.3.3.5.1
-- 1.3.6.1.4.1.34592.1.3.3.5.1
-- 1.3.6.1.4.1.34592.1.3.3.5.1
-- 1.3.6.1.4.1.34592.1.3.3.5.1
		-- 1.3.6.1.4.1.34592.1.3.3.5.1
		oltBridgeConfigEntry OBJECT-TYPE
			SYNTAX OltBridgeConfigEntry
			MAX-ACCESS not-accessible
			STATUS current
			DESCRIPTION
				" "
			INDEX { ponCardSlotId, oltId }
			::= { oltBridgeConfigTable 1 }


		OltBridgeConfigEntry ::=
			SEQUENCE {
				dynMacAgeTime
					Integer32,
				downStreamResetAgeTimer
					OperSwitch,
				bridgedVlanNumber
					Integer32,
				macOverWrite
					OperSwitch,
				discardUnknownMac
					OperSwitch,
				forwardTagOnSimpleBridge
					OperSwitch
			 }

--      1.3.6.1.4.1.34592.1.3.3.5.1.1
-- 1.3.6.1.4.1.34592.1.3.3.5.1.1
-- 1.3.6.1.4.1.34592.1.3.3.5.1.1
-- 1.3.6.1.4.1.34592.1.3.3.5.1.1
		-- 1.3.6.1.4.1.34592.1.3.3.5.1.1
		dynMacAgeTime OBJECT-TYPE
			SYNTAX Integer32 (0..2419200)
			MAX-ACCESS read-write
			STATUS current
			DESCRIPTION
				"OLT Mac leared entry age limit, the value unit is '1s'. Set
				this value to 0 will disable mac age feature"
			::= { oltBridgeConfigEntry 1 }


--      1.3.6.1.4.1.34592.1.3.3.5.1.2
-- 1.3.6.1.4.1.34592.1.3.3.5.1.2
-- 1.3.6.1.4.1.34592.1.3.3.5.1.2
-- 1.3.6.1.4.1.34592.1.3.3.5.1.2
		-- 1.3.6.1.4.1.34592.1.3.3.5.1.2
		downStreamResetAgeTimer OBJECT-TYPE
			SYNTAX OperSwitch
			MAX-ACCESS read-write
			STATUS current
			DESCRIPTION
				"Generally, only when olt receive learned mac from upstream (from PON port)
				will reset the age timer. This object give us an option to let olt reset
				age timer when received learned mac from downstream (from OLT's SNI port)."
			::= { oltBridgeConfigEntry 2 }


--      1.3.6.1.4.1.34592.1.3.3.5.1.3
-- 1.3.6.1.4.1.34592.1.3.3.5.1.3
-- 1.3.6.1.4.1.34592.1.3.3.5.1.3
-- 1.3.6.1.4.1.34592.1.3.3.5.1.3
		-- 1.3.6.1.4.1.34592.1.3.3.5.1.3
		bridgedVlanNumber OBJECT-TYPE
			SYNTAX Integer32 (0..64)
			MAX-ACCESS read-only
			STATUS current
			DESCRIPTION
				"briged vlan number"
			::= { oltBridgeConfigEntry 3 }


--      1.3.6.1.4.1.34592.1.3.3.5.1.4
-- 1.3.6.1.4.1.34592.1.3.3.5.1.4
-- 1.3.6.1.4.1.34592.1.3.3.5.1.4
-- 1.3.6.1.4.1.34592.1.3.3.5.1.4
		-- 1.3.6.1.4.1.34592.1.3.3.5.1.4
		macOverWrite OBJECT-TYPE
			SYNTAX OperSwitch
			MAX-ACCESS read-write
			STATUS current
			DESCRIPTION
				"when enable, the new coming MAC will overwrite the oldest learned
				MAC when the per-link learning buf is full; when disable, the frame
				with new mac will be dropped when the learning buf is full."
			::= { oltBridgeConfigEntry 4 }


--      1.3.6.1.4.1.34592.1.3.3.5.1.5
-- 1.3.6.1.4.1.34592.1.3.3.5.1.5
-- 1.3.6.1.4.1.34592.1.3.3.5.1.5
-- 1.3.6.1.4.1.34592.1.3.3.5.1.5
		-- 1.3.6.1.4.1.34592.1.3.3.5.1.5
		discardUnknownMac OBJECT-TYPE
			SYNTAX OperSwitch
			MAX-ACCESS read-write
			STATUS current
			DESCRIPTION
				"Discard unknown MAC, set to enable will cause the OLT to drop downstream
				frames with unknown (not learned) DAs"
			::= { oltBridgeConfigEntry 5 }


--      1.3.6.1.4.1.34592.1.3.3.5.1.6
-- 1.3.6.1.4.1.34592.1.3.3.5.1.6
-- 1.3.6.1.4.1.34592.1.3.3.5.1.6
-- 1.3.6.1.4.1.34592.1.3.3.5.1.6
		-- 1.3.6.1.4.1.34592.1.3.3.5.1.6
		forwardTagOnSimpleBridge OBJECT-TYPE
			SYNTAX OperSwitch
			MAX-ACCESS read-write
			STATUS current
			DESCRIPTION
				"Set the object to 'allow' will permit the OLT to forward tagged frames
				on simple bridge links. Set to 'disallow' will not permit the OLT
				to forward tagged frames on simple bridges."
			::= { oltBridgeConfigEntry 6 }


--      1.3.6.1.4.1.34592.1.3.3.6
-- 1.3.6.1.4.1.34592.1.3.3.6
-- 1.3.6.1.4.1.34592.1.3.3.6
-- 1.3.6.1.4.1.34592.1.3.3.6
		-- 1.3.6.1.4.1.34592.1.3.3.6
		dba OBJECT IDENTIFIER ::= { fdOlt 6 }


--      1.3.6.1.4.1.34592.1.3.3.6.1
-- 1.3.6.1.4.1.34592.1.3.3.6.1
-- 1.3.6.1.4.1.34592.1.3.3.6.1
-- 1.3.6.1.4.1.34592.1.3.3.6.1
		-- 1.3.6.1.4.1.34592.1.3.3.6.1
		linkLevelSizeTable OBJECT-TYPE
			SYNTAX SEQUENCE OF LinkLevelSizeEntry
			MAX-ACCESS not-accessible
			STATUS current
			DESCRIPTION
				"This table contains the configurations that the logical
				links which can register on each priority level"
			::= { dba 1 }


--      1.3.6.1.4.1.34592.1.3.3.6.1.1
-- 1.3.6.1.4.1.34592.1.3.3.6.1.1
-- 1.3.6.1.4.1.34592.1.3.3.6.1.1
-- 1.3.6.1.4.1.34592.1.3.3.6.1.1
		-- 1.3.6.1.4.1.34592.1.3.3.6.1.1
		linkLevelSizeEntry OBJECT-TYPE
			SYNTAX LinkLevelSizeEntry
			MAX-ACCESS not-accessible
			STATUS current
			DESCRIPTION
				"Each entry indicate an onu"
			INDEX { ponCardSlotId, oltId }
			::= { linkLevelSizeTable 1 }


		LinkLevelSizeEntry ::=
			SEQUENCE {
				level0Links
					Integer32,
				level1Links
					Integer32,
				level2Links
					Integer32,
				nonDbaLinks
					Integer32
			 }

--      1.3.6.1.4.1.34592.1.3.3.6.1.1.1
-- 1.3.6.1.4.1.34592.1.3.3.6.1.1.1
-- 1.3.6.1.4.1.34592.1.3.3.6.1.1.1
-- 1.3.6.1.4.1.34592.1.3.3.6.1.1.1
		-- 1.3.6.1.4.1.34592.1.3.3.6.1.1.1
		level0Links OBJECT-TYPE
			SYNTAX Integer32 (0..256)
			MAX-ACCESS read-write
			STATUS current
			DESCRIPTION
				"Priority level 0 link numbers that the olt will allow to register.
				Priority level 0 is 'min bw=max bw and the delay is sensitive'

				this object can only be changed when the olt is diable"
			::= { linkLevelSizeEntry 1 }


--      1.3.6.1.4.1.34592.1.3.3.6.1.1.2
-- 1.3.6.1.4.1.34592.1.3.3.6.1.1.2
-- 1.3.6.1.4.1.34592.1.3.3.6.1.1.2
-- 1.3.6.1.4.1.34592.1.3.3.6.1.1.2
		-- 1.3.6.1.4.1.34592.1.3.3.6.1.1.2
		level1Links OBJECT-TYPE
			SYNTAX Integer32 (0..256)
			MAX-ACCESS read-write
			STATUS current
			DESCRIPTION
				"Priority level 1 link numbers that the olt will allow to register.
				Priority level 1 is 'min bw!=0'


				this object can only be changed when the olt is diable"
			::= { linkLevelSizeEntry 2 }


--      1.3.6.1.4.1.34592.1.3.3.6.1.1.3
-- 1.3.6.1.4.1.34592.1.3.3.6.1.1.3
-- 1.3.6.1.4.1.34592.1.3.3.6.1.1.3
-- 1.3.6.1.4.1.34592.1.3.3.6.1.1.3
		-- 1.3.6.1.4.1.34592.1.3.3.6.1.1.3
		level2Links OBJECT-TYPE
			SYNTAX Integer32 (1..256)
			MAX-ACCESS read-write
			STATUS current
			DESCRIPTION
				"Priority level 2 link numbers that the olt will allow to register.
				Priority level 2 is 'min bw=0'


				this object can only be changed when the olt is diable"
			::= { linkLevelSizeEntry 3 }


--      1.3.6.1.4.1.34592.1.3.3.6.1.1.4
-- 1.3.6.1.4.1.34592.1.3.3.6.1.1.4
-- 1.3.6.1.4.1.34592.1.3.3.6.1.1.4
-- 1.3.6.1.4.1.34592.1.3.3.6.1.1.4
		-- 1.3.6.1.4.1.34592.1.3.3.6.1.1.4
		nonDbaLinks OBJECT-TYPE
			SYNTAX Integer32 (1..63)
			MAX-ACCESS read-write
			STATUS current
			DESCRIPTION
				"TDM level link numbers that the olt will allow to register.


				this object can only be changed when the olt is diable
				"
			::= { linkLevelSizeEntry 4 }


--      1.3.6.1.4.1.34592.1.3.3.6.2
-- 1.3.6.1.4.1.34592.1.3.3.6.2
-- 1.3.6.1.4.1.34592.1.3.3.6.2
-- 1.3.6.1.4.1.34592.1.3.3.6.2
		-- 1.3.6.1.4.1.34592.1.3.3.6.2
		dbaDropDownWeightTable OBJECT-TYPE
			SYNTAX SEQUENCE OF DbaDropDownWeightEntry
			MAX-ACCESS not-accessible
			STATUS current
			DESCRIPTION
				"DBA drop down weight configuration table"
			::= { dba 2 }


--      1.3.6.1.4.1.34592.1.3.3.6.2.1
-- 1.3.6.1.4.1.34592.1.3.3.6.2.1
-- 1.3.6.1.4.1.34592.1.3.3.6.2.1
-- 1.3.6.1.4.1.34592.1.3.3.6.2.1
		-- 1.3.6.1.4.1.34592.1.3.3.6.2.1
		dbaDropDownWeightEntry OBJECT-TYPE
			SYNTAX DbaDropDownWeightEntry
			MAX-ACCESS not-accessible
			STATUS current
			DESCRIPTION
				"DBA drop down weight configuration entry"
			INDEX { ponCardSlotId, oltId }
			::= { dbaDropDownWeightTable 1 }


		DbaDropDownWeightEntry ::=
			SEQUENCE {
				l0DropDownWeight
					Integer32,
				l1DropDownWeight
					Integer32,
				l2DropDownWeight
					Integer32
			 }

--      1.3.6.1.4.1.34592.1.3.3.6.2.1.1
-- 1.3.6.1.4.1.34592.1.3.3.6.2.1.1
-- 1.3.6.1.4.1.34592.1.3.3.6.2.1.1
-- 1.3.6.1.4.1.34592.1.3.3.6.2.1.1
		-- 1.3.6.1.4.1.34592.1.3.3.6.2.1.1
		l0DropDownWeight OBJECT-TYPE
			SYNTAX Integer32 (0..16383)
			MAX-ACCESS read-write
			STATUS current
			DESCRIPTION
				"level 0 drop down weight"
			::= { dbaDropDownWeightEntry 1 }


--      1.3.6.1.4.1.34592.1.3.3.6.2.1.2
-- 1.3.6.1.4.1.34592.1.3.3.6.2.1.2
-- 1.3.6.1.4.1.34592.1.3.3.6.2.1.2
-- 1.3.6.1.4.1.34592.1.3.3.6.2.1.2
		-- 1.3.6.1.4.1.34592.1.3.3.6.2.1.2
		l1DropDownWeight OBJECT-TYPE
			SYNTAX Integer32 (0..16383)
			MAX-ACCESS read-write
			STATUS current
			DESCRIPTION
				"level 1 drop down weight"
			::= { dbaDropDownWeightEntry 2 }


--      1.3.6.1.4.1.34592.1.3.3.6.2.1.3
-- 1.3.6.1.4.1.34592.1.3.3.6.2.1.3
-- 1.3.6.1.4.1.34592.1.3.3.6.2.1.3
-- 1.3.6.1.4.1.34592.1.3.3.6.2.1.3
		-- 1.3.6.1.4.1.34592.1.3.3.6.2.1.3
		l2DropDownWeight OBJECT-TYPE
			SYNTAX Integer32 (0..16383)
			MAX-ACCESS read-write
			STATUS current
			DESCRIPTION
				"level 2 drop down weight"
			::= { dbaDropDownWeightEntry 3 }


--      1.3.6.1.4.1.34592.1.3.3.6.3
-- 1.3.6.1.4.1.34592.1.3.3.6.3
-- 1.3.6.1.4.1.34592.1.3.3.6.3
-- 1.3.6.1.4.1.34592.1.3.3.6.3
		-- 1.3.6.1.4.1.34592.1.3.3.6.3
		dbaPollRateTable OBJECT-TYPE
			SYNTAX SEQUENCE OF DbaPollRateEntry
			MAX-ACCESS not-accessible
			STATUS current
			DESCRIPTION
				"DBA polling rate table"
			::= { dba 3 }


--      1.3.6.1.4.1.34592.1.3.3.6.3.1
-- 1.3.6.1.4.1.34592.1.3.3.6.3.1
-- 1.3.6.1.4.1.34592.1.3.3.6.3.1
-- 1.3.6.1.4.1.34592.1.3.3.6.3.1
		-- 1.3.6.1.4.1.34592.1.3.3.6.3.1
		dbaPollRateEntry OBJECT-TYPE
			SYNTAX DbaPollRateEntry
			MAX-ACCESS not-accessible
			STATUS current
			DESCRIPTION
				"DBA polling rate entry"
			INDEX { ponCardSlotId, oltId }
			::= { dbaPollRateTable 1 }


		DbaPollRateEntry ::=
			SEQUENCE {
				l0PollingRate
					Integer32,
				l1PollingRate
					Integer32,
				l2PollingRate
					Integer32
			 }

--      1.3.6.1.4.1.34592.1.3.3.6.3.1.1
-- 1.3.6.1.4.1.34592.1.3.3.6.3.1.1
-- 1.3.6.1.4.1.34592.1.3.3.6.3.1.1
-- 1.3.6.1.4.1.34592.1.3.3.6.3.1.1
		-- 1.3.6.1.4.1.34592.1.3.3.6.3.1.1
		l0PollingRate OBJECT-TYPE
			SYNTAX Integer32 (0..65535)
			MAX-ACCESS read-write
			STATUS current
			DESCRIPTION
				"level 0 links polling rate"
			::= { dbaPollRateEntry 1 }


--      1.3.6.1.4.1.34592.1.3.3.6.3.1.2
-- 1.3.6.1.4.1.34592.1.3.3.6.3.1.2
-- 1.3.6.1.4.1.34592.1.3.3.6.3.1.2
-- 1.3.6.1.4.1.34592.1.3.3.6.3.1.2
		-- 1.3.6.1.4.1.34592.1.3.3.6.3.1.2
		l1PollingRate OBJECT-TYPE
			SYNTAX Integer32 (0..65535)
			MAX-ACCESS read-write
			STATUS current
			DESCRIPTION
				"level 1 links polling rate"
			::= { dbaPollRateEntry 2 }


--      1.3.6.1.4.1.34592.1.3.3.6.3.1.3
-- 1.3.6.1.4.1.34592.1.3.3.6.3.1.3
-- 1.3.6.1.4.1.34592.1.3.3.6.3.1.3
-- 1.3.6.1.4.1.34592.1.3.3.6.3.1.3
		-- 1.3.6.1.4.1.34592.1.3.3.6.3.1.3
		l2PollingRate OBJECT-TYPE
			SYNTAX Integer32 (0..65535)
			MAX-ACCESS read-write
			STATUS current
			DESCRIPTION
				"level 2 links polling rate"
			::= { dbaPollRateEntry 3 }


--      1.3.6.1.4.1.34592.1.3.3.7
-- 1.3.6.1.4.1.34592.1.3.3.7
-- 1.3.6.1.4.1.34592.1.3.3.7
-- 1.3.6.1.4.1.34592.1.3.3.7
		-- 1.3.6.1.4.1.34592.1.3.3.7
		aggreBandWidthTable OBJECT-TYPE
			SYNTAX SEQUENCE OF AggreBandWidthEntry
			MAX-ACCESS not-accessible
			STATUS current
			DESCRIPTION
				"Aggregate bandwidth configuration table"
			::= { fdOlt 7 }


--      1.3.6.1.4.1.34592.1.3.3.7.1
-- 1.3.6.1.4.1.34592.1.3.3.7.1
-- 1.3.6.1.4.1.34592.1.3.3.7.1
-- 1.3.6.1.4.1.34592.1.3.3.7.1
		-- 1.3.6.1.4.1.34592.1.3.3.7.1
		aggreBandWidthEntry OBJECT-TYPE
			SYNTAX AggreBandWidthEntry
			MAX-ACCESS not-accessible
			STATUS current
			DESCRIPTION
				"Aggregate bandwidth configuration entry"
			INDEX { ponCardSlotId, oltId, directionId }
			::= { aggreBandWidthTable 1 }


		AggreBandWidthEntry ::=
			SEQUENCE {
				directionId
					DataDirection,
				aggreBandWidth
					Integer32,
				aggreMaxBurstSize
					Integer32
			 }

--      1.3.6.1.4.1.34592.1.3.3.7.1.1
-- 1.3.6.1.4.1.34592.1.3.3.7.1.1
-- 1.3.6.1.4.1.34592.1.3.3.7.1.1
-- 1.3.6.1.4.1.34592.1.3.3.7.1.1
		-- 1.3.6.1.4.1.34592.1.3.3.7.1.1
		directionId OBJECT-TYPE
			SYNTAX DataDirection
			MAX-ACCESS not-accessible
			STATUS current
			DESCRIPTION
				"Administrativly assigned identification for the purpose
				to distinguish different data direction"
			::= { aggreBandWidthEntry 1 }


--      1.3.6.1.4.1.34592.1.3.3.7.1.2
-- 1.3.6.1.4.1.34592.1.3.3.7.1.2
-- 1.3.6.1.4.1.34592.1.3.3.7.1.2
-- 1.3.6.1.4.1.34592.1.3.3.7.1.2
		-- 1.3.6.1.4.1.34592.1.3.3.7.1.2
		aggreBandWidth OBJECT-TYPE
			SYNTAX Integer32 (0..1000000)
			MAX-ACCESS read-write
			STATUS current
			DESCRIPTION
				"Aggregate bandwidth"
			::= { aggreBandWidthEntry 2 }


--      1.3.6.1.4.1.34592.1.3.3.7.1.3
-- 1.3.6.1.4.1.34592.1.3.3.7.1.3
-- 1.3.6.1.4.1.34592.1.3.3.7.1.3
-- 1.3.6.1.4.1.34592.1.3.3.7.1.3
		-- 1.3.6.1.4.1.34592.1.3.3.7.1.3
		aggreMaxBurstSize OBJECT-TYPE
			SYNTAX Integer32 (0..256)
			MAX-ACCESS read-write
			STATUS current
			DESCRIPTION
				"Aggregate max burst size"
			::= { aggreBandWidthEntry 3 }


--      1.3.6.1.4.1.34592.1.3.3.8
-- 1.3.6.1.4.1.34592.1.3.3.8
-- 1.3.6.1.4.1.34592.1.3.3.8
-- 1.3.6.1.4.1.34592.1.3.3.8
		-- 1.3.6.1.4.1.34592.1.3.3.8
		oltAclRuleTable OBJECT-TYPE
			SYNTAX SEQUENCE OF OltAclRuleEntry
			MAX-ACCESS not-accessible
			STATUS current
			DESCRIPTION
				"OLT acl rule configuration table"
			::= { fdOlt 8 }


--      1.3.6.1.4.1.34592.1.3.3.8.1
-- 1.3.6.1.4.1.34592.1.3.3.8.1
-- 1.3.6.1.4.1.34592.1.3.3.8.1
-- 1.3.6.1.4.1.34592.1.3.3.8.1
		-- 1.3.6.1.4.1.34592.1.3.3.8.1
		oltAclRuleEntry OBJECT-TYPE
			SYNTAX OltAclRuleEntry
			MAX-ACCESS not-accessible
			STATUS current
			DESCRIPTION
				"OLT configuration rule entry"
			INDEX { ponCardSlotId, oltId, oltPortId }
			::= { oltAclRuleTable 1 }


		OltAclRuleEntry ::=
			SEQUENCE {
				oltPortId
					INTEGER,
				oltAclRuleData
					OCTET STRING
			 }

--      1.3.6.1.4.1.34592.1.3.3.8.1.1
-- 1.3.6.1.4.1.34592.1.3.3.8.1.1
-- 1.3.6.1.4.1.34592.1.3.3.8.1.1
-- 1.3.6.1.4.1.34592.1.3.3.8.1.1
		-- 1.3.6.1.4.1.34592.1.3.3.8.1.1
		oltPortId OBJECT-TYPE
			SYNTAX INTEGER
				{
				oltPonPort(1),
				oltSniPort(2)
				}
			MAX-ACCESS not-accessible
			STATUS current
			DESCRIPTION
				"Administrativly assigned port ID, used as entry index"
			::= { oltAclRuleEntry 1 }


--      1.3.6.1.4.1.34592.1.3.3.8.1.2
-- 1.3.6.1.4.1.34592.1.3.3.8.1.2
-- 1.3.6.1.4.1.34592.1.3.3.8.1.2
-- 1.3.6.1.4.1.34592.1.3.3.8.1.2
		-- 1.3.6.1.4.1.34592.1.3.3.8.1.2
		oltAclRuleData OBJECT-TYPE
			SYNTAX OCTET STRING
			MAX-ACCESS read-write
			STATUS current
			DESCRIPTION
				" Description:
				This variable is used to contain the OLT ACL data. Data format:
				GET:
				     2            2          1         1       1         1
				------------------------------------------------------------------
				|data length|rule numbers|direction|priority|action|clause numbers|
				-------------------------------------------------------------------
				                         |<------repeat rule number times----------
				   1     6       1
				--------------------------------
				|  field  |  value  | operator |
				--------------------------------
				|<-repeat clause number times->|
				------------------------------>|

				SET/DELETE:
				    2            1            1       1         1
				---------------------------------------------------------
				|data length|command type|priority|reserved|clause numbers|
				---------------------------------------------------------
				     1        6         1
				--------------------------------
				|  field  |  value  | operator |
				--------------------------------
				|<-repeat clause number times->|

				para comment:
				command type: 1->set, 2->delete
				"
			::= { oltAclRuleEntry 2 }


--      1.3.6.1.4.1.34592.1.3.3.9
-- 1.3.6.1.4.1.34592.1.3.3.9
-- 1.3.6.1.4.1.34592.1.3.3.9
-- 1.3.6.1.4.1.34592.1.3.3.9
		-- 1.3.6.1.4.1.34592.1.3.3.9
		priCopyMapTable OBJECT-TYPE
			SYNTAX SEQUENCE OF PriCopyMapEntry
			MAX-ACCESS not-accessible
			STATUS current
			DESCRIPTION
				"Priority copy value map configuration table"
			::= { fdOlt 9 }


--      1.3.6.1.4.1.34592.1.3.3.9.1
-- 1.3.6.1.4.1.34592.1.3.3.9.1
-- 1.3.6.1.4.1.34592.1.3.3.9.1
-- 1.3.6.1.4.1.34592.1.3.3.9.1
		-- 1.3.6.1.4.1.34592.1.3.3.9.1
		priCopyMapEntry OBJECT-TYPE
			SYNTAX PriCopyMapEntry
			MAX-ACCESS not-accessible
			STATUS current
			DESCRIPTION
				"Priority copy value map configuration entry"
			INDEX { ponCardSlotId, oltId }
			::= { priCopyMapTable 1 }


		PriCopyMapEntry ::=
			SEQUENCE {
				priCopyMapData
					OCTET STRING
			 }

--      1.3.6.1.4.1.34592.1.3.3.9.1.1
-- 1.3.6.1.4.1.34592.1.3.3.9.1.1
-- 1.3.6.1.4.1.34592.1.3.3.9.1.1
-- 1.3.6.1.4.1.34592.1.3.3.9.1.1
		-- 1.3.6.1.4.1.34592.1.3.3.9.1.1
		priCopyMapData OBJECT-TYPE
			SYNTAX OCTET STRING
			MAX-ACCESS read-write
			STATUS current
			DESCRIPTION
				"                    1                   1         1                  ..                1              ..
				-----------------------------------------------------------------------------------------
				|A/B Precedence|Default COS| N |               COS         | M |          COS               |
				-----------------------------------------------------------------------------------------
				                                                     |<-repeat N times->|     |<-repeat M times->|"
			::= { priCopyMapEntry 1 }


--      1.3.6.1.4.1.34592.1.3.3.10
-- 1.3.6.1.4.1.34592.1.3.3.10
-- 1.3.6.1.4.1.34592.1.3.3.10
-- 1.3.6.1.4.1.34592.1.3.3.10
		-- 1.3.6.1.4.1.34592.1.3.3.10
		oltIgmpProxy OBJECT IDENTIFIER ::= { fdOlt 10 }


--      1.3.6.1.4.1.34592.1.3.3.10.1
-- 1.3.6.1.4.1.34592.1.3.3.10.1
-- 1.3.6.1.4.1.34592.1.3.3.10.1
-- 1.3.6.1.4.1.34592.1.3.3.10.1
		-- 1.3.6.1.4.1.34592.1.3.3.10.1
		igmpProxyConfigTable OBJECT-TYPE
			SYNTAX SEQUENCE OF IgmpProxyConfigEntry
			MAX-ACCESS not-accessible
			STATUS current
			DESCRIPTION
				" "
			::= { oltIgmpProxy 1 }


--      1.3.6.1.4.1.34592.1.3.3.10.1.1
-- 1.3.6.1.4.1.34592.1.3.3.10.1.1
-- 1.3.6.1.4.1.34592.1.3.3.10.1.1
-- 1.3.6.1.4.1.34592.1.3.3.10.1.1
		-- 1.3.6.1.4.1.34592.1.3.3.10.1.1
		igmpProxyConfigEntry OBJECT-TYPE
			SYNTAX IgmpProxyConfigEntry
			MAX-ACCESS not-accessible
			STATUS current
			DESCRIPTION
				" "
			REFERENCE
				"add all other needed igmp proxy parameters in this table"
			INDEX { ponCardSlotId, oltId }
			::= { igmpProxyConfigTable 1 }


		IgmpProxyConfigEntry ::=
			SEQUENCE {
				maxIgmpGroups
					Integer32,
				robustCount
					Integer32,
				queryInterval
					Integer32,
				queryRspTimeout
					Integer32,
				queryMaxResTime
					Integer32,
				startQueryCount
					Integer32,
				startupQueryInterval
					Integer32,
				lastMemberQueryCount
					Integer32,
				lastMemberQueryInterval
					Integer32,
				lastMemberQueryResTime
					Integer32,
				upstreamRetransCount
					Integer32,
				upstreamRetransInterval
					Integer32,
				igmpQueues
					Integer32,
				igmpSlaMinGuaranteedBW
					Integer32,
				igmpSlaMaxAllowedBW
					Integer32,
				igmpSlaDelaySensitive
					INTEGER,
				igmpSlaMaxBurstSize
					Integer32,
				igmpProxyOper
					INTEGER
			 }

--      1.3.6.1.4.1.34592.1.3.3.10.1.1.1
-- 1.3.6.1.4.1.34592.1.3.3.10.1.1.1
-- 1.3.6.1.4.1.34592.1.3.3.10.1.1.1
-- 1.3.6.1.4.1.34592.1.3.3.10.1.1.1
		-- 1.3.6.1.4.1.34592.1.3.3.10.1.1.1
		maxIgmpGroups OBJECT-TYPE
			SYNTAX Integer32 (0..4096)
			MAX-ACCESS read-write
			STATUS current
			DESCRIPTION
				" "
			::= { igmpProxyConfigEntry 1 }


--      1.3.6.1.4.1.34592.1.3.3.10.1.1.2
-- 1.3.6.1.4.1.34592.1.3.3.10.1.1.2
-- 1.3.6.1.4.1.34592.1.3.3.10.1.1.2
-- 1.3.6.1.4.1.34592.1.3.3.10.1.1.2
		-- 1.3.6.1.4.1.34592.1.3.3.10.1.1.2
		robustCount OBJECT-TYPE
			SYNTAX Integer32 (1..16)
			MAX-ACCESS read-write
			STATUS current
			DESCRIPTION
				" "
			::= { igmpProxyConfigEntry 2 }


--      1.3.6.1.4.1.34592.1.3.3.10.1.1.3
-- 1.3.6.1.4.1.34592.1.3.3.10.1.1.3
-- 1.3.6.1.4.1.34592.1.3.3.10.1.1.3
-- 1.3.6.1.4.1.34592.1.3.3.10.1.1.3
		-- 1.3.6.1.4.1.34592.1.3.3.10.1.1.3
		queryInterval OBJECT-TYPE
			SYNTAX Integer32 (12..65535)
			MAX-ACCESS read-write
			STATUS current
			DESCRIPTION
				" "
			::= { igmpProxyConfigEntry 3 }


--      1.3.6.1.4.1.34592.1.3.3.10.1.1.4
-- 1.3.6.1.4.1.34592.1.3.3.10.1.1.4
-- 1.3.6.1.4.1.34592.1.3.3.10.1.1.4
-- 1.3.6.1.4.1.34592.1.3.3.10.1.1.4
		-- 1.3.6.1.4.1.34592.1.3.3.10.1.1.4
		queryRspTimeout OBJECT-TYPE
			SYNTAX Integer32 (11..65534)
			MAX-ACCESS read-write
			STATUS current
			DESCRIPTION
				" "
			::= { igmpProxyConfigEntry 4 }


--      1.3.6.1.4.1.34592.1.3.3.10.1.1.5
-- 1.3.6.1.4.1.34592.1.3.3.10.1.1.5
-- 1.3.6.1.4.1.34592.1.3.3.10.1.1.5
-- 1.3.6.1.4.1.34592.1.3.3.10.1.1.5
		-- 1.3.6.1.4.1.34592.1.3.3.10.1.1.5
		queryMaxResTime OBJECT-TYPE
			SYNTAX Integer32 (1..255)
			MAX-ACCESS read-write
			STATUS current
			DESCRIPTION
				" "
			::= { igmpProxyConfigEntry 5 }


--      1.3.6.1.4.1.34592.1.3.3.10.1.1.6
-- 1.3.6.1.4.1.34592.1.3.3.10.1.1.6
-- 1.3.6.1.4.1.34592.1.3.3.10.1.1.6
-- 1.3.6.1.4.1.34592.1.3.3.10.1.1.6
		-- 1.3.6.1.4.1.34592.1.3.3.10.1.1.6
		startQueryCount OBJECT-TYPE
			SYNTAX Integer32 (0..16)
			MAX-ACCESS read-write
			STATUS current
			DESCRIPTION
				" "
			::= { igmpProxyConfigEntry 6 }


--      1.3.6.1.4.1.34592.1.3.3.10.1.1.7
-- 1.3.6.1.4.1.34592.1.3.3.10.1.1.7
-- 1.3.6.1.4.1.34592.1.3.3.10.1.1.7
-- 1.3.6.1.4.1.34592.1.3.3.10.1.1.7
		-- 1.3.6.1.4.1.34592.1.3.3.10.1.1.7
		startupQueryInterval OBJECT-TYPE
			SYNTAX Integer32 (12..65535)
			MAX-ACCESS read-write
			STATUS current
			DESCRIPTION
				"startup query intrval"
			::= { igmpProxyConfigEntry 7 }


--      1.3.6.1.4.1.34592.1.3.3.10.1.1.8
-- 1.3.6.1.4.1.34592.1.3.3.10.1.1.8
-- 1.3.6.1.4.1.34592.1.3.3.10.1.1.8
-- 1.3.6.1.4.1.34592.1.3.3.10.1.1.8
		-- 1.3.6.1.4.1.34592.1.3.3.10.1.1.8
		lastMemberQueryCount OBJECT-TYPE
			SYNTAX Integer32 (0..16)
			MAX-ACCESS read-write
			STATUS current
			DESCRIPTION
				"last  Member  Query  Count,range 0--16"
			::= { igmpProxyConfigEntry 8 }


--      1.3.6.1.4.1.34592.1.3.3.10.1.1.9
-- 1.3.6.1.4.1.34592.1.3.3.10.1.1.9
-- 1.3.6.1.4.1.34592.1.3.3.10.1.1.9
-- 1.3.6.1.4.1.34592.1.3.3.10.1.1.9
		-- 1.3.6.1.4.1.34592.1.3.3.10.1.1.9
		lastMemberQueryInterval OBJECT-TYPE
			SYNTAX Integer32 (11..65535)
			MAX-ACCESS read-write
			STATUS current
			DESCRIPTION
				"last  Member  Query  Interval"
			::= { igmpProxyConfigEntry 9 }


--      1.3.6.1.4.1.34592.1.3.3.10.1.1.10
-- 1.3.6.1.4.1.34592.1.3.3.10.1.1.10
-- 1.3.6.1.4.1.34592.1.3.3.10.1.1.10
-- 1.3.6.1.4.1.34592.1.3.3.10.1.1.10
		-- 1.3.6.1.4.1.34592.1.3.3.10.1.1.10
		lastMemberQueryResTime OBJECT-TYPE
			SYNTAX Integer32 (1..255)
			MAX-ACCESS read-write
			STATUS current
			DESCRIPTION
				"last  Membe  rQuery Response Time"
			::= { igmpProxyConfigEntry 10 }


--      1.3.6.1.4.1.34592.1.3.3.10.1.1.11
-- 1.3.6.1.4.1.34592.1.3.3.10.1.1.11
-- 1.3.6.1.4.1.34592.1.3.3.10.1.1.11
-- 1.3.6.1.4.1.34592.1.3.3.10.1.1.11
		-- 1.3.6.1.4.1.34592.1.3.3.10.1.1.11
		upstreamRetransCount OBJECT-TYPE
			SYNTAX Integer32 (0..3)
			MAX-ACCESS read-write
			STATUS current
			DESCRIPTION
				"upstream Retransmit Count"
			::= { igmpProxyConfigEntry 11 }


--      1.3.6.1.4.1.34592.1.3.3.10.1.1.12
-- 1.3.6.1.4.1.34592.1.3.3.10.1.1.12
-- 1.3.6.1.4.1.34592.1.3.3.10.1.1.12
-- 1.3.6.1.4.1.34592.1.3.3.10.1.1.12
		-- 1.3.6.1.4.1.34592.1.3.3.10.1.1.12
		upstreamRetransInterval OBJECT-TYPE
			SYNTAX Integer32 (1..65535)
			MAX-ACCESS read-write
			STATUS current
			DESCRIPTION
				"Upstream  Retransmit Interval,range 1--65535"
			::= { igmpProxyConfigEntry 12 }


--      1.3.6.1.4.1.34592.1.3.3.10.1.1.13
-- 1.3.6.1.4.1.34592.1.3.3.10.1.1.13
-- 1.3.6.1.4.1.34592.1.3.3.10.1.1.13
-- 1.3.6.1.4.1.34592.1.3.3.10.1.1.13
		-- 1.3.6.1.4.1.34592.1.3.3.10.1.1.13
		igmpQueues OBJECT-TYPE
			SYNTAX Integer32 (1..10)
			MAX-ACCESS read-write
			STATUS current
			DESCRIPTION
				" "
			::= { igmpProxyConfigEntry 13 }


--      1.3.6.1.4.1.34592.1.3.3.10.1.1.14
-- 1.3.6.1.4.1.34592.1.3.3.10.1.1.14
-- 1.3.6.1.4.1.34592.1.3.3.10.1.1.14
-- 1.3.6.1.4.1.34592.1.3.3.10.1.1.14
		-- 1.3.6.1.4.1.34592.1.3.3.10.1.1.14
		igmpSlaMinGuaranteedBW OBJECT-TYPE
			SYNTAX Integer32 (256..1000000)
			MAX-ACCESS read-write
			STATUS current
			DESCRIPTION
				" "
			::= { igmpProxyConfigEntry 14 }


--      1.3.6.1.4.1.34592.1.3.3.10.1.1.15
-- 1.3.6.1.4.1.34592.1.3.3.10.1.1.15
-- 1.3.6.1.4.1.34592.1.3.3.10.1.1.15
-- 1.3.6.1.4.1.34592.1.3.3.10.1.1.15
		-- 1.3.6.1.4.1.34592.1.3.3.10.1.1.15
		igmpSlaMaxAllowedBW OBJECT-TYPE
			SYNTAX Integer32 (256..1000000)
			MAX-ACCESS read-write
			STATUS current
			DESCRIPTION
				" "
			::= { igmpProxyConfigEntry 15 }


--      1.3.6.1.4.1.34592.1.3.3.10.1.1.16
-- 1.3.6.1.4.1.34592.1.3.3.10.1.1.16
-- 1.3.6.1.4.1.34592.1.3.3.10.1.1.16
-- 1.3.6.1.4.1.34592.1.3.3.10.1.1.16
		-- 1.3.6.1.4.1.34592.1.3.3.10.1.1.16
		igmpSlaDelaySensitive OBJECT-TYPE
			SYNTAX INTEGER
				{
				sensitive(1),
				tolerant(2)
				}
			MAX-ACCESS read-write
			STATUS current
			DESCRIPTION
				" "
			::= { igmpProxyConfigEntry 16 }


--      1.3.6.1.4.1.34592.1.3.3.10.1.1.17
-- 1.3.6.1.4.1.34592.1.3.3.10.1.1.17
-- 1.3.6.1.4.1.34592.1.3.3.10.1.1.17
-- 1.3.6.1.4.1.34592.1.3.3.10.1.1.17
		-- 1.3.6.1.4.1.34592.1.3.3.10.1.1.17
		igmpSlaMaxBurstSize OBJECT-TYPE
			SYNTAX Integer32 (1..256)
			MAX-ACCESS read-write
			STATUS current
			DESCRIPTION
				" "
			::= { igmpProxyConfigEntry 17 }


--      1.3.6.1.4.1.34592.1.3.3.10.1.1.19
-- 1.3.6.1.4.1.34592.1.3.3.10.1.1.19
-- 1.3.6.1.4.1.34592.1.3.3.10.1.1.19
-- 1.3.6.1.4.1.34592.1.3.3.10.1.1.19
		-- 1.3.6.1.4.1.34592.1.3.3.10.1.1.19
		igmpProxyOper OBJECT-TYPE
			SYNTAX INTEGER
				{
				restorePara(2),
				refreshGroups(3)
				}
			MAX-ACCESS read-write
			STATUS current
			DESCRIPTION
				"Restore all the configurable values to factory default"
			::= { igmpProxyConfigEntry 19 }


--      1.3.6.1.4.1.34592.1.3.3.10.2
-- 1.3.6.1.4.1.34592.1.3.3.10.2
-- 1.3.6.1.4.1.34592.1.3.3.10.2
-- 1.3.6.1.4.1.34592.1.3.3.10.2
		-- 1.3.6.1.4.1.34592.1.3.3.10.2
		igmpGroupTable OBJECT-TYPE
			SYNTAX SEQUENCE OF IgmpGroupEntry
			MAX-ACCESS not-accessible
			STATUS current
			DESCRIPTION
				" "
			::= { oltIgmpProxy 2 }


--      1.3.6.1.4.1.34592.1.3.3.10.2.1
-- 1.3.6.1.4.1.34592.1.3.3.10.2.1
-- 1.3.6.1.4.1.34592.1.3.3.10.2.1
-- 1.3.6.1.4.1.34592.1.3.3.10.2.1
		-- 1.3.6.1.4.1.34592.1.3.3.10.2.1
		igmpGroupEntry OBJECT-TYPE
			SYNTAX IgmpGroupEntry
			MAX-ACCESS not-accessible
			STATUS current
			DESCRIPTION
				" "
			INDEX { ponCardSlotId, oltId, igmpGroupIndex }
			::= { igmpGroupTable 1 }


		IgmpGroupEntry ::=
			SEQUENCE {
				igmpGroupIndex
					Integer32,
				igmpGroupVlan
					Integer32,
				igmpGroupIpAddr
					IpAddress
			 }

--      1.3.6.1.4.1.34592.1.3.3.10.2.1.1
-- 1.3.6.1.4.1.34592.1.3.3.10.2.1.1
-- 1.3.6.1.4.1.34592.1.3.3.10.2.1.1
-- 1.3.6.1.4.1.34592.1.3.3.10.2.1.1
		-- 1.3.6.1.4.1.34592.1.3.3.10.2.1.1
		igmpGroupIndex OBJECT-TYPE
			SYNTAX Integer32 (1..4094)
			MAX-ACCESS not-accessible
			STATUS current
			DESCRIPTION
				"Administratorly assigned entry index value"
			::= { igmpGroupEntry 1 }


--      1.3.6.1.4.1.34592.1.3.3.10.2.1.2
-- 1.3.6.1.4.1.34592.1.3.3.10.2.1.2
-- 1.3.6.1.4.1.34592.1.3.3.10.2.1.2
-- 1.3.6.1.4.1.34592.1.3.3.10.2.1.2
		-- 1.3.6.1.4.1.34592.1.3.3.10.2.1.2
		igmpGroupVlan OBJECT-TYPE
			SYNTAX Integer32 (1..4094)
			MAX-ACCESS read-only
			STATUS current
			DESCRIPTION
				" "
			::= { igmpGroupEntry 2 }


--      1.3.6.1.4.1.34592.1.3.3.10.2.1.3
-- 1.3.6.1.4.1.34592.1.3.3.10.2.1.3
-- 1.3.6.1.4.1.34592.1.3.3.10.2.1.3
-- 1.3.6.1.4.1.34592.1.3.3.10.2.1.3
		-- 1.3.6.1.4.1.34592.1.3.3.10.2.1.3
		igmpGroupIpAddr OBJECT-TYPE
			SYNTAX IpAddress
			MAX-ACCESS read-only
			STATUS current
			DESCRIPTION
				" "
			::= { igmpGroupEntry 3 }


--      1.3.6.1.4.1.34592.1.3.3.11
-- 1.3.6.1.4.1.34592.1.3.3.11
-- 1.3.6.1.4.1.34592.1.3.3.11
-- 1.3.6.1.4.1.34592.1.3.3.11
		-- 1.3.6.1.4.1.34592.1.3.3.11
		accessUserIdentifer OBJECT IDENTIFIER ::= { fdOlt 11 }


--      1.3.6.1.4.1.34592.1.3.3.11.1
-- 1.3.6.1.4.1.34592.1.3.3.11.1
-- 1.3.6.1.4.1.34592.1.3.3.11.1
-- 1.3.6.1.4.1.34592.1.3.3.11.1
		-- 1.3.6.1.4.1.34592.1.3.3.11.1
		accessUserIdentiferConfigTable OBJECT-TYPE
			SYNTAX SEQUENCE OF AccessUserIdentiferConfigEntry
			MAX-ACCESS not-accessible
			STATUS current
			DESCRIPTION
				"Description. PPPOE+ feature management objects"
			::= { accessUserIdentifer 1 }


--      1.3.6.1.4.1.34592.1.3.3.11.1.1
-- 1.3.6.1.4.1.34592.1.3.3.11.1.1
-- 1.3.6.1.4.1.34592.1.3.3.11.1.1
-- 1.3.6.1.4.1.34592.1.3.3.11.1.1
		-- 1.3.6.1.4.1.34592.1.3.3.11.1.1
		accessUserIdentiferConfigEntry OBJECT-TYPE
			SYNTAX AccessUserIdentiferConfigEntry
			MAX-ACCESS not-accessible
			STATUS current
			DESCRIPTION
				"Description. The PPPOE+ feature act on each OLT (PON port)"
			INDEX { ponCardSlotId, oltId }
			::= { accessUserIdentiferConfigTable 1 }


		AccessUserIdentiferConfigEntry ::=
			SEQUENCE {
				pppoePlusEnable
					OperSwitch,
				dhcpOption82
					OperSwitch
			 }

--      1.3.6.1.4.1.34592.1.3.3.11.1.1.1
-- 1.3.6.1.4.1.34592.1.3.3.11.1.1.1
-- 1.3.6.1.4.1.34592.1.3.3.11.1.1.1
-- 1.3.6.1.4.1.34592.1.3.3.11.1.1.1
		-- 1.3.6.1.4.1.34592.1.3.3.11.1.1.1
		pppoePlusEnable OBJECT-TYPE
			SYNTAX OperSwitch
			MAX-ACCESS read-write
			STATUS current
			DESCRIPTION
				"Description. Enable/Disable pppoe+ feature, when enabled
				PON card firmware will sniff each pppoe require frames
				sent from user divice and then add cared info (normal info
				will be onu ID,onu port, vlan ID) to the protocol specified
				frame field.

				This feature is usefull when exact user identify is needed.
				Disable OLT is essential before set this feature."
			::= { accessUserIdentiferConfigEntry 1 }


--      1.3.6.1.4.1.34592.1.3.3.11.1.1.2
-- 1.3.6.1.4.1.34592.1.3.3.11.1.1.2
-- 1.3.6.1.4.1.34592.1.3.3.11.1.1.2
-- 1.3.6.1.4.1.34592.1.3.3.11.1.1.2
		-- 1.3.6.1.4.1.34592.1.3.3.11.1.1.2
		dhcpOption82 OBJECT-TYPE
			SYNTAX OperSwitch
			MAX-ACCESS read-write
			STATUS current
			DESCRIPTION
				"Description."
			::= { accessUserIdentiferConfigEntry 2 }


--      1.3.6.1.4.1.34592.1.3.3.12
-- 1.3.6.1.4.1.34592.1.3.3.12
-- 1.3.6.1.4.1.34592.1.3.3.12
-- 1.3.6.1.4.1.34592.1.3.3.12
		-- 1.3.6.1.4.1.34592.1.3.3.12
		llid OBJECT IDENTIFIER ::= { fdOlt 12 }


--      1.3.6.1.4.1.34592.1.3.3.12.1
-- 1.3.6.1.4.1.34592.1.3.3.12.1
-- 1.3.6.1.4.1.34592.1.3.3.12.1
-- 1.3.6.1.4.1.34592.1.3.3.12.1
		-- 1.3.6.1.4.1.34592.1.3.3.12.1
		llidConfigTable OBJECT-TYPE
			SYNTAX SEQUENCE OF LlidConfigEntry
			MAX-ACCESS not-accessible
			STATUS current
			DESCRIPTION
				" "
			::= { llid 1 }


--      1.3.6.1.4.1.34592.1.3.3.12.1.1
-- 1.3.6.1.4.1.34592.1.3.3.12.1.1
-- 1.3.6.1.4.1.34592.1.3.3.12.1.1
-- 1.3.6.1.4.1.34592.1.3.3.12.1.1
		-- 1.3.6.1.4.1.34592.1.3.3.12.1.1
		llidConfigEntry OBJECT-TYPE
			SYNTAX LlidConfigEntry
			MAX-ACCESS not-accessible
			STATUS current
			DESCRIPTION
				" "
			INDEX { ponCardSlotId, oltId, linkId }
			::= { llidConfigTable 1 }


		LlidConfigEntry ::=
			SEQUENCE {
				linkId
					Unsigned32,
				llidAssigned
					Unsigned32,
				associatedOnuId
					Unsigned32,
				llidMac
					MacAddress,
				linkOnLineStatus
					DeviceStatus,
				keyChangeTimer
					Integer32,
				llidBridgeType
					INTEGER,
				llidMacEntryLimit
					Integer32,
				crossConnectLinkId
					Unsigned32,
				llidOperation
					INTEGER
			 }

--      1.3.6.1.4.1.34592.1.3.3.12.1.1.1
-- 1.3.6.1.4.1.34592.1.3.3.12.1.1.1
-- 1.3.6.1.4.1.34592.1.3.3.12.1.1.1
-- 1.3.6.1.4.1.34592.1.3.3.12.1.1.1
		-- 1.3.6.1.4.1.34592.1.3.3.12.1.1.1
		linkId OBJECT-TYPE
			SYNTAX Unsigned32 (1..4096)
			MAX-ACCESS not-accessible
			STATUS current
			DESCRIPTION
				"this object is defined to identify 'Logical Links' registered on
				OLT, it is a numbered value begin from 1 to max permit Link numbers.
				it is used within a OLT range.

				this object is different from the followwed 'llidAssigned' object,the
				latter is the LLID value allocated by OLT itself. the 'linkId' is
				allocated by PON card software."
			::= { llidConfigEntry 1 }


--      1.3.6.1.4.1.34592.1.3.3.12.1.1.2
-- 1.3.6.1.4.1.34592.1.3.3.12.1.1.2
-- 1.3.6.1.4.1.34592.1.3.3.12.1.1.2
-- 1.3.6.1.4.1.34592.1.3.3.12.1.1.2
		-- 1.3.6.1.4.1.34592.1.3.3.12.1.1.2
		llidAssigned OBJECT-TYPE
			SYNTAX Unsigned32
			MAX-ACCESS read-only
			STATUS current
			DESCRIPTION
				"LLID value allocated by OLT"
			::= { llidConfigEntry 2 }


--      1.3.6.1.4.1.34592.1.3.3.12.1.1.3
-- 1.3.6.1.4.1.34592.1.3.3.12.1.1.3
-- 1.3.6.1.4.1.34592.1.3.3.12.1.1.3
-- 1.3.6.1.4.1.34592.1.3.3.12.1.1.3
		-- 1.3.6.1.4.1.34592.1.3.3.12.1.1.3
		associatedOnuId OBJECT-TYPE
			SYNTAX Unsigned32
			MAX-ACCESS read-only
			STATUS current
			DESCRIPTION
				"Associated ONU ID. the ONU ID that this Logical Link register from"
			::= { llidConfigEntry 3 }


--      1.3.6.1.4.1.34592.1.3.3.12.1.1.4
-- 1.3.6.1.4.1.34592.1.3.3.12.1.1.4
-- 1.3.6.1.4.1.34592.1.3.3.12.1.1.4
-- 1.3.6.1.4.1.34592.1.3.3.12.1.1.4
		-- 1.3.6.1.4.1.34592.1.3.3.12.1.1.4
		llidMac OBJECT-TYPE
			SYNTAX MacAddress
			MAX-ACCESS read-only
			STATUS current
			DESCRIPTION
				"Logical Link's MAC Address"
			::= { llidConfigEntry 4 }


--      1.3.6.1.4.1.34592.1.3.3.12.1.1.5
-- 1.3.6.1.4.1.34592.1.3.3.12.1.1.5
-- 1.3.6.1.4.1.34592.1.3.3.12.1.1.5
-- 1.3.6.1.4.1.34592.1.3.3.12.1.1.5
		-- 1.3.6.1.4.1.34592.1.3.3.12.1.1.5
		linkOnLineStatus OBJECT-TYPE
			SYNTAX DeviceStatus
			MAX-ACCESS read-only
			STATUS current
			DESCRIPTION
				"Description."
			::= { llidConfigEntry 5 }


--      1.3.6.1.4.1.34592.1.3.3.12.1.1.6
-- 1.3.6.1.4.1.34592.1.3.3.12.1.1.6
-- 1.3.6.1.4.1.34592.1.3.3.12.1.1.6
-- 1.3.6.1.4.1.34592.1.3.3.12.1.1.6
		-- 1.3.6.1.4.1.34592.1.3.3.12.1.1.6
		keyChangeTimer OBJECT-TYPE
			SYNTAX Integer32 (0..65535)
			MAX-ACCESS read-write
			STATUS current
			DESCRIPTION
				"encryption used key change timer, set to non-zero value will enable
				down stream encryption, set to zero will disable this feature.
				the value unit is 'second'."
			::= { llidConfigEntry 6 }


--      1.3.6.1.4.1.34592.1.3.3.12.1.1.7
-- 1.3.6.1.4.1.34592.1.3.3.12.1.1.7
-- 1.3.6.1.4.1.34592.1.3.3.12.1.1.7
-- 1.3.6.1.4.1.34592.1.3.3.12.1.1.7
		-- 1.3.6.1.4.1.34592.1.3.3.12.1.1.7
		llidBridgeType OBJECT-TYPE
			SYNTAX INTEGER
				{
				simpleBridged(1),
				dedicatedSingleVlan(2),
				dedicatedDoubleVlan(3),
				sharedVlan(4),
				transparentVlan(5),
				translatedVlan(6),
				linkCrossConnect(7),
				prioritiedVlan(8),
				priorityCopySingleVlan(9),
				priorityCopyDoubleVlan(10),
				priorityCopySharedVlan(11),
				prioritySharedVlan(12),
				prioritySimpleBridged(13),
				transparentPrioritySharedVlan(14),
				transparentSharedVlanWithBroadcast(15),
				doubleTaggedSharedVlan(16)
				}
			MAX-ACCESS read-write
			STATUS current
			DESCRIPTION
				" "
			::= { llidConfigEntry 7 }


--      1.3.6.1.4.1.34592.1.3.3.12.1.1.8
-- 1.3.6.1.4.1.34592.1.3.3.12.1.1.8
-- 1.3.6.1.4.1.34592.1.3.3.12.1.1.8
-- 1.3.6.1.4.1.34592.1.3.3.12.1.1.8
		-- 1.3.6.1.4.1.34592.1.3.3.12.1.1.8
		llidMacEntryLimit OBJECT-TYPE
			SYNTAX Integer32 (0..4095)
			MAX-ACCESS read-write
			STATUS current
			DESCRIPTION
				" "
			::= { llidConfigEntry 8 }


--      1.3.6.1.4.1.34592.1.3.3.12.1.1.9
-- 1.3.6.1.4.1.34592.1.3.3.12.1.1.9
-- 1.3.6.1.4.1.34592.1.3.3.12.1.1.9
-- 1.3.6.1.4.1.34592.1.3.3.12.1.1.9
		-- 1.3.6.1.4.1.34592.1.3.3.12.1.1.9
		crossConnectLinkId OBJECT-TYPE
			SYNTAX Unsigned32
			MAX-ACCESS read-write
			STATUS current
			DESCRIPTION
				"the link ID of the link which Cross Connect with this link if it is
				in Cross Connect Bridge Mode."
			::= { llidConfigEntry 9 }


--      1.3.6.1.4.1.34592.1.3.3.12.1.1.10
-- 1.3.6.1.4.1.34592.1.3.3.12.1.1.10
-- 1.3.6.1.4.1.34592.1.3.3.12.1.1.10
-- 1.3.6.1.4.1.34592.1.3.3.12.1.1.10
		-- 1.3.6.1.4.1.34592.1.3.3.12.1.1.10
		llidOperation OBJECT-TYPE
			SYNTAX INTEGER
				{
				block(2),
				reRegist(3),
				breakCrossLink(4),
				restoreConfig(5),
				deleteLinkEntry(6)
				}
			MAX-ACCESS read-write
			STATUS current
			DESCRIPTION
				" "
			::= { llidConfigEntry 10 }


--      1.3.6.1.4.1.34592.1.3.3.12.2
-- 1.3.6.1.4.1.34592.1.3.3.12.2
-- 1.3.6.1.4.1.34592.1.3.3.12.2
-- 1.3.6.1.4.1.34592.1.3.3.12.2
		-- 1.3.6.1.4.1.34592.1.3.3.12.2
		llidAdvancedManage OBJECT IDENTIFIER ::= { llid 2 }


--      1.3.6.1.4.1.34592.1.3.3.12.2.1
-- 1.3.6.1.4.1.34592.1.3.3.12.2.1
-- 1.3.6.1.4.1.34592.1.3.3.12.2.1
-- 1.3.6.1.4.1.34592.1.3.3.12.2.1
		-- 1.3.6.1.4.1.34592.1.3.3.12.2.1
		linkOamRateTable OBJECT-TYPE
			SYNTAX SEQUENCE OF LinkOamRateEntry
			MAX-ACCESS not-accessible
			STATUS current
			DESCRIPTION
				"Description. Reserved, generally, the Link OAM rate is used
				for debugging
				"
			::= { llidAdvancedManage 1 }


--      1.3.6.1.4.1.34592.1.3.3.12.2.1.1
-- 1.3.6.1.4.1.34592.1.3.3.12.2.1.1
-- 1.3.6.1.4.1.34592.1.3.3.12.2.1.1
-- 1.3.6.1.4.1.34592.1.3.3.12.2.1.1
		-- 1.3.6.1.4.1.34592.1.3.3.12.2.1.1
		linkOamRateEntry OBJECT-TYPE
			SYNTAX LinkOamRateEntry
			MAX-ACCESS not-accessible
			STATUS current
			DESCRIPTION
				"Description."
			INDEX { ponCardSlotId, oltId, linkId }
			::= { linkOamRateTable 1 }


		LinkOamRateEntry ::=
			SEQUENCE {
				maxLinkOamRate
					Integer32,
				minLinkOamRate
					Integer32
			 }

--      1.3.6.1.4.1.34592.1.3.3.12.2.1.1.1
-- 1.3.6.1.4.1.34592.1.3.3.12.2.1.1.1
-- 1.3.6.1.4.1.34592.1.3.3.12.2.1.1.1
-- 1.3.6.1.4.1.34592.1.3.3.12.2.1.1.1
		-- 1.3.6.1.4.1.34592.1.3.3.12.2.1.1.1
		maxLinkOamRate OBJECT-TYPE
			SYNTAX Integer32 (0..25)
			MAX-ACCESS read-write
			STATUS current
			DESCRIPTION
				"Description."
			::= { linkOamRateEntry 1 }


--      1.3.6.1.4.1.34592.1.3.3.12.2.1.1.2
-- 1.3.6.1.4.1.34592.1.3.3.12.2.1.1.2
-- 1.3.6.1.4.1.34592.1.3.3.12.2.1.1.2
-- 1.3.6.1.4.1.34592.1.3.3.12.2.1.1.2
		-- 1.3.6.1.4.1.34592.1.3.3.12.2.1.1.2
		minLinkOamRate OBJECT-TYPE
			SYNTAX Integer32 (0..10)
			MAX-ACCESS read-write
			STATUS current
			DESCRIPTION
				"Description."
			::= { linkOamRateEntry 2 }


--      1.3.6.1.4.1.34592.1.3.3.12.3
-- 1.3.6.1.4.1.34592.1.3.3.12.3
-- 1.3.6.1.4.1.34592.1.3.3.12.3
-- 1.3.6.1.4.1.34592.1.3.3.12.3
		-- 1.3.6.1.4.1.34592.1.3.3.12.3
		sla OBJECT IDENTIFIER ::= { llid 3 }


--      1.3.6.1.4.1.34592.1.3.3.12.3.1
-- 1.3.6.1.4.1.34592.1.3.3.12.3.1
-- 1.3.6.1.4.1.34592.1.3.3.12.3.1
-- 1.3.6.1.4.1.34592.1.3.3.12.3.1
		-- 1.3.6.1.4.1.34592.1.3.3.12.3.1
		llidSlaTable OBJECT-TYPE
			SYNTAX SEQUENCE OF LlidSlaEntry
			MAX-ACCESS not-accessible
			STATUS current
			DESCRIPTION
				" "
			::= { sla 1 }


--      1.3.6.1.4.1.34592.1.3.3.12.3.1.1
-- 1.3.6.1.4.1.34592.1.3.3.12.3.1.1
-- 1.3.6.1.4.1.34592.1.3.3.12.3.1.1
-- 1.3.6.1.4.1.34592.1.3.3.12.3.1.1
		-- 1.3.6.1.4.1.34592.1.3.3.12.3.1.1
		llidSlaEntry OBJECT-TYPE
			SYNTAX LlidSlaEntry
			MAX-ACCESS not-accessible
			STATUS current
			DESCRIPTION
				" "
			INDEX { ponCardSlotId, oltId, linkId, directionId }
			::= { llidSlaTable 1 }


		LlidSlaEntry ::=
			SEQUENCE {
				minGuaranteedBW
					Integer32,
				maxAllowedBW
					Integer32,
				delaySensitive
					INTEGER,
				maxBurstSize
					Integer32,
				slaEnable
					OperSwitch
			 }

--      1.3.6.1.4.1.34592.1.3.3.12.3.1.1.1
-- 1.3.6.1.4.1.34592.1.3.3.12.3.1.1.1
-- 1.3.6.1.4.1.34592.1.3.3.12.3.1.1.1
-- 1.3.6.1.4.1.34592.1.3.3.12.3.1.1.1
		-- 1.3.6.1.4.1.34592.1.3.3.12.3.1.1.1
		minGuaranteedBW OBJECT-TYPE
			SYNTAX Integer32 (0..1000000)
			UNITS "kbps"
			MAX-ACCESS read-write
			STATUS current
			DESCRIPTION
				"Minimum guaranted bandwidth"
			::= { llidSlaEntry 1 }


--      1.3.6.1.4.1.34592.1.3.3.12.3.1.1.2
-- 1.3.6.1.4.1.34592.1.3.3.12.3.1.1.2
-- 1.3.6.1.4.1.34592.1.3.3.12.3.1.1.2
-- 1.3.6.1.4.1.34592.1.3.3.12.3.1.1.2
		-- 1.3.6.1.4.1.34592.1.3.3.12.3.1.1.2
		maxAllowedBW OBJECT-TYPE
			SYNTAX Integer32 (0..1000000)
			UNITS "kbps"
			MAX-ACCESS read-write
			STATUS current
			DESCRIPTION
				"Max allowed bandwidth"
			::= { llidSlaEntry 2 }


--      1.3.6.1.4.1.34592.1.3.3.12.3.1.1.3
-- 1.3.6.1.4.1.34592.1.3.3.12.3.1.1.3
-- 1.3.6.1.4.1.34592.1.3.3.12.3.1.1.3
-- 1.3.6.1.4.1.34592.1.3.3.12.3.1.1.3
		-- 1.3.6.1.4.1.34592.1.3.3.12.3.1.1.3
		delaySensitive OBJECT-TYPE
			SYNTAX INTEGER
				{
				tolerant(1),
				sensitive(2)
				}
			MAX-ACCESS read-write
			STATUS current
			DESCRIPTION
				"transmit delay sensitive or tolerant"
			::= { llidSlaEntry 3 }


--      1.3.6.1.4.1.34592.1.3.3.12.3.1.1.4
-- 1.3.6.1.4.1.34592.1.3.3.12.3.1.1.4
-- 1.3.6.1.4.1.34592.1.3.3.12.3.1.1.4
-- 1.3.6.1.4.1.34592.1.3.3.12.3.1.1.4
		-- 1.3.6.1.4.1.34592.1.3.3.12.3.1.1.4
		maxBurstSize OBJECT-TYPE
			SYNTAX Integer32 (1..256)
			UNITS "kbytes"
			MAX-ACCESS read-write
			STATUS current
			DESCRIPTION
				"Maximum burst size"
			::= { llidSlaEntry 4 }


--      1.3.6.1.4.1.34592.1.3.3.12.3.1.1.5
-- 1.3.6.1.4.1.34592.1.3.3.12.3.1.1.5
-- 1.3.6.1.4.1.34592.1.3.3.12.3.1.1.5
-- 1.3.6.1.4.1.34592.1.3.3.12.3.1.1.5
		-- 1.3.6.1.4.1.34592.1.3.3.12.3.1.1.5
		slaEnable OBJECT-TYPE
			SYNTAX OperSwitch
			MAX-ACCESS read-write
			STATUS current
			DESCRIPTION
				"Sla enable disable"
			::= { llidSlaEntry 5 }


--      1.3.6.1.4.1.34592.1.3.3.12.3.2
-- 1.3.6.1.4.1.34592.1.3.3.12.3.2
-- 1.3.6.1.4.1.34592.1.3.3.12.3.2
-- 1.3.6.1.4.1.34592.1.3.3.12.3.2
		-- 1.3.6.1.4.1.34592.1.3.3.12.3.2
		slaWeightTable OBJECT-TYPE
			SYNTAX SEQUENCE OF SlaWeightEntry
			MAX-ACCESS not-accessible
			STATUS current
			DESCRIPTION
				" "
			::= { sla 2 }


--      1.3.6.1.4.1.34592.1.3.3.12.3.2.1
-- 1.3.6.1.4.1.34592.1.3.3.12.3.2.1
-- 1.3.6.1.4.1.34592.1.3.3.12.3.2.1
-- 1.3.6.1.4.1.34592.1.3.3.12.3.2.1
		-- 1.3.6.1.4.1.34592.1.3.3.12.3.2.1
		slaWeightEntry OBJECT-TYPE
			SYNTAX SlaWeightEntry
			MAX-ACCESS not-accessible
			STATUS current
			DESCRIPTION
				" "
			INDEX { ponCardSlotId, oltId, linkId, directionId }
			::= { slaWeightTable 1 }


		SlaWeightEntry ::=
			SEQUENCE {
				dbaTokens
					Integer32,
				schedulerMinTokens
					Integer32,
				schedulerMaxTokens
					Integer32,
				forceReport
					TruthValue
			 }

--      1.3.6.1.4.1.34592.1.3.3.12.3.2.1.1
-- 1.3.6.1.4.1.34592.1.3.3.12.3.2.1.1
-- 1.3.6.1.4.1.34592.1.3.3.12.3.2.1.1
-- 1.3.6.1.4.1.34592.1.3.3.12.3.2.1.1
		-- 1.3.6.1.4.1.34592.1.3.3.12.3.2.1.1
		dbaTokens OBJECT-TYPE
			SYNTAX Integer32 (0..255)
			MAX-ACCESS read-write
			STATUS current
			DESCRIPTION
				" "
			::= { slaWeightEntry 1 }


--      1.3.6.1.4.1.34592.1.3.3.12.3.2.1.2
-- 1.3.6.1.4.1.34592.1.3.3.12.3.2.1.2
-- 1.3.6.1.4.1.34592.1.3.3.12.3.2.1.2
-- 1.3.6.1.4.1.34592.1.3.3.12.3.2.1.2
		-- 1.3.6.1.4.1.34592.1.3.3.12.3.2.1.2
		schedulerMinTokens OBJECT-TYPE
			SYNTAX Integer32 (0..511)
			MAX-ACCESS read-write
			STATUS current
			DESCRIPTION
				" "
			::= { slaWeightEntry 2 }


--      1.3.6.1.4.1.34592.1.3.3.12.3.2.1.3
-- 1.3.6.1.4.1.34592.1.3.3.12.3.2.1.3
-- 1.3.6.1.4.1.34592.1.3.3.12.3.2.1.3
-- 1.3.6.1.4.1.34592.1.3.3.12.3.2.1.3
		-- 1.3.6.1.4.1.34592.1.3.3.12.3.2.1.3
		schedulerMaxTokens OBJECT-TYPE
			SYNTAX Integer32 (0..511)
			MAX-ACCESS read-write
			STATUS current
			DESCRIPTION
				" "
			::= { slaWeightEntry 3 }


--      1.3.6.1.4.1.34592.1.3.3.12.3.2.1.4
-- 1.3.6.1.4.1.34592.1.3.3.12.3.2.1.4
-- 1.3.6.1.4.1.34592.1.3.3.12.3.2.1.4
-- 1.3.6.1.4.1.34592.1.3.3.12.3.2.1.4
		-- 1.3.6.1.4.1.34592.1.3.3.12.3.2.1.4
		forceReport OBJECT-TYPE
			SYNTAX TruthValue
			MAX-ACCESS read-write
			STATUS current
			DESCRIPTION
				" "
			::= { slaWeightEntry 4 }


--      1.3.6.1.4.1.34592.1.3.3.12.3.3
-- 1.3.6.1.4.1.34592.1.3.3.12.3.3
-- 1.3.6.1.4.1.34592.1.3.3.12.3.3
-- 1.3.6.1.4.1.34592.1.3.3.12.3.3
		-- 1.3.6.1.4.1.34592.1.3.3.12.3.3
		multicastSlaTable OBJECT-TYPE
			SYNTAX SEQUENCE OF MulticastSlaEntry
			MAX-ACCESS not-accessible
			STATUS current
			DESCRIPTION
				" "
			::= { sla 3 }


--      1.3.6.1.4.1.34592.1.3.3.12.3.3.1
-- 1.3.6.1.4.1.34592.1.3.3.12.3.3.1
-- 1.3.6.1.4.1.34592.1.3.3.12.3.3.1
-- 1.3.6.1.4.1.34592.1.3.3.12.3.3.1
		-- 1.3.6.1.4.1.34592.1.3.3.12.3.3.1
		multicastSlaEntry OBJECT-TYPE
			SYNTAX MulticastSlaEntry
			MAX-ACCESS not-accessible
			STATUS current
			DESCRIPTION
				" "
			INDEX { ponCardSlotId, oltId, linkId }
			::= { multicastSlaTable 1 }


		MulticastSlaEntry ::=
			SEQUENCE {
				multiMinGuanBW
					Integer32,
				multiMaxAllowedBW
					Integer32,
				multiDelaySensitive
					INTEGER,
				multiMaxBurstSize
					Integer32
			 }

--      1.3.6.1.4.1.34592.1.3.3.12.3.3.1.1
-- 1.3.6.1.4.1.34592.1.3.3.12.3.3.1.1
-- 1.3.6.1.4.1.34592.1.3.3.12.3.3.1.1
-- 1.3.6.1.4.1.34592.1.3.3.12.3.3.1.1
		-- 1.3.6.1.4.1.34592.1.3.3.12.3.3.1.1
		multiMinGuanBW OBJECT-TYPE
			SYNTAX Integer32 (256..1000000)
			MAX-ACCESS read-write
			STATUS current
			DESCRIPTION
				" "
			::= { multicastSlaEntry 1 }


--      1.3.6.1.4.1.34592.1.3.3.12.3.3.1.2
-- 1.3.6.1.4.1.34592.1.3.3.12.3.3.1.2
-- 1.3.6.1.4.1.34592.1.3.3.12.3.3.1.2
-- 1.3.6.1.4.1.34592.1.3.3.12.3.3.1.2
		-- 1.3.6.1.4.1.34592.1.3.3.12.3.3.1.2
		multiMaxAllowedBW OBJECT-TYPE
			SYNTAX Integer32 (256..1000000)
			MAX-ACCESS read-write
			STATUS current
			DESCRIPTION
				" "
			::= { multicastSlaEntry 2 }


--      1.3.6.1.4.1.34592.1.3.3.12.3.3.1.3
-- 1.3.6.1.4.1.34592.1.3.3.12.3.3.1.3
-- 1.3.6.1.4.1.34592.1.3.3.12.3.3.1.3
-- 1.3.6.1.4.1.34592.1.3.3.12.3.3.1.3
		-- 1.3.6.1.4.1.34592.1.3.3.12.3.3.1.3
		multiDelaySensitive OBJECT-TYPE
			SYNTAX INTEGER
				{
				sensitive(1),
				tolerant(2)
				}
			MAX-ACCESS read-write
			STATUS current
			DESCRIPTION
				" "
			::= { multicastSlaEntry 3 }


--      1.3.6.1.4.1.34592.1.3.3.12.3.3.1.4
-- 1.3.6.1.4.1.34592.1.3.3.12.3.3.1.4
-- 1.3.6.1.4.1.34592.1.3.3.12.3.3.1.4
-- 1.3.6.1.4.1.34592.1.3.3.12.3.3.1.4
		-- 1.3.6.1.4.1.34592.1.3.3.12.3.3.1.4
		multiMaxBurstSize OBJECT-TYPE
			SYNTAX Integer32 (1..256)
			MAX-ACCESS read-write
			STATUS current
			DESCRIPTION
				" "
			::= { multicastSlaEntry 4 }


--      1.3.6.1.4.1.34592.1.3.3.12.4
-- 1.3.6.1.4.1.34592.1.3.3.12.4
-- 1.3.6.1.4.1.34592.1.3.3.12.4
-- 1.3.6.1.4.1.34592.1.3.3.12.4
		-- 1.3.6.1.4.1.34592.1.3.3.12.4
		llidVlan OBJECT IDENTIFIER ::= { llid 4 }


--      1.3.6.1.4.1.34592.1.3.3.12.4.1
-- 1.3.6.1.4.1.34592.1.3.3.12.4.1
-- 1.3.6.1.4.1.34592.1.3.3.12.4.1
-- 1.3.6.1.4.1.34592.1.3.3.12.4.1
		-- 1.3.6.1.4.1.34592.1.3.3.12.4.1
		llidVlanCfgTable OBJECT-TYPE
			SYNTAX SEQUENCE OF LlidVlanCfgEntry
			MAX-ACCESS not-accessible
			STATUS current
			DESCRIPTION
				" "
			::= { llidVlan 1 }


--      1.3.6.1.4.1.34592.1.3.3.12.4.1.1
-- 1.3.6.1.4.1.34592.1.3.3.12.4.1.1
-- 1.3.6.1.4.1.34592.1.3.3.12.4.1.1
-- 1.3.6.1.4.1.34592.1.3.3.12.4.1.1
		-- 1.3.6.1.4.1.34592.1.3.3.12.4.1.1
		llidVlanCfgEntry OBJECT-TYPE
			SYNTAX LlidVlanCfgEntry
			MAX-ACCESS not-accessible
			STATUS current
			DESCRIPTION
				" "
			INDEX { ponCardSlotId, oltId, linkId, llidVlanTag }
			::= { llidVlanCfgTable 1 }


		LlidVlanCfgEntry ::=
			SEQUENCE {
				llidVlanTag
					Integer32,
				llidVlanRowStatus
					RowStatus
			 }

--      1.3.6.1.4.1.34592.1.3.3.12.4.1.1.1
-- 1.3.6.1.4.1.34592.1.3.3.12.4.1.1.1
-- 1.3.6.1.4.1.34592.1.3.3.12.4.1.1.1
-- 1.3.6.1.4.1.34592.1.3.3.12.4.1.1.1
		-- 1.3.6.1.4.1.34592.1.3.3.12.4.1.1.1
		llidVlanTag OBJECT-TYPE
			SYNTAX Integer32 (1..4094)
			MAX-ACCESS not-accessible
			STATUS current
			DESCRIPTION
				"Vlan and translated vlan tags.
				Data formats:
				------------------------------
				vlan tag | translated vlan id |
				------------------------------
				   2B             2B

				translated vlan tag must be set to 0 if the link is not in
				vlan translate mode"
			::= { llidVlanCfgEntry 1 }


--      1.3.6.1.4.1.34592.1.3.3.12.4.1.1.2
-- 1.3.6.1.4.1.34592.1.3.3.12.4.1.1.2
-- 1.3.6.1.4.1.34592.1.3.3.12.4.1.1.2
-- 1.3.6.1.4.1.34592.1.3.3.12.4.1.1.2
		-- 1.3.6.1.4.1.34592.1.3.3.12.4.1.1.2
		llidVlanRowStatus OBJECT-TYPE
			SYNTAX RowStatus
			MAX-ACCESS read-create
			STATUS current
			DESCRIPTION
				"Create or delete a vlan tag for a given LinkId"
			::= { llidVlanCfgEntry 2 }


--      1.3.6.1.4.1.34592.1.3.3.12.4.2
-- 1.3.6.1.4.1.34592.1.3.3.12.4.2
-- 1.3.6.1.4.1.34592.1.3.3.12.4.2
-- 1.3.6.1.4.1.34592.1.3.3.12.4.2
		-- 1.3.6.1.4.1.34592.1.3.3.12.4.2
		vlanLlidTable OBJECT-TYPE
			SYNTAX SEQUENCE OF VlanLlidEntry
			MAX-ACCESS not-accessible
			STATUS current
			DESCRIPTION
				" "
			::= { llidVlan 2 }


--      1.3.6.1.4.1.34592.1.3.3.12.4.2.1
-- 1.3.6.1.4.1.34592.1.3.3.12.4.2.1
-- 1.3.6.1.4.1.34592.1.3.3.12.4.2.1
-- 1.3.6.1.4.1.34592.1.3.3.12.4.2.1
		-- 1.3.6.1.4.1.34592.1.3.3.12.4.2.1
		vlanLlidEntry OBJECT-TYPE
			SYNTAX VlanLlidEntry
			MAX-ACCESS not-accessible
			STATUS current
			DESCRIPTION
				" "
			INDEX { ponCardSlotId, oltId, vlanId }
			::= { vlanLlidTable 1 }


		VlanLlidEntry ::=
			SEQUENCE {
				vlanId
					Unsigned32,
				linkIDsInVlan
					OCTET STRING
			 }

--      1.3.6.1.4.1.34592.1.3.3.12.4.2.1.1
-- 1.3.6.1.4.1.34592.1.3.3.12.4.2.1.1
-- 1.3.6.1.4.1.34592.1.3.3.12.4.2.1.1
-- 1.3.6.1.4.1.34592.1.3.3.12.4.2.1.1
		-- 1.3.6.1.4.1.34592.1.3.3.12.4.2.1.1
		vlanId OBJECT-TYPE
			SYNTAX Unsigned32 (1..4096)
			MAX-ACCESS not-accessible
			STATUS current
			DESCRIPTION
				" "
			::= { vlanLlidEntry 1 }


--      1.3.6.1.4.1.34592.1.3.3.12.4.2.1.2
-- 1.3.6.1.4.1.34592.1.3.3.12.4.2.1.2
-- 1.3.6.1.4.1.34592.1.3.3.12.4.2.1.2
-- 1.3.6.1.4.1.34592.1.3.3.12.4.2.1.2
		-- 1.3.6.1.4.1.34592.1.3.3.12.4.2.1.2
		linkIDsInVlan OBJECT-TYPE
			SYNTAX OCTET STRING
			MAX-ACCESS read-only
			STATUS current
			DESCRIPTION
				"This object is a linkId container, which contain all the linkIds
				value which belong to this vlan.

				Data formats:
				------------------------------------------------
				link number|linkId0|linkId1|.....|linkIdn|......
				------------------------------------------------
				  2B          1B      1B            1B"
			::= { vlanLlidEntry 2 }


--      1.3.6.1.4.1.34592.1.3.3.12.4.3
-- 1.3.6.1.4.1.34592.1.3.3.12.4.3
-- 1.3.6.1.4.1.34592.1.3.3.12.4.3
-- 1.3.6.1.4.1.34592.1.3.3.12.4.3
		-- 1.3.6.1.4.1.34592.1.3.3.12.4.3
		priVlanTable OBJECT-TYPE
			SYNTAX SEQUENCE OF PriVlanEntry
			MAX-ACCESS not-accessible
			STATUS current
			DESCRIPTION
				"Description. Reserved"
			::= { llidVlan 3 }


--      1.3.6.1.4.1.34592.1.3.3.12.4.3.1
-- 1.3.6.1.4.1.34592.1.3.3.12.4.3.1
-- 1.3.6.1.4.1.34592.1.3.3.12.4.3.1
-- 1.3.6.1.4.1.34592.1.3.3.12.4.3.1
		-- 1.3.6.1.4.1.34592.1.3.3.12.4.3.1
		priVlanEntry OBJECT-TYPE
			SYNTAX PriVlanEntry
			MAX-ACCESS not-accessible
			STATUS current
			DESCRIPTION
				"Description."
			INDEX { ponCardSlotId, oltId, linkId }
			::= { priVlanTable 1 }


		PriVlanEntry ::=
			SEQUENCE {
				netVlanId
					INTEGER,
				upstreamCos
					Integer32,
				priSelector
					INTEGER,
				minPriValue
					Integer32,
				maxPriValue
					Integer32,
				transNonTosFrame
					TruthValue,
				priVlanRowStatus
					RowStatus
			 }

--      1.3.6.1.4.1.34592.1.3.3.12.4.3.1.1
-- 1.3.6.1.4.1.34592.1.3.3.12.4.3.1.1
-- 1.3.6.1.4.1.34592.1.3.3.12.4.3.1.1
-- 1.3.6.1.4.1.34592.1.3.3.12.4.3.1.1
		-- 1.3.6.1.4.1.34592.1.3.3.12.4.3.1.1
		netVlanId OBJECT-TYPE
			SYNTAX INTEGER (1..4094)
			MAX-ACCESS read-create
			STATUS current
			DESCRIPTION
				"Description."
			::= { priVlanEntry 1 }


--      1.3.6.1.4.1.34592.1.3.3.12.4.3.1.2
-- 1.3.6.1.4.1.34592.1.3.3.12.4.3.1.2
-- 1.3.6.1.4.1.34592.1.3.3.12.4.3.1.2
-- 1.3.6.1.4.1.34592.1.3.3.12.4.3.1.2
		-- 1.3.6.1.4.1.34592.1.3.3.12.4.3.1.2
		upstreamCos OBJECT-TYPE
			SYNTAX Integer32 (0..7)
			MAX-ACCESS read-create
			STATUS current
			DESCRIPTION
				"Description."
			::= { priVlanEntry 2 }


--      1.3.6.1.4.1.34592.1.3.3.12.4.3.1.3
-- 1.3.6.1.4.1.34592.1.3.3.12.4.3.1.3
-- 1.3.6.1.4.1.34592.1.3.3.12.4.3.1.3
-- 1.3.6.1.4.1.34592.1.3.3.12.4.3.1.3
		-- 1.3.6.1.4.1.34592.1.3.3.12.4.3.1.3
		priSelector OBJECT-TYPE
			SYNTAX INTEGER
				{
				cos(1),
				tos(2)
				}
			MAX-ACCESS read-create
			STATUS current
			DESCRIPTION
				"Description."
			::= { priVlanEntry 3 }


--      1.3.6.1.4.1.34592.1.3.3.12.4.3.1.4
-- 1.3.6.1.4.1.34592.1.3.3.12.4.3.1.4
-- 1.3.6.1.4.1.34592.1.3.3.12.4.3.1.4
-- 1.3.6.1.4.1.34592.1.3.3.12.4.3.1.4
		-- 1.3.6.1.4.1.34592.1.3.3.12.4.3.1.4
		minPriValue OBJECT-TYPE
			SYNTAX Integer32 (0..7)
			MAX-ACCESS read-create
			STATUS current
			DESCRIPTION
				"Description."
			::= { priVlanEntry 4 }


--      1.3.6.1.4.1.34592.1.3.3.12.4.3.1.5
-- 1.3.6.1.4.1.34592.1.3.3.12.4.3.1.5
-- 1.3.6.1.4.1.34592.1.3.3.12.4.3.1.5
-- 1.3.6.1.4.1.34592.1.3.3.12.4.3.1.5
		-- 1.3.6.1.4.1.34592.1.3.3.12.4.3.1.5
		maxPriValue OBJECT-TYPE
			SYNTAX Integer32 (0..7)
			MAX-ACCESS read-create
			STATUS current
			DESCRIPTION
				"Description."
			::= { priVlanEntry 5 }


--      1.3.6.1.4.1.34592.1.3.3.12.4.3.1.6
-- 1.3.6.1.4.1.34592.1.3.3.12.4.3.1.6
-- 1.3.6.1.4.1.34592.1.3.3.12.4.3.1.6
-- 1.3.6.1.4.1.34592.1.3.3.12.4.3.1.6
		-- 1.3.6.1.4.1.34592.1.3.3.12.4.3.1.6
		transNonTosFrame OBJECT-TYPE
			SYNTAX TruthValue
			MAX-ACCESS read-create
			STATUS current
			DESCRIPTION
				"Description."
			::= { priVlanEntry 6 }


--      1.3.6.1.4.1.34592.1.3.3.12.4.3.1.7
-- 1.3.6.1.4.1.34592.1.3.3.12.4.3.1.7
-- 1.3.6.1.4.1.34592.1.3.3.12.4.3.1.7
-- 1.3.6.1.4.1.34592.1.3.3.12.4.3.1.7
		-- 1.3.6.1.4.1.34592.1.3.3.12.4.3.1.7
		priVlanRowStatus OBJECT-TYPE
			SYNTAX RowStatus
			MAX-ACCESS read-create
			STATUS current
			DESCRIPTION
				"Description."
			::= { priVlanEntry 7 }


--      1.3.6.1.4.1.34592.1.3.3.12.5
-- 1.3.6.1.4.1.34592.1.3.3.12.5
-- 1.3.6.1.4.1.34592.1.3.3.12.5
-- 1.3.6.1.4.1.34592.1.3.3.12.5
		-- 1.3.6.1.4.1.34592.1.3.3.12.5
		blockedLinkTable OBJECT-TYPE
			SYNTAX SEQUENCE OF BlockedLinkEntry
			MAX-ACCESS not-accessible
			STATUS current
			DESCRIPTION
				" "
			::= { llid 5 }


--      1.3.6.1.4.1.34592.1.3.3.12.5.1
-- 1.3.6.1.4.1.34592.1.3.3.12.5.1
-- 1.3.6.1.4.1.34592.1.3.3.12.5.1
-- 1.3.6.1.4.1.34592.1.3.3.12.5.1
		-- 1.3.6.1.4.1.34592.1.3.3.12.5.1
		blockedLinkEntry OBJECT-TYPE
			SYNTAX BlockedLinkEntry
			MAX-ACCESS not-accessible
			STATUS current
			DESCRIPTION
				" "
			INDEX { ponCardSlotId, oltId, linkId }
			::= { blockedLinkTable 1 }


		BlockedLinkEntry ::=
			SEQUENCE {
				blockedLinkMac
					MacAddress,
				blockedMacOper
					INTEGER
			 }

--      1.3.6.1.4.1.34592.1.3.3.12.5.1.1
-- 1.3.6.1.4.1.34592.1.3.3.12.5.1.1
-- 1.3.6.1.4.1.34592.1.3.3.12.5.1.1
-- 1.3.6.1.4.1.34592.1.3.3.12.5.1.1
		-- 1.3.6.1.4.1.34592.1.3.3.12.5.1.1
		blockedLinkMac OBJECT-TYPE
			SYNTAX MacAddress
			MAX-ACCESS read-only
			STATUS current
			DESCRIPTION
				" "
			::= { blockedLinkEntry 1 }


--      1.3.6.1.4.1.34592.1.3.3.12.5.1.2
-- 1.3.6.1.4.1.34592.1.3.3.12.5.1.2
-- 1.3.6.1.4.1.34592.1.3.3.12.5.1.2
-- 1.3.6.1.4.1.34592.1.3.3.12.5.1.2
		-- 1.3.6.1.4.1.34592.1.3.3.12.5.1.2
		blockedMacOper OBJECT-TYPE
			SYNTAX INTEGER { unblock(2) }
			MAX-ACCESS read-write
			STATUS current
			DESCRIPTION
				" "
			::= { blockedLinkEntry 2 }


--      1.3.6.1.4.1.34592.1.3.3.12.6
-- 1.3.6.1.4.1.34592.1.3.3.12.6
-- 1.3.6.1.4.1.34592.1.3.3.12.6
-- 1.3.6.1.4.1.34592.1.3.3.12.6
		-- 1.3.6.1.4.1.34592.1.3.3.12.6
		macAddr OBJECT IDENTIFIER ::= { llid 6 }


--      1.3.6.1.4.1.34592.1.3.3.12.6.1
-- 1.3.6.1.4.1.34592.1.3.3.12.6.1
-- 1.3.6.1.4.1.34592.1.3.3.12.6.1
-- 1.3.6.1.4.1.34592.1.3.3.12.6.1
		-- 1.3.6.1.4.1.34592.1.3.3.12.6.1
		dynamicMac OBJECT IDENTIFIER ::= { macAddr 1 }


--      1.3.6.1.4.1.34592.1.3.3.12.6.1.1
-- 1.3.6.1.4.1.34592.1.3.3.12.6.1.1
-- 1.3.6.1.4.1.34592.1.3.3.12.6.1.1
-- 1.3.6.1.4.1.34592.1.3.3.12.6.1.1
		-- 1.3.6.1.4.1.34592.1.3.3.12.6.1.1
		dynMacOperTable OBJECT-TYPE
			SYNTAX SEQUENCE OF DynMacOperEntry
			MAX-ACCESS not-accessible
			STATUS current
			DESCRIPTION
				" "
			::= { dynamicMac 1 }


--      1.3.6.1.4.1.34592.1.3.3.12.6.1.1.1
-- 1.3.6.1.4.1.34592.1.3.3.12.6.1.1.1
-- 1.3.6.1.4.1.34592.1.3.3.12.6.1.1.1
-- 1.3.6.1.4.1.34592.1.3.3.12.6.1.1.1
		-- 1.3.6.1.4.1.34592.1.3.3.12.6.1.1.1
		dynMacOperEntry OBJECT-TYPE
			SYNTAX DynMacOperEntry
			MAX-ACCESS not-accessible
			STATUS current
			DESCRIPTION
				" "
			INDEX { ponCardSlotId, oltId, linkId }
			::= { dynMacOperTable 1 }


		DynMacOperEntry ::=
			SEQUENCE {
				dynMacOperation
					INTEGER
			 }

--      1.3.6.1.4.1.34592.1.3.3.12.6.1.1.1.1
-- 1.3.6.1.4.1.34592.1.3.3.12.6.1.1.1.1
-- 1.3.6.1.4.1.34592.1.3.3.12.6.1.1.1.1
-- 1.3.6.1.4.1.34592.1.3.3.12.6.1.1.1.1
		-- 1.3.6.1.4.1.34592.1.3.3.12.6.1.1.1.1
		dynMacOperation OBJECT-TYPE
			SYNTAX INTEGER
				{
				clear(2),
				refresh(3)
				}
			MAX-ACCESS read-write
			STATUS current
			DESCRIPTION
				" "
			::= { dynMacOperEntry 1 }


--      1.3.6.1.4.1.34592.1.3.3.12.6.1.2
-- 1.3.6.1.4.1.34592.1.3.3.12.6.1.2
-- 1.3.6.1.4.1.34592.1.3.3.12.6.1.2
-- 1.3.6.1.4.1.34592.1.3.3.12.6.1.2
		-- 1.3.6.1.4.1.34592.1.3.3.12.6.1.2
		dynMacTable OBJECT-TYPE
			SYNTAX SEQUENCE OF DynMacEntry
			MAX-ACCESS not-accessible
			STATUS current
			DESCRIPTION
				" "
			::= { dynamicMac 2 }


--      1.3.6.1.4.1.34592.1.3.3.12.6.1.2.1
-- 1.3.6.1.4.1.34592.1.3.3.12.6.1.2.1
-- 1.3.6.1.4.1.34592.1.3.3.12.6.1.2.1
-- 1.3.6.1.4.1.34592.1.3.3.12.6.1.2.1
		-- 1.3.6.1.4.1.34592.1.3.3.12.6.1.2.1
		dynMacEntry OBJECT-TYPE
			SYNTAX DynMacEntry
			MAX-ACCESS not-accessible
			STATUS current
			DESCRIPTION
				" "
			INDEX { ponCardSlotId, oltId, linkId, dynMacIndex }
			::= { dynMacTable 1 }


		DynMacEntry ::=
			SEQUENCE {
				dynMacIndex
					Integer32,
				dynMacAddr
					MacAddress
			 }

--      1.3.6.1.4.1.34592.1.3.3.12.6.1.2.1.1
-- 1.3.6.1.4.1.34592.1.3.3.12.6.1.2.1.1
-- 1.3.6.1.4.1.34592.1.3.3.12.6.1.2.1.1
-- 1.3.6.1.4.1.34592.1.3.3.12.6.1.2.1.1
		-- 1.3.6.1.4.1.34592.1.3.3.12.6.1.2.1.1
		dynMacIndex OBJECT-TYPE
			SYNTAX Integer32 (1..4094)
			MAX-ACCESS not-accessible
			STATUS current
			DESCRIPTION
				" "
			::= { dynMacEntry 1 }


--      1.3.6.1.4.1.34592.1.3.3.12.6.1.2.1.2
-- 1.3.6.1.4.1.34592.1.3.3.12.6.1.2.1.2
-- 1.3.6.1.4.1.34592.1.3.3.12.6.1.2.1.2
-- 1.3.6.1.4.1.34592.1.3.3.12.6.1.2.1.2
		-- 1.3.6.1.4.1.34592.1.3.3.12.6.1.2.1.2
		dynMacAddr OBJECT-TYPE
			SYNTAX MacAddress
			MAX-ACCESS read-only
			STATUS current
			DESCRIPTION
				" "
			::= { dynMacEntry 2 }


--      1.3.6.1.4.1.34592.1.3.3.12.6.2
-- 1.3.6.1.4.1.34592.1.3.3.12.6.2
-- 1.3.6.1.4.1.34592.1.3.3.12.6.2
-- 1.3.6.1.4.1.34592.1.3.3.12.6.2
		-- 1.3.6.1.4.1.34592.1.3.3.12.6.2
		staticMac OBJECT IDENTIFIER ::= { macAddr 2 }


--      1.3.6.1.4.1.34592.1.3.3.12.6.2.1
-- 1.3.6.1.4.1.34592.1.3.3.12.6.2.1
-- 1.3.6.1.4.1.34592.1.3.3.12.6.2.1
-- 1.3.6.1.4.1.34592.1.3.3.12.6.2.1
		-- 1.3.6.1.4.1.34592.1.3.3.12.6.2.1
		staticMacTable OBJECT-TYPE
			SYNTAX SEQUENCE OF StaticMacEntry
			MAX-ACCESS not-accessible
			STATUS current
			DESCRIPTION
				" "
			::= { staticMac 1 }


--      1.3.6.1.4.1.34592.1.3.3.12.6.2.1.1
-- 1.3.6.1.4.1.34592.1.3.3.12.6.2.1.1
-- 1.3.6.1.4.1.34592.1.3.3.12.6.2.1.1
-- 1.3.6.1.4.1.34592.1.3.3.12.6.2.1.1
		-- 1.3.6.1.4.1.34592.1.3.3.12.6.2.1.1
		staticMacEntry OBJECT-TYPE
			SYNTAX StaticMacEntry
			MAX-ACCESS not-accessible
			STATUS current
			DESCRIPTION
				" "
			INDEX { ponCardSlotId, oltId, linkId, staticMacIndex }
			::= { staticMacTable 1 }


		StaticMacEntry ::=
			SEQUENCE {
				staticMacIndex
					Integer32,
				staticMacAddr
					MacAddress,
				staticMacRowStatus
					RowStatus
			 }

--      1.3.6.1.4.1.34592.1.3.3.12.6.2.1.1.1
-- 1.3.6.1.4.1.34592.1.3.3.12.6.2.1.1.1
-- 1.3.6.1.4.1.34592.1.3.3.12.6.2.1.1.1
-- 1.3.6.1.4.1.34592.1.3.3.12.6.2.1.1.1
		-- 1.3.6.1.4.1.34592.1.3.3.12.6.2.1.1.1
		staticMacIndex OBJECT-TYPE
			SYNTAX Integer32 (1..4096)
			MAX-ACCESS not-accessible
			STATUS current
			DESCRIPTION
				"Description."
			::= { staticMacEntry 1 }


--      1.3.6.1.4.1.34592.1.3.3.12.6.2.1.1.2
-- 1.3.6.1.4.1.34592.1.3.3.12.6.2.1.1.2
-- 1.3.6.1.4.1.34592.1.3.3.12.6.2.1.1.2
-- 1.3.6.1.4.1.34592.1.3.3.12.6.2.1.1.2
		-- 1.3.6.1.4.1.34592.1.3.3.12.6.2.1.1.2
		staticMacAddr OBJECT-TYPE
			SYNTAX MacAddress
			MAX-ACCESS read-only
			STATUS current
			DESCRIPTION
				" "
			::= { staticMacEntry 2 }


--      1.3.6.1.4.1.34592.1.3.3.12.6.2.1.1.3
-- 1.3.6.1.4.1.34592.1.3.3.12.6.2.1.1.3
-- 1.3.6.1.4.1.34592.1.3.3.12.6.2.1.1.3
-- 1.3.6.1.4.1.34592.1.3.3.12.6.2.1.1.3
		-- 1.3.6.1.4.1.34592.1.3.3.12.6.2.1.1.3
		staticMacRowStatus OBJECT-TYPE
			SYNTAX RowStatus
			MAX-ACCESS read-create
			STATUS current
			DESCRIPTION
				" "
			::= { staticMacEntry 3 }


--      1.3.6.1.4.1.34592.1.3.3.13
-- 1.3.6.1.4.1.34592.1.3.3.13
-- 1.3.6.1.4.1.34592.1.3.3.13
-- 1.3.6.1.4.1.34592.1.3.3.13
		-- 1.3.6.1.4.1.34592.1.3.3.13
		onuP2pTable OBJECT-TYPE
			SYNTAX SEQUENCE OF OnuP2pEntry
			MAX-ACCESS not-accessible
			STATUS current
			DESCRIPTION
				"Description."
			::= { fdOlt 13 }


--      1.3.6.1.4.1.34592.1.3.3.13.1
-- 1.3.6.1.4.1.34592.1.3.3.13.1
-- 1.3.6.1.4.1.34592.1.3.3.13.1
-- 1.3.6.1.4.1.34592.1.3.3.13.1
		-- 1.3.6.1.4.1.34592.1.3.3.13.1
		onuP2pEntry OBJECT-TYPE
			SYNTAX OnuP2pEntry
			MAX-ACCESS not-accessible
			STATUS current
			DESCRIPTION
				"Description."
			INDEX { ponCardSlotId }
			::= { onuP2pTable 1 }


		OnuP2pEntry ::=
			SEQUENCE {
				onuP2pEnDis
					INTEGER,
				onuP2pPonEnDis
					INTEGER
			 }

--      1.3.6.1.4.1.34592.1.3.3.13.1.1
-- 1.3.6.1.4.1.34592.1.3.3.13.1.1
-- 1.3.6.1.4.1.34592.1.3.3.13.1.1
-- 1.3.6.1.4.1.34592.1.3.3.13.1.1
		-- 1.3.6.1.4.1.34592.1.3.3.13.1.1
		onuP2pEnDis OBJECT-TYPE
			SYNTAX INTEGER
				{
				disable(0),
				enable(1)
				}
			MAX-ACCESS read-write
			STATUS current
			DESCRIPTION
				"0:disable
				1:enable"
			::= { onuP2pEntry 1 }


--      1.3.6.1.4.1.34592.1.3.3.13.1.2
-- 1.3.6.1.4.1.34592.1.3.3.13.1.2
-- 1.3.6.1.4.1.34592.1.3.3.13.1.2
-- 1.3.6.1.4.1.34592.1.3.3.13.1.2
		-- 1.3.6.1.4.1.34592.1.3.3.13.1.2
		onuP2pPonEnDis OBJECT-TYPE
			SYNTAX INTEGER
				{
				disdis(0),
				disen(1),
				endis(65536),
				enen(65537)
				}
			MAX-ACCESS read-write
			STATUS current
			DESCRIPTION
				"Description."
			::= { onuP2pEntry 2 }


--    1.3.6.1.4.1.34592.1.3.3.14
-- 1.3.6.1.4.1.34592.1.3.3.14
-- 1.3.6.1.4.1.34592.1.3.3.14
		-- 1.3.6.1.4.1.34592.1.3.3.14
		onuStatusTable OBJECT-TYPE
			SYNTAX SEQUENCE OF OnuStatusEntry
			MAX-ACCESS not-accessible
			STATUS current
			DESCRIPTION
				"Description."
			::= { fdOlt 14 }


--    1.3.6.1.4.1.34592.1.3.3.14.1
-- 1.3.6.1.4.1.34592.1.3.3.14.1
-- 1.3.6.1.4.1.34592.1.3.3.14.1
		-- 1.3.6.1.4.1.34592.1.3.3.14.1
		onuStatusEntry OBJECT-TYPE
			SYNTAX OnuStatusEntry
			MAX-ACCESS not-accessible
			STATUS current
			DESCRIPTION
				"Description."
			INDEX { ponCardSlotId, oltId }
			::= { onuStatusTable 1 }


		OnuStatusEntry ::=
			SEQUENCE {
				onuStatusBmp
					OCTET STRING
			 }

--    1.3.6.1.4.1.34592.1.3.3.14.1.2
-- 1.3.6.1.4.1.34592.1.3.3.14.1.1
-- 1.3.6.1.4.1.34592.1.3.3.14.1.1
		-- 1.3.6.1.4.1.34592.1.3.3.14.1.1
		onuStatusBmp OBJECT-TYPE
			SYNTAX OCTET STRING
			MAX-ACCESS read-only
			STATUS current
			DESCRIPTION
				"Description:
				Every one byte for one ONU online status, max 64 ONUs.
				not exist(0)
				online(1)
				offline(2)
				alarm(3)"
			::= { onuStatusEntry 1 }

--    1.3.6.1.4.1.34592.1.3.3.15
-- 1.3.6.1.4.1.34592.1.3.3.15
-- 1.3.6.1.4.1.34592.1.3.3.15
		-- 1.3.6.1.4.1.34592.1.3.3.15
		qinqConfigTable OBJECT-TYPE
			SYNTAX SEQUENCE OF QinqConfigEntry
			MAX-ACCESS not-accessible
			STATUS current
			DESCRIPTION
				"Description."
			::= { fdOlt 15 }


--    1.3.6.1.4.1.34592.1.3.3.15.1
-- 1.3.6.1.4.1.34592.1.3.3.15.1
-- 1.3.6.1.4.1.34592.1.3.3.15.1
		-- 1.3.6.1.4.1.34592.1.3.3.15.1
		qinqConfigEntry OBJECT-TYPE
			SYNTAX QinqConfigEntry
			MAX-ACCESS not-accessible
			STATUS current
			DESCRIPTION
				"Description."
			INDEX { ponCardSlotId, oltId, qinqId }
			::= { qinqConfigTable 1 }


		QinqConfigEntry ::=
			SEQUENCE {
				qinqId
					INTEGER,
				qinqConfigData
					OCTET STRING
			 }

--    1.3.6.1.4.1.34592.1.3.3.15.1.1
-- 1.3.6.1.4.1.34592.1.3.3.15.1.1
-- 1.3.6.1.4.1.34592.1.3.3.14.1.1
		-- 1.3.6.1.4.1.34592.1.3.3.15.1.1
		qinqId OBJECT-TYPE
			SYNTAX INTEGER (1..6)
			MAX-ACCESS not-accessible
			STATUS current
			DESCRIPTION
				"Description: qinqId(1-6)"
			::= { qinqConfigEntry 1 }

--    1.3.6.1.4.1.34592.1.3.3.15.1.2
-- 1.3.6.1.4.1.34592.1.3.3.15.1.2
-- 1.3.6.1.4.1.34592.1.3.3.14.1.2
		-- 1.3.6.1.4.1.34592.1.3.3.15.1.2
		qinqConfigData OBJECT-TYPE
			SYNTAX OCTET STRING
			MAX-ACCESS read-write
			STATUS current
			DESCRIPTION
				"Description: "
			::= { qinqConfigEntry 2 }

--      1.3.6.1.4.1.34592.1.3.3.20
-- 1.3.6.1.4.1.34592.1.3.3.20
-- 1.3.6.1.4.1.34592.1.3.3.20
-- 1.3.6.1.4.1.34592.1.3.3.20
		-- 1.3.6.1.4.1.34592.1.3.3.20
		fdOltConformance OBJECT IDENTIFIER ::= { fdOlt 20 }


--      1.3.6.1.4.1.34592.1.3.3.20.1
-- 1.3.6.1.4.1.34592.1.3.3.20.1
-- 1.3.6.1.4.1.34592.1.3.3.20.1
-- 1.3.6.1.4.1.34592.1.3.3.20.1
		-- 1.3.6.1.4.1.34592.1.3.3.20.1
		fdOltGroups OBJECT IDENTIFIER ::= { fdOltConformance 1 }


--      1.3.6.1.4.1.34592.1.3.3.20.1.1
-- 1.3.6.1.4.1.34592.1.3.3.20.1.1
-- 1.3.6.1.4.1.34592.1.3.3.20.1.1
-- 1.3.6.1.4.1.34592.1.3.3.20.1.1
		-- 1.3.6.1.4.1.34592.1.3.3.20.1.1
		oltBaseManageGroup OBJECT-GROUP
			OBJECTS { oltMacAddr, oltWorkState, oltEnable, maxPermitLLIDNumber, registeredLLIDNumber,
				accessedOnuNumber, oltUpgradeStat, onuMgmtDefType, onuStatusBmp, oltPortBandwidth,
				oltOperate, linkIdExhaust, onuIdExhaust, linkIdOverWrite, onuIdOverWrite,
				dynMacAgeTime, downStreamResetAgeTimer, bridgedVlanNumber, macOverWrite, discardUnknownMac,
				forwardTagOnSimpleBridge, level0Links, level1Links, level2Links, nonDbaLinks,
				l0DropDownWeight, l1DropDownWeight, l2DropDownWeight, l0PollingRate, l1PollingRate,
				l2PollingRate, aggreBandWidth, aggreMaxBurstSize, oltAclRuleData, priCopyMapData
				 }
			STATUS current
			DESCRIPTION
				"A collection of objects providing the basic OLT management."
			::= { fdOltGroups 1 }


--      1.3.6.1.4.1.34592.1.3.3.20.1.2
-- 1.3.6.1.4.1.34592.1.3.3.20.1.2
-- 1.3.6.1.4.1.34592.1.3.3.20.1.2
-- 1.3.6.1.4.1.34592.1.3.3.20.1.2
		-- 1.3.6.1.4.1.34592.1.3.3.20.1.2
		oltAdvanceManageGroup OBJECT-GROUP
			OBJECTS { oltChipProCode, oltChipVer, oltChipFirmVer, oltChipBootVer, oltChipPersVer,
				oltChipApp0Ver, oltChipApp1Ver, oltChipDiagVer, minOamRate, maxOamRate,
				oamRspTimeout, discoverPeriod, discoverWindow, discoverTimeoutVal, oltAddiVlanEthType,
				onuUltraLongDistanceTrans, oltBroadCastRateCtl, oltMultiCastRateCtl, oltUnkUcCastRateCtl, oltBroadCastRate,
				oltDdmInfoTemperature, oltDdmInfoVoltage, oltDdmInfoTxBias, oltDdmInfoTxPower, oltDdmInfoRxPower,
				oltDdmInfoVendor, oltDdmInfoProductName, oltDdmInfoVersion, oltDdmInfoSn }
			STATUS current
			DESCRIPTION
				"A collection of objects providing advanced OLT management feature"
			::= { fdOltGroups 2 }


--      1.3.6.1.4.1.34592.1.3.3.20.1.3
-- 1.3.6.1.4.1.34592.1.3.3.20.1.3
-- 1.3.6.1.4.1.34592.1.3.3.20.1.3
-- 1.3.6.1.4.1.34592.1.3.3.20.1.3
		-- 1.3.6.1.4.1.34592.1.3.3.20.1.3
		oltIgmpProxyGroup OBJECT-GROUP
			OBJECTS { maxIgmpGroups, robustCount, queryInterval, queryRspTimeout, queryMaxResTime,
				startQueryCount, startupQueryInterval, lastMemberQueryCount, lastMemberQueryInterval, lastMemberQueryResTime,
				upstreamRetransCount, upstreamRetransInterval, igmpQueues, igmpSlaMinGuaranteedBW, igmpSlaMaxAllowedBW,
				igmpSlaDelaySensitive, igmpSlaMaxBurstSize, igmpProxyOper, igmpGroupVlan, igmpGroupIpAddr
				 }
			STATUS current
			DESCRIPTION
				"A collection of objects providing OLT IGMP proxy feature management"
			::= { fdOltGroups 3 }


--      1.3.6.1.4.1.34592.1.3.3.20.1.4
-- 1.3.6.1.4.1.34592.1.3.3.20.1.4
-- 1.3.6.1.4.1.34592.1.3.3.20.1.4
-- 1.3.6.1.4.1.34592.1.3.3.20.1.4
		-- 1.3.6.1.4.1.34592.1.3.3.20.1.4
		oltPPPoEPlusGroup OBJECT-GROUP
			OBJECTS { pppoePlusEnable, dhcpOption82 }
			STATUS current
			DESCRIPTION
				"A collection of objects providing pppoe+ feature management"
			::= { fdOltGroups 4 }


--      1.3.6.1.4.1.34592.1.3.3.20.1.5
-- 1.3.6.1.4.1.34592.1.3.3.20.1.5
-- 1.3.6.1.4.1.34592.1.3.3.20.1.5
-- 1.3.6.1.4.1.34592.1.3.3.20.1.5
		-- 1.3.6.1.4.1.34592.1.3.3.20.1.5
		oltLlidBaseManageGroup OBJECT-GROUP
			OBJECTS { llidAssigned, associatedOnuId, llidMac, linkOnLineStatus, keyChangeTimer,
				llidBridgeType, llidMacEntryLimit, crossConnectLinkId, llidOperation, minGuaranteedBW,
				maxAllowedBW, delaySensitive, maxBurstSize, slaEnable, dbaTokens,
				schedulerMinTokens, schedulerMaxTokens, forceReport, llidVlanRowStatus, linkIDsInVlan,
				netVlanId, upstreamCos, priSelector, minPriValue, maxPriValue,
				transNonTosFrame, priVlanRowStatus, blockedLinkMac, blockedMacOper, dynMacOperation,
				dynMacAddr, staticMacAddr, staticMacRowStatus, multiMinGuanBW, multiMaxAllowedBW,
				multiDelaySensitive, multiMaxBurstSize }
			STATUS current
			DESCRIPTION
				"A collection of objects providing basic LLID (Logical Link)
				features management"
			::= { fdOltGroups 5 }


--      1.3.6.1.4.1.34592.1.3.3.20.1.6
-- 1.3.6.1.4.1.34592.1.3.3.20.1.6
-- 1.3.6.1.4.1.34592.1.3.3.20.1.6
-- 1.3.6.1.4.1.34592.1.3.3.20.1.6
		-- 1.3.6.1.4.1.34592.1.3.3.20.1.6
		oltLlidAdvanceManageGroup OBJECT-GROUP
			OBJECTS { maxLinkOamRate, minLinkOamRate }
			STATUS current
			DESCRIPTION
				"A collection of objects providing advanced LLID (Logical Link)
				features management"
			::= { fdOltGroups 6 }


--      1.3.6.1.4.1.34592.1.3.3.20.1.7
-- 1.3.6.1.4.1.34592.1.3.3.20.1.7
-- 1.3.6.1.4.1.34592.1.3.3.20.1.7
-- 1.3.6.1.4.1.34592.1.3.3.20.1.7
		-- 1.3.6.1.4.1.34592.1.3.3.20.1.7
		onuP2pManageGroup OBJECT-GROUP
			OBJECTS { onuP2pEnDis, onuP2pPonEnDis }
			STATUS current
			DESCRIPTION
				"Description."
			::= { fdOltGroups 7 }


--      1.3.6.1.4.1.34592.1.3.3.20.2
-- 1.3.6.1.4.1.34592.1.3.3.20.2
-- 1.3.6.1.4.1.34592.1.3.3.20.2
-- 1.3.6.1.4.1.34592.1.3.3.20.2
		-- 1.3.6.1.4.1.34592.1.3.3.20.2
		fdOltCompliances OBJECT IDENTIFIER ::= { fdOltConformance 2 }


--      1.3.6.1.4.1.34592.1.3.3.20.2.1
-- this module
-- this module
-- 1.3.6.1.4.1.34592.1.3.3.20.2.1
-- this module
-- 1.3.6.1.4.1.34592.1.3.3.20.2.1
-- this module
-- 1.3.6.1.4.1.34592.1.3.3.20.2.1
-- this module
		-- 1.3.6.1.4.1.34592.1.3.3.20.2.1
		fdOltCompliance MODULE-COMPLIANCE
			STATUS current
			DESCRIPTION
				"The compliance statement for fd epon device which
				implement FD-OLT-MIB"
			MODULE -- this module
				MANDATORY-GROUPS { oltBaseManageGroup, oltIgmpProxyGroup, oltPPPoEPlusGroup, oltLlidBaseManageGroup, onuP2pManageGroup
					 }
				GROUP oltAdvanceManageGroup
					DESCRIPTION
						"This group may or may not be supported"
				GROUP oltLlidAdvanceManageGroup
					DESCRIPTION
						"This group may or may not be supported"
			::= { fdOltCompliances 1 }



	END

--
-- FD-OLT-MIB.my
--
