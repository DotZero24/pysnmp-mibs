CISCOSB-BLTH-MIB DEFINITIONS ::= BEGIN
-- Date:                30 Mar 2022

IMPORTS
    OBJECT-TYPE, MODULE-IDENTITY                FROM SNMPv2-SMI
    DisplayString                               FROM SNMPv2-TC
    InterfaceIndex                              FROM IF-MIB
    MacAddress                                  FROM BRIDGE-MIB
    switch001                                    FROM CISCOSB-MIB;

rlBlth MODULE-IDENTITY
         LAST-UPDATED "202204300000Z"
                ORGANIZATION "Cisco Systems, Inc."
                CONTACT-INFO
                "Postal: 170 West Tasman Drive
                San Jose , CA 95134-1706
                USA


                Website:  Cisco Small Business Support Community <http://www.cisco.com/go/smallbizsupport>"


         DESCRIPTION
                "The private MIB module definition for CISCOSB Bluetooth."
         REVISION "202204300000Z"
         DESCRIPTION
                "Initial revision."
        ::= { switch001 246 }

rlBlthIfTable OBJECT-TYPE
    SYNTAX          SEQUENCE OF RlBlthIfTableEntry
    MAX-ACCESS      not-accessible
    STATUS          current
    DESCRIPTION     "The (conceptual) table listing the Bluetooth group Entry."
    ::= {rlBlth  1}

rlBlthIfTableEntry OBJECT-TYPE
    SYNTAX     RlBlthIfTableEntry
    MAX-ACCESS     not-accessible
    STATUS current
    DESCRIPTION "The (conceptual) table listing the Bluetooth entry."
    INDEX      { rlBlthIfIndex}
    ::= { rlBlthIfTable 1 }

RlBlthIfTableEntry::=SEQUENCE {
    rlBlthIfIndex                         InterfaceIndex,
    rlBlthPin                             DisplayString,
    rlBlthDeviceName                      DisplayString,
    rlBlthDongleMAC                       MacAddress,
    rlBlthDonglePresent                   INTEGER,
    rlBlthBus                             DisplayString,
    rlBlthState                           INTEGER,
    rlBlthPartnerName                     DisplayString
}

rlBlthIfIndex OBJECT-TYPE
    SYNTAX     InterfaceIndex
    MAX-ACCESS     read-only
    STATUS current
    DESCRIPTION
        "Key to Bluetooth if table"
    ::= { rlBlthIfTableEntry 1 }

rlBlthPin OBJECT-TYPE
    SYNTAX      DisplayString
    MAX-ACCESS     read-write
    STATUS current
    DESCRIPTION
        "Stores the Bluetooth PIN used by Bluetooth Adapter"
    ::= { rlBlthIfTableEntry 2 }

rlBlthDeviceName OBJECT-TYPE
    SYNTAX      DisplayString
    MAX-ACCESS     read-write
    STATUS current
    DESCRIPTION
        "Stores the device name used by Bluetooth Adapter"
    ::= { rlBlthIfTableEntry 3 }

rlBlthDongleMAC OBJECT-TYPE
    SYNTAX     MacAddress
    MAX-ACCESS read-write
    STATUS     current
    DESCRIPTION
           "Bluetooth Dongle MAC"
       ::= { rlBlthIfTableEntry 4 }

rlBlthDonglePresent OBJECT-TYPE
    SYNTAX      INTEGER{no(0), yes(1)}
    MAX-ACCESS     read-write
    STATUS current
    DESCRIPTION
        "Represents if Bluetooth Dongle is connected"
    ::= { rlBlthIfTableEntry 5 }

rlBlthBus OBJECT-TYPE
    SYNTAX      DisplayString
    MAX-ACCESS     read-write
    STATUS current
    DESCRIPTION
        "Stores the Bluetooth Bus type"
    ::= { rlBlthIfTableEntry 6 }

rlBlthState OBJECT-TYPE
    SYNTAX      INTEGER{notready(0), discoverable(1), connected(2), admindown(3)}
    MAX-ACCESS     read-write
    STATUS current
    DESCRIPTION
        "Stores the Bluetooth state"
    ::= { rlBlthIfTableEntry 7 }

rlBlthPartnerName OBJECT-TYPE
    SYNTAX      DisplayString
    MAX-ACCESS     read-write
    STATUS current
    DESCRIPTION
        "Bluetooth partner name"
    ::= { rlBlthIfTableEntry 8 }


END
