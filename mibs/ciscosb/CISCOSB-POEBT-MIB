CISCOSB-POEBT-MIB DEFINITIONS ::= BEGIN

IMPORTS
    DisplayString, TruthValue                               FROM SNMPv2-TC
    InterfaceIndexOrZero, InterfaceIndex                    FROM IF-MIB
    OBJECT-TYPE, MODULE-IDENTITY, Unsigned32, Counter32     FROM SNMPv2-SMI
    rlPethPsePortEntry                                      FROM CISCOSB-POE-MIB
    switch001                                                FROM CISCOSB-MIB;

rlPoeBt MODULE-IDENTITY
         LAST-UPDATED "202004100000Z"
                ORGANIZATION "Cisco Systems, Inc."
                CONTACT-INFO
                "Postal: 170 West Tasman Drive
                San Jose , CA 95134-1706
                USA


                Website:  Cisco Small Business Support Community <http://www.cisco.com/go/smallbizsupport>"

         DESCRIPTION
                "Add a new field in the PoE MIB to indicate Max power allocation allowed"
         REVISION "202004100000Z"
         DESCRIPTION
                "The private MIB module definition for Power Over Ethernet BT."
         REVISION "202004100000Z"
         DESCRIPTION
                "Initial revision."
        ::= { switch001 151 }


RlPoeBtClass ::= TEXTUAL-CONVENTION
    STATUS      current
    DESCRIPTION "PoE classes:
                "
    SYNTAX  INTEGER {
        noClass(1),
        class1(2),
        class2(3),
        class3(4),
        class4(5),
        class5(6),
        class6(7),
        class7(8),
        class8(9)
    }

rlPethPseBtPortTable OBJECT-TYPE
    SYNTAX SEQUENCE OF RlPethPseBtPortEntry
    MAX-ACCESS not-accessible
    STATUS     current
    DESCRIPTION
        " The table listing information for PoE 802.3BT ports."
    ::= {rlPoeBt 1 }

rlPethPseBtPortEntry  OBJECT-TYPE
    SYNTAX      RlPethPseBtPortEntry
    MAX-ACCESS  not-accessible
    STATUS      current
    DESCRIPTION
        " An entry in the rlPethPseBtPortTable.
        This configuration object augments the rlPethPsePortEntry."
    AUGMENTS { rlPethPsePortEntry }

    ::= {rlPethPseBtPortTable  1 }

RlPethPseBtPortEntry ::= SEQUENCE {
    rlPethPseBtPortAltAStatus               INTEGER,
    rlPethPseBtPortAltADetectionStatus      INTEGER,
    rlPethPseBtPortAltAMeasuredClass        RlPoeBtClass,
    rlPethPseBtPortAltAAssignedClass        RlPoeBtClass,
    rlPethPseBtPortAltAAllocPower           INTEGER,
    rlPethPseBtPortAltAInvalidSigCounter    Counter32,
    rlPethPseBtPortAltAPowerDeniedCounter   Counter32,
    rlPethPseBtPortAltAOverloadCounter      Counter32,
    rlPethPseBtPortAltAMPSAbsentCounter     Counter32,
    rlPethPseBtPortAltBStatus               INTEGER,
    rlPethPseBtPortAltBDetectionStatus      INTEGER,
    rlPethPseBtPortAltBMeasuredClass        RlPoeBtClass,
    rlPethPseBtPortAltBAssignedClass        RlPoeBtClass,
    rlPethPseBtPortAltBAllocPower           INTEGER,
    rlPethPseBtPortAltBInvalidSigCounter    Counter32,
    rlPethPseBtPortAltBPowerDeniedCounter   Counter32,
    rlPethPseBtPortAltBOverloadCounter      Counter32,
    rlPethPseBtPortAltBMPSAbsentCounter     Counter32,
    rlPethPseBtPortPowerClassMethod         INTEGER,
    rlPethPseBtPortAltAStatusDescription    DisplayString,
    rlPethPseBtPortAltBStatusDescription    DisplayString
}

rlPethPseBtPortAltAStatus OBJECT-TYPE
    SYNTAX      INTEGER (0..2147483647)
    MAX-ACCESS  read-only
    STATUS      current
    DESCRIPTION
        "This variable indicates on the hardware status of the primary ALT of rlPethPsePortIndex."
    ::= { rlPethPseBtPortEntry 1 }

rlPethPseBtPortAltADetectionStatus OBJECT-TYPE
    SYNTAX INTEGER   {
             disabled(1),
             searching(2),
             deliveringPower(3),
             fault(4)
    }
    MAX-ACCESS  read-only
    STATUS      current
    DESCRIPTION
       "This variable indicates on the detection status of the primary ALT of rlPethPsePortIndex."
    REFERENCE
      "IEEE Std 802.3af Section 30.9.1.1.5
       aPSEPowerDetectionStatus"
    ::= { rlPethPseBtPortEntry 2 }

rlPethPseBtPortAltAMeasuredClass OBJECT-TYPE
    SYNTAX  RlPoeBtClass
    MAX-ACCESS  read-only
    STATUS      current
    DESCRIPTION
        "This variable indicates the measured class of the PoE port"
    ::= { rlPethPseBtPortEntry 3 }

rlPethPseBtPortAltAAssignedClass OBJECT-TYPE
    SYNTAX  RlPoeBtClass
    MAX-ACCESS  read-only
    STATUS      current
    DESCRIPTION
        "This variable indicates the assigned class of the PoE port"
    ::= { rlPethPseBtPortEntry 4}

rlPethPseBtPortAltAAllocPower OBJECT-TYPE
    SYNTAX      INTEGER (0..2147483647)
    MAX-ACCESS  read-only
    STATUS      current
    DESCRIPTION
        "This variable indicates the power allocation per port in milli watts for Alt A."
    ::= { rlPethPseBtPortEntry 5 }

rlPethPseBtPortAltAInvalidSigCounter OBJECT-TYPE
    SYNTAX Counter32
    MAX-ACCESS read-only
    STATUS current
    DESCRIPTION
          "This counter is the same as pethPsePortInvalidSignatureCounter,
          on primary ALT. The counter is incremented when the PSE
          state diagram enters the state SIGNATURE_INVALID."
    REFERENCE
      "RFC3621 pethPsePortInvalidSignatureCounter"
    ::= { rlPethPseBtPortEntry 6 }

rlPethPseBtPortAltAPowerDeniedCounter OBJECT-TYPE
    SYNTAX Counter32
    MAX-ACCESS read-only
    STATUS current
    DESCRIPTION
          "This counter is the same as pethPsePortPowerDeniedCounter,
          on primary ALT. The counter is incremented when the PSE
          state diagram enters the state POWER_DENIED."
    REFERENCE
      "RFC3621 pethPsePortPowerDeniedCounter"
    ::= { rlPethPseBtPortEntry 7 }

rlPethPseBtPortAltAOverloadCounter OBJECT-TYPE
    SYNTAX Counter32
    MAX-ACCESS read-only
    STATUS current
    DESCRIPTION
          "This counter is the same as pethPsePortOverLoadCounter,
          on primary ALT. The counter is incremented when the PSE
          state diagram enters the state ERROR_DELAY_OVER."
    REFERENCE
      "RFC3621 pethPsePortOverLoadCounter"
    ::= { rlPethPseBtPortEntry 8 }

rlPethPseBtPortAltAMPSAbsentCounter OBJECT-TYPE
    SYNTAX Counter32
    MAX-ACCESS read-only
    STATUS current
    DESCRIPTION
          "This counter is the same as pethPsePortMPSAbsentCounter,
          on primary ALT. This counter is incremented when the PSE
          state diagram transitions directly from the state
          POWER_ON to the state IDLE due to tmpdo_timer_done
          being asserted."
    REFERENCE
      "RFC3621 pethPsePortMPSAbsentCounter"
    ::= { rlPethPseBtPortEntry 9 }

rlPethPseBtPortAltBStatus OBJECT-TYPE
    SYNTAX      INTEGER (0..2147483647)
    MAX-ACCESS  read-only
    STATUS      current
    DESCRIPTION
        "This variable indicates on the hardware status of the secondary ALT of rlPethPsePortIndex."
    ::= { rlPethPseBtPortEntry 10 }

rlPethPseBtPortAltBDetectionStatus OBJECT-TYPE
    SYNTAX INTEGER   {
             disabled(1),
             searching(2),
             deliveringPower(3),
             fault(4)
    }
    MAX-ACCESS  read-only
    STATUS      current
    DESCRIPTION
       "This variable indicates on the detection status of the secondary ALT of rlPethPsePortIndex."
    REFERENCE
      "IEEE Std 802.3af Section 30.9.1.1.5
       aPSEPowerDetectionStatus"
    ::= { rlPethPseBtPortEntry 11 }

rlPethPseBtPortAltBMeasuredClass OBJECT-TYPE
    SYNTAX  RlPoeBtClass
    MAX-ACCESS  read-only
    STATUS      current
    DESCRIPTION
        "This variable indicates the measured class of the PoE port"
    ::= { rlPethPseBtPortEntry 12 }

rlPethPseBtPortAltBAssignedClass OBJECT-TYPE
    SYNTAX  RlPoeBtClass
    MAX-ACCESS  read-only
    STATUS      current
    DESCRIPTION
        "This variable indicates the assigned class of the PoE port"
    ::= { rlPethPseBtPortEntry 13 }

rlPethPseBtPortAltBAllocPower OBJECT-TYPE
    SYNTAX      INTEGER (0..2147483647)
    MAX-ACCESS  read-only
    STATUS      current
    DESCRIPTION
        "This variable indicates the power allocation per port in milli watts for Alt B."
    ::= { rlPethPseBtPortEntry 14 }

rlPethPseBtPortAltBInvalidSigCounter OBJECT-TYPE
    SYNTAX Counter32
    MAX-ACCESS read-only
    STATUS current
    DESCRIPTION
          "This counter is the same as pethPsePortInvalidSignatureCounter,
          on Secondary ALT. The counter is incremented when the PSE
          state diagram enters the state SIGNATURE_INVALID."
    REFERENCE
      "RFC3621 pethPsePortInvalidSignatureCounter"
    ::= { rlPethPseBtPortEntry 15 }

rlPethPseBtPortAltBPowerDeniedCounter OBJECT-TYPE
    SYNTAX Counter32
    MAX-ACCESS read-only
    STATUS current
    DESCRIPTION
          "This counter is the same as pethPsePortPowerDeniedCounter,
          on Secondary ALT. The counter is incremented when the PSE
          state diagram enters the state POWER_DENIED."
    REFERENCE
      "RFC3621 pethPsePortPowerDeniedCounter"
    ::= { rlPethPseBtPortEntry 16 }

rlPethPseBtPortAltBOverloadCounter OBJECT-TYPE
    SYNTAX Counter32
    MAX-ACCESS read-only
    STATUS current
    DESCRIPTION
          "This counter is the same as pethPsePortOverLoadCounter,
          on Secondary ALT. The counter is incremented when the PSE
          state diagram enters the state ERROR_DELAY_OVER."
    REFERENCE
      "RFC3621 pethPsePortOverLoadCounter"
    ::= { rlPethPseBtPortEntry 17 }

rlPethPseBtPortAltBMPSAbsentCounter OBJECT-TYPE
    SYNTAX Counter32
    MAX-ACCESS read-only
    STATUS current
    DESCRIPTION
          "This counter is the same as pethPsePortMPSAbsentCounter,
          on Secondary ALT. This counter is incremented when the PSE
          state diagram transitions directly from the state
          POWER_ON to the state IDLE due to tmpdo_timer_done
          being asserted."
    REFERENCE
      "RFC3621 pethPsePortMPSAbsentCounter"
    ::= { rlPethPseBtPortEntry 18 }

rlPethPseBtPortPowerClassMethod OBJECT-TYPE
    SYNTAX  INTEGER {
        powerClassMethodRegular(1),
        powerClassMethodAutoClass(2)
    }
    MAX-ACCESS  read-only
    STATUS      current
    DESCRIPTION
        "This variable indicates the assigned class of the PoE port"
    ::= { rlPethPseBtPortEntry 19 }

rlPethPseBtPortAltAStatusDescription OBJECT-TYPE
    SYNTAX      DisplayString(SIZE(0..120))
    MAX-ACCESS  read-only
    STATUS      current
    DESCRIPTION
        "This variable indicates the description of the hardware status of rlPethPsePortIndex."
    ::= { rlPethPseBtPortEntry 20 }

rlPethPseBtPortAltBStatusDescription OBJECT-TYPE
    SYNTAX      DisplayString(SIZE(0..120))
    MAX-ACCESS  read-only
    STATUS      current
    DESCRIPTION
        "This variable indicates the description of the hardware status of rlPethPsePortIndex."
    ::= { rlPethPseBtPortEntry 21 }
END
