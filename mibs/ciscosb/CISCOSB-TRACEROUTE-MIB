CISCOSB-TRACEROUTE-MIB DEFINITIONS ::= BEGIN

-- Title: CISCOSB ROS
--                       Private Trace Route MIB
-- Version:              7.46
-- Date:                 15-Jan-2007

IMPORTS
    OBJECT-TYPE, MODULE-IDENTITY                            FROM SNMPv2-SMI
    switch001                                                FROM CISCOSB-MIB;

rlTraceRoute MODULE-IDENTITY
                LAST-UPDATED "200701020000Z"
                ORGANIZATION "Cisco Systems, Inc."
                CONTACT-INFO
                "Postal: 170 West Tasman Drive
                San Jose , CA 95134-1706
                USA


                Website:  Cisco Small Business Support Community <http://www.cisco.com/go/smallbizsupport>"

                DESCRIPTION
                      "This private MIB module defines TRACE ROUTE private MIBs."
                REVISION "200701020000Z"
                DESCRIPTION
                      "Initial revision."
        ::= { switch001 81 }

rlTraceRouteMibVersion OBJECT-TYPE
    SYNTAX  INTEGER
    MAX-ACCESS  read-only
    STATUS  current
    DESCRIPTION
        "MIB's version, the current version is 1."
    ::= { rlTraceRoute 1 }

rlTraceRouteWebLastTestName OBJECT-TYPE
    SYNTAX  INTEGER
    MAX-ACCESS  read-write
    STATUS  current
    DESCRIPTION
        "The last index of Traceroute WEB requests. Used to configure traceRouteCtlTestName by WEB user."
    ::= { rlTraceRoute 2 }

END
