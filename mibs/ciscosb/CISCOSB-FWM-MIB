CISCOSB-FWM-MIB DEFINITIONS ::= BEGIN

IMPORTS
    DisplayString, TruthValue                   FROM SNMPv2-TC
    OBJECT-TYPE, MODULE-IDENTITY, Unsigned32    FROM SNMPv2-SMI
    switch001                                    FROM CISCOSB-MIB;

rlFwm  MODULE-IDENTITY
                       LAST-UPDATED "200602120000Z"
                ORGANIZATION "Cisco Systems, Inc."
                CONTACT-INFO
                "Postal: 170 West Tasman Drive
                San Jose , CA 95134-1706
                USA


                Website:  Cisco Small Business Support Community <http://www.cisco.com/go/smallbizsupport>"

                       DESCRIPTION
                            "The private MIB module definition for firmware updates."
                       REVISION "200602120000Z"
                       DESCRIPTION
                            "Removed TRAP-TYPE from IMPORTS."
                       REVISION "200310180000Z"
                       DESCRIPTION
                            "Initial version of this MIB."
                       ::= { switch001 244 }

EntityType ::= TEXTUAL-CONVENTION
    STATUS current
    DESCRIPTION    "Entity type."
    SYNTAX INTEGER {
		not-relevant(0),
        cpld(1),
        fpga(2)
}

rlFwmTable OBJECT-TYPE
    SYNTAX      SEQUENCE OF RlFwmEntry
    MAX-ACCESS  not-accessible
    STATUS      current
    DESCRIPTION
        "This table shows the active and inactive entity(protocol) versions of each unit."
    ::= { rlFwm 1 }

rlFwmEntry OBJECT-TYPE
    SYNTAX      RlFwmEntry
    MAX-ACCESS  not-accessible
    STATUS      current
    DESCRIPTION
        "A entry of this table shows the active and inactive entity(protocol) versions of the device"
    INDEX  { rlFwmUnitIndex, rlFwmEntity, rlFwmIndex }
    ::= { rlFwmTable 1 }

RlFwmEntry ::= SEQUENCE {
    rlFwmUnitIndex                  INTEGER,
    rlFwmEntity                     EntityType,
    rlFwmIndex                      INTEGER,
    rlFwmVersionActive              DisplayString,
    rlFwmVersionInactive            DisplayString,
    rlFwmUpdateAvailable            TruthValue,
    rlFwmForceAutoUpdate            TruthValue
}

rlFwmUnitIndex OBJECT-TYPE
    SYNTAX      INTEGER
    MAX-ACCESS  not-accessible
    STATUS      current
    DESCRIPTION
        "The current stack unit position."
    ::= { rlFwmEntry 1 }

rlFwmEntity OBJECT-TYPE
    SYNTAX          EntityType
    MAX-ACCESS      not-accessible
    STATUS          current
    DESCRIPTION
        "Entity Type:
            not-relevant(0),
			cpld(1),
			fpga(2)
        "
    ::= {rlFwmEntry 2 }

rlFwmIndex OBJECT-TYPE
    SYNTAX      INTEGER
    MAX-ACCESS  not-accessible
    STATUS      current
    DESCRIPTION
        "The current index."
    ::= { rlFwmEntry 3 }

rlFwmVersionActive OBJECT-TYPE
    SYNTAX      DisplayString
    MAX-ACCESS  read-only
    STATUS      current
    DESCRIPTION
        "The current running version."
    ::= { rlFwmEntry 4 }

-- 0xFFFF symbolizes an invalid version ID

rlFwmVersionInactive OBJECT-TYPE
    SYNTAX      DisplayString
    MAX-ACCESS  read-only
    STATUS      current
    DESCRIPTION
        "The inactive version."
    ::= { rlFwmEntry 5 }

rlFwmUpdateAvailable OBJECT-TYPE
    SYNTAX      TruthValue
    MAX-ACCESS  read-only
    STATUS      current
    DESCRIPTION
        "The inactive version."
    ::= { rlFwmEntry 6 }

rlFwmForceAutoUpdate OBJECT-TYPE
    SYNTAX      TruthValue
    MAX-ACCESS  read-write
    STATUS      current
    DESCRIPTION
        "Forces automatic firmware update on next restart, regardless of update mode. Has MTSC/YANG parameter also."
    ::= { rlFwmEntry 7 }

rlFwmVersionUpdate OBJECT-TYPE
SYNTAX  EntityType
MAX-ACCESS  read-write
STATUS  current
DESCRIPTION
	"Update version (action MIB)"
::= {rlFwm 2 }

END
