-- *****************************************************************
-- Cisco VTP MIB
--
-- February, 1997 Chris Young
--
-- Copyright (c) 1996-1998, 1999, 2000 by cisco Systems, Inc.
-- All rights reserved.
-- *****************************************************************
--

-- VTP MIB
-- CMS# ENG-6198

CISCO-VTP-MIB DEFINITIONS ::= BEGIN

IMPORTS
    MODULE-IDENTITY, OBJECT-TYPE, NOTIFICATION-TYPE,
    Counter32, IpAddress, Gauge32
        FROM SNMPv2-SMI
    TEXTUAL-CONVENTION,
    RowStatus, DisplayString, DateAndTime, TruthValue, TestAndIncr
        FROM SNMPv2-TC
    InterfaceIndex, ifIndex
        FROM IF-MIB
    ciscoMgmt
        FROM CISCO-SMI
--    MODULE-COMPLIANCE, OBJECT-GROUP, NOTIFICATION-GROUP
    MODULE-COMPLIANCE, OBJECT-GROUP
        FROM SNMPv2-CONF;


ciscoVtpMIB MODULE-IDENTITY
    LAST-UPDATED "9901051130Z"
	ORGANIZATION "Cisco Systems, Inc."

	CONTACT-INFO
	"Postal: 170 West Tasman Drive
	San Jose , CA 95134-1706
	USA


	Website:  Cisco Small Business Support Community <http://www.cisco.com/go/smallbizsupport>"

    DESCRIPTION
            " Added import of NOTIFICATION-GROUP"
    REVISION
                "9902251130Z"
    DESCRIPTION
            " Added support for encapsulation type notApplicable"
    REVISION
                "9901051130Z"
    DESCRIPTION
            " Added support for encapsulation type negotiation"
    REVISION
                "9805191130Z"
    DESCRIPTION
            " Added Backup CRF object"
    REVISION
                "9708081138Z"
    DESCRIPTION
            " Added ARE and STE hop counts."
    REVISION
                "9705091130Z"
    DESCRIPTION
            " Added support for turning on VTP for Trunk cards."
    REVISION
                "9702241115Z"
    DESCRIPTION
            "The MIB module for devices implementing VTP."
    REVISION    "9701271730Z"
    DESCRIPTION
            "Added support for version 2 features."
    REVISION    "9609161230Z"
    DESCRIPTION
            "Updated the Token-Ring support."
    REVISION    "9607171230Z"
    DESCRIPTION
            "Updated to include objects in support of VTP pruning."
    REVISION    "9601181820Z"
    DESCRIPTION
            "Initial version of this MIB module."
    ::= { ciscoMgmt 46 }


vtpMIBObjects OBJECT IDENTIFIER ::= { ciscoVtpMIB 1 }


-- Textual Conventions

VlanIndex ::= TEXTUAL-CONVENTION
    STATUS       current
    DESCRIPTION
            "The VLAN-id of a VLAN on ISL trunks.

             VLANs above 1000 are reserved for default VLANs and
             future use. Modification of default parameters is
             allowed. Creation or deletion of VLANs above 1000 is not
             allowed."
    SYNTAX     INTEGER (0..1023)


ManagementDomainIndex ::= TEXTUAL-CONVENTION
    STATUS       current
    DESCRIPTION
            "An arbitrary integer-value to uniquely identify a
            management domain on the local system."
    SYNTAX     INTEGER (1..255)

OwnerString ::= TEXTUAL-CONVENTION
    STATUS       current
    DESCRIPTION
            "This data type is used to model an administratively
            assigned name of the owner of a resource.  This information
            is taken from the NVT ASCII character set.  It is suggested
            that this name contain one or more of the following: IP
            address, management station name, network manager's name,
            location, or phone number.  In some cases the agent itself
            will be the owner of an entry.  In these cases, this string
            shall be set to a string starting with 'monitor'.

            This definition is identical to that contained in RFC 1271."
    SYNTAX     OCTET STRING


VlanType ::= TEXTUAL-CONVENTION
    STATUS       current
    DESCRIPTION
            "The type of a VLAN.

            Note that the 'ethernet' type, is used for any ethernet or
            802.3 VLAN, including an ATM Ethernet ELAN; and the
            'tokenRing' ('trCrf') type is used for each VLAN
            representing a single logical 802.5 ring including an ATM
            Token-Ring ELAN.

            The 'trCrf' type is used for token ring VLANs made up of
            (at most) one transparently bridged LAN segment.

            The 'trBrf' type is used for VLANs which represent the
            scope of many 'trCrf' VLANs all connected together via
            source route bridging.  The token ring 'trBrf' can be said
            to represent the bridged broadcast domain."
    SYNTAX     INTEGER {
                   ethernet(1),
                   fddi(2),
                   tokenRing(3), -- also known as trCrf
                   fddiNet(4),
                   trNet(5), -- also known as trBrf
                   deprecated(6)
               }

--
-- VTP status
--

vtpStatus   OBJECT IDENTIFIER ::= { vtpMIBObjects 1 }


vtpVersion OBJECT-TYPE
    SYNTAX     INTEGER { one(1), two(2) }
    MAX-ACCESS read-only
    STATUS     current
    DESCRIPTION
            "The version of VTP in use on the local system.  A device
            will report its version capability and not any particular
            version in use on the device."
    ::= { vtpStatus 1 }

vtpMaxVlanStorage OBJECT-TYPE
    SYNTAX     INTEGER (-1..1023)
    MAX-ACCESS read-only
    STATUS     current
    DESCRIPTION
            "An estimate of the maximum number of VLANs about which the
            local system can recover complete VTP information after a
            reboot.  If the number of defined VLANs is greater than this
            value, then the system can not act as a VTP Server. For a
            device which has no means to calculate the estimated number,
            this value is -1."
    ::= { vtpStatus 2 }

vtpNotificationsEnabled OBJECT-TYPE
    SYNTAX     TruthValue
    MAX-ACCESS read-write
    STATUS     current
    DESCRIPTION
            "An indication of whether the notifications/traps defined by
            the vtpConfigNotificationsGroup are enabled."
    ::= { vtpStatus 3 }

--
-- VTP Management Domains
--

vlanManagementDomains   OBJECT IDENTIFIER ::= { vtpMIBObjects 2 }

managementDomainTable OBJECT-TYPE
    SYNTAX     SEQUENCE OF ManagementDomainEntry
    MAX-ACCESS not-accessible
    STATUS     current
    DESCRIPTION
            "The table containing information on the management domains
            in which the local system is participating.  Devices which
            support only one management domain will support just one row
            in this table, and will not let it be deleted nor let other
            rows be created.  Devices which support multiple management
            domains will allow rows to be created and deleted, but will
            not allow the last row to be deleted."
    ::= { vlanManagementDomains 1 }

managementDomainEntry OBJECT-TYPE
    SYNTAX     ManagementDomainEntry
    MAX-ACCESS not-accessible
    STATUS     current
    DESCRIPTION
            "Information about the status of one management domain."
    INDEX      { managementDomainIndex }
    ::= { managementDomainTable 1 }

ManagementDomainEntry ::= SEQUENCE {
    managementDomainIndex            ManagementDomainIndex,
    managementDomainName             DisplayString,
    managementDomainLocalMode        INTEGER,
    managementDomainConfigRevNumber  Gauge32,
    managementDomainLastUpdater      IpAddress,
    managementDomainLastChange       DateAndTime,
    managementDomainRowStatus        RowStatus,
    managementDomainTftpServer       IpAddress,
    managementDomainTftpPathname     DisplayString,
    managementDomainPruningState     INTEGER,
    managementDomainVersionInUse     INTEGER
}

managementDomainIndex OBJECT-TYPE
    SYNTAX     ManagementDomainIndex
    MAX-ACCESS not-accessible
    STATUS     current
    DESCRIPTION
            "An arbitrary value to uniquely identify the management
            domain on the local system."
    ::= { managementDomainEntry 1 }

managementDomainName OBJECT-TYPE
    SYNTAX     DisplayString (SIZE (0..32))
    MAX-ACCESS read-create
    STATUS     current
    DESCRIPTION
            "The management name of a domain in which the local system
            is participating.  The zero-length name corresponds to the
            'no management-domain' state which is the initial value at
            installation-time if not configured otherwise.  Note that
            the zero-length name does not correspond to an operational
            management domain, and a device does not send VTP
            advertisements while in the 'no management-domain' state.  A
            device leaves the 'no management-domain' state when it
            obtains a management-domain name, either through
            configuration or through inheriting the management-domain
            name from a received VTP advertisement.

            When the value of an existing instance of this object is
            modified by network management, the local system should re-
            initialize its VLAN information (for the given management
            domain) as if it had just been configured with a management
            domain name at installation time."
    ::= { managementDomainEntry 2 }

managementDomainLocalMode OBJECT-TYPE
    SYNTAX     INTEGER { client(1), server(2), transparent(3) }
    MAX-ACCESS read-create
    STATUS     current
    DESCRIPTION
            "An indication of whether the local system is acting as a
            VTP Client or as a VTP Server in this management domain.
            The value 'transparent' is a read-only indication that a
            device is not supporting VTP for this VTP management domain,
            e.g., because the amount of VLAN information is too large
            for it to hold in DRAM."
    ::= { managementDomainEntry 3 }

managementDomainConfigRevNumber OBJECT-TYPE
    SYNTAX     Gauge32
    MAX-ACCESS read-only
    STATUS     current
    DESCRIPTION
            "The current Configuration Revision Number as known by the
            local device for this management domain.  This value is
            updated (if necessary) whenever a VTP advertisement is
            received or generated.  When in the 'no management-domain'
            state, this value is 0."
    ::= { managementDomainEntry 4 }

managementDomainLastUpdater OBJECT-TYPE
    SYNTAX     IpAddress
    MAX-ACCESS read-only
    STATUS     current
    DESCRIPTION
            "The IP-address (or one of them) of the VTP Server which
            last updated the Configuration Revision Number, as indicated
            in the most recently received VTP advertisement for this
            management domain.  Before an advertisement has been
            received, this value is 0.0.0.0."
    ::= { managementDomainEntry 5 }

managementDomainLastChange OBJECT-TYPE
    SYNTAX     DateAndTime
    MAX-ACCESS read-only
    STATUS     current
    DESCRIPTION
            "The time at which the Configuration Revision Number was
            (last) increased to its current value, as indicated in the
            most recently received VTP advertisement for this management
            domain.

            The value 0x0000010100000000 indicates that the device which
            last increased the Configuration Revision Number had no idea
            of the date/time, or that no advertisement has been
            received."
    ::= { managementDomainEntry 6 }

managementDomainRowStatus OBJECT-TYPE
    SYNTAX     RowStatus
    MAX-ACCESS read-create
    STATUS     current
    DESCRIPTION
            "The status of this conceptual row."
    ::= { managementDomainEntry 7 }

managementDomainTftpServer OBJECT-TYPE
    SYNTAX     IpAddress
    MAX-ACCESS read-create
    STATUS     current
    DESCRIPTION
            "The IP address of a TFTP Server in/from which VTP VLAN
            information for this management domain is to be
            stored/retrieved.  If the information is being locally
            stored in NVRAM, this object should take the value 0.0.0.0."
    ::= { managementDomainEntry 8 }

managementDomainTftpPathname OBJECT-TYPE
    SYNTAX     DisplayString
    MAX-ACCESS read-create
    STATUS     current
    DESCRIPTION
            "The complete pathname of the file at the TFTP Server
            identified by the value of managementDomainTftpServer
            in/from which VTP VLAN information for this management
            domain is to be stored/retrieved.  If the value of
            corresponding instance of managementDomainTftpServer is
            0.0.0.0, the value of this object is ignored."
    ::= { managementDomainEntry 9 }

managementDomainPruningState  OBJECT-TYPE
    SYNTAX     INTEGER { enabled(1), disabled(2) }
    MAX-ACCESS read-create
    STATUS     current
    DESCRIPTION
            "An indication of whether VTP pruning is enabled or disabled
            in this managament domain.  This value can only be modified
            by local/network management when the value of the
            corresponding instance of managementDomainLocalMode is
            'server'."
    ::= { managementDomainEntry 10 }

managementDomainVersionInUse OBJECT-TYPE
    SYNTAX     INTEGER { version1 (1), version2 (2) }
    MAX-ACCESS read-create
    STATUS     current
    DESCRIPTION
            "The current version of the VTP that is in use by the
            designated management domain.  This value can only be
            modified by local/network managment when the value of the
            corresponding instance of managementDomainLocalMode is
            'server'."
    ::= { managementDomainEntry 11 }

--
-- VLAN information
--

vlanInfo   OBJECT IDENTIFIER ::= { vtpMIBObjects 3 }


-- Global information on current VLANs
--
-- This information is maintained by VTP Clients and VTP Servers

vtpVlanTable OBJECT-TYPE
    SYNTAX     SEQUENCE OF VtpVlanEntry
    MAX-ACCESS not-accessible
    STATUS     current
    DESCRIPTION
            "This table contains information on the VLANs which
            currently exist.  The creation, deletion or modification of
            entries occurs through: a) the receipt of VTP messages in
            VTP Clients and in VTP Servers, or, b) in VTP Servers (or in
            VTP transparent mode), through management operations acting
            upon entries in the vtpVlanEditTable and then issuing an
            'apply' command via the vtpVlanEditOperation object."
    ::= { vlanInfo 1 }

vtpVlanEntry OBJECT-TYPE
    SYNTAX     VtpVlanEntry
    MAX-ACCESS not-accessible
    STATUS     current
    DESCRIPTION
            "Information about one current VLAN.  The
            managementDomainIndex value in the INDEX clause indicates
            which management domain the VLAN is in."
    INDEX      { managementDomainIndex, vtpVlanIndex }
    ::= { vtpVlanTable 1 }

VtpVlanEntry ::= SEQUENCE {
    vtpVlanIndex               VlanIndex,
    vtpVlanState               INTEGER,
    vtpVlanType                VlanType,
    vtpVlanName                DisplayString,
    vtpVlanMtu                 INTEGER,
    vtpVlanDot10Said           OCTET STRING,
    vtpVlanRingNumber          INTEGER,
    vtpVlanBridgeNumber        INTEGER,
    vtpVlanStpType             INTEGER,
    vtpVlanParentVlan          VlanIndex,
    vtpVlanTranslationalVlan1  VlanIndex,
    vtpVlanTranslationalVlan2  VlanIndex,
    vtpVlanBridgeType          INTEGER,
    vtpVlanAreHopCount         INTEGER,
    vtpVlanSteHopCount         INTEGER,
    vtpVlanIsCRFBackup         TruthValue
}

vtpVlanIndex OBJECT-TYPE
    SYNTAX     VlanIndex
    MAX-ACCESS accessible-for-notify
    STATUS     current
    DESCRIPTION
            "The VLAN-id of this VLAN on ISL trunks."
    ::= { vtpVlanEntry 1 }

vtpVlanState  OBJECT-TYPE
    SYNTAX     INTEGER { operational(1),
                         suspended(2),
                         mtuTooBigForDevice(3),
                         mtuTooBigForTrunk(4) }
    MAX-ACCESS read-only
    STATUS     current
    DESCRIPTION
            "The state of this VLAN.

            The state 'mtuTooBigForDevice' indicates that this device
            cannot participate in this VLAN because the VLAN's MTU is
            larger than the device can support.

            The state 'mtuTooBigForTrunk' indicates that while this
            VLAN's MTU is supported by this device, it is too large for
            one or more of the device's trunk ports."
    ::= { vtpVlanEntry 2 }

vtpVlanType OBJECT-TYPE
    SYNTAX     VlanType
    MAX-ACCESS read-only
    STATUS     current
    DESCRIPTION
            "The type of this VLAN."
    ::= { vtpVlanEntry 3 }

vtpVlanName OBJECT-TYPE
    SYNTAX     DisplayString (SIZE (1..32))
    MAX-ACCESS read-only
    STATUS     current
    DESCRIPTION
            "The name of this VLAN.  This name is used as the ELAN-name
            for an ATM LAN-Emulation segment of this VLAN."
    ::= { vtpVlanEntry 4 }

vtpVlanMtu OBJECT-TYPE
    SYNTAX     INTEGER (1500..18190)
    MAX-ACCESS read-only
    STATUS     current
    DESCRIPTION
            "The MTU size on this VLAN, defined as the size of largest
            MAC-layer (information field portion of the) data frame
            which can be transmitted on the VLAN."
    ::= { vtpVlanEntry 5 }

vtpVlanDot10Said OBJECT-TYPE
    SYNTAX     OCTET STRING (SIZE (4))
    MAX-ACCESS read-only
    STATUS     current
    DESCRIPTION
            "The value of the 802.10 SAID field for this VLAN."
    ::= { vtpVlanEntry 6 }

vtpVlanRingNumber OBJECT-TYPE
    SYNTAX     INTEGER (0..4095)
    MAX-ACCESS read-only
    STATUS     current
    DESCRIPTION
            "The ring number of this VLAN.  This object is only
            instantiated when the value of the corresponding instance of
            vtpVlanType has a value of 'fddi' or 'tokenRing' and Source
            Routing (SRB) is configured for use on this VLAN."
    ::= { vtpVlanEntry 7 }

vtpVlanBridgeNumber OBJECT-TYPE
    SYNTAX     INTEGER (0..15)
    MAX-ACCESS read-only
    STATUS     current
    DESCRIPTION
            "The bridge number of the VTP-capable switches for this
            VLAN.  This object is only instantiated for VLANs that are
            involved with emulating token ring segments."
    ::= { vtpVlanEntry 8 }


vtpVlanStpType OBJECT-TYPE
     SYNTAX     INTEGER { ieee(1), ibm(2), hybrid(3) }
     MAX-ACCESS read-only
     STATUS     current
     DESCRIPTION
             " The type of the Spanning Tree Protocol (STP) running on
             this VLAN.  This object is only instanciated when the
             value of the corresponding instance of vtpVlanType has a
             value of 'fddiNet' or 'trNet'.

             The value returned by this object depends upon the value
             of the corresponding instance of vtpVlanEditStpType.

             - 'ieee' indicates IEEE STP is running exclusively.

             - 'ibm' indicates IBM STP is running exclusively.

             - 'hybrid' indicates a STP that allows a combination of
               IEEE and IBM is running.

             The 'hybrid' STP type results from tokenRing/fddi VLANs
             that are children of this trNet/fddiNet parent VLAN being
             configured in a combination of SRT and SRB
             vtpVlanBridgeTypes while the instance of
             vtpVlanEditStpType that corresponds to this object is set
             to 'auto'."
     ::= { vtpVlanEntry 9 }

vtpVlanParentVlan  OBJECT-TYPE
    SYNTAX     VlanIndex
    MAX-ACCESS read-only
    STATUS     current
    DESCRIPTION
            "The parent VLAN for this VLAN.  This object is only
            instantiated when the value of the corresponding instance of
            vtpVlanType has a value of 'fddi' or 'tokenRing' and Source
            Routing (SRB) is configured for use on this VLAN.  The
            parent VLAN must have a vtpVlanType value of fddiNet(4) or
            trNet(5), respectively."
    ::= { vtpVlanEntry 10 }

vtpVlanTranslationalVlan1  OBJECT-TYPE
    SYNTAX     VlanIndex
    MAX-ACCESS read-only
    STATUS     current
    DESCRIPTION
            "A VLAN to which this VLAN is being translational-bridged.
            If this value and the corresponding instance of
            vtpVlanTranslationalVlan2 are both zero, then this VLAN is
            not being translational-bridged."
    ::= { vtpVlanEntry 11 }

vtpVlanTranslationalVlan2  OBJECT-TYPE
    SYNTAX     VlanIndex
    MAX-ACCESS read-only
    STATUS     current
    DESCRIPTION
            "Another VLAN, i.e., other than that indicated by
            vtpVlanTranslationalVlan1, to which this VLAN is being
            translational-bridged.  If this value and the corresponding
            instance of vtpVlanTranslationalVlan1 are both zero, then
            this VLAN is not being translational-bridged."
    ::= { vtpVlanEntry 12 }

vtpVlanBridgeType OBJECT-TYPE
    SYNTAX     INTEGER { srt(1), srb(2) }
    MAX-ACCESS read-only
    STATUS     current
    DESCRIPTION
            "The type of the bridging mode in use on this VLAN.  This
            object is only instantiated when the value of the
            corresponding instance of vtpVlanType has a value of fddi(2)
            or tokenRing(3)."
    ::= { vtpVlanEntry 13 }

vtpVlanAreHopCount OBJECT-TYPE
    SYNTAX     INTEGER (1..13)
    MAX-ACCESS read-only
    STATUS     current
    DESCRIPTION
            "The maximum number of bridge hops allowed in
            All Routes Explorer frames on this VLAN.  This
            object is only instantiated when the value of the
            corresponding instance of vtpVlanType has a value of fddi(2)
            or tokenRing(3)."
    ::= { vtpVlanEntry 14 }

vtpVlanSteHopCount OBJECT-TYPE
    SYNTAX     INTEGER (1..13)
    MAX-ACCESS read-only
    STATUS     current
    DESCRIPTION
            "The maximum number of bridge hops allowed in
            Spanning Tree Explorer frames on this VLAN.  This
            object is only instantiated when the value of the
            corresponding instance of vtpVlanType has a value of fddi(2)
            or tokenRing(3)."
    ::= { vtpVlanEntry 15 }

vtpVlanIsCRFBackup OBJECT-TYPE
    SYNTAX     TruthValue
    MAX-ACCESS read-only
    STATUS     current
    DESCRIPTION
            " True if this VLAN is of type trCrf and also is acting as
            a backup trCrf for the ISL distributed BRF"
    ::= { vtpVlanEntry 16 }


-- Modification of Global VLAN Information
--
-- To change the global information on current VLANs, including
-- creating, modifying or deleting them,
--   . the current VLAN information is copied to the "Edit buffer",
--   . the information in the Edit buffer is modified as appropriate,
--   . an 'apply' is invoked to attempt to instanciate the modified
--     contents of the Edit Buffer as the new global VLAN information.
--
-- Only one manager can edit the Edit Buffer at a time.  So, a
-- request to copy the current VLAN information into the Edit Buffer
-- must fail if the Edit Buffer is already in use (i.e., is not empty).
-- Thus, concurrent attempts by multiple managers to gain use of the
-- Edit Buffer are resolved according to whichever of them succeeds
-- in performing a successful copy.  An OwnerString object provides
-- information on which manager currently has access.
--
-- Ownership of the Edit Buffer terminates when a NMS explicitly
-- releases it, or when a deadman-timer expires.  The deadman-timer
-- has a fixed expiry interval of 5 minutes.  The deadman-timer is
-- automatically started on a successful copy operation.  The
-- restartTimer operation allows an NMS to restart the deadman-timer
-- if it wishes to retain ownership of the Edit Buffer for longer
-- than 5 minutes.  The deadman-timer ceases when the apply operation
-- is invoked, and is restarted when the apply operation terminates.
-- Restarting the deadman-timer after termination of the apply
-- operation allows the results of the apply operation to be retained
-- until the requesting manager has retrieved them, but for only a
-- limited amount of time.

vlanEdit   OBJECT IDENTIFIER ::= { vtpMIBObjects 4 }

vtpEditControlTable OBJECT-TYPE
    SYNTAX     SEQUENCE OF VtpEditControlEntry
    MAX-ACCESS not-accessible
    STATUS     current
    DESCRIPTION
            "This table provides the means to control the editing of the
            VLANs for a particular management domain.  Each and every
            entry in this table augments its corresponding entry in the
            managementDomainTable; thus, an entry in this table is
            created/deleted only as a by-product of creating/deleting an
            entry in the managementDomainTable."
    ::= { vlanEdit 1 }

vtpEditControlEntry OBJECT-TYPE
    SYNTAX     VtpEditControlEntry
    MAX-ACCESS not-accessible
    STATUS     current
    DESCRIPTION
            "Control information for editing the VLANs in one management
            domain."
    AUGMENTS  { managementDomainEntry }
    ::= { vtpEditControlTable 1 }

VtpEditControlEntry ::= SEQUENCE {
    vtpVlanEditOperation        INTEGER,
    vtpVlanApplyStatus          INTEGER,
    vtpVlanEditBufferOwner      OwnerString,
    vtpVlanEditConfigRevNumber  Gauge32
}

vtpVlanEditOperation OBJECT-TYPE
    SYNTAX     INTEGER { none(1),
                         copy(2),
                         apply(3),
                         release(4),
                         restartTimer(5)
                       }
    MAX-ACCESS read-create
    STATUS     current
    DESCRIPTION
            "This object always has the value 'none' when read.  When
            written, each value causes the appropriate action:

             'copy' - causes the creation of rows in the
            vtpVlanEditTable exactly corresponding to the current global
            VLAN information for this management domain.  If the Edit
            Buffer (for this management domain) is not currently empty,
            a copy operation fails.  A successful copy operation starts
            the deadman-timer.

             'apply' - first performs a consistent check on the the
            modified information contained in the Edit Buffer, and if
            consistent, then tries to instanciate the modified
            information as the new global VLAN information.  Note that
            an empty Edit Buffer (for the management domain) would
            always result in an inconsistency since the default VLANs
            are required to be present.

             'release' - flushes the Edit Buffer (for this management
            domain), clears the Owner information, and aborts the
            deadman-timer.  A release is generated automatically if the
            deadman-timer ever expires.

             'restartTimer' - restarts the deadman-timer.

             'none' - no operation is performed."
    ::= { vtpEditControlEntry 1 }

vtpVlanApplyStatus OBJECT-TYPE
    SYNTAX     INTEGER { inProgress(1),
                         succeeded(2),
                         configNumberError(3),
                         inconsistentEdit(4),
                         tooBig(5),
                         localNVStoreFail(6),
                         remoteNVStoreFail(7),
                         editBufferEmpty(8),
                         someOtherError(9)
                       }
    MAX-ACCESS read-only
    STATUS     current
    DESCRIPTION
            "The current status of an 'apply' operation to instanciate
            the Edit Buffer as the new global VLAN information (for this
            management domain).  If no apply is currently active, the
            status represented is that of the most recently completed
            apply.  The possible values are:

               inProgress - 'apply' operation in progress;

               succeeded - the 'apply' was successful (this value is
                      also used when no apply has been invoked since the
                      last time the local system restarted);

               configNumberError - the apply failed because the value of
                      vtpVlanEditConfigRevNumber was less or equal to
                      the value of current value of vtpConfigRevNumber;

               inconsistentEdit - the apply failed because the modified
                      information was not self-consistent;

               tooBig - the apply failed because the modified
                      information was too large to fit in this VTP
                      Server's non-volatile storage location;

               localNVStoreFail - the apply failed in trying to store
                      the new information in a local non-volatile
                      storage location;

               remoteNVStoreFail - the apply failed in trying to store
                      the new information in a remote non-volatile
                      storage location;

               editBufferEmpty - the apply failed because the Edit
                      Buffer was empty (for this management domain).

               someOtherError - the apply failed for some other reason
                      (e.g., insufficient memory)."
    ::= { vtpEditControlEntry 2 }

vtpVlanEditBufferOwner OBJECT-TYPE
    SYNTAX     OwnerString
    MAX-ACCESS read-create
    STATUS     current
    DESCRIPTION
            "The management station which is currently using the Edit
            Buffer for this management domain.  When the Edit Buffer for
            a management domain is not currently in use, the value of
            this object is the zero-length string.  Note that it is also
            the zero-length string if a manager fails to set this object
            when invoking a copy operation."
    ::= { vtpEditControlEntry 3 }

vtpVlanEditConfigRevNumber OBJECT-TYPE
    SYNTAX     Gauge32
    MAX-ACCESS read-create
    STATUS     current
    DESCRIPTION
            "The Configuration Revision Number to be used for the next
            apply operation.  This value is initialized (by the agent)
            on a copy operation to be one greater than the value of
            vtpConfigRevNumber.  On an apply, if the number is less or
            equal to the value of vtpConfigRevNumber, then the apply
            fails.  The value can be modified (increased) by network
            management before an apply to ensure than an apply does not
            fail for this reason.

            This object is used to allow management control over whether
            a configuration revision received via a VTP advertisement
            after a copy operation but before the succeeding apply
            operation is lost by being overwritten by the (local) edit
            operation.  By default, the apply operation will fail in
            this situation.  By increasing this object's value after the
            copy but before the apply, management can control whether
            the apply is to succeed (with the update via VTP
            advertisement being lost)."
    ::= { vtpEditControlEntry 4 }


vtpVlanEditTable OBJECT-TYPE
    SYNTAX     SEQUENCE OF VtpVlanEditEntry
    MAX-ACCESS not-accessible
    STATUS     current
    DESCRIPTION
            "The table which contains the information in the Edit
            Buffers, one Edit Buffer per management domain.  The
            information for a particular management domain is
            initialized, by a 'copy' operation, to be the current global
            VLAN information for that management domain.  After
            initialization, editing can be performed to add VLANs,
            delete VLANs, or modify their global parameters.  The
            information as modified through editing is local to this
            Edit Buffer.  An apply operation using the
            vtpVlanEditOperation object is necessary to instanciate the
            modified information as the new global VLAN information for
            that management domain.

            To use the Edit Buffer, a manager acts as follows:

            1. ensures the Edit Buffer for a management domain is empty,
            i.e., there are no rows in this table for this management
            domain.

            2. issues a SNMP set operation which sets
            vtpVlanEditOperation to 'copy', and vtpVlanEditBufferOwner
            to its own identifier (e.g., its own IP address).

            3. if this set operation is successful, proceeds to edit the
            information in the vtpVlanEditTable.

            4. if and when the edited information is to be instantiated,
            issues a SNMP set operation which sets vtpVlanEditOperation
            to 'apply'.

            5. issues retrieval requests to obtain the value of
            vtpVlanApplyStatus, until the result of the apply is
            determined.

            6. releases the Edit Buffer by issuing a SNMP set operation
            which sets vtpVlanEditOperation to 'release'.

            Note that the information contained in this table is not
            saved across agent reboots."
    ::= { vlanEdit 2 }

vtpVlanEditEntry OBJECT-TYPE
    SYNTAX     VtpVlanEditEntry
    MAX-ACCESS not-accessible
    STATUS     current
    DESCRIPTION
            "Information about one VLAN in the Edit Buffer for a
            particular management domain."
    INDEX      { managementDomainIndex, vtpVlanEditIndex }
    ::= { vtpVlanEditTable 1 }

VtpVlanEditEntry ::= SEQUENCE {
    vtpVlanEditIndex               VlanIndex,
    vtpVlanEditState               INTEGER,
    vtpVlanEditType                VlanType,
    vtpVlanEditName                DisplayString,
    vtpVlanEditMtu                 INTEGER,
    vtpVlanEditDot10Said           OCTET STRING,
    vtpVlanEditRingNumber          INTEGER,
    vtpVlanEditBridgeNumber        INTEGER,
    vtpVlanEditStpType             INTEGER,
    vtpVlanEditParentVlan          VlanIndex,
    vtpVlanEditRowStatus           RowStatus,
    vtpVlanEditTranslationalVlan1  VlanIndex,
    vtpVlanEditTranslationalVlan2  VlanIndex,
    vtpVlanEditBridgeType          INTEGER,
    vtpVlanEditAreHopCount         INTEGER,
    vtpVlanEditSteHopCount         INTEGER,
    vtpVlanEditIsCRFBackup         TruthValue
}

vtpVlanEditIndex OBJECT-TYPE
    SYNTAX     VlanIndex
    MAX-ACCESS not-accessible
    STATUS     current
    DESCRIPTION
            "The VLAN-id which this VLAN would have on ISL trunks."
    ::= { vtpVlanEditEntry 1 }

vtpVlanEditState  OBJECT-TYPE
    SYNTAX     INTEGER {
                   operational(1),
                   suspended(2)
               }
    MAX-ACCESS read-create
    STATUS     current
    DESCRIPTION
            "The state which this VLAN would have."
    DEFVAL     { operational }
    ::= { vtpVlanEditEntry 2 }

vtpVlanEditType OBJECT-TYPE
    SYNTAX     VlanType
    MAX-ACCESS read-create
    STATUS     current
    DESCRIPTION
            "The type which this VLAN would have."
    DEFVAL     { ethernet }
    ::= { vtpVlanEditEntry 3 }

vtpVlanEditName OBJECT-TYPE
    SYNTAX     DisplayString (SIZE (1..32))
    MAX-ACCESS read-create
    STATUS     current
    DESCRIPTION
            "The name which this VLAN would have.  This name would be
            used as the ELAN-name for an ATM LAN-Emulation segment of
            this VLAN."
    ::= { vtpVlanEditEntry 4 }

vtpVlanEditMtu OBJECT-TYPE
    SYNTAX     INTEGER (1500..18190)
    MAX-ACCESS read-create
    STATUS     current
    DESCRIPTION
            "The MTU size which this VLAN would have, defined as the
            size of largest MAC-layer (information field portion of the)
            data frame which can be transmitted on the VLAN."
    DEFVAL     { 1500 }
    ::= { vtpVlanEditEntry 5 }

vtpVlanEditDot10Said OBJECT-TYPE
    SYNTAX     OCTET STRING (SIZE (4))
    MAX-ACCESS read-create
    STATUS     current
    DESCRIPTION
            "The value of the 802.10 SAID field which would be used for
            this VLAN."
    ::= { vtpVlanEditEntry 6 }

vtpVlanEditRingNumber OBJECT-TYPE
    SYNTAX     INTEGER (0..4095)
    MAX-ACCESS read-create
    STATUS     current
    DESCRIPTION
            "The ring number which would be used for this VLAN.  This
            object is only instantiated when the value of the
            corresponding instance of vtpVlanEditType has a value of
            'fddi' or 'tokenRing' and Source Routing (SRB) is configured
            for use on this VLAN."
    ::= { vtpVlanEditEntry 7 }

vtpVlanEditBridgeNumber OBJECT-TYPE
    SYNTAX     INTEGER (0..15)
    MAX-ACCESS read-create
    STATUS     current
    DESCRIPTION
            "The bridge number of the VTP-capable switches which would
            be used for this VLAN.  This object is only instantiated
            when the value of the corresponding instance of
            vtpVlanEditType has a value of fddiNet(4) or trNet(5)."
    ::= { vtpVlanEditEntry 8 }

vtpVlanEditStpType OBJECT-TYPE
     SYNTAX     INTEGER { ieee(1), ibm(2), auto(3) }
     MAX-ACCESS read-create
     STATUS     current
     DESCRIPTION
             "The type of the Spanning Tree Protocol which would be
             running on this VLAN.  This object is only instantiated when
             the value of the corresponding instance of vtpVlanEditType
             has a value of fddiNet(4) or trNet(5).

             If 'ieee' is selected, the STP that runs will be IEEE.

             If 'ibm' is selected, the STP that runs will be IBM.

             If 'auto' is selected, the STP that runs will be
             dependant on the values of vtpVlanEditBridgeType for all
             children tokenRing/fddi type VLANs.  This will result in
             a 'hybrid' STP (see vtpVlanStpType)."
     ::= { vtpVlanEditEntry 9 }

vtpVlanEditParentVlan  OBJECT-TYPE
    SYNTAX     VlanIndex
    MAX-ACCESS read-create
    STATUS     current
    DESCRIPTION
            "The VLAN index of the VLAN which would be the parent for
            this VLAN.  This object is only instantiated when the value
            of the corresponding instance of vtpVlanEditType has a value
            of 'fddi' or 'tokenRing' and Source Routing (SRB) is
            configured for use on this VLAN.  The parent VLAN must have
            a vtpVlanEditType value of fddiNet(4) or trNet(5),
            respectively."
    ::= { vtpVlanEditEntry 10 }

vtpVlanEditRowStatus OBJECT-TYPE
    SYNTAX     RowStatus
    MAX-ACCESS read-create
    STATUS     current
    DESCRIPTION
            "The status of this row.  Any and all columnar objects in an
            existing row can be modified irrespective of the status of
            the row.

            A row is not qualified for activation until instances of at
            least its vtpVlanEditType, vtpVlanEditName and
            vtpVlanEditDot10Said columns have appropriate values.

            The management station should endeavor to make all rows
            consistent in the table before 'apply'ing the buffer.  An
            inconsistent entry in the table will cause the entire
            buffer to be rejected with the vtpVlanApplyStatus object
            set to the appropriate error value."
    ::= { vtpVlanEditEntry 11 }

vtpVlanEditTranslationalVlan1 OBJECT-TYPE
    SYNTAX     VlanIndex
    MAX-ACCESS read-create
    STATUS     current
    DESCRIPTION
            "A VLAN to which this VLAN would be translational-bridged.
            If this value and the corresponding instance of
            vtpVlanTranslationalVlan2 are both zero, then this VLAN
            would not be translational-bridged."
    DEFVAL     { 0 }
    ::= { vtpVlanEditEntry 12 }

vtpVlanEditTranslationalVlan2 OBJECT-TYPE
    SYNTAX     VlanIndex
    MAX-ACCESS read-create
    STATUS     current
    DESCRIPTION
            "Another VLAN, i.e., other than that indicated by
            vtpVlanEditTranslationalVlan1, to which this VLAN would be
            translational-bridged.  If this value and the corresponding
            instance of vtpVlanTranslationalVlan1 are both zero, then
            this VLAN would not be translational-bridged."
    DEFVAL     { 0 }
    ::= { vtpVlanEditEntry 13 }

vtpVlanEditBridgeType OBJECT-TYPE
    SYNTAX     INTEGER { srt(1), srb(2) }
    MAX-ACCESS read-create
    STATUS     current
    DESCRIPTION
            "The type of bridging mode which would be in use on this
            VLAN.  This object is only instantiated when the value of
            the corresponding instance of vtpVlanEditType has a value of
            fddi(2) or tokenRing(3)."
    ::= { vtpVlanEditEntry 14 }

vtpVlanEditAreHopCount OBJECT-TYPE
    SYNTAX     INTEGER (1..13)
    MAX-ACCESS read-create
    STATUS     current
    DESCRIPTION
            "The maximum number of bridge hops allowed in
            All Routes Explorer frames on this VLAN.  This
            object is only instantiated when the value of the
            corresponding instance of vtpVlanType has a value of fddi(2)
            or tokenRing(3)."
    ::= { vtpVlanEditEntry 15 }

vtpVlanEditSteHopCount OBJECT-TYPE
    SYNTAX     INTEGER (1..13)
    MAX-ACCESS read-create
    STATUS     current
    DESCRIPTION
            "The maximum number of bridge hops allowed in
            Spanning Tree Explorer frames on this VLAN.  This
            object is only instantiated when the value of the
            corresponding instance of vtpVlanType has a value of fddi(2)
            or tokenRing(3)."
    ::= { vtpVlanEditEntry 16}

vtpVlanEditIsCRFBackup OBJECT-TYPE
    SYNTAX     TruthValue
    MAX-ACCESS read-create
    STATUS     current
    DESCRIPTION
            " True if this VLAN is of type trCrf and also is acting as
            a backup trCrf for the ISL distributed BRF"
    ::= { vtpVlanEditEntry 17 }
--
-- VTP Statistics
--

vtpStats      OBJECT IDENTIFIER ::= { vtpMIBObjects 5 }


vtpStatsTable OBJECT-TYPE
    SYNTAX     SEQUENCE OF VtpStatsEntry
    MAX-ACCESS not-accessible
    STATUS     current
    DESCRIPTION
            "A table of VTP statistics."
    ::= { vtpStats 1 }

vtpStatsEntry OBJECT-TYPE
    SYNTAX     VtpStatsEntry
    MAX-ACCESS not-accessible
    STATUS     current
    DESCRIPTION
            "VTP statistics for one management domain."
    AUGMENTS  { managementDomainEntry }
    ::= { vtpStatsTable 1 }

VtpStatsEntry ::= SEQUENCE {
    vtpInSummaryAdverts       Counter32,
    vtpInSubsetAdverts        Counter32,
    vtpInAdvertRequests       Counter32,
    vtpOutSummaryAdverts      Counter32,
    vtpOutSubsetAdverts       Counter32,
    vtpOutAdvertRequests      Counter32,
    vtpConfigRevNumberErrors  Counter32,
    vtpConfigDigestErrors     Counter32
}

vtpInSummaryAdverts OBJECT-TYPE
    SYNTAX     Counter32
    MAX-ACCESS read-only
    STATUS     current
    DESCRIPTION
            "The total number of VTP Summary Adverts received for this
            management domain."
    ::= { vtpStatsEntry 1 }

vtpInSubsetAdverts OBJECT-TYPE
    SYNTAX     Counter32
    MAX-ACCESS read-only
    STATUS     current
    DESCRIPTION
            "The total number of VTP Subset Adverts received for this
            management domain."
    ::= { vtpStatsEntry 2 }

vtpInAdvertRequests OBJECT-TYPE
    SYNTAX     Counter32
    MAX-ACCESS read-only
    STATUS     current
    DESCRIPTION
            "The total number of VTP Advert Requests received for this
            management domain."
    ::= { vtpStatsEntry 3 }

vtpOutSummaryAdverts OBJECT-TYPE
    SYNTAX     Counter32
    MAX-ACCESS read-only
    STATUS     current
    DESCRIPTION
            "The total number of VTP Summary Adverts sent for this
            management domain."
    ::= { vtpStatsEntry 4 }

vtpOutSubsetAdverts OBJECT-TYPE
    SYNTAX     Counter32
    MAX-ACCESS read-only
    STATUS     current
    DESCRIPTION
            "The total number of VTP Subset Adverts sent for this
            management domain."
    ::= { vtpStatsEntry 5 }

vtpOutAdvertRequests OBJECT-TYPE
    SYNTAX     Counter32
    MAX-ACCESS read-only
    STATUS     current
    DESCRIPTION
            "The total number of VTP Advert Requests sent for this
            management domain."
    ::= { vtpStatsEntry 6 }

vtpConfigRevNumberErrors  OBJECT-TYPE
    SYNTAX     Counter32
    MAX-ACCESS read-only
    STATUS     current
    DESCRIPTION
            "The number of occurrences of configuration revision number
            errors for this management domain.  A configuration revision
            number error occurs when a device receives a VTP
            advertisement for which:

            - the advertisement's Configuration Revision Number is the
              same as the current locally-held value, and

            - the advertisement's digest value is different from the
              current locally-held value."
    ::= { vtpStatsEntry 7 }

vtpConfigDigestErrors OBJECT-TYPE
    SYNTAX     Counter32
    MAX-ACCESS read-only
    STATUS     current
    DESCRIPTION
            "The number of occurrences of configuration digest errors
            for this management domain.  A configuration digest error
            occurs when a device receives a VTP advertisement for which:

            - the advertisement's Configuration Revision Number is
              greater than the current locally-held value, and

            - the advertisement's digest value does not match the VLAN
              information assumed by the receiver of the advertisement,
              where the infomation assumed is the combination of the
              information explicitly contained in the advertisement plus
              any omitted information as currently known by the
              receiving device."
    ::= { vtpStatsEntry 8 }



-- Trunk Ports

vlanTrunkPorts   OBJECT IDENTIFIER ::= { vtpMIBObjects 6 }

vlanTrunkPortTable OBJECT-TYPE
    SYNTAX     SEQUENCE OF VlanTrunkPortEntry
    MAX-ACCESS not-accessible
    STATUS     current
    DESCRIPTION
            "The table containing information on the local system's VLAN
            trunk ports."
    ::= { vlanTrunkPorts 1 }

vlanTrunkPortEntry OBJECT-TYPE
    SYNTAX     VlanTrunkPortEntry
    MAX-ACCESS not-accessible
    STATUS     current
    DESCRIPTION
            "Information about one trunk port."
    INDEX      { vlanTrunkPortIfIndex }
    ::= { vlanTrunkPortTable 1 }

VlanTrunkPortEntry ::= SEQUENCE {
    vlanTrunkPortIfIndex              InterfaceIndex,
    vlanTrunkPortManagementDomain     ManagementDomainIndex,
    vlanTrunkPortEncapsulationType    INTEGER,
    vlanTrunkPortVlansEnabled         OCTET STRING,
    vlanTrunkPortNativeVlan           VlanIndex,
    vlanTrunkPortRowStatus            RowStatus,
    vlanTrunkPortInJoins              Counter32,
    vlanTrunkPortOutJoins             Counter32,
    vlanTrunkPortOldAdverts           Counter32,
    vlanTrunkPortVlansPruningEligible OCTET STRING,
    vlanTrunkPortVlansXmitJoined      OCTET STRING,
    vlanTrunkPortVlansRcvJoined       OCTET STRING,
    vlanTrunkPortDynamicState         INTEGER,
    vlanTrunkPortDynamicStatus        INTEGER,
    vlanTrunkPortVtpEnabled           TruthValue,
    vlanTrunkPortEncapsulationOperType INTEGER
}

vlanTrunkPortIfIndex OBJECT-TYPE
    SYNTAX     InterfaceIndex
    MAX-ACCESS not-accessible
    STATUS     current
    DESCRIPTION
            "The value of ifIndex for the interface corresponding to
            this trunk port."
    ::= { vlanTrunkPortEntry 1 }

vlanTrunkPortManagementDomain OBJECT-TYPE
    SYNTAX     ManagementDomainIndex
    MAX-ACCESS read-create
    STATUS     current
    DESCRIPTION
            "The value of managementDomainIndex for the management
            domain on this trunk port.  Devices which support only one
            management domain will support this object read-only."
    ::= { vlanTrunkPortEntry 2 }

vlanTrunkPortEncapsulationType OBJECT-TYPE
    SYNTAX     INTEGER { isl(1), dot10(2), lane(3), dot1Q(4), negotiate(5) }
    MAX-ACCESS read-create
    STATUS     current
    DESCRIPTION
            "The type of VLAN encapsulation desired to be used on this trunk
            port. It is either a particular type, or 'negotiate' meaning
            whatever type results from the negotiation. negotiate(5) is not
            allowed if the port does not support negotiation or if its
            vlanTrunkPortDynamicState is set to on(1) or onNoNegotiate(5).
            Whether writing to this object in order to modify the encapsulation
            is supported is both device and interface specific."
    ::= { vlanTrunkPortEntry 3 }

vlanTrunkPortVlansEnabled OBJECT-TYPE
    SYNTAX     OCTET STRING (SIZE (128))
    MAX-ACCESS read-create
    STATUS     current
    DESCRIPTION
            "A string of octets containing one bit per VLAN in the
            management domain on this trunk port.  The first octet
            corresponds to VLANs with VlanIndex values of 0 through 7;
            the second octet to VLANs 8 through 15; etc.  The most
            significant bit of each octet corresponds to the lowest
            value VlanIndex in that octet.  If the bit corresponding to
            a VLAN is set to '1', then the local system is enabled for
            sending and receiving frames on that VLAN; if the bit is set
            to '0', then the system is disabled from sending and
            receiving frames on that VLAN.

            To avoid conflicts between overlapping partial updates by
            multiple managers, i.e., updates which modify only a portion
            of an instance of this object (e.g., enable/disable a single
            VLAN on the trunk port), any SNMP Set operation accessing an
            instance of this object should also write the value of
            vlanTrunkPortSetSerialNo."
    ::= { vlanTrunkPortEntry 4 }

vlanTrunkPortNativeVlan OBJECT-TYPE
    SYNTAX     VlanIndex
    MAX-ACCESS read-create
    STATUS     current
    DESCRIPTION
            "The VlanIndex of the VLAN which is represented by native
            frames on this trunk port.  For trunk ports not supporting
            the sending and receiving of native frames, this value
            should be set to zero."
    ::= { vlanTrunkPortEntry 5 }

vlanTrunkPortRowStatus OBJECT-TYPE
    SYNTAX     RowStatus
    MAX-ACCESS read-create
    STATUS     current
    DESCRIPTION
            "The status of this row.  In some circumstances, the
            creation of a row in this table is needed to enable the
            appropriate trunking/tagging protocol on the port, to enable
            the use of VTP on the port, and to assign the port to the
            appropriate management domain.  In other circumstances, rows
            in this table will be created as a by-product of other
            operations."
    ::= { vlanTrunkPortEntry 6 }

vlanTrunkPortInJoins OBJECT-TYPE
    SYNTAX     Counter32
    MAX-ACCESS read-only
    STATUS     current
    DESCRIPTION
            "The number of VTP Join messages received on this trunk
            port."
    ::= { vlanTrunkPortEntry 7 }

vlanTrunkPortOutJoins OBJECT-TYPE
    SYNTAX     Counter32
    MAX-ACCESS read-only
    STATUS     current
    DESCRIPTION
            "The number of VTP Join messages sent on this trunk port."
    ::= { vlanTrunkPortEntry 8 }

vlanTrunkPortOldAdverts OBJECT-TYPE
    SYNTAX     Counter32
    MAX-ACCESS read-only
    STATUS     current
    DESCRIPTION
            "The number of VTP Advertisement messages which indicated
            the sender does not support VLAN-pruning received on this
            trunk port."
    ::= { vlanTrunkPortEntry 9 }

vlanTrunkPortVlansPruningEligible OBJECT-TYPE
    SYNTAX     OCTET STRING (SIZE (128))
    MAX-ACCESS read-create
    STATUS     current
    DESCRIPTION
            "A string of octets containing one bit per VLAN in the
            management domain on this trunk port.  The first octet
            corresponds to VLANs with VlanIndex values of 0 through 7;
            the second octet to VLANs 8 through 15; etc.  The most
            significant bit of each octet corresponds to the lowest
            value VlanIndex in that octet.

            If the bit corresponding to a VLAN is set to '1', then the
            local system is permitted to prune that VLAN on this trunk
            port; if the bit is set to '0', then the system must not
            prune that VLAN on this trunk port.

            To avoid conflicts between overlapping partial updates by
            multiple managers, i.e., updates which modify only a portion
            of an instance of this object (e.g., enable/disable a single
            VLAN on the trunk port), any SNMP Set operation accessing an
            instance of this object should also write the value of
            vlanTrunkPortSetSerialNo."
    ::= { vlanTrunkPortEntry 10 }

vlanTrunkPortVlansXmitJoined OBJECT-TYPE
    SYNTAX     OCTET STRING (SIZE (128))
    MAX-ACCESS read-only
    STATUS     current
    DESCRIPTION
            "A string of octets containing one bit per VLAN in the
            management domain on this trunk port.  The first octet
            corresponds to VLANs with VlanIndex values of 0 through 7;
            the second octet to VLANs 8 through 15; etc.  The most
            significant bit of each octet corresponds to the lowest
            value VlanIndex in that octet.

            If the bit corresponding to a VLAN is set to '1', then this
            VLAN is presently being forwarded on this trunk port, i.e.,
            it is not pruned; if the bit is set to '0', then this VLAN
            is presently not being forwarded on this trunk port, either
            because it is pruned or for some other reason."
    ::= { vlanTrunkPortEntry 11 }

vlanTrunkPortVlansRcvJoined OBJECT-TYPE
    SYNTAX     OCTET STRING (SIZE (128))
    MAX-ACCESS read-only
    STATUS     current
    DESCRIPTION
            "A string of octets containing one bit per VLAN in the
            management domain on this trunk port.  The first octet
            corresponds to VLANs with VlanIndex values of 0 through 7;
            the second octet to VLANs 8 through 15; etc.  The most
            significant bit of each octet corresponds to the lowest
            value VlanIndex in that octet.

            If the bit corresponding to a VLAN is set to '1', then the
            local switch is currently sending joins for this VLAN on
            this trunk port, i.e., it is asking to receive frames for
            this VLAN; if the bit is set to '0', then the local switch
            is not currently sending joins for this VLAN on this trunk
            port."
    ::= { vlanTrunkPortEntry 12 }

vlanTrunkPortDynamicState OBJECT-TYPE
    SYNTAX     INTEGER { on(1), off(2), desirable(3), auto(4), onNoNegotiate(5)
}
    MAX-ACCESS read-create
    STATUS     current
    DESCRIPTION
            "For devices that allows dynamic determination of whether
            a link between two switches should be a trunk or not, this object
            allows the operator to mandate the behavior of that dynamic
            mechanism.

            on(1) dictates that the interface will always be a
            trunk. This is the value for static entries (those that
            show no dynamic behavior). If the negotiation is supported on this
            port, negotiation will take place with the far end to attempt
            to bring the far end into trunking state.

            off(2) allows an operator to specify that the specified
            interface is never to be trunk, regardless of any dynamic
            mechanisms to the contrary.  This value is useful for
            overriding the default behavior of some switches. If the
            negotiation is supported on this port, negotiation will take place
            with the far end to attempt on the link to bring the far end into
            non-trunking state.

            desirable(3) is used to indicate that it is desirable for
            the interface to become a trunk.  The device will initiate
            any negotiation necessary to become a trunk but will not
            become a trunk unless it receives confirmation from the far
            end on the link.

            auto(4) is used to indicate that the interface is capable
            and willing to become a trunk but will not initiate
            trunking negotiations.  The far end on the link are
            required to either start negotiations or start sending
            encapsulated packets, on which event the specified
            interface will become a trunk.

            onNoNegotiate(5) is used to indicate that the interface is permanent
ly
            set to be a trunk, and no negotiation takes place with the
            far end on the link to ensure consistent operation. This is similar
            to on(1) except no negotiation takes place with the far end.

            If the port does not support negotiation or its
            vlanTrunkPortEncapsulationType is set to negotiate(5),
            onNoNegotiate(5) is not allowed.

            Devices that do no support dynamic determination (for just
            a particular interface, encapsulation or for the whole
            device) need only support the 'on', and 'off' values."
       ::= { vlanTrunkPortEntry 13 }

vlanTrunkPortDynamicStatus OBJECT-TYPE
    SYNTAX     INTEGER { trunking(1), notTrunking(2) }
    MAX-ACCESS read-only
    STATUS     current
    DESCRIPTION
            " Indicates whether the specified interface is either
            acting as a trunk or not. This is a result of the
            vlanTrunkPortDynamicState and the ifOperStatus of the
            trunk port itself."
    ::= { vlanTrunkPortEntry 14 }

vlanTrunkPortVtpEnabled OBJECT-TYPE
    SYNTAX     TruthValue
    MAX-ACCESS read-create
    STATUS     current
    DESCRIPTION
            " Some trunk interface modules allow VTP to be
            enabled/disabled seperately from that of the central
            device.  In such a case this object provides management a
            way to remotely enable VTP on that module.  If a module
            does not support a seperate VTP enabled state then this
            object shall always return 'true' and will accept no other
            value during a SET operation."
    ::= { vlanTrunkPortEntry 15 }

vlanTrunkPortEncapsulationOperType OBJECT-TYPE
    SYNTAX     INTEGER { isl(1), dot10(2), lane(3), dot1Q(4), negotiating(5),
                         notApplicable(6) }
    MAX-ACCESS read-only
    STATUS     current
    DESCRIPTION
            "The type of VLAN encapsulation in use on this trunk port.
             For intefaces with vlanTrunkPortDynamicStatus of
             notTrunking(2) the vlanTrunkPortEncapsulationOperType shall
             be notApplicable(6). "
    ::= { vlanTrunkPortEntry 16 }

vlanTrunkPortSetSerialNo OBJECT-TYPE
    SYNTAX     TestAndIncr
    MAX-ACCESS read-write
    STATUS     current
    DESCRIPTION
            "An advisory lock used to allow several cooperating SNMPv2
            managers to coordinate their use of the SNMPv2 set operation
            acting upon any instance of vlanTrunkPortVlansEnabled."
    ::= { vlanTrunkPorts 2 }


-- VTP notifications

vtpNotifications   OBJECT IDENTIFIER ::= { ciscoVtpMIB 2 }
vtpNotificationsPrefix
                   OBJECT IDENTIFIER ::= { vtpNotifications 0 }
vtpNotificationsObjects
                   OBJECT IDENTIFIER ::= { vtpNotifications 1 }

vtpConfigRevNumberError NOTIFICATION-TYPE
    OBJECTS     { managementDomainConfigRevNumber }
    STATUS      current
    DESCRIPTION
            "A configuration revision number error notification
            signifies that a device has incremented its
            vtpConfigRevNumberErrors counter.

            Generation of this notification is suppressed if the
            vtpNotificationsEnabled has the value 'false'.

            The device must throttle the generation of consecutive
            vtpConfigRevNumberError notifications so that there is at
            least a five-second gap between notification of this type.
            When notification are throttled, they are dropped, not
            queued for sending at a future time.  (Note that
            'generating' a notification means sending to all configured
            recipients.)"
    ::= { vtpNotificationsPrefix 1 }

vtpConfigDigestError NOTIFICATION-TYPE
    OBJECTS     { managementDomainConfigRevNumber }
    STATUS      current
    DESCRIPTION
            "A configuration digest error notification signifies that a
            device has incremented its vtpConfigDigestErrors counter.

            Generation of this notification is suppressed if the
            vtpNotificationsEnabled has the value 'false'.

            The device must throttle the generation of consecutive
            vtpConfigDigestError notifications so that there is at least
            a five-second gap between notification of this type.  When
            notification are throttled, they are dropped, not queued for
            sending at a future time.  (Note that 'generating' a
            notification means sending to all configured recipients.)"
    ::= { vtpNotificationsPrefix 2 }

vtpServerDisabled NOTIFICATION-TYPE
    OBJECTS     { managementDomainConfigRevNumber, vtpMaxVlanStorage }
    STATUS      current
    DESCRIPTION
            "A VTP Server disabled notification is generated when the
            local system is no longer able to function as a VTP Server
            because the number of defined VLANs is greater than
            vtpMaxVlanStorage.

            Generation of this notification is suppressed if the
            vtpNotificationsEnabled has the value 'false'."
    ::= { vtpNotificationsPrefix 3 }

vtpMtuTooBig NOTIFICATION-TYPE
    OBJECTS     { vlanTrunkPortManagementDomain, vtpVlanState }
    STATUS      current
    DESCRIPTION
            "A VTP MTU tooBig notification is generated when a VLAN's
            MTU size is larger than can be supported either:

            - by one or more of its trunk ports:
              the included vtpVlanState has the value
              'mtuTooBigForTrunk' and the included
              vlanTrunkPortManagementDomain is for the first (or only)
              trunk port,
              or

            - by the device itself:
              vtpVlanState has the value 'mtuTooBigForDevice' and any
              instance of vlanTrunkPortManagementDomain is included.

            Devices which have no trunk ports do not send vtpMtuTooBig
            notifications.

            Generation of this notification is suppressed if the
            vtpNotificationsEnabled has the value 'false'."
    ::= { vtpNotificationsPrefix 4 }

vtpVlanRingNumberConfigConflict NOTIFICATION-TYPE
    OBJECTS     { vtpVlanIndex, vtpVlanRingNumber,
                  ifIndex, vtpVlanPortLocalSegment }
    STATUS      current
    DESCRIPTION
            "A VTP ring number configuration conflict notification is
            generated if, and only at the time when, a device learns of
            a conflict between:

            a) the ring number (vtpVlanPortLocalSegment) being used on a
               token ring segment attached to the port identified by
               ifIndex, and

            b) the VTP-obtained ring number (vtpVlanRingNumber) for the
               VLAN identified by vtpVlanIndex.

            When such a conflict occurs, the bridge port is put into an
            administrative down position until the conflict is resolved
            through local/network management intervention.

            This notification is only applicable to VLANs of type
            'tokenRing'."
    ::= { vtpNotificationsPrefix 5 }

vtpVersionOneDeviceDetected NOTIFICATION-TYPE
    OBJECTS     { vlanTrunkPortManagementDomain }
    STATUS      current
    DESCRIPTION
            "A VTP version one device detected notification is
            generated by a device when:

            a) a management domain has been put into version 2 mode
               (as accessed by managementDomainVersionInUse).
            b) 15 minutes has passed since a).
            c) a version 1 PDU is detected on a trunk on the device
               that is in that management domain which has a lower
               revision number than the current configuration."
    ::= { vtpNotificationsPrefix 6 }

vlanTrunkPortDynamicStatusChange  NOTIFICATION-TYPE
        OBJECTS         {vlanTrunkPortDynamicStatus}
        STATUS          current
        DESCRIPTION
                "A vlanTrunkPortDynamicStatusChange notification is
                generated by a device when the value of
                vlanTrunkPortDynamicStatus object has been changed."
        ::= { vtpNotificationsPrefix 7 }

vtpVlanPortLocalSegment OBJECT-TYPE
    SYNTAX     INTEGER (0..65535)
--    MAX-ACCESS accessible-for-notify
    MAX-ACCESS read-only
    STATUS     current
    DESCRIPTION
            "The ring (segment) number in use on a 802.5 ring.  For
            bridges supporting RFC 1525, this value is the same as given
            by dot1dSrPortLocalSegment for the bridge port attached to
            that ring.  When tokenRing VLANs are in use, each 'trNet'
            VLAN can/does have a different instance of
            dot1dSrPortLocalSegment for each physical port.  Note that
            access to the particuler instance of dot1dSrPortLocalSegment
            requires knowledge of how the agent supports the multiple
            'contexts' required to implement RFC 1525 for multiple
            VLANs; also note that the assignment of ifIndex values may
            be different in different 'contexts'."
    ::= { vtpNotificationsObjects 1 }





-- Conformance Information

vtpMIBConformance
               OBJECT IDENTIFIER ::= { ciscoVtpMIB 3 }

vtpMIBCompliances
               OBJECT IDENTIFIER ::= { vtpMIBConformance 1 }
vtpMIBGroups   OBJECT IDENTIFIER ::= { vtpMIBConformance 2 }


-- compliance statements

vtpMIBCompliance MODULE-COMPLIANCE
    STATUS  current
    DESCRIPTION
            "The compliance statement for VTP implementations."
    MODULE  -- this module
        MANDATORY-GROUPS { vtpBasicGroup,
                           vtpVlanInfoGroup,
--                           vtpConfigNotificationsGroup,
                           vtpStatsGroup,
                           vtpTrunkPortGroup
                         }

        OBJECT       managementDomainRowStatus
        SYNTAX       INTEGER { active(1)}   -- subset of RowStatus
        MIN-ACCESS   read-only
        DESCRIPTION
             "Write access is not required, and only one
             of the six enumerated values for the
             RowStatus textual convention need be
             supported, specifically: active(1)."

        OBJECT       vlanTrunkPortRowStatus
        SYNTAX       INTEGER { active(1)}   -- subset of RowStatus
        MIN-ACCESS   read-only
        DESCRIPTION
             "Write access is not required, and only one
             of the six enumerated values for the
             RowStatus textual convention need be
             supported, specifically: active(1)."

        OBJECT       vlanTrunkPortManagementDomain
        MIN-ACCESS   read-only
        DESCRIPTION  "Write access is not required."

        OBJECT       vlanTrunkPortEncapsulationType
        MIN-ACCESS   read-only
        DESCRIPTION  "Write access is not required."

        OBJECT       vlanTrunkPortNativeVlan
        MIN-ACCESS   read-only
        DESCRIPTION  "Write access is not required."

        GROUP        vtpVlanInfoEditGroup
        DESCRIPTION
            "This group must be implemented by VTP Servers.
            VTP Clients need not implement these objects, and
            must not allow VLANs to be created, modified, or
            destroyed using these objects."

    ::= { vtpMIBCompliances 1 }


-- units of conformance

vtpBasicGroup OBJECT-GROUP
    OBJECTS { vtpVersion, vtpMaxVlanStorage,
              vtpNotificationsEnabled,
              managementDomainName, managementDomainLocalMode,
              managementDomainConfigRevNumber,
              managementDomainLastUpdater,
              managementDomainLastChange,
              managementDomainTftpServer,
              managementDomainTftpPathname,
              managementDomainRowStatus }
    STATUS  current
    DESCRIPTION
            "A collection of objects providing basic status and control
            of a VTP implementation."
    ::= { vtpMIBGroups 1 }

vtpVlanInfoGroup OBJECT-GROUP
    OBJECTS { vtpVlanState, vtpVlanType, vtpVlanName,
              vtpVlanMtu, vtpVlanDot10Said,
              vtpVlanRingNumber, vtpVlanBridgeNumber,
              vtpVlanStpType, vtpVlanParentVlan,
              vtpVlanTranslationalVlan1,
              vtpVlanTranslationalVlan2,
              vtpVlanBridgeType, vtpVlanAreHopCount,
              vtpVlanSteHopCount, vtpVlanIsCRFBackup }
    STATUS  current
    DESCRIPTION
            "A collection of objects for monitoring VLAN information."
    ::= { vtpMIBGroups 13 }

vtpVlanInfoEditGroup OBJECT-GROUP
    OBJECTS { vtpVlanEditOperation, vtpVlanApplyStatus,
              vtpVlanEditBufferOwner, vtpVlanEditConfigRevNumber,
              vtpVlanEditState, vtpVlanEditType, vtpVlanEditName,
              vtpVlanEditMtu, vtpVlanEditDot10Said,
              vtpVlanEditRingNumber, vtpVlanEditBridgeNumber,
              vtpVlanEditStpType, vtpVlanEditParentVlan,
              vtpVlanEditRowStatus,
              vtpVlanEditTranslationalVlan1,
              vtpVlanEditTranslationalVlan2,
              vtpVlanEditBridgeType, vtpVlanEditAreHopCount,
              vtpVlanEditSteHopCount, vtpVlanEditIsCRFBackup }
    STATUS  current
    DESCRIPTION
            "A collection of objects for editing VLAN information in VTP
            Servers."
    ::= { vtpMIBGroups 14 }

vtpStatsGroup OBJECT-GROUP
    OBJECTS { vtpInSummaryAdverts, vtpInSubsetAdverts,
              vtpInAdvertRequests, vtpOutSummaryAdverts,
              vtpOutSubsetAdverts, vtpOutAdvertRequests,
              vtpConfigRevNumberErrors, vtpConfigDigestErrors }
    STATUS  current
    DESCRIPTION
            "A collection of objects providing VTP statistics."
    ::= { vtpMIBGroups 4 }

vtpTrunkPortGroup OBJECT-GROUP
    OBJECTS { vlanTrunkPortManagementDomain,
              vlanTrunkPortEncapsulationType,
              vlanTrunkPortVlansEnabled,
              vlanTrunkPortNativeVlan,
              vlanTrunkPortRowStatus,
              vlanTrunkPortSetSerialNo }
    STATUS  current
    DESCRIPTION
            "A collection of objects providing information on trunk
            ports."
    ::= { vtpMIBGroups 5 }

vtpTrunkPortGroup2 OBJECT-GROUP
    OBJECTS { vlanTrunkPortDynamicState, vlanTrunkPortDynamicStatus,
              vlanTrunkPortVtpEnabled }
    STATUS  current
    DESCRIPTION
            " Additional functionality added to the
            vlanTrunkPortTable. "
    ::= { vtpMIBGroups 11 }

vtpTrunkPortGroup3 OBJECT-GROUP
    OBJECTS { vlanTrunkPortEncapsulationOperType }
    STATUS  current
    DESCRIPTION
            " Additional functionality added to the
            vlanTrunkPortTable. "
    ::= { vtpMIBGroups 15 }

vtpTrunkPruningGroup OBJECT-GROUP
    OBJECTS { vlanTrunkPortInJoins, vlanTrunkPortOutJoins,
              vlanTrunkPortOldAdverts,
              vlanTrunkPortVlansPruningEligible,
              vlanTrunkPortVlansXmitJoined,
              vlanTrunkPortVlansRcvJoined }
    STATUS  current
    DESCRIPTION
            "A collection of objects providing information on VLAN
            pruning."
    ::= { vtpMIBGroups 7 }

vtpTrunkPruningGroup2 OBJECT-GROUP
    OBJECTS { managementDomainPruningState }
    STATUS  current
    DESCRIPTION
            "A collection of object providing information on whether
            VLAN pruning is enabled."
    ::= { vtpMIBGroups 10 }

vtpVersion2BasicGroup OBJECT-GROUP
    OBJECTS { managementDomainVersionInUse }
    STATUS  current
    DESCRIPTION
            " The object required to indicate the version of VTP in
            use by a management domain."
    ::= { vtpMIBGroups 12 }

-- vtpConfigNotificationsGroup NOTIFICATION-GROUP
--     NOTIFICATIONS { vtpConfigDigestError,
--                     vtpConfigRevNumberError,
--                     vtpServerDisabled,
--                     vtpMtuTooBig,
--                     vtpVlanRingNumberConfigConflict,
--                     vtpVersionOneDeviceDetected,
--                     vlanTrunkPortDynamicStatusChange,
--                     vtpVlanPortLocalSegment }
--     STATUS        current
--     DESCRIPTION
--             "The notifications which a VTP implementation is
--             required to implement."
--     ::= { vtpMIBGroups 6 }

END
