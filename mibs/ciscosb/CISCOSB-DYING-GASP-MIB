CISCOSB-DYING-GASP-MIB DEFINITIONS ::= BEGIN
-- Date:                29 Nov 2021

IMPORTS
    OBJECT-TYPE, MODULE-IDENTITY                FROM SNMPv2-SMI
    TEXTUAL-CONVENTION, TruthValue 				FROM SNMPv2-TC
    switch001                           FROM CISCOSB-MIB;


rlDyGsp MODULE-IDENTITY
         LAST-UPDATED "202104100000Z"
                ORGANIZATION "Cisco Systems, Inc."
                CONTACT-INFO
                "Postal: 170 West Tasman Drive
                San Jose , CA 95134-1706
                USA


                Website:  Cisco Small Business Support Community <http://www.cisco.com/go/smallbizsupport>"


         DESCRIPTION
                "The private MIB module definition for Dying Gasp feature."
         REVISION "200911260000Z"
         DESCRIPTION
                "Initial revision."
        ::= { switch001 245 }

rlDyGspModeConfig OBJECT-TYPE
    SYNTAX INTEGER {
        syslogPrimary-snmpSecondary(1),
        snmpPrimary-syslogSecondary(2),
        syslogPrimary-NoSecondary(3),
        snmpPrimary-NoSecondary(4),
        disabled(5)
    }
    MAX-ACCESS  read-write
    STATUS      current
    DESCRIPTION
        "Specifies the dying-gasp mode configuration."
    ::= { rlDyGsp 1 }

END
