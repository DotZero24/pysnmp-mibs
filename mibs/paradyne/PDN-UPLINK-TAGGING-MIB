-- ===============================================================
-- Copyright (C) 2003 Paradyne Corporation.
-- ===============================================================

PDN-UPLINK-TAGGING-MIB DEFINITIONS ::= BEGIN

IMPORTS
    MODULE-IDENTITY, OBJECT-TYPE, Unsigned32
        FROM SNMPv2-SMI
    OBJECT-GROUP
        FROM SNMPv2-CONF
    VlanId
        FROM Q-BRIDGE-MIB
    pdn-common
        FROM PDN-HEADER-MIB;

pdnUplinkTagging MODULE-IDENTITY
    LAST-UPDATED "200303120000Z"  -- March 12, 2003
    ORGANIZATION "Paradyne Networks
                  MIB Working Group
                  Other information about group editing the MIB"
    CONTACT-INFO "Paradyne Networks, Inc.
                  8545 126th Avenue North
                  Largo, FL 33733
                  www.paradyne.com

                  General Comments to: mibwg_team@paradyne.com

                  Editors
                        Clay Sikes"

    DESCRIPTION
        "This MIB contains objects that are used to configure Uplink Tagging (ULT).
        Uplink Tagging is a term used to describe a feature that simplifies the
        setup and administration of networks where a service provider wants to
        use a unique VLAN per subscriber port. Ingress frames will get tagged
        with a VLAN and these tagged frame will be transmitted on the uplink port
        towards the WAN.

        In cases where the hardware implementation permits, multiple units can be
        interconnected together to form a 'Uplink Tagging Domain (ULT Domain)'. A ULT
        domain is defined as the set of interconnected Paradyne DSLAMs that share a
        common block of VLAN IDs. The maximum number of Paradyne DSLAMs that can be
        interconnected is implementation dependent. Generally, all DSLAMs in a ULT
        Domain will be configured with the same block of VLAN IDs. Each chassis/unit
        will be assigned a unique ULT Index within the ULT Domain.

        There are two parts of configuring Uplink Tagging:
        1. Uplink Base VLAN Tag - This object specifies the beginning VLAN ID for a
                                  particular common block of VLAN IDs. This object
                                  will be defined as an enumeration whose values will
                                  depend on the number of port in a chassis/unit.
        2. Uplink Tag Index     - This object specifies the index within some block
                                  of VLAN IDs. Generally, this index can thought of a
                                  chassis/unit number as can be seen with the examples
                                  below."


    REVISION "200303120000Z"  -- March 12, 2003
    DESCRIPTION "Deprecated the origional objects, ultBaseVlanTag and
                ultIndex. Added new objects as follows:
                1. pdnUltIndex         - This new object is basically an Unsigned32
                                         that excludes '0'. It idea is that different
                                         implementations will support different maximum
                                         values of the index. As such, the syntax for
                                         this object will cover any implementation and
                                         actual implementation specific maximum values
                                         should be documented in something like the
                                         implementation's SNMP Op Spec.
               2. pdnGenUltBaseVlanTag - This object allows a any base VLAN Tag to
                                         be defined.
               3. pdn48UltBaseVlanTag  - This object defines a set of enumerations
                                         for base VLAN Tags for chassis/units that
                                         contain 48 ports.
               4. pdn24UltBaseVlanTag  - This object defines a set of enumerations
                                         for base VLAN Tags for chassis/units that
                                         contain 24 ports."

    REVISION "200205150000Z"  -- May 15, 2002
    DESCRIPTION "Initial Release."

::=  { pdn-common 37 }

-- Base in the MIB Module for all objects.
pdnUplinkTaggingObjects OBJECT IDENTIFIER ::= { pdnUplinkTagging 1 }

-- Objects for Rev 2 of this MIB
pdnUplinkTaggingObjectsR2 OBJECT IDENTIFIER ::= { pdnUplinkTagging 3 }




-- Uplink Tagging (ULT) Index
pdnUltIndex     OBJECT-TYPE
    SYNTAX      Unsigned32(1..4294967295)
    MAX-ACCESS  read-write
    STATUS      current
    DESCRIPTION "This object represents VLAN tag index which is an
                index into a block of VLAN Tags the unit will use. Generally,
                this can be also thought of as the chassis/unit number in the
                case where multiple units are interconnected and form a
                ULT Domain described above.

                It is strongly encouraged that the upper limit for
                a particular implementation be clearly documented in the
                product's SNMP Op Spec."
    DEFVAL      { 1 }
    ::= { pdnUplinkTaggingObjectsR2 1 }

-- Generic Uplink Tagging Base (ULT) VLAN Tag not related to the
-- number of ports that exist in a chassis/unit.
pdnGenUltBaseVlanTag     OBJECT-TYPE
    SYNTAX      VlanId
    MAX-ACCESS  read-write
    STATUS      current
    DESCRIPTION "This object can be used to allow any Uplink
                Tagging Base Index to be entered when they
                don't like the 'canned' list defined in the
                objects below."
    DEFVAL      { 16 }
    ::= { pdnUplinkTaggingObjectsR2 2 }

-- Uplink Tagging Base (ULT) VLAN Tag for 48 Port Units
pdn48UltBaseVlanTag  OBJECT-TYPE
    SYNTAX      INTEGER {
                                      -- Base VLAN Tag
                    ultBase16(1),     -- 16    (0x0010)
                    ultBase512(2),    -- 512   (0x0200)
                    ultBase1024(3),   -- 1024  (0x0400)
                    ultBase1536(4),   -- 1536  (0x0600)
                    ultBase2048(5),   -- 2048  (0x0800)
                    ultBase2560(6),   -- 2560  (0x0A00)
                    ultBase3072(7),   -- 3072  (0x0C00)
                    ultBase3584(8)    -- 3584  (0x0E00)
                }
    MAX-ACCESS  read-write
    STATUS      current
    DESCRIPTION "This object represents Uplink Tagging base index which
                is the starting VLAN ID for a particular common block
                of VLAN IDs for chassis/units that contain 48 DSL
                subscriber ports."
    DEFVAL      { ultBase16 }
    ::= { pdnUplinkTaggingObjectsR2 3 }

-- *********************************************************************************
-- The following table summarizes the range of VLAN tags in a stack where
-- each unit supports 48 ports and up to 5 stacked units are supported:
--     ULT Base VLAN Tag       Subscriber VLAN Port Tags (units 1 through 5)
--
--     16      (0x0010)        16    -   255
--     512     (0x0200)        512   -   751
--     1024    (0x0400)        1024  -  1263
--     1536    (0x0600)        1536  -  1775
--     2048    (0x0800)        2048  -  2287
--     2560    (0x0A00)        2560  -  2799
--     3072    (0x0C00)        3072  -  3311
--     3584    (0x0E00)        3584  -  3823
--
--
-- The following table shows the tags for each unit in a stack:
--    Note that the unit number equates to the ULT Index.
--
--    Base             Unit 1      Unit 2       Unit 3       Unit 4       Unit 5
--    Vlan Tag         ULT Tags    ULT Tags     ULT Tags     ULT Tags     ULT Tags
--
--      16  (0x0010)     16-63       64-111      112-159      160-207      208-255
--     512  (0x0200)    512-559     560-607      608-655      656-703      704-751
--    1024  (0x0400)   1024-1071   1072-1119    1120-1167    1168-1215    1216-1263
--    1536  (0x0600)   1536-1583   1584-1631    1632-1679    1680-1727    1728-1775
--    2048  (0x0800)   2048-2095   2096-2143    2144-2191    2192-2239    2240-2287
--    2560  (0x0A00)   2560-2607   2608-2655    2656-2703    2704-2751    2752-2799
--    3072  (0x0C00)   3072-3119   3120-3167    3168-3215    3216-3263    3264-3311
--    3584  (0x0E00)   3584-3631   3632-3679    3680-3727    3728-3775    3776-3823
-- **********************************************************************************


-- Uplink Tagging Base (ULT) VLAN Tag for 24 Port Units
pdn24UltBaseVlanTag  OBJECT-TYPE
    SYNTAX      INTEGER {
                                      -- Base VLAN Tag
                    ultBase16(1),     -- 16    (0x0010)
                    ultBase256(2),    -- 126   (0x0100)
                    ultBase512(3),    -- 512   (0x0200)
                    ultBase768(4),    -- 768   (0x0300)
                    ultBase1024(5),   -- 1024  (0x0400)
                    ultBase1280(6),   -- 1280  (0x0500)
                    ultBase1536(7),   -- 1536  (0x0600)
                    ultBase1792(8),   -- 1792  (0x0700)
                    ultBase2048(9),   -- 2048  (0x0800)
                    ultBase2304(10),  -- 2304  (0x0900)
                    ultBase2560(11),  -- 2560  (0x0A00)
                    ultBase2816(12),  -- 2816  (0x0B00)
                    ultBase3072(13),  -- 3072  (0x0C00)
                    ultBase3328(14),  -- 3328  (0x0D00)
                    ultBase3584(15),  -- 3584  (0x0E00)
                    ultBase3840(16)   -- 3840  (0x0F00)
                }
    MAX-ACCESS  read-write
    STATUS      current
    DESCRIPTION "This object represents Uplink Tagging base index which
                is the starting VLAN ID for a particular common block
                of VLAN IDs for chassis/units that contain 24 DSL
                subscriber ports."
    DEFVAL      { ultBase16 }
    ::= { pdnUplinkTaggingObjectsR2 4 }

-- **********************************************************************************
-- The following table summarizes the range of VLAN tags in a stack where
-- each unit supports 24 ports and up to 10 stacked units are supported:
--
--     ULT Base VLAN Tag       Subscriber VLAN Port Tags (units 1 through 10)
--
--     16      (0x0010)        16    -   255
--     256     (0x0100)        256   -   495
--     512     (0x0200)        512   -   751
--     768     (0x0300)        768   -  1007
--     1024    (0x0400)        1024  -  1263
--     1280    (0x0500)        1280  -  1519
--     1536    (0x0600)        1536  -  1775
--     1792    (0x0700)        1792  -  2031
--     2048    (0x0800)        2048  -  2287
--     2304    (0x0900)        2304  -  2543
--     2560    (0x0A00)        2560  -  2799
--     2816    (0x0B00)        2816  -  3057
--     3072    (0x0C00)        3072  -  3311
--     3328    (0x0D00)        3328  -  3567
--     3584    (0x0E00)        3584  -  3823
--     3840    (0x0F00)        3840  -  4079
--
--
-- The following table shows the tags for each unit in a stack:
--
--    Note that the unit number equates to the ULT Index.
--
--    Base             Unit 1      Unit 2       Unit 3       Unit 4       Unit 5
--    Vlan Tag         ULT Tags    ULT Tags     ULT Tags     ULT Tags     ULT Tags
--
--      16  (0x0010)     16-39       40-63        64-87        88-111      112-135
--     256  (0x0100)    256-279     280-303      304-327      328-351      352-375
--     512  (0x0200)    512-535     536-559      560-583      584-607      608-631
--     768  (0x0300)    768-791     792-815      816-839      840-863      864-887
--    1024  (0x0400)   1024-1047   1048-1071    1072-1095    1096-1119    1120-1143
--    1280  (0x0500)   1280-1303   1304-1327    1328-1351    1352-1375    1376-1399
--    1536  (0x0600)   1536-1559   1560-1583    1584-1607    1608-1631    1632-1655
--    1792  (0x0700)   1792-1815   1816-1839    1840-1863    1864-1887    1888-1911
--    2048  (0x0800)   2048-2071   2072-2095    2096-2119    2120-2143    2144-2167
--    2304  (0x0900)   2304-2327   2328-2351    2352-2375    2376-2399    2400-2423
--    2560  (0x0A00)   2560-2583   2584-2607    2608-2631    2632-2655    2656-2679
--    2816  (0x0B00)   2816-2839   2840-2863    2864-2887    2888-2911    2912-2935
--    3072  (0x0C00)   3072-3095   3096-3119    3120-3143    3144-3167    3168-3191
--    3328  (0x0D00)   3328-3351   3352-3375    3376-3399    3400-3423    3424-3447
--    3584  (0x0E00)   3584-3607   3608-3631    3632-3655    3656-3679    3680-3703
--    3840  (0x0F00)   3840-3863   3864-3887    3888-3911    3912-3935    3936-3959
--
--    Base             Unit 6      Unit 7       Unit 8       Unit 9       Unit 10
--    Vlan Tag         ULT Tags    ULT Tags     ULT Tags     ULT Tags     ULT Tags
--
--      16  (0x0010)    136-159     160-183      184-207      208-231      232-255
--     256  (0x0100)    376-399     400-423      424-447      448-471      472-495
--     512  (0x0200)    632-655     656-679      680-703      704-727      728-751
--     768  (0x0300)    888-911     912-935      936-959      960-983      984-1007
--    1024  (0x0400)   1144-1167   1168-1191    1192-1215    1216-1239    1240-1263
--    1280  (0x0500)   1400-1423   1424-1447    1448-1471    1472-1495    1496-1519
--    1536  (0x0600)   1656-1679   1680-1703    1704-1727    1728-1751    1752-1775
--    1792  (0x0700)   1912-1935   1936-1959    1960-1983    1984-2007    2008-2031
--    2048  (0x0800)   2168-2191   2192-2215    2216-2239    2240-2263    2264-2287
--    2304  (0x0900)   2424-2447   2448-2471    2472-2495    2496-2519    2520-2543
--    2560  (0x0A00)   2680-2703   2704-2727    2728-2751    2752-2775    2776-2799
--    2816  (0x0B00)   2936-2959   2960-2983    2984-3007    3008-3033    3034-3057
--    3072  (0x0C00)   3192-3215   3216-3239    3240-3263    3264-3287    3288-3311
--    3328  (0x0D00)   3448-3471   3472-3495    3496-3519    3520-3543    3544-3567
--    3584  (0x0E00)   3704-3727   3728-3751    3752-3775    3776-3799    3800-3823
--    3840  (0x0F00)   3960-3983   3984-4007    4008-4031    4032-4055    4056-4079
-- **********************************************************************************



-- **********************************************************************************
-- **********************************************************************************
-- **             The objects below have been deprecated                           **
-- **********************************************************************************
-- **********************************************************************************

-- Uplink Tagging Base (ULT) VLAN Tag
ultBaseVlanTag  OBJECT-TYPE
    SYNTAX      INTEGER {
                                      -- Base VLAN Tag
                    ultBase16(1),     -- 16    (0x0010)
                    ultBase512(2),    -- 512   (0x0200)
                    ultBase1024(3),   -- 1024  (0x0400)
                    ultBase1536(4),   -- 1536  (0x0600)
                    ultBase2048(5),   -- 2048  (0x0800)
                    ultBase2560(6),   -- 2560  (0x0A00)
                    ultBase3072(7),   -- 3072  (0x0C00)
                    ultBase3584(8)    -- 3584  (0x0E00)
                }
    MAX-ACCESS  read-write
    STATUS      deprecated
    DESCRIPTION "This object represents Uplink Tagging base index.

                 This object has been deprecated. Please use an object defined
                 in pdnUplinkTaggingObjectsR2."
    DEFVAL      { ultBase16 }
    ::= { pdnUplinkTaggingObjects 1 }


-- Uplink Tagging (ULT) Index
ultIndex        OBJECT-TYPE
    SYNTAX      INTEGER(1..5)
    MAX-ACCESS  read-write
    STATUS      deprecated
    DESCRIPTION "This object represents VLAN tag index which represents an
                index into a block of VLAN Tags the unit will use.

                This object has been deprecated. Please use pdnUltIndex, which
                is more general below."
    DEFVAL      { 1 }
    ::= { pdnUplinkTaggingObjects 2 }



--+++++++++++++++++++++++++++++++++++++++++++++++++++++++++++++++++++++++++++++
--
-- Conformance Information
--

pdnUplinkTaggingConformance  OBJECT IDENTIFIER ::= { pdnUplinkTagging 2 }
pdnUplinkTaggingGroups       OBJECT IDENTIFIER ::= { pdnUplinkTaggingConformance 1 }
pdnUplinkTaggingCompliances  OBJECT IDENTIFIER ::= { pdnUplinkTaggingConformance 2 }
pdnUplinkTaggingDeprecatedGroup OBJECT IDENTIFIER ::= { pdnUplinkTaggingConformance 3 }

--
-- Units of Conformance for Current Objects
--
pdn48PortUpLinkTaggingGroup OBJECT-GROUP
    OBJECTS     {
                     pdnUltIndex,
                     pdnGenUltBaseVlanTag,
                     pdn48UltBaseVlanTag
    }
    STATUS      current
    DESCRIPTION "Uplink Tagging Objects for 48-Port chassis/units."
    ::= { pdnUplinkTaggingGroups  1 }

pdn24PortUpLinkTaggingGroup OBJECT-GROUP
    OBJECTS     {
                     pdnUltIndex,
                     pdnGenUltBaseVlanTag,
                     pdn24UltBaseVlanTag
    }
    STATUS      current
    DESCRIPTION "Uplink Tagging Objects for 24-Port chassis/units."
    ::= { pdnUplinkTaggingGroups  2 }

--
-- Units of Conformance for Deprecated Objects
--
upLinkTaggingDeprecatedGroup OBJECT-GROUP
    OBJECTS     {
                     ultBaseVlanTag,
                     ultIndex
    }
    STATUS      deprecated
    DESCRIPTION "Objects not to use."
    ::= { pdnUplinkTaggingDeprecatedGroup 1 }


END
