-- ===============================================================
-- Copyright (C) 2000 Paradyne Corporation.
--  ATM Extension Group
-- ==============================================================

PDN-DS3EXT-MIB DEFINITIONS ::= BEGIN

    IMPORTS
        MODULE-IDENTITY , OBJECT-TYPE, Integer32,  NOTIFICATION-TYPE
            FROM SNMPv2-SMI
        DisplayString,TruthValue
            FROM SNMPv2-TC
        pdn-interfaces
            FROM PDN-HEADER-MIB
        dsx3CurrentEntry ,dsx3IntervalEntry, dsx3TotalEntry
            FROM DS3-MIB
		PerfCurrentCount, PerfIntervalCount, PerfTotalCount
		FROM PerfHist-TC-MIB;


-- ===============================================================
--
--   Ds3/E3 Extentions to the DS3-MIB
--
--  Release: 1.0  05/26/99 (Initial Release) J.Strain
--
--  Last Updated:
--
--
--	This group extends the DS3-MIB.
--
-- ===============================================================
--
--  Extentions to the ATM MIB (RFC 2515)
--
-- ===============================================================

    pdnDs3MIB MODULE-IDENTITY
        LAST-UPDATED "0207050000Z"
        ORGANIZATION "Paradyne Networks
                      MIB Working Group"
        CONTACT-INFO
                      "Paradyne Networks
                       331 Newman Springs Road
                       Red Bank, NJ 07701
                       www.paradyne.com

                       General Comments to: mibwg_team@eng.paradyne.com"

        DESCRIPTION
        "This MIB Module extends the DS3-MIB defined in rfc2496"

        REVISION "0207100000Z"
        DESCRIPTION "M. Mohankumar
		     Changed the index of devDs3FreeRunTable to Augment
		     dsx3TotalEntry."
        REVISION "0207050000Z"
        DESCRIPTION "M. Mohankumar
		     Added devDs3FreeRunTable that has the free running
		     counters for physical performance stats."
        REVISION "0005260000Z"
        DESCRIPTION "J. Strain
				o	add devDs3ConfigTimingMarkerCode
				o	augment the DS3/E3 Near End Group
				o 	 to add EB,ES,SES,PlcpSEFS for current
				o	 , interval and total tables
            o  Initial Release"

        ::= {  pdn-interfaces 14 }

    devDs3Objects    OBJECT IDENTIFIER ::= { pdnDs3MIB 1 }
--    devDs3MIBTraps      OBJECT IDENTIFIER ::= { pdnDs3MIB 2 }
--    devDs3MIBTrapPrefix OBJECT IDENTIFIER ::= { pdnDs3MIB 3 }
--    devDs3MIBConformance OBJECT IDENTIFIER ::= { pdnDs3MIB 4 }


devDs3ConfigTable OBJECT-TYPE
    SYNTAX  SEQUENCE OF DevDs3ConfigEntry
    MAX-ACCESS  not-accessible
    STATUS  current
    DESCRIPTION
           "The Paradyne Ds3-MIB Table Augment."
    ::= { devDs3Objects  1 }

devDs3ConfigEntry OBJECT-TYPE
    SYNTAX  DevDs3ConfigEntry
    MAX-ACCESS  not-accessible
    STATUS  current
    DESCRIPTION
           "An entry in the Paradyne Ds3-MIB Table."
    INDEX   { devDs3ConfigIfIndex }
    ::= { devDs3ConfigTable  1 }

DevDs3ConfigEntry ::=
    SEQUENCE {
    devDs3ConfigIfIndex
        Integer32,

    devDs3ConfigFramingType
        INTEGER,

    devDs3ConfigIgnoreCbit
        INTEGER,

    devDs3ConfigTimingMarkerCode
        INTEGER
    }

devDs3ConfigIfIndex OBJECT-TYPE
    SYNTAX  Integer32
    MAX-ACCESS  read-only
    STATUS  current
    DESCRIPTION
           "The index value which uniquely identifies the
            interface for which this entry contains information
            on interface tests.  The interface identified by a
            particular value of this index is the same interface
            as identified by the same value of ifIndex from the
            Interfaces table of MIB II (RFC 1213)."
    ::= { devDs3ConfigEntry 1 }

devDs3ConfigFramingType OBJECT-TYPE
    SYNTAX  INTEGER {
                 direct(1),	 -- Direct Mapping of ATM Cells into a Ds3 C-Bit Parity Format
                 plcp(2)	 -- PLCP mapping of ATM Cells into a Ds3 C-Bit Parity Format
               }
    MAX-ACCESS  read-write
    STATUS  current
    DESCRIPTION
           "The option provides the support for Direct Mapping or Physicial Layer
            Convergence Protocol (PLCP) mapping of ATM Cells into a Ds3 C-Bit Parity Format"
    ::= { devDs3ConfigEntry  2 }

devDs3ConfigIgnoreCbit OBJECT-TYPE
    SYNTAX  INTEGER {
                 no(1),		-- allow the ability to disable the accumulation
                            -- of C-Bit errors and the generation of C-Bit Alarms
                 yes(2)		-- Do NOT allow the ability to disable the accumulation
                            -- of C-Bit errors and the generation of C-Bit Alarms

               }
    MAX-ACCESS  read-write
    STATUS  current
    DESCRIPTION
           "Since not all networks support the C-Bit, we allow the ability to disable the accumulation
            of C-Bit errors and the generation of C-Bit Alarms."
    ::= { devDs3ConfigEntry  3 }

devDs3ConfigTimingMarkerCode OBJECT-TYPE
    SYNTAX  INTEGER {
                 traceable(1),     	-- Code means: Timing source is traceable to a primary
									--	reference source.

                 notTraceable(2)  	-- Code means: Timing source is not traceable to a primary
									--	 reference	source
               }
    MAX-ACCESS  read-write
    STATUS  current
    DESCRIPTION
           "The option supports the ability to send a 'Timing Marker' code to the far end."
    ::= { devDs3ConfigEntry  4 }

-- ===============================================================
--
--   Augmenting the DS3/E3 NearEnd Current Table ( RFC 2496 )
--
--

devDs3CurrentTable OBJECT-TYPE
    SYNTAX  SEQUENCE OF DevDs3CurrentEntry
    MAX-ACCESS  not-accessible
    STATUS  current
    DESCRIPTION
       "The Paradyne Extension to the Near End Current Table of the DS3-MIB."
    ::= { devDs3Objects 2   }

devDs3CurrentEntry OBJECT-TYPE
    SYNTAX  DevDs3CurrentEntry
    MAX-ACCESS  not-accessible
    STATUS  current
    DESCRIPTION
           "An entry in the Paradyne Extension to the dsx3CurrentTable of the DS3-MIB."
    AUGMENTS { dsx3CurrentEntry }
    ::= { devDs3CurrentTable 1 }

DevDs3CurrentEntry ::=
    SEQUENCE {

    devDs3CurrentEB
            PerfCurrentCount,
    devDs3CurrentES
            PerfCurrentCount,
    devDs3CurrentSES
            PerfCurrentCount,
    devDs3CurrentPlcpSEFS
            PerfCurrentCount

    }


devDs3CurrentEB OBJECT-TYPE
          SYNTAX  PerfCurrentCount
          MAX-ACCESS read-only
          STATUS current
          DESCRIPTION
		"The counter associated with the number of
                Errored Blocks"
          ::= { devDs3CurrentEntry 1}

devDs3CurrentES OBJECT-TYPE

          SYNTAX  PerfCurrentCount
          MAX-ACCESS read-only
          STATUS current
          DESCRIPTION
		"The counter associated with the number of
                Errored Seconds"
          ::= { devDs3CurrentEntry 2}

devDs3CurrentSES OBJECT-TYPE

          SYNTAX  PerfCurrentCount
          MAX-ACCESS read-only
          STATUS current
          DESCRIPTION
		"The counter associated with the number of
                 Severly Errored Seconds"
          ::= { devDs3CurrentEntry 3}

devDs3CurrentPlcpSEFS OBJECT-TYPE

          SYNTAX  PerfCurrentCount
          MAX-ACCESS read-only
          STATUS current
          DESCRIPTION
		"The counter associated with the number of
                PLCP Severely Errored Framing Seconds"
          ::= { devDs3CurrentEntry 4}


-- ===============================================================
--
--   Augmenting the DS3/E3 NearEnd Interval Table ( RFC 2496 )
--
--

devDs3IntervalTable OBJECT-TYPE
    SYNTAX  SEQUENCE OF DevDs3IntervalEntry
    MAX-ACCESS  not-accessible
    STATUS  current
    DESCRIPTION
       "The Paradyne Extension to the Near End Interval Table of the DS3-MIB."
    ::= { devDs3Objects 3 }

devDs3IntervalEntry OBJECT-TYPE
    SYNTAX  DevDs3IntervalEntry
    MAX-ACCESS  not-accessible
    STATUS  current
    DESCRIPTION
           "An entry in the Paradyne Extension to the dsx3IntervalTable of the DS3-MIB."
    AUGMENTS { dsx3IntervalEntry }
    ::= { devDs3IntervalTable 1 }

DevDs3IntervalEntry ::=
    SEQUENCE {

    devDs3IntervalEB
			PerfIntervalCount,
    devDs3IntervalES
			PerfIntervalCount,
    devDs3IntervalSES
			PerfIntervalCount,
    devDs3IntervalPlcpSEFS
			PerfIntervalCount

    }


devDs3IntervalEB OBJECT-TYPE

          SYNTAX  PerfIntervalCount
          MAX-ACCESS read-only
          STATUS current
          DESCRIPTION
		"The counter associated with the number of
                Errored Blocks"
          ::= { devDs3IntervalEntry 1}

devDs3IntervalES OBJECT-TYPE

          SYNTAX  PerfIntervalCount
          MAX-ACCESS read-only
          STATUS current
          DESCRIPTION
		"The counter associated with the number of
                Errored Seconds"
          ::= { devDs3IntervalEntry 2}

devDs3IntervalSES OBJECT-TYPE

          SYNTAX  PerfIntervalCount
          MAX-ACCESS read-only
          STATUS current
          DESCRIPTION
		"The counter associated with the number of
                 Severly Errored Seconds"
          ::= { devDs3IntervalEntry 3}

devDs3IntervalPlcpSEFS OBJECT-TYPE

          SYNTAX  PerfIntervalCount
          MAX-ACCESS read-only
          STATUS current
          DESCRIPTION
		"The counter associated with the number of
                PLCP Severely Errored Framing Seconds"
          ::= { devDs3IntervalEntry 4}

-- ===============================================================
--
--   Augmenting the DS3/E3 NearEnd Total Table ( RFC 2496 )
--
--

devDs3TotalTable OBJECT-TYPE
    SYNTAX  SEQUENCE OF DevDs3TotalEntry
    MAX-ACCESS  not-accessible
    STATUS  current
    DESCRIPTION
       "The Paradyne Extension to the Near End Total Table of the DS3-MIB."
    ::= { devDs3Objects 4 }

devDs3TotalEntry OBJECT-TYPE
    SYNTAX  DevDs3TotalEntry
    MAX-ACCESS  not-accessible
    STATUS  current
    DESCRIPTION
           "An entry in the Paradyne Extension to the dsx3TotalTable of the DS3-MIB."
    AUGMENTS { dsx3TotalEntry }
    ::= { devDs3TotalTable 1 }

DevDs3TotalEntry ::=
    SEQUENCE {

    devDs3TotalEB
            PerfTotalCount,
    devDs3TotalES
            PerfTotalCount,
    devDs3TotalSES
            PerfTotalCount,
    devDs3TotalPlcpSEFS
            PerfTotalCount

    }


devDs3TotalEB OBJECT-TYPE

          SYNTAX  PerfTotalCount
          MAX-ACCESS read-only
          STATUS current
          DESCRIPTION
		"The counter associated with the number of
                Errored Blocks"
          ::= { devDs3TotalEntry 1}

devDs3TotalES OBJECT-TYPE

          SYNTAX  PerfTotalCount
          MAX-ACCESS read-only
          STATUS current
          DESCRIPTION
		"The counter associated with the number of
                Errored Seconds"
          ::= { devDs3TotalEntry 2}

devDs3TotalSES OBJECT-TYPE

          SYNTAX  PerfTotalCount
          MAX-ACCESS read-only
          STATUS current
          DESCRIPTION
		"The counter associated with the number of
                 Severly Errored Seconds"
          ::= { devDs3TotalEntry 3}

devDs3TotalPlcpSEFS OBJECT-TYPE

          SYNTAX  PerfTotalCount
          MAX-ACCESS read-only
          STATUS current
          DESCRIPTION
		"The counter associated with the number of
                PLCP Severely Errored Framing Seconds"
          ::= { devDs3TotalEntry 4}

-- The Paradyne Free Running Statistics Table
--
-- This table contains the performance stats in the form of free running counters
--

devDs3FreeRunTable OBJECT-TYPE
    SYNTAX  SEQUENCE OF DevDs3FreeRunEntry
    MAX-ACCESS  not-accessible
    STATUS  current
    DESCRIPTION
       "The Paradyne Free Running Total of the performance stats."
    ::= { devDs3Objects 5 }

devDs3FreeRunEntry OBJECT-TYPE
    SYNTAX  DevDs3FreeRunEntry
    MAX-ACCESS  not-accessible
    STATUS  current
    DESCRIPTION
       "An entry in the Paradyne Free Running Total Table."
    AUGMENTS { dsx3TotalEntry }
    ::= { devDs3FreeRunTable 1 }

DevDs3FreeRunEntry ::=
    SEQUENCE {
	devDs3FreeRunPES 	PerfTotalCount,
	devDs3FreeRunPSES 	PerfTotalCount,
	devDs3FreeRunPSEFS 	PerfTotalCount,
	devDs3FreeRunUAS 	PerfTotalCount,
	devDs3FreeRunLCV 	PerfTotalCount,
	devDs3FreeRunPCV 	PerfTotalCount,
	devDs3FreeRunLES 	PerfTotalCount,
	devDs3FreeRunCCV 	PerfTotalCount,
	devDs3FreeRunCES 	PerfTotalCount,
	devDs3FreeRunCSES 	PerfTotalCount
    }

devDs3FreeRunPES OBJECT-TYPE
    SYNTAX  PerfTotalCount
    MAX-ACCESS read-only
    STATUS current
    DESCRIPTION
       "The counter associated with the number of
        P bit Errored Seconds."
    ::= { devDs3FreeRunEntry 1 }

devDs3FreeRunPSES OBJECT-TYPE
    SYNTAX  PerfTotalCount
    MAX-ACCESS read-only
    STATUS current
    DESCRIPTION
       "The counter associated with the number of
        P bit Severely Errored Seconds."
    ::= { devDs3FreeRunEntry 2 }

devDs3FreeRunPSEFS OBJECT-TYPE
    SYNTAX  PerfTotalCount
    MAX-ACCESS read-only
    STATUS current
    DESCRIPTION
       "The counter associated with the number of
        Severely Errored Frame Seconds."
    ::= { devDs3FreeRunEntry 3 }

devDs3FreeRunUAS OBJECT-TYPE
    SYNTAX  PerfTotalCount
    MAX-ACCESS read-only
    STATUS current
    DESCRIPTION
       "The counter associated with the number of
        Unavailable Seconds."
    ::= { devDs3FreeRunEntry 4 }

devDs3FreeRunLCV OBJECT-TYPE
    SYNTAX  PerfTotalCount
    MAX-ACCESS read-only
    STATUS current
    DESCRIPTION
       "The counter associated with the number of
        Line Coding Violations."
    ::= { devDs3FreeRunEntry 5 }

devDs3FreeRunPCV OBJECT-TYPE
    SYNTAX  PerfTotalCount
    MAX-ACCESS read-only
    STATUS current
    DESCRIPTION
       "The counter associated with the number of
        P bit Coding Violations."
    ::= { devDs3FreeRunEntry 6 }

devDs3FreeRunLES OBJECT-TYPE
    SYNTAX  PerfTotalCount
    MAX-ACCESS read-only
    STATUS current
    DESCRIPTION
       "The counter associated with the number of
        Line Erroed Seconds."
    ::= { devDs3FreeRunEntry 7 }

devDs3FreeRunCCV OBJECT-TYPE
    SYNTAX  PerfTotalCount
    MAX-ACCESS read-only
    STATUS current
    DESCRIPTION
       "The counter associated with the number of
        C bit Coding Violations."
    ::= { devDs3FreeRunEntry 8 }

devDs3FreeRunCES OBJECT-TYPE
    SYNTAX  PerfTotalCount
    MAX-ACCESS read-only
    STATUS current
    DESCRIPTION
       "The counter associated with the number of
        C bit Errored Seconds."
    ::= { devDs3FreeRunEntry 9 }

devDs3FreeRunCSES OBJECT-TYPE
    SYNTAX  PerfTotalCount
    MAX-ACCESS read-only
    STATUS current
    DESCRIPTION
       "The counter associated with the number of
        C bit Severly Errored Seconds."
    ::= { devDs3FreeRunEntry 10 }

END
