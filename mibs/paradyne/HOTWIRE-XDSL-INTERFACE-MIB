HOTWIRE-XDSL-INTERFACE-MIB DEFINITIONS ::= BEGIN

 --  Version : 1.7

 --  Last Updated :     01/11/00 Rajesh Gowda (IDSL changes to Atl3.1/4.0)
 --  Last Updated :     10/20/99 Wayne Jadoo (use the PDN-HEADER-MIB)
 --  Last Updated :     04/21/99 Rajesh Gowda (GSI 3.2 CAP, Atlantis Rel 2.1)
 --  Last Updated :     01/04/99 Rajesh Gowda (For Atlantis Rel 2.0)
 --  Last Updated :     11/10/98 Rajesh Gowda (For Atlantis Rel 2.0)
 --  Last Updated :     8/13/98 Rajesh Gowda (For Atlantis Rel 1.1)
 --  Last Updated :     6/02/98 Wayne Jadoo ( For Sumatra 2.3)
 --  Last Updated :     3/16/98  J.Strain ( for SN traps )
 --  Last Updated :     3/12/98  Rajesh Gowda (For CAP changes and MVL Rel 1.0)
 --  Last Updated :     02/03/98   Sachin Kamat (For Atlantis Release 1)
 --  Last Updated :     11/18/97  Gerard Lowry (For Sumatra/Midway Release 2)
 --  Last Updated :     11/7/97  Gene Zhu (For Sumatra/Midway Release 2)
 --  Last Updated :     8/25/97  Sachin Kamat (For Sumatra)
 --  Last Updated :     7/14/97  Prakash Easwar (For Sumatra)
 --  Last Updated :     7/9/97  Perry Wintner (For Midway)
 --  Last Updated :     5/5/97  Prakash Easwar (For Tonga)
 --  Updated By :       7/22/96  Gerard Lowry (For Bora-Bora)
 --  Created by:         Dave Arneson
 --                      Manu Kaycee


IMPORTS

   Counter, TimeTicks
    FROM RFC1155-SMI
   OBJECT-TYPE
     FROM RFC-1212
   TRAP-TYPE
     FROM RFC-1215
   ifIndex
     FROM RFC1213-MIB
   xdsl
     FROM PDN-HEADER-MIB
   pdnPortConfigVNID
     FROM HOT-DOMAIN-MIB;

 -- The Paradyne enterprise xDSL MIB. This MIB is written
 -- specifically to facilitate in the management of the
 -- xDSL interface on the device
 -- as long as a standard MIB for managing
 -- xDSL interfaces is not available.

 -- History
 -- 9/3/96
 --   1. Changed the trap numbers so that they are unique
 --      across all the hotwire MIBS.
 --   2. Changed the position of xdslDevice under the xdsl
 --      sub-tree.
 -- 10/6/96
 --   1. Changed the enum values for the
 --      xdslDevIfConfigReedSolomonDownForwardErrorCorrection object
 --      because the interpretation of this object has changed.
 --   2. Made minor corrections to objects for compilation purposes.
 --   3. Changed top-level oids to represent the "New Paradyne"
 -- 10/28/96
 --   1. Changed the Syntax for the Objects
 --       xdslDevIfStatsCentralRecErrorRate
 --       xdslDevIfStatsCentralRecErrorRate
 --      to OCTET STRING. This is because the
 --      value represented by these objects are floating point
 --      numbers
 --   2. changed the enterprise for traps to the MIB OID in which they
 --      are defined. This was decided in a MWG meeting
 -- 11/4/96
 --   1. Replaced "OCTET STRING" with DisplayString as all the objects
 --      with the OCTET STRING syntax are printable.
 -- 11/11/96
 --   1. Added SIZE to Object xdslDevIfConfigPortID (40 characters)
 --   2. Changed the name of xdslDevIfConfigEstimatedErrorRateThreshold
 --      to xdslDevIfConfigEstimatedHrErrRateThreshold
 --   3. added a new object
 --        xdslDevIfConfigEstimatedDayErrRateThreshold
 -- 12/13/96
 --    1. Changed the description for the following objects
 --        xdslDevIfStatsCentralRecErrorRate
 --        xdslDevIfStatsRemoteRecErrorRate
 -- 1/7/97
 --   1. Changed the definition of the following
 --         xdslDevIfStatsInterval
 -- 1/31/97
 --   1. Changed the description of the following objects
 --        xdslDevIfConfigPortSpeedBehaviour OBJECT-TYPE
 --        xdslDevIfConfigUpFixedPortSpeed
 --        xdslDevIfConfigDownFixedPortSpeed
 --        xdslDevIfConfigUpAdaptiveUpperBoundPortSpeed
 --        xdslDevIfConfigUpAdaptiveLowerBoundPortSpeed
 --        xdslDevIfConfigDownAdaptiveUpperBoundPortSpeed
 --        xdslDevIfConfigDownAdaptiveLowerBoundPortSpeed
 --        xdslDevIfLinkUpDownTransitionThreshold
 --        xdslDevIfConfigEstimatedDayErrRateThreshold
 --        xdslDevIfConfigEstimatedHrErrRateThreshold
 --        xdslDevIfConfigMarginThreshold
 --   2. Added a new object
 --        xdslDevIfConfigStartUpMargin
 -- 5/5/97
 --   1. Changed the description of the following objects
 --        xdslDevIfConfigMarginThreshold
 --        xdslDevIfConfigEstimatedHrErrRateThreshold
 --        xdslDevIfConfigEstimatedDayErrRateThreshold
 --        xdslDevIfLinkUpDownTransitionThreshold
 --        xdslDevIfConfigStartUpMargin
 -- 6/5/97
 --   1. Added the following objects to the XdslDevIfIntervalStatsEntry
 --      for Midway
 --        xdslDevIfStatsRemoteRecErroredMinutes
 --        xdslDevIfStatsRemoteRecSeverelyErroredMinutes
 --        xdslDevIfStatsCentralRecErroredMinutes
 --        xdslDevIfStatsCentralRecSeverelyErroredMinutes
 --
 -- 6/26/97
 --   1. Added the following objects to the XdslDevIfIntervalStatsEntry
 --      for Midway
 --        xdslDevIfStatsCentralReceivedOctets
 --        xdslDevIfStatsCentralTransmittedOctets
 --   2. Added the xdslRemoteSys group to the mib for Midway (endpoints
 --      without their own SNMP agent)
 -- 7/9/97
 --   1. Fixed description of XdslRemoteSys objects to refer to mib-2 system
 --      MIB descriptions.
 --
 -- 7/13/97
 --   1. Appended to the description of the following object
 --           xdslDevIfStatsUpStreamSpeed
 --
 -- 8/14/97
 --   1. Following objects have new enums and descriptions:
 --         xdslDevIfConfigUpFixedPortSpeed
 --         xdslDevIfConfigDownFixedPortSpeed
 --         xdslDevIfConfigUpAdaptiveUpperBoundPortSpeed
 --         xdslDevIfConfigUpAdaptiveLowerBoundPortSpeed
 --         xdslDevIfConfigDownAdaptiveUpperBoundPortSpeed
 --         xdslDevIfConfigDownAdaptiveLowerBoundPortSpeed
 --         xdslDevIfConfigReedSolomonDownForwardErrorCorrection
 --   2. New object added to xdslDevIfConfigTable for :
 --         xdslDevIfConfigTxPowerAttenuation
 --   3. New enum added to following object:
 --         xdslDevIfConfigReedSolomonDownForwardErrorCorrection
 --
 -- 8/25/97
 --   1. To add xdslRtuTypeMismatch and xdslRtuTypeMismatchClear
 --      trap.
 --
 -- 11/7/97
 --   1. Added the following traps
 --         xdslRtuCommunityNameDeleteFail
 --         xdslRtuRemoteServiceDomainDeleteFail
 --         xdslRtuTrapManagerDeleteFail
 --         xdslRtuStaticRouteDeleteFail
 --         xdslRtuCommunityNameInjectFail
 --         xdslRtuRemoteServiceDomainInjectFail
 --         xdslRtuTrapManagerInjectFail
 --         xdslRtuStaticRouteInjectFail
 --
 --
 -- 11/18/97
 --   1. Added group xdslRemoteDTEStatus for Donzi endpoint support
 --   2. Added the following trap
 --         xdslRtuSelfTestFail
 --  2/3/98
 --  1. To add the Atlantis RTU Last Gasp Trap "xdslRtuLastGasp".
 --
 -- 03/12/98
 --   1. Added a new group xdslDevMvlIfConfig for Atlantis MVL Rel 1.0
 --   2. For CAP changes
 --      a. Added new port speeds s1024, s896, s768, s512, s384, s256
 --         to the following objects :
 --         xdslDevIfConfigDownFixedPortSpeed
 --         xdslDevIfConfigDownAdaptiveUpperBoundPortSpeed
 --         xdslDevIfConfigDownAdaptiveLowerBoundPortSpeed
 --      b. Changed the desc. of xdslDevIfConfigTxPowerAttenuation
 --      c. Added new object xdslDevIfConfigSnTxPowerAttenuation
 --
 --  03/16/98
 --    1. Added 3 new SN traps for Atlantis
 --
 --   06/01/98
 --      Added xdslEnhancedLinkUpTrap
 --      Added RemoteSysCircuitId To the xdslRemoteSys Group
 --      Added a new xdslLinkUpDownInformation Group

 --  06/01/98
 --    1. Added a new 'xdslDevNAPCustomerAccount' group for accounting
 --       pure customer data only, i.e excluding LMC messages, test packets,
 --       errors etc,. for Network Access providers. This table is indexed
 --       by 2 indices, dsl port and interval(i.e current day and previous day)
 --
 --  06/01/98
 --     Changed enumerated data type from 'nonIntervalBased' to
 --     'previousDay' in  xdslDevIfStatsTable. This enty will
 --     have the statistics counted for previous 24 hours/calendar day,
 --     staring at 12 midnight.
 --
 --  8/14/98 - rgowda
 --     Changed the description and object names of the following objects.
 --     1. xdslDevIfStatsCentralReceivedOctets
 --     2. xdslDevIfStatsCentralTransmittedOctets
 --     3. xdslDevIfStatsRemoteReceivedOctets
 --     4. xdslDevIfStatsRemoteTransmittedOctets
 --     TO
 --     1. xdslDevIfStatsCentralReceivedKiloOctets
 --     2. xdslDevIfStatsCentralTransmittedKiloOctets
 --     3. xdslDevIfStatsRemoteReceivedKiloOctets
 --     4. xdslDevIfStatsRemoteTransmittedKiloOctets
 --
 --     Changed the description of the following objects.
 --     5. xdslDevNAPCustomerAccountRecKiloOctets
 --     6. xdslDevNAPCustomerAccountTrxKiloOctets
 --
 --  11/10/98 rgowda
 --    1. Added following 2 SN traps for Atlantis 2.0
 --       a. xdslRemoteInjectionFailureTrap
 --       b. xdslRemoteInjectionIncompatibleTrap
 --
 --   2. Deleted the following traps
 --         xdslRtuCommunityNameDeleteFail
 --         xdslRtuRemoteServiceDomainDeleteFail
 --         xdslRtuTrapManagerDeleteFail
 --         xdslRtuStaticRouteDeleteFail
 --         xdslRtuCommunityNameInjectFail
 --         xdslRtuRemoteServiceDomainInjectFail
 --         xdslRtuTrapManagerInjectFail
 --         xdslRtuStaticRouteInjectFail
 --
 --    3.  Added xdslRemoteInjection group
 --
 --  01/04/99 rgowda
 --    Changed the description and value range of the object
 --    xdslDevIfConfigMarginThreshold
 --
 --  04/21/99 rgowda
 --    1. Changed the description and value range of the object
 --       xdslDevIfConfigTxPowerAttenuation
 --    2. Added two new objects into xdslDevMvlIfConfigTable
 --       xdslDevMvlIfConfigOnHookTxPowerAttenuation
 --       xdslDevMvlIfConfigOffHookTxPowerAttenuation
 --    3. More enumerations/port speeds into the objects
 --       xdslDevIfConfigUpFixedPortSpeed
 --       xdslDevIfConfigUpAdaptiveUpperBoundPortSpeed
 --       xdslDevIfConfigUpAdaptiveLowerBoundPortSpeed
 --
 --	 10/20/99 Wayne Jadoo
 --       Added Imports from PDN-HEADER-MIB and
 --       added import for Timeticks.
 --
 --  01/11/00 Rajesh Gowda
 --       Added xdslDevIDSLConfig group
 --       Added Trap xdslLossOfNetworkTimingSignalTrap
 --
 --  04/27/00 Prakash Easwar
 --
 --  1) added three new objects to
 --
 --     xdslDevIfIntervalStatsTable
 --
 --         xdslDevIfStatsCentralTransmittedPkts
 --         xdslDevIfStatsCentralReceivedPkts
 --         xdslDevIfStatsCentralErrPkts
 --
 --   2) Deprecated objects
 --
 --      xdslRemoteInjectionType
 --
 --   3) deprecated traps
 --        xdslRemoteInjectionFailureTrap
 --        xdslRemoteInjectionIncompatibleTrap
 --
 --   added new speeds (enums) to the following objects
 --
 --     xdslDevIfConfigUpFixedPortSpeed
 --     xdslDevIfConfigDownFixedPortSpeed

 --   END OF COMMENTS

 xdslDevice       OBJECT IDENTIFIER ::= {  xdsl 1 }

 -- textual conventions

 DisplayString ::=
   OCTET STRING
  -- This data type is used to model textual information
  -- taken from the NVT ASCII character set.  By convention,
  -- objects with this syntax are declared as having
  -- SIZE (0..255)

  --      All groups within the MIB are mandatory.

 xdslDevIfStats     OBJECT IDENTIFIER ::= { xdslDevice 1 }

 xdslDevIfConfig  OBJECT IDENTIFIER ::= { xdslDevice 2 }

 xdslRemoteSys  OBJECT IDENTIFIER ::= { xdslDevice 3 }

 xdslRemoteDTEStatus  OBJECT IDENTIFIER ::= { xdslDevice 4 }

 xdslDevMvlIfConfig  OBJECT IDENTIFIER ::= { xdslDevice 5 }

 xdslDevNAPCustomerAccount  OBJECT IDENTIFIER ::= { xdslDevice 6 }

 xdslLinkUpDownInformation  OBJECT IDENTIFIER ::= { xdslDevice 7 }

 xdslRemoteInjection  OBJECT IDENTIFIER ::= { xdslDevice 8 }

 xdslDevIDSLConfig  OBJECT IDENTIFIER ::= { xdslDevice 9 }

 --  The xdslDevIfStats group. The implementation of this group is
 --  mandatory.

 xdslDevIfIntervalStatsTable OBJECT-TYPE
   SYNTAX SEQUENCE OF XdslDevIfIntervalStatsEntry
   ACCESS not-accessible
   STATUS mandatory
   DESCRIPTION
     "The xdslIfStatsTable provides statistics specific to the xDSL
      link. Statistics are collected on a per port basis and
      on specified intervals. Hence as such this table is
      indexed by the xdslDevIfStatsIfIndex and
      xdslDevIfStatsInterval. Also Statistics are grouped
      into remote and central statistics. By 'remote' we mean the
      statistics collected by the device at the customer premises
      and by 'central' we mean the statistics collected by the
      device located at the central office. The objects which
      are not grouped into these two groups are related to both
      ends of the xDSL link."
 ::= { xdslDevIfStats 1 }

 xdslDevIfIntervalStatsEntry OBJECT-TYPE
   SYNTAX XdslDevIfIntervalStatsEntry
   ACCESS not-accessible
   STATUS mandatory
   DESCRIPTION
     "Describes a specific xDSL satistics entry."
   INDEX { xdslDevIfStatsIfIndex,
           xdslDevIfStatsInterval }
 ::= { xdslDevIfIntervalStatsTable 1 }

 XdslDevIfIntervalStatsEntry ::=
   SEQUENCE {
     xdslDevIfStatsIfIndex
       INTEGER,
     xdslDevIfStatsInterval
       INTEGER,
     xdslDevIfStatsValid15MinuteIntervalCount
       Counter,
     xdslDevIfStatsElapsedTimeLinkUp
       Counter,
     xdslDevIfStatsLinkDownCount
       Counter,
     xdslDevIfStatsUpStreamSpeed
       INTEGER,
     xdslDevIfStatsCentralReceiverGain
       INTEGER,
     xdslDevIfStatsCentralRecMargin
       INTEGER,
     xdslDevIfStatsCentralRecAttenuationEstimate
       INTEGER,
     xdslDevIfStatsCentralRecTransmitPower
       INTEGER,
     xdslDevIfStatsCentralRecErrorRate
       DisplayString (SIZE (1..32)),
     xdslDevIfStatsCentralRecErroredSeconds
       INTEGER,
     xdslDevIfStatsCentralRecSeverelyErroredSeconds
       INTEGER,
     xdslDevIfStatsRemoteReceiverGain
       INTEGER,
     xdslDevIfStatsRemoteRecMargin
       INTEGER,
     xdslDevIfStatsRemoteRecAttenuationEstimate
       INTEGER,
     xdslDevIfStatsRemoteRecTransmitPower
       INTEGER,
     xdslDevIfStatsRemoteRecErrorRate
       DisplayString (SIZE (1..32)),
     xdslDevIfStatsRemoteRecErroredSeconds
       INTEGER,
     xdslDevIfStatsRemoteRecSeverelyErroredSeconds
       INTEGER,
     xdslDevIfStatsRemoteOctetsCorrected
       Counter,
     xdslDevIfStatsRemoteOctetsNotCorrected
       Counter,
     xdslDevIfStatsRemoteReceivedKiloOctets
       Counter,
     xdslDevIfStatsRemoteReceivedPkts
       Counter,
     xdslDevIfStatsRemoteRecErrPkts
       Counter,
     xdslDevIfStatsRemoteDroppedPkts
       Counter,
     xdslDevIfStatsRemoteTransmittedKiloOctets
       Counter,
     xdslDevIfStatsRemoteTransmittedPkts
       Counter,
     xdslDevIfStatsCentralRecErroredMinutes
       INTEGER,
     xdslDevIfStatsCentralRecSeverelyErroredMinutes
       INTEGER,
     xdslDevIfStatsRemoteRecErroredMinutes
       INTEGER,
     xdslDevIfStatsRemoteRecSeverelyErroredMinutes
       INTEGER,
     xdslDevIfStatsCentralReceivedKiloOctets
       Counter,
     xdslDevIfStatsCentralTransmittedKiloOctets
       Counter,
     xdslDevIfStatsCentralTransmittedPkts
       Counter,
     xdslDevIfStatsCentralReceivedPkts
       Counter,
     xdslDevIfStatsCentralErrPkts
       Counter
}

 xdslDevIfStatsIfIndex OBJECT-TYPE
   SYNTAX INTEGER
   ACCESS read-only
   STATUS mandatory
   DESCRIPTION
     "The value of this object corresponds directly to each
      DSL interface as described in ifTable."
 ::= { xdslDevIfIntervalStatsEntry 1 }

 xdslDevIfStatsInterval OBJECT-TYPE
   SYNTAX INTEGER {
     first15MinuteSlice (1),
     second15MinuteSlice (2),
     third15MinuteSlice (3),
     fourth15MinuteSlice (4),
     currentHour (5),
	  current15Minutes (6),
	  hour1of24hrs (7),
	  hour2of24hrs (8),
	  hour3of24hrs (9),
	  hour4of24hrs (10),
	  hour5of24hrs (11),
	  hour6of24hrs (12),
	  hour7of24hrs (13),
	  hour8of24hrs (14),
	  hour9of24hrs (15),
	  hour10of24hrs (16),
	  hour11of24hrs (17),
	  hour12of24hrs (18),
	  hour13of24hrs (19),
	  hour14of24hrs (20),
	  hour15of24hrs (21),
	  hour16of24hrs (22),
	  hour17of24hrs (23),
	  hour18of24hrs (24),
	  hour19of24hrs (25),
	  hour20of24hrs (26),
	  hour21of24hrs (27),
	  hour22of24hrs (28),
	  hour23of24hrs (29),
	  hour24of24hrs (30),
     current24Hours (31),
     previousDay (32)
   }
   ACCESS read-only
   STATUS mandatory
   DESCRIPTION
     "The value of this object corresponds to the
      interval of time during which statistics were
      collected. previousDay(32) will have the statistics
      collected from 12 midnight previous calendar day "
 ::= { xdslDevIfIntervalStatsEntry 2 }

 xdslDevIfStatsValid15MinuteIntervalCount OBJECT-TYPE
   SYNTAX Counter
   ACCESS read-only
   STATUS mandatory
   DESCRIPTION
     "Reflects the number of 15 minute intervals
      during which link was up and statistics were
      received from the remote end"
 ::= { xdslDevIfIntervalStatsEntry 3 }

 xdslDevIfStatsElapsedTimeLinkUp OBJECT-TYPE
   SYNTAX Counter
   ACCESS read-only
   STATUS mandatory
   DESCRIPTION
     "Reflects the elapsed time since the link was up."
 ::= { xdslDevIfIntervalStatsEntry 4 }

 xdslDevIfStatsLinkDownCount OBJECT-TYPE
   SYNTAX Counter
   ACCESS read-only
   STATUS mandatory
   DESCRIPTION
     "Reflects the number of times that the xDSL link has gone to a
      down state. This may be due to shutting down of the
      customers side of the link. It could also be due to error
      conditions which result in the going down. A large number of
      these per unit time (synchronized off sysUpTime) would be
      indicative of an error condition."
 ::= { xdslDevIfIntervalStatsEntry 5 }

 xdslDevIfStatsUpStreamSpeed OBJECT-TYPE
   SYNTAX INTEGER
   ACCESS read-only
   STATUS mandatory
   DESCRIPTION
     "The speed in the upstream (from the remote
      to the central site) direction. This object
      compliments the ifSpeed object in the ifTable which
      represents the speed in the downstream (from the
      central to the remote site) direction. The speed
      is measured in bits per second."
 ::= { xdslDevIfIntervalStatsEntry 6 }

 xdslDevIfStatsCentralReceiverGain OBJECT-TYPE
   SYNTAX INTEGER
   ACCESS read-only
   STATUS mandatory
   DESCRIPTION
     "Reflects the receiver gain at  the central site."
 ::= { xdslDevIfIntervalStatsEntry 7 }

 xdslDevIfStatsCentralRecMargin OBJECT-TYPE
   SYNTAX INTEGER
   ACCESS read-only
   STATUS mandatory
   DESCRIPTION
     "Reflects the margin at the central site."
 ::= { xdslDevIfIntervalStatsEntry 8 }

 xdslDevIfStatsCentralRecAttenuationEstimate OBJECT-TYPE
   SYNTAX INTEGER
   ACCESS read-only
   STATUS mandatory
   DESCRIPTION
     "Reflects the attenuation estimate at the central site."
 ::= { xdslDevIfIntervalStatsEntry 9 }

 xdslDevIfStatsCentralRecTransmitPower OBJECT-TYPE
   SYNTAX INTEGER
   ACCESS read-only
   STATUS mandatory
   DESCRIPTION
     "Reflects the transmit power at the central site."
 ::= { xdslDevIfIntervalStatsEntry 10 }

 xdslDevIfStatsCentralRecErrorRate OBJECT-TYPE
   SYNTAX  DisplayString (SIZE(1..32))
   ACCESS read-only
   STATUS mandatory
   DESCRIPTION
     "Reflects the error rate at the central site. This string
      will represent a floating point number of the form.
		[ErrRate][eE][+-][ErrRateBase] where ErrRate and ErrRateBase
		are integers. In Other Words
			ErrRate * [10^ -ErrRateBase]
      shown below are example of the values returned.
            123456E-5 = 1.23456
            344567e-6 = 0.344567"
 ::= { xdslDevIfIntervalStatsEntry 11 }

 xdslDevIfStatsCentralRecErroredSeconds OBJECT-TYPE
   SYNTAX INTEGER
   ACCESS read-only
   STATUS mandatory
   DESCRIPTION
     "Reflects the errored seconds at the central site."
 ::= { xdslDevIfIntervalStatsEntry 12 }

 xdslDevIfStatsCentralRecSeverelyErroredSeconds OBJECT-TYPE
   SYNTAX INTEGER
   ACCESS read-only
   STATUS mandatory
   DESCRIPTION
     "Reflects the severely errored seconds at the central site."
 ::= { xdslDevIfIntervalStatsEntry 13 }

 xdslDevIfStatsRemoteReceiverGain OBJECT-TYPE
   SYNTAX INTEGER
   ACCESS read-only
   STATUS mandatory
   DESCRIPTION
     "Reflects the receiver gain at the remote site"
 ::= { xdslDevIfIntervalStatsEntry 14 }

 xdslDevIfStatsRemoteRecMargin OBJECT-TYPE
   SYNTAX INTEGER
   ACCESS read-only
   STATUS mandatory
   DESCRIPTION
     "Reflects the margin at the remote site"
 ::= { xdslDevIfIntervalStatsEntry 15 }

 xdslDevIfStatsRemoteRecAttenuationEstimate OBJECT-TYPE
   SYNTAX INTEGER
   ACCESS read-only
   STATUS mandatory
   DESCRIPTION
     "Reflects the attenuation estimate at the remote site"
 ::= { xdslDevIfIntervalStatsEntry 16 }

 xdslDevIfStatsRemoteRecTransmitPower OBJECT-TYPE
   SYNTAX INTEGER
   ACCESS read-only
   STATUS mandatory
   DESCRIPTION
     "Reflects the transmit power at the remote site."
 ::= { xdslDevIfIntervalStatsEntry 17 }

 xdslDevIfStatsRemoteRecErrorRate OBJECT-TYPE
   SYNTAX  DisplayString (SIZE(1..32))
   ACCESS read-only
   STATUS mandatory
   DESCRIPTION
     "Reflects the error rate at the remote site. This string
      will represent a floating point number of the form a.b.
		[ErrRate][eE][+-][ErrRateBase] where ErrRate and ErrRateBase
		are integers. In Other Words
			ErrRate * [10^ -ErrRateBase]
      shown below are example of the values returned.
            123456E-5 = 1.23456
            344567e-6 = 0.344567"
 ::= { xdslDevIfIntervalStatsEntry 18 }

 xdslDevIfStatsRemoteRecErroredSeconds OBJECT-TYPE
   SYNTAX INTEGER
   ACCESS read-only
   STATUS mandatory
   DESCRIPTION
     "Reflects the errored seconds at the remote site."
 ::= { xdslDevIfIntervalStatsEntry 19 }

 xdslDevIfStatsRemoteRecSeverelyErroredSeconds OBJECT-TYPE
   SYNTAX INTEGER
   ACCESS read-only
   STATUS mandatory
   DESCRIPTION
     "Reflects the severely errored seconds at the remote site."
 ::= { xdslDevIfIntervalStatsEntry 20 }

 xdslDevIfStatsRemoteOctetsCorrected OBJECT-TYPE
   SYNTAX Counter
   ACCESS read-only
   STATUS mandatory
   DESCRIPTION
     "This object reflects the number of octets corrected
      when reed-solomon is turned on at the remote site."
 ::= { xdslDevIfIntervalStatsEntry 21 }

 xdslDevIfStatsRemoteOctetsNotCorrected OBJECT-TYPE
   SYNTAX Counter
   ACCESS read-only
   STATUS mandatory
   DESCRIPTION
     "This object reflects the number of octets not corrected
      when reed-solomon is turned on at the remote site."
 ::= { xdslDevIfIntervalStatsEntry 22 }

 xdslDevIfStatsRemoteReceivedKiloOctets OBJECT-TYPE
   SYNTAX Counter
   ACCESS read-only
   STATUS mandatory
   DESCRIPTION
     "The number of octets that have been received by the xDSL
      interface at the  remote site divided by 1000."
 ::= { xdslDevIfIntervalStatsEntry 23 }

 xdslDevIfStatsRemoteReceivedPkts OBJECT-TYPE
   SYNTAX Counter
   ACCESS read-only
   STATUS mandatory
   DESCRIPTION
     "The number of good packets that have been received by
      the xDSL interface at the remote site."
 ::= { xdslDevIfIntervalStatsEntry 24 }

 xdslDevIfStatsRemoteRecErrPkts OBJECT-TYPE
   SYNTAX Counter
   ACCESS read-only
   STATUS mandatory
   DESCRIPTION
     "Reflects the number packet receive with error by the xDSL
      interface at the remote site."
 ::= {xdslDevIfIntervalStatsEntry 25 }

 xdslDevIfStatsRemoteDroppedPkts OBJECT-TYPE
   SYNTAX Counter
   ACCESS read-only
   STATUS mandatory
   DESCRIPTION
     "Reflects the number of good packets that have been
      received by the xDSL interface at the remote site,
      but have been dropped due to insufficient buffer capacity."
 ::= { xdslDevIfIntervalStatsEntry 26 }

 xdslDevIfStatsRemoteTransmittedKiloOctets OBJECT-TYPE
   SYNTAX Counter
   ACCESS read-only
   STATUS mandatory
   DESCRIPTION
     "The number of octets that have been transmitted by the
      xDSL interface at the remote site divided by 1000."
 ::= { xdslDevIfIntervalStatsEntry 27 }

 xdslDevIfStatsRemoteTransmittedPkts OBJECT-TYPE
   SYNTAX Counter
   ACCESS read-only
   STATUS mandatory
   DESCRIPTION
     "The number of pkts that have been transmitted by the
      xDSL interface at the remote site."
 ::= { xdslDevIfIntervalStatsEntry 28 }

 xdslDevIfStatsCentralRecErroredMinutes OBJECT-TYPE
   SYNTAX INTEGER
   ACCESS read-only
   STATUS mandatory
   DESCRIPTION
     "Reflects the errored minutes at the central site."
 ::= { xdslDevIfIntervalStatsEntry 29 }

 xdslDevIfStatsCentralRecSeverelyErroredMinutes OBJECT-TYPE
   SYNTAX INTEGER
   ACCESS read-only
   STATUS mandatory
   DESCRIPTION
     "Reflects the severely errored minutes at the central site."
 ::= { xdslDevIfIntervalStatsEntry 30 }

 xdslDevIfStatsRemoteRecErroredMinutes OBJECT-TYPE
   SYNTAX INTEGER
   ACCESS read-only
   STATUS mandatory
   DESCRIPTION
     "Reflects the errored minutes at the remote site."
 ::= { xdslDevIfIntervalStatsEntry 31 }

 xdslDevIfStatsRemoteRecSeverelyErroredMinutes OBJECT-TYPE
   SYNTAX INTEGER
   ACCESS read-only
   STATUS mandatory
   DESCRIPTION
     "Reflects the severely errored minutes at the remote site."
 ::= { xdslDevIfIntervalStatsEntry 32 }

 xdslDevIfStatsCentralReceivedKiloOctets OBJECT-TYPE
   SYNTAX Counter
   ACCESS read-only
   STATUS mandatory
   DESCRIPTION
     "The number of octets that have been received by the xDSL
      interface at the central site divided by 1000."
 ::= { xdslDevIfIntervalStatsEntry 33 }

 xdslDevIfStatsCentralTransmittedKiloOctets OBJECT-TYPE
   SYNTAX Counter
   ACCESS read-only
   STATUS mandatory
   DESCRIPTION
     "The number of octets that have been transmitted by the
      xDSL interface at the central site divided by 1000."
 ::= { xdslDevIfIntervalStatsEntry 34 }

 xdslDevIfStatsCentralTransmittedPkts OBJECT-TYPE
   SYNTAX Counter
   ACCESS read-only
   STATUS mandatory
   DESCRIPTION
     "The number of packets that have been transmitted by the
      xDSL interface at the central site."
 ::= { xdslDevIfIntervalStatsEntry 35 }

 xdslDevIfStatsCentralReceivedPkts OBJECT-TYPE
   SYNTAX Counter
   ACCESS read-only
   STATUS mandatory
   DESCRIPTION
     "The number of packets that have been received by the
      xDSL interface at the central site."
 ::= { xdslDevIfIntervalStatsEntry 36 }

 xdslDevIfStatsCentralErrPkts OBJECT-TYPE
   SYNTAX Counter
   ACCESS read-only
   STATUS mandatory
   DESCRIPTION
     "The number of packets that have been received by the
      xDSL interface at the central site with error."
 ::= { xdslDevIfIntervalStatsEntry 37 }

 -- The xdslDevIFConfig group. Implementation of this group is
 -- mandatory for RADSL.

 xdslDevIfConfigTable OBJECT-TYPE
   SYNTAX SEQUENCE OF XdslDevIfConfigEntry
   ACCESS not-accessible
   STATUS mandatory
   DESCRIPTION
     "The xdslDevIfConfigTable provides config information specific
      to a xDSL device, or system. The table is indexed by an
      object which corresponds to ifIndex. These ifIndex entries,
      themselves, denote and identify specific xdsl interfaces on
      the board or module. Also the configuration parameters are
      grouped into two broad categories, 'up' and 'down'. 'up'
      reflects the upstream direction (from the customer premises
      to the central office). 'Down' reflects the downstream
      direction (from the central office to the customer premises)"
 ::= { xdslDevIfConfig 1 }

 xdslDevIfConfigEntry OBJECT-TYPE
   SYNTAX XdslDevIfConfigEntry
   ACCESS not-accessible
   STATUS mandatory
   DESCRIPTION
     "Describes a specific xDSL interface entry."
   INDEX { xdslDevIfConfigIfIndex }
 ::= { xdslDevIfConfigTable 1 }

 XdslDevIfConfigEntry ::=
   SEQUENCE {
     xdslDevIfConfigIfIndex
       INTEGER,
     xdslDevIfConfigPortSpeedBehaviour
       INTEGER,
     xdslDevIfConfigUpFixedPortSpeed
       INTEGER,
     xdslDevIfConfigDownFixedPortSpeed
       INTEGER,
     xdslDevIfConfigUpAdaptiveUpperBoundPortSpeed
       INTEGER,
     xdslDevIfConfigUpAdaptiveLowerBoundPortSpeed
       INTEGER,
     xdslDevIfConfigDownAdaptiveUpperBoundPortSpeed
       INTEGER,
     xdslDevIfConfigDownAdaptiveLowerBoundPortSpeed
       INTEGER,
     xdslDevIfConfigReedSolomonDownForwardErrorCorrection
       INTEGER,
     xdslDevIfConfigMarginThreshold
       INTEGER,
     xdslDevIfConfigEstimatedHrErrRateThreshold
       INTEGER,
     xdslDevIfConfigEstimatedDayErrRateThreshold
       INTEGER,
     xdslDevIfConfigPortID
       DisplayString (SIZE (1..40)),
     xdslDevIfLinkUpDownTransitionThreshold
       INTEGER,
     xdslDevIfConfigStartUpMargin
       INTEGER (-3..9),
     xdslDevIfConfigTxPowerAttenuation
       INTEGER,
     xdslDevIfConfigSnTxPowerAttenuation
       INTEGER
  }

 xdslDevIfConfigIfIndex OBJECT-TYPE
   SYNTAX INTEGER
   ACCESS read-only
   STATUS mandatory
   DESCRIPTION
     "The value of this object corresponds directly to each xDSL
      interface as described in ifTable. "
 ::= { xdslDevIfConfigEntry 1 }

 xdslDevIfConfigPortSpeedBehaviour OBJECT-TYPE
   SYNTAX INTEGER {
     fixed (1),
     adaptive (2)
   }
   ACCESS read-write
   STATUS mandatory
   DESCRIPTION
     "The value of this object corresponds to the
      behaviour of the specified port. The default
      value for this object is fixed (1). "
 ::= { xdslDevIfConfigEntry 2 }

 xdslDevIfConfigUpFixedPortSpeed OBJECT-TYPE
   SYNTAX INTEGER {
     s272 (1),
     s408 (2),
     s544 (3),
     s680 (4),
     s816 (5),
     s952 (6),
     s1088 (7),
     s91 (8),
	 s476 (9),
     s340 (10),
     s204 (11),
     s136 (12),
     s119 (13),
     s102 (14),
     s85 (15),
     s68 (16),
     s51 (17),
     s45 (18),
     s34 (19),
     s11 (20),
	  s2320 (21),
	  s2046 (22),
	  s1552 (23),
	  s1040 (24),
	  s784 (25),
	  s528 (26),
	  s400 (27),
	  s277 (28),
	  s144 (29)
   }
   ACCESS read-write
   STATUS mandatory
   DESCRIPTION
     "The value of this object corresponds to the upstream
      speed of the specified port for fixed port speed
      behaviour. All the speeds enumerated above are in kbps.
      If the port speed behaviour is adaptive an error of
      noSuchName will be returned by the agent.
      The default value for this object is s1088 (7)."
 ::= { xdslDevIfConfigEntry 3 }

 xdslDevIfConfigDownFixedPortSpeed OBJECT-TYPE
   SYNTAX INTEGER {
     s640 (1),
     s960 (2),
     s1280 (3),
     s1600 (4),
     s1920 (5),
     s2240 (6),
     s2560 (7),
     s2688 (8),
     s3200 (9),
     s4480 (10),
     s5120 (11),
     s6272 (12),
     s7168 (13),
     s1024 (14),
     s896 (15),
     s768 (16),
     s512 (17),
     s384 (18),
     s256 (19),
	  s2320 (20),
	  s2046 (21),
	  s1552 (22),
	  s1040 (23),
	  s784 (24),
	  s528 (25),
	  s400 (26),
	  s277 (27),
	  s144 (28)
   }
   ACCESS read-write
   STATUS mandatory
   DESCRIPTION
     "The value of this object corresponds to the downstream
      speed of the specified port for fixed port speed
      behaviour. All the speeds enumerated above are in kbps.
      if the port speed behaviour is adaptive an error of noSuchName
      will be returned by the agent.
      The default value for this object is  s2560 (7)."
 ::= { xdslDevIfConfigEntry 4 }

 xdslDevIfConfigUpAdaptiveUpperBoundPortSpeed OBJECT-TYPE
   SYNTAX INTEGER {
     s272 (1),
     s408 (2),
     s544 (3),
     s680 (4),
     s816 (5),
     s952 (6),
     s1088 (7),
     s91 (8),
	 s476 (9),
     s340 (10),
     s204 (11),
     s136 (12),
     s119 (13),
     s102 (14),
     s85 (15),
     s68 (16),
     s51 (17),
     s45 (18),
     s34 (19),
     s11 (20)
   }
   ACCESS read-write
   STATUS mandatory
   DESCRIPTION
     "The value of this object corresponds to the
      upper bound for the upstream port speed of the specified port
      for adaptive port speed behaviour. The speeds are measured
      in kbps.  If the port speed behaviour is fixed an error of
      noSuchName will be returned by the agent. The default value for
      this object is s1088."
 ::= { xdslDevIfConfigEntry 5 }

 xdslDevIfConfigUpAdaptiveLowerBoundPortSpeed OBJECT-TYPE
   SYNTAX INTEGER {
     s272 (1),
     s408 (2),
     s544 (3),
     s680 (4),
     s816 (5),
     s952 (6),
     s1088 (7),
     s91 (8),
	 s476 (9),
     s340 (10),
     s204 (11),
     s136 (12),
     s119 (13),
     s102 (14),
     s85 (15),
     s68 (16),
     s51 (17),
     s45 (18),
     s34 (19),
     s11 (20)
   }
   ACCESS read-write
   STATUS mandatory
   DESCRIPTION
     "The value of this object corresponds to the
      lower bound for the upstream port speed of the
      specified port for adaptive port speed behaviour
      in kbps. If the port speed behaviour is fixed an
      error of noSuchName will be returned by the agent.
      The default value for this object s272."
 ::= { xdslDevIfConfigEntry 6 }

 xdslDevIfConfigDownAdaptiveUpperBoundPortSpeed OBJECT-TYPE
   SYNTAX INTEGER {
     s640 (1),
     s960 (2),
     s1280 (3),
     s1600 (4),
     s1920 (5),
     s2240 (6),
     s2560 (7),
     s2688 (8),
     s3200 (9),
     s4480 (10),
     s5120 (11),
     s6272 (12),
     s7168 (13),
     s1024 (14),
     s896 (15),
     s768 (16),
     s512 (17),
     s384 (18),
     s256 (19)

   }
   ACCESS read-write
   STATUS mandatory
   DESCRIPTION
     "The value of this object corresponds to
      the upper bound allowed for the downstream port speed
      of the specified port for adaptive port speed
      behaviour. The speeds are measured in kbps.
      if the port speed behaviour is fixed an error of noSuchName
      will be returned by the agent. The default value for this
      object is s2560 (7)."
 ::= { xdslDevIfConfigEntry 7 }

 xdslDevIfConfigDownAdaptiveLowerBoundPortSpeed OBJECT-TYPE
   SYNTAX INTEGER {
     s640 (1),
     s960 (2),
     s1280 (3),
     s1600 (4),
     s1920 (5),
     s2240 (6),
     s2560 (7),
     s2688 (8),
     s3200 (9),
     s4480 (10),
     s5120 (11),
     s6272 (12),
     s7168 (13),
     s1024 (14),
     s896 (15),
     s768 (16),
     s512 (17),
     s384 (18),
     s256 (19)

   }
   ACCESS read-write
   STATUS mandatory
   DESCRIPTION
     "The value of this object corresponds to the
      Minimum lower bound allowed for the downstream port speed
      of the specified port for adaptive port speed behaviour.
      If the port speed behaviour is fixed an error of noSuchName
      will be returned by the agent.  The speeds are measured in kbps.
      The default value for this object is s640(1)."
 ::= { xdslDevIfConfigEntry 8 }

 xdslDevIfConfigReedSolomonDownForwardErrorCorrection OBJECT-TYPE
   SYNTAX INTEGER {
     minimizeError (1),
     minimizeDelay (2),
     reedSolomonNotSupported(3)

   }
   ACCESS read-write
   STATUS mandatory
   DESCRIPTION
     "The value of this object corresponds to the
      Reed-Solomon forward error correction in the downstream
      direction. The default value of this object should be
      minimizeError (1)."
 ::= { xdslDevIfConfigEntry 9 }

 xdslDevIfConfigMarginThreshold OBJECT-TYPE
   SYNTAX INTEGER
   ACCESS read-write
   STATUS mandatory
   DESCRIPTION
    "The value of this object corresponds to the offset from
     the startup margin. The threshold margin is calculated
     by subtracting the offset from the startup margin.
     Permissible range of values are between -7 and 14.
     A value of -9999 disables the threshold check. The default
     value of this object is 3"
 ::= { xdslDevIfConfigEntry 10 }

 xdslDevIfConfigEstimatedHrErrRateThreshold OBJECT-TYPE
   SYNTAX INTEGER
   ACCESS read-write
   STATUS mandatory
   DESCRIPTION
     "The value of this object corresponds to the
      estimated error rate threshold value on an hourly basis.
      A value of -9999 disables the threshold check. The  default value
      for this object is 1000."
 ::= { xdslDevIfConfigEntry 11 }

 xdslDevIfConfigEstimatedDayErrRateThreshold OBJECT-TYPE
   SYNTAX INTEGER
   ACCESS read-write
   STATUS mandatory
   DESCRIPTION
     "The value of this object corresponds to the
      estimated error rate threshold value on a daily basis. A
      value of -9999 disables this threshold check. The default value
      for this object is 10000"
 ::= { xdslDevIfConfigEntry 12 }

 xdslDevIfConfigPortID OBJECT-TYPE
   SYNTAX DisplayString (SIZE (1..40))
   ACCESS read-write
   STATUS mandatory
   DESCRIPTION
     "The value of this object corresponds to  40 character
      information only field that identifies what the DSL
      port is connected to (Circuit ID, MDF location,
      Customer name, etc.)"
 ::= { xdslDevIfConfigEntry 13 }

 xdslDevIfLinkUpDownTransitionThreshold OBJECT-TYPE
   SYNTAX INTEGER
   ACCESS read-write
   STATUS mandatory
   DESCRIPTION
     "The value of this object corresponds to the threshold
      value for link up-down transitions. If link up-down's exceed
      this threshold value a xdslLinkupDownTransitions
      trap is generated. This value would represent the number
      of link up-down transitions in a 15 minute interval. A value
      of -9999 disables the threshold check. The default value for this
      object is 0"
 ::= { xdslDevIfConfigEntry 14 }

 xdslDevIfConfigStartUpMargin OBJECT-TYPE
   SYNTAX INTEGER (-3..9)
   ACCESS read-write
   STATUS mandatory
   DESCRIPTION
     " The value of this object corresponds to the startup value
       of the margin for a DSL interface (specified by ifIndex).
       The unit is db (decibels. The higher the margin the better
       the quality of the line. The default value of this object is 3."
 ::= { xdslDevIfConfigEntry 15 }


 xdslDevIfConfigTxPowerAttenuation OBJECT-TYPE
   SYNTAX INTEGER
   ACCESS read-write
   STATUS mandatory
   DESCRIPTION
     " This value corresponds to the Transmitt Power Attenuation in dB
       for the access node. This value represents the downstream power
       level in dB. Permissible range of values are between -6 and 0.
       The default value of this object is 0 dB. The power levels +3
       and +6 may be used in future."
 ::= { xdslDevIfConfigEntry 16 }

 xdslDevIfConfigSnTxPowerAttenuation OBJECT-TYPE
   SYNTAX INTEGER
   ACCESS read-write
   STATUS mandatory
   DESCRIPTION
     " This value corresponds to the Transmitt Power Attenuation in dB
       for the service node. This value represents the upstream power
       level in dB. The default value of this object is -6 dB."
 ::= { xdslDevIfConfigEntry 17 }

 -- the Remote System Table

 xdslRemoteSysTable OBJECT-TYPE
   SYNTAX SEQUENCE OF XdslRemoteSysEntry
   ACCESS not-accessible
   STATUS mandatory
   DESCRIPTION
	"The Remote System information table.  This table is based
	 on the mib-2 system mib."
	 ::= { xdslRemoteSys 1 }

 xdslRemoteSysEntry OBJECT-TYPE
   SYNTAX XdslRemoteSysEntry
   ACCESS not-accessible
   STATUS mandatory
   DESCRIPTION
     "Describes a specific xDSL interface Remote Endpoint entry."
   INDEX { xdslRemoteSysIndex }
 ::= { xdslRemoteSysTable 1 }

 XdslRemoteSysEntry ::=
   SEQUENCE {
     xdslRemoteSysIndex
	INTEGER,
     xdslRemoteSysDescr
       DisplayString (SIZE (0..255)),
     xdslRemoteSysObjectID
       OBJECT IDENTIFIER,
     xdslRemoteSysUpTime
       TimeTicks,
     xdslRemoteSysContact
       DisplayString (SIZE (0..255)),
     xdslRemoteSysName
       DisplayString (SIZE (0..255)),
     xdslRemoteSysLocation
       DisplayString (SIZE (0..255)),
     xdslRemoteSysServices
       INTEGER (0..127),
     xdslRemoteSysCircuitId
       DisplayString (SIZE(1..32))
  }


 -- the Remote System group

          xdslRemoteSysIndex OBJECT-TYPE
	      SYNTAX INTEGER
              ACCESS read-only
              STATUS mandatory
              DESCRIPTION
		"Refer to the mib-2 system MIB for a description."
         ::= {  xdslRemoteSysEntry 1 }


          xdslRemoteSysDescr OBJECT-TYPE
              SYNTAX  DisplayString (SIZE (0..255))
              ACCESS  read-only
              STATUS  mandatory
              DESCRIPTION
		"Refer to the mib-2 system MIB for a description."
	 ::= {  xdslRemoteSysEntry 2 }

          xdslRemoteSysObjectID OBJECT-TYPE
              SYNTAX  OBJECT IDENTIFIER
              ACCESS  read-only
              STATUS  mandatory
              DESCRIPTION
		"Refer to the mib-2 system MIB for a description."
	 ::= {  xdslRemoteSysEntry 3 }

          xdslRemoteSysUpTime OBJECT-TYPE
              SYNTAX  TimeTicks
              ACCESS  read-only
              STATUS  mandatory
              DESCRIPTION
		"Refer to the mib-2 system MIB for a description."
	 ::= {  xdslRemoteSysEntry 4 }

          xdslRemoteSysContact OBJECT-TYPE
              SYNTAX  DisplayString (SIZE (0..255))
              ACCESS  read-write
              STATUS  mandatory
              DESCRIPTION
		"Refer to the mib-2 system MIB for a description."
	 ::= {  xdslRemoteSysEntry 5 }

          xdslRemoteSysName OBJECT-TYPE
              SYNTAX  DisplayString (SIZE (0..255))
              ACCESS  read-write
              STATUS  mandatory
              DESCRIPTION
		"Refer to the mib-2 system MIB for a description."
	 ::= {  xdslRemoteSysEntry 6 }

          xdslRemoteSysLocation OBJECT-TYPE
              SYNTAX  DisplayString (SIZE (0..255))
              ACCESS  read-write
              STATUS  mandatory
              DESCRIPTION
		"Refer to the mib-2 system MIB for a description."
	 ::= {  xdslRemoteSysEntry 7 }

          xdslRemoteSysServices OBJECT-TYPE
              SYNTAX  INTEGER (0..127)
              ACCESS  read-only
              STATUS  mandatory
              DESCRIPTION
		"Refer to the mib-2 system MIB for a description."
	 ::= {  xdslRemoteSysEntry 8 }

          xdslRemoteSysCircuitId OBJECT-TYPE
              SYNTAX        DisplayString (SIZE(1..32))
              ACCESS  read-only
              STATUS  mandatory
              DESCRIPTION
        "The value of this object reflects the Circuit ID
         for a Service Node."
     ::= {  xdslRemoteSysEntry 9 }


-- the Remote   DTE Status Table

xdslRemoteDTEStatusTable OBJECT-TYPE
	SYNTAX SEQUENCE OF XdslRemoteDTEStatusEntry
	ACCESS not-accessible
	STATUS mandatory
	DESCRIPTION
	"The Remote DTE Status table. This provides status information about the
	DTE port of the DSL RTUs."
	::= { xdslRemoteDTEStatus 1 }

xdslRemoteDTEStatusEntry OBJECT-TYPE
	SYNTAX  XdslRemoteDTEStatusEntry
	ACCESS not-accessible
	STATUS mandatory
	DESCRIPTION
	" This provides status information about the
	DTE port of a specific DSL RTU."
	INDEX { xdslRemoteDTEStatusIndex }
	::= { xdslRemoteDTEStatusTable 1 }

	XdslRemoteDTEStatusEntry ::=
	SEQUENCE {
	xdslRemoteDTEStatusIndex
	INTEGER,
	xdslRemoteDTEState
	INTEGER,
	xdslRemoteDTEType
	INTEGER,
	xdslRemoteDTEClockSource
	INTEGER,
	xdslRemoteDTEStrobe
	INTEGER,
	xdslRemoteDTELoopbackState
	INTEGER
	}

	-- the Remote DTE Status group

	xdslRemoteDTEStatusIndex OBJECT-TYPE
	SYNTAX INTEGER
	ACCESS read-only
	STATUS mandatory
	DESCRIPTION
	"The value of this object corresponds directly to each DSL interface as
described in the ifTable."
	::= {xdslRemoteDTEStatusEntry 1 }

	xdslRemoteDTEState OBJECT-TYPE
	SYNTAX INTEGER {
	inService (1),
	outOfService (2)
	}
	ACCESS read-only
	STATUS mandatory
	DESCRIPTION
	"The value of this object reflects the state of the DTE interface of the
DSL RTU."
	::= {xdslRemoteDTEStatusEntry 2 }

	xdslRemoteDTEType OBJECT-TYPE
	SYNTAX INTEGER {
	v35 (1),
	eia530 (2)
	}
	ACCESS read-only
	STATUS mandatory
	DESCRIPTION
	"The value of this object reflects the configuration of the DTE interface
of the DSL RTU."
	::= {xdslRemoteDTEStatusEntry 3 }

	xdslRemoteDTEClockSource OBJECT-TYPE
	SYNTAX INTEGER {
	internal (1),
	external (2)
	}
	ACCESS read-only
	STATUS mandatory
	DESCRIPTION
	"The value of this object reflects the timing configuration of the DTE
interface of the DSL RTU."
	::= {xdslRemoteDTEStatusEntry 4 }

	xdslRemoteDTEStrobe OBJECT-TYPE
	SYNTAX INTEGER {
	risingEdge (1),
	fallingEdge (2)
	}
	ACCESS read-only
	STATUS mandatory
	DESCRIPTION
	"The value of this object reflects the clock edge timing configuration of the DTE
interface of the DSL RTU."
	::= {xdslRemoteDTEStatusEntry 5 }

	xdslRemoteDTELoopbackState OBJECT-TYPE
	SYNTAX INTEGER {
	on (1),
	off (2)
	}
	ACCESS read-only
	STATUS mandatory
	DESCRIPTION
	"The value of this object reflects the loopback state  of the DTE
interface of the DSL RTU."
	::= {xdslRemoteDTEStatusEntry 6 }


 -- The xdslDevMvlConfig group. Implementation of this group is
 -- mandatory for Atlantis MVL Rel 1.0.

 xdslDevMvlIfConfigTable OBJECT-TYPE
   SYNTAX SEQUENCE OF XdslDevMvlIfConfigEntry
   ACCESS not-accessible
   STATUS mandatory
   DESCRIPTION
     "The xdslDevMvlIfConfigTable provides config information specific
      to a xDSL(MVL) device, or system. The table is indexed by an
      object which corresponds to ifIndex. These ifIndex entries,
      themselves, denote and identify specific xdsl(Mvl) interfaces on
      the board or module. "
 ::= { xdslDevMvlIfConfig 1 }

 xdslDevMvlIfConfigEntry OBJECT-TYPE
   SYNTAX XdslDevMvlIfConfigEntry
   ACCESS not-accessible
   STATUS mandatory
   DESCRIPTION
     "Describes a specific xDSL(MVL) interface entry."
   INDEX { xdslDevMvlIfConfigIfIndex }
 ::= { xdslDevMvlIfConfigTable 1 }

 XdslDevMvlIfConfigEntry ::=
   SEQUENCE {
     xdslDevMvlIfConfigIfIndex
       INTEGER,
     xdslDevMvlIfConfigUpperBoundPortSpeed
       INTEGER,
     xdslDevMvlIfConfigMarginThreshold
       INTEGER,
     xdslDevMvlIfConfigPortID
       DisplayString (SIZE (1..40)),
     xdslDevMvlIfLinkUpDownTransitionThreshold
       INTEGER,
     xdslDevMvlIfConfigOnHookTxPowerAttenuation
       INTEGER,
     xdslDevMvlIfConfigOffHookTxPowerAttenuation
       INTEGER
  }

 xdslDevMvlIfConfigIfIndex OBJECT-TYPE
   SYNTAX INTEGER
   ACCESS read-only
   STATUS mandatory
   DESCRIPTION
     "The value of this object corresponds directly to each xDSL(MVL)
      interface as described in ifTable. "
 ::= { xdslDevMvlIfConfigEntry 1 }

 xdslDevMvlIfConfigUpperBoundPortSpeed OBJECT-TYPE
   SYNTAX INTEGER
   ACCESS read-write
   STATUS mandatory
   DESCRIPTION
     "The value of this object corresponds to the upper bound
      port speed of the specified port. The speeds are measured in kbps.
      Supported speeds are 128, 192, 256, 320, 384, 448, 512
      576, 640, 704, 768.
      The default value of this object is 768 "
 ::= { xdslDevMvlIfConfigEntry 2 }

 xdslDevMvlIfConfigMarginThreshold OBJECT-TYPE
   SYNTAX INTEGER
   ACCESS read-write
   STATUS mandatory
   DESCRIPTION
     "The value of this object corresponds to the
      Margin threshold value. Permissible range of
      values are between -5 and 9.  A value of -9999
      disables the threshold check. The default value is 3"
 ::= { xdslDevMvlIfConfigEntry 3 }

 xdslDevMvlIfConfigPortID OBJECT-TYPE
   SYNTAX DisplayString (SIZE (1..40))
   ACCESS read-write
   STATUS mandatory
   DESCRIPTION
     "The value of this object corresponds to  40 character
      information only field that identifies what the DSL
      port is connected to (Circuit ID, MDF location,
      Customer name, etc.)"
 ::= { xdslDevMvlIfConfigEntry 4 }

 xdslDevMvlIfLinkUpDownTransitionThreshold OBJECT-TYPE
   SYNTAX INTEGER
   ACCESS read-write
   STATUS mandatory
   DESCRIPTION
     "The value of this object corresponds to the threshold
      value for link up-down transitions. If link up-down's exceed
      this threshold value a xdslLinkupDownTransitions
      trap is generated. This value would represent the number
      of link up-down transitions in a 15 minute interval. A value
      of -9999 disables the threshold check. The default value for this
      object is 0"
 ::= { xdslDevMvlIfConfigEntry 5 }

 xdslDevMvlIfConfigOnHookTxPowerAttenuation OBJECT-TYPE
   SYNTAX INTEGER
   ACCESS read-write
   STATUS mandatory
   DESCRIPTION
     " This value corresponds to the On-hook Transmitt Power Attenuation
       in dB for the access node and the service node. This value represents
       both downstream and upstream power level in dB while the phone is
       On-hook. Permissible range of values are between -2 and +10. The
       default value of this object is 10 dB."
 ::= { xdslDevMvlIfConfigEntry 6 }

 xdslDevMvlIfConfigOffHookTxPowerAttenuation OBJECT-TYPE
   SYNTAX INTEGER
   ACCESS read-write
   STATUS mandatory
   DESCRIPTION
     " This value corresponds to the Off-hook Transmitt Power Attenuation
       in dB for the access node and the service node. This value represents
       both downstream and upstream power level in dB while the phone is
       Off-hook. Permissible range of values are between -2 and +7. The
       default value of this object is 7 dB. "
 ::= { xdslDevMvlIfConfigEntry 7 }

 -- The xdslDevNAPCustomerAccount group. Implementation of this group is
 -- mandatory for Atlantis Rel 1.1.

 xdslDevNAPCustomerAccountTable OBJECT-TYPE
   SYNTAX SEQUENCE OF XdslDevNAPCustomerAccountEntry
   ACCESS not-accessible
   STATUS mandatory
   DESCRIPTION
     "The xdslDevNAPCustomerAccountTable provides customer accounting
      information on each DSL port. Network Access Providers can accurately
      bill their end station DSL customers by the amount of usage.
      The table is indexed by ifIndex and xdslDevNAPCustomerAccountInterval
      The ifIndex identifies specific xdsl interface on the device and
      xdslDevNAPCustomerAccountInterval specifies the accounting information
      is for the current day or the previous day. Customer data excludes all
      traffic used for management purpose."
 ::= { xdslDevNAPCustomerAccount 1 }

 xdslDevNAPCustomerAccountEntry OBJECT-TYPE
   SYNTAX XdslDevNAPCustomerAccountEntry
   ACCESS not-accessible
   STATUS mandatory
   DESCRIPTION
     "Provides customer related accounting information specific to an
      xDSL interface entry."
   INDEX { xdslDevNAPCustomerAccountIfIndex,
           xdslDevNAPCustomerAccountInterval }
 ::= { xdslDevNAPCustomerAccountTable 1 }

 XdslDevNAPCustomerAccountEntry ::=
   SEQUENCE {
     xdslDevNAPCustomerAccountIfIndex
       INTEGER,
     xdslDevNAPCustomerAccountInterval
       INTEGER,
     xdslDevNAPCustomerAccountRecKiloOctets
       INTEGER,
     xdslDevNAPCustomerAccountTrxKiloOctets
       INTEGER
  }

 xdslDevNAPCustomerAccountIfIndex OBJECT-TYPE
   SYNTAX INTEGER
   ACCESS read-only
   STATUS mandatory
   DESCRIPTION
     "The value of this object corresponds directly to each xDSL
      interface as described in ifTable. "
 ::= { xdslDevNAPCustomerAccountEntry 1 }

 xdslDevNAPCustomerAccountInterval OBJECT-TYPE
   SYNTAX INTEGER {
     currentDay (1),
     previousDay (2)
   }
   ACCESS read-only
   STATUS mandatory
   DESCRIPTION
     "The value of this object corresponds to the interval of time
      during which customer accounting data were collected. Day
      starts at 12.01 midnight "
 ::= { xdslDevNAPCustomerAccountEntry 2 }

 xdslDevNAPCustomerAccountRecKiloOctets OBJECT-TYPE
   SYNTAX INTEGER
   ACCESS read-only
   STATUS mandatory
   DESCRIPTION
     "Customer data received at the AN's DSL port in 1000 Octets.
      The default value of this object is 0 "
 ::= { xdslDevNAPCustomerAccountEntry 3 }

 xdslDevNAPCustomerAccountTrxKiloOctets OBJECT-TYPE
   SYNTAX INTEGER
   ACCESS read-only
   STATUS mandatory
   DESCRIPTION
     "Customer data transmitted over the AN's DSL port in 1000 Octets.
      The default value of this object is 0 "
 ::= { xdslDevNAPCustomerAccountEntry 4 }


 -- The xdslDevIDSLConfig Group { xdslDevice 9 }

 xdslDevIDSLConfigTable OBJECT-TYPE
   SYNTAX SEQUENCE OF XdslDevIDSLConfigEntry
   ACCESS not-accessible
   STATUS mandatory
   DESCRIPTION
     "The xdslDevIDSLConfigTable provides configuration specific to the IDSL link."
 ::= { xdslDevIDSLConfig 1 }

 xdslDevIDSLConfigEntry OBJECT-TYPE
   SYNTAX XdslDevIDSLConfigEntry
   ACCESS not-accessible
   STATUS mandatory
   DESCRIPTION
     "Describes a specific IDSL configuration entry."
   INDEX { ifIndex }
 ::= { xdslDevIDSLConfigTable 1 }

 XdslDevIDSLConfigEntry ::=
   SEQUENCE {
     xdslDevIDSLConfigPortSpeedBehaviour
       INTEGER,
     xdslDevIDSLConfigPortSpeed
       INTEGER,
     xdslDevIDSLConfigPortID
       DisplayString (SIZE (1..40)),
     xdslDevIDSLTimingPortTransceiverMode
       INTEGER,
     xdslDevIDSLConfigMarginThreshold
       INTEGER,
     xdslDevIDSLLinkUpDownTransitionThreshold
       INTEGER
 }

 xdslDevIDSLConfigPortSpeedBehaviour OBJECT-TYPE
   SYNTAX INTEGER {
     fixed (1),
     adaptive (2)
   }
   ACCESS read-write
   STATUS mandatory
   DESCRIPTION
     "The value of this object corresponds to the
      behaviour of the specified port. The default
      value for this object is fixed (1). "
 ::= { xdslDevIDSLConfigEntry 1 }

 xdslDevIDSLConfigPortSpeed OBJECT-TYPE
   SYNTAX INTEGER
   ACCESS read-write
   STATUS mandatory
   DESCRIPTION
     "The value of this object corresponds to both upstream
      and downstream speed of the specified port. All the
      speeds are in kbps. The default value for this object
      is 128 kbps."
 ::= { xdslDevIDSLConfigEntry 2 }

 xdslDevIDSLConfigPortID OBJECT-TYPE
   SYNTAX DisplayString (SIZE (1..40))
   ACCESS read-write
   STATUS mandatory
   DESCRIPTION
     "The value of this object corresponds to  40 character
      information only field that identifies what the DSL
      port is connected to (Circuit ID, MDF location,
      Customer name, etc.)"
 ::= { xdslDevIDSLConfigEntry 3 }

 xdslDevIDSLTimingPortTransceiverMode OBJECT-TYPE
   SYNTAX INTEGER {
          networkTiming (1),
          localTiming (2)
   }
   ACCESS read-write
   STATUS mandatory
   DESCRIPTION
     "The transceiver mode selected on the timing source port.
      Only one IDSL port can be set to NT mode. This timing
      will then be distributed to all other IDSL ports in the
      chassis that are set to LT.

      The selected xdslDevIDSLPrimaryTimingSourcePort provides clocking
      signals to the DSLAM when the transceiver mode is set to Network
      timing. The port selected for Network Timing mode will probably not
      used for customer data, but will receive a 2.048 Mhz Network clocking
      signal from a central office timing source and distribute this timing
      to other IDSL port cards."
 ::= { xdslDevIDSLConfigEntry 4 }

 xdslDevIDSLConfigMarginThreshold OBJECT-TYPE
   SYNTAX INTEGER
   ACCESS read-write
   STATUS mandatory
   DESCRIPTION
     "The value of this object corresponds to the
      Margin threshold value. A value of -9999 disables the
      threshold check. The value range of this object is
	  -5 to 10. The default value is 3"
 ::= { xdslDevIDSLConfigEntry 5 }

 xdslDevIDSLLinkUpDownTransitionThreshold OBJECT-TYPE
   SYNTAX INTEGER
   ACCESS read-write
   STATUS mandatory
   DESCRIPTION
     "The value of this object corresponds to the threshold
      value for link up-down transitions. If link up-down's exceed
      this threshold value a xdslLinkupDownTransitions
      trap is generated. This value would represent the number
      of link up-down transitions in a 15 minute interval. A value
      of -9999 disables the threshold check. The value range of this
	  object is 0 to 1000. The default value for this object is 0"
 ::= { xdslDevIDSLConfigEntry 6 }

 -- The xdslLinkUpDownInformation group.

xdslLinkDownReason OBJECT-TYPE
    SYNTAX  DisplayString  (SIZE (1..255))
    ACCESS  not-accessible
    STATUS  mandatory
    DESCRIPTION
        "This entry contains the reason as to why
         the DSL Link went down. This information
         is obtained when the DSL Link is coming up"
    ::= { xdslLinkUpDownInformation 1 }

 -- The xdslRemoteInjection group.

xdslRemoteInjectionType OBJECT-TYPE
    SYNTAX  INTEGER {
            filter (1)
    }
    ACCESS  not-accessible
    STATUS  deprecated
    DESCRIPTION
       "The value of this object corresponds to the remote
        injection type"
    ::= { xdslRemoteInjection 1 }


 -- Trap definitions
 -- All traps sent from the DSL cards will have the MCC card's address
 -- (in the NAP domain) in the ip-address field of the TRAP PDU.
 -- The first varbind of the trap PDU will be the ifIndex which is
 -- overloaded to specify which card in the chassis sent  the trap.

 xdslLinkUpDownTransitions TRAP-TYPE
   ENTERPRISE xdslDevice
   VARIABLES { ifIndex }
   DESCRIPTION
     "This trap signifies that the sending protocol
      entity recognizes that one of the xDSL communication
      links is in a fluctuating state. This is a trap of
      'minor' class."
 ::= 1

 xdslPortSpeedLow TRAP-TYPE
   ENTERPRISE xdslDevice
   VARIABLES { ifIndex }
   DESCRIPTION
     "This trap signifies that the port speed of the
      xDSL link has dropped below a threshold value.
      This is a trap of 'warning' class"
 ::= 2

 xdslPortSpeedNormal TRAP-TYPE
   ENTERPRISE xdslDevice
   VARIABLES { ifIndex }
   DESCRIPTION
     "This trap signifies that the port speed of the
      xDSL link has has gone above the threshold value.
      This is a trap of 'warning' class. This trap compliments the
      xdslPortSpeedLow Trap"
 ::= 102

xdslMarginLow TRAP-TYPE
   ENTERPRISE xdslDevice
   VARIABLES { ifIndex }
   DESCRIPTION
     "This trap signifies that the margin estimate
      is below a customer set threshold value. this is a trap
      of 'minor' class."
 ::= 3

 xdslMarginNormal TRAP-TYPE
   ENTERPRISE xdslDevice
   VARIABLES { ifIndex }
   DESCRIPTION
     "This trap signifies that the margin estimate  has gone
      above a customer set threshold value. this is a trap
      of 'minor' class. this trap compliments the xdslMarginLow
      trap"
 ::= 103

 xdslErrorRateHigh TRAP-TYPE
   ENTERPRISE xdslDevice
   VARIABLES { ifIndex }
   DESCRIPTION
     "This trap signifies that the error rate estimates
      is above a customer set threshold value. This is a trap
      of 'minor' class."
 ::= 4

 xdslErrorRateNormal TRAP-TYPE
   ENTERPRISE xdslDevice
   VARIABLES { ifIndex }
   DESCRIPTION
     "This trap signifies that the error rate estimates
      gone below a customer set threshold value. This is a trap
      of 'minor' class. This trap compliments the xdslErrorRateHigh trap."
 ::= 104

 xdslPortFailure TRAP-TYPE
   ENTERPRISE xdslDevice
   VARIABLES { ifIndex }
   DESCRIPTION
     "This trap signifies that the processor detected
      a bad modem set. This is a trap of 'major' class"
 ::= 5

 xdslPortOperational TRAP-TYPE
   ENTERPRISE xdslDevice
   VARIABLES { ifIndex }
   DESCRIPTION
     "This trap signifies that the modem set which was bad is now operational.
      This is a trap of 'major' class. This trap compliments the
      xdslPortFailure trap."
 ::= 105

 xdslTestStart TRAP-TYPE
   ENTERPRISE xdslDevice
   VARIABLES { ifIndex }
   DESCRIPTION
     "This trap signifies that a diagnostic test has started on one of the
      ports"
 ::= 6

 xdslTestOver TRAP-TYPE
   ENTERPRISE xdslDevice
   VARIABLES { ifIndex }
   DESCRIPTION
     "This trap signifies that the test has completed on one of the
      ports. This trap compliments the xdslTestStart trap."
   ::= 106

 xdslRtuTypeMismatch TRAP-TYPE
   ENTERPRISE xdslDevice
   VARIABLES { ifIndex }
   DESCRIPTION
    "The RTU configured in the DSL card does NOT match with the RTU connected
     to the DSL port indicated by the ifIndex."
  ::= 7

 xdslRtuTypeMismatchClear TRAP-TYPE
   ENTERPRISE xdslDevice
   VARIABLES { ifIndex }
   DESCRIPTION
    "The RTU configured in the DSL card does match with the RTU connected
     to the DSL port indicated by the ifIndex."
  ::= 107

 xdslRtuSelfTestFail TRAP-TYPE
   ENTERPRISE xdslDevice
   VARIABLES { ifIndex }
   DESCRIPTION
    "A self test failure from the RTU connected
     to the DSL port indicated by the ifIndex."
  ::= 16

xdslRtuLastGasp  TRAP-TYPE
  ENTERPRISE xdslDevice
  VARIABLES {ifIndex}
  DESCRIPTION
  "Card received LastGap message from SN followed by a link
   down condition one minute later. "
  ::= 17

 xdslSNDeviceFail  TRAP-TYPE
  ENTERPRISE xdslDevice
  VARIABLES {ifIndex}
  DESCRIPTION
  "Operating software has detected an internal device failure. The
   RTU is still operating."
  ::= 18

 xdslSNSelfTestFail  TRAP-TYPE
  ENTERPRISE xdslDevice
  VARIABLES {ifIndex}
  DESCRIPTION
  "Failure of the RTU's hardware components. This trap is only set if the
   hardware failure still allows sending traps."
  ::= 19

 xdslSNFatalReset  TRAP-TYPE
  ENTERPRISE xdslDevice
  VARIABLES {ifIndex}
  DESCRIPTION
  "Fatal error device reset"
  ::= 20

 xdslLinkDownAnalysisTrap  TRAP-TYPE
  ENTERPRISE xdslDevice
  VARIABLES {ifIndex, xdslLinkDownReason}
  DESCRIPTION
   "This trap signifies that the sending protocol
    entity recognizes that  the xDSL communication
    link is up. LinkDownReason conveys the reason
    for link down."
  ::= 21

-- This trap has been deprecated. Use the trap in pdn_filters.mib

 xdslRemoteInjectionFailureTrap  TRAP-TYPE
  ENTERPRISE xdslDevice
  VARIABLES {ifIndex, pdnPortConfigVNID, xdslRemoteInjectionType}
  DESCRIPTION
   "This trap signifies that the injection of filters to SN failed
    It is of warning class"
  ::= 22

-- This trap has been deprecated. Use the trap in pdn_filters.mib

 xdslRemoteInjectionIncompatibleTrap  TRAP-TYPE
  ENTERPRISE xdslDevice
  VARIABLES {ifIndex, pdnPortConfigVNID, xdslRemoteInjectionType}
  DESCRIPTION
   "This trap signifies that the injection of filters is not supported
    by the SN. It is of warning class"
  ::= 23

 xdslLossOfNetworkTimingSignalTrap  TRAP-TYPE
  ENTERPRISE xdslDevice
  VARIABLES {ifIndex}
  DESCRIPTION
   "This trap is generated by an IDSL port card when it detects
    that the line supplying timing signals to the chassis on the port
    designated as NT has dropped. The ifIndex corresponds to the port
    designated as NT."
  ::= 24

END
