-- ===============================================================
-- Copyright (C) 2000 Paradyne Corporation.
--  ATM M4 Extension Group
PDN-ATMM4EXT-MIB DEFINITIONS ::= BEGIN

    IMPORTS
        MODULE-IDENTITY , OBJECT-TYPE, OBJECT-IDENTITY,
        Gauge32, TimeTicks
            FROM SNMPv2-SMI
        TEXTUAL-CONVENTION
            FROM SNMPv2-TC
        MODULE-COMPLIANCE, OBJECT-GROUP
            FROM SNMPv2-CONF
        pdnAtm
            FROM PDN-HEADER-MIB
        atmfM4VpTestEntry, atmfM4VcTestEntry, atmfM4TcProtoCurrEntry, atmfM4TcProtoHistEntry
            FROM ATM-FORUM-SNMP-M4-MIB
        ifIndex
            FROM IF-MIB;

-- ===============================================================
--
--  Extentions to the ATM Forum M4  Mib
--
-- ===============================================================

    pdnAtmfM4ExtMIB MODULE-IDENTITY
        LAST-UPDATED "200103080000Z"
        ORGANIZATION "Paradyne Corporation
                      MIB Working Group"
        CONTACT-INFO
                  "Paradyne Corporation
                   8545 126th Avenue North
                   Largo, FL 33773
                   www.paradyne.com

                   General Comments to: mibwg_team@eng.paradyne.com"

        DESCRIPTION
            "This MIB Module extends the ATM-FORUM-SNMP-M4-MI defined
             in the Atm Forums M4 Mib
            "
        REVISION "200208150000Z"
        DESCRIPTION "P. Easwar
            o  Added New Table pdnAtmfM4VpLoopbackTestTable.
		"

        REVISION "200103080000Z"
        DESCRIPTION "R.A.Bowhall
            o  Added error code of adminStatusDisabled(8).
	    "

        REVISION "200009260000Z"
        DESCRIPTION "R. Steinberger
            o  Added size to pdnAtmfM4Vc1CellLoopReportedLocation.
            "
        REVISION "200009220000Z"
        DESCRIPTION "R. Steinberger
            o  Added error code of testTimeOut(7).
            o  Added description of use of pdnAtmfM4Vc1CellLoopTable
            o  Changed pdnAtmfM4Vc1CellLoopReportedLocation type to
               meet actual M4 definition of OCTET STRING(SIZE(16))
            o  Added the pdnAtmfM4LoopbackLocationTable
            "
        REVISION "200009210000Z"
        DESCRIPTION "J.Strain
            o  Added E2E and SEG as Multiple OAM Cell Tests
            o  documented mapping of atmfM4VcTestType to the corresponding
                                 atmfM4VcTestCode results table
            "
        REVISION "200009080000Z"
        DESCRIPTION "R. Steinberger
            o  Cleaned tabs throughout document.
            o  Fixed naming convention.
            o  Added pdnAtmfM4Vc1CellLoopTable for ATM OAM loopbacks
               that send only single test cell.
            o  Added conformance section.
            "
        REVISION "200006290000Z"
        DESCRIPTION "Z. Pan
            o  added augmented atmfM4VcTestTable for ATM OAM loopback test.
            "
        ::= {  pdnAtm 6 }

    pdnAtmfM4ExtObjects     OBJECT IDENTIFIER  ::= { pdnAtmfM4ExtMIB 1 }
    pdnAtmfM4ExtTraps       OBJECT IDENTIFIER  ::= { pdnAtmfM4ExtMIB 2 }
    pdnAtmfM4ExtConformance OBJECT IDENTIFIER  ::= { pdnAtmfM4ExtMIB 3 }
    pdnAtmfM4ExtTrapPrefix  OBJECT IDENTIFIER  ::= { pdnAtmfM4ExtTraps 0 }
--
-- Textual Conventions Specific to this MIB Module
--
PdnAtmfM4TestErrorCode ::= TEXTUAL-CONVENTION
    STATUS  current
    DESCRIPTION
        "The specific error codes related to attempting to run a test. The
         codes have the following meanings:

           noError(0)             -- No Error Occurred
           badIfIndex(1)          -- Specified interface does not exist
           noVccFound(2)          -- The Vcc does not exist on the interface
           notOwner(3)            -- Not the current owner of the test
           noResourceAvailable(4) -- Device memory allocation failure
           noLoopbackAllocated(5) -- Could not start the test
           testCompleted(6)       -- Test completed or stopped normally
           testTimeOut(7)         -- Test unsuccessfully due to timeout
           adminStatusDisabled(8) -- ifAdminStatus is Disabled
        "
    SYNTAX  INTEGER {
                noError(0),
                badIfIndex(1),
                noVccFound(2),
                notOwner(3),
                noResourceAvailable(4),
                noLoopbackAllocated(5),
                testCompleted(6),
                testTimeOut(7),
                adminStatusDisabled(8)
            }

--
-- ATM TC layer current and historical fifteen-minute interval statistics
-- pdnAtmfM4TcProtoCurrExtTable and pdnAtmfM4TcProtoHistExtTable
--

-- ATM TC layer current fifteen-minute interval data statistics

pdnAtmfM4TcProtoCurrExtTable OBJECT-TYPE
    SYNTAX  SEQUENCE OF PdnAtmfM4TcProtoCurrExtEntry
    MAX-ACCESS  not-accessible
    STATUS  current
    DESCRIPTION
       "The Paradyne Extension to the atmfM4TcProtoCurrTable of the
        ATM-FORUM-SNMP-M4-MIB."
    ::= { pdnAtmfM4ExtObjects 1   }

pdnAtmfM4TcProtoCurrExtEntry OBJECT-TYPE
    SYNTAX  PdnAtmfM4TcProtoCurrExtEntry
    MAX-ACCESS  not-accessible
    STATUS  current
    DESCRIPTION
       "The Paradyne Extension to the atmfM4TcProtoCurrTable of the
        ATM-FORUM-SNMP-M4-MIB."
    AUGMENTS { atmfM4TcProtoCurrEntry }
    ::= { pdnAtmfM4TcProtoCurrExtTable  1 }

PdnAtmfM4TcProtoCurrExtEntry ::= SEQUENCE {
    pdnAtmfM4TcProtoCurrCellIns         Gauge32,
    pdnAtmfM4TcProtoCurrCellOuts        Gauge32,
    pdnAtmfM4TcProtoCurrInDiscards      Gauge32,
    pdnAtmfM4TcProtoCurrOutDiscards     Gauge32,
    pdnAtmfM4TcProtoCurrLCDEvents       Gauge32,
    pdnAtmfM4TcProtoCurrUnknownCells    Gauge32,
    pdnAtmfM4TcProtoCurrCorrectedHEC    Gauge32
    }

pdnAtmfM4TcProtoCurrCellIns OBJECT-TYPE
    SYNTAX Gauge32
    MAX-ACCESS read-only
    STATUS current
    DESCRIPTION
    "The number of ATM cells received on this interface since the
     start of this interval"
    ::= { pdnAtmfM4TcProtoCurrExtEntry 1 }

pdnAtmfM4TcProtoCurrCellOuts OBJECT-TYPE
    SYNTAX Gauge32
    MAX-ACCESS read-only
    STATUS current
    DESCRIPTION
    "The number of ATM cells sent on this interface since the
     start of this interval"
    ::= { pdnAtmfM4TcProtoCurrExtEntry 2 }

pdnAtmfM4TcProtoCurrInDiscards OBJECT-TYPE
    SYNTAX Gauge32
    MAX-ACCESS read-only
    STATUS current
    DESCRIPTION
    "The number of RX ATM cells dropped on this interface since the
     start of this interval"
    ::= { pdnAtmfM4TcProtoCurrExtEntry 3 }

pdnAtmfM4TcProtoCurrOutDiscards OBJECT-TYPE
    SYNTAX Gauge32
    MAX-ACCESS read-only
    STATUS current
    DESCRIPTION
    "The number of TX ATM cells dropped on this interface since the
     start of this interval"
    ::= { pdnAtmfM4TcProtoCurrExtEntry 4 }

pdnAtmfM4TcProtoCurrLCDEvents OBJECT-TYPE
    SYNTAX Gauge32
    MAX-ACCESS read-only
    STATUS current
    DESCRIPTION
    "The number of Loss of Cell Delineation (LCD) event occurred
     on this interface since the start of this interval"
    ::= { pdnAtmfM4TcProtoCurrExtEntry 5 }

pdnAtmfM4TcProtoCurrUnknownCells OBJECT-TYPE
    SYNTAX Gauge32
    MAX-ACCESS read-only
    STATUS current
    DESCRIPTION
    "The number of unknown Cells received on this interface since
     the start of this interval"
    ::= { pdnAtmfM4TcProtoCurrExtEntry 6 }

pdnAtmfM4TcProtoCurrCorrectedHEC OBJECT-TYPE
    SYNTAX Gauge32
    MAX-ACCESS read-only
    STATUS current
    DESCRIPTION
    "The number of Cell with corrected HEC received on this interface
     since the start of this interval"
    ::= { pdnAtmfM4TcProtoCurrExtEntry 7 }

--
-- ATM TC layer historical fifteen-minute interval statistics
-- (per interface and time interval)
--

pdnAtmfM4TcProtoHistExtTable OBJECT-TYPE
    SYNTAX  SEQUENCE OF PdnAtmfM4TcProtoHistExtEntry
    MAX-ACCESS  not-accessible
    STATUS  current
    DESCRIPTION
       "The Paradyne Extension to the atmfM4TcProtoHistTable of the
        ATM-FORUM-SNMP-M4-MIB."
    ::= { pdnAtmfM4ExtObjects 2   }

pdnAtmfM4TcProtoHistExtEntry OBJECT-TYPE
    SYNTAX  PdnAtmfM4TcProtoHistExtEntry
    MAX-ACCESS  not-accessible
    STATUS  current
    DESCRIPTION
       "The Paradyne Extension to the atmfM4TcProtoHistTable of the
        ATM-FORUM-SNMP-M4-MIB."
    AUGMENTS { atmfM4TcProtoHistEntry }
    ::= { pdnAtmfM4TcProtoHistExtTable  1 }

PdnAtmfM4TcProtoHistExtEntry ::= SEQUENCE {
    pdnAtmfM4TcProtoHistCellIns         Gauge32,
    pdnAtmfM4TcProtoHistCellOuts        Gauge32,
    pdnAtmfM4TcProtoHistInDiscards      Gauge32,
    pdnAtmfM4TcProtoHistOutDiscards     Gauge32,
    pdnAtmfM4TcProtoHistLCDEvents       Gauge32,
    pdnAtmfM4TcProtoHistUnknownCells    Gauge32,
    pdnAtmfM4TcProtoHistCorrectedHEC    Gauge32
    }

pdnAtmfM4TcProtoHistCellIns OBJECT-TYPE
    SYNTAX Gauge32
    MAX-ACCESS read-only
    STATUS current
    DESCRIPTION
    "The number of ATM cells received on this interface
     during this interval"
    ::= { pdnAtmfM4TcProtoHistExtEntry 1 }

pdnAtmfM4TcProtoHistCellOuts OBJECT-TYPE
    SYNTAX Gauge32
    MAX-ACCESS read-only
    STATUS current
    DESCRIPTION
    "The number of ATM cells sent on this interface during
     this interval"
    ::= { pdnAtmfM4TcProtoHistExtEntry 2 }

pdnAtmfM4TcProtoHistInDiscards OBJECT-TYPE
    SYNTAX Gauge32
    MAX-ACCESS read-only
    STATUS current
    DESCRIPTION
    "The number of RX ATM cells dropped on this interface
     during this interval"
    ::= { pdnAtmfM4TcProtoHistExtEntry 3 }

pdnAtmfM4TcProtoHistOutDiscards OBJECT-TYPE
    SYNTAX Gauge32
    MAX-ACCESS read-only
    STATUS current
    DESCRIPTION
    "The number of TX ATM cells dropped on this interface
     during this interval"
    ::= { pdnAtmfM4TcProtoHistExtEntry 4 }

pdnAtmfM4TcProtoHistLCDEvents OBJECT-TYPE
    SYNTAX Gauge32
    MAX-ACCESS read-only
    STATUS current
    DESCRIPTION
    "The number of Loss of Cell Delineation (LCD) event occurred
     on this interface during this interval"
    ::= { pdnAtmfM4TcProtoHistExtEntry 5 }

pdnAtmfM4TcProtoHistUnknownCells OBJECT-TYPE
    SYNTAX Gauge32
    MAX-ACCESS read-only
    STATUS current
    DESCRIPTION
    "The number of unknown Cells received on this interface since
     the start of this interval"
    ::= { pdnAtmfM4TcProtoHistExtEntry 6 }

pdnAtmfM4TcProtoHistCorrectedHEC OBJECT-TYPE
    SYNTAX Gauge32
    MAX-ACCESS read-only
    STATUS current
    DESCRIPTION
    "The number of Cell with corrected HEC received on this interface
     during this interval"
    ::= { pdnAtmfM4TcProtoHistExtEntry 7 }


--
--  The following object defines a group of OAM test types.
--  This group is to contain any Paradyne Specific OAM test
--

pdnAtmfM4TestTypes OBJECT IDENTIFIER ::= { pdnAtmfM4ExtObjects 3 }

--
--  The following OID is defined to initiate continuous Segment OAM Cells
--

pdnAtmfM4TestOAMLoopbackSegMultiCell OBJECT-IDENTITY
     STATUS    current
     DESCRIPTION
          "This identifies an OAM Loopback Test on a VPL, VPC,
          VCL, or VCC termination point, using a segment OAM
          cell.

          The test type must have appended to it a code that uniquely
          identifies an intermediate point responsible for looping
          back the cell.  If this is absent, the loopback is performed
          at the end of the segment or connection.

          E.g., the OID { pdnAtmfM4TestOAMLoopbackSegMultiCell 5 } identifies
          that the loopback should be performed at the intermediate
          point labeled 5."
     ::= { pdnAtmfM4TestTypes 1 }

--
--  The following OID is defined to initiate continuous End to End OAM cells
--

pdnAtmfM4TestOAMLoopbackE2EMultiCell OBJECT-IDENTITY
     STATUS    current
     DESCRIPTION
          "This identifies an OAM Loopback Test on a VPL, VPC,
          VCL, or VCC termination point, using an end-to-end OAM
          cell."
     ::= { pdnAtmfM4TestTypes 2 }

--
--      Test Code to Test Results Matrix
--
--      atmfM4VcTestType                atmfM4VcTestCode Result Table
--      ________________                _____________________________
--
--      atmfM4TestOAMLoopbackSeg(standard is a single cell test)
--                                      pdnAtmfM4Vc1CellLoopTable
--      atmfM4TestOAMLoopbackE2E(standard is a single cell test)
--                                      pdnAtmfM4Vc1CellLoopTable
--
--      pdnAtmfM4TestOAMLoopbackSegMultiCell
--                                      pdnAtmfM4VcLoopbackTestTable
--      pdnAtmfM4TestOAMLoopbackE2EMultiCell
--                                      pdnAtmfM4VcLoopbackTestTable
--

--
-- OAM Loopback test (multiple cell) detailed results table
--

pdnAtmfM4VcLoopbackTestTable   OBJECT-TYPE
    SYNTAX       SEQUENCE OF PdnAtmfM4VcLoopbackTestEntry
    MAX-ACCESS   not-accessible
    STATUS       current
    DESCRIPTION
      "This table contains input and results for OAM loopback
       tests. There can be only one test running per ATM VCC
       This table should be used in conjunction with atmfM4VcTestTable
       with all the semantics of atmfM4VcTestTable."
::= { pdnAtmfM4ExtObjects 4 }

pdnAtmfM4VcLoopbackTestEntry OBJECT-TYPE
    SYNTAX       PdnAtmfM4VcLoopbackTestEntry
    MAX-ACCESS   not-accessible
    STATUS       current
    DESCRIPTION
      "An entry containing objects for test results
       for ATM OAM loopback test"
    AUGMENTS { atmfM4VcTestEntry }
::= { pdnAtmfM4VcLoopbackTestTable 1 }

PdnAtmfM4VcLoopbackTestEntry ::=
    SEQUENCE {
      pdnAtmfM4VcLoopbackTestElpsTime         TimeTicks,
      pdnAtmfM4VcLoopbackTestCellsSent        Gauge32,
      pdnAtmfM4VcLoopbackTestCellsRcvd        Gauge32,
      pdnAtmfM4VcLoopbackTestMinRTDelay       Gauge32,
      pdnAtmfM4VcLoopbackTestMaxRTDelay       Gauge32,
      pdnAtmfM4VcLoopbackTestAvgRTDelay       Gauge32,
      pdnAtmfM4VcLoopbackTestErrorCode        PdnAtmfM4TestErrorCode
    }

pdnAtmfM4VcLoopbackTestElpsTime OBJECT-TYPE
    SYNTAX       TimeTicks
    MAX-ACCESS   read-only
    STATUS       current
    DESCRIPTION
      "This object contains the time that has elapsed since the test started."
::= { pdnAtmfM4VcLoopbackTestEntry 1 }

pdnAtmfM4VcLoopbackTestCellsSent OBJECT-TYPE
    SYNTAX       Gauge32
    MAX-ACCESS   read-only
    STATUS       current
    DESCRIPTION
      "This object specifies a count of the number of test cells that
       have been sent. The value of this object stops increasing
       when it reaches its maximum value."
::= { pdnAtmfM4VcLoopbackTestEntry 2 }

pdnAtmfM4VcLoopbackTestCellsRcvd OBJECT-TYPE
    SYNTAX       Gauge32
    MAX-ACCESS   read-only
    STATUS       current
    DESCRIPTION
      "This object specifies a count of the number of test cells that
       have been received.  The value of this object stops increasing
       when it reaches its maximum value."
::= { pdnAtmfM4VcLoopbackTestEntry 3 }

pdnAtmfM4VcLoopbackTestMinRTDelay OBJECT-TYPE
    SYNTAX       Gauge32
    UNITS        "milliseconds"
    MAX-ACCESS   read-only
    STATUS       current
    DESCRIPTION
      "This object contains the value of the shortest round trip delay
       since the test has been started. It is calculated only on the cells
       that have been received. Cells that were dropped are not counted."
::= { pdnAtmfM4VcLoopbackTestEntry 4 }

pdnAtmfM4VcLoopbackTestMaxRTDelay OBJECT-TYPE
    SYNTAX       Gauge32
    UNITS        "milliseconds"
    MAX-ACCESS   read-only
    STATUS       current
    DESCRIPTION
      "This object contains the value of the longest round trip delay
       since the test has been started. It is calculated only on the cells
       that have been received. Cells that were dropped are not counted."
::= { pdnAtmfM4VcLoopbackTestEntry 5 }

pdnAtmfM4VcLoopbackTestAvgRTDelay OBJECT-TYPE
    SYNTAX       Gauge32
    UNITS        "milliseconds"
    MAX-ACCESS   read-only
    STATUS       current
    DESCRIPTION
      "This object contains the value of the average round trip delay
       since the test has been started. It is calculated only on the cells
       that have been received. Cells that were dropped are not counted."
::= { pdnAtmfM4VcLoopbackTestEntry 6 }

pdnAtmfM4VcLoopbackTestErrorCode OBJECT-TYPE
    SYNTAX       PdnAtmfM4TestErrorCode
    MAX-ACCESS   read-only
    STATUS       current
    DESCRIPTION
      "This object contains the specific error code on the test result."
::= { pdnAtmfM4VcLoopbackTestEntry 7 }

--
-- Single Cell OAM Loopback test detailed results
--
-- This table contains results for single cell OAM tests that are not
-- of a broadcast variety.
--
-- Recommended Use:
--
-- 1) The NMS will start a test using the M4 MIB's atmfM4VcTestTable.
-- 2) Upon starting the test, the agent will put the corresponding OID
--    of a row in this table into the atmfM4VcTestCode object.
-- 3) When the value of atmfM4VcTestResult is not equal to inProgress(3),
--    the values contained in this table should be read.
--
pdnAtmfM4Vc1CellLoopTable   OBJECT-TYPE
    SYNTAX       SEQUENCE OF PdnAtmfM4Vc1CellLoopEntry
    MAX-ACCESS   not-accessible
    STATUS       current
    DESCRIPTION
      "This table contains input and results for single cell OAM
       loopback tests. There can be only one test running per ATM VCC
       This table should be used in conjunction with atmfM4VcTestTable
       with all the semantics of atmfM4VcTestTable."
::= { pdnAtmfM4ExtObjects 5 }

pdnAtmfM4Vc1CellLoopEntry OBJECT-TYPE
    SYNTAX       PdnAtmfM4Vc1CellLoopEntry
    MAX-ACCESS   not-accessible
    STATUS       current
    DESCRIPTION
      "An entry containing objects for test results
       for a single cell ATM OAM loopback test"
    AUGMENTS { atmfM4VcTestEntry }
::= { pdnAtmfM4Vc1CellLoopTable 1 }

PdnAtmfM4Vc1CellLoopEntry ::=
    SEQUENCE {
      pdnAtmfM4Vc1CellLoopRTDelay             Gauge32,
      pdnAtmfM4Vc1CellLoopReportedLocation    OCTET STRING,
      pdnAtmfM4Vc1CellLoopErrorCode           PdnAtmfM4TestErrorCode
    }

pdnAtmfM4Vc1CellLoopRTDelay OBJECT-TYPE
    SYNTAX       Gauge32
    UNITS        "milliseconds"
    MAX-ACCESS   read-only
    STATUS       current
    DESCRIPTION
      "This object contains the value of the round trip delay of the
       the test cell. A value of zero indicates that no cell has been
       received."
::= { pdnAtmfM4Vc1CellLoopEntry 1 }

pdnAtmfM4Vc1CellLoopReportedLocation OBJECT-TYPE
    SYNTAX       OCTET STRING(SIZE(16))
    MAX-ACCESS   read-only
    STATUS       current
    DESCRIPTION
      "This object contains the value of the location identifier
       reported by the received cell."
::= { pdnAtmfM4Vc1CellLoopEntry 2 }

pdnAtmfM4Vc1CellLoopErrorCode OBJECT-TYPE
    SYNTAX       PdnAtmfM4TestErrorCode
    MAX-ACCESS   read-only
    STATUS       current
    DESCRIPTION
      "This object contains the specific error code on the test result."
::= { pdnAtmfM4Vc1CellLoopEntry 3 }

--
-- OAM Segment Loopback Location Code
--
pdnAtmfM4LoopbackLocationTable   OBJECT-TYPE
    SYNTAX       SEQUENCE OF PdnAtmfM4LoopbackLocationEntry
    MAX-ACCESS   not-accessible
    STATUS       current
    DESCRIPTION
          "This table contains the ATM OAM loopback location codes
           for ATM cell layer interfaces."
    ::= { pdnAtmfM4ExtObjects 6 }

pdnAtmfM4LoopbackLocationEntry OBJECT-TYPE
    SYNTAX       PdnAtmfM4LoopbackLocationEntry
    MAX-ACCESS   not-accessible
    STATUS       current
    DESCRIPTION
          "An entry containing objects for ATM OAM loopback locations."
    INDEX { ifIndex }
    ::= { pdnAtmfM4LoopbackLocationTable 1 }

PdnAtmfM4LoopbackLocationEntry ::=
    SEQUENCE {
      pdnAtmfM4LoopbackLocationCode        OCTET STRING
    }

pdnAtmfM4LoopbackLocationCode OBJECT-TYPE
    SYNTAX       OCTET STRING(SIZE(16))
    MAX-ACCESS   read-write
    STATUS       current
    DESCRIPTION
          "This object contains the value of ATM OAM Loopback Location Code"
    ::= { pdnAtmfM4LoopbackLocationEntry 1 }

pdnAtmfM4VpLoopbackTestTable   OBJECT-TYPE
    SYNTAX       SEQUENCE OF PdnAtmfM4VpLoopbackTestEntry
    MAX-ACCESS   not-accessible
    STATUS       current
    DESCRIPTION
      "This table contains input and results for OAM loopback
       tests. There can be only one test running per ATM VPC
       This table should be used in conjunction with atmfM4VpTestTable
       with all the semantics of atmfM4VpTestTable."
::= { pdnAtmfM4ExtObjects 7 }

pdnAtmfM4VpLoopbackTestEntry OBJECT-TYPE
    SYNTAX       PdnAtmfM4VpLoopbackTestEntry
    MAX-ACCESS   not-accessible
    STATUS       current
    DESCRIPTION
      "An entry containing objects for test results
       for ATM OAM loopback test"
    AUGMENTS { atmfM4VpTestEntry }
::= { pdnAtmfM4VpLoopbackTestTable 1 }

PdnAtmfM4VpLoopbackTestEntry ::=
    SEQUENCE {
      pdnAtmfM4VpLoopbackTestElpsTime         TimeTicks,
      pdnAtmfM4VpLoopbackTestCellsSent        Gauge32,
      pdnAtmfM4VpLoopbackTestCellsRcvd        Gauge32,
      pdnAtmfM4VpLoopbackTestMinRTDelay       Gauge32,
      pdnAtmfM4VpLoopbackTestMaxRTDelay       Gauge32,
      pdnAtmfM4VpLoopbackTestAvgRTDelay       Gauge32,
      pdnAtmfM4VpLoopbackTestErrorCode        PdnAtmfM4TestErrorCode
    }

pdnAtmfM4VpLoopbackTestElpsTime OBJECT-TYPE
    SYNTAX       TimeTicks
    MAX-ACCESS   read-only
    STATUS       current
    DESCRIPTION
      "This object contains the time that has elapsed since the test started."
::= { pdnAtmfM4VpLoopbackTestEntry 1 }

pdnAtmfM4VpLoopbackTestCellsSent OBJECT-TYPE
    SYNTAX       Gauge32
    MAX-ACCESS   read-only
    STATUS       current
    DESCRIPTION
      "This object specifies a count of the number of test cells that
       have been sent. The value of this object stops increasing
       when it reaches its maximum value."
::= { pdnAtmfM4VpLoopbackTestEntry 2 }

pdnAtmfM4VpLoopbackTestCellsRcvd OBJECT-TYPE
    SYNTAX       Gauge32
    MAX-ACCESS   read-only
    STATUS       current
    DESCRIPTION
      "This object specifies a count of the number of test cells that
       have been received.  The value of this object stops increasing
       when it reaches its maximum value."
::= { pdnAtmfM4VpLoopbackTestEntry 3 }

pdnAtmfM4VpLoopbackTestMinRTDelay OBJECT-TYPE
    SYNTAX       Gauge32
    UNITS        "milliseconds"
    MAX-ACCESS   read-only
    STATUS       current
    DESCRIPTION
      "This object contains the value of the shortest round trip delay
       since the test has been started. It is calculated only on the cells
       that have been received. Cells that were dropped are not counted."
::= { pdnAtmfM4VpLoopbackTestEntry 4 }

pdnAtmfM4VpLoopbackTestMaxRTDelay OBJECT-TYPE
    SYNTAX       Gauge32
    UNITS        "milliseconds"
    MAX-ACCESS   read-only
    STATUS       current
    DESCRIPTION
      "This object contains the value of the longest round trip delay
       since the test has been started. It is calculated only on the cells
       that have been received. Cells that were dropped are not counted."
::= { pdnAtmfM4VpLoopbackTestEntry 5 }

pdnAtmfM4VpLoopbackTestAvgRTDelay OBJECT-TYPE
    SYNTAX       Gauge32
    UNITS        "milliseconds"
    MAX-ACCESS   read-only
    STATUS       current
    DESCRIPTION
      "This object contains the value of the average round trip delay
       since the test has been started. It is calculated only on the cells
       that have been received. Cells that were dropped are not counted."
::= { pdnAtmfM4VpLoopbackTestEntry 6 }

pdnAtmfM4VpLoopbackTestErrorCode OBJECT-TYPE
    SYNTAX       PdnAtmfM4TestErrorCode
    MAX-ACCESS   read-only
    STATUS       current
    DESCRIPTION
      "This object contains the specific error code on the test result."
::= { pdnAtmfM4VpLoopbackTestEntry 7 }

-- Conformance Information

pdnAtmfM4Groups       OBJECT IDENTIFIER ::= { pdnAtmfM4ExtConformance 1 }
pdnAtmfM4Compliances  OBJECT IDENTIFIER ::= { pdnAtmfM4ExtConformance 2 }

pdnAtmfM4Compliance MODULE-COMPLIANCE
    STATUS  current
    DESCRIPTION
        "The compliance statement for SNMP entities which support
         the ATM M4 extensions."
    MODULE
         GROUP pdnAtmfM4LoopbackLocationGroup
         DESCRIPTION
             "The conditional objects in the Loopback Location Group."
             OBJECT  pdnAtmfM4LoopbackLocationCode
             MIN-ACCESS  read-only
             DESCRIPTION
                "Write access is not required"
    ::= { pdnAtmfM4Compliances 1 }

--
-- Units of Conformance
--

pdnAtmfM4TcCurrGroup OBJECT-GROUP
    OBJECTS {
        pdnAtmfM4TcProtoCurrCellIns,
        pdnAtmfM4TcProtoCurrCellOuts,
        pdnAtmfM4TcProtoCurrInDiscards,
        pdnAtmfM4TcProtoCurrOutDiscards,
        pdnAtmfM4TcProtoCurrLCDEvents,
        pdnAtmfM4TcProtoCurrUnknownCells,
        pdnAtmfM4TcProtoCurrCorrectedHEC
    }
    STATUS  current
    DESCRIPTION
        "The objects in the ATM TC layer current table."
    ::= { pdnAtmfM4Groups 1 }

pdnAtmfM4TcHistGroup OBJECT-GROUP
    OBJECTS {
        pdnAtmfM4TcProtoHistCellIns,
        pdnAtmfM4TcProtoHistCellOuts,
        pdnAtmfM4TcProtoHistInDiscards,
        pdnAtmfM4TcProtoHistOutDiscards,
        pdnAtmfM4TcProtoHistLCDEvents,
        pdnAtmfM4TcProtoHistUnknownCells,
        pdnAtmfM4TcProtoHistCorrectedHEC
    }
    STATUS  current
    DESCRIPTION
        "The objects in the ATM TC layer history table."
    ::= { pdnAtmfM4Groups 2 }

pdnAtmfM4VcLoopbackTestGroup OBJECT-GROUP
    OBJECTS {
        pdnAtmfM4VcLoopbackTestElpsTime,
        pdnAtmfM4VcLoopbackTestCellsSent,
        pdnAtmfM4VcLoopbackTestCellsRcvd,
        pdnAtmfM4VcLoopbackTestMinRTDelay,
        pdnAtmfM4VcLoopbackTestMaxRTDelay,
        pdnAtmfM4VcLoopbackTestAvgRTDelay,
        pdnAtmfM4VcLoopbackTestErrorCode
    }
    STATUS  current
    DESCRIPTION
        "The objects in the ATM OAM Loopback Test (multiple cell) table for ATM VCC."
    ::= { pdnAtmfM4Groups 3 }

pdnAtmfM4Vc1CellLoopGroup OBJECT-GROUP
    OBJECTS {
        pdnAtmfM4Vc1CellLoopRTDelay,
        pdnAtmfM4Vc1CellLoopReportedLocation,
        pdnAtmfM4Vc1CellLoopErrorCode
    }
    STATUS  current
    DESCRIPTION
        "The objects in the ATM Single Cell OAM Loopback Test table."
    ::= { pdnAtmfM4Groups 4 }

pdnAtmfM4LoopbackLocationGroup OBJECT-GROUP
    OBJECTS {
        pdnAtmfM4LoopbackLocationCode
    }
    STATUS  current
    DESCRIPTION
        "The objects in the ATM Loopback Location table."
    ::= { pdnAtmfM4Groups 5 }

pdnAtmfM4VpLoopbackTestGroup OBJECT-GROUP
    OBJECTS {
        pdnAtmfM4VpLoopbackTestElpsTime,
        pdnAtmfM4VpLoopbackTestCellsSent,
        pdnAtmfM4VpLoopbackTestCellsRcvd,
        pdnAtmfM4VpLoopbackTestMinRTDelay,
        pdnAtmfM4VpLoopbackTestMaxRTDelay,
        pdnAtmfM4VpLoopbackTestAvgRTDelay,
        pdnAtmfM4VpLoopbackTestErrorCode
    }
    STATUS  current
    DESCRIPTION
        "The objects in the ATM OAM Loopback Test (multiple cell) table for ATM VPC."
    ::= { pdnAtmfM4Groups 6 }
END
