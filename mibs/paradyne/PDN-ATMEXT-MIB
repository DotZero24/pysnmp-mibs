-- ===============================================================
-- Copyright (C) 2000-2002 Paradyne Corporation.
--  ATM Extension Group
PDN-ATMEXT-MIB DEFINITIONS ::= BEGIN

    IMPORTS
      MODULE-IDENTITY , OBJECT-IDENTITY,
      OBJECT-TYPE, Integer32,  NOTIFICATION-TYPE,
      Unsigned32
       FROM SNMPv2-SMI
      DisplayString,TruthValue
       FROM SNMPv2-TC
      NOTIFICATION-GROUP, OBJECT-GROUP
       FROM SNMPv2-CONF
      pdnAtm
       FROM PDN-HEADER-MIB
      ifIndex,ifOperStatus
       FROM IF-MIB
      atmInterfaceConfEntry, atmTrafficDescrParamEntry,
      atmVpCrossConnectAdminStatus, atmVcCrossConnectAdminStatus,
      aal5VccEntry
       FROM ATM-MIB;

-- ===============================================================
--
--  Extentions to the ATM MIB (RFC 2515)
--
-- ===============================================================

    pdnAtmExtMIB MODULE-IDENTITY
        LAST-UPDATED "200303310000Z"
        ORGANIZATION "Paradyne Networks
                       MIB Working Group"
        CONTACT-INFO
                       "Paradyne Networks
                       331 Newman Springs Road
                       Red Bank, NJ 07701
                       www.paradyne.com

                       General Comments to: mibwg_team@eng.paradyne.com"

        DESCRIPTION
            "This MIB Module extends the ATM-MIB defined in rfc2515"

        REVISION "200305150000Z"
        DESCRIPTION "P. Easwar
            o  Changed object name pdnAtmTrafficRateShape
               to pdnAtmTrafficShaping"
        REVISION "200305110000Z"
        DESCRIPTION "P. Easwar
            o  Added Two New Traffic Descriptor Types
                  o pdnAtmNoClpTaggingNoScrCdvtMdcr
                  o pdnAtmNoClpNoScrCdvtMdcr"
        REVISION "200304310000Z"
        DESCRIPTION "P. Easwar
            o  Added pdnAtmTrafficRateShape."

        REVISION "200303310000Z"
        DESCRIPTION "C. Sikes
            o  Added pdnAal5VccExtTable."

        REVISION "200203270000Z"
        DESCRIPTION "J. Pinto
            o  Added pdnAtmIfConfExtRateShape"

        REVISION "200012290000Z"
        DESCRIPTION "P. Easwar
            o  modified the following traps (name/description)
                o pdnAtmIfConfExtLineRateAlarmSet
                o pdnAtmIfConfExtLineRateAlarmClear
                ...to the following
                o pdnAtmIfConfExtEgressLineRateAlarmSet
                o pdnAtmIfConfExtEgressLineRateAlarmClear
            o  added the following traps
                o pdnAtmIfConfExtIngressLineRateAlarmSet
                o pdnAtmIfConfExtIngressLineRateAlarmClear
            o  deleted the following traps
                o pdnAtmCACGauranteeFailed
                o pdnAtmCACGauranteeRestored"

        REVISION "200012010000Z"
        DESCRIPTION "R. Steinberger
            o Added pdnAtmCACGauranteeFailed and pdnAtmCACGauranteeRestored.
            "

        REVISION "200007060000Z"
        DESCRIPTION "P. Easwar
            o  added the following traps
                o pdnAtmIfConfExtLineRateAlarmSet
                o pdnAtmIfConfExtLineRateAlarmClear
                o pdnAtmIfConfExtVplNoBandwidthAvail
                o pdnAtmIfConfExtVclNoBandwidthAvail
                o changed the description of the following objects
                o pdnAtmIfConfExtVbrRtBandwidthUtil
                o pdnAtmIfConfExtVbrNrtBandwidthUtil
                o  removed the DEFVAL clause from the following objects
                o pdnAtmIfConfExtVbrRtBandwidthUtil
                o pdnAtmIfConfExtVbrNrtBandwidthUtil"

        REVISION "200004280000Z"
        DESCRIPTION "J. Strain
            o  added the following objects to pdnAtmIfConfExtTable
                o pdnAtmIfConfExtBandwidthUtilCbrReserved
                o pdnAtmIfConfExtBandwidthUtilCbrAssigned
                o pdnAtmIfConfExtBandwidthUtilVbrRtReserved
                o pdnAtmIfConfExtBandwidthUtilVbrRtAssigned
                o pdnAtmIfConfExtBandwidthUtilVbrNrtReserved
                o pdnAtmIfConfExtBandwidthUtilVbrNrtAssigned
                o pdnAtmIfConfExtBandwidthUtilUbrReserved
                o pdnAtmIfConfExtBandwidthUtilUbrAssigned"

        REVISION "200003110000Z"
        DESCRIPTION "P. Easwar
            o  added pdnAtmIfConfExtUnknownCellThreshold
               and pdnAtmIfConfExtOcdEventThreshold"
        REVISION "200002180000Z"
        DESCRIPTION "P. Easwar
            o  Initial Release"

         ::= {  pdnAtm 5 }

    pdnAtmExtMIBObjects    OBJECT IDENTIFIER ::= { pdnAtmExtMIB 1 }
    pdnAtmExtMIBTraps      OBJECT IDENTIFIER ::= { pdnAtmExtMIB 2 }
    pdnAtmExtMIBTrapPrefix OBJECT IDENTIFIER ::= { pdnAtmExtMIBTraps 0 }
    pdnAtmExtMIBConformance OBJECT IDENTIFIER ::= { pdnAtmExtMIB 3 }
    pdnAtmExtMIBTrafficDescriptorTypes   OBJECT IDENTIFIER ::= { pdnAtmExtMIB 4 }

pdnAtmNoClpTaggingNoScrCdvtMdcr   OBJECT-IDENTITY
      STATUS   current
      DESCRIPTION
              "This Traffic Descriptor type is for no CLP with tagging
               and no Sustained Cell Rate. The Use of the Parameter
               Vector for this type:
               Parameter 1: Peak Cell Rate in cells/second
                            CLP=0+1 traffic
               Parameter 2: CDVT in tenths of a microsecond
               Parameter 3: Minimum Desired Cell Rate in cells/second (&lt;= PCR)
               Parameter 4: Tolerance To the MDCR Commitment
                            (&gt;= 1/MDCR) in milliseconds
               Parameter 5: not used

               This Traffic Descriptor type is applicable to connections
               following the UBR.2 conformance definition"
      REFERENCE
               "ATM Forum, ATM User-Network Interface,
                 Version 3.0 (UNI 3.0) Specification, 1994.
                ATM Forum, ATM User-Network Interface,
                 Version 3.1 (UNI 3.1) Specification
                 November 1994.
                ATM Forum, Traffic Management Specification,
                 Version 4.0, af-tm-0056.000, June 1996.
                ATM Forum, Traffic Management Specification,
                 Version 4.1, af-tm-0121.000, March 1999.
                ATM Forum, Addendum to Traffic Management Specification,
                 Version 4.1, for an optional Minimum Desired
                 Cell Rate (MDCR), af-tm-0150.000, July 2000."
      ::= { pdnAtmExtMIBTrafficDescriptorTypes 1   }

pdnAtmNoClpNoScrCdvtMdcr   OBJECT-IDENTITY
      STATUS   current
      DESCRIPTION
              "This Traffic Descriptor type is for no CLP
               and no Sustained Cell Rate. The Use of the Parameter
               Vector for this type:
               Parameter 1: Peak Cell Rate in cells/second
                            CLP=0+1 traffic
               Parameter 2: CDVT in tenths of a microsecond
               Parameter 3: Minimum Desired Cell Rate in cells/second (&lt;= PCR)
               Parameter 4: Tolerance To the MDCR Commitment
                            (&gt;= 1/MDCR) in milliseconds
               Parameter 5: not used
               This Traffic Descriptor type is applicable to connections
               following the UBR.1 conformance definition"
      REFERENCE
               "ATM Forum, ATM User-Network Interface,
                 Version 3.0 (UNI 3.0) Specification, 1994.
                ATM Forum, ATM User-Network Interface,
                 Version 3.1 (UNI 3.1) Specification
                 November 1994.
                ATM Forum, Traffic Management Specification,
                 Version 4.0, af-tm-0056.000, June 1996.
                ATM Forum, Traffic Management Specification,
                 Version 4.1, af-tm-0121.000, March 1999.
                ATM Forum, Addendum to Traffic Management Specification,
                 Version 4.1, for an optional Minimum Desired
                 Cell Rate (MDCR), af-tm-0150.000, July 2000."
      ::= { pdnAtmExtMIBTrafficDescriptorTypes 2   }

-- ===============================================================
--
--  Extentions to the ATM Interface Config Table (RFC 2515)
--
--  Release: 1.0  02/18/00 (Initial Release) Prakash Easwar
--
--  This MIB is intended to AUGMENT the atmInterfaceConfTable of the ATM-MIB
--

pdnAtmIfConfExtTable OBJECT-TYPE
    SYNTAX  SEQUENCE OF PdnAtmIfConfExtEntry
    MAX-ACCESS  not-accessible
    STATUS  current
    DESCRIPTION
      "The Paradyne Extension to the atmInterfaceConfTable of the ATM-MIB."
    ::= { pdnAtmExtMIBObjects 1   }

pdnAtmIfConfExtEntry OBJECT-TYPE
    SYNTAX  PdnAtmIfConfExtEntry
    MAX-ACCESS  not-accessible
    STATUS  current
    DESCRIPTION
       "An entry in the Paradyne Extension to the atmInterfaceConfTable of
       the ATM-MIB."
    AUGMENTS { atmInterfaceConfEntry }
    ::= { pdnAtmIfConfExtTable  1 }

PdnAtmIfConfExtEntry ::=
    SEQUENCE {

    pdnAtmIfConfExtVbrRtBandwidthUtil
        Integer32,

    pdnAtmIfConfExtVbrNrtBandwidthUtil
        Integer32,

    pdnAtmIfConfExtHecErrorThreshold
        Integer32,

    pdnAtmIfConfExtUnknownCellThreshold
        Integer32,

    pdnAtmIfConfExtOcdEventThreshold
        Integer32,

    pdnAtmIfConfExtBandwidthUtilCbrReserved
        Integer32,

    pdnAtmIfConfExtBandwidthUtilCbrAssigned
        Integer32,

    pdnAtmIfConfExtBandwidthUtilVbrRtReserved
        Integer32,

    pdnAtmIfConfExtBandwidthUtilVbrRtAssigned
        Integer32,

    pdnAtmIfConfExtBandwidthUtilVbrNrtReserved
        Integer32,

    pdnAtmIfConfExtBandwidthUtilVbrNrtAssigned
        Integer32,

    pdnAtmIfConfExtBandwidthUtilUbrReserved
        Integer32,

    pdnAtmIfConfExtBandwidthUtilUbrAssigned
        Integer32,

    pdnAtmIfConfExtRateShape
        Integer32
    }

pdnAtmIfConfExtVbrRtBandwidthUtil OBJECT-TYPE
    SYNTAX  Integer32 (0..9999)
    MAX-ACCESS  read-write
    STATUS  current
    DESCRIPTION
           "The bandwidth utilization for realtime vbr type traffic
            expressed as a percentage."
    ::= { pdnAtmIfConfExtEntry 1 }

pdnAtmIfConfExtVbrNrtBandwidthUtil OBJECT-TYPE
   SYNTAX  Integer32 (0..9999)
   MAX-ACCESS  read-write
   STATUS  current
   DESCRIPTION
           "The bandwidth utilization for non-realtime VBR type traffic
            expressed as a percentage."
   ::= { pdnAtmIfConfExtEntry 2 }

pdnAtmIfConfExtHecErrorThreshold OBJECT-TYPE
   SYNTAX  Integer32
   MAX-ACCESS  read-write
   STATUS  current
   DESCRIPTION
       "The value of this object represents the threshold value for
        the number of uncrorrectable HEC errors in a 15 minutes interval.
        An SNMP link Up/Down trap would be generated if the number of
        uncorrectable HEC errors in a 15 minutes interval exceeds this threshold.
        The valid range of this object is 0 to 1000. A value of 0 will cause
        a trap to be sent on each occurrence of a HEC error. A value of
        -9999 disables the threshold check.
        The default value for this object is 100. "
   DEFVAL  { 100 }
   ::= { pdnAtmIfConfExtEntry 3 }

 pdnAtmIfConfExtUnknownCellThreshold OBJECT-TYPE
   SYNTAX  Integer32
   MAX-ACCESS  read-write
   STATUS  current
   DESCRIPTION
       "The value of this object represents the threshold value for
        the number of unknown cells in a 15 minutes interval.
        An SNMP trap would be generated if the number of unknown
        cell in a 15 minutes interval exceeds this threshold.
        The valid range of this object is 0 to 1000. A value of 0 will
        cause a trap to be sent on each occurrence of an unknown cell.
        A value of -9999 disables the threshold check.
        The default value for this object is 10"
   DEFVAL  { 10 }
   ::= { pdnAtmIfConfExtEntry 4 }

 pdnAtmIfConfExtOcdEventThreshold OBJECT-TYPE
   SYNTAX  Integer32
   MAX-ACCESS  read-write
   STATUS  current
   DESCRIPTION
       "The value of this object represents the threshold value for
        the number of Out of Cell Delineation(OCD) events in a 15
        minutes interval. An SNMP trap would be generated if the number
        of OCD events in a 15 minutes interval exceeds this threshold.
        The valid range of this object is 0 to 1000. A value of 0 will
        cause a trap to be sent on each occurrence of a HEC error.
        A value of -9999 disables the threshold check.
        The default value for this object is 0"
   DEFVAL  { 0 }
   ::= { pdnAtmIfConfExtEntry 5 }


pdnAtmIfConfExtBandwidthUtilCbrReserved OBJECT-TYPE
          SYNTAX  Integer32
          MAX-ACCESS     read-write
          STATUS         current
          DESCRIPTION
           "This object specifies the percent of the interface bandwidth to
            be allocated to the CBR traffic class."
          ::= { pdnAtmIfConfExtEntry  6}

pdnAtmIfConfExtBandwidthUtilCbrAssigned OBJECT-TYPE
          SYNTAX  Integer32
          MAX-ACCESS     read-only
          STATUS         current
          DESCRIPTION
           "This object specifies the percent of bandwidth utilization
            (sometimes reffered to as over subscription) the connection
            Addmission Control algorithm has already allowed for the CBR class
            of service."
          ::= { pdnAtmIfConfExtEntry  7}

pdnAtmIfConfExtBandwidthUtilVbrRtReserved OBJECT-TYPE
          SYNTAX  Integer32
          MAX-ACCESS     read-write
          STATUS         current
          DESCRIPTION
           "This object specifies the percent of the interface bandwidth to
            be allocated to the VBR-rt traffic class."
          ::= { pdnAtmIfConfExtEntry  8}

pdnAtmIfConfExtBandwidthUtilVbrRtAssigned OBJECT-TYPE
          SYNTAX  Integer32
          MAX-ACCESS     read-only
          STATUS         current
          DESCRIPTION
           "This object specifies the percent of bandwidth utilization
            (sometimes reffered to as over subscription) the connection
            Addmission Control algorithm has already allowed for the VBR-rt class
            of service."
          ::= { pdnAtmIfConfExtEntry  9}

pdnAtmIfConfExtBandwidthUtilVbrNrtReserved OBJECT-TYPE
          SYNTAX  Integer32
          MAX-ACCESS     read-write
          STATUS         current
          DESCRIPTION
           "This object specifies the percent of the interface bandwidth to
            be allocated to the VBR-nrt traffic class."
          ::= { pdnAtmIfConfExtEntry  10}

pdnAtmIfConfExtBandwidthUtilVbrNrtAssigned OBJECT-TYPE
          SYNTAX  Integer32
          MAX-ACCESS     read-only
          STATUS         current
          DESCRIPTION
           "This object specifies the percent of bandwidth utilization
            (sometimes reffered to as over subscription) the connection
            Addmission Control algorithm has already allowed for the VBR-nrt class
            of service."
          ::= { pdnAtmIfConfExtEntry  11}

pdnAtmIfConfExtBandwidthUtilUbrReserved OBJECT-TYPE
          SYNTAX  Integer32
          MAX-ACCESS     read-write
          STATUS         current
          DESCRIPTION
           "This object specifies the percent of the interface bandwidth to
            be allocated to the UBR traffic class."
          ::= { pdnAtmIfConfExtEntry  12}

pdnAtmIfConfExtBandwidthUtilUbrAssigned OBJECT-TYPE
          SYNTAX  Integer32
          MAX-ACCESS     read-only
          STATUS         current
          DESCRIPTION
           "This object specifies the percent of bandwidth utilization
            (sometimes reffered to as over subscription) the connection
            Addmission Control algorithm has already allowed for the UBR class
            of service."
          ::= { pdnAtmIfConfExtEntry 13}

pdnAtmIfConfExtRateShape OBJECT-TYPE
          SYNTAX  Integer32 (512..46080)
	  UNITS "Kbps"
          MAX-ACCESS     read-write
          STATUS         current
          DESCRIPTION
           "This object is used to specify rate shaping on this interface.
            The valid range of this object is 512 to 46080 [512K..46Mbps]
	    with increments of 64K. The default value will be set depending
	    on the interface."
          ::= { pdnAtmIfConfExtEntry 14}

-- ===============================================================
--
--   Extentions to the ATM Interface Config Table (RFC 2515)
--
--  Release: 1.0  02/18/00 (Initial Release) Prakash Easwar
--
-- This MIB is intended to AUGMENT the atmTrafficDescrParamTable of the ATM-MIB
--

pdnAtmTrafficDescrParamExtTable OBJECT-TYPE
    SYNTAX  SEQUENCE OF PdnAtmTrafficDescrParamExtEntry
    MAX-ACCESS  not-accessible
    STATUS  current
    DESCRIPTION
       "The Paradyne Extension to the atmTrafficDescrParamTable of the ATM-MIB."
    ::= { pdnAtmExtMIBObjects 2   }

pdnAtmTrafficDescrParamExtEntry OBJECT-TYPE
    SYNTAX  PdnAtmTrafficDescrParamExtEntry
    MAX-ACCESS  not-accessible
    STATUS  current
    DESCRIPTION
           "An entry in the Paradyne Extension to the atmTrafficDescrParamTable
           of the ATM-MIB."
    AUGMENTS { atmTrafficDescrParamEntry }
    ::= { pdnAtmTrafficDescrParamExtTable  1 }

PdnAtmTrafficDescrParamExtEntry ::=
    SEQUENCE {

    pdnAtmTrafficDescrParamName
        DisplayString (SIZE(1..12)),

    pdnAtmTrafficPolicing
        TruthValue,

    pdnAtmTrafficShaping
        TruthValue
    }

pdnAtmTrafficDescrParamName OBJECT-TYPE
          SYNTAX  DisplayString (SIZE(1..12))
          MAX-ACCESS     read-create
          STATUS         current
          DESCRIPTION
           "The value of this Object identifies the traffic descriptor by a
            by a name."
          ::= { pdnAtmTrafficDescrParamExtEntry  1}

pdnAtmTrafficPolicing OBJECT-TYPE
          SYNTAX  TruthValue
          MAX-ACCESS     read-create
          STATUS         current
          DESCRIPTION
           "The value of this Object determines whether or not
            the vcl/vpl to which this traffic descriptor
            is bound will be policed"
          ::= { pdnAtmTrafficDescrParamExtEntry  2}

pdnAtmTrafficShaping OBJECT-TYPE
          SYNTAX  TruthValue
          MAX-ACCESS     read-create
          STATUS         current
          DESCRIPTION
           "The value of this Object determines whether or not
            the vcl/vpl to which this traffic descriptor
            is bound will be rate shaped to the specified
            traffic contract"
          ::= { pdnAtmTrafficDescrParamExtEntry  3}

-- ===============================================================
--
--   Extentions to the ATM AAL5 Virtual Channel Connection
--   Performance Statistics Table (aal5VccTable) in the ATM-MIB
--   (RFC 2515).
--
--
-- This MIB is intended to AUGMENT the aal5VccTable of the ATM-MIB.
--

pdnAal5VccExtTable OBJECT-TYPE
    SYNTAX  SEQUENCE OF PdnAal5VccExtEntry
    MAX-ACCESS  not-accessible
    STATUS  current
    DESCRIPTION
       "The Paradyne Extension to the aal5VccTable in the ATM-MIB."
    ::= { pdnAtmExtMIBObjects 3  }

pdnAal5VccExtEntry OBJECT-TYPE
    SYNTAX  PdnAal5VccExtEntry
    MAX-ACCESS  not-accessible
    STATUS  current
    DESCRIPTION
           "An entry in the Paradyne Extension to the aal5VccTable.
           in the ATM-MIB."
    AUGMENTS { aal5VccEntry }
    ::= { pdnAal5VccExtTable  1 }

PdnAal5VccExtEntry ::=
    SEQUENCE {
        pdnAal5VccExtOutPDUs        Unsigned32,
        pdnAal5VccExtInPDUs         Unsigned32
    }

pdnAal5VccExtOutPDUs OBJECT-TYPE
          SYNTAX         Unsigned32
          MAX-ACCESS     read-only
          STATUS         current
          DESCRIPTION
           "The total number of AAL5 CPCS PDUs transmitted on the
           interface associated with an AAL5 entry."
          ::= { pdnAal5VccExtEntry  1}

pdnAal5VccExtInPDUs OBJECT-TYPE
          SYNTAX         Unsigned32
          MAX-ACCESS     read-only
          STATUS         current
          DESCRIPTION
           "This total number of AAL5 CPCS PDUs transmitted on the
           interface associated with an AAL5 entry."
          ::= { pdnAal5VccExtEntry  2}


-- ===============================================================
--
-- Trap group
--

pdnAtmIfConfExtExcessInvalidCellsAlarm NOTIFICATION-TYPE
   OBJECTS { ifOperStatus,
             pdnAtmIfConfExtUnknownCellThreshold
           }
   STATUS current
   DESCRIPTION
       "This alarm indicates that the number of cells with
        uncorrectable HEC erros has exceeded the used defined
        the threshold. "
   ::= { pdnAtmExtMIBTrapPrefix 1 }

pdnAtmIfConfExtEgressLineRateAlarmSet NOTIFICATION-TYPE
   OBJECTS { ifIndex }
   STATUS current
   DESCRIPTION
       "This alarm indicates that the line rate of the specified
        interface has dropped below a value which violates the
        traffic contracts of the admitted connections in the egress
        (transmit) direction"
   ::= { pdnAtmExtMIBTrapPrefix 2 }

pdnAtmIfConfExtEgressLineRateAlarmClear NOTIFICATION-TYPE
   OBJECTS { ifIndex }
   STATUS current
   DESCRIPTION
       "This alarm indicates that the line rate of the specified
        interface has risen above a value which would no longer violate the
        traffic contracts of the admitted connections in the egress
        (transmit) direction"
   ::= { pdnAtmExtMIBTrapPrefix 102 }

pdnAtmIfConfExtVplNoBandwidthAvail NOTIFICATION-TYPE
   OBJECTS { atmVpCrossConnectAdminStatus }
   STATUS current
   DESCRIPTION
       "This alarm indicates that the traffic contract(s)
       associated with the Virtual Path (VP) Cross Connect
       cannot be satisfied by the ATM switch.
       It is left upto the implementation to decide whether or
       not the VP cross connect will be admitted"
   ::= { pdnAtmExtMIBTrapPrefix 3 }

pdnAtmIfConfExtVclNoBandwidthAvail NOTIFICATION-TYPE
   OBJECTS { atmVcCrossConnectAdminStatus }
   STATUS current
   DESCRIPTION
       "This alarm indicates that the traffic contract(s)
       associated with the Virtual Channel (VC) Cross Connect
       cannot be satisfied by the ATM switch.
       It is left upto the implementation to decide whether or
       not the VC cross connect will be admitted"
   ::= { pdnAtmExtMIBTrapPrefix 4 }

pdnAtmIfConfExtIngressLineRateAlarmSet NOTIFICATION-TYPE
   OBJECTS { ifIndex }
   STATUS current
   DESCRIPTION
       "This alarm indicates that the line rate of the specified
        interface has dropped below a value which violates the
        traffic contracts of the admitted connections in the ingress
        (receive) direction"
   ::= { pdnAtmExtMIBTrapPrefix 5 }

pdnAtmIfConfExtIngressLineRateAlarmClear NOTIFICATION-TYPE
   OBJECTS { ifIndex }
   STATUS current
   DESCRIPTION
       "This alarm indicates that the line rate of the specified
        interface has risen above a value which would no longer violate the
        traffic contracts of the admitted connections in the ingress
        (receive) direction"
   ::= { pdnAtmExtMIBTrapPrefix 105 }


-- ===============================================================
-- ==
-- == Conformance Information
-- ==
-- ===============================================================

pdnAtmExtMibCompliances   OBJECT IDENTIFIER ::= { pdnAtmExtMIBConformance 1 }
pdnAtmExtMibGroups        OBJECT IDENTIFIER ::= { pdnAtmExtMIBConformance 2 }


--
-- Compliance Statements
--

-- No MANDATORY-GROUPS are specified


--
-- Units of Conformance
--

pdnAtmIfConfExtGroup OBJECT-GROUP
   OBJECTS {
      pdnAtmIfConfExtVbrRtBandwidthUtil,
      pdnAtmIfConfExtVbrNrtBandwidthUtil,
      pdnAtmIfConfExtHecErrorThreshold,
      pdnAtmIfConfExtUnknownCellThreshold,
      pdnAtmIfConfExtOcdEventThreshold,
      pdnAtmIfConfExtBandwidthUtilCbrReserved,
      pdnAtmIfConfExtBandwidthUtilCbrAssigned,
      pdnAtmIfConfExtBandwidthUtilVbrRtReserved,
      pdnAtmIfConfExtBandwidthUtilVbrRtAssigned,
      pdnAtmIfConfExtBandwidthUtilVbrNrtReserved,
      pdnAtmIfConfExtBandwidthUtilVbrNrtAssigned,
      pdnAtmIfConfExtBandwidthUtilUbrReserved,
      pdnAtmIfConfExtBandwidthUtilUbrAssigned,
      pdnAtmIfConfExtRateShape
   }
   STATUS current
   DESCRIPTION
       "Objects grouped for the pdnAtmIfConfExtTable."
   ::= { pdnAtmExtMibGroups 1 }

pdnAtmTrafficDescrParamExtGroup OBJECT-GROUP
   OBJECTS {
      pdnAtmTrafficDescrParamName,
      pdnAtmTrafficPolicing,
      pdnAtmTrafficShaping
   }
   STATUS current
   DESCRIPTION
       "Objects grouped for the pdnAtmTrafficDescrParamExtTable."
   ::= { pdnAtmExtMibGroups 2 }

pdnAal5VccExtGroup OBJECT-GROUP
   OBJECTS {
      pdnAal5VccExtInPDUs,
      pdnAal5VccExtOutPDUs
   }
   STATUS current
   DESCRIPTION
       "Objects grouped for the pdnAal5VccExtTable."
   ::= { pdnAtmExtMibGroups 3 }

pdnAtmExtNotificationGroup NOTIFICATION-GROUP
   NOTIFICATIONS {
      pdnAtmIfConfExtExcessInvalidCellsAlarm,
      pdnAtmIfConfExtEgressLineRateAlarmSet,
      pdnAtmIfConfExtEgressLineRateAlarmClear,
      pdnAtmIfConfExtVplNoBandwidthAvail,
      pdnAtmIfConfExtVclNoBandwidthAvail,
      pdnAtmIfConfExtIngressLineRateAlarmSet,
      pdnAtmIfConfExtIngressLineRateAlarmClear
   }
   STATUS current
   DESCRIPTION
       "Objects grouped for Notification defined in this
        MIB."
   ::= { pdnAtmExtMibGroups 4 }



END
