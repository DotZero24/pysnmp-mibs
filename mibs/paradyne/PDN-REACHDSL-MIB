PDN-REACHDSL-MIB DEFINITIONS ::= BEGIN

--
-- Copyright (C) 2002, Paradyne. All rights reserved.
--

IMPORTS
    MODULE-IDENTITY, OBJECT-TYPE, Unsigned32
        FROM SNMPv2-SMI
    ifIndex
        FROM IF-MIB
    MODULE-COMPLIANCE, OBJECT-GROUP
        FROM SNMPv2-CONF
    DisplayString
        FROM SNMPv2-TC
    pdn-interfaces
        FROM PDN-HEADER-MIB;

pdnReachDSL  MODULE-IDENTITY
        LAST-UPDATED "200210151700Z"
        ORGANIZATION "Paradyne Corp MIB Working Group"
        CONTACT-INFO "Paradyne Networks, Inc.
              8545, 126th Ave. N.,
              Largo, FL 33779
              www.paradyne.com

           General Comments to:
              mibwg_team@eng.paradyne.com

           Editors: A.Z.Shaikh
                    Daniel Varagunasingh
		    Jesus Pinto"

        DESCRIPTION
           "The Paradyne enterprise ReachDSL MIB.
            This MIB is written specifically to facilitate
            in the management of ReachDSL devices as well as
            help in configuration of Spectrum Management
            specific objects for ReachDSL products."

        REVISION "200301151200Z"
        DESCRIPTION
           "1. This mib SHOULD only be used for reachDSL
	       specific technology and not for spectrum
	       management."

        REVISION "200301121200Z"
        DESCRIPTION
           "1. The pdn_spectrummgmt.mib is a new common
	       mib that should be used for all DSL interfaces
	       that require configuration spectrum management
	       parameters."

        REVISION "200210151700Z"
        DESCRIPTION
           "1. Deprecated the reach DSL Circuit Identifier Object.
            2. Added 'Quad Mode' as a loop measurement method.
            3. Added Configuration object for Quad Mode.
            4. Deprecated the old conformance statement &amp; units
               of conformance.
            5. Added new conformance statement &amp; units of
               conformance to clearly reflect the objects' roles."

        REVISION "200207120315Z"
        DESCRIPTION
           "1. Deprecated the Spectrum Management Zone Object.
            2. Added Loop Measurement Method object.
            3. Added EWL Units object.
            4. Added Spectrum Management Mode object.
            5. Added objects for Min &amp; Max EWL values.
            These changes are required for dynamic updation of
            spectrum management configuration."

        ::= { pdn-interfaces 20 }

pdnReachDSLObjects  OBJECT IDENTIFIER ::= { pdnReachDSL 1 }

--
-- START OF PdnReachDSL mib definitions
--

reachDSLSpectrumMgmtSelection OBJECT-TYPE
    SYNTAX      INTEGER {
                    enabled(1),
                    disabled(2)
                }
    MAX-ACCESS  read-write
    STATUS      current
    DESCRIPTION
       "This object has been deprecated. The corresponding
        object in the new pdn_spectrumMgmt.mib should be used
	instead.

	This object is used to Enable or Disable
        Spectrum Management on this device. Enabling
        this object limits the DSL speeds and the maximum
        transmit power on each port based on line length in order
        to meet local Spectrum Management guidelines.

        The values that this object can accept are controlled
        by the 'Mode' object."

    ::= { pdnReachDSLObjects 1 }

reachDSLSpectrumMgmtZone OBJECT-TYPE
    SYNTAX      INTEGER {
                    usa1(1),
                    uk1(2),
                    canada1(3),
                    japan1(4),
                    emea1(5)
                }
    MAX-ACCESS  read-only
    STATUS      deprecated
    DESCRIPTION
       "This object shows the geographic location or the spectrum
        zone used for spectrum management.  It also represents
        which Spectrum Management standard will be used on this
        device to calculate the effective maximum 'Tx Rates' and
        the maximum allowed 'Tx Power' to comply with Spectrum
        Management regulations for that specific region.

        Note: Spectrum Management must be Enabled for
              'SpectrumMgmtZone' to take effect."

    DEFVAL { usa1 }

    ::= { pdnReachDSLObjects 2 }

reachDSLSpectrumMgmtConfTable OBJECT-TYPE
    SYNTAX      SEQUENCE OF ReachDSLSpectrumMgmtConfEntry
    MAX-ACCESS  not-accessible
    STATUS      current
    DESCRIPTION
	"The ReachDSL Spectrum Management Configuration Table
        This table is used for configuring spectrum management
        objects."

    ::= { pdnReachDSLObjects 3 }

reachDSLSpectrumMgmtConfEntry OBJECT-TYPE
    SYNTAX      ReachDSLSpectrumMgmtConfEntry
    MAX-ACCESS  not-accessible
    STATUS      current
    DESCRIPTION
       	"An entry in the ReachDSL Spectrum Management
        Configuration table.

        Note: This entry can be accessed only for ifIndex
              values that belong to a physical interface.
              e.g. for ifType = 'adsl'."

    INDEX   { ifIndex }

    ::= { reachDSLSpectrumMgmtConfTable 1 }

ReachDSLSpectrumMgmtConfEntry ::=
    SEQUENCE {
        reachDSLSpectrumMgmtConfEWL            Unsigned32,
        reachDSLSpectrumMgmtConfLoopLength     INTEGER,
        reachDSLSpectrumMgmtConfAtucMaxTxPower INTEGER,
        reachDSLSpectrumMgmtConfAturMaxTxPower INTEGER,
        reachDSLSpectrumMgmtConfQuadMode       INTEGER
    }

reachDSLSpectrumMgmtConfEWL OBJECT-TYPE
    SYNTAX      Unsigned32
    MAX-ACCESS  read-write
    STATUS      current
    DESCRIPTION
       "This object has been deprecated. The corresponding
        object in the new pdn_spectrumMgmt.mib should be used
	instead.

        The Equivalent Working Length (EWL).  The value selected
        corresponds to the estimated length of the line in

            feet   - if 'EWLUnits' object is 'feet'.
            meters - if 'EWLUnits' object is 'meters'.

        This value is usually specified by the carrier and MUST
        be in integral multiples of

            500 feet, if 'EWLUnits' is 'feet'.
            200 meters, if 'EWLUnits' is 'meters'.

        The range of values that this object can take is determined
        by the 'MinEWL' and 'MaxEWL' objects.
        Changing this object may limit the maximum transmit power
        and the effective DSL speeds at which the ports train up.

        Note: This object will be used only if Spectrum Management
              is enabled and 'LoopMeasurementMethod' is 'ewl'.
              This object shares a mutual exclusion relationship
              with 'ConfLoopLength' &amp; 'ConfQuadMode' objects, as
              only one of the three will be used for configuration
              at any given instant of time."

    ::= { reachDSLSpectrumMgmtConfEntry 1 }

reachDSLSpectrumMgmtConfLoopLength OBJECT-TYPE
    SYNTAX      INTEGER {
                    short(1),
                    medium(2),
                    long(3)
                }
    MAX-ACCESS  read-write
    STATUS      current
    DESCRIPTION
       "This object has been deprecated. The corresponding
        object in the new pdn_spectrumMgmt.mib should be used
	instead.


        This entry specifies the loop length for the line. The
        configurable values are short(1), medium(2) and long(3).
        The 'Loop Length' feature can be used only if the
        'reachDSLSpectrumMgmtSelection' object is Enabled and
        the 'LoopMeasurementMethod' is 'loopLength'. Changing this
        object may limit the maximum transmit power and the
        effective DSL speeds at which ports train up.

        Note: This object shares a mutual exclusion relationship
              with the 'ConfEWL' &amp; 'ConfQuadMode' objects.
              i.e. only one of the three can be used for
              configuration at one time."

    ::= { reachDSLSpectrumMgmtConfEntry 2 }

reachDSLSpectrumMgmtConfAtucMaxTxPower OBJECT-TYPE
    SYNTAX      INTEGER (-140..120)
    UNITS       "tenth dB"
    MAX-ACCESS  read-write
    STATUS      current
    DESCRIPTION
        "The maximum transmit power at the ATUC (in tenth dB).
        This value will be based on the spectrum management
        selection.  It ranges from -140 to 120 in increments
        of 10."

    ::= { reachDSLSpectrumMgmtConfEntry 3 }

reachDSLSpectrumMgmtConfAturMaxTxPower OBJECT-TYPE
    SYNTAX      INTEGER (-140..120)
    UNITS       "tenth dB"
    MAX-ACCESS  read-write
    STATUS      current
    DESCRIPTION
        "The maximum transmit power at the ATUR (in tenth dB).
        This value will be based on the spectrum management
        selection. It ranges from -140 to 120 in increments
        of 10."

    ::= { reachDSLSpectrumMgmtConfEntry 4 }

reachDSLSpectrumMgmtConfQuadMode OBJECT-TYPE
    SYNTAX      INTEGER {
                    sameQuad(1),
                    segregatedQuadUpto3km(2),
                    segregatedQuadAbove3km(3)
                }
    MAX-ACCESS  read-write
    STATUS      current
    DESCRIPTION
       "This object has been deprecated. The corresponding
        object in the new pdn_spectrumMgmt.mib should be used
	instead.

        This entry specifies the quad cable configuration &amp;
        length for the line. The configurable values are
        sameQuad(1), segregatedQuadUpto3km(2) and
        segregatedQuadAbove3km(3). The 'Quad Mode' feature can be
        used only if the 'reachDSLSpectrumMgmtSelection' object
        is Enabled and the 'LoopMeasurementMethod' is 'quadMode'.
        Changing this object may limit the maximum transmit power
        and the effective DSL speeds at which ports train up.

        Note: This object shares a mutual exclusion relationship
              with the 'ConfEWL' &amp; 'ConfLoopLength' objects.
              i.e. only one of the three can be used for
              configuration at one time."

    ::= { reachDSLSpectrumMgmtConfEntry 5 }

reachDSLSpectrumMgmtLineInfoTable OBJECT-TYPE
    SYNTAX      SEQUENCE OF ReachDSLSpectrumMgmtLineInfoEntry
    MAX-ACCESS  not-accessible
    STATUS      current
    DESCRIPTION
       "This object has been deprecated. The corresponding
        object in the new pdn_spectrumMgmt.mib should be used
	instead.

        The ReachDSL Spectrum Management Line Info Table.
        This table gives information about the spectrum
        management ranges that are applicable for each port,
        based on the spectral requirements for the device."

    ::= { pdnReachDSLObjects 4 }

reachDSLSpectrumMgmtLineInfoEntry OBJECT-TYPE
    SYNTAX      ReachDSLSpectrumMgmtLineInfoEntry
    MAX-ACCESS  not-accessible
    STATUS      current
    DESCRIPTION
       "This object has been deprecated. The corresponding
        object in the new pdn_spectrumMgmt.mib should be used
	instead.


        An entry in the reachDSLSpectrumMgmtLineInfoTable table.

        Note: This entry can be accessed only for ifIndex values
              that belong to a physical interface.
              e.g. for ifType = 'adsl'."

    INDEX   { ifIndex }

    ::= { reachDSLSpectrumMgmtLineInfoTable 1 }

ReachDSLSpectrumMgmtLineInfoEntry ::=
    SEQUENCE {
        reachDSLSpectrumMgmtAtucMaxTxRate  Unsigned32,
        reachDSLSpectrumMgmtAtucMinTxRate  Unsigned32,
        reachDSLSpectrumMgmtAtucMaxTxPower INTEGER,
        reachDSLSpectrumMgmtAturMaxTxRate  Unsigned32,
        reachDSLSpectrumMgmtAturMinTxRate  Unsigned32,
        reachDSLSpectrumMgmtAturMaxTxPower INTEGER,
        reachDSLSpectrumMgmtMinEWL         Unsigned32,
        reachDSLSpectrumMgmtMaxEWL         Unsigned32
    }

reachDSLSpectrumMgmtAtucMaxTxRate OBJECT-TYPE
    SYNTAX      Unsigned32
    UNITS       "bps"
    MAX-ACCESS  read-only
    STATUS      current
    DESCRIPTION
       "This object has been deprecated. The corresponding
        object in the new pdn_spectrumMgmt.mib should be used
	instead.


        This rate will be the max allowed Tx Rate(in bps) for
        the port based on the Spectrum Management requirements for
        ATUC in a particular spectral compliance configuration."

    ::= { reachDSLSpectrumMgmtLineInfoEntry 1 }

reachDSLSpectrumMgmtAtucMinTxRate OBJECT-TYPE
    SYNTAX      Unsigned32
    UNITS       "bps"
    MAX-ACCESS  read-only
    STATUS      current
    DESCRIPTION
       "This object has been deprecated. The corresponding
        object in the new pdn_spectrumMgmt.mib should be used
	instead.


        This rate will be the min allowed Tx Rate based on the
        spectrum management requirements for the ATUC. The
        MinTxRate will be upper bounded by
        'reachDSLSpectrumMgmtAtucMaxTxRate' object."

    ::= { reachDSLSpectrumMgmtLineInfoEntry 2 }

reachDSLSpectrumMgmtAtucMaxTxPower OBJECT-TYPE
    SYNTAX      INTEGER(-140..120)
    UNITS       "tenth dB"
    MAX-ACCESS  read-only
    STATUS      current
    DESCRIPTION
       "This object has been deprecated. The corresponding
        object in the new pdn_spectrumMgmt.mib should be used
	instead.


        The maximum transmit power at the ATUC (in tenth dB).
        This value will be based on the spectrum management
        selection."

    ::= { reachDSLSpectrumMgmtLineInfoEntry 3 }

reachDSLSpectrumMgmtAturMaxTxRate OBJECT-TYPE
    SYNTAX      Unsigned32
    UNITS       "bps"
    MAX-ACCESS  read-only
    STATUS      current
    DESCRIPTION
       "This object has been deprecated. The corresponding
        object in the new pdn_spectrumMgmt.mib should be used
	instead.


        This rate will be the max allowed Tx Rate(in bps) for
        the port based on the Spectrum Management requirements for
        ATUC in a particular spectral compliance configuration."

    ::= { reachDSLSpectrumMgmtLineInfoEntry 4 }

reachDSLSpectrumMgmtAturMinTxRate OBJECT-TYPE
    SYNTAX      Unsigned32
    UNITS       "bps"
    MAX-ACCESS  read-only
    STATUS      current
    DESCRIPTION
       "This object has been deprecated. The corresponding
        object in the new pdn_spectrumMgmt.mib should be used
	instead.


        This rate will be the min allowed Tx Rate based on the
        spectrum management requirements for the ATUR. The
        MinTxRate will be upper bounded by
        'reachDSLSpectrumMgmtAturMaxTxRate' object."

    ::= { reachDSLSpectrumMgmtLineInfoEntry 5 }

reachDSLSpectrumMgmtAturMaxTxPower OBJECT-TYPE
    SYNTAX      INTEGER(-140..120)
    UNITS       "tenth dB"
    MAX-ACCESS  read-only
    STATUS      current
    DESCRIPTION
       "This object has been deprecated. The corresponding
        object in the new pdn_spectrumMgmt.mib should be used
	instead.


        The maximum transmit power at the ATUR (in tenth dB).  This
        value will be based on the spectrum management selection."

    ::= { reachDSLSpectrumMgmtLineInfoEntry 6 }

reachDSLSpectrumMgmtMinEWL OBJECT-TYPE
    SYNTAX      Unsigned32
    MAX-ACCESS  read-only
    STATUS      current
    DESCRIPTION
       "This object has been deprecated. The corresponding
        object in the new pdn_spectrumMgmt.mib should be used
	instead.


        The minimum value (in feet, if 'EWLUnits' is 'feet, or in
        meters, if 'EWLUnits' is 'meters') that the 'ConfEWL'
        object can accept. Together with the 'MaxEWL' object,
        this object indicates the range of EWL when 'EWLUnits' is
        either 'feet' or 'meters'.

        Note : This object is valid only if the
               'LoopMeasurementMethod' object is 'ewl'."

    ::= { reachDSLSpectrumMgmtLineInfoEntry 7 }

reachDSLSpectrumMgmtMaxEWL OBJECT-TYPE
    SYNTAX      Unsigned32
    MAX-ACCESS  read-only
    STATUS      current
    DESCRIPTION
       "This object has been deprecated. The corresponding
        object in the new pdn_spectrumMgmt.mib should be used
	instead.


        The maximum value (in feet, if 'EWLUnits' is 'feet, or in
        meters, if 'EWLUnits' is 'meters') that the 'ConfEWL'
        object can accept. Together with the 'MinEWL' object,
        this object indicates the range of EWL when 'EWLUnits' is
        either 'feet' or 'meters'.

        Note : This object is valid only if the
               'LoopMeasurementMethod' object is 'ewl'."

    ::= { reachDSLSpectrumMgmtLineInfoEntry 8 }

reachDSLLineTable OBJECT-TYPE
    SYNTAX      SEQUENCE OF ReachDSLLineEntry
    MAX-ACCESS  not-accessible
    STATUS      current
    DESCRIPTION
       "The ReachDSL Line Table."

    ::= { pdnReachDSLObjects 5 }

reachDSLLineEntry OBJECT-TYPE
    SYNTAX      ReachDSLLineEntry
    MAX-ACCESS  not-accessible
    STATUS      current
    DESCRIPTION
       "An entry in the reachDSLLineTable.

        Note: This entry can be accessed only for ifIndex values
              that belong to a physical interface.
              e.g. for ifType = 'adsl'."

    INDEX   { ifIndex }

    ::= { reachDSLLineTable 1 }

ReachDSLLineEntry ::=
    SEQUENCE {
        reachDSLPotsDetectionVoltage  INTEGER,
        reachDSLCircuitIdentifier     DisplayString
    }

reachDSLPotsDetectionVoltage OBJECT-TYPE
    SYNTAX      INTEGER (0..74)
    UNITS       "volts"
    MAX-ACCESS  read-write
    STATUS      current
    DESCRIPTION
        "This object defines the configurable voltage used to
        detect the presence of POTS on the DSL line. The range
        is 0-74 volts. The default value is 3 volts.

        Note: This object can be accessed only for ifIndex
              values that belong to a physical interface.
              i.e. ifType = adsl/reachDSL."

    DEFVAL { 3 }

    ::= { reachDSLLineEntry 1 }

reachDSLCircuitIdentifier OBJECT-TYPE
    SYNTAX      DisplayString (SIZE(1..32))
    MAX-ACCESS  read-write
    STATUS      deprecated
    DESCRIPTION
       "The value of this object reflects the transmission
        vendor's circuit identifier to facilitate troubleshooting.

        Note: This object can be accessed only for ifIndex
              values that belong to a physical interface.
              e.g. for ifType = 'adsl'.

        This object is deprecated in favor of ifAlias. It is
        highly recommended that future implementations use
        ifAlias to store the Circuit Identifier associated with
        reach DSL interfaces."

    ::= { reachDSLLineEntry 2 }

reachDSLSpectrumMgmtLoopMeasurementMethod OBJECT-TYPE
    SYNTAX      INTEGER {
                    none(1),
                    loopLength(2),
                    ewl(3),
                    quadMode(4)
                }
    MAX-ACCESS  read-only
    STATUS      current
    DESCRIPTION
       "This object has been deprecated. The corresponding
        object in the new pdn_spectrumMgmt.mib should be used
	instead.


        This object indicates the measurement method used in
        describing the Loop Length of a circuit. Following are the
        details of each of the options:

            none(1)       - Indicates that the Spectral Compliance
                            is NOT dependant on any Loop Length
                            measurements or configurations.
            loopLength(2) - The 'ConfLoopLength' object is used to
                            determine spectral compliance. The
                            'ConfEWL' &amp; 'ConfQuadMode' objects are
                            not used in this mode.
            ewl(3)        - The 'ConfEWL' object is used to
                            configure the estimated loop length,
                            which is used to determine spectral
                            compliance. In this mode the
                            'ConfLoopLength' &amp; 'ConfQuadMode'
                            objects are not used.
            quadMode(4)   - The 'ConfQuadMode' object is used to
                            determine spectral compliance. The
                            'ConfEWL' &amp; 'ConfLoopLength' objects
                            are not used in this mode.

        This object determines which of the three objects :
        'ConfEWL', 'ConfLoopLength' or 'ConfQuadMode' is used
        (if any) to enforce spectrally compliant maximum
        'Tx Rates' and the maximum allowed 'Tx Power' on a given
        circuit."

    ::= { pdnReachDSLObjects 6 }

reachDSLSpectrumMgmtEWLUnits OBJECT-TYPE
    SYNTAX      INTEGER {
                    none(1),
                    feet(2),
                    meters(3)
                }
    MAX-ACCESS  read-only
    STATUS      current
    DESCRIPTION
       "This object has been deprecated. The corresponding
        object in the new pdn_spectrumMgmt.mib should be used
	instead.


        This object indicates the units of measurement used in
        describing the Estimated Working Length of a circuit.
        Following are the details of each of the units:

            none(1)     - Indicates that the Spectral Compliance is
                          NOT dependant on the 'ConfEWL' object.
            feet(2)     - The 'ConfEWL' is measured and configured
                          in feet.
            meters(3)   - The 'ConfEWL' is measured and configured
                          in meters."

    ::= { pdnReachDSLObjects 7 }

reachDSLSpectrumMgmtMode OBJECT-TYPE
    SYNTAX      INTEGER {
                    enableOnly(1),
                    disableOnly(2),
                    both(3)
                }
    MAX-ACCESS  read-only
    STATUS      current
    DESCRIPTION
       "This object has been deprecated. The corresponding
        object in the new pdn_spectrumMgmt.mib should be used
	instead.


        This object restricts the MAX-ACCESS of the 'Selection'
        object.
        Following are the details of each of the values:

            enableOnly(1)  - Indicates that the 'Selection' object
                             IS always 'enabled' and cannot be set
                             to 'disabled'.
            disableOnly(2) - Indicates that the 'Selection' object
                             IS always 'disabled' and cannot be set
                             to 'enabled'.
            both(3)        - Indicates that the 'Selection' object
                             will accept both the 'enabled' and
                             'disabled' values."

    ::= { pdnReachDSLObjects 8 }

--
-- Conformance information
--

pdnReachDSLConformance  OBJECT IDENTIFIER
    ::= { pdnReachDSL 2 }

pdnReachDSLGroups       OBJECT IDENTIFIER
    ::= { pdnReachDSLConformance 1 }

pdnReachDSLCompliances  OBJECT IDENTIFIER
    ::= { pdnReachDSLConformance 2 }

-- Compliance statements

pdnReachDSLCompliance1 MODULE-COMPLIANCE
    STATUS      current
    DESCRIPTION
       "The compliance statement for SNMP entities which manage
        ReachDSL interfaces."

    MODULE   -- this module
        MANDATORY-GROUPS {
            pdnReachDSLGeneralConfigGroup,
            pdnReachDSLGeneralInformationGroup
        }

-- The groups :
--      pdnReachDSLEWLModeGroup
--      pdnReachDSLLoopLengthModeGroup
--      pdnReachDSLQuadModeGroup
-- are mutually exclusive; at most one of these groups is
-- implemented for a particular reachDSL interface. If the
-- Loop Measurement Method is 'none', then none of these
-- groups should be implemented.

    GROUP   pdnReachDSLEWLModeGroup
    DESCRIPTION
       "This group is mandatory for reachDSL interfaces whose
        loop/line length measurement method is EWL.
        i.e.the reachDSLSpectrumMgmtLoopMeasurementMethod object
        is 'ewl'."

    GROUP   pdnReachDSLLoopLengthModeGroup
    DESCRIPTION
       "This group is mandatory for reachDSL interfaces whose
        loop/line length measurement method is LoopLength (short
        /medium/long).
        i.e.the reachDSLSpectrumMgmtLoopMeasurementMethod object
        is 'loopLength'."

    GROUP   pdnReachDSLQuadModeGroup
    DESCRIPTION
       "This group is mandatory for reachDSL interfaces whose
        loop/line length measurement method is based on Quads.
        i.e.the reachDSLSpectrumMgmtLoopMeasurementMethod object
        is 'quadMode'."

    OBJECT      reachDSLSpectrumMgmtSelection
    MIN-ACCESS  read-only
    DESCRIPTION
       "Write access is not required."

    OBJECT      reachDSLSpectrumMgmtConfAtucMaxTxPower
    MIN-ACCESS  read-only
    DESCRIPTION
       "Write access is not required."

    OBJECT      reachDSLSpectrumMgmtConfAturMaxTxPower
    MIN-ACCESS  read-only
    DESCRIPTION
       "Write access is not required."

    OBJECT      reachDSLPotsDetectionVoltage
    MIN-ACCESS  read-only
    DESCRIPTION
       "Write access is not required."

    ::= { pdnReachDSLCompliances 2 }

-- Units of conformance

pdnReachDSLGeneralConfigGroup OBJECT-GROUP
    OBJECTS {
        reachDSLSpectrumMgmtSelection,
        reachDSLSpectrumMgmtConfAtucMaxTxPower,
        reachDSLSpectrumMgmtConfAturMaxTxPower,
        reachDSLPotsDetectionVoltage
    }
    STATUS      current
    DESCRIPTION
       "A collection of configuration objects required for
        providing access to configure all reachDSL interfaces."

    ::= { pdnReachDSLGroups 4 }

pdnReachDSLGeneralInformationGroup OBJECT-GROUP
    OBJECTS {
        reachDSLSpectrumMgmtAtucMaxTxRate,
        reachDSLSpectrumMgmtAtucMinTxRate,
        reachDSLSpectrumMgmtAtucMaxTxPower,
        reachDSLSpectrumMgmtAturMaxTxRate,
        reachDSLSpectrumMgmtAturMinTxRate,
        reachDSLSpectrumMgmtAturMaxTxPower,
        reachDSLSpectrumMgmtLoopMeasurementMethod,
        reachDSLSpectrumMgmtEWLUnits,
        reachDSLSpectrumMgmtMode
    }
    STATUS      current
    DESCRIPTION
       "A collection of objects providing information applicable
        to all reachDSL interfaces."

    ::= { pdnReachDSLGroups 5 }

-- The following three groups are mutually exclusive; at most one
-- of these groups is implemented for any interface

pdnReachDSLEWLModeGroup OBJECT-GROUP
    OBJECTS {
        reachDSLSpectrumMgmtConfEWL,
        reachDSLSpectrumMgmtMinEWL,
        reachDSLSpectrumMgmtMaxEWL
    }
    STATUS      current
    DESCRIPTION
       "A collection of objects providing configuration
        access and information specific to reachDSL interfaces
        whose loop/line length measurement method is EWL.
        i.e.the reachDSLSpectrumMgmtLoopMeasurementMethod object
        is 'ewl'."

    ::= { pdnReachDSLGroups 6 }

pdnReachDSLLoopLengthModeGroup OBJECT-GROUP
    OBJECTS {
        reachDSLSpectrumMgmtConfLoopLength
    }
    STATUS      current
    DESCRIPTION
       "A collection of object(s) providing configuration
        access and information specific to reachDSL interfaces
        whose loop/line length measurement method is Loop Length
        (short/medium/long).
        i.e.the reachDSLSpectrumMgmtLoopMeasurementMethod object
        is 'loopLength'."

    ::= { pdnReachDSLGroups 7 }

pdnReachDSLQuadModeGroup OBJECT-GROUP
    OBJECTS {
        reachDSLSpectrumMgmtConfQuadMode
    }
    STATUS      current
    DESCRIPTION
       "A collection of object(s) providing configuration
        access and information specific to reachDSL interfaces
        whose loop/line length measurement method is based on the
        Quad configuration.
        i.e.the reachDSLSpectrumMgmtLoopMeasurementMethod object
        is 'quadMode'."

    ::= { pdnReachDSLGroups 8 }

--
-- Deprecated definitions - Compliance
--

pdnReachDSLCompliance MODULE-COMPLIANCE
    STATUS      deprecated
    DESCRIPTION
       "The compliance statement for SNMP entities which manage
        ReachDSL interfaces."

MODULE   -- this module
    MANDATORY-GROUPS {
       pdnReachDSLConfigurationGroup, pdnReachDSLInformationGroup
    }

    OBJECT      reachDSLSpectrumMgmtSelection
    MIN-ACCESS  read-only
    DESCRIPTION
       "Write access is not required."

    OBJECT      reachDSLSpectrumMgmtConfEWL
    MIN-ACCESS  read-only
    DESCRIPTION
       "Write access is not required."

    OBJECT      reachDSLSpectrumMgmtConfLoopLength
    MIN-ACCESS  read-only
    DESCRIPTION
       "Write access is not required."

    OBJECT      reachDSLSpectrumMgmtConfAtucMaxTxPower
    MIN-ACCESS  read-only
    DESCRIPTION
       "Write access is not required."

    OBJECT      reachDSLSpectrumMgmtConfAturMaxTxPower
    MIN-ACCESS  read-only
    DESCRIPTION
       "Write access is not required."

    OBJECT      reachDSLPotsDetectionVoltage
    MIN-ACCESS  read-only
    DESCRIPTION
       "Write access is not required."

    OBJECT      reachDSLCircuitIdentifier
    MIN-ACCESS  read-only
    DESCRIPTION
       "Write access is not required."

    ::= { pdnReachDSLCompliances 1 }

--
-- Deprecated definitions - Groups
--

pdnReachDSLConfigurationGroup OBJECT-GROUP
    OBJECTS {
        reachDSLSpectrumMgmtSelection,
        reachDSLSpectrumMgmtConfEWL,
        reachDSLSpectrumMgmtConfLoopLength,
        reachDSLSpectrumMgmtConfAtucMaxTxPower,
        reachDSLSpectrumMgmtConfAturMaxTxPower,
        reachDSLPotsDetectionVoltage,
        reachDSLCircuitIdentifier
    }
    STATUS      deprecated -- Set as required for the group
    DESCRIPTION
       "A collection of configuration objects required
        for providing access to configuration as well
        as status information for reachDSL products."

    ::= { pdnReachDSLGroups 1 }

pdnReachDSLInformationGroup OBJECT-GROUP
    OBJECTS {
        reachDSLSpectrumMgmtAtucMaxTxRate,
        reachDSLSpectrumMgmtAtucMinTxRate,
        reachDSLSpectrumMgmtAtucMaxTxPower,
        reachDSLSpectrumMgmtAturMaxTxRate,
        reachDSLSpectrumMgmtAturMinTxRate,
        reachDSLSpectrumMgmtAturMaxTxPower,
        reachDSLSpectrumMgmtMinEWL,
        reachDSLSpectrumMgmtMaxEWL,
        reachDSLSpectrumMgmtLoopMeasurementMethod,
        reachDSLSpectrumMgmtEWLUnits,
        reachDSLSpectrumMgmtMode
    }
    STATUS      deprecated -- Set as required for the group
    DESCRIPTION
        "A collection of objects providing access meant
         specifically for accessing information for
         for reachDSL products."

    ::= { pdnReachDSLGroups 2 }

pdnReachDSLDeprecatedGroup OBJECT-GROUP
    OBJECTS {
        reachDSLSpectrumMgmtZone,
        reachDSLCircuitIdentifier
    }
    STATUS      deprecated -- Set as required for the group
    DESCRIPTION
        "A collection of objects that have been deprecated."

    ::= { pdnReachDSLGroups 3 }

END
