PDN-SCMEXT-MIB DEFINITIONS ::= BEGIN

IMPORTS
	RowStatus
		FROM SNMPv2-TC
	OBJECT-TYPE
		FROM RFC-1212
	pdnAtm
		FROM PDN-HEADER-MIB;

-- ===============================================================
--
--  Shelf Configuration Module ATM Configuration - J.Strain
--
--  Release: 1.0  05/26/99 (Initial Release)
--
--  History:
--  02/23/2000 - revamped devAtmAutoConfigXcon table
--			   - documented both tables better
--  02/07/2000 - fixed mistake in mib where devAtmMaxVci object
--      should be read-write not read-only
--

devAtmScm OBJECT IDENTIFIER ::= { pdnAtm  4 }

-- ==========================================================
--	Atm Configure Max VCI per VPI Table
--
--	This table is used to configure the maximum number of VCIs
--	supported by each of the uplink's VPIs.  If a VPI has not been assigned
--	any VCIs, it is not displayed on this table.  The total number of VCIs
--	that can be assigned to all the uplink's VPIs can be read from ATM-MIB
--	object 'atmInterfaceMzxVccs'
--	devAtmMaxIfIndex:	The uplink number for which Max VCIs are being
--	                     assigned.  This field is fixed at 1.
--	devAtmMaxVpi:	The VPI number for which Max VCIs are being assigned.
--	devAtmMaxVci:	The maximum VCI supported by the VPI on the
--	                     specified uplink.
--

devAtmMaxVciVpiConfig OBJECT IDENTIFIER ::= { devAtmScm  1 }

devAtmMaxVciVpiConfigTable OBJECT-TYPE
    SYNTAX  SEQUENCE OF DevAtmMaxVciVpiConfigEntry
    ACCESS  not-accessible
    STATUS  mandatory
    DESCRIPTION
           "The Paradyne MaxVciVpi-MIB Table ."
    ::= { devAtmMaxVciVpiConfig  1 }

devAtmMaxVciVpiConfigEntry OBJECT-TYPE
    SYNTAX  DevAtmMaxVciVpiConfigEntry
    ACCESS  not-accessible
    STATUS  mandatory
    DESCRIPTION
           "An entry in the Paradyne MaxVciVpi-MIB Interface Config Table."
    INDEX   { devAtmMaxIfIndex,  devAtmMaxVpi }
    ::= { devAtmMaxVciVpiConfigTable  1 }

DevAtmMaxVciVpiConfigEntry ::=
    SEQUENCE {
    devAtmMaxIfIndex
        INTEGER ,

    devAtmMaxVpi
        INTEGER ,

    devAtmMaxVci
        INTEGER ,

    devAtmMaxVciVpiRowStatus
        RowStatus
    }

devAtmMaxIfIndex OBJECT-TYPE
    SYNTAX  INTEGER
    ACCESS  read-only
    STATUS  mandatory
    DESCRIPTION
           "The index value which uniquely identifies the
            interface for which this entry contains information
            on interface tests.  The interface identified by a
            particular value of this index is the same interface
            as identified by the same value of ifIndex from the
            Interfaces table of MIB II (RFC 1213)."
    ::= { devAtmMaxVciVpiConfigEntry 1 }

devAtmMaxVpi OBJECT-TYPE
    SYNTAX  INTEGER
    ACCESS  read-only
    STATUS  mandatory
    DESCRIPTION
           "This object is used to specify the vpi of interest."
    ::= { devAtmMaxVciVpiConfigEntry  2 }

devAtmMaxVci OBJECT-TYPE
    SYNTAX  INTEGER
    ACCESS  read-write
    STATUS  mandatory
    DESCRIPTION
           "This object is used to specify the maximum number of vci's
			that will be allowed for the corresponding vpi."
    ::= { devAtmMaxVciVpiConfigEntry  3 }

devAtmMaxVciVpiRowStatus OBJECT-TYPE
    SYNTAX  RowStatus
    ACCESS  read-write
    STATUS  mandatory
    DESCRIPTION
           "This object is used to create
		a new row or modify or delete an
		existing row in this table."
--    DEFVAL  { active }

    ::= { devAtmMaxVciVpiConfigEntry  4 }

-- ==========================================================
--	Atm Auto Configure Cross Connect Table
--
--	This Table is used to automatically generate a fixed number of
--	VCL's on the said ifindex and automatically generate cross connects
--	to all the corresponding slot/ports in the Chassis.
--
--
--	This  table is used to configure the parameters necessary to
--	generate the automatic connections in the Cross Connect Table.  All
--	automatic connections are standard connections.  The automatic
--	connections are generated by configuring the parameters on this form,
--	clearing the current Cross Connect Table and resetting the SCM card.
--	devAtmAutoConfigXconIfIndex  #: The uplink ifindex used for all
--				automatic connections.
--	Base devAtmAutoConfigXconVpi: The uplink VPI used for all automatic
--				connections.  The default value for this field is 0.
--	Base devAtmAutoConfigXconVci: The uplink VCI used for the first
--				automatic connection. The uplink VCIs for automatic
--				connections are numbered consecutively starting at the
--				Base VCI.  The default  value for this field is 32.
--
-- NOTE: This Table is SLE compliant because just like the ATM-MIB
--       where there is ONLY one cross connect table per SLE, there is
--       also only one devAtmAutoConfigXconTable table per SLE.
--
-- ============================================================

devAtmAutoConfigXcon OBJECT IDENTIFIER ::= { devAtmScm  2 }

devAtmAutoConfigXconTable OBJECT-TYPE
    SYNTAX  SEQUENCE OF DevAtmAutoConfigXconEntry
    ACCESS  not-accessible
    STATUS  mandatory
    DESCRIPTION
           "The Paradyne AutoConfigXcon-MIB Table ."
    ::= { devAtmAutoConfigXcon  1 }

devAtmAutoConfigXconEntry OBJECT-TYPE
    SYNTAX  DevAtmAutoConfigXconEntry
    ACCESS  not-accessible
    STATUS  mandatory
    DESCRIPTION
           "An entry in the Paradyne AutoConfigXcon-MIB Table."

    INDEX   { devAtmAutoConfigXconChannel }
    ::= { devAtmAutoConfigXconTable  1 }

DevAtmAutoConfigXconEntry ::=
    SEQUENCE {

    devAtmAutoConfigXconChannel
        INTEGER ,

    devAtmAutoConfigXconIfIndex
        INTEGER ,

    devAtmAutoConfigXconVpi
        INTEGER ,

    devAtmAutoConfigXconVci
        INTEGER ,

    devAtmAutoConfigXconTraffic
        INTEGER ,

    devAtmAutoConfigXconRowStatus
        RowStatus

    }

devAtmAutoConfigXconChannel OBJECT-TYPE
    SYNTAX  INTEGER
    ACCESS  read-only
    STATUS  mandatory
    DESCRIPTION
           "The index value which uniquely identifies the
			row in this table as being a unique range of
			cross connects being automatically generated
			for the ifindex-devAtmAutoConfigXconIfIndex.
		"
    ::= { devAtmAutoConfigXconEntry 1 }

devAtmAutoConfigXconIfIndex OBJECT-TYPE
    SYNTAX  INTEGER
    ACCESS  read-write
    STATUS  mandatory
    DESCRIPTION
           "The index value which uniquely identifies the
            interface for which this entry contains information
            on interface tests.  The interface identified by a
            particular value of this index is the same interface
            as identified by the same value of ifIndex from the
            Interfaces table of MIB II (RFC 1213)."
    ::= { devAtmAutoConfigXconEntry 2 }

devAtmAutoConfigXconVpi OBJECT-TYPE
    SYNTAX  INTEGER
    ACCESS  read-write
    STATUS  mandatory
    DESCRIPTION
           "This object is used to specify the vpi part of the vpi/vci"
    ::= { devAtmAutoConfigXconEntry  3 }

devAtmAutoConfigXconVci OBJECT-TYPE
    SYNTAX  INTEGER
    ACCESS  read-write
    STATUS  mandatory
    DESCRIPTION
           "This object is used to specify the starting vci value."
    ::= { devAtmAutoConfigXconEntry  4 }

devAtmAutoConfigXconTraffic OBJECT-TYPE
    SYNTAX  INTEGER
    ACCESS  read-write
    STATUS  mandatory
    DESCRIPTION
           "This object is used to specify the class of service
            that this connection will be having."
    ::= { devAtmAutoConfigXconEntry  5 }

devAtmAutoConfigXconRowStatus OBJECT-TYPE
    SYNTAX  RowStatus
    ACCESS  read-write
    STATUS  mandatory
    DESCRIPTION
           "This object is used to create
        a new row or modify or delete an
        existing row in this table."

    ::= { devAtmAutoConfigXconEntry  6 }

END
