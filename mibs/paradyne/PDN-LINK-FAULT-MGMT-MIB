PDN-LINK-FAULT-MGMT-MIB DEFINITIONS ::= BEGIN

IMPORTS
    MODULE-IDENTITY, OBJECT-TYPE,
    Integer32
        FROM SNMPv2-SMI
    ifIndex
        FROM RFC1213-MIB
    pdnLinkFaultMgmt
        FROM PDN-HEADER-MIB
    MODULE-COMPLIANCE, OBJECT-GROUP
        FROM SNMPv2-CONF;

pdnLinkFaultMgmtMIB MODULE-IDENTITY
    LAST-UPDATED "200304031900Z"
    ORGANIZATION "Paradyne Corporation MIB Working Group"
    CONTACT-INFO
            "         Paradyne Networks Inc.

             Postal:  8545, 126th Ave. N.
                      Largo, FL 33779
                      US
             Editor:  Jesus Pinto
             Email:   mibwg_team@eng.paradyne.com"

    DESCRIPTION
            "This management information module supports the objects
             to be used for fault management configuration on primary
	     and secondary links."

   REVISION "200304231800Z"  -- April 23, 2003
   DESCRIPTION "- Added pdnLinkFailureSfPeriodBeforeSwitching object,
		- Added pdnLinkFailureSfBerThreshold object."

    ::= { pdnLinkFaultMgmt 1 }

pdnLinkFaultMgmtMIBObjects OBJECT IDENTIFIER ::=
	{ pdnLinkFaultMgmtMIB 1 }

pdnLinkFaultMgmtMIBConformance OBJECT IDENTIFIER ::=
	{ pdnLinkFaultMgmtMIB 2 }

pdnLinkFaultMgmtApsSelection OBJECT-TYPE
    SYNTAX      INTEGER { enabled(1), disabled(2) }
    MAX-ACCESS  read-write
    STATUS      current
    DESCRIPTION
            "This object is used to enable or disable the
	     Automatic Protection Switching (Aps) feature
	     on this device. This object can not be enabled
	     if the -Switchover due to link failures- is enabled."
    ::= { pdnLinkFaultMgmtMIBObjects 1 }

pdnLinkFaultMgmtSwitchoverSelection OBJECT-TYPE
    SYNTAX      INTEGER { enabled(1), disabled(2) }
    MAX-ACCESS  read-write
    STATUS      current
    DESCRIPTION
            "This object is used to enable or disable the
	     Switchover Due to link failures feature on
	     on this device. This object can not be enabled
	     if the APS feature is enabled."
    ::= { pdnLinkFaultMgmtMIBObjects 2 }

pdnDualLinkSelection OBJECT-TYPE
    SYNTAX      INTEGER { enabled(1), disabled(2) }
    MAX-ACCESS  read-write
    STATUS      current
    DESCRIPTION
            "This object is used to enable or disable the
	     ability to split traffic among dual links."
    ::= { pdnLinkFaultMgmtMIBObjects 4 }


--
-- Switchover due to Link Failure
--
-- This set of objects are used to configure the
-- conditions and thresholds in the primary link
-- before initiating a switchover to the alternate link.
--
--

pdnLinkFailureConfigTable OBJECT-TYPE
    SYNTAX	SEQUENCE OF PdnLinkFailureConfigEntry
    MAX-ACCESS  not-accessible
    STATUS	current
    DESCRIPTION
	    "This table contains one row per link
	     being monitored for link failures."
    ::= { pdnLinkFaultMgmtMIBObjects 3 }

pdnLinkFailureConfigEntry OBJECT-TYPE
    SYNTAX      PdnLinkFailureConfigEntry
    MAX-ACCESS  not-accessible
    STATUS      current
    DESCRIPTION
            "Configuration information about a particular
             interface being monitored for link failured."
    INDEX   { ifIndex }
    ::= { pdnLinkFailureConfigTable 1 }

PdnLinkFailureConfigEntry ::=
    SEQUENCE {
	pdnLinkFailureLOSPeriodBeforeSwitching	Integer32,
        pdnLinkFailureLOFPeriodBeforeSwitching	Integer32,
	pdnLinkFailureAISLPeriodBeforeSwitching	Integer32,
	pdnLinkFailureSdPeriodBeforeSwitching	Integer32,
	pdnLinkFailureSfPeriodBeforeSwitching	Integer32,
	pdnLinkFailureSdBerThreshold		Integer32,
	pdnLinkFailureSfBerThreshold		Integer32
    }

pdnLinkFailureLOSPeriodBeforeSwitching OBJECT-TYPE
    SYNTAX      Integer32 (0..300)
    UNITS	"seconds"
    MAX-ACCESS  read-write
    STATUS      current
    DESCRIPTION
            "This object allows users to configure the amount of
             time a LOS condition shall exist on this uplink before
             initiating a switchover.

	     Switchover due to LOS condition on this uplink will
             not be valid if any of the APS (Automatic Protection
             Switching) is enabled."
    ::= { pdnLinkFailureConfigEntry 1 }


pdnLinkFailureLOFPeriodBeforeSwitching OBJECT-TYPE
    SYNTAX      Integer32 (0..300)
    UNITS	"seconds"
    MAX-ACCESS  read-write
    STATUS      current
    DESCRIPTION
            "This object allows users to configure the amount of
             time a LOF condition shall exist on this uplink before
             initiating a switchover.

	     Switchover due to LOF condition on this uplink will
             not be valid if any of the APS (Automatic Protection
             Switching) is enabled."
    ::= { pdnLinkFailureConfigEntry 2 }

pdnLinkFailureAISLPeriodBeforeSwitching OBJECT-TYPE
    SYNTAX      Integer32 (0..300)
    UNITS	"seconds"
    MAX-ACCESS  read-write
    STATUS      current
    DESCRIPTION
            "This object allows users to configure the amount of
             time a AIS-L condition shall exist on this uplink before
             initiating a switchover.

	     Switchover due to AIS-L condition on this uplink will
             not be valid if any of the APS (Automatic Protection
             Switching) is enabled."
    ::= { pdnLinkFailureConfigEntry 3 }

pdnLinkFailureSdPeriodBeforeSwitching OBJECT-TYPE
    SYNTAX      Integer32 (0..300)
    UNITS	"seconds"
    MAX-ACCESS  read-write
    STATUS      current
    DESCRIPTION
            "This object allows users to configure the amount of
             time a Signal Degraded (Sd) condition shall exist on
	     this uplink before initiating a switchover.

	     Switchover due to Sd condition on this uplink will
             not be valid if any of the APS (Automatic Protection
             Switching) is enabled."
    ::= { pdnLinkFailureConfigEntry 4 }

pdnLinkFailureSfPeriodBeforeSwitching OBJECT-TYPE
    SYNTAX      Integer32 (0..300)
    UNITS	"seconds"
    MAX-ACCESS  read-write
    STATUS      current
    DESCRIPTION
            "This object allows users to configure the amount of
             time a Signal Failure Bit (Sf) condition shall exist on
	     this uplink before initiating a switchover.

	     Switchover due to Sf condition on this uplink will
             not be valid if any of the APS (Automatic Protection
             Switching) is enabled."
    ::= { pdnLinkFailureConfigEntry 5 }


pdnLinkFailureSdBerThreshold OBJECT-TYPE
    SYNTAX      Integer32 (5..9)
    MAX-ACCESS  read-write
    STATUS      current
    DESCRIPTION
            "This object allows users to configure the threshold
             for the Signal Degrade Bit Error Rate (Sd).

	     The negated value of this number is used as the exponent
	     of 10 for computing the threshold value for the Bit Error
	     Rate (BER). For example, a value of 5 indicates a BER
	     threshold of 10^-5."
    ::= { pdnLinkFailureConfigEntry 6 }

pdnLinkFailureSfBerThreshold OBJECT-TYPE
    SYNTAX      Integer32 (3..5)
    MAX-ACCESS  read-write
    STATUS      current
    DESCRIPTION
            "This object allows users to configure the threshold
             for the Signal Failure Bit Error Rate (Sf).

	     The negated value of this number is used as the exponent
	     of 10 for computing the threshold value for the Bit Error
	     Rate (BER). For example, a value of 5 indicates a BER
	     threshold of 10^-5."
    ::= { pdnLinkFailureConfigEntry 7 }


--
-- Conformance Information
--

pdnLinkFaultMgmtCompliances OBJECT IDENTIFIER
     ::= { pdnLinkFaultMgmtMIBConformance 1 }

pdnLinkFaultMgmtGroups OBJECT IDENTIFIER
     ::= { pdnLinkFaultMgmtMIBConformance 2 }

pdnLinkFaultMgmtCompliance MODULE-COMPLIANCE
     STATUS  current
     DESCRIPTION
             "The compliance statement for SNMP entities capable
	      of configuring link fault conditions."
     MODULE
     MANDATORY-GROUPS {	pdnLinkFaultMgmtGeneralGroup }

     OBJECT pdnLinkFaultMgmtApsSelection
     MIN-ACCESS read-only
     DESCRIPTION
	     "Write access is not required."

     OBJECT pdnLinkFaultMgmtSwitchoverSelection
     MIN-ACCESS read-only
     DESCRIPTION
	     "Write access is not required."

     OBJECT pdnDualLinkSelection
     MIN-ACCESS read-only
     DESCRIPTION
	     "Write access is not required."

     OBJECT pdnLinkFailureLOSPeriodBeforeSwitching
     MIN-ACCESS read-only
     DESCRIPTION
	     "Write access is not required."

     OBJECT pdnLinkFailureLOFPeriodBeforeSwitching
     MIN-ACCESS read-only
     DESCRIPTION
	     "Write access is not required."

     OBJECT pdnLinkFailureAISLPeriodBeforeSwitching
     MIN-ACCESS read-only
     DESCRIPTION
	     "Write access is not required."

     OBJECT pdnLinkFailureSdPeriodBeforeSwitching
     MIN-ACCESS read-only
     DESCRIPTION
	     "Write access is not required."

     OBJECT pdnLinkFailureSdBerThreshold
     MIN-ACCESS read-only
     DESCRIPTION
	     "Write access is not required."

     OBJECT pdnLinkFailureSfPeriodBeforeSwitching
     MIN-ACCESS read-only
     DESCRIPTION
	     "Write access is not required."

     OBJECT pdnLinkFailureSfBerThreshold
     MIN-ACCESS read-only
     DESCRIPTION
	     "Write access is not required."

-- Optional groups

     GROUP pdnLinkSwitchoverGroup
     DESCRIPTION
	     "Implementation of this group is optional for the
	      link fault management implementation."

     ::= { pdnLinkFaultMgmtCompliances 1 }

-- units of conformance

pdnLinkFaultMgmtGeneralGroup	OBJECT-GROUP
     OBJECTS
     {
	pdnLinkFaultMgmtApsSelection,
	pdnLinkFaultMgmtSwitchoverSelection,
	pdnDualLinkSelection
     }
     STATUS current
     DESCRIPTION
             "A collection of configuration objects applicable
              to link fault mgmt implementation."
     ::= { pdnLinkFaultMgmtGroups 1 }

pdnLinkSwitchoverGroup OBJECT-GROUP
     OBJECTS
     {
	pdnLinkFailureLOSPeriodBeforeSwitching,
	pdnLinkFailureLOFPeriodBeforeSwitching,
	pdnLinkFailureAISLPeriodBeforeSwitching,
	pdnLinkFailureSdPeriodBeforeSwitching,
	pdnLinkFailureSfPeriodBeforeSwitching,
	pdnLinkFailureSdBerThreshold,
	pdnLinkFailureSfBerThreshold
     }
     STATUS current
     DESCRIPTION
             "A collection of configuration objects applicable to
              all redundancy implementations."
     ::= { pdnLinkFaultMgmtGroups 2 }

END
