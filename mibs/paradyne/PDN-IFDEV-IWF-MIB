-- ===================================================================
-- == Copyright (C) 2004 Paradyne Corporation.                      ==
-- ===================================================================

PDN-IFDEV-IWF-MIB DEFINITIONS ::= BEGIN

IMPORTS
   MODULE-IDENTITY, OBJECT-TYPE, Counter32
      FROM SNMPv2-SMI
   OBJECT-GROUP, MODULE-COMPLIANCE
      FROM SNMPv2-CONF
   TEXTUAL-CONVENTION
       FROM SNMPv2-TC
   ifIndex
      FROM IF-MIB
   pdn-interfaces
      FROM PDN-HEADER-MIB;

pdnIfDevIwfMIB MODULE-IDENTITY
   LAST-UPDATED "200409100000Z"  -- September 10, 2004
   ORGANIZATION "Paradyne Networks
                 MIB Working Group
                 Other information about group editing the MIB"
   CONTACT-INFO "Paradyne Networks, Inc.
                 8545 126th Avenue North
                 Largo, FL 33733
                 www.paradyne.com

                 General Comments to: mibwg_team@paradyne.com

                 Editor
                    Clay Sikes"

   DESCRIPTION  "This module provides objects pertaining to the
                 management of an `Interface Device Interworking
                 Function' (IfDev IWF).

                 The following documents should be referenced with
                 respect to this MIB module:
                 [RFC 1662]    Simpson, W., `PPP in HDLC-like
                               framing', July 1994."

   REVISION     "200409100000Z"  -- September 10, 2004
   DESCRIPTION  "Initial release."

::=  { pdn-interfaces 27 }



-- ====================================================================
-- == Define groups for Notifications, MIB Objects, Accessible for   ==
-- == Notifications (AFNs), and Conformance.                         ==
-- == These may just be place holders.                               ==
-- ====================================================================
pdnIfDevIwfNotifications OBJECT IDENTIFIER ::= { pdnIfDevIwfMIB 0 }
pdnIfDevIwfObjects       OBJECT IDENTIFIER ::= { pdnIfDevIwfMIB 1 }
pdnIfDevIwfAFNs          OBJECT IDENTIFIER ::= { pdnIfDevIwfMIB 2 }
pdnIfDevIwfConformance   OBJECT IDENTIFIER ::= { pdnIfDevIwfMIB 3 }




-- ====================================================================
-- ==                  Textual Conventions                           ==
-- ====================================================================
TxRxUnit ::= TEXTUAL-CONVENTION
   STATUS      current
   DESCRIPTION "Identifies the unit of transmission.

                The unit other(1) is used when none of the other
                enumerations apply.

                The unit bits(2) is used when bits are being
                transmitted.

                The unit octets(3) is used for groups of 8 bits.

                The unit frames(4) is used for transmission at the data
                link layer.  A frame may include a header and/or a
                trailer, along with some number of units of data.

                The unit packets(5) is a basic unit of encapsulation,
                which typically is passed across the interface between
                the network layer and the data link layer.  A packet
                is usually mapped to a frame;  the exceptions are
                when data link layer fragmentation is being performed,
                or when multiple packets are incorporated into a single
                frame.

                The unit datagrams(6) is a unit of transmission in the
                network layer (such as IP).  A datagram may be
                encapsulated in one or more packets passed to the data
                link layer."

   REFERENCE   "RFC 1662, Section 1.2, `Terminology'."
   SYNTAX      INTEGER {
                  other(1),
                  bits(2),
                  octets(3),
                  frames(4),
                  packets(5),
                  datagrams(6)
               }




-- ====================================================================
-- ==                  MIB Objects                                   ==
-- ====================================================================




-- ===================================================================
-- == pdnIfDevIwfStatsTotalTable                                    ==
-- ===================================================================
pdnIfDevIwfStatsTotalTable  OBJECT-TYPE
   SYNTAX      SEQUENCE OF PdnIfDevIwfStatsTotalEntry
   MAX-ACCESS  not-accessible
   STATUS      current
   DESCRIPTION "The IfDev IWF Total Statistics Table.  This table
                contains counters for statistics.  Counters in this
                group contain `total' counts which are marked from the
                time the system was last re-initialized."
   ::= { pdnIfDevIwfObjects 1 }

pdnIfDevIwfStatsTotalEntry  OBJECT-TYPE
   SYNTAX      PdnIfDevIwfStatsTotalEntry
   MAX-ACCESS  not-accessible
   STATUS      current
   DESCRIPTION "An entry in the IfDev IWF Total Statistics Table."
   INDEX       { ifIndex }
   ::= { pdnIfDevIwfStatsTotalTable 1 }

PdnIfDevIwfStatsTotalEntry ::=
   SEQUENCE {
      pdnIfDevIwfStatsTotalBufferUnderruns        Counter32,
      pdnIfDevIwfStatsTotalMRUErrors              Counter32,
      pdnIfDevIwfStatsTotalRxUnit                 TxRxUnit,
      pdnIfDevIwfStatsTotalRx                     Counter32
   }

pdnIfDevIwfStatsTotalBufferUnderruns  OBJECT-TYPE
   SYNTAX      Counter32
   MAX-ACCESS  read-only
   STATUS      current
   DESCRIPTION "The number of times there was a buffer underrun."
   ::= { pdnIfDevIwfStatsTotalEntry 1 }

pdnIfDevIwfStatsTotalMRUErrors  OBJECT-TYPE
   SYNTAX      Counter32
   MAX-ACCESS  read-only
   STATUS      current
   DESCRIPTION "The number of times the Maximum Receive Unit size
                was exceeded."
   ::= { pdnIfDevIwfStatsTotalEntry 2 }

pdnIfDevIwfStatsTotalRxUnit  OBJECT-TYPE
   SYNTAX      TxRxUnit
   MAX-ACCESS  read-only
   STATUS      current
   DESCRIPTION "The unit type of data being received by the IWF."
   ::= { pdnIfDevIwfStatsTotalEntry 3 }

pdnIfDevIwfStatsTotalRx  OBJECT-TYPE
   SYNTAX      Counter32
   MAX-ACCESS  read-only
   STATUS      current
   DESCRIPTION "The number of units received by the IWF."
   ::= { pdnIfDevIwfStatsTotalEntry 4 }



-- ====================================================================
-- ==                  Accessible for Notifications (AFNs)           ==
-- ====================================================================
-- None defined



-- ===================================================================
-- ==                  Traps/Notifications                          ==
-- ===================================================================
-- None defined



-- ====================================================================
-- ==                  Conformance Information                       ==
-- ====================================================================

pdnIfDevIwfCompliances  OBJECT IDENTIFIER ::=
   { pdnIfDevIwfConformance 1 }
pdnIfDevIwfGroups       OBJECT IDENTIFIER ::=
   { pdnIfDevIwfConformance 2 }


-- ===========================
-- == Compliance Statements ==
-- ===========================


pdnIfDevIwfCompliance  MODULE-COMPLIANCE
   STATUS      current
   DESCRIPTION "The compliance statement for IfDev IWFs."
   MODULE      -- this module
   -- No mandatory groups are specified.

   GROUP       pdnIfDevIwfStatsTotalBufferUnderrunsGroup
   DESCRIPTION "This group is required for implementations that need
                to display IWF buffer underruns and the particular
                IfDev can support the underrun detection."

   GROUP       pdnIfDevIwfStatsTotalMRUErrorsGroup
   DESCRIPTION "This group is required for implementations that need
                to display IWF MRU errors and the particular IfDev
                can support MRU error detection."

   GROUP       pdnIfDevIwfStatsTotalRxGroup
   DESCRIPTION "This group is required for implementations that need
                to display the units of transmission received by the
                IWF and the IfDev can support the detection. "

    ::= { pdnIfDevIwfCompliances 1 }


-- ==========================
-- == Units of Conformance ==
-- ==========================

pdnIfDevIwfObjGroups   OBJECT IDENTIFIER ::= { pdnIfDevIwfGroups 1 }
pdnIfDevIwfAfnGroups   OBJECT IDENTIFIER ::= { pdnIfDevIwfGroups 2 }
pdnIfDevIwfNtfyGroups  OBJECT IDENTIFIER ::= { pdnIfDevIwfGroups 3 }


-- ===================
-- == Object Groups ==
-- ===================


pdnIfDevIwfStatsTotalBufferUnderrunsGroup  OBJECT-GROUP
   OBJECTS {
      pdnIfDevIwfStatsTotalBufferUnderruns
   }
   STATUS      current
   DESCRIPTION "The number of times there was a buffer underrun."
   ::= { pdnIfDevIwfObjGroups 1 }

pdnIfDevIwfStatsTotalMRUErrorsGroup  OBJECT-GROUP
   OBJECTS {
      pdnIfDevIwfStatsTotalMRUErrors
   }
   STATUS      current
   DESCRIPTION "The number of times the Maximum Receive Unit size
                was exceeded."
   ::= { pdnIfDevIwfObjGroups 2 }

pdnIfDevIwfStatsTotalRxGroup  OBJECT-GROUP
   OBJECTS {
      pdnIfDevIwfStatsTotalRxUnit,
      pdnIfDevIwfStatsTotalRx
   }
   STATUS      current
   DESCRIPTION "The number of units received by the IWF."
   ::= { pdnIfDevIwfObjGroups 3 }



-- =========================================
-- == Accessible for Notifications Groups ==
-- =========================================
-- None defined



-- =========================
-- == Notification Groups ==
-- =========================
-- None defined




-- =========
-- == END ==
-- =========
END
