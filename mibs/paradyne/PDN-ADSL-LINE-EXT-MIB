-- ===============================================================
-- Copyright (C) 2004 Paradyne Corporation.
-- ===============================================================

PDN-ADSL-LINE-EXT-MIB DEFINITIONS ::= BEGIN

IMPORTS
    MODULE-IDENTITY, OBJECT-TYPE, Unsigned32, Integer32, Gauge32
        FROM SNMPv2-SMI
    OBJECT-GROUP, MODULE-COMPLIANCE
        FROM SNMPv2-CONF
    TEXTUAL-CONVENTION, RowStatus
        FROM SNMPv2-TC
    SnmpAdminString
        FROM SNMP-FRAMEWORK-MIB
    ifIndex
        FROM IF-MIB
    pdn-interfaces
        FROM PDN-HEADER-MIB;

pdnAdslLineExtMIB MODULE-IDENTITY
    LAST-UPDATED "200503290000Z"  -- March 29, 2005
    ORGANIZATION "Paradyne Networks
                  MIB Working Group
                  Other information about group editing the MIB"
    CONTACT-INFO "Paradyne Networks, Inc.
                  8545 126th Avenue North
                  Largo, FL 33733
                  www.paradyne.com

                  General Comments to: mibwg_team@paradyne.com

                  Editor
                      Clay Sikes"

    DESCRIPTION
        "This MIB module is a supplement to the ADSL-LINE-MIB and to the
         ADSL-LINE-EXT-MIB, the `standard` MIBs, where additional objects
         are needed to support ADSL modes or flavors not covered in the
         `standard` MIBs.

         At the time this MIB was defined, the IETF ADSL MIB Working does
         not have any work on the 'standard' MIBs planned and/or has not produced
         a schedule to address ADSL2/ADSL2plus needs. As a result, these objects may
         be a `temporary' solution until MIBs/Objects are defined or extended to
         meet the needs of ADSL2/ADSL2plus.

         The following documents that should be referenced with respect
         to this MIB:
         [G.997.1]        ITU-T G997.1 `Physical layer management for Digital
                          Subscriber Line (DSL) transceivers', May 2003.
         [G.991.1 Am 1]   ITU-T-G997.1 Amendment 1 `Physical layer management
                          for Digital Subscriber Line (DSL) transceivers
                          Amendment 1', December 2003.
         [OA 305]         Telenor Networks Specification, Specification
                          Number OA 305, `Requirements for equipment to be
                          connected to the local sub-loop in the access network
                          of Telenor.  Equipment providing ADSL and PSTN or
                          ISDN Basic Access Services, full unbundled access
                          (service type EDF)', TN-NL-U-T/OA305/0101 2005,
                          Edition 4.1, January 1, 2005.
         [WT-090]         DSL Forum Working Text WT-090 `Protocol Independent
                          Object Model for Managing Next Generation ADSL
                          Technologies', Revision-1, September 2003.
         [WT-090-4]       DSL Forum Working Text WT-090 `Protocol Independent
                          Object Model for Managing Next Generation ADSL
                          Technologies', Revision-4, June 2004.
         [RFC 2662]       Bathrick, G., Ly, F. `ADSL-LINE-MIB', August 1999.
         [RFC 3440]       Ly, F., Bathrick, G. `ADSL-LINE-EXT-MIB', December 2002.

         Generally the MIB objects are defined using G.997.1 and the MIB
         objects are arranged using WT-090.

         =====================================================================
         ==                                                                 ==
         ==            Copyright (C) 2004 Paradyne Corporation.             ==
         ==                                                                 ==
         ====================================================================="

    REVISION "200503290000Z"  -- March 29, 2005
    DESCRIPTION "The `special' value was missing in the syntax for
                 pdnAdslLineStatusAtucActAtp and pdnAdslLineStatusAtucActAtp.

                 Added a note in the pdnAdslLineSubCarStatusTable indicating
                 that some objects may not be valid if a loop diagnostic has
                 not completed execution.

                 pdnAdslLineSubCarAtucHlogMt and pdnAdslLineSubCarAturHlogMt
                 were incorrectly represented.  These object had the syntax
                 and description of HLOGpsds and HLOGpsus from G.997.1.
                 Corrected the syntax and description for the HlogMt objects
                 and added pdnAdslLineSubCarAtucHlogPs and
                 pdnAdslLineSubCarAturHlogPs objects."

    REVISION "200501060000Z"  -- January 6, 2005
    DESCRIPTION "Changed the identifiers for the objects in the
                 pdnAdslLineStatusTable and the pdnAdslLineSubCarStatusTable
                 from `Ds' to `Atuc' and from `Us' to `Atur'.  When these
                 tables were first created, it was not absolutely clear how
                 `Ds' and `Us' mapped to `Atuc' and `Atur'.  However in
                 December 2004, the DSL Forum released TR-090, `Protocol
                 Independent Object Model for Managing Next Generation ADSL
                 Technologies' which notes in Section 5.4.4, `ATU Channel
                 Thresholds' and in Section 5.5.1, `ATU Sub-Carrier Status'
                 that the object instances associated with the ATU-C use
                 the xxxds version of the parameter while those associated
                 with the ATU-R use the xxxus version of the parameter.

                 Paradyne's Compliance Engineering requested a change to
                 the ranges for Maximum Nominal Transmit PSD objects per
                 the Telenor Networks Specification [OA 305], Section 7.2.2,
                 `Downstream transmit spectral mask'.
                 The objects effected were:
                     pdnAdslPsdConfAtucMaxNomPsd
                        from (-600..-400) to (-800..-400)
                     pdnAdslPsdConfAturMaxNomPsd
                        from (-600..-380) to (-650..-380)."

    REVISION "200410150000Z"  -- October 15, 2004
    DESCRIPTION "Fix transposed characters for PdnAdslTransmissionModeType
                 bits 38 and 39.
                 Added Line Status Table and Line Subcarrier Status Table.
                 Added missing range limits for pdnAdslLineL2Atpr."

    REVISION "200409100000Z"  -- September 10, 2004
    DESCRIPTION "Added new objects that were required for G.997.1 Amendment 1.
                 The additions include bit definitions for
                 PdnAdslTransmissionModeType and the pdnAdslLineL2Atprt object."

    REVISION "200404210000Z"  -- April 21, 2004
    DESCRIPTION "The value for pdnAdslPsdConfAtucMaxNomPsd did not match the range in
                G.997.1 (05/2003), Section 7.3.1.2.1. The correct range is -60 to -40."

    REVISION "200404200000Z"  -- April 20, 2004
    DESCRIPTION "Change the pdnAdslLineExtTable from augments to be indexed.
                 Some SNMP agents do a read-modify-write on a table row. As
                 a result, the instrumentation code may not be able to
                 determine which object the manager actually wants to set. For
                 example, consider the case where a manager wants to set the
                 transmission mode to allow ADSL2Plus modes. The instrumentation code,
                 in the case of a read-modify-write cycle, could result in receiving
                 a row where the adslLineTransAtucConf is is set one way while the
                 pdnAdslLineTransAtucConfig is set another way. This could result
                 in unpredictable results. This change will prevent the objects in
                 the ExtTables from existing in the same row as the objects in the
                 standard tables and prevent the unpredictable case from occurring."
    REVISION "200403010000Z"  -- March 1, 2004
    DESCRIPTION "Correct OID enumerations for objects in the pdnAdslPsdConfTable.
                 The OID 6 was skipped. That is pdnAdslPsdConfAturmaxNomAtp and
                 following objects were renumbered.
                 The pdnAdslLineLdsf object referred to the pdnAdslLinePmsf object
                 which was removed. pdnAdslLineLdsf was updated to remove the
                 reference."

    REVISION "200312080000Z"  -- December 8, 2003
    DESCRIPTION "Updated per MIBwg review. Change special case value for
                 pdnAdslPsdConfAtucMaxRxPwr from 9999 to 2048 to make it easier
                 for an NMS application to detect the special case. Collapse the
                 two Carrier Mask tables, one for upstream and one for downstream,
                 into a single table. The profile name can be used to distinguish
                 between an upstream and a downstream direction if needed."

    REVISION "200312030000Z"  -- December 3, 2003
    DESCRIPTION "Added objects to support MAXRXPWRus, CARMASKds, and CARMASKus per
                 new requirements."

    REVISION "200311191500Z"  -- November 19, 2003
    DESCRIPTION "Modified description text to clarify issues pertaining to
                 default profile names. General changes requested by
                 middleware and client implementors."

    REVISION "200311111500Z"  -- November 11, 2003
    DESCRIPTION "Changed the order of the indices for the
                 pdnAdslModeSpecificPsdTable to ease implementation in the
                 device."

    REVISION "200311061500Z"  -- November 6, 2003
    DESCRIPTION "Clean up, typo corrections, and clarifications."

    REVISION "200310311500Z"  -- October 31, 2003
    DESCRIPTION "Added pdnAdslLinePowerManagementStatus to provide a
                 mechanism to enable or disable power management
                 functionality."

    REVISION "200310231500Z"  -- October 23, 2003
    DESCRIPTION "Initial release."


::=  { pdn-interfaces 24 }


--
-- Define groups for Notifications, MIB Objects, Accessible for
-- Notifications (AFNs), and Conformance.
-- These may just be place holders.
--
pdnAdslLineExtNotifications OBJECT IDENTIFIER ::= { pdnAdslLineExtMIB 0 }
pdnAdslLineExtObjects       OBJECT IDENTIFIER ::= { pdnAdslLineExtMIB 1 }
pdnAdslLineExtAFNs          OBJECT IDENTIFIER ::= { pdnAdslLineExtMIB 2 }
pdnAdslLineExtConformance   OBJECT IDENTIFIER ::= { pdnAdslLineExtMIB 3 }


-- =============================================================================
-- ==                  Textual Conventions                                    ==
-- =============================================================================

PdnAdslTransmissionModeType  ::= TEXTUAL-CONVENTION
    STATUS      current
    DESCRIPTION "A set of ADSL line transmission modes, with one bit per mode."
    REFERENCE   "G.997.1, Section 7.3.1.1.1, ATU Transmission System Enabling (ATSE)."
    SYNTAX      BITS {
        -- Octet 1 --
        ansit1413(0),                   -- Bit 00 : Regional Std.  (ANSI T1.413)
        etsi(1),                        -- Bit 01 : Regional Std.  (ETSI DTS/TM06006)
        q9921PotsNonOverlapped(2),      -- Bit 02 : G.992.1  POTS non-overlapped spectrum
                                        --                   Annex A
        q9921PotsOverlapped(3),         -- Bit 03 : G.992.1  POTS overlapped spectrum
                                        --                   Annex A
        q9921IsdnNonOverlapped(4),      -- Bit 04 : G.992.1  ISDN non-overlapped spectrum
                                        --                   Annex B
        q9921isdnOverlapped(5),         -- Bit 05 : G.992.1  ISDN overlapped spectrum
                                        --                   Annex B
        q9921tcmIsdnNonOverlapped(6),   -- Bit 06 : G.992.1  TCM-ISDN non-overlapped spectrum
                                        --                   Annex C
        q9921tcmIsdnOverlapped(7),      -- Bit 07 : G.992.1  TCM-ISDN overlapped spectrum
                                        --                   Annex C

        -- Octet 2 --
        q9922potsNonOverlapeed(8),      -- Bit 08 : G.992.2  POTS non-overlapped spectrum
                                        --                   Annex A
        q9922potsOverlapped(9),         -- Bit 09 : G.992.2  POTS overlapped spectrum
                                        --                   Annex B
        q9922tcmIsdnNonOverlapped(10),  -- Bit 10 : G.992.2  TCM-ISDN non-overlapped spectrum
                                        --                   Annex C
        q9922tcmIsdnOverlapped(11),     -- Bit 11 : G.992.2  TCM-ISDN overlapped spectrum
                                        --                   Annex C
        q9921tcmIsdnSymmetric(12),      -- Bit 12 : G.992.1  TCM-ISDN symmetric
        reservedBit13(13),              -- Bit 13 : Reserved
        reservedBit14(14),              -- Bit 14 : Reserved
        reservedBit15(15),              -- Bit 15 : Reserved

        -- Octet 3 --
        reservedBit16(16),              -- Bit 16 : Reserved
        reservedBit17(17),              -- Bit 17 : Reserved
        q9923potsNonOverlapped(18),     -- Bit 18 : G.992.3  POTS non-overlapped spectrum
                                        --                   Annex A
        q9923potsOverlapped(19),        -- Bit 19 : G.992.3  POTS overlapped spectrum
                                        --                   Annex A
        q9923isdnNonOverlapped(20),     -- Bit 20 : G.992.3  ISDN non-overlapped spectrum
                                        --                   Annex B
        q9923isdnOverlapped(21),        -- Bit 21 : G.992.3  ISDN overlapped spectrum
                                        --                   Annex B
        reservedBit22(22),              -- Bit 22 : Reserved
        reservedBit23(23),              -- Bit 23 : Reserved

        -- Octet 4 --
        q9924potsNonOverlapped(24),     -- Bit 24 : G.992.4  POTS non-overlapped spectrum
                                        --                   Annex A
        q9924potsOverlapped(25),        -- Bit 25 : G.992.4  POTS overlapped spectrum
                                        --                   Annex A
        reservedBit26(26),              -- Bit 26 : Reserved
        reservedBit27(27),              -- Bit 27 : Reserved
        q9923DigitalNonOverlappedI(28), -- Bit 28 : G.992.3  All Digital Mode
                                        --                   non-overlapped spectrum
                                        --                   Annex I
        q9923DigitalOverlappedI(29),    -- Bit 29 : G.992.3  All Digital Mode
                                        --                   overlapped spectrum
                                        --                   Annex I
        q9923DigitalNonOverlappedJ(30), -- Bit 30 : G.992.3  All Digital Mode
                                        --                   non-overlapped spectrum
                                        --                   Annex J
        q9923DigitalOverlappedJ(31),    -- Bit 31 : G.992.3  All Digital Mode
                                        --                   overlapped spectrum
                                        --                   Annex J

        -- Octet 5 --
        q9924DigitalNonOverlappedI(32), -- Bit 32 : G.992.4  All Digital Mode
                                        --                   non-overlapped spectrum
                                        --                   Annex I
        q9924DigitalOverlappedI(33),    -- Bit 33 : G.992.4  All Digital Mode
                                        --                   overlapped spectrum
                                        --                   Annex I
        q9923ReachExtOverPotsMode1L(34),
                                        -- Bit 34 : G.992.3  Reach Extended operation
                                        --                   over POTS Mode 1
                                        --                   (non-overlapped,
                                        --                   wide upstream)
                                        --                   Annex L
        q9923ReachExtOverPotsMode2L(35),
                                        -- Bit 35 : G.992.3  Reach Extended operation
                                        --                   over POTS Mode 2
                                        --                   (non-overlapped,
                                        --                   narrow upstream)
                                        --                   Annex L
        q9923ReachExtOverPotsMode3L(36),
                                        -- Bit 36 : G.992.3  Reach Extended operation
                                        --                   over POTS Mode 3
                                        --                   (overlapped,
                                        --                   wide upstream)
                                        --                   Annex L
        q9923ReachExtOverPotsMode4L(37),
                                        -- Bit 37 : G.992.3  Reach Extended operation
                                        --                   over POTS Mode 4
                                        --                   (overlapped,
                                        --                   narrow upstream)
                                        --                   Annex L
        q9923ExtUpOverPotsNonOverlappedM(38),
                                        -- Bit 38 : G.992.3  Extended upstream operation
                                        --                   over POTS non-overlapped
                                        --                   spectrum
                                        --                   Annex M
        q9923ExtUpOverPotsOverlappedM(39),
                                        -- Bit 39 : G.992.3  Extended upstream operation
                                        --                   over POTS overlapped spectrum
                                        --                   Annex M

        -- Octet 6 --
        q9925potsNonOverlapped(40),     -- Bit 40 : G.992.5  POTS non-overlapped spectrum
                                        --                   Annex A
        q9925potsOverlapped(41),        -- Bit 41 : G.992.5  POTS overlapped spectrum
                                        --                   Annex A
        q9925isdnNonOverlapped(42),     -- Bit 42 : G.992.5  ISDN non-overlapped spectrum
                                        --                   Annex B
        q9925isdnOverlapped(43),        -- Bit 43 : G.992.5  ISDN overlapped spectrum
                                        --                   Annex B
        reserved44(44),                 -- Bit 44 : Reserved
        reserved45(45),                 -- Bit 45 : Reserved
        q9925DigitalNonOverlappedI(46), -- Bit 46 : G.992.5  All Digital Mode
                                        --                   non-overlapped spectrum
                                        --                   Annex I
        q9925DigitalOverlappedI(47),    -- Bit 47 : G.992.5  All Digital Mode
                                        --                   overlapped spectrum
                                        --                   Annex I

        -- Octet 7 --
        q9925DigitalNonOverlappedJ(48), -- Bit 48 : G.992.5  All Digital Mode
                                        --                   non-overlapped spectrum
                                        --                   Annex J
        q9925OverlappedJ(49),           -- Bit 49 : G.992.5  All Digital Mode
                                        --                   overlapped spectrum
                                        --                   Annex J
        q9925ExtUpOverPotsNonOverlappedM(50),
                                        -- Bit 50 : G.992.5  Extended upstream over
                                        --                   POTS non-overlapped spectrum
                                        --                   Annex M
        q9925ExtUpOverPotsOverlappedM(51),
                                        -- Bit 51 : G.992.5  Extended upstream over
                                        --                   POTS overlapped spectrum
                                        --                   Annex M
        reservedBit52(52),              -- Bit 52 : Reserved
        reservedBit53(53),              -- Bit 53 : Reserved
        reservedBit54(54),              -- Bit 54 : Reserved
        reservedBit55(55)               -- Bit 55 : Reserved
    }


-- =============================================================================
-- ==                  MIB Objects                                            ==
-- =============================================================================


-- =============
-- == ADSL Line
-- =============
pdnAdslLineExtTable OBJECT-TYPE
    SYNTAX      SEQUENCE OF PdnAdslLineExtEntry
    MAX-ACCESS  not-accessible
    STATUS      current
    DESCRIPTION "This table extends the adslLineTable in support of an
                 ADSL Line object.

                 The objects pdnAdslLineTransAtucCap, pdnAdslLineTrans-
                 AtucConfig, and pdnAdslLineTransAtucActual exist along
                 with their PdnAdslTransmissionModeType TC because the
                 AdslTransmissionModeType defined in the ADSL-LINE-EXT-MIB
                 does not include the ADSL2/ADSL2plus bits defined in
                 ITU G.997.1 (05/2003) ATU Transmission System Enabling (ATSE)
                 section.

                 When using the objects defined in this MIB with a syntax of
                 type PdnAdslTransmissionModeType, the interworking relationship
                 between these objects and the objects defined in the ADSL-LINE-
                 EXT-MIB defined with a syntax of type AdslTransmissionModeType
                 must be considered and explained in an implementation-specific
                 document such as an Operational Specification. Note that the
                 PdnAdslTransmissionModeType is a super set of the AdslTransmis-
                 sionModeType. One possible implementation could be as follows:
                     1.  Both objects of syntax AdslTransmissionModeType defined
                         in the ADSL-LINE-EXT-MIB and objects of syntax PdnAdsl-
                         TransmissionModeType defined in this MIB are supported.
                         By supporting both, a manager with the ADSL-LINE-EXT-MIB
                         loaded could manage the device with the restriction of
                         not being able to utilize ADSL2/ADSL2plus modes.
                     2.  When the ADSL2/ADSL2plus capabilities are desired, a manager
                         would have to use the objects defined in this MIB to
                         configure the transmission modes, read capability, or
                         read the actual transmission mode of the ATU-C.
                     3.  The transmission mode that the ATU-C is currently
                         configured for is based on the last object, adslLineTrans-
                         AtucConfig or pdnAdslLineTransAtucConfig, that was written."
    REFERENCE "WT-090, Section 5.1.1, ADSL Line."
    ::= { pdnAdslLineExtObjects 1 }

pdnAdslLineExtEntry     OBJECT-TYPE
    SYNTAX      PdnAdslLineExtEntry
    MAX-ACCESS  not-accessible
    STATUS      current
    DESCRIPTION "An extended entry in the adslLineTable."
    INDEX     { ifIndex }
    ::= { pdnAdslLineExtTable 1 }

PdnAdslLineExtEntry ::=
    SEQUENCE {
        pdnAdslLineTransAtucCap          PdnAdslTransmissionModeType,
        pdnAdslLineTransAtucConfig       PdnAdslTransmissionModeType,
        pdnAdslLineTransAtucActual       PdnAdslTransmissionModeType,
        pdnAdslLinePowerManagementConfig INTEGER,
        pdnAdslLineSpectrumProfile       SnmpAdminString,
        pdnAdslLinePmMode                BITS,
        pdnAdslLineL0Time                Unsigned32,
        pdnAdslLineL2Time                Unsigned32,
        pdnAdslLineL2Atpr                Unsigned32,
        pdnAdslLineLdsf                  INTEGER,
        pdnAdslLineL2Atprt               Unsigned32
    }

pdnAdslLineTransAtucCap OBJECT-TYPE
    SYNTAX      PdnAdslTransmissionModeType
    MAX-ACCESS  read-only
    STATUS      current
    DESCRIPTION "The transmission modes, represented by a bitmask that the
                 ATU-C is capable of supporting. The modes available are
                 limited by the design of the equipment."
    REFERENCE   "G.997.1, Section 7.3.1.1.1, ATU Transmission System
                 Enabling (ATSE).
                 RFC 3440, adslLineTransAtucCap."
    ::= { pdnAdslLineExtEntry 1 }

pdnAdslLineTransAtucConfig OBJECT-TYPE
    SYNTAX      PdnAdslTransmissionModeType
    MAX-ACCESS  read-write
    STATUS      current
    DESCRIPTION "The transmission modes, represented by a bitmask, currently
                 enabled by the ATU-C.  The manager can only set those modes
                 that are supported by the ATU-C. An ATU-C's supported modes
                 are provided by pdnAdslLineTransAtucCap."
    REFERENCE   "G.997.1, Section 7.3.1.1.1, ATU Transmission System
                 Enabling (ATSE).
                 RFC 3440 adslLineTransAtucConfig."
    ::= { pdnAdslLineExtEntry 2 }

pdnAdslLineTransAtucActual OBJECT-TYPE
    SYNTAX      PdnAdslTransmissionModeType
    MAX-ACCESS  read-only
    STATUS      current
    DESCRIPTION "The actual transmission mode of the ATU-C. During ADSL line
                 initialization, the ADSL Transceiver Unit Remote terminal
                 end (ATU-R) will determine the mode used for the link. This
                 value will be limited a single transmission mode that is a
                 subset of those modes enabled by the ATU-C and denoted by
                 pdnAdslLineTransAtucConfig. After an initialization has
                 occurred, its mode is saved as the `Current' mode and is
                 persistent should the link go down. This object returns 0
                 (i.e. BITS with no mode bit set) if the mode is not known."
    REFERENCE   "G.997.1, Section 7.3.1.1.1, ATU Transmission
                 System Enabling (ATSE).
                 RFC 3440 adslLineTransAtucActual."
    ::= { pdnAdslLineExtEntry 3 }

pdnAdslLinePowerManagementConfig OBJECT-TYPE
    SYNTAX      INTEGER {
                    enabled(1),
                    disabled(2)
                }
    MAX-ACCESS  read-write
    STATUS      current
    DESCRIPTION "This object enables or disables power management functionality."
    DEFVAL      { disabled }
    ::= { pdnAdslLineExtEntry 4 }

pdnAdslLineSpectrumProfile OBJECT-TYPE
    SYNTAX      SnmpAdminString (SIZE(0 | 1..32))
    MAX-ACCESS  read-write
    STATUS      current
    DESCRIPTION "The value of this object identifies the row in the ADSL
                 Line Spectrum Profile Table, pdnAdslLineSpectrumProfileTable,
                 which applies for this ADSL line. If this object is not
                 a zero-length string, it should default to the default profile
                 whose name is `DEFVAL'."
    REFERENCE   "WT-090, Section 5.1.1, ADSL Line."
    DEFVAL      { "DEFVAL" }
    ::= { pdnAdslLineExtEntry 5 }


pdnAdslLinePmMode OBJECT-TYPE
    SYNTAX      BITS {
                    idleStateL3(0),
                    lowPwrStateL1L2(1)
                }
    MAX-ACCESS  read-write
    STATUS      current
    DESCRIPTION "The line states the ATU-C or ATU-R may autonomously transition
                 to on this line. It is coded in a bit-map representation
                 (0 if not allowed, 1 if allowed) as follows:
                     idleStateL3(0)     - Bit 0  L3 state (Idle state)
                     lowPwrStateL1L2(1) - Bit 1  L1/L2 state (Low power state)"
    REFERENCE   "G.997.1, Section 7.3.1.1.4, Power Management State
                 Enabling (PMMode)."
    ::= { pdnAdslLineExtEntry 6 }

pdnAdslLineL0Time OBJECT-TYPE
    SYNTAX      Unsigned32(0..255)
    UNITS       "seconds"
    MAX-ACCESS  read-write
    STATUS      current
    DESCRIPTION "The minimum time, in seconds, between and Exit from the L2 state
                 and the next Entry into the L2 state."
    REFERENCE   "G.997.1, Section 7.3.1.1.5, Minimum L0 Time interval,between L2 exit
                 and next L2 entry (L0-TIME)."
    ::= { pdnAdslLineExtEntry 7 }

pdnAdslLineL2Time OBJECT-TYPE
    SYNTAX      Unsigned32(0..255)
    UNITS       "seconds"
    MAX-ACCESS  read-write
    STATUS      current
    DESCRIPTION "The minimum time, in seconds, between an Entry into the L2 state
                 and the first Power Trim in the L2 state and between two con-
                 secutive Power Trims in the L2 State."
    REFERENCE   "G.997.1, Section 7.3.1.1.6, Minimum L2 Time interval between L2
                 entry and first L2 trim (L2-TIME)."
    ::= { pdnAdslLineExtEntry 8 }

pdnAdslLineL2Atpr OBJECT-TYPE
    SYNTAX      Unsigned32(0..31)
    UNITS       "dB"
    MAX-ACCESS  read-write
    STATUS      current
    DESCRIPTION "The maximum aggregate transmit power reduction, in dB, that can
                 be performed through a single Power Trim in the L2 state.

                 At the time this MIB was produced, the upper limit for this object
                 was not updated in the G.997.1 with respect to ADSL2plus. As such,
                 the upper limit of this object should be defined in an implementation-
                 specific document such as an Operational Specification."
    REFERENCE   "G.997.1, Section 7.3.1.1.7, Maximum Aggregate Transmit Power
                 reduction per L2 trim (L2-ATPR)."
    ::= { pdnAdslLineExtEntry 9 }

pdnAdslLineLdsf OBJECT-TYPE
    SYNTAX      INTEGER {
                    ldsfMode0(1),
                    ldsfMode1(2)
                }
    MAX-ACCESS  read-write
    STATUS      current
    DESCRIPTION "Defines whether the line should be forced into the loop
                 diagnostics mode by the near-end ATU on this line.
                     ldsfMode0(1) - 0: Inhibits the near-end ATU from performing loop
                                       diagnostics mode procedures on the line. Loop
                                       diagnostic mode procedures may still be
                                       initiated by the far-end ATU.
                     ldsModef1(2) - 1: Forces the near-end ATU to perform the loop
                                       diagnostics procedures.

                 The line needs to be forced to the L3 state (idle state) before
                 it can be forced to the loop diagnostics mode. Only while the
                 line power management state is the L3 state, the line can be forced
                 into the loop diagnostics mode procedures.

                 The following are ways to force the line to the L3 state:
                 (1) Set the ifAdminStatus to down.

                 When the loop diagnostics mode procedures are completed successfully,
                 this object shall reset to ldsf0 and the line shall return to and
                 remain in the L3 idle state. The loop diagnostics data shall be
                 available at least until the line is forced to the L0 state. If the
                 loop diagnostics procedures can't be completed successfully, then
                 an Initialization Failure occurs. As long as loop diagnostics
                 procedures are not completed successfully, attempts shall be made
                 to do so, until the loop diagnostics mode is no longer forced on
                 the line through this configuration parameter."
    REFERENCE   "G.997.1, Section 7.3.1.1.8, Loop Diagnostics Mode forced (LDSF)."
    ::= { pdnAdslLineExtEntry 10 }

pdnAdslLineL2Atprt OBJECT-TYPE
    SYNTAX      Unsigned32(0..31)
    UNITS       "dB"
    MAX-ACCESS  read-write
    STATUS      current
    DESCRIPTION "This parameter represents the total maximum aggregate transmit
                 power reduction (in dB) that can be performed in an L2 state.
                 This is the sum of all reductions of L2 Request (i.e., at
                 transition of L0 to L2 state) and Power Trims."
    REFERENCE   "G.997.1 Am 1 , Section 7.3.1.1.9, Total maximum aggregate
                 transmit power reduction in L2 (L2-ATPRT)."
    ::= { pdnAdslLineExtEntry 11 }


-- ==============================
-- == ADSL Line Spectrum Profile
-- ==============================
pdnAdslLineSpectrumProfileTable OBJECT-TYPE
    SYNTAX      SEQUENCE OF PdnAdslLineSpectrumProfileEntry
    MAX-ACCESS  not-accessible
    STATUS      current
    DESCRIPTION "This table contains specific configuration of transmission
                 spectrum and power spectral density related parameters that
                 can be mapped to one of the ADSL lines."
    REFERENCE   "WT-090, Section 5.1.6, ADSL Line Spectrum Profile."
    ::= { pdnAdslLineExtObjects 2 }

pdnAdslLineSpectrumProfileEntry     OBJECT-TYPE
    SYNTAX      PdnAdslLineSpectrumProfileEntry
    MAX-ACCESS  not-accessible
    STATUS      current
    DESCRIPTION "Each entry contains a specific profile for transmission
                 spectrum and power spectral density related parameters.
                 A default profile with an index of `DEFVAL', will always
                 exist and its parameters will be set to vendor or product
                 specific values, unless otherwise specified in this document."
    INDEX     { IMPLIED pdnAdslLineSpectrumProfileName }
    ::= { pdnAdslLineSpectrumProfileTable 1 }

PdnAdslLineSpectrumProfileEntry ::=
    SEQUENCE {
        pdnAdslLineSpectrumProfileName              SnmpAdminString,
        pdnAdslLineSpectrumProfileRowStatus         RowStatus,
        pdnAdslLineSpectrumModeSpecificPsdProfile   SnmpAdminString,
        pdnAdslLineSpectrumAtucCarMaskProfile       SnmpAdminString,
        pdnAdslLineSpectrumAturCarMaskProfile       SnmpAdminString
    }

pdnAdslLineSpectrumProfileName OBJECT-TYPE
    SYNTAX      SnmpAdminString (SIZE(1..32))
    MAX-ACCESS  not-accessible
    STATUS      current
    DESCRIPTION "This object identifies a row in the pdnAdslLineSpectrumProfile-
                 Table. The system will always provide a default profile whose
                 name is `DEFVAL'."
    REFERENCE   "G.997.1, Section 7.3.1.1.1 ATU Transmission System Enabling
                 (ATSE)."
    ::= { pdnAdslLineSpectrumProfileEntry 1 }

pdnAdslLineSpectrumProfileRowStatus OBJECT-TYPE
    SYNTAX      RowStatus
    MAX-ACCESS  read-create
    STATUS      current
    DESCRIPTION "This object is used to create a new row or modify or delete an
                 existing row in this table. A profile is activated by setting
                 this object to `valid'.

                 Before a profile can be deleted or taken out of service, by
                 setting this object to `destroy' or `outOfService', the
                 profile must be first unreferenced from all entries that
                 referred to it (entries in the pdnAdslLineExtTable)."
    ::= { pdnAdslLineSpectrumProfileEntry 2 }

pdnAdslLineSpectrumModeSpecificPsdProfile OBJECT-TYPE
    SYNTAX      SnmpAdminString (SIZE(1..32))
    MAX-ACCESS  read-create
    STATUS      current
    DESCRIPTION "The value of this object identifies the row(s) in the ADSL
                 Mode-Specific PSD Configuration Table, pdnAdslModeSpecific-
                 PsdConfTable, which applies for this Line Spectrum Profile.

                 A particular ADSL line may need to support multiple mode-
                 specific power spectral density related settings. For example,
                 a ADSL line may need to support one set of settings for ADSL2
                 and another set of settings for ADSL2plus. See the pdnAdslMode-
                 SpecificPsdConfTable for additional detail. The system will always
                 provide a default profile whose name is `DEFVAL'"
    REFERENCE   "WT-090, Section 5.1.6 ADSL LIne Spectrum Profile and Section
                 5.1.7 ADSL Mode-Specific PSD Configuration."
    DEFVAL      { "DEFVAL" }
    ::= { pdnAdslLineSpectrumProfileEntry 3 }

pdnAdslLineSpectrumAtucCarMaskProfile OBJECT-TYPE
    SYNTAX      SnmpAdminString(SIZE(0..32))
    MAX-ACCESS  read-create
    STATUS      current
    DESCRIPTION "This object identifies one or more rows in the pdnAdslCarMaskTable.
                 The pdnAdslCarMaskTable is a table containing a list of subcarriers to
                 be masked in the downstream or upstream direction; the profile in the
                 pdAdslCarMaskTable that this object identifies will apply the masks
                 in the downstream direction.

                 This object defaults to an empty string meaning that no subcarriers are
                 masked by an administrator."
    REFERENCE   "WT-090, Section 5.1.6, ADSL Line Spectrum Profile.
                 G.997.1, Section 7.3.1.2.6, Downstream subcarrier masking (CARMASKds)."
    DEFVAL      { "" }
    ::= { pdnAdslLineSpectrumProfileEntry 4 }

pdnAdslLineSpectrumAturCarMaskProfile OBJECT-TYPE
    SYNTAX      SnmpAdminString(SIZE(0..32))
    MAX-ACCESS  read-create
    STATUS      current
    DESCRIPTION "This object identifies one or more rows in the pdnAdslCarMaskTable.
                 The pdnAdslCarMaskTable is a table containing a list of subcarriers to
                 be masked in the downstream or upstream direction; the profile in the
                 pdAdslCarMaskTable that this object identifies will apply the masks
                 in the upstream direction.

                 This object defaults to an empty string meaning that no subcarriers are
                 masked by an administrator."
    REFERENCE   "WT-090, Section 5.1.6, ADSL Line Spectrum Profile.
                 G.997.1, Section 7.3.1.2.7, Upstream subcarrier masking (CARMASKus)."
    DEFVAL      { "" }
    ::= { pdnAdslLineSpectrumProfileEntry 5 }


-- ========================================
-- == ADSL Mode-Specific PSD Configuration
-- ========================================
pdnAdslModeSpecificPsdConfTable OBJECT-TYPE
    SYNTAX      SEQUENCE OF PdnAdslModeSpecificPsdConfEntry
    MAX-ACCESS  not-accessible
    STATUS      current
    DESCRIPTION "This table binds an entry indexed by a specific ADSL type or
                 flavor (e.g. ADSL2 or ADSL2+) and indexed by a profile name
                 to a specific DSL PSD Configuration Profile."
    REFERENCE   "WT-090, Section 5.1, Configuration Management, and Section 5.1.6,
                 ADSL Line Spectrum Profile."
    ::= { pdnAdslLineExtObjects 3 }

pdnAdslModeSpecificPsdConfEntry     OBJECT-TYPE
    SYNTAX      PdnAdslModeSpecificPsdConfEntry
    MAX-ACCESS  not-accessible
    STATUS      current
    DESCRIPTION "An entry in the table. For each particular ADSL mode or
                 flavor supported (pdnAdslMOdeSpecificPsdConfAdslMode), there
                 will be an entry that points to an entry in the ADSL PSD
                 Configuration Table (pdnAdslPsdConfTable). For example,
                 if ADSL2 and ADSL2plus ADSL modes are supported, this
                 table will have the following two default entries:
                     1. An entry indexed by pdnAdslModeSpecificPsd-
                        ConfProfileName = 'DEFVAL' and pdnAdslModeSpecific-
                        PsdConfAdslMode = adsl2(1) and has pdnAdslModeSpecific-
                        PsdConfAdslPsdConfProfile = DEFVAL_ADSL2
                     2. An entry indexed by pdnAdslModeSpecificPsd-
                        ConfProfileName = 'DEFVAL' and pdnAdslModeSpecific-
                        PsdConfAdslMode = adsl2plus(3) and has pdnAdslModeSpecific-
                        PsdConfAdslPsdConfProfile = DEFVAL_ADSL2PLUS
                DEFVAL entries may be modified but not deleted."
    INDEX     { pdnAdslModeSpecificPsdConfProfileName,
                pdnAdslModeSpecificPsdConfAdslMode }
    ::= { pdnAdslModeSpecificPsdConfTable 1 }

PdnAdslModeSpecificPsdConfEntry ::=
    SEQUENCE {
        pdnAdslModeSpecificPsdConfProfileName         SnmpAdminString,
        pdnAdslModeSpecificPsdConfAdslMode            INTEGER,
        pdnAdslModeSpecificPsdConfRowStatus           RowStatus,
        pdnAdslModeSpecificPsdConfAdslPsdConfProfile  SnmpAdminString
    }

pdnAdslModeSpecificPsdConfProfileName OBJECT-TYPE
    SYNTAX      SnmpAdminString (SIZE(1..32))
    MAX-ACCESS  not-accessible
    STATUS      current
    DESCRIPTION "This object identifies a row in the pdnAdslModeSpecificPsdConfTable.
                 The system will always provide a default profile whose
                 name is 'DEFVAL'."
    REFERENCE   "WT-090, Section 5.1.7, ADSL Mode-Specific PSD Configuration."
    ::= { pdnAdslModeSpecificPsdConfEntry 1 }

pdnAdslModeSpecificPsdConfAdslMode OBJECT-TYPE
    SYNTAX      INTEGER {
                    adsl2(1),           -- G.992.3  ADSL transceivers - 2
                                        --          (ADSL2)
                    adsl2NoSplitter(2), -- G.992.4  Splitterless ADSL transceivers - 2
                                        --          (Splitterless ADSL2)
                    adsl2plus(3)        -- G.992.5  Extended Bandwidth ADSL2
                                        --          (ADSL2plus)
    }
    MAX-ACCESS  not-accessible
    STATUS      current
    DESCRIPTION "This object identifies a row in the pdnAdslModeSpecificPsdConfTable
                 containing parameters specific to a particular ADSL mode or
                 flavor identified by this object."
    REFERENCE   "WT-090, Section 5.1.7, ADSL Mode-Specific PSD Configuration."
    ::= { pdnAdslModeSpecificPsdConfEntry 2 }



pdnAdslModeSpecificPsdConfRowStatus OBJECT-TYPE
    SYNTAX      RowStatus
    MAX-ACCESS  read-create
    STATUS      current
    DESCRIPTION "This object is used to create a new row or modify or delete an
                 existing row in this table. A profile is activated by setting
                 this object to `valid'.

                 Before a profile can be deleted or taken out of service, by
                 setting this object to `destroy' or `outOfService', the
                 profile must be first unreferenced from all entries that
                 referred to it (entries in the pdnAdslLineSpectrumProfileTable)."
    ::= { pdnAdslModeSpecificPsdConfEntry 3 }

pdnAdslModeSpecificPsdConfAdslPsdConfProfile OBJECT-TYPE
    SYNTAX      SnmpAdminString (SIZE(1..32))
    MAX-ACCESS  read-create
    STATUS      current
    DESCRIPTION "This object identifies a row in the ADSL PSD Configuration
                 Table, pdnAdslPsdConfTable."
    REFERENCE   "WT-090, Section 5.1, Configuration Management, and Section 5.1.7,
                 ADSL Mode-Specific PSD Configuration.
                 G.997.1, Section 7.3.1.2, Power/PSD configuration parameters."
    ::= { pdnAdslModeSpecificPsdConfEntry 4 }


-- ==========================
-- == ADSL PSD Configuration
-- ==========================
pdnAdslPsdConfTable OBJECT-TYPE
    SYNTAX      SEQUENCE OF PdnAdslPsdConfEntry
    MAX-ACCESS  not-accessible
    STATUS      current
    DESCRIPTION "This table contains power spectral density settings."
    REFERENCE   "WT-090, Section 5.1.7, ADSL Mode-Specific PSD Configuration.
                 G.997.1, Section 7.3.1.2, Power/PSD configuration parameters."
    ::= { pdnAdslLineExtObjects 4 }

pdnAdslPsdConfEntry     OBJECT-TYPE
    SYNTAX      PdnAdslPsdConfEntry
    MAX-ACCESS  not-accessible
    STATUS      current
    DESCRIPTION "Each entry contains specific power spectral density settings for
                 a particular profile. A default profile for each particular
                 ADSL mode or flavor supporting PSD configuration will exist
                 (See the pdnAdslModeSpecificPsdConfAdslMode object the the
                 range of possible ADSL modes or flavors that are possible).
                 For example, if only ADSL2 and ADSL2plus modes are supported,
                 the indices would be 'DEFVAL_ADSL2' and 'DEFVAL_ADSL2PLUS'.
                 The DEFVAL rows may be modified but not deleted. The DEFVAL rows
                 will always exist and its parameters will be set to vendor or
                 product specific values, unless otherwise specified in this document."
    INDEX     { IMPLIED pdnAdslPsdConfProfileName }
    ::= { pdnAdslPsdConfTable 1 }

PdnAdslPsdConfEntry ::=
    SEQUENCE {
        pdnAdslPsdConfProfileName      SnmpAdminString,
        pdnAdslPsdConfRowStatus        RowStatus,
        pdnAdslPsdConfAtucMaxNomPsd    Integer32,
        pdnAdslPsdConfAturMaxNomPsd    Integer32,
        pdnAdslPsdConfAtucMaxNomAtp    Unsigned32,
        pdnAdslPsdConfAturMaxNomAtp    Unsigned32,
        pdnAdslPsdConfAtucMaxRxPwr     Integer32
    }

pdnAdslPsdConfProfileName OBJECT-TYPE
    SYNTAX      SnmpAdminString (SIZE(1..32))
    MAX-ACCESS  not-accessible
    STATUS      current
    DESCRIPTION "This object identifies a row in the pdnAdslPsdConfTable."
    REFERENCE   "WT-090, Section 5.1.7, ADSL Mode-Specific PSD Configuration."
    ::= { pdnAdslPsdConfEntry 1 }

pdnAdslPsdConfRowStatus OBJECT-TYPE
    SYNTAX      RowStatus
    MAX-ACCESS  read-create
    STATUS      current
    DESCRIPTION "This object is used to create a new row or modify or delete an
                 existing row in this table. A profile is activated by setting
                 this object to `valid'.

                 Before a profile can be deleted or taken out of service, by
                 setting this object to `destroy' or `outOfService', the
                 profile must be first unreferenced from all entries that
                 referred to it such as pdnAdslModeSpecificPsdConfAdslPsdConfProfile."
    ::= { pdnAdslPsdConfEntry 2 }

pdnAdslPsdConfAtucMaxNomPsd OBJECT-TYPE
    SYNTAX      Integer32(-800..-400)
    UNITS       "tenth dBm/Hz"
    MAX-ACCESS  read-create
    STATUS      current
    DESCRIPTION "Represents the Maximum nominal transmit PSD for the ATU-C.
                 The values range from -80 to -40 dBm/Hz in 0.1 dB steps."
    REFERENCE   "G.997.1, Section 7.3.1.2.1, Downstream Maximum Nominal Power
                 Spectral Density (MAXNOMPSDds), and Section 7.3.1.2.2, Upstream
                 Maximum Nominal Power Spectral Density (MAXNOMPSDus).
                 OA 305, Section 7.2.2, Downstream transmit spectral mask."
    ::= { pdnAdslPsdConfEntry 3 }

pdnAdslPsdConfAturMaxNomPsd OBJECT-TYPE
    SYNTAX      Integer32(-650..-380)
    UNITS       "tenth dBm/Hz"
    MAX-ACCESS  read-create
    STATUS      current
    DESCRIPTION "Represents the Maximum nominal transmit PSD for the ATU-R.
                 The values range from -65 to -38 dBm/Hz in 0.1 dB steps."
    REFERENCE   "G.997.1, Section 7.3.1.2.1, Downstream Maximum Nominal Power
                 Spectral Density (MAXNOMPSDds), and Section 7.3.1.2.2, Upstream
                 Maximum Nominal Power Spectral Density (MAXNOMPSDus)."
    ::= { pdnAdslPsdConfEntry 4 }

pdnAdslPsdConfAtucMaxNomAtp OBJECT-TYPE
    SYNTAX      Unsigned32(0..255)
    UNITS       "tenth dBm"
    MAX-ACCESS  read-create
    STATUS      current
    DESCRIPTION "Represents the Maximum nominal aggregate transmit power for
                 the ATU-C. The values range from 0 to 25.5 dBm in 0.1 dB steps."
    REFERENCE   "G.997.1, Section 7.3.1.2.3, Downstream Maximum Nominal Aggregate
                 Transmit Power (MAXNOMATPds), and Section 7.3.1.2.4, Upstream
                 Maximum Nominal Aggregate Transmit Power (MAXNOMATPus)."
    ::= { pdnAdslPsdConfEntry 5 }

pdnAdslPsdConfAturMaxNomAtp OBJECT-TYPE
    SYNTAX      Unsigned32(0..255)
    UNITS       "tenth dBm"
    MAX-ACCESS  read-create
    STATUS      current
    DESCRIPTION "Represents the Maximum nominal aggregate transmit power for
                 the ATU-R. The values range from 0 to 25.5 dBm in 0.1 dB steps."
    REFERENCE   "G.997.1, Section 7.3.1.2.3, Downstream Maximum Nominal Aggregate
                 Transmit Power (MAXNOMATPds), and Section 7.3.1.2.4, Upstream
                 Maximum Nominal Aggregate Transmit Power (MAXNOMATPus)."
    ::= { pdnAdslPsdConfEntry 6 }

pdnAdslPsdConfAtucMaxRxPwr OBJECT-TYPE
    SYNTAX      Integer32(-255..255 | 2048)
    UNITS       "tenth dBm"
    MAX-ACCESS  read-create
    STATUS      current
    DESCRIPTION "Represents the maximum upstream aggregate receive power over a
                 set of subcarriers (in dBm). The ATU-C shall request an upstream
                 power cutback such that the upstream aggregate receive power
                 over that set of subcarriers is at or below the configured
                 maximum value. It ranges from -25.5 to 25.5 dBm, with 0.1 dB
                 steps. The value 2048 is a special value and indicates that
                 no Upstream Maximum Aggregate Receive Power limit is to be
                 applied (i.e., the maximum value is infinite)."
    REFERENCE   "G.997.1, Section 7.3.1.2.5, Upstream Maximum Aggregate Receive
                 Power (MAXRXPWRus)."
    ::= { pdnAdslPsdConfEntry 7 }



-- =============================================================================
-- ==                      ADSL Values for NSC  (Number of Subcarriers)       ==
-- =============================================================================
-- == The following ITU recommendations should be reference for specific      ==
-- == values for NSCds and NSCus:                                             ==
-- ==     G.997.1, Physical layer management for DSL transceivers             ==
-- ==     G.992.1, ADSL, G.dmt                                                ==
-- ==     G.992.2, Splitterless ADSL, G.lite                                  ==
-- ==     G.992.3, ADSL2, G.dmt.bis                                           ==
-- ==     G.992.4, Splitterless ADSL2                                         ==
-- ==     G.992.5, Extended Bandwidth ADSL2, ADSL2plus                        ==
-- =============================================================================



-- ===========================
-- == ADSL Carrier Mask Table
-- ===========================
pdnAdslCarMaskTable OBJECT-TYPE
    SYNTAX      SEQUENCE OF PdnAdslCarMaskEntry
    MAX-ACCESS  not-accessible
    STATUS      current
    DESCRIPTION "This table contains a list of subcarriers that are to be
                 masked (i.e. not transmitted). Subcarriers that are not
                 entries in this table are not masked."
    REFERENCE   "WT-090, Section 5.1.6, ADSL Line Spectrum Profile.
                 G.997.1, Section 7.3.1.2.6, Downstream subcarrier masking
                 (CARMASKds).
                 G.997.1, Section 7.3.1.2.7, Upstream subcarrier masking
                 (CARMASKus)."
    ::= { pdnAdslLineExtObjects 5 }

pdnAdslCarMaskEntry     OBJECT-TYPE
    SYNTAX      PdnAdslCarMaskEntry
    MAX-ACCESS  not-accessible
    STATUS      current
    DESCRIPTION "Each entry represents a specific subcarrier that is masked
                 for a particular profile."
    INDEX       { pdnAdslCarMaskProfileName,
                  pdnAdslCarMaskSubCarrierIndex }
    ::= { pdnAdslCarMaskTable 1 }

PdnAdslCarMaskEntry ::=
    SEQUENCE {
        pdnAdslCarMaskProfileName             SnmpAdminString,
        pdnAdslCarMaskSubCarrierIndex         Unsigned32,
        pdnAdslCarMaskRowStatus               RowStatus,
        pdnAdslCarMaskSubCarrierStatus        INTEGER
    }

pdnAdslCarMaskProfileName OBJECT-TYPE
    SYNTAX      SnmpAdminString (SIZE(1..32))
    MAX-ACCESS  not-accessible
    STATUS      current
    DESCRIPTION "This object identifies a row in the pdnAdslCarMaskTable
                 based on a profile name."
    ::= { pdnAdslCarMaskEntry 1 }

pdnAdslCarMaskSubCarrierIndex OBJECT-TYPE
    SYNTAX      Unsigned32
    MAX-ACCESS  not-accessible
    STATUS      current
    DESCRIPTION "This object identifies a row in the pdnAdslCarMaskTable
                 based on subcarrier that is being masked. The subcarrier
                 index ranges from 0 to (NSCds-1 or NSCus-1 (NSC is Number of
                 Subcarriers) as specified in G.997.1 where NSCds is the higher
                 subcarrier that can be transmitted in the downstream direction and
                 NSCus is the higher subcarrier that can be transmitted in the
                 upstream direction. Please refer to the corresponding ITU
                 recommendation for specific values of NSCds and NSCus. The
                 `ADSL Values for NSC' comment above lists those recommendations."
    ::= { pdnAdslCarMaskEntry 2 }

pdnAdslCarMaskRowStatus OBJECT-TYPE
    SYNTAX      RowStatus
    MAX-ACCESS  read-create
    STATUS      current
    DESCRIPTION "This object is used to create a new row or delete an existing
                 row in this table. A row is activated by setting this object
                 to active(1)."
    ::= { pdnAdslCarMaskEntry 3 }

pdnAdslCarMaskSubCarrierStatus OBJECT-TYPE
    SYNTAX      INTEGER {
                    masked(1)
                }
    MAX-ACCESS  read-only
    STATUS      current
    DESCRIPTION "This object provides a clear indication that the subcarrier
                 is masked."
    ::= { pdnAdslCarMaskEntry 4 }


-- ================================
-- == ADSL Line Status Table
-- ================================
pdnAdslLineStatusTable OBJECT-TYPE
    SYNTAX      SEQUENCE OF PdnAdslLineStatusEntry
    MAX-ACCESS  not-accessible
    STATUS      current
    DESCRIPTION "This table contains current line status measurements."
    REFERENCE   "WT-090-4, Section 5.2.1, ADSL Line Status.
                 G.997.1, Section 7.5.1, Line test, diagnostics and status
                 parameters."
    ::= { pdnAdslLineExtObjects 6 }

pdnAdslLineStatusEntry     OBJECT-TYPE
    SYNTAX      PdnAdslLineStatusEntry
    MAX-ACCESS  not-accessible
    STATUS      current
    DESCRIPTION "Each entry represents an interface.
                 i.e. a row in the ifTable."
    INDEX       { ifIndex }
    ::= { pdnAdslLineStatusTable 1 }

PdnAdslLineStatusEntry ::=
    SEQUENCE {
        pdnAdslLineStatusAtucLineAtn                Unsigned32,
        pdnAdslLineStatusAturLineAtn                Unsigned32,
        pdnAdslLineStatusAtucSignalAtn              Unsigned32,
        pdnAdslLineStatusAturSignalAtn              Unsigned32,
        pdnAdslLineStatusAtucSnrMgn                 Integer32,
        pdnAdslLineStatusAturSnrMgn                 Integer32,
        pdnAdslLineStatusAtucMaxAttainableLineRate  Gauge32,
        pdnAdslLineStatusAturMaxAttainableLineRate  Gauge32,
        pdnAdslLineStatusAtucActAtp                 Integer32,
        pdnAdslLineStatusAturActAtp                 Integer32
    }

pdnAdslLineStatusAtucLineAtn OBJECT-TYPE
    SYNTAX      Unsigned32(0..1270 | 2048)
    UNITS       "tenth dB"
    MAX-ACCESS  read-only
    STATUS      current
    DESCRIPTION "The measured difference in the total power transmitted by
                 the ATU-C and the total power received by the ATU-R over all
                 subcarriers during diagnostics mode and initialization.
                 The value 2048 is a special value and indicates the line
                 attenuation is out of the range to be represented."
    REFERENCE   "G.997.1, Section 7.5.1.6, Downstream Line Attenuation
                 (LATNds)."
    ::= { pdnAdslLineStatusEntry 1 }

pdnAdslLineStatusAturLineAtn OBJECT-TYPE
    SYNTAX      Unsigned32(0..1270 | 2048)
    UNITS       "tenth dB"
    MAX-ACCESS  read-only
    STATUS      current
    DESCRIPTION "The measured difference in the total power transmitted by
                 the ATU-R and the total power received by the ATU-C over all
                 subcarriers during diagnostics mode and initialization.
                 The value 2048 is a special value and indicates the line
                 attenuation is out of the range to be represented."
    REFERENCE   "G.997.1, Section 7.5.1.7, Upstream Line Attenuation
                 (LATNus)."
    ::= { pdnAdslLineStatusEntry 2 }

pdnAdslLineStatusAtucSignalAtn OBJECT-TYPE
    SYNTAX      Unsigned32(0..1270 | 2048)
    UNITS       "tenth dB"
    MAX-ACCESS  read-only
    STATUS      current
    DESCRIPTION "The measured difference in the total power transmitted by
                 the ATU-C and the total power received by the ATU-R over all
                 subcarriers during showtime.  The value 2048 is a special
                 value and indicates the line attenuation is out of the
                 range to be represented."
    REFERENCE   "G.997.1, Section 7.5.1.8, Downstream Signal Attenuation
                 (SATNds)."
    ::= { pdnAdslLineStatusEntry 3 }

pdnAdslLineStatusAturSignalAtn OBJECT-TYPE
    SYNTAX      Unsigned32(0..1270 | 2048)
    UNITS       "tenth dB"
    MAX-ACCESS  read-only
    STATUS      current
    DESCRIPTION "The measured difference in the total power transmitted by
                 the ATU-R and the total power received by the ATU-C over all
                 subcarriers during showtime.  The value 2048 is a special
                 value and indicates the line attenuation is out of the
                 range to be represented."
    REFERENCE   "G.997.1, Section 7.5.1.9, Upstream Signal Attenuation
                 (SATNus)."
    ::= { pdnAdslLineStatusEntry 4 }

pdnAdslLineStatusAtucSnrMgn OBJECT-TYPE
    SYNTAX      Integer32(-640..630 | 2048)
    UNITS       "tenth dB"
    MAX-ACCESS  read-only
    STATUS      current
    DESCRIPTION "The upstream signal-to-noise ratio margin is the increase
                 in dB of the noise power received at the ATU-R, such that
                 the BER requirements are met for all upstream bearer
                 channels.  The value 2048 is a special value and indicates
                 the parameter is out of range to be represented."
    REFERENCE   "G.997.1, Section 7.5.1.10, Downstream Signal-to-Noise Ratio
                 Margin (SNRMds)."
    ::= { pdnAdslLineStatusEntry 5 }

pdnAdslLineStatusAturSnrMgn OBJECT-TYPE
    SYNTAX      Integer32(-640..630 | 2048)
    UNITS       "tenth dB"
    MAX-ACCESS  read-only
    STATUS      current
    DESCRIPTION "The downstream signal-to-noise ratio margin is the increase
                 in dB of the noise power received at the ATU-C, such that
                 the BER requirements are met for all upstream bearer
                 channels.  The value 2048 is a special value and indicates
                 the parameter is out of range to be represented."
    REFERENCE   "G.997.1, Section 7.5.1.11, Upstream Signal-to-Noise Ratio
                 Margin (SNRMus)."
    ::= { pdnAdslLineStatusEntry 6 }

pdnAdslLineStatusAtucMaxAttainableLineRate OBJECT-TYPE
    SYNTAX      Gauge32
    UNITS       "bps"
    MAX-ACCESS  read-only
    STATUS      current
    DESCRIPTION "The maximum downstream net data rate currently attainable
                 by the ATU-C transmitter and the ATU-R receiver."
    REFERENCE   "G.997.1, Section 7.5.1.12, Downstream Maximum Attainable
                 Data Rate (ATTNDRds)."
    ::= { pdnAdslLineStatusEntry 7 }

pdnAdslLineStatusAturMaxAttainableLineRate OBJECT-TYPE
    SYNTAX      Gauge32
    UNITS       "bps"
    MAX-ACCESS  read-only
    STATUS      current
    DESCRIPTION "The maximum upstream net data rate currently attainable
                 by the ATU-R transmitter and the ATU-C receiver."
    REFERENCE   "G.997.1, Section 7.5.1.13, Upstream Maximum Attainable
                 Data Rate (ATTNDRus)."
    ::= { pdnAdslLineStatusEntry 8 }

pdnAdslLineStatusAtucActAtp OBJECT-TYPE
    SYNTAX      Integer32(-310..310 | 2048)
    UNITS       "tenth dBm"
    MAX-ACCESS  read-only
    STATUS      current
    DESCRIPTION "The total amount of transmit power delivered by the ATU-C
                 at the U-R reference point, at the instant of the
                 measurement.  The value 2048 is a special value and
                 indicates the parameter is out of range to be represented."
    REFERENCE   "G.997.1, Section 7.5.1.16, Downstream Actual Aggregate
                 Transmit Power (ACTATPus)."
    ::= { pdnAdslLineStatusEntry 9 }

pdnAdslLineStatusAturActAtp OBJECT-TYPE
    SYNTAX      Integer32(-310..310 | 2048)
    UNITS       "tenth dBm"
    MAX-ACCESS  read-only
    STATUS      current
    DESCRIPTION "The total amount of transmit power delivered by the ATU-R
                 at the U-R reference point, at the instant of the
                 measurement.  The value 2048 is a special value and
                 indicates the parameter is out of range to be represented."
    REFERENCE   "G.997.1, Section 7.5.1.17, Upstream Actual Aggregate
                 Transmit Power (ACTATPds)."
    ::= { pdnAdslLineStatusEntry 10 }



-- =====================================
-- == ADSL Line Subcarrier Status Table
-- =====================================
pdnAdslLineSubCarStatusTable OBJECT-TYPE
    SYNTAX      SEQUENCE OF PdnAdslLineSubCarStatusEntry
    MAX-ACCESS  not-accessible
    STATUS      current
    DESCRIPTION "This table contains current line status measurements."
    REFERENCE   "WT-090-4, Section 5.2.1, ADSL Line Status.
                 G.997.1, Section 7.5.1, Line test, diagnostics and status
                 parameters."
    ::= { pdnAdslLineExtObjects 7 }

pdnAdslLineSubCarStatusEntry     OBJECT-TYPE
    SYNTAX      PdnAdslLineSubCarStatusEntry
    MAX-ACCESS  not-accessible
    STATUS      current
    DESCRIPTION "Each entry represents an interface.
                 i.e. a row in the ifTable.

                 Some objects in this table are only valid if a loop diagnostic
                 has successfully completed.  Those objects will return a
                 noSuchName for a Get or Get Next operation if no loop diagnostic
                 has completed."
    INDEX       { ifIndex,
                  pdnAdslLineCarrierIndex }
    ::= { pdnAdslLineSubCarStatusTable 1 }

PdnAdslLineSubCarStatusEntry ::=
    SEQUENCE {
        pdnAdslLineCarrierIndex           Unsigned32,
        pdnAdslLineSubCarAtucHlinPs       Integer32,
        pdnAdslLineSubCarAturHlinPs       Integer32,
        pdnAdslLineSubCarAtucHlogMt       Unsigned32,
        pdnAdslLineSubCarAturHlogMt       Unsigned32,
        pdnAdslLineSubCarAtucQlnPs        Unsigned32,
        pdnAdslLineSubCarAturQlnPs        Unsigned32,
        pdnAdslLineSubCarAtucSnrPs        Unsigned32,
        pdnAdslLineSubCarAturSnrPs        Unsigned32,
        pdnAdslLineSubCarAtucBitsPs       Unsigned32,
        pdnAdslLineSubCarAturBitsPs       Unsigned32,
        pdnAdslLineSubCarAtucHlogPs       Unsigned32,
        pdnAdslLineSubCarAturHlogPs       Unsigned32
    }

pdnAdslLineCarrierIndex OBJECT-TYPE
    SYNTAX      Unsigned32
    MAX-ACCESS  not-accessible
    STATUS      current
    DESCRIPTION "Identifies a row in the table based on a subcarrier.
                 The subcarrier index ranges from 0 to (NSCds-1 or NSCus-1
                 (NSC is Number of Subcarriers) as specified in G.997.1
                 where NSCds is the higher subcarrier that can be
                 transmitted in the downstream direction and NSCus is the
                 higher subcarrier that can be transmitted in the upstream
                 direction. Please refer to the corresponding ITU
                 recommendation for specific values of NSCds and NSCus.
                 The `ADSL Values for NSC' comment above lists those
                 recommendations."
    ::= { pdnAdslLineSubCarStatusEntry 1 }

pdnAdslLineSubCarAtucHlinPs OBJECT-TYPE
    SYNTAX      Integer32(-32768 | -32767..32767)
    MAX-ACCESS  read-only
    STATUS      current
    DESCRIPTION "The downstream linear representation, Hlin(f), of the
                 Channel Characteristics Function, H(f).  This value is
                 only available after a loop diagnostic procedure.  The
                 special value -32768 indicates that no measurement could
                 be done for the subcarrier because it is out of the
                 passband or that the attenuation is out of the range to
                 be represented."
    REFERENCE   "G.997.1, Section 7.5.1.18.2, Downstream H(f) Linear
                 Representation (HLINpsds)."
    ::= { pdnAdslLineSubCarStatusEntry 2 }

pdnAdslLineSubCarAturHlinPs OBJECT-TYPE
    SYNTAX      Integer32(-32768 | -32767..32767)
    MAX-ACCESS  read-only
    STATUS      current
    DESCRIPTION "The upstream linear representation, Hlin(f), of the
                 Channel Characteristics Function, H(f).  This value is
                 only available after a loop diagnostic procedure.  The
                 special value -32768 indicates that no measurement could
                 be done for the subcarrier because it is out of the
                 passband or that the attenuation is out of the range to
                 be represented."
    REFERENCE   "G.997.1, Section 7.5.1.18.6, Upstream H(f) Linear
                 Representation (HLINpsus)."
    ::= { pdnAdslLineSubCarStatusEntry 3 }

pdnAdslLineSubCarAtucHlogMt OBJECT-TYPE
    SYNTAX      Unsigned32(0..65535)
    MAX-ACCESS  read-only
    STATUS      current
    DESCRIPTION "The number of symbols used to measure downstream H(f)
                 logarithmic measurement values.  After a loop
                 diagnostic procedure, this parameter shall contain the
                 number of symbols used to generate the associate parameter.
                 It should correspond to the value specified in the
                 recommendation (e.g. the number of symbols in 1 s. time
                 interval for G.992.3)."
    REFERENCE   "G.997.1, Section 7.5.1.18.3, Downstream H(f) Logarithmic
                 Measurement Time (HLOGMTds)."
    ::= { pdnAdslLineSubCarStatusEntry 4 }

pdnAdslLineSubCarAturHlogMt OBJECT-TYPE
    SYNTAX      Unsigned32(0..65535)
    MAX-ACCESS  read-only
    STATUS      current
    DESCRIPTION "The number of symbols used to measure downstream H(f)
                 logarithmic measurement values.  After a loop
                 diagnostic procedure, this parameter shall contain the
                 number of symbols used to generate the associate parameter.
                 It should correspond to the value specified in the
                 recommendation (e.g. the number of symbols in 1 s. time
                 interval for G.992.3)."
    REFERENCE   "G.997.1, Section 7.5.1.18.7, Upstream H(f) Logarithmic
                 Measurement Time (HLOGMTus)."
    ::= { pdnAdslLineSubCarStatusEntry 5 }

pdnAdslLineSubCarAtucQlnPs OBJECT-TYPE
    SYNTAX      Unsigned32(0..254 | 255)
    UNITS       "dB"
    MAX-ACCESS  read-only
    STATUS      current
    DESCRIPTION "Downstream Quiet Line Noise.  The special value 255
                 indicates that no measurement could be done for the
                 subcarrier because it is out of the passband or that
                 the noise power Spectral Density (PSD) is out of the
                 range to be represented."
    REFERENCE   "G.997.1, Section 7.5.1.19.2, Downstream QLN(f) (QLNpsds)."
    ::= { pdnAdslLineSubCarStatusEntry 6 }

pdnAdslLineSubCarAturQlnPs OBJECT-TYPE
    SYNTAX      Unsigned32(0..254 | 255)
    UNITS       "dB"
    MAX-ACCESS  read-only
    STATUS      current
    DESCRIPTION "Upstream Quiet Line Noise.  The special value 255
                 indicates that no measurement could be done for the
                 subcarrier because it is out of the passband or that
                 the noise power spectral density (PSD) is out of the
                 range to be represented."
    REFERENCE   "G.997.1, Section 7.5.1.19.4, Upstream QLN(f) (QLNpsus)."
    ::= { pdnAdslLineSubCarStatusEntry 7 }

pdnAdslLineSubCarAtucSnrPs OBJECT-TYPE
    SYNTAX      Unsigned32(0..254 | 255 )
    UNITS       "dB"
    MAX-ACCESS  read-only
    STATUS      current
    DESCRIPTION "Downstream Signal-to-Noise Ratio.  The special value 255
                 indicates that no measurement could be done for the
                 subcarrier because it is out of the passband or that the
                 noise power spectral density (PSD) is out of the range to
                 be represented."
    REFERENCE   "G.997.1, Section 7.5.1.20.2, Downstream SNR(f) (SNRpsds)."
    ::= { pdnAdslLineSubCarStatusEntry 8 }

pdnAdslLineSubCarAturSnrPs OBJECT-TYPE
    SYNTAX      Unsigned32(0..254 | 255 )
    UNITS       "dB"
    MAX-ACCESS  read-only
    STATUS      current
    DESCRIPTION "Upstream Signal-to-Noise Ratio.  The special value 255
                 indicates that no measurement could be done for the
                 subcarrier because it is out of the passband or that the
                 noise power spectral density (PSD) is out of the range to
                 be represented."
    REFERENCE   "G.997.1, Section 7.5.1.20.4, Upstream SNR(f) (SNRpsus)."
    ::= { pdnAdslLineSubCarStatusEntry 9 }

pdnAdslLineSubCarAtucBitsPs OBJECT-TYPE
    SYNTAX      Unsigned32(0..15)
    UNITS       "Bits"
    MAX-ACCESS  read-only
    STATUS      current
    DESCRIPTION "Downstream bits allocation."
    REFERENCE   "G.997.1, Section 7.5.1.21.1, Downstream Bits Allocation
                 (BITSpsds)."
    ::= { pdnAdslLineSubCarStatusEntry 10 }

pdnAdslLineSubCarAturBitsPs OBJECT-TYPE
    SYNTAX      Unsigned32(0..15)
    UNITS       "Bits"
    MAX-ACCESS  read-only
    STATUS      current
    DESCRIPTION "Upstream bits allocation."
    REFERENCE   "G.997.1, Section 7.5.1.21.2, Upstream Bits Allocation
                 (BITSpsus)."
    ::= { pdnAdslLineSubCarStatusEntry 11 }

pdnAdslLineSubCarAtucHlogPs OBJECT-TYPE
    SYNTAX      Unsigned32(0..1022 | 1023)
    UNITS       "dB"
    MAX-ACCESS  read-only
    STATUS      current
    DESCRIPTION "The downstream logarithmic representation, Hlog(f), of
                 the Channel Characteristics function, H(f), providing
                 magnitude values.  The special value 1023 indicates
                 that no measurement could be done for the subcarrier
                 because it is out of the passband or that the attenuation
                 is out of the range to be represented."
    REFERENCE   "G.997.1, Section 7.5.1.18.4, Downstream H(f) Logarithmic
                 Representation (HLOGpsds)."
    ::= { pdnAdslLineSubCarStatusEntry 12 }

pdnAdslLineSubCarAturHlogPs OBJECT-TYPE
    SYNTAX      Unsigned32(0..1022 | 1023)
    UNITS       "dB"
    MAX-ACCESS  read-only
    STATUS      current
    DESCRIPTION "The upstream logarithmic representation, Hlog(f), of
                 the Channel Characteristics function, H(f), providing
                 magnitude values.  The special value 1023 indicates
                 that no measurement could be done for the subcarrier
                 because it is out of the passband or that the attenuation
                 is out of the range to be represented."
    REFERENCE   "G.997.1, Section 7.5.1.18.8, Upstream H(f) Logarithmic
                 Representation (HLOGpsus)."
    ::= { pdnAdslLineSubCarStatusEntry 13 }




-- =============================================================================
-- ==                  Accessible for Notifications (AFNs)                    ==
-- =============================================================================
-- None defined



-- =============================================================================
-- ==                  Traps/Notifications                                    ==
-- =============================================================================
-- None defined



-- =============================================================================
-- ==                  Conformance Information                                ==
-- =============================================================================

pdnAdslLineExtCompliances  OBJECT IDENTIFIER ::= { pdnAdslLineExtConformance 1 }
pdnAdslLineExtGroups       OBJECT IDENTIFIER ::= { pdnAdslLineExtConformance 2 }


-- ===========================
-- == Compliance Statements ==
-- ===========================


pdnAdslLineExtMIBCompliance MODULE-COMPLIANCE
    STATUS      current
    DESCRIPTION "The compliance statement for pdnAdslLineMIB entities which
                 implement the pdnAdslLineMIB."
    MODULE      -- this module
    -- No mandatory groups are specified

    GROUP       pdnAdslLineExtGroup
    DESCRIPTION "This group associates objects related to the DSL line
                 and is mandatory only for those entities which implement ADSL2
                 or ADSL2plus capabilities and providing that no IETF standard
                 MIB exists that has objects allowing ADSL2 or ADSL2plus
                 capabilities to be identified and controlled."

    GROUP       pdnAdslLineSpectrumGroup
    DESCRIPTION "This group associates objects related to spectrum and power
                 spectral configurations and is mandatory only for those
                 entities which implement ADSL2 or ADSL2plus capabilities and
                 providing that no IETF standard MIB exists that has objects
                 allowing ADSL2 or ADSL2plus capabilities to be identified and
                 controlled."

    GROUP       pdnAdslModeSpecificPsdGroup
    DESCRIPTION "This group associates objects related to spectrum and power
                 spectral configurations that are specific to a particular
                 type of ADSL mode is mandatory only for those entities which
                 implement ADSL2 or ADSL2plus capabilities and providing that
                 no IETF standard MIB exists that has objects allowing
                 ADSL2 or ADSL2plus capabilities to be identified and controlled."

    GROUP       pdnAdslPsdGroup
    DESCRIPTION "This group associates objects related to configuring profiles
                 for power spectral density setting and is mandatory only for
                 those entities which implement ADSL2 or ADSL2plus capabilities
                 and providing that no IETF standard MIB exists that has objects
                 allowing ADSL2 or ADSL2plus capabilities to be identified and
                 controlled."

    GROUP       pdnAdslCarMaskGroup
    DESCRIPTION "This group associates objects related to defining subcarriers
                 to be masked in the downstream direction."

    GROUP       pdnAdslLineL2AtprtGroup
    DESCRIPTION "This group adds an object for total maximum aggregate transmit
                 power reduction in L2."

    GROUP       pdnAdslLineStatusLineAtnGroup
    DESCRIPTION "This group associates status objects related to line
                 attenuation during diagnostic mode and initialization."

    GROUP       pdnAdslLineStatusSignalAtnGroup
    DESCRIPTION "This group associates status objects related to line
                 attenuation during showtime."

    GROUP       pdnAdslLineStatusSnrMgnGroup
    DESCRIPTION "This group associates status objects related to SNR margin
                 ratio."

    GROUP       pdnAdslLineStatusMaxattainableLineRateGroup
    DESCRIPTION "This group associates status objects related to the
                 current maximum attainable net data rate."

    GROUP       pdnAdslLineStatusActAtpGroup
    DESCRIPTION "This group associates status objects related to the
                 actual aggregate transmit power."

    GROUP       pdnAdslLineSubCarStatusHlinGroup
    DESCRIPTION "This group associates the status objects related to the
                 linear representation of the Channel Characteristics
                 Function on a per-subcarrier basis for a line."

    GROUP       pdnAdslLineSubCarStatusHlogMtGroup
    DESCRIPTION "This group associates the status objects related to the
                 logarithmic measurement time on a per-subcarrier basis
                 for the line"

    GROUP       pdnAdslLineSubCarStatusQlnGroup
    DESCRIPTION "This group associates the status objects related to the
                 Quiet Line Noise on a per-subcarrier basis for the line."

    GROUP       pdnAdslLineSubCarStatusSnrGroup
    DESCRIPTION "This group associates the status objects related to the
                 Signal-to-Noise Ratio on a per-subcarrier basis for the
                 line."

    GROUP       pdnAdslLineSubCarStatusBitsGroup
    DESCRIPTION "The group associates the status objects related to the
                 bits allocation on a per-subcarrier basis for the line."

    GROUP       pdnAdslLineSubCarStatusHlogGroup
    DESCRIPTION "The group associates the status objects related to the
                 logarithmic representation of the Channel Characteristics
                 function on a per-subcarrier basis for the line."




    -- All objects, if implemented, are expected to be implemented to the
    -- maximal level as specified in their OBJECT-TYPE macro.
    --

    ::= { pdnAdslLineExtCompliances 1 }


-- ==========================
-- == Units of Conformance ==
-- ==========================

pdnAdslLineExtObjGroups   OBJECT IDENTIFIER ::= { pdnAdslLineExtGroups 1 }
pdnAdslLineExtAfnGroups   OBJECT IDENTIFIER ::= { pdnAdslLineExtGroups 2 }
pdnAdslLineExtNtfyGroups  OBJECT IDENTIFIER ::= { pdnAdslLineExtGroups 3 }

-- ===================
-- == Object Groups ==
-- ===================

pdnAdslLineExtGroup OBJECT-GROUP
    OBJECTS {
        pdnAdslLineTransAtucCap,
        pdnAdslLineTransAtucConfig,
        pdnAdslLineTransAtucActual,
        pdnAdslLinePowerManagementConfig,
        pdnAdslLineSpectrumProfile,
        pdnAdslLinePmMode,
        pdnAdslLineL0Time,
        pdnAdslLineL2Time,
        pdnAdslLineL2Atpr,
        pdnAdslLineLdsf
    }
    STATUS      current
    DESCRIPTION "A collection of objects providing extended
                 configuration information about an ADSL Line."
    ::= { pdnAdslLineExtObjGroups 1 }

pdnAdslLineSpectrumGroup OBJECT-GROUP
    OBJECTS {
        pdnAdslLineSpectrumProfileRowStatus,
        pdnAdslLineSpectrumModeSpecificPsdProfile,
        pdnAdslLineSpectrumAtucCarMaskProfile,
        pdnAdslLineSpectrumAturCarMaskProfile
    }
    STATUS      current
    DESCRIPTION "A collection of objects providing transmission
                 spectrum and power spectral density related profiles."
    ::= { pdnAdslLineExtObjGroups 2 }

pdnAdslModeSpecificPsdGroup OBJECT-GROUP
    OBJECTS {
        pdnAdslModeSpecificPsdConfAdslPsdConfProfile,
        pdnAdslModeSpecificPsdConfRowStatus
    }
    STATUS      current
    DESCRIPTION "A collection of objects providing a mapping from an entry
                 into the ADSL Line Spectrum Table to a profile defining a
                 specific set of power spectral density settings."
    ::= { pdnAdslLineExtObjGroups 3 }

pdnAdslPsdGroup OBJECT-GROUP
    OBJECTS {
        pdnAdslPsdConfRowStatus,
        pdnAdslPsdConfAtucMaxNomPsd,
        pdnAdslPsdConfAturMaxNomPsd,
        pdnAdslPsdConfAtucMaxNomAtp,
        pdnAdslPsdConfAturMaxNomAtp,
        pdnAdslPsdConfAtucMaxRxPwr
    }
    STATUS      current
    DESCRIPTION "A collection of objects providing specific power spectral
                 density settings based on a named profile."
    ::= { pdnAdslLineExtObjGroups 4 }

pdnAdslCarMaskGroup OBJECT-GROUP
    OBJECTS {
        pdnAdslCarMaskRowStatus,
        pdnAdslCarMaskSubCarrierStatus
    }
    STATUS      current
    DESCRIPTION "A collection of objects providing the ability for an
                 administrator to mask out specific subcarriers in
                 the downstream or the upstream direction."
    ::= { pdnAdslLineExtObjGroups 5 }

pdnAdslLineL2AtprtGroup OBJECT-GROUP
    OBJECTS {
        pdnAdslLineL2Atprt
    }
    STATUS      current
    DESCRIPTION "Total maximum aggregate transmit power reduction in L2."
    ::= { pdnAdslLineExtObjGroups 6 }

pdnAdslLineStatusLineAtnGroup OBJECT-GROUP
    OBJECTS {
        pdnAdslLineStatusAtucLineAtn,
        pdnAdslLineStatusAturLineAtn
    }
    STATUS      current
    DESCRIPTION "Line attenuation during diagnostic mode and initialization."
    ::= { pdnAdslLineExtObjGroups 7 }

pdnAdslLineStatusSignalAtnGroup OBJECT-GROUP
    OBJECTS {
        pdnAdslLineStatusAtucSignalAtn,
        pdnAdslLineStatusAturSignalAtn
    }
    STATUS      current
    DESCRIPTION "Line attenuation during showtime."
    ::= { pdnAdslLineExtObjGroups 8 }

pdnAdslLineStatusSnrMgnGroup OBJECT-GROUP
    OBJECTS {
        pdnAdslLineStatusAtucSnrMgn,
        pdnAdslLineStatusAturSnrMgn
    }
    STATUS      current
    DESCRIPTION "SNR margin ratio."
    ::= { pdnAdslLineExtObjGroups 9 }

pdnAdslLineStatusMaxattainableLineRateGroup OBJECT-GROUP
    OBJECTS {
        pdnAdslLineStatusAtucMaxAttainableLineRate,
        pdnAdslLineStatusAturMaxAttainableLineRate
    }
    STATUS      current
    DESCRIPTION "Current maximum attainable net data rate."
    ::= { pdnAdslLineExtObjGroups 10 }

pdnAdslLineStatusActAtpGroup OBJECT-GROUP
    OBJECTS {
        pdnAdslLineStatusAtucActAtp,
        pdnAdslLineStatusAturActAtp
    }
    STATUS      current
    DESCRIPTION "Actual aggregate transmit power."
    ::= { pdnAdslLineExtObjGroups 11 }

pdnAdslLineSubCarStatusHlinGroup OBJECT-GROUP
    OBJECTS {
        pdnAdslLineSubCarAtucHlinPs,
        pdnAdslLineSubCarAturHlinPs
    }
    STATUS      current
    DESCRIPTION "Linear representation of the Channel
                 Characteristics function for a subcarrier on a line."
    ::= { pdnAdslLineExtObjGroups 12 }

pdnAdslLineSubCarStatusHlogMtGroup OBJECT-GROUP
    OBJECTS {
        pdnAdslLineSubCarAtucHlogMt,
        pdnAdslLineSubCarAturHlogMt
    }
    STATUS      current
    DESCRIPTION "Logarithmic measurement time of the Channel
                 Characteristics function for a subcarrier on a line."
    ::= { pdnAdslLineExtObjGroups 13 }

pdnAdslLineSubCarStatusQlnGroup OBJECT-GROUP
    OBJECTS {
        pdnAdslLineSubCarAtucQlnPs,
        pdnAdslLineSubCarAturQlnPs
    }
    STATUS      current
    DESCRIPTION "Quiet Line Noise for a subcarrier on a line."
    ::= { pdnAdslLineExtObjGroups 14 }

pdnAdslLineSubCarStatusSnrGroup OBJECT-GROUP
    OBJECTS {
        pdnAdslLineSubCarAtucSnrPs,
        pdnAdslLineSubCarAturSnrPs
    }
    STATUS      current
    DESCRIPTION "Signal-to-Noise Ratio for a subcarrier on a line."
    ::= { pdnAdslLineExtObjGroups 15 }

pdnAdslLineSubCarStatusBitsGroup OBJECT-GROUP
    OBJECTS {
        pdnAdslLineSubCarAtucBitsPs,
        pdnAdslLineSubCarAturBitsPs
    }
    STATUS      current
    DESCRIPTION "Bits allocation for a subcarrier on a line."
    ::= { pdnAdslLineExtObjGroups 16 }

pdnAdslLineSubCarStatusHlogGroup OBJECT-GROUP
    OBJECTS {
        pdnAdslLineSubCarAtucHlogPs,
        pdnAdslLineSubCarAturHlogPs
    }
    STATUS      current
    DESCRIPTION "Logarithmic representation of the Channel Characteristics
                 function for a subcarrier on a line."
    ::= { pdnAdslLineExtObjGroups 17 }




-- ==================================
-- == Accessible for Notify Groups ==
-- ==================================
-- None.



-- =========================
-- == Notification Groups ==
-- =========================
-- None.



-- =========
-- == END ==
-- =========
END
