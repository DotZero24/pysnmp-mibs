PDN-MPE-DOMAIN-MIB DEFINITIONS ::= BEGIN

-- Version :  1.0 APPROVED
-- Enterprise pdn domain mib (mpe support)
-- Copyright (C) 2000 Paradyne Corporation.

-- Created by : Wayne Jadoo / Prakash Easwar

-- The tables in this Mib is used primarily for configuring
-- VNIDs on a card. The configured VNIDs can then be bounded to
-- intefaces and clients can then be configured at each interface.
--
--  04/27/00 Prakash Easwar
--    1) added new object to mpePdnCardGeneralParamsTable
--
--          mpePdnCardGeneralParamsAdditionalClientsAvailable

IMPORTS
ClientState,
SwitchState,
VnidRange,
VnidTaggingState
FROM PDN-TC
MacAddress, RowStatus,
DisplayString
FROM SNMPv2-TC
entPhysicalIndex
FROM ENTITY-MIB
TimeTicks,
IpAddress
FROM RFC1155-SMI
TRAP-TYPE
FROM RFC-1215
ifIndex
FROM RFC1213-MIB
OBJECT-TYPE
FROM RFC-1212
mpe-domain
FROM PDN-HEADER-MIB
;

mpePdnDomainMIBObjects   OBJECT IDENTIFIER ::= { mpe-domain 1 }
mpePdnDomainMIBTraps     OBJECT IDENTIFIER ::= { mpe-domain 2 }
mpePdnCardGeneralParams  OBJECT IDENTIFIER ::= { mpePdnDomainMIBObjects 1 }
mpePdnCardConfig         OBJECT IDENTIFIER ::= { mpePdnDomainMIBObjects 2 }

-- mpePdnCardGeneralParams group
-- This group reflect the status of VNID tagging.

          mpePdnCardGeneralParamsTable OBJECT-TYPE
              SYNTAX  SEQUENCE OF MpePdnCardGeneralParamsEntry
              ACCESS  not-accessible
              STATUS  mandatory
              DESCRIPTION
                 "A table that allows configuration of a Card VNID state."
              ::= { mpePdnCardGeneralParams 1 }

          mpePdnCardGeneralParamsEntry OBJECT-TYPE
              SYNTAX  MpePdnCardGeneralParamsEntry
              ACCESS  not-accessible
              STATUS  mandatory
              DESCRIPTION
                 "A list of information for Card VNID."
              INDEX  { entPhysicalIndex }
              ::= { mpePdnCardGeneralParamsTable 1 }

          MpePdnCardGeneralParamsEntry ::=
              SEQUENCE {
               mpePdnCardGeneralParamsVNIDMode 	VnidTaggingState,
               mpePdnCardGeneralParamsAdditionalClientsAvailable INTEGER
              }

          mpePdnCardGeneralParamsVNIDMode  OBJECT-TYPE
              SYNTAX  VnidTaggingState
              ACCESS  read-write
              STATUS  mandatory
              DESCRIPTION
                 "The state of VNID tagging on the card."
              ::= { mpePdnCardGeneralParamsEntry  1 }

          mpePdnCardGeneralParamsAdditionalClientsAvailable OBJECT-TYPE
            SYNTAX   INTEGER
            ACCESS   read-only
            STATUS   mandatory
            DESCRIPTION
                "This object contains the current number
                of unallocated client entries in the client table"
             ::= { mpePdnCardGeneralParamsEntry  2 }

 -- The Card Configuration Table

          mpePdnCardConfigTable OBJECT-TYPE
              SYNTAX  SEQUENCE OF MpePdnCardConfigEntry
              ACCESS  not-accessible
              STATUS  mandatory
              DESCRIPTION
                 "A table that contains information about
                  Mux Forwarding, IP Filtering, IP Scoping
                  and domain name for each VNID."
              ::= { mpePdnCardConfig 1 }

          mpePdnCardConfigEntry OBJECT-TYPE
              SYNTAX  MpePdnCardConfigEntry
              ACCESS  not-accessible
              STATUS  mandatory
              DESCRIPTION
                 "A list of configuration information for each VNID."
              INDEX  { entPhysicalIndex, mpePdnCardConfigVnidId  }
              ::= { mpePdnCardConfigTable 1 }

			 MpePdnCardConfigEntry ::=
              SEQUENCE {
                mpePdnCardConfigVnidId       VnidRange,
                mpePdnCardConfigDomainName   DisplayString,
                mpePdnCardConfigMuxFwd       SwitchState,
                mpePdnCardConfigIPFiltering  SwitchState,
                mpePdnCardConfigIPScoping    SwitchState,
                mpePdnCardConfigVnidAuth     SwitchState,
                mpePdnCardConfigRowStatus    RowStatus
               }

          mpePdnCardConfigVnidId OBJECT-TYPE
              SYNTAX  VnidRange
              ACCESS  read-only
              STATUS  mandatory
              DESCRIPTION
                 "The VNID Id number of the virtual network for which this entry
                  contains management information."
              ::= { mpePdnCardConfigEntry 1 }

         mpePdnCardConfigDomainName OBJECT-TYPE
              SYNTAX  DisplayString
              ACCESS  read-write
              STATUS  mandatory
              DESCRIPTION
                 "The Domain name of the ISP for this VNID. The default value
                  for this object is a blank string"
              ::= { mpePdnCardConfigEntry 2 }

          mpePdnCardConfigMuxFwd OBJECT-TYPE
              SYNTAX  SwitchState
              ACCESS  read-write
              STATUS  mandatory
              DESCRIPTION
                 "This object shows if Mux Forwarding has been
                  enabled or disabled by the user."
              ::= { mpePdnCardConfigEntry 3 }

          mpePdnCardConfigIPFiltering OBJECT-TYPE
              SYNTAX  SwitchState
              ACCESS  read-write
              STATUS  mandatory
              DESCRIPTION
                  "This object shows if IP Filtering has been
                   enabled or disabled by the user."
              ::= { mpePdnCardConfigEntry 4 }

          mpePdnCardConfigIPScoping OBJECT-TYPE
              SYNTAX  SwitchState
              ACCESS  read-write
              STATUS  mandatory
              DESCRIPTION
                 "This object shows if IP Scoping has been
                  enabled or disabled by the user."
              ::= { mpePdnCardConfigEntry 5}

          mpePdnCardConfigVnidAuth OBJECT-TYPE
              SYNTAX  SwitchState
              ACCESS  read-write
              STATUS  mandatory
              DESCRIPTION
                 "This object shows if VNID authorization has been
                  enabled or disabled by the user. When this obect is
                  is enable, only interfaces bound to this VNID will accept
                  packets with this VNID."
              ::= { mpePdnCardConfigEntry 6 }

           mpePdnCardConfigRowStatus OBJECT-TYPE
              SYNTAX   RowStatus
              ACCESS   read-write
              STATUS   mandatory
              DESCRIPTION
                 "This object is used to create a new row or
                  or delete an existing row in this table"
              ::= { mpePdnCardConfigEntry 7 }

END
