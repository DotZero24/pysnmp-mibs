PDN-SONETEXT-MIB DEFINITIONS ::= BEGIN

IMPORTS
	OBJECT-TYPE
		FROM RFC-1212
	TRAP-TYPE
		FROM RFC-1215
	TimeTicks
		FROM RFC1155-SMI
	sonetSectionCurrentStatus,
	sonetLineCurrentStatus,
	sonetPathCurrentStatus
		FROM SONET-MIB
	pdnSonetMIB
		FROM PDN-HEADER-MIB;

-- ===============================================================
--
--   Extentions to the SONET-MIB
--
--  Release: 1.0  05/26/99 (Initial Release) J.Strain
--
--  History:
-- 02/07/2000 - added 2 objects to the devSonetConfigTable:
-- 	devSonetStatusLastChange and devSonetStatusChangeTrapEnable.
--	 Added a trap devSonetStatusChange
--
-- This group extends the SONET-MIB.
--

devSonetConfig OBJECT IDENTIFIER ::= { pdnSonetMIB  1 }
devSonetTraps OBJECT IDENTIFIER ::= { pdnSonetMIB  2 }

devSonetConfigTable OBJECT-TYPE
    SYNTAX  SEQUENCE OF DevSonetConfigEntry
    ACCESS  not-accessible
    STATUS  mandatory
    DESCRIPTION
           "The Paradyne Sonet-MIB Table Augment."
    ::= { devSonetConfig  1 }

devSonetConfigEntry OBJECT-TYPE
    SYNTAX  DevSonetConfigEntry
    ACCESS  not-accessible
    STATUS  mandatory
    DESCRIPTION
           "An entry in the Paradyne Sonet-MIB Interface Config Table."
    INDEX   { devSonetIfIndex }
    ::= { devSonetConfigTable  1 }

DevSonetConfigEntry ::=
    SEQUENCE {
    devSonetIfIndex
        INTEGER,
    devSonetXmitClkSrc
        INTEGER,
    devSonetStatusLastChange
	TimeTicks,
    devSonetStatusChangeTrapEnable
	INTEGER

    }

devSonetIfIndex OBJECT-TYPE
    SYNTAX  INTEGER
    ACCESS  read-only
    STATUS  mandatory
    DESCRIPTION
           "The index value which uniquely identifies the
            interface for which this entry contains information
            on interface tests.  The interface identified by a
            particular value of this index is the same interface
            as identified by the same value of ifIndex from the
            Interfaces table of MIB II (RFC 1213)."
    ::= { devSonetConfigEntry 1 }

devSonetXmitClkSrc OBJECT-TYPE
    SYNTAX  INTEGER {
                 loopTiming(1),
                 localTiming(2),
                 throughTiming(3),
                 systemTiming(4)
               }
    ACCESS  read-write
    STATUS  mandatory
    DESCRIPTION
           "This object is used to configure the clock to be used by the transmit
            side of the interface.
              loopTiming -- Timing is Extracted from the Receiving
                            OC-N signal and re-used on the Transmitting
                            OC-N signal. Thats is the timing is
                            supplied by the far-end OC-N interface.
              localTiming -- Timing provided by the internal clock.
              throughTiming -- Timing is Extracted from one OC-N interface
                               and used by the transmitted signal on another
                               OC-N interface.
              systemTiming -- Timing is provided by the source selected for
                               system  timing (devCfgClkSource)"
    ::= { devSonetConfigEntry  2 }

devSonetStatusLastChange OBJECT-TYPE
          SYNTAX  TimeTicks
          ACCESS  read-only
          STATUS mandatory
          DESCRIPTION
                 "The value of MIB II's sysUpTime object at the
                 time this Sonet entered its current line status
                 state.  If the current state was entered prior to
                 the last re-initialization of the proxy-agent,
                 then this object contains a zero value."
          ::= { devSonetConfigEntry 3 }

devSonetStatusChangeTrapEnable  OBJECT-TYPE

          SYNTAX      INTEGER {
                         enabled(1),
                         disabled(2)
                      }
          ACCESS  read-write
          STATUS      mandatory
          DESCRIPTION
                 "Indicates whether devSonetStatusChange traps
                 should be generated for this interface."
--          DEFVAL { disabled }
          ::= { devSonetConfigEntry 4 }

-- ===============================================
--
-- 			Sonet TRAPS
--
-- ===============================================



     devSonetStatusChange TRAP-TYPE

		ENTERPRISE devSonetTraps
         VARIABLES {
			devSonetStatusLastChange,
			sonetSectionCurrentStatus,
			sonetLineCurrentStatus,
			sonetPathCurrentStatus
			}
         DESCRIPTION
		"A devSonetStatusChange trap is sent when the
		value of an instance of sonetSectionCurrentStatus
		or sonetLineCurrentStatus or sonetPathCurrentStatus changes.
		It can be utilized by an NMS to trigger polls.  When
		the line status change results in a lower level
		line status change (i.e. sonet), then no traps for
		the lower level are sent."
                    ::= 1

END
