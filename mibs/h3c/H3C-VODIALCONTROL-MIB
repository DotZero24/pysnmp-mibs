-- ==========================================================================
-- Copyright (C) 2004 by H3C TECHNOLOGIES. All rights reserved.
--
-- Description: The purpose of this MIB file is to provide the definition of
--              voice dial control configuration.
-- Reference:
-- Version: V1.2
-- History:
-- V1.0 2005-03-22 Initial version, created by Yang Youku
-- V1.1 2005-10-08 Add enumerative value 'initial' to PhoneNumberType and
--      PhoneNumberPlan, by Cao Hui. Trim trailing spaces by longyin.
-- V1.2 2006-02-27 revised enumerative value of h3cVoPeerCfgOutbandMode by Zhou Xinzhong.
--      change 'h245AlphaNumeric' to 'h245' and add 'h225'.
-- ==========================================================================
H3C-VODIALCONTROL-MIB DEFINITIONS ::= BEGIN

IMPORTS
    OBJECT-TYPE, MODULE-IDENTITY, IpAddress, Integer32
        FROM SNMPv2-SMI
    RowStatus
        FROM SNMPv2-TC
    CodecType
        FROM H3C-VO-TYPE-MIB
    InetAddressType, InetAddress
        FROM INET-ADDRESS-MIB
    h3cVoice
        FROM HUAWEI-3COM-OID-MIB;


    h3cVoiceDialControl MODULE-IDENTITY
        LAST-UPDATED "200503150000Z"
        ORGANIZATION
            "Hangzhou H3C Tech. Co., Ltd."
        CONTACT-INFO
            "Platform Team Hangzhou H3C Tech. Co., Ltd.
            Hai-Dian District Beijing P.R. China
            http://www.h3c.com
            Zip:100085
            "
        DESCRIPTION
            "This MIB file is to provide the definition of
             voice dial control configuration."
        REVISION "200503150000Z"
        DESCRIPTION
            "The initial version of this MIB file."
        ::= { h3cVoice 5 }

--==================================
--      Type declaration
--==================================

    FaxProtocolType ::= INTEGER
        {
        nonstandardCompatible(1),
        t38(2),
        h323T38(3),
        sipT38(4),
        pcmG711alaw(5),
        pcmG711ulaw(6)
        }

    FaxBaudrateType ::= INTEGER
        {
        disable(1),
        voice(2),
        b2400(3),
        b4800(4),
        b9600(5),
        b14400(6)
        }

    FaxSupportModeType ::= INTEGER
        {
        rtp(1),
        vt(2),
        sip-udp(3)
        }

    FaxTrainMode ::= INTEGER
        {
        local(1),
        ppp(2)
        }

    PhoneNumberType ::= INTEGER
        {
            unknown(1),        -- The numbering type is unknown.
            abbreviated(2),    -- The numbering type is abbreviated.
            international(3),  -- The numbering type is international.
            national(4),       -- The numbering type is national.
            network(5),        -- The numbering type is network.
            reserved(6),       -- The numbering type is reserved.
            subscriber(7),     -- The numbering type is subscriber.
            initial(8)         -- The numbering type is initial.
        }

    PhoneNumberPlan ::= INTEGER
        {
            unknown(1),        -- The numbering plan is unknown.
            data(2),           -- Data numbering plan.
            isdn(3),           -- ISDN/telephone numbering plan.
            national(4),       -- National standard numbering plan.
            private(5),        -- Private numbering plan.
            reserved(6),       -- Reserved for extension.
            telex(7),          -- Telex numbering plan.
            initial(8)         -- Initial numbering plan.
        }


    h3cVoPeerObjects OBJECT IDENTIFIER ::= { h3cVoiceDialControl 1 }

--====================================================================
--                  h3cVoPeerCommonConfigTable
--
--====================================================================
    h3cVoPeerCommonConfigTable OBJECT-TYPE
        SYNTAX SEQUENCE OF H3CVoPeerCommonConfigEntry
        MAX-ACCESS not-accessible
        STATUS current
        DESCRIPTION
            "This table contains the general voice peer information."
        ::= { h3cVoPeerObjects 1 }


    h3cVoPeerCommonConfigEntry OBJECT-TYPE
        SYNTAX H3CVoPeerCommonConfigEntry
        MAX-ACCESS not-accessible
        STATUS current
        DESCRIPTION
            "The entry of h3cVoPeerCommonConfigTable."
        INDEX { h3cVoPeerCfgIndex }
        ::= { h3cVoPeerCommonConfigTable 1 }


    H3CVoPeerCommonConfigEntry ::=
        SEQUENCE {
            h3cVoPeerCfgIndex
                Integer32,
            h3cVoPeerCfgRowStatus
                RowStatus,
            h3cVoPeerCfgType
                INTEGER,
            h3cVoPeerCfgDesPattern
                OCTET STRING,
            h3cVoPeerCfgCodec1st
                CodecType,
            h3cVoPeerCfgCodec2nd
                CodecType,
            h3cVoPeerCfgCodec3rd
                CodecType,
            h3cVoPeerCfgCodec4th
                CodecType,
            h3cVoPeerCfgDSCP
                Integer32,
            h3cVoPeerCfgShutDown
                INTEGER,
            h3cVoPeerCfgVADEnable
                INTEGER,
            h3cVoPeerCfgOutbandMode
                INTEGER,
            h3cVoPeerCfgFaxLevel
                Integer32,
            h3cVoPeerCfgFaxBaudrate
                FaxBaudrateType,
            h3cVoPeerCfgFaxLocalTrainPara
                Integer32,
            h3cVoPeerCfgFaxProtocol
                FaxProtocolType,
            h3cVoPeerCfgT38FaxHRPackNum
                Integer32,
            h3cVoPeerCfgT38FaxLRPackNum
                Integer32,
            h3cVoPeerCfgFaxSendNSFEnable
                INTEGER,
            h3cVoPeerCfgFaxSupportMode
                FaxSupportModeType,
            h3cVoPeerCfgFaxTrainMode
                FaxTrainMode,
            h3cVoPeerCfgFaxEcm
                INTEGER,
            h3cVoPeerCfgPriority
                Integer32,
            h3cVoPeerCfgDescription
                OCTET STRING,
            h3cVoPeerCfgCallingNumberType
                PhoneNumberType,
            h3cVoPeerCfgCalledNumberType
                PhoneNumberType,
            h3cVoPeerCfgCallingNumberPlan
                PhoneNumberPlan,
            h3cVoPeerCfgCalledNumberPlan
                PhoneNumberPlan,
            h3cVoPeerCfgSelectStop
                INTEGER,
            h3cVoPeerCfgCallingNumSubstRule
                Integer32,
            h3cVoPeerCfgCalledNumSubstRule
                Integer32,
            h3cVoPeerCfgMaxCall
                Integer32
        }

    h3cVoPeerCfgIndex OBJECT-TYPE
        SYNTAX Integer32 (1..2147483647)
        MAX-ACCESS not-accessible
        STATUS current
        DESCRIPTION
            "The index of a dial entity common table."
        ::= { h3cVoPeerCommonConfigEntry 1 }


    h3cVoPeerCfgRowStatus OBJECT-TYPE
        SYNTAX RowStatus
        MAX-ACCESS read-create
        STATUS current
        DESCRIPTION
            "This object is used to create, delete or modify a row in
            this table."
        ::= { h3cVoPeerCommonConfigEntry 2 }


    h3cVoPeerCfgType OBJECT-TYPE
        SYNTAX INTEGER
            {
            pots(1),
            voip(2),
            vofr(3)
            }
        MAX-ACCESS read-create
        STATUS current
        DESCRIPTION
            "The type of voice entity."
        ::= { h3cVoPeerCommonConfigEntry 3 }


    h3cVoPeerCfgDesPattern OBJECT-TYPE
        SYNTAX OCTET STRING
        MAX-ACCESS read-create
        STATUS current
        DESCRIPTION
            "This object indicates the caller number of this dial peer."
        ::= { h3cVoPeerCommonConfigEntry 4 }


    h3cVoPeerCfgCodec1st OBJECT-TYPE
        SYNTAX CodecType
        MAX-ACCESS read-create
        STATUS current
        DESCRIPTION
            "This object indicates the first desirable CODEC of speech
            of this dial peer."
        ::= { h3cVoPeerCommonConfigEntry 5 }


    h3cVoPeerCfgCodec2nd OBJECT-TYPE
        SYNTAX CodecType
        MAX-ACCESS read-create
        STATUS current
        DESCRIPTION
            "This object indicates the second desirable CODEC of speech
            of this dial peer."
        ::= { h3cVoPeerCommonConfigEntry 6 }


    h3cVoPeerCfgCodec3rd OBJECT-TYPE
        SYNTAX CodecType
        MAX-ACCESS read-create
        STATUS current
        DESCRIPTION
            "This object indicates the third desirable CODEC of speech
            of this dial peer."
        ::= { h3cVoPeerCommonConfigEntry 7 }


    h3cVoPeerCfgCodec4th OBJECT-TYPE
        SYNTAX CodecType
        MAX-ACCESS read-create
        STATUS current
        DESCRIPTION
            "This object indicates the forth desirable CODEC of speech
            of this dial peer."
        ::= { h3cVoPeerCommonConfigEntry 8 }


    h3cVoPeerCfgDSCP OBJECT-TYPE
        SYNTAX Integer32
        MAX-ACCESS read-create
        STATUS current
        DESCRIPTION
            "This object indicates the DSCP(Different Service Code Point)
            value of voice packets."
        ::= { h3cVoPeerCommonConfigEntry 9 }


    h3cVoPeerCfgShutDown OBJECT-TYPE
        SYNTAX INTEGER
            {
            enable(1),
            disable(2)
            }
        MAX-ACCESS read-create
        STATUS current
        DESCRIPTION
            "This object indicates the current status of this dial peer."
        ::= { h3cVoPeerCommonConfigEntry 10 }


    h3cVoPeerCfgVADEnable OBJECT-TYPE
        SYNTAX INTEGER
            {
            enable(1),
            disable(2)
            }
        MAX-ACCESS read-create
        STATUS current
        DESCRIPTION
            "This object indicates whether the VAD(Voice Activity Detection)
            is enabled."
        ::= { h3cVoPeerCommonConfigEntry 11 }


    h3cVoPeerCfgOutbandMode OBJECT-TYPE
        SYNTAX INTEGER
            {
            h245(1),
            voice(2),
            sip(3),
            h225(4)
            }
        MAX-ACCESS read-create
        STATUS current
        DESCRIPTION
            "This object indicates the DTMF(Dual Tone Multi-Frequency)
            outband type of this dial peer."
        ::= { h3cVoPeerCommonConfigEntry 12 }


    h3cVoPeerCfgFaxLevel OBJECT-TYPE
        SYNTAX Integer32
        MAX-ACCESS read-create
        STATUS current
        DESCRIPTION
            "This object indicates the fax level of this dial peer."
        ::= { h3cVoPeerCommonConfigEntry 13 }


    h3cVoPeerCfgFaxBaudrate OBJECT-TYPE
        SYNTAX FaxBaudrateType
        MAX-ACCESS read-create
        STATUS current
        DESCRIPTION
            "This object indicates the fax baudrate of this dial peer."
        ::= { h3cVoPeerCommonConfigEntry 14 }


    h3cVoPeerCfgFaxLocalTrainPara OBJECT-TYPE
        SYNTAX Integer32
        MAX-ACCESS read-create
        STATUS current
        DESCRIPTION
            "This object indicates the fax local train threshold of this
            dial peer."
        ::= { h3cVoPeerCommonConfigEntry 15 }


    h3cVoPeerCfgFaxProtocol OBJECT-TYPE
        SYNTAX FaxProtocolType
        MAX-ACCESS read-create
        STATUS current
        DESCRIPTION
            "This object indicates the fax protocol of this dial peer."
        ::= { h3cVoPeerCommonConfigEntry 16 }


    h3cVoPeerCfgT38FaxHRPackNum OBJECT-TYPE
        SYNTAX Integer32 (0..2)
        MAX-ACCESS read-create
        STATUS current
        DESCRIPTION
            "This object indicates the high speed redundancy packet
            numbers."
        ::= { h3cVoPeerCommonConfigEntry 17 }


    h3cVoPeerCfgT38FaxLRPackNum OBJECT-TYPE
        SYNTAX Integer32 (0..5)
        MAX-ACCESS read-create
        STATUS current
        DESCRIPTION
            "This object indicates the low speed redundancy packet
            numbers."
        ::= { h3cVoPeerCommonConfigEntry 18 }


    h3cVoPeerCfgFaxSendNSFEnable OBJECT-TYPE
        SYNTAX INTEGER
            {
            enable(1),
            disable(2)
            }
        MAX-ACCESS read-create
        STATUS current
        DESCRIPTION
            "This object indicates whether sends NSF(non-standard faculty)
            to fax of this dial peer."
        ::= { h3cVoPeerCommonConfigEntry 19 }


    h3cVoPeerCfgFaxSupportMode OBJECT-TYPE
        SYNTAX FaxSupportModeType
        MAX-ACCESS read-create
        STATUS current
        DESCRIPTION
            "This object indicates the fax support mode of this dial peer."
        ::= { h3cVoPeerCommonConfigEntry 20 }


    h3cVoPeerCfgFaxTrainMode OBJECT-TYPE
        SYNTAX FaxTrainMode
        MAX-ACCESS read-create
        STATUS current
        DESCRIPTION
            "This object indicates the fax train mode of this dial peer."
        ::= { h3cVoPeerCommonConfigEntry 21 }


    h3cVoPeerCfgFaxEcm OBJECT-TYPE
        SYNTAX INTEGER
            {
            enable(1),
            disalbe(2)
            }
        MAX-ACCESS read-create
        STATUS current
        DESCRIPTION
            "This object indicates whether the ECM(error correct mode)
             is enabled."
        ::= { h3cVoPeerCommonConfigEntry 22 }


    h3cVoPeerCfgPriority OBJECT-TYPE
        SYNTAX Integer32
        MAX-ACCESS read-create
        STATUS current
        DESCRIPTION
            "This object indicates the priority of this dial peer."
        ::= { h3cVoPeerCommonConfigEntry 23 }


    h3cVoPeerCfgDescription   OBJECT-TYPE
        SYNTAX OCTET STRING
        MAX-ACCESS read-create
        STATUS current
        DESCRIPTION
            "This object indicates the textual description of this
            dial peer."
        ::= { h3cVoPeerCommonConfigEntry 24 }


    h3cVoPeerCfgCallingNumberType   OBJECT-TYPE
        SYNTAX PhoneNumberType
        MAX-ACCESS read-create
        STATUS current
        DESCRIPTION
            "This object indicates the type of calling number
            of this dial peer."
        ::= { h3cVoPeerCommonConfigEntry 25 }


    h3cVoPeerCfgCalledNumberType   OBJECT-TYPE
        SYNTAX PhoneNumberType
        MAX-ACCESS read-create
        STATUS current
        DESCRIPTION
            "This object indicates the type of called number
            of this dial peer."
        ::= { h3cVoPeerCommonConfigEntry 26 }


    h3cVoPeerCfgCallingNumberPlan   OBJECT-TYPE
        SYNTAX PhoneNumberPlan
        MAX-ACCESS read-create
        STATUS current
        DESCRIPTION
            "This object indicates the numbering plan of calling
            number of this dial peer."
        ::= { h3cVoPeerCommonConfigEntry 27 }


    h3cVoPeerCfgCalledNumberPlan   OBJECT-TYPE
        SYNTAX PhoneNumberPlan
        MAX-ACCESS read-create
        STATUS    current
        DESCRIPTION
            "This object indicates the numbering plan of called
            number of this dial peer."
    ::= { h3cVoPeerCommonConfigEntry 28 }


    h3cVoPeerCfgSelectStop   OBJECT-TYPE
        SYNTAX INTEGER
            {
            enable(1),
            disable(2)
            }
        MAX-ACCESS read-create
        STATUS current
        DESCRIPTION
            "This object indicates whether permitting the system
            to allocate alternative entities to establish a phone
            call."
        ::= { h3cVoPeerCommonConfigEntry 29 }


    h3cVoPeerCfgCallingNumSubstRule   OBJECT-TYPE
        SYNTAX Integer32(0..2147483647)
        MAX-ACCESS read-create
        STATUS current
        DESCRIPTION
            "This object indicates number-substitute rule of calling
            number."
        ::= { h3cVoPeerCommonConfigEntry 30 }


    h3cVoPeerCfgCalledNumSubstRule   OBJECT-TYPE
        SYNTAX Integer32(0..2147483647)
        MAX-ACCESS read-create
        STATUS current
        DESCRIPTION
            "This object indicates number-substitute rule of called
            number."
        ::= { h3cVoPeerCommonConfigEntry 31 }


    h3cVoPeerCfgMaxCall   OBJECT-TYPE
        SYNTAX Integer32(0..2147483647)
        MAX-ACCESS read-create
        STATUS current
        DESCRIPTION
            "The object indicates that this dial peer is bound with a tag that
            indicates a maximum call value."
        ::= {  h3cVoPeerCommonConfigEntry 32 }



--====================================================================
--                  h3cVoPOTSPeerConfigTable
--
--====================================================================
    h3cVoPOTSPeerConfigTable OBJECT-TYPE
        SYNTAX SEQUENCE OF H3CVoPOTSPeerConfigEntry
        MAX-ACCESS not-accessible
        STATUS current
        DESCRIPTION
            "This table contains the POTS(Public Switched Telephone Network)
            peer information."
        ::= { h3cVoPeerObjects 2 }


    h3cVoPOTSPeerConfigEntry OBJECT-TYPE
        SYNTAX H3CVoPOTSPeerConfigEntry
        MAX-ACCESS not-accessible
        STATUS current
        DESCRIPTION
            "The entry of h3cVoPOTSPeerConfigTable."
        INDEX { h3cVoPOTSPeerConfigIndex }
        ::= { h3cVoPOTSPeerConfigTable 1 }


    H3CVoPOTSPeerConfigEntry ::=
        SEQUENCE {
            h3cVoPOTSPeerConfigIndex
                Integer32,
            h3cVoPOTSPeerConfigPrefix
                OCTET STRING,
            h3cVoPOTSPeerConfigSubLine
                OCTET STRING,
            h3cVoPOTSPeerConfigSendNum
                Integer32
         }

    h3cVoPOTSPeerConfigIndex OBJECT-TYPE
        SYNTAX Integer32 (1..2147483647)
        MAX-ACCESS not-accessible
        STATUS current
        DESCRIPTION
            "The index of voice pots peer table."
        ::= { h3cVoPOTSPeerConfigEntry 1 }


    h3cVoPOTSPeerConfigPrefix OBJECT-TYPE
        SYNTAX OCTET STRING
        MAX-ACCESS read-write
        STATUS current
        DESCRIPTION
            "This object indicates the prefix which is added to the
            called number."
        ::= { h3cVoPOTSPeerConfigEntry 2 }


    h3cVoPOTSPeerConfigSubLine OBJECT-TYPE
        SYNTAX OCTET STRING
        MAX-ACCESS read-write
        STATUS current
        DESCRIPTION
            "This object indicates the voice subscriber line of
            this dial peer."
        ::= { h3cVoPOTSPeerConfigEntry 3 }


    h3cVoPOTSPeerConfigSendNum OBJECT-TYPE
        SYNTAX Integer32
        MAX-ACCESS read-write
        STATUS current
        DESCRIPTION
            "This object indicates the digit of phone number to be
            sent to the destination."
        ::= { h3cVoPOTSPeerConfigEntry 4 }



--====================================================================
--                  h3cVoVoIPPeerConfigTable
--
--====================================================================
    h3cVoVoIPPeerConfigTable OBJECT-TYPE
        SYNTAX SEQUENCE OF H3CVoVoIPPeerConfigEntry
        MAX-ACCESS not-accessible
        STATUS current
        DESCRIPTION
            "This table contains the voip peer information."
        ::= { h3cVoPeerObjects 3 }


    h3cVoVoIPPeerConfigEntry OBJECT-TYPE
        SYNTAX H3CVoVoIPPeerConfigEntry
        MAX-ACCESS not-accessible
        STATUS current
        DESCRIPTION
            "The entry of h3cVoVoIPPeerConfigTable."
        INDEX { h3cVoVoIPPeerCfgIndex }
        ::= { h3cVoVoIPPeerConfigTable 1 }


    H3CVoVoIPPeerConfigEntry ::=
        SEQUENCE {
            h3cVoVoIPPeerCfgIndex
                Integer32,
            h3cVoVoIPPeerCfgTargetType
                INTEGER,
            h3cVoVoIPPeerCfgTargetAddrType
                InetAddressType,
            h3cVoVoIPPeerCfgTargetAddr
                InetAddress,
            h3cVoVoIPPeerCfgFastStart
                INTEGER,
            h3cVoVoIPPeerCfgTunnel
                INTEGER,
            h3cVoVoIPPeerCfgAreaID
                OCTET STRING,
            h3cVoVoIPPeerCfgSendRing
                INTEGER
         }

    h3cVoVoIPPeerCfgIndex OBJECT-TYPE
        SYNTAX Integer32 (1..2147483647)
        MAX-ACCESS not-accessible
        STATUS current
        DESCRIPTION
            "The index of voice voip peer table."
        ::= { h3cVoVoIPPeerConfigEntry 1 }


    h3cVoVoIPPeerCfgTargetType OBJECT-TYPE
        SYNTAX INTEGER
            {
            unknown(1),
            ras(2),
            h323IpAddress(3),
            sipIpAddress(4),
            sipProxy(5)
            }
        MAX-ACCESS read-write
        STATUS current
        DESCRIPTION
            "This object indicates the type of the session target of this peer."
        ::= { h3cVoVoIPPeerConfigEntry 2 }


    h3cVoVoIPPeerCfgTargetAddrType OBJECT-TYPE
        SYNTAX  InetAddressType
        MAX-ACCESS read-write
        STATUS current
        DESCRIPTION
            "The IP address type of object h3cVoVoIPPeerCfgTargetAddr."
        ::= { h3cVoVoIPPeerConfigEntry 3 }


    h3cVoVoIPPeerCfgTargetAddr OBJECT-TYPE
        SYNTAX InetAddress
        MAX-ACCESS read-write
        STATUS current
        DESCRIPTION
            "This object indicates the target ip address. This object is
            valid when h3cVoVoIPPeerCfgTargetType is h323Ipv4 or sipIpv4."
        ::= { h3cVoVoIPPeerConfigEntry 4 }


    h3cVoVoIPPeerCfgFastStart OBJECT-TYPE
        SYNTAX INTEGER
            {
            enable(1),
            disable(2)
            }
        MAX-ACCESS read-write
        STATUS current
        DESCRIPTION
            "This object indicates whether the fast connection function
            is enabled."
       ::= { h3cVoVoIPPeerConfigEntry 5 }


    h3cVoVoIPPeerCfgTunnel OBJECT-TYPE
        SYNTAX INTEGER
            {
            enable(1),
            disable(2)
            }
        MAX-ACCESS read-write
        STATUS current
        DESCRIPTION
            "This object indicates whether the tunnel function
            is enabled."
        ::= { h3cVoVoIPPeerConfigEntry 6 }


    h3cVoVoIPPeerCfgAreaID OBJECT-TYPE
        SYNTAX OCTET STRING
        MAX-ACCESS read-write
        STATUS current
        DESCRIPTION
            "This object specifies service area-id."
        ::= { h3cVoVoIPPeerConfigEntry 7 }


    h3cVoVoIPPeerCfgSendRing OBJECT-TYPE
        SYNTAX INTEGER
            {
            enable(1),
            disable(2)
            }
        MAX-ACCESS read-write
        STATUS current
        DESCRIPTION
            "This object indicates whether sending ring is enabled."
        ::= { h3cVoVoIPPeerConfigEntry 8 }


--====================================================================
--                  h3cVoPeerDefaultConfigObjects
--
--====================================================================
    h3cVoPeerDefaultConfigObjects OBJECT IDENTIFIER ::= { h3cVoPeerObjects 4 }

    h3cVoPeerDefault1stCodecLevel OBJECT-TYPE
        SYNTAX CodecType
        MAX-ACCESS read-write
        STATUS current
        DESCRIPTION
            "The default priority of the first level CODEC(coding and
            decoding)."
        ::= { h3cVoPeerDefaultConfigObjects 2 }


    h3cVoPeerDefault2ndCodecLevel OBJECT-TYPE
        SYNTAX CodecType
        MAX-ACCESS read-write
        STATUS current
        DESCRIPTION
            "The default priority of the second level CODEC(coding and
            decoding)."
        ::= { h3cVoPeerDefaultConfigObjects 3 }


    h3cVoPeerDefault3rdCodecLevel OBJECT-TYPE
        SYNTAX CodecType
        MAX-ACCESS read-write
        STATUS current
        DESCRIPTION
            "The default priority of the third level CODEC(coding and
            decoding)."
        ::= { h3cVoPeerDefaultConfigObjects 4 }


    h3cVoPeerDefault4thCodecLevel OBJECT-TYPE
        SYNTAX CodecType
        MAX-ACCESS read-write
        STATUS current
        DESCRIPTION
            "The default priority of the fourth level CODEC(coding and
            decoding)."
        ::= { h3cVoPeerDefaultConfigObjects 5 }


    h3cVoPeerDefaultVADOn OBJECT-TYPE
        SYNTAX INTEGER
            {
            enable(1),
            disable(2)
            }
        MAX-ACCESS read-write
        STATUS current
        DESCRIPTION
            "The default value of dial peer's VAD(Voice Activity Detection)."
        ::= { h3cVoPeerDefaultConfigObjects 6 }


    h3cVoPeerDefaultFaxTransLevel OBJECT-TYPE
        SYNTAX Integer32
        MAX-ACCESS read-write
        STATUS current
        DESCRIPTION
            "The default value of dial peer's fax transmit level.
            The unit is db."
        ::= { h3cVoPeerDefaultConfigObjects 7 }


    h3cVoPeerDefaultFaxLocalTrain OBJECT-TYPE
        SYNTAX Integer32
        MAX-ACCESS read-write
        STATUS current
        DESCRIPTION
            "The default value of dial peer's fax local train threshold."
        ::= { h3cVoPeerDefaultConfigObjects 8 }


    h3cVoPeerDefaultFaxProtocol OBJECT-TYPE
        SYNTAX FaxProtocolType
        MAX-ACCESS read-write
        STATUS current
        DESCRIPTION
            "The default value of dial peer's fax protocol."
        ::= { h3cVoPeerDefaultConfigObjects 9 }


    h3cVoPeerDefaultFaxHSRedunNum OBJECT-TYPE
        SYNTAX Integer32 (0..2)
        MAX-ACCESS read-write
        STATUS current
        DESCRIPTION
            "The default value of dial peer's T38 fax protocol high
            redundancy packet number."
        ::= { h3cVoPeerDefaultConfigObjects 10 }


    h3cVoPeerDefaultFaxLSRedunNum OBJECT-TYPE
        SYNTAX Integer32 (0..5)
        MAX-ACCESS read-write
        STATUS current
        DESCRIPTION
            "The default value of dial peer's T38 fax protocol low
            redundancy packet number."
        ::= { h3cVoPeerDefaultConfigObjects 11 }


    h3cVoPeerDefaultFaxBaudrate OBJECT-TYPE
        SYNTAX FaxBaudrateType
        MAX-ACCESS read-write
        STATUS current
        DESCRIPTION
            "The default value of dial peer's fax baudrate."
        ::= { h3cVoPeerDefaultConfigObjects 12 }


    h3cVoPeerDefaultFaxNSF OBJECT-TYPE
        SYNTAX INTEGER
            {
            enable(1),
            disable(2)
            }
        MAX-ACCESS read-write
        STATUS current
        DESCRIPTION
            "The default value of fax NSF(non-standard faculty)."
        ::= { h3cVoPeerDefaultConfigObjects 13 }


    h3cVoPeerDefaultFaxSupportMode OBJECT-TYPE
        SYNTAX FaxSupportModeType
        MAX-ACCESS read-write
        STATUS current
        DESCRIPTION
            "The default mode of fax supported."
        ::= { h3cVoPeerDefaultConfigObjects 14 }


    h3cVoPeerDefaultFaxTrainMode OBJECT-TYPE
        SYNTAX FaxTrainMode
        MAX-ACCESS read-write
        STATUS current
        DESCRIPTION
            "The default value of fax training mode."
        ::= { h3cVoPeerDefaultConfigObjects 15 }


    h3cVoPeerDefaultFaxECM OBJECT-TYPE
        SYNTAX INTEGER
            {
            enable(1),
            disable(2)
            }
        MAX-ACCESS read-write
        STATUS current
        DESCRIPTION
            "The default value of fax ECM(Error Correct Mode) Mode."
        ::= { h3cVoPeerDefaultConfigObjects 16 }


--====================================================================
--                  h3cVoPeerCfgCallerPermitTable
--
--====================================================================
    h3cVoPeerCfgCallerPermitTable OBJECT-TYPE
        SYNTAX SEQUENCE OF H3CVoPeerCfgCallerPermitEntry
        MAX-ACCESS not-accessible
        STATUS current
        DESCRIPTION
            "The table contains permitted caller number in the specific
            voice entity for incoming call."
        ::= { h3cVoPeerObjects 5 }

    h3cVoPeerCfgCallerPermitEntry OBJECT-TYPE
        SYNTAX H3CVoPeerCfgCallerPermitEntry
        MAX-ACCESS not-accessible
        STATUS current
        DESCRIPTION
            "The entry of h3cVoPeerCfgCallerPermitTable."
        INDEX { h3cVoPeerCfgIndex, h3cVoPeerCfgCallerPermitNum }
        ::= { h3cVoPeerCfgCallerPermitTable 1 }

    H3CVoPeerCfgCallerPermitEntry ::=
        SEQUENCE {
            h3cVoPeerCfgCallerPermitNum
                OCTET STRING,
            h3cVoPeerCallerPermitRowStatus
                RowStatus
        }

    h3cVoPeerCfgCallerPermitNum OBJECT-TYPE
        SYNTAX OCTET STRING
        MAX-ACCESS not-accessible
        STATUS current
        DESCRIPTION
            "This object specifies permitted caller number."
        ::= { h3cVoPeerCfgCallerPermitEntry 1 }

    h3cVoPeerCallerPermitRowStatus OBJECT-TYPE
        SYNTAX RowStatus
        MAX-ACCESS read-create
        STATUS current
        DESCRIPTION
            "This object is used to create, delete or modify a row
            in this table."
        ::= { h3cVoPeerCfgCallerPermitEntry 2 }

END
