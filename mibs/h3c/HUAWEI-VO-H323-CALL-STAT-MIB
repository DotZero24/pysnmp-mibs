-- ==========================================================================
-- Copyright (C) 2002 by  HUAWEI TECHNOLOGIES. All rights reserved.
--
-- Description: The purpose of this MIB file is to provide the define of
--              the message statistic information MIB in H225.
-- Reference:
-- Version: V2.0
-- History:
-- V1.0 Initial version
-- V2.0 2004-10-20 Updated by gaolong
--      Re-write whole MIB with SNMPv2-SMI format.
--      Change underscores to hyphens
--      Modify module name from 'HUAWEI-H323-CALL-STATISTIC-MIB' to 'HUAWEI-VO-H323-CALL-STAT-MIB'
-- ==========================================================================
HUAWEI-VO-H323-CALL-STAT-MIB DEFINITIONS ::= BEGIN

	IMPORTS
		OBJECT-TYPE, MODULE-IDENTITY, Counter32
			FROM SNMPv2-SMI
		voice
			FROM HUAWEI-3COM-OID-MIB;


--
-- Node definitions
--

		hwVoiceH323CallStatMIB MODULE-IDENTITY
			LAST-UPDATED "200410200000Z"		-- Oct 20, 2004  GMT
			ORGANIZATION
				"Huawei-3COM Technologies Co., Ltd."
			CONTACT-INFO
				"PLAT Team Huawei 3Com Technologies co.,Ltd.
				Shang-Di Information Industry Base,
				Hai-Dian District Beijing P.R. China
				http://www.huawei-3com.com
				Zip:100085"
			DESCRIPTION
				" "
			REVISION "200404081345Z"		-- April 08, 2004 at 13:45 GMT
			DESCRIPTION
				""
			::= { voice 11 }

		hwVoH323CallStatObjects OBJECT IDENTIFIER ::= { hwVoiceH323CallStatMIB 1 }


		hwVoIPPH225StatObjects OBJECT IDENTIFIER ::= { hwVoH323CallStatObjects 1 }


--  IPP H225 Message Statistic Group
--
-- The objects in this group  store the message statistic information
--  in H225 .
		hwVoSend-Setup OBJECT-TYPE
			SYNTAX Counter32
			MAX-ACCESS read-only
			STATUS current
			DESCRIPTION
				"setup message number send to peer."
			::= { hwVoIPPH225StatObjects 1 }


		hwVoSend-CallProceeding OBJECT-TYPE
			SYNTAX Counter32
			MAX-ACCESS read-only
			STATUS current
			DESCRIPTION
				"CallProceeding message number send to peer."
			::= { hwVoIPPH225StatObjects 2 }


		hwVoSend-Alerting OBJECT-TYPE
			SYNTAX Counter32
			MAX-ACCESS read-only
			STATUS current
			DESCRIPTION
				"Alerting message number send to peer."
			::= { hwVoIPPH225StatObjects 3 }


		hwVoSend-Connect OBJECT-TYPE
			SYNTAX Counter32
			MAX-ACCESS read-only
			STATUS current
			DESCRIPTION
				"Connect message number send to peer."
			::= { hwVoIPPH225StatObjects 4 }


		hwVoSend-ReleaseComplete OBJECT-TYPE
			SYNTAX Counter32
			MAX-ACCESS read-only
			STATUS current
			DESCRIPTION
				"ReleaseComplete message number send to peer."
			::= { hwVoIPPH225StatObjects 5 }


		hwVoSend-FacilityIndUserInput OBJECT-TYPE
			SYNTAX Counter32
			MAX-ACCESS read-only
			STATUS current
			DESCRIPTION
				"FacilityIndUserInput message number send to peer."
			::= { hwVoIPPH225StatObjects 6 }


		hwVoSend-FacilityTCSRequest OBJECT-TYPE
			SYNTAX Counter32
			MAX-ACCESS read-only
			STATUS current
			DESCRIPTION
				"FacilityTCSRequest message number send to peer."
			::= { hwVoIPPH225StatObjects 7 }


		hwVoSend-FacilityTCSAck OBJECT-TYPE
			SYNTAX Counter32
			MAX-ACCESS read-only
			STATUS current
			DESCRIPTION
				"FacilityTCSAck message number send to peer."
			::= { hwVoIPPH225StatObjects 8 }


		hwVoSend-FacilityTCSReject OBJECT-TYPE
			SYNTAX Counter32
			MAX-ACCESS read-only
			STATUS current
			DESCRIPTION
				"FacilityTCSReject message number send to peer."
			::= { hwVoIPPH225StatObjects 9 }


		hwVoSend-FacilityOLCRequest OBJECT-TYPE
			SYNTAX Counter32
			MAX-ACCESS read-only
			STATUS current
			DESCRIPTION
				"FacilityOLCRequest message number send to peer."
			::= { hwVoIPPH225StatObjects 10 }


		hwVoSend-FacilityOLCAck OBJECT-TYPE
			SYNTAX Counter32
			MAX-ACCESS read-only
			STATUS current
			DESCRIPTION
				"FacilityOLCAck message number send to peer."
			::= { hwVoIPPH225StatObjects 11 }


		hwVoSend-FacilityOLCReject OBJECT-TYPE
			SYNTAX Counter32
			MAX-ACCESS read-only
			STATUS current
			DESCRIPTION
				"FacilityOLCReject message number send to peer."
			::= { hwVoIPPH225StatObjects 12 }


		hwVoSend-FacilityMSDRequest OBJECT-TYPE
			SYNTAX Counter32
			MAX-ACCESS read-only
			STATUS current
			DESCRIPTION
				"FacilityMSDRequest message number send to peer."
			::= { hwVoIPPH225StatObjects 13 }


		hwVoSend-FacilityMSDAck OBJECT-TYPE
			SYNTAX Counter32
			MAX-ACCESS read-only
			STATUS current
			DESCRIPTION
				"FacilityMSDAck message number send to peer."
			::= { hwVoIPPH225StatObjects 14 }


		hwVoSend-FacilityMSDReject OBJECT-TYPE
			SYNTAX Counter32
			MAX-ACCESS read-only
			STATUS current
			DESCRIPTION
				"FacilityMSDReject message number send to peer."
			::= { hwVoIPPH225StatObjects 15 }


		hwVoSend-FacilityCLCRequest OBJECT-TYPE
			SYNTAX Counter32
			MAX-ACCESS read-only
			STATUS current
			DESCRIPTION
				"FacilityCLCRequest message number send to peer."
			::= { hwVoIPPH225StatObjects 16 }


		hwVoSend-FacilityCLCAck OBJECT-TYPE
			SYNTAX Counter32
			MAX-ACCESS read-only
			STATUS current
			DESCRIPTION
				"FacilityCLCAck message number send to peer."
			::= { hwVoIPPH225StatObjects 17 }


		hwVoSend-FacilityStartH245 OBJECT-TYPE
			SYNTAX Counter32
			MAX-ACCESS read-only
			STATUS current
			DESCRIPTION
				"FacilityStartH245 message number send to peer."
			::= { hwVoIPPH225StatObjects 18 }


		hwVoSend-ErrorH225Msg OBJECT-TYPE
			SYNTAX Counter32
			MAX-ACCESS read-only
			STATUS current
			DESCRIPTION
				"Error 225 message number send to peer."
			::= { hwVoIPPH225StatObjects 19 }


		hwVoRecv-Setup OBJECT-TYPE
			SYNTAX Counter32
			MAX-ACCESS read-only
			STATUS current
			DESCRIPTION
				"Setup message number receive from peer."
			::= { hwVoIPPH225StatObjects 20 }


		hwVoRecv-CallProceeding OBJECT-TYPE
			SYNTAX Counter32
			MAX-ACCESS read-only
			STATUS current
			DESCRIPTION
				"CallProceeding message number receive from peer."
			::= { hwVoIPPH225StatObjects 21 }


		hwVoRecv-Alerting OBJECT-TYPE
			SYNTAX Counter32
			MAX-ACCESS read-only
			STATUS current
			DESCRIPTION
				"Alerting message number receive from peer."
			::= { hwVoIPPH225StatObjects 22 }


		hwVoRecv-Connect OBJECT-TYPE
			SYNTAX Counter32
			MAX-ACCESS read-only
			STATUS current
			DESCRIPTION
				"Connect message number receive from peer."
			::= { hwVoIPPH225StatObjects 23 }


		hwVoRecv-ReleaseComplete OBJECT-TYPE
			SYNTAX Counter32
			MAX-ACCESS read-only
			STATUS current
			DESCRIPTION
				"ReleaseComplete message number receive from peer."
			::= { hwVoIPPH225StatObjects 24 }


		hwVoRecv-Progress OBJECT-TYPE
			SYNTAX Counter32
			MAX-ACCESS read-only
			STATUS current
			DESCRIPTION
				"Progress message number receive from peer."
			::= { hwVoIPPH225StatObjects 25 }


		hwVoRecv-FacilityTCSRequest OBJECT-TYPE
			SYNTAX Counter32
			MAX-ACCESS read-only
			STATUS current
			DESCRIPTION
				"FacilityTCSRequest message number receive from peer."
			::= { hwVoIPPH225StatObjects 26 }


		hwVoRecv-FacilityTCSAck OBJECT-TYPE
			SYNTAX Counter32
			MAX-ACCESS read-only
			STATUS current
			DESCRIPTION
				"FacilityTCSAck message number receive from peer."
			::= { hwVoIPPH225StatObjects 27 }


		hwVoRecv-FacilityTCSReject OBJECT-TYPE
			SYNTAX Counter32
			MAX-ACCESS read-only
			STATUS current
			DESCRIPTION
				"FacilityTCSReject message number receive from peer."
			::= { hwVoIPPH225StatObjects 28 }


		hwVoRecv-FacilityOLCRequest OBJECT-TYPE
			SYNTAX Counter32
			MAX-ACCESS read-only
			STATUS current
			DESCRIPTION
				"FacilityOLCRequest message number receive from peer."
			::= { hwVoIPPH225StatObjects 29 }


		hwVoRecv-FacilityOLCAck OBJECT-TYPE
			SYNTAX Counter32
			MAX-ACCESS read-only
			STATUS current
			DESCRIPTION
				"FacilityOLCAck message number receive from peer."
			::= { hwVoIPPH225StatObjects 30 }


		hwVoRecv-FacilityOLCReject OBJECT-TYPE
			SYNTAX Counter32
			MAX-ACCESS read-only
			STATUS current
			DESCRIPTION
				"FacilityOLCReject message number receive from peer."
			::= { hwVoIPPH225StatObjects 31 }


		hwVoRecv-FacilityMSDRequest OBJECT-TYPE
			SYNTAX Counter32
			MAX-ACCESS read-only
			STATUS current
			DESCRIPTION
				"FacilityMSDRequest message number receive from peer."
			::= { hwVoIPPH225StatObjects 32 }


		hwVoRecv-FacilityMSDAck OBJECT-TYPE
			SYNTAX Counter32
			MAX-ACCESS read-only
			STATUS current
			DESCRIPTION
				"FacilityMSDAck message number receive from peer."
			::= { hwVoIPPH225StatObjects 33 }


		hwVoRecv-FacilityMSDReject OBJECT-TYPE
			SYNTAX Counter32
			MAX-ACCESS read-only
			STATUS current
			DESCRIPTION
				"FacilityMSDReject message number receive from peer."
			::= { hwVoIPPH225StatObjects 34 }


		hwVoRecv-FacilityCLCRequest OBJECT-TYPE
			SYNTAX Counter32
			MAX-ACCESS read-only
			STATUS current
			DESCRIPTION
				"FacilityCLCRequest message number receive from peer."
			::= { hwVoIPPH225StatObjects 35 }


		hwVoRecv-FacilityCLCAck OBJECT-TYPE
			SYNTAX Counter32
			MAX-ACCESS read-only
			STATUS current
			DESCRIPTION
				"FacilityCLCAck message number receive from peer."
			::= { hwVoIPPH225StatObjects 36 }


		hwVoRecv-UnknownH225Msg OBJECT-TYPE
			SYNTAX Counter32
			MAX-ACCESS read-only
			STATUS current
			DESCRIPTION
				"Unknow 225 message number receive from peer."
			::= { hwVoIPPH225StatObjects 37 }


		hwVoIPPH245StatObjects OBJECT IDENTIFIER ::= { hwVoH323CallStatObjects 2 }


-- IPP H245 Message Statistic Group
--
-- The objects in this group  store the message statistic information
--  in H245 .
		hwVoSend-TCSRequest OBJECT-TYPE
			SYNTAX Counter32
			MAX-ACCESS read-only
			STATUS current
			DESCRIPTION
				"TCSRequest message number send to peer."
			::= { hwVoIPPH245StatObjects 1 }


		hwVoSend-TCSAck OBJECT-TYPE
			SYNTAX Counter32
			MAX-ACCESS read-only
			STATUS current
			DESCRIPTION
				"TCSAck message number send to peer."
			::= { hwVoIPPH245StatObjects 2 }


		hwVoSend-TCSReject OBJECT-TYPE
			SYNTAX Counter32
			MAX-ACCESS read-only
			STATUS current
			DESCRIPTION
				"TCSReject message number send to peer."
			::= { hwVoIPPH245StatObjects 3 }


		hwVoSend-MSDRequest OBJECT-TYPE
			SYNTAX Counter32
			MAX-ACCESS read-only
			STATUS current
			DESCRIPTION
				"MSDRequest message number send to peer."
			::= { hwVoIPPH245StatObjects 4 }


		hwVoSend-MSDAck OBJECT-TYPE
			SYNTAX Counter32
			MAX-ACCESS read-only
			STATUS current
			DESCRIPTION
				"MSDAck message number send to peer."
			::= { hwVoIPPH245StatObjects 5 }


		hwVoSend-MSDReject OBJECT-TYPE
			SYNTAX Counter32
			MAX-ACCESS read-only
			STATUS current
			DESCRIPTION
				"MSDReject message number send to peer."
			::= { hwVoIPPH245StatObjects 6 }


		hwVoSend-OLCRequest OBJECT-TYPE
			SYNTAX Counter32
			MAX-ACCESS read-only
			STATUS current
			DESCRIPTION
				"OLCRequest message number send to peer."
			::= { hwVoIPPH245StatObjects 7 }


		hwVoSend-OLCAck OBJECT-TYPE
			SYNTAX Counter32
			MAX-ACCESS read-only
			STATUS current
			DESCRIPTION
				"OLCAck message number send to peer."
			::= { hwVoIPPH245StatObjects 8 }


		hwVoSend-OLCReject OBJECT-TYPE
			SYNTAX Counter32
			MAX-ACCESS read-only
			STATUS current
			DESCRIPTION
				"OLCReject message number send to peer."
			::= { hwVoIPPH245StatObjects 9 }


		hwVoSend-CLCRequest OBJECT-TYPE
			SYNTAX Counter32
			MAX-ACCESS read-only
			STATUS current
			DESCRIPTION
				"CLCRequest message number send to peer."
			::= { hwVoIPPH245StatObjects 10 }


		hwVoSend-CLCAck OBJECT-TYPE
			SYNTAX Counter32
			MAX-ACCESS read-only
			STATUS current
			DESCRIPTION
				"CLCAck message number send to peer."
			::= { hwVoIPPH245StatObjects 11 }


		hwVoSend-UserInput OBJECT-TYPE
			SYNTAX Counter32
			MAX-ACCESS read-only
			STATUS current
			DESCRIPTION
				"UserInput message number send to peer."
			::= { hwVoIPPH245StatObjects 12 }


		hwVoSend-ErrorH245Msg OBJECT-TYPE
			SYNTAX Counter32
			MAX-ACCESS read-only
			STATUS current
			DESCRIPTION
				"Error 245 message number send to peer."
			::= { hwVoIPPH245StatObjects 13 }


		hwVoRecv-TCSRequest OBJECT-TYPE
			SYNTAX Counter32
			MAX-ACCESS read-only
			STATUS current
			DESCRIPTION
				"TCSRequest message number receive from peer."
			::= { hwVoIPPH245StatObjects 14 }


		hwVoRecv-TCSAck OBJECT-TYPE
			SYNTAX Counter32
			MAX-ACCESS read-only
			STATUS current
			DESCRIPTION
				"TCSAck message number receive from peer."
			::= { hwVoIPPH245StatObjects 15 }


		hwVoRecv-TCSReject OBJECT-TYPE
			SYNTAX Counter32
			MAX-ACCESS read-only
			STATUS current
			DESCRIPTION
				"TCSReject message number receive from peer."
			::= { hwVoIPPH245StatObjects 16 }


		hwVoRecv-MSDRequest OBJECT-TYPE
			SYNTAX Counter32
			MAX-ACCESS read-only
			STATUS current
			DESCRIPTION
				"MSDRequest message number receive from peer."
			::= { hwVoIPPH245StatObjects 17 }


		hwVoRecv-MSDAck OBJECT-TYPE
			SYNTAX Counter32
			MAX-ACCESS read-only
			STATUS current
			DESCRIPTION
				"MSDAck message number receive from peer."
			::= { hwVoIPPH245StatObjects 18 }


		hwVoRecv-MSDReject OBJECT-TYPE
			SYNTAX Counter32
			MAX-ACCESS read-only
			STATUS current
			DESCRIPTION
				"MSDReject message number receive from peer."
			::= { hwVoIPPH245StatObjects 19 }


		hwVoRecv-OLCRequest OBJECT-TYPE
			SYNTAX Counter32
			MAX-ACCESS read-only
			STATUS current
			DESCRIPTION
				"OLCRequest message number receive from peer."
			::= { hwVoIPPH245StatObjects 20 }


		hwVoRecv-OLCAck OBJECT-TYPE
			SYNTAX Counter32
			MAX-ACCESS read-only
			STATUS current
			DESCRIPTION
				"OLCAck message number receive from peer."
			::= { hwVoIPPH245StatObjects 21 }


		hwVoRecv-OLCReject OBJECT-TYPE
			SYNTAX Counter32
			MAX-ACCESS read-only
			STATUS current
			DESCRIPTION
				"OLCReject message number receive from peer."
			::= { hwVoIPPH245StatObjects 22 }


		hwVoRecv-CLCRequest OBJECT-TYPE
			SYNTAX Counter32
			MAX-ACCESS read-only
			STATUS current
			DESCRIPTION
				"CLCRequest message number receive from peer."
			::= { hwVoIPPH245StatObjects 23 }


		hwVoRecv-CLCAck OBJECT-TYPE
			SYNTAX Counter32
			MAX-ACCESS read-only
			STATUS current
			DESCRIPTION
				"CLCAck message number receive from peer."
			::= { hwVoIPPH245StatObjects 24 }


		hwVoRecv-UserInput OBJECT-TYPE
			SYNTAX Counter32
			MAX-ACCESS read-only
			STATUS current
			DESCRIPTION
				"UserInput message number receive from peer."
			::= { hwVoIPPH245StatObjects 25 }


		hwVoRecv-UnknownH245Msg OBJECT-TYPE
			SYNTAX Counter32
			MAX-ACCESS read-only
			STATUS current
			DESCRIPTION
				"Unknow 245 message number receive from peer."
			::= { hwVoIPPH245StatObjects 26 }


		hwVoIPPRASStatObjects OBJECT IDENTIFIER ::= { hwVoH323CallStatObjects 3 }


-- IPP RAS Message Statistic Group
--
-- The objects in this group  store the message statistic information
--  in RAS .
		hwVoSend-GRQ OBJECT-TYPE
			SYNTAX Counter32
			MAX-ACCESS read-only
			STATUS current
			DESCRIPTION
				"GRQ message number send to peer."
			::= { hwVoIPPRASStatObjects 1 }


		hwVoSend-RRQ OBJECT-TYPE
			SYNTAX Counter32
			MAX-ACCESS read-only
			STATUS current
			DESCRIPTION
				"RRQ message number send to peer."
			::= { hwVoIPPRASStatObjects 2 }


		hwVoSend-ARQ OBJECT-TYPE
			SYNTAX Counter32
			MAX-ACCESS read-only
			STATUS current
			DESCRIPTION
				"ARQ message number send to peer."
			::= { hwVoIPPRASStatObjects 3 }


		hwVoSend-BRQ OBJECT-TYPE
			SYNTAX Counter32
			MAX-ACCESS read-only
			STATUS current
			DESCRIPTION
				"BRQ message number send to peer."
			::= { hwVoIPPRASStatObjects 4 }


		hwVoSend-DRQ OBJECT-TYPE
			SYNTAX Counter32
			MAX-ACCESS read-only
			STATUS current
			DESCRIPTION
				"DRQ message number send to peer."
			::= { hwVoIPPRASStatObjects 5 }


		hwVoSend-URQ OBJECT-TYPE
			SYNTAX Counter32
			MAX-ACCESS read-only
			STATUS current
			DESCRIPTION
				"URQ message number send to peer."
			::= { hwVoIPPRASStatObjects 6 }


		hwVoSend-UCF OBJECT-TYPE
			SYNTAX Counter32
			MAX-ACCESS read-only
			STATUS current
			DESCRIPTION
				"UCF message number send to peer."
			::= { hwVoIPPRASStatObjects 7 }


		hwVoSend-IRR OBJECT-TYPE
			SYNTAX Counter32
			MAX-ACCESS read-only
			STATUS current
			DESCRIPTION
				"IRR message number send to peer."
			::= { hwVoIPPRASStatObjects 8 }


		hwVoSend-ErrorRASMsg OBJECT-TYPE
			SYNTAX Counter32
			MAX-ACCESS read-only
			STATUS current
			DESCRIPTION
				"Error RAS message number send to peer."
			::= { hwVoIPPRASStatObjects 9 }


		hwVoRecv-GCF OBJECT-TYPE
			SYNTAX Counter32
			MAX-ACCESS read-only
			STATUS current
			DESCRIPTION
				"GCF message number receive from peer."
			::= { hwVoIPPRASStatObjects 10 }


		hwVoRecv-RCF OBJECT-TYPE
			SYNTAX Counter32
			MAX-ACCESS read-only
			STATUS current
			DESCRIPTION
				"RCF message number receive from peer."
			::= { hwVoIPPRASStatObjects 11 }


		hwVoRecv-ACF OBJECT-TYPE
			SYNTAX Counter32
			MAX-ACCESS read-only
			STATUS current
			DESCRIPTION
				"ACF message number receive from peer."
			::= { hwVoIPPRASStatObjects 12 }


		hwVoRecv-BCF OBJECT-TYPE
			SYNTAX Counter32
			MAX-ACCESS read-only
			STATUS current
			DESCRIPTION
				"BCF message number receive from peer."
			::= { hwVoIPPRASStatObjects 13 }


		hwVoRecv-DCF OBJECT-TYPE
			SYNTAX Counter32
			MAX-ACCESS read-only
			STATUS current
			DESCRIPTION
				"DCF message number receive from peer."
			::= { hwVoIPPRASStatObjects 14 }


		hwVoRecv-GRJ OBJECT-TYPE
			SYNTAX Counter32
			MAX-ACCESS read-only
			STATUS current
			DESCRIPTION
				"GRJ message number receive from peer."
			::= { hwVoIPPRASStatObjects 15 }


		hwVoRecv-RRJ OBJECT-TYPE
			SYNTAX Counter32
			MAX-ACCESS read-only
			STATUS current
			DESCRIPTION
				"RRJ message number receive from peer."
			::= { hwVoIPPRASStatObjects 16 }


		hwVoRecv-ARJ OBJECT-TYPE
			SYNTAX Counter32
			MAX-ACCESS read-only
			STATUS current
			DESCRIPTION
				"ARJ message number receive from peer."
			::= { hwVoIPPRASStatObjects 17 }


		hwVoRecv-BRJ OBJECT-TYPE
			SYNTAX Counter32
			MAX-ACCESS read-only
			STATUS current
			DESCRIPTION
				"BRJ message number receive from peer."
			::= { hwVoIPPRASStatObjects 18 }


		hwVoRecv-DRJ OBJECT-TYPE
			SYNTAX Counter32
			MAX-ACCESS read-only
			STATUS current
			DESCRIPTION
				"DRJ message number receive from peer."
			::= { hwVoIPPRASStatObjects 19 }


		hwVoRecv-URQ OBJECT-TYPE
			SYNTAX Counter32
			MAX-ACCESS read-only
			STATUS current
			DESCRIPTION
				"URQ message number receive from peer."
			::= { hwVoIPPRASStatObjects 20 }


		hwVoRecv-UCF OBJECT-TYPE
			SYNTAX Counter32
			MAX-ACCESS read-only
			STATUS current
			DESCRIPTION
				"UCF message number receive from peer."
			::= { hwVoIPPRASStatObjects 21 }


		hwVoRecv-URJ OBJECT-TYPE
			SYNTAX Counter32
			MAX-ACCESS read-only
			STATUS current
			DESCRIPTION
				"URJ message number receive from peer."
			::= { hwVoIPPRASStatObjects 22 }


		hwVoRecv-IRQ OBJECT-TYPE
			SYNTAX Counter32
			MAX-ACCESS read-only
			STATUS current
			DESCRIPTION
				"IRQ message number receive from peer."
			::= { hwVoIPPRASStatObjects 23 }


		hwVoRecv-UnknownRASMsg OBJECT-TYPE
			SYNTAX Counter32
			MAX-ACCESS read-only
			STATUS current
			DESCRIPTION
				"Unknow ras message number receive from peer."
			::= { hwVoIPPRASStatObjects 24 }



	END
