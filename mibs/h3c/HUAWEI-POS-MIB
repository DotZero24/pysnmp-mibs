-- ==========================================================================
-- Copyright (C) 2004 by  H3C TECHNOLOGIES. All rights reserved.
--
-- Description: The purpose of this MIB file is to provide the define of
--              POS MIB of serial router.
-- Reference:
-- Version: V1.1
-- History:
-- V1.0  The initial version, created by wangshijin 2004-07-02
-- V1.1  Refined this MIB which is completely conform with SMIv2.
--       Make the following changes:
--       1. Add MODULE-IDENTITY
--       2. Remove default value for posAppHostIP, posAppSourceIp, posAppRecvPacCounter
--       	posAppErrPacCouter, posAppDistrErrCounter, posAppBuffedCounter,
--       	posAppDiscardedCounter, posPosRecvPacCounter, posPosErrPacCounter,
--       	posPosMapErrCounter, posPosBuffedCounter, posPosDiscardedCounter
--       	posFCMConnectFailCounter and posFCMTimeoutCounter because their syntax is Counter32
--       3. Modify posPosIfIndex, posAsyAppIfIndex, posFCMIfIndex, posPadIfIndex of INTEGER range
--       4. Modify posPosId of INTEGER range
--       5. Add a new column object posPosInterType under posInterTable table	by caizibin  2004-10-11
--       6. Add an enumeration called pad(3) under the posAppConnectMode  by caizibin  2004-10-11
--       7. Add a new column object posAppX121Addr under posAppTable table	by caizibin  2004-10-11
--	 	 8. Add new object posPadWaitTime, posPadIdleTimeout, posPadPacType, posPadEnable,
--	    posPadCheckSChar by caizibin  2004-10-11
--       9.Refine some object's descrption to make them more readable
--	     10.Add posPadTable table
-- ==========================================================================
HUAWEI-POS-MIB    DEFINITIONS ::= BEGIN

IMPORTS
	RowStatus
        FROM SNMPv2-TC
    OBJECT-TYPE, NOTIFICATION-TYPE, MODULE-IDENTITY, IpAddress, Counter32
        FROM SNMPv2-SMI
    huawei,mlsr
		FROM HUAWEI-3COM-OID-MIB;

pos     MODULE-IDENTITY
        LAST-UPDATED "200410150000Z"
        ORGANIZATION
            "Hangzhou H3C Tech. Co., Ltd."
        CONTACT-INFO
            "Platform Team Hangzhou H3C Tech. Co., Ltd.
            Hai-Dian District Beijing P.R. China
            http://www.h3c.com
            Zip:100085
            "
        DESCRIPTION
                "The POS MIB module is used to manage
                 POS-Access. "
        REVISION	"200410120000Z"
        DESCRIPTION
                "The lastest version of this MIB module."
        REVISION	"200407020000Z"
        DESCRIPTION
                "The initial version of this MIB module."

		::= { mlsr 8 }


posAppTable   OBJECT-TYPE
   SYNTAX    	SEQUENCE OF POSAppEntry
   MAX-ACCESS   not-accessible
   STATUS    	current
   DESCRIPTION
             "The table to get and set the application informatin."
   ::= { pos 1 }

posAppEntry   OBJECT-TYPE
   SYNTAX    	POSAppEntry
   MAX-ACCESS   not-accessible
   STATUS    	current
   DESCRIPTION
             "The content of posAppTable."
   INDEX     { posAppId }
   ::= { posAppTable 1 }


POSAppEntry ::= SEQUENCE {
   posAppId
        INTEGER,
   posAppConnectMode
        INTEGER,
   posAppState
        INTEGER,
   posAppIfIndex
        INTEGER,
   posAppHostIP
        IpAddress,
   posAppPort
        INTEGER,
   posAppSourceIp
        IpAddress,
   posAppRecvPacCounter
        Counter32,
   posAppErrPacCounter
        Counter32,
   posAppDistrErrCounter
        Counter32,
   posAppBuffedCounter
        Counter32,
   posAppDiscardedCounter
        Counter32,
   posAppDebug
        INTEGER,
   posAppRowStatus
        RowStatus,
   posAppX121Addr
   	OCTET STRING
   }

posAppId   OBJECT-TYPE
   SYNTAX    	INTEGER(0..31)
   MAX-ACCESS   read-only
   STATUS    	current
   DESCRIPTION
             "The ID of application."
   ::= { posAppEntry 1 }

posAppConnectMode   OBJECT-TYPE
   SYNTAX    	INTEGER{
                        tcp(1),
                        flow(2),
                        pad(3)
                }
   MAX-ACCESS   read-create
   STATUS    	current
   DESCRIPTION
             "The connect mode of application.

             If the router and unix are connected by TCP protocol,
             the connect mode of application is tcp.

             If the router and unix are connected by async interface,
             the connect mode of application is flow.

             If the router is used as POSPAD device, the connect mode of application
             is pad."
   ::= { posAppEntry 2 }

posAppState   OBJECT-TYPE
   SYNTAX    	INTEGER{
                	noset(1),
                	down(2),
                	up(3),
                	ok(4),
                	kept(5),
                	linking(6),
                	linked(7)
             	}
   MAX-ACCESS   read-only
   STATUS    	current
   DESCRIPTION
             "The state of application."
   DEFVAL  {1}
   ::= { posAppEntry 3 }

posAppIfIndex   OBJECT-TYPE
   SYNTAX    	INTEGER(0..2147483647)
   MAX-ACCESS   read-create
   STATUS    	current
   DESCRIPTION
             "The interface index of the application
             whose connect mode is flow or pad."
   REFERENCE  "ifIndex"
   ::= { posAppEntry 4 }

posAppHostIP   OBJECT-TYPE
   SYNTAX    	IpAddress
   MAX-ACCESS   read-create
   STATUS    	current
   DESCRIPTION
             "The destination IP Address of application.
             Used for the application whose connect mode is tcp."
   ::= { posAppEntry 5 }

posAppPort   OBJECT-TYPE
   SYNTAX    	INTEGER(0..65535)
   MAX-ACCESS   read-create
   STATUS    	current
   DESCRIPTION
             "The destination port of application.
             Used for the application whose connect mode is tcp."
   ::= { posAppEntry 6 }

posAppSourceIp   OBJECT-TYPE
   SYNTAX    	IpAddress
   MAX-ACCESS   read-create
   STATUS    	current
   DESCRIPTION
             "The source IP Address of application.
             Used for the application whose connect mode is tcp."
   ::= { posAppEntry 7 }

posAppRecvPacCounter   OBJECT-TYPE
   SYNTAX    	Counter32
   MAX-ACCESS   read-only
   STATUS    	current
   DESCRIPTION
             "The number of packets received by the application."
   DEFVAL  {0}
   ::= { posAppEntry 8 }

posAppErrPacCounter   OBJECT-TYPE
   SYNTAX    	Counter32
   MAX-ACCESS   read-only
   STATUS    	current
   DESCRIPTION
             "The number of error packets received by the application."
   DEFVAL  {0}
   ::= { posAppEntry 9 }

posAppDistrErrCounter   OBJECT-TYPE
   SYNTAX    	Counter32
   MAX-ACCESS   read-only
   STATUS    	current
   DESCRIPTION
             "The number of packets that could not be sent to POS."
   DEFVAL  {0}
   ::= { posAppEntry 10 }

posAppBuffedCounter   OBJECT-TYPE
   SYNTAX    	Counter32
   MAX-ACCESS   read-only
   STATUS    	current
   DESCRIPTION
             "The number of packets stored in the buffer of application."
   DEFVAL  {0}
   ::= { posAppEntry 11 }

posAppDiscardedCounter   OBJECT-TYPE
   SYNTAX    	Counter32
   MAX-ACCESS   read-only
   STATUS    	current
   DESCRIPTION
             "The number of packets discarded by the application."
   DEFVAL  {0}
   ::= { posAppEntry 12 }

posAppDebug   OBJECT-TYPE
   SYNTAX    	INTEGER{
                        close(1),
                        open(2)
                }
   MAX-ACCESS   read-create
   STATUS    	current
   DESCRIPTION
             "The debugging switch of application."
   ::= { posAppEntry 13 }

posAppRowStatus   OBJECT-TYPE
   SYNTAX    	RowStatus
   MAX-ACCESS   read-create
   STATUS    	current
   DESCRIPTION
             "The status of row. Only support active, CreateAndGo and destroy."
   ::= { posAppEntry 14 }

posAppX121Addr OBJECT-TYPE
   SYNTAX    	OCTET STRING (SIZE(1..15))
   MAX-ACCESS   read-create
   STATUS    	current
   DESCRIPTION
             "The destination X121 Address of application which is
             an octet string made up of numeric.
             Used for the application whose connect mode is pad."
   ::= { posAppEntry 15 }

posInterTable   OBJECT-TYPE
   SYNTAX    	SEQUENCE OF POSInterEntry
   MAX-ACCESS   not-accessible
   STATUS    	current
   DESCRIPTION
             "The table to get and set the POS-Interface informatin."
   ::= { pos 2 }

posInterEntry   OBJECT-TYPE
   SYNTAX    	POSInterEntry
   MAX-ACCESS   not-accessible
   STATUS    	current
   DESCRIPTION
             "The content of posInterTable."
   INDEX     { posPosId }
   ::= { posInterTable 1 }


POSInterEntry ::= SEQUENCE {
   posPosId
        INTEGER,
   posPosIfIndex
        INTEGER,
   posPosConnectState
        INTEGER,
   posPosRecvPacCounter
        Counter32,
   posPosErrPacCounter
        Counter32,
   posPosMapErrCounter
        Counter32,
   posPosBuffedCounter
        Counter32,
   posPosDiscardedCounter
        Counter32,
   posPosInterDebug
        INTEGER,
   posPosInterRowStatus
        RowStatus,
   posPosInterType
   	INTEGER
   }

posPosId   OBJECT-TYPE
   SYNTAX    	INTEGER(0..255)
   MAX-ACCESS   read-only
   STATUS    	current
   DESCRIPTION
             "The ID of the POS-Interface."
   ::= { posInterEntry 1 }

posPosIfIndex   OBJECT-TYPE
   SYNTAX    	INTEGER(1..2147483647)
   MAX-ACCESS   read-create
   STATUS    	current
   DESCRIPTION
             "The interface index of the POS-Interface whose type is fcm, asy or pad-client."
   REFERENCE  "ifIndex"
   ::= { posInterEntry 2 }

posPosConnectState   OBJECT-TYPE
   SYNTAX    	INTEGER{
                        noset(1),
                        down(2),
                        up(3),
                        ok(4)
                }
   MAX-ACCESS   read-only
   STATUS    	current
   DESCRIPTION
             "The state of the POS-Interface."
   DEFVAL  {1}
   ::= { posInterEntry 3 }

posPosRecvPacCounter   OBJECT-TYPE
   SYNTAX    	Counter32
   MAX-ACCESS   read-only
   STATUS    	current
   DESCRIPTION
             "The number of packets received by the POS-Interface."
   DEFVAL  {0}
   ::= { posInterEntry 4 }

posPosErrPacCounter   OBJECT-TYPE
   SYNTAX    	Counter32
   MAX-ACCESS   read-only
   STATUS    	current
   DESCRIPTION
             "The number of error packets received by the POS-Interface."
   DEFVAL  {0}
   ::= { posInterEntry 5 }

posPosMapErrCounter   OBJECT-TYPE
   SYNTAX    	Counter32
   MAX-ACCESS   read-only
   STATUS    	current
   DESCRIPTION
             "The number of packets that could not be sent to application."
   DEFVAL  {0}
   ::= { posInterEntry 6 }

posPosBuffedCounter   OBJECT-TYPE
   SYNTAX    	Counter32
   MAX-ACCESS   read-only
   STATUS    	current
   DESCRIPTION
             "The number of packets stored in the buffer of the POS-Interface."
   DEFVAL  {0}
   ::= { posInterEntry 7 }

posPosDiscardedCounter   OBJECT-TYPE
   SYNTAX    	Counter32
   MAX-ACCESS   read-only
   STATUS    	current
   DESCRIPTION
             "The number of packets discarded by the POS-Interface."
   DEFVAL  {0}
   ::= { posInterEntry 8 }

posPosInterDebug   OBJECT-TYPE
   SYNTAX    	INTEGER{
                        close(1),
                        open(2)
                }
   MAX-ACCESS   read-create
   STATUS    	current
   DESCRIPTION
             "The debugging switch of the POS-Interface."
   ::= { posInterEntry 9 }

posPosInterRowStatus   OBJECT-TYPE
   SYNTAX    	RowStatus
   MAX-ACCESS   read-create
   STATUS    	current
   DESCRIPTION
             "The status of row. Only support active, CreateAndGo and destroy."
   ::= { posInterEntry 10 }

posPosInterType   OBJECT-TYPE
   SYNTAX    	INTEGER{
                        fcm(1),
                        asy(2),
                        pad-client(3),
                        pad-server(4)
                }
   MAX-ACCESS   read-create
   STATUS    	current
   DESCRIPTION
             "The type of interface.

             The POS-Access mode has four types: FCM-Access, ASYNC-Access,
             simulating POSPAD device, POSPAD-Access.

             FCM-Access mode means POS and router are connected through PSTN.
             In this case, posPosInterType should be set to fcm.

             ASYNC-Access mode means POS and router are connected by asynchronous cable.
             In this case, posPosInterType should be set to asy.

             Simulating POSPAD device means router connects POS through asynchronous cable
             and connects another router whose connect mode is pad-server through X.25 network.
             In this case, posPosInterType should be set to pad-client.

             POSPAD-Access mode means router connects POSPAD device through X.25 network.
             In this case, posPosInterType is pad-server. The posPosInterType
             can't be set to pad-server. It is autogenerated when POSPAD device initiates
             a connection to the router.
             "
   DEFVAL  {1}
   ::= { posInterEntry 11 }

posMapTable   OBJECT-TYPE
   SYNTAX    	SEQUENCE OF POSMapEntry
   MAX-ACCESS   not-accessible
   STATUS    	current
   DESCRIPTION
		"The table to get and set the informatin of mapping relation of destination and application."
   ::= { pos 3 }

posMapEntry   OBJECT-TYPE
   SYNTAX    	POSMapEntry
   MAX-ACCESS   not-accessible
   STATUS    	current
   DESCRIPTION
             "The content of posMapTable."
   INDEX     { posMapDes }
   ::= { posMapTable 1 }


POSMapEntry ::= SEQUENCE {
   posMapDes
        INTEGER,
   posMapAppNumber
        INTEGER,
   posMapRowStatus
        RowStatus
   }

posMapDes   OBJECT-TYPE
   SYNTAX    	INTEGER(-1..65535)
   MAX-ACCESS   read-create
   STATUS    	current
   DESCRIPTION
             "The destination code of the mapping item.
             If the value is -1, it is the default item of mapping relation."
   ::= { posMapEntry 1 }

posMapAppNumber   OBJECT-TYPE
   SYNTAX    	INTEGER(0..31)
   MAX-ACCESS   read-create
   STATUS    	current
   DESCRIPTION
             "The application index of the mapping item."

   ::= { posMapEntry 2 }

posMapRowStatus   OBJECT-TYPE
   SYNTAX    	RowStatus
   MAX-ACCESS   read-create
   STATUS    	current
   DESCRIPTION
             "The status of row. Only support active, CreateAndGo and destroy."
   ::= { posMapEntry 3 }

posAsyAppTable   OBJECT-TYPE
   SYNTAX    	SEQUENCE OF POSAsyAppEntry
   MAX-ACCESS   not-accessible
   STATUS    	current
   DESCRIPTION
             "The table to get and set the asynchronous-application interface information."
   ::= { pos 4 }

posAsyAppEntry   OBJECT-TYPE
   SYNTAX    	POSAsyAppEntry
   MAX-ACCESS   not-accessible
   STATUS    	current
   DESCRIPTION
             "The content of posAsyAppTable."
   INDEX     { posAsyAppIfIndex }
   ::= { posAsyAppTable 1 }

POSAsyAppEntry ::= SEQUENCE {
   posAsyAppIfIndex
        INTEGER,
   posAsyAppRowStatus
        RowStatus
   }

posAsyAppIfIndex   OBJECT-TYPE
   SYNTAX    	INTEGER(0..2147483647)
   MAX-ACCESS   read-only
   STATUS    	current
   DESCRIPTION
             "The interface index of asynchronous-application."
   REFERENCE  "ifIndex"
   ::= { posAsyAppEntry 1 }

posAsyAppRowStatus   OBJECT-TYPE
   SYNTAX    	RowStatus
   MAX-ACCESS   read-create
   STATUS    	current
   DESCRIPTION
             "The status of row. Only support active, CreateAndGo and destroy."
   ::= { posAsyAppEntry 2 }



posFCMTable   OBJECT-TYPE
   SYNTAX    	SEQUENCE OF POSFCMEntry
   MAX-ACCESS   not-accessible
   STATUS    	current
   DESCRIPTION
             "The table to get the information of FCM interface."
   ::= { pos 5 }

posFCMEntry   OBJECT-TYPE
   SYNTAX    	POSFCMEntry
   MAX-ACCESS   not-accessible
   STATUS    	current
   DESCRIPTION
             "The content of posFCMTable."
   INDEX     { posFCMIfIndex }
   ::= { posFCMTable 1 }


POSFCMEntry ::= SEQUENCE {
   posFCMIfIndex
        INTEGER,
   posFCMTimeoutCounter
        Counter32,
   posFCMConnectFailCounter
        Counter32
   }

posFCMIfIndex   OBJECT-TYPE
   SYNTAX    	INTEGER(0..2147483647)
   MAX-ACCESS   read-only
   STATUS    	current
   DESCRIPTION
             "The index of FCM interface."
   REFERENCE  "ifIndex"
   ::= { posFCMEntry 1 }

posFCMTimeoutCounter   OBJECT-TYPE
   SYNTAX    	Counter32
   MAX-ACCESS   read-only
   STATUS    	current
   DESCRIPTION
             "The number that modem was hung up for timeout."
   DEFVAL  {0}
   ::= { posFCMEntry 3 }

posFCMConnectFailCounter   OBJECT-TYPE
   SYNTAX    	Counter32
   MAX-ACCESS   read-only
   STATUS    	current
   DESCRIPTION
             "The number that modem could not handshake successfully."
   DEFVAL  {0}
   ::= { posFCMEntry 4 }



posAppSum   OBJECT-TYPE
   SYNTAX    	INTEGER(0..32)
   MAX-ACCESS   read-only
   STATUS    	current
   DESCRIPTION
             "The total of configued applications."
   DEFVAL  {0}
   ::= { pos 6 }



posInterSum   OBJECT-TYPE
   SYNTAX    	INTEGER(0..256)
   MAX-ACCESS   read-only
   STATUS    	current
   DESCRIPTION
             "The total of configued POS-Interfaces."
   DEFVAL  {0}
   ::= { pos 7 }



posEnable   OBJECT-TYPE
   SYNTAX    	INTEGER{
                        disable(1),
                        enable(2)
                }
   MAX-ACCESS   read-write
   STATUS    	current
   DESCRIPTION
             "To enable or diable pos-server."
   DEFVAL  {1}
   ::= { pos 8 }



posAppDebugAll   OBJECT-TYPE
   SYNTAX    	INTEGER{
                        close(1),
                        open(2)
                }
   MAX-ACCESS   read-write
   STATUS    	current
   DESCRIPTION
             "To open or close the debugging switch of all applications."
   DEFVAL  {1}
   ::= { pos 9 }



posPosDebugAll   OBJECT-TYPE
   SYNTAX    	INTEGER{
                        close(1),
                        open(2)
                }
   MAX-ACCESS   read-write
   STATUS    	current
   DESCRIPTION
             "To open or close the debugging switch of all POS-Interfaces."
   DEFVAL  {1}
   ::= { pos 10 }



posClearPacCounter   OBJECT-TYPE
   SYNTAX    	INTEGER{
                        clear(1),
                        counting(2)
                }
   MAX-ACCESS   read-write
   STATUS    	current
   DESCRIPTION
             "To reset all packet counters of all applicaions and POS-Interfaces."
   DEFVAL  {2}
   ::= { pos 11 }

posClearFCMCounter   OBJECT-TYPE
   SYNTAX    	INTEGER{
                        clear(1),
                        counting(2)
                }
   MAX-ACCESS   read-write
   STATUS    	current
   DESCRIPTION
             "To clear all counters of all FCM interfaces."
   DEFVAL  {2}
   ::= { pos 12 }



posEnableTrap   OBJECT-TYPE
   SYNTAX    	INTEGER{
                        disable(1),
                        enable(2)
                }
   MAX-ACCESS   read-write
   STATUS    	current
   DESCRIPTION
             "To enable or disable trap switch."
   DEFVAL  {1}
   ::= { pos 13 }

posFCMAnswerTime   OBJECT-TYPE
   SYNTAX    	INTEGER(500..2000)
   MAX-ACCESS   read-write
   STATUS    	current
   DESCRIPTION
             "FCM answer time, unit:ms."
   DEFVAL  {500}
      ::= { pos 14 }

posFCMTradeTime   OBJECT-TYPE
   SYNTAX    	INTEGER(30000..1200000)
   MAX-ACCESS   read-write
   STATUS    	current
   DESCRIPTION
             "FCM trade time, unit:ms."
   DEFVAL  {60000}
   ::= { pos 15 }

posFCMPacketInterval   OBJECT-TYPE
   SYNTAX    	INTEGER(3500..10000)
   MAX-ACCESS   read-write
   STATUS    	current
   DESCRIPTION
             "FCM packet interval time, unit:ms."
   DEFVAL  {5000}
   ::= { pos 16 }

posPadWaitTime  OBJECT-TYPE
   SYNTAX        INTEGER (100..10000)
   MAX-ACCESS    read-write
   STATUS        current
   DESCRIPTION
	    "The time that POS-Interface needs to wait to receive another packet, unit:ms.
	    It may be configured when router is used as POSPAD device. In other cases,
	    It is useless."
   ::= { pos 18 }

posPadIdleTimeout OBJECT-TYPE
   SYNTAX          INTEGER (0..600)
   MAX-ACCESS      read-write
   STATUS          current
   DESCRIPTION
		"If these is no packet transmitting through the time,
		the connection of POSPAD device and router whose connect mode
		is pad-server will be cut off. Unit:s."
   ::= { pos 19 }

posPadPacType	 OBJECT-TYPE
    SYNTAX        INTEGER {
    				       syn(1),
    				       asy(2)
                         }
    MAX-ACCESS    read-write
    STATUS        current
    DESCRIPTION
	  	"The type of packet.Between POSPAD device and router whose connect mode
		is pad-server, there are two types of packet. One is synchronous,
		the other is asynchronous."
    DEFVAL  {1}
    ::= { pos 20 }

posPadCheckSChar  OBJECT-TYPE
   SYNTAX    	INTEGER {
                    disable(1),
                    enable(2)
		        }
   MAX-ACCESS   read-write
   STATUS    	current
   DESCRIPTION
             "To enable or disable the checking of 10 04 characters in packet.
             It is used for the router which is used as POSPAD device.

             When the value is disable, it will check packet that just includes 10 04 charaters.
             If there are 10 04 packet, the router which is used as POSPAD device
             will disconnect from POSPAD-access router.

             When the value is enable, it will check 10 04 characters in packet.
             If there are 10 04 characters in packet, the router which is used as POSPAD
             device will disconnect from POSPAD-access router."
   DEFVAL  {2}
   ::= { pos 21 }

posPadTable   OBJECT-TYPE
   SYNTAX    	SEQUENCE OF POSPadEntry
   MAX-ACCESS   not-accessible
   STATUS    	current
   DESCRIPTION
		"The table to enable or disable POSPAD-Access function under serial interface."
   ::= { pos 22 }

posPadEntry   OBJECT-TYPE
   SYNTAX    	POSPadEntry
   MAX-ACCESS   not-accessible
   STATUS    	current
   DESCRIPTION
             "The content of posPadTable."
   INDEX     { posPadIfIndex }
   ::= { posPadTable 1 }


POSPadEntry ::= SEQUENCE {
   posPadIfIndex
        INTEGER,
   posPadRowStatus
        RowStatus
   }

posPadIfIndex   OBJECT-TYPE
   SYNTAX    	INTEGER(1..2147483647)
   MAX-ACCESS   not-accessible
   STATUS    	current
   DESCRIPTION
             "The index of serial interface."
   REFERENCE  "ifIndex"
   ::= { posPadEntry 1 }

posPadRowStatus   OBJECT-TYPE
   SYNTAX    	RowStatus
   MAX-ACCESS   read-create
   STATUS    	current
   DESCRIPTION
             "The status of row. Only support active, CreateAndGo and destroy."
   ::= { posPadEntry 2 }

posTrap        OBJECT IDENTIFIER ::= { pos 17 }

posAppNotReadyTrap NOTIFICATION-TYPE
   OBJECTS 	{ posAppId }
   STATUS  	current
   DESCRIPTION
             "The agent will send a trap when the application whose state is linked
             isn't ready to send or receive data.
             Only used for the application whose connect mode is tcp."
   ::= { posTrap 1 }



posAppConnectFailTrap NOTIFICATION-TYPE
   OBJECTS 	{ posAppId }
   STATUS  	current
   DESCRIPTION
             "The agent will send a trap if router can not connect to the application."
   ::= { posTrap 2 }



posAppStateChangeTrap NOTIFICATION-TYPE
   OBJECTS 	{ posAppId, posAppState }
   STATUS  	current
   DESCRIPTION
             "The agent will send a trap when the state of the application is changed to down or kept."
   ::= { posTrap 3 }



posAppNotConfigedTrap NOTIFICATION-TYPE
   OBJECTS 	{ posAppId }
   STATUS  	current
   DESCRIPTION
             "The agent will send a trap if the application isn't configured."
   ::= { posTrap 4 }



posAppBuffOverFlowTrap NOTIFICATION-TYPE
   OBJECTS 	{ posAppId }
   STATUS  	current
   DESCRIPTION
             "The agent will send a trap if the application buffer is overflowed."
   ::= { posTrap 5 }



posAppDebugOpenTrap NOTIFICATION-TYPE
   OBJECTS 	{ posAppId }
   STATUS  	current
   DESCRIPTION
             "The agent will send a trap if the debugging switch of application is open."
   ::= { posTrap 6 }



posAppDebugAllOpenTrap NOTIFICATION-TYPE
   STATUS  	current
   DESCRIPTION
             "The agent will send a trap if the all debugging switches of application are open."
   ::= { posTrap 7 }



posInterBuffOverFlowTrap NOTIFICATION-TYPE
   STATUS  	current
   DESCRIPTION
             "The agent will send a trap if the distributing buffer is overflowed."
   ::= { posTrap 8 }



posInterStateChangeTrap NOTIFICATION-TYPE
   OBJECTS 	{ posPosId, posPosConnectState }
   STATUS  	current
   DESCRIPTION
             "The agent will send a trap if the state of POS-Interface is changed to down."
   ::= { posTrap 9 }



posInterDebugOpenTrap NOTIFICATION-TYPE
   OBJECTS 	{ posPosId }
   STATUS  	current
   DESCRIPTION
             "The agent will send a trap if the debug of POS-Interface is open."
   ::= { posTrap 10 }



posInterDebugAllOpenTrap NOTIFICATION-TYPE
   STATUS  	current
   DESCRIPTION
             "The agent will send a trap if the all debugs of POS-Interface are open."
   ::= { posTrap 11 }



posFCMTimeoutTrap NOTIFICATION-TYPE
   OBJECTS 	{ posFCMIfIndex }
   STATUS  	current
   DESCRIPTION
             "The agent will send a trap if the modem is hung up for timeout."
   ::= { posTrap 12 }



posFCMConnectFailTrap NOTIFICATION-TYPE
   OBJECTS 	{ posFCMIfIndex }
   STATUS  	current
   DESCRIPTION
             "The agent will send a trap if the handshaking of modems is not successful."
   ::= { posTrap 13 }



posClearPacketCounter NOTIFICATION-TYPE
   STATUS  	current
   DESCRIPTION
             "The agent will send a trap when the packet counter of
             the POS application and interface is cleared."
   ::= { posTrap 14 }



posClearFcmCounter NOTIFICATION-TYPE
   STATUS  	current
   DESCRIPTION
             "The agent will send a trap when the FCM counter is cleared."
   ::= { posTrap 15 }

END
