-- =================================================================
-- Copyright (C) 2002 by H3C TECHNOLOGIES.  All rights reserved.
--
-- Description: Resilient Controllable Routing MIB
-- Reference:
-- Version: V1.1
-- History:
--   V1.0 2005-04-06 created by ZhangQiang
--     Initial version
--   V1.1 2005-06-28 modified by TanZhi and DaiRuiqiang
--     Rewrite the whole MIB
-- =================================================================
H3C-RCR-MIB DEFINITIONS ::= BEGIN

    IMPORTS
        h3cCommon
            FROM HUAWEI-3COM-OID-MIB
        InterfaceIndex
            FROM IF-MIB
        InetAddressType, InetAddress
            FROM INET-ADDRESS-MIB
        Integer32, OBJECT-TYPE, MODULE-IDENTITY, NOTIFICATION-TYPE
            FROM SNMPv2-SMI;

    h3cRcr MODULE-IDENTITY
        LAST-UPDATED "200506281936Z"        -- June 28, 2005 at 19:36 GMT
        ORGANIZATION
            "Hangzhou H3C Tech. Co., Ltd."
        CONTACT-INFO
            "Platform Team Hangzhou H3C Tech. Co., Ltd.
            Hai-Dian District Beijing P.R. China
            http://www.h3c.com
            Zip:100085
            "
        DESCRIPTION
            "This MIB is applicable to router-devices. It's made for RCR
            (Resilient Controllable Routing).
            RCR provides an effective resolution which can dynamically auto-adjust
            outbound traffic to the optimal external interface by monitoring the
            performance and traffic load of each external interface. It provides
            the functions of intelligentized traffic load distribution and the optimal external interface
            selection. This can optimally utilize the external interfaces. Furthermore,
            RCR realized the function which can select the optimal external interface
            based on different classes of operation flow."
        REVISION "200506281936Z"        -- June 28, 2005 at 19:36 GMT
        DESCRIPTION
            "The modified revision of this MIB module. Rewrite the whole MIB."
        ::= { h3cCommon 48 }
--
-- Node definitions
--


-- The member router-device(MR) information is defined here.
    h3cRcrMR OBJECT IDENTIFIER ::= { h3cRcr 1 }

-- Scalar MIB objects, which are considered as global variables
-- to all member router-devices, are defined in this section.
-- This group contains global variables of all member router-devices which
-- are controlled by RCR.

    h3cRcrMRGroup OBJECT IDENTIFIER ::= {   h3cRcrMR 1  }

    h3cRcrMRAllMaxUsedBandRate OBJECT-TYPE
        SYNTAX Integer32 (1..100)
        UNITS "%"
        MAX-ACCESS read-write
        STATUS current
        DESCRIPTION
            "The max used band rate of all external interfaces on member
            router-devices(MRs) which are controlled by RCR."
        ::= { h3cRcrMRGroup 1 }

    h3cRcrMRAllMinUsedBandRate OBJECT-TYPE
        SYNTAX Integer32 (0..100)
        UNITS "%"
        MAX-ACCESS read-write
        STATUS current
        DESCRIPTION
            "The min used band rate of all external interfaces on MRs
            which are controlled by RCR."
        ::= { h3cRcrMRGroup 2 }


    h3cRcrMRListenTime OBJECT-TYPE
        SYNTAX Integer32 (1..1440)
        UNITS "minute"
        MAX-ACCESS read-write
        STATUS current
        DESCRIPTION
            "The persistent time of a probe on member router-device(MR) which is
            controlled by RCR."
        ::= { h3cRcrMRGroup 3 }


    h3cRcrMRStateTable OBJECT-TYPE
        SYNTAX SEQUENCE OF H3cRcrMRStateEntry
        MAX-ACCESS not-accessible
        STATUS current
        DESCRIPTION
            "This table contains state information of each MR
            which is controlled by RCR."
        ::= { h3cRcrMR 2 }

    h3cRcrMRStateEntry OBJECT-TYPE
        SYNTAX H3cRcrMRStateEntry
        MAX-ACCESS not-accessible
        STATUS current
        DESCRIPTION
            "Entry items"
        INDEX { h3cRcrMRName }
        ::= { h3cRcrMRStateTable 1 }

    H3cRcrMRStateEntry ::=
        SEQUENCE {
            h3cRcrMRName
                OCTET STRING,
            h3cRcrMRState
                INTEGER,
            h3cRcrMRAuthType
                INTEGER,
            h3cRcrMRAuthPwd
                OCTET STRING
                 }

    h3cRcrMRName OBJECT-TYPE
        SYNTAX OCTET STRING (SIZE(1..32))
        MAX-ACCESS not-accessible
        STATUS current
        DESCRIPTION
            "The name of MR which is controlled by RCR."
        ::= { h3cRcrMRStateEntry 1 }

    h3cRcrMRState OBJECT-TYPE
        SYNTAX INTEGER
            {
            down(1),
            up(2),
            controlled(3)
            }
        MAX-ACCESS read-only
        STATUS current
        DESCRIPTION
            "The state of MR where identified on the controller
            router-device(CR).
            down: The MR has been enabled but has not connected
                  to the CR with TCP connection.
            up: The MR has already successfully connected to
                the CR but has not been ready for adjusting
                route.
            controlled: The MR has already passed the
                        consultation with the CR and could
                        be controlled by it."
        ::= { h3cRcrMRStateEntry 2 }

     h3cRcrMRAuthType OBJECT-TYPE
        SYNTAX INTEGER
            {
            simple(1),
            md5(2)
            }
        MAX-ACCESS read-write
        STATUS current
        DESCRIPTION
            "The authentication type of communication packet between CR and MR."
        ::= { h3cRcrMRStateEntry 3 }

    h3cRcrMRAuthPwd OBJECT-TYPE
        SYNTAX OCTET STRING
        MAX-ACCESS read-write
        STATUS current
        DESCRIPTION
            "The authentication password of communication packet between CR
            and MR.
            Reading this object always results in an OCTET STRING of length zero;
            authentication may not be bypassed by reading the MIB object."
        ::= { h3cRcrMRStateEntry 4 }

    h3cRcrMROutIfStateTable OBJECT-TYPE
        SYNTAX SEQUENCE OF H3cRcrMROutIfStateEntry
        MAX-ACCESS not-accessible
        STATUS current
        DESCRIPTION
            "This table contains the external interface states of each MR
            which is controlled by RCR."
        ::= { h3cRcrMR 3 }

    h3cRcrMROutIfStateEntry OBJECT-TYPE
        SYNTAX H3cRcrMROutIfStateEntry
        MAX-ACCESS not-accessible
        STATUS current
        DESCRIPTION
            "Entry items"
        INDEX { h3cRcrMRName, h3cRcrMROutIfName }
        ::= { h3cRcrMROutIfStateTable 1 }

    H3cRcrMROutIfStateEntry ::=
        SEQUENCE {
            h3cRcrMROutIfName
                OCTET STRING,
            h3cRcrMROutIfState
                INTEGER,
            h3cRcrMROutIfMaxUsedBandRate
                Integer32,
            h3cRcrMROutIfMinUsedBandRate
                Integer32,
            h3cRcrMROutIfUsedBandRate
                Integer32
                 }

    h3cRcrMROutIfName OBJECT-TYPE
        SYNTAX OCTET STRING (SIZE(1..48))
        MAX-ACCESS not-accessible
        STATUS current
        DESCRIPTION
            "The name of external interface on each MR."
        ::= { h3cRcrMROutIfStateEntry 1 }

    h3cRcrMROutIfState OBJECT-TYPE
        SYNTAX INTEGER
            {
            down(1),
            up(2),
            notExist(3)
            }
        MAX-ACCESS read-only
        STATUS current
        DESCRIPTION
            "The state of external interface on each MR."
        ::= { h3cRcrMROutIfStateEntry 2 }

    h3cRcrMROutIfMaxUsedBandRate OBJECT-TYPE
        SYNTAX Integer32 (1..100)
        UNITS "%"
        MAX-ACCESS read-write
        STATUS current
        DESCRIPTION
            "The max spendable bandwidth rate on external interface."
        ::= { h3cRcrMROutIfStateEntry 3 }

    h3cRcrMROutIfMinUsedBandRate OBJECT-TYPE
        SYNTAX Integer32 (0..100)
        UNITS "%"
        MAX-ACCESS read-write
        STATUS current
        DESCRIPTION
            "The min spendable bandwidth rate on external interface."
        ::= { h3cRcrMROutIfStateEntry 4 }

    h3cRcrMROutIfUsedBandRate  OBJECT-TYPE
        SYNTAX Integer32 (0..100)
        UNITS "%"
        MAX-ACCESS read-only
        STATUS current
        DESCRIPTION
            "The used bandwidth rate on external interface."
        ::= { h3cRcrMROutIfStateEntry 5 }

-- The controller router-device information are defined here.
   h3cRcrCR OBJECT IDENTIFIER ::= { h3cRcr 2 }

-- Scalar MIB objects, which are considered as global variables
-- to all member router-devices, are defined in this section.
    h3cRcrCRGroup OBJECT IDENTIFIER ::= {   h3cRcrCR 1  }

    h3cRcrCRState OBJECT-TYPE
        SYNTAX INTEGER
            {
            down(1),
            init(2),
            active(3)
            }
        MAX-ACCESS read-only
        STATUS current
        DESCRIPTION
            "The state of the CR which is controlled
            by RCR.
            down: The CR has been enabled but has not
                  started a TCP connection server.
            init: The CR has started a TCP connection
                  server and has been waiting for MR
                  connection, but has not been ready for adjusting route.
            active: The CR is ready for adjusting route."
        ::= { h3cRcrCRGroup 1 }

    h3cRcrCRPortNum OBJECT-TYPE
        SYNTAX Integer32
        MAX-ACCESS read-write
        STATUS current
        DESCRIPTION
            "The communication port number between CR and MR."
        ::= { h3cRcrCRGroup 2 }

     h3cRcrCRCtrlMode OBJECT-TYPE
        SYNTAX INTEGER
            {
            control(1),
            observe(2)
            }
        MAX-ACCESS read-write
        STATUS current
        DESCRIPTION

            "The observe mode or control mode is configured to operate in the CR.
             observe: The CR monitors prefixes and external interfaces based on default
                      and user-defined policies and then reports the status of
                      the network and the decisions that should be made but does
                      not implement any changes.
             controlled: The CR monitors prefixes and external interfaces based on default
                         and user-defined policies and then reports the status
                         of the network and the decisions that should be made
                         and implement any changes."
       ::= { h3cRcrCRGroup 3 }

    h3cRcrCRChooseMode OBJECT-TYPE
        SYNTAX INTEGER
        {
        good(1),
        best(2)
        }
        MAX-ACCESS read-write
        STATUS current
        DESCRIPTION
            "The algorithm used to choose an alternative external interface for a prefix.
             good: The first external interface that conforms to the policy is selected as
                   the new external interface.
             best: Information is collected from all external interfaces and the best one
                   is selected even though the best external interface may not be in-policy."
        ::= { h3cRcrCRGroup 4 }

    h3cRcrCRKeepaliveTime OBJECT-TYPE
        SYNTAX Integer32 (1..1000)
        UNITS "second"
        MAX-ACCESS read-write
        STATUS current
        DESCRIPTION
            "The interval time of the transmission of the keepalive communication
             packet between CR and MR."
        ::= { h3cRcrCRGroup 5 }


    h3cRcrCRPolicyMode OBJECT-TYPE
        SYNTAX INTEGER
            {
            prefix(1),
            operation(2),
            study(3)
            }
        MAX-ACCESS read-write
        STATUS current
        DESCRIPTION
            "The chosen policy mode which decides to change what prefix.
            prefix: An RCR policy is designed to select IP prefixes or to
                     select RCR learn policies using a match clause and then to
                     apply RCR policy configurations using a set clause.
            operation: To deside to adjusted prefixes based on operation
                        which user configured.
            study: To learn and optimize prefixes based on the highest
                    throughput or the highest delay."
        ::= { h3cRcrCRGroup 6 }

    h3cRcrCRStudyMode OBJECT-TYPE
        SYNTAX INTEGER
            {
            maxThoughout(1),
            maxDelay(2)
            }
        MAX-ACCESS read-write
        STATUS current
        DESCRIPTION
            "The mode of collecting prefix in studying configuration mode.
            It's to collect either the prefix of max thoughtout or the prefix
            of max delay time. It doesn't have a value when CR isn't in studying
            configuration mode."
        ::= { h3cRcrCRGroup 7 }

    h3cRcrCRStudyIpPrefixNum OBJECT-TYPE
        SYNTAX Integer32 (1..2500)
        MAX-ACCESS read-write
        STATUS current
        DESCRIPTION
            "The max number of collecting prefix in studying configuration mode."
        ::= { h3cRcrCRGroup 8 }

	h3cRcrCRIpPrefixLen OBJECT-TYPE
        SYNTAX Integer32 (1..32)
        MAX-ACCESS read-write
        STATUS current
        DESCRIPTION
            "The mask length of collecting prefix in configuration mode."
        DEFVAL { 24 }
        ::= { h3cRcrCRGroup 9 }

--RCR policy table is defined here.
    h3cRcrCRRcrPolicyTable OBJECT-TYPE
        SYNTAX SEQUENCE OF H3cRcrCRRcrPolicyEntry
        MAX-ACCESS not-accessible
        STATUS current
        DESCRIPTION
            "This table contains objects to get statistic information
            of interfaces on a device."
        ::= { h3cRcrCR 2 }

    h3cRcrCRRcrPolicyEntry OBJECT-TYPE
        SYNTAX H3cRcrCRRcrPolicyEntry
        MAX-ACCESS not-accessible
        STATUS current
        DESCRIPTION
            "Entry items"
        INDEX { h3cRcrCRRcrPlyID }
        ::= { h3cRcrCRRcrPolicyTable 1 }

    H3cRcrCRRcrPolicyEntry ::=
        SEQUENCE {
            h3cRcrCRRcrPlyID
                Integer32,
            h3cRcrCRRcrPlyMatchIPListName
                OCTET STRING,
            h3cRcrCRRcrPlyMatchStudyEnable
                INTEGER,
            h3cRcrCRRcrPlyMatchOperPlyName
                OCTET STRING,
            h3cRcrCRRcrAclNumber
                Integer32,
            h3cRcrCRRcrPlyDelayTime
                Integer32,
            h3cRcrCRRcrPlyLossRate
                Integer32
                  }

    h3cRcrCRRcrPlyID OBJECT-TYPE
        SYNTAX Integer32
        MAX-ACCESS not-accessible
        STATUS current
        DESCRIPTION
            "The ID of RCR policy which the user has configured."
        ::= { h3cRcrCRRcrPolicyEntry 1 }

    h3cRcrCRRcrPlyMatchIPListName OBJECT-TYPE
        SYNTAX OCTET STRING  (SIZE(1..19))
        MAX-ACCESS read-write
        STATUS current
        DESCRIPTION
            "The matched IP prefix list name of RCR policy which the user has
            configured."
        ::= { h3cRcrCRRcrPolicyEntry 2 }

    h3cRcrCRRcrPlyMatchStudyEnable OBJECT-TYPE
        SYNTAX INTEGER
            {
            disable(1),
            enable(2)
            }
        MAX-ACCESS read-write
        STATUS current
        DESCRIPTION
            "Whether the RCR policy which the user has configured is matched
            for studying prefix mode."
        ::= { h3cRcrCRRcrPolicyEntry 3 }

    h3cRcrCRRcrPlyMatchOperPlyName OBJECT-TYPE
        SYNTAX OCTET STRING  (SIZE(1..19))
        MAX-ACCESS read-write
        STATUS current
        DESCRIPTION
            "The matched operation policy name of RCR policy which the user
            has configured."
        ::= { h3cRcrCRRcrPolicyEntry 4 }

   h3cRcrCRRcrAclNumber OBJECT-TYPE
        SYNTAX Integer32 (3000..3999)
        MAX-ACCESS read-write
        STATUS current
        DESCRIPTION
            "The matched acl number of RCR operation policy which the user
            has configured."
        ::= { h3cRcrCRRcrPolicyEntry 5 }

    h3cRcrCRRcrPlyDelayTime OBJECT-TYPE
        SYNTAX Integer32  (1..10000)
        UNITS "millisecond"
        MAX-ACCESS read-write
        STATUS current
        DESCRIPTION
            "The absolute maximum delay time. The range of values that can be
            configured is from 1 to 10000."
        ::= { h3cRcrCRRcrPolicyEntry 6 }

    h3cRcrCRRcrPlyLossRate OBJECT-TYPE
        SYNTAX Integer32 (1..100)
        UNITS "%"
        MAX-ACCESS read-write
        STATUS current
        DESCRIPTION
            "The packet loss percent of prefix which the CR concerns."
        ::= { h3cRcrCRRcrPolicyEntry 7 }

--Matched prefix performance table define
    h3cRcrCRMatPrefixPerfTable OBJECT-TYPE
        SYNTAX SEQUENCE OF H3cRcrCRMatPrefixPerfEntry
        MAX-ACCESS not-accessible
        STATUS current
        DESCRIPTION
            "This table contains the matched prefix performance
            information."
        ::= { h3cRcrCR 3 }

    h3cRcrCRMatPrefixPerfEntry OBJECT-TYPE
        SYNTAX H3cRcrCRMatPrefixPerfEntry
        MAX-ACCESS not-accessible
        STATUS current
        DESCRIPTION
            "Entry items"
        INDEX { h3cRcrCRMatPrefPerfAddrType, h3cRcrCRMatPrefPerfDestIPAddr,
                h3cRcrCRMatPrefPerfDestMaskLen }
        ::= { h3cRcrCRMatPrefixPerfTable 1 }

    H3cRcrCRMatPrefixPerfEntry ::=
        SEQUENCE {
            h3cRcrCRMatPrefPerfAddrType
                InetAddressType,
            h3cRcrCRMatPrefPerfDestIPAddr
                InetAddress,
            h3cRcrCRMatPrefPerfDestMaskLen
                Integer32,
            h3cRcrCRMatPrefPerfDelayTime
                Integer32,
            h3cRcrCRMatPrefPerfLossRate
                Integer32,
            h3cRcrCRMatPrefPerfThroughput
                Integer32
                    }

    h3cRcrCRMatPrefPerfAddrType OBJECT-TYPE
        SYNTAX InetAddressType
        MAX-ACCESS not-accessible
        STATUS current
        DESCRIPTION
            "The destination IP addresses type of matched prefix which the CR
            wants (IPv4 or IPv6)."
        ::= { h3cRcrCRMatPrefixPerfEntry 1 }

    h3cRcrCRMatPrefPerfDestIPAddr OBJECT-TYPE
        SYNTAX InetAddress
        MAX-ACCESS not-accessible
        STATUS current
        DESCRIPTION
            "The destination IP address of matched prefix which the CR wants."
        ::= { h3cRcrCRMatPrefixPerfEntry 2 }

    h3cRcrCRMatPrefPerfDestMaskLen OBJECT-TYPE
        SYNTAX Integer32 (0..32)
        MAX-ACCESS not-accessible
        STATUS current
        DESCRIPTION
            "The destination IP address mask length of matched prefix which
            the CR wants."
        ::= { h3cRcrCRMatPrefixPerfEntry 3 }

    h3cRcrCRMatPrefPerfDelayTime OBJECT-TYPE
        SYNTAX Integer32  (1..10000)
        UNITS "second"
        MAX-ACCESS read-only
        STATUS current
        DESCRIPTION
            "The absolute maximum delay time of prefix which the CR has
            configured."
        ::= { h3cRcrCRMatPrefixPerfEntry 4 }

    h3cRcrCRMatPrefPerfLossRate OBJECT-TYPE
        SYNTAX Integer32 (1..100)
        UNITS "%"
        MAX-ACCESS read-only
        STATUS current
        DESCRIPTION
            "The packet loss percent of prefix which the CR has configured."
        ::= { h3cRcrCRMatPrefixPerfEntry 5 }

    h3cRcrCRMatPrefPerfThroughput OBJECT-TYPE
        SYNTAX Integer32
        UNITS "kb"
        MAX-ACCESS read-only
        STATUS current
        DESCRIPTION
            "The bandwidth of prefix which the CR has monitored."
        ::= { h3cRcrCRMatPrefixPerfEntry 6 }

--Adjusted prefix table define
    h3cRcrCRAdjustPrefixTable OBJECT-TYPE
        SYNTAX SEQUENCE OF H3cRcrCRAdjustPrefixEntry
        MAX-ACCESS not-accessible
        STATUS current
        DESCRIPTION
            "This table contains objects to get adjusted prefix information
            which the CR controlled."
        ::= { h3cRcrCR 4 }

    h3cRcrCRAdjustPrefixEntry OBJECT-TYPE
        SYNTAX H3cRcrCRAdjustPrefixEntry
        MAX-ACCESS not-accessible
        STATUS current
        DESCRIPTION
            "Entry items"
        INDEX { h3cRcrCRAdjuPrefDestAddrType, h3cRcrCRAdjuPrefDestAddr,
        	   h3cRcrCRAdjuPrefMaskLen, h3cRcrCRAdjuPrefPreMRName,
        	   h3cRcrCRAdjuPrefPreOutIfName }
        ::= { h3cRcrCRAdjustPrefixTable 1 }

    H3cRcrCRAdjustPrefixEntry ::=
        SEQUENCE {
            h3cRcrCRAdjuPrefDestAddrType
                InetAddressType,
            h3cRcrCRAdjuPrefDestAddr
                InetAddress,
            h3cRcrCRAdjuPrefMaskLen
                Integer32,
            h3cRcrCRAdjuPrefPreMRName
                OCTET STRING,
            h3cRcrCRAdjuPrefPreOutIfName
                OCTET STRING,
            h3cRcrCRAdjuPrefCurMRName
                OCTET STRING,
            h3cRcrCRAdjuPrefCurOutIfName
                OCTET STRING,
            h3cRcrCRAdjuPrefPersistTime
                Integer32,
            h3cRcrCRAdjuPrefAgeTime
                Integer32
                    }

    h3cRcrCRAdjuPrefDestAddrType OBJECT-TYPE
        SYNTAX InetAddressType
        MAX-ACCESS not-accessible
        STATUS current
        DESCRIPTION
            "The IP address type of the adjusted prefix which CR controlled
            (IPv4 or IPv6)."
        ::= { h3cRcrCRAdjustPrefixEntry 1 }

    h3cRcrCRAdjuPrefDestAddr OBJECT-TYPE
        SYNTAX InetAddress
        MAX-ACCESS not-accessible
        STATUS current
        DESCRIPTION
            "The IP address of the adjusted prefix which CR controlled."
        ::= { h3cRcrCRAdjustPrefixEntry 2 }

    h3cRcrCRAdjuPrefMaskLen OBJECT-TYPE
        SYNTAX Integer32  (0..32)
        MAX-ACCESS not-accessible
        STATUS current
        DESCRIPTION
            "The IP address mask length of the adjusted prefix which CR
            controlled."
        ::= { h3cRcrCRAdjustPrefixEntry 3 }

    h3cRcrCRAdjuPrefPreMRName OBJECT-TYPE
        SYNTAX OCTET STRING   (SIZE(1..32))
        MAX-ACCESS not-accessible
        STATUS current
        DESCRIPTION
            "The name of the MR which the previous outbound traffic
            flows through."
        ::= { h3cRcrCRAdjustPrefixEntry 4 }

    h3cRcrCRAdjuPrefPreOutIfName OBJECT-TYPE
        SYNTAX OCTET STRING (SIZE(1..48))
        MAX-ACCESS not-accessible
        STATUS current
        DESCRIPTION
            "The name of the external interface on the MR which the previous
            outbound traffic flows through."
        ::= { h3cRcrCRAdjustPrefixEntry 5 }

    h3cRcrCRAdjuPrefCurMRName OBJECT-TYPE
        SYNTAX OCTET STRING   (SIZE(1..32))
        MAX-ACCESS read-only
        STATUS current
        DESCRIPTION
            "The name of the MR which the current outbound traffic flows through."
        ::= { h3cRcrCRAdjustPrefixEntry 6 }

    h3cRcrCRAdjuPrefCurOutIfName OBJECT-TYPE
        SYNTAX OCTET STRING
        MAX-ACCESS read-only
        STATUS current
        DESCRIPTION
            "The name of the external interface on the MR which the current outbound
            traffic flows through."
        ::= { h3cRcrCRAdjustPrefixEntry 7 }

    h3cRcrCRAdjuPrefPersistTime OBJECT-TYPE
        SYNTAX Integer32
        UNITS "second"
        MAX-ACCESS read-only
        STATUS current
        DESCRIPTION
            "The persisting time from the time which the adjusted outbound
            traffic has been adjusted by CR to now."
        ::= { h3cRcrCRAdjustPrefixEntry 8 }

    h3cRcrCRAdjuPrefAgeTime OBJECT-TYPE
        SYNTAX Integer32
        UNITS "second"
        MAX-ACCESS read-only
        STATUS current
        DESCRIPTION
            "The time which the adjusted prefix remains."
        ::= { h3cRcrCRAdjustPrefixEntry 9 }
END
