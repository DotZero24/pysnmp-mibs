GUDEADS-PDU8110-MIB DEFINITIONS ::= BEGIN

IMPORTS
	enterprises,
	MODULE-IDENTITY,
	OBJECT-TYPE,
	NOTIFICATION-TYPE,
	Integer32,
	Unsigned32
		FROM SNMPv2-SMI
	OBJECT-GROUP,
	NOTIFICATION-GROUP
		FROM SNMPv2-CONF;

gudeads MODULE-IDENTITY
	LAST-UPDATED "200703051356Z"
	ORGANIZATION "Gude Analog- und Digitalsysteme GmbH"
	CONTACT-INFO
		"http://www.gudeads.com/"
	DESCRIPTION
		""
	REVISION "200703051356Z"
	DESCRIPTION
		"$Id: GUDEADS-PDU8110-MIB.txt 4232 2011-07-26 09:45:52Z petes1 $"
	::= { enterprises 28507 }


pdu8110PowerIndex OBJECT-TYPE
	SYNTAX  Integer32 (1)
	MAX-ACCESS not-accessible
	STATUS  current
	DESCRIPTION
		"Index of Power Channel entries"
	::= { pdu8110PowerEntry 1 }


pdu8110Current OBJECT-TYPE
	SYNTAX  Unsigned32
	UNITS
		"mA"
	MAX-ACCESS read-only
	STATUS  current
	DESCRIPTION
		"Actual Curent on Power Channel."
	::= { pdu8110PowerEntry 5 }


pdu8110PowerTable OBJECT-TYPE
	SYNTAX  SEQUENCE OF Enc2102PowerEntry
	MAX-ACCESS not-accessible
	STATUS  current
	DESCRIPTION
		"All available Channel Interfaces."
	::= { pdu8110PowerChan 2 }


pdu8110PowerEntry OBJECT-TYPE
	SYNTAX  Enc2102PowerEntry
	MAX-ACCESS not-accessible
	STATUS  current
	DESCRIPTION
		"An entry containing management information
		applicable to a particular Power Channel."
	INDEX {
		pdu8110PowerIndex }
	::= { pdu8110PowerTable 1 }


Enc2102PowerEntry ::= SEQUENCE {

	pdu8110PowerIndex Integer32,
	pdu8110ChanStatus Integer32,
	pdu8110Current    Unsigned32 }


pdu8110PowerChan OBJECT IDENTIFIER 	::= { pdu8110IntSensors 1 }

pdu8110ChanStatus OBJECT-TYPE
	SYNTAX  Integer32 (0..1)
	MAX-ACCESS read-only
	STATUS  current
	DESCRIPTION
		"0 = data not active, 1 = data valid"
	::= { pdu8110PowerEntry 2 }


pdu8110ActivePowerChan OBJECT-TYPE
	SYNTAX  Unsigned32 (1..2)
	MAX-ACCESS read-only
	STATUS  current
	DESCRIPTION
		"Number of suppported Power Channels."
	::= { pdu8110PowerChan 1 }


-- Notification Types
--

events OBJECT IDENTIFIER 	::= { gadsPDU8110 0 }

pdu8110TrapIPTable OBJECT-TYPE
	SYNTAX  SEQUENCE OF Epc8TrapIPEntry
	MAX-ACCESS not-accessible
	STATUS  current
	DESCRIPTION
		"list of all Trap receiver"
	::= { pdu8110SNMPaccess 2 }


gadsPDU8110 OBJECT IDENTIFIER 	::= { gudeads 23 }

pdu8110TrapIPEntry OBJECT-TYPE
	SYNTAX  Epc8TrapIPEntry
	MAX-ACCESS not-accessible
	STATUS  current
	DESCRIPTION
		"an entry containing management
		informations regarding the list of trap
		receivers"
	INDEX {
		pdu8110TrapIPIndex }
	::= { pdu8110TrapIPTable 1 }


Epc8TrapIPEntry ::= SEQUENCE {

	pdu8110TrapIPIndex Integer32,
	pdu8110TrapAddr    OCTET STRING }


pdu8110TrapIPIndex OBJECT-TYPE
	SYNTAX  Integer32 (1..8)
	MAX-ACCESS not-accessible
	STATUS  current
	DESCRIPTION
		"A unique value, greater than zero, for each receiver slot."
	::= { pdu8110TrapIPEntry 1 }


pdu8110DeviceConfig OBJECT IDENTIFIER 	::= { pdu8110Objects 2 }

pdu8110ExtActors OBJECT IDENTIFIER 	::= { pdu8110Objects 4 }

pdu8110ExtSensors OBJECT IDENTIFIER 	::= { pdu8110Objects 6 }

pdu8110SensorTable OBJECT-TYPE
	SYNTAX  SEQUENCE OF Pdu8110SensorEntry
	MAX-ACCESS not-accessible
	STATUS  current
	DESCRIPTION ""
	::= { pdu8110ExtSensors 1 }


pdu8110SensorEntry OBJECT-TYPE
	SYNTAX  Pdu8110SensorEntry
	MAX-ACCESS not-accessible
	STATUS  current
	DESCRIPTION ""
	INDEX {
		pdu8110SensorIndex }
	::= { pdu8110SensorTable 1 }


Pdu8110SensorEntry ::= SEQUENCE {

	pdu8110SensorIndex Integer32,
	pdu8110TempSensor  Integer32,
	pdu8110HygroSensor Integer32 }


pdu8110SensorIndex OBJECT-TYPE
	SYNTAX  Integer32 (1..2)
	MAX-ACCESS not-accessible
	STATUS  current
	DESCRIPTION ""
	::= { pdu8110SensorEntry 1 }


pdu8110TempSensor OBJECT-TYPE
	SYNTAX  Integer32
	UNITS
		"0.1 degree Celsius"
	MAX-ACCESS read-only
	STATUS  current
	DESCRIPTION
		"actual temperature,  a value of -9999 indicates
		that data is not available"
	::= { pdu8110SensorEntry 2 }


pdu8110HygroSensor OBJECT-TYPE
	SYNTAX  Integer32
	UNITS
		"0.1 percent humidity"
	MAX-ACCESS read-only
	STATUS  current
	DESCRIPTION
		"actual humidity,  a value of -9999 indicates
		that data is not available"
	::= { pdu8110SensorEntry 3 }


pdu8110SNMPaccess OBJECT IDENTIFIER 	::= { pdu8110CommonConfig 1 }

pdu8110TrapCtrl OBJECT-TYPE
	SYNTAX  Integer32 (0..2)
	MAX-ACCESS read-write
	STATUS  current
	DESCRIPTION
		"0 = off
		1 = Ver. 1
		2 = Ver. 2c"
	::= { pdu8110SNMPaccess 1 }


-- Scalars and Tables
--

pdu8110Objects OBJECT IDENTIFIER 	::= { gadsPDU8110 1 }

pdu8110CommonConfig OBJECT IDENTIFIER 	::= { pdu8110Objects 1 }

pdu8110IntActors OBJECT IDENTIFIER 	::= { pdu8110Objects 3 }

pdu8110TrapAddr OBJECT-TYPE
	SYNTAX  OCTET STRING (SIZE (0..99))
	MAX-ACCESS read-write
	STATUS  current
	DESCRIPTION
		"DNS name or IP address specifying one Trap receiver slot.
		A port can optionally be specified: 'name:port' An empty
		string disables this slot."
	::= { pdu8110TrapIPEntry 2 }


pdu8110IntSensors OBJECT IDENTIFIER 	::= { pdu8110Objects 5 }

-- Conformance
--

pdu8110Conf OBJECT IDENTIFIER 	::= { gadsPDU8110 2 }

-- Groups
--

pdu8110Groups OBJECT IDENTIFIER 	::= { pdu8110Conf 1 }

-- Compliance
--

pdu8110Compls OBJECT IDENTIFIER 	::= { pdu8110Conf 2 }


pdu8110TempEvtSen1 NOTIFICATION-TYPE
	OBJECTS {
		pdu8110TempSensor}
	STATUS  current
	DESCRIPTION
		"temperature limits exceeded"
	::= { events 1 }


pdu8110TempEvtSen2 NOTIFICATION-TYPE
	OBJECTS {
		pdu8110TempSensor}
	STATUS  current
	DESCRIPTION
		"temperature limits exceeded"
	::= { events 2 }


pdu8110HygroEvtSen1 NOTIFICATION-TYPE
	OBJECTS {
		pdu8110HygroSensor}
	STATUS  current
	DESCRIPTION
		"hygro limits exceeded"
	::= { events 3 }


pdu8110HygroEvtSen2 NOTIFICATION-TYPE
	OBJECTS {
		pdu8110HygroSensor}
	STATUS  current
	DESCRIPTION
		"hygro limits exceeded"
	::= { events 4 }

pdu8110BasicGroup OBJECT-GROUP
	OBJECTS {
		pdu8110TrapCtrl,
		pdu8110TrapAddr,
		pdu8110ActivePowerChan,
		pdu8110ChanStatus,
		pdu8110Current,
		pdu8110TempSensor,
		pdu8110HygroSensor }
	STATUS  current
	DESCRIPTION
		"Basic objects."
	::= { pdu8110Groups 1 }

pdu8110NotificationGroup NOTIFICATION-GROUP
	NOTIFICATIONS {
		pdu8110TempEvtSen1,
		pdu8110TempEvtSen2,
		pdu8110HygroEvtSen1,
		pdu8110HygroEvtSen2 }
	STATUS  current
	DESCRIPTION ""
	::= { pdu8110Groups 2 }

END
