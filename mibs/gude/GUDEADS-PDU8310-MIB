GUDEADS-PDU8310-MIB DEFINITIONS ::= BEGIN

IMPORTS
	enterprises,
	MODULE-IDENTITY,
	OBJECT-TYPE,
	NOTIFICATION-TYPE,
	Integer32,
	Unsigned32
		FROM SNMPv2-SMI
	OBJECT-GROUP,
	NOTIFICATION-GROUP
		FROM SNMPv2-CONF;

gudeads MODULE-IDENTITY
	LAST-UPDATED "200703051356Z"	-- Mar 5, 2007 1:56:00 PM
	ORGANIZATION "Gude Analog- und Digitalsysteme GmbH"
	CONTACT-INFO
		"http://www.gudeads.com/"
	DESCRIPTION
		""
	REVISION "200703051356Z"	-- Mar 5, 2007 1:56:00 PM
	DESCRIPTION
		"$Id:$"
	-- 1.3.6.1.4.1.28507
	::= { enterprises 28507 }



pdu8310AmperageEvt1 NOTIFICATION-TYPE
	OBJECTS {
		pdu8310PowerActive,
		pdu8310Current,
		pdu8310Voltage,
		pdu8310Frequency,
		pdu8310PowerApparent,
		pdu8310PowerReactive}
	STATUS  current
	DESCRIPTION
		"Event is triggered when a measured
		current is crossing the entered limits"
	-- 1.3.6.1.4.1.28507.27.0.1
	::= { events 1 }

pdu8310NotificationGroup NOTIFICATION-GROUP
	NOTIFICATIONS {
		pdu8310AmperageEvt1 }
	STATUS  current
	DESCRIPTION
		""
	-- 1.3.6.1.4.1.28507.27.2.1.2
	::= { pdu8310Groups 2 }

-- Notification Types
--

events OBJECT IDENTIFIER
	-- 1.3.6.1.4.1.28507.27.0
	::= { gadsPDU8310 0 }

pdu8310PowerIndex OBJECT-TYPE
	SYNTAX  Integer32 (1)
	MAX-ACCESS not-accessible
	STATUS  current
	DESCRIPTION
		"Index of Power Channel entries"
	-- 1.3.6.1.4.1.28507.27.1.5.1.2.1.1
	::= { pdu8310PowerEntry 1 }


pdu8310TrapIPTable OBJECT-TYPE
	SYNTAX  SEQUENCE OF Epc8TrapIPEntry
	MAX-ACCESS not-accessible
	STATUS  current
	DESCRIPTION
		"list of all Trap receiver"
	-- 1.3.6.1.4.1.28507.27.1.1.1.2
	::= { pdu8310SNMPaccess 2 }


pdu8310Current OBJECT-TYPE
	SYNTAX  Unsigned32
	UNITS
		"mA"
	MAX-ACCESS read-only
	STATUS  current
	DESCRIPTION
		"Actual Curent on Power Channel."
	-- 1.3.6.1.4.1.28507.27.1.5.1.2.1.5
	::= { pdu8310PowerEntry 5 }


gadsPDU8310 OBJECT IDENTIFIER
	-- 1.3.6.1.4.1.28507.27
	::= { gudeads 27 }

pdu8310Voltage OBJECT-TYPE
	SYNTAX  Unsigned32
	UNITS
		"V"
	MAX-ACCESS read-only
	STATUS  current
	DESCRIPTION
		"Actual Voltage on Power Channel"
	-- 1.3.6.1.4.1.28507.27.1.5.1.2.1.6
	::= { pdu8310PowerEntry 6 }


pdu8310TrapIPEntry OBJECT-TYPE
	SYNTAX  Epc8TrapIPEntry
	MAX-ACCESS not-accessible
	STATUS  current
	DESCRIPTION
		"an entry containing management
		informations regarding the list of trap
		receivers"
	INDEX {
		pdu8310TrapIPIndex }
	-- 1.3.6.1.4.1.28507.27.1.1.1.2.1
	::= { pdu8310TrapIPTable 1 }


Epc8TrapIPEntry ::= SEQUENCE {

	pdu8310TrapIPIndex Integer32,
	pdu8310TrapAddr    OCTET STRING }


pdu8310PowerTable OBJECT-TYPE
	SYNTAX  SEQUENCE OF Pdu8310PowerEntry
	MAX-ACCESS not-accessible
	STATUS  current
	DESCRIPTION
		"All available Channel Interfaces."
	-- 1.3.6.1.4.1.28507.27.1.5.1.2
	::= { pdu8310PowerChan 2 }


pdu8310PowerEntry OBJECT-TYPE
	SYNTAX  Pdu8310PowerEntry
	MAX-ACCESS not-accessible
	STATUS  current
	DESCRIPTION
		"An entry containing management information
		applicable to a particular Power Channel."
	INDEX {
		pdu8310PowerIndex }
	-- 1.3.6.1.4.1.28507.27.1.5.1.2.1
	::= { pdu8310PowerTable 1 }


Pdu8310PowerEntry ::= SEQUENCE {

	pdu8310PowerIndex               Integer32,
	pdu8310ChanStatus               Integer32,
	pdu8310EnergyActive             Unsigned32,
	pdu8310PowerActive              Unsigned32,
	pdu8310Current                  Unsigned32,
	pdu8310Voltage                  Unsigned32,
	pdu8310Frequency                Unsigned32,
	pdu8310PowerFactor              Integer32,
	pdu8310Pangle                   Integer32,
	pdu8310PowerApparent            Unsigned32,
	pdu8310PowerReactive            Unsigned32,
	pdu8310EnergyReactive           Unsigned32,
	pdu8310EnergyActiveResettable   Unsigned32,
	pdu8310EnergyReactiveResettable Unsigned32,
	pdu8310ResetTime                Unsigned32 }


pdu8310TrapIPIndex OBJECT-TYPE
	SYNTAX  Integer32 (1..8)
	MAX-ACCESS not-accessible
	STATUS  current
	DESCRIPTION
		"A unique value, greater than zero, for each receiver slot."
	-- 1.3.6.1.4.1.28507.27.1.1.1.2.1.1
	::= { pdu8310TrapIPEntry 1 }


pdu8310DeviceConfig OBJECT IDENTIFIER
	-- 1.3.6.1.4.1.28507.27.1.2
	::= { pdu8310Objects 2 }

pdu8310ExtActors OBJECT IDENTIFIER
	-- 1.3.6.1.4.1.28507.27.1.4
	::= { pdu8310Objects 4 }

pdu8310ExtSensors OBJECT IDENTIFIER
	-- 1.3.6.1.4.1.28507.27.1.6
	::= { pdu8310Objects 6 }

pdu8310SNMPaccess OBJECT IDENTIFIER
	-- 1.3.6.1.4.1.28507.27.1.1.1
	::= { pdu8310CommonConfig 1 }

pdu8310TrapCtrl OBJECT-TYPE
	SYNTAX  Integer32 (0..2)
	MAX-ACCESS read-write
	STATUS  current
	DESCRIPTION
		"0 = off
		1 = Ver. 1
		2 = Ver. 2c"
	-- 1.3.6.1.4.1.28507.27.1.1.1.1
	::= { pdu8310SNMPaccess 1 }


-- Scalars and Tables
--

pdu8310Objects OBJECT IDENTIFIER
	-- 1.3.6.1.4.1.28507.27.1
	::= { gadsPDU8310 1 }

pdu8310CommonConfig OBJECT IDENTIFIER
	-- 1.3.6.1.4.1.28507.27.1.1
	::= { pdu8310Objects 1 }

pdu8310PowerChan OBJECT IDENTIFIER
	-- 1.3.6.1.4.1.28507.27.1.5.1
	::= { pdu8310IntSensors 1 }

pdu8310IntActors OBJECT IDENTIFIER
	-- 1.3.6.1.4.1.28507.27.1.3
	::= { pdu8310Objects 3 }

pdu8310ChanStatus OBJECT-TYPE
	SYNTAX  Integer32 (0..1)
	MAX-ACCESS read-only
	STATUS  current
	DESCRIPTION
		"0 = data not active, 1 = data valid"
	-- 1.3.6.1.4.1.28507.27.1.5.1.2.1.2
	::= { pdu8310PowerEntry 2 }


pdu8310ActivePowerChan OBJECT-TYPE
	SYNTAX  Unsigned32 (1)
	MAX-ACCESS read-only
	STATUS  current
	DESCRIPTION
		"Number of suppported Power Channels."
	-- 1.3.6.1.4.1.28507.27.1.5.1.1
	::= { pdu8310PowerChan 1 }


pdu8310EnergyActive OBJECT-TYPE
	SYNTAX  Unsigned32
	UNITS
		"Wh"
	MAX-ACCESS read-only
	STATUS  current
	DESCRIPTION
		"Total accumulated Active Energy of Power Channel."
	-- 1.3.6.1.4.1.28507.27.1.5.1.2.1.3
	::= { pdu8310PowerEntry 3 }


pdu8310TrapAddr OBJECT-TYPE
	SYNTAX  OCTET STRING (SIZE (0..99))
	MAX-ACCESS read-write
	STATUS  current
	DESCRIPTION
		"DNS name or IP address specifying one Trap receiver slot.
		A port can optionally be specified: 'name:port' An empty
		string disables this slot."
	-- 1.3.6.1.4.1.28507.27.1.1.1.2.1.2
	::= { pdu8310TrapIPEntry 2 }


pdu8310PowerActive OBJECT-TYPE
	SYNTAX  Unsigned32
	UNITS
		"W"
	MAX-ACCESS read-only
	STATUS  current
	DESCRIPTION
		"Active Power"
	-- 1.3.6.1.4.1.28507.27.1.5.1.2.1.4
	::= { pdu8310PowerEntry 4 }


pdu8310IntSensors OBJECT IDENTIFIER
	-- 1.3.6.1.4.1.28507.27.1.5
	::= { pdu8310Objects 5 }

pdu8310PowerFactor OBJECT-TYPE
	SYNTAX  Integer32
	UNITS
		"0.001"
	MAX-ACCESS read-only
	STATUS  current
	DESCRIPTION
		"Power Factor of Channel between
		-1.0 and 1.00"
	-- 1.3.6.1.4.1.28507.27.1.5.1.2.1.8
	::= { pdu8310PowerEntry 8 }


-- Conformance
--

pdu8310Conf OBJECT IDENTIFIER
	-- 1.3.6.1.4.1.28507.27.2
	::= { gadsPDU8310 2 }

-- Groups
--

pdu8310Groups OBJECT IDENTIFIER
	-- 1.3.6.1.4.1.28507.27.2.1
	::= { pdu8310Conf 1 }

-- Compliance
--

pdu8310Compls OBJECT IDENTIFIER
	-- 1.3.6.1.4.1.28507.27.2.2
	::= { pdu8310Conf 2 }

pdu8310BasicGroup OBJECT-GROUP
	OBJECTS {
		pdu8310TrapCtrl,
		pdu8310TrapAddr,
		pdu8310ActivePowerChan,
		pdu8310ChanStatus,
		pdu8310EnergyActive,
		pdu8310PowerActive,
		pdu8310Current,
		pdu8310Voltage,
		pdu8310Frequency,
		pdu8310PowerFactor,
		pdu8310Pangle,
		pdu8310PowerApparent,
		pdu8310PowerReactive,
		pdu8310EnergyReactive,
		pdu8310EnergyActiveResettable,
		pdu8310EnergyReactiveResettable,
		pdu8310ResetTime }
	STATUS  current
	DESCRIPTION
		"Basic objects."
	-- 1.3.6.1.4.1.28507.27.2.1.1
	::= { pdu8310Groups 1 }

pdu8310Frequency OBJECT-TYPE
	SYNTAX  Unsigned32
	UNITS
		"0.01 hz"
	MAX-ACCESS read-only
	STATUS  current
	DESCRIPTION
		"Freqency of Power Channel"
	-- 1.3.6.1.4.1.28507.27.1.5.1.2.1.7
	::= { pdu8310PowerEntry 7 }


pdu8310Pangle OBJECT-TYPE
	SYNTAX  Integer32
	UNITS
		"0.1 degree"
	MAX-ACCESS read-only
	STATUS  current
	DESCRIPTION
		"Phase Angle between Voltage
		and L Line Current between
		-180.0 and 180.0"
	-- 1.3.6.1.4.1.28507.27.1.5.1.2.1.9
	::= { pdu8310PowerEntry 9 }


pdu8310PowerApparent OBJECT-TYPE
	SYNTAX  Unsigned32
	UNITS
		"VA"
	MAX-ACCESS read-only
	STATUS  current
	DESCRIPTION
		"L Line Mean Apparent Power"
	-- 1.3.6.1.4.1.28507.27.1.5.1.2.1.10
	::= { pdu8310PowerEntry 10 }


pdu8310PowerReactive OBJECT-TYPE
	SYNTAX  Unsigned32
	UNITS
		"VAR"
	MAX-ACCESS read-only
	STATUS  current
	DESCRIPTION
		"L Line Mean Reactive Power"
	-- 1.3.6.1.4.1.28507.27.1.5.1.2.1.11
	::= { pdu8310PowerEntry 11 }


pdu8310EnergyReactive OBJECT-TYPE
	SYNTAX  Unsigned32
	UNITS
		"VARh"
	MAX-ACCESS read-only
	STATUS  current
	DESCRIPTION
		"Total accumulated Reactive Energy
		of Power Channel."
	-- 1.3.6.1.4.1.28507.27.1.5.1.2.1.12
	::= { pdu8310PowerEntry 12 }


pdu8310EnergyActiveResettable OBJECT-TYPE
	SYNTAX  Unsigned32
	UNITS
		"Wh"
	MAX-ACCESS read-only
	STATUS  current
	DESCRIPTION
		"Resettable accumulated Active Energy
		of Power Channel."
	-- 1.3.6.1.4.1.28507.27.1.5.1.2.1.13
	::= { pdu8310PowerEntry 13 }


pdu8310EnergyReactiveResettable OBJECT-TYPE
	SYNTAX  Unsigned32
	UNITS
		"VARh"
	MAX-ACCESS read-only
	STATUS  current
	DESCRIPTION
		"Resettable accumulated Reactive Energy
		of Power Channel."
	-- 1.3.6.1.4.1.28507.27.1.5.1.2.1.14
	::= { pdu8310PowerEntry 14 }


pdu8310ResetTime OBJECT-TYPE
	SYNTAX  Unsigned32
	UNITS
		"s"
	MAX-ACCESS read-only
	STATUS  current
	DESCRIPTION
		"Time in seconds since last Energy
		Counter reset."
	-- 1.3.6.1.4.1.28507.27.1.5.1.2.1.15
	::= { pdu8310PowerEntry 15 }


END
