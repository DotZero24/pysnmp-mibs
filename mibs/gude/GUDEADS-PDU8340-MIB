GUDEADS-PDU8340-MIB DEFINITIONS ::= BEGIN

IMPORTS
	enterprises,
	MODULE-IDENTITY,
	OBJECT-TYPE,
	NOTIFICATION-TYPE,
	Integer32,
	Unsigned32
		FROM SNMPv2-SMI
	OBJECT-GROUP,
	NOTIFICATION-GROUP
		FROM SNMPv2-CONF;

gudeads MODULE-IDENTITY
	LAST-UPDATED "200703051356Z"	-- Mar 5, 2007 1:56:00 PM
	ORGANIZATION "Gude Analog- und Digitalsysteme GmbH"
	CONTACT-INFO
		"http://www.gudeads.com/"
	DESCRIPTION
		""
	REVISION "200703051356Z"	-- Mar 5, 2007 1:56:00 PM
	DESCRIPTION
		"$Id:$"
	-- 1.3.6.1.4.1.28507
	::= { enterprises 28507 }



pdu8340AirPressureEvtSen NOTIFICATION-TYPE
	OBJECTS {
		pdu8340SensorIndex,
		pdu8340AirPressure}
	STATUS  current
	DESCRIPTION
		"Air Pressure limits exceeded

		"
	-- 1.3.6.1.4.1.28507.54.3.4
	::= { events 4 }


pdu8340DewPtDiffEvtSen NOTIFICATION-TYPE
	OBJECTS {
		pdu8340SensorIndex,
		pdu8340DewPointDiff}
	STATUS  current
	DESCRIPTION
		"Dew Point Difference limits exceeded"
	-- 1.3.6.1.4.1.28507.54.3.5
	::= { events 5 }


pdu8340TempEvtSen NOTIFICATION-TYPE
	OBJECTS {
		pdu8340SensorIndex,
		pdu8340TempSensor}
	STATUS  current
	DESCRIPTION
		"temperature limits exceeded"
	-- 1.3.6.1.4.1.28507.54.3.1
	::= { events 1 }


pdu8340HygroEvtSen NOTIFICATION-TYPE
	OBJECTS {
		pdu8340SensorIndex,
		pdu8340HygroSensor}
	STATUS  current
	DESCRIPTION
		"hygro limits exceeded"
	-- 1.3.6.1.4.1.28507.54.3.2
	::= { events 2 }


pdu8340InputEvtSen NOTIFICATION-TYPE
	OBJECTS {
		pdu8340SensorIndex,
		pdu8340InputSensor}
	STATUS  current
	DESCRIPTION
		"change of logical input sensor state"
	-- 1.3.6.1.4.1.28507.54.3.3
	::= { events 3 }


pdu8340LineAmperageEvt NOTIFICATION-TYPE
	OBJECTS {
		pdu8340PowerIndex,
		pdu8340PowerActive,
		pdu8340Current,
		pdu8340Voltage,
		pdu8340Frequency,
		pdu8340PowerApparent,
		pdu8340PowerReactive}
	STATUS  current
	DESCRIPTION
		"Event is triggered when a measured
		current is crossing the entered limits"
	-- 1.3.6.1.4.1.28507.54.3.6
	::= { events 6 }

gadsPDU8340 OBJECT IDENTIFIER
	-- 1.3.6.1.4.1.28507.54
	::= { gudeads 54 }

-- Notification Types
--

events OBJECT IDENTIFIER
	-- 1.3.6.1.4.1.28507.54.3
	::= { gadsPDU8340 3 }

-- Scalars and Tables
--

pdu8340Objects OBJECT IDENTIFIER
	-- 1.3.6.1.4.1.28507.54.1
	::= { gadsPDU8340 1 }

pdu8340CommonConfig OBJECT IDENTIFIER
	-- 1.3.6.1.4.1.28507.54.1.1
	::= { pdu8340Objects 1 }

pdu8340SNMPaccess OBJECT IDENTIFIER
	-- 1.3.6.1.4.1.28507.54.1.1.1
	::= { pdu8340CommonConfig 1 }

pdu8340TrapCtrl OBJECT-TYPE
	SYNTAX  Integer32 (0..3)
	MAX-ACCESS read-write
	STATUS  current
	DESCRIPTION
		"0 = off
		1 = Ver. 1
		2 = Ver. 2c
		3 = Ver. 3"
	-- 1.3.6.1.4.1.28507.54.1.1.1.1
	::= { pdu8340SNMPaccess 1 }


pdu8340TrapIPTable OBJECT-TYPE
	SYNTAX  SEQUENCE OF Pdu8340TrapIPEntry
	MAX-ACCESS not-accessible
	STATUS  current
	DESCRIPTION
		"list of all Trap receiver"
	-- 1.3.6.1.4.1.28507.54.1.1.1.2
	::= { pdu8340SNMPaccess 2 }


pdu8340TrapIPEntry OBJECT-TYPE
	SYNTAX  Pdu8340TrapIPEntry
	MAX-ACCESS not-accessible
	STATUS  current
	DESCRIPTION
		"an entry containing management
		informations regarding the list of trap
		receivers"
	INDEX {
		pdu8340TrapIPIndex }
	-- 1.3.6.1.4.1.28507.54.1.1.1.2.1
	::= { pdu8340TrapIPTable 1 }


Pdu8340TrapIPEntry ::= SEQUENCE {

	pdu8340TrapIPIndex Integer32,
	pdu8340TrapAddr    OCTET STRING }


pdu8340TrapIPIndex OBJECT-TYPE
	SYNTAX  Integer32 (1..8)
	MAX-ACCESS read-only
	STATUS  current
	DESCRIPTION
		"A unique value, greater than zero, for each receiver slot."
	-- 1.3.6.1.4.1.28507.54.1.1.1.2.1.1
	::= { pdu8340TrapIPEntry 1 }


pdu8340TrapAddr OBJECT-TYPE
	SYNTAX  OCTET STRING (SIZE (0..99))
	MAX-ACCESS read-write
	STATUS  current
	DESCRIPTION
		"DNS name or IP address specifying one Trap receiver slot.
		A port can optionally be specified: 'name:port' An empty
		string disables this slot."
	-- 1.3.6.1.4.1.28507.54.1.1.1.2.1.2
	::= { pdu8340TrapIPEntry 2 }


pdu8340DeviceConfig OBJECT IDENTIFIER
	-- 1.3.6.1.4.1.28507.54.1.2
	::= { pdu8340Objects 2 }

pdu8340IntActors OBJECT IDENTIFIER
	-- 1.3.6.1.4.1.28507.54.1.3
	::= { pdu8340Objects 3 }

pdu8340Buzzer OBJECT-TYPE
	SYNTAX  Integer32 (0..1)
	UNITS	"0 = Off, 1 = On"
	MAX-ACCESS read-write
	STATUS  current
	DESCRIPTION
		"turn Buzzer on and off"
	-- 1.3.6.1.4.1.28507.54.1.3.10
	::= { pdu8340IntActors 10 }


pdu8340ExtActors OBJECT IDENTIFIER
	-- 1.3.6.1.4.1.28507.54.1.4
	::= { pdu8340Objects 4 }

pdu8340IntSensors OBJECT IDENTIFIER
	-- 1.3.6.1.4.1.28507.54.1.5
	::= { pdu8340Objects 5 }

pdu8340PowerChan OBJECT IDENTIFIER
	-- 1.3.6.1.4.1.28507.54.1.5.1
	::= { pdu8340IntSensors 1 }

pdu8340ActivePowerChan OBJECT-TYPE
	SYNTAX  Unsigned32 (1..2)
	MAX-ACCESS read-only
	STATUS  current
	DESCRIPTION
		"Number of suppported Power Channels."
	-- 1.3.6.1.4.1.28507.54.1.5.1.1
	::= { pdu8340PowerChan 1 }


pdu8340PowerTable OBJECT-TYPE
	SYNTAX  SEQUENCE OF Pdu8340PowerEntry
	MAX-ACCESS not-accessible
	STATUS  current
	DESCRIPTION
		"All available Channel Interfaces."
	-- 1.3.6.1.4.1.28507.54.1.5.1.2
	::= { pdu8340PowerChan 2 }


pdu8340PowerEntry OBJECT-TYPE
	SYNTAX  Pdu8340PowerEntry
	MAX-ACCESS not-accessible
	STATUS  current
	DESCRIPTION
		"An entry containing management information
		applicable to a particular Power Channel."
	INDEX {
		pdu8340PowerIndex }
	-- 1.3.6.1.4.1.28507.54.1.5.1.2.1
	::= { pdu8340PowerTable 1 }


Pdu8340PowerEntry ::= SEQUENCE {

	pdu8340PowerIndex                   Integer32,
	pdu8340ChanStatus                   Integer32,
	pdu8340AbsEnergyActive              Unsigned32,
	pdu8340PowerActive                  Integer32,
	pdu8340Current                      Unsigned32,
	pdu8340Voltage                      Unsigned32,
	pdu8340Frequency                    Unsigned32,
	pdu8340PowerFactor                  Integer32,
	pdu8340Pangle                       Integer32,
	pdu8340PowerApparent                Integer32,
	pdu8340PowerReactive                Integer32,
	pdu8340AbsEnergyReactive            Unsigned32,
	pdu8340AbsEnergyActiveResettable    Unsigned32,
	pdu8340AbsEnergyReactiveResettable  Unsigned32,
	pdu8340ResetTime                    Unsigned32,
	pdu8340ForwEnergyActive             Unsigned32,
	pdu8340ForwEnergyReactive           Unsigned32,
	pdu8340ForwEnergyActiveResettable   Unsigned32,
	pdu8340ForwEnergyReactiveResettable Unsigned32,
	pdu8340RevEnergyActive              Unsigned32,
	pdu8340RevEnergyReactive            Unsigned32,
	pdu8340RevEnergyActiveResettable    Unsigned32,
	pdu8340RevEnergyReactiveResettable  Unsigned32,
	pdu8340ResidualCurrent              Unsigned32 }


pdu8340ChanStatus OBJECT-TYPE
	SYNTAX  Integer32 (0..1)
	MAX-ACCESS read-only
	STATUS  current
	DESCRIPTION
		"0 = data not active, 1 = data valid"
	-- 1.3.6.1.4.1.28507.54.1.5.1.2.1.2
	::= { pdu8340PowerEntry 2 }


pdu8340AbsEnergyActive OBJECT-TYPE
	SYNTAX  Unsigned32
	UNITS	"Wh"
	MAX-ACCESS read-only
	STATUS  current
	DESCRIPTION
		"Absolute Active Energy counter."
	-- 1.3.6.1.4.1.28507.54.1.5.1.2.1.3
	::= { pdu8340PowerEntry 3 }


pdu8340PowerActive OBJECT-TYPE
	SYNTAX  Integer32
	UNITS	"W"
	MAX-ACCESS read-only
	STATUS  current
	DESCRIPTION
		"Active Power"
	-- 1.3.6.1.4.1.28507.54.1.5.1.2.1.4
	::= { pdu8340PowerEntry 4 }


pdu8340Current OBJECT-TYPE
	SYNTAX  Unsigned32
	UNITS	"mA"
	MAX-ACCESS read-only
	STATUS  current
	DESCRIPTION
		"Actual Current on Power Channel."
	-- 1.3.6.1.4.1.28507.54.1.5.1.2.1.5
	::= { pdu8340PowerEntry 5 }


pdu8340ResidualCurrent OBJECT-TYPE
	SYNTAX  Unsigned32
	UNITS	"mA"
	MAX-ACCESS read-only
	STATUS  current
	DESCRIPTION
		"Actual Residual Current on Power Channel.
		According Typ A IEC 60755. Only visible on
		models that support this feature."
	-- 1.3.6.1.4.1.28507.54.1.5.1.2.1.24
	::= { pdu8340PowerEntry 24 }


pdu8340Voltage OBJECT-TYPE
	SYNTAX  Unsigned32
	UNITS	"V"
	MAX-ACCESS read-only
	STATUS  current
	DESCRIPTION
		"Actual Voltage on Power Channel"
	-- 1.3.6.1.4.1.28507.54.1.5.1.2.1.6
	::= { pdu8340PowerEntry 6 }


pdu8340Frequency OBJECT-TYPE
	SYNTAX  Unsigned32
	UNITS	"0.01 hz"
	MAX-ACCESS read-only
	STATUS  current
	DESCRIPTION
		"Frequency of Power Channel"
	-- 1.3.6.1.4.1.28507.54.1.5.1.2.1.7
	::= { pdu8340PowerEntry 7 }


pdu8340PowerFactor OBJECT-TYPE
	SYNTAX  Integer32
	UNITS	"0.001"
	MAX-ACCESS read-only
	STATUS  current
	DESCRIPTION
		"Power Factor of Channel between
		-1.0 and 1.00"
	-- 1.3.6.1.4.1.28507.54.1.5.1.2.1.8
	::= { pdu8340PowerEntry 8 }


pdu8340Pangle OBJECT-TYPE
	SYNTAX  Integer32
	UNITS	"0.1 degree"
	MAX-ACCESS read-only
	STATUS  current
	DESCRIPTION
		"Phase Angle between Voltage
		and L Line Current between
		-180.0 and 180.0"
	-- 1.3.6.1.4.1.28507.54.1.5.1.2.1.9
	::= { pdu8340PowerEntry 9 }


pdu8340PowerApparent OBJECT-TYPE
	SYNTAX  Integer32
	UNITS	"VA"
	MAX-ACCESS read-only
	STATUS  current
	DESCRIPTION
		"L Line Mean Apparent Power"
	-- 1.3.6.1.4.1.28507.54.1.5.1.2.1.10
	::= { pdu8340PowerEntry 10 }


pdu8340PowerReactive OBJECT-TYPE
	SYNTAX  Integer32
	UNITS	"VAR"
	MAX-ACCESS read-only
	STATUS  current
	DESCRIPTION
		"L Line Mean Reactive Power"
	-- 1.3.6.1.4.1.28507.54.1.5.1.2.1.11
	::= { pdu8340PowerEntry 11 }


pdu8340AbsEnergyReactive OBJECT-TYPE
	SYNTAX  Unsigned32
	UNITS	"VARh"
	MAX-ACCESS read-only
	STATUS  current
	DESCRIPTION
		"Absolute Reactive Energy counter."
	-- 1.3.6.1.4.1.28507.54.1.5.1.2.1.12
	::= { pdu8340PowerEntry 12 }


pdu8340AbsEnergyActiveResettable OBJECT-TYPE
	SYNTAX  Unsigned32
	UNITS	"Wh"
	MAX-ACCESS read-write
	STATUS  current
	DESCRIPTION
		"Resettable Absolute Active Energy counter.
		Writing '0' resets all resettable counter."
	-- 1.3.6.1.4.1.28507.54.1.5.1.2.1.13
	::= { pdu8340PowerEntry 13 }


pdu8340AbsEnergyReactiveResettable OBJECT-TYPE
	SYNTAX  Unsigned32
	UNITS	"VARh"
	MAX-ACCESS read-only
	STATUS  current
	DESCRIPTION
		"Resettable Absolute Reactive Energy counter."
	-- 1.3.6.1.4.1.28507.54.1.5.1.2.1.14
	::= { pdu8340PowerEntry 14 }


pdu8340ResetTime OBJECT-TYPE
	SYNTAX  Unsigned32
	UNITS	"s"
	MAX-ACCESS read-only
	STATUS  current
	DESCRIPTION
		"Time in seconds since last Energy
		Counter reset."
	-- 1.3.6.1.4.1.28507.54.1.5.1.2.1.15
	::= { pdu8340PowerEntry 15 }


pdu8340ForwEnergyActive OBJECT-TYPE
	SYNTAX  Unsigned32
	UNITS	"Wh"
	MAX-ACCESS read-only
	STATUS  current
	DESCRIPTION
		"Forward Active Energy counter."
	-- 1.3.6.1.4.1.28507.54.1.5.1.2.1.16
	::= { pdu8340PowerEntry 16 }


pdu8340ForwEnergyReactive OBJECT-TYPE
	SYNTAX  Unsigned32
	UNITS	"VARh"
	MAX-ACCESS read-only
	STATUS  current
	DESCRIPTION
		"Forward Reactive Energy counter."
	-- 1.3.6.1.4.1.28507.54.1.5.1.2.1.17
	::= { pdu8340PowerEntry 17 }


pdu8340ForwEnergyActiveResettable OBJECT-TYPE
	SYNTAX  Unsigned32
	UNITS	"Wh"
	MAX-ACCESS read-only
	STATUS  current
	DESCRIPTION
		"Resettable Forward Active Energy counter."
	-- 1.3.6.1.4.1.28507.54.1.5.1.2.1.18
	::= { pdu8340PowerEntry 18 }


pdu8340ForwEnergyReactiveResettable OBJECT-TYPE
	SYNTAX  Unsigned32
	UNITS	"VARh"
	MAX-ACCESS read-only
	STATUS  current
	DESCRIPTION
		"Resettable Forward Reactive Energy counter."
	-- 1.3.6.1.4.1.28507.54.1.5.1.2.1.19
	::= { pdu8340PowerEntry 19 }


pdu8340RevEnergyActive OBJECT-TYPE
	SYNTAX  Unsigned32
	UNITS	"Wh"
	MAX-ACCESS read-only
	STATUS  current
	DESCRIPTION
		"Reverse Active Energy counter."
	-- 1.3.6.1.4.1.28507.54.1.5.1.2.1.20
	::= { pdu8340PowerEntry 20 }


pdu8340RevEnergyReactive OBJECT-TYPE
	SYNTAX  Unsigned32
	UNITS	"VARh"
	MAX-ACCESS read-only
	STATUS  current
	DESCRIPTION
		"Reverse Reactive Energy counter."
	-- 1.3.6.1.4.1.28507.54.1.5.1.2.1.21
	::= { pdu8340PowerEntry 21 }


pdu8340RevEnergyActiveResettable OBJECT-TYPE
	SYNTAX  Unsigned32
	UNITS	"Wh"
	MAX-ACCESS read-only
	STATUS  current
	DESCRIPTION
		"Resettable Reverse Active Energy counter."
	-- 1.3.6.1.4.1.28507.54.1.5.1.2.1.22
	::= { pdu8340PowerEntry 22 }


pdu8340RevEnergyReactiveResettable OBJECT-TYPE
	SYNTAX  Unsigned32
	UNITS	"VARh"
	MAX-ACCESS read-only
	STATUS  current
	DESCRIPTION
		"Resettable Reverse Reactive Energy counter."
	-- 1.3.6.1.4.1.28507.54.1.5.1.2.1.23
	::= { pdu8340PowerEntry 23 }


pdu8340ExtSensors OBJECT IDENTIFIER
	-- 1.3.6.1.4.1.28507.54.1.6
	::= { pdu8340Objects 6 }

pdu8340SensorTable OBJECT-TYPE
	SYNTAX  SEQUENCE OF Pdu8340SensorEntry
	MAX-ACCESS not-accessible
	STATUS  current
	DESCRIPTION ""
	-- 1.3.6.1.4.1.28507.54.1.6.1
	::= { pdu8340ExtSensors 1 }


pdu8340SensorEntry OBJECT-TYPE
	SYNTAX  Pdu8340SensorEntry
	MAX-ACCESS not-accessible
	STATUS  current
	DESCRIPTION ""
	INDEX {
		pdu8340SensorIndex }
	-- 1.3.6.1.4.1.28507.54.1.6.1.1
	::= { pdu8340SensorTable 1 }


Pdu8340SensorEntry ::= SEQUENCE {

	pdu8340SensorIndex  Integer32,
	pdu8340TempSensor   Integer32,
	pdu8340HygroSensor  Integer32,
	pdu8340InputSensor  INTEGER,
	pdu8340AirPressure  Integer32,
	pdu8340DewPoint     Integer32,
	pdu8340DewPointDiff Integer32 }


pdu8340SensorIndex OBJECT-TYPE
	SYNTAX  Integer32 (1..2)
	MAX-ACCESS read-only
	STATUS  current
	DESCRIPTION ""
	-- 1.3.6.1.4.1.28507.54.1.6.1.1.1
	::= { pdu8340SensorEntry 1 }


pdu8340TempSensor OBJECT-TYPE
	SYNTAX  Integer32
	UNITS	"0.1 degree Celsius"
	MAX-ACCESS read-only
	STATUS  current
	DESCRIPTION
		"actual temperature"
	-- 1.3.6.1.4.1.28507.54.1.6.1.1.2
	::= { pdu8340SensorEntry 2 }


pdu8340HygroSensor OBJECT-TYPE
	SYNTAX  Integer32
	UNITS	"0.1 percent humidity"
	MAX-ACCESS read-only
	STATUS  current
	DESCRIPTION
		"actual humidity"
	-- 1.3.6.1.4.1.28507.54.1.6.1.1.3
	::= { pdu8340SensorEntry 3 }


pdu8340InputSensor OBJECT-TYPE
	SYNTAX  INTEGER {
			off(0),
			on(1) }
	MAX-ACCESS read-only
	STATUS  current
	DESCRIPTION
		"logical state of input sensor"
	-- 1.3.6.1.4.1.28507.54.1.6.1.1.4
	::= { pdu8340SensorEntry 4 }


-- Conformance
--

pdu8340Conf OBJECT IDENTIFIER
	-- 1.3.6.1.4.1.28507.54.2
	::= { gadsPDU8340 2 }

-- Groups
--

pdu8340Groups OBJECT IDENTIFIER
	-- 1.3.6.1.4.1.28507.54.2.1
	::= { pdu8340Conf 1 }

-- Compliance
--

pdu8340Compls OBJECT IDENTIFIER
	-- 1.3.6.1.4.1.28507.54.2.2
	::= { pdu8340Conf 2 }

pdu8340BasicGroup OBJECT-GROUP
	OBJECTS {
		pdu8340TrapCtrl,
		pdu8340TrapIPIndex,
		pdu8340TrapAddr,
		pdu8340Buzzer,
		pdu8340ActivePowerChan,
		pdu8340PowerIndex,
		pdu8340ChanStatus,
		pdu8340AbsEnergyActive,
		pdu8340PowerActive,
		pdu8340Current,
		pdu8340Voltage,
		pdu8340Frequency,
		pdu8340PowerFactor,
		pdu8340Pangle,
		pdu8340PowerApparent,
		pdu8340PowerReactive,
		pdu8340AbsEnergyReactive,
		pdu8340AbsEnergyActiveResettable,
		pdu8340AbsEnergyReactiveResettable,
		pdu8340ResetTime,
		pdu8340ForwEnergyActive,
		pdu8340ForwEnergyReactive,
		pdu8340ForwEnergyActiveResettable,
		pdu8340ForwEnergyReactiveResettable,
		pdu8340RevEnergyActive,
		pdu8340RevEnergyReactive,
		pdu8340RevEnergyActiveResettable,
		pdu8340RevEnergyReactiveResettable,
		pdu8340ResidualCurrent,
		pdu8340SensorIndex,
		pdu8340TempSensor,
		pdu8340HygroSensor,
		pdu8340InputSensor,
		pdu8340AirPressure,
		pdu8340DewPoint,
		pdu8340DewPointDiff }
	STATUS  current
	DESCRIPTION
		"Basic objects."
	-- 1.3.6.1.4.1.28507.54.2.1.1
	::= { pdu8340Groups 1 }

pdu8340NotificationGroup NOTIFICATION-GROUP
	NOTIFICATIONS {
		pdu8340TempEvtSen,
		pdu8340HygroEvtSen,
		pdu8340InputEvtSen,
		pdu8340AirPressureEvtSen,
		pdu8340DewPtDiffEvtSen,
		pdu8340LineAmperageEvt }
	STATUS  current
	DESCRIPTION ""
	-- 1.3.6.1.4.1.28507.54.2.1.2
	::= { pdu8340Groups 2 }

pdu8340PowerIndex OBJECT-TYPE
	SYNTAX  Integer32 (1..2)
	MAX-ACCESS read-only
	STATUS  current
	DESCRIPTION
		"Index of Power Channel entries"
	-- 1.3.6.1.4.1.28507.54.1.5.1.2.1.1
	::= { pdu8340PowerEntry 1 }


pdu8340AirPressure OBJECT-TYPE
	SYNTAX  Integer32
	UNITS	"1 hPA (hectopascal) ~ 1 milibar"
	MAX-ACCESS read-only
	STATUS  current
	DESCRIPTION
		"actual air pressure"
	-- 1.3.6.1.4.1.28507.54.1.6.1.1.5
	::= { pdu8340SensorEntry 5 }


pdu8340DewPoint OBJECT-TYPE
	SYNTAX  Integer32
	UNITS	"0.1 degree Celsius"
	MAX-ACCESS read-only
	STATUS  current
	DESCRIPTION
		"dew point for actual temperature and humidity"
	-- 1.3.6.1.4.1.28507.54.1.6.1.1.6
	::= { pdu8340SensorEntry 6 }


pdu8340DewPointDiff OBJECT-TYPE
	SYNTAX  Integer32
	UNITS	"0.1 degree Celsius"
	MAX-ACCESS read-only
	STATUS  current
	DESCRIPTION
		"difference between dew point and actual
		temperature (Temp - DewPoint)"
	-- 1.3.6.1.4.1.28507.54.1.6.1.1.7
	::= { pdu8340SensorEntry 7 }


END
