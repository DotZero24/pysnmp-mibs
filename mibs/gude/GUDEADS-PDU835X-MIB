GUDEADS-PDU835X-MIB DEFINITIONS ::= BEGIN

IMPORTS
	enterprises,
	MODULE-IDENTITY,
	OBJECT-TYPE,
	NOTIFICATION-TYPE,
	Integer32,
	Unsigned32
		FROM SNMPv2-SMI
	OBJECT-GROUP,
	NOTIFICATION-GROUP
		FROM SNMPv2-CONF;

gudeads MODULE-IDENTITY
	LAST-UPDATED "200703051356Z"	-- Mar 5, 2007 1:56:00 PM
	ORGANIZATION "Gude Analog- und Digitalsysteme GmbH"
	CONTACT-INFO
		"http://www.gudeads.com/"
	DESCRIPTION
		""
	REVISION "200703051356Z"	-- Mar 5, 2007 1:56:00 PM
	DESCRIPTION
		"$Id:$"
	-- 1.3.6.1.4.1.28507
::= { enterprises 28507 }


gadsPDU835X OBJECT IDENTIFIER
	-- 1.3.6.1.4.1.28507.52
::= { gudeads 52 }

-- Notification Types
--

events OBJECT IDENTIFIER
	-- 1.3.6.1.4.1.28507.52.0
::= { gadsPDU835X 0 }

-- Scalars and Tables
--

pdu835XObjects OBJECT IDENTIFIER
	-- 1.3.6.1.4.1.28507.52.1
::= { gadsPDU835X 1 }

pdu835XCommonConfig OBJECT IDENTIFIER
	-- 1.3.6.1.4.1.28507.52.1.1
::= { pdu835XObjects 1 }

pdu835XSNMPaccess OBJECT IDENTIFIER
	-- 1.3.6.1.4.1.28507.52.1.1.1
::= { pdu835XCommonConfig 1 }

pdu835XTrapCtrl OBJECT-TYPE
	SYNTAX  Integer32 (0..2)
	MAX-ACCESS read-write
	STATUS  current
	DESCRIPTION
		"0 = off
		1 = Ver. 1
		2 = Ver. 2c"
	-- 1.3.6.1.4.1.28507.52.1.1.1.1
::= { pdu835XSNMPaccess 1 }


pdu835XTrapIPTable OBJECT-TYPE
	SYNTAX  SEQUENCE OF Pdu835XTrapIPEntry
	MAX-ACCESS not-accessible
	STATUS  current
	DESCRIPTION
		"list of all Trap receiver"
	-- 1.3.6.1.4.1.28507.52.1.1.1.2
::= { pdu835XSNMPaccess 2 }


pdu835XTrapIPEntry OBJECT-TYPE
	SYNTAX  Pdu835XTrapIPEntry
	MAX-ACCESS not-accessible
	STATUS  current
	DESCRIPTION
		"an entry containing management
		informations regarding the list of trap
		receivers"
	INDEX {
		pdu835XTrapIPIndex }
	-- 1.3.6.1.4.1.28507.52.1.1.1.2.1
::= { pdu835XTrapIPTable 1 }


Pdu835XTrapIPEntry ::= SEQUENCE {

	pdu835XTrapIPIndex Integer32,
	pdu835XTrapAddr    OCTET STRING }


pdu835XTrapIPIndex OBJECT-TYPE
	SYNTAX  Integer32 (1..8)
	MAX-ACCESS not-accessible
	STATUS  current
	DESCRIPTION
		"A unique value, greater than zero, for each receiver slot."
	-- 1.3.6.1.4.1.28507.52.1.1.1.2.1.1
::= { pdu835XTrapIPEntry 1 }


pdu835XTrapAddr OBJECT-TYPE
	SYNTAX  OCTET STRING (SIZE (0..99))
	MAX-ACCESS read-write
	STATUS  current
	DESCRIPTION
		"DNS name or IP address specifying one Trap receiver slot.
		A port can optionally be specified: 'name:port' An empty
		string disables this slot."
	-- 1.3.6.1.4.1.28507.52.1.1.1.2.1.2
::= { pdu835XTrapIPEntry 2 }


pdu835XDeviceConfig OBJECT IDENTIFIER
	-- 1.3.6.1.4.1.28507.52.1.2
::= { pdu835XObjects 2 }

pdu835XIntActors OBJECT IDENTIFIER
	-- 1.3.6.1.4.1.28507.52.1.3
::= { pdu835XObjects 3 }

pdu835XBuzzer OBJECT-TYPE
	SYNTAX  Integer32 (0..1)
	UNITS	"0 = Off, 1 = On"
	MAX-ACCESS read-write
	STATUS  current
	DESCRIPTION
		"turn Buzzer on and off"
	-- 1.3.6.1.4.1.28507.52.1.3.10
::= { pdu835XIntActors 10 }


pdu835XExtActors OBJECT IDENTIFIER
	-- 1.3.6.1.4.1.28507.52.1.4
::= { pdu835XObjects 4 }

pdu835XIntSensors OBJECT IDENTIFIER
	-- 1.3.6.1.4.1.28507.52.1.5
::= { pdu835XObjects 5 }

pdu835XPowerChan OBJECT IDENTIFIER
	-- 1.3.6.1.4.1.28507.52.1.5.1
::= { pdu835XIntSensors 1 }

pdu835XActivePowerChan OBJECT-TYPE
	SYNTAX  Unsigned32 (1..3)
	MAX-ACCESS read-only
	STATUS  current
	DESCRIPTION
		"Number of supported Power Channels."
	-- 1.3.6.1.4.1.28507.52.1.5.1.1
::= { pdu835XPowerChan 1 }


pdu835XActivePowerGroups OBJECT-TYPE
	SYNTAX  Unsigned32 (1..2)
	MAX-ACCESS read-only
	STATUS  current
	DESCRIPTION
		"Number of Power Groups. May vary with
		different PDU models."
	-- 1.3.6.1.4.1.28507.52.1.5.1.1
	-- 1.3.6.1.4.1.28507.52.1.5.3.1
::= { pdu835XPowerGroup 1 }


pdu835XPowerTable OBJECT-TYPE
	SYNTAX  SEQUENCE OF Pdu835XPowerEntry
	MAX-ACCESS not-accessible
	STATUS  current
	DESCRIPTION
		"All available Channel Interfaces."
	-- 1.3.6.1.4.1.28507.52.1.5.1.2
::= { pdu835XPowerChan 2 }


pdu835XPowerEntry OBJECT-TYPE
	SYNTAX  Pdu835XPowerEntry
	MAX-ACCESS not-accessible
	STATUS  current
	DESCRIPTION
		"An entry containing management information
		applicable to a particular Power Channel."
	INDEX {
		pdu835XPowerIndex }
	-- 1.3.6.1.4.1.28507.52.1.5.1.2.1
::= { pdu835XPowerTable 1 }


Pdu835XPowerEntry ::= SEQUENCE {

	pdu835XPowerIndex                   Integer32,
	pdu835XChanStatus                   Integer32,
	pdu835XAbsEnergyActive              Unsigned32,
	pdu835XPowerActive                  Integer32,
	pdu835XCurrent                      Unsigned32,
	pdu835XVoltage                      Unsigned32,
	pdu835XFrequency                    Unsigned32,
	pdu835XPowerFactor                  Integer32,
	pdu835XPangle                       Integer32,
	pdu835XPowerApparent                Integer32,
	pdu835XPowerReactive                Integer32,
	pdu835XAbsEnergyReactive            Unsigned32,
	pdu835XAbsEnergyActiveResettable    Unsigned32,
	pdu835XAbsEnergyReactiveResettable  Unsigned32,
	pdu835XResetTime                    Unsigned32,
	pdu835XForwEnergyActive             Unsigned32,
	pdu835XForwEnergyReactive           Unsigned32,
	pdu835XForwEnergyActiveResettable   Unsigned32,
	pdu835XForwEnergyReactiveResettable Unsigned32,
	pdu835XRevEnergyActive              Unsigned32,
	pdu835XRevEnergyReactive            Unsigned32,
	pdu835XRevEnergyActiveResettable    Unsigned32,
	pdu835XRevEnergyReactiveResettable  Unsigned32 }


pdu835XPowerIndex OBJECT-TYPE
	SYNTAX  Integer32 (1..6)
	MAX-ACCESS not-accessible
	STATUS  current
	DESCRIPTION
		"Index of Power Channel entries"
	-- 1.3.6.1.4.1.28507.52.1.5.1.2.1.1
::= { pdu835XPowerEntry 1 }


pdu835XChanStatus OBJECT-TYPE
	SYNTAX  Integer32 (0..1)
	MAX-ACCESS read-only
	STATUS  current
	DESCRIPTION
		"0 = data not active, 1 = data valid"
	-- 1.3.6.1.4.1.28507.52.1.5.1.2.1.2
::= { pdu835XPowerEntry 2 }


pdu835XAbsEnergyActive OBJECT-TYPE
	SYNTAX  Unsigned32
	UNITS	"Wh"
	MAX-ACCESS read-only
	STATUS  current
	DESCRIPTION
		"Absolute Active Energy counter."
	-- 1.3.6.1.4.1.28507.52.1.5.1.2.1.3
::= { pdu835XPowerEntry 3 }


pdu835XPowerActive OBJECT-TYPE
	SYNTAX  Integer32
	UNITS	"W"
	MAX-ACCESS read-only
	STATUS  current
	DESCRIPTION
		"Active Power"
	-- 1.3.6.1.4.1.28507.52.1.5.1.2.1.4
::= { pdu835XPowerEntry 4 }


pdu835XCurrent OBJECT-TYPE
	SYNTAX  Unsigned32
	UNITS	"mA"
	MAX-ACCESS read-only
	STATUS  current
	DESCRIPTION
		"Actual Curent on Power Channel."
	-- 1.3.6.1.4.1.28507.52.1.5.1.2.1.5
::= { pdu835XPowerEntry 5 }


pdu835XRCurrent3P OBJECT-TYPE
	SYNTAX  Unsigned32
	UNITS	"mA"
	MAX-ACCESS read-only
	STATUS  current
	DESCRIPTION
		"Actual Residual Current. Entry may not exist on models
		that support not this type of measurement."
	-- 1.3.6.1.4.1.28507.52.1.5.1.2.1.5
	-- 1.3.6.1.4.1.28507.52.1.5.3.2.1.2
::= { pdu835XEntry 2 }


pdu835XNCurrent3P OBJECT-TYPE
	SYNTAX  Unsigned32
	UNITS	"mA"
	MAX-ACCESS read-only
	STATUS  current
	DESCRIPTION
		"Actual Current of the neutral wire. Entry may not exist
		on models that support not this type of measurement."
	-- 1.3.6.1.4.1.28507.52.1.5.1.2.1.5
	-- 1.3.6.1.4.1.28507.52.1.5.3.2.1.3
::= { pdu835XEntry 3 }


pdu835XVoltage OBJECT-TYPE
	SYNTAX  Unsigned32
	UNITS	"V"
	MAX-ACCESS read-only
	STATUS  current
	DESCRIPTION
		"Actual Voltage on Power Channel"
	-- 1.3.6.1.4.1.28507.52.1.5.1.2.1.6
::= { pdu835XPowerEntry 6 }


pdu835XFrequency OBJECT-TYPE
	SYNTAX  Unsigned32
	UNITS	"0.01 hz"
	MAX-ACCESS read-only
	STATUS  current
	DESCRIPTION
		"Frequency of Power Channel"
	-- 1.3.6.1.4.1.28507.52.1.5.1.2.1.7
::= { pdu835XPowerEntry 7 }


pdu835XPowerFactor OBJECT-TYPE
	SYNTAX  Integer32
	UNITS	"0.001"
	MAX-ACCESS read-only
	STATUS  current
	DESCRIPTION
		"Power Factor of Channel between
		-1.0 and 1.00"
	-- 1.3.6.1.4.1.28507.52.1.5.1.2.1.8
::= { pdu835XPowerEntry 8 }


pdu835XPangle OBJECT-TYPE
	SYNTAX  Integer32
	UNITS	"0.1 degree"
	MAX-ACCESS read-only
	STATUS  current
	DESCRIPTION
		"Phase Angle between Voltage
		and L Line Current between
		-180.0 and 180.0"
	-- 1.3.6.1.4.1.28507.52.1.5.1.2.1.9
::= { pdu835XPowerEntry 9 }


pdu835XPowerApparent OBJECT-TYPE
	SYNTAX  Integer32
	UNITS	"VA"
	MAX-ACCESS read-only
	STATUS  current
	DESCRIPTION
		"L Line Mean Apparent Power"
	-- 1.3.6.1.4.1.28507.52.1.5.1.2.1.10
::= { pdu835XPowerEntry 10 }


pdu835XPowerReactive OBJECT-TYPE
	SYNTAX  Integer32
	UNITS	"VAR"
	MAX-ACCESS read-only
	STATUS  current
	DESCRIPTION
		"L Line Mean Reactive Power"
	-- 1.3.6.1.4.1.28507.52.1.5.1.2.1.11
::= { pdu835XPowerEntry 11 }


pdu835XAbsEnergyReactive OBJECT-TYPE
	SYNTAX  Unsigned32
	UNITS	"VARh"
	MAX-ACCESS read-only
	STATUS  current
	DESCRIPTION
		"Absolute Reactive Energy counter."
	-- 1.3.6.1.4.1.28507.52.1.5.1.2.1.12
::= { pdu835XPowerEntry 12 }


pdu835XAbsEnergyActiveResettable OBJECT-TYPE
	SYNTAX  Unsigned32
	UNITS	"Wh"
	MAX-ACCESS read-only
	STATUS  current
	DESCRIPTION
		"Resettable Absolute Active Energy counter."
	-- 1.3.6.1.4.1.28507.52.1.5.1.2.1.13
::= { pdu835XPowerEntry 13 }


pdu835XAbsEnergyReactiveResettable OBJECT-TYPE
	SYNTAX  Unsigned32
	UNITS	"VARh"
	MAX-ACCESS read-only
	STATUS  current
	DESCRIPTION
		"Resettable Absolute Reactive Energy counter."
	-- 1.3.6.1.4.1.28507.52.1.5.1.2.1.14
::= { pdu835XPowerEntry 14 }


pdu835XResetTime OBJECT-TYPE
	SYNTAX  Unsigned32
	UNITS	"s"
	MAX-ACCESS read-only
	STATUS  current
	DESCRIPTION
		"Time in seconds since last Energy
		Counter reset."
	-- 1.3.6.1.4.1.28507.52.1.5.1.2.1.15
::= { pdu835XPowerEntry 15 }


pdu835XForwEnergyActive OBJECT-TYPE
	SYNTAX  Unsigned32
	UNITS	"Wh"
	MAX-ACCESS read-only
	STATUS  current
	DESCRIPTION
		"Forward Active Energy counter."
	-- 1.3.6.1.4.1.28507.52.1.5.1.2.1.16
::= { pdu835XPowerEntry 16 }


pdu835XForwEnergyReactive OBJECT-TYPE
	SYNTAX  Unsigned32
	UNITS	"VARh"
	MAX-ACCESS read-only
	STATUS  current
	DESCRIPTION
		"Forward Reactive Energy counter."
	-- 1.3.6.1.4.1.28507.52.1.5.1.2.1.17
::= { pdu835XPowerEntry 17 }


pdu835XForwEnergyActiveResettable OBJECT-TYPE
	SYNTAX  Unsigned32
	UNITS	"Wh"
	MAX-ACCESS read-only
	STATUS  current
	DESCRIPTION
		"Resettable Forward Active Energy counter."
	-- 1.3.6.1.4.1.28507.52.1.5.1.2.1.18
::= { pdu835XPowerEntry 18 }


pdu835XForwEnergyReactiveResettable OBJECT-TYPE
	SYNTAX  Unsigned32
	UNITS	"VARh"
	MAX-ACCESS read-only
	STATUS  current
	DESCRIPTION
		"Resettable Forward Reactive Energy counter."
	-- 1.3.6.1.4.1.28507.52.1.5.1.2.1.19
::= { pdu835XPowerEntry 19 }


pdu835XRevEnergyActive OBJECT-TYPE
	SYNTAX  Unsigned32
	UNITS	"Wh"
	MAX-ACCESS read-only
	STATUS  current
	DESCRIPTION
		"Reverse Active Energy counter."
	-- 1.3.6.1.4.1.28507.52.1.5.1.2.1.20
::= { pdu835XPowerEntry 20 }


pdu835XRevEnergyReactive OBJECT-TYPE
	SYNTAX  Unsigned32
	UNITS	"VARh"
	MAX-ACCESS read-only
	STATUS  current
	DESCRIPTION
		"Reverse Reactive Energy counter."
	-- 1.3.6.1.4.1.28507.52.1.5.1.2.1.21
::= { pdu835XPowerEntry 21 }


pdu835XRevEnergyActiveResettable OBJECT-TYPE
	SYNTAX  Unsigned32
	UNITS	"Wh"
	MAX-ACCESS read-only
	STATUS  current
	DESCRIPTION
		"Resettable Reverse Active Energy counter."
	-- 1.3.6.1.4.1.28507.52.1.5.1.2.1.22
::= { pdu835XPowerEntry 22 }


pdu835XRevEnergyReactiveResettable OBJECT-TYPE
	SYNTAX  Unsigned32
	UNITS	"VARh"
	MAX-ACCESS read-only
	STATUS  current
	DESCRIPTION
		"Resettable Reverse Reactive Energy counter."
	-- 1.3.6.1.4.1.28507.52.1.5.1.2.1.23
::= { pdu835XPowerEntry 23 }


pdu835XPowerGroup OBJECT IDENTIFIER
	-- 1.3.6.1.4.1.28507.52.1.5.3
::= { pdu835XIntSensors 3 }

pdu835XPowerGroupTable OBJECT-TYPE
	SYNTAX  SEQUENCE OF Pdu835XEntry
	MAX-ACCESS not-accessible
	STATUS  current
	DESCRIPTION ""
	-- 1.3.6.1.4.1.28507.52.1.5.3.2
::= { pdu835XPowerGroup 2 }


pdu835XEntry OBJECT-TYPE
	SYNTAX  Pdu835XEntry
	MAX-ACCESS not-accessible
	STATUS  current
	DESCRIPTION
		"An entry containing management information
		applicable to a particular Power Group.
		Entries may not exist on every PDU model."
	INDEX {
		pdu835XPowerGroupIndex }
	-- 1.3.6.1.4.1.28507.52.1.5.3.2.1
::= { pdu835XPowerGroupTable 1 }


Pdu835XEntry ::= SEQUENCE {

	pdu835XPowerGroupIndex         Integer32,
	pdu835XRCurrent3P              Unsigned32,
	pdu835XNCurrent3P              Unsigned32,
	pdu835XMeasurementBoxConnected INTEGER }


pdu835XPowerGroupIndex OBJECT-TYPE
	SYNTAX  Integer32 (0..1)
	MAX-ACCESS not-accessible
	STATUS  current
	DESCRIPTION ""
	-- 1.3.6.1.4.1.28507.52.1.5.3.2.1.1
::= { pdu835XEntry 1 }


pdu835XExtSensors OBJECT IDENTIFIER
	-- 1.3.6.1.4.1.28507.52.1.6
::= { pdu835XObjects 6 }

pdu835XSensorTable OBJECT-TYPE
	SYNTAX  SEQUENCE OF Pdu835XSensorEntry
	MAX-ACCESS not-accessible
	STATUS  current
	DESCRIPTION ""
	-- 1.3.6.1.4.1.28507.52.1.6.1
::= { pdu835XExtSensors 1 }


pdu835XSensorEntry OBJECT-TYPE
	SYNTAX  Pdu835XSensorEntry
	MAX-ACCESS not-accessible
	STATUS  current
	DESCRIPTION ""
	INDEX {
		pdu835XSensorIndex }
	-- 1.3.6.1.4.1.28507.52.1.6.1.1
::= { pdu835XSensorTable 1 }


Pdu835XSensorEntry ::= SEQUENCE {

	pdu835XSensorIndex Integer32,
	pdu835XTempSensor  Integer32,
	pdu835XHygroSensor Integer32,
	pdu835XInputSensor INTEGER }


pdu835XSensorIndex OBJECT-TYPE
	SYNTAX  Integer32 (1..2)
	MAX-ACCESS not-accessible
	STATUS  current
	DESCRIPTION ""
	-- 1.3.6.1.4.1.28507.52.1.6.1.1.1
::= { pdu835XSensorEntry 1 }


pdu835XTempSensor OBJECT-TYPE
	SYNTAX  Integer32
	UNITS	"0.1 degree Celsius"
	MAX-ACCESS read-only
	STATUS  current
	DESCRIPTION
		"actual temperature,  a value of -9999 indicates
		that data is not available"
	-- 1.3.6.1.4.1.28507.52.1.6.1.1.2
::= { pdu835XSensorEntry 2 }


pdu835XHygroSensor OBJECT-TYPE
	SYNTAX  Integer32
	UNITS	"0.1 percent humidity"
	MAX-ACCESS read-only
	STATUS  current
	DESCRIPTION
		"actual humidity,  a value of -9999 indicates
		that data is not available"
	-- 1.3.6.1.4.1.28507.52.1.6.1.1.3
::= { pdu835XSensorEntry 3 }


pdu835XInputSensor OBJECT-TYPE
	SYNTAX  INTEGER {
			off(0),
			on(1) }
	MAX-ACCESS read-only
	STATUS  current
	DESCRIPTION
		"logical state of input sensor"
	-- 1.3.6.1.4.1.28507.52.1.6.1.1.4
::= { pdu835XSensorEntry 4 }


-- Conformance
--

pdu835XConf OBJECT IDENTIFIER
	-- 1.3.6.1.4.1.28507.52.2
::= { gadsPDU835X 2 }

-- Groups
--

pdu835XGroups OBJECT IDENTIFIER
	-- 1.3.6.1.4.1.28507.52.2.1
::= { pdu835XConf 1 }

-- Compliance
--

pdu835XCompls OBJECT IDENTIFIER
	-- 1.3.6.1.4.1.28507.52.2.2
::= { pdu835XConf 2 }


pdu835XTempEvtSen1 NOTIFICATION-TYPE
	OBJECTS {
		pdu835XTempSensor}
	STATUS  current
	DESCRIPTION
		"temperature limits exceeded"
	-- 1.3.6.1.4.1.28507.52.0.1
::= { events 1 }


pdu835XTempEvtSen2 NOTIFICATION-TYPE
	OBJECTS {
		pdu835XTempSensor}
	STATUS  current
	DESCRIPTION
		"temperature limits exceeded"
	-- 1.3.6.1.4.1.28507.52.0.2
::= { events 2 }


pdu835XHygroEvtSen1 NOTIFICATION-TYPE
	OBJECTS {
		pdu835XHygroSensor}
	STATUS  current
	DESCRIPTION
		"hygro limits exceeded"
	-- 1.3.6.1.4.1.28507.52.0.3
::= { events 3 }


pdu835XHygroEvtSen2 NOTIFICATION-TYPE
	OBJECTS {
		pdu835XHygroSensor}
	STATUS  current
	DESCRIPTION
		"hygro limits exceeded"
	-- 1.3.6.1.4.1.28507.52.0.4
::= { events 4 }


pdu835XInputEvtSen1 NOTIFICATION-TYPE
	OBJECTS {
		pdu835XInputSensor}
	STATUS  current
	DESCRIPTION
		"change of logical input sensor state"
	-- 1.3.6.1.4.1.28507.52.0.5
::= { events 5 }


pdu835XInputEvtSen2 NOTIFICATION-TYPE
	OBJECTS {
		pdu835XInputSensor}
	STATUS  current
	DESCRIPTION
		"change of logical input sensor state"
	-- 1.3.6.1.4.1.28507.52.0.6
::= { events 6 }


pdu835XAmperageEvt1 NOTIFICATION-TYPE
	OBJECTS {
		pdu835XPowerActive,
		pdu835XCurrent,
		pdu835XVoltage,
		pdu835XFrequency,
		pdu835XPowerApparent,
		pdu835XPowerReactive}
	STATUS  current
	DESCRIPTION
		"Event is triggered when a measured
		current is crossing the entered limits"
	-- 1.3.6.1.4.1.28507.52.0.7
	-- 1.3.6.1.4.1.28507.52.0.9
::= { events 9 }


pdu835XAmperageEvt2 NOTIFICATION-TYPE
	OBJECTS {
		pdu835XPowerActive,
		pdu835XCurrent,
		pdu835XVoltage,
		pdu835XFrequency,
		pdu835XPowerApparent,
		pdu835XPowerReactive}
	STATUS  current
	DESCRIPTION
		"Event is triggered when a measured
		current is crossing the entered limits"
	-- 1.3.6.1.4.1.28507.52.0.8
	-- 1.3.6.1.4.1.28507.52.0.10
::= { events 10 }


pdu835XAmperageEvt3 NOTIFICATION-TYPE
	OBJECTS {
		pdu835XPowerActive,
		pdu835XCurrent,
		pdu835XVoltage,
		pdu835XFrequency,
		pdu835XPowerApparent,
		pdu835XPowerReactive}
	STATUS  current
	DESCRIPTION
		"Event is triggered when a measured
		current is crossing the entered limits"
	-- 1.3.6.1.4.1.28507.52.0.9
	-- 1.3.6.1.4.1.28507.52.0.11
::= { events 11 }


pdu835XAmperageEvt4 NOTIFICATION-TYPE
	OBJECTS {
		pdu835XPowerActive,
		pdu835XCurrent,
		pdu835XVoltage,
		pdu835XFrequency,
		pdu835XPowerApparent,
		pdu835XPowerReactive}
	STATUS  current
	DESCRIPTION
		"Event is triggered when a measured
		current is crossing the entered limits"
	-- 1.3.6.1.4.1.28507.52.0.10
	-- 1.3.6.1.4.1.28507.52.0.12
::= { events 12 }


pdu835XAmperageEvt5 NOTIFICATION-TYPE
	OBJECTS {
		pdu835XPowerActive,
		pdu835XCurrent,
		pdu835XVoltage,
		pdu835XFrequency,
		pdu835XPowerApparent,
		pdu835XPowerReactive}
	STATUS  current
	DESCRIPTION
		"Event is triggered when a measured
		current is crossing the entered limits"
	-- 1.3.6.1.4.1.28507.52.0.11
	-- 1.3.6.1.4.1.28507.52.0.13
::= { events 13 }


pdu835XAmperageEvt6 NOTIFICATION-TYPE
	OBJECTS {
		pdu835XPowerActive,
		pdu835XCurrent,
		pdu835XVoltage,
		pdu835XFrequency,
		pdu835XPowerApparent,
		pdu835XPowerReactive}
	STATUS  current
	DESCRIPTION
		"Event is triggered when a measured
		current is crossing the entered limits"
	-- 1.3.6.1.4.1.28507.52.0.12
	-- 1.3.6.1.4.1.28507.52.0.14
::= { events 14 }

pdu835XBasicGroup OBJECT-GROUP
	OBJECTS {
		pdu835XTrapCtrl,
		pdu835XTrapAddr,
		pdu835XActivePowerChan,
		pdu835XChanStatus,
		pdu835XAbsEnergyActive,
		pdu835XPowerActive,
		pdu835XCurrent,
		pdu835XVoltage,
		pdu835XFrequency,
		pdu835XPowerFactor,
		pdu835XPangle,
		pdu835XPowerApparent,
		pdu835XPowerReactive,
		pdu835XAbsEnergyReactive,
		pdu835XAbsEnergyActiveResettable,
		pdu835XAbsEnergyReactiveResettable,
		pdu835XResetTime,
		pdu835XForwEnergyActive,
		pdu835XForwEnergyReactive,
		pdu835XForwEnergyActiveResettable,
		pdu835XForwEnergyReactiveResettable,
		pdu835XRevEnergyActive,
		pdu835XRevEnergyReactive,
		pdu835XRevEnergyActiveResettable,
		pdu835XRevEnergyReactiveResettable,
		pdu835XTempSensor,
		pdu835XHygroSensor,
		pdu835XInputSensor,
		pdu835XBuzzer,
		pdu835XNCurrent3P,
		pdu835XRCurrent3P,
		pdu835XMeasurementBoxConnected,
		pdu835XActivePowerGroups }
	STATUS  current
	DESCRIPTION
		"Basic objects."
	-- 1.3.6.1.4.1.28507.52.2.1.1
::= { pdu835XGroups 1 }

pdu835XNotificationGroup NOTIFICATION-GROUP
	NOTIFICATIONS {
		pdu835XTempEvtSen1,
		pdu835XTempEvtSen2,
		pdu835XHygroEvtSen1,
		pdu835XHygroEvtSen2,
		pdu835XInputEvtSen1,
		pdu835XInputEvtSen2,
		pdu835XAmperageEvt1,
		pdu835XAmperageEvt2,
		pdu835XAmperageEvt3,
		pdu835XAmperageEvt4,
		pdu835XAmperageEvt5,
		pdu835XAmperageEvt6,
		pdu835XMeasurementBoxEvt1,
		pdu835XMeasurementBoxEvt2 }
	STATUS  current
	DESCRIPTION ""
	-- 1.3.6.1.4.1.28507.52.2.1.2
::= { pdu835XGroups 2 }

pdu835XMeasurementBoxConnected OBJECT-TYPE
	SYNTAX  INTEGER {
			disconnected(0),
			connected(1) }
	MAX-ACCESS read-only
	STATUS  current
	DESCRIPTION
		"Shows if the external Measurement Box is connected."
	-- 1.3.6.1.4.1.28507.44.1.5.12
	-- 1.3.6.1.4.1.28507.52.1.5.3.2.1.4
::= { pdu835XEntry 4 }



pdu835XMeasurementBoxEvt1 NOTIFICATION-TYPE
	OBJECTS {
		pdu835XMeasurementBoxConnected}
	STATUS  current
	DESCRIPTION
		"Signals a change of the connection to the
		external Measurement Box."
	-- 1.3.6.1.4.1.28507.44.0.3
	-- 1.3.6.1.4.1.28507.52.0.7
::= { events 7 }


pdu835XMeasurementBoxEvt2 NOTIFICATION-TYPE
	STATUS  current
	DESCRIPTION
		"Signals a change of the connection to the
		external Measurement Box."
	-- 1.3.6.1.4.1.28507.44.0.3
	-- 1.3.6.1.4.1.28507.52.0.8
::= { events 8 }

END
