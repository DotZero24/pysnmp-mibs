GUDEADS-PDU8341-MIB DEFINITIONS ::= BEGIN

IMPORTS
	enterprises,
	MODULE-IDENTITY,
	OBJECT-TYPE,
	NOTIFICATION-TYPE,
	Integer32,
	Unsigned32
		FROM SNMPv2-SMI
	OBJECT-GROUP,
	NOTIFICATION-GROUP
		FROM SNMPv2-CONF;

gudeads MODULE-IDENTITY
	LAST-UPDATED "200703051356Z"	-- Mar 5, 2007 1:56:00 PM
	ORGANIZATION "Gude Analog- und Digitalsysteme GmbH"
	CONTACT-INFO
		"http://www.gudeads.com/"
	DESCRIPTION
		""
	REVISION "200703051356Z"	-- Mar 5, 2007 1:56:00 PM
	DESCRIPTION
		"$Id:$"
	-- 1.3.6.1.4.1.28507
	::= { enterprises 28507 }



pdu8341AirPressureEvtSen NOTIFICATION-TYPE
	OBJECTS {
		pdu8341SensorIndex,
		pdu8341AirPressure}
	STATUS  current
	DESCRIPTION
		"Air Pressure limits exceeded

		"
	-- 1.3.6.1.4.1.28507.65.3.4
	::= { events 4 }


pdu8341DewPtDiffEvtSen NOTIFICATION-TYPE
	OBJECTS {
		pdu8341SensorIndex,
		pdu8341DewPointDiff}
	STATUS  current
	DESCRIPTION
		"Dew Point Difference limits exceeded"
	-- 1.3.6.1.4.1.28507.65.3.5
	::= { events 5 }


pdu8341TempEvtSen NOTIFICATION-TYPE
	OBJECTS {
		pdu8341SensorIndex,
		pdu8341TempSensor}
	STATUS  current
	DESCRIPTION
		"temperature limits exceeded"
	-- 1.3.6.1.4.1.28507.65.3.1
	::= { events 1 }


pdu8341HygroEvtSen NOTIFICATION-TYPE
	OBJECTS {
		pdu8341SensorIndex,
		pdu8341HygroSensor}
	STATUS  current
	DESCRIPTION
		"hygro limits exceeded"
	-- 1.3.6.1.4.1.28507.65.3.2
	::= { events 2 }


pdu8341InputEvtSen NOTIFICATION-TYPE
	OBJECTS {
		pdu8341SensorIndex,
		pdu8341InputSensor}
	STATUS  current
	DESCRIPTION
		"change of logical input sensor state"
	-- 1.3.6.1.4.1.28507.65.3.3
	::= { events 3 }


pdu8341LineAmperageEvt NOTIFICATION-TYPE
	OBJECTS {
		pdu8341PowerIndex,
		pdu8341PowerActive,
		pdu8341Current,
		pdu8341Voltage,
		pdu8341Frequency,
		pdu8341PowerApparent,
		pdu8341PowerReactive}
	STATUS  current
	DESCRIPTION
		"Event is triggered when a measured
		current is crossing the entered limits"
	-- 1.3.6.1.4.1.28507.65.3.6
	::= { events 6 }

gadsPDU8341 OBJECT IDENTIFIER
	-- 1.3.6.1.4.1.28507.65
	::= { gudeads 65 }

-- Notification Types
--

events OBJECT IDENTIFIER
	-- 1.3.6.1.4.1.28507.65.3
	::= { gadsPDU8341 3 }

-- Scalars and Tables
--

pdu8341Objects OBJECT IDENTIFIER
	-- 1.3.6.1.4.1.28507.65.1
	::= { gadsPDU8341 1 }

pdu8341CommonConfig OBJECT IDENTIFIER
	-- 1.3.6.1.4.1.28507.65.1.1
	::= { pdu8341Objects 1 }

pdu8341SNMPaccess OBJECT IDENTIFIER
	-- 1.3.6.1.4.1.28507.65.1.1.1
	::= { pdu8341CommonConfig 1 }

pdu8341TrapCtrl OBJECT-TYPE
	SYNTAX  Integer32 (0..3)
	MAX-ACCESS read-write
	STATUS  current
	DESCRIPTION
		"0 = off
		1 = Ver. 1
		2 = Ver. 2c
		3 = Ver. 3"
	-- 1.3.6.1.4.1.28507.65.1.1.1.1
	::= { pdu8341SNMPaccess 1 }


pdu8341TrapIPTable OBJECT-TYPE
	SYNTAX  SEQUENCE OF Pdu8341TrapIPEntry
	MAX-ACCESS not-accessible
	STATUS  current
	DESCRIPTION
		"list of all Trap receiver"
	-- 1.3.6.1.4.1.28507.65.1.1.1.2
	::= { pdu8341SNMPaccess 2 }


pdu8341TrapIPEntry OBJECT-TYPE
	SYNTAX  Pdu8341TrapIPEntry
	MAX-ACCESS not-accessible
	STATUS  current
	DESCRIPTION
		"an entry containing management
		informations regarding the list of trap
		receivers"
	INDEX {
		pdu8341TrapIPIndex }
	-- 1.3.6.1.4.1.28507.65.1.1.1.2.1
	::= { pdu8341TrapIPTable 1 }


Pdu8341TrapIPEntry ::= SEQUENCE {

	pdu8341TrapIPIndex Integer32,
	pdu8341TrapAddr    OCTET STRING }


pdu8341TrapIPIndex OBJECT-TYPE
	SYNTAX  Integer32 (1..8)
	MAX-ACCESS read-only
	STATUS  current
	DESCRIPTION
		"A unique value, greater than zero, for each receiver slot."
	-- 1.3.6.1.4.1.28507.65.1.1.1.2.1.1
	::= { pdu8341TrapIPEntry 1 }


pdu8341TrapAddr OBJECT-TYPE
	SYNTAX  OCTET STRING (SIZE (0..99))
	MAX-ACCESS read-write
	STATUS  current
	DESCRIPTION
		"DNS name or IP address specifying one Trap receiver slot.
		A port can optionally be specified: 'name:port' An empty
		string disables this slot."
	-- 1.3.6.1.4.1.28507.65.1.1.1.2.1.2
	::= { pdu8341TrapIPEntry 2 }


pdu8341DeviceConfig OBJECT IDENTIFIER
	-- 1.3.6.1.4.1.28507.65.1.2
	::= { pdu8341Objects 2 }

pdu8341IntActors OBJECT IDENTIFIER
	-- 1.3.6.1.4.1.28507.65.1.3
	::= { pdu8341Objects 3 }

pdu8341Buzzer OBJECT-TYPE
	SYNTAX  Integer32 (0..1)
	UNITS	"0 = Off, 1 = On"
	MAX-ACCESS read-write
	STATUS  current
	DESCRIPTION
		"turn Buzzer on and off"
	-- 1.3.6.1.4.1.28507.65.1.3.10
	::= { pdu8341IntActors 10 }


pdu8341ExtActors OBJECT IDENTIFIER
	-- 1.3.6.1.4.1.28507.65.1.4
	::= { pdu8341Objects 4 }

pdu8341IntSensors OBJECT IDENTIFIER
	-- 1.3.6.1.4.1.28507.65.1.5
	::= { pdu8341Objects 5 }

pdu8341PowerChan OBJECT IDENTIFIER
	-- 1.3.6.1.4.1.28507.65.1.5.1
	::= { pdu8341IntSensors 1 }

pdu8341ActivePowerChan OBJECT-TYPE
	SYNTAX  Unsigned32 (1..2)
	MAX-ACCESS read-only
	STATUS  current
	DESCRIPTION
		"Number of suppported Power Channels."
	-- 1.3.6.1.4.1.28507.65.1.5.1.1
	::= { pdu8341PowerChan 1 }


pdu8341PowerTable OBJECT-TYPE
	SYNTAX  SEQUENCE OF Pdu8341PowerEntry
	MAX-ACCESS not-accessible
	STATUS  current
	DESCRIPTION
		"All available Channel Interfaces."
	-- 1.3.6.1.4.1.28507.65.1.5.1.2
	::= { pdu8341PowerChan 2 }


pdu8341PowerEntry OBJECT-TYPE
	SYNTAX  Pdu8341PowerEntry
	MAX-ACCESS not-accessible
	STATUS  current
	DESCRIPTION
		"An entry containing management information
		applicable to a particular Power Channel."
	INDEX {
		pdu8341PowerIndex }
	-- 1.3.6.1.4.1.28507.65.1.5.1.2.1
	::= { pdu8341PowerTable 1 }


Pdu8341PowerEntry ::= SEQUENCE {

	pdu8341PowerIndex                   Integer32,
	pdu8341ChanStatus                   Integer32,
	pdu8341AbsEnergyActive              Unsigned32,
	pdu8341PowerActive                  Integer32,
	pdu8341Current                      Unsigned32,
	pdu8341Voltage                      Unsigned32,
	pdu8341Frequency                    Unsigned32,
	pdu8341PowerFactor                  Integer32,
	pdu8341Pangle                       Integer32,
	pdu8341PowerApparent                Integer32,
	pdu8341PowerReactive                Integer32,
	pdu8341AbsEnergyReactive            Unsigned32,
	pdu8341AbsEnergyActiveResettable    Unsigned32,
	pdu8341AbsEnergyReactiveResettable  Unsigned32,
	pdu8341ResetTime                    Unsigned32,
	pdu8341ForwEnergyActive             Unsigned32,
	pdu8341ForwEnergyReactive           Unsigned32,
	pdu8341ForwEnergyActiveResettable   Unsigned32,
	pdu8341ForwEnergyReactiveResettable Unsigned32,
	pdu8341RevEnergyActive              Unsigned32,
	pdu8341RevEnergyReactive            Unsigned32,
	pdu8341RevEnergyActiveResettable    Unsigned32,
	pdu8341RevEnergyReactiveResettable  Unsigned32,
	pdu8341ResidualCurrent              Unsigned32 }


pdu8341ChanStatus OBJECT-TYPE
	SYNTAX  Integer32 (0..1)
	MAX-ACCESS read-only
	STATUS  current
	DESCRIPTION
		"0 = data not active, 1 = data valid"
	-- 1.3.6.1.4.1.28507.65.1.5.1.2.1.2
	::= { pdu8341PowerEntry 2 }


pdu8341AbsEnergyActive OBJECT-TYPE
	SYNTAX  Unsigned32
	UNITS	"Wh"
	MAX-ACCESS read-only
	STATUS  current
	DESCRIPTION
		"Absolute Active Energy counter."
	-- 1.3.6.1.4.1.28507.65.1.5.1.2.1.3
	::= { pdu8341PowerEntry 3 }


pdu8341PowerActive OBJECT-TYPE
	SYNTAX  Integer32
	UNITS	"W"
	MAX-ACCESS read-only
	STATUS  current
	DESCRIPTION
		"Active Power"
	-- 1.3.6.1.4.1.28507.65.1.5.1.2.1.4
	::= { pdu8341PowerEntry 4 }


pdu8341Current OBJECT-TYPE
	SYNTAX  Unsigned32
	UNITS	"mA"
	MAX-ACCESS read-only
	STATUS  current
	DESCRIPTION
		"Actual Current on Power Channel."
	-- 1.3.6.1.4.1.28507.65.1.5.1.2.1.5
	::= { pdu8341PowerEntry 5 }


pdu8341ResidualCurrent OBJECT-TYPE
	SYNTAX  Unsigned32
	UNITS	"mA"
	MAX-ACCESS read-only
	STATUS  current
	DESCRIPTION
		"Actual Residual Current on Power Channel.
		According Typ A IEC 60755. Only visible on
		models that support this feature."
	-- 1.3.6.1.4.1.28507.65.1.5.1.2.1.24
	::= { pdu8341PowerEntry 24 }


pdu8341Voltage OBJECT-TYPE
	SYNTAX  Unsigned32
	UNITS	"V"
	MAX-ACCESS read-only
	STATUS  current
	DESCRIPTION
		"Actual Voltage on Power Channel"
	-- 1.3.6.1.4.1.28507.65.1.5.1.2.1.6
	::= { pdu8341PowerEntry 6 }


pdu8341Frequency OBJECT-TYPE
	SYNTAX  Unsigned32
	UNITS	"0.01 hz"
	MAX-ACCESS read-only
	STATUS  current
	DESCRIPTION
		"Frequency of Power Channel"
	-- 1.3.6.1.4.1.28507.65.1.5.1.2.1.7
	::= { pdu8341PowerEntry 7 }


pdu8341PowerFactor OBJECT-TYPE
	SYNTAX  Integer32
	UNITS	"0.001"
	MAX-ACCESS read-only
	STATUS  current
	DESCRIPTION
		"Power Factor of Channel between
		-1.0 and 1.00"
	-- 1.3.6.1.4.1.28507.65.1.5.1.2.1.8
	::= { pdu8341PowerEntry 8 }


pdu8341Pangle OBJECT-TYPE
	SYNTAX  Integer32
	UNITS	"0.1 degree"
	MAX-ACCESS read-only
	STATUS  current
	DESCRIPTION
		"Phase Angle between Voltage
		and L Line Current between
		-180.0 and 180.0"
	-- 1.3.6.1.4.1.28507.65.1.5.1.2.1.9
	::= { pdu8341PowerEntry 9 }


pdu8341PowerApparent OBJECT-TYPE
	SYNTAX  Integer32
	UNITS	"VA"
	MAX-ACCESS read-only
	STATUS  current
	DESCRIPTION
		"L Line Mean Apparent Power"
	-- 1.3.6.1.4.1.28507.65.1.5.1.2.1.10
	::= { pdu8341PowerEntry 10 }


pdu8341PowerReactive OBJECT-TYPE
	SYNTAX  Integer32
	UNITS	"VAR"
	MAX-ACCESS read-only
	STATUS  current
	DESCRIPTION
		"L Line Mean Reactive Power"
	-- 1.3.6.1.4.1.28507.65.1.5.1.2.1.11
	::= { pdu8341PowerEntry 11 }


pdu8341AbsEnergyReactive OBJECT-TYPE
	SYNTAX  Unsigned32
	UNITS	"VARh"
	MAX-ACCESS read-only
	STATUS  current
	DESCRIPTION
		"Absolute Reactive Energy counter."
	-- 1.3.6.1.4.1.28507.65.1.5.1.2.1.12
	::= { pdu8341PowerEntry 12 }


pdu8341AbsEnergyActiveResettable OBJECT-TYPE
	SYNTAX  Unsigned32
	UNITS	"Wh"
	MAX-ACCESS read-write
	STATUS  current
	DESCRIPTION
		"Resettable Absolute Active Energy counter.
		Writing '0' resets all resettable counter."
	-- 1.3.6.1.4.1.28507.65.1.5.1.2.1.13
	::= { pdu8341PowerEntry 13 }


pdu8341AbsEnergyReactiveResettable OBJECT-TYPE
	SYNTAX  Unsigned32
	UNITS	"VARh"
	MAX-ACCESS read-only
	STATUS  current
	DESCRIPTION
		"Resettable Absolute Reactive Energy counter."
	-- 1.3.6.1.4.1.28507.65.1.5.1.2.1.14
	::= { pdu8341PowerEntry 14 }


pdu8341ResetTime OBJECT-TYPE
	SYNTAX  Unsigned32
	UNITS	"s"
	MAX-ACCESS read-only
	STATUS  current
	DESCRIPTION
		"Time in seconds since last Energy
		Counter reset."
	-- 1.3.6.1.4.1.28507.65.1.5.1.2.1.15
	::= { pdu8341PowerEntry 15 }


pdu8341ForwEnergyActive OBJECT-TYPE
	SYNTAX  Unsigned32
	UNITS	"Wh"
	MAX-ACCESS read-only
	STATUS  current
	DESCRIPTION
		"Forward Active Energy counter."
	-- 1.3.6.1.4.1.28507.65.1.5.1.2.1.16
	::= { pdu8341PowerEntry 16 }


pdu8341ForwEnergyReactive OBJECT-TYPE
	SYNTAX  Unsigned32
	UNITS	"VARh"
	MAX-ACCESS read-only
	STATUS  current
	DESCRIPTION
		"Forward Reactive Energy counter."
	-- 1.3.6.1.4.1.28507.65.1.5.1.2.1.17
	::= { pdu8341PowerEntry 17 }


pdu8341ForwEnergyActiveResettable OBJECT-TYPE
	SYNTAX  Unsigned32
	UNITS	"Wh"
	MAX-ACCESS read-only
	STATUS  current
	DESCRIPTION
		"Resettable Forward Active Energy counter."
	-- 1.3.6.1.4.1.28507.65.1.5.1.2.1.18
	::= { pdu8341PowerEntry 18 }


pdu8341ForwEnergyReactiveResettable OBJECT-TYPE
	SYNTAX  Unsigned32
	UNITS	"VARh"
	MAX-ACCESS read-only
	STATUS  current
	DESCRIPTION
		"Resettable Forward Reactive Energy counter."
	-- 1.3.6.1.4.1.28507.65.1.5.1.2.1.19
	::= { pdu8341PowerEntry 19 }


pdu8341RevEnergyActive OBJECT-TYPE
	SYNTAX  Unsigned32
	UNITS	"Wh"
	MAX-ACCESS read-only
	STATUS  current
	DESCRIPTION
		"Reverse Active Energy counter."
	-- 1.3.6.1.4.1.28507.65.1.5.1.2.1.20
	::= { pdu8341PowerEntry 20 }


pdu8341RevEnergyReactive OBJECT-TYPE
	SYNTAX  Unsigned32
	UNITS	"VARh"
	MAX-ACCESS read-only
	STATUS  current
	DESCRIPTION
		"Reverse Reactive Energy counter."
	-- 1.3.6.1.4.1.28507.65.1.5.1.2.1.21
	::= { pdu8341PowerEntry 21 }


pdu8341RevEnergyActiveResettable OBJECT-TYPE
	SYNTAX  Unsigned32
	UNITS	"Wh"
	MAX-ACCESS read-only
	STATUS  current
	DESCRIPTION
		"Resettable Reverse Active Energy counter."
	-- 1.3.6.1.4.1.28507.65.1.5.1.2.1.22
	::= { pdu8341PowerEntry 22 }


pdu8341RevEnergyReactiveResettable OBJECT-TYPE
	SYNTAX  Unsigned32
	UNITS	"VARh"
	MAX-ACCESS read-only
	STATUS  current
	DESCRIPTION
		"Resettable Reverse Reactive Energy counter."
	-- 1.3.6.1.4.1.28507.65.1.5.1.2.1.23
	::= { pdu8341PowerEntry 23 }


pdu8341ExtSensors OBJECT IDENTIFIER
	-- 1.3.6.1.4.1.28507.65.1.6
	::= { pdu8341Objects 6 }

pdu8341SensorTable OBJECT-TYPE
	SYNTAX  SEQUENCE OF Pdu8341SensorEntry
	MAX-ACCESS not-accessible
	STATUS  current
	DESCRIPTION ""
	-- 1.3.6.1.4.1.28507.65.1.6.1
	::= { pdu8341ExtSensors 1 }


pdu8341SensorEntry OBJECT-TYPE
	SYNTAX  Pdu8341SensorEntry
	MAX-ACCESS not-accessible
	STATUS  current
	DESCRIPTION ""
	INDEX {
		pdu8341SensorIndex }
	-- 1.3.6.1.4.1.28507.65.1.6.1.1
	::= { pdu8341SensorTable 1 }


Pdu8341SensorEntry ::= SEQUENCE {

	pdu8341SensorIndex  Integer32,
	pdu8341TempSensor   Integer32,
	pdu8341HygroSensor  Integer32,
	pdu8341InputSensor  INTEGER,
	pdu8341AirPressure  Integer32,
	pdu8341DewPoint     Integer32,
	pdu8341DewPointDiff Integer32 }


pdu8341SensorIndex OBJECT-TYPE
	SYNTAX  Integer32 (1..2)
	MAX-ACCESS read-only
	STATUS  current
	DESCRIPTION ""
	-- 1.3.6.1.4.1.28507.65.1.6.1.1.1
	::= { pdu8341SensorEntry 1 }


pdu8341TempSensor OBJECT-TYPE
	SYNTAX  Integer32
	UNITS	"0.1 degree Celsius"
	MAX-ACCESS read-only
	STATUS  current
	DESCRIPTION
		"actual temperature"
	-- 1.3.6.1.4.1.28507.65.1.6.1.1.2
	::= { pdu8341SensorEntry 2 }


pdu8341HygroSensor OBJECT-TYPE
	SYNTAX  Integer32
	UNITS	"0.1 percent humidity"
	MAX-ACCESS read-only
	STATUS  current
	DESCRIPTION
		"actual humidity"
	-- 1.3.6.1.4.1.28507.65.1.6.1.1.3
	::= { pdu8341SensorEntry 3 }


pdu8341InputSensor OBJECT-TYPE
	SYNTAX  INTEGER {
			off(0),
			on(1) }
	MAX-ACCESS read-only
	STATUS  current
	DESCRIPTION
		"logical state of input sensor"
	-- 1.3.6.1.4.1.28507.65.1.6.1.1.4
	::= { pdu8341SensorEntry 4 }


-- Conformance
--

pdu8341Conf OBJECT IDENTIFIER
	-- 1.3.6.1.4.1.28507.65.2
	::= { gadsPDU8341 2 }

-- Groups
--

pdu8341Groups OBJECT IDENTIFIER
	-- 1.3.6.1.4.1.28507.65.2.1
	::= { pdu8341Conf 1 }

-- Compliance
--

pdu8341Compls OBJECT IDENTIFIER
	-- 1.3.6.1.4.1.28507.65.2.2
	::= { pdu8341Conf 2 }

pdu8341BasicGroup OBJECT-GROUP
	OBJECTS {
		pdu8341TrapCtrl,
		pdu8341TrapIPIndex,
		pdu8341TrapAddr,
		pdu8341Buzzer,
		pdu8341ActivePowerChan,
		pdu8341PowerIndex,
		pdu8341ChanStatus,
		pdu8341AbsEnergyActive,
		pdu8341PowerActive,
		pdu8341Current,
		pdu8341Voltage,
		pdu8341Frequency,
		pdu8341PowerFactor,
		pdu8341Pangle,
		pdu8341PowerApparent,
		pdu8341PowerReactive,
		pdu8341AbsEnergyReactive,
		pdu8341AbsEnergyActiveResettable,
		pdu8341AbsEnergyReactiveResettable,
		pdu8341ResetTime,
		pdu8341ForwEnergyActive,
		pdu8341ForwEnergyReactive,
		pdu8341ForwEnergyActiveResettable,
		pdu8341ForwEnergyReactiveResettable,
		pdu8341RevEnergyActive,
		pdu8341RevEnergyReactive,
		pdu8341RevEnergyActiveResettable,
		pdu8341RevEnergyReactiveResettable,
		pdu8341ResidualCurrent,
		pdu8341SensorIndex,
		pdu8341TempSensor,
		pdu8341HygroSensor,
		pdu8341InputSensor,
		pdu8341AirPressure,
		pdu8341DewPoint,
		pdu8341DewPointDiff }
	STATUS  current
	DESCRIPTION
		"Basic objects."
	-- 1.3.6.1.4.1.28507.65.2.1.1
	::= { pdu8341Groups 1 }

pdu8341NotificationGroup NOTIFICATION-GROUP
	NOTIFICATIONS {
		pdu8341TempEvtSen,
		pdu8341HygroEvtSen,
		pdu8341InputEvtSen,
		pdu8341AirPressureEvtSen,
		pdu8341DewPtDiffEvtSen,
		pdu8341LineAmperageEvt }
	STATUS  current
	DESCRIPTION ""
	-- 1.3.6.1.4.1.28507.65.2.1.2
	::= { pdu8341Groups 2 }

pdu8341PowerIndex OBJECT-TYPE
	SYNTAX  Integer32 (1..4)
	MAX-ACCESS read-only
	STATUS  current
	DESCRIPTION
		"Index of Power Channel entries"
	-- 1.3.6.1.4.1.28507.65.1.5.1.2.1.1
	::= { pdu8341PowerEntry 1 }


pdu8341AirPressure OBJECT-TYPE
	SYNTAX  Integer32
	UNITS	"1 hPA (hectopascal) ~ 1 milibar"
	MAX-ACCESS read-only
	STATUS  current
	DESCRIPTION
		"actual air pressure"
	-- 1.3.6.1.4.1.28507.65.1.6.1.1.5
	::= { pdu8341SensorEntry 5 }


pdu8341DewPoint OBJECT-TYPE
	SYNTAX  Integer32
	UNITS	"0.1 degree Celsius"
	MAX-ACCESS read-only
	STATUS  current
	DESCRIPTION
		"dew point for actual temperature and humidity"
	-- 1.3.6.1.4.1.28507.65.1.6.1.1.6
	::= { pdu8341SensorEntry 6 }


pdu8341DewPointDiff OBJECT-TYPE
	SYNTAX  Integer32
	UNITS	"0.1 degree Celsius"
	MAX-ACCESS read-only
	STATUS  current
	DESCRIPTION
		"difference between dew point and actual
		temperature (Temp - DewPoint)"
	-- 1.3.6.1.4.1.28507.65.1.6.1.1.7
	::= { pdu8341SensorEntry 7 }


END
