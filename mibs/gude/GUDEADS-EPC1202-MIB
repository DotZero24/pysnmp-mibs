GUDEADS-EPC1202-MIB DEFINITIONS ::= BEGIN

IMPORTS
	enterprises,
	MODULE-IDENTITY,
	OBJECT-TYPE,
	NOTIFICATION-TYPE,
	Gauge32,
	Integer32,
	Unsigned32
		FROM SNMPv2-SMI
	OBJECT-GROUP,
	NOTIFICATION-GROUP
		FROM SNMPv2-CONF;

gudeads MODULE-IDENTITY
	LAST-UPDATED "200703051356Z"	-- Mar 5, 2007 1:56:00 PM
	ORGANIZATION "Gude Analog- und Digitalsysteme GmbH"
	CONTACT-INFO
		"http://www.gudeads.com/"
	DESCRIPTION
		""
	REVISION "200703051356Z"	-- Mar 5, 2007 1:56:00 PM
	DESCRIPTION
		"$Id:$"
	-- 1.3.6.1.4.1.28507
	::= { enterprises 28507 }


gadsEPC1202 OBJECT IDENTIFIER
	-- 1.3.6.1.4.1.28507.43
	::= { gudeads 43 }

-- Notification Types
--

events OBJECT IDENTIFIER
	-- 1.3.6.1.4.1.28507.43.3
	::= { gadsEPC1202 3 }

-- Scalars and Tables
--

epc1202Objects OBJECT IDENTIFIER
	-- 1.3.6.1.4.1.28507.43.1
	::= { gadsEPC1202 1 }

epc1202CommonConfig OBJECT IDENTIFIER
	-- 1.3.6.1.4.1.28507.43.1.1
	::= { epc1202Objects 1 }

epc1202SNMPaccess OBJECT IDENTIFIER
	-- 1.3.6.1.4.1.28507.43.1.1.1
	::= { epc1202CommonConfig 1 }

epc1202TrapCtrl OBJECT-TYPE
	SYNTAX  Integer32 (0..3)
	MAX-ACCESS read-write
	STATUS  current
	DESCRIPTION
		"0 = off
		1 = Ver. 1
		2 = Ver. 2c
		3 = Ver. 3"
	-- 1.3.6.1.4.1.28507.43.1.1.1.1
	::= { epc1202SNMPaccess 1 }


epc1202TrapIPTable OBJECT-TYPE
	SYNTAX  SEQUENCE OF Epc1202TrapIPEntry
	MAX-ACCESS not-accessible
	STATUS  current
	DESCRIPTION
		"list of all Trap receiver"
	-- 1.3.6.1.4.1.28507.43.1.1.1.2
	::= { epc1202SNMPaccess 2 }


epc1202TrapIPEntry OBJECT-TYPE
	SYNTAX  Epc1202TrapIPEntry
	MAX-ACCESS not-accessible
	STATUS  current
	DESCRIPTION
		"an entry containing management
		informations regarding the list of trap
		receivers"
	INDEX {
		epc1202TrapIPIndex }
	-- 1.3.6.1.4.1.28507.43.1.1.1.2.1
	::= { epc1202TrapIPTable 1 }


Epc1202TrapIPEntry ::= SEQUENCE {

	epc1202TrapIPIndex Integer32,
	epc1202TrapAddr    OCTET STRING }


epc1202TrapIPIndex OBJECT-TYPE
	SYNTAX  Integer32 (1..8)
	MAX-ACCESS read-only
	STATUS  current
	DESCRIPTION
		"A unique value, greater than zero, for each receiver slot."
	-- 1.3.6.1.4.1.28507.43.1.1.1.2.1.1
	::= { epc1202TrapIPEntry 1 }


epc1202TrapAddr OBJECT-TYPE
	SYNTAX  OCTET STRING (SIZE (0..99))
	MAX-ACCESS read-write
	STATUS  current
	DESCRIPTION
		"DNS name or IP address specifying one Trap receiver slot.
		A port can optionally be specified: 'name:port' An empty
		string disables this slot."
	-- 1.3.6.1.4.1.28507.43.1.1.1.2.1.2
	::= { epc1202TrapIPEntry 2 }


epc1202DeviceConfig OBJECT IDENTIFIER
	-- 1.3.6.1.4.1.28507.43.1.2
	::= { epc1202Objects 2 }

epc1202IntActors OBJECT IDENTIFIER
	-- 1.3.6.1.4.1.28507.43.1.3
	::= { epc1202Objects 3 }

epc1202relayports OBJECT IDENTIFIER
	-- 1.3.6.1.4.1.28507.43.1.3.1
	::= { epc1202IntActors 1 }

epc1202portNumber OBJECT-TYPE
	SYNTAX  Integer32 (1..4)
	MAX-ACCESS read-only
	STATUS  current
	DESCRIPTION
		"The number of Relay Ports"
	-- 1.3.6.1.4.1.28507.43.1.3.1.1
	::= { epc1202relayports 1 }


-- the Interfaces table
-- The Interfaces table contains information on the entity's
-- interfaces.  Each sub-layer below the internetwork-layer
-- of a network interface is considered to be an interface.

epc1202portTable OBJECT-TYPE
	SYNTAX  SEQUENCE OF Epc1202portEntry
	MAX-ACCESS not-accessible
	STATUS  current
	DESCRIPTION
		"list of all EPC Relay Ports"
	-- 1.3.6.1.4.1.28507.43.1.3.1.2
	::= { epc1202relayports 2 }


epc1202portEntry OBJECT-TYPE
	SYNTAX  Epc1202portEntry
	MAX-ACCESS not-accessible
	STATUS  current
	DESCRIPTION
		"An entry containing management information applicable to a
		particular relay port."
	INDEX {
		epc1202PortIndex }
	-- 1.3.6.1.4.1.28507.43.1.3.1.2.1
	::= { epc1202portTable 1 }


Epc1202portEntry ::= SEQUENCE {

	epc1202PortIndex        Integer32,
	epc1202PortName         OCTET STRING,
	epc1202PortState        INTEGER,
	epc1202PortSwitchCount  Integer32,
	epc1202PortStartupMode  INTEGER,
	epc1202PortStartupDelay Integer32,
	epc1202PortRepowerTime  Integer32 }


epc1202PortIndex OBJECT-TYPE
	SYNTAX  Integer32 (1..4)
	MAX-ACCESS read-only
	STATUS  current
	DESCRIPTION
		"A unique value, greater than zero, for each Relay Port."
	-- 1.3.6.1.4.1.28507.43.1.3.1.2.1.1
	::= { epc1202portEntry 1 }


epc1202PortName OBJECT-TYPE
	SYNTAX  OCTET STRING (SIZE (0..15))
	MAX-ACCESS read-write
	STATUS  current
	DESCRIPTION
		"A textual string containing name of a Relay Port."
	-- 1.3.6.1.4.1.28507.43.1.3.1.2.1.2
	::= { epc1202portEntry 2 }


epc1202PortState OBJECT-TYPE
	SYNTAX  INTEGER {
			off(0),
			on(1) }
	MAX-ACCESS read-write
	STATUS  current
	DESCRIPTION
		"current state of a Relay Port"
	-- 1.3.6.1.4.1.28507.43.1.3.1.2.1.3
	::= { epc1202portEntry 3 }


epc1202PortSwitchCount OBJECT-TYPE
	SYNTAX  Integer32
	MAX-ACCESS read-only
	STATUS  current
	DESCRIPTION
		"The total number of switch actions ocurred on a Relay Port.
		Does not count switch commands which will not switch
		the ralay state, so just real relay switches are displayed here."
	-- 1.3.6.1.4.1.28507.43.1.3.1.2.1.4
	::= { epc1202portEntry 4 }


epc1202PortStartupMode OBJECT-TYPE
	SYNTAX  INTEGER {
			off(0),
			on(1),
			laststate(2) }
	MAX-ACCESS read-write
	STATUS  current
	DESCRIPTION
		"set Mode of startup sequence (off, on , remember last state)"
	DEFVAL { off }
	-- 1.3.6.1.4.1.28507.43.1.3.1.2.1.5
	::= { epc1202portEntry 5 }


epc1202PortStartupDelay OBJECT-TYPE
	SYNTAX  Integer32
	UNITS	"seconds"
	MAX-ACCESS read-write
	STATUS  current
	DESCRIPTION
		"Delay in sec for startup action"
	DEFVAL { 0 }
	-- 1.3.6.1.4.1.28507.43.1.3.1.2.1.6
	::= { epc1202portEntry 6 }


epc1202PortRepowerTime OBJECT-TYPE
	SYNTAX  Integer32 (0..65535)
	UNITS	"seconds"
	MAX-ACCESS read-write
	STATUS  current
	DESCRIPTION
		"Delay in sec for repower port after switching off"
	DEFVAL { 0 }
	-- 1.3.6.1.4.1.28507.43.1.3.1.2.1.7
	::= { epc1202portEntry 7 }


epc1202ExtActors OBJECT IDENTIFIER
	-- 1.3.6.1.4.1.28507.43.1.4
	::= { epc1202Objects 4 }

epc1202IntSensors OBJECT IDENTIFIER
	-- 1.3.6.1.4.1.28507.43.1.5
	::= { epc1202Objects 5 }

epc1202PowerChan OBJECT IDENTIFIER
	-- 1.3.6.1.4.1.28507.43.1.5.1
	::= { epc1202IntSensors 1 }

epc1202ActivePowerChan OBJECT-TYPE
	SYNTAX  Unsigned32 (1)
	MAX-ACCESS read-only
	STATUS  current
	DESCRIPTION
		"Number of suppported Power Channels."
	-- 1.3.6.1.4.1.28507.43.1.5.1.1
	::= { epc1202PowerChan 1 }


epc1202PowerTable OBJECT-TYPE
	SYNTAX  SEQUENCE OF Epc1202PowerEntry
	MAX-ACCESS not-accessible
	STATUS  current
	DESCRIPTION
		"All available Channel Interfaces."
	-- 1.3.6.1.4.1.28507.43.1.5.1.2
	::= { epc1202PowerChan 2 }


epc1202PowerEntry OBJECT-TYPE
	SYNTAX  Epc1202PowerEntry
	MAX-ACCESS not-accessible
	STATUS  current
	DESCRIPTION
		"An entry containing management information
		applicable to a particular Power Channel."
	INDEX {
		epc1202PowerIndex }
	-- 1.3.6.1.4.1.28507.43.1.5.1.2.1
	::= { epc1202PowerTable 1 }


Epc1202PowerEntry ::= SEQUENCE {

	epc1202PowerIndex                   Integer32,
	epc1202ChanStatus                   Integer32,
	epc1202AbsEnergyActive              Gauge32,
	epc1202PowerActive                  Integer32,
	epc1202Current                      Gauge32,
	epc1202Voltage                      Gauge32,
	epc1202Frequency                    Gauge32,
	epc1202PowerFactor                  Integer32,
	epc1202Pangle                       Integer32,
	epc1202PowerApparent                Integer32,
	epc1202PowerReactive                Integer32,
	epc1202AbsEnergyReactive            Gauge32,
	epc1202AbsEnergyActiveResettable    Gauge32,
	epc1202AbsEnergyReactiveResettable  Gauge32,
	epc1202ResetTime                    Gauge32,
	epc1202ForwEnergyActive             Gauge32,
	epc1202ForwEnergyReactive           Gauge32,
	epc1202ForwEnergyActiveResettable   Gauge32,
	epc1202ForwEnergyReactiveResettable Gauge32,
	epc1202RevEnergyActive              Gauge32,
	epc1202RevEnergyReactive            Gauge32,
	epc1202RevEnergyActiveResettable    Gauge32,
	epc1202RevEnergyReactiveResettable  Gauge32 }


epc1202PowerIndex OBJECT-TYPE
	SYNTAX  Integer32 (1)
	MAX-ACCESS read-only
	STATUS  current
	DESCRIPTION
		"Index of Power Channel entries"
	-- 1.3.6.1.4.1.28507.43.1.5.1.2.1.1
	::= { epc1202PowerEntry 1 }


epc1202ChanStatus OBJECT-TYPE
	SYNTAX  Integer32 (0..1)
	MAX-ACCESS read-only
	STATUS  current
	DESCRIPTION
		"0 = data not active, 1 = data valid"
	-- 1.3.6.1.4.1.28507.43.1.5.1.2.1.2
	::= { epc1202PowerEntry 2 }


epc1202PowerActive OBJECT-TYPE
	SYNTAX  Integer32
	UNITS	"W"
	MAX-ACCESS read-only
	STATUS  current
	DESCRIPTION
		"Active Power"
	-- 1.3.6.1.4.1.28507.43.1.5.1.2.1.4
	::= { epc1202PowerEntry 4 }


epc1202PowerFactor OBJECT-TYPE
	SYNTAX  Integer32
	UNITS	"0.001"
	MAX-ACCESS read-only
	STATUS  current
	DESCRIPTION
		"Power Factor of Channel between
		-1.0 and 1.00"
	-- 1.3.6.1.4.1.28507.43.1.5.1.2.1.8
	::= { epc1202PowerEntry 8 }


epc1202Pangle OBJECT-TYPE
	SYNTAX  Integer32
	UNITS	"0.1 degree"
	MAX-ACCESS read-only
	STATUS  current
	DESCRIPTION
		"Phase Angle between Voltage
		and L Line Current between
		-180.0 and 180.0"
	-- 1.3.6.1.4.1.28507.43.1.5.1.2.1.9
	::= { epc1202PowerEntry 9 }


epc1202PowerApparent OBJECT-TYPE
	SYNTAX  Integer32
	UNITS	"VA"
	MAX-ACCESS read-only
	STATUS  current
	DESCRIPTION
		"L Line Mean Apparent Power"
	-- 1.3.6.1.4.1.28507.43.1.5.1.2.1.10
	::= { epc1202PowerEntry 10 }


epc1202PowerReactive OBJECT-TYPE
	SYNTAX  Integer32
	UNITS	"VAR"
	MAX-ACCESS read-only
	STATUS  current
	DESCRIPTION
		"L Line Mean Reactive Power"
	-- 1.3.6.1.4.1.28507.43.1.5.1.2.1.11
	::= { epc1202PowerEntry 11 }


epc1202OVPTable OBJECT-TYPE
	SYNTAX  SEQUENCE OF Epc1202OVPEntry
	MAX-ACCESS not-accessible
	STATUS  current
	DESCRIPTION
		"Overvoltage Protection Table"
	-- 1.3.6.1.4.1.28507.43.1.5.2
	::= { epc1202IntSensors 2 }


epc1202OVPEntry OBJECT-TYPE
	SYNTAX  Epc1202OVPEntry
	MAX-ACCESS not-accessible
	STATUS  current
	DESCRIPTION ""
	INDEX {
		epc1202OVPIndex }
	-- 1.3.6.1.4.1.28507.43.1.5.2.1
	::= { epc1202OVPTable 1 }


Epc1202OVPEntry ::= SEQUENCE {

	epc1202OVPIndex  Integer32,
	epc1202OVPStatus INTEGER }


epc1202OVPIndex OBJECT-TYPE
	SYNTAX  Integer32 (1)
	MAX-ACCESS read-only
	STATUS  current
	DESCRIPTION ""
	-- 1.3.6.1.4.1.28507.43.1.5.2.1.1
	::= { epc1202OVPEntry 1 }


epc1202OVPStatus OBJECT-TYPE
	SYNTAX  INTEGER {
			unknown(2),
			ok(1),
			failure(0) }
	MAX-ACCESS read-only
	STATUS  current
	DESCRIPTION
		"shows the status of the
		built-in Overvoltage Protection"
	-- 1.3.6.1.4.1.28507.43.1.5.2.1.2
	::= { epc1202OVPEntry 2 }


epc1202ExtSensors OBJECT IDENTIFIER
	-- 1.3.6.1.4.1.28507.43.1.6
	::= { epc1202Objects 6 }

epc1202SensorTable OBJECT-TYPE
	SYNTAX  SEQUENCE OF Epc1202SensorEntry
	MAX-ACCESS not-accessible
	STATUS  current
	DESCRIPTION ""
	-- 1.3.6.1.4.1.28507.43.1.6.1
	::= { epc1202ExtSensors 1 }


epc1202SensorEntry OBJECT-TYPE
	SYNTAX  Epc1202SensorEntry
	MAX-ACCESS not-accessible
	STATUS  current
	DESCRIPTION ""
	INDEX {
		epc1202SensorIndex }
	-- 1.3.6.1.4.1.28507.43.1.6.1.1
	::= { epc1202SensorTable 1 }


Epc1202SensorEntry ::= SEQUENCE {

	epc1202SensorIndex  Integer32,
	epc1202TempSensor   Integer32,
	epc1202HygroSensor  Integer32,
	epc1202InputSensor  INTEGER,
	epc1202AirPressure  Integer32,
	epc1202DewPoint     Integer32,
	epc1202DewPointDiff Integer32 }


epc1202SensorIndex OBJECT-TYPE
	SYNTAX  Integer32 (1)
	MAX-ACCESS read-only
	STATUS  current
	DESCRIPTION ""
	-- 1.3.6.1.4.1.28507.43.1.6.1.1.1
	::= { epc1202SensorEntry 1 }


epc1202TempSensor OBJECT-TYPE
	SYNTAX  Integer32
	UNITS	"0.1 degree Celsius"
	MAX-ACCESS read-only
	STATUS  current
	DESCRIPTION
		"actual temperature"
	-- 1.3.6.1.4.1.28507.43.1.6.1.1.2
	::= { epc1202SensorEntry 2 }


epc1202HygroSensor OBJECT-TYPE
	SYNTAX  Integer32
	UNITS	"0.1 percent humidity"
	MAX-ACCESS read-only
	STATUS  current
	DESCRIPTION
		"actual humidity"
	-- 1.3.6.1.4.1.28507.43.1.6.1.1.3
	::= { epc1202SensorEntry 3 }


epc1202InputSensor OBJECT-TYPE
	SYNTAX  INTEGER {
			off(0),
			on(1) }
	MAX-ACCESS read-only
	STATUS  current
	DESCRIPTION
		"logical state of input sensor"
	-- 1.3.6.1.4.1.28507.43.1.6.1.1.4
	::= { epc1202SensorEntry 4 }


-- Conformance
--

epc1202Conf OBJECT IDENTIFIER
	-- 1.3.6.1.4.1.28507.43.2
	::= { gadsEPC1202 2 }

-- Groups
--

epc1202Groups OBJECT IDENTIFIER
	-- 1.3.6.1.4.1.28507.43.2.1
	::= { epc1202Conf 1 }

-- Compliance
--

epc1202Compls OBJECT IDENTIFIER
	-- 1.3.6.1.4.1.28507.43.2.2
	::= { epc1202Conf 2 }


epc1202SwitchEvtPort NOTIFICATION-TYPE
	OBJECTS {
		epc1202PortIndex,
		epc1202PortName,
		epc1202PortState,
		epc1202PortSwitchCount}
	STATUS  current
	DESCRIPTION
		"Event is triggered when a port is switched"
	-- 1.3.6.1.4.1.28507.43.3.1
	::= { events 1 }

epc1202BasicGroup OBJECT-GROUP
	OBJECTS {
		epc1202TrapCtrl,
		epc1202TrapIPIndex,
		epc1202TrapAddr,
		epc1202portNumber,
		epc1202PortIndex,
		epc1202PortName,
		epc1202PortState,
		epc1202PortSwitchCount,
		epc1202PortStartupMode,
		epc1202PortStartupDelay,
		epc1202PortRepowerTime,
		epc1202ActivePowerChan,
		epc1202PowerIndex,
		epc1202ChanStatus,
		epc1202AbsEnergyActive,
		epc1202PowerActive,
		epc1202Current,
		epc1202Voltage,
		epc1202Frequency,
		epc1202PowerFactor,
		epc1202Pangle,
		epc1202PowerApparent,
		epc1202PowerReactive,
		epc1202AbsEnergyReactive,
		epc1202AbsEnergyActiveResettable,
		epc1202AbsEnergyReactiveResettable,
		epc1202ResetTime,
		epc1202ForwEnergyActive,
		epc1202ForwEnergyReactive,
		epc1202ForwEnergyActiveResettable,
		epc1202ForwEnergyReactiveResettable,
		epc1202RevEnergyActive,
		epc1202RevEnergyReactive,
		epc1202RevEnergyActiveResettable,
		epc1202RevEnergyReactiveResettable,
		epc1202OVPIndex,
		epc1202OVPStatus,
		epc1202SensorIndex,
		epc1202TempSensor,
		epc1202HygroSensor,
		epc1202InputSensor,
		epc1202AirPressure,
		epc1202DewPoint,
		epc1202DewPointDiff }
	STATUS  current
	DESCRIPTION
		"Basic objects."
	-- 1.3.6.1.4.1.28507.43.2.1.1
	::= { epc1202Groups 1 }

epc1202NotificationGroup NOTIFICATION-GROUP
	NOTIFICATIONS {
		epc1202SwitchEvtPort,
		epc1202TempEvtSen,
		epc1202InputEvtSen,
		epc1202AirPressureEvtSen,
		epc1202DewPtDiffEvtSen,
		epc1202OVPEvt,
		epc1202LineAmperageEvt,
		epc1202HygroEvtSen }
	STATUS  current
	DESCRIPTION
		""
	-- 1.3.6.1.4.1.28507.43.2.1.2
	::= { epc1202Groups 2 }

epc1202AbsEnergyActive OBJECT-TYPE
	SYNTAX  Gauge32
	UNITS	"Wh"
	MAX-ACCESS read-only
	STATUS  current
	DESCRIPTION
		"Absolute Active Energy counter."
	-- 1.3.6.1.4.1.28507.43.1.5.1.2.1.3
	::= { epc1202PowerEntry 3 }


epc1202Current OBJECT-TYPE
	SYNTAX  Gauge32
	UNITS	"mA"
	MAX-ACCESS read-only
	STATUS  current
	DESCRIPTION
		"Actual Curent on Power Channel."
	-- 1.3.6.1.4.1.28507.43.1.5.1.2.1.5
	::= { epc1202PowerEntry 5 }


epc1202Voltage OBJECT-TYPE
	SYNTAX  Gauge32
	UNITS	"V"
	MAX-ACCESS read-only
	STATUS  current
	DESCRIPTION
		"Actual Voltage on Power Channel"
	-- 1.3.6.1.4.1.28507.43.1.5.1.2.1.6
	::= { epc1202PowerEntry 6 }


epc1202Frequency OBJECT-TYPE
	SYNTAX  Gauge32
	UNITS	"0.01 hz"
	MAX-ACCESS read-only
	STATUS  current
	DESCRIPTION
		"Frequency of Power Channel"
	-- 1.3.6.1.4.1.28507.43.1.5.1.2.1.7
	::= { epc1202PowerEntry 7 }


epc1202AbsEnergyReactive OBJECT-TYPE
	SYNTAX  Gauge32
	UNITS	"VARh"
	MAX-ACCESS read-only
	STATUS  current
	DESCRIPTION
		"Absolute Reactive Energy counter."
	-- 1.3.6.1.4.1.28507.43.1.5.1.2.1.12
	::= { epc1202PowerEntry 12 }


epc1202AbsEnergyActiveResettable OBJECT-TYPE
	SYNTAX  Gauge32
	UNITS	"Wh"
	MAX-ACCESS read-write
	STATUS  current
	DESCRIPTION
		"Resettable Absolute Active Energy counter.
		Writing '0' resets all resettable counter."
	-- 1.3.6.1.4.1.28507.43.1.5.1.2.1.13
	::= { epc1202PowerEntry 13 }


epc1202AbsEnergyReactiveResettable OBJECT-TYPE
	SYNTAX  Gauge32
	UNITS	"VARh"
	MAX-ACCESS read-only
	STATUS  current
	DESCRIPTION
		"Resettable Absolute Reactive Energy counter."
	-- 1.3.6.1.4.1.28507.43.1.5.1.2.1.14
	::= { epc1202PowerEntry 14 }


epc1202ResetTime OBJECT-TYPE
	SYNTAX  Gauge32
	UNITS	"s"
	MAX-ACCESS read-only
	STATUS  current
	DESCRIPTION
		"Time in seconds since last Energy
		Counter reset."
	-- 1.3.6.1.4.1.28507.43.1.5.1.2.1.15
	::= { epc1202PowerEntry 15 }


epc1202ForwEnergyActive OBJECT-TYPE
	SYNTAX  Gauge32
	UNITS	"Wh"
	MAX-ACCESS read-only
	STATUS  current
	DESCRIPTION
		"Forward Active Energy counter."
	-- 1.3.6.1.4.1.28507.43.1.5.1.2.1.16
	::= { epc1202PowerEntry 16 }


epc1202ForwEnergyReactive OBJECT-TYPE
	SYNTAX  Gauge32
	UNITS	"VARh"
	MAX-ACCESS read-only
	STATUS  current
	DESCRIPTION
		"Forward Reactive Energy counter."
	-- 1.3.6.1.4.1.28507.43.1.5.1.2.1.17
	::= { epc1202PowerEntry 17 }


epc1202ForwEnergyActiveResettable OBJECT-TYPE
	SYNTAX  Gauge32
	UNITS	"Wh"
	MAX-ACCESS read-only
	STATUS  current
	DESCRIPTION
		"Resettable Forward Active Energy counter."
	-- 1.3.6.1.4.1.28507.43.1.5.1.2.1.18
	::= { epc1202PowerEntry 18 }


epc1202ForwEnergyReactiveResettable OBJECT-TYPE
	SYNTAX  Gauge32
	UNITS	"VARh"
	MAX-ACCESS read-only
	STATUS  current
	DESCRIPTION
		"Resettable Forward Reactive Energy counter."
	-- 1.3.6.1.4.1.28507.43.1.5.1.2.1.19
	::= { epc1202PowerEntry 19 }


epc1202RevEnergyActive OBJECT-TYPE
	SYNTAX  Gauge32
	UNITS	"Wh"
	MAX-ACCESS read-only
	STATUS  current
	DESCRIPTION
		"Reverse Active Energy counter."
	-- 1.3.6.1.4.1.28507.43.1.5.1.2.1.20
	::= { epc1202PowerEntry 20 }


epc1202RevEnergyReactive OBJECT-TYPE
	SYNTAX  Gauge32
	UNITS	"VARh"
	MAX-ACCESS read-only
	STATUS  current
	DESCRIPTION
		"Reverse Reactive Energy counter."
	-- 1.3.6.1.4.1.28507.43.1.5.1.2.1.21
	::= { epc1202PowerEntry 21 }


epc1202RevEnergyActiveResettable OBJECT-TYPE
	SYNTAX  Gauge32
	UNITS	"Wh"
	MAX-ACCESS read-only
	STATUS  current
	DESCRIPTION
		"Resettable Reverse Active Energy counter."
	-- 1.3.6.1.4.1.28507.43.1.5.1.2.1.22
	::= { epc1202PowerEntry 22 }


epc1202RevEnergyReactiveResettable OBJECT-TYPE
	SYNTAX  Gauge32
	UNITS	"VARh"
	MAX-ACCESS read-only
	STATUS  current
	DESCRIPTION
		"Resettable Reverse Reactive Energy counter."
	-- 1.3.6.1.4.1.28507.43.1.5.1.2.1.23
	::= { epc1202PowerEntry 23 }


epc1202AirPressure OBJECT-TYPE
	SYNTAX  Integer32
	UNITS	"1 hPA (hectopascal) ~ 1 milibar"
	MAX-ACCESS read-only
	STATUS  current
	DESCRIPTION
		"actual air pressure"
	-- 1.3.6.1.4.1.28507.43.1.6.1.1.5
	::= { epc1202SensorEntry 5 }


epc1202DewPoint OBJECT-TYPE
	SYNTAX  Integer32
	UNITS	"0.1 degree Celsius"
	MAX-ACCESS read-only
	STATUS  current
	DESCRIPTION
		"dew point for actual temperature and humidity"
	-- 1.3.6.1.4.1.28507.43.1.6.1.1.6
	::= { epc1202SensorEntry 6 }


epc1202DewPointDiff OBJECT-TYPE
	SYNTAX  Integer32
	UNITS	"0.1 degree Celsius"
	MAX-ACCESS read-only
	STATUS  current
	DESCRIPTION
		"difference between dew point and actual
		temperature (Temp - DewPoint)"
	-- 1.3.6.1.4.1.28507.43.1.6.1.1.7
	::= { epc1202SensorEntry 7 }



epc1202TempEvtSen NOTIFICATION-TYPE
	OBJECTS {
		epc1202SensorIndex,
		epc1202TempSensor}
	STATUS  current
	DESCRIPTION
		"temperature limits exceeded"
	-- 1.3.6.1.4.1.28507.43.3.3
	-- 1.3.6.1.4.1.28507.43.3.2
	::= { events 2 }


epc1202HygroEvtSen NOTIFICATION-TYPE
	OBJECTS {
		epc1202SensorIndex,
		epc1202HygroSensor}
	STATUS  current
	DESCRIPTION
		"hygro limits exceeded"
	-- 1.3.6.1.4.1.28507.43.3.4
	-- 1.3.6.1.4.1.28507.43.3.3
	::= { events 3 }


epc1202InputEvtSen NOTIFICATION-TYPE
	OBJECTS {
		epc1202SensorIndex,
		epc1202InputSensor}
	STATUS  current
	DESCRIPTION
		"change of logical input sensor state"
	-- 1.3.6.1.4.1.28507.43.3.5
	-- 1.3.6.1.4.1.28507.43.3.4
	::= { events 4 }


epc1202AirPressureEvtSen NOTIFICATION-TYPE
	OBJECTS {
		epc1202SensorIndex,
		epc1202AirPressure}
	STATUS  current
	DESCRIPTION
		"Air Pressure limits exceeded"
	-- 1.3.6.1.4.1.28507.43.3.6
	-- 1.3.6.1.4.1.28507.43.3.5
	::= { events 5 }


epc1202DewPtDiffEvtSen NOTIFICATION-TYPE
	OBJECTS {
		epc1202SensorIndex,
		epc1202DewPointDiff}
	STATUS  current
	DESCRIPTION
		"Dew Point Difference limits exceeded"
	-- 1.3.6.1.4.1.28507.43.3.7
	-- 1.3.6.1.4.1.28507.43.3.6
	::= { events 6 }


epc1202OVPEvt NOTIFICATION-TYPE
	OBJECTS {
		epc1202OVPStatus}
	STATUS  current
	DESCRIPTION
		"Event is triggered when the OVP status changes"
	-- 1.3.6.1.4.1.28507.43.3.8
	-- 1.3.6.1.4.1.28507.43.3.7
	::= { events 7 }


epc1202LineAmperageEvt NOTIFICATION-TYPE
	OBJECTS {
		epc1202PowerIndex,
		epc1202PowerActive,
		epc1202Current,
		epc1202Voltage,
		epc1202Frequency,
		epc1202PowerApparent,
		epc1202PowerReactive}
	STATUS  current
	DESCRIPTION
		"Event is triggered when a measured
		current is crossing the entered limits"
	-- 1.3.6.1.4.1.28507.43.3.9
	-- 1.3.6.1.4.1.28507.43.3.8
	::= { events 8 }

END
