GUDEADS-EPC1104-MIB DEFINITIONS ::= BEGIN

IMPORTS
	enterprises,
	MODULE-IDENTITY,
	OBJECT-TYPE,
	NOTIFICATION-TYPE,
	Integer32
		FROM SNMPv2-SMI
	OBJECT-GROUP,
	NOTIFICATION-GROUP
		FROM SNMPv2-CONF;

gudeads MODULE-IDENTITY
	LAST-UPDATED "200703051356Z"	-- Mar 5, 2007 1:56:00 PM
	ORGANIZATION "Gude Analog- und Digitalsysteme GmbH"
	CONTACT-INFO
		"http://www.gudeads.com/"
	DESCRIPTION
		""
	REVISION "200703051356Z"	-- Mar 5, 2007 1:56:00 PM
	DESCRIPTION
		"$Id:$"
	-- 1.3.6.1.4.1.28507
	::= { enterprises 28507 }


gadsEPC1104 OBJECT IDENTIFIER
	-- 1.3.6.1.4.1.28507.68
	::= { gudeads 68 }

-- Scalars and Tables
--

epc1104Objects OBJECT IDENTIFIER
	-- 1.3.6.1.4.1.28507.68.1
	::= { gadsEPC1104 1 }

epc1104CommonConfig OBJECT IDENTIFIER
	-- 1.3.6.1.4.1.28507.68.1.1
	::= { epc1104Objects 1 }

epc1104SNMPaccess OBJECT IDENTIFIER
	-- 1.3.6.1.4.1.28507.68.1.1.1
	::= { epc1104CommonConfig 1 }

epc1104TrapCtrl OBJECT-TYPE
	SYNTAX  Integer32 (0..3)
	MAX-ACCESS read-write
	STATUS  current
	DESCRIPTION
		"0 = off
		1 = Ver. 1
		2 = Ver. 2c
		3 = Ver. 3"
	-- 1.3.6.1.4.1.28507.68.1.1.1.1
	::= { epc1104SNMPaccess 1 }


epc1104TrapIPTable OBJECT-TYPE
	SYNTAX  SEQUENCE OF Epc8TrapIPEntry
	MAX-ACCESS not-accessible
	STATUS  current
	DESCRIPTION
		"list of all Trap receiver"
	-- 1.3.6.1.4.1.28507.68.1.1.1.2
	::= { epc1104SNMPaccess 2 }


epc1104TrapIPEntry OBJECT-TYPE
	SYNTAX  Epc8TrapIPEntry
	MAX-ACCESS not-accessible
	STATUS  current
	DESCRIPTION
		"an entry containing management
		informations regarding the list of trap
		receivers"
	INDEX {
		epc1104TrapIPIndex }
	-- 1.3.6.1.4.1.28507.68.1.1.1.2.1
	::= { epc1104TrapIPTable 1 }


Epc8TrapIPEntry ::= SEQUENCE {

	epc1104TrapIPIndex Integer32,
	epc1104TrapAddr    OCTET STRING }


epc1104TrapIPIndex OBJECT-TYPE
	SYNTAX  Integer32 (1..8)
	MAX-ACCESS read-only
	STATUS  current
	DESCRIPTION
		"A unique value, greater than zero, for each receiver slot."
	-- 1.3.6.1.4.1.28507.68.1.1.1.2.1.1
	::= { epc1104TrapIPEntry 1 }


epc1104TrapAddr OBJECT-TYPE
	SYNTAX  OCTET STRING (SIZE (0..99))
	MAX-ACCESS read-write
	STATUS  current
	DESCRIPTION
		"DNS name or IP address specifying one Trap receiver slot.
		A port can optionally be specified: 'name:port' An empty
		string disables this slot."
	-- 1.3.6.1.4.1.28507.68.1.1.1.2.1.2
	::= { epc1104TrapIPEntry 2 }


epc1104DeviceConfig OBJECT IDENTIFIER
	-- 1.3.6.1.4.1.28507.68.1.2
	::= { epc1104Objects 2 }

epc1104IntActors OBJECT IDENTIFIER
	-- 1.3.6.1.4.1.28507.68.1.3
	::= { epc1104Objects 3 }

epc1104relayports OBJECT IDENTIFIER
	-- 1.3.6.1.4.1.28507.68.1.3.1
	::= { epc1104IntActors 1 }

epc1104portNumber OBJECT-TYPE
	SYNTAX  Integer32 (1)
	MAX-ACCESS read-only
	STATUS  current
	DESCRIPTION
		"The number of Relay Ports"
	-- 1.3.6.1.4.1.28507.68.1.3.1.1
	::= { epc1104relayports 1 }


-- the Interfaces table
-- The Interfaces table contains information on the entity's
-- interfaces.  Each sub-layer below the internetwork-layer
-- of a network interface is considered to be an interface.

epc1104portTable OBJECT-TYPE
	SYNTAX  SEQUENCE OF Epc1104portEntry
	MAX-ACCESS not-accessible
	STATUS  current
	DESCRIPTION
		"list of all EPC Relay Ports"
	-- 1.3.6.1.4.1.28507.68.1.3.1.2
	::= { epc1104relayports 2 }


epc1104portEntry OBJECT-TYPE
	SYNTAX  Epc1104portEntry
	MAX-ACCESS not-accessible
	STATUS  current
	DESCRIPTION
		"An entry containing management information applicable to a
		particular relay port."
	INDEX {
		epc1104PortIndex }
	-- 1.3.6.1.4.1.28507.68.1.3.1.2.1
	::= { epc1104portTable 1 }


Epc1104portEntry ::= SEQUENCE {

	epc1104PortIndex        Integer32,
	epc1104PortName         OCTET STRING,
	epc1104PortState        INTEGER,
	epc1104PortSwitchCount  Integer32,
	epc1104PortStartupMode  INTEGER,
	epc1104PortStartupDelay Integer32,
	epc1104PortRepowerTime  Integer32 }


epc1104PortIndex OBJECT-TYPE
	SYNTAX  Integer32 (1)
	MAX-ACCESS read-only
	STATUS  current
	DESCRIPTION
		"A unique value, greater than zero, for each Relay Port."
	-- 1.3.6.1.4.1.28507.68.1.3.1.2.1.1
	::= { epc1104portEntry 1 }


epc1104PortName OBJECT-TYPE
	SYNTAX  OCTET STRING (SIZE (0..15))
	MAX-ACCESS read-write
	STATUS  current
	DESCRIPTION
		"A textual string containing name of a Relay Port."
	-- 1.3.6.1.4.1.28507.68.1.3.1.2.1.2
	::= { epc1104portEntry 2 }


epc1104PortState OBJECT-TYPE
	SYNTAX  INTEGER {
			off(0),
			on(1) }
	MAX-ACCESS read-write
	STATUS  current
	DESCRIPTION
		"current state a Relay Port"
	-- 1.3.6.1.4.1.28507.68.1.3.1.2.1.3
	::= { epc1104portEntry 3 }


epc1104PortSwitchCount OBJECT-TYPE
	SYNTAX  Integer32
	MAX-ACCESS read-only
	STATUS  current
	DESCRIPTION
		"The total number of switch actions ocurred on a Relay Port.
		Does not count switch commands which will not switch
		the ralay state, so just real relay switches are displayed here."
	-- 1.3.6.1.4.1.28507.68.1.3.1.2.1.4
	::= { epc1104portEntry 4 }


epc1104PortStartupMode OBJECT-TYPE
	SYNTAX  INTEGER {
			off(0),
			on(1),
			laststate(2) }
	MAX-ACCESS read-write
	STATUS  current
	DESCRIPTION
		"set Mode of startup sequence (off, on , remember last state)"
	DEFVAL { off }
	-- 1.3.6.1.4.1.28507.68.1.3.1.2.1.5
	::= { epc1104portEntry 5 }


epc1104PortStartupDelay OBJECT-TYPE
	SYNTAX  Integer32
	UNITS	"seconds"
	MAX-ACCESS read-write
	STATUS  current
	DESCRIPTION
		"Delay in sec for startup action"
	DEFVAL { 0 }
	-- 1.3.6.1.4.1.28507.68.1.3.1.2.1.6
	::= { epc1104portEntry 6 }


epc1104PortRepowerTime OBJECT-TYPE
	SYNTAX  Integer32 (0..65535)
	UNITS	"seconds"
	MAX-ACCESS read-write
	STATUS  current
	DESCRIPTION
		"Delay in sec for repower port after switching off"
	DEFVAL { 0 }
	-- 1.3.6.1.4.1.28507.68.1.3.1.2.1.7
	::= { epc1104portEntry 7 }


epc1104ExtActors OBJECT IDENTIFIER
	-- 1.3.6.1.4.1.28507.68.1.4
	::= { epc1104Objects 4 }

epc1104IntSensors OBJECT IDENTIFIER
	-- 1.3.6.1.4.1.28507.68.1.5
	::= { epc1104Objects 5 }

epc1104ExtSensors OBJECT IDENTIFIER
	-- 1.3.6.1.4.1.28507.68.1.6
	::= { epc1104Objects 6 }

-- Conformance
--

epc1104Conf OBJECT IDENTIFIER
	-- 1.3.6.1.4.1.28507.68.2
	::= { gadsEPC1104 2 }

-- Groups
--

epc1104Groups OBJECT IDENTIFIER
	-- 1.3.6.1.4.1.28507.68.2.1
	::= { epc1104Conf 1 }

-- Compliance
--

epc1104Compls OBJECT IDENTIFIER
	-- 1.3.6.1.4.1.28507.68.2.2
	::= { epc1104Conf 2 }

epc1104BasicGroup OBJECT-GROUP
	OBJECTS {
		epc1104TrapCtrl,
		epc1104TrapIPIndex,
		epc1104TrapAddr,
		epc1104portNumber,
		epc1104PortIndex,
		epc1104PortName,
		epc1104PortState,
		epc1104PortSwitchCount,
		epc1104PortStartupMode,
		epc1104PortStartupDelay,
		epc1104PortRepowerTime,
		epc1104SensorIndex,
		epc1104TempSensor,
		epc1104HygroSensor,
		epc1104InputSensor,
		epc1104AirPressure,
		epc1104DewPoint,
		epc1104DewPointDiff }
	STATUS  current
	DESCRIPTION
		"Basic objects."
	-- 1.3.6.1.4.1.28507.68.2.1.1
	::= { epc1104Groups 1 }

epc1104NotificationGroup NOTIFICATION-GROUP
	NOTIFICATIONS {
		epc1104SwitchEvtPort,
		epc1104TempEvtSen,
		epc1104HygroEvtSen,
		epc1104InputEvtSen,
		epc1104AirPressureEvtSen,
		epc1104DewPtDiffEvtSen }
	STATUS  current
	DESCRIPTION
		""
	-- 1.3.6.1.4.1.28507.68.2.1.2
	::= { epc1104Groups 2 }

-- Notification Types
--

events OBJECT IDENTIFIER
	-- 1.3.6.1.4.1.28507.68.3
	::= { gadsEPC1104 3 }

epc1104SensorTable OBJECT-TYPE
	SYNTAX  SEQUENCE OF Epc1104SensorEntry
	MAX-ACCESS not-accessible
	STATUS  current
	DESCRIPTION ""
	-- 1.3.6.1.4.1.28507.68.1.6.1
	::= { epc1104ExtSensors 1 }


epc1104SensorEntry OBJECT-TYPE
	SYNTAX  Epc1104SensorEntry
	MAX-ACCESS not-accessible
	STATUS  current
	DESCRIPTION ""
	INDEX {
		epc1104SensorIndex }
	-- 1.3.6.1.4.1.28507.68.1.6.1.1
	::= { epc1104SensorTable 1 }


Epc1104SensorEntry ::= SEQUENCE {

	epc1104SensorIndex  Integer32,
	epc1104TempSensor   Integer32,
	epc1104HygroSensor  Integer32,
	epc1104InputSensor  INTEGER,
	epc1104AirPressure  Integer32,
	epc1104DewPoint     Integer32,
	epc1104DewPointDiff Integer32 }


epc1104SensorIndex OBJECT-TYPE
	SYNTAX  Integer32 (1)
	MAX-ACCESS read-only
	STATUS  current
	DESCRIPTION ""
	-- 1.3.6.1.4.1.28507.68.1.6.1.1.1
	::= { epc1104SensorEntry 1 }


epc1104TempSensor OBJECT-TYPE
	SYNTAX  Integer32
	UNITS	"0.1 degree Celsius"
	MAX-ACCESS read-only
	STATUS  current
	DESCRIPTION
		"actual temperature"
	-- 1.3.6.1.4.1.28507.68.1.6.1.1.2
	::= { epc1104SensorEntry 2 }


epc1104HygroSensor OBJECT-TYPE
	SYNTAX  Integer32
	UNITS	"0.1 percent humidity"
	MAX-ACCESS read-only
	STATUS  current
	DESCRIPTION
		"actual humidity"
	-- 1.3.6.1.4.1.28507.68.1.6.1.1.3
	::= { epc1104SensorEntry 3 }


epc1104InputSensor OBJECT-TYPE
	SYNTAX  INTEGER {
			off(0),
			on(1) }
	MAX-ACCESS read-only
	STATUS  current
	DESCRIPTION
		"logical state of input sensor"
	-- 1.3.6.1.4.1.28507.68.1.6.1.1.4
	::= { epc1104SensorEntry 4 }



epc1104SwitchEvtPort NOTIFICATION-TYPE
	OBJECTS {
		epc1104PortIndex,
		epc1104PortName,
		epc1104PortState,
		epc1104PortSwitchCount}
	STATUS  current
	DESCRIPTION
		"Event is triggered when a port is switched"
	-- 1.3.6.1.4.1.28507.68.3.1
	::= { events 1 }


epc1104TempEvtSen NOTIFICATION-TYPE
	OBJECTS {
		epc1104SensorIndex,
		epc1104TempSensor}
	STATUS  current
	DESCRIPTION
		"temperature limits exceeded"
	-- 1.3.6.1.4.1.28507.68.3.2
	::= { events 2 }


epc1104InputEvtSen NOTIFICATION-TYPE
	OBJECTS {
		epc1104SensorIndex,
		epc1104InputSensor}
	STATUS  current
	DESCRIPTION
		"change of logical input sensor state"
	-- 1.3.6.1.4.1.28507.68.3.4
	::= { events 4 }


epc1104AirPressureEvtSen NOTIFICATION-TYPE
	OBJECTS {
		epc1104SensorIndex,
		epc1104AirPressure}
	STATUS  current
	DESCRIPTION
		"Air Pressure limits exceeded"
	-- 1.3.6.1.4.1.28507.68.3.5
	::= { events 5 }


epc1104DewPtDiffEvtSen NOTIFICATION-TYPE
	OBJECTS {
		epc1104SensorIndex,
		epc1104DewPointDiff}
	STATUS  current
	DESCRIPTION
		"Dew Point Difference limits exceeded"
	-- 1.3.6.1.4.1.28507.68.3.6
	::= { events 6 }

epc1104AirPressure OBJECT-TYPE
	SYNTAX  Integer32
	UNITS	"1 hPA (hectopascal) ~ 1 milibar"
	MAX-ACCESS read-only
	STATUS  current
	DESCRIPTION
		"actual air pressure"
	-- 1.3.6.1.4.1.28507.68.1.6.1.1.5
	::= { epc1104SensorEntry 5 }


epc1104DewPoint OBJECT-TYPE
	SYNTAX  Integer32
	UNITS	"0.1 degree Celsius"
	MAX-ACCESS read-only
	STATUS  current
	DESCRIPTION
		"dew point for actual temperature and humidity"
	-- 1.3.6.1.4.1.28507.68.1.6.1.1.6
	::= { epc1104SensorEntry 6 }


epc1104DewPointDiff OBJECT-TYPE
	SYNTAX  Integer32
	UNITS	"0.1 degree Celsius"
	MAX-ACCESS read-only
	STATUS  current
	DESCRIPTION
		"difference between dew point and actual
		temperature (Temp - DewPoint)"
	-- 1.3.6.1.4.1.28507.68.1.6.1.1.7
	::= { epc1104SensorEntry 7 }



epc1104HygroEvtSen NOTIFICATION-TYPE
	OBJECTS {
		epc1104SensorIndex,
		epc1104HygroSensor}
	STATUS  current
	DESCRIPTION
		"hygro limits exceeded"
	-- 1.3.6.1.4.1.28507.43.3.4
	-- 1.3.6.1.4.1.28507.68.3.3
	::= { events 3 }

END
