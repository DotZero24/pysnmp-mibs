GUDEADS-PDU8306-MIB DEFINITIONS ::= BEGIN

IMPORTS
	enterprises,
	MODULE-IDENTITY,
	OBJECT-TYPE,
	NOTIFICATION-TYPE,
	Integer32,
	Unsigned32
		FROM SNMPv2-SMI
	OBJECT-GROUP,
	NOTIFICATION-GROUP
		FROM SNMPv2-CONF;

gudeads MODULE-IDENTITY
	LAST-UPDATED "200703051356Z"	-- Mar 5, 2007 1:56:00 PM
	ORGANIZATION "Gude Analog- und Digitalsysteme GmbH"
	CONTACT-INFO
		"http://www.gudeads.com/"
	DESCRIPTION
		""
	REVISION "200703051356Z"	-- Mar 5, 2007 1:56:00 PM
	DESCRIPTION
		"$Id:$"
	-- 1.3.6.1.4.1.28507
	::= { enterprises 28507 }


gadsPDU8306 OBJECT IDENTIFIER
	-- 1.3.6.1.4.1.28507.44
	::= { gudeads 44 }

-- Notification Types
--

events OBJECT IDENTIFIER
	-- 1.3.6.1.4.1.28507.44.0
	::= { gadsPDU8306 0 }

-- Scalars and Tables
--

pdu8306Objects OBJECT IDENTIFIER
	-- 1.3.6.1.4.1.28507.44.1
	::= { gadsPDU8306 1 }

pdu8306CommonConfig OBJECT IDENTIFIER
	-- 1.3.6.1.4.1.28507.44.1.1
	::= { pdu8306Objects 1 }

pdu8306SNMPaccess OBJECT IDENTIFIER
	-- 1.3.6.1.4.1.28507.44.1.1.1
	::= { pdu8306CommonConfig 1 }

pdu8306TrapCtrl OBJECT-TYPE
	SYNTAX  Integer32 (0..2)
	MAX-ACCESS read-write
	STATUS  current
	DESCRIPTION
		"0 = off
		1 = Ver. 1
		2 = Ver. 2c"
	-- 1.3.6.1.4.1.28507.44.1.1.1.1
	::= { pdu8306SNMPaccess 1 }


pdu8306TrapIPTable OBJECT-TYPE
	SYNTAX  SEQUENCE OF Epc8TrapIPEntry
	MAX-ACCESS not-accessible
	STATUS  current
	DESCRIPTION
		"list of all Trap receiver"
	-- 1.3.6.1.4.1.28507.44.1.1.1.2
	::= { pdu8306SNMPaccess 2 }


pdu8306TrapIPEntry OBJECT-TYPE
	SYNTAX  Epc8TrapIPEntry
	MAX-ACCESS not-accessible
	STATUS  current
	DESCRIPTION
		"an entry containing management
		informations regarding the list of trap
		receivers"
	INDEX {
		pdu8306TrapIPIndex }
	-- 1.3.6.1.4.1.28507.44.1.1.1.2.1
	::= { pdu8306TrapIPTable 1 }


Epc8TrapIPEntry ::= SEQUENCE {

	pdu8306TrapIPIndex Integer32,
	pdu8306TrapAddr    OCTET STRING }


pdu8306TrapIPIndex OBJECT-TYPE
	SYNTAX  Integer32 (1..8)
	MAX-ACCESS not-accessible
	STATUS  current
	DESCRIPTION
		"A unique value, greater than zero, for each receiver slot."
	-- 1.3.6.1.4.1.28507.44.1.1.1.2.1.1
	::= { pdu8306TrapIPEntry 1 }


pdu8306TrapAddr OBJECT-TYPE
	SYNTAX  OCTET STRING (SIZE (0..99))
	MAX-ACCESS read-write
	STATUS  current
	DESCRIPTION
		"DNS name or IP address specifying one Trap receiver slot.
		A port can optionally be specified: 'name:port' An empty
		string disables this slot."
	-- 1.3.6.1.4.1.28507.44.1.1.1.2.1.2
	::= { pdu8306TrapIPEntry 2 }


pdu8306DeviceConfig OBJECT IDENTIFIER
	-- 1.3.6.1.4.1.28507.44.1.2
	::= { pdu8306Objects 2 }

pdu8306IntActors OBJECT IDENTIFIER
	-- 1.3.6.1.4.1.28507.44.1.3
	::= { pdu8306Objects 3 }

pdu8306ExtActors OBJECT IDENTIFIER
	-- 1.3.6.1.4.1.28507.44.1.4
	::= { pdu8306Objects 4 }

pdu8306IntSensors OBJECT IDENTIFIER
	-- 1.3.6.1.4.1.28507.44.1.5
	::= { pdu8306Objects 5 }

pdu8306PowerChan OBJECT IDENTIFIER
	-- 1.3.6.1.4.1.28507.44.1.5.1
	::= { pdu8306IntSensors 1 }

pdu8306ActivePowerChan OBJECT-TYPE
	SYNTAX  Unsigned32 (1..3)
	MAX-ACCESS read-only
	STATUS  current
	DESCRIPTION
		"Number of suppported Power Channels."
	-- 1.3.6.1.4.1.28507.44.1.5.1.1
	::= { pdu8306PowerChan 1 }


pdu8306PowerTable OBJECT-TYPE
	SYNTAX  SEQUENCE OF Pdu8306PowerEntry
	MAX-ACCESS not-accessible
	STATUS  current
	DESCRIPTION
		"All available Channel Interfaces."
	-- 1.3.6.1.4.1.28507.44.1.5.1.2
	::= { pdu8306PowerChan 2 }


pdu8306PowerEntry OBJECT-TYPE
	SYNTAX  Pdu8306PowerEntry
	MAX-ACCESS not-accessible
	STATUS  current
	DESCRIPTION
		"An entry containing management information
		applicable to a particular Power Channel."
	INDEX {
		pdu8306PowerIndex }
	-- 1.3.6.1.4.1.28507.44.1.5.1.2.1
	::= { pdu8306PowerTable 1 }


Pdu8306PowerEntry ::= SEQUENCE {

	pdu8306PowerIndex               Integer32,
	pdu8306ChanStatus               Integer32,
	pdu8306AbsEnergyActive          Unsigned32,
	pdu8306PowerActive              Integer32,
	pdu8306Current                  Unsigned32,
	pdu8306Voltage                  Unsigned32,
	pdu8306Frequency                Unsigned32,
	pdu8306PowerFactor              Integer32,
	pdu8306Pangle                   Integer32,
	pdu8306PowerApparent            Integer32,
	pdu8306PowerReactive            Integer32,
	pdu8306EnergyReactive           Unsigned32,
	pdu8306EnergyActiveResettable   Unsigned32,
	pdu8306EnergyReactiveResettable Unsigned32,
	pdu8306ResetTime                Unsigned32 }


pdu8306PowerIndex OBJECT-TYPE
	SYNTAX  Integer32 (1..3)
	MAX-ACCESS not-accessible
	STATUS  current
	DESCRIPTION
		"Index of Power Channel entries"
	-- 1.3.6.1.4.1.28507.44.1.5.1.2.1.1
	::= { pdu8306PowerEntry 1 }


pdu8306ChanStatus OBJECT-TYPE
	SYNTAX  Integer32 (0..1)
	MAX-ACCESS read-only
	STATUS  current
	DESCRIPTION
		"0 = data not active, 1 = data valid"
	-- 1.3.6.1.4.1.28507.44.1.5.1.2.1.2
	::= { pdu8306PowerEntry 2 }


pdu8306AbsEnergyActive OBJECT-TYPE
	SYNTAX  Unsigned32
	UNITS
		"Wh"
	MAX-ACCESS read-only
	STATUS  current
	DESCRIPTION
		"Absolute Active Energy counter."
	-- 1.3.6.1.4.1.28507.44.1.5.1.2.1.3
	::= { pdu8306PowerEntry 3 }


pdu8306PowerActive OBJECT-TYPE
	SYNTAX  Integer32
	UNITS
		"W"
	MAX-ACCESS read-only
	STATUS  current
	DESCRIPTION
		"Active Power"
	-- 1.3.6.1.4.1.28507.44.1.5.1.2.1.4
	::= { pdu8306PowerEntry 4 }


pdu8306Current OBJECT-TYPE
	SYNTAX  Unsigned32
	UNITS
		"mA"
	MAX-ACCESS read-only
	STATUS  current
	DESCRIPTION
		"Actual Curent on Power Channel."
	-- 1.3.6.1.4.1.28507.44.1.5.1.2.1.5
	::= { pdu8306PowerEntry 5 }


pdu8306Voltage OBJECT-TYPE
	SYNTAX  Unsigned32
	UNITS
		"V"
	MAX-ACCESS read-only
	STATUS  current
	DESCRIPTION
		"Actual Voltage on Power Channel"
	-- 1.3.6.1.4.1.28507.44.1.5.1.2.1.6
	::= { pdu8306PowerEntry 6 }


pdu8306Frequency OBJECT-TYPE
	SYNTAX  Unsigned32
	UNITS
		"0.01 hz"
	MAX-ACCESS read-only
	STATUS  current
	DESCRIPTION
		"Frequency of Power Channel"
	-- 1.3.6.1.4.1.28507.44.1.5.1.2.1.7
	::= { pdu8306PowerEntry 7 }


pdu8306PowerFactor OBJECT-TYPE
	SYNTAX  Integer32
	UNITS
		"0.001"
	MAX-ACCESS read-only
	STATUS  current
	DESCRIPTION
		"Power Factor of Channel between
		-1.0 and 1.00"
	-- 1.3.6.1.4.1.28507.44.1.5.1.2.1.8
	::= { pdu8306PowerEntry 8 }


pdu8306Pangle OBJECT-TYPE
	SYNTAX  Integer32
	UNITS
		"0.1 degree"
	MAX-ACCESS read-only
	STATUS  current
	DESCRIPTION
		"Phase Angle between Voltage
		and L Line Current between
		-180.0 and 180.0"
	-- 1.3.6.1.4.1.28507.44.1.5.1.2.1.9
	::= { pdu8306PowerEntry 9 }


pdu8306PowerApparent OBJECT-TYPE
	SYNTAX  Integer32
	UNITS
		"VA"
	MAX-ACCESS read-only
	STATUS  current
	DESCRIPTION
		"L Line Mean Apparent Power"
	-- 1.3.6.1.4.1.28507.44.1.5.1.2.1.10
	::= { pdu8306PowerEntry 10 }


pdu8306PowerReactive OBJECT-TYPE
	SYNTAX  Integer32
	UNITS
		"VAR"
	MAX-ACCESS read-only
	STATUS  current
	DESCRIPTION
		"L Line Mean Reactive Power"
	-- 1.3.6.1.4.1.28507.44.1.5.1.2.1.11
	::= { pdu8306PowerEntry 11 }


pdu8306EnergyReactive OBJECT-TYPE
	SYNTAX  Unsigned32
	UNITS
		"VARh"
	MAX-ACCESS read-only
	STATUS  current
	DESCRIPTION
		"Absolute Reactive Energy counter."
	-- 1.3.6.1.4.1.28507.44.1.5.1.2.1.12
	::= { pdu8306PowerEntry 12 }


pdu8306EnergyActiveResettable OBJECT-TYPE
	SYNTAX  Unsigned32
	UNITS
		"Wh"
	MAX-ACCESS read-only
	STATUS  current
	DESCRIPTION
		"Resettable Absolute Active Energy counter."
	-- 1.3.6.1.4.1.28507.44.1.5.1.2.1.13
	::= { pdu8306PowerEntry 13 }


pdu8306EnergyReactiveResettable OBJECT-TYPE
	SYNTAX  Unsigned32
	UNITS
		"VARh"
	MAX-ACCESS read-only
	STATUS  current
	DESCRIPTION
		"Resettable Absolute Reactive Energy counter."
	-- 1.3.6.1.4.1.28507.44.1.5.1.2.1.14
	::= { pdu8306PowerEntry 14 }


pdu8306ResetTime OBJECT-TYPE
	SYNTAX  Unsigned32
	UNITS
		"s"
	MAX-ACCESS read-only
	STATUS  current
	DESCRIPTION
		"Time in seconds since last Energy
		Counter reset."
	-- 1.3.6.1.4.1.28507.44.1.5.1.2.1.15
	::= { pdu8306PowerEntry 15 }


pdu8306MeasurementBoxConnected OBJECT-TYPE
	SYNTAX  INTEGER {
			disconnected(0),
			connected(1) }
	MAX-ACCESS read-only
	STATUS  current
	DESCRIPTION
		"Shows if the external Measurement Box is connected."
	-- 1.3.6.1.4.1.28507.44.1.5.12
	::= { pdu8306IntSensors 12 }


pdu8306ExtSensors OBJECT IDENTIFIER
	-- 1.3.6.1.4.1.28507.44.1.6
	::= { pdu8306Objects 6 }

pdu8306SensorTable OBJECT-TYPE
	SYNTAX  SEQUENCE OF Pdu8306SensorEntry
	MAX-ACCESS not-accessible
	STATUS  current
	DESCRIPTION ""
	-- 1.3.6.1.4.1.28507.44.1.6.1
	::= { pdu8306ExtSensors 1 }


pdu8306SensorEntry OBJECT-TYPE
	SYNTAX  Pdu8306SensorEntry
	MAX-ACCESS not-accessible
	STATUS  current
	DESCRIPTION ""
	INDEX {
		pdu8306SensorIndex }
	-- 1.3.6.1.4.1.28507.44.1.6.1.1
	::= { pdu8306SensorTable 1 }


Pdu8306SensorEntry ::= SEQUENCE {

	pdu8306SensorIndex Integer32,
	pdu8306TempSensor  Integer32,
	pdu8306HygroSensor Integer32,
	pdu8306InputSensor INTEGER }


pdu8306SensorIndex OBJECT-TYPE
	SYNTAX  Integer32 (1)
	MAX-ACCESS not-accessible
	STATUS  current
	DESCRIPTION ""
	-- 1.3.6.1.4.1.28507.44.1.6.1.1.1
	::= { pdu8306SensorEntry 1 }


pdu8306TempSensor OBJECT-TYPE
	SYNTAX  Integer32
	UNITS
		"0.1 degree Celsius"
	MAX-ACCESS read-only
	STATUS  current
	DESCRIPTION
		"actual temperature,  a value of -9999 indicates
		that data is not available"
	-- 1.3.6.1.4.1.28507.44.1.6.1.1.2
	::= { pdu8306SensorEntry 2 }


pdu8306HygroSensor OBJECT-TYPE
	SYNTAX  Integer32
	UNITS
		"0.1 percent humidity"
	MAX-ACCESS read-only
	STATUS  current
	DESCRIPTION
		"actual humidity,  a value of -9999 indicates
		that data is not available"
	-- 1.3.6.1.4.1.28507.44.1.6.1.1.3
	::= { pdu8306SensorEntry 3 }


pdu8306InputSensor OBJECT-TYPE
	SYNTAX  INTEGER {
			off(0),
			on(1) }
	MAX-ACCESS read-only
	STATUS  current
	DESCRIPTION
		"logical state of input sensor"
	-- 1.3.6.1.4.1.28507.44.1.6.1.1.4
	::= { pdu8306SensorEntry 4 }


-- Conformance
--

pdu8306Conf OBJECT IDENTIFIER
	-- 1.3.6.1.4.1.28507.44.2
	::= { gadsPDU8306 2 }

-- Groups
--

pdu8306Groups OBJECT IDENTIFIER
	-- 1.3.6.1.4.1.28507.44.2.1
	::= { pdu8306Conf 1 }

-- Compliance
--

pdu8306Compls OBJECT IDENTIFIER
	-- 1.3.6.1.4.1.28507.44.2.2
	::= { pdu8306Conf 2 }


pdu8306TempEvtSen1 NOTIFICATION-TYPE
	OBJECTS {
		pdu8306TempSensor}
	STATUS  current
	DESCRIPTION
		"temperature limits exceeded"
	-- 1.3.6.1.4.1.28507.44.0.1
	::= { events 1 }


pdu8306HygroEvtSen1 NOTIFICATION-TYPE
	OBJECTS {
		pdu8306HygroSensor}
	STATUS  current
	DESCRIPTION
		"hygro limits exceeded"
	-- 1.3.6.1.4.1.28507.44.0.2
	::= { events 2 }


pdu8306MeasurementBoxEvt NOTIFICATION-TYPE
	OBJECTS {
		pdu8306MeasurementBoxConnected}
	STATUS  current
	DESCRIPTION
		"Signals a change of the connection to the
		external Measurement Box."
	-- 1.3.6.1.4.1.28507.44.0.3
	::= { events 3 }

pdu8306BasicGroup OBJECT-GROUP
	OBJECTS {
		pdu8306TrapCtrl,
		pdu8306TrapAddr,
		pdu8306ActivePowerChan,
		pdu8306ChanStatus,
		pdu8306AbsEnergyActive,
		pdu8306PowerActive,
		pdu8306Current,
		pdu8306Voltage,
		pdu8306Frequency,
		pdu8306PowerFactor,
		pdu8306Pangle,
		pdu8306PowerApparent,
		pdu8306PowerReactive,
		pdu8306EnergyReactive,
		pdu8306EnergyActiveResettable,
		pdu8306EnergyReactiveResettable,
		pdu8306ResetTime,
		pdu8306MeasurementBoxConnected,
		pdu8306TempSensor,
		pdu8306HygroSensor,
		pdu8306InputSensor }
	STATUS  current
	DESCRIPTION
		"Basic objects."
	-- 1.3.6.1.4.1.28507.44.2.1.1
	::= { pdu8306Groups 1 }

pdu8306NotificationGroup NOTIFICATION-GROUP
	NOTIFICATIONS {
		pdu8306TempEvtSen1,
		pdu8306HygroEvtSen1,
		pdu8306MeasurementBoxEvt }
	STATUS  current
	DESCRIPTION ""
	-- 1.3.6.1.4.1.28507.44.2.1.2
	::= { pdu8306Groups 2 }

END
