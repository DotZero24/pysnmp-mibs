KYOCERA-MIB DEFINITIONS ::= BEGIN
--
--      Created and maintained by S.Kanemitsu   *** Modified by H.Yamamoto for debug ***
--      4th Sec, Engineering Dept. Printer Div., KYOCERA Corp.
--
--      Release:
--          June 7, 2000
--              Release 1.70
--              Adds kcprtSleepTimerMode for supporting new EnergyStar spec.

--      History:
--          September 7, 1998
--              Release 1.60
--              Adds Media-type capability. The first target model is FS-7000+.
--
--          June 8, 1998
--          Release 1.51
--              Fixed several syntax errors that are critical on Novell environment.
--
--          March 10, 1998
--          Release 1.5
--              Adds color support objects.
--              Adds one object to support host buffer on four interfaces.
--          Newly applied model:
--              FS-5800C
--
--          December 24, 1997
--          Release 1.42
--              Adds missing objects to kcprtGeneral.
--              Changes several SYNTAX from OCTET STRING to DisplayString
--
--          December 22, 1997
--          Release 1.41
--              Adds missing objects to kcprtChannel.
--
--          November 19, 1997
--          Release 1.40
--              Implements 'FILE' object on Hard Disk
--              Implements 'SJob' object on Hard Disk
--
--          September 18, 1997
--          Release 1.30
--
--      Applied printer models:
--          FS-7000, LS-7000 (Enhanced versions)
--
--      Warning:
--          Some objects may not be used for the older models.
--

--
--  Declare imports
--
    IMPORTS
	enterprises, OBJECT-TYPE
                FROM RFC1155-SMI
        hrDeviceIndex
            FROM HOST-RESOURCES-MIB
        DisplayString
            FROM RFC1213-MIB
        PresentOnOff, prtMarkerIndex
            FROM Printer-MIB;

--
--  Object identifier definition
--
    kyocera         OBJECT IDENTIFIER ::= { enterprises 1347 }

--  !! Following definition is for SNMPv2-SMI.
--  kcPrinter       MODULE-IDENTITY
--          LAST-UPDATED "9803100000Z"
--          ORGANIZATION "KYOCERA Corporation"
--          CONTACT-INFO
--              "       S. Kanemitsu
--                      IDS Group, Printer Div.
--              Postal: KYOCERA Corporation
--                      2-14-9 Tamagawadai
--                      Setagaya-ku, Tokyo 158-0096 Japan
--
--                 Tel: +81-3-3708-3858
--                 Fax: +81-3-3708-0423
--          DESCRIPTION
--              "The private MIB module for KYOCERA printers."
--      ::= { kyocera 43 }

--  !! Following definition is for SNMP(v1).
    kcPrinter       OBJECT IDENTIFIER ::= { kyocera 43 }

    kcprtGeneral        OBJECT IDENTIFIER ::= { kcPrinter 5 }
    kcprtInput          OBJECT IDENTIFIER ::= { kcPrinter 8 }
    kcprtOutput         OBJECT IDENTIFIER ::= { kcPrinter 9 }
    kcprtMarker         OBJECT IDENTIFIER ::= { kcPrinter 10 }
    kcprtColorant       OBJECT IDENTIFIER ::= { kcPrinter 12 }
    kcprtChannel        OBJECT IDENTIFIER ::= { kcPrinter 14 }
    kcprtBuzzer         OBJECT IDENTIFIER ::= { kcPrinter 17 }
    kcprtAlert          OBJECT IDENTIFIER ::= { kcPrinter 18 }
    kcprtMemoryResource OBJECT IDENTIFIER ::= { kcPrinter 20 }
    kcprtMediaList      OBJECT IDENTIFIER ::= { kcPrinter 21 }
    kcprtMailBox        OBJECT IDENTIFIER ::= { kcPrinter 22 }
    kcprtSubUnit        OBJECT IDENTIFIER ::= { kcPrinter 23 }
    kcprtJob            OBJECT IDENTIFIER ::= { kcPrinter 24 }
--
--  General group
--
--      To view and control the general settings.
--
    kcprtGeneralTable   OBJECT-TYPE
        SYNTAX  SEQUENCE OF KcprtGeneralEntry
        ACCESS  not-accessible
        STATUS  mandatory
        DESCRIPTION
            "This table contains the generic parameters that are applied
            to the KYOCERA network printer."

        ::= { kcprtGeneral 1 }

    kcprtGeneralEntry   OBJECT-TYPE
        SYNTAX  KcprtGeneralEntry
        ACCESS  not-accessible
        STATUS  mandatory
        DESCRIPTION
            "A list of general entries for KYOCERA printer."
        INDEX   { hrDeviceIndex }
        ::= { kcprtGeneralTable 1 }

    KcprtGeneralEntry   ::= SEQUENCE {
                    kcprtGeneralModelName   DisplayString,
                    kcprtOptionVersion      DisplayString,
                    kcprtKpdlLevel          INTEGER,
                    kcprtSystemUpTime       INTEGER,
                    kcprtBinNumber          INTEGER,
                    kcprtCardSlotCapacity   INTEGER,
                    kcprtRomSlotNumber      INTEGER,
                    kcprtSimmSlotCapacity   INTEGER,
                    kcprtSimmSlotUsed       INTEGER,
                    kcprtOriginalMemorySize INTEGER,
                    kcprtTotalMemorySize    INTEGER,
                    kcprtUserMemorySize     INTEGER,
                    kcprtVirtualMemory      INTEGER,
                    kcprtPageMemorySize     INTEGER,
                    kcprtHostBufferSize     INTEGER,
                    kcprtHostBuffer1stRate  INTEGER,
                    kcprtHostBuffer2ndRate  INTEGER,
                    kcprtHostBuffer3rdRate  INTEGER,
                    kcprtHostBufferOption   INTEGER,
                    kcprtBufferXoffLevel    INTEGER,
                    kcprtBufferXonLevel     INTEGER,
                    kcprtFFTimeout          INTEGER,
                    kcprtSleepTimer         INTEGER,
                    kcprtWakeupStatusPage   INTEGER,
                    kcprtOnlineControl      INTEGER,
                    kcprtCopyCount          INTEGER,
                    kcprtContinueKey        INTEGER,
                    kcprtSerialNumber       DisplayString,
                    kcprtAssetNumber        DisplayString,
                    kcprtSignature          OCTET STRING,
                    kcprtFirmParamCurrentRegister   OCTET STRING,
                    kcprtFirmParamCurrentValue   OCTET STRING,
                    kcprtSleepMode          INTEGER,
                    kcprtAutoContinueMode          INTEGER,
                    kcprtAutoContinueTimer          INTEGER,
                    kcprtAbsoluteModelName   DisplayString,
                    kcprtEquipmentID       DisplayString,
                    kcprtMaxCopyCount       INTEGER
            }

    kcprtGeneralModelName   OBJECT-TYPE
        SYNTAX  DisplayString   ( SIZE(0..32) )
        ACCESS  read-only
        STATUS  mandatory
        DESCRIPTION
            "The printer's model name."
        ::= { kcprtGeneralEntry 1 }

   kcprtOptionVersion      OBJECT-TYPE
        SYNTAX  DisplayString   ( SIZE(0..10) )
        ACCESS  read-only
        STATUS  mandatory
        DESCRIPTION
            "The string used for identify the option interface."
        ::= { kcprtGeneralEntry 2 }

    kcprtKpdlLevel          OBJECT-TYPE
        SYNTAX  INTEGER (0..3)
        ACCESS  read-only
        STATUS  mandatory
        DESCRIPTION
            "The level of KPDL. The value (0) means KPDL is not supported or KPDL ROM is missing."
        ::= { kcprtGeneralEntry 3 }

    kcprtSystemUpTime       OBJECT-TYPE
        SYNTAX  INTEGER (0..4294967295)
        ACCESS  read-only
        STATUS  mandatory
        DESCRIPTION
            "The amount of time since this printer was last powered on. Unit is second."
        ::= { kcprtGeneralEntry 4 }

    kcprtBinNumber          OBJECT-TYPE
        SYNTAX  INTEGER (0..255)
        ACCESS  read-only
        STATUS  mandatory
        DESCRIPTION
            "The number of paper bins that is implemented within printer itself.  This number does not show all of input bin number."
        ::= { kcprtGeneralEntry 5 }

    kcprtCardSlotCapacity   OBJECT-TYPE
        SYNTAX  INTEGER (0..255)
        ACCESS  read-only
        STATUS  mandatory
        DESCRIPTION
            "The number of IC card slots that this printer actually has.  The value (0) means this printer has no IC card slot."
        ::= { kcprtGeneralEntry 6 }

    kcprtRomSlotNumber      OBJECT-TYPE
        SYNTAX  INTEGER (0..255)
        ACCESS  read-only
        STATUS  mandatory
        DESCRIPTION
            "The number of option ROM slots.  The value (0) means this printer has no option ROM slot."
        ::= { kcprtGeneralEntry 7 }

    kcprtSimmSlotCapacity   OBJECT-TYPE
        SYNTAX  INTEGER (0..255)
        ACCESS  read-only
        STATUS  mandatory
        DESCRIPTION
            "The number of SIMM slots that this printer actually has."
        ::= { kcprtGeneralEntry 8 }

    kcprtSimmSlotUsed       OBJECT-TYPE
        SYNTAX  INTEGER (0..255)
        ACCESS  read-only
        STATUS  mandatory
        DESCRIPTION
            " The number of SIMM slots that is currently used for SIMM."
        ::= { kcprtGeneralEntry 9 }

    kcprtOriginalMemorySize OBJECT-TYPE
        SYNTAX  INTEGER (0..4294967295)
        ACCESS  read-only
        STATUS  mandatory
        DESCRIPTION
            "The amount of memory that this printer has on its controller board. Note this value does not include any other optional memory. Unit is kilobytes."
        ::= { kcprtGeneralEntry 10 }

    kcprtTotalMemorySize    OBJECT-TYPE
        SYNTAX  INTEGER (0..4294967295)
        ACCESS  read-only
        STATUS  mandatory
        DESCRIPTION
            "The amount of memory that this printer actually has. Unit is kilobytes."
        ::= { kcprtGeneralEntry 11 }

    kcprtUserMemorySize     OBJECT-TYPE
        SYNTAX  INTEGER (0..4294967295)
        ACCESS  read-only
        STATUS  mandatory
        DESCRIPTION
            "The amount of memory that is available for user. Unit is kilobyte."
        ::= { kcprtGeneralEntry 12 }

    kcprtVirtualMemory      OBJECT-TYPE
        SYNTAX  INTEGER {
            notSupported(0),
            support(1)
        }
        ACCESS  read-only
        STATUS  mandatory
        DESCRIPTION
            "This object shows whether this printer has the virtual memory function."
        ::= { kcprtGeneralEntry 13 }

    kcprtPageMemorySize     OBJECT-TYPE
        SYNTAX  INTEGER {
            mem128KB(1),
            mem256KB(2),
            mem512KB(3),
            memA4orLetter(4),
            memLegal(5),
            memwLetter(6),
            memwLegal(7)
        }
        ACCESS  read-write
        STATUS  mandatory
        DESCRIPTION
            "The page memory size corresponding to the FRPO R5 parameter. Because each model of our printer has slightly different value combination, it is recommended to verify the value after writing. Please ask to KYOCERA about the value combination for each printer. For example, our A3 type printer does not have this capability so that The value will be always 512KB(3). The value (-1) means others. Writing (-1) has no meaning."
        ::= { kcprtGeneralEntry 14 }

    kcprtHostBufferSize     OBJECT-TYPE
        SYNTAX  INTEGER (0..99)
        ACCESS  read-write
        STATUS  mandatory
        DESCRIPTION
            " The host buffer size in units of ten kilobytes. The value(0) means that the host buffer size is 5 Kbytes."
        ::= { kcprtGeneralEntry 15 }

    kcprtHostBuffer1stRate  OBJECT-TYPE
        SYNTAX  INTEGER (0..9)
        ACCESS  read-write
        STATUS  mandatory
        DESCRIPTION
            "The ratio of the main host buffer size."
        ::= { kcprtGeneralEntry 16 }

    kcprtHostBuffer2ndRate  OBJECT-TYPE
        SYNTAX  INTEGER (0..9)
        ACCESS  read-write
        STATUS  mandatory
        DESCRIPTION
            "The ratio of the 2nd host buffer size."
        ::= { kcprtGeneralEntry 17 }

    kcprtHostBuffer3rdRate  OBJECT-TYPE
        SYNTAX  INTEGER (0..9)
        ACCESS  read-write
        STATUS  mandatory
        DESCRIPTION
            "The ratio of the 3rd host buffer size. Note that this entry will be 'not accessible' if the printer has only two interfaces."
        ::= { kcprtGeneralEntry 18 }

    kcprtHostBufferOption   OBJECT-TYPE
        SYNTAX  INTEGER {
            automatic(0),
            fixed(1)
        }
        ACCESS  read-write
        STATUS  mandatory
        DESCRIPTION
            "In the automatic mode, the first data arriving from the computer go into main buffer (1st buffer). In the fixed mode, each buffer is fixed on the appropriate interface. Refer to User's manual."
        ::= { kcprtGeneralEntry 19 }

    kcprtBufferXoffLevel    OBJECT-TYPE
        SYNTAX  INTEGER (0..99)
        ACCESS  read-write
        STATUS  mandatory
        DESCRIPTION
            "The printer will pause for receiving data when the ratio of occupied data on the host buffer reaches this threshold level. Note that this value should be larger than kcprtBufferXonLevel. If not, the value is ignored."
        ::= { kcprtGeneralEntry 20 }

    kcprtBufferXonLevel     OBJECT-TYPE
        SYNTAX  INTEGER (0..99)
        ACCESS  read-write
        STATUS  mandatory
        DESCRIPTION
            "The printer will begin to receive data again when the ratio of occupied data on the host buffer becomes lower than this threshould level. Note that value should be less than kcprtBufferXoffLevel. If not, the value is ignored."
        ::= { kcprtGeneralEntry 21 }

    kcprtFFTimeout          OBJECT-TYPE
        SYNTAX  INTEGER (0..99)
        ACCESS  read-write
        STATUS  mandatory
        DESCRIPTION
            "The form-feed time-out timer in units of five seconds. The value (0) means the time-out timer is off."
        ::= { kcprtGeneralEntry 22 }

    kcprtSleepTimer         OBJECT-TYPE
        SYNTAX  INTEGER (1..48)
        ACCESS  read-write
        STATUS  mandatory
        DESCRIPTION
            "The value of sleep timer in units of five minutes. The value (0) means the sleep timer is off for previous model than FS-xxxx. The new models that implement kcprtSleepTimer does not allow to use a value (0) for disabling the sleep."
        ::= { kcprtGeneralEntry 23 }

    kcprtWakeupStatusPage   OBJECT-TYPE
        SYNTAX  INTEGER {
            disable(0),
            enable(1)
        }
        ACCESS  read-write
        STATUS  mandatory
        DESCRIPTION
            "If enable, a printer generates the status page each time it comes up."
        ::= { kcprtGeneralEntry 24 }

    kcprtOnlineControl      OBJECT-TYPE
        SYNTAX  INTEGER {
            offLine(0),
            onLine(1)
        }
        ACCESS  read-write
        STATUS  mandatory
        DESCRIPTION
            "This object controls the on/off line status. Note the writing value does not apply in some situation."
        ::= { kcprtGeneralEntry 25 }

    kcprtCopyCount          OBJECT-TYPE
        SYNTAX  INTEGER (1..999)
        ACCESS  read-write
        STATUS  mandatory
        DESCRIPTION
            "The default copy number."
        ::= { kcprtGeneralEntry 26 }

    kcprtContinueKey        OBJECT-TYPE
        SYNTAX  INTEGER{
            normal(0),
            continue(1)
        }
        ACCESS  read-write
        STATUS  mandatory
        DESCRIPTION
            "This object corresponds to the printer's CONTINUE key. Writing value (1) has a meaning only when the printer requires it.
            This object was newly added for FS-1700 and FS-3700."
        ::= { kcprtGeneralEntry 27 }

    kcprtSerialNumber   OBJECT-TYPE
        SYNTAX  DisplayString   ( SIZE(0..10) )
        ACCESS  read-only
        STATUS  mandatory
        DESCRIPTION
            "The octet string corresponding to the printer's serial number.
            This object was newly added for FS-1700 and FS-3700."
        ::= { kcprtGeneralEntry 28 }

    kcprtAssetNumber   OBJECT-TYPE
        SYNTAX  DisplayString   ( SIZE(0..16) )
        ACCESS  read-write
        STATUS  mandatory
        DESCRIPTION
            "The octet string corresponding to the printer's asset number.
            The format is up to the application.
            This object was newly added since FS-7000."
        ::= { kcprtGeneralEntry 29 }

    kcprtSignature  OBJECT-TYPE
        SYNTAX  OCTET STRING    ( SIZE(0..16) )
        ACCESS  read-write
        STATUS  mandatory
        DESCRIPTION
            "This object will be used as the signature field. Printer has no responsibility about the contents. In another word, the written value has no menaing for the printer. Application on host will use this field mainly for the security purpose."
        ::= { kcprtGeneralEntry 30 }

    kcprtFirmParamCurrentRegister  OBJECT-TYPE
        SYNTAX  OCTET STRING    ( SIZE(0..4) )
        ACCESS  read-write
        STATUS  mandatory
        DESCRIPTION
            "This object is FRPO parameter's register."
        ::= { kcprtGeneralEntry 31 }

    kcprtFirmParamCurrentValue  OBJECT-TYPE
        SYNTAX  OCTET STRING    ( SIZE(0..31) )
        ACCESS  read-write
        STATUS  mandatory
        DESCRIPTION
            "This object is FRPO parameter's current value."
        ::= { kcprtGeneralEntry 32 }

    kcprtSleepMode  OBJECT-TYPE
        SYNTAX  INTEGER    {
                off(0),
                on(1)
        }
        ACCESS  read-write
        STATUS  mandatory
        DESCRIPTION
            "When the value is off(0), the printer will never sleep even its sleep timer has appropriate timer value. Note the printer model that has this object cannot use the value less than five to kcprtSleepTimer. This may cause badValue result."
        ::= { kcprtGeneralEntry 33 }

    kcprtAutoContinueMode  OBJECT-TYPE
        SYNTAX  INTEGER    {
                off(0),
                on(1)
        }
        ACCESS  read-write
        STATUS  mandatory
        DESCRIPTION
            "When the value is off(0), the printer will never continue auto. "
        ::= { kcprtGeneralEntry 34 }

    kcprtAutoContinueTimer  OBJECT-TYPE
        SYNTAX  INTEGER(0..99)
        ACCESS  read-write
        STATUS  mandatory
        DESCRIPTION
            "When auto continue is on,  this timer value is seted, continue key is pushed after timer value."
        ::= { kcprtGeneralEntry 35 }

    kcprtAbsoluteModelName   OBJECT-TYPE
        SYNTAX  DisplayString   ( SIZE(0..32) )
        ACCESS  read-only
        STATUS  mandatory
        DESCRIPTION
            "The printer's absolute model name."
        ::= { kcprtGeneralEntry 36 }

    kcprtEquipmentID   OBJECT-TYPE
        SYNTAX  DisplayString   ( SIZE(0..16) )
        ACCESS  read-write
        STATUS  mandatory
        DESCRIPTION
            "The octet string corresponding to the equipment ID."
        ::= { kcprtGeneralEntry 37 }

    kcprtMaxCopyCount  OBJECT-TYPE
        SYNTAX  INTEGER
        ACCESS  read-only
        STATUS  mandatory
        DESCRIPTION
            "Max copy count value."
        ::= { kcprtGeneralEntry 38 }

--
--  General->CPU table
--
    kcprtCpuTable   OBJECT-TYPE
        SYNTAX  SEQUENCE OF KcprtCpuEntry
        ACCESS  not-accessible
        STATUS  mandatory
        DESCRIPTION
            "Information of CPU that is implemented in the printer."
        ::={ kcprtGeneral 4 }

    kcprtCpuEntry       OBJECT-TYPE
        SYNTAX  KcprtCpuEntry
        ACCESS  not-accessible
        STATUS  mandatory
        DESCRIPTION
            "A list of CPU information for KYOCERA printer."
        INDEX { hrDeviceIndex, kcprtCpuIndex }
        ::={ kcprtCpuTable 1 }

    KcprtCpuEntry   ::= SEQUENCE {
        kcprtCpuIndex   INTEGER,
        kcprtCpuName    DisplayString,
        kcprtCpuClock   INTEGER,
        kcprtCpuRole    INTEGER,
        kcprtFirmwareVersion    DisplayString,
        kcprtFirmwareUpdate     INTEGER
    }

    kcprtCpuIndex       OBJECT-TYPE
        SYNTAX  INTEGER
        ACCESS  not-accessible
        STATUS  mandatory
        DESCRIPTION
            "A unique value used by the printer to identify CPU on the printer's controller."
        ::={ kcprtCpuEntry 1 }

    kcprtCpuName        OBJECT-TYPE
        SYNTAX  DisplayString ( SIZE(0..31) )
        ACCESS  read-only
        STATUS  mandatory
        DESCRIPTION
            "The CPU model name, such as '68EC040'."
        ::={ kcprtCpuEntry 2 }

    kcprtCpuClock       OBJECT-TYPE
        SYNTAX  INTEGER
        ACCESS  read-only
        STATUS  mandatory
        DESCRIPTION
            "The clock speed of CPU in unit of MHz."
        ::={ kcprtCpuEntry 3 }

    kcprtCpuRole        OBJECT-TYPE
        SYNTAX  INTEGER {
            engine(0),
            controller(1)
        }
        ACCESS  read-only
        STATUS  mandatory
        DESCRIPTION
            "The role of this CPU. The value (-1) means others."
        ::={ kcprtCpuEntry 4 }

    kcprtFirmwareVersion    OBJECT-TYPE
        SYNTAX  DisplayString ( SIZE( 0..31 ) )
        ACCESS  read-only
        STATUS  mandatory
        DESCRIPTION
            "The version string for the firmware of this CPU."
        ::={ kcprtCpuEntry 5 }

    kcprtFirmwareUpdate     OBJECT-TYPE
        SYNTAX  INTEGER {
            enabled(3),
            disabled(4)
        }
        ACCESS  read-only
        STATUS  mandatory
        DESCRIPTION
            "Shows whether this firmware can be updated on the controller."
        ::={ kcprtCpuEntry 6 }

--
--  Input group
--
--      To view and/or control the input unit, especially for the MPF.
--      This goroup was newly added for FS-1700 and FS-3700.
--
    kcprtInputTable OBJECT-TYPE
        SYNTAX  SEQUENCE OF KcprtInputEntry
        ACCESS  not-accessible
        STATUS  mandatory
        DESCRIPTION
            "This table contains the basic part of the input unit. The main purpose is to control the MPF."
        ::={ kcprtInput 1 }

    kcprtInputEntry OBJECT-TYPE
        SYNTAX  KcprtInputEntry
        ACCESS  not-accessible
        STATUS  mandatory
        DESCRIPTION
            "A list of information for the input unit, especially for the MPF."
        INDEX { hrDeviceIndex, kcprtInputIndex }
        ::={ kcprtInputTable 1 }

    KcprtInputEntry ::= SEQUENCE {
        kcprtInputIndex         INTEGER,
        kcprtInputMPtrayMode    INTEGER,
        kcprtInputGroupMember   INTEGER,
        kcprtInputMediaListIndex   INTEGER,
        kcprtInputStatus   INTEGER,
        kcprtInputDialPaperSize   INTEGER,
        kcprtInputOtherPaperSize   INTEGER,
        prtInputCustomDimFeedDirDeclared   INTEGER,
        prtInputCustomDimXFeedDirDeclared   INTEGER,
        kcprnInputMediaMatrix   DisplayString,
        kcprnInputPaperSizeIndex   INTEGER
    }

    kcprtInputIndex OBJECT-TYPE
        SYNTAX  INTEGER
        ACCESS  not-accessible
        STATUS  mandatory
        DESCRIPTION
            "The value of the prtInputIndex of this printer that this entry is associated with."
        ::={ kcprtInputEntry 1 }

    kcprtInputMPtrayMode    OBJECT-TYPE
        SYNTAX  INTEGER{
            cassette(0),
            manual(1),
            first(2),
            notPresent(5)
        }
        ACCESS  read-write
        STATUS  mandatory
        DESCRIPTION
            "The value corresponding to the MPF mode."
        ::={ kcprtInputEntry 2 }

    kcprtInputGroupMember    OBJECT-TYPE
        SYNTAX  INTEGER{
            member(3),
            notMember(4),
            alone(5)
        }
        ACCESS  read-write
        STATUS  mandatory
        DESCRIPTION
            "This object shows the status of grouping. This grouping is also knwon as 'auto cassette' mode. The input subunit with the value member(3) is a member of the cassette group. The value alone(5) means the subunit cannot be a part of the group.
            For FS/LS-7000, the effect is slightly different. One feeder unit (PF-30) consists of two input tray. The input group object corresponds to each tray. The printer only allows each unit to be (or not to be) a part of the group. Therefore, if the monitor application sets the value member(3) to an object that corresponds to an input tray, the other tray on the same unit is also marked as member(3) automatically. This happens also in setting notMember(4) to each tray."
        ::={ kcprtInputEntry 3 }

    kcprtInputMediaListIndex    OBJECT-TYPE
        SYNTAX   INTEGER
        ACCESS   read-write
        STATUS   mandatory
        DESCRIPTION
            "This object holds an index value corresponding to kcprtMediaList table. Therefore, this value represents the current media type settings on each input tray."
        ::={ kcprtInputEntry 4 }

    kcprtInputStatus    OBJECT-TYPE
        SYNTAX   INTEGER{
            ready(0),
            down(1)
        }
        ACCESS   read-only
        STATUS   mandatory
        DESCRIPTION
            ""
        ::={ kcprtInputEntry 5 }

    kcprtInputDialPaperSize    OBJECT-TYPE
        SYNTAX   INTEGER
        ACCESS   read-only
        STATUS   mandatory
        DESCRIPTION
            ""
        ::={ kcprtInputEntry 6 }

    kcprtInputOtherPaperSize    OBJECT-TYPE
        SYNTAX   INTEGER
        ACCESS   read-write
        STATUS   mandatory
        DESCRIPTION
            ""
        ::={ kcprtInputEntry 7 }

prtInputCustomDimFeedDirDeclared OBJECT-TYPE
    SYNTAX  INTEGER (-2147483648..2147483647)
    ACCESS  read-write
    STATUS  mandatory
    DESCRIPTION
           "This object provides the value of the declared dimension, in
        the feed direction, of custom that is (or, if empty, was or
        will be) in this input sub-unit.  The feed direction is the
        direction in which the media is fed on this sub-unit.  This
        dimension is measured in input sub-unit dimensional units
        (prtInputDimUnit).  If this input sub-unit can reliably sense
        this value, the value is sensed by the printer and may not be
        changed by management requests.  Otherwise, the value may be
        changed."
    ::= { kcprtInputEntry  8 }

prtInputCustomDimXFeedDirDeclared OBJECT-TYPE
    SYNTAX  INTEGER (-2147483648..2147483647)
    ACCESS  read-write
    STATUS  mandatory
    DESCRIPTION
           "This object provides the value of the declared dimension, in
        the cross feed direction, of custom that is (or, if empty,
        was or will be) in this input sub-unit.  The cross  feed
        direction is ninety degrees relative to the feed direction
        associated with this sub-unit. This dimension is measured in
        input sub-unit dimensional units (prtInputDimUnit).  If this
        input sub-unit can reliably sense this value, the value is
        sensed by the printer and may not be changed by management
        requests. Otherwise, the value may be changed."
    ::= { kcprtInputEntry  9 }

    kcprnInputMediaMatrix    OBJECT-TYPE
        SYNTAX   DisplayString
        ACCESS   read-only
        STATUS   mandatory
        DESCRIPTION
            ""
        ::={ kcprtInputEntry 10 }

    kcprnInputPaperSizeIndex    OBJECT-TYPE
        SYNTAX   INTEGER
        ACCESS   read-write
        STATUS   mandatory
        DESCRIPTION
            ""
        ::={ kcprtInputEntry 11 }

--
--  Input group table
--
    kcprtInputGroupTable OBJECT-TYPE
        SYNTAX  SEQUENCE OF KcprtInputGroupEntry
        ACCESS  not-accessible
        STATUS  mandatory
        DESCRIPTION
            "This table contains information of the input tray group."
        ::={ kcprtInput 2 }

    kcprtInputGroupEntry OBJECT-TYPE
        SYNTAX  KcprtInputGroupEntry
        ACCESS  not-accessible
        STATUS  mandatory
        DESCRIPTION
            "Information for the input unit group."
        INDEX { hrDeviceIndex, kcprtInputGroupIndex }
        ::={ kcprtInputGroupTable 1 }

    KcprtInputGroupEntry ::= SEQUENCE {
        kcprtInputGroupIndex   INTEGER,
        kcprtInputGroupMode   INTEGER
    }

--
--  The object kcprtInputGroupEntry.1 is missing to prepare
--  for two dimensional object table.
--

    kcprtInputGroupIndex        OBJECT-TYPE
        SYNTAX  INTEGER
        ACCESS  not-accessible
        STATUS  mandatory
        DESCRIPTION
            ""
        ::={ kcprtInputGroupEntry 1 }

    kcprtInputGroupMode OBJECT-TYPE
        SYNTAX  INTEGER {
            off(0),
            group(1),
            size(2),
            all(3)
        }
        ACCESS  read-write
        STATUS  mandatory
        DESCRIPTION
            "This object corresponds to the printer system's auto cassette mode."
        ::={ kcprtInputGroupEntry 2 }

--
--  Output group
--
--      To view and/or control the output unit, especially for SO-6.
--
    kcprtOutputTable    OBJECT-TYPE
        SYNTAX  SEQUENCE OF KcprtOutputEntry
        ACCESS  not-accessible
        STATUS  mandatory
        DESCRIPTION
            "This table contains the basic part of the output unit. The main purpose is to control SO-6."
        ::={ kcprtOutput 1 }

    kcprtOutputEntry    OBJECT-TYPE
        SYNTAX  KcprtOutputEntry
        ACCESS  not-accessible
        STATUS  mandatory
        DESCRIPTION
            "A list of information for the output unit, especially for the SO-6."
        INDEX { hrDeviceIndex, kcprtOutputIndex }
        ::={ kcprtOutputTable 1 }

    KcprtOutputEntry    ::= SEQUENCE {
        kcprtOutputIndex            INTEGER,
        kcprtOutputMode             INTEGER,
        kcprtOutputMultiMode        INTEGER,
        kcprtOutputGroupNumber      INTEGER,
        kcprtOutputDefaultGroup     INTEGER,
        kcprtOutputBulkStatus       INTEGER,
        kcprtOutputTrayMaxCapacity  INTEGER,
        kcprtStapler                PresentOnOff,
        kcprtStaplerConsumableState INTEGER,
        kcprtOutputActionOnFull     INTEGER,
        kcprtOutputPunchStatus      INTEGER,
        kcprtOutputStatus           INTEGER
    }

    kcprtOutputIndex    OBJECT-TYPE
        SYNTAX  INTEGER
        ACCESS  not-accessible
        STATUS  mandatory
        DESCRIPTION
            "The value of the prtOutputIndex of this printer that this entry is associated with."
        ::={ kcprtOutputEntry 1 }

    kcprtOutputMode     OBJECT-TYPE
        SYNTAX  INTEGER {
            sorter(0),
            collator(1),
            stacker(2),
            mailbox(3)
        }
        ACCESS  read-write
        STATUS  mandatory
        DESCRIPTION
            "The operation mode of the sorter.  If this device does not support the sorter function, the reading value is (-1) and all writing are ignored.  Also, writing value (-1) does not take effect."
        ::={ kcprtOutputEntry 2 }

    kcprtOutputMultiMode        OBJECT-TYPE
        SYNTAX  INTEGER {
            off(0),
            id-specific(1),
            if-specific(2)
        }
        ACCESS  read-write
        STATUS  mandatory
        DESCRIPTION
            "In the multiple mode, the sorter can simultaneously be used by different computers.  Each computer may assign its own output trays.  This value determines how the tray is selected.
            The value (-1) means others or 'not supported'."
        ::={ kcprtOutputEntry 3 }

    kcprtOutputGroupNumber      OBJECT-TYPE
        SYNTAX  INTEGER
        ACCESS  read-only
        STATUS  mandatory
        DESCRIPTION
            "This entry shows how many groups are existing on the output device."
        ::={ kcprtOutputEntry 4 }

    kcprtOutputDefaultGroup     OBJECT-TYPE
        SYNTAX  INTEGER
        ACCESS  read-write
        STATUS  mandatory
        DESCRIPTION
            "The value of the kcprtTrayGroupIndex corresponding to the current output tray group in a sorter. This value has no meaning if this output unit is not a soter. The value (0) means that the multiple mode is disabled and all of trays will be able to use. Writing value (0) indicates a selection of bulkTray . Writing is only allowed when the multiple mode is enabled."
        ::={ kcprtOutputEntry 5 }

    kcprtOutputBulkStatus       OBJECT-TYPE
        SYNTAX  INTEGER {
            notFull(0),
            full(1)
        }
        ACCESS  read-only
        STATUS  mandatory
        DESCRIPTION
            "This entry shows current status of the bulk tray. Since the bulk tray of SO-6 has only a full sensor, this entry has only two states. In future, the state will be added."
        ::={ kcprtOutputEntry 6 }

    kcprtOutputTrayMaxCapacity      OBJECT-TYPE
        SYNTAX  INTEGER
        ACCESS  read-only
        STATUS  mandatory
        DESCRIPTION
            "This entry shows how many pages the tray on this output device can hold. Unit is sheet."
        ::={ kcprtOutputEntry 7 }

    kcprtStapler      OBJECT-TYPE
        SYNTAX  PresentOnOff
        ACCESS  read-only
        STATUS  mandatory
        DESCRIPTION
            "This object shows whether or not the stapler device is implemented onto the output subunit. If the device does not have the stapler, the returned value is notPresent(5). However, the old printers do not have this object so that they will response with error 'noSuchName'."
        ::={ kcprtOutputEntry 8 }

    kcprtStaplerConsumableState      OBJECT-TYPE
        SYNTAX  INTEGER
        ACCESS  read-only
        STATUS  mandatory
        DESCRIPTION
            "This object shows the current level of the stapler's consumable (pins). Because the current stapler does not have the inteligent sensor, this object returns atLeastOne(-3) if the level is more than 50 pins, and returns unknown(-2) if the level is less than 50 pins. If kcprtStapler returns 'notPresent(5)', this object returns value (0) to show the stapler (and pin) is not be there."
        ::={ kcprtOutputEntry 9 }

    kcprtOutputActionOnFull       OBJECT-TYPE
        SYNTAX  INTEGER {
            printStoppedWithMessage(0),
            printContinue(1)
        }
        ACCESS  read-write
        STATUS  mandatory
        DESCRIPTION
            "This object shows the action after output tray full."
        ::={ kcprtOutputEntry 10 }

    kcprtOutputPunchStatus       OBJECT-TYPE
        SYNTAX  INTEGER {
            none(0),
            enabled(1)
        }
        ACCESS  read-only
        STATUS  mandatory
        DESCRIPTION
            ""
        ::={ kcprtOutputEntry 11 }

    kcprtOutputStatus       OBJECT-TYPE
        SYNTAX  INTEGER {
            ready(0),
            down(1)
        }
        ACCESS  read-only
        STATUS  mandatory
        DESCRIPTION
            ""
        ::={ kcprtOutputEntry 12 }

--
--  Output->TrayGroup table
--
--      To see the multiple tray output device, such as SO-6.
--
kcprtTrayGroupTable     OBJECT-TYPE
    SYNTAX  SEQUENCE OF KcprtTrayGroupEntry
    ACCESS  not-accessible
    STATUS  mandatory
    DESCRIPTION
        "The concept of Group is for the multiple computer environment.  These contents take effect when kcprtOutputMultiMode is enable.  For further information, refer to the sorter manual. Note in case of off (0), the access to this content is ineffective."
    ::={ kcprtOutput 2 }

    kcprtTrayGroupEntry     OBJECT-TYPE
        SYNTAX  KcprtTrayGroupEntry
        ACCESS  not-accessible
        STATUS  mandatory
        DESCRIPTION
            "A list of information about the tray group on the multiple tray device."
        INDEX { hrDeviceIndex, kcprtOutputIndex, kcprtTrayGroupIndex }
        ::={ kcprtTrayGroupTable 1 }

    KcprtTrayGroupEntry ::= SEQUENCE {
        kcprtTrayGroupIndex         INTEGER,
        kcprtTrayGroupBeginIndex    INTEGER,
        kcprtTrayGroupEndIndex      INTEGER
    }

    kcprtTrayGroupIndex     OBJECT-TYPE
    SYNTAX  INTEGER
    ACCESS  not-accessible
    STATUS  mandatory
    DESCRIPTION
        "The unique value used by the printer to identify each tray groups.  Note that this value will be changed while the printer power cycles if Prescribe ASTK command is issued."
    ::={ kcprtTrayGroupEntry 1 }

    kcprtTrayGroupBeginIndex        OBJECT-TYPE
        SYNTAX  INTEGER
        ACCESS  read-only
        STATUS  mandatory
        DESCRIPTION
            "The value of the kcprtOutputTrayIndex corresponding to the tray that is assigned as the begining of this group."
        ::={ kcprtTrayGroupEntry 2 }

    kcprtTrayGroupEndIndex      OBJECT-TYPE
        SYNTAX  INTEGER
        ACCESS  read-only
        STATUS  mandatory
        DESCRIPTION
            "The value of the kcprtOutputTrayIndex corresponding to the tray that is assigned as the end of this group.  This index is automatically assigned by the printer when the group is created. Please refer to thePrescribe manual for detailed information."
        ::={ kcprtTrayGroupEntry 3 }


--
--  Output->Tray table
--
--      To see and control the individual tray.
--
    kcprtOutputTrayTable        OBJECT-TYPE
        SYNTAX  SEQUENCE OF KcprtOutputTrayEntry
        ACCESS  not-accessible
        STATUS  mandatory
        DESCRIPTION
            "Note in case of off (0), the access to this content is ineffective."
        ::={ kcprtOutput 3 }

    kcprtOutputTrayEntry        OBJECT-TYPE
        SYNTAX  KcprtOutputTrayEntry
        ACCESS  not-accessible
        STATUS  mandatory
        DESCRIPTION
            "A list of information about the individual tray."
        INDEX{ hrDeviceIndex, kcprtOutputIndex, kcprtOutputTrayIndex }
        ::={ kcprtOutputTrayTable 1 }

    KcprtOutputTrayEntry    ::= SEQUENCE {
        kcprtOutputTrayIndex    INTEGER,
        kcprtOutputTrayOrder    INTEGER,
        kcprtOutputTrayGroup    INTEGER,
        kcprtOutputTrayCount    INTEGER,
        kcprtOutputTrayName    DisplayString
    }

    kcprtOutputTrayIndex        OBJECT-TYPE
        SYNTAX  INTEGER
        ACCESS  not-accessible
        STATUS  mandatory
        DESCRIPTION
            "The unique value used by a printer to identify each trays. Values are expected to remain stable across successive printer power cycle. This contents has no meaning except for a sorter device."
        ::={ kcprtOutputTrayEntry 1 }

    kcprtOutputTrayOrder        OBJECT-TYPE
        SYNTAX  INTEGER
        ACCESS  read-only
        STATUS  mandatory
        DESCRIPTION
            "The output order for trays. The beginning number is (1) and the last number should be equal to the maximum tray number.
            When the multiple mode is  available, the order in the appropriate group is determined by this entry.
            The number should be unique and continuous in one group or the whole if the group function is disabled.
            The value (0) means the order has not been determined. In case all of the trays are not determined, the sorter will operate in default settings. About default settings, refer to the sorter's manual. Currently this entry is read-only."
        ::={ kcprtOutputTrayEntry 2 }

    kcprtOutputTrayGroup        OBJECT-TYPE
        SYNTAX  INTEGER
        ACCESS  read-only
        STATUS  mandatory
        DESCRIPTION
            "The value of kcprtTrayGroupIndex corresponding to the group that this tray is assigned to. The value (0) means this tray is not assigned to a group or the multiple mode is disable."
        ::={ kcprtOutputTrayEntry 3 }

    kcprtOutputTrayCount        OBJECT-TYPE
        SYNTAX  INTEGER
        ACCESS  read-only
        STATUS  mandatory
        DESCRIPTION
            "The count of page that the tray may be holding. Since the tray cannot count the page that it has currently, the value is not always same as the actual page counts.
            If all of paper is removed, this value will be 0. In SO-6, there is no full sensor. So, if the application needs to know whether the tray is full or not, the application should compare this value with OutputTrayMaxCapacity.
            In some case, the printer is turned on with remaining some pages on the tray for example, this value will be same as MaxCapacity to inform that paper is remaining and demand to remove the page."
        ::={ kcprtOutputTrayEntry 4 }

    kcprtOutputTrayName        OBJECT-TYPE
        SYNTAX  DisplayString ( SIZE(0..15) )
        ACCESS  read-write
        STATUS  mandatory
        DESCRIPTION
            "The name of tray is setted by user."
        ::={ kcprtOutputTrayEntry 5 }

--
--  Output->Punch table
--
--      To see and control the individual tray.
--
    kcprtPunchGroupTable        OBJECT-TYPE
        SYNTAX  SEQUENCE OF KcprtPunchGroupEntry
        ACCESS  not-accessible
        STATUS  mandatory
        DESCRIPTION
            "Note in case of off (0), the access to this content is ineffective."
        ::={ kcprtOutput 4 }

    kcprtPunchGroupEntry        OBJECT-TYPE
        SYNTAX  KcprtPunchGroupEntry
        ACCESS  not-accessible
        STATUS  mandatory
        DESCRIPTION
            "A list of information about the punch."
        INDEX{ hrDeviceIndex, kcprtPunchGroupIndex }
        ::={ kcprtPunchGroupTable 1 }

    KcprtPunchGroupEntry    ::= SEQUENCE {
        kcprtPunchGroupIndex    INTEGER,
        kcprtPunchGroupName     DisplayString,
        kcprtPunchGroupHoleNumber    INTEGER,
        kcprtPunchGroupType     DisplayString
    }

    kcprtPunchGroupIndex        OBJECT-TYPE
        SYNTAX  INTEGER
        ACCESS  not-accessible
        STATUS  mandatory
        DESCRIPTION
            ""
        ::={ kcprtPunchGroupEntry 1 }

    kcprtPunchGroupName        OBJECT-TYPE
        SYNTAX  DisplayString ( SIZE( 0..15 ) )
        ACCESS  read-only
        STATUS  mandatory
        DESCRIPTION
            "The punch group name. main or sub."
        ::={ kcprtPunchGroupEntry 2 }

    kcprtPunchGroupHoleNumber     OBJECT-TYPE
        SYNTAX  INTEGER
        ACCESS  read-only
        STATUS  mandatory
        DESCRIPTION
            "The value(2) is overseas centimeter or internal .The value(3) is overseas centimeter.The value(4) is france or sweden.
             The value(0) is US."
        ::={ kcprtPunchGroupEntry 3 }

    kcprtPunchGroupType        OBJECT-TYPE
        SYNTAX  DisplayString ( SIZE( 0..15 ) )
        ACCESS  read-only
        STATUS  mandatory
        DESCRIPTION
            "The punch group type.The US is overseas inch. The SE is sweden. The FR is france. The EU is overseas centimeter.
             The JP is internal."
        ::={ kcprtPunchGroupEntry 4 }

--
--  Marker
--
--      To see and control the marker unit specific for KYOCERA printer.
--
    kcprtMarkerTable        OBJECT-TYPE
        SYNTAX  SEQUENCE OF KcprtMarkerEntry
        ACCESS  not-accessible
        STATUS  mandatory
        DESCRIPTION
            "This table contains some useful entries to control the marker specific function."
        ::={ kcprtMarker 1 }

    kcprtMarkerEntry        OBJECT-TYPE
        SYNTAX  KcprtMarkerEntry
        ACCESS  not-accessible
        STATUS  mandatory
        DESCRIPTION
            "A list of entries that corresponds each function of the marker."
        INDEX{ hrDeviceIndex, prtMarkerIndex }
        ::={ kcprtMarkerTable 1 }

    KcprtMarkerEntry    ::= SEQUENCE {
        kcprtMarkerIndex                            INTEGER,
        kcprtMarkerKirLevel                         INTEGER,
        kcprtMarkerEcoprintLevel                    INTEGER,
        kcprtMarkerAddressabilityFeedDirDeclared    INTEGER,
        kcprtMarkerAddressabilityXFeedDirDeclared   INTEGER,
        kcprtMarkerAddressabilityFeedDirChosen      INTEGER,
        kcprtMarkerAddressabilityXFeedDirChosen     INTEGER,
        kcprtMarkerDrumCounter                      INTEGER,
        kcprtMarkerColorMode                        INTEGER,
        kcprtMarkerBitsPerPixel                     INTEGER,
        kcprtMarkerGlossMode                        INTEGER,
        kcprtMarkerServiceCount                     INTEGER
    }

    kcprtMarkerIndex        OBJECT-TYPE
        SYNTAX  INTEGER
        ACCESS  not-accessible
        STATUS  mandatory
        DESCRIPTION
            "The value of the prtMarkerIndex of the printer devices with which it is associated."
        ::={ kcprtMarkerEntry 1 }

    kcprtMarkerKirLevel     OBJECT-TYPE
        SYNTAX  INTEGER {
            offOrNotSupport(0),
            light(1),
            medium(2),
            dark(3)
        }
        ACCESS  read-write
        STATUS  mandatory
        DESCRIPTION
            "The value that shows current KIR level. The value (0) means off or not support (0)."
        ::={ kcprtMarkerEntry 2 }

    kcprtMarkerEcoprintLevel        OBJECT-TYPE
        SYNTAX  INTEGER {
            offOrNotSupport(0),
            light(1),
            medium(2),
            dark(3)
        }
        ACCESS  read-write
        STATUS  mandatory
        DESCRIPTION
            "The value that shows current Ecoprint level. The value (0) means off or not support."
        ::={ kcprtMarkerEntry 3 }

    kcprtMarkerAddressabilityFeedDirDeclared        OBJECT-TYPE
        SYNTAX  INTEGER
        ACCESS  read-write
        STATUS  mandatory
        DESCRIPTION
            "This object provides the value of the declared addressability, in the feed direction, of this marker. This addressability is measured in prtMarkerAddressabilityUnit."
        ::={ kcprtMarkerEntry 4 }

    kcprtMarkerAddressabilityXFeedDirDeclared       OBJECT-TYPE
        SYNTAX  INTEGER
        ACCESS  read-write
        STATUS  mandatory
        DESCRIPTION
            "This object provides the value of declared dimension, in the cross feed direction, of this marker device. This addressability is measured in prtMarkerAddressabilityUnit."
        ::={ kcprtMarkerEntry 5 }

    kcprtMarkerAddressabilityFeedDirChosen     OBJECT-TYPE
        SYNTAX  INTEGER
        ACCESS  read-only
        STATUS  mandatory
        DESCRIPTION
            "The value of the addressability, in the feed direction,  chosen by the printer. If the printer supports the declared addressability, this addressability is the same as the declared addressability. If not, this addressability is set to the closest addressability that the printer supports when the declared dimension is set."
        ::={ kcprtMarkerEntry 6 }

    kcprtMarkerAddressabilityXFeedDirChosen        OBJECT-TYPE
        SYNTAX  INTEGER
        ACCESS  read-only
        STATUS  mandatory
        DESCRIPTION
            "The value of the addressability, in the cross feed direction,  chosen by the printer. If the printer supports the declared addressability, this addressability is the same as the declared addressability. If not, this addressability is set to the closest addressability that the printer supports when the declared dimension is set."
        ::={ kcprtMarkerEntry 7 }

    kcprtMarkerDrumCounter      OBJECT-TYPE
        SYNTAX  INTEGER
        ACCESS  read-only
        STATUS  mandatory
        DESCRIPTION
            "The value of the drum counter. This value may not be same as any counter in the prtMarker group. The unit is prtMarkerCounterUnit.
            This object was newly added for FS-1700 and FS-3700."
        ::={ kcprtMarkerEntry 8 }

    kcprtMarkerColorMode        OBJECT-TYPE
        SYNTAX  INTEGER {
                monochrome(1),
                color(4)
        }
        ACCESS      read-write
        STATUS      mandatory
        DESCRIPTION
            "This object shows the current color mode of this marker device."
        ::={ kcprtMarkerEntry 9 }

    kcprtMarkerBitsPerPixel        OBJECT-TYPE
        SYNTAX  INTEGER
        ACCESS  read-write
        STATUS  mandatory
        DESCRIPTION
            "This object shows Bit/Pixel value."
        ::={ kcprtMarkerEntry 10 }

    kcprtMarkerGlossMode        OBJECT-TYPE
        SYNTAX  INTEGER {
                low(0),
                high(1)
        }
        ACCESS  read-write
        STATUS  mandatory
        DESCRIPTION
            "This object shows Gloss mode value."
        ::={ kcprtMarkerEntry 11 }

    kcprtMarkerServiceCount        OBJECT-TYPE
        SYNTAX  INTEGER
        ACCESS  read-only
        STATUS  mandatory
        DESCRIPTION
            "Added by Observium Developers"
        ::={ kcprtMarkerEntry 12 }

--
--  Colorant group
--
--
--
    kcprtColorantGeneralTable   OBJECT-TYPE
        SYNTAX  SEQUENCE OF KcprtColorantGeneralEntry
        ACCESS  not-accessible
        STATUS  mandatory
        DESCRIPTION
            ""
        ::={ kcprtColorant 1 }

    kcprtColorantGeneralEntry       OBJECT-TYPE
        SYNTAX  KcprtColorantGeneralEntry
        ACCESS  not-accessible
        STATUS  mandatory
        DESCRIPTION
            ""
        INDEX{ hrDeviceIndex }
        ::={ kcprtColorantGeneralTable 1 }

    KcprtColorantGeneralEntry       ::= SEQUENCE {
        kcprtColorQuality           INTEGER,
        kcprtColorMatching          INTEGER,
        kcprtColorantIdentifier     OCTET STRING,
        kcprtRGBSimulation                INTEGER,
        kcprtCMYKSimulation         INTEGER
    }

    kcprtColorQuality       OBJECT-TYPE
        SYNTAX      INTEGER {
            normal(0),
            quick(1),
            fine(2),
            presentation(3)
        }
        ACCESS      read-only
        STATUS      optional
        DESCRIPTION
        "Shows current quarity in color mode. If the printer does not support color, a value of notSupported(-2) is returned."
    ::={ kcprtColorantGeneralEntry 1 }

    kcprtColorMatching  OBJECT-TYPE
        SYNTAX      INTEGER {
            off(0),
            auto(1),
            vivid(2),
            display(3)
        }
        ACCESS      read-only
        STATUS      optional
        DESCRIPTION
        "Shows the color matching mode. If printer does not support color, this object will always give notSupported(-2), or this object will not be implemented. DisplayCompliant(3) shows the printer is doing color matching with refering a certaing display."
    ::={ kcprtColorantGeneralEntry 2 }

    kcprtColorantIdentifier OBJECT-TYPE
        SYNTAX      OCTET STRING( SIZE(0..16) )
        ACCESS      read-only
        STATUS      optional
        DESCRIPTION
        "Some identifier to identify the color unit uniquely."
    ::={ kcprtColorantGeneralEntry 3 }

    kcprtRGBSimulation  OBJECT-TYPE
        SYNTAX      INTEGER {
            none(0),
            smtpe240m(1),
            hdtv(2),
            trinitron(3),
            applergb(4),
            ntsc(5),
            kcrgb(6),
            custom(7)
        }
        ACCESS      read-only
        STATUS      optional
        DESCRIPTION
        "Shows the color RGB\81@Simulation. "
    ::={ kcprtColorantGeneralEntry 4 }

    kcprtCMYKSimulation  OBJECT-TYPE
        SYNTAX      INTEGER {
            normal(0),
            none(1),
            swop(2),
            euroscale(3),
            toyo(4),
            dic(5)
        }
        ACCESS      read-only
        STATUS      optional
        DESCRIPTION
        "Shows the color CMYK\81@Simulation. "
    ::={ kcprtColorantGeneralEntry 5 }

--
--  Channel group
--
--      To control the HEX dump function
--
    kcprtChannelTable       OBJECT-TYPE
        SYNTAX  SEQUENCE OF KcprtChannelEntry
        ACCESS  not-accessible
        STATUS  mandatory
        DESCRIPTION
            "This table control's HEX dump function."
        ::={ kcprtChannel 1 }

    kcprtChannelEntry       OBJECT-TYPE
        SYNTAX  KcprtChannelEntry
        ACCESS  not-accessible
        STATUS  mandatory
        DESCRIPTION
            ""
        INDEX{ hrDeviceIndex, kcprtChannelIndex }
        ::={ kcprtChannelTable 1 }

    KcprtChannelEntry       ::= SEQUENCE {
        kcprtChannelIndex       INTEGER,
        kcprtChannelMode        INTEGER,
        kcprtChannelCopyCount   INTEGER,
        kcprtChannelResolution  INTEGER,
        kcprtChannelPaperSize   INTEGER,
        kcprtHostBufferRatio    INTEGER,
        kcprtChannelErrorCounter    INTEGER
    }

    kcprtChannelIndex       OBJECT-TYPE
        SYNTAX  INTEGER
        ACCESS  not-accessible
        STATUS  mandatory
        DESCRIPTION
            "The value of the prtChannelIndex of the printer device that this prtChannelEntry is associated with."
        ::={ kcprtChannelEntry 1 }

    kcprtChannelMode        OBJECT-TYPE
        SYNTAX  INTEGER {
            through(0),
            hexDump(1)
        }
        ACCESS  read-write
        STATUS  mandatory
        DESCRIPTION
            "The current state of the mode of this channel. KYOCERA printer can set the hex dump mode to interface (channel). Writing affects all interface(channel).This setting is only valid for one job. After processing the job, this entry automatically returns through(0).
            This object used to be named kcprtChannelFunction."
        ::={ kcprtChannelEntry 2 }

    kcprtChannelCopyCount       OBJECT-TYPE
        SYNTAX  INTEGER (1..999)
        ACCESS  read-write
        STATUS  mandatory
        DESCRIPTION
            "The value corresponding to the copy count for each channel (interface). Kyocera printer manages the value for each interface individually.
            This object was newly added for FS-1700 and FS-3700."
        ::={ kcprtChannelEntry 3 }

    kcprtChannelResolution      OBJECT-TYPE
        SYNTAX  INTEGER
        ACCESS  read-write
        STATUS  mandatory
        DESCRIPTION
            "The value corresponding to the resolution for each channel (interface). Kyocera printer manages this setting for each interface individually.
            This object was newly added for FS-1700 and FS-3700."
        ::={ kcprtChannelEntry 4 }

    kcprtChannelPaperSize       OBJECT-TYPE
        SYNTAX  INTEGER
        ACCESS  read-write
        STATUS  mandatory
        DESCRIPTION
            "This value shows the current setting of the paper size for this channel. Kyocera printer manages this setting of each interface individually.
            This object was newly added for FS-1700 and FS-3700."
        ::={ kcprtChannelEntry 5 }

    kcprtHostBufferRatio       OBJECT-TYPE
        SYNTAX  INTEGER
        ACCESS  read-write
        STATUS  optional
        DESCRIPTION
            "This object shows the current ratio of each host buffer blocks. If kcprtHostBufferOption is automatic, there is no actual relation between the host buffer block and a channel that have same kcprtChannelIndex value. The first buffer will be assigned automatically by the printer system to a channel that is about to receive data. If value of kcprtHostBufferOption is fixed, the channel and the host buffer block that have same kcprtChannelIndex have fixed relation each other."
        ::={ kcprtChannelEntry 6 }

    kcprtChannelErrorCounter       OBJECT-TYPE
        SYNTAX  INTEGER	(0..4294967295)
        ACCESS  read-only
        STATUS  optional
        DESCRIPTION
            "This object shows the error counter of each channel. When it reaches its maximum value, it will return to zero."
        ::={ kcprtChannelEntry 7 }

--
--  Buzzer group
--
--  This group was newly added for FS-1700 and FS-3700.
--
    kcprtBuzzerTable        OBJECT-TYPE
        SYNTAX  SEQUENCE OF KcprtBuzzerEntry
        ACCESS  not-accessible
        STATUS  mandatory
        DESCRIPTION
            "This table contains information for each Buzzer device.
            This group was newly added for FS-1700 and FS-3700."
        ::={ kcprtBuzzer 1 }

    kcprtBuzzerEntry        OBJECT-TYPE
        SYNTAX  KcprtBuzzerEntry
        ACCESS  not-accessible
        STATUS  mandatory
        DESCRIPTION
            "A list of entries that are corresponding to each functions for the buzzer."
        INDEX   { hrDeviceIndex,  kcprtBuzzerIndex }
        ::={ kcprtBuzzerTable 1 }

    KcprtBuzzerEntry  ::= SEQUENCE {
        kcprtBuzzerIndex    INTEGER,
        kcprtBuzzerOnTime   INTEGER,
        kcprtBuzzerOffTime  INTEGER,
        kcprtBuzzerMode     INTEGER,
        kcprtBuzzerTone     INTEGER
    }

    kcprtBuzzerIndex        OBJECT-TYPE
        SYNTAX  INTEGER
        ACCESS  not-accessible
        STATUS  mandatory
        DESCRIPTION
            "The index used by the printer to identify each buzzer device. This value will not change while power cycle."
        ::={ kcprtBuzzerEntry 1 }

    kcprtBuzzerOnTime       OBJECT-TYPE
        SYNTAX  INTEGER (0..400)
        ACCESS  read-only
        STATUS  mandatory
        DESCRIPTION
            "The time in milliseconds while the buzzer is beeping. If this value is 0, it means the buzzer is not beeping. This object can have three values, 0, 200 and 400."
        ::={ kcprtBuzzerEntry 2 }

    kcprtBuzzerOffTime      OBJECT-TYPE
        SYNTAX  INTEGER (0..400)
        ACCESS  read-only
        STATUS  mandatory
        DESCRIPTION
            "The time in milliseconds while the buzzer is not beeping. This object can have three values, 9, 200, and 400."
        ::={ kcprtBuzzerEntry 3 }

    kcprtBuzzerMode     OBJECT-TYPE
        SYNTAX  INTEGER {
            off(0),
            on(1)
        }
        ACCESS  read-write
        STATUS  mandatory
        DESCRIPTION
            "If the value is On, the buzzer will be activated in the case of printer's error events. Note that this object cannot stop the buzzer that has already been beeping."
        ::={ kcprtBuzzerEntry 4 }

    kcprtBuzzerTone     OBJECT-TYPE
        SYNTAX  INTEGER (0..30000)
        ACCESS  read-only
        STATUS  mandatory
        DESCRIPTION
            "The value showing the buzzer's output frequency in mega hertz."
        ::={ kcprtBuzzerEntry 5 }

--
--  Alert group
--
--      Error log part
--
    kcprtAlertTable   OBJECT-TYPE
        SYNTAX  SEQUENCE OF KcprtAlertEntry
        ACCESS  not-accessible
        STATUS  mandatory
        DESCRIPTION
            ""
        ::= { kcprtAlert 1 }

    kcprtAlertEntry   OBJECT-TYPE
        SYNTAX  KcprtAlertEntry
        ACCESS  not-accessible
        STATUS  mandatory
        DESCRIPTION
            ""
        INDEX   { hrDeviceIndex, kcprtAlertIndex }
        ::= { kcprtAlertTable 1 }

    KcprtAlertEntry   ::= SEQUENCE {
                    kcprtAlertIndex         INTEGER,
                    kcprtAlertInformation   OCTET STRING
            }

    kcprtAlertIndex OBJECT-TYPE
        SYNTAX  INTEGER
        ACCESS  not-accessible
        STATUS  mandatory
        DESCRIPTION
            ""
        ::={ kcprtAlertEntry 1 }

     kcprtAlertInformation OBJECT-TYPE
        SYNTAX  OCTET STRING(SIZE(32))
        ACCESS  read-only
        STATUS  mandatory
        DESCRIPTION
            ""
        ::={ kcprtAlertEntry 2 }

--
--  Alert->AlertState table
--

    kcprtAlertStateTable   OBJECT-TYPE
        SYNTAX  SEQUENCE OF KcprtAlertStateEntry
        ACCESS  not-accessible
        STATUS  mandatory
        DESCRIPTION
            ""
        ::= { kcprtAlert 2 }

    kcprtAlertStateEntry   OBJECT-TYPE
        SYNTAX  KcprtAlertStateEntry
        ACCESS  not-accessible
        STATUS  mandatory
        DESCRIPTION
            ""
        INDEX   { hrDeviceIndex, kcprtAlertStateDisplayIndex }
        ::= { kcprtAlertStateTable 1 }

    KcprtAlertStateEntry   ::= SEQUENCE {
                    kcprtAlertStateDisplayIndex     INTEGER,
                    kcprtAlertStateDisplay          DisplayString,
                    kcprtAlertStateCode             INTEGER
            }

    kcprtAlertStateDisplayIndex OBJECT-TYPE
        SYNTAX  INTEGER
        ACCESS  not-accessible
        STATUS  mandatory
        DESCRIPTION
            ""
        ::={ kcprtAlertStateEntry 1 }

    kcprtAlertStateDisplay OBJECT-TYPE
        SYNTAX  DisplayString ( SIZE(0..31) )
        ACCESS  read-only
        STATUS  mandatory
        DESCRIPTION
            ""
        ::={ kcprtAlertStateEntry 2 }

   kcprtAlertStateCode OBJECT-TYPE
        SYNTAX  INTEGER
        ACCESS  read-only
        STATUS  mandatory
        DESCRIPTION
            ""
        ::={ kcprtAlertStateEntry 3 }


kcprtAlertJamLogTable	OBJECT-TYPE
SYNTAX		SEQUENCE OF KcprtAlertJamLogEntry
ACCESS		not-accessible
STATUS		mandatory
DESCRIPTION
"JAM\97\9A\97\F0\83\8D\83O\8F\EE\95\F1\82\F0\8AǗ\9D\82\B7\82\E9\83e\81[\83u\83\8B"
::= { kcprtAlert 3 }

kcprtAlertJamLogEntry	OBJECT-TYPE
SYNTAX		KcprtAlertJamLogEntry
ACCESS		not-accessible
STATUS		mandatory
DESCRIPTION
"JAM\97\9A\97\F0\83\8D\83O\83e\81[\83u\83\8B\82̃G\83\93\83g\83\8A"
INDEX	{ hrDeviceIndex, kcprtAlertJamLogIndex }
::= { kcprtAlertJamLogTable 1 }

KcprtAlertJamLogEntry	::= SEQUENCE {
kcprtAlertJamLogIndex		INTEGER,
kcprtAlertJamLogStamp		INTEGER,
kcprtAlertJamLogFactor		DisplayString,
kcprtAlertJamLogPosition		DisplayString,
kcprtAlertJamLogInput		INTEGER,
kcprtAlertJamLogPaper		INTEGER,
kcprtAlertJamLogMedia		INTEGER,
kcprtAlertJamLogOutput		INTEGER
}

kcprtAlertJamLogIndex	OBJECT-TYPE
SYNTAX		INTEGER
ACCESS		not-accessible
STATUS		mandatory
DESCRIPTION
            "JAM\97\9A\97\F0\83\8D\83O\82\F0\8E\AF\95ʂ\B7\82邽\82߂̃C\83\93\83f\83b\83N\83X"
        ::={ kcprtAlertJamLogEntry 1 }

kcprtAlertJamLogStamp	OBJECT-TYPE
SYNTAX		INTEGER
ACCESS		read-only
STATUS		mandatory
DESCRIPTION
            "JAM \94\AD\90\B6\8E\9E\82̃g\81[\83^\83\8B\83J\83E\83\93\83^\92l"
        ::={ kcprtAlertJamLogEntry 2 }

kcprtAlertJamLogFactor	OBJECT-TYPE
SYNTAX		DisplayString
ACCESS		read-only
STATUS		mandatory
DESCRIPTION
            "JAM\94\AD\90\B6\8E\9E\82\CCJAM\97v\88\F6\83R\81[\83h\82\F0\8E\A6\82\B7\95\B6\8E\9A\97\F1\81BJ01\81AJ02\A5\A5\A5\81B"
        ::={ kcprtAlertJamLogEntry 3 }

kcprtAlertJamLogPosition	OBJECT-TYPE
SYNTAX		DisplayString
ACCESS		read-only
STATUS		mandatory
DESCRIPTION
            "JAM\94\AD\90\B6\8E\9E\82\CCJAM\88ʒu\82\F0\8E\A6\82\B7\95\B6\8E\9A\97\F1\81B1\81A2\81A3\81A4\81AA\81AB\81AC\A5\A5\A5\81B"
        ::={ kcprtAlertJamLogEntry 4 }

kcprtAlertJamLogInput	OBJECT-TYPE
SYNTAX		INTEGER
ACCESS		read-only
STATUS		mandatory
DESCRIPTION
            "JAM\94\AD\90\B6\8E\9E\82ɗp\8E\86\82\F0\88\F8\82\A2\82\BD\8B\8B\8E\86\92i\81B\92l\82\CDPrescribe\82\CCPSRC\92l"
        ::={ kcprtAlertJamLogEntry 5 }

kcprtAlertJamLogPaper	OBJECT-TYPE
SYNTAX		INTEGER
ACCESS		read-only
STATUS		mandatory
DESCRIPTION
            "JAM\94\AD\90\B6\8E\9E\82̗p\8E\86\83T\83C\83Y\81B\92l\82\CDPrescribe\82\CCSPSZ\92l"
        ::={ kcprtAlertJamLogEntry 6 }

kcprtAlertJamLogMedia	OBJECT-TYPE
SYNTAX		INTEGER
ACCESS		read-only
STATUS		mandatory
DESCRIPTION
            "JAM\94\AD\90\B6\8E\9E\82̗p\8E\86\83^\83C\83v\81B\92l\82\CDPrescribe\82\CCMTYP\92l"
        ::={ kcprtAlertJamLogEntry 7 }

kcprtAlertJamLogOutput	OBJECT-TYPE
SYNTAX		INTEGER
ACCESS		read-only
STATUS		mandatory
DESCRIPTION
            "JAM\94\AD\90\B6\8E\9E\82̔r\8Fo\90\E6\81B\92l\82\CDPrescribe\82\CCOTRY\92l"
        ::={ kcprtAlertJamLogEntry 8 }


kcprtAlertCallLogTable	OBJECT-TYPE
SYNTAX		SEQUENCE OF KcprtAlertCallLogEntry
ACCESS		not-accessible
STATUS		mandatory
DESCRIPTION
"Call Service\97\9A\97\F0\83\8D\83O\8F\EE\95\F1\82\F0\8AǗ\9D\82\B7\82\E9\83e\81[\83u\83\8B"
::= { kcprtAlert 4 }

kcprtAlertCallLogEntry	OBJECT-TYPE
SYNTAX		KcprtAlertCallLogEntry
ACCESS		not-accessible
STATUS		mandatory
DESCRIPTION
"Call Service\97\9A\97\F0\83\8D\83O\83e\81[\83u\83\8B\82̃G\83\93\83g\83\8A"
INDEX	{ hrDeviceIndex, kcprtAlertCallLogIndex }
::= { kcprtAlertCallLogTable 1 }

KcprtAlertCallLogEntry	::= SEQUENCE {
kcprtAlertCallLogIndex		INTEGER,
kcprtAlertCallLogStamp		INTEGER,
kcprtAlertCallLogFactor		DisplayString
}

kcprtAlertCallLogIndex	OBJECT-TYPE
SYNTAX		INTEGER
ACCESS		not-accessible
STATUS		mandatory
DESCRIPTION
            "Call Service\97\9A\97\F0\83\8D\83O\82\F0\8E\AF\95ʂ\B7\82邽\82߂̃C\83\93\83f\83b\83N\83X"
        ::={ kcprtAlertCallLogEntry 1 }

kcprtAlertCallLogStamp	OBJECT-TYPE
SYNTAX		INTEGER
ACCESS		read-only
STATUS		mandatory
DESCRIPTION
            "Call Service\94\AD\90\B6\8E\9E\82̃g\81[\83^\83\8B\83J\83E\83\93\83^\92l"
        ::={ kcprtAlertCallLogEntry 2 }

kcprtAlertCallLogFactor	OBJECT-TYPE
SYNTAX		DisplayString
ACCESS		read-only
STATUS		mandatory
DESCRIPTION
" Call Service\94\AD\90\B6\8E\9E\82\CCCall Service\83R\81[\83h\81iCall\94ԍ\86\81j\82\A8\82\E6\82ь̏\E1\90؂藣\82\B5\83R\81[\83h\82\F0\8E\A6\82\B7\95\B6\8E\9A\97\F1\81BC0001\81AC6500\81ACF030\81AF0001\81AF0002\A5\A5\A5\81B"
        ::={ kcprtAlertCallLogEntry 3 }


kcprtAlertChangeLogTable	OBJECT-TYPE
SYNTAX		SEQUENCE OF KcprtAlertChangeLogEntry
ACCESS		not-accessible
STATUS		mandatory
DESCRIPTION
""
::= { kcprtAlert 5 }

kcprtAlertChangeLogEntry	OBJECT-TYPE
SYNTAX		KcprtAlertChangeLogEntry
ACCESS		not-accessible
STATUS		mandatory
DESCRIPTION
"\8F\C1\96Օi\8C\F0\8A\B7\97\9A\97\F0\83\8D\83O\83e\81[\83u\83\8B\82̃G\83\93\83g\83\8A"
INDEX	{ hrDeviceIndex, kcprtAlertChangeLogIndex }
::= { kcprtAlertChangeLogTable 1 }

KcprtAlertChangeLogEntry	::= SEQUENCE {
kcprtAlertChangeLogIndex		INTEGER,
kcprtAlertChangeLogStamp		INTEGER,
kcprtAlertChangeLogKind		DisplayString
}

kcprtAlertChangeLogIndex	OBJECT-TYPE
SYNTAX		INTEGER
ACCESS		not-accessible
STATUS		mandatory
DESCRIPTION
            "\8F\C1\96Օi\8C\F0\8A\B7\97\9A\97\F0\83\8D\83O\82\F0\8E\AF\95ʂ\B7\82邽\82߂̃C\83\93\83f\83b\83N\83X"
        ::={ kcprtAlertChangeLogEntry 1 }

kcprtAlertChangeLogStamp	OBJECT-TYPE
SYNTAX		INTEGER
ACCESS		read-only
STATUS		mandatory
DESCRIPTION
            "\8F\C1\96Օi\8C\F0\8A\B7\94\AD\90\B6\8E\9E\82̃g\81[\83^\83\8B\83J\83E\83\93\83^\92l"
        ::={ kcprtAlertChangeLogEntry 2 }

kcprtAlertChangeLogKind	OBJECT-TYPE
SYNTAX		DisplayString
ACCESS		read-only
STATUS		mandatory
DESCRIPTION
            ""
        ::={ kcprtAlertChangeLogEntry 3 }


kcprtAlertEventCountTable	OBJECT-TYPE
SYNTAX		SEQUENCE OF KcprtAlertEventCountEntry
ACCESS		not-accessible
STATUS		mandatory
DESCRIPTION
"JAM\81ACall Service\81A\8F\C1\96Օi\8C\F0\8A\B7\93\99\82̃C\83x\83\93\83g\94\AD\90\B6\89񐔏\EE\95\F1\82\F0\8AǗ\9D\82\B7\82\E9\83e\81[\83u\83\8B"
::= { kcprtAlert 6 }

kcprtAlertEventCountEntry	OBJECT-TYPE
SYNTAX		KcprtAlertEventCountEntry
ACCESS		not-accessible
STATUS		mandatory
DESCRIPTION
""
INDEX	{ hrDeviceIndex, kcprtAlertEventCountIndex }
::= { kcprtAlertEventCountTable 1 }

KcprtAlertEventCountEntry	::= SEQUENCE {
kcprtAlertEventCountIndex		INTEGER,
kcprtAlertEventCountFactor		DisplayString,
kcprtAlertEventCountValue		INTEGER
}

kcprtAlertEventCountIndex	OBJECT-TYPE
SYNTAX		INTEGER
ACCESS		not-accessible
STATUS		mandatory
DESCRIPTION
            "\83C\83x\83\93\83g\94\AD\90\B6\89񐔃J\83E\83\93\83g\82\F0\8E\AF\95ʂ\B7\82邽\82߂̃C\83\93\83f\83b\83N\83X"
        ::={ kcprtAlertEventCountEntry 1 }

kcprtAlertEventCountFactor	OBJECT-TYPE
SYNTAX		DisplayString
ACCESS		read-only
STATUS		mandatory
DESCRIPTION
"\94\AD\90\B6\83C\83x\83\93\83g\82\F0\8E\A6\82\B7\95\B6\8E\9A\97\F1\81iJAM\97v\88\F6\83R\81[\83h\81ACall Serive\83R\81[\83h\81A\8C\F0\8A\B7\83A\83C\83e\83\80\83R\81[\83h\81j\81BJ01\81AJ02\81A\A5\A5\A5\81AC0001\81AC6500\81ACF030\81A\A5\A5\A5\81AM01\81AM02\81AT01\A5\A5\A5"
        ::={ kcprtAlertEventCountEntry 2 }

kcprtAlertEventCountValue	OBJECT-TYPE
SYNTAX		INTEGER
ACCESS		read-only
STATUS		mandatory
DESCRIPTION
" kcprtAlertEventCountFactor\82Œʒm\82\B3\82\EA\82\E9\83C\83x\83\93\83g\82\AA\94\AD\90\B6\82\B5\82\BD\89\F1\90\94"
        ::={ kcprtAlertEventCountEntry 3 }





--
--  Memory Resource group
--
--      To see and control the resources on the memory device.
--

--
--  MemoryResource->MemoryDevice table
--
    kcprtMemoryDeviceTable      OBJECT-TYPE
        SYNTAX  SEQUENCE OF KcprtMemoryDeviceEntry
        ACCESS  not-accessible
        STATUS  mandatory
        DESCRIPTION
            "This table contains information for each memory device, such as the IC-Card."
        ::={ kcprtMemoryResource 1 }

    kcprtMemoryDeviceEntry      OBJECT-TYPE
        SYNTAX  KcprtMemoryDeviceEntry
        ACCESS  not-accessible
        STATUS  mandatory
        DESCRIPTION
            "A list of entries that are corresponding to the each function of the memory device."
        INDEX { hrDeviceIndex, kcprtMemoryDeviceIndex }
        ::={ kcprtMemoryDeviceTable 1 }

    KcprtMemoryDeviceEntry      ::= SEQUENCE {
        kcprtMemoryDeviceIndex      INTEGER,
        kcprtMemoryDeviceLocation   INTEGER,
        kcprtMemoryDeviceType       INTEGER,
        kcprtMemoryDeviceTotalSize  INTEGER,
        kcprtMemoryDeviceUsedSize   INTEGER,
        kcprtMemoryDeviceStatus     INTEGER,
	kcprtMemoryDeviceUnit	    INTEGER
    }

    kcprtMemoryDeviceIndex      OBJECT-TYPE
        SYNTAX  INTEGER
        ACCESS  not-accessible
        STATUS  mandatory
        DESCRIPTION
            "A unique value that is corresponding to each memory device, such as IC-Card. The value assignment will change if the IC-Card is removed or inserted."
        ::={ kcprtMemoryDeviceEntry 1 }

    kcprtMemoryDeviceLocation       OBJECT-TYPE
        SYNTAX  INTEGER {
            pcCard-A(0),
            pcCard-B(1),
            optionROMsocket(2),
            residentFont(3),
            downloadArea(4),
            hardDisk(5),
            memoryCard(6),
            others(255)
        }
        ACCESS  read-only
        STATUS  mandatory
        DESCRIPTION
            "The value shows the location of this memory device. Note that if the location is download area, only the resource that has been assigned to the current interface can be managed. To see other resources, the management application have to change the current interface."
        ::={ kcprtMemoryDeviceEntry 2 }

    kcprtMemoryDeviceType       OBJECT-TYPE
        SYNTAX  INTEGER {
            rom(0),
            flash(1),
            sram(2),
            dram(3),
            strage(4),
            others(255)
        }
        ACCESS  read-only
        STATUS  mandatory
        DESCRIPTION
            "The value shows the type of this memory device."
        ::={ kcprtMemoryDeviceEntry 3 }

    kcprtMemoryDeviceTotalSize      OBJECT-TYPE
        SYNTAX  INTEGER
        ACCESS  read-write
        STATUS  mandatory
        DESCRIPTION
            "The maximum space of the memory device. Unit is bytes."
        ::={ kcprtMemoryDeviceEntry 4 }

    kcprtMemoryDeviceUsedSize       OBJECT-TYPE
        SYNTAX  INTEGER
        ACCESS  read-only
        STATUS  mandatory
        DESCRIPTION
            "The amount of occupied space on the device. Unit is bytes. If the device cannot detect the amount, the value is (-1)."
        ::={ kcprtMemoryDeviceEntry 5 }

    kcprtMemoryDeviceStatus     OBJECT-TYPE
        SYNTAX  INTEGER {
            readyReadWrite(0),
            readyReadOnly(1),
            notAccessible(2),
            lowBattery(4)
        }
        ACCESS  read-write
        STATUS  mandatory
        DESCRIPTION
            "This value shows current status of this device. notAccessible means that the printer recognized the device but the access is impossible. lowBattery is for a kind of battery backuped device, such as IC-card."
        ::={ kcprtMemoryDeviceEntry 6 }

    kcprtMemoryDeviceUnit       OBJECT-TYPE
        SYNTAX  INTEGER
        ACCESS  read-only
        STATUS  mandatory
        DESCRIPTION
            ""
        ::={ kcprtMemoryDeviceEntry 7 }

--
--  MemoryResource->Partition table
--
    kcprtPartitionTable     OBJECT-TYPE
        SYNTAX  SEQUENCE OF KcprtPartitionEntry
        ACCESS  not-accessible
        STATUS  mandatory
        DESCRIPTION
            "This table contains partition information for each device."
        ::={ kcprtMemoryResource 2 }

    kcprtPartitionEntry     OBJECT-TYPE
        SYNTAX  KcprtPartitionEntry
        ACCESS  not-accessible
        STATUS  mandatory
        DESCRIPTION
            "A list of entries that is corresponding to the each information about the partition."
        INDEX {hrDeviceIndex, kcprtPartitionIndex }
        ::={ kcprtPartitionTable 1 }

    KcprtPartitionEntry ::= SEQUENCE {
        kcprtPartitionIndex         INTEGER,
        kcprtPartitionSize          INTEGER,
        kcprtPartitionLocation      INTEGER,
        kcprtPartitionResourceType  INTEGER,
        kcprtPartitionName          DisplayString,
        kcprtPartitionLoad          INTEGER
    }

    kcprtPartitionIndex     OBJECT-TYPE
        SYNTAX  INTEGER
        ACCESS  not-accessible
        STATUS  mandatory
        DESCRIPTION
            "A unique value corresponding to the each partition on the printer's memory device. This assigment will change in some cases."
        ::={ kcprtPartitionEntry 1 }

    kcprtPartitionSize      OBJECT-TYPE
        SYNTAX  INTEGER
        ACCESS  read-only
        STATUS  mandatory
        DESCRIPTION
            "This value shows the size of this partition. Unit is byte."
        ::={ kcprtPartitionEntry 2 }

    kcprtPartitionLocation      OBJECT-TYPE
        SYNTAX  INTEGER
        ACCESS  read-only
        STATUS  mandatory
        DESCRIPTION
            "This value of kcprtMemoryDeviceIndex corresponding to the device on which this partition exists. If the device is unknown, this value is (-1)."
        ::={ kcprtPartitionEntry 3 }

    kcprtPartitionResourceType      OBJECT-TYPE
        SYNTAX  INTEGER {
            void(0),
            macro(3),
            hostData(4),
            programData(5),
            messageData(6),
            fontData(7)
        }
        ACCESS  read-only
        STATUS  mandatory
        DESCRIPTION
            "The type of the resource that is using this partition."
        ::={ kcprtPartitionEntry 4 }

    kcprtPartitionName      OBJECT-TYPE
        SYNTAX  DisplayString ( SIZE(1..15) )
        ACCESS  read-only
        STATUS  mandatory
        DESCRIPTION
            "The name that is assigned to this partition."
        ::={ kcprtPartitionEntry 5 }

    kcprtPartitionLoad      OBJECT-TYPE
        SYNTAX  INTEGER {
            notLoaded(0),
            loaded(1)
        }
        ACCESS  read-only
        STATUS  mandatory
        DESCRIPTION
            "This value shows whether this partition has been read by the printer. basically, the resource should be read by the printer to make it available."
        ::={ kcprtPartitionEntry 6 }


--
--  MemoryResource->MacroData table
--
    kcprtMacroDataTable     OBJECT-TYPE
        SYNTAX  SEQUENCE OF KcprtMacroDataEntry
        ACCESS  not-accessible
        STATUS  mandatory
        DESCRIPTION
            "This table contains information about MACRO resource."
        ::={ kcprtMemoryResource 3 }

    kcprtMacroDataEntry     OBJECT-TYPE
        SYNTAX  KcprtMacroDataEntry
        ACCESS  not-accessible
        STATUS  mandatory
        DESCRIPTION
            ""
        INDEX { hrDeviceIndex, kcprtMacroDataIndex }
        ::={ kcprtMacroDataTable 1 }

    KcprtMacroDataEntry ::= SEQUENCE {
        kcprtMacroDataIndex         INTEGER,
        kcprtMacroDataName          DisplayString,
        kcprtMacroDataID            INTEGER,
        kcprtMacroDataType          INTEGER,
        kcprtMacroDataAutoLoad      INTEGER,
        kcprtMacroDataLocation      INTEGER,
        kcprtMacroDataAttribute     INTEGER
    }

    kcprtMacroDataIndex     OBJECT-TYPE
        SYNTAX  INTEGER
        ACCESS  not-accessible
        STATUS  mandatory
        DESCRIPTION
            ""
        ::={ kcprtMacroDataEntry 1 }

    kcprtMacroDataName      OBJECT-TYPE
        SYNTAX  DisplayString ( SIZE( 1..4 ) )
        ACCESS  read-only
        STATUS  mandatory
        DESCRIPTION
            "This value will be effective if the macro is described in Prescribe. Otherwise, this value will be NULL."
        ::={ kcprtMacroDataEntry 2 }

    kcprtMacroDataID        OBJECT-TYPE
        SYNTAX  INTEGER
        ACCESS  read-only
        STATUS  mandatory
        DESCRIPTION
            "This value will be effective if the macro is described in PCL. Otherwise, the value will be unknown(-1)."
        ::={ kcprtMacroDataEntry 3 }

    kcprtMacroDataType      OBJECT-TYPE
        SYNTAX  INTEGER {
            prescribe(1),
            pcl(2),
            others(255)
        }
        ACCESS  read-only
        STATUS  mandatory
        DESCRIPTION
            "This value is corresponding to the PDL that is used for decribing this macro."
        ::={ kcprtMacroDataEntry 4 }

    kcprtMacroDataAutoLoad      OBJECT-TYPE
        SYNTAX  INTEGER {
            off(0),
            onWithInitialize(1),
            onWithoutInitialize(2)
        }
        ACCESS  read-only
        STATUS  mandatory
        DESCRIPTION
            "This value shows the state of the form overlay function that is controled by AMCR command. Only one macro can be set as 'on', so at most one entry will have 'on' value."
        ::={ kcprtMacroDataEntry 5 }

    kcprtMacroDataLocation      OBJECT-TYPE
        SYNTAX  INTEGER
        ACCESS  read-only
        STATUS  mandatory
        DESCRIPTION
            "The value of kcprtMemoryDeviceIndex correspinding to the device that this macro is currently stored. unknown is (-1)."
        ::={ kcprtMacroDataEntry 6 }

    kcprtMacroDataAttribute     OBJECT-TYPE
        SYNTAX  INTEGER {
            notRegistered(0),
            registered(1)
        }
        ACCESS  read-only
        STATUS  mandatory
        DESCRIPTION
            "'notRegistered' means this resource is existing on the device but it is not available for the printer. For example, macro on the IC card that is inserted into the printer after turning on will be 'notRegistered'. To turn it into 'registered' user must select them from the front panel menu."
        ::={ kcprtMacroDataEntry 7 }


--
--  MemoryResource->HostData table
--
    kcprtHostDataTable      OBJECT-TYPE
        SYNTAX  SEQUENCE OF KcprtHostDataEntry
        ACCESS  not-accessible
        STATUS  mandatory
        DESCRIPTION
            "This table contains information about the host data. Note that 'Host data' does not mean the job itself."
        ::={ kcprtMemoryResource 4 }

    kcprtHostDataEntry      OBJECT-TYPE
        SYNTAX  KcprtHostDataEntry
        ACCESS  not-accessible
        STATUS  mandatory
        DESCRIPTION
            "A list of entries that are corresponding each information of the host data."
        INDEX { hrDeviceIndex, kcprtHostDataIndex }
        ::={ kcprtHostDataTable 1 }

    KcprtHostDataEntry      ::= SEQUENCE {
        kcprtHostDataIndex      INTEGER,
        kcprtHostDataName       DisplayString,
        kcprtHostDataLocation   INTEGER,
        kcprtHostDataAttribute  INTEGER
    }

    kcprtHostDataIndex      OBJECT-TYPE
        SYNTAX  INTEGER
        ACCESS  not-accessible
        STATUS  mandatory
        DESCRIPTION
            "A unique value corresponding to each information of the host data. The assigment will change in some case."
        ::={ kcprtHostDataEntry 1 }

    kcprtHostDataName       OBJECT-TYPE
        SYNTAX  DisplayString ( SIZE( 1..15 ) )
        ACCESS  read-only
        STATUS  mandatory
        DESCRIPTION
            "The name that is used for descriminating each host data."
        ::={ kcprtHostDataEntry 2 }

    kcprtHostDataLocation       OBJECT-TYPE
        SYNTAX  INTEGER
        ACCESS  read-only
        STATUS  mandatory
        DESCRIPTION
            "The value of kcprtMemoryDeviceIndex that is corresponding to the device in which this host data is stored. If the device is unknown, the value is -1."
        ::={ kcprtHostDataEntry 3 }

    kcprtHostDataAttribute      OBJECT-TYPE
        SYNTAX  INTEGER {
            notRegistered(0),
            registered(1)
        }
        ACCESS  read-only
        STATUS  mandatory
        DESCRIPTION
            "Basically, the value is always 'registered'."
        ::={ kcprtHostDataEntry 4 }


--
--  MemoryResource->ProgramData table
--
    kcprtProgramDataTable       OBJECT-TYPE
        SYNTAX  SEQUENCE OF KcprtProgramDataEntry
        ACCESS  not-accessible
        STATUS  mandatory
        DESCRIPTION
            "This table contains information about the program data. The program data is a kind of emulation and a Prescribe command, not a macro."
        ::={ kcprtMemoryResource 5 }

    kcprtProgramDataEntry       OBJECT-TYPE
        SYNTAX  KcprtProgramDataEntry
        ACCESS  not-accessible
        STATUS  mandatory
        DESCRIPTION
            "A list of entries that are corresponding to each information of the program data."
        INDEX { hrDeviceIndex, kcprtProgramDataIndex }
        ::={ kcprtProgramDataTable 1 }

    KcprtProgramDataEntry   ::= SEQUENCE {
        kcprtProgramDataIndex       INTEGER,
        kcprtProgramDataName        DisplayString,
        kcprtProgramDataType        INTEGER,
        kcprtProgramDataLocation    INTEGER,
        kcprtProgramDataAttribute   INTEGER
    }

    kcprtProgramDataIndex       OBJECT-TYPE
        SYNTAX  INTEGER
        ACCESS  not-accessible
        STATUS  mandatory
        DESCRIPTION
            "A unique value corresponding to each program data. This assigment may change in some case."
        ::={ kcprtProgramDataEntry 1 }

    kcprtProgramDataName        OBJECT-TYPE
        SYNTAX  DisplayString( SIZE( 1..15 ) )
        ACCESS  read-only
        STATUS  mandatory
        DESCRIPTION
            ""
        ::={ kcprtProgramDataEntry 2 }

    kcprtProgramDataType        OBJECT-TYPE
        SYNTAX  INTEGER {
            emulation(0),
            prescribe(1),
            panel(2),
            others(255)
        }
        ACCESS  read-only
        STATUS  mandatory
        DESCRIPTION
            ""
        ::={ kcprtProgramDataEntry 3 }

    kcprtProgramDataLocation        OBJECT-TYPE
        SYNTAX  INTEGER
        ACCESS  read-only
        STATUS  mandatory
        DESCRIPTION
            "The value of kcprtMemoryDeviceIndex corresponding to the device in which this program data is stored. If the device is unknown, the value is (-1)."
        ::={ kcprtProgramDataEntry 4 }

    kcprtProgramDataAttribute       OBJECT-TYPE
        SYNTAX  INTEGER {
            notRegistered(0),
            registered(1),
            running(2)
        }
        ACCESS  read-only
        STATUS  mandatory
        DESCRIPTION
            "'running' means the program is running."
        ::={ kcprtProgramDataEntry 5 }


--
--  MemoryResource->MessageData table
--
    kcprtMessageDataTable       OBJECT-TYPE
        SYNTAX  SEQUENCE OF KcprtMessageDataEntry
        ACCESS  not-accessible
        STATUS  mandatory
        DESCRIPTION
            "This is a bunch of message that is handled as one of the flont panel language by the printer."
        ::={ kcprtMemoryResource 6 }

    kcprtMessageDataEntry       OBJECT-TYPE
        SYNTAX  KcprtMessageDataEntry
        ACCESS  not-accessible
        STATUS  mandatory
        DESCRIPTION
            "A list of entries that are corresponding to each information of the message data."
        INDEX { hrDeviceIndex, kcprtMessageDataIndex }
        ::={ kcprtMessageDataTable 1 }

    KcprtMessageDataEntry       ::= SEQUENCE {
        kcprtMessageDataIndex       INTEGER,
        kcprtMessageDataName        DisplayString,
        kcprtMessageDataLocation    INTEGER,
        kcprtMessageDataAttribute   INTEGER
    }

    kcprtMessageDataIndex       OBJECT-TYPE
        SYNTAX  INTEGER
        ACCESS  not-accessible
        STATUS  mandatory
        DESCRIPTION
            "The index vaule that is assigned to each front panel language."
        ::={ kcprtMessageDataEntry 1 }

    kcprtMessageDataName        OBJECT-TYPE
        SYNTAX  DisplayString ( SIZE( 1..15 ) )
        ACCESS  read-only
        STATUS  mandatory
        DESCRIPTION
            "The name of the message data block."
        ::={ kcprtMessageDataEntry 2 }

    kcprtMessageDataLocation        OBJECT-TYPE
        SYNTAX  INTEGER
        ACCESS  read-only
        STATUS  mandatory
        DESCRIPTION
            "The value of kcprtMemoryDeviceIndex corresponding to the device in which this message data is stored. If the device is unknown, the value is -1."
        ::={ kcprtMessageDataEntry 3 }

    kcprtMessageDataAttribute       OBJECT-TYPE
        SYNTAX  INTEGER {
            notRegistered(0),
            registered(1)
        }
        ACCESS  read-only
        STATUS  mandatory
        DESCRIPTION
            "Always 'registered' in the current products."
        ::={ kcprtMessageDataEntry 4 }


--
--  MemoryResource->Font table
--
    kcprtFontDataTable      OBJECT-TYPE
        SYNTAX  SEQUENCE OF KcprtFontDataEntry
        ACCESS  not-accessible
        STATUS  mandatory
        DESCRIPTION
            "This table contains font information."
        ::={ kcprtMemoryResource 7 }

    kcprtFontDataEntry      OBJECT-TYPE
        SYNTAX  KcprtFontDataEntry
        ACCESS  not-accessible
        STATUS  mandatory
        DESCRIPTION
            "A list of entries that are corresponding each information of the font."
        INDEX { hrDeviceIndex, kcprtFontDataIndex }
        ::={ kcprtFontDataTable 1 }

    KcprtFontDataEntry      ::= SEQUENCE {
        kcprtFontDataIndex      INTEGER,
        kcprtTypeFaceName       DisplayString,
        kcprtFontID             INTEGER,
        kcprtFontType           INTEGER,
        kcprtFontLocation       INTEGER,
        kcprtFontAttribute      INTEGER
    }

    kcprtFontDataIndex      OBJECT-TYPE
        SYNTAX  INTEGER
        ACCESS  not-accessible
        STATUS  mandatory
        DESCRIPTION
            "A unique value corresponding to each font data. The assignment may change in some case."
        ::={ kcprtFontDataEntry 1 }

    kcprtTypeFaceName       OBJECT-TYPE
        SYNTAX  DisplayString ( SIZE( 0..31 ) )
        ACCESS  read-only
        STATUS  mandatory
        DESCRIPTION
            "The value will be NULL if no name has been assigned."
        ::={ kcprtFontDataEntry 2 }

    kcprtFontID     OBJECT-TYPE
        SYNTAX  INTEGER
        ACCESS  read-only
        STATUS  mandatory
        DESCRIPTION
            "This value will be -1 if no ID has been assigned."
        ::={ kcprtFontDataEntry 3 }

    kcprtFontType   OBJECT-TYPE
        SYNTAX  INTEGER {
            bitmap(0),
            scalable(1),
            others(255)
        }
        ACCESS  read-only
        STATUS  mandatory
        DESCRIPTION
            ""
        ::={ kcprtFontDataEntry 4 }

    kcprtFontLocation       OBJECT-TYPE
        SYNTAX  INTEGER
        ACCESS  read-only
        STATUS  mandatory
        DESCRIPTION
            "The value of kcprtMemoryDeviceIndex corresponding to the device on which this font is stored. If it is unknown, the value is -1."
        ::={ kcprtFontDataEntry 5 }

    kcprtFontAttribute      OBJECT-TYPE
        SYNTAX  INTEGER {
            notRegistered(0),
            registered (1)
        }
        ACCESS  read-only
        STATUS  mandatory
        DESCRIPTION
            "In the current printer, this value is always 'registered'."
        ::={ kcprtFontDataEntry 6 }

--
--  kcprtMemoryResource->File storage table
--
    kcprtFileStorageTable      OBJECT-TYPE
        SYNTAX  SEQUENCE OF KcprtFileStorageEntry
        ACCESS  not-accessible
        STATUS  mandatory
        DESCRIPTION
            "This table contains FILE storage information.
            'File' is an resource object that is used by PCL and/or KPDL.
            Sometimes it may be the dowloaded font. However, the printer system
            cannot recognize the resources's purpose and function.
            This table has information about the area for the file object."
        ::={ kcprtMemoryResource 8 }

    kcprtFileStorageEntry      OBJECT-TYPE
        SYNTAX  KcprtFileStorageEntry
        ACCESS  not-accessible
        STATUS  mandatory
        DESCRIPTION
            "A list of entries that are corresponding each information of the file storage.
            Basically the storage is an area located on the printer's hard disk."
        INDEX { hrDeviceIndex, kcprtFileStorageIndex }
        ::={ kcprtFileStorageTable 1 }

    KcprtFileStorageEntry      ::= SEQUENCE {
        kcprtFileStorageIndex           INTEGER,
        kcprtFileStorageLimitSize       INTEGER,
        kcprtFileStorageUsedSize        INTEGER,
        kcprtFileStorageUnit            INTEGER,
        kcprtFileStorageCounter         INTEGER
    }

    kcprtFileStorageIndex      OBJECT-TYPE
        SYNTAX  INTEGER
        ACCESS  not-accessible
        STATUS  mandatory
        DESCRIPTION
            "A unique value corresponding to each file storage information.
            The assignment may change in some case."
        ::={ kcprtFileStorageEntry 1 }

    kcprtFileStorageLimitSize      OBJECT-TYPE
        SYNTAX  INTEGER
        ACCESS  read-only
        STATUS  mandatory
        DESCRIPTION
            "The threshold value of the maximum storage size. The unit is specified
            by kcprtFileStorageUnit object. Value (-1) means 'unknown'.
            Note that this size does not garantee the maximum size. Printer will not
            save the file object if kcprtFileStorageUsedSize will exceed this value or
            the vacant room on the hard disk is running out."
        ::={ kcprtFileStorageEntry 2 }

    kcprtFileStorageUsedSize    OBJECT-TYPE
        SYNTAX  INTEGER
        ACCESS  read-only
        STATUS  mandatory
        DESCRIPTION
            "The used size of the file storage area. The unit is specified by
            kcprtFileStorageUnit object. Value (-1) means 'unknown'."
        ::={ kcprtFileStorageEntry 3 }

    kcprtFileStorageUnit    OBJECT-TYPE
        SYNTAX  INTEGER
        ACCESS  read-only
        STATUS  mandatory
        DESCRIPTION
            "This object shows the unit for both kcprtFileStorageLimitSize and
            kcprtFileStorageUsedSize.
            The value (1024) means the unit is 1Kbytes. In this case, the used size
            is 5120 bytes if kcprtFileStorageUsedSize object gives value (5)."
        ::={ kcprtFileStorageEntry 4 }

    kcprtFileStorageCounter OBJECT-TYPE
        SYNTAX  INTEGER (0..4294967295)
        ACCESS  read-only
        STATUS  mandatory
        DESCRIPTION
            "Note that this object does not show the number of the entry in this table.
            Each time when some change has happened on this table, this counter will
            be increased. The start value is 0. If the value will exceed the maximum
            limit, it will be set to 0."
        ::={ kcprtFileStorageEntry 5 }

--
--  kcprtMemoryResource-> File obejct table
--
    kcprtFileTable      OBJECT-TYPE
        SYNTAX  SEQUENCE OF KcprtFileEntry
        ACCESS  not-accessible
        STATUS  mandatory
        DESCRIPTION
            "This table contains FILE object information.
            'File' is an resource object that is used by PCL and/or KPDL.
            Sometimes it may be the dowloaded font. However, the printer system
            cannot recognize the resources's purpose and function."
        ::={ kcprtMemoryResource 9 }

    kcprtFileEntry      OBJECT-TYPE
        SYNTAX  KcprtFileEntry
        ACCESS  not-accessible
        STATUS  mandatory
        DESCRIPTION
            "A list of entries that are corresponding each information of the file object."
        INDEX { hrDeviceIndex, kcprtFileIndex }
        ::={ kcprtFileTable 1 }

    KcprtFileEntry      ::= SEQUENCE {
        kcprtFileIndex          INTEGER,
        kcprtFileName           OCTET STRING,
        kcprtFileSize           INTEGER
    }

    kcprtFileIndex  OBJECT-TYPE
        SYNTAX  INTEGER
        ACCESS  read-only
        STATUS  mandatory
        DESCRIPTION
            "An unique value assigned by the printer system to identify each file object.
            This assignment may be changed while running cycle."
        ::={ kcprtFileEntry 1 }

    kcprtFileName   OBJECT-TYPE
        SYNTAX  OCTET STRING   (SIZE(0..255))
        ACCESS  read-only
        STATUS  mandatory
        DESCRIPTION
            "This object gives the full-path name of the file object. If the file was made
            by KPDL interpreter, the name will be 'KPDL\filename'. If the file was made by
            PCL(PJL) interpreter, the name will be 'PJL\filename'. The character '\' is used
            as the terminator of directory name.
            Note that whether this value is human-readable or not is up to the incoming data
            and the interpreter.
            Note that this object will take quite long time to make a response."
        ::={ kcprtFileEntry 2 }

    kcprtFileSize   OBJECT-TYPE
        SYNTAX  INTEGER
        ACCESS  read-only
        STATUS  mandatory
        DESCRIPTION
            "The file size in byte."
        ::={ kcprtFileEntry 3 }


--
--  kcprtMemoryResource-> Saved Job Storage
--
    kcprtSJobStorageTable   OBJECT-TYPE
    SYNTAX  SEQUENCE OF KcprtSJobStorageEntry
    ACCESS  not-accessible
    STATUS  mandatory
    DESCRIPTION
        "This table gives information for the logical storage that contains Saved Job
        files.
        See description of kcprtSJobTable for the detail of Saved Job."
    ::={ kcprtMemoryResource 10 }

    kcprtSJobStorageEntry   OBJECT-TYPE
        SYNTAX  KcprtSJobStorageEntry
        ACCESS  not-accessible
        STATUS  mandatory
        DESCRIPTION
            "The entry may be changed while running-cycle."
        INDEX { hrDeviceIndex, kcprtSJobStorageIndex }
        ::={ kcprtSJobStorageTable 1 }

    KcprtSJobStorageEntry      ::=  SEQUENCE {
        kcprtSJobStorageIndex       INTEGER,
        kcprtSJobStorageLimitSize   INTEGER,
        kcprtSJobStorageUsedSize    INTEGER,
        kcprtSJobStorageUnit        INTEGER,
        kcprtSJobStorageStateCounter    INTEGER,
        kcprtSJobStorageAttribute   INTEGER
    }

    kcprtSJobStorageIndex   OBJECT-TYPE
        SYNTAX  INTEGER
        ACCESS  not-accessible
        STATUS  mandatory
        DESCRIPTION
            "A unique number that is assigned each SJob storage. This assignment will not
            change while running-cycle.
            The table with index(1) contains volatile SJobs only. The table with index(2)
            contains non-volatile SJobs only.
            "
        ::={ kcprtSJobStorageEntry 1 }

    kcprtSJobStorageLimitSize   OBJECT-TYPE
        SYNTAX  INTEGER
        ACCESS  read-only
        STATUS  mandatory
        DESCRIPTION
            "This logical storage's threshold size. Printer system will not save new SJob
            or delete the oldest SJob if the kcprtSJobStorageUsedSize is going to exceed
            this threshord or the actual vacant room is running out.
            The unit is specified by kcprtSJobStorageUnit.
            The value (-1) means 'unknown'."
        ::={ kcprtSJobStorageEntry 2 }

    kcprtSJobStorageUsedSize    OBJECT-TYPE
        SYNTAX  INTEGER
        ACCESS  read-only
        STATUS  mandatory
        DESCRIPTION
            "This logical storage's used size. The unit is specified by kcprtSJobStorageUnit.
            The value (-1) means 'unknown'."
        ::={ kcprtSJobStorageEntry 3 }

    kcprtSJobStorageUnit        OBJECT-TYPE
        SYNTAX  INTEGER
        ACCESS  read-only
        STATUS  mandatory
        DESCRIPTION
            "This object shows the unit size.
            For example, value(1024) means that one unit is 1024 bytes (1KBytes)."
        ::={ kcprtSJobStorageEntry 4 }

    kcprtSJobStorageStateCounter    OBJECT-TYPE
        SYNTAX  INTEGER (0..4294967295)
        ACCESS  read-only
        STATUS  mandatory
        DESCRIPTION
            "This counter will be increased when any change has happened on this SJob storage.
            For exmaple, this counter will be increased if new SJob is added onto this storage.
            The start value is 0. This object works as 4byte counter."
        ::={ kcprtSJobStorageEntry 5 }

    kcprtSJobStorageAttribute   OBJECT-TYPE
        SYNTAX  INTEGER {
            volatile(1),
            nonVolatile(2),
            unknown(255)
        }
        ACCESS  read-only
        STATUS  mandatory
        DESCRIPTION
            "There are two type of SJob. One is 'volatile' and the other is 'nonVolatile'.
            The volatile job will be deleted by the printer system when new SJob is coming and
            the storage is almost full. The oldest SJob will be deleted first. Therefore, this
            storage works as FIFO (First In First Out).
            The nonVolatile job will never be deleted by the printer system. If there is no
            enough room on the storage for the new SJob, it will not be saved on the storage.
            Please refer to the printer's instruction manual for detail.
            The 'volatile' storage can contain only 'volatile' SJob, and 'nonVolatile' storage
            can contain only 'nonVolatile' SJob.
            Note that one printer system can have only one 'volatile' storage and one 'nonVolatile'
            storage."
        ::={ kcprtSJobStorageEntry 6 }

--
--  kcprtMemoryRresource-> SJob Table
--
    kcprtSJobTable  OBJECT-TYPE
        SYNTAX  SEQUENCE OF KcprtSjobEntry
        ACCESS  not-accessible
        STATUS  mandatory
        DESCRIPTION
            "This table contains information for each SJob file.
            'SJob' means 'Saved Job'. This is actually a mass of video images that are about to
            be passed to printer's engine. By using several ways, user can pass one of SJob to
            the printer's engine to get the print out again. It is much easier than sending the
            same job from the host."
        ::={ kcprtMemoryResource 11 }

    kcprtSJobEntry  OBJECT-TYPE
        SYNTAX  KcprtSjobEntry
        ACCESS  not-accessible
        STATUS  mandatory
        DESCRIPTION
            ""
        INDEX { hrDeviceIndex, kcprtSJobIndex }
        ::={ kcprtSJobTable 1 }

    KcprtSjobEntry  ::= SEQUENCE    {
        kcprtSJobIndex      INTEGER,
        kcprtSjobID         OCTET STRING,
        kcprtSJobName       OCTET STRING,
        kcprtSJobOwner      OCTET STRING,
        kcprtSJobTime       OCTET STRING,
        kcprtSJobPageNumber INTEGER,
        kcprtSJobSize       INTEGER,
        kcprtSJobStorageRef INTEGER,
        kcprtSJobCopyCount  INTEGER,
        kcprtSJobBarcodePrintExistence INTEGER,
        kcprtSJobDuplexMode INTEGER,
        kcprtSJobOutputIndex INTEGER,
        kcprtSJobStaplePosition INTEGER,
        kcprtSJobBarcodePosition INTEGER,
        kcprtSJobStapleAndFoldCount INTEGER,
        kcprtSJobFoldMode INTEGER,
        kcprtSJobPunchMode INTEGER,
        kcprtSJobTransparencySeparationMode INTEGER,
        kcprtSJobTransparencySeparationInputIndex INTEGER,
        kcprtSJobRotatedCollationMode INTEGER,
        kcprtSJobBookletMode INTEGER,
        kcprtSJobJobOffsetMode INTEGER

    }

    kcprtSJobIndex          OBJECT-TYPE
        SYNTAX  INTEGER
        ACCESS  not-accessible
        STATUS  mandatory
        DESCRIPTION
            "A unique value assigned by the printer system to identify each SJob file."
        ::= { kcprtSJobEntry 1 }

    kcprtSjobID             OBJECT-TYPE
        SYNTAX  DisplayString   (SIZE(16))
        ACCESS  read-only
        STATUS  mandatory
        DESCRIPTION
            "A unique ID that can be used to specify the required SJob file. This ID is assigned by the printer system.
            Note that this value is different from kcprtSJobIndex value."
        ::= { kcprtSJobEntry 2 }

    kcprtSJobName           OBJECT-TYPE
        SYNTAX  DisplayString   (SIZE(0..31))
        ACCESS  read-only
        STATUS  mandatory
        DESCRIPTION
            "A string that can identify each SJob. This information will be assigned by
            the job sender. If the sender has not assigned any name, this value is NULL
            string."
        ::= { kcprtSJobEntry 3 }

    kcprtSJobOwner          OBJECT-TYPE
        SYNTAX  DisplayString   (SIZE(0..31))
        ACCESS  read-only
        STATUS  mandatory
        DESCRIPTION
            "A string that can be used to identify the SJob's owner (sender). This string
            should be assigned by the job sender. If not, NULL string will be placed."
        ::= { kcprtSJobEntry 4 }

    kcprtSJobTime           OBJECT-TYPE
        SYNTAX  DisplayString   (SIZE(0..31))
        ACCESS  read-only
        STATUS  mandatory
        DESCRIPTION
            "A string that can be used to recognize the Job submission time. This string
            should be assigned by the job sender. If not, NULL string will be applied."
        ::= { kcprtSJobEntry 5 }

    kcprtSJobPageNumber     OBJECT-TYPE
        SYNTAX  INTEGER
        ACCESS  read-only
        STATUS  mandatory
        DESCRIPTION
            "Total number of impressions that this SJob contains."
        ::= { kcprtSJobEntry 6 }

    kcprtSJobSize           OBJECT-TYPE
        SYNTAX  INTEGER (0..4294967295)
        ACCESS  read-only
        STATUS  mandatory
        DESCRIPTION
            "Total amount of SJob file. The unit it Byte."
        ::= { kcprtSJobEntry 7 }

    kcprtSJobStorageRef     OBJECT-TYPE
        SYNTAX  INTEGER
        ACCESS  read-only
        STATUS  mandatory
        DESCRIPTION
            "kcprtSJobStorageIndex value corresponding to each SJobStorage
            that contains this SJob file."
        ::= { kcprtSJobEntry 8 }

    kcprtSJobCopyCount     OBJECT-TYPE
        SYNTAX  INTEGER
        ACCESS  read-only
        STATUS  mandatory
        DESCRIPTION
            "Copy Count of SJob file."
        ::= { kcprtSJobEntry 9 }

    kcprtSJobBarcodePrintExistence     OBJECT-TYPE
        SYNTAX  INTEGER {
            notPrinting(0),
            firstPagePrinting(1),
            allPagePrinting(2)
        }
        ACCESS  read-only
        STATUS  mandatory
        DESCRIPTION
            ""
        ::= { kcprtSJobEntry 10 }

    kcprtSJobDuplexMode     OBJECT-TYPE
        SYNTAX  INTEGER {
            simplex(5),
            shortEdgeBindingDuplex(3),
            longEdgeBindingDuplex(4)
        }
        ACCESS  read-only
        STATUS  mandatory
        DESCRIPTION
            ""
        ::= { kcprtSJobEntry 11 }

    kcprtSJobOutputIndex     OBJECT-TYPE
        SYNTAX  INTEGER
        ACCESS  read-only
        STATUS  mandatory
        DESCRIPTION
            ""
        ::= { kcprtSJobEntry 12 }

    kcprtSJobStaplePosition     OBJECT-TYPE
        SYNTAX  INTEGER {
            off(0),
            oneFrontLocation(1),
            oneRearLocation(2),
            twoCentralLocation(3)
        }
        ACCESS  read-only
        STATUS  mandatory
        DESCRIPTION
            ""
        ::= { kcprtSJobEntry 13 }

    kcprtSJobBarcodePosition     OBJECT-TYPE
        SYNTAX  INTEGER
        ACCESS  read-only
        STATUS  mandatory
        DESCRIPTION
            ""
        ::= { kcprtSJobEntry 14 }

    kcprtSJobStapleAndFoldCount     OBJECT-TYPE
        SYNTAX  INTEGER
        ACCESS  read-only
        STATUS  mandatory
        DESCRIPTION
            ""
        ::= { kcprtSJobEntry 15 }

    kcprtSJobFoldMode     OBJECT-TYPE
        SYNTAX  INTEGER {
            off(0),
            foldandStaple(1)
        }
        ACCESS  read-only
        STATUS  mandatory
        DESCRIPTION
            ""
        ::= { kcprtSJobEntry 16 }

    kcprtSJobPunchMode     OBJECT-TYPE
        SYNTAX  INTEGER {
            off(0),
            main(1),
            sub(2)
        }
        ACCESS  read-only
        STATUS  mandatory
        DESCRIPTION
            ""
        ::= { kcprtSJobEntry 17 }

    kcprtSJobTransparencySeparationMode     OBJECT-TYPE
        SYNTAX  INTEGER {
            off(0),
            blankPaperIjnterReef(1),
            copySheetInterReef(2)
        }
        ACCESS  read-only
        STATUS  mandatory
        DESCRIPTION
            ""
        ::= { kcprtSJobEntry 18 }

    kcprtSJobTransparencySeparationInputIndex     OBJECT-TYPE
        SYNTAX  INTEGER
        ACCESS  read-only
        STATUS  mandatory
        DESCRIPTION
            ""
        ::= { kcprtSJobEntry 19 }

    kcprtSJobRotatedCollationMode     OBJECT-TYPE
        SYNTAX  INTEGER {
            off(0),
            on(1)
        }
        ACCESS  read-only
        STATUS  mandatory
        DESCRIPTION
            ""
        ::= { kcprtSJobEntry 20 }

    kcprtSJobBookletMode     OBJECT-TYPE
        SYNTAX  INTEGER {
            off(0),
            leftBinding(1),
            rightBinding(2)
        }
        ACCESS  read-only
        STATUS  mandatory
        DESCRIPTION
            ""
        ::= { kcprtSJobEntry 21 }

    kcprtSJobJobOffsetMode     OBJECT-TYPE
        SYNTAX  INTEGER {
            off(0),
            on(1)
        }
        ACCESS  read-only
        STATUS  mandatory
        DESCRIPTION
            ""
        ::= { kcprtSJobEntry 22 }

--
--  Media List group table
--
    kcprtMediaTable OBJECT-TYPE
        SYNTAX  SEQUENCE OF KcprtMediaEntry
        ACCESS  not-accessible
        STATUS  mandatory
        DESCRIPTION
            "This table contains information of the media type."
        ::={ kcprtMediaList 1 }

    kcprtMediaEntry OBJECT-TYPE
        SYNTAX  KcprtMediaEntry
        ACCESS  not-accessible
        STATUS  mandatory
        DESCRIPTION
            "Information for the media list."
        INDEX { hrDeviceIndex, kcprtMediaIndex }
        ::={ kcprtMediaTable 1 }

    KcprtMediaEntry ::= SEQUENCE {
        kcprtMediaIndex   INTEGER,
		kcprtMediaName    DisplayString,
        kcprtMediaWeight  INTEGER,
        kcprtMediaFuserMode  INTEGER,
        kcprtMediaPathType   INTEGER,
        kcprtMediaDensity   INTEGER,
        kcprtMediaManageLevel   INTEGER
    }


    kcprtMediaIndex OBJECT-TYPE
        SYNTAX  INTEGER
        ACCESS  not-accessible
        STATUS  mandatory
        DESCRIPTION
            "The index that the printer assigns internally to identify the mdeia type."
        ::={ kcprtMediaEntry 1 }

    kcprtMediaName OBJECT-TYPE
        SYNTAX  DisplayString ( SIZE(0..32) )
        ACCESS  read-write
        STATUS  mandatory
        DESCRIPTION
            "The fixed label to identify the each media type."
        ::={ kcprtMediaEntry 2 }

    kcprtMediaWeight OBJECT-TYPE
        SYNTAX  INTEGER   {
            normal(0),
            heavy(1),
            light(2),
            extraheavy(3)
        }
        ACCESS  read-write
        STATUS  mandatory
        DESCRIPTION
            "Controlls media type."
        ::={ kcprtMediaEntry 3 }

    kcprtMediaFuserMode OBJECT-TYPE
        SYNTAX  INTEGER   {
            high(0),
            middle(1),
            low(2),
            vellum(3)
        }
        ACCESS  read-write
        STATUS  mandatory
        DESCRIPTION
            "Configures fuser's temparature."
        ::={ kcprtMediaEntry 4 }

    kcprtMediaPathType OBJECT-TYPE
        SYNTAX  INTEGER   {
            enable(0),
            disable(1)
        }
        ACCESS  read-write
        STATUS  mandatory
        DESCRIPTION
            "Controls whether the duplexer can handle this media or not."
        ::={ kcprtMediaEntry 5 }

    kcprtMediaDensity OBJECT-TYPE
        SYNTAX  INTEGER
        ACCESS  read-write
        STATUS  mandatory
        DESCRIPTION
            "Controls density."
        ::={ kcprtMediaEntry 6 }

    kcprtMediaManageLevel OBJECT-TYPE
        SYNTAX  INTEGER   {
            disabled(0),
            enabled(15)
        }
        ACCESS  read-only
        STATUS  mandatory
        DESCRIPTION
            "Manage media type level."
        ::={ kcprtMediaEntry 7 }

--
--   Virtual MailBox Table
--
kcprtMailBoxTable	OBJECT-TYPE
SYNTAX	SEQUENCE OF KcprtMailBoxEntry
ACCESS	not-accessible
STATUS	mandatory
DESCRIPTION
	""
::= { kcprtMailBox 1 }

kcprtMailBoxEntry	OBJECT-TYPE
	SYNTAX	KcprtMailBoxEntry
	ACCESS	not-accessible
	STATUS	mandatory
	DESCRIPTION
		""
	INDEX { hrDeviceIndex, kcprtMailBoxIndex }
	::= { kcprtMailBoxTable 1 }

KcprtMailBoxEntry	::=	SEQUENCE {
	kcprtMailBoxIndex		INTEGER,
	kcprtMailBoxDeviceIndex		INTEGER,
	kcprtMailBoxStateCounter	INTEGER,
	kcprtMailBoxUsedTrays		INTEGER,
	kcprtMailBoxDocumentsNumber	INTEGER,
	kcprtMailBoxPageNumber		INTEGER,
	kcprtMailBoxUsedSize		INTEGER,
	kcprtMailBoxLimitSize		INTEGER,
	kcprtMailBoxMaxLimitSize	INTEGER,
	kcprtMailBoxUnit		INTEGER,
	kcprtMailBoxAliasCheck		DisplayString
}

kcprtMailBoxIndex	OBJECT-TYPE
	SYNTAX	INTEGER
	ACCESS	not-accessible
	STATUS	mandatory
	DESCRIPTION
		""
	::= { kcprtMailBoxEntry 1 }

kcprtMailBoxDeviceIndex	OBJECT-TYPE
	SYNTAX	INTEGER
	ACCESS	read-only
	STATUS	mandatory
	DESCRIPTION
		""
	::= { kcprtMailBoxEntry 2 }

kcprtMailBoxStateCounter	OBJECT-TYPE
	SYNTAX	INTEGER	(0..4294967295)
	ACCESS	read-only
	STATUS	mandatory
	DESCRIPTION
		""
	::= { kcprtMailBoxEntry 3 }

kcprtMailBoxUsedTrays		OBJECT-TYPE
	SYNTAX	INTEGER	(0..255)
	ACCESS	read-only
	STATUS	mandatory
	DESCRIPTION
		""
	::= { kcprtMailBoxEntry 4 }

kcprtMailBoxDocumentsNumber	OBJECT-TYPE
	SYNTAX	INTEGER	(0..4294967295)
	ACCESS	read-only
	STATUS	mandatory
	DESCRIPTION
		""
	::= { kcprtMailBoxEntry 5 }

kcprtMailBoxPageNumber	OBJECT-TYPE
	SYNTAX	INTEGER	(0..4294967295)
	ACCESS	read-only
	STATUS	mandatory
	DESCRIPTION
		""
	::= { kcprtMailBoxEntry 6 }

kcprtMailBoxUsedSize		OBJECT-TYPE
	SYNTAX	INTEGER	(0..4294967295)
	ACCESS	read-only
	STATUS	mandatory
	DESCRIPTION
		""
	::= { kcprtMailBoxEntry 7 }

kcprtMailBoxLimitSize		OBJECT-TYPE
	SYNTAX	INTEGER	(0.. 4294967295)
	ACCESS	read-write
	STATUS	mandatory
	DESCRIPTION
		""
	::= { kcprtMailBoxEntry 8 }

kcprtMailBoxMaxLimitSize		OBJECT-TYPE
	SYNTAX	INTEGER	(0..4294967295)
	ACCESS	read-only
	STATUS	mandatory
	DESCRIPTION
		""
	::= { kcprtMailBoxEntry 9 }

kcprtMailBoxUnit		OBJECT-TYPE
	SYNTAX	INTEGER
	ACCESS	read-only
	STATUS	mandatory
	DESCRIPTION
		""
	::= { kcprtMailBoxEntry 10 }

kcprtMailBoxAliasCheck	OBJECT-TYPE
	SYNTAX	DisplayString	(SIZE(0..31))
	ACCESS	read-write
	STATUS	mandatory
	DESCRIPTION
		""
	::= { kcprtMailBoxEntry 11 }

kcprtMailBoxTrayTable		OBJECT-TYPE
SYNTAX	SEQUENCE OF KcprtMailBoxTrayEntry
ACCESS	not-accessible
STATUS	mandatory
DESCRIPTION
	""
::= { kcprtMailBox 2 }

kcprtMailBoxTrayEntry		OBJECT-TYPE
	SYNTAX	KcprtMailBoxTrayEntry
	ACCESS	not-accessible
	STATUS	mandatory
	DESCRIPTION
		""
	INDEX { hrDeviceIndex, kcprtMailBoxIndex, kcprtMailBoxTrayIndex }
	::= { kcprtMailBoxTrayTable 1 }

KcprtMailBoxTrayEntry			::=	SEQUENCE {
	kcprtMailBoxTrayIndex			INTEGER,
	kcprtMailBoxTrayUsedFlag		INTEGER,
	kcprtMailBoxTrayLabel			DisplayString,
	kcprtMailBoxTrayLock			INTEGER,
	kcprtMailBoxTrayDocumentsNumber		INTEGER,
	kcprtMailBoxTrayPageNumber		INTEGER,
	kcprtMailBoxTrayOccupiedSize		INTEGER,
	kcprtMailBoxTraySharedSize		INTEGER,
	kcprtMailBoxTrayErrorLogNumber		INTEGER,
	kcprtMailBoxTrayPurgeDocuments		INTEGER,
	kcprtMailBoxTrayReset			INTEGER
}

kcprtMailBoxTrayIndex		OBJECT-TYPE
	SYNTAX	INTEGER
	ACCESS	not-accessible
	STATUS	mandatory
	DESCRIPTION
		""
	::= { kcprtMailBoxTrayEntry 1 }

kcprtMailBoxTrayUsedFlag	OBJECT-TYPE
	SYNTAX	INTEGER	{
		notUsed(0),
		used(1),
		unknown(255)
	}
	ACCESS	read-only
	STATUS	mandatory
	DESCRIPTION
		""
	::= { kcprtMailBoxTrayEntry 2 }

kcprtMailBoxTrayLabel		OBJECT-TYPE
	SYNTAX	DisplayString	(SIZE(0..31))
	ACCESS	read-write
	STATUS	mandatory
	DESCRIPTION
		""
	::= { kcprtMailBoxTrayEntry 3 }

kcprtMailBoxTrayLock		OBJECT-TYPE
	SYNTAX	INTEGER	{
		unlock(0),
		lock(1),
		unknown(255)
	}
	ACCESS	read-only
	STATUS	mandatory
	DESCRIPTION
		""
	::= { kcprtMailBoxTrayEntry 4 }

kcprtMailBoxTrayDocumentsNumber	OBJECT-TYPE
	SYNTAX	INTEGER	(0..4294967295)
	ACCESS	read-only
	STATUS	mandatory
	DESCRIPTION
		""
	::= { kcprtMailBoxTrayEntry 5 }

kcprtMailBoxTrayPageNumber	OBJECT-TYPE
	SYNTAX	INTEGER	(0..4294967295)
	ACCESS	read-only
	STATUS	mandatory
	DESCRIPTION
		""
	::= { kcprtMailBoxTrayEntry 6 }

kcprtMailBoxTrayOccupiedSize		OBJECT-TYPE
	SYNTAX	INTEGER	(0..4294967295)
	ACCESS	read-only
	STATUS	mandatory
	DESCRIPTION
		""
	::= { kcprtMailBoxTrayEntry 7 }

kcprtMailBoxTraySharedSize		OBJECT-TYPE
	SYNTAX	INTEGER	(0..4294967295)
	ACCESS	read-only
	STATUS	mandatory
	DESCRIPTION
		""
	::= { kcprtMailBoxTrayEntry 8 }

kcprtMailBoxTrayErrorLogNumber	OBJECT-TYPE
	SYNTAX	INTEGER	(0..4294967295)
	ACCESS	read-only
	STATUS	mandatory
	DESCRIPTION
		""
	::= { kcprtMailBoxTrayEntry 9 }

kcprtMailBoxTrayPurgeDocuments	OBJECT-TYPE
	SYNTAX	INTEGER	(0..4294967295)
	ACCESS	read-write
	STATUS	mandatory
	DESCRIPTION
		""
	::= { kcprtMailBoxTrayEntry 10 }

kcprtMailBoxTrayReset		OBJECT-TYPE
	SYNTAX	INTEGER	(0..4294967295)
	ACCESS	read-write
	STATUS	mandatory
	DESCRIPTION
		""
	::= { kcprtMailBoxTrayEntry 11 }


kcprtTrayJobTable		OBJECT-TYPE
	SYNTAX	SEQUENCE OF KcprtTrayJobEntry
	ACCESS	not-accessible
	STATUS	mandatory
	DESCRIPTION
	""
::= { kcprtMailBox 3 }

kcprtTrayJobEntry		OBJECT-TYPE
	SYNTAX	KcprtTrayJobEntry
	ACCESS	not-accessible
	STATUS	mandatory
	DESCRIPTION
		""
INDEX { hrDeviceIndex, kcprtMailBoxIndex, kcprtMailBoxTrayIndex, kcprtTrayJobIndex }
	::= { kcprtTrayJobTable 1 }

KcprtTrayJobEntry			::=	SEQUENCE {
	kcprtTrayJobIndex			INTEGER,
	kcprtTrayJobID				DisplayString,
	kcprtTrayJobName			DisplayString,
	kcprtTrayJobOwner			DisplayString,
	kcprtTrayJobTime			DisplayString,
	kcprtTrayJobPageNumber			INTEGER,
	kcprtTrayJobSize			INTEGER,
	kcprtTrayJobStorageResult		INTEGER
}

kcprtTrayJobIndex		OBJECT-TYPE
	SYNTAX	INTEGER
	ACCESS	not-accessible
	STATUS	mandatory
	DESCRIPTION
		""
	::= { kcprtTrayJobEntry 1 }

kcprtTrayJobID			OBJECT-TYPE
	SYNTAX	DisplayString	(SIZE(0..31))
	ACCESS	read-only
	STATUS	mandatory
	DESCRIPTION
		""
	::= { kcprtTrayJobEntry 2 }

kcprtTrayJobName		OBJECT-TYPE
	SYNTAX	DisplayString	(SIZE(0..31))
	ACCESS	read-only
	STATUS	mandatory
	DESCRIPTION
		""
	::= { kcprtTrayJobEntry 3 }

kcprtTrayJobOwner		OBJECT-TYPE
	SYNTAX	DisplayString	(SIZE(0..31))
	ACCESS	read-only
	STATUS	mandatory
	DESCRIPTION
		""
	::= { kcprtTrayJobEntry 4 }

kcprtTrayJobTime		OBJECT-TYPE
	SYNTAX	DisplayString	(SIZE(0..31))
	ACCESS	read-only
	STATUS	mandatory
	DESCRIPTION
		""
	::= { kcprtTrayJobEntry 5 }

kcprtTrayJobPageNumber	OBJECT-TYPE
	SYNTAX	INTEGER	(0..4294967295)
	ACCESS	read-only
	STATUS	mandatory
	DESCRIPTION
		""
	::= { kcprtTrayJobEntry 6 }

kcprtTrayJobSize		OBJECT-TYPE
	SYNTAX	INTEGER	(0..4294967295)
	ACCESS	read-only
	STATUS	mandatory
	DESCRIPTION
		""
	::= { kcprtTrayJobEntry 7 }

kcprtTrayJobStorageResult	OBJECT-TYPE
	SYNTAX	INTEGER	{
		noError(0),
		error(1),
		unknown(255)
	}
	ACCESS	read-only
	STATUS	mandatory
	DESCRIPTION
		""
	::= { kcprtTrayJobEntry 8 }

--
--  Sub Unit group table
--
    kcprtSubUnitTable OBJECT-TYPE
        SYNTAX  SEQUENCE OF KcprtSubUnitEntry
        ACCESS  not-accessible
        STATUS  mandatory
        DESCRIPTION
            "This table contains information of the sub unit."
        ::={ kcprtSubUnit 1 }

    kcprtSubUnitEntry OBJECT-TYPE
        SYNTAX  KcprtSubUnitEntry
        ACCESS  not-accessible
        STATUS  mandatory
        DESCRIPTION
            "Information for the sub unit."
        INDEX { hrDeviceIndex, kcprtSubUnitIndex }
        ::={ kcprtSubUnitTable 1 }

    KcprtSubUnitEntry ::= SEQUENCE {
        kcprtSubUnitIndex   INTEGER,
	 kcprtSubUnitModel   DisplayString,
        kcprtSubUnitAbsoluteModel  DisplayString,
        kcprtSubUnitTableIndex  INTEGER,
        kcprtSubUnitObjectIndex   INTEGER
    }

    kcprtSubUnitIndex          OBJECT-TYPE
        SYNTAX  INTEGER
        ACCESS  not-accessible
        STATUS  mandatory
        DESCRIPTION
            "A unique value assigned by the printer system to identify sub units."
        ::= { kcprtSubUnitEntry 1 }

    kcprtSubUnitModel           OBJECT-TYPE
        SYNTAX  DisplayString   (SIZE(0..31))
        ACCESS  read-only
        STATUS  mandatory
        DESCRIPTION
            "The printer's sub unit name."
        ::= { kcprtSubUnitEntry 2 }

    kcprtSubUnitAbsoluteModel           OBJECT-TYPE
        SYNTAX  DisplayString   (SIZE(0..31))
        ACCESS  read-only
        STATUS  mandatory
        DESCRIPTION
            "The printer's sub unit absolute name."
        ::= { kcprtSubUnitEntry 3 }

    kcprtSubUnitTableIndex OBJECT-TYPE
        SYNTAX  INTEGER
        ACCESS  read-only
        STATUS  mandatory
        DESCRIPTION
            "The printer's sub unit table index."
        ::={ kcprtSubUnitEntry 4 }

    kcprtSubUnitObjectIndex OBJECT-TYPE
        SYNTAX  INTEGER
        ACCESS  read-only
        STATUS  mandatory
        DESCRIPTION
            "The printer's sub unit object index."
        ::={ kcprtSubUnitEntry 5 }

--
--  Job group table
--
	kcprtJobGeneralTable	OBJECT-TYPE
		SYNTAX		SEQUENCE OF KcprtJobGeneralEntry
		ACCESS		not-accessible
		STATUS		mandatory
		DESCRIPTION
		"This table contains information of printer job."
	::= { kcprtJob 1 }

	kcprtJobGeneralEntry	OBJECT-TYPE
		SYNTAX		KcprtJobGeneralEntry
		ACCESS		not-accessible
		STATUS		mandatory
		DESCRIPTION
		"Information for printer job."
		INDEX	{ hrDeviceIndex }
	::= { kcprtJobGeneralTable 1 }

	KcprtJobGeneralEntry	::= SEQUENCE {
		kcprtJobMaxEntryNumber		INTEGER,
		kcprtJobNewestJobIndex		INTEGER,
		kcprtJobCancelByJobOwner	DisplayString
	}

	kcprtJobMaxEntryNumber	OBJECT-TYPE
		SYNTAX		INTEGER
		ACCESS		read-only
		STATUS		mandatory
		DESCRIPTION
		"Max job number on jmJobTable"
	::={ kcprtJobGeneralEntry 1 }

	kcprtJobNewestJobIndex	OBJECT-TYPE
		SYNTAX		INTEGER
		ACCESS		read-only
		STATUS		mandatory
		DESCRIPTION
		"The newest job index of jmJobTable"
	::={ kcprtJobGeneralEntry 2 }

	kcprtJobCancelByJobOwner	OBJECT-TYPE
		SYNTAX		DisplayString ( SIZE(0..63) )
		ACCESS		write-only
		STATUS		mandatory
		DESCRIPTION
		"Set jmJobOwner for cancel."
	::={ kcprtJobGeneralEntry 3 }

END
