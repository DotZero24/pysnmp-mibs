TEMPERATUREALERT-MIB DEFINITIONS ::= BEGIN

IMPORTS
	MODULE-IDENTITY,
        OBJECT-TYPE
                FROM SNMPv2-SMI
	DisplayString
                FROM SNMPv2-TC
	enterprises
		FROM RFC1155-SMI
	TRAP-TYPE
		FROM RFC-1215;

taMIB MODULE-IDENTITY
        LAST-UPDATED "1810231200Z"
        ORGANIZATION "Temperature@lert"
        CONTACT-INFO
                "Harry Schechter

                Postal: 3059 Connecticut Ave, #8115
			Washington, DC  20008

                E-mail: info@temperaturealert.com"
        DESCRIPTION
		"The Temperature@lert SNMP MIB."
        REVISION "1810231200Z"
        DESCRIPTION
                "Modified to include WiFi OIDs. adama@obsevium.org"
        REVISION "0610311200Z"
	DESCRIPTION
		"Current revision."
	::= { enterprises 27297 }


taTraps		OBJECT IDENTIFIER ::= { taMIB 0 }
taService       OBJECT IDENTIFIER ::= { taMIB 1 }
taWifi          OBJECT IDENTIFIER ::= { taMIB 2 }

taDeviceIndex OBJECT-TYPE
        SYNTAX  DisplayString
        MAX-ACCESS read-only
        STATUS current
        DESCRIPTION
                "COM Port of the device"
 ::= { taService 1 }

taTemperature OBJECT-TYPE
        SYNTAX  DisplayString
        MAX-ACCESS read-only
        STATUS current
        DESCRIPTION
                "The temperature picked up by the monitor."
 ::= { taService 2 }

taLastCheck OBJECT-TYPE
        SYNTAX  DisplayString
        MAX-ACCESS read-only
        STATUS current
        DESCRIPTION
                "The date and time when the monitor checked the temperature."
 ::= { taService 3 }

taTemperatureTable   OBJECT IDENTIFIER ::= { taWifi 7 }
taTemperatureEntry   OBJECT IDENTIFIER ::= { taTemperatureTable 1 }

taTemperaturePort OBJECT-TYPE
        SYNTAX  DisplayString
        MAX-ACCESS read-only
        STATUS current
        DESCRIPTION
                "The temperature picked up by the monitor."
 ::= { taTemperatureEntry 7 }


taNormal NOTIFICATION-TYPE
     OBJECTS           { taDeviceIndex, taTemperature, taLastCheck }
     STATUS            current
     DESCRIPTION
          "Fired when the alarm is read."
     ::= { taTraps 1 }

taHighAlarm NOTIFICATION-TYPE
     OBJECTS           { taDeviceIndex, taTemperature, taLastCheck }
     STATUS            current
     DESCRIPTION
          "Fired when the high alarm is tripped."
     ::= { taTraps 2 }

taLowAlarm NOTIFICATION-TYPE
     OBJECTS           { taDeviceIndex, taTemperature, taLastCheck }
     STATUS            current
     DESCRIPTION
          "Fired when the low alarm is tripped."
     ::= { taTraps 3 }

taShutdown NOTIFICATION-TYPE
     STATUS            current
     DESCRIPTION
          "Fired when the application is shutting down the server."
     ::= { taTraps 4 }

END
