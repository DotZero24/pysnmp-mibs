TI-MANUFACTURER-MIB DEFINITIONS ::= BEGIN

IMPORTS
        enterprises FROM SNMPv2-SMI;

-- TI Enterprise number is 294
-- Enterprise number must be changed for other vendors

        ti              OBJECT IDENTIFIER ::= { enterprises 294 }
        equipment       OBJECT IDENTIFIER ::= { ti 1 }
        eqName          OBJECT IDENTIFIER ::= { equipment 400 }

END
