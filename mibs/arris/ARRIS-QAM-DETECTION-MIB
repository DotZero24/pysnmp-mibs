ARRIS-QAM-DETECTION-MIB DEFINITIONS ::= BEGIN

IMPORTS
   MODULE-IDENTITY,
   OBJECT-TYPE,
   Integer32,
   Counter32,
   Counter64,
   IpAddress
      FROM SNMPv2-SMI
   arrisProdIdCM
      FROM ARRIS-MIB
   TruthValue, DisplayString, TimeStamp, DateAndTime, TEXTUAL-CONVENTION
      FROM SNMPv2-TC
   SnmpAdminString
      FROM SNMP-FRAMEWORK-MIB;

   arrisQamDetectionMib MODULE-IDENTITY
      LAST-UPDATED    "1007160000Z"  -- July 16, 2010
      ORGANIZATION    "ARRIS Broadband"
      CONTACT-INFO    "Derek Winters
                       Postal: ARRIS Broadband
                       3871 Lakefield Drive
                       Suite 300
                       Suwanee, GA 30024-1242
                       U.S.A."
      DESCRIPTION
       "This MIB module supplies the basic proprietary
        management objects for the QAM Detection Feature"

      -- Revision history
      REVISION    "1108030000Z"  -- August 03, 2011
         DESCRIPTION
      "Initial version"
::= { arrisProdIdCM 12 }

-- This MIB module contains the following groups.
arrisQamDetectionMibObjects          OBJECT IDENTIFIER ::= { arrisQamDetectionMib 1 }

arrisQamDetectionConfig          OBJECT IDENTIFIER ::= { arrisQamDetectionMibObjects 1 }

arrisQamDetectionConfigEnable OBJECT-TYPE
    SYNTAX      TruthValue
    MAX-ACCESS  read-write
    STATUS      current
    DESCRIPTION
    "This object is used to enable or disable the QAM Detection feature."
    ::= { arrisQamDetectionConfig 1 }

arrisQamDetectionConfigFrequencyTable OBJECT-TYPE
    SYNTAX      SEQUENCE OF ArrisQamDetectionConfigFrequencyEntry
    MAX-ACCESS  not-accessible
    STATUS      current
    DESCRIPTION
        "This table contains the MIB table required to configure the
         QAM Detection Frequencies under test."
    ::= { arrisQamDetectionConfig 2 }

arrisQamDetectionConfigFrequencyEntry OBJECT-TYPE
    SYNTAX      ArrisQamDetectionConfigFrequencyEntry
    MAX-ACCESS  not-accessible
    STATUS      current
    DESCRIPTION
        "This table contains the MIB table required to configure the
         QAM Detection Frequencies under test."
    INDEX { arrisQamDetectionConfigFrequencyIndex  }
    ::= {  arrisQamDetectionConfigFrequencyTable 1 }

ArrisQamDetectionConfigFrequencyEntry ::= SEQUENCE {
         arrisQamDetectionConfigFrequencyIndex        INTEGER,
         arrisQamDetectionConfigFrequency             Integer32 (91000000..999000000)
    }

arrisQamDetectionConfigFrequencyIndex OBJECT-TYPE
    SYNTAX      INTEGER (1..3)
    MAX-ACCESS  not-accessible
    STATUS      current
    DESCRIPTION
        "Index used to order the arrisQamDetectionConfigFrequencyTable entries."
    ::= { arrisQamDetectionConfigFrequencyEntry 1 }

arrisQamDetectionConfigFrequency OBJECT-TYPE
    SYNTAX      Integer32 (91000000..999000000)
    UNITS       "hertz"
    MAX-ACCESS  read-write
    STATUS      current
    DESCRIPTION
        "This object shows the frequency under test.  Value can be set to
	 91000000 Hz - 999000000 Hz.  Setting value to 0 will disable this
	 frequency."
    ::= { arrisQamDetectionConfigFrequencyEntry 2 }

arrisQamDetectionConfigClearResults OBJECT-TYPE
    SYNTAX      TruthValue
    MAX-ACCESS  read-write
    STATUS      current
    DESCRIPTION
    "This object is used to clear the QAM Detection results table."
    ::= { arrisQamDetectionConfig 3 }

-- arrisQamDetectionResultsTable MIB objects --

arrisQamDetectionResultsTable OBJECT-TYPE
    SYNTAX      SEQUENCE OF ArrisQamDetectionResultsEntry
    MAX-ACCESS  not-accessible
    STATUS      current
    DESCRIPTION
        "This table contains all the MIB variables required for the
         QAM Detection Results."
    ::= { arrisQamDetectionMibObjects 2 }

arrisQamDetectionResultsEntry OBJECT-TYPE
    SYNTAX      ArrisQamDetectionResultsEntry
    MAX-ACCESS  not-accessible
    STATUS      current
    DESCRIPTION
        "This table contains all the MIB variables required for the
         QAM Detection Results."
    INDEX { arrisQamDetectionResultsIndex  }
    ::= {  arrisQamDetectionResultsTable 1 }

ArrisQamDetectionResultsEntry ::= SEQUENCE {
         arrisQamDetectionResultsIndex                INTEGER,
         arrisQamDetectionResultsFreq                 Integer32 (91000000..999000000),
         arrisQamDetectionResultsTimestamp            DisplayString
    }

arrisQamDetectionResultsIndex OBJECT-TYPE
    SYNTAX      INTEGER (1..30)
    MAX-ACCESS  not-accessible
    STATUS      current
    DESCRIPTION
        "Index used to order the arrisQamDetectionResultsTable entries."
    ::= { arrisQamDetectionResultsEntry 1 }

arrisQamDetectionResultsFreq OBJECT-TYPE
    SYNTAX      Integer32 (91000000..999000000)
    UNITS       "hertz"
    MAX-ACCESS  read-only
    STATUS      current
    DESCRIPTION
        "This object shows a frequency where a QAM signal was detected."
    ::= { arrisQamDetectionResultsEntry 2 }

arrisQamDetectionResultsTimestamp OBJECT-TYPE
    SYNTAX      DisplayString
    MAX-ACCESS  read-only
    STATUS      current
    DESCRIPTION
        "This object shows the time and date of when a QAM signal was detected."
    ::= { arrisQamDetectionResultsEntry 3 }
END
