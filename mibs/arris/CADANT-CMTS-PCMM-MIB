--
-- Cadant PCMM MIB
--

CADANT-CMTS-PCMM-MIB DEFINITIONS ::= BEGIN

IMPORTS
	MODULE-IDENTITY,
	OBJECT-TYPE,
	Unsigned32
		FROM SNMPv2-SMI

    TEXTUAL-CONVENTION, DisplayString
        FROM SNMPv2-TC

    AdminState
        FROM CADANT-TC

    cadPCMibObjects
		FROM CADANT-CMTS-PACKETCABLE-MIB;

cadPCMMMib   MODULE-IDENTITY
	LAST-UPDATED	"201006010000Z" -- June 1, 2010
	ORGANIZATION	"Arris"
	CONTACT-INFO	"Arris
                     Suite 180
                     2400 E. Ogden Avenue
                     Lisle, IL 60532
                     U.S.A."
	DESCRIPTION	"This MIB Module supplies the management objects which are
                     specific to the PacketCable Multimedia client of COPS. The
                     objects for the management of the standard COPS protocol
                     reside in RFC2940."
       REVISION         "201006010000Z" -- June 1, 2010
	DESCRIPTION     "Add cadPCMMSubscriberIdVrfName."

       REVISION         "200910190000Z" -- October 19, 2009
	DESCRIPTION     "Add CopsVersion I05."

       REVISION         "200909210000Z" -- September 21, 2009
	DESCRIPTION     "Add CopsVersion."

       REVISION         "200503110000Z"
	DESCRIPTION     "Modify the unit of cadPCMMTimerT1 to deciseconds."

       REVISION     "200405050000Z" -- May 5, 2004
	DESCRIPTION "v1.0  - Original version"

::= { cadPCMibObjects 3 }


CopsVersion ::= TEXTUAL-CONVENTION
    STATUS       current
    DESCRIPTION
        "This TEXTUAL-CONVENTION describes the major PCMM
         COPS releases available on the C4."
    SYNTAX INTEGER {
        i02 (1),
        i03 (2),
        i04 (3),
        i05 (4)
    }


cadPCMMMibObjects OBJECT IDENTIFIER ::= { cadPCMMMib 1 }
cadPCMMConfigBase OBJECT IDENTIFIER ::= { cadPCMMMibObjects 1 }

cadPCMMAdminState OBJECT-TYPE
    SYNTAX          AdminState
    MAX-ACCESS      read-write
    STATUS          current
    DESCRIPTION     "The administrative state of PacketCable Multimedia
                     services on the CMTS."
    DEFVAL          { down }
    ::= { cadPCMMConfigBase 1 }

cadPCMMTimerT1 OBJECT-TYPE
    SYNTAX          Unsigned32 (1..3000)
    UNITS           "deciseconds"
    MAX-ACCESS      read-write
    STATUS          current
    DESCRIPTION     "Timer T1 limits the amount of time the Gate authorization
                     remains valid without a resource reservaton."
    DEFVAL          { 300 }
    ::= { cadPCMMConfigBase 2 }

cadPCMMCopsVersion OBJECT-TYPE
    SYNTAX          CopsVersion
    MAX-ACCESS      read-write
    STATUS          current
    DESCRIPTION     "This object describes the PCMM COPS version that the C4 will
                     advertise in the OPN message."
    DEFVAL          { i05 }
    ::= { cadPCMMConfigBase 3 }

cadPCMMSubscriberIdVrfName OBJECT-TYPE
    SYNTAX     DisplayString (SIZE (0..64))
    MAX-ACCESS read-write
    STATUS     current
    DESCRIPTION
               "The name of the virtual router (VRF) that will be used to determine
                where a subscriberID remotely connected is located. If the specified
                VRF does not exist, then the default VRF will be used instead."
    DEFVAL { "default" }
    ::= { cadPCMMConfigBase 4 }


-- notification group is for future extension.
--cadPCMMNotificationPrefix OBJECT IDENTIFIER    ::= { cadPCMMMib 2 }
--cadPCMMNotification OBJECT IDENTIFIER          ::= { cadPCMMNotificationPrefix 0 }

--cadPCMMConformance  OBJECT IDENTIFIER          ::= { cadPCMMMib 3 }
--cadPCMMCompliances  OBJECT IDENTIFIER          ::= { cadPCMMConformance 1 }
--cadPCMMGroups       OBJECT IDENTIFIER          ::= { cadPCMMConformance 2 }

END
