ARRIS-MTA-DEVICE-MIB DEFINITIONS ::= BEGIN

IMPORTS
   MODULE-IDENTITY,
   OBJECT-TYPE,
   Integer32,
   Counter32,
   Counter64,
   IpAddress
      FROM SNMPv2-SMI
   arrisProdIdCM
      FROM ARRIS-MIB
   TruthValue, DisplayString, TimeStamp, DateAndTime, TEXTUAL-CONVENTION, PhysAddress
      FROM SNMPv2-TC
   SnmpAdminString
      FROM SNMP-FRAMEWORK-MIB
   InetAddressType, InetAddress
      FROM INET-ADDRESS-MIB;

arrisMtaDevMib MODULE-IDENTITY
     LAST-UPDATED    "1506250000Z" -- June 25, 2015
     ORGANIZATION    "ARRIS Broadband"
     CONTACT-INFO    "Rodney Osborne
                      Postal: ARRIS Broadband
                      3871 Lakefield Drive
                      Suite 300
                      Suwanee, GA 30024-1242
                      U.S.A.
                      Phone:  +1 770-622-8400
                      E-mail: rodney.osborne@arrisi.com"
     DESCRIPTION
         "This MIB module supplies the basic proprietary
          management objects for ARRIS MTA devices."


-- Revision history
    REVISION    "1506250000Z" -- June 25, 2015
    DESCRIPTION
         "Added new MIB arrisMtadocsQosServiceTable, arrisMtadocsQosDisableLoggin, arrisMtadocsQosLogClear and arrisMtadocsQosShowDsxLogTable"
    REVISION    "1501200000Z" -- Jan 20, 2015
    DESCRIPTION
         "Change default value related description of mib arrisMtaDevPwrSupplyDataShutdownTime."
    REVISION    "1205020000Z" -- May 2, 2012
    DESCRIPTION
         "Add persistence to description for arrisMtaDevEndPntHDAudioEnable MIB and change default of arrisMtaDevWBSLIC to disable."
    REVISION    "1203160000Z" -- March 16, 2012
    DESCRIPTION
         "Added new table arrisMtaDevCmIpTable"

    REVISION    "1203150000Z" -- Mar 15, 2012
    DESCRIPTION
         "Modified OID for arrisMtaDevHDAudioEnable from 48 to 53"
    REVISION    "1203060000Z" -- Mar 6, 2012
    DESCRIPTION
         "Added new MIB arrisMtaDevHDAudioG722SampleRate"
    REVISION    "1202280000Z" -- Feb 28, 2012
    DESCRIPTION
         "Added new MIB arrisMtaDevProvisionedCodecArray"
    REVISION    "1202210000Z" -- Feb 21, 2012
    DESCRIPTION
         "Added MIBs to support HD Audio."
    REVISION    "1104180000Z" -- Apr 18, 2011
    DESCRIPTION
         "Modified MIB arrisMtaDevEndPntRingingWaveform description."
    REVISION    "1104070000Z" -- Apr 7, 2011
    DESCRIPTION
         "Added new MIB arrisMtaDevPwrSupplyEnableWifiShutdown"

    REVISION    "1006220000Z" -- June 22, 2010
    DESCRIPTION
         "Changed arrisMtaDevMaxCallPServiceFlows OID from { arrisMtaDevOperationalSetup 46 }
          to { arrisMtaDevOperationalSetup 47 }"

    REVISION    "1005050000Z" -- May 5, 2010
    DESCRIPTION
         "Added new MIB arrisMtaDevMaxCallPServiceFlows"

    REVISION    "1003030000Z" -- March 3, 2010
    DESCRIPTION
         "Added new alarm autonomous types upsAlarmAwaitingPower and upsAlarmShutdownPending for
          upsAlarmDescr MIB"

    REVISION    "1002100000Z" -- February 10, 2010
    DESCRIPTION
         "Added new alarm autonomous types upsAlarmBatteryBad, upsAlarmLowBattery, upsAlarmDepletedBattery,
          upsAlarmUpsOutputOff, upsAlarmOutputOffAsRequested, upsAlarmGeneralFault, upsAlarmShutdownImminent,
          upsAlarmBatteryMissing for upsAlarmDescr MIB"

    REVISION    "1001200000Z" -- January 20, 2010
    DESCRIPTION
         "Added new MIB arrisMtaDevEventFormat"

    REVISION    "0906300000Z" -- June 30, 2009
    DESCRIPTION
         "Added new MIB arrisMtaDevEndPntGainControlTxVoice, and arrisMtaDevEndPntGainControlRxVoice"

    REVISION    "0905040000Z" -- May 04, 2009
    DESCRIPTION
         "Added new MIB arrisMtaDevEndPntLoopReversal"

    REVISION    "0904290000Z" -- Apr 29, 2009
    DESCRIPTION
         "Added new MIB arrisMtaDevEndPntCIDEnable, arrisMtaDevEndPntCIDNameEnable,
          arrisMtaDevEndPntCIDDateTimeEnable"

    REVISION    "0904200000Z" -- Apr 20, 2009
    DESCRIPTION
         "Added new MIB arrisMtaDevEndPntCallWaitingRepeatSteady"

    REVISION    "0812020000Z" -- Dec 02, 2008
    DESCRIPTION
         "Added new MIB arrisMtaDevPersistentLineStatus"

    REVISION    "0902020000Z" -- February 13, 2009
    DESCRIPTION
        "Added new mib arrisMtaDevDTMFEndEventForceAscending"

    REVISION    "0809220000Z" -- Sept 22, 2008
    DESCRIPTION
         "Added ac-Fail chargerOverTemp-Shutdown chargerTemperature-High
          batteryCharger-Disabled chargerDownload-Failed and battery-Mismatch "

    REVISION    "0806170000Z" -- June 17, 2008
    DESCRIPTION
         "Added Null option to arrisMtaDevDefaultReasonNoCIDName and
         added new MIB arrisMtaDevOffHookFskDelay"

    REVISION    "0806100000Z" -- Jun 10, 2008
    DESCRIPTION
        "Added arrisMtaDevEndPntFaxOnlyLineTimeout"

    REVISION    "0804120000Z" -- April 12, 2008
    DESCRIPTION
        "Added arrisMtaDevRestoreNvmFactoryDefault"

    REVISION    "0804220000Z" -- April 22, 2008
    DESCRIPTION
        "Added arrisMtaDevVqmCallNumberIdentifierLastCall"

    REVISION    "0804010000Z" -- April 01, 2008
    DESCRIPTION
        "Added arrisMtaDevPwrSupplyControlChargerReset"

    REVISION    "0802220000Z" -- February 22, 2008
    DESCRIPTION
        "Added arrisMtaDevPwrSupplyHighestTemperatureTime and
         arrisMtaDevPwrSupplyHighestTemperatureClear"

    REVISION    "0802040000Z" -- February 04, 2008
    DESCRIPTION
        "Added arrisMtaDevPacketcableProvisioningFlow"
    REVISION    "0801290000Z" -- January 29, 2008
    DESCRIPTION
        "Added arrisMtaDevPwrSupplyHighestTemperature"
    REVISION    "0801170000Z" -- January 17, 2008
    DESCRIPTION
        "Increased range of arrisMtaDevGainControlRxVoice and TxVoice MIBs"

    REVISION    "0801170000Z" -- January 17, 2008
    DESCRIPTION
        "Added SDMF option to arrisMtaDevDefaultReasonNoCIDName"

    REVISION    "1107130000Z" -- November 13, 2007
    DESCRIPTION
        "Added arrisMtaDevGainControlOffHookEnable, arrisMtaDevGainControlOffHookFSK, and
         arrisMtaDevGainControlOffHookCAS"

   REVISION    "1007300000Z" -- October 30,2007
   DESCRIPTION
       "Added arrisMtaDevAutomaticCallResourceRecovery"

   REVISION    "0707270000Z" -- July 27,2007
    DESCRIPTION
        "Added arrisMtaDevTDDReportToCMS"

    REVISION    "0704090000Z" -- April 9,2007
    DESCRIPTION
        "Added arrisMtaDevAutomaticOsiDelay."

    REVISION    "0611290000Z" -- March 29, 2006
    DESCRIPTION
        "Added arrisMtaDevTFTPServerAddrOverrideFQDN. Also added new ProvMethodIndicator
         gupiTftpSvrOverride"

    REVISION    "0603290000Z" -- March 29, 2006
    DESCRIPTION
        "Added arrisMtaDevDspCpsSetting object."

    REVISION    "0602170000Z" -- February 17, 2006
    DESCRIPTION
        "Added in mib to allow for query of the Dhcp parameters per PD#76971."

    REVISION    "0502010000Z" -- February 1, 2005
    DESCRIPTION
        "Added object 'arrisMtaDevGainControl'."
    REVISION    "0507270000Z" -- July 27, 2005
    DESCRIPTION
        "Modified range for object 'arrisMtaDevGainControlLocalDTMF' from (-9..9) to (-15..9)."

    REVISION    "0502010000Z" -- February 1, 2005
    DESCRIPTION
        "Added object 'arrisMtaDevGainControl'."

    REVISION    "0501040000Z" -- January 4, 2005
    DESCRIPTION
        "Added object 'arrisMtaDevDspHandleNonPhaseReversedTone'."

    REVISION    "0412160000Z" -- December 16, 2004
    DESCRIPTION
        "Added object 'arrisMtaDevProvMethodIndicator' and table
         'arrisMtaDevEndPntTable."

    REVISION    "0307110000Z"  -- July 11, 2003
    DESCRIPTION
        "Initial version"
    ::= { arrisProdIdCM 3 }


-- Textual Conventions
ArrsMtaDevProvMethod ::= TEXTUAL-CONVENTION
    STATUS current
    DESCRIPTION "These are the various provisioning methods that are
                 supported by the device."
    SYNTAX INTEGER {
        docsisOnly(0),
        fullPacketCable(1),
        packetCableMinusKDC(2),
        cps(3),
        gupi(4),
        singleMAC(5),
        basic1(6),
        basic2(7),
        gupiEncryptedMtaConfig(8),
        gupiMacMta(9),
        gupiEncryptedMacMta(10),
        gupiTftpSvrOverride(11)
    }

CodecType ::= TEXTUAL-CONVENTION
 STATUS obsolete
 DESCRIPTION "These are the various types of codecs that
              may be supported."
 SYNTAX INTEGER{
               g711u(1),
               g711a(2),
               g7231(3),
               g729(4),
               g729a(5),
               g729e(6),
               g726(7),
               g728(8)
               }

PacketizationPeriodType ::= TEXTUAL-CONVENTION
 STATUS obsolete
 DESCRIPTION "The packetization periods supported by the PacketPort."
 SYNTAX INTEGER{
               ten(10),
               twenty(20),
               thirty(30)
               }

SignalingProtocol ::= TEXTUAL-CONVENTION
  STATUS obsolete
  DESCRIPTION "These are the various signaling protocols
              that may be supported."
  SYNTAX INTEGER{
            none(0),
            ncs(1)}


-- This MIB module contains the following groups.
arrisMtaDevMibObjects            OBJECT IDENTIFIER ::= { arrisMtaDevMib 1 }

arrisMtaDevBase                  OBJECT IDENTIFIER ::= { arrisMtaDevMibObjects 1 }
arrisMtaDevSetup                 OBJECT IDENTIFIER ::= { arrisMtaDevMibObjects 2 }
arrisMtaDevPowerSupplyTelemetry  OBJECT IDENTIFIER ::= { arrisMtaDevMibObjects 3 }
arrisMtaDevLineCard              OBJECT IDENTIFIER ::= { arrisMtaDevMibObjects 4 }
arrisMtaDispSignal              OBJECT IDENTIFIER ::= { arrisMtaDevMibObjects 5 }

-- arrisMtaDevTest                  OBJECT IDENTIFIER ::= { arrisMtaDevMibObjects 5 }

arrisMtadocsQosService          OBJECT IDENTIFIER ::= { arrisMtaDevMibObjects 6 }


arrisMtaDevMonitoringMib         OBJECT IDENTIFIER ::= { arrisMtaDevBase 1 }
arrisMtaDevControl               OBJECT IDENTIFIER ::= { arrisMtaDevMonitoringMib 1 }
arrisMtaDevTrace                 OBJECT IDENTIFIER ::= { arrisMtaDevMonitoringMib 2 }
arrisMtaDevParameters            OBJECT IDENTIFIER ::= { arrisMtaDevMonitoringMib 3 }
arrisMtaDevVqm                   OBJECT IDENTIFIER ::= { arrisMtaDevMonitoringMib 4 }

arrisMtaDevDhcp                  OBJECT IDENTIFIER ::= { arrisMtaDevBase 2 }

-- Production groups
-- arrisMtaDevPermanentSetup       OBJECT IDENTIFIER ::= { arrisMtaDevSetup 2 }
arrisMtaDevOperationalSetup     OBJECT IDENTIFIER ::= { arrisMtaDevSetup 3 }
arrisMtaDevEndPntSetup          OBJECT IDENTIFIER ::= { arrisMtaDevSetup 4 }
-- arrisMtaDevSalesSetup           OBJECT IDENTIFIER ::= { arrisMtaDevSetup 4 }

arrisMtaDevOptionality          OBJECT IDENTIFIER ::= { arrisMtaDevOperationalSetup 10 }
arrisMtaDevLoopVoltageMgmt      OBJECT IDENTIFIER ::= { arrisMtaDevOperationalSetup 11 }
arrisMtaDevGainControl          OBJECT IDENTIFIER ::= { arrisMtaDevOperationalSetup 12 }
arrisMtaDevLevelControl         OBJECT IDENTIFIER ::= { arrisMtaDevOperationalSetup 40 }
arrisMtaDevDiag                 OBJECT IDENTIFIER ::= { arrisMtaDevOperationalSetup 15 }
arrisMtaDevCmIp                 OBJECT IDENTIFIER ::= { arrisMtaDevOperationalSetup 48 }

-- arrisMtaDevManufacturingTest    OBJECT IDENTIFIER ::= { arrisMtaDevTest 2 }
-- arrisMtaDevOperationalTest      OBJECT IDENTIFIER ::= { arrisMtaDevTest 3 }



--
-- The following group describes the Monitoring MIB control objects
-- in the Arris MTA device.
--

arrisMtaDevResetCallStats OBJECT-TYPE
    SYNTAX      TruthValue
    MAX-ACCESS  read-write
    STATUS      current
    DESCRIPTION
          "Setting this object to true(1) will reset the following
             objects to their default values:
               arrisMtaDevRtpTxPktsTotal,
               arrisMtaDevRtpRxPktsTotal,
               arrisMtaDevRtpPercentPktsLostTotal,
               arrisMtaDevSignalingAvgLatency,
               arrisMtaDevSignalingTxSuccessfulMsgCnt,
               arrisMtaDevSignalingRxSuccessfulMsgCnt,
               arrisMtaDevSignalingTxNAKCnt,
               arrisMtaDevSignalingRxNAKCnt,
               arrisMtaDevSignalingRxNoACKCnt
             Setting this object to false(2) will do nothing.
             Reading this object always returns false(2)."
    ::= { arrisMtaDevControl 1 }

arrisMtaDevEnableCallpSigTrace OBJECT-TYPE
    SYNTAX INTEGER {
        disable(0),
        enable(1)
    }
    MAX-ACCESS read-write
    STATUS current
    DESCRIPTION
        "This MIB object is used to turn Callp signaling Message tracing
         on in the SYSLOG.  This option should be used with care as excessive
         messaging could adversly affect performance.  The default value is disable(0)."
    ::= { arrisMtaDevControl 2 }

arrisMtaDevEnableCallStatsSyslogRpt OBJECT-TYPE
    SYNTAX INTEGER {
        disable(0),
        enable(1)
    }
    MAX-ACCESS  read-write
    STATUS      current
    DESCRIPTION
       "This MIB object is used to enable end of call statistics reporting and
        Callp signaling last message reporting to syslog. If this is set to enable(1),
        then the end of call statistics will be reported in syslog messaging.
        If arrisMtaDevEnableCallSigLastMsgRpt is enabled, then the last 4K of signaling
        message will be reported in syslog messageing as well. If the set to
        diable(0), then end of call statistics and the Callp last signaling
        messages will not be reported in syslog messaging.  The default value is disable(0)."
    ::= { arrisMtaDevControl 3 }

arrisMtaDevSwDnldNoSvcImpact OBJECT-TYPE
    SYNTAX  INTEGER {
        disable(0),
        enable(1),
        strictEnable(2)
    }
    MAX-ACCESS  read-write
    STATUS      current
    DESCRIPTION
          "This MIB object is used to control the firmware download service impact feature.
           The value is kept in non-volatile storage. Operation is as follows:
           disable(0) - Always download firmware and reboot immediately after firmware download.
           enable(1) - Download firmware immediately but delay the reboot until all lines
              are on-hook and no connections are active.
           StrictEnable(2) - Do not download firmware if any phone endpoint is off hook."
    ::= { arrisMtaDevControl 4 }

arrisMtaDevEnableCallSigLastMsgRpt OBJECT-TYPE
    SYNTAX INTEGER {
        disable(0),
        enable(1)
    }
    MAX-ACCESS  read-write
    STATUS      current
    DESCRIPTION
          "This MIB object is used to enable or disable reporting of the Callp signaling
          'last message' to the MIB objects arrisMtaDevSignalingLastMsg1 through
          arrisMtaDevSignalingLastMsg16.  Together the sixteen MIB objects can contain a
          signaling message as large as 4000 bytes.  Each of the sixteen MIB objects will
          contain a 255 byte segment of the message.  If the message is too small to require
          all sixteen MIBs then the empty MIB objects will display the value 'Buffer is empty'.
          The default value is disable(0)."
    ::= { arrisMtaDevControl 5 }

arrisMtaDevNsadSwDnldStatus OBJECT-TYPE
    SYNTAX  INTEGER {
        download-Idle (0),
        download-Acceptance-In-Progress  (1),
		download-Application-Pending (2)
    }
    MAX-ACCESS  read-only
    STATUS      current
    DESCRIPTION
          "This MIB object is set to download-Idle upon startup and when the firmware download has completed.  The download-Acceptance-In-Progress setting denots that the unit is currently downloading the firmware in the background.  The download-Application-Pending state is set to indicate the load has been downloaded and accepted but is waiting to be applied. This MIB object is only valid if the arrisMtaDevSwDnldNoSvcImpact MIB object is set to enabled (1)."
	DEFVAL { download-Idle }
    ::= { arrisMtaDevControl 6 }

arrisMtaDevRestoreNvmFactoryDefault OBJECT-TYPE
    SYNTAX      TruthValue
    MAX-ACCESS  read-write
    STATUS      current
    DESCRIPTION
          "Setting this object to true(1) will reset the NVM to default values:
           Setting this object to false(2) will do nothing.
           Reading this object always returns false(2)."
    ::= { arrisMtaDevControl 7 }

arrisMtaDevEnableLogging OBJECT-TYPE
    SYNTAX  INTEGER {
        disable(0),
        enable(1)
    }
    MAX-ACCESS  read-write
    STATUS      current
    DESCRIPTION
          "This MIB object is used to enable or disable logging via the
    NCS logger.  Use arrisMtaDevLoggingContext to specify the desired
    log type."
    ::= { arrisMtaDevControl 8 }

arrisMtaDevLoggingContext OBJECT-TYPE
    SYNTAX  INTEGER {
        mgcp(0),
        cm-dhcp(1),
        mta-dhcp(2),
        dsx(3)
    }
    MAX-ACCESS  read-write
    STATUS      current
    DESCRIPTION
          "This MIB object sets the logging context for reading logs via SNMP."

    ::= { arrisMtaDevControl 9 }

arrisMtaDevEnablePacketLossConcealment OBJECT-TYPE
    SYNTAX  INTEGER {
	    disable(0),
	    enable(1)
    }
    MAX-ACCESS  read-write
    STATUS      current
    DESCRIPTION
          "This MIB object sets enable/disable of the Packet loss concealment(PLC) via SNMP."

    ::= { arrisMtaDevControl 10 }

 arrisMtaDevEnableRTCPStaticInterval OBJECT-TYPE
    SYNTAX  INTEGER {
	    disable(0),
	    enable(1)
    }
    MAX-ACCESS  read-write
    STATUS      current
    DESCRIPTION
          "This MIB object sets enable/disable of RTCP static interval via SNMP."
    DEFVAL { disable }
    ::= { arrisMtaDevControl 11 }

--
-- The following group describes the Monitoring MIB trace objects
-- in the Arris MTA device.
--

arrisMtaDevRtpTxPktsTotal OBJECT-TYPE
    SYNTAX      Integer32
    MAX-ACCESS  read-only
    STATUS      current
    DESCRIPTION
          "This MIB object reports the total number of RTP packets sent from the MTA
           since it was last started up or reset.  This value represents the total
           number of packets sent for all endpoints combined.  It is calculated from
           values obtained from the signaling end of call statistics.  Setting the MIB
           object arrisMtaDevResetCallStats to a value of true(1) will clear this
           counter."
    ::= { arrisMtaDevTrace 1 }

arrisMtaDevRtpRxPktsTotal OBJECT-TYPE
    SYNTAX      Integer32
    MAX-ACCESS  read-only
    STATUS      current
    DESCRIPTION
          "This MIB object reports the total number of RTP packets received from the MTA
           since it was last started up or reset.  This value represents the total
           number of packets received for all endpoints combined.  It is calculated from
           values obtained from the signaling end of call statistics.  Setting the MIB
           object arrisMtaDevResetCallStats to a value of true(1) will clear this
           counter."
    ::= { arrisMtaDevTrace 2 }

arrisMtaDevRtpPercentPktsLostTotal OBJECT-TYPE
    SYNTAX      Integer32
    MAX-ACCESS  read-only
    STATUS      current
    DESCRIPTION
          "This MIB object reports the percentage of RTP packets lost since the MTA was
           last started up or reset.  This value represents the total number of packets
           lost for all endpoints combined.  It is calculated from values obtained from
           the signaling end of call statistics.  Setting the MIB object
           arrisMtaDevResetCallStats to a value of true(1) will clear this counter.  The
           value field for this MIB object is represented as an integer value.  However,
           the actual value is a floating point type.  For example a returned (integer)
           value of '1745' will be displayed as '1745' but the actual (floating point) value
           would be '17.45%' packets lost.  Note:  The MSO must divide the integer return
           value by 100 to calculate the percentage value."
    ::= { arrisMtaDevTrace 3 }

arrisMtaDevProvState OBJECT-TYPE
    SYNTAX INTEGER {
        dhcpBound(1),
        dnsReqProvSvrIP(2),
        kdcHostNameDnsReq(3),
        kdcHostNameDnsRply(4),
        kdcIpDnsReq(5),
        kdcIpDnsRply(6),
        asReqSent(7),
        asRplyRcvd(8),
        tgsReqSent(9),
        tgsRplyRcvd(10),
        apReqSent(11),
        apRplyRcvd(12),
        enrollmentInform(13),
        cfgUrlSet(14),
        dnsReqTftpSvrIp(15),
        cfgFileReq(16),
        rcvCfgFile(17),
        syslogMsgProvComplete(18),
        statusInform(19),
        provcomplete(20)
    }
    MAX-ACCESS  read-only
    STATUS      current
    DESCRIPTION
          "The MIB object arrisMtaDevProvState reports the current provisioning state of the MTA."
    ::= { arrisMtaDevTrace 4 }

arrisMtaDevSWUpgradeStatus OBJECT-TYPE
    SYNTAX INTEGER {
        inProgress(1),
        completeFromProvisioning(2),
        completeFromMgt(3),
        failed(4),
        other(5)
    }
    MAX-ACCESS  read-only
    STATUS      current
    DESCRIPTION
          "This MIB object reports the current software upgrade status of the device.
           This MIB object obtains its value from the MIB object docsDevSwOperStatus."
    ::= { arrisMtaDevTrace 5 }

arrisMtaDevSignalingAvgLatency OBJECT-TYPE
    SYNTAX      Integer32
    MAX-ACCESS  read-only
    STATUS      current
    DESCRIPTION
          "This MIB object reports the Average latency/delay for responses to signaling messages.
           This is measured in milliseconds.  It is calculated from values obtained from the
           signaling end of call statistics.  Setting the MIB object arrisMtaDevResetCallStats to
           a value of true(1) will clear this MIB value."
    ::= { arrisMtaDevTrace 6 }

arrisMtaDevSignalingTxSuccessfulMsgCnt OBJECT-TYPE
    SYNTAX      Integer32
    MAX-ACCESS  read-only
    STATUS      current
    DESCRIPTION
          "This MIB object reports the total number of successful signaling messages sent from the
           MTA.  Setting the MIB object arrisMtaDevResetCallStats to a value of true(1) will clear
           this counter."
    ::= { arrisMtaDevTrace 7 }

arrisMtaDevSignalingRxSuccessfulMsgCnt OBJECT-TYPE
    SYNTAX      Integer32
    MAX-ACCESS  read-only
    STATUS      current
    DESCRIPTION
          "This MIB object reports the total number of successful signaling messages received by the
           MTA.  Setting the MIB object arrisMtaDevResetCallStats to a value of true(1) will clear
           this counter."
    ::= { arrisMtaDevTrace 8 }

arrisMtaDevSignalingTxNAKCnt OBJECT-TYPE
    SYNTAX      Integer32
    MAX-ACCESS  read-only
    STATUS      current
    DESCRIPTION
          "This MIB object reports the total number of negative acknowledgement signaling
           messages (NAKmessages) sent from the MTA.  Setting the MIB object
           arrisMtaDevResetCallStats to a value of true(1) will clear this counter."
    ::= { arrisMtaDevTrace 9 }

arrisMtaDevSignalingRxNAKCnt OBJECT-TYPE
    SYNTAX      Integer32
    MAX-ACCESS  read-only
    STATUS      current
    DESCRIPTION
          "This MIB object reports the total number of negative acknowledgement signaling
           messages (NAKmessages) received by the MTA.  Setting the MIB object
           arrisMtaDevResetCallStats to a value of true(1) will clear this counter."
    ::= { arrisMtaDevTrace 10 }

arrisMtaDevSignalingRxNoACKCnt OBJECT-TYPE
    SYNTAX      Integer32
    MAX-ACCESS  read-only
    STATUS      current
    DESCRIPTION
          "This MIB object reports the total number of 'no acknowledgement' signaling messages
           received by the MTA.  Setting the MIB object arrisMtaDevResetCallStats to a value of
           true(1) will clear this counter."
    ::= { arrisMtaDevTrace 11 }

arrisMtaDevSignalingLastMsg1 OBJECT-TYPE
    SYNTAX      SnmpAdminString
    MAX-ACCESS  read-only
    STATUS      current
    DESCRIPTION
          "This MIB object displays a 255 byte segment of the Callp last signaling message sent or received.
           This MIB object is one of sixteen total MIB objects which together can display a signaling message
           as large as 4000 bytes.  If the message is too small to require all sixteen MIBs then the empty MIB
           objects will display the value 'Buffer is empty'.  This MIB object must be enabled in order to display
           messages.  The MIB object arrisMtaDevEnableCallSigLastMsgRpt is used to enable or disable reporting
           of the Callp signaling 'last message' to the MIB objects arrisMtaDevSignalingLastMsg1 through
           arrisMtaDevSignalingLastMsg16."
    ::= { arrisMtaDevTrace 12 }

arrisMtaDevSignalingLastMsg2 OBJECT-TYPE
    SYNTAX      SnmpAdminString
    MAX-ACCESS  read-only
    STATUS      current
    DESCRIPTION
          "This MIB object displays a 255 byte segment of the Callp last signaling message sent or received.
           This MIB object is one of sixteen total MIB objects which together can display a signaling message
           as large as 4000 bytes.  If the message is too small to require all sixteen MIBs then the empty MIB
           objects will display the value 'Buffer is empty'.  This MIB object must be enabled in order to display
           messages.  The MIB object arrisMtaDevEnableCallSigLastMsgRpt is used to enable or disable reporting
           of the Callp signaling 'last message' to the MIB objects arrisMtaDevSignalingLastMsg1 through
           arrisMtaDevSignalingLastMsg16."
    ::= { arrisMtaDevTrace 13 }

arrisMtaDevSignalingLastMsg3 OBJECT-TYPE
    SYNTAX      SnmpAdminString
    MAX-ACCESS  read-only
    STATUS      current
    DESCRIPTION
          "This MIB object displays a 255 byte segment of the Callp last signaling message sent or received.
           This MIB object is one of sixteen total MIB objects which together can display a signaling message
           as large as 4000 bytes.  If the message is too small to require all sixteen MIBs then the empty MIB
           objects will display the value 'Buffer is empty'.  This MIB object must be enabled in order to display
           messages.  The MIB object arrisMtaDevEnableCallSigLastMsgRpt is used to enable or disable reporting
           of the Callp signaling 'last message' to the MIB objects arrisMtaDevSignalingLastMsg1 through
           arrisMtaDevSignalingLastMsg16."
    ::= { arrisMtaDevTrace 14 }

arrisMtaDevSignalingLastMsg4 OBJECT-TYPE
    SYNTAX      SnmpAdminString
    MAX-ACCESS  read-only
    STATUS      current
    DESCRIPTION
          "This MIB object displays a 255 byte segment of the Callp last signaling message sent or received.
           This MIB object is one of sixteen total MIB objects which together can display a signaling message
           as large as 4000 bytes.  If the message is too small to require all sixteen MIBs then the empty MIB
           objects will display the value 'Buffer is empty'.  This MIB object must be enabled in order to display
           messages.  The MIB object arrisMtaDevEnableCallSigLastMsgRpt is used to enable or disable reporting
           of the Callp signaling 'last message' to the MIB objects arrisMtaDevSignalingLastMsg1 through
           arrisMtaDevSignalingLastMsg16."
    ::= { arrisMtaDevTrace 15 }

arrisMtaDevSignalingLastMsg5 OBJECT-TYPE
    SYNTAX      SnmpAdminString
    MAX-ACCESS  read-only
    STATUS      current
    DESCRIPTION
          "This MIB object displays a 255 byte segment of the Callp last signaling message sent or received.
           This MIB object is one of sixteen total MIB objects which together can display a signaling message
           as large as 4000 bytes.  If the message is too small to require all sixteen MIBs then the empty MIB
           objects will display the value 'Buffer is empty'.  This MIB object must be enabled in order to display
           messages.  The MIB object arrisMtaDevEnableCallSigLastMsgRpt is used to enable or disable reporting
           of the Callp signaling 'last message' to the MIB objects arrisMtaDevSignalingLastMsg1 through
           arrisMtaDevSignalingLastMsg16."
     ::= { arrisMtaDevTrace 16 }

arrisMtaDevSignalingLastMsg6 OBJECT-TYPE
    SYNTAX      SnmpAdminString
    MAX-ACCESS  read-only
    STATUS      current
    DESCRIPTION
          "This MIB object displays a 255 byte segment of the Callp last signaling message sent or received.
           This MIB object is one of sixteen total MIB objects which together can display a signaling message
           as large as 4000 bytes.  If the message is too small to require all sixteen MIBs then the empty MIB
           objects will display the value 'Buffer is empty'.  This MIB object must be enabled in order to display
           messages.  The MIB object arrisMtaDevEnableCallSigLastMsgRpt is used to enable or disable reporting
           of the Callp signaling 'last message' to the MIB objects arrisMtaDevSignalingLastMsg1 through
           arrisMtaDevSignalingLastMsg16."
    ::= { arrisMtaDevTrace 17 }

arrisMtaDevSignalingLastMsg7 OBJECT-TYPE
    SYNTAX      SnmpAdminString
    MAX-ACCESS  read-only
    STATUS      current
    DESCRIPTION
          "This MIB object displays a 255 byte segment of the Callp last signaling message sent or received.
           This MIB object is one of sixteen total MIB objects which together can display a signaling message
           as large as 4000 bytes.  If the message is too small to require all sixteen MIBs then the empty MIB
           objects will display the value 'Buffer is empty'.  This MIB object must be enabled in order to display
           messages.  The MIB object arrisMtaDevEnableCallSigLastMsgRpt is used to enable or disable reporting
           of the Callp signaling 'last message' to the MIB objects arrisMtaDevSignalingLastMsg1 through
           arrisMtaDevSignalingLastMsg16."
    ::= { arrisMtaDevTrace 18 }

arrisMtaDevSignalingLastMsg8 OBJECT-TYPE
    SYNTAX      SnmpAdminString
    MAX-ACCESS  read-only
    STATUS      current
    DESCRIPTION
          "This MIB object displays a 255 byte segment of the Callp last signaling message sent or received.
           This MIB object is one of sixteen total MIB objects which together can display a signaling message
           as large as 4000 bytes.  If the message is too small to require all sixteen MIBs then the empty MIB
           objects will display the value 'Buffer is empty'.  This MIB object must be enabled in order to display
           messages.  The MIB object arrisMtaDevEnableCallSigLastMsgRpt is used to enable or disable reporting
           of the Callp signaling 'last message' to the MIB objects arrisMtaDevSignalingLastMsg1 through
           arrisMtaDevSignalingLastMsg16."
    ::= { arrisMtaDevTrace 19 }

arrisMtaDevSignalingLastMsg9 OBJECT-TYPE
    SYNTAX      SnmpAdminString
    MAX-ACCESS  read-only
    STATUS      current
    DESCRIPTION
          "This MIB object displays a 255 byte segment of the Callp last signaling message sent or received.
           This MIB object is one of sixteen total MIB objects which together can display a signaling message
           as large as 4000 bytes.  If the message is too small to require all sixteen MIBs then the empty MIB
           objects will display the value 'Buffer is empty'.  This MIB object must be enabled in order to display
           messages.  The MIB object arrisMtaDevEnableCallSigLastMsgRpt is used to enable or disable reporting
           of the Callp signaling 'last message' to the MIB objects arrisMtaDevSignalingLastMsg1 through
           arrisMtaDevSignalingLastMsg16."
    ::= { arrisMtaDevTrace 20 }

arrisMtaDevSignalingLastMsg10 OBJECT-TYPE
    SYNTAX      SnmpAdminString
    MAX-ACCESS  read-only
    STATUS      current
    DESCRIPTION
          "This MIB object displays a 255 byte segment of the Callp last signaling message sent or received.
           This MIB object is one of sixteen total MIB objects which together can display a signaling message
           as large as 4000 bytes.  If the message is too small to require all sixteen MIBs then the empty MIB
           objects will display the value 'Buffer is empty'.  This MIB object must be enabled in order to display
           messages.  The MIB object arrisMtaDevEnableCallSigLastMsgRpt is used to enable or disable reporting
           of the Callp signaling 'last message' to the MIB objects arrisMtaDevSignalingLastMsg1 through
           arrisMtaDevSignalingLastMsg16."
    ::= { arrisMtaDevTrace 21 }

arrisMtaDevSignalingLastMsg11 OBJECT-TYPE
    SYNTAX      SnmpAdminString
    MAX-ACCESS  read-only
    STATUS      current
    DESCRIPTION
          "This MIB object displays a 255 byte segment of the Callp last signaling message sent or received.
           This MIB object is one of sixteen total MIB objects which together can display a signaling message
           as large as 4000 bytes.  If the message is too small to require all sixteen MIBs then the empty MIB
           objects will display the value 'Buffer is empty'.  This MIB object must be enabled in order to display
           messages.  The MIB object arrisMtaDevEnableCallSigLastMsgRpt is used to enable or disable reporting
           of the Callp signaling 'last message' to the MIB objects arrisMtaDevSignalingLastMsg1 through
           arrisMtaDevSignalingLastMsg16."
    ::= { arrisMtaDevTrace 22 }

arrisMtaDevSignalingLastMsg12 OBJECT-TYPE
    SYNTAX      SnmpAdminString
    MAX-ACCESS  read-only
    STATUS      current
    DESCRIPTION
          "This MIB object displays a 255 byte segment of the Callp last signaling message sent or received.
           This MIB object is one of sixteen total MIB objects which together can display a signaling message
           as large as 4000 bytes.  If the message is too small to require all sixteen MIBs then the empty MIB
           objects will display the value 'Buffer is empty'.  This MIB object must be enabled in order to display
           messages.  The MIB object arrisMtaDevEnableCallSigLastMsgRpt is used to enable or disable reporting
           of the Callp signaling 'last message' to the MIB objects arrisMtaDevSignalingLastMsg1 through
           arrisMtaDevSignalingLastMsg16."
    ::= { arrisMtaDevTrace 23 }

arrisMtaDevSignalingLastMsg13 OBJECT-TYPE
    SYNTAX      SnmpAdminString
    MAX-ACCESS  read-only
    STATUS      current
    DESCRIPTION
          "This MIB object displays a 255 byte segment of the Callp last signaling message sent or received.
           This MIB object is one of sixteen total MIB objects which together can display a signaling message
           as large as 4000 bytes.  If the message is too small to require all sixteen MIBs then the empty MIB
           objects will display the value 'Buffer is empty'.  This MIB object must be enabled in order to display
           messages.  The MIB object arrisMtaDevEnableCallSigLastMsgRpt is used to enable or disable reporting
           of the Callp signaling 'last message' to the MIB objects arrisMtaDevSignalingLastMsg1 through
           arrisMtaDevSignalingLastMsg16."
    ::= { arrisMtaDevTrace 24 }

arrisMtaDevSignalingLastMsg14 OBJECT-TYPE
    SYNTAX      SnmpAdminString
    MAX-ACCESS  read-only
    STATUS      current
    DESCRIPTION
          "This MIB object displays a 255 byte segment of the Callp last signaling message sent or received.
           This MIB object is one of sixteen total MIB objects which together can display a signaling message
           as large as 4000 bytes.  If the message is too small to require all sixteen MIBs then the empty MIB
           objects will display the value 'Buffer is empty'.  This MIB object must be enabled in order to display
           messages.  The MIB object arrisMtaDevEnableCallSigLastMsgRpt is used to enable or disable reporting
           of the Callp signaling 'last message' to the MIB objects arrisMtaDevSignalingLastMsg1 through
           arrisMtaDevSignalingLastMsg16."
    ::= { arrisMtaDevTrace 25 }

arrisMtaDevSignalingLastMsg15 OBJECT-TYPE
    SYNTAX      SnmpAdminString
    MAX-ACCESS  read-only
    STATUS      current
    DESCRIPTION
          "This MIB object displays a 255 byte segment of the Callp last signaling message sent or received.
           This MIB object is one of sixteen total MIB objects which together can display a signaling message
           as large as 4000 bytes.  If the message is too small to require all sixteen MIBs then the empty MIB
           objects will display the value 'Buffer is empty'.  This MIB object must be enabled in order to display
           messages.  The MIB object arrisMtaDevEnableCallSigLastMsgRpt is used to enable or disable reporting
           of the Callp signaling 'last message' to the MIB objects arrisMtaDevSignalingLastMsg1 through
           arrisMtaDevSignalingLastMsg16."
    ::= { arrisMtaDevTrace 26 }

arrisMtaDevSignalingLastMsg16 OBJECT-TYPE
    SYNTAX      SnmpAdminString
    MAX-ACCESS  read-only
    STATUS      current
    DESCRIPTION
          "This MIB object displays a 255 byte segment of the Callp last signaling message sent or received.
           This MIB object is one of sixteen total MIB objects which together can display a signaling message
           as large as 4000 bytes.  If the message is too small to require all sixteen MIBs then the empty MIB
           objects will display the value 'Buffer is empty'.  This MIB object must be enabled in order to display
           messages.  The MIB object arrisMtaDevEnableCallSigLastMsgRpt is used to enable or disable reporting
           of the Callp signaling 'last message' to the MIB objects arrisMtaDevSignalingLastMsg1 through
           arrisMtaDevSignalingLastMsg16."
    ::= { arrisMtaDevTrace 27 }

arrisMtaDevEstimatedMinutesRemaining OBJECT-TYPE
    SYNTAX     INTEGER
    UNITS      "minutes"
    MAX-ACCESS read-only
    STATUS     current
    DESCRIPTION
            "An estimate of the time to battery charge depletion
            under the present load conditions if the utility power
            is off and remains off, or if it were to be lost and
            remain off.  A value of -1 indicates the information
            is unavailable at this time."
    ::= { arrisMtaDevTrace 44 }

arrisMtaDevEstimatedChargeRemaining OBJECT-TYPE
    SYNTAX     INTEGER
    UNITS      "percent"
    MAX-ACCESS read-only
    STATUS     current
    DESCRIPTION
            "An estimate of the battery charge remaining expressed
            as a percent of full charge.  A value of -1 indicates
            the information is unavailable at this time."
    ::= { arrisMtaDevTrace 45 }

--
-- The following group describes the Monitoring MIB Call Stats Table objects
-- in the Arris MTA device.
--

arrisMtaDevCallStatsTable OBJECT-TYPE
    SYNTAX SEQUENCE OF ArrisMtaDevCallStatsEntry
    MAX-ACCESS not-accessible
    STATUS current
    DESCRIPTION
        "This table reports various end of call statistics."
    ::= { arrisMtaDevTrace 46 }

arrisMtaDevCallStatsEntry OBJECT-TYPE
    SYNTAX ArrisMtaDevCallStatsEntry
    MAX-ACCESS not-accessible
    STATUS current
    DESCRIPTION
        "Each end point entry represents one telephone line"
    INDEX { arrisMtaDevCallStatsIndex }
    ::= { arrisMtaDevCallStatsTable 1 }

ArrisMtaDevCallStatsEntry ::= SEQUENCE {
    arrisMtaDevCallStatsIndex Integer32,
    arrisMtaDevCallStatsRtpTxPkts Integer32,
    arrisMtaDevCallStatsRtpRxPkts Integer32,
    arrisMtaDevCallStatsRtpPercentPktsLost Integer32,
    arrisMtaDevCallStatsAvgJitter Integer32,
    arrisMtaDevCallStatsMaxJitter Integer32,
    arrisMtaDevCallStatsAvgLatency Integer32,
    arrisMtaDevCallStatsHookStatus INTEGER,
    arrisMtaDevCallStatsSLICStatus INTEGER,
    arrisMtaDevCallStatsEndPntOpStatus INTEGER,
    arrisMtaDevCallStatsLineSubState BITS
}

arrisMtaDevCallStatsIndex OBJECT-TYPE
    SYNTAX Integer32
    MAX-ACCESS not-accessible
    STATUS current
    DESCRIPTION "The unique value which identifies the endpoint."
    ::= { arrisMtaDevCallStatsEntry 1 }

arrisMtaDevCallStatsRtpTxPkts OBJECT-TYPE
    SYNTAX      Integer32
    MAX-ACCESS  read-only
    STATUS      current
    DESCRIPTION
          "This MIB object reports the total number of RTP packets sent from
           the MTA during the most recent call.  This MIB object is included
           in a table of MIB objects which indexed by the endpoint (line number).
           Its value represents the total number of packets sent per endpoint.
           This value is obtained from the signaling end of call statistics."
    ::= { arrisMtaDevCallStatsEntry 2 }

arrisMtaDevCallStatsRtpRxPkts OBJECT-TYPE
    SYNTAX      Integer32
    MAX-ACCESS  read-only
    STATUS      current
    DESCRIPTION
          "This MIB object reports the total number of RTP packets received by
           the MTA during the most recent call.  This MIB object is included
           in a table of MIB objects which indexed by the endpoint (line number).
           Its value represents the total number of packets received per endpoint.
           This value is obtained from the signaling end of call statistics."
    ::= { arrisMtaDevCallStatsEntry 3 }

arrisMtaDevCallStatsRtpPercentPktsLost OBJECT-TYPE
    SYNTAX      Integer32
    MAX-ACCESS  read-only
    STATUS      current
    DESCRIPTION
          "This MIB object reports the percentage of RTP packets lost during the most
           recent call.  This MIB object is included in a table of MIB objects which
           indexed by the endpoint (line number).  Its value represents the total number
           of packets lost per endpoint.  It is calculated from values obtained from the
           signaling end of call statistics.  The value field for this MIB object is
           represented as an integer value.  However, the actual value is a floating point
           type.  For example A returned (integer) value of '1745' will be displayed as
           '1745' but the actual (floating point) value would be '17.45%' packets lost.
           Note:  The MSO must divide the integer return value by 100 to calculate the
           percentage value."
    ::= { arrisMtaDevCallStatsEntry 4 }

arrisMtaDevCallStatsAvgJitter OBJECT-TYPE
    SYNTAX      Integer32
    MAX-ACCESS  read-only
    STATUS      current
    DESCRIPTION
          "This MIB object reports the average jitter measurement during the most recent call.
           This MIB object is included in a table of MIB objects which indexed by the endpoint
           (line number).  Its value represents the average jitter measurement per endpoint.
           This value is measured in units of milliseconds.  This value is obtained from the
           signaling end of call statistics."
    ::= { arrisMtaDevCallStatsEntry 5 }

arrisMtaDevCallStatsMaxJitter OBJECT-TYPE
    SYNTAX      Integer32
    MAX-ACCESS  read-only
    STATUS      current
    DESCRIPTION
          "This MIB object reports the maximum jitter measurement during the most recent call.
           This MIB object is included in a table of MIB objects which indexed by the endpoint
           (line number).  Its value represents the maximum jitter measurement per endpoint.
           This value is measured in units of milliseconds.  This value is obtained from DSP
           statistics."
    ::= { arrisMtaDevCallStatsEntry 6 }

arrisMtaDevCallStatsAvgLatency OBJECT-TYPE
    SYNTAX      Integer32
    MAX-ACCESS  read-only
    STATUS      current
    DESCRIPTION
          "This MIB object reports the average latency observed during the most recent call.
           This MIB object is included in a table of MIB objects which indexed by the endpoint
           (line number).  This value is measured in units of milliseconds.  This value is
           obtained from the signaling end of call statistics."
    ::= { arrisMtaDevCallStatsEntry 7 }

arrisMtaDevCallStatsHookStatus OBJECT-TYPE
    SYNTAX  INTEGER {
        onHook(0),
        offHook(1)
    }
    MAX-ACCESS  read-only
    STATUS      current
    DESCRIPTION
          "This MIB object reports the hook status for each endpoint.
           Note:  The disconnected state is not a valid return value for this MIB object."
    ::= { arrisMtaDevCallStatsEntry 9 }

arrisMtaDevCallStatsSLICStatus OBJECT-TYPE
    SYNTAX  INTEGER {
        normal(0),
        overtemp(1)
    }
    MAX-ACCESS  read-only
    STATUS      current
    DESCRIPTION
          "This MIB object reports the over temperature condition of the SLIC chips."
    ::= { arrisMtaDevCallStatsEntry 10 }

arrisMtaDevCallStatsEndPntOpStatus OBJECT-TYPE
    SYNTAX  INTEGER {
        up(1),       -- ready to pass packets
        down(2),
        testing(3)   -- in some test mode
    }
    MAX-ACCESS  read-only
    STATUS      current
    DESCRIPTION
          "This MIB object reports the current operational status for each endpoint.
           This MIB object obtains its value from the MIB object ifAdminOperStatus."
    ::= { arrisMtaDevCallStatsEntry 11 }

arrisMtaDevCallStatsLineSubState OBJECT-TYPE
    SYNTAX BITS {
        normal(0),
        diagsPending(1),
        diagsFailed(2),
        lcProtection(3),
        dspFail(4)
    }
    MAX-ACCESS read-only
    STATUS current
    DESCRIPTION
          "This MIB object reports the current sub state for each line.
           This MIB object obtains its value from the lineRec."
    ::= { arrisMtaDevCallStatsEntry 12 }

arrisMtaDevRtpPktsLostTotal OBJECT-TYPE
    SYNTAX      Integer32
    MAX-ACCESS  read-only
    STATUS      current
    DESCRIPTION
          "This MIB object reports the RTP packets lost since the MTA was
           last started up or reset.  This value represents the total number of packets
           lost for all endpoints combined.  It is calculated from values obtained from
           the signaling end of call statistics.  Setting the MIB object
           arrisMtaDevResetCallStats to a value of true(1) will clear this counter."
    ::= { arrisMtaDevTrace 47 }

arrisMtaDevLastCallStartTime OBJECT-TYPE
    SYNTAX	DateAndTime
    MAX-ACCESS read-only
    STATUS current
    DESCRIPTION
          "This MIB object reports the last call start time from the eMTA. "
    ::= { arrisMtaDevTrace 48 }

arrisMtaDevLastCallEndTime OBJECT-TYPE
    SYNTAX	DateAndTime
    MAX-ACCESS read-only
    STATUS current
    DESCRIPTION
          "This MIB object reports the last call end time from the eMTA. "
    ::= { arrisMtaDevTrace 49 }

--
-- The following group describes Voice Quality Monitoring objects
-- in the Arris MTA device.
--

arrisMtaDevVqmLine OBJECT-TYPE
     SYNTAX Integer32
     MAX-ACCESS read-write
     STATUS current
     DESCRIPTION
         "Specifies the line for Voice Quality Metrics reporting."
     DEFVAL { 1 }
     ::= { arrisMtaDevVqm 1 }


arrisMtaDevVqmClear OBJECT-TYPE
     SYNTAX INTEGER {
         single-line(0),
         all-lines(1)
     }
     MAX-ACCESS read-write
     STATUS current
     DESCRIPTION
         "Clears Voice Quality Metrics for a single line or for all lines.
          Line number is specified using arrisMtaDevVqmLine."
     DEFVAL { single-line }
     ::= { arrisMtaDevVqm 2 }


arrisMtaDevVqmEnable OBJECT-TYPE
     SYNTAX INTEGER {
         disable(0),
         enable(1)
     }
     MAX-ACCESS read-write
     STATUS current
     DESCRIPTION
         "Enables/Disables recording Local Voice Metrics."
     DEFVAL { enable }
     ::= { arrisMtaDevVqm 3 }


arrisMtaDevVqmCallNumberTable OBJECT-TYPE
     SYNTAX SEQUENCE OF ArrisMtaDevVqmCallNumberEntry
     MAX-ACCESS not-accessible
     STATUS current
     DESCRIPTION
         "Voice Quality Metric history on a per call number basis.  This table
          provides call number history identifiers that can be entered into
          arrisMtaDevVqmIdent to provide statistics for a particular call number."
     ::= { arrisMtaDevVqm 4 }


arrisMtaDevVqmCallNumberEntry OBJECT-TYPE
     SYNTAX ArrisMtaDevVqmCallNumberEntry
     MAX-ACCESS not-accessible
     STATUS current
     DESCRIPTION
         "Voice Quality Metric history on a per call number basis."
     INDEX { arrisMtaDevVqmCallNumberIndex }
     ::= { arrisMtaDevVqmCallNumberTable 1 }


ArrisMtaDevVqmCallNumberEntry ::= SEQUENCE {
     arrisMtaDevVqmCallNumberIndex Integer32,
     arrisMtaDevVqmCallNumberIds DisplayString }


arrisMtaDevVqmCallNumberIndex OBJECT-TYPE
     SYNTAX Integer32
     MAX-ACCESS not-accessible
     STATUS current
     DESCRIPTION "A unique value which identifies the call number."
     ::= { arrisMtaDevVqmCallNumberEntry 1 }


arrisMtaDevVqmCallNumberIds OBJECT-TYPE
     SYNTAX DisplayString
     MAX-ACCESS read-only
     STATUS current
     DESCRIPTION
          "This displays a history of Call number identifiers for the specified line."
     ::= { arrisMtaDevVqmCallNumberEntry 2 }




arrisMtaDevVqmCallNumberIdentifier OBJECT-TYPE
     SYNTAX Integer32
     MAX-ACCESS read-write
     STATUS current
     DESCRIPTION
         "Specifies the call number for Voice Quality Metrics reporting.  Valid Ids
          to be entered here are obtained from arrisMtaDevVqmCallNumberIds."
     DEFVAL { 1 }
     ::= { arrisMtaDevVqm 5 }


arrisMtaDevVqmMetricTable OBJECT-TYPE
     SYNTAX SEQUENCE OF ArrisMtaDevVqmMetricEntry
     MAX-ACCESS not-accessible
     STATUS current
     DESCRIPTION
         "Voice Quality Metrics pertaining to a particular call number."
     ::= { arrisMtaDevVqm 6 }


arrisMtaDevVqmEnableRemote OBJECT-TYPE
     SYNTAX INTEGER {
         normal(0),
         forceDisable(1),
         forceEnable(2),
         default(3)
     }
     MAX-ACCESS read-write
     STATUS current
     DESCRIPTION
         "Determines policy to control Remote Voice Metrics (XR). The value of
          this MIB is persistent if it is set after configuration.
          When set to 'default', the value is restored to the default value, and it
          is no longer persistent.
            forceDisable - disables XR.  Overrides directive from Call Server.
            forceEnable - enables XR.  Overrides directive from Call Server.
            normal - has no effect.  Call Server Directives are obeyed.
            default - use the default value. The MIB is reset to the default value,
                      and the corresponding value in NVM is cleared."
     DEFVAL { normal }
     ::= { arrisMtaDevVqm 7 }


arrisMtaDevVqmThresholdEnable OBJECT-TYPE
     SYNTAX Integer32
     MAX-ACCESS read-write
     STATUS current
     DESCRIPTION
         "Zero Disables threshold reporting for Voice Metrics. Non-zero specifies the
          maximum number of logs allowed to be sent to report when a threshold is
          exceeded.  The more logs that are allowed, the more metrics that can be
          reported.  Metrics are reported in the order specified in
          arrisMtaDevVqmMetricIndex.  To minimize network traffic, logs are sent only
          when a threshold is first exceeded. Thereafter until the metric returns to
          normal, logs are inhibited.  To change this operation to send logs each
          time the threshold is exceeded, add 100 to the MIB value. "
     DEFVAL { 0 }
     ::= { arrisMtaDevVqm 8 }

arrisMtaDevVqmHistorySize OBJECT-TYPE
     SYNTAX Integer32 (2..50)
     MAX-ACCESS read-write
     STATUS current
     DESCRIPTION
         "The history size of Vqm record. Range 2 to 50."
     DEFVAL { 10 }
     ::= { arrisMtaDevVqm 9 }

arrisMtaDevVqmCallNumberIdentifierLastCall OBJECT-TYPE
     SYNTAX Integer32
     MAX-ACCESS read-only
     STATUS current
     DESCRIPTION
         "The last call identifier for Voice Quality Metrics reporting."
     ::= { arrisMtaDevVqm 10 }

arrisMtaDevVqmMetricEntry OBJECT-TYPE
     SYNTAX ArrisMtaDevVqmMetricEntry
     MAX-ACCESS not-accessible
     STATUS current
     DESCRIPTION
         "Voice Quality Metrics pertaining to a particular call number."
     INDEX { arrisMtaDevVqmMetricIndex }
     ::= { arrisMtaDevVqmMetricTable 1 }


ArrisMtaDevVqmMetricEntry ::= SEQUENCE {
     arrisMtaDevVqmMetricIndex  INTEGER,
     arrisMtaDevVqmMetricValues DisplayString,
     arrisMtaDevVqmThresholds   DisplayString }


-- When metrics are added/deleted make sure the values VQMETRIC_COMMON_MAX,
-- VQMETRIC_LOCAL_MAX & VQMETRIC_REMOTE_MAX are updated in callp_vqmon.h
--
arrisMtaDevVqmMetricIndex OBJECT-TYPE
     SYNTAX INTEGER {
-- Common Metrics
         callEndTime(1),
         callStartTime(2),
         callDuration(3),
         lineNumber(4),
         remIpAddress(5),
         cwErrors(6),
         cwErrorRate(7),
         dsSNR(8),
         microReflections(9),
         dsPwr(10),
         usPwr(11),
         eqiAverage(12),
         eqiMin(13),
         eqiMax(14),
         eqiInstantaneous(15),
-- Local Metrics
         mOS-LQ(16),
         mOS-CQ(17),
         rERL(18),
         signalLevel(19),
         noiseLevel(20),
         lossRate(21),
         plConcealment(22),
         discardRate(23),
         burstDensity(24),
         gapDensity(25),
         burstDuration(26),
         gapDuration(27),
         rTDelay(28),
         endSystemDelay(29),
         minGapSize(30),
         rFactor(31),
         extRFactor(32),
         jbAdaptive(33),
         jbRate(34),
         jBNomDelay(35),
         jBMaxDelay(36),
         jBAbsMaxDelay(37),
-- Remote Metrics
         mOS-LQRem(38),
         mOS-CQRem(39),
         rERLRem(40),
         signalLevelRem(41),
         noiseLevelRem(42),
         lossRateRem(43),
         plConcealmentRem(44),
         discardRateRem(45),
         burstDensityRem(46),
         gapDensityRem(47),
         burstDurationRem(48),
         gapDurationRem(49),
         rTDelayRem(50),
         endSystemDelayRem(51),
         minGapSizeRem(52),
         rFactorRem(53),
         extRFactorRem(54),
         jbAdaptiveRem(55),
         jbRateRem(56),
         jBNomDelayRem(57),
         jBMaxDelayRem(58),
         jBAbsMaxDelayRem(59),
-- New Local Metrcs
         txPackets(60),
         txOctets(61),
         rxPackets(62),
         rxOctets(63),
         packetLoss(64),
         intervalJitter(65),
         originator(66),
         intervalJitterRem(67),
         txcodec(68),
         rxcodec(69)
     }
     MAX-ACCESS not-accessible
     STATUS current
     DESCRIPTION "A unique value which identifies the metric."
     ::= { arrisMtaDevVqmMetricEntry 1 }


arrisMtaDevVqmMetricValues OBJECT-TYPE
     SYNTAX DisplayString
     MAX-ACCESS read-only
     STATUS current
     DESCRIPTION
          "This displays metrics for the specified call number."
     ::= { arrisMtaDevVqmMetricEntry 2 }


arrisMtaDevVqmThresholds OBJECT-TYPE
     SYNTAX DisplayString
     MAX-ACCESS read-write
     STATUS current
     DESCRIPTION
          "Sets/displays metric thresholds."
     ::= { arrisMtaDevVqmMetricEntry 3 }




--    The follow MIB OID is used on Dev0 and should be reserved
--    ::= { arrisMtaDevCallStatsEntry 12 }

-- The following group describes the Monitoring MIB parameter objects
-- on the Arris MTA device.
--

arrisMtaDevMaxCpeAllowed OBJECT-TYPE
    SYNTAX      Integer32
    MAX-ACCESS  read-only
    STATUS      current
    DESCRIPTION
          "This MIB object reflects the 'MaxCpeAllowed' parameter in the CM config file."
     ::= { arrisMtaDevParameters 1 }

arrisMtaDevNetworkAccess OBJECT-TYPE
    SYNTAX  INTEGER {
        no(0),
        yes(1)
    }
    MAX-ACCESS  read-only
    STATUS      current
    DESCRIPTION
          "This MIB object reflects the value of the 'NetworkAccess' parameter set in the CM config file."
    ::= { arrisMtaDevParameters 2 }

--
-- The following group describes the Monitoring MIB Line Parameter Table objects
-- on the Arris MTA device.
--

 arrisMtaDevLineParameterTable OBJECT-TYPE
    SYNTAX SEQUENCE OF ArrisMtaDevLineParameterEntry
    MAX-ACCESS not-accessible
    STATUS current
    DESCRIPTION
        "This table reports various line parameters on the eMTA."
    ::= { arrisMtaDevParameters 3 }

 arrisMtaDevLineParameterEntry OBJECT-TYPE
    SYNTAX ArrisMtaDevLineParameterEntry
    MAX-ACCESS not-accessible
    STATUS current
    DESCRIPTION
        "Each end point entry represents one telephone line"
    INDEX { arrisMtaDevInterfaceIndex }
    ::= { arrisMtaDevLineParameterTable 1 }

 ArrisMtaDevLineParameterEntry ::= SEQUENCE {
    arrisMtaDevInterfaceIndex Integer32,
    arrisMtaDevPktcDevEvEndpointName SnmpAdminString,
    arrisMtaDevActiveConnections Integer32,
    arrisMtaDevLineMWIActive TruthValue
    }

 arrisMtaDevInterfaceIndex OBJECT-TYPE
    SYNTAX      Integer32
    MAX-ACCESS  read-only
    STATUS      current
    DESCRIPTION
          "This MIB object shows the corresponding ifTable ifindex object for a particular line."
     ::= { arrisMtaDevLineParameterEntry 1 }

 arrisMtaDevPktcDevEvEndpointName OBJECT-TYPE
    SYNTAX      SnmpAdminString
    MAX-ACCESS  read-only
    STATUS      current
    DESCRIPTION
          "This MIB object provides the endpoint name in the following format: 'AALN/X:FQDN/IP Address'."
     ::= { arrisMtaDevLineParameterEntry 2 }

 arrisMtaDevActiveConnections OBJECT-TYPE
    SYNTAX      Integer32
    MAX-ACCESS  read-only
    STATUS      current
    DESCRIPTION
          "This MIB object shows the number of connections for a particular line whose mode is receive only, send only, send/receive, but not inactive."
     ::= { arrisMtaDevLineParameterEntry 3 }

 arrisMtaDevLineMWIActive OBJECT-TYPE
    SYNTAX      TruthValue
    MAX-ACCESS  read-only
    STATUS      current
    DESCRIPTION
          "This MIB object shows the MWI is active or not."
     ::= { arrisMtaDevLineParameterEntry 4 }

--
-- The following group describes the Monitoring MIB Upstream Service Flow Parameter Table objects
-- in the Arris MTA device.
--

 arrisMtaDevUpSvcFlowParameterTable OBJECT-TYPE
    SYNTAX SEQUENCE OF ArrisMtaDevUpSvcFlowParameterEntry
    MAX-ACCESS not-accessible
    STATUS current
    DESCRIPTION
        "This table reports various Upstream Service Flow parameters on the eMTA."
    ::= { arrisMtaDevParameters 4 }

 arrisMtaDevUpSvcFlowParameterEntry OBJECT-TYPE
    SYNTAX ArrisMtaDevUpSvcFlowParameterEntry
    MAX-ACCESS not-accessible
    STATUS current
    DESCRIPTION
        "Each end point entry represents one upstream service flow index"
    INDEX { arrisMtaDevDocsQosParamUpSvcFlowSFID }
    ::= { arrisMtaDevUpSvcFlowParameterTable 1 }

 ArrisMtaDevUpSvcFlowParameterEntry ::= SEQUENCE {
    arrisMtaDevDocsQosParamUpSvcFlowSFID Integer32,
    arrisMtaDevDocsQosParamUpSvcFlowSchedulingType Integer32
    }

 arrisMtaDevDocsQosParamUpSvcFlowSFID OBJECT-TYPE
    SYNTAX      Integer32
    MAX-ACCESS  read-only
    STATUS      current
    DESCRIPTION
          "This MIB object shows the corresponding upstream service flow SFID for a valid service flow index."
     ::= { arrisMtaDevUpSvcFlowParameterEntry 1 }

 arrisMtaDevDocsQosParamUpSvcFlowSchedulingType OBJECT-TYPE
    SYNTAX      Integer32
    MAX-ACCESS  read-only
    STATUS      current
    DESCRIPTION
          "This MIB object shows the corresponding upstream service flow scheduling type for a valid service flow index."
     ::= { arrisMtaDevUpSvcFlowParameterEntry 2 }


arrisMtaDevQosMode OBJECT-TYPE
    SYNTAX  INTEGER {
        dsxMode (1),
        bestEffort-FullDQos-PCMM (0)
    }
    MAX-ACCESS  read-only
    STATUS      current
    DESCRIPTION
          "This MIB object reflects the CPFS_DSX_DQOS bit of the Callp Feature Switch setting."
     ::= { arrisMtaDevParameters 5 }

arrisMtaDevEventFormat OBJECT-TYPE
    SYNTAX  INTEGER {
        pktc10 (0),
        pktc15 (1)
    }
    MAX-ACCESS  read-only
    STATUS      current
    DESCRIPTION
          "This object is used to determine which packet cable event format we are using:
           pktc10(0): pktc 1.0 event,
           pktc15(1): pktc 1.5 event."
     ::= { arrisMtaDevParameters 6 }

--
-- The following group describes the Dhcp parameters objects
-- in the Arris MTA device.
--

arrisMtaDevDhcpMtaParameters        OBJECT IDENTIFIER ::= { arrisMtaDevDhcp 1 }
arrisMtaDevDhcpSvrParameters        OBJECT IDENTIFIER ::= { arrisMtaDevDhcp 2 }
arrisMtaDevDhcpLeaseParameters      OBJECT IDENTIFIER ::= { arrisMtaDevDhcp 3 }
arrisMtaDevDhcpPktcOptParameters    OBJECT IDENTIFIER ::= { arrisMtaDevDhcp 4 }


arrisMtaDevDhcpMtaIpFQDN OBJECT-TYPE
     SYNTAX SnmpAdminString
     MAX-ACCESS read-only
     STATUS current
     DESCRIPTION
		 "This displays the currently defined MTA FQDN."
     ::= { arrisMtaDevDhcpMtaParameters 1 }

arrisMtaDevDhcpMtaIpAddr OBJECT-TYPE
     SYNTAX IpAddress
     MAX-ACCESS read-only
     STATUS current
     DESCRIPTION
		 "This displays the currently leased IP address ."
     ::= { arrisMtaDevDhcpMtaParameters 2 }

arrisMtaDevDhcpMtaSubNetMask OBJECT-TYPE
     SYNTAX IpAddress
     MAX-ACCESS read-only
     STATUS current
     DESCRIPTION
		 "This displays the current IP subnet mask in use."
     ::= { arrisMtaDevDhcpMtaParameters 3 }

arrisMtaDevDhcpMtaGatewayIpAddr OBJECT-TYPE
     SYNTAX IpAddress
     MAX-ACCESS read-only
     STATUS current
     DESCRIPTION
		 "This displays the current IP gateway address in use."
     ::= { arrisMtaDevDhcpMtaParameters 4 }

arrisMtaDevDhcpMtaConfigFile OBJECT-TYPE
     SYNTAX SnmpAdminString
     MAX-ACCESS read-only
     STATUS current
     DESCRIPTION
		 "This displays the MTA configuration file to be retrived."
     ::= { arrisMtaDevDhcpMtaParameters 5 }

arrisMtaDevDhcpState OBJECT-TYPE
     SYNTAX  INTEGER {
        idle      (0),    -- MTA is waiting to start the DHCP process.
    	discover  (1),	  -- MTA is currently trying to discover its IP address.
        selecting (2),	  -- MTA is currently trying to select its IP address.
        requesting(3),	  -- MTA is currently trying to request its IP address.
        bound     (4),	  -- IP Address is leased and no rebind/renew operation is taking place.
        renew     (5),    -- MTA is currently trying to renew its IP address.
        rebind    (6)     -- MTA is currently trying to rebind its IP address.
      }
     MAX-ACCESS read-only
     STATUS current
     DESCRIPTION
		 "This displays the current Dhcp state of the MTA."
     ::= { arrisMtaDevDhcpSvrParameters 1 }

arrisMtaDevDhcpPrimaryDhcpSvrIpAddr OBJECT-TYPE
     SYNTAX IpAddress
     MAX-ACCESS read-only
     STATUS current
     DESCRIPTION
		 "This displays the primary Dhcp server address."
     ::= { arrisMtaDevDhcpSvrParameters 2 }

arrisMtaDevDhcpSecondaryDhcpSvrIpAddr OBJECT-TYPE
     SYNTAX IpAddress
     MAX-ACCESS read-only
     STATUS current
     DESCRIPTION
		 "This displays the secondary Dhcp server address."
     ::= { arrisMtaDevDhcpSvrParameters 3 }


arrisMtaDevDhcpPrimaryDNSSvrIpAddr OBJECT-TYPE
     SYNTAX IpAddress
     MAX-ACCESS read-only
     STATUS current
     DESCRIPTION
		 "This displays the primary DNS server address."
     ::= { arrisMtaDevDhcpSvrParameters 4 }

arrisMtaDevDhcpSecondaryDNSSvrIpAddr OBJECT-TYPE
     SYNTAX IpAddress
     MAX-ACCESS read-only
     STATUS current
     DESCRIPTION
		 "This displays the secondary DNS server address."
     ::= { arrisMtaDevDhcpSvrParameters 5 }


arrisMtaDevDhcpOfferedLeaseTime OBJECT-TYPE
     SYNTAX Integer32
     MAX-ACCESS read-only
     STATUS current
     DESCRIPTION
		 "This displays the current IP Lease time expressed in seconds."
     ::= { arrisMtaDevDhcpLeaseParameters 1 }

arrisMtaDevDhcpLeaseTimeRemaining OBJECT-TYPE
     SYNTAX Integer32
     MAX-ACCESS read-only
     STATUS current
     DESCRIPTION
		 "This displays the remaining IP Lease time expressed in seconds."
     ::= { arrisMtaDevDhcpLeaseParameters 2 }

arrisMtaDevDhcpTimeUntilRenew OBJECT-TYPE
     SYNTAX Integer32
     MAX-ACCESS read-only
     STATUS current
     DESCRIPTION
		 "This displays the current time remaining before the MTA starts the lease renewal
          process.  This time is expressed in seconds."
     ::= { arrisMtaDevDhcpLeaseParameters 3 }

arrisMtaDevDhcpTimeUntilRebind OBJECT-TYPE
     SYNTAX Integer32
     MAX-ACCESS read-only
     STATUS current
     DESCRIPTION
		 "This displays the current time remaining before the MTA starts the lease rebinding
          process.  This time is expressed in seconds."
     ::= { arrisMtaDevDhcpLeaseParameters 4 }

arrisMtaDevDhcpPktcOptionId  OBJECT-TYPE
     SYNTAX INTEGER
     MAX-ACCESS read-only
     STATUS current
     DESCRIPTION
		 "This displays the Pktc DHCP Option ID of 122/177."
     ::= { arrisMtaDevDhcpPktcOptParameters 1 }

arrisMtaDevDhcpSvcProviderSnmpEntity OBJECT-TYPE
     SYNTAX SnmpAdminString
     MAX-ACCESS read-only
     STATUS current
     DESCRIPTION
		 "Current FQDN of the Service Provider's SNMP Entity."
     ::= { arrisMtaDevDhcpPktcOptParameters 2 }

arrisMtaDevDhcpKerberosRealmFqdn OBJECT-TYPE
     SYNTAX SnmpAdminString
     MAX-ACCESS read-only
     STATUS current
     DESCRIPTION
		 "FQDN of the Kerberos Realm. The PacketCable architecture requires an
		  MTA to authenticate itself to the TSP's network via the Kerberos protocol.
		  A Kerberos Realm name is required at the MTA to permit a DNS lookup for the
		  address of the TSP's Kerberos Key Distribution Center (KDC) entity."
     ::= { arrisMtaDevDhcpPktcOptParameters 3 }

arrisMtaDevDhcpRequestTgt OBJECT-TYPE
     SYNTAX SnmpAdminString
     MAX-ACCESS read-only
     STATUS current
     DESCRIPTION
		 "This sub-option encodes a boolean value which indicates whether an
   		  MTA should or should not utilize a TGT (Ticket Granting Ticket) when
   		  obtaining a service ticket for one of the PacketCable application
   		  servers.
   		    TRUE : Utilize the TGT process.
   		    FALSE: Do not utilize the TGT process."
     ::= { arrisMtaDevDhcpPktcOptParameters 4 }

arrisMtaDevDhcpProvTimer OBJECT-TYPE
     SYNTAX INTEGER
     MAX-ACCESS read-only
     STATUS current
     DESCRIPTION
		 "The provisioning timer defines the maximum time allowed for the MTA
    	  provisioning process to complete.  If this timer expires before the
      	  MTA has completed the provisioning process, the MTA should reset the
   	  	  timer and re-start its provisioning process from the beginning."
     ::= { arrisMtaDevDhcpPktcOptParameters 5 }

arrisMtaDevDhcpSecTicketInvalid OBJECT-TYPE
      SYNTAX   BITS {
        invalidateProvOnReboot (0),
        invalidateAllCmsOnReboot (1)
      }
     MAX-ACCESS read-only
     STATUS current
     DESCRIPTION
        " This object defines a Kerberos Ticket Control Mask that
          instructs the MTA to invalidate the specific application
          server Kerberos ticket(s) that are stored locally in the
          MTA NVRAM (non-volatile or persistent memory).
          If the MTA does not stored Kerberos tickets in NVRAM, it
          MUST ignore setting of this object, and MUST report a BITS
          value of zero when the object is read.
          If the MTA supports Kerberos tickets storage in NVRAM, the
          object value is encoded as follows:
          - setting the invalidateProvOnReboot bit (bit 0) to 1
            means that the MTA MUST invalidate the Kerberos
            Application Ticket(s) for the Provisioning Application
            at the next MTA reboot,
          - setting the invalidateAllCmsOnReboot bit (bit 1) to 1
            means that the MTA MUST invalidate the Kerberos
            Application Ticket(s) for all CMSes currently assigned
            to the MTA endpoints."
     ::= { arrisMtaDevDhcpPktcOptParameters 6 }

--
-- The following group describes the Power Supply Telemetry objects
-- in the Arris MTA device.
--
arrisMtaDevPwrSupplyBase    OBJECT IDENTIFIER ::= { arrisMtaDevPowerSupplyTelemetry 2 }
arrisMtaDevPwrSupplyControl OBJECT IDENTIFIER ::= { arrisMtaDevPowerSupplyTelemetry 3 }
arrisMtaDevPwrSupplyTimers  OBJECT IDENTIFIER ::= { arrisMtaDevPowerSupplyTelemetry 4 }
arrisMtaDevPwrSupplyStats   OBJECT IDENTIFIER ::= { arrisMtaDevPowerSupplyTelemetry 5 }
arrisMtaDevPwrSupplyAlarm   OBJECT IDENTIFIER ::= { arrisMtaDevPowerSupplyTelemetry 6 }

--
-- The following describes the line card tabl and entry that displays the state of the
-- line cards.  Objects are in the Arris MTA device.
--
arrisMtaDevLineCardTable OBJECT-TYPE
     SYNTAX SEQUENCE OF ArrisMtaDevLineCardEntry
     MAX-ACCESS not-accessible
     STATUS current
     DESCRIPTION
         "This table contains the state of each line card."
     ::= { arrisMtaDevLineCard 1 }

arrisMtaDevLineCardEntry OBJECT-TYPE
 SYNTAX ArrisMtaDevLineCardEntry
 MAX-ACCESS not-accessible
 STATUS current
 DESCRIPTION
  "An entry in the line card table."
 INDEX { arrisMtaDevLineCardLineNumber }
 ::= { arrisMtaDevLineCardTable 1 }

ArrisMtaDevLineCardEntry ::= SEQUENCE{
  arrisMtaDevLineCardLineNumber Integer32,   -- INDEX item
  arrisMtaDevLineCardState      INTEGER
 }

arrisMtaDevLineCardLineNumber OBJECT-TYPE
 SYNTAX Integer32
 MAX-ACCESS not-accessible
 STATUS current
 DESCRIPTION "The unique value which identifies the line card."
 ::= { arrisMtaDevLineCardEntry 1 }

arrisMtaDevLineCardState OBJECT-TYPE
 SYNTAX INTEGER {
			idle       (1),
			addressing (2),
			talking    (3),
			frwd-disc  (5),
			ringing    (6),
			onhook-tx  (7),
	     	plo        (14)
           }

 MAX-ACCESS read-only
 STATUS current
 DESCRIPTION "The line card state of the line."
 ::= { arrisMtaDevLineCardEntry 2 }

-- Ali PD 78887 END

-- PD 189252
arrisMtaDispSignalTable OBJECT-TYPE
     SYNTAX SEQUENCE OF ArrisMtaDispSignalEntry
     MAX-ACCESS not-accessible
     STATUS current
     DESCRIPTION
         "This table contains the NCS/SIP log"
     ::= { arrisMtaDispSignal 1 }

arrisMtaDispSignalEntry OBJECT-TYPE
 SYNTAX ArrisMtaDispSignalEntry
 MAX-ACCESS not-accessible
 STATUS current
 DESCRIPTION
  "An entry in the log table."
 INDEX { arrisMtaDevDispSignalLogindex }
 ::= { arrisMtaDispSignalTable 1 }

ArrisMtaDispSignalEntry ::= SEQUENCE{
  arrisMtaDevDispSignalLogindex INTEGER,
  arrisMtaDevDispSignalLog OCTET STRING
 }

arrisMtaDevDispSignalLogindex OBJECT-TYPE
 SYNTAX INTEGER (1..256)
 MAX-ACCESS not-accessible
 STATUS current
 DESCRIPTION "The index of signal log."
 ::= { arrisMtaDispSignalEntry 1 }

arrisMtaDevDispSignalLog OBJECT-TYPE
 SYNTAX OCTET STRING (SIZE (0..2048))
 MAX-ACCESS read-only
 STATUS current
 DESCRIPTION "Show the log of signal"
 ::= { arrisMtaDispSignalEntry 2 }

arrisMtadocsQosServiceTable OBJECT-TYPE
     SYNTAX SEQUENCE OF ArrisMtadocsQosServiceEntry
     MAX-ACCESS not-accessible
     STATUS current
     DESCRIPTION
         "This table contains the NCS/SIP log"
     ::= { arrisMtadocsQosService 1 }

arrisMtadocsQosServiceEntry OBJECT-TYPE
 SYNTAX ArrisMtadocsQosServiceEntry
 MAX-ACCESS not-accessible
 STATUS current
 DESCRIPTION
  "An entry in the Mta Qos log table."
 INDEX { arrisMtadocsQosServiceIndex }
 ::= { arrisMtadocsQosServiceTable 1 }

ArrisMtadocsQosServiceEntry ::= SEQUENCE{
  arrisMtadocsQosServiceIndex INTEGER,
  arrisMtadocsQosServiceFlowID INTEGER,
  arrisMtadocsQosServiceClassName OCTET STRING,
  arrisMtdocsQosServiceFlowDirection OCTET STRING,
  arrisMtdocsQosServicePrimaryFlow OCTET STRING,
  arrisMtadocsQosTrafficType OCTET STRING,
  arrisMtadocsQosServicePackets INTEGER
 }

arrisMtadocsQosServiceIndex OBJECT-TYPE
 SYNTAX INTEGER (1..100)
 MAX-ACCESS not-accessible
 STATUS current
 DESCRIPTION "The index of mta qos entry."
 ::= { arrisMtadocsQosServiceEntry 1 }

arrisMtadocsQosServiceFlowID OBJECT-TYPE
 SYNTAX INTEGER
 MAX-ACCESS read-only
 STATUS current
 DESCRIPTION "mta qos service flow id."
 ::= { arrisMtadocsQosServiceEntry 2 }

arrisMtadocsQosServiceClassName OBJECT-TYPE
 SYNTAX OCTET STRING
 MAX-ACCESS read-only
 STATUS current
 DESCRIPTION "mta qos service class name."
 ::= { arrisMtadocsQosServiceEntry 3 }

arrisMtdocsQosServiceFlowDirection OBJECT-TYPE
 SYNTAX OCTET STRING
 MAX-ACCESS read-only
 STATUS current
 DESCRIPTION "mta qos service flow direction."
 ::= { arrisMtadocsQosServiceEntry 4 }

arrisMtdocsQosServicePrimaryFlow OBJECT-TYPE
 SYNTAX OCTET STRING
 MAX-ACCESS read-only
 STATUS current
 DESCRIPTION "mta qos service primary flow"
 ::= { arrisMtadocsQosServiceEntry 5 }

arrisMtadocsQosTrafficType OBJECT-TYPE
 SYNTAX OCTET STRING
 MAX-ACCESS read-only
 STATUS current
 DESCRIPTION "mta qos traffic type."
 ::= { arrisMtadocsQosServiceEntry 6 }

arrisMtadocsQosServicePackets OBJECT-TYPE
 SYNTAX INTEGER
 MAX-ACCESS read-only
 STATUS current
 DESCRIPTION "Packets belong to the service."
 ::= { arrisMtadocsQosServiceEntry 7 }

arrisMtadocsQosDisableLoggin OBJECT-TYPE
 SYNTAX INTEGER{
			disableLoggin (1),
			enableLoggin (2)
           }
 MAX-ACCESS read-write
 STATUS current
 DESCRIPTION "disable mta qos log collecting."
 ::= { arrisMtadocsQosService 2 }

arrisMtadocsQosLogClear OBJECT-TYPE
 SYNTAX TruthValue
 MAX-ACCESS read-write
 STATUS current
 DESCRIPTION "Clear mta qos log. Always return true if get the value of this mib"
 ::= { arrisMtadocsQosService 3 }

arrisMtadocsQosShowDsxLogTable OBJECT-TYPE
     SYNTAX SEQUENCE OF ArrisMtadocsQosShowDsxLogEntry
     MAX-ACCESS not-accessible
     STATUS current
     DESCRIPTION
         "This table contains the DSX log"
     ::= { arrisMtadocsQosService 4 }

arrisMtadocsQosShowDsxLogEntry OBJECT-TYPE
 SYNTAX ArrisMtadocsQosShowDsxLogEntry
 MAX-ACCESS not-accessible
 STATUS current
 DESCRIPTION
  "An entry in the log table."
 INDEX { arrisMtadocsQosShowDsxLogIndex }
 ::= { arrisMtadocsQosShowDsxLogTable 1 }

ArrisMtadocsQosShowDsxLogEntry ::= SEQUENCE{
  arrisMtadocsQosShowDsxLogIndex INTEGER,
  arrisMtadocsQosShowDsxLog OCTET STRING
 }

arrisMtadocsQosShowDsxLogIndex OBJECT-TYPE
 SYNTAX INTEGER (1..256)
 MAX-ACCESS not-accessible
 STATUS current
 DESCRIPTION "The index of signal log."
 ::= { arrisMtadocsQosShowDsxLogEntry 1 }

arrisMtadocsQosShowDsxLog OBJECT-TYPE
 SYNTAX OCTET STRING (SIZE (0..2048))
 MAX-ACCESS read-only
 STATUS current
 DESCRIPTION "Show the log of dsx"
 ::= { arrisMtadocsQosShowDsxLogEntry 2 }

-- PD 189252 end

arrisMtaDevOptionality8ChnlKey OBJECT-TYPE
     SYNTAX SnmpAdminString
     MAX-ACCESS read-write
     STATUS deprecated
     DESCRIPTION
         "When correct key is entered, 8 channel DSP operation can be enabled using
          arrisMtaDevOptionality8ChnlEnable mib."
     ::= { arrisMtaDevOptionality 1 }


arrisMtaDevOptionality8ChnlEnable OBJECT-TYPE
     SYNTAX INTEGER {
         enabled(1),
         disabled(2),
         enabled-needs-to-be-reset(3),
         disabled-needs-to-be-reset(4)
     }
     MAX-ACCESS read-write
     STATUS deprecated
     DESCRIPTION
         "Enable or Disable 8 channel DSP operation.  Enabling requires presence
          of a valid 8 Channel DSP Key.  This key is entered via the
          arrisMtaDevOptionality8ChnlKey MIB.  When an Enable or Disable action
          is invoked, a reset of the unit is required before the action becomes
          effective.  Until the reset occurs this MIB indicates the need for a
          reset by displaying a status which includes _needs_to_be_reset.  Note
          that _needs_to_be_reset status values are not valid inputs to this MIB.
          Valid MIB inputs are enabled(1) and disabled(2)"
     ::= { arrisMtaDevOptionality 2 }


arrisMtaDevOptionalityLoopDiagKey OBJECT-TYPE
     SYNTAX SnmpAdminString
     MAX-ACCESS read-write
     STATUS deprecated
     DESCRIPTION
         "When correct key is entered, Loop Diag can be performed."
     ::= { arrisMtaDevOptionality 3 }


arrisMtaDevLoopVoltageKey OBJECT-TYPE
     SYNTAX SnmpAdminString
     MAX-ACCESS read-write
     STATUS current
     DESCRIPTION
         "When correct key is entered, Loop Voltage Mgmt. policy can be set.
          This MIB is only writable via configuration file."
     ::= { arrisMtaDevLoopVoltageMgmt 1 }


arrisMtaDevLoopVoltagePolicy OBJECT-TYPE
     SYNTAX INTEGER {
         always-voltage-present(1),
         rf-carrier-voltage-present(2),
         in-service-voltage-present(3),
         default-operation(4)
     }
     MAX-ACCESS read-write
     STATUS current
     DESCRIPTION
         "1. Maintain loop idle voltage at all times.
          2. Apply loop idle voltage at all times except when no RF QAM carrier is
             detected.   The intent of this policy option is to maintain idle
             voltage for all normal operation but to remove it if RF conditions
             appear to match a malicious cable cut (such may happen if a burglar is
             trying to disable the alarm system).
          3. Apply loop idle voltage only when the MTA device  is In-service (MTA IP
             address is received and valid config file has been received) and during
             manually initiated resets (either reset button or SNMP).  If this policy
             criterion is selected, then the EMTA MUST maintain loop idle voltage if a
             reset command is received (via SNMP or reset button or as part of a
             management initiated software upgrade).  Once the MTA has come back in-
             service,  any subsequent MTA out-of-service condition MUST result in
             removal of loop idle voltage (except for another manually initiated reset).
             As a failsafe, if the MTA has not come in-service within a provisionable
             time, then loop idle voltage MUST be removed.
          4. Apply loop idle voltage whenever the MTA device is in-service.
          5. This MIB is only writable via configuration file."
     DEFVAL { default-operation }
     ::= { arrisMtaDevLoopVoltageMgmt 2 }


arrisMtaDevLoopVoltageResetTimeout OBJECT-TYPE
     SYNTAX Integer32
     UNITS "seconds"
     MAX-ACCESS read-write
     STATUS current
     DESCRIPTION
         "Specifies the time after which to remove loop voltage if the MTA has not come
          in-service. Acceptable range is 8-1800 seconds.  Stored value must be divisible
          by 8 (any remainder will be discarded).  See arrisMtaDevLoopVoltagePolicy 3 for
          operational details.
          This MIB is only writable via configuration file.
          For D11PLUS builds, values from 8 through 32 will be multiplied by 3."
     DEFVAL { 300 } -- ( = 5 minutes )
     ::= { arrisMtaDevLoopVoltageMgmt 3 }

 arrisMtaDevLoopVoltageMaintTimeout OBJECT-TYPE
     SYNTAX Integer32
     UNITS "minutes"
     MAX-ACCESS read-write
     STATUS current
     DESCRIPTION
         "Specifies the time that loop voltage will be supplied regardless of RF condition.
          See arrisMtaDevLoopVoltagePolicy  for more detailed information.
          This MIB is only writable via configuration file."
     DEFVAL { 0 } -- ( = 0 minutes )
     ::= { arrisMtaDevLoopVoltageMgmt 4 }


arrisMtaDevVPNomJitterBuffer OBJECT-TYPE
     SYNTAX INTEGER {
         packetizationRatex1(1),
         packetizationRatex2(2),
		 packetizationRatex3(3),
		 packetizationRatex4(4)
     }
     MAX-ACCESS read-write
     STATUS current
     DESCRIPTION
         "Indicates the Voice Playout nominal jitter buffer."
     DEFVAL { packetizationRatex1 }
     ::= { arrisMtaDevOperationalSetup 1 }

arrisMtaDevVPJitterBufferMode OBJECT-TYPE
     SYNTAX INTEGER {
         adaptive(1),
         fixed(2),
         auto(3)
     }
     MAX-ACCESS read-write
     STATUS current
     DESCRIPTION
         "Indicates the Voice Playout jitter buffer mode."
     DEFVAL { adaptive }
     ::= { arrisMtaDevOperationalSetup 2 }

arrisMtaDevRTPTxQueueSize OBJECT-TYPE
     SYNTAX INTEGER(2..20)
     MAX-ACCESS read-write
     STATUS current
     DESCRIPTION
         "Sets the RTP transmit queue size."
     DEFVAL { 20 }
     ::= { arrisMtaDevOperationalSetup 3 }

arrisMtaDevEchoCancellerTailLength OBJECT-TYPE
     SYNTAX INTEGER {
         eightMs(1),
         thirtyTwoMs(2)
     }
     MAX-ACCESS read-write
     STATUS current
     DESCRIPTION
         "Indicates the length in milliseconds of the echo canceller tail.  This object
          is only settable during the processing of the MTA config file."
     DEFVAL { thirtyTwoMs }
     ::= { arrisMtaDevOperationalSetup 4 }

arrisMtaDevDspHandleNonPhaseReversedTone OBJECT-TYPE
     SYNTAX INTEGER {
         off(1),
         onECANEnable(2),
         onECANDisabled(3)
     }
     MAX-ACCESS read-write
     STATUS current
     DESCRIPTION
         "Set handling the DSP non phase reversed tone detection for modem.  A value of
          off(1) indicates the tone will not be handled.  A default value of onECANEnable(2)
          indicates the modem non phase reversed CED tone will be handled with echo canceller
          enabled.  A value of onECANDisabled(3) indicates the modem non phase reversed CED
          tone will be handled with echo canceller disabled."
     DEFVAL { onECANEnable }
     ::= { arrisMtaDevOperationalSetup 5 }

-- [ARRIS NOTE: For the published (publicly available) MIB, the MAX-ACCESS clause for
--  the 'arrisCmDevProvMethodIndicator' object should have a value of 'read-only'.]
arrisMtaDevProvMethodIndicator OBJECT-TYPE
     SYNTAX ArrsMtaDevProvMethod
     MAX-ACCESS read-write
     STATUS current
     DESCRIPTION
         "Indicates the method used to provision the device.  This object should only be
          changed by the configuration file.  The following provisioning methods are supported:

             docsisOnly(0)          - DOCSIS-only provisioning

             fullPacketCable(1)     - PacketCable 1.5 Flows. See
                                      arrisMtaDevPacketcableProvisioningFlow for which
                                      flow we are using.

             packetCableMinusKDC(2) - same as 'fullPacketCable', except with IPSEC and
                                      SNMPv3 disabled

             cps(3)                 - compatible with CPS2000 (SNMPv2; IPSEC disabled)

             gupi(4)                - SNMPv2, with no SNMP Informs and IPSEC disabled

             singleMAC(5)           - single config file (SNMPv2, single IP address,
                                      single MAC address, no SNMP Informs, IPSEC disabled

             basic1(6)              - Basic1 SNMPv2, without the SNMP Enrollment, Status Informs
                                      or Hash

             basic2(7)              - ARRIS Basic2 SNMPv2, without the SNMP Enrollment Inform or
	                              Hash

             gupiEncryptedMtaConfig(8) - Same as gupi(4) above with the MTA config file encrypted
                                         using an Arris proprietary method.

             gupiMacMta(9)          - gupi provisioning that uses MTA MAC address as the MTA config
                                      file name. (ie- 1337c0ded00d.bin)

             gupiEncryptedMacMta(10) - gupi encrypted mta config provisioning that uses MTA MAC address
                                       as the MTA config file name. (ie- 1337c0ded00d.bin)

             gupiTftpSvrOverride(11) - gupi provisioning where the FQDN of the MTA TFTP server is expected to
                                       be present in the MIB arrisMtaDevTFTPServerAddrOverrideFQDN"

     ::= { arrisMtaDevOperationalSetup 6 }

arrisMtaCfgRTPDynPortStart OBJECT-TYPE
    SYNTAX      Integer32
    MAX-ACCESS  read-write
    STATUS      current
    DESCRIPTION
          "This defines the starting value for a range of ports that will be used dynamically
           when sending out SIP RTP voice packets.  This MIB and arrisMtaCfgRTPDynPortEnd
           are to be used together.

           The range limit is 1024-65535. Where arrisMtaCfgRTPDynPortStart can be 1024 and
           arrisMtaCfgRTPDynPortEnd can be 65535.  The default range is 49152-65535.
           However it should be noted that the IANA defines the following ranges:

           The Well Known Ports are those from 0 through 1023.
           The Registered Ports are those from 1024 through 49151.
           The Dynamic and/or Private Ports are those from 49152 through 65535."
    ::= { arrisMtaDevOperationalSetup 7 }

arrisMtaCfgRTPDynPortEnd OBJECT-TYPE
    SYNTAX      Integer32
    MAX-ACCESS  read-write
    STATUS      current
    DESCRIPTION
          "This defines the starting value for a range of ports that will be used dynamically
           when sending out SIP RTP voice packets.  This MIB and arrisMtaCfgRTPDynPortStart
           are to be used together.

           The range limit is 1024-65535. Where arrisMtaCfgRTPDynPortStart can be 1024 and
           arrisMtaCfgRTPDynPortEnd can be 65535.  The default range is 49152-65535.
           However it should be noted that the IANA defines the following ranges:

           The Well Known Ports are those from 0 through 1023.
           The Registered Ports are those from 1024 through 49151.
           The Dynamic and/or Private Ports are those from 49152 through 65535."
    ::= { arrisMtaDevOperationalSetup 8 }

arrisMtaDevVPMaxJitterBuffer OBJECT-TYPE
     SYNTAX INTEGER {
         packetizationRatex1(1),
         packetizationRatex2(2),
		 packetizationRatex3(3),
		 packetizationRatex4(4),
                 packetizationRatex5(5),
                 packetizationRatex6(6)
     }
     MAX-ACCESS read-write
     STATUS current
     DESCRIPTION
         "Indicates the Voice Playout maximum jitter buffer."
     DEFVAL { packetizationRatex6 }
     ::= { arrisMtaDevOperationalSetup 9 }

arrisMtaDevPacketcableProvisioningFlow OBJECT-TYPE
 	SYNTAX INTEGER {
 		secure (0),
 		hybrid2 (1),
		hybrid1 (2),
		basic2 (3),
		basic1 (4),
		none (5)
 	}
 	MAX-ACCESS read-only
 	STATUS current
 	DESCRIPTION
 		"PacketCable simplified provisioning flow support for PC1.5 Compliance.  This object
		 will be updated by the Provisioning Code.  The following PC1.5 Compliant Provisioning
		 methods are supported:

		 secure (0) - PacketCable 1.5 Secure Flow

		 hybrid2 (1) - PacketCable 1.5 Hybrid 2 Flow

		 hybrid1 (2) - PacketCable 1.5 Hybrid 1 Flow

		 basic2 (3) - PacketCable 1.5 Basic 2 Flow

		 basic1 (4) - PacketCable 1.5 Basic 1 Flow

		 none (5) - ARRIS NON PacketCable 1.5 Flow"
 	DEFVAL { none }
 	::= { arrisMtaDevOperationalSetup 39 }

arrisMtaDevEnableIndexTenEleven OBJECT-TYPE
    SYNTAX INTEGER {
        disable(0),
        enable(1)
    }
    MAX-ACCESS  read-write
    STATUS      current
    DESCRIPTION
       "This MIB object is used to enable telephone line indices ten and eleven
       instead of telephone line indices nine and ten.  Index ten will be the
       mininum index for the MTA.  The default value for this MIB object is disablel(0)."
     ::= { arrisMtaDevOperationalSetup 13 }


arrisMtaDevGainControlFSK OBJECT-TYPE
     SYNTAX Integer32(-10..2)
     MAX-ACCESS read-write
     STATUS current
     DESCRIPTION
         "The transmit digital gain adjustment (dBm) for MTA generated FSK tones (CID and VMWI).
          A value of 2 increases the FSK level by 2 dBm. A value of -2 decreases the FSK
          level by 2 dBm."
     DEFVAL { 0 }
     ::= { arrisMtaDevGainControl 1 }

arrisMtaDevGainControlCAS OBJECT-TYPE
     SYNTAX Integer32(-2..2)
     MAX-ACCESS read-write
     STATUS current
     DESCRIPTION
         "The transmit digital gain adjustment (dBm) for MTA generated CAS tone.
          A value of 2 increases the playout level by 2 dBm. A value of -2 decreases the playout
          level by 2 dBm."
     DEFVAL { 0 }
     ::= { arrisMtaDevGainControl 2 }

arrisMtaDevGainControlLocalTone OBJECT-TYPE
     SYNTAX Integer32(-2..2)
     MAX-ACCESS read-write
     STATUS current
     DESCRIPTION
         "The transmit digital gain adjustment (dBm) for all MTA generated Call Progress tones
          (Dialtone, Busytone, Ringback, etc.) toward the CPE. A value of 2 increases the
          playout level by 2 dBm. A value of -2 decreases the playout level by 2 dBm. This MIB
          does not effect CAS tone levels - use arrisMtaDevGainControlCAS for adjusting the
          CAS tone."
     DEFVAL { 0 }
     ::= { arrisMtaDevGainControl 3 }

arrisMtaDevGainControlNetworkTone OBJECT-TYPE
     SYNTAX Integer32(-2..2)
     MAX-ACCESS read-write
     STATUS current
     DESCRIPTION
         "The transmit digital gain adjustment (dBm) for MTA generated Call Progress tones
          toward the network (Ringback).  A value of 2 increases the playout level by 2 dBm.
          A value of -2 decreases the playout level by 2 dBm."
     DEFVAL { 0 }
     ::= { arrisMtaDevGainControl 4 }

arrisMtaDevGainControlLocalDTMF OBJECT-TYPE
     SYNTAX Integer32(-15..9)
     MAX-ACCESS read-write
     STATUS current
     DESCRIPTION
         "The transmit digital gain adjustment (dBm) for MTA generated DTMF tones toward
          the local CPE (ex. DTMF CID). A value of 2 increases the playout level by 2 dBm.
          A value of -2 decreases the playout level by 2 dBm."
     DEFVAL { 0 }
     ::= { arrisMtaDevGainControl 5 }

arrisMtaDevGainControlNetworkDTMF OBJECT-TYPE
     SYNTAX Integer32(-9..9)
     MAX-ACCESS read-write
     STATUS current
     DESCRIPTION
         "The transmit digital gain adjustment (dBm) for MTA generated DTMF tones
          toward the network (ex. IPDT Pulse Dialing). A value of 2 increases the playout
          level by 2 dBm. A value of -2 decreases the playout level by 2 dBm."
     DEFVAL { 0 }
     ::= { arrisMtaDevGainControl 6 }

arrisMtaDevGainControlTxVoice OBJECT-TYPE
     SYNTAX Integer32(-16..16)
     MAX-ACCESS read-write
     STATUS current
     DESCRIPTION
         "The transmit digital gain adjustment (dBm) for voice. A value of 2 increases
          the voice level by 2 dBm. A value of -2 decreases the voice level by 2 dBm. This
          value does not effect the levels of local tones or FSK.
          NOTE: Use caution when changing this MIB. Increasing or decreasing the voice level
          by the larger numbers allowed in the range may compromise voice quality."
     DEFVAL { 0 }
     ::= { arrisMtaDevGainControl 7 }

arrisMtaDevGainControlRxVoice OBJECT-TYPE
     SYNTAX Integer32(-16..16)
     MAX-ACCESS read-write
     STATUS current
     DESCRIPTION
         "The receive digital gain adjustment (dBm) for voice. A value of 2 increases
          the voice level by 2 dBm. A value of -2 decreases the voice level by 2 dBm.
          NOTE: Use caution when changing this MIB. Increasing or decreasing the voice level
          by the larger numbers allowed in the range may compromise voice quality."
     DEFVAL { 0 }
     ::= { arrisMtaDevGainControl 8 }

arrisMtaDevLevelControlOffHookEnable OBJECT-TYPE
     SYNTAX INTEGER {
     disable(0),
     enable(1)
	 }
	 MAX-ACCESS read-write
     STATUS current
     DESCRIPTION
         "Allows for the use of the arrisMtaDevLevelControlOffHookFSK and
          arrisMtaDevLevelControlOffHookCAS MIBs.  When this is set to enable, those
          MIBs will be replace the arrisMtaDevLevelControlFSK and
          arrisMtaDevLevelControlCAS MIBs in off-hook situations."
     DEFVAL { 0 }
     ::= { arrisMtaDevLevelControl 1 }

arrisMtaDevLevelControlOffHookFSK OBJECT-TYPE
     SYNTAX Integer32(-32..-10)
     MAX-ACCESS read-write
     STATUS current
     DESCRIPTION
         "The transmit digital gain setting (dBm) for MTA generated FSK tones (CID and VMWI)
          while the line is off hook.  The MIB can be adjusted in 1dBm increcements from a high
          of -10dBm to a low of -32dBm.  The arrisMtaDevLevelControlOffHookEnable MIB must
          enabled to activate this MIB."
     DEFVAL { -15 }
     ::= { arrisMtaDevLevelControl 2 }

arrisMtaDevLevelControlOffHookCAS OBJECT-TYPE
     SYNTAX Integer32(-32..-10)
     MAX-ACCESS read-write
     STATUS current
     DESCRIPTION
         "The transmit digital gain setting (dBm) for MTA generated CAS tones (CID and VMWI)
          while the line is off hook.  The MIB can be adjusted in 1dBm increcements from a high
          of -10dBm to a low of -32dBm.  The arrisMtaDevLevelControlOffHookEnable MIB must
          enabled to activate this MIB."
     DEFVAL { -15 }
     ::= { arrisMtaDevLevelControl 3 }

-- arrisMtaDevEnableIndexTenEleven OBJECT-TYPE
--    SYNTAX INTEGER {
--        disable(0),
--        enable(1)
--    }
--    MAX-ACCESS  read-write
--    STATUS      current
--    DESCRIPTION
--       "This MIB object is used to enable telephone line indices ten and eleven
--       instead of telephone line indices nine and ten.  Index ten will be the
--       mininum index for the MTA.  The default value for this MIB object is disable(0)."
--    ::= { arrisMtaDevOperationalSetup 13 }

arrisMtaDevDspCpsSetting OBJECT-TYPE
     SYNTAX INTEGER {
         off(1),
         on(2)
     }
     MAX-ACCESS read-write
     STATUS current
     DESCRIPTION
         "Enable or Disable the ECAN fast constant power signal detection.  A default value of
         on(2) makes the echo cancellor disengage immediately when a high level constant power
         signal is detected.  A value of off(1) will not disengage the ECAN when a high level
         constant power signal is detected."
     DEFVAL { on }
     ::= { arrisMtaDevOperationalSetup 14 }

     arrisMtaDevVbdOverwriteLineBitmap OBJECT-TYPE
     SYNTAX INTEGER
     MAX-ACCESS read-write
     STATUS current
     DESCRIPTION
         "When set, changes fax/modem jitter buffer settings for the selected line to the
          VbdOverwriteJitterBuffer values entered in the config file.
          (0) no line set, (0x1) line #1 set, (0x2) line #2 set, (0x4) line #3 set, ..."
     DEFVAL { 0 }
     ::= { arrisMtaDevOperationalSetup 16 }

arrisMtaDevVbdOverwriteMinJitterBuffer OBJECT-TYPE
     SYNTAX INTEGER(10..160)
     MAX-ACCESS read-write
     STATUS current
     DESCRIPTION
         "When used in conjuction with arrisMtaDevVbdOverwriteLineBitmap, this value will
          be used as the minimun jitter buffer setting in all modem/fax calls for the selected
          lines."
     DEFVAL { 20 }
     ::= { arrisMtaDevOperationalSetup 17 }

arrisMtaDevVbdOverwriteNomJitterBuffer OBJECT-TYPE
     SYNTAX INTEGER(10..160)
     MAX-ACCESS read-write
     STATUS current
     DESCRIPTION
         "When used in conjuction with arrisMtaDevVbdOverwriteLineBitmap, this value will
          be used as the nominal jitter buffer setting in all modem/fax calls for the selected
          lines."
     DEFVAL { 70 }
     ::= { arrisMtaDevOperationalSetup 18 }

arrisMtaDevVbdOverwriteMaxJitterBuffer OBJECT-TYPE
     SYNTAX INTEGER(10..160)
     MAX-ACCESS read-write
     STATUS current
     DESCRIPTION
         "When used in conjuction with arrisMtaDevVbdOverwriteLineBitmap, this value will
          be used as the maximum jitter buffer setting in all modem/fax calls for the selected
          lines."
     DEFVAL { 160 }
     ::= { arrisMtaDevOperationalSetup 19 }

arrisMtaDevEventHideFQDNandIPAddress OBJECT-TYPE
    SYNTAX INTEGER {
        disable(0),
        enable(1)
    }
    MAX-ACCESS  read-write
    STATUS      current
    DESCRIPTION
       "This MIB object is used to enable hide MTA fqdn and IP address on basic web page event log
       .  The default value for this MIB object is disable(0)."
     ::= { arrisMtaDevOperationalSetup 20 }

arrisMtaDevDhcpOptionOverride OBJECT-TYPE
     SYNTAX INTEGER {
         off(1),
         on(2)
     }
     MAX-ACCESS read-write
     STATUS current
     DESCRIPTION
         "Typically the value received in the DHCP OFFER should not change in the DHCP ACK.  DHCP
         RENEW/REBIND values should be consistent with the value received in the DHCP OFFER. This
         MIB object will Enable or Disable the DHCP option code 122/177 suboption 3 value enforcement.
         A value of off(1) will enable DHCP option 122/177 suboption 3 value comparison
         checking.  A value of on(2) will disable the enforcement of DHCP option 122/177
         suboption 3 value comparison checking.
         The default value is off(1)."
     DEFVAL { off }
     ::= { arrisMtaDevOperationalSetup 21 }

arrisMtaDevTFTPServerAddrOverrideFQDN OBJECT-TYPE
     SYNTAX DisplayString
     MAX-ACCESS read-write
     STATUS current
     DESCRIPTION
        "FQDN of the TFTP Server that holds the MTA config file. This is used to override the default
         TFTP Server. This can only be used with the gupiTftpSvrOverride(11) Provisioning Method."
     ::= { arrisMtaDevOperationalSetup 22}

arrisMtaDevDefaultReasonNoCIDName OBJECT-TYPE
    SYNTAX INTEGER {
        unavailable(0),
        private(1),
        sendnothing(2),
        sdmf(3),
        excludeName(4)
    }
    MAX-ACCESS  read-write
    STATUS      current
    DESCRIPTION
       "This MIB object determines what reason is sent to the CPE when the Caller ID Name is not included in the signal request.
        The default value for this MIB object is 'O' for unavailable or outofarea(0). If the value of the MIB is set to private(1)
        then 'P' is sent to the CPE. The value of sendnothing(2) tells the MTA to send NULL reason for the missing name.
        The value of sdmf(3) sends the number only in NA SDMF format. The value of excludeName(4) tells the MTA to not include
        any name parameters or reason for missing name."
     ::= { arrisMtaDevOperationalSetup 23 }

arrisMtaDevSipConfigFileURL  OBJECT-TYPE
      SYNTAX      SnmpAdminString
      MAX-ACCESS  read-write
      STATUS      current
    DESCRIPTION
            "The URL of the SIP configuration file for redownloading provisioning and
            configuration parameters to this device."
      ::= { arrisMtaDevOperationalSetup 24 }

arrisMtaDevSipDwnldConfig OBJECT-TYPE
     SYNTAX INTEGER {
         off(1),
         on(2)
     }
     MAX-ACCESS read-write
     STATUS current
     DESCRIPTION
         "Enable a redownload of the SIP configuration file parameters specified via
         the configuration file URL obtained in the MIB object arrisMtaDevSipConfigFileURL.
         When read this MIB object will always return a value of off(1)."
     DEFVAL { off }
     ::= { arrisMtaDevOperationalSetup 25 }

arrisMtaDevSpecialConfigurationOverrideEnable OBJECT-TYPE
  SYNTAX BITS {
      enableDhcpOption60SubOpt18Ovrd(0),
      unused1(1),
      unused2(2),
      unused3(3),
      unused4(4),
      unused5(5),
      unused6(6),
      unused7(7),
      unused8(8),
      unused9(9),
      unused10(10),
      unused11(11),
      unused12(12),
      unused13(13),
      unused14(14),
      unused15(15),
      unused16(16),
      unused17(17),
      unused18(18),
      unused19(19),
      unused20(20),
      unused21(21),
      unused22(22),
      unused23(23),
      unused24(24),
      unused25(25),
      unused26(26),
      unused27(27),
      unused28(28),
      unused29(29),
      unused30(30),
      unused31(31)
  }
  MAX-ACCESS read-write
  STATUS current
  DESCRIPTION
    "This object is used to enable proprietary features of the Arris MTA
     From left to right, the specified bit indicates whether or not
     the corresponding MTA feature is enabled.  For example, if the first
     bit is set, then the enableDhcpOption60SubOpt18Ovrd feature is enabled. If
     it is zero, the feature is disabled.  NO bits are set by default.
	 Field is 32 bits long and all 32 bits must be written.

     /** BIT Descriptions **/
     0x80000000 : enableDhcpOption60SubOpt18Ovrd - Enable DHCP Option 60 SubOption 18 override
     0x40000000 : Reserved for Future.
     0x20000000 : Reserved for Future.
     0x10000000 : Reserved for Future.
     0x08000000 : Reserved for Future.
     0x04000000 : Reserved for Future.
     0x02000000 : Reserved for Future.
     0x01000000 : Reserved for Future.
     0x00800000 : Reserved for Future.
     0x00400000 : Reserved for Future.
     0x00200000 : Reserved for Future.
     0x00100000 : Reserved for Future.
     0x00080000 : Reserved for Future.
     0x00040000 : Reserved for Future.
     0x00020000 : Reserved for Future.
     0x00010000 : Reserved for Future.
     0x00008000 : Reserved for Future.
     0x00004000 : Reserved for Future.
     0x00002000 : Reserved for Future.
     0x00001000 : Reserved for Future.
     0x00000800 : Reserved for Future.
     0x00000400 : Reserved for Future.
     0x00000200 : Reserved for Future.
     0x00000100 : Reserved for Future.
     0x00000080 : Reserved for Future.
     0x00000040 : Reserved for Future.
     0x00000020 : Reserved for Future.
     0x00000010 : Reserved for Future.
     0x00000008 : Reserved for Future.
     0x00000004 : Reserved for Future.
     0x00000002 : Reserved for Future.
     0x00000001 : Reserved for Future."
  DEFVAL { '00000000'h }
 ::= { arrisMtaDevOperationalSetup 26 }

arrisMtaDevRtcpTosValue OBJECT-TYPE
    SYNTAX Integer32(0..63)
    MAX-ACCESS read-write
    STATUS current
    DESCRIPTION "This value determines what value is used in the IP TOS byte for RTCP packets."
    ::= { arrisMtaDevOperationalSetup 27 }

arrisMtaDevAutomaticOsiDelay OBJECT-TYPE
    SYNTAX Integer32(0..100)
    UNITS "100 milliseconds"
    MAX-ACCESS read-write
    STATUS current
    DESCRIPTION "This MIB defines the time, in 100ms increments, to wait after a DLCX is received before determining if an automatic OSI should be generated by the MTA to force a line disconnect.
    The default time is 5 seconds. A value of 0 would cause the OSI to be sent immediately (if there are no other connections on the line). The ppCfgMtaCallpFeatureSwitch must have the 0x20000000 bit set for this feature to be enabled."
    DEFVAL { 50 }
    ::= { arrisMtaDevOperationalSetup 28 }

arrisMtaDevCustomJitterBufferEnabled OBJECT-TYPE
     SYNTAX INTEGER {
         off(0),
         on(1)
     }
     MAX-ACCESS read-write
     STATUS current
     DESCRIPTION
         "Enables ability to customize jitter buffer settings using the CustomMinJitterBuffer, CustomNomJitterBuffer and CustomMaxJitterBuffer
          mibs.  When this setting is off, the jitter buffer will be determined using the arrisMtaDevVPNomJitterBuffer and
          arrisMtaDevVPMaxJitterBuffer mibs and defaults to min=nom=[(packet rate *1) + 5] and max = [(packet rate * 3) + 5] msecs.
          When set to on, the custom jitter buffer settings will default to 5-10-60 if no custom value is set using the CustomMinJitterBuffer,
          CustomNomJitterBuffer and CustomMaxJitterBuffer mibs."
     DEFVAL { off }
     ::= { arrisMtaDevOperationalSetup 29 }

arrisMtaDevCustomMinJitterBuffer OBJECT-TYPE
     SYNTAX INTEGER (5..160)
     MAX-ACCESS read-write
     STATUS current
     DESCRIPTION
         "Indicates the customized voice playout minimum jitter buffer to be used when the arrisMtaDevCustomJitterBufferEnabled is set to on.
          Valid range is 5-160 in increments of 5"
     DEFVAL { 5 }
     ::= { arrisMtaDevOperationalSetup 30 }

arrisMtaDevCustomNomJitterBuffer OBJECT-TYPE
     SYNTAX INTEGER (5..160 )
     MAX-ACCESS read-write
     STATUS current
     DESCRIPTION
         "Indicates the customized voice playout nominal jitter buffer to be used when the arrisMtaDevCustomJitterBufferEnabled is set to on.
          Valid range is 5-160 in increments of 5"
     DEFVAL { 10 }
     ::= { arrisMtaDevOperationalSetup 31 }

arrisMtaDevCustomMaxJitterBuffer OBJECT-TYPE
     SYNTAX INTEGER (5..160)
     MAX-ACCESS read-write
     STATUS current
     DESCRIPTION
         "Indicates the customized voice playout maximum jitter buffer to be used when the arrisMtaDevCustomJitterBufferEnabled is set to on.
          Valid range is 5-160 in increments of 5"
     DEFVAL { 120 }
     ::= { arrisMtaDevOperationalSetup 32 }

arrisMtaDevEnableDHCPLog OBJECT-TYPE
     SYNTAX INTEGER {
		 disable(0),
         enable(1)
	 }
     MAX-ACCESS read-write
     STATUS current
     DESCRIPTION
         "Used to enable/disable MTA DHCP logging."
     ::= { arrisMtaDevOperationalSetup 33 }

arrisMtaDevEnableMGCPLog OBJECT-TYPE
     SYNTAX INTEGER {
		 disable(0),
         enable(1)
	 }
     MAX-ACCESS read-write
     STATUS current
     DESCRIPTION
         "Used to enable/disable CallP Signalling logging"
     ::= { arrisMtaDevOperationalSetup 34 }

arrisMtaDevClearDHCPLog OBJECT-TYPE
	 SYNTAX INTEGER {
		 clear(1)
	 }
     MAX-ACCESS read-write
     STATUS current
     DESCRIPTION
        "Used to Clear the MTA DHCP Logs."
     ::= { arrisMtaDevOperationalSetup 35 }

arrisMtaDevClearMGCPLog OBJECT-TYPE
	 SYNTAX INTEGER {
		 clear(1)
	 }
     MAX-ACCESS read-write
     STATUS current
     DESCRIPTION
        "Used to Clear the MTA MGCP Logs."
     ::= { arrisMtaDevOperationalSetup 36 }

arrisMtaDevTDDReportToCMS OBJECT-TYPE
     SYNTAX INTEGER {
		 disable(0),
         enable(1)
	 }
     MAX-ACCESS read-write
     STATUS current
     DESCRIPTION
        "Allows configuration of whether TDD detection events are reported to CMS."
     DEFVAL { enable }
     ::= { arrisMtaDevOperationalSetup 37 }

arrisMtaDevAutomaticCallResourceRecovery OBJECT-TYPE
    SYNTAX Integer32(0..3600)
    UNITS "seconds"
    MAX-ACCESS read-write
    STATUS current
    DESCRIPTION "MIB defines the number of seconds to delay upon an on-hook event before detecting
                 that all resources acquired while a call was active need to be recovered on a line
                 in the IDLE state. A value of 0 disables the automatic feature."
     ::= { arrisMtaDevOperationalSetup 38 }

arrisMtaDevOffHookFskDelay OBJECT-TYPE
    SYNTAX Integer32(0..500)
    UNITS "milliseconds"
    MAX-ACCESS read-write
    STATUS current
    DESCRIPTION
    "MIB defines the time (in milliseconds) to delay before sending the FSK to the CPE.
    The delay starts upon receiving the ACK (DTMF D) from the CPE in response to the CAS tone for
    Call Waiting (or Type 2) Caller ID."
     ::= { arrisMtaDevOperationalSetup 41 }

arrisMtaDevT38Timeout OBJECT-TYPE
    SYNTAX Integer32(1..30)
    UNITS "seconds"
    MAX-ACCESS read-write
    STATUS current
    DESCRIPTION
    "Allows configuration of the T38 timeout, during which time the audio is muted, before T38
    failure events are reported to CMS."
    DEFVAL { 30 }
     ::= { arrisMtaDevOperationalSetup 42 }

arrisMtaDevSuperG3FaxRelay OBJECT-TYPE
     SYNTAX INTEGER {
		 disable(0),
         enable(1)
	 }
     MAX-ACCESS read-write
     STATUS current
    DESCRIPTION
    "Allows configuration of SuperG3 fax processing upon detection of the V21 CM or V.8 data signal.
     When disabled,   the MTA still detects the signaling for SuperG3 fax and the signal is used to
     setup the endpoint for SuperG3 pass-thru fax transmission via G711. When enabled the MTA handles
     the detection of SuperG3 signaling to trigger the start of T.38 process. The negotiation during
     call setup determines whether or not T.38 can be used to send the fax."
    DEFVAL { disable }
     ::= { arrisMtaDevOperationalSetup 43 }

arrisMtaDevDTMFEndEventForceAscending OBJECT-TYPE
     SYNTAX INTEGER {
         disable(0),
         enable(1)
     }
     MAX-ACCESS read-write
     STATUS current
     DESCRIPTION
        "Used to enable/disable RFC 2833 DTMF end event duration force ascending."
     DEFVAL { disable }
     ::= { arrisMtaDevOperationalSetup 44 }

arrisMtaDevDspHandleBellModemTone OBJECT-TYPE
     SYNTAX INTEGER {
         disable(0),
         enable(1)
     }
     MAX-ACCESS read-write
     STATUS current
     DESCRIPTION
         "Set the DSP to detect the Bell Modem Tone (2225kHz).  The Bell Modem Tone is
          frequently used by older data modems, usually in low speed setups.  When this
          MIB is set to enable(1), the DSP will detect the Bell Modem Tone from either the
          local or network end.  When this MIB is set to disable(0), the tone will be ignored."
     DEFVAL { disable }
     ::= { arrisMtaDevOperationalSetup 45 }

arrisMtaDevDhcpSubOpt3Immediate OBJECT-TYPE
     SYNTAX INTEGER {
         off(1),
         on(2)
     }
     MAX-ACCESS read-write
     STATUS current
     DESCRIPTION
         "This MIB object will control the comparison/handling of MTA DHCP Opt 122 SubOpt 3.
         A value of off(1) will disable DHCP option 122 suboption 3 comparison/handling on the fly.
         A value of on(2) will enable DHCP option 122 suboption 3 comparison/handling on the fly.
         SNMP notifications will be sent to the new Provisioning SNMP Entity.
         The default value is off(1)."
     DEFVAL { off }
     ::= { arrisMtaDevOperationalSetup 46 }


arrisMtaDevMaxCallPServiceFlows OBJECT-TYPE
     SYNTAX Integer32(0..64)
     MAX-ACCESS read-write
     STATUS current
     DESCRIPTION
         "Used to limit the number of calls (service flows). Outgoing calls, incoming calls,
          and conference call legs are included in this count. The EMTA ports are able to
          call each other without this limitation. Default value 0 means disable this feature."
     DEFVAL { 0 }
     ::= { arrisMtaDevOperationalSetup 47 }

--
-- The following MIBs control HD Voice Options
--

arrisMtaDevHDAudioDefaultPayloadType OBJECT-TYPE
     SYNTAX  INTEGER {
        static(0),
        dynamic(1)
     }
    MAX-ACCESS read-write
     STATUS current
    DESCRIPTION
         "The setting of this MIB provisions the MTA to offer the G722 codec with the defined
          static payload of (9)or a payload in the dynamic range of (96-127). This MIB setting is persistent."
     DEFVAL { static }
     ::= { arrisMtaDevOperationalSetup  49}

arrisMtaDevWBSLIC   OBJECT-TYPE
     SYNTAX  INTEGER    {
        disable(0),
        enable(1)
     }
     MAX-ACCESS read-write
     STATUS current
     DESCRIPTION
         "The setting of this MIB sets the SLIC and DSP to WB mode. This MIB setting is persistent.
         This MIB should be set from the CM configuration file. If this MIB value is altered in the
         CM configuration file then the modem will reboot automatically after the change is applied.
         A SNMP set after provisioning will take effect after the next reboot."
     DEFVAL { disable }
     ::= { arrisMtaDevOperationalSetup  50}

arrisMtaDevProvisionedCodecArray OBJECT-TYPE
 SYNTAX DisplayString
 MAX-ACCESS read-write
 STATUS current
 DESCRIPTION
  "This is the list of codecs offered in the SDP as well as codecs returned in capabilities
  for an AUEP response.
  This MIB is only used with NCS signaling.
   These are entered as a string separated by semi-colon ';' or comma ',' for example
   'PCMU;PCMA;G726-32;telephone-event'.
   This object should only be changed by the configuration file.

   The default string will be NULL. A NULL string will result in consistent operation to previous
   FW releases where all supported codecs are listed. "
 ::= { arrisMtaDevOperationalSetup 51 }

arrisMtaDevHDAudioG722SampleRate   OBJECT-TYPE
     SYNTAX  INTEGER    {
        rate8000(0),
        rate16000(1),
        rateDynamic(2)
     }
     MAX-ACCESS read-write
     STATUS current
     DESCRIPTION
         "This MIB controls the SampleRate advertised in the rtpmap for the HD codec G722.
         The actual sample rate is 16000 however for backward compatibility with RFC 1890
         the default is 8000. The dynamic selection is to set the sample rate to the same
         value received in SDP for the G722 codec.

         Examples:
             a=rtpmap: 99 G722-64/8000
             a=rtpmap: 99 G722-64/16000"
     DEFVAL { rate8000 }
     ::= { arrisMtaDevOperationalSetup  52}

arrisMtaDevHDAudioEnable OBJECT-TYPE
     SYNTAX  INTEGER {
        disable(0),
        enable(1)
     }
    MAX-ACCESS read-write
     STATUS current
    DESCRIPTION
         "The setting of this MIB enables the MTA to support HD Audio codecs such as G722."
     DEFVAL { enable }
     ::= { arrisMtaDevOperationalSetup  53}

arrisMtaDevRtcpJitterDisabled OBJECT-TYPE
     SYNTAX  INTEGER {
        off(0),
        on(1)
     }
    MAX-ACCESS read-write
     STATUS current
    DESCRIPTION
         "The setting of this MIB disables the MTA to report the real Jitter value in the RTCP packet."
     DEFVAL { off }
     ::= { arrisMtaDevOperationalSetup  54}

arrisMtaDevDiagLoopTable OBJECT-TYPE
     SYNTAX SEQUENCE OF ArrisMtaDevDiagLoopEntry
     MAX-ACCESS not-accessible
     STATUS current
     DESCRIPTION
         "Arris Touchstone specific per line loop diagnostic details"
     ::= { arrisMtaDevDiag 1 }

arrisMtaDevDiagLoopEntry OBJECT-TYPE
     SYNTAX ArrisMtaDevDiagLoopEntry
     MAX-ACCESS not-accessible
     STATUS current
     DESCRIPTION
         "Each end point entry represents one telephone line"
     INDEX { arrisMtaDevDiagLoopIndex }
     ::= { arrisMtaDevDiagLoopTable 1 }

ArrisMtaDevDiagLoopEntry ::= SEQUENCE {
     arrisMtaDevDiagLoopIndex Integer32,
     arrisMtaDevDiagLoopTime DisplayString,
     arrisMtaDevDiagLoopRequest TruthValue,
     arrisMtaDevDiagLoopLastResult INTEGER,
     arrisMtaDevDiagLoopHazardousPotentialTest DisplayString,
     arrisMtaDevDiagLoopForeignEmfTest DisplayString,
     arrisMtaDevDiagLoopResistiveFaultsTest DisplayString,
     arrisMtaDevDiagLoopReceiverOffHookTest DisplayString,
     arrisMtaDevDiagLoopRingerTest DisplayString }

arrisMtaDevDiagLoopIndex OBJECT-TYPE
     SYNTAX Integer32
     MAX-ACCESS not-accessible
     STATUS current
     DESCRIPTION "The unique value which identifies the port."
     ::= { arrisMtaDevDiagLoopEntry 1 }


arrisMtaDevDiagLoopTime OBJECT-TYPE
     SYNTAX DisplayString
     MAX-ACCESS read-only
     STATUS current
     DESCRIPTION "Reports the time & date when loop diagnostics
                  were last run on the selected line. (Patent Pending)"
     ::= { arrisMtaDevDiagLoopEntry 2 }

arrisMtaDevDiagLoopRequest OBJECT-TYPE
     SYNTAX TruthValue
     MAX-ACCESS read-write
     STATUS current
     DESCRIPTION "Setting this value to true will send a
                  diagnostics request on the line.  Reading this
                  value will always return false.  The
                  maintenance state of the line indicates
                  if diagnostics are being run on the line.
                  Note: Currently supported on TM402 only. (Patent Pending)"
     ::= { arrisMtaDevDiagLoopEntry 3 }

arrisMtaDevDiagLoopLastResult OBJECT-TYPE
     SYNTAX INTEGER{diagnostics-passed(1),hazardous-potential-test-failure(2),
                    foreign-emf-test-failure(3),resistive-faults-test-failure(4),
                    receiver-offhook-test-failure(5), ringer-test-failure(6),
                    invalid-state-to-init-diags(7), line-is-unprovisioned(8),
                    diagnostics-results-pending(9), not-started(10),
                    unsupported(11), ringer-test-warning(12) }
     MAX-ACCESS read-only
     STATUS current
     DESCRIPTION "Start loop diag testing with arrisMtaDevDiagLoopRequest.
                  Thereafter reading this MIB provides current status.  When testing
                  is complete, the status will be either all-loop-diags-passed
                  or the first test failed will be indicated. (Patent Pending)"
     ::= { arrisMtaDevDiagLoopEntry 4 }

arrisMtaDevDiagLoopHazardousPotentialTest OBJECT-TYPE
     SYNTAX DisplayString
     MAX-ACCESS read-only
     STATUS current
     DESCRIPTION "Displays the hazardous-potential-test result for the last
                  time that loop diags were run. (Patent Pending)"
     ::= { arrisMtaDevDiagLoopEntry 5 }

arrisMtaDevDiagLoopForeignEmfTest OBJECT-TYPE
     SYNTAX DisplayString
     MAX-ACCESS read-only
     STATUS current
     DESCRIPTION "Displays the foreign-emf-test result for the last
                  time that loop diags were run. (Patent Pending)"
     ::= { arrisMtaDevDiagLoopEntry 6 }

arrisMtaDevDiagLoopResistiveFaultsTest OBJECT-TYPE
     SYNTAX DisplayString
     MAX-ACCESS read-only
     STATUS current
     DESCRIPTION "Displays the resistive-faults-test result for the last
                  time that loop diags were run. (Patent Pending)"
     ::= { arrisMtaDevDiagLoopEntry 7 }

arrisMtaDevDiagLoopReceiverOffHookTest OBJECT-TYPE
     SYNTAX DisplayString
     MAX-ACCESS read-only
     STATUS current
     DESCRIPTION "Displays the receiver-offhook-test result for the last
                  time that loop diags were run. (Patent Pending)"
     ::= { arrisMtaDevDiagLoopEntry 8 }

arrisMtaDevDiagLoopRingerTest OBJECT-TYPE
     SYNTAX DisplayString
     MAX-ACCESS read-only
     STATUS current
     DESCRIPTION "Displays the ringer-test result for the last
                  time that loop diags were run. (Patent Pending)"
     ::= { arrisMtaDevDiagLoopEntry 9 }

arrisMtaDevCmIpTable OBJECT-TYPE
    SYNTAX     SEQUENCE OF ArrisMtaDevCmIpEntry
    MAX-ACCESS not-accessible
    STATUS     current
    DESCRIPTION
           "The ARRIS proprietary IP Address table used for getting
           CM IP address and physical address from MTA."
    ::= { arrisMtaDevCmIp 1 }

arrisMtaDevCmIpEntry OBJECT-TYPE
    SYNTAX     ArrisMtaDevCmIpEntry
    MAX-ACCESS not-accessible
    STATUS     current
    DESCRIPTION
           "Each entry contains one IP address and one physical address."
    INDEX       { arrisMtaDevCmIpIndex }
    ::= { arrisMtaDevCmIpTable 1 }

ArrisMtaDevCmIpEntry ::= SEQUENCE {
        arrisMtaDevCmIpIndex         Integer32,
        arrisMtaDevCmIpAddressType   InetAddressType,
        arrisMtaDevCmIpAddress       InetAddress,
        arrisMtaDevCmIpPhysAddress   PhysAddress
    }

arrisMtaDevCmIpIndex OBJECT-TYPE
    SYNTAX     Integer32 (0..0)
    MAX-ACCESS not-accessible
    STATUS     current
    DESCRIPTION
           "Index used to order the arrisMtaDevCmIpTable entries.
           Currently, CM only supports single IP address, thus
           there would be no more than 1 entry in arrisMtaDevCmIpTable"
    ::= { arrisMtaDevCmIpEntry 1 }

arrisMtaDevCmIpAddressType OBJECT-TYPE
    SYNTAX     InetAddressType
    MAX-ACCESS read-only
    STATUS     current
    DESCRIPTION
           "The type of arrisMtaDevCmIpAddress."
    ::= { arrisMtaDevCmIpEntry 2 }

arrisMtaDevCmIpAddress OBJECT-TYPE
    SYNTAX     InetAddress
    MAX-ACCESS read-only
    STATUS     current
    DESCRIPTION
           "The CM IP address."
    ::= { arrisMtaDevCmIpEntry 3 }

arrisMtaDevCmIpPhysAddress OBJECT-TYPE
    SYNTAX     PhysAddress (SIZE(0..65535))
    MAX-ACCESS read-only
    STATUS     current
    DESCRIPTION
           "The CM physical address."
    ::= { arrisMtaDevCmIpEntry 4 }

arrisMtaDevEndPntTable OBJECT-TYPE
     SYNTAX SEQUENCE OF ArrisMtaDevEndPntEntry
     MAX-ACCESS not-accessible
     STATUS current
     DESCRIPTION
         "Arris Touchstone specific per line provisioning details"
     ::= { arrisMtaDevEndPntSetup 3 }

arrisMtaDevEndPntEntry OBJECT-TYPE
     SYNTAX ArrisMtaDevEndPntEntry
     MAX-ACCESS not-accessible
     STATUS current
     DESCRIPTION
         "Each end point entry represents one telephone line"
     INDEX { arrisMtaDevEndPntIndex }
     ::= { arrisMtaDevEndPntTable 1 }

ArrisMtaDevEndPntEntry ::= SEQUENCE {
     arrisMtaDevEndPntIndex Integer32,
     arrisMtaDevEndPntDialingMethod INTEGER,
     arrisMtaDevEndPntRingingWaveform INTEGER,
     arrisMtaDevEndPntFaxOnlyLineTimeout Integer32,
     arrisMtaDevPersistentLineStatus INTEGER,
     arrisMtaDevEndPntCallWaitingRepeatSteady INTEGER,
     arrisMtaDevEndPntCIDEnable INTEGER,
     arrisMtaDevEndPntCIDNameEnable INTEGER,
     arrisMtaDevEndPntCIDDateTimeEnable INTEGER,
     arrisMtaDevEndPntLoopReversal INTEGER,
     arrisMtaDevEndPntGainControlTxVoice INTEGER,
     arrisMtaDevEndPntGainControlRxVoice INTEGER,
     arrisMtaDevEndPntHDAudioEnable INTEGER,
     arrisMtaDevEndPntHDAudioStatus INTEGER,
     arrisMtaDevEndPntCallPState INTEGER
}

arrisMtaDevEndPntIndex OBJECT-TYPE
 SYNTAX Integer32
 MAX-ACCESS not-accessible
 STATUS current
 DESCRIPTION "The unique value which identifies the port."
 ::= { arrisMtaDevEndPntEntry 1 }

arrisMtaDevEndPntDialingMethod OBJECT-TYPE
 SYNTAX INTEGER { tone(1), pulse(2), toneAndPulse(3), pulseWithDTMFRelay(4), toneAndPulseWithDTMFRelay(5) }
 MAX-ACCESS read-write
 STATUS current
 DESCRIPTION "Indicates the method used to dial the digits for this telephony
              endpoint.  If tone(1), tone dialing (DTMF) is used. If pulse(2),
              dial-pulse signaling is used to dial the digits, Tone dialing(DTMF) is
              disabled. If Tone & Pulse(3), tone dialing(DTMF) and dial-pulse signaling
              is used to dial the digits. If Pulse with DTMF relay(4), Tone dialing(DTMF)
              is disabled, and pulse dialed digits will be relayed in-band to the media
              gateway.  If Tone & Pulse with DTMF relay(5), Tone dialing (DTMF) is enable,
              and pulse dialed digits will be relayed in-band to the media gateway.
              NOTE: (4) & (5) will require IPDT solution as well as DTMF support by the
              Media gateway. The default value for this object is tone(1)."
 DEFVAL { tone }
 ::= { arrisMtaDevEndPntEntry 24 }

arrisMtaDevEndPntRingingWaveform OBJECT-TYPE
 SYNTAX INTEGER { normal(1), sinusoidal(2) }
 MAX-ACCESS read-write
 STATUS current
 DESCRIPTION "Indicates the voltage waveform used when ringing this telephony
              endpoint.  If normal(1) is used the standard waveform will be applied.
              If sinusoidal(2) is specified, extra waveshaping will be performed.  This
              is for use with telephones that exhibit increased sensitivity to the ring
              voltage waveform.  The default value for this object is normal(1)."
 DEFVAL { normal }
 ::= { arrisMtaDevEndPntEntry 25 }

arrisMtaDevEndPntFaxOnlyLineTimeout OBJECT-TYPE
 SYNTAX Integer32 (0..600)
 MAX-ACCESS read-write
 STATUS current
 DESCRIPTION
  "This object is used to define a line as a fax only line for NCS.  The default value of the
   object is zero which means no timeout.  When the object is set to a non-zero value
   a timer is started after the RTP mode becomes sendReceive.  If this timer pops without
   having received fax/modem tones on the connection the call will be dropped.  Its
   units are in seconds."
 DEFVAL { 0 }
 ::= { arrisMtaDevEndPntEntry 26 }

arrisMtaDevPersistentLineStatus OBJECT-TYPE
 SYNTAX INTEGER {
		 ignore(0),
     forceDisable(1)
	 }
     MAX-ACCESS read-write
     STATUS current
    DESCRIPTION
       "Set persistent line status. This MIB and the ifAdminStatus MIB impact the
	   line status.  If ignore(0) is set, the line status will be based on the
	   setting of ifAdminStatus in the MTA Config File.  If ifAdminStatus is
	   not set in the MTA Config File, then the ifAdminStatus will be set to the
	   default value.  The default value is up(1) if the line is provisioned and
	   down(2) if the line is not provisioned.
	   If this MIB is set to forceDisable(1), the service status of the line is set to
	   DOWN and the line state is set to EP_OOS after a reset.  This MIB is always
	   ignored in a Config File. This MIB will be set to ignore(0) if the
	   arrisMtaDevRestoreNvmFactoryDefault is set to clear(1)."
    DEFVAL { ignore }
     ::= { arrisMtaDevEndPntEntry 27 }

arrisMtaDevEndPntCallWaitingRepeatSteady OBJECT-TYPE
 SYNTAX INTEGER {
		 disable(0),
               enable(1)
	 }
     MAX-ACCESS read-write
     STATUS current
    DESCRIPTION
       "When enabled(1), it indicates that the call waiting tone should repeat forever.
       If disabled(0), it concludes using the finite rules."
    DEFVAL { disable }
     ::= { arrisMtaDevEndPntEntry 28 }

arrisMtaDevEndPntCIDEnable OBJECT-TYPE
 SYNTAX INTEGER {
         disable(0),
         enable(1)
	 }
     MAX-ACCESS read-write
     STATUS current
    DESCRIPTION
       "Used to enable/disable the All the Caller ID field send to phone.
       If it's diabled, no Caller ID information will be sent."
    DEFVAL { enable }
     ::= { arrisMtaDevEndPntEntry 29 }

arrisMtaDevEndPntCIDNameEnable OBJECT-TYPE
 SYNTAX INTEGER {
         disable(0),
         enable(1)
	 }
     MAX-ACCESS read-write
     STATUS current
    DESCRIPTION
       "Used to enable/disable the Name part of CallerID field send to phone."
    DEFVAL { enable }
     ::= { arrisMtaDevEndPntEntry 30 }

arrisMtaDevEndPntCIDDateTimeEnable OBJECT-TYPE
 SYNTAX INTEGER {
         disable(0),
         enable(1)
	 }
     MAX-ACCESS read-write
     STATUS current
    DESCRIPTION
       "Used to enable/disable the Date/Time part of CallerID field send to phone."
    DEFVAL { enable }
     ::= { arrisMtaDevEndPntEntry 31 }

arrisMtaDevEndPntLoopReversal OBJECT-TYPE
 SYNTAX INTEGER {
		 disable(0),
               enable(1)
	 }
     MAX-ACCESS read-write
     STATUS current
    DESCRIPTION
       "This mib is used to manage loop polarity/reversal. When enabled(1), it indicates that
       the line should be reversed to normal once the originating party hangs up first.
       If disabled(0), the loop keeps on being reversed while the originating party hangs up."
    DEFVAL { disable }
     ::= { arrisMtaDevEndPntEntry 32 }

arrisMtaDevEndPntGainControlTxVoice OBJECT-TYPE
     SYNTAX INTEGER{
         dBm16(16),
         dBm15(15),
         dBm14(14),
         dBm13(13),
         dBm12(12),
         dBm11(11),
         dBm10(10),
         dBm9(9),
         dBm8(8),
         dBm7(7),
         dBm6(6),
         dBm5(5),
         dBm4(4),
         dBm3(3),
         dBm2(2),
         dBm1(1),
         dBm0(0),
         dBm-1(-1),
         dBm-2(-2),
         dBm-3(-3),
         dBm-4(-4),
         dBm-5(-5),
         dBm-6(-6),
         dBm-7(-7),
         dBm-8(-8),
         dBm-9(-9),
         dBm-10(-10),
         dBm-11(-11),
         dBm-12(-12),
         dBm-13(-13),
         dBm-14(-14),
         dBm-15(-15),
         dBm-16(-16),
         disabled(-128)
     }
     MAX-ACCESS read-write
     STATUS current
     DESCRIPTION
         "The transmit digital gain adjustment (dBm) for voice for a specific endpoint.
          When set to a value other than disabled(-128), this MIB supersedes the
          arrisMtaDevGainControlTxVoice MIB.  A value of 2 increases
          the voice level by 2 dBm. A value of -2 decreases the voice level by 2 dBm. This
          value does not effect the levels of local tones or FSK.
          Setting this MIB to disabled(-128) will disable this MIB and the Tx Voice Gain will
          now be set by the arrisMtaDevGainControlTxVoice  MIB.
          NOTE: Use caution when changing this MIB. Increasing or decreasing the voice level
          by the larger numbers allowed in the range may compromise voice quality."
     DEFVAL { 0 }
     ::= { arrisMtaDevEndPntEntry 33 }

arrisMtaDevEndPntGainControlRxVoice OBJECT-TYPE
     SYNTAX INTEGER {
         dBm16(16),
         dBm15(15),
         dBm14(14),
         dBm13(13),
         dBm12(12),
         dBm11(11),
         dBm10(10),
         dBm9(9),
         dBm8(8),
         dBm7(7),
         dBm6(6),
         dBm5(5),
         dBm4(4),
         dBm3(3),
         dBm2(2),
         dBm1(1),
         dBm0(0),
         dBm-1(-1),
         dBm-2(-2),
         dBm-3(-3),
         dBm-4(-4),
         dBm-5(-5),
         dBm-6(-6),
         dBm-7(-7),
         dBm-8(-8),
         dBm-9(-9),
         dBm-10(-10),
         dBm-11(-11),
         dBm-12(-12),
         dBm-13(-13),
         dBm-14(-14),
         dBm-15(-15),
         dBm-16(-16),
         disabled(-128)
         }
     MAX-ACCESS read-write
     STATUS current
     DESCRIPTION
         "The transmit digital gain adjustment (dBm) for voice for a specific endpoint.
          When set to a value other than disabled(-128), this MIB supersedes the
          arrisMtaDevGainControlRxVoice MIB.  A value of 2 increases
          the voice level by 2 dBm. A value of -2 decreases the voice level by 2 dBm. This
          value does not effect the levels of local tones or FSK.
          Setting this MIB to disabled(-128) will disable this MIB and the Rx Voice Gain will
          now be set by the arrisMtaDevGainControlRxVoice  MIB.
          NOTE: Use caution when changing this MIB. Increasing or decreasing the voice level
          by the larger numbers allowed in the range may compromise voice quality."
     DEFVAL { 0 }
     ::= { arrisMtaDevEndPntEntry 34 }

arrisMtaDevEndPntHDAudioEnable OBJECT-TYPE
 SYNTAX INTEGER {
		 disable(0),
        enable(1)
	 }
     MAX-ACCESS read-write
     STATUS current
    DESCRIPTION
       "The setting of this MIB sets an individual line to support HD Audio codecs such as G722.
       The MTA MIB setting for arrisMtaDevHDAudioEnable can override the individual line setting.
       This MIB is persistent when modified post provisioning."
    DEFVAL { enable }
     ::= { arrisMtaDevEndPntEntry 35 }

arrisMtaDevEndPntHDAudioStatus OBJECT-TYPE
 SYNTAX INTEGER {
		 disabled(0),
        enabled(1),
        notprovisioned(2)
	 }
     MAX-ACCESS read-only
     STATUS current
    DESCRIPTION
       "Use this MIB to read the effective status of HD Audio for an endpoint."
     ::= { arrisMtaDevEndPntEntry 36 }

arrisMtaDevEndPntCallPState OBJECT-TYPE
     SYNTAX INTEGER{
    none(0),
    out-of-service(1),
    redialing(2),
    idle(3),
    predial(4),
    dialing(5),
    calling(6),
    ringing(7),
    connected(8),
    waithook(9),
    connected-alerting(10),
    call-waiting(11),
    three-way-calling(12),
    conference(13),
    predial-holding(14),
    dialing-holding(15),
    calling-holding(16),
    waithook-holding(17),
    waithook-alerting(18),
    flash-digit(19),
    stranded-call(20),
    conf-before-answer(21),
    autocall-ringing(22),
    emergency-inject(23),
    wait-reg(24),
    restart(25),
    disconnected(26),
    inservice(27)
     }
     MAX-ACCESS read-only
     STATUS current
    DESCRIPTION
       "Use this MIB to read the status of callp state"
     ::= { arrisMtaDevEndPntEntry 37 }

arrisMtaDevBatteryChargerFWRev OBJECT-TYPE
     SYNTAX SnmpAdminString
     MAX-ACCESS read-only
     STATUS current
     DESCRIPTION
         "The firmware rev of the battery charger."
     ::= { arrisMtaDevPwrSupplyBase 1 }

arrisMtaDevPwrSupplyBatteryTestTime OBJECT-TYPE
     SYNTAX INTEGER
     MAX-ACCESS read-only
     STATUS current
     DESCRIPTION
         "The present value of the Test Timer Scheduler expressed in days.  If the value
          read is 0xFF (255), the timer has been paused."
     ::= { arrisMtaDevPwrSupplyStats 4 }

arrisMtaDevPwrSupplyRatedBatCapacity OBJECT-TYPE
     SYNTAX INTEGER
     MAX-ACCESS read-only
     STATUS current
     DESCRIPTION
         "The rated capacity of the battery that is currently installed.  The value is
          expressed in units of energy (10 watt*minutes/count), rather than charge
          (amp*hours)."
     ::= { arrisMtaDevPwrSupplyStats 5 }

arrisMtaDevPwrSupplyTestedBatCapacity OBJECT-TYPE
     SYNTAX INTEGER
     MAX-ACCESS read-only
     STATUS current
     DESCRIPTION
         "The measured battery capacity expressed in 10 watt*minutes/count as determined
          by the last battery test cycle."
     ::= { arrisMtaDevPwrSupplyStats 6 }

arrisMtaDevPwrSupplyBatStateOfCharge OBJECT-TYPE
     SYNTAX INTEGER
     MAX-ACCESS read-only
     STATUS current
     DESCRIPTION
         "The present battery state of charge expressed in 10 watt*minutes/count.
          This value is approximate and is re-calibrated following a battery test cycle."
     ::= { arrisMtaDevPwrSupplyStats 7 }

arrisMtaDevPwrSupplyReadBatteryPwr OBJECT-TYPE
     SYNTAX INTEGER
     MAX-ACCESS read-only
     STATUS current
     DESCRIPTION
         "The present load power expressed in 50mW/count and is an eight-second
          moving average. This is the power being removed or applied to the battery.
          Power is being removed while AC is not present or during the battery test.
          Power is being applied if battery is being charged."
     ::= { arrisMtaDevPwrSupplyStats 8 }

arrisMtaDevPwrSupplySecondsOnBattery OBJECT-TYPE
     SYNTAX INTEGER
     MAX-ACCESS read-only
     STATUS current
     DESCRIPTION
         "The present value of time expired since AC Failed and running on the battery."
     ::= { arrisMtaDevPwrSupplyStats 9 }

arrisMtaDevPwrSupplyBatRatedMinutes OBJECT-TYPE
     SYNTAX INTEGER
     UNITS "minutes"
     MAX-ACCESS read-only
     STATUS current
     DESCRIPTION
         "An estimate of the rated run-time on the battery based upon the unit's
          typical idle power and the rated capacity of the battery when fully charged."
     ::= { arrisMtaDevPwrSupplyStats 10 }

arrisMtaDevPwrSupplyBatAvailableMinutes OBJECT-TYPE
     SYNTAX INTEGER
     UNITS "minutes"
     MAX-ACCESS read-only
     STATUS current
     DESCRIPTION
         "An estimate of the available run-time on the battery based upon the unit's
          typical idle power and the tested capacity of the battery when fully charged."
     ::= { arrisMtaDevPwrSupplyStats 11 }

arrisMtaDevPwrSupplySecondsOnBattery2 OBJECT-TYPE
     SYNTAX INTEGER
     MAX-ACCESS read-only
     STATUS current
     DESCRIPTION
         "Same as arrisMtaDevPwrSupplySecondsOnBattery but for 2nd battery."
     ::= { arrisMtaDevPwrSupplyStats 12 }

arrisMtaDevPwrSupplyBatRatedMinutes2 OBJECT-TYPE
     SYNTAX INTEGER
     UNITS "minutes"
     MAX-ACCESS read-only
     STATUS current
     DESCRIPTION
         "Same as arrisMtaDevPwrSupplyBatRatedMinutes but for 2nd battery."
     ::= { arrisMtaDevPwrSupplyStats 13 }

arrisMtaDevPwrSupplyBatAvailableMinutes2 OBJECT-TYPE
     SYNTAX INTEGER
     UNITS "minutes"
     MAX-ACCESS read-only
     STATUS current
     DESCRIPTION
         "Same as arrisMtaDevPwrSupplyBatAvailableMinutes but for 2nd battery."
     ::= { arrisMtaDevPwrSupplyStats 14 }

arrisMtaDevPwrSupplyTelemetryValues OBJECT-TYPE
     SYNTAX SnmpAdminString
     MAX-ACCESS read-only
     STATUS current
     DESCRIPTION
         "Power Supply Telemetry Values.  Fields are delimited by semicolons."
     ::= { arrisMtaDevPwrSupplyStats 15 }


ac-Fail                        OBJECT IDENTIFIER ::= { arrisMtaDevPwrSupplyAlarm  1 }

chargerOverTemp-Shutdown       OBJECT IDENTIFIER ::= { arrisMtaDevPwrSupplyAlarm  2 }

chargerTemperature-High        OBJECT IDENTIFIER ::= { arrisMtaDevPwrSupplyAlarm  3 }

batteryCharger-Disabled        OBJECT IDENTIFIER ::= { arrisMtaDevPwrSupplyAlarm  4 }

chargerDownload-Failed         OBJECT IDENTIFIER ::= { arrisMtaDevPwrSupplyAlarm  5 }

battery-Mismatch               OBJECT IDENTIFIER ::= { arrisMtaDevPwrSupplyAlarm  6 }

upsAlarmBatteryBad             OBJECT IDENTIFIER ::= { arrisMtaDevPwrSupplyAlarm  7 }

upsAlarmLowBattery             OBJECT IDENTIFIER ::= { arrisMtaDevPwrSupplyAlarm  8 }

upsAlarmDepletedBattery        OBJECT IDENTIFIER ::= { arrisMtaDevPwrSupplyAlarm  9 }

upsAlarmUpsOutputOff           OBJECT IDENTIFIER ::= { arrisMtaDevPwrSupplyAlarm  10 }

upsAlarmOutputOffAsRequested   OBJECT IDENTIFIER ::= { arrisMtaDevPwrSupplyAlarm  11 }

upsAlarmGeneralFault           OBJECT IDENTIFIER ::= { arrisMtaDevPwrSupplyAlarm  12 }

upsAlarmShutdownImminent       OBJECT IDENTIFIER ::= { arrisMtaDevPwrSupplyAlarm  13 }

upsAlarmBatteryMissing         OBJECT IDENTIFIER ::= { arrisMtaDevPwrSupplyAlarm  14 }

upsAlarmAwaitingPower          OBJECT IDENTIFIER ::= { arrisMtaDevPwrSupplyAlarm  15 }

upsAlarmShutdownPending        OBJECT IDENTIFIER ::= { arrisMtaDevPwrSupplyAlarm  16 }


arrisMtaDevBatteryStatusTable OBJECT-TYPE
     SYNTAX SEQUENCE OF ArrisMtaDevBatteryStatusEntry
     MAX-ACCESS not-accessible
     STATUS current
     DESCRIPTION
         "The Power Supply Telemetry table ...There will be one row in this
          table for each battery pack in the device"
     ::= { arrisMtaDevPwrSupplyStats 3 }

arrisMtaDevBatteryStatusEntry OBJECT-TYPE
     SYNTAX ArrisMtaDevBatteryStatusEntry
     MAX-ACCESS not-accessible
     STATUS current
     DESCRIPTION
         "Status information for a single battery pack.  An entry in this
          table exists for each battery pack contained in the device."
     INDEX { arrisMtaDevBatteryStatusIndex }
     ::= { arrisMtaDevBatteryStatusTable 1 }

ArrisMtaDevBatteryStatusEntry ::= SEQUENCE {
     arrisMtaDevBatteryStatusIndex INTEGER,
     arrisMtaDevBatteryOperState INTEGER,
     arrisMtaDevBatteryLastStateChange TimeStamp,
     arrisMtaDevBatteryOperSubState SnmpAdminString,
     arrisMtaDevBatteryOrderingCode SnmpAdminString,
     arrisMtaDevBatteryEprom SnmpAdminString
}

arrisMtaDevBatteryStatusIndex OBJECT-TYPE
     SYNTAX INTEGER
     MAX-ACCESS not-accessible
     STATUS current
     DESCRIPTION
         "An index value that uniquely identifies each battery pack
          in the MTA device.  The table index ...."
     ::= { arrisMtaDevBatteryStatusEntry 1 }

arrisMtaDevBatteryOperState OBJECT-TYPE
     SYNTAX INTEGER {
         unavailable(0),
         invalid(1),
         shutdownWarning(2),
         batteryReversedShorted(3),
         batteryLow-replaceBattery-acFail(4),
         batteryLow-replaceBattery(5),
         batteryLow-acFail(6),
         batteryLow(7),
         batteryMissing(8),
         acFail-replaceBattery(9),
         replaceBattery(10),
         acFail(11),
         normal(12),
         testInProgress(13),
         chargerFailure(14)
     }
     MAX-ACCESS read-only
     STATUS current
     DESCRIPTION
         "Indicates the current operational state of the battery."
     ::= { arrisMtaDevBatteryStatusEntry 2 }

arrisMtaDevBatteryLastStateChange OBJECT-TYPE
     SYNTAX TimeStamp
     MAX-ACCESS read-only
     STATUS current
     DESCRIPTION
         "The value of sysUpTime at the time the battery entered its
          current operational state.  If the current state was entered
          prior to the last re-initialization of the local network management
          subsystem, then this object contains a zero value."
     ::= { arrisMtaDevBatteryStatusEntry 3 }

arrisMtaDevBatteryOperSubState OBJECT-TYPE
     SYNTAX SnmpAdminString
     MAX-ACCESS read-only
     STATUS current
     DESCRIPTION
         "Indicates the current sub-state of the battery.  This info
          is not designed to match the arrisMtaDevBatteryOperState but to
          provide additional information as to the UPS Status."
     ::= { arrisMtaDevBatteryStatusEntry 4 }

arrisMtaDevBatteryOrderingCode OBJECT-TYPE
     SYNTAX SnmpAdminString
     MAX-ACCESS read-only
     STATUS current
     DESCRIPTION
         "The Arris ordering code for the battery(s) currently installed."
     ::= { arrisMtaDevBatteryStatusEntry 5 }

arrisMtaDevBatteryEprom OBJECT-TYPE
     SYNTAX SnmpAdminString
     MAX-ACCESS read-only
     STATUS current
     DESCRIPTION
         "Battery EPROM information for the battery(s) currently installed."
     ::= { arrisMtaDevBatteryStatusEntry 6 }

arrisMtaDevPwrSupplyEnableDataShutdown OBJECT-TYPE
     SYNTAX  INTEGER {
         enabled(1),
         disabled(2)
     }
     MAX-ACCESS read-write
     STATUS current
     DESCRIPTION ""
     DEFVAL { disabled }
     ::= { arrisMtaDevPwrSupplyControl 1 }
arrisMtaDevPwrSupplyEnableWifiShutdown OBJECT-TYPE
     SYNTAX  INTEGER {
     		 disabled(0),
         enabled(1)
     }
     MAX-ACCESS read-write
     STATUS current
     DESCRIPTION "This MIB allows WTMx52 modems to shut down its wireless signal for power saving when modem switches to battery power.
     If set this MIB to true, when AC fail and MTA is on Battery power, after about a timeout(specified by arrisMtaDevPwrSupplyDataShutdownTime), wifi signal would be turned off to save power and restored when AC power is on again.
     Note: This MIB only takes affect when arrisMtaDevPwrSupplyEnableDataShutdown is set to disable."
     DEFVAL { disabled }
     ::= { arrisMtaDevPwrSupplyControl 2 }
arrisMtaDevPwrSupplyLowBatteryThresh OBJECT-TYPE
     SYNTAX Integer32
     MAX-ACCESS read-write
     STATUS current
     DESCRIPTION
         "Sets the low battery threshold, which is used to detect a low battery condition.
          The variable is expressed in 10 watt*minutes/count.  The initial default value
          is equivalent to 1 hour of holdup time. (Only available on MODEL 5 and MODEL 6 modems. Not supported on TM508/512)"
     ::= { arrisMtaDevPwrSupplyControl 3 }

arrisMtaDevPwrSupplyTypicalIdlePwr OBJECT-TYPE
     SYNTAX Integer32
     MAX-ACCESS read-only
     STATUS current
     DESCRIPTION
         "The typical Idle power expressed in 50 mw/count.  A typical value is
          loaded upon power up. It is used in conjunction with the Tested Battery Capacity,
          Low Battery Threshold and the Replace Battery Threshold to determine when to
          raise Replace Battery Alarm or the Low Battery Alarm. (Only available on MODEL 5 and MODEL 6 modems. Not supported on TM508/512)"
     ::= { arrisMtaDevPwrSupplyControl 4 }

arrisMtaDevPwrSupplyReplaceBatThresh OBJECT-TYPE
     SYNTAX Integer32
     MAX-ACCESS read-write
     STATUS current
     DESCRIPTION
         "Sets the minimum acceptable battery charge needed to achieve the desired End of
          Life holdup time based on typical Idle Power.  If the Tested Battery Capacity
          minus the Charge Hysteresis loss (20%) is less than this value, the Replace
          Battery alarm will be raised.  The variable is expressed in 10 watt*minutes/count.
          The initial default value provides 1 hour of holdup time. (Only available on MODEL 5 and MODEL 6 modems. Not supported on TM508/512)"
     ::= { arrisMtaDevPwrSupplyControl 5 }

arrisMtaDevPwrSupplyChargeState OBJECT-TYPE
     SYNTAX Integer32
     MAX-ACCESS read-write
     STATUS current
     DESCRIPTION
         "Causes the battery to be charged to the level that is specified by the data.
          The value of charge is expressed in 10 watt*minutes/count.  In order for the
          battery to be charged to the correct level, issuing this command will cause
          the charger to enter a discharge/charge cycle. The initial default value for
          this parameter is 0.8 times the Rated Battery Capacity. This command should
          be used with discretion. (Only available on MODEL 5 and MODEL 6 modems. Not supported on TM508/512)"
     ::= { arrisMtaDevPwrSupplyControl 6 }


arrisMtaDevPwrSupplyBatteryTest OBJECT-TYPE
     SYNTAX INTEGER {
         testScheduled(0),
         disableAutoTesting(1),
         testInProgress(2),
         testPending(3)
     }
     MAX-ACCESS read-write
     STATUS current
     DESCRIPTION
         "This MIB cannot be set on TM402 devices.

          This feature controls the scheduling of the battery test.

          TestScheduled: When written, causes the battery test scheduler to resume at its
          current value.  When read, means that the battery test will run when the scheduled
          time expires.

          DisableAutoTesting: When written, freezes the battery test scheduler at its
          current value.  When read, means that the battery test will never run - with one
          exception. If a battery is removed and replaced, the test will run immediately.
          Once the test completes, the pause status will still be in effect. Therefore,
          the battery test will not run a second time.

          TestInProgress: When written, causes the battery test cycle to start immediately
          and the test scheduler to be reset to its default value of 180 days. This command
          is ignored if there is a test in progress.  When read, means test in progress.

          TestPending: If a battery test is in progress and either: AC power is lost; or a
          full charge is requested - the battery test is paused and the status is reported
          as pending.  This is a read-only value."
     ::= { arrisMtaDevPwrSupplyControl 8 }



arrisMtaDevPwrSupplyConfigRunTime OBJECT-TYPE
     SYNTAX Integer32
     UNITS "minutes"
     MAX-ACCESS read-write
     STATUS current
     DESCRIPTION
         "An estimate of the available run-time on the battery based upon the unit's
          typical idle power and the programmed battery charge setting.  The available
          battery back up time may be adjusted using this value.  By programming the
          run-time to a lower value, the total service life of the battery is extended.
          Increasing the run-time in turn decreases the total service life of the battery.
          Setting this value greater than arrisMtaDevPwrSupplyBatAvailableMinutes will not
          provide a run-time greater than arrisMtaDevPwrSupplyBatAvailableMinutes.  This
          value can only be set to multiples of 5 minutes."
     ::= { arrisMtaDevPwrSupplyControl 9 }



arrisMtaDevPwrSupplyConfigReplaceBatTime OBJECT-TYPE
     SYNTAX Integer32
     UNITS "minutes"
     MAX-ACCESS read-write
     STATUS current
     DESCRIPTION
         "Determines the replace battery threshold in terms of run-time minutes.  If a battery's
          capacity has degraded to a point where it can no longer provide more than x minutes of
          run-time, the Replace Battery condition becomes active. The default value at power up
          is 60 minutes.  This value can only be set to multiples of 5 minutes."
     ::= { arrisMtaDevPwrSupplyControl 10 }



arrisMtaDevPwrSupplyConfigReplaceBatTime2 OBJECT-TYPE
     SYNTAX Integer32
     UNITS "minutes"
     MAX-ACCESS read-write
     STATUS current
     DESCRIPTION
         "Same as arrisMtaDevPwrSupplyConfigReplaceBatTime but for 2nd battery."
     ::= { arrisMtaDevPwrSupplyControl 11 }



arrisMtaDevPwrSupplyOverTempAlarmControl OBJECT-TYPE
     SYNTAX INTEGER {
        disable(0),
        enable(1),
		pendingenable(2),
		pendingdisable(3)
     }
     MAX-ACCESS read-write
     STATUS current
     DESCRIPTION
         "Determines whether an Over Temperature Alarm is issued when the temperature
          specified in arrisMtaDevPwrSupplyOverTempAlarmThreshold is reached.  Also
          determines whether the battery charger shuts down upon reaching 90C.

          For 602 devices and above, this is always Enabled and cannot be set to Disabled.
          For 502/552/504 devices, this is settable to Enabled and Disabled."
     ::= { arrisMtaDevPwrSupplyControl 12 }



arrisMtaDevPwrSupplyOverTempAlarmThreshold OBJECT-TYPE
     SYNTAX Integer32
     UNITS "degrees-C"
     MAX-ACCESS read-write
     STATUS current
     DESCRIPTION
         "Determines temperature threshold for Over Temperature Alarm.  Minimum
          temperature is 50C.  Maximum is 70C."
     ::= { arrisMtaDevPwrSupplyControl 13 }



arrisMtaDevPwrSupplyTemperature OBJECT-TYPE
     SYNTAX SnmpAdminString
     MAX-ACCESS read-only
     STATUS current
     DESCRIPTION
         "The current temperature in degrees C.  This is only available
          when arrisMtaDevPwrSupplyOverTempAlarmControl is enabled."
     ::= { arrisMtaDevPwrSupplyControl 14 }

arrisMtaDevPwrSupplyHiTempBatteryShutdownControl OBJECT-TYPE
     SYNTAX INTEGER {
        disable(0),
        enable(1)
     }
     MAX-ACCESS read-write
     STATUS current
     DESCRIPTION
         "Determines whether the battery will be turned off when the temperature
         reaches 75C and above."
     ::= { arrisMtaDevPwrSupplyControl 15 }

arrisMtaDevPwrSupplyHighestTemperature OBJECT-TYPE
     SYNTAX SnmpAdminString
     MAX-ACCESS read-only
     STATUS current
     DESCRIPTION
         "The highest recorded battery charger temperature in degrees C.  This is only available
          when arrisMtaDevPwrSupplyOverTempAlarmControl is enabled."
     ::= { arrisMtaDevPwrSupplyControl 16 }

arrisMtaDevPwrSupplyHighestTemperatureTime OBJECT-TYPE
     SYNTAX SnmpAdminString
     MAX-ACCESS read-only
     STATUS current
     DESCRIPTION
         "Displays the time and date when the highest temperature was recorded."
     ::= { arrisMtaDevPwrSupplyControl 17 }

arrisMtaDevPwrSupplyHighestTemperatureClear OBJECT-TYPE
     SYNTAX INTEGER {
         clear(1)
     }
     MAX-ACCESS read-write
     STATUS current
     DESCRIPTION
         "Setting this MIB Clears arrisMtaDevPwrSupplyHighestTemperature and
          arrisMtaDevPwrSupplyHighestTemperatureTime. These MIBs will be assigned
          new values in a maximum of 4 seconds when the current temperature is calculated."
     ::= { arrisMtaDevPwrSupplyControl 18 }

 arrisMtaDevPwrSupplyControlChargerReset OBJECT-TYPE
     SYNTAX TruthValue
     MAX-ACCESS read-write
     STATUS current
     DESCRIPTION
         "This MIB object will reset the battery charger when set to true(1).
         Warning:  Resetting the battery charger in an AC Fail condition will immediately
         shutdown the unit.  This MIB object will always return false(2) when read."
     ::= { arrisMtaDevPwrSupplyControl 19 }

arrisMtaDevPwrSupplyDataShutdownTime OBJECT-TYPE
     SYNTAX Integer32
     UNITS "seconds"
     MAX-ACCESS read-write
     STATUS current
     DESCRIPTION
         "Indicates the timeout period, in seconds, that the device will terminate
          data services.  The timer will start upon loss of AC power and operation
          of battery backup begins.  After the timer expires, the device will stop
          providing data services (Ethernet and USB) and shutdown those functions
          to conserve battery capacity. The default value for this object is 15
          minutes(900 seconds) on model7 units, 5 minutes(300 seconds) on 16xx units
          that support 802.11n(1642/62/72), and 1682 and 24xx units which support 802.11ac."
     ::= { arrisMtaDevPwrSupplyTimers 1 }


arrisMtaDevPwrSupplyFullChargeTime OBJECT-TYPE
     SYNTAX  Integer32
     MAX-ACCESS read-write
     STATUS current
     DESCRIPTION
         "Causes the battery to be charged to 100% of its rated voltage and be maintained
          at that level according the number of days set by the data.  After the time has
          elapsed, the battery charge level will be returned to the value specified by
          arrisMtaDevPwrSupplyChargeState.  Range of reported values: 0-16 days.
          Values that can be written range from 1-16 days.  If 1 is written the full charge
          level will be maintained for 1 day.  After that the full charge state will be
          aborted and the battery charge will return to the set charge level or a test
          will resume if one is pending.  (This MIB is only effective on TM5xx and TM6xx HW models)"
     ::= { arrisMtaDevPwrSupplyTimers 2 }




END
