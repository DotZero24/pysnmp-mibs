CADANT-SHOWCM-FORMAT-MIB DEFINITIONS ::= BEGIN

IMPORTS
    OBJECT-TYPE, MODULE-IDENTITY
        FROM SNMPv2-SMI
    DisplayString, RowStatus, TEXTUAL-CONVENTION
        FROM SNMPv2-TC
    cadExperimental
        FROM CADANT-PRODUCTS-MIB;

cadShowCmFormatMib MODULE-IDENTITY
    LAST-UPDATED "201509210000Z"
    ORGANIZATION "Cadant Inc."
    CONTACT-INFO
        "support@arris.com"
    DESCRIPTION "This MIB contains definitions for modifying the output of the
                 show cable modem CLI command"

    REVISION "201509210000Z" -- 2015, 09, 21 = Sept 21, 2015
    DESCRIPTION "Remove obsolete state-docsis20, interface-docsis20; update contact info; add OFDM column types"
    REVISION "201307030000Z" -- 2013, 05, 31 = May 31st, 2013
    DESCRIPTION "Add column ds-last-penalty-time, ds-penalty-count,us-last-penalty-time,us-penalty-count"
    REVISION "201305310000Z" -- 2013, 05, 31 = May 31st, 2013
    DESCRIPTION "Add column tx-pwr"
    REVISION "201112010000Z" -- 2011, 12, 02 = Dec 2nd, 2011
    DESCRIPTION "Add column qos-primary"
    REVISION "201010140000Z" -- 2010, 10, 14 = Oct 14th, 2010
    DESCRIPTION "Add column bonded-actual"
    REVISION "201001280000Z" -- 2010, 01, 28 = Jan 28th, 2010
    DESCRIPTION "Add columns l2vpn-id and l2vpn-qtag"
    REVISION "201001120000Z" -- 2010, 01, 12 = Jan 12th, 2010
    DESCRIPTION "Add column fec-percent-uncorrected"
    REVISION "200909160000Z" -- 2009, 09, 16 = Sep 16th, 2009
    DESCRIPTION "change multiple-rows-uchan to multiple-uchan. Add columns cpe-count, cpe-type, cpe-ip, cm-cpe-ip, cm-mac, cm-ip and cpe-mac"
    REVISION "200905150000Z" -- 2009, 05, 15 = May 5th, 2009
    DESCRIPTION "remove columns uchan-fec-corrected  uchan-fec-good uchan-fec-uncorrected uchan-rec-pwr uchan-response-percent uchan-snr uchan-power-adj uchan-timing
	             add multiple-rows-uchan, add multiple_rows enumeration MIB object"
    REVISION "200904230000Z" -- 2009, 04, 23 = April 23rd, 2009
    DESCRIPTION "add columns uchan-fec-corrected  uchan-fec-good uchan-fec-uncorrected uchan-rec-pwr uchan-response-percent uchan-snr uchan-power-adj uchan-timing"
    REVISION "200812150000Z" -- 2008, 12, 15 = December 15th, 2008
    DESCRIPTION "add columns service-type-prov & service-type-curr"
    REVISION "200807160000Z" -- 2008, 07, 16 = July 16th, 2008
    DESCRIPTION "add columns fpcm-cpe"
    REVISION "200712090000Z" -- 2007, 12, 09 = December 9th, 2007
    DESCRIPTION "add columns bonded, cable-mac, state-docsis20, interface-docsis20"
    REVISION "200612140000Z" -- 2006, 12, 14 = December 14th, 2006
    DESCRIPTION "add column cfgfilelong"
    REVISION "200610160000Z" -- 2006, 10, 16 = October 16th, 2006
    DESCRIPTION "add column fpcm-us-ds-counts"
    REVISION "200604130000Z" -- 2006, 04, 13 = April 13th, 2006
    DESCRIPTION "add column load-balance-group"
    REVISION "200603080000Z" -- 2006, 03, 08 = March 8th, 2006
    DESCRIPTION "merged columns filter-grp-cm-down, filter-grp-cm-up into one column filter-cm"
    REVISION "200512210000Z" -- 2005, 12, 21 = December 21st, 2005
    DESCRIPTION "removed columns filter-grp-cpe-down, filter-grp-cpe-up"
    REVISION "200511300000Z" -- 2005, 11, 30 = November 30th, 2005
    DESCRIPTION "added columns cm-type,	fpccm-online, fpccm-qos"
    REVISION "200511180000Z" -- 2005, 11, 18 = November 18th, 2005
    DESCRIPTION "added column flex-path-id"
    REVISION "200510180000Z" -- 2005, 10, 18 = October 18th, 2005
    DESCRIPTION "added columns filter-grp-cm-down, filter-grp-cm-up, filter-grp-cpe-down, filter-grp-cpe-up"
    REVISION "200509290000Z" -- 2005, 09, 29 = September 29th, 2005
    DESCRIPTION "added columns docsis-capability and docsis-provisioned"
    REVISION "200506160000Z"
    DESCRIPTION "created"
    ::= { cadExperimental 20 }

--
-- Column Name Textual Convention
--
ShowCmFormatColumnName ::= TEXTUAL-CONVENTION
    STATUS current
    DESCRIPTION
        "Enumeration of the show cable modem column names"
    SYNTAX INTEGER {
        none(0),
        multiple-uchan(1),
        cm-cfg-file(2),
        cm-down-pwr(3),
        cm-down-snr(4),
        cm-microreflec(5),
        cm-sysdesc(6),
        cm-time-polled(7),
        cm-timing(8),
        cm-up-pwr(9),
        congest-down(10),
        congest-up(11),
        cpe(12),
        crc(13),
        docsis-reg(14),
        fec-corrected(15),
        fec-good(16),
        fec-uncorrected(17),
        flap-last-flap(18),
        flap-prev-state(19),
        flaps-prov(20),
        flaps-ranging(21),
        flaps-reg(22),
        hcs(23),
        interface(24),
        ip(25),
        mac(26),
        microreflec(27),
        policed-down(28),
        power-adj(29),
        qos(30),
        rec-pwr(31),
        response-percent(32),
        sid(33),
        snr(34),
        state(35),
        timing(36),
        uptime(37),
        vendor(38),
        docsis-capability(39),
        docsis-provisioned(40),
        filter-cm(41),
        flex-path-id(42),
        cm-type(43),
        fpccm-online(44),
        fpcm-qos(45),
        load-balance-group(46),
        fpcm-us-ds-counts(47),
        cm-cfg-file-long(48),
        bonded (49),
        cable-mac (50),
        fpcm-cpe (53),
        service-type-prov (54),
        service-type-curr (55),
        bpi(56),
        fec-unerrored(57),
        cpe-ip(58),
        cpe-mac(59),
        cpe-type(60),
        cm-cpe-ip(61),
        cpe-count(62),
        cm-ip(63),
        cm-mac(64),
        fec-percent-uncorrected(65),
        l2vpn-id(66),
        l2vpn-qtag(67),
        bonded-actual(68),
        qos-primary(69),
        tx-pwr(70),
        ds-last-penalty-time(71),
    	ds-penalty-count(72),
        us-last-penalty-time(73),
        us-penalty-count(74),
        ofdm-ds-profiles(75),
        ofdm-modulation-supported(76),
        ofdm-ds-frequency-supported(77),
        us-frequency-supported(78)
    }

--
-- show cable modem format table
--

cadShowCmFormatTable OBJECT-TYPE
    SYNTAX     SEQUENCE OF CadShowCmFormatEntry
    MAX-ACCESS not-accessible
    STATUS     current
    DESCRIPTION
        "This table contains formatting information for the show cable modem
         format CLI command."
    ::= { cadShowCmFormatMib 1 }

cadShowCmFormatEntry OBJECT-TYPE
    SYNTAX     CadShowCmFormatEntry
    MAX-ACCESS not-accessible
    STATUS     current
    DESCRIPTION
        "Each entry contains a format name along with all of the columns that
         should be displayed when that format name is used via show cable
         modem format <format_name>. cadShowCmFormatCol1 must be set to a
         valid, non-empty when creating a row. Also, should more column
         names be specified, they must be specified in increasing order,
         with no gaps betweens the columns set. That is, if N column names
         are to be specified, then all columns from cadShowCmFormatCol1 to
         cadShowCmFormatCol[N] must be specified."
    INDEX { cadShowCmFormatName }
    ::= { cadShowCmFormatTable 1 }

CadShowCmFormatEntry ::= SEQUENCE {
    cadShowCmFormatName      DisplayString,
    cadShowCmFormatCol1      ShowCmFormatColumnName,
    cadShowCmFormatCol2      ShowCmFormatColumnName,
    cadShowCmFormatCol3      ShowCmFormatColumnName,
    cadShowCmFormatCol4      ShowCmFormatColumnName,
    cadShowCmFormatCol5      ShowCmFormatColumnName,
    cadShowCmFormatCol6      ShowCmFormatColumnName,
    cadShowCmFormatCol7      ShowCmFormatColumnName,
    cadShowCmFormatCol8      ShowCmFormatColumnName,
    cadShowCmFormatCol9      ShowCmFormatColumnName,
    cadShowCmFormatCol10     ShowCmFormatColumnName,
    cadShowCmFormatCol11     ShowCmFormatColumnName,
    cadShowCmFormatCol12     ShowCmFormatColumnName,
    cadShowCmFormatCol13     ShowCmFormatColumnName,
    cadShowCmFormatCol14     ShowCmFormatColumnName,
    cadShowCmFormatCol15     ShowCmFormatColumnName,
    cadShowCmFormatCol16     ShowCmFormatColumnName,
    cadShowCmFormatCol17     ShowCmFormatColumnName,
    cadShowCmFormatCol18     ShowCmFormatColumnName,
    cadShowCmFormatCol19     ShowCmFormatColumnName,
    cadShowCmFormatCol20     ShowCmFormatColumnName,
    cadShowCmFormatCol21     ShowCmFormatColumnName,
    cadShowCmFormatCol22     ShowCmFormatColumnName,
    cadShowCmFormatCol23     ShowCmFormatColumnName,
    cadShowCmFormatCol24     ShowCmFormatColumnName,
    cadShowCmFormatCol25     ShowCmFormatColumnName,
    cadShowCmFormatCol26     ShowCmFormatColumnName,
    cadShowCmFormatCol27     ShowCmFormatColumnName,
    cadShowCmFormatCol28     ShowCmFormatColumnName,
    cadShowCmFormatCol29     ShowCmFormatColumnName,
    cadShowCmFormatCol30     ShowCmFormatColumnName,
    cadShowCmFormatCol31     ShowCmFormatColumnName,
    cadShowCmFormatCol32     ShowCmFormatColumnName,
    cadShowCmFormatMultiRows INTEGER,
    cadShowCmFormatRowStatus RowStatus
}

cadShowCmFormatName OBJECT-TYPE
    SYNTAX     DisplayString (SIZE(1..32))
    MAX-ACCESS not-accessible
    STATUS     current
    DESCRIPTION
        "This is the name of the format. It is used as format_name in the CLI
         commands 'show cable modem format <format_name>' and 'configure cable
         modem format <format_name> <col_1> [col_2] ... [col_N]'"
    ::= { cadShowCmFormatEntry 1 }

cadShowCmFormatCol1 OBJECT-TYPE
    SYNTAX     ShowCmFormatColumnName
    MAX-ACCESS read-create
    STATUS     current
    DESCRIPTION
        "This is the name of the 1st column in the CLI command 'configure cable
         modem format <format_name> <col_1> [col_2] ... [col_N]'"
    DEFVAL { none }
    ::= { cadShowCmFormatEntry 2 }

cadShowCmFormatCol2 OBJECT-TYPE
    SYNTAX     ShowCmFormatColumnName
    MAX-ACCESS read-create
    STATUS     current
    DESCRIPTION
        "This is the name of the 2nd column in the CLI command 'configure cable
         modem format <format_name> <col_1> [col_2] ... [col_N]'"
    DEFVAL { none }
    ::= { cadShowCmFormatEntry 3 }

cadShowCmFormatCol3 OBJECT-TYPE
    SYNTAX     ShowCmFormatColumnName
    MAX-ACCESS read-create
    STATUS     current
    DESCRIPTION
        "This is the name of the 3rd column in the CLI command 'configure cable
         modem format <format_name> <col_1> [col_2] ... [col_N]'"
    DEFVAL { none }
    ::= { cadShowCmFormatEntry 4 }

cadShowCmFormatCol4 OBJECT-TYPE
    SYNTAX     ShowCmFormatColumnName
    MAX-ACCESS read-create
    STATUS     current
    DESCRIPTION
        "This is the name of the 4th column in the CLI command 'configure cable
         modem format <format_name> <col_1> [col_2] ... [col_N]'"
    DEFVAL { none }
    ::= { cadShowCmFormatEntry 5 }

cadShowCmFormatCol5 OBJECT-TYPE
    SYNTAX     ShowCmFormatColumnName
    MAX-ACCESS read-create
    STATUS     current
    DESCRIPTION
        "This is the name of the 5th column in the CLI command 'configure cable
         modem format <format_name> <col_1> [col_2] ... [col_N]'"
    DEFVAL { none }
    ::= { cadShowCmFormatEntry 6 }

cadShowCmFormatCol6 OBJECT-TYPE
    SYNTAX     ShowCmFormatColumnName
    MAX-ACCESS read-create
    STATUS     current
    DESCRIPTION
        "This is the name of the 6th column in the CLI command 'configure cable
         modem format <format_name> <col_1> [col_2] ... [col_N]'"
    DEFVAL { none }
    ::= { cadShowCmFormatEntry 7 }

cadShowCmFormatCol7 OBJECT-TYPE
    SYNTAX     ShowCmFormatColumnName
    MAX-ACCESS read-create
    STATUS     current
    DESCRIPTION
        "This is the name of the 7th column in the CLI command 'configure cable
         modem format <format_name> <col_1> [col_2] ... [col_N]'"
    DEFVAL { none }
    ::= { cadShowCmFormatEntry 8 }

cadShowCmFormatCol8 OBJECT-TYPE
    SYNTAX     ShowCmFormatColumnName
    MAX-ACCESS read-create
    STATUS     current
    DESCRIPTION
        "This is the name of the 8th column in the CLI command 'configure cable
         modem format <format_name> <col_1> [col_2] ... [col_N]'"
    DEFVAL { none }
    ::= { cadShowCmFormatEntry 9 }

cadShowCmFormatCol9 OBJECT-TYPE
    SYNTAX     ShowCmFormatColumnName
    MAX-ACCESS read-create
    STATUS     current
    DESCRIPTION
        "This is the name of the 9th column in the CLI command 'configure cable
         modem format <format_name> <col_1> [col_2] ... [col_N]'"
    DEFVAL { none }
    ::= { cadShowCmFormatEntry 10 }

cadShowCmFormatCol10 OBJECT-TYPE
    SYNTAX     ShowCmFormatColumnName
    MAX-ACCESS read-create
    STATUS     current
    DESCRIPTION
        "This is the name of the 10th column in the CLI command 'configure cable
         modem format <format_name> <col_1> [col_2] ... [col_N]'"
    DEFVAL { none }
    ::= { cadShowCmFormatEntry 11 }

cadShowCmFormatCol11 OBJECT-TYPE
    SYNTAX     ShowCmFormatColumnName
    MAX-ACCESS read-create
    STATUS     current
    DESCRIPTION
        "This is the name of the 11th column in the CLI command 'configure cable
         modem format <format_name> <col_1> [col_2] ... [col_N]'"
    DEFVAL { none }
    ::= { cadShowCmFormatEntry 12 }

cadShowCmFormatCol12 OBJECT-TYPE
    SYNTAX     ShowCmFormatColumnName
    MAX-ACCESS read-create
    STATUS     current
    DESCRIPTION
        "This is the name of the 12th column in the CLI command 'configure cable
         modem format <format_name> <col_1> [col_2] ... [col_N]'"
    DEFVAL { none }
    ::= { cadShowCmFormatEntry 13 }

cadShowCmFormatCol13 OBJECT-TYPE
    SYNTAX     ShowCmFormatColumnName
    MAX-ACCESS read-create
    STATUS     current
    DESCRIPTION
        "This is the name of the 13th column in the CLI command 'configure cable
         modem format <format_name> <col_1> [col_2] ... [col_N]'"
    DEFVAL { none }
    ::= { cadShowCmFormatEntry 14 }

cadShowCmFormatCol14 OBJECT-TYPE
    SYNTAX     ShowCmFormatColumnName
    MAX-ACCESS read-create
    STATUS     current
    DESCRIPTION
        "This is the name of the 14th column in the CLI command 'configure cable
         modem format <format_name> <col_1> [col_2] ... [col_N]'"
    DEFVAL { none }
    ::= { cadShowCmFormatEntry 15 }

cadShowCmFormatCol15 OBJECT-TYPE
    SYNTAX     ShowCmFormatColumnName
    MAX-ACCESS read-create
    STATUS     current
    DESCRIPTION
        "This is the name of the 15th column in the CLI command 'configure cable
         modem format <format_name> <col_1> [col_2] ... [col_N]'"
    DEFVAL { none }
    ::= { cadShowCmFormatEntry 16 }

cadShowCmFormatCol16 OBJECT-TYPE
    SYNTAX     ShowCmFormatColumnName
    MAX-ACCESS read-create
    STATUS     current
    DESCRIPTION
        "This is the name of the 16th column in the CLI command 'configure cable
         modem format <format_name> <col_1> [col_2] ... [col_N]'"
    DEFVAL { none }
    ::= { cadShowCmFormatEntry 17 }

cadShowCmFormatCol17 OBJECT-TYPE
    SYNTAX     ShowCmFormatColumnName
    MAX-ACCESS read-create
    STATUS     current
    DESCRIPTION
        "This is the name of the 17th column in the CLI command 'configure cable
         modem format <format_name> <col_1> [col_2] ... [col_N]'"
    DEFVAL { none }
    ::= { cadShowCmFormatEntry 18 }

cadShowCmFormatCol18 OBJECT-TYPE
    SYNTAX     ShowCmFormatColumnName
    MAX-ACCESS read-create
    STATUS     current
    DESCRIPTION
        "This is the name of the 18th column in the CLI command 'configure cable
         modem format <format_name> <col_1> [col_2] ... [col_N]'"
    DEFVAL { none }
    ::= { cadShowCmFormatEntry 19 }

cadShowCmFormatCol19 OBJECT-TYPE
    SYNTAX     ShowCmFormatColumnName
    MAX-ACCESS read-create
    STATUS     current
    DESCRIPTION
        "This is the name of the 19th column in the CLI command 'configure cable
         modem format <format_name> <col_1> [col_2] ... [col_N]'"
    DEFVAL { none }
    ::= { cadShowCmFormatEntry 20 }

cadShowCmFormatCol20 OBJECT-TYPE
    SYNTAX     ShowCmFormatColumnName
    MAX-ACCESS read-create
    STATUS     current
    DESCRIPTION
        "This is the name of the 20th column in the CLI command 'configure cable
         modem format <format_name> <col_1> [col_2] ... [col_N]'"
    DEFVAL { none }
    ::= { cadShowCmFormatEntry 21 }

cadShowCmFormatCol21 OBJECT-TYPE
    SYNTAX     ShowCmFormatColumnName
    MAX-ACCESS read-create
    STATUS     current
    DESCRIPTION
        "This is the name of the 21st column in the CLI command 'configure cable
         modem format <format_name> <col_1> [col_2] ... [col_N]'"
    DEFVAL { none }
    ::= { cadShowCmFormatEntry 22 }

cadShowCmFormatCol22 OBJECT-TYPE
    SYNTAX     ShowCmFormatColumnName
    MAX-ACCESS read-create
    STATUS     current
    DESCRIPTION
        "This is the name of the 22nd column in the CLI command 'configure cable
         modem format <format_name> <col_1> [col_2] ... [col_N]'"
    DEFVAL { none }
    ::= { cadShowCmFormatEntry 23 }

cadShowCmFormatCol23 OBJECT-TYPE
    SYNTAX     ShowCmFormatColumnName
    MAX-ACCESS read-create
    STATUS     current
    DESCRIPTION
        "This is the name of the 23rd column in the CLI command 'configure cable
         modem format <format_name> <col_1> [col_2] ... [col_N]'"
    DEFVAL { none }
    ::= { cadShowCmFormatEntry 24 }

cadShowCmFormatCol24 OBJECT-TYPE
    SYNTAX     ShowCmFormatColumnName
    MAX-ACCESS read-create
    STATUS     current
    DESCRIPTION
        "This is the name of the 24th column in the CLI command 'configure cable
         modem format <format_name> <col_1> [col_2] ... [col_N]'"
    DEFVAL { none }
    ::= { cadShowCmFormatEntry 25 }

cadShowCmFormatCol25 OBJECT-TYPE
    SYNTAX     ShowCmFormatColumnName
    MAX-ACCESS read-create
    STATUS     current
    DESCRIPTION
        "This is the name of the 25th column in the CLI command 'configure cable
         modem format <format_name> <col_1> [col_2] ... [col_N]'"
    DEFVAL { none }
    ::= { cadShowCmFormatEntry 26 }

cadShowCmFormatCol26 OBJECT-TYPE
    SYNTAX     ShowCmFormatColumnName
    MAX-ACCESS read-create
    STATUS     current
    DESCRIPTION
        "This is the name of the 26th column in the CLI command 'configure cable
         modem format <format_name> <col_1> [col_2] ... [col_N]'"
    DEFVAL { none }
    ::= { cadShowCmFormatEntry 27 }

cadShowCmFormatCol27 OBJECT-TYPE
    SYNTAX     ShowCmFormatColumnName
    MAX-ACCESS read-create
    STATUS     current
    DESCRIPTION
        "This is the name of the 27th column in the CLI command 'configure cable
         modem format <format_name> <col_1> [col_2] ... [col_N]'"
    DEFVAL { none }
    ::= { cadShowCmFormatEntry 28 }

cadShowCmFormatCol28 OBJECT-TYPE
    SYNTAX     ShowCmFormatColumnName
    MAX-ACCESS read-create
    STATUS     current
    DESCRIPTION
        "This is the name of the 28th column in the CLI command 'configure cable
         modem format <format_name> <col_1> [col_2] ... [col_N]'"
    DEFVAL { none }
    ::= { cadShowCmFormatEntry 29 }

cadShowCmFormatCol29 OBJECT-TYPE
    SYNTAX     ShowCmFormatColumnName
    MAX-ACCESS read-create
    STATUS     current
    DESCRIPTION
        "This is the name of the 29th column in the CLI command 'configure cable
         modem format <format_name> <col_1> [col_2] ... [col_N]'"
    DEFVAL { none }
    ::= { cadShowCmFormatEntry 30 }

cadShowCmFormatCol30 OBJECT-TYPE
    SYNTAX     ShowCmFormatColumnName
    MAX-ACCESS read-create
    STATUS     current
    DESCRIPTION
        "This is the name of the 30th column in the CLI command 'configure cable
         modem format <format_name> <col_1> [col_2] ... [col_N]'"
    DEFVAL { none }
    ::= { cadShowCmFormatEntry 31 }

cadShowCmFormatCol31 OBJECT-TYPE
    SYNTAX     ShowCmFormatColumnName
    MAX-ACCESS read-create
    STATUS     current
    DESCRIPTION
        "This is the name of the 31st column in the CLI command 'configure cable
         modem format <format_name> <col_1> [col_2] ... [col_N]'"
    DEFVAL { none }
    ::= { cadShowCmFormatEntry 32 }

cadShowCmFormatCol32 OBJECT-TYPE
    SYNTAX     ShowCmFormatColumnName
    MAX-ACCESS read-create
    STATUS     current
    DESCRIPTION
        "This is the name of the 32nd column in the CLI command 'configure cable
         modem format <format_name> <col_1> [col_2] ... [col_N]'"
    DEFVAL { none }
    ::= { cadShowCmFormatEntry 33 }

cadShowCmFormatMultiRows OBJECT-TYPE
    SYNTAX INTEGER {
        multiple-uchan(1)
    }
    MAX-ACCESS read-create
    STATUS current
    DESCRIPTION
        "This is set if we desire multiple rows for each CM. Currently the only condition available id for multiple uchan."
    ::= { cadShowCmFormatEntry 34 }
--
-- Add new columns above here. Do not add new columns below RowStatus
--
cadShowCmFormatRowStatus OBJECT-TYPE
    SYNTAX     RowStatus
    MAX-ACCESS read-create
    STATUS     current
    DESCRIPTION
        "Control object for this row."
    DEFVAL { createAndGo }
    ::= { cadShowCmFormatEntry 80 }
--
-- This is the end of the cadShowCmFormat table. Do not add new columns after RowStatus
--

END
