CADANT-CMTS-TOPO-MIB DEFINITIONS ::= BEGIN

IMPORTS
    OBJECT-TYPE,
    MODULE-IDENTITY,
    Integer32,
    Counter32,
    Unsigned32,
    Counter64
	FROM SNMPv2-SMI
    DisplayString,
    TEXTUAL-CONVENTION,
    RowStatus,
    TimeInterval,
    TruthValue
        FROM SNMPv2-TC
    OBJECT-GROUP,
    MODULE-COMPLIANCE
        FROM SNMPv2-CONF
    cadTopology
        FROM CADANT-PRODUCTS-MIB
    PrimaryState
        FROM CADANT-TC
    InterfaceIndex, InterfaceIndexOrZero
        FROM IF-MIB
    ChSetId,
    IfDirection,
    docsIf3MdNodeStatusEntry,
    docsIf3DsChSetEntry,
    docsIf3UsChSetEntry
        FROM DOCS-IF3-MIB
    clabTopoFiberNodeCfgNodeName,
    clabTopoFiberNodeCfgEntry
        FROM CLAB-TOPO-MIB
    cadIfMacDomainIfIndex
        FROM CADANT-CMTS-LAYER2CMTS-MIB;
cadTopologyMib MODULE-IDENTITY
    LAST-UPDATED "201402240000Z" -- Feb 24, 2014
    ORGANIZATION
        "Arris International, Inc."
    CONTACT-INFO
        "Arris Technical Support
         Postal: ARRIS
         E-Mail: support@arrisi.com"
    DESCRIPTION
        " This MIB module contains Cadant proprietary topology MIB information. "
    REVISION  "201402240000Z" -- Feb 24, 2014
    DESCRIPTION
        "Additional statistics on fiber-nodes."
    REVISION  "200808140000Z" -- Aug 14, 2008
    DESCRIPTION
        "Rename cadMdNodeStatusTable to cadFiberNodeStatusTable."
    REVISION  "200804090000Z" -- Apr 9, 2008
    DESCRIPTION
        "Remove cadDsChSetRelationshipTable and cadUsChSetRelationshipTable."
    REVISION  "200706040000Z" -- June 04, 2007
    DESCRIPTION
        " Initial version. "
    ::= { cadTopology 1 }



cadTopologyMibObjects OBJECT IDENTIFIER ::= { cadTopologyMib 1 }


--=======================================================
--=   Cadant MacDomain Node Status Table
--=======================================================
cadFiberNodeStatusTable OBJECT-TYPE
    SYNTAX      SEQUENCE OF CadFiberNodeStatusEntry
    MAX-ACCESS  not-accessible
    STATUS      current
    DESCRIPTION
        "A Table containing information about the
         Cadant Fiber Node status. "
    ::= { cadTopologyMibObjects 1 }

cadFiberNodeStatusEntry OBJECT-TYPE
    SYNTAX      CadFiberNodeStatusEntry
    MAX-ACCESS  not-accessible
    STATUS      current
    DESCRIPTION
        "A conceptual row containing information about the
         Cadant FiberNode status. "
    AUGMENTS    { clabTopoFiberNodeCfgEntry }
    ::= { cadFiberNodeStatusTable 1 }

CadFiberNodeStatusEntry ::= SEQUENCE {
    cadFiberNodeOperStatus                  PrimaryState,

    cadFiberNodeNumOther                    Integer32,
    cadFiberNodeNumInitRanging              Integer32,
    cadFiberNodeNumRangingComplete          Integer32,
    cadFiberNodeNumStartEae                 Integer32,
    cadFiberNodeNumStartDhcpv4              Integer32,
    cadFiberNodeNumStartDhcpv6              Integer32,
    cadFiberNodeNumDhcpv4Complete           Integer32,
    cadFiberNodeNumDhcpv6Complete           Integer32,
    cadFiberNodeNumStartCfgFileDownload     Integer32,
    cadFiberNodeNumCfgFileDownloadComplete  Integer32,
    cadFiberNodeNumStartRegistration        Integer32,
    cadFiberNodeNumRegistrationComplete     Integer32,
    cadFiberNodeNumOperational              Integer32,
    cadFiberNodeNumBpiInit                  Integer32,
    cadFiberNodeNumForwardingDisabled       Integer32,
    cadFiberNodeNumRfMuteAll                Integer32,
    cadFiberNodeNumTotal                    Integer32,
    cadFiberNodeNumRangingAborted           Integer32,
    cadFiberNodeNumRangFlaps                Integer32,
    cadFiberNodeNumProvFlaps                Integer32,
    cadFiberNodeNumRegFlaps                 Integer32
}

cadFiberNodeOperStatus OBJECT-TYPE
        SYNTAX  PrimaryState
        MAX-ACCESS read-only
        STATUS  current
        DESCRIPTION
            "Cadant Fiber Node operation status."
        ::= { cadFiberNodeStatusEntry 1 }

cadFiberNodeNumOther OBJECT-TYPE
        SYNTAX      Integer32
        MAX-ACCESS  read-only
        STATUS      deprecated
        DESCRIPTION
            "The number of modems on this fiber-node in state other(1)"
        ::= { cadFiberNodeStatusEntry 11 }

cadFiberNodeNumInitRanging OBJECT-TYPE
        SYNTAX      Integer32
        MAX-ACCESS  read-only
        STATUS      deprecated
        DESCRIPTION
            "The number of modems on this fiber-node in state initialRanging(2)"
        ::= { cadFiberNodeStatusEntry 12 }

cadFiberNodeNumRangingComplete OBJECT-TYPE
        SYNTAX      Integer32
        MAX-ACCESS  read-only
        STATUS      deprecated
        DESCRIPTION
            "The number of modems on this fiber-node in state rangingAutoAdjComplete(4)"
        ::= { cadFiberNodeStatusEntry 13 }

cadFiberNodeNumStartEae OBJECT-TYPE
        SYNTAX      Integer32
        MAX-ACCESS  read-only
        STATUS      deprecated
        DESCRIPTION
            "The number of modems on this fiber-node in state startEae(10)"
        ::= { cadFiberNodeStatusEntry 14 }

cadFiberNodeNumStartDhcpv4 OBJECT-TYPE
        SYNTAX      Integer32
        MAX-ACCESS  read-only
        STATUS      deprecated
        DESCRIPTION
            "The number of modems on this fiber-node in state startDhcpv4(11)"
        ::= { cadFiberNodeStatusEntry 15 }

cadFiberNodeNumStartDhcpv6 OBJECT-TYPE
        SYNTAX      Integer32
        MAX-ACCESS  read-only
        STATUS      deprecated
        DESCRIPTION
            "The number of modems on this fiber-node in state startDhcpv6(12)"
        ::= { cadFiberNodeStatusEntry 16 }

cadFiberNodeNumDhcpv4Complete OBJECT-TYPE
        SYNTAX      Integer32
        MAX-ACCESS  read-only
        STATUS      deprecated
        DESCRIPTION
            "The number of modems on this fiber-node in state dhcpv4Complete(5)"
        ::= { cadFiberNodeStatusEntry 17 }

cadFiberNodeNumDhcpv6Complete OBJECT-TYPE
        SYNTAX      Integer32
        MAX-ACCESS  read-only
        STATUS      deprecated
        DESCRIPTION
            "The number of modems on this fiber-node in state dhcpv6Complete(13)"
        ::= { cadFiberNodeStatusEntry 18 }

cadFiberNodeNumStartCfgFileDownload OBJECT-TYPE
        SYNTAX      Integer32
        MAX-ACCESS  read-only
        STATUS      deprecated
        DESCRIPTION
            "The number of modems on this fiber-node in state startConfigFileDownload(14)"
        ::= { cadFiberNodeStatusEntry 19 }

cadFiberNodeNumCfgFileDownloadComplete OBJECT-TYPE
        SYNTAX      Integer32
        MAX-ACCESS  read-only
        STATUS      deprecated
        DESCRIPTION
            "The number of modems on this fiber-node in state configFileDownloadComplete(15)"
        ::= { cadFiberNodeStatusEntry 20 }

cadFiberNodeNumStartRegistration OBJECT-TYPE
        SYNTAX      Integer32
        MAX-ACCESS  read-only
        STATUS      deprecated
        DESCRIPTION
            "The number of modems on this fiber-node in state startRegistration(16)"
        ::= { cadFiberNodeStatusEntry 21 }

cadFiberNodeNumRegistrationComplete OBJECT-TYPE
        SYNTAX      Integer32
        MAX-ACCESS  read-only
        STATUS      deprecated
        DESCRIPTION
            "The number of modems on this fiber-node in state registrationComplete(6)"
        ::= { cadFiberNodeStatusEntry 22 }

cadFiberNodeNumOperational OBJECT-TYPE
        SYNTAX      Integer32
        MAX-ACCESS  read-only
        STATUS      deprecated
        DESCRIPTION
            "The number of modems on this fiber-node in state operational(8)"
        ::= { cadFiberNodeStatusEntry 23 }

cadFiberNodeNumBpiInit OBJECT-TYPE
        SYNTAX      Integer32
        MAX-ACCESS  read-only
        STATUS      deprecated
        DESCRIPTION
            "The number of modems on this fiber-node in state bpiInit(9)"
        ::= { cadFiberNodeStatusEntry 24 }

cadFiberNodeNumForwardingDisabled OBJECT-TYPE
        SYNTAX      Integer32
        MAX-ACCESS  read-only
        STATUS      deprecated
        DESCRIPTION
            "The number of modems on this fiber-node in state forwardingDisabled(17)"
        ::= { cadFiberNodeStatusEntry 25 }

cadFiberNodeNumRfMuteAll OBJECT-TYPE
        SYNTAX      Integer32
        MAX-ACCESS  read-only
        STATUS      deprecated
        DESCRIPTION
            "The number of modems on this fiber-node in state rfMuteAll(18)"
        ::= { cadFiberNodeStatusEntry 26 }

cadFiberNodeNumTotal OBJECT-TYPE
        SYNTAX      Integer32
        MAX-ACCESS  read-only
        STATUS      deprecated
        DESCRIPTION
            "The total count of cable modems on this fiber-node"
        ::= { cadFiberNodeStatusEntry 27 }

cadFiberNodeNumRangingAborted OBJECT-TYPE
        SYNTAX      Integer32
        MAX-ACCESS  read-only
        STATUS      deprecated
        DESCRIPTION
            "The number of modems on this fiber-node in state rangingAborted(3)"
        ::= { cadFiberNodeStatusEntry 28 }

cadFiberNodeNumRangFlaps OBJECT-TYPE
        SYNTAX      Integer32
        MAX-ACCESS  read-only
        STATUS      deprecated
        DESCRIPTION
            "The number of times a CM on this fiber-node fiber-node has reset in Ranging states."
        ::= { cadFiberNodeStatusEntry 29 }

cadFiberNodeNumProvFlaps OBJECT-TYPE
        SYNTAX      Integer32
        MAX-ACCESS  read-only
        STATUS      deprecated
        DESCRIPTION
            "The number of times a CM on this fiber-node has reset in Provisioning states."
        ::= { cadFiberNodeStatusEntry 30 }

cadFiberNodeNumRegFlaps OBJECT-TYPE
        SYNTAX      Integer32
        MAX-ACCESS  read-only
        STATUS      deprecated
        DESCRIPTION
            "The number of times a CM on this fiber-node has reset in Registered state."
        ::= { cadFiberNodeStatusEntry 31 }



--=======================================================
--=   Cadant Fiber Node Channel Table
--=======================================================
cadChlFnTable OBJECT-TYPE
    SYNTAX      SEQUENCE OF CadChlFnEntry
    MAX-ACCESS  not-accessible
    STATUS      current
    DESCRIPTION
        "A Table containing information about the
         Cadant Topology fiber node channel. "
    ::= { cadTopologyMibObjects 2 }

cadChlFnEntry OBJECT-TYPE
    SYNTAX      CadChlFnEntry
    MAX-ACCESS  not-accessible
    STATUS      current
    DESCRIPTION
        "A conceptual row containing information about the
         Cadant fiber node channel. "
    INDEX       { cadIfMacDomainIfIndex, clabTopoFiberNodeCfgNodeName, cadChlIfIndex }
    ::= { cadChlFnTable 1 }

CadChlFnEntry ::= SEQUENCE {
    cadChlIfIndex           InterfaceIndex,
    cadChlFnIfDirection     IfDirection,
    cadChlFnMdUsOrDsSgId    Unsigned32,
    cadChlFnUsOrDsPhysChlIfIndex    InterfaceIndexOrZero,
    cadChlFnChlId           Unsigned32
}

cadChlIfIndex OBJECT-TYPE
    SYNTAX  InterfaceIndex
    MAX-ACCESS not-accessible
    STATUS  current
    DESCRIPTION
	"Fiber node channel interface index."
    ::= { cadChlFnEntry 1 }

cadChlFnIfDirection OBJECT-TYPE
    SYNTAX  IfDirection

    MAX-ACCESS read-only
    STATUS  current
    DESCRIPTION
	"Fiber node channel direction."
    ::= { cadChlFnEntry 2 }

cadChlFnMdUsOrDsSgId OBJECT-TYPE
    SYNTAX  Unsigned32 (0..255)
    MAX-ACCESS read-only
    STATUS  current
    DESCRIPTION
	"MD-US-SG ID or MD-DS-SG ID in this fiber node."
    ::= { cadChlFnEntry 3 }

cadChlFnUsOrDsPhysChlIfIndex OBJECT-TYPE
    SYNTAX  InterfaceIndexOrZero
    MAX-ACCESS read-only
    STATUS  current
    DESCRIPTION
	"Interface index of an physical upstream or downstream channel."
    ::= { cadChlFnEntry 4 }

cadChlFnChlId OBJECT-TYPE
    SYNTAX  Unsigned32 (1..255)
    MAX-ACCESS read-only
    STATUS  current
    DESCRIPTION
	"Fiber node channel id. This value comes from cadMacChlChannelId of cadMacChlTable."
    ::= { cadChlFnEntry 5 }

END
