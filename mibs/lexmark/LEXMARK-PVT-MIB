--
--
-- Lexmark International
--
--
-- filename: lexmark1.mib
-- $Revision: 1.4 $
-- $Date: 2002/05/10 15:26:24 $
--
--
--
-- Version 3.1.7

LEXMARK-PVT-MIB DEFINITIONS ::= BEGIN

IMPORTS
    enterprises, Gauge, Counter, IpAddress
        FROM RFC1155-SMI
    DisplayString, PhysAddress
        FROM RFC1213-MIB
    OBJECT-TYPE
        FROM RFC-1212
    TRAP-TYPE
        FROM RFC-1215;

lexmark   OBJECT IDENTIFIER ::= { enterprises 641 }
adapter   OBJECT IDENTIFIER ::= { lexmark 1 }
printer   OBJECT IDENTIFIER ::= { lexmark 2 }
attachment OBJECT IDENTIFIER ::= { lexmark 3 }
opsys     OBJECT IDENTIFIER ::= { adapter 1 }
lexlink   OBJECT IDENTIFIER ::= { adapter 2 }
lexipx    OBJECT IDENTIFIER ::= { adapter 3 }
lextalk   OBJECT IDENTIFIER ::= { adapter 4 }
lextcp    OBJECT IDENTIFIER ::= { adapter 5 }
lexhttp   OBJECT IDENTIFIER ::= { lextcp 6 }
lexdhcp   OBJECT IDENTIFIER ::= { lextcp 7 }
lexhdwr   OBJECT IDENTIFIER ::= { adapter 6 }
lexmac    OBJECT IDENTIFIER ::= { adapter 7 }
lextrap   OBJECT IDENTIFIER ::= { adapter 8 }
time      OBJECT IDENTIFIER ::= { adapter 9 }
prtgen    OBJECT IDENTIFIER ::= { printer 1 }
pgcount   OBJECT IDENTIFIER ::= { prtgen 5 }
fax       OBJECT IDENTIFIER ::= { attachment 1 }

-- The INA Operating System Group

opsysCodeRev OBJECT-TYPE
    SYNTAX  DisplayString (SIZE (0..255))
    ACCESS  read-only
    STATUS  mandatory
    DESCRIPTION
        "A textual identification of network adapter's firmware revision
         level.  For example: 7.15.1"
    ::= { opsys 1 }

opsysJobTimeout OBJECT-TYPE
    SYNTAX  INTEGER (10..255)
    ACCESS  read-write
    STATUS  mandatory
    DESCRIPTION
        "The adapter job timeout period in seconds."
    ::= { opsys 2 }

opsysCurrentJob OBJECT-TYPE
    SYNTAX  DisplayString (SIZE (0..255))
    ACCESS  read-only
    STATUS  mandatory
    DESCRIPTION
        "A textual description of the currently printing job containing
         the Source NOS, Source server, Source user, Job number, and Job
         size, separated by CR LF.  A NULL string indicates no active job.
         For multiport adapters, this reflects job status of printer port 1."
    ::= { opsys 3 }

opsysRAMSize OBJECT-TYPE
    SYNTAX  INTEGER
    ACCESS  read-only
    STATUS  mandatory
    DESCRIPTION
        "The size of the network adapter's RAM in bytes."
    ::= { opsys 4 }

opsysNVRAMSize OBJECT-TYPE
    SYNTAX  INTEGER
    ACCESS  read-only
    STATUS  mandatory
    DESCRIPTION
        "The size of the network adapter's NVRAM in bytes."
    ::= { opsys 5 }

opsysROMSize OBJECT-TYPE
    SYNTAX  INTEGER
    ACCESS  read-only
    STATUS  mandatory
    DESCRIPTION
        "The size of the network adapter's ROM in bytes."
    ::= { opsys 6 }

opsysROMType OBJECT-TYPE
    SYNTAX  DisplayString (SIZE (0..255))
    ACCESS  read-only
    STATUS  mandatory
    DESCRIPTION
        "A textual description of the network adapter's ROM technology.
         Currently valid types are: MASK_ROM, OTP, FLASH, UV_EPROM,
         EEPROM, and OTHER."
    ::= { opsys 7 }

opsysProtocols OBJECT-TYPE
    SYNTAX  INTEGER (0..65535)
    ACCESS  read-only
    STATUS  mandatory
    DESCRIPTION
        "A bitmap representing the protocols supported by the network adapter.

         Bit  Value  Protocol
         ---  -----  ----------
         0    1      LexLink
         1    2      Netware
         2    4      AppleTalk
         3    8      TCP/IP
         4    16     AirPrint
         5    32     reserved
         6    64     NDS"
    ::= { opsys 8 }

opsysTimeToReset OBJECT-TYPE
    SYNTAX  INTEGER
    ACCESS  read-write
    STATUS  mandatory
    DESCRIPTION
        "The amount of time remaining until the adapter performs a power
         on reset.  A value of -1 indicates no reset is scheduled.
         Setting to 0 causes the adapter to reset immediately. The only
         valid set value is 0."
    ::= { opsys 9 }

opsysCardPartNo OBJECT-TYPE
    SYNTAX  DisplayString (SIZE (0..255))
    ACCESS  read-only
    STATUS  mandatory
    DESCRIPTION
        "A textual representation of the network adapter's part number."
    ::= { opsys 10 }

opsysCardEC OBJECT-TYPE
    SYNTAX  DisplayString (SIZE (0..255))
    ACCESS  read-only
    STATUS  mandatory
    DESCRIPTION
        "A textual representation of the network adapter's EC level."
    ::= { opsys 11 }

opsysCurrentJobTable OBJECT-TYPE
    SYNTAX SEQUENCE OF OpsysCurrentJobEntry
    ACCESS  not-accessible
    STATUS  mandatory
    DESCRIPTION
        "A table of current job information for each of the network
         adapter's printer ports."
    ::= { opsys 12 }

opsysCurrentJobEntry OBJECT-TYPE
    SYNTAX  OpsysCurrentJobEntry
    ACCESS  not-accessible
    STATUS  mandatory
    DESCRIPTION
        "An entry containing job information for one printer port."
    INDEX   { opsysCurrentJobEntryIndex }
    ::= { opsysCurrentJobTable 1 }

OpsysCurrentJobEntry ::= SEQUENCE {
    opsysCurrentJobEntryIndex       INTEGER,
    opsysCurrentJobString           DisplayString
    }

opsysCurrentJobEntryIndex OBJECT-TYPE
    SYNTAX  INTEGER (1..2147483647)
    ACCESS  read-only
    STATUS  mandatory
    DESCRIPTION
        "A unique value used by the adapter to identify job information
         for one printer port.  Each entry corresponds to a value
         lexhdwrPortTableIndex."
    ::= { opsysCurrentJobEntry 1 }

opsysCurrentJobString OBJECT-TYPE
    SYNTAX  DisplayString (SIZE (0..255))
    ACCESS  read-only
    STATUS  mandatory
    DESCRIPTION
        "A textual description of the this printer port's currently
         printing job containing the Source NOS, Source server,
         Source user, Job number, and Job size, separated by CR LF.
         A NULL string indicates no active job."
    ::= { opsysCurrentJobEntry 2 }

opsysDeviceType OBJECT-TYPE
    SYNTAX  OCTET STRING (SIZE (2))
    ACCESS  read-only
    STATUS  mandatory
    DESCRIPTION
        "A two byte code representing the adapter's type."
    ::= { opsys 13 }

opsysAdapterName OBJECT-TYPE
    SYNTAX  OCTET STRING (SIZE (64))
    ACCESS  read-only
    STATUS  mandatory
    DESCRIPTION
        "A Unicode representation of the adapter's name."
    ::= { opsys 14 }

opsysAdapterCapabilities OBJECT-TYPE
    SYNTAX  OCTET STRING (SIZE (4))
    ACCESS  read-only
    STATUS  mandatory
    DESCRIPTION
        "A bitmap representing the capabilities of the adapter.

         Bit  Value       Frame type
         ---  ----------  --------------------------
         31   0x80000000  NPANT via Netware and IP
         30   0x40000000  Receive-only Fax
         29   0x20000000  reserved
         28   0x10000000  Adapter HTTP
         27   0x08000000  Printer HTTP
         26   0x04000000  HTTP Configuration Page
         25   0x02000000  Copier Option"
    ::= { opsys 15 }

-- The LexLink Group

lexlinkActivated OBJECT-TYPE
    SYNTAX  INTEGER {
        off(1),
        on(2)
        }
    ACCESS  read-write
    STATUS  mandatory
    DESCRIPTION
        "The activation status of the LexLink protocol.  If this
         variable is changed, the adapter must be reset before the
         change will take effect.  See opsysTimeToReset."
    ::= { lexlink 1 }

lexlinkNickname OBJECT-TYPE
    SYNTAX  DisplayString (SIZE (0..24))
    ACCESS  read-write
    STATUS  mandatory
    DESCRIPTION
        "The nickname assigned to the adapter for the LexLink protocol.
         Note that some adapters may not support the maximum length."
    ::= { lexlink 2 }


-- The LexIPX Group (Netware)

lexipxActivated OBJECT-TYPE
    SYNTAX  INTEGER {
        off(1),
        on(2)
        }
    ACCESS  read-write
    STATUS  mandatory
    DESCRIPTION
        "The activation status of the Netware protocol.  If this variable
         is changed, the adapter must be reset before the change will take
         effect.  See opsysTimeToReset."
    ::= { lexipx 1 }

lexipxLoginName OBJECT-TYPE
    SYNTAX  DisplayString (SIZE (0..43))
    ACCESS  read-write
    STATUS  mandatory
    DESCRIPTION
        "The adapter's Netware login name.  If this variable is changed, the
         adapter must be reset before the change will take effect.  See
         opsysTimeToReset."
    ::= { lexipx 2 }

lexipxNetNumber OBJECT-TYPE
    SYNTAX  DisplayString (SIZE (8))
    ACCESS  read-only
    STATUS  mandatory
    DESCRIPTION
        "The network number of the Netware network to which the adapter is
         connected."
    ::= { lexipx 3 }

lexipxSAPMode OBJECT-TYPE
    SYNTAX  INTEGER {
        off(1),
        on(2)
        }
    ACCESS  read-write
    STATUS  mandatory
    DESCRIPTION
        "The network adapter's current Netware SAP'ing status."

    ::= { lexipx 4 }

lexipxServerMode OBJECT-TYPE
    SYNTAX  INTEGER {
        pserver(1),
        rprinter(2)
    }
    ACCESS  read-write
    STATUS  mandatory
    DESCRIPTION
        "The current Netware server mode of the adapter.  If this variable
         is changed, the adapter must be reset before the change will take
         effect.  See opsysTimeToReset."
    ::= { lexipx 5 }

lexipxNumPorts OBJECT-TYPE
    SYNTAX  INTEGER
    ACCESS  read-only
    STATUS  mandatory
    DESCRIPTION
        "The number of Netware printer ports."
    ::= { lexipx 6 }

lexipxPortInfoTable OBJECT-TYPE
    SYNTAX  SEQUENCE OF LexipxPortInfoEntry
    ACCESS  not-accessible
    STATUS  mandatory
    DESCRIPTION
        "A table of Netware printer port information."
    ::= { lexipx 7 }

lexipxPortInfoEntry OBJECT-TYPE
    SYNTAX  LexipxPortInfoEntry
    ACCESS  not-accessible
    STATUS  mandatory
    DESCRIPTION
        "An entry containing Netware printer port information."
    INDEX   { lexipxPortInfoIndex }
    ::= { lexipxPortInfoTable 1 }

LexipxPortInfoEntry ::= SEQUENCE {
    lexipxPortInfoIndex             INTEGER,
    lexipxPortInfoPollIntvl         INTEGER,
    lexipxPortInfoEnable            INTEGER,
    lexipxPortInfoBannerPage        INTEGER
    }

lexipxPortInfoIndex OBJECT-TYPE
    SYNTAX  INTEGER (1..2147483647)
    ACCESS  read-only
    STATUS  mandatory
    DESCRIPTION
        "A unique value used by the adapter to identify Netware printer ports."
    ::= { lexipxPortInfoEntry 1 }

lexipxPortInfoPollIntvl OBJECT-TYPE
    SYNTAX  INTEGER (1..16383)
    ACCESS  read-write
    STATUS  mandatory
    DESCRIPTION
        "The Netware queue polling interval for this printer port."
    ::= { lexipxPortInfoEntry 2 }

lexipxPortInfoEnable OBJECT-TYPE
    SYNTAX  INTEGER {
        disabled(1),
        enabled(2)
        }
    ACCESS  read-write
    STATUS  mandatory
    DESCRIPTION
        "The Netware queue status of this printer port."
    ::= { lexipxPortInfoEntry 3 }

lexipxPortInfoBannerPage OBJECT-TYPE
    SYNTAX  INTEGER {
        off(1),
        postscript(2),
        ascii(3)
        }
    ACCESS  read-only
    STATUS  mandatory
    DESCRIPTION
        "The Netware queue banner page status for this printer port."

    ::= { lexipxPortInfoEntry 4 }

lexipxNumPrefServers OBJECT-TYPE
    SYNTAX  INTEGER
    ACCESS  read-only
    STATUS  mandatory
    DESCRIPTION
        "The maximum number of preferred Netware servers supported by this
         network adapter."
    ::= { lexipx 8 }

lexipxPrefSrvrTable OBJECT-TYPE
    SYNTAX  SEQUENCE OF LexipxPrefSrvrEntry
    ACCESS  not-accessible
    STATUS  mandatory
    DESCRIPTION
        "A table of the network adapter's preferred Netware servers."
    ::= { lexipx 9 }

lexipxPrefSrvrEntry OBJECT-TYPE
    SYNTAX  LexipxPrefSrvrEntry
    ACCESS  not-accessible
    STATUS  mandatory
    DESCRIPTION
        "An entry containing preferred Netware server information."
    INDEX   { lexipxPrefSrvrIndex }
    ::= { lexipxPrefSrvrTable 1 }

LexipxPrefSrvrEntry ::= SEQUENCE {
    lexipxPrefSrvrIndex             INTEGER,
    lexipxPrefSrvrName              DisplayString
    }

lexipxPrefSrvrIndex OBJECT-TYPE
    SYNTAX  INTEGER (1..2147483647)
    ACCESS  read-only

    STATUS  mandatory
    DESCRIPTION
        "A unique value used by the adapter to identify preferred Netware
         servers."
    ::= { lexipxPrefSrvrEntry 1 }

lexipxPrefSrvrName OBJECT-TYPE
    SYNTAX  DisplayString (SIZE (0..47))
    ACCESS  read-write
    STATUS  mandatory
    DESCRIPTION
        "The name of this preferred Netware server. If this variable is
         changed, the adapter must be reset before the change will take
         effect.  See opsysTimeToReset."
    ::= { lexipxPrefSrvrEntry 2 }

lexipxConnSrvrTable OBJECT-TYPE
    SYNTAX  SEQUENCE OF LexipxConnSrvrEntry
    ACCESS  not-accessible
    STATUS  mandatory
    DESCRIPTION
        "A table of connected Netware server information."
    ::= { lexipx 10 }

lexipxConnSrvrEntry OBJECT-TYPE
    SYNTAX  LexipxConnSrvrEntry
    ACCESS  not-accessible
    STATUS  mandatory
    DESCRIPTION
        "An entry containing connected Netware server information."
    INDEX   { lexipxConnSrvrIndex }
    ::= { lexipxConnSrvrTable 1 }

LexipxConnSrvrEntry ::= SEQUENCE {
    lexipxConnSrvrIndex             INTEGER,
    lexipxConnSrvrName              DisplayString,
    lexipxConnSrvrNet               DisplayString,
    lexipxConnSrvrNode              DisplayString,
    lexipxConnSrvrConnNum           INTEGER,
    lexipxConnSrvrConnId            INTEGER,
    lexipxConnSrvrPSConnID          INTEGER
    }

lexipxConnSrvrIndex OBJECT-TYPE
    SYNTAX  INTEGER (1..2147483647)
    ACCESS  read-only
    STATUS  mandatory
    DESCRIPTION
        "A unique value used by the adapter to identify connected Netware
         servers."
    ::= { lexipxConnSrvrEntry 1 }

lexipxConnSrvrName OBJECT-TYPE
    SYNTAX  DisplayString (SIZE (0..255))
    ACCESS  read-only
    STATUS  mandatory
    DESCRIPTION
        "The name of this connected Netware server."
    ::= { lexipxConnSrvrEntry 2 }

lexipxConnSrvrNet OBJECT-TYPE
    SYNTAX  DisplayString (SIZE (8))
    ACCESS  read-only
    STATUS  mandatory
    DESCRIPTION
        "The Netware network number of this connected Netware server."
    ::= { lexipxConnSrvrEntry 3 }

lexipxConnSrvrNode OBJECT-TYPE
    SYNTAX  DisplayString (SIZE (12))
    ACCESS  read-only
    STATUS  mandatory
    DESCRIPTION
        "The Netware node address of the connected Netware server."
    ::= { lexipxConnSrvrEntry 4 }

lexipxConnSrvrConnNum OBJECT-TYPE
    SYNTAX  INTEGER (0..65535)
    ACCESS  read-only
    STATUS  mandatory
    DESCRIPTION
        "The connection number of the connected Netware server (pserver
         mode only)."
    ::= { lexipxConnSrvrEntry 5 }

lexipxConnSrvrConnId OBJECT-TYPE
    SYNTAX  INTEGER (0..65535)
    ACCESS  read-only
    STATUS  mandatory
    DESCRIPTION
        "The connection ID of the connected Netware server (rprinter mode
         only)."
    ::= { lexipxConnSrvrEntry 6 }

lexipxConnSrvrPSConnID OBJECT-TYPE
    SYNTAX  INTEGER (0..65535)
    ACCESS  read-only
    STATUS  mandatory
    DESCRIPTION
        "The connection ID of the connected Netware pserver (rprinter mode
         only)."
    ::= { lexipxConnSrvrEntry 7 }

lexipxFrameType OBJECT-TYPE
    SYNTAX  INTEGER (0..255)
    ACCESS  read-write
    STATUS  mandatory
    DESCRIPTION
        "A bitmap of the supported IPX frame types.

         Bit  Value  Frame type
         ---  -----  --------------------------
         0    1      Token-Ring
         1    2      Token-Ring Source Routed
         2    4      Token-Ring SNAP
         3    8      Token-Ring SNAP Source Routed
         4    16     Ethernet 802.2
         5    32     Ethernet 802.3
         6    64     Ethernet Type 2
         7    128    Ethernet SNAP"
    ::= { lexipx 11 }

lexipxTrapTable OBJECT-TYPE
    SYNTAX SEQUENCE OF LexipxTrapEntry
    ACCESS  not-accessible
    STATUS  mandatory
    DESCRIPTION
        "A table of IPX trap destination configurations."
::= { lexipx 12 }

lexipxTrapEntry OBJECT-TYPE
    SYNTAX  LexipxTrapEntry
    ACCESS  not-accessible
    STATUS  mandatory
    DESCRIPTION
        "An entry containing an IPX trap destination's configuration."
    INDEX   { lexipxTrapIndex }
    ::= { lexipxTrapTable 1 }

LexipxTrapEntry ::= SEQUENCE {
    lexipxTrapIndex                 INTEGER,
    lexipxTrapMask                  INTEGER,
    lexipxTrapNetworkAddress        OCTET STRING,
    lexipxTrapNodeAddress           OCTET STRING
    }

lexipxTrapIndex OBJECT-TYPE
    SYNTAX  INTEGER (1..2147483647)
    ACCESS  read-only
    STATUS  mandatory
    DESCRIPTION
        "A unique value used by the adapter to identify IPX trap destinations."
    ::= { lexipxTrapEntry 1 }

lexipxTrapMask OBJECT-TYPE
    SYNTAX  INTEGER (0..65535)
    ACCESS  read-write
    STATUS  mandatory
    DESCRIPTION
        "The trap mask for the trap destination.  It is implemented as a
         bitmap specifying a mask of intervention required conditions for
         which the adapter should send trap messages.  Setting a bit to 1
         enables the corresponding trap.  A value of 511 will cause the
         adapter to send traps for all intervention required conditions.

         The bitmap is defined below:

         Bit  Value  Condition
         ---  -----  --------------------------
         0    1      Output hopper full
         1    2      Load Paper
         2    4      Paper Jam
         3    8      Toner Low
         4    16     Service Required
         5    32     Disk Error
         6    64     Cover Opened
         7    128    Page Complexity Error
         8    256    Offline"
    ::= { lexipxTrapEntry 2 }

lexipxTrapNetworkAddress OBJECT-TYPE
    SYNTAX  OCTET STRING (SIZE (4))
    ACCESS  read-write
    STATUS  mandatory
    DESCRIPTION
        "The IPX network address of the trap destination. (4 bytes)"
    ::= { lexipxTrapEntry 3 }

lexipxTrapNodeAddress OBJECT-TYPE
    SYNTAX  OCTET STRING (SIZE (6))
    ACCESS  read-write
    STATUS  mandatory
    DESCRIPTION
        "The IPX node address of the trap destination. (6 bytes)"
    ::= { lexipxTrapEntry 4 }

lexipxTrapType OBJECT-TYPE
    SYNTAX  INTEGER {
         multiplexed(1),
         individual(2)
         }
    ACCESS  read-write
    STATUS  mandatory
    DESCRIPTION
        "The type of SNMP over IPX traps that will be sent by the adapter.

         Setting this variable to multiplexed(1) configures all intervention
         required conditions to send an irCondition trap (specific trap
         number 1) and for the clearing of intervention required conditions
         to send an irCleared trap (specific trap number 0).

         Setting this variable to individual(2) causes each intervention
         required condition to send its corresponding trap (specific traps
         numbered 2 through 10) and for the clearing of intervention required
         conditions to cause an irClearedTypeII trap (specific trap number 11).

         See the Trap Definitions Group for more information.

         Individual(2) is the default for IPX and is necessary for NMS
         annotations."
    ::= { lexipx 13 }

lexipxGSQ OBJECT-TYPE
    SYNTAX  INTEGER (5..600)
    ACCESS  read-write
    STATUS  mandatory
    DESCRIPTION
        "The General Service Query (GSQ) interval.  This is the period
         in seconds that the adapter waits after a failed GSQ before
         attempting another as it searches for Netware servers."
    ::= { lexipx 14 }


-- The LexTalk Group

lextalkActivated OBJECT-TYPE
    SYNTAX  INTEGER {
        off(1),
        on(2)
        }
    ACCESS  read-write
    STATUS  mandatory
    DESCRIPTION
        "The activation status of the AppleTalk protocol. If this
         variable is changed, the adapter must be reset before the
         change will take effect.  See opsysTimeToReset."
    ::= { lextalk 1 }

lextalkAddress OBJECT-TYPE
    SYNTAX  DisplayString (SIZE (0..9))
    ACCESS  read-only
    STATUS  mandatory
    DESCRIPTION
        "The AppleTalk Address of the network card.
         This variable is not implemented on the XLe adapters."
::= { lextalk 2 }

lextalkName OBJECT-TYPE
    SYNTAX  DisplayString (SIZE (0..32))
    ACCESS  read-only
    STATUS  mandatory
    DESCRIPTION
        "The AppleTalk name of this adapter.
         This variable is not implemented on the XLe adapters."
::= { lextalk 3 }

lextalkZone OBJECT-TYPE
    SYNTAX  DisplayString (SIZE (0..32))
    ACCESS  read-only
    STATUS  mandatory
    DESCRIPTION
        "The AppleTalk zone name of this adapter.
         This variable is not implemented on the XLe adapters."
::= { lextalk 4 }

lextalkType OBJECT-TYPE
    SYNTAX  DisplayString (SIZE (0..32))
    ACCESS  read-only
    STATUS  mandatory
    DESCRIPTION
        "The AppleTalk type of this adapter.
         This variable is not implemented on the XLe adapters."
    ::= { lextalk 5 }


-- The LexTCP Group

lextcpActivated OBJECT-TYPE
    SYNTAX  INTEGER {
        off(1),
        on(2)
        }
    ACCESS  read-write
    STATUS  mandatory
    DESCRIPTION
        "The activation status of the TCP/IP Protocol. If this
         variable is changed, the adapter must be reset before the
         change will take effect.  See opsysTimeToReset."
    ::= { lextcp 1 }

lextcpBootpEnable OBJECT-TYPE
    SYNTAX  INTEGER {
        disabled(1),
        enabled(2)
        }
    ACCESS  read-write
    STATUS  mandatory
    DESCRIPTION
        "The status of whether or not BOOTP is attempted to determine
         the IP parameters. If this variable is changed, the adapter
         must be reset before the change will take effect.  See
         opsysTimeToReset."
    ::= { lextcp 2 }

lextcpAddressServ OBJECT-TYPE
    SYNTAX  IpAddress
    ACCESS  read-only
    STATUS  mandatory
    DESCRIPTION
        "The IP address of the DHCP, BOOTP, or RARP server that
         provided the adapter's IP address."
    ::={ lextcp 3 }

lextcpNumNPAPservers OBJECT-TYPE
    SYNTAX  INTEGER
    ACCESS  read-only
    STATUS  mandatory
    DESCRIPTION
        "The maximum number of concurrent NPAP over TCP server
         connections."
    ::= { lextcp 4 }

lextcpNPAPserversTable OBJECT-TYPE
    SYNTAX  SEQUENCE OF LextcpNPAPserversEntry
    ACCESS  not-accessible
    STATUS  mandatory
    DESCRIPTION
        "A table of NPAP over TCP server information."
    ::= { lextcp 5 }

lextcpNPAPserversEntry OBJECT-TYPE
    SYNTAX  LextcpNPAPserversEntry
    ACCESS  not-accessible
    STATUS  mandatory
    DESCRIPTION
        "An entry containing NPAP over TCP server information."
    INDEX   { lextcpNPAPserverIndex }
    ::= { lextcpNPAPserversTable 1 }

LextcpNPAPserversEntry ::= SEQUENCE {
    lextcpNPAPserverIndex           INTEGER,
    lextcpNPAPserverAddress         IpAddress
    }

lextcpNPAPserverIndex OBJECT-TYPE
    SYNTAX  INTEGER (1..2147483647)
    ACCESS  read-only
    STATUS  mandatory
    DESCRIPTION
        "A unique value used by the adapter to identify NPAP
         over TCP servers."
    ::= { lextcpNPAPserversEntry 1 }

lextcpNPAPserverAddress OBJECT-TYPE
    SYNTAX  IpAddress
    ACCESS  read-only
    STATUS  mandatory
    DESCRIPTION
        "The IP address of this NPAP over TCP server."
    ::={ lextcpNPAPserversEntry 2 }


-- The HTTP Group

lexhttpEnable OBJECT-TYPE
    SYNTAX  INTEGER {
         disabled(1),
         enabled(2)
         }
    ACCESS  read-write
    STATUS  mandatory
    DESCRIPTION
        "The status of whether the adapter will enable the HTTP server.
         If this variable is changed, the adapter must be reset before
         the change will take effect.  See opsysTimeToReset."
    ::= { lexhttp 1 }

lexhttpNumLinks OBJECT-TYPE
    SYNTAX  INTEGER (0..65535)
    ACCESS  read-only
    STATUS  mandatory
    DESCRIPTION
        "The number of configurable HTTP links for the adapter."
    ::= { lexhttp 2 }

lexhttpBytesRemaining OBJECT-TYPE
    SYNTAX  INTEGER (0..65535)
    ACCESS  read-only
    STATUS  mandatory
    DESCRIPTION
        "The number of bytes available to store HTTP link and label
         information."
    ::= { lexhttp 3 }

lexhttpResetLinks OBJECT-TYPE
    SYNTAX  INTEGER {
        noReset(1),
        reset(2)
        }
    ACCESS  read-write
    STATUS  mandatory
    DESCRIPTION
        "A control for restoring default values for HTTP link settings.
         Setting the variable to reset will cause all of the
         HTTP link settings to be reset to their default values."
    ::= { lexhttp 4 }

lexhttpLinkTable OBJECT-TYPE
    SYNTAX  SEQUENCE OF LexhttpLinkTableEntry
    ACCESS  not-accessible
    STATUS  mandatory
    DESCRIPTION
        "A table of HTTP Link settings."
    ::= { lexhttp 5 }

lexhttpLinkTableEntry OBJECT-TYPE
    SYNTAX  LexhttpLinkTableEntry
    ACCESS  not-accessible
    STATUS  mandatory
    DESCRIPTION
        "An entry containing HTTP link settings."
    INDEX  { lexhttpLinkTableIndex }
   ::= { lexhttpLinkTable 1 }

LexhttpLinkTableEntry ::= SEQUENCE {
    lexhttpLinkTableIndex           INTEGER,
    lexhttpLinkTableStatus          INTEGER,
    lexhttpLinkTableLabel           DisplayString,
    lexhttpLinkTableURL             DisplayString
    }

lexhttpLinkTableIndex OBJECT-TYPE
    SYNTAX INTEGER(0..65535)
    ACCESS read-only
    STATUS mandatory
    DESCRIPTION
        "A unique value used by the adapter to identify HTTP link settings."
    ::= { lexhttpLinkTableEntry 1 }

lexhttpLinkTableStatus OBJECT-TYPE
    SYNTAX  INTEGER {
        linkOff(1),
        customOn(2),
        useDefault(3),
        defaultOff(4),
        defaultOn(5),
        eraseCustom(6)
        }
    ACCESS  read-write
    STATUS  mandatory
    DESCRIPTION
        "The status of the HTTP link.

         Get operation:
         linkOff       -- Server will not display the link
         personalOn    -- Server will display the custom link
         useDefault    -- Write-only
         defaultOff    -- Reserved
         defaultOn     -- Server will display the default link
         eraseCustom   -- Write-only

         Set operation:
         linkOff       -- Puts the link in linkOff status
         customOn      -- Puts the link in customOn status
         useDefault    -- Clears the Label and URL for this link and puts the
         .                link in defaultOn status
         defaultOff    -- Read-only
         defaultOn     -- Read-only
         eraseCustom   -- Clears the Label and URL for this link and puts the
         .                link in linkOff status"
    ::= { lexhttpLinkTableEntry 2 }

lexhttpLinkTableLabel OBJECT-TYPE
    SYNTAX  DisplayString (SIZE (0..255))
    ACCESS  read-write
    STATUS  mandatory
    DESCRIPTION
        "The text to be displayed as the label of this HTTP link.  It may be set
         to define a custom link.  Note that when read, this always reflects what
         the server would display.  As such, if the status of this link is
         defaultOn, it will not return your custom label if read even though it
         has been stored.  Setting the status for this link to customOn will
         activate your custom link label.  Remember that setting the status of
         this link to eraseCustom or useDefault clears this variable."
    ::= { lexhttpLinkTableEntry 3 }

lexhttpLinkTableURL OBJECT-TYPE
    SYNTAX  DisplayString (SIZE (0..255))
    ACCESS  read-write
    STATUS  mandatory
    DESCRIPTION
        "The URL to be hyperlinked to by the HTTP link.  It may be set to
         define a custom link.  Note that when read, this always reflects what
         the server would use.  As such, if the status of this link is
         defaultOn, it will not return your custom URL if read even though it
         has been stored.  Setting the status for this link to customOn will
         activate your custom link URL.  Remember that setting the status of
         this link to eraseCustom or useDefault clears this variable."
    ::= { lexhttpLinkTableEntry 4 }

lexhttpConfigEnable OBJECT-TYPE
    SYNTAX  INTEGER {
        disabled(1),
        enabled(2)
        }
    ACCESS  read-write
    STATUS  obsolete
    DESCRIPTION
        "The status of whether HTTP configuration page is enabled."
    ::= { lexhttp 6 }


-- The DHCP Group

lexdhcpDhcpEnable OBJECT-TYPE
    SYNTAX  INTEGER {
        disabled(1),
        enabled(2)
        }
    ACCESS  read-write
    STATUS  mandatory
    DESCRIPTION
        "The status of whether DHCP is enabled."
    ::= { lexdhcp 1 }

lexdhcpRarpEnable OBJECT-TYPE
    SYNTAX  INTEGER {
        disabled(1),
        enabled(2)
        }
    ACCESS  read-write
    STATUS  mandatory
    DESCRIPTION
        "The status of whether RARP is enabled."
    ::= { lexdhcp 2 }

lexdhcpAddressSource OBJECT-TYPE
    SYNTAX  INTEGER {
        manual(1),
        dhcp(2),
        bootp(3),
        rarp(4)
        }
    ACCESS  read-only
    STATUS  mandatory
    DESCRIPTION
        "The method by which the current IP parameters were obtained."
    ::= { lexdhcp 3 }

lexdhcpWinsStatus OBJECT-TYPE
    SYNTAX  INTEGER {
        unregistered(1),
        registered(2),
        pending(3),
        rejected(4)
        }
    ACCESS  read-only
    STATUS  mandatory
    DESCRIPTION
        "The adapter's WINS server registration status."
    ::= { lexdhcp 4 }

lexdhcpWinsServer OBJECT-TYPE
    SYNTAX  IpAddress
    ACCESS  read-only
    STATUS  mandatory
    DESCRIPTION
        "The IP address of the WINS server."
    ::= { lexdhcp 5 }

lexdhcpHostname OBJECT-TYPE
    SYNTAX  DisplayString (SIZE (1..63))
    ACCESS  read-write
    STATUS  mandatory
    DESCRIPTION
        "The adapter's TCP/IP hostname.
Setting 63 chars for OEM - MS310dn, 510dn, 610dn but other Lexmark Printers still max of 15 characters"
    ::= { lexdhcp 6 }

lexdhcpLeaseLength OBJECT-TYPE
    SYNTAX  INTEGER
    ACCESS  read-only
    STATUS  mandatory
    DESCRIPTION
        "The length of the adapter's DHCP address lease in seconds."
    ::= { lexdhcp 7 }

lexdhcpTimetoExpire OBJECT-TYPE
    SYNTAX  INTEGER
    ACCESS  read-only
    STATUS  mandatory
    DESCRIPTION
        "The number of seconds until the DHCP address lease expires."
    ::= { lexdhcp 8 }

lexdhcpDNSServer OBJECT-TYPE
    SYNTAX  IpAddress
    ACCESS  read-write
    STATUS  mandatory
    DESCRIPTION
        "The IP address of the DNS server."
    ::= { lexdhcp 9 }


-- The Hardware Group

lexhdwrNumPorts OBJECT-TYPE
    SYNTAX  INTEGER (0..65535)
    ACCESS  read-only
    STATUS  mandatory
    DESCRIPTION
        "The number of printer ports supported by this network adapter."
    ::= { lexhdwr 1 }

lexhdwrPortTable OBJECT-TYPE
    SYNTAX  SEQUENCE OF LexhdwrPortTableEntry
    ACCESS  not-accessible
    STATUS  mandatory
    DESCRIPTION
        "A table of the adapter's printer port hardware settings."
    ::= { lexhdwr 2 }

lexhdwrPortTableEntry OBJECT-TYPE
    SYNTAX  LexhdwrPortTableEntry
    ACCESS  not-accessible
    STATUS  mandatory
    DESCRIPTION
        "An entry containing printer port hardware settings."
    INDEX   { lexhdwrPortTableIndex }
    ::= { lexhdwrPortTable 1 }

LexhdwrPortTableEntry ::= SEQUENCE {
    lexhdwrPortTableIndex           INTEGER,
    lexhdwrPortTableType            INTEGER,
    lexhdwrPortTableParm1           INTEGER,
    lexhdwrPortTableParm2           INTEGER,
    lexhdwrPortTableParm3           INTEGER,
    lexhdwrPortTableParm4           INTEGER,
    lexhdwrPortTableParm5           INTEGER,
    lexhdwrPortTableParm6           INTEGER,
    lexhdwrPortTableParm7           INTEGER,
    lexhdwrPortTableParm8           INTEGER,
    lexhdwrPortTableParm9           INTEGER
    }

lexhdwrPortTableIndex OBJECT-TYPE
    SYNTAX  INTEGER (1..2147483647)
    ACCESS  read-only
    STATUS  mandatory
    DESCRIPTION
        "A unique value used by the adapter to identify printer ports."
    ::= { lexhdwrPortTableEntry 1 }

lexhdwrPortTableType OBJECT-TYPE
    SYNTAX INTEGER {
        internal(1),
        parallel(2),
        serial(3)
        }
    ACCESS read-only
    STATUS mandatory
    DESCRIPTION
        "The type of attachment for this printer port."
    ::= { lexhdwrPortTableEntry 2 }

lexhdwrPortTableParm1 OBJECT-TYPE
    SYNTAX INTEGER
    ACCESS read-write
    STATUS mandatory
    DESCRIPTION
        "For serial and parallel ports, this is the port timeout in seconds.

         For internal ports, this parameter is unused."
    ::= { lexhdwrPortTableEntry 3 }

lexhdwrPortTableParm2 OBJECT-TYPE
    SYNTAX INTEGER
    ACCESS read-write
    STATUS mandatory
    DESCRIPTION
        "For serial ports, this is the baud rate in bits per second.

         For parallel ports, this is the port mode and is defined as follows:
         standard(0),
         enhanced(1)

         For internal ports, this parameter is unused."
    ::= { lexhdwrPortTableEntry 4 }

lexhdwrPortTableParm3 OBJECT-TYPE
    SYNTAX INTEGER
    ACCESS read-write
    STATUS mandatory
    DESCRIPTION
        "For serial ports, this is the parity and is defined as follows:
         none(0),
         odd(1),
         even(2),
         space(3),
         mark(4)

         For parallel and internal ports, this parameter is unused."
    ::= { lexhdwrPortTableEntry 5 }

lexhdwrPortTableParm4 OBJECT-TYPE
    SYNTAX INTEGER
    ACCESS read-write
    STATUS mandatory
    DESCRIPTION
        "For serial ports, this is the number of data bits.

         For parallel and internal ports, this parameter is unused."
    ::= { lexhdwrPortTableEntry 6 }

lexhdwrPortTableParm5 OBJECT-TYPE
    SYNTAX INTEGER
    ACCESS read-write
    STATUS mandatory
    DESCRIPTION
        "For serial ports, this is the number of stop bits and is defined
         as follows:
         bitsOne(2),
         bitsOneAndHalf(3),
         bitsTwo(4)

         For parallel and internal ports, this parameter is unused."
    ::= { lexhdwrPortTableEntry 7 }

lexhdwrPortTableParm6 OBJECT-TYPE
    SYNTAX INTEGER
    ACCESS read-write
    STATUS mandatory
    DESCRIPTION
        "For serial ports, this is the pacing mode and is defined as follows:
         paceDtr(0),
         paceXonXff(1)

         For non XLe parallel ports, this is the parallel protocol and is defined
         as follows:
         auto(2),
         ecp(3),
         byte(4),
         nibble(5),
         compatible(6)

         For internal ports, and XLe parallel ports this parameter is unused."
    ::= { lexhdwrPortTableEntry 8 }

lexhdwrPortTableParm7 OBJECT-TYPE
    SYNTAX INTEGER {
       off(1),
       on(2),
       auto(3)
       }
    ACCESS read-write
    STATUS mandatory
    DESCRIPTION
        "For all ports, this is the configured NPAP mode. For internal ports this is a read-only variable."
    ::= { lexhdwrPortTableEntry 9 }

lexhdwrPortTableParm8 OBJECT-TYPE
    SYNTAX INTEGER {
       npapInactive(1),
       npapActive(2)
       }
    ACCESS read-only
    STATUS mandatory
    DESCRIPTION
        "For all ports, this is the NPAP status. For internal ports this is a read-only variable."
    ::= { lexhdwrPortTableEntry 10 }

lexhdwrPortTableParm9 OBJECT-TYPE
    SYNTAX INTEGER {
       printer(1),
       fax(2)
       }
    ACCESS read-write
    STATUS mandatory
    DESCRIPTION
        "For serial ports, this is the class of device attached.

         This variable is unused on the XLe adapters."
    ::= { lexhdwrPortTableEntry 11 }


-- The MAC Group

lexmacType OBJECT-TYPE
    SYNTAX  DisplayString (SIZE (0..255))
    ACCESS  read-only
    STATUS  mandatory
    DESCRIPTION
        "A textual representation of network medium to which the network
         adapter is attached (e.g. Ethernet)."
    ::= { lexmac 1 }

lexmacSpeed OBJECT-TYPE
    SYNTAX  Gauge
    ACCESS  read-only
    STATUS  mandatory
    DESCRIPTION
        "The speed, in bits per second, of the network medium to which the
         network adapter is attached."
    ::= { lexmac 2 }

lexmacConnType OBJECT-TYPE
    SYNTAX  INTEGER {
       aui(1),
       bnc(2),
       stp(3),
       utp(4)
       }
    ACCESS  read-only
    STATUS  mandatory
    DESCRIPTION
        "The connection type by which the network adapter is connected to
         the network medium."
    ::= { lexmac 3 }

lexmacUAA OBJECT-TYPE
    SYNTAX  PhysAddress
    ACCESS  read-only
    STATUS  mandatory
    DESCRIPTION
        "The network adapter's universally administered network address."
    ::= { lexmac 4 }

lexmacLAA OBJECT-TYPE
    SYNTAX  PhysAddress
    ACCESS  read-only
    STATUS  mandatory
    DESCRIPTION
        "The network adapter's locally administered network address.  A
         value of all zeros indicates that the LAA is not in use."
    ::= { lexmac 5 }


-- The Trap Group

lextrapDestNum OBJECT-TYPE
    SYNTAX  INTEGER
    ACCESS  read-only
    STATUS  mandatory
    DESCRIPTION
        "The maximum number of IP trap destinations supported by this
         network adapter."
    ::={ lextrap 1 }

-- The Trap Destination Table (IP)

lextrapDestTable OBJECT-TYPE
    SYNTAX  SEQUENCE OF LextrapDestEntry
    ACCESS  not-accessible
    STATUS  mandatory
    DESCRIPTION
        "A table of IP trap destination configurations."
    ::= { lextrap 2 }

lextrapDestEntry OBJECT-TYPE
    SYNTAX  LextrapDestEntry
    ACCESS  not-accessible
    STATUS  mandatory
    DESCRIPTION
        "An entry containing an IP trap destination configuration."
    INDEX    { lextrapDestIndex }
    ::= { lextrapDestTable 1 }

LextrapDestEntry ::= SEQUENCE {
    lextrapDestIndex                INTEGER,
    lextrapDestIPAddr               IpAddress,
    lextrapDestMask                 INTEGER
    }

lextrapDestIndex OBJECT-TYPE
    SYNTAX  INTEGER (1..2147483647)
    ACCESS  read-only
    STATUS  mandatory
    DESCRIPTION
        "A unique value used by the adapter to identify IP trap destinations."
    ::= { lextrapDestEntry 1 }

lextrapDestIPAddr OBJECT-TYPE
    SYNTAX  IpAddress
    ACCESS  read-write
    STATUS  mandatory
    DESCRIPTION
        "The IP address of the trap destination."
    ::= { lextrapDestEntry 2 }

lextrapDestMask OBJECT-TYPE
    SYNTAX  INTEGER (0..65535)
    ACCESS  read-write
    STATUS  mandatory
    DESCRIPTION
        "The trap mask for the trap destination.  It is implemented as a
         bitmap specifying a mask of intervention required conditions for
         which the adapter should send trap messages.  Setting a bit to 1
         enables the corresponding trap.  A value of 1023 will cause the
         adapter to send traps for all intervention required conditions.

         The bitmap is defined below:

         Bit  Value  Condition
         ---  -----  --------------------------
         0    1      Output hopper full
         1    2      Load Paper
         2    4      Paper Jam
         3    8      Toner Low
         4    16     Service Required
         5    32     Disk Error
         6    64     Cover Opened
         7    128    Page Complexity Error
         8    256    Offline
         9    512    Printer MIB (RFC 1759)"
    ::= { lextrapDestEntry 3 }

lextrapIPTrapType OBJECT-TYPE
    SYNTAX  INTEGER {
         multiplexed(1),
         individual(2)
         }
    ACCESS  read-write
    STATUS  mandatory
    DESCRIPTION
        "The type of SNMP over IP traps that will be sent by the adapter.

         Setting this variable to multiplexed(1) configures all intervention
         required conditions to send an irCondition trap (specific trap number 1)
         and for the clearing of intervention required conditions to send an
         irCleared trap (specific trap number 0).

         Setting this variable to individual(2) causes each intervention required
         condition to send its corresponding trap (specific traps numbered 2
         through 10) and for the clearing of intervention required conditions
         to cause an irClearedTypeII trap (specific trap number 11).

         See the Trap Definitions Group for more information.

         Type 1 is the default for IP."
    ::= { lextrap 3 }

-- The Time Group

timeReset OBJECT-TYPE
    SYNTAX  INTEGER {
        noReset(1),
        reset(2)
        }
    ACCESS  read-write
    STATUS  mandatory
    DESCRIPTION
        "A control for initiating an update of the system time and date using
         the specified timeSource.  Setting the variable to reset will cause
         the system to update it's time and date using the specified time source.
         See timeSource."
    ::={ time 1 }

timeSource OBJECT-TYPE
    SYNTAX  INTEGER {
        none(1),        -- Do not use an external source to update clock
        ntp(2),         -- Use NTP/SNTP server per RFC2030
        netware(3)      -- Use an attached Netware server
        }
    ACCESS  read-write
    STATUS  mandatory
    DESCRIPTION
        "The source for setting the system time and date.  If this variable
         is changed, the time must be reset before the change will have an effect.
         See timeReset."
    ::={ time 2 }

timeUTCOffset OBJECT-TYPE
    SYNTAX  INTEGER (-720..720)
    ACCESS  read-only
    STATUS  mandatory
    DESCRIPTION
        "The offset in minutes from UTC (formerly GMT) of local time.  Use a
         negative value if West of UTC.  Use a positive value if East of UTC."
    ::={ time 3 }

timeDSTEnable OBJECT-TYPE
    SYNTAX  INTEGER {
        disabled(1),
        enabled(2)
        }
    ACCESS  read-write
    STATUS  mandatory
    DESCRIPTION
        "The status of whether automatic Daylight Savings Time adjust is enabled.
         See timeDSTStartDate, timeDSTEndDate, and timeDSTOffset for configuration
         options."
    ::={ time 4 }

timeDSTStartDate OBJECT-TYPE
    SYNTAX  OCTET STRING (SIZE (11))
    ACCESS  read-only
    STATUS  mandatory
    DESCRIPTION
        "A textual representation of the day and time the Daylight Savings Time
         adjust should start if enabled (see timeDSTEnable).  The format of string
         is as follows:

         Byte Meaning
         ---- ------------------------------------------------------------
         0    Which occurence in the month of the day specified in byte 1.
              Valid values are:
                F => First Occurence
                1 => First Occurence
                2 => Second Occurence
                3 => Third Occurence
                4 => Fourth Occurence
                5 => Fifth Occurence
                L => Last Occurence
         1    A 1-digit field indicating the day of week (0=Sun..6=Sat)
         2-3  A 2-digit field indicating the month.
         4-5  A 2-digit field indicating the hour
         6-7  A 2-digit field indicating the minute
         8-9  A 2-digit field indicating the second

         The default setting is F004020000 which corresponds to the first Sunday
         of April at 2:00:00 am."
    ::={ time 5 }

timeDSTEndDate OBJECT-TYPE
    SYNTAX  OCTET STRING (SIZE (11))
    ACCESS  read-only
    STATUS  mandatory
    DESCRIPTION
        "A textual representation of the day and time the Daylight Savings Time
         adjust should end if enabled (see timeDSTEnable).  The format of string
         is as defined for timeDSTStartDate

         The default setting is L010020000 which corresponds to the last Sunday
         of October at 2:00:00 am."
    ::={ time 6 }

timeDSTOffset OBJECT-TYPE
    SYNTAX  INTEGER (0..120)
    ACCESS  read-only
    STATUS  mandatory
    DESCRIPTION
        "The offset in minutes that should be applied to local time during Daylight
         Savings Time."
    ::={ time 7 }

timeServerAddress OBJECT-TYPE
    SYNTAX  IpAddress
    ACCESS  read-write
    STATUS  mandatory
    DESCRIPTION
        "If the specified time source is NTP (see timeSource), this is the IP address
         of the NTP server to use.  Otherwise, the value is ignored."
    ::={ time 8 }

timeServerName OBJECT-TYPE
    SYNTAX  DisplayString (SIZE (0..63))
    ACCESS  read-write
    STATUS  mandatory
    DESCRIPTION
        "If the specified time source is NTP (see timeSource), and the NTP server
         address is not set (0.0.0.0), this is the DNS domainname of the NTP server.

         If the specified time source is Netware (see timeSource), the is the name of
         Netware server.  Otherwise, the value is ignored."
    ::={ time 9 }


-- The General Printer Group

prtgenNumber OBJECT-TYPE
    SYNTAX  INTEGER
    ACCESS  read-only
    STATUS  mandatory
    DESCRIPTION
        "The number of printers, regardless of their current state,
         available to this adapter."
    ::= { prtgen 1 }

prtgenInfoTable OBJECT-TYPE
    SYNTAX  SEQUENCE OF PrtgenInfoEntry
    ACCESS  not-accessible
    STATUS  mandatory
    DESCRIPTION
        "A table of the network adapter's attached printer information."
    ::= { prtgen 2 }

prtgenInfoEntry OBJECT-TYPE
    SYNTAX  PrtgenInfoEntry
    ACCESS  not-accessible
    STATUS  mandatory
    DESCRIPTION
        "An entry containing attached printer information."
    INDEX   { prtgenPrinterIndex }
    ::= { prtgenInfoTable 1 }

PrtgenInfoEntry ::= SEQUENCE {
    prtgenPrinterIndex              INTEGER,
    prtgenPrinterName               DisplayString,
    prtgenPeripheralID              DisplayString,
    prtgenCodeRevision              DisplayString,
    prtgenResValue                  INTEGER,
    prtgenSerialNo                  DisplayString,
    prtgenAssetTag			 DisplayString
    }

prtgenPrinterIndex OBJECT-TYPE
    SYNTAX  INTEGER (1..2147483647)
    ACCESS  read-only
    STATUS  mandatory
    DESCRIPTION
        "A unique value used by the network adapter to identify attached
         printers."
    ::= { prtgenInfoEntry 1 }

prtgenPrinterName OBJECT-TYPE
    SYNTAX  DisplayString (SIZE (0..255))
    ACCESS  read-only
    STATUS  mandatory
    DESCRIPTION
        "A textual description of the make and model of the attached printer,
         if known."
    ::= { prtgenInfoEntry 2 }

prtgenPeripheralID OBJECT-TYPE
    SYNTAX  DisplayString (SIZE (0..255))
    ACCESS  read-only
    STATUS  mandatory
    DESCRIPTION
        "A textual description of the peripheral ID of the attached printer
         as defined by the IEEE 1284 standard, if known."
    ::= { prtgenInfoEntry 3 }

prtgenCodeRevision OBJECT-TYPE
    SYNTAX  DisplayString (SIZE (0..255))
    ACCESS  read-only
    STATUS  mandatory
    DESCRIPTION
        "A textual representation of the code revision level of the attached
         printer, if known."
    ::= { prtgenInfoEntry 4 }

prtgenResValue OBJECT-TYPE
    SYNTAX  INTEGER
    ACCESS  read-only
    STATUS  mandatory
    DESCRIPTION
        "This object is currently unused and reserved."
    ::= { prtgenInfoEntry 5 }

prtgenSerialNo OBJECT-TYPE
    SYNTAX  DisplayString (SIZE (0..255))
    ACCESS  read-only
    STATUS  mandatory
    DESCRIPTION
        "A textual representation of the serial number of the attached
         printer, if known."
    ::= { prtgenInfoEntry 6 }

prtgenAssetTag OBJECT-TYPE
    SYNTAX  DisplayString (SIZE (0..255))
    ACCESS  read-write
    STATUS  mandatory
    DESCRIPTION
        "A textual representation of the asset tag of the
         printer, if known."
    ::= { prtgenInfoEntry 7 }

prtgenStatusTable OBJECT-TYPE
    SYNTAX  SEQUENCE OF PrtgenStatusEntry
    ACCESS  not-accessible
    STATUS  mandatory
    DESCRIPTION
        "A table of the network adapter's attached printer status."
    ::= { prtgen 3 }

prtgenStatusEntry OBJECT-TYPE
    SYNTAX  PrtgenStatusEntry
    ACCESS  not-accessible
    STATUS  mandatory
    DESCRIPTION
        "An entry containing attached printer status."
    INDEX   { prtgenStatPrinterIndex }
    ::= { prtgenStatusTable 1 }

PrtgenStatusEntry ::= SEQUENCE {
    prtgenStatPrinterIndex          INTEGER,
    prtgenStatusIRC                 INTEGER,
    prtgenStatusOutHopFull          INTEGER,
    prtgenStatusInputEmpty          INTEGER,
    prtgenStatusPaperJam            INTEGER,
    prtgenStatusTonerError          INTEGER,
    prtgenStatusSrvcReqd            INTEGER,
    prtgenStatusDiskError           INTEGER,
    prtgenStatusCoverOpen           INTEGER,
    prtgenStatusPageComplex         INTEGER,
    prtgenStatusLineStatus          INTEGER,
    prtgenStatusBusy                INTEGER,
    prtgenStatusWaiting             INTEGER,
    prtgenStatusWarming             INTEGER,
    prtgenStatusPrinting            INTEGER
    }

prtgenStatPrinterIndex OBJECT-TYPE
    SYNTAX  INTEGER (1..2147483647)
    ACCESS  read-only
    STATUS  mandatory
    DESCRIPTION
        "A unique value used by the network adapter to identify attached
         printers."
    ::= { prtgenStatusEntry 1 }

prtgenStatusIRC OBJECT-TYPE
    SYNTAX  INTEGER
    ACCESS  read-only
    STATUS  mandatory
    DESCRIPTION
        "The printer's current intervention required code."
    ::= { prtgenStatusEntry 2 }

prtgenStatusOutHopFull OBJECT-TYPE
    SYNTAX  INTEGER {
        notFull(1),
        full(2),
        unknown(3)
        }
    ACCESS  read-only
    STATUS  mandatory
    DESCRIPTION
        "The printer's current output hopper status."
    ::= { prtgenStatusEntry 3 }

prtgenStatusInputEmpty OBJECT-TYPE
    SYNTAX  INTEGER {
        notEmpty(1),
        empty(2),
        unknown(3)
        }
    ACCESS  read-only
    STATUS  mandatory
    DESCRIPTION
        "The printer's current active input paper tray status."
    ::= { prtgenStatusEntry 4 }

prtgenStatusPaperJam OBJECT-TYPE
    SYNTAX  INTEGER {
        notJammed(1),
        jamed(2),
        unknown(3)
        }
    ACCESS  read-only
    STATUS  mandatory
    DESCRIPTION
        "The printer's current paper path status."
    ::= { prtgenStatusEntry 5 }

prtgenStatusTonerError OBJECT-TYPE
    SYNTAX  INTEGER {
        noTonerError(1),
        tonerError(2),
        unknown(3)
        }
    ACCESS  read-only
    STATUS  mandatory
    DESCRIPTION
        "The printer's current toner supply status."
    ::= { prtgenStatusEntry 6 }

prtgenStatusSrvcReqd OBJECT-TYPE
    SYNTAX  INTEGER {
        noServiceRequired(1),
        serviceRequired(2),
        unknown(3)
        }
    ACCESS  read-only
    STATUS  mandatory
    DESCRIPTION
        "The printer's current service required status."
    ::= { prtgenStatusEntry 7 }

prtgenStatusDiskError OBJECT-TYPE
    SYNTAX  INTEGER {
        noDiskError(1),
        diskError(2),
        unknown(3)
        }
    ACCESS  read-only
    STATUS  mandatory
    DESCRIPTION
        "The printer's current disk sub-system status."
    ::= { prtgenStatusEntry 8 }

prtgenStatusCoverOpen OBJECT-TYPE
    SYNTAX  INTEGER {
        noCoverOpen(1),
        coverOpen(2),
        unknown(3)
        }
    ACCESS  read-only
    STATUS  mandatory
    DESCRIPTION
        "The printer's current cover status."
    ::= { prtgenStatusEntry 9 }

prtgenStatusPageComplex OBJECT-TYPE
    SYNTAX  INTEGER {
        noComplexPage(1),
        complexPage(2),
        unknown(3)
        }
    ACCESS  read-only
    STATUS  mandatory
    DESCRIPTION
        "The printer's current complex page status."
    ::= { prtgenStatusEntry 10 }

prtgenStatusLineStatus OBJECT-TYPE
    SYNTAX  INTEGER {
        online(1),
        offline(2),
        unknown(3)
        }
    ACCESS  read-only
    STATUS  mandatory
    DESCRIPTION
        "The printer's current online/offline status."
    ::= { prtgenStatusEntry 11 }

prtgenStatusBusy OBJECT-TYPE
    SYNTAX  INTEGER {
        notBusy(1),
        busy(2),
        unknown(3)
        }
    ACCESS  read-only
    STATUS  mandatory
    DESCRIPTION
        "The printer's current bust status."
    ::= { prtgenStatusEntry 12 }

prtgenStatusWaiting OBJECT-TYPE
    SYNTAX  INTEGER {
        notWaiting(1),
        waiting(2),
        unknown(3)
        }
    ACCESS  read-only
    STATUS  mandatory
    DESCRIPTION
        "The printer's current waiting status."
    ::= { prtgenStatusEntry 13 }

prtgenStatusWarming OBJECT-TYPE
    SYNTAX  INTEGER {
        notWarming(1),
        warming(2),
        unknown(3)
        }
    ACCESS  read-only
    STATUS  mandatory
    DESCRIPTION
        "The printer's current warming status."
    ::= { prtgenStatusEntry 14 }

prtgenStatusPrinting OBJECT-TYPE
    SYNTAX  INTEGER {
        notPrinting(1),
        printing(2),
        unknown(3)
        }
    ACCESS  read-only
    STATUS  mandatory
    DESCRIPTION
        "The printer's current printing status."
    ::= { prtgenStatusEntry 15 }

prtgenFamilyID OBJECT-TYPE
    SYNTAX  INTEGER
    ACCESS  read-only
    STATUS  mandatory
    DESCRIPTION
        "The printer's NPA family ID."
    ::= { prtgen 4 }

-- The Printer Page Count Group

pgTotal OBJECT-TYPE
    SYNTAX  Counter
    ACCESS  read-only
    STATUS  mandatory
    DESCRIPTION
        "The total number of pages printed."
    ::= { pgcount 1 }

pgMono OBJECT-TYPE
    SYNTAX  Counter
    ACCESS  read-only
    STATUS  mandatory
    DESCRIPTION
        "The number of monochrome pages printed."
    ::= { pgcount 2 }

pgColor OBJECT-TYPE
    SYNTAX  Counter
    ACCESS  read-only
    STATUS  mandatory
    DESCRIPTION
        "The number of color pages printed."
    ::= { pgcount 3 }

-- The recieve fax group

faxNumber OBJECT-TYPE
    SYNTAX  INTEGER
    ACCESS  read-only
    STATUS  mandatory
    DESCRIPTION
        "The number of fax modems attached to the adapter."
    ::= { fax 1 }

faxTable OBJECT-TYPE
    SYNTAX  SEQUENCE OF FaxEntry
    ACCESS  not-accessible
    STATUS  mandatory
    DESCRIPTION
        "A table of the network adapter's attached fax modems configuration data."
    ::= { fax 2 }

faxEntry OBJECT-TYPE
    SYNTAX  FaxEntry
    ACCESS  not-accessible
    STATUS  mandatory
    DESCRIPTION
        "An entry containing attached fax modem configuration data."
    INDEX   { faxIndex }
    ::= { faxTable 1 }

FaxEntry ::= SEQUENCE {
    faxIndex                        INTEGER,
    faxPort                         INTEGER,
    faxAdapterCapabilities          INTEGER,
    faxModemCapabilities            INTEGER,
    faxSelectedCapabilities         INTEGER,
    faxActiveCapabilities           INTEGER,
    faxIDString                     DisplayString,
    faxInitString                   DisplayString,
    faxNumberRings                  INTEGER,
    faxScaling                      INTEGER,
    faxBinaryEncoding               INTEGER,
    faxPrinterPort                  INTEGER,
    faxInputTray                    INTEGER,
    faxOutputBin                    INTEGER
    }

faxIndex OBJECT-TYPE
    SYNTAX  INTEGER (1..2147483647)
    ACCESS  read-only
    STATUS  mandatory
    DESCRIPTION
        "A unique value used by the adapter to identify fax ports."
    ::= { faxEntry 1 }

faxPort OBJECT-TYPE
    SYNTAX  INTEGER {
        serial1(145),
        serial2(146),
        serial3(147),
        serial4(148),
        serial5(149)
        }
    ACCESS  read-only
    STATUS  mandatory
    DESCRIPTION
        "The network adapter's port to which this modem is attached."
    ::= { faxEntry 2 }

faxAdapterCapabilities OBJECT-TYPE
    SYNTAX  INTEGER (0..2147483647)
    ACCESS  read-only
    STATUS  mandatory
    DESCRIPTION
        "A bitmap representing the fax capabilities of the network adapter.

         Bit  Value   Capabilities
         ---  ------  --------------------
         0    1       Fine Resolution
         1    2       2D Encoding
         2    4       T6 Encoding
         3    8       ECM
         4    16      Binary File Transfer
         5    32      300 x 300
         6    64      400 x 400
         7    128     200 x 400
         8    256     Uncompressed Mode
         9    512     255mm Width
         10   1024    303mm Width
         11   2048    Legal Length
         12   4096    Unlimited Length
         13   8192    V.17 (14400)
         14   16384   V.33 (14400)
         15   32768   V.29 and V.27 (9600)
         16   65536   V.29 (9600)
         17   131072  V.27 (4800)
         18   262144  V27 (2400)"
    ::= { faxEntry 3 }

faxModemCapabilities OBJECT-TYPE
    SYNTAX  INTEGER (0..2147483647)
    ACCESS  read-only
    STATUS  mandatory
    DESCRIPTION
        "A bitmap representing the fax capabilities of the attached modem.

         Bit  Value   Capabilities
         ---  ------  --------------------
         0    1       Fine Resolution
         1    2       2D Encoding
         2    4       T6 Encoding
         3    8       ECM
         4    16      Binary File Transfer
         5    32      300 x 300
         6    64      400 x 400
         7    128     200 x 400
         8    256     Uncompressed Mode
         9    512     255mm Width
         10   1024    303mm Width
         11   2048    Legal Length
         12   4096    Unlimited Length
         13   8192    V.17 (14400)
         14   16384   V.33 (14400)
         15   32768   V.29 and V.27 (9600)
         16   65536   V.29 (9600)
         17   131072  V.27 (4800)
         18   262144  V27 (2400)"
    ::= { faxEntry 4 }

faxSelectedCapabilities OBJECT-TYPE
    SYNTAX  INTEGER (0..2147483647)
    ACCESS  read-write
    STATUS  mandatory
    DESCRIPTION
        "A bitmap representing the user selected fax capabilities.

         Bit  Value   Capabilities
         ---  ------  --------------------
         0    1       Fine Resolution
         1    2       2D Encoding
         2    4       T6 Encoding
         3    8       ECM
         4    16      Binary File Transfer
         5    32      300 x 300
         6    64      400 x 400
         7    128     200 x 400
         8    256     Uncompressed Mode
         9    512     255mm Width
         10   1024    303mm Width
         11   2048    Legal Length
         12   4096    Unlimited Length
         13   8192    V.17 (14400)
         14   16384   V.33 (14400)
         15   32768   V.29 and V.27 (9600)
         16   65536   V.29 (9600)
         17   131072  V.27 (4800)
         18   262144  V27 (2400)"
    ::= { faxEntry 5 }

faxActiveCapabilities OBJECT-TYPE
    SYNTAX  INTEGER (0..2147483647)
    ACCESS  read-only
    STATUS  mandatory
    DESCRIPTION
        "A bitmap representing the active fax capabilities.  This is
        the logical and of faxAdapterCapabilities, faxModemCapabilities,
        and faxSelectedCapabilities.

         Bit  Value   Capabilities
         ---  ------  --------------------
         0    1       Fine Resolution
         1    2       2D Encoding
         2    4       T6 Encoding
         3    8       ECM
         4    16      Binary File Transfer
         5    32      300 x 300
         6    64      400 x 400
         7    128     200 x 400
         8    256     Uncompressed Mode
         9    512     255mm Width
         10   1024    303mm Width
         11   2048    Legal Length
         12   4096    Unlimited Length
         13   8192    V.17 (14400)
         14   16384   V.33 (14400)
         15   32768   V.29 and V.27 (9600)
         16   65536   V.29 (9600)
         17   131072  V.27 (4800)
         18   262144  V27 (2400)"
    ::= { faxEntry 6 }

faxIDString OBJECT-TYPE
    SYNTAX  DisplayString (SIZE (0..20))
    ACCESS  read-write
    STATUS  mandatory
    DESCRIPTION
        "The textual identification that is used to identify this fax device.
         This text is sent to a connected fax device at the start of a call."
    ::= { faxEntry 7 }

faxInitString OBJECT-TYPE
    SYNTAX  DisplayString (SIZE (0..128))
    ACCESS  read-write
    STATUS  mandatory
    DESCRIPTION
        "The commands used be the network adapter to initialize an attached modem."
    ::= { faxEntry 8 }

faxNumberRings OBJECT-TYPE
    SYNTAX  INTEGER (1..255)
    ACCESS  read-write
    STATUS  mandatory
    DESCRIPTION
        "The number of rings that the network adapter should wait before answering."
    ::= { faxEntry 9 }

faxScaling OBJECT-TYPE
    SYNTAX  INTEGER {
       scaleToFit(1),
       cropToFit(2)
       }
    ACCESS  read-write
    STATUS  mandatory
    DESCRIPTION
        "The mechanism used to resolve size descrepancies between the received fax
         the printer's available forms."
    ::= { faxEntry 10 }

faxBinaryEncoding OBJECT-TYPE
    SYNTAX  INTEGER {
       taggedBinary(1),
       ascii85(2)
       }
    ACCESS  read-write
    STATUS  mandatory
    DESCRIPTION
        "The encoding used when sending fax data to the attached printer."
    ::= { faxEntry 11 }

faxPrinterPort OBJECT-TYPE
    SYNTAX  INTEGER {
       parallel1(129),
       parallel2(130),
       firstAvail(255)
       }
    ACCESS  read-write
    STATUS  mandatory
    DESCRIPTION
        "The port (printer) to which received faxes should be printed."
    ::= { faxEntry 13 }

faxInputTray OBJECT-TYPE
    SYNTAX  INTEGER
    ACCESS  read-write
    STATUS  mandatory
    DESCRIPTION
        "The input tray from which received faxes should be printed.
         The value 255 indicates printer default."
    ::= { faxEntry 14 }

faxOutputBin OBJECT-TYPE
    SYNTAX  INTEGER
    ACCESS  read-write
    STATUS  mandatory
    DESCRIPTION
        "The output bin to which received faxes should be printed.
         The value 255 indicates printer default."
    ::= { faxEntry 15 }

-- The Trap Definitions Group

irCleared TRAP-TYPE
    ENTERPRISE adapter
    VARIABLES  {prtgenStatusIRC}
    DESCRIPTION "The condition on the printer has been cleared."
    -- NMS trap annotation
    --#TYPE "Lexmark: error condition cleared (type 1)"
    --#SUMMARY "The condition on the printer has been cleared"
    --#ARGUMENTS {}
    --#SEVERITY INFORMATIONAL
    --#TIMEINDEX 6
    --#HELP "lexmib.hlp"
    --#HELPTAG 60002
    --#STATE OPERATIONAL
    ::= 0

irCondition TRAP-TYPE
    ENTERPRISE adapter
    VARIABLES  {prtgenStatusIRC}
    DESCRIPTION "An error condition exists on the printer"
    -- NMS trap annotation
    --#TYPE "Lexmark: error on the printer (type 1)"
    --#SUMMARY "An error condition exists on the printer"
    --#ARGUMENTS {}
    --#SEVERITY MAJOR
    --#TIMEINDEX 6
    --#HELP "lexmib.hlp"
    --#HELPTAG 60001
    --#STATE DEGRADED
    ::= 1

irOutputFull TRAP-TYPE
    ENTERPRISE adapter
    VARIABLES  {prtgenStatusIRC}
    DESCRIPTION "The printers output bin is full."
    -- NMS trap annotation
    --#TYPE "Lexmark: output bin full."
    --#SUMMARY "The printers output bin is full. Printing cannot continue until the condition is cleared."
    --#ARGUMENTS {}
    --#SEVERITY MAJOR
    --#TIMEINDEX 6
    --#HELP "lexmib.hlp"
    --#HELPTAG 60003
    --#STATE DEGRADED
    ::= 2

irLoadPaper TRAP-TYPE
    ENTERPRISE adapter
    VARIABLES  {prtgenStatusIRC}
    DESCRIPTION "Load paper on the printer"
    -- NMS trap annotation
    --#TYPE "Lexmark: out of paper."
    --#SUMMARY "Load paper on the printer. Printing cannot continue until the condition is cleared."
    --#ARGUMENTS {}
    --#SEVERITY MAJOR
    --#TIMEINDEX 6
    --#HELP "lexmib.hlp"
    --#HELPTAG 60004
    --#STATE DEGRADED
    ::= 3

irPaperJam TRAP-TYPE
    ENTERPRISE adapter
    VARIABLES  {prtgenStatusIRC}
    DESCRIPTION "Paper jam on the printer."
    -- NMS trap annotation
    --#TYPE "Lexmark: paper jam."
    --#SUMMARY "Paper jam on the printer. Printing cannot continue until the condition is cleared."
    --#ARGUMENTS {}
    --#SEVERITY MAJOR
    --#TIMEINDEX 6
    --#HELP "lexmib.hlp"
    --#HELPTAG 60005
    --#STATE DEGRADED
    ::= 4

irTonerLow TRAP-TYPE
    ENTERPRISE adapter
    VARIABLES  {prtgenStatusIRC}
    DESCRIPTION "Toner low on the printer"
    -- NMS trap annotation
    --#TYPE "Lexmark: toner low."
    --#SUMMARY "Toner low on the printer. Printing will continue."
    --#ARGUMENTS {}
    --#SEVERITY MAJOR
    --#TIMEINDEX 6
    --#HELP "lexmib.hlp"
    --#HELPTAG 60006
    --#STATE DEGRADED
    ::= 5

irServiceReq TRAP-TYPE
    ENTERPRISE adapter
    VARIABLES  {prtgenStatusIRC}
    DESCRIPTION "Service required on the printer"
    -- NMS trap annotation
    --#TYPE "Lexmark: service required."
    --#SUMMARY "Service required on the printer. Printing cannot continue until the condition is cleared."
    --#ARGUMENTS {}
    --#SEVERITY MAJOR
    --#TIMEINDEX 6
    --#HELP "lexmib.hlp"
    --#HELPTAG 60007
    --#STATE DEGRADED
    ::= 6

irDiskErr TRAP-TYPE
    ENTERPRISE adapter
    VARIABLES  {prtgenStatusIRC}
    DESCRIPTION "Disk error on the printer"
    -- NMS trap annotation
    --#TYPE "Lexmark: disk error."
    --#SUMMARY "Disk error on the printer. Printing cannot continue until the condition is cleared."
    --#ARGUMENTS {}
    --#SEVERITY MAJOR
    --#TIMEINDEX 6
    --#HELP "lexmib.hlp"
    --#HELPTAG 60008
    --#STATE DEGRADED
    ::= 7

irCoverOpen TRAP-TYPE
    ENTERPRISE adapter
    VARIABLES  {prtgenStatusIRC}
    DESCRIPTION "Cover open on the printer"
    -- NMS trap annotation
    --#TYPE "Lexmark: cover open."
    --#SUMMARY "Cover open on the printer. Printing cannot continue until the condition is cleared."
    --#ARGUMENTS {}
    --#SEVERITY MAJOR
    --#TIMEINDEX 6
    --#HELP "lexmib.hlp"
    --#HELPTAG 60009
    --#STATE DEGRADED
    ::= 8

irPageComplexity TRAP-TYPE
    ENTERPRISE adapter
    VARIABLES  {prtgenStatusIRC}
    DESCRIPTION "Page complexity error on the printer"
    -- NMS trap annotation
    --#TYPE "Lexmark: page complexity error."
    --#SUMMARY "Page complexity error on the printer. Printing cannot continue until the condition is cleared."
    --#ARGUMENTS {}
    --#SEVERITY MAJOR
    --#TIMEINDEX 6
    --#HELP "lexmib.hlp"
    --#HELPTAG 60010
    --#STATE DEGRADED
    ::= 9

irOffline TRAP-TYPE
    ENTERPRISE adapter
    VARIABLES  {prtgenStatusIRC}
    DESCRIPTION "The printer is offline"
    -- NMS trap annotation
    --#TYPE "Lexmark: offline."
    --#SUMMARY "The printer is offline. Printing cannot continue until the condition is cleared."
    --#ARGUMENTS {}
    --#SEVERITY MAJOR
    --#TIMEINDEX 6
    --#HELP "lexmib.hlp"
    --#HELPTAG 60011
    --#STATE DEGRADED
    ::= 10

irClearedTypeII TRAP-TYPE
    ENTERPRISE adapter
    VARIABLES  {prtgenStatusIRC}
    DESCRIPTION "The condition on the printer has been cleared."
    -- NMS trap annotation
    --#TYPE "Lexmark: error condition cleared (type 2)"
    --#SUMMARY "The condition on the printer has been cleared."
    --#ARGUMENTS {}
    --#SEVERITY MAJOR
    --#TIMEINDEX 6
    --#HELP "lexmib.hlp"
    --#HELPTAG 60012
    --#STATE OPERATIONAL
    ::= 11

END
