-- *****************************************************************
-- uts-bbs-common.my: UTStarcom Broadband Switch Common MIB
--   This MIB contains the common definitions used across the
--   the UTStarcom Broadband Switch line.
--
-- September 2003, Sunitha Nagendra
--
-- Copyright (c) 2003 by UTStarcom, Inc.
-- All rights reserved.
-- *****************************************************************
--

UTS-BBS-COMMON-MIB DEFINITIONS ::= BEGIN

IMPORTS
    MODULE-IDENTITY
        FROM SNMPv2-SMI
    MODULE-COMPLIANCE,
    OBJECT-GROUP
        FROM SNMPv2-CONF
    utBroadbandModules,
    utsBroadbandSwitch
        FROM UTS-COMMON-MIB;


utBBSCommonModule MODULE-IDENTITY
    LAST-UPDATED    "200309291200Z"    -- 29 September 2003 12:00:00 EST
    ORGANIZATION    "UTStarcom, Inc."
        CONTACT-INFO
                "  Postal: UTStarcom Inc
                           33 Wood Ave South, 3rd Floor
                           Iselin, NJ 08830

                   WEB: http://www.utstar.com"

    DESCRIPTION
        "MIB module includes common definitions and object identifiers assigned to
                 to different MIB components of Broadband switch."

    REVISION        "200309291200Z"   -- 29 September 2003 12:00:00 EST
    DESCRIPTION
        "Initial version of this MIB."
    ::= { utBroadbandModules 1 }

--
-- MIB Classification
--
utBBSMIB OBJECT IDENTIFIER ::= { utsBroadbandSwitch 1}

-- BBS Chassis MIB
utBBSChassis OBJECT IDENTIFIER ::= { utBBSMIB 1}

-- BBS Products
utBBSProducts  OBJECT IDENTIFIER ::= { utBBSMIB 2}


-- Entity Instance
BBSEntityInstance ::= TEXTUAL-CONVENTION
        STATUS     current
        DESCRIPTION
                "Instance of an Entity in the NE. For example, the slot number
                 is the entity instance of the entity type slot. Entity Instance
                 is provided to aid in locating MO in the EMS. For now, the
                 Entity Instance will correspond to the Cfgdb DN. It will look
                 something like this for slot-4:
                 ;vr=0;chassis;chassisView=front;slot=4;  "
        SYNTAX  OCTET STRING (SIZE(0..255))


-- BBS Alarm and Event (Trap) Objects
utBBSTrapObjects OBJECT IDENTIFIER ::= { utBBSMIB 3}

-- utBBS Entity Instance for Alarms and Events
utBBSTrapEntityInstance OBJECT-TYPE
        SYNTAX     BBSEntityInstance
        MAX-ACCESS accessible-for-notify
        STATUS     current
        DESCRIPTION
                "Reserved for traps. This indicates the source of the problem
                   reported by this trap (for now, the Cfg DN)."
        ::= { utBBSTrapObjects 1 }

utsBBSProductSysId	OBJECT-IDENTITY
	STATUS     current
	DESCRIPTION
		""
	::= { utsBroadbandSwitch 2 }

utBBS1000	OBJECT-IDENTITY
	STATUS     current
	DESCRIPTION
		""
	::= { utsBBSProductSysId 1 }

utBBS5000	OBJECT-IDENTITY
	STATUS     current
	DESCRIPTION
		""
	::= { utsBBSProductSysId 2 }

utBBS4000	OBJECT-IDENTITY
	STATUS     current
	DESCRIPTION
		""
	::= { utsBBSProductSysId 3 }

utBBS2000	OBJECT-IDENTITY
	STATUS     current
	DESCRIPTION
		""
	::= { utsBBSProductSysId 4 }

utBBS1000plus	OBJECT-IDENTITY
	STATUS     current
	DESCRIPTION
		"bbs1000+ system id."
	::= { utsBBSProductSysId 5 }

utBBSEponOnuSysId  OBJECT-IDENTITY
	STATUS     current
	DESCRIPTION
		""
	::= { utsBBSProductSysId 100 }

utBBSGepon	OBJECT-IDENTITY
	STATUS     current
	DESCRIPTION
		""
	::= { utsBroadbandSwitch 3}

utBBSGeponOnu	OBJECT-IDENTITY
	STATUS     current
	DESCRIPTION
		"the root of gepon onu manangement information base"
	::= { utsBroadbandSwitch 100}

utAccounting	OBJECT-IDENTITY
	STATUS     current
	DESCRIPTION
		""
	::= { utBBSGepon 1 }

utConfiguration	OBJECT-IDENTITY
	STATUS     current
	DESCRIPTION
		""
	::= { utBBSGepon 2 }

utFault		OBJECT-IDENTITY
	STATUS     current
	DESCRIPTION
		""
	::= { utBBSGepon 3 }

utPerformance	OBJECT-IDENTITY
	STATUS     current
	DESCRIPTION
		""
	::= { utBBSGepon 4 }

utSecurity	OBJECT-IDENTITY
	STATUS     current
	DESCRIPTION
		""
	::= { utBBSGepon 5 }

--
-- ONU branch
--

utBBSEponOnuSysId200A   OBJECT-IDENTITY
	STATUS          current
	DESCRIPTION
		"gepon onu 200a system objet ID"
	::= { utBBSEponOnuSysId 1 }

utBBSEponOnuSysId2024   OBJECT-IDENTITY
	STATUS          current
	DESCRIPTION
		"gepon onu 2024 system objet ID"
	::= { utBBSEponOnuSysId 2 }

utBBSEponOnuSysId2004   OBJECT-IDENTITY
	STATUS          current
	DESCRIPTION
		"gepon onu 2004 system objet ID"
	::= { utBBSEponOnuSysId 6 }


utBBSGeponOnu200A  OBJECT-IDENTITY
	STATUS     current
	DESCRIPTION
		"the root of gepon onu 200a manangement information base"
	::= { utBBSGeponOnu 1}

utBBSGeponOnu2024  OBJECT-IDENTITY
	STATUS     current
	DESCRIPTION
		"the root of gepon onu 2024 manangement information base"
	::= { utBBSGeponOnu 2}

utBBSGeponOnu2004  OBJECT-IDENTITY
	STATUS     current
	DESCRIPTION
		"the root of gepon onu 2004 manangement information base"
	::= { utBBSGeponOnu 6}

--
-- OLT branch
--

utsGeponBBS	OBJECT-IDENTITY
	STATUS     current
	DESCRIPTION
		"the root of gepon olt manangement information base"
	::= { utsBroadbandSwitch 200}

utsGeponBBS1000  OBJECT-IDENTITY
	STATUS     current
	DESCRIPTION
		"the root of gepon olt 1000 manangement information base"
	::= { utsGeponBBS 1}

utsGeponBBS1000plus  OBJECT-IDENTITY
	STATUS     current
	DESCRIPTION
		"the root of gepon olt 1000plus manangement information base"
	::= { utsGeponBBS 2}


utsGeponBBS4000  OBJECT-IDENTITY
	STATUS     current
	DESCRIPTION
		"the root of gepon olt 4000 manangement information base"
	::= { utsGeponBBS 6}

utsGeponBBS4000Accounting	OBJECT-IDENTITY
	STATUS     current
	DESCRIPTION
		"Peculiar Accounting for BBS Olt 4000"
	::= { utsGeponBBS4000 1 }

utsGeponBBS4000Configuration	OBJECT-IDENTITY
	STATUS     current
	DESCRIPTION
		"Peculiar Configuration for BBS Olt 4000"
	::= { utsGeponBBS4000 2 }

utsGeponBBS4000Fault		OBJECT-IDENTITY
	STATUS     current
	DESCRIPTION
		"Peculiar Fault for BBS Olt 4000"
	::= { utsGeponBBS4000 3 }

utsGeponBBS4000Performance	OBJECT-IDENTITY
	STATUS     current
	DESCRIPTION
		"Peculiar Performance for BBS Olt 4000"
	::= { utsGeponBBS4000 4 }

utsGeponBBS4000Security	OBJECT-IDENTITY
	STATUS     current
	DESCRIPTION
		"Peculiar Security for BBS Olt 4000"
	::= { utsGeponBBS4000 5 }

utsGeponBBS4000V5TG	OBJECT-IDENTITY
	STATUS     current
	DESCRIPTION
		"Peculiar V5TG for BBS Olt 4000"
	::= { utsGeponBBS4000 6 }

END
