-- *****************************************************************************
-- Filename:        ut-epon-perf.mib
-- Description:     Contains iSwitch MIB Extension.
-- MIB Version:     1.00
--
-- Copyright (C) 2001 by UTStarcom, Inc. All rights reserved.
-- Reproduction of this document is authorized on the condition that
-- the foregoing copyright notice is included.
--
-- NOTE:  The contents of this document are subject to change without notice
-- *****************************************************************************

-- *****************************************************************************
-- Version:        $Id:  $
-- Last Modified:  $DateTime:  $
-- Change List #:  $Change:  $
-- *****************************************************************************

UTSTARCOM-GE-PON-PERF-MIB DEFINITIONS ::= BEGIN

    IMPORTS
        MODULE-IDENTITY, OBJECT-TYPE, IpAddress,
        Counter64                               FROM SNMPv2-SMI
        Counter32                               FROM SNMPv2-SMI
        Counter, TimeTicks                      FROM RFC1155-SMI
        RowStatus, TruthValue                   FROM SNMPv2-TC
        DisplayString                           FROM RFC1213-MIB
        ifIndex                                 FROM IF-MIB
        MacAddress, BridgeId, Timeout           FROM BRIDGE-MIB
        uts-epon                                FROM UTS-EPON-MIB;
--        utsGeponBBS1000plus                   FROM UTS-BBS-COMMON-MIB;

   utPerformance  MODULE-IDENTITY
        LAST-UPDATED "9407272253Z"      -- Wed Jul 27 22:53:04 PDT 1994
        ORGANIZATION "UTStarcom Inc"
        CONTACT-INFO
            "Postal: UTStarcom Inc
             Alameda, California 9xxxx
             Tel:    +1 510 555 1212
             E-Mail: mibs@utstar.com "
      DESCRIPTION
         "Contains UT EPON MIB Extensions."
     ::= { uts-epon 4   }




--
--  epon objects extersion
--

utsEthIfPerfExt     OBJECT IDENTIFIER ::= { utPerformance 1 }
utsEfmPonPerfExt     OBJECT IDENTIFIER ::= { utPerformance 2 }
utsLayer3PerfExt     OBJECT IDENTIFIER ::= { utPerformance 3 }

--
--  Performance Global configuation
--  zhaoxf add 21 Apri,2006
--
utsGlbConfPerfExt     OBJECT IDENTIFIER ::= { utPerformance 4 }

utsPerfStaOperGroup  OBJECT IDENTIFIER ::= { utsGlbConfPerfExt 1 }

utsPerfStaClearAll OBJECT-TYPE
   SYNTAX      INTEGER
    {
     allPorts(1),
     allEthPorts(2),
     allLagPorts(3),
     allOLTPorts(4),
     allONUPorts(5)
    }
	MAX-ACCESS  read-write
	STATUS      current
	DESCRIPTION
	    "Clear statistic counters.
	     allPorts(1) is for all switch ports, OLT pon ports and ONU PON ports;
	     allEthPorts(2) is for all Ethernet ports only;
	     allLagPorts(3) is for all LAG ports only;
	     allOLTPorts(4) is for all OLT ports;
	     allONUPorts(5) is for all ONU ports."
   ::= { utsPerfStaOperGroup 1 }

utsPerfStaPMEnable OBJECT-TYPE
   SYNTAX      INTEGER
    {
	  enable(1),
	  disable(2)
    }
	MAX-ACCESS  read-write
	STATUS      current
	DESCRIPTION
    "Enable or disable the TFTP performance management globally."
   ::= { utsPerfStaOperGroup 2 }


--
--  ethernet interface extersion
--


utsEthIfStatsExtObjects OBJECT IDENTIFIER ::= { utsEthIfPerfExt 1 }

--
-- Ether-like interface extension private MIB objects
--


--
--  ethernet interface table's extension
--
   utsEthIfStatsExtTable  OBJECT-TYPE
        SYNTAX      SEQUENCE OF UtsEthIfStatsExtEntry
        MAX-ACCESS  not-accessible
        STATUS      current
        DESCRIPTION
            "A list of UTStarcom's extension to the interface entries. The
             nnumber of entries is given by the value of ifNumber. This table
             contains additional objects for the interface table and ether-like table."
       ::= { utsEthIfStatsExtObjects 1 }

   utsEthIfStatsExtEntry OBJECT-TYPE
       SYNTAX       UtsEthIfStatsExtEntry
       MAX-ACCESS   not-accessible
       STATUS       current
       DESCRIPTION
          "An entry containing additional management information
            applicable to a particular interface."
      INDEX { utsEthIfExtIndex }
      ::= { utsEthIfStatsExtTable 1 }

    UtsEthIfStatsExtEntry ::=
        SEQUENCE {
            utsEthIfExtIndex
                INTEGER,
            utsEthIfExtModule
                INTEGER,
            utsEthIfExtPort
                INTEGER,
            utsEthIfExtInOctets
                Counter64,
            utsEthIfExtInUcastPkts
                Counter64,
            utsEthIfExtInNUcastPkts
                Counter64,
            utsEthIfExtInDiscards
                Counter64,
            utsEthIfExtInErrors
                Counter64,
            utsEthIfExtInUnknownProtos
                Counter64,
            utsEthIfExtOutOctets
                Counter64,
            utsEthIfExtOutUcastPkts
                Counter64,
            utsEthIfExtOutNUcastPkts
                Counter64,
            utsEthIfExtOutDiscards
                Counter64,
            utsEthIfExtOutErrors
                Counter64,
            utsEthIfExtOutQLen
                Counter64,
            utsEthIfExtIpInReceives
                Counter64,
            utsEthIfExtIpInHdrErrors
                Counter64,
            utsEthIfExtIpForwDatagrams
                Counter64,
            utsEthIfExtIpInDiscards
                Counter64,
            utsEthIfExtDot1dBasePortDelayExceededDiscards
                Counter64,
            utsEthIfExtDot1dBasePortMtuExceededDiscards
                Counter64,
            utsEthIfExtDot1dTpPortInFrames
                Counter64,
            utsEthIfExtDot1dTpPortOutFrames
                Counter64,
            utsEthIfExtDot1dPortInDiscards
                Counter64,
            utsEthIfExtStatsDropEvents
                Counter64,
            utsEthIfExtStatsMulticastPkts
                Counter64,
            utsEthIfExtStatsBroadcastPkts
                Counter64,
            utsEthIfExtStatsUndersizePkts
                Counter64,
            utsEthIfExtStatsFragments
                Counter64,
            utsEthIfExtStatsPkts64Octets
                Counter64,
            utsEthIfExtStatsPkts65to127Octets
                Counter64,
            utsEthIfExtStatsPkts128to255Octets
                Counter64,
            utsEthIfExtStatsPkts256to511Octets
                Counter64,
            utsEthIfExtStatsPkts512to1023Octets
                Counter64,
            utsEthIfExtStatsPkts1024to1518Octets
                Counter64,
            utsEthIfExtStatsOversizePkts
                Counter64,
            utsEthIfExtStatsJabbers
                Counter64,
            utsEthIfExtStatsOctets
                Counter64,
            utsEthIfExtStatsPkts
                Counter64,
            utsEthIfExtStatsCollisions
                Counter64,
            utsEthIfExtStatsCRCAlignErrors
                Counter64,
            utsEthIfExtStatsTxNoErrors
                Counter64,
            utsEthIfExtStatsRxNoErrors
                Counter64,
            utsEthIfExtDot3StatsAlignmentErrors
                Counter64,
            utsEthIfExtDot3StatsFCSErrors
                Counter64,
            utsEthIfExtDot3StatsSingleCollisionFrames
                Counter64,
            utsEthIfExtDot3StatsMultipleCollisionFrames
                Counter64,
            utsEthIfExtDot3StatsSQETTestErrors
                Counter64,
            utsEthIfExtDot3StatsDeferredTransmissions
                Counter64,
            utsEthIfExtDot3StatsLateCollisions
                Counter64,
            utsEthIfExtDot3StatsExcessiveCollisions
                Counter64,
            utsEthIfExtDot3StatsInternalMacTransmitErrors
                Counter64,
            utsEthIfExtDot3StatsCarrierSenseErrors
                Counter64,
            utsEthIfExtDot3StatsFrameTooLongs
                Counter64,
            utsEthIfExtDot3StatsInternalMacReceiveErrors
                Counter64,
            utsEthIfExtDot3StatsSymbolErrors
                Counter64,
            utsEthIfExtDot3ControlInUnknownOpcodes
                Counter64,
            utsEthIfExtDot3InPauseFrames
                Counter64,
            utsEthIfExtDot3OutPauseFrames
                Counter64,
            utsEthIfHCInOctets
                Counter64,
            utsEthIfHCInUcastPkts
                Counter64,
            utsEthIfHCInMulticastPkts
                Counter64,
            utsEthIfHCInBroadcastPkts
                Counter64,
            utsEthIfHCOutOctets
                Counter64,
            utsEthIfHCOutUcastPkts
                Counter64,
            utsEthIfHCOutMulticastPkts
                Counter64,
            utsEthIfHCOutBroadcastPkts
                Counter64,
            utsEthIfPMStatus
                INTEGER
       }


    utsEthIfExtIndex OBJECT-TYPE
        SYNTAX      INTEGER
        MAX-ACCESS  not-accessible
        STATUS      current
        DESCRIPTION
           "Ethernet interface number"
       ::= { utsEthIfStatsExtEntry 1 }

    utsEthIfExtModule OBJECT-TYPE
        SYNTAX      INTEGER
        MAX-ACCESS  read-only
        STATUS      current
        DESCRIPTION
           "Ethernet interface module number"
       ::= { utsEthIfStatsExtEntry 2 }

    utsEthIfExtPort OBJECT-TYPE
        SYNTAX      INTEGER
        MAX-ACCESS  read-only
        STATUS      current
        DESCRIPTION
           "Ethernet interface port number"
       ::= { utsEthIfStatsExtEntry 3 }


    utsEthIfExtInOctets OBJECT-TYPE
        SYNTAX      Counter64
        MAX-ACCESS  read-only
        STATUS      current

        DESCRIPTION
            "Ethernet interface in Octets"
        ::= { utsEthIfStatsExtEntry 6 }

    utsEthIfExtInUcastPkts OBJECT-TYPE
        SYNTAX      Counter64
        MAX-ACCESS  read-only
        STATUS      current

        DESCRIPTION
            "Ethernet interface in unicast packets"
        ::= { utsEthIfStatsExtEntry 7 }

    utsEthIfExtInNUcastPkts OBJECT-TYPE
        SYNTAX      Counter64
        MAX-ACCESS  read-only
        STATUS      current

        DESCRIPTION
            "Ethernet interface in no unicast packets"
        ::= { utsEthIfStatsExtEntry 8 }

    utsEthIfExtInDiscards OBJECT-TYPE
        SYNTAX      Counter64
        MAX-ACCESS  read-only
        STATUS      current

        DESCRIPTION
            "Ethernet interface in discard packets"
        ::= { utsEthIfStatsExtEntry 9 }

    utsEthIfExtInErrors OBJECT-TYPE
        SYNTAX      Counter64
        MAX-ACCESS  read-only
        STATUS      current

        DESCRIPTION
            "Ethernet interface in error packets"
        ::= { utsEthIfStatsExtEntry 10 }

    utsEthIfExtInUnknownProtos OBJECT-TYPE
        SYNTAX      Counter64
        MAX-ACCESS  read-only
        STATUS      current

        DESCRIPTION
            "Ethernet interface in unknown protocol packets"
        ::= { utsEthIfStatsExtEntry 11 }

    utsEthIfExtOutOctets OBJECT-TYPE
        SYNTAX      Counter64
        MAX-ACCESS  read-only
        STATUS      current

        DESCRIPTION
            "Ethernet interface out octets"
        ::= { utsEthIfStatsExtEntry 12 }

    utsEthIfExtOutUcastPkts OBJECT-TYPE
        SYNTAX      Counter64
        MAX-ACCESS  read-only
        STATUS      current

        DESCRIPTION
            "Ethernet interface out unicast packets"
        ::= { utsEthIfStatsExtEntry 13 }

    utsEthIfExtOutNUcastPkts OBJECT-TYPE
        SYNTAX      Counter64
        MAX-ACCESS  read-only
        STATUS      current

        DESCRIPTION
            "Ethernet interface out no unicast packets"
        ::= { utsEthIfStatsExtEntry 14 }

    utsEthIfExtOutDiscards OBJECT-TYPE
        SYNTAX      Counter64
        MAX-ACCESS  read-only
        STATUS      current

        DESCRIPTION
            "Ethernet interface out discard packets"
        ::= { utsEthIfStatsExtEntry 15 }

    utsEthIfExtOutErrors OBJECT-TYPE
        SYNTAX      Counter64
        MAX-ACCESS  read-only
        STATUS      current

        DESCRIPTION
            "Ethernet interface out error packets"
        ::= { utsEthIfStatsExtEntry 16 }

    utsEthIfExtOutQLen OBJECT-TYPE
        SYNTAX      Counter64
        MAX-ACCESS  read-only
        STATUS      current

        DESCRIPTION
            "Ethernet interface out packets length in queue"
        ::= { utsEthIfStatsExtEntry 17 }

    utsEthIfExtIpInReceives OBJECT-TYPE
        SYNTAX      Counter64
        MAX-ACCESS  read-only
        STATUS      current

        DESCRIPTION
            "Ethernet interface recieve ip packets"
        ::= { utsEthIfStatsExtEntry 18 }

    utsEthIfExtIpInHdrErrors OBJECT-TYPE
        SYNTAX      Counter64
        MAX-ACCESS  read-only
        STATUS      current

        DESCRIPTION
            "Ethernet interface ip handler error packet"
        ::= { utsEthIfStatsExtEntry 19 }

    utsEthIfExtIpForwDatagrams OBJECT-TYPE
        SYNTAX      Counter64
        MAX-ACCESS  read-only
        STATUS      current

        DESCRIPTION
            "Ethernet interface ip forward datagrams"
        ::= { utsEthIfStatsExtEntry 20 }

    utsEthIfExtIpInDiscards OBJECT-TYPE
        SYNTAX      Counter64
        MAX-ACCESS  read-only
        STATUS      current

        DESCRIPTION
            "Ethernet interface ip in discard packets"
        ::= { utsEthIfStatsExtEntry 21 }

    utsEthIfExtDot1dBasePortDelayExceededDiscards OBJECT-TYPE
        SYNTAX      Counter64
        MAX-ACCESS  read-only
        STATUS      current

        DESCRIPTION
            "Ethernet interface dot1dbaseport delay exceed discard"
        ::= { utsEthIfStatsExtEntry 22 }

    utsEthIfExtDot1dBasePortMtuExceededDiscards OBJECT-TYPE
        SYNTAX      Counter64
        MAX-ACCESS  read-only
        STATUS      current

        DESCRIPTION
            "dot1d baseport mtu exceed discard"
        ::= { utsEthIfStatsExtEntry 23 }

    utsEthIfExtDot1dTpPortInFrames OBJECT-TYPE
        SYNTAX      Counter64
        MAX-ACCESS  read-only
        STATUS      current

        DESCRIPTION
            "dot1d tp port in frames"
        ::= { utsEthIfStatsExtEntry 24 }

    utsEthIfExtDot1dTpPortOutFrames OBJECT-TYPE
        SYNTAX      Counter64
        MAX-ACCESS  read-only
        STATUS      current

        DESCRIPTION
            "dot1d tpport out frame"
        ::= { utsEthIfStatsExtEntry 25 }

    utsEthIfExtDot1dPortInDiscards OBJECT-TYPE
        SYNTAX      Counter64
        MAX-ACCESS  read-only
        STATUS      current

        DESCRIPTION
            "dot1d port in discard packets"
        ::= { utsEthIfStatsExtEntry 26 }

    utsEthIfExtStatsDropEvents OBJECT-TYPE
        SYNTAX      Counter64
        MAX-ACCESS  read-only
        STATUS      current

        DESCRIPTION
            "statistics drop events"
        ::= { utsEthIfStatsExtEntry 27 }

    utsEthIfExtStatsMulticastPkts OBJECT-TYPE
        SYNTAX      Counter64
        MAX-ACCESS  read-only
        STATUS      current

        DESCRIPTION
            "statistics multicast packets"
        ::= { utsEthIfStatsExtEntry 28 }

    utsEthIfExtStatsBroadcastPkts OBJECT-TYPE
        SYNTAX      Counter64
        MAX-ACCESS  read-only
        STATUS      current

        DESCRIPTION
            "statistic broadcast packets"
        ::= { utsEthIfStatsExtEntry 29 }

    utsEthIfExtStatsUndersizePkts OBJECT-TYPE
        SYNTAX      Counter64
        MAX-ACCESS  read-only
        STATUS      current

        DESCRIPTION
            "statistic undersize packets"
        ::= { utsEthIfStatsExtEntry 30 }

    utsEthIfExtStatsFragments OBJECT-TYPE
        SYNTAX      Counter64
        MAX-ACCESS  read-only
        STATUS      current

        DESCRIPTION
            "statistic fragments"
        ::= { utsEthIfStatsExtEntry 31 }

    utsEthIfExtStatsPkts64Octets OBJECT-TYPE
        SYNTAX      Counter64
        MAX-ACCESS  read-only
        STATUS      current

        DESCRIPTION
            "statistics 64 octets packets"
        ::= { utsEthIfStatsExtEntry 32 }

    utsEthIfExtStatsPkts65to127Octets OBJECT-TYPE
        SYNTAX      Counter64
        MAX-ACCESS  read-only
        STATUS      current

        DESCRIPTION
            "statistic 65 to 127 octets packets"
        ::= { utsEthIfStatsExtEntry 33 }

    utsEthIfExtStatsPkts128to255Octets OBJECT-TYPE
        SYNTAX      Counter64
        MAX-ACCESS  read-only
        STATUS      current

        DESCRIPTION
            "statistic 128 to 255 octets packets"
        ::= { utsEthIfStatsExtEntry 34 }

    utsEthIfExtStatsPkts256to511Octets OBJECT-TYPE
        SYNTAX      Counter64
        MAX-ACCESS  read-only
        STATUS      current

        DESCRIPTION
            "statistic 256 to 511 octets packets"
        ::= { utsEthIfStatsExtEntry 35 }

    utsEthIfExtStatsPkts512to1023Octets OBJECT-TYPE
        SYNTAX      Counter64
        MAX-ACCESS  read-only
        STATUS      current

        DESCRIPTION
            "statistic 512 to 1023 octets packets"
        ::= { utsEthIfStatsExtEntry 36 }

    utsEthIfExtStatsPkts1024to1518Octets OBJECT-TYPE
        SYNTAX      Counter64
        MAX-ACCESS  read-only
        STATUS      current

        DESCRIPTION
            "statistic 1024 to 1518 octets packets"
        ::= { utsEthIfStatsExtEntry 37 }

    utsEthIfExtStatsOversizePkts OBJECT-TYPE
        SYNTAX      Counter64
        MAX-ACCESS  read-only
        STATUS      current

        DESCRIPTION
            "oversize packets"
        ::= { utsEthIfStatsExtEntry 38 }

    utsEthIfExtStatsJabbers OBJECT-TYPE
        SYNTAX      Counter64
        MAX-ACCESS  read-only
        STATUS      current

        DESCRIPTION
            "jabber packet"
        ::= { utsEthIfStatsExtEntry 39 }

    utsEthIfExtStatsOctets OBJECT-TYPE
        SYNTAX      Counter64
        MAX-ACCESS  read-only
        STATUS      current

        DESCRIPTION
            "statistic octets"
        ::= { utsEthIfStatsExtEntry 40 }

    utsEthIfExtStatsPkts OBJECT-TYPE
        SYNTAX      Counter64
        MAX-ACCESS  read-only
        STATUS      current

        DESCRIPTION
            "statistic packets"
        ::= { utsEthIfStatsExtEntry 41 }

    utsEthIfExtStatsCollisions OBJECT-TYPE
        SYNTAX      Counter64
        MAX-ACCESS  read-only
        STATUS      current

        DESCRIPTION
            "collision packets"
        ::= { utsEthIfStatsExtEntry 42 }

    utsEthIfExtStatsCRCAlignErrors OBJECT-TYPE
        SYNTAX      Counter64
        MAX-ACCESS  read-only
        STATUS      current

        DESCRIPTION
            "CRC allign error packets"
        ::= { utsEthIfStatsExtEntry 43 }

    utsEthIfExtStatsTxNoErrors OBJECT-TYPE
        SYNTAX      Counter64
        MAX-ACCESS  read-only
        STATUS      current

        DESCRIPTION
            "tx no error packets"
        ::= { utsEthIfStatsExtEntry 44 }

    utsEthIfExtStatsRxNoErrors OBJECT-TYPE
        SYNTAX      Counter64
        MAX-ACCESS  read-only
        STATUS      current

        DESCRIPTION
            "rx no error packets"
        ::= { utsEthIfStatsExtEntry 45 }

    utsEthIfExtDot3StatsAlignmentErrors OBJECT-TYPE
        SYNTAX      Counter64
        MAX-ACCESS  read-only
        STATUS      current

        DESCRIPTION
            "dot3 alignment error packet"
        ::= { utsEthIfStatsExtEntry 46 }

    utsEthIfExtDot3StatsFCSErrors OBJECT-TYPE
        SYNTAX      Counter64
        MAX-ACCESS  read-only
        STATUS      current

        DESCRIPTION
            "statistic fcs error"
        ::= { utsEthIfStatsExtEntry 47 }

    utsEthIfExtDot3StatsSingleCollisionFrames OBJECT-TYPE
        SYNTAX      Counter64
        MAX-ACCESS  read-only
        STATUS      current

        DESCRIPTION
            "single collision frames"
        ::= { utsEthIfStatsExtEntry 48 }

    utsEthIfExtDot3StatsMultipleCollisionFrames OBJECT-TYPE
        SYNTAX      Counter64
        MAX-ACCESS  read-only
        STATUS      current

        DESCRIPTION
            "multiple collision frames"
        ::= { utsEthIfStatsExtEntry 49 }

    utsEthIfExtDot3StatsSQETTestErrors OBJECT-TYPE
        SYNTAX      Counter64
        MAX-ACCESS  read-only
        STATUS      current

        DESCRIPTION
            "SQET test error packets"
        ::= { utsEthIfStatsExtEntry 50 }

    utsEthIfExtDot3StatsDeferredTransmissions OBJECT-TYPE
        SYNTAX      Counter64
        MAX-ACCESS  read-only
        STATUS      current

        DESCRIPTION
            "deferred transmission packets"
        ::= { utsEthIfStatsExtEntry 51 }

    utsEthIfExtDot3StatsLateCollisions OBJECT-TYPE
        SYNTAX      Counter64
        MAX-ACCESS  read-only
        STATUS      current

        DESCRIPTION
            "late collision packets"
        ::= { utsEthIfStatsExtEntry 52 }

    utsEthIfExtDot3StatsExcessiveCollisions OBJECT-TYPE
        SYNTAX      Counter64
        MAX-ACCESS  read-only
        STATUS      current

        DESCRIPTION
            "excessive collision packets"
        ::= { utsEthIfStatsExtEntry 53 }

    utsEthIfExtDot3StatsInternalMacTransmitErrors OBJECT-TYPE
        SYNTAX      Counter64
        MAX-ACCESS  read-only
        STATUS      current

        DESCRIPTION
            "internal mac transmit error packets"
        ::= { utsEthIfStatsExtEntry 54 }

    utsEthIfExtDot3StatsCarrierSenseErrors OBJECT-TYPE
        SYNTAX      Counter64
        MAX-ACCESS  read-only
        STATUS      current

        DESCRIPTION
            "carrier sense error packets"
        ::= { utsEthIfStatsExtEntry 55 }

    utsEthIfExtDot3StatsFrameTooLongs OBJECT-TYPE
        SYNTAX      Counter64
        MAX-ACCESS  read-only
        STATUS      current

        DESCRIPTION
            "frame too long packets"
        ::= { utsEthIfStatsExtEntry 56 }

    utsEthIfExtDot3StatsInternalMacReceiveErrors OBJECT-TYPE
        SYNTAX      Counter64
        MAX-ACCESS  read-only
        STATUS      current

        DESCRIPTION
            "internal mac receive error packets"
        ::= { utsEthIfStatsExtEntry 57 }

    utsEthIfExtDot3StatsSymbolErrors OBJECT-TYPE
        SYNTAX      Counter64
        MAX-ACCESS  read-only
        STATUS      current

        DESCRIPTION
            "symbol error packets"
        ::= { utsEthIfStatsExtEntry 58 }

    utsEthIfExtDot3ControlInUnknownOpcodes OBJECT-TYPE
        SYNTAX      Counter64
        MAX-ACCESS  read-only
        STATUS      current

        DESCRIPTION
            "unknown control in opcode packets"
        ::= { utsEthIfStatsExtEntry 59 }

    utsEthIfExtDot3InPauseFrames OBJECT-TYPE
        SYNTAX      Counter64
        MAX-ACCESS  read-only
        STATUS      current

        DESCRIPTION
            "in pause frames"
        ::= { utsEthIfStatsExtEntry 60 }

    utsEthIfExtDot3OutPauseFrames OBJECT-TYPE
        SYNTAX      Counter64
        MAX-ACCESS  read-only
        STATUS      current

        DESCRIPTION
            "out pause frames"
        ::= { utsEthIfStatsExtEntry 61 }

    utsEthIfHCInOctets OBJECT-TYPE
        SYNTAX      Counter64
        MAX-ACCESS  read-only
        STATUS      current

        DESCRIPTION
            "HC in octets"
        ::= { utsEthIfStatsExtEntry 62 }

    utsEthIfHCInUcastPkts OBJECT-TYPE
        SYNTAX      Counter64
        MAX-ACCESS  read-only
        STATUS      current

        DESCRIPTION
            "HC In unicast packets"
        ::= { utsEthIfStatsExtEntry 63 }

    utsEthIfHCInMulticastPkts OBJECT-TYPE
        SYNTAX      Counter64
        MAX-ACCESS  read-only
        STATUS      current

        DESCRIPTION
            "HC in multicast packets"
        ::= { utsEthIfStatsExtEntry 64 }

    utsEthIfHCInBroadcastPkts OBJECT-TYPE
        SYNTAX      Counter64
        MAX-ACCESS  read-only
        STATUS      current

        DESCRIPTION
            "HC in broadcast packets"
        ::= { utsEthIfStatsExtEntry 65 }

    utsEthIfHCOutOctets OBJECT-TYPE
        SYNTAX      Counter64
        MAX-ACCESS  read-only
        STATUS      current

        DESCRIPTION
            "HC out octets"
        ::= { utsEthIfStatsExtEntry 66 }

    utsEthIfHCOutUcastPkts OBJECT-TYPE
        SYNTAX      Counter64
        MAX-ACCESS  read-only
        STATUS      current

        DESCRIPTION
            "HC out unicast packets"
        ::= { utsEthIfStatsExtEntry 67 }

    utsEthIfHCOutMulticastPkts OBJECT-TYPE
        SYNTAX      Counter64
        MAX-ACCESS  read-only
        STATUS      current

        DESCRIPTION
            "HC out multicast packets"
        ::= { utsEthIfStatsExtEntry 68 }

    utsEthIfHCOutBroadcastPkts OBJECT-TYPE
        SYNTAX      Counter64
        MAX-ACCESS  read-only
        STATUS      current

        DESCRIPTION
            "HC out broadcast packets"
        ::= { utsEthIfStatsExtEntry 69 }


    utsEthIfPMStatus OBJECT-TYPE
    SYNTAX      INTEGER
    {
       enable(1),
       disable(2)
    }
	MAX-ACCESS  read-write
	STATUS      current
	DESCRIPTION
	    "Enable or disable the Ethernet interface TFTP performance management."
   ::= { utsEthIfStatsExtEntry 100 }



------
------ EPON statistics extension
------



------
------ OLT
------

utsEponPonExtObjects OBJECT IDENTIFIER ::= { utsEfmPonPerfExt 1 }

utsEponPonStatsExt OBJECT IDENTIFIER ::= { utsEponPonExtObjects 1 }



------
------ ONU
------

--utsEponOnuExtObjects OBJECT IDENTIFIER ::= { utsEfmPonPerfExt 2 }

--utsEponOnuStatsExt OBJECT IDENTIFIER ::= { utsEponOnuExtObjects 1 }



------
------
------


--
--  epon Pon interface statistics table's extension
--

   utsPonIfExtStatsTable  OBJECT-TYPE
        SYNTAX      SEQUENCE OF UtsPonIfExtStatsEntry
        MAX-ACCESS  not-accessible
        STATUS      current
        DESCRIPTION
            "A list of UTStarcom's extension to the interface entries. The
             number of entries is given by the value of pon if index."
       ::= { utsEponPonStatsExt 1 }

   utsPonIfExtStatsEntry OBJECT-TYPE
       SYNTAX       UtsPonIfExtStatsEntry
       MAX-ACCESS   not-accessible
       STATUS       current
       DESCRIPTION
          "An entry containing additional management information
            applicable to a particular interface."
      INDEX { utsPonIfExtIndex }
      ::= { utsPonIfExtStatsTable 1 }


    UtsPonIfExtStatsEntry ::=
        SEQUENCE {
            utsPonIfExtIndex
                INTEGER,
            utsPonIfExtModule
                INTEGER,
            utsPonIfExtPort
                INTEGER,
            utsPonIfExtLogicalLinkId
                INTEGER,
            utsPonIfExtStatsMacControlFrameTx
                Counter64,
            utsPonIfExtStatsMacControlFrameRx
                Counter64,
            utsPonIfExtStatsUnsupportedMPCPFramesRx
                Counter64,
            utsPonIfExtStatsDiscoveryWindowSent
                Counter64,
            utsPonIfExtStatsDiscoveryTimeout
                Counter64,
            utsPonIfExtStatsReportFramesTx
                Counter64,
            utsPonIfExtStatsReportFramesRx
                Counter64,
            utsPonIfExtStatsGateTx
                Counter64,
            utsPonIfExtStatsGateRx
                Counter64,
            utsPonIfExtStatsRegisterTx
                Counter64,
            utsPonIfExtStatsRegisterRx
                Counter64,
            utsPonIfExtStatsRegisterAttempts
                Counter64,
            utsPonIfExtStatsRegisterRequestTx
                Counter64,
            utsPonIfExtStatsRegisterRequestRx
                Counter64,
            utsPonIfExtStatsRegisterAckTx
                Counter64,
            utsPonIfExtStatsRegisterAckRx
                Counter64,
            utsPonIfExtStatsTxFramesPerPriority0
                Counter64,
            utsPonIfExtStatsTxFramesPerPriority1
                Counter64,
            utsPonIfExtStatsTxFramesPerPriority2
                Counter64,
            utsPonIfExtStatsTxFramesPerPriority3
                Counter64,
            utsPonIfExtStatsTxFramesPerPriority4
                Counter64,
            utsPonIfExtStatsTxFramesPerPriority5
                Counter64,
            utsPonIfExtStatsTxFramesPerPriority6
                Counter64,
            utsPonIfExtStatsTxFramesPerPriority7
                Counter64,
            utsPonIfExtStatsRxFramesPerPriority0
                Counter64,
            utsPonIfExtStatsRxFramesPerPriority1
                Counter64,
            utsPonIfExtStatsRxFramesPerPriority2
                Counter64,
            utsPonIfExtStatsRxFramesPerPriority3
                Counter64,
            utsPonIfExtStatsRxFramesPerPriority4
                Counter64,
            utsPonIfExtStatsRxFramesPerPriority5
                Counter64,
            utsPonIfExtStatsRxFramesPerPriority6
                Counter64,
            utsPonIfExtStatsRxFramesPerPriority7
                Counter64,
            utsPonIfExtStatsDroppedFramesPerPriority0
                Counter64,
            utsPonIfExtStatsDroppedFramesPerPriority1
                Counter64,
            utsPonIfExtStatsDroppedFramesPerPriority2
                Counter64,
            utsPonIfExtStatsDroppedFramesPerPriority3
                Counter64,
            utsPonIfExtStatsDroppedFramesPerPriority4
                Counter64,
            utsPonIfExtStatsDroppedFramesPerPriority5
                Counter64,
            utsPonIfExtStatsDroppedFramesPerPriority6
                Counter64,
            utsPonIfExtStatsDroppedFramesPerPriority7
                Counter64,
            utsPonIfExtStatsFramesTx
                Counter64,
            utsPonIfExtStatsSingleCollisionFrames
                Counter64,
            utsPonIfExtStatsMultipleCollisionFrames
                Counter64,
            utsPonIfExtStatsFramesRx
                Counter64,
            utsPonIfExtStatsAlignmentErrs
                Counter64,
            utsPonIfExtStatsLlidFramesRx
                Counter64,
            utsPonIfExtStatsBcastFramesRx
                Counter64,
            utsPonIfExtStatsInvalidErrFramesRx
                Counter64,
            utsPonIfExtStatsLlidBcastErrFramesRx
                Counter64,
            utsPonIfExtStatsHCFramesErrRx
                Counter64,
            utsPonIfExtStatsOnuByteCount
                Counter64,
            utsPonIfExtStatsErrOnuBytes
                Counter64,
            utsPonIfExtStatsHostFramesPonTx
                Counter64,
            utsPonIfExtStatsHostFramesPonRx
                Counter64,
            utsPonIfExtStatsHostOctetsTx
                Counter64,
            utsPonIfExtStatsHostOctetsRx
                Counter64,
            utsPonIfExtStatsPauseFramesPonRx
                Counter64,
            utsPonIfExtStatsPauseFramesSystemRx
                Counter64,
            utsPonIfExtStatsPauseFramesSystemTx
                Counter64,
            utsPonIfExtStatsOamFramesTx
                Counter64,
            utsPonIfExtStatsOamFramesRx
                Counter64,
            utsPonIfExtStatsGrantFramesRx
                Counter64,
            utsPonIfExtStatsTotalFramesRx
                Counter64,
            utsPonIfExtStatsTotalFramesRxErr
                Counter64,
            utsPonIfExtStatsTotalFramesTx
                Counter64,
            utsPonIfExtStatsPonDroppedTxFrames
                Counter64,
            utsPonIfExtStatsTotalOctetsRxErrSystem
                Counter64,
            utsPonIfExtStatsTotalOctetsRx
                Counter64,
            utsPonIfExtStatsHostFramesPonDropped
                Counter64,
            utsPonIfExtStatsFrameTooLongErrsSystemRx
                Counter64,
            utsPonIfExtStatsSystemDroppedTxFrames
                Counter64,
            utsPonIfExtStatsFcsErrs
                Counter64,
            utsPonIfExtStatsPauseFramesPonTx
                Counter64,
            utsPonIfExtStatsDiscardBridgePkts
                Counter64,
            utsPonIfExtStatsFramePonTxOk
                Counter64,
            utsPonIfExtStatsFramePonRxOk
                Counter64,
            utsPonIfExtStatsFramePonRxErr
                Counter64,
            utsPonIfExtStatsFrameSysTxOk
                Counter64,
            utsPonIfExtStatsFrameSysRxOk
                Counter64,
            utsPonIfExtStatsFrameSysRxErr
               Counter64,
            utsPonIfExtStatsPonOctetsTxOk
               Counter64,
            utsPonIfExtStatsPonOctetsRxOk
               Counter64,
            utsPonIfExtPMStatus
               INTEGER
       }

    utsPonIfExtIndex OBJECT-TYPE
        SYNTAX      INTEGER
        MAX-ACCESS  not-accessible
        STATUS      current
        DESCRIPTION
           " Pon interface index"
       ::= { utsPonIfExtStatsEntry 1 }

    utsPonIfExtModule OBJECT-TYPE
        SYNTAX      INTEGER
        MAX-ACCESS  read-only
        STATUS      current
        DESCRIPTION
           " Pon interface Module index"
       ::= { utsPonIfExtStatsEntry 2 }

    utsPonIfExtPort OBJECT-TYPE
        SYNTAX      INTEGER
        MAX-ACCESS  read-only
        STATUS      current
        DESCRIPTION
           " Pon interface port index"
       ::= { utsPonIfExtStatsEntry 3 }

    utsPonIfExtLogicalLinkId OBJECT-TYPE
        SYNTAX      INTEGER
        MAX-ACCESS  read-only
        STATUS      current
        DESCRIPTION
           " Pon interface logical port index"
       ::= { utsPonIfExtStatsEntry 4 }

    utsPonIfExtStatsMacControlFrameTx OBJECT-TYPE
        SYNTAX      Counter64
        MAX-ACCESS  read-only
        STATUS      current

        DESCRIPTION
            "mac control frame txed"
        ::= { utsPonIfExtStatsEntry 6 }

    utsPonIfExtStatsMacControlFrameRx OBJECT-TYPE
        SYNTAX      Counter64
        MAX-ACCESS  read-only
        STATUS      current

        DESCRIPTION
            "mac control frame rxed"
        ::= { utsPonIfExtStatsEntry 7 }

    utsPonIfExtStatsUnsupportedMPCPFramesRx OBJECT-TYPE
        SYNTAX      Counter64
        MAX-ACCESS  read-only
        STATUS      current

        DESCRIPTION
            "unsupported mpcp frame rxed"
        ::= { utsPonIfExtStatsEntry 8 }

    utsPonIfExtStatsDiscoveryWindowSent OBJECT-TYPE
        SYNTAX      Counter64
        MAX-ACCESS  read-only
        STATUS      current

        DESCRIPTION
            "discovery window sent"
        ::= { utsPonIfExtStatsEntry 9 }

    utsPonIfExtStatsDiscoveryTimeout OBJECT-TYPE
        SYNTAX      Counter64
        MAX-ACCESS  read-only
        STATUS      current

        DESCRIPTION
            "statistic discovery timeout "
        ::= { utsPonIfExtStatsEntry 10 }

    utsPonIfExtStatsReportFramesTx OBJECT-TYPE
        SYNTAX      Counter64
        MAX-ACCESS  read-only
        STATUS      current

        DESCRIPTION
            "report frames txed"
        ::= { utsPonIfExtStatsEntry 11 }

    utsPonIfExtStatsReportFramesRx OBJECT-TYPE
        SYNTAX      Counter64
        MAX-ACCESS  read-only
        STATUS      current

        DESCRIPTION
            "report frame rxed"
        ::= { utsPonIfExtStatsEntry 12 }

    utsPonIfExtStatsGateTx OBJECT-TYPE
        SYNTAX      Counter64
        MAX-ACCESS  read-only
        STATUS      current

        DESCRIPTION
            "gate txed frame"
        ::= { utsPonIfExtStatsEntry 13 }

    utsPonIfExtStatsGateRx OBJECT-TYPE
        SYNTAX      Counter64
        MAX-ACCESS  read-only
        STATUS      current

        DESCRIPTION
            "gate rxed frame"
        ::= { utsPonIfExtStatsEntry 14 }

    utsPonIfExtStatsRegisterTx OBJECT-TYPE
        SYNTAX      Counter64
        MAX-ACCESS  read-only
        STATUS      current

        DESCRIPTION
            "register txed frame"
        ::= { utsPonIfExtStatsEntry 15 }

    utsPonIfExtStatsRegisterRx OBJECT-TYPE
        SYNTAX      Counter64
        MAX-ACCESS  read-only
        STATUS      current

        DESCRIPTION
            "register rxed frame"
        ::= { utsPonIfExtStatsEntry 16 }

    utsPonIfExtStatsRegisterAttempts OBJECT-TYPE
        SYNTAX      Counter64
        MAX-ACCESS  read-only
        STATUS      current

        DESCRIPTION
            "register attempt times"
        ::= { utsPonIfExtStatsEntry 17 }

    utsPonIfExtStatsRegisterRequestTx OBJECT-TYPE
        SYNTAX      Counter64
        MAX-ACCESS  read-only
        STATUS      current

        DESCRIPTION
            "register request txed"
        ::= { utsPonIfExtStatsEntry 18 }

    utsPonIfExtStatsRegisterRequestRx OBJECT-TYPE
        SYNTAX      Counter64
        MAX-ACCESS  read-only
        STATUS      current

        DESCRIPTION
            " register request rxed"
        ::= { utsPonIfExtStatsEntry 19 }

    utsPonIfExtStatsRegisterAckTx OBJECT-TYPE
        SYNTAX      Counter64
        MAX-ACCESS  read-only
        STATUS      current

        DESCRIPTION
            "register ack txed"
        ::= { utsPonIfExtStatsEntry 20 }

    utsPonIfExtStatsRegisterAckRx OBJECT-TYPE
        SYNTAX      Counter64
        MAX-ACCESS  read-only
        STATUS      current

        DESCRIPTION
            "register ack rxed"
        ::= { utsPonIfExtStatsEntry 21 }

    utsPonIfExtStatsTxFramesPerPriority0 OBJECT-TYPE
        SYNTAX      Counter64
        MAX-ACCESS  read-only
        STATUS      current

        DESCRIPTION
            "tx frames on priority 0"
        ::= { utsPonIfExtStatsEntry 22 }

    utsPonIfExtStatsTxFramesPerPriority1 OBJECT-TYPE
        SYNTAX      Counter64
        MAX-ACCESS  read-only
        STATUS      current

        DESCRIPTION
            "tx frames on priority 1"
        ::= { utsPonIfExtStatsEntry 23 }

    utsPonIfExtStatsTxFramesPerPriority2 OBJECT-TYPE
        SYNTAX      Counter64
        MAX-ACCESS  read-only
        STATUS      current

        DESCRIPTION
            "tx frames on priority 2"
        ::= { utsPonIfExtStatsEntry 24 }

    utsPonIfExtStatsTxFramesPerPriority3 OBJECT-TYPE
        SYNTAX      Counter64
        MAX-ACCESS  read-only
        STATUS      current

        DESCRIPTION
            "tx frames on priority 3"
        ::= { utsPonIfExtStatsEntry 25 }

    utsPonIfExtStatsTxFramesPerPriority4 OBJECT-TYPE
        SYNTAX      Counter64
        MAX-ACCESS  read-only
        STATUS      current

        DESCRIPTION
            "tx frames on priority 4"
        ::= { utsPonIfExtStatsEntry 26 }

    utsPonIfExtStatsTxFramesPerPriority5 OBJECT-TYPE
        SYNTAX      Counter64
        MAX-ACCESS  read-only
        STATUS      current

        DESCRIPTION
            "tx frames on priority 5"
        ::= { utsPonIfExtStatsEntry 27 }

    utsPonIfExtStatsTxFramesPerPriority6 OBJECT-TYPE
        SYNTAX      Counter64
        MAX-ACCESS  read-only
        STATUS      current

        DESCRIPTION
            "tx frames on priority 6"
        ::= { utsPonIfExtStatsEntry 28 }

    utsPonIfExtStatsTxFramesPerPriority7 OBJECT-TYPE
        SYNTAX      Counter64
        MAX-ACCESS  read-only
        STATUS      current

        DESCRIPTION
            "tx frames on priority 7"
        ::= { utsPonIfExtStatsEntry 29 }

    utsPonIfExtStatsRxFramesPerPriority0 OBJECT-TYPE
        SYNTAX      Counter64
        MAX-ACCESS  read-only
        STATUS      current

        DESCRIPTION
            "rx frames on priority 0"
        ::= { utsPonIfExtStatsEntry 30 }

    utsPonIfExtStatsRxFramesPerPriority1 OBJECT-TYPE
        SYNTAX      Counter64
        MAX-ACCESS  read-only
        STATUS      current

        DESCRIPTION
            "rx frames on priority 1"
        ::= { utsPonIfExtStatsEntry 31 }

    utsPonIfExtStatsRxFramesPerPriority2 OBJECT-TYPE
        SYNTAX      Counter64
        MAX-ACCESS  read-only
        STATUS      current

        DESCRIPTION
            "rx frames on priority 2"
        ::= { utsPonIfExtStatsEntry 32 }

    utsPonIfExtStatsRxFramesPerPriority3 OBJECT-TYPE
        SYNTAX      Counter64
        MAX-ACCESS  read-only
        STATUS      current

        DESCRIPTION
            "rx frames on priority 3"
        ::= { utsPonIfExtStatsEntry 33 }

    utsPonIfExtStatsRxFramesPerPriority4 OBJECT-TYPE
        SYNTAX      Counter64
        MAX-ACCESS  read-only
        STATUS      current

        DESCRIPTION
            "rx frames on priority 4"
        ::= { utsPonIfExtStatsEntry 34 }

    utsPonIfExtStatsRxFramesPerPriority5 OBJECT-TYPE
        SYNTAX      Counter64
        MAX-ACCESS  read-only
        STATUS      current

        DESCRIPTION
            "rx frames on priority 5"
        ::= { utsPonIfExtStatsEntry 35 }

    utsPonIfExtStatsRxFramesPerPriority6 OBJECT-TYPE
        SYNTAX      Counter64
        MAX-ACCESS  read-only
        STATUS      current

        DESCRIPTION
            "rx frames on priority 6"
        ::= { utsPonIfExtStatsEntry 36 }

    utsPonIfExtStatsRxFramesPerPriority7 OBJECT-TYPE
        SYNTAX      Counter64
        MAX-ACCESS  read-only
        STATUS      current

        DESCRIPTION
            "rx frames on priority 7"
        ::= { utsPonIfExtStatsEntry 37 }

    utsPonIfExtStatsDroppedFramesPerPriority0 OBJECT-TYPE
        SYNTAX      Counter64
        MAX-ACCESS  read-only
        STATUS      current

        DESCRIPTION
            "dropped frames per priority 0"
        ::= { utsPonIfExtStatsEntry 38 }

    utsPonIfExtStatsDroppedFramesPerPriority1 OBJECT-TYPE
        SYNTAX      Counter64
        MAX-ACCESS  read-only
        STATUS      current

        DESCRIPTION
            "dropped frames per priority 1"
        ::= { utsPonIfExtStatsEntry 39 }

    utsPonIfExtStatsDroppedFramesPerPriority2 OBJECT-TYPE
        SYNTAX      Counter64
        MAX-ACCESS  read-only
        STATUS      current

        DESCRIPTION
            "dropped frames per priority 2"
        ::= { utsPonIfExtStatsEntry 40 }

    utsPonIfExtStatsDroppedFramesPerPriority3 OBJECT-TYPE
        SYNTAX      Counter64
        MAX-ACCESS  read-only
        STATUS      current

        DESCRIPTION
            "dropped frames per priority 3"
        ::= { utsPonIfExtStatsEntry 41 }

    utsPonIfExtStatsDroppedFramesPerPriority4 OBJECT-TYPE
        SYNTAX      Counter64
        MAX-ACCESS  read-only
        STATUS      current

        DESCRIPTION
            "dropped frames per priority 4"
        ::= { utsPonIfExtStatsEntry 42 }

    utsPonIfExtStatsDroppedFramesPerPriority5 OBJECT-TYPE
        SYNTAX      Counter64
        MAX-ACCESS  read-only
        STATUS      current

        DESCRIPTION
            "dropped frames per priority 5"
        ::= { utsPonIfExtStatsEntry 43 }

    utsPonIfExtStatsDroppedFramesPerPriority6 OBJECT-TYPE
        SYNTAX      Counter64
        MAX-ACCESS  read-only
        STATUS      current

        DESCRIPTION
            "dropped frames per priority 6"
        ::= { utsPonIfExtStatsEntry 44 }

    utsPonIfExtStatsDroppedFramesPerPriority7 OBJECT-TYPE
        SYNTAX      Counter64
        MAX-ACCESS  read-only
        STATUS      current

        DESCRIPTION
            "dropped frames per priority 7"
        ::= { utsPonIfExtStatsEntry 45 }

    utsPonIfExtStatsFramesTx OBJECT-TYPE
        SYNTAX      Counter64
        MAX-ACCESS  read-only
        STATUS      current

        DESCRIPTION
            "tx frames"
        ::= { utsPonIfExtStatsEntry 46 }

    utsPonIfExtStatsSingleCollisionFrames OBJECT-TYPE
        SYNTAX      Counter64
        MAX-ACCESS  read-only
        STATUS      current

        DESCRIPTION
            "single collision frame"
        ::= { utsPonIfExtStatsEntry 47 }

    utsPonIfExtStatsMultipleCollisionFrames OBJECT-TYPE
        SYNTAX      Counter64
        MAX-ACCESS  read-only
        STATUS      current

        DESCRIPTION
            "multiple collision frame"
        ::= { utsPonIfExtStatsEntry 48 }

    utsPonIfExtStatsFramesRx OBJECT-TYPE
        SYNTAX      Counter64
        MAX-ACCESS  read-only
        STATUS      current

        DESCRIPTION
            "rx frames"
        ::= { utsPonIfExtStatsEntry 49 }

    utsPonIfExtStatsAlignmentErrs OBJECT-TYPE
        SYNTAX      Counter64
        MAX-ACCESS  read-only
        STATUS      current

        DESCRIPTION
            "alignment error packet"
        ::= { utsPonIfExtStatsEntry 50 }

    utsPonIfExtStatsLlidFramesRx OBJECT-TYPE
        SYNTAX      Counter64
        MAX-ACCESS  read-only
        STATUS      current

        DESCRIPTION
            "logical link id rx frame"
        ::= { utsPonIfExtStatsEntry 51 }

    utsPonIfExtStatsBcastFramesRx OBJECT-TYPE
        SYNTAX      Counter64
        MAX-ACCESS  read-only
        STATUS      current

        DESCRIPTION
            "receive broadcast frame"
        ::= { utsPonIfExtStatsEntry 52 }

    utsPonIfExtStatsInvalidErrFramesRx OBJECT-TYPE
        SYNTAX      Counter64
        MAX-ACCESS  read-only
        STATUS      current

        DESCRIPTION
            "recevie invalid frame"
        ::= { utsPonIfExtStatsEntry 53 }

    utsPonIfExtStatsLlidBcastErrFramesRx OBJECT-TYPE
        SYNTAX      Counter64
        MAX-ACCESS  read-only
        STATUS      current

        DESCRIPTION
            "receive logical link id error broadcast frame"
        ::= { utsPonIfExtStatsEntry 54 }

    utsPonIfExtStatsHCFramesErrRx OBJECT-TYPE
        SYNTAX      Counter64
        MAX-ACCESS  read-only
        STATUS      current

        DESCRIPTION
            "HC receive error frames"
        ::= { utsPonIfExtStatsEntry 55 }

    utsPonIfExtStatsOnuByteCount OBJECT-TYPE
        SYNTAX      Counter64
        MAX-ACCESS  read-only
        STATUS      current

        DESCRIPTION
            "statistic onu byte count"
        ::= { utsPonIfExtStatsEntry 56 }

    utsPonIfExtStatsErrOnuBytes OBJECT-TYPE
        SYNTAX      Counter64
        MAX-ACCESS  read-only
        STATUS      current

        DESCRIPTION
            "statistic onu error bytes"
        ::= { utsPonIfExtStatsEntry 57 }

    utsPonIfExtStatsHostFramesPonTx OBJECT-TYPE
        SYNTAX      Counter64
        MAX-ACCESS  read-only
        STATUS      current

        DESCRIPTION
            "host transmit frame"
        ::= { utsPonIfExtStatsEntry 58 }

    utsPonIfExtStatsHostFramesPonRx OBJECT-TYPE
        SYNTAX      Counter64
        MAX-ACCESS  read-only
        STATUS      current

        DESCRIPTION
            "host receive frame"
        ::= { utsPonIfExtStatsEntry 59 }

    utsPonIfExtStatsHostOctetsTx OBJECT-TYPE
        SYNTAX      Counter64
        MAX-ACCESS  read-only
        STATUS      current

        DESCRIPTION
            "host transmit octets"
        ::= { utsPonIfExtStatsEntry 60 }

    utsPonIfExtStatsHostOctetsRx OBJECT-TYPE
        SYNTAX      Counter64
        MAX-ACCESS  read-only
        STATUS      current

        DESCRIPTION
            "host recevie octets"
        ::= { utsPonIfExtStatsEntry 61 }

    utsPonIfExtStatsPauseFramesPonRx OBJECT-TYPE
        SYNTAX      Counter64
        MAX-ACCESS  read-only
        STATUS      current

        DESCRIPTION
            "pon recevie pause frames"
        ::= { utsPonIfExtStatsEntry 62 }

    utsPonIfExtStatsPauseFramesSystemRx OBJECT-TYPE
        SYNTAX      Counter64
        MAX-ACCESS  read-only
        STATUS      current

        DESCRIPTION
            "system receive pause frames"
        ::= { utsPonIfExtStatsEntry 63 }

    utsPonIfExtStatsPauseFramesSystemTx OBJECT-TYPE
        SYNTAX      Counter64
        MAX-ACCESS  read-only
        STATUS      current

        DESCRIPTION
            "system transmit pause frame"
        ::= { utsPonIfExtStatsEntry 64 }

    utsPonIfExtStatsOamFramesTx OBJECT-TYPE
        SYNTAX      Counter64
        MAX-ACCESS  read-only
        STATUS      current

        DESCRIPTION
            "transmit oam frames"
        ::= { utsPonIfExtStatsEntry 65 }

    utsPonIfExtStatsOamFramesRx OBJECT-TYPE
        SYNTAX      Counter64
        MAX-ACCESS  read-only
        STATUS      current

        DESCRIPTION
            "receive oam frames"
        ::= { utsPonIfExtStatsEntry 66 }

    utsPonIfExtStatsGrantFramesRx OBJECT-TYPE
        SYNTAX      Counter64
        MAX-ACCESS  read-only
        STATUS      current

        DESCRIPTION
            "receive grant frames"
        ::= { utsPonIfExtStatsEntry 67 }

    utsPonIfExtStatsTotalFramesRx OBJECT-TYPE
        SYNTAX      Counter64
        MAX-ACCESS  read-only
        STATUS      current

        DESCRIPTION
            "receive total frame"
        ::= { utsPonIfExtStatsEntry 68 }

    utsPonIfExtStatsTotalFramesRxErr OBJECT-TYPE
        SYNTAX      Counter64
        MAX-ACCESS  read-only
        STATUS      current

        DESCRIPTION
            "total receive error frame"
        ::= { utsPonIfExtStatsEntry 69 }

    utsPonIfExtStatsTotalFramesTx OBJECT-TYPE
        SYNTAX      Counter64
        MAX-ACCESS  read-only
        STATUS      current

        DESCRIPTION
            "total transmit frames"
        ::= { utsPonIfExtStatsEntry 70 }

    utsPonIfExtStatsPonDroppedTxFrames OBJECT-TYPE
        SYNTAX      Counter64
        MAX-ACCESS  read-only
        STATUS      current

        DESCRIPTION
            "pon transmit dropped frames"
        ::= { utsPonIfExtStatsEntry 71 }

    utsPonIfExtStatsTotalOctetsRxErrSystem OBJECT-TYPE
        SYNTAX      Counter64
        MAX-ACCESS  read-only
        STATUS      current

        DESCRIPTION
            "system total receive octets"
        ::= { utsPonIfExtStatsEntry 72 }

    utsPonIfExtStatsTotalOctetsRx OBJECT-TYPE
        SYNTAX      Counter64
        MAX-ACCESS  read-only
        STATUS      current

        DESCRIPTION
            "total receive octets"
        ::= { utsPonIfExtStatsEntry 73 }

    utsPonIfExtStatsHostFramesPonDropped OBJECT-TYPE
        SYNTAX      Counter64
        MAX-ACCESS  read-only
        STATUS      current

        DESCRIPTION
            "pon dropped host frames"
        ::= { utsPonIfExtStatsEntry 74 }

    utsPonIfExtStatsFrameTooLongErrsSystemRx OBJECT-TYPE
        SYNTAX      Counter64
        MAX-ACCESS  read-only
        STATUS      current

        DESCRIPTION
            "system receive too long frame"
        ::= { utsPonIfExtStatsEntry 75 }

    utsPonIfExtStatsSystemDroppedTxFrames OBJECT-TYPE
        SYNTAX      Counter64
        MAX-ACCESS  read-only
        STATUS      current

        DESCRIPTION
            "system dropped transmit frames"
        ::= { utsPonIfExtStatsEntry 76 }

    utsPonIfExtStatsFcsErrs OBJECT-TYPE
        SYNTAX      Counter64
        MAX-ACCESS  read-only
        STATUS      current

        DESCRIPTION
            "fcs error frame"
        ::= { utsPonIfExtStatsEntry 77 }

    utsPonIfExtStatsPauseFramesPonTx OBJECT-TYPE
        SYNTAX      Counter64
        MAX-ACCESS  read-only
        STATUS      current

        DESCRIPTION
            "pon transmit pause frame"
        ::= { utsPonIfExtStatsEntry 78 }

    utsPonIfExtStatsDiscardBridgePkts OBJECT-TYPE
        SYNTAX      Counter64
        MAX-ACCESS  read-only
        STATUS      current

        DESCRIPTION
            "discard bridge packets"
        ::= { utsPonIfExtStatsEntry 79 }

    utsPonIfExtStatsFramePonTxOk OBJECT-TYPE
        SYNTAX      Counter64
        MAX-ACCESS  read-only
        STATUS      current

        DESCRIPTION
            "Pon tx ok frame"
        ::= { utsPonIfExtStatsEntry 80 }

    utsPonIfExtStatsFramePonRxOk OBJECT-TYPE
        SYNTAX      Counter64
        MAX-ACCESS  read-only
        STATUS      current

        DESCRIPTION
            "Pon rx ok frame"
        ::= { utsPonIfExtStatsEntry 81 }

    utsPonIfExtStatsFramePonRxErr OBJECT-TYPE
        SYNTAX      Counter64
        MAX-ACCESS  read-only
        STATUS      current

        DESCRIPTION
            "Pon rx err ok frame"
        ::= { utsPonIfExtStatsEntry 82 }

    utsPonIfExtStatsFrameSysTxOk OBJECT-TYPE
        SYNTAX      Counter64
        MAX-ACCESS  read-only
        STATUS      current

        DESCRIPTION
            "System tx ok frame"
        ::= { utsPonIfExtStatsEntry 83 }

    utsPonIfExtStatsFrameSysRxOk OBJECT-TYPE
        SYNTAX      Counter64
        MAX-ACCESS  read-only
        STATUS      current

        DESCRIPTION
            "System rx ok frame"
        ::= { utsPonIfExtStatsEntry 84 }

    utsPonIfExtStatsFrameSysRxErr OBJECT-TYPE
        SYNTAX      Counter64
        MAX-ACCESS  read-only
        STATUS      current

        DESCRIPTION
            "System tx ok frame"
        ::= { utsPonIfExtStatsEntry 85 }

-- PON Octets: Both ONU and OLT
-- Added Dec 31 2005 by zhaoxf

    utsPonIfExtStatsPonOctetsTxOk OBJECT-TYPE
        SYNTAX      Counter64
        MAX-ACCESS  read-only
        STATUS      current

        DESCRIPTION
            "PON octets rxed."
        ::= { utsPonIfExtStatsEntry 86 }

    utsPonIfExtStatsPonOctetsRxOk OBJECT-TYPE
        SYNTAX      Counter64
        MAX-ACCESS  read-only
        STATUS      current

        DESCRIPTION
            "PON octets rxed."
        ::= { utsPonIfExtStatsEntry 87 }

    utsPonIfExtPMStatus OBJECT-TYPE
    SYNTAX      INTEGER
    {
       enable(1),
       disable(2)
    }
	MAX-ACCESS  read-write
	STATUS      current
	DESCRIPTION
	    "Enable or disable the PON interface TFTP performance management."
   ::= { utsPonIfExtStatsEntry 100 }

------------------------------------------------------
--    Immenstar chip counters
------------------------------------------------------

-- interface statistics per RFC 2863

   utsPonIf2ExtStatsTable  OBJECT-TYPE
        SYNTAX      SEQUENCE OF UtsPonIf2ExtStatsEntry
        MAX-ACCESS  not-accessible
        STATUS      current
        DESCRIPTION
            "A list of UTStarcom's extension to the interface entries. The
             number of entries is given by the value of pon if index."
       ::= { utsEponPonStatsExt 2 }

   utsPonIf2ExtStatsEntry OBJECT-TYPE
       SYNTAX       UtsPonIf2ExtStatsEntry
       MAX-ACCESS   not-accessible
       STATUS       current
       DESCRIPTION
          "An entry containing additional management information
            applicable to a particular interface."
      INDEX { utsPonIf2ExtStatsIndex }
      ::= { utsPonIf2ExtStatsTable 1 }


    UtsPonIf2ExtStatsEntry ::=
        SEQUENCE {
            utsPonIf2ExtStatsIndex
                INTEGER,
            utsPonIf2ExtStatsModule
                INTEGER,
            utsPonIf2ExtStatsPort
                INTEGER,
            utsPonIf2ExtStatsLogicalLinkId
                INTEGER,
            utsPonIfExtStatsInOctets
                Counter64,
			utsPonIfExtStatsOutOctets
			    Counter64,
			utsPonIfExtStatsInUnicast
			    Counter64,
			utsPonIfExtStatsOutUnicast
			    Counter64,
			utsPonIfExtStatsInMulticast
			    Counter64,
			utsPonIfExtStatsOutMulticast
			    Counter64,
			utsPonIfExtStatsInBroadcast
			    Counter64,
			utsPonIfExtStatsOutBroadcast
			    Counter64,
			utsPonIfExtStatsInDiscards
			    Counter64,
			utsPonIfExtStatsOutDiscards
			    Counter64,
			utsPonIfExtStatsInErrors
			    Counter64,
			utsPonIfExtStatsOutErrors
			    Counter64,
			utsPonIfExtStatsInUnknownProtos
                Counter64,
            utsPonIfExtStatsPMStatus
               INTEGER
       }

    utsPonIf2ExtStatsIndex OBJECT-TYPE
        SYNTAX      INTEGER
        MAX-ACCESS  not-accessible
        STATUS      current
        DESCRIPTION
           " Pon interface index"
       ::= { utsPonIf2ExtStatsEntry 1 }

    utsPonIf2ExtStatsModule OBJECT-TYPE
        SYNTAX      INTEGER
        MAX-ACCESS  read-only
        STATUS      current
        DESCRIPTION
           " Pon interface Module index"
       ::= { utsPonIf2ExtStatsEntry 2 }

    utsPonIf2ExtStatsPort OBJECT-TYPE
        SYNTAX      INTEGER
        MAX-ACCESS  read-only
        STATUS      current
        DESCRIPTION
           " Pon interface port index"
       ::= { utsPonIf2ExtStatsEntry 3 }

    utsPonIf2ExtStatsLogicalLinkId OBJECT-TYPE
        SYNTAX      INTEGER
        MAX-ACCESS  read-only
        STATUS      current
        DESCRIPTION
           " Pon interface logical port index"
       ::= { utsPonIf2ExtStatsEntry 4 }

    utsPonIfExtStatsInOctets OBJECT-TYPE
        SYNTAX      Counter64
        MAX-ACCESS  read-only
        STATUS      current
        DESCRIPTION
           " Pon interface in octets"
       ::= { utsPonIf2ExtStatsEntry 5 }

    utsPonIfExtStatsOutOctets OBJECT-TYPE
        SYNTAX      Counter64
        MAX-ACCESS  read-only
        STATUS      current
        DESCRIPTION
           " Pon interface out octets"
       ::= { utsPonIf2ExtStatsEntry 6 }

    utsPonIfExtStatsInUnicast OBJECT-TYPE
        SYNTAX      Counter64
        MAX-ACCESS  read-only
        STATUS      current
        DESCRIPTION
           " Pon interface in unicast"
       ::= { utsPonIf2ExtStatsEntry 7 }

    utsPonIfExtStatsOutUnicast OBJECT-TYPE
        SYNTAX      Counter64
        MAX-ACCESS  read-only
        STATUS      current
        DESCRIPTION
           " Pon interface out unicast"
       ::= { utsPonIf2ExtStatsEntry 8 }

    utsPonIfExtStatsInMulticast OBJECT-TYPE
        SYNTAX      Counter64
        MAX-ACCESS  read-only
        STATUS      current
        DESCRIPTION
           " Pon interface in multicast"
       ::= { utsPonIf2ExtStatsEntry 9 }

    utsPonIfExtStatsOutMulticast OBJECT-TYPE
        SYNTAX      Counter64
        MAX-ACCESS  read-only
        STATUS      current
        DESCRIPTION
           " Pon interface out multicast"
       ::= { utsPonIf2ExtStatsEntry 10 }

    utsPonIfExtStatsInBroadcast OBJECT-TYPE
        SYNTAX      Counter64
        MAX-ACCESS  read-only
        STATUS      current
        DESCRIPTION
           " Pon interface in broadcast"
       ::= { utsPonIf2ExtStatsEntry 11 }

    utsPonIfExtStatsOutBroadcast OBJECT-TYPE
        SYNTAX      Counter64
        MAX-ACCESS  read-only
        STATUS      current
        DESCRIPTION
           " Pon interface out broadcast"
       ::= { utsPonIf2ExtStatsEntry 12 }

    utsPonIfExtStatsInDiscards OBJECT-TYPE
        SYNTAX      Counter64
        MAX-ACCESS  read-only
        STATUS      current
        DESCRIPTION
           " Pon interface in discards"
       ::= { utsPonIf2ExtStatsEntry 13 }

    utsPonIfExtStatsOutDiscards OBJECT-TYPE
        SYNTAX      Counter64
        MAX-ACCESS  read-only
        STATUS      current
        DESCRIPTION
           " Pon interface out discards"
       ::= { utsPonIf2ExtStatsEntry 14 }

    utsPonIfExtStatsInErrors OBJECT-TYPE
        SYNTAX      Counter64
        MAX-ACCESS  read-only
        STATUS      current
        DESCRIPTION
           " Pon interface in errors"
       ::= { utsPonIf2ExtStatsEntry 15 }

    utsPonIfExtStatsOutErrors OBJECT-TYPE
        SYNTAX      Counter64
        MAX-ACCESS  read-only
        STATUS      current
        DESCRIPTION
           " Pon interface in errors"
       ::= { utsPonIf2ExtStatsEntry 16 }

    utsPonIfExtStatsInUnknownProtos OBJECT-TYPE
        SYNTAX      Counter64
        MAX-ACCESS  read-only
        STATUS      current
        DESCRIPTION
           " Pon interface in unknown protos"
       ::= { utsPonIf2ExtStatsEntry 17 }



    utsPonIfExtStatsPMStatus OBJECT-TYPE
		SYNTAX      INTEGER
				    {
				       enable(1),
				       disable(2)
				    }
		MAX-ACCESS  read-write
		STATUS      current
		DESCRIPTION
		    "Enable or disable the PON interface TFTP performance management."
       ::= { utsPonIf2ExtStatsEntry 30 }

-- Ethernet-like interface stats per RFC 3635

   utsPonEthLikeIf2ExtStatsTable  OBJECT-TYPE
        SYNTAX      SEQUENCE OF UtsPonEthLikeIf2ExtStatsEntry
        MAX-ACCESS  not-accessible
        STATUS      current
        DESCRIPTION
            "A list of UTStarcom's extension to the interface entries. The
             number of entries is given by the value of pon if index."
       ::= { utsEponPonStatsExt 3 }

   utsPonEthLikeIf2ExtStatsEntry OBJECT-TYPE
       SYNTAX       UtsPonEthLikeIf2ExtStatsEntry
       MAX-ACCESS   not-accessible
       STATUS       current
       DESCRIPTION
          "An entry containing additional management information
            applicable to a particular interface."
      INDEX { utsPonEthLikeIfExtIndex }
      ::= { utsPonEthLikeIf2ExtStatsTable 1 }


    UtsPonEthLikeIf2ExtStatsEntry ::=
        SEQUENCE {
            utsPonEthLikeIfExtIndex
                INTEGER,
            utsPonEthLikeIfExtModule
                INTEGER,
            utsPonEthLikeIfExtPort
                INTEGER,
            utsPonEthLikeIfExtLogicalPortId
                INTEGER,
			utsPonIfExtStatsAlignmentErrors
			    Counter64,
			utsPonIfExtStatsFcsErrors
			    Counter64,
			utsPonIfExtStatsSingleCollision
			    Counter32,
			utsPonIfExtStatsMultipleCollision
			    Counter32,
			utsPonIfExtStatsSqeTestErros
			    Counter32,
			utsPonIfExtStatsDeferredTransmissions
			    Counter32,
			utsPonIfExtStatsLateCollisions
			    Counter32,
			utsPonIfExtStatsExcessiveCollisions
			    Counter32,
			utsPonIfExtStatsInternalMacTxErrors
			    Counter64,
			utsPonIfExtStatsCarrierSenseErrors
			    Counter32,
			utsPonIfExtStatsFrameTooLong
			    Counter64,
			utsPonIfExtStatsInternalMacRxErrors
			    Counter64,
			utsPonIfExtStatsSymbolErrors
			    Counter64,
			utsPonIfExtInUnknownOpcode
			    Counter64,
			utsPonIfExtStatsInPauseFrames
			    Counter64,
			utsPonIfExtStatsOutPauseFrames
			    Counter64,
			utsPonEthLikeIfExtPMStatus
               INTEGER
       }

    utsPonEthLikeIfExtIndex OBJECT-TYPE
        SYNTAX      INTEGER
        MAX-ACCESS  not-accessible
        STATUS      current
        DESCRIPTION
           " Pon interface index"
       ::= { utsPonEthLikeIf2ExtStatsEntry 1 }

    utsPonEthLikeIfExtModule OBJECT-TYPE
        SYNTAX      INTEGER
        MAX-ACCESS  read-only
        STATUS      current
        DESCRIPTION
           " Pon interface Module index"
       ::= { utsPonEthLikeIf2ExtStatsEntry 2 }

    utsPonEthLikeIfExtPort OBJECT-TYPE
        SYNTAX      INTEGER
        MAX-ACCESS  read-only
        STATUS      current
        DESCRIPTION
           " Pon interface port index"
       ::= { utsPonEthLikeIf2ExtStatsEntry 3 }

    utsPonEthLikeIfExtLogicalPortId OBJECT-TYPE
        SYNTAX      INTEGER
        MAX-ACCESS  read-only
        STATUS      current
        DESCRIPTION
           " Pon interface logical port index"
       ::= { utsPonEthLikeIf2ExtStatsEntry 4 }

    utsPonIfExtStatsAlignmentErrors OBJECT-TYPE
        SYNTAX      Counter64
        MAX-ACCESS  read-only
        STATUS      current
        DESCRIPTION
           "Alignment errors"
       ::= { utsPonEthLikeIf2ExtStatsEntry 5 }

    utsPonIfExtStatsFcsErrors OBJECT-TYPE
        SYNTAX      Counter64
        MAX-ACCESS  read-only
        STATUS      current
        DESCRIPTION
           "Fcs errors"
       ::= { utsPonEthLikeIf2ExtStatsEntry 6 }

    utsPonIfExtStatsSingleCollision OBJECT-TYPE
        SYNTAX      Counter32
        MAX-ACCESS  read-only
        STATUS      current
        DESCRIPTION
           "Single collision"
       ::= { utsPonEthLikeIf2ExtStatsEntry 7 }

    utsPonIfExtStatsMultipleCollision OBJECT-TYPE
        SYNTAX      Counter32
        MAX-ACCESS  read-only
        STATUS      current
        DESCRIPTION
           "Multiple collision"
       ::= { utsPonEthLikeIf2ExtStatsEntry 8 }

    utsPonIfExtStatsSqeTestErros OBJECT-TYPE
        SYNTAX      Counter32
        MAX-ACCESS  read-only
        STATUS      current
        DESCRIPTION
           "Sqe test errors"
       ::= { utsPonEthLikeIf2ExtStatsEntry 9 }

    utsPonIfExtStatsDeferredTransmissions OBJECT-TYPE
        SYNTAX      Counter32
        MAX-ACCESS  read-only
        STATUS      current
        DESCRIPTION
           "Deferred transmissions"
       ::= { utsPonEthLikeIf2ExtStatsEntry 10 }

    utsPonIfExtStatsLateCollisions OBJECT-TYPE
        SYNTAX      Counter32
        MAX-ACCESS  read-only
        STATUS      current
        DESCRIPTION
           "Late collisions"
       ::= { utsPonEthLikeIf2ExtStatsEntry 11 }

    utsPonIfExtStatsExcessiveCollisions OBJECT-TYPE
        SYNTAX      Counter32
        MAX-ACCESS  read-only
        STATUS      current
        DESCRIPTION
           "Excessive collisions"
       ::= { utsPonEthLikeIf2ExtStatsEntry 12 }

    utsPonIfExtStatsInternalMacTxErrors OBJECT-TYPE
        SYNTAX      Counter64
        MAX-ACCESS  read-only
        STATUS      current
        DESCRIPTION
           "Internal MAC tx errors"
       ::= { utsPonEthLikeIf2ExtStatsEntry 13 }

    utsPonIfExtStatsCarrierSenseErrors OBJECT-TYPE
        SYNTAX      Counter32
        MAX-ACCESS  read-only
        STATUS      current
        DESCRIPTION
           "Carrier sense errors"
       ::= { utsPonEthLikeIf2ExtStatsEntry 14 }

    utsPonIfExtStatsFrameTooLong OBJECT-TYPE
        SYNTAX      Counter64
        MAX-ACCESS  read-only
        STATUS      current
        DESCRIPTION
           "Frame too long"
       ::= { utsPonEthLikeIf2ExtStatsEntry 15 }

    utsPonIfExtStatsInternalMacRxErrors OBJECT-TYPE
        SYNTAX      Counter64
        MAX-ACCESS  read-only
        STATUS      current
        DESCRIPTION
           "Internal MAC rx errors"
       ::= { utsPonEthLikeIf2ExtStatsEntry 16 }

    utsPonIfExtStatsSymbolErrors OBJECT-TYPE
        SYNTAX      Counter64
        MAX-ACCESS  read-only
        STATUS      current
        DESCRIPTION
           "Symbol errors"
       ::= { utsPonEthLikeIf2ExtStatsEntry 17 }

    utsPonIfExtInUnknownOpcode OBJECT-TYPE
        SYNTAX      Counter64
        MAX-ACCESS  read-only
        STATUS      current
        DESCRIPTION
           "In unknown opcode"
       ::= { utsPonEthLikeIf2ExtStatsEntry 18 }

    utsPonIfExtStatsInPauseFrames OBJECT-TYPE
        SYNTAX      Counter64
        MAX-ACCESS  read-only
        STATUS      current
        DESCRIPTION
           "In pause frames"
       ::= { utsPonEthLikeIf2ExtStatsEntry 19 }

    utsPonIfExtStatsOutPauseFrames OBJECT-TYPE
        SYNTAX      Counter64
        MAX-ACCESS  read-only
        STATUS      current
        DESCRIPTION
           "Out pause frames"
       ::= { utsPonEthLikeIf2ExtStatsEntry 20 }

    utsPonEthLikeIfExtPMStatus OBJECT-TYPE
		SYNTAX      INTEGER
				    {
				       enable(1),
				       disable(2)
				    }
		MAX-ACCESS  read-write
		STATUS      current
		DESCRIPTION
		    "Enable or disable the PON interface TFTP performance management."
       ::= { utsPonEthLikeIf2ExtStatsEntry 30 }

-- EPON statistics per EFM EPON MIB

   utsPonEfmIf2ExtStatsTable  OBJECT-TYPE
        SYNTAX      SEQUENCE OF UtsPonEfmIf2ExtStatsEntry
        MAX-ACCESS  not-accessible
        STATUS      current
        DESCRIPTION
            "A list of UTStarcom's extension to the interface entries. The
             number of entries is given by the value of pon if index."
       ::= { utsEponPonStatsExt 4 }

   utsPonEfmIf2ExtStatsEntry OBJECT-TYPE
       SYNTAX       UtsPonEfmIf2ExtStatsEntry
       MAX-ACCESS   not-accessible
       STATUS       current
       DESCRIPTION
          "An entry containing additional management information
            applicable to a particular interface."
      INDEX { utsPonEfmIfExtIndex }
      ::= { utsPonEfmIf2ExtStatsTable 1 }


    UtsPonEfmIf2ExtStatsEntry ::=
        SEQUENCE {
            utsPonEfmIfExtIndex
                INTEGER,
            utsPonEfmIfExtModule
                INTEGER,
            utsPonEfmIfExtPort
                INTEGER,
            utsPonEfmIfExtLogicalPortId
                INTEGER,
			utsPonIfExtStatsMacCtrlFrameRx
			    Counter32,
			utsPonIfExtStatsDiscWindowsSent
			    Counter32,
			utsPonIfExtStatsDiscTimeout
			    Counter32,
			utsPonIfExtStatsTxRegRequest
			    Counter32,
			utsPonIfExtStatsRxRegRequest
			    Counter32,
			utsPonIfExtStatsTxRegAck
			    Counter32,
			utsPonIfExtStatsRxRegAck
			    Counter32,
			utsPonIfExtStatsTxReport
			    Counter32,
			utsPonIfExtStatsRxReport
			    Counter32,
			utsPonIfExtStatsTxGate
			    Counter32,
			utsPonIfExtStatsRxGate
			    Counter32,
			utsPonIfExtStatsTxRegister
			    Counter32,
			utsPonIfExtStatsRxRegister
			    Counter32,
			utsPonIfExtStatsRxNotSupported
			    Counter32,
			utsPonIfExtStatsSldErrors
			    Counter32,
			utsPonIfExtStatsCrc8Errors
			    Counter32,
			utsPonIfExtStatsBadLlid
			    Counter32,
			utsPonIfExtStatsGoodLlid
			    Counter32,
			utsPonIfExtStatsOnuPonCastLlid
			    Counter32,
			utsPonIfExtStatsOltPonCastLlid
			    Counter32,
			utsPonIfExtStatsBcastLlidNotOnuId
			    Counter32,
			utsPonIfExtStatsOnuLlidNotBcast
			    Counter32,
			utsPonIfExtStatsBcastLlidPlusOnuId
			    Counter32,
			utsPonIfExtStatsNotBcastLlidNotOnuLId
			    Counter32,
			utsPonIfExtStatsPcsCodingViolation
			    Counter32,
			utsPonIfExtStatsFecCorrectedBlocks
			    Counter32,
			utsPonIfExtStatsFecUncorrectableBlocks
			    Counter32
       }

    utsPonEfmIfExtIndex OBJECT-TYPE
        SYNTAX      INTEGER
        MAX-ACCESS  not-accessible
        STATUS      current
        DESCRIPTION
           " Pon interface index"
       ::= { utsPonEfmIf2ExtStatsEntry 1 }

    utsPonEfmIfExtModule OBJECT-TYPE
        SYNTAX      INTEGER
        MAX-ACCESS  read-only
        STATUS      current
        DESCRIPTION
           " Pon interface Module index"
       ::= { utsPonEfmIf2ExtStatsEntry 2 }

    utsPonEfmIfExtPort OBJECT-TYPE
        SYNTAX      INTEGER
        MAX-ACCESS  read-only
        STATUS      current
        DESCRIPTION
           " Pon interface port index"
       ::= { utsPonEfmIf2ExtStatsEntry 3 }

    utsPonEfmIfExtLogicalPortId OBJECT-TYPE
        SYNTAX      INTEGER
        MAX-ACCESS  read-only
        STATUS      current
        DESCRIPTION
           " Pon interface logical port index"
       ::= { utsPonEfmIf2ExtStatsEntry 4 }

    utsPonIfExtStatsMacCtrlFrameRx OBJECT-TYPE
        SYNTAX      Counter32
        MAX-ACCESS  read-only
        STATUS      current
        DESCRIPTION
           "MAC ctrl frame rx"
       ::= { utsPonEfmIf2ExtStatsEntry 5 }

    utsPonIfExtStatsDiscWindowsSent OBJECT-TYPE
        SYNTAX      Counter32
        MAX-ACCESS  read-only
        STATUS      current
        DESCRIPTION
           "Disc windows sent"
       ::= { utsPonEfmIf2ExtStatsEntry 6 }

    utsPonIfExtStatsDiscTimeout OBJECT-TYPE
        SYNTAX      Counter32
        MAX-ACCESS  read-only
        STATUS      current
        DESCRIPTION
           "Disc timeout"
       ::= { utsPonEfmIf2ExtStatsEntry 7 }

    utsPonIfExtStatsTxRegRequest OBJECT-TYPE
        SYNTAX      Counter32
        MAX-ACCESS  read-only
        STATUS      current
        DESCRIPTION
           "Tx reg request"
       ::= { utsPonEfmIf2ExtStatsEntry 8 }

    utsPonIfExtStatsRxRegRequest OBJECT-TYPE
        SYNTAX      Counter32
        MAX-ACCESS  read-only
        STATUS      current
        DESCRIPTION
           "Rx reg request"
       ::= { utsPonEfmIf2ExtStatsEntry 9 }

    utsPonIfExtStatsTxRegAck OBJECT-TYPE
        SYNTAX      Counter32
        MAX-ACCESS  read-only
        STATUS      current
        DESCRIPTION
           "Tx reg ack"
       ::= { utsPonEfmIf2ExtStatsEntry 10 }

    utsPonIfExtStatsRxRegAck OBJECT-TYPE
        SYNTAX      Counter32
        MAX-ACCESS  read-only
        STATUS      current
        DESCRIPTION
           "Rx reg ack"
       ::= { utsPonEfmIf2ExtStatsEntry 11 }

    utsPonIfExtStatsTxReport OBJECT-TYPE
        SYNTAX      Counter32
        MAX-ACCESS  read-only
        STATUS      current
        DESCRIPTION
           "Tx report"
       ::= { utsPonEfmIf2ExtStatsEntry 12 }

    utsPonIfExtStatsRxReport OBJECT-TYPE
        SYNTAX      Counter32
        MAX-ACCESS  read-only
        STATUS      current
        DESCRIPTION
           "Rx report"
       ::= { utsPonEfmIf2ExtStatsEntry 13 }

    utsPonIfExtStatsTxGate OBJECT-TYPE
        SYNTAX      Counter32
        MAX-ACCESS  read-only
        STATUS      current
        DESCRIPTION
           "Tx gate"
       ::= { utsPonEfmIf2ExtStatsEntry 14 }

    utsPonIfExtStatsRxGate OBJECT-TYPE
        SYNTAX      Counter32
        MAX-ACCESS  read-only
        STATUS      current
        DESCRIPTION
           "Rx gate"
       ::= { utsPonEfmIf2ExtStatsEntry 15 }

    utsPonIfExtStatsTxRegister OBJECT-TYPE
        SYNTAX      Counter32
        MAX-ACCESS  read-only
        STATUS      current
        DESCRIPTION
           "Tx register"
       ::= { utsPonEfmIf2ExtStatsEntry 16 }

    utsPonIfExtStatsRxRegister OBJECT-TYPE
        SYNTAX      Counter32
        MAX-ACCESS  read-only
        STATUS      current
        DESCRIPTION
           "Rx register"
       ::= { utsPonEfmIf2ExtStatsEntry 17 }

    utsPonIfExtStatsRxNotSupported OBJECT-TYPE
        SYNTAX      Counter32
        MAX-ACCESS  read-only
        STATUS      current
        DESCRIPTION
           "Rx not supported"
       ::= { utsPonEfmIf2ExtStatsEntry 18 }

    utsPonIfExtStatsSldErrors OBJECT-TYPE
        SYNTAX      Counter32
        MAX-ACCESS  read-only
        STATUS      current
        DESCRIPTION
           "Sld errors"
       ::= { utsPonEfmIf2ExtStatsEntry 19 }

    utsPonIfExtStatsCrc8Errors OBJECT-TYPE
        SYNTAX      Counter32
        MAX-ACCESS  read-only
        STATUS      current
        DESCRIPTION
           "Crc8 errors"
       ::= { utsPonEfmIf2ExtStatsEntry 20 }

    utsPonIfExtStatsBadLlid OBJECT-TYPE
        SYNTAX      Counter32
        MAX-ACCESS  read-only
        STATUS      current
        DESCRIPTION
           "Bad llid"
       ::= { utsPonEfmIf2ExtStatsEntry 21 }

    utsPonIfExtStatsGoodLlid OBJECT-TYPE
        SYNTAX      Counter32
        MAX-ACCESS  read-only
        STATUS      current
        DESCRIPTION
           "Good llid"
       ::= { utsPonEfmIf2ExtStatsEntry 22 }

    utsPonIfExtStatsOnuPonCastLlid OBJECT-TYPE
        SYNTAX      Counter32
        MAX-ACCESS  read-only
        STATUS      current
        DESCRIPTION
           "ONU PON cast llid"
       ::= { utsPonEfmIf2ExtStatsEntry 23 }

    utsPonIfExtStatsOltPonCastLlid OBJECT-TYPE
        SYNTAX      Counter32
        MAX-ACCESS  read-only
        STATUS      current
        DESCRIPTION
           "OLT PON cast llid"
       ::= { utsPonEfmIf2ExtStatsEntry 24 }

    utsPonIfExtStatsBcastLlidNotOnuId OBJECT-TYPE
        SYNTAX      Counter32
        MAX-ACCESS  read-only
        STATUS      current
        DESCRIPTION
           "Bcast llid not onu id"
       ::= { utsPonEfmIf2ExtStatsEntry 25 }

    utsPonIfExtStatsOnuLlidNotBcast OBJECT-TYPE
        SYNTAX      Counter32
        MAX-ACCESS  read-only
        STATUS      current
        DESCRIPTION
           "ONU llid not bcast"
       ::= { utsPonEfmIf2ExtStatsEntry 26 }

    utsPonIfExtStatsBcastLlidPlusOnuId OBJECT-TYPE
        SYNTAX      Counter32
        MAX-ACCESS  read-only
        STATUS      current
        DESCRIPTION
           "Bcast llid plus ONU ID"
       ::= { utsPonEfmIf2ExtStatsEntry 27 }

    utsPonIfExtStatsNotBcastLlidNotOnuLId OBJECT-TYPE
        SYNTAX      Counter32
        MAX-ACCESS  read-only
        STATUS      current
        DESCRIPTION
           "Not bcast llid not onu id"
       ::= { utsPonEfmIf2ExtStatsEntry 28 }

    utsPonIfExtStatsPcsCodingViolation OBJECT-TYPE
        SYNTAX      Counter32
        MAX-ACCESS  read-only
        STATUS      current
        DESCRIPTION
           "PCS coding violation"
       ::= { utsPonEfmIf2ExtStatsEntry 29 }

    utsPonIfExtStatsFecCorrectedBlocks OBJECT-TYPE
        SYNTAX      Counter32
        MAX-ACCESS  read-only
        STATUS      current
        DESCRIPTION
           "FEC corrected blocks"
       ::= { utsPonEfmIf2ExtStatsEntry 30 }

    utsPonIfExtStatsFecUncorrectableBlocks OBJECT-TYPE
        SYNTAX      Counter32
        MAX-ACCESS  read-only
        STATUS      current
        DESCRIPTION
           "FEC uncorrectable blocks"
       ::= { utsPonEfmIf2ExtStatsEntry 31 }

-- ONU traffic statistics
-- Retrieve traffic-management based statistics information collected
-- by an OLT on a per ONU traffic-profile basis

   utsPonOnuTrafficExtStatsTable  OBJECT-TYPE
        SYNTAX      SEQUENCE OF UtsPonOnuTrafficExtStatsEntry
        MAX-ACCESS  not-accessible
        STATUS      current
        DESCRIPTION
            "A list of UTStarcom's extension to the interface entries. The
             number of entries is given by the value of pon if index."
       ::= { utsEponPonStatsExt 5 }

   utsPonOnuTrafficExtStatsEntry OBJECT-TYPE
       SYNTAX       UtsPonOnuTrafficExtStatsEntry
       MAX-ACCESS   not-accessible
       STATUS       current
       DESCRIPTION
          "An entry containing additional management information
            applicable to a particular interface."
      INDEX { utsPonnuTrafficExtIndex }
      ::= { utsPonOnuTrafficExtStatsTable 1 }


    UtsPonOnuTrafficExtStatsEntry ::=
        SEQUENCE {
            utsPonnuTrafficExtIndex
                INTEGER,
            utsPonnuTrafficExtModule
                INTEGER,
            utsPonnuTrafficExtPort
                INTEGER,
            utsPonnuTrafficExtLogicalPortId
                INTEGER,
			utsPonOnuAllForwaredPackets
			    Counter64,
			utsPonOnuAllForwaredOctets
			    Counter64,
			utsPonOnuMarkedForwaredOctets
			    Counter64,
			utsPonOnuAllDiscardedPackets
			    Counter64,
			utsPonOnuAllDiscardedOctets
			    Counter64,
			utsPonOnuUnderCirDiscardedOctets
			    Counter64,
		    utsPonOnuOverCirUnderPirDiscardedOctets
			    Counter64,
			utsPonOnuOverPirDiscardedOctets
			    Counter64,
			utsPonOnuTrafficExtPMStatus
			    INTEGER
       }

    utsPonnuTrafficExtIndex OBJECT-TYPE
        SYNTAX      INTEGER
        MAX-ACCESS  not-accessible
        STATUS      current
        DESCRIPTION
           " Pon interface index"
       ::= { utsPonOnuTrafficExtStatsEntry 1 }

    utsPonnuTrafficExtModule OBJECT-TYPE
        SYNTAX      INTEGER
        MAX-ACCESS  read-only
        STATUS      current
        DESCRIPTION
           " Pon interface Module index"
       ::= { utsPonOnuTrafficExtStatsEntry 2 }

    utsPonnuTrafficExtPort OBJECT-TYPE
        SYNTAX      INTEGER
        MAX-ACCESS  read-only
        STATUS      current
        DESCRIPTION
           " Pon interface port index"
       ::= { utsPonOnuTrafficExtStatsEntry 3 }

    utsPonnuTrafficExtLogicalPortId OBJECT-TYPE
        SYNTAX      INTEGER
        MAX-ACCESS  read-only
        STATUS      current
        DESCRIPTION
           " Pon interface logical port index"
       ::= { utsPonOnuTrafficExtStatsEntry 4 }

    utsPonOnuAllForwaredPackets OBJECT-TYPE
        SYNTAX      Counter64
        MAX-ACCESS  read-only
        STATUS      current
        DESCRIPTION
           "All forwarded packets"
       ::= { utsPonOnuTrafficExtStatsEntry 5 }

    utsPonOnuAllForwaredOctets OBJECT-TYPE
        SYNTAX      Counter64
        MAX-ACCESS  read-only
        STATUS      current
        DESCRIPTION
           "All forwarded octets"
       ::= { utsPonOnuTrafficExtStatsEntry 6 }

    utsPonOnuMarkedForwaredOctets OBJECT-TYPE
        SYNTAX      Counter64
        MAX-ACCESS  read-only
        STATUS      current
        DESCRIPTION
           "Marked forwarded octets"
       ::= { utsPonOnuTrafficExtStatsEntry 7 }

    utsPonOnuAllDiscardedPackets OBJECT-TYPE
        SYNTAX      Counter64
        MAX-ACCESS  read-only
        STATUS      current
        DESCRIPTION
           "All discarded packets"
       ::= { utsPonOnuTrafficExtStatsEntry 8 }

    utsPonOnuAllDiscardedOctets OBJECT-TYPE
        SYNTAX      Counter64
        MAX-ACCESS  read-only
        STATUS      current
        DESCRIPTION
           "All discarded octets"
       ::= { utsPonOnuTrafficExtStatsEntry 9 }

    utsPonOnuUnderCirDiscardedOctets OBJECT-TYPE
        SYNTAX      Counter64
        MAX-ACCESS  read-only
        STATUS      current
        DESCRIPTION
           "Under CIR discarded octets"
       ::= { utsPonOnuTrafficExtStatsEntry 10 }

    utsPonOnuOverCirUnderPirDiscardedOctets OBJECT-TYPE
        SYNTAX      Counter64
        MAX-ACCESS  read-only
        STATUS      current
        DESCRIPTION
           "Over CIR under PIR discarded octets"
       ::= { utsPonOnuTrafficExtStatsEntry 11 }

    utsPonOnuOverPirDiscardedOctets OBJECT-TYPE
        SYNTAX      Counter64
        MAX-ACCESS  read-only
        STATUS      current
        DESCRIPTION
           "Over PIR discarded octets"
       ::= { utsPonOnuTrafficExtStatsEntry 12 }

    utsPonOnuTrafficExtPMStatus OBJECT-TYPE
		SYNTAX      INTEGER
				    {
				       enable(1),
				       disable(2)
				    }
		MAX-ACCESS  read-write
		STATUS      current
		DESCRIPTION
		    "Enable or disable the PON interface TFTP performance management."
       ::= { utsPonOnuTrafficExtStatsEntry 30 }


-- IS8015A statistics for PM

   utsPonIf2ExtStatTable  OBJECT-TYPE
        SYNTAX      SEQUENCE OF UtsPonIf2ExtStatEntry
        MAX-ACCESS  not-accessible
        STATUS      current
        DESCRIPTION
            "A list of UTStarcom's extension to the interface entries. The
             number of entries is given by the value of pon if index."
       ::= { utsEponPonStatsExt 6 }

   utsPonIf2ExtStatEntry OBJECT-TYPE
       SYNTAX       UtsPonIf2ExtStatEntry
       MAX-ACCESS   not-accessible
       STATUS       current
       DESCRIPTION
          "An entry containing additional management information
            applicable to a particular interface."
      INDEX { utsPonIf2ExtStatModule, utsPonIf2ExtStatDevice,
              utsPonIf2ExtStatPort,utsPonIf2ExtStatLogicalLinkId}
      ::= { utsPonIf2ExtStatTable 1 }


    UtsPonIf2ExtStatEntry ::=
        SEQUENCE {
            utsPonIf2ExtStatModule
                INTEGER,
            utsPonIf2ExtStatDevice
                INTEGER,
            utsPonIf2ExtStatPort
                INTEGER,
            utsPonIf2ExtStatLogicalLinkId
                INTEGER,

            utsPonIfExtSysFrameTxOk
                Counter64,
			utsPonIfExtSysFrameRxOk
			    Counter64,
            utsPonIfExtSysFrameTxErr
                Counter64,
			utsPonIfExtSysFrameRxErr
			    Counter64,
			utsPonIfExtSysFrameTxUnicast
			    Counter64,
            utsPonIfExtSysFrameRxUnicast
                Counter64,
			utsPonIfExtSysFrameTxMulticast
			    Counter64,
            utsPonIfExtSysFrameRxMulticast
                Counter64,
			utsPonIfExtSysFrameTxBroadcast
			    Counter64,
            utsPonIfExtSysFrameRxBroadcast
                Counter64,

			utsPonIfExtSysOctetTxOk
			    Counter64,
            utsPonIfExtSysOctetRxOk
                Counter64,

			utsPonIfExtPonFrameTxOk
			    Counter64,
            utsPonIfExtPonFrameRxOk
                Counter64,

			utsPonIfExtPonOctetTxOk
			    Counter64,
            utsPonIfExtPonOctetRxOk
                Counter64,

			utsPonIfExtEponFrameRxReport
			    Counter64,
            utsPonIfExtEponFrameTxReport
                Counter64,
			utsPonIfExtEponFrameRxGate
			    Counter64,
            utsPonIfExtEponFrameTxGate
                Counter64,
            utsPonIfExtEponFrameRxRegReq
                Counter64,
            utsPonIfExtEponFrameTxRegReq
                Counter64,
            utsPonIfExtEponFrameRxReg
                Counter64,
            utsPonIfExtEponFrameTxReg
                Counter64,
            utsPonIfExtEponFrameRxRegAck
                Counter64,
            utsPonIfExtEponFrameTxRegAck
                Counter64,
            utsPonIfExtEponFrameCrc8Error
                Counter64,
            utsPonIfExtEponFrameSldError
                Counter64,
            utsPonIfExtEponFrameRxPpsRate
                Counter64,
            utsPonIfExtEponFrameTxPpsRate
                Counter64,
            utsPonIfExtEponFrameRxbpsRate
                Counter64,
            utsPonIfExtEponFrameTxbpsRate
                Counter64,
            utsPonIfExtEponFrameRxBandwidthPercent
                INTEGER,
            utsPonIfExtEponFrameTxBandwidthPercent
                INTEGER,
            utsPonIfExtEponFrameRxPirRate
                Counter64,
            utsPonIfExtEponFrameTxPirRate
                Counter64,

            utsPonIfExtStatPMStatus
               INTEGER
       }

    utsPonIf2ExtStatModule OBJECT-TYPE
        SYNTAX      INTEGER
        MAX-ACCESS  not-accessible
        STATUS      current
        DESCRIPTION
           " Pon interface Module index"
       ::= { utsPonIf2ExtStatEntry 1 }

    utsPonIf2ExtStatDevice OBJECT-TYPE
        SYNTAX      INTEGER
        MAX-ACCESS  not-accessible
        STATUS      current
        DESCRIPTION
           " Pon interface device index"
       ::= { utsPonIf2ExtStatEntry 2 }

    utsPonIf2ExtStatPort OBJECT-TYPE
        SYNTAX      INTEGER
        MAX-ACCESS  not-accessible
        STATUS      current
        DESCRIPTION
           " Pon interface port index"
       ::= { utsPonIf2ExtStatEntry 3 }

    utsPonIf2ExtStatLogicalLinkId OBJECT-TYPE
        SYNTAX      INTEGER
        MAX-ACCESS  not-accessible
        STATUS      current
        DESCRIPTION
           " Pon interface logical port index"
       ::= { utsPonIf2ExtStatEntry 4 }

    utsPonIfExtSysFrameTxOk OBJECT-TYPE
        SYNTAX      Counter64
        MAX-ACCESS  read-only
        STATUS      current
        DESCRIPTION
           "OLT/ONU system frame Tx OK"
       ::= { utsPonIf2ExtStatEntry 5 }

    utsPonIfExtSysFrameRxOk OBJECT-TYPE
        SYNTAX      Counter64
        MAX-ACCESS  read-only
        STATUS      current
        DESCRIPTION
           "OLT/ONU System frame Rx OK"
       ::= { utsPonIf2ExtStatEntry 6 }

    utsPonIfExtSysFrameTxErr OBJECT-TYPE
        SYNTAX      Counter64
        MAX-ACCESS  read-only
        STATUS      current
        DESCRIPTION
           "OLT/ONU System frame Tx error"
       ::= { utsPonIf2ExtStatEntry 7 }

    utsPonIfExtSysFrameRxErr OBJECT-TYPE
        SYNTAX      Counter64
        MAX-ACCESS  read-only
        STATUS      current
        DESCRIPTION
           "OLT/ONU System frame Rx error"
       ::= { utsPonIf2ExtStatEntry 8 }

    utsPonIfExtSysFrameTxUnicast OBJECT-TYPE
        SYNTAX      Counter64
        MAX-ACCESS  read-only
        STATUS      current
        DESCRIPTION
           "OLT/ONU System frame Tx unicast"
       ::= { utsPonIf2ExtStatEntry 9 }

    utsPonIfExtSysFrameRxUnicast OBJECT-TYPE
        SYNTAX      Counter64
        MAX-ACCESS  read-only
        STATUS      current
        DESCRIPTION
           "OLT/ONU System frame Rx unicast"
       ::= { utsPonIf2ExtStatEntry 10 }

    utsPonIfExtSysFrameTxMulticast OBJECT-TYPE
        SYNTAX      Counter64
        MAX-ACCESS  read-only
        STATUS      current
        DESCRIPTION
           "OLT/ONU System frame Tx multicast"
       ::= { utsPonIf2ExtStatEntry 11 }

    utsPonIfExtSysFrameRxMulticast OBJECT-TYPE
        SYNTAX      Counter64
        MAX-ACCESS  read-only
        STATUS      current
        DESCRIPTION
           "OLT/ONU System frame Rx multicast"
       ::= { utsPonIf2ExtStatEntry 12 }

    utsPonIfExtSysFrameTxBroadcast OBJECT-TYPE
        SYNTAX      Counter64
        MAX-ACCESS  read-only
        STATUS      current
        DESCRIPTION
           "OLT/ONU System frame Tx broadcast"
       ::= { utsPonIf2ExtStatEntry 13 }

    utsPonIfExtSysFrameRxBroadcast OBJECT-TYPE
        SYNTAX      Counter64
        MAX-ACCESS  read-only
        STATUS      current
        DESCRIPTION
           "OLT/ONU System frame Rx broadcast"
       ::= { utsPonIf2ExtStatEntry 14 }

    utsPonIfExtSysOctetTxOk OBJECT-TYPE
        SYNTAX      Counter64
        MAX-ACCESS  read-only
        STATUS      current
        DESCRIPTION
           "OLT/ONU System octet Tx OK"
       ::= { utsPonIf2ExtStatEntry 30 }

    utsPonIfExtSysOctetRxOk OBJECT-TYPE
        SYNTAX      Counter64
        MAX-ACCESS  read-only
        STATUS      current
        DESCRIPTION
           "OLT/ONU System octet Rx OK"
       ::= { utsPonIf2ExtStatEntry 31 }

    utsPonIfExtPonFrameTxOk OBJECT-TYPE
        SYNTAX      Counter64
        MAX-ACCESS  read-only
        STATUS      current
        DESCRIPTION
           "OLT/ONU PON frame Tx OK"
       ::= { utsPonIf2ExtStatEntry 60 }

    utsPonIfExtPonFrameRxOk OBJECT-TYPE
        SYNTAX      Counter64
        MAX-ACCESS  read-only
        STATUS      current
        DESCRIPTION
           "OLT/ONU PON frame Rx OK"
       ::= { utsPonIf2ExtStatEntry 61 }

    utsPonIfExtPonOctetTxOk OBJECT-TYPE
        SYNTAX      Counter64
        MAX-ACCESS  read-only
        STATUS      current
        DESCRIPTION
           "OLT/ONU PON octet Tx OK"
       ::= { utsPonIf2ExtStatEntry 80 }

    utsPonIfExtPonOctetRxOk OBJECT-TYPE
        SYNTAX      Counter64
        MAX-ACCESS  read-only
        STATUS      current
        DESCRIPTION
           "OLT/ONU PON octet Rx OK"
       ::= { utsPonIf2ExtStatEntry 81 }


    utsPonIfExtEponFrameRxReport OBJECT-TYPE
        SYNTAX      Counter64
        MAX-ACCESS  read-only
        STATUS      current
        DESCRIPTION
           "OLT EPON frame Rx report"
       ::= { utsPonIf2ExtStatEntry 100 }

    utsPonIfExtEponFrameTxReport OBJECT-TYPE
        SYNTAX      Counter64
        MAX-ACCESS  read-only
        STATUS      current
        DESCRIPTION
           "ONU EPON frame Tx report"
       ::= { utsPonIf2ExtStatEntry 101 }


    utsPonIfExtEponFrameRxGate OBJECT-TYPE
        SYNTAX      Counter64
        MAX-ACCESS  read-only
        STATUS      current
        DESCRIPTION
           "ONU EPON frame Rx gate"
       ::= { utsPonIf2ExtStatEntry 102 }

    utsPonIfExtEponFrameTxGate OBJECT-TYPE
        SYNTAX      Counter64
        MAX-ACCESS  read-only
        STATUS      current
        DESCRIPTION
           "OLT EPON frame Tx gate"
       ::= { utsPonIf2ExtStatEntry 103 }

    utsPonIfExtEponFrameRxRegReq OBJECT-TYPE
        SYNTAX      Counter64
        MAX-ACCESS  read-only
        STATUS      current
        DESCRIPTION
           "OLT EPON frame Rx register request"
       ::= { utsPonIf2ExtStatEntry 104 }

    utsPonIfExtEponFrameTxRegReq OBJECT-TYPE
        SYNTAX      Counter64
        MAX-ACCESS  read-only
        STATUS      current
        DESCRIPTION
           "ONU EPON frame Tx register request"
       ::= { utsPonIf2ExtStatEntry 105 }

    utsPonIfExtEponFrameRxReg OBJECT-TYPE
        SYNTAX      Counter64
        MAX-ACCESS  read-only
        STATUS      current
        DESCRIPTION
           "ONU EPON frame Rx register"
       ::= { utsPonIf2ExtStatEntry 106 }

    utsPonIfExtEponFrameTxReg OBJECT-TYPE
        SYNTAX      Counter64
        MAX-ACCESS  read-only
        STATUS      current
        DESCRIPTION
           "OLT EPON frame Tx register"
       ::= { utsPonIf2ExtStatEntry 107 }

    utsPonIfExtEponFrameRxRegAck OBJECT-TYPE
        SYNTAX      Counter64
        MAX-ACCESS  read-only
        STATUS      current
        DESCRIPTION
           "OLT EPON frame Rx register acknowledge"
       ::= { utsPonIf2ExtStatEntry 108 }

    utsPonIfExtEponFrameTxRegAck OBJECT-TYPE
        SYNTAX      Counter64
        MAX-ACCESS  read-only
        STATUS      current
        DESCRIPTION
           "ONU EPON frame Tx register acknowledge"
       ::= { utsPonIf2ExtStatEntry 109 }

    utsPonIfExtEponFrameCrc8Error OBJECT-TYPE
        SYNTAX      Counter64
        MAX-ACCESS  read-only
        STATUS      current
        DESCRIPTION
           "ONU/OLT EPON frame CRC8 error"
       ::= { utsPonIf2ExtStatEntry 110 }

    utsPonIfExtEponFrameSldError OBJECT-TYPE
        SYNTAX      Counter64
        MAX-ACCESS  read-only
        STATUS      current
        DESCRIPTION
           "ONU EPON frame CRC8 error"
       ::= { utsPonIf2ExtStatEntry 111 }

   utsPonIfExtEponFrameRxPpsRate OBJECT-TYPE
        SYNTAX      Counter64
        MAX-ACCESS  read-only
        STATUS      current
        DESCRIPTION
           "ONU EPON frame Rx PPS Rate."
       ::= { utsPonIf2ExtStatEntry 121 }

   utsPonIfExtEponFrameTxPpsRate OBJECT-TYPE
        SYNTAX      Counter64
        MAX-ACCESS  read-only
        STATUS      current
        DESCRIPTION
           "ONU EPON frame Tx PPS Rate."
       ::= { utsPonIf2ExtStatEntry 122 }

   utsPonIfExtEponFrameRxbpsRate OBJECT-TYPE
        SYNTAX      Counter64
        MAX-ACCESS  read-only
        STATUS      current
        DESCRIPTION
           "ONU EPON frame Rx bps Rate, the unit is kbps."
       ::= { utsPonIf2ExtStatEntry 123 }

   utsPonIfExtEponFrameTxbpsRate OBJECT-TYPE
        SYNTAX      Counter64
        MAX-ACCESS  read-only
        STATUS      current
        DESCRIPTION
           "ONU EPON frame Tx bps Rate, the unit is kbps."
       ::= { utsPonIf2ExtStatEntry 124 }

   utsPonIfExtEponFrameRxBandwidthPercent OBJECT-TYPE
        SYNTAX      INTEGER
        MAX-ACCESS  read-only
        STATUS      current
        DESCRIPTION
           "ONU EPON frame Rx bandwidth percent, the unit is 1/1000."
       ::= { utsPonIf2ExtStatEntry 125 }

   utsPonIfExtEponFrameTxBandwidthPercent OBJECT-TYPE
        SYNTAX      INTEGER
        MAX-ACCESS  read-only
        STATUS      current
        DESCRIPTION
           "ONU EPON frame Tx bandwidth percent, the unit is 1/1000."
       ::= { utsPonIf2ExtStatEntry 126 }

   utsPonIfExtEponFrameRxPirRate OBJECT-TYPE
        SYNTAX      Counter64
        MAX-ACCESS  read-only
        STATUS      current
        DESCRIPTION
           "ONU EPON frame Rx Pir bps Rate, the unit is kbps."
       ::= { utsPonIf2ExtStatEntry 127 }

   utsPonIfExtEponFrameTxPirRate OBJECT-TYPE
        SYNTAX      Counter64
        MAX-ACCESS  read-only
        STATUS      current
        DESCRIPTION
           "ONU EPON frame Tx Pir bps Rate, the unit is kbps."
       ::= { utsPonIf2ExtStatEntry 128 }



    utsPonIfExtStatPMStatus OBJECT-TYPE
		SYNTAX      INTEGER
				    {
				       enable(1),
				       disable(2)
				    }
		MAX-ACCESS  read-write
		STATUS      current
		DESCRIPTION
		    "Enable or disable the PON interface TFTP performance management."
       ::= { utsPonIf2ExtStatEntry 200 }

------
------
------


------
------  Layer3 extension
------

utsLayer3StatsExtObjects OBJECT IDENTIFIER ::= { utsLayer3PerfExt 1 }

--
--  ip DHCP server statistics table's extension
--


	utsIpDhcpServerStatsGroup OBJECT IDENTIFIER ::= { utsLayer3StatsExtObjects 1 }

    utsIpDhcpServerStatsFreeBindings OBJECT-TYPE
        SYNTAX      INTEGER
        MAX-ACCESS  read-only
        STATUS      current

        DESCRIPTION
            "Dhcp server statistics free bindings"
        ::= { utsIpDhcpServerStatsGroup 1 }


    utsIpDhcpServerStatsAutoBindings OBJECT-TYPE
        SYNTAX      INTEGER
        MAX-ACCESS  read-only
        STATUS      current

        DESCRIPTION
            "Dhcp server statistics auto bindings"
        ::= { utsIpDhcpServerStatsGroup 2 }



    utsIpDhcpServerStatsExpiredBindings OBJECT-TYPE
        SYNTAX      INTEGER
        MAX-ACCESS  read-only
        STATUS      current

        DESCRIPTION
            "Dhcp server statistics expired bindings"
        ::= { utsIpDhcpServerStatsGroup 3 }


    utsIpDhcpServerStatsOfferBindings OBJECT-TYPE
        SYNTAX      INTEGER
        MAX-ACCESS  read-only
        STATUS      current

        DESCRIPTION
            "Dhcp server statistics offer bindings"
        ::= { utsIpDhcpServerStatsGroup 4 }


    utsIpDhcpServerStatsManualFree OBJECT-TYPE
        SYNTAX      INTEGER
        MAX-ACCESS  read-only
        STATUS      current

        DESCRIPTION
            "Dhcp server statistics manual free"
        ::= { utsIpDhcpServerStatsGroup 5 }


    utsIpDhcpServerStatsManualBindings OBJECT-TYPE
        SYNTAX      INTEGER
        MAX-ACCESS  read-only
        STATUS      current

        DESCRIPTION
            "Dhcp server statistics manual bindings"
        ::= { utsIpDhcpServerStatsGroup 6 }


    utsIpDhcpServerStatsManualExpired OBJECT-TYPE
        SYNTAX      INTEGER
        MAX-ACCESS  read-only
        STATUS      current

        DESCRIPTION
            "Dhcp server statistics manual expired"
        ::= { utsIpDhcpServerStatsGroup 7 }


    utsIpDhcpServerStatsManualOffer OBJECT-TYPE
        SYNTAX      INTEGER
        MAX-ACCESS  read-only
        STATUS      current

        DESCRIPTION
            "Dhcp server statistics manual offer"
        ::= { utsIpDhcpServerStatsGroup 8 }



    utsIpDhcpServerStatsDiscoverPackets OBJECT-TYPE
        SYNTAX      INTEGER
        MAX-ACCESS  read-only
        STATUS      current

        DESCRIPTION
            "Dhcp server statistics discover packets"
        ::= { utsIpDhcpServerStatsGroup 9 }


    utsIpDhcpServerStatsRequestPackets OBJECT-TYPE
        SYNTAX      INTEGER
        MAX-ACCESS  read-only
        STATUS      current

        DESCRIPTION
            "Dhcp server statistics request packets"
        ::= { utsIpDhcpServerStatsGroup 10 }


    utsIpDhcpServerStatsReleasePackets OBJECT-TYPE
        SYNTAX      INTEGER
        MAX-ACCESS  read-only
        STATUS      current

        DESCRIPTION
            "Dhcp server statistics release packets"
        ::= { utsIpDhcpServerStatsGroup 11 }


    utsIpDhcpServerStatsDeclinePackets OBJECT-TYPE
        SYNTAX      INTEGER
        MAX-ACCESS  read-only
        STATUS      current

        DESCRIPTION
            "Dhcp server statistics decline packets"
        ::= { utsIpDhcpServerStatsGroup 12 }

    utsIpDhcpServerStatsInformPackets OBJECT-TYPE
        SYNTAX      INTEGER
        MAX-ACCESS  read-only
        STATUS      current

        DESCRIPTION
            "Dhcp server statistics inform packets"
        ::= { utsIpDhcpServerStatsGroup 13 }



    utsIpDhcpServerStatsinvalidPackets OBJECT-TYPE
        SYNTAX      INTEGER
        MAX-ACCESS  read-only
        STATUS      current

        DESCRIPTION
            "Dhcp server statistics invalid packets"
        ::= { utsIpDhcpServerStatsGroup 14 }



    utsIpDhcpServerStatsOfferPackets OBJECT-TYPE
        SYNTAX      INTEGER
        MAX-ACCESS  read-only
        STATUS      current

        DESCRIPTION
            "Dhcp server statistics offer packets"
        ::= { utsIpDhcpServerStatsGroup 15 }


    utsIpDhcpServerStatsAckPackets OBJECT-TYPE
        SYNTAX      INTEGER
        MAX-ACCESS  read-only
        STATUS      current

        DESCRIPTION
            "Dhcp server statistics ack packets"
        ::= { utsIpDhcpServerStatsGroup 16 }



    utsIpDhcpServerStatsNakPackets OBJECT-TYPE
        SYNTAX      INTEGER
        MAX-ACCESS  read-only
        STATUS      current

        DESCRIPTION
            "Dhcp server statistics nak packets"
        ::= { utsIpDhcpServerStatsGroup 17 }



    utsIpDhcpServerStatsReplyPackets OBJECT-TYPE
        SYNTAX      INTEGER
        MAX-ACCESS  read-only
        STATUS      current

        DESCRIPTION
            "Dhcp server statistics reply packets"
        ::= { utsIpDhcpServerStatsGroup 18 }

END
