-- *****************************************************************************
-- Filename:        epon-security.mib
-- Description:     Contains iSwitch MIB Extension.
-- MIB Version:     1.00
--
-- Copyright (C) 2001 by UTStarcom, Inc. All rights reserved.
-- Reproduction of this document is authorized on the condition that
-- the foregoing copyright notice is included.
--
-- NOTE:  The contents of this document are subject to change without notice
-- *****************************************************************************

-- *****************************************************************************
-- Version:        $Id:  $
-- Last Modified:  $DateTime:  $
-- Change List #:  $Change:  $
-- *****************************************************************************

UTEPON4000SECURITY-MIB DEFINITIONS ::= BEGIN

    IMPORTS
        MODULE-IDENTITY, OBJECT-TYPE, IpAddress FROM SNMPv2-SMI
        Counter, TimeTicks			FROM RFC1155-SMI
        RowStatus, TruthValue                   FROM SNMPv2-TC
        ifIndex, DisplayString                  FROM RFC1213-MIB
        MacAddress, BridgeId, Timeout           FROM BRIDGE-MIB
        utsGeponBBS4000                         FROM UTS-BBS-COMMON-MIB;


   utsGeponBBS4000Security  MODULE-IDENTITY
        LAST-UPDATED "9407272253Z"      -- Wed Jul 27 22:53:04 PDT 1994
        ORGANIZATION "UTSTARcom Inc"
        CONTACT-INFO
            "Postal: UTSTARcom Inc
             Alameda, California 9xxxx
             Tel:    +1 510 555 1212
             E-Mail: mibs@utstar.com "
      DESCRIPTION
         "Contains UT EPON MIB Extensions."
     ::= { utsGeponBBS4000 5   }



utsEfmPonSecurityExt     OBJECT IDENTIFIER ::= { utsGeponBBS4000Security 1 }
utsEponSecExtObjects     OBJECT IDENTIFIER ::= { utsEfmPonSecurityExt 1 }


------
------ 1. Security
------


utsDot3SecurityMIB OBJECT IDENTIFIER ::= { utsEponSecExtObjects 1 }

utsDot3SecurityObjects OBJECT IDENTIFIER ::= { utsDot3SecurityMIB 1 }

utsDot3SecurityOltObjects OBJECT IDENTIFIER ::= { utsDot3SecurityObjects 1 }

END
