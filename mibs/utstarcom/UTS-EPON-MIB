-- *****************************************************************************
-- Filename:        uts-epon.mib
-- Description:     Contains iSwitch node registrations
-- MIB Version:     1.00
--
-- Copyright (C) 2001 by UTStarcom, Inc. All rights reserved.
-- Reproduction of this document is authorized on the condition that
-- the foregoing copyright notice is included.
--
-- NOTE:  The contents of this document are subject to change without notice
-- *****************************************************************************

-- *****************************************************************************
-- Version:        $Id:  $
-- Last Modified:  $DateTime:  $
-- Change List #:  $Change:  $
-- *****************************************************************************

UTS-EPON-MIB DEFINITIONS ::= BEGIN

   IMPORTS
       MODULE-IDENTITY                 FROM SNMPv2-SMI
       wacos                           FROM WACOS-GW-ROOT-MIB;

   uts-epon  MODULE-IDENTITY
           LAST-UPDATED "9407272253Z"      -- Wed Jul 27 22:53:04 PDT 1994
           ORGANIZATION "UTSTARcom Inc"
           CONTACT-INFO
          "       Postal: UTSTARcom Inc
                  Alameda, California 9xxxx
          Tel:    +1 510 555 1212
          E-Mail: mibs@utstar.com "
      DESCRIPTION
         "Contains iSwitch MIB Extensions."
     ::= { wacos 1800}
--
--  epon node registrations
--


utAccounting        OBJECT IDENTIFIER ::= { uts-epon 1 }
utConfigure      OBJECT IDENTIFIER ::= { uts-epon 2 }
utFault          OBJECT IDENTIFIER ::= { uts-epon 3 }
utPerformance    OBJECT IDENTIFIER ::= { uts-epon 4 }
utSecurity       OBJECT IDENTIFIER ::= { uts-epon 5 }




END
