UTSTARCOM-ROOT-MIB DEFINITIONS ::= BEGIN
	IMPORTS
		MODULE-IDENTITY, enterprises FROM SNMPv2-SMI;

utstarcom MODULE-IDENTITY
	LAST-UPDATED      "200509011621Z"
	ORGANIZATION      "UTStarcom, Inc."
	CONTACT-INFO      " "
	DESCRIPTION       "	"
    REVISION      "200509011621Z"
    DESCRIPTION    "Initial version"

::= { enterprises 1949 }

utsRoot 						OBJECT IDENTIFIER ::= { utstarcom 1 }
utsProducts						OBJECT IDENTIFIER ::= { utsRoot 3 }
utsBroadbandSwitch 				OBJECT IDENTIFIER ::= { utsProducts 10 }
utsBBSProductSysId				OBJECT IDENTIFIER ::= { utsBroadbandSwitch 2 }
utBBSEponOnuSysId   			OBJECT IDENTIFIER ::= { utsBBSProductSysId 100 }

utBBSEponOnuSysId2004   OBJECT-IDENTITY
	STATUS          current
	DESCRIPTION
		"gepon onu 2004 system objet ID"
	::= { utBBSEponOnuSysId 6 }

utBBSGeponOnu	OBJECT-IDENTITY
	STATUS     current
	DESCRIPTION
		"the root of gepon onu manangement information base"
	::= { utsBroadbandSwitch 100}

utBBSGeponOnu2004  OBJECT-IDENTITY
	STATUS     current
	DESCRIPTION
		"the root of gepon onu 2004 manangement information base"
	::= { utBBSGeponOnu 6}

utBBSGeponOnu404 	OBJECT-IDENTITY
	STATUS     current
	DESCRIPTION
		"the root of gepon onu 404 manangement information base"
	::= { utBBSGeponOnu 7}


END
