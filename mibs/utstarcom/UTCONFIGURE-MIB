-- *****************************************************************************
-- Filename:        epon-utConfigure.mib
-- Description:     Contains iSwitch MIB Extension.
-- MIB Version:     1.00
--
-- Copyright (C) 2001 by UTStarcom, Inc. All rights reserved.
-- Reproduction of this document is authorized on the condition that
-- the foregoing copyright notice is included.
--
-- NOTE:  The contents of this document are subject to change without notice
-- *****************************************************************************

-- *****************************************************************************
-- Version:        $Id:  $
-- Last Modified:  $DateTime:  $
-- Change List #:  $Change:  $
-- *****************************************************************************

UTCONFIGURE-MIB DEFINITIONS ::= BEGIN

    IMPORTS
        MODULE-IDENTITY, OBJECT-TYPE, IpAddress FROM SNMPv2-SMI

        Counter, TimeTicks		FROM RFC1155-SMI
        RowStatus, TruthValue,
        TEXTUAL-CONVENTION              FROM SNMPv2-TC
        InterfaceIndex			FROM IF-MIB
        ifIndex					FROM IF-MIB
        InterfaceIndexOrZero    FROM IF-MIB
        DisplayString          		FROM SNMPv2-TC
        PhysAddress				FROM SNMPv2-TC
        MacAddress                      FROM BRIDGE-MIB
        BridgeId				FROM BRIDGE-MIB
        Timeout					FROM BRIDGE-MIB
        uts-epon                        FROM UTS-EPON-MIB;
--        utsGeponBBS1000plus                   FROM UTS-BBS-COMMON-MIB;

   utConfigure  MODULE-IDENTITY
        LAST-UPDATED "9407272253Z"      -- Wed Jul 27 22:53:04 PDT 1994
        ORGANIZATION "UTSTARcom Inc"
        CONTACT-INFO
            "Postal: UTSTARcom Inc
             Alameda, California 9xxxx
             Tel:    +1 510 555 1212
             E-Mail: mibs@utstar.com "
      DESCRIPTION
         "Contains UT EPON MIB Extensions."
     ::= { uts-epon 2   }


    UtsSyslogServerityLevelType ::= TEXTUAL-CONVENTION
        STATUS  current
        DESCRIPTION
            "The Syslog serverity types used by UT's BBS1000
             SyslogServerTable."
        SYNTAX  INTEGER {
			emergencies(1),
			alerts(2),
			critical(3),
			errors(4),
			warnings(5),
			notifications(6),
			informational(7),
			debugging(8)
			--,disabled(9)
        }

    UtsConfStationIdType ::= TEXTUAL-CONVENTION
        STATUS    current
        DESCRIPTION
            "The station Id to identify the issued configuration command"
        SYNTAX DisplayString(SIZE(0..16))

    UtsConfStatusType ::= TEXTUAL-CONVENTION
        STATUS    current
        DESCRIPTION
            "Confiuration/Test command result."
        SYNTAX INTEGER
        {
            success(1),
            failure(2),
            busy(3)
        }

--
--  epon objects extersion
--

utsSystemConfExt     OBJECT IDENTIFIER ::= { utConfigure 1 }

utsEthIfConfExt     OBJECT IDENTIFIER ::= { utConfigure 2 }

utsEfmPonConfExt     OBJECT IDENTIFIER ::= { utConfigure 3 }

utsServiceConfExt   OBJECT IDENTIFIER ::= { utConfigure 4 }

utsDiagnosisConfExt  OBJECT IDENTIFIER ::= { utConfigure 5 }

--
--  epon system and module extension
--

utsSystemExtObjects OBJECT IDENTIFIER ::= { utsSystemConfExt 1 }

eponOamInitAlm  OBJECT IDENTIFIER ::= { utsSystemConfExt 2 }


--
-- epon module table
--


--
--  epon board info
--
   utsEponModuleBoardTable  OBJECT-TYPE
        SYNTAX      SEQUENCE OF UtsEponModuleBoardEntry
        MAX-ACCESS  not-accessible
        STATUS      current
        DESCRIPTION
            "A list of board information in a EPON box."
       ::= { utsSystemExtObjects 1 }


   utsEponModuleBoardEntry OBJECT-TYPE
       SYNTAX       UtsEponModuleBoardEntry
       MAX-ACCESS   not-accessible
       STATUS       current
       DESCRIPTION
          "An entry contains board information on a module."
      INDEX { utsEponModuleBoardPhyId }
      ::= { utsEponModuleBoardTable 1 }


    UtsEponModuleBoardEntry ::=
        SEQUENCE {
            utsEponModuleBoardPhyId
                INTEGER,
            utsEponModuleBoardType
                INTEGER,
            utsEponModuleBoardState
                INTEGER,
            utsEponModuleBoardSwVer
                DisplayString,
            utsEponModuleBoardBootromVer
                DisplayString,
            utsEponModuleBoardVer
                DisplayString,
            utsEponModuleBoardAction
                INTEGER
        }


    utsEponModuleBoardPhyId OBJECT-TYPE
        SYNTAX      INTEGER
        MAX-ACCESS  read-only
        STATUS      current
        DESCRIPTION
           "The physical module number"
       ::= { utsEponModuleBoardEntry 1 }

    utsEponModuleBoardType OBJECT-TYPE
        SYNTAX      INTEGER
        {
            other(1),
            gsm(2),
            epm04a(3),
            epm04b(4),
            ltm(20),
            ltm6(21)
        }
        MAX-ACCESS  read-only
        STATUS      current
        DESCRIPTION
           "The line card type. In EPON, BCM, OLT are supported"
       ::= { utsEponModuleBoardEntry 2 }

    utsEponModuleBoardState OBJECT-TYPE
        SYNTAX      INTEGER
        {
            unknown(1),
            init(2),
            active(3),
            offline(4)
         }
        MAX-ACCESS  read-only
        STATUS      current
        DESCRIPTION
           "The internal state of line card"
       ::= { utsEponModuleBoardEntry 3 }

    utsEponModuleBoardSwVer OBJECT-TYPE
        SYNTAX      DisplayString(SIZE(0..63))
        MAX-ACCESS  read-only
        STATUS      current
        DESCRIPTION
           "Software version of the board. The software verion is applicable
           to the whole box and therefore belongs to the GSM board.  For LTM
           boards, the this object returns 'None'."
       ::= { utsEponModuleBoardEntry 7 }

    utsEponModuleBoardBootromVer OBJECT-TYPE
        SYNTAX      DisplayString(SIZE(0..63))
        MAX-ACCESS  read-only
        STATUS      current
        DESCRIPTION
           "The Bootrom version of the board. The Bootrom verion is
           applicable to the whole box and therefore belongs to the GSM board.
           For LTM boards, the this object returns 'None'."
       ::= { utsEponModuleBoardEntry 9 }

    utsEponModuleBoardVer OBJECT-TYPE
        SYNTAX      DisplayString(SIZE(0..63))
        MAX-ACCESS  read-only
        STATUS      current
        DESCRIPTION
           "The Olt Firmware revision for the LTM board.  Each of the
           two LTM boards has a copy of the firmware running therefore both
           will show a firmware version.  For now, however, the two are always
           the same.  For GSM boards, the this object returns 'None'."
       ::= { utsEponModuleBoardEntry 10 }

    utsEponModuleBoardAction OBJECT-TYPE
	   SYNTAX INTEGER
       {
            normal(0), -- read only for normal status
       	    reset(1)   -- write-only
       }
	   MAX-ACCESS   read-write
	   STATUS       current
	   DESCRIPTION
	     "Reset PON module."
	   ::= { utsEponModuleBoardEntry 11}

--
--  PON system group
--
   utsPonSystemGroup OBJECT IDENTIFIER ::= { utsSystemExtObjects 2 }

   utsPonSysVlanIdBase OBJECT-TYPE
		SYNTAX  INTEGER (2..4094)
		MAX-ACCESS  read-write
		STATUS  current
		DESCRIPTION
			"Pon system vlan id base for sla."
        ::= { utsPonSystemGroup 1 }

   utsPonSysLocalAuthentication OBJECT-TYPE
		SYNTAX  INTEGER
		{
				enabled(1),
				disabled(2)
		}
		MAX-ACCESS  read-write
		STATUS  current
		DESCRIPTION
			"Pon system local sla authentication."
        ::= { utsPonSystemGroup 2 }

   utsPonSysLogicalPortStrictBinging OBJECT-TYPE
		SYNTAX  INTEGER
		{
				enabled(1),
				disabled(2)
		}
		MAX-ACCESS  read-write
		STATUS  current
		DESCRIPTION
			"Pon system local logical port strict binding."
        ::= { utsPonSystemGroup 3 }

   utsPonSysSlaSynchronization OBJECT-TYPE
		SYNTAX  INTEGER
		{
				enabled(1),
				disabled(2)
		}
		MAX-ACCESS  read-write
		STATUS  current
		DESCRIPTION
			"Pon system local sla sync with radius server authentication."
        ::= { utsPonSystemGroup 4 }

   utsPonSysOltMACAgingTime OBJECT-TYPE
       SYNTAX       INTEGER (0..2400)
	   MAX-ACCESS   read-write
	   STATUS       current
	   DESCRIPTION
	        "Pon System OLT MAC address aging time, 0 means disable."
	   ::= { utsPonSystemGroup 5 }

   utsPonSysOnuAuthTimeOut OBJECT-TYPE
       SYNTAX       INTEGER (1..6000)
	   MAX-ACCESS   read-write
	   STATUS       current
	   DESCRIPTION
	        "Pon System remote management onu authentication time out value, range <1..6000> - seconds, default: 15(sec)."
	   ::= { utsPonSystemGroup 6 }

   utsPonSysOlpMode OBJECT-TYPE
       SYNTAX       INTEGER
       {
        enable(1),
        disable(2)
       }
	   MAX-ACCESS   read-write
	   STATUS       current
	   DESCRIPTION
	        "Pon System optical line protection mode."
	   ::= { utsPonSystemGroup 7 }

   utsPonSysDot1adTPID OBJECT-TYPE
       SYNTAX       INTEGER -- 0x8100 by default
	   MAX-ACCESS   read-write
	   STATUS       current
	   DESCRIPTION
	        "OLT PON TPID configuation"
	   ::= { utsPonSystemGroup 8 }

   utsPonSysReceiveSensitivityMax OBJECT-TYPE
       SYNTAX       INTEGER
	   MAX-ACCESS   read-write
	   STATUS       current
	   DESCRIPTION
	        "The Receive Sensitivity(Max), the standard(default value) is -27dBm."
	   ::= { utsPonSystemGroup 9 }

   utsPonSysOverloadOpticalPower OBJECT-TYPE
       SYNTAX       INTEGER
	   MAX-ACCESS   read-write
	   STATUS       current
	   DESCRIPTION
	        "The Over load optical power(Max), the standard(default value) is +4dBm."
	   ::= { utsPonSystemGroup 10 }

--
--  Syslog configuration extension
--

   utsSyslogExt OBJECT IDENTIFIER ::= { utsSystemExtObjects 3 }

   utsSyslogGroup OBJECT IDENTIFIER ::= { utsSyslogExt 1 }

   utsSyslogFormat OBJECT-TYPE
		SYNTAX  INTEGER
		{
			non-rfc3164(1),
			rfc3164(2)
		}
		MAX-ACCESS  read-write
		STATUS  current
		DESCRIPTION
			"Syslog format cisco-like or rfc3164."
        ::= { utsSyslogGroup 1 }

   utsSyslogConsoleSeverity OBJECT-TYPE
      SYNTAX  UtsSyslogServerityLevelType
		MAX-ACCESS  read-write
		STATUS  current
		DESCRIPTION
			"Syslog console severity level."
        ::= { utsSyslogGroup 2 }


   utsSyslogFlashSeverity OBJECT-TYPE
		SYNTAX  UtsSyslogServerityLevelType
		MAX-ACCESS  read-write
		STATUS  current
		DESCRIPTION
			"Syslog flash severity level."
        ::= { utsSyslogGroup 3 }

--   utsSyslogFlashModule OBJECT-TYPE
--		SYNTAX       INTEGER
--		{
--		     alarm(1),
--		     event(2),
--		     others(3)
--		}
--		MAX-ACCESS  read-write
--		STATUS  current
--		DESCRIPTION
--		" Syslog flash module selection.
--			alarm(1) will select logging the alarm message to flash;
--			even(2) will select logging the even message to flash;
--			others(3)will select logging the other syslog message to flash;
--		"
--        ::= { utsSyslogGroup 4 }

------
------     syslog server table
------


    utsSyslogServerTable  OBJECT-TYPE
        SYNTAX      SEQUENCE OF UtsSyslogServerEntry
        MAX-ACCESS  not-accessible
        STATUS      current
        DESCRIPTION
            "A list of syslog server information entries."
        ::= { utsSyslogExt  2 }

    utsSyslogServerEntry OBJECT-TYPE
        SYNTAX       UtsSyslogServerEntry
        MAX-ACCESS   not-accessible
        STATUS       current
        DESCRIPTION
            "An entry contains syslog server information."
        INDEX { utsSyslogServerId }
        ::= { utsSyslogServerTable 1 }

    UtsSyslogServerEntry ::=
        SEQUENCE {
            utsSyslogServerId               INTEGER,
            utsSyslogServerIpAddress        IpAddress,
            utsSyslogServerPort             INTEGER,
            utsSyslogServerFacilityAuth     UtsSyslogServerityLevelType,
            utsSyslogServerFacilityDhcp     UtsSyslogServerityLevelType,
            utsSyslogServerFacilityEthernet UtsSyslogServerityLevelType,
            utsSyslogServerFacilityPon      UtsSyslogServerityLevelType,
            utsSyslogServerFacilitySnmp     UtsSyslogServerityLevelType,
            utsSyslogServerFacilitySys      UtsSyslogServerityLevelType,
            utsSyslogServerFacilitySyslog   UtsSyslogServerityLevelType,
            utsSyslogServerFacilityUser     UtsSyslogServerityLevelType
        }

    utsSyslogServerId OBJECT-TYPE
        SYNTAX      INTEGER
        MAX-ACCESS  read-only
        STATUS      current
        DESCRIPTION
            "The index of syslog server's table."
        ::= { utsSyslogServerEntry 1 }

    utsSyslogServerIpAddress OBJECT-TYPE
        SYNTAX      IpAddress
        MAX-ACCESS  read-write
        STATUS      current
        DESCRIPTION
            "Syslog server host's ip address"
        ::= { utsSyslogServerEntry 2 }

    utsSyslogServerPort OBJECT-TYPE
        SYNTAX      INTEGER (1..65535)
        MAX-ACCESS  read-write
        STATUS      current
        DESCRIPTION
            "Syslog server host's port number"
        ::= { utsSyslogServerEntry 3 }

    utsSyslogServerFacilityAuth OBJECT-TYPE
        SYNTAX      UtsSyslogServerityLevelType
        MAX-ACCESS  read-write
        STATUS      current
        DESCRIPTION
            "Syslog server auth facility serverity level."
        DEFVAL { informational }
        ::= { utsSyslogServerEntry 4 }

    utsSyslogServerFacilityDhcp OBJECT-TYPE
        SYNTAX      UtsSyslogServerityLevelType
        MAX-ACCESS  read-write
        STATUS      current
        DESCRIPTION
            "Syslog server dhcp facility serverity level."
        DEFVAL { informational }
        ::= { utsSyslogServerEntry 5 }

    utsSyslogServerFacilityEthernet OBJECT-TYPE
        SYNTAX      UtsSyslogServerityLevelType
        MAX-ACCESS  read-write
        STATUS      current
        DESCRIPTION
            "Syslog server ethernet facility serverity level."
        DEFVAL { informational }
        ::= { utsSyslogServerEntry 6 }

    utsSyslogServerFacilityPon OBJECT-TYPE
        SYNTAX      UtsSyslogServerityLevelType
        MAX-ACCESS  read-write
        STATUS      current
        DESCRIPTION
            "Syslog server pon facility serverity level."
        DEFVAL { informational }
        ::= { utsSyslogServerEntry 7 }

    utsSyslogServerFacilitySnmp OBJECT-TYPE
        SYNTAX      UtsSyslogServerityLevelType
        MAX-ACCESS  read-write
        STATUS      current
        DESCRIPTION
            "Syslog server snmp facility serverity level."
        DEFVAL { informational }
        ::= { utsSyslogServerEntry 8 }

    utsSyslogServerFacilitySys OBJECT-TYPE
        SYNTAX      UtsSyslogServerityLevelType
        MAX-ACCESS  read-write
        STATUS      current
        DESCRIPTION
            "Syslog server sys facility serverity level."
        DEFVAL { informational }
        ::= { utsSyslogServerEntry 9 }

    utsSyslogServerFacilitySyslog OBJECT-TYPE
        SYNTAX      UtsSyslogServerityLevelType
        MAX-ACCESS  read-write
        STATUS      current
        DESCRIPTION
            "Syslog server syslog facility serverity level."
        DEFVAL { informational }
        ::= { utsSyslogServerEntry 10 }

    utsSyslogServerFacilityUser OBJECT-TYPE
        SYNTAX      UtsSyslogServerityLevelType
        MAX-ACCESS  read-write
        STATUS      current
        DESCRIPTION
            "Syslog server user facility serverity level."
        DEFVAL { informational }
        ::= { utsSyslogServerEntry 11 }


--
--  epon configuration management system group
--

utsManagementConfExt OBJECT IDENTIFIER ::= { utsSystemExtObjects 4 }

utsSystemConfGroup OBJECT IDENTIFIER ::= { utsManagementConfExt 1 }

utsFTPConfGroup OBJECT IDENTIFIER ::= { utsManagementConfExt 2 }

utsFileSystemGroup OBJECT IDENTIFIER ::= { utsManagementConfExt 3 }

utsChassisConfGroup OBJECT IDENTIFIER ::= { utsManagementConfExt 4 }

utsTFTPConfGroup OBJECT IDENTIFIER ::= { utsManagementConfExt 5 }

utsLedMgmtConfExt OBJECT IDENTIFIER ::= { utsManagementConfExt 6 }

utsSNMPConfExt OBJECT IDENTIFIER ::= { utsManagementConfExt 7 }

--
--  BBS1000+ SNMP management mib definition
--

utsSNMPConfObjects OBJECT IDENTIFIER ::= { utsSNMPConfExt 1 }

--
--  system community table
--
    utsSysCommunityTable  OBJECT-TYPE
        SYNTAX      SEQUENCE OF UtsSysCommunityEntry
        MAX-ACCESS  not-accessible
        STATUS      current
        DESCRIPTION
            "The community table (4 entries).  This table lists
		 	community strings and the access levels."

       ::= { utsSNMPConfObjects 1 }

   utsSysCommunityEntry OBJECT-TYPE
       SYNTAX       UtsSysCommunityEntry
       MAX-ACCESS   not-accessible
       STATUS       current
       DESCRIPTION
          "System community table entry."
       INDEX { utsSysCommunityIndex }
       ::= { utsSysCommunityTable 1 }

   UtsSysCommunityEntry ::=
       SEQUENCE {
	    utsSysCommunityIndex
	     INTEGER,
--	    utsSysCommunityEnable
--	     INTEGER,
	    utsSysCommunityString
	     OCTET STRING,
	    utsSysCommunityAccess
	     INTEGER,
	    utsSysCommunityRowStatus
	     RowStatus
       }

  utsSysCommunityIndex OBJECT-TYPE
   SYNTAX INTEGER (1..4)
   MAX-ACCESS not-accessible
   STATUS current
   DESCRIPTION
    "The index of community in the table.
    "
   ::= { utsSysCommunityEntry 1 }

  utsSysCommunityString OBJECT-TYPE
   SYNTAX OCTET STRING
   MAX-ACCESS read-create
   STATUS current
   DESCRIPTION
    "Configurable community string with access rights
      defined by the value of utsSysCommunityAccess.
    "
   ::= { utsSysCommunityEntry 3 }

  utsSysCommunityAccess OBJECT-TYPE
		   SYNTAX INTEGER
		    {
    	      readOnly(1),
		      readWrite(2)
		    }
		   MAX-ACCESS read-create
		   STATUS current
		   DESCRIPTION
		    " A value of
		      readWrite(2) allows the community to read and write
		      all objects except restricted items such as
		      community strings, which cannot be accessed at all.
		      A value of readOnly(1) allows the community to read
		      all objects except restricted items.
		    "
		   ::= { utsSysCommunityEntry 4 }

   utsSysCommunityRowStatus OBJECT-TYPE
			SYNTAX RowStatus
			MAX-ACCESS read-create
			STATUS current
			DESCRIPTION
				"Row status"
			::= { utsSysCommunityEntry 5 }

--
-- BBS1000+ LED state display mib definition
--

utsLedGlobalLedDispGroup OBJECT IDENTIFIER ::= { utsLedMgmtConfExt 1 }

--
-- BBS1000+ chassis LED state display mib group
--

   utsBBSLEDSysPowerLedState OBJECT-TYPE
        SYNTAX INTEGER
        {
            turn-on(1),    -- led on.
            turn-off(2)    -- led off.
        }
        MAX-ACCESS read-only
        STATUS  current
        DESCRIPTION
            "bbs LED state display: system power LED."
        ::= { utsLedGlobalLedDispGroup 1 }

   utsBBSLEDSystemLedState OBJECT-TYPE
        SYNTAX INTEGER
        {
            green-on(1),    -- system normal.
            red-on(2)       -- system exceptional state.
        }
        MAX-ACCESS read-only
        STATUS  current
        DESCRIPTION
            "bbs LED state display: SYS LED."
        ::= { utsLedGlobalLedDispGroup 2 }

   utsBBSLEDFanLedState OBJECT-TYPE
        SYNTAX INTEGER
        {
            green-on(1),  -- fan normal.
            red-on(2)     -- fan abnormal state.
        }
        MAX-ACCESS read-only
        STATUS  current
        DESCRIPTION
            "bbs LED state display: FAN LED."
        ::= { utsLedGlobalLedDispGroup 3 }

   utsBBSLEDAlarmCriticalLedState OBJECT-TYPE
        SYNTAX INTEGER
        {
            red-on(1),
            red-off(2)
        }
        MAX-ACCESS read-only
        STATUS  current
        DESCRIPTION
            "bbs LED state display: Critical alarm LED."
        ::= { utsLedGlobalLedDispGroup 4 }

   utsBBSLEDAlarmMajorLedState OBJECT-TYPE
        SYNTAX INTEGER
        {
            red-on(1),
            red-off(2)
        }
        MAX-ACCESS read-only
        STATUS  current
        DESCRIPTION
            "bbs LED state display: major alarm LED."
        ::= { utsLedGlobalLedDispGroup 5 }

   utsBBSLEDAlarmMinorLedState OBJECT-TYPE
        SYNTAX INTEGER
        {
            yellow-on(1),
            yellow-off(2)
        }
        MAX-ACCESS read-only
        STATUS  current
        DESCRIPTION
            "bbs LED state display: minor alarm LED."
        ::= { utsLedGlobalLedDispGroup 6 }

   utsBBSLEDGsmUplinkSFP1State OBJECT-TYPE
        SYNTAX INTEGER
        {
            green-on(1),      --   SFP Port 1 Link UP
            green-off(2),     --   SFP Port 1 Link DOWN
            green-flashing(3) --   With data passing through
        }
        MAX-ACCESS read-only
        STATUS  current
        DESCRIPTION
            "bbs LED state display: up link port SFP-1 link LED."
        ::= { utsLedGlobalLedDispGroup 7 }

   utsBBSLEDGsmUplinkSFP2State OBJECT-TYPE
        SYNTAX INTEGER
        {
            green-on(1),
            green-off(2),
            green-flashing(3)
        }
        MAX-ACCESS read-only
        STATUS  current
        DESCRIPTION
            "bbs LED state display: up link port SFP-2 link LED."
        ::= { utsLedGlobalLedDispGroup 8 }

   utsBBSLEDGsmUplinkSFP3State OBJECT-TYPE
        SYNTAX INTEGER
        {
            green-on(1),
            green-off(2),
            green-flashing(3)
        }
        MAX-ACCESS read-only
        STATUS  current
        DESCRIPTION
            "bbs LED state display: up link port SFP-3 link LED."
        ::= { utsLedGlobalLedDispGroup 9 }

   utsBBSLEDGsmUplinkSFP4State OBJECT-TYPE
        SYNTAX INTEGER
        {
            green-on(1),
            green-off(2),
            green-flashing(3)
        }
        MAX-ACCESS read-only
        STATUS  current
        DESCRIPTION
            "bbs LED state display: up link port SFP-4 link LED."
        ::= { utsLedGlobalLedDispGroup 10 }

--
--  pon slot led state display table
--

utsLedPonSlotLedDispObjs OBJECT IDENTIFIER ::= { utsLedMgmtConfExt 2 }

    utsLedPonSlotLedDispTable  OBJECT-TYPE
        SYNTAX      SEQUENCE OF UtsLedPonSlotLedDispEntry
        MAX-ACCESS  not-accessible
        STATUS      current
        DESCRIPTION
            "bbs system PON slot LED state display table."
       ::= { utsLedPonSlotLedDispObjs 1 }

utsLedPonSlotLedDispEntry OBJECT-TYPE
   SYNTAX       UtsLedPonSlotLedDispEntry
   MAX-ACCESS   not-accessible
       STATUS       current
       DESCRIPTION
          "An entry containing led state information of a pon slot."
      INDEX { utsLedPonSlotLedDispSlotId }
      ::= { utsLedPonSlotLedDispTable 1 }

     UtsLedPonSlotLedDispEntry ::=
        SEQUENCE {
            utsLedPonSlotLedDispSlotId
                INTEGER,
            utsLedPonSlotLedDispPowLedStat
                INTEGER,
	    		utsLedPonSlotLedDispFaultLedStat
                INTEGER,
            utsLedPonSlotLedDispSwapLedStat
                INTEGER,
            utsLedPonSlotLedDispPonPort1LedStat
                INTEGER,
	    	utsLedPonSlotLedDispPonPort2LedStat
			 		INTEGER,
            utsLedPonSlotLedDispPonPort3LedStat
                INTEGER,
            utsLedPonSlotLedDispPonPort4LedStat
                INTEGER
       }

    utsLedPonSlotLedDispSlotId OBJECT-TYPE
        SYNTAX      INTEGER
        MAX-ACCESS  read-only
        STATUS      current
        DESCRIPTION
           "A read-only value that identifies the pon module slot id."
       ::= { utsLedPonSlotLedDispEntry 1 }

    utsLedPonSlotLedDispPowLedStat OBJECT-TYPE
        SYNTAX      INTEGER
        {
          green-on(1),
          green-off(2)
        }
        MAX-ACCESS  read-only
        STATUS      current
        DESCRIPTION
           "pon slot power supply LED state."
       ::= { utsLedPonSlotLedDispEntry 2 }

    utsLedPonSlotLedDispFaultLedStat OBJECT-TYPE
        SYNTAX      INTEGER
        {
          red-on(1),
          red-off(2)
        }
        MAX-ACCESS  read-only
        STATUS      current
        DESCRIPTION
           "pon slot fault LED state."
       ::= { utsLedPonSlotLedDispEntry 3 }

    utsLedPonSlotLedDispSwapLedStat OBJECT-TYPE
        SYNTAX      INTEGER
        {
          yellow-on(1),       -- Modular Can Be Unplugged
          yellow-off(2),      -- Modular Can Not Unplugged
          yellow-flashing(3)  -- Module Is Waiting For Host to Confirm Unplug request
        }
        MAX-ACCESS  read-only
        STATUS      current
        DESCRIPTION
           "pon slot hot swap LED state."
       ::= { utsLedPonSlotLedDispEntry 4 }

    utsLedPonSlotLedDispPonPort1LedStat OBJECT-TYPE
        SYNTAX      INTEGER
        {
          green-on(1),
          red-on(2),
          led-off(3)
        }
        MAX-ACCESS  read-only
        STATUS      current
        DESCRIPTION
           "pon slot pon port 1 LED state."
       ::= { utsLedPonSlotLedDispEntry 5 }

    utsLedPonSlotLedDispPonPort2LedStat OBJECT-TYPE
        SYNTAX      INTEGER
        {
          green-on(1),
          red-on(2),
          led-off(3)
        }
        MAX-ACCESS  read-only
        STATUS      current
        DESCRIPTION
           "pon slot pon port 2 LED state."
       ::= { utsLedPonSlotLedDispEntry 6 }

    utsLedPonSlotLedDispPonPort3LedStat OBJECT-TYPE
        SYNTAX      INTEGER
        {
          green-on(1),
          red-on(2),
          led-off(3)
        }
        MAX-ACCESS  read-only
        STATUS      current
        DESCRIPTION
           "pon slot pon port 3 LED state."
       ::= { utsLedPonSlotLedDispEntry 7 }

    utsLedPonSlotLedDispPonPort4LedStat OBJECT-TYPE
        SYNTAX      INTEGER
        {
          green-on(1),
          red-on(2),
          led-off(3)
        }
        MAX-ACCESS  read-only
        STATUS      current
        DESCRIPTION
           "pon slot pon port 4 LED state."
       ::= { utsLedPonSlotLedDispEntry 8 }

--
--  BBS System boot Configuration
--
utsBBSSysOperState OBJECT-TYPE
        SYNTAX INTEGER
        {
            other(1),    -- read-only status.
            running(2),  -- read-only status.
            reset(3)     -- write to reset system
        }
        MAX-ACCESS read-write
        STATUS  current
        DESCRIPTION
            "bbs system running/reset state."
        ::= { utsSystemConfGroup 1 }

utsBBSSysBootMethod OBJECT-TYPE
        SYNTAX INTEGER
        {
            ftp(1),
            flash(2)
        }
        MAX-ACCESS read-write
        STATUS current
        DESCRIPTION
            "bbs system boot method"
        ::= { utsSystemConfGroup 2 }

utsBBSSysBootFileName OBJECT-TYPE
        SYNTAX DisplayString(SIZE(0..63))
        MAX-ACCESS read-write
        STATUS current
        DESCRIPTION
            "bbs system boot image file name with path"
        ::= { utsSystemConfGroup 3 }

utsBBSOutBandInterfaceIpAddr OBJECT-TYPE
    SYNTAX IpAddress
    MAX-ACCESS  read-write
    STATUS current
    DESCRIPTION
        "ip address of the bbs system out-of band management interface, user could
        use SNMP or telnet protocol communicate with the system through this
        ip address"
    ::= { utsSystemConfGroup 4 }

utsBBSOutbandInterfaceIpMask OBJECT-TYPE
    SYNTAX IpAddress
    MAX-ACCESS  read-write
    STATUS current
    DESCRIPTION
         "ip mask of the bbs system out-of band management interface"
    ::= { utsSystemConfGroup 5 }

utsBBSOutbandInterfaceNextHop OBJECT-TYPE
    SYNTAX IpAddress
    MAX-ACCESS  read-write
    STATUS current
    DESCRIPTION
         "Next Hop ip address of the bbs system out-of band management interface"
    ::= { utsSystemConfGroup 6 }

utsBBSBootFTPUserName OBJECT-TYPE
    SYNTAX  DisplayString(SIZE(0..23))
    MAX-ACCESS  read-write
    STATUS  current
    DESCRIPTION
        "The ftp user name used to download the boot image."
    ::= { utsSystemConfGroup 7 }

utsBBSBootFTPPassword OBJECT-TYPE
    SYNTAX  DisplayString(SIZE(0..15))
    MAX-ACCESS  read-write
    STATUS  current
    DESCRIPTION
        "The ftp user name used to download the boot image."
    ::= { utsSystemConfGroup 8 }


utsBBSBootFTPServerIpAddress OBJECT-TYPE
    SYNTAX IpAddress
    MAX-ACCESS  read-write
    STATUS current
    DESCRIPTION
         "The ftp server IP address that bbs used to download the boot image from."
    ::= { utsSystemConfGroup 9 }

utsBBSSaveRunningConfigure OBJECT-TYPE
    SYNTAX INTEGER
    {
        success(1),  -- read-only, save configuration success.
        failure(2),  -- read-only, save confiiguration fail.
        save(3)     -- write-only, save the current configuration into flash.
    }
    MAX-ACCESS  read-write
    STATUS current
    DESCRIPTION
         "Write to this mib will save the current running configuration into flash."
    ::= { utsSystemConfGroup 10 }

-- Delelte the utsBBSMgmtTrafficInBandTTL and utsBBSMgmtTrafficOutBandTTL by Tomsong 20070821
utsBBSMgmtTrafficInBandTTL OBJECT-TYPE
    SYNTAX INTEGER
    (
      1..255
    )
    MAX-ACCESS  read-write
    STATUS current
    DESCRIPTION
         "TTL configuration for management traffic"
    ::= { utsSystemConfGroup 12 }

utsBBSMgmtTrafficOutBandTTL OBJECT-TYPE
    SYNTAX INTEGER
    (
      1..255
    )
    MAX-ACCESS  read-write
    STATUS current
    DESCRIPTION
         "TTL configuration for management traffic"
    ::= { utsSystemConfGroup 13 }

utsBBSMgmtSysRunningMode OBJECT-TYPE
    SYNTAX INTEGER
    {
--      isp-service-tag-handling-mode(1),
      unique-tag-handling-mode(2),
--      application-tag-handling-mode(3),
--      qinq-tag-mode(4)
        mixed-tag-mode(5)  -- mixed for Application, ISP mode for per OLT PON port, QinQ mode for per ONU PON port;
    }
    MAX-ACCESS  read-write
    STATUS current
    DESCRIPTION
         "Unique tag handling mode: each ONU is assigned with an unique VLAN id, and internally
                                    OLT is in a stacked but not nested mode. Traffic behind ONU
                                    is always untagged.
          mixed-tag-mode: the detailed tag mode is Per OLT PON port( Application or ISP mode) or ONU PON port ( QinQ-tag-mode).
         "
    ::= { utsSystemConfGroup 14 }

utsBBSBPDUTermination OBJECT-TYPE
    SYNTAX INTEGER
    {
      enable(1),
      disable(2)
    }
    MAX-ACCESS  read-write
    STATUS current
    DESCRIPTION
    	"Enable or disable BPDU termination."
    ::= { utsSystemConfGroup 15 }

utsBBSSysSoftwareRateLimiting OBJECT-TYPE
    SYNTAX INTEGER
    {
      enable(1),
      disable(2)
    }
    MAX-ACCESS  read-write
    STATUS current
    DESCRIPTION
    	"The switch of software rate limiting,
    	 the default value is enable."
    ::= { utsSystemConfGroup 16 }


utsBBSSysHardwareRateLimiting OBJECT-TYPE
    SYNTAX INTEGER
    {
      enable(1),
      disable(2)
    }
    MAX-ACCESS  read-write
    STATUS current
    DESCRIPTION
    	"The switch of hardware rate limiting,
    	 the default value is enable."
    ::= { utsSystemConfGroup 17 }

utsBBSSysCpuUtilityAlarmThresholdTotal OBJECT-TYPE
    SYNTAX INTEGER
    ( 0..100)
    MAX-ACCESS  read-write
    STATUS current
    DESCRIPTION
    	"Total CPU utility threshold in percentage. If it is
    	 above the threshold, a trap will be send to NMS. '0'
    	 is to disable this function."
    DEFVAL {90}
    ::= { utsSystemConfGroup 18 }

utsBBSSysCpuUtilityAlarmThresholdPerTask OBJECT-TYPE
    SYNTAX INTEGER
    ( 0..100)
    MAX-ACCESS  read-write
    STATUS current
    DESCRIPTION
    	"Single task CPU utility threshold in percentage.
    	 If it is above the threshold, a trap will be send to NMS. '0'
    	 is to disable this function."
    DEFVAL {50}
    ::= { utsSystemConfGroup 19 }

utsBBSSysMemoryUtilityAlarmThreshold OBJECT-TYPE
    SYNTAX INTEGER
    ( 0..1000)
    MAX-ACCESS  read-write
    STATUS current
    DESCRIPTION
    	"System memory utility threshold in 0.1 percentage.
    	 If it is above the threshold, a trap will be send to NMS. '0'
    	 is to disable this function."
    DEFVAL {750 }
    ::= { utsSystemConfGroup 20 }

utsBBSSysARPAgingTime OBJECT-TYPE
       SYNTAX       INTEGER (30..65535)
	   MAX-ACCESS   read-write
	   STATUS       current
	   DESCRIPTION
	        "System ARP aging time."
	   ::= { utsSystemConfGroup 21 }

utsBBSSysMACAgingTime OBJECT-TYPE
   SYNTAX       INTEGER (0..65535)
   MAX-ACCESS   read-write
   STATUS       current
   DESCRIPTION
     "System switch MAC address aging time. The value range is 0, 10..65535.
      0 is to disbale system switch MAC aging."
   ::= { utsSystemConfGroup 22 }

utsBBSSysFactoryDefault OBJECT-TYPE
   SYNTAX       INTEGER
   {
            normal(0),  -- read only status
            factoryDefault(1)     -- write to reset configuation
   }

   MAX-ACCESS   read-write
   STATUS       current
   DESCRIPTION
     "Set configuation to factory default"
   ::= { utsSystemConfGroup 23 }

utsBBSOnuByteErrorWindow OBJECT-TYPE
   SYNTAX       INTEGER(1..20)    -- seconds
   MAX-ACCESS   read-write
   STATUS       current
   DESCRIPTION
     "ONU traffic byte error detecting window size, 1 to 20 seconds."
   ::= { utsSystemConfGroup 24 }

utsBBSOnuByteErrorThresholdMin OBJECT-TYPE
   SYNTAX       INTEGER(1..300)    -- bytes
   MAX-ACCESS   read-write
   STATUS       current
   DESCRIPTION
     "ONU traffic byte error threshold."
   ::= { utsSystemConfGroup 25 }

-- Add utsBBSMgmtTrafficTTL for management traffic by Tomsong 20070821
utsBBSMgmtTrafficTTL OBJECT-TYPE
    SYNTAX INTEGER
    (
      1..255
    )
    MAX-ACCESS  read-write
    STATUS current
    DESCRIPTION
         "TTL configuration for management traffic"
    ::= { utsSystemConfGroup 26 }

-- Add igmp parameter for the control mode and special mode only by Tomsong 20070906

utsBBSMgmtLastMembQueryIntvl OBJECT-TYPE
    SYNTAX     INTEGER
    UNITS      "seconds"
    MAX-ACCESS read-write
    STATUS     current
    DESCRIPTION
            "The Last Member Query Interval is the Max Response Time
            inserted into Group-Specific Queries sent in response to
            Leave Group messages, and is also the amount of time between
            Group-Specific Query messages.  This value may be tuned to
            modify the leave latency of the network.  A reduced value
            results in reduced time to detect the loss of the last
            member of a group.  The value of this object is irrelevant
            if igmpInterfaceVersion is 1. The value should be from 1 to 25,
            the default value is 1"
    DEFVAL     { 1 }
    ::= { utsSystemConfGroup 28 }

utsBBSMgmtQueryInterval OBJECT-TYPE
    SYNTAX     INTEGER(10..3600)
    UNITS      "seconds"
    MAX-ACCESS read-write
    STATUS     current
    DESCRIPTION
            "The frequency at which IGMP Host-Query packets are
            transmitted."
    DEFVAL     { 125 }
    ::= { utsSystemConfGroup 29 }

utsBBSMgmtQueryMaxRespTime OBJECT-TYPE
    SYNTAX     INTEGER
    UNITS      "seconds"
    MAX-ACCESS read-write
    STATUS     current
    DESCRIPTION
            "The maximum query response time advertised in IGMPv2
            queries, the range should be from 1 to 25."
    DEFVAL     { 10 }
    ::= { utsSystemConfGroup 30 }

utsBBSMgmtRobustness OBJECT-TYPE
    SYNTAX     INTEGER (2..10)
    MAX-ACCESS read-write
    STATUS     current
    DESCRIPTION
            "The Robustness Variable allows tuning for the expected
            packet loss on a subnet.  If a subnet is expected to be
            lossy, the Robustness Variable may be increased.  IGMP is
            robust to (Robustness Variable-1) packet losses."
    ::= { utsSystemConfGroup 31 }

utsBBSMgmtMaxFrameSize OBJECT-TYPE
    SYNTAX     INTEGER (64..16368)
    MAX-ACCESS read-write
    STATUS     current
    DESCRIPTION
            "The max frame size of system."
    DEFVAL     { 1532 }
    ::= { utsSystemConfGroup 32 }

utsBBSMgmtOption82FormatModeSetting OBJECT-TYPE
   SYNTAX      INTEGER
   {
            default(1),     -- default setting
            customized(2),  -- customized by the user
            ctc(3)			-- special format for ctc
   }

   MAX-ACCESS   read-write
   STATUS       current
   DESCRIPTION
     "Set configuation to option82 to select the option82 mode."
   ::= { utsSystemConfGroup 33 }

utsBBSMgmtOption82DefaultCircuitID OBJECT-TYPE
    SYNTAX    DisplayString(SIZE(0..63))
    MAX-ACCESS  read-only
    STATUS    current
    DESCRIPTION
        "The default value of the Circuit ID"
    ::= { utsSystemConfGroup 34 }

utsBBSMgmtOption82CustomizedCircuitID OBJECT-TYPE
    SYNTAX    DisplayString(SIZE(0..63))
    MAX-ACCESS  read-write
    STATUS    current
    DESCRIPTION
        "Setting the Circuit ID format when enable Cutomized mode."
    ::= { utsSystemConfGroup 35 }

utsBBSMgmtOption82DefaultRemoteID OBJECT-TYPE
    SYNTAX    DisplayString(SIZE(0..63))
    MAX-ACCESS  read-only
    STATUS    current
    DESCRIPTION
        "The default value of the Remote ID"
    ::= { utsSystemConfGroup 36 }

utsBBSMgmtOption82CustomizedRemoteID OBJECT-TYPE
    SYNTAX    DisplayString(SIZE(0..63))
    MAX-ACCESS  read-write
    STATUS    current
    DESCRIPTION
        "Setting the Remote ID format when enable Cutomized mode."
    ::= { utsSystemConfGroup 37 }

utsBBSMgmtGratuitousArpLearning OBJECT-TYPE
   SYNTAX      INTEGER
   {
            enable(1),    -- default setting
            disable(2)    -- customized by the user
   }

   MAX-ACCESS   read-write
   STATUS       current
   DESCRIPTION
     "Set configuation to the learning of gratuitous arp."
   ::= { utsSystemConfGroup 38 }

-- Add by tomsong for alarm sync

utsBBSMgmtAlarmSessionId OBJECT-TYPE
   SYNTAX      INTEGER
   MAX-ACCESS   read-only
   STATUS       current
   DESCRIPTION
     "The counter increments by 1 each time the node resets."
   ::= { utsSystemConfGroup 39 }

utsBBSMgmtAlarmLastSeqNo OBJECT-TYPE
   SYNTAX      INTEGER
   MAX-ACCESS   read-only
   STATUS       current
   DESCRIPTION
     "This counter contains current alarm sequence number assigned by Fault Management Enhancement application."
   ::= { utsSystemConfGroup 40 }

utsBBSMgmtLoopbackDetection OBJECT-TYPE
   SYNTAX      INTEGER
   {
   	 disable(1), -- default value
     enable(2)
   }
   MAX-ACCESS   read-write
   STATUS       current
   DESCRIPTION
     "This setting to set the loopback detection in the system level, and the default value is disable."
   ::= { utsSystemConfGroup 41 }

utsBBSMgmtLoopbackDetectIntervalTime OBJECT-TYPE
   SYNTAX      INTEGER (60..7200)
   MAX-ACCESS   read-write
   STATUS       current
   DESCRIPTION
     "This setting to set the interval time of loopback detection, the default value is 60 second."
   ::= { utsSystemConfGroup 42 }

utsBBSMgmtOption82CtcAccessNodeIdentifier OBJECT-TYPE
    SYNTAX    DisplayString(SIZE(0..50))
    MAX-ACCESS  read-write
    STATUS    current
    DESCRIPTION
        "The access node identifier for ctc format."
    ::= { utsSystemConfGroup 43 }

utsBBSMgmtArpLearning OBJECT-TYPE
   SYNTAX      INTEGER
   {
            enable(1),    -- default setting
            disable(2)    -- customized by the user
   }

   MAX-ACCESS   read-write
   STATUS       current
   DESCRIPTION
     "Set configuation to the learning of arp."
   ::= { utsSystemConfGroup 45 }

utsBBSMgmtOnuDisplayPolicy OBJECT-TYPE
   SYNTAX      INTEGER
   {
            onlineonly(1),          -- default setting
            all(2)                  -- all
   }

   MAX-ACCESS   read-write
   STATUS       current
   DESCRIPTION
     "Set configuation to the onu table."
   ::= { utsSystemConfGroup 49 }

utsBBSMgmtSoftwareVersion OBJECT-TYPE
   SYNTAX    DisplayString(SIZE(0..63))
   MAX-ACCESS   read-only
   STATUS       current
   DESCRIPTION
     "Get configuation to software version."
   ::= { utsSystemConfGroup 50 }

utsBBSMgmtIgmpProxySourceIP OBJECT-TYPE
   SYNTAX    IpAddress
   MAX-ACCESS   read-write
   STATUS       current
   DESCRIPTION
     "Setting of source ip address of IGMP proxy."
   ::= { utsSystemConfGroup 51 }

utsBBSMgmtOnuAutoConfigServerIP OBJECT-TYPE
   SYNTAX    IpAddress
   MAX-ACCESS   read-write
   STATUS       current
   DESCRIPTION
     "Setting of servier ip address of auto config server for onu."
   ::= { utsSystemConfGroup 52 }

utsBBSMgmtOnuAutoConfigServerMask OBJECT-TYPE
   SYNTAX    IpAddress
   MAX-ACCESS   read-write
   STATUS       current
   DESCRIPTION
     "Setting of servier ip mask of auto config server for onu."
   ::= { utsSystemConfGroup 53 }

utsBBSMgmtUplinkBandwidthThreshold OBJECT-TYPE
   SYNTAX    INTEGER
   MAX-ACCESS   read-write
   STATUS       current
   DESCRIPTION
     "Setting of Uplink Bandwidth percent threshold, the unit is 1/1000."
   ::= { utsSystemConfGroup 54 }

utsBBSMgmtUniBandwidthThreshold OBJECT-TYPE
   SYNTAX    INTEGER
   MAX-ACCESS   read-write
   STATUS       current
   DESCRIPTION
     "Setting of Onu uni Bandwidth percent threshold, the unit is 1/1000."
   ::= { utsSystemConfGroup 55 }




--
--   BBS System FTP Configuration
--

utsFTPConfAction OBJECT-TYPE
    SYNTAX  INTEGER
    {
        get(1), -- download file to the bbs system
        put(2)  -- upload file from the bbs system
    }
    MAX-ACCESS  read-write
    STATUS  current
    DESCRIPTION
        "bbs system ftp get(download) or put(upload) action. BBS only support binary file format"
    ::= { utsFTPConfGroup 1 }

utsFTPConfHostAddress OBJECT-TYPE
    SYNTAX  IpAddress
    MAX-ACCESS  read-write
    STATUS  current
    DESCRIPTION
        "bbs system ftp host IP address"
    ::= { utsFTPConfGroup 2 }

utsFTPConfUserName OBJECT-TYPE
    SYNTAX  DisplayString(SIZE(0..23))
    MAX-ACCESS  read-write
    STATUS  current
    DESCRIPTION
        "bbs system ftp user name"
    ::= { utsFTPConfGroup 3 }

utsFTPConfPassword OBJECT-TYPE
    SYNTAX  DisplayString(SIZE(0..15))
    MAX-ACCESS  read-write
    STATUS  current
    DESCRIPTION
        "bbs system ftp password"
    ::= { utsFTPConfGroup 4 }

utsFTPConfLocalFileName OBJECT-TYPE
    SYNTAX  DisplayString(SIZE(0..63))
    MAX-ACCESS  read-write
    STATUS  current
    DESCRIPTION
        "bbs system ftp local file name with path"
    ::= { utsFTPConfGroup 5 }

 utsFTPConfRemoteFileName OBJECT-TYPE
    SYNTAX  DisplayString(SIZE(0..63))
    MAX-ACCESS  read-write
    STATUS  current
    DESCRIPTION
        "bbs system ftp remote file name with path"
    ::= { utsFTPConfGroup 6 }

 utsFTPConfStatus OBJECT-TYPE
     SYNTAX  INTEGER
     {
         success(1),
         failure(2),
         busy(3)
     }
     MAX-ACCESS  read-only
     STATUS  current
     DESCRIPTION
         "FTP Upload/Download status"
     ::= { utsFTPConfGroup 7 }

  utsFTPConfStationId  OBJECT-TYPE
     SYNTAX  DisplayString(SIZE(0..32))
     MAX-ACCESS  read-write
     STATUS  current
     DESCRIPTION
         "station id, a string used to identify the issuer of FTP action."
     ::= { utsFTPConfGroup 8 }

--
--   BBS System TFTP Configuration
--
 utsTFTPConfAction OBJECT-TYPE
    SYNTAX  INTEGER
    {
        get(1), -- download file to the bbs system
        put(2)  -- upload file from the bbs system
    }
    MAX-ACCESS  read-write
    STATUS  current
    DESCRIPTION
        "bbs system tftp get(download) or put(upload) action. BBS only support binary file format"
    ::= { utsTFTPConfGroup 1 }

 utsTFTPConfHostAddress OBJECT-TYPE
    SYNTAX  IpAddress
    MAX-ACCESS  read-write
    STATUS  current
    DESCRIPTION
        "bbs system tftp server host IP address"
    ::= { utsTFTPConfGroup 2 }

 utsTFTPConfLocalFileName OBJECT-TYPE
    SYNTAX  DisplayString(SIZE(0..63))
    MAX-ACCESS  read-write
    STATUS  current
    DESCRIPTION
        "bbs system tftp local file name with path"
    ::= { utsTFTPConfGroup 5 }

 utsTFTPConfRemoteFileName OBJECT-TYPE
    SYNTAX  DisplayString(SIZE(0..63))
    MAX-ACCESS  read-write
    STATUS  current
    DESCRIPTION
        "bbs system tftp remote file name with path"
    ::= { utsTFTPConfGroup 6 }

 utsTFTPConfStatus OBJECT-TYPE
     SYNTAX  INTEGER
     {
         success(1),
         failure(2),
         busy(3)
     }
     MAX-ACCESS  read-only
     STATUS  current
     DESCRIPTION
         "TFTP Upload/Download status"
     ::= { utsTFTPConfGroup 7 }

  utsTFTPConfStationId  OBJECT-TYPE
     SYNTAX  DisplayString(SIZE(0..32))
     MAX-ACCESS  read-write
     STATUS  current
     DESCRIPTION
         "station id, a string used to identify the issuer of TFTP action."
     ::= { utsTFTPConfGroup 8 }


--
--  File System commands
--
utsFileSystemCommand OBJECT-TYPE
    SYNTAX    INTEGER
    {
        list(1),
        copy(2),
        rename(3),
	     delete(4)
    }
    MAX-ACCESS  read-write
    STATUS    current
    DESCRIPTION
        "Some file-system command can be performed on the bbs flash files.
         list(1) will list all files  in flash in a string with following format
            'filename,filesize,filedate,filetime';'filename,filesize,filedate,filetime'
         "
    ::= { utsFileSystemGroup 1 }

utsFileSystemListDirectory OBJECT-TYPE
    SYNTAX    DisplayString(SIZE(0..255))
    MAX-ACCESS  read-write
    STATUS    current
    DESCRIPTION
        "The legal directories should be flash:, nvm:syslog, nvm:cfgdata"
    ::= { utsFileSystemGroup 2 }

utsFileSystemListDirectoryResult OBJECT-TYPE
    SYNTAX    DisplayString(SIZE(0..255))
    MAX-ACCESS  read-only
    STATUS    current
    DESCRIPTION
        "The result of the list(1) command
	 reported in utsFileSystemListDirectoryResult in the following format,
	 For normal file, like:
	    'filename1,filesize1,filedate1,filetime1';
            'filename2,filesize2,filedate2,filetime2';
         For directory file, add DIR indication for directory file, like:
            'filename1, DIR, filesize1,filedate1,filetime1'
            'filename2, DIR, filesize2,filedate2,filetime2'
         A null string represents no files in the directory"
    ::= { utsFileSystemGroup 3 }

utsFileSystemSrcFileName OBJECT-TYPE
    SYNTAX    DisplayString(SIZE(0..255))
    MAX-ACCESS  read-write
    STATUS    current
    DESCRIPTION
        "If the command is rename, this file name is the original(old) file name.
         If the command is copy, this file name is the source file name.
		 If the command is delete, this is the name of the file to be deleted"
    ::= { utsFileSystemGroup 4 }

utsFileSystemDstFileName OBJECT-TYPE
    SYNTAX    DisplayString(SIZE(0..255))
    MAX-ACCESS  read-write
    STATUS    current
    DESCRIPTION
        "If the command is rename, this file name is the new file name.
         If the command is copy, this file name is the destination file name."
    ::= { utsFileSystemGroup 5 }

utsFileSystemCommandStatus OBJECT-TYPE
    SYNTAX    UtsConfStatusType
    MAX-ACCESS  read-only
    STATUS    current
    DESCRIPTION
        "The result of the file-system command issued."
    ::= { utsFileSystemGroup 6 }

utsFileSystemCommandStationId OBJECT-TYPE
    SYNTAX  UtsConfStationIdType
    MAX-ACCESS read-write
    STATUS current
    DESCRIPTION
        "Station id, a string used to identify the isuuer of the file-system command"
    ::= { utsFileSystemGroup 7 }

-- add by tomsong 2007/11/07
utsFileSystemListDirectoryResultEndFlag OBJECT-TYPE
    SYNTAX    INTEGER
    {
        end(1),
        unremitting(2)
    }
    MAX-ACCESS  read-only
    STATUS    current
    DESCRIPTION
        "If this flag is end(1),then should not read again, if this flag is unremitting(2),then should
         read agagin until the flag change to end"
    ::= { utsFileSystemGroup 8 }


 -- postphone to 3.0, zhaoxf Dec 30, 2005
 -- utsFileSystemFlashFreeSize OBJECT-TYPE
 --   SYNTAX  INTEGER
 --   MAX-ACCESS read-only
 --   STATUS current
 --   DESCRIPTION
 --       "The free bytes of flash device"
 --   ::= { utsFileSystemGroup 8 }

--
--  BBS Chassis System Configuration
--
utsBBSChassisPwrType OBJECT-TYPE
        SYNTAX INTEGER
        {
            ac(1),    -- read-only status.
            dc(2)  -- read-only status.
        }
        MAX-ACCESS read-only
        STATUS  current
        DESCRIPTION
            "bbs power supply module type, AC or DC."
        ::= { utsChassisConfGroup 1 }

utsBBSChassisPwrLowSlot OBJECT-TYPE
        SYNTAX INTEGER
        {
            empty(1),
            installed-not-work(2),
            installed-and-work(3)
        }
        MAX-ACCESS read-only
        STATUS current
        DESCRIPTION
            "whether the chassis power module in low slot exist and work normally"
        ::= { utsChassisConfGroup 2 }

utsBBSChassisPwrHighSlot OBJECT-TYPE
        SYNTAX INTEGER
        {
            empty(1),
            installed-not-work(2),
            installed-and-work(3)
        }
        MAX-ACCESS read-only
        STATUS current
        DESCRIPTION
            "whether the chassis power module in high slot exist and work normally"
        ::= { utsChassisConfGroup 3 }

utsBBSChassisInternalPowerStat OBJECT-TYPE
        SYNTAX INTEGER
        {
            normal(1),
	    abnormal(2)
        }
        MAX-ACCESS read-only
        STATUS current
        DESCRIPTION
            "chassis the system power module status, such as over voltage, low voltage, etc"
        ::= { utsChassisConfGroup 4 }

utsBBSChassisFanTrayStat OBJECT-TYPE
        SYNTAX INTEGER
        {
            normal  (1),
            abnormal (2)
        }
        MAX-ACCESS read-only
        STATUS current
        DESCRIPTION
            "whether the chassis Fan tray module exist"
        ::= { utsChassisConfGroup 5 }

utsBBSChassisTempCur OBJECT-TYPE
        SYNTAX INTEGER
        MAX-ACCESS read-only
        STATUS current
        DESCRIPTION
            "chassis CURRENT temperature "
        ::= { utsChassisConfGroup 6 }

utsBBSChassisTempUpLimit OBJECT-TYPE
        SYNTAX INTEGER (0..75)
        MAX-ACCESS read-write
        STATUS current
        DESCRIPTION
            "the threshold of chassis module temperature"
        DEFVAL {55}
        ::= { utsChassisConfGroup 7 }


--
--  ethernet interface extersion
--

utsEthIfExtObjects OBJECT IDENTIFIER ::= { utsEthIfConfExt 1 }


--
--  ethernet interface table's extension
--
    utsEthIfExtTable  OBJECT-TYPE
        SYNTAX      SEQUENCE OF UtsEthIfExtEntry
        MAX-ACCESS  not-accessible
        STATUS      current
        DESCRIPTION
            "A list of UTStarcom's extension to the interface entries. The
            number of entries is given by the value of ifNumber. This table
            contains additional objects for the interface table which is defined
            in ref1213."
       ::= { utsEthIfExtObjects 1 }

utsEthIfExtEntry OBJECT-TYPE
   SYNTAX       UtsEthIfExtEntry
   MAX-ACCESS   not-accessible
       STATUS       current
       DESCRIPTION
          "An entry containing additional management information
            applicable to a particular interface."
      INDEX { ifIndex }
      ::= { utsEthIfExtTable 1 }

     UtsEthIfExtEntry ::=
        SEQUENCE {
            utsEthIfExtModuleId
                INTEGER,
            utsEthIfExtPortId
                INTEGER,
	    	utsEthIfExtLinkAggGroupId
                INTEGER,
            utsEthIfExtLoopbackPortId
                INTEGER,
            utsEthIfExtVlanId
                INTEGER,
	    	utsEthIfExtPortType
			 	INTEGER,
            utsEthIfExtIpAddress
                IpAddress,
            utsEthIfExtIpNetmask
                IpAddress,
	    	utsEthIfExtSwitchMode
				INTEGER,
	    	utsEthIfExtAdminStatus
				INTEGER,
		    utsEthIfExtIfIndex
		        INTEGER,
		    utsEthIfExtDescription
		        DisplayString
       }

    utsEthIfExtModuleId OBJECT-TYPE
        SYNTAX      INTEGER
        MAX-ACCESS  read-only
        STATUS      current
        DESCRIPTION
           "A read-only value that identifies the interface module id."
       ::= { utsEthIfExtEntry 1	}

    utsEthIfExtPortId OBJECT-TYPE
        SYNTAX      INTEGER
        MAX-ACCESS  read-only
        STATUS      current
        DESCRIPTION
           "A read-only value that identifies the interface port Id."
       ::= { utsEthIfExtEntry 2	}

    utsEthIfExtLinkAggGroupId  OBJECT-TYPE
		SYNTAX         INTEGER
		MAX-ACCESS     read-only
		STATUS         current
		DESCRIPTION
	    "Link Aggregation group number. This value has meaning when
			the port type is a lag-port."
		::= { utsEthIfExtEntry 3 }

    utsEthIfExtLoopbackPortId OBJECT-TYPE
        SYNTAX      INTEGER
        MAX-ACCESS  not-accessible
        STATUS      current
        DESCRIPTION
           "A value that identifies the interface loopback port id. This value
		   has meaning when the port type is a loopback-port."
       ::= { utsEthIfExtEntry 4	}

    utsEthIfExtVlanId OBJECT-TYPE
        SYNTAX      INTEGER
        MAX-ACCESS  read-only
        STATUS      current
        DESCRIPTION
           "The interface vlan id. This value is meaningful only
		   when the port type is vlan-port or supervlan-port."
       ::= { utsEthIfExtEntry 5	}

    utsEthIfExtPortType OBJECT-TYPE
        SYNTAX    INTEGER {
	        port(1),
		    lag-port(2),
		    loopback-port(3),
		    vlan-port(4),
		    supervlan-port(5),
			invalid-port(6)
	    }
        MAX-ACCESS  read-only
        STATUS      current
        DESCRIPTION
            "A value that idicates the ethernet interface port type.
		        port             -  Physical port.
			    lag-port         -  Link Aggregation Port.
			    loopback-port    - supports loopback.
			    vlan-port        - VLAN port.
			    suppervlan-port  - Supper VLAN port.
                invalid-port    -  the port is in invalid state."
        ::= { utsEthIfExtEntry 6	}

    utsEthIfExtIpAddress OBJECT-TYPE
        SYNTAX      IpAddress
        MAX-ACCESS  read-write
        STATUS      current
        DESCRIPTION
           "Ip address of the particular interface. The IpAddress of the particular
            interfce can be assigned by writting this object.
            The utsEthIfExtIpAddress and utsEthIfExtIpNetmask must be set at same time"
       ::= { utsEthIfExtEntry 7 }

    utsEthIfExtIpNetmask OBJECT-TYPE
        SYNTAX      IpAddress
        MAX-ACCESS  read-write
        STATUS      current
        DESCRIPTION
           "The network Mask of the subnet associated with this interface.
            The utsEthIfExtIpAddress and utsEthIfExtIpNetmask must be set at same time"
       ::= { utsEthIfExtEntry 8 }

    utsEthIfExtSwitchMode  OBJECT-TYPE
	   SYNTAX  INTEGER
             {
                  layer-2(1),
                  layer-3(2)
             }
	   MAX-ACCESS read-write
	   STATUS  current
	   DESCRIPTION
		      "A value to change the port mode to/from Layer-2/Layer-3 mode.
			 port in layer-3 mode has routing capability"
          ::= { utsEthIfExtEntry 9	}

    utsEthIfExtAdminStatus  OBJECT-TYPE
           SYNTAX INTEGER
             {
                up(1),
                down(2)
             }
		  MAX-ACCESS read-write
		  STATUS  current
		  DESCRIPTION
		      "Use to turn up/down the interface in this entry."
          ::= { utsEthIfExtEntry 10	}

    utsEthIfExtIfIndex OBJECT-TYPE
       SYNTAX  INTEGER
	   MAX-ACCESS read-only
	   STATUS  current
	   DESCRIPTION
		      "extend interface table index."
          ::= { utsEthIfExtEntry 11	}

    utsEthIfExtDescription OBJECT-TYPE       --Add by tomsong for NMS MRD 4.8.5, 2007.5.9
       SYNTAX DisplayString(SIZE(0..63))
       MAX-ACCESS read-write
	   STATUS  current
	   DESCRIPTION
		      "The description for the interface."
          ::= { utsEthIfExtEntry 12	}

--
--   switch port table extension
--
    utsSwitchPortExtTable  OBJECT-TYPE
        SYNTAX      SEQUENCE OF UtsSwitchPortExtEntry
        MAX-ACCESS  not-accessible
        STATUS      current
        DESCRIPTION
            "A list of UTStarcom's extension to the switch port entries. The
            number of entries is given by the number of logical port. This table
            contains additional objects for the switch port."
       ::= { utsEthIfExtObjects 8 }

	utsSwitchPortExtEntry OBJECT-TYPE
	   SYNTAX       UtsSwitchPortExtEntry
	   MAX-ACCESS   not-accessible
	       STATUS       current
	       DESCRIPTION
	          "An entry containing additional management information
	            applicable to a particular switch port."
	      INDEX { utsSwitchPortExtIfNum }
	      ::= { utsSwitchPortExtTable 1 }

     UtsSwitchPortExtEntry ::=
        SEQUENCE {
            utsSwitchPortExtIfNum            INTEGER,
            utsSwitchPortExtModuleId         INTEGER,
            utsSwitchPortExtPortId           INTEGER,
	    	utsSwitchPortExtLAGId            INTEGER,
	    	utsSwitchPortExtPortType	     INTEGER,
		    utsSwitchPortExtACLDefAction     INTEGER,
		    utsSwitchPortExtAdmFlowControlRx INTEGER,
		   -- utsEthIfExtOprFlowControlRx
		     --     INTEGER,
		    utsSwitchPortExtAdmFlowControlTx INTEGER,
		    -- utsEthIfExtOprFlowControlTx
		       --   INTEGER,
		    utsSwitchPortExtIpMuticastFilter INTEGER
		    -- utsEthIfExtAction
		       --   INTEGER
       }

  utsSwitchPortExtIfNum  OBJECT-TYPE
    SYNTAX         INTEGER
	MAX-ACCESS     not-accessible
	STATUS         current
	DESCRIPTION
	   "The interface index denotes switch ports and link aggregation.
	   For 1000:The range is 1-44. 1-12 denotes switch ports and 13-44 denotes link aggregations.
	   For 4000:The range is 1-72. 1-48 denotes switch ports and 49-72 denotes link aggregations."
	::= { utsSwitchPortExtEntry 1 }


  utsSwitchPortExtModuleId  OBJECT-TYPE
    SYNTAX         INTEGER
	MAX-ACCESS     read-only
	STATUS         current
	DESCRIPTION
	   "The module index to this switch port entry."
	::= { utsSwitchPortExtEntry 2 }

  utsSwitchPortExtPortId  OBJECT-TYPE
    SYNTAX         INTEGER
	MAX-ACCESS     read-only
	STATUS         current
	DESCRIPTION
	   "The port index to this switch port entry."
	::= { utsSwitchPortExtEntry 3 }

  utsSwitchPortExtLAGId  OBJECT-TYPE
    SYNTAX         INTEGER
	MAX-ACCESS     read-only
	STATUS         current
	DESCRIPTION
	   "The LAG index to this switch port entry."
	::= { utsSwitchPortExtEntry 4 }

  utsSwitchPortExtPortType  OBJECT-TYPE
    SYNTAX         INTEGER
	{
		gePort(1),
		lagPort(2)
	}
	MAX-ACCESS     read-only
	STATUS         current
	DESCRIPTION
	   "The interface type: GE port or LAG port."
	::= { utsSwitchPortExtEntry 5 }


  utsSwitchPortExtACLDefAction  OBJECT-TYPE
    SYNTAX  INTEGER
    {
 	   	 preConfiguration(1),
	   	 noPreConfiguration(2)
    }
   	MAX-ACCESS     read-write
	STATUS         current
	DESCRIPTION
	   "The ACL default action of this port."
	::= { utsSwitchPortExtEntry 6 }


  utsSwitchPortExtAdmFlowControlRx  OBJECT-TYPE
    SYNTAX  INTEGER
   	   {
   	      enable(1),
   	      disable(2)
   	      -- desire(3),
   	   }
	MAX-ACCESS     read-write
	STATUS         current
	DESCRIPTION
	   "Set the receive flow control administrative
	    status on the port."

	::= { utsSwitchPortExtEntry 7 }


--   utsSwitchPortExtOprFlowControlRx OBJECT-TYPE
 --  	   SYNTAX  INTEGER
   	   --{
   	     -- enabled(1),
   	      --disabled(2),
   	      --disagree(3),
   	      --notAvailable(4)     for non-physical port,
   	   	                      -- vlan interface, loopback interface, etc
   	   --}
	   --MAX-ACCESS read-only
	   --STATUS  current
	   --DESCRIPTION
		 --     "Indicates the receive flow control operational
 	       --    status of the port. If the port could not reach an agreement
 	         --  on the link protocol with the far end, its operational
			   --status will be disagree(3)"
       --::= { utsEthIfExtEntry 8	}

    utsSwitchPortExtAdmFlowControlTx OBJECT-TYPE
   	   SYNTAX  INTEGER
   	   {
   	      enable(1),
   	      disable(2)
   	      -- desire(3),
   	   }
	   MAX-ACCESS read-write
	   STATUS  current
	   DESCRIPTION
		      "Set the send flow control administrative
			   status on the port."
       DEFVAL {1}
          ::= { utsSwitchPortExtEntry 9	}

    --utsSwitchPortExtOprFlowControlTx OBJECT-TYPE
   	  -- SYNTAX  INTEGER
   	   --{
   	     -- enabled(1),
   	      --disabled(2),
   	      --disagreed(3),
   	      --notAvailable(4)     for non-physical port,
   	   	                      -- vlan interface, loopback interface, etc
   	  -- }
	   --MAX-ACCESS read-only
	   --STATUS  current
	   --DESCRIPTION
		 --     "Indicates the send flow control operational
 	       --    status of the port. If the port could not reach an agreement
 	         --  on the link protocol with the far end, its operational
			   --status will be disagree(3)"
     --  ::= { utsEthIfExtEntry 10	}

    utsSwitchPortExtIpMuticastFilter OBJECT-TYPE
   	   SYNTAX  INTEGER
   	   {
   	      enable(1),
   	      disable(2)
   	   }
	   MAX-ACCESS read-write
	   STATUS  current
	   DESCRIPTION
		      "Set the ip multicast filter for the port."
      ::= { utsSwitchPortExtEntry 11	}
-- the utsEthIntelligentLinkTable table
-- implemented by Core Switch chip
-- Vlan

utsEthIntelligentLinkTable OBJECT-TYPE
          SYNTAX SEQUENCE OF UtsEthIntelligentLinkEntry
          MAX-ACCESS not-accessible
          STATUS current
          DESCRIPTION
             "Intelligent Link Table for uplink side."
          ::= { utsEthIfExtObjects 15 }

       utsEthIntelligentLinkEntry OBJECT-TYPE
          SYNTAX UtsEthIntelligentLinkEntry
          MAX-ACCESS not-accessible
          STATUS current
          DESCRIPTION
             "An entry in the intelligent link table for Eth interface."
          INDEX	{ utsEthIntelligentLinkGroupId }
       ::= { utsEthIntelligentLinkTable 1 }


       UtsEthIntelligentLinkEntry ::=
          SEQUENCE {
             utsEthIntelligentLinkGroupId              INTEGER,
             utsEthIntelligentLinkGroupName            DisplayString,
             utsEthIntelligentLinkMasterPortType       INTEGER,
             utsEthIntelligentLinkMasterPortModuleId   INTEGER,
             utsEthIntelligentLinkMasterPortDeviceId   INTEGER,
             utsEthIntelligentLinkMasterPortPortId     INTEGER,
             utsEthIntelligentLinkMasterLinkAggGroupId INTEGER,
             utsEthIntelligentLinkSlavePortType        INTEGER,
             utsEthIntelligentLinkSlavePortModuleId    INTEGER,
             utsEthIntelligentLinkSlavePortDeviceId    INTEGER,
             utsEthIntelligentLinkSlavePortPortId      INTEGER,
             utsEthIntelligentLinkSlaveLinkAggGroupId  INTEGER,
             utsEthIntelligentLinkMasterPortStatus     INTEGER,
             utsEthIntelligentLinkSlavePortStatus      INTEGER,
             utsEthIntelligentLinkRowStatus            RowStatus
          }

   utsEthIntelligentLinkGroupId OBJECT-TYPE
      SYNTAX      INTEGER
      MAX-ACCESS  not-accessible
      STATUS      current
      DESCRIPTION
         "An indication of intelligent link group id."
      ::= { utsEthIntelligentLinkEntry 1 }


   utsEthIntelligentLinkGroupName OBJECT-TYPE
      SYNTAX DisplayString (SIZE(0..16))
      MAX-ACCESS read-create
      STATUS current
      DESCRIPTION
         "An name of intelligent link group."
      ::= { utsEthIntelligentLinkEntry 2 }

   utsEthIntelligentLinkMasterPortType OBJECT-TYPE
      SYNTAX      INTEGER
      {
      	 ethernetport(1),
      	 linkaggroup(2)
      }
      MAX-ACCESS  read-create
      STATUS      current
      DESCRIPTION
         "To indicate the master port is common ehternet port or link agg group."
      ::= { utsEthIntelligentLinkEntry 3 }

   utsEthIntelligentLinkMasterPortModuleId OBJECT-TYPE
        SYNTAX  INTEGER
        MAX-ACCESS  read-create
        STATUS  current
        DESCRIPTION
            "Specify Master Port Module ID."
        ::= { utsEthIntelligentLinkEntry 4 }

    utsEthIntelligentLinkMasterPortDeviceId OBJECT-TYPE
        SYNTAX  INTEGER
        MAX-ACCESS  read-create
        STATUS  current
        DESCRIPTION
            "Specify Master Port Device ID."
        ::= { utsEthIntelligentLinkEntry 5 }

    utsEthIntelligentLinkMasterPortPortId OBJECT-TYPE
        SYNTAX  INTEGER
        MAX-ACCESS  read-create
        STATUS  current
        DESCRIPTION
            "Specify Master Port ID."
        ::= { utsEthIntelligentLinkEntry 6 }

    utsEthIntelligentLinkMasterLinkAggGroupId OBJECT-TYPE
        SYNTAX  INTEGER
        MAX-ACCESS  read-create
        STATUS  current
        DESCRIPTION
            "Specify Master Link Agg Group Id."
        ::= { utsEthIntelligentLinkEntry 7 }

    utsEthIntelligentLinkSlavePortType OBJECT-TYPE
      SYNTAX      INTEGER
      {
      	 ethernetport(1),
      	 linkaggroup(2)
      }
      MAX-ACCESS  read-create
      STATUS      current
      DESCRIPTION
         "To indicate the slave port is common ehternet port or link agg group."
      ::= { utsEthIntelligentLinkEntry 8 }

   utsEthIntelligentLinkSlavePortModuleId OBJECT-TYPE
        SYNTAX  INTEGER
        MAX-ACCESS  read-create
        STATUS  current
        DESCRIPTION
            "Specify Slave Port Module ID."
        ::= { utsEthIntelligentLinkEntry 9 }

    utsEthIntelligentLinkSlavePortDeviceId OBJECT-TYPE
        SYNTAX  INTEGER
        MAX-ACCESS  read-create
        STATUS  current
        DESCRIPTION
            "Specify Slave Port Device ID."
        ::= { utsEthIntelligentLinkEntry 10 }

    utsEthIntelligentLinkSlavePortPortId OBJECT-TYPE
        SYNTAX  INTEGER
        MAX-ACCESS  read-create
        STATUS  current
        DESCRIPTION
            "Specify Slave Port ID."
        ::= { utsEthIntelligentLinkEntry 11 }

    utsEthIntelligentLinkSlaveLinkAggGroupId OBJECT-TYPE
        SYNTAX  INTEGER
        MAX-ACCESS  read-create
        STATUS  current
        DESCRIPTION
            "Specify Slave Link Agg Group Id."
        ::= { utsEthIntelligentLinkEntry 12 }

    utsEthIntelligentLinkMasterPortStatus OBJECT-TYPE
        SYNTAX  INTEGER
        {
           active(1),
           standby(2),
           notready(3)
        }
        MAX-ACCESS  read-only
        STATUS  current
        DESCRIPTION
            "Master port status."
        ::= { utsEthIntelligentLinkEntry 13 }

    utsEthIntelligentLinkSlavePortStatus OBJECT-TYPE
        SYNTAX  INTEGER
        {
           active(1),
           standby(2),
           notready(3)
        }
        MAX-ACCESS  read-only
        STATUS  current
        DESCRIPTION
            "Slave port status."
        ::= { utsEthIntelligentLinkEntry 14 }


   	utsEthIntelligentLinkRowStatus OBJECT-TYPE
        SYNTAX         RowStatus
        MAX-ACCESS     read-create
        STATUS         current
        DESCRIPTION
           "Row status for the current entry. "
       ::= { utsEthIntelligentLinkEntry 15 }


--
-- ip interface secondary IP addres table
--
    utsIfSecondIpTable  OBJECT-TYPE
        SYNTAX      SEQUENCE OF UtsIfSecondIpEntry
        MAX-ACCESS  not-accessible
        STATUS      current
        DESCRIPTION
            "this table contains all secondary ip address configured for a ip interface."
       ::= { utsEthIfExtObjects 7 }

	utsIfSecondIpEntry OBJECT-TYPE
   	SYNTAX       UtsIfSecondIpEntry
   	MAX-ACCESS   not-accessible
      STATUS       current
      DESCRIPTION
          "An entry containing secondary ip address informaiton
            applicable to a particular interface."
      INDEX { utsIfSecondIpIfIndex, utsIfSecondIpAddress, utsIfSecondIpNetmask }
      ::= { utsIfSecondIpTable 1 }

     UtsIfSecondIpEntry ::=
        SEQUENCE {
        		utsIfSecondIpIfIndex
        			 InterfaceIndex,
            utsIfSecondIpAddress
                IpAddress,
            utsIfSecondIpNetmask
                IpAddress,
	    		utsIfSecondIpStatus
					RowStatus
       }
	utsIfSecondIpIfIndex OBJECT-TYPE
    	SYNTAX     InterfaceIndex
    	MAX-ACCESS not-accessible
    	STATUS     current
    	DESCRIPTION
            "The interface for which this entry contains information for
            an secondary IP address."
    	::= { utsIfSecondIpEntry 1 }

    utsIfSecondIpAddress OBJECT-TYPE
        SYNTAX      IpAddress
        MAX-ACCESS  read-create
        STATUS      current
        DESCRIPTION
           "secondary Ip address of the particular interface. The IpAddress of the particular
            interfce can be assigned by writting this object.
            The utsIfSecondIpAddress and utsIfSecondIpNetmask must be set at same time"
       ::= { utsIfSecondIpEntry 7 }

    utsIfSecondIpNetmask OBJECT-TYPE
        SYNTAX      IpAddress
        MAX-ACCESS  read-create
        STATUS      current
        DESCRIPTION
           "The network Mask of the subnet associated with this interface.
            The utsIfSecondIpAddress and utsIfSecondIpNetmask must be set at same time"
       ::= { utsIfSecondIpEntry 8 }

    utsIfSecondIpStatus OBJECT-TYPE
        SYNTAX          RowStatus
        MAX-ACCESS      read-create
        STATUS          current
        DESCRIPTION
            "Row status for the current entry. "
        ::= { utsIfSecondIpEntry 9 }

--
--  link aggregation Extension
--

-- the lagUtExtDot3adAgg table

          -- Implementation of the lagUtExtDot3adAgg group is optional.  It is
          -- implemented by those lag that support the IEEE 802.3 link aggregations
          -- Protocol.

    utsLagExtDot3adAggTable OBJECT-TYPE
        SYNTAX      SEQUENCE OF UtsLagExtDot3adAggEntry
        MAX-ACCESS  not-accessible
        STATUS      current
        DESCRIPTION
            "lagMIB UtExt DotsadAgg Table."
        ::= { utsEthIfExtObjects 2 }

    utsLagExtDot3adAggEntry OBJECT-TYPE
        SYNTAX          UtsLagExtDot3adAggEntry
        MAX-ACCESS      not-accessible
        STATUS          current
        DESCRIPTION
            "An entry in the lagMIB extension table	for link aggregation interface."
        INDEX { utsLagExtDot3adAggGroupId }
        ::= { utsLagExtDot3adAggTable 1 }

    UtsLagExtDot3adAggEntry ::=
        SEQUENCE {
            utsLagExtDot3adAggGroupId       INTEGER,
            utsLagExtDot3adAggName          DisplayString,
            utsLagExtDot3adAggPerLinkSpeed  INTEGER,
            utsLagExtDot3adAggPortListPorts OCTET STRING,
            utsLagExtDot3adAggRtag          INTEGER,
            utsLagExtDot3adAggStatus        RowStatus
    	}

    utsLagExtDot3adAggGroupId OBJECT-TYPE
        SYNTAX  INTEGER
        MAX-ACCESS  read-create
        STATUS  current
        DESCRIPTION
            "An indication of what link aggregation group index of the 802.3 lag is
            running."
        ::= { utsLagExtDot3adAggEntry 1 }

    utsLagExtDot3adAggName OBJECT-TYPE
        SYNTAX  DisplayString (SIZE(0..16))
        MAX-ACCESS  read-create
        STATUS  current
        DESCRIPTION
            "Specify the name of the link aggregation group."
        ::= { utsLagExtDot3adAggEntry 2 }

    utsLagExtDot3adAggPerLinkSpeed OBJECT-TYPE
        SYNTAX  INTEGER
        MAX-ACCESS  read-only
        STATUS  current
        DESCRIPTION
            "Specify the speed of the link aggregation group."
        ::= { utsLagExtDot3adAggEntry 3 }

    utsLagExtDot3adAggPortListPorts OBJECT-TYPE
        SYNTAX      OCTET STRING
        MAX-ACCESS  read-create
        STATUS      current
        DESCRIPTION
            "Each octet within this value specifies a set of eight ports, with the
            first octet specifying ports 1 through 8, the second octet specifying
            ports 9 through 16, etc.  Within each octet, the least significant bit
            represents the lowest numbered port, and the most significant bit
            represents the highest numbered port.  Thus, each port of the bridge
            is represented by a single bit within the value of this object.  If that
            bit has a value of '1' then that port is included in the set of ports;
            the port is not included if its bit has a value of '0'."
        ::= { utsLagExtDot3adAggEntry 4 }

    utsLagExtDot3adAggRtag OBJECT-TYPE
        SYNTAX  INTEGER {
            srcMac(1),
            destMac(2),
            srcMacNDestMac(3),
            srcIp(4),
            destIp(5),
            srcIpNDestIp(6)
        }
        MAX-ACCESS  read-create
        STATUS  current
        DESCRIPTION
            "Specify the load balancing rules number for the link aggregation group. "
        ::= { utsLagExtDot3adAggEntry 6 }

    utsLagExtDot3adAggStatus OBJECT-TYPE
        SYNTAX          RowStatus
        MAX-ACCESS      read-create
        STATUS          current
        DESCRIPTION
            "Row status for the current entry. "
        ::= { utsLagExtDot3adAggEntry 9 }

--
-- To display mac address for the link aggregation ports
--

	utsLagExtLinkAggMacTable OBJECT-TYPE
		SYNTAX      SEQUENCE OF UtsLagExtLinkAggMacEntry
		MAX-ACCESS  not-accessible
		STATUS      current
		DESCRIPTION
			"lagMIB UtExt LinkAggMac Table."
		::= { utsEthIfExtObjects 3 }

	utsLagExtLinkAggMacEntry OBJECT-TYPE
		SYNTAX       UtsLagExtLinkAggMacEntry
		MAX-ACCESS   not-accessible
		STATUS       current
		DESCRIPTION
			"An entry in the lagMIB extension table."
		INDEX
		{
			utsLagExtLinkAggMacAddress,utsLagExtLinkAggMacVlanId
		}
		::= { utsLagExtLinkAggMacTable 1 }

	UtsLagExtLinkAggMacEntry ::=
		SEQUENCE {
			utsLagExtLinkAggMacInterface			DisplayString,
			utsLagExtLinkAggMacModule           INTEGER,
			utsLagExtLinkAggMacPort             INTEGER,
			utsLagExtLinkAggMacVlanId           INTEGER,
			utsLagExtLinkAggMacIsStatic         INTEGER,
			utsLagExtLinkAggMacIntfType		   INTEGER,
			utsLagExtLinkAggMacTrunkId          INTEGER,
			utsLagExtLinkAggMacAddress          MacAddress,
			utsLagExtLinkAggStatus		    		RowStatus
		}


	utsLagExtLinkAggMacInterface  OBJECT-TYPE
		SYNTAX  DisplayString (SIZE(0..32))
		MAX-ACCESS  read-only
		STATUS  current
		DESCRIPTION
			"interface name string when showing mac address table."
		::= { utsLagExtLinkAggMacEntry 1 }

	utsLagExtLinkAggMacModule OBJECT-TYPE
		SYNTAX  INTEGER
		MAX-ACCESS  read-create
		STATUS  current
		DESCRIPTION
			"The Module number of the learned mac address entry."
		::= { utsLagExtLinkAggMacEntry 2 }

	utsLagExtLinkAggMacPort OBJECT-TYPE
		SYNTAX  INTEGER
		MAX-ACCESS  read-create
		STATUS  current
		DESCRIPTION
			"The port number from which this mac address was learned. Only
            when utsLagExtLinkAggMacBelongToTrunk is false."
		::= { utsLagExtLinkAggMacEntry 3 }

	utsLagExtLinkAggMacVlanId OBJECT-TYPE
		SYNTAX  INTEGER
		MAX-ACCESS  read-create
		STATUS  current
		DESCRIPTION
			"The vlan id of the learned mac address entry."
		::= { utsLagExtLinkAggMacEntry 4 }

	utsLagExtLinkAggMacIsStatic OBJECT-TYPE
		SYNTAX  INTEGER {
			true(1),
			false(2)
		}
		MAX-ACCESS  read-create
		STATUS  current
		DESCRIPTION
			"A flag to show where the mac address is static."
		::= { utsLagExtLinkAggMacEntry 5 }

	utsLagExtLinkAggMacIntfType OBJECT-TYPE
		SYNTAX  INTEGER {
			belongtotrunk(1),
			normal-port(2),
			cpu(3)
		}
		MAX-ACCESS  read-create
		STATUS  current
		DESCRIPTION
			"A flag indicating whether this mac address belongs to a trunk or other.
            if it is belongtotrunk, the utsLagExtLinkAggMacTrunkId will be relevant
            and the utsLagExtLinkAggMacPort should be ignored.  if the value
            of this flag is normal-port, this mac address belongs to an individual
            port, not to a trunk.  The object utsLagExtLinkAggMacPort then
            contains the valid port number from which this address was learned
            from. The trunkId in this case should be ignored.  if the value is cpu(3),
            utsLagExtLinkAggMacTrunkId and utsLagExtLinkAggMacPort is not used, and it is not configurable."
		::= { utsLagExtLinkAggMacEntry 6 }

	utsLagExtLinkAggMacTrunkId OBJECT-TYPE
		SYNTAX  INTEGER
		MAX-ACCESS  read-create
		STATUS  current
		DESCRIPTION
			"The Trunk id of the learned mac address.  Only valid when
            utsLagExtLinkAggMacBelongToTrunk is true."
		::= { utsLagExtLinkAggMacEntry 7 }

	utsLagExtLinkAggMacAddress OBJECT-TYPE
		SYNTAX  MacAddress
		MAX-ACCESS  read-create
		STATUS  current
		DESCRIPTION
			"The physical address of the learned mac address entry."
		::= { utsLagExtLinkAggMacEntry 8 }

	utsLagExtLinkAggStatus OBJECT-TYPE
		SYNTAX         RowStatus
	   MAX-ACCESS     read-create
      STATUS         current
      DESCRIPTION
      	"Row status for the current entry. "
      ::= { utsLagExtLinkAggMacEntry 9 }


-- the utsLagExtDot1qVlan table
-- implemented by those lag that support the IEEE 802.1q
-- Vlan

       utsLagExtDot1qVlanTable OBJECT-TYPE
          SYNTAX SEQUENCE OF UtsLagExtDot1qVlanEntry
          MAX-ACCESS not-accessible
          STATUS current
          DESCRIPTION
             "lagMIB UtExt Dot1q Vlan Table."
          ::= { utsEthIfExtObjects 4 }

       utsLagExtDot1qVlanEntry OBJECT-TYPE
          SYNTAX UtsLagExtDot1qVlanEntry
          MAX-ACCESS not-accessible
          STATUS current
          DESCRIPTION
             "An entry in the lagMIB extension table for vlan."
          INDEX	{ utsLagExtDot1qVlanIndex }
       ::= { utsLagExtDot1qVlanTable 1 }


       UtsLagExtDot1qVlanEntry ::=
          SEQUENCE {
             utsLagExtDot1qVlanIndex                 INTEGER,
             utsLagExtDot1qVlanName                  DisplayString,
             utsLagExtDot1qVlanPortListPorts         OCTET STRING,
             utsLagExtDot1qVlanTaggedPortListPorts   OCTET STRING,
             utsLagExtDot1qVlanPortVidListPorts      OCTET STRING,
             utsLagExtDot1qVlanStatus                RowStatus,
	     		 utsLagExtDot1qVlanUnTaggedPortListPorts OCTET STRING,
	     		 utsLagExtDot1qVlanIgmpSnoop	           INTEGER,
	     		 utsEponDot1qVlanStpBridgeEnable	        INTEGER,
                 utsLagExtDot1qVlanPPPoEPlus               INTEGER,
                 utsLagExtDot1qVlanL2DHCPOption82          INTEGER,
                 utsLagExtDot1qVlanArpProxySwitch          INTEGER
          }

   utsLagExtDot1qVlanIndex OBJECT-TYPE
      SYNTAX      INTEGER (1..4094)
      MAX-ACCESS  read-create
      STATUS      current
      DESCRIPTION
         "An indication of what vlan index of the 802.1q is running."
      ::= { utsLagExtDot1qVlanEntry 1 }


   utsLagExtDot1qVlanName OBJECT-TYPE
      SYNTAX DisplayString (SIZE(0..16))
      MAX-ACCESS read-create
      STATUS current
      DESCRIPTION
         "Specify the name of the vlan group."
      ::= { utsLagExtDot1qVlanEntry 2 }

   utsLagExtDot1qVlanPortListPorts OBJECT-TYPE
      SYNTAX      OCTET STRING
      MAX-ACCESS  read-only
      STATUS      current
      DESCRIPTION
         "Each octet within this value specifies a set of eight ports, with the
         first octet specifying ports 1 through 8, the second octet specifying
         ports 9 through 16, etc.  Within each octet, the most significant bit
         represents the lowest numbered port, and the least significant bit
         represents the highest numbered port.  Thus, each port of the bridge
         is represented by a single bit within the value of this object.  If that
         bit has a value of '1' then that port is included in the set of ports;
         the port is not included if its bit has a value of '0'."
      ::= { utsLagExtDot1qVlanEntry 3 }

   utsLagExtDot1qVlanTaggedPortListPorts OBJECT-TYPE
      SYNTAX      OCTET STRING
      MAX-ACCESS  read-create
      STATUS      current
      DESCRIPTION
         "Each octet within this value specifies a set of eight ports, with the
         first octet specifying ports 1 through 8, the second octet specifying
         ports 9 through 16, etc.  Within each octet, the most significant bit
         represents the lowest numbered port, and the least significant bit
         represents the highest numbered port.  Thus, each port of the bridge
         is represented by a single bit within the value of this object.  If that
         bit has a value of '1' then that port is included in the set of ports;
         the port is not included if its bit has a value of '0'."
   ::= { utsLagExtDot1qVlanEntry 4 }


   utsLagExtDot1qVlanPortVidListPorts OBJECT-TYPE
      SYNTAX         OCTET STRING
      MAX-ACCESS     read-create
      STATUS         current
      DESCRIPTION
         "Specify the member of the current vlan whose port based
         vlan id is also vlan id, it must be subnet of port lists."
      ::= { utsLagExtDot1qVlanEntry 5 }

   utsLagExtDot1qVlanStatus OBJECT-TYPE
      SYNTAX         RowStatus
      MAX-ACCESS     read-create
      STATUS         current
      DESCRIPTION
         "Row status for the current entry. "
      ::= { utsLagExtDot1qVlanEntry 6 }

   utsLagExtDot1qVlanUnTaggedPortListPorts OBJECT-TYPE
      SYNTAX      OCTET STRING
      MAX-ACCESS  read-create
      STATUS      current
      DESCRIPTION
         "Each octet within this value specifies a set of eight ports, with the
         first octet specifying ports 1 through 8, the second octet specifying
         ports 9 through 16, etc.  Within each octet, the most significant bit
         represents the lowest numbered port, and the least significant bit
         represents the highest numbered port.  Thus, each port of the bridge
         is represented by a single bit within the value of this object.  If that
         bit has a value of '1' then that port is included in the set of ports;
         the port is not included if its bit has a value of '0'."
   ::= { utsLagExtDot1qVlanEntry 7 }


   utsLagExtDot1qVlanIgmpSnoop OBJECT-TYPE
       SYNTAX      INTEGER
               {
                  enable(1),
                  disable(2)
               }
       MAX-ACCESS  read-create
       STATUS      current
       DESCRIPTION
          "indicate whether or not igmp snooping is running for this vlan id."
   ::= { utsLagExtDot1qVlanEntry 8 }

   utsEponDot1qVlanStpBridgeEnable OBJECT-TYPE
       SYNTAX      INTEGER
               {
                  enable(1),
                  disable(2)
               }
       MAX-ACCESS  read-create
       STATUS      current
       DESCRIPTION
          "Enable or disable the stp protocol for configured VLAN ID,
          disable will remove a entry in stp table, enable will add a entry in stp table"
   ::= { utsLagExtDot1qVlanEntry 9 }
   utsLagExtDot1qVlanPPPoEPlus OBJECT-TYPE
       SYNTAX      INTEGER
               {
                  enable(1),
                  disable(2)
               }
       MAX-ACCESS  read-create
       STATUS      current
       DESCRIPTION
          "indicate whether or not PPPoE plus is running for this vlan id."
   ::= { utsLagExtDot1qVlanEntry 10 }

   utsLagExtDot1qVlanL2DHCPOption82 OBJECT-TYPE
       SYNTAX      INTEGER
               {
                  enable(1),
                  disable(2)
               }
       MAX-ACCESS  read-create
       STATUS      current
       DESCRIPTION
          "indicate whether or not L2 mode DHCP option82 is running for this vlan id."
   ::= { utsLagExtDot1qVlanEntry 11 }

   utsLagExtDot1qVlanArpProxySwitch OBJECT-TYPE
       SYNTAX      INTEGER
               {
                  enable(1),
                  disable(2)
               }
       MAX-ACCESS  read-create
       STATUS      current
       DESCRIPTION
          "indicate whether or not arp proxy in this sub vlan, if want to enalbe the precondition is the vlan
           is sub-vlan and the according the svi of super vlan is valid."
   ::= { utsLagExtDot1qVlanEntry 12 }

--
--  Layer 2 conf ext
--

   utsLayer2ConfExt	OBJECT IDENTIFIER ::= { utsEthIfExtObjects 5 }

   utsLay2MulticastExt	OBJECT IDENTIFIER ::= { utsLayer2ConfExt 1 }

   utsEponMulticastCtrlGroup OBJECT IDENTIFIER ::= { utsLay2MulticastExt 1 }

--   utsIgmpSnoopingQueryInterval OBJECT-TYPE
--		SYNTAX  INTEGER
--		MAX-ACCESS  read-write
--		STATUS  current
--		DESCRIPTION
--			"Igmp snooping interval b/w general queries(in secs)."
--        ::= { utsIgmpSnoopingGroup 1 }

--   utsIgmpSnoopingAnxiousTimer OBJECT-TYPE
--		SYNTAX  INTEGER
--		MAX-ACCESS  read-write
--		STATUS  current
--		DESCRIPTION
--			"Igmp snooping anxious period timer(in seconds)."
--        ::= { utsIgmpSnoopingGroup 2 }

--   utsIgmpSnoopingV1HostTimer OBJECT-TYPE
--		SYNTAX  INTEGER
--		MAX-ACCESS  read-write
--		STATUS  current
--		DESCRIPTION
--			"Igmp snooping version 1 host timer(in seconds)."
--        ::= { utsIgmpSnoopingGroup 3 }

--   utsIgmpSnoopingRobustness OBJECT-TYPE
--		SYNTAX  INTEGER
--		MAX-ACCESS  read-write
--		STATUS  current
--		DESCRIPTION
--			"Igmp snooping robustness variable."
--        ::= { utsIgmpSnoopingGroup 4 }

--   utsIgmpSnoopingReportSuppression OBJECT-TYPE
--		SYNTAX  INTEGER
--		{
--				enabled(1),
--				disabled(2)
--		}
--		MAX-ACCESS  read-write
--		STATUS  current
--		DESCRIPTION
--			"Igmp snooping report suppression is enabled or not."
--        ::= { utsIgmpSnoopingGroup 5 }

   utsEponMulticastCtrlIpmcEnable OBJECT-TYPE
		SYNTAX  INTEGER
		{
				enabled(1),
				disabled(2)
		}
		MAX-ACCESS  read-write
		STATUS  current
		DESCRIPTION
			"global Igmp snooping ipmc is enabled or not."
        ::= { utsEponMulticastCtrlGroup 6 }

   utsEponMulticastCtrlIgmpSnoopingStatus OBJECT-TYPE
		SYNTAX  INTEGER
		{
				enabled(1),
				disabled(2)
		}
		MAX-ACCESS  read-write
		STATUS  current
		DESCRIPTION
			"global Igmp snooping is enabled or not."
        ::= { utsEponMulticastCtrlGroup 7 }

   utsEponMcastCtrlIgmpProxyStatus OBJECT-TYPE
		SYNTAX  INTEGER
		{
				enabled(1),
				disabled(2)
		}
		MAX-ACCESS  read-write
		STATUS  current
		DESCRIPTION
			"Igmp proxy is enabled or not."
        ::= { utsEponMulticastCtrlGroup 8 }

   utsEponMulticastCtrlSuperVidList OBJECT-TYPE
      SYNTAX         OCTET STRING(SIZE(0..512))
      MAX-ACCESS     read-write
      STATUS         current
      DESCRIPTION
         "Specify the vlan id for which the multicast function is enabled.
          Each octet within this value specifies a set of eight vlan, with the
         first octet specifying ports 1 through 8, the second octet specifying
         ports 9 through 16, etc.  Within each octet, the most significant bit
         represents the lowest numbered vlan, and the least significant bit
         represents the highest numbered vlan.  Thus, each port of the bridge
         is represented by a single bit within the value of this object.  If that
         bit has a value of '1' then that port is included in the set of vlans;
         the vlan is not included if its bit has a value of '0'."
      ::= { utsEponMulticastCtrlGroup 9 }



--
-- monitor session
--

   utsMonitorSessionGroup OBJECT IDENTIFIER ::= { utsLayer2ConfExt 2 }

   utsMonitorSessionModule OBJECT-TYPE
		SYNTAX  INTEGER
		MAX-ACCESS  read-write
		STATUS  current
		DESCRIPTION
			"Monitor session control module number."
        ::= { utsMonitorSessionGroup 1 }


   utsMonitorSessionPort OBJECT-TYPE
		SYNTAX  INTEGER
		MAX-ACCESS  read-write
		STATUS  current
		DESCRIPTION
			"Monitor session control port umber."
        ::= { utsMonitorSessionGroup 2 }


   utsMonitorSessionIngressPortBitLists OBJECT-TYPE
		SYNTAX  OCTET STRING(SIZE(0..16))
		MAX-ACCESS  read-write
		STATUS  current
		DESCRIPTION
			"Monitor session control ingress port bit lists ."
        ::= { utsMonitorSessionGroup 3 }


   utsMonitorSessionEngressPortBitLists OBJECT-TYPE
		SYNTAX  OCTET STRING(SIZE(0..16))
		MAX-ACCESS  read-write
		STATUS  current
		DESCRIPTION
			"Monitor session control ingress port bit lists ."
        ::= { utsMonitorSessionGroup 4 }

--
-- gigaethernet interface rate control (port mirroring)
-- rename UtsIntfRateControlEntry ?

utsIntfRateControlObjects OBJECT IDENTIFIER ::= { utsLayer2ConfExt 3 }

utsIntfRateControlTable OBJECT-TYPE
SYNTAX  SEQUENCE OF UtsIntfRateControlEntry
        MAX-ACCESS  not-accessible
        STATUS  current
        DESCRIPTION
"Table for interface rate control MIB objects."
        ::= { utsIntfRateControlObjects 1 }

utsIntfRateControlEntry OBJECT-TYPE
SYNTAX  UtsIntfRateControlEntry
       MAX-ACCESS  not-accessible
       STATUS  current
       DESCRIPTION
"An entry in the interface rate control MIB table."
       INDEX  {utsIntfRateControlModuleId, utsIntfRateControlPortId  }
       ::= { utsIntfRateControlTable 1 }

UtsIntfRateControlEntry ::=
       SEQUENCE {
          utsIntfRateControlModuleId				INTEGER,
          utsIntfRateControlPortId					INTEGER,
          utsIntfRateControlMcastEnable	  		    INTEGER,
          utsIntfRateControlMcastLimit				INTEGER,
          utsIntfRateControlBcastEnable			    INTEGER,
          utsIntfRateControlBcastLimit				INTEGER,
          utsIntfRateControlUnicastEnable			INTEGER,
          utsIntfRateControlUnicastLimit			INTEGER,
          utsIntfRateLimitIngressBandwidth		    INTEGER,
          utsIntfRateLimitEgressBandwidth			INTEGER,
          utsIntfRateControlMaxFrameSize			INTEGER,
          utsIntfRateControlIsolationCtrl			INTEGER,
          utsIntfRateControlUplinkSpeed  			INTEGER,
          utsIntfRateControlVlanIngressFilter		INTEGER,
          utsIntfRateControlUplinkTranceiverType    INTEGER,
          utsIntfRateControlAutoNegotiation         INTEGER,
          utsIntfRateLimitIngressBurstSize           INTEGER,
          utsIntfRateLimitEgressBurstSize           INTEGER,
          utsIntfRateControlUplinkDuplexStatus      INTEGER,
          utsIntfRateControlUplinkPortMode          INTEGER
       }


utsIntfRateControlModuleId OBJECT-TYPE
SYNTAX  INTEGER
       MAX-ACCESS  read-only
       STATUS  current
       DESCRIPTION
"A value that identifies the interface rate control module index"
        ::= { utsIntfRateControlEntry 1 }


utsIntfRateControlPortId OBJECT-TYPE
SYNTAX  INTEGER
       MAX-ACCESS  read-only
       STATUS  current
       DESCRIPTION
"A value that identifies the interface rate control port index"
        ::= { utsIntfRateControlEntry 2 }


utsIntfRateControlMcastEnable OBJECT-TYPE
SYNTAX  INTEGER
	{
	   enabled(1),
 	   disabled(2)
        }
       MAX-ACCESS  read-write
       STATUS  current
       DESCRIPTION
"A value that identifies the interface rate control multi-cast enbaled or disabled flag."
        ::= { utsIntfRateControlEntry 3 }


utsIntfRateControlMcastLimit OBJECT-TYPE
SYNTAX  INTEGER (0..33550000)
       MAX-ACCESS  read-write
       STATUS  current
       DESCRIPTION
"A value that identifies the interface rate control multi-cast rate limit, unit is pps."
        ::= { utsIntfRateControlEntry 4 }



utsIntfRateControlBcastEnable OBJECT-TYPE
SYNTAX  INTEGER
		{
			enabled(1),
 			disabled(2)
        }
       MAX-ACCESS  read-write
       STATUS  current
       DESCRIPTION
"A value that identifies the interface rate control broadcast enbaled or disabled flag."
        ::= { utsIntfRateControlEntry 5 }


utsIntfRateControlBcastLimit OBJECT-TYPE
SYNTAX  INTEGER (0..33550000)
       MAX-ACCESS  read-write
       STATUS  current
       DESCRIPTION
"A value that identifies the interface rate control broadcast rate limit, unit is pps."
        ::= { utsIntfRateControlEntry 6 }


utsIntfRateControlUnicastEnable OBJECT-TYPE
SYNTAX  INTEGER
		{
			enabled(1),
 			disabled(2)
        }
       MAX-ACCESS  read-write
       STATUS  current
       DESCRIPTION
"A value that identifies the interface rate control uni-cast enbaled or disabled flag."
        ::= { utsIntfRateControlEntry 7 }


utsIntfRateControlUnicastLimit OBJECT-TYPE
SYNTAX  INTEGER (0..33550000)
       MAX-ACCESS  read-write
       STATUS  current
       DESCRIPTION
          "A value that identifies the interface rate control uni-cast rate limit, unit is pps."
        ::= { utsIntfRateControlEntry 8 }

utsIntfRateLimitIngressBandwidth OBJECT-TYPE
SYNTAX  INTEGER (1..1000)
       MAX-ACCESS  read-write
       STATUS  current
       DESCRIPTION
          "A value that identifies the switch giga Ethernet interface ingress rate control.
           From 1 to 1000M with a granularity of 1M. this attribute will be affected by the
           value of utsIntRateControlUplinkSpeed. the default value is the max physical speed
           of this port."
        ::= { utsIntfRateControlEntry 9 }

utsIntfRateLimitEgressBandwidth OBJECT-TYPE
SYNTAX  INTEGER (1..1000)
       MAX-ACCESS  read-write
       STATUS  current
       DESCRIPTION
          "A value that identifies the switch giga Ethernet interface egress rate control.
           From 1 to 1000M with a granularity of 1M. this attribute will be affected by
           the value of utsIntRateControlUplinkSpeed. the default value is the max physical
           speed of this port."
        ::= { utsIntfRateControlEntry 10 }

utsIntfRateControlMaxFrameSize OBJECT-TYPE
SYNTAX  INTEGER (64..16383)
       MAX-ACCESS  read-write
       STATUS  current
       DESCRIPTION
           "BBS1000/1000+: Max accepted frame size setting for each GE port, all the frame size greater than it
            will be dropped.  (Max-frame 64-16383). the default value 1536.
            BBS4000: not applicable.
            "
        ::= { utsIntfRateControlEntry 11 }

utsIntfRateControlIsolationCtrl OBJECT-TYPE
    SYNTAX INTEGER
    {
        enable(1),
        disable(2)
    }
    MAX-ACCESS  read-write
    STATUS current
    DESCRIPTION
         "User traffic isolation control. Control for enable or disable the traffic talking between different OLTs. For downlink port only."
    DEFVAL {disable}
    ::= { utsIntfRateControlEntry 12 }

 -- zhaoxf Dec 26 2005

utsIntfRateControlUplinkSpeed OBJECT-TYPE
    SYNTAX INTEGER
    {
        ten-mega(10),
        hundred-mega(100),
        giga-mega(1000)
    }
    MAX-ACCESS  read-write
    STATUS current
    DESCRIPTION
         "configure bbs1000 uplink port maximum physical speed, only apply to uplink port. "
    DEFVAL {giga-mega}
    ::= { utsIntfRateControlEntry 13 }

utsIntfRateControlVlanIngressFilter OBJECT-TYPE
    SYNTAX INTEGER
    {
        enable(1),
        disable(2)
    }
    MAX-ACCESS  read-write
    STATUS current
    DESCRIPTION
         "Enable gigaEthernet port vlan ingress filtering. When enables Ingress Filtering for this port.
          then the ingress port discards any frame received on that port whose VLAN classification does
          not include that port in its member set. The default value is 0, that is, disable Ingress
          Filtering on that port."
    DEFVAL{enable}
    ::= { utsIntfRateControlEntry 14 }

utsIntfRateControlUplinkTranceiverType OBJECT-TYPE
    SYNTAX INTEGER
    {
        optical(1),
        copper(2)
    }
    MAX-ACCESS  read-only
    STATUS current
    DESCRIPTION
         "The tranceiver type.
          Note: BBS4000 GEM04A only support copper;
         "
    -- DEFVAL()
    ::= { utsIntfRateControlEntry 15 }

utsIntfRateControlAutoNegotiation OBJECT-TYPE
    SYNTAX INTEGER
    {
        enable(1),
        disable(2)
    }
    MAX-ACCESS  read-write
    STATUS current
    DESCRIPTION
         "Enable or disable the phyical port auto negotiation. For uplink port only."
    DEFVAL{ enable }
    ::= { utsIntfRateControlEntry 16 }

utsIntfRateLimitIngressBurstSize OBJECT-TYPE
    SYNTAX INTEGER
    MAX-ACCESS  read-write
    STATUS current
    DESCRIPTION
         "The burst size of ingress.
          For BBS1000/1000+ The validate value range is 4|8|16|32|64|128|256|512;
          For BBS4000 The validate value range is 0~13, (0: disable, others: 32Kbits * 2^(x-1)."
    -- DEFVAL()
    ::= { utsIntfRateControlEntry 17 }

utsIntfRateLimitEgressBurstSize OBJECT-TYPE
    SYNTAX INTEGER (4..512)
    MAX-ACCESS  read-write
    STATUS current
    DESCRIPTION
         "The burst size of egress.
         For BBS1000/1000+ The validate value range is 4|8|16|32|64|128|256|512;
         For BBS4000 The validate value range is 0~13, (0: disable, others: 32Kbits * 2^(x-1)."
    -- DEFVAL()
    ::= { utsIntfRateControlEntry 18 }

utsIntfRateControlUplinkDuplexStatus OBJECT-TYPE
    SYNTAX INTEGER
    {
        full-duplex(1),
        half-duplex(2)
    }
    MAX-ACCESS  read-write
    STATUS current
    DESCRIPTION
         "Set the duplex status of the port. For uplink port only."
    DEFVAL{full-duplex}
    ::= { utsIntfRateControlEntry 19 }



-- Lay 2 span tree protocol(STP/RSTP) MIB


utsEponBridgeObjects OBJECT IDENTIFIER ::= { utsLayer2ConfExt 4 }

utsEponDot1dStpTable OBJECT-TYPE
SYNTAX  SEQUENCE OF UtsEponDot1dStpEntry
        MAX-ACCESS  not-accessible
        STATUS  current
        DESCRIPTION
"Table for interface rate control MIB objects."
        ::= { utsEponBridgeObjects 1 }

utsEponDot1dStpEntry OBJECT-TYPE
SYNTAX  UtsEponDot1dStpEntry
       MAX-ACCESS  not-accessible
       STATUS  current
       DESCRIPTION
"An entry in the epon 802.1d stp MIB table."
       INDEX  {utsEponDot1dStpBridgeVlanID  }
       ::= { utsEponDot1dStpTable 1 }

UtsEponDot1dStpEntry ::=
       SEQUENCE {
       	utsEponDot1dStpBridgeVlanID			INTEGER,
         utsDot1dStpPriority						INTEGER,
         utsDot1dStpTimeSinceTopologyChange	TimeTicks,
         utsDot1dStpTopChanges					Counter,
         utsDot1dStpDesignatedRoot				BridgeId,
         utsDot1dStpRootCost						INTEGER,
         utsDot1dStpRootPort						INTEGER,
         utsDot1dStpMaxAge							Timeout,
         utsDot1dStpHelloTime						Timeout,
         utsDot1dStpHoldTime						INTEGER,
         utsDot1dStpForwardDelay					Timeout,
         utsDot1dStpBridgeMaxAge					Timeout,
         utsDot1dStpBridgeHelloTime				Timeout,
		   utsDot1dStpBridgeForwardDelay			Timeout,
		   utsDot1dStpBridgeOwnBridgeID			BridgeId
       }

utsEponDot1dStpBridgeVlanID OBJECT-TYPE
    SYNTAX  INTEGER (1..4094)
    MAX-ACCESS  read-only
    STATUS  current
    DESCRIPTION
            "VLAN ID "
    ::= { utsEponDot1dStpEntry 1 }

utsDot1dStpPriority OBJECT-TYPE
    SYNTAX  INTEGER (0..65535)
    MAX-ACCESS  read-write
    STATUS  current
    DESCRIPTION
            "Bridge Priority, an Unsigned value used to represent the priority
             component of a Bridge Identifier. Valid Bridge Priorities are in the
             range 0 through 61 440, in steps of 4096."
    REFERENCE
            "IEEE 802.1D-1990: Section 4.5.3.7"
    ::= { utsEponDot1dStpEntry 2 }

utsDot1dStpTimeSinceTopologyChange OBJECT-TYPE
    SYNTAX  TimeTicks
    MAX-ACCESS  read-only
    STATUS  current
    DESCRIPTION
            "The time (in hundredths of a second) since the
            last time a topology change was detected by the
            bridge entity."
    REFERENCE
            "IEEE 802.1D-1990: Section 6.8.1.1.3"
    ::= { utsEponDot1dStpEntry 3 }

utsDot1dStpTopChanges OBJECT-TYPE
    SYNTAX  Counter
    MAX-ACCESS  read-only
    STATUS  current
    DESCRIPTION
            "The total number of topology changes detected by
            this bridge since the management entity was last
            reset or initialized."
    REFERENCE
            "IEEE 802.1D-1990: Section 6.8.1.1.3"
    ::= { utsEponDot1dStpEntry 4 }

utsDot1dStpDesignatedRoot OBJECT-TYPE
    SYNTAX  BridgeId
    MAX-ACCESS  read-only
    STATUS  current
    DESCRIPTION
            "The bridge identifier of the root of the spanning
            tree as determined by the Spanning Tree Protocol
            as executed by this node.  This value is used as
            the Root Identifier parameter in all Configuration
            Bridge PDUs originated by this node."
    REFERENCE
            "IEEE 802.1D-1990: Section 4.5.3.1"
    ::= { utsEponDot1dStpEntry 5 }

utsDot1dStpRootCost OBJECT-TYPE
    SYNTAX  INTEGER
    MAX-ACCESS  read-only
    STATUS  current
    DESCRIPTION
            "The cost of the path to the root as seen from
            this bridge."
    REFERENCE
            "IEEE 802.1D-1990: Section 4.5.3.2"
    ::= { utsEponDot1dStpEntry 6 }

utsDot1dStpRootPort OBJECT-TYPE
    SYNTAX  INTEGER
    MAX-ACCESS  read-only
    STATUS  current
    DESCRIPTION
            "The port number of the port which offers the
            lowest cost path from this bridge to the root
            bridge."
    REFERENCE
            "IEEE 802.1D-1990: Section 4.5.3.3"
    ::= { utsEponDot1dStpEntry 7 }

utsDot1dStpMaxAge OBJECT-TYPE
    SYNTAX  Timeout
    MAX-ACCESS  read-only
    STATUS  current
    DESCRIPTION
            "The maximum age of Spanning Tree Protocol
            information learned from the network on any port
            before it is discarded, in units of hundredths of
            a second.  This is the actual value that this
            bridge is currently using."
    REFERENCE
            "IEEE 802.1D-1990: Section 4.5.3.4"
    ::= { utsEponDot1dStpEntry 8 }

utsDot1dStpHelloTime OBJECT-TYPE
    SYNTAX  Timeout
    MAX-ACCESS  read-only
    STATUS  current
    DESCRIPTION
            "The amount of time between the transmission of
            Configuration bridge PDUs by this node on any port
            when it is the root of the spanning tree or trying
            to become so, in units of a second.
            This is the actual value that this bridge is
            currently using."
    REFERENCE
            "IEEE 802.1D-1990: Section 4.5.3.5"
    ::= { utsEponDot1dStpEntry 9 }

utsDot1dStpHoldTime OBJECT-TYPE
    SYNTAX  INTEGER
    MAX-ACCESS  read-only
    STATUS  current
    DESCRIPTION
            "This time value determines the interval length
            during which no more than two Configuration bridge
            PDUs shall be transmitted by this node, in units
            of a second."
    REFERENCE
            "IEEE 802.1D-1990: Section 4.5.3.14"
    ::= { utsEponDot1dStpEntry 10 }

utsDot1dStpForwardDelay OBJECT-TYPE
    SYNTAX  Timeout
    MAX-ACCESS  read-only
    STATUS  current
    DESCRIPTION
            "This time value, measured in units
            of a second, controls how fast a port changes its
            spanning state when moving towards the Forwarding
            state.  The value determines how long the port
            stays in each of the Listening and Learning
            states, which precede the Forwarding state.  This
            value is also used, when a topology change has
            been detected and is underway, to age all dynamic
            entries in the Forwarding Database.  [Note that
            this value is the one that this bridge is
            currently using, in contrast to
            dot1dStpBridgeForwardDelay which is the value that
            this bridge and all others would start using
            if/when this bridge were to become the root.]"
    REFERENCE
            "IEEE 802.1D-1990: Section 4.5.3.6"
    ::= { utsEponDot1dStpEntry 11 }

utsDot1dStpBridgeMaxAge OBJECT-TYPE
    SYNTAX  Timeout (6..40)
    MAX-ACCESS  read-write
    STATUS  current
    DESCRIPTION
            "The value that all bridges use for MaxAge when
            this bridge is acting as the root.  Note that
            802.1D-1990 specifies that the range for this
            parameter is related to the value of
            dot1dStpBridgeHelloTime. The granularity of this
            timer is specified by 802.1D-1990 to be 1 second.
            An agent may return a badValue error if a set is
            attempted to a value which is not a whole number
            of seconds."
    REFERENCE
            "IEEE 802.1D-1990: Section 4.5.3.8"
    ::= { utsEponDot1dStpEntry 12 }

utsDot1dStpBridgeHelloTime OBJECT-TYPE
    SYNTAX  Timeout (1..10)
    MAX-ACCESS  read-write
    STATUS  current
    DESCRIPTION
            "The value that all bridges use for HelloTime when
            this bridge is acting as the root.  The
            granularity of this timer is specified by 802.1D-
            1990 to be 1 second.  An agent may return a
            badValue error if a set is attempted to a value
            which is not a whole number of seconds."
    REFERENCE
            "IEEE 802.1D-1990: Section 4.5.3.9"
    ::= { utsEponDot1dStpEntry 13 }

utsDot1dStpBridgeForwardDelay OBJECT-TYPE
    SYNTAX  Timeout (4..30)
    MAX-ACCESS  read-write
    STATUS  current
    DESCRIPTION
            "The value that all bridges use for ForwardDelay
            when this bridge is acting as the root.  Note that
            802.1D-1990 specifies that the range for this
            parameter is related to the value of
            dot1dStpBridgeMaxAge.  The granularity of this
            timer is specified by 802.1D-1990 to be 1 second.
            An agent may return a badValue error if a set is
            attempted to a value which is not a whole number
            of seconds."
    REFERENCE
            "IEEE 802.1D-1990: Section 4.5.3.10"
    ::= { utsEponDot1dStpEntry 14 }

utsDot1dStpBridgeOwnBridgeID OBJECT-TYPE
    SYNTAX  BridgeId
    MAX-ACCESS  read-only
    STATUS  current
    DESCRIPTION
            "the bridge identifier of this swith."
    ::= { utsEponDot1dStpEntry 15 }


-- The Spanning Tree Port Table

utsEponDot1dStpPortTable OBJECT-TYPE
    SYNTAX  SEQUENCE OF UtsEponDot1dStpPortEntry
    MAX-ACCESS  not-accessible
    STATUS  current
    DESCRIPTION
            "A table that contains port-specific information
            for the Spanning Tree Protocol."
    ::= { utsEponBridgeObjects 2 }

utsEponDot1dStpPortEntry OBJECT-TYPE
    SYNTAX  UtsEponDot1dStpPortEntry
    MAX-ACCESS  not-accessible
    STATUS  current
    DESCRIPTION
            "A list of information maintained by every port
            about the Spanning Tree Protocol state for that
            port."
    INDEX   { utsEponDot1dStpPortIntfIndex, utsEponDot1dStpPortVlanID }
    ::= { utsEponDot1dStpPortTable 1 }

UtsEponDot1dStpPortEntry ::=
    SEQUENCE {
        utsEponDot1dStpPortIntfIndex
        		INTEGER,
        utsEponDot1dStpPortVlanID
            INTEGER,
        utsEponDot1dStpModuleID
            INTEGER,
        utsEponDot1dStpPortID
            INTEGER,
		  utsEponDot1dStpPortLagID
		      INTEGER,
        utsEponDot1dStpPortPriority
            INTEGER,
        utsEponDot1dStpPortState
            INTEGER,
        utsEponDot1dStpPortEnable
            INTEGER,
        utsEponDot1dStpPortPathCost
            INTEGER,
        utsEponDot1dStpPortDesignatedRoot
            BridgeId,
        utsEponDot1dStpPortDesignatedCost
            INTEGER,
        utsEponDot1dStpPortDesignatedBridge
            BridgeId,
        utsEponDot1dStpPortDesignatedPort
            OCTET STRING,
--        utsEponDot1dStpPortForwardTransitions
--            Counter,
        utsEponDot1dStpPortFastEnable
            INTEGER
    }

utsEponDot1dStpPortIntfIndex OBJECT-TYPE
   SYNTAX  INTEGER
	MAX-ACCESS   read-only
	STATUS       current
	DESCRIPTION
	   "The interface index denotes switch ports and link aggregations,
	    For 1000:The range is 1-44. 1-12 denotes switch ports and 13-44 denotes link aggregations.
	    For 4000:The range is 1-72. 1-48 denotes switch ports and 49-72 denotes link aggregations."
	::= { utsEponDot1dStpPortEntry  1 }

utsEponDot1dStpPortVlanID OBJECT-TYPE
    SYNTAX  INTEGER (1..4094)
    MAX-ACCESS  read-only
    STATUS  current
    DESCRIPTION
            "The vlan ID that will run stp protocol."
    REFERENCE
            "IEEE 802.1D-1990: Section 6.8.2.1.2"
    ::= { utsEponDot1dStpPortEntry 2 }

utsEponDot1dStpModuleID OBJECT-TYPE
    SYNTAX  INTEGER
    MAX-ACCESS  read-only
    STATUS  current
    DESCRIPTION
            "The port number of the port for which this entry
            contains Spanning Tree Protocol management
            information.
            For 1000: The range is 1-3.
            For 4000: The range is 1-12."
    REFERENCE
            "IEEE 802.1D-1990: Section 6.8.2.1.2"
    ::= { utsEponDot1dStpPortEntry 3 }

utsEponDot1dStpPortID OBJECT-TYPE
    SYNTAX  INTEGER (1..4)
    MAX-ACCESS  read-only
    STATUS  current
    DESCRIPTION
            "The port number of the port for which this entry
            contains Spanning Tree Protocol management
            information."
    REFERENCE
            "IEEE 802.1D-1990: Section 6.8.2.1.2"
    ::= { utsEponDot1dStpPortEntry 4 }

utsEponDot1dStpPortLagID OBJECT-TYPE
   SYNTAX       INTEGER
	MAX-ACCESS   read-only
	STATUS       current
	DESCRIPTION
	   "Link Aggregation Port Id on which STP is runing. "
	::= { utsEponDot1dStpPortEntry  5 }

utsEponDot1dStpPortPriority OBJECT-TYPE
    SYNTAX  INTEGER (0..240)
    MAX-ACCESS  read-write
    STATUS  current
    DESCRIPTION
            "The value of the priority field which is
            contained in the first (in network byte order)
            octet of the (2 octet long) Port ID.  The other
            octet of the Port ID is given by the value of
            dot1dStpPort."
    REFERENCE
            "IEEE 802.1D-1990: Section 4.5.5.1"
    ::= { utsEponDot1dStpPortEntry 6 }

utsEponDot1dStpPortState OBJECT-TYPE
    SYNTAX  INTEGER {
                disabled(1),
                blocking(2),
                listening(3),
                learning(4),
                forwarding(5),
                broken(6)
            }
    MAX-ACCESS  read-only
    STATUS  current
    DESCRIPTION
            "The port's current state as defined by
            application of the Spanning Tree Protocol.  This
            state controls what action a port takes on
            reception of a frame.  If the bridge has detected
            a port that is malfunctioning it will place that
            port into the broken(6) state.  For ports which
            are disabled (see dot1dStpPortEnable), this object
            will have a value of disabled(1)."
    REFERENCE
            "IEEE 802.1D-1990: Section 4.5.5.2"
    ::= { utsEponDot1dStpPortEntry 7 }

utsEponDot1dStpPortEnable OBJECT-TYPE
    SYNTAX  INTEGER {
                enabled(1),
                disabled(2)
            }
    MAX-ACCESS  read-only
    STATUS  current
    DESCRIPTION
            "The enabled/disabled status of the port."
    REFERENCE
            "IEEE 802.1D-1990: Section 4.5.5.2"
    ::= { utsEponDot1dStpPortEntry 8 }

utsEponDot1dStpPortPathCost OBJECT-TYPE
    SYNTAX  INTEGER (1..20000000)
    MAX-ACCESS  read-write
    STATUS  current
    DESCRIPTION
            "The contribution of this port to the path cost of
            paths towards the spanning tree root which include
            this port.  802.1D-1990 recommends that the
            default value of this parameter be in inverse
            proportion to the speed of the attached LAN."
    REFERENCE
            "IEEE 802.1D-1990: Section 4.5.5.3"
    ::= { utsEponDot1dStpPortEntry 9 }

utsEponDot1dStpPortDesignatedRoot OBJECT-TYPE
    SYNTAX  BridgeId
    MAX-ACCESS  read-only
    STATUS  current
    DESCRIPTION
            "The unique Bridge Identifier of the Bridge
            recorded as the Root in the Configuration BPDUs
            transmitted by the Designated Bridge for the
            segment to which the port is attached."
    REFERENCE
            "IEEE 802.1D-1990: Section 4.5.5.4"
    ::= { utsEponDot1dStpPortEntry 10 }

utsEponDot1dStpPortDesignatedCost OBJECT-TYPE
    SYNTAX  INTEGER
    MAX-ACCESS  read-only
    STATUS  current
    DESCRIPTION
            "The path cost of the Designated Port of the
            segment connected to this port.  This value is
            compared to the Root Path Cost field in received
            bridge PDUs."
    REFERENCE
            "IEEE 802.1D-1990: Section 4.5.5.5"
    ::= { utsEponDot1dStpPortEntry 11 }

utsEponDot1dStpPortDesignatedBridge OBJECT-TYPE
    SYNTAX  BridgeId
    MAX-ACCESS  read-only
    STATUS  current
    DESCRIPTION
            "The Bridge Identifier of the bridge which this
            port considers to be the Designated Bridge for
            this port's segment."
    REFERENCE
            "IEEE 802.1D-1990: Section 4.5.5.6"
    ::= { utsEponDot1dStpPortEntry 12 }

utsEponDot1dStpPortDesignatedPort OBJECT-TYPE
    SYNTAX  OCTET STRING
    MAX-ACCESS  read-only
    STATUS  current
    DESCRIPTION
            "The Port Identifier of the port on the Designated
            Bridge for this port's segment."
    REFERENCE
            "IEEE 802.1D-1990: Section 4.5.5.7"
    ::= { utsEponDot1dStpPortEntry 13 }

--utsEponDot1dStpPortForwardTransitions OBJECT-TYPE
--    SYNTAX  Counter
--    MAX-ACCESS  read-only
--    STATUS  current
--    DESCRIPTION
--            "The number of times this port has transitioned
--            from the Learning state to the Forwarding state."
--    ::= { utsEponDot1dStpPortEntry 14 }

utsEponDot1dStpPortFastEnable OBJECT-TYPE
    SYNTAX  INTEGER{enable(1),disable(2)}
    MAX-ACCESS  read-write
    STATUS  current
    DESCRIPTION
            "The number of times this port has transitioned
            from the Learning state to the Forwarding state."
    ::= { utsEponDot1dStpPortEntry 15 }


-- igmp snooping configuration

utsIgmpSnoopCfgObjects OBJECT IDENTIFIER ::= { utsLayer2ConfExt 5 }

utsIgmpSnoopCfgTable OBJECT-TYPE
SYNTAX  SEQUENCE OF UtsIgmpSnoopCfgEntry
        MAX-ACCESS  not-accessible
        STATUS  current
        DESCRIPTION
"Table for igmp snoop control MIB objects."
        ::= { utsIgmpSnoopCfgObjects 1 }

utsIgmpSnoopCfgEntry OBJECT-TYPE
   SYNTAX UtsIgmpSnoopCfgEntry
   MAX-ACCESS not-accessible
   STATUS current
   DESCRIPTION
      "An entry in the lagMIB extension table for vlan."
   INDEX	{ utsIgmpSnoopVlanId }
::= { utsIgmpSnoopCfgTable 1 }


UtsIgmpSnoopCfgEntry ::=
   SEQUENCE {
      utsIgmpSnoopVlanId                INTEGER,
      utsIgmpSnoopLastMembAgeTmr        INTEGER,
      utsIgmpSnoopMCAgeTmr        	INTEGER,
      utsIgmpSnoopRouterAgeTmr  	INTEGER,
      utsIgmpSnoopSrcOnlyMcAgeTmr     	INTEGER
   }

utsIgmpSnoopVlanId  OBJECT-TYPE
     SYNTAX      INTEGER
     MAX-ACCESS  read-only
     STATUS      current
     DESCRIPTION
        "An indication of what vlan index of the 802.1q is running."
     ::= { utsIgmpSnoopCfgEntry 1 }

utsIgmpSnoopLastMembAgeTmr  OBJECT-TYPE
     SYNTAX      INTEGER (1..65535)
     MAX-ACCESS  read-write
     STATUS      current
     DESCRIPTION
        "igmp last member age timer."
     ::= { utsIgmpSnoopCfgEntry 2 }

utsIgmpSnoopMCAgeTmr  OBJECT-TYPE
     SYNTAX      INTEGER (1..65535)
     MAX-ACCESS  read-write
     STATUS      current
     DESCRIPTION
        "igmp multicast cache item ageing time."
     ::= { utsIgmpSnoopCfgEntry 3 }

utsIgmpSnoopRouterAgeTmr  OBJECT-TYPE
     SYNTAX      INTEGER (1..65535)
     MAX-ACCESS  read-write
     STATUS      current
     DESCRIPTION
        "Configure Router Age Timer."
     ::= { utsIgmpSnoopCfgEntry 4 }

utsIgmpSnoopSrcOnlyMcAgeTmr  OBJECT-TYPE
     SYNTAX      INTEGER (1..65535)
     MAX-ACCESS  read-write
     STATUS      current
     DESCRIPTION
        "Configure Source Only Multicast Age Timer"
     ::= { utsIgmpSnoopCfgEntry 5 }


-- Add the monitor session by tomsong 20070906

--utsMonitorSessionObjects OBJECT IDENTIFIER ::= { utsLayer2ConfExt 6 }
--
--	utsMonitorSessionControlTable OBJECT-TYPE
--	SYNTAX  SEQUENCE OF UtsMonitorSessionControlEntry
--	        MAX-ACCESS  not-accessible
--	        STATUS  current
--	        DESCRIPTION
--			"Table for monitor session MIB objects."
--	        ::= { utsMonitorSessionObjects 1 }
--
--	utsMonitorSessionControlEntry OBJECT-TYPE
--	SYNTAX  UtsMonitorSessionControlEntry
--	       MAX-ACCESS  not-accessible
--	       STATUS  current
--	       DESCRIPTION
--		   "An entry in the monitor session control MIB table."
--	       INDEX  {utsMonitorSessionID }
--	       ::= { utsMonitorSessionControlTable 1 }
--
--	UtsMonitorSessionControlEntry ::=
--	       SEQUENCE {
--	          utsMonitorSessionID                   INTEGER,
--	          utsMonitorSessionModule				INTEGER,
--	          utsMonitorSessionPort					INTEGER,
--	          utsMonitorSessionIngressPortBitLists	  OCTET STRING,
--	          utsMonitorSessionEngressPortBitLists	  OCTET STRING,
--	          utsMonitorSessionActive				INTEGER,
--	          utsMonitorSessionRowStatus              RowStatus
--	       }
--
--	utsMonitorSessionID OBJECT-TYPE
--		SYNTAX  INTEGER(1..4)
--		MAX-ACCESS  read-create
--		STATUS  current
--		DESCRIPTION
--			"Monitor session ID."
--        ::= { utsMonitorSessionControlEntry 1 }
--
--	utsMonitorSessionModule OBJECT-TYPE
--		SYNTAX  INTEGER
--		MAX-ACCESS  read-write
--		STATUS  current
--		DESCRIPTION
--			"Monitor session control module number."
--        ::= { utsMonitorSessionControlEntry 2 }
--
--
--   utsMonitorSessionPort OBJECT-TYPE
--		SYNTAX  INTEGER
--		MAX-ACCESS  read-write
--		STATUS  current
--		DESCRIPTION
--			"Monitor session control port umber."
--        ::= { utsMonitorSessionControlEntry 3 }
--
--
--   utsMonitorSessionIngressPortBitLists OBJECT-TYPE
--		SYNTAX  OCTET STRING
--		MAX-ACCESS  read-write
--		STATUS  current
--		DESCRIPTION
--			"Monitor session control ingress port bit lists ."
--        ::= { utsMonitorSessionControlEntry 4 }
--
--
--   utsMonitorSessionEngressPortBitLists OBJECT-TYPE
--		SYNTAX  OCTET STRING
--		MAX-ACCESS  read-write
--		STATUS  current
--		DESCRIPTION
--			"Monitor session control ingress port bit lists ."
--        ::= { utsMonitorSessionControlEntry 5 }
--
--
--   utsMonitorSessionActive OBJECT-TYPE
--		SYNTAX  INTEGER
--		{
--			enable(1),
--			disable(2)
--		}
--		MAX-ACCESS  read-write
--		STATUS  current
--		DESCRIPTION
--			"Monitor session enable or disable."
--        ::= { utsMonitorSessionControlEntry 6 }
--
--
--   utsMonitorSessionRowStatus OBJECT-TYPE
--			SYNTAX RowStatus
--			MAX-ACCESS read-create
--			STATUS current
--			DESCRIPTION
--				"Row status"
--			::= { utsMonitorSessionControlEntry 7 }

--
-- SUPER SVI group
--


   utsLayer3ConfExt	OBJECT IDENTIFIER ::= { utsEthIfExtObjects 6 }

--   utsIntfSuperSVIGroup OBJECT IDENTIFIER ::= { utsLayer3ConfExt 1 }

   utsIntfSuperSVITable OBJECT-TYPE
   	SYNTAX SEQUENCE OF UtsIntfSuperSVIEntry
   	MAX-ACCESS not-accessible
   	STATUS current
   	DESCRIPTION
      	"Table for Super SVI Vlan entries"
   ::= { utsLayer3ConfExt 1 }

   utsIntfSuperSVIEntry OBJECT-TYPE
      SYNTAX UtsIntfSuperSVIEntry
      MAX-ACCESS not-accessible
      STATUS  current
      DESCRIPTION
         "An entry in the utsIntfSuperSVITable"
      INDEX  { utsIntfSuperSVIVlanId }
   ::= { utsIntfSuperSVITable 1 }


   UtsIntfSuperSVIEntry	::=
      SEQUENCE {
         utsIntfSuperSVIVlanId 				INTEGER,
         utsIntfSuperSVIVlanMemberBitmap 	OCTET STRING,
		 	utsIntfSuperSVIVlanRowStatus 		RowStatus
      }

   utsIntfSuperSVIVlanId OBJECT-TYPE
		SYNTAX  INTEGER
		MAX-ACCESS  read-create
		STATUS  current
		DESCRIPTION
			"Ethernet interface super vlan if number."
        ::= { utsIntfSuperSVIEntry 1 }


   utsIntfSuperSVIVlanMemberBitmap OBJECT-TYPE
		SYNTAX  OCTET STRING(SIZE(0..520))
		MAX-ACCESS  read-create
		STATUS  current
		DESCRIPTION
			"Ethernet interface super vlan if number."
        ::= { utsIntfSuperSVIEntry 2 }

   utsIntfSuperSVIVlanRowStatus OBJECT-TYPE
		SYNTAX  RowStatus
		MAX-ACCESS  read-create
		STATUS  current
		DESCRIPTION
			"Ethernet interface super vlan table row status."
        ::= { utsIntfSuperSVIEntry 3 }


--
-- L3 static route table
--

utsStaticRouteObjects OBJECT IDENTIFIER ::= { utsLayer3ConfExt 2 }

utsStaticRouteTable OBJECT-TYPE
SYNTAX  SEQUENCE OF UtsStaticRouteEntry
        MAX-ACCESS  not-accessible
        STATUS  current
        DESCRIPTION
"Table for interface static route MIB objects."
        ::= { utsStaticRouteObjects 1 }

utsStaticRouteEntry OBJECT-TYPE
SYNTAX  UtsStaticRouteEntry
       MAX-ACCESS  not-accessible
       STATUS  current
       DESCRIPTION
"An entry in the interface static route MIB table."
       INDEX  {utsStaticRouteIpAddress, utsStaticRouteSubnetMask, utsStaticRouteNextHop  }
       ::= { utsStaticRouteTable 1 }

UtsStaticRouteEntry ::=
       SEQUENCE {
                    utsStaticRouteIpAddress					IpAddress,
                    utsStaticRouteSubnetMask				IpAddress,
                    utsStaticRouteNextHop					IpAddress,
                    utsStaticRouteIfIndex					INTEGER,
                    utsStaticRouteMetric					INTEGER,
                    utsStaticRouteStatus					RowStatus
       }


utsStaticRouteIpAddress OBJECT-TYPE
SYNTAX  IpAddress
       MAX-ACCESS  read-create
       STATUS  current
       DESCRIPTION
"Static route entry's ip address."
        ::= { utsStaticRouteEntry 1 }


utsStaticRouteSubnetMask OBJECT-TYPE
SYNTAX  IpAddress
       MAX-ACCESS  read-create
       STATUS  current
       DESCRIPTION
"Static route entry's subnet mask."
        ::= { utsStaticRouteEntry 2 }


utsStaticRouteNextHop OBJECT-TYPE
SYNTAX  IpAddress
       MAX-ACCESS  read-create
       STATUS  current
       DESCRIPTION
"Static route entry's next hop's ip address."
        ::= { utsStaticRouteEntry 3 }



utsStaticRouteIfIndex OBJECT-TYPE
SYNTAX  INTEGER
       MAX-ACCESS  read-only
       STATUS  current
       DESCRIPTION
"Static route entry's interface number."
        ::= { utsStaticRouteEntry 4 }


utsStaticRouteMetric OBJECT-TYPE
SYNTAX  INTEGER (1..255)
       MAX-ACCESS  read-create
       STATUS  current
       DESCRIPTION
"Static route entry's metric, can not modify it after created. "
        ::= { utsStaticRouteEntry 5 }


utsStaticRouteStatus OBJECT-TYPE
SYNTAX  RowStatus
       MAX-ACCESS  read-create
       STATUS  current
       DESCRIPTION
"Static route entry's row status."
        ::= { utsStaticRouteEntry 6 }


--
--  DHCP global configuration
--


   utsLayer3DHCPExt	OBJECT IDENTIFIER ::= { utsLayer3ConfExt 3 }

   utsDHCPServiceGroup OBJECT IDENTIFIER ::= { utsLayer3DHCPExt 1 }

   utsDHCPServiceState OBJECT-TYPE
		SYNTAX  INTEGER
		{
				no-service(1),
				server-active(2),
				relay-active(3)
		}
		MAX-ACCESS  read-write
		STATUS  current
		DESCRIPTION
			"DHCP service type and state."
        ::= { utsDHCPServiceGroup 1 }

   utsDHCPRelayOption82 OBJECT-TYPE
		SYNTAX  INTEGER
		{
				enable(1),
				disable(2)
		}
		MAX-ACCESS  read-write
		STATUS  current
		DESCRIPTION
			"Enable The DHCP option82 operation."
        ::= { utsDHCPServiceGroup 2 }

   utsDHCPRelayInforChk OBJECT-TYPE
		SYNTAX  INTEGER
		{
				enable(1),
				disable(2)
		}
		MAX-ACCESS  read-write
		STATUS  current
		DESCRIPTION
			"Enable or disable DHCP security check."
        ::= { utsDHCPServiceGroup 3 }

   utsDHCPRelayPolicy OBJECT-TYPE
		SYNTAX  INTEGER
		{
				drop(1),
				keep(2),
				replace(3)
		}
		MAX-ACCESS  read-write
		STATUS  current
		DESCRIPTION
			"Dhcp relay option parameter ."
        ::= { utsDHCPServiceGroup 4 }

   utsDHCPRelayMaxhop OBJECT-TYPE
		SYNTAX  INTEGER	(1..15)
		MAX-ACCESS  read-write
		STATUS  current
		DESCRIPTION
			"Maximum hop between client and server."
        ::= { utsDHCPServiceGroup 5 }

   utsDHCPServiceMode OBJECT-TYPE
		SYNTAX  INTEGER
		{
				rfc2131(1),
				sbb(2)
		}
		MAX-ACCESS  read-write
		STATUS  current
		DESCRIPTION
			"dhcp server service mode selection"
        ::= { utsDHCPServiceGroup 6 }

 --  utsDHCPBindingClear OBJECT-TYPE
--		SYNTAX  INTEGER
--		{
  --          clearAllDynamic(1)
	--	}
	--	MAX-ACCESS  write-only
	--	STATUS  current
	--	DESCRIPTION
	--		"Clear DHCP binding for specific type."
      --  ::= { utsDHCPServiceGroup 10 }

 --  utsDHCPRelayClear OBJECT-TYPE
--		SYNTAX  INTEGER
--		{
  --          clearStatistics(1)
	--	}
	--	MAX-ACCESS  write-only
	--	STATUS  current
	--	DESCRIPTION
	--		"Clear DHCP relay agent statistics."
      --  ::= { utsDHCPServiceGroup 11 }

 --  utsDHCPServerClear OBJECT-TYPE
--		SYNTAX  INTEGER
--		{
  --          clearStatistics(1)
	--	}
	--	MAX-ACCESS  write-only
	--	STATUS  current
	--	DESCRIPTION
	--		"Clear DHCP server statistics."
      --  ::= { utsDHCPServiceGroup 12 }

--
-- DHCP POOL table
--


utsDHCPPoolTable OBJECT-TYPE
SYNTAX  SEQUENCE OF UtsDHCPPoolEntry
        MAX-ACCESS  not-accessible
        STATUS  current
        DESCRIPTION
"Table for dhcp pool MIB objects."
        ::= { utsLayer3DHCPExt 2 }

utsDHCPPoolEntry OBJECT-TYPE
SYNTAX  UtsDHCPPoolEntry
       MAX-ACCESS  not-accessible
       STATUS  current
       DESCRIPTION
"An entry in the DHCP pool MIB table."
       INDEX  { utsDHCPPoolName  }
       ::= { utsDHCPPoolTable 1 }

UtsDHCPPoolEntry ::=
       SEQUENCE {
         utsDHCPPoolName				DisplayString,
         utsDHCPPoolDomainName		    DisplayString,
         utsDHCPPoolNetworkAddress	    IpAddress,
         utsDHCPPoolNetworkMask		    IpAddress,
			utsDHCPPoolClassId			DisplayString,
         utsDHCPPoolLeaseTime			INTEGER,
			utsDHCPPoolMeritDump		DisplayString,
			utsDHCPPoolRootPath			DisplayString,
			utsDHCPPoolStatus           RowStatus
}

utsDHCPPoolName OBJECT-TYPE
SYNTAX  DisplayString (SIZE(0..63))
       MAX-ACCESS  read-create
       STATUS  current
       DESCRIPTION
"DHCP pool name. "
        ::= { utsDHCPPoolEntry 1 }


utsDHCPPoolDomainName OBJECT-TYPE
SYNTAX  DisplayString
       MAX-ACCESS  read-only
       STATUS  current
       DESCRIPTION
"DHCP domain name. "
        ::= { utsDHCPPoolEntry 2 }



utsDHCPPoolNetworkAddress OBJECT-TYPE
SYNTAX  IpAddress
       MAX-ACCESS  read-create
       STATUS  current
       DESCRIPTION
"DHCP pool network number. when create a pool entry, network address must provide. "
        ::= { utsDHCPPoolEntry 3 }


utsDHCPPoolNetworkMask OBJECT-TYPE
SYNTAX  IpAddress
       MAX-ACCESS  read-create
       STATUS  current
       DESCRIPTION
"DHCP pool network mask, when create a pool entry, network address must provide."
        ::= { utsDHCPPoolEntry 4 }

utsDHCPPoolClassId OBJECT-TYPE
SYNTAX  DisplayString
       MAX-ACCESS  read-create
       STATUS  current
       DESCRIPTION
"DHCP pool class id for VoIP pool"
        ::= { utsDHCPPoolEntry 5 }


utsDHCPPoolLeaseTime OBJECT-TYPE
SYNTAX  INTEGER
       MAX-ACCESS  read-create
       STATUS  current
       DESCRIPTION
"DHCP pool lease time in minutes,-1 means infinite"
        ::= { utsDHCPPoolEntry 6 }

utsDHCPPoolMeritDump OBJECT-TYPE
SYNTAX  DisplayString (SIZE(0..63))
       MAX-ACCESS  read-create
       STATUS  current
       DESCRIPTION
"DHCP pool path-name of a file to which the client's core image should be dumped in the event the client crashes."
        ::= { utsDHCPPoolEntry 7 }

utsDHCPPoolRootPath OBJECT-TYPE
SYNTAX  DisplayString (SIZE(0..63))
       MAX-ACCESS  read-create
       STATUS  current
       DESCRIPTION
"the path-name that contains the client's root disk."
        ::= { utsDHCPPoolEntry 8 }

utsDHCPPoolStatus OBJECT-TYPE
SYNTAX  RowStatus
       MAX-ACCESS  read-create
       STATUS  current
       DESCRIPTION
"DHCP pool entry status"
        ::= { utsDHCPPoolEntry 11 }


--
-- DHCP pool dns server table
--

utsDHCPPoolDnsServerTable OBJECT-TYPE
SYNTAX  SEQUENCE OF UtsDHCPPoolDnsServerEntry
        MAX-ACCESS  not-accessible
        STATUS  current
        DESCRIPTION
"Table for dhcp pool dns server MIB objects."
        ::= { utsLayer3DHCPExt 3 }

utsDHCPPoolDnsServerEntry OBJECT-TYPE
SYNTAX  UtsDHCPPoolDnsServerEntry
       MAX-ACCESS  not-accessible
       STATUS  current
       DESCRIPTION
"An entry in the DHCP pool dns server MIB table. maximum entries number is 8."
       INDEX  { utsDHCPPoolName, utsDHCPPoolDnsServerIpAddress  }
       ::= { utsDHCPPoolDnsServerTable 1 }

UtsDHCPPoolDnsServerEntry ::=
       SEQUENCE {
--         utsDHCPPoolDnsServerPoolName		DisplayString,
         utsDHCPPoolDnsServerIpAddress		IpAddress,
         utsDHCPPoolDnsServerDomainName	DisplayString,
         utsDHCPPoolDnsServerStatus	      RowStatus
}

--utsDHCPPoolDnsServerPoolName OBJECT-TYPE
--SYNTAX  DisplayString
--       MAX-ACCESS  read-only
--       STATUS  current
--       DESCRIPTION
--"DHCP dns server pool name. "
--        ::= { utsDHCPPoolDnsServerEntry 1 }

utsDHCPPoolDnsServerIpAddress OBJECT-TYPE
SYNTAX  IpAddress
       MAX-ACCESS  read-create
       STATUS  current
       DESCRIPTION
"DHCP pool dns server ip address."
        ::= { utsDHCPPoolDnsServerEntry 2 }

utsDHCPPoolDnsServerDomainName OBJECT-TYPE
SYNTAX  DisplayString
       MAX-ACCESS  read-only
       STATUS  current
       DESCRIPTION
"DHCP dns-server pool domain name. "
        ::= { utsDHCPPoolDnsServerEntry 3 }


utsDHCPPoolDnsServerStatus OBJECT-TYPE
SYNTAX  RowStatus
       MAX-ACCESS  read-create
       STATUS  current
       DESCRIPTION
"DHCP dns-server table entry status. "
        ::= { utsDHCPPoolDnsServerEntry 4 }

--
-- default router
--
-- DHCP pool default router table
--
--

utsDHCPPoolDefaultRouterTable OBJECT-TYPE
SYNTAX  SEQUENCE OF UtsDHCPPoolDefaultRouterEntry
        MAX-ACCESS  not-accessible
        STATUS  current
        DESCRIPTION
"Table for dhcp pool default router MIB objects."
        ::= { utsLayer3DHCPExt 4 }

utsDHCPPoolDefaultRouterEntry OBJECT-TYPE
SYNTAX  UtsDHCPPoolDefaultRouterEntry
       MAX-ACCESS  not-accessible
       STATUS  current
       DESCRIPTION
"An entry in the DHCP pool default router MIB table, maximum number is 1."
       INDEX  { utsDHCPPoolName, utsDHCPPoolDefaultRouterIpAddress  }
       ::= { utsDHCPPoolDefaultRouterTable 1 }

UtsDHCPPoolDefaultRouterEntry ::=
       SEQUENCE {
--          utsDHCPPoolDefaultRouterPoolName	DisplayString,
          utsDHCPPoolDefaultRouterIpAddress	IpAddress,
--          utsDHCPPoolDefaultRouterDomainName	DisplayString,
          utsDHCPPoolDefaultRouterStatus	   RowStatus
}

--utsDHCPPoolDefaultRouterPoolName OBJECT-TYPE
--SYNTAX  DisplayString
--       MAX-ACCESS  read-only
--       STATUS  current
--       DESCRIPTION
--"DHCP default router pool name. "
--        ::= { utsDHCPPoolDefaultRouterEntry 1 }



utsDHCPPoolDefaultRouterIpAddress OBJECT-TYPE
SYNTAX  IpAddress
       MAX-ACCESS  read-create
       STATUS  current
       DESCRIPTION
"DHCP pool default router ip address."
        ::= { utsDHCPPoolDefaultRouterEntry 2 }


--utsDHCPPoolDefaultRouterDomainName OBJECT-TYPE
--SYNTAX  DisplayString
--       MAX-ACCESS  read-only
--       STATUS  current
--       DESCRIPTION
--"DHCP default router pool domain name. "
--        ::= { utsDHCPPoolDefaultRouterEntry 3 }


utsDHCPPoolDefaultRouterStatus OBJECT-TYPE
SYNTAX  RowStatus
       MAX-ACCESS  read-create
       STATUS  current
       DESCRIPTION
"DHCP default router entry status "
        ::= { utsDHCPPoolDefaultRouterEntry 4 }


--
-- DHCP pool excluded address table
--

utsDHCPPoolExcludedTable OBJECT-TYPE
SYNTAX  SEQUENCE OF UtsDHCPPoolExcludedEntry
        MAX-ACCESS  not-accessible
        STATUS  current
        DESCRIPTION
"Table for dhcp pool excluded MIB objects."
        ::= { utsLayer3DHCPExt 5 }

utsDHCPPoolExcludedEntry OBJECT-TYPE
SYNTAX  UtsDHCPPoolExcludedEntry
       MAX-ACCESS  not-accessible
       STATUS  current
       DESCRIPTION
           "An entry in the DHCP pool excluded MIB table, maximum entries is 8."
       INDEX  { utsDHCPPoolName, utsDHCPPoolExcludedLowIpAddress }
       ::= { utsDHCPPoolExcludedTable 1 }

UtsDHCPPoolExcludedEntry ::=
       SEQUENCE {
--          utsDHCPPoolExcludedPoolName		DisplayString,
          utsDHCPPoolExcludedLowIpAddress	IpAddress,
          utsDHCPPoolExcludedHighIpAddress	IpAddress,
--          utsDHCPPoolExcludedDomainName		DisplayString,
          utsDHCPPoolExcludedStatus     	RowStatus
}

--utsDHCPPoolExcludedPoolName OBJECT-TYPE
--SYNTAX  DisplayString
--       MAX-ACCESS  read-only
--       STATUS  current
--       DESCRIPTION
--"DHCP excluded address pool name. "
--        ::= { utsDHCPPoolExcludedEntry 1 }



utsDHCPPoolExcludedLowIpAddress OBJECT-TYPE
SYNTAX  IpAddress
       MAX-ACCESS  read-create
       STATUS  current
       DESCRIPTION
"DHCP pool excluded low ip address."
        ::= { utsDHCPPoolExcludedEntry 2 }



utsDHCPPoolExcludedHighIpAddress OBJECT-TYPE
SYNTAX  IpAddress
       MAX-ACCESS  read-create
       STATUS  current
       DESCRIPTION
"DHCP pool excluded high ip address"
        ::= { utsDHCPPoolExcludedEntry 3 }


--utsDHCPPoolExcludedDomainName OBJECT-TYPE
--SYNTAX  DisplayString
--       MAX-ACCESS  read-only
--       STATUS  current
--       DESCRIPTION
--"DHCP excluded pool domain name. "
--        ::= { utsDHCPPoolExcludedEntry 4 }



utsDHCPPoolExcludedStatus OBJECT-TYPE
SYNTAX  RowStatus
       MAX-ACCESS  read-create
       STATUS  current
       DESCRIPTION
"DHCP pool excluded row status"
        ::= { utsDHCPPoolExcludedEntry 5 }

--
-- DHCP manual binding table
--


utsDHCPPoolManualBindTable OBJECT-TYPE
SYNTAX  SEQUENCE OF UtsDHCPPoolManualBindEntry
        MAX-ACCESS  not-accessible
        STATUS  current
        DESCRIPTION
"Table for dhcp pool manual bind MIB objects."
        ::= { utsLayer3DHCPExt 6 }

utsDHCPPoolManualBindEntry OBJECT-TYPE
SYNTAX  UtsDHCPPoolManualBindEntry
       MAX-ACCESS  not-accessible
       STATUS  current
       DESCRIPTION
"An entry in the DHCP pool manual bind MIB table."
       INDEX  { utsDHCPPoolName, utsDHCPPoolManualBindIpAddress }
       ::= { utsDHCPPoolManualBindTable 1 }

UtsDHCPPoolManualBindEntry ::=
       SEQUENCE {
--         utsDHCPPoolManualBindPoolName		      DisplayString,
         utsDHCPPoolManualBindIpAddress		   IpAddress,
         utsDHCPPoolManualBindVlanId		      INTEGER,
         utsDHCPPoolManualBindHardwareAddress	MacAddress,
--         utsDHCPPoolManualBindDomainName	      DisplayString,
	 		utsDHCPPoolManualBindStatus		      RowStatus
}


--utsDHCPPoolManualBindPoolName OBJECT-TYPE
--SYNTAX  DisplayString
--       MAX-ACCESS  read-only
--       STATUS  current
--       DESCRIPTION
--"DHCP manual bind pool name. "
--        ::= { utsDHCPPoolManualBindEntry 1 }


utsDHCPPoolManualBindIpAddress OBJECT-TYPE
SYNTAX  IpAddress
       MAX-ACCESS  read-create
       STATUS  current
       DESCRIPTION
"DHCP pool default router ip address"
        ::= { utsDHCPPoolManualBindEntry 2 }

utsDHCPPoolManualBindVlanId OBJECT-TYPE
SYNTAX  INTEGER
       MAX-ACCESS  read-create
       STATUS  current
       DESCRIPTION
"DHCP pool manual bind vlan id. "
        ::= { utsDHCPPoolManualBindEntry 3 }

utsDHCPPoolManualBindHardwareAddress OBJECT-TYPE
SYNTAX  MacAddress
       MAX-ACCESS  read-create
       STATUS  current
       DESCRIPTION
"DHCP pool manual bind hardware mac address. "
        ::= { utsDHCPPoolManualBindEntry 4 }

--utsDHCPPoolManualBindDomainName OBJECT-TYPE
--SYNTAX  DisplayString
--       MAX-ACCESS  read-only
--       STATUS  current
--       DESCRIPTION
--"DHCP manual bind pool domain name. "
--        ::= { utsDHCPPoolManualBindEntry 5 }


utsDHCPPoolManualBindStatus OBJECT-TYPE
SYNTAX  RowStatus
       MAX-ACCESS  read-create
       STATUS  current
       DESCRIPTION
"DHCP pool manual bind entry status. "
        ::= { utsDHCPPoolManualBindEntry 6 }


--
-- SHOW ip dhcp binding
--


utsIpDHCPPoolBindingTable OBJECT-TYPE
SYNTAX  SEQUENCE OF UtsIpDHCPPoolBindingEntry
        MAX-ACCESS  not-accessible
        STATUS  current
        DESCRIPTION
"Table for ip dhcp pool binding MIB objects."
        ::= { utsLayer3DHCPExt 7 }

utsIpDHCPPoolBindingEntry OBJECT-TYPE
SYNTAX  UtsIpDHCPPoolBindingEntry
       MAX-ACCESS  not-accessible
       STATUS  current
       DESCRIPTION
		"An entry in the ip DHCP pool binding MIB table."
       INDEX  { utsDHCPPoolName, utsIpDHCPPoolBindingIpAddress }
       ::= { utsIpDHCPPoolBindingTable 1 }

UtsIpDHCPPoolBindingEntry ::=
       SEQUENCE {
--         utsIpDHCPPoolBindingPoolName				DisplayString,
         utsIpDHCPPoolBindingIpAddress				IpAddress,
         utsIpDHCPPoolBindingVlanId					INTEGER,
         utsIpDHCPPoolBindingState					INTEGER,
			utsIpDHCPPoolBindingType					INTEGER,
         utsIpDHCPPoolBindingHardwareAddress		MacAddress,
			utsIpDHCPPoolBindingLeaseExpiredTime	DisplayString,
			utsIpDHCPPoolBindingClear               INTEGER

}

--utsIpDHCPPoolBindingPoolName OBJECT-TYPE
--SYNTAX  DisplayString
--       MAX-ACCESS  read-only
--       STATUS  current
--       DESCRIPTION
--"DHCP binding pool name. "
--        ::= { utsIpDHCPPoolBindingEntry 1 }


utsIpDHCPPoolBindingIpAddress OBJECT-TYPE
SYNTAX  IpAddress
       MAX-ACCESS  read-only
       STATUS  current
       DESCRIPTION
"DHCP binding ip address. "
        ::= { utsIpDHCPPoolBindingEntry 2 }

utsIpDHCPPoolBindingVlanId OBJECT-TYPE
SYNTAX  INTEGER
       MAX-ACCESS  read-only
       STATUS  current
       DESCRIPTION
"DHCP pool manual bind vlan id for VoIP pool. "
        ::= { utsIpDHCPPoolBindingEntry 3 }

utsIpDHCPPoolBindingState OBJECT-TYPE
SYNTAX  INTEGER
		{
		free(1),
		expire(2),
		offer(3),
		bind(4)
		}
       MAX-ACCESS  read-only
       STATUS  current
       DESCRIPTION
"DHCP binding state"
        ::= { utsIpDHCPPoolBindingEntry 4 }


utsIpDHCPPoolBindingType OBJECT-TYPE
SYNTAX  INTEGER
		{
		automatic(1),
		manual(2),
		framed(3)
		}
       MAX-ACCESS  read-only
       STATUS  current
       DESCRIPTION
"DHCP binding type"
        ::= { utsIpDHCPPoolBindingEntry 5 }


utsIpDHCPPoolBindingHardwareAddress OBJECT-TYPE
SYNTAX  MacAddress
       MAX-ACCESS  read-only
       STATUS  current
       DESCRIPTION
"DHCP pool manual bind hardware mac address. "
        ::= { utsIpDHCPPoolBindingEntry 6 }




utsIpDHCPPoolBindingLeaseExpiredTime OBJECT-TYPE
SYNTAX  DisplayString
       MAX-ACCESS  read-only
       STATUS  current
       DESCRIPTION
"DHCP pool manual bind lease time. "
        ::= { utsIpDHCPPoolBindingEntry 7 }



utsIpDHCPPoolBindingClear OBJECT-TYPE
       SYNTAX  INTEGER
       {
      	  normal(0), -- read only for normal statuss
      	  clear(1)   -- write to delete the current binding entry
       }
       MAX-ACCESS  read-write
       STATUS  current
       DESCRIPTION
       "Release the specific binding."
       ::= { utsIpDHCPPoolBindingEntry 8 }

------
------ NTP server
------
--
-- DHCP pool ntp server table
--

utsDHCPPoolNtpServerTable OBJECT-TYPE
SYNTAX  SEQUENCE OF UtsDHCPPoolNtpServerEntry
        MAX-ACCESS  not-accessible
        STATUS  current
        DESCRIPTION
"Table for dhcp pool ntp server MIB objects."
        ::= { utsLayer3DHCPExt 8 }

utsDHCPPoolNtpServerEntry OBJECT-TYPE
SYNTAX  UtsDHCPPoolNtpServerEntry
       MAX-ACCESS  not-accessible
       STATUS  current
       DESCRIPTION
"An entry in the DHCP pool ntp server MIB table. max entry number is 3."
       INDEX  { utsDHCPPoolName, utsDHCPPoolNtpServerIpAddress  }
       ::= { utsDHCPPoolNtpServerTable 1 }

UtsDHCPPoolNtpServerEntry ::=
       SEQUENCE {
--         utsDHCPPoolNtpServerPoolName		DisplayString,
         utsDHCPPoolNtpServerIpAddress		IpAddress,
--         utsDHCPPoolNtpServerDomainName	DisplayString,
         utsDHCPPoolNtpServerStatus			RowStatus

}

--utsDHCPPoolNtpServerPoolName OBJECT-TYPE
--SYNTAX  DisplayString
--       MAX-ACCESS  read-only
--       STATUS  current
--       DESCRIPTION
--"DHCP ntp server pool name. "
--        ::= { utsDHCPPoolNtpServerEntry 1 }



utsDHCPPoolNtpServerIpAddress OBJECT-TYPE
SYNTAX  IpAddress
       MAX-ACCESS  read-create
       STATUS  current
       DESCRIPTION
"DHCP pool ntp server ip address."
        ::= { utsDHCPPoolNtpServerEntry 2 }

--utsDHCPPoolNtpServerDomainName OBJECT-TYPE
--SYNTAX  DisplayString
--       MAX-ACCESS  read-create
--       STATUS  current
--       DESCRIPTION
--"DHCP ntp-server pool domain name. "
--        ::= { utsDHCPPoolNtpServerEntry 3 }


utsDHCPPoolNtpServerStatus OBJECT-TYPE
SYNTAX  RowStatus
       MAX-ACCESS  read-create
       STATUS  current
       DESCRIPTION
"DHCP ntp-server entry status. "
        ::= { utsDHCPPoolNtpServerEntry 4 }


------
------ log server
------

--
-- DHCP pool log server table
--

utsDHCPPoolLogServerTable OBJECT-TYPE
SYNTAX  SEQUENCE OF UtsDHCPPoolLogServerEntry
        MAX-ACCESS  not-accessible
        STATUS  current
        DESCRIPTION
"Table for dhcp pool log server MIB objects."
        ::= { utsLayer3DHCPExt 9 }

utsDHCPPoolLogServerEntry OBJECT-TYPE
SYNTAX  UtsDHCPPoolLogServerEntry
       MAX-ACCESS  not-accessible
       STATUS  current
       DESCRIPTION
"An entry in the DHCP pool log server MIB table, max entry number is 3."
       INDEX  { utsDHCPPoolName, utsDHCPPoolLogServerIpAddress }
       ::= { utsDHCPPoolLogServerTable 1 }

UtsDHCPPoolLogServerEntry ::=
       SEQUENCE {
--         utsDHCPPoolLogServerPoolName		DisplayString,
         utsDHCPPoolLogServerIpAddress		IpAddress,
--         utsDHCPPoolLogServerDomainName	DisplayString,
         utsDHCPPoolLogServerStatus	      RowStatus
}

--utsDHCPPoolLogServerPoolName OBJECT-TYPE
--SYNTAX  DisplayString
--       MAX-ACCESS  read-only
--       STATUS  current
--       DESCRIPTION
--           "DHCP log server pool name. "
--        ::= { utsDHCPPoolLogServerEntry 1 }

utsDHCPPoolLogServerIpAddress OBJECT-TYPE
SYNTAX  IpAddress
       MAX-ACCESS  read-create
       STATUS  current
       DESCRIPTION
"DHCP pool log server ip address"
        ::= { utsDHCPPoolLogServerEntry 2 }

--utsDHCPPoolLogServerDomainName OBJECT-TYPE
--    SYNTAX  DisplayString
--    MAX-ACCESS  read-only
--    STATUS  current
--    DESCRIPTION
--        "DHCP log server pool domain name. "
--    ::= { utsDHCPPoolLogServerEntry 3 }


utsDHCPPoolLogServerStatus OBJECT-TYPE
    SYNTAX  RowStatus
    MAX-ACCESS  read-create
    STATUS  current
    DESCRIPTION
        "DHCP log server entry status. "
    ::= { utsDHCPPoolLogServerEntry 4 }

------
------ LPR server
------
--
-- DHCP pool LPR server table
--

--utsDHCPPoolLprServerTable OBJECT-TYPE
--SYNTAX  SEQUENCE OF UtsDHCPPoolLprServerEntry
--        MAX-ACCESS  not-accessible
--        STATUS  current
--        DESCRIPTION
--"Table for dhcp pool Lpr server MIB objects."
--        ::= { utsLayer3DHCPExt 10 }
--
--utsDHCPPoolLprServerEntry OBJECT-TYPE
--SYNTAX  UtsDHCPPoolLprServerEntry
--       MAX-ACCESS  not-accessible
--       STATUS  current
--       DESCRIPTION
--"An entry in the DHCP pool Lpr server MIB table."
--       INDEX  { utsDHCPPoolLprServerPoolName, utsDHCPPoolLprServerIpAddress  }
--       ::= { utsDHCPPoolLprServerTable 1 }
--
--UtsDHCPPoolLprServerEntry ::=
--       SEQUENCE {
--         utsDHCPPoolLprServerPoolName		DisplayString,
--         utsDHCPPoolLprServerIpAddress		IpAddress,
--         utsDHCPPoolLprServerDomainName		DisplayString,
--         utsDHCPPoolLprServerStatus			RowStatus
--
--}
--
--utsDHCPPoolLprServerPoolName OBJECT-TYPE
--SYNTAX  DisplayString
--       MAX-ACCESS  read-only
--       STATUS  current
--       DESCRIPTION
--"DHCP Lpr server pool name. "
--        ::= { utsDHCPPoolLprServerEntry 1 }
--
--
--
--utsDHCPPoolLprServerIpAddress OBJECT-TYPE
--SYNTAX  IpAddress
--       MAX-ACCESS  read-write
--       STATUS  current
--       DESCRIPTION
--"DHCP pool Lpr server ip address"
--        ::= { utsDHCPPoolLprServerEntry 2 }
--
--utsDHCPPoolLprServerDomainName OBJECT-TYPE
--SYNTAX  DisplayString
--       MAX-ACCESS  read-only
--       STATUS  current
--       DESCRIPTION
--"DHCP dns-server pool domain name. "
--        ::= { utsDHCPPoolLprServerEntry 3 }

--
--utsDHCPPoolLprServerStatus OBJECT-TYPE
--SYNTAX  RowStatus
--       MAX-ACCESS  read-create
--       STATUS  current
--       DESCRIPTION
--"DHCP lpr-server status  "
--        ::= { utsDHCPPoolLprServerEntry 4 }


--
-- DHCP pool included address table
--

utsDHCPPoolIncludedTable OBJECT-TYPE
SYNTAX  SEQUENCE OF UtsDHCPPoolIncludedEntry
        MAX-ACCESS  not-accessible
        STATUS  current
        DESCRIPTION
"Table for dhcp pool included MIB objects."
        ::= { utsLayer3DHCPExt 11 }

utsDHCPPoolIncludedEntry OBJECT-TYPE
SYNTAX  UtsDHCPPoolIncludedEntry
       MAX-ACCESS  not-accessible
       STATUS  current
       DESCRIPTION
           "An entry in the DHCP pool excluded MIB table, maximum number is 8."
       INDEX  { utsDHCPPoolName, utsDHCPPoolIncludedLowIpAddress }
       ::= { utsDHCPPoolIncludedTable 1 }

UtsDHCPPoolIncludedEntry ::=
       SEQUENCE {
--         utsDHCPPoolIncludedPoolName		 DisplayString,
         utsDHCPPoolIncludedLowIpAddress	 IpAddress,
         utsDHCPPoolIncludedHighIpAddress	 IpAddress,
--         utsDHCPPoolIncludedDomainName		 DisplayString,
         utsDHCPPoolIncludedStatus     	 RowStatus
}

--utsDHCPPoolIncludedPoolName OBJECT-TYPE
--SYNTAX  DisplayString
--       MAX-ACCESS  read-only
--       STATUS  current
--       DESCRIPTION
--"DHCP included address pool name. "
--        ::= { utsDHCPPoolIncludedEntry 1 }


utsDHCPPoolIncludedLowIpAddress OBJECT-TYPE
SYNTAX  IpAddress
       MAX-ACCESS  read-create
       STATUS  current
       DESCRIPTION
"DHCP pool included low ip address"
        ::= { utsDHCPPoolIncludedEntry 2 }


utsDHCPPoolIncludedHighIpAddress OBJECT-TYPE
SYNTAX  IpAddress
       MAX-ACCESS  read-create
       STATUS  current
       DESCRIPTION
"DHCP pool included high ip address"
        ::= { utsDHCPPoolIncludedEntry 3 }

--utsDHCPPoolIncludedDomainName OBJECT-TYPE
--SYNTAX  DisplayString
--       MAX-ACCESS  read-only
--       STATUS  current
--       DESCRIPTION
--"DHCP included pool domain name. "
--        ::= { utsDHCPPoolIncludedEntry 4 }


utsDHCPPoolIncludedStatus OBJECT-TYPE
SYNTAX  RowStatus
       MAX-ACCESS  read-create
       STATUS  current
       DESCRIPTION
"DHCP pool included row status"
        ::= { utsDHCPPoolIncludedEntry 5 }


--
-- DHCP relay server table
--

utsDHCPRelayServerTable OBJECT-TYPE
SYNTAX  SEQUENCE OF UtsDHCPRelayServerEntry
        MAX-ACCESS  not-accessible
        STATUS  current
        DESCRIPTION
"Table for dhcp relay dhcp server MIB objects."
        ::= { utsLayer3DHCPExt 12 }

utsDHCPRelayServerEntry OBJECT-TYPE
SYNTAX  UtsDHCPRelayServerEntry
       MAX-ACCESS  not-accessible
       STATUS  current
       DESCRIPTION
           "An entry in the DHCP relay server MIB table."
       INDEX  { utsDHCPRelayIfIndex  }
       ::= { utsDHCPRelayServerTable 1 }

UtsDHCPRelayServerEntry ::=
       SEQUENCE {
       		   utsDHCPRelayIfIndex     	InterfaceIndex,
               utsDHCPRelayServerID			IpAddress,
               utsDHCPRelayGateway			IpAddress,
               utsDHCPRelayStatus			RowStatus,
               utsDHCPRelaySecondServer	IpAddress
			}

utsDHCPRelayIfIndex OBJECT-TYPE
SYNTAX  InterfaceIndex
       MAX-ACCESS  read-create
       STATUS  current
       DESCRIPTION
"DHCP server IP address configured for this interface."
        ::= { utsDHCPRelayServerEntry 1 }

utsDHCPRelayServerID OBJECT-TYPE
SYNTAX  IpAddress
       MAX-ACCESS  read-create
       STATUS  current
       DESCRIPTION
"primary DHCP server IP address configured for this interface."
        ::= { utsDHCPRelayServerEntry 2 }

utsDHCPRelayGateway OBJECT-TYPE
SYNTAX  IpAddress
       MAX-ACCESS  read-create
       STATUS  current
       DESCRIPTION
"Configure gateway IP address to DHCP server."
        ::= { utsDHCPRelayServerEntry 3 }

utsDHCPRelayStatus OBJECT-TYPE
SYNTAX  RowStatus
       MAX-ACCESS  read-create
       STATUS  current
       DESCRIPTION
"dhcp relay Server row status. "
        ::= { utsDHCPRelayServerEntry 4 }

utsDHCPRelaySecondServer OBJECT-TYPE
SYNTAX  IpAddress
       MAX-ACCESS  read-create
       STATUS  current
       DESCRIPTION
"secondary DHCP server IP address configured for this interface. zero means no secondary server is configured."
        ::= { utsDHCPRelayServerEntry 5 }

--
--  DHCP number of lease in specific VLAN
--

utsDHCPLeaseNumTable OBJECT-TYPE
SYNTAX  SEQUENCE OF UtsDHCPLeaseNumEntry
        MAX-ACCESS  not-accessible
        STATUS  current
        DESCRIPTION
"Table for the MIB objects of dhcp VLAN lease number under Custom mode."
        ::= { utsLayer3DHCPExt 13 }

utsDHCPLeaseNumEntry OBJECT-TYPE
SYNTAX  UtsDHCPLeaseNumEntry
       MAX-ACCESS  not-accessible
       STATUS  current
       DESCRIPTION
       "An entry in the DHCP VLAN lease number MIB table."
       INDEX  { utsDHCPLeaseNumVlan  }
       ::= { utsDHCPLeaseNumTable 1 }

UtsDHCPLeaseNumEntry ::=
       SEQUENCE {
       		   utsDHCPLeaseNumVlan     	INTEGER,
               utsDHCPLeaseNumVal	    INTEGER,
               utsDHCPLeaseNumStatus    RowStatus
			}

utsDHCPLeaseNumVlan OBJECT-TYPE
      SYNTAX      INTEGER
      MAX-ACCESS  read-only
      STATUS      current
      DESCRIPTION
         "VLAN ID"
      ::= { utsDHCPLeaseNumEntry 1 }

utsDHCPLeaseNumVal OBJECT-TYPE
       SYNTAX  INTEGER(1..512)
       MAX-ACCESS  read-create
       STATUS  current
       DESCRIPTION
"The lease number for specific VLAN"
        ::= { utsDHCPLeaseNumEntry 2 }

utsDHCPLeaseNumStatus OBJECT-TYPE
       SYNTAX  RowStatus
       MAX-ACCESS  read-create
       STATUS  current
       DESCRIPTION
"Row status for the current entry."
        ::= { utsDHCPLeaseNumEntry 3 }

------
------
------
------         SNTP
------
------


   utsIpSNTPExt	OBJECT IDENTIFIER ::= { utsLayer3ConfExt 4 }

   utsSNTPGroup OBJECT IDENTIFIER ::= { utsIpSNTPExt 1 }

   utsSNTPServiceState OBJECT-TYPE
		SYNTAX  INTEGER
		{
				no-service(1),
				client-active(2)
		}
		MAX-ACCESS  read-write
		STATUS  current
		DESCRIPTION
			"SNTP serive type and state."
        ::= { utsSNTPGroup 1 }

   utsSNTPPollInterval OBJECT-TYPE
		SYNTAX  INTEGER(16..16284)
		MAX-ACCESS  read-write
		STATUS  current
		DESCRIPTION
			"SNTP Polling Interval."
        ::= { utsSNTPGroup 2 }

   utsSNTPTimeZone OBJECT-TYPE
		SYNTAX  INTEGER(-12..13)
		MAX-ACCESS  read-write
		STATUS  current
		DESCRIPTION
			"SNTP Timezone."
        ::= { utsSNTPGroup 3 }

   utsSNTPClockSync OBJECT-TYPE
		SYNTAX  INTEGER
		{
				force-sync(1)
		}
		MAX-ACCESS  read-write
		STATUS  current
		DESCRIPTION
			"SNTP clock."
        ::= { utsSNTPGroup 4 }

   utsSNTPCurrentTime OBJECT-TYPE
		SYNTAX  DisplayString
		MAX-ACCESS  read-only
		STATUS  current
		DESCRIPTION
			"SNTP current time."
        ::= { utsSNTPGroup 5 }


   utsSNTPLastUpdateTime OBJECT-TYPE
		SYNTAX  DisplayString
		MAX-ACCESS  read-only
		STATUS  current
		DESCRIPTION
			"SNTP last update time."
        ::= { utsSNTPGroup 6 }



--
-- SNTP Server table
--


utsSNTPServerTable OBJECT-TYPE
SYNTAX  SEQUENCE OF UtsSNTPServerEntry
        MAX-ACCESS  not-accessible
        STATUS  current
        DESCRIPTION
"Table for SNTP Server MIB objects."
        ::= { utsIpSNTPExt 2 }

utsSNTPServerEntry OBJECT-TYPE
SYNTAX  UtsSNTPServerEntry
       MAX-ACCESS  not-accessible
       STATUS  current
       DESCRIPTION
"An entry in the SNTP Server MIB table."
       INDEX  { utsSNTPServerId  }
       ::= { utsSNTPServerTable 1 }

UtsSNTPServerEntry ::=
       SEQUENCE {
	   utsSNTPServerId          INTEGER,
           utsSNTPServerIpAddress	IpAddress,
           utsSNTPServerState		INTEGER,
           utsSNTPServerVersion	    DisplayString,
	   utsSNTPServerStatus      RowStatus
}

utsSNTPServerId OBJECT-TYPE
    SYNTAX  INTEGER  (1..3)
    MAX-ACCESS  read-create
    STATUS  current
    DESCRIPTION
        "SNTP Server Id. "
    ::= { utsSNTPServerEntry 1 }

utsSNTPServerIpAddress OBJECT-TYPE
    SYNTAX  IpAddress
    MAX-ACCESS  read-create
    STATUS  current
    DESCRIPTION
        "SNTP Server Address. "
    ::= { utsSNTPServerEntry 2 }

utsSNTPServerState OBJECT-TYPE
    SYNTAX  INTEGER
	{
        up(1),
	down(2)
	}
    MAX-ACCESS  read-only
    STATUS  current
    DESCRIPTION
        "SNTP Server State. "
    ::= { utsSNTPServerEntry 3 }

utsSNTPServerVersion OBJECT-TYPE
    SYNTAX  DisplayString
    MAX-ACCESS  read-create
    STATUS  current
    DESCRIPTION
        "SNTP Server version info, range 1-4. "
    ::= { utsSNTPServerEntry 4 }

utsSNTPServerStatus OBJECT-TYPE
SYNTAX  RowStatus
       MAX-ACCESS  read-create
       STATUS  current
       DESCRIPTION
"SNTP Server status. "
        ::= { utsSNTPServerEntry 5 }


utsHostRouteObjs OBJECT IDENTIFIER ::= { utsLayer3ConfExt 5 }


utsHostRouteTable OBJECT-TYPE
    SYNTAX SEQUENCE OF UtsHostRouteEntry
    MAX-ACCESS not-accessible
    STATUS current
    DESCRIPTION
        "Table for host route."
    ::= {  utsHostRouteObjs 1 }

utsHostRouteEntry OBJECT-TYPE
    SYNTAX UtsHostRouteEntry
    MAX-ACCESS  not-accessible
    STATUS current
    DESCRIPTION
        "An entry in the host route MIB table."
    INDEX { utsHostRouteIpAddress }
    ::= { utsHostRouteTable 1 }

UtsHostRouteEntry ::=
    SEQUENCE {
        utsHostRouteIpAddress
		    IpAddress,
	    utsHostRouteType
		    INTEGER,
		utsHostRouteModuleId
		    INTEGER,
	    utsHostRoutePortId
		    INTEGER,
		utsHostRouteLinkAggGroupId
		    INTEGER,
	    utsHostRouteVlanId
		    INTEGER,
	    utsHostRouteArpType
		    INTEGER,
		utsHostRouteVlanSubVlanId
		    INTEGER,
	    utsHostRouteMacAddress
	            MacAddress,
		utsHostRouteRowStatus
		    RowStatus
    }

utsHostRouteIpAddress OBJECT-TYPE
    SYNTAX      IpAddress
	MAX-ACCESS 	read-create
	STATUS      current
	DESCRIPTION
	   "IP Address of the Host Route Entry."
	::= { utsHostRouteEntry 1 }

utsHostRouteType  OBJECT-TYPE
    SYNTAX      INTEGER {
	    port-based(1),
		lag-based(2),
--		loop-back-type(3),
		vlan-based(4),
--		super-vlan-based(5),
		onu-vlan-based(6)
	}
	MAX-ACCESS  read-create
	STATUS      current
	DESCRIPTION
	    "Indicates the host route type."
	::= { utsHostRouteEntry 2 }


utsHostRouteModuleId  OBJECT-TYPE
    SYNTAX       INTEGER
	MAX-ACCESS   read-create
	STATUS       current
	DESCRIPTION
	    "Module Id of the Host Route Entry. It is valid if the HostRouteType
		is port-based or valid when vlan-based member has been added."
	::= { utsHostRouteEntry 3 }

utsHostRoutePortId  OBJECT-TYPE
    SYNTAX       INTEGER
	MAX-ACCESS   read-create
	STATUS       current
	DESCRIPTION
	    "Port Id of the Host Route Entry. It is valid if the HostRouteType
		is port-based or valid when vlan-based member has been added"
	::= { utsHostRouteEntry 4 }

utsHostRouteLinkAggGroupId  OBJECT-TYPE
    SYNTAX       INTEGER
	MAX-ACCESS   read-create
	STATUS       current
	DESCRIPTION
	    "Port Id of the Host Route Entry. It is only valid if the host route
		 entry is based on Link Aggregation port. HostRouteType is lag-based"
	::= { utsHostRouteEntry 5 }

utsHostRouteVlanId  OBJECT-TYPE
    SYNTAX       INTEGER
	MAX-ACCESS   read-create
	STATUS       current
	DESCRIPTION
	    "VLAN Id of the Host Route Entry. It is only valid if the host route
		 entry is based on VLAN Id. HostRouteType is vlan-based"
	::= { utsHostRouteEntry 6 }

utsHostRouteArpType  OBJECT-TYPE
    SYNTAX       INTEGER
	{

			host-route-static(4),
			host-route-dynamic(5),
			host-route-inherit-from-arp(6)
	}
	MAX-ACCESS   read-only
	STATUS       current
	DESCRIPTION
	    "Identify the arp type of the Host Route Entry. host-route-inherit-from-arp(6) is read-only, not writable."
	::= { utsHostRouteEntry 7 }



utsHostRouteVlanSubVlanId  OBJECT-TYPE
    SYNTAX       INTEGER
	MAX-ACCESS   read-create
	STATUS       current
	DESCRIPTION
	    "Identify the memeber's SubVlan Id within the Super VLAN of the Host
		Route Entry. It is only valid if the host route entry is based on
		Super VLAN Id. HostRouteType is super-vlan-based"
	::= { utsHostRouteEntry 8 }

utsHostRouteMacAddress OBJECT-TYPE
    SYNTAX      MacAddress
    MAX-ACCESS  read-only
    STATUS      current
    DESCRIPTION
        "the MAC address mapping to ip address of host route"
    ::= { utsHostRouteEntry 9 }


utsHostRouteRowStatus OBJECT-TYPE
    SYNTAX      RowStatus
    MAX-ACCESS  read-create
    STATUS      current
    DESCRIPTION
        "Writing invalid has the effect of adding/deleting this entry.
  		 Only be able to create/delete setting to createAndGo/destory.
  		 active will be returned when query"
    ::= { utsHostRouteEntry 10 }



------
------   iP Route Table
------

utsIpRouteObjects OBJECT IDENTIFIER ::= { utsLayer3ConfExt 6 }

utsIpRouteTable  OBJECT-TYPE
    SYNTAX  SEQUENCE OF UtsIpRouteEntry
	MAX-ACCESS not-accessible
	STATUS     current
	DESCRIPTION
	    "Table of IP Routing Information."
	::= { utsIpRouteObjects 1 }

utsIpRouteEntry OBJECT-TYPE
   SYNTAX      UtsIpRouteEntry
   MAX-ACCESS  not-accessible
   STATUS      current
   DESCRIPTION
       "An entry in the IP route MIB table."
   INDEX { utsIpRouteEntryIndex }
   ::= { utsIpRouteTable 1 }


UtsIpRouteEntry ::=
    SEQUENCE {
	    utsIpRouteEntryIndex         INTEGER,
		utsIpRouteEntryOwner         INTEGER,
		utsIpRouteEntryIpAddr        IpAddress,
		utsIpRouteEntryIpMask        IpAddress,
		utsIpRouteEntryType          INTEGER,
	    utsIpRouteEntryCost          INTEGER,
		utsIpRouteEntryNextHop1      IpAddress,
		utsIpRouteEntryNextHop2      IpAddress,
		utsIpRouteEntryNextHop3      IpAddress,
		utsIpRouteEntryNextHop4      IpAddress,
		utsIpRouteEntryVlanId1       INTEGER,
		utsIpRouteEntryVlanId2       INTEGER,
		utsIpRouteEntryVlanId3       INTEGER,
		utsIpRouteEntryVlanId4       INTEGER
    }

utsIpRouteEntryIndex  OBJECT-TYPE
    SYNTAX            INTEGER
	MAX-ACCESS 	      read-only
	STATUS            current
	DESCRIPTION
	  "An index into the IpRoute Table."
	::= { utsIpRouteEntry 1 }

utsIpRouteEntryOwner  OBJECT-TYPE
    SYNTAX            INTEGER
	{
	    direct(1),
		static(2),
	    rip(3),
		ospf(4),
		bgp(5),
		other(6)
	}
	MAX-ACCESS 	      read-only
	STATUS            current
	DESCRIPTION
	  "A flag indicates which protocol that the route entry derived from.
	    direct - Direct Connect,
		static - Static Route.
		rip    - Routing Information Protocol,
		ospf   - Open Shortest Path First.
		bgp    - Border Gateway Protocol.
		other  - None of above."
	::= { utsIpRouteEntry 2 }

utsIpRouteEntryIpAddr    OBJECT-TYPE
    SYNTAX               IpAddress
	MAX-ACCESS           read-only
	STATUS               current
	DESCRIPTION
	    "The IP Address of the remote network."
	::= { utsIpRouteEntry 3 }

utsIpRouteEntryIpMask    OBJECT-TYPE
    SYNTAX               IpAddress
	MAX-ACCESS           read-only
	STATUS               current
	DESCRIPTION
	    "The IP Mask of the remote network."
	::= { utsIpRouteEntry 4 }

utsIpRouteEntryType    OBJECT-TYPE
	SYNTAX             INTEGER
	{
	   other(1),
	   ospfia(2),
	   ospfe1(3),
	   ospfe2(4),
	   ospfnssa2(5),
	   ospfnssa1(6)
	}
	MAX-ACCESS         read-only
	STATUS             current
	DESCRIPTION
		"The Route Type of this entry.
		    ospfia    - OSPF Inter Area.
			ospfe1    - OSPF External Type 1.
			ospfe2    - OSPF External Type 2.
			ospfnssa2 - OSPF Not So Stub Area Type 2.
			ospfnssa1 - OSPF Not So Stub Area Type 1.
			other     - Unknown or None of above."
	::= { utsIpRouteEntry 5 }

utsIpRouteEntryCost    OBJECT-TYPE
    SYNTAX             INTEGER
	MAX-ACCESS 	       read-only
	STATUS             current
	DESCRIPTION
	  "The cost value of the routing entry for routing protocol specified in utsIpRouteEntryOwner."
	::= { utsIpRouteEntry 6 }

utsIpRouteEntryNextHop1   OBJECT-TYPE
    SYNTAX                IpAddress
	MAX-ACCESS            read-only
	STATUS                current
	DESCRIPTION
	    "The IP address 1st next hop router."
	::= { utsIpRouteEntry 7 }

utsIpRouteEntryNextHop2   OBJECT-TYPE
    SYNTAX                IpAddress
	MAX-ACCESS            read-only
	STATUS                current
	DESCRIPTION
	    "The IP address 2nd next hop router."
	::= { utsIpRouteEntry 8 }

utsIpRouteEntryNextHop3   OBJECT-TYPE
    SYNTAX                IpAddress
	MAX-ACCESS            read-only
	STATUS                current
	DESCRIPTION
	    "The IP address 3rd next hop router."
	::= { utsIpRouteEntry 9 }

utsIpRouteEntryNextHop4   OBJECT-TYPE
    SYNTAX                IpAddress
	MAX-ACCESS            read-only
	STATUS                current
	DESCRIPTION
	    "The IP address 4th next hop router."
	::= { utsIpRouteEntry 10 }

utsIpRouteEntryVlanId1    OBJECT-TYPE
    SYNTAX                INTEGER
	MAX-ACCESS            read-only
	STATUS                current
	DESCRIPTION
	    "The VLAN Id of the 1st next hop switch."
	::= { utsIpRouteEntry 23 }

utsIpRouteEntryVlanId2    OBJECT-TYPE
    SYNTAX                INTEGER
	MAX-ACCESS            read-only
	STATUS                current
	DESCRIPTION
	    "The VLAN Id of the 2nd next hop switch."
	::= { utsIpRouteEntry 24 }

utsIpRouteEntryVlanId3    OBJECT-TYPE
    SYNTAX                INTEGER
	MAX-ACCESS            read-only
	STATUS                current
	DESCRIPTION
	    "The VLAN Id of the 3rd next hop switch."
	::= { utsIpRouteEntry 25 }

utsIpRouteEntryVlanId4    OBJECT-TYPE
    SYNTAX                INTEGER
	MAX-ACCESS            read-only
	STATUS                current
	DESCRIPTION
		"The VLAN Id of the 4th next hop switch."
	::= { utsIpRouteEntry 26 }


------
------   PIM Global Configuration
------

   utsIpMulticastExt	OBJECT IDENTIFIER ::= { utsLayer3ConfExt 7 }

   utsIpPIMExtConfGroup OBJECT IDENTIFIER ::= { utsIpMulticastExt 1 }


   utsIpPIMExtGblCRPHoldTmr OBJECT-TYPE
   SYNTAX      INTEGER (3..65535)
	MAX-ACCESS  read-write
	STATUS      current
	DESCRIPTION
	    "PIM configured CRP hold timer, Default is 150 secs."
	DEFVAL      { 150 }
   ::= { utsIpPIMExtConfGroup 1 }

   utsIpPIMExtGblJoinPrunTmr OBJECT-TYPE
		SYNTAX  INTEGER (1..65535)
		MAX-ACCESS  read-write
		STATUS  current
		DESCRIPTION
			"Configure PIM join prune timer, Default is 60 secs."
		DEFVAL      { 60 }
      ::= { utsIpPIMExtConfGroup 2 }

   utsIpPIMExtGblRpStaticCtrl OBJECT-TYPE
		SYNTAX  INTEGER
		{
		   disable(1),
		   enable(2)
		}
		MAX-ACCESS  read-write
		STATUS  current
		DESCRIPTION
			"Enable/disable all rp-static entries, default enabled."
      ::= { utsIpPIMExtConfGroup 3 }

----
--- ip pim interface configruation
----

utsIpPIMInterfaceCfgObj OBJECT IDENTIFIER ::= { utsIpMulticastExt 2 }

utsPimIntfTable OBJECT-TYPE
SYNTAX  SEQUENCE OF UtsPimIntfEntry
        MAX-ACCESS  not-accessible
        STATUS  current
        DESCRIPTION
"Table for dot3 OLT MIBs."
        ::= { utsIpPIMInterfaceCfgObj 1 }

utsPimIntfEntry OBJECT-TYPE
SYNTAX  UtsPimIntfEntry
       MAX-ACCESS  not-accessible
       STATUS  current
       DESCRIPTION
"An entry in the dot3 PLT MIBs table."
       INDEX  { utsPimIntfIfIndex }
       ::= { utsPimIntfTable 1 }

UtsPimIntfEntry ::=
       SEQUENCE {
                    utsPimIntfIfIndex			InterfaceIndex,
                    utsPimIntfAddress			IpAddress,
                    utsPimIntfNetMask			IpAddress,
                    utsPimIntfMode			INTEGER,
                    utsPimIntfDRPriority		INTEGER,
--                    utsPimIntfHelloHoldtime		INTEGER,
                    utsPimIntfHelloInterval		INTEGER,
                    utsPimIntfJoinPruneInterval		INTEGER,
                    utsPimInterfaceDR			IpAddress,
                    utsPimIntfStatus			RowStatus,
--                    utsPimIntfCBSRPref		        INTEGER,
                    utsPimIntfNeighbNum		        INTEGER
--                    utsPimIntfCBSRHashMask   INTEGER
       }


utsPimIntfIfIndex OBJECT-TYPE
SYNTAX  InterfaceIndex
        MAX-ACCESS  read-only
        STATUS  current
        DESCRIPTION
           "The ifIndex value of this PIM interface."
        ::= { utsPimIntfEntry 1 }

utsPimIntfAddress OBJECT-TYPE
SYNTAX  IpAddress
        MAX-ACCESS  read-only
        STATUS  current
        DESCRIPTION
           "The IP address of the PIM interface."
        ::= { utsPimIntfEntry 2 }

utsPimIntfNetMask OBJECT-TYPE
SYNTAX  IpAddress
        MAX-ACCESS  read-only
        STATUS  current
        DESCRIPTION
           "The network mask for the IP address of the PIM interface."
        ::= { utsPimIntfEntry 3 }

utsPimIntfMode OBJECT-TYPE
SYNTAX  INTEGER
	{
--	   dense(1),
	   sparse(2),
--	   sparseDense(3),
	   no-pim(4)
	}
        MAX-ACCESS  read-write
        STATUS  current
        DESCRIPTION
           "The configured mode of this PIM interface, set no-pim mode will disable pim on this interface."
        ::= { utsPimIntfEntry 4 }

utsPimIntfDRPriority OBJECT-TYPE
SYNTAX  INTEGER (0..255)
        MAX-ACCESS  read-write
        STATUS  current
        DESCRIPTION
           "The preference value for the local interface DR election"
		  DEFVAL     { 2 }
        ::= { utsPimIntfEntry 5 }

--utsPimIntfHelloHoldtime OBJECT-TYPE
--SYNTAX  INTEGER (0..65535)
--        MAX-ACCESS  read-write
--        STATUS  current
--        DESCRIPTION
--           "The value set in the Holdtime field of PIM Hello messages
--           transmitted on this interface. A value of 65535 represents
--           an 'infinite' holdtime."
--        ::= { utsPimIntfEntry 6 }

utsPimIntfHelloInterval OBJECT-TYPE
SYNTAX  INTEGER (1..65535)
        MAX-ACCESS  read-write
        STATUS  current
        DESCRIPTION
           "The frequency at which PIM Hello messages are transmitted on this interface."
        DEFVAL     { 30 }
        ::= { utsPimIntfEntry 7 }

utsPimIntfJoinPruneInterval OBJECT-TYPE
SYNTAX  INTEGER (1..65535)
        MAX-ACCESS  read-write
        STATUS  current
        DESCRIPTION
           "The frequency at which this router sends PIM Join/Prune messages on this PIM interface."
        DEFVAL     { 60 }
        ::= { utsPimIntfEntry 8 }

utsPimInterfaceDR OBJECT-TYPE
SYNTAX  IpAddress
        MAX-ACCESS  read-only
        STATUS  current
        DESCRIPTION
           "The primary IP address of the Designated Router on this PIM interface"
        ::= { utsPimIntfEntry 9 }

utsPimIntfStatus OBJECT-TYPE
SYNTAX  RowStatus
        MAX-ACCESS  read-only
        STATUS  current
        DESCRIPTION
           "The status of this entry."
        ::= { utsPimIntfEntry 10 }

utsPimIntfNeighbNum OBJECT-TYPE
SYNTAX  INTEGER
        MAX-ACCESS  read-only
        STATUS  current
        DESCRIPTION
           "Neighbor number of this interface."
        ::= { utsPimIntfEntry 12 }

--
-- ip pim neighbor mib
--

utsIpPIMNeighborObj OBJECT IDENTIFIER ::= { utsIpMulticastExt 3 }

utsPimNeighborTable OBJECT-TYPE
SYNTAX  SEQUENCE OF UtsPimNeighborEntry
        MAX-ACCESS  not-accessible
        STATUS  current
        DESCRIPTION
"Table for dot3 OLT MIBs."
        ::= { utsIpPIMNeighborObj 1 }

utsPimNeighborEntry OBJECT-TYPE
SYNTAX  UtsPimNeighborEntry
       MAX-ACCESS  not-accessible
       STATUS  current
       DESCRIPTION
"An entry in pim neighbor MIBs table."
       INDEX  { utsPimNeighborAddress }
       ::= { utsPimNeighborTable 1 }

UtsPimNeighborEntry ::=
       SEQUENCE {
                    utsPimNeighborAddress	IpAddress,
                    utsPimNeighborIfIndex	InterfaceIndex,
                    utsPimNeighborUpTime	TimeTicks,
                    utsPimNeighborExpiryTime	TimeTicks,
                    utsPimNeighborMode		INTEGER,
                    utsPimNeighborDRPriority	INTEGER
       }


utsPimNeighborAddress OBJECT-TYPE
SYNTAX  IpAddress
       MAX-ACCESS  read-only
       STATUS  current
       DESCRIPTION
"The IP address of the PIM neighbor for which this entry
contains information."
        ::= { utsPimNeighborEntry 1 }

utsPimNeighborIfIndex OBJECT-TYPE
SYNTAX  InterfaceIndex
       MAX-ACCESS  read-only
       STATUS  current
       DESCRIPTION
"The value of ifIndex for the interface used to reach this
PIM neighbor."
        ::= { utsPimNeighborEntry 2 }

utsPimNeighborUpTime OBJECT-TYPE
SYNTAX  TimeTicks
       MAX-ACCESS  read-only
       STATUS  current
       DESCRIPTION
"The time since this PIM neighbor (last) became a neighbor"
        ::= { utsPimNeighborEntry 3 }

utsPimNeighborExpiryTime OBJECT-TYPE
SYNTAX  TimeTicks
       MAX-ACCESS  read-only
       STATUS  current
       DESCRIPTION
"The minimum time remaining before this PIM neighbor will be aged out"
        ::= { utsPimNeighborEntry 4 }

utsPimNeighborMode OBJECT-TYPE
SYNTAX  INTEGER { dense(1), sparse(2) }
       MAX-ACCESS  read-only
       STATUS  current
       DESCRIPTION
"The active PIM mode of this neighbor."
        ::= { utsPimNeighborEntry 5 }

utsPimNeighborDRPriority OBJECT-TYPE
SYNTAX  INTEGER
       MAX-ACCESS  read-only
       STATUS  current
       DESCRIPTION
"The value of the Designated Router Priority from the last PIM Hello message received from this neighbor."
        ::= { utsPimNeighborEntry 6 }

--
-- ip pim rp table
--

utsIpPIMRPObj OBJECT IDENTIFIER ::= { utsIpMulticastExt 4 }

utsPimRpTable OBJECT-TYPE
SYNTAX  SEQUENCE OF UtsPimRpEntry
        MAX-ACCESS  not-accessible
        STATUS  current
        DESCRIPTION
"Table for dot3 OLT MIBs."
        ::= { utsIpPIMRPObj 1 }

utsPimRpEntry OBJECT-TYPE
SYNTAX  UtsPimRpEntry
       MAX-ACCESS  not-accessible
       STATUS  current
       DESCRIPTION
"An entry in the dot3 PLT MIBs table."
       INDEX  { utsPimRpGroupAddress, utsPimRpGroupMask, utsPimRpAddress }
       ::= { utsPimRpTable 1 }

UtsPimRpEntry ::=
       SEQUENCE {
                    utsPimRpGroupAddress	IpAddress,
                    utsPimRpGroupMask		IpAddress,
                    utsPimRpAddress		IpAddress,
                    utsPimRpUpTime		TimeTicks,
                    utsPimRpHoldTime		INTEGER,
                    utsPimRpPriority		INTEGER,
                    utsPimRpInfoSource		IpAddress,
                    utsPimRpVersion		INTEGER,
                    utsPimRpType		INTEGER,
                    utsPimRpStatus		RowStatus
--                    utsPimRpActivity      INTEGER
       }


utsPimRpGroupAddress OBJECT-TYPE
SYNTAX  IpAddress
       MAX-ACCESS  read-only
       STATUS  current
       DESCRIPTION
"The IP multicast group address for which this entry contains information about an RP."
        ::= { utsPimRpEntry 1 }

utsPimRpGroupMask OBJECT-TYPE
SYNTAX  IpAddress
       MAX-ACCESS  read-only
       STATUS  current
       DESCRIPTION
"The multicast group address mask"
        ::= { utsPimRpEntry 2 }

utsPimRpAddress OBJECT-TYPE
SYNTAX  IpAddress
       MAX-ACCESS  read-only
       STATUS  current
       DESCRIPTION
"The unicast address of the RP."
        ::= { utsPimRpEntry 3 }

utsPimRpUpTime OBJECT-TYPE
SYNTAX  TimeTicks
       MAX-ACCESS  read-only
       STATUS  current
       DESCRIPTION
"The time since this PIM RP (last) was learned by the local router."
        ::= { utsPimRpEntry 4 }

utsPimRpHoldTime OBJECT-TYPE
SYNTAX  INTEGER
       MAX-ACCESS  read-only
       STATUS  current
       DESCRIPTION
"The holdtime of this RP entry.  This object is 0 ifpimRPSetRPType is not 'bsr'."
        ::= { utsPimRpEntry 5 }

utsPimRpPriority OBJECT-TYPE
SYNTAX  INTEGER
       MAX-ACCESS  read-only
       STATUS  current
       DESCRIPTION
"The RP Priority in the PIM Candidate-RP-Advertisement
 message or PIM Bootstrap message by which this RP was learned."
        ::= { utsPimRpEntry 6 }

utsPimRpInfoSource OBJECT-TYPE
SYNTAX  IpAddress
       MAX-ACCESS  read-only
       STATUS  current
       DESCRIPTION
"The router that this RP information received from."
        ::= { utsPimRpEntry 7 }

utsPimRpVersion OBJECT-TYPE
SYNTAX  INTEGER
       MAX-ACCESS  read-only
       STATUS  current
       DESCRIPTION
"The version of PIM which is running on this interface."
        ::= { utsPimRpEntry 8 }

utsPimRpType OBJECT-TYPE
SYNTAX  INTEGER
        {
          static (1),
          bsr (2),
          embedded (3),
          other (4)
        }
       MAX-ACCESS  read-only
       STATUS  current
       DESCRIPTION
"This object indicates how the RP was learnt. 'static'
 means from local configuration, 'bsr' means the PIM
 Bootstrap Router (BSR) mechanism"
        ::= { utsPimRpEntry 9 }

utsPimRpStatus OBJECT-TYPE
SYNTAX  RowStatus
       MAX-ACCESS  read-create
       STATUS  current
       DESCRIPTION
"Row status for the current entry."
        ::= { utsPimRpEntry 10 }


--
-- ip pim candidate rp table
--

 utsIpPIMCandiRPObj OBJECT IDENTIFIER ::= { utsIpMulticastExt 5 }

 utsPimCandidateRPTable OBJECT-TYPE
 SYNTAX  SEQUENCE OF UtsPimCandidateRPEntry
        MAX-ACCESS  not-accessible
        STATUS  current
        DESCRIPTION
"Table for pim candidate rp MIBs."
        ::= { utsIpPIMCandiRPObj 1 }

utsPimCandidateRPEntry OBJECT-TYPE
SYNTAX  UtsPimCandidateRPEntry
       MAX-ACCESS  not-accessible
       STATUS  current
       DESCRIPTION
	"An entry in the candidate rp MIBs table."
       INDEX  { utsPimCandidateRPGrpAddress,utsPimCandidateRPGrpAddressMask,utsPimCandidateRPIntfIndex }
       ::= { utsPimCandidateRPTable 1 }

UtsPimCandidateRPEntry ::=
       SEQUENCE {
                    utsPimCandidateRPIntfIndex			InterfaceIndex,
                    utsPimCandidateRPGrpAddress			IpAddress,
                    utsPimCandidateRPGrpAddressMask	IpAddress,
                    utsPimCandidateRPPriority			INTEGER,
                    utsPimCandidateRPHoldTimer			INTEGER,
                    utsPimCandidateRPRowStatus			RowStatus
       }

utsPimCandidateRPIntfIndex OBJECT-TYPE
SYNTAX  InterfaceIndex
       MAX-ACCESS  read-only
       STATUS  current
       DESCRIPTION
"The ifIndex value of this PIM interface."
        ::= { utsPimCandidateRPEntry 1 }

utsPimCandidateRPGrpAddress OBJECT-TYPE
SYNTAX  IpAddress
       MAX-ACCESS  read-create
       STATUS  current
       DESCRIPTION
"Multicast group ip address that the router will advertise to BSR"
        ::= { utsPimCandidateRPEntry 2 }

utsPimCandidateRPGrpAddressMask OBJECT-TYPE
SYNTAX  IpAddress
       MAX-ACCESS  read-create
       STATUS  current
       DESCRIPTION
"Multicast group ip address mask that the router will advertise to BSR"
        ::= { utsPimCandidateRPEntry 3 }

utsPimCandidateRPPriority OBJECT-TYPE
SYNTAX  INTEGER (0..255)
       MAX-ACCESS  read-create
       STATUS  current
       DESCRIPTION
"Rp priority."
        ::= { utsPimCandidateRPEntry 4 }

utsPimCandidateRPHoldTimer OBJECT-TYPE
SYNTAX  INTEGER
       MAX-ACCESS  read-create
       STATUS  current
       DESCRIPTION
"RP hold time.
For 1000:The range is (3..65535).
For 4000:The range is (0..255)"
       DEFVAL{150}
        ::= { utsPimCandidateRPEntry 5 }

utsPimCandidateRPRowStatus OBJECT-TYPE
SYNTAX  RowStatus
       MAX-ACCESS  read-create
       STATUS  current
       DESCRIPTION
"The status of this entry"
        ::= { utsPimCandidateRPEntry 6 }


--
-- ip multicast table
--

utsIpMRouteObj OBJECT IDENTIFIER ::= { utsIpMulticastExt 6 }

utsIpMulticastRoutingTable OBJECT-TYPE
SYNTAX  SEQUENCE OF UtsIpMulticastRoutingEntry
        MAX-ACCESS  not-accessible
        STATUS  current
        DESCRIPTION
"Table for dot3 OLT MIBs."
        ::= { utsIpMRouteObj 1 }

utsIpMulticastRoutingEntry OBJECT-TYPE
SYNTAX  UtsIpMulticastRoutingEntry
       MAX-ACCESS  not-accessible
       STATUS  current
       DESCRIPTION
"An entry in the ip multicast route MIBs table."
       INDEX  { utsIpMRouteGroup,utsIpMRouteOutIfIndex, utsIpMRouteSource}
       ::= { utsIpMulticastRoutingTable 1 }

UtsIpMulticastRoutingEntry ::=
       SEQUENCE {
                    utsIpMRouteGroup		IpAddress,
                    utsIpMRouteSource		IpAddress,
                    utsIpMRouteSourceMask	IpAddress,
                    utsIpMRouteUpTime		TimeTicks,
                    utsIpMRouteExpiryTime	TimeTicks,
                    utsIpMRouteRpAddress	IpAddress,
                    utsIpMRouteInIfIndex	InterfaceIndexOrZero,
                    utsIpMRouteOutIfIndex	InterfaceIndexOrZero,
                    utsIpMRouteRPFNeighb	IpAddress,
                    utsIpMRouteFlag		BITS
       }

utsIpMRouteGroup OBJECT-TYPE
SYNTAX  IpAddress
       MAX-ACCESS  read-only
       STATUS  current
       DESCRIPTION
"The IP multicast group address for which this entry contains multicast routing information."
        ::= { utsIpMulticastRoutingEntry 1 }

utsIpMRouteSource OBJECT-TYPE
SYNTAX  IpAddress
       MAX-ACCESS  read-only
       STATUS  current
       DESCRIPTION
"The network address which when combined with the corresponding
 value of ipMRouteSourceMask identifies the sources for which
 this entry contains multicast routing information."
        ::= { utsIpMulticastRoutingEntry 2 }

utsIpMRouteSourceMask OBJECT-TYPE
SYNTAX  IpAddress
       MAX-ACCESS  read-only
       STATUS  current
       DESCRIPTION
"The network mask which when combined with the corresponding value
 of ipMRouteSource identifies the sources for which this entry
 contains multicast routing information."
        ::= { utsIpMulticastRoutingEntry 3 }

utsIpMRouteUpTime OBJECT-TYPE
SYNTAX  TimeTicks
       MAX-ACCESS  read-only
       STATUS  current
       DESCRIPTION
"The time since the multicast routing information represented
 by this entry was learned by the router."
        ::= { utsIpMulticastRoutingEntry 4 }

utsIpMRouteExpiryTime OBJECT-TYPE
SYNTAX  TimeTicks
       MAX-ACCESS  read-only
       STATUS  current
       DESCRIPTION
"The minimum amount of time remaining before this entry will be aged out."
        ::= { utsIpMulticastRoutingEntry 5 }

utsIpMRouteRpAddress OBJECT-TYPE
SYNTAX  IpAddress
       MAX-ACCESS  read-only
       STATUS  current
       DESCRIPTION
"The address of the Rendezvous Point (RP) for the group
 represented by pimMRouteGroup."
        ::= { utsIpMulticastRoutingEntry 6 }


utsIpMRouteInIfIndex OBJECT-TYPE
SYNTAX  InterfaceIndexOrZero
       MAX-ACCESS  read-only
       STATUS  current
       DESCRIPTION
"The value of ifIndex for the interface on which IP
 datagrams sent by these sources to this multicast address are received."
        ::= { utsIpMulticastRoutingEntry 7 }

utsIpMRouteOutIfIndex OBJECT-TYPE
SYNTAX  InterfaceIndexOrZero
       MAX-ACCESS  read-only
       STATUS  current
       DESCRIPTION
"The value of ifIndex for the interface from which IP datagrams of this group will be sent out."
        ::= { utsIpMulticastRoutingEntry 8 }

utsIpMRouteRPFNeighb OBJECT-TYPE
SYNTAX  IpAddress
       MAX-ACCESS  read-only
       STATUS  current
       DESCRIPTION
"The address of the RPF neighbor, from which IP datagrams sent by
 these sources to this multicast group address are received, or zero
 if the RPF neighbor is unknown or is not a PIM neighbor."
        ::= { utsIpMulticastRoutingEntry 9 }

utsIpMRouteFlag OBJECT-TYPE
SYNTAX  BITS {dense(0),
              sparse(1),
              connected(2),
              local(3),
              pruned(4),
              rp-bit-set(5),
              register-flag(6),
              spt-bit-set(7),
              join-spt(8)}
       MAX-ACCESS  read-only
       STATUS  current
       DESCRIPTION
"Indicate multicast route attribute carried on this entry"
        ::= { utsIpMulticastRoutingEntry 10 }

--
-- IP PIM CBSR Group
--  zhaoxf add 21 Apri,2006
--

utsIpPIMExtCBSRConf OBJECT IDENTIFIER ::= { utsIpMulticastExt 7 }


utsIpPIMExtCBSRStatus OBJECT-TYPE
   SYNTAX      INTEGER
    {
     enable(1),
     disable(2)
    }
	MAX-ACCESS  read-write
	STATUS      current
	DESCRIPTION
	    "PIM configured CBSR status, the default status is disabled."
	DEFVAL      { disable }
   ::= { utsIpPIMExtCBSRConf 1 }


utsIpPIMExtCBSRInterface OBJECT-TYPE
    SYNTAX      INTEGER
	MAX-ACCESS  read-write
	STATUS      current
	DESCRIPTION
	    "PIM configured CBSR interface, which must
	     be a route port interface or SVI or super SVI."
   ::= { utsIpPIMExtCBSRConf 2 }


utsIpPIMExtCBSRPriority OBJECT-TYPE
SYNTAX  INTEGER (0..255)
        MAX-ACCESS  read-write
        STATUS  current
        DESCRIPTION
           "The priority for the local interface as a candidate bootstrap router.
           This object is mapping to CLI command: ip pim bsr-candidate"
        DEFVAL     { 0 }
        ::= { utsIpPIMExtCBSRConf 3}


utsIpPIMExtCBSRHashMaskLen OBJECT-TYPE
SYNTAX  INTEGER (0..32)
        MAX-ACCESS  read-write
        STATUS  current
        DESCRIPTION
           "Hash Mask length for RP selection."
        DEFVAL     { 0 }
        ::= { utsIpPIMExtCBSRConf 4 }


------
------   IP ARP Configuration
------

utsIpArpObjs OBJECT IDENTIFIER ::= { utsLayer3ConfExt 8 }


utsEponArpTable OBJECT-TYPE
    SYNTAX SEQUENCE OF UtsEponArpEntry
    MAX-ACCESS not-accessible
    STATUS current
    DESCRIPTION
        "Table for arp mapping entry."
    ::= {  utsIpArpObjs 1 }

utsEponArpEntry OBJECT-TYPE
    SYNTAX UtsEponArpEntry
    MAX-ACCESS  not-accessible
    STATUS current
    DESCRIPTION
        "An entry in the arp MIB table."
    INDEX { utsEponArpIpAddress }
    ::= { utsEponArpTable 1 }

UtsEponArpEntry ::=
    SEQUENCE {
        utsEponArpIpAddress
		    IpAddress,
	    utsEponArpMacAddress
	            PhysAddress,
	    utsEponArpIntfType
		    INTEGER,
	    utsEponArpModuleId
		    INTEGER,
	    utsEponArpPortId
		    INTEGER,
	    utsEponArpLinkAggGroupId
		    INTEGER,
	    utsEponArpVlanId
		    INTEGER,
	    utsEponArpItemType
	            INTEGER,
	    utsEponArpVlanSubVlanId
		    INTEGER,
	    utsEponArpRowStatus
		    RowStatus
    }

utsEponArpIpAddress OBJECT-TYPE
   SYNTAX      IpAddress
	MAX-ACCESS 	read-create
	STATUS      current
	DESCRIPTION
	   "IP Address of the arp Entry."
	::= { utsEponArpEntry 1 }

utsEponArpMacAddress OBJECT-TYPE
   SYNTAX      PhysAddress
	MAX-ACCESS 	read-create
	STATUS      current
	DESCRIPTION
	   "mac Address of the arp Entry."
	::= { utsEponArpEntry 2 }

utsEponArpIntfType  OBJECT-TYPE
   SYNTAX      INTEGER {
	  port-based(1),
	  lag-based(2),
	  vlan-based(3),
	  super-vlan-based(4),
	  onu-vlan-based(5)
	}
	MAX-ACCESS  read-create
	STATUS      current
	DESCRIPTION
	    "Indicates the arp interface type."
	::= { utsEponArpEntry 3 }


utsEponArpModuleId  OBJECT-TYPE
   SYNTAX       INTEGER
	MAX-ACCESS   read-create
	STATUS       current
	DESCRIPTION
	    "Module Id of the arp Entry. It is valid if the ArpItemType
		is port-based or valid when vlan-based member has been added."
	::= { utsEponArpEntry 4 }

utsEponArpPortId  OBJECT-TYPE
   SYNTAX       INTEGER
	MAX-ACCESS   read-create
	STATUS       current
	DESCRIPTION
	    "Port Id of the arp Entry. It is valid if the ArpItemType
		is port-based or valid when vlan-based member has been added"
	::= { utsEponArpEntry 5 }

utsEponArpLinkAggGroupId  OBJECT-TYPE
   SYNTAX       INTEGER
	MAX-ACCESS   read-create
	STATUS       current
	DESCRIPTION
	    "aggregation link group Id of the arp Entry. It is only valid if the arp
		 entry is based on Link Aggregation port. ArpItemType is lag-based"
	::= { utsEponArpEntry 6 }

utsEponArpVlanId  OBJECT-TYPE
    SYNTAX       INTEGER
	MAX-ACCESS   read-create
	STATUS       current
	DESCRIPTION
	    "VLAN Id of the arp Entry. It is only valid if the arp
		 entry is based on VLAN Id. ArpItemType is vlan-based"
	::= { utsEponArpEntry 7 }

utsEponArpItemType  OBJECT-TYPE
   SYNTAX       INTEGER
	{
      static(1),
      dynamic(2),
            invalid(3),
            dhcp(4)
	}
	MAX-ACCESS   read-create
	STATUS       current
	DESCRIPTION
	    "Identify the arp learning type of the arp Entry.
	    static - created by system operator.
	    dynamic - learned by arp protocol.
	    Invalid - not complete  "
	::= { utsEponArpEntry 8 }



utsEponArpVlanSubVlanId  OBJECT-TYPE
   SYNTAX       INTEGER (2..4094)
	MAX-ACCESS   read-create
	STATUS       current
	DESCRIPTION
	    "Identify the memeber's SubVlan Id within the Super VLAN of the arp Entry. It is only
	    valid if the arp entry is based on Super VLAN Id. ArpItemType is super-vlan-based"
	::= { utsEponArpEntry 9 }

utsEponArpRowStatus OBJECT-TYPE
    SYNTAX      RowStatus
    MAX-ACCESS  read-create
    STATUS      current
    DESCRIPTION
        "Writing invalid has the effect of adding/deleting this entry.
  		 Only be able to create/delete setting to createAndGo/destory.
  		 active will be returned when query"
    ::= { utsEponArpEntry 10 }



utsIgmpMIBObjects OBJECT IDENTIFIER ::= { utsLayer3ConfExt 9 }

--
--  The IGMP Interface Table
--

utsIgmpInterfaceTable OBJECT-TYPE
    SYNTAX     SEQUENCE OF UtsIgmpInterfaceEntry
    MAX-ACCESS not-accessible
    STATUS     current
    DESCRIPTION
            "The (conceptual) table listing the interfaces on which IGMP
            is enabled."
    ::= { utsIgmpMIBObjects 1 }

utsIgmpInterfaceEntry OBJECT-TYPE
    SYNTAX     UtsIgmpInterfaceEntry
    MAX-ACCESS not-accessible
    STATUS     current
    DESCRIPTION
            "An entry (conceptual row) representing an interface on
            which IGMP is enabled."
    INDEX      { utsIgmpIntfIfIndex }
    ::= { utsIgmpInterfaceTable 1 }

UtsIgmpInterfaceEntry ::= SEQUENCE {
    utsIgmpIntfIfIndex               InterfaceIndex,
    utsIgmpIntfVersion               INTEGER,
    utsIgmpIntfQuerier               IpAddress,
    utsIgmpIntfGrpMembInterval	     INTEGER,
    utsIgmpIntfLastMembQueryIntvl    INTEGER,
    utsIgmpIntfQueryInterval         INTEGER,
    utsIgmpIntfQueryMaxRespTime      INTEGER,
    utsIgmpIntfRobustness            INTEGER,
    utsIgmpIntfStartupQueryIntval    INTEGER,
    utsIgmpIntfUnsolictReportIntval  INTEGER,
    utsIgmpIntfGroups                INTEGER,
    utsIgmpIntfProxyStatus	     INTEGER
-- Deleted by Zhaoxf Dec 10, 2006
--    utsIgmpIntfStatus           RowStatus
}

utsIgmpIntfIfIndex OBJECT-TYPE
    SYNTAX     InterfaceIndex
    MAX-ACCESS not-accessible
    STATUS     current
    DESCRIPTION
            "The ifIndex value of the interface for which IGMP is enabled."
    ::= { utsIgmpInterfaceEntry 1 }

utsIgmpIntfVersion OBJECT-TYPE
    SYNTAX     INTEGER
    {
       disable-igmp(0),
       version2(2)
    }
    MAX-ACCESS read-write
    STATUS     current
    DESCRIPTION
            "The version of IGMP which is running on this interface.
            This object can be used to configure a router capable of
            running either value.  For IGMP to function correctly, all
            routers on a LAN must be configured to run the same version
            of IGMP on that LAN."
    DEFVAL     { 2 }
    ::= { utsIgmpInterfaceEntry 2 }

utsIgmpIntfQuerier OBJECT-TYPE
    SYNTAX     IpAddress
    MAX-ACCESS read-only
    STATUS     current
    DESCRIPTION
            "The address of the IGMP Querier on the IP subnet to which
            this interface is attached."
    ::= { utsIgmpInterfaceEntry 3 }

utsIgmpIntfGrpMembInterval OBJECT-TYPE
    SYNTAX     INTEGER
    UNITS      "seconds"
    MAX-ACCESS read-only
    STATUS     current
    DESCRIPTION
            "The Group Membership Interval is the amount of time that
            must pass before a multicast router decides there are no
            more members of a group on a network.  This value MUST be
            ((the Robustness Variable) times (the Query Interval))
            plus (one Query Response Interval)."
    ::= { utsIgmpInterfaceEntry 4 }

utsIgmpIntfLastMembQueryIntvl OBJECT-TYPE
    SYNTAX     INTEGER (1..3600)
    UNITS      "seconds"
    MAX-ACCESS read-write
    STATUS     current
    DESCRIPTION
            "The Last Member Query Interval is the Max Response Time
            inserted into Group-Specific Queries sent in response to
            Leave Group messages, and is also the amount of time between
            Group-Specific Query messages.  This value may be tuned to
            modify the leave latency of the network.  A reduced value
            results in reduced time to detect the loss of the last
            member of a group.  The value of this object is irrelevant
            if igmpInterfaceVersion is 1."
    DEFVAL     { 1 }
    ::= { utsIgmpInterfaceEntry 5 }

utsIgmpIntfQueryInterval OBJECT-TYPE
    SYNTAX     INTEGER
    UNITS      "seconds"
    MAX-ACCESS read-write
    STATUS     current
    DESCRIPTION
            "The frequency at which IGMP Host-Query packets are
            transmitted on this interface."
    DEFVAL     { 125 }
    ::= { utsIgmpInterfaceEntry 6 }

utsIgmpIntfQueryMaxRespTime OBJECT-TYPE
    SYNTAX     INTEGER (10..25)
    UNITS      "seconds"
    MAX-ACCESS read-write
    STATUS     current
    DESCRIPTION
            "The maximum query response time advertised in IGMPv2
            queries on this interface."
    DEFVAL     { 10 }
    ::= { utsIgmpInterfaceEntry 7 }

utsIgmpIntfRobustness OBJECT-TYPE
    SYNTAX     INTEGER (2..10)
    MAX-ACCESS read-write
    STATUS     current
    DESCRIPTION
            "The Robustness Variable allows tuning for the expected
            packet loss on a subnet.  If a subnet is expected to be
            lossy, the Robustness Variable may be increased.  IGMP is
            robust to (Robustness Variable-1) packet losses."
    DEFVAL     { 2 }
    ::= { utsIgmpInterfaceEntry 8 }

utsIgmpIntfStartupQueryIntval OBJECT-TYPE
    SYNTAX     INTEGER (10..3600)
    UNITS      "seconds"
    MAX-ACCESS read-write
    STATUS     current
    DESCRIPTION
            "the interval between General Queries sent by a Querier
            on startup.  Default: 1/4 the Query Interval."
    DEFVAL     { 32 }
    ::= { utsIgmpInterfaceEntry 9 }

utsIgmpIntfUnsolictReportIntval OBJECT-TYPE
    SYNTAX     INTEGER (10..3600)
    UNITS      "seconds"
    MAX-ACCESS read-write
    STATUS     current
    DESCRIPTION
            "The Unsolicited Report Interval is the time between
            repetitions of a host's initial report of membership
            in a group.  Default: 10 seconds."
    DEFVAL     { 10 }
    ::= { utsIgmpInterfaceEntry 10 }

utsIgmpIntfGroups OBJECT-TYPE
    SYNTAX     INTEGER
    MAX-ACCESS read-only
    STATUS     current
    DESCRIPTION
            "The current number of entries for this interface in the
            Cache Table."
    ::= { utsIgmpInterfaceEntry 11 }

utsIgmpIntfProxyStatus OBJECT-TYPE
    SYNTAX     INTEGER
    {
       enable(1),
       disable(2)
    }
    MAX-ACCESS read-write
    STATUS     current
    DESCRIPTION
            "enable igmp proxy on this interface"
    ::= { utsIgmpInterfaceEntry 12 }

-- Deleted by zhaoxf Dec 11, 2006

-- utsIgmpIntfStatus OBJECT-TYPE
--  SYNTAX     RowStatus
--    MAX-ACCESS read-write
--    STATUS     current
--    DESCRIPTION
--            "The activation of a row enables IGMP on the interface.  The
--            destruction of a row disables IGMP on the interface."
--    ::= { utsIgmpInterfaceEntry 13 }

--
--  The IGMP Cache Table
--

utsIgmpCacheTable OBJECT-TYPE
    SYNTAX     SEQUENCE OF UtsIgmpCacheEntry
    MAX-ACCESS not-accessible
    STATUS     current
    DESCRIPTION
            "The (conceptual) table listing the IP multicast groups for
            which there are members on a particular interface."
    ::= { utsIgmpMIBObjects 2 }

utsIgmpCacheEntry OBJECT-TYPE
    SYNTAX     UtsIgmpCacheEntry
    MAX-ACCESS not-accessible
    STATUS     current
    DESCRIPTION
            "An entry (conceptual row) in the igmpCacheTable."
    INDEX      { utsIgmpCacheIfIndex, utsIgmpCacheGroupAddress }
    ::= { utsIgmpCacheTable 1 }

UtsIgmpCacheEntry ::= SEQUENCE {
    utsIgmpCacheIfIndex            InterfaceIndex,
    utsIgmpCacheGroupAddress       IpAddress,
    utsIgmpCacheType		   			INTEGER,
    utsIgmpCacheLastReporter       IpAddress,
    utsIgmpCacheExpiryTime         TimeTicks,
    utsIgmpCacheStatus             RowStatus
}

utsIgmpCacheIfIndex OBJECT-TYPE
    SYNTAX     InterfaceIndex
    MAX-ACCESS not-accessible
    STATUS     current
    DESCRIPTION
            "The ifIndex for which this entry contains information for an IP multicast group address."
    ::= { utsIgmpCacheEntry 1 }


utsIgmpCacheGroupAddress OBJECT-TYPE
    SYNTAX     IpAddress
    MAX-ACCESS not-accessible
    STATUS     current
    DESCRIPTION
            "The IP multicast group address for which this entry contains information."
    ::= { utsIgmpCacheEntry 2 }

utsIgmpCacheType OBJECT-TYPE
    SYNTAX     INTEGER
    {
       static(1),
       dynamic(2)
    }
    MAX-ACCESS read-create
    STATUS     current
    DESCRIPTION
            "An indication of whether the local system is a member of this group address on this interface."
    ::= { utsIgmpCacheEntry 3 }

utsIgmpCacheLastReporter OBJECT-TYPE
    SYNTAX     IpAddress
    MAX-ACCESS read-only
    STATUS     current
    DESCRIPTION
            "The IP address of the source of the last membership report
            received for this IP Multicast group address on this
            interface.  If no membership report has been received, this
            object has the value 0.0.0.0."
    ::= { utsIgmpCacheEntry 4 }

utsIgmpCacheExpiryTime OBJECT-TYPE
    SYNTAX     TimeTicks
    MAX-ACCESS read-only
    STATUS     current
    DESCRIPTION
            "The minimum amount of time remaining before this entry will
            be aged out.  A value of 0 indicates that the entry is only
            present because igmpCacheSelf is true and that if the router
            left the group, this entry would be aged out immediately.
            Note that some implementations may process membership
            reports from the local system in the same way as reports
            from other hosts, so a value of 0 is not required."
    ::= { utsIgmpCacheEntry 5 }

utsIgmpCacheStatus OBJECT-TYPE
    SYNTAX     RowStatus
    MAX-ACCESS read-create
    STATUS     current
    DESCRIPTION
            "The status of this entry."
    ::= { utsIgmpCacheEntry 6 }

--
--  The IGMP Snooping Table
--

utsIgmpSnoopingTable OBJECT-TYPE
    SYNTAX     SEQUENCE OF UtsIgmpSnoopingEntry
    MAX-ACCESS not-accessible
    STATUS     current
    DESCRIPTION
            "The IGMP Snooping Table."
    ::= { utsIgmpMIBObjects 3 }

utsIgmpSnoopingEntry OBJECT-TYPE
    SYNTAX     UtsIgmpSnoopingEntry
    MAX-ACCESS not-accessible
    STATUS     current
    DESCRIPTION
            "An entry in the igmp snooping table."
    INDEX      { utsIgmpSnoopingVID, utsIgmpSnoopingGroupAddress }
    ::= { utsIgmpSnoopingTable 1 }

UtsIgmpSnoopingEntry ::= SEQUENCE {
    utsIgmpSnoopingVID             INTEGER,
    utsIgmpSnoopingGroupAddress    IpAddress,
    utsIgmpSnoopingType		   	   INTEGER,
    utsIgmpSnoopingExpiryTime      TimeTicks,
    utsIgmpSnoopingEgressPortList  OCTET STRING,
    utsIgmpSnoopingRowStatus       RowStatus
}

utsIgmpSnoopingVID OBJECT-TYPE
    SYNTAX     INTEGER
    MAX-ACCESS not-accessible
    STATUS     current
    DESCRIPTION
            "The VLAN ID in the igmp snooping table."
    ::= { utsIgmpSnoopingEntry 1 }


utsIgmpSnoopingGroupAddress OBJECT-TYPE
    SYNTAX     IpAddress
    MAX-ACCESS not-accessible
    STATUS     current
    DESCRIPTION
            "The IP multicast group address for which this entry contains information."
    ::= { utsIgmpSnoopingEntry 2 }

utsIgmpSnoopingType OBJECT-TYPE
    SYNTAX     INTEGER
    {
       static(1),
       dynamic(2)
    }
    MAX-ACCESS read-create
    STATUS     current
    DESCRIPTION
            "An indication of whether the local system is a member of this group address on this interface."
    ::= { utsIgmpSnoopingEntry 3 }

utsIgmpSnoopingExpiryTime OBJECT-TYPE
    SYNTAX     TimeTicks
    MAX-ACCESS read-only
    STATUS     current
    DESCRIPTION
            "The expiry time, when snooping type is static, the expirey time should be display never."
    ::= { utsIgmpSnoopingEntry 4 }

utsIgmpSnoopingEgressPortList OBJECT-TYPE
    SYNTAX     OCTET STRING
    MAX-ACCESS read-create
    STATUS     current
    DESCRIPTION
            "Each octet within this value specifies a set of eight ports, with the
         first octet specifying ports 1 through 8, the second octet specifying
         ports 9 through 16, etc.  Within each octet, the most significant bit
         represents the lowest numbered port, and the least significant bit
         represents the highest numbered port.  Thus, each port of the bridge
         is represented by a single bit within the value of this object.  If that
         bit has a value of '1' then that port is included in the set of ports;
         the port is not included if its bit has a value of '0'."
    ::= { utsIgmpSnoopingEntry 5 }

utsIgmpSnoopingRowStatus OBJECT-TYPE
    SYNTAX     RowStatus
    MAX-ACCESS read-create
    STATUS     current
    DESCRIPTION
            "The status of this entry."
    ::= { utsIgmpSnoopingEntry 6 }

-------------------------------------------------------------------------------

------
------    PON's mib objects extension
------


--
--  EPON interface extension
--


utsEponConfExtObjects OBJECT IDENTIFIER ::= { utsEfmPonConfExt 1 }



------
------ 1. OLT
------


utsDot3OltMIB OBJECT IDENTIFIER ::= { utsEponConfExtObjects 1}

utsDot3OltObjects OBJECT IDENTIFIER ::= { utsDot3OltMIB 1}

utsDot3OltTable OBJECT-TYPE
SYNTAX  SEQUENCE OF UtsDot3OltEntry
        MAX-ACCESS  not-accessible
        STATUS  current
        DESCRIPTION
"Table for dot3 OLT MIBs."
        ::= { utsDot3OltObjects 1 }

utsDot3OltEntry OBJECT-TYPE
SYNTAX  UtsDot3OltEntry
       MAX-ACCESS  not-accessible
       STATUS  current
       DESCRIPTION
"An entry in the dot3 PLT MIBs table."
       INDEX  { ifIndex }
       ::= { utsDot3OltTable 1 }

UtsDot3OltEntry ::=
       SEQUENCE {
                    utsDot3OltModuleId					        INTEGER,
                    utsDot3OltPortId					        INTEGER,
                    utsDot3OltOperStatus				        INTEGER,
                    utsDot3OltMACAddress				        MacAddress,
                    utsDot3OltMaxLLID					        INTEGER,
                    utsDot3OltMACAddressAgingTime		        INTEGER,
                    utsDot3OltARPPON2CNI				        TruthValue,
                    utsDot3OltARPCNI2PON				        TruthValue,
                    utsDot3OltIGMPSnooping				        TruthValue,
                    utsDot3OltIGMPTimeout				        INTEGER,
                    utsDot3OltVlanTagExchangeDnLinkPrefix		INTEGER,
                    utsDot3OltVlanStackNestedModeVlanType		INTEGER,
                    utsDot3OltMultiCopyBroadcastEnable			TruthValue,
                    utsDot3OltDiscardUnlearnedAddress			TruthValue,
                    utsDot3OltHwVersion					        DisplayString,
                    utsDot3OltFwVersion					        DisplayString,
                    utsDot3OltTransceiverType				    INTEGER,
		            utsDot3OltAdminStatus                       INTEGER,
                    utsDot3OltTransceiverVendor                 INTEGER,
                    utsDot3OltRegisteredONUCount                INTEGER,
                    utsDot3OltOamLimit                          INTEGER,
--                    utsDot3OltAction                            INTEGER
                    utsDot3OltRunningMode                       INTEGER
       }


utsDot3OltModuleId OBJECT-TYPE
SYNTAX  INTEGER
       MAX-ACCESS  read-only
       STATUS  current
       DESCRIPTION
"A read-only value that identifies the olt module index"
        ::= { utsDot3OltEntry 1 }


utsDot3OltPortId OBJECT-TYPE
SYNTAX  INTEGER
       MAX-ACCESS  read-only
       STATUS  current
       DESCRIPTION
"A read-only value that identifies the olt port index"
        ::= { utsDot3OltEntry 2 }


utsDot3OltOperStatus OBJECT-TYPE
SYNTAX  INTEGER {
          up(1),
          down(2)
          -- ,testing(3)
      }
       MAX-ACCESS  read-only
       STATUS  current
       DESCRIPTION
"A  read-only value that identifies the operational state of the  Multi-
Point MAC Control sublayer as defined in [802.3ah] clause 64. When  this
attribute has the enumeration 'unregistered' the interface may  be  used
for  registering a link partner. When this attribute has the enumeration
'registering'  the  interface is in the process of registering  a  link-
partner.  When  this  attribute  has the  enumeration  'registered'  the
interface has an established link-partner. It's identical to
dot3MpcpRegistrationState in Dot3MpcpEntry."
       REFERENCE   "[802.3ah], 30.3.5.1.7."
        ::= { utsDot3OltEntry 3 }

utsDot3OltMACAddress OBJECT-TYPE
SYNTAX  MacAddress
       MAX-ACCESS  read-only
       STATUS  current
       DESCRIPTION
"A  read-only value that identifies the source_address parameter of OLT"
       REFERENCE   "[802.3ah], 30.3.5.1.6."
        ::= { utsDot3OltEntry 4 }

utsDot3OltMaxLLID OBJECT-TYPE
SYNTAX  INTEGER
       MAX-ACCESS  read-only
       STATUS  current
       DESCRIPTION
"Maximum number of supported LLID."
        ::= { utsDot3OltEntry 5 }


utsDot3OltMACAddressAgingTime OBJECT-TYPE
SYNTAX  INTEGER
       MAX-ACCESS  read-only
       STATUS  current
       DESCRIPTION
"The time after which a MAC address will be removed from OLT address table,
measured in milliseconds. 0-86400000."
        ::= { utsDot3OltEntry 6 }

utsDot3OltARPPON2CNI OBJECT-TYPE
SYNTAX  TruthValue
       MAX-ACCESS  read-only
       STATUS  current
       DESCRIPTION
"Enable ARP from PON port to CNI port. Fixed value = true"
        ::= { utsDot3OltEntry 8 }

utsDot3OltARPCNI2PON OBJECT-TYPE
SYNTAX  TruthValue
       MAX-ACCESS  read-only
       STATUS  current
       DESCRIPTION
"Enable ARP from CNI port to PON port. Fixed value = true."
        ::= { utsDot3OltEntry 9 }


utsDot3OltIGMPSnooping OBJECT-TYPE
SYNTAX  TruthValue
       MAX-ACCESS  read-only
       STATUS  current
       DESCRIPTION
"enable/disable IGMP Snooping function on the olt pon port"
        ::= { utsDot3OltEntry 10 }

utsDot3OltIGMPTimeout OBJECT-TYPE
SYNTAX  INTEGER
       MAX-ACCESS  read-only
       STATUS  current
       DESCRIPTION
"Remove a group address from the ONU IGMP filter table according
to membership message timeout, measureded in seconds. 16-bit value."
        ::= { utsDot3OltEntry 11 }

utsDot3OltVlanTagExchangeDnLinkPrefix OBJECT-TYPE
SYNTAX  INTEGER (0..255)
       MAX-ACCESS  read-only
       STATUS  current
       DESCRIPTION
"VLAN tag prefix for VLAN exchange handling of downlink traffic.
8-bit value."
        ::= { utsDot3OltEntry 12 }

utsDot3OltVlanStackNestedModeVlanType OBJECT-TYPE
SYNTAX  INTEGER (0..65535)
       MAX-ACCESS  read-only
       STATUS  current
       DESCRIPTION
"Nested VLAN type. This is the only non-common (0x8100 or
0x9100) value Set LLID VLAN configuration can configure for
nested mode VLAN type for stacked VLAN of any LLID. It will
be used for a ONU only if stack handling mode is selected and
utsDot3OnuVlanStackNestedMode is TRUE and utsDot3OnuVlanStackNestedModeVlanType
is vlanTypeOther. Return fixed value 33024 (0x8100)."
        ::= { utsDot3OltEntry 13 }


utsDot3OltMultiCopyBroadcastEnable OBJECT-TYPE
SYNTAX  TruthValue
	MAX-ACCESS  read-only
       STATUS  current
       DESCRIPTION
	        "Enabling / disabling this option determines the ability
	         to support multiple LLIDs VLANs. Return fixed value 'false'."
        ::= { utsDot3OltEntry 14 }


utsDot3OltDiscardUnlearnedAddress OBJECT-TYPE
SYNTAX  TruthValue
MAX-ACCESS  read-only
       STATUS  current
       DESCRIPTION
	      "Forward / discard any frame received from unlearned source
	      address when originating ONU entries limit inside address table
		  is reached. Fixed value = true."
        ::= { utsDot3OltEntry 15 }


utsDot3OltHwVersion OBJECT-TYPE
SYNTAX  DisplayString
       MAX-ACCESS  read-only
       STATUS  current
       DESCRIPTION
"Hardware version of OLT. Returns default value M3."
        ::= { utsDot3OltEntry 16 }

utsDot3OltFwVersion OBJECT-TYPE
SYNTAX  DisplayString
       MAX-ACCESS  read-only
       STATUS  current
       DESCRIPTION
"Firmware version of OLT."
        ::= { utsDot3OltEntry 17 }


utsDot3OltTransceiverType OBJECT-TYPE
SYNTAX  INTEGER {
        null(1),
        sff(3),
        sfp(5)
}
       MAX-ACCESS  read-only
       STATUS  current
       DESCRIPTION
"transceiver type for the following transceiver table."
        ::= { utsDot3OltEntry 18 }

utsDot3OltAdminStatus OBJECT-TYPE
     SYNTAX  INTEGER {
         up(1), -- ready to pass packets
         down(2), --
         testing(3) -- in some test mode
     }
     MAX-ACCESS  read-write
     STATUS  current
     DESCRIPTION
         "The desired state of the OLT module.  The
          testing(3) state indicates that no operational
          packets can be passed, current olt do not support testing mode."
     ::= { utsDot3OltEntry 19}
utsDot3OltTransceiverVendor OBJECT-TYPE
SYNTAX  INTEGER {
        zenko(1),
        zonu(2),
        infineon(3),
        fiberxon(4),
        ezconn(5)
}
       MAX-ACCESS  read-only
       STATUS  current
       DESCRIPTION
"transceiver vendor for the following transceiver table.
Returns fixed value fiberxon(4)."
        ::= { utsDot3OltEntry 20 }

utsDot3OltRegisteredONUCount OBJECT-TYPE
       SYNTAX  INTEGER (1..64)
       MAX-ACCESS  read-only
       STATUS  current
       DESCRIPTION
"Registered ONU number."
        ::= { utsDot3OltEntry 21 }

utsDot3OltOamLimit OBJECT-TYPE
       SYNTAX  INTEGER
       {
       	 enable(1),
       	 disable(2)
       }
       MAX-ACCESS  read-write
       STATUS  current
       DESCRIPTION
       "Enable or disable the oam configuration for rate limit."
       DEFVAL { disable }
        ::= { utsDot3OltEntry 22 }

--Added by tomsong 2006-06-22, move the configuration of running mode to PON port.
utsDot3OltRunningMode OBJECT-TYPE
    SYNTAX INTEGER
    {
      isp-service-tag-handling-mode(1),
      application-tag-handling-mode(2)
    }
    MAX-ACCESS  read-write
    STATUS current
    DESCRIPTION
         "Application tag handling mode: this mode is also called transparent mode, which means OLT
                                    will not do any tag manipulation and ONU is not associated
                                    to any specific tag. Traffic behind ONU can be either tagged
                                    or untagged depending upon applications. Internally OLT is
                                    in a transparent mode.
          ISP service tag handling mode: this mode is used to assign ISP service tag(s) to multiple
                                    ONUs so traffic belonging to a specific ISP can be forwarded
                                    directly according to the ISP service tag. Traffic behind
                                    ONU is always untagged. Internally OLT is in a stacked but
                                    not nested mode.
         "
    ::= { utsDot3OltEntry 23 }


utsDot3Olt2Objects OBJECT IDENTIFIER ::= { utsDot3OltMIB 3}

-- EPM04B PON module configurations

utsDot3Olt2Table OBJECT-TYPE
SYNTAX  SEQUENCE OF UtsDot3Olt2Entry
        MAX-ACCESS  not-accessible
        STATUS  current
        DESCRIPTION
"Table for OLT type 2 MIBs."
        ::= { utsDot3Olt2Objects 1 }

utsDot3Olt2Entry OBJECT-TYPE
SYNTAX  UtsDot3Olt2Entry
       MAX-ACCESS  not-accessible
       STATUS  current
       DESCRIPTION
"An entry in the OLT type 2 MIBs table."
       INDEX  { utsDot3Olt2ModuleId, utsDot3Olt2DeviceId}
       ::= { utsDot3Olt2Table 1 }

UtsDot3Olt2Entry ::=
       SEQUENCE {
                   utsDot3Olt2ModuleId					        INTEGER,
                   utsDot3Olt2DeviceId					        INTEGER,
                   utsDot3Olt2Status			                INTEGER,
                   utsDot3Olt2MACAddress				        MacAddress,
--                   utsDot3OltMACAddressAgingTime                INTEGER,
                   utsDot3OltPortIsolation				        INTEGER,
                   utsDot3OltDot1adEnable				        TruthValue,
--                   utsDot3OltDot1adTPID				            INTEGER,
                   utsDot3OltDot1xMode                          INTEGER,
                   utsDot3OltMPCPTimeout                        INTEGER,
                   utsDot3OltNNIFlowControlTxEnable             TruthValue,
                   utsDot3OltNNIFlowControlRxEnable             TruthValue,
                   utsDot3OltNNIFlowControlLowTreshold          INTEGER,
                   utsDot3OltNNIFlowControlHighTreshold         INTEGER,
                   utsDot3OltFDBClear                           INTEGER,
                   utsDot3OltEncryptionMode                     INTEGER,
                   utsDot3OltEncryptionRekeyTimer               INTEGER
              }

utsDot3Olt2ModuleId OBJECT-TYPE
SYNTAX  INTEGER
       MAX-ACCESS  read-only
       STATUS  current
       DESCRIPTION
"A read-only value that identifies the olt module index"
        ::= { utsDot3Olt2Entry 1 }

utsDot3Olt2DeviceId OBJECT-TYPE
SYNTAX  INTEGER
       MAX-ACCESS  read-only
       STATUS  current
       DESCRIPTION
"A read-only value that identifies the olt device index"
        ::= { utsDot3Olt2Entry 2 }

utsDot3Olt2Status OBJECT-TYPE
SYNTAX  INTEGER
   	   {
   	     waitforImage(1), -- wait for image: only during ethernet boot
   	     normal(2),
   	     departure(3),    -- graceful departure
   	     timeout(4)       -- keep-alive timed-out
	   }
       MAX-ACCESS  read-only
       STATUS  current
       DESCRIPTION
"OLT device status"
        ::= { utsDot3Olt2Entry 3}

utsDot3Olt2MACAddress OBJECT-TYPE
SYNTAX  MacAddress
       MAX-ACCESS  read-only
       STATUS  current
       DESCRIPTION
"A  read-only value that identifies the source_address parameter of OLT"
       REFERENCE   "[802.3ah], 30.3.5.1.6."
        ::= { utsDot3Olt2Entry 4}

utsDot3OltPortIsolation OBJECT-TYPE
SYNTAX  INTEGER
		{
		 enable(1),
		 disable(2)
		}
       MAX-ACCESS  read-write
       STATUS  current
       DESCRIPTION
"OLT Port Isolation mode"
        ::= { utsDot3Olt2Entry 6}

utsDot3OltDot1adEnable OBJECT-TYPE
       SYNTAX  TruthValue
       MAX-ACCESS  read-write
       STATUS  current
       DESCRIPTION
"whether to enable dot1ad"
        ::= { utsDot3Olt2Entry 7}

-- utsDot3OltDot1adTPID OBJECT-TYPE
--       SYNTAX  INTEGER
--       MAX-ACCESS  read-write
--       STATUS  current
--       DESCRIPTION
-- "Tag protocol id, by default 0x88a8."
--        ::= { utsDot3Olt2Entry 8}

utsDot3OltDot1xMode OBJECT-TYPE
       SYNTAX  INTEGER
       {
         enabled(1),
         disabled(2)
       }
       MAX-ACCESS  read-only
       STATUS  current
       DESCRIPTION
"802.1x authentication mode status."
        ::= { utsDot3Olt2Entry 9}

utsDot3OltMPCPTimeout OBJECT-TYPE
       SYNTAX  INTEGER(0..50)
       MAX-ACCESS  read-only
       STATUS  current
       DESCRIPTION
"MPCP timeout: 0 means timeout disabled. Value range 0, 20..50."
        ::= { utsDot3Olt2Entry 10}

utsDot3OltNNIFlowControlTxEnable OBJECT-TYPE
       SYNTAX  TruthValue
       MAX-ACCESS  read-only
       STATUS  current
       DESCRIPTION
"Turn on/off Tx-Flowcontrol functionality on NNI ports"
        ::= { utsDot3Olt2Entry 11}

utsDot3OltNNIFlowControlRxEnable OBJECT-TYPE
       SYNTAX  TruthValue
       MAX-ACCESS  read-only
       STATUS  current
       DESCRIPTION
"Turn on/off Rx-Flowcontrol functionality on NNI ports"
        ::= { utsDot3Olt2Entry 12}

utsDot3OltNNIFlowControlLowTreshold OBJECT-TYPE
       SYNTAX  INTEGER(0..100) -- shall be lower than High Thresold
       MAX-ACCESS  read-only
       STATUS  current
       DESCRIPTION
"buffer low threshold limit (0 to 100 percent) for NNI port flow control."
        ::= { utsDot3Olt2Entry 13}

utsDot3OltNNIFlowControlHighTreshold OBJECT-TYPE
       SYNTAX  INTEGER(0..100) -- shall be higher than High Thresold
       MAX-ACCESS  read-only
       STATUS  current
       DESCRIPTION
"buffer low threshold limit (0 to 100 percent) for NNI port flow control."
        ::= { utsDot3Olt2Entry 14}

utsDot3OltFDBClear OBJECT-TYPE
       SYNTAX  INTEGER
       {
         clearAll(1),
         clearUnicast(2),
         clearMulticast(3),
         clearDynamic(4)
       }
       MAX-ACCESS  read-write
       STATUS  current
       DESCRIPTION
"Clear OLT FDB entries"
        ::= { utsDot3Olt2Entry 15}

utsDot3OltEncryptionMode OBJECT-TYPE
       SYNTAX  INTEGER
       {
         aes48(1),
  --     aes32(2),
         ctc-churning(3),
         disable(4)
       }
       MAX-ACCESS  read-write
       STATUS  current
       DESCRIPTION
"Global-level encryption mode"
        ::= { utsDot3Olt2Entry 16}

utsDot3OltEncryptionRekeyTimer OBJECT-TYPE
       SYNTAX  INTEGER(0..640)
       MAX-ACCESS  read-write
       STATUS  current
       DESCRIPTION
"Select rekeying timer value (in seconds), 0 means disable rekeying"
       DEFVAL{10}
        ::= { utsDot3Olt2Entry 17}


-- EPM04B PON port configurations

utsDot3Olt2PortTable OBJECT-TYPE
SYNTAX  SEQUENCE OF UtsDot3Olt2PortEntry
        MAX-ACCESS  not-accessible
        STATUS  current
        DESCRIPTION
"Table for OLT type 2 port MIBs."
        ::= { utsDot3Olt2Objects 2 }

utsDot3Olt2PortEntry OBJECT-TYPE
SYNTAX  UtsDot3Olt2PortEntry
       MAX-ACCESS  not-accessible
       STATUS  current
       DESCRIPTION
"An entry in the OLT type 2 port MIBs table."
       INDEX  { utsDot3OltPortModuleId, utsDot3OltPortDeviceId, utsDot3OltPortPortId }
       ::= { utsDot3Olt2PortTable 1 }

UtsDot3Olt2PortEntry ::=
       SEQUENCE {
                    utsDot3OltPortModuleId				        INTEGER,
                    utsDot3OltPortDeviceId                      INTEGER,
                    utsDot3OltPortPortId	 		            INTEGER,
                    utsDot3OltOperState 			            INTEGER,
                    utsDot3OltAdminState                        INTEGER,
--                    utsDot3OltMACAddress				        MacAddress,
--                    utsDot3OltLPortNumber				        INTEGER,
--                    utsDot3OltMACAddressAgingTime		        INTEGER,
                    utsDot3OltRegisteredOnuNum                  INTEGER,
                    utsDot3OltSyncTime                          INTEGER,
                    utsDot3OltLaserOnTime                       INTEGER,
                    utsDot3OltLaserOffTime                      INTEGER,
                    utsDot3OltTxFECEnable                       TruthValue,
                    utsDot3OltTransceiverTx                     INTEGER,
                    utsDot3OltTransceiverRx                     INTEGER,
--                    utsDot3OltONUP2PEnable                      TruthValue,
                    utsDot3OltMPCPGateBackoffTime               INTEGER,
--                    utsDot3OltEncryptionMode                    INTEGER,
--                    utsDot3OltEncryptionRekeyTimer              INTEGER,
                    utsDot3OltP2pEnable                         TruthValue,
                    utsDot3OltOlpPort                           INTEGER,
--                    utsDot3OltPonTrunckProtectionGroupId        INTEGER,
                    utsDot3OltPortLoopbackDetection             INTEGER,
                    utsDot3OltPortLoopbackDetectionControl      INTEGER,
                    utsDot3OltPortTransmissionPower             INTEGER,
                    utsDot3OltPortReceivingPower                INTEGER,
                    utsDot3OltPortRealtimeMulticastTraffic      INTEGER,
                    utsDot3OltPortSupplyVoltage                 INTEGER,
                    utsDot3OltPortCurrentBias                   INTEGER,
                    utsDot3OltPortCurrentTemperature            INTEGER
       }

utsDot3OltPortModuleId OBJECT-TYPE
SYNTAX  INTEGER
       MAX-ACCESS  read-only
       STATUS  current
       DESCRIPTION
"A read-only value that identifies the olt module index"
        ::= { utsDot3Olt2PortEntry 1 }

utsDot3OltPortDeviceId OBJECT-TYPE
SYNTAX  INTEGER
       MAX-ACCESS  read-only
       STATUS  current
       DESCRIPTION
"A read-only value that identifies the olt device index"
        ::= { utsDot3Olt2PortEntry 2 }

utsDot3OltPortPortId OBJECT-TYPE
SYNTAX  INTEGER
       MAX-ACCESS  read-only
       STATUS  current
       DESCRIPTION
"A read-only value that identifies the olt port index"
        ::= { utsDot3Olt2PortEntry 3 }

utsDot3OltOperState OBJECT-TYPE
SYNTAX  INTEGER {
          up(1),
          down(2)
          -- ,testing(3)
      }
       MAX-ACCESS  read-only
       STATUS  current
       DESCRIPTION
"A  read-only value that identifies the operational state of the  Multi-
Point MAC Control sublayer as defined in [802.3ah] clause 64. When  this
attribute has the enumeration 'unregistered' the interface may  be  used
for  registering a link partner. When this attribute has the enumeration
'registering'  the  interface is in the process of registering  a  link-
partner.  When  this  attribute  has the  enumeration  'registered'  the
interface has an established link-partner. It's identical to
dot3MpcpRegistrationState in Dot3MpcpEntry."
       REFERENCE   "[802.3ah], 30.3.5.1.7."
        ::= { utsDot3Olt2PortEntry 4 }

utsDot3OltAdminState OBJECT-TYPE
     SYNTAX  INTEGER {
         up(1), -- ready to pass packets
         down(2) --
     }
     MAX-ACCESS  read-write
     STATUS  current
     DESCRIPTION
         "The desired state of the OLT module.  The
          testing(3) state indicates that no operational
          packets can be passed, current olt do not support testing mode."
     ::= { utsDot3Olt2PortEntry 5}


utsDot3OltRegisteredOnuNum OBJECT-TYPE
       SYNTAX  INTEGER (0..64)
       MAX-ACCESS  read-only
       STATUS  current
       DESCRIPTION
"Registered ONU number."
        ::= { utsDot3Olt2PortEntry 10 }

utsDot3OltSyncTime OBJECT-TYPE
       SYNTAX  INTEGER
       MAX-ACCESS  read-only
       STATUS  current
       DESCRIPTION
"PON port sync time."
        ::= { utsDot3Olt2PortEntry 11 }

utsDot3OltLaserOnTime OBJECT-TYPE
       SYNTAX  INTEGER
       MAX-ACCESS  read-only
       STATUS  current
       DESCRIPTION
"Laser on time."
        ::= { utsDot3Olt2PortEntry 12 }

utsDot3OltLaserOffTime OBJECT-TYPE
       SYNTAX  INTEGER
       MAX-ACCESS  read-only
       STATUS  current
       DESCRIPTION
"Laser off time."
        ::= { utsDot3Olt2PortEntry 13 }

utsDot3OltTxFECEnable OBJECT-TYPE
       SYNTAX  TruthValue
       MAX-ACCESS  read-write
       STATUS  current
       DESCRIPTION
"Tx FEC enable or disable."
        ::= { utsDot3Olt2PortEntry 14 }

utsDot3OltTransceiverTx OBJECT-TYPE
       SYNTAX  INTEGER
       {
         enable(1),
         disable(2)
       }
       MAX-ACCESS  read-write
       STATUS  current
       DESCRIPTION
"Transceiver Tx enable or disable."
        ::= { utsDot3Olt2PortEntry 15 }

utsDot3OltTransceiverRx OBJECT-TYPE
       SYNTAX  INTEGER
       {
         enable(1),
         disable(2)
       }
       MAX-ACCESS  read-write
       STATUS  current
       DESCRIPTION
"Transceiver Tx enable or disable."
        ::= { utsDot3Olt2PortEntry 16 }


utsDot3OltMPCPGateBackoffTime OBJECT-TYPE
       SYNTAX  INTEGER(0..31)
       MAX-ACCESS  read-write
       STATUS  current
       DESCRIPTION
"Set OLT CTC special MPCP registration mode and the MPCP gate delay time.
 0:  disable CTC special MPCP registration mode.
 1..31: enable CTC special MPCP registration mode and set the MPCP gate
        delay in multiples of cycle time (1-31)
"
        ::= { utsDot3Olt2PortEntry 18 }

utsDot3OltP2pEnable OBJECT-TYPE
       SYNTAX  TruthValue
       MAX-ACCESS  read-write
       STATUS  current
       DESCRIPTION
"Enable or disable P2P"
        ::= { utsDot3Olt2PortEntry 21 }

utsDot3OltOlpPort OBJECT-TYPE
       SYNTAX  INTEGER(0..8)
       MAX-ACCESS  read-write
       STATUS  current
       DESCRIPTION
"Set the Olp port number on OSW. 0 means disable
the Optiocal Line Protection function for this PON port."
        ::= { utsDot3Olt2PortEntry 22 }

--utsDot3OltPonTrunckProtectionGroupId OBJECT-TYPE
--       SYNTAX  INTEGER
--       MAX-ACCESS  read-only
--       STATUS  current
--       DESCRIPTION
--"Pon Trunck Protection Group id, 0 means this port not in any group."
--        ::= { utsDot3Olt2PortEntry 23 }

utsDot3OltPortLoopbackDetection OBJECT-TYPE
       SYNTAX  INTEGER
       {
       	  disable(1), --default value
       	  enable(2)
       }
       MAX-ACCESS  read-write
       STATUS  current
       DESCRIPTION
"Set the switch of loopback dectection for each olt port, the default value is disable."
        ::= { utsDot3Olt2PortEntry 24 }

utsDot3OltPortLoopbackDetectionControl OBJECT-TYPE
       SYNTAX  INTEGER
       {
       	  disable(1), --default value
       	  enable(2)
       }
       MAX-ACCESS  read-write
       STATUS  current
       DESCRIPTION
"Set the switch of loopback dectection control for each olt port, the default value is disable.
 In the disable status, if detect the loop, send the event only, otherwise, send the event and shut
 down the onu"
        ::= { utsDot3Olt2PortEntry 26 }

utsDot3OltPortTransmissionPower OBJECT-TYPE
       SYNTAX  INTEGER
       MAX-ACCESS  read-only
       STATUS  current
       DESCRIPTION
"The transmission power of OLT port."
        ::= { utsDot3Olt2PortEntry 27 }

utsDot3OltPortReceivingPower OBJECT-TYPE
       SYNTAX  INTEGER
       MAX-ACCESS  read-only
       STATUS  current
       DESCRIPTION
"The Receiving power of OLT port."
        ::= { utsDot3Olt2PortEntry 28 }

utsDot3OltPortRealtimeMulticastTraffic OBJECT-TYPE
       SYNTAX  INTEGER
       MAX-ACCESS  read-only
       STATUS  current
       DESCRIPTION
"The realtime multicast traffic of OLT port."
        ::= { utsDot3Olt2PortEntry 29 }

utsDot3OltPortSupplyVoltage OBJECT-TYPE
       SYNTAX  INTEGER
       MAX-ACCESS  read-only
       STATUS  current
       DESCRIPTION
"The supply voltage of OLT port."
        ::= { utsDot3Olt2PortEntry 30 }

utsDot3OltPortCurrentBias OBJECT-TYPE
       SYNTAX  INTEGER
       MAX-ACCESS  read-only
       STATUS  current
       DESCRIPTION
"The current bias of OLT port."
        ::= { utsDot3Olt2PortEntry 31 }

utsDot3OltPortCurrentTemperature OBJECT-TYPE
       SYNTAX  INTEGER
       MAX-ACCESS  read-only
       STATUS  current
       DESCRIPTION
"The current temperature of OLT port."
        ::= { utsDot3Olt2PortEntry 32 }

-- EPM04B PON QoS configurations

utsDot3Olt2QoSGlbTable OBJECT-TYPE
SYNTAX  SEQUENCE OF UtsDot3Olt2QoSGlbEntry
        MAX-ACCESS  not-accessible
        STATUS  current
        DESCRIPTION
"Table for OLT type 2 QoS MIBs."
        ::= { utsDot3Olt2Objects 3 }

utsDot3Olt2QoSGlbEntry OBJECT-TYPE
SYNTAX  UtsDot3Olt2QoSGlbEntry
       MAX-ACCESS  not-accessible
       STATUS  current
       DESCRIPTION
"An entry in the OLT type 2 QoS MIBs table."
       INDEX  { utsDot3OltQosModuleId,utsDot3OltQosDeviceId }
       ::= { utsDot3Olt2QoSGlbTable 1 }

UtsDot3Olt2QoSGlbEntry ::=
       SEQUENCE {
                   utsDot3OltQosModuleId					    INTEGER,
                   utsDot3OltQosDeviceId					    INTEGER,
                   utsDot3OltQoSMode                            INTEGER,
                   utsDot3OltQoSL2OverheadInclude               TruthValue,
                   utsDot3OltWREDEnable				            TruthValue,
                   utsDot3OltSchedulingMode                     INTEGER,
                   utsDot3OltSchedulingWeight                   OCTET STRING,
                   utsDot3OltDot1p2QueueMap                     OCTET STRING,
                   utsDot3OltDscp2QueueMap                      OCTET STRING,
                   utsDot3OltDefaultTx802Dot1pValue             INTEGER,
                   utsDot3OltDefaultCosQueue                    INTEGER,
                   utsDot3OltTxDot1pRemark                      OCTET STRING,
                   utsDot3OltTxDscpRemark                       OCTET STRING
       }

utsDot3OltQosModuleId OBJECT-TYPE
SYNTAX  INTEGER
       MAX-ACCESS  read-only
       STATUS  current
       DESCRIPTION
"A read-only value that identifies the olt module index"
        ::= { utsDot3Olt2QoSGlbEntry 1 }

utsDot3OltQosDeviceId OBJECT-TYPE
SYNTAX  INTEGER
       MAX-ACCESS  read-only
       STATUS  current
       DESCRIPTION
"A read-only value that identifies the olt device index"
        ::= { utsDot3Olt2QoSGlbEntry 2 }

utsDot3OltQoSMode OBJECT-TYPE
	   SYNTAX  INTEGER
	   {
	     modeDscp(1),     --  use DSCP mode
	     mode8021p(2)     --  use 802.1p mode
	   }
       MAX-ACCESS  read-write
       STATUS  current
       DESCRIPTION
"Sets global DSCP/802.1p mode, to specify whether to use the DSCP value or
 802.1p value for packet marking/queueing/classification."
        ::= { utsDot3Olt2QoSGlbEntry 3 }

utsDot3OltQoSL2OverheadInclude OBJECT-TYPE
	   SYNTAX  TruthValue
	   MAX-ACCESS  read-write
       STATUS  current
       DESCRIPTION
"Whether to include L2 overheads for spolicing/shaping rate."
        ::= { utsDot3Olt2QoSGlbEntry 4 }

utsDot3OltWREDEnable OBJECT-TYPE
       SYNTAX  TruthValue
       MAX-ACCESS  read-write
       STATUS  current
       DESCRIPTION
"enable or disable WRED globally."
        ::= { utsDot3Olt2QoSGlbEntry 5}


utsDot3OltSchedulingMode OBJECT-TYPE
	   SYNTAX  INTEGER
	   {
	   	  sp(1),           -- use strict priority
	   	  wrr(2),          -- weighted-round-robin
	   	  hierarchical(3)  -- hierarchical queueing, default
	   }
	   MAX-ACCESS  read-write
       STATUS  current
       DESCRIPTION
"Sets the intra LLID/NNI port queue scheduler policy at the OLT. The same policy
 applies to both upstream and downstream schedulers. The scheduling can be
 either strict-priority, weighted-round-robin or hierarchical queueing. For
 hierarchical queueing, queues 7 and 6 are in strict priority, and remaing queues
 are in weighted-round-robin mode."
        ::= { utsDot3Olt2QoSGlbEntry 6 }

utsDot3OltSchedulingWeight OBJECT-TYPE
	   SYNTAX  OCTET STRING(SIZE(8))  -- weight[queue index]: 0x01[0] 23[1] 45[2] 67[3] 89[4] ab[5] cd[6] ef[7]
	   MAX-ACCESS  read-write
       STATUS  current
       DESCRIPTION
"For the intra LLID/NNI port queue scheduler policy of weighted round robin, weights from 1 to
 255 can be selected for each of the 8 queues."
        ::= { utsDot3Olt2QoSGlbEntry 7 }

utsDot3OltDot1p2QueueMap OBJECT-TYPE
	   SYNTAX  OCTET STRING(SIZE(8))  -- queue[dot1p value]:  0x01[0] 23[1] 45[2] 67[3] 89[4] ab[5] cd[6] ef[7]
	   MAX-ACCESS  read-write
       STATUS  current
       DESCRIPTION
"Sets the 802.1p-to-output queue mapping table (3bits to 3bits) at the OLT. The
 table specifies one of 8 possible CoS queues per NNI/LLID port.
 Queue number(from 0-7)for 802.1p value 0 to 7"
        ::= { utsDot3Olt2QoSGlbEntry 8 }

utsDot3OltDscp2QueueMap OBJECT-TYPE
	   SYNTAX  OCTET STRING(SIZE(8))  -- queue[DSCP value]:  0x01[0] 23[1] 45[2] 67[3] 89[4] ab[5] cd[6] ef[7]
	   MAX-ACCESS  read-write
       STATUS  current
       DESCRIPTION
"Sets the DSCP-to-output queue mapping table (3bits to 3bits) at the OLT. The
 three most significant bits of the packet's DSCP value is used for the mapping.
 The table therefore maps the packet's DSCP[0:2] value to one of eight possible
 CoS queues.
 Queue number(0-7)for dscp[0:2] values."
        ::= { utsDot3Olt2QoSGlbEntry 9 }

utsDot3OltDefaultTx802Dot1pValue OBJECT-TYPE
	   SYNTAX  INTEGER
	   MAX-ACCESS  read-write
       STATUS  current
       DESCRIPTION
"Default Tx 802.1p value for VLAN tag."
        ::= { utsDot3Olt2QoSGlbEntry 10 }

utsDot3OltDefaultCosQueue OBJECT-TYPE
	   SYNTAX  INTEGER
	   MAX-ACCESS  read-write
       STATUS  current
       DESCRIPTION
"Default CoS queue(0 to 7) for queueing untagged
 packets in 802.1p QoS mode or non-IP packets in
 DSCP QoS mode.
"
        ::= { utsDot3Olt2QoSGlbEntry 11 }

utsDot3OltTxDot1pRemark OBJECT-TYPE
	   SYNTAX  OCTET STRING(SIZE(8)) -- If policing mark-bit=1, this specifies the
	                 -- remarking table from input 802.1p value to output 802.1p value
	   MAX-ACCESS  read-write
       STATUS  current
       DESCRIPTION
"Sets the 802.1p remarking table, when a packet is to be re-marked as a result of
 tokenbucket policing. This table takes the three bits of the original 802.1p
 value and one mark bit from the tokenbucket policing logic and specifies
 the new three-bit 802.1p value to be written in the outgoing packet header.
 This table applies globally, to any packet-remarking for both upstream and downstream
 directions at the OLT.
"
        ::= { utsDot3Olt2QoSGlbEntry 12 }

utsDot3OltTxDscpRemark OBJECT-TYPE
	   SYNTAX  OCTET STRING(SIZE(64)) -- if policing mark-bit=1, this specifies the remarking
                                      -- table from input DSCP value to the 6-bit output
       MAX-ACCESS  read-write
       STATUS  current
       DESCRIPTION
"Sets the DSCP remarking table, when a packet is to be re-marked as a result of tokenbucket
 policing. This table takes the six bits of the original DSCP value and and specifies the
 new six-bit DSCP value to be written in the outgoing packet header, if the packet is to
 be marked as a result of policing. This table applies globally, to any packet-remarking
 for both upstream and downstream directions at the OLT.
"
        ::= { utsDot3Olt2QoSGlbEntry 13 }
-- DBA

utsDot3Olt2DbaGlbTable OBJECT-TYPE
SYNTAX  SEQUENCE OF UtsDot3Olt2DbaGlbEntry
        MAX-ACCESS  not-accessible
        STATUS  current
        DESCRIPTION
"Table for OLT type 2 DBA MIBs."
        ::= { utsDot3Olt2Objects 4 }

utsDot3Olt2DbaGlbEntry OBJECT-TYPE
SYNTAX  UtsDot3Olt2DbaGlbEntry
       MAX-ACCESS  not-accessible
       STATUS  current
       DESCRIPTION
"An entry in the OLT type 2 DBA MIBs table."
       INDEX  { utsDot3OltDbaGlbModuleId,utsDot3OltDbaGlbDeviceId}
       ::= { utsDot3Olt2DbaGlbTable 1 }


UtsDot3Olt2DbaGlbEntry ::=
       SEQUENCE {
                   utsDot3OltDbaGlbModuleId					        INTEGER,
                   utsDot3OltDbaGlbDeviceId					        INTEGER,
                   utsDot3OltDbaMode                                INTEGER,
                   utsDot3OltDbaAlgorithm                           INTEGER
       }

utsDot3OltDbaGlbModuleId OBJECT-TYPE
SYNTAX  INTEGER
       MAX-ACCESS  read-only
       STATUS  current
       DESCRIPTION
"A read-only value that identifies the olt module index"
        ::= { utsDot3Olt2DbaGlbEntry 1 }

utsDot3OltDbaGlbDeviceId OBJECT-TYPE
SYNTAX  INTEGER
       MAX-ACCESS  read-only
       STATUS  current
       DESCRIPTION
"A read-only value that identifies the olt device index"
        ::= { utsDot3Olt2DbaGlbEntry 2 }

utsDot3OltDbaMode OBJECT-TYPE
SYNTAX  INTEGER
       {
         hardware-dba(1),        -- use hardware DBA
         software-dba(2),        -- use software dynamic DBA
         hardware-dynamic-dba(3) -- use hardwareDBA with dynamic cycletime tuning
       }
       MAX-ACCESS  read-write
       STATUS  current
       DESCRIPTION
"Sets the DBA mode, to specify whether to use hardware-based DBA or software based DBA.
 The DBA mode is global, and the same mode is used for all EPONS of the OLT."
        ::= { utsDot3Olt2DbaGlbEntry 3 }

utsDot3OltDbaAlgorithm OBJECT-TYPE
SYNTAX  INTEGER
       {
         max-min(1),               --
         ceilingmax-min(2),        --
         fixedmin(3)               --
       }
       MAX-ACCESS  read-write
       STATUS  current
       DESCRIPTION
"Sets the DBA algorithm options for upstream bandwidth allocation among ONUs."
        ::= { utsDot3Olt2DbaGlbEntry 4 }

-- EPON OLT Broadcast/Unknown Unicast/Unknown Multicast Policing

utsDot3Olt2PolicingTable OBJECT-TYPE
SYNTAX  SEQUENCE OF UtsDot3Olt2PolicingEntry
        MAX-ACCESS  not-accessible
        STATUS  current
        DESCRIPTION
"Table for OLT type 2 policing MIBs."
        ::= { utsDot3Olt2Objects 7 }

utsDot3Olt2PolicingEntry OBJECT-TYPE
SYNTAX  UtsDot3Olt2PolicingEntry
       MAX-ACCESS  not-accessible
       STATUS  current
       DESCRIPTION
"An entry in the OLT type 2 policing MIBs table."
       INDEX  {utsDot3OltPolicingModuleId, utsDot3OltPolicingDeviceId}
       ::= { utsDot3Olt2PolicingTable 1 }


UtsDot3Olt2PolicingEntry ::=
       SEQUENCE {
                    utsDot3OltPolicingModuleId			         INTEGER,
                    utsDot3OltPolicingDeviceId			         INTEGER,
                    utsDot3OltBcPoliceEnable                     TruthValue,
                    utsDot3OltBcPoliceRate                       INTEGER,
                    utsDot3OltBcPoliceBurstSize                  INTEGER,
                    utsDot3OltUmcPoliceEnable                    TruthValue,
                    utsDot3OltUmcPoliceRate                      INTEGER,
                    utsDot3OltUmcPoliceBurstSize                  INTEGER,
                    utsDot3OltUucPoliceEnable                     TruthValue,
                    utsDot3OltUucPoliceRate                       INTEGER,
                    utsDot3OltUucPoliceBurstSize                  INTEGER
       }

utsDot3OltPolicingModuleId OBJECT-TYPE
SYNTAX  INTEGER
       MAX-ACCESS  read-only
       STATUS  current
       DESCRIPTION
"A read-only value that identifies the olt module index"
        ::= { utsDot3Olt2PolicingEntry 1 }

utsDot3OltPolicingDeviceId OBJECT-TYPE
SYNTAX  INTEGER
       MAX-ACCESS  read-only
       STATUS  current
       DESCRIPTION
"A read-only value that identifies the olt device index"
        ::= { utsDot3Olt2PolicingEntry 2 }

utsDot3OltBcPoliceEnable OBJECT-TYPE
SYNTAX  TruthValue
       MAX-ACCESS  read-write
       STATUS  current
       DESCRIPTION
"Enable or disable broadcast policing"
       ::= { utsDot3Olt2PolicingEntry 3 }

utsDot3OltBcPoliceRate OBJECT-TYPE
SYNTAX  INTEGER           -- in Kbps
       MAX-ACCESS  read-write
       STATUS  current
       DESCRIPTION
"broadcast policing rate (in Kbps)"
       ::= { utsDot3Olt2PolicingEntry 4 }

utsDot3OltBcPoliceBurstSize OBJECT-TYPE
SYNTAX  INTEGER           -- in KB
       MAX-ACCESS  read-write
       STATUS  current
       DESCRIPTION
"broadcast policing burst size (in KB)"
       ::= { utsDot3Olt2PolicingEntry 5 }

utsDot3OltUmcPoliceEnable OBJECT-TYPE
SYNTAX  TruthValue
       MAX-ACCESS  read-write
       STATUS  current
       DESCRIPTION
"Enable or disable unknown multicast policing"
       ::= { utsDot3Olt2PolicingEntry 6 }

utsDot3OltUmcPoliceRate OBJECT-TYPE
SYNTAX  INTEGER           -- in Kbps
       MAX-ACCESS  read-write
       STATUS  current
       DESCRIPTION
"unknown multicast policing rate (in Kbps)"
       ::= { utsDot3Olt2PolicingEntry 7 }

utsDot3OltUmcPoliceBurstSize OBJECT-TYPE
SYNTAX  INTEGER           -- in KB
       MAX-ACCESS  read-write
       STATUS  current
       DESCRIPTION
"unknown multicast policing burst size (in KB)"
       ::= { utsDot3Olt2PolicingEntry 8 }

utsDot3OltUucPoliceEnable OBJECT-TYPE
SYNTAX  TruthValue
       MAX-ACCESS  read-write
       STATUS  current
       DESCRIPTION
"enable or disable unknown unicast policing"
       ::= { utsDot3Olt2PolicingEntry 9 }


utsDot3OltUucPoliceRate OBJECT-TYPE
SYNTAX  INTEGER           -- in Kbps
       MAX-ACCESS  read-write
       STATUS  current
       DESCRIPTION
"unknown unicast policing rate (in Kbps)"
       ::= { utsDot3Olt2PolicingEntry 10 }


utsDot3OltUucPoliceBurstSize OBJECT-TYPE
SYNTAX  INTEGER           -- in KB
       MAX-ACCESS  read-write
       STATUS  current
       DESCRIPTION
"unknown unicast policing burst size (in KB)"
       ::= { utsDot3Olt2PolicingEntry 11 }

-- EPON OLT VLAN stacking function

utsDot3Olt2VlanStackingTable OBJECT-TYPE
SYNTAX  SEQUENCE OF UtsDot3Olt2VlanStackingEntry
        MAX-ACCESS  not-accessible
        STATUS  current
        DESCRIPTION
"Table for OLT type 2 VLAN stacking MIBs."
        ::= { utsDot3Olt2Objects 8 }

utsDot3Olt2VlanStackingEntry OBJECT-TYPE
SYNTAX  UtsDot3Olt2VlanStackingEntry
       MAX-ACCESS  not-accessible
       STATUS  current
       DESCRIPTION
"An entry in the OLT type 2  VLAN stacking MIBs table."
       INDEX  {utsDot3OltVlanStackingModuleId, utsDot3OltVlanStackingDeviceId,
               utsDot3OltVlanStackingPortId,utsDot3Olt2VlanStackingLogicalPortId,
               utsDot3Olt2VlanStackingCVlanId}
       ::= { utsDot3Olt2VlanStackingTable 1 }

UtsDot3Olt2VlanStackingEntry ::=
       SEQUENCE {
                    utsDot3OltVlanStackingModuleId			         INTEGER,
                    utsDot3OltVlanStackingDeviceId			         INTEGER,
                    utsDot3OltVlanStackingPortId                     INTEGER,
                    utsDot3Olt2VlanStackingLogicalPortId             INTEGER,

                    utsDot3Olt2VlanStackingCVlanId                   INTEGER,
                    utsDot3Olt2VlanStackingSVlanId                   INTEGER,
                    utsDot3Olt2VlanStackingPriMode                   INTEGER,
                    utsDot3Olt2VlanStackingSVlanPri                  INTEGER,
                    utsDot3Olt2VlanStackingRowStatus                 RowStatus
       }

utsDot3OltVlanStackingModuleId OBJECT-TYPE
SYNTAX  INTEGER
       MAX-ACCESS  not-accessible
       STATUS  current
       DESCRIPTION
"A read-only value that identifies the olt module index"
        ::= { utsDot3Olt2VlanStackingEntry 1 }

utsDot3OltVlanStackingDeviceId OBJECT-TYPE
SYNTAX  INTEGER
       MAX-ACCESS  not-accessible
       STATUS  current
       DESCRIPTION
"A read-only value that identifies the olt device index"
        ::= { utsDot3Olt2VlanStackingEntry 2 }

utsDot3OltVlanStackingPortId OBJECT-TYPE
SYNTAX  INTEGER
       MAX-ACCESS  not-accessible
       STATUS  current
       DESCRIPTION
"OLT PON port ID"
       ::= { utsDot3Olt2VlanStackingEntry 3 }

utsDot3Olt2VlanStackingLogicalPortId OBJECT-TYPE
SYNTAX  INTEGER
       MAX-ACCESS  not-accessible
       STATUS  current
       DESCRIPTION
"Logical port ID"
       ::= { utsDot3Olt2VlanStackingEntry 4 }

utsDot3Olt2VlanStackingCVlanId OBJECT-TYPE
SYNTAX  INTEGER(1..4094)
       MAX-ACCESS  not-accessible
       STATUS  current
       DESCRIPTION
"CVLAN ID"
       ::= { utsDot3Olt2VlanStackingEntry 5 }

utsDot3Olt2VlanStackingSVlanId OBJECT-TYPE
SYNTAX  INTEGER(1..4094)
       MAX-ACCESS  read-create
       STATUS  current
       DESCRIPTION
"SVLAN ID"
       ::= { utsDot3Olt2VlanStackingEntry 6 }

utsDot3Olt2VlanStackingPriMode OBJECT-TYPE
SYNTAX INTEGER
	   {
	     copy(1), -- copy internal priority to out priority
	     zero(2)
	   }
       MAX-ACCESS  read-create
       STATUS  current
       DESCRIPTION
"SVLAN ID"
       ::= { utsDot3Olt2VlanStackingEntry 7 }

utsDot3Olt2VlanStackingSVlanPri OBJECT-TYPE
SYNTAX INTEGER
       MAX-ACCESS  read-create
       STATUS  current
       DESCRIPTION
"SVLAN priority"
       ::= { utsDot3Olt2VlanStackingEntry 8 }

utsDot3Olt2VlanStackingRowStatus OBJECT-TYPE
SYNTAX  RowStatus
       MAX-ACCESS  read-create
       STATUS  current
       DESCRIPTION
"Row Status"
       ::= { utsDot3Olt2VlanStackingEntry 9 }

-- EPM04B PON static FDB configurations

utsDot3Olt2StaticFDBTable OBJECT-TYPE
SYNTAX  SEQUENCE OF UtsDot3Olt2StaticFDBEntry
        MAX-ACCESS  not-accessible
        STATUS  current
        DESCRIPTION
"Table for OLT type 2 port MIBs."
        ::= { utsDot3Olt2Objects 9 }

utsDot3Olt2StaticFDBEntry OBJECT-TYPE
SYNTAX  UtsDot3Olt2StaticFDBEntry
       MAX-ACCESS  not-accessible
       STATUS  current
       DESCRIPTION
"An entry in the OLT type 2 port MIBs table."
       INDEX  { utsDot3OltStaticFDBModuleId, utsDot3OltStaticFDBDeviceId }
       ::= { utsDot3Olt2StaticFDBTable 1 }

UtsDot3Olt2StaticFDBEntry ::=
       SEQUENCE {
                    utsDot3OltStaticFDBModuleId				        INTEGER,
                    utsDot3OltStaticFDBDeviceId                     INTEGER,
                    utsDot3OltStaticFDBDstMacAddr                   MacAddress,
                    utsDot3OltStaticFDBVlanId                       INTEGER,
                    utsDot3OltStaticFDBEgressPort                   OCTET STRING,
                    utsDot3OltStaticFDBRowStatus                    RowStatus
       }

utsDot3OltStaticFDBModuleId OBJECT-TYPE
SYNTAX  INTEGER
       MAX-ACCESS  not-accessible
       STATUS  current
       DESCRIPTION
"Module ID"
        ::= { utsDot3Olt2StaticFDBEntry 1 }

utsDot3OltStaticFDBDeviceId OBJECT-TYPE
SYNTAX  INTEGER
       MAX-ACCESS  not-accessible
       STATUS  current
       DESCRIPTION
"Device ID"
        ::= { utsDot3Olt2StaticFDBEntry 2 }

utsDot3OltStaticFDBDstMacAddr OBJECT-TYPE
SYNTAX  MacAddress
       MAX-ACCESS  read-create
       STATUS  current
       DESCRIPTION
"Destination MAC address"
        ::= { utsDot3Olt2StaticFDBEntry 3 }

utsDot3OltStaticFDBVlanId OBJECT-TYPE
SYNTAX  INTEGER(1..4094)
       MAX-ACCESS  read-create
       STATUS  current
       DESCRIPTION
"VLAN ID"
        ::= { utsDot3Olt2StaticFDBEntry 4 }

utsDot3OltStaticFDBEgressPort OBJECT-TYPE
SYNTAX  OCTET STRING(SIZE(1)) --  from left to right, 0B1011... means port 1,3,4s
       MAX-ACCESS  read-create
       STATUS  current
       DESCRIPTION
"Egress port map"
        ::= { utsDot3Olt2StaticFDBEntry 5 }

utsDot3OltStaticFDBRowStatus OBJECT-TYPE
SYNTAX  RowStatus
       MAX-ACCESS  read-create
       STATUS  current
       DESCRIPTION
"Row status"
        ::= { utsDot3Olt2StaticFDBEntry 6 }

-- Display FDB table

-- EPM04B PON static FDB configurations

utsDot3Olt2FDBTable OBJECT-TYPE
SYNTAX  SEQUENCE OF UtsDot3Olt2FDBEntry
        MAX-ACCESS  not-accessible
        STATUS  current
        DESCRIPTION
"Table for OLT type 2 port MIBs."
        ::= { utsDot3Olt2Objects 10 }

utsDot3Olt2FDBEntry OBJECT-TYPE
SYNTAX  UtsDot3Olt2FDBEntry
       MAX-ACCESS  not-accessible
       STATUS  current
       DESCRIPTION
"An entry in the OLT type 2 port MIBs table."
       INDEX  { utsDot3OltFDBModuleId, utsDot3OltFDBDeviceId, utsDot3OltFDBIndex }
       ::= { utsDot3Olt2FDBTable 1 }

UtsDot3Olt2FDBEntry ::=
       SEQUENCE {
                    utsDot3OltFDBModuleId				      INTEGER,
                    utsDot3OltFDBDeviceId                     INTEGER,
                    utsDot3OltFDBIndex                        INTEGER,
                    utsDot3OltFDBDstMacAddr                   MacAddress,
                    utsDot3OltFDBVlanId                       INTEGER,
                    utsDot3OltFDBEgressPort                   OCTET STRING,
                    utsDot3OltFDBStatus                       INTEGER
       }

utsDot3OltFDBModuleId OBJECT-TYPE
SYNTAX  INTEGER
       MAX-ACCESS  read-only
       STATUS  current
       DESCRIPTION
"Module ID"
        ::= { utsDot3Olt2FDBEntry 1 }

utsDot3OltFDBDeviceId OBJECT-TYPE
SYNTAX  INTEGER
       MAX-ACCESS  read-only
       STATUS  current
       DESCRIPTION
"Device ID"
        ::= { utsDot3Olt2FDBEntry 2 }

utsDot3OltFDBIndex OBJECT-TYPE
SYNTAX  INTEGER
       MAX-ACCESS  read-only
       STATUS  current
       DESCRIPTION
"Device ID"
        ::= { utsDot3Olt2FDBEntry 3 }

utsDot3OltFDBDstMacAddr OBJECT-TYPE
SYNTAX  MacAddress
       MAX-ACCESS  read-only
       STATUS  current
       DESCRIPTION
"Destination MAC address"
        ::= { utsDot3Olt2FDBEntry 4 }

utsDot3OltFDBVlanId OBJECT-TYPE
SYNTAX  INTEGER(1..4094)
       MAX-ACCESS  read-only
       STATUS  current
       DESCRIPTION
"VLAN ID"
        ::= { utsDot3Olt2FDBEntry 5 }

utsDot3OltFDBEgressPort OBJECT-TYPE
SYNTAX  OCTET STRING(SIZE(1)) --  from left to right, 0B1011... means port 1,3,4s
       MAX-ACCESS  read-only
       STATUS  current
       DESCRIPTION
"Egress port map"
        ::= { utsDot3Olt2FDBEntry 6 }

utsDot3OltFDBStatus OBJECT-TYPE
SYNTAX INTEGER
	   {
	      invalid(1), -- the entry is no longer valid but not flushed yet
	      dynamic(2), -- dynamically learned
	      local(3),   -- local port MAC address
	      static(4),  -- statically added
	      igmpSnooping(5) -- via IGMP snooping
	   }
       MAX-ACCESS  read-only
       STATUS  current
       DESCRIPTION
"Egress port map"
        ::= { utsDot3Olt2FDBEntry 7 }


-- PON port DBA

utsDot3Olt2PortDbaTable OBJECT-TYPE
SYNTAX  SEQUENCE OF UtsDot3Olt2PortDbaEntry
        MAX-ACCESS  not-accessible
        STATUS  current
        DESCRIPTION
"Table for OLT type 2 PON port DBA MIBs."
        ::= { utsDot3Olt2Objects 11 }

utsDot3Olt2PortDbaEntry OBJECT-TYPE
SYNTAX  UtsDot3Olt2PortDbaEntry
       MAX-ACCESS  not-accessible
       STATUS  current
       DESCRIPTION
"An entry in the OLT type 2 PON port DBA MIBs table."
       INDEX  { utsDot3OltPortDbaModuleId,utsDot3OltPortDbaDeviceId, utsDot3OltPortDbaPortId}
       ::= { utsDot3Olt2PortDbaTable 1 }


UtsDot3Olt2PortDbaEntry ::=
       SEQUENCE {
                   utsDot3OltPortDbaModuleId				        INTEGER,
                   utsDot3OltPortDbaDeviceId				        INTEGER,
                   utsDot3OltPortDbaPortId                          INTEGER,

                   utsDot3OltPortDbaCycleSize                       INTEGER,
                   utsDot3OltPortDbaDiscoveryFreq                   INTEGER,
                   utsDot3OltPortDbaDiscoverySize                   INTEGER
       }

utsDot3OltPortDbaModuleId OBJECT-TYPE
SYNTAX  INTEGER
       MAX-ACCESS  read-only
       STATUS  current
       DESCRIPTION
"A read-only value that identifies the olt module index"
        ::= { utsDot3Olt2PortDbaEntry 1 }

utsDot3OltPortDbaDeviceId OBJECT-TYPE
SYNTAX  INTEGER
       MAX-ACCESS  read-only
       STATUS  current
       DESCRIPTION
"A read-only value that identifies the olt device index"
        ::= { utsDot3Olt2PortDbaEntry 2 }

utsDot3OltPortDbaPortId OBJECT-TYPE
SYNTAX  INTEGER
       MAX-ACCESS  read-only
       STATUS  current
       DESCRIPTION
"A read-only value that identifies the olt port index"
        ::= { utsDot3Olt2PortDbaEntry 3 }

utsDot3OltPortDbaCycleSize OBJECT-TYPE
SYNTAX INTEGER(12500..1000000)
       MAX-ACCESS  read-write
       STATUS  current
       DESCRIPTION
"Sets the DBA cycle time in TQ for HW DBA and SW DBA"
       DEFVAL{125000}
        ::= { utsDot3Olt2PortDbaEntry 4 }

utsDot3OltPortDbaDiscoveryFreq OBJECT-TYPE
SYNTAX  INTEGER(0..255)
       MAX-ACCESS  read-write
       STATUS  current
       DESCRIPTION
"Sets the DBA discovery frequency"
       DEFVAL{64}
        ::= { utsDot3Olt2PortDbaEntry 5 }

utsDot3OltPortDbaDiscoverySize OBJECT-TYPE
SYNTAX  INTEGER(1024..14000)
       MAX-ACCESS  read-write
       STATUS  current
       DESCRIPTION
"Sets the DBA discovery size in TQ"
       DEFVAL{14000}
        ::= { utsDot3Olt2PortDbaEntry 6 }


--
--  PON protection
--

    utsDot3Olt2PonProtectionTable OBJECT-TYPE
        SYNTAX      SEQUENCE OF UtsPonTrunckProtectionEntry
        MAX-ACCESS  not-accessible
        STATUS      current
        DESCRIPTION
            "Pon Trunck Protection Table, for the phase I, the port 1 and port 2 must be in the same module, and
            the id of port 1 and port 2 must be 1&2 or 3&4."
        ::= { utsDot3Olt2Objects 12 }

    utsPonTrunckProtectionEntry OBJECT-TYPE
        SYNTAX          UtsPonTrunckProtectionEntry
        MAX-ACCESS      not-accessible
        STATUS          current
        DESCRIPTION
            "An entry in the Pon Protection table for Pon Trunck Protection interface."
        INDEX { utsPonTrunckProtectionGroupId }
        ::= { utsDot3Olt2PonProtectionTable 1 }

    UtsPonTrunckProtectionEntry ::=
        SEQUENCE {
            utsPonTrunckProtectionGroupId   INTEGER,
            utsPonTrunckProtectionName      DisplayString,
            utsPonTrunckProtectionPort1ModuleId  INTEGER,
            utsPonTrunckProtectionPort1DeviceId  INTEGER,
            utsPonTrunckProtectionPort1PortId    INTEGER,
            utsPonTrunckProtectionPort2ModuleId  INTEGER,
            utsPonTrunckProtectionPort2DeviceId  INTEGER,
            utsPonTrunckProtectionPort2PortId    INTEGER,
            utsPonTrunckProtectionPort1Status    INTEGER,
            utsPonTrunckProtectionPort2Status    INTEGER,
            utsPonTrunckProtectionPortSwitchOver INTEGER,
            utsPonTrunckProtectionPortSwitchOverResult INTEGER,
            utsPonTrunckProtectionRowStatus      RowStatus
    	}

    utsPonTrunckProtectionGroupId OBJECT-TYPE
        SYNTAX  INTEGER
        MAX-ACCESS  read-create
        STATUS  current
        DESCRIPTION
            "An indication of what Pon Trunck Protection group index is running."
        ::= { utsPonTrunckProtectionEntry 1 }

    utsPonTrunckProtectionName OBJECT-TYPE
        SYNTAX  DisplayString (SIZE(0..16))
        MAX-ACCESS  read-create
        STATUS  current
        DESCRIPTION
            "Specify the name of the Pon Trunck Protection group."
        ::= { utsPonTrunckProtectionEntry 2 }

    utsPonTrunckProtectionPort1ModuleId OBJECT-TYPE
        SYNTAX  INTEGER
        MAX-ACCESS  read-create
        STATUS  current
        DESCRIPTION
            "Specify Port 1 Module ID."
        ::= { utsPonTrunckProtectionEntry 3 }

    utsPonTrunckProtectionPort1DeviceId OBJECT-TYPE
        SYNTAX  INTEGER
        MAX-ACCESS  read-create
        STATUS  current
        DESCRIPTION
            "Specify Port 1 Device ID."
        ::= { utsPonTrunckProtectionEntry 4 }

    utsPonTrunckProtectionPort1PortId OBJECT-TYPE
        SYNTAX  INTEGER
        MAX-ACCESS  read-create
        STATUS  current
        DESCRIPTION
            "Specify Port 1 Port ID."
        ::= { utsPonTrunckProtectionEntry 5 }

    utsPonTrunckProtectionPort2ModuleId OBJECT-TYPE
        SYNTAX  INTEGER
        MAX-ACCESS  read-create
        STATUS  current
        DESCRIPTION
            "Specify Port 2 Module ID."
        ::= { utsPonTrunckProtectionEntry 6 }

    utsPonTrunckProtectionPort2DeviceId OBJECT-TYPE
        SYNTAX  INTEGER
        MAX-ACCESS  read-create
        STATUS  current
        DESCRIPTION
            "Specify Port 2 Device ID."
        ::= { utsPonTrunckProtectionEntry 7 }

    utsPonTrunckProtectionPort2PortId OBJECT-TYPE
        SYNTAX  INTEGER
        MAX-ACCESS  read-create
        STATUS  current
        DESCRIPTION
            "Specify Port 2 Port ID."
        ::= { utsPonTrunckProtectionEntry 8 }

    utsPonTrunckProtectionPort1Status OBJECT-TYPE
        SYNTAX  INTEGER
        {
          active(1),
          standby(2),
          unknown(3)
        }
        MAX-ACCESS  read-only
        STATUS  current
        DESCRIPTION
            "The status of Port 1."
        ::= { utsPonTrunckProtectionEntry 9 }

     utsPonTrunckProtectionPort2Status OBJECT-TYPE
        SYNTAX  INTEGER
        {
          active(1),
          standby(2),
          unknown(3)
        }
        MAX-ACCESS  read-only
        STATUS  current
        DESCRIPTION
            "The status of Port 2."
        ::= { utsPonTrunckProtectionEntry 10 }

     utsPonTrunckProtectionPortSwitchOver OBJECT-TYPE
        SYNTAX  INTEGER
        {
          switchover(1)
        }
        MAX-ACCESS  read-write
        STATUS  current
        DESCRIPTION
            "Switch over for this group."
        ::= { utsPonTrunckProtectionEntry 11 }

     utsPonTrunckProtectionPortSwitchOverResult OBJECT-TYPE
        SYNTAX  INTEGER
        {
           none(1),
           executing(2),
           success(3),
           fail(4)
        }
        MAX-ACCESS  read-only
        STATUS  current
        DESCRIPTION
            "The result of switch over."
        ::= { utsPonTrunckProtectionEntry 12 }

    utsPonTrunckProtectionRowStatus OBJECT-TYPE
        SYNTAX          RowStatus
        MAX-ACCESS      read-create
        STATUS          current
        DESCRIPTION
            "Row status for the current entry. "
        ::= { utsPonTrunckProtectionEntry 15 }

-- the utsPonVlanTranslationTable table
-- implemented by PON chip
-- Vlan

utsPonVlanTranslationTable OBJECT-TYPE
          SYNTAX SEQUENCE OF UtsPonVlanTranslationEntry
          MAX-ACCESS not-accessible
          STATUS current
          DESCRIPTION
             "Vlan Translaiton Table for PON side."
          ::= { utsDot3Olt2Objects 15 }

       utsPonVlanTranslationEntry OBJECT-TYPE
          SYNTAX UtsPonVlanTranslationEntry
          MAX-ACCESS not-accessible
          STATUS current
          DESCRIPTION
             "An entry in the vlan translation table for Pon interface."
          INDEX	{ utsPonVlanTranslationModuleID, utsPonVlanTranslationDeviceID, utsPonVlanTranslationPortID, utsPonVlanTranslationLogicPortID, utsPonVlanTranslationOldVID, utsPonVlanTranslationOldCos}
       ::= { utsPonVlanTranslationTable 1 }


       UtsPonVlanTranslationEntry ::=
          SEQUENCE {
             utsPonVlanTranslationModuleID                   INTEGER,
             utsPonVlanTranslationDeviceID                   INTEGER,
             utsPonVlanTranslationPortID                     INTEGER,
             utsPonVlanTranslationLogicPortID                INTEGER,
             utsPonVlanTranslationOldVID                     INTEGER,
             utsPonVlanTranslationOldCos                     INTEGER,
             utsPonVlanTranslationNewVID                     INTEGER,
             utsPonVlanTranslationNewCos                     INTEGER,
             utsPonVlanTranslationRowStatus                  RowStatus
          }

   utsPonVlanTranslationModuleID OBJECT-TYPE
      SYNTAX      INTEGER
      MAX-ACCESS  not-accessible
      STATUS      current
      DESCRIPTION
         "An indication of module id."
      ::= { utsPonVlanTranslationEntry 1 }


   utsPonVlanTranslationDeviceID OBJECT-TYPE
      SYNTAX INTEGER
      MAX-ACCESS not-accessible
      STATUS current
      DESCRIPTION
         "An indication of device id."
      ::= { utsPonVlanTranslationEntry 2 }

   utsPonVlanTranslationPortID OBJECT-TYPE
      SYNTAX INTEGER
      MAX-ACCESS not-accessible
      STATUS current
      DESCRIPTION
         "An indication of olt port id."
      ::= { utsPonVlanTranslationEntry 3 }

   utsPonVlanTranslationLogicPortID OBJECT-TYPE
      SYNTAX INTEGER
      MAX-ACCESS not-accessible
      STATUS current
      DESCRIPTION
         "An indication of olt onu id."
      ::= { utsPonVlanTranslationEntry 4 }

   utsPonVlanTranslationOldVID OBJECT-TYPE
      SYNTAX      INTEGER
      MAX-ACCESS  not-accessible
      STATUS      current
      DESCRIPTION
         "The value of pre-translation vlan id, the value shoud be from 0 to 4095, 4095 means do not care this value."
      ::= { utsPonVlanTranslationEntry 5 }

   utsPonVlanTranslationOldCos OBJECT-TYPE
      SYNTAX      INTEGER
      MAX-ACCESS  not-accessible
      STATUS      current
      DESCRIPTION
         "The old cos,the range should be 0 to 8, 8 means do not care this value."
   ::= { utsPonVlanTranslationEntry 6 }

   utsPonVlanTranslationNewVID OBJECT-TYPE
      SYNTAX      INTEGER
      MAX-ACCESS  read-create
      STATUS      current
      DESCRIPTION
         "The value of after-translation vlan id, the value shoud be from 0 to 4094."
      ::= { utsPonVlanTranslationEntry 7 }

   utsPonVlanTranslationNewCos OBJECT-TYPE
      SYNTAX      INTEGER
      MAX-ACCESS  read-create
      STATUS      current
      DESCRIPTION
         "The new cos for N:1 translaiton, the value should be 0 to 7;when in 1:1 translation, this value should be set 8."
   ::= { utsPonVlanTranslationEntry 8 }


   utsPonVlanTranslationRowStatus OBJECT-TYPE
      SYNTAX         RowStatus
      MAX-ACCESS     read-create
      STATUS         current
      DESCRIPTION
         "Row status for the current entry. "
      ::= { utsPonVlanTranslationEntry 9 }

------
------
------

utsDot3OltTransceiverObjects OBJECT IDENTIFIER ::= { utsDot3OltMIB 2}

utsDot3OltTransceiverTable OBJECT-TYPE
SYNTAX  SEQUENCE OF UtsDot3OltTransceiverEntry
        MAX-ACCESS  not-accessible
        STATUS  current
        DESCRIPTION
"Table for dot3 OLT transceiver MIBs."
        ::= { utsDot3OltTransceiverObjects 1 }

utsDot3OltTransceiverEntry OBJECT-TYPE
SYNTAX  UtsDot3OltTransceiverEntry
       MAX-ACCESS  not-accessible
       STATUS  current
       DESCRIPTION
"An entry in the dot3 PLT MIBs table."
       INDEX  { utsDot3OltTransceiverIndex }
       ::= { utsDot3OltTransceiverTable 1 }

UtsDot3OltTransceiverEntry ::=
       SEQUENCE {
                    utsDot3OltTransceiverIndex						INTEGER,
                    utsDot3OltTransceiverPONPortLinkIndPolarity	    INTEGER,
		    	    utsDot3OltTransceiverAGCResetGateOffset			INTEGER,
                    utsDot3OltTransceiverAGCResetDiscoveryOffset	INTEGER,
                    utsDot3OltTransceiverAGCResetDuration			INTEGER,
                    utsDot3OltTransceiverAGCResetPolarity			INTEGER,
                    utsDot3OltTransceiverCDRResetGateOffset			INTEGER,
                    utsDot3OltTransceiverCDRResetDiscoveryOffset	INTEGER,
                    utsDot3OltTransceiverCDRResetDuration			INTEGER,
                    utsDot3OltTransceiverCDRResetPolarity			INTEGER,
                    utsDot3OltTransceiverEndGrantResetOffset		INTEGER,
                    utsDot3OltTransceiverEndGrantResetDuration		INTEGER,
                    utsDot3OltTransceiverEndGrantResetPolarity		INTEGER,
                    utsDot3OltTransceiverDiscoveryRelockEnable		TruthValue,
                    utsDot3OltTransceiverDiscoveryLaserRxLossPolarity	INTEGER,
                    utsDot3OltTransceiverPONTxDisablePolarity		INTEGER,
                    utsDot3OltTransceiverOpticsDeadZone				INTEGER,
                    utsDot3OltTransceiverUseOpticsSignalLoss		TruthValue,
                    utsDot3OltTransceiverAGCLockTime					INTEGER,
                    utsDot3OltTransceiverCDRLockTime					INTEGER
       }


utsDot3OltTransceiverIndex OBJECT-TYPE
SYNTAX  INTEGER
       MAX-ACCESS  read-only
       STATUS  current
       DESCRIPTION
"Index of tranceiver's table which is corresponding to the tranceiver type in olt table. "
        ::= { utsDot3OltTransceiverEntry 1 }

utsDot3OltTransceiverPONPortLinkIndPolarity OBJECT-TYPE
SYNTAX  INTEGER
       MAX-ACCESS  read-only
       STATUS  current
       DESCRIPTION
"Polarity of the PON port link indication clock. 0 - Active low, 1 - Active high."
        ::= { utsDot3OltTransceiverEntry 2 }


utsDot3OltTransceiverAGCResetGateOffset OBJECT-TYPE
SYNTAX  INTEGER
       MAX-ACCESS  read-only
       STATUS  current
       DESCRIPTION
"AGC reset activation offset before normal grant CDR reset activation,
measured in 8 nanoseconds units. 12-bit value (0 - 4095)."
        ::= { utsDot3OltTransceiverEntry 3 }

utsDot3OltTransceiverAGCResetDiscoveryOffset OBJECT-TYPE
SYNTAX  INTEGER
       MAX-ACCESS  read-only
       STATUS  current
       DESCRIPTION
"AGC reset activation offset before discovery CDR reset activation,
measured in 8 nanoseconds units. 12-bit value (0 - 4095)."
        ::= { utsDot3OltTransceiverEntry 4 }

utsDot3OltTransceiverAGCResetDuration OBJECT-TYPE
SYNTAX  INTEGER
       MAX-ACCESS  read-only
       STATUS  current
       DESCRIPTION
"AGC reset pulse duration, measured
in 8 nanoseconds units. 3-bit value (0 - 7)."
        ::= { utsDot3OltTransceiverEntry 5 }

utsDot3OltTransceiverAGCResetPolarity OBJECT-TYPE
SYNTAX  INTEGER
       MAX-ACCESS  read-only
       STATUS  current
       DESCRIPTION
"AGC reset pulse polarity. 0 - Active low, 1 - Active high."
        ::= { utsDot3OltTransceiverEntry 6 }



utsDot3OltTransceiverCDRResetGateOffset OBJECT-TYPE
SYNTAX  INTEGER
       MAX-ACCESS  read-only
       STATUS  current
       DESCRIPTION
"CDR reset activation offset before start of normal grant, measured in
8 nanoseconds units. 12-bit value (0 - 4095)."
        ::= { utsDot3OltTransceiverEntry 7 }

utsDot3OltTransceiverCDRResetDiscoveryOffset OBJECT-TYPE
SYNTAX  INTEGER
       MAX-ACCESS  read-only
       STATUS  current
       DESCRIPTION
"CDR reset activation offset before start of discovery window,
measured in 8 nanoseconds units. 12-bit value (0 - 4095)."
        ::= { utsDot3OltTransceiverEntry 8 }

utsDot3OltTransceiverCDRResetDuration OBJECT-TYPE
SYNTAX  INTEGER
       MAX-ACCESS  read-only
       STATUS  current
       DESCRIPTION
"CDR reset pulse duration, measured
in 8 nanoseconds units. 3-bit value (0 - 7)."
        ::= { utsDot3OltTransceiverEntry 9 }

utsDot3OltTransceiverCDRResetPolarity OBJECT-TYPE
SYNTAX  INTEGER
       MAX-ACCESS  read-only
       STATUS  current
       DESCRIPTION
"AGC reset pulse polarity. 0 - Active low, 1 - Active high."
        ::= { utsDot3OltTransceiverEntry 10 }

utsDot3OltTransceiverEndGrantResetOffset OBJECT-TYPE
SYNTAX  INTEGER
       MAX-ACCESS  read-only
       STATUS  current
       DESCRIPTION
"End of grant reset activation offset, measured in 8 nanoseconds units.
12-bit value (0 - 4095)."
        ::= { utsDot3OltTransceiverEntry 11 }

utsDot3OltTransceiverEndGrantResetDuration OBJECT-TYPE
SYNTAX  INTEGER
       MAX-ACCESS  read-only
       STATUS  current
       DESCRIPTION
"End of grant reset pulse duration, measured in 8 nanoseconds units.
3-bit value (0 - 7)."
        ::= { utsDot3OltTransceiverEntry 12 }

utsDot3OltTransceiverEndGrantResetPolarity OBJECT-TYPE
SYNTAX  INTEGER
       MAX-ACCESS  read-only
       STATUS  current
       DESCRIPTION
"End of grant reset pulse polarity. 0 - Active low, 1 - Active high."
        ::= { utsDot3OltTransceiverEntry 13 }

utsDot3OltTransceiverDiscoveryRelockEnable OBJECT-TYPE
SYNTAX  TruthValue
       MAX-ACCESS  read-only
       STATUS  current
       DESCRIPTION
"Enable the Rx PHY re-locking mechanism during discovery window."
        ::= { utsDot3OltTransceiverEntry 14 }

utsDot3OltTransceiverDiscoveryLaserRxLossPolarity OBJECT-TYPE
SYNTAX  INTEGER
       MAX-ACCESS  read-only
       STATUS  current
       DESCRIPTION
"Laser Rx loss signal polarity. 0 - Active low, 1 - Active high."
        ::= { utsDot3OltTransceiverEntry 15 }

utsDot3OltTransceiverPONTxDisablePolarity OBJECT-TYPE
SYNTAX  INTEGER
       MAX-ACCESS  read-only
       STATUS  current
       DESCRIPTION
"PON optics transmission signal polarity. 0 - Active low, 1 - Active high."
        ::= { utsDot3OltTransceiverEntry 16 }

utsDot3OltTransceiverOpticsDeadZone OBJECT-TYPE
SYNTAX  INTEGER
       MAX-ACCESS  read-only
       STATUS  current
       DESCRIPTION
"Minimal length between the end of a grant to the start of the other,
measured in 8 nanoseconds units. 4-bit value (0 - 15)."
        ::= { utsDot3OltTransceiverEntry 17 }

utsDot3OltTransceiverUseOpticsSignalLoss OBJECT-TYPE
SYNTAX  TruthValue
       MAX-ACCESS  read-only
       STATUS  current
       DESCRIPTION
"Use the optics signal loss?signal by
the OLT line status state machine."
        ::= { utsDot3OltTransceiverEntry 18 }


utsDot3OltTransceiverAGCLockTime OBJECT-TYPE
SYNTAX  INTEGER
       MAX-ACCESS  read-only
       STATUS  current
       DESCRIPTION
"PON upstream data AGC lock time measured in TQ (in increments  of  16ns)."
        ::= { utsDot3OltTransceiverEntry 19 }


utsDot3OltTransceiverCDRLockTime OBJECT-TYPE
SYNTAX  INTEGER
       MAX-ACCESS  read-only
       STATUS  current
       DESCRIPTION
"PON RX signal synchronization time measured in TQ. 16-bit value."
        ::= { utsDot3OltTransceiverEntry 20 }



------
------ 2. ONU
------

utsDot3OnuMIB OBJECT IDENTIFIER ::= { utsEponConfExtObjects 2}

utsDot3OnuObjects OBJECT IDENTIFIER ::= { utsDot3OnuMIB 1}

utsDot3OnuTable OBJECT-TYPE
SYNTAX  SEQUENCE OF UtsDot3OnuEntry
        MAX-ACCESS  not-accessible
        STATUS  current
        DESCRIPTION
"Table for dot3 ONU MIBs."
        ::= { utsDot3OnuObjects 1 }

utsDot3OnuEntry OBJECT-TYPE
SYNTAX  UtsDot3OnuEntry
       MAX-ACCESS  not-accessible
       STATUS  current
       DESCRIPTION
"An entry in the dot3 Onu MIBs table."
       INDEX  { ifIndex }
       ::= { utsDot3OnuTable 1 }

UtsDot3OnuEntry ::=
       SEQUENCE {
               utsDot3OnuModuleId				INTEGER,
               utsDot3OnuPortId					INTEGER,
               utsDot3OnuLogicalPortId		   INTEGER,
               utsDot3OnuRegistrationState	INTEGER,
               utsDot3OnuHwVersion				DisplayString,
               utsDot3OnuFwVersion				DisplayString,
               utsDot3OnuMaxLLID				   INTEGER,
               utsDot3OnuOAMStandardVersion	INTEGER,
		       utsDot3OnuRTT                 INTEGER,
		       utsDot3OnuHwType              INTEGER,
		       utsDot3OnuSwitchHwRev			DisplayString,
		       utsDot3OnuSwitchFwRev			DisplayString,
		       utsDot3OnuIADStatus				INTEGER,
		       utsDot3OnuPonMacAddress			MacAddress,
               utsDot3OnuAES128EncryptionStatus	INTEGER,
               utsDot3OnuAES128EncryptionKey    OCTET STRING,
               utsDot3OnuPonLoopbackTestStatus  INTEGER,
               utsDot3OnuPonLoopbackTestVlanId INTEGER,
               utsDot3OnuEthernetLinkStatus    INTEGER,
-- will take effect in node version 3.0
--		       utsDot3OnuMaxPendingGrants      INTEGER,
		       utsDot3OnuSwitchMacAddress	   MacAddress,
		       utsDot3OnuAdminStatus      INTEGER,
		       utsDot3OnuMulticastFilter  INTEGER,
		       utsDot3OnuRMAutoNegotiation INTEGER,
		       utsDot3OnuReset             INTEGER,
		       utsDot3OnuQinQ              INTEGER,
		       utsDot3OnuCATVStatus        INTEGER
        }

utsDot3OnuModuleId OBJECT-TYPE
SYNTAX  INTEGER
       MAX-ACCESS  read-only
       STATUS  current
       DESCRIPTION
"A read only value to identifiy the OLT module id for the current ONU."
        ::= { utsDot3OnuEntry 1 }


utsDot3OnuPortId OBJECT-TYPE
SYNTAX  INTEGER
       MAX-ACCESS  read-only
       STATUS  current
       DESCRIPTION
"A read only value to identifiy the OLT port id for the current ONU."
        ::= { utsDot3OnuEntry 2 }


utsDot3OnuLogicalPortId OBJECT-TYPE
SYNTAX  INTEGER
       MAX-ACCESS  read-only
       STATUS  current
       DESCRIPTION
"A read only value to identifiy the logical port id for the current ONU."
        ::= { utsDot3OnuEntry 3 }


utsDot3OnuRegistrationState OBJECT-TYPE
SYNTAX  INTEGER {
          unregistered(1),
          pending(2),
          registered(3)
}

       MAX-ACCESS  read-only
       STATUS  current
       DESCRIPTION
"A  read-only value that identifies the operational state of the  Multi-
Point MAC Control sublayer as defined in [802.3ah] clause 64. When  this
attribute has the enumeration 'unregistered' the interface may  be  used
for  registering a link partner. When this attribute has the enumeration
'registering'  the  interface is in the process of registering  a  link-
partner.  When  this  attribute  has the  enumeration  'registered'  the
interface has an established link-partner. It's identical to
dot3MpcpRegistrationState in Dot3MpcpEntry."
       REFERENCE   "[802.3ah], 30.3.5.1.7."
        ::= { utsDot3OnuEntry 4 }

utsDot3OnuHwVersion OBJECT-TYPE
SYNTAX  DisplayString
       MAX-ACCESS  read-only
       STATUS  current
       DESCRIPTION
"Hardware version of ONU PON component."
        ::= { utsDot3OnuEntry 5 }

utsDot3OnuFwVersion OBJECT-TYPE
SYNTAX  DisplayString
       MAX-ACCESS  read-only
       STATUS  current
       DESCRIPTION
"Firmware version of ONU PON component."
        ::= { utsDot3OnuEntry 6 }

utsDot3OnuMaxLLID OBJECT-TYPE
SYNTAX  INTEGER
       MAX-ACCESS  read-only
       STATUS  current
       DESCRIPTION
"Maximum number of supported LLID."
        ::= { utsDot3OnuEntry 7 }


utsDot3OnuOAMStandardVersion OBJECT-TYPE
SYNTAX  INTEGER {
	oam-802-3ah-draft-1-2(1),
	oam-802-3ah-draft-2-0(2)
}
       MAX-ACCESS  read-only
       STATUS  current
       DESCRIPTION
"ONU supports OAM standard according to 802.3ah draft 1.2 or 2.0.
Only support oam-802-3ah-draft-2-0(2)."
        ::= { utsDot3OnuEntry 8 }


utsDot3OnuRTT OBJECT-TYPE
SYNTAX  INTEGER
       MAX-ACCESS  read-only
       STATUS  current
       DESCRIPTION
"Round Trip Time in TQ unit."
        ::= { utsDot3OnuEntry 9 }

utsDot3OnuHwType OBJECT-TYPE
SYNTAX  INTEGER
   {
		  onu100(1),
			onu1000B(2),
			onu1000C(3),
			onu200A(4),
			onu200B(5),
			onu2024(6),
			onu2004(7),
		  onu101K(8),
		  onu301(9),
		  onu301C(10),
		  onu404(11),
		  onu404C(12),
		  onu804(13),
		  onu804C(14),
		  onu1001C(15),
			onu3004(16),
	    onu1001i(17),
	    onu2004i(18),
	    onu404i(19),
	    clt2060(20),
	    onu204i(21),
	    onu208i(22),
	    onu204h(23),
	    onu408t(24),
	    onu2024i(25),
	    onub210(26),
	    onu1001h(27),
	    onub220(28),
	    onu804i(29),
	    onu101(30),
	    onu1001b(31),
	    onu2004h(32),
	    onu204d(33),
	    onu404t(34),
	    onu4024t(35),
	    onu4024i(36),
        onu101i(38),
        onub1205y(39),
        onub1205d(40),
        onub130(41),
	    tkOnu(100),
	    pmcOnu(101),
	    unknow(200)
	}
       MAX-ACCESS  read-only
       STATUS  current
       DESCRIPTION
"ONU Hardware Type"
        ::= { utsDot3OnuEntry 10 }

utsDot3OnuSwitchHwRev OBJECT-TYPE
SYNTAX  DisplayString
       MAX-ACCESS  read-only
       STATUS  current
       DESCRIPTION
"Hardware version of ONU switch component."
        ::= { utsDot3OnuEntry 11 }

utsDot3OnuSwitchFwRev OBJECT-TYPE
SYNTAX  DisplayString
       MAX-ACCESS  read-only
       STATUS  current
       DESCRIPTION
"firmware version of ONU switch component."
        ::= { utsDot3OnuEntry 12 }

utsDot3OnuIADStatus OBJECT-TYPE
	SYNTAX  INTEGER
		{
			ready(1),
			unknown(2)
		}
   MAX-ACCESS  read-only
   STATUS  current
   DESCRIPTION
      "Whether Onu switch component  is ready for operation"
   ::= { utsDot3OnuEntry 13 }

utsDot3OnuPonMacAddress OBJECT-TYPE
   SYNTAX  MacAddress
   MAX-ACCESS  read-only
   STATUS  current
   DESCRIPTION
      "ONU PON part mac address."
   ::= { utsDot3OnuEntry 14 }

-- Zhaoxf added on Dec 25 2005

utsDot3OnuAES128EncryptionStatus OBJECT-TYPE
   SYNTAX  INTEGER
	{
		disable(1),
		bidirectional(2),
		downlink(3)
	}
   MAX-ACCESS  read-write
   STATUS  current
   DESCRIPTION
      "AES encryption status for ONU"
   ::= { utsDot3OnuEntry 15 }

utsDot3OnuAES128EncryptionKey OBJECT-TYPE
   SYNTAX  OCTET STRING(SIZE(0..16))
   MAX-ACCESS  read-write
   STATUS  current
   DESCRIPTION
      "AES encryption key set for ONU. The NULL string will
      restore it to default value."
   ::= { utsDot3OnuEntry 16 }

utsDot3OnuPonLoopbackTestStatus OBJECT-TYPE
   SYNTAX  INTEGER
   {
      disable(1),
	  enable(2)
   }
   MAX-ACCESS  read-write
   STATUS  current
   DESCRIPTION
      "Enable or disable PON loopback test"
   ::= { utsDot3OnuEntry 17 }

utsDot3OnuPonLoopbackTestVlanId OBJECT-TYPE
   SYNTAX  INTEGER ( 1..4094 )
   MAX-ACCESS  read-write
   STATUS  current
   DESCRIPTION
      "Set the VLAN ID for PON loopback test. The VID is only meaningful
in ISP mode, application mode and QinQ mode. In unique tag mode, VID
is not meaningful."
   ::= { utsDot3OnuEntry 18 }

utsDot3OnuEthernetLinkStatus  OBJECT-TYPE
   SYNTAX  INTEGER
   {
     linkdown(1),
     linkup(2),
     unknow(3)
   }
   MAX-ACCESS  read-only
   STATUS  current
   DESCRIPTION
      "The link status of ONU UNI port"
   ::= { utsDot3OnuEntry 19 }

--utsDot3OnuMaxPendingGrants OBJECT-TYPE
--   SYNTAX  INTEGER
--   MAX-ACCESS  read-only
--   STATUS  current
--   DESCRIPTION
--      "The ONU Maximum Pending Grants."
--   ::= { utsDot3OnuEntry 20 }

-- zhaoxf added, Jan 15,2006

utsDot3OnuSwitchMacAddress OBJECT-TYPE
   SYNTAX  MacAddress
   MAX-ACCESS  read-only
   STATUS  current
   DESCRIPTION
      "ONU switch part mac address."
   ::= { utsDot3OnuEntry 21 }

utsDot3OnuAdminStatus OBJECT-TYPE
   SYNTAX  INTEGER
   {
   	 up(1),
   	 down(2),
   	 testing(3)
   }
   MAX-ACCESS  read-write
   STATUS  current
   DESCRIPTION
      "Set the ONU PON part administrator status"
   ::= { utsDot3OnuEntry 24 }

utsDot3OnuMulticastFilter OBJECT-TYPE
   SYNTAX  INTEGER
   {
   	 enable(1),
   	 disable(2)
   }
   MAX-ACCESS  read-write
   STATUS  current
   DESCRIPTION
      "Enable or disable the ONU multicast filtering."
   ::= { utsDot3OnuEntry 25 }

utsDot3OnuRMAutoNegotiation OBJECT-TYPE
   SYNTAX  INTEGER
   {
   	 auto10M(1),
   	 auto100M(2),
   	 auto1000M(3),
   	 half10M(4),
   	 full10M(5),
   	 half100M(6),
   	 full100M(7)
   	 --half1000M(8),
   	 --full1000M(9)
   }
   MAX-ACCESS  read-write
   STATUS  current
   DESCRIPTION
      "Set the ONU remote managment auto negotiation attributes."
   ::= { utsDot3OnuEntry 26 }

utsDot3OnuReset OBJECT-TYPE
   SYNTAX  INTEGER
   {
   	 normal(1), -- read only for normal status
   	 reset(2)   -- write to reset the ONU
   }
   MAX-ACCESS  read-write
   STATUS  current
   DESCRIPTION
      "Reset the ONU PON part."
   ::= { utsDot3OnuEntry 27 }

--Added by tomsong for Q-in-Q function support 2006.6.22
utsDot3OnuQinQ OBJECT-TYPE
    SYNTAX INTEGER
    {
      disable(1),
      enable(2)
    }
    MAX-ACCESS  read-write
    STATUS current
    DESCRIPTION
         "Enable or disable Q-in-Q function, the default value is disable!"
    ::= { utsDot3OnuEntry 28 }

utsDot3OnuCATVStatus OBJECT-TYPE
    SYNTAX INTEGER
    {
      on(1),
      off(2)
    }
    MAX-ACCESS  read-write
    STATUS current
    DESCRIPTION
         "Enable or disable CATV. Only for ONU have CATV function, such as ONU3004, ONU804."
    ::= { utsDot3OnuEntry 29 }
-- ONU2 MIB

-- utsDot3Onu2Objects OBJECT IDENTIFIER ::= { utsDot3OnuMIB 2}

utsDot3Onu2Table OBJECT-TYPE
SYNTAX  SEQUENCE OF UtsDot3Onu2Entry
        MAX-ACCESS  not-accessible
        STATUS  current
        DESCRIPTION
"Table for dot3 ONU MIBs."
        ::= { utsDot3OnuObjects 2 }

utsDot3Onu2Entry OBJECT-TYPE
SYNTAX  UtsDot3Onu2Entry
       MAX-ACCESS  not-accessible
       STATUS  current
       DESCRIPTION
"An entry in the dot3 Onu MIBs table."
       INDEX  { utsDot3Onu2ModuleId, utsDot3Onu2DeviceId,utsDot3Onu2PortId, utsDot3Onu2LogicalPortId }
       ::= { utsDot3Onu2Table 1 }

UtsDot3Onu2Entry ::=
       SEQUENCE {
               utsDot3Onu2ModuleId			   INTEGER,
               utsDot3Onu2DeviceId             INTEGER,
               utsDot3Onu2PortId			   INTEGER,
               utsDot3Onu2LogicalPortId		   INTEGER,
               utsDot3OnuLlid                  INTEGER,
               utsDot3EepromVersion            INTEGER,
               utsDot3OamVersion               INTEGER,
               utsDot3OnuMacAddress            MacAddress,
               utsDot3OnuAdmin                 INTEGER,
               utsDot3OnuTransparentMode       INTEGER,
               utsDot3OnuStatus                INTEGER,
               utsDot3OnuMpcpTimeout           INTEGER,
               utsDot3OnuVendor                OCTET STRING,
               utsDot3OnuModule                OCTET STRING,
               utsDot3OnuHwVer                 OCTET STRING,
               utsDot3OnuSerialNumber          OCTET STRING,
               utsDot3OnuLaserOnTime           INTEGER,
               utsDot3OnuLaserOffTime          INTEGER,
               utsDot3OnuDot1adEnable          TruthValue,
               utsDot3OnuDot1adTPID            INTEGER,
               utsDot3Onu2Reset                INTEGER
        }

utsDot3Onu2ModuleId OBJECT-TYPE
SYNTAX  INTEGER
       MAX-ACCESS  read-only
       STATUS  current
       DESCRIPTION
"A read only value to identifiy the OLT module id for the current ONU."
        ::= { utsDot3Onu2Entry 1 }

utsDot3Onu2DeviceId OBJECT-TYPE
SYNTAX  INTEGER
       MAX-ACCESS  read-only
       STATUS  current
       DESCRIPTION
"A read only value to identifiy the OLT device id for the current ONU."
        ::= { utsDot3Onu2Entry 2 }

utsDot3Onu2PortId OBJECT-TYPE
SYNTAX  INTEGER
       MAX-ACCESS  read-only
       STATUS  current
       DESCRIPTION
"A read only value to identifiy the OLT port id for the current ONU."
        ::= { utsDot3Onu2Entry 3 }

utsDot3Onu2LogicalPortId OBJECT-TYPE
SYNTAX  INTEGER
       MAX-ACCESS  read-only
       STATUS  current
       DESCRIPTION
"A read only value to identifiy the logical port id for the current ONU."
        ::= { utsDot3Onu2Entry 4 }

utsDot3OnuLlid OBJECT-TYPE
SYNTAX  INTEGER
       MAX-ACCESS  read-only
       STATUS  current
       DESCRIPTION
"The logical link ID"
        ::= { utsDot3Onu2Entry 5 }

utsDot3EepromVersion OBJECT-TYPE
SYNTAX  INTEGER
       MAX-ACCESS  read-only
       STATUS  current
       DESCRIPTION
"EEPROM version"
        ::= { utsDot3Onu2Entry 6 }

utsDot3OamVersion OBJECT-TYPE
SYNTAX  INTEGER
       MAX-ACCESS  read-only
       STATUS  current
       DESCRIPTION
"OAM version"
        ::= { utsDot3Onu2Entry 7 }

utsDot3OnuMacAddress OBJECT-TYPE
SYNTAX MacAddress
       MAX-ACCESS  read-only
       STATUS  current
       DESCRIPTION
"ONU MAC address"
        ::= { utsDot3Onu2Entry 8 }

utsDot3OnuAdmin OBJECT-TYPE
SYNTAX INTEGER
	   {
	     up(1),
	     down(2)
	   }
       MAX-ACCESS  read-write
       STATUS  current
       DESCRIPTION
"ONU Admin status"
        ::= { utsDot3Onu2Entry 9 }

utsDot3OnuTransparentMode OBJECT-TYPE
SYNTAX INTEGER
	   {
	     enable(1),
	     disable(2)
	   }
       MAX-ACCESS  read-write
       STATUS  current
       DESCRIPTION
"ONU Admin status"
        ::= { utsDot3Onu2Entry 10 }

utsDot3OnuStatus OBJECT-TYPE
SYNTAX INTEGER
	   {
	     registered(1),  -- registered
	     deregistered(2) -- deregistered normally
	   }
       MAX-ACCESS  read-write
       STATUS  current
       DESCRIPTION
"ONU Admin status"
        ::= { utsDot3Onu2Entry 11 }

utsDot3OnuMpcpTimeout OBJECT-TYPE
SYNTAX INTEGER
       MAX-ACCESS  read-write
       STATUS  current
       DESCRIPTION
"MPCP timeout value"
        ::= { utsDot3Onu2Entry 12 }

utsDot3OnuVendor OBJECT-TYPE
SYNTAX OCTET STRING(SIZE(1..16))
       MAX-ACCESS  read-only
       STATUS  current
       DESCRIPTION
"ONU vendor"
        ::= { utsDot3Onu2Entry 13 }

utsDot3OnuModule OBJECT-TYPE
SYNTAX OCTET STRING(SIZE(1..16))
       MAX-ACCESS  read-only
       STATUS  current
       DESCRIPTION
"ONU Module"
        ::= { utsDot3Onu2Entry 14 }

utsDot3OnuHwVer OBJECT-TYPE
SYNTAX OCTET STRING(SIZE(2))
       MAX-ACCESS  read-only
       STATUS  current
       DESCRIPTION
"ONU hardware version"
        ::= { utsDot3Onu2Entry 15 }

utsDot3OnuSerialNumber OBJECT-TYPE
SYNTAX OCTET STRING(SIZE(6))
       MAX-ACCESS  read-only
       STATUS  current
       DESCRIPTION
"ONU hardware version"
        ::= { utsDot3Onu2Entry 16 }

utsDot3OnuLaserOnTime OBJECT-TYPE
SYNTAX INTEGER
       MAX-ACCESS  read-only
       STATUS  current
       DESCRIPTION
"Laser on time"
        ::= { utsDot3Onu2Entry 17 }

utsDot3OnuLaserOffTime OBJECT-TYPE
SYNTAX INTEGER
       MAX-ACCESS  read-only
       STATUS  current
       DESCRIPTION
"Laser off time"
        ::= { utsDot3Onu2Entry 18 }

utsDot3OnuDot1adEnable OBJECT-TYPE
SYNTAX TruthValue
       MAX-ACCESS  read-write
       STATUS  current
       DESCRIPTION
"Whether to enable dot1ad"
        ::= { utsDot3Onu2Entry 19 }

utsDot3OnuDot1adTPID OBJECT-TYPE
SYNTAX INTEGER
       MAX-ACCESS  read-write
       STATUS  current
       DESCRIPTION
"Tag protocol id, by default 0x88a8"
        ::= { utsDot3Onu2Entry 20 }

utsDot3Onu2Reset OBJECT-TYPE
SYNTAX  INTEGER
       {
         normal(1),    -- read only, normal status
         resetGlobal(2),      -- write only, reset ONU globally
         resetMpcp(3)         -- write only, MPCP reset
       }
       MAX-ACCESS  read-write
       STATUS  current
       DESCRIPTION
"Reset ONU"
        ::= { utsDot3Onu2Entry 21 }

-- ONU traffic profile

utsDot3Onu2TrafficProfTable OBJECT-TYPE
SYNTAX  SEQUENCE OF UtsDot3Onu2TrafficProfEntry
        MAX-ACCESS  not-accessible
        STATUS  current
        DESCRIPTION
"Table for dot3 ONU MIBs."
        ::= { utsDot3OnuObjects 5 }

utsDot3Onu2TrafficProfEntry OBJECT-TYPE
SYNTAX  UtsDot3Onu2TrafficProfEntry
       MAX-ACCESS  not-accessible
       STATUS  current
       DESCRIPTION
"An entry in the dot3 Onu MIBs table."
       INDEX  { utsDot3OnuTProfModuleId,utsDot3OnuTProfDeviceId,utsDot3OnuTProfPortId,
                utsDot3OnuTProfLogicalPortId }
       ::= { utsDot3Onu2TrafficProfTable 1 }

UtsDot3Onu2TrafficProfEntry ::=
       SEQUENCE {
               utsDot3OnuTProfModuleId			   INTEGER,
               utsDot3OnuTProfDeviceId             INTEGER,
               utsDot3OnuTProfPortId			   INTEGER,
               utsDot3OnuTProfLogicalPortId		   INTEGER,
               utsDot3OnuUpstreamPir                INTEGER,
               utsDot3OnuDownstreamPir              INTEGER,
               utsDot3OnuUpstreamCir                INTEGER,
               utsDot3OnuDownstreamCir              INTEGER,
               utsDot3OnuUpstreamMaxBurstSize       INTEGER,
               utsDot3OnuDownstreamMaxBurstSize     INTEGER,
--               utsDot3OnuUpsteamMaxDelay           INTEGER,
--               utsDot3OnuUpsteamMaxJitter          INTEGER,
               utsDot3OnuUpstreamWeight             INTEGER,
               utsDot3OnuUpstreamFir                INTEGER
        }

utsDot3OnuTProfModuleId OBJECT-TYPE
SYNTAX  INTEGER
       MAX-ACCESS  read-only
       STATUS  current
       DESCRIPTION
"A read only value to identifiy the OLT module id for the current ONU."
        ::= { utsDot3Onu2TrafficProfEntry 1 }

utsDot3OnuTProfDeviceId OBJECT-TYPE
SYNTAX  INTEGER
       MAX-ACCESS  read-only
       STATUS  current
       DESCRIPTION
"A read only value to identifiy the OLT device id for the current ONU."
        ::= { utsDot3Onu2TrafficProfEntry 2 }

utsDot3OnuTProfPortId OBJECT-TYPE
SYNTAX  INTEGER
       MAX-ACCESS  read-only
       STATUS  current
       DESCRIPTION
"A read only value to identifiy the OLT port id for the current ONU."
        ::= { utsDot3Onu2TrafficProfEntry 3 }

utsDot3OnuTProfLogicalPortId OBJECT-TYPE
SYNTAX  INTEGER
       MAX-ACCESS  read-only
       STATUS  current
       DESCRIPTION
"A read only value to identifiy the logical port id for the current ONU."
        ::= { utsDot3Onu2TrafficProfEntry 4 }

utsDot3OnuUpstreamPir OBJECT-TYPE
SYNTAX  INTEGER(1..1000000)
       MAX-ACCESS  read-write
       STATUS  current
       DESCRIPTION
"Maximum Bandwidth/PIR (in Kbps).
 Upstream DBA: 256Kbps - 1000Mbps with the granularity of 256Kbps;
 Upstream policing: 16Kbps - 1000Mbps with ranularity:
                      16Kbps - 4Mbps:   16Kbps;
                      4Mbps  - 125Mbps: 512Kbps;
                      125Mbps- 1Gbps:   2Mbps."
        ::= { utsDot3Onu2TrafficProfEntry 5 }

utsDot3OnuDownstreamPir OBJECT-TYPE
SYNTAX  INTEGER(1..1000000)
       MAX-ACCESS  read-write
       STATUS  current
       DESCRIPTION
"Maximum Bandwidth/PIR (in Kbps).
 Downstream policing: 16Kbps - 1000Mbps with ranularity:
                      16Kbps - 4Mbps:   16Kbps;
                      4Mbps  - 125Mbps: 512Kbps;
                      125Mbps- 1Gbps:   2Mbps."
        ::= { utsDot3Onu2TrafficProfEntry 6 }

utsDot3OnuUpstreamCir OBJECT-TYPE
SYNTAX  INTEGER(1..1000000)
       MAX-ACCESS  read-write
       STATUS  current
       DESCRIPTION
"Committed Bandwidth/CIR (in Kbps).
 Upstream DBA: 256Kbps - 970Mbps with the granularity of 256Kbps;
 Upstream policing: 16Kbps - 1000Mbps with ranularity:
                      16Kbps - 4Mbps:   16Kbps;
                      4Mbps  - 125Mbps: 512Kbps;
                      125Mbps- 1Gbps:   2Mbps."
        ::= { utsDot3Onu2TrafficProfEntry 7 }

utsDot3OnuDownstreamCir OBJECT-TYPE
SYNTAX  INTEGER(1..1000000)
       MAX-ACCESS  read-write
       STATUS  current
       DESCRIPTION
"Committed Bandwidth/CIR (in Kbps).
 Downstream policing: 16Kbps - 1000Mbps with ranularity:
                      16Kbps - 4Mbps:   16Kbps;
                      4Mbps  - 125Mbps: 512Kbps;
                      125Mbps- 1Gbps:   2Mbps."
        ::= { utsDot3Onu2TrafficProfEntry 8 }


utsDot3OnuUpstreamMaxBurstSize OBJECT-TYPE
SYNTAX  INTEGER(1..1000)
       MAX-ACCESS  read-write
       STATUS  current
       DESCRIPTION
"Maximum Burst Size (in Kb): 16KB - 1MB"
        ::= { utsDot3Onu2TrafficProfEntry 9 }

utsDot3OnuDownstreamMaxBurstSize OBJECT-TYPE
SYNTAX  INTEGER(1..1000)
       MAX-ACCESS  read-write
       STATUS  current
       DESCRIPTION
"Maximum Burst Size (in Kb): 16KB - 1MB"
        ::= { utsDot3Onu2TrafficProfEntry 10 }

utsDot3OnuUpstreamWeight OBJECT-TYPE
SYNTAX  INTEGER(1..10)
       MAX-ACCESS  read-write
       STATUS  current
       DESCRIPTION
"Priority/Weight Field.The default priority for an ONU is 1. 1 is lowest and 10 is highest.
 The priority value is used when deciding the proportion of bandwidth
 given to an ONU (beyond its CIR) in case of upstream bandwidth contention among ONUs.
 It is for both HW DBA and SW DBA."
       DEFVAL {1}
        ::= { utsDot3Onu2TrafficProfEntry 11 }

utsDot3OnuUpstreamFir OBJECT-TYPE
SYNTAX  INTEGER(0..1000000)       -- kb
       MAX-ACCESS  read-write
       STATUS  current
       DESCRIPTION
"Upstream fixed bandwidth, only available for software
 DBA mode and on hardware DBA mode, the value shall keep Zero."
        ::= { utsDot3Onu2TrafficProfEntry 12 }


-- utsDot3Onu2Objects OBJECT IDENTIFIER ::= { utsDot3OnuMIB 2}
--  CTC spec
--

utsDot3Onu2CtcTable OBJECT-TYPE
SYNTAX  SEQUENCE OF UtsDot3Onu2CtcEntry
        MAX-ACCESS  not-accessible
        STATUS  current
        DESCRIPTION
"Table for dot3 ONU MIBs."
        ::= { utsDot3OnuObjects 10 }

utsDot3Onu2CtcEntry OBJECT-TYPE
SYNTAX  UtsDot3Onu2CtcEntry
       MAX-ACCESS  not-accessible
       STATUS  current
       DESCRIPTION
"An entry in the dot3 Onu MIBs table."
       INDEX  { utsDot3OnuCtcModuleId,utsDot3OnuCtcDeviceId,utsDot3OnuCtcPortId,utsDot3OnuCtcLogicalPortId}
       ::= { utsDot3Onu2CtcTable 1 }

UtsDot3Onu2CtcEntry ::=
       SEQUENCE {
               utsDot3OnuCtcModuleId		   INTEGER,
               utsDot3OnuCtcDeviceId           INTEGER,
               utsDot3OnuCtcPortId			   INTEGER,
               utsDot3OnuCtcLogicalPortId	   INTEGER,

               utsDot3OnuCtcLlid               INTEGER,
               utsDot3OnuOui                   OCTET STRING,
               utsDot3OnuOamExtVersion         INTEGER,

               utsDot3Onu2SerialNumber         OCTET STRING,
               utsDot3OnuFwVer                 OCTET STRING,
               utsDot3OnuChipsetId             OCTET STRING,

               utsDot3OnuGEPortNumber          INTEGER,
               utsDot3OnuGEPortList            OCTET STRING,
               utsDot3OnuFEPortNumber          INTEGER,
               utsDot3OnuFEPortList            OCTET STRING,
               utsDot3OnuPOTSPortNumber        INTEGER,
               utsDot3OnuPOTSPortList          OCTET STRING,
               utsDot3OnuE1PortNumber          INTEGER,
               utsDot3OnuE1PortList            OCTET STRING,

               utsDot3OnuUpsQueueNum           INTEGER,
               utsDot3OnuMaxUpsQueueNum        INTEGER,
               utsDot3OnuDownsQueueNum         INTEGER,
               utsDot3OnuMaxDownsQueueNum      INTEGER,

               utsDot3OnuBatteryInstalled      TruthValue,

               utsDot3OnuFECAbility            INTEGER,
               utsDot3OnuFECMode               INTEGER,

               utsDot3OnuClassifiRuleClear     INTEGER,

               utsDot3OnuMulticastSwitch       INTEGER,
               utsDot3OnuMCastControlType      INTEGER,
               utsDot3OnuMCastEntryNum         INTEGER,
               utsDot3OnuMCastEntryClear       INTEGER,
--               utsDot3OnuDBAQueueSetNum        INTEGER,
               utsDot3Onu2CtcReset             INTEGER,
               utsDot3Onu2CtcRegisterStatus    INTEGER,
               utsDot3Onu2CtcEncryptTraffic    INTEGER,
               utsDot3Onu2CtcFDBAgingTime      INTEGER,
               utsDot3Onu2CtcFDBClear          INTEGER,
               utsDot3Onu2CtcAdmin             INTEGER,
               utsDot3Onu2CtcRTT               INTEGER,
               utsDot3Onu2CtcPVid              INTEGER,
               utsDot3Onu2CtcMaxMacAddress     INTEGER,
               utsDot3Onu2CtcVoIPPortLock      OCTET STRING,
               utsDot3Onu2CtcE1PortLock        OCTET STRING,
               utsDot3Onu2CtcSwitchAdminStatus INTEGER,
--               utsDot3Onu2CtcOpticalPower      INTEGER,
               utsDot3Onu2FastLeaveAbility     OCTET STRING,
               utsDot3Onu2FastLeaveAdminControl INTEGER,
               utsDot3Onu2EthernetPortAlarmReversion INTEGER,
               utsDot3Onu2MulticastFilter        INTEGER


        }

utsDot3OnuCtcModuleId OBJECT-TYPE
SYNTAX  INTEGER
       MAX-ACCESS  read-only
       STATUS  current
       DESCRIPTION
"A read only value to identifiy the OLT module id for the current ONU."
        ::= { utsDot3Onu2CtcEntry 1 }

utsDot3OnuCtcDeviceId OBJECT-TYPE
SYNTAX  INTEGER
       MAX-ACCESS  read-only
       STATUS  current
       DESCRIPTION
"A read only value to identifiy the OLT device id for the current ONU."
        ::= { utsDot3Onu2CtcEntry 2 }

utsDot3OnuCtcPortId OBJECT-TYPE
SYNTAX  INTEGER
       MAX-ACCESS  read-only
       STATUS  current
       DESCRIPTION
"A read only value to identifiy the OLT port id for the current ONU."
        ::= { utsDot3Onu2CtcEntry 3 }

utsDot3OnuCtcLogicalPortId OBJECT-TYPE
SYNTAX  INTEGER
       MAX-ACCESS  read-only
       STATUS  current
       DESCRIPTION
"A read only value to identifiy the logical port id for the current ONU."
        ::= { utsDot3Onu2CtcEntry 4 }

utsDot3OnuCtcLlid OBJECT-TYPE
SYNTAX  INTEGER
       MAX-ACCESS  read-only
       STATUS  current
       DESCRIPTION
"The logical link ID"
        ::= { utsDot3Onu2CtcEntry 5 }

utsDot3OnuOui OBJECT-TYPE
SYNTAX  OCTET STRING(SIZE(3))
       MAX-ACCESS  read-only
       STATUS  current
       DESCRIPTION
"OUI"
        ::= { utsDot3Onu2CtcEntry 6 }

utsDot3OnuOamExtVersion OBJECT-TYPE
SYNTAX  INTEGER
       MAX-ACCESS  read-only
       STATUS  current
       DESCRIPTION
"OAM Extension version"
        ::= { utsDot3Onu2CtcEntry 7 }

utsDot3Onu2SerialNumber OBJECT-TYPE
SYNTAX  OCTET STRING(SIZE(38))     -- CTC spec
       MAX-ACCESS  read-only
       STATUS  current
       DESCRIPTION
"Vendor ID:4
 ONU model:4
 ONU ID: ONU MAC address
 Hardware version:8
 Software version:16
 "
        ::= { utsDot3Onu2CtcEntry 8 }


utsDot3OnuFwVer  OBJECT-TYPE
SYNTAX  OCTET STRING     -- CTC spec
       MAX-ACCESS  read-only
       STATUS  current
       DESCRIPTION
"ONU firmware version"
        ::= { utsDot3Onu2CtcEntry 9 }

utsDot3OnuChipsetId OBJECT-TYPE
SYNTAX  OCTET STRING(SIZE(8)) -- CTC spec
       MAX-ACCESS  read-only
       STATUS  current
       DESCRIPTION
"ONU chipset ID
 Vendor ID:2
 Chip model:2
 Revision:1
 IC_Version/date:3
 "
        ::= { utsDot3Onu2CtcEntry 10 }

utsDot3OnuGEPortNumber OBJECT-TYPE
SYNTAX  INTEGER     -- CTC spec
       MAX-ACCESS  read-only
       STATUS  current
       DESCRIPTION
"GE port number"
        ::= { utsDot3Onu2CtcEntry 11 }

utsDot3OnuGEPortList OBJECT-TYPE
SYNTAX  OCTET STRING(SIZE(8))     -- CTC spec, 0x01[8..1] 23[16..9] 45[17..24] 67[25..32] 89[33..40] ab[41..48] cd[49..56] ef[57..64]
       MAX-ACCESS  read-only
       STATUS  current
       DESCRIPTION
"GE port bitmap"
        ::= { utsDot3Onu2CtcEntry 12 }

utsDot3OnuFEPortNumber OBJECT-TYPE
SYNTAX  INTEGER     -- CTC spec
       MAX-ACCESS  read-only
       STATUS  current
       DESCRIPTION
"FE port number"
        ::= { utsDot3Onu2CtcEntry 13 }

utsDot3OnuFEPortList OBJECT-TYPE
SYNTAX  OCTET STRING(SIZE(8))     -- CTC spec, 0x01[1..8] 23[9..16] 45[17..24] 67[25..32] 89[33..40] ab[41..48] cd[49..56] ef[57..64]
       MAX-ACCESS  read-only
       STATUS  current
       DESCRIPTION
"FE port bitmap"
        ::= { utsDot3Onu2CtcEntry 14 }

utsDot3OnuPOTSPortNumber OBJECT-TYPE
SYNTAX  INTEGER     -- CTC spec
       MAX-ACCESS  read-only
       STATUS  current
       DESCRIPTION
"POTS port number"
        ::= { utsDot3Onu2CtcEntry 15 }

utsDot3OnuPOTSPortList OBJECT-TYPE
SYNTAX  OCTET STRING(SIZE(8))     -- ctc spec, 0x01[1..8]
       MAX-ACCESS  read-only
       STATUS  current
       DESCRIPTION
"POTS port bitmap"
        ::= { utsDot3Onu2CtcEntry 16 }

utsDot3OnuE1PortNumber OBJECT-TYPE
SYNTAX  INTEGER     -- CTC spec
       MAX-ACCESS  read-only
       STATUS  current
       DESCRIPTION
"E1 port number"
        ::= { utsDot3Onu2CtcEntry 17 }

utsDot3OnuE1PortList OBJECT-TYPE
SYNTAX  OCTET STRING(SIZE(1))     -- CTC spec, 0x01[1..8]
       MAX-ACCESS  read-only
      STATUS  current
       DESCRIPTION
"E1 port bitmap"
        ::= { utsDot3Onu2CtcEntry 18 }

utsDot3OnuUpsQueueNum OBJECT-TYPE
SYNTAX  INTEGER     -- CTC spec
       MAX-ACCESS  read-only
       STATUS  current
       DESCRIPTION
"Upstream queue number"
        ::= { utsDot3Onu2CtcEntry 19 }

utsDot3OnuMaxUpsQueueNum OBJECT-TYPE
SYNTAX  INTEGER     -- CTC spec
       MAX-ACCESS  read-only
       STATUS  current
       DESCRIPTION
"Max upstream queue number"
        ::= { utsDot3Onu2CtcEntry 20 }

utsDot3OnuDownsQueueNum OBJECT-TYPE
SYNTAX  INTEGER     -- CTC spec
       MAX-ACCESS  read-only
       STATUS  current
       DESCRIPTION
"Down stream queue number"
        ::= { utsDot3Onu2CtcEntry 21 }

utsDot3OnuMaxDownsQueueNum OBJECT-TYPE
SYNTAX  INTEGER     -- CTC spec
       MAX-ACCESS  read-only
       STATUS  current
       DESCRIPTION
"Max down stream queue number"
        ::= { utsDot3Onu2CtcEntry 22 }

utsDot3OnuBatteryInstalled OBJECT-TYPE
SYNTAX  TruthValue
       MAX-ACCESS  read-only
       STATUS  current
       DESCRIPTION
"Wether have ONU battery backup"
        ::= { utsDot3Onu2CtcEntry 23 }

utsDot3OnuFECAbility OBJECT-TYPE
SYNTAX  INTEGER     -- CTC spec
	   {
	     unknown(1),
	     supported(2),
	     notsupported(3)
	   }
       MAX-ACCESS  read-only
       STATUS  current
       DESCRIPTION
"FEC ability"
        ::= { utsDot3Onu2CtcEntry 24 }

utsDot3OnuFECMode OBJECT-TYPE
SYNTAX  INTEGER     -- CTC spec
	   {
	     unknown(1),   -- read only
	     enable(2),
	     disable(3)
	   }
       MAX-ACCESS  read-write
       STATUS  current
       DESCRIPTION
"Set FEC mode"
        ::= { utsDot3Onu2CtcEntry 25 }

utsDot3OnuClassifiRuleClear OBJECT-TYPE
SYNTAX  INTEGER     -- CTC spec
	   {
	       clear(1)  -- write only
	   }
       MAX-ACCESS  read-write
       STATUS  current
       DESCRIPTION
"Clear all the classification rule for this ONU"
        ::= { utsDot3Onu2CtcEntry 26 }

utsDot3OnuMulticastSwitch OBJECT-TYPE
SYNTAX  INTEGER     -- CTC spec
	   {
	       ctc-specialSnooping(1), -- CTC specific IGMP snooping
	       ctc-controlSnooping(2), -- CTC controlable IGMP snooping
	       standard-Snooping(3)   -- standard IGMP snooping
	   }
       MAX-ACCESS  read-write
       STATUS  current
       DESCRIPTION
"Set the ONU multicast swith mechanism"
        ::= { utsDot3Onu2CtcEntry 27 }

utsDot3OnuMCastControlType OBJECT-TYPE
SYNTAX  INTEGER
	   {
	       gda-mac-only(1),   -- GDA MAC only
	       gda-mac-mvlan(2),  -- GDA MAC + Multicast VLAN ID
	       gda-mac-sa-mac(3)  -- optional
	   }
       MAX-ACCESS  read-write
       STATUS  current
       DESCRIPTION
"Set the multicast control type"
        ::= { utsDot3Onu2CtcEntry 28 }

utsDot3OnuMCastEntryNum  OBJECT-TYPE
SYNTAX  INTEGER
       MAX-ACCESS  read-only
       STATUS  current
       DESCRIPTION
"ONU multicast entry number"
        ::= { utsDot3Onu2CtcEntry 29 }

utsDot3OnuMCastEntryClear OBJECT-TYPE
SYNTAX  INTEGER
	   {
	       clear(1)       -- write only
	   }
       MAX-ACCESS  read-write
       STATUS  current
       DESCRIPTION
"Clear the ONU multicast forward entry"
        ::= { utsDot3Onu2CtcEntry 30 }

-- utsDot3OnuDBAQueueSetNum OBJECT-TYPE
-- SYNTAX  INTEGER                               2..4
--       MAX-ACCESS  read-only
--       STATUS  current
--       DESCRIPTION
-- "Number of queue sets"
   --     ::= { utsDot3Onu2CtcEntry 31 }

utsDot3Onu2CtcReset OBJECT-TYPE
SYNTAX  INTEGER
       {
         reset(1)           -- write only
       }
       MAX-ACCESS  read-write
       STATUS  current
       DESCRIPTION
"Reset ONU"
        ::= { utsDot3Onu2CtcEntry 32 }

utsDot3Onu2CtcRegisterStatus OBJECT-TYPE
SYNTAX  INTEGER
       {
         register(1),       -- accept ONU register request
         deregister(2)        -- do not accept ONU register request, but reserve the LLID
       }
       MAX-ACCESS  read-only
       STATUS  current
       DESCRIPTION
"NU register status"
        ::= { utsDot3Onu2CtcEntry 33 }

utsDot3Onu2CtcEncryptTraffic OBJECT-TYPE
SYNTAX  INTEGER
       {
          disable(1),
          ctc-churning(2),
          aES48(3)
  --      AES32(4)
       }
       MAX-ACCESS  read-write
       STATUS  current
       DESCRIPTION
"Enable the encryption for downstream traffic to specific ONU"
        ::= { utsDot3Onu2CtcEntry 34 }

utsDot3Onu2CtcFDBAgingTime OBJECT-TYPE
SYNTAX  INTEGER(0..1048)
       MAX-ACCESS  read-write
       STATUS  current
       DESCRIPTION
"FDB aging time"
        ::= { utsDot3Onu2CtcEntry 35 }

utsDot3Onu2CtcFDBClear OBJECT-TYPE
       SYNTAX  INTEGER
       {
         clearAll(1),
         clearUnicast(2),
         clearMulticast(3),
         clearDynamic(4)
       }
       MAX-ACCESS  read-write
       STATUS  current
       DESCRIPTION
"Clear ONU FDB entries"
        ::= { utsDot3Onu2CtcEntry 36}

utsDot3Onu2CtcAdmin OBJECT-TYPE
SYNTAX  INTEGER
       {
         up(1),
         down(2)
       }
       MAX-ACCESS  read-write
       STATUS  current
       DESCRIPTION
"Admin down/up control"
        ::= { utsDot3Onu2CtcEntry 37 }

utsDot3Onu2CtcRTT OBJECT-TYPE
SYNTAX  INTEGER
       MAX-ACCESS  read-only
       STATUS  current
       DESCRIPTION
"ONU round trip time"
        ::= { utsDot3Onu2CtcEntry 38 }

utsDot3Onu2CtcPVid OBJECT-TYPE
SYNTAX  INTEGER
       MAX-ACCESS  read-write
       STATUS  current
       DESCRIPTION
"PVID setting for this ONU in OLT PON"
        ::= { utsDot3Onu2CtcEntry 39 }

utsDot3Onu2CtcMaxMacAddress OBJECT-TYPE    --Add by Tomsong for NMS MRD 4.8.12, 2007.5.10
SYNTAX  INTEGER(0..100)
       MAX-ACCESS  read-write
       STATUS  current
       DESCRIPTION
"The Max Mac Address Number for a ONU in the PON port, 0 means no limit, default value is 0."
       DEFVAL {0}
        ::= { utsDot3Onu2CtcEntry 40 }

utsDot3Onu2CtcVoIPPortLock OBJECT-TYPE
SYNTAX  OCTET STRING(SIZE(8))
       MAX-ACCESS  read-write
       STATUS  current
       DESCRIPTION
"VoIP port lock or unlock, the bits of string from left to right delegate VOIP port 1 to 64,and for the each bit,
 1 means port activated or to activate the port, 0 means Port disactivated or to disactivate the port, the default
  value for each bit is 0."
        ::= { utsDot3Onu2CtcEntry 50 }

utsDot3Onu2CtcE1PortLock OBJECT-TYPE
SYNTAX  OCTET STRING(SIZE(1))
       MAX-ACCESS  read-write
       STATUS  current
       DESCRIPTION
"E1 port lock or unlock,the bits of string from left to right delegate E1 port 1 to 8,and for the each bit,
 1 means port activated or to activate the port, 0 means Port disactivated or to disactivate the port, the default
  value for each bit is 0."
        ::= { utsDot3Onu2CtcEntry 51 }

utsDot3Onu2CtcSwitchAdminStatus OBJECT-TYPE
SYNTAX  INTEGER
      {
       ready(1),
       notready(2)
      }
       MAX-ACCESS  read-only
       STATUS  current
       DESCRIPTION
"The admin status of ONU switch, if ready,EMS could  get and set for the ONU switch, if not-ready,wait for ONU switch ready."
        ::= { utsDot3Onu2CtcEntry 52 }

--utsDot3Onu2CtcOpticalPower OBJECT-TYPE
--SYNTAX INTEGER
--       MAX-ACCESS  read-only
--       STATUS  current
--       DESCRIPTION
--"The optical power of the ONU from the OLT side to measure."
--        ::= { utsDot3Onu2CtcEntry 53 }

utsDot3Onu2FastLeaveAbility OBJECT-TYPE
SYNTAX  OCTET STRING(SIZE(1))
       MAX-ACCESS  read-only
       STATUS  current
       DESCRIPTION
"Bitmap,bit0: 1 means support Non-Fast-Leave in CTC IGMP snooping, 0 means not support;
        bit1: 1 means support Fast-Leave in CTC IGMP snooping, 0 means not support;
        bit2: 1 means support Non-Fast-Leave in CTC Control Multicast, 0 means not support;
        bit3: 1 means support Fast-Leave in CTC Control Multicast, 0 means not support;
        bit4~bit7 keep zero,ignore when receive"
        ::= { utsDot3Onu2CtcEntry 54 }

utsDot3Onu2FastLeaveAdminControl  OBJECT-TYPE
SYNTAX INTEGER
      {
         disable(1),
         enable(2)
      }
       MAX-ACCESS  read-write
       STATUS  current
       DESCRIPTION
"To control the state the Fast-Leave in ONU"
        ::= { utsDot3Onu2CtcEntry 55 }

utsDot3Onu2EthernetPortAlarmReversion  OBJECT-TYPE
SYNTAX INTEGER
      {
         disable(1),
         enable(2)
      }
       MAX-ACCESS  read-write
       STATUS  current
       DESCRIPTION
"To control the Ethernet port alarm whether to use the alarm reversion, the default is disable."
        ::= { utsDot3Onu2CtcEntry 56 }

utsDot3Onu2MulticastFilter  OBJECT-TYPE
SYNTAX INTEGER
      {
         enable(1),
         disable(2)
      }
       MAX-ACCESS  read-write
       STATUS  current
       DESCRIPTION
"To control the multicast switch of PON in the ONU."
        ::= { utsDot3Onu2CtcEntry 58 }


-- ONU QoS

utsDot3Onu2QoSTable OBJECT-TYPE
SYNTAX  SEQUENCE OF UtsDot3Onu2QoSEntry
        MAX-ACCESS  not-accessible
        STATUS  current
        DESCRIPTION
"Table for dot3 ONU MIBs."
        ::= { utsDot3OnuObjects 3 }

utsDot3Onu2QoSEntry OBJECT-TYPE
SYNTAX  UtsDot3Onu2QoSEntry
       MAX-ACCESS  not-accessible
       STATUS  current
       DESCRIPTION
"An entry in the dot3 Onu MIBs table."
       INDEX  { utsDot3OnuQosModuleId,utsDot3OnuQosDeviceId,
                utsDot3OnuQosPortId,utsDot3OnuQosLogicalPortId }
       ::= { utsDot3Onu2QoSTable 1 }

UtsDot3Onu2QoSEntry ::=
       SEQUENCE {
               utsDot3OnuQosModuleId		   INTEGER,
               utsDot3OnuQosDeviceId           INTEGER,
               utsDot3OnuQosPortId			   INTEGER,
               utsDot3OnuQosLogicalPortId	   INTEGER,
               utsDot3OnuQoSMode               INTEGER,
               utsDot3OnuAclClassifiEnable     TruthValue,
               utsDot3OnuSchedulingMode        INTEGER,
               utsDot3OnuSchedulingWeightRatio INTEGER,
               utsDot3OnuDot1p2QueueMap        OCTET STRING,
               utsDot3OnuDscp2QueueMap         OCTET STRING,
               utsDot3OnuDefault802Dot1p       INTEGER,
               utsDot3OnuDefaultDscp           INTEGER,
               utsDot3OnuDefaultQueue          INTEGER,
               utsDot3OnuShaperAction          INTEGER,
               utsDot3OnuUpsPolicingAction     INTEGER,
               utsDot3OnuDownsPolicingAction   INTEGER
        }

utsDot3OnuQosModuleId OBJECT-TYPE
SYNTAX  INTEGER
       MAX-ACCESS  read-only
       STATUS  current
       DESCRIPTION
"A read only value to identifiy the OLT module id for the current ONU."
        ::= { utsDot3Onu2QoSEntry 1 }

utsDot3OnuQosDeviceId OBJECT-TYPE
SYNTAX  INTEGER
       MAX-ACCESS  read-only
       STATUS  current
       DESCRIPTION
"A read only value to identifiy the OLT device id for the current ONU."
        ::= { utsDot3Onu2QoSEntry 2 }

utsDot3OnuQosPortId OBJECT-TYPE
SYNTAX  INTEGER
       MAX-ACCESS  read-only
       STATUS  current
       DESCRIPTION
"A read only value to identifiy the OLT port id for the current ONU."
        ::= { utsDot3Onu2QoSEntry 3 }

utsDot3OnuQosLogicalPortId OBJECT-TYPE
SYNTAX  INTEGER
       MAX-ACCESS  read-only
       STATUS  current
       DESCRIPTION
"A read only value to identifiy the logical port id for the current ONU."
        ::= { utsDot3Onu2QoSEntry 4 }

utsDot3OnuQoSMode  OBJECT-TYPE
SYNTAX  INTEGER
       {
         dscp(1),
         dot1p(2)
       }
       MAX-ACCESS  read-write
       STATUS  current
       DESCRIPTION
"Enables either DSCP or 802.1p mode in the ONU to specify whether to
 use the DSCP value or 802.1p value for packet marking/queueing."
        ::= { utsDot3Onu2QoSEntry 5 }

utsDot3OnuAclClassifiEnable  OBJECT-TYPE
SYNTAX  TruthValue
       MAX-ACCESS  read-write
       STATUS  current
       DESCRIPTION
"Enables or disables ACL-based classification in the ONU.
 If ACL-based classification is turned off, the incoming
 packet's QoS marking will be used to decide the output queue,
 and the packet will not be remarked."
        ::= { utsDot3Onu2QoSEntry 6 }

utsDot3OnuSchedulingMode OBJECT-TYPE
SYNTAX  INTEGER               -- strict priority or WRR or hierarchical mode
       {
	       sp(1),
	       wrr(2),
	       hierarchical(3)
       }
       MAX-ACCESS  read-write
       STATUS  current
       DESCRIPTION
"Sets the output-queue scheduler policy at the ONU. The same policy applies to
 both upstream and downstream schedulers. The scheduling can be either
 strict-priority or Weighted-round-robin or Hierarchical queueing.
 For weighted round robin, an adjacent-weight ratio of 1, 2, 3, 4, 5, 6, 7
 or 8 can be configured.   (For example, if the weight ratio is 1,
 the weights for the eight queues are 1:1:1:1:1:1:1:1.  If the weight
 ratio is 2, the weights are 1:2:4:8:16:32:64:128.) For hierarchical
 queueing, queues 7 and 6 are in strict priority mode and the remaining
 queues are in weighted round robin mode."
        ::= { utsDot3Onu2QoSEntry 7 }

utsDot3OnuSchedulingWeightRatio OBJECT-TYPE
SYNTAX  INTEGER(1..7)
       MAX-ACCESS  read-write
       STATUS  current
       DESCRIPTION
"weight ratio in case of WRR mode, the weight
 ratio specifies the ratio of weights between two
 adjacent priority queues. We cannot assign
 arbitrary weights to different queues, we can
 only assign weight ratio of 1,2,3,4,5,6,7.
"
        ::= { utsDot3Onu2QoSEntry 8 }

utsDot3OnuDot1p2QueueMap  OBJECT-TYPE
SYNTAX  OCTET STRING(SIZE(8))
       MAX-ACCESS  read-write
       STATUS  current
       DESCRIPTION
"Sets the 802.1p to CoS output queue mapping table(3bits to 3 bits)
 at the ONU. This table is used when the global_qos_mode is set to
 802.1p and the classification-mode is turned off.
 This table specifies 802.1p-to-queue mapping in both upstream
 and downstream directions.
"
        ::= { utsDot3Onu2QoSEntry 9 }

utsDot3OnuDscp2QueueMap  OBJECT-TYPE
SYNTAX  OCTET STRING(SIZE(8))
       MAX-ACCESS  read-write
       STATUS  current
       DESCRIPTION
"Sets the DSCP(most-significant three bits) to CoS output queue
 mapping table(3bits to 3bits) at the ONU. This table is used
 when the global_qos_mode is set to DSCP and the classification-mode
 is turned off. This table specifies dscp-to-queue mapping in both
 upstream and downstream direction.
"
        ::= { utsDot3Onu2QoSEntry 10 }

utsDot3OnuDefault802Dot1p OBJECT-TYPE
       SYNTAX  INTEGER
       MAX-ACCESS  read-write
       STATUS  current
       DESCRIPTION
"Configures the default value for the 802.1p for packets at the ONU.
 In the 802.1p QoS mode, the default 802.1p and default CoS queue
 values are used for an unclassified packet (when classification
 mode is turned on) or for untagged packets (when classification
 mode is turned off).
"
        ::= { utsDot3Onu2QoSEntry 11 }

utsDot3OnuDefaultDscp OBJECT-TYPE
       SYNTAX  INTEGER
       MAX-ACCESS  read-write
       STATUS  current
       DESCRIPTION
"Configures the default value for the DSCP for packets at the ONU.
 In the DSCP QoS mode, the default DSCP and default CoS queue values
 are used for an unclassified packet (when classification mode is
 turned on) or for non-IP packets (when classification mode is turned off).
"
        ::= { utsDot3Onu2QoSEntry 12 }

utsDot3OnuDefaultQueue OBJECT-TYPE
       SYNTAX  INTEGER
       MAX-ACCESS  read-write
       STATUS  current
       DESCRIPTION
"Configures the default value for the CoS queue at the ONU.
"
        ::= { utsDot3Onu2QoSEntry 13 }

utsDot3OnuShaperAction OBJECT-TYPE
       SYNTAX  INTEGER
       {
          disable(1),
          cir(2),
          pir(3)
       }
       MAX-ACCESS  read-write
       STATUS  current
       DESCRIPTION
"Sets (for a particular ONU's traffic) the downstream traffic-shaping
 configuration at the OLT in terms of whether to shape
 downstream ONU traffic according to its CIR or PIR
 rates, specified in the ONU's traffic profile.
 The ONU to be shaped is specified by the OLT device
 id and its LLID-based logical port with which the ONU
 is associated. Downstream traffic is shaped by a tokenbucket
 shaper to smoothen the traffic and prevent packet drops downstream
 at the ONU due to its limited buffer space.
"
        ::= { utsDot3Onu2QoSEntry 14 }

utsDot3OnuUpsPolicingAction OBJECT-TYPE
       SYNTAX  INTEGER
       {
          disable(1),             -- disable policing
          mark-cir(2),            -- Mark traffic once it exceeds its CIR
          mark-pir(3),            -- Mark traffic once it exceeds its CIR
          mark-cir-drop-pir(4),   -- Mark traffic once it exceeds its CIR and drop once it exceeds its PIR
          drop-cir(5),            -- Drop traffic once it exceeds its CIR
          drop-pir(6)             -- Drop traffic once it exceeds its PIR
       }
       MAX-ACCESS  read-write
       STATUS  current
       DESCRIPTION
"Sets (for a particular ONU's traffic) the upstream
 traffic-policing action at the OLT, in terms of whether the policer
 should mark and/or drop packets above the CIR/PIR rates specified
 in the ONU's traffic profile.
"
        ::= { utsDot3Onu2QoSEntry 16 }

utsDot3OnuDownsPolicingAction OBJECT-TYPE
       SYNTAX  INTEGER
       {
          disable(1),             -- disable policing
          mark-cir(2),            -- Mark traffic once it exceeds its CIR
          mark-pir(3),            -- Mark traffic once it exceeds its CIR
          mark-cir-drop-pir(4),   -- Mark traffic once it exceeds its CIR and drop once it exceeds its PIR
          drop-cir(5),            -- Drop traffic once it exceeds its CIR
          drop-pir(6)             -- Drop traffic once it exceeds its PIR
       }
       MAX-ACCESS  read-write
       STATUS  current
       DESCRIPTION
"Sets (for a particular ONU's traffic) the downstream
 traffic-policing action at the OLT, in terms of whether the policer
 should mark and/or drop packets above the CIR/PIR rates specified
 in the ONU's traffic profile.
"
        ::= { utsDot3Onu2QoSEntry 17 }

-- ONU traffic Classification rule

utsDot3Onu2ClassifiRuleTable OBJECT-TYPE
SYNTAX  SEQUENCE OF UtsDot3Onu2ClassifiRuleEntry
        MAX-ACCESS  not-accessible
        STATUS  current
        DESCRIPTION
"Table for dot3 ONU MIBs."
        ::= { utsDot3OnuObjects 4 }

utsDot3Onu2ClassifiRuleEntry OBJECT-TYPE
SYNTAX  UtsDot3Onu2ClassifiRuleEntry
       MAX-ACCESS  not-accessible
       STATUS  current
       DESCRIPTION
"An entry in the dot3 Onu MIBs table."
       INDEX  { utsDot3OnuClassifiModuleId,utsDot3OnuClassifiDeviceId,
                utsDot3OnuClassifiPortId, utsDot3OnuClassifiLogicalPortId }
       ::= { utsDot3Onu2ClassifiRuleTable 1 }

UtsDot3Onu2ClassifiRuleEntry ::=
       SEQUENCE {
               utsDot3OnuClassifiModuleId		     INTEGER,
               utsDot3OnuClassifiDeviceId            INTEGER,
               utsDot3OnuClassifiPortId	             INTEGER,
               utsDot3OnuClassifiLogicalPortId       INTEGER,
               utsDot3OnuClassifiRuleIndex           INTEGER,
               utsDot3OnuClassifiRuleEnable          TruthValue,
               utsDot3OnuClassifiRuleProtId          INTEGER,
               utsDot3OnuClassifiRuleUniPort         INTEGER,
               utsDot3OnuClassifiRuleL4SrcPortStart  INTEGER,
               utsDot3OnuClassifiRuleL4SrcPortEnd    INTEGER,
               utsDot3OnuClassifiRuleL4DstPortStart  INTEGER,
               utsDot3OnuClassifiRuleL4DstPortEnd    INTEGER,
               utsDot3OnuClassifiRuleDscp            INTEGER,
               utsDot3OnuClassifiRule802Dot1p        INTEGER,
               utsDot3OnuClassifiRuleCosQueue        INTEGER
        }

utsDot3OnuClassifiModuleId OBJECT-TYPE
SYNTAX  INTEGER
       MAX-ACCESS  read-only
       STATUS  current
       DESCRIPTION
"A read only value to identifiy the OLT module id for the current ONU."
        ::= { utsDot3Onu2ClassifiRuleEntry 1 }

utsDot3OnuClassifiDeviceId OBJECT-TYPE
SYNTAX  INTEGER
       MAX-ACCESS  read-only
       STATUS  current
       DESCRIPTION
"A read only value to identifiy the OLT device id for the current ONU."
        ::= { utsDot3Onu2ClassifiRuleEntry 2 }

utsDot3OnuClassifiPortId OBJECT-TYPE
SYNTAX  INTEGER
       MAX-ACCESS  read-only
       STATUS  current
       DESCRIPTION
"A read only value to identifiy the OLT port id for the current ONU."
        ::= { utsDot3Onu2ClassifiRuleEntry 3 }

utsDot3OnuClassifiLogicalPortId OBJECT-TYPE
SYNTAX  INTEGER
       MAX-ACCESS  read-only
       STATUS  current
       DESCRIPTION
"A read only value to identifiy the logical port id for the current ONU."
        ::= { utsDot3Onu2ClassifiRuleEntry 4 }

utsDot3OnuClassifiRuleIndex OBJECT-TYPE
SYNTAX  INTEGER
       MAX-ACCESS  read-create
       STATUS  current
       DESCRIPTION
"ACL entry index(from 0 to 7)"
        ::= { utsDot3Onu2ClassifiRuleEntry 5 }

utsDot3OnuClassifiRuleEnable OBJECT-TYPE
SYNTAX  TruthValue
       MAX-ACCESS  read-create
       STATUS  current
       DESCRIPTION
"Whether Classifier rule is valid or not"
        ::= { utsDot3Onu2ClassifiRuleEntry 6 }

utsDot3OnuClassifiRuleProtId OBJECT-TYPE
SYNTAX  INTEGER
  	   {
  	    tcp(1),  -- incoming Protocol id field must be TCP
  	    udp(2),  -- incoming Protocol id field must be UDP
  	    any(3)   -- incoming Protocol id field can be either TCP or UDP
	   }
       MAX-ACCESS  read-create
       STATUS  current
       DESCRIPTION
"Protocol id enum - TCP, UDP or ANY"
        ::= { utsDot3Onu2ClassifiRuleEntry 7 }

utsDot3OnuClassifiRuleUniPort OBJECT-TYPE
SYNTAX  INTEGER         -- Input UNI port
       MAX-ACCESS  read-create
       STATUS  current
       DESCRIPTION
"Input UNI port"
        ::= { utsDot3Onu2ClassifiRuleEntry 8 }

utsDot3OnuClassifiRuleL4SrcPortStart OBJECT-TYPE
SYNTAX  INTEGER
       MAX-ACCESS  read-create
       STATUS  current
       DESCRIPTION
"TCP/UDP Source Port start"
        ::= { utsDot3Onu2ClassifiRuleEntry 9 }

utsDot3OnuClassifiRuleL4SrcPortEnd OBJECT-TYPE
SYNTAX  INTEGER
       MAX-ACCESS  read-create
       STATUS  current
       DESCRIPTION
"TCP/UDP Source Port end"
        ::= { utsDot3Onu2ClassifiRuleEntry 10 }

utsDot3OnuClassifiRuleL4DstPortStart OBJECT-TYPE
SYNTAX  INTEGER
       MAX-ACCESS  read-create
       STATUS  current
       DESCRIPTION
"TCP/UDP destination Port start"
        ::= { utsDot3Onu2ClassifiRuleEntry 11 }

utsDot3OnuClassifiRuleL4DstPortEnd OBJECT-TYPE
SYNTAX  INTEGER
       MAX-ACCESS  read-create
       STATUS  current
       DESCRIPTION
"TCP/UDP destination Port end"
        ::= { utsDot3Onu2ClassifiRuleEntry 12 }

utsDot3OnuClassifiRuleDscp OBJECT-TYPE
SYNTAX  INTEGER
       MAX-ACCESS  read-create
       STATUS  current
       DESCRIPTION
"Outgoing DSCP value (0-64). This field is
 valid when the global QoS mode is DSCP."
        ::= { utsDot3Onu2ClassifiRuleEntry 13 }

utsDot3OnuClassifiRule802Dot1p OBJECT-TYPE
SYNTAX  INTEGER
       MAX-ACCESS  read-create
       STATUS  current
       DESCRIPTION
"Outgoing 802.1p value (0-7). This field is
 valid when the global QoS mode is 802.1p "
        ::= { utsDot3Onu2ClassifiRuleEntry 14 }

utsDot3OnuClassifiRuleCosQueue OBJECT-TYPE
SYNTAX  INTEGER
       MAX-ACCESS  read-create
       STATUS  current
       DESCRIPTION
"Output CoS Queue number (queue# 0 to 7)"
        ::= { utsDot3Onu2ClassifiRuleEntry 15 }

-- ONU Ethernet port configuration

utsDot3Onu2CtcEtherPortTable OBJECT-TYPE
SYNTAX  SEQUENCE OF UtsDot3Onu2CtcEtherPortEntry
        MAX-ACCESS  not-accessible
        STATUS  current
        DESCRIPTION
"Table for dot3 ONU MIBs."
        ::= { utsDot3OnuObjects 11 }

utsDot3Onu2CtcEtherPortEntry OBJECT-TYPE
SYNTAX  UtsDot3Onu2CtcEtherPortEntry
       MAX-ACCESS  not-accessible
       STATUS  current
       DESCRIPTION
"An entry in the dot3 Onu MIBs table."
       INDEX  { utsDot3OnuEtherPortModuleId,utsDot3OnuEtherPortDeviceId,utsDot3OnuEtherPortPortId,
                utsDot3OnuEtherPortLogicalPortId,utsDot3OnuEtherPortIndex }
       ::= { utsDot3Onu2CtcEtherPortTable 1 }

UtsDot3Onu2CtcEtherPortEntry ::=
       SEQUENCE {
               utsDot3OnuEtherPortModuleId	         INTEGER,
               utsDot3OnuEtherPortDeviceId           INTEGER,
               utsDot3OnuEtherPortPortId	         INTEGER,
               utsDot3OnuEtherPortLogicalPortId	     INTEGER,
               utsDot3OnuEtherPortIndex              INTEGER,

               utsDot3OnuEtherPortPhyAdminState      INTEGER,
               utsDot3OnuEtherPortPhyAdminCtrl       INTEGER,

               utsDot3OnuEtherPortAutoNegAdminSt     INTEGER,
               utsDot3OnuEtherPortAutoNegLocTec      OCTET STRING,
               utsDot3OnuEtherPortAutoNegAbility     OCTET STRING,
               utsDot3OnuEtherPortAutoNegRestart     INTEGER,
               utsDot3OnuEtherPortAutoNegAdminCtrl   INTEGER,

               utsDot3OnuEtherPortLinkState          INTEGER,
			   utsDot3OnuEtherPortPause              INTEGER,

			   utsDot3OnuEtherPortPolicingEnable     TruthValue,
			   utsDot3OnuEtherPortPolicingCIR        INTEGER,
			   utsDot3OnuEtherPortPolicingCBS        INTEGER,
			   utsDot3OnuEtherPortPolicingEBS        INTEGER,

			   utsDot3OnuEtherPortVlanMode           INTEGER,
			   utsDot3OnuEtherPortVlanTPID           INTEGER,
			   utsDot3OnuEtherPortVlanTag            INTEGER,
--			   utsDot3OnuEtherPortVlanDefTag         INTEGER,
			   utsDot3OnuEtherPortVlanTranslation    OCTET STRING,

			   utsDot3OnuEtherPortMaxMVlanNum        INTEGER,
			   utsDot3OnuEtherPortMVlanList          OCTET STRING,
			   utsDot3OnuEtherPortMVlanClear         INTEGER,

			   utsDot3OnuEtherPortMaxMcGroupNum      INTEGER,
			   utsDot3OnuEtherPortMcTagStripe     INTEGER,

			   utsDot3OnuEtherPortClassifiRuleClear  INTEGER,

			   utsDot3OnuEtherPortDSPolicingEnable     TruthValue,
			   utsDot3OnuEtherPortDSPolicingCIR        INTEGER,
			   utsDot3OnuEtherPortDSPolicingPIR        INTEGER,
			   utsDot3OnuEtherPortVlanNTo1Translation  OCTET STRING


        }

utsDot3OnuEtherPortModuleId OBJECT-TYPE
SYNTAX  INTEGER
       MAX-ACCESS  read-only
       STATUS  current
       DESCRIPTION
"A read only value to identifiy the OLT module id for the current ONU."
        ::= { utsDot3Onu2CtcEtherPortEntry 1 }

utsDot3OnuEtherPortDeviceId OBJECT-TYPE
SYNTAX  INTEGER
       MAX-ACCESS  read-only
       STATUS  current
       DESCRIPTION
"A read only value to identifiy the OLT device id for the current ONU."
        ::= { utsDot3Onu2CtcEtherPortEntry 2 }

utsDot3OnuEtherPortPortId OBJECT-TYPE
SYNTAX  INTEGER
       MAX-ACCESS  read-only
       STATUS  current
       DESCRIPTION
"A read only value to identifiy the OLT port id for the current ONU."
        ::= { utsDot3Onu2CtcEtherPortEntry 3 }

utsDot3OnuEtherPortLogicalPortId OBJECT-TYPE
SYNTAX  INTEGER
       MAX-ACCESS  read-only
       STATUS  current
       DESCRIPTION
"A read only value to identifiy the logical port id for the current ONU."
        ::= { utsDot3Onu2CtcEtherPortEntry 4 }

utsDot3OnuEtherPortIndex OBJECT-TYPE
SYNTAX  INTEGER
       MAX-ACCESS  read-only
       STATUS  current
       DESCRIPTION
"ACL entry index(from 0 to 7)"
        ::= { utsDot3Onu2CtcEtherPortEntry 5 }

utsDot3OnuEtherPortPhyAdminState OBJECT-TYPE
SYNTAX  INTEGER
		{
		  disabled(1),
		  enabled(2)
		}
       MAX-ACCESS  read-only
       STATUS  current
       DESCRIPTION
"Phy admin status"
        ::= { utsDot3Onu2CtcEtherPortEntry 6 }

utsDot3OnuEtherPortPhyAdminCtrl OBJECT-TYPE
SYNTAX  INTEGER
		{
		  deactivate(1),   -- write only?
		  activate(2)      -- write only?
		}
       MAX-ACCESS  read-write
       STATUS  current
       DESCRIPTION
"Phy admin control"
        ::= { utsDot3Onu2CtcEtherPortEntry 7 }

utsDot3OnuEtherPortAutoNegAdminSt OBJECT-TYPE
SYNTAX  INTEGER
		{
		  disabled(1),
		  enabled(2)
		}
       MAX-ACCESS  read-only
       STATUS  current
       DESCRIPTION
"Auto negotiation admin state"
        ::= { utsDot3Onu2CtcEtherPortEntry 8 }

utsDot3OnuEtherPortAutoNegLocTec OBJECT-TYPE
SYNTAX OCTET STRING(SIZE(3..8))
--		{
--		  global(1),          global
--		  other(2),
--		  unknown(3),
--		  baseT10(14),        10BASE-T
--		  baseTFD10(142),     10BASE-TFD
--		  baseT4100(23),      100BASE-T4
--		  baseTx100(25),      100BASE-TX
--		  baseTxFD100(252),   100BASE-TXFD
--		  baseT2100(32),      100BASE-T2
--		  baseT2FD100(322),   100BASE-T2FD
--		  baseX1000(36),      1000BASE-X
--		  baseXFD1000(362),   1000BASE-XFD
--		  baseT1000(40),      1000BASE-T
--		  baseTFD1000(402),   1000BASE-TFD");
--        fdx_pause(312),
--        fdx_apause(313),
--        fdx_spause(314),
--        fdx_bpause(315),
--        rem_fault1(37)
--        rem_fault2(372)
--        isoethernet(8029)
--		  na(1000)		      NA
--		}
       MAX-ACCESS  read-only
       STATUS  current
       DESCRIPTION
"Auto negotiation local technoloty ability"
        ::= { utsDot3Onu2CtcEtherPortEntry 9 }

utsDot3OnuEtherPortAutoNegAbility OBJECT-TYPE
SYNTAX OCTET STRING(SIZE(3..8))
--		{
--		  global(1),          global
--		  other(2),
--		  unknown(3),
--		  baseT10(14),        10BASE-T
--		  baseTFD10(142),     10BASE-TFD
--		  baseT4100(23),      100BASE-T4
--		  baseTx100(25),      100BASE-TX
--		  baseTxFD100(252),   100BASE-TXFD
--		  baseT2100(32),      100BASE-T2
--		  baseT2FD100(322),   100BASE-T2FD
--		  baseX1000(36),      1000BASE-X
--		  baseXFD1000(362),   1000BASE-XFD
--		  baseT1000(40),      1000BASE-T
--		  baseTFD1000(402),   1000BASE-TFD");
--        fdx_pause(312),
--        fdx_apause(313),
--        fdx_spause(314),
--        fdx_bpause(315),
--        rem_fault1(37)
--        rem_fault2(372)
--        isoethernet(8029)
--		  na(1000)		      NA
--		}
       MAX-ACCESS  read-only
       STATUS  current
       DESCRIPTION
"Auto negotiation ability notification"
        ::= { utsDot3Onu2CtcEtherPortEntry 10 }

utsDot3OnuEtherPortAutoNegRestart OBJECT-TYPE
SYNTAX  INTEGER
		{
		  restart(1)  -- write only
		}
       MAX-ACCESS  read-write
       STATUS  current
       DESCRIPTION
"Force restart auto negotiation"
        ::= { utsDot3Onu2CtcEtherPortEntry 11 }

utsDot3OnuEtherPortAutoNegAdminCtrl OBJECT-TYPE
SYNTAX  INTEGER
		{
		  deactivate(1),  --
		  activate(2)    --
		}
       MAX-ACCESS  read-write
       STATUS  current
       DESCRIPTION
"Enable or disable phy auto negotiation function"
        ::= { utsDot3Onu2CtcEtherPortEntry 12 }

utsDot3OnuEtherPortLinkState OBJECT-TYPE
SYNTAX  INTEGER
	   {
	      down(0),
	      up(1)
	   }
       MAX-ACCESS  read-only
       STATUS  current
       DESCRIPTION
"ACL entry index(from 0 to 7)"
        ::= { utsDot3Onu2CtcEtherPortEntry 30 }

utsDot3OnuEtherPortPause OBJECT-TYPE
SYNTAX  INTEGER
	   {
	      disable(1),     -- Flow control is disabled
	      enable(2)       -- Flow control is enabled
	   }
       MAX-ACCESS  read-write
       STATUS  current
       DESCRIPTION
"UNI port flow control function"
        ::= { utsDot3Onu2CtcEtherPortEntry 31 }


utsDot3OnuEtherPortPolicingEnable OBJECT-TYPE
SYNTAX  TruthValue
       MAX-ACCESS  read-write
       STATUS  current
       DESCRIPTION
"Enable or disable ingress policing function"
        ::= { utsDot3Onu2CtcEtherPortEntry 32 }

utsDot3OnuEtherPortPolicingCIR OBJECT-TYPE
SYNTAX  INTEGER                  -- Kbps
       MAX-ACCESS  read-write
       STATUS  current
       DESCRIPTION
"Ingress CIR."
        ::= { utsDot3Onu2CtcEtherPortEntry 33 }

utsDot3OnuEtherPortPolicingCBS OBJECT-TYPE
SYNTAX  INTEGER                  -- byte
       MAX-ACCESS  read-write
       STATUS  current
       DESCRIPTION
"Port policing bucket depth. Only is valid when the port policing is enabled."
        ::= { utsDot3Onu2CtcEtherPortEntry 34 }

utsDot3OnuEtherPortPolicingEBS OBJECT-TYPE
SYNTAX  INTEGER                 -- byte
       MAX-ACCESS  read-write
       STATUS  current
       DESCRIPTION
"Port policing extra burst size. Only is valid when the port policing is enabled."
        ::= { utsDot3Onu2CtcEtherPortEntry 35 }

utsDot3OnuEtherPortVlanMode OBJECT-TYPE
SYNTAX  INTEGER
	   {
	     transparent(1),    --  transparent mode
	     tag(2),            --  tag         mode
	     translation(3),    --  translation mode
	     vlanStacking(4)    --  VLAN stacking mode
	   }
       MAX-ACCESS  read-write
       STATUS  current
       DESCRIPTION
"Ether port VLAN mode"
        ::= { utsDot3Onu2CtcEtherPortEntry 36 }

utsDot3OnuEtherPortVlanTPID OBJECT-TYPE
SYNTAX  INTEGER               --defult 0x88a8
       MAX-ACCESS  read-write
       STATUS  current
       DESCRIPTION
"VLAN TPID under VLAN tag mode"
        ::= { utsDot3Onu2CtcEtherPortEntry 37 }

utsDot3OnuEtherPortVlanTag OBJECT-TYPE
SYNTAX  INTEGER(1..4094)               --
       MAX-ACCESS  read-write
       STATUS  current
       DESCRIPTION
"VLAN tag under VLAN tag mode, or Default VLAN tag under VLAN translation/stacking mode"
        ::= { utsDot3Onu2CtcEtherPortEntry 38 }

utsDot3OnuEtherPortVlanTranslation OBJECT-TYPE
SYNTAX  OCTET STRING(SIZE(64))     --0x 0123[in-tpid 1] 4567[in-tag 1] 89ab[out-tpid 1] cdef[out-tag 1] 0x0123[in-tpid 2] 4567[in-tag 2] 89ab[out-tpid 2] cdef[out-tag 2]...
       MAX-ACCESS  read-write
       STATUS  current
       DESCRIPTION
"VLAN translation entry or VLAN stacking entry, MAX 8 entry, this is only for 1:1 mode."
        ::= { utsDot3Onu2CtcEtherPortEntry 40 }

utsDot3OnuEtherPortMaxMVlanNum OBJECT-TYPE
SYNTAX INTEGER
       MAX-ACCESS  read-only
       STATUS  current
       DESCRIPTION
"Max multicast VLAN number"
        ::= { utsDot3Onu2CtcEtherPortEntry 41 }

utsDot3OnuEtherPortMVlanList OBJECT-TYPE
SYNTAX OCTET STRING(SIZE(8..128))  -- 0x01 23[MVlan 1] 45 67[MVlan 2] 89 ab[MVlan 3]
       MAX-ACCESS  read-write
       STATUS  current
       DESCRIPTION
"Multicast VLAN list for this ONU UNI port, the minimal multicast
 VLAN number could be displayed is 4 and the max number is 32."
        ::= { utsDot3Onu2CtcEtherPortEntry 42 }

utsDot3OnuEtherPortMVlanClear OBJECT-TYPE
SYNTAX INTEGER
 	   {
 	      clear(1) -- write only
	   }
       MAX-ACCESS  read-write
       STATUS  current
       DESCRIPTION
"Clear the multicast VLAN of the port"
        ::= { utsDot3Onu2CtcEtherPortEntry 43 }

utsDot3OnuEtherPortMaxMcGroupNum OBJECT-TYPE
SYNTAX INTEGER
       MAX-ACCESS  read-write
       STATUS  current
       DESCRIPTION
"Max multicast group number, the range should be from 4 to 1024."
        ::= { utsDot3Onu2CtcEtherPortEntry 44 }

utsDot3OnuEtherPortMcTagStripe OBJECT-TYPE
SYNTAX INTEGER
	   {
	      enable(1),
	      disable(2)
	   }
       MAX-ACCESS  read-write
       STATUS  current
       DESCRIPTION
"Multicast VLAN tag stripe or not"
        ::= { utsDot3Onu2CtcEtherPortEntry 45 }

utsDot3OnuEtherPortClassifiRuleClear OBJECT-TYPE
SYNTAX INTEGER
 	   {
 	      clear(1) -- write only
	   }
       MAX-ACCESS  read-write
       STATUS  current
       DESCRIPTION
"Clear the classification rule of the port"
        ::= { utsDot3Onu2CtcEtherPortEntry 46 }

utsDot3OnuEtherPortDSPolicingEnable OBJECT-TYPE
SYNTAX  TruthValue
       MAX-ACCESS  read-write
       STATUS  current
       DESCRIPTION
"Enable or disable egress policing function"
        ::= { utsDot3Onu2CtcEtherPortEntry 47 }

utsDot3OnuEtherPortDSPolicingCIR OBJECT-TYPE
SYNTAX  INTEGER                         --kbps
       MAX-ACCESS  read-write
       STATUS  current
       DESCRIPTION
"Egress CIR, value from 0x0 to 0xffffffff, Kbps."
        ::= { utsDot3Onu2CtcEtherPortEntry 48 }

utsDot3OnuEtherPortDSPolicingPIR OBJECT-TYPE
SYNTAX  INTEGER                 -- kbps
       MAX-ACCESS  read-write
       STATUS  current
       DESCRIPTION
"Egress PIR, value from 0x0 to 0xffffffff, Kbps."
        ::= { utsDot3Onu2CtcEtherPortEntry 49 }

utsDot3OnuEtherPortVlanNTo1Translation OBJECT-TYPE
SYNTAX  OCTET STRING(SIZE(64))     --0x 0123[in-tpid 1] 4567[in-tag 1] 89ab[out-tpid 1] cdef[out-tag 1] 0x0123[in-tpid 2] 4567[in-tag 2] 89ab[out-tpid 2] cdef[out-tag 2]...
       MAX-ACCESS  read-write
       STATUS  current
       DESCRIPTION
"VLAN translation entry or VLAN stacking entry, MAX 8 entry, this is only for N:1 mode."
        ::= { utsDot3Onu2CtcEtherPortEntry 50 }


-- ONU Ethernet port classification configuration

utsDot3Onu2CtcEtherPortClassifiTable OBJECT-TYPE
SYNTAX  SEQUENCE OF UtsDot3Onu2CtcEtherPortClassifiEntry
        MAX-ACCESS  not-accessible
        STATUS  current
        DESCRIPTION
"Table for dot3 ONU MIBs."
        ::= { utsDot3OnuObjects 12 }

utsDot3Onu2CtcEtherPortClassifiEntry OBJECT-TYPE
SYNTAX  UtsDot3Onu2CtcEtherPortClassifiEntry
       MAX-ACCESS  not-accessible
       STATUS  current
       DESCRIPTION
"An entry in the dot3 Onu MIBs table."
       INDEX  { utsDot3OnuEthPClassifiModuleId,utsDot3OnuEthPClassifiDeviceId,
                utsDot3OnuEthPClassifiPortId,utsDot3OnuEthPClassifiLogicalPortId,
                utsDot3OnuEthPClassifiPortIndex,utsDot3OnuEthPClassifiRuleIndex}
       ::= { utsDot3Onu2CtcEtherPortClassifiTable 1 }

UtsDot3Onu2CtcEtherPortClassifiEntry ::=
       SEQUENCE {
               utsDot3OnuEthPClassifiModuleId        INTEGER,
               utsDot3OnuEthPClassifiDeviceId        INTEGER,
               utsDot3OnuEthPClassifiPortId		     INTEGER,
               utsDot3OnuEthPClassifiLogicalPortId   INTEGER,
               utsDot3OnuEthPClassifiPortIndex       INTEGER,
               utsDot3OnuEthPClassifiRuleIndex       INTEGER,
               utsDot3OnuClassifiPrecedence          INTEGER,
               utsDot3OnuClassifiQueueMapped         INTEGER,
               utsDot3OnuClassifiEtherPriMark        INTEGER,
               utsDot3OnuClassifiFSelect1            INTEGER,
               utsDot3OnuClassifiFMatch1             OCTET STRING,
               utsDot3OnuClassifiOperator1           INTEGER,

               utsDot3OnuClassifiFSelect2            INTEGER,
               utsDot3OnuClassifiFMatch2             OCTET STRING,
               utsDot3OnuClassifiOperator2           INTEGER,

               utsDot3OnuClassifiFSelect3            INTEGER,
               utsDot3OnuClassifiFMatch3             OCTET STRING,
               utsDot3OnuClassifiOperator3           INTEGER,

               utsDot3OnuClassifiRowStatus           RowStatus
        }

utsDot3OnuEthPClassifiModuleId OBJECT-TYPE
SYNTAX  INTEGER
       MAX-ACCESS  not-accessible
       STATUS  current
       DESCRIPTION
"A read only value to identifiy the OLT module id for the current ONU."
        ::= { utsDot3Onu2CtcEtherPortClassifiEntry 1 }

utsDot3OnuEthPClassifiDeviceId OBJECT-TYPE
SYNTAX  INTEGER
       MAX-ACCESS  not-accessible
       STATUS  current
       DESCRIPTION
"A read only value to identifiy the OLT device id for the current ONU."
        ::= { utsDot3Onu2CtcEtherPortClassifiEntry 2 }

utsDot3OnuEthPClassifiPortId OBJECT-TYPE
SYNTAX  INTEGER
       MAX-ACCESS  not-accessible
       STATUS  current
       DESCRIPTION
"A read only value to identifiy the OLT port id for the current ONU."
        ::= { utsDot3Onu2CtcEtherPortClassifiEntry 3 }

utsDot3OnuEthPClassifiLogicalPortId OBJECT-TYPE
SYNTAX  INTEGER
       MAX-ACCESS  not-accessible
       STATUS  current
       DESCRIPTION
"A read only value to identifiy the logical port id for the current ONU."
        ::= { utsDot3Onu2CtcEtherPortClassifiEntry 4 }

utsDot3OnuEthPClassifiPortIndex OBJECT-TYPE
SYNTAX  INTEGER
       MAX-ACCESS  not-accessible
       STATUS  current
       DESCRIPTION
"ONU Ethernet port index"
        ::= { utsDot3Onu2CtcEtherPortClassifiEntry 5 }

utsDot3OnuEthPClassifiRuleIndex OBJECT-TYPE
SYNTAX  INTEGER(1..8)
       MAX-ACCESS  not-accessible
       STATUS  current
       DESCRIPTION
"ONU Ethernet port classification rule"
        ::= { utsDot3Onu2CtcEtherPortClassifiEntry 6 }

utsDot3OnuClassifiPrecedence OBJECT-TYPE
SYNTAX  INTEGER(1..8)
       MAX-ACCESS  read-create
       STATUS  current
       DESCRIPTION
"Phy admin status"
        ::= { utsDot3Onu2CtcEtherPortClassifiEntry 7 }

utsDot3OnuClassifiQueueMapped OBJECT-TYPE
SYNTAX  INTEGER(1..8)
       MAX-ACCESS  read-create
       STATUS  current
       DESCRIPTION
"Queue mapped"
        ::= { utsDot3Onu2CtcEtherPortClassifiEntry 8 }

utsDot3OnuClassifiEtherPriMark OBJECT-TYPE
SYNTAX  INTEGER(0..255)      -- 0..7, 255: 255 means no mark
       MAX-ACCESS  read-create
       STATUS  current
       DESCRIPTION
"Queue mapped"
        ::= { utsDot3Onu2CtcEtherPortClassifiEntry 9 }

utsDot3OnuClassifiFSelect1 OBJECT-TYPE
SYNTAX  INTEGER(0..11)        --
       MAX-ACCESS  read-create
       STATUS  current
       DESCRIPTION
"Field select for entry 1"
        ::= { utsDot3Onu2CtcEtherPortClassifiEntry 11 }

utsDot3OnuClassifiFMatch1 OBJECT-TYPE
SYNTAX  OCTET STRING(SIZE(6))   -- 0x fe dc ba 98 76 54 32 10
       MAX-ACCESS  read-create
       STATUS  current
       DESCRIPTION
"Match value for field 1 in entry 1"
        ::= { utsDot3Onu2CtcEtherPortClassifiEntry 12 }

utsDot3OnuClassifiOperator1 OBJECT-TYPE
SYNTAX  INTEGER(0..7)   --
       MAX-ACCESS  read-create
       STATUS  current
       DESCRIPTION
"Validation operator for entry 1"
        ::= { utsDot3Onu2CtcEtherPortClassifiEntry 13 }

utsDot3OnuClassifiFSelect2 OBJECT-TYPE
SYNTAX  INTEGER(0..11)        --
       MAX-ACCESS  read-create
       STATUS  current
       DESCRIPTION
"Field select for entry 1"
        ::= { utsDot3Onu2CtcEtherPortClassifiEntry 21 }

utsDot3OnuClassifiFMatch2 OBJECT-TYPE
SYNTAX  OCTET STRING(SIZE(6))   -- 0x fe dc ba 98 76 54 32 10
       MAX-ACCESS  read-create
       STATUS  current
       DESCRIPTION
"Match value for field 1 in entry 1"
        ::= { utsDot3Onu2CtcEtherPortClassifiEntry 22 }

utsDot3OnuClassifiOperator2 OBJECT-TYPE
SYNTAX  INTEGER(0..7)   --
       MAX-ACCESS  read-create
       STATUS  current
       DESCRIPTION
"Validation operator for entry 1"
        ::= { utsDot3Onu2CtcEtherPortClassifiEntry 23 }

utsDot3OnuClassifiFSelect3 OBJECT-TYPE
SYNTAX  INTEGER(0..11)        --
       MAX-ACCESS  read-create
       STATUS  current
       DESCRIPTION
"Field select for entry 1"
        ::= { utsDot3Onu2CtcEtherPortClassifiEntry 31 }

utsDot3OnuClassifiFMatch3 OBJECT-TYPE
SYNTAX  OCTET STRING(SIZE(6))   -- 0x fe dc ba 98 76 54 32 10
       MAX-ACCESS  read-create
       STATUS  current
       DESCRIPTION
"Match value for field 1 in entry 1"
        ::= { utsDot3Onu2CtcEtherPortClassifiEntry 32 }

utsDot3OnuClassifiOperator3 OBJECT-TYPE
SYNTAX  INTEGER(0..7)   --
       MAX-ACCESS  read-create
       STATUS  current
       DESCRIPTION
"Validation operator for entry 1"
        ::= { utsDot3Onu2CtcEtherPortClassifiEntry 33 }

utsDot3OnuClassifiRowStatus OBJECT-TYPE
SYNTAX  RowStatus
       MAX-ACCESS  read-create
       STATUS  current
       DESCRIPTION
"Row status"
        ::= { utsDot3Onu2CtcEtherPortClassifiEntry 100 }

-- ONU multicast control configuration

utsDot3Onu2CtcMulticastCtrlTable OBJECT-TYPE
SYNTAX  SEQUENCE OF UtsDot3Onu2CtcMulticastCtrlEntry
        MAX-ACCESS  not-accessible
        STATUS  current
        DESCRIPTION
"Table for dot3 ONU multicast control MIBs."
        ::= { utsDot3OnuObjects 13 }

utsDot3Onu2CtcMulticastCtrlEntry OBJECT-TYPE
SYNTAX  UtsDot3Onu2CtcMulticastCtrlEntry
       MAX-ACCESS  not-accessible
       STATUS  current
       DESCRIPTION
"An entry in the dot3 Onu multicast control MIBs table."
       INDEX  { utsDot3Onu2MCtrlModuleId,utsDot3Onu2MCtrlDeviceId,
                utsDot3Onu2MCtrlPortId,utsDot3Onu2MCtrlLogicalPortId,
                utsDot3Onu2MCastEntryIndex}
       ::= { utsDot3Onu2CtcMulticastCtrlTable 1 }

UtsDot3Onu2CtcMulticastCtrlEntry ::=
       SEQUENCE {
               utsDot3Onu2MCtrlModuleId		         INTEGER,
               utsDot3Onu2MCtrlDeviceId              INTEGER,
               utsDot3Onu2MCtrlPortId		         INTEGER,
               utsDot3Onu2MCtrlLogicalPortId         INTEGER,
               utsDot3Onu2MCastEntryIndex            INTEGER,

               utsDot3OnuMCastEntryUserId            INTEGER,
               utsDot3OnuMCastEntryMcVlanId          INTEGER,
               utsDot3OnuMCastEntryMcMacAddr         MacAddress

--               utsDot3OnuMCastEntryRowStatus         RowStatus
        }

utsDot3Onu2MCtrlModuleId OBJECT-TYPE
SYNTAX  INTEGER
       MAX-ACCESS  read-only
       STATUS  current
       DESCRIPTION
"A read only value to identifiy the OLT module id for the current ONU."
        ::= { utsDot3Onu2CtcMulticastCtrlEntry 1 }

utsDot3Onu2MCtrlDeviceId OBJECT-TYPE
SYNTAX  INTEGER
       MAX-ACCESS  read-only
       STATUS  current
       DESCRIPTION
"A read only value to identifiy the OLT device id for the current ONU."
        ::= { utsDot3Onu2CtcMulticastCtrlEntry 2 }

utsDot3Onu2MCtrlPortId OBJECT-TYPE
SYNTAX  INTEGER
       MAX-ACCESS  read-only
       STATUS  current
       DESCRIPTION
"A read only value to identifiy the OLT port id for the current ONU."
        ::= { utsDot3Onu2CtcMulticastCtrlEntry 3 }

utsDot3Onu2MCtrlLogicalPortId OBJECT-TYPE
SYNTAX  INTEGER
       MAX-ACCESS  read-only
       STATUS  current
       DESCRIPTION
"A read only value to identifiy the logical port id for the current ONU."
        ::= { utsDot3Onu2CtcMulticastCtrlEntry 4 }

utsDot3Onu2MCastEntryIndex OBJECT-TYPE
SYNTAX  INTEGER(1..32)
       MAX-ACCESS  read-only
       STATUS  current
       DESCRIPTION
"ONU multicast entry index"
        ::= { utsDot3Onu2CtcMulticastCtrlEntry 5 }

utsDot3OnuMCastEntryUserId OBJECT-TYPE
SYNTAX  INTEGER
       MAX-ACCESS  read-only
       STATUS  current
       DESCRIPTION
"User ID or port ID"
        ::= { utsDot3Onu2CtcMulticastCtrlEntry 6 }

utsDot3OnuMCastEntryMcVlanId OBJECT-TYPE
SYNTAX  INTEGER(1..4094)
       MAX-ACCESS  read-only
       STATUS  current
       DESCRIPTION
"Multicast VLAN ID"
        ::= { utsDot3Onu2CtcMulticastCtrlEntry 7 }

utsDot3OnuMCastEntryMcMacAddr OBJECT-TYPE
SYNTAX  MacAddress
       MAX-ACCESS  read-only
       STATUS  current
       DESCRIPTION
"Multicast MAC address"
        ::= { utsDot3Onu2CtcMulticastCtrlEntry 8 }


-- CTC ONU DBA configuration

utsDot3Onu2CtcDbaTable OBJECT-TYPE
SYNTAX  SEQUENCE OF UtsDot3Onu2CtcDbaEntry
        MAX-ACCESS  not-accessible
        STATUS  current
        DESCRIPTION
"Table for dot3 ONU multicast control MIBs."
        ::= { utsDot3OnuObjects 14 }

utsDot3Onu2CtcDbaEntry OBJECT-TYPE
SYNTAX  UtsDot3Onu2CtcDbaEntry
       MAX-ACCESS  not-accessible
       STATUS  current
       DESCRIPTION
"An entry in the dot3 Onu multicast control MIBs table."
       INDEX  { utsDot3OnuDbaModuleId,utsDot3OnuDbaDeviceId,utsDot3OnuDbaPortId,
                utsDot3OnuDbaLogicalPortId }
       ::= { utsDot3Onu2CtcDbaTable 1 }

UtsDot3Onu2CtcDbaEntry ::=
       SEQUENCE {
               utsDot3OnuDbaModuleId		         INTEGER,
               utsDot3OnuDbaDeviceId                 INTEGER,
               utsDot3OnuDbaPortId			         INTEGER,
               utsDot3OnuDbaLogicalPortId	         INTEGER,
               utsDot3Onu2DbaQueueSetNum             INTEGER,
               utsDot3Onu2DbaQueueBitmap1            OCTET STRING,
               utsDot3Onu2DbaQueueSetThreshold1      OCTET STRING,
               utsDot3Onu2DbaQueueBitmap2            OCTET STRING,
               utsDot3Onu2DbaQueueSetThreshold2      OCTET STRING,
               utsDot3Onu2DbaQueueBitmap3            OCTET STRING,
               utsDot3Onu2DbaQueueSetThreshold3      OCTET STRING,
               utsDot3Onu2DbaQueueBitmap4            OCTET STRING,
               utsDot3Onu2DbaQueueSetThreshold4      OCTET STRING
--               utsDot3Onu2DbaQueueSetCommit          INTEGER

        }

utsDot3OnuDbaModuleId OBJECT-TYPE
SYNTAX  INTEGER
       MAX-ACCESS  read-only
       STATUS  current
       DESCRIPTION
"A read only value to identifiy the OLT module id for the current ONU."
        ::= { utsDot3Onu2CtcDbaEntry 1 }

utsDot3OnuDbaDeviceId OBJECT-TYPE
SYNTAX  INTEGER
       MAX-ACCESS  read-only
       STATUS  current
       DESCRIPTION
"A read only value to identifiy the OLT device id for the current ONU."
        ::= { utsDot3Onu2CtcDbaEntry 2 }

utsDot3OnuDbaPortId OBJECT-TYPE
SYNTAX  INTEGER
       MAX-ACCESS  read-only
       STATUS  current
       DESCRIPTION
"A read only value to identifiy the OLT port id for the current ONU."
        ::= { utsDot3Onu2CtcDbaEntry 3 }

utsDot3OnuDbaLogicalPortId OBJECT-TYPE
SYNTAX  INTEGER
       MAX-ACCESS  read-only
       STATUS  current
       DESCRIPTION
"A read only value to identifiy the logical port id for the current ONU."
        ::= { utsDot3Onu2CtcDbaEntry 4 }

utsDot3Onu2DbaQueueSetNum OBJECT-TYPE
		SYNTAX  INTEGER (2..4)
		MAX-ACCESS  read-write
		STATUS  current
		DESCRIPTION
			"Number of queue sets"
        ::= { utsDot3Onu2CtcDbaEntry 5 }


utsDot3Onu2DbaQueueBitmap1 OBJECT-TYPE
		SYNTAX  OCTET STRING(SIZE(1))  -- 0B: Bit 0[Que 1] 1[Que 2] 2[Que 3] 3[Que 4] 4[Que 5] 5[Que 6] 6[Que 7] 7[Que 8]
		MAX-ACCESS  read-write
		STATUS  current
		DESCRIPTION
			"Queue bitmap, bit value 1 indecate the corresponding queue is present."
        ::= { utsDot3Onu2CtcDbaEntry 7 }

utsDot3Onu2DbaQueueSetThreshold1 OBJECT-TYPE
		SYNTAX  OCTET STRING(SIZE(16))  -- 0x: 0123[Que 1] 4567[Que 2] 89ab[Que 3] cdef[Que 4] ...
		MAX-ACCESS  read-write
		STATUS  current
		DESCRIPTION
			"Threshold for queues in queue set 1"
        ::= { utsDot3Onu2CtcDbaEntry 8 }

utsDot3Onu2DbaQueueBitmap2 OBJECT-TYPE
		SYNTAX  OCTET STRING(SIZE(1))  -- 0B: Bit 0[Que 1] 1[Que 2] 2[Que 3] 3[Que 4] 4[Que 5] 5[Que 6] 6[Que 7] 7[Que 8]
		MAX-ACCESS  read-write
		STATUS  current
		DESCRIPTION
			"Queue bitmap, bit value 1 indecate the corresponding queue is present."
        ::= { utsDot3Onu2CtcDbaEntry 9 }

utsDot3Onu2DbaQueueSetThreshold2 OBJECT-TYPE
		SYNTAX  OCTET STRING(SIZE(16))  -- 0x: 01[Que 1] 12[Que 2] 34[Que 3] 56[Que 4] 78[Que 5] 9a[Que 6] bc[Que 7] de[Que 8]
		MAX-ACCESS  read-write
		STATUS  current
		DESCRIPTION
			"Threshold for queues in queue set 2"
        ::= { utsDot3Onu2CtcDbaEntry 10 }

utsDot3Onu2DbaQueueBitmap3 OBJECT-TYPE
		SYNTAX  OCTET STRING(SIZE(1))  -- 0B: Bit 0[Que 1] 1[Que 2] 2[Que 3] 3[Que 4] 4[Que 5] 5[Que 6] 6[Que 7] 7[Que 8]
		MAX-ACCESS  read-write
		STATUS  current
		DESCRIPTION
			"Queue bitmap, bit value 1 indecate the corresponding queue is present."
        ::= { utsDot3Onu2CtcDbaEntry 11 }

utsDot3Onu2DbaQueueSetThreshold3 OBJECT-TYPE
		SYNTAX  OCTET STRING(SIZE(16))  -- 0x: 01[Que 1] 12[Que 2] 34[Que 3] 56[Que 4] 78[Que 5] 9a[Que 6] bc[Que 7] de[Que 8]
		MAX-ACCESS  read-write
		STATUS  current
		DESCRIPTION
			"Threshold for queues in queue set 3"
        ::= { utsDot3Onu2CtcDbaEntry 12 }

utsDot3Onu2DbaQueueBitmap4 OBJECT-TYPE
		SYNTAX  OCTET STRING(SIZE(1))  -- 0B: Bit 0[Que 1] 1[Que 2] 2[Que 3] 3[Que 4] 4[Que 5] 5[Que 6] 6[Que 7] 7[Que 8]
		MAX-ACCESS  read-write
		STATUS  current
		DESCRIPTION
			"Queue bitmap, bit value 1 indecate the corresponding queue is present."
        ::= { utsDot3Onu2CtcDbaEntry 13 }

utsDot3Onu2DbaQueueSetThreshold4 OBJECT-TYPE
		SYNTAX  OCTET STRING(SIZE(16))  -- 0x: 01[Que 1] 12[Que 2] 34[Que 3] 56[Que 4] 78[Que 5] 9a[Que 6] bc[Que 7] de[Que 8]
		MAX-ACCESS  read-write
		STATUS  current
		DESCRIPTION
			"Threshold for queues in queue set 4"
        ::= { utsDot3Onu2CtcDbaEntry 14 }

-- ONU loopback test

utsDot3Onu2CtcLpBkTable OBJECT-TYPE
SYNTAX  SEQUENCE OF UtsDot3Onu2CtcLpBkEntry
        MAX-ACCESS  not-accessible
        STATUS  current
        DESCRIPTION
"Table for dot3 ONU multicast control MIBs."
        ::= { utsDot3OnuObjects 15 }

utsDot3Onu2CtcLpBkEntry OBJECT-TYPE
SYNTAX  UtsDot3Onu2CtcLpBkEntry
       MAX-ACCESS  not-accessible
       STATUS  current
       DESCRIPTION
"An entry in the dot3 Onu multicast control MIBs table."
       INDEX  { utsDot3OnuLpBkModuleId,utsDot3OnuLpBkDeviceId,utsDot3OnuLpBkPortId,
                utsDot3OnuLpBkLogicalPortId }
       ::= { utsDot3Onu2CtcLpBkTable 1 }

UtsDot3Onu2CtcLpBkEntry ::=
       SEQUENCE {
               utsDot3OnuLpBkModuleId		         INTEGER,
               utsDot3OnuLpBkDeviceId                INTEGER,
               utsDot3OnuLpBkPortId			         INTEGER,
               utsDot3OnuLpBkLogicalPortId	         INTEGER,
               utsDot3OnuLpBkMode                    INTEGER,
               utsDot3OnuLpBkPacketSize              INTEGER,
               utsDot3OnuLpBkPacketNum               INTEGER,
               utsDot3OnuLpBkStart                   TruthValue,
               utsDot3OnuLpBkEnd                     TruthValue,
               utsDot3OnuLpBkResult                  OCTET STRING,
               utsDot3OnuLpBkRowStatus               RowStatus
        }

utsDot3OnuLpBkModuleId OBJECT-TYPE
SYNTAX  INTEGER
       MAX-ACCESS  not-accessible
       STATUS  current
       DESCRIPTION
"A read only value to identifiy the OLT module id for the current ONU."
        ::= { utsDot3Onu2CtcLpBkEntry 1 }

utsDot3OnuLpBkDeviceId OBJECT-TYPE
SYNTAX  INTEGER
       MAX-ACCESS  not-accessible
       STATUS  current
       DESCRIPTION
"A read only value to identifiy the OLT device id for the current ONU."
        ::= { utsDot3Onu2CtcLpBkEntry 2 }

utsDot3OnuLpBkPortId OBJECT-TYPE
SYNTAX  INTEGER
       MAX-ACCESS  not-accessible
       STATUS  current
       DESCRIPTION
"A read only value to identifiy the OLT port id for the current ONU."
        ::= { utsDot3Onu2CtcLpBkEntry 3 }

utsDot3OnuLpBkLogicalPortId OBJECT-TYPE
SYNTAX  INTEGER
       MAX-ACCESS  not-accessible
       STATUS  current
       DESCRIPTION
"A read only value to identifiy the logical port id for the current ONU."
        ::= { utsDot3Onu2CtcLpBkEntry 4 }

utsDot3OnuLpBkMode OBJECT-TYPE
		SYNTAX  INTEGER
		{
		  local(1),
		  remote(2)
		}
		MAX-ACCESS  read-create
		STATUS  current
		DESCRIPTION
			" loopback mode"
        ::= { utsDot3Onu2CtcLpBkEntry 5 }

utsDot3OnuLpBkPacketSize OBJECT-TYPE
		SYNTAX  INTEGER(64..1500)
		MAX-ACCESS  read-create
		STATUS  current
		DESCRIPTION
			"loopback packet size"
        ::= { utsDot3Onu2CtcLpBkEntry 6 }

utsDot3OnuLpBkPacketNum OBJECT-TYPE
		SYNTAX  INTEGER(1..100)
		MAX-ACCESS  read-create
		STATUS  current
		DESCRIPTION
			"loopback packet number"
        ::= { utsDot3Onu2CtcLpBkEntry 7 }

utsDot3OnuLpBkStart OBJECT-TYPE
		SYNTAX  TruthValue
		MAX-ACCESS  read-create
		STATUS  current
		DESCRIPTION
			"loopback test start or not"
        ::= { utsDot3Onu2CtcLpBkEntry 8 }

utsDot3OnuLpBkEnd OBJECT-TYPE
		SYNTAX  TruthValue
		MAX-ACCESS  read-create
		STATUS  current
		DESCRIPTION
			"loopback test stop or not"
        ::= { utsDot3Onu2CtcLpBkEntry 9 }

utsDot3OnuLpBkResult OBJECT-TYPE
		SYNTAX  OCTET STRING
		MAX-ACCESS  read-only
		STATUS  current
		DESCRIPTION
			"loopback test result, like:
			 Out of Seqance frames: 0
			 99 packets transmitted, 99 received, 0% packet loss
			 rtt min/avg/max = 0/0/0 ms"
        ::= { utsDot3Onu2CtcLpBkEntry 10 }

utsDot3OnuLpBkRowStatus OBJECT-TYPE
		SYNTAX  RowStatus
		MAX-ACCESS  read-create
		STATUS  current
		DESCRIPTION
			"Row status"
        ::= { utsDot3Onu2CtcLpBkEntry 11 }

-- ONU Ethernet port classification configuration application table

utsDot3Onu2CtcClassifiAppTable OBJECT-TYPE
SYNTAX  SEQUENCE OF UtsDot3Onu2CtcClassifiAppEntry
        MAX-ACCESS  not-accessible
        STATUS  current
        DESCRIPTION
"Table for dot3 ONU MIBs."
        ::= { utsDot3OnuObjects 16 }

utsDot3Onu2CtcClassifiAppEntry OBJECT-TYPE
SYNTAX  UtsDot3Onu2CtcClassifiAppEntry
       MAX-ACCESS  not-accessible
       STATUS  current
       DESCRIPTION
"An entry in the dot3 Onu classification application MIBs table."
       INDEX  { utsDot3OnuClassifiAppModuleId,utsDot3OnuClassifiAppDeviceId,
                utsDot3OnuClassifiAppPortId,utsDot3OnuClassifiAppLogicalPortId,
                utsDot3OnuClassifiAppPortIndex, utsDot3OnuClassifiAppClassId,
                utsDot3OnuClassifiAppFieldId}
       ::= { utsDot3Onu2CtcClassifiAppTable 1 }

UtsDot3Onu2CtcClassifiAppEntry ::=
       SEQUENCE {
               utsDot3OnuClassifiAppModuleId         INTEGER,
               utsDot3OnuClassifiAppDeviceId         INTEGER,
               utsDot3OnuClassifiAppPortId		     INTEGER,
               utsDot3OnuClassifiAppLogicalPortId    INTEGER,
               utsDot3OnuClassifiAppPortIndex        INTEGER,
               utsDot3OnuClassifiAppClassId          INTEGER,
               utsDot3OnuClassifiAppFieldId          INTEGER,

--               utsDot3OnuClassifiAppRuleIndex        INTEGER,
               utsDot3OnuClassifiAppPrecedence       INTEGER,
               utsDot3OnuClassifiAppQueueMapped      INTEGER,
               utsDot3OnuClassifiAppPriMark          INTEGER,

               utsDot3OnuClassifiAppRowStatus        RowStatus
        }

utsDot3OnuClassifiAppModuleId OBJECT-TYPE
SYNTAX  INTEGER
       MAX-ACCESS  not-accessible
       STATUS  current
       DESCRIPTION
"A read only value to identifiy the OLT module id for the current ONU."
        ::= { utsDot3Onu2CtcClassifiAppEntry 1 }

utsDot3OnuClassifiAppDeviceId OBJECT-TYPE
SYNTAX  INTEGER
       MAX-ACCESS  not-accessible
       STATUS  current
       DESCRIPTION
"A read only value to identifiy the OLT device id for the current ONU."
        ::= { utsDot3Onu2CtcClassifiAppEntry 2 }

utsDot3OnuClassifiAppPortId OBJECT-TYPE
SYNTAX  INTEGER
       MAX-ACCESS  not-accessible
       STATUS  current
       DESCRIPTION
"A read only value to identifiy the OLT port id for the current ONU."
        ::= { utsDot3Onu2CtcClassifiAppEntry 3 }

utsDot3OnuClassifiAppLogicalPortId OBJECT-TYPE
SYNTAX  INTEGER
       MAX-ACCESS  not-accessible
       STATUS  current
       DESCRIPTION
"A read only value to identifiy the logical port id for the current ONU."
        ::= { utsDot3Onu2CtcClassifiAppEntry 4 }

utsDot3OnuClassifiAppPortIndex OBJECT-TYPE
SYNTAX  INTEGER
       MAX-ACCESS  not-accessible
       STATUS  current
       DESCRIPTION
"ONU Ethernet port index"
        ::= { utsDot3Onu2CtcClassifiAppEntry 5 }

utsDot3OnuClassifiAppClassId OBJECT-TYPE
SYNTAX  INTEGER(1..32)
       MAX-ACCESS  not-accessible
       STATUS  current
       DESCRIPTION
"ONU classification profile ID"
        ::= { utsDot3Onu2CtcClassifiAppEntry 6 }

utsDot3OnuClassifiAppFieldId OBJECT-TYPE
SYNTAX  INTEGER(1..120)
       MAX-ACCESS  not-accessible
       STATUS  current
       DESCRIPTION
"ONU classification rule ID"
        ::= { utsDot3Onu2CtcClassifiAppEntry 7 }


utsDot3OnuClassifiAppPrecedence OBJECT-TYPE
SYNTAX  INTEGER(1..20)
       MAX-ACCESS  read-create
       STATUS  current
       DESCRIPTION
"Phy admin status"
        ::= { utsDot3Onu2CtcClassifiAppEntry 8 }

utsDot3OnuClassifiAppQueueMapped OBJECT-TYPE
SYNTAX  INTEGER(0..7)
       MAX-ACCESS  read-create
       STATUS  current
       DESCRIPTION
"Queue mapped"
        ::= { utsDot3Onu2CtcClassifiAppEntry 9 }

utsDot3OnuClassifiAppPriMark OBJECT-TYPE
SYNTAX  INTEGER(0..255)  -- 0..7 for new priority, 255 for none
       MAX-ACCESS  read-create
       STATUS  current
       DESCRIPTION
"ONU classification new priority"
        ::= { utsDot3Onu2CtcClassifiAppEntry 10 }

utsDot3OnuClassifiAppRowStatus OBJECT-TYPE
SYNTAX  RowStatus
       MAX-ACCESS  read-create
       STATUS  current
       DESCRIPTION
"Row status"
        ::= { utsDot3Onu2CtcClassifiAppEntry 11 }


-- Valid ONU MAC table

utsDot3Onu2CtcValidOnuMacTable OBJECT-TYPE
SYNTAX  SEQUENCE OF UtsDot3Onu2CtcValidOnuMacEntry
        MAX-ACCESS  not-accessible
        STATUS  current
        DESCRIPTION
"Table for dot3 ONU MIBs."
        ::= { utsDot3OnuObjects 17 }

utsDot3Onu2CtcValidOnuMacEntry OBJECT-TYPE
SYNTAX  UtsDot3Onu2CtcValidOnuMacEntry
       MAX-ACCESS  not-accessible
       STATUS  current
       DESCRIPTION
"An entry in the dot3 valid ONU MAC MIBs table."
       INDEX  { utsDot3OnuValidOnuMacModuleId,utsDot3OnuValidOnuMacDeviceId,
                utsDot3OnuValidOnuMacPortId,utsDot3OnuValidOnuMacAppLPortId}
       ::= { utsDot3Onu2CtcValidOnuMacTable 1 }

UtsDot3Onu2CtcValidOnuMacEntry ::=
       SEQUENCE {
               utsDot3OnuValidOnuMacModuleId         INTEGER,
               utsDot3OnuValidOnuMacDeviceId         INTEGER,
               utsDot3OnuValidOnuMacPortId		     INTEGER,
               utsDot3OnuValidOnuMacAppLPortId       INTEGER,

               utsDot3ValidOnuMacAddr                MacAddress
        }

utsDot3OnuValidOnuMacModuleId OBJECT-TYPE
SYNTAX  INTEGER
       MAX-ACCESS  not-accessible
       STATUS  current
       DESCRIPTION
"A read only value to identifiy the OLT module id for the current ONU."
        ::= { utsDot3Onu2CtcValidOnuMacEntry 1 }

utsDot3OnuValidOnuMacDeviceId OBJECT-TYPE
SYNTAX  INTEGER
       MAX-ACCESS  not-accessible
       STATUS  current
       DESCRIPTION
"A read only value to identifiy the OLT device id for the current ONU."
        ::= { utsDot3Onu2CtcValidOnuMacEntry 2 }

utsDot3OnuValidOnuMacPortId OBJECT-TYPE
SYNTAX  INTEGER
       MAX-ACCESS  not-accessible
       STATUS  current
       DESCRIPTION
"A read only value to identifiy the OLT port id for the current ONU."
        ::= { utsDot3Onu2CtcValidOnuMacEntry 3 }

utsDot3OnuValidOnuMacAppLPortId OBJECT-TYPE
SYNTAX  INTEGER
       MAX-ACCESS  not-accessible
       STATUS  current
       DESCRIPTION
"A read only value to identifiy the logical port id for the current ONU."
        ::= { utsDot3Onu2CtcValidOnuMacEntry 4 }

utsDot3ValidOnuMacAddr OBJECT-TYPE
SYNTAX  MacAddress
       MAX-ACCESS  read-write
       STATUS  current
       DESCRIPTION
"Valid ONU MAC address"
        ::= { utsDot3Onu2CtcValidOnuMacEntry 5 }


-- EPM04B PON static FDB configurations

utsDot3Onu2StaticFDBTable OBJECT-TYPE
SYNTAX  SEQUENCE OF UtsDot3Onu2StaticFDBEntry
        MAX-ACCESS  not-accessible
        STATUS  current
        DESCRIPTION
"Table for OLT type 2 port MIBs."
        ::= { utsDot3OnuObjects 18 }

utsDot3Onu2StaticFDBEntry OBJECT-TYPE
SYNTAX  UtsDot3Onu2StaticFDBEntry
       MAX-ACCESS  not-accessible
       STATUS  current
       DESCRIPTION
"An entry in the OLT type 2 port MIBs table."
       INDEX  { utsDot3OnuStaticFDBModuleId, utsDot3OnuStaticFDBDeviceId,
                utsDot3OnuStaticFDBPortId, utsDot3OnuStaticFDBLPortId}
       ::= { utsDot3Onu2StaticFDBTable 1 }

UtsDot3Onu2StaticFDBEntry ::=
       SEQUENCE {
                    utsDot3OnuStaticFDBModuleId				        INTEGER,
                    utsDot3OnuStaticFDBDeviceId                     INTEGER,
                    utsDot3OnuStaticFDBPortId                       INTEGER,
                    utsDot3OnuStaticFDBLPortId                      INTEGER,

                    utsDot3OnuStaticFDBDstMacAddr                   MacAddress,
                    utsDot3OnuStaticFDBVlanId                       INTEGER,
                    utsDot3OnuStaticFDBEgressPort                   INTEGER,
                    utsDot3OnuStaticFDBFunction                     INTEGER,
                    utsDot3OnuStaticFDBRowStatus                    RowStatus
       }

utsDot3OnuStaticFDBModuleId OBJECT-TYPE
SYNTAX  INTEGER
       MAX-ACCESS  not-accessible
       STATUS  current
       DESCRIPTION
"Module ID"
        ::= { utsDot3Onu2StaticFDBEntry 1 }

utsDot3OnuStaticFDBDeviceId OBJECT-TYPE
SYNTAX  INTEGER
       MAX-ACCESS  not-accessible
       STATUS  current
       DESCRIPTION
"Device ID"
        ::= { utsDot3Onu2StaticFDBEntry 2 }

utsDot3OnuStaticFDBPortId OBJECT-TYPE
SYNTAX  INTEGER
       MAX-ACCESS  not-accessible
       STATUS  current
       DESCRIPTION
"OLT PON port ID"
        ::= { utsDot3Onu2StaticFDBEntry 3 }

utsDot3OnuStaticFDBLPortId OBJECT-TYPE
SYNTAX  INTEGER
       MAX-ACCESS  not-accessible
       STATUS  current
       DESCRIPTION
"ONU Logical port ID"
        ::= { utsDot3Onu2StaticFDBEntry 4 }

utsDot3OnuStaticFDBDstMacAddr OBJECT-TYPE
SYNTAX  MacAddress
       MAX-ACCESS  read-create
       STATUS  current
       DESCRIPTION
"Destination MAC address"
        ::= { utsDot3Onu2StaticFDBEntry 5 }

utsDot3OnuStaticFDBVlanId OBJECT-TYPE
SYNTAX  INTEGER(1..4094)
       MAX-ACCESS  read-create
       STATUS  current
       DESCRIPTION
"VLAN ID"
        ::= { utsDot3Onu2StaticFDBEntry 6 }

utsDot3OnuStaticFDBEgressPort OBJECT-TYPE
SYNTAX INTEGER
       MAX-ACCESS  read-create
       STATUS  current
       DESCRIPTION
"Egress port number"
        ::= { utsDot3Onu2StaticFDBEntry 7 }

utsDot3OnuStaticFDBFunction OBJECT-TYPE
SYNTAX  INTEGER
	   {
	      staticForward(1),           -- static entry for forwarding
	      filterSrcMac(2),     -- static entry for source MAC filering
	      filterDstMac(3)      -- static entry for source MAC filering
	   }
       MAX-ACCESS  read-create
       STATUS  current
       DESCRIPTION
"Static FBD entry function"
        ::= { utsDot3Onu2StaticFDBEntry 8 }

utsDot3OnuStaticFDBRowStatus OBJECT-TYPE
SYNTAX  RowStatus
       MAX-ACCESS  read-create
       STATUS  current
       DESCRIPTION
"Row status"
        ::= { utsDot3Onu2StaticFDBEntry 9 }

-- Display FDB table

-- EPM04B PON static FDB configurations

utsDot3Onu2FDBTable OBJECT-TYPE
SYNTAX  SEQUENCE OF UtsDot3Onu2FDBEntry
        MAX-ACCESS  not-accessible
        STATUS  current
        DESCRIPTION
"Table for OLT type 2 port MIBs."
        ::= { utsDot3OnuObjects 19 }

utsDot3Onu2FDBEntry OBJECT-TYPE
SYNTAX  UtsDot3Onu2FDBEntry
       MAX-ACCESS  not-accessible
       STATUS  current
       DESCRIPTION
"An entry in the OLT type 2 port MIBs table."
       INDEX  { utsDot3OnuFDBModuleId, utsDot3OnuFDBDeviceId,
                utsDot3OnuFDBPortId, utsDot3OnuFDBLPortId, utsDot3OnuFDBIndex }
       ::= { utsDot3Onu2FDBTable 1 }

UtsDot3Onu2FDBEntry ::=
       SEQUENCE {
                    utsDot3OnuFDBModuleId				      INTEGER,
                    utsDot3OnuFDBDeviceId                     INTEGER,
                    utsDot3OnuFDBPortId                       INTEGER,
                    utsDot3OnuFDBLPortId                      INTEGER,
                    utsDot3OnuFDBIndex                        INTEGER,

                    utsDot3OnuFDBDstMacAddr                   MacAddress,
                    utsDot3OnuFDBVlanId                       INTEGER,
                    utsDot3OnuFDBEgressPort                   OCTET STRING,
                    utsDot3OnuFDBStatus                       INTEGER
       }

utsDot3OnuFDBModuleId OBJECT-TYPE
SYNTAX  INTEGER
       MAX-ACCESS  not-accessible
       STATUS  current
       DESCRIPTION
"Module ID"
        ::= { utsDot3Onu2FDBEntry 1 }

utsDot3OnuFDBDeviceId OBJECT-TYPE
SYNTAX  INTEGER
       MAX-ACCESS  not-accessible
       STATUS  current
       DESCRIPTION
"Device ID"
        ::= { utsDot3Onu2FDBEntry 2 }

utsDot3OnuFDBLPortId OBJECT-TYPE
SYNTAX  INTEGER
       MAX-ACCESS  not-accessible
       STATUS  current
       DESCRIPTION
"ONU Logical port ID"
        ::= { utsDot3Onu2FDBEntry 3 }

utsDot3OnuFDBPortId OBJECT-TYPE
SYNTAX  INTEGER
       MAX-ACCESS  not-accessible
       STATUS  current
       DESCRIPTION
"OLT PON port ID"
        ::= { utsDot3Onu2FDBEntry 4 }


utsDot3OnuFDBIndex OBJECT-TYPE
SYNTAX  INTEGER
       MAX-ACCESS  not-accessible
       STATUS  current
       DESCRIPTION
"ONU FDB index"
        ::= { utsDot3Onu2FDBEntry 5 }

utsDot3OnuFDBDstMacAddr OBJECT-TYPE
SYNTAX  MacAddress
       MAX-ACCESS  read-create
       STATUS  current
       DESCRIPTION
"Destination MAC address"
        ::= { utsDot3Onu2FDBEntry 6 }

utsDot3OnuFDBVlanId OBJECT-TYPE
SYNTAX  INTEGER(1..4094)
       MAX-ACCESS  read-create
       STATUS  current
       DESCRIPTION
"VLAN ID"
        ::= { utsDot3Onu2FDBEntry 7 }

utsDot3OnuFDBEgressPort OBJECT-TYPE
SYNTAX  OCTET STRING(SIZE(1)) --  from left to right, 0B1011... means port 1,3,4s
       MAX-ACCESS  read-create
       STATUS  current
       DESCRIPTION
"Egress port map"
        ::= { utsDot3Onu2FDBEntry 8 }

utsDot3OnuFDBStatus OBJECT-TYPE
SYNTAX INTEGER
	   {
	      invalid(1), -- the entry is no longer valid but not flushed yet
	      dynamic(2), -- dynamically learned
	      local(3),   -- local port MAC address
	      static(4),  -- statically added
	      igmpSnooping(5), -- via IGMP snooping
	      filterSrcMac(6), -- filtering  by Dst MAC address
	      filterDstMac(7)  -- filtering  by Dst MAC address
	   }
       MAX-ACCESS  read-create
       STATUS  current
       DESCRIPTION
"Egress port map"
        ::= { utsDot3Onu2FDBEntry 9 }

--  ONU classification rules

utsDot3Onu2CtcClassifiRuleTable OBJECT-TYPE
SYNTAX  SEQUENCE OF UtsDot3Onu2CtcClassifiRuleEntry
        MAX-ACCESS  not-accessible
        STATUS  current
        DESCRIPTION
"Table for dot3 ONU MIBs."
        ::= { utsDot3OnuObjects 20 }

utsDot3Onu2CtcClassifiRuleEntry OBJECT-TYPE
SYNTAX  UtsDot3Onu2CtcClassifiRuleEntry
       MAX-ACCESS  not-accessible
       STATUS  current
       DESCRIPTION
"An entry in the dot3 Onu classification rule MIBs table."
       INDEX  { utsDot3OnuClassifiRuleProfId,utsDot3OnuClassifiRuleId}
       ::= { utsDot3Onu2CtcClassifiRuleTable 1 }

UtsDot3Onu2CtcClassifiRuleEntry ::=
       SEQUENCE {
               utsDot3OnuClassifiRuleProfId         INTEGER,
               utsDot3OnuClassifiRuleId             INTEGER,
               utsDot3OnuClassifiRuleBitMap		    OCTET STRING,

               utsDot3OnuClassifiRuleDMacOper       INTEGER,
               utsDot3OnuClassifiRuleDMac           MacAddress,
               utsDot3OnuClassifiRuleDMac2          MacAddress,

               utsDot3OnuClassifiRuleSMacOper       INTEGER,
               utsDot3OnuClassifiRuleSMac           MacAddress,
               utsDot3OnuClassifiRuleSMac2          MacAddress,

               utsDot3OnuClassifiRulePriOper        INTEGER,
               utsDot3OnuClassifiRulePri            INTEGER,
               utsDot3OnuClassifiRulePri2           INTEGER,

               utsDot3OnuClassifiRuleVlanOper       INTEGER,
               utsDot3OnuClassifiRuleVlanId         INTEGER,
               utsDot3OnuClassifiRuleVlanId2        INTEGER,

               utsDot3OnuClassifiRuleTypeOper       INTEGER,
               utsDot3OnuClassifiRuleType           INTEGER,
               utsDot3OnuClassifiRuleType2          INTEGER,

--               utsDot3OnuClassifiRuleIpProtOper     INTEGER,
--               utsDot3OnuClassifiRuleIpProt         INTEGER,
               utsDot3OnuClassifiRuleSIPOper        INTEGER,
               utsDot3OnuClassifiRuleSIP            IpAddress,
               utsDot3OnuClassifiRuleSIP2           IpAddress,

               utsDot3OnuClassifiRuleDIPOper        INTEGER,
               utsDot3OnuClassifiRuleDIP            IpAddress,
               utsDot3OnuClassifiRuleDIP2           IpAddress,

               utsDot3OnuClassifiRuleDSCPOper       INTEGER,
               utsDot3OnuClassifiRuleDSCP           INTEGER,
               utsDot3OnuClassifiRuleDSCP2          INTEGER,

               utsDot3OnuClassifiRuleSPortOper      INTEGER,
               utsDot3OnuClassifiRuleSPort1         INTEGER,
               utsDot3OnuClassifiRuleSPort2         INTEGER,
               utsDot3OnuClassifiRuleDPortOper      INTEGER,
               utsDot3OnuClassifiRuleDPort1         INTEGER,
               utsDot3OnuClassifiRuleDPort2         INTEGER,

               utsDot3OnuClassifiRuleProtocolOper   INTEGER,
               utsDot3OnuClassifiRuleProtocol       INTEGER,
               utsDot3OnuClassifiRuleProtocol2      INTEGER
        }

utsDot3OnuClassifiRuleProfId OBJECT-TYPE
SYNTAX  INTEGER
       MAX-ACCESS  not-accessible
       STATUS  current
       DESCRIPTION
"Profile ID"
        ::= { utsDot3Onu2CtcClassifiRuleEntry 1 }

utsDot3OnuClassifiRuleId OBJECT-TYPE
SYNTAX  INTEGER
       MAX-ACCESS  not-accessible
       STATUS  current
       DESCRIPTION
"Rule index"
        ::= { utsDot3Onu2CtcClassifiRuleEntry 2 }

utsDot3OnuClassifiRuleBitMap   OBJECT-TYPE
SYNTAX OCTET STRING(SIZE(4))  -- from left to right
       MAX-ACCESS  read-only
       STATUS  current
       DESCRIPTION
"Field selecting"
        ::= { utsDot3Onu2CtcClassifiRuleEntry 3 }

utsDot3OnuClassifiRuleDMacOper   OBJECT-TYPE
SYNTAX  INTEGER
	   {
	      eq(1),neq(2),ngt(3),nlt(4),ex(5),nex(6),range(7)
	   }
       MAX-ACCESS  read-only
       STATUS  current
       DESCRIPTION
"Destination MAC operating"
       DEFVAL{eq}
        ::= { utsDot3Onu2CtcClassifiRuleEntry 4 }

utsDot3OnuClassifiRuleDMac   OBJECT-TYPE
SYNTAX  MacAddress
       MAX-ACCESS  read-only
       STATUS  current
       DESCRIPTION
"Destination MAC address"
        ::= { utsDot3Onu2CtcClassifiRuleEntry 5 }

utsDot3OnuClassifiRuleDMac2   OBJECT-TYPE
SYNTAX  MacAddress
       MAX-ACCESS  read-only
       STATUS  current
       DESCRIPTION
"Destination MAC address 2"
        ::= { utsDot3Onu2CtcClassifiRuleEntry 6 }


utsDot3OnuClassifiRuleSMacOper   OBJECT-TYPE
SYNTAX  INTEGER
	   {
	      eq(1),neq(2),ngt(3),nlt(4),ex(5),nex(6),range(7)
	   }
       MAX-ACCESS  read-only
       STATUS  current
       DESCRIPTION
"Source MAC operating"
       DEFVAL{eq}
        ::= { utsDot3Onu2CtcClassifiRuleEntry 7 }

utsDot3OnuClassifiRuleSMac   OBJECT-TYPE
SYNTAX  MacAddress
       MAX-ACCESS  read-only
       STATUS  current
       DESCRIPTION
"Source MAC address"
        ::= { utsDot3Onu2CtcClassifiRuleEntry 8 }

utsDot3OnuClassifiRuleSMac2   OBJECT-TYPE
SYNTAX  MacAddress
       MAX-ACCESS  read-only
       STATUS  current
       DESCRIPTION
"Source MAC address 2 "
        ::= { utsDot3Onu2CtcClassifiRuleEntry 9 }

utsDot3OnuClassifiRulePriOper   OBJECT-TYPE
SYNTAX  INTEGER
	   {
	      eq(1),neq(2),ngt(3),nlt(4),ex(5),nex(6),range(7)
	   }
       MAX-ACCESS  read-only
       STATUS  current
       DESCRIPTION
"Priority operating"
       DEFVAL{eq}
        ::= { utsDot3Onu2CtcClassifiRuleEntry 10 }

utsDot3OnuClassifiRulePri   OBJECT-TYPE
SYNTAX  INTEGER
       MAX-ACCESS  read-only
       STATUS  current
       DESCRIPTION
"Priority value"
        ::= { utsDot3Onu2CtcClassifiRuleEntry 11 }

utsDot3OnuClassifiRulePri2   OBJECT-TYPE
SYNTAX  INTEGER
       MAX-ACCESS  read-only
       STATUS  current
       DESCRIPTION
"Priority value 2"
        ::= { utsDot3Onu2CtcClassifiRuleEntry 12 }


utsDot3OnuClassifiRuleVlanOper   OBJECT-TYPE
SYNTAX  INTEGER
	   {
	      eq(1),neq(2),ngt(3),nlt(4),ex(5),nex(6),range(7)
	   }
       MAX-ACCESS  read-only
       STATUS  current
       DESCRIPTION
"VLAN operating"
       DEFVAL{eq}
        ::= { utsDot3Onu2CtcClassifiRuleEntry 13 }

utsDot3OnuClassifiRuleVlanId   OBJECT-TYPE
SYNTAX  INTEGER(1..4094)
       MAX-ACCESS  read-only
       STATUS  current
       DESCRIPTION
"VLAN ID"
        ::= { utsDot3Onu2CtcClassifiRuleEntry 14 }

utsDot3OnuClassifiRuleVlanId2   OBJECT-TYPE
SYNTAX  INTEGER(1..4094)
       MAX-ACCESS  read-only
       STATUS  current
       DESCRIPTION
"VLAN ID 2"
        ::= { utsDot3Onu2CtcClassifiRuleEntry 15 }

utsDot3OnuClassifiRuleTypeOper   OBJECT-TYPE
SYNTAX  INTEGER
	   {
	      eq(1),neq(2),ngt(3),nlt(4),ex(5),nex(6),range(7)
	   }
       MAX-ACCESS  read-only
       STATUS  current
       DESCRIPTION
"Type operating"
       DEFVAL{eq}
        ::= { utsDot3Onu2CtcClassifiRuleEntry 16 }

utsDot3OnuClassifiRuleType   OBJECT-TYPE
SYNTAX  INTEGER
       MAX-ACCESS  read-only
       STATUS  current
       DESCRIPTION
"Type"
        ::= { utsDot3Onu2CtcClassifiRuleEntry 17 }

utsDot3OnuClassifiRuleType2   OBJECT-TYPE
SYNTAX  INTEGER
       MAX-ACCESS  read-only
       STATUS  current
       DESCRIPTION
       "Type 2"
        ::= { utsDot3Onu2CtcClassifiRuleEntry 18 }

utsDot3OnuClassifiRuleSIPOper   OBJECT-TYPE
SYNTAX  INTEGER
	   {
	      eq(1),neq(2),ngt(3),nlt(4),ex(5),nex(6),range(7)
	   }
       MAX-ACCESS  read-only
       STATUS  current
       DESCRIPTION
"Source IP address operating"
       DEFVAL{eq}
        ::= { utsDot3Onu2CtcClassifiRuleEntry 19 }

utsDot3OnuClassifiRuleSIP   OBJECT-TYPE
SYNTAX  IpAddress
       MAX-ACCESS  read-only
       STATUS  current
       DESCRIPTION
"Source IP address"
        ::= { utsDot3Onu2CtcClassifiRuleEntry 20 }

utsDot3OnuClassifiRuleSIP2   OBJECT-TYPE
SYNTAX  IpAddress
       MAX-ACCESS  read-only
       STATUS  current
       DESCRIPTION
"Source IP address 2"
        ::= { utsDot3Onu2CtcClassifiRuleEntry 21 }

utsDot3OnuClassifiRuleDIPOper   OBJECT-TYPE
SYNTAX  INTEGER
	   {
	      eq(1),neq(2),ngt(3),nlt(4),ex(5),nex(6),range(7)
	   }
       MAX-ACCESS  read-only
       STATUS  current
       DESCRIPTION
"Destination IP address operating"
       DEFVAL{eq}
        ::= { utsDot3Onu2CtcClassifiRuleEntry 22 }

utsDot3OnuClassifiRuleDIP   OBJECT-TYPE
SYNTAX  IpAddress
       MAX-ACCESS  read-only
       STATUS  current
       DESCRIPTION
"Destination IP address"
        ::= { utsDot3Onu2CtcClassifiRuleEntry 23 }

utsDot3OnuClassifiRuleDIP2   OBJECT-TYPE
SYNTAX  IpAddress
       MAX-ACCESS  read-only
       STATUS  current
       DESCRIPTION
"Destination IP address 2"
        ::= { utsDot3Onu2CtcClassifiRuleEntry 24 }

utsDot3OnuClassifiRuleDSCPOper   OBJECT-TYPE
SYNTAX  INTEGER
	   {
	      eq(1),neq(2),ngt(3),nlt(4),ex(5),nex(6),range(7)
	   }
       MAX-ACCESS  read-only
       STATUS  current
       DESCRIPTION
"DSCP operating"
       DEFVAL{eq}
        ::= { utsDot3Onu2CtcClassifiRuleEntry 25 }

utsDot3OnuClassifiRuleDSCP   OBJECT-TYPE
SYNTAX  INTEGER
       MAX-ACCESS  read-only
       STATUS  current
       DESCRIPTION
"DSCP"
        ::= { utsDot3Onu2CtcClassifiRuleEntry 26 }

utsDot3OnuClassifiRuleDSCP2   OBJECT-TYPE
SYNTAX  INTEGER
       MAX-ACCESS  read-only
       STATUS  current
       DESCRIPTION
"DSCP 2"
        ::= { utsDot3Onu2CtcClassifiRuleEntry 27 }

utsDot3OnuClassifiRuleSPortOper   OBJECT-TYPE
SYNTAX  INTEGER
	   {
	      eq(1),neq(2),ngt(3),nlt(4),ex(5),nex(6),range(7)
	   }
       MAX-ACCESS  read-only
       STATUS  current
       DESCRIPTION
"Source IP port operating"
       DEFVAL{eq}
        ::= { utsDot3Onu2CtcClassifiRuleEntry 28 }

utsDot3OnuClassifiRuleSPort1   OBJECT-TYPE
SYNTAX  INTEGER
       MAX-ACCESS  read-only
       STATUS  current
       DESCRIPTION
"Source port 1"
        ::= { utsDot3Onu2CtcClassifiRuleEntry 29 }

utsDot3OnuClassifiRuleSPort2   OBJECT-TYPE
SYNTAX  INTEGER
       MAX-ACCESS  read-only
       STATUS  current
       DESCRIPTION
"Source port 2"
       ::= { utsDot3Onu2CtcClassifiRuleEntry 30 }

utsDot3OnuClassifiRuleDPortOper   OBJECT-TYPE
SYNTAX  INTEGER
	   {
	      eq(1),neq(2),ngt(3),nlt(4),ex(5),nex(6),range(7)
	   }
       MAX-ACCESS  read-only
       STATUS  current
       DESCRIPTION
"Destination IP port operating"
       DEFVAL{eq}
       ::= { utsDot3Onu2CtcClassifiRuleEntry 31 }

utsDot3OnuClassifiRuleDPort1   OBJECT-TYPE
SYNTAX  INTEGER
       MAX-ACCESS  read-only
       STATUS  current
       DESCRIPTION
"Destination port 1"
        ::= { utsDot3Onu2CtcClassifiRuleEntry 32 }

utsDot3OnuClassifiRuleDPort2   OBJECT-TYPE
SYNTAX  INTEGER
       MAX-ACCESS  read-only
       STATUS  current
       DESCRIPTION
"Destination port 2"
        ::= { utsDot3Onu2CtcClassifiRuleEntry 33 }

utsDot3OnuClassifiRuleProtocolOper   OBJECT-TYPE
SYNTAX  INTEGER
	   {
	      eq(1),neq(2),ngt(3),nlt(4),ex(5),nex(6),range(7)
	   }
       MAX-ACCESS  read-only
       STATUS  current
       DESCRIPTION
"Protocol operation"
       DEFVAL{eq}
        ::= { utsDot3Onu2CtcClassifiRuleEntry 34 }

utsDot3OnuClassifiRuleProtocol   OBJECT-TYPE
SYNTAX  INTEGER
       MAX-ACCESS  read-only
       STATUS  current
       DESCRIPTION
"Protocol value"
        ::= { utsDot3Onu2CtcClassifiRuleEntry 35 }

utsDot3OnuClassifiRuleProtocol2  OBJECT-TYPE
SYNTAX  INTEGER
       MAX-ACCESS  read-only
       STATUS  current
       DESCRIPTION
"Protocol value 2"
        ::= { utsDot3Onu2CtcClassifiRuleEntry 36 }

--
--   ACL Profile Import Configuration Table
--
utsDot3OnuClassifiImportTable  OBJECT-TYPE
    SYNTAX       SEQUENCE OF UtsDot3OnuClassifiImportEntry
	MAX-ACCESS   not-accessible
	STATUS       current
	DESCRIPTION
	   "A list of import classification profile information."
    ::= { utsDot3OnuObjects 21 }

utsDot3OnuClassifiImportEntry  OBJECT-TYPE
    SYNTAX       UtsDot3OnuClassifiImportEntry
	MAX-ACCESS   not-accessible
	STATUS       current
	DESCRIPTION
	   "An entry in classification profile import table."
	INDEX {  utsDot3OnuClassifiImportClassId}
    ::= { utsDot3OnuClassifiImportTable 1 }

UtsDot3OnuClassifiImportEntry ::=
    SEQUENCE {
	    utsDot3OnuClassifiImportClassId     INTEGER,
	    utsDot3OnuClassifiImportFileName      DisplayString,
	    utsDot3OnuClassifiImportStatus        RowStatus
}

utsDot3OnuClassifiImportClassId  OBJECT-TYPE
    SYNTAX         INTEGER
	MAX-ACCESS     read-create
	STATUS         current
	DESCRIPTION
	   "The index to this classification profile import entry."
	::= { utsDot3OnuClassifiImportEntry 1 }

utsDot3OnuClassifiImportFileName  OBJECT-TYPE
    SYNTAX         DisplayString(SIZE(1..63))
	MAX-ACCESS     read-create
	STATUS         current
	DESCRIPTION
	   "The profile name associate with this classification profile import entry."
	::= { utsDot3OnuClassifiImportEntry 2 }

utsDot3OnuClassifiImportStatus  OBJECT-TYPE
    SYNTAX         RowStatus
	MAX-ACCESS     read-create
	STATUS         current
	DESCRIPTION
	   "The profile name associate with this classification profile import entry."
	::= { utsDot3OnuClassifiImportEntry 3 }

-- ONU loopback group

utsDot3Onu2CtcLpBkGroup OBJECT IDENTIFIER ::= { utsDot3OnuObjects 22 }

utsDot3Onu2LpBkModuleId OBJECT-TYPE
SYNTAX  INTEGER
       MAX-ACCESS  read-write
       STATUS  current
       DESCRIPTION
"Module ID"
        ::= { utsDot3Onu2CtcLpBkGroup 1 }

utsDot3Onu2LpBkDeviceId OBJECT-TYPE
SYNTAX  INTEGER
       MAX-ACCESS  read-write
       STATUS  current
       DESCRIPTION
"OLT device ID"
        ::= { utsDot3Onu2CtcLpBkGroup 2 }

utsDot3Onu2LpBkPortId OBJECT-TYPE
SYNTAX  INTEGER
       MAX-ACCESS  read-write
       STATUS  current
       DESCRIPTION
"OLT port ID"
        ::= { utsDot3Onu2CtcLpBkGroup 3 }

utsDot3Onu2LpBkLogicalPortId OBJECT-TYPE
SYNTAX  INTEGER
       MAX-ACCESS  read-write
       STATUS  current
       DESCRIPTION
"Logical port ID"
        ::= { utsDot3Onu2CtcLpBkGroup 4 }

utsDot3Onu2LpBkMode OBJECT-TYPE
		SYNTAX  INTEGER
		{
		  local(1),
		  remote(2)
		}
		MAX-ACCESS  read-write
		STATUS  current
		DESCRIPTION
			" loopback mode"
        ::= { utsDot3Onu2CtcLpBkGroup 5 }

utsDot3Onu2LpBkPacketSize OBJECT-TYPE
		SYNTAX  INTEGER(64..1500)
		MAX-ACCESS  read-write
		STATUS  current
		DESCRIPTION
			"loopback packet size"
        ::= { utsDot3Onu2CtcLpBkGroup 6 }

utsDot3Onu2LpBkPacketNum OBJECT-TYPE
		SYNTAX  INTEGER(1..65535)
		MAX-ACCESS  read-write
		STATUS  current
		DESCRIPTION
			"loopback packet number"
        ::= { utsDot3Onu2CtcLpBkGroup 7 }

utsDot3Onu2LpBkStart OBJECT-TYPE
		SYNTAX  TruthValue
		MAX-ACCESS  read-write
		STATUS  current
		DESCRIPTION
			"loopback test start or not"
        ::= { utsDot3Onu2CtcLpBkGroup 8 }

-- utsDot3Onu2LpBkEnd OBJECT-TYPE
--		SYNTAX  TruthValue
--		MAX-ACCESS  read-write
--		STATUS  current
--		DESCRIPTION
--			"loopback test stop or not"
--        ::= { utsDot3Onu2CtcLpBkGroup 9 }

utsDot3Onu2LpBkResult OBJECT-TYPE
		SYNTAX  OCTET STRING
		MAX-ACCESS  read-write
		STATUS  current
		DESCRIPTION
			"loopback test result, like:
			 Out of Seqance frames: 0
			 99 packets transmitted, 99 received, 0% packet loss
			 rtt min/avg/max = 0/0/0 ms"
        ::= { utsDot3Onu2CtcLpBkGroup 10 }

--
-- Selective QinQ Table, added by tomsong in 2008.7.21
--

utsDot3Onu2SelectiveQinQTable OBJECT-TYPE
SYNTAX  SEQUENCE OF UtsDot3Onu2SelectiveQinQEntry
        MAX-ACCESS  not-accessible
        STATUS  current
        DESCRIPTION
"Table for dot3 ONU Selective QinQ MIBs."
        ::= { utsDot3OnuObjects 23 }

utsDot3Onu2SelectiveQinQEntry OBJECT-TYPE
SYNTAX  UtsDot3Onu2SelectiveQinQEntry
       MAX-ACCESS  not-accessible
       STATUS  current
       DESCRIPTION
"An entry in the dot3 Onu Selective QinQ MIBs table."
       INDEX  { utsDot3OnuSelectiveQinQModuleId,utsDot3OnuSelectiveQinQDeviceId,utsDot3OnuSelectiveQinQPortId,utsDot3OnuSelectiveQinQLogicalPortId,utsDot3OnuSelectiveQinQEtherType,utsDot3OnuSelectiveQinQCos,utsDot3OnuSelectiveQinQStartCVID,utsDot3OnuSelectiveQinQEndCVID}
       ::= { utsDot3Onu2SelectiveQinQTable 1 }

UtsDot3Onu2SelectiveQinQEntry ::=
       SEQUENCE {
               utsDot3OnuSelectiveQinQModuleId		     INTEGER,
               utsDot3OnuSelectiveQinQDeviceId           INTEGER,
               utsDot3OnuSelectiveQinQPortId		     INTEGER,
               utsDot3OnuSelectiveQinQLogicalPortId	     INTEGER,
               utsDot3OnuSelectiveQinQEtherType          INTEGER,
               utsDot3OnuSelectiveQinQCos                INTEGER,
               utsDot3OnuSelectiveQinQStartCVID          INTEGER,
               utsDot3OnuSelectiveQinQEndCVID            INTEGER,
               utsDot3OnuSelectiveQinQSVID               INTEGER,
               utsDot3OnuSelectiveQinQSCosSourceSelect   INTEGER,
--               utsDot3OnuSelectiveQinQSTPID              INTEGER,
               utsDot3OnuSelectiveQinQSAppointCos        INTEGER,
               utsDot3OnuSelectiveQinQRowStatus          RowStatus
        }

utsDot3OnuSelectiveQinQModuleId OBJECT-TYPE
SYNTAX  INTEGER
       MAX-ACCESS  not-accessible
       STATUS  current
       DESCRIPTION
"A read only value to identifiy the OLT module id for the current ONU."
        ::= { utsDot3Onu2SelectiveQinQEntry 1 }

utsDot3OnuSelectiveQinQDeviceId OBJECT-TYPE
SYNTAX  INTEGER
       MAX-ACCESS  not-accessible
       STATUS  current
       DESCRIPTION
"A read only value to identifiy the OLT device id for the current ONU."
        ::= { utsDot3Onu2SelectiveQinQEntry 2 }

utsDot3OnuSelectiveQinQPortId OBJECT-TYPE
SYNTAX  INTEGER
       MAX-ACCESS  not-accessible
       STATUS  current
       DESCRIPTION
"A read only value to identifiy the OLT port id for the current ONU."
        ::= { utsDot3Onu2SelectiveQinQEntry 3 }

utsDot3OnuSelectiveQinQLogicalPortId OBJECT-TYPE
SYNTAX  INTEGER
       MAX-ACCESS  not-accessible
       STATUS  current
       DESCRIPTION
"A read only value to identifiy the logical port id for the current ONU."
        ::= { utsDot3Onu2SelectiveQinQEntry 4 }

utsDot3OnuSelectiveQinQEtherType OBJECT-TYPE
      SYNTAX      INTEGER
      MAX-ACCESS  not-accessible
      STATUS      current
      DESCRIPTION
         "The value of ethertype,eg,ARP - 0x0806, ECMA - 0x0803, IP - 0x0800, the value should be from
          0x0 to 0xfffe, 0xffff means do not set this area,all match."
      ::= { utsDot3Onu2SelectiveQinQEntry 5 }

utsDot3OnuSelectiveQinQCos OBJECT-TYPE
      SYNTAX      INTEGER
      MAX-ACCESS  not-accessible
      STATUS      current
      DESCRIPTION
         "The value should be from 0 to 8, 0 to 7 means in fact value in 802.1p, the 8 means do not care this area,all match."
      ::= { utsDot3Onu2SelectiveQinQEntry 6 }

utsDot3OnuSelectiveQinQStartCVID OBJECT-TYPE
      SYNTAX      INTEGER
      MAX-ACCESS  not-accessible
      STATUS      current
      DESCRIPTION
         "The value should be from 0 to 4095, 0 to 4094 means in fact value in 802.1q, the 4095 means do not care this area,all match."
      ::= { utsDot3Onu2SelectiveQinQEntry 7 }

utsDot3OnuSelectiveQinQEndCVID OBJECT-TYPE
      SYNTAX      INTEGER
      MAX-ACCESS  not-accessible
      STATUS      current
      DESCRIPTION
         "The value should be from 0 to 4095, 0 to 4094 means in fact value in 802.1q, the 4095 means do not care this area,all match."
      ::= { utsDot3Onu2SelectiveQinQEntry 8 }

utsDot3OnuSelectiveQinQSVID OBJECT-TYPE
      SYNTAX      INTEGER
      MAX-ACCESS  read-create
      STATUS      current
      DESCRIPTION
         "The value should be from 0 to 4095."
      ::= { utsDot3Onu2SelectiveQinQEntry 9 }

utsDot3OnuSelectiveQinQSCosSourceSelect OBJECT-TYPE
      SYNTAX      INTEGER
      {
      	copyfromctag(1),              -- the STAG Cos is copy from CTAG Cos
      	usingappointnewvalue(2)       -- the STAG Cos is using the appint value from configuration
      }
      MAX-ACCESS  read-create
      STATUS      current
      DESCRIPTION
         "The STAG Cos Source Select."
      ::= { utsDot3Onu2SelectiveQinQEntry 10 }

--utsDot3OnuSelectiveQinQSTPID OBJECT-TYPE
--      SYNTAX      INTEGER
--      MAX-ACCESS  read-create
--      STATUS      current
--      DESCRIPTION
--         "The TPID for STAG, the 0xFFFF means do not adpot this value in the packet, using the system define TPID value or default TPID value."
--      ::= { utsDot3Onu2SelectiveQinQEntry 10 }

utsDot3OnuSelectiveQinQSAppointCos OBJECT-TYPE
      SYNTAX      INTEGER
      MAX-ACCESS  read-create
      STATUS      current
      DESCRIPTION
         "The Cos for STAG when source select is usingappointnewvalue in utsDot3OnuSelectiveQinQSCosSourceSelect, the value shoud be from 0 to 7."
      ::= { utsDot3Onu2SelectiveQinQEntry 11 }

utsDot3OnuSelectiveQinQRowStatus OBJECT-TYPE
      SYNTAX         RowStatus
      MAX-ACCESS     read-create
      STATUS         current
      DESCRIPTION
         "Row status for the current entry. "
      ::= { utsDot3Onu2SelectiveQinQEntry 12 }

-- unbound ONU table
--

utsDot3UnboundOnuObjects OBJECT IDENTIFIER ::= { utsDot3OnuMIB 2}

utsDot3UnboundOnuTable OBJECT-TYPE
SYNTAX  SEQUENCE OF UtsDot3UnboundOnuEntry
        MAX-ACCESS  not-accessible
        STATUS  current
        DESCRIPTION
"Table for dot3 ONU MIBs."
        ::= { utsDot3UnboundOnuObjects 1 }

utsDot3UnboundOnuEntry OBJECT-TYPE
SYNTAX  UtsDot3UnboundOnuEntry
       MAX-ACCESS  not-accessible
       STATUS  current
       DESCRIPTION
"An entry in the dot3 Onu MIBs table."
       INDEX  { utsDot3UnboundOnuModuleId, utsDot3UnboundOnuPortId, utsDot3UnboundOnuLlid }
       ::= { utsDot3UnboundOnuTable 1 }

UtsDot3UnboundOnuEntry ::=
       SEQUENCE {
               utsDot3UnboundOnuModuleId		INTEGER,
               utsDot3UnboundOnuPortId			INTEGER,
               utsDot3UnboundOnuLlid			INTEGER,
   	           utsDot3UnboundOnuPonMacAddr	    MacAddress
       }


utsDot3UnboundOnuModuleId OBJECT-TYPE
SYNTAX  INTEGER
       MAX-ACCESS  read-only
       STATUS  current
       DESCRIPTION
"A read only value to identifiy the OLT module id for the current ONU."
        ::= { utsDot3UnboundOnuEntry 1 }

utsDot3UnboundOnuPortId OBJECT-TYPE
SYNTAX  INTEGER
       MAX-ACCESS  read-only
       STATUS  current
       DESCRIPTION
"A read only value to identifiy the OLT port id for the current ONU."
        ::= { utsDot3UnboundOnuEntry 2 }


utsDot3UnboundOnuLlid OBJECT-TYPE
SYNTAX  INTEGER
       MAX-ACCESS  read-only
       STATUS  current
       DESCRIPTION
"A read only value to identifiy the LLID for the current ONU."
        ::= { utsDot3UnboundOnuEntry 3 }

utsDot3UnboundOnuPonMacAddr OBJECT-TYPE
SYNTAX  MacAddress
   MAX-ACCESS  read-only
   STATUS  current
   DESCRIPTION
"A read only value to identifiy the Mac Address for the current ONU."
        ::= { utsDot3UnboundOnuEntry 4 }


--
--  ONU switch management table
--

utsDot3OnuSwitchObjects OBJECT IDENTIFIER ::= { utsDot3OnuMIB 3}

utsDot3OnuSwitchTable OBJECT-TYPE
SYNTAX  SEQUENCE OF UtsDot3OnuSwitchEntry
        MAX-ACCESS  not-accessible
        STATUS  current
        DESCRIPTION
  "Table for dot3 ONU Switch MIBs."
        ::= { utsDot3OnuSwitchObjects 1 }




utsDot3OnuSwitchEntry OBJECT-TYPE
SYNTAX  UtsDot3OnuSwitchEntry
       MAX-ACCESS  not-accessible
       STATUS  current
       DESCRIPTION
"An entry in the dot3 Onu switch MIBs table."
       INDEX  { utsDot3OnuSwitchModuleId, utsDot3OnuSwitchPortId, utsDot3OnuSwitchOnuId }
       ::= { utsDot3OnuSwitchTable 1 }



UtsDot3OnuSwitchEntry ::=
       SEQUENCE {
               utsDot3OnuSwitchModuleId     INTEGER,
               utsDot3OnuSwitchPortId     INTEGER,
               utsDot3OnuSwitchOnuId         INTEGER,
               utsDot3OnuSwitchMngStatus    INTEGER,
            utsDot3OnuSwitchIpAddress    IpAddress,
            utsDot3OnuSwtichType         INTEGER,
            utsDot3OnuSwitchFirmwareVer  OCTET STRING,
            utsDot3OnuSwitchMacAddr      MacAddress,
            utsDot3OnuSwitchMngVlan         INTEGER,
            utsDot3OnuSwitchRowStatus         RowStatus
       }




utsDot3OnuSwitchModuleId OBJECT-TYPE
SYNTAX  INTEGER
       MAX-ACCESS  not-accessible
       STATUS  current
       DESCRIPTION
"A read only value to identifiy the OLT module id for the current ONU."
        ::= { utsDot3OnuSwitchEntry 1 }



utsDot3OnuSwitchPortId OBJECT-TYPE
SYNTAX  INTEGER
       MAX-ACCESS  not-accessible
       STATUS  current
       DESCRIPTION
"A read only value to identifiy the OLT port id for the current ONU."
        ::= { utsDot3OnuSwitchEntry 2 }




utsDot3OnuSwitchOnuId OBJECT-TYPE
SYNTAX  INTEGER
       MAX-ACCESS  not-accessible
       STATUS  current
       DESCRIPTION
"A read only value to identifiy the ONU ID for the current ONU."
        ::= { utsDot3OnuSwitchEntry 3 }



utsDot3OnuSwitchMngStatus OBJECT-TYPE
   SYNTAX  INTEGER
   {
    autoConfigured(1),    -- IP assigned by DHCP
    manualConfigured(2)   -- IP manual configured
   }
   MAX-ACCESS  read-only
   STATUS  current

   DESCRIPTION
      "Entry status for management."
   ::= { utsDot3OnuSwitchEntry 4 }




utsDot3OnuSwitchIpAddress OBJECT-TYPE
   SYNTAX  IpAddress
   MAX-ACCESS  read-create
   STATUS  current
   DESCRIPTION
      "ONU Switch IP address, if manual configured, a host route should be added for this IP"
   ::= { utsDot3OnuSwitchEntry 5 }



utsDot3OnuSwtichType OBJECT-TYPE
   SYNTAX  INTEGER
   {
	    onu100(1),
			onu1000B(2),
			onu1000C(3),
			onu200A(4),
			onu200B(5),
			onu2024(6),
			onu2004(7),
		  onu101K(8),
		  onu301(9),
		  onu301C(10),
		  onu404(11),
		  onu404C(12),
		  onu804(13),
		  onu804C(14),
		  onu1001C(15),
			onu3004(16),
	    onu1001i(17),
	    onu2004i(18),
	    onu404i(19),
	    clt2060(20),
	    onu204i(21),
	    onu208i(22),
	    onu204h(23),
	    onu408t(24),
	    onu2024i(25),
	    onub210(26),
	    onu1001h(27),
	    onub220(28),
	    onu804i(29),
	    onu101(30),
	    onu1001b(31),
	    onu2004h(32),
	    onu204d(33),
	    onu404t(34),
	    onu4024t(35),
	    onu4024i(36),
        onu101i(38),
        onub1205y(39),
        onub1205d(40),
        onub130(41),
	    tkOnu(100),
	    pmcOnu(101),
	    unknow(200)
 }
   MAX-ACCESS  read-only
   STATUS  current
   DESCRIPTION
      "ONU Switch MAC address"
   ::= { utsDot3OnuSwitchEntry 6 }



utsDot3OnuSwitchFirmwareVer OBJECT-TYPE
   SYNTAX  OCTET STRING
   MAX-ACCESS  read-only
   STATUS  current
   DESCRIPTION
      "ONU Switch Firmware version"
   ::= { utsDot3OnuSwitchEntry 7 }



utsDot3OnuSwitchMacAddr OBJECT-TYPE
   SYNTAX  MacAddress
   MAX-ACCESS  read-only
   STATUS  current
   DESCRIPTION
      "ONU Switch MAC address"
   ::= { utsDot3OnuSwitchEntry 8 }



utsDot3OnuSwitchMngVlan OBJECT-TYPE
   SYNTAX  INTEGER(1..4094)
   MAX-ACCESS  read-create
   STATUS  current
   DESCRIPTION
      "ONU Switch management VLAN"
   ::= { utsDot3OnuSwitchEntry 9 }



utsDot3OnuSwitchRowStatus  OBJECT-TYPE
    SYNTAX         RowStatus
 MAX-ACCESS     read-create
 STATUS         current
 DESCRIPTION
    "Row Status of this entry"
 ::= { utsDot3OnuSwitchEntry 10 }





------
------ 3. ONU OAM
------


utsDot3OnuOamMIB OBJECT IDENTIFIER ::= { utsEponConfExtObjects 3}

utsDot3OnuOamObjects OBJECT IDENTIFIER ::= { utsDot3OnuOamMIB 1}

utsDot3OnuOamTable OBJECT-TYPE
SYNTAX  SEQUENCE OF UtsDot3OnuOamEntry
        MAX-ACCESS  not-accessible
        STATUS  current
        DESCRIPTION
"Table for dot3 ONU OAM MIBs."
        ::= { utsDot3OnuOamObjects 1 }

utsDot3OnuOamEntry OBJECT-TYPE
SYNTAX  UtsDot3OnuOamEntry
       MAX-ACCESS  not-accessible
       STATUS  current
       DESCRIPTION
"An entry in the dot3 Onu OAM MIBs table."
       INDEX  { ifIndex }
       ::= { utsDot3OnuOamTable 1 }

UtsDot3OnuOamEntry ::=
       SEQUENCE {

                    utsDot3OnuOAMModuleId							INTEGER,
                    utsDot3OnuOAMPortId							INTEGER,
                    utsDot3OnuOAMLogicalPortId					INTEGER,
                    utsDot3OnuOAMMode								INTEGER,

                    utsDot3OnuOAMDeviceIdentifier				INTEGER,
                    utsDot3OnuOAMVersionIdentifier				INTEGER,

                    utsDot3OnuOAMLinktestTotalFrame			INTEGER,
                    utsDot3OnuOAMLinktestFrameSize				INTEGER,
                    utsDot3OnuOAMLinktestDelayMeasureEnable	TruthValue,
                    utsDot3OnuOAMLinktestVLANTagEnable		TruthValue,
                    utsDot3OnuOAMLinktestVLANTagPriority		INTEGER,
                    utsDot3OnuOAMLinktestVLANTagVID         INTEGER,
                    utsDot3OnuOAMLinktestFrameSent          INTEGER,
                    utsDot3OnuOAMLinktestFrameReceived      INTEGER,
                    utsDot3OnuOAMLinktestErrFrameReceived   INTEGER,
                    utsDot3OnuOAMLinktestMinDelay      		INTEGER,
                    utsDot3OnuOAMLinktestMeanDelay          INTEGER,
                    utsDot3OnuOAMLinktestMaxDelay      		INTEGER,

             --       utsDot3OnuOAMPingStart          		TruthValue,
                    utsDot3OnuOAMPingElapsedTime  				INTEGER,

                    utsDot3OnuOAMPortState               	INTEGER,
                    utsDot3OnuOAMStartTest                	INTEGER,
                    utsDot3OnuOAMLinkTestStatus           	UtsConfStatusType,
					  		utsDot3OnuOAMLinkTestStationId       	UtsConfStationIdType,
					  		utsDot3OnuOAMLinkTestResultStr       	DisplayString,
                     utsDot3OnuOAMPingStatus            		UtsConfStatusType,
					  		utsDot3OnuOAMPingStationId         		UtsConfStationIdType,
					  		utsDot3OnuOAMPingResultStr         		DisplayString
              --      utsDot3OnuOAMLoopbackStatus        	UtsConfStatusType,
              --      utsDot3OnuOAMLinktestStatus        	UtsConfStatusType,
              --      utsDot3OnuOAMPingStatus            	UtsConfStatusType,
              --      utsDot3OnuOAMLinktestStationId     	UtsConfStationIdType,
              --      utsDot3OnuOAMPingStationId         	UtsConfStationIdType,
              --      utsDot3OnuOAMLoopbackStationId     	UtsConfStationIdType
         }

utsDot3OnuOAMModuleId OBJECT-TYPE
SYNTAX  INTEGER
         MAX-ACCESS  read-only
         STATUS  current
         DESCRIPTION
   "A read only value to identify OLT module id"
          ::= { utsDot3OnuOamEntry 1 }

utsDot3OnuOAMPortId OBJECT-TYPE
SYNTAX  INTEGER
         MAX-ACCESS  read-only
         STATUS  current
         DESCRIPTION
   "A read only value to identify OLT port id"
          ::= { utsDot3OnuOamEntry 2 }

utsDot3OnuOAMLogicalPortId OBJECT-TYPE
SYNTAX  INTEGER
         MAX-ACCESS  read-only
         STATUS  current
         DESCRIPTION
   "A read only value to identify ONU logical port id"
          ::= { utsDot3OnuOamEntry 3 }

utsDot3OnuOAMMode OBJECT-TYPE
SYNTAX  INTEGER {
          passive(1),
          active(2)
}
       MAX-ACCESS  read-only
       STATUS  current
       DESCRIPTION
"OAM mode. Only supports active(2)"
        ::= { utsDot3OnuOamEntry 4 }


utsDot3OnuOAMDeviceIdentifier OBJECT-TYPE
SYNTAX  INTEGER
       MAX-ACCESS  read-only
       STATUS  current
       DESCRIPTION
"MAC Vendor products identifier."
        ::= { utsDot3OnuOamEntry 9 }

utsDot3OnuOAMVersionIdentifier OBJECT-TYPE
SYNTAX  INTEGER
       MAX-ACCESS  read-only
       STATUS  current
       DESCRIPTION
"Identifier which distinguishes between versions of a particular vendor
product. In a case of Passave ONU - ONU Hardware major version."
        ::= { utsDot3OnuOamEntry 10 }

utsDot3OnuOAMLinktestTotalFrame OBJECT-TYPE
SYNTAX  INTEGER (0..1000)
       MAX-ACCESS  read-write
       STATUS  current
       DESCRIPTION
"Total number of frames to be sent during link test.
 0     -- stop link test operation,
 other -- number of link test frame to be sent."
        ::= { utsDot3OnuOamEntry 23 }

utsDot3OnuOAMLinktestFrameSize OBJECT-TYPE
	SYNTAX  INTEGER (60..1514)
   MAX-ACCESS  read-write
   STATUS  current
   DESCRIPTION
		"Measurement frames data size, measured in bytes. Not including
		 Preamble, SFD, and FCS. 60 - 1514."
   ::= { utsDot3OnuOamEntry 24 }

utsDot3OnuOAMLinktestDelayMeasureEnable OBJECT-TYPE
SYNTAX  TruthValue
       MAX-ACCESS  read-only
       STATUS  current
       DESCRIPTION
"Link test includes delay measurement, which corresponds to the difference
between sent and received times (including granting delay and firmware
processing time overheads)."
        ::= { utsDot3OnuOamEntry 25 }

utsDot3OnuOAMLinktestVLANTagEnable OBJECT-TYPE
SYNTAX  TruthValue
       MAX-ACCESS  read-only
       STATUS  current
       DESCRIPTION
"Enable VLAN tag in link test frames."
        ::= { utsDot3OnuOamEntry 26 }

utsDot3OnuOAMLinktestVLANTagPriority OBJECT-TYPE
SYNTAX  INTEGER
       MAX-ACCESS  read-only
       STATUS  current
       DESCRIPTION
"Priority in VLAN tag. 0 - 7."
        ::= { utsDot3OnuOamEntry 27 }

utsDot3OnuOAMLinktestVLANTagVID OBJECT-TYPE
SYNTAX  INTEGER
       MAX-ACCESS  read-only
       STATUS  current
       DESCRIPTION
"VLAN ID in VLAN tag. 0 - 4094."
        ::= { utsDot3OnuOamEntry 28 }

utsDot3OnuOAMLinktestFrameSent OBJECT-TYPE
SYNTAX  INTEGER
       MAX-ACCESS  read-only
       STATUS  current
       DESCRIPTION
"Number of measurement frames sent during the test."
        ::= { utsDot3OnuOamEntry 29 }

utsDot3OnuOAMLinktestFrameReceived OBJECT-TYPE
SYNTAX  INTEGER
       MAX-ACCESS  read-only
       STATUS  current
       DESCRIPTION
"Number of measurement frames including error frames received during the test."
        ::= { utsDot3OnuOamEntry 30 }

utsDot3OnuOAMLinktestErrFrameReceived OBJECT-TYPE
SYNTAX  INTEGER
       MAX-ACCESS  read-only
       STATUS  current
       DESCRIPTION
"Number of measurement error frames received during the test."
        ::= { utsDot3OnuOamEntry 31 }

utsDot3OnuOAMLinktestMinDelay OBJECT-TYPE
SYNTAX  INTEGER
       MAX-ACCESS  read-only
       STATUS  current
       DESCRIPTION
"The minimal delay collected from link delay measurements measured in TQ units.
Relevant only if link delay measurement is enabled and the test is completed
within current command."
        ::= { utsDot3OnuOamEntry 32 }

utsDot3OnuOAMLinktestMeanDelay OBJECT-TYPE
    SYNTAX  INTEGER
    MAX-ACCESS  read-only
    STATUS  current
    DESCRIPTION
        "The mean delay collected from link delay measurements measured in TQ units.
         Relevant only if link delay measurement is enabled and the test is completed
         within current command."
        ::= { utsDot3OnuOamEntry 33 }

utsDot3OnuOAMLinktestMaxDelay OBJECT-TYPE
SYNTAX  INTEGER
       MAX-ACCESS  read-only
       STATUS  current
       DESCRIPTION
"The maximal delay collected from link delay measurements measured in TQ units.
Relevant only if link delay measurement is enabled and the test is completed
within current command."
        ::= { utsDot3OnuOamEntry 34 }

-- utsDot3OnuOAMPingStart OBJECT-TYPE
--     SYNTAX  TruthValue
--     MAX-ACCESS  read-write
--     STATUS  current
--     DESCRIPTION
--          "Start ping with PAS-SOFT simulates ping data (60 bytes)."
--       ::= { utsDot3OnuOamEntry 35 }

utsDot3OnuOAMPingElapsedTime OBJECT-TYPE
	SYNTAX  INTEGER
   MAX-ACCESS  read-only
   STATUS  current
   DESCRIPTION
      "Total Ping time, not including PAS_SOFT overhead. Measured in Milliseconds.
       -1 - timeout, 0 - below time measurement resolution, 1-32767 - Total Ping time."
   ::= { utsDot3OnuOamEntry 36 }

utsDot3OnuOAMPortState OBJECT-TYPE
    SYNTAX  INTEGER {
        onuOAMOk (1),
        onuOAMnotRunning(2)     -- ONU is not OK or not attched
    }
    MAX-ACCESS  read-only
    STATUS  current
    DESCRIPTION
        "Indicates if the ONU state is OK or not."
    ::= { utsDot3OnuOamEntry 37 }

utsDot3OnuOAMStartTest OBJECT-TYPE
    SYNTAX  INTEGER {
        onuloopbacktest(1),
        onulinktest(2),
        onupingtest(3)
    }
    MAX-ACCESS  read-write
    STATUS  current
    DESCRIPTION
        "Write corresponding value to this variable will start the corresponding
        Onu OAM test."
    ::= { utsDot3OnuOamEntry 38 }

utsDot3OnuOAMLinkTestStatus OBJECT-TYPE
    SYNTAX  UtsConfStatusType
    MAX-ACCESS  read-only
    STATUS  current
    DESCRIPTION
        "Onu OAM Link Test status"
    ::= { utsDot3OnuOamEntry 39 }

utsDot3OnuOAMLinkTestStationId OBJECT-TYPE
    SYNTAX  UtsConfStationIdType
    MAX-ACCESS  read-write
    STATUS  current
    DESCRIPTION
        "Station id, a string used to identify the issuer of Link Test."
    ::= { utsDot3OnuOamEntry 40 }

utsDot3OnuOAMLinkTestResultStr OBJECT-TYPE
    SYNTAX  DisplayString
	MAX-ACCESS read-only
	STATUS  current
	DESCRIPTION
	    "A string that describes the result of OAM Link Test."
	::= { utsDot3OnuOamEntry 41 }

utsDot3OnuOAMPingStatus OBJECT-TYPE
    SYNTAX  UtsConfStatusType
    MAX-ACCESS  read-only
    STATUS  current
    DESCRIPTION
        "Onu OAM Test status"
    ::= { utsDot3OnuOamEntry 42 }

utsDot3OnuOAMPingStationId OBJECT-TYPE
    SYNTAX  UtsConfStationIdType
    MAX-ACCESS  read-write
    STATUS  current
    DESCRIPTION
        "Station id, a string used to identify the issuer of OAM Ping Test."
    ::= { utsDot3OnuOamEntry 43 }

utsDot3OnuOAMPingResultStr OBJECT-TYPE
   SYNTAX  DisplayString
	MAX-ACCESS read-only
	STATUS  current
	DESCRIPTION
	    "A string that describes the result of OAM Ping Test."
	::= { utsDot3OnuOamEntry 44 }

------
------ 4. DBA
------

utsDot3DbaMIB OBJECT IDENTIFIER ::= { utsEponConfExtObjects 4}

utsDot3DbaOltObjects OBJECT IDENTIFIER ::= { utsDot3DbaMIB 1}

utsDot3DbaOltTable OBJECT-TYPE
SYNTAX  SEQUENCE OF UtsDot3DbaOltEntry
        MAX-ACCESS  not-accessible
        STATUS  current
        DESCRIPTION
"Table for dot3 Dba MIBs."
        ::= { utsDot3DbaOltObjects 1 }

utsDot3DbaOltEntry OBJECT-TYPE
SYNTAX  UtsDot3DbaOltEntry
       MAX-ACCESS  not-accessible
       STATUS  current
       DESCRIPTION
"An entry in the dot3 Dba MIBs table."
       INDEX  { ifIndex }
       ::= { utsDot3DbaOltTable 1 }

UtsDot3DbaOltEntry ::=
       SEQUENCE
       {
          utsDot3DbaOltModuleId				INTEGER,
          utsDot3DbaOltPortId					INTEGER,
          utsDot3DbaOltAlgorithm				INTEGER,
          utsDot3DbaOltDiscoverySize		INTEGER,
          utsDot3DbaOltDiscoveryFreq		INTEGER,
          utsDot3DbaOltCycleSize				INTEGER,
          utsDot3DbaOltPlatoCycleSize		INTEGER,
          utsDot3DbaOltPlatoDiscoveryFreq	INTEGER
       }

utsDot3DbaOltModuleId OBJECT-TYPE
SYNTAX  INTEGER
       MAX-ACCESS  read-only
       STATUS  current
       DESCRIPTION
"A read only value to identidy OLT module id"
        ::= { utsDot3DbaOltEntry 1 }

utsDot3DbaOltPortId OBJECT-TYPE
SYNTAX  INTEGER
       MAX-ACCESS  read-only
       STATUS  current
       DESCRIPTION
"A read only value to identidy OLT port id"
        ::= { utsDot3DbaOltEntry 2 }


utsDot3DbaOltAlgorithm OBJECT-TYPE
SYNTAX  INTEGER {
          internalEqualShare(1),
          -- aristotle(2),
          -- thales(3),
          -- socrates(4),
          plato(5)
          -- vendorExtension1(6),
          -- vendorExtension2(7),
          -- vendorExtension3(8)
}
       MAX-ACCESS  read-write
       STATUS  current
       DESCRIPTION
"DBA algorithm for specific OLT. Select 'internalEqualShare' can also be used to stop
any other external DBA algorithms. For now, only internalEqualShare(1) and plato(5) supported"
        ::= { utsDot3DbaOltEntry 3 }

utsDot3DbaOltDiscoverySize OBJECT-TYPE
SYNTAX  INTEGER (0..65535)
       MAX-ACCESS  read-write
       STATUS  current
       DESCRIPTION
"Discovery grant length. Default value is 1792 (0x700) TQ."
        ::= { utsDot3DbaOltEntry 4 }

utsDot3DbaOltDiscoveryFreq OBJECT-TYPE
SYNTAX  INTEGER (0..65535)
       MAX-ACCESS  read-write
       STATUS  current
       DESCRIPTION
"How often the OLT should send discovery frames to the ONUs, measured in
grant cycles. Default value is 500."
        ::= { utsDot3DbaOltEntry 5 }

utsDot3DbaOltCycleSize OBJECT-TYPE
SYNTAX  INTEGER (16384..131072)
       MAX-ACCESS  read-write
       STATUS  current
       DESCRIPTION
"Grant cycle size, measured in TQ. The default value is 0x50000.
 For PLATO version 2.0 or above, this paramter is not configurable."
        ::= { utsDot3DbaOltEntry 6 }

utsDot3DbaOltPlatoCycleSize OBJECT-TYPE
SYNTAX  INTEGER (1..255)
       MAX-ACCESS  read-write
       STATUS  current
       DESCRIPTION
"PLATO Grant cycle size, measured in 50us. only used when dba algorithm is plato,
 and default value is 10. For PLATO version 2.0 or above, this paramter is not configurable."
        ::= { utsDot3DbaOltEntry 7 }

utsDot3DbaOltPlatoDiscoveryFreq OBJECT-TYPE
SYNTAX  INTEGER (1..255)
       MAX-ACCESS  read-write
       STATUS  current
       DESCRIPTION
"How often the OLT should send discovery frames to the ONUs when olt use plato dba algorithm, measured in
grant cycles. Default value is 50."
        ::= { utsDot3DbaOltEntry 8 }

--
--dba sla
--


utsDot3DbaSlaObjects OBJECT IDENTIFIER ::= { utsDot3DbaMIB 2}

utsDot3DbaSlaTable OBJECT-TYPE
   SYNTAX  SEQUENCE OF UtsDot3DbaSlaEntry
   MAX-ACCESS  not-accessible
   STATUS  current
   DESCRIPTION
   "Table for dot3 ONU SLA MIBs."
   ::= { utsDot3DbaSlaObjects 1 }

utsDot3DbaSlaEntry OBJECT-TYPE
	SYNTAX  UtsDot3DbaSlaEntry
   MAX-ACCESS  not-accessible
   STATUS  current
   DESCRIPTION
		"An entry in the dot3 DBA MIBs table."
   INDEX  { ifIndex }
   ::= { utsDot3DbaSlaTable 1 }

UtsDot3DbaSlaEntry ::=
       SEQUENCE
       {
          utsDot3DbaSlaModuleId			  	   INTEGER,
          utsDot3DbaSlaPortId					   INTEGER,
          utsDot3DbaSlaLogicalPortId		   INTEGER,
          utsDot3DbaSlaUpCommittedBandwidth	INTEGER,
          utsDot3DbaSlaUpMaxBandwidth			INTEGER,
--          utsDot3DbaSlaMaxBurstSize			INTEGER,
          utsDot3DbaSlaVLANID                INTEGER,
          utsDot3DbaSlaUNIMaxMACAddress      INTEGER,
          utsDot3DbaSlaIPAddress				   IpAddress,
          utsDot3DbaSlaSubnetMask			   IpAddress,
          utsDot3DbaSlaCallingStationId      OCTET STRING,
          utsDot3DbaSlaPlatoClass			   INTEGER,
          utsDot3DbaSlaBindingMacAddress	   MacAddress,
          utsDot3DbaSlaDownPolicingEnable	   INTEGER,
          utsDot3DbaSlaDownMaxBandwidth	   INTEGER,
          utsDot3DbaSlaDownMaxBurstSize	   INTEGER,
  --        utsDot3DbaSlaDownHiPriFramePref	   INTEGER,
  --        utsDot3DbaSlaDownShortFramePref	   INTEGER,
          utsDot3DbaSlaP2PPolicingEnable     INTEGER,
          utsDot3DbaSlaP2PPolicingONUList     OCTET STRING,
          utsDot3DbaSlaP2PMaxBandwidth	   INTEGER,
          utsDot3DbaSlaP2PMaxBurstSize	   INTEGER
  --        utsDot3DbaSlaP2PHiPriFramePref	   INTEGER,
  --        utsDot3DbaSlaP2PShortFramePref	   INTEGER

       }


utsDot3DbaSlaModuleId OBJECT-TYPE
	SYNTAX  INTEGER
   MAX-ACCESS  read-only
   STATUS  current
   DESCRIPTION
		"A read only value to identify module ID of the LTM module of the EPON device to which an ONU should be attached."
   ::= { utsDot3DbaSlaEntry 1 }

utsDot3DbaSlaPortId OBJECT-TYPE
	SYNTAX  INTEGER
   MAX-ACCESS  read-only
   STATUS  current
   DESCRIPTION
		"A read only value to identify port number of the OLT of the LTM module of the EPON device to which an ONU should
 		 be attached."
   ::= { utsDot3DbaSlaEntry 2 }

utsDot3DbaSlaLogicalPortId OBJECT-TYPE
	SYNTAX  INTEGER
   MAX-ACCESS  read-only
   STATUS  current
   DESCRIPTION
		"A read only value to identify logical port number of an ONU when it's attached to an OLT."
   ::= { utsDot3DbaSlaEntry 3 }

utsDot3DbaSlaUpCommittedBandwidth OBJECT-TYPE
	SYNTAX  INTEGER (1..1000000)
   MAX-ACCESS  read-write
   STATUS  current
   DESCRIPTION
		"Committed bandwidth for a specific ONU/LLID measured in terms of Kbps, it
		 will be converted into TQ internally. It will be used to control upstream bandwidth."
   ::= { utsDot3DbaSlaEntry 4 }

utsDot3DbaSlaUpMaxBandwidth OBJECT-TYPE
	SYNTAX  INTEGER (1..1000000)
   MAX-ACCESS  read-write
   STATUS  current
   DESCRIPTION
		"Maximal bandwidth for a specific ONU/LLID measured in terms of Kbps, it
		 will be converted into TQ internally. It will be used to control upstream bandwidth."
   ::= { utsDot3DbaSlaEntry 5 }

utsDot3DbaSlaVLANID OBJECT-TYPE
	SYNTAX  INTEGER (1..4094)
   MAX-ACCESS  read-write
   STATUS  current
   DESCRIPTION
		"VLAN ID of an ONU when it's attached to an OLT, writable in layer-2 mode, read-only in layer-3 mode."
   ::= { utsDot3DbaSlaEntry 13 }

utsDot3DbaSlaUNIMaxMACAddress OBJECT-TYPE
	SYNTAX  INTEGER
   MAX-ACCESS  read-write
   STATUS  current
   DESCRIPTION
		"Maximum allowed number of MAC addresses that can be attached to an ONU's UNI.
		One of the following values: 1-16,30, 62, 126, 254, 8190.
		when set to 8190, it means to remove the MAC address limitation."
   DEFVAL { 8190 }
   ::= { utsDot3DbaSlaEntry 14 }

utsDot3DbaSlaIPAddress OBJECT-TYPE
	SYNTAX  IpAddress
   MAX-ACCESS  read-only
   STATUS  current
   DESCRIPTION
		"IP address to be assigned to the device attached to an ONU's UNI."
   ::= { utsDot3DbaSlaEntry 17 }

utsDot3DbaSlaSubnetMask OBJECT-TYPE
	SYNTAX  IpAddress
   MAX-ACCESS  read-only
   STATUS  current
   DESCRIPTION
		"Subnet mask to be assigned to the device attached to an ONU's UNI."
   ::= { utsDot3DbaSlaEntry 18 }

utsDot3DbaSlaCallingStationId OBJECT-TYPE
	SYNTAX  OCTET STRING(SIZE(0..32))
   MAX-ACCESS  read-only
   STATUS  current
   DESCRIPTION
		"Calling station id of an ONU. It may include MAC address plus serial number.
		UNI."
   ::= { utsDot3DbaSlaEntry 23 }

utsDot3DbaSlaPlatoClass		OBJECT-TYPE
	SYNTAX  INTEGER (0..7)
   MAX-ACCESS  read-write
   STATUS  current
   DESCRIPTION
		"Priority of the traffic of an ONU when using plato DBA algorithm."
   ::= { utsDot3DbaSlaEntry 24 }

utsDot3DbaSlaBindingMacAddress        OBJECT-TYPE
	SYNTAX  MacAddress
   MAX-ACCESS  read-write
   STATUS  current
   DESCRIPTION
		"the MacAddress of the onu binded to this logic link id."
   ::= { utsDot3DbaSlaEntry 25 }

-- Down stream policing

utsDot3DbaSlaDownPolicingEnable		OBJECT-TYPE
	SYNTAX  INTEGER
	{
	   enable(1),
	   disable(2)
	}
   MAX-ACCESS  read-write
   STATUS  current
   DESCRIPTION
		"enable or disable down stream policing."
   ::= { utsDot3DbaSlaEntry 26 }

utsDot3DbaSlaDownMaxBandwidth		OBJECT-TYPE
	SYNTAX  INTEGER (0..1000000)
   MAX-ACCESS  read-write
   STATUS  current
   DESCRIPTION
		"Maximum bandwidth allowed(1000000 Kbps for M3, 500,000 Kbps for M4) for the ONU, Kbits/ Sec."
   ::= { utsDot3DbaSlaEntry 27 }

utsDot3DbaSlaDownMaxBurstSize		OBJECT-TYPE
	SYNTAX  INTEGER (0..8192)
   MAX-ACCESS  read-write
   STATUS  current
   DESCRIPTION
		"Maximal number of bytes in a burst, measured in KBytes. The value is truncated to
		 the nearest smaller 128bytes multiple value. default value 256"
   ::= { utsDot3DbaSlaEntry 28 }

-- utsDot3DbaSlaDownHiPriFramePref		OBJECT-TYPE
-- SYNTAX  INTEGER
--	{
--	  enable(1),
--	  disable(2)
--	}
--   MAX-ACCESS  read-write
--   STATUS  current
--   DESCRIPTION
--   "Disable or Enable high priority frames preference."
--   ::= { utsDot3DbaSlaEntry 29 }

-- utsDot3DbaSlaDownShortFramePref		OBJECT-TYPE
--	SYNTAX  INTEGER
--	{
--	  enable(1),
--	  disable(2)
--	}
--   MAX-ACCESS  read-write
--   STATUS  current
--   DESCRIPTION
--		"Disable or enable short frames preference."
--   ::= { utsDot3DbaSlaEntry 30 }


-- P2P stream policing, Zhaoxf added on Dec 25, 2005

utsDot3DbaSlaP2PPolicingEnable		OBJECT-TYPE
	SYNTAX  INTEGER
	{
	   enable(1),
	   disable(2)
	}
   MAX-ACCESS  read-write
   STATUS  current
   DESCRIPTION
		"Enable or disable P2P stream policing."
   ::= { utsDot3DbaSlaEntry 36 }

utsDot3DbaSlaP2PPolicingONUList		OBJECT-TYPE
   SYNTAX OCTET STRING(SIZE(0..8))
   MAX-ACCESS  read-write
   STATUS  current
   DESCRIPTION
		"The ONU logical port list, excluding the current port itself.
		The ONU list bitmap from left to right indicates ONU logical
		port 1..64."
   ::= { utsDot3DbaSlaEntry 37 }

utsDot3DbaSlaP2PMaxBandwidth		OBJECT-TYPE
   SYNTAX  INTEGER (0..1000000)
   MAX-ACCESS  read-write
   STATUS  current
   DESCRIPTION
   		"The maximum bandwidth allowed(1000000 Kbps for M3, 500,000 Kbps for M4) for the ONU, Kbits/ Sec."
   ::= { utsDot3DbaSlaEntry 38 }

utsDot3DbaSlaP2PMaxBurstSize		OBJECT-TYPE
	SYNTAX  INTEGER (0..8192)
   MAX-ACCESS  read-write
   STATUS  current
   DESCRIPTION
		"The maximal number of bytes in a burst, measured in KBytes. The value is truncated to
		 the nearest smaller 128 bytes multiple value. default value 256"
   ::= { utsDot3DbaSlaEntry 39 }



--utsDot3DbaSlaP2PHiPriFramePref		OBJECT-TYPE
--	SYNTAX  INTEGER
--	{
--    enable(1),
--	  disable(2)
--	}
--   MAX-ACCESS  read-write
--   STATUS  current
--   DESCRIPTION
--		"Disable or Enable high priority frames preference."
--   ::= { utsDot3DbaSlaEntry 40 }

-- utsDot3DbaSlaP2PShortFramePref		OBJECT-TYPE
--	SYNTAX  INTEGER
--	{
--	  enable(1),
--	  disable(2)
--	}
--   MAX-ACCESS  read-write
--   STATUS  current
--   DESCRIPTION
--	"Disable or enable short frames preference."
--   ::= { utsDot3DbaSlaEntry 41 }


------
------ 6. VLAN & LLID
------

utsDot3OnuVlanMIB OBJECT IDENTIFIER ::= { utsEponConfExtObjects 6}

-- remove onu vlan table temporarily

--utsDot3OnuVlanObjects OBJECT IDENTIFIER ::= { utsDot3OnuVlanMIB 1}
--
--utsDot3OnuVlanTable OBJECT-TYPE
--SYNTAX  SEQUENCE OF UtsDot3OnuVlanEntry
--        MAX-ACCESS  not-accessible
--        STATUS  current
--        DESCRIPTION
--"Table for dot3 ONU Vlan MIBs."
--        ::= { utsDot3OnuVlanObjects 1 }
--
--utsDot3OnuVlanEntry OBJECT-TYPE
--SYNTAX  UtsDot3OnuVlanEntry
--       MAX-ACCESS  not-accessible
--       STATUS  current
--       DESCRIPTION
--"An entry in the dot3 PLT MIBs table."
--       INDEX  { ifIndex }
--       ::= { utsDot3OnuVlanTable 1 }
--
--UtsDot3OnuVlanEntry ::=
--       SEQUENCE {
--                    utsDot3OnuVlanModuleId				INTEGER,
--                    utsDot3OnuVlanPortId				INTEGER,
--                    utsDot3OnuVlanLogicalPortId				INTEGER,
--                    utsDot3OnuVlanMode				INTEGER,
--                    utsDot3OnuVlanExchangeTagUpLink		INTEGER,
--                    utsDot3OnuVlanExchangeTagDnLinkSuffix	INTEGER,
--                    utsDot3OnuVlanStackTag			INTEGER,
--                    utsDot3OnuVlanStackNestedMode		TruthValue,
--                    utsDot3OnuVlanStackNestedModeVlanType	INTEGER
--       }
--
--
--utsDot3OnuVlanModuleId OBJECT-TYPE
--SYNTAX  INTEGER
--       MAX-ACCESS  read-only
--       STATUS  current
--       DESCRIPTION
--"A read only value to identify OLT module id for the attached ONU"
--        ::= { utsDot3OnuVlanEntry 1 }
--
--utsDot3OnuVlanPortId OBJECT-TYPE
--SYNTAX  INTEGER
--       MAX-ACCESS  read-only
--       STATUS  current
--       DESCRIPTION
--"A read only value to identify OLT port id for the attached ONU"
--        ::= { utsDot3OnuVlanEntry 2 }
--
--utsDot3OnuVlanLogicalPortId OBJECT-TYPE
--SYNTAX  INTEGER
--       MAX-ACCESS  read-only
--       STATUS  current
--       DESCRIPTION
--"A read only value to identify ONU logical id. "
--        ::= { utsDot3OnuVlanEntry 3 }
--
--utsDot3OnuVlanMode OBJECT-TYPE
--SYNTAX  INTEGER {
--          unchange(0),
--          exchange(1),
--          stack(2)
--}
--
--       MAX-ACCESS  read-write
--       STATUS  current
--       DESCRIPTION
--"Handling mode for LLID and VLAN tag. unchange - LLID frames (which may
--contain VLAN tags) are passed unchanged both in downlink and in uplink;
--exchange - LLID frames?VLAN tags are exchanged; stack - LLID frames?VLAN tags are stacked."
--        ::= { utsDot3OnuVlanEntry 4 }
--
--utsDot3OnuVlanExchangeTagUpLink OBJECT-TYPE
--SYNTAX  INTEGER (0..4094)
--       MAX-ACCESS  read-write
--       STATUS  current
--       DESCRIPTION
--"VLAN tag id, applied to exchange handling mode."
--        ::= { utsDot3OnuVlanEntry 5 }
--
--utsDot3OnuVlanExchangeTagDnLinkSuffix OBJECT-TYPE
--SYNTAX  INTEGER (0..15)
--       MAX-ACCESS  read-write
--       STATUS  current
--       DESCRIPTION
--"VLAN tag suffix id used as downlink exchanged tag suffix. The final tag is composed
--of utsDot3OltVlanTagExchangeDnLinkPrefix (8 MSB bits) and
--utsDot3OnuVlanExchangeTagDnLinkSuffix (4 LSB bits). It's applied to exchange
--handling mode."
--        ::= { utsDot3OnuVlanEntry 6 }
--
--utsDot3OnuVlanStackTag OBJECT-TYPE
--SYNTAX  INTEGER (0..4094)
--       MAX-ACCESS  read-write
--       STATUS  current
--       DESCRIPTION
--"Stacked VLAN tag id for both uplink and downlink traffic, applied to stack
--handling mode."
--        ::= { utsDot3OnuVlanEntry 7 }
--
--utsDot3OnuVlanStackNestedMode OBJECT-TYPE
--SYNTAX  TruthValue
--       MAX-ACCESS  read-write
--       STATUS  current
--       DESCRIPTION
--"TRUE - Nested mode - Tag adding to every frame, tagged or untagged. VLAN tag
--is removed from downlink tagged frames with tag equal to utsDot3OnuVlanStackTag;
--FALSE - Service mode - Tag adding to untagged frames only, VLAN tag is removed
--from every downlink tagged frames. It's applied to stack handling mode."
--        ::= { utsDot3OnuVlanEntry 8 }
--
--utsDot3OnuVlanStackNestedModeVlanType OBJECT-TYPE
--SYNTAX  INTEGER {
--          vlanType8100H(0),
--          vlanType9100H(1),
--          vlanTypeOther(2)
--}
--       MAX-ACCESS  read-write
--       STATUS  current
--       DESCRIPTION
--"Nested VLAN type. It's valid only if stack handling mode is selected and
--utsDot3OnuVlanStackNestedMode is TRUE. utsDot3OltVlanStackNestedModeVlanType will
--be used if utsDot3OnuVlanStackNestedModeVlanType is vlanTypeOther."
--        ::= { utsDot3OnuVlanEntry 9 }


-- ===========================================================================
--
--  ONU Firmware Upgrade Table
--
-- ===========================================================================

utsDot3OnuUpgradeMIB OBJECT IDENTIFIER ::= { utsEponConfExtObjects 7}

utsDot3OnuUpgradeStateObjects OBJECT IDENTIFIER ::= { utsDot3OnuUpgradeMIB 1 }

utsDot3OnuUpgradePortListGroup   OBJECT IDENTIFIER ::= { utsDot3OnuUpgradeStateObjects 1 }


utsDot3OnuUpgradeManualPortListStateBitMap OBJECT-TYPE
   SYNTAX  OCTET STRING (SIZE(0..255))
   MAX-ACCESS  read-write
   STATUS  current
   DESCRIPTION
       "Onu firmware upgrade olt port list bit map. BBS1000 has 8 olt ports.
       Each olt port can connect up to 32 onu device. The olt port bit map
       defined as following port 1,2,3,....8....256
	   To include a port in manual upgrade set the correponding bit to 1."
   ::= { utsDot3OnuUpgradePortListGroup 1 }

utsDot3OnuUpgradeSchedulePortListStateBitMap OBJECT-TYPE
   SYNTAX  OCTET STRING (SIZE(0..255))
   MAX-ACCESS  read-write
   STATUS  current
   DESCRIPTION
       "Onu firmware upgrade olt port list bit map. BBS1000 has 8 olt ports.
       Each olt port can connect up to 32 onu device. The port bit map
       defined as following port 1,2,3,....256.
       To include a port in schedule upgrade set the correponding bit to 1"
   ::= { utsDot3OnuUpgradePortListGroup 2 }


utsDot3OnuUpgradeForceManualPortListBitMap OBJECT-TYPE
   SYNTAX  OCTET STRING (SIZE(0..255))
   MAX-ACCESS  read-write
   STATUS  current
   DESCRIPTION
       "Onu firmware upgrade olt port list bit map. BBS1000 has 8 olt ports.
       Each olt port can connect up to 32 onu device. The olt port bit map
       defined as following port 1,2,3,....8....256. Force upgrade without revision checking.
	   To include a port in force manual upgrade set the correponding bit to 1."
   ::= { utsDot3OnuUpgradePortListGroup 3 }


utsDot3OnuUpgradeNormalManualPortListBitMap OBJECT-TYPE
   SYNTAX  OCTET STRING (SIZE(0..255))
   MAX-ACCESS  read-write
   STATUS  current
   DESCRIPTION
       "Onu firmware upgrade olt port list bit map. BBS1000 has 8 olt ports.
       Each olt port can connect up to 32 onu device. The olt port bit map
       defined as following port 1,2,3,....8....256. Normal upgrade with revision checking.
	   To include a port in normal manual upgrade set the correponding bit to 1."
   ::= { utsDot3OnuUpgradePortListGroup 4 }




--
-- Hardware type configuration
--

utsDot3OnuHwTypeUpgradeObjects OBJECT IDENTIFIER ::= { utsDot3OnuUpgradeMIB 2}

utsDot3OnuHwTypeUpgradeTable OBJECT-TYPE
    SYNTAX      SEQUENCE OF UtsDot3OnuHwTypeUpgradeEntry
    MAX-ACCESS  not-accessible
    STATUS      current
    DESCRIPTION
        "A list of Onu hardware information"
    ::= { utsDot3OnuHwTypeUpgradeObjects 1}

utsDot3OnuHwTypeUpgradeEntry OBJECT-TYPE
    SYNTAX      UtsDot3OnuHwTypeUpgradeEntry
    MAX-ACCESS  not-accessible
    STATUS      current
    DESCRIPTION
        "An entry contains Onu hardware upgrade information"
    INDEX {  utsDot3OnuHwTypeUpgradeHwType,  utsDot3OnuHwTypeUpgradeMethod, utsDot3OnuHwTypeUpgradeComponent}
    ::= { utsDot3OnuHwTypeUpgradeTable 1}

UtsDot3OnuHwTypeUpgradeEntry ::=
    SEQUENCE {
        utsDot3OnuHwTypeUpgradeHwType          INTEGER,
        utsDot3OnuHwTypeUpgradeMethod          INTEGER,
        utsDot3OnuHwTypeUpgradeHwRev           DisplayString,
        utsDot3OnuHwTypeUpgradeFwRev           DisplayString,
        utsDot3OnuHwTypeUpgradeImageName       DisplayString,
        utsDot3OnuHwTypeUpgradeStatus          RowStatus,
        utsDot3OnuHwTypeUpgradeComponent       INTEGER
		}


utsDot3OnuHwTypeUpgradeHwType  OBJECT-TYPE
    SYNTAX  INTEGER
    {
	  	onu100(1),
			onu1000B(2),
			onu1000C(3),
			onu200A(4),
			onu200B(5),
			onu2024(6),
			onu2004(7),
		  onu101K(8),
		  onu301(9),
		  onu301C(10),
		  onu404(11),
		  onu404C(12),
		  onu804(13),
		  onu804C(14),
		  onu1001C(15),
			onu3004(16),
	    onu1001i(17),
	    onu2004i(18),
	    onu404i(19),
	    clt2060(20),
	    onu204i(21),
	    onu208i(22),
	    onu204h(23),
	    onu408t(24),
	    onu2024i(25),
	    onub210(26),
	    onu1001h(27),
	    onub220(28),
	    onu804i(29),
	    onu101(30),
	    onu1001b(31),
	    onu2004h(32),
	    onu204d(33),
	    onu404t(34),
	    onu4024t(35),
	    onu4024i(36),
        onu101i(38),
        onub1205y(39),
        onub1205d(40),
        onub130(41),
	    tkOnu(100),
	    pmcOnu(101),
	    unknow(200)
    }
    MAX-ACCESS  read-create
    STATUS  current
    DESCRIPTION
       "onu model which need firmware upgrade"
    ::= { utsDot3OnuHwTypeUpgradeEntry 1 }

utsDot3OnuHwTypeUpgradeMethod OBJECT-TYPE
      SYNTAX  INTEGER
      {
           manual(1),
           scheduled(2),
           auto(3)
      }
      MAX-ACCESS  read-create
      STATUS  current
      DESCRIPTION
           "Onu firmware upgrade method (manual or scheduled)"
      ::= { utsDot3OnuHwTypeUpgradeEntry 2 }

utsDot3OnuHwTypeUpgradeHwRev  OBJECT-TYPE
    SYNTAX  DisplayString(SIZE(0..63))
    MAX-ACCESS  read-create
    STATUS  current
    DESCRIPTION
         "Onu firmware upgrade hardware revision"
    ::= { utsDot3OnuHwTypeUpgradeEntry 3 }

utsDot3OnuHwTypeUpgradeFwRev  OBJECT-TYPE
      SYNTAX  DisplayString(SIZE(0..63))
      MAX-ACCESS  read-create
      STATUS  current
      DESCRIPTION
          "Onu firmware upgrade firmware revision"
      ::= { utsDot3OnuHwTypeUpgradeEntry 4 }

utsDot3OnuHwTypeUpgradeImageName OBJECT-TYPE
      SYNTAX  DisplayString(SIZE(0..63))
      MAX-ACCESS  read-create
      STATUS  current
      DESCRIPTION
          "Onu firmware upgrade Image Name"
      ::= { utsDot3OnuHwTypeUpgradeEntry 5 }


utsDot3OnuHwTypeUpgradeStatus  OBJECT-TYPE
    SYNTAX  RowStatus
    MAX-ACCESS  read-create
    STATUS  current
    DESCRIPTION
         "Onu firmware upgrade hardware entry status"
    ::= { utsDot3OnuHwTypeUpgradeEntry 6 }

utsDot3OnuHwTypeUpgradeComponent OBJECT-TYPE
    SYNTAX  INTEGER
    {
         onu-pon-firmware(1),
         onu-switch-firmware(2)
    }
    MAX-ACCESS  read-create
    STATUS  current
    DESCRIPTION
         "the component in Onu which need firmware upgrade"
    ::= { utsDot3OnuHwTypeUpgradeEntry 7 }

--
-- Onu FW Upgrade
--


utsDot3OnuFWUpgradeObjects OBJECT IDENTIFIER ::= { utsDot3OnuUpgradeMIB 3}

utsDot3OnuFWUpgradeScheduleTable OBJECT-TYPE
    SYNTAX      SEQUENCE OF UtsDot3OnuFWUpgradeScheduleEntry
    MAX-ACCESS  not-accessible
    STATUS      current
    DESCRIPTION
        "A list of Onu firmware information"
    ::= { utsDot3OnuFWUpgradeObjects 1}

utsDot3OnuFWUpgradeScheduleEntry OBJECT-TYPE
    SYNTAX      UtsDot3OnuFWUpgradeScheduleEntry
    MAX-ACCESS  not-accessible
    STATUS      current
    DESCRIPTION
        "An entry contains scheduled Onu firmware upgrade information"
    INDEX {  utsDot3OnuFWUpgradeStartingHour, utsDot3OnuFWUpgradeStartingMinute }
    ::= { utsDot3OnuFWUpgradeScheduleTable 1}

UtsDot3OnuFWUpgradeScheduleEntry ::=
    SEQUENCE {
        utsDot3OnuFWUpgradeStartingHour        INTEGER,
        utsDot3OnuFWUpgradeStartingMinute      INTEGER,
        utsDot3OnuFWUpgradeDuration            INTEGER,
        utsDot3OnuFWUpgradePortListBitMap      OCTET STRING,
        utsDot3OnuFWUpgradeOption              INTEGER,
        utsDot3OnuFWUpgradeRowStatus           RowStatus
    }

utsDot3OnuFWUpgradeStartingHour OBJECT-TYPE
      SYNTAX  INTEGER
      MAX-ACCESS  read-create
      STATUS  current
      DESCRIPTION
          "Onu firmware upgrade schedule starting hour."
      ::= { utsDot3OnuFWUpgradeScheduleEntry 1}

utsDot3OnuFWUpgradeStartingMinute OBJECT-TYPE
      SYNTAX  INTEGER
      MAX-ACCESS  read-create
      STATUS  current
      DESCRIPTION
          "Onu firmware upgrade schedule starting minute."
      ::= { utsDot3OnuFWUpgradeScheduleEntry 2}


utsDot3OnuFWUpgradeDuration OBJECT-TYPE
     SYNTAX  INTEGER(10..600)
     MAX-ACCESS  read-create
     STATUS  current
     DESCRIPTION
         "Onu firmware upgrade duration in minutes. Default is 150."
     ::= { utsDot3OnuFWUpgradeScheduleEntry 4 }

utsDot3OnuFWUpgradePortListBitMap OBJECT-TYPE
   SYNTAX  OCTET STRING (SIZE(0..255))
   MAX-ACCESS  read-create
   STATUS  current
   DESCRIPTION
       "Onu firmware upgrade port list bit map. BBS1000 has 8 olt ports.
       Each olt port can connect up to 32 onu device. The port bit map
       defined as following port 1,2,3,....256.
       To include a port in upgrade set the correponding bit to 1"
   ::= { utsDot3OnuFWUpgradeScheduleEntry 5 }


utsDot3OnuFWUpgradeOption OBJECT-TYPE
     SYNTAX  INTEGER
     {
         normal(1),
         force(2)
     }
     MAX-ACCESS  read-create
     STATUS  current
     DESCRIPTION
         "Onu firmware upgrade option."
     ::= { utsDot3OnuFWUpgradeScheduleEntry 6 }


utsDot3OnuFWUpgradeRowStatus OBJECT-TYPE
      SYNTAX      RowStatus
      MAX-ACCESS  read-create
      STATUS      current
      DESCRIPTION
          "Only be able to create/delete. Setting to createAndGo/destory. active will be returned when query."
      ::= { utsDot3OnuFWUpgradeScheduleEntry 7  }



utsDot3OnuFWUpgradeResultObjects OBJECT IDENTIFIER ::= { utsDot3OnuUpgradeMIB 4}

utsDot3OnuFWUpgradeResultTable OBJECT-TYPE
    SYNTAX      SEQUENCE OF UtsDot3OnuFWUpgradeResultEntry
    MAX-ACCESS  not-accessible
    STATUS      current
    DESCRIPTION
        "A list of sjow Onu firmware information"
    ::= { utsDot3OnuFWUpgradeResultObjects 1}

utsDot3OnuFWUpgradeResultEntry OBJECT-TYPE
    SYNTAX      UtsDot3OnuFWUpgradeResultEntry
    MAX-ACCESS  not-accessible
    STATUS      current
    DESCRIPTION
        "An entry contains Onu firmware upgrade information status"
    INDEX {  utsDot3OnuFWUpgradeResultIndex }
    ::= { utsDot3OnuFWUpgradeResultTable 1}

UtsDot3OnuFWUpgradeResultEntry ::=
    SEQUENCE {
        utsDot3OnuFWUpgradeResultIndex             INTEGER,
        utsDot3OnuFWUpgradeResultUpgMode           INTEGER,
        utsDot3OnuFWUpgradeResultStartingHour      INTEGER,
        utsDot3OnuFWUpgradeResultStartingMinute    INTEGER,
        utsDot3OnuFWUpgradeResultModule            INTEGER,
        utsDot3OnuFWUpgradeResultPort              INTEGER,
        utsDot3OnuFWUpgradeResultLogicalPort       INTEGER,
        utsDot3OnuFWUpgradeResultStatus            INTEGER,
        utsDot3OnuFWUpgradeResultStationId         MacAddress,
        utsDot3OnuFWUpgradeResultTargetVer         DisplayString,
        utsDot3OnuFWUpgradeResultCurrVer           DisplayString,
        utsDot3OnuFWUpgradeResultFinalState        DisplayString

    }

utsDot3OnuFWUpgradeResultIndex OBJECT-TYPE
   SYNTAX  INTEGER
   MAX-ACCESS  read-only
   STATUS  current
   DESCRIPTION
       "Show Onu firmware upgrade table index"
   ::= { utsDot3OnuFWUpgradeResultEntry 1 }

utsDot3OnuFWUpgradeResultUpgMode OBJECT-TYPE
   SYNTAX  INTEGER
   {
		manual(1),
		scheduled(2)
   }
   MAX-ACCESS  read-only
   STATUS  current
   DESCRIPTION
       "Show Onu firmware upgrade mode(manual or scheduled)"
   ::= { utsDot3OnuFWUpgradeResultEntry 2 }

utsDot3OnuFWUpgradeResultStartingHour OBJECT-TYPE
   SYNTAX  INTEGER(0..23)
   MAX-ACCESS  read-only
   STATUS  current
   DESCRIPTION
       "Show Onu firmware upgrade staring time(if scheduled)"
   ::= { utsDot3OnuFWUpgradeResultEntry 3 }


utsDot3OnuFWUpgradeResultStartingMinute OBJECT-TYPE
   SYNTAX  INTEGER(0..59)
   MAX-ACCESS  read-only
   STATUS  current
   DESCRIPTION
       "Show Onu firmware upgrade staring time(if scheduled)"
   ::= { utsDot3OnuFWUpgradeResultEntry 4 }

utsDot3OnuFWUpgradeResultModule OBJECT-TYPE
   SYNTAX  INTEGER
   MAX-ACCESS  read-only
   STATUS  current
   DESCRIPTION
       "Show Onu firmware upgrade module number"
   ::= { utsDot3OnuFWUpgradeResultEntry 5 }



utsDot3OnuFWUpgradeResultPort OBJECT-TYPE
   SYNTAX  INTEGER
   MAX-ACCESS  read-only
   STATUS  current
   DESCRIPTION
       "Show Onu firmware upgrade port number"
   ::= { utsDot3OnuFWUpgradeResultEntry 6 }


utsDot3OnuFWUpgradeResultLogicalPort OBJECT-TYPE
   SYNTAX  INTEGER
   MAX-ACCESS  read-only
   STATUS  current
   DESCRIPTION
       "Show Onu firmware upgrade logical port number"
   ::= { utsDot3OnuFWUpgradeResultEntry 7 }



utsDot3OnuFWUpgradeResultStatus OBJECT-TYPE
   SYNTAX  INTEGER
   {
		none(1),
		begin(2),
		end(3),
		fail(4),
		success(5)
   }
   MAX-ACCESS  read-only
   STATUS  current
   DESCRIPTION
       "Show Onu firmware upgrade status"
   ::= { utsDot3OnuFWUpgradeResultEntry 8 }

utsDot3OnuFWUpgradeResultStationId OBJECT-TYPE
   SYNTAX  MacAddress
   MAX-ACCESS  read-only
   STATUS  current
   DESCRIPTION
       "Show Onu firmware upgrade station mac address"
   ::= { utsDot3OnuFWUpgradeResultEntry 9 }


utsDot3OnuFWUpgradeResultTargetVer OBJECT-TYPE
   SYNTAX  DisplayString(SIZE(0..255))
   MAX-ACCESS  read-only
   STATUS  current
   DESCRIPTION
       "Show Onu firmware upgrade target version"
   ::= { utsDot3OnuFWUpgradeResultEntry 10 }


utsDot3OnuFWUpgradeResultCurrVer OBJECT-TYPE
   SYNTAX  DisplayString(SIZE(0..255))
   MAX-ACCESS  read-only
   STATUS  current
   DESCRIPTION
       "Show Onu firmware upgrade current version"
   ::= { utsDot3OnuFWUpgradeResultEntry 11 }


utsDot3OnuFWUpgradeResultFinalState OBJECT-TYPE
   SYNTAX  DisplayString(SIZE(0..255))
   MAX-ACCESS  read-only
   STATUS  current
   DESCRIPTION
       "Show Onu firmware upgrade final state"
   ::= { utsDot3OnuFWUpgradeResultEntry 12 }

--
--  utsDot3Olt2OnuFWUpgradeReqGroup: when OLT receive a ONU upgrade command from NMS or CLI,
--  OLT will send a SNMP request msg to ONU, to tell ONU get a new version firmware from OLT.
--  this is group is specially for ONU which has switch component such as ON200a in current.
--
--  Deleted by zxf Feb 15,2006
--
--   UTS MLS Qos extension.
--

utsMLSQosConfExt  OBJECT IDENTIFIER ::= { utsServiceConfExt  1 }

utsMLSQosExtObjects OBJECT IDENTIFIER ::= { utsMLSQosConfExt  1 }

--
--  QOS Cos queue Map table contains entry of mapping between
--  Cos and queue.
--
utsMLSQosExtCosQueueMapTable  OBJECT-TYPE
    SYNTAX    SEQUENCE OF UtsMLSQosExtCosQueueMapEntry
    MAX-ACCESS  not-accessible
    STATUS  current
    DESCRIPTION
        "A list of MLS Qos Cos to Queue mapping information.
	 There are 8 Cos priorities (1-8) and 4 queues(1-4)"
    ::= { utsMLSQosExtObjects 1 }

utsMLSQosExtCosQueueMapEntry  OBJECT-TYPE
    SYNTAX      UtsMLSQosExtCosQueueMapEntry
    MAX-ACCESS  not-accessible
    STATUS      current
    DESCRIPTION
        "An entry containing Cos to Queue mapping information of a given Cos"
    INDEX { utsMLSQosExtCosPriority }
    ::= { utsMLSQosExtCosQueueMapTable 1 }

UtsMLSQosExtCosQueueMapEntry ::=
   SEQUENCE {
      utsMLSQosExtCosPriority   INTEGER,
		utsMLSQosExtCosQueueNum   INTEGER
	}

utsMLSQosExtCosPriority  OBJECT-TYPE
   SYNTAX       INTEGER(0..7)
	MAX-ACCESS   read-only
	STATUS       current
	DESCRIPTION
	   "MLS Qos Cos priority."
	::= { utsMLSQosExtCosQueueMapEntry  1 }

utsMLSQosExtCosQueueNum  OBJECT-TYPE
   SYNTAX       INTEGER(0..3)
	MAX-ACCESS   read-write
	STATUS       current
	DESCRIPTION
	   "MLS Qos queue number."
	::= {  utsMLSQosExtCosQueueMapEntry  2 }

--
--  QOS Cos queue Schedule
--
utsMLSQosExtCosQueueSchedTable  OBJECT-TYPE
    SYNTAX    SEQUENCE OF UtsMLSQosExtCosQueueSchedEntry
    MAX-ACCESS  not-accessible
    STATUS  current
    DESCRIPTION
        "A list of MLS Cos queue schedule information."
    ::= { utsMLSQosExtObjects 2 }

utsMLSQosExtCosQueueSchedEntry  OBJECT-TYPE
    SYNTAX     UtsMLSQosExtCosQueueSchedEntry
    MAX-ACCESS  not-accessible
    STATUS      current
    DESCRIPTION
        "An entry containing Cos queue schedule information."
    INDEX { utsMLSQosExtCosQueueSchedIntfIndex,
            utsMLSQosExtCosQueueSchedQueueNum
           }
    ::= { utsMLSQosExtCosQueueSchedTable 1 }

UtsMLSQosExtCosQueueSchedEntry ::=
    SEQUENCE {
	utsMLSQosExtCosQueueSchedIntfIndex  INTEGER,
   utsMLSQosExtCosQueueSchedModuleId   INTEGER,
	utsMLSQosExtCosQueueSchedPortId     INTEGER,
	utsMLSQosExtCosQueueSchedLagPortId  INTEGER,
	utsMLSQosExtCosQueueSchedQueueNum   INTEGER,
	utsMLSQosExtCosQueueSchedWeight     INTEGER,
	utsMLSQosExtCosQueueSchedMode       INTEGER
	}

utsMLSQosExtCosQueueSchedIntfIndex OBJECT-TYPE
   SYNTAX  INTEGER
	MAX-ACCESS   read-only
	STATUS       current
	DESCRIPTION
	   "The interface index denotes switch ports and link aggregations,
	    For 1000:The range is 1-44. 1-12 denotes switch ports and 13-44 denotes link aggregations.
	    For 4000:The range is 1-72. 1-48 denotes switch ports and 49-72 denotes link aggregations."
	::= { utsMLSQosExtCosQueueSchedEntry  1 }

utsMLSQosExtCosQueueSchedModuleId OBJECT-TYPE
   	SYNTAX       INTEGER
	MAX-ACCESS   read-only
	STATUS       current
	DESCRIPTION
	   "MLS Qos Cos queue schedule Module Id."
	::= { utsMLSQosExtCosQueueSchedEntry  2 }

utsMLSQosExtCosQueueSchedPortId OBJECT-TYPE
   	SYNTAX       INTEGER
	MAX-ACCESS   read-only
	STATUS       current
	DESCRIPTION
	   "MLS Qos Cos queue schedule Port Id."
	::= { utsMLSQosExtCosQueueSchedEntry  3 }


utsMLSQosExtCosQueueSchedLagPortId OBJECT-TYPE
   	SYNTAX       INTEGER
	MAX-ACCESS   read-only
	STATUS       current
	DESCRIPTION
	   "MLS Qos Cos queue schedule Link Aggregation Port Id. "
	::= { utsMLSQosExtCosQueueSchedEntry  4 }


utsMLSQosExtCosQueueSchedQueueNum OBJECT-TYPE
    SYNTAX        INTEGER(0..3)
    MAX-ACCESS    read-only
	STATUS       current
    DESCRIPTION
	    "The MLS Qos Cos queue schedule entry's queue number."
    ::= { utsMLSQosExtCosQueueSchedEntry  5 }

utsMLSQosExtCosQueueSchedWeight OBJECT-TYPE
    SYNTAX INTEGER(0..15)
    MAX-ACCESS    read-write
	STATUS       current
    DESCRIPTION
        "The MLS Qos Cos queue schedule entry's weight. Only apply when mode is
		set to WRR"
    ::= { utsMLSQosExtCosQueueSchedEntry  6 }

utsMLSQosExtCosQueueSchedMode OBJECT-TYPE
    SYNTAX INTEGER {
		unknown(1),
		sp(2),
		wrr(3),
		spandwrr(4)
	}
    MAX-ACCESS    read-write
	 STATUS       current
    DESCRIPTION
        "The MLS Qos Cos queue schedule entry's mode."
    ::= { utsMLSQosExtCosQueueSchedEntry  7 }

--
--   QOS Dscp Map Table
--
-- utsMLSQosExtMapObjects  OBJECT IDENTIFIER ::= { utsMLSQosExtObjects 3 }

--
--   Dscp-Cos Mapping Table
--
utsMLSQosExtDscpCosMapTable  OBJECT-TYPE
    SYNTAX    SEQUENCE OF UtsMLSQosExtDscpCosMapEntry
    MAX-ACCESS  not-accessible
	STATUS  current
	DESCRIPTION
	    "A list of MLS Dscp Map information."
	::= { utsMLSQosExtObjects 3 }

utsMLSQosExtDscpCosMapEntry OBJECT-TYPE
    SYNTAX      UtsMLSQosExtDscpCosMapEntry
    MAX-ACCESS  not-accessible
    STATUS      current
    DESCRIPTION
        "An entry containing MLS Dscp Cos map information.
        For 1000, the interface index is valid;
        For 4000, the interface index is invalid,the mapping table is global per system, so all the fileds about interface index should be 0."
    INDEX { utsMLSQosExtDscpCosMapIntfIndex,
            utsMLSQosExtDscpCosMapDscpVal }
    ::= { utsMLSQosExtDscpCosMapTable 1 }

UtsMLSQosExtDscpCosMapEntry ::=
    SEQUENCE {
		utsMLSQosExtDscpCosMapIntfIndex   INTEGER,
      utsMLSQosExtDscpCosMapModuleId   INTEGER,
		utsMLSQosExtDscpCosMapPortId     INTEGER,
		utsMLSQosExtDscpCosMapLagPortId  INTEGER,
      utsMLSQosExtDscpCosMapDscpVal    INTEGER,
      utsMLSQosExtDscpCosMapCosVal     INTEGER
    }

utsMLSQosExtDscpCosMapIntfIndex OBJECT-TYPE
    SYNTAX       INTEGER
    MAX-ACCESS   read-only
    STATUS       current
    DESCRIPTION
        "The interface index denotes switch ports and link aggregations.
         For 1000:The range is 1-44. 1-12 denotes switch ports and 13-44 denotes link aggregations.
         For 4000:The range is 1-72. 1-48 denotes switch ports and 49-72 denotes link aggregations."
    ::= {  utsMLSQosExtDscpCosMapEntry 1 }

utsMLSQosExtDscpCosMapModuleId  OBJECT-TYPE
    SYNTAX       INTEGER
    MAX-ACCESS   read-only
    STATUS       current
    DESCRIPTION
        "Dscp Cos Map module Id. This value is valid only if the interface
         is a giga-ethernet port"
    ::= {  utsMLSQosExtDscpCosMapEntry 2 }

utsMLSQosExtDscpCosMapPortId  OBJECT-TYPE
    SYNTAX       INTEGER
    MAX-ACCESS   read-only
    STATUS       current
    DESCRIPTION
        "Dscp Cos Map Port Id. This value is valid only if the interface
         is a giga-ethernet port"
    ::= { utsMLSQosExtDscpCosMapEntry 3 }


utsMLSQosExtDscpCosMapLagPortId  OBJECT-TYPE
    SYNTAX       INTEGER
    MAX-ACCESS   read-only
    STATUS       current
    DESCRIPTION
        "Dscp Cos Map Link Aggregation Port Id. This value is valid only if
		the interface is a link aggregation port"
    ::= { utsMLSQosExtDscpCosMapEntry 4 }


utsMLSQosExtDscpCosMapDscpVal OBJECT-TYPE
    SYNTAX       INTEGER (0..63)
    MAX-ACCESS   read-only
    STATUS       current
    DESCRIPTION
        "Dscp Cos Map entry source Dscp value, range 0-63"
    ::= { utsMLSQosExtDscpCosMapEntry 5 }

utsMLSQosExtDscpCosMapCosVal OBJECT-TYPE
    SYNTAX       INTEGER (0..7)
	MAX-ACCESS   read-write
	STATUS       current
	DESCRIPTION
	    "Dscp Cos Map entry Cos value. range 0-7"
	::= { utsMLSQosExtDscpCosMapEntry 6 }

--
--   Dscp-Mutation Mapping Table
--
utsMLSQosExtDscpMutMapTable  OBJECT-TYPE
    SYNTAX    SEQUENCE OF UtsMLSQosExtDscpMutMapEntry
    MAX-ACCESS  not-accessible
	STATUS  current
	DESCRIPTION
	    "A list of MLS Dscp-Mutation Map information."
	::= { utsMLSQosExtObjects 4 }

utsMLSQosExtDscpMutMapEntry OBJECT-TYPE
    SYNTAX      UtsMLSQosExtDscpMutMapEntry
    MAX-ACCESS  not-accessible
    STATUS      current
    DESCRIPTION
        "An entry containing MLS Dscp-Mutation map information.
        For 1000, the interface index is valid;
        For 4000, the interface index is invalid,the mapping table is global per system, so all the fileds about interface index should be 0."
    INDEX { utsMLSQosExtDscpMutMapIntfIndex,
            utsMLSQosExtDscpMutMapDscpVal }
    ::= { utsMLSQosExtDscpMutMapTable 1 }

UtsMLSQosExtDscpMutMapEntry ::=
    SEQUENCE {
	utsMLSQosExtDscpMutMapIntfIndex  INTEGER,
   utsMLSQosExtDscpMutMapModuleId   INTEGER,
	utsMLSQosExtDscpMutMapPortId     INTEGER,
	utsMLSQosExtDscpMutMapLagPortId  INTEGER,
   utsMLSQosExtDscpMutMapDscpVal    INTEGER,
   utsMLSQosExtDscpMutMapMutVal     INTEGER
    }

utsMLSQosExtDscpMutMapIntfIndex OBJECT-TYPE
    SYNTAX       INTEGER
    MAX-ACCESS   read-only
    STATUS       current
    DESCRIPTION
        "The interface index denotes switch ports and link aggregations.
         For 1000:The range is 1-44. 1-12 denotes switch ports and 13-44 denotes link aggregations.
         For 4000:The range is 1-72. 1-48 denotes switch ports and 49-72 denotes link aggregations."
    ::= {  utsMLSQosExtDscpMutMapEntry 1 }

utsMLSQosExtDscpMutMapModuleId  OBJECT-TYPE
    SYNTAX       INTEGER
    MAX-ACCESS   read-only
    STATUS       current
    DESCRIPTION
        "Dscp-Mutation Map module Id."
    ::= {  utsMLSQosExtDscpMutMapEntry 2 }

utsMLSQosExtDscpMutMapPortId  OBJECT-TYPE
    SYNTAX       INTEGER
    MAX-ACCESS   read-only
    STATUS       current
    DESCRIPTION
        "Dscp-Mutation Map Port Id."
    ::= { utsMLSQosExtDscpMutMapEntry 3 }

utsMLSQosExtDscpMutMapLagPortId  OBJECT-TYPE
    SYNTAX       INTEGER
    MAX-ACCESS   read-only
    STATUS       current
    DESCRIPTION
        "Dscp-Mutation Map Link Aggregation Port Id."
    ::= { utsMLSQosExtDscpMutMapEntry 4 }

utsMLSQosExtDscpMutMapDscpVal OBJECT-TYPE
    SYNTAX       INTEGER (0..63)
    MAX-ACCESS   read-only
    STATUS       current
    DESCRIPTION
        "Dscp-Mutation Map entry source Dscp value"
    ::= { utsMLSQosExtDscpMutMapEntry 5 }

utsMLSQosExtDscpMutMapMutVal OBJECT-TYPE
    SYNTAX       INTEGER (0..63)
	MAX-ACCESS   read-write
	STATUS       current
	DESCRIPTION
	    "Dscp-Mutation Map entry mutation value."
	::= { utsMLSQosExtDscpMutMapEntry 6 }

--
--   ip-prec-dscp Mapping Table
--
utsMLSQosExtIpPrecDscpMapTable  OBJECT-TYPE
    SYNTAX    SEQUENCE OF UtsMLSQosExtIpPrecDscpMapEntry
    MAX-ACCESS  not-accessible
	STATUS  current
	DESCRIPTION
	    "A list of MLS Ip-Prec-Dscp Map information."
	::= { utsMLSQosExtObjects 5 }

utsMLSQosExtIpPrecDscpMapEntry OBJECT-TYPE
    SYNTAX      UtsMLSQosExtIpPrecDscpMapEntry
    MAX-ACCESS  not-accessible
    STATUS      current
    DESCRIPTION
        "An entry containing MLS Ip-Prec-Dscp map information.
         For 1000, the interface index is valid;
         For 4000, the interface index is invalid,the mapping table is global per system, so all the fileds about interface index should be 0."
    INDEX { utsMLSQosExtIpPrecDscpMapIntfIndex,
            utsMLSQosExtIpPrecDscpMapIpPrecVal }
    ::= { utsMLSQosExtIpPrecDscpMapTable 1 }

UtsMLSQosExtIpPrecDscpMapEntry ::=
    SEQUENCE {
	utsMLSQosExtIpPrecDscpMapIntfIndex  INTEGER,
   utsMLSQosExtIpPrecDscpMapModuleId   INTEGER,
	utsMLSQosExtIpPrecDscpMapPortId     INTEGER,
	utsMLSQosExtIpPrecDscpMapLagPortId  INTEGER,
   utsMLSQosExtIpPrecDscpMapIpPrecVal  INTEGER,
   utsMLSQosExtIpPrecDscpMapDscpVal    INTEGER
    }

utsMLSQosExtIpPrecDscpMapIntfIndex  OBJECT-TYPE
    SYNTAX       INTEGER
    MAX-ACCESS   read-only
    STATUS       current
    DESCRIPTION
        "The interface index denotes switch ports and link aggregations.
        For 1000:The range is 1-44. 1-12 denotes switch ports and 13-44 denotes link aggregations.
        For 4000:The range is 1-72. 1-48 denotes switch ports and 49-72 denotes link aggregations."
    ::= {  utsMLSQosExtIpPrecDscpMapEntry 1 }

utsMLSQosExtIpPrecDscpMapModuleId  OBJECT-TYPE
    SYNTAX       INTEGER
    MAX-ACCESS   read-only
    STATUS       current
    DESCRIPTION
        "Ip-Prec-Dscp Map Module Id."
    ::= { utsMLSQosExtIpPrecDscpMapEntry 2 }

utsMLSQosExtIpPrecDscpMapPortId  OBJECT-TYPE
    SYNTAX       INTEGER
    MAX-ACCESS   read-only
    STATUS       current
    DESCRIPTION
        "Ip-Prec-Dscp Map Port Id."
    ::= { utsMLSQosExtIpPrecDscpMapEntry 3 }

utsMLSQosExtIpPrecDscpMapLagPortId  OBJECT-TYPE
    SYNTAX       INTEGER
    MAX-ACCESS   read-only
    STATUS       current
    DESCRIPTION
        "Ip-Prec-Dscp Map Link Aggregation Port Id."
    ::= { utsMLSQosExtIpPrecDscpMapEntry 4 }

utsMLSQosExtIpPrecDscpMapIpPrecVal OBJECT-TYPE
    SYNTAX       INTEGER (0..7)
    MAX-ACCESS   read-only
    STATUS       current
    DESCRIPTION
        "Ip-Prec-Dscp Map entry Ip-Prec value"
    ::= { utsMLSQosExtIpPrecDscpMapEntry 5 }

utsMLSQosExtIpPrecDscpMapDscpVal OBJECT-TYPE
    SYNTAX       INTEGER (0..63)
	MAX-ACCESS   read-write
	STATUS       current
	DESCRIPTION
	    "Ip-Prec-Dscp Map entry Dscp value."
	::= { utsMLSQosExtIpPrecDscpMapEntry 6 }


--
--   QOS Dscp Trust Table
--
--
utsMLSQosExtDscpTrustTable  OBJECT-TYPE
    SYNTAX    SEQUENCE OF UtsMLSQosExtDscpTrustEntry
    MAX-ACCESS  not-accessible
    STATUS  current
    DESCRIPTION
        "A list of MLS Dscp Trust ."
    ::= { utsMLSQosExtObjects 6 }

utsMLSQosExtDscpTrustEntry OBJECT-TYPE
    SYNTAX      UtsMLSQosExtDscpTrustEntry
    MAX-ACCESS  not-accessible
    STATUS      current
    DESCRIPTION
        "An entry containing MLS Dscp trust information."
    INDEX {  utsMLSQosExtDscpTrustIntfIndex }
    ::= { utsMLSQosExtDscpTrustTable 1 }

UtsMLSQosExtDscpTrustEntry ::=
    SEQUENCE {
	utsMLSQosExtDscpTrustIntfIndex  		INTEGER,
   utsMLSQosExtDscpTrustModuleId   		INTEGER,
	utsMLSQosExtDscpTrustPortId     		INTEGER,
	utsMLSQosExtDscpTrustLagPortId  		INTEGER,
	utsMLSQosExtDscpTrustMode       		INTEGER,
	utsMLSQosExtDscpTrustIntfQosCtrl   INTEGER
	}

utsMLSQosExtDscpTrustIntfIndex  OBJECT-TYPE
    SYNTAX        INTEGER
    MAX-ACCESS    read-only
    STATUS        current
    DESCRIPTION
	    "The interface index denotes switch ports and link aggregations.
	     For 1000:The range is 1-44. 1-12 denotes switch ports and 13-44 denotes link aggregations.
	     For 4000:The range is 1-72. 1-48 denotes switch ports and 49-72 denotes link aggregations."
    ::= { utsMLSQosExtDscpTrustEntry 1 }

utsMLSQosExtDscpTrustModuleId  OBJECT-TYPE
    SYNTAX        INTEGER
    MAX-ACCESS    read-only
    STATUS        current
    DESCRIPTION
	    "Identify the module of this entry's interface."
    ::= { utsMLSQosExtDscpTrustEntry 2 }

utsMLSQosExtDscpTrustPortId  OBJECT-TYPE
    SYNTAX        INTEGER
    MAX-ACCESS    read-only
    STATUS        current
    DESCRIPTION
        "Identify the port of this entry's interface."
    ::= { utsMLSQosExtDscpTrustEntry 3 }

utsMLSQosExtDscpTrustLagPortId  OBJECT-TYPE
    SYNTAX        INTEGER
    MAX-ACCESS    read-only
    STATUS        current
    DESCRIPTION
        "Identify the Link Aggregation Port of this entry's interface."
    ::= { utsMLSQosExtDscpTrustEntry 4 }

utsMLSQosExtDscpTrustMode  OBJECT-TYPE
    SYNTAX        INTEGER
	{   not-trusted(1),
	    trust-dscp(2),
        ip-precedence(3)
    }
    MAX-ACCESS    read-write
    STATUS        current
    DESCRIPTION
        "Identify the entry's trust mode. "
    ::= { utsMLSQosExtDscpTrustEntry 5 }

utsMLSQosExtDscpTrustIntfQosCtrl  OBJECT-TYPE
    SYNTAX        INTEGER
    {
       enable(1),
	    disable(2)
    }
    MAX-ACCESS    read-write
    STATUS        current
    DESCRIPTION
	    "enable or disable qos function for an interface."
    ::= { utsMLSQosExtDscpTrustEntry 6 }


--
--   ACL extension
--


utsAclExt OBJECT IDENTIFIER ::=  { utsServiceConfExt  2 }

--
--   ACL Profile Table
--
utsAclExtProfileTable  OBJECT-TYPE
    SYNTAX       SEQUENCE OF UtsAclExtProfileEntry
	MAX-ACCESS   not-accessible
	STATUS       current
	DESCRIPTION
	   "A list of ACL Profile information."
    ::= { utsAclExt 1 }

utsAclExtProfileEntry OBJECT-TYPE
    SYNTAX       UtsAclExtProfileEntry
	MAX-ACCESS   not-accessible
	STATUS       current
	DESCRIPTION
	   "An entry in the ACL MIB extension table."
	INDEX { utsAclExtProfileId,
 		    utsAclExtProfileFieldId,
	 	    utsAclExtProfileRuleId }
    ::= { utsAclExtProfileTable 1 }

UtsAclExtProfileEntry ::=
    SEQUENCE  {
	utsAclExtProfileId                 			INTEGER,
	utsAclExtProfileFieldId            			INTEGER,
	utsAclExtProfileRuleId             			INTEGER,
	utsAclExtProfileName               			DisplayString,
    utsAclExtProfileFieldName          			DisplayString,
    utsAclExtProfileRuleName           			DisplayString,
    utsAclExtProfileFieldBitmap        			INTEGER,

	utsAclExtProfileFieldMaskDstMac          		MacAddress,
	utsAclExtProfileFieldMaskSrcMac          		MacAddress,
    utsAclExtProfileFieldMaskArpTargetMac			MacAddress,
    utsAclExtProfileFieldMaskArpSendMac     		MacAddress,
	utsAclExtProfileFieldMaskSrcIp           		IpAddress,
	utsAclExtProfileFieldMaskDstIp           		IpAddress,
    utsAclExtProfileFieldMaskVlan           		INTEGER,
	utsAclExtProfileFieldMaskEtherType       		INTEGER,

-- for BBS1000/1000+ only
	utsAclExtProfileFieldMaskTcpSrcPort      		INTEGER,
	utsAclExtProfileFieldMaskTcpDstPort      		INTEGER,
-- 1000 end

-- for BBS4000 only
	utsAclExtProfileFieldMaskSrcPortMin        	INTEGER,
	utsAclExtProfileFieldMaskSrcPortMax        	INTEGER,
	utsAclExtProfileFieldMaskDstPortMin        	INTEGER,
	utsAclExtProfileFieldMaskDstPortMax        	INTEGER,
-- 	4000 end

	utsAclExtProfileFieldMaskTagPri          		INTEGER,
	utsAclExtProfileFieldMaskDscp            		INTEGER,
	utsAclExtProfileFieldMaskProtocol        		INTEGER,
-- zhaoxf modified Dec 11,2006
--	utsAclExtProfileFieldMaskNewDscp         		INTEGER,
--	utsAclExtProfileFieldMaskNewTagPri       		INTEGER,
--	utsAclExtProfileFieldMaskNewRateLimit    		INTEGER,
--	utsAclExtProfileFieldMaskAction          		INTEGER,
    utsAclExtProfileFieldMaskIHL	                INTEGER,
    utsAclExtProfileFieldMaskFragmentOffset       INTEGER,

	utsAclExtProfileRuleValDstMac            	MacAddress,
	utsAclExtProfileRuleValSrcMac            	MacAddress,
    utsAclExtProfileRuleValArpTargetMac	 		MacAddress,
    utsAclExtProfileRuleValArpSendMac        	MacAddress,
	utsAclExtProfileRuleValSrcIp             	IpAddress,
	utsAclExtProfileRuleValDstIp             	IpAddress,
    utsAclExtProfileRuleValVlan              	INTEGER,
	utsAclExtProfileRuleValEtherType         	INTEGER,

-- for BBS1000/1000+ only
	utsAclExtProfileRuleValTcpSrcPort        	INTEGER,
    utsAclExtProfileRuleValTcpDstPort        	INTEGER,
-- end

-- for BBS4000 only
	utsAclExtProfileRuleValSrcPortMin        	INTEGER,
	utsAclExtProfileRuleValSrcPortMax        	INTEGER,
	utsAclExtProfileRuleValDstPortMin        	INTEGER,
	utsAclExtProfileRuleValDstPortMax        	INTEGER,
-- 	4000 end
	utsAclExtProfileRuleValTagPri            	INTEGER,
	utsAclExtProfileRuleValDscp              	INTEGER,
	utsAclExtProfileRuleValProtocol          	INTEGER,
	utsAclExtProfileRuleValNewDscp           	INTEGER,
	utsAclExtProfileRuleValNewTagPri         	INTEGER,
	utsAclExtProfileRuleValNewBandwidth      	INTEGER,
-- Added by Zhaoxf Dec 11,2006
	utsAclExtProfileRuleValNewBurstSize         INTEGER,
	utsAclExtProfileRuleValNewOutPort           INTEGER,
    utsAclExtProfileRuleValNewOutTag            INTEGER,
    utsAclExtProfileRuleValNewVlanId            INTEGER,
    utsAclExtProfileRuleValIHL	                INTEGER,
    utsAclExtProfileRuleValFragmentOffset       INTEGER,
	utsAclExtProfileRuleValAction            	INTEGER
}


utsAclExtProfileId  OBJECT-TYPE
    SYNTAX        INTEGER
	MAX-ACCESS    read-only
	STATUS        current
	DESCRIPTION
	    "An ID to identify the ACL profile."
	::= { utsAclExtProfileEntry 1 }

utsAclExtProfileFieldId  OBJECT-TYPE
    SYNTAX        INTEGER(1..64)
	MAX-ACCESS    read-only
	STATUS        current
	DESCRIPTION
	    "The profile field Id of the ACL profile."
	::= { utsAclExtProfileEntry 2 }

utsAclExtProfileRuleId   OBJECT-TYPE
    SYNTAX        INTEGER
	MAX-ACCESS    read-only
	STATUS        current
	DESCRIPTION
	    "An ID to identify the ACL profile."
	::= { utsAclExtProfileEntry 3 }

utsAclExtProfileName  OBJECT-TYPE
    SYNTAX        DisplayString(SIZE(0..32))
	MAX-ACCESS    read-only
	STATUS        current
	DESCRIPTION
	    "ACL profile name."
	::= { utsAclExtProfileEntry 4 }

utsAclExtProfileFieldName  OBJECT-TYPE
    SYNTAX        DisplayString(SIZE(0..32))
	MAX-ACCESS    read-only
	STATUS        current
	DESCRIPTION
	    "ACL profile field name."
	::= { utsAclExtProfileEntry 5 }

utsAclExtProfileRuleName  OBJECT-TYPE
    SYNTAX        DisplayString(SIZE(0..32))
	MAX-ACCESS    read-only
	STATUS        current
	DESCRIPTION
	    "ACL profile rule name."
	::= { utsAclExtProfileEntry 6 }

utsAclExtProfileFieldBitmap  OBJECT-TYPE
    SYNTAX        INTEGER
	MAX-ACCESS    read-only
	STATUS        current
	DESCRIPTION
	    "ACL profile field bitmap."
	::= { utsAclExtProfileEntry 7 }


utsAclExtProfileFieldMaskDstMac  OBJECT-TYPE
    SYNTAX        MacAddress
	MAX-ACCESS    read-only
	STATUS        current
	DESCRIPTION
	    "ACL profile field mask destination MAC address."
	::= { utsAclExtProfileEntry 8 }

utsAclExtProfileFieldMaskSrcMac  OBJECT-TYPE
    SYNTAX        MacAddress
	MAX-ACCESS    read-only
	STATUS        current
	DESCRIPTION
	    "ACL profile field mask source MAC address."
	::= { utsAclExtProfileEntry 9 }

utsAclExtProfileFieldMaskArpTargetMac  OBJECT-TYPE
    SYNTAX        MacAddress
	MAX-ACCESS    read-only
	STATUS        current
	DESCRIPTION
	    "ACL profile field mask ARP target MAC address."
	::= { utsAclExtProfileEntry 10 }

utsAclExtProfileFieldMaskArpSendMac  OBJECT-TYPE
    SYNTAX        MacAddress
	MAX-ACCESS    read-only
	STATUS        current
	DESCRIPTION
	    "ACL profile field mask ARP send MAC address."
	::= { utsAclExtProfileEntry 11 }

utsAclExtProfileFieldMaskSrcIp  OBJECT-TYPE
    SYNTAX        IpAddress
	MAX-ACCESS    read-only
	STATUS        current
	DESCRIPTION
	    "ACL profile field mask source IP address."
	::= { utsAclExtProfileEntry 12 }

utsAclExtProfileFieldMaskDstIp  OBJECT-TYPE
    SYNTAX        IpAddress
	MAX-ACCESS    read-only
	STATUS        current
	DESCRIPTION
	    "ACL profile field mask destination IP address."
	::= { utsAclExtProfileEntry 13 }

utsAclExtProfileFieldMaskVlan  OBJECT-TYPE
    SYNTAX        INTEGER
	MAX-ACCESS    read-only
	STATUS        current
	DESCRIPTION
	    "ACL profile field mask VLAN."
	::= { utsAclExtProfileEntry 14 }

utsAclExtProfileFieldMaskEtherType  OBJECT-TYPE
    SYNTAX        INTEGER
	{
	    tag(1),
		untag(2),
		etherII(3),
		eight02dot3(4)
	}
	MAX-ACCESS    read-only
	STATUS        current
	DESCRIPTION
	    "ACL profile field mask ethernet type."
	::= { utsAclExtProfileEntry 15 }

utsAclExtProfileFieldMaskTcpSrcPort  OBJECT-TYPE
    SYNTAX        INTEGER
	MAX-ACCESS    read-only
	STATUS        current
	DESCRIPTION
	    "ACL profile field mask TCP source port."
	::= { utsAclExtProfileEntry 16 }

utsAclExtProfileFieldMaskTcpDstPort  OBJECT-TYPE
    SYNTAX        INTEGER
	MAX-ACCESS    read-only
	STATUS        current
	DESCRIPTION
	    "ACL profile field mask TCP destination port."
	::= { utsAclExtProfileEntry 17 }


utsAclExtProfileFieldMaskSrcPortMin  OBJECT-TYPE
    SYNTAX        INTEGER
	MAX-ACCESS    read-only
	STATUS        current
	DESCRIPTION
	    "ACL profile field mask minimum source port."
	::= { utsAclExtProfileEntry 18 }

utsAclExtProfileFieldMaskSrcPortMax  OBJECT-TYPE
    SYNTAX        INTEGER
	MAX-ACCESS    read-only
	STATUS        current
	DESCRIPTION
	    "ACL profile field mask maximum source port."
	::= { utsAclExtProfileEntry 19 }

utsAclExtProfileFieldMaskDstPortMin  OBJECT-TYPE
    SYNTAX        INTEGER
	MAX-ACCESS    read-only
	STATUS        current
	DESCRIPTION
	    "ACL profile field mask minimum destination port."
	::= { utsAclExtProfileEntry 20 }

utsAclExtProfileFieldMaskDstPortMax  OBJECT-TYPE
    SYNTAX        INTEGER
	MAX-ACCESS    read-only
	STATUS        current
	DESCRIPTION
	    "ACL profile field mask maximum destination port."
	::= { utsAclExtProfileEntry 21 }

utsAclExtProfileFieldMaskTagPri  OBJECT-TYPE
    SYNTAX        INTEGER
	MAX-ACCESS    read-only
	STATUS        current
	DESCRIPTION
	    "ACL profile field mask tag priority."
	::= { utsAclExtProfileEntry 22 }

utsAclExtProfileFieldMaskDscp  OBJECT-TYPE
    SYNTAX        INTEGER
	MAX-ACCESS    read-only
	STATUS        current
	DESCRIPTION
	    "ACL profile field mask Dscp."
	::= { utsAclExtProfileEntry 23 }

utsAclExtProfileFieldMaskProtocol  OBJECT-TYPE
    SYNTAX        INTEGER
	MAX-ACCESS    read-only
	STATUS        current
	DESCRIPTION
	    "ACL profile field mask Protocol."
	::= { utsAclExtProfileEntry 24 }

utsAclExtProfileFieldMaskIHL  OBJECT-TYPE
    SYNTAX        INTEGER
	MAX-ACCESS    read-only
	STATUS        current
	DESCRIPTION
	    "ACL profile field mask for IP header length."
	::= { utsAclExtProfileEntry 25 }

utsAclExtProfileFieldMaskFragmentOffset  OBJECT-TYPE
    SYNTAX        INTEGER
	MAX-ACCESS    read-only
	STATUS        current
	DESCRIPTION
	    "ACL profile field mask for fragment offset."
	::= { utsAclExtProfileEntry 26 }

-- Rule value


utsAclExtProfileRuleValDstMac  OBJECT-TYPE
    SYNTAX        MacAddress
	MAX-ACCESS    read-only
	STATUS        current
	DESCRIPTION
	    "ACL profile rule value destination MAC address."
	::= { utsAclExtProfileEntry 100 }

utsAclExtProfileRuleValSrcMac  OBJECT-TYPE
    SYNTAX        MacAddress
	MAX-ACCESS    read-only
	STATUS        current
	DESCRIPTION
	    "ACL profile rule value source MAC address."
	::= { utsAclExtProfileEntry 101 }

utsAclExtProfileRuleValArpTargetMac  OBJECT-TYPE
    SYNTAX        MacAddress
	MAX-ACCESS    read-only
	STATUS        current
	DESCRIPTION
	    "ACL profile rule value ARP target MAC address."
	::= { utsAclExtProfileEntry 102 }

utsAclExtProfileRuleValArpSendMac  OBJECT-TYPE
    SYNTAX        MacAddress
	MAX-ACCESS    read-only
	STATUS        current
	DESCRIPTION
	    "ACL profile rule value ARP send MAC address."
	::= { utsAclExtProfileEntry 103 }

utsAclExtProfileRuleValSrcIp  OBJECT-TYPE
    SYNTAX        IpAddress
	MAX-ACCESS    read-only
	STATUS        current
	DESCRIPTION
	    "ACL profile rule value source IP address."
	::= { utsAclExtProfileEntry 104 }

utsAclExtProfileRuleValDstIp  OBJECT-TYPE
    SYNTAX        IpAddress
	MAX-ACCESS    read-only
	STATUS        current
	DESCRIPTION
	    "ACL profile rule value destination IP address."
	::= { utsAclExtProfileEntry 105 }

utsAclExtProfileRuleValVlan  OBJECT-TYPE
    SYNTAX        INTEGER
	MAX-ACCESS    read-only
	STATUS        current
	DESCRIPTION
	    "ACL profile rule value VLAN."
	::= { utsAclExtProfileEntry 106 }

utsAclExtProfileRuleValEtherType  OBJECT-TYPE
    SYNTAX        INTEGER
	{
	    tag(1),
		untag(2),
		etherII(3),
		eight02dot3(4)
	}
	MAX-ACCESS    read-only
	STATUS        current
	DESCRIPTION
	    "ACL profile rule value ethernet type."
	::= { utsAclExtProfileEntry 107 }

utsAclExtProfileRuleValTcpSrcPort  OBJECT-TYPE
    SYNTAX        INTEGER
	MAX-ACCESS    read-only
	STATUS        current
	DESCRIPTION
	    "ACL profile rule value TCP source port."
	::= { utsAclExtProfileEntry 108 }

utsAclExtProfileRuleValTcpDstPort  OBJECT-TYPE
    SYNTAX        INTEGER
	MAX-ACCESS    read-only
	STATUS        current
	DESCRIPTION
	    "ACL profile rule value TCP destination port."
	::= { utsAclExtProfileEntry 109 }

utsAclExtProfileRuleValSrcPortMin  OBJECT-TYPE
    SYNTAX        INTEGER
	MAX-ACCESS    read-only
	STATUS        current
	DESCRIPTION
	    "ACL profile rule value TCP source port."
	::= { utsAclExtProfileEntry 110 }

utsAclExtProfileRuleValSrcPortMax  OBJECT-TYPE
    SYNTAX        INTEGER
	MAX-ACCESS    read-only
	STATUS        current
	DESCRIPTION
	    "ACL profile rule value TCP destination port."
	::= { utsAclExtProfileEntry 111 }

utsAclExtProfileRuleValDstPortMin  OBJECT-TYPE
    SYNTAX        INTEGER
	MAX-ACCESS    read-only
	STATUS        current
	DESCRIPTION
	    "ACL profile rule value TCP source port."
	::= { utsAclExtProfileEntry 112 }

utsAclExtProfileRuleValDstPortMax  OBJECT-TYPE
    SYNTAX        INTEGER
	MAX-ACCESS    read-only
	STATUS        current
	DESCRIPTION
	    "ACL profile rule value TCP destination port."
	::= { utsAclExtProfileEntry 113 }

utsAclExtProfileRuleValTagPri  OBJECT-TYPE
    SYNTAX        INTEGER
	MAX-ACCESS    read-only
	STATUS        current
	DESCRIPTION
	    "ACL profile rule value tag priority."
	::= { utsAclExtProfileEntry 114 }

utsAclExtProfileRuleValDscp  OBJECT-TYPE
    SYNTAX        INTEGER
	MAX-ACCESS    read-only
	STATUS        current
	DESCRIPTION
	    "ACL profile rule value Dscp."
	::= { utsAclExtProfileEntry 115 }

utsAclExtProfileRuleValProtocol  OBJECT-TYPE
    SYNTAX        INTEGER
	MAX-ACCESS    read-only
	STATUS        current
	DESCRIPTION
	    "ACL profile rule value Protocol."
	::= { utsAclExtProfileEntry 116 }

utsAclExtProfileRuleValNewDscp  OBJECT-TYPE
    SYNTAX        INTEGER
	MAX-ACCESS    read-only
	STATUS        current
	DESCRIPTION
	    "ACL profile rule value new Dscp."
	::= { utsAclExtProfileEntry 117 }

utsAclExtProfileRuleValNewTagPri  OBJECT-TYPE
    SYNTAX        INTEGER
	MAX-ACCESS    read-only
	STATUS        current
	DESCRIPTION
	    "ACL profile rule value new tag priority."
	::= { utsAclExtProfileEntry 118 }

utsAclExtProfileRuleValNewBandwidth  OBJECT-TYPE
    SYNTAX        INTEGER
	MAX-ACCESS    read-only
	STATUS        current
	DESCRIPTION
	    "ACL profile rule value new bandwidth."
	::= { utsAclExtProfileEntry 119 }

utsAclExtProfileRuleValNewBurstSize  OBJECT-TYPE
    SYNTAX        INTEGER
	MAX-ACCESS    read-only
	STATUS        current
	DESCRIPTION
	    "ACL profile rule value new burst size."
	::= { utsAclExtProfileEntry 120 }

utsAclExtProfileRuleValNewOutPort  OBJECT-TYPE
    SYNTAX        INTEGER
	MAX-ACCESS    read-only
	STATUS        current
	DESCRIPTION
	    "ACL profile rule value new out port."
	::= { utsAclExtProfileEntry 121 }

utsAclExtProfileRuleValNewOutTag  OBJECT-TYPE
    SYNTAX        INTEGER(1..4094)
	MAX-ACCESS    read-only
	STATUS        current
	DESCRIPTION
	    "ACL profile rule value new out tag."
	::= { utsAclExtProfileEntry 122 }

utsAclExtProfileRuleValNewVlanId  OBJECT-TYPE
    SYNTAX        INTEGER(1..4094)
	MAX-ACCESS    read-only
	STATUS        current
	DESCRIPTION
	    "New VLAN ID for VLAN remark or append VLAN."
	::= { utsAclExtProfileEntry 123 }

utsAclExtProfileRuleValIHL  OBJECT-TYPE
    SYNTAX        INTEGER
	MAX-ACCESS    read-only
	STATUS        current
	DESCRIPTION
	    "ACL profile rule value IP head length."
	::= { utsAclExtProfileEntry 124 }

utsAclExtProfileRuleValFragmentOffset  OBJECT-TYPE
    SYNTAX        INTEGER
	MAX-ACCESS    read-only
	STATUS        current
	DESCRIPTION
	    "ACL profile rule value fragment offset."
	::= { utsAclExtProfileEntry 125 }

utsAclExtProfileRuleValAction  OBJECT-TYPE
    SYNTAX        INTEGER
	{
	    permit(1),
	    deny(2),
		remark-dscp(3),
		remark-priority(4),
		rate-limit(5),
		remark-vlan(6),
		append-vlan(7)
	}
	MAX-ACCESS    read-only
	STATUS        current
	DESCRIPTION
	    "ACL profile rule value action."
	::= { utsAclExtProfileEntry 200 }

--
--   Interface ACL Profile Configuration Table
--
utsAclExtIntfConfigTable  OBJECT-TYPE
    SYNTAX       SEQUENCE OF UtsAclExtIntfConfigEntry
	MAX-ACCESS   not-accessible
	STATUS       current
	DESCRIPTION
	   "A list of Interface ACL Profile information."
    ::= { utsAclExt 2 }

utsAclExtIntfConfigEntry  OBJECT-TYPE
    SYNTAX       UtsAclExtIntfConfigEntry
	MAX-ACCESS   not-accessible
	STATUS       current
	DESCRIPTION
	   "An entry in interface ACL MIB table."
	INDEX { utsAclExtIntfConfigIntfNum }
    ::= { utsAclExtIntfConfigTable 1 }

UtsAclExtIntfConfigEntry ::=
    SEQUENCE {
	utsAclExtIntfConfigIntfNum          INTEGER,
	utsAclExtIntfConfigIntfModule       INTEGER,
	utsAclExtIntfConfigIntfPort         INTEGER,
	utsAclExtIntfConfigIntfLagGrpId     INTEGER,
	utsAclExtIntfConfigIntfFilterType   INTEGER,
	utsAclExtIntfConfigApplProfileId    INTEGER,
	utsAclExtIntfConfigApplStatus	    	RowStatus
}

utsAclExtIntfConfigIntfNum  OBJECT-TYPE
    SYNTAX         INTEGER
	MAX-ACCESS     read-create
	STATUS         current
	DESCRIPTION
	   "The interface index denotes switch ports and link aggregation.
	   For 1000:The range is 1-44. 1-12 denotes switch ports and 13-44 denotes link aggregations.
	   For 4000:The range is 1-72. 1-48 denotes switch ports and 49-72 denotes link aggregations."
	::= { utsAclExtIntfConfigEntry 1 }


utsAclExtIntfConfigIntfModule  OBJECT-TYPE
    SYNTAX         INTEGER
	MAX-ACCESS     read-only
	STATUS         current
	DESCRIPTION
	   "The interface index to this Interface/ACL profile entry."
	::= { utsAclExtIntfConfigEntry 2 }

utsAclExtIntfConfigIntfPort  OBJECT-TYPE
    SYNTAX         INTEGER
	MAX-ACCESS     read-only
	STATUS         current
	DESCRIPTION
	   "The interface index to this Interface/ACL profile entry."
	::= { utsAclExtIntfConfigEntry 3 }

utsAclExtIntfConfigIntfLagGrpId  OBJECT-TYPE
    SYNTAX         INTEGER
	MAX-ACCESS     read-only
	STATUS         current
	DESCRIPTION
	   "The interface index to this Interface/ACL profile entry."
	::= { utsAclExtIntfConfigEntry 4 }

utsAclExtIntfConfigIntfFilterType  OBJECT-TYPE
    SYNTAX         INTEGER
	{
		mgmt-type(1),
		hardware-type(2)
	}
	MAX-ACCESS     read-only
	STATUS         current
	DESCRIPTION
	   "The management interface index to this Interface/ACL profile entry."
	::= { utsAclExtIntfConfigEntry 5 }


utsAclExtIntfConfigApplProfileId  OBJECT-TYPE
    SYNTAX         INTEGER
	MAX-ACCESS     read-create
	STATUS         current
	DESCRIPTION
	   "The ACL profile associate with this Interface."
	::= { utsAclExtIntfConfigEntry 6 }


utsAclExtIntfConfigApplStatus  OBJECT-TYPE
    SYNTAX         RowStatus
	MAX-ACCESS     read-create
	STATUS         current
	DESCRIPTION
	   "The row status of the ACL profile associate with this Interface."
	::= { utsAclExtIntfConfigEntry 7 }

--
--   ACL Profile Import Configuration Table
--
utsAclExtProfileImportTable  OBJECT-TYPE
    SYNTAX       SEQUENCE OF UtsAclExtProfileImportEntry
	MAX-ACCESS   not-accessible
	STATUS       current
	DESCRIPTION
	   "A list of import ACL profile information."
    ::= { utsAclExt 3 }

utsAclExtProfileImportEntry  OBJECT-TYPE
    SYNTAX       UtsAclExtProfileImportEntry
	MAX-ACCESS   not-accessible
	STATUS       current
	DESCRIPTION
	   "An entry in ACL profile import table."
	INDEX {  utsAclExtProfileImportProfileId}
    ::= { utsAclExtProfileImportTable 1 }

UtsAclExtProfileImportEntry ::=
    SEQUENCE {
	    utsAclExtProfileImportProfileId     INTEGER,
	    utsAclExtProfileImportFileName      DisplayString,
	    utsAclExtProfileImportStatus        RowStatus
}

utsAclExtProfileImportProfileId  OBJECT-TYPE
    SYNTAX         INTEGER
	MAX-ACCESS     read-create
	STATUS         current
	DESCRIPTION
	   "The index to this ACL profile import entry."
	::= { utsAclExtProfileImportEntry 1 }

utsAclExtProfileImportFileName  OBJECT-TYPE
    SYNTAX         DisplayString(SIZE(0..63))
	MAX-ACCESS     read-create
	STATUS         current
	DESCRIPTION
	   "The profile name associate with this ACL profile import entry."
	::= { utsAclExtProfileImportEntry 2 }

utsAclExtProfileImportStatus  OBJECT-TYPE
    SYNTAX         RowStatus
	MAX-ACCESS     read-create
	STATUS         current
	DESCRIPTION
	   "The profile name associate with this ACL profile import entry."
	::= { utsAclExtProfileImportEntry 3 }

-- EPON device ACL MIB

utsDot3Olt2AclProfTable OBJECT-TYPE
SYNTAX  SEQUENCE OF UtsDot3Olt2AclProfEntry
        MAX-ACCESS  not-accessible
        STATUS  current
        DESCRIPTION
"Table for OLT type 2 ACL MIBs."
        ::= { utsAclExt 4 }

utsDot3Olt2AclProfEntry OBJECT-TYPE
SYNTAX  UtsDot3Olt2AclProfEntry
       MAX-ACCESS  not-accessible
       STATUS  current
       DESCRIPTION
"An entry in the OLT type 2 ACL MIBs table."
       INDEX  { utsDot3OltAclModuleId, utsDot3OltAclDeviceId, utsDot3OltAclRuleIndex }
       ::= { utsDot3Olt2AclProfTable 1 }


UtsDot3Olt2AclProfEntry ::=
       SEQUENCE {
                    utsDot3OltAclModuleId				         INTEGER,
                    utsDot3OltAclDeviceId				         INTEGER,
                    utsDot3OltAclRuleIndex                       INTEGER,
                    utsDot3OltAclPonPort                         INTEGER,
                    utsDot3OltAclLLIDPort                        INTEGER,
				    utsDot3OltAclMask                            INTEGER,
				    utsDot3OltAclVlanId                          INTEGER,
					utsDot3OltAclVlanIdMask                      INTEGER,
					utsDot3OltAclIpSaOrMacDa4                    INTEGER,
					utsDot3OltAclIpSaOrMacDa4Mask                INTEGER,
					utsDot3OltAclIpDaOrL2Type                    INTEGER,
					utsDot3OltAclIpDaOrL2TypeMask                INTEGER,
					utsDot3OltAclIpProtocolId                    INTEGER,
					utsDot3OltAclIpProtocolIdMask                INTEGER,
					utsDot3OltAclL4SrcPortOrMacDa2               INTEGER,
					utsDot3OltAclL4SrcPortOrMacDa2Mask           INTEGER,
					utsDot3OltAclL4DstPort                       INTEGER,
					utsDot3OltAclL4DstPortMask                   INTEGER,
					utsDot3OltAclIpOptionsPresent                TruthValue,
					utsDot3OltAclIpFragmentedPacket              TruthValue,
					utsDot3OltAclAction                          INTEGER,
					utsDot3OltAclDirection                       INTEGER,
					utsDot3OltAclPacketType                      INTEGER
       }

utsDot3OltAclModuleId OBJECT-TYPE
SYNTAX  INTEGER
       MAX-ACCESS  read-only
       STATUS  current
       DESCRIPTION
"A read-only value that identifies the olt module index"
        ::= { utsDot3Olt2AclProfEntry 1 }

utsDot3OltAclDeviceId OBJECT-TYPE
SYNTAX  INTEGER
       MAX-ACCESS  read-only
       STATUS  current
       DESCRIPTION
"A read-only value that identifies the olt device index"
        ::= { utsDot3Olt2AclProfEntry 2 }

utsDot3OltAclRuleIndex OBJECT-TYPE
SYNTAX  INTEGER(1..1500)
       MAX-ACCESS  read-create
       STATUS  current
       DESCRIPTION
"Configures an ACL rule in the bi-direction at the OLT. There are a
 total of 1500 ACL entries in the table. The action can be either
 PERMIT or DENY. Each ACL can specify the VLAN, the IP src/destination
 address, IP protocol-id, ethernet type, MAC destination address,
 L4 src/destination ports, ip_options_present flag, ip_fragment_present flag,
 direction and packet type. Most of these fields are bit-maskable.
 The last ACL rule (ruleindex 1499) is the default rule, which applies
 when no other ACL entry is hit."
        ::= { utsDot3Olt2AclProfEntry 3 }

utsDot3OltAclPonPort OBJECT-TYPE
SYNTAX  INTEGER(1..4)
       MAX-ACCESS  read-create
       STATUS  current
       DESCRIPTION
"OLT device PON port index."
        ::= { utsDot3Olt2AclProfEntry 4 }

utsDot3OltAclLLIDPort OBJECT-TYPE
SYNTAX  INTEGER(0..64)
       MAX-ACCESS  read-create
       STATUS  current
       DESCRIPTION
"OLT device ONU port index. 0 means this ACL rule apply to specify PON port only."
        ::= { utsDot3Olt2AclProfEntry 5 }

utsDot3OltAclMask OBJECT-TYPE
       SYNTAX  INTEGER   -- Begin with left bit 0:15
       MAX-ACCESS  read-create
       STATUS  current
       DESCRIPTION
"Global Mask for specifying which field of structure is valid."
        ::= { utsDot3Olt2AclProfEntry 6 }

utsDot3OltAclVlanId OBJECT-TYPE
       SYNTAX  INTEGER
       MAX-ACCESS  read-create
       STATUS  current
       DESCRIPTION
"VLAN ID."
        ::= { utsDot3Olt2AclProfEntry 7 }

utsDot3OltAclVlanIdMask OBJECT-TYPE
       SYNTAX  INTEGER     -- Begin with left bit 0:15
       MAX-ACCESS  read-create
       STATUS  current
       DESCRIPTION
"VLAN ID mask."
        ::= { utsDot3Olt2AclProfEntry 8 }

utsDot3OltAclIpSaOrMacDa4 OBJECT-TYPE
       SYNTAX  INTEGER
       MAX-ACCESS  read-create
       STATUS  current
       DESCRIPTION
"IP source address or MAC address dest0to3."
        ::= { utsDot3Olt2AclProfEntry 9 }

utsDot3OltAclIpSaOrMacDa4Mask OBJECT-TYPE
       SYNTAX  INTEGER
       MAX-ACCESS  read-create
       STATUS  current
       DESCRIPTION
"IP source address or MAC address dest0to3 mask."
        ::= { utsDot3Olt2AclProfEntry 10 }

utsDot3OltAclIpDaOrL2Type OBJECT-TYPE
       SYNTAX  INTEGER
       MAX-ACCESS  read-create
       STATUS  current
       DESCRIPTION
"IP destination address or ethernet type/length."
        ::= { utsDot3Olt2AclProfEntry 11 }

utsDot3OltAclIpDaOrL2TypeMask OBJECT-TYPE
       SYNTAX  INTEGER
       MAX-ACCESS  read-create
       STATUS  current
       DESCRIPTION
"IP destination address or ethernet type/length mask."
        ::= { utsDot3Olt2AclProfEntry 12 }

utsDot3OltAclIpProtocolId OBJECT-TYPE
       SYNTAX  INTEGER
       MAX-ACCESS  read-create
       STATUS  current
       DESCRIPTION
"IP Protocol id field."
        ::= { utsDot3Olt2AclProfEntry 13 }

utsDot3OltAclIpProtocolIdMask OBJECT-TYPE
       SYNTAX  INTEGER
       MAX-ACCESS  read-create
       STATUS  current
       DESCRIPTION
"IP Protocol id mask."
        ::= { utsDot3Olt2AclProfEntry 14 }

utsDot3OltAclL4SrcPortOrMacDa2 OBJECT-TYPE
       SYNTAX  INTEGER
       MAX-ACCESS  read-create
       STATUS  current
       DESCRIPTION
"Layer4 source port or MAC address dest4to5."
        ::= { utsDot3Olt2AclProfEntry 15 }

utsDot3OltAclL4SrcPortOrMacDa2Mask OBJECT-TYPE
       SYNTAX  INTEGER
       MAX-ACCESS  read-create
       STATUS  current
       DESCRIPTION
"Layer4 source port or MAC address dest4to5 mask."
        ::= { utsDot3Olt2AclProfEntry 16 }

utsDot3OltAclL4DstPort OBJECT-TYPE
       SYNTAX  INTEGER
       MAX-ACCESS  read-create
       STATUS  current
       DESCRIPTION
"Layer4 destination port."
        ::= { utsDot3Olt2AclProfEntry 17 }

utsDot3OltAclL4DstPortMask OBJECT-TYPE
       SYNTAX  INTEGER
       MAX-ACCESS  read-create
       STATUS  current
       DESCRIPTION
"Layer4 destination port mask."
        ::= { utsDot3Olt2AclProfEntry 18 }

utsDot3OltAclIpOptionsPresent OBJECT-TYPE
       SYNTAX  TruthValue
       MAX-ACCESS  read-create
       STATUS  current
       DESCRIPTION
"Whether IP options present."
        ::= { utsDot3Olt2AclProfEntry 19 }

utsDot3OltAclIpFragmentedPacket OBJECT-TYPE
       SYNTAX  TruthValue
       MAX-ACCESS  read-create
       STATUS  current
       DESCRIPTION
"Whether IP fragmented packet."
        ::= { utsDot3Olt2AclProfEntry 20 }

utsDot3OltAclAction OBJECT-TYPE
       SYNTAX  INTEGER
       {
       	 permit(1),
       	 deny(2)
       }
       MAX-ACCESS  read-create
       STATUS  current
       DESCRIPTION
"Action to be taken - PERMIT or DENY."
        ::= { utsDot3Olt2AclProfEntry 21 }

utsDot3OltAclDirection OBJECT-TYPE
       SYNTAX  INTEGER
       {
       	 egress(1),
       	 ingress(2)
       }
       MAX-ACCESS  read-create
       STATUS  current
       DESCRIPTION
"Direction - Egress or Ingress."
        ::= { utsDot3Olt2AclProfEntry 22 }

utsDot3OltAclPacketType OBJECT-TYPE
       SYNTAX  INTEGER
       {
       	 ip(1),
       	 ethernet(2),
       	 arp(3)
       }
       MAX-ACCESS  read-create
       STATUS  current
       DESCRIPTION
"Packet Type - IP, ARP or Ethernet."
        ::= { utsDot3Olt2AclProfEntry 23 }

------------------------------------------------------------
--  OLT PON ACL configure table
------------------------------------------------------------

-- EPON device ACL MIB

utsDot3Olt2AclConfTable OBJECT-TYPE
SYNTAX  SEQUENCE OF UtsDot3Olt2AclConfEntry
        MAX-ACCESS  not-accessible
        STATUS  current
        DESCRIPTION
"Table for OLT type 2 ACL MIBs."
        ::= { utsAclExt 5 }

utsDot3Olt2AclConfEntry OBJECT-TYPE
SYNTAX  UtsDot3Olt2AclConfEntry
       MAX-ACCESS  not-accessible
       STATUS  current
       DESCRIPTION
"An entry in the OLT type 2 ACL MIBs table."
       INDEX  { utsDot3OltAclConfModuleId, utsDot3OltAclConfDeviceId, utsDot3OltAclConfPonPort,
                utsDot3OltAclConfLlidPort, utsDot3OltAclConfProfId, utsDot3OltAclConfDir }
       ::= { utsDot3Olt2AclConfTable 1 }


UtsDot3Olt2AclConfEntry ::=
       SEQUENCE {
                    utsDot3OltAclConfModuleId	 		         INTEGER,
                    utsDot3OltAclConfDeviceId	  		         INTEGER,
                    utsDot3OltAclConfPonPort                     INTEGER,
                    utsDot3OltAclConfLlidPort                    INTEGER,
                    utsDot3OltAclConfProfId                      INTEGER,
                    utsDot3OltAclConfDir                         INTEGER,
--                    utsDot3OltAclConfUpstream                    TruthValue,
--                    utsDot3OltAclConfDownstream                  TruthValue,
                    utsDot3OltAclConfRowStatus                   RowStatus
       }

utsDot3OltAclConfModuleId OBJECT-TYPE
SYNTAX  INTEGER
       MAX-ACCESS  not-accessible
       STATUS  current
       DESCRIPTION
"A read-only value that identifies the olt module index"
        ::= { utsDot3Olt2AclConfEntry 1 }

utsDot3OltAclConfDeviceId OBJECT-TYPE
SYNTAX  INTEGER
       MAX-ACCESS  not-accessible
       STATUS  current
       DESCRIPTION
"A read-only value that identifies the olt device index"
        ::= { utsDot3Olt2AclConfEntry 2 }

utsDot3OltAclConfPonPort OBJECT-TYPE
SYNTAX  INTEGER(1..4)
       MAX-ACCESS  not-accessible
       STATUS  current
       DESCRIPTION
"OLT device PON port index."
        ::= { utsDot3Olt2AclConfEntry 4 }

utsDot3OltAclConfLlidPort OBJECT-TYPE
SYNTAX  INTEGER(0..64)
       MAX-ACCESS  not-accessible
       STATUS  current
       DESCRIPTION
"OLT device ONU port index. 0 means this ACL rule apply to specify PON port only."
        ::= { utsDot3Olt2AclConfEntry 5 }

utsDot3OltAclConfProfId OBJECT-TYPE
SYNTAX  INTEGER(1..64)
       MAX-ACCESS  not-accessible
       STATUS  current
       DESCRIPTION
"Configures an ACL rule in the bi-direction at the OLT. There are a
 total of 1500 ACL entries in the table. The action can be either
 PERMIT or DENY. Each ACL can specify the VLAN, the IP src/destination
 address, IP protocol-id, ethernet type, MAC destination address,
 L4 src/destination ports, ip_options_present flag, ip_fragment_present flag,
 direction and packet type. Most of these fields are bit-maskable.
 The last ACL rule (ruleindex 1499) is the default rule, which applies
 when no other ACL entry is hit."
        ::= { utsDot3Olt2AclConfEntry 6 }

utsDot3OltAclConfDir OBJECT-TYPE
SYNTAX  INTEGER
	   {
	     upstream(1),
	     downstream(2)
	   }
       MAX-ACCESS  not-accessible
       STATUS  current
       DESCRIPTION
"ACl configuration for upstream or downstream."
        ::= { utsDot3Olt2AclConfEntry 7 }


utsDot3OltAclConfRowStatus OBJECT-TYPE
SYNTAX  RowStatus
       MAX-ACCESS  read-create
       STATUS  current
       DESCRIPTION
"Row Status"
        ::= { utsDot3Olt2AclConfEntry 9 }


-------------------------------------------------------------------------------
--      CTC controllrable IGMP
-------------------------------------------------------------------------------

utsCtcCtrlIgmpExt OBJECT IDENTIFIER ::=  { utsServiceConfExt  3 }

utsCtcMulticastCtrlExtObjects OBJECT IDENTIFIER ::= { utsCtcCtrlIgmpExt 1}

utsOnuCtcMulticastCtrlTable OBJECT-TYPE
SYNTAX  SEQUENCE OF UtsOnuCtcMulticastCtrlEntry
        MAX-ACCESS  not-accessible
        STATUS  current
        DESCRIPTION
"Table for ONU multicast control, which following CTC spec."
        ::= { utsCtcMulticastCtrlExtObjects 1 }

utsOnuCtcMulticastCtrlEntry OBJECT-TYPE
SYNTAX  UtsOnuCtcMulticastCtrlEntry
       MAX-ACCESS  not-accessible
       STATUS  current
       DESCRIPTION
"An entry in the ONU multicast control table."
       INDEX  { utsDot3OnuMCtrlModuleId,utsDot3OnuMCtrlDeviceId,utsDot3OnuMCtrlPonPortId,
                utsDot3OnuMCtrlLogicalPortId,
                utsDot3OnuMCtrlEtherPortIndex,utsDot3OnuMCastVlan,utsDot3OnuMCastGroupStart}
       ::= { utsOnuCtcMulticastCtrlTable 1 }

UtsOnuCtcMulticastCtrlEntry ::=
       SEQUENCE
       {
               utsDot3OnuMCtrlModuleId		         INTEGER,
               utsDot3OnuMCtrlDeviceId               INTEGER,
               utsDot3OnuMCtrlPonPortId	             INTEGER,
               utsDot3OnuMCtrlLogicalPortId	         INTEGER,
               utsDot3OnuMCtrlEtherPortIndex         INTEGER,
               utsDot3OnuMCastVlan                   INTEGER,
               utsDot3OnuMCastGroupStart             IpAddress,
               utsDot3OnuMCastGroupEnd               IpAddress,
               utsDot3OnuAuthType                    INTEGER,
               utsDot3OnuMCastCtrlRowStatus          RowStatus
       }

utsDot3OnuMCtrlModuleId OBJECT-TYPE
SYNTAX  INTEGER(1..12)
       MAX-ACCESS  not-accessible
       STATUS  current
       DESCRIPTION
"The OLT module id for the current ONU."
        ::= { utsOnuCtcMulticastCtrlEntry 1 }

utsDot3OnuMCtrlDeviceId OBJECT-TYPE
SYNTAX  INTEGER(1..4)
       MAX-ACCESS  not-accessible
       STATUS  current
       DESCRIPTION
"The OLT device id for the current ONU."
        ::= { utsOnuCtcMulticastCtrlEntry 2 }

utsDot3OnuMCtrlPonPortId OBJECT-TYPE
SYNTAX  INTEGER(1..4)
       MAX-ACCESS  not-accessible
       STATUS  current
       DESCRIPTION
"The OLT port id for the current ONU."
        ::= { utsOnuCtcMulticastCtrlEntry 3 }

utsDot3OnuMCtrlLogicalPortId OBJECT-TYPE
SYNTAX  INTEGER(1..64)
       MAX-ACCESS  not-accessible
       STATUS  current
       DESCRIPTION
"The logical port id for the current ONU."
        ::= { utsOnuCtcMulticastCtrlEntry 4 }

utsDot3OnuMCtrlEtherPortIndex OBJECT-TYPE
SYNTAX  INTEGER(1..8)
       MAX-ACCESS  not-accessible
       STATUS  current
       DESCRIPTION
"ONU Ethernet port Index"
        ::= { utsOnuCtcMulticastCtrlEntry 5 }

utsDot3OnuMCastVlan OBJECT-TYPE
SYNTAX INTEGER(1..4094)
       MAX-ACCESS  not-accessible
       STATUS  current
       DESCRIPTION
"Multicast VLAN ID"
        ::= { utsOnuCtcMulticastCtrlEntry 6 }

utsDot3OnuMCastGroupStart OBJECT-TYPE
SYNTAX  IpAddress
       MAX-ACCESS  not-accessible
       STATUS  current
       DESCRIPTION
"IP multicast group start address"
        ::= { utsOnuCtcMulticastCtrlEntry 7 }

utsDot3OnuMCastGroupEnd OBJECT-TYPE
SYNTAX  IpAddress
       MAX-ACCESS  read-create
       STATUS  current
       DESCRIPTION
"IP multicast group end address"
        ::= { utsOnuCtcMulticastCtrlEntry 8 }

utsDot3OnuAuthType OBJECT-TYPE
SYNTAX INTEGER
       {
          permit(1),
          deny(2),
          preview(3)
       }

       MAX-ACCESS  read-create
       STATUS  current
       DESCRIPTION
"ONU multicast authenticated type"
        ::= { utsOnuCtcMulticastCtrlEntry 9 }

utsDot3OnuMCastCtrlRowStatus OBJECT-TYPE
SYNTAX RowStatus
       MAX-ACCESS  read-create
       STATUS  current
       DESCRIPTION
"Row status"
        ::= { utsOnuCtcMulticastCtrlEntry 10 }


-----------------------------------------------------------
--      ONU port band control, CTC spec
-----------------------------------------------------------

utsOnuCtcBandCtrlTable OBJECT-TYPE
SYNTAX  SEQUENCE OF UtsOnuCtcBandCtrlEntry
        MAX-ACCESS  not-accessible
        STATUS  current
        DESCRIPTION
"Table for ONU band control, which following CTC spec."
        ::= { utsCtcMulticastCtrlExtObjects 2 }

utsOnuCtcBandCtrlEntry OBJECT-TYPE
SYNTAX  UtsOnuCtcBandCtrlEntry
       MAX-ACCESS  not-accessible
       STATUS  current
       DESCRIPTION
"An entry in the ONU band control table."
       INDEX  { utsDot3OnuBandCtrlModuleId,utsDot3OnuBandCtrlDeviceId,utsDot3OnuBandCtrlPonPortId,
                utsDot3OnuBandCtrlLogicalPortId,utsDot3OnuBandCtrlEtherPortIndex}
       ::= { utsOnuCtcBandCtrlTable 1 }

UtsOnuCtcBandCtrlEntry ::=
       SEQUENCE
       {
               utsDot3OnuBandCtrlModuleId	         INTEGER,
               utsDot3OnuBandCtrlDeviceId            INTEGER,
               utsDot3OnuBandCtrlPonPortId		     INTEGER,
               utsDot3OnuBandCtrlLogicalPortId	     INTEGER,
               utsDot3OnuBandCtrlEtherPortIndex      INTEGER,
               utsDot3OnuMaxActiveChannel            INTEGER,
               utsDot3OnuPreviewLength               INTEGER,
               utsDot3OnuPreviewCount                INTEGER,
               utsDot3OnuPreviewInterval             INTEGER,
               utsDot3OnuPreviewResetTime            INTEGER,
               utsDot3OnuMGroupJoinNum               INTEGER
--               utsDot3OnuBandCtrlRowStatus           RowStatus
       }

utsDot3OnuBandCtrlModuleId OBJECT-TYPE
SYNTAX  INTEGER(1..12)
       MAX-ACCESS  read-only
       STATUS  current
       DESCRIPTION
"A read only value to identifiy the OLT module id for the current ONU."
        ::= { utsOnuCtcBandCtrlEntry 1 }

utsDot3OnuBandCtrlDeviceId OBJECT-TYPE
SYNTAX  INTEGER(1..4)
       MAX-ACCESS  read-only
       STATUS  current
       DESCRIPTION
"A read only value to identifiy the OLT device id for the current ONU."
        ::= { utsOnuCtcBandCtrlEntry 2 }

utsDot3OnuBandCtrlPonPortId OBJECT-TYPE
SYNTAX  INTEGER(1..4)
       MAX-ACCESS  read-only
       STATUS  current
       DESCRIPTION
"A read only value to identifiy the OLT port id for the current ONU."
        ::= { utsOnuCtcBandCtrlEntry 3 }

utsDot3OnuBandCtrlLogicalPortId OBJECT-TYPE
SYNTAX  INTEGER(1..64)
       MAX-ACCESS  read-only
       STATUS  current
       DESCRIPTION
"A read only value to identifiy the logical port id for the current ONU."
        ::= { utsOnuCtcBandCtrlEntry 4 }

utsDot3OnuBandCtrlEtherPortIndex OBJECT-TYPE
SYNTAX  INTEGER(1..8)
       MAX-ACCESS  read-only
       STATUS  current
       DESCRIPTION
"ONU Ethernet port"
        ::= { utsOnuCtcBandCtrlEntry 5 }

utsDot3OnuMaxActiveChannel OBJECT-TYPE
SYNTAX INTEGER(1..64)
       MAX-ACCESS  read-write
       STATUS  current
       DESCRIPTION
"Max band one user can apply at the same"
        ::= { utsOnuCtcBandCtrlEntry 6 }

utsDot3OnuPreviewLength OBJECT-TYPE
SYNTAX INTEGER(1..300)
       MAX-ACCESS  read-write
       STATUS  current
       DESCRIPTION
"Band preview length, in seconds"
        ::= { utsOnuCtcBandCtrlEntry 7 }

utsDot3OnuPreviewCount OBJECT-TYPE
SYNTAX INTEGER(1..10)
       MAX-ACCESS  read-write
       STATUS  current
       DESCRIPTION
"Band preview count"
        ::= { utsOnuCtcBandCtrlEntry 8 }

utsDot3OnuPreviewInterval OBJECT-TYPE
SYNTAX INTEGER(1..60)
       MAX-ACCESS  read-write
       STATUS  current
       DESCRIPTION
"Band preview interval, in seconds"
        ::= { utsOnuCtcBandCtrlEntry 9 }

utsDot3OnuPreviewResetTime OBJECT-TYPE
SYNTAX INTEGER(10..3600)
       MAX-ACCESS  read-write
       STATUS  current
       DESCRIPTION
"Band preview reset time, in seconds"
        ::= { utsOnuCtcBandCtrlEntry 10 }

utsDot3OnuMGroupJoinNum OBJECT-TYPE
SYNTAX INTEGER
       MAX-ACCESS  read-only
       STATUS  current
       DESCRIPTION
"ONU join Multicast group number in this port"
        ::= { utsOnuCtcBandCtrlEntry 11 }

--   OLT IGMP proxy VLAN configuation, CTC spec

utsOltCtcIgmpCtrlExtObjects OBJECT IDENTIFIER ::= {  utsCtcMulticastCtrlExtObjects 3 }

utsOltCtcIgmpProxyCtrlGroup OBJECT IDENTIFIER ::= { utsOltCtcIgmpCtrlExtObjects 1 }


utsOltCtcMulticastCtrlMode OBJECT-TYPE
SYNTAX  INTEGER
       {
         special(1),    -- using CTC-special igmp
         control(2),    -- using CTC-control igmp
         standard(3)    -- using standard igmp
       }
       MAX-ACCESS  read-write
       STATUS  current
       DESCRIPTION
"OLT IGMP proxy mode"
        ::= { utsOltCtcIgmpProxyCtrlGroup 2 }

utsOltNoCdrForShortJoinLeave OBJECT-TYPE
SYNTAX INTEGER(1..15)
       MAX-ACCESS  read-write
       STATUS  current
       DESCRIPTION
"In control mode, do not create cdr for short time join and leave, the range is from 1 to 15, default value
 is 3 second."
DEFVAL {3}
        ::= { utsOltCtcIgmpProxyCtrlGroup 3 }

utsOltNoTimeForShortPreview OBJECT-TYPE
SYNTAX INTEGER(1..15)
       MAX-ACCESS  read-write
       STATUS  current
       DESCRIPTION
"In control mode, do not time for short preview, the range is from 1 to 15, default value is 3 second."
DEFVAL {3}
        ::= { utsOltCtcIgmpProxyCtrlGroup 4 }

---------------------------------------------------
--     CDR MIBs, CTC spec
---------------------------------------------------

utsCtcCdrExtObjects OBJECT IDENTIFIER ::= { utsCtcCtrlIgmpExt 2}

utsOltCtcCdrCtrlGroup OBJECT IDENTIFIER ::= { utsCtcCdrExtObjects 1 }

utsOltCtcCdrServerIpAddr OBJECT-TYPE
SYNTAX  IpAddress
       MAX-ACCESS  read-write
       STATUS  current
       DESCRIPTION
"CDR server IP address"
        ::= { utsOltCtcCdrCtrlGroup 1 }

utsOltCtcCdrPort OBJECT-TYPE
SYNTAX  INTEGER(1..65535)
       MAX-ACCESS  read-write
       STATUS  current
       DESCRIPTION
"CDR server udp port"
        ::= { utsOltCtcCdrCtrlGroup 2 }

utsOltCtcCdrReportInterval OBJECT-TYPE
SYNTAX  INTEGER(10..3600)
       MAX-ACCESS  read-write
       STATUS  current
       DESCRIPTION
"CDR report interval in seconds"
        ::= { utsOltCtcCdrCtrlGroup 3 }

utsOltCtcCdrReportCount OBJECT-TYPE
SYNTAX  INTEGER(10..1000)
       MAX-ACCESS  read-write
       STATUS  current
       DESCRIPTION
"Set the CDR counting number which will trigger the report to CDR server"
        ::= { utsOltCtcCdrCtrlGroup 4 }

utsOltCtcCdrForceReport OBJECT-TYPE
SYNTAX  INTEGER
       {
        force(1)  -- write only
       }
       MAX-ACCESS  read-write
       STATUS  current
       DESCRIPTION
"Force CDR report to server"
        ::= { utsOltCtcCdrCtrlGroup 5 }

utsOltCtcCdrReportMode OBJECT-TYPE
SYNTAX  INTEGER
	   {
	     periodical(1),
	     counting(2),
	     force(3)
	   }
       MAX-ACCESS  read-write
       STATUS  current
       DESCRIPTION
"Set CDR reporting mode"
        ::= { utsOltCtcCdrCtrlGroup 6 }

utsOltCtcCdrReportSwitch OBJECT-TYPE
SYNTAX  INTEGER
	   {
	     enable(1),
	     disable(2)
	   }
       MAX-ACCESS  read-write
       STATUS  current
       DESCRIPTION
"Set CDR reporting switch, the default value is enable."
        ::= { utsOltCtcCdrCtrlGroup 8 }

-----------------------------------------------------------
--      OLT pull down multcast traffic table
-----------------------------------------------------------

utsOltPullDownMcTable OBJECT-TYPE
SYNTAX  SEQUENCE OF UtsOltPullDownMcEntry
        MAX-ACCESS  not-accessible
        STATUS  current
        DESCRIPTION
"Table for OLT multcast pull down control."
        ::= { utsCtcMulticastCtrlExtObjects 4 }

utsOltPullDownMcEntry OBJECT-TYPE
SYNTAX  UtsOltPullDownMcEntry
       MAX-ACCESS  not-accessible
       STATUS  current
       DESCRIPTION
"An entry in the OLT multcast pull down control table."
       INDEX  { utsOltPullDownMcGroupIpAddr }
       ::= { utsOltPullDownMcTable 1 }

UtsOltPullDownMcEntry ::=
       SEQUENCE
       {
               utsOltPullDownMcGroupIpAddr              IpAddress,
               utsOltPullDownMcGroupMVlan               INTEGER,
               utsOltPullDownMcGroupRowStatus           RowStatus
       }


utsOltPullDownMcGroupIpAddr OBJECT-TYPE
SYNTAX  IpAddress
       MAX-ACCESS  not-accessible
       STATUS  current
       DESCRIPTION
"OLT pull down multicast group IP address"
        ::= { utsOltPullDownMcEntry 1 }

utsOltPullDownMcGroupMVlan OBJECT-TYPE
SYNTAX  INTEGER
       MAX-ACCESS  read-create
       STATUS  current
       DESCRIPTION
"OLT pull down multicast VLAN of specific multicast group"
        ::= { utsOltPullDownMcEntry 2 }

utsOltPullDownMcGroupRowStatus OBJECT-TYPE
SYNTAX  RowStatus
       MAX-ACCESS  read-create
       STATUS  current
       DESCRIPTION
"Row status"
        ::= { utsOltPullDownMcEntry 3 }


-----------------------------------------------------------
--      OLT multicast VLAN/Multicast group mapping table
-----------------------------------------------------------

utsOltGlbMulticastGroupTable OBJECT-TYPE
SYNTAX  SEQUENCE OF UtsOltGlbMulticastGroupEntry
        MAX-ACCESS  not-accessible
        STATUS  current
        DESCRIPTION
"Table for OLT multcast VLAN mapping table control."
        ::= { utsCtcMulticastCtrlExtObjects 5 }

utsOltGlbMulticastGroupEntry OBJECT-TYPE
SYNTAX  UtsOltGlbMulticastGroupEntry
       MAX-ACCESS  not-accessible
       STATUS  current
       DESCRIPTION
"An entry in the OLT multcast VLAN mapping control table."
       INDEX  { utsOltGlbMulticastGroupMVlan }
       ::= { utsOltGlbMulticastGroupTable 1 }

UtsOltGlbMulticastGroupEntry ::=
       SEQUENCE
       {
               utsOltGlbMulticastGroupMVlan               INTEGER,
               utsOltGlbMulticastGroupIpAddrStart         IpAddress,
               utsOltGlbMulticastGroupIpAddrEnd           IpAddress,
               utsOltGlbMulticastGroupRowStatus           RowStatus
       }


utsOltGlbMulticastGroupMVlan OBJECT-TYPE
SYNTAX  INTEGER
       MAX-ACCESS  not-accessible
       STATUS  current
       DESCRIPTION
"Multicast VLAN"
        ::= { utsOltGlbMulticastGroupEntry 1 }

utsOltGlbMulticastGroupIpAddrStart OBJECT-TYPE
SYNTAX  IpAddress
       MAX-ACCESS  read-create
       STATUS  current
       DESCRIPTION
"Multicast group start IP address"
        ::= { utsOltGlbMulticastGroupEntry 2 }

utsOltGlbMulticastGroupIpAddrEnd OBJECT-TYPE
SYNTAX  IpAddress
       MAX-ACCESS  read-create
       STATUS  current
       DESCRIPTION
"Multicast group end IP address"
        ::= { utsOltGlbMulticastGroupEntry 3 }


utsOltGlbMulticastGroupRowStatus OBJECT-TYPE
SYNTAX  RowStatus
       MAX-ACCESS  read-create
       STATUS  current
       DESCRIPTION
"Row status"
        ::= { utsOltGlbMulticastGroupEntry 4 }

-- ONU multicast table


utsOnuCtcMulticastTable OBJECT-TYPE
SYNTAX  SEQUENCE OF UtsOnuCtcMulticastEntry
        MAX-ACCESS  not-accessible
        STATUS  current
        DESCRIPTION
"Table for ONU multicast group list, which following CTC spec."
        ::= { utsCtcMulticastCtrlExtObjects 6 }

utsOnuCtcMulticastEntry OBJECT-TYPE
SYNTAX  UtsOnuCtcMulticastEntry
       MAX-ACCESS  not-accessible
       STATUS  current
       DESCRIPTION
"An entry in the ONU multicast group table."
       INDEX  { utsDot3OnuMCastModuleId,utsDot3OnuMCastDeviceId,utsDot3OnuMCastPortId,
                utsDot3OnuMCastLogicalPortId,utsDot3OnuMCastEtherPortId,utsDot3OnuMCastGroup}
       ::= { utsOnuCtcMulticastTable 1 }

UtsOnuCtcMulticastEntry ::=
       SEQUENCE
       {
               utsDot3OnuMCastModuleId	             INTEGER,
               utsDot3OnuMCastDeviceId               INTEGER,
               utsDot3OnuMCastPortId	             INTEGER,
               utsDot3OnuMCastLogicalPortId	         INTEGER,
               utsDot3OnuMCastEtherPortId            INTEGER,
               utsDot3OnuMCastGroup                  IpAddress,
               utsDot3OnuMCastMVlan                  INTEGER,
               utsDot3OnuMCastAuthType               INTEGER,
               utsDot3OnuMCastDuration               INTEGER
       }

utsDot3OnuMCastModuleId OBJECT-TYPE
SYNTAX  INTEGER(1..12)
       MAX-ACCESS  not-accessible
       STATUS  current
       DESCRIPTION
"The OLT module id for the current ONU."
        ::= { utsOnuCtcMulticastEntry 1 }

utsDot3OnuMCastDeviceId OBJECT-TYPE
SYNTAX  INTEGER(1..4)
       MAX-ACCESS  not-accessible
       STATUS  current
       DESCRIPTION
"The OLT device id for the current ONU."
        ::= { utsOnuCtcMulticastEntry 2 }

utsDot3OnuMCastPortId OBJECT-TYPE
SYNTAX  INTEGER(1..4)
       MAX-ACCESS  not-accessible
       STATUS  current
       DESCRIPTION
"The OLT port id for the current ONU."
        ::= { utsOnuCtcMulticastEntry 3 }

utsDot3OnuMCastLogicalPortId OBJECT-TYPE
SYNTAX  INTEGER(1..64)
       MAX-ACCESS  not-accessible
       STATUS  current
       DESCRIPTION
"The logical port id for the current ONU."
        ::= { utsOnuCtcMulticastEntry 4 }

utsDot3OnuMCastEtherPortId OBJECT-TYPE
SYNTAX  INTEGER
       MAX-ACCESS  not-accessible
       STATUS  current
       DESCRIPTION
"ONU Ethernet port Index"
        ::= { utsOnuCtcMulticastEntry 5 }

utsDot3OnuMCastGroup OBJECT-TYPE
SYNTAX  IpAddress
       MAX-ACCESS  read-only
       STATUS  current
       DESCRIPTION
"IP multicast group"
        ::= { utsOnuCtcMulticastEntry 6 }

utsDot3OnuMCastMVlan OBJECT-TYPE
SYNTAX INTEGER(1..4094)
       MAX-ACCESS  read-only
       STATUS  current
       DESCRIPTION
"Multicast VLAN ID"
        ::= { utsOnuCtcMulticastEntry 7 }

utsDot3OnuMCastAuthType OBJECT-TYPE
SYNTAX INTEGER
       {
          permit(1),
          deny(2),
          preview(3)
       }

       MAX-ACCESS  read-only
       STATUS  current
       DESCRIPTION
"ONU multicast authenticated type"
        ::= { utsOnuCtcMulticastEntry 8 }

utsDot3OnuMCastDuration OBJECT-TYPE
SYNTAX INTEGER
       MAX-ACCESS  read-only
       STATUS  current
       DESCRIPTION
"Multicast duration"
        ::= { utsOnuCtcMulticastEntry 9 }

--
-----------------------------------------------------------
--      ONU multicast statistics
-----------------------------------------------------------

utsOnuCtcMCastStatTable OBJECT-TYPE
SYNTAX  SEQUENCE OF UtsOnuCtcMCastStatEntry
        MAX-ACCESS  not-accessible
        STATUS  current
        DESCRIPTION
"ONU multicast statistics table."
        ::= { utsCtcMulticastCtrlExtObjects 7 }

utsOnuCtcMCastStatEntry OBJECT-TYPE
SYNTAX  UtsOnuCtcMCastStatEntry
       MAX-ACCESS  not-accessible
       STATUS  current
       DESCRIPTION
"An entry in the ONU multicast statistics table."
       INDEX  { utsDot3OnuMCastStatMGroup }
       ::= { utsOnuCtcMCastStatTable 1 }

UtsOnuCtcMCastStatEntry ::=
       SEQUENCE
       {
               utsDot3OnuMCastStatMGroup             IpAddress,
               utsDot3OnuMCastStatUserNum            INTEGER,
               utsDot3OnuMCastStatRequestNum         INTEGER,
               utsDot3OnuMCastStatReqRejNum          INTEGER,
               utsDot3OnuMCastStatTotalTime          INTEGER,
               utsDot3OnuMCastStatAverageTime        INTEGER

       }

utsDot3OnuMCastStatMGroup OBJECT-TYPE
SYNTAX  IpAddress
       MAX-ACCESS  not-accessible
       STATUS  current
       DESCRIPTION
"Multicast groups"
        ::= { utsOnuCtcMCastStatEntry 2 }

utsDot3OnuMCastStatUserNum OBJECT-TYPE
SYNTAX  INTEGER
       MAX-ACCESS  read-only
       STATUS  current
       DESCRIPTION
"User number under this group"
        ::= { utsOnuCtcMCastStatEntry 3 }

utsDot3OnuMCastStatRequestNum OBJECT-TYPE
SYNTAX  INTEGER
       MAX-ACCESS  read-only
       STATUS  current
       DESCRIPTION
"Request number for this group"
        ::= { utsOnuCtcMCastStatEntry 4 }

utsDot3OnuMCastStatReqRejNum OBJECT-TYPE
SYNTAX  INTEGER
       MAX-ACCESS  read-only
       STATUS  current
       DESCRIPTION
"Rejected number for this group"
        ::= { utsOnuCtcMCastStatEntry 5 }

utsDot3OnuMCastStatTotalTime OBJECT-TYPE
SYNTAX  INTEGER
       MAX-ACCESS  read-only
       STATUS  current
       DESCRIPTION
"Totoal time for this group"
        ::= { utsOnuCtcMCastStatEntry 6 }

utsDot3OnuMCastStatAverageTime OBJECT-TYPE
SYNTAX  INTEGER
       MAX-ACCESS  read-only
       STATUS  current
       DESCRIPTION
"Average time for this group"
        ::= { utsOnuCtcMCastStatEntry 8 }

-- Multicast Online Group Stat. per ONU, required by NMS

utsOnuCtcMulticastOnlineGroupStatTable OBJECT-TYPE
SYNTAX  SEQUENCE OF UtsOnuCtcMulticastOnlineGroupStatEntry
        MAX-ACCESS  not-accessible
        STATUS  current
        DESCRIPTION
"Table for ONU multicast online group stat table."
        ::= { utsCtcMulticastCtrlExtObjects 8 }

utsOnuCtcMulticastOnlineGroupStatEntry OBJECT-TYPE
SYNTAX  UtsOnuCtcMulticastOnlineGroupStatEntry
       MAX-ACCESS  not-accessible
       STATUS  current
       DESCRIPTION
"An entry in the ONU multicast online group stat table."
       INDEX  { utsDot3OnuMCastOnlineGroupStatModuleId,utsDot3OnuMCastOnlineGroupStatDeviceId,utsDot3OnuMCastOnlineGroupStatPortId,
                utsDot3OnuMCastOnlineGroupStatLogicalPortId}
       ::= { utsOnuCtcMulticastOnlineGroupStatTable 1 }

UtsOnuCtcMulticastOnlineGroupStatEntry ::=
       SEQUENCE
       {
               utsDot3OnuMCastOnlineGroupStatModuleId	             INTEGER,
               utsDot3OnuMCastOnlineGroupStatDeviceId                INTEGER,
               utsDot3OnuMCastOnlineGroupStatPortId	                 INTEGER,
               utsDot3OnuMCastOnlineGroupStatLogicalPortId	         INTEGER,
               utsDot3OnuMCastOnlineGroupStatNumber                  INTEGER
       }

utsDot3OnuMCastOnlineGroupStatModuleId OBJECT-TYPE
SYNTAX  INTEGER(1..12)
       MAX-ACCESS  not-accessible
       STATUS  current
       DESCRIPTION
"The OLT module id for the current ONU."
        ::= { utsOnuCtcMulticastOnlineGroupStatEntry 1 }

utsDot3OnuMCastOnlineGroupStatDeviceId OBJECT-TYPE
SYNTAX  INTEGER(1..4)
       MAX-ACCESS  not-accessible
       STATUS  current
       DESCRIPTION
"The OLT device id for the current ONU."
        ::= { utsOnuCtcMulticastOnlineGroupStatEntry 2 }

utsDot3OnuMCastOnlineGroupStatPortId OBJECT-TYPE
SYNTAX  INTEGER(1..4)
       MAX-ACCESS  not-accessible
       STATUS  current
       DESCRIPTION
"The OLT port id for the current ONU."
        ::= { utsOnuCtcMulticastOnlineGroupStatEntry 3 }

utsDot3OnuMCastOnlineGroupStatLogicalPortId OBJECT-TYPE
SYNTAX  INTEGER(1..64)
       MAX-ACCESS  not-accessible
       STATUS  current
       DESCRIPTION
"The logical port id for the current ONU."
        ::= { utsOnuCtcMulticastOnlineGroupStatEntry 4 }


utsDot3OnuMCastOnlineGroupStatNumber OBJECT-TYPE
SYNTAX INTEGER
       MAX-ACCESS  read-only
       STATUS  current
       DESCRIPTION
"Multicast online group stat number."
        ::= { utsOnuCtcMulticastOnlineGroupStatEntry 5 }


-- Multicast Stat. per UNI per ONU, required by NMS

utsOnuCtcMulticastStatForUserPortTable OBJECT-TYPE
SYNTAX  SEQUENCE OF UtsOnuCtcMulticastStatForUserPortEntry
        MAX-ACCESS  not-accessible
        STATUS  current
        DESCRIPTION
"Table for ONU multicast stat for each ONU UNI user port table."
        ::= { utsCtcMulticastCtrlExtObjects 9 }

utsOnuCtcMulticastStatForUserPortEntry OBJECT-TYPE
SYNTAX  UtsOnuCtcMulticastStatForUserPortEntry
       MAX-ACCESS  not-accessible
       STATUS  current
       DESCRIPTION
"An entry in the ONU multicast user port stat table."
       INDEX  { utsDot3OnuMCastStatForUserPortModuleId,utsDot3OnuMCastStatForUserPortDeviceId,utsDot3OnuMCastStatForUserPortPortId,
                utsDot3OnuMCastStatForUserPortLogicalPortId,utsDot3OnuMCastStatForUserPortEthernetPortId }
       ::= { utsOnuCtcMulticastStatForUserPortTable 1 }

UtsOnuCtcMulticastStatForUserPortEntry ::=
       SEQUENCE
       {
               utsDot3OnuMCastStatForUserPortModuleId	             INTEGER,
               utsDot3OnuMCastStatForUserPortDeviceId                INTEGER,
               utsDot3OnuMCastStatForUserPortPortId	                 INTEGER,
               utsDot3OnuMCastStatForUserPortLogicalPortId	         INTEGER,
               utsDot3OnuMCastStatForUserPortEthernetPortId          INTEGER,
               utsDot3OnuMCastStatForUserPortViewNumber              INTEGER,
               utsDot3OnuMCastStatForUserPortTotalTime               INTEGER,
               utsDot3OnuMCastStatForUserPortAverageTime             INTEGER
       }

utsDot3OnuMCastStatForUserPortModuleId OBJECT-TYPE
SYNTAX  INTEGER(1..12)
       MAX-ACCESS  not-accessible
       STATUS  current
       DESCRIPTION
"The OLT module id for the current ONU."
        ::= { utsOnuCtcMulticastStatForUserPortEntry 1 }

utsDot3OnuMCastStatForUserPortDeviceId OBJECT-TYPE
SYNTAX  INTEGER(1..4)
       MAX-ACCESS  not-accessible
       STATUS  current
       DESCRIPTION
"The OLT device id for the current ONU."
        ::= { utsOnuCtcMulticastStatForUserPortEntry 2 }

utsDot3OnuMCastStatForUserPortPortId OBJECT-TYPE
SYNTAX  INTEGER(1..4)
       MAX-ACCESS  not-accessible
       STATUS  current
       DESCRIPTION
"The OLT port id for the current ONU."
        ::= { utsOnuCtcMulticastStatForUserPortEntry 3 }

utsDot3OnuMCastStatForUserPortLogicalPortId OBJECT-TYPE
SYNTAX  INTEGER(1..64)
       MAX-ACCESS  not-accessible
       STATUS  current
       DESCRIPTION
"The logical port id for the current ONU."
        ::= { utsOnuCtcMulticastStatForUserPortEntry 4 }

utsDot3OnuMCastStatForUserPortEthernetPortId OBJECT-TYPE
SYNTAX  INTEGER
       MAX-ACCESS  not-accessible
       STATUS  current
       DESCRIPTION
"The ethernet port id for the current ONU."
        ::= { utsOnuCtcMulticastStatForUserPortEntry 5 }


utsDot3OnuMCastStatForUserPortViewNumber OBJECT-TYPE
SYNTAX INTEGER
       MAX-ACCESS  read-only
       STATUS  current
       DESCRIPTION
"Multicast requrest number for the ONU UNI port."
        ::= { utsOnuCtcMulticastStatForUserPortEntry 6 }


utsDot3OnuMCastStatForUserPortTotalTime OBJECT-TYPE
SYNTAX INTEGER
       MAX-ACCESS  read-only
       STATUS  current
       DESCRIPTION
"Multicast total time for the ONU UNI port."
        ::= { utsOnuCtcMulticastStatForUserPortEntry 7 }

utsDot3OnuMCastStatForUserPortAverageTime OBJECT-TYPE
SYNTAX INTEGER
       MAX-ACCESS  read-only
       STATUS  current
       DESCRIPTION
"Multicast average time for the ONU UNI port."
        ::= { utsOnuCtcMulticastStatForUserPortEntry 8 }

--
--   UTS Diagnosis extension.
--

utsDiagnosisPONConfExt  OBJECT IDENTIFIER ::= { utsDiagnosisConfExt  1 }

utsDiagnosisEthConfExt OBJECT IDENTIFIER ::= { utsDiagnosisConfExt  2 }

--  ONU Optical Power Measure Table

utsDot3Onu2OpticalPowerMeasureTable OBJECT-TYPE
SYNTAX  SEQUENCE OF UtsDot3Onu2OpticalPowerMeasureEntry
        MAX-ACCESS  not-accessible
        STATUS  current
        DESCRIPTION
"Table for dot3 ONU Optical Power Measure."
        ::= { utsDiagnosisPONConfExt 1 }

utsDot3Onu2OpticalPowerMeasureEntry OBJECT-TYPE
SYNTAX  UtsDot3Onu2OpticalPowerMeasureEntry
       MAX-ACCESS  not-accessible
       STATUS  current
       DESCRIPTION
"An entry in the dot3 Onu Optical Power Measure table."
       INDEX  { utsDot3OnuOpticalPowerModuleId,utsDot3OnuOpticalPowerDeviceId,utsDot3OnuOpticalPowerPortId,utsDot3OnuOpticalPowerLogicalPortId}
       ::= { utsDot3Onu2OpticalPowerMeasureTable 1 }

UtsDot3Onu2OpticalPowerMeasureEntry ::=
       SEQUENCE {
               utsDot3OnuOpticalPowerModuleId		   INTEGER,
               utsDot3OnuOpticalPowerDeviceId          INTEGER,
               utsDot3OnuOpticalPowerPortId			   INTEGER,
               utsDot3OnuOpticalPowerLogicalPortId	   INTEGER,
               utsDot3OnuOpticalPowerValue             INTEGER,
               utsDot3OnuOpticalPowerAdmin             INTEGER
        }

utsDot3OnuOpticalPowerModuleId OBJECT-TYPE
SYNTAX  INTEGER
       MAX-ACCESS  read-only
       STATUS  current
       DESCRIPTION
"A read only value to identifiy the OLT module id for the current ONU."
        ::= { utsDot3Onu2OpticalPowerMeasureEntry 1 }

utsDot3OnuOpticalPowerDeviceId OBJECT-TYPE
SYNTAX  INTEGER
       MAX-ACCESS  read-only
       STATUS  current
       DESCRIPTION
"A read only value to identifiy the OLT device id for the current ONU."
        ::= { utsDot3Onu2OpticalPowerMeasureEntry 2 }

utsDot3OnuOpticalPowerPortId OBJECT-TYPE
SYNTAX  INTEGER
       MAX-ACCESS  read-only
       STATUS  current
       DESCRIPTION
"A read only value to identifiy the OLT port id for the current ONU."
        ::= { utsDot3Onu2OpticalPowerMeasureEntry 3 }

utsDot3OnuOpticalPowerLogicalPortId OBJECT-TYPE
SYNTAX  INTEGER
       MAX-ACCESS  read-only
       STATUS  current
       DESCRIPTION
"A read only value to identifiy the logical port id for the current ONU."
        ::= { utsDot3Onu2OpticalPowerMeasureEntry 4 }

utsDot3OnuOpticalPowerValue OBJECT-TYPE
SYNTAX  INTEGER
       MAX-ACCESS  read-only
       STATUS  current
       DESCRIPTION
"A read only value of the ONU optical power."
        ::= { utsDot3Onu2OpticalPowerMeasureEntry 5 }

utsDot3OnuOpticalPowerAdmin OBJECT-TYPE
SYNTAX  INTEGER
{
        enable(1),
        disable(2)       --default value
}
       MAX-ACCESS  read-write
       STATUS  current
       DESCRIPTION
"This entry to set the optical power measure switch,when NMS want to get the power value, NMS should
set the admin switch to enable first, then set the request to get the value, when Node return the result
of the power value, Node should set the admin switch to disable auto."
        ::= { utsDot3Onu2OpticalPowerMeasureEntry 6 }


--  OLT Port Diagnosis Table

utsDot3Olt2PortDiagnosisTable OBJECT-TYPE
SYNTAX  SEQUENCE OF UtsDot3Olt2PortDiagnosisEntry
        MAX-ACCESS  not-accessible
        STATUS  current
        DESCRIPTION
"Table for OLT type 2 port Diagnosis MIBs."
        ::= { utsDiagnosisPONConfExt 2 }

utsDot3Olt2PortDiagnosisEntry OBJECT-TYPE
SYNTAX  UtsDot3Olt2PortDiagnosisEntry
       MAX-ACCESS  not-accessible
       STATUS  current
       DESCRIPTION
"An entry in the OLT type 2 port Diagnosis MIBs table."
       INDEX  { utsDot3OltPortDiagnosisModuleId, utsDot3OltPortDiagnosisDeviceId, utsDot3OltPortDiagnosisPortId }
       ::= { utsDot3Olt2PortDiagnosisTable 1 }

UtsDot3Olt2PortDiagnosisEntry ::=
       SEQUENCE {
                    utsDot3OltPortDiagnosisModuleId 	        INTEGER,
                    utsDot3OltPortDiagnosisDeviceId             INTEGER,
                    utsDot3OltPortDiagnosisPortId	            INTEGER,
                    utsDot3OltPortDiagnosisAction               INTEGER,
                    utsDot3OltPortDiagnosisStatus               INTEGER,
                    utsDot3OltPortDiagnosisResult               DisplayString
       }

utsDot3OltPortDiagnosisModuleId OBJECT-TYPE
SYNTAX  INTEGER
       MAX-ACCESS  read-only
       STATUS  current
       DESCRIPTION
"A read-only value that identifies the olt module index"
        ::= { utsDot3Olt2PortDiagnosisEntry 1 }

utsDot3OltPortDiagnosisDeviceId OBJECT-TYPE
SYNTAX  INTEGER
       MAX-ACCESS  read-only
       STATUS  current
       DESCRIPTION
"A read-only value that identifies the olt device index"
        ::= { utsDot3Olt2PortDiagnosisEntry 2 }

utsDot3OltPortDiagnosisPortId OBJECT-TYPE
SYNTAX  INTEGER
       MAX-ACCESS  read-only
       STATUS  current
       DESCRIPTION
"A read-only value that identifies the olt port index"
        ::= { utsDot3Olt2PortDiagnosisEntry 3 }

utsDot3OltPortDiagnosisAction OBJECT-TYPE
       SYNTAX  INTEGER
       {
       	   start(1),
       	   stop(2)
       }
       MAX-ACCESS  read-write
       STATUS  current
       DESCRIPTION
"Start or stop diagnosis process on this pon port."
        ::= { utsDot3Olt2PortDiagnosisEntry 4 }

utsDot3OltPortDiagnosisStatus OBJECT-TYPE
       SYNTAX  INTEGER
       MAX-ACCESS  read-only
       STATUS  current
       DESCRIPTION
"The percentage of diagnosis process, the range is 0 to 100."
        ::= { utsDot3Olt2PortDiagnosisEntry 5 }

utsDot3OltPortDiagnosisResult OBJECT-TYPE
       SYNTAX  DisplayString(SIZE(0..255))
       MAX-ACCESS  read-only
       STATUS  current
       DESCRIPTION
"The Result of diagnosis result, there are list all bad onu's mac address, the format like,
 '000e35467412,000f1fbbef55,000e123456', a null string reprents no bad onu"
        ::= { utsDot3Olt2PortDiagnosisEntry 6 }


--  ONU Optical Transceiver Diagnosis Table

utsDot3Onu2OpticalTransceiverDiagnosisTable OBJECT-TYPE
SYNTAX  SEQUENCE OF UtsDot3Onu2OpticalTransceiverDiagnosisEntry
        MAX-ACCESS  not-accessible
        STATUS  current
        DESCRIPTION
"Table for dot3 ONU Optical Transceiver Diagnosis."
        ::= { utsDiagnosisPONConfExt 3 }

utsDot3Onu2OpticalTransceiverDiagnosisEntry OBJECT-TYPE
SYNTAX  UtsDot3Onu2OpticalTransceiverDiagnosisEntry
       MAX-ACCESS  not-accessible
       STATUS  current
       DESCRIPTION
"An entry in the dot3 Onu Optical Transceiver Diagnosis table."
       INDEX  { utsDot3OnuOpticalTransceiverDiagnosisModuleId,utsDot3OnuOpticalTransceiverDiagnosisDeviceId,utsDot3OnuOpticalTransceiverDiagnosisPortId,utsDot3OnuOpticalTransceiverDiagnosisLogicalPortId}
       ::= { utsDot3Onu2OpticalTransceiverDiagnosisTable 1 }

UtsDot3Onu2OpticalTransceiverDiagnosisEntry ::=
       SEQUENCE {
               utsDot3OnuOpticalTransceiverDiagnosisModuleId		    INTEGER,
               utsDot3OnuOpticalTransceiverDiagnosisDeviceId            INTEGER,
               utsDot3OnuOpticalTransceiverDiagnosisPortId			    INTEGER,
               utsDot3OnuOpticalTransceiverDiagnosisLogicalPortId	    INTEGER,
               utsDot3OnuOpticalTransceiverDiagnosisTemperature         INTEGER,
               utsDot3OnuOpticalTransceiverDiagnosisVoltage             INTEGER,
               utsDot3OnuOpticalTransceiverDiagnosisTxBiasCurrent       INTEGER,
               utsDot3OnuOpticalTransceiverDiagnosisTxPower             INTEGER,
               utsDot3OnuOpticalTransceiverDiagnosisRxPower             INTEGER,
               utsDot3OnuOpticalTransceiverDiagnosisAlarmOperation      INTEGER,
               utsDot3OnuOpticalTransceiverDiagnosisTempHighAlarm       INTEGER,
               utsDot3OnuOpticalTransceiverDiagnosisTempLowAlarm        INTEGER,
               utsDot3OnuOpticalTransceiverDiagnosisTempHighWarning     INTEGER,
               utsDot3OnuOpticalTransceiverDiagnosisTempLowWarning      INTEGER,
               utsDot3OnuOpticalTransceiverDiagnosisVoltageHighAlarm       INTEGER,
               utsDot3OnuOpticalTransceiverDiagnosisVoltageLowAlarm        INTEGER,
               utsDot3OnuOpticalTransceiverDiagnosisVoltageHighWarning     INTEGER,
               utsDot3OnuOpticalTransceiverDiagnosisVoltageLowWarning      INTEGER,
               utsDot3OnuOpticalTransceiverDiagnosisBiasHighAlarm          INTEGER,
               utsDot3OnuOpticalTransceiverDiagnosisBiasLowAlarm           INTEGER,
               utsDot3OnuOpticalTransceiverDiagnosisBiasHighWarning        INTEGER,
               utsDot3OnuOpticalTransceiverDiagnosisBiasLowWarning         INTEGER,
               utsDot3OnuOpticalTransceiverDiagnosisTxPowerHighAlarm          INTEGER,
               utsDot3OnuOpticalTransceiverDiagnosisTxPowerLowAlarm           INTEGER,
               utsDot3OnuOpticalTransceiverDiagnosisTxPowerHighWarning        INTEGER,
               utsDot3OnuOpticalTransceiverDiagnosisTxPowerLowWarning         INTEGER,
               utsDot3OnuOpticalTransceiverDiagnosisRxPowerHighAlarm          INTEGER,
               utsDot3OnuOpticalTransceiverDiagnosisRxPowerLowAlarm           INTEGER,
               utsDot3OnuOpticalTransceiverDiagnosisRxPowerHighWarning        INTEGER,
               utsDot3OnuOpticalTransceiverDiagnosisRxPowerLowWarning         INTEGER
        }

utsDot3OnuOpticalTransceiverDiagnosisModuleId OBJECT-TYPE
SYNTAX  INTEGER
       MAX-ACCESS  read-only
       STATUS  current
       DESCRIPTION
"A read only value to identifiy the OLT module id for the current ONU."
        ::= { utsDot3Onu2OpticalTransceiverDiagnosisEntry 1 }

utsDot3OnuOpticalTransceiverDiagnosisDeviceId OBJECT-TYPE
SYNTAX  INTEGER
       MAX-ACCESS  read-only
       STATUS  current
       DESCRIPTION
"A read only value to identifiy the OLT device id for the current ONU."
        ::= { utsDot3Onu2OpticalTransceiverDiagnosisEntry 2 }

utsDot3OnuOpticalTransceiverDiagnosisPortId OBJECT-TYPE
SYNTAX  INTEGER
       MAX-ACCESS  read-only
       STATUS  current
       DESCRIPTION
"A read only value to identifiy the OLT port id for the current ONU."
        ::= { utsDot3Onu2OpticalTransceiverDiagnosisEntry 3 }

utsDot3OnuOpticalTransceiverDiagnosisLogicalPortId OBJECT-TYPE
SYNTAX  INTEGER
       MAX-ACCESS  read-only
       STATUS  current
       DESCRIPTION
"A read only value to identifiy the logical port id for the current ONU."
        ::= { utsDot3Onu2OpticalTransceiverDiagnosisEntry 4 }

utsDot3OnuOpticalTransceiverDiagnosisTemperature OBJECT-TYPE
SYNTAX  INTEGER
       MAX-ACCESS  read-only
       STATUS  current
       DESCRIPTION
"A read only value of the ONU optical temperature, the unit is 1/256 centigrade, the fact range should be -128 to +128."
        ::= { utsDot3Onu2OpticalTransceiverDiagnosisEntry 5 }

utsDot3OnuOpticalTransceiverDiagnosisVoltage OBJECT-TYPE
SYNTAX  INTEGER
       MAX-ACCESS  read-only
       STATUS  current
       DESCRIPTION
"A read only value of the ONU optical Voltage, the unit is 100 microvolt, the fact range should be 0 to 6.55 volt."
        ::= { utsDot3Onu2OpticalTransceiverDiagnosisEntry 6 }

utsDot3OnuOpticalTransceiverDiagnosisTxBiasCurrent OBJECT-TYPE
SYNTAX  INTEGER
       MAX-ACCESS  read-only
       STATUS  current
       DESCRIPTION
"A read only value of the ONU optical Tx Bias Current, the unit is 2 microampere, the fact range should be 0 to 131 milliampere."
        ::= { utsDot3Onu2OpticalTransceiverDiagnosisEntry 7 }


utsDot3OnuOpticalTransceiverDiagnosisTxPower OBJECT-TYPE
SYNTAX  INTEGER
       MAX-ACCESS  read-only
       STATUS  current
       DESCRIPTION
"A read only value of the ONU optical Tx Power, the unit is 0.1 uW, the fact range should be 0 to 6.5535mW."
        ::= { utsDot3Onu2OpticalTransceiverDiagnosisEntry 8 }


utsDot3OnuOpticalTransceiverDiagnosisRxPower OBJECT-TYPE
SYNTAX  INTEGER
       MAX-ACCESS  read-only
       STATUS  current
       DESCRIPTION
"A read only value of the ONU optical Rx Power, the unit is 0.1 uW, the fact range should be 0 to 6.5535mW."
        ::= { utsDot3Onu2OpticalTransceiverDiagnosisEntry 9 }

utsDot3OnuOpticalTransceiverDiagnosisAlarmOperation OBJECT-TYPE
SYNTAX  INTEGER
     {
        enable(1),
        disable(2)
     }
       MAX-ACCESS  read-write
       STATUS  current
       DESCRIPTION
"A setting value of the ONU Alarm Operation."
        ::= { utsDot3Onu2OpticalTransceiverDiagnosisEntry 12 }

utsDot3OnuOpticalTransceiverDiagnosisTempHighAlarm OBJECT-TYPE
SYNTAX  INTEGER
       MAX-ACCESS  read-write
       STATUS  current
       DESCRIPTION
"A setting value of the ONU Temp High Alarm."
        ::= { utsDot3Onu2OpticalTransceiverDiagnosisEntry 15 }

utsDot3OnuOpticalTransceiverDiagnosisTempLowAlarm OBJECT-TYPE
SYNTAX  INTEGER
       MAX-ACCESS  read-write
       STATUS  current
       DESCRIPTION
"A setting value of the ONU Temp Low Alarm."
        ::= { utsDot3Onu2OpticalTransceiverDiagnosisEntry 16 }

utsDot3OnuOpticalTransceiverDiagnosisTempHighWarning OBJECT-TYPE
SYNTAX  INTEGER
       MAX-ACCESS  read-write
       STATUS  current
       DESCRIPTION
"A setting value of the ONU Temp High Warning."
        ::= { utsDot3Onu2OpticalTransceiverDiagnosisEntry 17 }

utsDot3OnuOpticalTransceiverDiagnosisTempLowWarning OBJECT-TYPE
SYNTAX  INTEGER
       MAX-ACCESS  read-write
       STATUS  current
       DESCRIPTION
"A setting value of the ONU Temp Low Warning."
        ::= { utsDot3Onu2OpticalTransceiverDiagnosisEntry 18 }


utsDot3OnuOpticalTransceiverDiagnosisVoltageHighAlarm OBJECT-TYPE
SYNTAX  INTEGER
       MAX-ACCESS  read-write
       STATUS  current
       DESCRIPTION
"A setting value of the ONU Voltage High Alarm."
        ::= { utsDot3Onu2OpticalTransceiverDiagnosisEntry 19 }

utsDot3OnuOpticalTransceiverDiagnosisVoltageLowAlarm OBJECT-TYPE
SYNTAX  INTEGER
       MAX-ACCESS  read-write
       STATUS  current
       DESCRIPTION
"A setting value of the ONU Voltage Low Alarm."
        ::= { utsDot3Onu2OpticalTransceiverDiagnosisEntry 20 }

utsDot3OnuOpticalTransceiverDiagnosisVoltageHighWarning OBJECT-TYPE
SYNTAX  INTEGER
       MAX-ACCESS  read-write
       STATUS  current
       DESCRIPTION
"A setting value of the ONU Voltage High Warning."
        ::= { utsDot3Onu2OpticalTransceiverDiagnosisEntry 21 }

utsDot3OnuOpticalTransceiverDiagnosisVoltageLowWarning OBJECT-TYPE
SYNTAX  INTEGER
       MAX-ACCESS  read-write
       STATUS  current
       DESCRIPTION
"A setting value of the ONU Voltage Low Warning."
        ::= { utsDot3Onu2OpticalTransceiverDiagnosisEntry 22 }

utsDot3OnuOpticalTransceiverDiagnosisBiasHighAlarm OBJECT-TYPE
SYNTAX  INTEGER
       MAX-ACCESS  read-write
       STATUS  current
       DESCRIPTION
"A setting value of the ONU Bias High Alarm."
        ::= { utsDot3Onu2OpticalTransceiverDiagnosisEntry 23 }

utsDot3OnuOpticalTransceiverDiagnosisBiasLowAlarm OBJECT-TYPE
SYNTAX  INTEGER
       MAX-ACCESS  read-write
       STATUS  current
       DESCRIPTION
"A setting value of the ONU Bias Low Alarm."
        ::= { utsDot3Onu2OpticalTransceiverDiagnosisEntry 24 }

utsDot3OnuOpticalTransceiverDiagnosisBiasHighWarning OBJECT-TYPE
SYNTAX  INTEGER
       MAX-ACCESS  read-write
       STATUS  current
       DESCRIPTION
"A setting value of the ONU Bias High Warning."
        ::= { utsDot3Onu2OpticalTransceiverDiagnosisEntry 25 }

utsDot3OnuOpticalTransceiverDiagnosisBiasLowWarning OBJECT-TYPE
SYNTAX  INTEGER
       MAX-ACCESS  read-write
       STATUS  current
       DESCRIPTION
"A setting value of the ONU Bias Low Warning."
        ::= { utsDot3Onu2OpticalTransceiverDiagnosisEntry 26 }

utsDot3OnuOpticalTransceiverDiagnosisTxPowerHighAlarm OBJECT-TYPE
SYNTAX  INTEGER
       MAX-ACCESS  read-write
       STATUS  current
       DESCRIPTION
"A setting value of the ONU Tx Power High Alarm."
        ::= { utsDot3Onu2OpticalTransceiverDiagnosisEntry 27 }

utsDot3OnuOpticalTransceiverDiagnosisTxPowerLowAlarm OBJECT-TYPE
SYNTAX  INTEGER
       MAX-ACCESS  read-write
       STATUS  current
       DESCRIPTION
"A setting value of the ONU Tx Power Low Alarm."
        ::= { utsDot3Onu2OpticalTransceiverDiagnosisEntry 28 }

utsDot3OnuOpticalTransceiverDiagnosisTxPowerHighWarning OBJECT-TYPE
SYNTAX  INTEGER
       MAX-ACCESS  read-write
       STATUS  current
       DESCRIPTION
"A setting value of the ONU Tx Power High Warning."
        ::= { utsDot3Onu2OpticalTransceiverDiagnosisEntry 29 }

utsDot3OnuOpticalTransceiverDiagnosisTxPowerLowWarning OBJECT-TYPE
SYNTAX  INTEGER
       MAX-ACCESS  read-write
       STATUS  current
       DESCRIPTION
"A setting value of the ONU Tx Power Low Warning."
        ::= { utsDot3Onu2OpticalTransceiverDiagnosisEntry 30 }

utsDot3OnuOpticalTransceiverDiagnosisRxPowerHighAlarm OBJECT-TYPE
SYNTAX  INTEGER
       MAX-ACCESS  read-write
       STATUS  current
       DESCRIPTION
"A setting value of the ONU Rx Power High Alarm."
        ::= { utsDot3Onu2OpticalTransceiverDiagnosisEntry 31 }

utsDot3OnuOpticalTransceiverDiagnosisRxPowerLowAlarm OBJECT-TYPE
SYNTAX  INTEGER
       MAX-ACCESS  read-write
       STATUS  current
       DESCRIPTION
"A setting value of the ONU Rx Power Low Alarm."
        ::= { utsDot3Onu2OpticalTransceiverDiagnosisEntry 32 }

utsDot3OnuOpticalTransceiverDiagnosisRxPowerHighWarning OBJECT-TYPE
SYNTAX  INTEGER
       MAX-ACCESS  read-write
       STATUS  current
       DESCRIPTION
"A setting value of the ONU Rx Power High Warning."
        ::= { utsDot3Onu2OpticalTransceiverDiagnosisEntry 33 }

utsDot3OnuOpticalTransceiverDiagnosisRxPowerLowWarning OBJECT-TYPE
SYNTAX  INTEGER
       MAX-ACCESS  read-write
       STATUS  current
       DESCRIPTION
"A setting value of the ONU Rx Power Low Warning."
        ::= { utsDot3Onu2OpticalTransceiverDiagnosisEntry 34 }
END
