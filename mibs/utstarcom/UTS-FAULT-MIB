UTS-FAULT-MIB DEFINITIONS ::= BEGIN

IMPORTS
	OBJECT-TYPE, OBJECT-IDENTITY, MODULE-IDENTITY,
	IpAddress, Unsigned32, Integer32, Counter32
		FROM SNMPv2-SMI
	TEXTUAL-CONVENTION, DisplayString, RowStatus,
	RowPointer, DateAndTime
		FROM SNMPv2-TC
	utCommonOam, utCommonPlatformModules
		FROM UTS-COMMON-MIB
	WORD, BOOL
		FROM UTS-COMMON-TC-MIB;

utFmModule MODULE-IDENTITY
	LAST-UPDATED "200111151635Z"
	ORGANIZATION
		"UTStarcom (China) Corp., ShenZhen Branch.
		3G Department, OA&M Team."
	CONTACT-INFO
		"Contact: UTStarcom Customer Support Group

		Postal: UTStarcom Shenzhen R&D Center
		            3/F, Legend Building,
		            High-tech Industrial Park,
		            Nanshan Shenzhen, 518057, PRC

		            Tel: +86 (755) 6983555
		            Fax: +86 (755) 6983786

		            WEB: http://www.utstar.com"
	DESCRIPTION
		"The MIB module for UTStarcom UMTS Embedded System Fault Management.

		Copyright (c) 2002 UTStarcom, Inc.
		All rights reserved.

		Reproduction of this document is authorized on the condition that the
		foregoing copyright notice is included.

		This SNMP MIB module (Specification) embodies UTStarcom proprietary
		intellectual property.  UTStarcom retains all title and ownership in
		the Specification, including any revisions.

		UTStarcom grants all interested parties a non-exclusive license to use
		and distribute an unmodified copy of this Specification in connection
		with management of UTStarcom products, and without fee, provided this
		copyright notice and license appear on all copies.

		This Specification is supplied 'AS IS' and UTStarcom makes no warranty,
		either express or implied, as to the use, operation, condition, or
		performance of the Specification."

	REVISION "200204280000Z"
	DESCRIPTION
		"Initial version of the root MIB module UTS-COMMON-MIB."

	REVISION "200204271337Z"
	DESCRIPTION
		"Initial version of the root MIB module for GGSN function"

	REVISION "200204160000Z"
	DESCRIPTION
		"Initial version of the root MIB module UTS-COMMON-MIB."

	REVISION "200402251547Z"
	DESCRIPTION
		"add utFmAlarmDelayTable to manage MTNET alarm delay rule."

	REVISION "200403030950Z"
	DESCRIPTION
		"Modify 3G alarm resource type list."
::= { utCommonPlatformModules 2 }


AlarmResourceType ::= TEXTUAL-CONVENTION
	STATUS     current
	DESCRIPTION
		"3G FM Resource Type list for R2.5

		========Software error
		Inner software module communication

		General software resource error

		Inter board communication

		Platform detected software error
		Notes, for CMS (Chassis management system) only

		Software module (Server type NE)
		Notes,
		such as software module fail, application abnormal shutdown,

		Inter-software module communication (Server type NE)

		NE external communication with private protocol
		Notes, applicable to inter-NE communication with private protocol

		========Protocol error
		MTP1 protocol

		MTP2 protocol

		MTP3 protocol

		M3UA protocol

		SCCP protocol

		ISUP protocol

		RANAP protocol

		MAP-B protocol

		MAP-Gd protocol

		MAP-C protocol

		MAP-D protocol

		MAP-E  protocol

		MAP-G protocol

		MAP-Gr protocol

		MAP-Gc protocol

		MAP-Lh protocol

		MAP-Lg  protocol

		SAAL protocol  protocol

		CAP protocol  protocol

		INAP protocol protocol

		GTP' protocol

		MEGACO protocol

		GMM protocol

		BSSAP+ protocol

		SM protocol

		SGSN SM protocol

		Gi Interface

		IMA Protocol

		STC protocol

		ALCAP protocol

		GTP-U protocol

		========Physical/Logical link error
		MTP3 link

		MTP3 link set

		MTP3 route set

		MTP3B link

		MTP3B link set

		MTP3B route set

		M3UA Association

		M3UA PSP

		M3UA PS

		E1 trunk

		E1 circuit

		H110 Time slot

		STM link

		IP link

		SCCOP link

		AAL2-PVC

		AAL5-PVC


		========Specific Resource error
		CDR Resource

		CELL

		Hardware resource (fan/power/board hardware error/clock/etc.)

		Sub-agent problem

		Platform management channel problem

		IP/MAC address problem
		Notes, IP/MAC address invalid/conflict

		Common protocol HA control part

		User dialog
		Notes, such as user dialog usage alarm, etc.

		Database connection

		Authentication error
		Notes,
		Such as utiGmlcClientAuthFailure,utiGmlcSubscriberAuthFailure,utiGmlcGMLCAuthFailure, etc.

		GMLC route problem

		========Threshold crossing alerting
		TCA

		value 0 means all resource type.
		"
	SYNTAX  INTEGER {
		alarmResourceTypeDefault (0),
		alarmResourceInnerSofModuleComm (1),
		alarmResourceGenSoftErr (2),
		alarmResourceInterBoardComm (3),
		alarmResourcePlatformSoft (4),
		alarmResourceSoftModule (5),
		alarmResourceInterSoftModule (6),
		alarmResourceNeExtComm (7),
		alarmResourceMtp1Protocol (21),
		alarmResourceMtp2Protocol (22),
		alarmResourceMtp3Protocol (23),
		alarmResourceM3uaProtocol (24),
		alarmResourceSccpProtocol (25),
		alarmResourceIsupProtocol (26),
		alarmResourceRanapProtocol (27),
		alarmResourceMapBProtocol (28),
		alarmResourceMapGdProtocol (29),
		alarmResourceMapCProtocol (30),
		alarmResourceMapDProtocol (31),
		alarmResourceMapEProtocol (32),
		alarmResourceMapGProtocol (33),
		alarmResourceMapGrProtocol (34),
		alarmResourceMapGcProtocol (35),
		alarmResourceMapLhProtocol (36),
		alarmResourceMapLgProtocol (37),
		alarmResourceSaalProtocol (38),
		alarmResourceCapProtocol (39),
		alarmResourceInapProtcol (40),
		alarmResourceGtpProtocol (41),
		alarmResourceMegacoProtocol (42),
		alarmResourceGmmProtocol (43),
		alarmResourceBssapProtocol (44),
		alarmResourceSmProtocol (45),
		alarmResourceSgsnSmProtocol (46),
		alarmResourceGiInterface (47),
		alarmResourceImaProtocol (48),
		alarmResourceStcProtocol (49),
		alarmResourceAlCapProtocol (50),
		alarmResourceGtpUProtocol (51),
		alarmResourceMtp3link (71),
		alarmResourceMtp3linkSet (72),
		alarmResourceMtp3RouteSet (73),
		alarmResourceMtp3BLink (74),
		alarmResourceMtp3BLinkSet (75),
		alarmResourceMtp3BRouteSet (76),
		alarmResourceAssociation (77),
		alarmResourceM3uaPsp (78),
		alarmResourceM3uaPs (79),
		alarmResourceTrunk (80),
		alarmResourceTrunkCircuit (81),
		alarmResourceH110TimeSlot (82),
		alarmResourceStmlink (83),
		alarmResourceIpLink (84),
		alarmResourceSccopLink (85),
		alarmResourceAal2Pvc (86),
		alarmResourceAal5Pvc (87),
		alarmResourceCdr (111),
		alarmResourceCell (112),
		alarmResourceHwRcsource (113),
		alarmResourceSaFailure (114),
		alarmResourcePlatformMgmtChannel (115),
		alarmResourceIpOrMacAddr (116),
		alarmResourceCpHaControl (117),
		alarmResourceUsrDialog (118),
		alarmResourceDbConn (119),
		alarmResourceAuthentication (120),
		alarmResourceGmlcRoute (121),
		alarmResourceTca (151)
	}


AlarmSeverity ::= TEXTUAL-CONVENTION
	STATUS     current
	DESCRIPTION
		"The textual convention for alarm severity level:

		alarmLevelClear       - The Cleared severity level indicates that
		                        the fault has been cleared.
		alarmLevelCritical    - The Critical severity level indicates the most
		                        severe service affecting condition has occurred,
		                        and the whole system may not be functioning properly.
		                        Urgent and immediate corrective action is required.
		alarmLevelMajor       - The Major severity level indicates service
		                        affecting condition has occurred. Immediate
		                        corrective action is required.
		alarmLevelMinor       - The Minor severity level indicates service
		                        not affecting condition has occurred. Corrective
		                        action should be taken to avoid more serious
		                        service affecting fault.
		alarmLevelWarning     - The Warning severity level indicates some issues
		                        occur and may be potential service affecting.
		                        Precautions have to be taken in order to avoid
		                        more serious service affecting fault."
	SYNTAX  INTEGER {
		alarmLevelClear (0),
		alarmLevelWarning (1),
		alarmLevelMinor (2),
		alarmLevelMajor (3),
		alarmLevelCritical (4),
		alarmLevelIndeterminate (5)
	}


AlarmType ::= TEXTUAL-CONVENTION
	STATUS     current
	DESCRIPTION
		"The textual convention for alarm type:
		alarmTypeCommunication    - alarm associates with Communication issues
		alarmTypeEquipment        - alarm associates with equipment or hardware issues
		alarmTypeEnvironmental    - alarm associates with the environment where the
		                            system is operating
		alarmTypeProcessingError  - alarm associates with processing issues
		alarmTypeQualityOfService - alarm associates with the quality of service issues"
	SYNTAX  INTEGER {
		alarmTypeCommunication (2),
		alarmTypeEquipment (3),
		alarmTypeEnvironmental (4),
		alarmTypeProcessingError (10),
		alarmTypeQualityOfService (11)
	}


ProbableCause ::= TEXTUAL-CONVENTION
	STATUS     current
	DESCRIPTION
		"The definiation of alarm probable cause, refer to: M.3100, X.731/X.733, GSM12.11 etc."
	SYNTAX  INTEGER {
		probableCauseIndeterminate (1),
		probableCauseAlarmIndicationSignal (2),
		probableCauseCallSetupFailure (3),
		probableCauseDegradedSignal (4),
		probableCauseFarEndReceiverFailure (5),
		probableCauseFramingError (6),
		probableCauseLossOfFrame (7),
		probableCauseLossOfPointer (8),
		probableCauseLossOfSignal (9),
		probableCausePayloadTypeMismatch (10),
		probableCauseTransmissionError (11),
		probableCauseRemoteAlarmInterface (12),
		probableCauseExcessiveBitErrorRate (13),
		probableCausePathTraceMismatch (14),
		probableCauseUnavailable (15),
		probableCauseSignalLabelMismatch (16),
		probableCauseLossOfMultiFrame (17),
		probableCauseBackPlaneFailure (18),
		probableCauseDataSetProblem (19),
		probableCauseEquipmentIdentifierDuplication (20),
		probableCauseExternalInterfaceDeviceProblem (21),
		probableCauseLineCardProblem (22),
		probableCauseMultiplexerProblem (23),
		probableCauseNeIdentifierDuplication (24),
		probableCausePowerProblem (25),
		probableCauseProcessorProblem (26),
		probableCauseProtectionPathFailure (27),
		probableCauseReceiverFailure (28),
		probableCauseReplaceableUnitMissing (29),
		probableCauseReplaceableUnitTypeMismatch (30),
		probableCauseSynchronisationSourceMismatch (31),
		probableCauseTerminalProblem (32),
		probableCauseTimingProblem (33),
		probableCauseTransmitterFailure (34),
		probableCauseTrunkCardProblem (35),
		probableCauseReplaceableUnitProblem (36),
		probableCauseAirCompressorFailure (37),
		probableCauseAirConditioningFailure (38),
		probableCauseAirDryerFailure (39),
		probableCauseBatteryDischarging (40),
		probableCauseBatteryFailure (41),
		probableCauseCommercialPowerFailure (42),
		probableCauseCoolingFanFailure (43),
		probableCauseEngineFailure (44),
		probableCauseFireDetectorFailure (45),
		probableCauseFuseFailure (46),
		probableCauseGeneratorFailure (47),
		probableCauseLowBatteryThreshold (48),
		probableCausePumpFailure (49),
		probableCauseRectifierFailure (50),
		probableCauseRectifierHighVoltage (51),
		probableCauseRectifierLowFVoltage (52),
		probableCauseVentilationSystemFailure (53),
		probableCauseEnclosureDoorOpen (54),
		probableCauseExplosiveGas (55),
		probableCauseFireDetected (56),
		probableCauseFloodDetected (57),
		probableCauseHighHumidity (58),
		probableCauseHighTemperature (59),
		probableCauseHighWind (60),
		probableCauseIceBuildUp (61),
		probableCauseIntrusionDetection (62),
		probableCauseLowFuel (63),
		probableCauseLowHumidity (64),
		probableCauseLowCablePressure (65),
		probableCauseLowTemperature (66),
		probableCauseLowWater (67),
		probableCauseSmokeDetected (68),
		probableCauseToxicGas (69),
		probableCauseStorageCapacityProblem (70),
		probableCauseMemoryMismatch (71),
		probableCauseCorruptData (72),
		probableCauseOutOfCPUCycles (73),
		probableCauseSoftwareEnvironmentProblem (74),
		probableCauseSoftwareDownloadFailure (75),
		probableCauseAdapterError (200),
		probableCauseApplicationSubsystemFailure (201),
		probableCauseBandwidthReduction (202),
		probableCauseCommunicationProtocolError (203),
		probableCauseCommunicationSubsystemFailure (204),
		probableCauseConfigurationOrCustomizingError (205),
		probableCauseCongestion (206),
		probableCauseCpuCyclesLimitExceeded (207),
		probableCauseDataSetOrModemError (208),
		probableCauseDteDceInterfaceError (209),
		probableCauseEquipmentMalfunction (210),
		probableCauseExcessiveVibration (211),
		probableCauseFileError (212),
		probableCauseHeatingOrVentilationOrCoolingSystemProblem (213),
		probableCauseHumidityUnacceptable (214),
		probableCauseInputOutputDeviceError (215),
		probableCauseInputDeviceError (216),
		probableCauseLanError (217),
		probableCauseLeakDetection (218),
		probableCauseLocalNodeTransmissionError (219),
		probableCauseMaterialSupplyExhausted (220),
		probableCauseOutOfMemory (221),
		probableCauseOutputDeviceError (222),
		probableCausePerformanceDegraded (223),
		probableCausePressureUnacceptable (224),
		probableCauseQueueSizeExceeded (225),
		probableCauseReceiveFailure (226),
		probableCauseRemoteNodeTransmissionError (227),
		probableCauseResourceAtOrNearingCapacity (228),
		probableCauseResponseTimeExcessive (229),
		probableCauseRetransmissionRateExcessive (230),
		probableCauseSoftwareError (231),
		probableCauseSoftwareProgramAbnormallyTerminated (232),
		probableCauseSoftwareProgramError (233),
		probableCauseTemperatureUnacceptable (234),
		probableCauseThresholdCrossed (235),
		probableCauseToxicLeakDetected (236),
		probableCauseTransmitFailure (237),
		probableCauseUnderlyingResourceUnavailable (238),
		probableCauseVersionMismatch (239),
		probableCauseAbisToBTSInterfaceFailure (500),
		probableCauseAbisToTRXInterfaceFailure (501),
		probableCauseAntennaProblem (502),
		probableCauseBatteryBreakdown (503),
		probableCauseBatteryChargingFault (504),
		probableCauseClockSynchronisationProblem (505),
		probableCauseCombinerProblem (506),
		probableCauseDiskProblem (507),
		probableCauseEquipmentFailure (508),
		probableCauseExcessiveReceiverTemperature (509),
		probableCauseExcessiveTransmitterOutputPower (510),
		probableCauseExcessiveTransmitterTemperature (511),
		probableCauseFrequencyHoppingDegraded (512),
		probableCauseFrequencyHoppingFailure (513),
		probableCauseFrequencyRedefinitionFailed (514),
		probableCauseLineInterfaceFailure (515),
		probableCauseLinkFailure (516),
		probableCauseLossOfSynchronisation (517),
		probableCauseLostRedundancy (518),
		probableCauseMainsBreakdownWithBatteryBackup (519),
		probableCauseMainsBreakdownWithoutBatteryBackup (520),
		probableCausePowerSupplyFailure (521),
		probableCauseReceiverAntennaFault (522),
		probableCauseReceiverMulticouplerFailure (523),
		probableCauseReducedTransmitterOutputPower (524),
		probableCauseSignalQualityEvaluationFault (525),
		probableCauseTimeslotHardwareFailure (526),
		probableCauseTransceiverProblem (527),
		probableCauseTranscoderProblem (528),
		probableCauseTranscoderOrRateAdapterProblem (529),
		probableCauseTransmitterAntennaFailure (530),
		probableCauseTransmitterAntennaNotAdjusted (531),
		probableCauseTransmitterLowVoltageOrCurrent (532),
		probableCauseTransmitterOffFrequency (533),
		probableCauseDatabaseInconsistency (534),
		probableCauseFileSystemCallUnsuccessful (535),
		probableCauseInputParameterOutOfRange (536),
		probableCauseInvalidParameter (537),
		probableCauseInvalidPointer (538),
		probableCauseMessageNotExpected (539),
		probableCauseMessageNotInitialised (540),
		probableCauseMessageOutOfSequence (541),
		probableCauseSystemCallUnsuccessful (542),
		probableCauseTimeoutExpired (543),
		probableCauseVariableOutOfRange (544),
		probableCauseWatchDogTimerExpired (545),
		probableCauseCoolingSystemFailure (546),
		probableCauseExternalPowerSupplyFailure (547),
		probableCauseExternalTransmissionDeviceFailure (548),
		probableCauseReducedAlarmReporting (549),
		probableCauseReducedEventReporting (550),
		probableCauseReducedLoggingCapability (551),
		probableCauseSystemResourcesOverload (552),
		probableCauseBroadcastChannelFailure (553),
		probableCauseConnectionEstablishmentError (554),
		probableCauseInvalidMessageReceived (555),
		probableCauseInvalidMSUReceived (556),
		probableCauseLapdLinkProtocolFailure (557),
		probableCauseLocalAlarmIndication (558),
		probableCauseRemoteAlarmIndication (559),
		probableCauseRoutingFailure (560),
		probableCauseSs7ProtocolFailure (561),
		probableCauseTca (1000)
	}


-- MP: {SUBAGENT_API_MIB_PARTID_FM}

utFaultManagement  OBJECT-IDENTITY
	STATUS     current
	DESCRIPTION
		""
	::= { utCommonOam 2 }

utAlarmModelTable  OBJECT-TYPE
	SYNTAX SEQUENCE OF UtAlarmModelEntry
	MAX-ACCESS not-accessible
	STATUS     current
	DESCRIPTION
		""
	::= { utFaultManagement 1 }

utAlarmModelEntry  OBJECT-TYPE
	SYNTAX 	UtAlarmModelEntry
	MAX-ACCESS not-accessible
	STATUS     current
	DESCRIPTION
		""
	INDEX { utAlarmModelOID }
	::= { utAlarmModelTable 1 }

UtAlarmModelEntry ::= SEQUENCE {
	utAlarmModelOID
		OBJECT IDENTIFIER,
	utAlarmModelSeverity
		AlarmSeverity,
	utAlarmModelType
		AlarmType,
	utAlarmModelProbableCause
		ProbableCause,
	utAlarmModelClearType
		INTEGER,
	utAlarmModelResourceType
		AlarmResourceType,
	utAlarmModelFilteredFlag
		BOOL
}

utAlarmModelOID  OBJECT-TYPE
	SYNTAX     OBJECT IDENTIFIER
	MAX-ACCESS not-accessible
	STATUS     current
	DESCRIPTION
		"Object ID of a specific alarm"
	::= { utAlarmModelEntry 1 }

utAlarmModelSeverity  OBJECT-TYPE
	SYNTAX     AlarmSeverity
	MAX-ACCESS read-write
	STATUS     current
	DESCRIPTION
		"It presents a specific alarm's severity. It can be redefined."
	::= { utAlarmModelEntry 2 }

utAlarmModelType  OBJECT-TYPE
	SYNTAX     AlarmType
	MAX-ACCESS read-write
	STATUS     current
	DESCRIPTION
		"It presents a specific alarm's type. It can be redefined."
	::= { utAlarmModelEntry 3 }

utAlarmModelProbableCause  OBJECT-TYPE
	SYNTAX     ProbableCause
	MAX-ACCESS read-only
	STATUS     current
	DESCRIPTION
		"It presents a specific alarm's probable cause"
	::= { utAlarmModelEntry 4 }

utAlarmModelClearType  OBJECT-TYPE
	SYNTAX     INTEGER {
		adac (0),
		admc (1)
	}
	MAX-ACCESS read-only
	STATUS     current
	DESCRIPTION
		"It presents a specific alarm's clear type."
	::= { utAlarmModelEntry 5 }

utAlarmModelResourceType  OBJECT-TYPE
	SYNTAX     AlarmResourceType
	MAX-ACCESS read-only
	STATUS     current
	DESCRIPTION
		"It presents a specific alarm's resource type."
	::= { utAlarmModelEntry 6 }

utAlarmModelFilteredFlag  OBJECT-TYPE
	SYNTAX     BOOL
	MAX-ACCESS read-write
	STATUS     current
	DESCRIPTION
		"The variable is used to indicate whether a specific alarm is filtered by alarm OID. TRUE: filteredFALSE: non-filtered"
	::= { utAlarmModelEntry 7 }

-- ***************************************
-- *
-- * Alarm Trap
-- *
-- **************************************
-- *
-- * The Alarm Trap Notification should have the following mandatory
-- * parameters, in the specified order:
-- *
-- *    - the alarm source IP address at the module instance level
-- *    - alarm occurrence time
-- *    - alarm severity level
-- *    - alarm type
-- *    - probable cause
-- *    - alarm clearance type which indicates how the alarm can be cleared
-- *    - any additional information related to the specific alarm
-- *
-- * For example, an alarm trap for a product XXX may look like:
-- *
-- *   utXXXAlarmTrapEventReport  NOTIFICATION-TYPE
-- *	 OBJECTS { utAlarmModuleInstanceIpAddr,
-- *		   utAlarmOccurrenceTime,
-- *		   utAlarmSeverity,
-- *		   utAlarmType,
-- *		   utAlarmProbableCause,
-- *		   utAlarmClearType,
-- *		   ... (any additional application specific information varbinds) }
-- *	 STATUS current
-- *	 DESCRIPTION
-- *		"The Alarm Trap Events for XXX"
-- *	 ::= { utXXXAlarmTrapEvent 1 }
-- *
-- *
-- ***************************************

utAlarmEventTrap  OBJECT-IDENTITY
	STATUS     current
	DESCRIPTION
		"The sub-tree for fault trap definition."
	::= { utFaultManagement 2 }

utAlarmTrapMandatoryAttr  OBJECT-IDENTITY
	STATUS     current
	DESCRIPTION
		"The sub-tree for common alarm trap attribution."
	::= { utAlarmEventTrap 1 }

utAlarmSeqNo  OBJECT-TYPE
	SYNTAX     Counter32
	MAX-ACCESS accessible-for-notify
	STATUS     current
	DESCRIPTION
		"Reserved for OAM. Application doesn't care this node at all."
	::= { utAlarmTrapMandatoryAttr 1 }

utAlarmOccurrenceTime  OBJECT-TYPE
	SYNTAX     DateAndTime
	MAX-ACCESS accessible-for-notify
	STATUS     current
	DESCRIPTION
		"The occurrence time of alarm, which gives the time when the alarm is generated."
	::= { utAlarmTrapMandatoryAttr 2 }

utAlarmSeverity  OBJECT-TYPE
	SYNTAX     AlarmSeverity
	MAX-ACCESS accessible-for-notify
	STATUS     current
	DESCRIPTION
		"The severity of the alarm, that aligned with the ISO Ref.X.733: Cleared, Information, Critical, Major, Minor, and Warning."
	::= { utAlarmTrapMandatoryAttr 3 }

utAlarmProbableCause  OBJECT-TYPE
	SYNTAX     ProbableCause
	MAX-ACCESS accessible-for-notify
	STATUS     current
	DESCRIPTION
		"The probable cause of the alarm as defined in ISO Ref.X.733 and others."
	::= { utAlarmTrapMandatoryAttr 4 }

utAlarmType  OBJECT-TYPE
	SYNTAX     AlarmType
	MAX-ACCESS accessible-for-notify
	STATUS     current
	DESCRIPTION
		"The alarm type (categories, or classes) as defined in ISO Ref.X.733: Communication alarms, Qos alarms, Processing error alarms, Equipment alarms, and Environmental alarms."
	::= { utAlarmTrapMandatoryAttr 5 }

utAlarmClearType  OBJECT-TYPE
	SYNTAX     INTEGER {
		alarmClearAuto (0),
		alarmClearManual (1)
	}
	MAX-ACCESS accessible-for-notify
	STATUS     current
	DESCRIPTION
		"The item which indicates how the alarm can be cleared:
		alarmClearAuto    - the alarm is cleared by application itself
		alarmClearManual  - the alarm to be cleared by manual operation"
	::= { utAlarmTrapMandatoryAttr 6 }

utAlarmResourceType  OBJECT-TYPE
	SYNTAX     Integer32
	MAX-ACCESS accessible-for-notify
	STATUS     current
	DESCRIPTION
		""
	::= { utAlarmTrapMandatoryAttr 7 }

utEventTrapMandatoryAttr  OBJECT-IDENTITY
	STATUS     current
	DESCRIPTION
		""
	::= { utAlarmEventTrap 2 }

utEventSeqNo  OBJECT-TYPE
	SYNTAX     Counter32
	MAX-ACCESS accessible-for-notify
	STATUS     current
	DESCRIPTION
		"Reserved for OAM to implement reliable trap transmission."
	::= { utEventTrapMandatoryAttr 1 }

utEventOccurrenceTime  OBJECT-TYPE
	SYNTAX     DateAndTime
	MAX-ACCESS accessible-for-notify
	STATUS     current
	DESCRIPTION
		"The occurrence time of event, which gives the time when the event is generated."
	::= { utEventTrapMandatoryAttr 2 }

utAlarmFiltering  OBJECT-IDENTITY
	STATUS     current
	DESCRIPTION
		"Sub-tree to cover the UTS UMTS Embedded System Alarm Filtering."
	::= { utFaultManagement 3 }

utAlarmFilteringSeverity  OBJECT-TYPE
	SYNTAX     Integer32
	MAX-ACCESS read-write
	STATUS     current
	DESCRIPTION
		"The leaf is used for filtering specified severity alarms.

		bit0 - cleared alarm
		bit1 - warning alarm
		bit2 - minor alarm
		bit3 - major alarm
		bit4 - critical alarm


		1 - represent the alarm will be sent to NMS;
		0 - this kind of alarms will be filtered by agent;

		other useless bits: fill in digitial 1 always.

		for examples, if operator wants to filter critical alarms.
		this leaf needs to be set to value
		0x FF FF FF E1

		low 8 bits are: 1110,0001 = E1
		cauz if operator wants to filter critical alarms, meaning that others
		whose priority is lower than critical need to be filtered as well.

		attention: cleared alarm can't be filtered.
		DEFAULT:{-1}"
	::= { utAlarmFiltering 1 }

utAlarmFilteringType  OBJECT-TYPE
	SYNTAX     Integer32
	MAX-ACCESS read-write
	STATUS     current
	DESCRIPTION
		"The leaf is used for filtering specified type alarms.

		bit2 - communication
		bit3 - equipment
		bit4 - environment
		bit10 - processing error
		bit11 - quality of service

		1 - represent the alarm will be sent to NMS;
		0 - this kind of alarms will be filtered by agent;

		other useless bits: fill in digitial 1 always.

		for examples, if operator wants to filter communication alarms only,
		this leaf needs to be set to value
		0x FF FF FF FB
		DEFAULT:{-1}"
	::= { utAlarmFiltering 2 }

utActiveAlarmTable  OBJECT-TYPE
	SYNTAX SEQUENCE OF UtActiveAlarmEntry
	MAX-ACCESS not-accessible
	STATUS     current
	DESCRIPTION
		"The content of the active alarm table is not the individual alarms.
		Each entry in the table is corresponding to a specific alarm condition
		existing at a particular MO instance. That is, alarm OID and originating
		MO instance ID (not the module that detects the alarm condition,
		but rather the module that is experiencing the reported problem)
		 together will uniquely identify an entry in the active alarm table.
		Multiple alarms for the same fault condition happened at the same
		MO instance might be generated by the application that detects
		the fault condition, only one entry will be registered in the active alarm table."
	::= { utFaultManagement 4 }

utActiveAlarmEntry  OBJECT-TYPE
	SYNTAX 	UtActiveAlarmEntry
	MAX-ACCESS not-accessible
	STATUS     current
	DESCRIPTION
		""
	INDEX { utActiveAlarmEntryID }
	::= { utActiveAlarmTable 1 }

UtActiveAlarmEntry ::= SEQUENCE {
	utActiveAlarmEntryID
		Unsigned32,
	utActiveAlarmObjectID
		OBJECT IDENTIFIER,
	utActiveAlarmSourceMO
		RowPointer,
	utActiveAlarmSeqNo
		Unsigned32,
	utActiveAlarmFirstDectetTime
		DateAndTime,
	utActiveAlarmLastReportTime
		DateAndTime,
	utActiveAlarmRepeatedNumbers
		Unsigned32,
	utActiveAlarmSeverity
		AlarmSeverity,
	utActiveAlarmFirstTrapPDU
		OCTET STRING,
	utActiveAlarmClearingFlag
		RowStatus
}

utActiveAlarmEntryID  OBJECT-TYPE
	SYNTAX     Unsigned32
	MAX-ACCESS not-accessible
	STATUS     current
	DESCRIPTION
		"to differentiate the entries in the table"
	::= { utActiveAlarmEntry 1 }

-- GET_FROM_SC

utActiveAlarmObjectID  OBJECT-TYPE
	SYNTAX     OBJECT IDENTIFIER
	MAX-ACCESS read-only
	STATUS     current
	DESCRIPTION
		"as defined in the MIB with the NOTIFICATION-TYPE macro"
	::= { utActiveAlarmEntry 2 }

-- GET_FROM_SC

utActiveAlarmSourceMO  OBJECT-TYPE
	SYNTAX     RowPointer
	MAX-ACCESS read-only
	STATUS     current
	DESCRIPTION
		"from where the alarm is originated"
	::= { utActiveAlarmEntry 3 }

-- GET_FROM_SC

utActiveAlarmSeqNo  OBJECT-TYPE
	SYNTAX     Unsigned32
	MAX-ACCESS read-only
	STATUS     current
	DESCRIPTION
		""
	::= { utActiveAlarmEntry 4 }

-- GET_FROM_SC

utActiveAlarmFirstDectetTime  OBJECT-TYPE
	SYNTAX     DateAndTime
	MAX-ACCESS read-only
	STATUS     current
	DESCRIPTION
		"when the alarm is initially detected and reported"
	::= { utActiveAlarmEntry 5 }

-- GET_FROM_SC

utActiveAlarmLastReportTime  OBJECT-TYPE
	SYNTAX     DateAndTime
	MAX-ACCESS read-only
	STATUS     current
	DESCRIPTION
		"when the alarm is last reported"
	::= { utActiveAlarmEntry 6 }

-- GET_FROM_SC

utActiveAlarmRepeatedNumbers  OBJECT-TYPE
	SYNTAX     Unsigned32
	MAX-ACCESS read-only
	STATUS     current
	DESCRIPTION
		"number of reports for the same alarm from the same alarm source"
	::= { utActiveAlarmEntry 7 }

-- GET_FROM_SC

utActiveAlarmSeverity  OBJECT-TYPE
	SYNTAX     AlarmSeverity
	MAX-ACCESS read-only
	STATUS     current
	DESCRIPTION
		"reported severity from alarm source"
	::= { utActiveAlarmEntry 8 }

-- GET_FROM_SC

utActiveAlarmFirstTrapPDU  OBJECT-TYPE
	SYNTAX     OCTET STRING
	MAX-ACCESS read-only
	STATUS     current
	DESCRIPTION
		"a pointer to the first trap pdu(for synchronizing)"
	::= { utActiveAlarmEntry 9 }

utActiveAlarmClearingFlag  OBJECT-TYPE
	SYNTAX     RowStatus
	MAX-ACCESS read-only
	STATUS     current
	DESCRIPTION
		"rowstatus of the table."
	::= { utActiveAlarmEntry 10 }

utHistoryAlarmTable  OBJECT-TYPE
	SYNTAX SEQUENCE OF UtHistoryAlarmEntry
	MAX-ACCESS not-accessible
	STATUS     current
	DESCRIPTION
		"The contents of historical alarm table include all the alarms generated before. If alarm numbers
		in the table are up to table dimension, new subsequent alarms will replace the oldest alarms.

		only support get operation."
	::= { utFaultManagement 5 }

utHistoryAlarmEntry  OBJECT-TYPE
	SYNTAX 	UtHistoryAlarmEntry
	MAX-ACCESS not-accessible
	STATUS     current
	DESCRIPTION
		""
	INDEX { utHistoryAlarmSeqNo }
	::= { utHistoryAlarmTable 1 }

UtHistoryAlarmEntry ::= SEQUENCE {
	utHistoryAlarmSeqNo
		Unsigned32,
	utHistoryAlarmTrapPDU
		OCTET STRING
}

utHistoryAlarmSeqNo  OBJECT-TYPE
	SYNTAX     Unsigned32
	MAX-ACCESS not-accessible
	STATUS     current
	DESCRIPTION
		""
	::= { utHistoryAlarmEntry 1 }

-- GET_FROM_SC

utHistoryAlarmTrapPDU  OBJECT-TYPE
	SYNTAX     OCTET STRING
	MAX-ACCESS read-only
	STATUS     current
	DESCRIPTION
		""
	::= { utHistoryAlarmEntry 2 }

utHistoryEventTable  OBJECT-TYPE
	SYNTAX SEQUENCE OF UtHistoryEventEntry
	MAX-ACCESS not-accessible
	STATUS     current
	DESCRIPTION
		"The contents of historical event table include all the events generated before. If event numbers
		in the table are up to table dimension, new subsequent events will replace the oldest events.

		only support get operation."
	::= { utFaultManagement 6 }

utHistoryEventEntry  OBJECT-TYPE
	SYNTAX 	UtHistoryEventEntry
	MAX-ACCESS not-accessible
	STATUS     current
	DESCRIPTION
		""
	INDEX { utHistoryEventSeqNo }
	::= { utHistoryEventTable 1 }

UtHistoryEventEntry ::= SEQUENCE {
	utHistoryEventSeqNo
		Unsigned32,
	utHistoryEventTrapPDU
		OCTET STRING
}

utHistoryEventSeqNo  OBJECT-TYPE
	SYNTAX     Unsigned32
	MAX-ACCESS not-accessible
	STATUS     current
	DESCRIPTION
		""
	::= { utHistoryEventEntry 1 }

-- GET_FROM_SC

utHistoryEventTrapPDU  OBJECT-TYPE
	SYNTAX     OCTET STRING
	MAX-ACCESS read-only
	STATUS     current
	DESCRIPTION
		""
	::= { utHistoryEventEntry 2 }

utAlarmClearActionTable  OBJECT-TYPE
	SYNTAX SEQUENCE OF UtAlarmClearActionEntry
	MAX-ACCESS not-accessible
	STATUS     current
	DESCRIPTION
		"The table is used for clearing a specfic alarm in active alarm table."
	::= { utFaultManagement 7 }

utAlarmClearActionEntry  OBJECT-TYPE
	SYNTAX 	UtAlarmClearActionEntry
	MAX-ACCESS not-accessible
	STATUS     current
	DESCRIPTION
		"ACTION_TABLE"
	INDEX { utAlarmClearActionCmd }
	::= { utAlarmClearActionTable 1 }

UtAlarmClearActionEntry ::= SEQUENCE {
	utAlarmClearActionCmd
		Integer32,
	utAlarmClearActionCorrelationNo
		OCTET STRING,
	utAlarmClearActionSeqNo
		Unsigned32,
	utAlarmClearActionRowStatus
		RowStatus
}

utAlarmClearActionCmd  OBJECT-TYPE
	SYNTAX     Integer32
	MAX-ACCESS not-accessible
	STATUS     current
	DESCRIPTION
		""
	::= { utAlarmClearActionEntry 1 }

utAlarmClearActionCorrelationNo  OBJECT-TYPE
	SYNTAX     OCTET STRING
	MAX-ACCESS read-create
	STATUS     current
	DESCRIPTION
		""
	::= { utAlarmClearActionEntry 2 }

utAlarmClearActionSeqNo  OBJECT-TYPE
	SYNTAX     Unsigned32
	MAX-ACCESS read-create
	STATUS     current
	DESCRIPTION
		""
	::= { utAlarmClearActionEntry 3 }

utAlarmClearActionRowStatus  OBJECT-TYPE
	SYNTAX     RowStatus
	MAX-ACCESS read-create
	STATUS     current
	DESCRIPTION
		""
	::= { utAlarmClearActionEntry 4 }

utAlarmConfigration  OBJECT-IDENTITY
	STATUS     current
	DESCRIPTION
		"Sub-tree for common configration parameters involved in alarm & event."
	::= { utFaultManagement 8 }

utHistroyAlarmTableSize  OBJECT-TYPE
	SYNTAX     Integer32 (1..1024)
	MAX-ACCESS read-write
	STATUS     current
	DESCRIPTION
		"operator shall be able to set table size in runtime.
		DEFAULT:{2048}"
	::= { utAlarmConfigration 1 }

utHistoryEventTableSize  OBJECT-TYPE
	SYNTAX     Integer32 (1..256)
	MAX-ACCESS read-write
	STATUS     current
	DESCRIPTION
		"operator shall be able to set table size in runtime.
		DEFAULT:{2048}"
	::= { utAlarmConfigration 2 }

-- GET_FROM_SC

utCurrentAlarmSeqNo  OBJECT-TYPE
	SYNTAX     Unsigned32
	MAX-ACCESS read-only
	STATUS     current
	DESCRIPTION
		""
	::= { utAlarmConfigration 3 }

-- GET_FROM_SC

utCurrentEventSeqNo  OBJECT-TYPE
	SYNTAX     Unsigned32
	MAX-ACCESS read-only
	STATUS     current
	DESCRIPTION
		""
	::= { utAlarmConfigration 4 }

utFmTrapNeId  OBJECT-TYPE
	SYNTAX     OCTET STRING (SIZE(0..255))
	MAX-ACCESS read-only
	STATUS     current
	DESCRIPTION
		"NE identifier."
	::= { utAlarmConfigration 5 }

utFmTrapRcverTable  OBJECT-TYPE
	SYNTAX SEQUENCE OF UtFmTrapRcverEntry
	MAX-ACCESS not-accessible
	STATUS     current
	DESCRIPTION
		""
	::= { utFaultManagement 9 }

utFmTrapRcverEntry  OBJECT-TYPE
	SYNTAX 	UtFmTrapRcverEntry
	MAX-ACCESS not-accessible
	STATUS     current
	DESCRIPTION
		""
	INDEX { utFmTrapRcverIP,
		utFmTrapRcverPort }
	::= { utFmTrapRcverTable 1 }

UtFmTrapRcverEntry ::= SEQUENCE {
	utFmTrapRcverIP
		IpAddress,
	utFmTrapRcverPort
		WORD,
	utFmTrapRcverRowStatus
		RowStatus
}

utFmTrapRcverIP  OBJECT-TYPE
	SYNTAX     IpAddress
	MAX-ACCESS not-accessible
	STATUS     current
	DESCRIPTION
		""
	::= { utFmTrapRcverEntry 1 }

utFmTrapRcverPort  OBJECT-TYPE
	SYNTAX     WORD
	MAX-ACCESS not-accessible
	STATUS     current
	DESCRIPTION
		""
	::= { utFmTrapRcverEntry 2 }

utFmTrapRcverRowStatus  OBJECT-TYPE
	SYNTAX     RowStatus
	MAX-ACCESS read-create
	STATUS     current
	DESCRIPTION
		""
	::= { utFmTrapRcverEntry 3 }

utFmAlarmDelayTable  OBJECT-TYPE
	SYNTAX SEQUENCE OF UtFmAlarmDelayEntry
	MAX-ACCESS not-accessible
	STATUS     current
	DESCRIPTION
		"By adding an alarm delay rule downto an NE,
		a certain alarm can be delayed in agent, before it is sent to OMC.
		An alarm delay rule may include any combination of below conditions
		"
	::= { utFaultManagement 10 }

utFmAlarmDelayEntry  OBJECT-TYPE
	SYNTAX 	UtFmAlarmDelayEntry
	MAX-ACCESS not-accessible
	STATUS     current
	DESCRIPTION
		""
	INDEX { utFmAlarmDelayRuleID }
	::= { utFmAlarmDelayTable 1 }

UtFmAlarmDelayEntry ::= SEQUENCE {
	utFmAlarmDelayRuleID
		Unsigned32,
	utFmAlarmDelaySeverity
		Integer32,
	utFmAlarmDelayType
		Integer32,
	utFmAlarmDelayResourceType
		AlarmResourceType,
	utFmAlarmDelayAlarmID
		OBJECT IDENTIFIER,
	utFmAlarmDelayBeginTime
		DisplayString,
	utFmAlarmDelayEndTime
		DisplayString,
	utFmAlarmDelaySecond
		Unsigned32,
	utFmAlarmDelayRowStatus
		RowStatus
}

utFmAlarmDelayRuleID  OBJECT-TYPE
	SYNTAX     Unsigned32 (1..16)
	MAX-ACCESS read-only
	STATUS     current
	DESCRIPTION
		"Once a delay rule is set to NE,
		the delay rule takes effective immediately.
		If the total number of alarm delay rules exceeds 16 on an NE,
		the NE should deny any new delay rules."
	::= { utFmAlarmDelayEntry 1 }

utFmAlarmDelaySeverity  OBJECT-TYPE
	SYNTAX     Integer32
	MAX-ACCESS read-create
	STATUS     current
	DESCRIPTION
		"ENUM
		Bit mask
		alarmLevelClear :Bit(0),
		alarmLevelWarning :Bit(1)
		alarmLevelMinor :Bit(2)
		alarmLevelMajor :Bit(3)
		alarmLevelCritical :Bit(4)
		default value: 0x11110(30)
		DEFAULT:{30}"
	::= { utFmAlarmDelayEntry 2 }

utFmAlarmDelayType  OBJECT-TYPE
	SYNTAX     Integer32
	MAX-ACCESS read-create
	STATUS     current
	DESCRIPTION
		"ENUM
		Bit mask
		AlarmTypeCommunication:Bit(2)
		AlarmTypeEquipment: Bit(3)
		AlarmTypeEnvironmental: Bit(4)
		AlarmTypeProcessingError: Bit(10)
		AlarmTypeQualityOfService: Bit(11)
		default value:0x110000011100(3100)
		DEFAULT:{3100}"
	::= { utFmAlarmDelayEntry 3 }

utFmAlarmDelayResourceType  OBJECT-TYPE
	SYNTAX     AlarmResourceType
	MAX-ACCESS read-create
	STATUS     current
	DESCRIPTION
		"Available values are all potential Entity Types of this NE,
		and All.
		The default value is All (0).
		DEFAULT:{0}"
	::= { utFmAlarmDelayEntry 4 }

utFmAlarmDelayAlarmID  OBJECT-TYPE
	SYNTAX     OBJECT IDENTIFIER
	MAX-ACCESS read-create
	STATUS     current
	DESCRIPTION
		"Available values are all potential Alarm ID of this NE,
		and All.
		The default value is All
		DEFAULT:{0.0}"
	::= { utFmAlarmDelayEntry 5 }

utFmAlarmDelayBeginTime  OBJECT-TYPE
	SYNTAX     DisplayString
	MAX-ACCESS read-create
	STATUS     current
	DESCRIPTION
		"Effective Timespan (FromTime and ToTime).
		This condition specifies the effective timespan within a day.
		FromTime should prior to ToTime.
		The timespan cannot stride 00:00AM.
		The format of FromTime and ToTime is HH:MM
		for example:
		01:25 means that the rule will be valid form 1:25"
	::= { utFmAlarmDelayEntry 6 }

utFmAlarmDelayEndTime  OBJECT-TYPE
	SYNTAX     DisplayString
	MAX-ACCESS read-create
	STATUS     current
	DESCRIPTION
		"Effective Timespan (FromTime and ToTime).
		This condition specifies the effective timespan within a day.
		FromTime should prior to ToTime.
		The timespan cannot stride 00:00AM.
		The format of FromTime and ToTime is HH:MM
		for example:
		13:25 means that the rule will be invalid at 13:25"
	::= { utFmAlarmDelayEntry 7 }

utFmAlarmDelaySecond  OBJECT-TYPE
	SYNTAX     Unsigned32 (0..86400)
	MAX-ACCESS read-create
	STATUS     current
	DESCRIPTION
		"Delay SecondsThe valid value is (0,60*60*24).
		In other words, the maximum delay time is 24 hours."
	::= { utFmAlarmDelayEntry 8 }

utFmAlarmDelayRowStatus  OBJECT-TYPE
	SYNTAX     RowStatus
	MAX-ACCESS read-create
	STATUS     current
	DESCRIPTION
		""
	::= { utFmAlarmDelayEntry 9 }

utEventSeqNo  OBJECT-TYPE
	SYNTAX     Counter32
	MAX-ACCESS accessible-for-notify
	STATUS     current
	DESCRIPTION
		"Reserved for OAM to implement reliable trap transmission."
	::= { utEventTrapMandatoryAttr 10 }

END


-- This MIB was created using NuDesign Team's Visual MIBuilder (Ver 4.3).
