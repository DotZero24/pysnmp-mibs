-- Copyright 1999 MITEL Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, condition, or performance of the Specification.


MITEL-SX2000-MIB

    --FORCE-INCLUDE <mib.h>
    --FORCE-INCLUDE <snmpdefs.h>
    --FORCE-INCLUDE <snmpstat.h>
    --FORCE-INCLUDE "mibhand.h"
    --EXCLUDE mitelExtInterfaces
    --EXCLUDE mitelPropNotifications
    --EXCLUDE mitelPropReset

	DEFINITIONS ::= BEGIN


    IMPORTS
	OBJECT-TYPE
		FROM RFC-1212
	TRAP-TYPE
		FROM RFC-1215
	DisplayString
		FROM RFC1213-MIB
    mitelAppCallServer, mitelConfCompliances, mitelConfAgents,
    mitelGrpCs2000, mitelIdCs2000Light
        FROM MITEL-MIB;

    mitelAppCs2000  OBJECT IDENTIFIER ::= {mitelAppCallServer 1}
-- MODULE-IDENTITY
--        LAST-UPDATED      "9903010000Z"
--        ORGANIZATION      "MITEL Corporation"
--        CONTACT-INFO      "Standards Group,
--                           Postal:    MITEL Corporation
--                           350 Legget Drive, PO Box 13089
--                           Kanata, Ontario
--                           Canada  K2K 1X3
--                           Tel: +1 613 592 2122
--                           Fax: +1 613 592 4784
--                           E-mail: std@mitel.com"
--        DESCRIPTION       "The MITEL SX-2000 MIB module."
--        REVISION          "9903010000Z"
--            DESCRIPTION   "SX-2000 MIB Version 1.0"

-- For SNMPv1 compliance:
Integer32 ::= INTEGER (-2147483648..2147483647)
DateAndTime ::= OCTET STRING(SIZE(8 | 11))

    -- ************************************
    -- SX-2000-specific Textual Conventions
    -- ************************************

    MitelCs2000AlarmLevelType ::= INTEGER {
                                almClear(1),     -- all clear
                                almMinor(2),     -- minor alarm
                                almMajor(3),     -- major alarm
                                almCritical(4)   -- critical alarm
				}

--TEXTUAL-CONVENTION
--        STATUS            current
--        DESCRIPTION       "The MITEL-defined alarm level type."


    -- ************************************
    -- The mitelAppCs2000 subtree... SX-2000.
    -- ************************************

    mitelCs2000System  OBJECT IDENTIFIER ::= {mitelAppCs2000 1 }
--OBJECT-IDENTITY
--    STATUS                current
--    DESCRIPTION           "Subtree for any product-specific information."
--    ::= { mitelAppCs2000 1 }

    mitelCs2000Alarms  OBJECT IDENTIFIER ::= {mitelAppCs2000 2}
--OBJECT-IDENTITY
--    STATUS                current
--    DESCRIPTION           "Alarms information for the SX-2000."
--    ::= { mitelAppCs2000 2 }

    -- ************************************
    -- The mitel subtree... table of Call Server-specific system information.
    -- ************************************

    mitelCs2000SysName    OBJECT-TYPE
        SYNTAX            DisplayString
        ACCESS        read-only
        STATUS           mandatory
        DESCRIPTION       "The name of the call server."
        ::= { mitelCs2000System 1 }


    -- ************************************
    -- The mitelCs2000Alarms subtree... table of alarm states
    -- ************************************


    mitelCs2000AlmLevel       OBJECT-TYPE
        SYNTAX            MitelCs2000AlarmLevelType
        ACCESS        read-only
        STATUS           mandatory
        DESCRIPTION       "The current overall alarm level for the call
                          server."
        ::= { mitelCs2000Alarms 1 }

    mitelCs2000AlmDetectDate  OBJECT-TYPE
        SYNTAX            DateAndTime
        ACCESS        read-only
        STATUS           mandatory
        DESCRIPTION       "Defines when the alarm was detected."
        ::= { mitelCs2000Alarms 2 }

    mitelCs2000AlmNbrCategories OBJECT-TYPE
        SYNTAX            Integer32
        ACCESS        read-only
        STATUS           mandatory
        DESCRIPTION       "Defines the number of associated entries in
                          the categories table."
        ::= { mitelCs2000Alarms 3 }

    -- ************************************
    -- The mitelCs2000CategoryTable subtree... table of categorized alarms
    -- ************************************

    mitelCs2000CategoryTable  OBJECT-TYPE
        SYNTAX            SEQUENCE OF MitelCs2000CategoryTableEntry
        ACCESS        not-accessible
        STATUS           mandatory
        DESCRIPTION       "Table defining the alarm state for individual
                          call server categories. There will be multiple
                          categories for each call server. The number of
                          rows in the table is determined by the total
                          of the mitelCs2000AlmTblNbrCategories value."
        ::= { mitelCs2000Alarms 4 }

    mitelCs2000CategoryTableEntry OBJECT-TYPE
        SYNTAX            MitelCs2000CategoryTableEntry
        ACCESS        not-accessible
        STATUS           mandatory
        DESCRIPTION       "A row defining a single category."
        INDEX             { mitelCs2000CatTblIndex }
        ::= { mitelCs2000CategoryTable 1 }

    MitelCs2000CategoryTableEntry ::=
        SEQUENCE {
          mitelCs2000CatTblIndex            INTEGER,
          mitelCs2000CatTblAvailable        Integer32,
          mitelCs2000CatTblUnavailable      Integer32,
          mitelCs2000CatTblLevel            MitelCs2000AlarmLevelType,
          mitelCs2000CatTblMinorThresh      Integer32,
          mitelCs2000CatTblMajorThresh      Integer32,
          mitelCs2000CatTblCriticalThresh   Integer32,
          mitelCs2000CatTblName             DisplayString
        }

    mitelCs2000CatTblIndex    OBJECT-TYPE
        SYNTAX           INTEGER
        ACCESS        read-only
        STATUS           mandatory
        DESCRIPTION       "Differentiates the different category reports
                          for the call server. The first category
                          will have an index value of 1, the second will
                          have 2, etc. up to the last category report. The
                          highest possible index value is 100."
        ::= { mitelCs2000CategoryTableEntry 1 }

    mitelCs2000CatTblAvailable OBJECT-TYPE
        SYNTAX            Integer32
        ACCESS        read-only
        STATUS           mandatory
        DESCRIPTION       "The number of available resources of this type
                          of category on this call server."
        ::= { mitelCs2000CategoryTableEntry 2 }

    mitelCs2000CatTblUnavailable OBJECT-TYPE
        SYNTAX            Integer32
        ACCESS        read-only
        STATUS           mandatory
        DESCRIPTION       "The number of unavailable resources of this type
                          of category on this call server."
        ::= { mitelCs2000CategoryTableEntry 3 }

    mitelCs2000CatTblLevel    OBJECT-TYPE
        SYNTAX            MitelCs2000AlarmLevelType
        ACCESS        read-only
        STATUS           mandatory
        DESCRIPTION       "Defines the alarm level for this category on this
                          call server."
        ::= { mitelCs2000CategoryTableEntry 4 }

    mitelCs2000CatTblMinorThresh OBJECT-TYPE
        SYNTAX            Integer32
        ACCESS        read-only
        STATUS           mandatory
        DESCRIPTION       "The percentage unavailable threshold indicating
                          a minor alarm on this call server category."
        ::= { mitelCs2000CategoryTableEntry 5 }

    mitelCs2000CatTblMajorThresh OBJECT-TYPE
        SYNTAX            Integer32
        ACCESS        read-only
        STATUS           mandatory
        DESCRIPTION       "The percentage unavailable threshold indicating
                          a major alarm on this call server category."
        ::= { mitelCs2000CategoryTableEntry 6 }

    mitelCs2000CatTblCriticalThresh OBJECT-TYPE
        SYNTAX            Integer32
        ACCESS        read-only
        STATUS           mandatory
        DESCRIPTION       "The percentage unavailable threshold indicating
                          a critical alarm on this call server category."
        ::= { mitelCs2000CategoryTableEntry 7 }

    mitelCs2000CatTblName     OBJECT-TYPE
        SYNTAX            DisplayString
        ACCESS        read-only
        STATUS           mandatory
        DESCRIPTION       "The name of this resource category."
        ::= { mitelCs2000CategoryTableEntry 8 }

    -- ************************************
    -- The SX-2000 Notifications
    -- ************************************

    mitelCs2000Notifications  OBJECT IDENTIFIER ::= {mitelAppCs2000 3}
--        STATUS           mandatory
--        DESCRIPTION       "The common traps supported by MITEL agents."
--        ::= { mitelAppCs2000 3 }

    mitelCs2000NotifAlarm     TRAP-TYPE
    ENTERPRISE mitelIdCs2000Light
        VARIABLES {
          mitelCs2000SysName,      	     -- the name of the system
          mitelCs2000AlmLevel,           -- the call server alarm level
          mitelCs2000AlmDetectDate,      -- the alarm detection time
          mitelCs2000AlmNbrCategories    -- indicates the number of assoc'd categories
        }
--        STATUS           mandatory
        DESCRIPTION       "This notification is generated whenever
                          an alarm condition is detected or cleared. The
                          manager is expected to retrieve the corresponding
                          alarm and category table information."
        ::= 201

    -- ************************************
    -- The mitelConformance subtree.
    -- ************************************

    mitelComplCs2000 OBJECT IDENTIFIER ::= {mitelConfCompliances 4}
-- MODULE-COMPLIANCE
--        STATUS           mandatory
--        DESCRIPTION       "The compliance statement for SNMPv2 entities which
--                           implement the MITEL SX-2000 MIB."
--        MODULE
--              compliance to the MITEL SX-2000 MIB module
--          MANDATORY-GROUPS { mitelGrpCs2000System }
--        ::= { mitelConfCompliances 4 }

    mitelGrpCs2000System  OBJECT IDENTIFIER ::= {mitelGrpCs2000 1}
--OBJECT-GROUP
--        OBJECTS           {
--                            mitelCs2000SysName
--                          }
--        STATUS          mandatory
--        DESCRIPTION       "The system information objects in the SX-2000 MIB."
--        ::= { mitelGrpCs2000 1 }

    mitelGrpCs2000Alarms  OBJECT IDENTIFIER ::= {mitelGrpCs2000 2}
--OBJECT-GROUP
--        OBJECTS           {
--                            mitelCs2000AlmLevel,
--                            mitelCs2000AlmDetectDate,
--                            mitelCs2000AlmNbrCategories,
--                            mitelCs2000CatTblAvailable,
--                            mitelCs2000CatTblUnavailable,
--                            mitelCs2000CatTblLevel,
--                            mitelCs2000CatTblMinorThresh,
--                            mitelCs2000CatTblMajorThresh,
--                            mitelCs2000CatTblCriticalThresh,
--                            mitelCs2000CatTblName
--                          }
--        STATUS           mandatory
--        DESCRIPTION       "The alarms-related objects in the SX-2000 MIB."
--        ::= { mitelGrpCs2000 2 }

--  mitelGrpCs2000AlarmsNotifs NOTIFICATION-GROUP
--      OBJECTS           {
--                          mitelCs2000NotifAlarm
--                        }
--      STATUS           mandatory
--      DESCRIPTION       "The current notifications in the SX-2000 MIB."
--      ::= { mitelGrpCs2000 3 }

    -- ************************************
    -- The mitelConfAgents subtree.
    -- ************************************

    mitelAgentCs2000    OBJECT IDENTIFIER ::= {mitelConfAgents 2}
--AGENT-CAPABILITIES
--        PRODUCT-RELEASE   "MITEL Agent Release 1.0 for SX-2000"
--        STATUS           mandatory
--        DESCRIPTION       "MITEL SX-2000 Agent."
--
--        SUPPORTS          SNMPv2-MIB
--            INCLUDES      {
--                            snmpStatsGroup, snmpORGroup,
--                            snmpTrapGroup, snmpSetGroup,
--                            snmpV1Group
--                          systemGroup, snmpGroup, snmpSetGroup,
--                          snmpBasicNotificationsGroup
--                          }
--
--        SUPPORTS          MITEL-MIB
--            INCLUDES      {
--                            mitelGrpCmnNotifBasic
--                          }
--            VARIATION     mitelNotifEnblTblEnable
--                ACCESS      read-only
--                DESCRIPTION "Implemented as a configuration file item."
--            VARIATION     mitelNotifEnblTblAck
--                ACCESS      read-only
--                DESCRIPTION "Acknowledgement of notifications is not
--                             supported. Will always return False."
--
--        SUPPORTS          MITEL-SX2000-MIB
--            INCLUDES      {
--                            mitelGrpCs2000Alarms,
--                          mitelGrpCs2000AlarmsNotifs
--                         }
--    ::= { mitelConfAgents 2 }

END -- MITEL-SX2000-MIB
