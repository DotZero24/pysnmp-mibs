-- Copyright 2006, 2007 MITEL Networks Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, condition, or performance of the Specification.

MITEL-BWM-MIB DEFINITIONS ::= BEGIN

    IMPORTS
        MODULE-IDENTITY,
        OBJECT-IDENTITY,
        OBJECT-TYPE,
        Integer32, Gauge32, Counter32        FROM SNMPv2-SMI
        TEXTUAL-CONVENTION, DateAndTime,
        DisplayString                        FROM SNMPv2-TC
        MODULE-COMPLIANCE,
        OBJECT-GROUP                         FROM SNMPv2-CONF
        mitelIpera3000Applications           FROM MITEL-IperaVoiceLAN-MIB;

    mitelBandWidthManagement        MODULE-IDENTITY
        LAST-UPDATED      "200703261541Z"
        ORGANIZATION      "MITEL Networks Corporation"
        CONTACT-INFO      "Standards Group,
                           Postal:    MITEL Networks Corporation
                           350 Legget Drive, PO Box 13089
                           Kanata, Ontario
                           Canada  K2K 2W7
                           Tel: +1 613 592 2122
                           Fax: +1 613 592 4784
                           E-mail: std@mitel.com"
        DESCRIPTION       "MIB for the Mitel Ipera 3000 Bandwidth Management
                           Application."
        REVISION          "200703261541Z"
        DESCRIPTION       "Added Units to the object descriptions."
        REVISION          "200608281626Z"
        DESCRIPTION       "Initial Version."
    ::= { mitelIpera3000Applications 1 }

    -- ****************************************************************
    -- MITEL Ipera 3000 BWM Contents
    -- ****************************************************************

    -- Notifications
    -- mitelBWMNotifications OBJECT IDENTIFIER ::= { mitelBandWidthManagement XXX }
    -- Note: Notifications will be handled by the Mitel common alarm framework
    --       (private.enterprises.mitel.mitelProprietary.mitelPropCommon.mitelCmnAlarms),
    --       and therefore no notifications branch is required.

    -- Tables, Scalars
    mitelBWMObjects       OBJECT IDENTIFIER ::= { mitelBandWidthManagement 1 }

    -- Conformance
    mitelBWMConformance   OBJECT IDENTIFIER ::= { mitelBandWidthManagement 2 }

    -- ****************************************************************
    -- MITEL Ipera 3000 BWM-specific Textual Conventions
    -- ****************************************************************

    MitelBWMPercentage ::=      TEXTUAL-CONVENTION
        DISPLAY-HINT      "d"
        STATUS            current
        DESCRIPTION       "Percentage value (from 0 to 100)."
        SYNTAX            Integer32 (0..100)

    MitelBWMZoneID ::=          TEXTUAL-CONVENTION
        DISPLAY-HINT      "d"
        STATUS            current
        DESCRIPTION       "Zone Identifier."
        SYNTAX            Integer32 (1..250)

    MitelBWMZAPID ::=           TEXTUAL-CONVENTION
        DISPLAY-HINT      "d"
        STATUS            current
        DESCRIPTION       "Zone Access Point Identifier."
        SYNTAX            Integer32 (1..6)

    -- ****************************************************************
    -- MITEL Ipera 3000 BWM Current Bandwidth Table
    -- ****************************************************************

    -- This table contains statistics about the state of bandwidth management for zone
    -- access points managed currently by this ICP.

    -- This table will be empty unless bandwidth reporting & statistics is enabled,
    -- and at least one zone access point is defined as managed by this ICP.

    mitelBWMCurrentTable                OBJECT-TYPE
        SYNTAX            SEQUENCE OF MitelBWMCurrentTableEntry
        MAX-ACCESS        not-accessible
        STATUS            current
        DESCRIPTION       "This table contains current statistics related to
                          bandwidth management for zone access points managed
                          by this ICP."
        ::= { mitelBWMObjects 1 }

    mitelBWMCurrentTableEntry           OBJECT-TYPE
        SYNTAX            MitelBWMCurrentTableEntry
        MAX-ACCESS        not-accessible
        STATUS            current
        DESCRIPTION       "A row defining a single current bandwidth table entry."
        INDEX             { mitelBWMCurrentZoneID,
                            mitelBWMCurrentParentZoneID,
                            mitelBWMCurrentZAPID }
        ::= { mitelBWMCurrentTable 1 }

    MitelBWMCurrentTableEntry::=
        SEQUENCE {
          mitelBWMCurrentZoneID           MitelBWMZoneID,
          mitelBWMCurrentParentZoneID     MitelBWMZoneID,
          mitelBWMCurrentZAPID            MitelBWMZAPID,
          mitelBWMCurrentZAPLabel         DisplayString,
          mitelBWMCurrentBandwidthInUse   Gauge32,
          mitelBWMCurrentBandwidthLimit   Gauge32,
          mitelBWMCurrentBandwidthRatio   MitelBWMPercentage
        }

    mitelBWMCurrentZoneID               OBJECT-TYPE
        SYNTAX            MitelBWMZoneID
        MAX-ACCESS        read-only
        STATUS            current
        DESCRIPTION       "Zone access points are defined between a zone and it's
                          parent, i.e.  [a]<--b-->[c].  This is the ID of the zone (a)."
        ::= { mitelBWMCurrentTableEntry 1 }

    mitelBWMCurrentParentZoneID         OBJECT-TYPE
        SYNTAX            MitelBWMZoneID
        MAX-ACCESS        read-only
        STATUS            current
        DESCRIPTION       "A zone access point is defined between a zone and it's
                          parent, i.e. [a]<--b-->[c] This is the ID of the parent
                          zone (c)."
        ::= { mitelBWMCurrentTableEntry 2 }

    mitelBWMCurrentZAPID                OBJECT-TYPE
        SYNTAX            MitelBWMZAPID
        MAX-ACCESS        read-only
        STATUS            current
        DESCRIPTION       "A zone access point is defined between a zone and it's
                          parent, i.e. [a]<--b-->[c] This is the ID of the zone
                          access point (b)."
        ::= { mitelBWMCurrentTableEntry 3 }

    mitelBWMCurrentZAPLabel             OBJECT-TYPE
        SYNTAX            DisplayString
        MAX-ACCESS        read-only
        STATUS            current
        DESCRIPTION       "This the zone access point label, as supplied by the
                          user."
        ::= { mitelBWMCurrentTableEntry 4 }

    mitelBWMCurrentBandwidthInUse       OBJECT-TYPE
        SYNTAX            Gauge32
        UNITS             "kilobits per second"
        MAX-ACCESS        read-only
        STATUS            current
        DESCRIPTION       "This is the bandwidth currently in use at the zone
                          access point by managed voice over IP media streams.
                          Units in kilobits per second."
        ::= { mitelBWMCurrentTableEntry 5 }

    mitelBWMCurrentBandwidthLimit       OBJECT-TYPE
        SYNTAX            Gauge32
        UNITS             "kilobits per second"
        MAX-ACCESS        read-only
        STATUS            current
        DESCRIPTION       "This is the bandwidth limit currently configured at the
                          zone access point for managed voice over IP media streams.
                          Units in kilobits per second."
        ::= { mitelBWMCurrentTableEntry 6 }

    mitelBWMCurrentBandwidthRatio       OBJECT-TYPE
        SYNTAX            MitelBWMPercentage
        MAX-ACCESS        read-only
        STATUS            current
        DESCRIPTION       "This is the ratio of mitelBWMCurrentBandwidthInUse
                          to mitelBWMCurrentBandwidthLimit expressed as a
                          percentage."
        ::= { mitelBWMCurrentTableEntry 7 }

    -- ****************************************************************
    -- MITEL Ipera 3000 BWM Cumulative CAC Stats Table
    -- ****************************************************************

    -- This table contains cumulative statistics about the number of calls which
    -- have been admitted or rejected by connection admission control based on
    -- bandwidth availability at zone access points managed currently by this ICP.

    -- This table will be empty unless connection admission control is enabled,
    -- and at least one zone access point is defined as managed by this ICP.

    mitelBWMCumCACTable                 OBJECT-TYPE
        SYNTAX            SEQUENCE OF MitelBWMCumCACTableEntry
        MAX-ACCESS        not-accessible
        STATUS            current
        DESCRIPTION       "This table contains cumulative statistics related to
                          bandwidth management connection admission control for
                          zone access points managed by this ICP."
        ::= { mitelBWMObjects 2 }

    mitelBWMCumCACTableEntry     OBJECT-TYPE
        SYNTAX            MitelBWMCumCACTableEntry
        MAX-ACCESS        not-accessible
        STATUS            current
        DESCRIPTION       "A row defining a single cumulative connection admission
                          control statistics table entry."
        INDEX             { mitelBWMCumZoneID,
                            mitelBWMCumParentZoneID,
                            mitelBWMCumZAPID }
        ::= { mitelBWMCumCACTable 1 }

    MitelBWMCumCACTableEntry ::=
        SEQUENCE {
          mitelBWMCumZoneID               MitelBWMZoneID,
          mitelBWMCumParentZoneID         MitelBWMZoneID,
          mitelBWMCumZAPID                MitelBWMZAPID,
          mitelBWMCumZAPLabel             DisplayString,
          mitelBWMCumCACAdmissions        Counter32,
          mitelBWMCumCACRejections        Counter32,
          mitelBWMCumCACRejectionRatio    MitelBWMPercentage
        }

    mitelBWMCumZoneID                   OBJECT-TYPE
        SYNTAX            MitelBWMZoneID
        MAX-ACCESS        read-only
        STATUS            current
        DESCRIPTION       "Zone access points are defined between a zone and it's
                          parent, i.e.  [a]<--b-->[c].  This is the ID of the zone (a)."
        ::= { mitelBWMCumCACTableEntry 1 }

    mitelBWMCumParentZoneID             OBJECT-TYPE
        SYNTAX            MitelBWMZoneID
        MAX-ACCESS        read-only
        STATUS            current
        DESCRIPTION       "A zone access point is defined between a zone and it's
                          parent, i.e. [a]<--b-->[c] This is the ID of the parent
                          zone (c)."
        ::= { mitelBWMCumCACTableEntry 2 }

    mitelBWMCumZAPID                    OBJECT-TYPE
        SYNTAX            MitelBWMZAPID
        MAX-ACCESS        read-only
        STATUS            current
        DESCRIPTION       "A zone access point is defined between a zone and it's
                          parent, i.e. [a]<--b-->[c] This is the ID of the zone
                          access point (b)."
        ::= { mitelBWMCumCACTableEntry 3 }

    mitelBWMCumZAPLabel                 OBJECT-TYPE
        SYNTAX            DisplayString
        MAX-ACCESS        read-only
        STATUS            current
        DESCRIPTION       "This the zone access point label, as supplied by the
                          user."
        ::= { mitelBWMCumCACTableEntry 4 }

    mitelBWMCumCACAdmissions            OBJECT-TYPE
        SYNTAX            Counter32
        UNITS             "calls"
        MAX-ACCESS        read-only
        STATUS            current
        DESCRIPTION       "This is the number of calls admitted through this zone
                          access point by this ICP since the system was started or
                          the zone access point was created, or since the cumulative
                          statistics were cleared."
        ::= { mitelBWMCumCACTableEntry 5 }

    mitelBWMCumCACRejections            OBJECT-TYPE
        SYNTAX            Counter32
        UNITS             "calls"
        MAX-ACCESS        read-only
        STATUS            current
        DESCRIPTION       "This is the number of calls rejected due to bandwidth being
                          fully utilized at this zone access point by this ICP since
                          the system was started or the zone access point was created,
                          or since the cumulative statistics were cleared."
        ::= { mitelBWMCumCACTableEntry 6 }

    mitelBWMCumCACRejectionRatio        OBJECT-TYPE
        SYNTAX            MitelBWMPercentage
        MAX-ACCESS        read-only
        STATUS            current
        DESCRIPTION       "This is the ratio of mitelBWMCACRejections
                          to the sum of mitelBWMCACRejections and
                          mitelBWMCACAdmissions (i.e. rejections to all
                          calls) expressed as a percentage."
        ::= { mitelBWMCumCACTableEntry 7 }

    -- ****************************************************************
    -- MITEL Ipera 3000 BWM 15 Minute Historical Statistics Table
    -- ****************************************************************

    -- This table contains historical bandwidth management statistics for zone
    -- access points managed currently by this ICP recorded at 15 minute intervals.

    -- This table will be empty unless connection admission control or bandwidth
    -- reporting & statistics are enabled, and at least one zone access point is
    -- defined as managed by this ICP.

    mitelBWM15MinHistoryTable   OBJECT-TYPE
        SYNTAX            SEQUENCE OF MitelBWM15MinHistoryTableEntry
        MAX-ACCESS        not-accessible
        STATUS            current
        DESCRIPTION       "This table contains historical statistics recorded at
                          15 minute intervals related to bandwidth management for
                          zone access points managed by this ICP."
        ::= { mitelBWMObjects 3 }

    mitelBWM15MinHistoryTableEntry     OBJECT-TYPE
        SYNTAX            MitelBWM15MinHistoryTableEntry
        MAX-ACCESS        not-accessible
        STATUS            current
        DESCRIPTION       "A row defining a single 15 minute interval for a specific
                          zone access point in the 15 minute historical table."
        INDEX             { mitelBWM15MinZoneID,
                            mitelBWM15MinParentZoneID,
                            mitelBWM15MinZAPID,
                            mitelBWM15MinDateAndTime }
        ::= { mitelBWM15MinHistoryTable 1 }

    MitelBWM15MinHistoryTableEntry ::=
        SEQUENCE {
          mitelBWM15MinZoneID                MitelBWMZoneID,
          mitelBWM15MinParentZoneID          MitelBWMZoneID,
          mitelBWM15MinZAPID                 MitelBWMZAPID,
          mitelBWM15MinDateAndTime           DateAndTime,
          mitelBWM15MinZAPLabel              DisplayString,
          mitelBWM15MinCACAdmissions         Counter32,
          mitelBWM15MinCACRejections         Counter32,
          mitelBWM15MinCACRejectionRatio     MitelBWMPercentage,
          mitelBWM15MinAverageBandwidthUsed  Gauge32,
          mitelBWM15MinPeakBandwidthUsed     Gauge32,
          mitelBWM15MinAverageAvailable      Gauge32,
          mitelBWM15MinFinalBandwidthLimit   Gauge32,
          mitelBWM15MinPeakBandwidthRatio    MitelBWMPercentage,
          mitelBWM15MinPeakBwdthAboveLimit   Gauge32
        }

    mitelBWM15MinZoneID   OBJECT-TYPE
        SYNTAX            MitelBWMZoneID
        MAX-ACCESS        read-only
        STATUS            current
        DESCRIPTION       "Zone access points are defined between a zone and it's
                          parent, i.e.  [a]<--b-->[c].  This is the ID of the zone (a)."
        ::= { mitelBWM15MinHistoryTableEntry 1 }

    mitelBWM15MinParentZoneID   OBJECT-TYPE
        SYNTAX            MitelBWMZoneID
        MAX-ACCESS        read-only
        STATUS            current
        DESCRIPTION       "A zone access point is defined between a zone and it's
                          parent, i.e. [a]<--b-->[c] This is the ID of the parent
                          zone (c)."
        ::= { mitelBWM15MinHistoryTableEntry 2 }

    mitelBWM15MinZAPID                  OBJECT-TYPE
        SYNTAX            MitelBWMZAPID
        MAX-ACCESS        read-only
        STATUS            current
        DESCRIPTION       "A zone access point is defined between a zone and it's
                          parent, i.e. [a]<--b-->[c] This is the ID of the zone
                          access point (b)."
        ::= { mitelBWM15MinHistoryTableEntry 3 }

    mitelBWM15MinDateAndTime            OBJECT-TYPE
        SYNTAX            DateAndTime
        MAX-ACCESS        read-only
        STATUS            current
        DESCRIPTION       "The system date and time as set when the interval was
                          recorded.  Note that if the system date and time are
                          changed while recording intervals, the interval with the
                          earliest Date and Time value may not necessarily be the
                          oldest entry."
        ::= { mitelBWM15MinHistoryTableEntry 4 }

    mitelBWM15MinZAPLabel               OBJECT-TYPE
        SYNTAX            DisplayString
        MAX-ACCESS        read-only
        STATUS            current
        DESCRIPTION       "This the zone access point label, as supplied by the
                          user."
        ::= { mitelBWM15MinHistoryTableEntry 5 }

    mitelBWM15MinCACAdmissions          OBJECT-TYPE
        SYNTAX            Counter32
        UNITS             "calls"
        MAX-ACCESS        read-only
        STATUS            current
        DESCRIPTION       "This is the number of calls admitted through this zone
                          access point by this ICP during the interval."
        ::= { mitelBWM15MinHistoryTableEntry 6 }

    mitelBWM15MinCACRejections          OBJECT-TYPE
        SYNTAX            Counter32
        UNITS             "calls"
        MAX-ACCESS        read-only
        STATUS            current
        DESCRIPTION       "This is the number of calls rejected due to bandwidth being
                          fully utilized at this zone access point by this ICP during
                          the interval."
        ::= { mitelBWM15MinHistoryTableEntry 7 }

    mitelBWM15MinCACRejectionRatio      OBJECT-TYPE
        SYNTAX            MitelBWMPercentage
        MAX-ACCESS        read-only
        STATUS            current
        DESCRIPTION       "This is the ratio of mitelBWMCACRejections
                          to the sum of mitelBWMCACRejections and
                          mitelBWMCACAdmissions (i.e. rejections to all
                          calls) expressed as a percentage."
        ::= { mitelBWM15MinHistoryTableEntry 8 }

    mitelBWM15MinAverageBandwidthUsed   OBJECT-TYPE
        SYNTAX            Gauge32
        UNITS             "kilobits per second"
        MAX-ACCESS        read-only
        STATUS            current
        DESCRIPTION       "This is the average bandwidth in use at the zone
                          access point by managed voice over IP media streams
                          over the interval. Units in kilobits per second."
        ::= { mitelBWM15MinHistoryTableEntry 9 }

    mitelBWM15MinPeakBandwidthUsed      OBJECT-TYPE
        SYNTAX            Gauge32
        UNITS             "kilobits per second"
        MAX-ACCESS        read-only
        STATUS            current
        DESCRIPTION       "This is the peak bandwidth limit in use at the zone
                          access point by managed voice over IP media streams
                          during the interval. Units in kilobits per second."
        ::= { mitelBWM15MinHistoryTableEntry 10 }

    mitelBWM15MinAverageAvailable       OBJECT-TYPE
        SYNTAX            Gauge32
        UNITS             "kilobits per second"
        MAX-ACCESS        read-only
        STATUS            current
        DESCRIPTION       "This is the average bandwidth available at the zone
                          access point for managed voice over IP media streams
                          during the interval. Units in kilobits per second."
        ::= { mitelBWM15MinHistoryTableEntry 11 }

    mitelBWM15MinFinalBandwidthLimit    OBJECT-TYPE
        SYNTAX            Gauge32
        UNITS             "kilobits per second"
        MAX-ACCESS        read-only
        STATUS            current
        DESCRIPTION       "This is the configured bandwidth limit for the zone
                          access point for managed voice over IP media streams
                          recorded at the end of the interval. Units in kilobits per second."
        ::= { mitelBWM15MinHistoryTableEntry 12 }

    mitelBWM15MinPeakBandwidthRatio     OBJECT-TYPE
        SYNTAX            MitelBWMPercentage
        MAX-ACCESS        read-only
        STATUS            current
        DESCRIPTION       "This is the ratio of mitelBWMPeakBandwidthUsed
                          to mitelBWMFinalBandwidthLimit expressed as a
                          percentage."
        ::= { mitelBWM15MinHistoryTableEntry 13 }

    mitelBWM15MinPeakBwdthAboveLimit    OBJECT-TYPE
        SYNTAX            Gauge32
        UNITS             "kilobits per second"
        MAX-ACCESS        read-only
        STATUS            current
        DESCRIPTION       "This is the difference between mitelBWMPeakBandwidthUsed
                          and mitelBWMFinalBandwidthLimit if it was ever
                          over the limit for the the zone access point for managed
                          voice over IP media streams during the interval.
                          Units in kilobits per second."
        ::= { mitelBWM15MinHistoryTableEntry 14 }

   -- ****************************************************************
    -- MITEL Ipera 3000 BWM 24 Hour Historical Statistics Table
    -- ****************************************************************

    -- This table contains historical bandwidth management statistics for zone
    -- access points managed currently by this ICP recorded at 24 hour intervals.

    -- This table will be empty unless connection admission control or bandwidth
    -- reporting & statistics are enabled, and at least one zone access point is
    -- defined as managed by this ICP.

    mitelBWM24HrHistoryTable   OBJECT-TYPE
        SYNTAX            SEQUENCE OF MitelBWM24HrHistoryTableEntry
        MAX-ACCESS        not-accessible
        STATUS            current
        DESCRIPTION       "This table contains historical statistics recorded at
                          24 hour intervals related to bandwidth management for
                          zone access points managed by this ICP."
        ::= { mitelBWMObjects 4 }

    mitelBWM24HrHistoryTableEntry     OBJECT-TYPE
        SYNTAX            MitelBWM24HrHistoryTableEntry
        MAX-ACCESS        not-accessible
        STATUS            current
        DESCRIPTION       "A row defining a single 24 hour interval for a specific
                          zone access point in the 24 hour historical table."
        INDEX             { mitelBWM24HrZoneID,
                            mitelBWM24HrParentZoneID,
                            mitelBWM24HrZAPID,
                            mitelBWM24HrDateAndTime }
        ::= { mitelBWM24HrHistoryTable 1 }

    MitelBWM24HrHistoryTableEntry ::=
        SEQUENCE {
          mitelBWM24HrZoneID                MitelBWMZoneID,
          mitelBWM24HrParentZoneID          MitelBWMZoneID,
          mitelBWM24HrZAPID                 MitelBWMZAPID,
          mitelBWM24HrDateAndTime           DateAndTime,
          mitelBWM24HrZAPLabel              DisplayString,
          mitelBWM24HrCACAdmissions         Counter32,
          mitelBWM24HrCACRejections         Counter32,
          mitelBWM24HrCACRejectionRatio     MitelBWMPercentage,
          mitelBWM24HrAverageBandwidthUsed  Gauge32,
          mitelBWM24HrPeakBandwidthUsed     Gauge32,
          mitelBWM24HrAverageAvailable      Gauge32,
          mitelBWM24HrFinalBandwidthLimit   Gauge32,
          mitelBWM24HrPeakBandwidthRatio    MitelBWMPercentage,
          mitelBWM24HrPeakBwdthAboveLimit   Gauge32
        }

    mitelBWM24HrZoneID   OBJECT-TYPE
        SYNTAX            MitelBWMZoneID
        MAX-ACCESS        read-only
        STATUS            current
        DESCRIPTION       "Zone access points are defined between a zone and it's
                          parent, i.e.  [a]<--b-->[c].  This is the ID of the zone (a)."
        ::= { mitelBWM24HrHistoryTableEntry 1 }

    mitelBWM24HrParentZoneID   OBJECT-TYPE
        SYNTAX            MitelBWMZoneID
        MAX-ACCESS        read-only
        STATUS            current
        DESCRIPTION       "A zone access point is defined between a zone and it's
                          parent, i.e. [a]<--b-->[c] This is the ID of the parent
                          zone (c)."
        ::= { mitelBWM24HrHistoryTableEntry 2 }

    mitelBWM24HrZAPID                  OBJECT-TYPE
        SYNTAX            MitelBWMZAPID
        MAX-ACCESS        read-only
        STATUS            current
        DESCRIPTION       "A zone access point is defined between a zone and it's
                          parent, i.e. [a]<--b-->[c] This is the ID of the zone
                          access point (b)."
        ::= { mitelBWM24HrHistoryTableEntry 3 }

    mitelBWM24HrDateAndTime            OBJECT-TYPE
        SYNTAX            DateAndTime
        MAX-ACCESS        read-only
        STATUS            current
        DESCRIPTION       "The system date and time as set when the interval was
                          recorded.  Note that if the system date and time are
                          changed while recording intervals, the interval with the
                          earliest Date and Time value may not necessarily be the
                          oldest entry."
        ::= { mitelBWM24HrHistoryTableEntry 4 }

    mitelBWM24HrZAPLabel               OBJECT-TYPE
        SYNTAX            DisplayString
        MAX-ACCESS        read-only
        STATUS            current
        DESCRIPTION       "This the zone access point label, as supplied by the
                          user."
        ::= { mitelBWM24HrHistoryTableEntry 5 }

    mitelBWM24HrCACAdmissions          OBJECT-TYPE
        SYNTAX            Counter32
        UNITS             "calls"
        MAX-ACCESS        read-only
        STATUS            current
        DESCRIPTION       "This is the number of calls admitted through this zone
                          access point by this ICP during the interval."
        ::= { mitelBWM24HrHistoryTableEntry 6 }

    mitelBWM24HrCACRejections          OBJECT-TYPE
        SYNTAX            Counter32
        UNITS             "calls"
        MAX-ACCESS        read-only
        STATUS            current
        DESCRIPTION       "This is the number of calls rejected due to bandwidth being
                          fully utilized at this zone access point by this ICP during
                          the interval."
        ::= { mitelBWM24HrHistoryTableEntry 7 }

    mitelBWM24HrCACRejectionRatio      OBJECT-TYPE
        SYNTAX            MitelBWMPercentage
        MAX-ACCESS        read-only
        STATUS            current
        DESCRIPTION       "This is the ratio of mitelBWMCACRejections
                          to the sum of mitelBWMCACRejections and
                          mitelBWMCACAdmissions (i.e. rejections to all
                          calls) expressed as a percentage."
        ::= { mitelBWM24HrHistoryTableEntry 8 }

    mitelBWM24HrAverageBandwidthUsed   OBJECT-TYPE
        SYNTAX            Gauge32
        UNITS             "kilobits per second"
        MAX-ACCESS        read-only
        STATUS            current
        DESCRIPTION       "This is the average bandwidth in use at the zone
                          access point by managed voice over IP media streams
                          over the interval. Units in kilobits per second."
        ::= { mitelBWM24HrHistoryTableEntry 9 }

    mitelBWM24HrPeakBandwidthUsed      OBJECT-TYPE
        SYNTAX            Gauge32
        UNITS             "kilobits per second"
        MAX-ACCESS        read-only
        STATUS            current
        DESCRIPTION       "This is the peak bandwidth limit in use at the zone
                          access point by managed voice over IP media streams
                          during the interval. Units in kilobits per second."
        ::= { mitelBWM24HrHistoryTableEntry 10 }

    mitelBWM24HrAverageAvailable       OBJECT-TYPE
        SYNTAX            Gauge32
        UNITS             "kilobits per second"
        MAX-ACCESS        read-only
        STATUS            current
        DESCRIPTION       "This is the average bandwidth available at the zone
                          access point for managed voice over IP media streams
                          during the interval. Units in kilobits per second."
        ::= { mitelBWM24HrHistoryTableEntry 11 }

    mitelBWM24HrFinalBandwidthLimit    OBJECT-TYPE
        SYNTAX            Gauge32
        UNITS             "kilobits per second"
        MAX-ACCESS        read-only
        STATUS            current
        DESCRIPTION       "This is the configured bandwidth limit for the zone
                          access point for managed voice over IP media streams
                          recorded at the end of the interval.
                          Units in kilobits per second."
        ::= { mitelBWM24HrHistoryTableEntry 12 }

    mitelBWM24HrPeakBandwidthRatio     OBJECT-TYPE
        SYNTAX            MitelBWMPercentage
        MAX-ACCESS        read-only
        STATUS            current
        DESCRIPTION       "This is the ratio of mitelBWMPeakBandwidthUsed
                          to mitelBWMFinalBandwidthLimit expressed as a
                          percentage."
        ::= { mitelBWM24HrHistoryTableEntry 13 }

    mitelBWM24HrPeakBwdthAboveLimit    OBJECT-TYPE
        SYNTAX            Gauge32
        UNITS             "kilobits per second"
        MAX-ACCESS        read-only
        STATUS            current
        DESCRIPTION       "This is the difference between mitelBWMPeakBandwidthUsed
                          and mitelBWMFinalBandwidthLimit if it was ever
                          over the limit for the the zone access point for managed
                          voice over IP media streams during the interval.
                          Units in kilobits per second."
        ::= { mitelBWM24HrHistoryTableEntry 14 }

    -- ****************************************************************
    -- MITEL Ipera 3000 BWM Compliances
    -- ****************************************************************

    mitelBWMGroups   OBJECT-IDENTITY
	STATUS            current
        DESCRIPTION       "The group subtree. Leaves in this subtree identify
                          object groupings used in the compliance statements."
        ::= { mitelBWMConformance 1 }

    mitelBWMCompliances    OBJECT-IDENTITY
        STATUS            current
        DESCRIPTION       "The compliance subtree. Leaves in this subtree are
                          used for defining the ways in which an agent can
                          claim compliance with this or other MITEL MIBs."
        ::= { mitelBWMConformance 2 }

    mitelBWMCompliance MODULE-COMPLIANCE
        STATUS            current
        DESCRIPTION       "The compliance statement for SNMPv2 entities which
                          implement the Mitel Bandwidth Management MIB."

        MODULE  -- this module
        MANDATORY-GROUPS  { mitelBWMCurrentStatisticsGroup,
                            mitelBWMCumulativeStatisticsGroup }

        GROUP             mitelBWMHistoricalStatisticsGroup
        DESCRIPTION       "This group is mandatory for agents implementing this
                          MIB."

    ::= { mitelBWMCompliances 1 }

    mitelBWMCurrentStatisticsGroup     OBJECT-GROUP
        OBJECTS           { mitelBWMCurrentZoneID,
                            mitelBWMCurrentParentZoneID,
                            mitelBWMCurrentZAPID,
                            mitelBWMCurrentZAPLabel,
                            mitelBWMCurrentBandwidthInUse,
                            mitelBWMCurrentBandwidthLimit,
                            mitelBWMCurrentBandwidthRatio }
        STATUS            current
        DESCRIPTION       "A collection of objects providing current statistics
                          pertaining to bandwidth management at zone access
                          points managed by the ICP."

    ::= { mitelBWMGroups 1 }

    mitelBWMCumulativeStatisticsGroup     OBJECT-GROUP
        OBJECTS           { mitelBWMCumZoneID,
                            mitelBWMCumParentZoneID,
                            mitelBWMCumZAPID,
                            mitelBWMCumZAPLabel,
                            mitelBWMCumCACAdmissions,
                            mitelBWMCumCACRejections,
                            mitelBWMCumCACRejectionRatio }
        STATUS            current
        DESCRIPTION       "A collection of objects providing cumulative CAC
                          statistics pertaining to bandwidth management at zone
                          access points managed by the ICP."
    ::= { mitelBWMGroups 2 }

    mitelBWMHistoricalStatisticsGroup  OBJECT-GROUP
        OBJECTS           { mitelBWM15MinZoneID,
                            mitelBWM15MinParentZoneID,
                            mitelBWM15MinZAPID,
                            mitelBWM15MinDateAndTime,
                            mitelBWM15MinZAPLabel,
                            mitelBWM15MinCACAdmissions,
                            mitelBWM15MinCACRejections,
                            mitelBWM15MinCACRejectionRatio,
                            mitelBWM15MinAverageBandwidthUsed,
                            mitelBWM15MinPeakBandwidthUsed,
                            mitelBWM15MinAverageAvailable,
                            mitelBWM15MinFinalBandwidthLimit,
                            mitelBWM15MinPeakBandwidthRatio,
                            mitelBWM15MinPeakBwdthAboveLimit,

                            mitelBWM24HrZoneID,
                            mitelBWM24HrParentZoneID,
                            mitelBWM24HrZAPID,
                            mitelBWM24HrDateAndTime,
                            mitelBWM24HrZAPLabel,
                            mitelBWM24HrCACAdmissions,
                            mitelBWM24HrCACRejections,
                            mitelBWM24HrCACRejectionRatio,
                            mitelBWM24HrAverageBandwidthUsed,
                            mitelBWM24HrPeakBandwidthUsed,
                            mitelBWM24HrAverageAvailable,
                            mitelBWM24HrFinalBandwidthLimit,
                            mitelBWM24HrPeakBandwidthRatio,
                            mitelBWM24HrPeakBwdthAboveLimit }
        STATUS              current
        DESCRIPTION       "A collection of objects providing historical CAC and bandwidth
                          statistics pertaining to bandwidth management at zone
                          access points managed by the ICP."
    ::= { mitelBWMGroups 3 }

END
