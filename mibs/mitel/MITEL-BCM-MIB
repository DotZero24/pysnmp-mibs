-- Copyright 2009 MITEL Networks Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, condition, or performance of the Specification.

MITEL-BCM-MIB DEFINITIONS ::= BEGIN

    IMPORTS
        MODULE-IDENTITY, OBJECT-TYPE,
        Counter32, Integer32
            FROM SNMPv2-SMI
        MODULE-COMPLIANCE, OBJECT-GROUP
            FROM SNMPv2-CONF
        PhysAddress, DisplayString
            FROM SNMPv2-TC
        InterfaceIndex
            FROM IF-MIB
        mitelPropTransmission
            FROM MITEL-MIB;

    mitelBCM    MODULE-IDENTITY
        LAST-UPDATED      "200903170000Z"
        ORGANIZATION      "MITEL Networks Corporation"
        CONTACT-INFO      "Standards Group,
                           Postal:    MITEL Networks Corporation
                           350 Legget Drive, PO Box 13089
                           Kanata, Ontario
                           Canada  K2K 2W7
                           Tel: +1 613 592 2122
                           Fax: +1 613 592 4784
                           E-mail: std@mitel.com"
        DESCRIPTION       "The MITEL Broadcom Switch MIB module.
                           This MIB module is defined to specifically
                           provide additional statistical information
                           for the Broadcom Switch subsystem."
        REVISION          "200903170000Z"
        DESCRIPTION       "Added new BCM chip to the enumeration.
                           Also updated copyright."
        REVISION          "200601100000Z"
        DESCRIPTION       "Applied stronger lint and made corrections.
                           Also updated copyright."
        REVISION          "200510040100Z"
        DESCRIPTION       "Integrated in change requests and added mitelBCMChipCount."
        REVISION          "200510030100Z"
        DESCRIPTION       "Added Compliance and Conformance statements."
        REVISION          "200509300100Z"
        DESCRIPTION       "Created."
    ::= { mitelPropTransmission 1 }

    mitelBCMObjects      OBJECT IDENTIFIER ::= { mitelBCM 1 }
    mitelBCMConformance  OBJECT IDENTIFIER ::= { mitelBCM 2 }

    -- ****************************************************************
    -- The Mitel BCM Port Group
    -- ****************************************************************

   mitelBCMPortTable  OBJECT-TYPE
        SYNTAX         SEQUENCE OF MitelBCMPortTableEntry
        MAX-ACCESS     not-accessible
        STATUS         current
        DESCRIPTION    "Table defining statistical information about each
                        port of a Broadcom Switch sub-system."
        ::= { mitelBCMObjects 1 }

   mitelBCMPortTableEntry OBJECT-TYPE
        SYNTAX            MitelBCMPortTableEntry
        MAX-ACCESS        not-accessible
        STATUS            current
        DESCRIPTION       "A row defining a single BCM Port table entry."
        INDEX             { mitelBCMPortIndex }
        ::= { mitelBCMPortTable 1 }

    MitelBCMPortTableEntry ::=
        SEQUENCE {
          mitelBCMPortIndex       InterfaceIndex,
          mitelBCMPortRxSAChanges Counter32,
          mitelBCMPortRxLastSA    PhysAddress
        }

    mitelBCMPortIndex  OBJECT-TYPE
        SYNTAX         InterfaceIndex
        MAX-ACCESS     read-only -- smilint warning should be not-accessible
        STATUS         current
        DESCRIPTION    "The interface identifier for this switch port.
                        Usually corresponds to ifIndex in the ifTable."
        ::= { mitelBCMPortTableEntry 1 }

    mitelBCMPortRxSAChanges  OBJECT-TYPE
        SYNTAX               Counter32
        MAX-ACCESS           read-only
        STATUS               current
        DESCRIPTION          "The number of times the source address (SA)
                              of good received packets has changed.  A
                              count greater than one generally indicates
                              the port is connected to a repeater based
                              network."
        ::= { mitelBCMPortTableEntry 2 }

    mitelBCMPortRxLastSA  OBJECT-TYPE
        SYNTAX            PhysAddress
        MAX-ACCESS        read-only
        STATUS            current
        DESCRIPTION       "The last received source address on this port."
        ::= { mitelBCMPortTableEntry 3 }

    -- ****************************************************************
    -- The Mitel BCM Chip Group
    -- ****************************************************************

    mitelBCMChipCount  OBJECT-TYPE
        SYNTAX         Integer32
        MAX-ACCESS     read-only
        STATUS         current
        DESCRIPTION    "The number of BCM ethernet chips in the system."
        ::= { mitelBCMObjects 2 }

    mitelBCMChipTable  OBJECT-TYPE
        SYNTAX         SEQUENCE OF MitelBCMChipTableEntry
        MAX-ACCESS     not-accessible
        STATUS         current
        DESCRIPTION    "Table defining characteristic information about
                        each Broadcom Switch chip in the system."
        ::= { mitelBCMObjects 3 }

    mitelBCMChipTableEntry OBJECT-TYPE
        SYNTAX            MitelBCMChipTableEntry
        MAX-ACCESS        not-accessible
        STATUS            current
        DESCRIPTION       "A row defining a single Broadcom (BCM) Chip
                           table entry."
        INDEX             { mitelBCMChipIndex }
        ::= { mitelBCMChipTable 1 }

    MitelBCMChipTableEntry ::=
        SEQUENCE {
          mitelBCMChipIndex       Integer32,
          mitelBCMChipBIST        BITS,
          mitelBCMChipRev         DisplayString,
          mitelBCMChipType        INTEGER
        }
    mitelBCMChipIndex  OBJECT-TYPE
        SYNTAX         Integer32 (1..65535)
        MAX-ACCESS     read-only -- smilint warning should be not-accessible
        STATUS         current
        DESCRIPTION    "The identifier for this switch chip."
        ::= { mitelBCMChipTableEntry 1 }

    mitelBCMChipBIST  OBJECT-TYPE
        SYNTAX         BITS {
                           bcRam(0),
                           ipDbm(1),
                           mRam(2),
                           gmRam(3)
                       }
        MAX-ACCESS     read-only
        STATUS         current
        DESCRIPTION    "The status of the BCM ethernet chip
                        built-in-self-test (BIST).

                        BCRAM(0) bit 2^0 - Buffer control RAM (only in BCM5380M)
                        IPDBM(1) bit 2^1 - Internal packet data buffer memory
                        MRAM(2)  bit 2^2 - MIB RAM (only in BCM5380M)
                        GMRAM(3) bit 2^3 - Gigabit MIB RAM (only in BCM5380M)

                        If the bit is set, then that sub-system has failed."
        ::= { mitelBCMChipTableEntry 2 }

    mitelBCMChipRev  OBJECT-TYPE
        SYNTAX         DisplayString
        MAX-ACCESS     read-only
        STATUS         current
        DESCRIPTION    "The BCM ethernet chip revision ID."
        ::= { mitelBCMChipTableEntry 3 }

    mitelBCMChipType  OBJECT-TYPE
        SYNTAX         INTEGER {
                              bcm5380m(1),
                              bcm5325e(2),
                              bcm5324m(3),
                              bcmOther(4)
                       }
        MAX-ACCESS     read-only
        STATUS         current
        DESCRIPTION    "The BCM ethernet chip type."
        ::= { mitelBCMChipTableEntry 4 }

    --
    --
    -- Conformance information
    --
    --

    mitelBCMCompliances  OBJECT IDENTIFIER ::= { mitelBCMConformance 1 }
    mitelBCMGroups       OBJECT IDENTIFIER ::= { mitelBCMConformance 2 }

    --
    --
    -- Compliance statements
    --
    --

    mitelBCMSwitchCompliance MODULE-COMPLIANCE
        STATUS  current
        DESCRIPTION
                "The compliance statement for mitel nodes that
                 include a BCM switch sub-system."

        MODULE  --  this module

        MANDATORY-GROUPS { mitelBCMPortGroup,
                           mitelBCMChipGroup }

    ::= { mitelBCMCompliances 1 }

    mitelBCMPortGroup   OBJECT-GROUP
        OBJECTS {
            mitelBCMPortIndex,
            mitelBCMPortRxSAChanges,
            mitelBCMPortRxLastSA
        }
        STATUS  current
        DESCRIPTION
            "A collection of objects that provide statistical
             infrormation about BCM switch ports."
     ::= { mitelBCMGroups 1 }

    mitelBCMChipGroup   OBJECT-GROUP
        OBJECTS {
            mitelBCMChipCount,
            mitelBCMChipIndex,
            mitelBCMChipBIST,
            mitelBCMChipRev,
            mitelBCMChipType
        }
        STATUS  current
        DESCRIPTION
            "A collection of objects that provide
            infrormation about BCM switch Chips."
     ::= { mitelBCMGroups 2 }

-- MITEL-BCM-MIB

END
