SDX-ROOT-MIB DEFINITIONS ::= BEGIN

IMPORTS
	Counter32, Gauge32, Integer32, IpAddress, NOTIFICATION-TYPE,OBJECT-TYPE, TimeTicks, enterprises, MODULE-IDENTITY, OBJECT-IDENTITY
		FROM SNMPv2-SMI
	Ipv6Address
		FROM IPV6-TC
	 InetAddressType, InetAddress
		FROM INET-ADDRESS-MIB;

netScaler MODULE-IDENTITY
	LAST-UPDATED "201312050000Z"
	ORGANIZATION "Citrix Systems, Inc."
	CONTACT-INFO  "Citrix Technical Assistance Center
			Postal: Citrix Systems, Inc.
				851 West Cypress Creek Road
				Fort Lauderdale, Florida  33309
				United States
			Tel: +1-800-4-CITRIX (+1-800-424-8749)
			E-mail: customercare@citrix.com"
	DESCRIPTION "The enterprise specific MIB for Citrix Application Delivery Management."
	::= { enterprises 5951 }


sdxRoot OBJECT IDENTIFIER
	::= { netScaler 6}

sdxEventGroup OBJECT IDENTIFIER
::= { sdxRoot  1 }


systemGroup OBJECT IDENTIFIER
::= { sdxRoot  2 }

systemPlatform OBJECT-TYPE
	SYNTAX  OCTET STRING
	MAX-ACCESS  read-only
	STATUS  current
	DESCRIPTION
		"Platform"
	::= { systemGroup 1 }

systemProduct OBJECT-TYPE
	SYNTAX  OCTET STRING
	MAX-ACCESS  read-only
	STATUS  current
	DESCRIPTION
		"Product Name"
	::= { systemGroup 2 }

systemBuildNumber OBJECT-TYPE
	SYNTAX  OCTET STRING
	MAX-ACCESS  read-only
	STATUS  current
	DESCRIPTION
		"Build Number"
	::= { systemGroup 3 }

systemSvmIPAddressType OBJECT-TYPE
	SYNTAX  InetAddressType
	MAX-ACCESS  read-only
	STATUS  current
	DESCRIPTION
		"Type of systemSvmIPAddress"
	::= { systemGroup 4 }
systemSvmIPAddress OBJECT-TYPE
	SYNTAX  InetAddress
	MAX-ACCESS  read-only
	STATUS  current
	DESCRIPTION
		"Management Service IP Address"
	::= { systemGroup 5 }

systemXenIPAddressType OBJECT-TYPE
	SYNTAX  InetAddressType
	MAX-ACCESS  read-only
	STATUS  current
	DESCRIPTION
		"Type of systemXenIPAddress"
	::= { systemGroup 6 }
systemXenIPAddress OBJECT-TYPE
	SYNTAX  InetAddress
	MAX-ACCESS  read-only
	STATUS  current
	DESCRIPTION
		"XenServer IP Address"
	::= { systemGroup 7 }

systemNetmaskType OBJECT-TYPE
	SYNTAX  InetAddressType
	MAX-ACCESS  read-only
	STATUS  current
	DESCRIPTION
		"Type of systemNetmask"
	::= { systemGroup 8 }
systemNetmask OBJECT-TYPE
	SYNTAX  InetAddress
	MAX-ACCESS  read-only
	STATUS  current
	DESCRIPTION
		"Netmask"
	::= { systemGroup 9 }

systemGatewayType OBJECT-TYPE
	SYNTAX  InetAddressType
	MAX-ACCESS  read-only
	STATUS  current
	DESCRIPTION
		"Type of systemGateway"
	::= { systemGroup 10 }
systemGateway OBJECT-TYPE
	SYNTAX  InetAddress
	MAX-ACCESS  read-only
	STATUS  current
	DESCRIPTION
		"Gateway "
	::= { systemGroup 11 }

systemNetworkInterface OBJECT-TYPE
	SYNTAX  OCTET STRING
	MAX-ACCESS  read-only
	STATUS  current
	DESCRIPTION
		"Interface on which management needs to be enabled"
	::= { systemGroup 12 }

systemDns OBJECT-TYPE
	SYNTAX  OCTET STRING
	MAX-ACCESS  read-only
	STATUS  current
	DESCRIPTION
		"DNS Server"
	::= { systemGroup 13 }

systemSysId OBJECT-TYPE
	SYNTAX  OCTET STRING
	MAX-ACCESS  read-only
	STATUS  current
	DESCRIPTION
		"System Id"
	::= { systemGroup 15 }

systemSerial OBJECT-TYPE
	SYNTAX  OCTET STRING
	MAX-ACCESS  read-only
	STATUS  current
	DESCRIPTION
		"Serial Number"
	::= { systemGroup 16 }

systemCurrentTime OBJECT-TYPE
	SYNTAX  Integer32
	MAX-ACCESS  read-only
	STATUS  current
	DESCRIPTION
		"Current Time"
	::= { systemGroup 17 }

systemUptime OBJECT-TYPE
	SYNTAX  OCTET STRING
	MAX-ACCESS  read-only
	STATUS  current
	DESCRIPTION
		"Uptime"
	::= { systemGroup 18 }

systemBiosVersion OBJECT-TYPE
	SYNTAX  OCTET STRING
	MAX-ACCESS  read-only
	STATUS  current
	DESCRIPTION
		"BIOS Version"
	::= { systemGroup 19 }

systemMaxThroughput OBJECT-TYPE
	SYNTAX  OCTET STRING
	MAX-ACCESS  read-only
	STATUS  current
	DESCRIPTION
		"Maximum Throughput in Mbps"
	::= { systemGroup 20 }

systemAvailableThroughput OBJECT-TYPE
	SYNTAX  OCTET STRING
	MAX-ACCESS  read-only
	STATUS  current
	DESCRIPTION
		"Available Throughput in Mbps"
	::= { systemGroup 21 }

systemHostId OBJECT-TYPE
	SYNTAX  OCTET STRING
	MAX-ACCESS  read-only
	STATUS  current
	DESCRIPTION
		"Host Id"
	::= { systemGroup 22 }

systemCustomID OBJECT-TYPE
	SYNTAX  OCTET STRING
	MAX-ACCESS  read-only
	STATUS  current
	DESCRIPTION
		"Custom identification number for appliance"
	::= { systemGroup 23 }

systemCpuUsage OBJECT-TYPE
	SYNTAX  OCTET STRING
	MAX-ACCESS  read-only
	STATUS  current
	DESCRIPTION
		"CPU Usage (%)"
	::= { systemGroup 24 }

systemMemoryUsage OBJECT-TYPE
	SYNTAX  OCTET STRING
	MAX-ACCESS  read-only
	STATUS  current
	DESCRIPTION
		"Memory Usage (%)"
	::= { systemGroup 25 }

systemDiskUsage OBJECT-TYPE
	SYNTAX  OCTET STRING
	MAX-ACCESS  read-only
	STATUS  current
	DESCRIPTION
		"Disk Usage (%)"
	::= { systemGroup 26 }


sysHealthGroup OBJECT IDENTIFIER
::= { systemGroup  1000 }

hardwareResourceTable OBJECT-TYPE
	SYNTAX  SEQUENCE OF HardwareResourceEntry
	MAX-ACCESS  not-accessible
	STATUS  current
	DESCRIPTION
		"hardwareResourcetable"
	::= { sysHealthGroup 1 }

hardwareResourceEntry OBJECT-TYPE
	SYNTAX  HardwareResourceEntry
	MAX-ACCESS  not-accessible
	STATUS  current
	DESCRIPTION
		"..."
	INDEX { hardwareResourceName, hardwareResourceHostIPAddressType, hardwareResourceHostIPAddress }
	::= { hardwareResourceTable  1}

HardwareResourceEntry ::= SEQUENCE {
	hardwareResourceName OCTET STRING,
	hardwareResourceHostIPAddressType InetAddressType,
	hardwareResourceHostIPAddress InetAddress,
	hardwareResourceCurrentValue OCTET STRING,
	hardwareResourceExpectedValue OCTET STRING,
	hardwareResourceUnit OCTET STRING,
	hardwareResourceStatus OCTET STRING
}

hardwareResourceName OBJECT-TYPE
	SYNTAX  OCTET STRING
	MAX-ACCESS  read-only
	STATUS  current
	DESCRIPTION
		"Resource name"
	::= { hardwareResourceEntry 1 }

hardwareResourceHostIPAddressType OBJECT-TYPE
	SYNTAX  InetAddressType
	MAX-ACCESS  read-only
	STATUS  current
	DESCRIPTION
		"Type of hardwareResourceHostIPAddress"
	::= { hardwareResourceEntry 2 }
hardwareResourceHostIPAddress OBJECT-TYPE
	SYNTAX  InetAddress
	MAX-ACCESS  read-only
	STATUS  current
	DESCRIPTION
		"Host IP Address"
	::= { hardwareResourceEntry 3 }

hardwareResourceCurrentValue OBJECT-TYPE
	SYNTAX  OCTET STRING
	MAX-ACCESS  read-only
	STATUS  current
	DESCRIPTION
		"Current value of the resource"
	::= { hardwareResourceEntry 4 }

hardwareResourceExpectedValue OBJECT-TYPE
	SYNTAX  OCTET STRING
	MAX-ACCESS  read-only
	STATUS  current
	DESCRIPTION
		"Expected value of the resource"
	::= { hardwareResourceEntry 5 }

hardwareResourceUnit OBJECT-TYPE
	SYNTAX  OCTET STRING
	MAX-ACCESS  read-only
	STATUS  current
	DESCRIPTION
		"Measurement unit for the resource"
	::= { hardwareResourceEntry 6 }

hardwareResourceStatus OBJECT-TYPE
	SYNTAX  OCTET STRING
	MAX-ACCESS  read-only
	STATUS  current
	DESCRIPTION
		"Health status of the resource - OK/ERROR"
	::= { hardwareResourceEntry 7 }

softwareResourceTable OBJECT-TYPE
	SYNTAX  SEQUENCE OF SoftwareResourceEntry
	MAX-ACCESS  not-accessible
	STATUS  current
	DESCRIPTION
		"softwareResourcetable"
	::= { sysHealthGroup 2 }

softwareResourceEntry OBJECT-TYPE
	SYNTAX  SoftwareResourceEntry
	MAX-ACCESS  not-accessible
	STATUS  current
	DESCRIPTION
		"..."
	INDEX { softwareResourceName, softwareResourceHostIPAddressType, softwareResourceHostIPAddress }
	::= { softwareResourceTable  1}

SoftwareResourceEntry ::= SEQUENCE {
	softwareResourceName OCTET STRING,
	softwareResourceHostIPAddressType InetAddressType,
	softwareResourceHostIPAddress InetAddress,
	softwareResourceCurrentValue OCTET STRING,
	softwareResourceExpectedValue OCTET STRING,
	softwareResourceUnit OCTET STRING,
	softwareResourceStatus OCTET STRING
}

softwareResourceName OBJECT-TYPE
	SYNTAX  OCTET STRING
	MAX-ACCESS  read-only
	STATUS  current
	DESCRIPTION
		"Resource name"
	::= { softwareResourceEntry 1 }

softwareResourceHostIPAddressType OBJECT-TYPE
	SYNTAX  InetAddressType
	MAX-ACCESS  read-only
	STATUS  current
	DESCRIPTION
		"Type of softwareResourceHostIPAddress"
	::= { softwareResourceEntry 2 }
softwareResourceHostIPAddress OBJECT-TYPE
	SYNTAX  InetAddress
	MAX-ACCESS  read-only
	STATUS  current
	DESCRIPTION
		"Host IP Address"
	::= { softwareResourceEntry 3 }

softwareResourceCurrentValue OBJECT-TYPE
	SYNTAX  OCTET STRING
	MAX-ACCESS  read-only
	STATUS  current
	DESCRIPTION
		"Current value of the resource"
	::= { softwareResourceEntry 4 }

softwareResourceExpectedValue OBJECT-TYPE
	SYNTAX  OCTET STRING
	MAX-ACCESS  read-only
	STATUS  current
	DESCRIPTION
		"Expected value of the resource"
	::= { softwareResourceEntry 5 }

softwareResourceUnit OBJECT-TYPE
	SYNTAX  OCTET STRING
	MAX-ACCESS  read-only
	STATUS  current
	DESCRIPTION
		"Measurement unit for the resource"
	::= { softwareResourceEntry 6 }

softwareResourceStatus OBJECT-TYPE
	SYNTAX  OCTET STRING
	MAX-ACCESS  read-only
	STATUS  current
	DESCRIPTION
		"Health status of the resource - OK/ERROR"
	::= { softwareResourceEntry 7 }

diskTable OBJECT-TYPE
	SYNTAX  SEQUENCE OF DiskEntry
	MAX-ACCESS  not-accessible
	STATUS  current
	DESCRIPTION
		"disktable"
	::= { sysHealthGroup 3 }

diskEntry OBJECT-TYPE
	SYNTAX  DiskEntry
	MAX-ACCESS  not-accessible
	STATUS  current
	DESCRIPTION
		"..."
	INDEX { diskName, diskHostIPAddressType, diskHostIPAddress }
	::= { diskTable  1}

DiskEntry ::= SEQUENCE {
	diskName OCTET STRING,
	diskHostIPAddressType InetAddressType,
	diskHostIPAddress InetAddress,
	diskTransactionRate OCTET STRING,
	diskBlockReadRate OCTET STRING,
	diskBlockWriteRate OCTET STRING,
	diskTotalBlocksRead OCTET STRING,
	diskTotalBlocksWritten OCTET STRING,
	diskUtilized OCTET STRING,
	diskSize OCTET STRING,
	diskBayNumber OCTET STRING
}

diskName OBJECT-TYPE
	SYNTAX  OCTET STRING
	MAX-ACCESS  read-only
	STATUS  current
	DESCRIPTION
		"Name of the Disk"
	::= { diskEntry 1 }

diskHostIPAddressType OBJECT-TYPE
	SYNTAX  InetAddressType
	MAX-ACCESS  read-only
	STATUS  current
	DESCRIPTION
		"Type of diskHostIPAddress"
	::= { diskEntry 2 }
diskHostIPAddress OBJECT-TYPE
	SYNTAX  InetAddress
	MAX-ACCESS  read-only
	STATUS  current
	DESCRIPTION
		"Host IP Address"
	::= { diskEntry 3 }

diskTransactionRate OBJECT-TYPE
	SYNTAX  OCTET STRING
	MAX-ACCESS  read-only
	STATUS  current
	DESCRIPTION
		"Transactions per second"
	::= { diskEntry 4 }

diskBlockReadRate OBJECT-TYPE
	SYNTAX  OCTET STRING
	MAX-ACCESS  read-only
	STATUS  current
	DESCRIPTION
		"Blocks read per second"
	::= { diskEntry 5 }

diskBlockWriteRate OBJECT-TYPE
	SYNTAX  OCTET STRING
	MAX-ACCESS  read-only
	STATUS  current
	DESCRIPTION
		"Blocks written per second"
	::= { diskEntry 6 }

diskTotalBlocksRead OBJECT-TYPE
	SYNTAX  OCTET STRING
	MAX-ACCESS  read-only
	STATUS  current
	DESCRIPTION
		"Total blocks read"
	::= { diskEntry 7 }

diskTotalBlocksWritten OBJECT-TYPE
	SYNTAX  OCTET STRING
	MAX-ACCESS  read-only
	STATUS  current
	DESCRIPTION
		"Total blocks written"
	::= { diskEntry 8 }

diskUtilized OBJECT-TYPE
	SYNTAX  OCTET STRING
	MAX-ACCESS  read-only
	STATUS  current
	DESCRIPTION
		"Utilization of the disk (bytes)"
	::= { diskEntry 9 }

diskSize OBJECT-TYPE
	SYNTAX  OCTET STRING
	MAX-ACCESS  read-only
	STATUS  current
	DESCRIPTION
		"Size of the disk (bytes)"
	::= { diskEntry 10 }

diskBayNumber OBJECT-TYPE
	SYNTAX  OCTET STRING
	MAX-ACCESS  read-only
	STATUS  current
	DESCRIPTION
		"Bay number"
	::= { diskEntry 11 }

srTable OBJECT-TYPE
	SYNTAX  SEQUENCE OF SrEntry
	MAX-ACCESS  not-accessible
	STATUS  current
	DESCRIPTION
		"srtable"
	::= { sysHealthGroup 4 }

srEntry OBJECT-TYPE
	SYNTAX  SrEntry
	MAX-ACCESS  not-accessible
	STATUS  current
	DESCRIPTION
		"..."
	INDEX { srName, srBayNumber, srHostIPAddressType, srHostIPAddress }
	::= { srTable  1}

SrEntry ::= SEQUENCE {
	srName OCTET STRING,
	srBayNumber OCTET STRING,
	srHostIPAddressType InetAddressType,
	srHostIPAddress InetAddress,
	srUtilized OCTET STRING,
	srSize OCTET STRING,
	srStatus OCTET STRING
}

srName OBJECT-TYPE
	SYNTAX  OCTET STRING
	MAX-ACCESS  read-only
	STATUS  current
	DESCRIPTION
		"Name of the storage repository"
	::= { srEntry 1 }

srBayNumber OBJECT-TYPE
	SYNTAX  OCTET STRING
	MAX-ACCESS  read-only
	STATUS  current
	DESCRIPTION
		"Bay number"
	::= { srEntry 2 }

srHostIPAddressType OBJECT-TYPE
	SYNTAX  InetAddressType
	MAX-ACCESS  read-only
	STATUS  current
	DESCRIPTION
		"Type of srHostIPAddress"
	::= { srEntry 3 }
srHostIPAddress OBJECT-TYPE
	SYNTAX  InetAddress
	MAX-ACCESS  read-only
	STATUS  current
	DESCRIPTION
		"Host IP Address"
	::= { srEntry 4 }

srUtilized OBJECT-TYPE
	SYNTAX  OCTET STRING
	MAX-ACCESS  read-only
	STATUS  current
	DESCRIPTION
		"Physical utilization of the storage repository"
	::= { srEntry 5 }

srSize OBJECT-TYPE
	SYNTAX  OCTET STRING
	MAX-ACCESS  read-only
	STATUS  current
	DESCRIPTION
		"Physical size of the storage repository"
	::= { srEntry 6 }

srStatus OBJECT-TYPE
	SYNTAX  OCTET STRING
	MAX-ACCESS  read-only
	STATUS  current
	DESCRIPTION
		"Status of the storage repository - OK/ERROR"
	::= { srEntry 7 }

interfaceTable OBJECT-TYPE
	SYNTAX  SEQUENCE OF InterfaceEntry
	MAX-ACCESS  not-accessible
	STATUS  current
	DESCRIPTION
		"interfacetable"
	::= { sysHealthGroup 5 }

interfaceEntry OBJECT-TYPE
	SYNTAX  InterfaceEntry
	MAX-ACCESS  not-accessible
	STATUS  current
	DESCRIPTION
		"..."
	INDEX { interfaceMappedPort, interfaceHostIPAddressType, interfaceHostIPAddress }
	::= { interfaceTable  1}

InterfaceEntry ::= SEQUENCE {
	interfacePort OCTET STRING,
	interfaceHostIPAddressType InetAddressType,
	interfaceHostIPAddress InetAddress,
	interfaceState OCTET STRING,
	interfaceRxPackets OCTET STRING,
	interfaceTxPackets OCTET STRING,
	interfaceRxBytes OCTET STRING,
	interfaceTxBytes OCTET STRING,
	interfaceRxErrors OCTET STRING,
	interfaceTxErrors OCTET STRING,
	interfaceVfTotal Integer32,
	interfaceVfAssigned Integer32,
	interfaceMappedPort OCTET STRING
}

interfacePort OBJECT-TYPE
	SYNTAX  OCTET STRING
	MAX-ACCESS  read-only
	STATUS  current
	DESCRIPTION
		"Port Name Ex: 10/1"
	::= { interfaceEntry 1 }

interfaceHostIPAddressType OBJECT-TYPE
	SYNTAX  InetAddressType
	MAX-ACCESS  read-only
	STATUS  current
	DESCRIPTION
		"Type of interfaceHostIPAddress"
	::= { interfaceEntry 2 }
interfaceHostIPAddress OBJECT-TYPE
	SYNTAX  InetAddress
	MAX-ACCESS  read-only
	STATUS  current
	DESCRIPTION
		"Host IP Address"
	::= { interfaceEntry 3 }

interfaceState OBJECT-TYPE
	SYNTAX  OCTET STRING
	MAX-ACCESS  read-only
	STATUS  current
	DESCRIPTION
		"State of the Interface - UP/DOWN"
	::= { interfaceEntry 4 }

interfaceRxPackets OBJECT-TYPE
	SYNTAX  OCTET STRING
	MAX-ACCESS  read-only
	STATUS  current
	DESCRIPTION
		"Received packets"
	::= { interfaceEntry 5 }

interfaceTxPackets OBJECT-TYPE
	SYNTAX  OCTET STRING
	MAX-ACCESS  read-only
	STATUS  current
	DESCRIPTION
		"Transmitted packets"
	::= { interfaceEntry 6 }

interfaceRxBytes OBJECT-TYPE
	SYNTAX  OCTET STRING
	MAX-ACCESS  read-only
	STATUS  current
	DESCRIPTION
		"Received bytes"
	::= { interfaceEntry 7 }

interfaceTxBytes OBJECT-TYPE
	SYNTAX  OCTET STRING
	MAX-ACCESS  read-only
	STATUS  current
	DESCRIPTION
		"Transmitted bytes"
	::= { interfaceEntry 8 }

interfaceRxErrors OBJECT-TYPE
	SYNTAX  OCTET STRING
	MAX-ACCESS  read-only
	STATUS  current
	DESCRIPTION
		"Receiving errors"
	::= { interfaceEntry 9 }

interfaceTxErrors OBJECT-TYPE
	SYNTAX  OCTET STRING
	MAX-ACCESS  read-only
	STATUS  current
	DESCRIPTION
		"Transmission errors"
	::= { interfaceEntry 10 }

interfaceVfTotal OBJECT-TYPE
	SYNTAX  Integer32
	MAX-ACCESS  read-only
	STATUS  current
	DESCRIPTION
		"Total Virtual Functions"
	::= { interfaceEntry 11 }

interfaceVfAssigned OBJECT-TYPE
	SYNTAX  Integer32
	MAX-ACCESS  read-only
	STATUS  current
	DESCRIPTION
		"Assigned Virtual Functions"
	::= { interfaceEntry 12 }

interfaceMappedPort OBJECT-TYPE
	SYNTAX  OCTET STRING
	MAX-ACCESS  read-only
	STATUS  current
	DESCRIPTION
		"Mapped Port Name Ex: eth0"
	::= { interfaceEntry 13 }

healthMonitoringTable OBJECT-TYPE
	SYNTAX  SEQUENCE OF HealthMonitoringEntry
	MAX-ACCESS  not-accessible
	STATUS  current
	DESCRIPTION
		"healthMonitoringtable"
	::= { sysHealthGroup 6 }

healthMonitoringEntry OBJECT-TYPE
	SYNTAX  HealthMonitoringEntry
	MAX-ACCESS  not-accessible
	STATUS  current
	DESCRIPTION
		"..."
	INDEX { hmName, hmHostIPAddressType, hmHostIPAddress }
	::= { healthMonitoringTable  1}

HealthMonitoringEntry ::= SEQUENCE {
	hmName OCTET STRING,
	hmHostIPAddressType InetAddressType,
	hmHostIPAddress InetAddress,
	hmStatus OCTET STRING,
	hmNoOfFailures Integer32,
	hmUnit OCTET STRING,
	hmCurrentValue OCTET STRING
}

hmName OBJECT-TYPE
	SYNTAX  OCTET STRING
	MAX-ACCESS  read-only
	STATUS  current
	DESCRIPTION
		"IPMI Sensor Name"
	::= { healthMonitoringEntry 1 }

hmHostIPAddressType OBJECT-TYPE
	SYNTAX  InetAddressType
	MAX-ACCESS  read-only
	STATUS  current
	DESCRIPTION
		"Type of hmHostIPAddress"
	::= { healthMonitoringEntry 2 }
hmHostIPAddress OBJECT-TYPE
	SYNTAX  InetAddress
	MAX-ACCESS  read-only
	STATUS  current
	DESCRIPTION
		"Host IP Address"
	::= { healthMonitoringEntry 3 }

hmStatus OBJECT-TYPE
	SYNTAX  OCTET STRING
	MAX-ACCESS  read-only
	STATUS  current
	DESCRIPTION
		"IPMI Sensor Status - OK/ERROR/NA"
	::= { healthMonitoringEntry 4 }

hmNoOfFailures OBJECT-TYPE
	SYNTAX  Integer32
	MAX-ACCESS  read-only
	STATUS  current
	DESCRIPTION
		"Number of consecutive times the failure has been observed"
	::= { healthMonitoringEntry 5 }

hmUnit OBJECT-TYPE
	SYNTAX  OCTET STRING
	MAX-ACCESS  read-only
	STATUS  current
	DESCRIPTION
		"Measurement Unit"
	::= { healthMonitoringEntry 6 }

hmCurrentValue OBJECT-TYPE
	SYNTAX  OCTET STRING
	MAX-ACCESS  read-only
	STATUS  current
	DESCRIPTION
		"Current Value of the IPMI Sensor"
	::= { healthMonitoringEntry 7 }


deviceGroup OBJECT IDENTIFIER
::= { sdxRoot  3 }

xenTable OBJECT-TYPE
	SYNTAX  SEQUENCE OF XenEntry
	MAX-ACCESS  not-accessible
	STATUS  current
	DESCRIPTION
		"xentable"
	::= { deviceGroup 1 }

xenEntry OBJECT-TYPE
	SYNTAX  XenEntry
	MAX-ACCESS  not-accessible
	STATUS  current
	DESCRIPTION
		"..."
	INDEX { xenIpAddressType, xenIpAddress }
	::= { xenTable  1}

XenEntry ::= SEQUENCE {
	xenIpAddressType InetAddressType,
	xenIpAddress InetAddress,
	xenHostname OCTET STRING,
	xenDescription OCTET STRING,
	xenVersion OCTET STRING,
	xenUuid OCTET STRING,
	xenNumberOfCPU Integer32,
	xenCpuUsage OCTET STRING,
	xenMemoryTotal OCTET STRING,
	xenMemoryFree OCTET STRING,
	xenMemoryUsage OCTET STRING,
	xenTx OCTET STRING,
	xenRx OCTET STRING,
	xenUptime OCTET STRING,
	xenSslCoresTotal Integer32,
	xenIscsiIQN OCTET STRING,
	xenEdition OCTET STRING,
	xenExpiry OCTET STRING,
	xenProductCode OCTET STRING,
	xenSerialNumber OCTET STRING,
	xenVersionLong OCTET STRING,
	xenVersionShort OCTET STRING,
	xenBuildNumber OCTET STRING,
	xenBuildDate OCTET STRING,
	xenNumberOfCPUCores Integer32
}

xenIpAddressType OBJECT-TYPE
	SYNTAX  InetAddressType
	MAX-ACCESS  read-only
	STATUS  current
	DESCRIPTION
		"Type of xenIpAddress"
	::= { xenEntry 1 }
xenIpAddress OBJECT-TYPE
	SYNTAX  InetAddress
	MAX-ACCESS  read-only
	STATUS  current
	DESCRIPTION
		"IP Address for this managed device"
	::= { xenEntry 2 }

xenHostname OBJECT-TYPE
	SYNTAX  OCTET STRING
	MAX-ACCESS  read-only
	STATUS  current
	DESCRIPTION
		"Assign hostname to managed device, if this is not provided, name will be set as host name "
	::= { xenEntry 3 }

xenDescription OBJECT-TYPE
	SYNTAX  OCTET STRING
	MAX-ACCESS  read-only
	STATUS  current
	DESCRIPTION
		"Description of managed device"
	::= { xenEntry 4 }

xenVersion OBJECT-TYPE
	SYNTAX  OCTET STRING
	MAX-ACCESS  read-only
	STATUS  current
	DESCRIPTION
		"Device Version"
	::= { xenEntry 5 }

xenUuid OBJECT-TYPE
	SYNTAX  OCTET STRING
	MAX-ACCESS  read-only
	STATUS  current
	DESCRIPTION
		"UUID of host"
	::= { xenEntry 6 }

xenNumberOfCPU OBJECT-TYPE
	SYNTAX  Integer32
	MAX-ACCESS  read-only
	STATUS  current
	DESCRIPTION
		"Number of total CPU of host"
	::= { xenEntry 7 }

xenCpuUsage OBJECT-TYPE
	SYNTAX  OCTET STRING
	MAX-ACCESS  read-only
	STATUS  current
	DESCRIPTION
		"CPU Usage (%) of host"
	::= { xenEntry 8 }

xenMemoryTotal OBJECT-TYPE
	SYNTAX  OCTET STRING
	MAX-ACCESS  read-only
	STATUS  current
	DESCRIPTION
		"Total memory of host in MB"
	::= { xenEntry 9 }

xenMemoryFree OBJECT-TYPE
	SYNTAX  OCTET STRING
	MAX-ACCESS  read-only
	STATUS  current
	DESCRIPTION
		"Free memory available (MB) in host"
	::= { xenEntry 10 }

xenMemoryUsage OBJECT-TYPE
	SYNTAX  OCTET STRING
	MAX-ACCESS  read-only
	STATUS  current
	DESCRIPTION
		"Memory Usage (%) of host"
	::= { xenEntry 11 }

xenTx OBJECT-TYPE
	SYNTAX  OCTET STRING
	MAX-ACCESS  read-only
	STATUS  current
	DESCRIPTION
		"Out Throughput (Mbps) of host"
	::= { xenEntry 12 }

xenRx OBJECT-TYPE
	SYNTAX  OCTET STRING
	MAX-ACCESS  read-only
	STATUS  current
	DESCRIPTION
		"In Throughput (Mbps) of host"
	::= { xenEntry 13 }

xenUptime OBJECT-TYPE
	SYNTAX  OCTET STRING
	MAX-ACCESS  read-only
	STATUS  current
	DESCRIPTION
		"Uptime of device"
	::= { xenEntry 14 }

xenSslCoresTotal OBJECT-TYPE
	SYNTAX  Integer32
	MAX-ACCESS  read-only
	STATUS  current
	DESCRIPTION
		"Total SSL Cores available in host"
	::= { xenEntry 15 }

xenIscsiIQN OBJECT-TYPE
	SYNTAX  OCTET STRING
	MAX-ACCESS  read-only
	STATUS  current
	DESCRIPTION
		"iSCSI IQN"
	::= { xenEntry 16 }

xenEdition OBJECT-TYPE
	SYNTAX  OCTET STRING
	MAX-ACCESS  read-only
	STATUS  current
	DESCRIPTION
		"XenServer Edition"
	::= { xenEntry 17 }

xenExpiry OBJECT-TYPE
	SYNTAX  OCTET STRING
	MAX-ACCESS  read-only
	STATUS  current
	DESCRIPTION
		"XenServer Expiry"
	::= { xenEntry 18 }

xenProductCode OBJECT-TYPE
	SYNTAX  OCTET STRING
	MAX-ACCESS  read-only
	STATUS  current
	DESCRIPTION
		"XenServer Product Code"
	::= { xenEntry 19 }

xenSerialNumber OBJECT-TYPE
	SYNTAX  OCTET STRING
	MAX-ACCESS  read-only
	STATUS  current
	DESCRIPTION
		"Device Serial Number"
	::= { xenEntry 20 }

xenVersionLong OBJECT-TYPE
	SYNTAX  OCTET STRING
	MAX-ACCESS  read-only
	STATUS  current
	DESCRIPTION
		"XenServer Version (full text)"
	::= { xenEntry 21 }

xenVersionShort OBJECT-TYPE
	SYNTAX  OCTET STRING
	MAX-ACCESS  read-only
	STATUS  current
	DESCRIPTION
		"XenServer Version"
	::= { xenEntry 22 }

xenBuildNumber OBJECT-TYPE
	SYNTAX  OCTET STRING
	MAX-ACCESS  read-only
	STATUS  current
	DESCRIPTION
		"XenServer Build Number"
	::= { xenEntry 23 }

xenBuildDate OBJECT-TYPE
	SYNTAX  OCTET STRING
	MAX-ACCESS  read-only
	STATUS  current
	DESCRIPTION
		"XenServer Build Date"
	::= { xenEntry 24 }

xenNumberOfCPUCores OBJECT-TYPE
	SYNTAX  Integer32
	MAX-ACCESS  read-only
	STATUS  current
	DESCRIPTION
		"Number of total CPU cores of host"
	::= { xenEntry 25 }

netscalerTable OBJECT-TYPE
	SYNTAX  SEQUENCE OF NetscalerEntry
	MAX-ACCESS  not-accessible
	STATUS  current
	DESCRIPTION
		"netscalertable"
	::= { deviceGroup 2 }

netscalerEntry OBJECT-TYPE
	SYNTAX  NetscalerEntry
	MAX-ACCESS  not-accessible
	STATUS  current
	DESCRIPTION
		"..."
	INDEX { nsIpAddressType, nsIpAddress, nsHostIPAddressType, nsHostIPAddress }
	::= { netscalerTable  1}

NetscalerEntry ::= SEQUENCE {
	nsIpAddressType InetAddressType,
	nsIpAddress InetAddress,
	nsHostIPAddressType InetAddressType,
	nsHostIPAddress InetAddress,
	nsProfileName OCTET STRING,
	nsName OCTET STRING,
	nsNetmaskType InetAddressType,
	nsNetmask InetAddress,
	nsGatewayType InetAddressType,
	nsGateway InetAddress,
	nsHostname OCTET STRING,
	nsDescription OCTET STRING,
	nsVersion OCTET STRING,
	nsUuid OCTET STRING,
	nsInstanceState OCTET STRING,
	nsVirtualFunctions OCTET STRING,
	nsSslVirtualFunctions OCTET STRING,
	nsVmState OCTET STRING,
	nsNumberOfCPU Integer32,
	nsVmMemoryTotal OCTET STRING,
	nsUptime OCTET STRING,
	nsNumberOfSSLCores Integer32,
	nsCpuCoreMgmt OCTET STRING,
	nsCpuCorePE OCTET STRING,
	nsVmDescription OCTET STRING,
	nsThroughput OCTET STRING,
	nsNumberOfCores Integer32,
	nsNsCPUUsage OCTET STRING,
	nsNsMemoryUsage OCTET STRING,
	nsNsTx OCTET STRING,
	nsNsRx OCTET STRING,
	nsHttpReq OCTET STRING,
	nsUpsince OCTET STRING,
	nsLicense OCTET STRING,
	nsHaMasterState OCTET STRING,
	nsHaIPAddressType InetAddressType,
	nsHaIPAddress InetAddress,
	nsNodeState OCTET STRING,
	nsHaSync OCTET STRING,
	nsPps OCTET STRING,
	nsNumberOfSslCoresUp Integer32,
	nsIfOby1 OCTET STRING,
	nsIf0by2 OCTET STRING,
	nsNsVLANId Integer32,
	nsNsVLANTagged OCTET STRING,
	nsVlanType Integer32
}

nsIpAddressType OBJECT-TYPE
	SYNTAX  InetAddressType
	MAX-ACCESS  read-only
	STATUS  current
	DESCRIPTION
		"Type of nsIpAddress"
	::= { netscalerEntry 1 }
nsIpAddress OBJECT-TYPE
	SYNTAX  InetAddress
	MAX-ACCESS  read-only
	STATUS  current
	DESCRIPTION
		"IP Address for this managed device"
	::= { netscalerEntry 2 }

nsHostIPAddressType OBJECT-TYPE
	SYNTAX  InetAddressType
	MAX-ACCESS  read-only
	STATUS  current
	DESCRIPTION
		"Type of nsHostIPAddress"
	::= { netscalerEntry 3 }
nsHostIPAddress OBJECT-TYPE
	SYNTAX  InetAddress
	MAX-ACCESS  read-only
	STATUS  current
	DESCRIPTION
		"Host IPAddress where VM is provisioned"
	::= { netscalerEntry 4 }

nsProfileName OBJECT-TYPE
	SYNTAX  OCTET STRING
	MAX-ACCESS  read-only
	STATUS  current
	DESCRIPTION
		"Device Profile Name that is attached with this managed device"
	::= { netscalerEntry 5 }

nsName OBJECT-TYPE
	SYNTAX  OCTET STRING
	MAX-ACCESS  read-only
	STATUS  current
	DESCRIPTION
		"Name of managed device"
	::= { netscalerEntry 6 }

nsNetmaskType OBJECT-TYPE
	SYNTAX  InetAddressType
	MAX-ACCESS  read-only
	STATUS  current
	DESCRIPTION
		"Type of nsNetmask"
	::= { netscalerEntry 7 }
nsNetmask OBJECT-TYPE
	SYNTAX  InetAddress
	MAX-ACCESS  read-only
	STATUS  current
	DESCRIPTION
		"Netmask of managed device"
	::= { netscalerEntry 8 }

nsGatewayType OBJECT-TYPE
	SYNTAX  InetAddressType
	MAX-ACCESS  read-only
	STATUS  current
	DESCRIPTION
		"Type of nsGateway"
	::= { netscalerEntry 9 }
nsGateway OBJECT-TYPE
	SYNTAX  InetAddress
	MAX-ACCESS  read-only
	STATUS  current
	DESCRIPTION
		"Default Gateway of managed device"
	::= { netscalerEntry 10 }

nsHostname OBJECT-TYPE
	SYNTAX  OCTET STRING
	MAX-ACCESS  read-only
	STATUS  current
	DESCRIPTION
		"Assign hostname to managed device, if this is not provided, name will be set as host name "
	::= { netscalerEntry 11 }

nsDescription OBJECT-TYPE
	SYNTAX  OCTET STRING
	MAX-ACCESS  read-only
	STATUS  current
	DESCRIPTION
		"Description of managed device"
	::= { netscalerEntry 12 }

nsVersion OBJECT-TYPE
	SYNTAX  OCTET STRING
	MAX-ACCESS  read-only
	STATUS  current
	DESCRIPTION
		"Device Version"
	::= { netscalerEntry 13 }

nsUuid OBJECT-TYPE
	SYNTAX  OCTET STRING
	MAX-ACCESS  read-only
	STATUS  current
	DESCRIPTION
		"UUID of VM Instance generated by Hypervisor"
	::= { netscalerEntry 14 }

nsInstanceState OBJECT-TYPE
	SYNTAX  OCTET STRING
	MAX-ACCESS  read-only
	STATUS  current
	DESCRIPTION
		"State of device, UP only if device accessible"
	::= { netscalerEntry 15 }

nsVirtualFunctions OBJECT-TYPE
	SYNTAX  OCTET STRING
	MAX-ACCESS  read-only
	STATUS  current
	DESCRIPTION
		"Virtual Functions assigned to VM Instance depending on SDX platform"
	::= { netscalerEntry 16 }

nsSslVirtualFunctions OBJECT-TYPE
	SYNTAX  OCTET STRING
	MAX-ACCESS  read-only
	STATUS  current
	DESCRIPTION
		"SSL Virtual Functions assigned to VM Instance"
	::= { netscalerEntry 17 }

nsVmState OBJECT-TYPE
	SYNTAX  OCTET STRING
	MAX-ACCESS  read-only
	STATUS  current
	DESCRIPTION
		"State of Virtual Machine (Running | Halted)"
	::= { netscalerEntry 18 }

nsNumberOfCPU OBJECT-TYPE
	SYNTAX  Integer32
	MAX-ACCESS  read-only
	STATUS  current
	DESCRIPTION
		"Number of CPU that is assigned to VM Instance"
	::= { netscalerEntry 19 }

nsVmMemoryTotal OBJECT-TYPE
	SYNTAX  OCTET STRING
	MAX-ACCESS  read-only
	STATUS  current
	DESCRIPTION
		"Total Memory of VM Instance in MB. 2048MB, 5120MB"
	::= { netscalerEntry 21 }

nsUptime OBJECT-TYPE
	SYNTAX  OCTET STRING
	MAX-ACCESS  read-only
	STATUS  current
	DESCRIPTION
		"Uptime of device"
	::= { netscalerEntry 26 }

nsNumberOfSSLCores OBJECT-TYPE
	SYNTAX  Integer32
	MAX-ACCESS  read-only
	STATUS  current
	DESCRIPTION
		"Assign number of ssl virtual functions to VM Instance"
	::= { netscalerEntry 27 }

nsCpuCoreMgmt OBJECT-TYPE
	SYNTAX  OCTET STRING
	MAX-ACCESS  read-only
	STATUS  current
	DESCRIPTION
		"Management CPU cores assigned to VM Instance"
	::= { netscalerEntry 28 }

nsCpuCorePE OBJECT-TYPE
	SYNTAX  OCTET STRING
	MAX-ACCESS  read-only
	STATUS  current
	DESCRIPTION
		"Packet Engine cores assigned to VM Instance"
	::= { netscalerEntry 29 }

nsVmDescription OBJECT-TYPE
	SYNTAX  OCTET STRING
	MAX-ACCESS  read-only
	STATUS  current
	DESCRIPTION
		"Description of the VM instance"
	::= { netscalerEntry 30 }

nsThroughput OBJECT-TYPE
	SYNTAX  OCTET STRING
	MAX-ACCESS  read-only
	STATUS  current
	DESCRIPTION
		"Assign throughput in Mbps to VM Instance"
	::= { netscalerEntry 31 }

nsNumberOfCores OBJECT-TYPE
	SYNTAX  Integer32
	MAX-ACCESS  read-only
	STATUS  current
	DESCRIPTION
		"Number of cores that are assigned to VM Instance"
	::= { netscalerEntry 32 }

nsNsCPUUsage OBJECT-TYPE
	SYNTAX  OCTET STRING
	MAX-ACCESS  read-only
	STATUS  current
	DESCRIPTION
		"CPU Usage (%) of Citrix ADC Instance"
	::= { netscalerEntry 33 }

nsNsMemoryUsage OBJECT-TYPE
	SYNTAX  OCTET STRING
	MAX-ACCESS  read-only
	STATUS  current
	DESCRIPTION
		"Memory Usage (%)"
	::= { netscalerEntry 35 }

nsNsTx OBJECT-TYPE
	SYNTAX  OCTET STRING
	MAX-ACCESS  read-only
	STATUS  current
	DESCRIPTION
		"Out Throughput of Citrix ADC Instance in Mbps"
	::= { netscalerEntry 36 }

nsNsRx OBJECT-TYPE
	SYNTAX  OCTET STRING
	MAX-ACCESS  read-only
	STATUS  current
	DESCRIPTION
		"In Throughput of Citrix ADC Instance in Mbps"
	::= { netscalerEntry 37 }

nsHttpReq OBJECT-TYPE
	SYNTAX  OCTET STRING
	MAX-ACCESS  read-only
	STATUS  current
	DESCRIPTION
		"HTTP Requests/second"
	::= { netscalerEntry 38 }

nsUpsince OBJECT-TYPE
	SYNTAX  OCTET STRING
	MAX-ACCESS  read-only
	STATUS  current
	DESCRIPTION
		"Upsince of managed device"
	::= { netscalerEntry 39 }

nsLicense OBJECT-TYPE
	SYNTAX  OCTET STRING
	MAX-ACCESS  read-only
	STATUS  current
	DESCRIPTION
		"Feature License for Citrix ADC Instance, needs to be set while provisioning (standard, enterprise, platinum)"
	::= { netscalerEntry 40 }

nsHaMasterState OBJECT-TYPE
	SYNTAX  OCTET STRING
	MAX-ACCESS  read-only
	STATUS  current
	DESCRIPTION
		"Master State (Primary/Secondary)"
	::= { netscalerEntry 41 }

nsHaIPAddressType OBJECT-TYPE
	SYNTAX  InetAddressType
	MAX-ACCESS  read-only
	STATUS  current
	DESCRIPTION
		"Type of nsHaIPAddress"
	::= { netscalerEntry 42 }
nsHaIPAddress OBJECT-TYPE
	SYNTAX  InetAddress
	MAX-ACCESS  read-only
	STATUS  current
	DESCRIPTION
		"Peer IP Address"
	::= { netscalerEntry 43 }

nsNodeState OBJECT-TYPE
	SYNTAX  OCTET STRING
	MAX-ACCESS  read-only
	STATUS  current
	DESCRIPTION
		"Node State of Citrix ADC Instance"
	::= { netscalerEntry 44 }

nsHaSync OBJECT-TYPE
	SYNTAX  OCTET STRING
	MAX-ACCESS  read-only
	STATUS  current
	DESCRIPTION
		"HA Synchronization State"
	::= { netscalerEntry 45 }

nsPps OBJECT-TYPE
	SYNTAX  OCTET STRING
	MAX-ACCESS  read-only
	STATUS  current
	DESCRIPTION
		"Assign packets per seconds to Citrix ADC Instance"
	::= { netscalerEntry 46 }

nsNumberOfSslCoresUp OBJECT-TYPE
	SYNTAX  Integer32
	MAX-ACCESS  read-only
	STATUS  current
	DESCRIPTION
		"Number of SSL Cores Up"
	::= { netscalerEntry 47 }

nsIfOby1 OBJECT-TYPE
	SYNTAX  OCTET STRING
	MAX-ACCESS  read-only
	STATUS  current
	DESCRIPTION
		"Network 0/1 on VM Instance"
	::= { netscalerEntry 48 }

nsIf0by2 OBJECT-TYPE
	SYNTAX  OCTET STRING
	MAX-ACCESS  read-only
	STATUS  current
	DESCRIPTION
		"Network 0/2 on VM Instance"
	::= { netscalerEntry 49 }

nsNsVLANId OBJECT-TYPE
	SYNTAX  Integer32
	MAX-ACCESS  read-only
	STATUS  current
	DESCRIPTION
		"VLAN Id"
	::= { netscalerEntry 50 }

nsNsVLANTagged OBJECT-TYPE
	SYNTAX  OCTET STRING
	MAX-ACCESS  read-only
	STATUS  current
	DESCRIPTION
		"NSVLAN Tagged"
	::= { netscalerEntry 51 }

nsVlanType OBJECT-TYPE
	SYNTAX  Integer32
	MAX-ACCESS  read-only
	STATUS  current
	DESCRIPTION
		"VLAN Type, Citrix ADC or L2 VLAN"
	::= { netscalerEntry 52 }

netscalerSDWANInstanceTable OBJECT-TYPE
	SYNTAX  SEQUENCE OF NetscalerSDWANInstanceEntry
	MAX-ACCESS  not-accessible
	STATUS  current
	DESCRIPTION
		"netscalerSDWANInstancetable"
	::= { deviceGroup 3 }

netscalerSDWANInstanceEntry OBJECT-TYPE
	SYNTAX  NetscalerSDWANInstanceEntry
	MAX-ACCESS  not-accessible
	STATUS  current
	DESCRIPTION
		"..."
	INDEX { cbIpAddressType, cbIpAddress, cbHostIPAddressType, cbHostIPAddress }
	::= { netscalerSDWANInstanceTable  1}

NetscalerSDWANInstanceEntry ::= SEQUENCE {
	cbIpAddressType InetAddressType,
	cbIpAddress InetAddress,
	cbHostIPAddressType InetAddressType,
	cbHostIPAddress InetAddress,
	cbProfileName OCTET STRING,
	cbName OCTET STRING,
	cbNetmaskType InetAddressType,
	cbNetmask InetAddress,
	cbGatewayType InetAddressType,
	cbGateway InetAddress,
	cbHostname OCTET STRING,
	cbDescription OCTET STRING,
	cbVersion OCTET STRING,
	cbInstanceState OCTET STRING,
	cbUuid OCTET STRING,
	cbVirtualFunctions OCTET STRING,
	cbVmState OCTET STRING,
	cbNumberOfCPU Integer32,
	cbVmCPUUsage OCTET STRING,
	cbVmMemoryTotal OCTET STRING,
	cbVmMemoryFree OCTET STRING,
	cbVmMemoryUsage OCTET STRING,
	cbUptime OCTET STRING,
	cbDiskAllocation OCTET STRING,
	cbAPAIPADDRESSType InetAddressType,
	cbAPAIPADDRESS InetAddress,
	cbAPANetMaskType InetAddressType,
	cbAPANetMask InetAddress,
	cbAPAGatewayType InetAddressType,
	cbAPAGateway InetAddress,
	cbPluginIPADDRESSType InetAddressType,
	cbPluginIPADDRESS InetAddress,
	cbMgmtIPAddressType InetAddressType,
	cbMgmtIPAddress InetAddress
}

cbIpAddressType OBJECT-TYPE
	SYNTAX  InetAddressType
	MAX-ACCESS  read-only
	STATUS  current
	DESCRIPTION
		"Type of cbIpAddress"
	::= { netscalerSDWANInstanceEntry 1 }
cbIpAddress OBJECT-TYPE
	SYNTAX  InetAddress
	MAX-ACCESS  read-only
	STATUS  current
	DESCRIPTION
		"IP Address for this managed device"
	::= { netscalerSDWANInstanceEntry 2 }

cbHostIPAddressType OBJECT-TYPE
	SYNTAX  InetAddressType
	MAX-ACCESS  read-only
	STATUS  current
	DESCRIPTION
		"Type of cbHostIPAddress"
	::= { netscalerSDWANInstanceEntry 3 }
cbHostIPAddress OBJECT-TYPE
	SYNTAX  InetAddress
	MAX-ACCESS  read-only
	STATUS  current
	DESCRIPTION
		"Host IPAddress where VM is provisioned"
	::= { netscalerSDWANInstanceEntry 4 }

cbProfileName OBJECT-TYPE
	SYNTAX  OCTET STRING
	MAX-ACCESS  read-only
	STATUS  current
	DESCRIPTION
		"Device Profile Name that is attached with this managed device"
	::= { netscalerSDWANInstanceEntry 5 }

cbName OBJECT-TYPE
	SYNTAX  OCTET STRING
	MAX-ACCESS  read-only
	STATUS  current
	DESCRIPTION
		"Name of managed device"
	::= { netscalerSDWANInstanceEntry 6 }

cbNetmaskType OBJECT-TYPE
	SYNTAX  InetAddressType
	MAX-ACCESS  read-only
	STATUS  current
	DESCRIPTION
		"Type of cbNetmask"
	::= { netscalerSDWANInstanceEntry 7 }
cbNetmask OBJECT-TYPE
	SYNTAX  InetAddress
	MAX-ACCESS  read-only
	STATUS  current
	DESCRIPTION
		"Netmask of managed device"
	::= { netscalerSDWANInstanceEntry 8 }

cbGatewayType OBJECT-TYPE
	SYNTAX  InetAddressType
	MAX-ACCESS  read-only
	STATUS  current
	DESCRIPTION
		"Type of cbGateway"
	::= { netscalerSDWANInstanceEntry 9 }
cbGateway OBJECT-TYPE
	SYNTAX  InetAddress
	MAX-ACCESS  read-only
	STATUS  current
	DESCRIPTION
		"Default Gateway of managed device"
	::= { netscalerSDWANInstanceEntry 10 }

cbHostname OBJECT-TYPE
	SYNTAX  OCTET STRING
	MAX-ACCESS  read-only
	STATUS  current
	DESCRIPTION
		"Assign hostname to managed device, if this is not provided, name will be set as host name "
	::= { netscalerSDWANInstanceEntry 11 }

cbDescription OBJECT-TYPE
	SYNTAX  OCTET STRING
	MAX-ACCESS  read-only
	STATUS  current
	DESCRIPTION
		"Description of managed device"
	::= { netscalerSDWANInstanceEntry 12 }

cbVersion OBJECT-TYPE
	SYNTAX  OCTET STRING
	MAX-ACCESS  read-only
	STATUS  current
	DESCRIPTION
		"Device Version"
	::= { netscalerSDWANInstanceEntry 13 }

cbInstanceState OBJECT-TYPE
	SYNTAX  OCTET STRING
	MAX-ACCESS  read-only
	STATUS  current
	DESCRIPTION
		"State of device, UP only if device accessible"
	::= { netscalerSDWANInstanceEntry 14 }

cbUuid OBJECT-TYPE
	SYNTAX  OCTET STRING
	MAX-ACCESS  read-only
	STATUS  current
	DESCRIPTION
		"UUID of VM Instance generated by Hypervisor"
	::= { netscalerSDWANInstanceEntry 15 }

cbVirtualFunctions OBJECT-TYPE
	SYNTAX  OCTET STRING
	MAX-ACCESS  read-only
	STATUS  current
	DESCRIPTION
		"Virtual Functions assigned to VM Instance depending on SDX platform"
	::= { netscalerSDWANInstanceEntry 16 }

cbVmState OBJECT-TYPE
	SYNTAX  OCTET STRING
	MAX-ACCESS  read-only
	STATUS  current
	DESCRIPTION
		"State of Virtual Machine (Running | Halted)"
	::= { netscalerSDWANInstanceEntry 17 }

cbNumberOfCPU OBJECT-TYPE
	SYNTAX  Integer32
	MAX-ACCESS  read-only
	STATUS  current
	DESCRIPTION
		"Number of CPU that is assigned to VM Instance"
	::= { netscalerSDWANInstanceEntry 18 }

cbVmCPUUsage OBJECT-TYPE
	SYNTAX  OCTET STRING
	MAX-ACCESS  read-only
	STATUS  current
	DESCRIPTION
		"CPU Usage (%) of VM Instance"
	::= { netscalerSDWANInstanceEntry 19 }

cbVmMemoryTotal OBJECT-TYPE
	SYNTAX  OCTET STRING
	MAX-ACCESS  read-only
	STATUS  current
	DESCRIPTION
		"Total Memory of VM Instance in MB. 2048MB, 5120MB"
	::= { netscalerSDWANInstanceEntry 20 }

cbVmMemoryFree OBJECT-TYPE
	SYNTAX  OCTET STRING
	MAX-ACCESS  read-only
	STATUS  current
	DESCRIPTION
		"Free Memory (MB) available in VM Instance"
	::= { netscalerSDWANInstanceEntry 21 }

cbVmMemoryUsage OBJECT-TYPE
	SYNTAX  OCTET STRING
	MAX-ACCESS  read-only
	STATUS  current
	DESCRIPTION
		"Memory Usage (%) of VM Instance"
	::= { netscalerSDWANInstanceEntry 22 }

cbUptime OBJECT-TYPE
	SYNTAX  OCTET STRING
	MAX-ACCESS  read-only
	STATUS  current
	DESCRIPTION
		"Uptime of device"
	::= { netscalerSDWANInstanceEntry 25 }

cbDiskAllocation OBJECT-TYPE
	SYNTAX  OCTET STRING
	MAX-ACCESS  read-only
	STATUS  current
	DESCRIPTION
		"Disk allocation for VM Instance"
	::= { netscalerSDWANInstanceEntry 30 }

cbAPAIPADDRESSType OBJECT-TYPE
	SYNTAX  InetAddressType
	MAX-ACCESS  read-only
	STATUS  current
	DESCRIPTION
		"Type of cbAPAIPADDRESS"
	::= { netscalerSDWANInstanceEntry 47 }
cbAPAIPADDRESS OBJECT-TYPE
	SYNTAX  InetAddress
	MAX-ACCESS  read-only
	STATUS  current
	DESCRIPTION
		"aPA IP Address"
	::= { netscalerSDWANInstanceEntry 48 }

cbAPANetMaskType OBJECT-TYPE
	SYNTAX  InetAddressType
	MAX-ACCESS  read-only
	STATUS  current
	DESCRIPTION
		"Type of cbAPANetMask"
	::= { netscalerSDWANInstanceEntry 49 }
cbAPANetMask OBJECT-TYPE
	SYNTAX  InetAddress
	MAX-ACCESS  read-only
	STATUS  current
	DESCRIPTION
		"aPA Netmask"
	::= { netscalerSDWANInstanceEntry 50 }

cbAPAGatewayType OBJECT-TYPE
	SYNTAX  InetAddressType
	MAX-ACCESS  read-only
	STATUS  current
	DESCRIPTION
		"Type of cbAPAGateway"
	::= { netscalerSDWANInstanceEntry 51 }
cbAPAGateway OBJECT-TYPE
	SYNTAX  InetAddress
	MAX-ACCESS  read-only
	STATUS  current
	DESCRIPTION
		"aPA Gateway"
	::= { netscalerSDWANInstanceEntry 52 }

cbPluginIPADDRESSType OBJECT-TYPE
	SYNTAX  InetAddressType
	MAX-ACCESS  read-only
	STATUS  current
	DESCRIPTION
		"Type of cbPluginIPADDRESS"
	::= { netscalerSDWANInstanceEntry 53 }
cbPluginIPADDRESS OBJECT-TYPE
	SYNTAX  InetAddress
	MAX-ACCESS  read-only
	STATUS  current
	DESCRIPTION
		"Plugin IP Address"
	::= { netscalerSDWANInstanceEntry 54 }

cbMgmtIPAddressType OBJECT-TYPE
	SYNTAX  InetAddressType
	MAX-ACCESS  read-only
	STATUS  current
	DESCRIPTION
		"Type of cbMgmtIPAddress"
	::= { netscalerSDWANInstanceEntry 57 }
cbMgmtIPAddress OBJECT-TYPE
	SYNTAX  InetAddress
	MAX-ACCESS  read-only
	STATUS  current
	DESCRIPTION
		"Management IP Address for this Managed Device"
	::= { netscalerSDWANInstanceEntry 58 }

netscalerSDWANAcceleratorTable OBJECT-TYPE
	SYNTAX  SEQUENCE OF NetscalerSDWANAcceleratorEntry
	MAX-ACCESS  not-accessible
	STATUS  current
	DESCRIPTION
		"netscalerSDWANAcceleratortable"
	::= { deviceGroup 4 }

netscalerSDWANAcceleratorEntry OBJECT-TYPE
	SYNTAX  NetscalerSDWANAcceleratorEntry
	MAX-ACCESS  not-accessible
	STATUS  current
	DESCRIPTION
		"..."
	INDEX { cbAcceleratorIpAddressType, cbAcceleratorIpAddress, cbAcceleratorHostIPAddressType, cbAcceleratorHostIPAddress }
	::= { netscalerSDWANAcceleratorTable  1}

NetscalerSDWANAcceleratorEntry ::= SEQUENCE {
	cbAcceleratorIpAddressType InetAddressType,
	cbAcceleratorIpAddress InetAddress,
	cbAcceleratorHostIPAddressType InetAddressType,
	cbAcceleratorHostIPAddress InetAddress,
	cbAcceleratorProfileName OCTET STRING,
	cbAcceleratorName OCTET STRING,
	cbAcceleratorNetmaskType InetAddressType,
	cbAcceleratorNetmask InetAddress,
	cbAcceleratorGatewayType InetAddressType,
	cbAcceleratorGateway InetAddress,
	cbAcceleratorHostname OCTET STRING,
	cbAcceleratorDescription OCTET STRING,
	cbAcceleratorVersion OCTET STRING,
	cbAcceleratorInstanceState OCTET STRING,
	cbAcceleratorUuid OCTET STRING,
	cbAcceleratorVmState OCTET STRING,
	cbAcceleratorNumberOfCPU Integer32,
	cbAcceleratorVmCPUUsage OCTET STRING,
	cbAcceleratorVmMemoryTotal OCTET STRING,
	cbAcceleratorVmMemoryFree OCTET STRING,
	cbAcceleratorVmMemoryUsage OCTET STRING,
	cbAcceleratorUptime OCTET STRING,
	cbAcceleratorIpList OCTET STRING,
	cbAcceleratorMgmtIPAddressType InetAddressType,
	cbAcceleratorMgmtIPAddress InetAddress
}

cbAcceleratorIpAddressType OBJECT-TYPE
	SYNTAX  InetAddressType
	MAX-ACCESS  read-only
	STATUS  current
	DESCRIPTION
		"Type of cbAcceleratorIpAddress"
	::= { netscalerSDWANAcceleratorEntry 1 }
cbAcceleratorIpAddress OBJECT-TYPE
	SYNTAX  InetAddress
	MAX-ACCESS  read-only
	STATUS  current
	DESCRIPTION
		"IP Address for this managed device"
	::= { netscalerSDWANAcceleratorEntry 2 }

cbAcceleratorHostIPAddressType OBJECT-TYPE
	SYNTAX  InetAddressType
	MAX-ACCESS  read-only
	STATUS  current
	DESCRIPTION
		"Type of cbAcceleratorHostIPAddress"
	::= { netscalerSDWANAcceleratorEntry 3 }
cbAcceleratorHostIPAddress OBJECT-TYPE
	SYNTAX  InetAddress
	MAX-ACCESS  read-only
	STATUS  current
	DESCRIPTION
		"Host IPAddress where VM is provisioned"
	::= { netscalerSDWANAcceleratorEntry 4 }

cbAcceleratorProfileName OBJECT-TYPE
	SYNTAX  OCTET STRING
	MAX-ACCESS  read-only
	STATUS  current
	DESCRIPTION
		"Device Profile Name that is attached with this managed device"
	::= { netscalerSDWANAcceleratorEntry 5 }

cbAcceleratorName OBJECT-TYPE
	SYNTAX  OCTET STRING
	MAX-ACCESS  read-only
	STATUS  current
	DESCRIPTION
		"Name of managed device"
	::= { netscalerSDWANAcceleratorEntry 6 }

cbAcceleratorNetmaskType OBJECT-TYPE
	SYNTAX  InetAddressType
	MAX-ACCESS  read-only
	STATUS  current
	DESCRIPTION
		"Type of cbAcceleratorNetmask"
	::= { netscalerSDWANAcceleratorEntry 7 }
cbAcceleratorNetmask OBJECT-TYPE
	SYNTAX  InetAddress
	MAX-ACCESS  read-only
	STATUS  current
	DESCRIPTION
		"Netmask of managed device"
	::= { netscalerSDWANAcceleratorEntry 8 }

cbAcceleratorGatewayType OBJECT-TYPE
	SYNTAX  InetAddressType
	MAX-ACCESS  read-only
	STATUS  current
	DESCRIPTION
		"Type of cbAcceleratorGateway"
	::= { netscalerSDWANAcceleratorEntry 9 }
cbAcceleratorGateway OBJECT-TYPE
	SYNTAX  InetAddress
	MAX-ACCESS  read-only
	STATUS  current
	DESCRIPTION
		"Default Gateway of managed device"
	::= { netscalerSDWANAcceleratorEntry 10 }

cbAcceleratorHostname OBJECT-TYPE
	SYNTAX  OCTET STRING
	MAX-ACCESS  read-only
	STATUS  current
	DESCRIPTION
		"Assign hostname to managed device, if this is not provided, name will be set as host name "
	::= { netscalerSDWANAcceleratorEntry 11 }

cbAcceleratorDescription OBJECT-TYPE
	SYNTAX  OCTET STRING
	MAX-ACCESS  read-only
	STATUS  current
	DESCRIPTION
		"Description of managed device"
	::= { netscalerSDWANAcceleratorEntry 12 }

cbAcceleratorVersion OBJECT-TYPE
	SYNTAX  OCTET STRING
	MAX-ACCESS  read-only
	STATUS  current
	DESCRIPTION
		"Device Version"
	::= { netscalerSDWANAcceleratorEntry 13 }

cbAcceleratorInstanceState OBJECT-TYPE
	SYNTAX  OCTET STRING
	MAX-ACCESS  read-only
	STATUS  current
	DESCRIPTION
		"State of device, UP only if device accessible"
	::= { netscalerSDWANAcceleratorEntry 14 }

cbAcceleratorUuid OBJECT-TYPE
	SYNTAX  OCTET STRING
	MAX-ACCESS  read-only
	STATUS  current
	DESCRIPTION
		"UUID of VM Instance generated by Hypervisor"
	::= { netscalerSDWANAcceleratorEntry 15 }

cbAcceleratorVmState OBJECT-TYPE
	SYNTAX  OCTET STRING
	MAX-ACCESS  read-only
	STATUS  current
	DESCRIPTION
		"State of Virtual Machine (Running | Halted)"
	::= { netscalerSDWANAcceleratorEntry 16 }

cbAcceleratorNumberOfCPU OBJECT-TYPE
	SYNTAX  Integer32
	MAX-ACCESS  read-only
	STATUS  current
	DESCRIPTION
		"Number of CPU that is assigned to VM Instance"
	::= { netscalerSDWANAcceleratorEntry 17 }

cbAcceleratorVmCPUUsage OBJECT-TYPE
	SYNTAX  OCTET STRING
	MAX-ACCESS  read-only
	STATUS  current
	DESCRIPTION
		"CPU Usage (%) of VM Instance"
	::= { netscalerSDWANAcceleratorEntry 18 }

cbAcceleratorVmMemoryTotal OBJECT-TYPE
	SYNTAX  OCTET STRING
	MAX-ACCESS  read-only
	STATUS  current
	DESCRIPTION
		"Total Memory of VM Instance in MB. 2048MB, 5120MB"
	::= { netscalerSDWANAcceleratorEntry 19 }

cbAcceleratorVmMemoryFree OBJECT-TYPE
	SYNTAX  OCTET STRING
	MAX-ACCESS  read-only
	STATUS  current
	DESCRIPTION
		"Free Memory (MB) available in VM Instance"
	::= { netscalerSDWANAcceleratorEntry 20 }

cbAcceleratorVmMemoryUsage OBJECT-TYPE
	SYNTAX  OCTET STRING
	MAX-ACCESS  read-only
	STATUS  current
	DESCRIPTION
		"Memory Usage (%) of VM Instance"
	::= { netscalerSDWANAcceleratorEntry 21 }

cbAcceleratorUptime OBJECT-TYPE
	SYNTAX  OCTET STRING
	MAX-ACCESS  read-only
	STATUS  current
	DESCRIPTION
		"Uptime of device"
	::= { netscalerSDWANAcceleratorEntry 24 }

cbAcceleratorIpList OBJECT-TYPE
	SYNTAX  OCTET STRING
	MAX-ACCESS  read-only
	STATUS  current
	DESCRIPTION
		"Specify the list of Citrix SD-WAN IPs for which this device will act as a Citrix SD-WAN Accelerator."
	::= { netscalerSDWANAcceleratorEntry 31 }

cbAcceleratorMgmtIPAddressType OBJECT-TYPE
	SYNTAX  InetAddressType
	MAX-ACCESS  read-only
	STATUS  current
	DESCRIPTION
		"Type of cbAcceleratorMgmtIPAddress"
	::= { netscalerSDWANAcceleratorEntry 38 }
cbAcceleratorMgmtIPAddress OBJECT-TYPE
	SYNTAX  InetAddress
	MAX-ACCESS  read-only
	STATUS  current
	DESCRIPTION
		"Management IP Address for this Managed Device"
	::= { netscalerSDWANAcceleratorEntry 39 }


eventVarBindOids OBJECT IDENTIFIER
::= { sdxEventGroup 1 }

source OBJECT-TYPE
	SYNTAX  OCTET STRING
	MAX-ACCESS  accessible-for-notify
	STATUS  current
	DESCRIPTION
		"IP address of the device generating the event"
	::= { eventVarBindOids 1 }

entityName OBJECT-TYPE
	SYNTAX  OCTET STRING
	MAX-ACCESS  accessible-for-notify
	STATUS  current
	DESCRIPTION
		"Name of the entity associated with this alarm"
	::= { eventVarBindOids 2 }

entityType OBJECT-TYPE
	SYNTAX  OCTET STRING
	MAX-ACCESS  accessible-for-notify
	STATUS  current
	DESCRIPTION
		"Type of entity associated with this alarm"
	::= { eventVarBindOids 3 }

eventMessage OBJECT-TYPE
	SYNTAX  OCTET STRING
	MAX-ACCESS  accessible-for-notify
	STATUS  current
	DESCRIPTION
		"Message associated with this alarm"
	::= { eventVarBindOids 4 }

thresholdValue OBJECT-TYPE
	SYNTAX  OCTET STRING
	MAX-ACCESS  accessible-for-notify
	STATUS  current
	DESCRIPTION
		"High threshold value configured for this alarm"
	::= { eventVarBindOids 5 }

currentValue OBJECT-TYPE
	SYNTAX  OCTET STRING
	MAX-ACCESS  accessible-for-notify
	STATUS  current
	DESCRIPTION
		"Current value of the entity when high or normal threshold trap is sent"
	::= { eventVarBindOids 6 }

severity OBJECT-TYPE
	SYNTAX  OCTET STRING
	MAX-ACCESS  accessible-for-notify
	STATUS  current
	DESCRIPTION
		"Severity associated with this alarm"
	::= { eventVarBindOids 7 }


mpsEvents OBJECT IDENTIFIER
::= { sdxEventGroup 2 }

cpuUsageHigh NOTIFICATION-TYPE
	OBJECTS  {source, entityName, eventMessage, currentValue, thresholdValue, severity}
	STATUS  current
	DESCRIPTION
		"CPU utilization has exceeded the high threshold value"
	::= { mpsEvents 1 }

cpuUsageNormal NOTIFICATION-TYPE
	OBJECTS  {source, entityName, eventMessage, currentValue, thresholdValue, severity}
	STATUS  current
	DESCRIPTION
		"CPU utilization has returned to normal"
	::= { mpsEvents 2 }

memoryUsageHigh NOTIFICATION-TYPE
	OBJECTS  {source, entityName, eventMessage, currentValue, thresholdValue, severity}
	STATUS  current
	DESCRIPTION
		"Memory utilization has exceeded the high threshold value."
	::= { mpsEvents 3 }

memoryUsageNormal NOTIFICATION-TYPE
	OBJECTS  {source, entityName, eventMessage, currentValue, thresholdValue, severity}
	STATUS  current
	DESCRIPTION
		"Memory utilization has returned to normal"
	::= { mpsEvents 4 }

xenHttpFailed NOTIFICATION-TYPE
	OBJECTS  {source, entityName, eventMessage, severity}
	STATUS  current
	DESCRIPTION
		"HTTP communication between the Management Service and XenServer has failed"
	::= { mpsEvents 5 }

xenHttpNormal NOTIFICATION-TYPE
	OBJECTS  {source, entityName, eventMessage, severity}
	STATUS  current
	DESCRIPTION
		"HTTP communication between the Management Service and XenServer has returned to normal"
	::= { mpsEvents 6 }

xenSshFailed NOTIFICATION-TYPE
	OBJECTS  {source, entityName, eventMessage, severity}
	STATUS  current
	DESCRIPTION
		"SSH communication between the Management Service and XenServer has failed"
	::= { mpsEvents 7 }

xenSshNormal NOTIFICATION-TYPE
	OBJECTS  {source, entityName, eventMessage, severity}
	STATUS  current
	DESCRIPTION
		"SSH communication between the Management Service and XenServer has returned to normal"
	::= { mpsEvents 8 }

xenApiFailed NOTIFICATION-TYPE
	OBJECTS  {source, entityName, eventMessage, severity}
	STATUS  current
	DESCRIPTION
		"XenAPI communication between the Management Service and XenServer has failed"
	::= { mpsEvents 9 }

xenApiNormal NOTIFICATION-TYPE
	OBJECTS  {source, entityName, eventMessage, severity}
	STATUS  current
	DESCRIPTION
		"XenAPI communication between the Management Service and XenServer has returned to normal"
	::= { mpsEvents 10 }

xenPingFailed NOTIFICATION-TYPE
	OBJECTS  {source, entityName, eventMessage, severity}
	STATUS  current
	DESCRIPTION
		"ICMP Ping between the Management Service and XenServer has failed"
	::= { mpsEvents 11 }

xenPingNormal NOTIFICATION-TYPE
	OBJECTS  {source, entityName, eventMessage, severity}
	STATUS  current
	DESCRIPTION
		"ICMP Ping between the Management Service and XenServer has returned to normal"
	::= { mpsEvents 12 }

ipmiStateError NOTIFICATION-TYPE
	OBJECTS  {source, entityName, eventMessage, severity}
	STATUS  current
	DESCRIPTION
		"Intelligent Platform Management Interface (IPMI) utility is missing"
	::= { mpsEvents 13 }

ipmiStateNormal NOTIFICATION-TYPE
	OBJECTS  {source, entityName, eventMessage, severity}
	STATUS  current
	DESCRIPTION
		"Intelligent Platform Management Interface (IPMI) utility is detected"
	::= { mpsEvents 14 }

bmcFirmwareVersionError NOTIFICATION-TYPE
	OBJECTS  {source, entityName, eventMessage, severity}
	STATUS  current
	DESCRIPTION
		"BMC firmware is missing or the version is not supported"
	::= { mpsEvents 15 }

bmcFirmwareVersionNormal NOTIFICATION-TYPE
	OBJECTS  {source, entityName, eventMessage, severity}
	STATUS  current
	DESCRIPTION
		"BMC firmware is detected or the version has returned to a supported version"
	::= { mpsEvents 16 }

resourceStateError NOTIFICATION-TYPE
	OBJECTS  {source, entityName, eventMessage, severity}
	STATUS  current
	DESCRIPTION
		"A hardware or software resource error has occurred; entityName and eventMessage show specific failure information"
	::= { mpsEvents 17 }

resourceStateNormal NOTIFICATION-TYPE
	OBJECTS  {source, entityName, eventMessage, severity}
	STATUS  current
	DESCRIPTION
		"The hardware or software resource error has been fixed and normal state has been restored; entityName and eventMessage show details"
	::= { mpsEvents 18 }

fanSpeedError NOTIFICATION-TYPE
	OBJECTS  {source, entityName, eventMessage, currentValue, severity}
	STATUS  current
	DESCRIPTION
		"Fan speed is either high or low"
	::= { mpsEvents 19 }

fanSpeedNormal NOTIFICATION-TYPE
	OBJECTS  {source, entityName, eventMessage, currentValue, severity}
	STATUS  current
	DESCRIPTION
		"Fan speed has returned to normal"
	::= { mpsEvents 20 }

cpuTempError NOTIFICATION-TYPE
	OBJECTS  {source, entityName, eventMessage, currentValue, severity}
	STATUS  current
	DESCRIPTION
		"CPU temperature error; entityName and eventMessage show specific failure information"
	::= { mpsEvents 21 }

cpuTempNormal NOTIFICATION-TYPE
	OBJECTS  {source, entityName, eventMessage, currentValue, severity}
	STATUS  current
	DESCRIPTION
		"CPU temperature has returned to normal"
	::= { mpsEvents 22 }

systemTempError NOTIFICATION-TYPE
	OBJECTS  {source, entityName, eventMessage, currentValue, severity}
	STATUS  current
	DESCRIPTION
		"System temperature error; entityName and eventMessage show specific failure information"
	::= { mpsEvents 23 }

systemTempNormal NOTIFICATION-TYPE
	OBJECTS  {source, entityName, eventMessage, currentValue, severity}
	STATUS  current
	DESCRIPTION
		"System temperature has returned to normal"
	::= { mpsEvents 24 }

voltageError NOTIFICATION-TYPE
	OBJECTS  {source, entityName, eventMessage, currentValue, severity}
	STATUS  current
	DESCRIPTION
		"Voltage error; entityName and eventMessage show specific failure information"
	::= { mpsEvents 25 }

voltageNormal NOTIFICATION-TYPE
	OBJECTS  {source, entityName, eventMessage, currentValue, severity}
	STATUS  current
	DESCRIPTION
		"Voltage has returned to normal"
	::= { mpsEvents 26 }

powerSupplyFailed NOTIFICATION-TYPE
	OBJECTS  {source, entityName, eventMessage, severity}
	STATUS  current
	DESCRIPTION
		"Power Supply error; entityName and eventMessage show specific failure information information"
	::= { mpsEvents 27 }

powerSupplyNormal NOTIFICATION-TYPE
	OBJECTS  {source, entityName, eventMessage, severity}
	STATUS  current
	DESCRIPTION
		"Power Supply has returned to normal condition"
	::= { mpsEvents 28 }

healthCounterError NOTIFICATION-TYPE
	OBJECTS  {source, entityName, eventMessage, currentValue, severity}
	STATUS  current
	DESCRIPTION
		"Health Counter Error; entityName and eventMessage show specific failure information"
	::= { mpsEvents 31 }

healthCounterNormal NOTIFICATION-TYPE
	OBJECTS  {source, entityName, eventMessage, currentValue, severity}
	STATUS  current
	DESCRIPTION
		"Health Counter Error condition has returned to normal; entityName and eventMessage show details"
	::= { mpsEvents 32 }

interfaceDown NOTIFICATION-TYPE
	OBJECTS  {source, entityName, eventMessage, severity}
	STATUS  current
	DESCRIPTION
		"A network interface has gone  down; entityName and eventMessage show details"
	::= { mpsEvents 33 }

interfaceUp NOTIFICATION-TYPE
	OBJECTS  {source, entityName, eventMessage, severity}
	STATUS  current
	DESCRIPTION
		"The network interface has returned to UP state; entityName and eventMessage show details"
	::= { mpsEvents 34 }

diskUtilizationHigh NOTIFICATION-TYPE
	OBJECTS  {source, entityName, eventMessage, currentValue, thresholdValue, severity}
	STATUS  current
	DESCRIPTION
		"This trap is sent when the Disk utilization goes high. 'entityName' and 'eventMessage' will show specific failure information"
	::= { mpsEvents 35 }

diskUtilizationNormal NOTIFICATION-TYPE
	OBJECTS  {source, entityName, eventMessage, currentValue, thresholdValue, severity}
	STATUS  current
	DESCRIPTION
		"This trap is sent when the Disk utilization becomes normal. 'entityName' and 'eventMessage' will show specific failure information"
	::= { mpsEvents 36 }

srStatusError NOTIFICATION-TYPE
	OBJECTS  {source, entityName, eventMessage, severity}
	STATUS  current
	DESCRIPTION
		"This trap is sent when a storage repository status is not good. 'entityName' and 'eventMessage' will show specific failure information"
	::= { mpsEvents 37 }

srStatusNormal NOTIFICATION-TYPE
	OBJECTS  {source, entityName, eventMessage, severity}
	STATUS  current
	DESCRIPTION
		"This trap is sent when a storage repository status becomes normal. 'entityName' and 'eventMessage' will show specific failure information"
	::= { mpsEvents 38 }

subSystemDown NOTIFICATION-TYPE
	OBJECTS  {source, entityName, eventMessage, severity}
	STATUS  current
	DESCRIPTION
		"A subsystem has gone DOWN; entityName shows details"
	::= { mpsEvents 43 }

subSystemUp NOTIFICATION-TYPE
	OBJECTS  {source, entityName, eventMessage, severity}
	STATUS  current
	DESCRIPTION
		"A subsystem has returned to the UP state; entityName shows details"
	::= { mpsEvents 44 }

subSystemFailed NOTIFICATION-TYPE
	OBJECTS  {source, entityName, eventMessage, severity}
	STATUS  current
	DESCRIPTION
		"A subsystem has failed; entityName shows details"
	::= { mpsEvents 45 }

mpsDown NOTIFICATION-TYPE
	OBJECTS  {source, eventMessage, severity}
	STATUS  current
	DESCRIPTION
		"All subsystems are DOWN"
	::= { mpsEvents 46 }

mpsUp NOTIFICATION-TYPE
	OBJECTS  {source, eventMessage, severity}
	STATUS  current
	DESCRIPTION
		"All subsystems are UP"
	::= { mpsEvents 47 }

passwordRecoveryFailed NOTIFICATION-TYPE
	OBJECTS  {source, entityName, eventMessage, severity}
	STATUS  current
	DESCRIPTION
		"Password recovery has failed"
	::= { mpsEvents 48 }

passwordRecoverySuccess NOTIFICATION-TYPE
	OBJECTS  {source, entityName, eventMessage, severity}
	STATUS  current
	DESCRIPTION
		"Password has been recovered successfully"
	::= { mpsEvents 49 }

deviceAdded NOTIFICATION-TYPE
	OBJECTS  {source, entityName, eventMessage, severity}
	STATUS  current
	DESCRIPTION
		"A managed device has been added"
	::= { mpsEvents 50 }

deviceRemoved NOTIFICATION-TYPE
	OBJECTS  {source, entityName, eventMessage, severity}
	STATUS  current
	DESCRIPTION
		"A managed device has been removed"
	::= { mpsEvents 51 }

deviceModified NOTIFICATION-TYPE
	OBJECTS  {source, entityName, eventMessage, severity}
	STATUS  current
	DESCRIPTION
		"An attribute of a managed device has been changed"
	::= { mpsEvents 52 }

devicePowerStateChanged NOTIFICATION-TYPE
	OBJECTS  {source, entityName, eventMessage, severity}
	STATUS  current
	DESCRIPTION
		"Power state of a managed device has changed"
	::= { mpsEvents 53 }

deviceStateChanged NOTIFICATION-TYPE
	OBJECTS  {source, entityName, eventMessage, severity}
	STATUS  current
	DESCRIPTION
		"Instance state of a managed device has changed"
	::= { mpsEvents 54 }

deviceBootFailed NOTIFICATION-TYPE
	OBJECTS  {source, entityName, eventMessage, severity}
	STATUS  current
	DESCRIPTION
		"A managed device has failed to start"
	::= { mpsEvents 55 }

deviceRebootFailed NOTIFICATION-TYPE
	OBJECTS  {source, entityName, eventMessage, severity}
	STATUS  current
	DESCRIPTION
		"A managed device has failed to restart"
	::= { mpsEvents 56 }

backupFailed NOTIFICATION-TYPE
	OBJECTS  {source, entityName, eventMessage, severity}
	STATUS  current
	DESCRIPTION
		"This trap is sent when the backup operation fails"
	::= { mpsEvents 58 }

networkConfigChanged NOTIFICATION-TYPE
	OBJECTS  {source, entityName, eventMessage, severity}
	STATUS  current
	DESCRIPTION
		"This trap is sent when Network Configuration is changed"
	::= { mpsEvents 62 }

loginFailure NOTIFICATION-TYPE
	OBJECTS  {source, entityName, eventMessage, severity}
	STATUS  current
	DESCRIPTION
		"This trap is sent when User Authentication fails. 'entityName' and 'eventMessage' will show specific failure information"
	::= { mpsEvents 71 }

inventoryFailed NOTIFICATION-TYPE
	OBJECTS  {source, entityName, eventMessage, severity}
	STATUS  current
	DESCRIPTION
		"XenServer inventory collection has failed"
	::= { mpsEvents 72 }

healthMonitorPluginError NOTIFICATION-TYPE
	OBJECTS  {source, entityName, eventMessage, severity}
	STATUS  current
	DESCRIPTION
		"This trap is sent when health monitor plugin (xsnsmonitor) is not installed on XenServer"
	::= { mpsEvents 73 }

healthMonitorPluginNormal NOTIFICATION-TYPE
	OBJECTS  {source, entityName, eventMessage}
	STATUS  current
	DESCRIPTION
		"This trap is sent when health monitor plugin (xsnsmonitor) is back to installed state on XenServer"
	::= { mpsEvents 74 }

versionMatrixMisMatch NOTIFICATION-TYPE
	OBJECTS  {source, entityName, eventMessage, severity}
	STATUS  current
	DESCRIPTION
		"This trap is sent when version matrix mismatch is detected"
	::= { mpsEvents 75 }

logicalDriveFailed NOTIFICATION-TYPE
	OBJECTS  {source, entityName, eventMessage, currentValue, severity}
	STATUS  current
	DESCRIPTION
		"Logical Drive Failed"
	::= { mpsEvents 76 }

physicalDriveFailed NOTIFICATION-TYPE
	OBJECTS  {source, entityName, eventMessage, currentValue, severity}
	STATUS  current
	DESCRIPTION
		"Physical Drive Failed"
	::= { mpsEvents 77 }

trapConfigFailure NOTIFICATION-TYPE
	OBJECTS  {source, entityName, eventMessage, severity}
	STATUS  current
	DESCRIPTION
		"This trap is sent when failure occurs in adding snmp trap destination"
	::= { mpsEvents 78 }

pooledLicenseGrace NOTIFICATION-TYPE
	OBJECTS  {source, entityName, eventMessage, severity}
	STATUS  current
	DESCRIPTION
		"This trap is sent when license is on grace for more than 6(threshold) hours"
	::= { mpsEvents 80 }

pooledLicenseGraceNormal NOTIFICATION-TYPE
	OBJECTS  {source, entityName, eventMessage, severity}
	STATUS  current
	DESCRIPTION
		"License in not under Grace"
	::= { mpsEvents 81 }

pooledLicenseCapacityPartial NOTIFICATION-TYPE
	OBJECTS  {source, entityName, eventMessage, severity}
	STATUS  current
	DESCRIPTION
		"LicenseCapacityNormal; SDX is running on partial license capacity"
	::= { mpsEvents 82 }

pooledLicenseCapacityNormal NOTIFICATION-TYPE
	OBJECTS  {source, entityName, eventMessage, severity}
	STATUS  current
	DESCRIPTION
		"LicenseCapacityNormal; SDX is running on proper license capacity"
	::= { mpsEvents 83 }

sslCertThresholdBreached NOTIFICATION-TYPE
	OBJECTS  {source, entityName, eventMessage, severity}
	STATUS  current
	DESCRIPTION
		"sslCertThresholdBreached;Certificate expiry"
	::= { mpsEvents 96 }

sslCertThresholdNormal NOTIFICATION-TYPE
	OBJECTS  {source, entityName, eventMessage, severity}
	STATUS  current
	DESCRIPTION
		"sslCertThresholdNormal"
	::= { mpsEvents 97 }

inventoryUp NOTIFICATION-TYPE
	OBJECTS  {source, entityName, eventMessage, severity}
	STATUS  current
	DESCRIPTION
		"Inventory has returned to normal condition"
	::= { mpsEvents 101 }

logicalDriveNormal NOTIFICATION-TYPE
	OBJECTS  {source, entityName, eventMessage, currentValue, severity}
	STATUS  current
	DESCRIPTION
		"Logical Drive Normal"
	::= { mpsEvents 102 }

physicalDriveNormal NOTIFICATION-TYPE
	OBJECTS  {source, entityName, eventMessage, currentValue, severity}
	STATUS  current
	DESCRIPTION
		"Physical Drive Normal"
	::= { mpsEvents 103 }

deviceBooted NOTIFICATION-TYPE
	OBJECTS  {source, entityName, eventMessage, severity}
	STATUS  current
	DESCRIPTION
		"A managed device has failed to start"
	::= { mpsEvents 104 }

deviceRebooted NOTIFICATION-TYPE
	OBJECTS  {source, entityName, eventMessage, severity}
	STATUS  current
	DESCRIPTION
		"A managed device has failed to restart"
	::= { mpsEvents 105 }

hsmStateError NOTIFICATION-TYPE
	OBJECTS  {source, entityName, eventMessage, severity}
	STATUS  current
	DESCRIPTION
		"FIPS is non-operational, unable to determine HSM state"
	::= { mpsEvents 145 }

hsmStateNormal NOTIFICATION-TYPE
	OBJECTS  {source, entityName, eventMessage, severity}
	STATUS  current
	DESCRIPTION
		"FIPS is operational,HSM state is back to normal"
	::= { mpsEvents 146 }

sdxVersionMismatchError NOTIFICATION-TYPE
	OBJECTS  {source, entityName, eventMessage, severity}
	STATUS  current
	DESCRIPTION
		"There is a mismatch in svm and platform versions"
	::= { mpsEvents 147 }

sdxVersionMismatchNormal NOTIFICATION-TYPE
	OBJECTS  {source, entityName, eventMessage, severity}
	STATUS  current
	DESCRIPTION
		"svm and platform version are matching"
	::= { mpsEvents 148 }

HypervisorDiskUtilizationHigh NOTIFICATION-TYPE
	OBJECTS  {source, entityName, eventMessage, currentValue, thresholdValue, severity}
	STATUS  current
	DESCRIPTION
		"Hypervisor disk utilization has exceeded the high threshold value"
	::= { mpsEvents 149 }

HypervisorDiskUtilizationNormal NOTIFICATION-TYPE
	OBJECTS  {source, entityName, eventMessage, currentValue, thresholdValue, severity}
	STATUS  current
	DESCRIPTION
		"Hypervisor disk utilization has returned to normal"
	::= { mpsEvents 150 }

pooledLicenseGraceCritical NOTIFICATION-TYPE
	OBJECTS  {source, entityName, eventMessage, severity}
	STATUS  current
	DESCRIPTION
		"This trap is sent when license is on grace for more than 1(threshold) day(s)"
	::= { mpsEvents 151 }


END -- end of module MIB
