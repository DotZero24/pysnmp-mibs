-- *****************************************************************
-- QTECH-CM-PORTAL-MIB.mib:  Qtech China Mobile Portal MIB file
--
-- March 2010, panshiyong
--
-- Copyright (c) 2010 by Qtech Networks Co.,Ltd.
-- All rights reserved.
--
-- *****************************************************************
--

QTECH-CM-PORTAL-MIB DEFINITIONS ::= BEGIN

IMPORTS
    MODULE-IDENTITY,
    OBJECT-TYPE,
    Counter32,
    Unsigned32,
    Integer32
            FROM SNMPv2-SMI
    InetAddressType,
    InetAddress
            FROM INET-ADDRESS-MIB
    DisplayString,
    RowStatus
            FROM SNMPv2-TC
    MODULE-COMPLIANCE,
    OBJECT-GROUP
            FROM SNMPv2-CONF
    qtechMgmt
            FROM QTECH-SMI;

qtechCMPortalMIB MODULE-IDENTITY
    LAST-UPDATED "201003220000Z"
    ORGANIZATION "Qtech Networks Co.,Ltd."
    CONTACT-INFO
           "
           Tel: 4008-111-000

           E-mail: service@qtech.com.cn"
    DESCRIPTION
           "This module defines qtech portal mibs."
    REVISION      "201003220000Z"
    DESCRIPTION
           "Initial version of this MIB module."
    ::= { qtechMgmt 74 }


qtechCMPortalMIBObjects OBJECT IDENTIFIER ::= { qtechCMPortalMIB 1 }


qtechCMPortalMaxAuthNum OBJECT-TYPE
		SYNTAX   Integer32
    MAX-ACCESS  read-write
    STATUS  current
    DESCRIPTION
    		"The max number of all portal authenticated user online."
    ::= { qtechCMPortalMIBObjects 1 }

qtechCMPortalCurAuthNum OBJECT-TYPE
		SYNTAX  Integer32
    MAX-ACCESS  read-only
    STATUS  current
    DESCRIPTION
    		"The current number of all portal authenticated user online."
    ::= { qtechCMPortalMIBObjects 2 }

qtechCMPortalServerInetAddressType OBJECT-TYPE
		SYNTAX InetAddressType
    MAX-ACCESS read-write
    STATUS  current
    DESCRIPTION
    		"The inet address type of the portal server."
		::= { qtechCMPortalMIBObjects 3 }

qtechCMPortalServerInetAddress OBJECT-TYPE
		SYNTAX InetAddress
    MAX-ACCESS read-write
    STATUS  current
    DESCRIPTION
    		"The inet address of portal server."
		::= { qtechCMPortalMIBObjects 4 }

qtechCMPortalServerInetPortNumber OBJECT-TYPE
		SYNTAX  INTEGER
    MAX-ACCESS  read-write
    STATUS  current
    DESCRIPTION
    		"The inet port number of portal server."
		::= { qtechCMPortalMIBObjects 5 }

qtechCMPortalServerUnavailableCode OBJECT-TYPE
		SYNTAX  INTEGER {
		        	not-configured(0),
		        	ping-failed(1)
		        }
    MAX-ACCESS read-only
    STATUS  current
    DESCRIPTION
    		"The flag code of portal server unavailable:
    		 0 - not-configured,
    		 1 - ping-failed
    		 "
    ::= { qtechCMPortalMIBObjects 6 }

qtechCMPortalAuthReqCount OBJECT-TYPE
    SYNTAX Counter32
    MAX-ACCESS read-only
    STATUS  current
    DESCRIPTION
    		"The authenticator request count of portal server."
    ::= { qtechCMPortalMIBObjects 7 }

qtechCMPortalAuthRespCount OBJECT-TYPE
    SYNTAX Counter32
    MAX-ACCESS read-only
    STATUS  current
    DESCRIPTION
    		"The authenticator respone count of portal server."
    ::= { qtechCMPortalMIBObjects 8 }

qtechCMPortalChallengeReqCount OBJECT-TYPE
    SYNTAX Counter32
    MAX-ACCESS read-only
    STATUS  current
    DESCRIPTION
    		"The challenge request count of portal server."
    ::= { qtechCMPortalMIBObjects 9 }

qtechCMPortalChallengeRespCount OBJECT-TYPE
    SYNTAX Counter32
    MAX-ACCESS read-only
    STATUS  current
    DESCRIPTION
    		"The challenge request count of portal server."
    ::= { qtechCMPortalMIBObjects 10 }

qtechCMPortalGlobalServerURL OBJECT-TYPE
    SYNTAX DisplayString (SIZE (0..255))
    MAX-ACCESS read-write
    STATUS  current
    DESCRIPTION
    		"The URL of portal server."
    ::= { qtechCMPortalMIBObjects 11 }

--
-- qtech CMCC Portal URL Info
--
qtechCMPortalServerURLTable OBJECT-TYPE
        SYNTAX  SEQUENCE OF QtechCMPortalServerURLEntry
        MAX-ACCESS  not-accessible
        STATUS  current
        DESCRIPTION
            "The table of Portal URL Info."
        ::= { qtechCMPortalMIBObjects 12 }

qtechCMPortalServerURLEntry OBJECT-TYPE
        SYNTAX  QtechCMPortalServerURLEntry
        MAX-ACCESS  not-accessible
        STATUS  current
        DESCRIPTION
            "The entry of Portal URL info table."
        INDEX   { qtechCMPortalServerURLId }
        ::= { qtechCMPortalServerURLTable 1 }

QtechCMPortalServerURLEntry ::=
    SEQUENCE {
            qtechCMPortalServerURLId          Unsigned32,
            qtechCMPortalServerURL            DisplayString,
            qtechCMPortalServerName           DisplayString,
            qtechCMPortalServerInUsedCount    Unsigned32,
            qtechCMPortalServerConfigStatus   RowStatus
            }

qtechCMPortalServerURLId OBJECT-TYPE
        SYNTAX       Unsigned32
        MAX-ACCESS   read-only
        STATUS       current
        DESCRIPTION
            "The Id of the Portal Server in device."
        ::= { qtechCMPortalServerURLEntry 1 }

qtechCMPortalServerURL OBJECT-TYPE
        SYNTAX  DisplayString (SIZE (0..255))
        MAX-ACCESS  read-write
        STATUS  current
        DESCRIPTION
            " The Portal URL."
         ::= { qtechCMPortalServerURLEntry 2 }

qtechCMPortalServerName OBJECT-TYPE
        SYNTAX  DisplayString (SIZE (0..32))
        MAX-ACCESS  read-write
        STATUS  current
        DESCRIPTION
            " The Portal Server's Name."
         ::= { qtechCMPortalServerURLEntry 3 }

qtechCMPortalServerInUsedCount OBJECT-TYPE
        SYNTAX       Unsigned32
        MAX-ACCESS   read-only
        STATUS       current
        DESCRIPTION
            "The count that this Portal Server is used by Control Cells in the device."
        ::= { qtechCMPortalServerURLEntry 4 }

qtechCMPortalServerConfigStatus OBJECT-TYPE
        SYNTAX  RowStatus
        MAX-ACCESS  read-write
        STATUS  current
        DESCRIPTION
            "Setting this object to 'invalid' will try to remove specific Portal Server from device."
         ::= { qtechCMPortalServerURLEntry 5 }

qtechCMPortalHttpReqCount OBJECT-TYPE
    SYNTAX Counter32
    MAX-ACCESS read-only
    STATUS  current
    DESCRIPTION
    		"The http request count to portal server for redirection."
    ::= { qtechCMPortalMIBObjects 13 }

qtechCMPortalHttpRespCount OBJECT-TYPE
    SYNTAX Counter32
    MAX-ACCESS read-only
    STATUS  current
    DESCRIPTION
    		"The http response count by portal server for redirection."
    ::= { qtechCMPortalMIBObjects 14 }

qtechCMPortalExceptionFailCount OBJECT-TYPE
    SYNTAX Counter32
    MAX-ACCESS read-only
    STATUS  current
    DESCRIPTION
    		"The user offline count for exception reason."
    ::= { qtechCMPortalMIBObjects 15 }

qtechCMPortalAuthSuccessedCount OBJECT-TYPE
    SYNTAX Counter32
    MAX-ACCESS read-only
    STATUS  current
    DESCRIPTION
    		"The radius authenticator response count for success result."
    ::= { qtechCMPortalMIBObjects 16 }

qtechCMPortalNormalAuthReqCount OBJECT-TYPE
    SYNTAX Counter32
    MAX-ACCESS read-only
    STATUS  current
    DESCRIPTION
    		"The normal authenticator request count of portal server."
    ::= { qtechCMPortalMIBObjects 17 }

qtechCMPortalEDUAuthReqCount OBJECT-TYPE
    SYNTAX Counter32
    MAX-ACCESS read-only
    STATUS  current
    DESCRIPTION
    		"The education authenticator request count of portal server."
    ::= { qtechCMPortalMIBObjects 18 }

qtechCMPortalStarbucksAuthReqCount OBJECT-TYPE
    SYNTAX Counter32
    MAX-ACCESS read-only
    STATUS  current
    DESCRIPTION
    		"The starbuck authenticator request count of portal server."
    ::= { qtechCMPortalMIBObjects 19 }

qtechCMPortalNormalAuthRespCount OBJECT-TYPE
    SYNTAX Counter32
    MAX-ACCESS read-only
    STATUS  current
    DESCRIPTION
    		"The normal authenticator respone count of portal server."
    ::= { qtechCMPortalMIBObjects 20 }

qtechCMPortalEDUAuthRespCount OBJECT-TYPE
    SYNTAX Counter32
    MAX-ACCESS read-only
    STATUS  current
    DESCRIPTION
    		"The education authenticator respone count of portal server."
    ::= { qtechCMPortalMIBObjects 21 }

qtechCMPortalStarbucksAuthRespCount OBJECT-TYPE
    SYNTAX Counter32
    MAX-ACCESS read-only
    STATUS  current
    DESCRIPTION
    		"The starbucks authenticator respone count of portal server."
    ::= { qtechCMPortalMIBObjects 22 }

qtechACPortalMaxAuthNum OBJECT-TYPE
		SYNTAX   Integer32
    MAX-ACCESS  read-only
    STATUS  current
    DESCRIPTION
    		"The max number of AC systerm authenticated user online."
    ::= { qtechCMPortalMIBObjects 23 }

qtechACPortalCurrentMaxAuthNum OBJECT-TYPE
		SYNTAX   Integer32
    MAX-ACCESS  read-only
    STATUS  current
    DESCRIPTION
    		"The max number of AC current authenticated user online."
    ::= { qtechCMPortalMIBObjects 24}

---
---Portal trap nodes
---
qtechCMPortalMIBTrap    OBJECT IDENTIFIER ::= { qtechCMPortalMIB 0 }

qtechCMPortalServerDownTrap NOTIFICATION-TYPE
   OBJECTS {
   			qtechCMPortalServerInetAddressType,
        qtechCMPortalServerInetAddress,
        qtechCMPortalServerInetPortNumber,
        qtechCMPortalServerUnavailableCode }
   STATUS current
   DESCRIPTION
   		"This trap is generated when the portal server doesn't
   		 respond client's requests for specified times."
   ::= { qtechCMPortalMIBTrap 1 }

qtechCMPortalServerRecoverTrap NOTIFICATION-TYPE
   OBJECTS {
   			qtechCMPortalServerInetAddressType,
        qtechCMPortalServerInetAddress,
        qtechCMPortalServerInetPortNumber,
        qtechCMPortalServerUnavailableCode }
   STATUS current
   DESCRIPTION
   		"This trap is generated when the portal server recover from
   		 the down status."
   ::= { qtechCMPortalMIBTrap 2 }

---
---compliance statements
---
qtechCMPortalMIBConformance OBJECT IDENTIFIER ::= { qtechCMPortalMIB 2 }
qtechCMPortalMIBCompliances OBJECT IDENTIFIER ::= { qtechCMPortalMIBConformance 1 }
qtechCMPortalMIBGroups      OBJECT IDENTIFIER ::= { qtechCMPortalMIBConformance 2 }

qtechCMPortalMIBCompliance MODULE-COMPLIANCE
   STATUS  current
   DESCRIPTION
   			"The compliance statement for entities which implement
       	 the Portal MIB"
   MODULE  -- this module
   GROUP qtechCMPortalMIBGroup
 	 DESCRIPTION
        "This group is mandatory only for those system which support portal function."
   ::= { qtechCMPortalMIBCompliances 1 }

qtechCMPortalMIBGroup OBJECT-GROUP
   OBJECTS {
   			qtechCMPortalMaxAuthNum,
   			qtechCMPortalCurAuthNum,
   			qtechCMPortalServerInetAddressType,
   			qtechCMPortalServerInetAddress,
   			qtechCMPortalServerInetPortNumber,
   			qtechCMPortalServerUnavailableCode,
   			qtechCMPortalAuthReqCount,
   			qtechCMPortalAuthRespCount,
   			qtechCMPortalChallengeReqCount,
   			qtechCMPortalChallengeRespCount,
   			qtechCMPortalGlobalServerURL,
   			qtechCMPortalServerURL,
                        qtechCMPortalServerName,
                        qtechCMPortalServerInUsedCount,
                        qtechCMPortalServerConfigStatus,
		    qtechCMPortalHttpReqCount,
			qtechCMPortalHttpRespCount,
			qtechCMPortalExceptionFailCount,
		    qtechCMPortalAuthSuccessedCount,
		    qtechCMPortalNormalAuthReqCount,
		    qtechCMPortalEDUAuthReqCount,
		    qtechCMPortalStarbucksAuthReqCount,
		    qtechCMPortalNormalAuthRespCount,
		    qtechCMPortalEDUAuthRespCount,
		    qtechCMPortalStarbucksAuthRespCount,
		    qtechACPortalMaxAuthNum,
		    qtechACPortalCurrentMaxAuthNum
      }
   STATUS  deprecated
   DESCRIPTION
         "The basic collection of objects providing management of portal management."
   ::= { qtechCMPortalMIBGroups 1 }

END
