-- **********************************************************************
-- QTECH-MPLS-L3VPN-RES-MIB.mib: Qtech Mpls L3vpn Resource Statics MIB file
--
-- March 2013, WangMeng
--
-- Copyright (c) 2013 by Qtech Networks Co.,Ltd.
-- All rights reserved.
--
-- **********************************************************************

QTECH-MPLS-L3VPN-RES-MIB DEFINITIONS ::= BEGIN
IMPORTS
   MODULE-IDENTITY,
   OBJECT-TYPE,
   Integer32
      FROM SNMPv2-SMI                                     -- [RFC2578]
   MODULE-COMPLIANCE, OBJECT-GROUP
      FROM SNMPv2-CONF                                    -- [RFC2580]
   RowStatus, StorageType, DisplayString
      FROM SNMPv2-TC                                      -- [RFC2579]
   InetAddress, InetAddressType
      FROM INET-ADDRESS-MIB                               -- [RFC4001]
   mplsL3VpnVrfName
      FROM MPLS-L3VPN-STD-MIB
   bgp4PathAttrIpAddrPrefix,
   bgp4PathAttrIpAddrPrefixLen,
   bgp4PathAttrPeer
      FROM BGP4-MIB
   qtechMgmt
      FROM QTECH-SMI;

-- **********************************************************************
-- * MODULE IDENTITY
-- **********************************************************************
qtechmplsL3VpnResMIB MODULE-IDENTITY
   LAST-UPDATED "201302210000Z"
   ORGANIZATION "Qtech Networks Co.,Ltd."
   CONTACT-INFO
                "Tel: 4008-111-000
                E-mail: service@qtech.com.cn"
   DESCRIPTION
        "This MIB contains managed object definitions for the
         neighbors' parameters of the
         Layer-3 Multiprotocol Label Switching Virtual
         Private Networks.

        Copyright (C) The Internet Society (2006).  This
        version of this MIB module is part of RFC4382; see
        the RFC itself for full legal notices."
  -- Revision history.
  REVISION
      "201302210000Z"
   DESCRIPTION
      "Initial version.  Published as RFC 4382."
   ::= { qtechMgmt 123 }

qtechmplsL3VpnResMIBObjects OBJECT IDENTIFIER ::= {qtechmplsL3VpnResMIB 1}

-- **********************************************************************
-- * qtechmplsL3VpnResTable table
-- **********************************************************************
qtechmplsL3VpnResTable  OBJECT-TYPE
    SYNTAX        SEQUENCE OF QtechmplsL3VpnResEntry
    MAX-ACCESS    not-accessible
    STATUS        current
    DESCRIPTION
       "This table specifies import/export RT resources on
        VRF and the RT/RD resource in VPNV4 route.
        Entries in this table define the map for VRF and
		VPNV4 neighbor."
    ::= { qtechmplsL3VpnResMIBObjects 1 }

qtechmplsL3VpnResEntry  OBJECT-TYPE
    SYNTAX        QtechmplsL3VpnResEntry
    MAX-ACCESS    not-accessible
    STATUS        current
    DESCRIPTION
       "An entry in this table is created by an LSR for
        every VRF capable of supporting MPLS L3VPN.  The
        indexing provides an ordering of VRFs name and
		VPNV4 neighber address"
    INDEX       { qtechmplsL3VpnResPeAddr,
                  qtechmplsL3VpnResVrfName}
    ::= { qtechmplsL3VpnResTable 1 }

QtechmplsL3VpnResEntry ::= SEQUENCE {
    qtechmplsL3VpnResPeAddr        InetAddress,
    qtechmplsL3VpnResVrfName      	DisplayString,
    qtechmplsL3VpnResRtCollect     DisplayString,
    qtechmplsL3VpnResRdCollect     DisplayString,
    qtechmplsL3VpnResIntfAddr      InetAddress,
    qtechmplsL3VpnResImptRt        DisplayString,
	qtechmplsL3VpnResExptRt        DisplayString
}

qtechmplsL3VpnResPeAddr OBJECT-TYPE
          SYNTAX InetAddress
          MAX-ACCESS read-only
          STATUS current
          DESCRIPTION
              "This attribute shall specify the remote address of
                the bgp neighbor in Layer-3 Multiprotocol Label
                Switching Virtual Private Networks. "
           ::= { qtechmplsL3VpnResEntry 1 }

qtechmplsL3VpnResVrfName OBJECT-TYPE
          SYNTAX DisplayString
          MAX-ACCESS read-only
          STATUS current
          DESCRIPTION
              "This attribute shall specify the name of VPN instance. "
           ::= { qtechmplsL3VpnResEntry 2 }

qtechmplsL3VpnResRtCollect OBJECT-TYPE
          SYNTAX DisplayString
          MAX-ACCESS read-write
          STATUS current
          DESCRIPTION
              "This attribute shall specify RT collection in route which learned from VPNV4 neighbor. "
           ::= { qtechmplsL3VpnResEntry 3 }

qtechmplsL3VpnResRdCollect OBJECT-TYPE
          SYNTAX DisplayString
          MAX-ACCESS read-only
          STATUS current
          DESCRIPTION
              "This attribute shall specify RD collection in route which learned from VPNV4 neighbor. "
           ::= { qtechmplsL3VpnResEntry 4 }

qtechmplsL3VpnResIntfAddr OBJECT-TYPE
          SYNTAX        InetAddress
          MAX-ACCESS    read-only
          STATUS        current
          DESCRIPTION
              "This attribute shall specify the local address which used to connect VPNV4 neighbor。"
          ::= { qtechmplsL3VpnResEntry 5 }

qtechmplsL3VpnResImptRt OBJECT-TYPE
          SYNTAX     DisplayString
          MAX-ACCESS read-only
          STATUS     current
          DESCRIPTION
              "This attribute shall specify import RT configured on VPN instance."
          ::= { qtechmplsL3VpnResEntry 6 }

qtechmplsL3VpnResExptRt OBJECT-TYPE
          SYNTAX     DisplayString
          MAX-ACCESS read-only
          STATUS     current
          DESCRIPTION
              "This attribute shall specify export RT configured on VPN instance."
          ::= { qtechmplsL3VpnResEntry 7 }
-- **********************************************************************
-- * End of qtechmplsL3VpnResTable table
-- **********************************************************************

END
