-- *******************************************************************
-- QTECH-CAPWAP-MOBILITY-MIB.mib : Qtech MOBILITY MIB file
-- January 2009, shenyongjian
--
-- Copyright (c) 2009 by Qtech Networks Co.,Ltd.
-- All rights reserved.
-- *******************************************************************
--
QTECH-CAPWAP-MOBILITY-MIB DEFINITIONS ::= BEGIN

IMPORTS
        IpAddress,
        OBJECT-TYPE,
        MODULE-IDENTITY,
        Counter32
                FROM SNMPv2-SMI
        MacAddress,
        DisplayString,
        RowStatus
                FROM SNMPv2-TC
        Ipv6Address
                FROM IPV6-TC
        InetAddressType,
        InetAddress
                FROM INET-ADDRESS-MIB
        MODULE-COMPLIANCE,
        OBJECT-GROUP
                FROM SNMPv2-CONF
        qtechMgmt
                FROM QTECH-SMI;

qtechMobilityMIB MODULE-IDENTITY
    LAST-UPDATED "200909180000Z"
    ORGANIZATION "Qtech Networks Co.,Ltd."
    CONTACT-INFO
        "
    Tel: 4008-111-000

    E-mail: service@qtech.com.cn"
    DESCRIPTION
        "This module defines roam mobility mibs."
    REVISION      "200909180000Z"
    DESCRIPTION
        "Initial version of this MIB module."
    ::= { qtechMgmt 64}


--*****************define the roam mobility nodes********************
qtechMobilityMIBObjects OBJECT IDENTIFIER   ::= {qtechMobilityMIB 1}
qtechMobility           OBJECT IDENTIFIER   ::= {qtechMobilityMIBObjects 1}
qtechMobilityIf         OBJECT IDENTIFIER   ::= {qtechMobilityMIBObjects 2}
qtechMobilityTrap       OBJECT IDENTIFIER   ::= {qtechMobilityMIBObjects 3}

--********************************************************************
--                                                                  **
--                       MOBILITY GROUP MIB                         **
--                                                                  **
--********************************************************************

--*********1.Roam Mobility Group Entry***************
qtechMobilityEntryTable OBJECT-TYPE
    SYNTAX SEQUENCE OF QtechMobilityEntry
    MAX-ACCESS not-accessible
    STATUS current
    DESCRIPTION
         "Creat the roam mobility group"
    ::= {qtechMobility 1}

qtechMobilityEntry OBJECT-TYPE
    SYNTAX QtechMobilityEntry
    MAX-ACCESS not-accessible
    STATUS current
    DESCRIPTION
         "The entry of roam mobility group table"
    INDEX  { qtechRoamGroupId }
    ::= { qtechMobilityEntryTable 1 }

QtechMobilityEntry ::=
    SEQUENCE {
        qtechRoamGroupId                    INTEGER,
        qtechRoamGroupName                  DisplayString,
        qtechRoamGroupMyAddress             IpAddress,
        qtechRoamGroupMcEnable              INTEGER,
        qtechRoamGroupMcAddress             IpAddress,
        qtechRoamGroupKeepaliveCount        INTEGER,
        qtechRoamGroupKeepaliveInterval     INTEGER,
        qtechRoamGroupIsFast                INTEGER,
        qtechRoamGroupCreateStatus          RowStatus,
        qtechRoamGroupMyAddressIPv6         Ipv6Address
    }

--The group id of roam mobility group
qtechRoamGroupId OBJECT-TYPE
     SYNTAX  INTEGER (0..8)
     MAX-ACCESS read-only
     STATUS current
     DESCRIPTION
              "The group id of roam mobility group"
     ::= { qtechMobilityEntry 1 }

--The group name of roam mobility group
qtechRoamGroupName OBJECT-TYPE
     SYNTAX  DisplayString
     MAX-ACCESS read-create
     STATUS current
     DESCRIPTION
              "The group name of roam mobility group"
     ::= { qtechMobilityEntry 2 }

--The group ipv4 address of roam mobility group
qtechRoamGroupMyAddress OBJECT-TYPE
     SYNTAX  IpAddress
     MAX-ACCESS read-only
     STATUS current
     DESCRIPTION
             "The group local ipv4 address of roam mobility group"
     ::= { qtechMobilityEntry 3 }

--The flag whether the roam mobility group mc is enable
qtechRoamGroupMcEnable OBJECT-TYPE
     SYNTAX  INTEGER
     MAX-ACCESS read-create
     STATUS current
     DESCRIPTION
              "The flag whether the roam mobility group mc is enable"
     ::= { qtechMobilityEntry 4 }

--The multicast addr of roam mobility group
qtechRoamGroupMcAddress OBJECT-TYPE
     SYNTAX  IpAddress
     MAX-ACCESS read-create
     STATUS current
     DESCRIPTION
             "The multicast addr of roam mobility group"
     ::= { qtechMobilityEntry 5 }

--The keepalive count of roam mobility group
qtechRoamGroupKeepaliveCount OBJECT-TYPE
     SYNTAX  INTEGER (2..30)
     MAX-ACCESS read-create
     STATUS current
     DESCRIPTION
              "The keepalive count of roam mobility group"
     ::= { qtechMobilityEntry 6 }

--The keepalive interval of roam mobility group
qtechRoamGroupKeepaliveInterval OBJECT-TYPE
     SYNTAX  INTEGER (1..30)
     MAX-ACCESS read-create
     STATUS current
     DESCRIPTION
              "The keepalive interval in seconds of roam mobility group"
     ::= { qtechMobilityEntry 7 }

--The flag whether the roam mobility group run in fast roaming mode
qtechRoamGroupIsFast OBJECT-TYPE
     SYNTAX  INTEGER
     MAX-ACCESS read-create
     STATUS current
     DESCRIPTION
              "The flag whether the roam mobility group run in fast roaming mode"
     ::= {qtechMobilityEntry 8 }

--This object indicate the creat or delete of the table
qtechRoamGroupCreateStatus OBJECT-TYPE
    SYNTAX   RowStatus
    MAX-ACCESS read-create
    STATUS   current
    DESCRIPTION
           "This object indicate the creat or delete of the Mobility table"
    ::= { qtechMobilityEntry 9 }

--The group ipv6 address of roam mobility group
qtechRoamGroupMyAddressIPv6 OBJECT-TYPE
     SYNTAX  Ipv6Address
     MAX-ACCESS read-only
     STATUS current
     DESCRIPTION
             "The group local ipv6 address of roam mobility group"
     ::= { qtechMobilityEntry 10 }

--*********2.Roam Mobility Member Entry***************
qtechMobilityMemberEntryTable OBJECT-TYPE
    SYNTAX SEQUENCE OF QtechMobilityMemberEntry
    MAX-ACCESS not-accessible
    STATUS current
    DESCRIPTION
         "Creat the roam mobility group member"
    ::= {qtechMobility 2}

qtechMobilityMemberEntry OBJECT-TYPE
    SYNTAX QtechMobilityMemberEntry
    MAX-ACCESS not-accessible
    STATUS current
    DESCRIPTION
         "The entry of roam mobility member"
    INDEX  { qtechRoamMemberGroupId, qtechRoamMemberPeerAddress }
    ::= { qtechMobilityMemberEntryTable 1 }

QtechMobilityMemberEntry ::=
    SEQUENCE {
        qtechRoamMemberGroupId               INTEGER,
        qtechRoamMemberPeerAddress           IpAddress,
        qtechRoamMemberIsList                INTEGER,
        qtechRoamMemberDataChannelIsOK       INTEGER,
        qtechRoamMemberDataChannelFailTimes  INTEGER,
        qtechRoamMemberDTLSIsClient          INTEGER,
        qtechRoamMemberDTLSIsOK              INTEGER,
        qtechRoamMemberCreateStatus          RowStatus
    }

--The group id of roam mobility group member
qtechRoamMemberGroupId OBJECT-TYPE
     SYNTAX  INTEGER (0..8)
     MAX-ACCESS read-only
     STATUS current
     DESCRIPTION
              "The group id of roam mobility group"
     ::= { qtechMobilityMemberEntry 1 }

--The peer ipv4 address of roam mobility group member
qtechRoamMemberPeerAddress OBJECT-TYPE
     SYNTAX  IpAddress
     MAX-ACCESS read-only
     STATUS current
     DESCRIPTION
              "The peer ipv4 address of roam mobility group member"
     ::= { qtechMobilityMemberEntry 2 }

--The flag whether roam mobility group member in roam list
qtechRoamMemberIsList OBJECT-TYPE
 SYNTAX  INTEGER (0..1)
     MAX-ACCESS read-create
     STATUS current
     DESCRIPTION
             "The flag whether roam mobility group member in roam list"
     ::= { qtechMobilityMemberEntry 3 }

--The flag whether the data channel of roam mobility group member is ok
qtechRoamMemberDataChannelIsOK OBJECT-TYPE
     SYNTAX  INTEGER (0..1)
     MAX-ACCESS read-only
     STATUS current
     DESCRIPTION
             "The flag whether the data channel of roam mobility group member is ok"
     ::= { qtechMobilityMemberEntry 4 }

--The Fail times of the data channel of roam mobility group member
qtechRoamMemberDataChannelFailTimes OBJECT-TYPE
     SYNTAX  INTEGER
     MAX-ACCESS read-only
     STATUS current
     DESCRIPTION
              "The Fail times of the data channel of roam mobility group member"
     ::= { qtechMobilityMemberEntry 5 }

--The flag whether the roam group member is client
qtechRoamMemberDTLSIsClient OBJECT-TYPE
     SYNTAX  INTEGER
     MAX-ACCESS read-only
     STATUS current
     DESCRIPTION
             "The flag whether the roam mobility group member is client"
     ::= { qtechMobilityMemberEntry 6 }

--The flag whether the roam group member dtls is ok
qtechRoamMemberDTLSIsOK OBJECT-TYPE
     SYNTAX  INTEGER (0..1)
     MAX-ACCESS read-only
     STATUS current
     DESCRIPTION
             "The flag whether the roam mobility group member dtls is ok"
     ::= { qtechMobilityMemberEntry 7 }

--This object indicate the creat or delete of the table
qtechRoamMemberCreateStatus OBJECT-TYPE
     SYNTAX   RowStatus
     MAX-ACCESS read-create
     STATUS   current
     DESCRIPTION
           "This object indicate the creat or delete of the Mobility table"
     ::= { qtechMobilityMemberEntry 8 }

--*********3.creat the AP control entry***************
qtechAPCtrlCreatEntryTable OBJECT-TYPE
   SYNTAX SEQUENCE OF QtechAPCtrlCreatEntry
   MAX-ACCESS not-accessible
   STATUS current
   DESCRIPTION
          "Creat the AP control block"
   ::= {qtechMobility 3}

qtechAPCtrlCreatEntry OBJECT-TYPE
   SYNTAX QtechAPCtrlCreatEntry
   MAX-ACCESS not-accessible
   STATUS current
   DESCRIPTION
          "The entry of the AP control block"
   INDEX { qtechAPName }
   ::= { qtechAPCtrlCreatEntryTable 1}

QtechAPCtrlCreatEntry ::=
    SEQUENCE {
        qtechAPName                DisplayString,
        qtechPriority              INTEGER,
        qtechPrimaryACIP           IpAddress,
        qtechPrimaryACName         DisplayString,
        qtechSecondaryACIP         IpAddress,
        qtechSecondaryACName       DisplayString,
        qtechTertiaryACIP          IpAddress,
        qtechTertiaryACName        DisplayString,
        qtechAPCtrlCreatStatus     RowStatus
    }

--The AP control block name
qtechAPName OBJECT-TYPE
     SYNTAX DisplayString
     MAX-ACCESS not-accessible
     STATUS current
     DESCRIPTION
             "The name of the AP control block"
     ::= { qtechAPCtrlCreatEntry 1}

--The priority of AP control block
qtechPriority OBJECT-TYPE
    SYNTAX INTEGER (1..4)
    MAX-ACCESS read-create
    STATUS current
    DESCRIPTION
            "The priority of AP control block"
    ::= { qtechAPCtrlCreatEntry 2 }

--The primary AC  ip of AP control block
qtechPrimaryACIP OBJECT-TYPE
    SYNTAX IpAddress
    MAX-ACCESS read-create
    STATUS current
    DESCRIPTION
            "The primary AC IP of AP control block"
    ::= { qtechAPCtrlCreatEntry 3 }

--The primary AC Name of AP control block
qtechPrimaryACName OBJECT-TYPE
     SYNTAX  DisplayString
     MAX-ACCESS read-create
     STATUS current
     DESCRIPTION
              "The primary AC Name of AP control block"
     ::= { qtechAPCtrlCreatEntry 4 }

--The secondary AC  ip of AP control block
qtechSecondaryACIP OBJECT-TYPE
    SYNTAX IpAddress
    MAX-ACCESS read-create
    STATUS current
    DESCRIPTION
            "The secondary AC IP of AP control block"
    ::= { qtechAPCtrlCreatEntry 5 }

--The secondary AC Name of AP control block
qtechSecondaryACName OBJECT-TYPE
     SYNTAX  DisplayString
     MAX-ACCESS read-create
     STATUS current
     DESCRIPTION
              "The secondary AC Name of AP control block"
     ::= { qtechAPCtrlCreatEntry 6 }

--The tertiary AC  ip of AP control block
qtechTertiaryACIP OBJECT-TYPE
    SYNTAX IpAddress
    MAX-ACCESS read-create
    STATUS current
    DESCRIPTION
            "The tertiary AC IP of AP control block"
    ::= { qtechAPCtrlCreatEntry 7 }

--The tertiary AC Name of AP control block
qtechTertiaryACName OBJECT-TYPE
     SYNTAX  DisplayString
     MAX-ACCESS read-create
     STATUS current
     DESCRIPTION
              "The tertiary AC Name of AP control block"
     ::= { qtechAPCtrlCreatEntry 8 }

--The object indicates the creat or delete of the AP control table
qtechAPCtrlCreatStatus OBJECT-TYPE
    SYNTAX RowStatus
    MAX-ACCESS read-create
    STATUS current
    DESCRIPTION
           "The flag of the AP control table"
    ::= {qtechAPCtrlCreatEntry 9}


--*********5.creat the Wlan control entry***************
qtechWLANCtrlCreatEntryTable OBJECT-TYPE
   SYNTAX SEQUENCE OF QtechWLANCtrlCreatEntry
   MAX-ACCESS not-accessible
   STATUS current
   DESCRIPTION
          "Creat the WLAN control block"
   ::= {qtechMobility 4}

qtechWLANCtrlCreatEntry OBJECT-TYPE
   SYNTAX QtechWLANCtrlCreatEntry
   MAX-ACCESS not-accessible
   STATUS current
   DESCRIPTION
          "The entry of the WLAN group control block"
   INDEX { qtechWLANID }
   ::= { qtechWLANCtrlCreatEntryTable 1}

QtechWLANCtrlCreatEntry ::=
    SEQUENCE {
         qtechWLANID              INTEGER,
         qtechAnchorACIPaddr      IpAddress,
         qtechWLANCtrlCreatStatus RowStatus,
         qtechAnchorACIPaddrIPv6  Ipv6Address
    }

--the name of WLAN
qtechWLANID OBJECT-TYPE
     SYNTAX INTEGER
     MAX-ACCESS read-only
     STATUS current
     DESCRIPTION
             "The name of the wlan"
     ::= { qtechWLANCtrlCreatEntry 1 }

--the anchor ac ipv4 address of wlan
qtechAnchorACIPaddr OBJECT-TYPE
     SYNTAX IpAddress
     MAX-ACCESS read-create
     STATUS current
     DESCRIPTION
             "The anchor ac ip address of wlan"
     ::= { qtechWLANCtrlCreatEntry 2 }

--the object indicate creat or delete of the WLAN control table
qtechWLANCtrlCreatStatus  OBJECT-TYPE
    SYNTAX RowStatus
    MAX-ACCESS read-create
    STATUS current
    DESCRIPTION
           "the object indicate creat or delete of the WLAN control table"
    ::= { qtechWLANCtrlCreatEntry 3 }

--the anchor ac ipv6 address of wlan
qtechAnchorACIPaddrIPv6 OBJECT-TYPE
     SYNTAX Ipv6Address
     MAX-ACCESS read-create
     STATUS current
     DESCRIPTION
             "The anchor ac ipv6 address of wlan"
     ::= { qtechWLANCtrlCreatEntry 4 }

--***************simple param***************
--6 ping the other AC in the mobility
qtechMobilityACPing OBJECT-TYPE
     SYNTAX IpAddress
     MAX-ACCESS read-write
     STATUS current
     DESCRIPTION
              "Ping the other AC in the mobility"
     ::= {qtechMobility 5}

--7 Handoff Requests Received of Global Mobility Statistics
qtechGlobalHandoffRequestsReceived OBJECT-TYPE
      SYNTAX INTEGER
      MAX-ACCESS read-write
      STATUS current
      DESCRIPTION
               "Handoff requests received of global mobility statistics"
      ::= {qtechMobility 6}

--8 Handoff End Requests Received
qtechGlobalHandoffEndRequestsReceived OBJECT-TYPE
     SYNTAX INTEGER
     MAX-ACCESS read-write
     STATUS current
     DESCRIPTION
             "Handoff end requests received"
     ::= {qtechMobility 7}

--9 State Transitions Disabllowed
qtechGlobalStateTransitionsDisabled OBJECT-TYPE
     SYNTAX INTEGER
     MAX-ACCESS read-write
     STATUS current
     DESCRIPTION
             "State transitions Disallowed"
     ::= {qtechMobility 8}

--10 Resource Unavailable
qtechGlobalResourceUnavailable OBJECT-TYPE
     SYNTAX INTEGER
     MAX-ACCESS read-write
     STATUS current
     DESCRIPTION
            "Resource Unavailable"
     ::= {qtechMobility 9}

--11 Handoff Requests Ignored
qtechRespondeHandoffRequestIgnored OBJECT-TYPE
      SYNTAX INTEGER
      MAX-ACCESS read-write
      STATUS current
      DESCRIPTION
             "Handoff Requests Ignored"
      ::= {qtechMobility 10}

--12 Ping Pong Handoff Requests Dropped
qtechRespondePingPongHandoffRequestsDropped OBJECT-TYPE
      SYNTAX INTEGER
      MAX-ACCESS read-write
      STATUS current
      DESCRIPTION
             "Ping Pong handoff Requests Dropped"
      ::= {qtechMobility 11}

--13 Handoff Requests Drooped
qtechRespondeHandoffRequestsDroped OBJECT-TYPE
      SYNTAX INTEGER
      MAX-ACCESS read-write
      STATUS current
      DESCRIPTION
             "Handoff Requests Droped"
      ::= {qtechMobility 12}

--14 Handoff Requests Denied
qtechRespondeHandoffRequestsDenied OBJECT-TYPE
      SYNTAX INTEGER
      MAX-ACCESS read-write
      STATUS current
      DESCRIPTION
             "Handoff Requests Denied"
      ::= {qtechMobility 13}

--15 Client Handoff as local
qtechRespondeClientHandoffasLocal OBJECT-TYPE
      SYNTAX INTEGER
      MAX-ACCESS read-write
      STATUS current
      DESCRIPTION
             "Client Handoff as local"
      ::= {qtechMobility 14}

--16 Client Handoff as Foreign
qtechRespondeClientHandoffasForeign OBJECT-TYPE
      SYNTAX INTEGER
      MAX-ACCESS read-write
      STATUS current
      DESCRIPTION
             "Client Handoff as Foreign"
      ::= {qtechMobility 15}

--17 Anchor Requests Received
qtechRespondeAnchorRequestsReceived OBJECT-TYPE
      SYNTAX INTEGER
      MAX-ACCESS read-write
      STATUS current
      DESCRIPTION
             "Anchor Requests Received"
      ::= {qtechMobility 16}

--18 Anchor Requests Denied
qtechRespondeAnchorRequestDenied OBJECT-TYPE
      SYNTAX INTEGER
      MAX-ACCESS read-write
      STATUS current
      DESCRIPTION
             "Anchor Requests Denied"
      ::= {qtechMobility 17}

--19 Anchor Transferred
qtechRespondeAnchorTransferred OBJECT-TYPE
      SYNTAX INTEGER
      MAX-ACCESS read-write
      STATUS current
      DESCRIPTION
             "Anchor Transferred"
      ::= {qtechMobility 18}

--20 Handoff Requests Sent
qtechInitHandoffRequestsSent OBJECT-TYPE
      SYNTAX INTEGER
      MAX-ACCESS read-write
      STATUS current
      DESCRIPTION
             "Handoff Requests Sent"
      ::= {qtechMobility 19}

--21 Handoff Replies Received
qtechInitHandoffReplyReceived OBJECT-TYPE
      SYNTAX INTEGER
      MAX-ACCESS read-write
      STATUS current
      DESCRIPTION
             "Handoff Replies Received"
      ::= {qtechMobility 20}

--22 Handoff as local reveived
qtechInitHandoffasLocalReceived OBJECT-TYPE
      SYNTAX INTEGER
      MAX-ACCESS read-write
      STATUS current
      DESCRIPTION
             "Handoff as local received"
      ::= {qtechMobility 21}

--23 Handoff as Foreign Received
qtechInitHandoffasForeignReceived OBJECT-TYPE
       SYNTAX INTEGER
       MAX-ACCESS read-write
       STATUS current
       DESCRIPTION
              "Handoff as Foreign Received"
       ::= {qtechMobility 22}

--24 Handoff Denys Received
qtechInitHandoffDenyReceived OBJECT-TYPE
        SYNTAX INTEGER
        MAX-ACCESS read-write
        STATUS current
        DESCRIPTION
              "Handoff Denys Received"
        ::= {qtechMobility 23}

--25 Anchor Request Sent
qtechInitAnchorRequestSent OBJECT-TYPE
         SYNTAX INTEGER
         MAX-ACCESS read-write
         STATUS current
         DESCRIPTION
                "Anchor Request Sent"
         ::= {qtechMobility 24}

--26 Anchor Deny Received
qtechInitAnchorDenyReceived OBJECT-TYPE
         SYNTAX INTEGER
         MAX-ACCESS read-write
         STATUS current
         DESCRIPTION
                "Anchor Deny Received"
         ::= {qtechMobility 25}

--27 AP priority enable
qtechAPPriorityEnable OBJECT-TYPE
         SYNTAX INTEGER
         MAX-ACCESS read-write
         STATUS current
         DESCRIPTION
                "AP priority enable"
         ::= {qtechMobility 26}

--28 The primary backup ac ip of ALL AP control block
qtechPrimaryBackUpACIP OBJECT-TYPE
    SYNTAX IpAddress
    MAX-ACCESS read-create
    STATUS current
    DESCRIPTION
            "The primary backup AC IP of ALL AP control block"
    ::= { qtechMobility 27 }

--29 The primary backup ac name of ALL AP control block
qtechPrimaryBackUpACName OBJECT-TYPE
     SYNTAX  DisplayString
     MAX-ACCESS read-create
     STATUS current
     DESCRIPTION
              "The primary backup ac name of ALL AP control block"
     ::= { qtechMobility 28 }

--30 The secondary backup ac ip of ALL AP control block
qtechSecondaryBackUpACIP OBJECT-TYPE
    SYNTAX IpAddress
    MAX-ACCESS read-create
    STATUS current
    DESCRIPTION
            "The secondary backup AC IP of ALL AP control block"
    ::= { qtechMobility 29 }

--31 The secondary backup ac name of ALL AP control block
qtechSecondaryBackUpACName OBJECT-TYPE
     SYNTAX  DisplayString
     MAX-ACCESS read-create
     STATUS current
     DESCRIPTION
              "The secondary backup ac name of ALL AP control block"
     ::= { qtechMobility 30 }

--32 The teriary backup ac ip of ALL AP control block
qtechTeriaryBackUpACip OBJECT-TYPE
    SYNTAX IpAddress
    MAX-ACCESS read-create
    STATUS current
    DESCRIPTION
            "The teriary backup AC IP of ALL AP control block"
    ::= { qtechMobility 31 }

--33 The teriary backup ac name of ALL AP control block
qtechTeriaryBackUpACName OBJECT-TYPE
     SYNTAX  DisplayString
     MAX-ACCESS read-create
     STATUS current
     DESCRIPTION
              "The teriary backup ac name of ALL AP control block"
     ::= { qtechMobility 32 }

--34 The roaming successful times which in the same control domain (local roam)
qtechACIntraRoam OBJECT-TYPE
     SYNTAX  Counter32
     MAX-ACCESS read-only
     STATUS current
     DESCRIPTION
              "The roaming successful times which in the same control domain"
     ::= { qtechMobility 33 }

--35 The roaming out successful times which in the different control domain (inter ac roam)
qtechACInterRoamIn OBJECT-TYPE
     SYNTAX  Counter32
     MAX-ACCESS read-only
     STATUS current
     DESCRIPTION
              "The roaming in successful times which in the different control domain"
     ::= { qtechMobility 34 }

--36 The roaming in successful times which in the different control domain (inter ac roam)
qtechACInterRoamOut OBJECT-TYPE
     SYNTAX  Counter32
     MAX-ACCESS read-only
     STATUS current
     DESCRIPTION
              "The roaming out successful times which in the different control domain"
     ::= { qtechMobility 35 }

--37 ping the other IPv6 member in the mobility group
qtechMobilityACPingIPv6 OBJECT-TYPE
     SYNTAX Ipv6Address
     MAX-ACCESS read-write
     STATUS current
     DESCRIPTION
              "Ping the other IPv6 AC in the mobility"
     ::= {qtechMobility 36}

--*********38.Roam Mobility Member Entry***************
qtechMobilityIPv6MemberEntryTable OBJECT-TYPE
    SYNTAX SEQUENCE OF QtechMobilityIPv6MemberEntry
    MAX-ACCESS not-accessible
    STATUS current
    DESCRIPTION
         "Creat the roam mobility group member"
    ::= {qtechMobility 37}

qtechMobilityIPv6MemberEntry OBJECT-TYPE
    SYNTAX QtechMobilityIPv6MemberEntry
    MAX-ACCESS not-accessible
    STATUS current
    DESCRIPTION
         "The entry of roam mobility member"
    INDEX  { qtechRoamIPv6MemberGroupId, qtechRoamIPv6MemberPeerAddress }
    ::= { qtechMobilityIPv6MemberEntryTable 1 }

QtechMobilityIPv6MemberEntry ::=
    SEQUENCE {
        qtechRoamIPv6MemberGroupId                 INTEGER,
        qtechRoamIPv6MemberPeerAddress             Ipv6Address,
        qtechRoamIPv6MemberIsList                  INTEGER,
        qtechRoamIPv6MemberDataChannelIsOK         INTEGER,
        qtechRoamIPv6MemberDataChannelFailTimes    INTEGER,
        qtechRoamIPv6MemberDTLSIsClient            INTEGER,
        qtechRoamIPv6MemberDTLSIsOK                INTEGER,
        qtechRoamIPv6MemberCreateStatus            RowStatus
    }

--The group id of roam mobility group member
qtechRoamIPv6MemberGroupId OBJECT-TYPE
     SYNTAX  INTEGER (0..8)
     MAX-ACCESS read-only
     STATUS current
     DESCRIPTION
              "The group id of roam mobility group"
     ::= { qtechMobilityIPv6MemberEntry 1 }

--The peer ipv4 address of roam mobility group member
qtechRoamIPv6MemberPeerAddress OBJECT-TYPE
     SYNTAX  Ipv6Address
     MAX-ACCESS read-only
     STATUS current
     DESCRIPTION
              "The peer ipv4 address of roam mobility group member"
     ::= { qtechMobilityIPv6MemberEntry 2 }

--The flag whether roam mobility group member in roam list
qtechRoamIPv6MemberIsList OBJECT-TYPE
 SYNTAX  INTEGER (0..1)
     MAX-ACCESS read-create
     STATUS current
     DESCRIPTION
             "The flag whether roam mobility group member in roam list"
     ::= { qtechMobilityIPv6MemberEntry 3 }

--The flag whether the data channel of roam mobility group member is ok
qtechRoamIPv6MemberDataChannelIsOK OBJECT-TYPE
     SYNTAX  INTEGER (0..1)
     MAX-ACCESS read-only
     STATUS current
     DESCRIPTION
             "The flag whether the data channel of roam mobility group member is ok"
     ::= { qtechMobilityIPv6MemberEntry 4 }

--The Fail times of the data channel of roam mobility group member
qtechRoamIPv6MemberDataChannelFailTimes OBJECT-TYPE
     SYNTAX  INTEGER
     MAX-ACCESS read-only
     STATUS current
     DESCRIPTION
              "The Fail times of the data channel of roam mobility group member"
     ::= { qtechMobilityIPv6MemberEntry 5 }

--The flag whether the roam group member is client
qtechRoamIPv6MemberDTLSIsClient OBJECT-TYPE
     SYNTAX  INTEGER
     MAX-ACCESS read-only
     STATUS current
     DESCRIPTION
             "The flag whether the roam mobility group member is client"
     ::= { qtechMobilityIPv6MemberEntry 6 }

--The flag whether the roam group member dtls is ok
qtechRoamIPv6MemberDTLSIsOK OBJECT-TYPE
     SYNTAX  INTEGER (0..1)
     MAX-ACCESS read-only
     STATUS current
     DESCRIPTION
             "The flag whether the roam mobility group member dtls is ok"
     ::= { qtechMobilityIPv6MemberEntry 7 }

--This object indicate the creat or delete of the table
qtechRoamIPv6MemberCreateStatus OBJECT-TYPE
     SYNTAX   RowStatus
     MAX-ACCESS read-create
     STATUS   current
     DESCRIPTION
           "This object indicate the creat or delete of the Mobility table"
     ::= { qtechMobilityIPv6MemberEntry 8 }

--*********39.Roam Mobility User***************
qtechMobilityUserEntryTable OBJECT-TYPE
    SYNTAX SEQUENCE OF QtechMobilityUserEntry
    MAX-ACCESS not-accessible
    STATUS current
    DESCRIPTION
         "Show the mobility user"
    ::= {qtechMobility 38}

qtechMobilityUserEntry OBJECT-TYPE
    SYNTAX QtechMobilityUserEntry
    MAX-ACCESS not-accessible
    STATUS current
    DESCRIPTION
         "The entry of mobility user"
    INDEX  { qtechRoamUserMac }
    ::= { qtechMobilityUserEntryTable 1 }

QtechMobilityUserEntry ::=
    SEQUENCE {
        qtechRoamUserMac                           MacAddress,
        qtechRoamUserRoamType                      INTEGER,
        qtechRoamUserRoamOutAcAddressType          InetAddressType,
        qtechRoamUserRoamOutAcAddress              InetAddress,
        qtechRoamUserRoamInAcAddressType           InetAddressType,
        qtechRoamUserRoamInAcAddress               InetAddress,
        qtechRoamUserRoamOutApMac                  MacAddress,
        qtechRoamUserRoamInApMac                   MacAddress,
        qtechRoamUserRoamOutVid                    INTEGER,
        qtechRoamUserRoamInVid                     INTEGER
    }

--The STA MAC of mobility user entry
qtechRoamUserMac OBJECT-TYPE
     SYNTAX  MacAddress
     MAX-ACCESS read-only
     STATUS current
     DESCRIPTION
              "The STA MAC of mobility user entry"
     ::= { qtechMobilityUserEntry 1 }

--The Roam Type of mobility user entry
qtechRoamUserRoamType OBJECT-TYPE
     SYNTAX  INTEGER
     MAX-ACCESS read-only
     STATUS current
     DESCRIPTION
              "The Roam Type of mobility user entry"
     ::= { qtechMobilityUserEntry 2 }

--The RO-AC Address Type of mobility user entry
qtechRoamUserRoamOutAcAddressType OBJECT-TYPE
     SYNTAX  InetAddressType
     MAX-ACCESS read-only
     STATUS current
     DESCRIPTION
              "The RO-AC Address Type of mobility user entry"
     ::= { qtechMobilityUserEntry 3 }

--The RO-AC Address of mobility user entry
qtechRoamUserRoamOutAcAddress OBJECT-TYPE
     SYNTAX  InetAddress
     MAX-ACCESS read-only
     STATUS current
     DESCRIPTION
              "The RO-AC Address of mobility user entry"
     ::= { qtechMobilityUserEntry 4 }

--The RI-AC Address Type of mobility user entry
qtechRoamUserRoamInAcAddressType OBJECT-TYPE
     SYNTAX  InetAddressType
     MAX-ACCESS read-only
     STATUS current
     DESCRIPTION
              "The RI-AC Address Type of mobility user entry"
     ::= { qtechMobilityUserEntry 5 }

--The RI-AC Address of mobility user entry
qtechRoamUserRoamInAcAddress OBJECT-TYPE
     SYNTAX  InetAddress
     MAX-ACCESS read-only
     STATUS current
     DESCRIPTION
              "The RI-AC Address of mobility user entry"
     ::= { qtechMobilityUserEntry 6 }

--The RO-AP MAC of mobility user entry
qtechRoamUserRoamOutApMac OBJECT-TYPE
     SYNTAX  MacAddress
     MAX-ACCESS read-only
     STATUS current
     DESCRIPTION
              "The RO-AP MAC of mobility user entry"
     ::= { qtechMobilityUserEntry 7 }

--The RI-AP MAC of mobility user entry
qtechRoamUserRoamInApMac OBJECT-TYPE
     SYNTAX  MacAddress
     MAX-ACCESS read-only
     STATUS current
     DESCRIPTION
              "The RI-AP MAC of mobility user entry"
     ::= { qtechMobilityUserEntry 8 }

--The RO-VLAN of mobility user entry
qtechRoamUserRoamOutVid OBJECT-TYPE
     SYNTAX  INTEGER
     MAX-ACCESS read-only
     STATUS current
     DESCRIPTION
              "The RO-VLAN of mobility user entry"
     ::= { qtechMobilityUserEntry 9 }

--The RI-VLAN of mobility user entry
qtechRoamUserRoamInVid OBJECT-TYPE
     SYNTAX  INTEGER
     MAX-ACCESS read-only
     STATUS current
     DESCRIPTION
              "The RI-VLAN of mobility user entry"
     ::= { qtechMobilityUserEntry 10 }

--*********40.Roam Mobility Track Entry***************
qtechMobilityTrackEntryTable OBJECT-TYPE
    SYNTAX SEQUENCE OF QtechMobilityTrackEntry
    MAX-ACCESS not-accessible
    STATUS current
    DESCRIPTION
         "Show the roam track of user"
    ::= {qtechMobility 39}

qtechMobilityTrackEntry OBJECT-TYPE
    SYNTAX QtechMobilityTrackEntry
    MAX-ACCESS not-accessible
    STATUS current
    DESCRIPTION
         "The entry of roam mobility track"
    INDEX  { qtechRoamTrackStaMac, qtechRoamTrackId }
    ::= { qtechMobilityTrackEntryTable 1 }

QtechMobilityTrackEntry ::=
    SEQUENCE {
        qtechRoamTrackStaMac                       MacAddress,
        qtechRoamTrackId                           INTEGER,
        qtechRoamTrackAcAddressType                InetAddressType,
        qtechRoamTrackAcAddress                    InetAddress,
        qtechRoamTrackApMac                        MacAddress,
        qtechRoamTrackRadioId                      INTEGER,
        qtechRoamTrackStaIp                        IpAddress,
        qtechRoamTrackStaIpv6                      Ipv6Address,
        qtechRoamTrackStaOnlineTime                INTEGER
    }

--The STA MAC of roam mobility track entry
qtechRoamTrackStaMac OBJECT-TYPE
     SYNTAX  MacAddress
     MAX-ACCESS read-only
     STATUS current
     DESCRIPTION
              "The STA MAC of roam mobility track entry"
     ::= { qtechMobilityTrackEntry 1 }

--The TrackId of roam mobility track entry
qtechRoamTrackId OBJECT-TYPE
     SYNTAX  INTEGER
     MAX-ACCESS read-only
     STATUS current
     DESCRIPTION
              "The TrackId of roam mobility track entry"
     ::= { qtechMobilityTrackEntry 2 }

--The AC Address Type of roam mobility track entry
qtechRoamTrackAcAddressType OBJECT-TYPE
     SYNTAX  InetAddressType
     MAX-ACCESS read-only
     STATUS current
     DESCRIPTION
             "The AC Address Type of roam mobility track entry"
     ::= { qtechMobilityTrackEntry 3 }

--The AC Address of roam mobility track entry
qtechRoamTrackAcAddress OBJECT-TYPE
     SYNTAX  InetAddress
     MAX-ACCESS read-only
     STATUS current
     DESCRIPTION
             "The AC Address Type of roam mobility track entry"
     ::= { qtechMobilityTrackEntry 4 }

--The AP Mac of roam mobility track entry
qtechRoamTrackApMac OBJECT-TYPE
     SYNTAX  MacAddress
     MAX-ACCESS read-only
     STATUS current
     DESCRIPTION
              "The AP Mac of roam mobility track entry"
     ::= { qtechMobilityTrackEntry 5 }

--The RadioId of roam mobility track entry
qtechRoamTrackRadioId OBJECT-TYPE
     SYNTAX  INTEGER
     MAX-ACCESS read-only
     STATUS current
     DESCRIPTION
             "The RadioId of roam mobility track entry"
     ::= { qtechMobilityTrackEntry 6 }

--The STA IPv4 Address of roam mobility track entry
qtechRoamTrackStaIp OBJECT-TYPE
     SYNTAX  IpAddress
     MAX-ACCESS read-only
     STATUS current
     DESCRIPTION
             "The STA IPv4 Address of roam mobility track entry"
     ::= { qtechMobilityTrackEntry 7 }

--The STA IPv6 Address of roam mobility track entry
qtechRoamTrackStaIpv6 OBJECT-TYPE
     SYNTAX  Ipv6Address
     MAX-ACCESS read-only
     STATUS current
     DESCRIPTION
             "The STA IPv6 Address of roam mobility track entry"
     ::= { qtechMobilityTrackEntry 8 }

--The STA online time of roam mobility track entry
qtechRoamTrackStaOnlineTime OBJECT-TYPE
     SYNTAX  INTEGER
     MAX-ACCESS read-only
     STATUS current
     DESCRIPTION
             "The STA online time of roam mobility track entry"
     ::= { qtechMobilityTrackEntry 9 }

qtechMobilityMIBCompliances OBJECT IDENTIFIER ::={qtechMobilityIf 1}
qtechMobilityMIBGroups      OBJECT IDENTIFIER ::={qtechMobilityIf 2}

--compliance statements
qtechMobilityMIBCompliance MODULE-COMPLIANCE
      STATUS current
      DESCRIPTION
               "The compliance statement for entities which implement the CAPWAP MOBILITY MIB"
      MODULE -- this module
             MANDATORY-GROUPS{ qtechMobilityMIBGroup
             }
      ::= { qtechMobilityMIBCompliances 1}

--units of conformance
qtechMobilityMIBGroup OBJECT-GROUP
      OBJECTS {
--ROAM GROUP
        qtechRoamGroupName,
        qtechRoamGroupMyAddress,
        qtechRoamGroupMcEnable,
        qtechRoamGroupMcAddress,
        qtechRoamGroupKeepaliveCount,
        qtechRoamGroupKeepaliveInterval,
        qtechRoamGroupIsFast,
        qtechRoamGroupCreateStatus,
--ROAM MEMBER
        qtechRoamMemberIsList,
        qtechRoamMemberDataChannelIsOK,
        qtechRoamMemberDataChannelFailTimes,
        qtechRoamMemberDTLSIsClient,
        qtechRoamMemberDTLSIsOK,
        qtechRoamMemberCreateStatus,
--AP  MEMBER
        qtechPriority,
        qtechPrimaryACIP,
        qtechPrimaryACName,
        qtechSecondaryACIP,
        qtechSecondaryACName,
        qtechTertiaryACIP,
        qtechTertiaryACName,
        qtechAPCtrlCreatStatus,
--WLAN MEMBER
        qtechAnchorACIPaddr,
        qtechWLANCtrlCreatStatus,
--Mobility staticstic
        qtechGlobalHandoffRequestsReceived,
        qtechGlobalHandoffEndRequestsReceived,
        qtechGlobalStateTransitionsDisabled,
        qtechGlobalResourceUnavailable,
        qtechRespondeHandoffRequestIgnored,
        qtechRespondePingPongHandoffRequestsDropped,
        qtechRespondeHandoffRequestsDroped,
        qtechRespondeHandoffRequestsDenied,
        qtechRespondeClientHandoffasLocal,
        qtechRespondeClientHandoffasForeign,
        qtechRespondeAnchorRequestsReceived,
        qtechRespondeAnchorRequestDenied,
        qtechRespondeAnchorTransferred,
        qtechInitHandoffRequestsSent,
        qtechInitHandoffReplyReceived,
        qtechInitHandoffasLocalReceived,
        qtechInitHandoffasForeignReceived,
        qtechInitHandoffDenyReceived,
        qtechInitAnchorRequestSent,
        qtechInitAnchorDenyReceived,
        qtechAPPriorityEnable,
        qtechPrimaryBackUpACIP,
        qtechPrimaryBackUpACName,
        qtechSecondaryBackUpACIP,
        qtechSecondaryBackUpACName,
        qtechTeriaryBackUpACip,
        qtechTeriaryBackUpACName,
        qtechACIntraRoam,
        qtechACInterRoamIn,
        qtechACInterRoamOut,
        qtechMobilityACPingIPv6,
--ROAM IPv6 Member
        qtechRoamIPv6MemberGroupId,
        qtechRoamIPv6MemberPeerAddress,
        qtechRoamIPv6MemberIsList,
        qtechRoamIPv6MemberDataChannelIsOK,
        qtechRoamIPv6MemberDataChannelFailTimes,
        qtechRoamIPv6MemberDTLSIsClient,
        qtechRoamIPv6MemberDTLSIsOK,
        qtechRoamIPv6MemberCreateStatus,
--ROAM User Entry
        qtechRoamUserMac,
        qtechRoamUserRoamType,
        qtechRoamUserRoamOutAcAddressType,
        qtechRoamUserRoamOutAcAddress,
        qtechRoamUserRoamInAcAddressType,
        qtechRoamUserRoamInAcAddress,
        qtechRoamUserRoamOutApMac,
        qtechRoamUserRoamInApMac,
        qtechRoamUserRoamOutVid,
        qtechRoamUserRoamInVid,
--ROAM Track Entry
        qtechRoamTrackStaMac,
        qtechRoamTrackId,
        qtechRoamTrackAcAddressType,
        qtechRoamTrackAcAddress,
        qtechRoamTrackApMac,
        qtechRoamTrackRadioId,
        qtechRoamTrackStaIp,
        qtechRoamTrackStaIpv6,
        qtechRoamTrackStaOnlineTime
      }
      STATUS current
      DESCRIPTION
               "A collection of objects providing mobility configure."
      ::= {qtechMobilityMIBGroups 1 }


qtechMobilityTrapSta       OBJECT IDENTIFIER ::= { qtechMobilityTrap 1 }
qtechMobilityTrapStaIf     OBJECT IDENTIFIER ::= { qtechMobilityTrap 2 }

-- ****************************************
--
--               Notify nodes
--
-- ****************************************
qtechMobilityNotifyApMac OBJECT-TYPE
    SYNTAX      MacAddress
    MAX-ACCESS  accessible-for-notify
    STATUS      current
    DESCRIPTION
        "Represents the unique identifier of a WTP."
    ::= { qtechMobilityTrapSta 1 }

qtechMobilityNotifyStaMac OBJECT-TYPE
    SYNTAX      MacAddress
    MAX-ACCESS  accessible-for-notify
    STATUS      current
    DESCRIPTION
        "Represents the unique identifier of a STA."
    ::= { qtechMobilityTrapSta 2 }

qtechMobilityNotifyApIp OBJECT-TYPE
    SYNTAX      IpAddress
    MAX-ACCESS  accessible-for-notify
    STATUS      current
    DESCRIPTION
        "Represents the Ip address of a WTP."
    ::= { qtechMobilityTrapSta 3 }

qtechMobilityNotifyStaIp OBJECT-TYPE
    SYNTAX      IpAddress
    MAX-ACCESS  accessible-for-notify
    STATUS      current
    DESCRIPTION
        "Represents the Ip of a STA."
    ::= { qtechMobilityTrapSta 4 }

qtechMobilityNotifyStaOperType OBJECT-TYPE
    SYNTAX      INTEGER
    MAX-ACCESS  accessible-for-notify
    STATUS      current
    DESCRIPTION
        "Represents the STA operation, 1-del,2-add,3-roaming,4-ipupdate,5-ipv6update"
    ::= { qtechMobilityTrapSta 5 }

qtechMobilityNotifyStaApRadioId OBJECT-TYPE
    SYNTAX      INTEGER(1..2)
    MAX-ACCESS  accessible-for-notify
    STATUS      current
    DESCRIPTION
        "Represents the radio id which STA attach."
    ::= { qtechMobilityTrapSta 6 }

qtechMobilityNotifyStaApRadioType OBJECT-TYPE
    SYNTAX      INTEGER (1..2)
    MAX-ACCESS  accessible-for-notify
    STATUS      current
    DESCRIPTION
              "1--802.11b
               2--802.11a"
    ::= { qtechMobilityTrapSta 7 }

qtechMobilityNotifyStaVlanId OBJECT-TYPE
    SYNTAX      INTEGER (1..4094)
    MAX-ACCESS  accessible-for-notify
    STATUS      current
    DESCRIPTION
              "Vlan Id the sta belongs to"
    ::= { qtechMobilityTrapSta 8 }

qtechMobilityNotifyStaWlanId OBJECT-TYPE
    SYNTAX      INTEGER (1..4095)
    MAX-ACCESS  accessible-for-notify
    STATUS      current
    DESCRIPTION
              "Wlan Id the sta belongs to"
    ::= { qtechMobilityTrapSta 9 }

qtechMobilityNotifyStaIpv6 OBJECT-TYPE
    SYNTAX      Ipv6Address
    MAX-ACCESS  accessible-for-notify
    STATUS      current
    DESCRIPTION
              "Sta ipv6 address."
    ::= { qtechMobilityTrapSta 10 }

qtechMobilityNotifyStaAssoAuthMode  OBJECT-TYPE
    SYNTAX  INTEGER {
        open(0),
        wep(1),
        dot1x-wep(2),
        dot1x-wpa(3),
        dot1x-wpa2(4),
        mab(5),
        psk-wpa(6),
        psk-wpa2(7),
        wapi(8)
    }
    MAX-ACCESS  accessible-for-notify
    STATUS  current
    DESCRIPTION
            "The Sta associate authentication mode."
    ::= { qtechMobilityTrapSta 11}

qtechMobilityNotifyStaNetAuthMode  OBJECT-TYPE
    SYNTAX  INTEGER {
        open(0),
        web(1)
    }
    MAX-ACCESS  accessible-for-notify
    STATUS  current
    DESCRIPTION
            "The Sta's authentication mode after associated."
    ::= { qtechMobilityTrapSta 12}

qtechMobilityNotifyStaSsid  OBJECT-TYPE
    SYNTAX  DisplayString
    MAX-ACCESS  accessible-for-notify
    STATUS  current
    DESCRIPTION
            "The wlan ssid with the sta associated."
    ::= { qtechMobilityTrapSta 13}

qtechMobilityNotifyStaLinkRate  OBJECT-TYPE
    SYNTAX  INTEGER
    MAX-ACCESS  accessible-for-notify
    STATUS  current
    DESCRIPTION
            "The link rate with the sta associated, unit: 1kbps."
    ::= { qtechMobilityTrapSta 14}

qtechMobilityNotifyStaCurChan  OBJECT-TYPE
    SYNTAX  INTEGER
    MAX-ACCESS  accessible-for-notify
    STATUS  current
    DESCRIPTION
            "The Sta current use channel after associated."
    ::= { qtechMobilityTrapSta 15}

qtechMobilityNotifyStaClientType  OBJECT-TYPE
    SYNTAX  DisplayString
    MAX-ACCESS  accessible-for-notify
    STATUS  current
    DESCRIPTION
            "The Sta's type."
    ::= { qtechMobilityTrapSta 16}

qtechMobilityNotifyStaRssi OBJECT-TYPE
    SYNTAX  INTEGER
    MAX-ACCESS  accessible-for-notify
    STATUS  current
    DESCRIPTION
            "The Sta's RSSI."
    ::= { qtechMobilityTrapSta 17}

qtechMobilityNotifyStaReason OBJECT-TYPE
    SYNTAX  DisplayString
    MAX-ACCESS  accessible-for-notify
    STATUS  current
    DESCRIPTION
            "The Sta's down reason."
    ::= { qtechMobilityTrapSta 18}

qtechMobilityNotifyStaOper NOTIFICATION-TYPE
    OBJECTS     {
                  qtechMobilityNotifyApMac,
                  qtechMobilityNotifyStaMac,
                  qtechMobilityNotifyApIp,
                  qtechMobilityNotifyStaIp,
                  qtechMobilityNotifyStaOperType,
                  qtechMobilityNotifyStaApRadioId,
                  qtechMobilityNotifyStaApRadioType,
                  qtechMobilityNotifyStaVlanId,
                  qtechMobilityNotifyStaWlanId,
                  qtechMobilityNotifyStaIpv6,
                  qtechMobilityNotifyStaAssoAuthMode,
                  qtechMobilityNotifyStaNetAuthMode,
                  qtechMobilityNotifyStaSsid,
                  qtechMobilityNotifyStaLinkRate,
                  qtechMobilityNotifyStaCurChan,
                  qtechMobilityNotifyStaClientType,
                  qtechMobilityNotifyStaRssi,
                  qtechMobilityNotifyStaReason
                }
    STATUS      current
    DESCRIPTION
        "This notification is sent by the AC when a sta enter or quit or ip update."
    ::= { qtechMobilityTrapStaIf 1 }

END
