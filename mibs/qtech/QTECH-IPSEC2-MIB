--
-- QTECH-IPSEC2-MIB.mib
-- MIB generated by MG-SOFT Visual MIB Builder Version 6.0  Build 88
-- Tuesday, February 14, 2012 at 13:07:15
--

	QTECH-IPSEC2-MIB DEFINITIONS ::= BEGIN

		IMPORTS
			OBJECT-GROUP, MODULE-COMPLIANCE, NOTIFICATION-GROUP
				FROM SNMPv2-CONF
			IpAddress, Integer32, Unsigned32, Gauge32, Counter32,
			Counter64, OBJECT-TYPE, NOTIFICATION-TYPE
				FROM SNMPv2-SMI
			DisplayString, TimeStamp, TEXTUAL-CONVENTION
				FROM SNMPv2-TC
			qtechMgmt
                                 FROM QTECH-SMI;

        qtechIPSec2MibModule MODULE-IDENTITY
			LAST-UPDATED "201112191637Z"		-- December 19, 2011 at 16:37 GMT
			ORGANIZATION
				"Organization."
			CONTACT-INFO
				"Contact-info."
			DESCRIPTION
				"Description."
			::= { qtechMgmt 108 }


--
-- Textual conventions
--

		QtechIPSecNegoType ::= TEXTUAL-CONVENTION
			STATUS current
			DESCRIPTION
				"The type of key used by an IPSec Phase-2 Tunnel. invalidType(2147483647)
				is defined as invalid value."
			SYNTAX INTEGER
				{
				ike(1),
				manual(2),
				invalidType(2147483647)
				}

		QtechEncapMode ::= TEXTUAL-CONVENTION
			STATUS current
			DESCRIPTION
				"The encapsulation mode used by an IPSec Phase-2 Tunnel."
			SYNTAX INTEGER
				{
				tunnel(1),
				transport(2),
				invalidMode(2147483647)
				}

		QtechEncryptAlgo ::= TEXTUAL-CONVENTION
			STATUS current
			DESCRIPTION
				"The encryption algorithm used in the IKE and IPSec negotiations.
				invalidAlg(2147483647) is defined as invalid value."
			SYNTAX INTEGER
				{
				none(0),
				desCbc(2),
				threedesCbc(3),
				aesCbc(12),
				sm1Cbc(128),
				invalidAlg(2147483647)
				}

		QtechAuthAlgo ::= TEXTUAL-CONVENTION
			STATUS current
			DESCRIPTION
				"The authentication algorithm used in the IKE negotiations.
				invalidAlg(2147483647) is defined as invalid value."
			SYNTAX INTEGER
				{
				none(0),
				md5(2),
				sha(3),
				invalidAlg(2147483647)
				}

		QtechDiffHellmanGrp ::= TEXTUAL-CONVENTION
			STATUS current
			DESCRIPTION
				"The Diffie Hellman Group used in the IKE and IPSec negotiations.
				invalidAlg(2147483647) is defined as invalid value."
			SYNTAX INTEGER
				{
				modp768(1),
				modp1024(2),
				invalidMode(2147483647)
				}

		QtechIPSecTunnelState ::= TEXTUAL-CONVENTION
			STATUS current
			DESCRIPTION
				"The state of IPSec tunnel."
			SYNTAX INTEGER
				{
				establishing(1),
				active(2),
				expiring(3)
				}

		QtechSaProtocol ::= TEXTUAL-CONVENTION
			STATUS current
			DESCRIPTION
				"The protocol of security association."
			SYNTAX INTEGER
				{
				reserved(0),
				isakmp(1),
				ah(2),
				esp(3)
				}

		QtechTrafficType ::= TEXTUAL-CONVENTION
			STATUS current
			DESCRIPTION
				"The type of the data flow."
			SYNTAX INTEGER
				{
				ipv4Addr(1),
				ipv4AddrSubnet(2),
				ipv6Addr(3),
				ipv6AddrSubnet(4),
				ipv4AddrRange(5),
				ipv6AddrRange(6)
				}

--  1.3.6.1.4.1.27514.1.1.10.2.108.1
-- December 19, 2011 at 16:37 GMT
--
-- Textual conventions
--
		QtechIPSec2NegoType ::= TEXTUAL-CONVENTION
			STATUS current
			DESCRIPTION
				"The type of key used by an IPSec Phase-2 Tunnel. invalidType(2147483647)
				is defined as invalid value."
			SYNTAX INTEGER
				{
				ike(1),
				manual(2),
				invalidType(2147483647)
				}

		QtechIPSec2TunnelState ::= TEXTUAL-CONVENTION
			STATUS current
			DESCRIPTION
				"The state of IPSec tunnel."
			SYNTAX INTEGER
				{
				establishing(1),
				active(2),
				expiring(3)
				}


--
-- Node definitions
--

		-- 1.3.6.1.4.1.27514.1.1.10.2.108.1
		qtechIPSec2Objects OBJECT IDENTIFIER ::= { qtechIPSec2MibModule 1 }


		-- 1.3.6.1.4.1.27514.1.1.10.2.108.1.1
		qtechIPSec2TunnelTable OBJECT-TYPE
			SYNTAX SEQUENCE OF QtechIPSec2TunnelEntry
			MAX-ACCESS not-accessible
			STATUS current
			DESCRIPTION
				"The IPSec Phase-2 Tunnel Table. There is one
				entry in this table for each active IPSec Phase-2 Tunnel."
			::= { qtechIPSec2Objects 1 }


		-- 1.3.6.1.4.1.27514.1.1.10.2.108.1.1.1
		qtechIPSec2TunnelEntry OBJECT-TYPE
			SYNTAX QtechIPSec2TunnelEntry
			MAX-ACCESS not-accessible
			STATUS current
			DESCRIPTION
				"Information about QtechIPSec2TunnelTable."
			INDEX { qtechIPSec2TunIfIndex, qtechIPSec2TunRemoteAddr, qtechIPSec2TrafficLocalType, qtechIPSec2TrafficLocalProtocol, qtechIPSec2TrafficLocalAddr1,
				qtechIPSec2TrafficLocalAddr2, qtechIPSec2TrafficLocalPort, qtechIPSec2TrafficRemoteAddr1, qtechIPSec2TrafficRemoteAddr2, qtechIPSec2TrafficRemotePort
				 }
			::= { qtechIPSec2TunnelTable 1 }


		QtechIPSec2TunnelEntry ::=
			SEQUENCE {
				qtechIPSec2TunIfIndex
					Integer32,
				qtechIPSec2TunnelTrafficIndex
					Integer32,
				qtechIPSec2TunIndex
					Integer32,
				qtechIPSec2TunIKETunnelIndex
					Integer32,
				qtechIPSec2TunnelAhOutSaIndex
					Integer32,
				qtechIPSec2TunnelAhInSaIndex
					Integer32,
				qtechIPSec2TunnelEspOutSaIndex
					Integer32,
				qtechIPSec2TunnelEspInSaIndex
					Integer32,
				qtechIPSec2TunLocalAddr
					IpAddress,
				qtechIPSec2TunRemoteAddr
					IpAddress,
				qtechIPSec2TunLocalHostname
					DisplayString,
				qtechIPSec2TunRemoteHostname
					DisplayString,
				qtechIPSec2TunKeyType
					QtechIPSec2NegoType,
				qtechIPSec2TunEncapMode
					QtechEncapMode,
				qtechIPSec2TunInitiator
					INTEGER,
				qtechIPSec2TunLifeSize
					Integer32,
				qtechIPSec2TunLifeTime
					Integer32,
				qtechIPSec2TunRemainTime
					Integer32,
				qtechIPSec2TunActiveTime
					Integer32,
				qtechIPSec2TunCreateTime
					TimeStamp,
				qtechIPSec2TunRemainSize
					Integer32,
				qtechIPSec2TunTotalRefreshes
					Counter32,
				qtechIPSec2TunCurrentSaInstances
					Gauge32,
				qtechIPSec2TunInSaEncryptAlgo
					QtechEncryptAlgo,
				qtechIPSec2TunInSaAhAuthAlgo
					QtechAuthAlgo,
				qtechIPSec2TunInSaEspAuthAlgo
					QtechAuthAlgo,
				qtechIPSec2TunDiffHellmanGrp
					QtechDiffHellmanGrp,
				qtechIPSec2TunOutSaEncryptAlgo
					QtechEncryptAlgo,
				qtechIPSec2TunOutSaAhAuthAlgo
					QtechAuthAlgo,
				qtechIPSec2TunOutSaEspAuthAlgo
					QtechAuthAlgo,
				qtechIPSec2TunMapName
					DisplayString,
				qtechIPSec2TunSeqNum
					Integer32,
				qtechIPSec2TunStatus
					QtechIPSec2TunnelState
			 }

		-- 1.3.6.1.4.1.27514.1.1.10.2.108.1.1.1.1
		qtechIPSec2TunIfIndex OBJECT-TYPE
			SYNTAX Integer32 (1..2147483647)
			MAX-ACCESS read-only
			STATUS current
			DESCRIPTION
				"The interface index( the ifIndex of ifTable )."
			::= { qtechIPSec2TunnelEntry 1 }


		-- 1.3.6.1.4.1.27514.1.1.10.2.108.1.1.1.2
		qtechIPSec2TunnelTrafficIndex OBJECT-TYPE
			SYNTAX Integer32
			MAX-ACCESS read-only
			STATUS current
			DESCRIPTION
				"Description."
			::= { qtechIPSec2TunnelEntry 2 }


		-- 1.3.6.1.4.1.27514.1.1.10.2.108.1.1.1.3
		qtechIPSec2TunIndex OBJECT-TYPE
			SYNTAX Integer32 (1..2147483647)
			MAX-ACCESS read-only
			STATUS current
			DESCRIPTION
				"The index of IPSec Phase-2 Tunnel Table. The value of
				the index is a number which begins at one and is
				incremented with each tunnel that is created. The
				value of this object will wrap at 2,147,483,647."
			::= { qtechIPSec2TunnelEntry 3 }


		-- 1.3.6.1.4.1.27514.1.1.10.2.108.1.1.1.5
		qtechIPSec2TunIKETunnelIndex OBJECT-TYPE
			SYNTAX Integer32 (1..2147483647)
			MAX-ACCESS read-only
			STATUS current
			DESCRIPTION
				"The index of the associated IPSec Phase-1 IKE Tunnel
				(IKETunIndex in the IKETunnelTable). 2147483647 is defined as
				invalid value. "
			::= { qtechIPSec2TunnelEntry 5 }


		-- 1.3.6.1.4.1.27514.1.1.10.2.108.1.1.1.6
		qtechIPSec2TunnelAhOutSaIndex OBJECT-TYPE
			SYNTAX Integer32
			MAX-ACCESS read-only
			STATUS current
			DESCRIPTION
				"Description."
			::= { qtechIPSec2TunnelEntry 6 }


		-- 1.3.6.1.4.1.27514.1.1.10.2.108.1.1.1.7
		qtechIPSec2TunnelAhInSaIndex OBJECT-TYPE
			SYNTAX Integer32 (1..2147483647)
			MAX-ACCESS read-only
			STATUS current
			DESCRIPTION
				"The index of the associated IPSec Phase-1 IKE Tunnel
				(IKETunIndex in the IKETunnelTable). 2147483647 is defined as
				invalid value. "
			::= { qtechIPSec2TunnelEntry 7 }


		-- 1.3.6.1.4.1.27514.1.1.10.2.108.1.1.1.8
		qtechIPSec2TunnelEspOutSaIndex OBJECT-TYPE
			SYNTAX Integer32 (1..2147483647)
			MAX-ACCESS read-only
			STATUS current
			DESCRIPTION
				"The index of the associated IPSec Phase-1 IKE Tunnel
				(IKETunIndex in the IKETunnelTable). 2147483647 is defined as
				invalid value. "
			::= { qtechIPSec2TunnelEntry 8 }


		-- 1.3.6.1.4.1.27514.1.1.10.2.108.1.1.1.9
		qtechIPSec2TunnelEspInSaIndex OBJECT-TYPE
			SYNTAX Integer32
			MAX-ACCESS read-only
			STATUS current
			DESCRIPTION
				"Description."
			::= { qtechIPSec2TunnelEntry 9 }


		-- 1.3.6.1.4.1.27514.1.1.10.2.108.1.1.1.10
		qtechIPSec2TunLocalAddr OBJECT-TYPE
			SYNTAX IpAddress
			MAX-ACCESS read-only
			STATUS current
			DESCRIPTION
				"The IP address of the local peer for the IPSec Phase-2
				Tunnel. 0.0.0.0 is defined as invalid value."
			::= { qtechIPSec2TunnelEntry 10 }


		-- 1.3.6.1.4.1.27514.1.1.10.2.108.1.1.1.11
		qtechIPSec2TunRemoteAddr OBJECT-TYPE
			SYNTAX IpAddress
			MAX-ACCESS read-only
			STATUS current
			DESCRIPTION
				"The IP address of the remote peer for the IPSec Phase-2
				Tunnel. 0.0.0.0 is defined as invalid value."
			::= { qtechIPSec2TunnelEntry 11 }


		-- 1.3.6.1.4.1.27514.1.1.10.2.108.1.1.1.12
		qtechIPSec2TunLocalHostname OBJECT-TYPE
			SYNTAX DisplayString
			MAX-ACCESS read-only
			STATUS current
			DESCRIPTION
				"The Hostname of the local peer for the IPSec Phase-2
				Tunnel."
			::= { qtechIPSec2TunnelEntry 12 }


		-- 1.3.6.1.4.1.27514.1.1.10.2.108.1.1.1.13
		qtechIPSec2TunRemoteHostname OBJECT-TYPE
			SYNTAX DisplayString
			MAX-ACCESS read-only
			STATUS current
			DESCRIPTION
				"The Hostname of the remote peer for the IPSec Phase-2
				Tunnel. "
			::= { qtechIPSec2TunnelEntry 13 }


		-- 1.3.6.1.4.1.27514.1.1.10.2.108.1.1.1.14
		qtechIPSec2TunKeyType OBJECT-TYPE
			SYNTAX QtechIPSec2NegoType
			MAX-ACCESS read-only
			STATUS current
			DESCRIPTION
				"The key negotiate mode used by the IPSec Phase-2 Tunnel."
			::= { qtechIPSec2TunnelEntry 14 }


		-- 1.3.6.1.4.1.27514.1.1.10.2.108.1.1.1.15
		qtechIPSec2TunEncapMode OBJECT-TYPE
			SYNTAX QtechEncapMode
			MAX-ACCESS read-only
			STATUS current
			DESCRIPTION
				"The encapsulation mode used by the IPSec Phase-2 Tunnel."
			::= { qtechIPSec2TunnelEntry 15 }


		-- 1.3.6.1.4.1.27514.1.1.10.2.108.1.1.1.16
		qtechIPSec2TunInitiator OBJECT-TYPE
			SYNTAX INTEGER
				{
				local(1),
				remote(2),
				none(2147483647)
				}
			MAX-ACCESS read-only
			STATUS current
			DESCRIPTION
				"The initiator of this IPSec tunnel. Value none is used for manual
				IPsec tunnel, for there is no initiator or responder in this method."
			::= { qtechIPSec2TunnelEntry 16 }


		-- 1.3.6.1.4.1.27514.1.1.10.2.108.1.1.1.17
		qtechIPSec2TunLifeSize OBJECT-TYPE
			SYNTAX Integer32 (1..2147483647)
			MAX-ACCESS read-only
			STATUS current
			DESCRIPTION
				"The negotiated LifeSize of the IPSec Phase-2 Tunnel in kilobytes.
				2147483647 is defined as invalid value."
			::= { qtechIPSec2TunnelEntry 17 }


		-- 1.3.6.1.4.1.27514.1.1.10.2.108.1.1.1.18
		qtechIPSec2TunLifeTime OBJECT-TYPE
			SYNTAX Integer32 (1..2147483647)
			MAX-ACCESS read-only
			STATUS current
			DESCRIPTION
				"The negotiated LifeTime of the IPSec Phase-2 Tunnel in seconds.
				2147483647 is defined as invalid value."
			::= { qtechIPSec2TunnelEntry 18 }


		-- 1.3.6.1.4.1.27514.1.1.10.2.108.1.1.1.19
		qtechIPSec2TunRemainTime OBJECT-TYPE
			SYNTAX Integer32 (0..2147483647)
			MAX-ACCESS read-only
			STATUS current
			DESCRIPTION
				"The remain time of SA in seconds. 2147483647 is defined as invalid
				value."
			::= { qtechIPSec2TunnelEntry 19 }


		-- 1.3.6.1.4.1.27514.1.1.10.2.108.1.1.1.20
		qtechIPSec2TunActiveTime OBJECT-TYPE
			SYNTAX Integer32 (0..2147483647)
			MAX-ACCESS read-only
			STATUS current
			DESCRIPTION
				"The duration the IPSec Phase-2 Tunnel has been active in
				hundredths of seconds. 2147483647 is defined as invalid value."
			::= { qtechIPSec2TunnelEntry 20 }


		-- 1.3.6.1.4.1.27514.1.1.10.2.108.1.1.1.21
		qtechIPSec2TunCreateTime OBJECT-TYPE
			SYNTAX TimeStamp
			MAX-ACCESS read-only
			STATUS current
			DESCRIPTION
				"The Time Stamp when the IPSec Phase-2 Tunnel created."
			::= { qtechIPSec2TunnelEntry 21 }


		-- 1.3.6.1.4.1.27514.1.1.10.2.108.1.1.1.23
		qtechIPSec2TunRemainSize OBJECT-TYPE
			SYNTAX Integer32 (0..2147483647)
			MAX-ACCESS read-only
			STATUS current
			DESCRIPTION
				"The remain LifeSize of SA in kilobytes. 2147483647 is defined as
				invalid value."
			::= { qtechIPSec2TunnelEntry 23 }


		-- 1.3.6.1.4.1.27514.1.1.10.2.108.1.1.1.24
		qtechIPSec2TunTotalRefreshes OBJECT-TYPE
			SYNTAX Counter32
			MAX-ACCESS read-only
			STATUS current
			DESCRIPTION
				"The total number of security association refreshing performed."
			::= { qtechIPSec2TunnelEntry 24 }


		-- 1.3.6.1.4.1.27514.1.1.10.2.108.1.1.1.25
		qtechIPSec2TunCurrentSaInstances OBJECT-TYPE
			SYNTAX Gauge32
			MAX-ACCESS read-only
			STATUS current
			DESCRIPTION
				"The number of security associations which are currently active
				or expiring."
			::= { qtechIPSec2TunnelEntry 25 }


		-- 1.3.6.1.4.1.27514.1.1.10.2.108.1.1.1.26
		qtechIPSec2TunInSaEncryptAlgo OBJECT-TYPE
			SYNTAX QtechEncryptAlgo
			MAX-ACCESS read-only
			STATUS current
			DESCRIPTION
				"The encryption algorithm used by the inbound security association
				of the IPSec Phase-2 Tunnel."
			::= { qtechIPSec2TunnelEntry 26 }


		-- 1.3.6.1.4.1.27514.1.1.10.2.108.1.1.1.27
		qtechIPSec2TunInSaAhAuthAlgo OBJECT-TYPE
			SYNTAX QtechAuthAlgo
			MAX-ACCESS read-only
			STATUS current
			DESCRIPTION
				"The authentication algorithm used by the inbound authentication
				header (AH) security association of the IPSec Phase-2 Tunnel."
			::= { qtechIPSec2TunnelEntry 27 }


		-- 1.3.6.1.4.1.27514.1.1.10.2.108.1.1.1.28
		qtechIPSec2TunInSaEspAuthAlgo OBJECT-TYPE
			SYNTAX QtechAuthAlgo
			MAX-ACCESS read-only
			STATUS current
			DESCRIPTION
				"The authentication algorithm used by the inbound encapsulation
				security protocol(ESP) security association of the IPSec
				Phase-2 Tunnel."
			::= { qtechIPSec2TunnelEntry 28 }


		-- 1.3.6.1.4.1.27514.1.1.10.2.108.1.1.1.29
		qtechIPSec2TunDiffHellmanGrp OBJECT-TYPE
			SYNTAX QtechDiffHellmanGrp
			MAX-ACCESS read-only
			STATUS current
			DESCRIPTION
				"The Diffie Hellman Group used by the security association of the
				IPSec Phase-2 Tunnel."
			::= { qtechIPSec2TunnelEntry 29 }


		-- 1.3.6.1.4.1.27514.1.1.10.2.108.1.1.1.30
		qtechIPSec2TunOutSaEncryptAlgo OBJECT-TYPE
			SYNTAX QtechEncryptAlgo
			MAX-ACCESS read-only
			STATUS current
			DESCRIPTION
				"The encryption algorithm used by the outbound security
				association of the IPSec Phase-2 Tunnel."
			::= { qtechIPSec2TunnelEntry 30 }


		-- 1.3.6.1.4.1.27514.1.1.10.2.108.1.1.1.31
		qtechIPSec2TunOutSaAhAuthAlgo OBJECT-TYPE
			SYNTAX QtechAuthAlgo
			MAX-ACCESS read-only
			STATUS current
			DESCRIPTION
				"The authentication algorithm used by the outbound
				authentication header (AH) security association of
				the IPSec Phase-2 Tunnel."
			::= { qtechIPSec2TunnelEntry 31 }


		-- 1.3.6.1.4.1.27514.1.1.10.2.108.1.1.1.32
		qtechIPSec2TunOutSaEspAuthAlgo OBJECT-TYPE
			SYNTAX QtechAuthAlgo
			MAX-ACCESS read-only
			STATUS current
			DESCRIPTION
				"The authentication algorithm used by the outbound encapsulation
				security protocol(ESP) security association of the IPSec
				Phase-2 Tunnel."
			::= { qtechIPSec2TunnelEntry 32 }


		-- 1.3.6.1.4.1.27514.1.1.10.2.108.1.1.1.33
		qtechIPSec2TunMapName OBJECT-TYPE
			SYNTAX DisplayString
			MAX-ACCESS read-only
			STATUS current
			DESCRIPTION
				"The Map name used by this IPSec tunnel."
			::= { qtechIPSec2TunnelEntry 33 }


		-- 1.3.6.1.4.1.27514.1.1.10.2.108.1.1.1.34
		qtechIPSec2TunSeqNum OBJECT-TYPE
			SYNTAX Integer32 (1..2147483647)
			MAX-ACCESS read-only
			STATUS current
			DESCRIPTION
				"The sequence number of policy used by this IPSec tunnel."
			::= { qtechIPSec2TunnelEntry 34 }


		-- 1.3.6.1.4.1.27514.1.1.10.2.108.1.1.1.35
		qtechIPSec2TunStatus OBJECT-TYPE
			SYNTAX QtechIPSec2TunnelState
			MAX-ACCESS read-write
			STATUS current
			DESCRIPTION
				"The status of the IPSec Tunnel."
			::= { qtechIPSec2TunnelEntry 35 }


		-- 1.3.6.1.4.1.27514.1.1.10.2.108.1.2
		qtechIPSec2TunnelStatTable OBJECT-TYPE
			SYNTAX SEQUENCE OF QtechIPSec2TunnelStatEntry
			MAX-ACCESS not-accessible
			STATUS current
			DESCRIPTION
				"The IPSec Phase-2 Tunnel Statistics Table. "
			::= { qtechIPSec2Objects 2 }


		-- 1.3.6.1.4.1.27514.1.1.10.2.108.1.2.1
		qtechIPSec2TunnelStatEntry OBJECT-TYPE
			SYNTAX QtechIPSec2TunnelStatEntry
			MAX-ACCESS not-accessible
			STATUS current
			DESCRIPTION
				"Information about QtechIPSec2TunnelStatTable."
			INDEX { qtechIPSec2TunIndex }
			::= { qtechIPSec2TunnelStatTable 1 }


		QtechIPSec2TunnelStatEntry ::=
			SEQUENCE {
				qtechIPSec2TunInOctets
					Counter64,
				qtechIPSec2TunInDecompOctets
					Counter64,
				qtechIPSec2TunInPkts
					Counter64,
				qtechIPSec2TunInSpeed
					Counter64,
				qtechIPSec2TunInDropPkts
					Counter64,
				qtechIPSec2TunOutOctets
					Counter64,
				qtechIPSec2TunOutUncompOctets
					Counter64,
				qtechIPSec2TunOutPkts
					Counter64,
				qtechIPSec2TunOutSpeed
					Counter64,
				qtechIPSec2TunOutDropPkts
					Counter64
			 }

		-- 1.3.6.1.4.1.27514.1.1.10.2.108.1.2.1.1
		qtechIPSec2TunInOctets OBJECT-TYPE
			SYNTAX Counter64
			MAX-ACCESS read-only
			STATUS current
			DESCRIPTION
				"The total number of octets received by this IPSec Phase-2 Tunnel.
				This value is accumulated BEFORE determining whether or not the
				packet should be decompressed."
			::= { qtechIPSec2TunnelStatEntry 1 }


		-- 1.3.6.1.4.1.27514.1.1.10.2.108.1.2.1.2
		qtechIPSec2TunInDecompOctets OBJECT-TYPE
			SYNTAX Counter64
			MAX-ACCESS read-only
			STATUS current
			DESCRIPTION
				"The total number of decompressed octets received by this IPSec
				Phase-2 Tunnel. This value is accumulated AFTER the packet
				is decompressed."
			::= { qtechIPSec2TunnelStatEntry 2 }


		-- 1.3.6.1.4.1.27514.1.1.10.2.108.1.2.1.3
		qtechIPSec2TunInPkts OBJECT-TYPE
			SYNTAX Counter64
			MAX-ACCESS read-only
			STATUS current
			DESCRIPTION
				"The total number of packets received by this IPSec Phase-2 Tunnel."
			::= { qtechIPSec2TunnelStatEntry 3 }


		-- 1.3.6.1.4.1.27514.1.1.10.2.108.1.2.1.4
		qtechIPSec2TunInSpeed OBJECT-TYPE
			SYNTAX Counter64
			MAX-ACCESS read-only
			STATUS current
			DESCRIPTION
				"The Speed(bps) of packets received by this IPSec Phase-2 Tunnel."
			::= { qtechIPSec2TunnelStatEntry 4 }


		-- 1.3.6.1.4.1.27514.1.1.10.2.108.1.2.1.5
		qtechIPSec2TunInDropPkts OBJECT-TYPE
			SYNTAX Counter64
			MAX-ACCESS read-only
			STATUS current
			DESCRIPTION
				"The total number of packets dropped during receiving process
				by this IPSec Phase-2 Tunnel."
			::= { qtechIPSec2TunnelStatEntry 5 }


		-- 1.3.6.1.4.1.27514.1.1.10.2.108.1.2.1.6
		qtechIPSec2TunOutOctets OBJECT-TYPE
			SYNTAX Counter64
			MAX-ACCESS read-only
			STATUS current
			DESCRIPTION
				"The total number of octets sent by this IPSec Phase-2 Tunnel.
				This value is accumulated AFTER determining whether or not
				the packet should be compressed."
			::= { qtechIPSec2TunnelStatEntry 6 }


		-- 1.3.6.1.4.1.27514.1.1.10.2.108.1.2.1.7
		qtechIPSec2TunOutUncompOctets OBJECT-TYPE
			SYNTAX Counter64
			MAX-ACCESS read-only
			STATUS current
			DESCRIPTION
				"The total number of uncompressed octets sent by this IPSec Phase-2
				Tunnel.This value is accumulated BEFORE the packet is compressed."
			::= { qtechIPSec2TunnelStatEntry 7 }


		-- 1.3.6.1.4.1.27514.1.1.10.2.108.1.2.1.8
		qtechIPSec2TunOutPkts OBJECT-TYPE
			SYNTAX Counter64
			MAX-ACCESS read-only
			STATUS current
			DESCRIPTION
				"The total number of packets sent by this IPSec Phase-2 Tunnel."
			::= { qtechIPSec2TunnelStatEntry 8 }


		-- 1.3.6.1.4.1.27514.1.1.10.2.108.1.2.1.9
		qtechIPSec2TunOutSpeed OBJECT-TYPE
			SYNTAX Counter64
			MAX-ACCESS read-only
			STATUS current
			DESCRIPTION
				"The Speed(bps) of packets sent by this IPSec Phase-2 Tunnel. "
			::= { qtechIPSec2TunnelStatEntry 9 }


		-- 1.3.6.1.4.1.27514.1.1.10.2.108.1.2.1.10
		qtechIPSec2TunOutDropPkts OBJECT-TYPE
			SYNTAX Counter64
			MAX-ACCESS read-only
			STATUS current
			DESCRIPTION
				"The total number of packets dropped during sending process
				by this IPSec Phase-2 Tunnel."
			::= { qtechIPSec2TunnelStatEntry 10 }


		-- 1.3.6.1.4.1.27514.1.1.10.2.108.1.3
		qtechIPSec2SaTable OBJECT-TYPE
			SYNTAX SEQUENCE OF QtechIPSec2SaEntry
			MAX-ACCESS not-accessible
			STATUS current
			DESCRIPTION
				"The IPSec Phase-2 Security Protection Index Table.  This table
				contains an entry for each active and expiring security association."
			::= { qtechIPSec2Objects 3 }


		-- 1.3.6.1.4.1.27514.1.1.10.2.108.1.3.1
		qtechIPSec2SaEntry OBJECT-TYPE
			SYNTAX QtechIPSec2SaEntry
			MAX-ACCESS not-accessible
			STATUS current
			DESCRIPTION
				"Information about QtechIPSec2SaTable."
			INDEX { qtechIPSec2SaIndex }
			::= { qtechIPSec2SaTable 1 }


		QtechIPSec2SaEntry ::=
			SEQUENCE {
				qtechIPSec2SaIndex
					Integer32,
				qtechIPSec2SaDirection
					INTEGER,
				qtechIPSec2SaValue
					Unsigned32,
				qtechIPSec2SaProtocol
					QtechSaProtocol,
				qtechIPSec2SaEncryptAlgo
					QtechEncryptAlgo,
				qtechIPSec2SaAuthAlgo
					QtechAuthAlgo,
				qtechIPSec2SaStatus
					QtechIPSec2TunnelState
			 }

		-- 1.3.6.1.4.1.27514.1.1.10.2.108.1.3.1.1
		qtechIPSec2SaIndex OBJECT-TYPE
			SYNTAX Integer32 (1..2147483647)
			MAX-ACCESS read-only
			STATUS current
			DESCRIPTION
				"The number of the Sa associated with the Phase-2 Tunnel
				Table.  The value of this index is a number which begins
				at one and is incremented with each Sa associated with
				an IPSec Phase-2 Tunnel.  The value of this object will
				wrap at 2,147,483,647."
			::= { qtechIPSec2SaEntry 1 }


		-- 1.3.6.1.4.1.27514.1.1.10.2.108.1.3.1.2
		qtechIPSec2SaDirection OBJECT-TYPE
			SYNTAX INTEGER
				{
				in(1),
				out(2)
				}
			MAX-ACCESS read-only
			STATUS current
			DESCRIPTION
				"The direction of the SA."
			::= { qtechIPSec2SaEntry 2 }


		-- 1.3.6.1.4.1.27514.1.1.10.2.108.1.3.1.3
		qtechIPSec2SaValue OBJECT-TYPE
			SYNTAX Unsigned32 (1..4294967295)
			MAX-ACCESS read-only
			STATUS current
			DESCRIPTION
				"The value of the SPI."
			::= { qtechIPSec2SaEntry 3 }


		-- 1.3.6.1.4.1.27514.1.1.10.2.108.1.3.1.4
		qtechIPSec2SaProtocol OBJECT-TYPE
			SYNTAX QtechSaProtocol
			MAX-ACCESS read-only
			STATUS current
			DESCRIPTION
				"The security protocol of the SA."
			::= { qtechIPSec2SaEntry 4 }


		-- 1.3.6.1.4.1.27514.1.1.10.2.108.1.3.1.5
		qtechIPSec2SaEncryptAlgo OBJECT-TYPE
			SYNTAX QtechEncryptAlgo
			MAX-ACCESS read-only
			STATUS current
			DESCRIPTION
				"The encryption algorithm used by the security association
				of the IPSec Phase-2 Tunnel."
			::= { qtechIPSec2SaEntry 5 }


		-- 1.3.6.1.4.1.27514.1.1.10.2.108.1.3.1.6
		qtechIPSec2SaAuthAlgo OBJECT-TYPE
			SYNTAX QtechAuthAlgo
			MAX-ACCESS read-only
			STATUS current
			DESCRIPTION
				"The authentication algorithm used by the SA."
			::= { qtechIPSec2SaEntry 6 }


		-- 1.3.6.1.4.1.27514.1.1.10.2.108.1.3.1.7
		qtechIPSec2SaStatus OBJECT-TYPE
			SYNTAX QtechIPSec2TunnelState
			MAX-ACCESS read-only
			STATUS current
			DESCRIPTION
				"The status of the SA."
			::= { qtechIPSec2SaEntry 7 }


		-- 1.3.6.1.4.1.27514.1.1.10.2.108.1.4
		qtechIPSec2TrafficTable OBJECT-TYPE
			SYNTAX SEQUENCE OF QtechIPSec2TrafficEntry
			MAX-ACCESS not-accessible
			STATUS current
			DESCRIPTION
				"The IPSec Phase-2 Tunnel Traffic Table. "
			::= { qtechIPSec2Objects 4 }


		-- 1.3.6.1.4.1.27514.1.1.10.2.108.1.4.1
		qtechIPSec2TrafficEntry OBJECT-TYPE
			SYNTAX QtechIPSec2TrafficEntry
			MAX-ACCESS not-accessible
			STATUS current
			DESCRIPTION
				"Information about QtechIPSec2TrafficTable."
			INDEX { qtechIPSec2TunnelTrafficIndex }
			::= { qtechIPSec2TrafficTable 1 }


		QtechIPSec2TrafficEntry ::=
			SEQUENCE {
				qtechIPSec2TrafficIndex
					Integer32,
				qtechIPSec2TrafficLocalType
					QtechTrafficType,
				qtechIPSec2TrafficLocalAddr1
					IpAddress,
				qtechIPSec2TrafficLocalAddr2
					IpAddress,
				qtechIPSec2TrafficLocalProtocol
					Integer32,
				qtechIPSec2TrafficLocalPort
					Integer32,
				qtechIPSec2TrafficLocalHostname
					DisplayString,
				qtechIPSec2TrafficRemoteType
					QtechTrafficType,
				qtechIPSec2TrafficRemoteAddr1
					IpAddress,
				qtechIPSec2TrafficRemoteAddr2
					IpAddress,
				qtechIPSec2TrafficRemoteProtocol
					Integer32,
				qtechIPSec2TrafficRemotePort
					Integer32,
				qtechIPSec2TrafficRemoteHostname
					DisplayString
			 }

		-- 1.3.6.1.4.1.27514.1.1.10.2.108.1.4.1.1
		qtechIPSec2TrafficIndex OBJECT-TYPE
			SYNTAX Integer32
			MAX-ACCESS read-only
			STATUS current
			DESCRIPTION
				"Description."
			::= { qtechIPSec2TrafficEntry 1 }


		-- 1.3.6.1.4.1.27514.1.1.10.2.108.1.4.1.2
		qtechIPSec2TrafficLocalType OBJECT-TYPE
			SYNTAX QtechTrafficType
			MAX-ACCESS read-only
			STATUS current
			DESCRIPTION
				"The type of local peer. Possible values are: a single
				IP address, or an IP address range, or an IP subnet."
			::= { qtechIPSec2TrafficEntry 2 }


		-- 1.3.6.1.4.1.27514.1.1.10.2.108.1.4.1.3
		qtechIPSec2TrafficLocalAddr1 OBJECT-TYPE
			SYNTAX IpAddress
			MAX-ACCESS read-only
			STATUS current
			DESCRIPTION
				"The first specification of local peer's IP address. If
				the local peer type is single IP address, then this is the
				value of the IP address. If the local peer type is IP subnet,
				then this is the value of the subnet. If the local peer type
				is IP address range, then this is the value of beginning IP
				address of the range."
			::= { qtechIPSec2TrafficEntry 3 }


		-- 1.3.6.1.4.1.27514.1.1.10.2.108.1.4.1.4
		qtechIPSec2TrafficLocalAddr2 OBJECT-TYPE
			SYNTAX IpAddress
			MAX-ACCESS read-only
			STATUS current
			DESCRIPTION
				"The second specification of local peer's IP address. If the local
				peer type is single IP address, then this is the value of the
				IP address. If the local peer type is IP subnet, then this is
				the value of the subnet mask. If the local peer type is IP
				address range, then this is the value of ending IP address of
				the range."
			::= { qtechIPSec2TrafficEntry 4 }


		-- 1.3.6.1.4.1.27514.1.1.10.2.108.1.4.1.5
		qtechIPSec2TrafficLocalProtocol OBJECT-TYPE
			SYNTAX Integer32 (0..255)
			MAX-ACCESS read-only
			STATUS current
			DESCRIPTION
				"The protocol number of the local peer's traffic."
			::= { qtechIPSec2TrafficEntry 5 }


		-- 1.3.6.1.4.1.27514.1.1.10.2.108.1.4.1.6
		qtechIPSec2TrafficLocalPort OBJECT-TYPE
			SYNTAX Integer32 (0..65535)
			MAX-ACCESS read-only
			STATUS current
			DESCRIPTION
				"The port number of the local peer's traffic."
			::= { qtechIPSec2TrafficEntry 6 }


		-- 1.3.6.1.4.1.27514.1.1.10.2.108.1.4.1.7
		qtechIPSec2TrafficLocalHostname OBJECT-TYPE
			SYNTAX DisplayString
			MAX-ACCESS read-only
			STATUS current
			DESCRIPTION
				"The Hostname of local peer's IP address."
			::= { qtechIPSec2TrafficEntry 7 }


		-- 1.3.6.1.4.1.27514.1.1.10.2.108.1.4.1.8
		qtechIPSec2TrafficRemoteType OBJECT-TYPE
			SYNTAX QtechTrafficType
			MAX-ACCESS read-only
			STATUS current
			DESCRIPTION
				"The type of remote peer. Possible values are: a single
				IP address, or an IP address range, or an IP subnet."
			::= { qtechIPSec2TrafficEntry 8 }


		-- 1.3.6.1.4.1.27514.1.1.10.2.108.1.4.1.9
		qtechIPSec2TrafficRemoteAddr1 OBJECT-TYPE
			SYNTAX IpAddress
			MAX-ACCESS read-only
			STATUS current
			DESCRIPTION
				"The first specification of remote peer's IP address.
				If the remote peer type is single IP address, then
				this is the value of the IP address. If the remote
				peer type is IP subnet, then this is the value
				of the subnet. If the remote peer type is IP
				address range, then this is the value of beginning
				IP address of the range."
			::= { qtechIPSec2TrafficEntry 9 }


		-- 1.3.6.1.4.1.27514.1.1.10.2.108.1.4.1.10
		qtechIPSec2TrafficRemoteAddr2 OBJECT-TYPE
			SYNTAX IpAddress
			MAX-ACCESS read-only
			STATUS current
			DESCRIPTION
				"Single IP address, then this is the value of the IP
				address. If the remote peer type is IP subnet,
				then this is the value of the subnet mask. If the
				remote peer type is IP address range, then this
				is the value of ending IP address of the range."
			::= { qtechIPSec2TrafficEntry 10 }


		-- 1.3.6.1.4.1.27514.1.1.10.2.108.1.4.1.11
		qtechIPSec2TrafficRemoteProtocol OBJECT-TYPE
			SYNTAX Integer32 (0..255)
			MAX-ACCESS read-only
			STATUS current
			DESCRIPTION
				"The protocol number of the remote peer's traffic."
			::= { qtechIPSec2TrafficEntry 11 }


		-- 1.3.6.1.4.1.27514.1.1.10.2.108.1.4.1.12
		qtechIPSec2TrafficRemotePort OBJECT-TYPE
			SYNTAX Integer32 (0..65535)
			MAX-ACCESS read-only
			STATUS current
			DESCRIPTION
				"The port number of the remote peer's traffic."
			::= { qtechIPSec2TrafficEntry 12 }


		-- 1.3.6.1.4.1.27514.1.1.10.2.108.1.4.1.13
		qtechIPSec2TrafficRemoteHostname OBJECT-TYPE
			SYNTAX DisplayString
			MAX-ACCESS read-only
			STATUS current
			DESCRIPTION
				"The Hostname of remote peer's IP address."
			::= { qtechIPSec2TrafficEntry 13 }


		-- 1.3.6.1.4.1.27514.1.1.10.2.108.1.5
		qtechIPSec2GlobalStats OBJECT IDENTIFIER ::= { qtechIPSec2Objects 5 }


		-- 1.3.6.1.4.1.27514.1.1.10.2.108.1.5.1
		qtechIPSec2GlobalActiveTunnels OBJECT-TYPE
			SYNTAX Gauge32
			MAX-ACCESS read-only
			STATUS current
			DESCRIPTION
				"The total number of currently active  IPSec Phase-2 Tunnels."
			::= { qtechIPSec2GlobalStats 1 }


		-- 1.3.6.1.4.1.27514.1.1.10.2.108.1.5.2
		qtechIPSec2GlobalActiveSas OBJECT-TYPE
			SYNTAX Gauge32
			MAX-ACCESS read-only
			STATUS current
			DESCRIPTION
				"The total number of currently active or expiring IPSec Phase-2 SA."
			::= { qtechIPSec2GlobalStats 2 }


		-- 1.3.6.1.4.1.27514.1.1.10.2.108.1.5.3
		qtechIPSec2GlobalInOctets OBJECT-TYPE
			SYNTAX Counter64
			MAX-ACCESS read-only
			STATUS current
			DESCRIPTION
				"The total number of octets received by all current and previous
				IPSec Phase-2 Tunnels. This value is accumulated BEFORE determining
				whether or not the packet should be decompressed."
			::= { qtechIPSec2GlobalStats 3 }


		-- 1.3.6.1.4.1.27514.1.1.10.2.108.1.5.4
		qtechIPSec2GlobalInPkts OBJECT-TYPE
			SYNTAX Counter64
			MAX-ACCESS read-only
			STATUS current
			DESCRIPTION
				"The total number of packets received by all current and
				previous IPSec Phase-2 Tunnels."
			::= { qtechIPSec2GlobalStats 4 }


		-- 1.3.6.1.4.1.27514.1.1.10.2.108.1.5.5
		qtechIPSec2GlobalInSpeed OBJECT-TYPE
			SYNTAX Counter64
			MAX-ACCESS read-only
			STATUS current
			DESCRIPTION
				"The total speed(bps) of packets received by all current and
				previous IPSec Phase-2 Tunnels."
			::= { qtechIPSec2GlobalStats 5 }


		-- 1.3.6.1.4.1.27514.1.1.10.2.108.1.5.6
		qtechIPSec2GlobalInDrops OBJECT-TYPE
			SYNTAX Counter64
			MAX-ACCESS read-only
			STATUS current
			DESCRIPTION
				"The total number of packets dropped during receiving
				process by all current and previous IPSec Phase-2
				Tunnels. "
			::= { qtechIPSec2GlobalStats 6 }


		-- 1.3.6.1.4.1.27514.1.1.10.2.108.1.5.7
		qtechIPSec2GlobalOutOctets OBJECT-TYPE
			SYNTAX Counter64
			MAX-ACCESS read-only
			STATUS current
			DESCRIPTION
				"The total number of octets sent by all current and previous
				IPSec Phase-2 Tunnels. This value is accumulated AFTER
				determining whether or not the packet should be compressed."
			::= { qtechIPSec2GlobalStats 7 }


		-- 1.3.6.1.4.1.27514.1.1.10.2.108.1.5.8
		qtechIPSec2GlobalOutPkts OBJECT-TYPE
			SYNTAX Counter64
			MAX-ACCESS read-only
			STATUS current
			DESCRIPTION
				"The total number of packets sent by all current and previous
				IPSec Phase-2 Tunnels."
			::= { qtechIPSec2GlobalStats 8 }


		-- 1.3.6.1.4.1.27514.1.1.10.2.108.1.5.9
		qtechIPSec2GlobalOutSpeed OBJECT-TYPE
			SYNTAX Counter64
			MAX-ACCESS read-only
			STATUS current
			DESCRIPTION
				"The total speed(bps) of packets sent by all current and previous
				IPSec Phase-2 Tunnels."
			::= { qtechIPSec2GlobalStats 9 }


		-- 1.3.6.1.4.1.27514.1.1.10.2.108.1.5.10
		qtechIPSec2GlobalOutDrops OBJECT-TYPE
			SYNTAX Counter64
			MAX-ACCESS read-only
			STATUS current
			DESCRIPTION
				"The total number of packets dropped during sending process
				by all current and previous IPSec Phase-2 Tunnels."
			::= { qtechIPSec2GlobalStats 10 }


		-- 1.3.6.1.4.1.27514.1.1.10.2.108.1.6
		qtechIPSec2TrapObject OBJECT IDENTIFIER ::= { qtechIPSec2Objects 6 }


		-- 1.3.6.1.4.1.27514.1.1.10.2.108.1.6.1
		qtechIPSec2MapName OBJECT-TYPE
			SYNTAX DisplayString
			MAX-ACCESS accessible-for-notify
			STATUS current
			DESCRIPTION
				"The IPSec map name with a trap."
			::= { qtechIPSec2TrapObject 1 }


		-- 1.3.6.1.4.1.27514.1.1.10.2.108.1.6.2
		qtechIPSec2SeqNum OBJECT-TYPE
			SYNTAX Integer32
			MAX-ACCESS accessible-for-notify
			STATUS current
			DESCRIPTION
				"The IPSec map sequence number with a trap."
			::= { qtechIPSec2TrapObject 2 }


		-- 1.3.6.1.4.1.27514.1.1.10.2.108.1.6.3
		qtechIPSec2SpiValue OBJECT-TYPE
			SYNTAX Integer32
			MAX-ACCESS accessible-for-notify
			STATUS current
			DESCRIPTION
				"The SPI value associated with a trap."
			::= { qtechIPSec2TrapObject 3 }


		-- 1.3.6.1.4.1.27514.1.1.10.2.108.1.7
		qtechIPSec2Trap OBJECT IDENTIFIER ::= { qtechIPSec2Objects 7 }


		-- 1.3.6.1.4.1.27514.1.1.10.2.108.1.7.1
		qtechIPSec2Notifications OBJECT IDENTIFIER ::= { qtechIPSec2Trap 1 }


		-- 1.3.6.1.4.1.27514.1.1.10.2.108.1.7.1.1
		qtechIPSec2TunnelStart NOTIFICATION-TYPE
			OBJECTS { qtechIPSec2TunIfIndex, qtechIPSec2TunRemoteAddr, qtechIPSec2TrafficLocalType, qtechIPSec2TrafficLocalAddr1, qtechIPSec2TrafficLocalAddr2,
				qtechIPSec2TrafficLocalProtocol, qtechIPSec2TrafficLocalPort, qtechIPSec2TrafficRemoteAddr1, qtechIPSec2TrafficRemoteAddr2, qtechIPSec2TrafficRemotePort
				 }
			STATUS current
			DESCRIPTION
				"This notification is generated when an IPSec Phase-2
				Tunnel is created."
			::= { qtechIPSec2Notifications 1 }


		-- 1.3.6.1.4.1.27514.1.1.10.2.108.1.7.1.2
		qtechIPSec2TunnelStop NOTIFICATION-TYPE
			OBJECTS { qtechIPSec2TunIfIndex, qtechIPSec2TunRemoteAddr, qtechIPSec2TrafficLocalType, qtechIPSec2TrafficLocalAddr1, qtechIPSec2TrafficLocalAddr2,
				qtechIPSec2TrafficLocalProtocol, qtechIPSec2TrafficLocalPort, qtechIPSec2TrafficRemoteAddr1, qtechIPSec2TrafficRemoteAddr2, qtechIPSec2TrafficRemotePort
				 }
			STATUS current
			DESCRIPTION
				"This notification is generated when an IPSec Phase-2
				Tunnel is deleted."
			::= { qtechIPSec2Notifications 2 }


		-- 1.3.6.1.4.1.27514.1.1.10.2.108.2
		qtechIPSec2Conformance OBJECT IDENTIFIER ::= { qtechIPSec2MibModule 2 }


		-- 1.3.6.1.4.1.27514.1.1.10.2.108.2.1
		qtechIPSec2Compliances OBJECT IDENTIFIER ::= { qtechIPSec2Conformance 1 }


		-- 1.3.6.1.4.1.27514.1.1.10.2.108.2.1.1
		qtechIPSec2Compliance MODULE-COMPLIANCE
			STATUS current
			DESCRIPTION
				" "
			MODULE -- this module
				MANDATORY-GROUPS { qtechIPSec2TunnelTableGroup, qtechIPSec2TunnelStatGroup, qtechIPSec2SaGroup, qtechIPSec2TrafficTableGroup, qtechIPSec2GlobalStatsGroup,
					qtechIPSec2TrapObjectGroup, qtechIPSec2TrapGroup }
			::= { qtechIPSec2Compliances 1 }


		-- 1.3.6.1.4.1.27514.1.1.10.2.108.2.2
		qtechIPSec2Groups OBJECT IDENTIFIER ::= { qtechIPSec2Conformance 2 }


		-- 1.3.6.1.4.1.27514.1.1.10.2.108.2.2.1
		qtechIPSec2TunnelTableGroup OBJECT-GROUP
			OBJECTS { qtechIPSec2TunIfIndex, qtechIPSec2TunLocalAddr, qtechIPSec2TunRemoteAddr, qtechIPSec2TunLocalHostname, qtechIPSec2TunRemoteHostname,
				qtechIPSec2TunKeyType, qtechIPSec2TunEncapMode, qtechIPSec2TunInitiator, qtechIPSec2TunLifeSize, qtechIPSec2TunLifeTime,
				qtechIPSec2TunRemainTime, qtechIPSec2TunActiveTime, qtechIPSec2TunCreateTime, qtechIPSec2TunRemainSize, qtechIPSec2TunTotalRefreshes,
				qtechIPSec2TunCurrentSaInstances, qtechIPSec2TunInSaEncryptAlgo, qtechIPSec2TunInSaAhAuthAlgo, qtechIPSec2TunInSaEspAuthAlgo, qtechIPSec2TunDiffHellmanGrp,
				qtechIPSec2TunOutSaEncryptAlgo, qtechIPSec2TunOutSaAhAuthAlgo, qtechIPSec2TunOutSaEspAuthAlgo, qtechIPSec2TunMapName, qtechIPSec2TunSeqNum,
				qtechIPSec2TunStatus, qtechIPSec2TunInOctets, qtechIPSec2TunInDecompOctets, qtechIPSec2TunInPkts, qtechIPSec2TunInSpeed,
				qtechIPSec2TunInDropPkts, qtechIPSec2TunOutOctets, qtechIPSec2TunOutUncompOctets, qtechIPSec2TunOutPkts, qtechIPSec2TunOutSpeed,
				qtechIPSec2TunOutDropPkts }
			STATUS current
			DESCRIPTION
				"The group contains the IPSec tunnel's property information."
			::= { qtechIPSec2Groups 1 }


		-- 1.3.6.1.4.1.27514.1.1.10.2.108.2.2.2
		qtechIPSec2TunnelStatGroup OBJECT-GROUP
			OBJECTS { qtechIPSec2TunInOctets, qtechIPSec2TunInDecompOctets, qtechIPSec2TunInPkts, qtechIPSec2TunInSpeed, qtechIPSec2TunInDropPkts,
				qtechIPSec2TunOutOctets, qtechIPSec2TunOutUncompOctets, qtechIPSec2TunOutPkts, qtechIPSec2TunOutSpeed, qtechIPSec2TunOutDropPkts
				 }
			STATUS current
			DESCRIPTION
				"The group contains the IPSec tunnel's statistic information."
			::= { qtechIPSec2Groups 2 }


		-- 1.3.6.1.4.1.27514.1.1.10.2.108.2.2.3
		qtechIPSec2SaGroup OBJECT-GROUP
			OBJECTS { qtechIPSec2SaIndex, qtechIPSec2SaDirection, qtechIPSec2SaValue, qtechIPSec2SaProtocol, qtechIPSec2SaEncryptAlgo,
				qtechIPSec2SaAuthAlgo, qtechIPSec2SaStatus }
			STATUS current
			DESCRIPTION
				"The group contains the SA's property information."
			::= { qtechIPSec2Groups 3 }


		-- 1.3.6.1.4.1.27514.1.1.10.2.108.2.2.4
		qtechIPSec2TrafficTableGroup OBJECT-GROUP
			OBJECTS { qtechIPSec2TrafficLocalType, qtechIPSec2TrafficLocalAddr1, qtechIPSec2TrafficLocalAddr2, qtechIPSec2TrafficLocalProtocol, qtechIPSec2TrafficLocalPort,
				qtechIPSec2TrafficRemoteAddr1, qtechIPSec2TrafficRemoteAddr2, qtechIPSec2TrafficRemotePort, qtechIPSec2TrafficLocalHostname, qtechIPSec2TrafficRemoteType,
				qtechIPSec2TrafficRemoteProtocol, qtechIPSec2TrafficRemoteHostname }
			STATUS current
			DESCRIPTION
				"The group contains the property information of the
				data flow protected by IPSec tunnel."
			::= { qtechIPSec2Groups 4 }


		-- 1.3.6.1.4.1.27514.1.1.10.2.108.2.2.5
		qtechIPSec2GlobalStatsGroup OBJECT-GROUP
			OBJECTS { qtechIPSec2GlobalActiveTunnels, qtechIPSec2GlobalActiveSas, qtechIPSec2GlobalInOctets, qtechIPSec2GlobalInPkts, qtechIPSec2GlobalInSpeed,
				qtechIPSec2GlobalInDrops, qtechIPSec2GlobalOutOctets, qtechIPSec2GlobalOutPkts, qtechIPSec2GlobalOutSpeed, qtechIPSec2GlobalOutDrops
				 }
			STATUS current
			DESCRIPTION
				"The group contains all of the IPSec tunnel's statistic
				information."
			::= { qtechIPSec2Groups 5 }


		-- 1.3.6.1.4.1.27514.1.1.10.2.108.2.2.6
		qtechIPSec2TrapObjectGroup OBJECT-GROUP
			OBJECTS { qtechIPSec2MapName, qtechIPSec2SeqNum, qtechIPSec2SpiValue }
			STATUS current
			DESCRIPTION
				"The group contains all of trap objects of IPSec tunnels."
			::= { qtechIPSec2Groups 6 }


		-- 1.3.6.1.4.1.27514.1.1.10.2.108.2.2.7
		qtechIPSec2TrapGroup NOTIFICATION-GROUP
			NOTIFICATIONS { qtechIPSec2TunnelStart, qtechIPSec2TunnelStop }
			STATUS current
			DESCRIPTION
				"The group contains all of trap of IPSec tunnels."
			::= { qtechIPSec2Groups 7 }



	END

--
-- QTECH-IPSEC2-MIB.mib
--
