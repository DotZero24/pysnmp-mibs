-- *****************************************************************
-- QTECH-AP-MGMT-MIB.mib:  Qtech AP MGMT MIB file
--
-- July 2013, linwei4
--
-- Copyright (c) 2012 by Qtech Networks Co.,Ltd.
-- All rights reserved.
-- *****************************************************************
--
QTECH-AP-MGMT-MIB DEFINITIONS ::= BEGIN

IMPORTS
        OBJECT-TYPE,
        Integer32,
        MODULE-IDENTITY
                FROM SNMPv2-SMI
        qtechMgmt
                FROM QTECH-SMI;

qtechApMgmtMIB MODULE-IDENTITY
    LAST-UPDATED "201307230000Z"
    ORGANIZATION "Qtech Networks Co.,Ltd."
    CONTACT-INFO
        "
    Tel: 4008-111-000

    E-mail: service@qtech.com.cn"
    DESCRIPTION
        "This module defines ac management mibs."
    REVISION      "201307230000Z"
    DESCRIPTION
        "Initial version of this MIB module."
    ::= { qtechMgmt 124}

--***************** define the AP root nodes *****************
qtechApMgmtMIBObjects OBJECT IDENTIFIER      ::= { qtechApMgmtMIB 1 }
qtechApMgmt     OBJECT IDENTIFIER ::= { qtechApMgmtMIBObjects 1 }

--********************************************************************
--                                                                  **
--                  AP nodes                                        **
--                                                                  **
--********************************************************************

-- 1.ap_mode, the ap's mode
qtechApMode OBJECT-TYPE
    SYNTAX  INTEGER (0..1)
    MAX-ACCESS  read-only
    STATUS  current
    DESCRIPTION
            "The ap mode:
            0--fit
            1--fat"
    ::= { qtechApMgmt 1 }

END
