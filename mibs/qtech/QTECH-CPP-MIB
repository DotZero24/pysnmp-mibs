-- *****************************************************************
-- QTECH-CPP-MIB.mib:  Qtech CPP MIB file
--
-- Dec 2014, Linxiaojie
--
-- Copyright (c) 2012 by Qtech Networks Co.,Ltd.
-- All rights reserved.
--
-- *****************************************************************
--

QTECH-CPP-MIB DEFINITIONS ::= BEGIN

IMPORTS
        MODULE-IDENTITY,
        OBJECT-TYPE,
        NOTIFICATION-TYPE,
        Integer32,
        OBJECT-TYPE
                FROM SNMPv2-SMI
        TruthValue,
        DisplayString
                FROM SNMPv2-TC
        MODULE-COMPLIANCE,
        OBJECT-GROUP
                FROM SNMPv2-CONF
        qtechMgmt
                FROM QTECH-SMI;

qtechCPPMIB MODULE-IDENTITY
        LAST-UPDATED "201412192100Z"
        ORGANIZATION "Qtech Networks Co.,Ltd."
        CONTACT-INFO
                "
                Tel: 4008-111-000

                E-mail: service@qtech.com.cn"
        DESCRIPTION
                "This module defines qtech cpp mibs."
        REVISION      "201412192100Z"
        DESCRIPTION
                "Add a table about cpp."
        REVISION      "201412192100Z"
        DESCRIPTION
                "Initial version of this MIB module."
        ::= { qtechMgmt 132 }

qtechCPPMIBObjects OBJECT IDENTIFIER ::= { qtechCPPMIB 1 }

qtechCPPTable OBJECT-TYPE
        SYNTAX 			SEQUENCE OF QtechCPPEntry
        MAX-ACCESS 	not-accessible
        STATUS 			current
        DESCRIPTION
            " "
        ::= { qtechCPPMIBObjects 1 }

qtechCPPEntry OBJECT-TYPE
        SYNTAX 			QtechCPPEntry
        MAX-ACCESS 	not-accessible
        STATUS 			current
        DESCRIPTION
            " "
        INDEX { cppIndex }
        ::= { qtechCPPTable 1 }

QtechCPPEntry ::=
        SEQUENCE {
            cppIndex			Integer32,
            cppDeviceId			Integer32,
            cppSlotId			Integer32,
            cppCardIndex		DisplayString,
            cppPacketType		DisplayString,
            cppTrafficClass		Integer32,
            cppBandwidth		Integer32,
            cppRate			Integer32,
            cppDrop			Integer32,
            cppTotal			Integer32,
            cppTotalDrop		Integer32
        }
cppIndex OBJECT-TYPE
        SYNTAX 			Integer32 (1..2147483647)
        MAX-ACCESS 	read-only
        STATUS 			current
        DESCRIPTION
            " "
        ::= { qtechCPPEntry 1 }

cppDeviceId OBJECT-TYPE
        SYNTAX 			Integer32 (1..2147483647)
        MAX-ACCESS 	read-only
        STATUS 			current
        DESCRIPTION
            " "
        ::= { qtechCPPEntry 2 }

cppSlotId OBJECT-TYPE
        SYNTAX 			Integer32 (1..2147483647)
        MAX-ACCESS 	read-only
        STATUS 			current
        DESCRIPTION
            " "
        ::= { qtechCPPEntry 3 }

cppCardIndex OBJECT-TYPE
        SYNTAX DisplayString(SIZE (1..32))
        MAX-ACCESS read-only
        STATUS current
        DESCRIPTION
            " "
        ::= { qtechCPPEntry 4 }

cppPacketType OBJECT-TYPE
        SYNTAX DisplayString(SIZE (1..32))
        MAX-ACCESS read-only
        STATUS current
        DESCRIPTION
            " "
        ::= { qtechCPPEntry 5 }

cppTrafficClass OBJECT-TYPE
        SYNTAX 			Integer32 (1..2147483647)
        MAX-ACCESS 	read-only
        STATUS 			current
        DESCRIPTION
            " "
        ::= { qtechCPPEntry 6 }

cppBandwidth OBJECT-TYPE
        SYNTAX 			Integer32 (1..2147483647)
        MAX-ACCESS 	read-only
        STATUS 			current
        DESCRIPTION
            " "
        ::= { qtechCPPEntry 7 }

cppRate OBJECT-TYPE
        SYNTAX 			Integer32 (1..2147483647)
        MAX-ACCESS 	read-only
        STATUS 			current
        DESCRIPTION
            " "
        ::= { qtechCPPEntry 8 }

cppDrop OBJECT-TYPE
        SYNTAX 			Integer32 (1..2147483647)
        MAX-ACCESS 	read-only
        STATUS 			current
        DESCRIPTION
            " "
        ::= { qtechCPPEntry 9 }

cppTotal OBJECT-TYPE
        SYNTAX 			Integer32 (1..2147483647)
        MAX-ACCESS 	read-only
        STATUS 			current
        DESCRIPTION
            " "
        ::= { qtechCPPEntry 10 }

cppTotalDrop OBJECT-TYPE
        SYNTAX 			Integer32 (1..2147483647)
        MAX-ACCESS 	read-only
        STATUS 			current
        DESCRIPTION
            " "
        ::= { qtechCPPEntry 11 }

END
