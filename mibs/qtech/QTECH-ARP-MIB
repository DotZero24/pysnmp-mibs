-- *****************************************************************
-- QTECH-ARP-MIB.mib:  Qtech Arp MIB file
--
-- March 2002, Wuzg
--
-- Copyright (c) 2002 by Qtech Networks Co.,Ltd.
-- All rights reserved.
--
-- *****************************************************************
--

QTECH-ARP-MIB DEFINITIONS ::= BEGIN

IMPORTS
        MODULE-IDENTITY,
        OBJECT-TYPE,
        IpAddress,
        Integer32,
        Counter32
                FROM SNMPv2-SMI
        RowStatus,
        PhysAddress
                FROM SNMPv2-TC
        MODULE-COMPLIANCE,
        OBJECT-GROUP
                FROM SNMPv2-CONF
        IfIndex
                FROM QTECH-TC
        qtechMgmt
                FROM QTECH-SMI;

qtechArpMIB MODULE-IDENTITY
        LAST-UPDATED "200203200000Z"
        ORGANIZATION "Qtech Networks Co.,Ltd."
        CONTACT-INFO
                "
                Tel: 4008-111-000

                E-mail: service@qtech.com.cn"
        DESCRIPTION
                "This module defines qtech arp mibs."
        REVISION      "200203200000Z"
        DESCRIPTION
                "Initial version of this MIB module."
        ::= { qtechMgmt 2}

qtechArpMIBObjects OBJECT IDENTIFIER ::= { qtechArpMIB 1 }


 -- IP Address Translation table

 -- The IP address translation table contain the IpAddress to
 -- `physical' address equivalences for ARP(Address Resolution Protocol).

 qtechArpTable OBJECT-TYPE
     SYNTAX  SEQUENCE OF QtechArpEntry
     MAX-ACCESS  not-accessible
     STATUS  current
     DESCRIPTION
             "The IP Address Translation table used for mapping
             from IP addresses to physical addresses."
     ::= { qtechArpMIBObjects 1 }

 qtechArpEntry OBJECT-TYPE
     SYNTAX  QtechArpEntry
     MAX-ACCESS  not-accessible
     STATUS  current
     DESCRIPTION
             "Each entry contains one IpAddress to `physical'
             address equivalence."
     INDEX   { qtechArpIfIndex,
               qtechArpNetAddress }
     ::= { qtechArpTable 1 }

 QtechArpEntry ::=
     SEQUENCE {
         qtechArpIfIndex
             IfIndex,
         qtechArpPhysAddress
             PhysAddress,
         qtechArpNetAddress
             IpAddress,
         qtechArpRemainAge
             Integer32,
         qtechArpType
             INTEGER,
         qtechArpEntryType
             INTEGER,
         qtechArpStatus
             RowStatus
     }

 qtechArpIfIndex OBJECT-TYPE
     SYNTAX  IfIndex
     MAX-ACCESS  read-only
     STATUS  current
     DESCRIPTION
             "The interface on which this entry's equivalence
             is effective.  The interface identified by a
             particular value of this index is the same
             interface as identified by the same value of
             ifIndex."
     ::= { qtechArpEntry 1 }

 qtechArpPhysAddress OBJECT-TYPE
     SYNTAX  PhysAddress
     MAX-ACCESS  read-create
     STATUS  current
     DESCRIPTION
             "The media-dependent `physical' address."
     ::= { qtechArpEntry 2 }

 qtechArpNetAddress OBJECT-TYPE
     SYNTAX  IpAddress
     MAX-ACCESS  read-only
     STATUS  current
     DESCRIPTION
             "The IpAddress corresponding to the media-
             dependent `physical' address."
     ::= { qtechArpEntry 3 }

 qtechArpRemainAge OBJECT-TYPE
     SYNTAX  Integer32
     MAX-ACCESS  read-only
     STATUS  current
     DESCRIPTION
             "The remain age of this ARP entry, in units of minute"
     ::= { qtechArpEntry 4 }

 qtechArpType OBJECT-TYPE
     SYNTAX  INTEGER {
                 arpa(1)       -- none of the following
             }
     MAX-ACCESS  read-create
     STATUS  current
     DESCRIPTION
             "The ARP type of the entry."
     ::= { qtechArpEntry 5 }

 qtechArpEntryType OBJECT-TYPE
     SYNTAX  INTEGER {
                 static(1),   -- arp entry which is configured manually, these entries will not aging
                 dynamic(2), -- learnd by system, thest entry  may aging.
                 interface(3), -- the arp entry of the corresponding ip of the interface
                 vrrp(4), -- arp entry which is added by the vrrp protocol
                 trusted(5) -- arp entrty which is added through the smp server
             }
     MAX-ACCESS  read-only
     STATUS  current
     DESCRIPTION
             "The entry type."
     ::= { qtechArpEntry 6 }

 qtechArpStatus OBJECT-TYPE
        SYNTAX RowStatus
        MAX-ACCESS read-create
        STATUS current
        DESCRIPTION
            "entry status of this entry. and the means in this enviraments can
            reffer to the text-convention definition of the RowStatus."
    ::= { qtechArpEntry 7 }




 --  Interface configure for ARP(Address Resolution Protocol)

 qtechArpIfTable OBJECT-TYPE
     SYNTAX  SEQUENCE OF QtechArpIfEntry
     MAX-ACCESS  not-accessible
     STATUS  current
     DESCRIPTION
             "Interface configure for ARP(Address Resolution Protocol)."
     ::= { qtechArpMIBObjects 2 }

 qtechArpIfEntry OBJECT-TYPE
     SYNTAX  QtechArpIfEntry
     MAX-ACCESS  not-accessible
     STATUS  current
     DESCRIPTION
             "Each entry contains a interface configure for ARP"
     INDEX   { qtechArpIfIfIndex}
     ::= { qtechArpIfTable 1 }

 QtechArpIfEntry ::=
     SEQUENCE {
         qtechArpIfIfIndex
             IfIndex,
         qtechArpIfCacheTimeOut
             INTEGER
     }

 qtechArpIfIfIndex OBJECT-TYPE
     SYNTAX  IfIndex
     MAX-ACCESS  read-only
     STATUS  current
     DESCRIPTION
             "The interface on which this entry's equivalence
             is effective.  The interface identified by a
             particular value of this index is the same
             interface as identified by the same value of
             ifIndex."
     ::= { qtechArpIfEntry 1 }

 qtechArpIfCacheTimeOut OBJECT-TYPE
        SYNTAX INTEGER (60..18000)
        MAX-ACCESS read-write
        STATUS current
        DESCRIPTION
            "Aging time in units of second of Arp table"
        ::= { qtechArpIfEntry 2 }

 --  Counter for ARP(Address Resolution Protocol)

 qtechArpCurrentTotalNumber OBJECT-TYPE
        SYNTAX Counter32
        MAX-ACCESS read-only
        STATUS current
        DESCRIPTION
            "Number of current total arp entrys this system have"
        ::= { qtechArpMIBObjects 3 }

 qtechArpCurrentUnresolveNumber OBJECT-TYPE
        SYNTAX Counter32
        MAX-ACCESS read-only
        STATUS current
        DESCRIPTION
            "Number of current unresolve arp entrys this system have"
        ::= { qtechArpMIBObjects 4 }

qtechArpMIBConformance OBJECT IDENTIFIER ::= { qtechArpMIB 2 }
qtechArpMIBCompliances OBJECT IDENTIFIER ::= { qtechArpMIBConformance 1 }
qtechArpMIBGroups      OBJECT IDENTIFIER ::= { qtechArpMIBConformance 2 }


-- compliance statements

qtechArpMIBCompliance MODULE-COMPLIANCE
        STATUS  current
        DESCRIPTION
                "The compliance statement for entities which implement
                the Qtech Arp MIB"
        MODULE  -- this module
                MANDATORY-GROUPS { qtechArpMIBGroup
                 }
--        OBJECT           ipNetToMediaIfIndex
--        MIN-ACCESS       read-only
--        DESCRIPTION     "Write access is not required."
--
--        OBJECT           ipNetToMediaPhysAddress
--        MIN-ACCESS       read-create
--        DESCRIPTION     "read-create access is permitted."
--
--        OBJECT           ipNetToMediaNetAddress
--        MIN-ACCESS       read-only
--        DESCRIPTION     "Write access is not required."

        ::= { qtechArpMIBCompliances 1 }

-- units of conformance

qtechArpMIBGroup OBJECT-GROUP
        OBJECTS {
         qtechArpIfIndex,
         qtechArpPhysAddress,
         qtechArpNetAddress,
         qtechArpRemainAge,
         qtechArpType,
         qtechArpEntryType,
         qtechArpStatus,
         qtechArpIfIfIndex,
         qtechArpIfCacheTimeOut,
         qtechArpCurrentTotalNumber,
         qtechArpCurrentUnresolveNumber
        }
        STATUS  current
        DESCRIPTION
                "A collection of objects providing arp management and
                opertion to a Qtech agent."
        ::= { qtechArpMIBGroups 1 }

END
