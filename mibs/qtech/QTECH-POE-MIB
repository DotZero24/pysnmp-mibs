-- *****************************************************************
-- QTECH-POE-MIB.mib:  Qtech POE MIB file
--
-- Feb 2012, Hedong
--
-- Copyright (c) 2012 by Qtech Networks Co.,Ltd.
-- All rights reserved.
--
-- *****************************************************************
--

QTECH-POE-MIB DEFINITIONS ::= BEGIN

IMPORTS
        MODULE-IDENTITY,
        OBJECT-TYPE,
        NOTIFICATION-TYPE,
        Integer32,
        OBJECT-TYPE
                FROM SNMPv2-SMI
			  TruthValue
			    			FROM SNMPv2-TC
        MODULE-COMPLIANCE,
        OBJECT-GROUP
                FROM SNMPv2-CONF
        qtechMgmt
                FROM QTECH-SMI;

qtechPoeMIB MODULE-IDENTITY
        LAST-UPDATED "201202140000Z"
        ORGANIZATION "Qtech Networks Co.,Ltd."
        CONTACT-INFO
                "
                Tel: 4008-111-000

                E-mail: service@qtech.com.cn"
        DESCRIPTION
                "This module defines qtech poe mibs."
        REVISION      "201202140000Z"
        DESCRIPTION
                "Add a table about poe."
        REVISION      "201202140000Z"
        DESCRIPTION
                "Initial version of this MIB module."
        ::= { qtechMgmt 110 }

qtechPoeConfigMIBObjects OBJECT IDENTIFIER ::= { qtechPoeMIB 1 }

qtechIfPoeTable OBJECT-TYPE
        SYNTAX 			SEQUENCE OF QtechIfPoeEntry
        MAX-ACCESS 	not-accessible
        STATUS 			current
        DESCRIPTION
            " "
        ::= { qtechPoeConfigMIBObjects 1 }

-- 6.1 配置信息		6.1.2 接口配置		表A.8 接口POE配置

qtechIfPoeEntry OBJECT-TYPE
        SYNTAX 			QtechIfPoeEntry
        MAX-ACCESS 	not-accessible
        STATUS 			current
        DESCRIPTION
            " "
        INDEX { ifPoeIndex }
        ::= { qtechIfPoeTable 1 }

QtechIfPoeEntry ::=
        SEQUENCE {
            ifPoeIndex 			Integer32,
            ifIsPoe 				TruthValue,
            ifPoeEnable 		INTEGER,
            ifPoePwrStatus 	INTEGER,
            ifPoeMaxPwrSet 	Integer32,
            ifPoePriority 	INTEGER,
						ifPoeConsumingPwr	Integer32
        }

ifPoeIndex OBJECT-TYPE
        SYNTAX 			Integer32 (1..2147483647)
        MAX-ACCESS 	read-only
        STATUS 			current
        DESCRIPTION
            " "
        ::= { qtechIfPoeEntry 1 }

ifIsPoe OBJECT-TYPE
        SYNTAX TruthValue
        MAX-ACCESS read-only
        STATUS current
        DESCRIPTION
            " "
        ::= { qtechIfPoeEntry 2 }

ifPoeEnable OBJECT-TYPE
        SYNTAX INTEGER {
            enabled(1),
            disabled(2)
        }
        MAX-ACCESS read-write
        STATUS current
        DESCRIPTION
            " "
        ::= { qtechIfPoeEntry 3 }

ifPoePwrStatus OBJECT-TYPE
        SYNTAX INTEGER {
            on(1),
            off(2)
        }
        MAX-ACCESS read-only
        STATUS current
        DESCRIPTION
            " "
        ::= { qtechIfPoeEntry 4 }

ifPoeMaxPwrSet OBJECT-TYPE
        SYNTAX Integer32 (1..2147483647)
        MAX-ACCESS read-write
        STATUS current
        DESCRIPTION
            " "
        ::= { qtechIfPoeEntry 5 }

ifPoePriority OBJECT-TYPE
				SYNTAX INTEGER   {
               critical(1),
               high(2),
               low(3)
	     	}
        MAX-ACCESS read-write
        STATUS  current
        DESCRIPTION
              " "
        ::= { qtechIfPoeEntry 6 }

-- 6.2 性能信息		6.2.2 接口性能信息		表A.16 接口性能统计

ifPoeConsumingPwr OBJECT-TYPE
				SYNTAX 			Integer32
        MAX-ACCESS 	read-only
        STATUS  		current
        DESCRIPTION
              " "
        ::= { qtechIfPoeEntry 7 }

-- Notification
qtechPoeTraps OBJECT IDENTIFIER ::= { qtechPoeMIB 2 }

-- 6.3 告警及通告		表A.17 交换机系统告警及通告

ifPoePowerOffTrap NOTIFICATION-TYPE
    OBJECTS { ifPoeIndex }
    STATUS  current
    DESCRIPTION
            " "
    ::= { qtechPoeTraps 1 }

ifPoePowerOnTrap NOTIFICATION-TYPE
    OBJECTS { ifPoeIndex }
    STATUS  current
    DESCRIPTION
            " "
    ::= { qtechPoeTraps 2 }

END
