-- *******************************************************************
-- QTECH-WLAN-QOS-EXTRA-MIB.mib : Qtech WLAN QOS MIB
--
-- Oct 2009, HUANGTAO
--
-- Copyright (c) 2009 by Qtech Networks Co.,Ltd.
-- All rights reserved.
-- *******************************************************************


QTECH-WLAN-QOS-EXTRA-MIB  DEFINITIONS ::= BEGIN

	IMPORTS
	          MODULE-IDENTITY,
	          OBJECT-TYPE
               FROM SNMPv2-SMI

            TruthValue
               FROM SNMPv2-TC

            MODULE-COMPLIANCE,
            OBJECT-GROUP
               FROM SNMPv2-CONF

            qtechApCfgRadioId,
            qtechApgWlanId,
            qtechStaMacAddr,
            qtechApMacAddr
               FROM QTECH-AC-MGMT-MIB


            qtechMgmt
               FROM QTECH-SMI;

--********************************************************************
--*  MODULE IDENTITY
--********************************************************************

qtechWlanQosExtraMib MODULE-IDENTITY
            LAST-UPDATED    "200909080000Z"
            ORGANIZATION    "Qtech Networks Co.,Ltd"
			      CONTACT-INFO
                "
                Tel: 4008-111-000

                E-mail: service@qtech.com.cn"
            DESCRIPTION
                "This MIB is intended to be implemented on all those
                devices operating as Central controllers, that
                terminate the Light Weight Access Point Protocol
                tunnel from Cisco Light-weight LWAPP Access Points.

                Information provided by this MIB is used to study
                the quality of service in the voice and video traffic
                on the WLAN.

                The relationship between CC and the LWAPP APs
                can be depicted as follows:

                      +......+     +......+     +......+
                      +      +     +      +     +      +
                      +  CC  +     +  CC  +     +  CC  +
                      +      +     +      +     +      +
                      +......+     +......+     +......+
                        ..            .             .
                        ..            .             .
                       .  .            .             .
                      .    .            .             .
                     .      .            .             .
                    .        .            .             .
                +......+ +......+     +......+      +......+
                +      + +      +     +      +      +      +
                +  AP  + +  AP  +     +  AP  +      +  AP  +
                +      + +      +     +      +      +      +
                +......+ +......+     +......+      +......+
                           .              .             .
                         .  .              .             .
                        .    .              .             .
                       .      .              .             .
                      .        .              .             .
                   +......+ +......+     +......+      +......+
                   +      + +      +     +      +      +      +
                   +  MN  + +  MN  +     +  MN  +      +  MN  +
                   +      + +      +     +      +      +      +
                   +......+ +......+     +......+      +......+


                The LWAPP tunnel exists between the controller and
                the APs.  The MNs communicate with the APs through
                the protocol defined by the 802.11 standard.

                LWAPP APs, upon bootup, discover and join one of the
                controllers and the controller pushes the configuration,
                that includes the WLAN parameters, to the LWAPP APs.
                The APs then encapsulate all the 802.11 frames from
                wireless clients inside LWAPP frames and forward
                the LWAPP frames to the controller.

                                   GLOSSARY

                Access Point ( AP )

                An entity that contains an 802.11 medium access
                control ( MAC ) and physical layer ( PHY ) interface
                and provides access to the distribution services via
                the wireless medium for associated clients.

                LWAPP APs encapsulate all the 802.11 frames in
                LWAPP frames and sends them to the controller to which
                it is logically connected.

                Gratuitous Probe Response (GPR)

                The Gratuitous Probe Response feature aids in conserving
                battery power of WLAN-enabled cell phones by providing
                a high rate packet on the order of tens of milliseconds
                such that these kind of phones can wake up and wait at
                predefined intervals, to reduce battery power.  The
                GPR packet is transmitted from the AP at a predefined
                time interval.


                Light Weight Access Point Protocol ( LWAPP )

                This is a generic protocol that defines the
                communication between the Access Points and the
                Central Controller.

                Mobile Node ( MN )

                A roaming 802.11 wireless device in a wireless
                network associated with an access point. Mobile Node
                and client are used interchangeably.

                TU

                A measurement of time in units of 1024 microseconds.

                User Priority ( UP )

                Specifies a the priority rules in QOS for handling user
                priority.

                EDCA

                As defined in 802.11e standard, Enhanced distributed
                channel access(EDCA) parameter set element is used
                by the AP to establish policy, to change policy when
                accepting new clients, or to adapt to changes in
                offered load.

                REFERENCE

                [1] Wireless LAN Medium Access Control ( MAC ) and
                Physical Layer ( PHY ) Specifications

                [2] Draft-obara-capwap-lwapp-00.txt, IETF Light
                Weight Access Point Protocol "


                REVISION        "200909080000Z"
                DESCRIPTION
                        "Initial version of this MIB module."
        ::= { qtechMgmt 60 }


--********************************************************************
--*  SubMODULE IDENTITY
--********************************************************************


qtechWlanDeviceWMMObjects OBJECT IDENTIFIER
        ::= { qtechWlanQosExtraMib    1 }

qtechWlanDeviceEDCAObjects OBJECT IDENTIFIER
        ::= { qtechWlanQosExtraMib    2 }

qtechWlanDevicePrivMappingObjects OBJECT IDENTIFIER
        ::= { qtechWlanQosExtraMib   3 }

qtechWlanDeviceRatelimitObjects OBJECT IDENTIFIER
        ::= { qtechWlanQosExtraMib    4 }

qtechWlanQosMIBConform OBJECT IDENTIFIER
		::= { qtechWlanQosExtraMib 5 }




--*************************************************
--qtechWlanDeviceWMMObjects Config
--*************************************************

qtechWMMStatusTable OBJECT-TYPE
            SYNTAX          SEQUENCE OF QtechWMMStatusEntry
            MAX-ACCESS      not-accessible
            STATUS          current
            DESCRIPTION
                " wmm status for each wlan"

        ::= { qtechWlanDeviceWMMObjects  1 }

qtechWMMStatusEntry OBJECT-TYPE
			SYNTAX			QtechWMMStatusEntry
			MAX-ACCESS		not-accessible
			STATUS			current
			DESCRIPTION
				" "
			INDEX   {
                    qtechApgWlanId
                }
		::= { qtechWMMStatusTable 1 }

QtechWMMStatusEntry ::=
        SEQUENCE {
            qtechWMMStatus            TruthValue,
            qtechAPSDStatus           TruthValue,
            qtechSMPSStatus           TruthValue
        }

qtechWMMStatus OBJECT-TYPE
            SYNTAX          TruthValue
            MAX-ACCESS      read-write
            STATUS          current
            DESCRIPTION
                " the wmm enable WMM or disable WMM
                    "
            DEFVAL          {1}
        ::= { qtechWMMStatusEntry 1 }



qtechAPSDStatus OBJECT-TYPE
            SYNTAX          TruthValue
            MAX-ACCESS      read-write
            STATUS          current
            DESCRIPTION
                "display APSD-Support is enable or disable
                    "
            DEFVAL          {1}
        ::= { qtechWMMStatusEntry 2 }


qtechSMPSStatus OBJECT-TYPE
            SYNTAX          TruthValue
            MAX-ACCESS      read-write
            STATUS          current
            DESCRIPTION
                "display the AP's smps-support status
                    "
            DEFVAL          {1}
        ::= { qtechWMMStatusEntry 3 }


--********************************************************************
--*    EDCA Param set
--********************************************************************


 -- **********************************************************************

 --      SMT EDCA Config TABLE

 -- **********************************************************************

 qtechdot11EDCATable OBJECT-TYPE

          SYNTAX SEQUENCE OF Qtechdot11EDCAEntry

          MAX-ACCESS not-accessible

          STATUS current

          DESCRIPTION

               "Conceptual table for EDCA default parameter values at a non-AP

               STA. This table shall contain the four entries of the EDCA

               parameters corresponding to four possible ACs. Index 1 corresponds

               to AC_BK, index 2 to AC_BE, index 3 to AC_VI, and index 4 to AC_VO."

         REFERENCE "IEEE 802.11-2007, 9.1.3.1"

      ::= { qtechWlanDeviceEDCAObjects 1 }

 qtechdot11EDCAEntry OBJECT-TYPE

         SYNTAX Qtechdot11EDCAEntry

         MAX-ACCESS not-accessible

         STATUS current

         DESCRIPTION

           "An Entry (conceptual row) in the EDCA Table.

           ifIndex - Each IEEE 802.11 interface is represented by an ifEntry.

           Interface tables in this MIB module are indexed by ifIndex."
	INDEX {
         qtechApMacAddr,
         qtechApCfgRadioId,
         qtechdot11EDCATableIndex
    }

     ::= { qtechdot11EDCATable 1 }

 Qtechdot11EDCAEntry ::=

         SEQUENCE {  qtechdot11EDCATableIndex        INTEGER,

                     qtechdot11EDCATableCWmin        INTEGER,

                     qtechdot11EDCATableCWmax        INTEGER,

                     qtechdot11EDCATableAIFSN        INTEGER,

                     qtechdot11EDCATableTXOPLimit    INTEGER,

                     qtechdot11EDCATableMSDULifetime INTEGER,

                     qtechdot11EDCATableMandatory    TruthValue }


 qtechdot11EDCATableIndex OBJECT-TYPE

         SYNTAX INTEGER (1..4)

         MAX-ACCESS not-accessible

         STATUS current

         DESCRIPTION

             "The auxiliary variable used to identify instances of the columnar

              objects in the EDCA Table. The value of this variable is

              1) 1, if the value of the AC is AC_BK.

              2) 2, if the value of the AC is AC_BE.

              3) 3, if the value of the AC is AC_VI.

              4) 4, if the value of the AC is AC_VO."

     ::= { qtechdot11EDCAEntry 1 }

 qtechdot11EDCATableCWmin OBJECT-TYPE

         SYNTAX INTEGER (0..255)

         MAX-ACCESS read-write

         STATUS current

         DESCRIPTION

              "This attribute shall specify the value of the minimum size of the

              window that shall be used by a STA for a particular AC for

              generating a random number for the backoff. The value of this

              attribute shall be such that it could always be expressed in the

              form of 2X - 1, where X is an integer. The default value for this

              attribute is

              1) aCWmin, if qtechdot11EDCATableIndex is 1 or 2.

              2) (aCWmin+1)/2 - 1, if qtechdot11EDCATableIndex is 3.

              3) (aCWmin+1)/4 - 1, if qtechdot11EDCATableIndex is 4."

     ::= { qtechdot11EDCAEntry 2 }

 qtechdot11EDCATableCWmax OBJECT-TYPE

         SYNTAX INTEGER (0..65535)

         MAX-ACCESS read-write

         STATUS current

         DESCRIPTION

              "This attribute shall specify the value of the maximum size of the

              window that shall be used by a STA for a particular AC for

              generating a random number for the backoff. The value of this

              attribute shall be such that it could always be expressed in the

              form of 2X - 1, where X is an integer. The default value for this

              attribute is

              1) aCWmax, if qtechdot11EDCATableIndex is 1 or 2.

              2) aCWmin, if qtechdot11EDCATableIndex is 3.

              3) (aCWmin+1)/2 - 1, if qtechdot11EDCATableIndex is 4."

     ::= { qtechdot11EDCAEntry 3 }

 qtechdot11EDCATableAIFSN OBJECT-TYPE

         SYNTAX INTEGER (2..15)

         MAX-ACCESS read-write

         STATUS current

         DESCRIPTION

              "This attribute shall specify the number of slots, after a SIFS

              duration, that the STA, for a particular AC, shall sense the

              medium idle either before transmitting or executing a backoff. The

              default value for this attribute is

              1) 7, if qtechdot11EDCATableIndex is 1,

              2) 3, if qtechdot11EDCATableIndex is 2

              3) 2, otherwise."

     ::= { qtechdot11EDCAEntry 4 }

 qtechdot11EDCATableTXOPLimit OBJECT-TYPE

         SYNTAX INTEGER (0..65535)

         MAX-ACCESS read-write

         STATUS current

         DESCRIPTION

              "This attribute shall specify the maximum number of microseconds of

              an EDCA TXOP for a given AC at a non-AP STA. The default value for

              this attribute is

              1) 0 for all PHYs, if qtechdot11EDCATableIndex is 1 or 2; this

              implies that the sender can send one MSDU in an EDCA TXOP,

              2) 3008 microseconds for Clause 17 and Clause 19 PHY and 6016

              microseconds for Clause 18 PHY, if qtechdot11EDCATableIndex is 3,

              3) 1504 microseconds for Clause 17 and Clause 19 PHY and 3264

              microseconds for Clause 18 PHY, if qtechdot11EDCATableIndex is 4."

     ::= { qtechdot11EDCAEntry 5 }

 qtechdot11EDCATableMSDULifetime OBJECT-TYPE

         SYNTAX INTEGER (0..500)

         MAX-ACCESS read-write

         STATUS current

         DESCRIPTION

              "This attribute shall specify (in TUs) the maximum duration an

              MSDU, for a given AC, would be retained by the MAC before it is

              discarded. The default value for this parameter shall be 500."

     ::= { qtechdot11EDCAEntry 6 }

 qtechdot11EDCATableMandatory OBJECT-TYPE

         SYNTAX TruthValue

         MAX-ACCESS read-write

         STATUS current

         DESCRIPTION

             "This attribute, when TRUE, indicates that admission control is

              mandatory for the given AC. When False, this attribute indicates

              that the admission control is not mandatory for the given AC. The

              default value for this parameter shall be FALSE."

     ::= { qtechdot11EDCAEntry 7 }

 -- **********************************************************************

 --      End of SMT EDCA Config TABLE

 -- **********************************************************************


 -- **********************************************************************

 --      SMT AP EDCA Config TABLE

 -- **********************************************************************

 qtechdot11QAPEDCATable OBJECT-TYPE

          SYNTAX SEQUENCE OF Qtechdot11QAPEDCAEntry

          MAX-ACCESS not-accessible

          STATUS current

          DESCRIPTION

               "Conceptual table for EDCA default parameter values at the AP.

               This table shall contain the four entries of the EDCA parameters

               corresponding to four possible ACs. Index 1 corresponds to AC_BK,

               index 2 to AC_BE, index 3 to AC_VI, and index 4 to AC_VO."

         REFERENCE "IEEE 802.11-2007, 9.9.1"

      ::= { qtechWlanDeviceEDCAObjects 2}

 qtechdot11QAPEDCAEntry OBJECT-TYPE

          SYNTAX Qtechdot11QAPEDCAEntry

          MAX-ACCESS not-accessible

          STATUS current

          DESCRIPTION

              "An Entry (conceptual row) in the EDCA Table.

              ifIndex - Each IEEE 802.11 interface is represented by an

              ifEntry. Interface tables in this MIB module are indexed

              by ifIndex."

      INDEX {
         qtechApMacAddr,
         qtechApCfgRadioId,
         qtechdot11QAPEDCATableIndex
      }

      ::= { qtechdot11QAPEDCATable 1 }

 Qtechdot11QAPEDCAEntry ::=

          SEQUENCE {  qtechdot11QAPEDCATableIndex            INTEGER,

                      qtechdot11QAPEDCATableCWmin            INTEGER,

                      qtechdot11QAPEDCATableCWmax            INTEGER,

                      qtechdot11QAPEDCATableAIFSN            INTEGER,

                      qtechdot11QAPEDCATableTXOPLimit        INTEGER,

                      qtechdot11QAPEDCATableMSDULifetime     INTEGER,

                      qtechdot11QAPEDCATableMandatory        TruthValue }


 qtechdot11QAPEDCATableIndex OBJECT-TYPE

          SYNTAX INTEGER (1..4)

          MAX-ACCESS not-accessible

          STATUS current

          DESCRIPTION

               "The auxiliary variable used to identify instances of the columnar

               objects in the EDCA Table. The value of this variable is

                1) 1, if the value of the AC is AC_BK.

                2) 2, if the value of the AC is AC_BE.

                3) 3, if the value of the AC is AC_VI.

                4) 4, if the value of the AC is AC_VO."

     ::= { qtechdot11QAPEDCAEntry 1 }

 qtechdot11QAPEDCATableCWmin OBJECT-TYPE

         SYNTAX INTEGER (0..255)

         MAX-ACCESS read-write

         STATUS current

         DESCRIPTION

              "This attribute shall specify the value of the minimum size of the

              window that shall be used by an AP for a particular AC for

              generating a random number for the backoff. The value of this

              attribute shall be such that it could always be expressed in the

              form of 2X - 1, where X is an integer. The default value for this

              attribute is

              1) aCWmin, if qtechdot11QAPEDCATableIndex is 1 or 2.

              2) (aCWmin+1)/2 - 1, if qtechdot11QAPEDCATableIndex is 3.

              3) (aCWmin+1)/4 - 1, if qtechdot11QAPEDCATableIndex is 4."

     ::= { qtechdot11QAPEDCAEntry 2 }

 qtechdot11QAPEDCATableCWmax OBJECT-TYPE

         SYNTAX INTEGER (0..65535)

         MAX-ACCESS read-write

         STATUS current

         DESCRIPTION

              "This attribute shall specify the value of the maximum size of the

              window that shall be used by an AP for a particular AC for

              generating a random number for the backoff. The value of this

              attribute shall be such that it could always be expressed in the

              form of 2X - 1, where X is an integer. The default value for this

              attribute is

              1) aCWmax, if qtechdot11QAPEDCATableIndex is 1.

              2) 4*(aCWmin+1) - 1, if qtechdot11QAPEDCATableIndex is 2.

              3) aCWmin, if qtechdot11QAPEDCATableIndex is 3.

              4) (aCWmin+1)/2 - 1, if qtechdot11QAPEDCATableIndex is 4."

     ::= { qtechdot11QAPEDCAEntry 3 }

 qtechdot11QAPEDCATableAIFSN OBJECT-TYPE

         SYNTAX INTEGER (1..15)

         MAX-ACCESS read-write

         STATUS current

         DESCRIPTION

              "This attribute shall specify the number of slots, after a SIFS

              duration, that the AP, for a particular AC, shall sense the

              medium idle either before transmitting or executing a backoff. The

              default value for this attribute is

              1) 7, if qtechdot11QAPEDCATableIndex is 1,

              2) 3, if qtechdot11QAPEDCATableIndex is 2

              3) 1, otherwise."

     ::= { qtechdot11QAPEDCAEntry 4 }

 qtechdot11QAPEDCATableTXOPLimit OBJECT-TYPE

         SYNTAX INTEGER (0..65535)

         MAX-ACCESS read-write

         STATUS current

         DESCRIPTION

              "This attribute shall specify the maximum number of microseconds of

              an EDCA TXOP for a given AC at the AP. The default value for

              this attribute is

              1) 0 for all PHYs, if qtechdot11QAPEDCATableIndex is 1 or 2; this

              implies that the sender can send one MSDU in an EDCA TXOP,

              2) 3008 microseconds for Clause 17 and Clause 19 PHY and 6016

              microseconds for Clause 18 PHY, if qtechdot11QAPEDCATableIndex is 3,

              3) 1504 microseconds for Clause 17 and Clause 19 PHY and 3264

               microseconds for Clause 18 PHY, if qtechdot11QAPEDCATableIndex is 4."

      ::= { qtechdot11QAPEDCAEntry 5 }

 qtechdot11QAPEDCATableMSDULifetime OBJECT-TYPE

          SYNTAX INTEGER (0..500)

          MAX-ACCESS read-write

          STATUS current

          DESCRIPTION

               "This attribute shall specify (in TUs) the maximum duration an

               MSDU, for a given AC, would be retained by the MAC at the AP before

               it is discarded. The default value for this parameter shall be

               500."

      ::= { qtechdot11QAPEDCAEntry 6 }

 qtechdot11QAPEDCATableMandatory OBJECT-TYPE

          SYNTAX TruthValue

          MAX-ACCESS read-write

          STATUS current

          DESCRIPTION

               "This attribute, when TRUE, indicates that admission control is

               mandatory for the given AC. When False, this attribute indicates

               that the admission control is not mandatory for the given AC. The

               default value for this parameter shall be FALSE."

      ::= { qtechdot11QAPEDCAEntry 7 }

 -- **********************************************************************

 --      End of SMT AP EDCA Config TABLE

 -- **********************************************************************


--********************************************************
--qtechWlanDeviceEDCAObjects Config
--********************************************************
qtechWlanEDCATable OBJECT-TYPE
            SYNTAX          SEQUENCE OF QtechEDCAStatusEntry
            MAX-ACCESS      not-accessible
            STATUS          current
            DESCRIPTION
                "some wmm access catagery's attribution doesn't appeared in stadard MIBS
                so , we add it here
                "
        ::= { qtechWlanDeviceEDCAObjects 3 }

qtechEDCAStatusEntry	OBJECT-TYPE
			SYNTAX		QtechEDCAStatusEntry
			MAX-ACCESS	not-accessible
			STATUS		current
			DESCRIPTION
				" "
      INDEX {
         qtechApMacAddr,
         qtechApCfgRadioId,
         qtechdot11QAPEDCATableIndex
      }
		::= { qtechWlanEDCATable 1 }

QtechEDCAStatusEntry ::=
        SEQUENCE {
            qtechQAPEDCAqueuedepth          INTEGER,
            qtechQAPEDCAcacPolicy           INTEGER,
            qtechQAPEDCAcacParam            INTEGER
        }

qtechQAPEDCAqueuedepth OBJECT-TYPE
            SYNTAX          INTEGER  (1..512)
            MAX-ACCESS      read-write
            STATUS          current
            DESCRIPTION
                "software queue depth for each wmm access catagery"
            DEFVAL      {512}
        ::= { qtechEDCAStatusEntry 1 }


qtechQAPEDCAcacPolicy OBJECT-TYPE
            SYNTAX          INTEGER {nocac(0), usernum-based(1), channelutilization-based(2)}
            MAX-ACCESS      read-write
            STATUS          current
            DESCRIPTION
                "now  only have two kind of CAC policy , usernum-based (1) and channelutilization-based {2} "

            DEFVAL          {0}
        ::= { qtechEDCAStatusEntry 2}

qtechQAPEDCAcacParam OBJECT-TYPE
            SYNTAX          INTEGER  (0..100)
            MAX-ACCESS      read-write
            STATUS          current
            DESCRIPTION
                "cac param used to determine whether the sta is allowed to be in the high access catagery "
            DEFVAL          {20} -- Used by usernum-based cac policy
        ::= { qtechEDCAStatusEntry 3}


--********************************************************
--qtechWlanDevicePrivMappingObjects config
--********************************************************

qtechWlanDevicePrivMappingWlanDefaultObjects OBJECT IDENTIFIER ::= { qtechWlanDevicePrivMappingObjects 1 }

qtechWlanDevicePrivMappingAPDefaultObjects OBJECT IDENTIFIER ::= { qtechWlanDevicePrivMappingObjects 2 }

qtechWlanDevicePrivMappingTableObjects OBJECT IDENTIFIER ::= { qtechWlanDevicePrivMappingObjects 3 }

--********************************************************
--WLAN default WMM AC Config
--********************************************************

qtechWlanDefaultACTable OBJECT-TYPE
            SYNTAX              SEQUENCE OF QtechWlanDefaultACEntry
            MAX-ACCESS          not-accessible
            STATUS              current
            DESCRIPTION
                " this  table used by non-wmm sta,
                we map the pkt from non-wmm sta to the default WMM access catagery "

        ::= { qtechWlanDevicePrivMappingWlanDefaultObjects 1 }


qtechWlanDefaultACEntry OBJECT-TYPE
			SYNTAX				QtechWlanDefaultACEntry
			MAX-ACCESS			not-accessible
			STATUS				current
			DESCRIPTION
				" "
			INDEX    {
                    qtechApgWlanId
                     }
		::= { qtechWlanDefaultACTable 1}

QtechWlanDefaultACEntry ::=
        SEQUENCE {
            qtechWlanDefualtACnum          INTEGER,
            qtechWlanMaxstadot1ptag        INTEGER
        }

qtechWlanDefualtACnum  OBJECT-TYPE
            SYNTAX          INTEGER
            MAX-ACCESS      read-write
            STATUS          current
            DESCRIPTION
                " this defines the ap's default WMM AC ,used for non-wmm sta
                    "
        ::= { qtechWlanDefaultACEntry 1 }

qtechWlanMaxstadot1ptag  OBJECT-TYPE
            SYNTAX          INTEGER
            MAX-ACCESS      read-write
            STATUS          current
            DESCRIPTION
                " max 802.11e tags a sta in the wlan can use,
                 all pkt have tag larger than this value will fall in the default AC
                    "
        ::= { qtechWlanDefaultACEntry 2 }


--********************************************************
-- AP defualt WMM_AC-DSCP, WMM_AC-802DOT1P mapping pairs config
--********************************************************


qtechPrivMappingAPstatusTable OBJECT-TYPE
            SYNTAX          SEQUENCE OF QtechAPdefaultStatusMappingEntry
            MAX-ACCESS      not-accessible
            STATUS          current
            DESCRIPTION
                " when use CAPWAP, we must map pkt belong to certain WMM-AC to a Certian DSCP priv/802.1p pri
                 and as we must encap the pkt ,we must support two kind of mappings - trunnel and inner,
                 you can get the concept in RFC 5416
                    "
        ::= { qtechWlanDevicePrivMappingAPDefaultObjects 1 }

qtechAPdefaultStatusMappingEntry		OBJECT-TYPE
			SYNTAX				QtechAPdefaultStatusMappingEntry
			MAX-ACCESS			not-accessible
			STATUS				current
			DESCRIPTION
				" "
            INDEX   {
                   qtechApMacAddr
                   }
		::= { qtechPrivMappingAPstatusTable 1 }

QtechAPdefaultStatusMappingEntry ::=
        SEQUENCE {
            qtechdot1pmappingstatus        INTEGER,
            qtechdscpmappingstatus         INTEGER
        }

qtechdot1pmappingstatus OBJECT-TYPE
            SYNTAX          INTEGER
            MAX-ACCESS      read-write
            STATUS          current
            DESCRIPTION
                "How to set the pkt's 802.1p tag  "
            DEFVAL { 0 }
        ::= { qtechAPdefaultStatusMappingEntry  1 }

qtechdscpmappingstatus OBJECT-TYPE
            SYNTAX          INTEGER
            MAX-ACCESS      read-write
            STATUS          current
            DESCRIPTION
                " how to set the pkt's dscp tag
                    "
            DEFVAL {0}
        ::= { qtechAPdefaultStatusMappingEntry 2 }


qtechPrivMappingAPDefaultTable OBJECT-TYPE
            SYNTAX          SEQUENCE OF QtechPrivMappingAPDefaultEntry
            MAX-ACCESS      not-accessible
            STATUS          current
            DESCRIPTION
                " when use CAPWAP, we must map pkt belong to certain WMM-AC to a Certian DSCP priv/802.1p pri
                 and as we must encap the pkt ,we must support two kind of mappings - trunnel and inner,
                 you can get the concept in RFC 5416
                    "
        ::= { qtechWlanDevicePrivMappingAPDefaultObjects 2 }

qtechPrivMappingAPDefaultEntry		OBJECT-TYPE
			SYNTAX			QtechPrivMappingAPDefaultEntry
			MAX-ACCESS		not-accessible
			STATUS			current
			DESCRIPTION
				" "
			INDEX   {
                   qtechApMacAddr,
                   qtechdot11QAPEDCATableIndex
                    }
		::= { qtechPrivMappingAPDefaultTable 1 }

QtechPrivMappingAPDefaultEntry ::=
            SEQUENCE  {
                qtechAPdefaultDSCPTag      INTEGER,
                qtechAPdefaultDot1pTag     INTEGER
            }

qtechAPdefaultDSCPTag OBJECT-TYPE
            SYNTAX          INTEGER (0..63)
            MAX-ACCESS      read-write
            STATUS          current
            DESCRIPTION
                " DEFAULT dscp tag for certain AC"
        ::= { qtechPrivMappingAPDefaultEntry 1 }

qtechAPdefaultDot1pTag OBJECT-TYPE
            SYNTAX          INTEGER
            MAX-ACCESS      read-write
            STATUS          current
            DESCRIPTION
                " default DOT1P TAG VALUE FOR CERTAIN ac"
        ::= { qtechPrivMappingAPDefaultEntry 2 }

--********************************************************
-- mapping tables config
-- svp pkt mapping config
--********************************************************
qtechSVPMappingTable           OBJECT-TYPE
            SYNTAX               SEQUENCE  OF QtechSVPMappingEntry
            MAX-ACCESS           not-accessible
            STATUS               current
            DESCRIPTION
                " dot11radio-SVP-pkt --> WMM-AC:pkt"
        ::= { qtechWlanDevicePrivMappingTableObjects 1 }

qtechSVPMappingEntry   OBJECT-TYPE
            SYNTAX              QtechSVPMappingEntry
            MAX-ACCESS          not-accessible
            STATUS              current
            DESCRIPTION
                "   svp mapping info
                "
            INDEX   {
                    qtechApgWlanId
                }
        ::= { qtechSVPMappingTable 1}



QtechSVPMappingEntry   ::=
            SEQUENCE {
                 qtechSVPmappingStatus      INTEGER,
                 qtechSVPmappingAC          INTEGER
            }

qtechSVPmappingStatus      OBJECT-TYPE
            SYNTAX          INTEGER {enable(0), disable(1)}
            MAX-ACCESS      read-write
            STATUS          current
            DESCRIPTION
             " enable or disable the svp mapping "
        ::= { qtechSVPMappingEntry 1 }

qtechSVPmappingAC          OBJECT-TYPE
            SYNTAX          INTEGER {wmmvo(1), wmmvi(2), wmmbe(3), wmmbk(4)}
            MAX-ACCESS      read-write
            STATUS          current
            DESCRIPTION
            " MAPPING AC"
        ::= { qtechSVPMappingEntry 2 }

--********************************************************
--  qtechWlanDeviceRatelimitObjects
--  wlan-based info config
--  ap-based info config
--  mac-baesd info config
--********************************************************


qtechWlanRatelimitTable OBJECT-TYPE
            SYNTAX          SEQUENCE OF QtechWlanRatelimitEntry
            MAX-ACCESS      not-accessible
            STATUS          current
            DESCRIPTION
                " WLAN-based ratelimit"
        ::= { qtechWlanDeviceRatelimitObjects 1 }

qtechWlanRatelimitEntry	OBJECT-TYPE
             SYNTAX             QtechWlanRatelimitEntry
             MAX-ACCESS         not-accessible
             STATUS             current
             DESCRIPTION
                       " "
             INDEX { qtechApgWlanId, qtechWlanRateLimitDirect }
		::= { qtechWlanRatelimitTable  1 }



QtechWlanRatelimitEntry ::=
            SEQUENCE {
                qtechWlanRateLimitDirect           INTEGER,
                qtechWlanRatelimitStatus           INTEGER,
                qtechWlanAverageRate               INTEGER,
                qtechWlanBurstRate                 INTEGER
            }

qtechWlanRateLimitDirect OBJECT-TYPE
            SYNTAX          INTEGER (0..1)
            MAX-ACCESS      read-only
            STATUS          current
            DESCRIPTION
                " direction of the ratelimited stream
                "
        ::= { qtechWlanRatelimitEntry 1 }

qtechWlanRatelimitStatus OBJECT-TYPE
            SYNTAX          INTEGER (0..1)
            MAX-ACCESS      read-write
            STATUS          current
            DESCRIPTION
                " enable | diable the ratelimit "
        ::= { qtechWlanRatelimitEntry 2 }


qtechWlanAverageRate OBJECT-TYPE
            SYNTAX          INTEGER
            MAX-ACCESS      read-write
            STATUS          current
            DESCRIPTION
                " average rate of the limited stream "
        ::= { qtechWlanRatelimitEntry 3 }

qtechWlanBurstRate OBJECT-TYPE
            SYNTAX          INTEGER
            MAX-ACCESS      read-write
            STATUS          current
            DESCRIPTION
                " burst rate of the limited stream "
        ::= { qtechWlanRatelimitEntry 4 }


qtechAPRatelimitTable  OBJECT-TYPE
            SYNTAX          SEQUENCE OF QtechAPRatelimitEntry
            MAX-ACCESS      not-accessible
            STATUS          current
            DESCRIPTION
                " ap-based ratelimit"
        ::= { qtechWlanDeviceRatelimitObjects 2 }

qtechAPRatelimitEntry	OBJECT-TYPE
			SYNTAX			QtechAPRatelimitEntry
			MAX-ACCESS		not-accessible
			STATUS			current
			DESCRIPTION
				" "
            INDEX   {
                    qtechApMacAddr,
                    qtechAPRateLimitDirect
                    }
		::= { qtechAPRatelimitTable  1 }


QtechAPRatelimitEntry ::=
            SEQUENCE {
                qtechAPRateLimitDirect             INTEGER,
                qtechAPRatelimitStatus             INTEGER,
                qtechAPAverageRate                 INTEGER,
                qtechAPBurstRate                   INTEGER
            }


qtechAPRateLimitDirect OBJECT-TYPE
            SYNTAX          INTEGER (0..1)
            MAX-ACCESS      not-accessible
            STATUS          current
            DESCRIPTION
                " direction of the ratelimited stream
                "
        ::= { qtechAPRatelimitEntry 1 }

qtechAPRatelimitStatus OBJECT-TYPE
            SYNTAX          INTEGER (0..1)
            MAX-ACCESS      read-write
            STATUS          current
            DESCRIPTION
                " enable | diable the ratelimit "
        ::= { qtechAPRatelimitEntry 2 }


qtechAPAverageRate OBJECT-TYPE
            SYNTAX          INTEGER
            MAX-ACCESS      read-write
            STATUS          current
            DESCRIPTION
                " average rate of the limited stream "
        ::= { qtechAPRatelimitEntry 3 }

qtechAPBurstRate OBJECT-TYPE
            SYNTAX          INTEGER
            MAX-ACCESS      read-write
            STATUS          current
            DESCRIPTION
                " burst rate of the limited stream "
        ::= { qtechAPRatelimitEntry 4 }



qtechUserRatelimitTable  OBJECT-TYPE
            SYNTAX          SEQUENCE OF QtechUserRatelimitEntry
            MAX-ACCESS      not-accessible
            STATUS          current
            DESCRIPTION
                " MAC-based ratelimit"
        ::= { qtechWlanDeviceRatelimitObjects 3 }

qtechUserRatelimitEntry	OBJECT-TYPE
            SYNTAX          QtechUserRatelimitEntry
			MAX-ACCESS		not-accessible
			STATUS			current
			DESCRIPTION
				" "
            INDEX   {
                    qtechStaMacAddr,
                    qtechUserRateLimitDirect,
                    qtechApgWlanId
                    }
		::= { qtechUserRatelimitTable  1 }


QtechUserRatelimitEntry ::=
            SEQUENCE {
                qtechUserRateLimitDirect           INTEGER,
                qtechUserRatelimitStatus           INTEGER,
                qtechUserAverageRate               INTEGER,
                qtechUserBurstRate                 INTEGER
            }


qtechUserRateLimitDirect OBJECT-TYPE
            SYNTAX          INTEGER (0..1)
            MAX-ACCESS      not-accessible
            STATUS          current
            DESCRIPTION
                " direction of the ratelimited stream
                "
        ::= { qtechUserRatelimitEntry 1 }

qtechUserRatelimitStatus OBJECT-TYPE
            SYNTAX          INTEGER (0..1)
            MAX-ACCESS      read-write
            STATUS          current
            DESCRIPTION
                " enable | diable the ratelimit "
        ::= { qtechUserRatelimitEntry 2 }


qtechUserAverageRate OBJECT-TYPE
            SYNTAX          INTEGER
            MAX-ACCESS      read-write
            STATUS          current
            DESCRIPTION
                " average rate of the limited stream "
        ::= { qtechUserRatelimitEntry 3 }

qtechUserBurstRate OBJECT-TYPE
            SYNTAX          INTEGER
            MAX-ACCESS      read-write
            STATUS          current
            DESCRIPTION
                " burst rate of the limited stream "
        ::= { qtechUserRatelimitEntry 4 }






--********************************************************************
--*    Compliance statements
--********************************************************************

qtechWlanQosMIBCompliances  OBJECT IDENTIFIER  ::= { qtechWlanQosMIBConform 1 }
qtechWlanQosMIBGroups  OBJECT IDENTIFIER  ::= { qtechWlanQosMIBConform 2 }

qtechWlanQosMIBCompliance MODULE-COMPLIANCE
        STATUS  current
        DESCRIPTION
                "The compliance statement for entities which implement
                the Qos module of Qtech Ac Manager"
        MODULE
                MANDATORY-GROUPS {
                qtechWlanQosWMMEDCAConfigGroup,
                qtechWlanQosRatelimitConfigGroup,
                qtechWlanQosPriMappingonfigGroup
        }
        ::= { qtechWlanQosMIBCompliances 1 }


--********************************************************************
--*    Units of conformance
--********************************************************************
qtechWlanQosWMMEDCAConfigGroup OBJECT-GROUP
        OBJECTS {
		        qtechWMMStatus ,
            qtechAPSDStatus,
            qtechSMPSStatus,
			      qtechQAPEDCAqueuedepth,
            qtechQAPEDCAcacPolicy,
            qtechQAPEDCAcacParam,
			      qtechWlanDefualtACnum,
            qtechWlanMaxstadot1ptag,
			      qtechdot1pmappingstatus,
            qtechdscpmappingstatus,
			      qtechAPdefaultDSCPTag,
            qtechAPdefaultDot1pTag,
			qtechdot11EDCATableCWmin,
			qtechdot11EDCATableCWmax,
			qtechdot11EDCATableAIFSN,
			qtechdot11EDCATableTXOPLimit,
			qtechdot11EDCATableMSDULifetime,
			qtechdot11EDCATableMandatory,
			qtechdot11QAPEDCATableCWmin,
			qtechdot11QAPEDCATableCWmax,
			qtechdot11QAPEDCATableAIFSN,
			qtechdot11QAPEDCATableTXOPLimit,
			qtechdot11QAPEDCATableMSDULifetime,
			qtechdot11QAPEDCATableMandatory
        }
        STATUS     current
        DESCRIPTION
                "This collection of objects represents the
                WMM quality-of-service parameters  networks. "
        ::= { qtechWlanQosMIBGroups 1 }

qtechWlanQosRatelimitConfigGroup OBJECT-GROUP
        OBJECTS  {
			      qtechWlanRateLimitDirect,
            qtechWlanRatelimitStatus,
            qtechWlanAverageRate,
            qtechWlanBurstRate,
            qtechAPRatelimitStatus,
            qtechAPAverageRate,
            qtechAPBurstRate,
            qtechUserRatelimitStatus,
            qtechUserAverageRate,
            qtechUserBurstRate
        }
        STATUS     current
        DESCRIPTION
                "This collection of objects represents the
                 ratelimit parameters 802.11 networks. "
        ::= { qtechWlanQosMIBGroups 2 }

qtechWlanQosPriMappingonfigGroup OBJECT-GROUP
        OBJECTS {
					qtechSVPmappingStatus,
					qtechSVPmappingAC
                }
        STATUS     current
        DESCRIPTION
                "This collection of objects represents the
                pri-mapping parameters 802.11 networks. "
        ::= { qtechWlanQosMIBGroups 3 }


END
