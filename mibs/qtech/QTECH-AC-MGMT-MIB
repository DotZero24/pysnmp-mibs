-- *******************************************************************
-- QTECH-AC-MGMT-MIB.mib : Qtech AC MGMT MIB file
-- January 2009, huangyuanbo
--
-- Copyright (c) 2009 by Qtech Networks Co.,Ltd.
-- All rights reserved.
-- *******************************************************************
--
QTECH-AC-MGMT-MIB DEFINITIONS ::= BEGIN

IMPORTS
        IpAddress,
        OBJECT-TYPE,
        MODULE-IDENTITY,
        NOTIFICATION-TYPE,
        TimeTicks,
        Counter32
                FROM SNMPv2-SMI
        MacAddress,
        TruthValue,
        DisplayString,
        RowStatus
                FROM SNMPv2-TC
        MODULE-COMPLIANCE,
        NOTIFICATION-GROUP,
        OBJECT-GROUP
                FROM SNMPv2-CONF
        InetAddress,
        InetAddressType
                FROM INET-ADDRESS-MIB
        capwapBaseNtfChannelType
                FROM CAPWAP-BASE-MIB
        capwapBaseNtfAuthenMethod
                FROM CAPWAP-BASE-MIB
        capwapBaseNtfChannelDownReason
                FROM CAPWAP-BASE-MIB
        qtechMgmt
                FROM QTECH-SMI;

qtechAcMgmtMIB MODULE-IDENTITY
    LAST-UPDATED "200909180000Z"
    ORGANIZATION "Qtech Networks Co.,Ltd."
    CONTACT-INFO
        "
    Tel: 4008-111-000

    E-mail: service@qtech.com.cn"
    DESCRIPTION
        "This module defines ac management mibs."
    REVISION      "200909180000Z"
    DESCRIPTION
        "Initial version of this MIB module."
    ::= { qtechMgmt 56}

--***************** define the AC root nodes *****************
qtechAcMgmtAcMIBObjects OBJECT IDENTIFIER      ::= { qtechAcMgmtMIB 1 }
qtechAcMgmtAc     OBJECT IDENTIFIER ::= { qtechAcMgmtAcMIBObjects 1 }
qtechAcMgmtAcIf   OBJECT IDENTIFIER ::= { qtechAcMgmtAcMIBObjects 2 }

--***************** define the AP root nodes *****************
qtechAcMgmtApMIBObjects OBJECT IDENTIFIER      ::= { qtechAcMgmtMIB 2 }
qtechAcMgmtAp     OBJECT IDENTIFIER ::= { qtechAcMgmtApMIBObjects 1 }
qtechAcMgmtApIf   OBJECT IDENTIFIER ::= { qtechAcMgmtApMIBObjects 2 }

--******** define the AP group root nodes ************
qtechAcMgmtApgMIBObjects OBJECT IDENTIFIER      ::= { qtechAcMgmtMIB 3 }
qtechAcMgmtApg     OBJECT IDENTIFIER ::= { qtechAcMgmtApgMIBObjects 1 }
qtechAcMgmtApgIf   OBJECT IDENTIFIER ::= { qtechAcMgmtApgMIBObjects 2 }

--******** define the Wlan root nodes ************
qtechAcMgmtWlanMIBObjects OBJECT IDENTIFIER      ::= { qtechAcMgmtMIB 4 }
qtechAcMgmtWlan     OBJECT IDENTIFIER ::= { qtechAcMgmtWlanMIBObjects 1 }
qtechAcMgmtWlanIf   OBJECT IDENTIFIER ::= { qtechAcMgmtWlanMIBObjects 2 }

--******** define the Sta root nodes ************
qtechAcMgmtStaMIBObjects OBJECT IDENTIFIER      ::= { qtechAcMgmtMIB 5 }
qtechAcMgmtSta     OBJECT IDENTIFIER ::= { qtechAcMgmtStaMIBObjects 1 }
qtechAcMgmtStaIf   OBJECT IDENTIFIER ::= { qtechAcMgmtStaMIBObjects 2 }

-- ******** define the notify nodes *************
qtechAcMgmtNotificationsMIBObjects OBJECT IDENTIFIER      ::= { qtechAcMgmtMIB 6 }
qtechAcMgmtNtfObjects     OBJECT IDENTIFIER ::= { qtechAcMgmtNotificationsMIBObjects 1 }
qtechAcMgmtNotifications     OBJECT IDENTIFIER ::= { qtechAcMgmtNotificationsMIBObjects 2 }

--********************************************************************
--                                                                  **
--                  AC nodes                                        **
--                                                                  **
--********************************************************************

-- 1.sta_limit, the station num ac support
qtechAcStaLimit OBJECT-TYPE
    SYNTAX  INTEGER (1..2147483647)
    MAX-ACCESS  read-write
    STATUS  current
    DESCRIPTION
            "The max station this AC supports."
    ::= { qtechAcMgmtAc 1 }

-- 2.wtp_limit, the wtp num ac support
qtechAcWtpLimit OBJECT-TYPE
    SYNTAX  INTEGER (1..2147483647)
    MAX-ACCESS  read-write
    STATUS  current
    DESCRIPTION
            "The max wtp this AC supports."
    ::= { qtechAcMgmtAc 2 }

-- 3.[no] r_mac_field, 0-disable,1-enable
qtechAcRMacField OBJECT-TYPE
    SYNTAX  INTEGER (0..1)
    MAX-ACCESS  read-write
    STATUS  current
    DESCRIPTION
            "Set AC's R-MAC Field."
    ::= { qtechAcMgmtAc 3 }

-- 4.[no] data_dtls, 0-disable,1-enable
qtechAcDataDtls OBJECT-TYPE
    SYNTAX  INTEGER (0..1)
    MAX-ACCESS  read-write
    STATUS  current
    DESCRIPTION
            "Set AC's DTLS Policy Field."
    ::= { qtechAcMgmtAc 4 }

-- 5.[no] ecn_support, 0-disable,1-enable
qtechAcEcnSupport OBJECT-TYPE
    SYNTAX  INTEGER (0..1)
    MAX-ACCESS  read-write
    STATUS  current
    DESCRIPTION
            "Set AC's ECN Support Field."
    ::= { qtechAcMgmtAc 5 }

-- 6.[no] backup_ac_ip ip_address
qtechAcAcIpTable OBJECT-TYPE
    SYNTAX  SEQUENCE OF QtechAcAcIpTableEntry
    MAX-ACCESS  not-accessible
    STATUS  current
    DESCRIPTION
            "Add or Del the AC's backup ip address."
    ::= { qtechAcMgmtAc 6 }

qtechAcAcIpTableEntry OBJECT-TYPE
    SYNTAX  QtechAcAcIpTableEntry
    MAX-ACCESS  not-accessible
    STATUS  current
    DESCRIPTION
        "The entry of Ac's backup ip address."
    INDEX   { qtechAcAcIpIndex}
    ::= { qtechAcAcIpTable 1 }

QtechAcAcIpTableEntry ::=
    SEQUENCE {
        qtechAcAcIpIndex      INTEGER,
        qtechAcBackAcIp       IpAddress,
        qtechAcAcIpRS         RowStatus
    }

-- The Ac name with priority index
qtechAcAcIpIndex OBJECT-TYPE
    SYNTAX  INTEGER (1..512)
    MAX-ACCESS  read-only
    STATUS  current
    DESCRIPTION
            "AC's Ac name with priority index."
    ::= { qtechAcAcIpTableEntry 1 }

qtechAcBackAcIp OBJECT-TYPE
    SYNTAX  IpAddress
    MAX-ACCESS  read-write
    STATUS  current
    DESCRIPTION
            "Set AC's ip list."
    ::= { qtechAcAcIpTableEntry 2 }

qtechAcAcIpRS OBJECT-TYPE
    SYNTAX     RowStatus
    MAX-ACCESS read-write
    STATUS     current
    DESCRIPTION
         "Used to add or del a backup ac ip address in the ac."
    ::= { qtechAcAcIpTableEntry 3 }

-- 7.[no] ecn_support, set the mtu
qtechAcMtu OBJECT-TYPE
    SYNTAX  INTEGER (0..1500)
    MAX-ACCESS  read-write
    STATUS  current
    DESCRIPTION
            "Set AC's MTU."
    ::= { qtechAcMgmtAc 7 }

-- 8.ac_name, set the ac name
qtechAcAcName OBJECT-TYPE
    SYNTAX  DisplayString (SIZE (0..255))
    MAX-ACCESS  read-write
    STATUS  current
    DESCRIPTION
            "Set AC's Name."
    ::= { qtechAcMgmtAc 8 }

-- location location_string
qtechAcLocation  OBJECT-TYPE
    SYNTAX  DisplayString (SIZE (1..255))
    MAX-ACCESS  read-write
    STATUS  current
    DESCRIPTION
            "Ac's location information."
    ::= { qtechAcMgmtAc 9}

-- reset ap_name
qtechAcResetAp  OBJECT-TYPE
    SYNTAX  DisplayString (SIZE (1..255))
    MAX-ACCESS  read-write
    STATUS  current
    DESCRIPTION
            "Delete the ap by assigning the ap name."
    ::= { qtechAcMgmtAc 10}

-- The ap num attached to this ac.
qtechAcApNum OBJECT-TYPE
    SYNTAX  INTEGER (1..800)
    MAX-ACCESS  read-only
    STATUS  current
    DESCRIPTION
            "Ap num attached to this ac."
    ::= { qtechAcMgmtAc 11 }

-- The Ac's 802.11a rate set
qtechAc80211aRateTable OBJECT-TYPE
    SYNTAX  SEQUENCE OF QtechAc80211aRateEntry
    MAX-ACCESS  not-accessible
    STATUS  current
    DESCRIPTION
            "The Ap attributes."
    ::= { qtechAcMgmtAc 12 }

qtechAc80211aRateEntry OBJECT-TYPE
    SYNTAX  QtechAc80211aRateEntry
    MAX-ACCESS  not-accessible
    STATUS  current
    DESCRIPTION
        "Get and set the Ap attribtues."
    INDEX   { qtechAc80211aRate }
    ::= { qtechAc80211aRateTable 1 }

QtechAc80211aRateEntry ::=
    SEQUENCE {
        qtechAc80211aRate     INTEGER,
        qtechAc80211aRateType INTEGER
    }

qtechAc80211aRate  OBJECT-TYPE
    SYNTAX  INTEGER (1..8)
    MAX-ACCESS  not-accessible
    STATUS  current
    DESCRIPTION
            "The global 802.11a rate set in this AC.
            802.11a-6, 9, 12, 18, 24, 36, 48, and 54 Mbps.
            set 1 for 6Mbps, set 2 for 9Mbps, set 3 for 12Mbps,etc..."
    ::= { qtechAc80211aRateEntry 1}

qtechAc80211aRateType  OBJECT-TYPE
    SYNTAX  INTEGER (1..3)
    MAX-ACCESS  read-write
    STATUS  current
    DESCRIPTION
            "The rate type:
            1--disable
            2--mandatory
            3--support"
    ::= { qtechAc80211aRateEntry 2}

-- The Ac's 802.11b rate set
qtechAc80211bRateTable OBJECT-TYPE
    SYNTAX  SEQUENCE OF QtechAc80211bRateEntry
    MAX-ACCESS  not-accessible
    STATUS  current
    DESCRIPTION
            "The 802.11b rate attributes."
    ::= { qtechAcMgmtAc 13 }

qtechAc80211bRateEntry OBJECT-TYPE
    SYNTAX  QtechAc80211bRateEntry
    MAX-ACCESS  not-accessible
    STATUS  current
    DESCRIPTION
        "Get and set the Ap attribtues."
    INDEX   { qtechAc80211bRate }
    ::= { qtechAc80211bRateTable 1 }

QtechAc80211bRateEntry ::=
    SEQUENCE {
        qtechAc80211bRate     INTEGER,
        qtechAc80211bRateType INTEGER
    }

qtechAc80211bRate  OBJECT-TYPE
    SYNTAX  INTEGER (1..3)
    MAX-ACCESS  not-accessible
    STATUS  current
    DESCRIPTION
            "The global 802.11b rate set in this AC.
            802.11b-1, 2, 5.5, 11Mbps.
            set 1 for 1Mbps, set 2 for 2Mbps, set 3 for 5.5Mbps,etc..."
    ::= { qtechAc80211bRateEntry 1}

qtechAc80211bRateType  OBJECT-TYPE
    SYNTAX  INTEGER (1..3)
    MAX-ACCESS  read-write
    STATUS  current
    DESCRIPTION
            "The rate type:
            1--disable
            2--mandatory
            3--support"
    ::= { qtechAc80211bRateEntry 2}

qtechAcFallback  OBJECT-TYPE
    SYNTAX  INTEGER (1..2)
    MAX-ACCESS  read-write
    STATUS  current
    DESCRIPTION
            "The fallback state:
            1--enable, 2--disable"
    ::= { qtechAcMgmtAc 14}

qtechAcStaNum  OBJECT-TYPE
    SYNTAX  INTEGER (1..24000)
    MAX-ACCESS  read-only
    STATUS  current
    DESCRIPTION
            "The client num in this AC."
    ::= { qtechAcMgmtAc 15}

qtechAcMacAddr  OBJECT-TYPE
    SYNTAX  MacAddress
    MAX-ACCESS  read-only
    STATUS  current
    DESCRIPTION
            "The AC's mac address."
    ::= { qtechAcMgmtAc 16}

qtechAcDescriptor  OBJECT-TYPE
    SYNTAX  DisplayString (SIZE (1..255))
    MAX-ACCESS  read-only
    STATUS  current
    DESCRIPTION
            "The AC's descriptor."
    ::= { qtechAcMgmtAc 17}

qtechAcPID  OBJECT-TYPE
    SYNTAX  DisplayString (SIZE (1..255))
    MAX-ACCESS  read-only
    STATUS  current
    DESCRIPTION
            "The AC's product id."
    ::= { qtechAcMgmtAc 18}

qtechAcHwId  OBJECT-TYPE
    SYNTAX  DisplayString (SIZE (1..255))
    MAX-ACCESS  read-only
    STATUS  current
    DESCRIPTION
            "The AC's Hardware Id."
    ::= { qtechAcMgmtAc 19}

qtechAcSN  OBJECT-TYPE
    SYNTAX  DisplayString (SIZE (1..255))
    MAX-ACCESS  read-only
    STATUS  current
    DESCRIPTION
            "The AC's serial number."
    ::= { qtechAcMgmtAc 20}

qtechAcTemp  OBJECT-TYPE
    SYNTAX  INTEGER
    MAX-ACCESS  read-only
    STATUS  current
    DESCRIPTION
            "The AC's temperature."
    ::= { qtechAcMgmtAc 21}

qtechAcAPUpDownCtrl  OBJECT-TYPE
    SYNTAX  INTEGER (0..1)
    MAX-ACCESS  read-write
    STATUS  current
    DESCRIPTION
            "The AP Up/Down trap control
                0 - off
                1 - on."
    ::= { qtechAcMgmtAc 22}

qtechAcAPJoinFailCtrl  OBJECT-TYPE
    SYNTAX  INTEGER (0..1)
    MAX-ACCESS  read-write
    STATUS  current
    DESCRIPTION
            "The AP join fail control
                0 - off
                1 - on."
    ::= { qtechAcMgmtAc 23}

qtechAcAPDecryEroReportCtrl  OBJECT-TYPE
    SYNTAX  INTEGER (0..1)
    MAX-ACCESS  read-write
    STATUS  current
    DESCRIPTION
            "The AP Decry Error Report control
                0 - off
                1 - on."
    ::= { qtechAcMgmtAc 24}

qtechAcApImageUpdtCtrl  OBJECT-TYPE
    SYNTAX  INTEGER (0..1)
    MAX-ACCESS  read-write
    STATUS  current
    DESCRIPTION
            "The AP Image Update Control
                0 - off
                1 - on."
    ::= { qtechAcMgmtAc 25}

qtechAcApConfigMsgEroCtrl  OBJECT-TYPE
    SYNTAX  INTEGER
    MAX-ACCESS  read-write
    STATUS  current
    DESCRIPTION
            "The AP Config Message Error
                0 - off
                1 - on."
    ::= { qtechAcMgmtAc 26}

qtechAcApRadioOperStatuCtrl  OBJECT-TYPE
    SYNTAX  INTEGER
    MAX-ACCESS  read-write
    STATUS  current
    DESCRIPTION
            "The AP Radio Oper Status
                0 - off
                1 - on."
    ::= { qtechAcMgmtAc 27}

qtechAcApAuthenFailCtrl  OBJECT-TYPE
    SYNTAX  INTEGER
    MAX-ACCESS  read-write
    STATUS  current
    DESCRIPTION
            "The AP Authen Fail trap control
                0 - off
                1 - on."
    ::= { qtechAcMgmtAc 28}

qtechAcApTimestampCtrl  OBJECT-TYPE
    SYNTAX  INTEGER
    MAX-ACCESS  read-write
    STATUS  current
    DESCRIPTION
            "The AP timestamp trap control
                0 - off
                1 - on."
    ::= { qtechAcMgmtAc 29}

qtechAcStaOperCtrl  OBJECT-TYPE
    SYNTAX  INTEGER
    MAX-ACCESS  read-write
    STATUS  current
    DESCRIPTION
            "The Sta operation trap control
                0 - off
                1 - on."
    ::= { qtechAcMgmtAc 30}

qtechAcType  OBJECT-TYPE
    SYNTAX  INTEGER {
        ws5302(1),
        ws5708(2),
        m8600ws(3),
        ws3302(4),
        m12000ws(5),
        ws5504(6),
        ws6108(7),
        ws6816(8),
        m18000-WS-ED(9),
        m8600E-WS-ED(10),
        eg2000(11)
    }
    MAX-ACCESS  read-only
    STATUS  current
    DESCRIPTION
            "The Ac type."
    ::= { qtechAcMgmtAc 31}

qtechAcNeid  OBJECT-TYPE
    SYNTAX  DisplayString (SIZE (1..255))
    MAX-ACCESS  read-write
    STATUS  current
    DESCRIPTION
            "The Ac system net id."
    ::= { qtechAcMgmtAc 32}

qtechAcManufacturer  OBJECT-TYPE
    SYNTAX  DisplayString (SIZE (1..255))
    MAX-ACCESS  read-only
    STATUS  current
    DESCRIPTION
            "The Ac's Manufacturer."
    ::= { qtechAcMgmtAc 33}

qtechAcSwVer  OBJECT-TYPE
    SYNTAX  DisplayString (SIZE (1..255))
    MAX-ACCESS  read-only
    STATUS  current
    DESCRIPTION
            "The Ac's software version."
    ::= { qtechAcMgmtAc 34}

qtechAcSwManufacturer  OBJECT-TYPE
    SYNTAX  DisplayString (SIZE (1..255))
    MAX-ACCESS  read-only
    STATUS  current
    DESCRIPTION
            "The Ac's software Manufacturer."
    ::= { qtechAcMgmtAc 35}

qtechAcStaResourceNotEnough  OBJECT-TYPE
    SYNTAX  INTEGER
    MAX-ACCESS  read-only
    STATUS  current
    DESCRIPTION
            "The sta number which can not attach to
             this system for not enough resource."
    ::= { qtechAcMgmtAc 36}

qtechAcPppoeClientAct  OBJECT-TYPE
    SYNTAX  INTEGER
    MAX-ACCESS  read-only
    STATUS  current
    DESCRIPTION
            "The active client number in this AC."
    ::= { qtechAcMgmtAc 37}

qtechAcPppoeClientMax  OBJECT-TYPE
    SYNTAX  INTEGER
    MAX-ACCESS  read-only
    STATUS  current
    DESCRIPTION
            "The client number which this AC support."
    ::= { qtechAcMgmtAc 38}

qtechAcStaActThredhold  OBJECT-TYPE
    SYNTAX  INTEGER
    MAX-ACCESS  read-write
    STATUS  current
    DESCRIPTION
            "The thredhold which the client attach to this AC in one hour."
    ::= { qtechAcMgmtAc 39}

qtechAcStaDisactThredhold  OBJECT-TYPE
    SYNTAX  INTEGER
    MAX-ACCESS  read-write
    STATUS  current
    DESCRIPTION
            "The thredhold which the client leave this AC in one hour."
    ::= { qtechAcMgmtAc 40}

qtechAcStaTotalRoamThredhold  OBJECT-TYPE
    SYNTAX  INTEGER
    MAX-ACCESS  read-only
    STATUS  current
    DESCRIPTION
            "The thredhold which the client's total roaming times."
    ::= { qtechAcMgmtAc 41}

qtechAcStaPerRoamThredhold  OBJECT-TYPE
    SYNTAX  INTEGER
    MAX-ACCESS  read-only
    STATUS  current
    DESCRIPTION
            "The thredhold which the client's roaming times per minite."
    ::= { qtechAcMgmtAc 42}

-- [no] sta-off-line-remain-time number
qtechAcStaOffLineRemainTime  OBJECT-TYPE
    SYNTAX  INTEGER(0..365)
    MAX-ACCESS  read-write
    STATUS  current
    DESCRIPTION
            "This object presents the time which the off line STA statistic remain in the AC."
    ::= { qtechAcMgmtAc 43}

-- [no] sta-off-line-number number
qtechAcStaOffLineNumber  OBJECT-TYPE
    SYNTAX  INTEGER(0..5000)
    MAX-ACCESS  read-write
    STATUS  current
    DESCRIPTION
            "This object presents the max number of the off line STA number statistic."
    ::= { qtechAcMgmtAc 44}

-- sta-off-line-del mac-addr
qtechAcStaOffLineDelSingle  OBJECT-TYPE
    SYNTAX  MacAddress
    MAX-ACCESS  read-write
    STATUS  current
    DESCRIPTION
            "This object presents the mac address which the off line STA to remove its statistic."
    ::= { qtechAcMgmtAc 45}

-- sta-off-line-del all
qtechAcStaOffLineDelAll  OBJECT-TYPE
    SYNTAX  INTEGER(1..1)
    MAX-ACCESS  read-write
    STATUS  current
    DESCRIPTION
            "This object is set to clear all of the off line STA's statistic."
    ::= { qtechAcMgmtAc 46}

-- no ap-config ap-name
qtechAcRmOffLineApConfig  OBJECT-TYPE
    SYNTAX  DisplayString (SIZE (1..65))
    MAX-ACCESS  read-write
    STATUS  current
    DESCRIPTION
            "This object is set to delete the off line AP's configuration."
    ::= { qtechAcMgmtAc 47}

qtechAcFlowBlGroupTable OBJECT-TYPE
    SYNTAX  SEQUENCE OF QtechAcFlowBlGroupEntry
    MAX-ACCESS  not-accessible
    STATUS  current
    DESCRIPTION
            "The flow balance group table"
    ::= { qtechAcMgmtAc 48 }

qtechAcFlowBlGroupEntry OBJECT-TYPE
    SYNTAX  QtechAcFlowBlGroupEntry
    MAX-ACCESS  not-accessible
    STATUS  current
    DESCRIPTION
        "Get and set the flow balance group attribute."
    INDEX   { qtechAcFlowBlGroupName }
    ::= { qtechAcFlowBlGroupTable 1 }

QtechAcFlowBlGroupEntry ::=
    SEQUENCE {
        qtechAcFlowBlGroupName                DisplayString,
        qtechAcFlowBlApName1                  DisplayString,
        qtechAcFlowBlApName2                  DisplayString,
        qtechAcFlowBlApName3                  DisplayString,
        qtechAcFlowBlApName4                  DisplayString,
        qtechAcFlowBlApName5                  DisplayString,
        qtechAcFlowBlApName6                  DisplayString,
        qtechAcFlowBlApName7                  DisplayString,
        qtechAcFlowBlApName8                  DisplayString,
        qtechAcFlowBlApName9                  DisplayString,
        qtechAcFlowBlApName10                 DisplayString,
        qtechAcFlowBlNum                      INTEGER,
        qtechAcFlowBlRS                       RowStatus,
        qtechAcFlowBlEnable                   INTEGER,
        qtechAcFlowBlBase                     INTEGER,
        qtechAcFlowBlIsEnable                 TruthValue
    }

qtechAcFlowBlGroupName  OBJECT-TYPE
    SYNTAX  DisplayString
    MAX-ACCESS  read-only
    STATUS  current
    DESCRIPTION
            "The flow balance group's name."
    ::= { qtechAcFlowBlGroupEntry 1}

qtechAcFlowBlApName1  OBJECT-TYPE
    SYNTAX  DisplayString
    MAX-ACCESS  read-write
    STATUS  current
    DESCRIPTION
            "The AP name belong to this flow balance group."
    ::= { qtechAcFlowBlGroupEntry 2}

qtechAcFlowBlApName2  OBJECT-TYPE
    SYNTAX  DisplayString
    MAX-ACCESS  read-write
    STATUS  current
    DESCRIPTION
            "The AP name belong to this flow balance group."
    ::= { qtechAcFlowBlGroupEntry 3}

qtechAcFlowBlApName3  OBJECT-TYPE
    SYNTAX  DisplayString
    MAX-ACCESS  read-write
    STATUS  current
    DESCRIPTION
            "The AP name belong to this flow balance group."
    ::= { qtechAcFlowBlGroupEntry 4}

qtechAcFlowBlApName4  OBJECT-TYPE
    SYNTAX  DisplayString
    MAX-ACCESS  read-write
    STATUS  current
    DESCRIPTION
            "The AP name belong to this flow balance group."
    ::= { qtechAcFlowBlGroupEntry 5}

qtechAcFlowBlApName5  OBJECT-TYPE
    SYNTAX  DisplayString
    MAX-ACCESS  read-write
    STATUS  current
    DESCRIPTION
            "The AP name belong to this flow balance group."
    ::= { qtechAcFlowBlGroupEntry 6}

qtechAcFlowBlApName6  OBJECT-TYPE
    SYNTAX  DisplayString
    MAX-ACCESS  read-write
    STATUS  current
    DESCRIPTION
            "The AP name belong to this flow balance group."
    ::= { qtechAcFlowBlGroupEntry 7}

qtechAcFlowBlApName7  OBJECT-TYPE
    SYNTAX  DisplayString
    MAX-ACCESS  read-write
    STATUS  current
    DESCRIPTION
            "The AP name belong to this flow balance group."
    ::= { qtechAcFlowBlGroupEntry 8}

qtechAcFlowBlApName8  OBJECT-TYPE
    SYNTAX  DisplayString
    MAX-ACCESS  read-write
    STATUS  current
    DESCRIPTION
            "The AP name belong to this flow balance group."
    ::= { qtechAcFlowBlGroupEntry 9}

qtechAcFlowBlApName9  OBJECT-TYPE
    SYNTAX  DisplayString
    MAX-ACCESS  read-write
    STATUS  current
    DESCRIPTION
            "The AP name belong to this flow balance group."
    ::= { qtechAcFlowBlGroupEntry 10}

qtechAcFlowBlApName10  OBJECT-TYPE
    SYNTAX  DisplayString
    MAX-ACCESS  read-write
    STATUS  current
    DESCRIPTION
            "The AP name belong to this flow balance group."
    ::= { qtechAcFlowBlGroupEntry 11}

qtechAcFlowBlNum  OBJECT-TYPE
    SYNTAX  INTEGER(0..1000)
    MAX-ACCESS  read-write
    STATUS  current
    DESCRIPTION
            "The flow balance group's flow throshold."
    ::= { qtechAcFlowBlGroupEntry 12}

qtechAcFlowBlRS OBJECT-TYPE
    SYNTAX     RowStatus
    MAX-ACCESS read-write
    STATUS     current
    DESCRIPTION
         "Used to add or del or modify the flow balance table."
    ::= { qtechAcFlowBlGroupEntry 13 }

qtechAcFlowBlEnable OBJECT-TYPE
    SYNTAX     INTEGER
    MAX-ACCESS read-write
    STATUS     current
    DESCRIPTION
         "The flow balance group's flow enable throshold."
    ::= { qtechAcFlowBlGroupEntry 14 }

qtechAcFlowBlBase OBJECT-TYPE
    SYNTAX     INTEGER
    MAX-ACCESS read-write
    STATUS     current
    DESCRIPTION
         "The flow balance group's flow base."
    ::= { qtechAcFlowBlGroupEntry 15 }

qtechAcFlowBlIsEnable  OBJECT-TYPE
    SYNTAX  TruthValue
    MAX-ACCESS  read-write
    STATUS  current
    DESCRIPTION
            "The flow balance group's enable/disable."
    ::= { qtechAcFlowBlGroupEntry 16}

qtechAcNumBlGroupTable OBJECT-TYPE
    SYNTAX  SEQUENCE OF QtechAcNumBlGroupEntry
    MAX-ACCESS  not-accessible
    STATUS  current
    DESCRIPTION
            "The number balance group table"
    ::= { qtechAcMgmtAc 49 }

qtechAcNumBlGroupEntry OBJECT-TYPE
    SYNTAX  QtechAcNumBlGroupEntry
    MAX-ACCESS  not-accessible
    STATUS  current
    DESCRIPTION
        "Get and set the number balance group attribute."
    INDEX   { qtechAcNumBlGroupName }
    ::= { qtechAcNumBlGroupTable 1 }

QtechAcNumBlGroupEntry ::=
    SEQUENCE {
        qtechAcNumBlGroupName                DisplayString,
        qtechAcNumBlApName1                  DisplayString,
        qtechAcNumBlApName2                  DisplayString,
        qtechAcNumBlApName3                  DisplayString,
        qtechAcNumBlApName4                  DisplayString,
        qtechAcNumBlApName5                  DisplayString,
        qtechAcNumBlApName6                  DisplayString,
        qtechAcNumBlApName7                  DisplayString,
        qtechAcNumBlApName8                  DisplayString,
        qtechAcNumBlApName9                  DisplayString,
        qtechAcNumBlApName10                 DisplayString,
        qtechAcNumBlNum                      INTEGER,
        qtechAcNumBlRS                       RowStatus,
        qtechAcNumBlEnable                   INTEGER,
        qtechAcNumBlIsEnable                 TruthValue
    }

qtechAcNumBlGroupName  OBJECT-TYPE
    SYNTAX  DisplayString
    MAX-ACCESS  read-only
    STATUS  current
    DESCRIPTION
            "The number balance group's name."
    ::= { qtechAcNumBlGroupEntry 1}

qtechAcNumBlApName1  OBJECT-TYPE
    SYNTAX  DisplayString
    MAX-ACCESS  read-write
    STATUS  current
    DESCRIPTION
            "The AP name belong to this number balance group."
    ::= { qtechAcNumBlGroupEntry 2}

qtechAcNumBlApName2  OBJECT-TYPE
    SYNTAX  DisplayString
    MAX-ACCESS  read-write
    STATUS  current
    DESCRIPTION
            "The AP name belong to this number balance group."
    ::= { qtechAcNumBlGroupEntry 3}

qtechAcNumBlApName3  OBJECT-TYPE
    SYNTAX  DisplayString
    MAX-ACCESS  read-write
    STATUS  current
    DESCRIPTION
            "The AP name belong to this number balance group."
    ::= { qtechAcNumBlGroupEntry 4}

qtechAcNumBlApName4  OBJECT-TYPE
    SYNTAX  DisplayString
    MAX-ACCESS  read-write
    STATUS  current
    DESCRIPTION
            "The AP name belong to this number balance group."
    ::= { qtechAcNumBlGroupEntry 5}

qtechAcNumBlApName5  OBJECT-TYPE
    SYNTAX  DisplayString
    MAX-ACCESS  read-write
    STATUS  current
    DESCRIPTION
            "The AP name belong to this number balance group."
    ::= { qtechAcNumBlGroupEntry 6}

qtechAcNumBlApName6  OBJECT-TYPE
    SYNTAX  DisplayString
    MAX-ACCESS  read-write
    STATUS  current
    DESCRIPTION
            "The AP name belong to this number balance group."
    ::= { qtechAcNumBlGroupEntry 7}

qtechAcNumBlApName7  OBJECT-TYPE
    SYNTAX  DisplayString
    MAX-ACCESS  read-write
    STATUS  current
    DESCRIPTION
            "The AP name belong to this number balance group."
    ::= { qtechAcNumBlGroupEntry 8}

qtechAcNumBlApName8  OBJECT-TYPE
    SYNTAX  DisplayString
    MAX-ACCESS  read-write
    STATUS  current
    DESCRIPTION
            "The AP name belong to this number balance group."
    ::= { qtechAcNumBlGroupEntry 9}

qtechAcNumBlApName9  OBJECT-TYPE
    SYNTAX  DisplayString
    MAX-ACCESS  read-write
    STATUS  current
    DESCRIPTION
            "The AP name belong to this number balance group."
    ::= { qtechAcNumBlGroupEntry 10}

qtechAcNumBlApName10  OBJECT-TYPE
    SYNTAX  DisplayString
    MAX-ACCESS  read-write
    STATUS  current
    DESCRIPTION
            "The AP name belong to this number balance group."
    ::= { qtechAcNumBlGroupEntry 11}

qtechAcNumBlNum  OBJECT-TYPE
    SYNTAX  INTEGER(0..1000)
    MAX-ACCESS  read-write
    STATUS  current
    DESCRIPTION
            "The number balance group's number throshold."
    ::= { qtechAcNumBlGroupEntry 12}

qtechAcNumBlRS OBJECT-TYPE
    SYNTAX     RowStatus
    MAX-ACCESS read-write
    STATUS     current
    DESCRIPTION
         "Used to add or del or modify the number balance table."
    ::= { qtechAcNumBlGroupEntry 13 }

qtechAcNumBlEnable  OBJECT-TYPE
    SYNTAX  INTEGER
    MAX-ACCESS  read-write
    STATUS  current
    DESCRIPTION
            "The number balance group's number enable throshold."
    ::= { qtechAcNumBlGroupEntry 14}

qtechAcNumBlIsEnable  OBJECT-TYPE
    SYNTAX  TruthValue
    MAX-ACCESS  read-write
    STATUS  current
    DESCRIPTION
            "The number balance group's enable/disable."
    ::= { qtechAcNumBlGroupEntry 15}

qtechAcInAcRoamNum  OBJECT-TYPE
    SYNTAX  INTEGER
    MAX-ACCESS  read-only
    STATUS  current
    DESCRIPTION
            "The Sta roaming in this AC."
    ::= { qtechAcMgmtAc 50}

qtechAcBetweenAcRoamInNum  OBJECT-TYPE
    SYNTAX  INTEGER
    MAX-ACCESS  read-only
    STATUS  current
    DESCRIPTION
            "The Sta roaming in timers while roaming between ACs."
    ::= { qtechAcMgmtAc 51}

qtechAcStaOnOverThrodOperCtrl  OBJECT-TYPE
    SYNTAX  INTEGER
    MAX-ACCESS  read-write
    STATUS  current
    DESCRIPTION
            "The Sta on times over thredhold trap control
                0 - off
                1 - on."
    ::= { qtechAcMgmtAc 52}

qtechAcStaOffOverThrodOperCtrl  OBJECT-TYPE
    SYNTAX  INTEGER
    MAX-ACCESS  read-write
    STATUS  current
    DESCRIPTION
            "The Sta off times over thredhold trap control
                0 - off
                1 - on."
    ::= { qtechAcMgmtAc 53}

qtechAcBetweenAcRoamOutNum OBJECT-TYPE
    SYNTAX  INTEGER
    MAX-ACCESS  read-only
    STATUS  current
    DESCRIPTION
            "The Sta roaming out timers while roaming between ACs."
    ::= { qtechAcMgmtAc 54}

qtechAcCpusageSwitch  OBJECT-TYPE
    SYNTAX  INTEGER
    MAX-ACCESS  read-write
    STATUS  current
    DESCRIPTION
            "This object presents the qtechApCpuUsageTrapTimer node active or not.
             1 -- on
             2 -- off"
    ::= { qtechAcMgmtAc 55 }

qtechAcCpuUsageTrapTimer OBJECT-TYPE
    SYNTAX      INTEGER
    MAX-ACCESS  read-write
    STATUS      current
    DESCRIPTION
            "This object represents the AP's cpu usage info trap timer,
             second. Set to all APs."
    ::= { qtechAcMgmtAc 56 }

qtechAcStatTrapTimer  OBJECT-TYPE
    SYNTAX  INTEGER
    MAX-ACCESS  read-write
    STATUS  current
    DESCRIPTION
            "This object present the AP's radio statistic
             trap timer, second. Set to all APs."
    ::= { qtechAcMgmtAc 57}

qtechAcHeartBeat  OBJECT-TYPE
    SYNTAX  INTEGER
    MAX-ACCESS  read-write
    STATUS  current
    DESCRIPTION
            "The heart beat between AC and AP，should not greater than 75s，second.
             Set 0 to turn off this function."
    ::= { qtechAcMgmtAc 58}

qtechAcTotalApSupNum  OBJECT-TYPE
    SYNTAX  INTEGER
    MAX-ACCESS  read-only
    STATUS  current
    DESCRIPTION
            "This object present the ACs' max num of supported APs."
    ::= { qtechAcMgmtAc 59}

qtechAcTotalStaSupNum  OBJECT-TYPE
    SYNTAX  INTEGER
    MAX-ACCESS  read-only
    STATUS  current
    DESCRIPTION
            "This object present the ACs' max num of supported STAs."
    ::= { qtechAcMgmtAc 60}

qtechAcTotalPppoeSupNum  OBJECT-TYPE
    SYNTAX  INTEGER
    MAX-ACCESS  read-only
    STATUS  current
    DESCRIPTION
            "This object present the ACs' maximum number of pppoe authentication."
    ::= { qtechAcMgmtAc 61}

qtechAcCurTotalApSupNum  OBJECT-TYPE
    SYNTAX  INTEGER
    MAX-ACCESS  read-only
    STATUS  current
    DESCRIPTION
            "This object present the current ACs' max num of supported STAs."
    ::= { qtechAcMgmtAc 62}

qtechAcCurTotalStaSupNum  OBJECT-TYPE
    SYNTAX  INTEGER
    MAX-ACCESS  read-only
    STATUS  current
    DESCRIPTION
            "This object present the current ACs' max num of supported STAs."
    ::= { qtechAcMgmtAc 63}

qtechAcCurTotalPppoeSupNum  OBJECT-TYPE
    SYNTAX  INTEGER
    MAX-ACCESS  read-only
    STATUS  current
    DESCRIPTION
            "This object present the current the ACs' maximum number of pppoe authentication."
    ::= { qtechAcMgmtAc 64}

qtechAcNasId  OBJECT-TYPE
    SYNTAX      DisplayString
    MAX-ACCESS  read-write
    STATUS      current
    DESCRIPTION
            "The NAS ID about this AC."
    ::= { qtechAcMgmtAc 65}

qtechAcStaLimitLicense OBJECT-TYPE
    SYNTAX  INTEGER
    MAX-ACCESS  read-only
    STATUS  current
    DESCRIPTION
            "The max station this AC supports by license."
    ::= { qtechAcMgmtAc 66 }

qtechAcWtpLimitLicense OBJECT-TYPE
    SYNTAX  INTEGER
    MAX-ACCESS  read-only
    STATUS  current
    DESCRIPTION
            "The max wtp this AC supports by license."
    ::= { qtechAcMgmtAc 67 }

qtechAcStaIpv6Num  OBJECT-TYPE
    SYNTAX  INTEGER (1..24000)
    MAX-ACCESS  read-only
    STATUS  current
    DESCRIPTION
            "The ipv6 client num in this AC."
    ::= { qtechAcMgmtAc 68}

qtechAcIpv6  OBJECT-TYPE
    SYNTAX      DisplayString
    MAX-ACCESS  read-only
    STATUS      current
    DESCRIPTION
            "AC's ipv6 address."
    ::= { qtechAcMgmtAc 69}

qtechAcIpv6Prefix  OBJECT-TYPE
    SYNTAX      DisplayString
    MAX-ACCESS  read-only
    STATUS      current
    DESCRIPTION
            "AC's ipv6 address prefix."
    ::= { qtechAcMgmtAc 70}

qtechAcIpv6Type  OBJECT-TYPE
    SYNTAX  INTEGER {
        unknown(0),
        unicase(1),
        anycase(2),
        multicase(3)
    }
    MAX-ACCESS  read-only
    STATUS      current
    DESCRIPTION
            "AC's ipv6 address type."
    ::= { qtechAcMgmtAc 71}

qtechAcIpv6AddrType  OBJECT-TYPE
    SYNTAX      DisplayString
    MAX-ACCESS  read-only
    STATUS      current
    DESCRIPTION
            "AC's anycast address type."
    ::= { qtechAcMgmtAc 72}

qtechAcKickClient  OBJECT-TYPE
    SYNTAX  MacAddress
    MAX-ACCESS  read-write
    STATUS  current
    DESCRIPTION
            "Set the mac and corresponding client will be kicked. Get this object will return last kicked client."
    ::= { qtechAcMgmtAc 73}

qtechAcOpenStaNum  OBJECT-TYPE
    SYNTAX  INTEGER
    MAX-ACCESS  read-only
    STATUS  current
    DESCRIPTION
            "Open client num in this AC."
    ::= { qtechAcMgmtAc 74}

qtechAcOpenStaAbnormalDownTimes  OBJECT-TYPE
    SYNTAX  INTEGER
    MAX-ACCESS  read-only
    STATUS  current
    DESCRIPTION
            "The times open client is abnormaly offline."
    ::= { qtechAcMgmtAc 75}

qtechAcWepPskStaNum  OBJECT-TYPE
    SYNTAX  INTEGER
    MAX-ACCESS  read-only
    STATUS  current
    DESCRIPTION
            "WEP/PSK client num in this AC."
    ::= { qtechAcMgmtAc 76}

qtechAcWepPskStaAbnormalDownTimes  OBJECT-TYPE
    SYNTAX  INTEGER
    MAX-ACCESS  read-only
    STATUS  current
    DESCRIPTION
            "The times WEP/PSK client is abnormaly offline."
    ::= { qtechAcMgmtAc 77}

--********************************************************************
--                                                                  **
--                  AP nodes                                        **
--                                                                  **
--********************************************************************
qtechApCfgTable OBJECT-TYPE
    SYNTAX  SEQUENCE OF QtechApCfgEntry
    MAX-ACCESS  not-accessible
    STATUS  current
    DESCRIPTION
            "The Ap attributes."
    ::= { qtechAcMgmtAp 1 }

qtechApCfgEntry OBJECT-TYPE
    SYNTAX  QtechApCfgEntry
    MAX-ACCESS  not-accessible
    STATUS  current
    DESCRIPTION
        "Get and set the Ap attribtues."
    INDEX   { qtechApMacAddr }
    ::= { qtechApCfgTable 1 }

QtechApCfgEntry ::=
    SEQUENCE {
        qtechApMacAddr                 MacAddress,
        qtechApApName                  DisplayString,
        qtechApApgName                 DisplayString,
        qtechApDiscTimer               INTEGER,
        qtechApEchoReqTimer            INTEGER,
        qtechApEroReportTimer          INTEGER,
        qtechApStaTimeoutTimer         INTEGER,
        qtechApStatisticsTimer         INTEGER,
        qtechApFallback                INTEGER,
        qtechApImageId                 DisplayString,
        qtechApIpDhcp                  INTEGER,
        qtechApLocation                DisplayString,
        qtechApWpsMfp                  INTEGER,
        qtechApLastRebootReason        INTEGER,
        qtechApEthernetIfName          DisplayString,
        qtechApEthernetIfMacAddress    MacAddress,
        qtechApEthernetIfAdminStatus   INTEGER,
        qtechApEthernetIfOperStatus    INTEGER,
        qtechApEthernetIfRxUcastPkts   Counter32,
        qtechApEthernetIfRxNUcastPkts  Counter32,
        qtechApEthernetIfTxUcastPkts   Counter32,
        qtechApEthernetIfTxNUcastPkts  Counter32,
        qtechApEthernetIfDuplex        INTEGER,
        qtechApEthernetIfLinkSpeed     INTEGER,
        qtechApEthernetIfPOEPower      INTEGER,
        qtechApEthernetIfRxBoardPkts   Counter32,
        qtechApEthernetIfRxMultiPkts   Counter32,
        qtechApEthernetIfTxBoardPkts   Counter32,
        qtechApEthernetIfTxMultiPkts   Counter32,
        qtechApEthernetIfDropPkts      Counter32,
        qtechApAdminStatus             INTEGER,
        qtechApSn                      DisplayString,
        qtechApIp                      IpAddress,
        qtechApStaNum                  INTEGER,
        qtechApToFat                   INTEGER,
        qtechApId                      INTEGER,
        qtechApSwVer                   DisplayString,
        qtechApBootVer                 DisplayString,
        qtechApPID                     DisplayString,
        qtechApHwVer                   DisplayString,
        qtechApStaLimit                INTEGER,
        qtechApFactoryDefault          INTEGER,
        qtechApCpuUsageTrapTimer       INTEGER,
        qtechApStatTrapTimer           INTEGER,
        qtechApLinkOnTimeInterval      INTEGER,
        qtechApNetId                   DisplayString,
        qtechApUptime                  DisplayString,
        qtechApState                   INTEGER,
        qtechApNasId                   DisplayString,
        qtechApCoverArea               INTEGER,
        qtechApLinkOnTimeIntervalMs    TimeTicks,
        qtechApUptimeMs                TimeTicks,
        qtechApHbUptimeMs              TimeTicks,
        qtechApIpv6                    InetAddress,
        qtechApIpv6Prefix              DisplayString,
        qtechApIpv6PrefixLen           INTEGER,
        qtechApIpv6Type                INTEGER,
        qtechApIpv6Gateway             DisplayString,
        qtechApIpv6StaNum              INTEGER
    }

qtechApMacAddr  OBJECT-TYPE
    SYNTAX  MacAddress
    MAX-ACCESS  read-only
    STATUS  current
    DESCRIPTION
            "The AP's ethernet mac address."
    ::= { qtechApCfgEntry 1}

-- The AP Name
qtechApApName  OBJECT-TYPE
    SYNTAX  DisplayString (SIZE (1..64))
    MAX-ACCESS  read-write
    STATUS  current
    DESCRIPTION
            "Ap's Name."
    ::= { qtechApCfgEntry 2}

-- The Ap group name
qtechApApgName  OBJECT-TYPE
    SYNTAX  DisplayString (SIZE (1..255))
    MAX-ACCESS  read-write
    STATUS  current
    DESCRIPTION
            "Ap group Name."
    ::= { qtechApCfgEntry 3 }

-- The Discovery timer
qtechApDiscTimer  OBJECT-TYPE
    SYNTAX  INTEGER (2..180)
    MAX-ACCESS  read-write
    STATUS  current
    DESCRIPTION
            "Discovery timer."
    ::= { qtechApCfgEntry 4 }

-- The Echo Request timer
qtechApEchoReqTimer  OBJECT-TYPE
    SYNTAX  INTEGER (5..255)
    MAX-ACCESS  read-write
    STATUS  current
    DESCRIPTION
            "Echo Request timer."
    ::= { qtechApCfgEntry 5 }

-- The Error Report timer
qtechApEroReportTimer  OBJECT-TYPE
    SYNTAX  INTEGER (1..1080)
    MAX-ACCESS  read-write
    STATUS  current
    DESCRIPTION
            "Error Report timer."
    ::= { qtechApCfgEntry 6 }

-- The Sta timeout timer
qtechApStaTimeoutTimer  OBJECT-TYPE
    SYNTAX  INTEGER (1..2700)
    MAX-ACCESS  read-write
    STATUS  current
    DESCRIPTION
            "station idle timeout timer."
    ::= { qtechApCfgEntry 7 }

-- The Statistics timeout timer
qtechApStatisticsTimer  OBJECT-TYPE
    SYNTAX  INTEGER (1..65535)
    MAX-ACCESS  read-write
    STATUS  current
    DESCRIPTION
            "station idle timeout timer."
    ::= { qtechApCfgEntry 8 }

-- The fallback value, 1-enable, 2-disable
qtechApFallback  OBJECT-TYPE
    SYNTAX  INTEGER (1..2)
    MAX-ACCESS  read-write
    STATUS  current
    DESCRIPTION
            "The fallback value, 1--enable, 2--disable."
    ::= { qtechApCfgEntry 9 }

-- The Image id
qtechApImageId  OBJECT-TYPE
    SYNTAX  DisplayString (SIZE (1..128))
    MAX-ACCESS  read-write
    STATUS  current
    DESCRIPTION
            "The Image version."
    ::= { qtechApCfgEntry 10 }

-- The ip dhcp option value, 0-standard, 1-private
qtechApIpDhcp  OBJECT-TYPE
    SYNTAX  INTEGER (0..1)
    MAX-ACCESS  read-write
    STATUS  current
    DESCRIPTION
            "The ip dhcp option value, 0--standard, 1--private."
    ::= { qtechApCfgEntry 11 }

-- The ap location
qtechApLocation  OBJECT-TYPE
    SYNTAX  DisplayString (SIZE(1..255))
    MAX-ACCESS  read-write
    STATUS  current
    DESCRIPTION
            "Ap Location."
    ::= { qtechApCfgEntry 12}

-- 0-disable, 1-enable
qtechApWpsMfp  OBJECT-TYPE
    SYNTAX  INTEGER (0..1)
    MAX-ACCESS  read-write
    STATUS  current
    DESCRIPTION
            "0-disable, 1-enable."
    ::= { qtechApCfgEntry 13}

qtechApLastRebootReason  OBJECT-TYPE
    SYNTAX  INTEGER {
                notSupport(0),
                acInit(1),
                linkFail(2),
                sWFail(3),
                hWFail(4),
                otherFail(5),
                unknown(255)
            }
    MAX-ACCESS  read-only
    STATUS  current
    DESCRIPTION
            "The AP's last reboot reason."
    ::= { qtechApCfgEntry 14}

qtechApEthernetIfName OBJECT-TYPE
    SYNTAX DisplayString (SIZE(1..32))
    MAX-ACCESS read-only
    STATUS current
    DESCRIPTION
            "This object represents the name of the Ethernet interface."
    ::= { qtechApCfgEntry 15 }

qtechApEthernetIfMacAddress OBJECT-TYPE
    SYNTAX     MacAddress
    MAX-ACCESS read-only
    STATUS     current
    DESCRIPTION
            "This object represents MAC address of the Ethernet interface
             in the slot represented by qtechApEthernetIfSlotId."
    ::= { qtechApCfgEntry 16 }

qtechApEthernetIfAdminStatus OBJECT-TYPE
    SYNTAX      INTEGER
    MAX-ACCESS read-only
    STATUS     current
    DESCRIPTION
            "This object represents the admin state of the physical
             Ethernet interface on the AP."
    ::= { qtechApCfgEntry 17 }

qtechApEthernetIfOperStatus OBJECT-TYPE
    SYNTAX      INTEGER
    MAX-ACCESS read-only
    STATUS     current
    DESCRIPTION
            "This object represents the operational state of the physical
             Ethernet interface on the AP."
    ::= { qtechApCfgEntry 18 }

qtechApEthernetIfRxUcastPkts OBJECT-TYPE
    SYNTAX     Counter32
    UNITS      "packets"
    MAX-ACCESS read-only
    STATUS     current
    DESCRIPTION
            "This object represents total number of unicast packets
            received on the interface."
    ::= { qtechApCfgEntry 19 }

qtechApEthernetIfRxNUcastPkts OBJECT-TYPE
    SYNTAX      Counter32
    UNITS       "packets"
    MAX-ACCESS  read-only
    STATUS      current
    DESCRIPTION
            "This object represents total number of non-unicast or
            mulitcast packets received on the interface"
    ::= { qtechApCfgEntry 20 }

qtechApEthernetIfTxUcastPkts OBJECT-TYPE
    SYNTAX     Counter32
    UNITS      "packets"
    MAX-ACCESS read-only
    STATUS     current
    DESCRIPTION
            "This object represents total number of unicast packets
            transmitted on the interface."
    ::= { qtechApCfgEntry 21 }

qtechApEthernetIfTxNUcastPkts OBJECT-TYPE
    SYNTAX     Counter32
    UNITS      "packets"
    MAX-ACCESS read-only
    STATUS     current
    DESCRIPTION
            "This object represents total number of non-unicast or
            mulitcast packets transmitted on the interface"
    ::= { qtechApCfgEntry 22 }

qtechApEthernetIfDuplex OBJECT-TYPE
    SYNTAX     INTEGER {
        unknown(1),
        halfduplex(2),
        fullduplex(3),
        auto(4)
    }
    MAX-ACCESS read-only
    STATUS     current
    DESCRIPTION
            "This object represents interface's duplex mode"
    ::= { qtechApCfgEntry 23 }

qtechApEthernetIfLinkSpeed OBJECT-TYPE
    SYNTAX     INTEGER
    MAX-ACCESS read-only
    STATUS     current
    DESCRIPTION
            "Speed of the interface in units of 1,000,000 bits per second"
    ::= { qtechApCfgEntry 24 }

qtechApEthernetIfPOEPower OBJECT-TYPE
    SYNTAX     INTEGER {
        none(1),
        drawn(2),
        notdrawn(3)
    }
    MAX-ACCESS read-only
    STATUS     current
    DESCRIPTION
      "This object represents whether this interface supports
      Power Over Ethernet (POE)
      none     - POE is not supported
      drawn    - This interface supports POE, and power is
                 being drawn
      notdrawn - POE power is not drawn"
    ::= { qtechApCfgEntry 25 }


qtechApAdminStatus OBJECT-TYPE
    SYNTAX     INTEGER {
        enable(1),
        disable(2)
    }
    MAX-ACCESS read-write
    STATUS     current
    DESCRIPTION
      "This object represents whether this interface supports
      Power Over Ethernet (POE)
      enable     - enable to admin
      disable    - disable to admin"
    ::= { qtechApCfgEntry 26 }

qtechApEthernetIfRxBoardPkts OBJECT-TYPE
    SYNTAX      Counter32
    UNITS       "packets"
    MAX-ACCESS  read-only
    STATUS      current
    DESCRIPTION
            "This object represents total number of boardcast packets received on the interface"
    ::= { qtechApCfgEntry 27 }

qtechApEthernetIfRxMultiPkts OBJECT-TYPE
    SYNTAX      Counter32
    UNITS       "packets"
    MAX-ACCESS  read-only
    STATUS      current
    DESCRIPTION
            "This object represents total number of mulitcast packets received on the interface"
    ::= { qtechApCfgEntry 28 }

qtechApEthernetIfTxBoardPkts OBJECT-TYPE
    SYNTAX      Counter32
    UNITS       "packets"
    MAX-ACCESS  read-only
    STATUS      current
    DESCRIPTION
            "This object represents total number of boardcast packets transmitted on the interface"
    ::= { qtechApCfgEntry 29 }

qtechApEthernetIfTxMultiPkts OBJECT-TYPE
    SYNTAX      Counter32
    UNITS       "packets"
    MAX-ACCESS  read-only
    STATUS      current
    DESCRIPTION
            "This object represents total number of multicast packets transmitted on the interface"
    ::= { qtechApCfgEntry 30 }

qtechApEthernetIfDropPkts OBJECT-TYPE
    SYNTAX      Counter32
    UNITS       "packets"
    MAX-ACCESS  read-only
    STATUS      current
    DESCRIPTION
            "This object represents total number of packets dropped on the interface"
    ::= { qtechApCfgEntry 31 }

qtechApSn OBJECT-TYPE
    SYNTAX      DisplayString
    MAX-ACCESS  read-only
    STATUS      current
    DESCRIPTION
            "This object represents SN string of the AP."
    ::= { qtechApCfgEntry 32 }

qtechApIp OBJECT-TYPE
    SYNTAX      IpAddress
    MAX-ACCESS  read-only
    STATUS      current
    DESCRIPTION
            "This object represents ip address of the AP."
    ::= { qtechApCfgEntry 33 }

qtechApStaNum OBJECT-TYPE
    SYNTAX      INTEGER
    MAX-ACCESS  read-only
    STATUS      current
    DESCRIPTION
            "This object represents Sta Num attach to the AP."
    ::= { qtechApCfgEntry 34 }

qtechApToFat OBJECT-TYPE
    SYNTAX      INTEGER(0..1)
    MAX-ACCESS  read-write
    STATUS      current
    DESCRIPTION
            "This object represents the ap mode, 0 - fit, 1 - fat."
    ::= { qtechApCfgEntry 35 }

qtechApId OBJECT-TYPE
    SYNTAX      INTEGER(1..800)
    MAX-ACCESS  read-only
    STATUS      current
    DESCRIPTION
            "The AP Id"
    ::= { qtechApCfgEntry 36 }

qtechApSwVer OBJECT-TYPE
    SYNTAX      DisplayString
    MAX-ACCESS  read-only
    STATUS      current
    DESCRIPTION
            "This object represents SN string of the AP."
    ::= { qtechApCfgEntry 37 }

qtechApBootVer OBJECT-TYPE
    SYNTAX      DisplayString
    MAX-ACCESS  read-only
    STATUS      current
    DESCRIPTION
            "This object represents boot version string of the AP."
    ::= { qtechApCfgEntry 38 }

qtechApPID OBJECT-TYPE
    SYNTAX      DisplayString
    MAX-ACCESS  read-only
    STATUS      current
    DESCRIPTION
            "This object represents product id string of the AP."
    ::= { qtechApCfgEntry 39 }

qtechApHwVer OBJECT-TYPE
    SYNTAX      DisplayString
    MAX-ACCESS  read-only
    STATUS      current
    DESCRIPTION
            "This object represents hardware string of the AP."
    ::= { qtechApCfgEntry 40 }

qtechApStaLimit OBJECT-TYPE
    SYNTAX      INTEGER(1..30)
    MAX-ACCESS  read-write
    STATUS      current
    DESCRIPTION
            "This object represents client num limit of the AP."
    ::= { qtechApCfgEntry 41 }

qtechApFactoryDefault OBJECT-TYPE
    SYNTAX      INTEGER {
        normal(0),
        reset(1)
    }
    MAX-ACCESS  read-write
    STATUS      current
    DESCRIPTION
            "1 -- Set the ap to reboot with the factory default configuration."
    ::= { qtechApCfgEntry 42 }

qtechApCpuUsageTrapTimer OBJECT-TYPE
    SYNTAX      INTEGER
    MAX-ACCESS  read-write
    STATUS      current
    DESCRIPTION
            "This object represents the AP's cpu usage info trap timer,
             second."
    ::= { qtechApCfgEntry 43 }


qtechApStatTrapTimer  OBJECT-TYPE
    SYNTAX  INTEGER
    MAX-ACCESS  read-write
    STATUS  current
    DESCRIPTION
            "This object present the AP's radio statistic
             trap timer, second."
    ::= { qtechApCfgEntry 44}

qtechApLinkOnTimeInterval OBJECT-TYPE
    SYNTAX      INTEGER
    MAX-ACCESS  read-only
    STATUS      current
    DESCRIPTION
            "This object represents the AP's Link on time interval, seconds."
    ::= { qtechApCfgEntry 45 }

qtechApNetId OBJECT-TYPE
    SYNTAX      DisplayString
    MAX-ACCESS  read-write
    STATUS      current
    DESCRIPTION
            "This object represents the AP's net unit code."
    ::= { qtechApCfgEntry 46 }

qtechApUptime OBJECT-TYPE
    SYNTAX      DisplayString
    MAX-ACCESS  read-only
    STATUS      current
    DESCRIPTION
            "This object represents the AP's capwap uptime."
    ::= { qtechApCfgEntry 47 }

qtechApState OBJECT-TYPE
    SYNTAX      INTEGER
    MAX-ACCESS  read-only
    STATUS      current
    DESCRIPTION
            "This object represents the AP's state.
                1 -- on line;
                2 -- off line"
    ::= { qtechApCfgEntry 48 }

qtechApNasId  OBJECT-TYPE
    SYNTAX      DisplayString
    MAX-ACCESS  read-write
    STATUS      current
    DESCRIPTION
            "The NAS ID about this AP."
    ::= { qtechApCfgEntry 49 }

qtechApCoverArea OBJECT-TYPE
    SYNTAX      INTEGER
    MAX-ACCESS  read-write
    STATUS      current
    DESCRIPTION
            "This object represents the AP's cover type.
                1 -- Type A: School;
                2 -- Type B: Airfield, Station;
                3 -- Type C: Hospital, Hotel, Marketplace;
                4 -- Type D: Group customers with specific WLAN requirements"
    ::= { qtechApCfgEntry 50 }

qtechApLinkOnTimeIntervalMs OBJECT-TYPE
    SYNTAX      TimeTicks
    MAX-ACCESS  read-only
    STATUS      current
    DESCRIPTION
            "This object represents the AP's Link on time interval, 0.01seconds."
    ::= { qtechApCfgEntry 51 }

qtechApUptimeMs OBJECT-TYPE
    SYNTAX      TimeTicks
    MAX-ACCESS  read-only
    STATUS      current
    DESCRIPTION
            "This object represents the AP's capwap uptime, 0.01seconds."
    ::= { qtechApCfgEntry 52 }

qtechApHbUptimeMs OBJECT-TYPE
    SYNTAX      TimeTicks
    MAX-ACCESS  read-only
    STATUS      current
    DESCRIPTION
            "This object represents the AP's capwap hotback uptime, 0.01seconds."
    ::= { qtechApCfgEntry 53 }

qtechApIpv6 OBJECT-TYPE
    SYNTAX      InetAddress
    MAX-ACCESS  read-only
    STATUS      current
    DESCRIPTION
            "This object represents ipv6 address of the AP."
    ::= { qtechApCfgEntry 54 }

qtechApIpv6Prefix OBJECT-TYPE
    SYNTAX      DisplayString
    MAX-ACCESS  read-only
    STATUS      current
    DESCRIPTION
            "This object represents ipv6 address prefix of the AP."
    ::= { qtechApCfgEntry 55 }

qtechApIpv6PrefixLen OBJECT-TYPE
    SYNTAX      INTEGER
    MAX-ACCESS  read-only
    STATUS      current
    DESCRIPTION
            "This object represents ipv6 address prefix length of the AP."
    ::= { qtechApCfgEntry 56 }

qtechApIpv6Type OBJECT-TYPE
    SYNTAX  INTEGER {
        unknown(0),
        unicase(1),
        anycase(2),
        multicase(3)
    }
    MAX-ACCESS  read-only
    STATUS      current
    DESCRIPTION
            "This object represents ipv6 address type of the AP."
    ::= { qtechApCfgEntry 57 }

qtechApIpv6Gateway OBJECT-TYPE
    SYNTAX      DisplayString
    MAX-ACCESS  read-only
    STATUS      current
    DESCRIPTION
            "This object represents ipv6 gateway address of the AP."
    ::= { qtechApCfgEntry 58 }

qtechApIpv6StaNum OBJECT-TYPE
    SYNTAX      INTEGER
    MAX-ACCESS  read-only
    STATUS      current
    DESCRIPTION
            "This object represents ipv6 Sta Num attach to the AP."
    ::= { qtechApCfgEntry 59 }
-- ***********************************
-- ap configuration per radio
-- ***********************************
qtechApCfgRadioTable OBJECT-TYPE
    SYNTAX  SEQUENCE OF QtechApCfgRadioEntry
    MAX-ACCESS  not-accessible
    STATUS  current
    DESCRIPTION
            "Set the ap attribute per radio."
    ::= { qtechAcMgmtAp 2 }

qtechApCfgRadioEntry OBJECT-TYPE
    SYNTAX  QtechApCfgRadioEntry
    MAX-ACCESS  not-accessible
    STATUS  current
    DESCRIPTION
        "The entry of image id table."
    INDEX   { qtechApMacAddr, qtechApCfgRadioId }
    ::= { qtechApCfgRadioTable 1 }

QtechApCfgRadioEntry ::=
    SEQUENCE {
        qtechApCfgRadioId      INTEGER,
        qtechApRadioEn         INTEGER,
        qtechApTxPower         INTEGER,
        qtechApDtimPeriod      INTEGER,
        qtechApBeaconPeriod    INTEGER,
        qtechApCountry         DisplayString,
        qtechApPreaShort       INTEGER,
        qtechApRadioBssid      MacAddress,
        qtechApTxPowerLevel    INTEGER,
        qtechApTxPowerGlobal   INTEGER,
        qtechApCurChan         INTEGER,
        qtechApRfGlobal        INTEGER,
        qtechApRadioType       INTEGER,
        qtechApRadio11bSup     INTEGER,
        qtechApMaxTxPower      INTEGER,
        qtechApMinTxPower      INTEGER,
        qtechApCurTxPower      INTEGER,
        qtechApMaxTxPowerPer   INTEGER,
        qtechApMinTxPowerPer   INTEGER
    }

-- The radio id
qtechApCfgRadioId  OBJECT-TYPE
    SYNTAX  INTEGER (1..31)
    MAX-ACCESS  read-only
    STATUS  current
    DESCRIPTION
            "The radio id, 1~31."
    ::= { qtechApCfgRadioEntry 1 }

-- 0-disable, 1-enable
qtechApRadioEn  OBJECT-TYPE
    SYNTAX  INTEGER (0..1)
    MAX-ACCESS  read-write
    STATUS  current
    DESCRIPTION
            "0--disable, 1--enable."
    ::= { qtechApCfgRadioEntry 2 }

-- The AP Tx Power
qtechApTxPower  OBJECT-TYPE
    SYNTAX  INTEGER (1..100)
    MAX-ACCESS  read-write
    STATUS  current
    DESCRIPTION
            "Tx power, 1%."
    ::= { qtechApCfgRadioEntry 3}

-- The AP beacon dtim period
qtechApDtimPeriod  OBJECT-TYPE
    SYNTAX  INTEGER (1..255)
    MAX-ACCESS  read-write
    STATUS  current
    DESCRIPTION
            "beacon dtim period, second."
    ::= { qtechApCfgRadioEntry 4}

-- The beacon period
qtechApBeaconPeriod  OBJECT-TYPE
    SYNTAX  INTEGER (20..1000)
    MAX-ACCESS  read-write
    STATUS  current
    DESCRIPTION
            "beacon period, millisecond."
    ::= { qtechApCfgRadioEntry 5}

-- The ap country code
qtechApCountry  OBJECT-TYPE
    SYNTAX  DisplayString (SIZE(0..255))
    MAX-ACCESS  read-write
    STATUS  current
    DESCRIPTION
            "Ap country code."
    ::= { qtechApCfgRadioEntry 6}

-- 0-not support short preamble,1-support short preamble
qtechApPreaShort  OBJECT-TYPE
    SYNTAX  INTEGER (0..1)
    MAX-ACCESS  read-write
    STATUS  current
    DESCRIPTION
            "Short preamble support."
    ::= { qtechApCfgRadioEntry 7}

qtechApRadioBssid  OBJECT-TYPE
    SYNTAX  MacAddress
    MAX-ACCESS  read-only
    STATUS  current
    DESCRIPTION
            "The AP's radio mac address(BSSID)."
    ::= { qtechApCfgRadioEntry 8}

qtechApTxPowerLevel  OBJECT-TYPE
    SYNTAX  INTEGER (1..600)
    MAX-ACCESS  read-only
    STATUS  current
    DESCRIPTION
            "The ap's tx power level in the radio."
    ::= { qtechApCfgRadioEntry 9}

qtechApTxPowerGlobal  OBJECT-TYPE
    SYNTAX  INTEGER (0..1)
    MAX-ACCESS  read-write
    STATUS  current
    DESCRIPTION
            "The ap's tx power config as the Global or not.
             0--customer, 1-global."
    ::= { qtechApCfgRadioEntry 10}

qtechApCurChan  OBJECT-TYPE
    SYNTAX  INTEGER (1..165)
    MAX-ACCESS  read-write
    STATUS  current
    DESCRIPTION
            "The ap's current channel in the radio."
    ::= { qtechApCfgRadioEntry 11}

qtechApRfGlobal  OBJECT-TYPE
    SYNTAX  INTEGER (0..1)
    MAX-ACCESS  read-write
    STATUS  current
    DESCRIPTION
            "The ap's channel config as the Global or not.
             0--customer, 1-global."
    ::= { qtechApCfgRadioEntry 12}

qtechApRadioType  OBJECT-TYPE
    SYNTAX  INTEGER (1..2)
    MAX-ACCESS  read-write
    STATUS  current
    DESCRIPTION
            "1--802.11b
             2--802.11a"
    ::= { qtechApCfgRadioEntry 13}

qtechApRadio11bSup  OBJECT-TYPE
    SYNTAX  INTEGER (1..2)
    MAX-ACCESS  read-only
    STATUS  current
    DESCRIPTION
            "1--support 802.11b
             2--not support 802.11b"
    ::= { qtechApCfgRadioEntry 14}

-- The AP Max Tx Power
qtechApMaxTxPower  OBJECT-TYPE
    SYNTAX  INTEGER
    MAX-ACCESS  read-only
    STATUS  current
    DESCRIPTION
            "Max tx power, mw."
    ::= { qtechApCfgRadioEntry 15}

-- The AP Min Tx Power
qtechApMinTxPower  OBJECT-TYPE
    SYNTAX  INTEGER
    MAX-ACCESS  read-only
    STATUS  current
    DESCRIPTION
            "Min tx power, mw."
    ::= { qtechApCfgRadioEntry 16}

-- The AP Current Tx Power
qtechApCurTxPower  OBJECT-TYPE
    SYNTAX  INTEGER
    MAX-ACCESS  read-write
    STATUS  current
    DESCRIPTION
            "Current tx power, mw."
    ::= { qtechApCfgRadioEntry 17}

-- The AP Max Tx Power Percent
qtechApMaxTxPowerPer  OBJECT-TYPE
    SYNTAX  INTEGER
    MAX-ACCESS  read-only
    STATUS  current
    DESCRIPTION
            "Max tx power percent, %."
    ::= { qtechApCfgRadioEntry 18}

-- The AP Min Tx Power Percent
qtechApMinTxPowerPer  OBJECT-TYPE
    SYNTAX  INTEGER
    MAX-ACCESS  read-only
    STATUS  current
    DESCRIPTION
            "Min tx power percent, %."
    ::= { qtechApCfgRadioEntry 19}

qtechApRadioRateCfgTable OBJECT-TYPE
    SYNTAX  SEQUENCE OF QtechApRadioRateCfgEntry
    MAX-ACCESS  not-accessible
    STATUS  current
    DESCRIPTION
            "The rate set of the ap's radio."
    ::= { qtechAcMgmtAp 3 }

qtechApRadioRateCfgEntry OBJECT-TYPE
    SYNTAX  QtechApRadioRateCfgEntry
    MAX-ACCESS  not-accessible
    STATUS  current
    DESCRIPTION
        "The attribute of the ap radio rate type."
    INDEX   { qtechApMacAddr, qtechApCfgRadioId, qtechApRadioRate }
    ::= { qtechApRadioRateCfgTable 1 }

QtechApRadioRateCfgEntry ::=
        SEQUENCE {
            qtechApRadioRate             INTEGER,
            qtechApRadioRateType         INTEGER
        }

qtechApRadioRate  OBJECT-TYPE
    SYNTAX  INTEGER (1..8)
    MAX-ACCESS  not-accessible
    STATUS  current
    DESCRIPTION
            "The ap's rate set in the radio.
            802.11a-6, 9, 12, 18, 24, 36, 48, and 54 Mbps.
            set 1 for 6Mbps, set 2 for 9Mbps, set 3 for 12Mbps,etc...
            802.11b-1, 2, 5.5, 11Mbps.
            set 1 for 1Mbps, set 2 for 2Mbps, set 3 for 5.5Mbps,etc..."
    ::= { qtechApRadioRateCfgEntry 1}

qtechApRadioRateType  OBJECT-TYPE
    SYNTAX  INTEGER (1..3)
    MAX-ACCESS  read-write
    STATUS  current
    DESCRIPTION
            "The rate type:
            1--disable
            2--mandatory
            3--support"
    ::= { qtechApRadioRateCfgEntry 2}


-- static ip config
qtechApStaticIpCfgTable OBJECT-TYPE
    SYNTAX  SEQUENCE OF QtechApStaticIpCfgEntry
    MAX-ACCESS  not-accessible
    STATUS  current
    DESCRIPTION
            "The rate set of the ap's radio."
    ::= { qtechAcMgmtAp 4 }

qtechApStaticIpCfgEntry OBJECT-TYPE
    SYNTAX  QtechApStaticIpCfgEntry
    MAX-ACCESS  not-accessible
    STATUS  current
    DESCRIPTION
        "Config the static ip address of the ap."
    INDEX   { qtechApMacAddr }
    ::= { qtechApStaticIpCfgTable 1 }

QtechApStaticIpCfgEntry ::=
        SEQUENCE {
            qtechApIpAddr             IpAddress,
            qtechApIpMask             IpAddress,
            qtechApIpGetway           IpAddress,
            qtechApStaticIpRS         RowStatus
        }

qtechApIpAddr  OBJECT-TYPE
    SYNTAX  IpAddress
    MAX-ACCESS  read-write
    STATUS  current
    DESCRIPTION
            "The AP's Static Ip Address"
    ::= { qtechApStaticIpCfgEntry 1}

qtechApIpMask  OBJECT-TYPE
    SYNTAX  IpAddress
    MAX-ACCESS  read-write
    STATUS  current
    DESCRIPTION
            "The AP's Static Ip Address Mask"
    ::= { qtechApStaticIpCfgEntry 2}

qtechApIpGetway  OBJECT-TYPE
    SYNTAX  IpAddress
    MAX-ACCESS  read-write
    STATUS  current
    DESCRIPTION
            "The AP's Static Ip Address Getway"
    ::= { qtechApStaticIpCfgEntry 3}

qtechApStaticIpRS  OBJECT-TYPE
    SYNTAX  RowStatus
    MAX-ACCESS  read-write
    STATUS  current
    DESCRIPTION
            "The AP's Static Ip Address Row status"
    ::= { qtechApStaticIpCfgEntry 4}


qtechApOfflineTable OBJECT-TYPE
    SYNTAX  SEQUENCE OF QtechApOfflineEntry
    MAX-ACCESS  not-accessible
    STATUS  current
    DESCRIPTION
            "The Ap offline time attributes."
    ::= { qtechAcMgmtAp 5 }

qtechApOfflineEntry OBJECT-TYPE
    SYNTAX  QtechApOfflineEntry
    MAX-ACCESS  not-accessible
    STATUS  current
    DESCRIPTION
        "Get and set the Ap attribtues."
    INDEX   { qtechApOffMacAddr }
    ::= { qtechApOfflineTable 1 }

QtechApOfflineEntry ::=
    SEQUENCE {
        qtechApOfftime                    INTEGER,
        qtechApOffApName                  DisplayString,
        qtechApOffMacAddr                 MacAddress
    }

qtechApOfftime  OBJECT-TYPE
    SYNTAX  INTEGER
    MAX-ACCESS  read-only
    STATUS  current
    DESCRIPTION
            "The AP's ethernet mac address."
    ::= { qtechApOfflineEntry 1}

-- The AP Name
qtechApOffApName  OBJECT-TYPE
    SYNTAX  DisplayString (SIZE (1..32))
    MAX-ACCESS  read-only
    STATUS  current
    DESCRIPTION
            "Offline Ap's Name."
    ::= { qtechApOfflineEntry 2}

qtechApOffMacAddr  OBJECT-TYPE
    SYNTAX  MacAddress
    MAX-ACCESS  read-only
    STATUS  current
    DESCRIPTION
            "The offline AP's ethernet mac address."
    ::= { qtechApOfflineEntry 3}

--********************************************************************
--    qtechApBackupState                                           **
--********************************************************************
qtechApBackupStateTable OBJECT-TYPE
    SYNTAX  SEQUENCE OF QtechApBackupStateEntry
    MAX-ACCESS  not-accessible
    STATUS  current
    DESCRIPTION
            "The Ap backup state."
    ::= { qtechAcMgmtAp 6 }

qtechApBackupStateEntry OBJECT-TYPE
    SYNTAX  QtechApBackupStateEntry
    MAX-ACCESS  not-accessible
    STATUS  current
    DESCRIPTION
        "Get the Ap backup state."
    INDEX   { qtechApMacAddr }
    ::= { qtechApBackupStateTable 1 }

QtechApBackupStateEntry ::=
    SEQUENCE {
        qtechApBackupState             INTEGER
    }

qtechApBackupState  OBJECT-TYPE
    SYNTAX  INTEGER {
                    unknown(0),
                    master(1),
                    slave(2)
                }
    MAX-ACCESS  read-only
    STATUS  current
    DESCRIPTION
            "The AP's backup state."
    ::= { qtechApBackupStateEntry 1 }

--********************************************************************
--                                                                  **
--                  AP Group nodes                                  **
--                                                                  **
--********************************************************************
qtechApgCfgTable OBJECT-TYPE
    SYNTAX  SEQUENCE OF QtechApgCfgEntry
    MAX-ACCESS  not-accessible
    STATUS  current
    DESCRIPTION
            "The attribute of the ap group."
    ::= { qtechAcMgmtApg 1 }

qtechApgCfgEntry OBJECT-TYPE
    SYNTAX  QtechApgCfgEntry
    MAX-ACCESS  not-accessible
    STATUS  current
    DESCRIPTION
        "The attribute of the ap group."
    INDEX   { qtechApgApgName }
    ::= { qtechApgCfgTable 1 }

QtechApgCfgEntry ::=
        SEQUENCE {
            qtechApgApgName             DisplayString,
            qtechApgDiscTimer           INTEGER,
            qtechApgEchoReqTimer        INTEGER,
            qtechApgEroReportTimer      INTEGER,
            qtechApgStaTimeoutTimer     INTEGER,
            qtechApgStatisticsTimer     INTEGER,
            qtechApgFallback            INTEGER,
            qtechApgImageId             DisplayString,
            qtechApgCreatEn             INTEGER
        }

-- The AP Group Name
qtechApgApgName  OBJECT-TYPE
    SYNTAX  DisplayString (SIZE (1..64))
    MAX-ACCESS  read-only
    STATUS  current
    DESCRIPTION
            "Ap group's Name."
    ::= { qtechApgCfgEntry 1}

-- The Discovery timer
qtechApgDiscTimer  OBJECT-TYPE
    SYNTAX  INTEGER (2..180)
    MAX-ACCESS  read-write
    STATUS  current
    DESCRIPTION
            "Discovery timer."
    ::= { qtechApgCfgEntry 2 }

-- The Echo Request timer
qtechApgEchoReqTimer  OBJECT-TYPE
    SYNTAX  INTEGER (5..255)
    MAX-ACCESS  read-write
    STATUS  current
    DESCRIPTION
            "Echo Request timer."
    ::= { qtechApgCfgEntry 3 }


-- The Error Report timer
qtechApgEroReportTimer  OBJECT-TYPE
    SYNTAX  INTEGER (1..1080)
    MAX-ACCESS  read-write
    STATUS  current
    DESCRIPTION
            "Error Report timer."
    ::= { qtechApgCfgEntry 4 }

-- The Sta timeout timer
qtechApgStaTimeoutTimer  OBJECT-TYPE
    SYNTAX  INTEGER (60..86400)
    MAX-ACCESS  read-write
    STATUS  current
    DESCRIPTION
            "station idle timeout timer."
    ::= { qtechApgCfgEntry 5 }

-- The Statistics timeout timer
qtechApgStatisticsTimer  OBJECT-TYPE
    SYNTAX  INTEGER (1..65535)
    MAX-ACCESS  read-write
    STATUS  current
    DESCRIPTION
            "station idle timeout timer."
    ::= { qtechApgCfgEntry 6 }

-- The fallback value, 1-enable, 2-disable
qtechApgFallback  OBJECT-TYPE
    SYNTAX  INTEGER (1..2)
    MAX-ACCESS  read-write
    STATUS  current
    DESCRIPTION
            "The fallback value, 1--enable, 2--disable."
    ::= { qtechApgCfgEntry 7 }

-- The Image id, should be 8 bytes
qtechApgImageId  OBJECT-TYPE
    SYNTAX  DisplayString (SIZE (1..128))
    MAX-ACCESS  read-write
    STATUS  current
    DESCRIPTION
            "The Ap image version string."
    ::= { qtechApgCfgEntry 8 }


-- 0-del, 1-creat
qtechApgCreatEn  OBJECT-TYPE
    SYNTAX  INTEGER (0..1)
    MAX-ACCESS  read-write
    STATUS  current
    DESCRIPTION
            "0-del, 1-creat."
    ::= { qtechApgCfgEntry 9 }

-- ***************************************
-- ap group attribute per radio
-- ***************************************
qtechApgCfgRadioTable OBJECT-TYPE
    SYNTAX  SEQUENCE OF QtechApgCfgRadioEntry
    MAX-ACCESS  not-accessible
    STATUS  current
    DESCRIPTION
            "The ap group attribute per radio."
    ::= { qtechAcMgmtApg 2 }

qtechApgCfgRadioEntry OBJECT-TYPE
    SYNTAX  QtechApgCfgRadioEntry
    MAX-ACCESS  not-accessible
    STATUS  current
    DESCRIPTION
        "The ap group attribute per radio."
    INDEX   { qtechApgApgName, qtechApgEnableRadioId}
    ::= { qtechApgCfgRadioTable 1 }

QtechApgCfgRadioEntry ::=
    SEQUENCE {
        qtechApgEnableRadioId    INTEGER,
        qtechApgEnableRadioEn    INTEGER
    }

-- The radio id
qtechApgEnableRadioId  OBJECT-TYPE
    SYNTAX  INTEGER (1..31)
    MAX-ACCESS  not-accessible
    STATUS  current
    DESCRIPTION
            "The radio id, 1~31."
    ::= { qtechApgCfgRadioEntry 1 }

-- 0-disable, 1-enable
qtechApgEnableRadioEn  OBJECT-TYPE
    SYNTAX  INTEGER (0..1)
    MAX-ACCESS  read-write
    STATUS  current
    DESCRIPTION
            "0--disable, 1--enable."
    ::= { qtechApgCfgRadioEntry 2 }

-- ************************************
-- wlan-cvi mapping configure
-- ************************************
qtechApgIntfMapTable OBJECT-TYPE
    SYNTAX  SEQUENCE OF QtechApgIntfMapEntry
    MAX-ACCESS  not-accessible
    STATUS  current
    DESCRIPTION
            "Set the wlan-interface map table type."
    ::= { qtechAcMgmtApg 3 }

qtechApgIntfMapEntry OBJECT-TYPE
    SYNTAX  QtechApgIntfMapEntry
    MAX-ACCESS  not-accessible
    STATUS  current
    DESCRIPTION
            "The entry of the wlan-interface map table."
    INDEX   { qtechApgApgName, qtechApgWlanIndex }
    ::= { qtechApgIntfMapTable 1 }

QtechApgIntfMapEntry ::=
    SEQUENCE {
        qtechApgWlanIndex        INTEGER,
        qtechApgWlanId           INTEGER,
        qtechApgVlanId           INTEGER,
        qtechApgRadioId          INTEGER,
        qtechApgWlanIntfMapRS    RowStatus
    }

-- The wlan-intf map index
qtechApgWlanIndex  OBJECT-TYPE
    SYNTAX  INTEGER (1..64)
    MAX-ACCESS  read-only
    STATUS  current
    DESCRIPTION
            "Wlan Id."
    ::= { qtechApgIntfMapEntry 1 }

-- The Wlan Id
qtechApgWlanId  OBJECT-TYPE
    SYNTAX  INTEGER (1..4094)
    MAX-ACCESS  read-write
    STATUS  current
    DESCRIPTION
            "Wlan Id."
    ::= { qtechApgIntfMapEntry 2 }

-- The Intf Id
qtechApgVlanId OBJECT-TYPE
    SYNTAX  INTEGER (1..4094)
    MAX-ACCESS  read-write
    STATUS  current
    DESCRIPTION
            "Vlan Id."
    ::= { qtechApgIntfMapEntry 3 }

-- The Radio Id
qtechApgRadioId  OBJECT-TYPE
    SYNTAX  INTEGER (1..16)
    MAX-ACCESS  read-write
    STATUS  current
    DESCRIPTION
            "Radio Id."
    ::= { qtechApgIntfMapEntry 4 }

qtechApgWlanIntfMapRS OBJECT-TYPE
    SYNTAX     RowStatus
    MAX-ACCESS read-write
    STATUS     current
    DESCRIPTION
         "Used to add or del a wlan-intf map in the ap group."
    ::= { qtechApgIntfMapEntry 5 }


--********************************************************************
--                                                                  **
--                  WLAN nodes                                      **
--                                                                  **
--********************************************************************
qtechWlanCfgTable OBJECT-TYPE
    SYNTAX  SEQUENCE OF QtechWlanCfgEntry
    MAX-ACCESS  not-accessible
    STATUS  current
    DESCRIPTION
            "The wlan attribute."
    ::= { qtechAcMgmtWlan 1 }

qtechWlanCfgEntry OBJECT-TYPE
    SYNTAX  QtechWlanCfgEntry
    MAX-ACCESS  not-accessible
    STATUS  current
    DESCRIPTION
        "The wlan attribute."
    INDEX   { qtechWlanId}
    ::= { qtechWlanCfgTable 1 }

QtechWlanCfgEntry ::=
    SEQUENCE {
        qtechWlanId                INTEGER,
        qtechWlanShort             INTEGER,
        qtechWlanSpctMgmt          INTEGER,
        qtechWlanEnQos             INTEGER,
        qtechWlanShortSlotTime     INTEGER,
        qtechWlanEnableApsd        INTEGER,
        qtechWlanAckType           INTEGER,
        qtechWlanTunnelType        INTEGER,
        qtechWlanBroadSsid         INTEGER,
        qtechWlanRts               INTEGER,
        qtechWlanShortTry          INTEGER,
        qtechWlanLongTry           INTEGER,
        qtechWlanStaNum            INTEGER,
        qtechWlanNasId             DisplayString
    }

-- The Wlan id
qtechWlanId  OBJECT-TYPE
    SYNTAX  INTEGER (1..512)
    MAX-ACCESS  read-only
    STATUS  current
    DESCRIPTION
            "Wlan Id."
    ::= { qtechWlanCfgEntry 1}

-- The short preamble value, 0-disable, 1-enable
qtechWlanShort  OBJECT-TYPE
    SYNTAX  INTEGER (0..2)
    MAX-ACCESS  read-write
    STATUS  current
    DESCRIPTION
            "Short Preamble."
    ::= { qtechWlanCfgEntry 2 }


-- The Spectrum_Management value, 0-disable, 1-enable
qtechWlanSpctMgmt  OBJECT-TYPE
    SYNTAX  INTEGER (0..1)
    MAX-ACCESS  read-write
    STATUS  current
    DESCRIPTION
            "Spectrum_Management."
    ::= { qtechWlanCfgEntry 3 }


-- The Spectrum_Management value, 0-disable, 1-enable
qtechWlanEnQos  OBJECT-TYPE
    SYNTAX  INTEGER (0..1)
    MAX-ACCESS  read-write
    STATUS  current
    DESCRIPTION
            "enbale qos value."
    ::= { qtechWlanCfgEntry 4 }

-- The Spectrum_Management value, 0-disable, 1-enable
qtechWlanShortSlotTime  OBJECT-TYPE
    SYNTAX  INTEGER (0..1)
    MAX-ACCESS  read-write
    STATUS  current
    DESCRIPTION
            "short slot time value."
    ::= { qtechWlanCfgEntry 5 }

-- The IEEE 802.11 Add WLAN.APSD value, 0-disable, 1-enable
qtechWlanEnableApsd  OBJECT-TYPE
    SYNTAX  INTEGER (0..1)
    MAX-ACCESS  read-write
    STATUS  current
    DESCRIPTION
            "IEEE 802.11 Add WLAN.APSD value."
    ::= { qtechWlanCfgEntry 6 }

-- 0-delayed, 1-immediate
qtechWlanAckType  OBJECT-TYPE
    SYNTAX  INTEGER (0..1)
    MAX-ACCESS  read-write
    STATUS  current
    DESCRIPTION
            "Ack delayed or immediate value."
    ::= { qtechWlanCfgEntry 7 }

-- 0-local, 1-80211, 2-8023
qtechWlanTunnelType  OBJECT-TYPE
    SYNTAX  INTEGER (0..2)
    MAX-ACCESS  read-write
    STATUS  current
    DESCRIPTION
            "Tunnel type value."
    ::= { qtechWlanCfgEntry 8 }

-- 0-disable, 1-enable
qtechWlanBroadSsid  OBJECT-TYPE
    SYNTAX  INTEGER (0..1)
    MAX-ACCESS  read-write
    STATUS  current
    DESCRIPTION
            "Broad Ssid value, 0--disable, 1--enable."
    ::= { qtechWlanCfgEntry 9 }

-- rts threshold
qtechWlanRts  OBJECT-TYPE
    SYNTAX  INTEGER (0..255)
    MAX-ACCESS  read-write
    STATUS  current
    DESCRIPTION
            "rts threshold."
    ::= { qtechWlanCfgEntry 10 }

-- Short retries
qtechWlanShortTry  OBJECT-TYPE
    SYNTAX  INTEGER (0..255)
    MAX-ACCESS  read-write
    STATUS  current
    DESCRIPTION
            "Short retries."
    ::= { qtechWlanCfgEntry 11 }

-- Long retries
qtechWlanLongTry  OBJECT-TYPE
    SYNTAX  INTEGER (0..255)
    MAX-ACCESS  read-write
    STATUS  current
    DESCRIPTION
            "Long retries."
    ::= { qtechWlanCfgEntry 12 }

-- WLAN sta number
qtechWlanStaNum  OBJECT-TYPE
    SYNTAX  INTEGER
    MAX-ACCESS  read-only
    STATUS  current
    DESCRIPTION
            "The wireless stationes attach to this wlan."
    ::= { qtechWlanCfgEntry 13 }

-- WLAN nas id
qtechWlanNasId  OBJECT-TYPE
    SYNTAX  DisplayString
    MAX-ACCESS  read-write
    STATUS  current
    DESCRIPTION
            "The NAS ID about this wlan."
    ::= { qtechWlanCfgEntry 14 }

-- *******************************
-- wlan creat table
-- *******************************
qtechWlanWlanCreatTable OBJECT-TYPE
    SYNTAX  SEQUENCE OF QtechWlanWlanCreatEntry
    MAX-ACCESS  not-accessible
    STATUS  current
    DESCRIPTION
            "Wlan creat table."
    ::= { qtechAcMgmtWlan 2 }

qtechWlanWlanCreatEntry OBJECT-TYPE
    SYNTAX  QtechWlanWlanCreatEntry
    MAX-ACCESS  not-accessible
    STATUS  current
    DESCRIPTION
        "The entry of Braod Ssid value table."
    INDEX   { qtechWlanId}
    ::= { qtechWlanWlanCreatTable 1 }

QtechWlanWlanCreatEntry ::=
    SEQUENCE {
        qtechWlanWlanSsid          DisplayString,
        qtechWlanWlanProfile       DisplayString,
        qtechWlanCreateMapRS       RowStatus
    }

-- ssid string
qtechWlanWlanSsid  OBJECT-TYPE
    SYNTAX  DisplayString (SIZE(1..255))
    MAX-ACCESS  read-write
    STATUS  current
    DESCRIPTION
            "Wlan Ssid."
    ::= { qtechWlanWlanCreatEntry 1 }

-- profile string
qtechWlanWlanProfile  OBJECT-TYPE
    SYNTAX  DisplayString (SIZE(1..255))
    MAX-ACCESS  read-write
    STATUS  current
    DESCRIPTION
            "Wlan profile."
    ::= { qtechWlanWlanCreatEntry 2 }

qtechWlanCreateMapRS OBJECT-TYPE
    SYNTAX     RowStatus
    MAX-ACCESS read-write
    STATUS     current
    DESCRIPTION
             "Used to add a wlan."
    ::= { qtechWlanWlanCreatEntry 3 }

-- *************************************
-- channel channel_num regulatory band {unii0-unii6} {enable|disable}
-- *************************************
qtechWlanChanBandTable OBJECT-TYPE
    SYNTAX  SEQUENCE OF QtechWlanChanBandEntry
    MAX-ACCESS  not-accessible
    STATUS  current
    DESCRIPTION
            "Channel band table type."
    ::= { qtechAcMgmtWlan 3 }

qtechWlanChanBandEntry OBJECT-TYPE
    SYNTAX  QtechWlanChanBandEntry
    MAX-ACCESS  not-accessible
    STATUS  current
    DESCRIPTION
        "The entry of channel band table."
    INDEX   { qtechWlanId, qtechWlanBandV}
    ::= { qtechWlanChanBandTable 1 }

QtechWlanChanBandEntry ::=
    SEQUENCE {
        qtechWlanChanV              INTEGER,
        qtechWlanBandV              INTEGER,
        qtechWlanChanBandEn         INTEGER,
        qtechWlanChanBandRS         RowStatus
    }

-- band
qtechWlanBandV  OBJECT-TYPE
    SYNTAX  INTEGER (1..7)
    MAX-ACCESS  not-accessible
    STATUS  current
    DESCRIPTION
            "1 for unii0, 2 for unii1 .. 7 for unii6."
    ::= { qtechWlanChanBandEntry 1 }

-- channel
qtechWlanChanV  OBJECT-TYPE
    SYNTAX  INTEGER (0..255)
    MAX-ACCESS  read-write
    STATUS  current
    DESCRIPTION
            "fragment threshold."
    ::= { qtechWlanChanBandEntry 2 }

-- 0-disable,1-enable
qtechWlanChanBandEn  OBJECT-TYPE
    SYNTAX  INTEGER (0..1)
    MAX-ACCESS  read-write
    STATUS  current
    DESCRIPTION
            "0-disable,1-enable ."
    ::= { qtechWlanChanBandEntry 3 }

qtechWlanChanBandRS OBJECT-TYPE
    SYNTAX     RowStatus
    MAX-ACCESS read-write
    STATUS     current
    DESCRIPTION
             "Used to config a wlan channel band."
    ::= { qtechWlanChanBandEntry 4 }

-- 15.speed speed_type radio radio_id 55555

-- ***************************************
-- regulatory limit First_Channel Number_of_Channels Mx_Tx_Power_Level
-- ***************************************
qtechWlanLimitChanTable OBJECT-TYPE
    SYNTAX  SEQUENCE OF QtechWlanLimitChanEntry
    MAX-ACCESS  not-accessible
    STATUS  current
    DESCRIPTION
            "Channel band table type."
    ::= { qtechAcMgmtWlan 4 }

qtechWlanLimitChanEntry OBJECT-TYPE
    SYNTAX  QtechWlanLimitChanEntry
    MAX-ACCESS  not-accessible
    STATUS  current
    DESCRIPTION
            "The entry of channel band table."
    INDEX   { qtechWlanId}
    ::= { qtechWlanLimitChanTable 1 }

QtechWlanLimitChanEntry ::=
    SEQUENCE {
        qtechWlanLimitChanFirstV       INTEGER,
        qtechWlanLimitChanNumV         INTEGER,
        qtechWlanLimitChanMaxTxPowerLv INTEGER,
        qtechWlanLimitChanRS           RowStatus
     }

-- first channel
qtechWlanLimitChanFirstV  OBJECT-TYPE
    SYNTAX  INTEGER (0..255)
    MAX-ACCESS  read-write
    STATUS  current
    DESCRIPTION
            "first channel."
    ::= { qtechWlanLimitChanEntry 1 }

-- Channel num
qtechWlanLimitChanNumV  OBJECT-TYPE
    SYNTAX  INTEGER (0..6)
    MAX-ACCESS  read-write
    STATUS  current
    DESCRIPTION
            "Channel num."
    ::= { qtechWlanLimitChanEntry 2 }

-- Max Tx Power Level
qtechWlanLimitChanMaxTxPowerLv  OBJECT-TYPE
    SYNTAX  INTEGER (1..8)
    MAX-ACCESS  read-write
    STATUS  current
    DESCRIPTION
            "Max Tx Power Level ."
    ::= { qtechWlanLimitChanEntry 3 }

qtechWlanLimitChanRS OBJECT-TYPE
    SYNTAX     RowStatus
    MAX-ACCESS read-write
    STATUS     current
    DESCRIPTION
             "Used to config a wlan limit chan."
    ::= { qtechWlanLimitChanEntry 4 }


--********************************************************************
--                                                                  **
--                  STA nodes                                       **
--                                                                  **
--********************************************************************
qtechStaTable OBJECT-TYPE
    SYNTAX  SEQUENCE OF QtechStaEntry
    MAX-ACCESS  not-accessible
    STATUS  current
    DESCRIPTION
            "qtech AC MGMT station table."
    ::= { qtechAcMgmtSta 1 }

qtechStaEntry OBJECT-TYPE
    SYNTAX  QtechStaEntry
    MAX-ACCESS  not-accessible
    STATUS  current
    DESCRIPTION
        "qtech AC MGMT station entry."
    INDEX   { qtechStaMacAddr}
    ::= { qtechStaTable 1 }

QtechStaEntry ::=
    SEQUENCE {
        qtechStaMacAddr                MacAddress,
        qtechStaApMacAddr              MacAddress,
        qtechStaVlan                   INTEGER,
        qtechStaWlanId                 INTEGER,
        qtechStaIp                     IpAddress,
        qtechStaApIp                   IpAddress,
        qtechStaApRadioId              INTEGER,
        qtechStaApRadioType            INTEGER,
        qtechStaAssoType               INTEGER,
        qtechStaAuthType               INTEGER,
        qtechStaRoamTimesPerMin        INTEGER,
        qtechStaOnTimesPerHour         INTEGER,
        qtechStaOffTimesPerHour        INTEGER,
        qtechStaIpv6                   InetAddress,
        qtechStaAssoAuthMode           INTEGER,
        qtechStaNetAuthMode            INTEGER,
        qtechStaSsid                   DisplayString,
        qtechStaLinkRate               INTEGER,
        qtechStaCurChan                INTEGER,
        qtechStaClientType             DisplayString,
        qtechStaRssi                   INTEGER,
        qtechStaUserName               DisplayString,
        qtechStaTerminalType           DisplayString,
        qtechStaOnlineTime             DisplayString,
        qtechStaUpTimeInterval         INTEGER
     }

qtechStaMacAddr  OBJECT-TYPE
    SYNTAX  MacAddress
    MAX-ACCESS  read-only
    STATUS  current
    DESCRIPTION
            "The STA's mac address."
    ::= { qtechStaEntry 1}

qtechStaApMacAddr  OBJECT-TYPE
    SYNTAX  MacAddress
    MAX-ACCESS  read-only
    STATUS  current
    DESCRIPTION
            "The  mac address with the AP which the STA attached."
    ::= { qtechStaEntry 2}

qtechStaVlan  OBJECT-TYPE
    SYNTAX  INTEGER
    MAX-ACCESS  read-only
    STATUS  current
    DESCRIPTION
            "Vlan id the STA belong to."
    ::= { qtechStaEntry 3 }

qtechStaWlanId  OBJECT-TYPE
    SYNTAX  INTEGER
    MAX-ACCESS  read-only
    STATUS  current
    DESCRIPTION
            "Wlan id the STA belong to."
    ::= { qtechStaEntry 4 }

qtechStaIp OBJECT-TYPE
    SYNTAX      IpAddress
    MAX-ACCESS  read-only
    STATUS      current
    DESCRIPTION
            "This object represents ip address of the client."
    ::= { qtechStaEntry 5 }

qtechStaApIp OBJECT-TYPE
    SYNTAX      IpAddress
    MAX-ACCESS  read-only
    STATUS      current
    DESCRIPTION
            "This object represents ip address of AP which the client attaches to."
    ::= { qtechStaEntry 6 }

qtechStaApRadioId OBJECT-TYPE
    SYNTAX      INTEGER
    MAX-ACCESS  read-only
    STATUS      current
    DESCRIPTION
            "This object represents radio id of AP which the client attaches to."
    ::= { qtechStaEntry 7 }

qtechStaApRadioType OBJECT-TYPE
    SYNTAX      INTEGER
    MAX-ACCESS  read-only
    STATUS      current
    DESCRIPTION
            "This object represents ip address of AP which the client attaches to."
    ::= { qtechStaEntry 8 }

qtechStaAssoType OBJECT-TYPE
    SYNTAX      INTEGER
    MAX-ACCESS  read-only
    STATUS      current
    DESCRIPTION
            "This object represents sta's associate type."
    ::= { qtechStaEntry 9 }

qtechStaAuthType OBJECT-TYPE
    SYNTAX      INTEGER
    MAX-ACCESS  read-only
    STATUS      current
    DESCRIPTION
            "This object represents sta's authentication type."
    ::= { qtechStaEntry 10 }

qtechStaRoamTimesPerMin  OBJECT-TYPE
    SYNTAX  INTEGER
    MAX-ACCESS  read-only
    STATUS  current
    DESCRIPTION
            "The Sta roaming times in the last minite."
    ::= { qtechStaEntry 11}

qtechStaOnTimesPerHour  OBJECT-TYPE
    SYNTAX  INTEGER
    MAX-ACCESS  read-only
    STATUS  current
    DESCRIPTION
            "The Sta turn on times in the last hour."
    ::= { qtechStaEntry 12}

qtechStaOffTimesPerHour  OBJECT-TYPE
    SYNTAX  INTEGER
    MAX-ACCESS  read-only
    STATUS  current
    DESCRIPTION
            "The Sta turn off times in the last hour."
    ::= { qtechStaEntry 13}

qtechStaIpv6  OBJECT-TYPE
    SYNTAX  InetAddress
    MAX-ACCESS  read-only
    STATUS  current
    DESCRIPTION
            "The Sta ipv6 address."
    ::= { qtechStaEntry 14}

qtechStaAssoAuthMode  OBJECT-TYPE
    SYNTAX  INTEGER {
        open(0),
        wep(1),
        dot1x-wep(2),
        dot1x-wpa(3),
        dot1x-wpa2(4),
        mab(5),
        psk-wpa(6),
        psk-wpa2(7),
        wapi(8)
    }
    MAX-ACCESS  read-only
    STATUS  current
    DESCRIPTION
            "The Sta associate authentication mode."
    ::= { qtechStaEntry 15}

qtechStaNetAuthMode  OBJECT-TYPE
    SYNTAX  INTEGER {
        open(0),
        web(1)
    }
    MAX-ACCESS  read-only
    STATUS  current
    DESCRIPTION
            "The Sta's authentication mode after associated."
    ::= { qtechStaEntry 16}

qtechStaSsid  OBJECT-TYPE
    SYNTAX  DisplayString
    MAX-ACCESS  read-only
    STATUS  current
    DESCRIPTION
            "This object represents wlan ssid with the sta associated."
    ::= { qtechStaEntry 17}

qtechStaLinkRate  OBJECT-TYPE
    SYNTAX  INTEGER
    MAX-ACCESS  read-only
    STATUS  current
    DESCRIPTION
            "This object represents link rate with the sta associated, unit: kbps."
    ::= { qtechStaEntry 18}

qtechStaCurChan  OBJECT-TYPE
    SYNTAX  INTEGER
    MAX-ACCESS  read-only
    STATUS  current
    DESCRIPTION
            "The Sta's current channel."
    ::= { qtechStaEntry 19}

qtechStaClientType OBJECT-TYPE
    SYNTAX      DisplayString (SIZE (0..64))
    MAX-ACCESS  read-only
    STATUS      current
    DESCRIPTION
         "The sta's type."
    ::= { qtechStaEntry 20 }

qtechStaRssi OBJECT-TYPE
    SYNTAX  INTEGER
    MAX-ACCESS  read-only
    STATUS  current
    DESCRIPTION
            "The Sta's current RSSI."
    ::= { qtechStaEntry 21}

qtechStaUserName  OBJECT-TYPE
    SYNTAX  DisplayString
    MAX-ACCESS  read-only
    STATUS  current
    DESCRIPTION
            "This object represents user name with the sta associated."
    ::= { qtechStaEntry 22}

qtechStaTerminalType  OBJECT-TYPE
    SYNTAX  DisplayString
    MAX-ACCESS  read-only
    STATUS  current
    DESCRIPTION
            "This object represents terminal type with the sta associated."
    ::= { qtechStaEntry 23}

qtechStaOnlineTime  OBJECT-TYPE
    SYNTAX  DisplayString
    MAX-ACCESS  read-only
    STATUS  current
    DESCRIPTION
            "This object represents the time when sta is associated."
    ::= { qtechStaEntry 24}

qtechStaUpTimeInterval OBJECT-TYPE
    SYNTAX  INTEGER
    MAX-ACCESS  read-only
    STATUS  current
    DESCRIPTION
            "This object represents how long sta is online(in seconds)."
    ::= { qtechStaEntry 25}

-- ****************************************
--
--               Notify nodes
--
-- ****************************************
qtechNotifyApMac OBJECT-TYPE
    SYNTAX      MacAddress
    MAX-ACCESS  accessible-for-notify
    STATUS      current
    DESCRIPTION
        "Represents the unique identifier of a WTP."
    ::= { qtechAcMgmtNtfObjects 1 }

qtechNotifyStaMac OBJECT-TYPE
    SYNTAX      MacAddress
    MAX-ACCESS  accessible-for-notify
    STATUS      current
    DESCRIPTION
        "Represents the unique identifier of a STA."
    ::= { qtechAcMgmtNtfObjects 2 }

qtechNotifyApIp OBJECT-TYPE
    SYNTAX      IpAddress
    MAX-ACCESS  accessible-for-notify
    STATUS      current
    DESCRIPTION
        "Represents the Ip address of a WTP."
    ::= { qtechAcMgmtNtfObjects 3 }

qtechNotifyStaIp OBJECT-TYPE
    SYNTAX      IpAddress
    MAX-ACCESS  accessible-for-notify
    STATUS      current
    DESCRIPTION
        "Represents the Ip of a STA."
    ::= { qtechAcMgmtNtfObjects 4 }

qtechNotifyStaOperType OBJECT-TYPE
    SYNTAX      INTEGER
    MAX-ACCESS  accessible-for-notify
    STATUS      current
    DESCRIPTION
        "Represents the STA operation, 1-del,2-add,3-roaming,4-ipupdate,5-ipv6update"
    ::= { qtechAcMgmtNtfObjects 5 }

qtechNotifyStaApRadioId OBJECT-TYPE
    SYNTAX      INTEGER(1..2)
    MAX-ACCESS  accessible-for-notify
    STATUS      current
    DESCRIPTION
        "Represents the radio id which STA attach."
    ::= { qtechAcMgmtNtfObjects 6 }

qtechNotifyStaApRadioType OBJECT-TYPE
    SYNTAX      INTEGER (1..2)
    MAX-ACCESS  accessible-for-notify
    STATUS      current
    DESCRIPTION
              "1--802.11b
               2--802.11a"
    ::= { qtechAcMgmtNtfObjects 7 }

qtechNotifyStaVlanId OBJECT-TYPE
    SYNTAX      INTEGER (1..4094)
    MAX-ACCESS  accessible-for-notify
    STATUS      current
    DESCRIPTION
              "Vlan Id the sta belongs to"
    ::= { qtechAcMgmtNtfObjects 8 }

qtechNotifyStaWlanId OBJECT-TYPE
    SYNTAX      INTEGER (1..4095)
    MAX-ACCESS  accessible-for-notify
    STATUS      current
    DESCRIPTION
              "Wlan Id the sta belongs to"
    ::= { qtechAcMgmtNtfObjects 9 }

qtechNotifyAcMBChangeV OBJECT-TYPE
    SYNTAX      INTEGER (1..2)
    MAX-ACCESS  accessible-for-notify
    STATUS      current
    DESCRIPTION
              "1 - Master to backup,
               2 - Backup to master"
    ::= { qtechAcMgmtNtfObjects 10 }

qtechNotifyStaOperTimes OBJECT-TYPE
    SYNTAX      INTEGER (1..65535)
    MAX-ACCESS  accessible-for-notify
    STATUS      current
    DESCRIPTION
              "This object present the times when the
               STA is active, disactive, roaming."
    ::= { qtechAcMgmtNtfObjects 11 }

qtechNotifyAcPowerIndex OBJECT-TYPE
    SYNTAX      INTEGER
    MAX-ACCESS  accessible-for-notify
    STATUS      current
    DESCRIPTION
              "This object present the AC's power unit index."
    ::= { qtechAcMgmtNtfObjects 12 }

qtechNotifyAcPowerStatu OBJECT-TYPE
    SYNTAX      INTEGER
    MAX-ACCESS  accessible-for-notify
    STATUS      current
    DESCRIPTION
              "This object present the AC's power statu, 0-off, 1-on."
    ::= { qtechAcMgmtNtfObjects 13 }

qtechNotifyTime OBJECT-TYPE
    SYNTAX      DisplayString
    MAX-ACCESS  accessible-for-notify
    STATUS      current
    DESCRIPTION
              "This object present the sta operation current time."
    ::= { qtechAcMgmtNtfObjects 14 }

qtechNotifyOldVer OBJECT-TYPE
    SYNTAX      DisplayString
    MAX-ACCESS  accessible-for-notify
    STATUS      current
    DESCRIPTION
              "This object present the AP's old version."
    ::= { qtechAcMgmtNtfObjects 15 }

qtechNotifyNewVer OBJECT-TYPE
    SYNTAX      DisplayString
    MAX-ACCESS  accessible-for-notify
    STATUS      current
    DESCRIPTION
              "This object present the AP's new version."
    ::= { qtechAcMgmtNtfObjects 16 }

qtechNotifyVerUpdtReason OBJECT-TYPE
    SYNTAX      INTEGER (1..6)
    MAX-ACCESS  accessible-for-notify
    STATUS      current
    DESCRIPTION
              "This object present the AP's firmware updating fail reason.
                1 -- Image is not ready.
                2 -- AC send image fail.
                3 -- Link down when update ap image.
                4 -- Active image file error.
                5 -- AP response error.
                6 -- AP has image in flash."
    ::= { qtechAcMgmtNtfObjects 17 }

qtechNotifyStaIpv6 OBJECT-TYPE
    SYNTAX      InetAddress
    MAX-ACCESS  accessible-for-notify
    STATUS      current
    DESCRIPTION
              "Sta ipv6 address."
    ::= { qtechAcMgmtNtfObjects 18 }

qtechNotifyStaAssoAuthMode  OBJECT-TYPE
    SYNTAX  INTEGER {
        open(0),
        wep(1),
        dot1x-wep(2),
        dot1x-wpa(3),
        dot1x-wpa2(4),
        mab(5),
        psk-wpa(6),
        psk-wpa2(7),
        wapi(8)
    }
    MAX-ACCESS  accessible-for-notify
    STATUS  current
    DESCRIPTION
            "The Sta associate authentication mode."
    ::= { qtechAcMgmtNtfObjects 19}

qtechNotifyStaNetAuthMode  OBJECT-TYPE
    SYNTAX  INTEGER {
        open(0),
        web(1)
    }
    MAX-ACCESS  accessible-for-notify
    STATUS  current
    DESCRIPTION
            "The Sta's authentication mode after associated."
    ::= { qtechAcMgmtNtfObjects 20}

qtechNotifyStaSsid  OBJECT-TYPE
    SYNTAX  DisplayString
    MAX-ACCESS  accessible-for-notify
    STATUS  current
    DESCRIPTION
            "The wlan ssid with the sta associated."
    ::= { qtechAcMgmtNtfObjects 21}

qtechNotifyStaLinkRate  OBJECT-TYPE
    SYNTAX  INTEGER
    MAX-ACCESS  accessible-for-notify
    STATUS  current
    DESCRIPTION
            "The link rate with the sta associated, unit: 1kbps."
    ::= { qtechAcMgmtNtfObjects 22}

qtechNotifyStaCurChan  OBJECT-TYPE
    SYNTAX  INTEGER
    MAX-ACCESS  accessible-for-notify
    STATUS  current
    DESCRIPTION
            "The Sta current use channel after associated."
    ::= { qtechAcMgmtNtfObjects 23}

qtechNotifyStaClientType  OBJECT-TYPE
    SYNTAX  DisplayString
    MAX-ACCESS  accessible-for-notify
    STATUS  current
    DESCRIPTION
            "The Sta's type."
    ::= { qtechAcMgmtNtfObjects 24}

qtechNotifyStaRssi OBJECT-TYPE
    SYNTAX  INTEGER
    MAX-ACCESS  accessible-for-notify
    STATUS  current
    DESCRIPTION
            "The Sta's RSSI."
    ::= { qtechAcMgmtNtfObjects 25}

qtechNotifyStaReason OBJECT-TYPE
    SYNTAX  DisplayString
    MAX-ACCESS  accessible-for-notify
    STATUS  current
    DESCRIPTION
            "The Sta's down reason."
    ::= { qtechAcMgmtNtfObjects 26}

qtechNotifyStaTimestamp OBJECT-TYPE
    SYNTAX  INTEGER
    MAX-ACCESS  accessible-for-notify
    STATUS  current
    DESCRIPTION
            "Seconds since device bootup when this trap is sent."
    ::= { qtechAcMgmtNtfObjects 27}

qtechNotifyStaOnlineTimeval OBJECT-TYPE
    SYNTAX  INTEGER
    MAX-ACCESS  accessible-for-notify
    STATUS  current
    DESCRIPTION
            "Sta's total online time in seconds."
    ::= { qtechAcMgmtNtfObjects 28}

qtechNotifyStaIpv4Upflow OBJECT-TYPE
    SYNTAX  INTEGER
    MAX-ACCESS  accessible-for-notify
    STATUS  current
    DESCRIPTION
            "Sta's total IPv4 upflow in kbps."
    ::= { qtechAcMgmtNtfObjects 29}

qtechNotifyStaIpv4Downflow OBJECT-TYPE
    SYNTAX  INTEGER
    MAX-ACCESS  accessible-for-notify
    STATUS  current
    DESCRIPTION
            "Sta's total IPv4 downflow in kbps."
    ::= { qtechAcMgmtNtfObjects 30}

qtechNotifyApTimeStampFail NOTIFICATION-TYPE
    OBJECTS     {
                  qtechNotifyApMac
                }
    STATUS      current
    DESCRIPTION
        "This notification is sent by the AC when an AP sync the time failed."
    ::= { qtechAcMgmtNotifications 1 }

qtechNotifyStaOper NOTIFICATION-TYPE
    OBJECTS     {
                  qtechNotifyApMac,
                  qtechNotifyStaMac,
                  qtechNotifyApIp,
                  qtechNotifyStaIp,
                  qtechNotifyStaOperType,
                  qtechNotifyStaApRadioId,
                  qtechNotifyStaApRadioType,
                  qtechNotifyStaVlanId,
                  qtechNotifyStaWlanId,
                  qtechNotifyTime,
                  qtechNotifyStaIpv6,
                  qtechNotifyStaAssoAuthMode,
                  qtechNotifyStaNetAuthMode,
                  qtechNotifyStaSsid,
                  qtechNotifyStaLinkRate,
                  qtechNotifyStaCurChan,
                  qtechNotifyStaClientType,
                  qtechNotifyStaRssi,
                  qtechNotifyStaReason
                }
    STATUS      current
    DESCRIPTION
        "This notification is sent by the AC when a sta enter or quit or ip update."
    ::= { qtechAcMgmtNotifications 2 }

qtechNotifyAcMBChange NOTIFICATION-TYPE
    OBJECTS     {
                  qtechNotifyAcMBChangeV
                }
    STATUS      current
    DESCRIPTION
        "This notification is sent by the AC change from
         smaster to backup or backup to master."
    ::= { qtechAcMgmtNotifications 3 }

qtechNotifyApSwUpdtFail NOTIFICATION-TYPE
    OBJECTS     {
                  qtechNotifyApMac,
                  qtechNotifyOldVer,
                  qtechNotifyNewVer,
                  qtechNotifyVerUpdtReason
                }
    STATUS      current
    DESCRIPTION
        "This notification is sent by the AC when update the AP software failed."
    ::= { qtechAcMgmtNotifications 4 }

qtechNotifyStaActOverThredhold NOTIFICATION-TYPE
    OBJECTS     {
                  qtechNotifyApMac,
                  qtechNotifyStaMac,
                  qtechNotifyStaApRadioId,
                  qtechNotifyStaApRadioType,
                  qtechNotifyStaOperTimes
                }
    STATUS      current
    DESCRIPTION
        "This notification is sent by the AC when a sta active times over thredhold."
    ::= { qtechAcMgmtNotifications 5 }

qtechNotifyStaDisactOverThredhold NOTIFICATION-TYPE
    OBJECTS     {
                  qtechNotifyApMac,
                  qtechNotifyStaMac,
                  qtechNotifyStaApRadioId,
                  qtechNotifyStaApRadioType,
                  qtechNotifyStaOperTimes
                }
    STATUS      current
    DESCRIPTION
        "This notification is sent by the AC when a sta's disactive times over thredhold."
    ::= { qtechAcMgmtNotifications 6 }

qtechNotifyStaRoamTotal NOTIFICATION-TYPE
    OBJECTS     {
                  qtechNotifyApMac,
                  qtechNotifyStaMac,
                  qtechNotifyStaApRadioId,
                  qtechNotifyStaApRadioType,
                  qtechNotifyStaOperTimes
                }
    STATUS      current
    DESCRIPTION
        "This notification is sent by the AC when a sta's total
         roaming times over thredhold ."
    ::= { qtechAcMgmtNotifications 7 }

qtechNotifyStaRoamPerMin NOTIFICATION-TYPE
    OBJECTS     {
                  qtechNotifyApMac,
                  qtechNotifyStaMac,
                  qtechNotifyStaApRadioId,
                  qtechNotifyStaApRadioType,
                  qtechNotifyStaOperTimes
                }
    STATUS      current
    DESCRIPTION
        "This notification is sent by the AC when a sta's
         roaming times per minite over thredhold ."
    ::= { qtechAcMgmtNotifications 8 }

qtechNotifyAcPowerStatus NOTIFICATION-TYPE
    OBJECTS     {
                  qtechNotifyAcPowerIndex,
                  qtechNotifyAcPowerStatu
                }
    STATUS      current
    DESCRIPTION
        "This notification is sent by the AC when the
         AC's power unit status changed."
    ::= { qtechAcMgmtNotifications 9 }

qtechNotify86PowerOffAlarm NOTIFICATION-TYPE
    OBJECTS     {
                  qtechNotifyAcPowerIndex
                }
    STATUS      current
    DESCRIPTION
        "This notification is sent by the 86 power off."
    ::= { qtechAcMgmtNotifications 10 }

qtechNotify86PowerOffAlarmClear NOTIFICATION-TYPE
    OBJECTS     {
                  qtechNotifyAcPowerIndex
                }
    STATUS      current
    DESCRIPTION
        "This notification is sent by the 86 power on."
    ::= { qtechAcMgmtNotifications 11 }

qtechNotifyApSwUpdtSuccess NOTIFICATION-TYPE
    OBJECTS     {
                  qtechNotifyApMac,
                  qtechNotifyOldVer,
                  qtechNotifyNewVer
                }
    STATUS      current
    DESCRIPTION
        "This notification is sent by the AC when update the AP software success."
    ::= { qtechAcMgmtNotifications 12 }

qtechNotifyApUp NOTIFICATION-TYPE
    OBJECTS     {
                  qtechApMacAddr,
                  capwapBaseNtfChannelType,
                  capwapBaseNtfAuthenMethod
                }
    STATUS      current
    DESCRIPTION
        "This notification is sent by the AC when a CAPWAP channel
         established."
    ::= { qtechAcMgmtNotifications 13 }

qtechNotifyApDown NOTIFICATION-TYPE
    OBJECTS     {
                  qtechApMacAddr,
                  capwapBaseNtfChannelType,
                  capwapBaseNtfChannelDownReason
                }
    STATUS      current
    DESCRIPTION
        "This notification is sent by the AC when CAPWAP channel
         becomes down."
    ::= { qtechAcMgmtNotifications 14 }

qtechNotifyApSwUpdtFailApMac NOTIFICATION-TYPE
    OBJECTS     {
                  qtechApMacAddr,
                  qtechNotifyOldVer,
                  qtechNotifyNewVer,
                  qtechNotifyVerUpdtReason
                }
    STATUS      current
    DESCRIPTION
        "This notification is sent by the AC when update the AP software failed."
    ::= { qtechAcMgmtNotifications 15 }

qtechNotifyApTimeStampFailApMac NOTIFICATION-TYPE
    OBJECTS     {
                  qtechApMacAddr
                }
    STATUS      current
    DESCRIPTION
        "This notification is sent by the AC when an AP sync the time failed."
    ::= { qtechAcMgmtNotifications 16 }

qtechNotifyStaOperAlternate NOTIFICATION-TYPE
    OBJECTS     {
                  qtechNotifyStaOperType,
                  qtechNotifyStaMac,
                  qtechNotifyStaIp,
                  qtechNotifyApMac,
                  qtechNotifyApIp,
                  qtechNotifyStaApRadioId,
                  qtechNotifyStaApRadioType,
                  qtechNotifyStaWlanId,
                  qtechNotifyStaSsid,
                  qtechNotifyStaVlanId,
                  qtechNotifyStaLinkRate,
                  qtechNotifyStaCurChan,
                  qtechNotifyStaRssi,
                  qtechNotifyStaTimestamp,
                  qtechNotifyStaOnlineTimeval,
                  qtechNotifyStaIpv4Upflow,
                  qtechNotifyStaIpv4Downflow
                }
    STATUS      current
    DESCRIPTION
        "This notification is sent by the AC when a sta is up, down or roaming."
    ::= { qtechAcMgmtNotifications 17 }


--********************************************************************
--                                                                  **
--           conformance information                                **
--                                                                  **
--********************************************************************
qtechAcMgmtAcMIBConformance OBJECT IDENTIFIER ::= { qtechAcMgmtMIB 7 }
qtechAcMgmtAcMIBCompliances OBJECT IDENTIFIER ::= { qtechAcMgmtAcMIBConformance 1 }
qtechAcMgmtAcMIBGroups      OBJECT IDENTIFIER ::= { qtechAcMgmtAcMIBConformance 2 }


--********************************************************************
--                                                                  **
--           compliance statements                                  **
--                                                                  **
--********************************************************************
qtechAcMgmtAcMIBCompliance MODULE-COMPLIANCE
        STATUS  current
        DESCRIPTION
                "The compliance statement for entities which implement
                the Qtech Ac Manager Ac"
        MODULE  -- this module
                MANDATORY-GROUPS { qtechAcMgmtAcMIBGroup, qtechAcMgmtAcTrapGroup }
        ::= { qtechAcMgmtAcMIBCompliances 1 }


--********************************************************************
--                                                                  **
--           units of conformance                                   **
--                                                                  **
--********************************************************************
qtechAcMgmtAcMIBGroup OBJECT-GROUP
        OBJECTS {
            qtechAcStaLimit,
            qtechAcWtpLimit,
            qtechAcRMacField,
            qtechAcDataDtls,
            qtechAcEcnSupport,
            qtechAcBackAcIp,
            qtechAcMtu,
            qtechAcAcName,
            qtechAcLocation,
            qtechAcResetAp,
            qtechAcApNum,
            qtechAc80211aRateType,
            qtechAc80211bRateType,
            qtechAcFallback,
            qtechAcStaNum,
            qtechAcMacAddr,
            qtechAcDescriptor,
            qtechAcPID,
            qtechAcHwId,
            qtechAcSN,
            qtechAcTemp,
            qtechAcAPUpDownCtrl,
            qtechAcAPJoinFailCtrl,
            qtechAcAPDecryEroReportCtrl,
            qtechAcApImageUpdtCtrl,
            qtechAcApConfigMsgEroCtrl,
            qtechAcApRadioOperStatuCtrl,
            qtechAcApAuthenFailCtrl,
            qtechAcApTimestampCtrl,
            qtechAcStaOperCtrl,
            qtechAcType,
            qtechAcNeid,
            qtechAcManufacturer,
            qtechAcSwVer,
            qtechAcSwManufacturer,
            qtechAcStaResourceNotEnough,
            qtechAcPppoeClientAct,
            qtechAcPppoeClientMax,
            qtechAcStaActThredhold,
            qtechAcStaDisactThredhold,
            qtechAcStaTotalRoamThredhold,
            qtechAcStaPerRoamThredhold,
            qtechAcStaOffLineRemainTime,
            qtechAcStaOffLineNumber,
            qtechAcStaOffLineDelSingle,
            qtechAcStaOffLineDelAll,
            qtechAcRmOffLineApConfig,
            qtechAcFlowBlApName1,
            qtechAcFlowBlApName2,
            qtechAcFlowBlApName3,
            qtechAcFlowBlApName4,
            qtechAcFlowBlApName5,
            qtechAcFlowBlApName6,
            qtechAcFlowBlApName7,
            qtechAcFlowBlApName8,
            qtechAcFlowBlApName9,
            qtechAcFlowBlApName10,
            qtechAcFlowBlNum,
            qtechAcFlowBlRS,
            qtechAcNumBlApName1,
            qtechAcNumBlApName2,
            qtechAcNumBlApName3,
            qtechAcNumBlApName4,
            qtechAcNumBlApName5,
            qtechAcNumBlApName6,
            qtechAcNumBlApName7,
            qtechAcNumBlApName8,
            qtechAcNumBlApName9,
            qtechAcNumBlApName10,
            qtechAcNumBlNum,
            qtechAcNumBlRS,
            qtechAcInAcRoamNum,
            qtechAcBetweenAcRoamInNum,
            qtechAcStaOnOverThrodOperCtrl,
            qtechAcStaOffOverThrodOperCtrl,
            qtechAcBetweenAcRoamOutNum,
            qtechAcCpusageSwitch,
            qtechAcCpuUsageTrapTimer,
            qtechAcStatTrapTimer,
            qtechAcHeartBeat,
            qtechAcTotalApSupNum,
            qtechAcTotalStaSupNum,
            qtechAcTotalPppoeSupNum,
            qtechAcCurTotalApSupNum,
            qtechAcCurTotalStaSupNum,
            qtechAcCurTotalPppoeSupNum,
            qtechAcNasId,
            qtechAcStaLimitLicense,
            qtechAcWtpLimitLicense,
            qtechAcStaIpv6Num,
            qtechAcIpv6,
            qtechAcIpv6Prefix,
            qtechAcIpv6Type,
            qtechAcIpv6AddrType,
            qtechApApName,
            qtechApApgName,
            qtechApDiscTimer,
            qtechApEchoReqTimer,
            qtechApEroReportTimer,
            qtechApStaTimeoutTimer,
            qtechApStatisticsTimer,
            qtechApFallback,
            qtechApImageId,
            qtechApIpDhcp,
            qtechApLocation,
            qtechApWpsMfp,
            qtechApLastRebootReason,
            qtechApEthernetIfName,
            qtechApEthernetIfMacAddress,
            qtechApEthernetIfAdminStatus,
            qtechApEthernetIfOperStatus,
            qtechApEthernetIfRxUcastPkts,
            qtechApEthernetIfRxNUcastPkts,
            qtechApEthernetIfTxUcastPkts,
            qtechApEthernetIfTxNUcastPkts,
            qtechApEthernetIfDuplex,
            qtechApEthernetIfLinkSpeed,
            qtechApEthernetIfPOEPower,
            qtechApAdminStatus,
            qtechApEthernetIfRxBoardPkts,
            qtechApEthernetIfRxMultiPkts,
            qtechApEthernetIfTxBoardPkts,
            qtechApEthernetIfTxMultiPkts,
            qtechApEthernetIfDropPkts,
            qtechApSn,
            qtechApIp,
            qtechApStaNum,
            qtechApToFat,
            qtechApId,
            qtechApSwVer,
            qtechApBootVer,
            qtechApPID,
            qtechApHwVer,
            qtechApStaLimit,
            qtechApFactoryDefault,
            qtechApCpuUsageTrapTimer,
            qtechApStatTrapTimer,
            qtechApLinkOnTimeInterval,
            qtechApNetId,
            qtechApUptime,
            qtechApOfftime,
            qtechApState,
            qtechApNasId,
            qtechApCoverArea,
            qtechApLinkOnTimeIntervalMs,
            qtechApUptimeMs,
            qtechApHbUptimeMs,
            qtechApIpv6,
            qtechApIpv6Prefix,
            qtechApIpv6PrefixLen,
            qtechApIpv6Type,
            qtechApIpv6Gateway,
            qtechApIpv6StaNum,
            qtechApRadioEn,
            qtechApTxPower,
            qtechApDtimPeriod,
            qtechApBeaconPeriod,
            qtechApCountry,
            qtechApPreaShort,
            qtechApRadioBssid,
            qtechApTxPowerLevel,
            qtechApTxPowerGlobal,
            qtechApCurChan,
            qtechApRfGlobal,
            qtechApRadioRateType,
            qtechApRadioType,
            qtechApRadio11bSup,
            qtechApMaxTxPower,
            qtechApMinTxPower,
            qtechApCurTxPower,
            qtechApMaxTxPowerPer,
            qtechApMinTxPowerPer,
            qtechApIpAddr,
            qtechApIpMask,
            qtechApIpGetway,
            qtechApStaticIpRS,
            qtechApgDiscTimer,
            qtechApgEchoReqTimer,
            qtechApgEroReportTimer,
            qtechApgStaTimeoutTimer,
            qtechApgStatisticsTimer,
            qtechApgFallback,
            qtechApgImageId,
            qtechApgCreatEn,
            qtechApgEnableRadioEn,
            qtechApgWlanId,
            qtechApgVlanId,
            qtechApgWlanIntfMapRS,
            qtechWlanShort,
            qtechWlanSpctMgmt,
            qtechWlanEnQos,
            qtechWlanShortSlotTime,
            qtechWlanEnableApsd,
            qtechWlanAckType,
            qtechWlanTunnelType,
            qtechWlanBroadSsid,
            qtechWlanWlanSsid,
            qtechWlanWlanProfile,
            qtechWlanCreateMapRS,
            qtechWlanRts,
            qtechWlanShortTry,
            qtechWlanLongTry,
            qtechWlanStaNum,
            qtechWlanNasId,
            qtechWlanChanV,
            qtechWlanChanBandEn,
            qtechWlanLimitChanRS,
            qtechWlanChanBandRS,
            qtechStaApMacAddr,
            qtechStaVlan,
            qtechStaWlanId,
            qtechStaIp,
            qtechStaApIp,
            qtechStaApRadioId,
            qtechStaApRadioType,
            qtechStaAssoType,
            qtechStaAuthType,
            qtechStaRoamTimesPerMin,
            qtechStaOnTimesPerHour,
            qtechStaOffTimesPerHour,
            qtechNotifyApMac,
            qtechNotifyStaMac,
            qtechNotifyApIp,
            qtechNotifyStaIp,
            qtechNotifyStaOperType,
            qtechNotifyStaApRadioId,
            qtechNotifyStaApRadioType,
            qtechNotifyStaVlanId,
            qtechNotifyStaWlanId,
            qtechNotifyTime,
            qtechNotifyOldVer,
            qtechNotifyNewVer,
            qtechNotifyVerUpdtReason,
            qtechNotifyAcMBChangeV,
            qtechNotifyStaOperTimes,
            qtechNotifyAcPowerIndex,
            qtechNotifyAcPowerStatu,
            qtechAcKickClient,
            qtechAcOpenStaNum,
            qtechAcOpenStaAbnormalDownTimes,
            qtechAcWepPskStaNum,
            qtechAcWepPskStaAbnormalDownTimes
        }
        STATUS  current
        DESCRIPTION
                "A collection of objects providing ac manager (echo) ability to a
                Qtech agent."
        ::= { qtechAcMgmtAcMIBGroups 1 }

qtechAcMgmtAcTrapGroup NOTIFICATION-GROUP
    NOTIFICATIONS {
        qtechNotifyApTimeStampFail,
        qtechNotifyStaOper,
        qtechNotifyAcMBChange,
        qtechNotifyApSwUpdtFail,
        qtechNotifyStaActOverThredhold,
        qtechNotifyStaDisactOverThredhold,
        qtechNotifyStaRoamTotal,
        qtechNotifyStaRoamPerMin,
        qtechNotifyAcPowerStatus,
        qtechNotify86PowerOffAlarm,
        qtechNotify86PowerOffAlarmClear,
        qtechNotifyApSwUpdtSuccess,
        qtechNotifyApUp,
        qtechNotifyApDown,
        qtechNotifyApSwUpdtFailApMac,
        qtechNotifyApTimeStampFailApMac
        }
    STATUS  current
    DESCRIPTION
        "A collection of traps providing ac manager (echo) ability to a
         Qtech agent."
    ::= { qtechAcMgmtAcMIBGroups 2 }

END
