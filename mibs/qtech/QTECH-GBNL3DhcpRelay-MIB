QTECH-GBNL3DhcpRelay-MIB  DEFINITIONS ::= BEGIN

    IMPORTS
        MODULE-IDENTITY, OBJECT-TYPE,
        Integer32, Counter32,
        TimeTicks, IpAddress                    FROM SNMPv2-SMI
        DisplayString, TruthValue,RowStatus     FROM SNMPv2-TC

        MODULE-COMPLIANCE, OBJECT-GROUP         FROM SNMPv2-CONF

        gbnL3                                   FROM QTECH-MASTER-MIB;

    gbnL3DhcpRelay  MODULE-IDENTITY
        LAST-UPDATED    "0105030000Z"  -- May 03,2001
        ORGANIZATION    "QTECH LLC"
        CONTACT-INFO    "Basil Budko
                         E-mail: budko@qtech.ru"

        DESCRIPTION     "GBN Enterprise MIB definition."

        REVISION        "0105030000Z"  -- May 03,2001
        DESCRIPTION     "Initial MIB creation."

        ::= { gbnL3 5 }

------------------------------------------------------------------------------
-- Textual Conventions (i.e., these do not affect object encoding):
------------------------------------------------------------------------------


    dhcpRelayEnableStatus OBJECT-TYPE
        SYNTAX INTEGER {
             enable(1),
             disable(2)
        }
        MAX-ACCESS read-write
        STATUS current
        DESCRIPTION
            ""
        ::= { gbnL3DhcpRelay 1 }

     dhcpRelayDebugStatus OBJECT-TYPE
        SYNTAX INTEGER {
             enable(1),
             disable(2)
        }
        MAX-ACCESS read-write
        STATUS obsolete
        DESCRIPTION
            ""
        ::= { gbnL3DhcpRelay 2 }

    dhcpRelayGroupTable OBJECT-TYPE
        SYNTAX SEQUENCE OF DhcpRelayGroupEntry
        MAX-ACCESS not-accessible
        STATUS current
        DESCRIPTION
            ""
        ::= { gbnL3DhcpRelay 3 }

    dhcpRelayGroupEntry  OBJECT-TYPE
        SYNTAX DhcpRelayGroupEntry
        MAX-ACCESS not-accessible
        STATUS current
        DESCRIPTION
            "Table entry for switch interface control and status information."
        INDEX { dhcpRelaySvrGroupNo }
        ::= { dhcpRelayGroupTable 1 }

    DhcpRelayGroupEntry ::= SEQUENCE {
        dhcpRelaySvrGroupNo         Integer32,
        dhcpRelayServerIp           IpAddress
      }

    dhcpRelaySvrGroupNo    OBJECT-TYPE
        SYNTAX Integer32(1..32)
        MAX-ACCESS read-only
        STATUS current
        DESCRIPTION
            "Group number"
        ::= { dhcpRelayGroupEntry 1 }


    dhcpRelayServerIp    OBJECT-TYPE
        SYNTAX IpAddress
        MAX-ACCESS   read-write
        STATUS current
        DESCRIPTION
            "Dhcp Server IP Address of the group"
        ::= { dhcpRelayGroupEntry 2 }


    dhcpRelayIfaceTable OBJECT-TYPE
        SYNTAX SEQUENCE OF DhcpRelayIfaceEntry
        MAX-ACCESS not-accessible
        STATUS current
        DESCRIPTION
            ""
        ::= { gbnL3DhcpRelay 4 }

    dhcpRelayIfaceEntry  OBJECT-TYPE
        SYNTAX DhcpRelayIfaceEntry
        MAX-ACCESS not-accessible
        STATUS current
        DESCRIPTION
            "Table entry for switch interface control and status information."
        INDEX { dhcpRelaySvrVlanIfaceNo }
        ::= { dhcpRelayIfaceTable 1 }

    DhcpRelayIfaceEntry ::= SEQUENCE {
        dhcpRelaySvrVlanIfaceNo     Integer32(1..32),
        dhcpRelayVlanIfaceGroupNo   Integer32(1..32)
      }

    dhcpRelaySvrVlanIfaceNo  OBJECT-TYPE
        SYNTAX Integer32(1..32)
        MAX-ACCESS read-only
        STATUS current
        DESCRIPTION
            "interface number"
        ::= { dhcpRelayIfaceEntry 1 }

    dhcpRelayVlanIfaceGroupNo  OBJECT-TYPE
        SYNTAX Integer32(1..32)
        MAX-ACCESS read-write
        STATUS current
        DESCRIPTION
            "Group number"
        ::= { dhcpRelayIfaceEntry 2 }



     dhcpRelayHideServerIp OBJECT-TYPE
        SYNTAX INTEGER {
             enable(1),
             disable(2)
        }
        MAX-ACCESS read-write
        STATUS current
        DESCRIPTION
            ""
        ::= { gbnL3DhcpRelay 5 }
END
