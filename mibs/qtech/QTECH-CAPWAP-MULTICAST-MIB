-- *****************************************************************
-- QTECH-CAPWAP-MULTICAST-MIB.mib:  Qtech CAPWAP MULTICAST MIB file
--
-- Oct 2009, xieweiwu
--
-- Copyright (c) 2009 by Qtech Networks Co.,Ltd.
-- All rights reserved.
--
-- *****************************************************************
--

QTECH-CAPWAP-MULTICAST-MIB DEFINITIONS ::= BEGIN

IMPORTS
        MODULE-IDENTITY,
        OBJECT-TYPE,
        IpAddress
                FROM SNMPv2-SMI
        MODULE-COMPLIANCE,
        OBJECT-GROUP
                FROM SNMPv2-CONF
        qtechMgmt
                FROM QTECH-SMI;

qtechCapwapMulticastMIB MODULE-IDENTITY
        LAST-UPDATED "200910220000Z"
        ORGANIZATION "Qtech Networks Co.,Ltd."
        CONTACT-INFO
                "
                Tel: 4008-111-000

                E-mail: service@qtech.com.cn"
        DESCRIPTION
                "This module defines qtech Capwap Multicast mibs."
        REVISION      "200910220000Z"
        DESCRIPTION
                "Initial version of this MIB module."
        ::= { qtechMgmt 59}

qtechCapwapMulticastMIBObjects OBJECT IDENTIFIER ::= { qtechCapwapMulticastMIB 1 }


--capwap multicast mode
qtechCapwapMulticastWorkingMode OBJECT-TYPE
        SYNTAX INTEGER {
            unicast(1),    -- Working in capwap unicast(1),
            multicast(2)    -- Working in capwap multicast(2)
        }
        MAX-ACCESS read-write
        STATUS current
        DESCRIPTION
            "System Multicast working mode:
             unicast(1):
                Working in capwap unicast.
             multicast(2):
                Working in capwap multicast."
        DEFVAL { unicast }
        ::= { qtechCapwapMulticastMIBObjects 1 }

--show capwap multicast group address
qtechCapwapMulticastGroup OBJECT-TYPE
        SYNTAX IpAddress
        MAX-ACCESS read-write
        STATUS current
        DESCRIPTION
            "the address of capwap multicast"
        ::= { qtechCapwapMulticastMIBObjects 2 }

qtechCapwapMulticastMIBConformance OBJECT IDENTIFIER ::= { qtechCapwapMulticastMIB 2 }
qtechCapwapMulticastMIBCompliances OBJECT IDENTIFIER ::= { qtechCapwapMulticastMIBConformance 1 }
qtechCapwapMulticastMIBGroups      OBJECT IDENTIFIER ::= { qtechCapwapMulticastMIBConformance 2 }


-- compliance statements

qtechCapwapMulticastMIBCompliance MODULE-COMPLIANCE
        STATUS  current
        DESCRIPTION
                "The compliance statement for entities which implement
                the Qtech Capwap Multicast MIB"
        MODULE  -- this module
                MANDATORY-GROUPS { qtechCapwapMulticastMIBGroup
                 }
        ::= { qtechCapwapMulticastMIBCompliances 1 }

-- units of conformance

qtechCapwapMulticastMIBGroup OBJECT-GROUP
        OBJECTS {
           qtechCapwapMulticastWorkingMode,
           qtechCapwapMulticastGroup
        }
        STATUS  current
        DESCRIPTION
                "A collection of objects providing CapwapMulticast configure ."
        ::= { qtechCapwapMulticastMIBGroups 1 }

END
