-- *****************************************************************
-- QTECH-AUTH-GATEWAY-MIB.mib:  Qtech Auth-Gateway MIB file
--
-- April 2009, Chenfg
--
-- Copyright (c) 2009 by Qtech Networks Co.,Ltd.
-- All rights reserved.
--
-- *****************************************************************
--

QTECH-AUTH-GATEWAY-MIB DEFINITIONS ::= BEGIN

IMPORTS
    MODULE-IDENTITY,
    OBJECT-TYPE,
    NOTIFICATION-TYPE,
    IpAddress,
    Unsigned32,
    TimeTicks,
    Gauge32
            FROM SNMPv2-SMI
    RowStatus,
    MacAddress,
    DisplayString
            FROM SNMPv2-TC
    IfIndex
            FROM QTECH-TC
    InetAddressType,
    InetAddress
            FROM INET-ADDRESS-MIB
    MODULE-COMPLIANCE,
    OBJECT-GROUP,
    NOTIFICATION-GROUP
            FROM SNMPv2-CONF
    qtechMgmt
            FROM QTECH-SMI;

qtechWebAuthMIB MODULE-IDENTITY
    LAST-UPDATED "201003080000Z"
    ORGANIZATION "Qtech Networks Co.,Ltd."
    CONTACT-INFO
            "
            Tel: 4008-111-000

            E-mail: service@qtech.com.cn"
    DESCRIPTION
            "This module defines qtech authGateway mibs."
    REVISION      "201003080000Z"
    DESCRIPTION
            "Added qtechWebAuthUserExtTable."
    REVISION      "201002220000Z"
    DESCRIPTION
            "Add some objects for Application Security Zone Solutions
             by Wujj."
    REVISION      "200904160000Z"
    DESCRIPTION
            "Initial version of this MIB module."
    ::= { qtechMgmt 40}

qtechWebAuthMIBObjects OBJECT IDENTIFIER ::= { qtechWebAuthMIB 1 }


-- Web authentication gateway user table

qtechWebAuthUserTable OBJECT-TYPE
    SYNTAX  SEQUENCE OF QtechWebAuthUserEntry
    MAX-ACCESS  not-accessible
    STATUS      current
    DESCRIPTION
            "A table that contains generic information about every user
            that is authenticated by web authentication gateway."
    ::= { qtechWebAuthMIBObjects 1 }

qtechWebAuthUserEntry OBJECT-TYPE
    SYNTAX  QtechWebAuthUserEntry
    MAX-ACCESS  not-accessible
    STATUS  current
    DESCRIPTION
         "The entry of web authentication gateway table."
    INDEX   { authUserIpAddr }
    ::= { qtechWebAuthUserTable 1 }

QtechWebAuthUserEntry ::=
    SEQUENCE {
        authUserIpAddr                   IpAddress,
        authUserOnlineFlag               Gauge32,
        authUserTimeLimit                Gauge32,
        authUserTimeUsed                 Gauge32,
        authUserStatus                   RowStatus,
        authUserRoleName                 OCTET STRING,
        authUserSecZoneName              OCTET STRING,
        authUserSecZonePermissionType    Gauge32,
        authUserSecZonePermissionList    OCTET STRING,
        authUserOtherPermissionType      Gauge32,
        authUserTerminateCause	         Gauge32
    }

authUserIpAddr OBJECT-TYPE
    SYNTAX  IpAddress
    MAX-ACCESS  read-only
    STATUS  current
    DESCRIPTION
            "The IP address of the user."
    ::= { qtechWebAuthUserEntry 1 }

authUserOnlineFlag OBJECT-TYPE
    SYNTAX  Gauge32
    MAX-ACCESS  read-only
    STATUS  current
    DESCRIPTION
            "The online(1)/offline(2) flag of the user."
    ::= { qtechWebAuthUserEntry 2 }


authUserTimeLimit OBJECT-TYPE
    SYNTAX  Gauge32
    MAX-ACCESS  read-create
    STATUS  current
    DESCRIPTION
            "The value, in seconds, is time limit of the online user.
            If the time is unlimited, then this object has the value 0."
    ::= { qtechWebAuthUserEntry 3 }

authUserTimeUsed OBJECT-TYPE
    SYNTAX  Gauge32
    MAX-ACCESS  read-only
    STATUS  current
    DESCRIPTION
            "The value, in seconds, is time used by the online user."
    ::= { qtechWebAuthUserEntry 4 }

-- up-link bandwidth Limit
-- ::= { qtechWebAuthUserEntry 5 }     this OID is obsolete

-- down-link bandwidth Limit
-- ::= { qtechWebAuthUserEntry 6 }     this OID is obsolete

-- intramural up-link flow limit
-- ::= { qtechWebAuthUserEntry 7 }     this OID is obsolete

-- intramural down-link flow limit
-- ::= { qtechWebAuthUserEntry 8 }     this OID is obsolete

-- inland up-link flow limit
-- ::= { qtechWebAuthUserEntry 9 }     this OID is obsolete

-- inland down-link flow limit
-- ::= { qtechWebAuthUserEntry 10 }    this OID is obsolete

-- overseas up-link flow limit
-- ::= { qtechWebAuthUserEntry 11 }    this OID is obsolete

-- overseas down-link flow limit
-- ::= { qtechWebAuthUserEntry 12 }    this OID is obsolete

-- intramural up-link flow counter
-- ::= { qtechWebAuthUserEntry 13 }    this OID is obsolete

-- intramural down-link flow counter
-- ::= { qtechWebAuthUserEntry 14 }    this OID is obsolete

-- inland up-link flow counter
-- ::= { qtechWebAuthUserEntry 15 }    this OID is obsolete

-- inland down-link flow counter
-- ::= { qtechWebAuthUserEntry 16 }    this OID is obsolete

-- overseas up-link flow counter
-- ::= { qtechWebAuthUserEntry 17 }    this OID is obsolete

-- overseas down-link flow counter
-- ::= { qtechWebAuthUserEntry 18 }    this OID is obsolete

authUserStatus OBJECT-TYPE
    SYNTAX RowStatus
    MAX-ACCESS read-create
    STATUS current
    DESCRIPTION
            "The status of this row, by which new entries may be
            created, or old entries deleted from this table."
   ::= { qtechWebAuthUserEntry 19 }

authUserRoleName OBJECT-TYPE
    SYNTAX  OCTET STRING(SIZE (32))
    MAX-ACCESS read-create
    STATUS current
    DESCRIPTION
            "The roleName of the user, defined in Application Security Zone Solutions.
            Apply to all support the Application Security Zone Solutions RSR Series products."
    ::= { qtechWebAuthUserEntry 20 }

authUserSecZoneName OBJECT-TYPE
    SYNTAX  OCTET STRING(SIZE (32))
    MAX-ACCESS read-create
    STATUS current
    DESCRIPTION
            "User login secZoneName, defined in Application Security Zone Solutions.
            Apply to all support the Application Security Zone Solutions Firewall Series products."
    ::= { qtechWebAuthUserEntry 21}

authUserSecZonePermissionType OBJECT-TYPE
    SYNTAX  Gauge32
    MAX-ACCESS read-create
    STATUS current
    DESCRIPTION
            "Login user's permission type, defined in Application Security Zone Solutions.
            Apply to all support the Application Security Zone Solutions Firewall Series products.
            permit(1),deny(2)"
    ::= { qtechWebAuthUserEntry 22}

authUserSecZonePermissionList OBJECT-TYPE
    SYNTAX  OCTET STRING(SIZE (512))
    MAX-ACCESS read-create
    STATUS current
    DESCRIPTION
            "Login user's permission list, defined in Application Security Zone Solutions.
            Apply to all support the Application Security Zone Solutions Firewall Series products.
            for example,the permission list 192.168.20.21-255.255.255.255、192.168.21.21-255.255.255.0、192.168.22.22-255.255.255.128
            values C0A81414FFFFFFFFFFC0A81515FFFFFF00C0A81616FFFFFF80"
    ::= { qtechWebAuthUserEntry 23}

authUserOtherPermissionType  OBJECT-TYPE
    SYNTAX  Gauge32
    MAX-ACCESS read-create
    STATUS current
    DESCRIPTION
            "Login user's other permission type, defined in Application Security Zone Solutions.
            Apply to all support the Application Security Zone Solutions Firewall Series products.
            permit(1),deny(2)"
    ::= { qtechWebAuthUserEntry 24}

authUserTerminateCause OBJECT-TYPE
    SYNTAX  Gauge32
    MAX-ACCESS  read-only
    STATUS  current
    DESCRIPTION
            "The value, used by the offline user."
    ::= { qtechWebAuthUserEntry 25 }

-- Web authentication gateway user extension table

qtechWebAuthUserExtTable OBJECT-TYPE
    SYNTAX  SEQUENCE OF QtechWebAuthUserExtEntry
    MAX-ACCESS  not-accessible
    STATUS      current
    DESCRIPTION
            "A table that contains generic information about every user
            that is authenticated by web authentication gateway."
    ::= { qtechWebAuthMIBObjects 2 }

qtechWebAuthUserExtEntry OBJECT-TYPE
    SYNTAX  QtechWebAuthUserExtEntry
    MAX-ACCESS  not-accessible
    STATUS  current
    DESCRIPTION
         "The entry of web authentication gateway table."
    INDEX   { authUserExtAddrType, authUserExtAddr }
    ::= { qtechWebAuthUserExtTable 1 }

QtechWebAuthUserExtEntry ::=
    SEQUENCE {
        authUserExtAddrType                 InetAddressType,
        authUserExtAddr                     InetAddress,
        authUserExtMac                      MacAddress,
        authUserExtIfIndex                  IfIndex,
        authUserExtVlanId                   Unsigned32,
        authUserExtOnlineFlag               Gauge32,
        authUserExtTimeLimit                Gauge32,
        authUserExtTimeUsed                 Gauge32,
        authUserExtErrCause                 DisplayString,
        authUserExtStatus                   RowStatus
    }

authUserExtAddrType OBJECT-TYPE
    SYNTAX  InetAddressType
    MAX-ACCESS  read-only
    STATUS  current
    DESCRIPTION
            "The type of Internet address of the the user."
    ::= { qtechWebAuthUserExtEntry 1 }

authUserExtAddr OBJECT-TYPE
    SYNTAX  InetAddress (SIZE(0..64))
    MAX-ACCESS  read-only
    STATUS  current
    DESCRIPTION
            "The Internet address of the the user. The type of this address is
            determined by the value of the authUserExtAddrType object."
    ::= { qtechWebAuthUserExtEntry 2 }

authUserExtMac OBJECT-TYPE
    SYNTAX  MacAddress
    MAX-ACCESS  read-only
    STATUS  current
    DESCRIPTION
            "The MAC address of the the user."
    ::= { qtechWebAuthUserExtEntry 3 }

authUserExtIfIndex OBJECT-TYPE
    SYNTAX  IfIndex
    MAX-ACCESS  read-only
    STATUS  current
    DESCRIPTION
            "The interface index associated with the user."
    ::= { qtechWebAuthUserExtEntry 4 }

authUserExtVlanId OBJECT-TYPE
    SYNTAX  Unsigned32
    MAX-ACCESS  read-only
    STATUS  current
    DESCRIPTION
            "The VLAN-ID associated with the user."
    ::= { qtechWebAuthUserExtEntry 5 }

authUserExtOnlineFlag OBJECT-TYPE
    SYNTAX  Gauge32
    MAX-ACCESS  read-only
    STATUS  current
    DESCRIPTION
            "The online(1)/offline(2) flag of the user."
    ::= { qtechWebAuthUserExtEntry 6 }

authUserExtTimeLimit OBJECT-TYPE
    SYNTAX  Gauge32
    MAX-ACCESS  read-create
    STATUS  current
    DESCRIPTION
            "The value, in seconds, is time limit of the online user.
            If the time is unlimited, then this object has the value 0."
    ::= { qtechWebAuthUserExtEntry 7 }

authUserExtTimeUsed OBJECT-TYPE
    SYNTAX  Gauge32
    MAX-ACCESS  read-only
    STATUS  current
    DESCRIPTION
            "The value, in seconds, is time used by the online user."
    ::= { qtechWebAuthUserExtEntry 8 }

authUserExtErrCause OBJECT-TYPE
    SYNTAX DisplayString (SIZE  (0..64))
    MAX-ACCESS read-only
    STATUS current
    DESCRIPTION
            "The error cause information of the offline user.
            The default value is the null string, which indicates no error."
    DEFVAL { "" }
    ::= { qtechWebAuthUserExtEntry 9 }

authUserExtStatus OBJECT-TYPE
    SYNTAX RowStatus
    MAX-ACCESS read-create
    STATUS current
    DESCRIPTION
            "The status of this row, by which new entries may be
            created, or old entries deleted from this table."
    ::= { qtechWebAuthUserExtEntry 10 }


-- webauth user white list
-- add 2010-06
qtechWebAuthWhiteListTable OBJECT-TYPE
    SYNTAX   SEQUENCE OF QtechWebAuthWhiteListEntry
    MAX-ACCESS  not-accessible
    STATUS      current
    DESCRIPTION
         "A table that contains Whitelist of user authenticated
          by web authenticaton gateway."
    ::= { qtechWebAuthMIBObjects 3 }

qtechWebAuthWhiteListEntry OBJECT-TYPE
    SYNTAX  QtechWebAuthWhiteListEntry
    MAX-ACCESS  not-accessible
    STATUS  current
    DESCRIPTION
         "The entry of web authentication user Whitelist
          table."
    INDEX   {
            qtechWebAuthWhiteListAddress,
            qtechWebAuthWhiteListNetMask
        }
    ::= { qtechWebAuthWhiteListTable 1 }

QtechWebAuthWhiteListEntry ::=
    SEQUENCE {
        qtechWebAuthWhiteListAddress     IpAddress,
        qtechWebAuthWhiteListNetMask     IpAddress,
        qtechWebAuthWhiteListPort1       Unsigned32,
        qtechWebAuthWhiteListPort2       Unsigned32,
        qtechWebAuthWhiteListPort3       Unsigned32,
        qtechWebAuthWhiteListPort4       Unsigned32,
        qtechWebAuthWhiteListPort5       Unsigned32,
        qtechWebAuthWhiteListPort6       Unsigned32,
        qtechWebAuthWhiteListPort7       Unsigned32,
        qtechWebAuthWhiteListPort8       Unsigned32,
        qtechWebAuthWhiteListBindArpFlag INTEGER,
        qtechWebAuthWhiteListStatus      RowStatus
    }

qtechWebAuthWhiteListAddress OBJECT-TYPE
    SYNTAX IpAddress
    MAX-ACCESS read-only
    STATUS current
    DESCRIPTION
            "The ip address of user white list."
    ::= { qtechWebAuthWhiteListEntry 1 }

qtechWebAuthWhiteListNetMask OBJECT-TYPE
    SYNTAX IpAddress
    MAX-ACCESS read-only
    STATUS current
    DESCRIPTION
            "The NetMask of user white list."
    ::= { qtechWebAuthWhiteListEntry 2 }

qtechWebAuthWhiteListPort1 OBJECT-TYPE
    SYNTAX Unsigned32
    MAX-ACCESS read-create
    STATUS current
    DESCRIPTION
            "The access port1 of user white list."
    ::= { qtechWebAuthWhiteListEntry 3 }

qtechWebAuthWhiteListPort2 OBJECT-TYPE
    SYNTAX Unsigned32
    MAX-ACCESS read-create
    STATUS current
    DESCRIPTION
            "The access port2 of user white list."
    ::= { qtechWebAuthWhiteListEntry 4 }

qtechWebAuthWhiteListPort3 OBJECT-TYPE
    SYNTAX Unsigned32
    MAX-ACCESS read-create
    STATUS current
    DESCRIPTION
            "The access port3 of user white list."
    ::= { qtechWebAuthWhiteListEntry 5 }

qtechWebAuthWhiteListPort4 OBJECT-TYPE
    SYNTAX Unsigned32
    MAX-ACCESS read-create
    STATUS current
    DESCRIPTION
            "The access port4 of user white list."
    ::= { qtechWebAuthWhiteListEntry 6 }

qtechWebAuthWhiteListPort5 OBJECT-TYPE
    SYNTAX Unsigned32
    MAX-ACCESS read-create
    STATUS current
    DESCRIPTION
            "The access port5 of user white list."
    ::= { qtechWebAuthWhiteListEntry 7 }

qtechWebAuthWhiteListPort6 OBJECT-TYPE
    SYNTAX Unsigned32
    MAX-ACCESS read-create
    STATUS current
    DESCRIPTION
            "The access port6 of user white list."
    ::= { qtechWebAuthWhiteListEntry 8 }

qtechWebAuthWhiteListPort7 OBJECT-TYPE
    SYNTAX Unsigned32
    MAX-ACCESS read-create
    STATUS current
    DESCRIPTION
            "The access port7 of user white list."
    ::= { qtechWebAuthWhiteListEntry 9 }

qtechWebAuthWhiteListPort8 OBJECT-TYPE
    SYNTAX Unsigned32
    MAX-ACCESS read-create
    STATUS current
    DESCRIPTION
            "The access port8 of user white list."
    ::= { qtechWebAuthWhiteListEntry 10 }

qtechWebAuthWhiteListBindArpFlag OBJECT-TYPE
    SYNTAX INTEGER {
              no(0),
              yes(1)
           }
    MAX-ACCESS read-create
    STATUS current
    DESCRIPTION
            "The flag represent whether bind the arp or not.
             0 - not binding arp,
             1 - need to binding arp"
    ::= { qtechWebAuthWhiteListEntry 11 }

qtechWebAuthWhiteListStatus OBJECT-TYPE
    SYNTAX RowStatus
    MAX-ACCESS read-create
    STATUS current
    DESCRIPTION
            "The status of this row, by which new entries may be
            created, or old entries deleted from this table."
    ::= { qtechWebAuthWhiteListEntry 12 }


-- webauth SDG user list
-- add 2010-12
qtechWebAuthSDGUserTable OBJECT-TYPE
    SYNTAX   SEQUENCE OF QtechWebAuthSDGUserEntry
    MAX-ACCESS  not-accessible
    STATUS      current
    DESCRIPTION
         "A table that contains webauth SDG user."
    ::= { qtechWebAuthMIBObjects 4 }

qtechWebAuthSDGUserEntry OBJECT-TYPE
    SYNTAX  QtechWebAuthSDGUserEntry
    MAX-ACCESS  not-accessible
    STATUS  current
    DESCRIPTION
         "The SDG user entry of web authentication gateway table."
    INDEX   { authSDGUserVrfg, authSDGUserIpAddr }
    ::= { qtechWebAuthSDGUserTable 1 }

QtechWebAuthSDGUserEntry ::=
    SEQUENCE {
        authSDGUserVrfg                   DisplayString,
        authSDGUserIpAddr                   IpAddress,
        authSDGUserOnlineFlag               Gauge32,
        authSDGUserTimeLimit                Gauge32,
        authSDGUserTimeUsed                 Gauge32,
        authSDGUserVrf                    DisplayString,
        authSDGUserRoleName                 OCTET STRING,
        authSDGUserSecZoneName              OCTET STRING,
        authSDGUserSecZonePermissionType    Gauge32,
        authSDGUserSecZonePermissionList    OCTET STRING,
        authSDGUserOtherPermissionType      Gauge32,
        authSDGUserTerminateCause	         Gauge32,
        authSDGUserStatus                   RowStatus
    }

authSDGUserVrfg OBJECT-TYPE
    SYNTAX  DisplayString (SIZE (0..32))
    MAX-ACCESS  read-only
    STATUS  current
    DESCRIPTION
            "The vrf group name of the SDG user."
    ::= { qtechWebAuthSDGUserEntry 1 }

authSDGUserIpAddr OBJECT-TYPE
    SYNTAX  IpAddress
    MAX-ACCESS  read-only
    STATUS  current
    DESCRIPTION
            "The IP address of the SDG user."
    ::= { qtechWebAuthSDGUserEntry 2 }

authSDGUserOnlineFlag OBJECT-TYPE
    SYNTAX  Gauge32
    MAX-ACCESS  read-only
    STATUS  current
    DESCRIPTION
            "The online(1)/offline(2) flag of the SDG user."
    ::= { qtechWebAuthSDGUserEntry 3 }


authSDGUserTimeLimit OBJECT-TYPE
    SYNTAX  Gauge32
    MAX-ACCESS  read-create
    STATUS  current
    DESCRIPTION
            "The value, in seconds, is time limit of the online SDG user.
            If the time is unlimited, then this object has the value 0."
    ::= { qtechWebAuthSDGUserEntry 4 }

authSDGUserTimeUsed OBJECT-TYPE
    SYNTAX  Gauge32
    MAX-ACCESS  read-only
    STATUS  current
    DESCRIPTION
            "The value, in seconds, is time used by the online SDG user."
    ::= { qtechWebAuthSDGUserEntry 5 }

authSDGUserVrf OBJECT-TYPE
    SYNTAX  DisplayString
    MAX-ACCESS  read-only
    STATUS  current
    DESCRIPTION
            "The (dest) vrf name for the user."
    ::= { qtechWebAuthSDGUserEntry 6 }

-- up-link bandwidth Limit
-- ::= { qtechWebAuthSDGUserEntry 7 }     this OID is obsolete

-- down-link bandwidth Limit
-- ::= { qtechWebAuthSDGUserEntry 8 }     this OID is obsolete

-- intramural up-link flow limit
-- ::= { qtechWebAuthSDGUserEntry 9 }     this OID is obsolete

-- intramural down-link flow limit
-- ::= { qtechWebAuthSDGUserEntry 10 }     this OID is obsolete

-- inland up-link flow limit
-- ::= { qtechWebAuthSDGUserEntry 11 }     this OID is obsolete

-- inland down-link flow limit
-- ::= { qtechWebAuthSDGUserEntry 12 }    this OID is obsolete

-- overseas up-link flow limit
-- ::= { qtechWebAuthSDGUserEntry 13 }    this OID is obsolete

-- overseas down-link flow limit
-- ::= { qtechWebAuthSDGUserEntry 14 }    this OID is obsolete

-- intramural up-link flow counter
-- ::= { qtechWebAuthSDGUserEntry 15 }    this OID is obsolete

-- intramural down-link flow counter
-- ::= { qtechWebAuthSDGUserEntry 16 }    this OID is obsolete

-- inland up-link flow counter
-- ::= { qtechWebAuthSDGUserEntry 17 }    this OID is obsolete

-- inland down-link flow counter
-- ::= { qtechWebAuthSDGUserEntry 18 }    this OID is obsolete

-- overseas up-link flow counter
-- ::= { qtechWebAuthSDGUserEntry 19 }    this OID is obsolete

-- overseas down-link flow counter
-- ::= { qtechWebAuthSDGUserEntry 20 }    this OID is obsolete

authSDGUserRoleName OBJECT-TYPE
    SYNTAX  OCTET STRING(SIZE (32))
    MAX-ACCESS read-create
    STATUS current
    DESCRIPTION
            "The roleName of the user, defined in Application Security Zone Solutions.
            Apply to all support the Application Security Zone Solutions RSR Series products."
    ::= { qtechWebAuthSDGUserEntry 21 }

authSDGUserSecZoneName OBJECT-TYPE
    SYNTAX  OCTET STRING(SIZE (32))
    MAX-ACCESS read-create
    STATUS current
    DESCRIPTION
            "User login secZoneName, defined in Application Security Zone Solutions.
            Apply to all support the Application Security Zone Solutions Firewall Series products."
    ::= { qtechWebAuthSDGUserEntry 22}

authSDGUserSecZonePermissionType OBJECT-TYPE
    SYNTAX  Gauge32
    MAX-ACCESS read-create
    STATUS current
    DESCRIPTION
            "Login user's permission type, defined in Application Security Zone Solutions.
            Apply to all support the Application Security Zone Solutions Firewall Series products.
            permit(1),deny(2)"
    ::= { qtechWebAuthSDGUserEntry 23}

authSDGUserSecZonePermissionList OBJECT-TYPE
    SYNTAX  OCTET STRING(SIZE (512))
    MAX-ACCESS read-create
    STATUS current
    DESCRIPTION
            "Login user's permission list, defined in Application Security Zone Solutions.
            Apply to all support the Application Security Zone Solutions Firewall Series products.
            for example,the permission list 192.168.20.21-255.255.255.255、192.168.21.21-255.255.255.0、192.168.22.22-255.255.255.128
            values C0A81414FFFFFFFFFFC0A81515FFFFFF00C0A81616FFFFFF80"
    ::= { qtechWebAuthSDGUserEntry 24}

authSDGUserOtherPermissionType  OBJECT-TYPE
    SYNTAX  Gauge32
    MAX-ACCESS read-create
    STATUS current
    DESCRIPTION
            "Login user's other permission type, defined in Application Security Zone Solutions.
            Apply to all support the Application Security Zone Solutions Firewall Series products.
            permit(1),deny(2)"
    ::= { qtechWebAuthSDGUserEntry 25}

authSDGUserTerminateCause OBJECT-TYPE
    SYNTAX  Gauge32
    MAX-ACCESS  read-only
    STATUS  current
    DESCRIPTION
            "The value, used by the offline user."
    ::= { qtechWebAuthSDGUserEntry 26 }

authSDGUserStatus OBJECT-TYPE
    SYNTAX RowStatus
    MAX-ACCESS read-create
    STATUS current
    DESCRIPTION
            "The status of this row, by which new entries may be
            created, or old entries deleted from this table."
   ::= { qtechWebAuthSDGUserEntry 27 }


-- Web authentication user table indexed with mac address.
-- added 2013-03

qtechWebAuthMacUserTable OBJECT-TYPE
    SYNTAX  SEQUENCE OF QtechWebAuthMacUserEntry
    MAX-ACCESS  not-accessible
    STATUS      current
    DESCRIPTION
            "A table that contains information, indexed with mac address,
            for each user that is authenticated by web authentication gateway."
    ::= { qtechWebAuthMIBObjects 5 }

qtechWebAuthMacUserEntry OBJECT-TYPE
    SYNTAX  QtechWebAuthMacUserEntry
    MAX-ACCESS  not-accessible
    STATUS  current
    DESCRIPTION
         "The entry of web authentication mac table."
    INDEX   { qtechAuthMacUserMacAddr }
    ::= { qtechWebAuthMacUserTable 1 }

QtechWebAuthMacUserEntry ::=
    SEQUENCE {
        qtechAuthMacUserMacAddr               MacAddress,
        qtechAuthMacUserName                  OCTET STRING,
        qtechAuthMacUserTerminalId            OCTET STRING
    }

qtechAuthMacUserMacAddr OBJECT-TYPE
    SYNTAX  MacAddress
    MAX-ACCESS  read-only
    STATUS  current
    DESCRIPTION
            "The MAC address of the the user."
    ::= { qtechWebAuthMacUserEntry 1 }

qtechAuthMacUserName OBJECT-TYPE
    SYNTAX  OCTET STRING(SIZE (253))
    MAX-ACCESS read-only
    STATUS current
    DESCRIPTION
            "Name of the user, specified with qtechAuthMacUserMacAddr. "
    ::= { qtechWebAuthMacUserEntry 2 }

qtechAuthMacUserTerminalId OBJECT-TYPE
    SYNTAX  OCTET STRING(SIZE (253))
    MAX-ACCESS read-only
    STATUS current
    DESCRIPTION
            "Terminal Identification of the user, specified with qtechAuthMacUserMacAddr. "
    ::= { qtechWebAuthMacUserEntry 3 }

qtechWebAuthUserMIB OBJECT IDENTIFIER ::= { qtechWebAuthMIBObjects 6 }

qtechWebAuthUserMIBTable OBJECT-TYPE
    SYNTAX  SEQUENCE OF QtechWebAuthUserMIBEntry
    MAX-ACCESS  not-accessible
    STATUS      current
    DESCRIPTION
            "A table that contains information, indexed with ip address,
			for each user that is authenticated by web authentication gateway."
	::= { qtechWebAuthUserMIB 1 }

qtechWebAuthUserMIBEntry OBJECT-TYPE
    SYNTAX  QtechWebAuthUserMIBEntry
    MAX-ACCESS  not-accessible
    STATUS  current
    DESCRIPTION
         "The entry of web authentication ip table."
    INDEX   { qtechAuthUserMIBIpAddress }
    ::= { qtechWebAuthUserMIBTable 1 }

QtechWebAuthUserMIBEntry ::=
    SEQUENCE {
        qtechAuthUserMIBIpAddress                IpAddress,
        qtechAuthUserMIBName                     OCTET STRING,
        qtechAuthUserMIBAuthType                 Gauge32,
        qtechAuthUserMIBMacAddress               MacAddress,
        qtechAuthUserMIBVlanId                   Gauge32,
        qtechAuthUserMIBPortIndex                Gauge32,
        qtechAuthUserMIBTimeUsed                 Gauge32
    }

qtechAuthUserMIBIpAddress OBJECT-TYPE
    SYNTAX    IpAddress
    MAX-ACCESS read-only
    STATUS current
    DESCRIPTION
            "Webauth user ip address. "
    ::= { qtechWebAuthUserMIBEntry 1 }

qtechAuthUserMIBName OBJECT-TYPE
    SYNTAX    OCTET STRING
    MAX-ACCESS read-only
    STATUS current
    DESCRIPTION
            "Webauth username. "
    ::= { qtechWebAuthUserMIBEntry 2 }

qtechAuthUserMIBAuthType OBJECT-TYPE
    SYNTAX    Gauge32
    MAX-ACCESS read-only
    STATUS current
    DESCRIPTION
            "Webauth user authentication type, 1-v2portal, 2-iportal. "
    ::= { qtechWebAuthUserMIBEntry 3 }

qtechAuthUserMIBMacAddress OBJECT-TYPE
    SYNTAX    MacAddress
    MAX-ACCESS read-only
    STATUS current
    DESCRIPTION
            "Webauth user mac address. "
    ::= { qtechWebAuthUserMIBEntry 4 }

qtechAuthUserMIBVlanId OBJECT-TYPE
    SYNTAX    Gauge32
    MAX-ACCESS read-only
    STATUS current
    DESCRIPTION
            "Webauth user vlanid. "
    ::= { qtechWebAuthUserMIBEntry 5 }

qtechAuthUserMIBPortIndex OBJECT-TYPE
    SYNTAX    Gauge32
    MAX-ACCESS read-only
    STATUS current
    DESCRIPTION
            "Webauth user authentication port index. "
    ::= { qtechWebAuthUserMIBEntry 6 }

qtechAuthUserMIBTimeUsed OBJECT-TYPE
    SYNTAX    Gauge32
    MAX-ACCESS read-only
    STATUS current
    DESCRIPTION
            "Webauth user time used. "
    ::= { qtechWebAuthUserMIBEntry 7 }

-- web-auth trap

qtechWebAuthMIBTraps        OBJECT IDENTIFIER ::= { qtechWebAuthMIB 2 }
qtechWebAuthMIBTrapsObjects OBJECT IDENTIFIER ::= { qtechWebAuthMIB 4 }

-- Trap Objects
qtechWebAuthApMac OBJECT-TYPE
    SYNTAX      MacAddress
    MAX-ACCESS  accessible-for-notify
    STATUS      current
    DESCRIPTION
        "Represents the unique identifier of a AP."
    ::= { qtechWebAuthMIBTrapsObjects 1 }

qtechWebAuthApIp OBJECT-TYPE
    SYNTAX      IpAddress
    MAX-ACCESS  accessible-for-notify
    STATUS      current
    DESCRIPTION
        "Represents the Ip address of a AP."
    ::= { qtechWebAuthMIBTrapsObjects 2 }

qtechWebAuthStaMac OBJECT-TYPE
    SYNTAX      MacAddress
    MAX-ACCESS  accessible-for-notify
    STATUS      current
    DESCRIPTION
        "Represents the unique identifier of a STA."
    ::= { qtechWebAuthMIBTrapsObjects 3 }

qtechWebAuthStaIp OBJECT-TYPE
    SYNTAX      IpAddress
    MAX-ACCESS  accessible-for-notify
    STATUS      current
    DESCRIPTION
        "Represents the Ip of a STA."
    ::= { qtechWebAuthMIBTrapsObjects 4 }

qtechWebAuthStaIpv6 OBJECT-TYPE
    SYNTAX      InetAddress
    MAX-ACCESS  accessible-for-notify
    STATUS      current
    DESCRIPTION
              "Sta ipv6 address."
    ::= { qtechWebAuthMIBTrapsObjects 5 }

qtechWebAuthStaOperType OBJECT-TYPE
    SYNTAX      INTEGER (1..3)
    MAX-ACCESS  accessible-for-notify
    STATUS      current
    DESCRIPTION
        "Represents the sta's web-auth operation, 1-webon,2-weboff, 3-webauthfail"
    ::= { qtechWebAuthMIBTrapsObjects 6 }

qtechWebAuthStaApRadioId OBJECT-TYPE
    SYNTAX      INTEGER(1..2)
    MAX-ACCESS  accessible-for-notify
    STATUS      current
    DESCRIPTION
        "Represents the radio id which STA attach."
    ::= { qtechWebAuthMIBTrapsObjects 7 }

qtechWebAuthStaApRadioType OBJECT-TYPE
    SYNTAX      INTEGER (1..2)
    MAX-ACCESS  accessible-for-notify
    STATUS      current
    DESCRIPTION
              "1--802.11b
               2--802.11a"
    ::= { qtechWebAuthMIBTrapsObjects 8 }

qtechWebAuthStaVlanId OBJECT-TYPE
    SYNTAX      INTEGER (1..4094)
    MAX-ACCESS  accessible-for-notify
    STATUS      current
    DESCRIPTION
              "Vlan Id the sta belongs to"
    ::= { qtechWebAuthMIBTrapsObjects 9 }

qtechWebAuthStaWlanId OBJECT-TYPE
    SYNTAX      INTEGER (1..4095)
    MAX-ACCESS  accessible-for-notify
    STATUS      current
    DESCRIPTION
              "Wlan Id the sta belongs to"
    ::= { qtechWebAuthMIBTrapsObjects 10 }

qtechWebAuthOperTime OBJECT-TYPE
    SYNTAX	TimeTicks
    MAX-ACCESS  accessible-for-notify
    STATUS      current
    DESCRIPTION
              "Sta auth oper time"
    ::= { qtechWebAuthMIBTrapsObjects 11 }

qtechWebAuthStaAssoAuthMode OBJECT-TYPE
    SYNTAX  INTEGER {
        open(0),
        wep(1),
        dot1x-wep(2),
        dot1x-wpa(3),
        dot1x-wpa2(4),
        mab(5),
        psk-wpa(6),
        psk-wpa2(7),
        wapi(8)
    }
    MAX-ACCESS  accessible-for-notify
    STATUS  current
    DESCRIPTION
            "The Sta associate authentication mode."
    ::= { qtechWebAuthMIBTrapsObjects 12 }

qtechWebAuthStaNetAuthMode OBJECT-TYPE
    SYNTAX  INTEGER {
        open(0),
        web(1)
    }
    MAX-ACCESS  accessible-for-notify
    STATUS  current
    DESCRIPTION
            "The Sta's authentication mode after associated."
    ::= { qtechWebAuthMIBTrapsObjects 13 }

qtechWebAuthStaRssi OBJECT-TYPE
    SYNTAX      INTEGER
    MAX-ACCESS  accessible-for-notify
    STATUS      current
    DESCRIPTION
            "The Sta's Received Signal Strength Indicator."
    ::= { qtechWebAuthMIBTrapsObjects 14 }

qtechWebAuthStaSsid OBJECT-TYPE
    SYNTAX  DisplayString
    MAX-ACCESS  accessible-for-notify
    STATUS  current
    DESCRIPTION
            "Sta associate ssid."
    ::= { qtechWebAuthMIBTrapsObjects 15 }

qtechWebAuthStaLinkRate OBJECT-TYPE
    SYNTAX  INTEGER
    MAX-ACCESS  accessible-for-notify
    STATUS  current
    DESCRIPTION
            "Sta link rate."
    ::= { qtechWebAuthMIBTrapsObjects 16 }

qtechWebAuthStaCurChannel OBJECT-TYPE
    SYNTAX  INTEGER
    MAX-ACCESS  accessible-for-notify
    STATUS  current
    DESCRIPTION
            "Sta current channel."
    ::= { qtechWebAuthMIBTrapsObjects 17 }

qtechWebAuthStaUsername OBJECT-TYPE
    SYNTAX	DisplayString (SIZE(1..255))
    MAX-ACCESS  accessible-for-notify
    STATUS      current
    DESCRIPTION
              "Sta auth username"
    ::= { qtechWebAuthMIBTrapsObjects 18 }

qtechWebAuthStaTerminalType OBJECT-TYPE
    SYNTAX      DisplayString
    MAX-ACCESS  accessible-for-notify
    STATUS      current
    DESCRIPTION
              "Sta terminal type"
    ::= { qtechWebAuthMIBTrapsObjects 19 }

qtechWebAuthStaTerminateCause OBJECT-TYPE
    SYNTAX  INTEGER
    MAX-ACCESS  accessible-for-notify
    STATUS  current
    DESCRIPTION
            "Sta terminate cause."
    ::= { qtechWebAuthMIBTrapsObjects 20 }

qtechWebAuthStaReplyMessage OBJECT-TYPE
    SYNTAX  DisplayString
    MAX-ACCESS  accessible-for-notify
    STATUS  current
    DESCRIPTION
            "Sta auth fail reason ."
    ::= { qtechWebAuthMIBTrapsObjects 21 }

qtechWebAuthStaTerminalId OBJECT-TYPE
    SYNTAX      DisplayString
    MAX-ACCESS  accessible-for-notify
    STATUS      current
    DESCRIPTION
              "Sta terminal Identification"
    ::= { qtechWebAuthMIBTrapsObjects 22 }

qtechWebAuthType OBJECT-TYPE
    SYNTAX    INTEGER (1..2)
    MAX-ACCESS  accessible-for-notify
    STATUS      current
    DESCRIPTION
              "Webauth user type(1-v2portal, 2-iportal)"
    ::= { qtechWebAuthMIBTrapsObjects 23 }

qtechWebAuthPortIndex OBJECT-TYPE
    SYNTAX    INTEGER
    MAX-ACCESS  accessible-for-notify
    STATUS      current
    DESCRIPTION
              "Webauth user authentication port index"
    ::= { qtechWebAuthMIBTrapsObjects 24 }

-- Trap Node
qtechWebAuthUserLeave NOTIFICATION-TYPE
    OBJECTS   { authUserIpAddr, authUserTimeUsed, authUserTerminateCause }
    STATUS     current
    DESCRIPTION
            "The user offline trap."
    ::= { qtechWebAuthMIBTraps 1 }

qtechWebAuthUserExtLeave NOTIFICATION-TYPE
    OBJECTS  {
                authUserExtAddrType,
                authUserExtAddr,
                authUserExtMac,
                authUserExtIfIndex,
                authUserExtVlanId,
                authUserExtTimeUsed,
                authUserExtErrCause
    }
    STATUS     current
    DESCRIPTION
            "The user extension offline trap."
    ::= { qtechWebAuthMIBTraps 2 }

qtechWebAuthSDGUserLeave NOTIFICATION-TYPE
    OBJECTS   {
		    authSDGUserVrfg,
		    authSDGUserIpAddr,
		    authSDGUserTimeUsed,
		    authSDGUserTerminateCause
    }
    STATUS     current
    DESCRIPTION
            "The user offline trap."
    ::= { qtechWebAuthMIBTraps 3 }

qtechWebAuthWlanMgmt NOTIFICATION-TYPE
    OBJECTS   {
          qtechWebAuthApMac,
          qtechWebAuthApIp,
          qtechWebAuthStaMac,
          qtechWebAuthStaIp,
          qtechWebAuthStaIpv6,
          qtechWebAuthStaOperType,
          qtechWebAuthStaApRadioId,
          qtechWebAuthStaApRadioType,
          qtechWebAuthStaVlanId,
          qtechWebAuthStaWlanId,
          qtechWebAuthOperTime,
          qtechWebAuthStaAssoAuthMode,
          qtechWebAuthStaNetAuthMode,
          qtechWebAuthStaRssi,
          qtechWebAuthStaSsid,
          qtechWebAuthStaLinkRate,
          qtechWebAuthStaCurChannel,
          qtechWebAuthStaUsername,
          qtechWebAuthStaTerminalType,
          qtechWebAuthStaTerminateCause,
          qtechWebAuthStaReplyMessage,
          qtechWebAuthStaTerminalId
    }
    STATUS     current
    DESCRIPTION
            "Wlan Web-auth user mgmt trap sent when sta login or logout."
    ::= { qtechWebAuthMIBTraps 4 }

qtechWebAuthUserOper NOTIFICATION-TYPE
    OBJECTS    {
                qtechWebAuthStaOperType,
                qtechWebAuthType,
                qtechWebAuthStaUsername,
                qtechWebAuthStaIp,
                qtechWebAuthStaMac,
                qtechWebAuthStaVlanId,
                qtechWebAuthPortIndex,
                qtechWebAuthStaTerminateCause
	}
    STATUS     current
    DESCRIPTION
            "Web-auth user mgmt trap sent when user login, logout or authentication failed."
    ::= { qtechWebAuthMIBTraps 5 }

-- compliance statements

qtechWebAuthMIBConformance OBJECT IDENTIFIER ::= { qtechWebAuthMIB 3 }
qtechWebAuthMIBCompliances OBJECT IDENTIFIER ::= { qtechWebAuthMIBConformance 1 }
qtechWebAuthMIBGroups      OBJECT IDENTIFIER ::= { qtechWebAuthMIBConformance 2 }

qtechWebAuthMIBCompliance MODULE-COMPLIANCE
    STATUS  current
    DESCRIPTION
            "The compliance statement for entities which implement
            the My WebAuth MIB"
    MODULE  -- this module
            MANDATORY-GROUPS { qtechWebAuthMIBGroup, qtechWebAuthTrapGroup
             }

    ::= { qtechWebAuthMIBCompliances 1 }

-- units of conformance

qtechWebAuthMIBGroup OBJECT-GROUP
    OBJECTS {
         authUserIpAddr,
         authUserOnlineFlag,
         authUserTimeLimit,
         authUserTimeUsed,
         authUserStatus,
         authUserRoleName,
         authUserSecZoneName,
         authUserSecZonePermissionType,
         authUserSecZonePermissionList,
         authUserOtherPermissionType,
         authUserTerminateCause,
         authUserExtAddrType,
         authUserExtAddr,
         authUserExtMac,
         authUserExtIfIndex,
         authUserExtVlanId,
         authUserExtOnlineFlag,
         authUserExtTimeLimit,
         authUserExtTimeUsed,
         authUserExtErrCause,
         authUserExtStatus,
         qtechWebAuthWhiteListAddress,
         qtechWebAuthWhiteListNetMask,
         qtechWebAuthWhiteListPort1,
         qtechWebAuthWhiteListPort2,
         qtechWebAuthWhiteListPort3,
         qtechWebAuthWhiteListPort4,
         qtechWebAuthWhiteListPort5,
         qtechWebAuthWhiteListPort6,
         qtechWebAuthWhiteListPort7,
         qtechWebAuthWhiteListPort8,
         qtechWebAuthWhiteListBindArpFlag,
         qtechWebAuthWhiteListStatus,
         authSDGUserVrfg,
         authSDGUserIpAddr,
         authSDGUserOnlineFlag,
         authSDGUserTimeLimit,
         authSDGUserTimeUsed,
         authSDGUserVrf,
         authSDGUserRoleName,
         authSDGUserSecZoneName,
         authSDGUserSecZonePermissionType,
         authSDGUserSecZonePermissionList,
         authSDGUserOtherPermissionType,
         authSDGUserTerminateCause,
         authSDGUserStatus
         }
    STATUS  current
    DESCRIPTION
            "A collection of objects providing authGateway management and
            opertion to a Qtech agent."
    ::= { qtechWebAuthMIBGroups 1 }

qtechWebAuthTrapGroup NOTIFICATION-GROUP
    NOTIFICATIONS {
        qtechWebAuthUserLeave,
        qtechWebAuthUserExtLeave,
        qtechWebAuthSDGUserLeave
    }
    STATUS  current
    DESCRIPTION
            "A collection of traps providing authGateway management and
            opertion to a Qtech agent."
    ::= { qtechWebAuthMIBGroups 2 }

END
