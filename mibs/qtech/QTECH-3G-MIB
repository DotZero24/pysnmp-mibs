-- ====================================================================
-- Copyright (c) 2011 by Qtech Networks Co.,Ltd. All rights reserved.
--
-- Description: The MIB is designed to get 3G wireless safenet solution statistic information.
-- Reference: rujie Enterprise MIB
-- =====================================================================

QTECH-3G-MIB DEFINITIONS ::= BEGIN

    IMPORTS
        DisplayString,TEXTUAL-CONVENTION,TimeStamp
            FROM SNMPv2-TC
        IpAddress, Integer32, Counter32, Counter64, OBJECT-TYPE,
        MODULE-IDENTITY, Gauge32, NOTIFICATION-TYPE, Unsigned32
            FROM SNMPv2-SMI
        MODULE-COMPLIANCE, OBJECT-GROUP, NOTIFICATION-GROUP
            FROM SNMPv2-CONF
        qtechMgmt
            FROM QTECH-SMI;

    qtech3GMonitor MODULE-IDENTITY
        LAST-UPDATED "201102220000Z"
        ORGANIZATION
            "Qtech Networks Co.,Ltd."
        CONTACT-INFO
            "Tel: 4008-111-000
             E-mail: service@qtech.com.cn"
        DESCRIPTION
            "The MIB is designed to get statistic information of
             3G wireless safenet. With this MIB, we can get information of a certain
             3G user or all users."
        REVISION      "201102220000Z"
        DESCRIPTION
                "Initial version of this MIB module."
        ::= { qtechMgmt 95 }


-- ========================================================================
-- Node definitions
-- ========================================================================
--Begin the node of qtech3GObjects.

    qtech3GObjects OBJECT IDENTIFIER ::= { qtech3GMonitor 1 }

-- ===============================================
-- Begin the table of qtech3GTable.
-- ===============================================

    qtech3GTable OBJECT-TYPE
        SYNTAX SEQUENCE OF Qtech3GEntry
        MAX-ACCESS not-accessible
        STATUS current
        DESCRIPTION
            "The 3G connection infomation fot every user. There is one
             entry in this table for each active 3G connection."
        ::= { qtech3GObjects 1 }

    qtech3GEntry OBJECT-TYPE
        SYNTAX Qtech3GEntry
        MAX-ACCESS not-accessible
        STATUS current
        DESCRIPTION
            "Information about qtech3GTunnelTable."
        INDEX { qtech3GIPAddr }
        ::= { qtech3GTable 1 }

    Qtech3GEntry ::=
        SEQUENCE {
            qtech3gUsername
                DisplayString,
            qtech3GOnlineStatus
            	INTEGER,
            qtech3GIMEI
                DisplayString,
            qtech3GIPAddrType
            	INTEGER,
            qtech3GIPAddr
            	IpAddress,
            qtech3GUplineTime
                TimeStamp,
            qtech3GActiveTime
           	    Integer32,
            qtech3GSignalStrength
           	    Integer32,
            qtech3GISP
           	    INTEGER,
            qtech3GSysMode
           	    INTEGER,
            qtech3GServiceStatus
            	INTEGER,
            qtech3GRoamingStatus
                INTEGER,
            qtech3GDomain
            	INTEGER,
            qtech3GSIMStatus
                INTEGER,
   	    qtech3GSignalStrengthPercent
                Integer32,
            qtech3GApn
                DisplayString,
            qtech3GCellID
                Integer32,
            qtech3GLAC
                Integer32,
            qtech3GBSID
                Integer32,
            qtech3GSID
                Integer32,
            qtech3GNID
                Integer32,
            qtech3GIMSI
                DisplayString,
            qtech3GESN
                DisplayString,
            qtech3GPhoneNumber
                DisplayString,
            qtech3GifIndex
                INTEGER,
            qtech3GBSLONG
                Integer32,
            qtech3GBSLAT
                Integer32,
	    qtech3GBackupInfo
	            INTEGER,
            qtech3GSerialNumber
                DisplayString,
	    qtech3GBackupIMSI
                DisplayString,
            qtech3GGatewayIPAddr
            	IpAddress,
	    qtech3GLineDownCause
	            Integer32,
	    qtech3GModemType
	            INTEGER
        }

    qtech3gUsername OBJECT-TYPE
        SYNTAX DisplayString
        MAX-ACCESS read-only
        STATUS current
        DESCRIPTION
            "The Username  of 3G User."
        ::= { qtech3GEntry 1 }

    qtech3GOnlineStatus OBJECT-TYPE
        SYNTAX INTEGER
            {
                lpm(0),
		online(1),
                offline(4),
		ftm(5),
		reset(6),
		rfOff(7)
            }
        MAX-ACCESS read-only
        STATUS current
        DESCRIPTION
            "the status of 3G user. online or offline"
        ::= { qtech3GEntry 2 }

    qtech3GIMEI OBJECT-TYPE
        SYNTAX DisplayString
        MAX-ACCESS read-only
        STATUS current
        DESCRIPTION
            "the IMEI number of 3G user."
        ::= { qtech3GEntry 3 }

    qtech3GIPAddrType OBJECT-TYPE
         SYNTAX INTEGER {
            ipv4Addr(1),
            ipv6Addr(2)
         }
        MAX-ACCESS read-only
        STATUS current
        DESCRIPTION
            "The IP Address type of remote user."
        ::= { qtech3GEntry 4 }

    qtech3GIPAddr OBJECT-TYPE
        SYNTAX IpAddress
        MAX-ACCESS read-only
        STATUS current
        DESCRIPTION
            "The 3G remote users's IP address."
        ::= { qtech3GEntry 5 }

    qtech3GUplineTime OBJECT-TYPE
        SYNTAX TimeStamp
        MAX-ACCESS read-only
        STATUS current
        DESCRIPTION
            "The value of up line time for this 3G user."
        ::= { qtech3GEntry 6 }


        -- 1.3.6.1.4.1.27514.1.1.10.2.95.1.1.1.7
        qtech3GActiveTime OBJECT-TYPE
			SYNTAX Integer32 (0..2147483647)
			MAX-ACCESS read-only
			STATUS current
			DESCRIPTION
				"The duration of the 3G connection has been active for one user.
				2147483647 is defined as invalid value."
			::= { qtech3GEntry 7 }


		-- 1.3.6.1.4.1.27514.1.1.10.2.95.1.1.1.8
		qtech3GSignalStrength OBJECT-TYPE
			SYNTAX Integer32 (-150..0)
			MAX-ACCESS read-only
			STATUS current
			DESCRIPTION
				"The signal strength of the 3G connection for this user."
			::= { qtech3GEntry 8 }


		-- 1.3.6.1.4.1.27514.1.1.10.2.95.1.1.1.9
		qtech3GISP OBJECT-TYPE
			SYNTAX INTEGER
				{
				chinaUnicom(1),
				chinaTelecom(2),
				chinaMobile(3)
				}
			MAX-ACCESS read-only
			STATUS current
			DESCRIPTION
				"the ISP of 3G networsk."
			::= { qtech3GEntry 9 }


		-- 1.3.6.1.4.1.27514.1.1.10.2.95.1.1.1.10
		qtech3GSysMode OBJECT-TYPE
			SYNTAX INTEGER
				{
				noService(0),
				amps(1),
				cdma(2),
				gsmGprs(3),
				hdr(4),
				wcdma(5),
				gps(6),
				gsmCdma(7),
				cdmaHdrHybrid(8),
				tdscdma(15),
				td-1te(100),
				fdd-lte(101)
				}
			MAX-ACCESS read-only
			STATUS current
			DESCRIPTION
				"the system mode of 3G networsk."
			::= { qtech3GEntry 10 }


		-- 1.3.6.1.4.1.27514.1.1.10.2.95.1.1.1.11
		qtech3GServiceStatus OBJECT-TYPE
			SYNTAX INTEGER
				{
				noService(0),
				restricted(1),
				valid(2),
				restrictedRegional(3),
				powerSavingAndDeepSleepState(4)
				}
			MAX-ACCESS read-only
			STATUS current
			DESCRIPTION
				"the sevice status of 3G user."
			::= { qtech3GEntry 11 }


		-- 1.3.6.1.4.1.27514.1.1.10.2.95.1.1.1.12
		qtech3GRoamingStatus OBJECT-TYPE
			SYNTAX INTEGER
				{
				noRoaming(0),
				roaming(1)
				}
			MAX-ACCESS read-only
			STATUS current
			DESCRIPTION
				"the roaming status of 3G  user."
			::= { qtech3GEntry 12 }


		-- 1.3.6.1.4.1.27514.1.1.10.2.95.1.1.1.13
		qtech3GDomain OBJECT-TYPE
			SYNTAX INTEGER
				{
				noService(0),
				onlyCS(1),
				onlyPS(2),
				pSCS(3),
				pSCSnotRegistered(4),
				ePSService(100),
				cdmaNotSupport(255)
				}
			MAX-ACCESS read-only
			STATUS current
			DESCRIPTION
				"the Domain status of 3G user ."
			::= { qtech3GEntry 13 }


		-- 1.3.6.1.4.1.27514.1.1.10.2.95.1.1.1.14
		qtech3GSIMStatus OBJECT-TYPE
			SYNTAX INTEGER
				{
				invalidUsimCard(0),
				validUsimCard(1),
				invalidForCS(2),
				invalidForPS(3),
				invalidForCSPS(4),
				noUsimCard(255)
				}
			MAX-ACCESS read-only
			STATUS current
			DESCRIPTION
				"the SIM card status of 3G user."
			::= { qtech3GEntry 14 }


		-- 1.3.6.1.4.1.27514.1.1.10.2.95.1.1.1.15
		qtech3GSignalStrengthPercent OBJECT-TYPE
			SYNTAX Integer32 (0..100)
			MAX-ACCESS read-only
			STATUS current
			DESCRIPTION
				"The percent of signal strength of the 3G connection for this user."
			::= { qtech3GEntry 15 }


		-- 1.3.6.1.4.1.27514.1.1.10.2.95.1.1.1.16
		qtech3GApn OBJECT-TYPE
			SYNTAX DisplayString
			MAX-ACCESS read-only
			STATUS current
			DESCRIPTION
				"The access-point  of 3G User(only used in TD-SCDMA and WCDMA)."
			::= { qtech3GEntry 16 }


		-- 1.3.6.1.4.1.27514.1.1.10.2.95.1.1.1.17
		qtech3GCellID OBJECT-TYPE
			SYNTAX Integer32 (0..100)
			MAX-ACCESS read-only
			STATUS current
			DESCRIPTION
				"The access Cell id  of 3G User(only used in TD-SCDMA and WCDMA)."
			::= { qtech3GEntry 17 }


		-- 1.3.6.1.4.1.27514.1.1.10.2.95.1.1.1.18
		qtech3GLAC OBJECT-TYPE
			SYNTAX Integer32 (0..100)
			MAX-ACCESS read-only
			STATUS current
			DESCRIPTION
				"The Location Area Code  of 3G User(only used in TD-SCDMA and WCDMA)."
			::= { qtech3GEntry 18 }


		-- 1.3.6.1.4.1.27514.1.1.10.2.95.1.1.1.19
		qtech3GBSID OBJECT-TYPE
			SYNTAX Integer32 (0..100)
			MAX-ACCESS read-only
			STATUS current
			DESCRIPTION
				"The Base Station ID  of 3G User(only used in CDMA2000)."
			::= { qtech3GEntry 19 }


		-- 1.3.6.1.4.1.27514.1.1.10.2.95.1.1.1.20
		qtech3GNID OBJECT-TYPE
			SYNTAX Integer32 (0..100)
			MAX-ACCESS read-only
			STATUS current
			DESCRIPTION
				"The Network ID  of 3G User(only used in CDMA2000)."
			::= { qtech3GEntry 20 }


		-- 1.3.6.1.4.1.27514.1.1.10.2.95.1.1.1.21
		qtech3GSID OBJECT-TYPE
			SYNTAX Integer32 (0..100)
			MAX-ACCESS read-only
			STATUS current
			DESCRIPTION
				"The System ID  of 3G User(only used in CDMA2000)."
			::= { qtech3GEntry 21 }


		-- 1.3.6.1.4.1.27514.1.1.10.2.95.1.1.1.22
		qtech3GIMSI OBJECT-TYPE
			SYNTAX DisplayString
			MAX-ACCESS read-only
			STATUS current
			DESCRIPTION
				"The IMSI  of 3G User."
			::= { qtech3GEntry 22 }


		-- 1.3.6.1.4.1.27514.1.1.10.2.95.1.1.1.23
		qtech3GESN OBJECT-TYPE
			SYNTAX DisplayString
			MAX-ACCESS read-only
			STATUS current
			DESCRIPTION
				"The ESN  of 3G User(only used in CDMA2000)."
			::= { qtech3GEntry 23 }


		-- 1.3.6.1.4.1.27514.1.1.10.2.95.1.1.1.24
		qtech3GPhoneNumber OBJECT-TYPE
			SYNTAX DisplayString
			MAX-ACCESS read-only
			STATUS current
			DESCRIPTION
				"The Phone Number of 3G User."
			::= { qtech3GEntry 24 }


		-- 1.3.6.1.4.1.27514.1.1.10.2.95.1.1.1.25
		qtech3GifIndex OBJECT-TYPE
			SYNTAX INTEGER
			MAX-ACCESS read-only
			STATUS current
			DESCRIPTION
				"The Index of 3G Interface."
			::= { qtech3GEntry 25 }


		-- 1.3.6.1.4.1.27514.1.1.10.2.95.1.1.1.26
		qtech3GBSLONG OBJECT-TYPE
			SYNTAX Integer32
			MAX-ACCESS read-only
			STATUS current
			DESCRIPTION
				"The longitude of 3G User(only used in CDMA2000)."
			::= { qtech3GEntry 26 }


		-- 1.3.6.1.4.1.27514.1.1.10.2.95.1.1.1.27
		qtech3GBSLAT OBJECT-TYPE
			SYNTAX Integer32
			MAX-ACCESS read-only
			STATUS current
			DESCRIPTION
				"The latitude of 3G User(only used in CDMA2000)."
			::= { qtech3GEntry 27 }


		-- 1.3.6.1.4.1.27514.1.1.10.2.95.1.1.1.28
		qtech3GBackupInfo OBJECT-TYPE
			SYNTAX INTEGER
				{
				no-backup(0),
				myself(1),
				master(2),
				slave(3)
				}
			MAX-ACCESS read-only
			STATUS current
			DESCRIPTION
				"The backup info of 3G line."
			::= { qtech3GEntry 28 }


		-- 1.3.6.1.4.1.27514.1.1.10.2.95.1.1.1.29
		qtech3GSerialNumber OBJECT-TYPE
			SYNTAX DisplayString
			MAX-ACCESS read-only
			STATUS current
			DESCRIPTION
				"The serial number of 3G router."
			::= { qtech3GEntry 29 }


		-- 1.3.6.1.4.1.27514.1.1.10.2.95.1.1.1.30
		qtech3GBackupIMSI OBJECT-TYPE
			SYNTAX DisplayString
			MAX-ACCESS read-only
			STATUS current
			DESCRIPTION
				"The IMSI of 3G backup line."
			::= { qtech3GEntry 30 }


		-- 1.3.6.1.4.1.27514.1.1.10.2.95.1.1.1.31
		qtech3GGatewayIPAddr OBJECT-TYPE
			SYNTAX IpAddress
			MAX-ACCESS read-only
			STATUS current
			DESCRIPTION
				"The IP address of the 3g gateway."
			::= { qtech3GEntry 31 }


		-- 1.3.6.1.4.1.27514.1.1.10.2.95.1.1.1.32
		qtech3GLineDownCause OBJECT-TYPE
			SYNTAX Integer32
			MAX-ACCESS read-only
			STATUS current
			DESCRIPTION
				"The cause of line down."
			::= { qtech3GEntry 32 }

	       qtech3GModemType OBJECT-TYPE
			SYNTAX INTEGER
				{
				modem-type-3G(1),
				modem-type-4G(2)
				}
			MAX-ACCESS read-only
			STATUS current
			DESCRIPTION
				"the type of modem used in router."
			::= { qtech3GEntry 33 }


-- ===============================================
-- Begin the table of qtech3GstatTable.
-- ===============================================

    qtech3GStatTable OBJECT-TYPE
        SYNTAX SEQUENCE OF Qtech3GStatEntry
        MAX-ACCESS not-accessible
        STATUS current
        DESCRIPTION
            "The 3G connection infomation fot every user. There is one
             entry in this table for each active 3G connection."
        ::= { qtech3GObjects 2 }

    qtech3GStatEntry OBJECT-TYPE
        SYNTAX Qtech3GStatEntry
        MAX-ACCESS not-accessible
        STATUS current
        DESCRIPTION
            "Information about qtech3GTunnelTable."
        INDEX { qtech3GIPAddr }
        ::= { qtech3GStatTable 1 }

    Qtech3GStatEntry ::=
        SEQUENCE {
            qtech3GInOctets
                Counter64,
            qtech3GOutOctets
                Counter64,
            qtech3GInSpeed
                Counter64,
            qtech3GOutSpeed
                Counter64,
            qtech3G2IMSI
                DisplayString,
            qtech3G2ifIndex
                INTEGER
        }

    qtech3GInOctets OBJECT-TYPE
        SYNTAX Counter64
        MAX-ACCESS read-only
        STATUS current
        DESCRIPTION
            "The total number of octets received by this 3G user."
        ::= { qtech3GStatEntry 1 }

    qtech3GOutOctets OBJECT-TYPE
        SYNTAX Counter64
        MAX-ACCESS read-only
        STATUS current
        DESCRIPTION
            "The total number of octets sent by this 3G user."
        ::= { qtech3GStatEntry 2 }

    qtech3GInSpeed OBJECT-TYPE
        SYNTAX Counter64
        MAX-ACCESS read-only
        STATUS current
        DESCRIPTION
            "The Speed(bps) of packets received by this 3G user."
        ::= { qtech3GStatEntry 3 }

    qtech3GOutSpeed OBJECT-TYPE
        SYNTAX Counter64
        MAX-ACCESS read-only
        STATUS current
        DESCRIPTION
            "The Speed(bps) of packets snet by this 3G user."
        ::= { qtech3GStatEntry 4 }

    qtech3G2IMSI OBJECT-TYPE
        SYNTAX DisplayString
        MAX-ACCESS read-only
        STATUS current
        DESCRIPTION
            "The IMSI  of 3G User."
        ::= { qtech3GStatEntry 5 }

    qtech3G2ifIndex OBJECT-TYPE
    SYNTAX  INTEGER
    MAX-ACCESS  read-only
    STATUS  current
    DESCRIPTION
            "The Index of 3G Interface."
    ::= { qtech3GStatEntry 6 }

-- ===============================================
-- Begin the qtech3GTrapObject.
-- ===============================================

    qtech3GTrap OBJECT IDENTIFIER ::= { qtech3GObjects 3 }

    qtech3GNotifications OBJECT IDENTIFIER ::= { qtech3GTrap 1 }

    qtech3GSignalThreshold NOTIFICATION-TYPE
        OBJECTS {
                qtech3GIPAddr,
                qtech3GSignalStrength,
                qtech3GSignalStrengthPercent,
                qtech3GIMSI
        }
        STATUS current
        DESCRIPTION
            "This notification is generated when 3G signal is lower
            than the specific Threshold value."
        ::= { qtech3GNotifications 1 }

    qtech3GUpLine NOTIFICATION-TYPE
        OBJECTS {
                qtech3GIPAddr,
        	qtech3gUsername,
        	qtech3GIMSI,
                qtech3GBackupInfo,
                qtech3GSerialNumber,
                qtech3GGatewayIPAddr
        }
        STATUS current
        DESCRIPTION
            "This notification is generated when 3G user up line."
        ::= { qtech3GNotifications 2 }

    qtech3GDownLine NOTIFICATION-TYPE
        OBJECTS {
                qtech3GLineDownCause,
		qtech3GIPAddr,
                qtech3gUsername,
                qtech3GIMSI
        	}
        STATUS current
        DESCRIPTION
            "This notification is generated when 3G user down line."
        ::= { qtech3GNotifications 3 }

      qtech3GChangeAccessPoint NOTIFICATION-TYPE
        OBJECTS {
                qtech3GIPAddr,
                qtech3GApn,
                qtech3gUsername,
                qtech3GIMSI
                }
        STATUS current
        DESCRIPTION
            "This notification is generated when 3G change access point."
        ::= { qtech3GNotifications 4 }

       qtech3GBackupIntfSwitch NOTIFICATION-TYPE
        OBJECTS {
                qtech3GIPAddr,
                qtech3gUsername,
                qtech3GIMSI,
                qtech3GSerialNumber,
                qtech3GBackupIMSI
                }
        STATUS current
        DESCRIPTION
            "This notification is generated when 3G switch to backup interface
            in double card backup configuration."
        ::= { qtech3GNotifications 5 }

       qtech3GBaseSationSwitch NOTIFICATION-TYPE
           OBJECTS {
                   qtech3GISP,
                   qtech3GCellID,
                   qtech3GLAC,
                   qtech3GBSID,
                   qtech3GSID,
                   qtech3GNID,
                   qtech3GIMSI,
                   qtech3GPhoneNumber
                }
        STATUS current
        DESCRIPTION
            "This notification is generated when the access base station changes."
        ::= { qtech3GNotifications 6 }

	qtech3GTrafficInformation NOTIFICATION-TYPE
        OBJECTS {
                qtech3GIPAddr,
		qtech3GIMSI,
		qtech3GSerialNumber,
		qtech3GInOctets,
		qtech3GOutOctets
	}
        STATUS current
        DESCRIPTION
            "This notification is used for reporting the traffic information of 3G user regularly. "
        ::= { qtech3GNotifications 7 }

-- ===============================================
-- Begin the scalar parameters
-- ===============================================
    qtech3GBsNumber OBJECT-TYPE
        SYNTAX Integer32
        MAX-ACCESS  read-only
        STATUS  current
        DESCRIPTION
            "The number of Base Station available on the system"
        ::= { qtech3GObjects 4 }

-- ===============================================
-- Begin the table of qtech3GBsTable.
-- ===============================================

    qtech3GBsTable OBJECT-TYPE
        SYNTAX SEQUENCE OF Qtech3GBsEntry
        MAX-ACCESS not-accessible
        STATUS current
        DESCRIPTION
            "The Base Station Information."
        ::= { qtech3GObjects 5 }

    qtech3GBsEntry OBJECT-TYPE
        SYNTAX Qtech3GBsEntry
        MAX-ACCESS not-accessible
        STATUS current
        DESCRIPTION
            "Information about Base Station."
        INDEX { qtech3GBsSN }
        ::= { qtech3GBsTable 1 }

    Qtech3GBsEntry ::=
        SEQUENCE {
            qtech3GBsSN
                Integer32,
            qtech3GBsISP
           	    INTEGER,
            qtech3GBsMode
           	    INTEGER,
            qtech3GBsIMSI
                DisplayString,
 	        qtech3GBsLAC
                Integer32,
            qtech3GBsCellID
                Integer32,
            qtech3GBsBSID
                Integer32,
            qtech3GBsSID
                Integer32,
            qtech3GBsNID
                Integer32,
            qtech3GBsRssi
                Integer32,
            qtech3GBsBSLONG
                Integer32,
            qtech3GBsBSLAT
                Integer32
        }

    qtech3GBsSN OBJECT-TYPE
        SYNTAX Integer32
        MAX-ACCESS read-only
        STATUS current
        DESCRIPTION
            "the Sequence Of The Base Station."
        ::= { qtech3GBsEntry 1 }

    qtech3GBsISP OBJECT-TYPE
        SYNTAX INTEGER
            {
            chinaUnicom(1),
            chinaTelecom(2),
            chinaMobile(3)
            }
        MAX-ACCESS read-only
        STATUS current
        DESCRIPTION
            "the ISP of 3G networsk."
        ::= { qtech3GBsEntry 2 }

    qtech3GBsMode OBJECT-TYPE
        SYNTAX INTEGER
            {
            sys2GMode(1),
            sys3GMode(2)
            }
        MAX-ACCESS read-only
        STATUS current
        DESCRIPTION
            "the sys mode of 3G networsk."
        ::= { qtech3GBsEntry 3 }

     qtech3GBsIMSI OBJECT-TYPE
        SYNTAX DisplayString
        MAX-ACCESS read-only
        STATUS current
        DESCRIPTION
            "The IMSI of 3G User."
        ::= { qtech3GBsEntry 4 }

    qtech3GBsLAC OBJECT-TYPE
        SYNTAX Integer32
        MAX-ACCESS read-only
        STATUS current
        DESCRIPTION
            "The Location Area Code  of 3G User(only used in TD-SCDMA and WCDMA)."
        ::= { qtech3GBsEntry 5 }

     qtech3GBsCellID OBJECT-TYPE
        SYNTAX Integer32
        MAX-ACCESS read-only
        STATUS current
        DESCRIPTION
            "The access Cell id  of 3G User(only used in TD-SCDMA and WCDMA)."
        ::= { qtech3GBsEntry 6 }

    qtech3GBsBSID OBJECT-TYPE
        SYNTAX Integer32
        MAX-ACCESS read-only
        STATUS current
        DESCRIPTION
            "The Base Station ID  of 3G User(only used in CDMA2000)."
        ::= { qtech3GBsEntry 7 }

     qtech3GBsSID OBJECT-TYPE
        SYNTAX Integer32
        MAX-ACCESS read-only
        STATUS current
        DESCRIPTION
            "The System ID  of 3G User(only used in CDMA2000)."
        ::= { qtech3GBsEntry 8 }

     qtech3GBsNID OBJECT-TYPE
        SYNTAX Integer32
        MAX-ACCESS read-only
        STATUS current
        DESCRIPTION
            "The Network ID  of 3G User(only used in CDMA2000)."
        ::= { qtech3GBsEntry 9 }

    qtech3GBsRssi OBJECT-TYPE
        SYNTAX Integer32
        MAX-ACCESS read-only
        STATUS current
        DESCRIPTION
            "the strength of the connection."
        ::= { qtech3GBsEntry 10 }

	qtech3GBsBSLONG OBJECT-TYPE
        SYNTAX Integer32
        MAX-ACCESS read-only
        STATUS current
        DESCRIPTION
            "The longitude of 3G User(only used in CDMA2000)."
        ::= { qtech3GBsEntry 11 }

	qtech3GBsBSLAT OBJECT-TYPE
        SYNTAX Integer32
        MAX-ACCESS read-only
        STATUS current
        DESCRIPTION
            "The latitude of 3G User(only used in CDMA2000)."
        ::= { qtech3GBsEntry 12 }

--  ===============================================
-- Begin the table of qtech3GDeviceManagementTable.
-- ===============================================
		-- 1.3.6.1.4.1.27514.1.1.10.2.95.1.6
		qtech3GDeviceManagementTable OBJECT-TYPE
			SYNTAX SEQUENCE OF Qtech3GDeviceManagementEntry
			MAX-ACCESS not-accessible
			STATUS current
			DESCRIPTION
				"The 3G equipment infomation."
			::= { qtech3GObjects 6 }

		-- 1.3.6.1.4.1.27514.1.1.10.2.95.1.6.1
		qtech3GDeviceManagementEntry OBJECT-TYPE
			SYNTAX Qtech3GDeviceManagementEntry
			MAX-ACCESS not-accessible
			STATUS current
			DESCRIPTION
				"Information about qtech3GDeviceManagementTable."
			INDEX { qtech3GRouterSlotNumber }
			::= { qtech3GDeviceManagementTable 1 }

            Qtech3GDeviceManagementEntry ::=
                SEQUENCE {
                    qtech3GRouterType
                        DisplayString,
                    qtech3GRouterSN
                        DisplayString,
                    qtech3GRouterSlotNumber
                        DisplayString,
                    qtech3GLineCardType
                        DisplayString,
                    qtech3GCardIMSI
                        DisplayString,
                    qtech3GModemIMEI
                        DisplayString,
                    qtech3GIntfIPAddr
                        IpAddress,
                    qtech3GCardPhoneNumber
                        DisplayString,
                    qtech3GLineDetected
                        Unsigned32,
                    qtech3GLineDetectedResult
                        INTEGER,
                    qtech3GLineDetectedMainCause
                        INTEGER,
                    qtech3GLineDetectedSubCause
                        INTEGER,
                    qtech3GDeviceBackupInfo
                        INTEGER,
                    qtech3GRssiStrength
                        Integer32,
      	            qtech3GRssiStrengthPercent
                        Integer32,
                    qtech3GNetworkISPMode
                        INTEGER,
       	            qtech3GNetworkSysMode
                        INTEGER,
                    qtech3GNetworkServiceStatus
                        INTEGER,
                    qtech3GSIMCardStatus
                        INTEGER,
                    qtech3GDailMode
                        INTEGER,
                    qtech3GDeviceBackupIMSI
                        DisplayString,
                    qtech3GLineDetectedMode
                        INTEGER,
                    qtech3GPppUsername
                        DisplayString,
                    qtech3GUserApn
                        DisplayString,
                    qtech3GModemOnlineStatus
                        INTEGER,
                    qtech3GIntfIPAddrType
                        INTEGER,
                    qtech3GUserUplineTime
                        TimeStamp,
                    qtech3GUserActiveTime
                        Integer32,
                    qtech3GSIMRoamingStatus
                        INTEGER,
                    qtech3GAcessBSCellID
                        Integer32,
                    qtech3GAcessBSLAC
                        Integer32,
                    qtech3GAcessBSLONG
                        Integer32,
                    qtech3GAcessBSLAT
                        Integer32,
                    qtech3GDialOnDemandIfIndex
                        Integer32,
                    qtech3GTrafficPreventMode
                        INTEGER,
                    qtech3GTrafficPreventIfIndex
                        INTEGER,
                    qtech3GTrafficPreventListID
                        INTEGER,
                    qtech3GTrafficPreventListName
                        DisplayString,
                    qtech3GDeviceModemType
                        INTEGER,
                    qtech3GTrafficTrapInterval
                        Integer32,
                    qtech3GRssiThreshold
                        Integer32,
                    qtech3GTrapFilterMode
                        INTEGER,
                    qtech3GISPtimeout
                        Integer32,
                    qtech3GEncrypt_type
                        INTEGER,
                    qtech3GPassword
                        DisplayString
                }

		-- 1.3.6.1.4.1.27514.1.1.10.2.95.1.6.1.1
		qtech3GRouterType OBJECT-TYPE
			SYNTAX DisplayString
			MAX-ACCESS read-only
			STATUS current
			DESCRIPTION
				"Equipment tpye of 3G router."
			::= { qtech3GDeviceManagementEntry 1 }


		-- 1.3.6.1.4.1.27514.1.1.10.2.95.1.6.1.2
		qtech3GRouterSN OBJECT-TYPE
			SYNTAX DisplayString
			MAX-ACCESS read-only
			STATUS current
			DESCRIPTION
				"The serial number of 3G router."
			::= { qtech3GDeviceManagementEntry 2 }


		-- 1.3.6.1.4.1.27514.1.1.10.2.95.1.6.1.3
		qtech3GRouterSlotNumber OBJECT-TYPE
			SYNTAX DisplayString
			MAX-ACCESS read-only
			STATUS current
			DESCRIPTION
				"The number of the activity slot in 3G router."
			::= { qtech3GDeviceManagementEntry 3 }


		-- 1.3.6.1.4.1.27514.1.1.10.2.95.1.6.1.4
		qtech3GLineCardType OBJECT-TYPE
			SYNTAX DisplayString
			MAX-ACCESS read-only
			STATUS current
			DESCRIPTION
				"The tpye of 3G router line card."
			::= { qtech3GDeviceManagementEntry 4 }


		-- 1.3.6.1.4.1.27514.1.1.10.2.95.1.6.1.5
		qtech3GCardIMSI OBJECT-TYPE
			SYNTAX DisplayString
			MAX-ACCESS read-only
			STATUS current
			DESCRIPTION
				"The IMSI  of 3G User."
			::= { qtech3GDeviceManagementEntry 5 }


		-- 1.3.6.1.4.1.27514.1.1.10.2.95.1.6.1.6
		qtech3GModemIMEI OBJECT-TYPE
			SYNTAX DisplayString
			MAX-ACCESS read-only
			STATUS current
			DESCRIPTION
				"The IMEI number of 3G user."
			::= { qtech3GDeviceManagementEntry 6 }


		-- 1.3.6.1.4.1.27514.1.1.10.2.95.1.6.1.7
		qtech3GIntfIPAddr OBJECT-TYPE
			SYNTAX IpAddress
			MAX-ACCESS read-only
			STATUS current
			DESCRIPTION
				"The IP Address of 3G interface."
			::= { qtech3GDeviceManagementEntry 7 }


		-- 1.3.6.1.4.1.27514.1.1.10.2.95.1.6.1.8
		qtech3GCardPhoneNumber OBJECT-TYPE
			SYNTAX DisplayString
			MAX-ACCESS read-only
			STATUS current
			DESCRIPTION
				"The Phone Number of 3G User."
			::= { qtech3GDeviceManagementEntry 8 }


		-- 1.3.6.1.4.1.27514.1.1.10.2.95.1.6.1.9
		qtech3GLineDetected OBJECT-TYPE
			SYNTAX Unsigned32
			MAX-ACCESS read-write
			STATUS current
			DESCRIPTION
				"The command is used for Detecting 3G line."
			::= { qtech3GDeviceManagementEntry 9 }


		-- 1.3.6.1.4.1.27514.1.1.10.2.95.1.6.1.10
		qtech3GLineDetectedResult OBJECT-TYPE
			SYNTAX INTEGER
				{
				noRsponse(0),
				pass(1),
				failed(2),
				using(3),
				detecting(4)
				}
			MAX-ACCESS read-only
			STATUS current
			DESCRIPTION
				"The result of 3G line detection."
			::= { qtech3GDeviceManagementEntry 10 }


		-- 1.3.6.1.4.1.27514.1.1.10.2.95.1.6.1.11
		qtech3GLineDetectedMainCause OBJECT-TYPE
			SYNTAX INTEGER
				{
				noGivenReason(0),
				dialFailed(1),
				pppFailed(2),
				ipsecSetupFailed(3)
				}
			MAX-ACCESS read-only
			STATUS current
			DESCRIPTION
				"The main cause of 3G line detection filed."
			::= { qtech3GDeviceManagementEntry 11 }


		-- 1.3.6.1.4.1.27514.1.1.10.2.95.1.6.1.12
		qtech3GLineDetectedSubCause OBJECT-TYPE
			SYNTAX INTEGER
				{
				noGivenReason(0),
				simCardInvalid(1),
				aPNInvalid(2),
				powerlower(3),
				userInfoError(4),
				ipsecSetupFailed(5)
				}
			MAX-ACCESS read-only
			STATUS current
			DESCRIPTION
				"The details cause of 3G line detection filed."
			::= { qtech3GDeviceManagementEntry 12 }


		-- 1.3.6.1.4.1.27514.1.1.10.2.95.1.6.1.13
		qtech3GDeviceBackupInfo OBJECT-TYPE
			SYNTAX INTEGER
				{
				no-backup(0),
				myself(1),
				master(2),
				slave(3)
				}
			MAX-ACCESS read-only
			STATUS current
			DESCRIPTION
				"The backup info of 3G line."
			::= { qtech3GDeviceManagementEntry 13 }


		-- 1.3.6.1.4.1.27514.1.1.10.2.95.1.6.1.14
		qtech3GRssiStrength OBJECT-TYPE
			SYNTAX Integer32 (-150..0)
			MAX-ACCESS read-only
			STATUS current
			DESCRIPTION
				"The signal strength of the 3G connection for this user."
			::= { qtech3GDeviceManagementEntry 14 }


		-- 1.3.6.1.4.1.27514.1.1.10.2.95.1.6.1.15
		qtech3GRssiStrengthPercent OBJECT-TYPE
			SYNTAX Integer32 (0..100)
			MAX-ACCESS read-only
			STATUS current
			DESCRIPTION
				"The percent of signal strength of the 3G connection for this user."
			::= { qtech3GDeviceManagementEntry 15 }


		-- 1.3.6.1.4.1.27514.1.1.10.2.95.1.6.1.16
		qtech3GNetworkISPMode OBJECT-TYPE
			SYNTAX INTEGER
				{
				chinaUnicom(1),
				chinaTelecom(2),
				chinaMobile(3)
				}
			MAX-ACCESS read-only
			STATUS current
			DESCRIPTION
				"the ISP of 3G networsk."
			::= { qtech3GDeviceManagementEntry 16 }


		-- 1.3.6.1.4.1.27514.1.1.10.2.95.1.6.1.17
		qtech3GNetworkSysMode OBJECT-TYPE
			SYNTAX INTEGER
				{
				noService(0),
				amps(1),
				cdma(2),
				gsmGprs(3),
				hdr(4),
				wcdma(5),
				gps(6),
				gsmCdma(7),
				cdmaHdrHybrid(8),
				td-scdma(15),
				td-1te(100),
				fdd-lte(101)
				}
			MAX-ACCESS read-write
			STATUS current
			DESCRIPTION
				"the system mode of 3G networsk."
			::= { qtech3GDeviceManagementEntry 17 }


		-- 1.3.6.1.4.1.27514.1.1.10.2.95.1.6.1.18
		qtech3GNetworkServiceStatus OBJECT-TYPE
			SYNTAX INTEGER
				{
				noService(0),
				restricted(1),
				valid(2),
				restrictedRegional(3),
				powerSavingAndDeepSleepState(4)
				}
			MAX-ACCESS read-only
			STATUS current
			DESCRIPTION
				"the sevice status of 3G user."
			::= { qtech3GDeviceManagementEntry 18 }


		-- 1.3.6.1.4.1.27514.1.1.10.2.95.1.6.1.19
		qtech3GSIMCardStatus OBJECT-TYPE
			SYNTAX INTEGER
				{
				invalidUsimCard(0),
				validUsimCard(1),
				invalidForCS(2),
				invalidForPS(3),
				invalidForCSPS(4),
				noUsimCard(255)
				}
			MAX-ACCESS read-only
			STATUS current
			DESCRIPTION
				"the SIM card status of 3G user."
			::= { qtech3GDeviceManagementEntry 19 }


		-- 1.3.6.1.4.1.27514.1.1.10.2.95.1.6.1.20
		qtech3GDailMode OBJECT-TYPE
			SYNTAX INTEGER
				{
				dialOnDemand(0),
				autoDail(1)
				}
			MAX-ACCESS read-write
			STATUS current
			DESCRIPTION
				"the dial mode of 3G user."
			::= { qtech3GDeviceManagementEntry 20 }


		-- 1.3.6.1.4.1.27514.1.1.10.2.95.1.6.1.21
		qtech3GDeviceBackupIMSI OBJECT-TYPE
			SYNTAX DisplayString
			MAX-ACCESS read-only
			STATUS current
			DESCRIPTION
				"The IMSI of 3G backup line."
			::= { qtech3GDeviceManagementEntry 21 }


		-- 1.3.6.1.4.1.27514.1.1.10.2.95.1.6.1.22
		qtech3GLineDetectedMode OBJECT-TYPE
			SYNTAX INTEGER
				{
				vpdnMode(0),
				ipsecMode(1)
				}
			MAX-ACCESS read-write
			STATUS current
			DESCRIPTION
				"The mode of 3G backup line detected."
			::= { qtech3GDeviceManagementEntry 22 }


		-- 1.3.6.1.4.1.27514.1.1.10.2.95.1.6.1.23
		qtech3GPppUsername OBJECT-TYPE
			SYNTAX DisplayString
			MAX-ACCESS read-write
			STATUS current
			DESCRIPTION
				"The Username of 3G or 4G User."
			::= { qtech3GDeviceManagementEntry 23 }


		-- 1.3.6.1.4.1.27514.1.1.10.2.95.1.6.1.24
		qtech3GUserApn OBJECT-TYPE
			SYNTAX DisplayString
			MAX-ACCESS read-write
			STATUS current
			DESCRIPTION
				"The access-point of 3G or 4G User."
			::= { qtech3GDeviceManagementEntry 24 }


		-- 1.3.6.1.4.1.27514.1.1.10.2.95.1.6.1.25
		qtech3GModemOnlineStatus OBJECT-TYPE
			SYNTAX INTEGER
				{
				minimum-function(0),
				fully-function(1),
				offline-mode(2),
				sim-activate(3),
				sim-deactivate(4)
				}
			MAX-ACCESS read-only
			STATUS current
			DESCRIPTION
				"The status of 3G or 4G user. online or offline."
			::= { qtech3GDeviceManagementEntry 25 }


		-- 1.3.6.1.4.1.27514.1.1.10.2.95.1.6.1.26
		qtech3GIntfIPAddrType OBJECT-TYPE
			SYNTAX INTEGER
				{
				ipv4Addr(1),
				ipv6Addr(2)
				}
			MAX-ACCESS read-only
			STATUS current
			DESCRIPTION
				"The IP Address type of remote user"
			::= { qtech3GDeviceManagementEntry 26 }


		-- 1.3.6.1.4.1.27514.1.1.10.2.95.1.6.1.27
		qtech3GUserUplineTime OBJECT-TYPE
			SYNTAX TimeStamp
			MAX-ACCESS read-only
			STATUS current
			DESCRIPTION
				"The upline time of the 3G or 4G user  after system start"
			::= { qtech3GDeviceManagementEntry 27 }


		-- 1.3.6.1.4.1.27514.1.1.10.2.95.1.6.1.28
		qtech3GUserActiveTime OBJECT-TYPE
			SYNTAX Integer32 (0..2147483647)
			MAX-ACCESS read-only
			STATUS current
			DESCRIPTION
				"The duration of the 3G or 4g connection has been active for one user."
			::= { qtech3GDeviceManagementEntry 28 }


		-- 1.3.6.1.4.1.27514.1.1.10.2.95.1.6.1.29
		qtech3GSIMRoamingStatus OBJECT-TYPE
			SYNTAX INTEGER
				{
				noRoaming(0),
				roaming(1)
				}
			MAX-ACCESS read-only
			STATUS current
			DESCRIPTION
				"the romain status of 3G user ."
			::= { qtech3GDeviceManagementEntry 29 }


		-- 1.3.6.1.4.1.27514.1.1.10.2.95.1.6.1.30
		qtech3GAcessBSCellID OBJECT-TYPE
			SYNTAX Integer32 (0..100)
			MAX-ACCESS read-only
			STATUS current
			DESCRIPTION
				"The access Cell id  of 3G or 4g User."
			::= { qtech3GDeviceManagementEntry 30 }


		-- 1.3.6.1.4.1.27514.1.1.10.2.95.1.6.1.31
		qtech3GAcessBSLAC OBJECT-TYPE
			SYNTAX Integer32 (0..100)
			MAX-ACCESS read-only
			STATUS current
			DESCRIPTION
				"The Location Area Code  of 3G User."
			::= { qtech3GDeviceManagementEntry 31 }


		-- 1.3.6.1.4.1.27514.1.1.10.2.95.1.6.1.32
		qtech3GAcessBSLONG OBJECT-TYPE
			SYNTAX Integer32
			MAX-ACCESS read-only
			STATUS current
			DESCRIPTION
				"The longitude of 3G User."
			::= { qtech3GDeviceManagementEntry 32 }


		-- 1.3.6.1.4.1.27514.1.1.10.2.95.1.6.1.33
		qtech3GAcessBSLAT OBJECT-TYPE
			SYNTAX Integer32
			MAX-ACCESS read-only
			STATUS current
			DESCRIPTION
				"The latitude of 3G User."
			::= { qtech3GDeviceManagementEntry 33 }


		-- 1.3.6.1.4.1.27514.1.1.10.2.95.1.6.1.34
		qtech3GDialOnDemandIfIndex OBJECT-TYPE
			SYNTAX Integer32
			MAX-ACCESS read-only
			STATUS current
			DESCRIPTION
				"The Index of trigger dial-up interface."
			::= { qtech3GDeviceManagementEntry 34 }


		-- 1.3.6.1.4.1.27514.1.1.10.2.95.1.6.1.35
		qtech3GTrafficPreventMode OBJECT-TYPE
			SYNTAX INTEGER
				{
				disable(0),
				enable(1)
				}
			MAX-ACCESS read-only
			STATUS current
			DESCRIPTION
				"The status of the traffic prevent function appliled currently "
			::= { qtech3GDeviceManagementEntry 35 }


		-- 1.3.6.1.4.1.27514.1.1.10.2.95.1.6.1.36
		qtech3GTrafficPreventIfIndex OBJECT-TYPE
			SYNTAX INTEGER
			MAX-ACCESS read-only
			STATUS current
			DESCRIPTION
				"The Index of traffic-prevent interface."
			::= { qtech3GDeviceManagementEntry 36 }


		-- 1.3.6.1.4.1.27514.1.1.10.2.95.1.6.1.37
		qtech3GTrafficPreventListID OBJECT-TYPE
			SYNTAX INTEGER
			MAX-ACCESS read-only
			STATUS current
			DESCRIPTION
				"The Index of traffic-prevent Acl list id."
			::= { qtech3GDeviceManagementEntry 37 }


		-- 1.3.6.1.4.1.27514.1.1.10.2.95.1.6.1.38
		qtech3GTrafficPreventListName OBJECT-TYPE
			SYNTAX DisplayString
			MAX-ACCESS read-only
			STATUS current
			DESCRIPTION
				"The Index of traffic-prevent Acl list name."
			::= { qtech3GDeviceManagementEntry 38 }


		-- 1.3.6.1.4.1.27514.1.1.10.2.95.1.6.1.39
		qtech3GDeviceModemType OBJECT-TYPE
			SYNTAX INTEGER
				{
				modem-type-3G(1),
				modem-type-4G(2)
				}
			MAX-ACCESS read-only
			STATUS current
			DESCRIPTION
				"the type of modem used in router."
			::= { qtech3GDeviceManagementEntry 39 }

		-- 1.3.6.1.4.1.27514.1.1.10.2.95.1.6.1.40
		qtech3GTrafficTrapInterval OBJECT-TYPE
			SYNTAX Integer32 (1..1440)
			MAX-ACCESS read-write
			STATUS current
			DESCRIPTION
				"The interval of traffic-info notification appliled currently."
			::= { qtech3GDeviceManagementEntry 40 }

	        -- 1.3.6.1.4.1.27514.1.1.10.2.95.1.6.1.41
		qtech3GRssiThreshold OBJECT-TYPE
			SYNTAX Integer32 (-150..0)
			MAX-ACCESS read-write
			STATUS current
			DESCRIPTION
				"the threshold value of rssi notification appliled currently."
			::= { qtech3GDeviceManagementEntry 41 }

		-- 1.3.6.1.4.1.27514.1.1.10.2.95.1.6.1.42
		qtech3GTrapFilterMode OBJECT-TYPE
			SYNTAX INTEGER
				{
				disable(0),
				enable(1)
				}
			MAX-ACCESS read-write
			STATUS current
			DESCRIPTION
				"The status of the trap filter function appliled currently."
			::= { qtech3GDeviceManagementEntry 42 }

	        -- 1.3.6.1.4.1.27514.1.1.10.2.95.1.6.1.43
		qtech3GISPtimeout OBJECT-TYPE
			SYNTAX Integer32 (1..36000)
			MAX-ACCESS read-write
			STATUS current
			DESCRIPTION
				"The timeout parameter of trap filter function appliled currently."
			::= { qtech3GDeviceManagementEntry 43 }

		-- 1.3.6.1.4.1.27514.1.1.10.2.95.1.6.1.44
		qtech3GEncrypt_type OBJECT-TYPE
			SYNTAX INTEGER
				{
				ENCRYPT_NONE(0),
				ENCRYPT_TEMP(7)
				}
			MAX-ACCESS read-write
			STATUS current
			DESCRIPTION
				"The Encrypt type appliled currently."
			::= { qtech3GDeviceManagementEntry 44 }

		-- 1.3.6.1.4.1.27514.1.1.10.2.95.1.6.1.45
		qtech3GPassword OBJECT-TYPE
			SYNTAX DisplayString
			MAX-ACCESS read-write
			STATUS current
			DESCRIPTION
				"The password appliled currently."
			::= { qtech3GDeviceManagementEntry 45 }

--  ===============================================
-- ADD new qtech3GTrapObject.
-- ===============================================

    qtech3GTrapNew OBJECT IDENTIFIER ::= { qtech3GMonitor 2 }

    qtech3GNotificationsNew OBJECT IDENTIFIER ::= { qtech3GTrapNew 1 }

    qtech3GLineDetectedNotification NOTIFICATION-TYPE
        OBJECTS {
                qtech3GRouterSN,
	            qtech3GCardIMSI,
                qtech3GIntfIPAddr,
		        qtech3GLineDetected,
        	    qtech3GLineDetectedResult,
        	    qtech3GLineDetectedMainCause,
		        qtech3GLineDetectedSubCause,
		        qtech3GDeviceBackupInfo,
		        qtech3GRssiStrength,
		        qtech3GDeviceBackupIMSI
        	  }
        STATUS current
        DESCRIPTION
            "This notification is generated when user detecting 3g line."
        ::= { qtech3GNotificationsNew 1 }


		-- 1.3.6.1.4.1.27514.1.1.10.2.95.2.1.2
		qtech3GUserUpLine NOTIFICATION-TYPE
			OBJECTS {
			        qtech3GRouterSlotNumber,
			        qtech3GCardIMSI,
			        qtech3GIntfIPAddr,
			        qtech3GTrafficPreventListName,
			        qtech3GTrafficPreventListID,
                                qtech3GTrafficPreventIfIndex,
                                qtech3GTrafficPreventMode,
                                qtech3GPppUsername,
                                qtech3GRouterSN,
                                qtech3GCardPhoneNumber,
                                qtech3GDailMode,
                                qtech3GDialOnDemandIfIndex,
                                qtech3GDeviceModemType
				}
			STATUS current
			DESCRIPTION
				"This notification is generated when 4G user up line."
			::= { qtech3GNotificationsNew 2 }


		-- 1.3.6.1.4.1.27514.1.1.10.2.95.2.1.3
		qtech3GUserDownLine NOTIFICATION-TYPE
			OBJECTS {
			        qtech3GRouterSlotNumber,
			        qtech3GCardIMSI,
			        qtech3GIntfIPAddr,
			        qtech3GTrafficPreventListName,
			        qtech3GTrafficPreventListID,
                                qtech3GTrafficPreventIfIndex,
                                qtech3GTrafficPreventMode,
                                qtech3GPppUsername, qtech3GRouterSN,
                                qtech3GCardPhoneNumber,
                                qtech3GDailMode,
                                qtech3GDialOnDemandIfIndex,
                                qtech3GDeviceModemType }
			STATUS current
			DESCRIPTION
				"This notification is generated when 4G user down line."
			::= { qtech3GNotificationsNew 3 }


		-- 1.3.6.1.4.1.27514.1.1.10.2.95.2.1.4
		qtech3GRssiNotification NOTIFICATION-TYPE
			OBJECTS {
			        qtech3GRouterSlotNumber,
			        qtech3GCardIMSI,
			        qtech3GRouterSN,
			        qtech3GIntfIPAddr,
			        qtech3GRssiStrengthPercent,
				qtech3GRssiStrength,
				qtech3GDeviceModemType
			}
			STATUS current
			DESCRIPTION
				"This notification is generated when 4G signal is lower
				than the specific threshold value."
			::= { qtech3GNotificationsNew 4 }


		-- 1.3.6.1.4.1.27514.1.1.10.2.95.2.1.5
		qtech3GTrafficInfoNotification NOTIFICATION-TYPE
			OBJECTS {
			        qtech3GRouterSlotNumber,
			        qtech3GCardIMSI,
			        qtech3GRouterSN,
			        qtech3GIntfIPAddr,
			        qtech3GOutOctets,
				    qtech3GInOctets,
				    qtech3GDeviceModemType,
				    qtech3GLineCardType,
				    qtech3GModemIMEI,
				    qtech3GCardPhoneNumber,
                    qtech3GDeviceBackupInfo,
                    qtech3GRssiStrength,
                    qtech3GRssiStrengthPercent,
                    qtech3GNetworkISPMode,
				    qtech3GNetworkSysMode,
				    qtech3GSIMCardStatus,
				    qtech3GDailMode,
				    qtech3GPppUsername,
				    qtech3GUserActiveTime,
				    qtech3GAcessBSCellID,
				    qtech3GAcessBSLAC,
				    qtech3GAcessBSLONG,
				    qtech3GAcessBSLAT,
				    qtech3GInSpeed,
				    qtech3GOutSpeed,
				    qtech3G2ifIndex,
				    qtech3GTrafficTrapInterval,
				    qtech3GRssiThreshold,
				    qtech3GTrapFilterMode,
				    qtech3GISPtimeout
				    }
			STATUS current
			DESCRIPTION
				"This notification is used for reporting the traffic information of 4G user regularly. "
			::= { qtech3GNotificationsNew 5 }


		-- 1.3.6.1.4.1.27514.1.1.10.2.95.2.1.6
		qtech3GBackupMaster NOTIFICATION-TYPE
			OBJECTS {
			        qtech3GRouterSlotNumber,
			        qtech3GCardIMSI,
			        qtech3GIntfIPAddr,
			        qtech3GTrafficPreventListName,
			        qtech3GTrafficPreventListID,
				    qtech3GTrafficPreventIfIndex,
				    qtech3GTrafficPreventMode,
                    qtech3GPppUsername,
                    qtech3GRouterSN,
                    qtech3GCardPhoneNumber,
                    qtech3GDailMode,
                    qtech3GDialOnDemandIfIndex,
                    qtech3GDeviceModemType
                    }
			STATUS current
			DESCRIPTION
				"This notification is generated when 4G is switching to master line."
			::= { qtech3GNotificationsNew 6 }


		-- 1.3.6.1.4.1.27514.1.1.10.2.95.2.1.7
		qtech3GBackupSlave NOTIFICATION-TYPE
			OBJECTS {
			        qtech3GRouterSlotNumber,
			        qtech3GCardIMSI,
			        qtech3GIntfIPAddr,
			        qtech3GTrafficPreventListName,
			        qtech3GTrafficPreventListID,
				    qtech3GTrafficPreventIfIndex,
				    qtech3GTrafficPreventMode,
				    qtech3GPppUsername,
				    qtech3GRouterSN,
				    qtech3GCardPhoneNumber,
				    qtech3GDailMode,
				    qtech3GDialOnDemandIfIndex,
				    qtech3GDeviceModemType }
			STATUS current
			DESCRIPTION
				"This notification is generated when 4G is switching to slave line."
			::= { qtech3GNotificationsNew 7 }

	END

--
-- QTECH-3G-MIB.mib
--
