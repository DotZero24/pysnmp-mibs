-- *****************************************************************
-- QTECH-NFPP-MIB.mib:  Qtech NFPP MIB file
--
-- July 2009, yuhuabing
--
-- Copyright (c) 2009 by Qtech Networks Co.,Ltd.
-- All rights reserved.
--
-- *****************************************************************
--

QTECH-NFPP-MIB DEFINITIONS ::= BEGIN

IMPORTS
        MODULE-IDENTITY,
        OBJECT-TYPE,
        NOTIFICATION-TYPE
                FROM SNMPv2-SMI
        MODULE-COMPLIANCE,
        OBJECT-GROUP,
        NOTIFICATION-GROUP
                FROM SNMPv2-CONF
        qtechMgmt
                FROM QTECH-SMI;

qtechNFPPMIB MODULE-IDENTITY
        LAST-UPDATED "200907090000Z"
        ORGANIZATION "Qtech Networks Co.,Ltd."
        CONTACT-INFO
                "
                Tel: 4008-111-000

                E-mail: service@qtech.com.cn"
        DESCRIPTION
                "This module defines qtech NFPP mibs."
        REVISION      "200907090000Z"
        DESCRIPTION
                "Initial version of this MIB module."
        ::= { qtechMgmt 43}

qtechNFPPMIBObjects OBJECT IDENTIFIER ::= { qtechNFPPMIB 1 }

  qtechNFPPMessageContent OBJECT-TYPE
          SYNTAX OCTET STRING(SIZE(0..512))
          MAX-ACCESS accessible-for-notify
          STATUS current
          DESCRIPTION
            "NFPP Message Content"
          ::= { qtechNFPPMIBObjects 0}

-- notifications

qtechNFPPMIBNotificationPrefix OBJECT IDENTIFIER ::= { qtechNFPPMIB 2 }
qtechNFPPMIBNotifications OBJECT IDENTIFIER ::= { qtechNFPPMIBNotificationPrefix 0 }

qtechNFPPMessageGenerated NOTIFICATION-TYPE
	OBJECTS   {qtechNFPPMessageContent}
	STATUS	   current
	DESCRIPTION
	       "When NFPP Event Occur, this message is Generated."
	::= { qtechNFPPMIBNotifications 1 }


qtechNFPPMIBConformance OBJECT IDENTIFIER ::= { qtechNFPPMIB 3}
qtechNFPPMIBCompliances OBJECT IDENTIFIER ::= { qtechNFPPMIBConformance 1 }
qtechNFPPMIBGroups      OBJECT IDENTIFIER ::= { qtechNFPPMIBConformance 2 }

-- compliance statements

qtechNFPPMIBCompliance MODULE-COMPLIANCE
        STATUS  current
        DESCRIPTION
                "The compliance statement for entities which implement
                the Qtech NFPP MIB"
        MODULE  -- this module
                MANDATORY-GROUPS {
                        qtechNFPPNotifObjectsGroup,
                        qtechNFPPNotificationsGroup
                 }
         ::= { qtechNFPPMIBCompliances 1 }

-- units of conformance

qtechNFPPNotifObjectsGroup OBJECT-GROUP
       OBJECTS {
           qtechNFPPMessageContent
       }
       STATUS  current
       DESCRIPTION
                "A collection of objects that specify information for
                 TRIP notifications."
       ::= { qtechNFPPMIBGroups 1 }

qtechNFPPNotificationsGroup NOTIFICATION-GROUP
        NOTIFICATIONS {
               qtechNFPPMessageGenerated
        }
        STATUS        current
        DESCRIPTION
              "A collection of NFPP traps."
      ::= { qtechNFPPMIBGroups 2 }

END
