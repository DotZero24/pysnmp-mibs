-- *****************************************************************
-- QTECH-CAPWAP-SERVER-MIB.mib:  Qtech Capwap Server MIB file
--
-- Aug 2010, xueweiwen
--
-- Copyright (c) 2010 by Qtech Networks Co.,Ltd.
-- All rights reserved.
--
-- *****************************************************************
--

QTECH-CAPWAP-SERVER-MIB DEFINITIONS ::= BEGIN

IMPORTS
    MODULE-IDENTITY,
    OBJECT-TYPE,
    Counter32,
    Unsigned32,
    IpAddress
            FROM SNMPv2-SMI
    InetAddressType,
    InetAddress
            FROM INET-ADDRESS-MIB
    DisplayString,
    RowStatus
            FROM SNMPv2-TC
    MODULE-COMPLIANCE,
    OBJECT-GROUP
            FROM SNMPv2-CONF
    qtechMgmt
            FROM QTECH-SMI;

qtechCapwapSvrMIB MODULE-IDENTITY
    LAST-UPDATED "201008240000Z"
    ORGANIZATION "Qtech Networks Co.,Ltd."
    CONTACT-INFO
           "
           Tel: 4008-111-000

           E-mail: service@qtech.com.cn"
    DESCRIPTION
           "This module defines qtech capwap server mibs."
    REVISION      "201008240000Z"
    DESCRIPTION
           "Initial version of this MIB module."
    ::= { qtechMgmt 89 }


qtechCapwapSvrMIBObjects OBJECT IDENTIFIER ::= { qtechCapwapSvrMIB 1 }


-- capwap server white list url
qtechCapwapSvrWhiteListURLTable OBJECT-TYPE
    SYNTAX  SEQUENCE OF QtechCapwapSvrWhiteListURLEntry
    MAX-ACCESS  not-accessible
    STATUS  current
    DESCRIPTION
        "The table of Capwap server white list URL Info."
    ::= { qtechCapwapSvrMIBObjects 1 }

qtechCapwapSvrWhiteListURLEntry OBJECT-TYPE
    SYNTAX  QtechCapwapSvrWhiteListURLEntry
    MAX-ACCESS  not-accessible
    STATUS  current
    DESCRIPTION
        "The entry of Capwap server white list URL info table."
    INDEX   { qtechCapwapSvrWhiteListIndex }
    ::= { qtechCapwapSvrWhiteListURLTable 1 }

QtechCapwapSvrWhiteListURLEntry ::=
    SEQUENCE {
        qtechCapwapSvrWhiteListIndex            Unsigned32,
        qtechCapwapSvrWhiteListURL              DisplayString,
        qtechCapwapSvrWhiteListURLParserStatus  DisplayString,
        qtechCapwapSvrWhiteListURLRowStatus     RowStatus
    }

qtechCapwapSvrWhiteListIndex OBJECT-TYPE
    SYNTAX       Unsigned32
    MAX-ACCESS   read-only
    STATUS       current
    DESCRIPTION
        "The index of the Capwap server white list url."
    ::= { qtechCapwapSvrWhiteListURLEntry 1 }

qtechCapwapSvrWhiteListURL OBJECT-TYPE
    SYNTAX       DisplayString (SIZE (0..255))
    MAX-ACCESS   read-create
    STATUS       current
    DESCRIPTION
        "The URL of the Capwap server white list."
    ::= { qtechCapwapSvrWhiteListURLEntry 2 }

qtechCapwapSvrWhiteListURLParserStatus OBJECT-TYPE
    SYNTAX       DisplayString (SIZE (0..255))
    MAX-ACCESS   read-only
    STATUS       current
    DESCRIPTION
        "The URL parser status of the Capwap server white list."
    ::= { qtechCapwapSvrWhiteListURLEntry 3 }

qtechCapwapSvrWhiteListURLRowStatus OBJECT-TYPE
    SYNTAX       RowStatus
    MAX-ACCESS   read-create
    STATUS       current
    DESCRIPTION
        "The RowStatus of the Capwap server white list URL table."
    ::= { qtechCapwapSvrWhiteListURLEntry 4 }


-- capwap server white list ip
qtechCapwapSvrWhiteListIPTable OBJECT-TYPE
    SYNTAX  SEQUENCE OF QtechCapwapSvrWhiteListIPEntry
    MAX-ACCESS  not-accessible
    STATUS  current
    DESCRIPTION
        "The table of Capwap server white list IP Info."
    ::= { qtechCapwapSvrMIBObjects 2 }

qtechCapwapSvrWhiteListIPEntry OBJECT-TYPE
    SYNTAX  QtechCapwapSvrWhiteListIPEntry
    MAX-ACCESS  not-accessible
    STATUS  current
    DESCRIPTION
        "The entry of Capwap server white list IP info table."
    INDEX   { qtechCapwapSvrWhiteListIP }
    ::= { qtechCapwapSvrWhiteListIPTable 1 }

QtechCapwapSvrWhiteListIPEntry ::=
    SEQUENCE {
        qtechCapwapSvrWhiteListIP            IpAddress,
        qtechCapwapSvrWhiteListIPRowStatus   RowStatus
    }

qtechCapwapSvrWhiteListIP OBJECT-TYPE
    SYNTAX       IpAddress
    MAX-ACCESS   read-only
    STATUS       current
    DESCRIPTION
        "The IP of the Capwap server white list."
    ::= { qtechCapwapSvrWhiteListIPEntry 1 }

qtechCapwapSvrWhiteListIPRowStatus OBJECT-TYPE
    SYNTAX       RowStatus
    MAX-ACCESS   read-create
    STATUS       current
    DESCRIPTION
        "The RowStatus of the Capwap server white list IP table."
    ::= { qtechCapwapSvrWhiteListIPEntry 2 }


-- capwap server black list URL
qtechCapwapSvrBlackListURLTable OBJECT-TYPE
    SYNTAX  SEQUENCE OF QtechCapwapSvrBlackListURLEntry
    MAX-ACCESS  not-accessible
    STATUS  current
    DESCRIPTION
        "The table of Portal URL Info."
    ::= { qtechCapwapSvrMIBObjects 3 }

qtechCapwapSvrBlackListURLEntry OBJECT-TYPE
    SYNTAX  QtechCapwapSvrBlackListURLEntry
    MAX-ACCESS  not-accessible
    STATUS  current
    DESCRIPTION
        "The entry of Portal URL info table."
    INDEX   { qtechCapwapSvrBlackListIndex }
    ::= { qtechCapwapSvrBlackListURLTable 1 }

QtechCapwapSvrBlackListURLEntry ::=
    SEQUENCE {
        qtechCapwapSvrBlackListIndex            Unsigned32,
        qtechCapwapSvrBlackListURL              DisplayString,
        qtechCapwapSvrBlackListURLParserStatus  DisplayString,
        qtechCapwapSvrBlackListURLRowStatus     RowStatus
    }

qtechCapwapSvrBlackListIndex OBJECT-TYPE
    SYNTAX       Unsigned32
    MAX-ACCESS   read-only
    STATUS       current
    DESCRIPTION
        "The URL of the Capwap server black list."
    ::= { qtechCapwapSvrBlackListURLEntry 1 }

qtechCapwapSvrBlackListURL OBJECT-TYPE
    SYNTAX       DisplayString (SIZE (0..255))
    MAX-ACCESS   read-create
    STATUS       current
    DESCRIPTION
        "The URL of the Capwap server black list."
    ::= { qtechCapwapSvrBlackListURLEntry 2 }

qtechCapwapSvrBlackListURLParserStatus OBJECT-TYPE
    SYNTAX       DisplayString (SIZE (0..255))
    MAX-ACCESS   read-only
    STATUS       current
    DESCRIPTION
        "The URL parser status of the Capwap server black list."
    ::= { qtechCapwapSvrBlackListURLEntry 3 }

qtechCapwapSvrBlackListURLRowStatus OBJECT-TYPE
    SYNTAX       RowStatus
    MAX-ACCESS   read-create
    STATUS       current
    DESCRIPTION
        "The RowStatus of the Capwap server black list IP table."
    ::= { qtechCapwapSvrBlackListURLEntry 4 }


-- capwap server black list ip
qtechCapwapSvrBlackListIPTable OBJECT-TYPE
    SYNTAX  SEQUENCE OF QtechCapwapSvrBlackListIPEntry
    MAX-ACCESS  not-accessible
    STATUS  current
    DESCRIPTION
        "The table of Capwap server black list IP Info."
    ::= { qtechCapwapSvrMIBObjects 4 }

qtechCapwapSvrBlackListIPEntry OBJECT-TYPE
    SYNTAX  QtechCapwapSvrBlackListIPEntry
    MAX-ACCESS  not-accessible
    STATUS  current
    DESCRIPTION
        "The entry of Capwap server black list IP info table."
    INDEX   { qtechCapwapSvrBlackListIP }
    ::= { qtechCapwapSvrBlackListIPTable 1 }

QtechCapwapSvrBlackListIPEntry ::=
    SEQUENCE {
        qtechCapwapSvrBlackListIP            IpAddress,
        qtechCapwapSvrBlackListIPRowStatus   RowStatus
    }

qtechCapwapSvrBlackListIP OBJECT-TYPE
    SYNTAX       IpAddress
    MAX-ACCESS   read-only
    STATUS       current
    DESCRIPTION
        "The IP of the Capwap server black list."
    ::= { qtechCapwapSvrBlackListIPEntry 1 }

qtechCapwapSvrBlackListIPRowStatus OBJECT-TYPE
    SYNTAX       RowStatus
    MAX-ACCESS   read-create
    STATUS       current
    DESCRIPTION
        "The RowStatus of the Capwap server black list IP table."
    ::= { qtechCapwapSvrBlackListIPEntry 2 }


-- capwap server black list port
qtechCapwapSvrBlackListPortTable OBJECT-TYPE
    SYNTAX  SEQUENCE OF QtechCapwapSvrBlackListPortEntry
    MAX-ACCESS  not-accessible
    STATUS  current
    DESCRIPTION
        "The table of Capwap server black list port Info."
    ::= { qtechCapwapSvrMIBObjects 5 }

qtechCapwapSvrBlackListPortEntry OBJECT-TYPE
    SYNTAX  QtechCapwapSvrBlackListPortEntry
    MAX-ACCESS  not-accessible
    STATUS  current
    DESCRIPTION
        "The entry of Capwap server black list port info table."
    INDEX   { qtechCapwapSvrBlackListPort }
    ::= { qtechCapwapSvrBlackListPortTable 1 }

QtechCapwapSvrBlackListPortEntry ::=
    SEQUENCE {
        qtechCapwapSvrBlackListPort            INTEGER,
        qtechCapwapSvrBlackListPortRowStatus   RowStatus
    }

qtechCapwapSvrBlackListPort OBJECT-TYPE
    SYNTAX       INTEGER
    MAX-ACCESS   read-only
    STATUS       current
    DESCRIPTION
        "The port of the Capwap server black list."
    ::= { qtechCapwapSvrBlackListPortEntry 1 }

qtechCapwapSvrBlackListPortRowStatus OBJECT-TYPE
    SYNTAX       RowStatus
    MAX-ACCESS   read-create
    STATUS       current
    DESCRIPTION
        "The RowStatus of the Capwap server black list port table."
    ::= { qtechCapwapSvrBlackListPortEntry 2 }


---
---compliance statements
---
qtechCapwapSvrMIBConformance OBJECT IDENTIFIER ::= { qtechCapwapSvrMIB 2 }
qtechCapwapSvrMIBCompliances OBJECT IDENTIFIER ::= { qtechCapwapSvrMIBConformance 1 }
qtechCapwapSvrMIBGroups      OBJECT IDENTIFIER ::= { qtechCapwapSvrMIBConformance 2 }

qtechCapwapSvrMIBCompliance MODULE-COMPLIANCE
   STATUS  current
   DESCRIPTION
   			"The compliance statement for entities which implement
       	 the capwapServer MIB"
   MODULE
   GROUP qtechCapwapSvrMIBGroup
 	 DESCRIPTION
        "This group is mandatory only for those system which support
         capwapServer function."
   ::= { qtechCapwapSvrMIBCompliances 1 }

qtechCapwapSvrMIBGroup OBJECT-GROUP
   OBJECTS {
        qtechCapwapSvrWhiteListURL,
        qtechCapwapSvrWhiteListURLParserStatus,
        qtechCapwapSvrWhiteListURLRowStatus,
        qtechCapwapSvrWhiteListIP,
        qtechCapwapSvrWhiteListIPRowStatus,
        qtechCapwapSvrBlackListURL,
        qtechCapwapSvrBlackListURLParserStatus,
        qtechCapwapSvrBlackListURLRowStatus,
        qtechCapwapSvrBlackListIP,
        qtechCapwapSvrBlackListIPRowStatus,
        qtechCapwapSvrBlackListPort,
        qtechCapwapSvrBlackListPortRowStatus
      }
   STATUS  deprecated
   DESCRIPTION
         "The basic collection of objects providing management of capwapServer management."
   ::= { qtechCapwapSvrMIBGroups 1 }

END
