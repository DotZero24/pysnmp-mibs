-- *****************************************************************
-- QTECH-TRAP-FORMAT-MIB.mib:  Qtech TRAP FORMAT MIB file
--
-- May 2011, Panshiyong
--
-- Copyright(c) 2011 by Qtech Networks Co.,Ltd.
-- All rights reserved.
--
-- *****************************************************************
--

QTECH-TRAP-FORMAT-MIB DEFINITIONS ::= BEGIN

IMPORTS
        MODULE-IDENTITY,
        OBJECT-TYPE,
        TimeTicks,
        Unsigned32,
        IpAddress
                FROM SNMPv2-SMI
        Counter
                FROM RFC1155-SMI
        DisplayString
                FROM SNMPv2-TC
        MODULE-COMPLIANCE,
        OBJECT-GROUP
                FROM SNMPv2-CONF
        qtechMgmt
                FROM QTECH-SMI;

qtechTrapFormatMIB MODULE-IDENTITY
        LAST-UPDATED "201105110000Z"
        ORGANIZATION "Qtech Networks Co.,Ltd."
        CONTACT-INFO
                "
                Tel: 4008-111-000

                E-mail: service@qtech.com.cn"
        DESCRIPTION
                "This module defines qtech trap-format mibs."
        REVISION      "201105110000Z"
        DESCRIPTION
                "Initial version of this MIB module."
        ::= { qtechMgmt 97 }


qtechTrapFormatMIBObjects OBJECT IDENTIFIER ::= { qtechTrapFormatMIB 1 }


--**********************************************************************
-- qtech Trap Format MIB info
--**********************************************************************
qtechTrapFormatTrapSerialNo OBJECT-TYPE
    SYNTAX DisplayString(SIZE (1..32))
    MAX-ACCESS read-only
    STATUS current
    DESCRIPTION
        "Serial NO. of trap informations."
    ::= { qtechTrapFormatMIBObjects 1 }

qtechTrapFormatTrapLevel OBJECT-TYPE
    SYNTAX DisplayString(SIZE (1..32))
    MAX-ACCESS read-only
    STATUS current
    DESCRIPTION
        "Original level of trap informations:
         1 - critical,
         2 - major,
         3 - minor,
         4 - normal,
         5 - uncertain.
        "
    ::= { qtechTrapFormatMIBObjects 2 }

qtechTrapFormatTrapType OBJECT-TYPE
    SYNTAX DisplayString(SIZE (1..32))
    MAX-ACCESS read-only
    STATUS current
    DESCRIPTION
        "Original type of trap informations:
         1 - Communication Trap,
         2 - Environment Trap,
         3 - Device Trap,
         4 - Process Error Trap,
         5 - Quality of Service Trap.
        "
    ::= { qtechTrapFormatMIBObjects 3 }

qtechTrapFormatTrapReasonNo OBJECT-TYPE
    SYNTAX INTEGER
    MAX-ACCESS read-only
    STATUS current
    DESCRIPTION
        "Reason NO. of trap informations."
    ::= { qtechTrapFormatMIBObjects 4 }

qtechTrapFormatTrapReasons OBJECT-TYPE
    SYNTAX DisplayString(SIZE (1..64))
    MAX-ACCESS read-only
    STATUS current
    DESCRIPTION
        "Reasons of trap informations."
    ::= { qtechTrapFormatMIBObjects 5 }

qtechTrapFormatTrapStatus OBJECT-TYPE
    SYNTAX INTEGER
    MAX-ACCESS read-only
    STATUS current
    DESCRIPTION
        "Status of trap informations:
         1 - active,
         0 - eliminate.
        "
    ::= { qtechTrapFormatMIBObjects 6 }

qtechTrapFormatTrapTitle OBJECT-TYPE
    SYNTAX DisplayString(SIZE (1..64))
    MAX-ACCESS read-only
    STATUS current
    DESCRIPTION
        "Title of trap informations."
    ::= { qtechTrapFormatMIBObjects 7 }

qtechTrapFormatTrapContent OBJECT-TYPE
    SYNTAX DisplayString(SIZE (1..64))
    MAX-ACCESS read-only
    STATUS current
    DESCRIPTION
        "Content of trap informations."
    ::= { qtechTrapFormatMIBObjects 8 }

qtechTrapFormatTrapTime OBJECT-TYPE
    SYNTAX Counter
    MAX-ACCESS read-only
    STATUS current
    DESCRIPTION
        "The time (in seconds) since the trap alarm occurred
         of the system was last re-initialized."
    ::= { qtechTrapFormatMIBObjects 9 }

qtechTrapFormatTrapSlotInfo OBJECT-TYPE
    SYNTAX DisplayString
    MAX-ACCESS read-only
    STATUS current
    DESCRIPTION
        "The slot info(1/2 or 2) of slot that send trap."
    ::= { qtechTrapFormatMIBObjects 10 }


--**********************************************************************
-- about conformance info
--**********************************************************************
qtechTrapFormatMIBConformance OBJECT IDENTIFIER ::= { qtechTrapFormatMIB 2 }
qtechTrapFormatMIBCompliances OBJECT IDENTIFIER ::= { qtechTrapFormatMIBConformance 1 }
qtechTrapFormatMIBGroups      OBJECT IDENTIFIER ::= { qtechTrapFormatMIBConformance 2 }

-- compliance statements
qtechTrapFormatMIBCompliance MODULE-COMPLIANCE
    STATUS  current
    DESCRIPTION
        "The compliance statement for entities which implement
         the Qtech Trap Format MIB"
    MODULE
    MANDATORY-GROUPS {
        qtechTrapFormatMIBGroup
    }
    ::= { qtechTrapFormatMIBCompliances 1 }

-- units of conformance
qtechTrapFormatMIBGroup OBJECT-GROUP
        OBJECTS {
            qtechTrapFormatTrapSerialNo,
            qtechTrapFormatTrapLevel,
            qtechTrapFormatTrapType,
            qtechTrapFormatTrapReasonNo,
            qtechTrapFormatTrapReasons,
            qtechTrapFormatTrapStatus,
            qtechTrapFormatTrapTitle,
            qtechTrapFormatTrapContent,
            qtechTrapFormatTrapTime,
			qtechTrapFormatTrapSlotInfo
        }
        STATUS  current
        DESCRIPTION
                "A collection of objects providing Capwap App configure."
        ::= { qtechTrapFormatMIBGroups 1 }

END
