-- *****************************************************************
-- QTECH-FIBER-MIB.mib:  Qtech FIBER MIB file
--
-- January 2012, wangyouliang
--
-- Copyright (c) 2012 by Qtech Networks Co.,Ltd.
-- All rights reserved.
--
-- *****************************************************************
--

QTECH-FIBER-MIB DEFINITIONS ::= BEGIN

IMPORTS
        MODULE-IDENTITY,
        OBJECT-TYPE
                FROM SNMPv2-SMI
        TruthValue,
        DisplayString
                FROM SNMPv2-TC
        MODULE-COMPLIANCE,
        OBJECT-GROUP
                FROM SNMPv2-CONF
        IfIndex
                FROM QTECH-TC
        qtechMgmt
                FROM QTECH-SMI;

qtechFiberMIB MODULE-IDENTITY
        LAST-UPDATED "201111280000Z"
        ORGANIZATION "Qtech Networks Co.,Ltd."
        CONTACT-INFO
                "
                Tel: 4008-111-000

                E-mail: service@qtech.com.cn"
        DESCRIPTION
                "This module defines qtech fiber module information mibs."
        REVISION      "201111280000Z"
        DESCRIPTION
                "Initial version of this MIB module."
        ::= { qtechMgmt 105}

qtechFiberMIBObjects OBJECT IDENTIFIER ::= { qtechFiberMIB 1 }


-- ---------------------------------------------------------- --
-- A table for getting Fiber port information.
-- ---------------------------------------------------------- --
qtechFiberTable OBJECT-TYPE
        SYNTAX SEQUENCE OF QtechFiberEntry
        MAX-ACCESS not-accessible
        STATUS current
        DESCRIPTION
            "A table for getting Fiber Module information"
        ::= { qtechFiberMIBObjects 1 }

qtechFiberEntry OBJECT-TYPE
        SYNTAX QtechFiberEntry
        MAX-ACCESS not-accessible
        STATUS current
        DESCRIPTION
            "Entry of a Fiber Module information."
        INDEX { qtechFiberPortIndex }
        ::= { qtechFiberTable 1 }

QtechFiberEntry ::=
        SEQUENCE {
                qtechFiberPortIndex IfIndex,
                qtechFiberPortDescr DisplayString,
                qtechFiberTransceiverType INTEGER,
                qtechFiberConnectorType INTEGER,
                qtechFiberWavelength INTEGER,
                qtechFiberTransferDistanceSMF INTEGER,
                qtechFiberTransferDistance62point5umOM1 INTEGER,
                qtechFiberTransferDistance62point5um INTEGER,
                qtechFiberTransferDistance50umOM2 INTEGER,
                qtechFiberTransferDistance50um INTEGER,
                qtechFiberTransferDistance50umOM3 INTEGER,
                qtechFiberTransferDistanceEBW50um INTEGER,
                qtechFiberTransferDistanceCopper INTEGER,
                qtechFiberTransferDistanceCableAssembly INTEGER,
                qtechFiberDDMSupportStatus TruthValue,
                qtechFiberSerialNumber DisplayString,
                qtechFiberTemp INTEGER,
                qtechFiberTempStatus INTEGER,
                qtechFiberVoltage INTEGER,
                qtechFiberVoltageStatus INTEGER,
                qtechFiberBias INTEGER,
                qtechFiberBiasStatus INTEGER,
                qtechFiberChannel1Bias INTEGER,
                qtechFiberChannel1BiasStatus INTEGER,
                qtechFiberChannel2Bias INTEGER,
                qtechFiberChannel2BiasStatus INTEGER,
                qtechFiberChannel3Bias INTEGER,
                qtechFiberChannel3BiasStatus INTEGER,
                qtechFiberChannel4Bias INTEGER,
                qtechFiberChannel4BiasStatus INTEGER,
                qtechFiberRXpowerIntegerpart INTEGER,
                qtechFiberRXpowerDecimalpart INTEGER,
                qtechFiberRXpowertype INTEGER,
                qtechFiberRXpowerStatus INTEGER,
                qtechFiberChannel1RXpowerIntegerpart INTEGER,
                qtechFiberChannel1RXpowerDecimalpart INTEGER,
                qtechFiberChannel1RXpowertype INTEGER,
                qtechFiberChannel1RXpowerStatus INTEGER,
                qtechFiberChannel2RXpowerIntegerpart INTEGER,
                qtechFiberChannel2RXpowerDecimalpart INTEGER,
                qtechFiberChannel2RXpowertype INTEGER,
                qtechFiberChannel2RXpowerStatus INTEGER,
                qtechFiberChannel3RXpowerIntegerpart INTEGER,
                qtechFiberChannel3RXpowerDecimalpart INTEGER,
                qtechFiberChannel3RXpowertype INTEGER,
                qtechFiberChannel3RXpowerStatus INTEGER,
                qtechFiberChannel4RXpowerIntegerpart INTEGER,
                qtechFiberChannel4RXpowerDecimalpart INTEGER,
                qtechFiberChannel4RXpowertype INTEGER,
                qtechFiberChannel4RXpowerStatus INTEGER,
                qtechFiberTXpowerIntegerpart INTEGER,
                qtechFiberTXpowerDecimalpart INTEGER,
                qtechFiberTXpowerStatus INTEGER,
                qtechFiberChannel1TXpowerIntegerpart INTEGER,
                qtechFiberChannel1TXpowerDecimalpart INTEGER,
                qtechFiberChannel1TXpowerStatus INTEGER,
                qtechFiberChannel2TXpowerIntegerpart INTEGER,
                qtechFiberChannel2TXpowerDecimalpart INTEGER,
                qtechFiberChannel2TXpowerStatus INTEGER,
                qtechFiberChannel3TXpowerIntegerpart INTEGER,
                qtechFiberChannel3TXpowerDecimalpart INTEGER,
                qtechFiberChannel3TXpowerStatus INTEGER,
                qtechFiberChannel4TXpowerIntegerpart INTEGER,
                qtechFiberChannel4TXpowerDecimalpart INTEGER,
                qtechFiberChannel4TXpowerStatus INTEGER
        }

qtechFiberPortIndex OBJECT-TYPE
        SYNTAX IfIndex
        MAX-ACCESS not-accessible
        STATUS current
        DESCRIPTION
            "Port index of the port."
        ::= { qtechFiberEntry 1 }

qtechFiberPortDescr OBJECT-TYPE
        SYNTAX DisplayString (SIZE(1..32))
        MAX-ACCESS read-only
        STATUS current
        DESCRIPTION
            "Discription of the port."
        ::= { qtechFiberEntry 2 }

qtechFiberTransceiverType OBJECT-TYPE
        SYNTAX INTEGER {
            unknown(1),
            fiber100BASEGTSFP(2),
            fiber100BASESXSFP(3),
            fiber100BASELXSFP(4),
            fiber100BASELHSFP(5),
	    fiber100BASEZXSFP(6),
            fiber100CopperSFP(7),
            fiber1000BASEGTSFP(8),
            fiber1000BASESXSFP(9),
            fiber1000BASELXSFP(10),
            fiber1000BASELHSFP(11),
	    fiber1000BASEZXSFP(12),
            fiber1000CopperSFP(13),
            fiber10GCopperSFPPlus(14),
            fiber10GBASESRSFPPlus(15),
            fiber10GBASELRSFPPlus(16),
            fiber10GBASEERSFPPlus(17),
            fiber10GBASEZRSFPPlus(18),
            fiber10GCopperXFP(19),
            fiber10GBASESRXFP(20),
            fiber10GBASELRXFP(21),
            fiber10GBASEERXFP(22),
            fiber10GBASEZRXFP(23),
            fiber40GActiveCableQSFPPlus(24),
            fiber40GLR4QSFPPlus(25),
            fiber40GCopperQSFPPlus(26),
            fiber40GSR4QSFPPlus(27),
            fiber2500CopperSFP(28)
        }
        MAX-ACCESS read-only
        STATUS current
        DESCRIPTION
            "Transceiver type of the Fiber module insered into the port."
        ::= { qtechFiberEntry 3 }

qtechFiberConnectorType OBJECT-TYPE
        SYNTAX INTEGER {
	    meaningless(0),
            unknownorunspecified(1),
            vendorspecific(2),
            sc(3),
            fiberChannelStyle1CopperConnector(4),
            fiberChannelStyle2CopperConnector(5),
            bncortnc(6),
            fiberChannelCoaxialHeaders(7),
            fiberJack(8),
            lc(9),
            mtrj(10),
            mu(11),
            sg(12),
            opticalPigtail(13),
            hssdcII(14),
            copperPigtail(15),
	    mpo(16),
	    rj45(17),
            noSparableConnector(18)
        }
        MAX-ACCESS read-only
        STATUS current
        DESCRIPTION
            "Connector type of the Fiber module insered into the port.
	     If the transceiver type of Fiber module is unknown(1), then this
             object contains a zero value."
        ::= { qtechFiberEntry 4 }

qtechFiberWavelength OBJECT-TYPE
        SYNTAX INTEGER
        MAX-ACCESS read-only
        STATUS current
        DESCRIPTION
            "The value of wavelength of the Fiber module insered into the port.
	     If the transceiver type of Fiber module is either fiber100CopperSFP(7)
	     or fiber1000CopperSFP(13) (or fiber10GCopperSFPPlus(14),
	     or fiber10GCopperXFP(19), or fiber40GCopperQSFPPlus(26), or fiber2500CopperSFP(28), or unknown(1)), then this
             object contains a zero value."
        ::= { qtechFiberEntry 5 }

qtechFiberTransferDistanceSMF OBJECT-TYPE
        SYNTAX INTEGER
        MAX-ACCESS read-only
        STATUS current
        DESCRIPTION
            "The value of transfer distance of the Fiber module insered into the port.
	     This value specifies the link length that is supported by the
	     transceiver while operating in compliance with the applicable
	     standards using single mode fiber for. The value is in units of kilometers.
	     A value of zero means that the transceiver does not support single mode fiber."
        ::= { qtechFiberEntry 6 }

qtechFiberTransferDistance62point5umOM1 OBJECT-TYPE
        SYNTAX INTEGER
        MAX-ACCESS read-only
        STATUS current
        DESCRIPTION
            "The value of transfer distance of the Fiber module insered into the port.
	     This value specifies the link length that is supported by the
	     transceiver while operating in compliance with the applicable
	     standards using 62.5 micron multimode (200 MHz*Km at 850 nm, 500 MHz*Km
	     at 1310 nm) fiber. The value is in units of meters.
	     A value of zero means that the transceiver does not
	     support 62.5 micron multimode fiber or the Fiber module type
	     is neither SFP/SFP+ nor QSFP+."
        ::= { qtechFiberEntry 7 }

qtechFiberTransferDistance62point5um OBJECT-TYPE
        SYNTAX INTEGER
        MAX-ACCESS read-only
        STATUS current
        DESCRIPTION
            "The value of transfer distance of the Fiber module insered into the port.
	     This value specifies the link length that is supported by the
	     transceiver while operating in compliance with the applicable
	     standards using 62.5 micron core multimode (200 MHz*Km at 850 nm, 500 MHz*Km
	     at 1310 nm) fiber. The value is in units of meters.
	     A value of zero means that the transceiver does not
	     support 62.5 micron multimode fiber or the Fiber module type is not XFP."
        ::= { qtechFiberEntry 8 }

qtechFiberTransferDistance50umOM2 OBJECT-TYPE
        SYNTAX INTEGER
        MAX-ACCESS read-only
        STATUS current
        DESCRIPTION
            "The value of transfer distance of the Fiber module insered into the port.
	     This value specifies the link length that is supported by the
	     transceiver while operating in compliance with the applicable
	     standards using 50 micron multimode (500 MHz*Km at 850 nm for SFP module
	     or at 850 nm and 1310 nm for QSFP+ module) fiber. The value is in units of meters.
	     A value of zero means that the transceiver does not
	     support 50 micron multimode fiber or the Fiber module type
	     is neither SFP/SFP+ nor QSFP+."
        ::= { qtechFiberEntry 9 }

qtechFiberTransferDistance50um OBJECT-TYPE
        SYNTAX INTEGER
        MAX-ACCESS read-only
        STATUS current
        DESCRIPTION
            "The value of transfer distance of the Fiber module insered into the port.
	     This value specifies the link length that is supported by the
	     transceiver while operating in compliance with the applicable
	     standards using 50 micron core multimode (500 MHz*Km at 850 nm and 1310 nm) fiber.
	     The value is in units of meters.
	     A value of zero means that the transceiver does not
	     support 50 micron core multimode fiber or the Fiber module type
	     is not XFP."
        ::= { qtechFiberEntry 10 }

qtechFiberTransferDistance50umOM3 OBJECT-TYPE
        SYNTAX INTEGER
        MAX-ACCESS read-only
        STATUS current
        DESCRIPTION
            "The value of transfer distance of the Fiber module insered into the port.
	     This value specifies the link length that is supported by the
	     transceiver while operating in compliance with the applicable
	     standards using 50 micron multimode OM3(2000 MHz*Km) fiber.
	     The value is in units of meters.
	     A value of zero means that the transceiver does not
	     support 50 micron multimode fiber or the Fiber module type
	     is neither SFP/SFP+ nor QSFP+."
        ::= { qtechFiberEntry 11 }

qtechFiberTransferDistanceEBW50um OBJECT-TYPE
        SYNTAX INTEGER
        MAX-ACCESS read-only
        STATUS current
        DESCRIPTION
            "The value of transfer distance of the Fiber module insered into the port.
	     This value specifies the link length that is supported by the
	     transceiver while operating in compliance with the applicable
	     standards using 2000 MHz*Km (850nm) extended bandwidth 50
	     micron core multimode fiber. The value is in units of meters.
	     A value of zero means that the transceiver does not support
	     extended bandwidth 50 micron multimode fiber or the Fiber module type is not XFP."
        ::= { qtechFiberEntry 12 }

qtechFiberTransferDistanceCopper OBJECT-TYPE
        SYNTAX INTEGER
        MAX-ACCESS read-only
        STATUS current
        DESCRIPTION
            "The value of transfer distance of the Fiber module insered into the port.
	     This value specifies the link length that is supported by the
	     transceiver while operating in compliance with the applicable
	     standards using copper cables. The value is in units of meters.
	     A value of zero means that the transceiver does not support copper cables
	     or the Fiber module type is neither SFP/SFP+ nor XFP."
        ::= { qtechFiberEntry 13 }

qtechFiberTransferDistanceCableAssembly OBJECT-TYPE
        SYNTAX INTEGER
        MAX-ACCESS read-only
        STATUS current
        DESCRIPTION
            "The value of transfer distance of the Fiber module insered into the port.
	     This value specifies the link length of the Cable assembly passive.
	     The value is in units of meters.
	     A value of zero means that the transceiver is not a cable assemblyor
	     or the Fiber module type is not QSFP+."
        ::= { qtechFiberEntry 14 }

qtechFiberDDMSupportStatus OBJECT-TYPE
        SYNTAX        TruthValue
        MAX-ACCESS    read-only
        STATUS        current
        DESCRIPTION
        "This object indicates that whether the Digital Diagnostic Monitors is implemeted."
    ::= { qtechFiberEntry 15 }

qtechFiberSerialNumber OBJECT-TYPE
        SYNTAX DisplayString (SIZE(1..32))
        MAX-ACCESS read-only
        STATUS current
        DESCRIPTION
            "The serial number of the Fiber module insered into the port."
        ::= { qtechFiberEntry 16 }

qtechFiberTemp OBJECT-TYPE
        SYNTAX INTEGER
        MAX-ACCESS read-only
        STATUS current
        DESCRIPTION
            "The temperature of the Fiber module insered into the port.
	    The value is in units of degrees Celsius.
	    If the qtechFiberDDMSupportStatus is false, the temperature value is 0."
        ::= { qtechFiberEntry 17 }

qtechFiberTempStatus OBJECT-TYPE
        SYNTAX INTEGER {
            unknown(1),
            ok(2),
            warning(3),
            alarm(4)
        }
        MAX-ACCESS read-only
        STATUS current
        DESCRIPTION
            "The status ok(2) indicates that the temperature of the Fiber module is in
	    the normal level. The status warning(3) indicates that the temperature of
	    the Fiber module exceeds high warning level or is below low warning level.
            The status alarm(4) indicates that the temperature of
	    the Fiber module exceeds high alarm level or is below low alarm level.
	    If the qtechFiberDDMSupportStatus is false or the Fiber module type is
	    neither SFP/SFP+ nor XFP(or not QSFP+), the status is unknown(1)."
        ::= { qtechFiberEntry 18 }

qtechFiberVoltage OBJECT-TYPE
        SYNTAX INTEGER
        MAX-ACCESS read-only
        STATUS current
        DESCRIPTION
            "The voltage of the Fiber module insered into the port.
	    The value is in units of mVolts.
	    If the qtechFiberDDMSupportStatus is false, the voltage value is 0."
        ::= { qtechFiberEntry 19 }

qtechFiberVoltageStatus OBJECT-TYPE
        SYNTAX INTEGER {
            unknown(1),
            ok(2),
            warning(3),
            alarm(4)
        }
        MAX-ACCESS read-only
        STATUS current
        DESCRIPTION
            "The status ok(2) indicates that the voltage of the Fiber module is in
	    the normal level. The status warning(3) indicates that the voltage of
	    the Fiber module exceeds high warning level or is below low warning level.
            The status alarm(4) indicates that the voltage of
	    the Fiber module exceeds high alarm level or is below low alarm level.
	    If the qtechFiberDDMSupportStatus is false or the Fiber module type is
	    neither SFP/SFP+ nor XFP(or not QSFP+), the status is unknown(1)."
        ::= { qtechFiberEntry 20 }

qtechFiberBias OBJECT-TYPE
        SYNTAX INTEGER
        MAX-ACCESS read-only
        STATUS current
        DESCRIPTION
            "The bias of the Fiber module insered into the port.
	    The value is in units of uA.
	    If the qtechFiberDDMSupportStatus is false or the Fiber module type is
	    neither SFP/SFP+ nor XFP, the bias value is 0."
        ::= { qtechFiberEntry 21 }

qtechFiberBiasStatus OBJECT-TYPE
        SYNTAX INTEGER {
            unknown(1),
            ok(2),
            warning(3),
            alarm(4)
        }
        MAX-ACCESS read-only
        STATUS current
        DESCRIPTION
            "The status ok(2) indicates that the bias of the Fiber module is in
	    the normal level. The status warning(3) indicates that the bias of
	    the Fiber module exceeds high warning level or is below low warning level.
            The status alarm(4) indicates that the bias of
	    the Fiber module exceeds high alarm level or is below low alarm level.
	    If the qtechFiberDDMSupportStatus is false or the Fiber module type is
	    neither SFP/SFP+ nor XFP, the status is unknown(1)."
        ::= { qtechFiberEntry 22 }

qtechFiberChannel1Bias OBJECT-TYPE
        SYNTAX INTEGER
        MAX-ACCESS read-only
        STATUS current
        DESCRIPTION
            "The bias in Channel 1 of the QSFP+ Fiber module insered into the port.
	    The value is in units of uA.
	    If the qtechFiberDDMSupportStatus is false or the Fiber module type is
	    not QSFP+, the bias value in Channel 1 is 0."
        ::= { qtechFiberEntry 23 }

qtechFiberChannel1BiasStatus OBJECT-TYPE
        SYNTAX INTEGER {
            unknown(1),
            ok(2),
            warning(3),
            alarm(4)
        }
        MAX-ACCESS read-only
        STATUS current
        DESCRIPTION
            "The status ok(2) indicates that the bias in the Channel 1 of QSFP+ is in
	    the normal level. The status warning(3) indicates
	    that the bias in the Channel 1 exceeds high warning level or is
	    below low warning level. The status alarm(4) indicates that the bias in
	    the Channel 1 exceeds high alarm level or is below low alarm level.
	    If the qtechFiberDDMSupportStatus is false or the Fiber module type is
	    not QSFP+, the status is unknown(1)."
        ::= { qtechFiberEntry 24 }

qtechFiberChannel2Bias OBJECT-TYPE
        SYNTAX INTEGER
        MAX-ACCESS read-only
        STATUS current
        DESCRIPTION
            "The bias in Channel 2 of the QSFP+ Fiber module insered into the port.
	    The value is in units of uA.
	    If the qtechFiberDDMSupportStatus is false or the Fiber module type is
	    not QSFP+, the bias value in Channel 2 is 0."
        ::= { qtechFiberEntry 25 }

qtechFiberChannel2BiasStatus OBJECT-TYPE
        SYNTAX INTEGER {
            unknown(1),
            ok(2),
            warning(3),
            alarm(4)
        }
        MAX-ACCESS read-only
        STATUS current
        DESCRIPTION
            "The status ok(2) indicates that the bias in the Channel 2 of QSFP+ is in
	    the normal level. The status warning(3) indicates
	    that the bias in the Channel 2 exceeds high warning level or is
	    below low warning level. The status alarm(4) indicates that the bias in
	    the Channel 2 exceeds high alarm level or is below low alarm level.
	    If the qtechFiberDDMSupportStatus is false or the Fiber module type is
	    not QSFP+, the status is unknown(1)."
        ::= { qtechFiberEntry 26 }

qtechFiberChannel3Bias OBJECT-TYPE
        SYNTAX INTEGER
        MAX-ACCESS read-only
        STATUS current
        DESCRIPTION
            "The bias in Channel 3 of the QSFP+ Fiber module insered into the port.
	    The value is in units of uA.
	    If the qtechFiberDDMSupportStatus is false or the Fiber module type is
	    not QSFP+, the bias value in Channel 3 is 0."
        ::= { qtechFiberEntry 27 }

qtechFiberChannel3BiasStatus OBJECT-TYPE
        SYNTAX INTEGER {
            unknown(1),
            ok(2),
            warning(3),
            alarm(4)
        }
        MAX-ACCESS read-only
        STATUS current
        DESCRIPTION
            "The status ok(2) indicates that the bias in the Channel 3 of QSFP+ is in
	    the normal level. The status warning(3) indicates
	    that the bias in the Channel 3 exceeds high warning level or is
	    below low warning level. The status alarm(4) indicates that the bias in
	    the Channel 3 exceeds high alarm level or is below low alarm level.
	    If the qtechFiberDDMSupportStatus is false or the Fiber module type is
	    not QSFP+, the status is unknown(1)."
        ::= { qtechFiberEntry 28 }

qtechFiberChannel4Bias OBJECT-TYPE
        SYNTAX INTEGER
        MAX-ACCESS read-only
        STATUS current
        DESCRIPTION
            "The bias in Channel 4 of the QSFP+ Fiber module insered into the port.
	    The value is in units of uA.
	    If the qtechFiberDDMSupportStatus is false or the Fiber module type is
	    not QSFP+, the bias value in Channel 4 is 0."
        ::= { qtechFiberEntry 29 }

qtechFiberChannel4BiasStatus OBJECT-TYPE
        SYNTAX INTEGER {
            unknown(1),
            ok(2),
            warning(3),
            alarm(4)
        }
        MAX-ACCESS read-only
        STATUS current
        DESCRIPTION
            "The status ok(2) indicates that the bias in the Channel 4 of QSFP+ is in
	    the normal level. The status warning(3) indicates
	    that the bias in the Channel 4 exceeds high warning level or is
	    below low warning level. The status alarm(4) indicates that the bias in
	    the Channel 4 exceeds high alarm level or is below low alarm level.
	    If the qtechFiberDDMSupportStatus is false or the Fiber module type is
	    not QSFP+, the status is unknown(1)."
        ::= { qtechFiberEntry 30 }

qtechFiberRXpowerIntegerpart OBJECT-TYPE
        SYNTAX INTEGER
        MAX-ACCESS read-only
        STATUS current
        DESCRIPTION
            "The integer part of Rx power of the Fiber module insered into the port.
	    The value is in units of dbm.
	    If the qtechFiberDDMSupportStatus is false or the Fiber module type is
	    neither SFP/SFP+ nor XFP, the integer part of Rx power value
	    is -100(means that the value is invalid)."
        ::= { qtechFiberEntry 31 }

qtechFiberRXpowerDecimalpart OBJECT-TYPE
        SYNTAX INTEGER
        MAX-ACCESS read-only
        STATUS current
        DESCRIPTION
            "The decimal part of Rx power of the Fiber module insered into the port.
	    The value is in units of dbm.
	    If the qtechFiberDDMSupportStatus is false or the Fiber module type is
	    neither SFP/SFP+ nor XFP, the decimal part of Rx power value
	    is -100(means that the value is invalid)."
        ::= { qtechFiberEntry 32 }

qtechFiberRXpowertype OBJECT-TYPE
        SYNTAX INTEGER {
            unknown(1),
            average(2),
            oma(3)
        }
        MAX-ACCESS read-only
        STATUS current
        DESCRIPTION
            "The value indicates whether the received power measurement
	     represents average input optical power(2) or oma(3).
	     If the qtechFiberDDMSupportStatus is false or the Fiber module type is
	     neither SFP/SFP+ nor XFP (or not QSFP+), the value is unknown(1)."
        ::= { qtechFiberEntry 33 }

qtechFiberRXpowerStatus OBJECT-TYPE
        SYNTAX INTEGER {
            unknown(1),
            ok(2),
            warning(3),
            alarm(4)
        }
        MAX-ACCESS read-only
        STATUS current
        DESCRIPTION
            "The status ok(2) indicates that the Rx power of the Fiber module is in
	    the normal level. The status warning(3) indicates that the Rx power of
	    the Fiber module exceeds high warning level or is below low warning level.
            The status alarm(4) indicates that the Rx power of
	    the Fiber module exceeds high alarm level or is below low alarm level.
	    If the qtechFiberDDMSupportStatus is false or the Fiber module type is
	    neither SFP/SFP+ nor XFP, the status is unknown(1)."
        ::= { qtechFiberEntry 34 }

qtechFiberChannel1RXpowerIntegerpart OBJECT-TYPE
        SYNTAX INTEGER
        MAX-ACCESS read-only
        STATUS current
        DESCRIPTION
            "The integer part of Rx power in Channel 1 of the QSFP+
	    Fiber module insered into the port. The value is in units of dbm.
	    If the qtechFiberDDMSupportStatus is false or the Fiber module type is
	    not QSFP+, the integer part of Rx power value in Channel 1
	    is -100(means the value is invalid)."
        ::= { qtechFiberEntry 35 }

qtechFiberChannel1RXpowerDecimalpart OBJECT-TYPE
        SYNTAX INTEGER
        MAX-ACCESS read-only
        STATUS current
        DESCRIPTION
            "The decimal part of Rx power in Channel 1 of the QSFP+
	    Fiber module insered into the port. The value is in units of dbm.
	    If the qtechFiberDDMSupportStatus is false or the Fiber module type is
	    not QSFP+, the decimal part of Rx power value in Channel 1
	    is -100(means the value is invalid)."
        ::= { qtechFiberEntry 36 }

qtechFiberChannel1RXpowertype OBJECT-TYPE
        SYNTAX INTEGER {
            unknown(1),
            average(2),
            oma(3)
        }
        MAX-ACCESS read-only
        STATUS current
        DESCRIPTION
            "The value indicates whether the received power measurement
	     represents average input optical power(2) or oma(3) in Channel 1 of QSFP+.
	     If the qtechFiberDDMSupportStatus is false or the Fiber module type is
	     not QSFP+, the value is unknown(1)."
        ::= { qtechFiberEntry 37 }

qtechFiberChannel1RXpowerStatus OBJECT-TYPE
        SYNTAX INTEGER {
            unknown(1),
            ok(2),
            warning(3),
            alarm(4)
        }
        MAX-ACCESS read-only
        STATUS current
        DESCRIPTION
            "The status ok(2) indicates that the Rx power in the Channel 1 of QSFP+ is in
	    the normal level. The status warning(3) indicates that
	    the Rx power in the Channel 1 exceeds high warning level or is below
	    low warning level. The status alarm(4) indicates that the Rx power in the
	    Channel 1 exceeds high alarm level or is below low alarm level.
	    If the qtechFiberDDMSupportStatus is false or the Fiber module type is
	    not QSFP+, the status is unknown(1)."
        ::= { qtechFiberEntry 38 }

qtechFiberChannel2RXpowerIntegerpart OBJECT-TYPE
        SYNTAX INTEGER
        MAX-ACCESS read-only
        STATUS current
        DESCRIPTION
            "The integer part of Rx power in Channel 1 of the QSFP+
	    Fiber module insered into the port. The value is in units of dbm.
	    If the qtechFiberDDMSupportStatus is false or the Fiber module type is
	    not QSFP+, the integer part of Rx power value in Channel 1
	    is -100(means the value is invalid)."
        ::= { qtechFiberEntry 39 }

qtechFiberChannel2RXpowerDecimalpart OBJECT-TYPE
        SYNTAX INTEGER
        MAX-ACCESS read-only
        STATUS current
        DESCRIPTION
            "The decimal part of Rx power in Channel 1 of the QSFP+
	    Fiber module insered into the port. The value is in units of dbm.
	    If the qtechFiberDDMSupportStatus is false or the Fiber module type is
	    not QSFP+, the decimal part of Rx power value in Channel 2
	    is -100(means the value is invalid)."
        ::= { qtechFiberEntry 40 }

qtechFiberChannel2RXpowertype OBJECT-TYPE
        SYNTAX INTEGER {
            unknown(1),
            average(2),
            oma(3)
        }
        MAX-ACCESS read-only
        STATUS current
        DESCRIPTION
            "The value indicates whether the received power measurement
	     represents average input optical power(2) or oma(3) in Channel 2 of QSFP+.
	     If the qtechFiberDDMSupportStatus is false or the Fiber module type is
	     not QSFP+, the value is unknown(1)."
        ::= { qtechFiberEntry 41 }

qtechFiberChannel2RXpowerStatus OBJECT-TYPE
        SYNTAX INTEGER {
            unknown(1),
            ok(2),
            warning(3),
            alarm(4)
        }
        MAX-ACCESS read-only
        STATUS current
        DESCRIPTION
            "The status ok(2) indicates that the Rx power in the Channel 2 of QSFP+ is in
	    the normal level. The status warning(3) indicates that
	    the Rx power in the Channel 2 exceeds high warning level or is below
	    low warning level. The status alarm(4) indicates that the Rx power in the
	    Channel 2 exceeds high alarm level or is below low alarm level.
	    If the qtechFiberDDMSupportStatus is false or the Fiber module type is
	    not QSFP+, the status is unknown(1)."
        ::= { qtechFiberEntry 42 }

qtechFiberChannel3RXpowerIntegerpart OBJECT-TYPE
        SYNTAX INTEGER
        MAX-ACCESS read-only
        STATUS current
        DESCRIPTION
            "The integer part of Rx power in Channel 3 of the QSFP+
	    Fiber module insered into the port. The value is in units of dbm.
	    If the qtechFiberDDMSupportStatus is false or the Fiber module type is
	    not QSFP+, the integer part of Rx power value in Channel 3
	    is -100(means the value is invalid)."
        ::= { qtechFiberEntry 43 }

qtechFiberChannel3RXpowerDecimalpart OBJECT-TYPE
        SYNTAX INTEGER
        MAX-ACCESS read-only
        STATUS current
        DESCRIPTION
            "The decimal part of Rx power in Channel 3 of the QSFP+
	    Fiber module insered into the port. The value is in units of dbm.
	    If the qtechFiberDDMSupportStatus is false or the Fiber module type is
	    not QSFP+, the decimal part of Rx power value in Channel 3
	    is -100(means the value is invalid)."
        ::= { qtechFiberEntry 44 }

qtechFiberChannel3RXpowertype OBJECT-TYPE
        SYNTAX INTEGER {
            unknown(1),
            average(2),
            oma(3)
        }
        MAX-ACCESS read-only
        STATUS current
        DESCRIPTION
            "The value indicates whether the received power measurement
	     represents average input optical power(2) or oma(3) in Channel 3 of QSFP+.
	     If the qtechFiberDDMSupportStatus is false or the Fiber module type is
	     not QSFP+, the value is unknown(1)."
        ::= { qtechFiberEntry 45 }

qtechFiberChannel3RXpowerStatus OBJECT-TYPE
        SYNTAX INTEGER {
            unknown(1),
            ok(2),
            warning(3),
            alarm(4)
        }
        MAX-ACCESS read-only
        STATUS current
        DESCRIPTION
            "The status ok(2) indicates that the Rx power in the Channel 3 of QSFP+ is in
	    the normal level. The status warning(3) indicates that
	    the Rx power in the Channel 3 exceeds high warning level or is below
	    low warning level. The status alarm(4) indicates that the Rx power in the
	    Channel 3 exceeds high alarm level or is below low alarm level.
	    If the qtechFiberDDMSupportStatus is false or the Fiber module type is
	    not QSFP+, the status is unknown(1)."
        ::= { qtechFiberEntry 46 }

qtechFiberChannel4RXpowerIntegerpart OBJECT-TYPE
        SYNTAX INTEGER
        MAX-ACCESS read-only
        STATUS current
        DESCRIPTION
            "The integer part of Rx power in Channel 4 of the QSFP+
	    Fiber module insered into the port. The value is in units of dbm.
	    If the qtechFiberDDMSupportStatus is false or the Fiber module type is
	    not QSFP+, the integer part of Rx power value in Channel 4
	    is -100(means the value is invalid)."
        ::= { qtechFiberEntry 47 }

qtechFiberChannel4RXpowerDecimalpart OBJECT-TYPE
        SYNTAX INTEGER
        MAX-ACCESS read-only
        STATUS current
        DESCRIPTION
            "The decimal part of Rx power in Channel 4 of the QSFP+
	    Fiber module insered into the port. The value is in units of dbm.
	    If the qtechFiberDDMSupportStatus is false or the Fiber module type is
	    not QSFP+, the decimal part of Rx power value in Channel 4
	    is -100(means the value is invalid)."
        ::= { qtechFiberEntry 48 }

qtechFiberChannel4RXpowertype OBJECT-TYPE
        SYNTAX INTEGER {
            unknown(1),
            average(2),
            oma(3)
        }
        MAX-ACCESS read-only
        STATUS current
        DESCRIPTION
            "The value indicates whether the received power measurement
	     represents average input optical power(2) or oma(3) in Channel 4 of QSFP+.
	     If the qtechFiberDDMSupportStatus is false or the Fiber module type is
	     not QSFP+, the value is unknown(1)."
        ::= { qtechFiberEntry 49 }

qtechFiberChannel4RXpowerStatus OBJECT-TYPE
        SYNTAX INTEGER {
            unknown(1),
            ok(2),
            warning(3),
            alarm(4)
        }
        MAX-ACCESS read-only
        STATUS current
        DESCRIPTION
            "The status ok(2) indicates that the Rx power in the Channel 4 of QSFP+ is in
	    the normal level. The status warning(3) indicates that
	    the Rx power in the Channel 4 exceeds high warning level or is below
	    low warning level. The status alarm(4) indicates that the Rx power in the
	    Channel 4 exceeds high alarm level or is below low alarm level.
	    If the qtechFiberDDMSupportStatus is false or the Fiber module type is
	    not QSFP+, the status is unknown(1)."
        ::= { qtechFiberEntry 50 }

qtechFiberTXpowerIntegerpart OBJECT-TYPE
        SYNTAX INTEGER
        MAX-ACCESS read-only
        STATUS current
        DESCRIPTION
            "The integer part of Tx power of the Fiber module insered into the port.
	    The value is in units of dbm.
	    If the qtechFiberDDMSupportStatus is false or the Fiber module type is
	    neither SFP/SFP+ nor XFP, the integer part of Tx power value
	    is -100(means that the value is invalid)."
        ::= { qtechFiberEntry 51 }

qtechFiberTXpowerDecimalpart OBJECT-TYPE
        SYNTAX INTEGER
        MAX-ACCESS read-only
        STATUS current
        DESCRIPTION
            "The decimal part of Tx power of the Fiber module insered into the port.
	    The value is in units of dbm.
	    If the qtechFiberDDMSupportStatus is false or the Fiber module type is
	    neither SFP/SFP+ nor XFP, the decimal part of Tx power value
	    is -100(means that the value is invalid)."
        ::= { qtechFiberEntry 52 }

qtechFiberTXpowerStatus OBJECT-TYPE
        SYNTAX INTEGER {
            unknown(1),
            ok(2),
            warning(3),
            alarm(4)
        }
        MAX-ACCESS read-only
        STATUS current
        DESCRIPTION
            "The status ok(2) indicates that the Tx power of the Fiber module is in
	    the normal level. The status warning(3) indicates that the Tx power of
	    the Fiber module exceeds high warning level or is below low warning level.
            The status alarm(4) indicates that the Tx power of
	    the Fiber module exceeds high alarm level or is below low alarm level.
	    If the qtechFiberDDMSupportStatus is false or the Fiber module type is
	    neither SFP/SFP+ nor XFP, the status is unknown(1)."
        ::= { qtechFiberEntry 53 }

qtechFiberChannel1TXpowerIntegerpart OBJECT-TYPE
        SYNTAX INTEGER
        MAX-ACCESS read-only
        STATUS current
        DESCRIPTION
            "The integer part of Tx power in Channel 1 of the QSFP+
	    Fiber module insered into the port. The value is in units of dbm.
	    If the qtechFiberDDMSupportStatus is false or the Fiber module type is
	    not QSFP+, the integer part of Tx power value in Channel 1
	    is -100(means the value is invalid)."
        ::= { qtechFiberEntry 54 }

qtechFiberChannel1TXpowerDecimalpart OBJECT-TYPE
        SYNTAX INTEGER
        MAX-ACCESS read-only
        STATUS current
        DESCRIPTION
            "The decimal part of Tx power in Channel 1 of the QSFP+
	    Fiber module insered into the port. The value is in units of dbm.
	    If the qtechFiberDDMSupportStatus is false or the Fiber module type is
	    not QSFP+, the decimal part of Tx power value in Channel 1
	    is -100(means the value is invalid)."
        ::= { qtechFiberEntry 55 }

qtechFiberChannel1TXpowerStatus OBJECT-TYPE
        SYNTAX INTEGER {
            unknown(1),
            ok(2),
            warning(3),
            alarm(4)
        }
        MAX-ACCESS read-only
        STATUS current
        DESCRIPTION
            "The status ok(2) indicates that the Tx power in the Channel 1 of QSFP+ is in
	    the normal level. The status warning(3) indicates that
	    the Tx power in the Channel 1 exceeds high warning level or is below
	    low warning level. The status alarm(4) indicates that the Tx power in the
	    Channel 1 exceeds high alarm level or is below low alarm level.
	    If the qtechFiberDDMSupportStatus is false or the Fiber module type is
	    not QSFP+, the status is unknown(1)."
        ::= { qtechFiberEntry 56 }

qtechFiberChannel2TXpowerIntegerpart OBJECT-TYPE
        SYNTAX INTEGER
        MAX-ACCESS read-only
        STATUS current
        DESCRIPTION
            "The integer part of Tx power in Channel 1 of the QSFP+
	    Fiber module insered into the port. The value is in units of dbm.
	    If the qtechFiberDDMSupportStatus is false or the Fiber module type is
	    not QSFP+, the integer part of Tx power value in Channel 1
	    is -100(means the value is invalid)."
        ::= { qtechFiberEntry 57 }

qtechFiberChannel2TXpowerDecimalpart OBJECT-TYPE
        SYNTAX INTEGER
        MAX-ACCESS read-only
        STATUS current
        DESCRIPTION
            "The decimal part of Tx power in Channel 1 of the QSFP+
	    Fiber module insered into the port. The value is in units of dbm.
	    If the qtechFiberDDMSupportStatus is false or the Fiber module type is
	    not QSFP+, the decimal part of Tx power value in Channel 2
	    is -100(means the value is invalid)."
        ::= { qtechFiberEntry 58 }

qtechFiberChannel2TXpowerStatus OBJECT-TYPE
        SYNTAX INTEGER {
            unknown(1),
            ok(2),
            warning(3),
            alarm(4)
        }
        MAX-ACCESS read-only
        STATUS current
        DESCRIPTION
            "The status ok(2) indicates that the Tx power in the Channel 2 of QSFP+ is in
	    the normal level. The status warning(3) indicates that
	    the Tx power in the Channel 2 exceeds high warning level or is below
	    low warning level. The status alarm(4) indicates that the Tx power in the
	    Channel 2 exceeds high alarm level or is below low alarm level.
	    If the qtechFiberDDMSupportStatus is false or the Fiber module type is
	    not QSFP+, the status is unknown(1)."
        ::= { qtechFiberEntry 59 }

qtechFiberChannel3TXpowerIntegerpart OBJECT-TYPE
        SYNTAX INTEGER
        MAX-ACCESS read-only
        STATUS current
        DESCRIPTION
            "The integer part of Tx power in Channel 3 of the QSFP+
	    Fiber module insered into the port. The value is in units of dbm.
	    If the qtechFiberDDMSupportStatus is false or the Fiber module type is
	    not QSFP+, the integer part of Tx power value in Channel 3
	    is -100(means the value is invalid)."
        ::= { qtechFiberEntry 60 }

qtechFiberChannel3TXpowerDecimalpart OBJECT-TYPE
        SYNTAX INTEGER
        MAX-ACCESS read-only
        STATUS current
        DESCRIPTION
            "The decimal part of Tx power in Channel 3 of the QSFP+
	    Fiber module insered into the port. The value is in units of dbm.
	    If the qtechFiberDDMSupportStatus is false or the Fiber module type is
	    not QSFP+, the decimal part of Tx power value in Channel 3
	    is -100(means the value is invalid)."
        ::= { qtechFiberEntry 61 }

qtechFiberChannel3TXpowerStatus OBJECT-TYPE
        SYNTAX INTEGER {
            unknown(1),
            ok(2),
            warning(3),
            alarm(4)
        }
        MAX-ACCESS read-only
        STATUS current
        DESCRIPTION
            "The status ok(2) indicates that the Tx power in the Channel 3 of QSFP+ is in
	    the normal level. The status warning(3) indicates that
	    the Tx power in the Channel 3 exceeds high warning level or is below
	    low warning level. The status alarm(4) indicates that the Tx power in the
	    Channel 3 exceeds high alarm level or is below low alarm level.
	    If the qtechFiberDDMSupportStatus is false or the Fiber module type is
	    not QSFP+, the status is unknown(1)."
        ::= { qtechFiberEntry 62 }

qtechFiberChannel4TXpowerIntegerpart OBJECT-TYPE
        SYNTAX INTEGER
        MAX-ACCESS read-only
        STATUS current
        DESCRIPTION
            "The integer part of Tx power in Channel 4 of the QSFP+
	    Fiber module insered into the port. The value is in units of dbm.
	    If the qtechFiberDDMSupportStatus is false or the Fiber module type is
	    not QSFP+, the integer part of Tx power value in Channel 4
	    is -100(means the value is invalid)."
        ::= { qtechFiberEntry 63 }

qtechFiberChannel4TXpowerDecimalpart OBJECT-TYPE
        SYNTAX INTEGER
        MAX-ACCESS read-only
        STATUS current
        DESCRIPTION
            "The decimal part of Tx power in Channel 4 of the QSFP+
	    Fiber module insered into the port. The value is in units of dbm.
	    If the qtechFiberDDMSupportStatus is false or the Fiber module type is
	    not QSFP+, the decimal part of Tx power value in Channel 4
	    is -100(means the value is invalid)."
        ::= { qtechFiberEntry 64 }

qtechFiberChannel4TXpowerStatus OBJECT-TYPE
        SYNTAX INTEGER {
            unknown(1),
            ok(2),
            warning(3),
            alarm(4)
        }
        MAX-ACCESS read-only
        STATUS current
        DESCRIPTION
            "The status ok(2) indicates that the Tx power in the Channel 4 of QSFP+ is in
	    the normal level. The status warning(3) indicates that
	    the Tx power in the Channel 4 exceeds high warning level or is below
	    low warning level. The status alarm(4) indicates that the Tx power in the
	    Channel 4 exceeds high alarm level or is below low alarm level.
	    If the qtechFiberDDMSupportStatus is false or the Fiber module type is
	    not QSFP+, the status is unknown(1)."
        ::= { qtechFiberEntry 65 }

qtechFiberMIBConformance OBJECT IDENTIFIER ::= { qtechFiberMIB 2 }
qtechFiberMIBCompliances OBJECT IDENTIFIER ::= { qtechFiberMIBConformance 1 }
qtechFiberMIBGroups      OBJECT IDENTIFIER ::= { qtechFiberMIBConformance 2 }

-- ---------------------------------------------------------- --
-- compliance statements
-- ---------------------------------------------------------- --
qtechFiberMIBConpliance MODULE-COMPLIANCE
        STATUS  current
        DESCRIPTION
                "The compliance statement for entities which implement
                the Qtech Fiber MIB"
        MODULE  -- this module
                MANDATORY-GROUPS {
                        qtechFiberMIBGroup
                }
         ::= { qtechFiberMIBCompliances 1 }

qtechFiberMIBGroup OBJECT-GROUP
        OBJECTS {
                qtechFiberPortDescr,
                qtechFiberTransceiverType,
                qtechFiberConnectorType,
                qtechFiberWavelength,
                qtechFiberTransferDistanceSMF,
                qtechFiberTransferDistance62point5umOM1,
                qtechFiberTransferDistance62point5um,
                qtechFiberTransferDistance50umOM2,
                qtechFiberTransferDistance50um,
                qtechFiberTransferDistance50umOM3,
                qtechFiberTransferDistanceEBW50um,
                qtechFiberTransferDistanceCopper,
                qtechFiberTransferDistanceCableAssembly,
                qtechFiberDDMSupportStatus,
                qtechFiberSerialNumber,
                qtechFiberTemp,
                qtechFiberTempStatus,
                qtechFiberVoltage,
                qtechFiberVoltageStatus,
                qtechFiberBias,
                qtechFiberBiasStatus,
                qtechFiberChannel1Bias,
                qtechFiberChannel1BiasStatus,
                qtechFiberChannel2Bias,
                qtechFiberChannel2BiasStatus,
                qtechFiberChannel3Bias,
                qtechFiberChannel3BiasStatus,
                qtechFiberChannel4Bias,
                qtechFiberChannel4BiasStatus,
                qtechFiberRXpowerIntegerpart,
                qtechFiberRXpowerDecimalpart,
                qtechFiberRXpowertype,
                qtechFiberRXpowerStatus,
                qtechFiberChannel1RXpowerIntegerpart,
                qtechFiberChannel1RXpowerDecimalpart,
                qtechFiberChannel1RXpowertype,
                qtechFiberChannel1RXpowerStatus,
                qtechFiberChannel2RXpowerIntegerpart,
                qtechFiberChannel2RXpowerDecimalpart,
                qtechFiberChannel2RXpowertype,
                qtechFiberChannel2RXpowerStatus,
                qtechFiberChannel3RXpowerIntegerpart,
                qtechFiberChannel3RXpowerDecimalpart,
                qtechFiberChannel3RXpowertype,
                qtechFiberChannel3RXpowerStatus,
                qtechFiberChannel4RXpowerIntegerpart,
                qtechFiberChannel4RXpowerDecimalpart,
                qtechFiberChannel4RXpowertype,
                qtechFiberChannel4RXpowerStatus,
                qtechFiberTXpowerIntegerpart,
                qtechFiberTXpowerDecimalpart,
                qtechFiberTXpowerStatus,
                qtechFiberChannel1TXpowerIntegerpart,
                qtechFiberChannel1TXpowerDecimalpart,
                qtechFiberChannel1TXpowerStatus,
                qtechFiberChannel2TXpowerIntegerpart,
                qtechFiberChannel2TXpowerDecimalpart,
                qtechFiberChannel2TXpowerStatus,
                qtechFiberChannel3TXpowerIntegerpart,
                qtechFiberChannel3TXpowerDecimalpart,
                qtechFiberChannel3TXpowerStatus,
                qtechFiberChannel4TXpowerIntegerpart,
                qtechFiberChannel4TXpowerDecimalpart,
                qtechFiberChannel4TXpowerStatus
        }
        STATUS  current
        DESCRIPTION
                "A collection of objects providing Fiber managment."
        ::= { qtechFiberMIBGroups 1 }
END
