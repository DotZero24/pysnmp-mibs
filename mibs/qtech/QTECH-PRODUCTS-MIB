-- *****************************************************************
-- QTECH-PRODUCTS-MIB.mib:  Qtech Product Object Identifier Assignments
--
-- March 2002, Wuzg
--
-- Copyright (c) 2002 by Qtech Networks Co.,Ltd.
-- All rights reserved.
--
-- *****************************************************************
--

QTECH-PRODUCTS-MIB DEFINITIONS ::= BEGIN

IMPORTS
        MODULE-IDENTITY
                FROM SNMPv2-SMI
        qtechModules,
        qtechSwitchProducts
                FROM QTECH-SMI
        qtechRouterProducts
                FROM QTECH-ROUTER-SMI
        qtechGatewayProducts
                FROM QTECH-GATEWAY-SMI
        qtechWirelessProducts
                FROM QTECH-WIRELESS-SMI
        qtechSoftwareProducts
                FROM QTECH-SOFTWARE-SMI;

qtechProductsMIB MODULE-IDENTITY
        LAST-UPDATED "200203200000Z"
        ORGANIZATION "Qtech Networks Co.,Ltd."
        CONTACT-INFO
                "
                Tel: 4008-111-000

                E-mail: service@qtech.com.cn"
        DESCRIPTION
                "This module defines the object identifiers that are
            		assigned to various hardware platforms, and hence are
            		returned as values for sysObjectID"
        REVISION      "200203200000Z"
        DESCRIPTION
                "Initial version of this MIB module."
        ::= { qtechModules 1}

-- devices return a sysObjectID value that corresponds to the
-- device model number

-- ****************************** switch ***********************************

s2126G   OBJECT IDENTIFIER ::= { qtechSwitchProducts 1 }

s2126GL3 OBJECT IDENTIFIER ::= { qtechSwitchProducts 2 }

s2150G   OBJECT IDENTIFIER ::= { qtechSwitchProducts 3 }

s2150GL3 OBJECT IDENTIFIER ::= { qtechSwitchProducts 4 }

s4909 OBJECT IDENTIFIER ::= { qtechSwitchProducts 5 }

s3550-12G OBJECT IDENTIFIER ::= { qtechSwitchProducts 6 }

s3550-24G OBJECT IDENTIFIER ::= { qtechSwitchProducts 8 }

s21-STACKING OBJECT IDENTIFIER ::= { qtechSwitchProducts 11 }

s3550-24 OBJECT IDENTIFIER ::= { qtechSwitchProducts 12 }

s3550-48 OBJECT IDENTIFIER ::= { qtechSwitchProducts 13 }

s3550-12SFP-GT OBJECT IDENTIFIER ::= { qtechSwitchProducts 15 }

s6806 OBJECT IDENTIFIER ::= { qtechSwitchProducts 16 }

s6810 OBJECT IDENTIFIER ::= { qtechSwitchProducts 17 }

s2126S OBJECT IDENTIFIER ::= { qtechSwitchProducts 18 }

s2126S-STACKING OBJECT IDENTIFIER ::= { qtechSwitchProducts 19 }

s1908PLUS OBJECT IDENTIFIER ::= { qtechSwitchProducts 20 }

s1916PLUS OBJECT IDENTIFIER ::= { qtechSwitchProducts 21 }

s6506 OBJECT IDENTIFIER ::= { qtechSwitchProducts 22 }

s2126S-08  OBJECT IDENTIFIER ::= { qtechSwitchProducts 23 }

s2126S-16  OBJECT IDENTIFIER ::= { qtechSwitchProducts 24 }

s6806E OBJECT IDENTIFIER ::= { qtechSwitchProducts 25 }

s6810E OBJECT IDENTIFIER ::= { qtechSwitchProducts 26 }

s2026G OBJECT IDENTIFIER ::= { qtechSwitchProducts 27 }

s3750-24 OBJECT IDENTIFIER ::= { qtechSwitchProducts 28 }

s3750-48 OBJECT IDENTIFIER ::= { qtechSwitchProducts 29 }

s2126    OBJECT IDENTIFIER ::= { qtechSwitchProducts 30 }

s2126-STACKING    OBJECT IDENTIFIER ::= { qtechSwitchProducts 31 }

-- s2026F OBJECT IDENTIFIER ::= { qtechSwitchProducts 32 }

s2026F OBJECT IDENTIFIER ::= { qtechSwitchProducts 33 }

s3760-12SFP-GT OBJECT IDENTIFIER ::= { qtechSwitchProducts 34 }

s4009 OBJECT IDENTIFIER ::= { qtechSwitchProducts 35 }

s3526 OBJECT IDENTIFIER ::= { qtechSwitchProducts 36 }

s3512G OBJECT IDENTIFIER ::= { qtechSwitchProducts 37 }

hcl-12GCS-L3 OBJECT IDENTIFIER ::= { qtechSwitchProducts 38 }

hcl-24GS-L3 OBJECT IDENTIFIER ::= { qtechSwitchProducts 39 }

hcl-48TMS-2S-S OBJECT IDENTIFIER ::= { qtechSwitchProducts 40 }

s5750-24GT-12SFP OBJECT IDENTIFIER ::= { qtechSwitchProducts 41 }

s5750P-24GT-12SFP OBJECT IDENTIFIER ::= { qtechSwitchProducts 42 }

s8606 OBJECT IDENTIFIER ::= { qtechSwitchProducts 43 }

s8610 OBJECT IDENTIFIER ::= { qtechSwitchProducts 44 }

s8606B OBJECT IDENTIFIER ::= { qtechSwitchProducts 45 }

s9620 OBJECT IDENTIFIER ::= { qtechSwitchProducts 46 }

s2924G OBJECT IDENTIFIER ::= { qtechSwitchProducts 47 }

s3760-24 OBJECT IDENTIFIER ::= { qtechSwitchProducts 48 }

s3760-48 OBJECT IDENTIFIER ::= { qtechSwitchProducts 49 }

s3750E-24 OBJECT IDENTIFIER ::= { qtechSwitchProducts 50 }

s3750E-48 OBJECT IDENTIFIER ::= { qtechSwitchProducts 51 }

--s3750E-12SFP-GT OBJECT IDENTIFIER ::= { qtechSwitchProducts 52 }

s5750S-24GT-12SFP OBJECT IDENTIFIER ::= { qtechSwitchProducts 53 }

s2128G OBJECT IDENTIFIER ::= { qtechSwitchProducts 54 }

s2927XG OBJECT IDENTIFIER ::= { qtechSwitchProducts 55 }

s3512GPLUS OBJECT IDENTIFIER ::= { qtechSwitchProducts 56 }

s7604 OBJECT IDENTIFIER ::= { qtechSwitchProducts 57 }

s7606 OBJECT IDENTIFIER ::= { qtechSwitchProducts 58 }

s7610 OBJECT IDENTIFIER ::= { qtechSwitchProducts 59 }

s5750-24SFP-12GT OBJECT IDENTIFIER ::= { qtechSwitchProducts 60 }

s5750-48GT-4SFP OBJECT IDENTIFIER ::= { qtechSwitchProducts 61 }

s5750S-48GT-4SFP OBJECT IDENTIFIER ::= { qtechSwitchProducts 62 }

s3250-24 OBJECT IDENTIFIER ::= { qtechSwitchProducts 63 }

s3250-48 OBJECT IDENTIFIER ::= { qtechSwitchProducts 64 }

s2724G OBJECT IDENTIFIER ::= { qtechSwitchProducts 65 }

s2951XG OBJECT IDENTIFIER ::= { qtechSwitchProducts 66 }

s3750-24-UB OBJECT IDENTIFIER ::= { qtechSwitchProducts 67 }

s3750-48-UB OBJECT IDENTIFIER ::= { qtechSwitchProducts 68 }

scg5510  OBJECT IDENTIFIER ::= { qtechSwitchProducts 69 }

s2052G  OBJECT IDENTIFIER ::= { qtechSwitchProducts 70 }

s2328G  OBJECT IDENTIFIER ::= { qtechSwitchProducts 71 }

s8614  OBJECT IDENTIFIER ::= { qtechSwitchProducts 72 }

s5760-24GT-4SFP  OBJECT IDENTIFIER ::= { qtechSwitchProducts 73 }

--s5650-27XG  OBJECT IDENTIFIER ::= { qtechSwitchProducts 74 }

s5760-48GT-4SFP  OBJECT IDENTIFIER ::= { qtechSwitchProducts 75 }

--s5450-28GT  OBJECT IDENTIFIER ::= { qtechSwitchProducts 76 }

s3250P-24  OBJECT IDENTIFIER ::= { qtechSwitchProducts 78 }

--s2928G  OBJECT IDENTIFIER ::= { qtechSwitchProducts 79 }

--s2952G  OBJECT IDENTIFIER ::= { qtechSwitchProducts 80 }

--s2028G  OBJECT IDENTIFIER ::= { qtechSwitchProducts 81 }

s2628G  OBJECT IDENTIFIER ::= { qtechSwitchProducts 82 }

s2652G  OBJECT IDENTIFIER ::= { qtechSwitchProducts 83 }

--s5750R-48GT-4SFP OBJECT IDENTIFIER ::= { qtechSwitchProducts 84 }

s5750P-48GT-4SFP OBJECT IDENTIFIER ::= { qtechSwitchProducts 85 }

--s5750R-24GT-4SFP OBJECT IDENTIFIER ::= { qtechSwitchProducts 86 }

--s5750P-24GT-4SFP OBJECT IDENTIFIER ::= { qtechSwitchProducts 87 }

--s5750-24GT-4SFP OBJECT IDENTIFIER ::= { qtechSwitchProducts 88 }

--s5750S-24GT-4SFP OBJECT IDENTIFIER ::= { qtechSwitchProducts 89 }

s5750-48GT-4SFP-A OBJECT IDENTIFIER ::= { qtechSwitchProducts 92 }

s5750-48GT-4SFP-AP OBJECT IDENTIFIER ::= { qtechSwitchProducts 93 }

s2352G OBJECT IDENTIFIER ::= { qtechSwitchProducts 94 }

--nm2-24esw OBJECT IDENTIFIER ::= { qtechSwitchProducts 95 }

--nmx-24esw OBJECT IDENTIFIER ::= { qtechSwitchProducts 95 }

--nm2-16esw OBJECT IDENTIFIER ::= { qtechSwitchProducts 96 }

--s5750E-24SFP-12GT OBJECT IDENTIFIER ::= { qtechSwitchProducts 97 }

s3760E-24 OBJECT IDENTIFIER ::= { qtechSwitchProducts 98 }

s3760E-48 OBJECT IDENTIFIER ::= { qtechSwitchProducts 99 }

s3250E-24 OBJECT IDENTIFIER ::= { qtechSwitchProducts 100 }

s2628G-P OBJECT IDENTIFIER ::= { qtechSwitchProducts 101 }

s3250E-48 OBJECT IDENTIFIER ::= { qtechSwitchProducts 102 }

s2652G-P OBJECT IDENTIFIER ::= { qtechSwitchProducts 103 }

S3760E-24P OBJECT IDENTIFIER ::= { qtechSwitchProducts 104 }

S3760E-48P OBJECT IDENTIFIER ::= { qtechSwitchProducts 105 }

s2628G-E OBJECT IDENTIFIER ::= { qtechSwitchProducts 106 }

s2652G-E OBJECT IDENTIFIER ::= { qtechSwitchProducts 107 }

S5750-24GT/8SFP-E OBJECT IDENTIFIER ::= { qtechSwitchProducts 111 }

S5750-24GT/8SFP-P OBJECT IDENTIFIER ::= { qtechSwitchProducts 112 }

S5750-48GT/4SFP-E OBJECT IDENTIFIER ::= { qtechSwitchProducts 113 }

S5750-48GT/4SFP-P OBJECT IDENTIFIER ::= { qtechSwitchProducts 114 }

S2928G-E OBJECT IDENTIFIER ::= { qtechSwitchProducts 117 }

S2952G-E OBJECT IDENTIFIER ::= { qtechSwitchProducts 118 }

S2924GT/8SFP-XS-P OBJECT IDENTIFIER ::= { qtechSwitchProducts 120 }

S6200-48XS OBJECT IDENTIFIER ::= { qtechSwitchProducts 123 }

S2628G-I OBJECT IDENTIFIER ::= { qtechSwitchProducts 126 }

S2652G-I OBJECT IDENTIFIER ::= { qtechSwitchProducts 127 }

S6000-48GT4XS OBJECT IDENTIFIER ::= { qtechSwitchProducts 128 }

S6210-32XS8QXS OBJECT IDENTIFIER ::= { qtechSwitchProducts 129}

S6210-48XS OBJECT IDENTIFIER ::= { qtechSwitchProducts 130}

S15010 OBJECT IDENTIFIER ::= { qtechSwitchProducts 131 }

S12006 OBJECT IDENTIFIER ::= { qtechSwitchProducts 132 }

S12010 OBJECT IDENTIFIER ::= { qtechSwitchProducts 133 }

S5750-28GT-L OBJECT IDENTIFIER ::= { qtechSwitchProducts 137 }

S5750-52GT-L OBJECT IDENTIFIER ::= { qtechSwitchProducts 138 }

S5750-24SFP/8GT-E OBJECT IDENTIFIER ::= { qtechSwitchProducts 139 }

S6000-86GT10XS OBJECT IDENTIFIER ::= { qtechSwitchProducts 141 }

S2928G-S OBJECT IDENTIFIER ::= { qtechSwitchProducts 142 }

S2950G-S OBJECT IDENTIFIER ::= { qtechSwitchProducts 143 }

S5750-28GT-S OBJECT IDENTIFIER ::= { qtechSwitchProducts 144 }

S2628G-S OBJECT IDENTIFIER ::= { qtechSwitchProducts 146 }

S2652G-S OBJECT IDENTIFIER ::= { qtechSwitchProducts 147 }

S6220-24XS OBJECT IDENTIFIER ::= { qtechSwitchProducts 148 }

S6220-48XS4QXS OBJECT IDENTIFIER ::= { qtechSwitchProducts 150 }

S6220-48XT4QXS OBJECT IDENTIFIER ::= { qtechSwitchProducts 151 }

S6000-24GT/8SFP OBJECT IDENTIFIER ::= { qtechSwitchProducts 153 }

S6000-48GT/4SFP OBJECT IDENTIFIER ::= { qtechSwitchProducts 154 }

S2928G-24P OBJECT IDENTIFIER ::= { qtechSwitchProducts 155 }

S2928G-12P OBJECT IDENTIFIER ::= { qtechSwitchProducts 156 }

S5750-24GT/8SFP-S OBJECT IDENTIFIER ::= { qtechSwitchProducts 157 }

S5750-48GT/4SFP-S OBJECT IDENTIFIER ::= { qtechSwitchProducts 158 }

S2528G-24P OBJECT IDENTIFIER ::= { qtechSwitchProducts 169 }

RG-S2910-24GT4XS-E OBJECT IDENTIFIER ::= { qtechSwitchProducts 174 }

RG-S2910-48GT4XS-E OBJECT IDENTIFIER ::= { qtechSwitchProducts 175 }

RG-S2910C-24GT2XS-P-E OBJECT IDENTIFIER ::= { qtechSwitchProducts 176 }

RG-S2910C-24GT2XS-HP-E OBJECT IDENTIFIER ::= { qtechSwitchProducts 177 }

RG-S2910C-48GT2XS-HP-E OBJECT IDENTIFIER ::= { qtechSwitchProducts 178 }

RG-S5750-24GT4XS-L OBJECT IDENTIFIER ::= { qtechSwitchProducts 179 }

RG-S5750-48GT4XS-L OBJECT IDENTIFIER ::= { qtechSwitchProducts 180 }

RG-S5750-24GT4XS-H OBJECT IDENTIFIER ::= { qtechSwitchProducts 190 }

RG-S5750-48GT4XS-H OBJECT IDENTIFIER ::= { qtechSwitchProducts 191 }

RG-S5750C-28GT4XS-H OBJECT IDENTIFIER ::= { qtechSwitchProducts 192 }

RG-S5750C-28SFP4XS-H OBJECT IDENTIFIER ::= { qtechSwitchProducts 193 }

RG-S5750C-48GT4XS-H OBJECT IDENTIFIER ::= { qtechSwitchProducts 194 }

RG-S5750C-28GT4XS-HP-H OBJECT IDENTIFIER ::= { qtechSwitchProducts 195 }

RG-S5750C-48GT4XS-HP-H OBJECT IDENTIFIER ::= { qtechSwitchProducts 196 }

S2320G-P OBJECT IDENTIFIER ::= { qtechSwitchProducts 202 }

NBS5628XG OBJECT IDENTIFIER ::= { qtechSwitchProducts 210 }

NBS5652XG OBJECT IDENTIFIER ::= { qtechSwitchProducts 211 }

RG-AS224T OBJECT IDENTIFIER ::= { qtechSwitchProducts 220 }

RG-AS248T OBJECT IDENTIFIER ::= { qtechSwitchProducts 221 }

RG-AS224GT OBJECT IDENTIFIER ::= { qtechSwitchProducts 222 }

RG-AS224GT-P OBJECT IDENTIFIER ::= { qtechSwitchProducts 223 }

RG-AS248GT OBJECT IDENTIFIER ::= { qtechSwitchProducts 224 }

RG-AS324GT OBJECT IDENTIFIER ::= { qtechSwitchProducts 225 }

RG-AS324GF OBJECT IDENTIFIER ::= { qtechSwitchProducts 226 }

RG-AS348GT OBJECT IDENTIFIER ::= { qtechSwitchProducts 227 }

RG-AS216T OBJECT IDENTIFIER ::= { qtechSwitchProducts 228 }

RG-AS216GT OBJECT IDENTIFIER ::= { qtechSwitchProducts 229 }

-- ****************************** router ***********************************

r2620 OBJECT IDENTIFIER ::= { qtechRouterProducts 1 }

r2624 OBJECT IDENTIFIER ::= { qtechRouterProducts 2 }

r2690 OBJECT IDENTIFIER ::= { qtechRouterProducts 3 }

r2692 OBJECT IDENTIFIER ::= { qtechRouterProducts 4 }

r3642 OBJECT IDENTIFIER ::= { qtechRouterProducts 5 }

r3662 OBJECT IDENTIFIER ::= { qtechRouterProducts 6 }

nbr1000 OBJECT IDENTIFIER ::= { qtechRouterProducts 7 }

nbr200  OBJECT IDENTIFIER ::= { qtechRouterProducts 8 }

secvpn100 OBJECT IDENTIFIER ::= { qtechRouterProducts 9 }

r2632 OBJECT IDENTIFIER ::= { qtechRouterProducts 10 }

r1762 OBJECT IDENTIFIER ::= { qtechRouterProducts 11 }

rcms OBJECT IDENTIFIER ::= { qtechRouterProducts 12 }

hcl-r1762 OBJECT IDENTIFIER ::= { qtechRouterProducts 13 }

hcl-r2632 OBJECT IDENTIFIER ::= { qtechRouterProducts 14 }

hcl-r2692 OBJECT IDENTIFIER ::= { qtechRouterProducts 15 }

hcl-r3642 OBJECT IDENTIFIER ::= { qtechRouterProducts 16 }

hcl-r3662 OBJECT IDENTIFIER ::= { qtechRouterProducts 17 }

r3740 OBJECT IDENTIFIER ::= { qtechRouterProducts 18 }

nbr2000 OBJECT IDENTIFIER ::= { qtechRouterProducts 19 }

nbr300 OBJECT IDENTIFIER ::= { qtechRouterProducts 20 }

nbr1200 OBJECT IDENTIFIER ::= { qtechRouterProducts 21 }

nbr1500 OBJECT IDENTIFIER ::= { qtechRouterProducts 22 }

r2716 OBJECT IDENTIFIER ::= { qtechRouterProducts 23 }

r2724 OBJECT IDENTIFIER ::= { qtechRouterProducts 24 }

r3802 OBJECT IDENTIFIER ::= { qtechRouterProducts 25 }

r3804 OBJECT IDENTIFIER ::= { qtechRouterProducts 26 }

rsr50-20 OBJECT IDENTIFIER ::= { qtechRouterProducts 27 }

rsr50-40 OBJECT IDENTIFIER ::= { qtechRouterProducts 28 }

rsr50-80 OBJECT IDENTIFIER ::= { qtechRouterProducts 29 }

npe50-20 OBJECT IDENTIFIER ::= { qtechRouterProducts 30 }

rsr10-02 OBJECT IDENTIFIER ::= { qtechRouterProducts 31 }

rsr20-04 OBJECT IDENTIFIER ::= { qtechRouterProducts 32 }

vpn120 OBJECT IDENTIFIER ::= { qtechRouterProducts 33 }

rsr20-24 OBJECT IDENTIFIER ::= { qtechRouterProducts 35 }

--nmx-24esw-l2 OBJECT IDENTIFIER ::= { qtechRouterProducts 39 }

--nmx-24esw-3gel3 OBJECT IDENTIFIER ::= { qtechRouterProducts 40 }

rsr20-14 OBJECT IDENTIFIER ::= { qtechRouterProducts 41 }

rsr30-44 OBJECT IDENTIFIER ::= { qtechRouterProducts 42 }

r2700v2v3 OBJECT IDENTIFIER ::= { qtechRouterProducts 43 }

r2700v5 OBJECT IDENTIFIER ::= { qtechRouterProducts 44 }

npe50-40 OBJECT IDENTIFIER ::= { qtechRouterProducts 45 }

rsr20-18 OBJECT IDENTIFIER ::= { qtechRouterProducts 46 }

rsr50E-80 OBJECT IDENTIFIER ::= { qtechRouterProducts 47 }

npe50e-80 OBJECT IDENTIFIER ::= { qtechRouterProducts 49 }

rsr7708 OBJECT IDENTIFIER ::= { qtechRouterProducts 50 }

dnmx-48esw OBJECT IDENTIFIER ::= { qtechRouterProducts 51 }

rsr7704 OBJECT IDENTIFIER ::= { qtechRouterProducts 52 }

rsr7716 OBJECT IDENTIFIER ::= { qtechRouterProducts 53 }

rsr20-14e OBJECT IDENTIFIER ::= { qtechRouterProducts 54 }

rsr20-14f OBJECT IDENTIFIER ::= { qtechRouterProducts 55 }

rsr10-01g-w OBJECT IDENTIFIER ::= { qtechRouterProducts 56 }

rsr10-01g-c OBJECT IDENTIFIER ::= { qtechRouterProducts 57 }

rsr10-01g-td OBJECT IDENTIFIER ::= { qtechRouterProducts 58 }

rsr50e-40 OBJECT IDENTIFIER ::= { qtechRouterProducts 66 }


--*******************wireless*************************************
WS5708-V10 OBJECT IDENTIFIER ::= { qtechWirelessProducts 1 }

AP220-SE-V10 OBJECT IDENTIFIER ::= { qtechWirelessProducts 2 }

WS5302-V10 OBJECT IDENTIFIER ::= { qtechWirelessProducts 3 }

AP220-E-V10 OBJECT IDENTIFIER ::= { qtechWirelessProducts 4 }

AP620-H-V10 OBJECT IDENTIFIER ::= { qtechWirelessProducts 5 }

AP220-SH-V10 OBJECT IDENTIFIER ::= { qtechWirelessProducts 8 }

M8600-WS-V10 OBJECT IDENTIFIER ::= { qtechWirelessProducts 14 }

AP620-H-S-V10 OBJECT IDENTIFIER ::= { qtechWirelessProducts 17 }

AP220-SH-V20 OBJECT IDENTIFIER ::= { qtechWirelessProducts 18 }

AP220-E-V11 OBJECT IDENTIFIER ::= { qtechWirelessProducts 19 }

AP220-SE-V11 OBJECT IDENTIFIER ::= { qtechWirelessProducts 20 }

AP220-SH-V11 OBJECT IDENTIFIER ::= { qtechWirelessProducts 23 }

AP220-E-V20 OBJECT IDENTIFIER ::= { qtechWirelessProducts 24 }

AP220-SE-V20 OBJECT IDENTIFIER ::= { qtechWirelessProducts 25 }

AP220-E-V199 OBJECT IDENTIFIER ::= { qtechWirelessProducts 26 }

AP220-I-V10 OBJECT IDENTIFIER ::= { qtechWirelessProducts 27 }

AP220-SI-V10 OBJECT IDENTIFIER ::= { qtechWirelessProducts 28 }

AP220-E-M-V15 OBJECT IDENTIFIER ::= { qtechWirelessProducts 29 }

AP220-SH-V30 OBJECT IDENTIFIER ::= { qtechWirelessProducts 30 }

AP620-H-V20 OBJECT IDENTIFIER ::= { qtechWirelessProducts 31 }

AP220-E-V30 OBJECT IDENTIFIER ::= { qtechWirelessProducts 34 }

AP220-E-M-V20 OBJECT IDENTIFIER ::= { qtechWirelessProducts 35 }


--********************gateway*************************************
EG1000S OBJECT IDENTIFIER ::= { qtechGatewayProducts 1 }
EG1000C OBJECT IDENTIFIER ::= { qtechGatewayProducts 2 }
EG1000M OBJECT IDENTIFIER ::= { qtechGatewayProducts 3 }
EG1000E OBJECT IDENTIFIER ::= { qtechGatewayProducts 5 }

NPE40   OBJECT IDENTIFIER ::= { qtechGatewayProducts 6 }
NPE50E  OBJECT IDENTIFIER ::= { qtechGatewayProducts 7 }
NPE60   OBJECT IDENTIFIER ::= { qtechGatewayProducts 8 }
NPE80   OBJECT IDENTIFIER ::= { qtechGatewayProducts 9 }

NBR2000G   OBJECT IDENTIFIER ::= { qtechGatewayProducts 10 }
NBR2500G   OBJECT IDENTIFIER ::= { qtechGatewayProducts 11 }

NPE60E  OBJECT IDENTIFIER ::= { qtechGatewayProducts 13 }

NBR1300G OBJECT IDENTIFIER ::= { qtechGatewayProducts 18 }
NBR1500G OBJECT IDENTIFIER ::= { qtechGatewayProducts 19 }
EG1000L  OBJECT IDENTIFIER ::= { qtechGatewayProducts 20 }
EG2000K  OBJECT IDENTIFIER ::= { qtechGatewayProducts 21 }
NBR2000D OBJECT IDENTIFIER ::= { qtechGatewayProducts 22 }
NBR1000G OBJECT IDENTIFIER ::= { qtechGatewayProducts 23 }
EG2000D  OBJECT IDENTIFIER ::= { qtechGatewayProducts 24 }
EG2000T  OBJECT IDENTIFIER ::= { qtechGatewayProducts 25 }
EG2000G  OBJECT IDENTIFIER ::= { qtechGatewayProducts 26 }
EG2000X  OBJECT IDENTIFIER ::= { qtechGatewayProducts 27 }
EG2000XE OBJECT IDENTIFIER ::= { qtechGatewayProducts 28 }
EG2000CE OBJECT IDENTIFIER ::= { qtechGatewayProducts 29 }
EG2000SE OBJECT IDENTIFIER ::= { qtechGatewayProducts 30 }
EG2000GE OBJECT IDENTIFIER ::= { qtechGatewayProducts 31 }
NBR2020G OBJECT IDENTIFIER ::= { qtechGatewayProducts 33 }
EG2000P  OBJECT IDENTIFIER ::= { qtechGatewayProducts 35 }
EG2000UE OBJECT IDENTIFIER ::= { qtechGatewayProducts 36 }


--********************software*************************************
RG-ESS1000 OBJECT IDENTIFIER ::= { qtechSoftwareProducts 1 }


END
