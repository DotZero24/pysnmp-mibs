-- ====================================================================
-- Copyright (c) 2012 by Qtech Networks Co.,Ltd. All rights reserved.
--
-- Description: The MIB is designed to get SMM(short message management) statistic information of 3G router .
-- Reference: rujie Enterprise MIB
-- =====================================================================

QTECH-SMM-MIB DEFINITIONS ::= BEGIN
    IMPORTS
        MODULE-IDENTITY,
        NOTIFICATION-TYPE,
        OBJECT-TYPE,
        IpAddress,
        Integer32,
        Counter32,
        Counter64,
        Gauge32,
        Unsigned32
            FROM SNMPv2-SMI
        MODULE-COMPLIANCE,
        OBJECT-GROUP,
        NOTIFICATION-GROUP
            FROM SNMPv2-CONF
        DisplayString,
        TEXTUAL-CONVENTION,
        TimeStamp
            FROM SNMPv2-TC
        qtechMgmt
            FROM QTECH-SMI;

    qtechSmmMIB MODULE-IDENTITY
        LAST-UPDATED "201212100000Z"
        ORGANIZATION
            "Qtech Networks Co.,Ltd."
        CONTACT-INFO
            "Tel: 4008-111-000
             E-mail: service@qtech.com.cn"
        DESCRIPTION
            "The MIB is designed to get SMM statistic information of 3G router.
            With this MIB, we can get information of a certain 3G user or all users."
        REVISION      "201212100000Z"
        DESCRIPTION
                "Initial version of this MIB module."
        ::= { qtechMgmt 120 }

    qtechSmmObjects OBJECT IDENTIFIER ::= { qtechSmmMIB 1 }
    qtechSmmTrapObjects OBJECT IDENTIFIER ::= { qtechSmmMIB 2 }
    qtechSmmTraps OBJECT IDENTIFIER ::= { qtechSmmMIB 3 }

-- ===============================================
-- Begin the scalar parameters
-- ===============================================
    qtechReportSimBillSwitch OBJECT-TYPE
        SYNTAX Unsigned32
        MAX-ACCESS read-write
        STATUS current
        DESCRIPTION
            "The switch of reporting sim bill."
        ::= { qtechSmmObjects 1 }

    qtechQuerySimBillCmd OBJECT-TYPE
        SYNTAX OCTET STRING (SIZE (0..256))
        MAX-ACCESS read-write
        STATUS current
        DESCRIPTION
            "The cmd of query sim bill"
        ::= { qtechSmmObjects 2 }

-- ===============================================
-- Begin the table of qtechSmsUseTable.
-- ===============================================
    qtechSmsUseTable OBJECT-TYPE
        SYNTAX SEQUENCE OF QtechSmsUseEntry
        MAX-ACCESS not-accessible
        STATUS current
        DESCRIPTION
            "The statistic information of sms."
        ::= { qtechSmmObjects 3 }

    qtechSmsUseEntry OBJECT-TYPE
        SYNTAX QtechSmsUseEntry
        MAX-ACCESS not-accessible
        STATUS current
        DESCRIPTION
            "The statistic information of sms."
        INDEX { qtechSimImsi }
        ::= { qtechSmsUseTable 1 }

    QtechSmsUseEntry ::=
        SEQUENCE {
            qtechSimImsi
                DisplayString,
            qtechSmsUseCnt
           	    Unsigned32
        }

    qtechSimImsi OBJECT-TYPE
        SYNTAX DisplayString (SIZE (0..20))
        MAX-ACCESS read-only
        STATUS current
        DESCRIPTION
            "The imsi of sim card."
        ::= { qtechSmsUseEntry 1 }

    qtechSmsUseCnt OBJECT-TYPE
        SYNTAX Unsigned32
        MAX-ACCESS read-only
        STATUS current
        DESCRIPTION
            "The sms count of using"
        ::= { qtechSmsUseEntry 2 }

-- ===============================================
-- Begin the trap bindvar.
-- ===============================================
    qtechSimBillTrapObjects OBJECT IDENTIFIER ::= { qtechSmmTrapObjects 1 }
    qtechQuerySimBillContent OBJECT-TYPE
        SYNTAX OCTET STRING (SIZE (0..1024))
        MAX-ACCESS accessible-for-notify
        STATUS current
        DESCRIPTION
            "The sim bill content of query "
        ::= { qtechSimBillTrapObjects 1 }

    qtechReportSimBillContent OBJECT-TYPE
        SYNTAX OCTET STRING (SIZE (0..1024))
        MAX-ACCESS accessible-for-notify
        STATUS current
        DESCRIPTION
            "The sim bill content of report "
        ::= { qtechSimBillTrapObjects 2 }


-- ===============================================
-- Begin the qtechSimBillTrap.
-- ===============================================
	qtechSimBillNotifications OBJECT IDENTIFIER ::= { qtechSmmTraps 1 }
    qtechQuerySimBill NOTIFICATION-TYPE
        OBJECTS { qtechQuerySimBillContent }
        STATUS current
        DESCRIPTION
            "This notification is sim bill content of query."
        ::= { qtechSimBillNotifications 1 }

    qtechReportSimBill NOTIFICATION-TYPE
        OBJECTS { qtechReportSimBillContent }
        STATUS current
        DESCRIPTION
            "This notification is sim bill content of report."
        ::= { qtechSimBillNotifications 2 }



END
