-- *****************************************************************
-- QTECH-CAPWAP-MULTICAST6-MIB.mib:  Qtech CAPWAP MULTICAST6 MIB file
--
-- May 2010, xieweiwu
--
-- Copyright (c) 2010 by Qtech Networks Co.,Ltd.
-- All rights reserved.
--
-- *****************************************************************
--

QTECH-CAPWAP-MULTICAST6-MIB DEFINITIONS ::= BEGIN

IMPORTS
        MODULE-IDENTITY,
        OBJECT-TYPE
                FROM SNMPv2-SMI
		    InetAddress
		            FROM INET-ADDRESS-MIB
        MODULE-COMPLIANCE,
        OBJECT-GROUP
                FROM SNMPv2-CONF
        qtechMgmt
                FROM QTECH-SMI;

qtechCapwapMulticast6MIB MODULE-IDENTITY
        LAST-UPDATED "201005200000Z"
        ORGANIZATION "Qtech Networks Co.,Ltd."
        CONTACT-INFO
                "
                Tel: 4008-111-000

                E-mail: service@qtech.com.cn"
        DESCRIPTION
                "This module defines qtech Capwap Multicast6 mibs."
        REVISION      "201005200000Z"
        DESCRIPTION
                "Initial version of this MIB module."
        ::= { qtechMgmt 85}

qtechCapwapMulticast6MIBObjects OBJECT IDENTIFIER ::= { qtechCapwapMulticast6MIB 1 }


--capwap multicast6 mode
qtechCapwapMulticast6WorkingMode OBJECT-TYPE
        SYNTAX INTEGER {
            disabled(1),   -- Multicast6 mode disable
            unicast(2),    -- Working in capwap unicast(2),
            multicast(3)    -- Working in capwap multicast(3)
        }
        MAX-ACCESS read-write
        STATUS current
        DESCRIPTION
            "System Multicast6 working mode:
             disabled(1):
                Multicast6 mode disable, and all MLD report or leave
                message will be discard.
             unicast(2):
                Working in capwap unicast.
             multicast(3):
                Working in capwap multicast."
        DEFVAL { disabled }
        ::= { qtechCapwapMulticast6MIBObjects 1 }

--show capwap multicast6 group address
qtechCapwapMulticast6Group OBJECT-TYPE
        SYNTAX InetAddress
        MAX-ACCESS read-write
        STATUS current
        DESCRIPTION
            "the address of capwap multicast"
        ::= { qtechCapwapMulticast6MIBObjects 2 }

qtechCapwapMulticast6MIBConformance OBJECT IDENTIFIER ::= { qtechCapwapMulticast6MIB 2 }
qtechCapwapMulticast6MIBCompliances OBJECT IDENTIFIER ::= { qtechCapwapMulticast6MIBConformance 1 }
qtechCapwapMulticast6MIBGroups      OBJECT IDENTIFIER ::= { qtechCapwapMulticast6MIBConformance 2 }


-- compliance statements

qtechCapwapMulticast6MIBCompliance MODULE-COMPLIANCE
        STATUS  current
        DESCRIPTION
                "The compliance statement for entities which implement
                the Qtech Capwap Multicast6 MIB"
        MODULE  -- this module
                MANDATORY-GROUPS { qtechCapwapMulticast6MIBGroup
                 }
        ::= { qtechCapwapMulticast6MIBCompliances 1 }

-- units of conformance

qtechCapwapMulticast6MIBGroup OBJECT-GROUP
        OBJECTS {
           qtechCapwapMulticast6WorkingMode,
           qtechCapwapMulticast6Group
        }
        STATUS  current
        DESCRIPTION
                "A collection of objects providing CapwapMulticast6 configure ."
        ::= { qtechCapwapMulticast6MIBGroups 1 }

END
