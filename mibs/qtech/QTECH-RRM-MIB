-- *******************************************************************
-- QTECH-RRM-MIB.mib : Qtech RRM MIB file
-- November 2009, chenmingjin
--
-- Copyright (c) 2009 by Qtech Networks Co.,Ltd.
-- All rights reserved.
-- *******************************************************************

QTECH-RRM-MIB DEFINITIONS ::= BEGIN

IMPORTS
        IpAddress,
        OBJECT-TYPE,
        MODULE-IDENTITY,
        NOTIFICATION-TYPE,
        Integer32,
        Unsigned32
                FROM SNMPv2-SMI
        MacAddress,
        DisplayString,
        TruthValue
                FROM SNMPv2-TC
        NOTIFICATION-GROUP,
        MODULE-COMPLIANCE,
        OBJECT-GROUP
                FROM SNMPv2-CONF
        qtechMgmt
                FROM QTECH-SMI;

--********************************************************************
--  MODULE IDENTITY
--********************************************************************

qtechRrmMIB MODULE-IDENTITY
    LAST-UPDATED "200912150000Z"
    ORGANIZATION "Qtech Networks Co.,Ltd."
    CONTACT-INFO
        "
    Tel: 4008-111-000

    E-mail: service@qtech.com.cn"
    DESCRIPTION
        "This module defines wlan rrm mibs."
    REVISION      "200912150000Z"
    DESCRIPTION
        "Initial version of this MIB module."
    ::= { qtechMgmt 63 }


--********************** define the Rrm root nodes ***************************
qtechRrmMIBObjects     OBJECT IDENTIFIER     ::= { qtechRrmMIB 1 }
qtechRrmMIBTraps       OBJECT IDENTIFIER     ::= { qtechRrmMIB 2 }
qtechRrmMIBConformance OBJECT IDENTIFIER     ::= { qtechRrmMIB 3 }


--***************** define the qtechRrmMIBObjects nodes *********************
qtechRrmObjectsGroup   OBJECT IDENTIFIER      ::= { qtechRrmMIBObjects 1 }
qtechRrmObjectsDot11a  OBJECT IDENTIFIER      ::= { qtechRrmMIBObjects 2 }
qtechRrmObjectsDot11b  OBJECT IDENTIFIER      ::= { qtechRrmMIBObjects 3 }
qtechRrmObjectsAP     	OBJECT IDENTIFIER      ::= { qtechRrmMIBObjects 4 }

--***************** define the qtechRrmObjectsDot11a nodes *****************
qtechRrmDCADot11a      OBJECT IDENTIFIER      ::= { qtechRrmObjectsDot11a 1 }
qtechRrmTPCDot11a      OBJECT IDENTIFIER      ::= { qtechRrmObjectsDot11a 2 }
qtechRrmCHDDot11a      OBJECT IDENTIFIER      ::= { qtechRrmObjectsDot11a 3 }
qtechRrmGroupDot11a    OBJECT IDENTIFIER      ::= { qtechRrmObjectsDot11a 4 }
qtechRrmProfileDot11a  OBJECT IDENTIFIER      ::= { qtechRrmObjectsDot11a 5 }
qtechRrmMonitorDot11a  OBJECT IDENTIFIER      ::= { qtechRrmObjectsDot11a 6 }
qtechRrmFactoryDot11a  OBJECT IDENTIFIER      ::= { qtechRrmObjectsDot11a 7 }

--***************** define the qtechRrmObjectsDot11a nodes *****************
qtechRrmDCADot11b      OBJECT IDENTIFIER      ::= { qtechRrmObjectsDot11b 1 }
qtechRrmTPCDot11b      OBJECT IDENTIFIER      ::= { qtechRrmObjectsDot11b 2 }
qtechRrmCHDDot11b      OBJECT IDENTIFIER      ::= { qtechRrmObjectsDot11b 3 }
qtechRrmGroupDot11b    OBJECT IDENTIFIER      ::= { qtechRrmObjectsDot11b 4 }
qtechRrmProfileDot11b  OBJECT IDENTIFIER      ::= { qtechRrmObjectsDot11b 5 }
qtechRrmMonitorDot11b  OBJECT IDENTIFIER      ::= { qtechRrmObjectsDot11b 6 }
qtechRrmFactoryDot11b  OBJECT IDENTIFIER      ::= { qtechRrmObjectsDot11b 7 }


--********************************************************************
--                                                                  **
--                           Rf group name                          **
--                                                                  **
--********************************************************************

qtechRrmRFNetworkName OBJECT-TYPE
    SYNTAX      DisplayString (SIZE(1..19))
    MAX-ACCESS  read-write
    STATUS      current
    DESCRIPTION
        "RF Network Group Name to which this Qtech Switch belongs.
         Airespace Switches on a network form a RF Network Group as
         well as a Mobility Group. RF Network Groups does the channel
         and power management of AP while Mobility Group does load
         balancing and hand off for clients."
    ::= { qtechRrmObjectsGroup 1 }


--********************************************************************
--                                                                  **
--                       AP Profile Display                         **
--                                                                  **
--********************************************************************
ProfileState ::= INTEGER { pass (1), fail (0) }

qtechRrmAPIfSlotId OBJECT-TYPE
    SYNTAX 			INTEGER(1..32)
    MAX-ACCESS 	read-only
    STATUS 			current
    DESCRIPTION
        		"Number of Radio Interfaces on the Airespace AP.
         		Currently maximum two interfaces are supported.
         		One would be of type 802.11a and other of type
         		802.11b/g."
    ::= {  qtechRrmObjectsAP 1 }

qtechRrmAPName OBJECT-TYPE
    SYNTAX 			DisplayString (SIZE(1..32))
    MAX-ACCESS 	read-only
    STATUS 			current
    DESCRIPTION
        		"Name assigned to this AP. If an AP is not configured its
         		factory default name will be ap:<last three byte of
         		MACAddress> eg. ap:af:12:be"
    ::= { qtechRrmObjectsAP 2 }


--********************************************************************
-- * Begin of qtechRrmAPIfProfileThresholdConfigTable
--********************************************************************

qtechRrmAPIfProfileThresholdConfigTable OBJECT-TYPE
		SYNTAX 			SEQUENCE OF QtechRrmAPIfProfileThresholdConfigEntry
		MAX-ACCESS 	not-accessible
		STATUS 			current
		DESCRIPTION
        		"Table of attributes for various thresholds to be
         		set on each Airespace AP Interface for Load
        		performance profile , interference performance
        		profile and Noise performance profile."
		::= { qtechRrmObjectsAP 3 }

qtechRrmAPIfProfileThresholdConfigEntry OBJECT-TYPE
		SYNTAX 			QtechRrmAPIfProfileThresholdConfigEntry
 		MAX-ACCESS 	not-accessible
  	STATUS 			current
  	DESCRIPTION
         		"An entry (conceptual row) in the Phy Thresholds
          	Table. Entries in this MIB are indexed by
        		qtechRrmAPDot3MacAddress and qtechRrmAPIfSlotId"
   	INDEX { qtechRrmAPIfThresholdMacAddr, qtechRrmAPIfThresholdRadioType }
    ::= { qtechRrmAPIfProfileThresholdConfigTable 1 }

QtechRrmAPIfProfileThresholdConfigEntry ::=
     	SEQUENCE {
     				qtechRrmAPIfThresholdMacAddr    MacAddress,
            qtechRrmAPIfThresholdRadioType  INTEGER,
            qtechRrmAPIfThresholdName DisplayString,
            qtechRrmAPIfForeignInterferenceThreshold INTEGER,
            qtechRrmAPIfForeignNoiseThreshold        INTEGER,
            qtechRrmAPIfRFUtilizationThreshold       INTEGER,
            qtechRrmAPIfThroughputThreshold          Unsigned32,
            qtechRrmAPIfMobilesThreshold             INTEGER,
            qtechRrmAPIfForeignGlobalConfig          INTEGER,
            qtechRrmAPIfNoiseGlobalConfig            INTEGER,
            qtechRrmAPIfRFUtilizationGlobalConfig    INTEGER,
            qtechRrmAPIfThroughputGlobalConfig       INTEGER,
            qtechRrmAPIfMobilesGlobalConfig          INTEGER
		}

qtechRrmAPIfThresholdRadioType OBJECT-TYPE
    SYNTAX 			INTEGER {type80211a(0),type80211b(1)}
    MAX-ACCESS 	read-only
    STATUS 			current
    DESCRIPTION
      			"radio type, type 802.11b means 2.4GHz, type 802.11a means 5GHz,"
		::= {qtechRrmAPIfProfileThresholdConfigEntry 1 }

qtechRrmAPIfForeignInterferenceThreshold OBJECT-TYPE
    SYNTAX 			INTEGER(1..100)
    MAX-ACCESS 	read-write
    STATUS 			current
    DESCRIPTION
      			"foreign interference threshold between 1 and 100 percent."
		::= {qtechRrmAPIfProfileThresholdConfigEntry 2 }

qtechRrmAPIfForeignNoiseThreshold OBJECT-TYPE
    SYNTAX 			INTEGER(-127..0)
    MAX-ACCESS 	read-write
    STATUS 			current
    DESCRIPTION
     				"foreign noise threshold between -127 and 0 dBm."
   	::= {qtechRrmAPIfProfileThresholdConfigEntry 3 }

qtechRrmAPIfRFUtilizationThreshold OBJECT-TYPE
    SYNTAX 			INTEGER(1..100)
    MAX-ACCESS 	read-write
    STATUS 			current
    DESCRIPTION
    				"RF utlization threshold between 1 and 100 percent."
		::= {qtechRrmAPIfProfileThresholdConfigEntry 4 }

qtechRrmAPIfThroughputThreshold OBJECT-TYPE
    SYNTAX 			Unsigned32(1000..10000000)
    MAX-ACCESS 	read-write
    STATUS 			current
    DESCRIPTION
    				" Airespace AP data-rate threshold between 1000 and 1000000000."
		::= {qtechRrmAPIfProfileThresholdConfigEntry 5 }

qtechRrmAPIfMobilesThreshold OBJECT-TYPE
    SYNTAX 			INTEGER(1..128)
    MAX-ACCESS 	read-write
    STATUS 			current
    DESCRIPTION
    				" Airespace AP mobiles threshold between 1 and 128."
		::= {qtechRrmAPIfProfileThresholdConfigEntry 6 }

qtechRrmAPIfThresholdName OBJECT-TYPE
    SYNTAX 			DisplayString (SIZE(1..32))
    MAX-ACCESS 	read-only
    STATUS 			current
    DESCRIPTION
        		"The name of the AP"
    ::= { qtechRrmAPIfProfileThresholdConfigEntry 7 }

qtechRrmAPIfThresholdMacAddr OBJECT-TYPE
    SYNTAX      MacAddress
    MAX-ACCESS  read-only
    STATUS      current
    DESCRIPTION
            "The MAC address of radio on the AP"
    ::= { qtechRrmAPIfProfileThresholdConfigEntry 8 }

qtechRrmAPIfForeignGlobalConfig OBJECT-TYPE
    SYNTAX 			INTEGER(0..1)
    MAX-ACCESS  read-write
    STATUS      current
    DESCRIPTION
            "Interference threshold inherited from global or not, 1: global config, 0: ap config"
    ::= { qtechRrmAPIfProfileThresholdConfigEntry 9 }

qtechRrmAPIfNoiseGlobalConfig OBJECT-TYPE
    SYNTAX 			INTEGER(0..1)
    MAX-ACCESS  read-write
    STATUS      current
    DESCRIPTION
            "Noise threshold inherited from global or not, 1: global config, 0: ap config"
    ::= { qtechRrmAPIfProfileThresholdConfigEntry 10 }

qtechRrmAPIfRFUtilizationGlobalConfig OBJECT-TYPE
    SYNTAX 			INTEGER(0..1)
    MAX-ACCESS  read-write
    STATUS      current
    DESCRIPTION
            "RFUtilization threshold inherited from global or not, 1: global config, 0: ap config"
    ::= { qtechRrmAPIfProfileThresholdConfigEntry 11 }

qtechRrmAPIfThroughputGlobalConfig OBJECT-TYPE
    SYNTAX 			INTEGER(0..1)
    MAX-ACCESS  read-write
    STATUS      current
    DESCRIPTION
            "Throughput threshold inherited from global or not, 1: global config, 0: ap config"
    ::= { qtechRrmAPIfProfileThresholdConfigEntry 12 }

qtechRrmAPIfMobilesGlobalConfig OBJECT-TYPE
    SYNTAX 			INTEGER(0..1)
    MAX-ACCESS  read-write
    STATUS      current
    DESCRIPTION
            "Mobiles threshold inherited from global or not, 1: global config, 0: ap config"
    ::= { qtechRrmAPIfProfileThresholdConfigEntry 13 }

--********************************************************************
-- * Begin of qtechRrmAPIfLoadParametersTable
--********************************************************************
qtechRrmAPIfLoadParametersTable OBJECT-TYPE
		SYNTAX 			SEQUENCE OF QtechRrmAPIfLoadParametersEntry
		MAX-ACCESS 	not-accessible
		STATUS 			current
		DESCRIPTION
        		"These are RRM performance related read only parameters
        		per Airespace AP"
		::= { qtechRrmObjectsAP 4 }

qtechRrmAPIfLoadParametersEntry OBJECT-TYPE
		SYNTAX 			QtechRrmAPIfLoadParametersEntry
		MAX-ACCESS 	not-accessible
		STATUS 			current
		DESCRIPTION
          	"An entry (conceptual row) in the Table.
          	Entries in this MIB are indexed by
         	qtechRrmAPDot3MacAddress and qtechRrmAPIfSlotId"
 		INDEX { qtechRrmAPIfLoadMacAddr, qtechRrmAPIfLoadSlotId }
 		::= { qtechRrmAPIfLoadParametersTable 1 }

QtechRrmAPIfLoadParametersEntry ::=
  	SEQUENCE {
  	    qtechRrmAPIfLoadName DisplayString,
        qtechRrmAPIfLoadMacAddr MacAddress,
        qtechRrmAPIfLoadSlotId INTEGER,
     		qtechRrmAPIfLoadRxUtilization        INTEGER,
   			qtechRrmAPIfLoadTxUtilization        INTEGER,
  			qtechRrmAPIfLoadChannelUtilization   INTEGER,
   			qtechRrmAPIfLoadNumOfClients         Integer32,
   			qtechRrmAPIfPoorSNRClients           Integer32,
   			qtechRrmAPIfThroughput		      INTEGER
		}

qtechRrmAPIfLoadRxUtilization OBJECT-TYPE
		SYNTAX 			INTEGER(0..100)
		MAX-ACCESS 	read-only
		STATUS 			current
		DESCRIPTION
      			"This is the percentage of time the Airespace AP
        		receiver is busy operating on packets. It is a number
       			from 0-100 representing a load from 0 to 1."
		::= { qtechRrmAPIfLoadParametersEntry 1 }

qtechRrmAPIfLoadTxUtilization OBJECT-TYPE
 		SYNTAX 			INTEGER(0..100)
		MAX-ACCESS 	read-only
		STATUS 			current
		DESCRIPTION
      			"This is the percentage of time the Airespace AP
         		transmitter is busy operating on packets. It is a
       			number from 0-100 representing a load from 0 to 1."
		::= { qtechRrmAPIfLoadParametersEntry 2 }

qtechRrmAPIfLoadChannelUtilization OBJECT-TYPE
    SYNTAX 			INTEGER(0..100)
    MAX-ACCESS 	read-only
    STATUS 			current
    DESCRIPTION
            "Channel Utilization"
    ::= { qtechRrmAPIfLoadParametersEntry 3 }

qtechRrmAPIfLoadNumOfClients OBJECT-TYPE
		SYNTAX 			Integer32
   	MAX-ACCESS 	read-only
   	STATUS 			current
   	DESCRIPTION
         		"This is the number of clients attached to this Airespace
        		AP at the last measurement interval(This comes from
        		APF)"
    ::= { qtechRrmAPIfLoadParametersEntry 4 }

qtechRrmAPIfPoorSNRClients OBJECT-TYPE
		SYNTAX 			Integer32
		MAX-ACCESS 	read-only
		STATUS 			current
		DESCRIPTION
           	"This is the number of clients with poor SNR attached to
          	this Airespace AP at the last measurement interval
          	( This comes from APF )."
		::= { qtechRrmAPIfLoadParametersEntry 5 }

qtechRrmAPIfLoadName OBJECT-TYPE
    SYNTAX 			DisplayString (SIZE(1..32))
    MAX-ACCESS 	read-only
    STATUS 			current
    DESCRIPTION
        		"The name of the AP"
    ::= { qtechRrmAPIfLoadParametersEntry 6 }

qtechRrmAPIfLoadMacAddr OBJECT-TYPE
    SYNTAX      MacAddress
    MAX-ACCESS  read-only
    STATUS      current
    DESCRIPTION
            "The MAC address of radio on the AP"
    ::= { qtechRrmAPIfLoadParametersEntry 7 }

qtechRrmAPIfLoadSlotId OBJECT-TYPE
    SYNTAX 			INTEGER(1..32)
    MAX-ACCESS 	read-only
    STATUS 			current
    DESCRIPTION
        		"Number of Radio Interfaces on the Airespace AP.
         		Currently maximum two interfaces are supported.
         		One would be of type 802.11a and other of type
         		802.11b/g."
    ::= {  qtechRrmAPIfLoadParametersEntry 8 }

qtechRrmAPIfThroughput OBJECT-TYPE
    SYNTAX 			INTEGER
    MAX-ACCESS 	read-only
    STATUS 			current
    DESCRIPTION
        		"Throughput in ap's radio, it represent the performance of
        		ap"
    ::= {  qtechRrmAPIfLoadParametersEntry 9 }


--********************************************************************
-- * Begin of qtechRrmAPIfChannelInterferenceInfoTable
--********************************************************************

qtechRrmAPIfChannelInterferenceInfoTable OBJECT-TYPE
		SYNTAX 			SEQUENCE OF QtechRrmAPIfChannelInterferenceInfoEntry
		MAX-ACCESS 	not-accessible
		STATUS 			current
		DESCRIPTION
         		"This is a table of channel information like interference
         		and noise from other 802.11 networks on each channel."
		::= { qtechRrmObjectsAP 5 }

qtechRrmAPIfChannelInterferenceInfoEntry OBJECT-TYPE
 		SYNTAX 			QtechRrmAPIfChannelInterferenceInfoEntry
 		MAX-ACCESS 	not-accessible
  	STATUS 			current
		DESCRIPTION
        		"An entry (conceptual row) in the Table.
          	Entries in this MIB are indexed by
        		qtechRrmAPDot3MacAddress, qtechRrmAPIfSlotId"
		INDEX { qtechRrmAPIfInterferenceMacAddr, qtechRrmAPIfInterferenceSlotId,
                qtechRrmAPIfInterferenceChannelNo}
		::= { qtechRrmAPIfChannelInterferenceInfoTable 1 }

QtechRrmAPIfChannelInterferenceInfoEntry ::=
    SEQUENCE {
        qtechRrmAPIfInterferenceName DisplayString,
        qtechRrmAPIfInterferenceMacAddr MacAddress,
        qtechRrmAPIfInterferenceSlotId INTEGER,
    		qtechRrmAPIfInterferenceChannelNo     		Integer32,
    		qtechRrmAPIfInterferencePower         		Integer32,
    		qtechRrmAPIfInterferenceUtilization   		INTEGER
    }

qtechRrmAPIfInterferenceChannelNo OBJECT-TYPE
  	SYNTAX 			Integer32
   	MAX-ACCESS 	read-only
   	STATUS 			current
   	DESCRIPTION
           	"Channel Number on AP"
    ::= { qtechRrmAPIfChannelInterferenceInfoEntry 1}

qtechRrmAPIfInterferencePower OBJECT-TYPE
		SYNTAX 			Integer32
		MAX-ACCESS 	read-only
		STATUS 			current
		DESCRIPTION
		       "Power of Interference from other 802.11 networks on
		        this channel"
		::= { qtechRrmAPIfChannelInterferenceInfoEntry 2}

qtechRrmAPIfInterferenceUtilization OBJECT-TYPE
		SYNTAX 			INTEGER(0..100)
		MAX-ACCESS 	read-only
		STATUS 			current
		DESCRIPTION
						"Interference from other 802.11 networks on this
		        channel"
		::= { qtechRrmAPIfChannelInterferenceInfoEntry 3}

qtechRrmAPIfInterferenceName OBJECT-TYPE
    SYNTAX 			DisplayString (SIZE(1..32))
    MAX-ACCESS 	read-only
    STATUS 			current
    DESCRIPTION
        		"The name of the AP"
    ::= { qtechRrmAPIfChannelInterferenceInfoEntry 4 }

qtechRrmAPIfInterferenceMacAddr OBJECT-TYPE
    SYNTAX      MacAddress
    MAX-ACCESS  read-only
    STATUS      current
    DESCRIPTION
            "The MAC address of radio on the AP"
    ::= { qtechRrmAPIfChannelInterferenceInfoEntry 5 }

qtechRrmAPIfInterferenceSlotId OBJECT-TYPE
    SYNTAX 			INTEGER(1..32)
    MAX-ACCESS 	read-only
    STATUS 			current
    DESCRIPTION
        		"Number of Radio Interfaces on the Airespace AP.
         		Currently maximum two interfaces are supported.
         		One would be of type 802.11a and other of type
         		802.11b/g."
    ::= {  qtechRrmAPIfChannelInterferenceInfoEntry 6 }

--********************************************************************
-- * Begin of qtechRrmAPIfChannelNoiseInfoTable
--********************************************************************
qtechRrmAPIfChannelNoiseInfoTable OBJECT-TYPE
		SYNTAX 			SEQUENCE OF QtechRrmAPIfChannelNoiseInfoEntry
		MAX-ACCESS 	not-accessible
		STATUS 			current
		DESCRIPTION
          	"This is a table of channel information like
         		interference and noise from other 802.11 networks on
          	each channel."
		::= { qtechRrmObjectsAP 6 }

qtechRrmAPIfChannelNoiseInfoEntry OBJECT-TYPE
  	SYNTAX QtechRrmAPIfChannelNoiseInfoEntry
  	MAX-ACCESS not-accessible
 		STATUS current
 		DESCRIPTION
          	"An entry (conceptual row) in the Table.
           	Entries in this MIB are indexed by qtechRrmAPDot3MacAddress,
           	qtechRrmAPIfSlotId"
  	INDEX { qtechRrmAPIfNoiseMacAddr, qtechRrmAPIfNoiseSlotId,
               qtechRrmAPIfNoiseChannelNo }
 		::= { qtechRrmAPIfChannelNoiseInfoTable 1 }

QtechRrmAPIfChannelNoiseInfoEntry ::=
		SEQUENCE {
		    qtechRrmAPIfNoiseName DisplayString,
        qtechRrmAPIfNoiseMacAddr MacAddress,
        qtechRrmAPIfNoiseSlotId INTEGER,
     		qtechRrmAPIfNoiseChannelNo         	Integer32,
 				qtechRrmAPIfDBNoisePower          		Integer32
		}

qtechRrmAPIfNoiseChannelNo OBJECT-TYPE
		SYNTAX 			Integer32
 		MAX-ACCESS 	read-only
   	STATUS 			current
  	DESCRIPTION
           	"Channel Number on AP"
    ::= { qtechRrmAPIfChannelNoiseInfoEntry 1 }

qtechRrmAPIfDBNoisePower OBJECT-TYPE
 		SYNTAX 			Integer32
		MAX-ACCESS 	read-only
		STATUS 			current
		DESCRIPTION
        		"This is the average noise power in dBm on
          	each channel that is available to Airespace AP"
    ::= { qtechRrmAPIfChannelNoiseInfoEntry 2 }

qtechRrmAPIfNoiseName OBJECT-TYPE
    SYNTAX 			DisplayString (SIZE(1..32))
    MAX-ACCESS 	read-only
    STATUS 			current
    DESCRIPTION
        		"The name of the AP"
    ::= { qtechRrmAPIfChannelNoiseInfoEntry 3 }

qtechRrmAPIfNoiseMacAddr OBJECT-TYPE
    SYNTAX      MacAddress
    MAX-ACCESS  read-only
    STATUS      current
    DESCRIPTION
            "The MAC address of radio on the AP"
    ::= { qtechRrmAPIfChannelNoiseInfoEntry 4 }

qtechRrmAPIfNoiseSlotId OBJECT-TYPE
    SYNTAX 			INTEGER(1..32)
    MAX-ACCESS 	read-only
    STATUS 			current
    DESCRIPTION
        		"Number of Radio Interfaces on the Airespace AP.
         		Currently maximum two interfaces are supported.
         		One would be of type 802.11a and other of type
         		802.11b/g."
    ::= {  qtechRrmAPIfChannelNoiseInfoEntry 5 }

--********************************************************************
-- * Begin of qtechRrmAPIfProfileStateTable
--********************************************************************

qtechRrmAPIfProfileStateTable OBJECT-TYPE
		SYNTAX 			SEQUENCE OF QtechRrmAPIfProfileStateEntry
		MAX-ACCESS 	not-accessible
		STATUS 			current
		DESCRIPTION
		        "This is a table of state of interference monitor
		         on each Airespace AP"
		::= { qtechRrmObjectsAP 7 }

qtechRrmAPIfProfileStateEntry OBJECT-TYPE
		SYNTAX 			QtechRrmAPIfProfileStateEntry
		MAX-ACCESS 	not-accessible
		STATUS 			current
		DESCRIPTION
		       "An entry (conceptual row) in the Table.
		        Entries in this MIB are indexed by qtechRrmAPDot3MacAddress,
		        qtechRrmAPIfSlotId"
		INDEX { qtechRrmAPIfProfileMacAddr, qtechRrmAPIfProfileSlotId }
		::= { qtechRrmAPIfProfileStateTable 1 }

QtechRrmAPIfProfileStateEntry ::=
		SEQUENCE {
		    qtechRrmAPIfProfileName DisplayString,
        qtechRrmAPIfProfileMacAddr MacAddress,
        qtechRrmAPIfProfileSlotId INTEGER,
        qtechRrmAPIfLoadProfileState          	ProfileState,
        qtechRrmAPIfInterferenceProfileState 	ProfileState,
        qtechRrmAPIfNoiseProfileState         	ProfileState,
        qtechRrmAPIfCoverageProfileState      	ProfileState,
        qtechRrmAPIfPerformanceProfileState 		ProfileState
		}

qtechRrmAPIfLoadProfileState OBJECT-TYPE
		SYNTAX 			ProfileState
		MAX-ACCESS 	read-only
		STATUS 			current
		DESCRIPTION
		        "This field represents the current state of the LOAD
		         monitor. This is a total measurement of the business of
		         this Airespace AP. PASS indicates that this Airespace
		         AP is performing adequately compared to the Airespace
		         AP profile. FAIL indicates the Airespace AP is not
		         performing adequately against the LOAD profile."
		::= { qtechRrmAPIfProfileStateEntry 1 }


qtechRrmAPIfInterferenceProfileState OBJECT-TYPE
		SYNTAX 			ProfileState
		MAX-ACCESS 	read-only
		STATUS 			current
		DESCRIPTION
		       "This field represents the current state of Interference
		        monitor. This is a total measurement of the interference
		        present at this Airespace AP. PASS indicates that this
		        Airespace AP is performing adequately compared to the
		        Interference profile.  FAIL indicates the Airespace AP
		        is not performing adequately against the Interference
		        profile."
		::= { qtechRrmAPIfProfileStateEntry 2 }

qtechRrmAPIfNoiseProfileState OBJECT-TYPE
		SYNTAX 			ProfileState
		MAX-ACCESS 	read-only
		STATUS 			current
		DESCRIPTION
						"This field represents the current state of Noise
						monitor. This is a total measurement of the noise
						present at this Airespace AP. PASS indicates that this
						Airespace AP is performing adequately compared to the
						noise profile.
						FAIL indicates the Airespace AP is not performing
						adequately against the noise profile."
		::= { qtechRrmAPIfProfileStateEntry 3 }

qtechRrmAPIfCoverageProfileState OBJECT-TYPE
		SYNTAX 			ProfileState
		MAX-ACCESS 	read-only
		STATUS 			current
		DESCRIPTION
		       "This field represents the current state of coverage
		        monitor. This is a total measurement of the client
		        coverage at this Airespace AP. PASS indicates that
		        this  Airespace AP is performing adequately compared
		        to the  coverage profile. FAIL indicates the Airespace
		        AP is not performing adequately against the coverage
		        profile."
		::= { qtechRrmAPIfProfileStateEntry 4}

qtechRrmAPIfPerformanceProfileState OBJECT-TYPE
		SYNTAX 			ProfileState
		MAX-ACCESS 	read-only
		STATUS 			current
		DESCRIPTION
		       ""
		::= { qtechRrmAPIfProfileStateEntry 5}

qtechRrmAPIfProfileName OBJECT-TYPE
    SYNTAX 			DisplayString (SIZE(1..32))
    MAX-ACCESS 	read-only
    STATUS 			current
    DESCRIPTION
        		"The name of the AP"
    ::= { qtechRrmAPIfProfileStateEntry 6 }

qtechRrmAPIfProfileMacAddr OBJECT-TYPE
    SYNTAX      MacAddress
    MAX-ACCESS  read-only
    STATUS      current
    DESCRIPTION
            "The MAC address of radio on the AP"
    ::= { qtechRrmAPIfProfileStateEntry 7 }

qtechRrmAPIfProfileSlotId OBJECT-TYPE
    SYNTAX 			INTEGER(1..32)
    MAX-ACCESS 	read-only
    STATUS 			current
    DESCRIPTION
        		"Number of Radio Interfaces on the Airespace AP.
         		Currently maximum two interfaces are supported.
         		One would be of type 802.11a and other of type
         		802.11b/g."
    ::= {  qtechRrmAPIfProfileStateEntry 8 }

--********************************************************************
-- * Begin of qtechRrmAPIfRxNeighborsTable
--********************************************************************
qtechRrmAPIfRxNeighborsTable OBJECT-TYPE
		SYNTAX 			SEQUENCE OF QtechRrmAPIfRxNeighborsEntry
		MAX-ACCESS 	not-accessible
		STATUS 			current
		DESCRIPTION
		        "This is a table of Rx Neighbors for each Airespace AP
		         with their RSSI value."
		::= { qtechRrmObjectsAP 8 }

qtechRrmAPIfRxNeighborsEntry OBJECT-TYPE
		SYNTAX 			QtechRrmAPIfRxNeighborsEntry
		MAX-ACCESS 	not-accessible
		STATUS 			current
		DESCRIPTION
		        "An entry (conceptual row) in the Table.
		         Entries in this MIB are indexed by qtechRrmAPDot3MacAddress
		         qtechRrmAPIfSlotId, qtechRrmAPIfRxNeighborMacAddress"
		INDEX { qtechRrmAPIfRxNeighborMacAddr, qtechRrmAPIfRxNeighborSlotId,
		        qtechRrmAPIfRxNeighborMacAddress, qtechRrmAPIfRxNeighborSlot}
		::= { qtechRrmAPIfRxNeighborsTable 1 }

QtechRrmAPIfRxNeighborsEntry ::=
		SEQUENCE {
		    qtechRrmAPIfRxNeighborName DisplayString,
        qtechRrmAPIfRxNeighborMacAddr MacAddress,
        qtechRrmAPIfRxNeighborSlotId INTEGER,
				qtechRrmAPIfRxNeighborMacAddress          	MacAddress,
				qtechRrmAPIfRxNeighborSlot                	Integer32,
				qtechRrmAPIfRxNeighborIpAddress           	IpAddress,
				qtechRrmAPIfRxNeighborRSSI                	Integer32,
				qtechRrmAPIfRxNeighborSNR                	Integer32,
				qtechRrmAPIfRxNeighborChannel             	Integer32,
				qtechRrmAPIfRxNeighborChannelWidth        	INTEGER
		}

qtechRrmAPIfRxNeighborMacAddress OBJECT-TYPE
		SYNTAX 			MacAddress
		MAX-ACCESS 	read-only
		STATUS 			current
		DESCRIPTION
		   			"MAC Address of Rx Neighbor of the Airespace AP"
		::= { qtechRrmAPIfRxNeighborsEntry 1 }

qtechRrmAPIfRxNeighborSlot OBJECT-TYPE
		SYNTAX 			Integer32
		MAX-ACCESS 	read-only
		STATUS 			current
		DESCRIPTION
		       "Slot value of the Rx Neighbor"
		::= { qtechRrmAPIfRxNeighborsEntry 2 }

qtechRrmAPIfRxNeighborIpAddress OBJECT-TYPE
		SYNTAX 			IpAddress
		MAX-ACCESS 	read-only
		STATUS 			current
		DESCRIPTION
		       "IP Address of Rx Neighbor of the Airespace AP"
		::= { qtechRrmAPIfRxNeighborsEntry 3 }

qtechRrmAPIfRxNeighborRSSI OBJECT-TYPE
		SYNTAX 			Integer32
		MAX-ACCESS 	read-only
		STATUS 			current
		DESCRIPTION
		       "RSSI value of the Rx Neighbor"
		::= { qtechRrmAPIfRxNeighborsEntry 4 }

qtechRrmAPIfRxNeighborSNR OBJECT-TYPE
		SYNTAX 			Integer32
		MAX-ACCESS 	read-only
		STATUS 			current
		DESCRIPTION
		       "SNR value of the Rx Neighbor"
		::= { qtechRrmAPIfRxNeighborsEntry 5 }

qtechRrmAPIfRxNeighborChannel OBJECT-TYPE
		SYNTAX  		Integer32
		MAX-ACCESS 	read-only
		STATUS 			current
		DESCRIPTION
		    		"This object represents Channel information which
		     		neighboring Access point is using."
		::= { qtechRrmAPIfRxNeighborsEntry 6 }

qtechRrmAPIfRxNeighborChannelWidth OBJECT-TYPE
		SYNTAX  		INTEGER {
		           five(1),
		           ten(2),
		           twenty(3),
		           aboveforty(4),
		           belowforty(5)
		}
		MAX-ACCESS 	read-only
		STATUS 			current
		DESCRIPTION
		    		"This object represents Channel bandwidth information
		     		which neighboring Access point is using."
		::= { qtechRrmAPIfRxNeighborsEntry 7 }

qtechRrmAPIfRxNeighborName OBJECT-TYPE
    SYNTAX 			DisplayString (SIZE(1..32))
    MAX-ACCESS 	read-only
    STATUS 			current
    DESCRIPTION
        		"The name of the AP"
    ::= { qtechRrmAPIfRxNeighborsEntry 8 }

qtechRrmAPIfRxNeighborMacAddr OBJECT-TYPE
    SYNTAX      MacAddress
    MAX-ACCESS  read-only
    STATUS      current
    DESCRIPTION
            "The MAC address of radio on the AP"
    ::= { qtechRrmAPIfRxNeighborsEntry 9 }

qtechRrmAPIfRxNeighborSlotId OBJECT-TYPE
    SYNTAX 			INTEGER(1..32)
    MAX-ACCESS 	read-only
    STATUS 			current
    DESCRIPTION
        		"Number of Radio Interfaces on the Airespace AP.
         		Currently maximum two interfaces are supported.
         		One would be of type 802.11a and other of type
         		802.11b/g."
    ::= {  qtechRrmAPIfRxNeighborsEntry 10 }

-- *****************************************************************


--********************************************************************
-- * Begin of qtechRrmAPIfStationRSSICoverageInfoTable
--********************************************************************
qtechRrmAPIfStationRSSICoverageInfoTable OBJECT-TYPE
    SYNTAX 			SEQUENCE OF QtechRrmAPIfStationRSSICoverageInfoEntry
    MAX-ACCESS 	not-accessible
    STATUS 			current
    DESCRIPTION
            "This is a table of channel information like interference
             and noise from other 802.11 networks on each channel."
    ::= { qtechRrmObjectsAP 9 }

qtechRrmAPIfStationRSSICoverageInfoEntry OBJECT-TYPE
		SYNTAX 			QtechRrmAPIfStationRSSICoverageInfoEntry
		MAX-ACCESS 	not-accessible
		STATUS 			current
		DESCRIPTION
		       "An entry (conceptual row) in the Table.
		        Entries in this MIB are indexed by qtechRrmAPDot3MacAddress,
		        qtechRrmAPIfSlotId"
		INDEX { qtechRrmAPIfStationRSSIMacAddr, qtechRrmAPIfStationRSSISlotId,
		        qtechRrmAPIfStationRSSICoverageIndex}
		::= { qtechRrmAPIfStationRSSICoverageInfoTable 1 }

QtechRrmAPIfStationRSSICoverageInfoEntry ::=
		SEQUENCE {
		    qtechRrmAPIfStationRSSIName DisplayString,
        qtechRrmAPIfStationRSSIMacAddr MacAddress,
        qtechRrmAPIfStationRSSISlotId INTEGER,
				qtechRrmAPIfStationRSSICoverageIndex     Integer32,
				qtechRrmAPIfRSSILevel                    Integer32,
				qtechRrmAPIfStationCountOnRSSI           Integer32
		}

qtechRrmAPIfStationRSSICoverageIndex OBJECT-TYPE
		SYNTAX 			Integer32
		MAX-ACCESS 	read-only
		STATUS 			current
		DESCRIPTION
		       "RSSI Coverage Index on AP"
		::= { qtechRrmAPIfStationRSSICoverageInfoEntry 1 }

qtechRrmAPIfRSSILevel OBJECT-TYPE
		SYNTAX 			Integer32
		MAX-ACCESS 	read-only
		STATUS 			current
		DESCRIPTION
		       "RSSI Level"
		::= { qtechRrmAPIfStationRSSICoverageInfoEntry 2 }

qtechRrmAPIfStationCountOnRSSI OBJECT-TYPE
		SYNTAX 			Integer32
		MAX-ACCESS 	read-only
		STATUS 			current
		DESCRIPTION
		        "Number of stations on this RSSI Level"
		::= { qtechRrmAPIfStationRSSICoverageInfoEntry 3 }

qtechRrmAPIfStationRSSIName OBJECT-TYPE
    SYNTAX 			DisplayString (SIZE(1..32))
    MAX-ACCESS 	read-only
    STATUS 			current
    DESCRIPTION
        		"The name of the AP"
    ::= { qtechRrmAPIfStationRSSICoverageInfoEntry 4 }

qtechRrmAPIfStationRSSIMacAddr OBJECT-TYPE
    SYNTAX      MacAddress
    MAX-ACCESS  read-only
    STATUS      current
    DESCRIPTION
            "The MAC address of radio on the AP"
    ::= { qtechRrmAPIfStationRSSICoverageInfoEntry 5 }

qtechRrmAPIfStationRSSISlotId OBJECT-TYPE
    SYNTAX 			INTEGER(1..32)
    MAX-ACCESS 	read-only
    STATUS 			current
    DESCRIPTION
        		"Number of Radio Interfaces on the Airespace AP.
         		Currently maximum two interfaces are supported.
         		One would be of type 802.11a and other of type
         		802.11b/g."
    ::= {  qtechRrmAPIfStationRSSICoverageInfoEntry 6 }

-- ********************************************************************
-- * Begin of qtechRrmAPIfStationSNRCoverageInfoTable
-- ********************************************************************
qtechRrmAPIfStationSNRCoverageInfoTable OBJECT-TYPE
		SYNTAX 			SEQUENCE OF QtechRrmAPIfStationSNRCoverageInfoEntry
		MAX-ACCESS 	not-accessible
		STATUS 			current
		DESCRIPTION
		        "This is a table of Signal to Noise ratio Coverage
		         information on an AP Interface."
		::= { qtechRrmObjectsAP 10 }

qtechRrmAPIfStationSNRCoverageInfoEntry OBJECT-TYPE
		SYNTAX 			QtechRrmAPIfStationSNRCoverageInfoEntry
		MAX-ACCESS 	not-accessible
		STATUS 			current
		DESCRIPTION
		       "An entry (conceptual row) in the Table.
		        Entries in this MIB are indexed by qtechRrmAPDot3MacAddress,
		        qtechRrmAPIfSlotId"
		INDEX { qtechRrmAPIfStationSNRMacAddr, qtechRrmAPIfStationSNRSlotId,
		        qtechRrmAPIfStationSNRCoverageIndex}
		::= { qtechRrmAPIfStationSNRCoverageInfoTable 1 }

QtechRrmAPIfStationSNRCoverageInfoEntry ::=
		SEQUENCE {
		    qtechRrmAPIfStationSNRName DisplayString,
        qtechRrmAPIfStationSNRMacAddr MacAddress,
        qtechRrmAPIfStationSNRSlotId INTEGER,
				qtechRrmAPIfStationSNRCoverageIndex     	Integer32,
				qtechRrmAPIfSNRLevel                 		Integer32,
				qtechRrmAPIfStationCountOnSNR        		Integer32
		}

qtechRrmAPIfStationSNRCoverageIndex OBJECT-TYPE
		SYNTAX 			Integer32
		MAX-ACCESS 	read-only
		STATUS 			current
		DESCRIPTION
		       "SNR Coverage Index on AP"
    ::= { qtechRrmAPIfStationSNRCoverageInfoEntry 1}

qtechRrmAPIfSNRLevel OBJECT-TYPE
		SYNTAX 			Integer32
		MAX-ACCESS 	read-only
		STATUS 			current
		DESCRIPTION
		       "SNR Level"
		::= { qtechRrmAPIfStationSNRCoverageInfoEntry 2}

qtechRrmAPIfStationCountOnSNR OBJECT-TYPE
    SYNTAX 			Integer32
    MAX-ACCESS 	read-only
    STATUS 			current
    DESCRIPTION
          "Number of stations on this SNR Level"
    ::= { qtechRrmAPIfStationSNRCoverageInfoEntry 3}

qtechRrmAPIfStationSNRName OBJECT-TYPE
    SYNTAX 			DisplayString (SIZE(1..32))
    MAX-ACCESS 	read-only
    STATUS 			current
    DESCRIPTION
        		"The name of the AP"
    ::= { qtechRrmAPIfStationSNRCoverageInfoEntry 4 }

qtechRrmAPIfStationSNRMacAddr OBJECT-TYPE
    SYNTAX      MacAddress
    MAX-ACCESS  read-only
    STATUS      current
    DESCRIPTION
            "The MAC address of radio on the AP"
    ::= { qtechRrmAPIfStationSNRCoverageInfoEntry 5 }

qtechRrmAPIfStationSNRSlotId OBJECT-TYPE
    SYNTAX 			INTEGER(1..32)
    MAX-ACCESS 	read-only
    STATUS 			current
    DESCRIPTION
        		"Number of Radio Interfaces on the Airespace AP.
         		Currently maximum two interfaces are supported.
         		One would be of type 802.11a and other of type
         		802.11b/g."
    ::= {  qtechRrmAPIfStationSNRCoverageInfoEntry 6 }

-- ********************************************************************
-- * Begin of qtechRrmAPIfRecommendedRFParametersTable
-- ********************************************************************
qtechRrmAPIfRecommendedRFParametersTable OBJECT-TYPE
		SYNTAX 			SEQUENCE OF QtechRrmAPIfRecommendedRFParametersEntry
		MAX-ACCESS 	not-accessible
		STATUS 			current
		DESCRIPTION
		  			" This table list Best Channel,Best TxPowerLevel,
		    		Best RTSThreshold,Best FragmentationThreshold etc
		    		for this AP Interface as determined by RRM."
		::= { qtechRrmObjectsAP 11 }

qtechRrmAPIfRecommendedRFParametersEntry OBJECT-TYPE
		SYNTAX 			QtechRrmAPIfRecommendedRFParametersEntry
		MAX-ACCESS 	not-accessible
		STATUS 			current
		DESCRIPTION
		       "An entry (conceptual row) in the Table.
		        Entries in this MIB are indexed by qtechRrmAPDot3MacAddress,
		        qtechRrmAPIfSlotId"
		INDEX { qtechRrmAPIfRecommendedMacAddr, qtechRrmAPIfRecommendedSlotId}
    ::= { qtechRrmAPIfRecommendedRFParametersTable 1 }

QtechRrmAPIfRecommendedRFParametersEntry ::=
		SEQUENCE {
		    qtechRrmAPIfRecommendedName DisplayString,
        qtechRrmAPIfRecommendedMacAddr MacAddress,
        qtechRrmAPIfRecommendedSlotId INTEGER,
				qtechRrmAPIfRecommendedChannelNumber             Integer32,
				qtechRrmAPIfRecommendedTxPowerLevel              Integer32,
				qtechRrmAPIfRecommendedRTSThreshold              Integer32,
				qtechRrmAPIfRecommendedFragmentationThreshold    Integer32
		}

qtechRrmAPIfRecommendedChannelNumber OBJECT-TYPE
		SYNTAX 			Integer32
		MAX-ACCESS 	read-only
		STATUS 			current
		DESCRIPTION
		       "Recommended ChannelNumber by RRM for this APIf"
		::= { qtechRrmAPIfRecommendedRFParametersEntry 1}

qtechRrmAPIfRecommendedTxPowerLevel OBJECT-TYPE
		SYNTAX 			Integer32
		MAX-ACCESS 	read-only
		STATUS 			current
		DESCRIPTION
		       "Recommended TxPowerLevel by RRM for this APIf"
		::= { qtechRrmAPIfRecommendedRFParametersEntry 2}

qtechRrmAPIfRecommendedRTSThreshold OBJECT-TYPE
		SYNTAX 			Integer32
		MAX-ACCESS 	read-only
		STATUS 			current
		DESCRIPTION
		       "Recommended RTSThreshold by RRM for this APIf"
		::= { qtechRrmAPIfRecommendedRFParametersEntry 3}

qtechRrmAPIfRecommendedFragmentationThreshold OBJECT-TYPE
		SYNTAX 			Integer32
		MAX-ACCESS 	read-only
		STATUS 			current
		DESCRIPTION
		       "Recommended Fragmentation Threshold by RRM for this
		        APIf"
		::= { qtechRrmAPIfRecommendedRFParametersEntry 4}

qtechRrmAPIfRecommendedName OBJECT-TYPE
    SYNTAX 			DisplayString (SIZE(1..32))
    MAX-ACCESS 	read-only
    STATUS 			current
    DESCRIPTION
        		"The name of the AP"
    ::= { qtechRrmAPIfRecommendedRFParametersEntry 5 }

qtechRrmAPIfRecommendedMacAddr OBJECT-TYPE
    SYNTAX      MacAddress
    MAX-ACCESS  read-only
    STATUS      current
    DESCRIPTION
            "The MAC address of radio on the AP"
    ::= { qtechRrmAPIfRecommendedRFParametersEntry 6 }

qtechRrmAPIfRecommendedSlotId OBJECT-TYPE
    SYNTAX 			INTEGER(1..32)
    MAX-ACCESS 	read-only
    STATUS 			current
    DESCRIPTION
        		"Number of Radio Interfaces on the Airespace AP.
         		Currently maximum two interfaces are supported.
         		One would be of type 802.11a and other of type
         		802.11b/g."
    ::= {  qtechRrmAPIfRecommendedRFParametersEntry 7 }

--********************************************************************
-- * Begin of qtechRrmAPRadioTable
--********************************************************************

qtechRrmAPRadioTable OBJECT-TYPE
		SYNTAX 			SEQUENCE OF QtechRrmAPRadioEntry
		MAX-ACCESS 	not-accessible
		STATUS 			current
		DESCRIPTION
        		"ap radio table"
		::= { qtechRrmObjectsAP 12 }

qtechRrmAPRadioEntry OBJECT-TYPE
		SYNTAX 			QtechRrmAPRadioEntry
 		MAX-ACCESS 	not-accessible
  	STATUS 			current
  	DESCRIPTION
         		"all radio in aps"
   	INDEX { qtechRrmAPMacAddr, qtechRrmAPRadioID}
    ::= { qtechRrmAPRadioTable 1 }

QtechRrmAPRadioEntry ::=
 		SEQUENCE {
 						qtechRrmAPRealName  DisplayString,
            qtechRrmAPMacAddr MacAddress,
     				qtechRrmAPRadioID    INTEGER,
     				qtechRrmAPRadioType  INTEGER
		}

qtechRrmAPRadioID OBJECT-TYPE
    SYNTAX 			INTEGER(1..32)
    MAX-ACCESS 	read-only
    STATUS 			current
    DESCRIPTION
        		"Number of Radio Interfaces on the Qtech AP.
         		Currently maximum 32 interfaces are supported."
    ::= { qtechRrmAPRadioEntry 1 }

qtechRrmAPRadioType OBJECT-TYPE
    SYNTAX 			INTEGER {type80211a(0),type80211b(1)}
    MAX-ACCESS 	read-only
    STATUS 			current
    DESCRIPTION
      			"radio type, type 802.11b means 2.4GHz, type 802.11a means 5GHz,"
		::= { qtechRrmAPRadioEntry 2 }

qtechRrmAPRealName OBJECT-TYPE
    SYNTAX 			DisplayString (SIZE(1..32))
    MAX-ACCESS 	read-only
    STATUS 			current
    DESCRIPTION
        		"The name of the AP"
    ::= { qtechRrmAPRadioEntry 3 }

qtechRrmAPMacAddr OBJECT-TYPE
    SYNTAX      MacAddress
    MAX-ACCESS  read-only
    STATUS      current
    DESCRIPTION
            "The MAC address of radio on the AP"
    ::= { qtechRrmAPRadioEntry 4 }

--********************************************************************
-- * Begin of qtechRrmAPIfThroughputParametersTable
--********************************************************************
qtechRrmAPIfThroughputParametersTable OBJECT-TYPE
		SYNTAX 			SEQUENCE OF QtechRrmAPIfThroughputParametersEntry
		MAX-ACCESS 	not-accessible
		STATUS 			current
		DESCRIPTION
        		"These are RRM performance related read only parameters
        		per Airespace AP"
		::= { qtechRrmObjectsAP 13 }

qtechRrmAPIfThroughputParametersEntry OBJECT-TYPE
		SYNTAX 			QtechRrmAPIfThroughputParametersEntry
		MAX-ACCESS 	not-accessible
		STATUS 			current
		DESCRIPTION
          	"An entry (conceptual row) in the Table.
          	Entries in this MIB are indexed by
         	qtechRrmAPDot3MacAddress and qtechRrmAPIfSlotId"
 		INDEX { qtechRrmAPIfThroughputMacAddr, qtechRrmAPIfThroughputSlotId }
 		::= { qtechRrmAPIfThroughputParametersTable 1 }

QtechRrmAPIfThroughputParametersEntry ::=
  	SEQUENCE {
        qtechRrmAPIfThroughputMacAddr MacAddress,
        qtechRrmAPIfThroughputSlotId  INTEGER,
        qtechRrmAPIfThroughputAPName  DisplayString,
     		qtechRrmAPIfThroughputRx      INTEGER,
   			qtechRrmAPIfThroughputTx      INTEGER,
   			qtechRrmAPIfThroughputTotal	 INTEGER
		}

qtechRrmAPIfThroughputMacAddr OBJECT-TYPE
    SYNTAX      MacAddress
    MAX-ACCESS  read-only
    STATUS      current
    DESCRIPTION
            "The MAC address of radio on the AP"
    ::= { qtechRrmAPIfThroughputParametersEntry 1 }

qtechRrmAPIfThroughputSlotId OBJECT-TYPE
    SYNTAX 			INTEGER(1..32)
    MAX-ACCESS 	read-only
    STATUS 			current
    DESCRIPTION
        		"Number of Radio Interfaces on the Airespace AP.
         		Currently maximum two interfaces are supported.
         		One would be of type 802.11a and other of type
         		802.11b/g."
    ::= { qtechRrmAPIfThroughputParametersEntry 2 }

qtechRrmAPIfThroughputAPName OBJECT-TYPE
    SYNTAX 			DisplayString (SIZE(1..64))
    MAX-ACCESS 	read-only
    STATUS 			current
    DESCRIPTION
        		"The name of the AP"
    ::= { qtechRrmAPIfThroughputParametersEntry 3 }

qtechRrmAPIfThroughputRx OBJECT-TYPE
		SYNTAX 			INTEGER
		MAX-ACCESS 	read-only
		STATUS 			current
		DESCRIPTION
      			"This is the RX throughput"
		::= { qtechRrmAPIfThroughputParametersEntry 4 }

qtechRrmAPIfThroughputTx OBJECT-TYPE
 		SYNTAX 			INTEGER
		MAX-ACCESS 	read-only
		STATUS 			current
		DESCRIPTION
      			"This is the TX throughput"
		::= { qtechRrmAPIfThroughputParametersEntry 5 }

qtechRrmAPIfThroughputTotal OBJECT-TYPE
    SYNTAX 			INTEGER
    MAX-ACCESS 	read-only
    STATUS 			current
    DESCRIPTION
            "This is the total throughput"
    ::= { qtechRrmAPIfThroughputParametersEntry 6 }

--********************************************************************
-- * Begin of qtechRrmAPSnrBSSIDTable
--********************************************************************
qtechRrmAPSnrBSSIDTable OBJECT-TYPE
		SYNTAX 			SEQUENCE OF QtechRrmAPSnrBSSIDEntry
		MAX-ACCESS 	not-accessible
		STATUS 			current
		DESCRIPTION
        		"These are stat on ap snr BSSID"
		::= { qtechRrmObjectsAP 14 }

qtechRrmAPSnrBSSIDEntry OBJECT-TYPE
		SYNTAX 			QtechRrmAPSnrBSSIDEntry
		MAX-ACCESS 	not-accessible
		STATUS 			current
		DESCRIPTION
          	"An entry (conceptual row) in the Table.
          	Entries in this MIB are indexed by
         	qtechRrmAPDot3MacAddress and qtechRrmAPIfSlotId"
 		INDEX { qtechRrmAPSnrBSSIDMacAddr, qtechRrmAPSnrBSSIDSlotId }
 		::= { qtechRrmAPSnrBSSIDTable 1 }

QtechRrmAPSnrBSSIDEntry ::=
  	SEQUENCE {
        qtechRrmAPSnrBSSIDMacAddr                  MacAddress,
        qtechRrmAPSnrBSSIDSlotId                   INTEGER,
        qtechRrmAPSnrBSSIDAPName                   DisplayString,
     		qtechRrmAPSnrBSSIDAverageSignalStrength    INTEGER,
   			qtechRrmAPSnrBSSIDSignalPkts               INTEGER,
   			qtechRrmAPSnrBSSIDHighestRxSignalStrength  INTEGER,
   			qtechRrmAPSnrBSSIDLowestRxSignalStrength   INTEGER,
   			qtechRrmAPSnrBSSIDSampleTime               INTEGER
		}

qtechRrmAPSnrBSSIDMacAddr OBJECT-TYPE
    SYNTAX      MacAddress
    MAX-ACCESS  read-only
    STATUS      current
    DESCRIPTION
            "The MAC address of radio on the AP"
    ::= { qtechRrmAPSnrBSSIDEntry 1 }

qtechRrmAPSnrBSSIDSlotId OBJECT-TYPE
    SYNTAX 			INTEGER(1..32)
    MAX-ACCESS 	read-only
    STATUS 			current
    DESCRIPTION
        		"Number of Radio Interfaces on the Airespace AP.
         		Currently maximum two interfaces are supported.
         		One would be of type 802.11a and other of type
         		802.11b/g."
    ::= { qtechRrmAPSnrBSSIDEntry 2 }

qtechRrmAPSnrBSSIDAPName OBJECT-TYPE
    SYNTAX 			DisplayString (SIZE(1..64))
    MAX-ACCESS 	read-only
    STATUS 			current
    DESCRIPTION
        		"The name of the AP"
    ::= { qtechRrmAPSnrBSSIDEntry 3 }

qtechRrmAPSnrBSSIDAverageSignalStrength OBJECT-TYPE
		SYNTAX 			INTEGER
		MAX-ACCESS 	read-only
		STATUS 			current
		DESCRIPTION
      			"The average signal strength during monitor"
		::= { qtechRrmAPSnrBSSIDEntry 4 }

qtechRrmAPSnrBSSIDSignalPkts OBJECT-TYPE
 		SYNTAX 			INTEGER
		MAX-ACCESS 	read-only
		STATUS 			current
		DESCRIPTION
      			"The number of signal packets"
		::= { qtechRrmAPSnrBSSIDEntry 5 }

qtechRrmAPSnrBSSIDHighestRxSignalStrength OBJECT-TYPE
    SYNTAX 			INTEGER
    MAX-ACCESS 	read-only
    STATUS 			current
    DESCRIPTION
            "The highest rx signal strength during monitor"
    ::= { qtechRrmAPSnrBSSIDEntry 6 }

qtechRrmAPSnrBSSIDLowestRxSignalStrength OBJECT-TYPE
		SYNTAX 			INTEGER
		MAX-ACCESS 	read-only
		STATUS 			current
		DESCRIPTION
      			"The lowest rx signal strength during monitor"
		::= { qtechRrmAPSnrBSSIDEntry 7 }

qtechRrmAPSnrBSSIDSampleTime OBJECT-TYPE
 		SYNTAX 			INTEGER
		MAX-ACCESS 	read-only
		STATUS 			current
		DESCRIPTION
      			"The sample time"
		::= { qtechRrmAPSnrBSSIDEntry 8 }

--********************************************************************
--                                                                  **
--                           DCA Algorithm                          **
--                                                                  **
--********************************************************************
qtechRrmDot11bDynamicChannelAssignment OBJECT-TYPE
    SYNTAX      INTEGER {
        automatic (1),
        runOnce (2),
        static (3)
    }
    MAX-ACCESS  read-write
    STATUS      current
    DESCRIPTION
            "Dynamic channel assignment(DCA) has three modes. When the
            mode is auto, the channel assignment will be periodically
            updated for all APs that permit this operation. When the
            DCA is runOnce, channel assignments are updated based on
            the UPDATE_CMD received from the management. When the DCA
            is static, no dynamic channel assignments occurs and value
            are set to their global default.  Default is auto."
    DEFVAL { automatic }
    ::= { qtechRrmDCADot11b 1 }

qtechRrmDot11bAnchorTime OBJECT-TYPE
    SYNTAX      Unsigned32
    MAX-ACCESS  read-write
    STATUS      current
    DESCRIPTION
            "the time of DCA algorithm to start"
    DEFVAL { 0 }
    ::= { qtechRrmDCADot11b 2 }

qtechRrmDot11bChannalWidth11n OBJECT-TYPE
    SYNTAX      Unsigned32
    MAX-ACCESS  read-write
    STATUS      current
    DESCRIPTION
            "channel width in DCA for 802.11n"
    DEFVAL { 20 }
    ::= { qtechRrmDCADot11b 3 }

qtechRrmDot11bDynamicChannelUpdateInterval OBJECT-TYPE
    SYNTAX      Unsigned32
    MAX-ACCESS  read-write
    STATUS      current
    DESCRIPTION
            "When Channel dynamic alogirthm is running, this interval
            (in secs) specifies how often Channel assignement updates
            are attempted on an AP. NOTE: hysteresis is built into
            the algorithms so we will not have uproductive changes
            occuring. Default value is 600 secs"
    DEFVAL { 600 }
    ::= { qtechRrmDCADot11b 4 }

qtechRrmDot11bDCASensitivity OBJECT-TYPE
    SYNTAX      INTEGER {
        low (1),
        medium (2),
        high (3)
    }
    MAX-ACCESS  read-write
    STATUS      current
    DESCRIPTION
            "Consider foreign factor in DCA algorithm"
    DEFVAL  { medium }
    ::= { qtechRrmDCADot11b 5 }

qtechRrmDot11bForeignInterfereFactorEnable OBJECT-TYPE
    SYNTAX      INTEGER {disable(0),enable(1)}
    MAX-ACCESS  read-write
    STATUS      current
    DESCRIPTION
            "Consider foreign factor in DCA algorithm"
    DEFVAL  { enable }
    ::= { qtechRrmDCADot11b 6 }

qtechRrmDot11bLoadFactorEnable OBJECT-TYPE
    SYNTAX      INTEGER {disable(0),enable(1)}
    MAX-ACCESS  read-write
    STATUS      current
    DESCRIPTION
            "Consider foreign factor in DCA algorithm"
    DEFVAL  { disable }
    ::= { qtechRrmDCADot11b 7 }

qtechRrmDot11bNoiseFactorEnable OBJECT-TYPE
    SYNTAX      INTEGER {disable(0),enable(1)}
    MAX-ACCESS  read-write
    STATUS      current
    DESCRIPTION
            "Consider foreign factor in DCA algorithm"
    DEFVAL  { disable }
    ::= { qtechRrmDCADot11b 8 }

qtechRrmDot11bChannelUpdateCmdInvoke OBJECT-TYPE
    SYNTAX      INTEGER { default (0), activate (1) }
    MAX-ACCESS  read-write
    STATUS      current
    DESCRIPTION
        "When set to activate this starts a DCA calculation regardless
         of the dynamic update interval. This command should be invoke
         on Group Leader Qtech Switch.Invoking on a Qtech
         Switch which is not a Group leader has no effect."
    ::= {  qtechRrmDCADot11b 9 }

qtechRrmDot11bDCAChannelTable OBJECT-TYPE
    SYNTAX      SEQUENCE OF QtechRrmDot11bDCAChannelEntry
    MAX-ACCESS  not-accessible
    STATUS      current
    DESCRIPTION
       "This is a table of Qtech Switch addresses that identifies
        the members of the Dot11a RF group containing this Qtech
        Switch. Max size is 20 entries."
    ::= { qtechRrmDCADot11b 10 }

qtechRrmDot11bDCAChannelEntry OBJECT-TYPE
    SYNTAX      QtechRrmDot11bDCAChannelEntry
    MAX-ACCESS  not-accessible
    STATUS      current
    DESCRIPTION
        " ... "
    INDEX { qtechRrmDot11bDCAChannelIndex }
    ::= { qtechRrmDot11bDCAChannelTable 1 }

QtechRrmDot11bDCAChannelEntry ::=
    SEQUENCE {
        qtechRrmDot11bDCAChannelIndex        INTEGER,
        qtechRrmDot11bDCAChannelOperation    INTEGER
    }

qtechRrmDot11bDCAChannelIndex OBJECT-TYPE
    SYNTAX      INTEGER
    MAX-ACCESS  read-only
    STATUS      current
    DESCRIPTION
            "the index of dca channel."
    ::= { qtechRrmDot11bDCAChannelEntry 1 }

qtechRrmDot11bDCAChannelOperation OBJECT-TYPE
    SYNTAX      INTEGER {delete(0),add(1)}
    MAX-ACCESS  read-write
    STATUS      current
    DESCRIPTION
            "add or delete the channel using in DCA algorithm."
    ::= { qtechRrmDot11bDCAChannelEntry 2 }


qtechRrmDot11aDynamicChannelAssignment OBJECT-TYPE
    SYNTAX      INTEGER {
        automatic (1),
        runOnce (2),
        static (3)
    }
    MAX-ACCESS  read-write
    STATUS      current
    DESCRIPTION
            "Dynamic channel assignment(DCA) has three modes. When the
            mode is auto, the channel assignment will be periodically
            updated for all APs that permit this operation. When the
            DCA is runOnce, channel assignments are updated based on
            the UPDATE_CMD received from the management. When the DCA
            is static, no dynamic channel assignments occurs and value
            are set to their global default.  Default is auto."
    DEFVAL { automatic }
    ::= { qtechRrmDCADot11a 1 }

qtechRrmDot11aAnchorTime OBJECT-TYPE
    SYNTAX      Unsigned32
    MAX-ACCESS  read-write
    STATUS      current
    DESCRIPTION
            "the time of DCA algorithm to start"
    DEFVAL { 0 }
    ::= { qtechRrmDCADot11a 2 }

qtechRrmDot11aChannalWidth11n OBJECT-TYPE
    SYNTAX      Unsigned32
    MAX-ACCESS  read-write
    STATUS      current
    DESCRIPTION
            "channel width in DCA for 802.11n"
    DEFVAL { 20 }
    ::= { qtechRrmDCADot11a 3 }

qtechRrmDot11aDynamicChannelUpdateInterval OBJECT-TYPE
    SYNTAX      Unsigned32
    MAX-ACCESS  read-write
    STATUS      current
    DESCRIPTION
            "When Channel dynamic alogirthm is running, this interval
            (in secs) specifies how often Channel assignement updates
            are attempted on an AP. NOTE: hysteresis is built into
            the algorithms so we will not have uproductive changes
            occuring. Default value is 600 secs"
    DEFVAL { 600 }
    ::= { qtechRrmDCADot11a 4 }

qtechRrmDot11aDCASensitivity OBJECT-TYPE
    SYNTAX      INTEGER {
        low (1),
        medium (2),
        high (3)
    }
    MAX-ACCESS  read-write
    STATUS      current
    DESCRIPTION
            "Consider foreign factor in DCA algorithm"
    DEFVAL  { medium }
    ::= { qtechRrmDCADot11a 5 }

qtechRrmDot11aForeignInterfereFactorEnable OBJECT-TYPE
    SYNTAX      INTEGER {disable(0),enable(1)}
    MAX-ACCESS  read-write
    STATUS      current
    DESCRIPTION
            "Consider foreign factor in DCA algorithm"
    DEFVAL  { enable }
    ::= { qtechRrmDCADot11a 6 }

qtechRrmDot11aLoadFactorEnable OBJECT-TYPE
    SYNTAX      INTEGER {disable(0),enable(1)}
    MAX-ACCESS  read-write
    STATUS      current
    DESCRIPTION
            "Consider foreign factor in DCA algorithm"
    DEFVAL  { disable }
    ::= { qtechRrmDCADot11a 7 }

qtechRrmDot11aNoiseFactorEnable OBJECT-TYPE
    SYNTAX      INTEGER {disable(0),enable(1)}
    MAX-ACCESS  read-write
    STATUS      current
    DESCRIPTION
            "Consider foreign factor in DCA algorithm"
    DEFVAL  { disable }
    ::= { qtechRrmDCADot11a 8 }

qtechRrmDot11aChannelUpdateCmdInvoke OBJECT-TYPE
    SYNTAX      INTEGER { default (0), activate (1) }
    MAX-ACCESS  read-write
    STATUS      current
    DESCRIPTION
        "When set to activate this starts a DCA calculation regardless
         of the dynamic update interval. This command should be invoke
         on Group Leader Qtech Switch.Invoking on a Qtech
         Switch which is not a Group leader has no effect."
    ::= {  qtechRrmDCADot11a 9 }

qtechRrmDot11aDCAChannelTable OBJECT-TYPE
    SYNTAX      SEQUENCE OF QtechRrmDot11aDCAChannelEntry
    MAX-ACCESS  not-accessible
    STATUS      current
    DESCRIPTION
       "This is a table of Qtech Switch addresses that identifies
        the members of the Dot11a RF group containing this Qtech
        Switch. Max size is 20 entries."
    ::= { qtechRrmDCADot11a 10 }

qtechRrmDot11aDCAChannelEntry OBJECT-TYPE
    SYNTAX      QtechRrmDot11aDCAChannelEntry
    MAX-ACCESS  not-accessible
    STATUS      current
    DESCRIPTION
        " ... "
    INDEX { qtechRrmDot11aDCAChannelIndex }
    ::= { qtechRrmDot11aDCAChannelTable 1 }

QtechRrmDot11aDCAChannelEntry ::=
    SEQUENCE {
        qtechRrmDot11aDCAChannelIndex        INTEGER,
        qtechRrmDot11aDCAChannelOperation    INTEGER
    }

qtechRrmDot11aDCAChannelIndex OBJECT-TYPE
    SYNTAX      INTEGER
    MAX-ACCESS  read-only
    STATUS      current
    DESCRIPTION
            "the index of dca channel."
    ::= { qtechRrmDot11aDCAChannelEntry 1 }

qtechRrmDot11aDCAChannelOperation OBJECT-TYPE
    SYNTAX      INTEGER {delete(0),add(1)}
    MAX-ACCESS  read-write
    STATUS      current
    DESCRIPTION
            "add or delete the channel using in DCA algorithm."
    ::= { qtechRrmDot11aDCAChannelEntry 2 }

--********************************************************************
--                                                                  **
--                           TPC Algorithm                          **
--                                                                  **
--********************************************************************
qtechRrmDot11bDTPCSupport OBJECT-TYPE
    SYNTAX      INTEGER {disable(0),enable(1)}
    MAX-ACCESS  read-write
    STATUS current
    DESCRIPTION
        "This attribute may be used to enable the DTPC support on all
        802.11b/g radios. DTPC or Dynamic Transmit Power Control support
        means that the radio's transmit power will be advertised in the
        beacons and probe responses."
    DEFVAL { enable }
    ::= { qtechRrmTPCDot11b 1 }

qtechRrmDot11bDynamicTransmitPowerControl OBJECT-TYPE
    SYNTAX      INTEGER {
        automatic (1),
        runOnce (2),
        static (3)
    }
    MAX-ACCESS  read-write
    STATUS      current
    DESCRIPTION
        "Dynamic transmit power (DTP) has three modes. When the mode
         is auto, the transmit power of each Qtech AP will be
         periodically updated for all Qtech APs that permit this
         operation. When the DTP is runOnce,transmit power update will
         occur based on the UPDATE_CMD received from the management.
         When the DTP is static, no dynamic transmit power updates
         occur and their global defaults are used.  Default is auto."
    DEFVAL { automatic }
    ::= { qtechRrmTPCDot11b 2 }

qtechRrmDot11bDynamicTxPowerControlInterval OBJECT-TYPE
    SYNTAX      Unsigned32
    MAX-ACCESS  read-only
    STATUS      current
    DESCRIPTION
        "When Tx PowerControl dynamic alogirthm is running, this
         interval(in secs) specifies how often TxPower control updates
         are attempted on an Qtech AP. NOTE: hysteresis is
         build into the algorithms so we will not have uproductive
         changes occuring. Default value is 600 secs"
   DEFVAL { 600 }
   ::= { qtechRrmTPCDot11b 3 }

qtechRrmDot11bCurrentTxPowerLevel OBJECT-TYPE
    SYNTAX      INTEGER (1..8)
    MAX-ACCESS  read-write
    STATUS      current
    DESCRIPTION
            "The TxPowerLevel N currently being used to transmit data.
            Some PHYs also use this value to determine the receiver
            sensitivity requirements for CCA."
    ::= { qtechRrmTPCDot11b 4 }

qtechRrmDot11bPowerUpdateCmdInvoke OBJECT-TYPE
    SYNTAX      INTEGER { default (0), activate (1) }
    MAX-ACCESS  read-write
    STATUS      current
    DESCRIPTION
        "When set to activate this starts a DTP calculation regardless
         of the dynamic update interval. This command should be
         invoke on Group Leader Qtech Switch.Invoking on a
         Qtech Switch which is not a Group leader has no effect."
    ::= {  qtechRrmTPCDot11b 5 }

qtechRrmDot11bTXPowerThreshold OBJECT-TYPE
    SYNTAX      INTEGER (-90..-60)
    MAX-ACCESS  read-write
    STATUS      current
    DESCRIPTION
            "threshold value in TPC algorithm"
    DEFVAL { -70 }
    ::= { qtechRrmTPCDot11b 6 }

qtechRrmDot11bTPCNeighborNumber OBJECT-TYPE
    SYNTAX      INTEGER
    MAX-ACCESS  read-only
    STATUS      current
    DESCRIPTION
            "threshold value in TPC algorithm"
    DEFVAL { 3 }
    ::= { qtechRrmTPCDot11b 7 }

qtechRrmDot11aDTPCSupport OBJECT-TYPE
    SYNTAX      INTEGER {disable(0),enable(1)}
    MAX-ACCESS  read-write
    STATUS current
    DESCRIPTION
        "This attribute may be used to enable the DTPC support on all
        802.11b/g radios. DTPC or Dynamic Transmit Power Control support
        means that the radio's transmit power will be advertised in the
        beacons and probe responses."
    DEFVAL { enable }
    ::= { qtechRrmTPCDot11a 1 }

qtechRrmDot11aDynamicTransmitPowerControl OBJECT-TYPE
    SYNTAX      INTEGER {
        automatic (1),
        runOnce (2),
        static (3)
    }
    MAX-ACCESS  read-write
    STATUS      current
    DESCRIPTION
        "Dynamic transmit power (DTP) has three modes. When the mode
         is auto, the transmit power of each Qtech AP will be
         periodically updated for all Qtech APs that permit this
         operation. When the DTP is runOnce,transmit power update will
         occur based on the UPDATE_CMD received from the management.
         When the DTP is static, no dynamic transmit power updates
         occur and their global defaults are used.  Default is auto."
    DEFVAL { automatic }
    ::= { qtechRrmTPCDot11a 2 }

qtechRrmDot11aDynamicTxPowerControlInterval OBJECT-TYPE
    SYNTAX      Unsigned32
    MAX-ACCESS  read-only
    STATUS      current
    DESCRIPTION
        "When Tx PowerControl dynamic alogirthm is running, this
         interval(in secs) specifies how often TxPower control updates
         are attempted on an Qtech AP. NOTE: hysteresis is
         build into the algorithms so we will not have uproductive
         changes occuring. Default value is 600 secs"
   DEFVAL { 600 }
   ::= { qtechRrmTPCDot11a 3 }

qtechRrmDot11aCurrentTxPowerLevel OBJECT-TYPE
    SYNTAX      INTEGER (1..8)
    MAX-ACCESS  read-write
    STATUS      current
    DESCRIPTION
            "The TxPowerLevel N currently being used to transmit data.
            Some PHYs also use this value to determine the receiver
            sensitivity requirements for CCA."
    ::= { qtechRrmTPCDot11a 4 }

qtechRrmDot11aPowerUpdateCmdInvoke OBJECT-TYPE
    SYNTAX      INTEGER { default (0), activate (1) }
    MAX-ACCESS  read-write
    STATUS      current
    DESCRIPTION
        "When set to activate this starts a DTP calculation regardless
         of the dynamic update interval. This command should be
         invoke on Group Leader Qtech Switch.Invoking on a
         Qtech Switch which is not a Group leader has no effect."
    ::= {  qtechRrmTPCDot11a 5 }

qtechRrmDot11aTXPowerThreshold OBJECT-TYPE
    SYNTAX      INTEGER (-90..-60)
    MAX-ACCESS  read-write
    STATUS      current
    DESCRIPTION
            "threshold value in TPC algorithm"
    DEFVAL { -70 }
    ::= { qtechRrmTPCDot11a 6 }

qtechRrmDot11aTPCNeighborNumber OBJECT-TYPE
    SYNTAX      INTEGER
    MAX-ACCESS  read-only
    STATUS      current
    DESCRIPTION
            "threshold value in TPC algorithm"
    DEFVAL { 3 }
    ::= { qtechRrmTPCDot11a 7 }

--********************************************************************
--                                                                  **
--                           CHD Algorithm                          **
--                                                                  **
--********************************************************************
qtechRrmDot11bCoverageEnable OBJECT-TYPE
    SYNTAX      INTEGER {disable(0),enable(1)}
    MAX-ACCESS  read-write
    STATUS      current
    DESCRIPTION
        "CHD algorighm. Default is enable."
    DEFVAL { enable }
    ::= { qtechRrmCHDDot11b 1 }

qtechRrmDot11bCoverageExceptionGlobal OBJECT-TYPE
    SYNTAX      INTEGER (1..100)
    MAX-ACCESS  read-write
    STATUS      current
    DESCRIPTION
        "CHD algorighm."
    DEFVAL { 25 }
    ::= { qtechRrmCHDDot11b 2 }

qtechRrmDot11bCoverageLevelGlobal OBJECT-TYPE
    SYNTAX      INTEGER (1..75)
    MAX-ACCESS  read-write
    STATUS      current
    DESCRIPTION
        "CHD algorighm."
    DEFVAL { 3 }
    ::= { qtechRrmCHDDot11b 3 }

qtechRrmDot11bCoverageDataRSSIThreshold OBJECT-TYPE
    SYNTAX      INTEGER (-90..-60)
    MAX-ACCESS  read-write
    STATUS      current
    DESCRIPTION
        "CHD algorighm."
    DEFVAL { -80 }
    ::= { qtechRrmCHDDot11b 4 }

qtechRrmDot11bCoverageVoiceRSSIThreshold OBJECT-TYPE
    SYNTAX      INTEGER (-90..-60)
    MAX-ACCESS  read-write
    STATUS      current
    DESCRIPTION
        "CHD algorighm."
    DEFVAL { -75 }
    ::= { qtechRrmCHDDot11b 5 }

qtechRrmDot11bCoverageDataPacketCount OBJECT-TYPE
    SYNTAX      INTEGER (1..255)
    MAX-ACCESS  read-write
    STATUS      current
    DESCRIPTION
        "CHD algorighm."
    DEFVAL { 10 }
    ::= { qtechRrmCHDDot11b 6 }

qtechRrmDot11bCoverageVoicePacketCount OBJECT-TYPE
    SYNTAX      INTEGER (1..255)
    MAX-ACCESS  read-write
    STATUS      current
    DESCRIPTION
        "CHD algorighm."
    DEFVAL { 10 }
    ::= { qtechRrmCHDDot11b 7 }

qtechRrmDot11bCoverageDataFailRate OBJECT-TYPE
    SYNTAX      INTEGER (1..100)
    MAX-ACCESS  read-write
    STATUS      current
    DESCRIPTION
        "CHD algorighm."
    DEFVAL { 20 }
    ::= { qtechRrmCHDDot11b 8 }

qtechRrmDot11bCoverageVoiceFailRate OBJECT-TYPE
    SYNTAX      INTEGER (1..100)
    MAX-ACCESS  read-write
    STATUS      current
    DESCRIPTION
        "CHD algorighm."
    DEFVAL { 20 }
    ::= { qtechRrmCHDDot11b 9 }

qtechRrmDot11aCoverageEnable OBJECT-TYPE
    SYNTAX      INTEGER {disable(0),enable(1)}
    MAX-ACCESS  read-write
    STATUS      current
    DESCRIPTION
        "CHD algorighm. Default is enable."
    DEFVAL { enable }
    ::= { qtechRrmCHDDot11a 1 }

qtechRrmDot11aCoverageExceptionGlobal OBJECT-TYPE
    SYNTAX      INTEGER (1..100)
    MAX-ACCESS  read-write
    STATUS      current
    DESCRIPTION
        "CHD algorighm."
    DEFVAL { 25 }
    ::= { qtechRrmCHDDot11a 2 }

qtechRrmDot11aCoverageLevelGlobal OBJECT-TYPE
    SYNTAX      INTEGER (1..75)
    MAX-ACCESS  read-write
    STATUS      current
    DESCRIPTION
        "CHD algorighm."
    DEFVAL { 3 }
    ::= { qtechRrmCHDDot11a 3 }

qtechRrmDot11aCoverageDataRSSIThreshold OBJECT-TYPE
    SYNTAX      INTEGER (-90..-60)
    MAX-ACCESS  read-write
    STATUS      current
    DESCRIPTION
        "CHD algorighm."
    DEFVAL { -80 }
    ::= { qtechRrmCHDDot11a 4 }

qtechRrmDot11aCoverageVoiceRSSIThreshold OBJECT-TYPE
    SYNTAX      INTEGER (-90..-60)
    MAX-ACCESS  read-write
    STATUS      current
    DESCRIPTION
        "CHD algorighm."
    DEFVAL { -75 }
    ::= { qtechRrmCHDDot11a 5 }

qtechRrmDot11aCoverageDataPacketCount OBJECT-TYPE
    SYNTAX      INTEGER (1..255)
    MAX-ACCESS  read-write
    STATUS      current
    DESCRIPTION
        "CHD algorighm."
    DEFVAL { 10 }
    ::= { qtechRrmCHDDot11a 6 }

qtechRrmDot11aCoverageVoicePacketCount OBJECT-TYPE
    SYNTAX      INTEGER (1..255)
    MAX-ACCESS  read-write
    STATUS      current
    DESCRIPTION
        "CHD algorighm."
    DEFVAL { 10 }
    ::= { qtechRrmCHDDot11a 7 }

qtechRrmDot11aCoverageDataFailRate OBJECT-TYPE
    SYNTAX      INTEGER (1..100)
    MAX-ACCESS  read-write
    STATUS      current
    DESCRIPTION
        "CHD algorighm."
    DEFVAL { 20 }
    ::= { qtechRrmCHDDot11a 8 }

qtechRrmDot11aCoverageVoiceFailRate OBJECT-TYPE
    SYNTAX      INTEGER (1..100)
    MAX-ACCESS  read-write
    STATUS      current
    DESCRIPTION
        "CHD algorighm."
    DEFVAL { 20 }
    ::= { qtechRrmCHDDot11a 9 }

--********************************************************************
--                                                                  **
--                      RRM Group Infomation                        **
--                                                                  **
--********************************************************************
qtechRrmDot11bGlobalAutomaticGrouping OBJECT-TYPE
    SYNTAX      INTEGER { automatic (1), off (0) }
    MAX-ACCESS  read-write
    STATUS      current
    DESCRIPTION
        "Dynamic grouping has two modes: on and off. When the grouping
         is off, no dynamic grouping occurs. Each Qtech Switch
         optimizes only its own Qtech APs' parameters. When
         grouping is on, the Qtech Switches form groups and
         elect leaders to perform better dynamic parameter
         optimization."
    DEFVAL { automatic }
    ::= { qtechRrmGroupDot11b 1 }

qtechRrmDot11bGroupLeaderMacAddr OBJECT-TYPE
    SYNTAX      MacAddress
    MAX-ACCESS  read-only
    STATUS      current
    DESCRIPTION
        "This is the MAC address of the group leader for the Dot11b
         group containing this Qtech Switch."
    ::= { qtechRrmGroupDot11b 2 }

qtechRrmDot11bGroupLeader OBJECT-TYPE
    SYNTAX      INTEGER {no(0),yes(1)}
    MAX-ACCESS  read-only
    STATUS      current
    DESCRIPTION
        "If this Qtech Switch is a Dot11b Group Leader then this
         attribute will be true else it will be false."
    ::= { qtechRrmGroupDot11b 3 }

qtechRrmDot11bGroupLastUpdateTime OBJECT-TYPE
    SYNTAX      Unsigned32
    MAX-ACCESS  read-only
    STATUS      current
    DESCRIPTION
        "Last time the Dot11b grouping was updated on this Qtech
         Switch. This is valid only if the Qtech Switch is a
         group leader."
    ::= { qtechRrmGroupDot11b 4 }

qtechRrmDot11bGroupInterval OBJECT-TYPE
    SYNTAX      Unsigned32
    MAX-ACCESS  read-only
    STATUS      current
    DESCRIPTION
        "When grouping is on, this interval(in secs) represents the
         period with which the grouping algorithm is run. Grouping
         algorithm will also run when the group contents changes and
         the automatic grouping is enabled. A dynamic grouping can be
         started upon request from the system administrator. Default
         value is 3600 secs."
    DEFVAL { 3600 }
    ::= {qtechRrmGroupDot11b 5}

qtechRrmDot11bGroupTable OBJECT-TYPE
    SYNTAX      SEQUENCE OF QtechRrmDot11bGroupEntry
    MAX-ACCESS  not-accessible
    STATUS      current
    DESCRIPTION
       "This is a table of Qtech Switch addresses that identifies
        the members of the Dot11b RF group containing this Qtech
        Switch. Max size is 20 entries."
    ::= { qtechRrmGroupDot11b 6 }

qtechRrmDot11bGroupEntry OBJECT-TYPE
    SYNTAX      QtechRrmDot11bGroupEntry
    MAX-ACCESS  not-accessible
    STATUS      current
    DESCRIPTION
        " ... "
    INDEX { qtechRrmDot11bPeerMacAddress }
    ::= { qtechRrmDot11bGroupTable 1 }

QtechRrmDot11bGroupEntry ::=
    SEQUENCE {
        qtechRrmDot11bPeerMacAddress       MacAddress,
        qtechRrmDot11bPeerIpAddress        IpAddress
    }

qtechRrmDot11bPeerMacAddress OBJECT-TYPE
    SYNTAX      MacAddress
    MAX-ACCESS  read-only
    STATUS      current
    DESCRIPTION
            "The MAC address of the member Switch."
    ::= { qtechRrmDot11bGroupEntry 1 }

qtechRrmDot11bPeerIpAddress OBJECT-TYPE
    SYNTAX      IpAddress
    MAX-ACCESS  read-only
    STATUS      current
    DESCRIPTION
            "The IP address of the Qtech Switch."
    ::= { qtechRrmDot11bGroupEntry 2 }

qtechRrmDot11bSummaryTable OBJECT-TYPE
    SYNTAX      SEQUENCE OF QtechRrmDot11bSummaryEntry
    MAX-ACCESS  not-accessible
    STATUS      current
    DESCRIPTION
       ""
    ::= { qtechRrmGroupDot11b 7 }

qtechRrmDot11bSummaryEntry OBJECT-TYPE
    SYNTAX      QtechRrmDot11bSummaryEntry
    MAX-ACCESS  not-accessible
    STATUS      current
    DESCRIPTION
        " ... "
    INDEX { qtechRrmDot11bSummaryMacAddress, qtechRrmDot11bAPRadioID}
    ::= { qtechRrmDot11bSummaryTable 1 }

QtechRrmDot11bSummaryEntry ::=
    SEQUENCE {
        qtechRrmDot11bSummaryMacAddress   MacAddress,
        qtechRrmDot11bAPname           					DisplayString,
        qtechRrmDot11bAPRadioID									Unsigned32,
        qtechRrmDot11bAPChannel        					Unsigned32,
        qtechRrmDot11bAPTxPower        					Unsigned32,
        qtechRrmDot11bAPChannelRrmChangeFlag    	INTEGER,
        qtechRrmDot11bAPTxPowerRrmChangeFlag    	INTEGER
    }

qtechRrmDot11bAPname OBJECT-TYPE
    SYNTAX      DisplayString
    MAX-ACCESS  read-only
    STATUS      current
    DESCRIPTION
            ""
    ::= { qtechRrmDot11bSummaryEntry 1 }

qtechRrmDot11bAPRadioID OBJECT-TYPE
    SYNTAX      Unsigned32
    MAX-ACCESS  read-only
    STATUS      current
    DESCRIPTION
            ""
    ::= { qtechRrmDot11bSummaryEntry 2 }

qtechRrmDot11bAPChannel OBJECT-TYPE
    SYNTAX      Unsigned32
    MAX-ACCESS  read-only
    STATUS      current
    DESCRIPTION
            ""
    ::= { qtechRrmDot11bSummaryEntry 3 }

qtechRrmDot11bAPTxPower OBJECT-TYPE
    SYNTAX      Unsigned32
    MAX-ACCESS  read-only
    STATUS      current
    DESCRIPTION
            ""
    ::= { qtechRrmDot11bSummaryEntry 4 }

qtechRrmDot11bAPChannelRrmChangeFlag OBJECT-TYPE
    SYNTAX      INTEGER {no(0),yes(1)}
    MAX-ACCESS  read-only
    STATUS      current
    DESCRIPTION
            ""
    ::= { qtechRrmDot11bSummaryEntry 5 }

qtechRrmDot11bAPTxPowerRrmChangeFlag OBJECT-TYPE
    SYNTAX      INTEGER {no(0),yes(1)}
    MAX-ACCESS  read-only
    STATUS      current
    DESCRIPTION
            ""
    ::= { qtechRrmDot11bSummaryEntry 6 }

qtechRrmDot11bSummaryMacAddress OBJECT-TYPE
    SYNTAX      MacAddress
    MAX-ACCESS  read-only
    STATUS      current
    DESCRIPTION
            "The MAC address of the member Switch."
    ::= { qtechRrmDot11bSummaryEntry 7 }


qtechRrmDot11aGlobalAutomaticGrouping OBJECT-TYPE
    SYNTAX      INTEGER { automatic (1), off (0) }
    MAX-ACCESS  read-write
    STATUS      current
    DESCRIPTION
        "Dynamic grouping has two modes: on and off. When the grouping
         is off, no dynamic grouping occurs. Each Qtech Switch
         optimizes only its own Qtech APs' parameters. When
         grouping is on, the Qtech Switches form groups and
         elect leaders to perform better dynamic parameter
         optimization."
    DEFVAL { automatic }
    ::= { qtechRrmGroupDot11a 1 }

qtechRrmDot11aGroupLeaderMacAddr OBJECT-TYPE
    SYNTAX      MacAddress
    MAX-ACCESS  read-only
    STATUS      current
    DESCRIPTION
        "This is the MAC address of the group leader for the dot11a
         group containing this Qtech Switch."
    ::= { qtechRrmGroupDot11a 2 }

qtechRrmDot11aGroupLeader OBJECT-TYPE
    SYNTAX      INTEGER {no(0),yes(1)}
    MAX-ACCESS  read-only
    STATUS      current
    DESCRIPTION
        "If this Qtech Switch is a Dot11a Group Leader then this
         attribute will be true else it will be false."
    ::= { qtechRrmGroupDot11a 3 }

qtechRrmDot11aGroupLastUpdateTime OBJECT-TYPE
    SYNTAX      Unsigned32
    MAX-ACCESS  read-only
    STATUS      current
    DESCRIPTION
        "Last time the dot11a grouping was updated on this Qtech
         Switch. This is valid only if the Qtech Switch is a
         group leader."
    ::= { qtechRrmGroupDot11a 4 }

qtechRrmDot11aGroupInterval OBJECT-TYPE
    SYNTAX      Unsigned32
    MAX-ACCESS  read-only
    STATUS      current
    DESCRIPTION
        "When grouping is on, this interval(in secs) represents the
         period with which the grouping algorithm is run. Grouping
         algorithm will also run when the group contents changes and
         the automatic grouping is enabled. A dynamic grouping can be
         started upon request from the system administrator. Default
         value is 3600 secs."
    DEFVAL { 3600 }
    ::= {qtechRrmGroupDot11a 5}

qtechRrmDot11aGroupTable OBJECT-TYPE
    SYNTAX      SEQUENCE OF QtechRrmDot11aGroupEntry
    MAX-ACCESS  not-accessible
    STATUS      current
    DESCRIPTION
       "This is a table of Qtech Switch addresses that identifies
        the members of the Dot11a RF group containing this Qtech
        Switch. Max size is 20 entries."
    ::= { qtechRrmGroupDot11a 6 }

qtechRrmDot11aGroupEntry OBJECT-TYPE
    SYNTAX      QtechRrmDot11aGroupEntry
    MAX-ACCESS  not-accessible
    STATUS      current
    DESCRIPTION
        " ... "
    INDEX { qtechRrmDot11aPeerMacAddress }
    ::= { qtechRrmDot11aGroupTable 1 }

QtechRrmDot11aGroupEntry ::=
    SEQUENCE {
        qtechRrmDot11aPeerMacAddress       MacAddress,
        qtechRrmDot11aPeerIpAddress        IpAddress
    }

qtechRrmDot11aPeerMacAddress OBJECT-TYPE
    SYNTAX      MacAddress
    MAX-ACCESS  read-only
    STATUS      current
    DESCRIPTION
            "The MAC address of the member Switch."
    ::= { qtechRrmDot11aGroupEntry 1 }

qtechRrmDot11aPeerIpAddress OBJECT-TYPE
    SYNTAX      IpAddress
    MAX-ACCESS  read-only
    STATUS      current
    DESCRIPTION
            "The IP address of the Qtech Switch."
    ::= { qtechRrmDot11aGroupEntry 2 }

qtechRrmDot11aSummaryTable OBJECT-TYPE
    SYNTAX      SEQUENCE OF QtechRrmDot11aSummaryEntry
    MAX-ACCESS  not-accessible
    STATUS      current
    DESCRIPTION
       ""
    ::= { qtechRrmGroupDot11a 7 }

qtechRrmDot11aSummaryEntry OBJECT-TYPE
    SYNTAX      QtechRrmDot11aSummaryEntry
    MAX-ACCESS  not-accessible
    STATUS      current
    DESCRIPTION
        " ... "
    INDEX { qtechRrmDot11aSummaryMacAddress,  qtechRrmDot11aAPRadioID}
    ::= { qtechRrmDot11aSummaryTable 1 }

QtechRrmDot11aSummaryEntry ::=
    SEQUENCE {
        qtechRrmDot11aSummaryMacAddress MacAddress,
        qtechRrmDot11aAPname           					DisplayString,
        qtechRrmDot11aAPRadioID									Unsigned32,
        qtechRrmDot11aAPChannel        					Unsigned32,
        qtechRrmDot11aAPTxPower        					Unsigned32,
        qtechRrmDot11aAPChannelRrmChangeFlag    	INTEGER,
        qtechRrmDot11aAPTxPowerRrmChangeFlag    	INTEGER
    }

qtechRrmDot11aAPname OBJECT-TYPE
    SYNTAX      DisplayString
    MAX-ACCESS  read-only
    STATUS      current
    DESCRIPTION
            ""
    ::= { qtechRrmDot11aSummaryEntry 1 }

qtechRrmDot11aAPRadioID OBJECT-TYPE
    SYNTAX      Unsigned32
    MAX-ACCESS  read-only
    STATUS      current
    DESCRIPTION
            ""
    ::= { qtechRrmDot11aSummaryEntry 2 }

qtechRrmDot11aAPChannel OBJECT-TYPE
    SYNTAX      Unsigned32
    MAX-ACCESS  read-only
    STATUS      current
    DESCRIPTION
            ""
    ::= { qtechRrmDot11aSummaryEntry 3 }

qtechRrmDot11aAPTxPower OBJECT-TYPE
    SYNTAX      Unsigned32
    MAX-ACCESS  read-only
    STATUS      current
    DESCRIPTION
            ""
    ::= { qtechRrmDot11aSummaryEntry 4 }

qtechRrmDot11aAPChannelRrmChangeFlag OBJECT-TYPE
    SYNTAX      INTEGER {no(0),yes(1)}
    MAX-ACCESS  read-only
    STATUS      current
    DESCRIPTION
            ""
    ::= { qtechRrmDot11aSummaryEntry 5 }

qtechRrmDot11aAPTxPowerRrmChangeFlag OBJECT-TYPE
    SYNTAX      INTEGER {no(0),yes(1)}
    MAX-ACCESS  read-only
    STATUS      current
    DESCRIPTION
            ""
    ::= { qtechRrmDot11aSummaryEntry 6 }

qtechRrmDot11aSummaryMacAddress OBJECT-TYPE
    SYNTAX      MacAddress
    MAX-ACCESS  read-only
    STATUS      current
    DESCRIPTION
            "The MAC address of the member Switch."
    ::= { qtechRrmDot11aSummaryEntry 7 }

--********************************************************************
--                                                                  **
--                       RRM Profile Value                          **
--                                                                  **
--********************************************************************
qtechRrmDot11bForeignInterferenceThreshold OBJECT-TYPE
    SYNTAX      INTEGER(1..100)
    MAX-ACCESS  read-write
    STATUS      current
    DESCRIPTION
            "foreign 802.11B interference threshold between 0 and 100
            percent."
    DEFVAL { 10 }
    ::= {qtechRrmProfileDot11b 1 }

qtechRrmDot11bForeignNoiseThreshold OBJECT-TYPE
    SYNTAX      INTEGER(-127..0)
    MAX-ACCESS  read-write
    STATUS      current
    DESCRIPTION
            " 802.11B foreign noise threshold between -127 and 0 dBm."
    DEFVAL { -70 }
    ::= {qtechRrmProfileDot11b 2 }

qtechRrmDot11bRFUtilizationThreshold OBJECT-TYPE
    SYNTAX      INTEGER(1..100)
    MAX-ACCESS  read-write
    STATUS      current
    DESCRIPTION
            "802.11B RF utlization threshold between 0 and 100
            percent."
    DEFVAL { 80 }
    ::= {qtechRrmProfileDot11b 3 }

qtechRrmDot11bThroughputThreshold OBJECT-TYPE
    SYNTAX      Unsigned32(1000..10000000)
    MAX-ACCESS  read-write
    STATUS      current
    DESCRIPTION
            " 802.11B throughput threshold between 1000 and 10000000"
    DEFVAL { 1000000 }
    ::= {qtechRrmProfileDot11b 4 }

qtechRrmDot11bMobilesThreshold OBJECT-TYPE
    SYNTAX      INTEGER(1..75)
    MAX-ACCESS  read-write
    STATUS      current
    DESCRIPTION
            "802.11B mobiles threshold between 1 and 75"
    DEFVAL { 12 }
    ::= {qtechRrmProfileDot11b 5 }


qtechRrmDot11aForeignInterferenceThreshold OBJECT-TYPE
    SYNTAX      INTEGER(1..100)
    MAX-ACCESS  read-write
    STATUS      current
    DESCRIPTION
            "foreign 802.11A interference threshold between 0 and 100
            percent."
    DEFVAL { 10 }
    ::= {qtechRrmProfileDot11a 1 }

qtechRrmDot11aForeignNoiseThreshold OBJECT-TYPE
    SYNTAX      INTEGER(-127..0)
    MAX-ACCESS  read-write
    STATUS      current
    DESCRIPTION
            " 802.11A foreign noise threshold between -127 and 0 dBm."
    DEFVAL { -70 }
    ::= {qtechRrmProfileDot11a 2 }

qtechRrmDot11aRFUtilizationThreshold OBJECT-TYPE
    SYNTAX      INTEGER(1..100)
    MAX-ACCESS  read-write
    STATUS      current
    DESCRIPTION
            "802.11A RF utlization threshold between 0 and 100
            percent."
    DEFVAL { 80 }
    ::= {qtechRrmProfileDot11a 3 }

qtechRrmDot11aThroughputThreshold OBJECT-TYPE
    SYNTAX      Unsigned32(1000..10000000)
    MAX-ACCESS  read-write
    STATUS      current
    DESCRIPTION
            " 802.11A throughput threshold between 1000 and 10000000"
    DEFVAL { 1000000 }
    ::= {qtechRrmProfileDot11a 4 }

qtechRrmDot11aMobilesThreshold OBJECT-TYPE
    SYNTAX      INTEGER(1..75)
    MAX-ACCESS  read-write
    STATUS      current
    DESCRIPTION
            "802.11A mobiles threshold between 1 and 75"
    DEFVAL { 12 }
    ::= {qtechRrmProfileDot11a 5 }


--********************************************************************
--                                                                  **
--                         RRM Monitor                              **
--                                                                  **
--********************************************************************
qtechRrmDot11bMonitorEnable OBJECT-TYPE
    SYNTAX      INTEGER { enable (1), disable (0) }
    MAX-ACCESS  read-write
    STATUS      current
    DESCRIPTION
        "Enable or disable monitor function."
    DEFVAL { enable }
    ::= { qtechRrmMonitorDot11b 1 }

qtechRrmDot11bChannelMonitorList OBJECT-TYPE
    SYNTAX      INTEGER {
        all(1),
        country(2),
        dca(3)
    }
    MAX-ACCESS  read-write
    STATUS      current
    DESCRIPTION
    "This attribute specifies the channels on which the switch monitors
     noise, interference and rogues.  The first option allows
     monitoring on all channels while the second one on only those
     that are supported by the country of operation. the option dca
     implies that the monitor channel list will include those channels
     that are used by automatic channel assignment."
    DEFVAL { country }
    ::= { qtechRrmMonitorDot11b 2 }

qtechRrmDot11bMonitorInterval OBJECT-TYPE
    SYNTAX      Unsigned32(60..3600)
    MAX-ACCESS  read-write
    STATUS      current
    DESCRIPTION
       "This interval( in secs) specifies how often the AP goto off
       channel state to monitor. Default is 300 secs"
    DEFVAL { 180 }
    ::= {qtechRrmMonitorDot11b 3}

qtechRrmDot11bCoverageMeasurementInterval OBJECT-TYPE
    SYNTAX      Unsigned32(60..3600)
    MAX-ACCESS  read-write
    STATUS      current
    DESCRIPTION
       "This interval( in secs) specifies how often do we get new
       coverage measurements at each Qtech AP. Default is 300 secs"
    DEFVAL { 180 }
    ::= {qtechRrmMonitorDot11b 4}

qtechRrmDot11bLoadMeasurementInterval OBJECT-TYPE
    SYNTAX      Unsigned32(60..3600)
    MAX-ACCESS  read-write
    STATUS      current
    DESCRIPTION
       "This interval( in secs) specifies how often do we get new
       load measurements at each Qtech AP. Default is 300 secs"
    DEFVAL { 60 }
    ::= {qtechRrmMonitorDot11b 5}

qtechRrmDot11bNoiseMeasurementInterval OBJECT-TYPE
    SYNTAX      Unsigned32(60..3600)
    MAX-ACCESS  read-write
    STATUS      current
    DESCRIPTION
       "This interval( in secs) specifies how often do we get new
        noise and interference measurements at each Qtech AP.
        Default is 300 secs"
    DEFVAL { 180 }
    ::= { qtechRrmMonitorDot11b 6 }

qtechRrmDot11bSignalMeasurementInterval OBJECT-TYPE
    SYNTAX      Unsigned32(60..3600)
    MAX-ACCESS  read-write
    STATUS      current
    DESCRIPTION
       "This interval (in secs) specifies how often do we get new
        signal strength measurements at each Qtech AP. Default is
        300 secs"
    DEFVAL { 60 }
    ::= { qtechRrmMonitorDot11b 7 }

qtechRrmDot11bNeighborMessageInterval OBJECT-TYPE
    SYNTAX      Unsigned32(60..3600)
    MAX-ACCESS  read-write
    STATUS      current
    DESCRIPTION
       "This interval (in secs) specifies how often the AP send
       neighbor message"
    DEFVAL { 60 }
    ::= { qtechRrmMonitorDot11b 8 }


qtechRrmDot11aMonitorEnable OBJECT-TYPE
    SYNTAX      INTEGER { enable (1), disable (0) }
    MAX-ACCESS  read-write
    STATUS      current
    DESCRIPTION
        "Enable or disable monitor function."
    DEFVAL { enable }
    ::= { qtechRrmMonitorDot11a 1 }

qtechRrmDot11aChannelMonitorList OBJECT-TYPE
    SYNTAX      INTEGER {
        all(1),
        country(2),
        dca(3)
    }
    MAX-ACCESS  read-write
    STATUS      current
    DESCRIPTION
    "This attribute specifies the channels on which the switch monitors
     noise, interference and rogues.  The first option allows
     monitoring on all channels while the second one on only those
     that are supported by the country of operation. the option dca
     implies that the monitor channel list will include those channels
     that are used by automatic channel assignment."
    DEFVAL { country }
    ::= { qtechRrmMonitorDot11a 2 }

qtechRrmDot11aMonitorInterval OBJECT-TYPE
    SYNTAX      Unsigned32(60..3600)
    MAX-ACCESS  read-write
    STATUS      current
    DESCRIPTION
       "This interval( in secs) specifies how often the AP goto off
       channel state to monitor. Default is 300 secs"
    DEFVAL { 180 }
    ::= {qtechRrmMonitorDot11a 3}

qtechRrmDot11aCoverageMeasurementInterval OBJECT-TYPE
    SYNTAX      Unsigned32(60..3600)
    MAX-ACCESS  read-write
    STATUS      current
    DESCRIPTION
       "This interval( in secs) specifies how often do we get new
       coverage measurements at each Qtech AP. Default is 300 secs"
    DEFVAL { 180 }
    ::= {qtechRrmMonitorDot11a 4}

qtechRrmDot11aLoadMeasurementInterval OBJECT-TYPE
    SYNTAX      Unsigned32(60..3600)
    MAX-ACCESS  read-write
    STATUS      current
    DESCRIPTION
       "This interval( in secs) specifies how often do we get new
       load measurements at each Qtech AP. Default is 300 secs"
    DEFVAL { 60 }
    ::= {qtechRrmMonitorDot11a 5}

qtechRrmDot11aNoiseMeasurementInterval OBJECT-TYPE
    SYNTAX      Unsigned32(60..3600)
    MAX-ACCESS  read-write
    STATUS      current
    DESCRIPTION
       "This interval( in secs) specifies how often do we get new
        noise and interference measurements at each Qtech AP.
        Default is 300 secs"
    DEFVAL { 180 }
    ::= { qtechRrmMonitorDot11a 6 }

qtechRrmDot11aSignalMeasurementInterval OBJECT-TYPE
    SYNTAX      Unsigned32(60..3600)
    MAX-ACCESS  read-write
    STATUS      current
    DESCRIPTION
       "This interval (in secs) specifies how often do we get new
        signal strength measurements at each Qtech AP. Default is
        300 secs"
    DEFVAL { 60 }
    ::= { qtechRrmMonitorDot11a 7 }

qtechRrmDot11aNeighborMessageInterval OBJECT-TYPE
    SYNTAX      Unsigned32(60..3600)
    MAX-ACCESS  read-write
    STATUS      current
    DESCRIPTION
       "This interval (in secs) specifies how often the AP send
       neighbor message"
    DEFVAL { 60 }
    ::= { qtechRrmMonitorDot11a 8 }


--********************************************************************
--                                                                  **
--                    Set Factory Defaults                          **
--                                                                  **
--********************************************************************
qtechRrmDot11bSetFactoryDefault OBJECT-TYPE
    SYNTAX      INTEGER {default(0),activate (1)}
    MAX-ACCESS  read-write
    STATUS      current
    DESCRIPTION
            "When set to activate all Rrm parameters are reset to
            factory defaults"
   ::= { qtechRrmFactoryDot11b 1 }

qtechRrmDot11aSetFactoryDefault OBJECT-TYPE
    SYNTAX      INTEGER {default(0),activate (1)}
    MAX-ACCESS  read-write
    STATUS      current
    DESCRIPTION
            "When set to activate all Rrm parameters are reset to
            factory defaults"
   ::= { qtechRrmFactoryDot11a 1 }


-- *************************************************************
-- qtechRrmTrapControl would specify all the objects that enable/disable the
-- the generation of traps by Qtech Switch
-- qtechRrmTraps would specify all the possible traps that Qtech Switch
-- would need to generate
-- *************************************************************

--***************** define the qtechRrmMIBObjects nodes *****************
qtechRrmTrapControl    OBJECT IDENTIFIER ::= { qtechRrmMIBTraps 1 }
qtechRrmTrapVariable   OBJECT IDENTIFIER ::= { qtechRrmMIBTraps 2 }
qtechRrmTraps          OBJECT IDENTIFIER ::= { qtechRrmMIBTraps 3 }


-- *************************************************************
-- extra trap variables definining here
-- *************************************************************
-- for AP infomation
qtechRrmAPMacAddrTrapVariable OBJECT-TYPE
    SYNTAX      MacAddress
    MAX-ACCESS  accessible-for-notify
    STATUS      current
    DESCRIPTION
            "the variable of ap radio MAC address in trap"
    ::= { qtechRrmTrapVariable 1 }

qtechRrmAPRadioIDTrapVariable OBJECT-TYPE
    SYNTAX      Integer32
    MAX-ACCESS  accessible-for-notify
    STATUS      current
    DESCRIPTION
            "the variable of radio id in trap"
    ::= { qtechRrmTrapVariable 2 }

qtechRrmAPRadioTypeTrapVariable OBJECT-TYPE
    SYNTAX      INTEGER  {type80211a(0), type80211b(1)}
    MAX-ACCESS  accessible-for-notify
    STATUS      current
    DESCRIPTION
            "the variable of radio type in trap"
    ::= { qtechRrmTrapVariable 3 }

-- Get Trap Value
qtechRrmClientNumberTrapVariable OBJECT-TYPE
    SYNTAX      Integer32
    MAX-ACCESS  accessible-for-notify
    STATUS      current
    DESCRIPTION
            "the variable of client number in trap"
    ::= { qtechRrmTrapVariable 4 }

qtechRrmForeignInterfereTrapVariable OBJECT-TYPE
    SYNTAX      Integer32
    MAX-ACCESS  accessible-for-notify
    STATUS      current
    DESCRIPTION
            "the variable of interference in trap"
    ::= { qtechRrmTrapVariable 5 }

qtechRrmNoiseTrapVariable OBJECT-TYPE
    SYNTAX      Integer32
    MAX-ACCESS  accessible-for-notify
    STATUS      current
    DESCRIPTION
            "the variable of noise in trap"
    ::= { qtechRrmTrapVariable 6 }

qtechRrmThroughputTrapVariable OBJECT-TYPE
    SYNTAX      Unsigned32
    MAX-ACCESS  accessible-for-notify
    STATUS      current
    DESCRIPTION
            "the variable of throughput in trap"
    ::= { qtechRrmTrapVariable 7 }

qtechRrmUtilizationTrapVariable OBJECT-TYPE
    SYNTAX      Integer32
    MAX-ACCESS  accessible-for-notify
    STATUS      current
    DESCRIPTION
            "the variable of utilization in trap"
    ::= { qtechRrmTrapVariable 8 }

-- for TPC
qtechRrmAPTxPowerBeforeChange OBJECT-TYPE
    SYNTAX      Integer32
    MAX-ACCESS  accessible-for-notify
    STATUS      current
    DESCRIPTION
    "The txpower level before change"
    ::= {  qtechRrmTrapVariable 9 }

qtechRrmAPTxPowerAfterChange OBJECT-TYPE
    SYNTAX      Integer32
    MAX-ACCESS  accessible-for-notify
    STATUS      current
    DESCRIPTION
    "The txpower level after change"
    ::= {  qtechRrmTrapVariable 10 }

-- for DCA
qtechRrmAPChannelNumberBeforeChannge OBJECT-TYPE
    SYNTAX      Integer32
    MAX-ACCESS  accessible-for-notify
    STATUS      current
    DESCRIPTION
    "The channel before change"
    ::= {  qtechRrmTrapVariable 11 }

qtechRrmAPChannelNumberAfterChannge OBJECT-TYPE
    SYNTAX      Integer32
    MAX-ACCESS  accessible-for-notify
    STATUS      current
    DESCRIPTION
    "The channel after channge"
    ::= {  qtechRrmTrapVariable 12 }


qtechRrmDot11bGroupLeaderMacAddrTrapVariable OBJECT-TYPE
    SYNTAX      MacAddress
    MAX-ACCESS  accessible-for-notify
    STATUS      current
    DESCRIPTION
            "The MAC address of the group leader."
    ::= { qtechRrmTrapVariable 13 }

qtechRrmDot11aGroupLeaderMacAddrTrapVariable OBJECT-TYPE
    SYNTAX      MacAddress
    MAX-ACCESS  accessible-for-notify
    STATUS      current
    DESCRIPTION
            "The MAC address of the group leader."
    ::= { qtechRrmTrapVariable 14 }

qtechRrmAPChannelChangeReason OBJECT-TYPE
    SYNTAX  	INTEGER {
            signal(1),
            interference(2),
            noise(3),
	          load(4),
	          radar(5),
	          other(6)
     }
    MAX-ACCESS 	accessible-for-notify
    STATUS 	current
    DESCRIPTION
	     "The reason cause the channel changed"
    ::= { qtechRrmTrapVariable 15 }

qtechRrmAPChannelChangeReasonValue OBJECT-TYPE
    SYNTAX      Integer32
    MAX-ACCESS  accessible-for-notify
    STATUS      current
    DESCRIPTION
    	     "The special value along with the reason of channel change"
    ::= {  qtechRrmTrapVariable 16 }

qtechRrmAPTxPowerChangeCoverageFlag OBJECT-TYPE
    SYNTAX      INTEGER {no(0),yes(1)}
    MAX-ACCESS  accessible-for-notify
    STATUS      current
    DESCRIPTION
    	    "Indication the power change cause by which algorithm, TPC
    	    Algorithm or CHD Algorithm"
    ::= {  qtechRrmTrapVariable 17 }

qtechRrmDFSFreeCount OBJECT-TYPE
    SYNTAX      INTEGER
    MAX-ACCESS  accessible-for-notify
    STATUS      current
    DESCRIPTION
    	    "Indication the number of channel usable"
    ::= {  qtechRrmTrapVariable 18 }

qtechRrmAPChannelChangeCount OBJECT-TYPE
    SYNTAX      INTEGER
    MAX-ACCESS  accessible-for-notify
    STATUS      current
    DESCRIPTION
    	    "the number of channel change"
    ::= {  qtechRrmTrapVariable 19 }

-- *************************************************************
-- Whenever LOAD, NOISE, INTERFERENCE, COVERAGE Profile state changes
-- from PASS to FAIL for Qtech AP IF, notification will be sent, if
-- configured to do so.
-- *************************************************************

qtechRrmAPDot11bProfileTrapControlMask OBJECT-TYPE
    SYNTAX      Unsigned32
    MAX-ACCESS  read-write
    STATUS      current
    DESCRIPTION
           "This mask describes what events merit traps to network
            management. If the bit for a particular event is turned
            on then notification will be generated on event occurance.
                Event                    corresponding bit
                -----                    -----------------
                ClientNumProfileFail             1
                LoadProfileFail                  2
                NoiseProfileFail                 4
                InterferenceProfileFail          8
                PerformanceProfileFailed         16
           "
    DEFVAL { 0 }
    ::= { qtechRrmTrapControl 1 }

qtechRrmAPDot11aProfileTrapControlMask OBJECT-TYPE
    SYNTAX      Unsigned32
    MAX-ACCESS  read-write
    STATUS      current
    DESCRIPTION
           "This mask describes what events merit traps to network
            management. If the bit for a particular event is turned
            on then notification will be generated on event occurance.
                Event                    corresponding bit
                -----                    -----------------
                ClientNumProfileFail             1
                LoadProfileFail                  2
                NoiseProfileFail                 4
                InterferenceProfileFail          8
                PerformanceProfileFailed         16
           "
    DEFVAL { 0 }
    ::= { qtechRrmTrapControl 2 }

qtechRrmAPClientNumProfileFailed NOTIFICATION-TYPE
    OBJECTS {
        qtechRrmAPMacAddrTrapVariable,
        qtechRrmAPRadioIDTrapVariable,
        qtechRrmAPRadioTypeTrapVariable,
        qtechRrmClientNumberTrapVariable
    }
    STATUS current
    DESCRIPTION
        "too many clients "
    ::= { qtechRrmTraps 1 }

qtechRrmAPLoadProfileFailed NOTIFICATION-TYPE
    OBJECTS {
        qtechRrmAPMacAddrTrapVariable,
        qtechRrmAPRadioIDTrapVariable,
        qtechRrmAPRadioTypeTrapVariable,
        qtechRrmUtilizationTrapVariable
    }
    STATUS current
    DESCRIPTION
        "When LOAD Profile state changes from PASS to FAIL,
         notification will be sent with Dot3 MAC address of Qtech
         AP and slot ID of Qtech AP IF. This trap sending can be
         enable/disable using qtechRrmRrmProfileTrapControlFlag "
    ::= { qtechRrmTraps 2 }

qtechRrmAPNoiseProfileFailed NOTIFICATION-TYPE
    OBJECTS {
        qtechRrmAPMacAddrTrapVariable,
        qtechRrmAPRadioIDTrapVariable,
        qtechRrmAPRadioTypeTrapVariable,
        qtechRrmNoiseTrapVariable
    }
    STATUS current
    DESCRIPTION
        "When Noise Profile state changes from PASS to FAIL,
         notification will be sent with Dot3 MAC address of Qtech
         AP and slot ID of Qtech AP IF. This trap sending can be
         enable/disable using qtechRrmRrmProfileTrapControlFlag "
    ::= { qtechRrmTraps 3 }

qtechRrmAPInterferenceProfileFailed NOTIFICATION-TYPE
    OBJECTS {
        qtechRrmAPMacAddrTrapVariable,
        qtechRrmAPRadioIDTrapVariable,
        qtechRrmAPRadioTypeTrapVariable,
        qtechRrmForeignInterfereTrapVariable
    }
    STATUS current
    DESCRIPTION
        "When Interference Profile state changes from PASS to FAIL,
         notification will be sent with Dot3 MAC address of Qtech
         AP and slot ID of Qtech AP IF. This trap sending can be
         enable/disable using qtechRrmRrmProfileTrapControlFlag "
    ::= { qtechRrmTraps 4 }

qtechRrmAPPerformanceProfileFailed NOTIFICATION-TYPE
    OBJECTS {
        qtechRrmAPMacAddrTrapVariable,
        qtechRrmAPRadioIDTrapVariable,
        qtechRrmAPRadioTypeTrapVariable,
        qtechRrmThroughputTrapVariable
    }
    STATUS current
    DESCRIPTION
        " "
    ::= { qtechRrmTraps 5 }

qtechRrmAPClientNumProfileUpdatedToPass NOTIFICATION-TYPE
    OBJECTS {
        qtechRrmAPMacAddrTrapVariable,
        qtechRrmAPRadioIDTrapVariable,
        qtechRrmAPRadioTypeTrapVariable,
        qtechRrmClientNumberTrapVariable
    }
    STATUS current
    DESCRIPTION
        ""
    ::= { qtechRrmTraps 6 }

qtechRrmAPLoadProfileUpdatedToPass NOTIFICATION-TYPE
    OBJECTS {
        qtechRrmAPMacAddrTrapVariable,
        qtechRrmAPRadioIDTrapVariable,
        qtechRrmAPRadioTypeTrapVariable,
        qtechRrmUtilizationTrapVariable
    }
    STATUS current
    DESCRIPTION
        "When LOAD Profile state changes from FAIL to PASSt this
         notification will be sent with Dot3 MAC address of Qtech
         AP and slot ID of Qtech AP IF. This trap sending can be
         enable/disable using qtechRrmRrmProfileTrapControlFlag "
    ::= { qtechRrmTraps 7 }

qtechRrmAPNoiseProfileUpdatedToPass NOTIFICATION-TYPE
    OBJECTS {
        qtechRrmAPMacAddrTrapVariable,
        qtechRrmAPRadioIDTrapVariable,
        qtechRrmAPRadioTypeTrapVariable,
        qtechRrmNoiseTrapVariable
    }
    STATUS current
    DESCRIPTION
        "When Noise Profile state changes from FAIL tp PASS,
         notification will be sent with Dot3 MAC address of Qtech
         AP and slot ID of Qtech AP IF. This trap sending can be
         enable/disable using qtechRrmRrmProfileTrapControlFlag "
    ::= { qtechRrmTraps 8 }

qtechRrmAPInterferenceProfileUpdatedToPass NOTIFICATION-TYPE
    OBJECTS {
        qtechRrmAPMacAddrTrapVariable,
        qtechRrmAPRadioIDTrapVariable,
        qtechRrmAPRadioTypeTrapVariable,
        qtechRrmForeignInterfereTrapVariable
    }
    STATUS current
    DESCRIPTION
        "When Interference Profile state changes from FAIL tp PASS,
         notification will be sent with Dot3 MAC address of Qtech
         AP and slot ID of Qtech AP IF. This trap sending can be
         enable /disable using qtechRrmRrmProfileTrapControlFlag "
    ::= { qtechRrmTraps 9 }

qtechRrmAPPerformanceProfileUpdatedToPass NOTIFICATION-TYPE
    OBJECTS {
        qtechRrmAPMacAddrTrapVariable,
        qtechRrmAPRadioIDTrapVariable,
        qtechRrmAPRadioTypeTrapVariable,
        qtechRrmThroughputTrapVariable
    }
    STATUS current
    DESCRIPTION
        " "
    ::= { qtechRrmTraps 10 }


qtechRrmAPDot11bParamUpdateTrapControlMask OBJECT-TYPE
    SYNTAX      Unsigned32
    MAX-ACCESS  read-write
    STATUS      current
    DESCRIPTION
           "Mac Parameters are updated for a Qtech AP interface
            whenever Dynamic Algorithm are run. This mask describes
            what update events merit traps to network management. If
            the bit for a particular event is turned on then
            notification will be generated on event occurance.
                Event                    corresponding bit
                -----                    -----------------
                TxPowerChange                  1
                ChannelChange                  2
           "
    DEFVAL { 0 }
    ::= { qtechRrmTrapControl 3 }

qtechRrmAPDot11aParamUpdateTrapControlMask OBJECT-TYPE
    SYNTAX      Unsigned32
    MAX-ACCESS  read-write
    STATUS      current
    DESCRIPTION
           "Mac Parameters are updated for a Qtech AP interface
            whenever Dynamic Algorithm are run. This mask describes
            what update events merit traps to network management. If
            the bit for a particular event is turned on then
            notification will be generated on event occurance.
                Event                    corresponding bit
                -----                    -----------------
                TxPowerChange                  1
                ChannelChange                  2
           "
    DEFVAL { 0 }
    ::= { qtechRrmTrapControl 4 }

qtechRrmAPCurrentTxPowerChanged NOTIFICATION-TYPE
    OBJECTS {
        qtechRrmAPMacAddrTrapVariable,
        qtechRrmAPRadioIDTrapVariable,
        qtechRrmAPRadioTypeTrapVariable,
        qtechRrmAPTxPowerBeforeChange,
        qtechRrmAPTxPowerAfterChange,
        qtechRrmAPTxPowerChangeCoverageFlag
    }
    STATUS current
    DESCRIPTION
        "Whenever dynamic algorithms are running and
         qtechRrmAPIfPhyPowerAutomaticOn is true, Qtech AP Interface's
         CurrentTxPower might get updated by algorithm. When
         this occurs notification will be sent with Dot3 MAC address of
         Qtech AP and slot ID of Qtech AP IF along with the
         currentTxPower for this Qtech AP IF"
    ::= { qtechRrmTraps 11 }

qtechRrmAPCurrentChannelChanged NOTIFICATION-TYPE
    OBJECTS {
        qtechRrmAPMacAddrTrapVariable,
        qtechRrmAPRadioIDTrapVariable,
        qtechRrmAPRadioTypeTrapVariable,
        qtechRrmAPChannelNumberBeforeChannge,
        qtechRrmAPChannelNumberAfterChannge,
        qtechRrmAPChannelChangeReason,
        qtechRrmAPChannelChangeReasonValue,
        qtechRrmAPChannelChangeCount
    }
    STATUS current
    DESCRIPTION
        "Whenever dynamic algorithms are running and
         qtechRrmAPIfPhyChannelAutomaticOn is true, Qtech AP
         Interface's CurrentChannel might get updated by algorithm.
         When this occurs notification will be sent with Dot3 MAC
         address of Qtech AP and slot ID of Qtech AP IF along
         with the currentChannel for this Qtech AP IF"
    ::= { qtechRrmTraps 12 }


-- *************************************************************
-- Also, when dynamic grouping is done and new Group leader is choosen
-- NMS needs to be informed so that necessary updates can be done in
-- NMS.
-- *************************************************************

qtechRrmDot11bGroupingDone NOTIFICATION-TYPE
    OBJECTS { qtechRrmDot11bGroupLeaderMacAddrTrapVariable }
    STATUS current
    DESCRIPTION
        "When Grouping is done, this notification will be sent from the
         previous Group Leader where grouping algorithm was run. It has
         MAC address of the new Group Leader."
    ::= { qtechRrmTraps 13 }

qtechRrmDot11aGroupingDone NOTIFICATION-TYPE
    OBJECTS { qtechRrmDot11aGroupLeaderMacAddrTrapVariable }
    STATUS current
    DESCRIPTION
        "When Grouping is done, this notification will be sent from the
         previous Group Leader where grouping algorithm was run. It has
         MAC address of the new Group Leader."
    ::= { qtechRrmTraps 14 }


qtechRrmDot11bDFSFreeCountBelowThreshold NOTIFICATION-TYPE
    OBJECTS { qtechRrmDFSFreeCount }
    STATUS current
    DESCRIPTION
        "When the free channel in 802.11b DCA too few, this notification
         will be sent"
    ::= { qtechRrmTraps 15 }

qtechRrmDot11aDFSFreeCountBelowThreshold NOTIFICATION-TYPE
    OBJECTS { qtechRrmDFSFreeCount }
    STATUS current
    DESCRIPTION
        "When the free channel in 802.11b DCA too few, this notification
         will be sent"
    ::= { qtechRrmTraps 16 }

qtechRrmNeighborAPInterference NOTIFICATION-TYPE
    OBJECTS { qtechRrmAPMacAddrTrapVariable }
    STATUS current
    DESCRIPTION
        "notice when find interference form neighbor AP"
    ::= { qtechRrmTraps 17 }

qtechRrmStationInterference NOTIFICATION-TYPE
    OBJECTS { qtechRrmAPMacAddrTrapVariable }
    STATUS current
    DESCRIPTION
        "notice when find interference form station"
    ::= { qtechRrmTraps 18 }

qtechRrmOtherDiveceInterference NOTIFICATION-TYPE
    OBJECTS { qtechRrmAPMacAddrTrapVariable }
    STATUS current
    DESCRIPTION
        "notice when find interference form other divece"
    ::= { qtechRrmTraps 19 }

--***************** define the qtechRrmMIBConformance nodes ************
qtechRrmMIBCompliances OBJECT IDENTIFIER ::= { qtechRrmMIBConformance 1 }
qtechRrmMIBGroups      OBJECT IDENTIFIER ::= { qtechRrmMIBConformance 2 }

--********************************************************************
--                                                                  **
--           compliance statements                                  **
--                                                                  **
--********************************************************************
qtechRrmMIBCompliance MODULE-COMPLIANCE
    STATUS  current
    DESCRIPTION
            "The compliance statement for entities which implement
            the Qtech RRM module"
    MODULE  -- this module
        MANDATORY-GROUPS {
            qtechRrmMIBGroup,
            qtechRrmTrapsGroup
        }
    ::= { qtechRrmMIBCompliances 1 }

--********************************************************************
--                                                                  **
--           units of conformance                                   **
--                                                                  **
--********************************************************************
qtechRrmMIBGroup OBJECT-GROUP
    OBJECTS {

--Begin rf group
        qtechRrmRFNetworkName,

--Begin AP auto-rf
				qtechRrmAPName,
				qtechRrmAPIfThresholdRadioType,
				qtechRrmAPIfForeignInterferenceThreshold,
				qtechRrmAPIfForeignNoiseThreshold,
				qtechRrmAPIfRFUtilizationThreshold,
				qtechRrmAPIfThroughputThreshold,
				qtechRrmAPIfMobilesThreshold,
				qtechRrmAPIfThresholdMacAddr,
        qtechRrmAPIfThresholdRadioType,
        qtechRrmAPIfThresholdName,

				qtechRrmAPIfLoadRxUtilization,
				qtechRrmAPIfLoadTxUtilization,
				qtechRrmAPIfLoadChannelUtilization,
				qtechRrmAPIfLoadNumOfClients,
				qtechRrmAPIfPoorSNRClients,
				qtechRrmAPIfLoadName,
        qtechRrmAPIfLoadMacAddr,
        qtechRrmAPIfLoadSlotId,
        qtechRrmAPIfThroughput,

				qtechRrmAPIfInterferenceChannelNo,
				qtechRrmAPIfInterferencePower,
				qtechRrmAPIfInterferenceUtilization,
				qtechRrmAPIfInterferenceName,
        qtechRrmAPIfInterferenceMacAddr,
        qtechRrmAPIfInterferenceSlotId,

				qtechRrmAPIfNoiseChannelNo,
				qtechRrmAPIfDBNoisePower,
				qtechRrmAPIfNoiseName,
        qtechRrmAPIfNoiseMacAddr,
        qtechRrmAPIfNoiseSlotId,

				qtechRrmAPIfLoadProfileState,
				qtechRrmAPIfInterferenceProfileState,
				qtechRrmAPIfNoiseProfileState,
				qtechRrmAPIfCoverageProfileState,
				qtechRrmAPIfPerformanceProfileState,
				qtechRrmAPIfProfileName,
        qtechRrmAPIfProfileMacAddr,
        qtechRrmAPIfProfileSlotId,

				qtechRrmAPIfRxNeighborMacAddress,
				qtechRrmAPIfRxNeighborSlot,
				qtechRrmAPIfRxNeighborIpAddress,
				qtechRrmAPIfRxNeighborRSSI,
				qtechRrmAPIfRxNeighborSNR,
				qtechRrmAPIfRxNeighborChannel,
				qtechRrmAPIfRxNeighborChannelWidth,
				qtechRrmAPIfRxNeighborName,
        qtechRrmAPIfRxNeighborMacAddr,
        qtechRrmAPIfRxNeighborSlotId,

				qtechRrmAPIfStationRSSICoverageIndex,
				qtechRrmAPIfRSSILevel,
				qtechRrmAPIfStationCountOnRSSI,
				qtechRrmAPIfStationRSSIName,
        qtechRrmAPIfStationRSSIMacAddr,
        qtechRrmAPIfStationRSSISlotId,

				qtechRrmAPIfStationSNRCoverageIndex,
				qtechRrmAPIfSNRLevel,
				qtechRrmAPIfStationCountOnSNR,
				qtechRrmAPIfStationSNRName,
        qtechRrmAPIfStationSNRMacAddr,
        qtechRrmAPIfStationSNRSlotId,

				qtechRrmAPIfRecommendedChannelNumber,
				qtechRrmAPIfRecommendedTxPowerLevel,
				qtechRrmAPIfRecommendedRTSThreshold,
				qtechRrmAPIfRecommendedFragmentationThreshold,
				qtechRrmAPIfRecommendedName,
        qtechRrmAPIfRecommendedMacAddr,
        qtechRrmAPIfRecommendedSlotId,

     		qtechRrmAPRadioID,
     		qtechRrmAPRadioType,
     		qtechRrmAPRealName,
        qtechRrmAPMacAddr,

        qtechRrmAPIfThroughputMacAddr,
        qtechRrmAPIfThroughputSlotId,
        qtechRrmAPIfThroughputAPName,
     	qtechRrmAPIfThroughputRx,
   	qtechRrmAPIfThroughputTx,
   	qtechRrmAPIfThroughputTotal,

        qtechRrmAPSnrBSSIDMacAddr,
        qtechRrmAPSnrBSSIDSlotId,
        qtechRrmAPSnrBSSIDAPName,
     	qtechRrmAPSnrBSSIDAverageSignalStrength,
   	qtechRrmAPSnrBSSIDSignalPkts,
   	qtechRrmAPSnrBSSIDHighestRxSignalStrength,
   	qtechRrmAPSnrBSSIDLowestRxSignalStrength,
   	qtechRrmAPSnrBSSIDSampleTime,

--Begin qtechRrmDCA
        qtechRrmDot11bDynamicChannelAssignment,
        qtechRrmDot11bAnchorTime,
        qtechRrmDot11bChannalWidth11n,
        qtechRrmDot11bDynamicChannelUpdateInterval,
        qtechRrmDot11bDCASensitivity,
        qtechRrmDot11bForeignInterfereFactorEnable,
        qtechRrmDot11bLoadFactorEnable,
        qtechRrmDot11bNoiseFactorEnable,
        qtechRrmDot11bChannelUpdateCmdInvoke,
        qtechRrmDot11bDCAChannelIndex,
        qtechRrmDot11bDCAChannelOperation,
        qtechRrmDot11aDynamicChannelAssignment,
        qtechRrmDot11aAnchorTime,
        qtechRrmDot11aChannalWidth11n,
        qtechRrmDot11aDynamicChannelUpdateInterval,
        qtechRrmDot11aDCASensitivity,
        qtechRrmDot11aForeignInterfereFactorEnable,
        qtechRrmDot11aLoadFactorEnable,
        qtechRrmDot11aNoiseFactorEnable,
        qtechRrmDot11aChannelUpdateCmdInvoke,
        qtechRrmDot11aDCAChannelIndex,
        qtechRrmDot11aDCAChannelOperation,

--Begin qtechRrmTPC
        qtechRrmDot11bDTPCSupport,
        qtechRrmDot11bDynamicTransmitPowerControl,
        qtechRrmDot11bDynamicTxPowerControlInterval,
        qtechRrmDot11bCurrentTxPowerLevel,
        qtechRrmDot11bPowerUpdateCmdInvoke,
        qtechRrmDot11bTXPowerThreshold,
        qtechRrmDot11bTPCNeighborNumber,
        qtechRrmDot11aDTPCSupport,
        qtechRrmDot11aDynamicTransmitPowerControl,
        qtechRrmDot11aDynamicTxPowerControlInterval,
        qtechRrmDot11aCurrentTxPowerLevel,
        qtechRrmDot11aPowerUpdateCmdInvoke,
        qtechRrmDot11aTXPowerThreshold,
        qtechRrmDot11aTPCNeighborNumber,

--Begin qtechRrmCHD
        qtechRrmDot11bCoverageEnable,
        qtechRrmDot11bCoverageExceptionGlobal,
        qtechRrmDot11bCoverageLevelGlobal,
        qtechRrmDot11bCoverageDataRSSIThreshold,
        qtechRrmDot11bCoverageVoiceRSSIThreshold,
        qtechRrmDot11bCoverageDataPacketCount,
        qtechRrmDot11bCoverageVoicePacketCount,
        qtechRrmDot11bCoverageDataFailRate,
        qtechRrmDot11bCoverageVoiceFailRate,
        qtechRrmDot11aCoverageEnable,
        qtechRrmDot11aCoverageExceptionGlobal,
        qtechRrmDot11aCoverageLevelGlobal,
        qtechRrmDot11aCoverageDataRSSIThreshold,
        qtechRrmDot11aCoverageVoiceRSSIThreshold,
        qtechRrmDot11aCoverageDataPacketCount,
        qtechRrmDot11aCoverageVoicePacketCount,
        qtechRrmDot11aCoverageDataFailRate,
        qtechRrmDot11aCoverageVoiceFailRate,

--Begin qtechRrmGroup
        qtechRrmDot11bGlobalAutomaticGrouping,
        qtechRrmDot11bGroupLeaderMacAddr,
        qtechRrmDot11bGroupLeader,
        qtechRrmDot11bGroupLastUpdateTime,
        qtechRrmDot11bGroupInterval,
        qtechRrmDot11bPeerMacAddress,
        qtechRrmDot11bPeerIpAddress,
        qtechRrmDot11bAPname,
        qtechRrmDot11bAPRadioID,
        qtechRrmDot11bAPChannel,
        qtechRrmDot11bAPTxPower,
        qtechRrmDot11bAPChannelRrmChangeFlag,
        qtechRrmDot11bAPTxPowerRrmChangeFlag,
        qtechRrmDot11bSummaryMacAddress,

        qtechRrmDot11aGlobalAutomaticGrouping,
        qtechRrmDot11aGroupLeader,
        qtechRrmDot11aGroupLastUpdateTime,
        qtechRrmDot11aGroupInterval,
        qtechRrmDot11aPeerMacAddress,
        qtechRrmDot11aPeerIpAddress,
        qtechRrmDot11aAPname,
        qtechRrmDot11aAPRadioID,
        qtechRrmDot11aAPChannel,
        qtechRrmDot11aAPTxPower,
        qtechRrmDot11aAPChannelRrmChangeFlag,
        qtechRrmDot11aAPTxPowerRrmChangeFlag,
        qtechRrmDot11aSummaryMacAddress,

--Begin qtechRrmProfile
        qtechRrmDot11bForeignInterferenceThreshold,
        qtechRrmDot11bForeignNoiseThreshold,
        qtechRrmDot11bRFUtilizationThreshold,
        qtechRrmDot11bThroughputThreshold,
        qtechRrmDot11bMobilesThreshold,
        qtechRrmDot11aForeignInterferenceThreshold,
        qtechRrmDot11aForeignNoiseThreshold,
        qtechRrmDot11aRFUtilizationThreshold,
        qtechRrmDot11aThroughputThreshold,
        qtechRrmDot11aMobilesThreshold,

--Begin qtechRrmMonitor
        qtechRrmDot11bMonitorEnable,
        qtechRrmDot11bChannelMonitorList,
        qtechRrmDot11bMonitorInterval,
        qtechRrmDot11bCoverageMeasurementInterval,
        qtechRrmDot11bLoadMeasurementInterval,
        qtechRrmDot11bNoiseMeasurementInterval,
        qtechRrmDot11bSignalMeasurementInterval,
        qtechRrmDot11bNeighborMessageInterval,
        qtechRrmDot11aMonitorEnable,
        qtechRrmDot11aChannelMonitorList,
        qtechRrmDot11aMonitorInterval,
        qtechRrmDot11aCoverageMeasurementInterval,
        qtechRrmDot11aLoadMeasurementInterval,
        qtechRrmDot11aNoiseMeasurementInterval,
        qtechRrmDot11aSignalMeasurementInterval,
        qtechRrmDot11aNeighborMessageInterval,

--Begin qtechRrmFactory
        qtechRrmDot11bSetFactoryDefault,
        qtechRrmDot11aSetFactoryDefault
    }
    STATUS      current
    DESCRIPTION
        "This collection of objects provide the information
         about Qtech Radio Resource Management Configuration
         Parameters. These objects are defined under qtechRrmRrm object."
    ::= { qtechRrmMIBGroups 1 }

qtechRrmTrapsGroup OBJECT-GROUP
    OBJECTS {
--Begin qtechRrmTrapControl
        qtechRrmAPDot11bProfileTrapControlMask,
        qtechRrmAPDot11aProfileTrapControlMask,
        qtechRrmAPDot11bParamUpdateTrapControlMask,
        qtechRrmAPDot11aParamUpdateTrapControlMask,

--Begin qtechRrmTrapVariable
-- for Ap info
        qtechRrmAPMacAddrTrapVariable,
        qtechRrmAPRadioIDTrapVariable,
        qtechRrmAPRadioTypeTrapVariable,
-- for Trap value
        qtechRrmClientNumberTrapVariable,
        qtechRrmForeignInterfereTrapVariable,
        qtechRrmNoiseTrapVariable,
        qtechRrmThroughputTrapVariable,
        qtechRrmUtilizationTrapVariable,
-- for TPC
        qtechRrmAPTxPowerBeforeChange,
        qtechRrmAPTxPowerAfterChange,
        qtechRrmAPTxPowerChangeCoverageFlag,

-- for DCA
        qtechRrmAPChannelNumberBeforeChannge,
        qtechRrmAPChannelNumberAfterChannge,
        qtechRrmAPChannelChangeReason,
        qtechRrmAPChannelChangeReasonValue,
        qtechRrmAPChannelChangeCount,
        qtechRrmDFSFreeCount,

-- for leader
        qtechRrmDot11bGroupLeaderMacAddrTrapVariable,
        qtechRrmDot11aGroupLeaderMacAddrTrapVariable
    }
    STATUS      current
    DESCRIPTION
        "This collection of objects provide the information
         about Qtech Trap Configuration and Trap definition.
         These objects are defined under qtechRrmTrap."
    ::= { qtechRrmMIBGroups 2 }

qtechRrmTrap NOTIFICATION-GROUP
    NOTIFICATIONS {
        qtechRrmAPClientNumProfileFailed,
        qtechRrmAPLoadProfileFailed,
        qtechRrmAPNoiseProfileFailed,
        qtechRrmAPInterferenceProfileFailed,
        qtechRrmAPPerformanceProfileFailed,
        qtechRrmAPClientNumProfileUpdatedToPass,
        qtechRrmAPLoadProfileUpdatedToPass,
        qtechRrmAPNoiseProfileUpdatedToPass,
        qtechRrmAPInterferenceProfileUpdatedToPass,
        qtechRrmAPPerformanceProfileUpdatedToPass,
        qtechRrmAPCurrentTxPowerChanged,
        qtechRrmAPCurrentChannelChanged,
        qtechRrmDot11bGroupingDone,
        qtechRrmDot11aGroupingDone,
        qtechRrmDot11bDFSFreeCountBelowThreshold,
        qtechRrmDot11aDFSFreeCountBelowThreshold,
        qtechRrmNeighborAPInterference,
        qtechRrmStationInterference,
        qtechRrmOtherDiveceInterference
    }
    STATUS      current
    DESCRIPTION
        "This  collection of objects provides all notification
         that Switch need to generate to the Management System."
    ::= { qtechRrmMIBGroups 3 }

END
