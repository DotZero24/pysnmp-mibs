-- *****************************************************************
-- QTECH-IP-MANAGE-MIB.mib:  Qtech IP MANAGE MIB file
--
-- March 2002, Wuzg
--
-- Copyright (c) 2002 by Qtech Networks Co.,Ltd.
-- All rights reserved.
--
-- *****************************************************************
--

QTECH-IP-MANAGE-MIB DEFINITIONS ::= BEGIN

IMPORTS
        MODULE-IDENTITY,
        OBJECT-TYPE,
        IpAddress
                FROM SNMPv2-SMI
        MODULE-COMPLIANCE,
        OBJECT-GROUP
                FROM SNMPv2-CONF
        EnabledStatus
                FROM P-BRIDGE-MIB
        qtechMgmt
                FROM QTECH-SMI;

qtechIpManageMIB MODULE-IDENTITY
        LAST-UPDATED "200203200000Z"
        ORGANIZATION "Qtech Networks Co.,Ltd."
        CONTACT-INFO
                "
                Tel: 4008-111-000

                E-mail: service@qtech.com.cn"
        DESCRIPTION
                "This module defines qtech IP managment mibs."
        REVISION      "200203200000Z"
        DESCRIPTION
                "Initial version of this MIB module."
        ::= { qtechMgmt 12}

qtechDhcpMIBObjects OBJECT IDENTIFIER ::= { qtechIpManageMIB 1 }
qtechIpMIBObjects OBJECT IDENTIFIER ::= { qtechIpManageMIB 2 }
--
-- qtech  Dhcp Group
--

qtechDhcpRelayAgentGlobalStatus OBJECT-TYPE
    SYNTAX EnabledStatus
    MAX-ACCESS read-write
    STATUS current
    DESCRIPTION
            "Global Dhcp relay agent status"
    DEFVAL { disabled }
            ::={ qtechDhcpMIBObjects 2 }

qtechDhcpServerIp OBJECT-TYPE
    SYNTAX IpAddress
    MAX-ACCESS read-write
    STATUS current
    DESCRIPTION
             "Ip address of internet host which returns configuration
              parameters to DHCP clients."
        ::={ qtechDhcpMIBObjects 3 }


qtechIpDefaultGateWay OBJECT-TYPE
    SYNTAX IpAddress
    MAX-ACCESS read-write
    STATUS current
    DESCRIPTION
             "Ip default gateway of system. This value applay only in layer 2"
        ::={ qtechIpMIBObjects 1 }

qtechIpManageMIBConformance OBJECT IDENTIFIER ::= { qtechIpManageMIB 3 }
qtechIpManageMIBCompliances OBJECT IDENTIFIER ::= { qtechIpManageMIBConformance 1 }
qtechIpManageMIBGroups      OBJECT IDENTIFIER ::= { qtechIpManageMIBConformance 2 }


-- compliance statements

qtechIpManageMIBCompliance MODULE-COMPLIANCE
        STATUS  current
        DESCRIPTION
                "The compliance statement for entities which implement
                the Qtech Snooping Dhcp MIB"
        MODULE  -- this module
                MANDATORY-GROUPS { qtechL2L3DhcpManageMIBGroup
                 }
        ::= { qtechIpManageMIBCompliances 1 }

-- units of conformance

qtechL2L3DhcpManageMIBGroup OBJECT-GROUP
        OBJECTS {
           qtechDhcpRelayAgentGlobalStatus,
           qtechDhcpServerIp
        }
        STATUS  current
        DESCRIPTION
                "A collection of objects providing IP managment in layer2 or layer3 mode."
        ::= { qtechIpManageMIBGroups 1 }

END
