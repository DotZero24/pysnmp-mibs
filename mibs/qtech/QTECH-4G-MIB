-- ====================================================================
-- Copyright (c) 2011 by Qtech Networks Co.,Ltd. All rights reserved.
--
-- Description: The MIB is designed to get 3G wireless safenet solution statistic information.
-- Reference: rujie Enterprise MIB
-- =====================================================================

QTECH-4G-MIB DEFINITIONS ::= BEGIN

    IMPORTS
        DisplayString,TEXTUAL-CONVENTION,TimeStamp
            FROM SNMPv2-TC
        IpAddress, Integer32, Counter32, Counter64, OBJECT-TYPE,
        MODULE-IDENTITY, Gauge32, NOTIFICATION-TYPE, Unsigned32
            FROM SNMPv2-SMI
        MODULE-COMPLIANCE, OBJECT-GROUP, NOTIFICATION-GROUP
            FROM SNMPv2-CONF
        qtechMgmt
            FROM QTECH-SMI;

    qtech4GMonitor MODULE-IDENTITY
        LAST-UPDATED "201403110000Z"
        ORGANIZATION
            "Qtech Networks Co.,Ltd."
        CONTACT-INFO
            "Tel: 4008-111-000
             E-mail: service@qtech.com.cn"
        DESCRIPTION
            "The MIB is designed to get statistic information of
             4G wireless safenet. With this MIB, we can get information of a certain
             4G user or all users."
        REVISION      "201403110000Z"
        DESCRIPTION
                "Initial version of this MIB module."
        ::= { qtechMgmt 127 }


-- ========================================================================
-- Node definitions
-- ========================================================================
--Begin the node of qtech4gObjects.

    qtech4GObjects OBJECT IDENTIFIER ::= { qtech4GMonitor 1 }

-- ===============================================
-- Begin the table of qtech4GTable.
-- ===============================================

    qtech4GTable OBJECT-TYPE
        SYNTAX SEQUENCE OF Qtech4GEntry
        MAX-ACCESS not-accessible
        STATUS current
        DESCRIPTION
            "The 4G connection infomation fot every user. There is one
             entry in this table for each active 4G connection."
        ::= { qtech4GObjects 1 }

    qtech4GEntry OBJECT-TYPE
        SYNTAX Qtech4GEntry
        MAX-ACCESS not-accessible
        STATUS current
        DESCRIPTION
            "Information about qtech4GTunnelTable."
        INDEX { qtech4GRouterSlotNumber }
        ::= { qtech4GTable 1 }

    Qtech4GEntry ::=
        SEQUENCE {
            qtech4GUsername
                DisplayString,
            qtech4GApn
                DisplayString,
            qtech4GOnlineStatus
                INTEGER,
            qtech4GIMEI
                DisplayString,
            qtech4GIPAddrType
                INTEGER,
            qtech4GIPAddr
                IpAddress,
            qtech4GUplineTime
                TimeStamp,
            qtech4GActiveTime
                Integer32,
            qtech4GRSRP
                Integer32,
            qtech4GSignalStrengthPercent
                Integer32,
            qtech4GISP
                INTEGER,
            qtech4GSysMode
                INTEGER,
            qtech4GServiceStatus
                INTEGER,
            qtech4GRoamingStatus
                INTEGER,
            qtech4GDomain
                INTEGER,
            qtech4GSIMStatus
                INTEGER,
            qtech4GCellID
                Integer32,
            qtech4GLAC
                Integer32,
            qtech4GIMSI
                DisplayString,
            qtech4GPhoneNumber
                DisplayString,
            qtech4GifIndex
                INTEGER,
            qtech4GInOctets
                Counter64,
            qtech4GOutOctets
                Counter64,
            qtech4GInSpeed
                Counter64,
            qtech4GOutSpeed
                Counter64,
            qtech4GBSLONG
                Integer32,
            qtech4GBSLAT
                Integer32,
            qtech4GRouterType
                DisplayString,
            qtech4GRouterSN
                DisplayString,
            qtech4GRouterSlotNumber
                DisplayString,
            qtech4GLineCardType
                DisplayString,
            qtech4GDialdMode
		INTEGER,
            qtech4GDialOnDemandIfIndex
                INTEGER,
            qtech4GTrafficPreventMode
                INTEGER,
            qtech4GTrafficPreventIfIndex
                INTEGER,
            qtech4GTrafficPreventListID
                INTEGER,
            qtech4GTrafficPreventListName
                DisplayString
        }

    qtech4GUsername OBJECT-TYPE
        SYNTAX DisplayString
        MAX-ACCESS read-only
        STATUS current
        DESCRIPTION
            "The Username of 4G User."
        ::= { qtech4GEntry 1 }

    qtech4GApn OBJECT-TYPE
        SYNTAX DisplayString
        MAX-ACCESS read-only
        STATUS current
        DESCRIPTION
            "The access-point of 4G User."
        ::= { qtech4GEntry 2 }

    qtech4GOnlineStatus OBJECT-TYPE
        SYNTAX INTEGER
            {
                minimum-function(0),
                fully-function(1),
                offline-mode(2),
                sim-activate(3),
                sim-deactivate(4)
            }
        MAX-ACCESS read-only
        STATUS current
        DESCRIPTION
            "the status of 4G user. online or offline"
        ::= { qtech4GEntry 3 }

    qtech4GIMEI OBJECT-TYPE
        SYNTAX DisplayString
        MAX-ACCESS read-only
        STATUS current
        DESCRIPTION
            "the IMEI number of 4G user."
        ::= { qtech4GEntry 4 }

    qtech4GIPAddrType OBJECT-TYPE
         SYNTAX INTEGER {
            ipv4Addr(1),
            ipv6Addr(2)
        }
        MAX-ACCESS read-only
        STATUS current
        DESCRIPTION
            "The IP Address type of remote user."
        ::= { qtech4GEntry 5 }

    qtech4GIPAddr OBJECT-TYPE
        SYNTAX IpAddress
        MAX-ACCESS read-only
        STATUS current
        DESCRIPTION
            "The 4G remote users's IP address."
        ::= { qtech4GEntry 6 }

    qtech4GUplineTime OBJECT-TYPE
        SYNTAX TimeStamp
        MAX-ACCESS read-only
        STATUS current
        DESCRIPTION
            "The value of up line time for this 4G user."
        ::= { qtech4GEntry 7 }

    qtech4GActiveTime OBJECT-TYPE
        SYNTAX Integer32 (0..2147483647)
        MAX-ACCESS read-only
        STATUS current
        DESCRIPTION
            "The duration of the 4G connection has been active for one user.
            2147483647 is defined as invalid value."
        ::= { qtech4GEntry 8 }

    qtech4GRSRP OBJECT-TYPE
        SYNTAX Integer32 (-150..0)
        MAX-ACCESS read-only
        STATUS current
        DESCRIPTION
            "The RSRP of the 4G connection for this user."
        ::= { qtech4GEntry 9 }

    qtech4GSignalStrengthPercent OBJECT-TYPE
        SYNTAX Integer32 (0..100)
        MAX-ACCESS read-only
        STATUS current
        DESCRIPTION
            "The percent of signal strength of the 4G connection for this user."
        ::= { qtech4GEntry 10 }

    qtech4GISP OBJECT-TYPE
        SYNTAX INTEGER
            {
                unknow(0),
                chinaUnicom(1),
                chinaTelecom(2),
                chinaMobile(3)
            }
        MAX-ACCESS read-only
        STATUS current
        DESCRIPTION
            "the ISP of 4G networsk."
        ::= { qtech4GEntry 11 }

    qtech4GSysMode OBJECT-TYPE
        SYNTAX INTEGER
            {
                no-service(0),
                gsm-gprs(3),
                wcdma(5),
                td-scdma(15),
                lte(17)
            }
        MAX-ACCESS read-only
        STATUS current
        DESCRIPTION
            "the system mode of 4G networsk."
        ::= { qtech4GEntry 12 }

    qtech4GServiceStatus OBJECT-TYPE
        SYNTAX INTEGER
            {
                noService(0),
                restricted(1),
                valid(2),
                restrictedRegional(3),
                powerSavingAndDeepSleepState(4)
            }
        MAX-ACCESS read-only
        STATUS current
        DESCRIPTION
            "the sevice status of 4G user."
        ::= { qtech4GEntry 13 }

    qtech4GRoamingStatus OBJECT-TYPE
        SYNTAX INTEGER
            {
                noRoaming(0),
                roaming(1)
            }
        MAX-ACCESS read-only
        STATUS current
        DESCRIPTION
            "the roaming status of 4G  user."
        ::= { qtech4GEntry 14 }

    qtech4GDomain OBJECT-TYPE
        SYNTAX INTEGER
            {
                noService(0),
                onlyCS(1),
                onlyPS(2),
                pSCS(3),
                ePS(4)
            }
        MAX-ACCESS read-only
        STATUS current
        DESCRIPTION
            "the Domain status of 4G user ."
        ::= { qtech4GEntry 15 }

    qtech4GSIMStatus OBJECT-TYPE
        SYNTAX INTEGER
            {
                invalidUsimCard(0),
                validUsimCard(1),
                noUsimCard(255)
            }
        MAX-ACCESS read-only
        STATUS current
        DESCRIPTION
            "the SIM card status of 4G user."
        ::= { qtech4GEntry 16 }

    qtech4GCellID OBJECT-TYPE
        SYNTAX Integer32 (0..100)
        MAX-ACCESS read-only
        STATUS current
        DESCRIPTION
            "The access Cell id  of 4G User."
        ::= { qtech4GEntry 17 }

      qtech4GLAC OBJECT-TYPE
        SYNTAX Integer32 (0..100)
        MAX-ACCESS read-only
        STATUS current
        DESCRIPTION
            "The Location Area Code  of 4G User."
        ::= { qtech4GEntry 18 }

    qtech4GIMSI OBJECT-TYPE
        SYNTAX DisplayString
        MAX-ACCESS read-only
        STATUS current
        DESCRIPTION
            "The IMSI  of 4G User."
        ::= { qtech4GEntry 19 }

    qtech4GPhoneNumber OBJECT-TYPE
        SYNTAX DisplayString
        MAX-ACCESS read-only
        STATUS current
        DESCRIPTION
            "The Phone Number of 4G User."
        ::= { qtech4GEntry 20 }

    qtech4GifIndex OBJECT-TYPE
        SYNTAX  INTEGER
        MAX-ACCESS  read-only
        STATUS  current
        DESCRIPTION
            "The Index of 4G Interface."
        ::= { qtech4GEntry 21 }

    qtech4GInOctets OBJECT-TYPE
        SYNTAX Counter64
        MAX-ACCESS read-only
        STATUS current
        DESCRIPTION
            "The total number of octets received by this 4G user."
        ::= { qtech4GEntry 22 }

    qtech4GOutOctets OBJECT-TYPE
        SYNTAX Counter64
        MAX-ACCESS read-only
        STATUS current
        DESCRIPTION
            "The total number of octets sent by this 4G user."
        ::= { qtech4GEntry 23 }

    qtech4GInSpeed OBJECT-TYPE
        SYNTAX Counter64
        MAX-ACCESS read-only
        STATUS current
        DESCRIPTION
            "The Speed(bps) of packets received by this 4G user."
        ::= { qtech4GEntry 24 }

    qtech4GOutSpeed OBJECT-TYPE
        SYNTAX Counter64
        MAX-ACCESS read-only
        STATUS current
        DESCRIPTION
            "The Speed(bps) of packets snet by this 4G user."
        ::= { qtech4GEntry 25 }

    qtech4GBSLONG OBJECT-TYPE
        SYNTAX Integer32
        MAX-ACCESS read-only
        STATUS current
        DESCRIPTION
            "The longitude of 4G User."
        ::= { qtech4GEntry 26 }

    qtech4GBSLAT OBJECT-TYPE
        SYNTAX Integer32
        MAX-ACCESS read-only
        STATUS current
        DESCRIPTION
            "The latitude of 4G User."
        ::= { qtech4GEntry 27 }

    qtech4GRouterType OBJECT-TYPE
        SYNTAX DisplayString
        MAX-ACCESS read-only
        STATUS current
        DESCRIPTION
            "Equipment tpye of 4G router."
        ::= { qtech4GEntry 28 }

    qtech4GRouterSN OBJECT-TYPE
        SYNTAX DisplayString
        MAX-ACCESS read-only
        STATUS current
        DESCRIPTION
            "The serial number of 4G router."
        ::= { qtech4GEntry 29 }

    qtech4GRouterSlotNumber OBJECT-TYPE
        SYNTAX DisplayString
        MAX-ACCESS read-only
        STATUS current
        DESCRIPTION
            "The number of the activity slot in 4G router."
        ::= { qtech4GEntry 30 }

    qtech4GLineCardType OBJECT-TYPE
        SYNTAX DisplayString
        MAX-ACCESS read-only
        STATUS current
        DESCRIPTION
            "The tpye of 4G router line card."
        ::= { qtech4GEntry 31 }

    qtech4GDialdMode OBJECT-TYPE
        SYNTAX INTEGER
            {
                auto-dial(0),
                dial-on-demand(1)
            }
        MAX-ACCESS read-only
        STATUS current
        DESCRIPTION
            "The dial mode of 4G user "
        ::= { qtech4GEntry 32 }

    qtech4GDialOnDemandIfIndex OBJECT-TYPE
        SYNTAX  INTEGER
        MAX-ACCESS  read-only
        STATUS  current
        DESCRIPTION
            "The Index of trigger dial-up interface."
        ::= { qtech4GEntry 33 }

    qtech4GTrafficPreventMode OBJECT-TYPE
        SYNTAX INTEGER
            {
                disable(0),
                enable(1)
            }
        MAX-ACCESS read-only
        STATUS current
        DESCRIPTION
            "The status of the traffic prevent function appliled currently "
        ::= { qtech4GEntry 34 }

    qtech4GTrafficPreventIfIndex OBJECT-TYPE
        SYNTAX  INTEGER
        MAX-ACCESS  read-only
        STATUS  current
        DESCRIPTION
            "The Index of traffic-prevent interface."
        ::= { qtech4GEntry 35 }

    qtech4GTrafficPreventListID OBJECT-TYPE
        SYNTAX  INTEGER
        MAX-ACCESS  read-only
        STATUS  current
        DESCRIPTION
            "The Index of traffic-prevent Acl list id."
        ::= { qtech4GEntry 36 }

    qtech4GTrafficPreventListName OBJECT-TYPE
        SYNTAX  DisplayString
        MAX-ACCESS  read-only
        STATUS  current
        DESCRIPTION
            "The Index of traffic-prevent Acl list name."
        ::= { qtech4GEntry 37 }


--Begin the node of qtech4GTrap.

    qtech4GTrap OBJECT IDENTIFIER ::= { qtech4GMonitor 2 }

-- ===============================================
-- Begin the qtech4GTrapObject.
-- ===============================================
    qtech4GNotifications OBJECT IDENTIFIER ::= { qtech4GTrap 1 }

    qtech4GUpLine NOTIFICATION-TYPE
        OBJECTS { qtech4GRouterSlotNumber,
                  qtech4GIMSI,
                  qtech4GUsername,
                  qtech4GRouterSN,
                  qtech4GPhoneNumber,
                  qtech4GDialdMode,
                  qtech4GDialOnDemandIfIndex,
                  qtech4GTrafficPreventMode,
                  qtech4GTrafficPreventIfIndex,
                  qtech4GIPAddr,
                  qtech4GTrafficPreventListID,
                  qtech4GTrafficPreventListName
                }
        STATUS current
        DESCRIPTION
            "This notification is generated when 4G user up line."
        ::= { qtech4GNotifications 1 }

    qtech4GDownLine NOTIFICATION-TYPE
        OBJECTS { qtech4GRouterSlotNumber,
                  qtech4GIMSI,
                  qtech4GUsername,
                  qtech4GRouterSN,
                  qtech4GPhoneNumber,
                  qtech4GDialdMode,
                  qtech4GDialOnDemandIfIndex,
                  qtech4GTrafficPreventMode,
                  qtech4GTrafficPreventIfIndex,
                  qtech4GIPAddr,
                  qtech4GTrafficPreventListID,
                  qtech4GTrafficPreventListName
                }
        STATUS current
        DESCRIPTION
            "This notification is generated when 4G user down line."
        ::= { qtech4GNotifications 2 }

    qtech4GSignalThreshold NOTIFICATION-TYPE
        OBJECTS {   qtech4GRouterSlotNumber,
                    qtech4GIMSI,
                    qtech4GRSRP,
                    qtech4GSignalStrengthPercent
                }
        STATUS current
        DESCRIPTION
            "This notification is generated when 4G signal is lower
            than the specific Threshold value."
        ::= { qtech4GNotifications 3 }

    qtech4GTrafficInformation NOTIFICATION-TYPE
        OBJECTS {   qtech4GRouterSlotNumber,
                    qtech4GIMSI,
                    qtech4GInOctets,
                    qtech4GOutOctets
                }
        STATUS current
        DESCRIPTION
            "This notification is used for reporting the traffic information of 4G user regularly. "
        ::= { qtech4GNotifications 4 }

    qtech4GBackupMaster NOTIFICATION-TYPE
        OBJECTS { qtech4GRouterSlotNumber,
                  qtech4GIMSI,
                  qtech4GUsername,
                  qtech4GRouterSN,
                  qtech4GPhoneNumber,
                  qtech4GDialdMode,
                  qtech4GDialOnDemandIfIndex,
                  qtech4GTrafficPreventMode,
                  qtech4GTrafficPreventIfIndex,
                  qtech4GIPAddr,
                  qtech4GTrafficPreventListID,
                  qtech4GTrafficPreventListName
                }
        STATUS current
        DESCRIPTION
            "This notification is generated when 4G is switching to master line."
        ::= { qtech4GNotifications 5 }

    qtech4GBackupSlave NOTIFICATION-TYPE
        OBJECTS { qtech4GRouterSlotNumber,
                  qtech4GIMSI,
                  qtech4GUsername,
                  qtech4GRouterSN,
                  qtech4GPhoneNumber,
                  qtech4GDialdMode,
                  qtech4GDialOnDemandIfIndex,
                  qtech4GTrafficPreventMode,
                  qtech4GTrafficPreventIfIndex,
                  qtech4GIPAddr,
                  qtech4GTrafficPreventListID,
                  qtech4GTrafficPreventListName
                }
        STATUS current
        DESCRIPTION
            "This notification is generated when 4G is switching to slave line."
        ::= { qtech4GNotifications 6 }

END
