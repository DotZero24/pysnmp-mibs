-- *****************************************************************
-- QTECH-WEB-PORTAL-MIB.mib:  Qtech Web Portal MIB file
--
-- Feb 2010, Panshiyong
--
-- Copyright (c) 2010 by Qtech Networks Co.,Ltd.
-- All rights reserved.
--
-- *****************************************************************

QTECH-WEB-PORTAL-MIB DEFINITIONS ::= BEGIN

IMPORTS
    MODULE-IDENTITY,
    OBJECT-TYPE
            FROM SNMPv2-SMI
    DisplayString,
    RowStatus
            FROM SNMPv2-TC
    MODULE-COMPLIANCE,
    OBJECT-GROUP,
    NOTIFICATION-GROUP
            FROM SNMPv2-CONF
    qtechMgmt
            FROM QTECH-SMI;

qtechWebPortalMIB MODULE-IDENTITY
    LAST-UPDATED "201002020000Z"
    ORGANIZATION "Qtech Networks Co.,Ltd."
    CONTACT-INFO
            "
            Tel: 4008-111-000

            E-mail: service@qtech.com.cn"
    DESCRIPTION
            "This module defines web portal mibs."
    REVISION      "201002020000Z"
    DESCRIPTION
            "Initial version of this MIB module."
    ::= { qtechMgmt 69 }


--***************** define the web portal root nodes ******************
qtechWebPortalMIBObjects       OBJECT IDENTIFIER ::= { qtechWebPortalMIB 1 }
qtechWebPortalGlobalMIBObjects OBJECT IDENTIFIER ::= { qtechWebPortalMIBObjects 1 }
qtechWebPortalLocalMIBObjects  OBJECT IDENTIFIER ::= { qtechWebPortalMIBObjects 2 }

--********************************************************************
--                                                                  **
--                  Global nodes                                    **
--                                                                  **
--********************************************************************

-- global web auth type
qtechWebPortalGlbWebAuthType OBJECT-TYPE
    SYNTAX INTEGER {
                 internal(0),
                 customized(1),
                 external(2)
           }
    MAX-ACCESS  read-write
    STATUS  current
    DESCRIPTION
            "The type of global web authentication:
             0 - internal,
             1 - customized,
             2 - external."
    DEFVAL { internal }
    ::= { qtechWebPortalGlobalMIBObjects 1 }

-- global method list
qtechWebPortalGlbMethodList OBJECT-TYPE
    SYNTAX DisplayString (SIZE (1..63))
    MAX-ACCESS  read-write
    STATUS  current
    DESCRIPTION
            "A human readable string representing the global authentication method-list."
    ::= { qtechWebPortalGlobalMIBObjects 2 }

-- global customized page file name
qtechWebPortalGlbCustomizedPageName OBJECT-TYPE
    SYNTAX DisplayString (SIZE (1..130))
    MAX-ACCESS  read-write
    STATUS  current
    DESCRIPTION
            "A human readable string representiong the global customized page file name."
    ::= { qtechWebPortalGlobalMIBObjects 3 }

-- global external web portal URL
qtechWebPortalGlbExternalWebPortalURL OBJECT-TYPE
    SYNTAX DisplayString (SIZE (1..130))
    MAX-ACCESS  read-write
    STATUS  current
    DESCRIPTION
            "A human readable string representiong the global external
             web portal page URL."
    ::= { qtechWebPortalGlobalMIBObjects 4 }

-- global customized logo name
qtechWebPortalGlbCustomizedLogoName OBJECT-TYPE
    SYNTAX  DisplayString(SIZE (1..130))
    MAX-ACCESS  read-write
    STATUS  current
    DESCRIPTION
            "A human readable string representiong the global logo picture
             name of the internal web portal."
    ::= { qtechWebPortalGlobalMIBObjects 5 }

-- global echo manufacturer logo
qtechWebPortalGlbEchoManufacturerLogo OBJECT-TYPE
    SYNTAX  INTEGER {
									 disable(0),
                   enable(1)
               }
    MAX-ACCESS  read-write
    STATUS  current
    DESCRIPTION
            "The global flag of display manufacturer logo or not
             0 - disable,
             1 - enable."
    DEFVAL { enable }
    ::= { qtechWebPortalGlobalMIBObjects 6 }

-- global welcome message
qtechWebPortalGlbWelcomeMsg OBJECT-TYPE
    SYNTAX OCTET STRING(SIZE (1..2047))
    MAX-ACCESS  read-write
    STATUS  current
    DESCRIPTION
            "A human readable string representing the global welcome message."
    ::= { qtechWebPortalGlobalMIBObjects 7 }

-- global web-page title
qtechWebPortalGlbWebPageTitle OBJECT-TYPE
    SYNTAX DisplayString(SIZE (1..130))
    MAX-ACCESS  read-write
    STATUS  current
    DESCRIPTION
            "A human readable string representing the global web-page title."
    ::= { qtechWebPortalGlobalMIBObjects 8 }


--********************************************************************
--                                                                  **
--                  Local nodes                                     **
--                                                                  **
--********************************************************************

qtechWebPortalAuthTable OBJECT-TYPE
    SYNTAX SEQUENCE OF QtechWebPortalAuthEntry
    MAX-ACCESS not-accessible
    STATUS current
    DESCRIPTION
            "A table of web portal entries."
    ::= { qtechWebPortalLocalMIBObjects 1 }

qtechWebPortalAuthEntry OBJECT-TYPE
    SYNTAX QtechWebPortalAuthEntry
    MAX-ACCESS not-accessible
    STATUS current
    DESCRIPTION
            "Define all attributes of the web portal."
    INDEX { qtechWebPortalNetMode,
            qtechWebPortalNetID }
    ::= { qtechWebPortalAuthTable 1 }

QtechWebPortalAuthEntry ::=
    SEQUENCE {
        qtechWebPortalNetMode               INTEGER,
        qtechWebPortalNetID                 INTEGER,
        qtechWebPortalWebAuthType           INTEGER,
        qtechWebPortalUseGlbConfigFlag      INTEGER,
		    qtechWebPortalMetholdList           DisplayString,
        qtechWebPortalCustomizedPageName    DisplayString,
        qtechWebPortalExtWebPortalURL       DisplayString,
        qtechWebPortalCustomizedLogoName    DisplayString,
        qtechWebPortalEchoManufacturerLogo  INTEGER,
        qtechWebPortalWelcomeMsg            OCTET STRING,
        qtechWebPortalWebPageTitle          DisplayString,
        qtechWebPortalEntryStatus           RowStatus
    }

qtechWebPortalNetMode OBJECT-TYPE
        SYNTAX INTEGER {
                    wlan(1),
                    ethernet(2),
                    vlan(3)
               }
        MAX-ACCESS read-only
        STATUS current
        DESCRIPTION
            "The net mode of web portal, the value is as fallow:
             1 - wlan,
             2 - ethernet,
             3 - vlan."
        ::= { qtechWebPortalAuthEntry  1 }

qtechWebPortalNetID OBJECT-TYPE
        SYNTAX INTEGER(1..4095)
        MAX-ACCESS read-only
        STATUS current
        DESCRIPTION
            "The net NO. of web portal."
        ::= { qtechWebPortalAuthEntry  2 }

qtechWebPortalWebAuthType OBJECT-TYPE
        SYNTAX INTEGER {
                   internal(0),
                   customized(1),
                   external(2)
               }
        MAX-ACCESS read-create
        STATUS current
        DESCRIPTION
            "The type of web authentication:
             0 - internal,
             1 - customized,
             2 - external."
        DEFVAL { internal }
        ::= { qtechWebPortalAuthEntry  3 }

qtechWebPortalUseGlbConfigFlag OBJECT-TYPE
        SYNTAX INTEGER {
                   disable(0),
                   enable(1)
               }
        MAX-ACCESS read-create
        STATUS current
        DESCRIPTION
            "The flag of use global web authentication configure info or not:
             0 - disable,
             1 - enable."
        DEFVAL { enable }
        ::= { qtechWebPortalAuthEntry  4 }

qtechWebPortalMetholdList OBJECT-TYPE
        SYNTAX DisplayString(SIZE (1..64))
        MAX-ACCESS read-create
        STATUS current
        DESCRIPTION
            "A human readable string representing the AAA authentication methold list
             of web portal."
        ::= { qtechWebPortalAuthEntry  5 }

qtechWebPortalCustomizedPageName OBJECT-TYPE
        SYNTAX DisplayString(SIZE (1..130))
        MAX-ACCESS read-create
        STATUS current
        DESCRIPTION
            "A human readable string representiong the name of customized
             page file name."
        ::= { qtechWebPortalAuthEntry  6 }

qtechWebPortalExtWebPortalURL OBJECT-TYPE
        SYNTAX DisplayString(SIZE (1..130))
        MAX-ACCESS read-create
        STATUS current
        DESCRIPTION
            "A human readable string representiong the URL of
             the external web portal page."
        ::= { qtechWebPortalAuthEntry  7 }

qtechWebPortalCustomizedLogoName OBJECT-TYPE
        SYNTAX DisplayString(SIZE (1..130))
        MAX-ACCESS read-create
        STATUS current
        DESCRIPTION
            "A human readable string representing the customized logo picture name
             of the internal web portal."
        ::= { qtechWebPortalAuthEntry  8 }

qtechWebPortalEchoManufacturerLogo OBJECT-TYPE
        SYNTAX INTEGER {
                   disable(0),
                   enable(1)
               }
        MAX-ACCESS read-create
        STATUS current
        DESCRIPTION
            "The flag of display the manufacturer logo or not:
             0 - disable,
             1 - enable."
        DEFVAL { enable }
        ::= { qtechWebPortalAuthEntry  9 }

qtechWebPortalWelcomeMsg OBJECT-TYPE
        SYNTAX OCTET STRING(SIZE (1..2047))
        MAX-ACCESS read-create
        STATUS current
        DESCRIPTION
            "A human readable string representing the welcome message of
             the internal web portal."
        ::= { qtechWebPortalAuthEntry  10 }

qtechWebPortalWebPageTitle OBJECT-TYPE
        SYNTAX DisplayString(SIZE (1..130))
        MAX-ACCESS read-create
        STATUS current
        DESCRIPTION
            "A human readable string representing the web-page title of
             the internel web portal."
        ::= { qtechWebPortalAuthEntry  11 }

qtechWebPortalEntryStatus OBJECT-TYPE
        SYNTAX RowStatus
        MAX-ACCESS read-create
        STATUS current
        DESCRIPTION
            "The status of this conceptual row.

            To create a row in this table, a manager must
            set this object to either createAndGo(4) or
            createAndWait(5).

            Until instances of all corresponding columns are
            appropriately configured, the value of the webPortalEntryStatus
            corresponding instance of the column is 'notReady'.

            In particular, a newly created row cannot be made
            active until the corresponding instance of
            webPortalEntryStatus has been set.
            "
        ::= { qtechWebPortalAuthEntry  12 }


--*************************** conformance information *****************************************
qtechWebPortalMIBConformance OBJECT IDENTIFIER ::= { qtechWebPortalMIB 2 }
qtechWebPortalMIBCompliances OBJECT IDENTIFIER ::= { qtechWebPortalMIBConformance 1 }
qtechWebPortalMIBGroups      OBJECT IDENTIFIER ::= { qtechWebPortalMIBConformance 2 }

-- compliance statements

qtechWebPortalMIBCompliance MODULE-COMPLIANCE
        STATUS  current
        DESCRIPTION
            "The compliance statement for entities which implement
             the Qtech Web Portal MIB
            "
        MODULE  -- this module
            MANDATORY-GROUPS { qtechWebPortalMIBGroup }
        ::= { qtechWebPortalMIBCompliances 1 }


-- units of conformance

qtechWebPortalMIBGroup OBJECT-GROUP
        OBJECTS {
            qtechWebPortalGlbWebAuthType,
            qtechWebPortalGlbMethodList,
            qtechWebPortalGlbCustomizedPageName,
            qtechWebPortalGlbExternalWebPortalURL,
            qtechWebPortalGlbCustomizedLogoName,
            qtechWebPortalGlbEchoManufacturerLogo,
            qtechWebPortalGlbWelcomeMsg,
            qtechWebPortalGlbWebPageTitle,
            qtechWebPortalNetMode,
            qtechWebPortalNetID,
            qtechWebPortalWebAuthType,
            qtechWebPortalUseGlbConfigFlag,
		        qtechWebPortalMetholdList,
            qtechWebPortalCustomizedPageName,
            qtechWebPortalExtWebPortalURL,
            qtechWebPortalCustomizedLogoName,
            qtechWebPortalEchoManufacturerLogo,
            qtechWebPortalWelcomeMsg,
            qtechWebPortalWebPageTitle,
            qtechWebPortalEntryStatus
        }
        STATUS  current
        DESCRIPTION
                "A collection of objects providing web portal (echo) ability to a
                 Qtech agent.
                "
        ::= { qtechWebPortalMIBGroups 1 }

END
