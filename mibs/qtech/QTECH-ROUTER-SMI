-- *****************************************************************
-- QTECH-ROUTER-SMI.mib: Qtech Router SMI File
--
-- Jan. 2005, Wuzg
--
-- Copyright (c) 2005 by Qtech Networks Co.,Ltd.
-- All rights reserved.
--
-- *****************************************************************
--

QTECH-ROUTER-SMI DEFINITIONS ::= BEGIN

IMPORTS
        MODULE-IDENTITY,
        OBJECT-IDENTITY
                FROM SNMPv2-SMI
        products
                FROM QTECH-SMI;

router          OBJECT IDENTIFIER ::= { products 2 }

routerMib MODULE-IDENTITY
        LAST-UPDATED "200501060000Z"
        ORGANIZATION "Qtech Networks Co.,Ltd."
        CONTACT-INFO
                "
                Tel: 4008-111-000

                E-mail: service@qtech.com.cn"
        DESCRIPTION
                "The Structure of Management Information for the
                 Qtech enterprise."
        REVISION      "200501060000Z"
        DESCRIPTION
                "Initial version of this MIB module."
        ::= { router 1 }

qtechRouterProducts OBJECT-IDENTITY
        STATUS  current
        DESCRIPTION
                "qtechRouterProducts is the root OBJECT IDENTIFIER from
                which sysObjectID values are assigned for router.  Actual
                values are defined in QTECH-PRODUCTS-MIB."
        ::= { routerMib 1 }

END
