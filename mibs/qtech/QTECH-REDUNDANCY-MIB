-- *****************************************************************
-- QTECH-REDUNDANCY-MIB.mib:  Qtech redundancy and pluggable MIB file
--
-- Sep.2003,  guody
--
-- Copyright (c) 2002 by Qtech Networks Co.,Ltd.
-- All rights reserved.
--
-- *****************************************************************
--

QTECH-REDUNDANCY-MIB DEFINITIONS ::= BEGIN

IMPORTS
        MODULE-IDENTITY,
        OBJECT-TYPE,
        Integer32
                FROM SNMPv2-SMI
        DisplayString
                FROM SNMPv2-TC
        MODULE-COMPLIANCE,
        OBJECT-GROUP
                FROM SNMPv2-CONF
        qtechMgmt
                FROM QTECH-SMI;

qtechRedundancyMIB MODULE-IDENTITY
        LAST-UPDATED "200309100000Z"
        ORGANIZATION "Qtech Networks Co.,Ltd."
        CONTACT-INFO
                "
                Tel: 4008-111-000

                E-mail: service@qtech.com.cn"
        DESCRIPTION
                "This module defines qtech redundancy mibs."
        REVISION      "200309200000Z"
        DESCRIPTION
                "Initial version of this MIB module."
        ::= { qtechMgmt 34}

qtechRedundancyMIBObjects OBJECT IDENTIFIER ::= { qtechRedundancyMIB 1 }

qtechRedundancyForceSwitchover OBJECT-TYPE
        SYNTAX INTEGER
        MAX-ACCESS read-write
        STATUS current
        DESCRIPTION
            "Setting any values except for 0 resets the current supervisor engine and enables the redundancy standby
             supervisor engine to start working. The object value is always be 0. "
        ::= { qtechRedundancyMIBObjects 1 }

qtechMainCPU OBJECT-TYPE
   	SYNTAX  INTEGER {
                increasing(0), -- Supervisor engine in slot with low number is prior to be in the master state.
                decreasing(1)  -- Supervisor engine in slot with high number is prior to be in the master state.
             }
        MAX-ACCESS read-only
        STATUS current
        DESCRIPTION
          "The object determines which supervisor engine is prior to be in the master state when redundancy event occurs.
           In fact, it might be inconsistent with the expectation. For example, the supervisor engine prior to be in the
           master state fails to start."
        ::= { qtechRedundancyMIBObjects 2 }


qtechPluggableMIBObjects OBJECT IDENTIFIER ::= { qtechRedundancyMIB 2 }

qtechPluggableModuleInfoTable OBJECT-TYPE
        SYNTAX SEQUENCE OF QtechPluggableModuleInfoEntry
        MAX-ACCESS not-accessible
        STATUS current
        DESCRIPTION
            "Table of entrance to the module settings."
        ::= { qtechPluggableMIBObjects  1 }

qtechPluggableModuleInfoEntry OBJECT-TYPE
        SYNTAX QtechPluggableModuleInfoEntry
        MAX-ACCESS not-accessible
        STATUS current
        DESCRIPTION
            "Entrance to the module settings."
        INDEX { qtechPluggableModuleInfoDeviceIndex, qtechPluggableModuleInfoSlotIndex }
        ::= { qtechPluggableModuleInfoTable 1 }

QtechPluggableModuleInfoEntry ::=
        SEQUENCE {
             qtechPluggableModuleInfoDeviceIndex Integer32,
             qtechPluggableModuleInfoSlotIndex Integer32,
             qtechPluggableModuleStatus INTEGER,
             qtechPluggableModuleConfigType INTEGER,
             qtechPluggableModuleConfigSwVer DisplayString,
             qtechPluggableModuleOnlineSwVer DisplayString,
             qtechPluggableModuleConfigInfoDescr DisplayString,
             qtechPluggableModuleOnlineInfoDescr DisplayString,
             qtechPluggableModuleConfigPortsNum Integer32,
             qtechPluggableModuleOnlinePortsNum Integer32,
             qtechPluggableModuleAction  INTEGER
        }

qtechPluggableModuleInfoDeviceIndex OBJECT-TYPE
        SYNTAX Integer32
        MAX-ACCESS read-only
        STATUS current
        DESCRIPTION
            "The index of device which the module is in."
        ::= { qtechPluggableModuleInfoEntry 1 }

qtechPluggableModuleInfoSlotIndex OBJECT-TYPE
        SYNTAX Integer32
        MAX-ACCESS read-only
        STATUS current
        DESCRIPTION
            "The index of slot which the module is in."
        ::= { qtechPluggableModuleInfoEntry 2 }

qtechPluggableModuleStatus  OBJECT-TYPE
        SYNTAX  INTEGER {
                none(0),          --Module is not existed. Module type has not been pre-set, either.
                ok(1),            --Module works normally.
                installed(2),     --Pre-set the module
                conflict(3),      --Conflict between the pre-set module and actual plugged module type.
                removed(4),       --Remove the module
                uninstalled(5),   --Unistall the module, but the module is still plugged.
                verIncompatible(6), --Version incompatibility
                cannot-qtechup(7), --Can not start the module
                resetting(8),       --Resetting the module
                master(9),          --Supervisor engine is in the master state.
                backup(10)          --Supervisor engine is in the backup state.

             }
        MAX-ACCESS read-only
        STATUS current
        DESCRIPTION
            "Module state."
        ::= { qtechPluggableModuleInfoEntry 3 }



qtechPluggableModuleConfigType OBJECT-TYPE
        SYNTAX INTEGER{
                none(0),     --The module has not been plugged.
                m6800-24T-4SFP-4GT(1),
                m6800-32T-4SFP-GT(2),
                m6800-32FMT(3),
                m6800-12GB(4),
                m6800-24SFP(5),
                m6800-12SFP-GT(6),
                m6800-1XENPAK(7),
                m6800-2XENPAK(8),
                m6800-MSC(9),
                m6800-CM(10),
                m6800-24GT-8SFP(11)
             }
        MAX-ACCESS read-write
        STATUS current
        DESCRIPTION
            "Use this object to add the module configuration. Without setting any type(none), the system automatically
             sets all parameters to the default value according to module type to be back. When the object are reading,
             the system is back to the set type of none."
	::= { qtechPluggableModuleInfoEntry 4 }

qtechPluggableModuleConfigSwVer OBJECT-TYPE
        SYNTAX DisplayString(SIZE (1..32))
        MAX-ACCESS read-only
        STATUS current
        DESCRIPTION
          "Version of configured module."
        ::= { qtechPluggableModuleInfoEntry 5 }


qtechPluggableModuleOnlineSwVer OBJECT-TYPE
        SYNTAX DisplayString(SIZE (1..32))
        MAX-ACCESS read-only
        STATUS current
        DESCRIPTION
          "The actual version of the plugged module."
        ::= { qtechPluggableModuleInfoEntry 6 }


qtechPluggableModuleConfigInfoDescr OBJECT-TYPE
        SYNTAX DisplayString(SIZE (1..32))
        MAX-ACCESS read-only
        STATUS current
        DESCRIPTION
            "Module name configuration. Different models have different module names.
             It is null when there is no module configuration."
        ::= { qtechPluggableModuleInfoEntry 7 }

qtechPluggableModuleOnlineInfoDescr  OBJECT-TYPE
        SYNTAX DisplayString(SIZE (1..32))
        MAX-ACCESS read-only
        STATUS current
        DESCRIPTION
            "Module name of actual plugged module.Different models have different module names.
             It is null when there is no module configuration."
        ::= { qtechPluggableModuleInfoEntry 8 }

qtechPluggableModuleConfigPortsNum OBJECT-TYPE
        SYNTAX Integer32
        MAX-ACCESS read-only
        STATUS current
        DESCRIPTION
            "Configure the module port numbe."
        ::= { qtechPluggableModuleInfoEntry 9 }

qtechPluggableModuleOnlinePortsNum OBJECT-TYPE
        SYNTAX Integer32
        MAX-ACCESS read-only
        STATUS current
        DESCRIPTION
            "The actual port number of the plugged module."
        ::= { qtechPluggableModuleInfoEntry 10 }

qtechPluggableModuleAction  OBJECT-TYPE
        SYNTAX INTEGER{
                none(0),         --Read the information
                reset(1),        --Reset the module
                clearAllConf(2), --Restore all the module configurations to the default
                uninstall(3)     --Unistall this module
              }
        MAX-ACCESS read-write
        STATUS current
        DESCRIPTION
            "This object contains the operations to the module:
             Module reset(1)
             Restore all settings to the default value(2)
             Module remove(3)
             When reading the object value, it always be back to zero."
        ::= { qtechPluggableModuleInfoEntry 11 }


qtechRedundancyMIBConformance OBJECT IDENTIFIER ::= { qtechRedundancyMIB 3 }
qtechRedundancyMIBCompliances OBJECT IDENTIFIER ::= { qtechRedundancyMIBConformance 1 }
qtechRedundancyMIBGroups      OBJECT IDENTIFIER ::= { qtechRedundancyMIBConformance 2 }


-- compliance statements

qtechRedundancyMIBCompliance MODULE-COMPLIANCE
        STATUS  current
        DESCRIPTION
                "The compliance statement for entities which implement
                the Qtech System MIB"
        MODULE  -- this module
                MANDATORY-GROUPS { qtechRedundancyMIBGroup
                 }
        ::= { qtechRedundancyMIBCompliances 1 }

-- units of conformance

qtechRedundancyMIBGroup OBJECT-GROUP
        OBJECTS {
               qtechRedundancyForceSwitchover,
               qtechMainCPU,
               qtechPluggableModuleInfoDeviceIndex,
               qtechPluggableModuleInfoSlotIndex,
               qtechPluggableModuleStatus,
               qtechPluggableModuleConfigType,
               qtechPluggableModuleConfigSwVer,
               qtechPluggableModuleOnlineSwVer,
               qtechPluggableModuleConfigInfoDescr,
               qtechPluggableModuleOnlineInfoDescr,
               qtechPluggableModuleConfigPortsNum,
               qtechPluggableModuleOnlinePortsNum,
               qtechPluggableModuleAction

        }
        STATUS  current
        DESCRIPTION
                "A collection of objects providing system information and
                opertion to a Qtech agent."
        ::= { qtechRedundancyMIBGroups  1 }

END
