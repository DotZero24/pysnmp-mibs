--Delta-MIB { iso(1) org(3) dod(6) internet(1) private(4) enterprises(1) delta(2254) ups(2) sensor(500) }


DeltaSensor-MIB DEFINITIONS ::= BEGIN


IMPORTS
	enterprises, IpAddress
		FROM RFC1155-SMI
	DisplayString
		FROM RFC1213-MIB
	OBJECT-TYPE
		FROM RFC-1212
	TRAP-TYPE
		FROM RFC-1215;


delta				OBJECT IDENTIFIER ::=  { enterprises 2254 }

ups					OBJECT IDENTIFIER ::=  { delta 2 }

sensor				OBJECT IDENTIFIER ::=  { ups 500 }

dsensorMonitor		OBJECT IDENTIFIER ::=  { sensor 1 }
dsensorConfigure	OBJECT IDENTIFIER ::=  { sensor 2 }
dsensorTraps		OBJECT IDENTIFIER ::=  { sensor 20 }


--
-- dsensor Monitoring group
--

   dsensorTemperature OBJECT-TYPE
       SYNTAX     INTEGER
       UNITS      "degrees Centigrade"
       ACCESS     read-only
       STATUS     mandatory
       DESCRIPTION
               "The ambient environmental temperature."
       ::= { dsensorMonitor 1 }

   dsensorHumidity OBJECT-TYPE
       SYNTAX     INTEGER
       UNITS      "percentage"
       ACCESS     read-only
       STATUS     mandatory
       DESCRIPTION
               "The environmental humidity."
       ::= { dsensorMonitor 2 }

   dsensorWarnOverTemperature OBJECT-TYPE
       SYNTAX     INTEGER{
                  on(1),
                  off(2)
       }
       ACCESS     read-only
       STATUS     mandatory
       DESCRIPTION
               "Does the environment over warning temperature?"
       ::= { dsensorMonitor 3 }

   dsensorWarnOverHumidity OBJECT-TYPE
       SYNTAX     INTEGER{
                  on(1),
                  off(2)
       }
       ACCESS     read-only
       STATUS     mandatory
       DESCRIPTION
               "Does the environment over warning humidity?"
       ::= { dsensorMonitor 4 }

   dsensorAlarmOverTemperature OBJECT-TYPE
       SYNTAX     INTEGER{
                  on(1),
                  off(2)
       }
       ACCESS     read-only
       STATUS     mandatory
       DESCRIPTION
               "Does the environment over alarm temperature?"
       ::= { dsensorMonitor 5 }

   dsensorAlarmOverHumidity OBJECT-TYPE
       SYNTAX     INTEGER{
                  on(1),
                  off(2)
       }
       ACCESS     read-only
       STATUS     mandatory
       DESCRIPTION
               "Does the environment over alarm humidity?"
       ::= { dsensorMonitor 6 }

   dsensorAlarmRelay1 OBJECT-TYPE
       SYNTAX     INTEGER{
                  on(1),
                  off(2)
       }
       ACCESS     read-only
       STATUS     mandatory
       DESCRIPTION
               ""
       ::= { dsensorMonitor 7 }

   dsensorAlarmRelay2 OBJECT-TYPE
       SYNTAX     INTEGER{
                  on(1),
                  off(2)
       }
       ACCESS     read-only
       STATUS     mandatory
       DESCRIPTION
               ""
       ::= { dsensorMonitor 8 }

    dsensorAlarmRelay3 OBJECT-TYPE
       SYNTAX     INTEGER{
                  on(1),
                  off(2)
       }
       ACCESS     read-only
       STATUS     mandatory
       DESCRIPTION
               ""
       ::= { dsensorMonitor 9 }

   dsensorAlarmRelay4 OBJECT-TYPE
       SYNTAX     INTEGER{
                  on(1),
                  off(2)
       }
       ACCESS     read-only
       STATUS     mandatory
       DESCRIPTION
               ""
       ::= { dsensorMonitor 10 }

--
-- dsensor Configure group
--

   dsensorSetTemperatureWarnLimit OBJECT-TYPE
       SYNTAX     INTEGER
       UNITS      "Degrees Centigrade"
       ACCESS     read-write
       STATUS     mandatory
       DESCRIPTION
               "Alarm dsensorOverWarnTemperature on when the environmental
		temperature over the value."
       ::= { dsensorConfigure 1 }

   dsensorSetHumidityWarnLimit OBJECT-TYPE
       SYNTAX     INTEGER
       UNITS      "percentage"
       ACCESS     read-write
       STATUS     mandatory
       DESCRIPTION
               "Alarm dsensorOverWarnHumidity on when the environmental
		humidity over the value."
       ::= { dsensorConfigure 2 }

   dsensorSetTemperatureAlarmLimit OBJECT-TYPE
       SYNTAX     INTEGER
       UNITS      "degrees Centigrade"
       ACCESS     read-write
       STATUS     mandatory
       DESCRIPTION
               "Alarm dsensorOverAlarmTemperature on when the environmental
		temperature over the value."
       ::= { dsensorConfigure 3 }

   dsensorSetHumidityAlarmLimit OBJECT-TYPE
       SYNTAX     INTEGER
       UNITS      "percentage"
       ACCESS     read-write
       STATUS     mandatory
       DESCRIPTION
               "Alarm dsensorOverAlarmHumidity on when the environmental
		humidity over the value."
       ::= { dsensorConfigure 4 }

   dsensorSetRelay1 OBJECT-TYPE
       SYNTAX     INTEGER{
                  normalClose(1),
                  normalOpen(2)
       }
       ACCESS     read-write
       STATUS     mandatory
       DESCRIPTION
               ""
       ::= { dsensorConfigure 5 }

   dsensorSetRelay2 OBJECT-TYPE
       SYNTAX     INTEGER{
                  normalClose(1),
                  normalOpen(2)
       }
       ACCESS     read-write
       STATUS     mandatory
       DESCRIPTION
               ""
       ::= { dsensorConfigure 6 }

   dsensorSetRelay3 OBJECT-TYPE
       SYNTAX     INTEGER{
                  normalClose(1),
                  normalOpen(2)
       }
       ACCESS     read-write
       STATUS     mandatory
       DESCRIPTION
               ""
       ::= { dsensorConfigure 7 }

   dsensorSetRelay4 OBJECT-TYPE
       SYNTAX     INTEGER{
                  normalClose(1),
                  normalOpen(2)
       }
       ACCESS     read-write
       STATUS     mandatory
       DESCRIPTION
               ""
       ::= { dsensorConfigure 8 }

--
-- dsensor Trap group
--

   dsensorCommunicationLost TRAP-TYPE
       ENTERPRISE dsensorTraps
       DESCRIPTION
	"WARNING: Communication with the environmental sensor failed."
       ::= 1

   dsensorCommunicationEstablished TRAP-TYPE
       ENTERPRISE dsensorTraps
       DESCRIPTION
	"INFORMATION: Communication with the environmental sensor reestablished."
       ::= 2

   dsensorOverWarningTemperature TRAP-TYPE
       ENTERPRISE dsensorTraps
       DESCRIPTION
	"SEVER: The environment over warning temperature."
       ::= 3

   dsensorNoLongerOverWarningTemperature TRAP-TYPE
       ENTERPRISE dsensorTraps
       DESCRIPTION
	"INFORMATION: The environment recovered from over warning temperature."
       ::= 4

   dsensorOverAlarmTemperature TRAP-TYPE
       ENTERPRISE dsensorTraps
       DESCRIPTION
	"SEVER: The environment over alarm temperature."
       ::= 5

   dsensorNoLongerOverAlarmTemperature TRAP-TYPE
       ENTERPRISE dsensorTraps
       DESCRIPTION
	"INFORMATION: The environment recovered from over alarm temperature."
       ::= 6

   dsensorOverWarningHumidity TRAP-TYPE
       ENTERPRISE dsensorTraps
       DESCRIPTION
	"SEVER: The environment over warning humidity."
       ::= 7

   dsensorNoLongerOverWarningHumidity TRAP-TYPE
       ENTERPRISE dsensorTraps
       DESCRIPTION
	"INFORMATION: The environment recovered from over warning humidity."
       ::= 8

   dsensorOverAlarmHumidity TRAP-TYPE
       ENTERPRISE dsensorTraps
       DESCRIPTION
	"SEVER: The environment over alarm humidity."
       ::= 9

   dsensorNoLongerOverAlarmHumidity TRAP-TYPE
       ENTERPRISE dsensorTraps
       DESCRIPTION
	"INFORMATION: The environment recovered from over alarm humidity."
       ::= 10

   dsensorRelay1Alarm TRAP-TYPE
       ENTERPRISE dsensorTraps
       DESCRIPTION
	"INFORMATION: The environment relay1 is not in normal state."
       ::= 11

   dsensorRelay1Normal TRAP-TYPE
       ENTERPRISE dsensorTraps
       DESCRIPTION
	"INFORMATION: The environment relay1 is in normal state."
       ::= 12

   dsensorRelay2Alarm TRAP-TYPE
       ENTERPRISE dsensorTraps
       DESCRIPTION
	"INFORMATION: The environment relay2 is not in normal state."
       ::= 13

   dsensorRelay2Normal TRAP-TYPE
       ENTERPRISE dsensorTraps
       DESCRIPTION
	"INFORMATION: The environment relay2 is in normal state."
       ::= 14

   dsensorRelay3Alarm TRAP-TYPE
       ENTERPRISE dsensorTraps
       DESCRIPTION
	"INFORMATION: The environment relay3 is not in normal state."
       ::= 15

   dsensorRelay3Normal TRAP-TYPE
       ENTERPRISE dsensorTraps
       DESCRIPTION
	"INFORMATION: The environment relay3 is in normal state."
       ::= 16

   dsensorRelay4Alarm TRAP-TYPE
       ENTERPRISE dsensorTraps
       DESCRIPTION
	"INFORMATION: The environment relay4 is not in normal state."
       ::= 17

   dsensorRelay4Normal TRAP-TYPE
       ENTERPRISE dsensorTraps
       DESCRIPTION
	"INFORMATION: The environment relay4 is in normal state."
       ::= 18

END
