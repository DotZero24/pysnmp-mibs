--Delta-MIB { iso(1) org(3) dod(6) internet(1) private(4) enterprises(1) delta(2254) ups(2) upsv5(5) }


DeltaUPSv5-MIB DEFINITIONS ::= BEGIN


IMPORTS
	enterprises, IpAddress, TimeTicks
		FROM RFC1155-SMI
	DisplayString
		FROM RFC1213-MIB
	OBJECT-TYPE
		FROM RFC-1212
	TRAP-TYPE
		FROM RFC-1215;


delta				OBJECT IDENTIFIER ::=  { enterprises 2254 }

ups					OBJECT IDENTIFIER ::=  { delta 2 }

upsv5				OBJECT IDENTIFIER ::=  { ups 5 }

dupsIdent			OBJECT IDENTIFIER ::=  { upsv5 1 }
dupsControl			OBJECT IDENTIFIER ::=  { upsv5 2 }
dupsConfig			OBJECT IDENTIFIER ::=  { upsv5 3 }
dupsInput			OBJECT IDENTIFIER ::=  { upsv5 4 }
dupsOutput			OBJECT IDENTIFIER ::=  { upsv5 5 }
dupsBypass			OBJECT IDENTIFIER ::=  { upsv5 6 }
dupsBattery			OBJECT IDENTIFIER ::=  { upsv5 7 }
dupsTest 			OBJECT IDENTIFIER ::=  { upsv5 8 }
dupsAlarm 			OBJECT IDENTIFIER ::=  { upsv5 9 }
dupsPowerModule		OBJECT IDENTIFIER ::=  { upsv5 10 }
dupsTrapArgs		OBJECT IDENTIFIER ::=  { upsv5 11 }
dupsParallel		OBJECT IDENTIFIER ::=  { upsv5 12 }
dupsIntegrated 	OBJECT IDENTIFIER ::=  { upsv5 13 }
dupsTraps			OBJECT IDENTIFIER ::=  { upsv5 20 }


--
-- dups Ident group
--
   dupsIdentManufacturer OBJECT-TYPE
       SYNTAX     DisplayString (SIZE(0..20))
       ACCESS     read-only
       STATUS     mandatory
       DESCRIPTION
               "The name of the UPS manufacturer."
       ::= { dupsIdent 1 }

   dupsIdentModel OBJECT-TYPE
       SYNTAX     DisplayString (SIZE(0..31))
       ACCESS     read-only
       STATUS     mandatory
       DESCRIPTION
               "The UPS Model designation."
       ::= { dupsIdent 2 }

   dupsIdentUPSSoftwareVersion OBJECT-TYPE
       SYNTAX     DisplayString (SIZE(0..15))
       ACCESS     read-only
       STATUS     mandatory
       DESCRIPTION
               "The UPS firmware/software version(s). This variable
               may or may not has the same value as
               upsIdentAgentSoftwareVersion in some implementations."
       ::= { dupsIdent 3 }

   dupsIdentAgentSoftwareVersion OBJECT-TYPE
       SYNTAX     DisplayString (SIZE(0..15))
       ACCESS     read-only
       STATUS     mandatory
       DESCRIPTION
               "The UPS agent software version. This variable may or
               may not has the same value as
               upsIdentUPSSoftwareVersion in some implementations."
       ::= { dupsIdent 4 }

   dupsIdentName OBJECT-TYPE
       SYNTAX     DisplayString (SIZE(0..63))
       ACCESS     read-write
       STATUS     mandatory
       DESCRIPTION
               "A string identifying the UPS. This object should be
               set by the administrator."
       ::= { dupsIdent 5 }

   dupsAttachedDevices OBJECT-TYPE
       SYNTAX     DisplayString (SIZE(0..63))
       ACCESS     read-write
       STATUS     mandatory
       DESCRIPTION
               "A string identifying the devices attached to the
               output(s) of the UPS. This object should be set by
               the administrator."
       ::= { dupsIdent 6 }

   dupsRatingOutputVA OBJECT-TYPE
       SYNTAX     INTEGER
       UNITS      "VA"
       ACCESS     read-only
       STATUS     mandatory
       DESCRIPTION
               "The magnitude of the nominal output VA rating.
               The value -1 indicates this UPS does not support this item."
       ::= { dupsIdent 7 }

   dupsRatingOutputVoltage OBJECT-TYPE
       SYNTAX     INTEGER
       UNITS      "Volt"
       ACCESS     read-only
       STATUS     mandatory
       DESCRIPTION
               "The magnitude of the nominal output voltage rating.
               The value -1 indicates this UPS does not support this item."
       ::= { dupsIdent 8 }

   dupsRatingOutputFrequency OBJECT-TYPE
       SYNTAX     INTEGER
       UNITS      "Hz"
       ACCESS     read-only
       STATUS     mandatory
       DESCRIPTION
               "The magnitude of the nominal output frequency rating.
               The value -1 indicates this UPS does not support this item."
       ::= { dupsIdent 9 }

   dupsRatingInputVoltage OBJECT-TYPE
       SYNTAX     INTEGER
       UNITS      "Volt"
       ACCESS     read-only
       STATUS     mandatory
       DESCRIPTION
               "The magnitude of the nominal input voltage rating.
               The value -1 indicates this UPS does not support this item."
       ::= { dupsIdent 10 }

   dupsRatingInputFrequency OBJECT-TYPE
       SYNTAX     INTEGER
       UNITS      "Hz"
       ACCESS     read-only
       STATUS     mandatory
       DESCRIPTION
               "The magnitude of the nominal input frequency rating.
               The value -1 indicates this UPS does not support this item."
       ::= { dupsIdent 11 }

   dupsRatingBatteryVoltage OBJECT-TYPE
       SYNTAX     INTEGER
       UNITS      "Volt"
       ACCESS     read-only
       STATUS     mandatory
       DESCRIPTION
               "The magnitude of the nominal battery voltage rating.
               The value -1 indicates this UPS does not support this item."
       ::= { dupsIdent 12 }

   dupsLowTransferVoltUpBound OBJECT-TYPE
       SYNTAX     INTEGER
       UNITS      "Volt"
       ACCESS     read-only
       STATUS     mandatory
       DESCRIPTION
               "The minimum input line voltage upper bound allowed
               before the UPS system transfers to battery backup.
               The value -1 indicates this UPS does not support this item."
       ::= { dupsIdent 13 }

   dupsLowTransferVoltLowBound OBJECT-TYPE
       SYNTAX     INTEGER
       UNITS      "Volt"
       ACCESS     read-only
       STATUS     mandatory
       DESCRIPTION
               "The minimum input line voltage lower bound allowed
               before the UPS system transfers to battery backup.
               The value -1 indicates this UPS does not support this item."
       ::= { dupsIdent 14 }

   dupsHighTransferVoltUpBound OBJECT-TYPE
       SYNTAX     INTEGER
       UNITS      "Volt"
       ACCESS     read-only
       STATUS     mandatory
       DESCRIPTION
               "The maximum input line voltage upper bound allowed
               before the UPS system transfers to battery backup.
               The value -1 indicates this UPS does not support this item."
       ::= { dupsIdent 15 }

   dupsHighTransferVoltLowBound OBJECT-TYPE
       SYNTAX     INTEGER
       UNITS      "Volt"
       ACCESS     read-only
       STATUS     mandatory
       DESCRIPTION
               "The maximum input line voltage lower bound allowed
               before the UPS system transfers to battery backup.
               The value -1 indicates this UPS does not support this item."
       ::= { dupsIdent 16 }

   dupsLowBattTime OBJECT-TYPE
       SYNTAX     INTEGER
       UNITS      "Second"
       ACCESS     read-only
       STATUS     mandatory
       DESCRIPTION
               "Minutes, time from low battery to low battery shutdown.
               The value -1 indicates this UPS does not support this item."
       ::= { dupsIdent 17 }

   dupsOutletRelays OBJECT-TYPE
       SYNTAX     INTEGER
       ACCESS     read-only
       STATUS     mandatory
       DESCRIPTION
               "Number of outlet relay. If it is 0, the function is not
               available for the UPS."
       ::= { dupsIdent 18 }

   dupsType OBJECT-TYPE
       SYNTAX     INTEGER {
           on-line(1),
           off-line(2),
           line-interactive(3),
           three-phase(4),
           splite-phase(5)
       }
       ACCESS     read-only
       STATUS     mandatory
       DESCRIPTION
               "Indicate the UPS type."
       ::= { dupsIdent 19 }

--
-- dups Control group
--
   dupsShutdownType OBJECT-TYPE
       SYNTAX     INTEGER {
           output(1),
           system(2)
       }
       ACCESS     read-write
       STATUS     mandatory
       DESCRIPTION
               "This object determines the nature of the action to be
               taken at the time when the countdown of the
               upsShutdownAfterDelay and upsRebootWithDuration
               objects reaches zero.
               Setting this object to output(1) indicates that
               shutdown requests should cause only the output of the
               UPS to turn off.  Setting this object to system(2)
               indicates that shutdown requests will cause the entire
               UPS system to turn off."
       ::= { dupsControl 1 }

   dupsAutoReboot OBJECT-TYPE
       SYNTAX     INTEGER {
           on(1),
           off(2)
       }
       ACCESS     read-write
       STATUS     mandatory
       DESCRIPTION
               "In backup mode, the UPS may shutdown normally by SDA command,
               dry-contact remote shutdown signal or low battery shutdown.
               This command is used to determine the unit should restart or
               not next time when the power restores"
       ::= { dupsControl 2 }

   dupsShutdownAction OBJECT-TYPE
       SYNTAX     INTEGER
       ACCESS     read-write
       STATUS     mandatory
       DESCRIPTION
               "If the value is greater than 0 the UPS performs
               shutdown action that defined by ShutdownType after
               the seconds. 0, aborted."
       ::= { dupsControl 3 }

   dupsRestartAction OBJECT-TYPE
       SYNTAX     INTEGER
       ACCESS     read-write
       STATUS     mandatory
       DESCRIPTION
               "UPS will restart after the indicated number of minutes.
                -1, aborted."
       ::= { dupsControl 4 }

   dupsSetOutletRelay OBJECT-TYPE
       SYNTAX     INTEGER
       ACCESS     read-write
       STATUS     mandatory
       DESCRIPTION
               "Indicate which outlet relay, from 1,2,3... ."
       ::= { dupsControl 5 }

   dupsRelayOffDelay OBJECT-TYPE
       SYNTAX     INTEGER
       ACCESS     read-write
       STATUS     mandatory
       DESCRIPTION
               "Turn the relay off after the seconds. The relay was indicated
                by SetOutletRelay."
       ::= { dupsControl 6 }

   dupsRelayOnDelay OBJECT-TYPE
       SYNTAX     INTEGER
       ACCESS     read-write
       STATUS     mandatory
       DESCRIPTION
               "Turn the relay on after the minutes. The relay was indicated
                by SetOutletRelay."
       ::= { dupsControl 7 }

   dupsSmartShutdown OBJECT-TYPE
       SYNTAX     INTEGER
       ACCESS     read-write
       STATUS     mandatory
       DESCRIPTION
               "Any value to initiate the Smart Shutdown for the UPS."
       ::= { dupsControl 8 }

   dupsClearEnergy OBJECT-TYPE
       SYNTAX     INTEGER
       ACCESS     read-write
       STATUS     mandatory
       DESCRIPTION
               "Any value to clear the energy record in the UPS."
       ::= { dupsControl 9 }

--
-- dups Configure group
--
   dupsConfigBuzzerAlarm OBJECT-TYPE
       SYNTAX     INTEGER {
           alarm(1),
           silence(2)
       }
       ACCESS     read-write
       STATUS     mandatory
       DESCRIPTION
               "UPS will keep silence but will alarm again when
               next power event is occurred"
       ::= { dupsConfig 1 }

   dupsConfigBuzzerState OBJECT-TYPE
       SYNTAX     INTEGER {
           enable(1),
           disable(2)
       }
       ACCESS     read-write
       STATUS     mandatory
       DESCRIPTION
               "If it is disabled then the UPS is always muted."
       ::= { dupsConfig 2 }

   dupsConfigSensitivity OBJECT-TYPE
       SYNTAX     INTEGER {
           normal(1),
           reduced(2),
           low(3)
       }
       ACCESS    read-write
       STATUS    mandatory
       DESCRIPTION
               "The seneitivity of the UPS to utility line
               abnormalities or noises."
       ::= { dupsConfig 3 }

   dupsConfigLowVoltageTransferPoint OBJECT-TYPE
       SYNTAX     INTEGER
       UNITS      "Volt"
       ACCESS     read-write
       STATUS     mandatory
       DESCRIPTION
               "The minimum input line voltage allowed before the UPS
               system transfers to battery backup."
       ::= { dupsConfig 4 }

   dupsConfigHighVoltageTransferPoint OBJECT-TYPE
       SYNTAX     INTEGER
       UNITS      "Volt"
       ACCESS     read-write
       STATUS     mandatory
       DESCRIPTION
               "The maximum line voltage allowed before the UPS
               system transfers to battery backup."
       ::= { dupsConfig 5 }

   dupsConfigUPSBootDelay OBJECT-TYPE
       SYNTAX     INTEGER
       UNITS      "Second"
       ACCESS     read-write
       STATUS     mandatory
       DESCRIPTION
               "Delay the UPS startup after power restores. The power
               quality may not stable when power restores, this
               feature let the UPS wait a period of time to startup
               the system."
       ::= { dupsConfig 6 }

   dupsConfigExternalBatteryPack OBJECT-TYPE
       SYNTAX     INTEGER
       ACCESS     read-write
       STATUS     mandatory
       DESCRIPTION
               "Indicate the number of external battery pack."
       ::= { dupsConfig 7 }

   dupsConfigSmartShutdownOSDelay OBJECT-TYPE
       SYNTAX     INTEGER
       UNITS      "Second"
       ACCESS     read-write
       STATUS     mandatory
       DESCRIPTION
               "The estimated operating system shutdown delay time for
               Smart Shutdown."
       ::= { dupsConfig 8 }

   dupsConfigSmartShutdownUPSDelay OBJECT-TYPE
       SYNTAX     INTEGER
       UNITS      "Second"
       ACCESS     read-write
       STATUS     mandatory
       DESCRIPTION
               "The estimated UPS shutdown delay time for
               Smart Shutdown."
       ::= { dupsConfig 9 }

   dupsConfigEconomicMode OBJECT-TYPE
       SYNTAX     INTEGER {
           enable(1),
           disable(2)
       }
       ACCESS     read-write
       STATUS     mandatory
       DESCRIPTION
               "Used to enable or disable the economic mode."
       ::= { dupsConfig 10 }

--
-- dups Input group
--
   dupsInputNumLines OBJECT-TYPE
       SYNTAX     INTEGER
       ACCESS     read-only
       STATUS     mandatory
       DESCRIPTION
               "The number of input lines utilized in this device."
       ::= { dupsInput 1 }

   dupsInputFrequency1 OBJECT-TYPE
       SYNTAX     INTEGER
       UNITS      "0.1 Hertz"
       ACCESS     read-only
       STATUS     mandatory
       DESCRIPTION
               "The current input line 1 frequency to the UPS
               system in 1/10 Hz. The value -1 indicates this UPS does
               not support this item."
       ::= { dupsInput 2 }

   dupsInputVoltage1 OBJECT-TYPE
       SYNTAX     INTEGER
       UNITS      "0.1 Volt"
       ACCESS     read-only
       STATUS     mandatory
       DESCRIPTION
               "The Input phase 1 voltage of the UPS system in 1/10 V.
               The value -1 indicates this UPS does not support this item."
       ::= { dupsInput 3 }

   dupsInputVoltage12 OBJECT-TYPE
       SYNTAX     INTEGER
       UNITS      "0.1 Volt"
       ACCESS     read-only
       STATUS     mandatory
       DESCRIPTION
               "The Input line 1-2 voltage of the UPS system in 1/10 V.
               The value -1 indicates this UPS does not support this item."
       ::= { dupsInput 4 }

   dupsInputCurrent1 OBJECT-TYPE
       SYNTAX     INTEGER
       UNITS      "0.1 Amp"
       ACCESS     read-only
       STATUS     mandatory
       DESCRIPTION
               "The Input line 1 current to the UPS system in 1/10 A.
               The value -1 indicates this UPS does not support this item."
       ::= { dupsInput 5 }

   dupsInputPower1 OBJECT-TYPE
       SYNTAX     INTEGER
       UNITS      "1 Watt"
       ACCESS     read-only
       STATUS     mandatory
       DESCRIPTION
               "The Input line 1 power to the UPS system in 1 Watt.
               The value -1 indicates this UPS does not support this item."
       ::= { dupsInput 6 }

   dupsInputFrequency2 OBJECT-TYPE
       SYNTAX     INTEGER
       UNITS      "0.1 Hertz"
       ACCESS     read-only
       STATUS     mandatory
       DESCRIPTION
               "The current input line 2 frequency to the UPS system
                in 1/10 Hz.
                The value -1 indicates this UPS does not support this item."
       ::= { dupsInput 7 }

   dupsInputVoltage2 OBJECT-TYPE
       SYNTAX     INTEGER
       UNITS      "0.1 Volt"
       ACCESS     read-only
       STATUS     mandatory
       DESCRIPTION
               "The Input phase 2 voltage of the UPS system in 1/10 V.
               The value -1 indicates this UPS does not support this item."
       ::= { dupsInput 8 }

   dupsInputVoltage23 OBJECT-TYPE
       SYNTAX     INTEGER
       UNITS      "0.1 Volt"
       ACCESS     read-only
       STATUS     mandatory
       DESCRIPTION
               "The Input line 2-3 voltage of the UPS system in 1/10 V.
               The value -1 indicates this UPS does not support this item."
       ::= { dupsInput 9 }

   dupsInputCurrent2 OBJECT-TYPE
       SYNTAX     INTEGER
       UNITS      "0.1 Amp"
       ACCESS     read-only
       STATUS     mandatory
       DESCRIPTION
               "The Input line 2 current to the UPS system in 1/10 A.
               The value -1 indicates this UPS does not support this item."
       ::= { dupsInput 10 }

   dupsInputPower2 OBJECT-TYPE
       SYNTAX     INTEGER
       UNITS      "1 Watt"
       ACCESS     read-only
       STATUS     mandatory
       DESCRIPTION
               "The Input line 2 power to the UPS system in 1 Watt.
               The value -1 indicates this UPS does not support this item."
       ::= { dupsInput 11 }

   dupsInputFrequency3 OBJECT-TYPE
       SYNTAX     INTEGER
       UNITS      "0.1 Hertz"
       ACCESS     read-only
       STATUS     mandatory
       DESCRIPTION
               "The current input line 3 frequency to the UPS system
               in 1/10 Hz.
               The value -1 indicates this UPS does not support this item."
       ::= { dupsInput 12 }

   dupsInputVoltage3 OBJECT-TYPE
       SYNTAX     INTEGER
       UNITS      "0.1 Volt"
       ACCESS     read-only
       STATUS     mandatory
       DESCRIPTION
               "The Input phase 3 voltage of the UPS system in 1/10 V.
               The value -1 indicates this UPS does not support this item."
       ::= { dupsInput 13 }

   dupsInputVoltage31 OBJECT-TYPE
       SYNTAX     INTEGER
       UNITS      "0.1 Volt"
       ACCESS     read-only
       STATUS     mandatory
       DESCRIPTION
               "The Input line 3-1 voltage of the UPS system in 1/10 V.
               The value -1 indicates this UPS does not support this item."
       ::= { dupsInput 14 }

   dupsInputCurrent3 OBJECT-TYPE
       SYNTAX     INTEGER
       UNITS      "0.1 Amp"
       ACCESS     read-only
       STATUS     mandatory
       DESCRIPTION
               "The Input line 3 current to the UPS system in 1/10 A.
               The value -1 indicates this UPS does not support this item."
       ::= { dupsInput 15 }

   dupsInputPower3 OBJECT-TYPE
       SYNTAX     INTEGER
       UNITS      "1 Watt"
       ACCESS     read-only
       STATUS     mandatory
       DESCRIPTION
               "The Input line 3 power to the UPS system in 1 Watt.
               The value -1 indicates this UPS does not support this item."
       ::= { dupsInput 16 }

   dupsInputEnergy1 OBJECT-TYPE
       SYNTAX     INTEGER
       UNITS      "1 kWh"
       ACCESS     read-only
       STATUS     mandatory
       DESCRIPTION
               "The Input line 1 energy to the UPS system in 1 kWh.
               The value -1 indicates this UPS does not support this item."
       ::= { dupsInput 17 }

   dupsInputEnergy2 OBJECT-TYPE
       SYNTAX     INTEGER
       UNITS      "1 kWh"
       ACCESS     read-only
       STATUS     mandatory
       DESCRIPTION
               "The Input line 2 energy to the UPS system in 1 kWh.
               The value -1 indicates this UPS does not support this item."
       ::= { dupsInput 18 }

   dupsInputEnergy3 OBJECT-TYPE
       SYNTAX     INTEGER
       UNITS      "1 kWh"
       ACCESS     read-only
       STATUS     mandatory
       DESCRIPTION
               "The Input line 3 energy to the UPS system in 1 kWh.
               The value -1 indicates this UPS does not support this item."
       ::= { dupsInput 19 }

   dupsInputEnergyTotal OBJECT-TYPE
       SYNTAX     INTEGER
       UNITS      "1 kWh"
       ACCESS     read-only
       STATUS     mandatory
       DESCRIPTION
               "The total Input energy to the UPS system in 1 kWh.
               The value -1 indicates this UPS does not support this item."
       ::= { dupsInput 20 }

   dupsInputLineFailCause OBJECT-TYPE
       SYNTAX     INTEGER {
           no(1),
           outoftolvolt(2),
           outoftolfreq(3),
           utilityoff(4)
       }
       ACCESS     read-only
       STATUS     mandatory
       DESCRIPTION
               "Cause of input outage."
       ::= { dupsInput 21 }

   dupsInputBadStatus OBJECT-TYPE
       SYNTAX     INTEGER {
           yes(1),
           no(2)
       }
       ACCESS     read-only
       STATUS     mandatory
       DESCRIPTION
               "Incorrect input voltage or frequency."
       ::= { dupsInput 22 }

--
-- dups Output group
--
   dupsOutputSource OBJECT-TYPE
       SYNTAX     INTEGER {
           normal(1),
           battery(2),
           bypass(3),
           reducing(4),
           boosting(5),
           manualBypass(6),
           other(7),
           noOutput(8),
           onEco(9)
       }
       ACCESS     read-only
       STATUS     mandatory
       DESCRIPTION
               "The present source of output power. The enumeration
               noOutput(8) indicates that there is no source of output
               power (and therefore no output power), for example,
               the system has opened the output breaker."
       ::= { dupsOutput 1 }

   dupsOutputFrequency OBJECT-TYPE
       SYNTAX     INTEGER
       UNITS      "0.1 Hertz"
       ACCESS     read-only
       STATUS     mandatory
       DESCRIPTION
               "The present output frequency in 1/10 Hz.
               The value -1 indicates this UPS does not support this item."
       ::= { dupsOutput 2 }

   dupsOutputNumLines OBJECT-TYPE
       SYNTAX     INTEGER
       ACCESS     read-only
       STATUS     mandatory
       DESCRIPTION
               "The number of output lines utilized in this device."
       ::= { dupsOutput 3 }

   dupsOutputVoltage1 OBJECT-TYPE
       SYNTAX     INTEGER
       UNITS      "0.1 Volt"
       ACCESS     read-only
       STATUS     mandatory
       DESCRIPTION
               "The Output phase 1 voltage of the UPS system in 1/10 V.
               The value -1 indicates this UPS does not support this item."
	::= { dupsOutput 4 }

   dupsOutputVoltage12 OBJECT-TYPE
       SYNTAX     INTEGER
       UNITS      "0.1 Volt"
       ACCESS     read-only
       STATUS     mandatory
       DESCRIPTION
               "The Output line 1-2 voltage of the UPS system in 1/10 V.
               The value -1 indicates this UPS does not support this item."
	::= { dupsOutput 5 }

   dupsOutputCurrent1 OBJECT-TYPE
       SYNTAX     INTEGER
       UNITS      "0.1 Amp"
       ACCESS     read-only
       STATUS     mandatory
       DESCRIPTION
               "The Output line 1 current of the UPS system in 1/10 A.
               The value -1 indicates this UPS does not support this item."
	::= { dupsOutput 6 }

   dupsOutputPower1 OBJECT-TYPE
       SYNTAX     INTEGER
       UNITS      "1 Watt"
       ACCESS     read-only
       STATUS     mandatory
       DESCRIPTION
               "The Output line 1 active power of the UPS system in watts.
               The value -1 indicates this UPS does not support this item."
	::= { dupsOutput 7 }

   dupsOutputLoad1 OBJECT-TYPE
       SYNTAX     INTEGER
       UNITS      "1 Percent"
       ACCESS     read-only
       STATUS     mandatory
       DESCRIPTION
               "The current UPS output line 1 load expressed in percent
               of rated capacity.
               The value -1 indicates this UPS does not support this item."
	::= { dupsOutput 8 }

   dupsOutputVoltage2 OBJECT-TYPE
       SYNTAX     INTEGER
       UNITS      "0.1 Volt"
       ACCESS     read-only
       STATUS     mandatory
       DESCRIPTION
               "The Output phase 2 voltage of the UPS system in 1/10 V.
               The value -1 indicates this UPS does not support this item."
	::= { dupsOutput 9 }

   dupsOutputVoltage23 OBJECT-TYPE
       SYNTAX     INTEGER
       UNITS      "0.1 Volt"
       ACCESS     read-only
       STATUS     mandatory
       DESCRIPTION
               "The Output line 2-3 voltage of the UPS system in 1/10 V.
               The value -1 indicates this UPS does not support this item."
	::= { dupsOutput 10 }

   dupsOutputCurrent2 OBJECT-TYPE
       SYNTAX     INTEGER
       UNITS      "0.1 Amp"
       ACCESS     read-only
       STATUS     mandatory
       DESCRIPTION
               "The Output line 2 current of the UPS system in 1/10 A.
               The value -1 indicates this UPS does not support this item."
	::= { dupsOutput 11 }

   dupsOutputPower2 OBJECT-TYPE
       SYNTAX     INTEGER
       UNITS      "1 Watt"
       ACCESS     read-only
       STATUS     mandatory
       DESCRIPTION
               "The Output line 2 active power of the UPS system in watts.
               The value -1 indicates this UPS does not support this item."
	::= { dupsOutput 12 }

   dupsOutputLoad2 OBJECT-TYPE
       SYNTAX     INTEGER
       UNITS      "1 Percent"
       ACCESS     read-only
       STATUS     mandatory
       DESCRIPTION
               "The current UPS output line 2 load expressed in percent
               of rated capacity.
               The value -1 indicates this UPS does not support this item."
	::= { dupsOutput 13 }

   dupsOutputVoltage3 OBJECT-TYPE
       SYNTAX     INTEGER
       UNITS      "0.1 Volt"
       ACCESS     read-only
       STATUS     mandatory
       DESCRIPTION
               "The Output phase 3 voltage of the UPS system in 1/10 V.
               The value -1 indicates this UPS does not support this item."
	::= { dupsOutput 14 }

   dupsOutputVoltage31 OBJECT-TYPE
       SYNTAX     INTEGER
       UNITS      "0.1 Volt"
       ACCESS     read-only
       STATUS     mandatory
       DESCRIPTION
               "The Output line 3-1 voltage of the UPS system in 1/10 V.
               The value -1 indicates this UPS does not support this item."
	::= { dupsOutput 15 }

   dupsOutputCurrent3 OBJECT-TYPE
       SYNTAX     INTEGER
       UNITS      "0.1 Amp"
       ACCESS     read-only
       STATUS     mandatory
       DESCRIPTION
               "The Output line 3 current of the UPS system in 1/10 A.
               The value -1 indicates this UPS does not support this item."
	::= { dupsOutput 16 }

   dupsOutputPower3 OBJECT-TYPE
       SYNTAX     INTEGER
       UNITS      "1 Watt"
       ACCESS     read-only
       STATUS     mandatory
       DESCRIPTION
               "The Output line 3 active power of the UPS system in watts.
               The value -1 indicates this UPS does not support this item."
	::= { dupsOutput 17 }

   dupsOutputLoad3 OBJECT-TYPE
       SYNTAX     INTEGER
       UNITS      "1 Percent"
       ACCESS     read-only
       STATUS     mandatory
       DESCRIPTION
               "The current UPS output line 3 load expressed in percent
               of rated capacity.
               The value -1 indicates this UPS does not support this item."
	::= { dupsOutput 18 }

   dupsOutputTotalActivePower OBJECT-TYPE
       SYNTAX     INTEGER
       UNITS      "0.1 kW"
       ACCESS     read-only
       STATUS     mandatory
       DESCRIPTION
               "The total output active power of the UPS system in 0.1 kW.
               The value -1 indicates this UPS does not support this item."
	::= { dupsOutput 19 }

   dupsOutputTotalApparentPower OBJECT-TYPE
       SYNTAX     INTEGER
       UNITS      "0.1 kVA"
       ACCESS     read-only
       STATUS     mandatory
       DESCRIPTION
               "The total output apparent power of the UPS system in 0.1 kVA.
               The value -1 indicates this UPS does not support this item."
	::= { dupsOutput 20 }

   dupsOutputTotalPowerFactor OBJECT-TYPE
       SYNTAX     INTEGER
       UNITS      "1 Percent"
       ACCESS     read-only
       STATUS     mandatory
       DESCRIPTION
               "The total output power factor of the UPS system.
               The value -1 indicates this UPS does not support this item."
	::= { dupsOutput 21 }

   dupsOutputEnergy1 OBJECT-TYPE
       SYNTAX     INTEGER
       UNITS      "1 kWh"
       ACCESS     read-only
       STATUS     mandatory
       DESCRIPTION
               "The UPS output line 1 energy in kWh.
               The value -1 indicates this UPS does not support this item."
	::= { dupsOutput 22 }

   dupsOutputEnergy2 OBJECT-TYPE
       SYNTAX     INTEGER
       UNITS      "1 kWh"
       ACCESS     read-only
       STATUS     mandatory
       DESCRIPTION
               "The UPS output line 2 energy in kWh.
               The value -1 indicates this UPS does not support this item."
	::= { dupsOutput 23 }

   dupsOutputEnergy3 OBJECT-TYPE
       SYNTAX     INTEGER
       UNITS      "1 kWh"
       ACCESS     read-only
       STATUS     mandatory
       DESCRIPTION
               "The UPS output line 3 energy in kWh.
               The value -1 indicates this UPS does not support this item."
	::= { dupsOutput 24 }

   dupsOutputEnergyTotal OBJECT-TYPE
       SYNTAX     INTEGER
       UNITS      "1 kWh"
       ACCESS     read-only
       STATUS     mandatory
       DESCRIPTION
               "The UPS total output energy in kWh.
               The value -1 indicates this UPS does not support this item."
	::= { dupsOutput 25 }

--
-- dups Bypass group
--
   dupsBypassFrequency OBJECT-TYPE
       SYNTAX     INTEGER
       UNITS      "0.1 Hertz"
       ACCESS     read-only
       STATUS     mandatory
       DESCRIPTION
               "The present bypass frequency in 1/10 Hz.
               The value -1 indicates this UPS does not support this item."
       ::= { dupsBypass 1 }

   dupsBypassNumLines OBJECT-TYPE
       SYNTAX     INTEGER
       ACCESS     read-only
       STATUS     mandatory
       DESCRIPTION
               "The number of bypass lines utilized in this device."
       ::= { dupsBypass 2 }

   dupsBypassVoltage1 OBJECT-TYPE
       SYNTAX     INTEGER
       UNITS      "0.1 Volt"
       ACCESS     read-only
       STATUS     mandatory
       DESCRIPTION
               "The bypass phase 1 voltage of the UPS system in 1/10 V.
               The value -1 indicates this UPS does not support this item."
	::= { dupsBypass 3 }

   dupsBypassVoltage12 OBJECT-TYPE
       SYNTAX     INTEGER
       UNITS      "0.1 Volt"
       ACCESS     read-only
       STATUS     mandatory
       DESCRIPTION
               "The bypass line 1-2 voltage of the UPS system in 1/10 V.
               The value -1 indicates this UPS does not support this item."
	::= { dupsBypass 4 }

   dupsBypassCurrent1 OBJECT-TYPE
       SYNTAX     INTEGER
       UNITS      "0.1 Amp"
       ACCESS     read-only
       STATUS     mandatory
       DESCRIPTION
               "The bypass line 1 current of the UPS system in 1/10 A.
               The value -1 indicates this UPS does not support this item."
	::= { dupsBypass 5 }

   dupsBypassPower1 OBJECT-TYPE
       SYNTAX     INTEGER
       UNITS      "1 Watt"
       ACCESS     read-only
       STATUS     mandatory
       DESCRIPTION
               "The bypass line 1 real power of the UPS system in watts.
               The value -1 indicates this UPS does not support this item."
	::= { dupsBypass 6 }

   dupsBypassVoltage2 OBJECT-TYPE
       SYNTAX     INTEGER
       UNITS      "0.1 Volt"
       ACCESS     read-only
       STATUS     mandatory
       DESCRIPTION
               "The bypass phase 2 voltage of the UPS system in 1/10 V.
               The value -1 indicates this UPS does not support this item."
	::= { dupsBypass 7 }

   dupsBypassVoltage23 OBJECT-TYPE
       SYNTAX     INTEGER
       UNITS      "0.1 Volt"
       ACCESS     read-only
       STATUS     mandatory
       DESCRIPTION
               "The bypass line 2-3 voltage of the UPS system in 1/10 V.
               The value -1 indicates this UPS does not support this item."
	::= { dupsBypass 8 }

   dupsBypassCurrent2 OBJECT-TYPE
       SYNTAX     INTEGER
       UNITS      "0.1 Amp"
       ACCESS     read-only
       STATUS     mandatory
       DESCRIPTION
               "The bypass line 2 current of the UPS system in 1/10 A.
               The value -1 indicates this UPS does not support this item."
	::= { dupsBypass 9 }

   dupsBypassPower2 OBJECT-TYPE
       SYNTAX     INTEGER
       UNITS      "1 Watt"
       ACCESS     read-only
       STATUS     mandatory
       DESCRIPTION
               "The bypass line 2 real power of the UPS system in watts.
               The value -1 indicates this UPS does not support this item."
	::= { dupsBypass 10 }

   dupsBypassVoltage3 OBJECT-TYPE
       SYNTAX     INTEGER
       UNITS      "0.1 Volt"
       ACCESS     read-only
       STATUS     mandatory
       DESCRIPTION
               "The bypass phase 3 voltage of the UPS system in 1/10 V.
               The value -1 indicates this UPS does not support this item."
	::= { dupsBypass 11 }

   dupsBypassVoltage31 OBJECT-TYPE
       SYNTAX     INTEGER
       UNITS      "0.1 Volt"
       ACCESS     read-only
       STATUS     mandatory
       DESCRIPTION
               "The bypass line 3-1 voltage of the UPS system in 1/10 V.
               The value -1 indicates this UPS does not support this item."
	::= { dupsBypass 12 }

   dupsBypassCurrent3 OBJECT-TYPE
       SYNTAX     INTEGER
       UNITS      "0.1 Amp"
       ACCESS     read-only
       STATUS     mandatory
       DESCRIPTION
               "The bypass line 3 current of the UPS system in 1/10 A.
               The value -1 indicates this UPS does not support this item."
	::= { dupsBypass 13 }

   dupsBypassPower3 OBJECT-TYPE
       SYNTAX     INTEGER
       UNITS      "1 Watt"
       ACCESS     read-only
       STATUS     mandatory
       DESCRIPTION
               "The bypass line 3 real power of the UPS system in watts.
               The value -1 indicates this UPS does not support this item."
	::= { dupsBypass 14 }

   dupsBypassSTSTemperature OBJECT-TYPE
       SYNTAX     INTEGER
       UNITS      "1 Degree Celsius"
       ACCESS     read-only
       STATUS     mandatory
       DESCRIPTION
               "The measurement of bypass STS temperature.
               The value -1 indicates this UPS does not support this item."
	::= { dupsBypass 15 }

--
-- dups Battery group
--
   dupsBatteryCondition OBJECT-TYPE
       SYNTAX     INTEGER {
           good(1),
           weak(2),
           replace(3)
       }
       ACCESS     read-only
       STATUS     mandatory
       DESCRIPTION
               "The indication of the capacity remaining in the UPS
               system's batteries when AC normal."
       ::= { dupsBattery 1 }

   dupsBatteryStatus OBJECT-TYPE
       SYNTAX     INTEGER {
           ok(1),
           low(2),
           depleted(3)
       }
       ACCESS     read-only
       STATUS     mandatory
       DESCRIPTION
               "The indication of the capacity remaining in the UPS
               system's batteries when AC failed.   A value of ok
               indicates that the remaining run-time is greater than
               upsConfigLowBattTime.  A value of low indicates
               that the remaining battery run-time is less than or
               equal to upsConfigLowBattTime.  A value of
               depleted indicates that the UPS will be unable
               to sustain the present load when and if the utility
               power is lost (including the possibility that the
               utility power is currently absent and the UPS is
               unable to sustain the output)."
       ::= { dupsBattery 2 }

   dupsBatteryCharge OBJECT-TYPE
       SYNTAX     INTEGER {
           floating(1),
           charging(2),
           resting(3),
           discharging(4)
       }
       ACCESS     read-only
       STATUS     mandatory
       DESCRIPTION
	           "Representing the battery charge status."
       ::= { dupsBattery 3 }

   dupsSecondsOnBattery OBJECT-TYPE
       SYNTAX     INTEGER
       UNITS      "1 Second"
       ACCESS     read-only
       STATUS     mandatory
       DESCRIPTION
               "If the unit is on battery power, the elapsed time
               since the UPS last switched to battery power, or the
               time since the network management subsystem was last
               restarted, whichever is less.  Zero shall be returned
               if the unit is not on battery power."
       ::= { dupsBattery 4 }

   dupsBatteryEstimatedTime OBJECT-TYPE
       SYNTAX     INTEGER
       UNITS      "1 Minute"
       ACCESS     read-only
       STATUS     mandatory
       DESCRIPTION
               "Estimated time from backup to low battery shutdown."
       ::= { dupsBattery 5 }

   dupsBatteryPosVoltage OBJECT-TYPE
       SYNTAX     INTEGER
       UNITS      "0.1 Volt DC"
       ACCESS     read-only
       STATUS     mandatory
       DESCRIPTION
               "The magnitude of the present positive battery voltage
               in 1/10 V."
       ::= { dupsBattery 6 }

   dupsBatteryNegVoltage OBJECT-TYPE
       SYNTAX     INTEGER
       UNITS      "-0.1 Volt DC"
       ACCESS     read-only
       STATUS     mandatory
       DESCRIPTION
               "The magnitude of the present negative battery voltage
               in -1/10 V."
       ::= { dupsBattery 7 }

   dupsBatteryPosCurrent OBJECT-TYPE
       SYNTAX     INTEGER
       UNITS      "0.1 Amp DC"
       ACCESS     read-only
       STATUS     mandatory
       DESCRIPTION
               "The present positive battery current in 1/10 A."
       ::= { dupsBattery 8 }

   dupsBatteryNegCurrent OBJECT-TYPE
       SYNTAX     INTEGER
       UNITS      "0.1 Amp DC"
       ACCESS     read-only
       STATUS     mandatory
       DESCRIPTION
               "The present negative battery current in 1/10 A."
       ::= { dupsBattery 9 }

   dupsBatteryPosCapacity OBJECT-TYPE
       SYNTAX     INTEGER (0..100)
       UNITS      "1 Percent"
       ACCESS     read-only
       STATUS     mandatory
       DESCRIPTION
               "An estimate of the positive battery charge remaining
               expressed as a percent of full charge."
       ::= { dupsBattery 10 }

   dupsBatteryNegCapacity OBJECT-TYPE
       SYNTAX     INTEGER (0..100)
       UNITS      "1 Percent"
       ACCESS     read-only
       STATUS     mandatory
       DESCRIPTION
               "An estimate of the negative battery charge remaining
               expressed as a percent of full charge."
       ::= { dupsBattery 11 }

   dupsTemperature OBJECT-TYPE
       SYNTAX     INTEGER
       UNITS      "1 Degrees Centigrade"
       ACCESS     read-only
       STATUS     mandatory
       DESCRIPTION
               "The measurement of internal temperature in the UPS."
       ::= { dupsBattery 12 }

   dupsLastReplaceDate OBJECT-TYPE
       SYNTAX     DisplayString (SIZE(0..8))
       ACCESS     read-only
       STATUS     mandatory
       DESCRIPTION
               "The last battery replacement date. The format is YYYYMMDD."
       ::= { dupsBattery 13 }

   dupsNextReplaceDate OBJECT-TYPE
       SYNTAX     DisplayString (SIZE(0..8))
       ACCESS     read-only
       STATUS     mandatory
       DESCRIPTION
               "The next battery replacement date. The format is YYYYMMDD."
       ::= { dupsBattery 14 }

   dupsBatteryBreaker OBJECT-TYPE
       SYNTAX     INTEGER {
           open(1),
           close(2)
       }
       ACCESS     read-only
       STATUS     mandatory
       DESCRIPTION
	           "Indicate the battery breaker status."
       ::= { dupsBattery 15 }

   dupsBatteryCab1Tempurature OBJECT-TYPE
       SYNTAX     INTEGER
       UNITS      "1 Degrees Centigrade"
       ACCESS     read-only
       STATUS     mandatory
       DESCRIPTION
	           "Temperature of battery cabnet 1."
       ::= { dupsBattery 16 }

   dupsBatteryCab2Tempurature OBJECT-TYPE
       SYNTAX     INTEGER
       UNITS      "1 Degrees Centigrade"
       ACCESS     read-only
       STATUS     mandatory
       DESCRIPTION
	           "Temperature of battery cabnet 2."
       ::= { dupsBattery 17 }

   dupsBatteryCab3Tempurature OBJECT-TYPE
       SYNTAX     INTEGER
       UNITS      "1 Degrees Centigrade"
       ACCESS     read-only
       STATUS     mandatory
       DESCRIPTION
	           "Temperature of battery cabnet 3."
       ::= { dupsBattery 18 }

   dupsBatteryCab4Tempurature OBJECT-TYPE
       SYNTAX     INTEGER
       UNITS      "1 Degrees Centigrade"
       ACCESS     read-only
       STATUS     mandatory
       DESCRIPTION
	           "Temperature of battery cabnet 4."
       ::= { dupsBattery 19 }

--
-- dups Test group
--
   dupsTestType OBJECT-TYPE
       SYNTAX     INTEGER {
           abort(1),
           generalTest(2),
           batteryTest(3),
           testFor10sec(4),
           testUntilBattlow(5)
       }
       ACCESS     read-write
       STATUS     mandatory
       DESCRIPTION
               "Perform the UPS Test procedure."
       ::= { dupsTest 1 }

   dupsTestResultsSummary OBJECT-TYPE
       SYNTAX     INTEGER {
           noTestsInitiated(1),
           donePass(2),
           inProgress(3),
           generalTestFail(4),
           batteryTestFail(5),
           deepBatteryTestFail(6)
       }
       ACCESS     read-only
       STATUS     mandatory
       DESCRIPTION
               "The results of the current or last UPS diagnostics
               test performed. The values for donePass(1),
               generalTestFail(3), and batteryTestFail(4) indicate that the
               test completed either successfully, with a warning, or
               with an error, respectively.Tests which have not yet
               concluded are indicated by inProgress(2).  The value
               noTestsInitiated(1) indicates that no previous test
               results are available."
       ::= { dupsTest 2 }

   dupsTestResultsDetail OBJECT-TYPE
       SYNTAX     DisplayString (SIZE (0..255))
       ACCESS     read-only
       STATUS     mandatory
       DESCRIPTION
               "Additional information about upsTestResultsSummary.
               If no additional information available, a zero length
               string is returned."
       ::= { dupsTest 3 }

   dupsGeneratorTest OBJECT-TYPE
       SYNTAX     INTEGER {
           abort(1),
           start(2)
       }
       ACCESS     read-write
       STATUS     mandatory
       DESCRIPTION
               "Perform the Generator Test procedure."
       ::= { dupsTest 4 }

   dupsGeneratorTestStatus OBJECT-TYPE
       SYNTAX     INTEGER {
           inProgress(1),
           none(2),
           inhibitTest(3),
           abnormallyTerminate(4),
           byInstruction(5),
           byTimeout(6)
       }
       ACCESS     read-only
       STATUS     mandatory
       DESCRIPTION
               "The results of the current or last generator diagnostics
                test performed.The values for None(2), InhibitTest(3),
                AbnormallyTerminate(4), ByInstruction(5), and ByTimeout(6)
                indicate that the tye of termination test. Tests which have
                not yet concluded are indicated by inProgress(1)"
       ::= { dupsTest 5 }

--
-- dups Alarm group
--
   dupsAlarmDisconnect OBJECT-TYPE
       SYNTAX     INTEGER{
                  on(1),
                  off(2)
       }
       ACCESS read-only
       STATUS     mandatory
       DESCRIPTION
               "Indicate the communication of the UPS is connected
               or disconnect?"
       ::= { dupsAlarm 1 }

   dupsAlarmInputOutOfRange OBJECT-TYPE
       SYNTAX     INTEGER{
                  on(1),
                  off(2)
       }
       ACCESS read-only
       STATUS     mandatory
       DESCRIPTION
               "Representing the input power is out of tolerance.
               This item is used to indicate the input power fail,
               a test condition should not set this item on."
       ::= { dupsAlarm 2 }

   dupsAlarmBatteryLow OBJECT-TYPE
       SYNTAX     INTEGER{
                  on(1),
                  off(2)
       }
       ACCESS read-only
       STATUS     mandatory
       DESCRIPTION
               "Are the UPS batteries low?"
       ::= { dupsAlarm 3 }

   dupsAlarmLoadOnBypass OBJECT-TYPE
       SYNTAX     INTEGER{
                  on(1),
                  off(2)
       }
       ACCESS read-only
       STATUS     mandatory
       DESCRIPTION
               "Does the UPS load on bypass?"
       ::= { dupsAlarm 4 }

   dupsAlarmOther OBJECT-TYPE
       SYNTAX     INTEGER{
                  on(1),
                  off(2)
       }
       ACCESS     read-only
       STATUS     mandatory
       DESCRIPTION
               "Indicate there is an alarm detected but which
               is not defined here."
       ::= { dupsAlarm 5 }

   dupsAlarmBatteryGroundFault OBJECT-TYPE
       SYNTAX     INTEGER{
                  on(1),
                  off(2)
       }
       ACCESS read-only
       STATUS     mandatory
       DESCRIPTION
               "To indicate the battery ground fault has
               been detected."
       ::= { dupsAlarm 6 }

   dupsAlarmTestInProgress OBJECT-TYPE
       SYNTAX     INTEGER{
                  on(1),
                  off(2)
       }
       ACCESS read-only
       STATUS     mandatory
       DESCRIPTION
               "Does the UPS test in progress?"
       ::= { dupsAlarm 7 }

   dupsAlarmBatteryTestFail OBJECT-TYPE
       SYNTAX     INTEGER{
                  on(1),
                  off(2)
       }
       ACCESS read-only
       STATUS     mandatory
       DESCRIPTION
               "Does the UPS test fail?"
       ::= { dupsAlarm 8 }

   dupsAlarmFuseFailure OBJECT-TYPE
       SYNTAX     INTEGER{
                  on(1),
                  off(2)
       }
       ACCESS read-only
       STATUS     mandatory
       DESCRIPTION
               "The failure of one or more fuses has been detected."
       ::= { dupsAlarm 9 }

   dupsAlarmOutputOverload OBJECT-TYPE
       SYNTAX     INTEGER{
                  on(1),
                  off(2)
       }
       ACCESS read-only
       STATUS     mandatory
       DESCRIPTION
               "The output load exceeds the UPS output capacity."
       ::= { dupsAlarm 10 }

   dupsAlarmInverterAbnormal OBJECT-TYPE
       SYNTAX     INTEGER{
                  on(1),
                  off(2)
       }
       ACCESS read-only
       STATUS     mandatory
       DESCRIPTION
               "Representing the inverter fail alarm."
       ::= { dupsAlarm 11 }

   dupsAlarmLoadOnReserve OBJECT-TYPE
       SYNTAX     INTEGER{
                  on(1),
                  off(2)
       }
       ACCESS read-only
       STATUS     mandatory
       DESCRIPTION
               "Does the UPS load on reserve?"
       ::= { dupsAlarm 12 }

   dupsAlarmTemperature OBJECT-TYPE
       SYNTAX     INTEGER{
                  on(1),
                  off(2)
       }
       ACCESS read-only
       STATUS     mandatory
       DESCRIPTION
               "Representing one of the temperature sensors has
               been determined its value is out of the limits."
       ::= { dupsAlarm 13 }

   dupsAlarmBypassOutOfRange OBJECT-TYPE
       SYNTAX     INTEGER{
                  on(1),
                  off(2)
       }
       ACCESS     read-only
       STATUS     mandatory
       DESCRIPTION
               "The bypass power is out of range."
       ::= { dupsAlarm 14 }

   dupsAlarmStandby OBJECT-TYPE
       SYNTAX     INTEGER{
                  on(1),
                  off(2)
       }
       ACCESS     read-only
       STATUS     mandatory
       DESCRIPTION
               "The UPS system is in the standby state."
       ::= { dupsAlarm 15 }

   dupsAlarmChargerFail OBJECT-TYPE
       SYNTAX     INTEGER{
                  on(1),
                  off(2)
       }
       ACCESS     read-only
       STATUS     mandatory
       DESCRIPTION
               "An incorrected problem has been detected
               within the UPS charger subsystem"
       ::= { dupsAlarm 16 }

   dupsAlarmFanFail OBJECT-TYPE
       SYNTAX     INTEGER{
                  on(1),
                  off(2)
       }
       ACCESS     read-only
       STATUS     mandatory
       DESCRIPTION
               "The failure of one or more fans in the UPS
               has been detected."
       ::= { dupsAlarm 17 }

   dupsAlarmEconomicMode OBJECT-TYPE
       SYNTAX     INTEGER{
                  on(1),
                  off(2)
       }
       ACCESS     read-only
       STATUS     mandatory
       DESCRIPTION
               "The UPS is working in the economic mode
               (act like an off-line UPS)."
       ::= { dupsAlarm 18 }

   dupsAlarmOutputOff OBJECT-TYPE
       SYNTAX     INTEGER{
                  on(1),
                  off(2)
       }
       ACCESS     read-only
       STATUS     mandatory
       DESCRIPTION
               "UPS output is turned off."
       ::= { dupsAlarm 19 }

   dupsAlarmSmartShutdown OBJECT-TYPE
       SYNTAX     INTEGER{
                  on(1),
                  off(2)
       }
       ACCESS     read-only
       STATUS     mandatory
       DESCRIPTION
               "Indicates whether the Smart Shutdown is in progress."
       ::= { dupsAlarm 20 }

   dupsAlarmEmergencyPowerOff OBJECT-TYPE
       SYNTAX     INTEGER{
                  on(1),
                  off(2)
       }
       ACCESS     read-only
       STATUS     mandatory
       DESCRIPTION
               "Representing the UPS is shutdown due to the
               Emergency Power Off button is pressed."
       ::= { dupsAlarm 21 }

   dupsAlarmUPSShutdown OBJECT-TYPE
       SYNTAX     INTEGER{
                  on(1),
                  off(2)
       }
       ACCESS     read-only
       STATUS     mandatory
       DESCRIPTION
               "The UPS has been shutdown including remote and
               fault shutdown."
       ::= { dupsAlarm 22 }

   dupsAlarmEPO OBJECT-TYPE
       SYNTAX     INTEGER{
                  on(1),
                  off(2)
       }
       ACCESS     read-only
       STATUS     mandatory
       DESCRIPTION
               "Representing the UPS is shutdown due to the
               Emergency Power Off button is pressed."
       ::= { dupsAlarm 23 }

   dupsAlarmOutVoltOverLimit OBJECT-TYPE
       SYNTAX     INTEGER{
                  on(1),
                  off(2)
       }
       ACCESS     read-only
       STATUS     mandatory
       DESCRIPTION
               "To indicate the output voltage is over limit."
       ::= { dupsAlarm 24 }

   dupsAlarmOutVoltUnderLimit OBJECT-TYPE
       SYNTAX     INTEGER{
                  on(1),
                  off(2)
       }
       ACCESS     read-only
       STATUS     mandatory
       DESCRIPTION
               "To indicate the output voltage is under limit."
       ::= { dupsAlarm 25 }

   dupsAlarmPowerModule OBJECT-TYPE
       SYNTAX     INTEGER{
                  on(1),
                  off(2)
       }
       ACCESS     read-only
       STATUS     mandatory
       DESCRIPTION
               "To indicate there is at least one alarm from power module."
       ::= { dupsAlarm 26 }

   dupsAlarmOutputBreaker OBJECT-TYPE
       SYNTAX     INTEGER{
                  open(1),
                  close(2)
       }
       ACCESS     read-only
       STATUS     mandatory
       DESCRIPTION
               "To indicate the output breaker is detected open or close."
       ::= { dupsAlarm 27 }

   dupsAlarmOutletBank1Breaker OBJECT-TYPE
       SYNTAX     INTEGER{
                  open(1),
                  close(2)
       }
       ACCESS     read-only
       STATUS     mandatory
       DESCRIPTION
               "To indicate the outlet bank-1 breaker is detected open or close."
       ::= { dupsAlarm 28 }

   dupsAlarmOutletBank2Breaker OBJECT-TYPE
       SYNTAX     INTEGER{
                  open(1),
                  close(2)
       }
       ACCESS     read-only
       STATUS     mandatory
       DESCRIPTION
               "To indicate the outlet bank-2 breaker is detected open or close."
       ::= { dupsAlarm 29 }

   dupsAlarmOutletBank3Breaker OBJECT-TYPE
       SYNTAX     INTEGER{
                  open(1),
                  close(2)
       }
       ACCESS     read-only
       STATUS     mandatory
       DESCRIPTION
               "To indicate the outlet bank-3 breaker is detected open or close."
       ::= { dupsAlarm 30 }

   dupsAlarmOutletBank4Breaker OBJECT-TYPE
       SYNTAX     INTEGER{
                  open(1),
                  close(2)
       }
       ACCESS     read-only
       STATUS     mandatory
       DESCRIPTION
               "To indicate the outlet bank-4 breaker is detected open or close."
       ::= { dupsAlarm 31 }

   dupsAlarmSummary OBJECT-TYPE
       SYNTAX     INTEGER{
                  none(1),
                  informational(2),
                  warning(3),
                  alarm(4)
       }
       ACCESS     read-only
       STATUS     mandatory
       DESCRIPTION
               "To indicate the alarm level for the UPS."
       ::= { dupsAlarm 32 }

   dupsAlarmRedundancyLoss OBJECT-TYPE
       SYNTAX     INTEGER{
                  on(1),
                  off(2)
       }
       ACCESS     read-only
       STATUS     mandatory
       DESCRIPTION
               "To indicate the capacity of redundancy lost in a modular UPS."
       ::= { dupsAlarm 33 }

   dupsAlarmPhaseAsynchronous OBJECT-TYPE
       SYNTAX     INTEGER{
                  asynchronous(1),
                  synchronous(2)
       }
       ACCESS     read-only
       STATUS     mandatory
       DESCRIPTION
               "To indicate the Phase is detected asynchronous or synchronous."
       ::= { dupsAlarm 34 }

   dupsAlarmRectifierAbnormal OBJECT-TYPE
       SYNTAX     INTEGER{
                  alarm(1),
                  normal(2)
       }
       ACCESS     read-only
       STATUS     mandatory
       DESCRIPTION
               "To indicate the Rectifier is detected alarm or normal."
       ::= { dupsAlarm 35 }

   dupsAlarmBypassBreakerOpen OBJECT-TYPE
       SYNTAX     INTEGER{
                  open(1),
                  close(2)
       }
       ACCESS     read-only
       STATUS     mandatory
       DESCRIPTION
               "To indicate the bypass breaker is detected open or close."
       ::= { dupsAlarm 36 }

   dupsAlarmMainInputBreakerOpen OBJECT-TYPE
       SYNTAX     INTEGER{
                  open(1),
                  close(2)
       }
       ACCESS     read-only
       STATUS     mandatory
       DESCRIPTION
               "To indicate the main input breaker is detected open or close."
       ::= { dupsAlarm 37 }

   dupsAlarmManualBypassBreaker OBJECT-TYPE
       SYNTAX     INTEGER{
                  open(1),
                  close(2)
       }
       ACCESS     read-only
       STATUS     mandatory
       DESCRIPTION
               "To indicate the manual bypass breaker is detected open or close."
       ::= { dupsAlarm 38 }

--
-- dups Power Module group
--

   dupsPMBypassInputAlarm OBJECT-TYPE
       SYNTAX     INTEGER{
                  on(1),
                  off(2)
       }
       ACCESS     read-only
       STATUS     mandatory
       DESCRIPTION
               "Indicates the bypass voltage/frequency is abnormal."
       ::= { dupsPowerModule 1 }

   dupsPMBypassPhaseAlarm OBJECT-TYPE
       SYNTAX     INTEGER{
                  on(1),
                  off(2)
       }
       ACCESS     read-only
       STATUS     mandatory
       DESCRIPTION
               "Indicates the bypass phase sequence is abnormal."
       ::= { dupsPowerModule 2 }

   dupsPMBypassSTSOverloadAlarm OBJECT-TYPE
       SYNTAX     INTEGER{
                  on(1),
                  off(2)
       }
       ACCESS     read-only
       STATUS     mandatory
       DESCRIPTION
               "Indicates the bypass STS overload."
       ::= { dupsPowerModule 3 }

   dupsPMBypassSTSOverTempAlarm OBJECT-TYPE
       SYNTAX     INTEGER{
                  on(1),
                  off(2)
       }
       ACCESS     read-only
       STATUS     mandatory
       DESCRIPTION
               "Indicates the bypass STS over temperature."
       ::= { dupsPowerModule 4 }

   dupsPMBypassSTSFailAlarm OBJECT-TYPE
       SYNTAX     INTEGER{
                  on(1),
                  off(2)
       }
       ACCESS     read-only
       STATUS     mandatory
       DESCRIPTION
               "Indicates the bypass STS fail."
       ::= { dupsPowerModule 5 }

   dupsPMTable OBJECT-TYPE
       SYNTAX     SEQUENCE OF DupsPMEntry
       ACCESS     not-accessible
       STATUS     mandatory
       DESCRIPTION
	       "A list of power module table entries."
       ::= { dupsPowerModule 6 }

   dupsPMEntry OBJECT-TYPE
       SYNTAX     DupsPMEntry
       ACCESS     not-accessible
       STATUS     mandatory
       DESCRIPTION
	       "An entry containing information applicable to a particular
		   power module."
       INDEX { dupsPMID }
       ::= { dupsPMTable 1 }

   DupsPMEntry ::= SEQUENCE {
       dupsPMID         INTEGER,
       dupsPMPFCTemp    INTEGER,
       dupsPMINVTemp    INTEGER,
       dupsPMINVTempR   INTEGER,
       dupsPMINVTempS   INTEGER,
       dupsPMINVTempT   INTEGER,
       dupsPMINVVolt1   INTEGER,
       dupsPMINVVolt2   INTEGER,
       dupsPMINVVolt3   INTEGER,
       dupsPMStsNotExist   INTEGER,
       dupsPMStsOff        INTEGER,
       dupsPMStsRepair     INTEGER,
       dupsPMStsFaultShutdown   INTEGER,
       dupsPMStsPFCFuseFail     INTEGER,
       dupsPMStsPFCOverTempWarning   INTEGER,
       dupsPMStsPFCOverTempShutdown  INTEGER,
       dupsPMStsPFCOverVoltWarning   INTEGER,
       dupsPMStsPFCOverVoltShutdown  INTEGER,
       dupsPMStsPFCUnderVoltWarning  INTEGER,
       dupsPMStsPFCUnderVoltShutdown INTEGER,
       dupsPMStsPFCGeneralFault      INTEGER,
       dupsPMStsPFCFanFail           INTEGER,
       dupsPMStsPFCCurrentLimit      INTEGER,
       dupsPMStsPFCOff               INTEGER,
       dupsPMStsPFCInnerCommFail     INTEGER,
       dupsPMStsPFCNotCalibrated     INTEGER,
       dupsPMStsINVFuseFail          INTEGER,
       dupsPMStsINVOverTempWarning   INTEGER,
       dupsPMStsINVOverTempShutdown  INTEGER,
       dupsPMStsINVFanFail           INTEGER,
       dupsPMStsINVShortCircuit      INTEGER,
       dupsPMStsINVSTSFail           INTEGER,
       dupsPMStsINVCircuitFail       INTEGER,
       dupsPMStsINVOverVolt          INTEGER,
       dupsPMStsINVOverload          INTEGER,
       dupsPMStsINVInnerCommFail     INTEGER,
       dupsPMStsINVEPO               INTEGER,
       dupsPMStsINVParallelCommFail  INTEGER,
       dupsPMStsINVParallelFail      INTEGER,
       dupsPMStsINVSTSOn             INTEGER,
       dupsPMStsINVNotCalibrated     INTEGER,
       dupsPMStsChargerFail          INTEGER,
       dupsPMSummaryStatus           INTEGER,
       dupsPMPFCTempR   INTEGER,
       dupsPMPFCTempS   INTEGER,
       dupsPMPFCTempT   INTEGER
   }

   dupsPMID OBJECT-TYPE
       SYNTAX     INTEGER
       ACCESS     not-accessible
       STATUS     mandatory
       DESCRIPTION
	       "The power module identifier."
       ::= { dupsPMEntry 1 }

   dupsPMPFCTemp OBJECT-TYPE
       SYNTAX     INTEGER
       UNITS      "1 Degree Celsius"
       ACCESS     read-only
       STATUS     mandatory
       DESCRIPTION
	       "The power module PFC temperature."
       ::= { dupsPMEntry 2 }

   dupsPMINVTemp OBJECT-TYPE
       SYNTAX     INTEGER
       UNITS      "1 Degree Celsius"
       ACCESS     read-only
       STATUS     mandatory
       DESCRIPTION
	       "The power module inverter temperature."
       ::= { dupsPMEntry 3 }

   dupsPMINVTempR OBJECT-TYPE
       SYNTAX     INTEGER
       UNITS      "1 Degree Celsius"
       ACCESS     read-only
       STATUS     mandatory
       DESCRIPTION
	       "The power module inverter-R temperature."
       ::= { dupsPMEntry 4 }

   dupsPMINVTempS OBJECT-TYPE
       SYNTAX     INTEGER
       UNITS      "1 Degree Celsius"
       ACCESS     read-only
       STATUS     mandatory
       DESCRIPTION
	       "The power module inverter-S temperature."
       ::= { dupsPMEntry 5 }

   dupsPMINVTempT OBJECT-TYPE
       SYNTAX     INTEGER
       UNITS      "1 Degree Celsius"
       ACCESS     read-only
       STATUS     mandatory
       DESCRIPTION
	       "The power module inverter-T temperature."
       ::= { dupsPMEntry 6 }

   dupsPMINVVolt1 OBJECT-TYPE
       SYNTAX     INTEGER
       UNITS      "0.1 Volt"
       ACCESS     read-only
       STATUS     mandatory
       DESCRIPTION
	       "The inverter line 1 voltage of the power module in 1/10 V."
       ::= { dupsPMEntry 7 }

   dupsPMINVVolt2 OBJECT-TYPE
       SYNTAX     INTEGER
       UNITS      "0.1 Volt"
       ACCESS     read-only
       STATUS     mandatory
       DESCRIPTION
	       "The inverter line 2 voltage of the power module in 1/10 V."
       ::= { dupsPMEntry 8 }

   dupsPMINVVolt3 OBJECT-TYPE
       SYNTAX     INTEGER
       UNITS      "0.1 Volt"
       ACCESS     read-only
       STATUS     mandatory
       DESCRIPTION
	       "The inverter line 3 voltage of the power module in 1/10 V."
       ::= { dupsPMEntry 9 }

   dupsPMStsNotExist OBJECT-TYPE
       SYNTAX     INTEGER{
                  notExist(1),
                  existed(2)
       }
       ACCESS     read-only
       STATUS     mandatory
       DESCRIPTION
               "Indicates the power module is existed or not?"
       ::= { dupsPMEntry 10 }

   dupsPMStsOff OBJECT-TYPE
       SYNTAX     INTEGER{
                  pmOff(1),
                  pmOn(2)
       }
       ACCESS     read-only
       STATUS     mandatory
       DESCRIPTION
               "Indicates the power module is on or off?"
       ::= { dupsPMEntry 11 }

   dupsPMStsRepair OBJECT-TYPE
       SYNTAX     INTEGER{
                  repair(1),
                  notRepair(2)
       }
       ACCESS     read-only
       STATUS     mandatory
       DESCRIPTION
               "Indicates the power module is in repair mode or not?"
       ::= { dupsPMEntry 12 }

   dupsPMStsFaultShutdown OBJECT-TYPE
       SYNTAX     INTEGER{
                  alarm(1),
                  normal(2)
       }
       ACCESS     read-only
       STATUS     mandatory
       DESCRIPTION
               "Indicates the power module status of fault shutdown."
       ::= { dupsPMEntry 13 }

   dupsPMStsPFCFuseFail OBJECT-TYPE
       SYNTAX     INTEGER{
                  alarm(1),
                  normal(2)
       }
       ACCESS     read-only
       STATUS     mandatory
       DESCRIPTION
               "Indicates the power module PFC fuse open or close?"
       ::= { dupsPMEntry 14 }

   dupsPMStsPFCOverTempWarning OBJECT-TYPE
       SYNTAX     INTEGER{
                  warning(1),
                  normal(2)
       }
       ACCESS     read-only
       STATUS     mandatory
       DESCRIPTION
               "Indicates the power module PFC over temperature warning."
       ::= { dupsPMEntry 15 }

   dupsPMStsPFCOverTempShutdown OBJECT-TYPE
       SYNTAX     INTEGER{
                  alarm(1),
                  normal(2)
       }
       ACCESS     read-only
       STATUS     mandatory
       DESCRIPTION
               "Indicates the power module PFC over temperature shutdown."
       ::= { dupsPMEntry 16 }

   dupsPMStsPFCOverVoltWarning OBJECT-TYPE
       SYNTAX     INTEGER{
                  warning(1),
                  normal(2)
       }
       ACCESS     read-only
       STATUS     mandatory
       DESCRIPTION
               "Indicates the power module PFC over voltage warning."
       ::= { dupsPMEntry 17 }

   dupsPMStsPFCOverVoltShutdown OBJECT-TYPE
       SYNTAX     INTEGER{
                  alarm(1),
                  normal(2)
       }
       ACCESS     read-only
       STATUS     mandatory
       DESCRIPTION
               "Indicates the power module PFC over voltage shutdown."
       ::= { dupsPMEntry 18 }

   dupsPMStsPFCUnderVoltWarning OBJECT-TYPE
       SYNTAX     INTEGER{
                  warning(1),
                  normal(2)
       }
       ACCESS     read-only
       STATUS     mandatory
       DESCRIPTION
               "Indicates the power module PFC under voltage warning."
       ::= { dupsPMEntry 19 }

   dupsPMStsPFCUnderVoltShutdown OBJECT-TYPE
       SYNTAX     INTEGER{
                  alarm(1),
                  normal(2)
       }
       ACCESS     read-only
       STATUS     mandatory
       DESCRIPTION
               "Indicates the power module PFC under voltage shutdown."
       ::= { dupsPMEntry 20 }

   dupsPMStsPFCGeneralFault OBJECT-TYPE
       SYNTAX     INTEGER{
                  alarm(1),
                  normal(2)
       }
       ACCESS     read-only
       STATUS     mandatory
       DESCRIPTION
               "Indicates the power module PFC genreal fault."
       ::= { dupsPMEntry 21 }

   dupsPMStsPFCFanFail OBJECT-TYPE
       SYNTAX     INTEGER{
                  alarm(1),
                  normal(2)
       }
       ACCESS     read-only
       STATUS     mandatory
       DESCRIPTION
               "Indicates the power module PFC fan fail."
       ::= { dupsPMEntry 22 }

   dupsPMStsPFCCurrentLimit OBJECT-TYPE
       SYNTAX     INTEGER{
                  alarm(1),
                  normal(2)
       }
       ACCESS     read-only
       STATUS     mandatory
       DESCRIPTION
               "Indicates the power module PFC output current limit."
       ::= { dupsPMEntry 23 }

   dupsPMStsPFCOff OBJECT-TYPE
       SYNTAX     INTEGER{
                  alarm(1),
                  normal(2)
       }
       ACCESS     read-only
       STATUS     mandatory
       DESCRIPTION
               "Indicates the power module PFC off."
       ::= { dupsPMEntry 24 }

   dupsPMStsPFCInnerCommFail OBJECT-TYPE
       SYNTAX     INTEGER{
                  alarm(1),
                  normal(2)
       }
       ACCESS     read-only
       STATUS     mandatory
       DESCRIPTION
               "Indicates the power module PFC inner communication fail."
       ::= { dupsPMEntry 25 }

   dupsPMStsPFCNotCalibrated OBJECT-TYPE
       SYNTAX     INTEGER{
                  alarm(1),
                  normal(2)
       }
       ACCESS     read-only
       STATUS     mandatory
       DESCRIPTION
               "Indicates the power module PFC is not calibrated."
       ::= { dupsPMEntry 26 }

   dupsPMStsINVFuseFail OBJECT-TYPE
       SYNTAX     INTEGER{
                  open(1),
                  close(2)
       }
       ACCESS     read-only
       STATUS     mandatory
       DESCRIPTION
               "Indicates the power module Inverter fuse open or close?"
       ::= { dupsPMEntry 27 }

   dupsPMStsINVOverTempWarning OBJECT-TYPE
       SYNTAX     INTEGER{
                  warning(1),
                  normal(2)
       }
       ACCESS     read-only
       STATUS     mandatory
       DESCRIPTION
               "Indicates the power module Inverter over temperature warning."
       ::= { dupsPMEntry 28 }

   dupsPMStsINVOverTempShutdown OBJECT-TYPE
       SYNTAX     INTEGER{
                  alarm(1),
                  normal(2)
       }
       ACCESS     read-only
       STATUS     mandatory
       DESCRIPTION
               "Indicates the power module Inverter over temperature shutdown."
       ::= { dupsPMEntry 29 }

   dupsPMStsINVFanFail OBJECT-TYPE
       SYNTAX     INTEGER{
                  alarm(1),
                  normal(2)
       }
       ACCESS     read-only
       STATUS     mandatory
       DESCRIPTION
               "Indicates the power module Inverter fan fail."
       ::= { dupsPMEntry 30 }

   dupsPMStsINVShortCircuit OBJECT-TYPE
       SYNTAX     INTEGER{
                  alarm(1),
                  normal(2)
       }
       ACCESS     read-only
       STATUS     mandatory
       DESCRIPTION
               "Indicates the power module Inverter short circuit."
       ::= { dupsPMEntry 31 }

   dupsPMStsINVSTSFail OBJECT-TYPE
       SYNTAX     INTEGER{
                  alarm(1),
                  normal(2)
       }
       ACCESS     read-only
       STATUS     mandatory
       DESCRIPTION
               "Indicates the power module Inverter STS fail."
       ::= { dupsPMEntry 32 }

   dupsPMStsINVCircuitFail OBJECT-TYPE
       SYNTAX     INTEGER{
                  alarm(1),
                  normal(2)
       }
       ACCESS     read-only
       STATUS     mandatory
       DESCRIPTION
               "Indicates the power module Inverter circuit fail shutdown."
       ::= { dupsPMEntry 33 }

   dupsPMStsINVOverVolt OBJECT-TYPE
       SYNTAX     INTEGER{
                  alarm(1),
                  normal(2)
       }
       ACCESS     read-only
       STATUS     mandatory
       DESCRIPTION
               "Indicates the power module Inverter over voltage shutdown."
       ::= { dupsPMEntry 34 }

   dupsPMStsINVOverload OBJECT-TYPE
       SYNTAX     INTEGER{
                  alarm(1),
                  normal(2)
       }
       ACCESS     read-only
       STATUS     mandatory
       DESCRIPTION
               "Indicates the power module Inverter overload."
       ::= { dupsPMEntry 35 }

   dupsPMStsINVInnerCommFail OBJECT-TYPE
       SYNTAX     INTEGER{
                  alarm(1),
                  normal(2)
       }
       ACCESS     read-only
       STATUS     mandatory
       DESCRIPTION
               "Indicates the power module Inverter inner communication fail."
       ::= { dupsPMEntry 36 }

   dupsPMStsINVEPO OBJECT-TYPE
       SYNTAX     INTEGER{
                  alarm(1),
                  normal(2)
       }
       ACCESS     read-only
       STATUS     mandatory
       DESCRIPTION
               "Indicates the power module Inverter EPO shutdown."
       ::= { dupsPMEntry 37 }

   dupsPMStsINVParallelCommFail OBJECT-TYPE
       SYNTAX     INTEGER{
                  alarm(1),
                  normal(2)
       }
       ACCESS     read-only
       STATUS     mandatory
       DESCRIPTION
               "Indicates the power module Inverter parallel communication fail."
       ::= { dupsPMEntry 38 }

   dupsPMStsINVParallelFail OBJECT-TYPE
       SYNTAX     INTEGER{
                  alarm(1),
                  normal(2)
       }
       ACCESS     read-only
       STATUS     mandatory
       DESCRIPTION
               "Indicates the power module Inverter parallel fail."
       ::= { dupsPMEntry 39 }

   dupsPMStsINVSTSOn OBJECT-TYPE
       SYNTAX     INTEGER{
                  on(1),
                  off(2)
       }
       ACCESS     read-only
       STATUS     mandatory
       DESCRIPTION
               "Indicates the status of power module Inverter state."
       ::= { dupsPMEntry 40 }

   dupsPMStsINVNotCalibrated OBJECT-TYPE
       SYNTAX     INTEGER{
                  alarm(1),
                  normal(2)
       }
       ACCESS     read-only
       STATUS     mandatory
       DESCRIPTION
               "Indicates the power module Inverter is not calibrated."
       ::= { dupsPMEntry 41 }

   dupsPMStsChargerFail OBJECT-TYPE
       SYNTAX     INTEGER{
                  alarm(1),
                  normal(2)
       }
       ACCESS     read-only
       STATUS     mandatory
       DESCRIPTION
               "Indicates the power module Charger fail."
       ::= { dupsPMEntry 42 }

   dupsPMSummaryStatus OBJECT-TYPE
       SYNTAX     INTEGER{
                  abnormal(1),
                  normal(2)
       }
       ACCESS     read-only
       STATUS     mandatory
       DESCRIPTION
	       "The power module summary status."
       ::= { dupsPMEntry 43 }

   dupsPMPFCTempR OBJECT-TYPE
       SYNTAX     INTEGER
       UNITS      "1 Degree Celsius"
       ACCESS     read-only
       STATUS     mandatory
       DESCRIPTION
	       "The power module pfc-R temperature."
       ::= { dupsPMEntry 44 }

   dupsPMPFCTempS OBJECT-TYPE
       SYNTAX     INTEGER
       UNITS      "1 Degree Celsius"
       ACCESS     read-only
       STATUS     mandatory
       DESCRIPTION
	       "The power module pfc-S temperature."
       ::= { dupsPMEntry 45 }

   dupsPMPFCTempT OBJECT-TYPE
       SYNTAX     INTEGER
       UNITS      "1 Degree Celsius"
       ACCESS     read-only
       STATUS     mandatory
       DESCRIPTION
	       "The power module pfc-T temperature."
       ::= { dupsPMEntry 46 }

--
-- dups Trap Args
--
   dupsDescription OBJECT-TYPE
       SYNTAX     DisplayString
       ACCESS     read-only
       STATUS     mandatory
       DESCRIPTION
               "This OID is used for traps to send with a string argument.
               A get of this OID will return an empty string."
       ::= { dupsTrapArgs 1 }

   dupsTimeTicks OBJECT-TYPE
       SYNTAX     TimeTicks
       ACCESS     read-only
       STATUS     mandatory
       DESCRIPTION
               "This OID is used for traps to send with a TimeTicks argument.
               A get of this OID will return 0."
       ::= { dupsTrapArgs 2 }

--
-- dups Parallel group
--
   dupsParallelRatingVA OBJECT-TYPE
       SYNTAX     INTEGER
       UNITS      "1 VA"
       ACCESS     read-only
       STATUS     mandatory
       DESCRIPTION
               "The summary rating VA to the parallel UPSs system."
       ::= { dupsParallel 1 }

   dupsParallelRatingPower OBJECT-TYPE
       SYNTAX     INTEGER
       UNITS      "1 Watt"
       ACCESS     read-only
       STATUS     mandatory
       DESCRIPTION
               "The summary rating power to the parallel UPSs system."
       ::= { dupsParallel 2 }

   dupsParallelInCurrent1 OBJECT-TYPE
       SYNTAX     INTEGER
       UNITS      "0.1 Amp"
       ACCESS     read-only
       STATUS     mandatory
       DESCRIPTION
               "The summary input line 1 current to the parallel UPSs system in 1/10 A.
               The value -1 indicates this UPS does not support this item."
       ::= { dupsParallel 3 }

   dupsParallelInCurrent2 OBJECT-TYPE
       SYNTAX     INTEGER
       UNITS      "0.1 Amp"
       ACCESS     read-only
       STATUS     mandatory
       DESCRIPTION
               "The summary input line 2 current to the parallel UPSs system in 1/!0 A.
               The value -1 indicates this UPS does not support this item."
       ::= { dupsParallel 4 }

   dupsParallelInCurrent3 OBJECT-TYPE
       SYNTAX     INTEGER
       UNITS      "0.1 Amp"
       ACCESS     read-only
       STATUS     mandatory
       DESCRIPTION
               "The summary input line 3 current to the parallel UPSs system in 1/!0 A.
               The value -1 indicates this UPS does not support this item."
       ::= { dupsParallel 5 }

   dupsParallelOutCurrent1 OBJECT-TYPE
       SYNTAX     INTEGER
       UNITS      "0.1 Amp"
       ACCESS     read-only
       STATUS     mandatory
       DESCRIPTION
               "The summary output line 1 current to the parallel UPSs system in 1/10 A.
               The value -1 indicates this UPS does not support this item."
       ::= { dupsParallel 6 }

   dupsParallelOutCurrent2 OBJECT-TYPE
       SYNTAX     INTEGER
       UNITS      "0.1 Amp"
       ACCESS     read-only
       STATUS     mandatory
       DESCRIPTION
               "The summary output line 2 current to the parallel UPSs system in 1/10 A.
               The value -1 indicates this UPS does not support this item."
       ::= { dupsParallel 7 }

   dupsParallelOutCurrent3 OBJECT-TYPE
       SYNTAX     INTEGER
       UNITS      "0.1 Amp"
       ACCESS     read-only
       STATUS     mandatory
       DESCRIPTION
               "The summary output line 3 current to the parallel UPSs system in 1/10 A.
               The value -1 indicates this UPS does not support this item."
       ::= { dupsParallel 8 }

   dupsParallelOutPower1 OBJECT-TYPE
       SYNTAX     INTEGER
       UNITS      "1 Watt"
       ACCESS     read-only
       STATUS     mandatory
       DESCRIPTION
               "The summary output line 1 power to the parallel UPSs system.
               The value -1 indicates this UPS does not support this item."
       ::= { dupsParallel 9 }

   dupsParallelOutPower2 OBJECT-TYPE
       SYNTAX     INTEGER
       UNITS      "1 Watt"
       ACCESS     read-only
       STATUS     mandatory
       DESCRIPTION
               "The summary output line 2 power to the parallel UPSs system.
               The value -1 indicates this UPS does not support this item."
       ::= { dupsParallel 10 }

   dupsParallelOutPower3 OBJECT-TYPE
       SYNTAX     INTEGER
       UNITS      "1 Watt"
       ACCESS     read-only
       STATUS     mandatory
       DESCRIPTION
               "The summary output line 3 power to the parallel UPSs system.
               The value -1 indicates this UPS does not support this item."
       ::= { dupsParallel 11 }

   dupsParallelInEnergy1 OBJECT-TYPE
       SYNTAX     INTEGER
       UNITS      "1 kWh"
       ACCESS     read-only
       STATUS     mandatory
       DESCRIPTION
               "The summary input line 1 energy to the parallel UPSs system.
               The value -1 indicates this UPS does not support this item."
       ::= { dupsParallel 12 }

   dupsParallelInEnergy2 OBJECT-TYPE
       SYNTAX     INTEGER
       UNITS      "1 kWh"
       ACCESS     read-only
       STATUS     mandatory
       DESCRIPTION
               "The summary input line 2 energy to the parallel UPSs system.
               The value -1 indicates this UPS does not support this item."
       ::= { dupsParallel 13 }

   dupsParallelInEnergy3 OBJECT-TYPE
       SYNTAX     INTEGER
       UNITS      "1 kWh"
       ACCESS     read-only
       STATUS     mandatory
       DESCRIPTION
               "The summary input line 3 energy to the parallel UPSs system.
               The value -1 indicates this UPS does not support this item."
       ::= { dupsParallel 14 }

   dupsParallelInEnergyTotal OBJECT-TYPE
       SYNTAX     INTEGER
       UNITS      "1 kWh"
       ACCESS     read-only
       STATUS     mandatory
       DESCRIPTION
               "The summary total input energy to the parallel UPSs system.
               The value -1 indicates this UPS does not support this item."
       ::= { dupsParallel 15 }

   dupsParallelOutEnergy1 OBJECT-TYPE
       SYNTAX     INTEGER
       UNITS      "1 kWh"
       ACCESS     read-only
       STATUS     mandatory
       DESCRIPTION
               "The summary output line 1 energy to the parallel UPSs system.
               The value -1 indicates this UPS does not support this item."
       ::= { dupsParallel 16 }

   dupsParallelOutEnergy2 OBJECT-TYPE
       SYNTAX     INTEGER
       UNITS      "1 kWh"
       ACCESS     read-only
       STATUS     mandatory
       DESCRIPTION
               "The summary output line 2 energy to the parallel UPSs system.
               The value -1 indicates this UPS does not support this item."
       ::= { dupsParallel 17 }

   dupsParallelOutEnergy3 OBJECT-TYPE
       SYNTAX     INTEGER
       UNITS      "1 kWh"
       ACCESS     read-only
       STATUS     mandatory
       DESCRIPTION
               "The summary output line 3 energy to the parallel UPSs system.
               The value -1 indicates this UPS does not support this item."
       ::= { dupsParallel 18 }

   dupsParallelOutEnergyTotal OBJECT-TYPE
       SYNTAX     INTEGER
       UNITS      "1 kWh"
       ACCESS     read-only
       STATUS     mandatory
       DESCRIPTION
               "The summary total output energy to the parallel UPSs system.
               The value -1 indicates this UPS does not support this item."
       ::= { dupsParallel 19 }

--
-- dups Integrated group
--
   dupsIntegratedParallel OBJECT-TYPE
       SYNTAX     INTEGER{
                  parallel(1),
                  noParallel(2)
       }
       ACCESS     read-only
       STATUS     mandatory
       DESCRIPTION
               "Multiple frame with the same group present."
       ::= { dupsIntegrated 1 }

   dupsIntegratedDryInput1 OBJECT-TYPE
       SYNTAX     INTEGER{
                  active(1),
                  inactive(2)
       }
       ACCESS     read-only
       STATUS     mandatory
       DESCRIPTION
               "Dry1 Input state."
       ::= { dupsIntegrated 2 }

   dupsIntegratedDryInput2 OBJECT-TYPE
       SYNTAX     INTEGER{
                  active(1),
                  inactive(2)
       }
       ACCESS     read-only
       STATUS     mandatory
       DESCRIPTION
               "Dry2 Input state."
       ::= { dupsIntegrated 3 }

   dupsIntegratedDryInput3 OBJECT-TYPE
       SYNTAX     INTEGER{
                  active(1),
                  inactive(2)
       }
       ACCESS     read-only
       STATUS     mandatory
       DESCRIPTION
               "Dry3 Input state."
       ::= { dupsIntegrated 4 }

   dupsIntegratedDryInput4 OBJECT-TYPE
       SYNTAX     INTEGER{
                  active(1),
                  inactive(2)
       }
       ACCESS     read-only
       STATUS     mandatory
       DESCRIPTION
               "Dry4 Input state."
       ::= { dupsIntegrated 5 }


--
-- dups Trap group
--

   dupsCommunicationLost TRAP-TYPE
       ENTERPRISE dupsTraps
       VARIABLES { dupsTimeTicks, dupsDescription }
       DESCRIPTION
       "SEVER: Communication with the UPS failed."
       ::= 1

   dupsCommunicationEstablished TRAP-TYPE
       ENTERPRISE dupsTraps
       VARIABLES { dupsTimeTicks, dupsDescription }
       DESCRIPTION
       "INFORMATION: Communication with the UPS reestablished."
       ::= 2

   dupsPowerFail TRAP-TYPE
       ENTERPRISE dupsTraps
       VARIABLES { dupsTimeTicks, dupsDescription }
       DESCRIPTION
       "WARNING: Power failed! The UPS is operating on battery power."
       ::= 3

   dupsPowerRestored TRAP-TYPE
       ENTERPRISE dupsTraps
       VARIABLES { dupsTimeTicks, dupsDescription }
       DESCRIPTION
       "INFORMATION: Power restored! The utility power restored."
       ::= 4

   dupsLowBattery TRAP-TYPE
       ENTERPRISE dupsTraps
       VARIABLES { dupsTimeTicks, dupsDescription }
       DESCRIPTION
       "SEVER: The UPS batteries are low and will soon be exhausted."
       ::= 5

   dupsReturnFromLowBattery TRAP-TYPE
       ENTERPRISE dupsTraps
       VARIABLES { dupsTimeTicks, dupsDescription }
       DESCRIPTION
       "INFORMATION: The UPS has returned from a low battery condition."
       ::= 6

   dupsLoadOnBypass TRAP-TYPE
       ENTERPRISE dupsTraps
       VARIABLES { dupsTimeTicks, dupsDescription }
       DESCRIPTION
       "SEVER: The UPS loads on bypass."
       ::= 7

   dupsNoLongerLoadOnBypass TRAP-TYPE
       ENTERPRISE dupsTraps
       VARIABLES { dupsTimeTicks, dupsDescription }
       DESCRIPTION
       "INFORMATION: The UPS is not on bypass mode."
       ::= 8

   dupsUPSFault TRAP-TYPE
       ENTERPRISE dupsTraps
       VARIABLES { dupsTimeTicks, dupsDescription }
       DESCRIPTION
       "SEVER: A general fault caused in the UPS."
       ::= 9

   dupsReturnFromUPSFault TRAP-TYPE
       ENTERPRISE dupsTraps
       VARIABLES { dupsTimeTicks, dupsDescription }
       DESCRIPTION
       "INFORMATION: The UPS is returned from general fault."
       ::= 10

   dupsBatteryGroundFault TRAP-TYPE
       ENTERPRISE dupsTraps
       VARIABLES { dupsTimeTicks, dupsDescription }
       DESCRIPTION
       "SEVER: The UPS battery ground fault."
       ::= 11

   dupsNoLongerBatteryFault TRAP-TYPE
       ENTERPRISE dupsTraps
       VARIABLES { dupsTimeTicks, dupsDescription }
       DESCRIPTION
       "INFORMATION: The UPS recovered from battery ground fault."
       ::= 12

   dupsTestInProgress TRAP-TYPE
       ENTERPRISE dupsTraps
       VARIABLES { dupsTimeTicks, dupsDescription }
       DESCRIPTION
       "INFORMATION: The UPS test in progress."
       ::= 13

   dupsBatteryTestFail TRAP-TYPE
       ENTERPRISE dupsTraps
       VARIABLES { dupsTimeTicks, dupsDescription }
       DESCRIPTION
       "SEVER: The UPS test fail."
       ::= 14

   dupsFuseFailure TRAP-TYPE
       ENTERPRISE dupsTraps
       VARIABLES { dupsTimeTicks, dupsDescription }
       DESCRIPTION
       "SEVER: The UPS fuse failed."
       ::= 15

   dupsFuseRecovered TRAP-TYPE
       ENTERPRISE dupsTraps
       VARIABLES { dupsTimeTicks, dupsDescription }
       DESCRIPTION
       "INFORMATION: The UPS fuse recovered."
       ::= 16

   dupsOutputOverload TRAP-TYPE
       ENTERPRISE dupsTraps
       VARIABLES { dupsTimeTicks, dupsDescription }
       DESCRIPTION
       "SEVER: The UPS overload!."
       ::= 17

   dupsNoLongerOverload TRAP-TYPE
       ENTERPRISE dupsTraps
       VARIABLES { dupsTimeTicks, dupsDescription }
       DESCRIPTION
       "INFORMATION: Recovered from UPS overload."
       ::= 18

   dupsInverterAbnormal TRAP-TYPE
       ENTERPRISE dupsTraps
       VARIABLES { dupsTimeTicks, dupsDescription }
       DESCRIPTION
       "SEVER: The UPS inverter abnormal."
       ::= 19

   dupsInverterRecovered TRAP-TYPE
       ENTERPRISE dupsTraps
       VARIABLES { dupsTimeTicks, dupsDescription }
       DESCRIPTION
       "INFORMATION: Recovered from UPS inverter abnormal."
       ::= 20

   dupsSmartShutdownInit TRAP-TYPE
       ENTERPRISE dupsTraps
       VARIABLES { dupsTimeTicks, dupsDescription }
       DESCRIPTION
       "SEVER: Smart Shutdown is initiated."
       ::= 21

   dupsCancelShutdown TRAP-TYPE
       ENTERPRISE dupsTraps
       VARIABLES { dupsTimeTicks, dupsDescription }
       DESCRIPTION
       "INFORMATION: Cancel UPS Shutdown."
       ::= 22

   dupsTestCompleted TRAP-TYPE
       ENTERPRISE dupsTraps
       VARIABLES { dupsTimeTicks, dupsDescription }
       DESCRIPTION
       "INFORMATION: This trap is sent upon completion of a UPS diagnostic test."
       ::= 23

   dupsEPOON TRAP-TYPE
       ENTERPRISE dupsTraps
       VARIABLES { dupsTimeTicks, dupsDescription }
       DESCRIPTION
       "INFORMATION: This trap is sent when emergency power off is on."
       ::= 24

   dupsEPOOFF TRAP-TYPE
       ENTERPRISE dupsTraps
       VARIABLES { dupsTimeTicks, dupsDescription }
       DESCRIPTION
       "INFORMATION: This trap is sent when UPS recover from emergency power off."
       ::= 25

   dupsTemperatureAlarm TRAP-TYPE
       ENTERPRISE dupsTraps
       VARIABLES { dupsTimeTicks, dupsDescription }
       DESCRIPTION
       "SEVER: This trap is sent when the UPS temperature out of range."
       ::= 26

   dupsTemperatureNormal TRAP-TYPE
       ENTERPRISE dupsTraps
       VARIABLES { dupsTimeTicks, dupsDescription }
       DESCRIPTION
       "INFORMATION: This trap is sent when UPS temperature back to normal."
       ::= 27

   dupsBattReplace TRAP-TYPE
       ENTERPRISE dupsTraps
       VARIABLES { dupsTimeTicks, dupsDescription }
       DESCRIPTION
       "WARNING: The battery needs to be replaced."
       ::= 28

   dupsReturnFromBattReplace TRAP-TYPE
       ENTERPRISE dupsTraps
       VARIABLES { dupsTimeTicks, dupsDescription }
       DESCRIPTION
       "INFORMATION: The UPS recovered from battery replacement."
       ::= 29

   dupsOutputOff TRAP-TYPE
       ENTERPRISE dupsTraps
       VARIABLES { dupsTimeTicks, dupsDescription }
       DESCRIPTION
       "SEVER: Indicate the UPS output is turned off."
       ::= 30

   dupsReturnFromOutputOff TRAP-TYPE
       ENTERPRISE dupsTraps
       VARIABLES { dupsTimeTicks, dupsDescription }
       DESCRIPTION
       "INFORMATION: The UPS recovered from output off."
       ::= 31

   dupsShutdown TRAP-TYPE
       ENTERPRISE dupsTraps
       VARIABLES { dupsTimeTicks, dupsDescription }
       DESCRIPTION
       "SEVER: The UPS has been shutdown including remote and fault shutdown."
       ::= 32

   dupsReturnFromShutdown TRAP-TYPE
       ENTERPRISE dupsTraps
       VARIABLES { dupsTimeTicks, dupsDescription }
       DESCRIPTION
       "INFORMATION: The UPS recovered from shutdown."
       ::= 33

   dupsChargerFail TRAP-TYPE
       ENTERPRISE dupsTraps
       VARIABLES { dupsTimeTicks, dupsDescription }
       DESCRIPTION
       "SEVER: An incorrected problem has been detected within the UPS charger subsystem."
       ::= 34

   dupsReturnFromChargerFail TRAP-TYPE
       ENTERPRISE dupsTraps
       VARIABLES { dupsTimeTicks, dupsDescription }
       DESCRIPTION
       "INFORMATION: The UPS recovered from charger fail."
       ::= 35

   dupsOnStandby TRAP-TYPE
       ENTERPRISE dupsTraps
       VARIABLES { dupsTimeTicks, dupsDescription }
       DESCRIPTION
       "SEVER: The UPS system is in the standby state."
       ::= 36

   dupsReturnFromStandby TRAP-TYPE
       ENTERPRISE dupsTraps
       VARIABLES { dupsTimeTicks, dupsDescription }
       DESCRIPTION
       "INFORMATION: The UPS no longer on standby mode."
       ::= 37

   dupsFanFail TRAP-TYPE
       ENTERPRISE dupsTraps
       VARIABLES { dupsTimeTicks, dupsDescription }
       DESCRIPTION
       "SEVER: The failure of one or more fans in the UPS has been detected."
       ::= 38

   dupsReturnFromFanFail TRAP-TYPE
       ENTERPRISE dupsTraps
       VARIABLES { dupsTimeTicks, dupsDescription }
       DESCRIPTION
       "INFORMATION: The UPS recover from fan fail."
       ::= 39

   dupsOnEconomic TRAP-TYPE
       ENTERPRISE dupsTraps
       VARIABLES { dupsTimeTicks, dupsDescription }
       DESCRIPTION
       "INFORMATION: The UPS is working in the economic mode (act like an off-line UPS)."
       ::= 40

   dupsReturnFromEconomic TRAP-TYPE
       ENTERPRISE dupsTraps
       VARIABLES { dupsTimeTicks, dupsDescription }
       DESCRIPTION
       "INFORMATION: The UPS no longer on economic mode."
       ::= 41

   dupsPowerModuleFail TRAP-TYPE
       ENTERPRISE dupsTraps
       VARIABLES { dupsTimeTicks, dupsDescription }
       DESCRIPTION
       "INFORMATION: One of the power modules is detected failed."
       ::= 42

   dupsReturnFromPowerModuleFail TRAP-TYPE
       ENTERPRISE dupsTraps
       VARIABLES { dupsTimeTicks, dupsDescription }
       DESCRIPTION
       "INFORMATION: The power module is back to normal."
       ::= 43

   dupsOutputBreakerOff TRAP-TYPE
       ENTERPRISE dupsTraps
       VARIABLES { dupsTimeTicks, dupsDescription }
       DESCRIPTION
       "INFORMATION: The output breaker is detected off."
       ::= 44

   dupsReturnFromOutputBreakerOff TRAP-TYPE
       ENTERPRISE dupsTraps
       VARIABLES { dupsTimeTicks, dupsDescription }
       DESCRIPTION
       "INFORMATION: The output breaker is back to on."
       ::= 45

   dupsBatteryDepleted TRAP-TYPE
       ENTERPRISE dupsTraps
       VARIABLES { dupsTimeTicks, dupsDescription }
       DESCRIPTION
       "SEVER: The UPS batteries are depleted and will soon be exhausted."
       ::= 46

   dupsReturnFromBatteryDepleted TRAP-TYPE
       ENTERPRISE dupsTraps
       VARIABLES { dupsTimeTicks, dupsDescription }
       DESCRIPTION
       "INFORMATION: The UPS has returned from a battery depleted condition."
       ::= 47

   dupsLoadOnManualBypass TRAP-TYPE
       ENTERPRISE dupsTraps
       VARIABLES { dupsTimeTicks, dupsDescription }
       DESCRIPTION
       "SEVER: The UPS loads on manual bypass."
       ::= 48

   dupsNoLongerLoadOnManualBypass TRAP-TYPE
       ENTERPRISE dupsTraps
       VARIABLES { dupsTimeTicks, dupsDescription }
       DESCRIPTION
       "INFORMATION: The UPS is not on manual bypass mode."
       ::= 49

   dupsBatteryBreakerOpen TRAP-TYPE
       ENTERPRISE dupsTraps
       VARIABLES { dupsTimeTicks, dupsDescription }
       DESCRIPTION
       "SEVER: The battery breaker is detected open."
       ::= 50

   dupsReturnFromBatteryBreakerOpen TRAP-TYPE
       ENTERPRISE dupsTraps
       VARIABLES { dupsTimeTicks, dupsDescription }
       DESCRIPTION
       "INFORMATION: The battery breaker is returned from open."
       ::= 51

   dupsOutletBankOn TRAP-TYPE
       ENTERPRISE dupsTraps
       VARIABLES { dupsTimeTicks, dupsDescription }
       DESCRIPTION
       "SEVER: The outlet bank was turned on."
       ::= 52

   dupsOutletBankOff TRAP-TYPE
       ENTERPRISE dupsTraps
       VARIABLES { dupsTimeTicks, dupsDescription }
       DESCRIPTION
       "INFORMATION: The outlet bank was turned off."
       ::= 53

   dupsRedundancyLoss TRAP-TYPE
       ENTERPRISE dupsTraps
       VARIABLES { dupsTimeTicks, dupsDescription }
       DESCRIPTION
       "WARNING: The redundancy capacity lost in a modular UPS."
       ::= 54

   dupsReturnFromRedundancyLoss TRAP-TYPE
       ENTERPRISE dupsTraps
       VARIABLES { dupsTimeTicks, dupsDescription }
       DESCRIPTION
       "INFORMATION: The redundancy capacity recoverd in a modular UPS."
       ::= 55

   dupsPhaseAsynchronous TRAP-TYPE
       ENTERPRISE dupsTraps
       VARIABLES { dupsTimeTicks, dupsDescription }
       DESCRIPTION
       "SEVER: The phase is detected asynchronous."
       ::= 56

   dupsReturnFromPhaseAsynchronous TRAP-TYPE
       ENTERPRISE dupsTraps
       VARIABLES { dupsTimeTicks, dupsDescription }
       DESCRIPTION
       "INFORMATION: The phase is returned from asynchronous."
       ::= 57

   dupsRectifierAbnormal TRAP-TYPE
       ENTERPRISE dupsTraps
       VARIABLES { dupsTimeTicks, dupsDescription }
       DESCRIPTION
       "SEVER: The rectifier is detected abnormal."
       ::= 58

   dupsReturnFromRectifierAbnormal TRAP-TYPE
       ENTERPRISE dupsTraps
       VARIABLES { dupsTimeTicks, dupsDescription }
       DESCRIPTION
       "INFORMATION: The rectifier is returned from abnormal."
       ::= 59

   dupsBypassBreakerOpen TRAP-TYPE
       ENTERPRISE dupsTraps
       VARIABLES { dupsTimeTicks, dupsDescription }
       DESCRIPTION
       "SEVER: The bypass breaker is detected open."
       ::= 60

   dupsReturnFromBypassBreakerOpen TRAP-TYPE
       ENTERPRISE dupsTraps
       VARIABLES { dupsTimeTicks, dupsDescription }
       DESCRIPTION
       "INFORMATION: The bypass breaker is returned from open."
       ::= 61

   dupsMainInputBreakerOpen TRAP-TYPE
       ENTERPRISE dupsTraps
       VARIABLES { dupsTimeTicks, dupsDescription }
       DESCRIPTION
       "SEVER: The main inputs breaker is detected open."
       ::= 62

   dupsReturnFromMainInputBreakerOpen TRAP-TYPE
       ENTERPRISE dupsTraps
       VARIABLES { dupsTimeTicks, dupsDescription }
       DESCRIPTION
       "INFORMATION: The main input breaker is returned from open."
       ::= 63


   dupsManualBypassBreakerOpen TRAP-TYPE
       ENTERPRISE dupsTraps
       VARIABLES { dupsTimeTicks, dupsDescription }
       DESCRIPTION
       "SEVER: The manual bypass breaker is detected open."
       ::= 64

   dupsReturnFromManualBypassBreakerOpen TRAP-TYPE
       ENTERPRISE dupsTraps
       VARIABLES { dupsTimeTicks, dupsDescription }
       DESCRIPTION
       "INFORMATION: The manual bypass breaker is returned from open."
       ::= 65

END
