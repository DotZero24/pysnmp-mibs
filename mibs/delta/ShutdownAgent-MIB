--Delta-MIB { iso(1) org(3) dod(6) internet(1) private(4) enterprises(1) delta(2254) ups(2) shutdownagent(200) }


ShutdownAgent-MIB DEFINITIONS ::= BEGIN


IMPORTS
	enterprises, IpAddress
		FROM RFC1155-SMI
	DisplayString
		FROM RFC1213-MIB
	OBJECT-TYPE
		FROM RFC-1212
	TRAP-TYPE
		FROM RFC-1215;


delta				OBJECT IDENTIFIER ::=  { enterprises 2254 }

ups					OBJECT IDENTIFIER ::=  { delta 2 }

shutdownagent		OBJECT IDENTIFIER ::=  { ups 200 }

dagentMonitor		OBJECT IDENTIFIER ::=  { shutdownagent 1 }
dagentConfigure		OBJECT IDENTIFIER ::=  { shutdownagent 2 }
dagentControl		OBJECT IDENTIFIER ::=  { shutdownagent 3 }

--
-- shutdown_agent Monitoring group
--

   dagentOSVersion OBJECT-TYPE
       SYNTAX     DisplayString (SIZE(0..128))
       ACCESS     read-only
       STATUS     mandatory
       DESCRIPTION
				"The operating system version."
       ::= { dagentMonitor 1 }

   dagentSoftwareVersion OBJECT-TYPE
       SYNTAX     DisplayString (SIZE(0..15))
       ACCESS     read-only
       STATUS     mandatory
       DESCRIPTION
				"The Shutdown Agent software version."
       ::= { dagentMonitor 2 }

   dagentIsOSCountdown OBJECT-TYPE
       SYNTAX     INTEGER {
           yes(1),
           no(2)
       }
       ACCESS     read-only
       STATUS     mandatory
       DESCRIPTION
				"Determine if the OS is counting down or not."
       ::= { dagentMonitor 3 }

   dagentOSCountdown OBJECT-TYPE
       SYNTAX     INTEGER
       UNITS      "second"
       ACCESS     read-only
       STATUS     mandatory
       DESCRIPTION
				"Reply the OS delay countdown time in second."
       ::= { dagentMonitor 4 }

   dagentShutdownReason OBJECT-TYPE
       SYNTAX     INTEGER {
           none(1),
           power_fail(2),
           battery_low(3),
           overload(4),
           on_bypass(5),
           smart_shutdown(6)
       }
       ACCESS     read-only
       STATUS     mandatory
       DESCRIPTION
				"The triggered event to shutdown the OS."
       ::= { dagentMonitor 5 }

   dagentHostName OBJECT-TYPE
       SYNTAX     DisplayString (SIZE(0..64))
       ACCESS     read-only
       STATUS     mandatory
       DESCRIPTION
				"The host name of this host."
       ::= { dagentMonitor 6 }

--
-- shutdown_agent Configure group
--

   dagentSetShutdownType OBJECT-TYPE
       SYNTAX     INTEGER {
           shutdown(1),
           power_off(2),
           hibernate(3)
       }
       ACCESS     read-write
       STATUS     mandatory
       DESCRIPTION
				"Determine the OS shutdown type."
       ::= { dagentConfigure 1 }

   dagentSetEnablePowerFail OBJECT-TYPE
       SYNTAX     INTEGER {
           enable(1),
           disable(2)
       }
       ACCESS     read-write
       STATUS     mandatory
       DESCRIPTION
				"Enable or disable power fail shutdown option."
       ::= { dagentConfigure 2 }

   dagentSetOSDelayPowerFail OBJECT-TYPE
       SYNTAX     INTEGER
       UNITS      "second"
       ACCESS     read-write
       STATUS     mandatory
       DESCRIPTION
				"Set the OS shutdown delay time for the power fail event."
       ::= { dagentConfigure 3 }

   dagentSetEnableBatteryLow OBJECT-TYPE
       SYNTAX     INTEGER {
           enable(1),
           disable(2)
       }
       ACCESS     read-write
       STATUS     mandatory
       DESCRIPTION
				"Enable or disable battery low shutdown option."
       ::= { dagentConfigure 4 }

   dagentSetOSDelayBatteryLow OBJECT-TYPE
       SYNTAX     INTEGER
       UNITS      "second"
       ACCESS     read-write
       STATUS     mandatory
       DESCRIPTION
				"Set the OS shutdown delay time for the battery low event."
       ::= { dagentConfigure 5 }

   dagentSetEnableOverload OBJECT-TYPE
       SYNTAX     INTEGER {
           enable(1),
           disable(2)
       }
       ACCESS     read-write
       STATUS     mandatory
       DESCRIPTION
				"Enable or disable overload shutdown option."
       ::= { dagentConfigure 6 }

   dagentSetOSDelayOverload OBJECT-TYPE
       SYNTAX     INTEGER
       UNITS      "second"
       ACCESS     read-write
       STATUS     mandatory
       DESCRIPTION
				"Set the OS shutdown delay time for the overload event."
       ::= { dagentConfigure 7 }

   dagentSetEnableBypass OBJECT-TYPE
       SYNTAX     INTEGER {
           enable(1),
           disable(2)
       }
       ACCESS     read-write
       STATUS     mandatory
       DESCRIPTION
				"Enable or disable bypass shutdown option."
       ::= { dagentConfigure 8 }

   dagentSetOSDelayBypass OBJECT-TYPE
       SYNTAX     INTEGER
       UNITS      "second"
       ACCESS     read-write
       STATUS     mandatory
       DESCRIPTION
				"Set the OS shutdown delay time for the bypass event."
       ::= { dagentConfigure 9 }

   dagentSetEnableSmartShutdown OBJECT-TYPE
       SYNTAX     INTEGER {
           enable(1),
           disable(2)
       }
       ACCESS     read-write
       STATUS     mandatory
       DESCRIPTION
				"Enable or disable smart shutdown option."
       ::= { dagentConfigure 10 }

   dagentSetOSDelaySmartShutdown OBJECT-TYPE
       SYNTAX     INTEGER
       UNITS      "second"
       ACCESS     read-write
       STATUS     mandatory
       DESCRIPTION
				"Set the OS shutdown delay time for the smart shutdown event."
       ::= { dagentConfigure 11 }

--
-- shutdown_agent Control group
--

   dagentCancelShutdown OBJECT-TYPE
       SYNTAX     INTEGER {
           cancel(1),
           resume(2)
       }
       ACCESS     read-write
       STATUS     mandatory
       DESCRIPTION
               "If the OS countdown is in progress and the value is 1 then the
               software pauses the shutdown countdown action. If the value is 2
               then the software resume the shutdown countdown action again."
       ::= { dagentControl 1 }

END
