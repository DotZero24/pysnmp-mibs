ACOS-SYSTEM-CPU-OPER-MIB DEFINITIONS ::= BEGIN
	IMPORTS
		DisplayString, PhysAddress
		FROM SNMPv2-TC
	InetAddressType
		FROM INET-ADDRESS-MIB
	acosRootOper
		FROM A10-AX-MIB
	MODULE-IDENTITY, OBJECT-TYPE, Counter32, Integer32, Counter64, OBJECT-IDENTITY, NOTIFICATION-TYPE
		FROM SNMPv2-SMI;
		acosSystemCpu MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "SystemCpu OID for ACOS"
				::=  {  acosRootOper 40  }

acosSystemCpuVserverDataCpu         OBJECT IDENTIFIER ::= { acosSystemCpu 4 }

systemCpuVserverDataCpuVserverCpuUsageTable OBJECT-TYPE
		SYNTAX SEQUENCE OF SystemCpuVserverDataCpuVserverCpuUsageEntry
		MAX-ACCESS not-accessible
		STATUS current
		::={ acosSystemCpuVserverDataCpu 1 }


	systemCpuVserverDataCpuVserverCpuUsageEntry OBJECT-TYPE
		SYNTAX SystemCpuVserverDataCpuVserverCpuUsageEntry
		MAX-ACCESS not-accessible
		STATUS current
		INDEX {
			vserverName,
			cpuId
		}
		::={ systemCpuVserverDataCpuVserverCpuUsageTable 1 }


	SystemCpuVserverDataCpuVserverCpuUsageEntry ::=
		SEQUENCE {
			vserverName DisplayString,
			cpuId INTEGER,
			dcpuStr DisplayString,
			oneSec CounterBasedGauge64,
			fiveSec CounterBasedGauge64,
			tenSec CounterBasedGauge64,
			thirtySec CounterBasedGauge64,
			sixtySec CounterBasedGauge64
		}

		vserverName OBJECT-TYPE
		SYNTAX  DisplayString
		MAX-ACCESS read-only
		STATUS current
		DESCRIPTION  ""
		::={ systemCpuVserverDataCpuVserverCpuUsageEntry 1 }

		cpuId OBJECT-TYPE
		SYNTAX  INTEGER
		MAX-ACCESS read-only
		STATUS current
		DESCRIPTION  ""
		::={ systemCpuVserverDataCpuVserverCpuUsageEntry 2 }

		dcpuStr OBJECT-TYPE
		SYNTAX  DisplayString
		MAX-ACCESS read-only
		STATUS current
		DESCRIPTION  ""
		::={ systemCpuVserverDataCpuVserverCpuUsageEntry 3 }

		oneSec OBJECT-TYPE
		SYNTAX  CounterBasedGauge64
		MAX-ACCESS read-only
		STATUS current
		DESCRIPTION  ""
		::={ systemCpuVserverDataCpuVserverCpuUsageEntry 4 }

		fiveSec OBJECT-TYPE
		SYNTAX  CounterBasedGauge64
		MAX-ACCESS read-only
		STATUS current
		DESCRIPTION  ""
		::={ systemCpuVserverDataCpuVserverCpuUsageEntry 5 }

		tenSec OBJECT-TYPE
		SYNTAX  CounterBasedGauge64
		MAX-ACCESS read-only
		STATUS current
		DESCRIPTION  ""
		::={ systemCpuVserverDataCpuVserverCpuUsageEntry 6 }

		thirtySec OBJECT-TYPE
		SYNTAX  CounterBasedGauge64
		MAX-ACCESS read-only
		STATUS current
		DESCRIPTION  ""
		::={ systemCpuVserverDataCpuVserverCpuUsageEntry 7 }

		sixtySec OBJECT-TYPE
		SYNTAX  CounterBasedGauge64
		MAX-ACCESS read-only
		STATUS current
		DESCRIPTION  ""
		::={ systemCpuVserverDataCpuVserverCpuUsageEntry 8 }

acosSystemCpuVportDataCpu           OBJECT IDENTIFIER ::= { acosSystemCpu 5 }

systemCpuVportDataCpuVportCpuUsageTable OBJECT-TYPE
		SYNTAX SEQUENCE OF SystemCpuVportDataCpuVportCpuUsageEntry
		MAX-ACCESS not-accessible
		STATUS current
		::={ acosSystemCpuVportDataCpu 1 }


	systemCpuVportDataCpuVportCpuUsageEntry OBJECT-TYPE
		SYNTAX SystemCpuVportDataCpuVportCpuUsageEntry
		MAX-ACCESS not-accessible
		STATUS current
		INDEX {
			vserverName,
			portNumber,
			protocol,
			cpuId
		}
		::={ systemCpuVportDataCpuVportCpuUsageTable 1 }


	SystemCpuVportDataCpuVportCpuUsageEntry ::=
		SEQUENCE {
			vserverName DisplayString,
			portNumber INTEGER,
			protocol DisplayString,
			cpuId INTEGER,
			vportType DisplayString,
			dcpuStr DisplayString,
			oneSec CounterBasedGauge64,
			fiveSec CounterBasedGauge64,
			tenSec CounterBasedGauge64,
			thirtySec CounterBasedGauge64,
			sixtySec CounterBasedGauge64
		}

		vserverName OBJECT-TYPE
		SYNTAX  DisplayString
		MAX-ACCESS read-only
		STATUS current
		DESCRIPTION  ""
		::={ systemCpuVportDataCpuVportCpuUsageEntry 1 }

		portNumber OBJECT-TYPE
		SYNTAX  INTEGER
		MAX-ACCESS read-only
		STATUS current
		DESCRIPTION  ""
		::={ systemCpuVportDataCpuVportCpuUsageEntry 2 }

		protocol OBJECT-TYPE
		SYNTAX  DisplayString
		MAX-ACCESS read-only
		STATUS current
		DESCRIPTION  ""
		::={ systemCpuVportDataCpuVportCpuUsageEntry 3 }

		cpuId OBJECT-TYPE
		SYNTAX  INTEGER
		MAX-ACCESS read-only
		STATUS current
		DESCRIPTION  ""
		::={ systemCpuVportDataCpuVportCpuUsageEntry 4 }

		vportType OBJECT-TYPE
		SYNTAX  DisplayString
		MAX-ACCESS read-only
		STATUS current
		DESCRIPTION  ""
		::={ systemCpuVportDataCpuVportCpuUsageEntry 5 }

		dcpuStr OBJECT-TYPE
		SYNTAX  DisplayString
		MAX-ACCESS read-only
		STATUS current
		DESCRIPTION  ""
		::={ systemCpuVportDataCpuVportCpuUsageEntry 6 }

		oneSec OBJECT-TYPE
		SYNTAX  CounterBasedGauge64
		MAX-ACCESS read-only
		STATUS current
		DESCRIPTION  ""
		::={ systemCpuVportDataCpuVportCpuUsageEntry 7 }

		fiveSec OBJECT-TYPE
		SYNTAX  CounterBasedGauge64
		MAX-ACCESS read-only
		STATUS current
		DESCRIPTION  ""
		::={ systemCpuVportDataCpuVportCpuUsageEntry 8 }

		tenSec OBJECT-TYPE
		SYNTAX  CounterBasedGauge64
		MAX-ACCESS read-only
		STATUS current
		DESCRIPTION  ""
		::={ systemCpuVportDataCpuVportCpuUsageEntry 9 }

		thirtySec OBJECT-TYPE
		SYNTAX  CounterBasedGauge64
		MAX-ACCESS read-only
		STATUS current
		DESCRIPTION  ""
		::={ systemCpuVportDataCpuVportCpuUsageEntry 10 }

		sixtySec OBJECT-TYPE
		SYNTAX  CounterBasedGauge64
		MAX-ACCESS read-only
		STATUS current
		DESCRIPTION  ""
		::={ systemCpuVportDataCpuVportCpuUsageEntry 11 }

acosSystemCpuDataCpu                OBJECT IDENTIFIER ::= { acosSystemCpu 1 }

systemCpuDataCpuCpuUsageTable OBJECT-TYPE
		SYNTAX SEQUENCE OF SystemCpuDataCpuCpuUsageEntry
		MAX-ACCESS not-accessible
		STATUS current
		::={ acosSystemCpuDataCpu 1 }


	systemCpuDataCpuCpuUsageEntry OBJECT-TYPE
		SYNTAX SystemCpuDataCpuCpuUsageEntry
		MAX-ACCESS not-accessible
		STATUS current
		INDEX {
			cpuId
		}
		::={ systemCpuDataCpuCpuUsageTable 1 }


	SystemCpuDataCpuCpuUsageEntry ::=
		SEQUENCE {
			cpuId INTEGER,
			oneSec CounterBasedGauge64,
			fiveSec CounterBasedGauge64,
			tenSec CounterBasedGauge64,
			thirtySec CounterBasedGauge64,
			sixtySec CounterBasedGauge64,
			dcpuStr DisplayString
		}

		cpuId OBJECT-TYPE
		SYNTAX  INTEGER
		MAX-ACCESS read-only
		STATUS current
		DESCRIPTION  ""
		::={ systemCpuDataCpuCpuUsageEntry 1 }

		oneSec OBJECT-TYPE
		SYNTAX  CounterBasedGauge64
		MAX-ACCESS read-only
		STATUS current
		DESCRIPTION  ""
		::={ systemCpuDataCpuCpuUsageEntry 2 }

		fiveSec OBJECT-TYPE
		SYNTAX  CounterBasedGauge64
		MAX-ACCESS read-only
		STATUS current
		DESCRIPTION  ""
		::={ systemCpuDataCpuCpuUsageEntry 3 }

		tenSec OBJECT-TYPE
		SYNTAX  CounterBasedGauge64
		MAX-ACCESS read-only
		STATUS current
		DESCRIPTION  ""
		::={ systemCpuDataCpuCpuUsageEntry 4 }

		thirtySec OBJECT-TYPE
		SYNTAX  CounterBasedGauge64
		MAX-ACCESS read-only
		STATUS current
		DESCRIPTION  ""
		::={ systemCpuDataCpuCpuUsageEntry 5 }

		sixtySec OBJECT-TYPE
		SYNTAX  CounterBasedGauge64
		MAX-ACCESS read-only
		STATUS current
		DESCRIPTION  ""
		::={ systemCpuDataCpuCpuUsageEntry 6 }

		dcpuStr OBJECT-TYPE
		SYNTAX  DisplayString
		MAX-ACCESS read-only
		STATUS current
		DESCRIPTION  ""
		::={ systemCpuDataCpuCpuUsageEntry 7 }

acosSystemCpuCtrlCpu                OBJECT IDENTIFIER ::= { acosSystemCpu 2 }

systemCpuCtrlCpuCpuUsageTable OBJECT-TYPE
		SYNTAX SEQUENCE OF SystemCpuCtrlCpuCpuUsageEntry
		MAX-ACCESS not-accessible
		STATUS current
		::={ acosSystemCpuCtrlCpu 1 }


	systemCpuCtrlCpuCpuUsageEntry OBJECT-TYPE
		SYNTAX SystemCpuCtrlCpuCpuUsageEntry
		MAX-ACCESS not-accessible
		STATUS current
		INDEX {
			crtlCpuId
		}
		::={ systemCpuCtrlCpuCpuUsageTable 1 }


	SystemCpuCtrlCpuCpuUsageEntry ::=
		SEQUENCE {
			crtlCpuId INTEGER,
			crtlOneSec CounterBasedGauge64,
			crtlFiveSec CounterBasedGauge64,
			crtlTenSec CounterBasedGauge64,
			crtlThirtySec CounterBasedGauge64,
			crtlSixtySec CounterBasedGauge64
		}

		crtlCpuId OBJECT-TYPE
		SYNTAX  INTEGER
		MAX-ACCESS read-only
		STATUS current
		DESCRIPTION  ""
		::={ systemCpuCtrlCpuCpuUsageEntry 1 }

		crtlOneSec OBJECT-TYPE
		SYNTAX  CounterBasedGauge64
		MAX-ACCESS read-only
		STATUS current
		DESCRIPTION  ""
		::={ systemCpuCtrlCpuCpuUsageEntry 2 }

		crtlFiveSec OBJECT-TYPE
		SYNTAX  CounterBasedGauge64
		MAX-ACCESS read-only
		STATUS current
		DESCRIPTION  ""
		::={ systemCpuCtrlCpuCpuUsageEntry 3 }

		crtlTenSec OBJECT-TYPE
		SYNTAX  CounterBasedGauge64
		MAX-ACCESS read-only
		STATUS current
		DESCRIPTION  ""
		::={ systemCpuCtrlCpuCpuUsageEntry 4 }

		crtlThirtySec OBJECT-TYPE
		SYNTAX  CounterBasedGauge64
		MAX-ACCESS read-only
		STATUS current
		DESCRIPTION  ""
		::={ systemCpuCtrlCpuCpuUsageEntry 5 }

		crtlSixtySec OBJECT-TYPE
		SYNTAX  CounterBasedGauge64
		MAX-ACCESS read-only
		STATUS current
		DESCRIPTION  ""
		::={ systemCpuCtrlCpuCpuUsageEntry 6 }

acosSystemCpuDataCpuOverall         OBJECT IDENTIFIER ::= { acosSystemCpu 3 }

systemCpuDataCpuOverallCpuUsageTable OBJECT-TYPE
		SYNTAX SEQUENCE OF SystemCpuDataCpuOverallCpuUsageEntry
		MAX-ACCESS not-accessible
		STATUS current
		::={ acosSystemCpuDataCpuOverall 1 }


	systemCpuDataCpuOverallCpuUsageEntry OBJECT-TYPE
		SYNTAX SystemCpuDataCpuOverallCpuUsageEntry
		MAX-ACCESS not-accessible
		STATUS current
		INDEX {
			allCpuId
		}
		::={ systemCpuDataCpuOverallCpuUsageTable 1 }


	SystemCpuDataCpuOverallCpuUsageEntry ::=
		SEQUENCE {
			allCpuId INTEGER,
			allOneSec CounterBasedGauge64,
			allFiveSec CounterBasedGauge64,
			allTenSec CounterBasedGauge64,
			allThirtySec CounterBasedGauge64,
			allSixtySec CounterBasedGauge64,
			allDcpuStr DisplayString
		}

		allCpuId OBJECT-TYPE
		SYNTAX  INTEGER
		MAX-ACCESS read-only
		STATUS current
		DESCRIPTION  ""
		::={ systemCpuDataCpuOverallCpuUsageEntry 1 }

		allOneSec OBJECT-TYPE
		SYNTAX  CounterBasedGauge64
		MAX-ACCESS read-only
		STATUS current
		DESCRIPTION  ""
		::={ systemCpuDataCpuOverallCpuUsageEntry 2 }

		allFiveSec OBJECT-TYPE
		SYNTAX  CounterBasedGauge64
		MAX-ACCESS read-only
		STATUS current
		DESCRIPTION  ""
		::={ systemCpuDataCpuOverallCpuUsageEntry 3 }

		allTenSec OBJECT-TYPE
		SYNTAX  CounterBasedGauge64
		MAX-ACCESS read-only
		STATUS current
		DESCRIPTION  ""
		::={ systemCpuDataCpuOverallCpuUsageEntry 4 }

		allThirtySec OBJECT-TYPE
		SYNTAX  CounterBasedGauge64
		MAX-ACCESS read-only
		STATUS current
		DESCRIPTION  ""
		::={ systemCpuDataCpuOverallCpuUsageEntry 5 }

		allSixtySec OBJECT-TYPE
		SYNTAX  CounterBasedGauge64
		MAX-ACCESS read-only
		STATUS current
		DESCRIPTION  ""
		::={ systemCpuDataCpuOverallCpuUsageEntry 6 }

		allDcpuStr OBJECT-TYPE
		SYNTAX  DisplayString
		MAX-ACCESS read-only
		STATUS current
		DESCRIPTION  ""
		::={ systemCpuDataCpuOverallCpuUsageEntry 7 }

END
