ACOS-TEMPLATE-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosTemplate MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Template OID for ACOS"
				::=  {  acosRootStats 160  }

acosTemplateGtpPolicy               OBJECT IDENTIFIER ::= { acosTemplate 6 }
acosTemplateGtpPolicyS              OBJECT IDENTIFIER ::= { acosTemplateGtpPolicy 1 }

templateGtpPolicySTable OBJECT-TYPE
		SYNTAX SEQUENCE OF TemplateGtpPolicySEntry
		MAX-ACCESS not-accessible
		STATUS current
		::={ acosTemplateGtpPolicyS 1 }


	templateGtpPolicySEntry OBJECT-TYPE
		SYNTAX TemplateGtpPolicySEntry
		MAX-ACCESS not-accessible
		STATUS current
		INDEX {
			name
		}
		::={ templateGtpPolicySTable 1 }


	TemplateGtpPolicySEntry ::=
		SEQUENCE {
			name DisplayString,
			gtpV0CTunnelCreated CounterBasedGauge64,
			gtpV0CTunnelHalfOpen CounterBasedGauge64,
			gtpV0CTunnelHalfClosed CounterBasedGauge64,
			gtpV0CTunnelClosed CounterBasedGauge64,
			gtpV0CTunnelDeleted CounterBasedGauge64,
			gtpV0CHalfOpenTunnelClosed CounterBasedGauge64,
			gtpV1CTunnelCreated CounterBasedGauge64,
			gtpV1CTunnelHalfOpen CounterBasedGauge64,
			gtpV1CTunnelHalfClosed CounterBasedGauge64,
			gtpV1CTunnelClosed CounterBasedGauge64,
			gtpV1CTunnelDeleted CounterBasedGauge64,
			gtpV1CHalfOpenTunnelClosed CounterBasedGauge64,
			gtpV2CTunnelCreated CounterBasedGauge64,
			gtpV2CTunnelHalfOpen CounterBasedGauge64,
			gtpV2CTunnelHalfClosed CounterBasedGauge64,
			gtpV2CTunnelClosed CounterBasedGauge64,
			gtpV2CTunnelDeleted CounterBasedGauge64,
			gtpV2CHalfOpenTunnelClosed CounterBasedGauge64,
			gtpUTunnelCreated CounterBasedGauge64,
			gtpUTunnelDeleted CounterBasedGauge64,
			gtpV0CUpdatePdpRespUnsuccess CounterBasedGauge64,
			gtpV1CUpdatePdpRespUnsuccess CounterBasedGauge64,
			gtpV2CModBearerRespUnsuccess CounterBasedGauge64,
			gtpV0CCreatePdpRespUnsuccess CounterBasedGauge64,
			gtpV1CCreatePdpRespUnsuccess CounterBasedGauge64,
			gtpV2CCreateSessRespUnsuccess CounterBasedGauge64,
			gtpV2CPiggybackMessage CounterBasedGauge64,
			gtpPathManagementMessage CounterBasedGauge64,
			gtpV0CTunnelDeletedRestart CounterBasedGauge64,
			gtpV1CTunnelDeletedRestart CounterBasedGauge64,
			gtpV2CTunnelDeletedRestart CounterBasedGauge64,
			gtpV0CReservedMessageAllow CounterBasedGauge64,
			gtpV1CReservedMessageAllow CounterBasedGauge64,
			gtpV2CReservedMessageAllow CounterBasedGauge64,
			gtpV2CLoadContrInfoExceed CounterBasedGauge64,
			gtpV1CPduNotificationRequestForward CounterBasedGauge64,
			gtpV1CPduNotificationRejectRequestForward CounterBasedGauge64,
			gtpV0CPduNotificationRequestForward CounterBasedGauge64,
			gtpV0CPduNotificationRejectRequestForward CounterBasedGauge64,
			gtpV0CMessageSkippedApnFilteringNoImsi CounterBasedGauge64,
			gtpV1CMessageSkippedApnFilteringNoImsi CounterBasedGauge64,
			gtpV2CMessageSkippedApnFilteringNoImsi CounterBasedGauge64,
			gtpV0CMessageSkippedMsisdnFilteringNoImsi CounterBasedGauge64,
			gtpV1CMessageSkippedMsisdnFilteringNoImsi CounterBasedGauge64,
			gtpV2CMessageSkippedMsisdnFilteringNoImsi CounterBasedGauge64,
			gtpV0CPacketDummyMsisdn CounterBasedGauge64,
			gtpV1CPacketDummyMsisdn CounterBasedGauge64,
			gtpV2CPacketDummyMsisdn CounterBasedGauge64,
			dropVldSanityGtpV2CMessageWithTeidZeroExpected CounterBasedGauge64,
			dropVldSanityGtpV1CMessageWithTeidZeroExpected CounterBasedGauge64,
			dropVldSanityGtpV0CMessageWithTeidZeroExpected CounterBasedGauge64,
			dropVldGtpIeRepeatCountExceed CounterBasedGauge64,
			dropVldReservedFieldSet CounterBasedGauge64,
			dropVldTunnelIdFlag CounterBasedGauge64,
			dropVldInvalidFlowLabelV0 CounterBasedGauge64,
			dropVldInvalidTeid CounterBasedGauge64,
			dropVldOutOfState CounterBasedGauge64,
			dropVldMandatoryInformationElement CounterBasedGauge64,
			dropVldMandatoryIeInGroupedIe CounterBasedGauge64,
			dropVldOutOfOrderIe CounterBasedGauge64,
			dropVldOutOfStateIe CounterBasedGauge64,
			dropVldReservedInformationElement CounterBasedGauge64,
			dropVldVersionNotSupported CounterBasedGauge64,
			dropVldMessageLength CounterBasedGauge64,
			dropVldCrossLayerCorrelation CounterBasedGauge64,
			dropVldCountryCodeMismatch CounterBasedGauge64,
			dropVldGtpUSpoofedSourceAddress CounterBasedGauge64,
			dropVldGtpBearerCountExceed CounterBasedGauge64,
			dropVldGtpV2WrongLbiCreateBearerReq CounterBasedGauge64,
			gtpCHandoverInProgressWithConn CounterBasedGauge64,
			dropVldV0ReservedMessageDrop CounterBasedGauge64,
			dropVldV1ReservedMessageDrop CounterBasedGauge64,
			dropVldV2ReservedMessageDrop CounterBasedGauge64,
			dropVldInvalidPktLenPiggyback CounterBasedGauge64,
			dropVldSanityFailedPiggyback CounterBasedGauge64,
			dropVldSequenceNumCorrelation CounterBasedGauge64,
			dropVldGtpv0SeqnumBufferFull CounterBasedGauge64,
			dropVldGtpv1SeqnumBufferFull CounterBasedGauge64,
			dropVldGtpv2SeqnumBufferFull CounterBasedGauge64,
			dropVldGtpInvalidImsiLenDrop CounterBasedGauge64,
			dropVldGtpInvalidApnLenDrop CounterBasedGauge64,
			dropVldProtocolFlagUnset CounterBasedGauge64,
			dropVldGtpv0SubscriberAttrMiss CounterBasedGauge64,
			dropVldGtpv1SubscriberAttrMiss CounterBasedGauge64,
			dropVldGtpv2SubscriberAttrMiss CounterBasedGauge64,
			dropVldGtpV0CIeLenExceedMsgLen CounterBasedGauge64,
			dropVldGtpV1CIeLenExceedMsgLen CounterBasedGauge64,
			dropVldGtpV2CIeLenExceedMsgLen CounterBasedGauge64,
			dropVldGtpV0CMessageLengthMismatch CounterBasedGauge64,
			dropVldGtpV1CMessageLengthMismatch CounterBasedGauge64,
			dropVldGtpV2CMessageLengthMismatch CounterBasedGauge64,
			dropVldGtpV0CMessageSkippedApnFilteringNoApn CounterBasedGauge64,
			dropVldGtpV1CMessageSkippedApnFilteringNoApn CounterBasedGauge64,
			dropVldGtpV2CMessageSkippedApnFilteringNoApn CounterBasedGauge64,
			dropFltMessageFiltering CounterBasedGauge64,
			dropFltApnFiltering CounterBasedGauge64,
			dropFltMsisdnFiltering CounterBasedGauge64,
			dropFltRatTypeFiltering CounterBasedGauge64,
			dropFltGtpInGtp CounterBasedGauge64,
			dropRlGtpV0CAgg CounterBasedGauge64,
			dropRlGtpV1CAgg CounterBasedGauge64,
			dropRlGtpV2CAgg CounterBasedGauge64,
			dropRlGtpV1CCreatePdpRequest CounterBasedGauge64,
			dropRlGtpV2CCreateSessionRequest CounterBasedGauge64,
			dropRlGtpV1CUpdatePdpRequest CounterBasedGauge64,
			dropRlGtpV2CModifyBearerRequest CounterBasedGauge64,
			dropRlGtpUTunnelCreate CounterBasedGauge64,
			dropRlGtpUUplinkByte CounterBasedGauge64,
			dropRlGtpUUplinkPacket CounterBasedGauge64,
			dropRlGtpUDownlinkByte CounterBasedGauge64,
			dropRlGtpUDownlinkPacket CounterBasedGauge64,
			dropRlGtpUTotalByte CounterBasedGauge64,
			dropRlGtpUTotalPacket CounterBasedGauge64,
			dropRlGtpUMaxConcurrentTunnels CounterBasedGauge64
		}

			name OBJECT-TYPE
			SYNTAX  DisplayString
			MAX-ACCESS read-only
			STATUS current
			DESCRIPTION  "Configure the GTP Policy Name"
			::={ templateGtpPolicySEntry 1 }

			gtpV0CTunnelCreated OBJECT-TYPE
			SYNTAX  CounterBasedGauge64
			MAX-ACCESS read-only
			STATUS current
			DESCRIPTION  "GTPv0-C Tunnel Created"
			::={ templateGtpPolicySEntry 2 }

			gtpV0CTunnelHalfOpen OBJECT-TYPE
			SYNTAX  CounterBasedGauge64
			MAX-ACCESS read-only
			STATUS current
			DESCRIPTION  "GTPv0-C Half open tunnel created"
			::={ templateGtpPolicySEntry 3 }

			gtpV0CTunnelHalfClosed OBJECT-TYPE
			SYNTAX  CounterBasedGauge64
			MAX-ACCESS read-only
			STATUS current
			DESCRIPTION  "GTPv0-C Tunnel Delete Request"
			::={ templateGtpPolicySEntry 4 }

			gtpV0CTunnelClosed OBJECT-TYPE
			SYNTAX  CounterBasedGauge64
			MAX-ACCESS read-only
			STATUS current
			DESCRIPTION  "GTPv0-C Tunnel Marked Deleted"
			::={ templateGtpPolicySEntry 5 }

			gtpV0CTunnelDeleted OBJECT-TYPE
			SYNTAX  CounterBasedGauge64
			MAX-ACCESS read-only
			STATUS current
			DESCRIPTION  "GTPv0-C Tunnel Deleted"
			::={ templateGtpPolicySEntry 6 }

			gtpV0CHalfOpenTunnelClosed OBJECT-TYPE
			SYNTAX  CounterBasedGauge64
			MAX-ACCESS read-only
			STATUS current
			DESCRIPTION  "GTPv0-C Half open tunnel closed"
			::={ templateGtpPolicySEntry 7 }

			gtpV1CTunnelCreated OBJECT-TYPE
			SYNTAX  CounterBasedGauge64
			MAX-ACCESS read-only
			STATUS current
			DESCRIPTION  "GTPv1-C Tunnel Created"
			::={ templateGtpPolicySEntry 8 }

			gtpV1CTunnelHalfOpen OBJECT-TYPE
			SYNTAX  CounterBasedGauge64
			MAX-ACCESS read-only
			STATUS current
			DESCRIPTION  "GTPv1-C Half open tunnel created"
			::={ templateGtpPolicySEntry 9 }

			gtpV1CTunnelHalfClosed OBJECT-TYPE
			SYNTAX  CounterBasedGauge64
			MAX-ACCESS read-only
			STATUS current
			DESCRIPTION  "GTPv1-C Tunnel Delete Request"
			::={ templateGtpPolicySEntry 10 }

			gtpV1CTunnelClosed OBJECT-TYPE
			SYNTAX  CounterBasedGauge64
			MAX-ACCESS read-only
			STATUS current
			DESCRIPTION  "GTPv1-C Tunnel Marked Deleted"
			::={ templateGtpPolicySEntry 11 }

			gtpV1CTunnelDeleted OBJECT-TYPE
			SYNTAX  CounterBasedGauge64
			MAX-ACCESS read-only
			STATUS current
			DESCRIPTION  "GTPv1-C Tunnel Deleted"
			::={ templateGtpPolicySEntry 12 }

			gtpV1CHalfOpenTunnelClosed OBJECT-TYPE
			SYNTAX  CounterBasedGauge64
			MAX-ACCESS read-only
			STATUS current
			DESCRIPTION  "GTPv1-C Half open tunnel closed"
			::={ templateGtpPolicySEntry 13 }

			gtpV2CTunnelCreated OBJECT-TYPE
			SYNTAX  CounterBasedGauge64
			MAX-ACCESS read-only
			STATUS current
			DESCRIPTION  "GTPv2-C Tunnel Created"
			::={ templateGtpPolicySEntry 14 }

			gtpV2CTunnelHalfOpen OBJECT-TYPE
			SYNTAX  CounterBasedGauge64
			MAX-ACCESS read-only
			STATUS current
			DESCRIPTION  "GTPv2-C Half open tunnel created"
			::={ templateGtpPolicySEntry 15 }

			gtpV2CTunnelHalfClosed OBJECT-TYPE
			SYNTAX  CounterBasedGauge64
			MAX-ACCESS read-only
			STATUS current
			DESCRIPTION  "GTPv2-C Tunnel Delete Request"
			::={ templateGtpPolicySEntry 16 }

			gtpV2CTunnelClosed OBJECT-TYPE
			SYNTAX  CounterBasedGauge64
			MAX-ACCESS read-only
			STATUS current
			DESCRIPTION  "GTPv2-C Tunnel Marked Deleted"
			::={ templateGtpPolicySEntry 17 }

			gtpV2CTunnelDeleted OBJECT-TYPE
			SYNTAX  CounterBasedGauge64
			MAX-ACCESS read-only
			STATUS current
			DESCRIPTION  "GTPv2-C Tunnel Deleted"
			::={ templateGtpPolicySEntry 18 }

			gtpV2CHalfOpenTunnelClosed OBJECT-TYPE
			SYNTAX  CounterBasedGauge64
			MAX-ACCESS read-only
			STATUS current
			DESCRIPTION  "GTPv2-C Half open tunnel closed"
			::={ templateGtpPolicySEntry 19 }

			gtpUTunnelCreated OBJECT-TYPE
			SYNTAX  CounterBasedGauge64
			MAX-ACCESS read-only
			STATUS current
			DESCRIPTION  "GTP-U Tunnel Created"
			::={ templateGtpPolicySEntry 20 }

			gtpUTunnelDeleted OBJECT-TYPE
			SYNTAX  CounterBasedGauge64
			MAX-ACCESS read-only
			STATUS current
			DESCRIPTION  "GTP-U Tunnel Deleted"
			::={ templateGtpPolicySEntry 21 }

			gtpV0CUpdatePdpRespUnsuccess OBJECT-TYPE
			SYNTAX  CounterBasedGauge64
			MAX-ACCESS read-only
			STATUS current
			DESCRIPTION  "GTPv0-C Update PDP Context Response Unsuccessful"
			::={ templateGtpPolicySEntry 22 }

			gtpV1CUpdatePdpRespUnsuccess OBJECT-TYPE
			SYNTAX  CounterBasedGauge64
			MAX-ACCESS read-only
			STATUS current
			DESCRIPTION  "GTPv1-C Update PDP Context Response Unsuccessful"
			::={ templateGtpPolicySEntry 23 }

			gtpV2CModBearerRespUnsuccess OBJECT-TYPE
			SYNTAX  CounterBasedGauge64
			MAX-ACCESS read-only
			STATUS current
			DESCRIPTION  "GTPv2-C Modify Bearer Response Unsuccessful"
			::={ templateGtpPolicySEntry 24 }

			gtpV0CCreatePdpRespUnsuccess OBJECT-TYPE
			SYNTAX  CounterBasedGauge64
			MAX-ACCESS read-only
			STATUS current
			DESCRIPTION  "GTPv0-C Create PDP Context Response Unsuccessful"
			::={ templateGtpPolicySEntry 25 }

			gtpV1CCreatePdpRespUnsuccess OBJECT-TYPE
			SYNTAX  CounterBasedGauge64
			MAX-ACCESS read-only
			STATUS current
			DESCRIPTION  "GTPv1-C Create PDP Context Response Unsuccessful"
			::={ templateGtpPolicySEntry 26 }

			gtpV2CCreateSessRespUnsuccess OBJECT-TYPE
			SYNTAX  CounterBasedGauge64
			MAX-ACCESS read-only
			STATUS current
			DESCRIPTION  "GTPv2-C Create Session Response Unsuccessful"
			::={ templateGtpPolicySEntry 27 }

			gtpV2CPiggybackMessage OBJECT-TYPE
			SYNTAX  CounterBasedGauge64
			MAX-ACCESS read-only
			STATUS current
			DESCRIPTION  "GTPv2-C Piggyback Message"
			::={ templateGtpPolicySEntry 28 }

			gtpPathManagementMessage OBJECT-TYPE
			SYNTAX  CounterBasedGauge64
			MAX-ACCESS read-only
			STATUS current
			DESCRIPTION  "GTP Path Management Messages Received"
			::={ templateGtpPolicySEntry 29 }

			gtpV0CTunnelDeletedRestart OBJECT-TYPE
			SYNTAX  CounterBasedGauge64
			MAX-ACCESS read-only
			STATUS current
			DESCRIPTION  "GTPv0-C Tunnel Deleted with Restart/failure"
			::={ templateGtpPolicySEntry 30 }

			gtpV1CTunnelDeletedRestart OBJECT-TYPE
			SYNTAX  CounterBasedGauge64
			MAX-ACCESS read-only
			STATUS current
			DESCRIPTION  "GTPv1-C Tunnel Deleted with Restart/failure"
			::={ templateGtpPolicySEntry 31 }

			gtpV2CTunnelDeletedRestart OBJECT-TYPE
			SYNTAX  CounterBasedGauge64
			MAX-ACCESS read-only
			STATUS current
			DESCRIPTION  "GTPv2-C Tunnel Deleted with Restart/failure"
			::={ templateGtpPolicySEntry 32 }

			gtpV0CReservedMessageAllow OBJECT-TYPE
			SYNTAX  CounterBasedGauge64
			MAX-ACCESS read-only
			STATUS current
			DESCRIPTION  "Permit GTPv0-C Reserved Messages"
			::={ templateGtpPolicySEntry 33 }

			gtpV1CReservedMessageAllow OBJECT-TYPE
			SYNTAX  CounterBasedGauge64
			MAX-ACCESS read-only
			STATUS current
			DESCRIPTION  "Permit GTPv1-C Reserved Messages"
			::={ templateGtpPolicySEntry 34 }

			gtpV2CReservedMessageAllow OBJECT-TYPE
			SYNTAX  CounterBasedGauge64
			MAX-ACCESS read-only
			STATUS current
			DESCRIPTION  "Permit GTPv2-C Reserved Messages"
			::={ templateGtpPolicySEntry 35 }

			gtpV2CLoadContrInfoExceed OBJECT-TYPE
			SYNTAX  CounterBasedGauge64
			MAX-ACCESS read-only
			STATUS current
			DESCRIPTION  "GTPv2-C Load Control Info IEs in message exceeded 2"
			::={ templateGtpPolicySEntry 36 }

			gtpV1CPduNotificationRequestForward OBJECT-TYPE
			SYNTAX  CounterBasedGauge64
			MAX-ACCESS read-only
			STATUS current
			DESCRIPTION  "GTPv1-C PDU Notification Request Forward"
			::={ templateGtpPolicySEntry 37 }

			gtpV1CPduNotificationRejectRequestForward OBJECT-TYPE
			SYNTAX  CounterBasedGauge64
			MAX-ACCESS read-only
			STATUS current
			DESCRIPTION  "GTPv1-C PDU Notification Reject Request Forward"
			::={ templateGtpPolicySEntry 38 }

			gtpV0CPduNotificationRequestForward OBJECT-TYPE
			SYNTAX  CounterBasedGauge64
			MAX-ACCESS read-only
			STATUS current
			DESCRIPTION  "GTPv0-C PDU Notification Request Forward"
			::={ templateGtpPolicySEntry 39 }

			gtpV0CPduNotificationRejectRequestForward OBJECT-TYPE
			SYNTAX  CounterBasedGauge64
			MAX-ACCESS read-only
			STATUS current
			DESCRIPTION  "GTPv0-C PDU Notification Reject Request Forward"
			::={ templateGtpPolicySEntry 40 }

			gtpV0CMessageSkippedApnFilteringNoImsi OBJECT-TYPE
			SYNTAX  CounterBasedGauge64
			MAX-ACCESS read-only
			STATUS current
			DESCRIPTION  "GTPv0-C APN/IMSI Filtering Skipped (No IMSI)"
			::={ templateGtpPolicySEntry 108 }

			gtpV1CMessageSkippedApnFilteringNoImsi OBJECT-TYPE
			SYNTAX  CounterBasedGauge64
			MAX-ACCESS read-only
			STATUS current
			DESCRIPTION  "GTPv1-C APN/IMSI Filtering Skipped (No IMSI)"
			::={ templateGtpPolicySEntry 109 }

			gtpV2CMessageSkippedApnFilteringNoImsi OBJECT-TYPE
			SYNTAX  CounterBasedGauge64
			MAX-ACCESS read-only
			STATUS current
			DESCRIPTION  "GTPv2-C APN/IMSI Filtering Skipped (No IMSI)"
			::={ templateGtpPolicySEntry 110 }

			gtpV0CMessageSkippedMsisdnFilteringNoImsi OBJECT-TYPE
			SYNTAX  CounterBasedGauge64
			MAX-ACCESS read-only
			STATUS current
			DESCRIPTION  "GTPv0-C MSISDN Filtering Skipped (No MSISDN)"
			::={ templateGtpPolicySEntry 111 }

			gtpV1CMessageSkippedMsisdnFilteringNoImsi OBJECT-TYPE
			SYNTAX  CounterBasedGauge64
			MAX-ACCESS read-only
			STATUS current
			DESCRIPTION  "GTPv1-C MSISDN Filtering Skipped (No MSISDN)"
			::={ templateGtpPolicySEntry 112 }

			gtpV2CMessageSkippedMsisdnFilteringNoImsi OBJECT-TYPE
			SYNTAX  CounterBasedGauge64
			MAX-ACCESS read-only
			STATUS current
			DESCRIPTION  "GTPv2-C MSISDN Filtering Skipped (No MSISDN)"
			::={ templateGtpPolicySEntry 113 }

			gtpV0CPacketDummyMsisdn OBJECT-TYPE
			SYNTAX  CounterBasedGauge64
			MAX-ACCESS read-only
			STATUS current
			DESCRIPTION  "GTPv0-C Packet With Dummy MSISDN Forwarded"
			::={ templateGtpPolicySEntry 114 }

			gtpV1CPacketDummyMsisdn OBJECT-TYPE
			SYNTAX  CounterBasedGauge64
			MAX-ACCESS read-only
			STATUS current
			DESCRIPTION  "GTPv1-C Packet With Dummy MSISDN Forwarded"
			::={ templateGtpPolicySEntry 115 }

			gtpV2CPacketDummyMsisdn OBJECT-TYPE
			SYNTAX  CounterBasedGauge64
			MAX-ACCESS read-only
			STATUS current
			DESCRIPTION  "GTPv2-C Packet With Dummy MSISDN Forwarded"
			::={ templateGtpPolicySEntry 116 }

			dropVldSanityGtpV2CMessageWithTeidZeroExpected OBJECT-TYPE
			SYNTAX  CounterBasedGauge64
			MAX-ACCESS read-only
			STATUS current
			DESCRIPTION  "Validation Drop: GTPv2-C Create Session Request with TEID"
			::={ templateGtpPolicySEntry 41 }

			dropVldSanityGtpV1CMessageWithTeidZeroExpected OBJECT-TYPE
			SYNTAX  CounterBasedGauge64
			MAX-ACCESS read-only
			STATUS current
			DESCRIPTION  "Validation Drop: GTPv1-C PDU Notification Request with TEID"
			::={ templateGtpPolicySEntry 42 }

			dropVldSanityGtpV0CMessageWithTeidZeroExpected OBJECT-TYPE
			SYNTAX  CounterBasedGauge64
			MAX-ACCESS read-only
			STATUS current
			DESCRIPTION  "Validation Drop: GTPv0-C PDU Notification Request with TEID"
			::={ templateGtpPolicySEntry 43 }

			dropVldGtpIeRepeatCountExceed OBJECT-TYPE
			SYNTAX  CounterBasedGauge64
			MAX-ACCESS read-only
			STATUS current
			DESCRIPTION  "Validation Drop: GTP repeated IE count exceeded"
			::={ templateGtpPolicySEntry 44 }

			dropVldReservedFieldSet OBJECT-TYPE
			SYNTAX  CounterBasedGauge64
			MAX-ACCESS read-only
			STATUS current
			DESCRIPTION  "Validation Drop: Reserved Header Field Set"
			::={ templateGtpPolicySEntry 45 }

			dropVldTunnelIdFlag OBJECT-TYPE
			SYNTAX  CounterBasedGauge64
			MAX-ACCESS read-only
			STATUS current
			DESCRIPTION  "Validation Drop: Tunnel Header Flag Not Set"
			::={ templateGtpPolicySEntry 46 }

			dropVldInvalidFlowLabelV0 OBJECT-TYPE
			SYNTAX  CounterBasedGauge64
			MAX-ACCESS read-only
			STATUS current
			DESCRIPTION  "Validation Drop: Invalid Flow Label in GTPv0-C Header"
			::={ templateGtpPolicySEntry 47 }

			dropVldInvalidTeid OBJECT-TYPE
			SYNTAX  CounterBasedGauge64
			MAX-ACCESS read-only
			STATUS current
			DESCRIPTION  "Validation Drop: Invalid TEID Value"
			::={ templateGtpPolicySEntry 48 }

			dropVldOutOfState OBJECT-TYPE
			SYNTAX  CounterBasedGauge64
			MAX-ACCESS read-only
			STATUS current
			DESCRIPTION  "Validation Drop: Out Of State GTP Message"
			::={ templateGtpPolicySEntry 49 }

			dropVldMandatoryInformationElement OBJECT-TYPE
			SYNTAX  CounterBasedGauge64
			MAX-ACCESS read-only
			STATUS current
			DESCRIPTION  "Validation Drop: Mandatory IE Not Present"
			::={ templateGtpPolicySEntry 50 }

			dropVldMandatoryIeInGroupedIe OBJECT-TYPE
			SYNTAX  CounterBasedGauge64
			MAX-ACCESS read-only
			STATUS current
			DESCRIPTION  "Validation Drop: Mandatory IE in Grouped IE Not Present"
			::={ templateGtpPolicySEntry 51 }

			dropVldOutOfOrderIe OBJECT-TYPE
			SYNTAX  CounterBasedGauge64
			MAX-ACCESS read-only
			STATUS current
			DESCRIPTION  "Validation Drop: GTPv1-C Message Out of Order IE"
			::={ templateGtpPolicySEntry 52 }

			dropVldOutOfStateIe OBJECT-TYPE
			SYNTAX  CounterBasedGauge64
			MAX-ACCESS read-only
			STATUS current
			DESCRIPTION  "Validation Drop: Unexpected IE Present in Message"
			::={ templateGtpPolicySEntry 53 }

			dropVldReservedInformationElement OBJECT-TYPE
			SYNTAX  CounterBasedGauge64
			MAX-ACCESS read-only
			STATUS current
			DESCRIPTION  "Validation Drop: Reserved IE Field Present"
			::={ templateGtpPolicySEntry 54 }

			dropVldVersionNotSupported OBJECT-TYPE
			SYNTAX  CounterBasedGauge64
			MAX-ACCESS read-only
			STATUS current
			DESCRIPTION  "Validation Drop: Invalid GTP version"
			::={ templateGtpPolicySEntry 55 }

			dropVldMessageLength OBJECT-TYPE
			SYNTAX  CounterBasedGauge64
			MAX-ACCESS read-only
			STATUS current
			DESCRIPTION  "Validation Drop: Message Length Exceeded"
			::={ templateGtpPolicySEntry 56 }

			dropVldCrossLayerCorrelation OBJECT-TYPE
			SYNTAX  CounterBasedGauge64
			MAX-ACCESS read-only
			STATUS current
			DESCRIPTION  "Validation Drop: Cross Layer IP Address Mismatch"
			::={ templateGtpPolicySEntry 57 }

			dropVldCountryCodeMismatch OBJECT-TYPE
			SYNTAX  CounterBasedGauge64
			MAX-ACCESS read-only
			STATUS current
			DESCRIPTION  "Validation Drop: Country Code Mismatch in IMSI and MSISDN"
			::={ templateGtpPolicySEntry 58 }

			dropVldGtpUSpoofedSourceAddress OBJECT-TYPE
			SYNTAX  CounterBasedGauge64
			MAX-ACCESS read-only
			STATUS current
			DESCRIPTION  "Validation Drop: GTP-U IP Address Spoofed"
			::={ templateGtpPolicySEntry 59 }

			dropVldGtpBearerCountExceed OBJECT-TYPE
			SYNTAX  CounterBasedGauge64
			MAX-ACCESS read-only
			STATUS current
			DESCRIPTION  "Validation Drop: GTP Bearer count exceeded max (11)"
			::={ templateGtpPolicySEntry 60 }

			dropVldGtpV2WrongLbiCreateBearerReq OBJECT-TYPE
			SYNTAX  CounterBasedGauge64
			MAX-ACCESS read-only
			STATUS current
			DESCRIPTION  "Validation Drop: GTPV2-C Wrong LBI in Create Bearer Request"
			::={ templateGtpPolicySEntry 61 }

			gtpCHandoverInProgressWithConn OBJECT-TYPE
			SYNTAX  CounterBasedGauge64
			MAX-ACCESS read-only
			STATUS current
			DESCRIPTION  "GTP-C matching a conn with Handover In Progress"
			::={ templateGtpPolicySEntry 62 }

			dropVldV0ReservedMessageDrop OBJECT-TYPE
			SYNTAX  CounterBasedGauge64
			MAX-ACCESS read-only
			STATUS current
			DESCRIPTION  "Validation Drop: GTPv0-C Reserved Message Drop"
			::={ templateGtpPolicySEntry 64 }

			dropVldV1ReservedMessageDrop OBJECT-TYPE
			SYNTAX  CounterBasedGauge64
			MAX-ACCESS read-only
			STATUS current
			DESCRIPTION  "Validation Drop: GTPv1-C Reserved Message Drop"
			::={ templateGtpPolicySEntry 65 }

			dropVldV2ReservedMessageDrop OBJECT-TYPE
			SYNTAX  CounterBasedGauge64
			MAX-ACCESS read-only
			STATUS current
			DESCRIPTION  "Validation Drop: GTPv2-C Reserved Message Drop"
			::={ templateGtpPolicySEntry 66 }

			dropVldInvalidPktLenPiggyback OBJECT-TYPE
			SYNTAX  CounterBasedGauge64
			MAX-ACCESS read-only
			STATUS current
			DESCRIPTION  "Validation Drop: Piggyback message invalid packet length"
			::={ templateGtpPolicySEntry 67 }

			dropVldSanityFailedPiggyback OBJECT-TYPE
			SYNTAX  CounterBasedGauge64
			MAX-ACCESS read-only
			STATUS current
			DESCRIPTION  "Validation Drop: piggyback message anomaly failed"
			::={ templateGtpPolicySEntry 68 }

			dropVldSequenceNumCorrelation OBJECT-TYPE
			SYNTAX  CounterBasedGauge64
			MAX-ACCESS read-only
			STATUS current
			DESCRIPTION  "Validation Drop: GTP-C Sequence number Mismatch"
			::={ templateGtpPolicySEntry 69 }

			dropVldGtpv0SeqnumBufferFull OBJECT-TYPE
			SYNTAX  CounterBasedGauge64
			MAX-ACCESS read-only
			STATUS current
			DESCRIPTION  "Validation Drop: GTPV0-C conn Sequence number Buffer Full"
			::={ templateGtpPolicySEntry 70 }

			dropVldGtpv1SeqnumBufferFull OBJECT-TYPE
			SYNTAX  CounterBasedGauge64
			MAX-ACCESS read-only
			STATUS current
			DESCRIPTION  "Validation Drop: GTPV1-C conn Sequence number Buffer Full"
			::={ templateGtpPolicySEntry 71 }

			dropVldGtpv2SeqnumBufferFull OBJECT-TYPE
			SYNTAX  CounterBasedGauge64
			MAX-ACCESS read-only
			STATUS current
			DESCRIPTION  "Validation Drop: GTPV2-C conn Sequence number Buffer Full"
			::={ templateGtpPolicySEntry 72 }

			dropVldGtpInvalidImsiLenDrop OBJECT-TYPE
			SYNTAX  CounterBasedGauge64
			MAX-ACCESS read-only
			STATUS current
			DESCRIPTION  "Validation Drop: GTP-C Invalid IMSI Length Drop"
			::={ templateGtpPolicySEntry 73 }

			dropVldGtpInvalidApnLenDrop OBJECT-TYPE
			SYNTAX  CounterBasedGauge64
			MAX-ACCESS read-only
			STATUS current
			DESCRIPTION  "Validation Drop: GTP-C Invalid APN Length Drop"
			::={ templateGtpPolicySEntry 74 }

			dropVldProtocolFlagUnset OBJECT-TYPE
			SYNTAX  CounterBasedGauge64
			MAX-ACCESS read-only
			STATUS current
			DESCRIPTION  "Validation Drop: Protocol flag in Header Field not Set"
			::={ templateGtpPolicySEntry 75 }

			dropVldGtpv0SubscriberAttrMiss OBJECT-TYPE
			SYNTAX  CounterBasedGauge64
			MAX-ACCESS read-only
			STATUS current
			DESCRIPTION  "Validation Drop: GTPV0-c Subscriber Attributes Missing"
			::={ templateGtpPolicySEntry 102 }

			dropVldGtpv1SubscriberAttrMiss OBJECT-TYPE
			SYNTAX  CounterBasedGauge64
			MAX-ACCESS read-only
			STATUS current
			DESCRIPTION  "Validation Drop: GTPV1-c Subscriber Attributes Missing"
			::={ templateGtpPolicySEntry 103 }

			dropVldGtpv2SubscriberAttrMiss OBJECT-TYPE
			SYNTAX  CounterBasedGauge64
			MAX-ACCESS read-only
			STATUS current
			DESCRIPTION  "Validation Drop: GTPV2-c Subscriber Attributes Missing"
			::={ templateGtpPolicySEntry 104 }

			dropVldGtpV0CIeLenExceedMsgLen OBJECT-TYPE
			SYNTAX  CounterBasedGauge64
			MAX-ACCESS read-only
			STATUS current
			DESCRIPTION  "GTPv0-C IE Length Exceeds Message Length"
			::={ templateGtpPolicySEntry 96 }

			dropVldGtpV1CIeLenExceedMsgLen OBJECT-TYPE
			SYNTAX  CounterBasedGauge64
			MAX-ACCESS read-only
			STATUS current
			DESCRIPTION  "GTPv1-C IE Length Exceeds Message Length"
			::={ templateGtpPolicySEntry 97 }

			dropVldGtpV2CIeLenExceedMsgLen OBJECT-TYPE
			SYNTAX  CounterBasedGauge64
			MAX-ACCESS read-only
			STATUS current
			DESCRIPTION  "GTPv2-C IE Length Exceeds Message Length"
			::={ templateGtpPolicySEntry 98 }

			dropVldGtpV0CMessageLengthMismatch OBJECT-TYPE
			SYNTAX  CounterBasedGauge64
			MAX-ACCESS read-only
			STATUS current
			DESCRIPTION  "GTPv0-C Message Length Mismatch Across Layers"
			::={ templateGtpPolicySEntry 99 }

			dropVldGtpV1CMessageLengthMismatch OBJECT-TYPE
			SYNTAX  CounterBasedGauge64
			MAX-ACCESS read-only
			STATUS current
			DESCRIPTION  "GTPv1-C Message Length Mismatch Across Layers"
			::={ templateGtpPolicySEntry 100 }

			dropVldGtpV2CMessageLengthMismatch OBJECT-TYPE
			SYNTAX  CounterBasedGauge64
			MAX-ACCESS read-only
			STATUS current
			DESCRIPTION  "GTPv2-C Message Length Mismatch Across Layers"
			::={ templateGtpPolicySEntry 101 }

			dropVldGtpV0CMessageSkippedApnFilteringNoApn OBJECT-TYPE
			SYNTAX  CounterBasedGauge64
			MAX-ACCESS read-only
			STATUS current
			DESCRIPTION  "Validation Drop: GTPv0-C APN/IMSI Filtering Dropped (No APN)"
			::={ templateGtpPolicySEntry 105 }

			dropVldGtpV1CMessageSkippedApnFilteringNoApn OBJECT-TYPE
			SYNTAX  CounterBasedGauge64
			MAX-ACCESS read-only
			STATUS current
			DESCRIPTION  "Validation Drop: GTPv1-C APN/IMSI Filtering Dropped (No APN)"
			::={ templateGtpPolicySEntry 106 }

			dropVldGtpV2CMessageSkippedApnFilteringNoApn OBJECT-TYPE
			SYNTAX  CounterBasedGauge64
			MAX-ACCESS read-only
			STATUS current
			DESCRIPTION  "Validation Drop: GTPv2-C APN/IMSI Filtering Dropped (No APN)"
			::={ templateGtpPolicySEntry 107 }

			dropFltMessageFiltering OBJECT-TYPE
			SYNTAX  CounterBasedGauge64
			MAX-ACCESS read-only
			STATUS current
			DESCRIPTION  "Filtering Drop: Message Type Not Permitted on Interface"
			::={ templateGtpPolicySEntry 76 }

			dropFltApnFiltering OBJECT-TYPE
			SYNTAX  CounterBasedGauge64
			MAX-ACCESS read-only
			STATUS current
			DESCRIPTION  "Filtering Drop: APN IMSI Filtering"
			::={ templateGtpPolicySEntry 77 }

			dropFltMsisdnFiltering OBJECT-TYPE
			SYNTAX  CounterBasedGauge64
			MAX-ACCESS read-only
			STATUS current
			DESCRIPTION  "Filtering Drop: MSISDN Filtering"
			::={ templateGtpPolicySEntry 78 }

			dropFltRatTypeFiltering OBJECT-TYPE
			SYNTAX  CounterBasedGauge64
			MAX-ACCESS read-only
			STATUS current
			DESCRIPTION  "Filtering Drop: RAT Type Filtering"
			::={ templateGtpPolicySEntry 79 }

			dropFltGtpInGtp OBJECT-TYPE
			SYNTAX  CounterBasedGauge64
			MAX-ACCESS read-only
			STATUS current
			DESCRIPTION  "Filtering Drop: GTP in GTP Tunnel Present"
			::={ templateGtpPolicySEntry 80 }

			dropRlGtpV0CAgg OBJECT-TYPE
			SYNTAX  CounterBasedGauge64
			MAX-ACCESS read-only
			STATUS current
			DESCRIPTION  "Rate-limit Drop: Maximum GTPv0-C Message rate"
			::={ templateGtpPolicySEntry 81 }

			dropRlGtpV1CAgg OBJECT-TYPE
			SYNTAX  CounterBasedGauge64
			MAX-ACCESS read-only
			STATUS current
			DESCRIPTION  "Rate-limit Drop: Maximum GTPv1-C Message rate"
			::={ templateGtpPolicySEntry 82 }

			dropRlGtpV2CAgg OBJECT-TYPE
			SYNTAX  CounterBasedGauge64
			MAX-ACCESS read-only
			STATUS current
			DESCRIPTION  "Rate-limit Drop: Maximum GTPv2-C Message rate"
			::={ templateGtpPolicySEntry 83 }

			dropRlGtpV1CCreatePdpRequest OBJECT-TYPE
			SYNTAX  CounterBasedGauge64
			MAX-ACCESS read-only
			STATUS current
			DESCRIPTION  "Rate-limit Drop: GTPv1-C Create PDP Request rate"
			::={ templateGtpPolicySEntry 84 }

			dropRlGtpV2CCreateSessionRequest OBJECT-TYPE
			SYNTAX  CounterBasedGauge64
			MAX-ACCESS read-only
			STATUS current
			DESCRIPTION  "Rate-limit Drop: GTPv2-C Create Session Request rate"
			::={ templateGtpPolicySEntry 85 }

			dropRlGtpV1CUpdatePdpRequest OBJECT-TYPE
			SYNTAX  CounterBasedGauge64
			MAX-ACCESS read-only
			STATUS current
			DESCRIPTION  "Rate-limit Drop: GTPv1-C Update PDP Request rate"
			::={ templateGtpPolicySEntry 86 }

			dropRlGtpV2CModifyBearerRequest OBJECT-TYPE
			SYNTAX  CounterBasedGauge64
			MAX-ACCESS read-only
			STATUS current
			DESCRIPTION  "Rate-limit Drop: GTPv2-C Modify Bearer Request rate"
			::={ templateGtpPolicySEntry 87 }

			dropRlGtpUTunnelCreate OBJECT-TYPE
			SYNTAX  CounterBasedGauge64
			MAX-ACCESS read-only
			STATUS current
			DESCRIPTION  "Rate-limit Drop: GTP-U Tunnel Creation rate"
			::={ templateGtpPolicySEntry 88 }

			dropRlGtpUUplinkByte OBJECT-TYPE
			SYNTAX  CounterBasedGauge64
			MAX-ACCESS read-only
			STATUS current
			DESCRIPTION  "Rate-limit Drop: GTP-U Uplink byte rate"
			::={ templateGtpPolicySEntry 89 }

			dropRlGtpUUplinkPacket OBJECT-TYPE
			SYNTAX  CounterBasedGauge64
			MAX-ACCESS read-only
			STATUS current
			DESCRIPTION  "Rate-limit Drop: GTP-U Uplink packet rate"
			::={ templateGtpPolicySEntry 90 }

			dropRlGtpUDownlinkByte OBJECT-TYPE
			SYNTAX  CounterBasedGauge64
			MAX-ACCESS read-only
			STATUS current
			DESCRIPTION  "Rate-limit Drop: GTP-U Downlink byte rate"
			::={ templateGtpPolicySEntry 91 }

			dropRlGtpUDownlinkPacket OBJECT-TYPE
			SYNTAX  CounterBasedGauge64
			MAX-ACCESS read-only
			STATUS current
			DESCRIPTION  "Rate-limit Drop: GTP-U Downlink packet rate"
			::={ templateGtpPolicySEntry 92 }

			dropRlGtpUTotalByte OBJECT-TYPE
			SYNTAX  CounterBasedGauge64
			MAX-ACCESS read-only
			STATUS current
			DESCRIPTION  "Rate-limit Drop: GTP-U Total byte rate"
			::={ templateGtpPolicySEntry 93 }

			dropRlGtpUTotalPacket OBJECT-TYPE
			SYNTAX  CounterBasedGauge64
			MAX-ACCESS read-only
			STATUS current
			DESCRIPTION  "Rate-limit Drop: GTP-U Total packet rate"
			::={ templateGtpPolicySEntry 94 }

			dropRlGtpUMaxConcurrentTunnels OBJECT-TYPE
			SYNTAX  CounterBasedGauge64
			MAX-ACCESS read-only
			STATUS current
			DESCRIPTION  "Rate-limit Drop: GTP-U Concurrent Tunnels"
			::={ templateGtpPolicySEntry 95 }

END
