ACOS-LOGGING-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosLogging MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Logging OID for ACOS"
				::=  {  acosRootStats 117  }

acosLoggingLocalLog                 OBJECT IDENTIFIER ::= { acosLogging 15 }
acosLoggingLocalLogGlobal           OBJECT IDENTIFIER ::= { acosLoggingLocalLog 5 }
acosLoggingLocalLogGlobalS          OBJECT IDENTIFIER ::= { acosLoggingLocalLogGlobal 1 }

		enqueue OBJECT-TYPE
		SYNTAX  CounterBasedGauge64
		MAX-ACCESS read-only
		STATUS current
		DESCRIPTION  "Total local-log enqueue"
		::={ acosLoggingLocalLogGlobalS 1 }

		enqueueFull OBJECT-TYPE
		SYNTAX  CounterBasedGauge64
		MAX-ACCESS read-only
		STATUS current
		DESCRIPTION  "Total local-log queue full"
		::={ acosLoggingLocalLogGlobalS 2 }

		enqueueError OBJECT-TYPE
		SYNTAX  CounterBasedGauge64
		MAX-ACCESS read-only
		STATUS current
		DESCRIPTION  "Total local-log enqueue error"
		::={ acosLoggingLocalLogGlobalS 3 }

		dequeue OBJECT-TYPE
		SYNTAX  CounterBasedGauge64
		MAX-ACCESS read-only
		STATUS current
		DESCRIPTION  "Total local-log dequeue"
		::={ acosLoggingLocalLogGlobalS 4 }

		dequeueError OBJECT-TYPE
		SYNTAX  CounterBasedGauge64
		MAX-ACCESS read-only
		STATUS current
		DESCRIPTION  "Total local-log dequeue processing error"
		::={ acosLoggingLocalLogGlobalS 5 }

		rawLog OBJECT-TYPE
		SYNTAX  CounterBasedGauge64
		MAX-ACCESS read-only
		STATUS current
		DESCRIPTION  "Total local-log raw logs"
		::={ acosLoggingLocalLogGlobalS 6 }

		rawLogError OBJECT-TYPE
		SYNTAX  CounterBasedGauge64
		MAX-ACCESS read-only
		STATUS current
		DESCRIPTION  "Total raw log logging error"
		::={ acosLoggingLocalLogGlobalS 7 }

		logSummarized OBJECT-TYPE
		SYNTAX  CounterBasedGauge64
		MAX-ACCESS read-only
		STATUS current
		DESCRIPTION  "Total raw log summarized"
		::={ acosLoggingLocalLogGlobalS 8 }

		l1LogSummarized OBJECT-TYPE
		SYNTAX  CounterBasedGauge64
		MAX-ACCESS read-only
		STATUS current
		DESCRIPTION  "Total layer 1 log summarized"
		::={ acosLoggingLocalLogGlobalS 9 }

		l2LogSummarized OBJECT-TYPE
		SYNTAX  CounterBasedGauge64
		MAX-ACCESS read-only
		STATUS current
		DESCRIPTION  "Total layer 2 log summarized"
		::={ acosLoggingLocalLogGlobalS 10 }

		logSummarizedError OBJECT-TYPE
		SYNTAX  CounterBasedGauge64
		MAX-ACCESS read-only
		STATUS current
		DESCRIPTION  "Total local-log summarization error"
		::={ acosLoggingLocalLogGlobalS 11 }

		aamDb OBJECT-TYPE
		SYNTAX  CounterBasedGauge64
		MAX-ACCESS read-only
		STATUS current
		DESCRIPTION  "Total local-log AAM raw database"
		::={ acosLoggingLocalLogGlobalS 12 }

		epDb OBJECT-TYPE
		SYNTAX  CounterBasedGauge64
		MAX-ACCESS read-only
		STATUS current
		DESCRIPTION  "Total local-log EP raw database"
		::={ acosLoggingLocalLogGlobalS 13 }

		fwDb OBJECT-TYPE
		SYNTAX  CounterBasedGauge64
		MAX-ACCESS read-only
		STATUS current
		DESCRIPTION  "Total local-log Firewall raw database"
		::={ acosLoggingLocalLogGlobalS 15 }

		aamTopUserDb OBJECT-TYPE
		SYNTAX  CounterBasedGauge64
		MAX-ACCESS read-only
		STATUS current
		DESCRIPTION  "Total local-log AAM top user summary database"
		::={ acosLoggingLocalLogGlobalS 16 }

		epTopUserDb OBJECT-TYPE
		SYNTAX  CounterBasedGauge64
		MAX-ACCESS read-only
		STATUS current
		DESCRIPTION  "Total local-log EP top user summary database"
		::={ acosLoggingLocalLogGlobalS 17 }

		epTopSrcDb OBJECT-TYPE
		SYNTAX  CounterBasedGauge64
		MAX-ACCESS read-only
		STATUS current
		DESCRIPTION  "Total local-log EP top client summary database"
		::={ acosLoggingLocalLogGlobalS 18 }

		epTopDstDb OBJECT-TYPE
		SYNTAX  CounterBasedGauge64
		MAX-ACCESS read-only
		STATUS current
		DESCRIPTION  "Total local-log EP top destination summary database"
		::={ acosLoggingLocalLogGlobalS 19 }

		epTopDomainDb OBJECT-TYPE
		SYNTAX  CounterBasedGauge64
		MAX-ACCESS read-only
		STATUS current
		DESCRIPTION  "Total local-log EP top domain summary database"
		::={ acosLoggingLocalLogGlobalS 20 }

		epTopWebCategoryDb OBJECT-TYPE
		SYNTAX  CounterBasedGauge64
		MAX-ACCESS read-only
		STATUS current
		DESCRIPTION  "Total local-log EP top web-category summary database"
		::={ acosLoggingLocalLogGlobalS 21 }

		epTopHostDb OBJECT-TYPE
		SYNTAX  CounterBasedGauge64
		MAX-ACCESS read-only
		STATUS current
		DESCRIPTION  "Total local-log EP top host summary database"
		::={ acosLoggingLocalLogGlobalS 22 }

		fwTopAppDb OBJECT-TYPE
		SYNTAX  CounterBasedGauge64
		MAX-ACCESS read-only
		STATUS current
		DESCRIPTION  "Total local-log Firewall top application summary database"
		::={ acosLoggingLocalLogGlobalS 28 }

		fwTopSrcDb OBJECT-TYPE
		SYNTAX  CounterBasedGauge64
		MAX-ACCESS read-only
		STATUS current
		DESCRIPTION  "Total local-log Firewall top source summary database"
		::={ acosLoggingLocalLogGlobalS 29 }

		fwTopAppSrcDb OBJECT-TYPE
		SYNTAX  CounterBasedGauge64
		MAX-ACCESS read-only
		STATUS current
		DESCRIPTION  "Total local-log Firewall top application and source summary database"
		::={ acosLoggingLocalLogGlobalS 30 }

		fwTopCategoryDb OBJECT-TYPE
		SYNTAX  CounterBasedGauge64
		MAX-ACCESS read-only
		STATUS current
		DESCRIPTION  "Total local-log Firewall top category summary database"
		::={ acosLoggingLocalLogGlobalS 31 }

		dbErro OBJECT-TYPE
		SYNTAX  CounterBasedGauge64
		MAX-ACCESS read-only
		STATUS current
		DESCRIPTION  "Total local-log database create error"
		::={ acosLoggingLocalLogGlobalS 32 }

		query OBJECT-TYPE
		SYNTAX  CounterBasedGauge64
		MAX-ACCESS read-only
		STATUS current
		DESCRIPTION  "Total local-log axapi query"
		::={ acosLoggingLocalLogGlobalS 33 }

		response OBJECT-TYPE
		SYNTAX  CounterBasedGauge64
		MAX-ACCESS read-only
		STATUS current
		DESCRIPTION  "Total local-log axapi response"
		::={ acosLoggingLocalLogGlobalS 34 }

		queryError OBJECT-TYPE
		SYNTAX  CounterBasedGauge64
		MAX-ACCESS read-only
		STATUS current
		DESCRIPTION  "Total local-log axapi query error"
		::={ acosLoggingLocalLogGlobalS 35 }

		fwTopThrDb OBJECT-TYPE
		SYNTAX  CounterBasedGauge64
		MAX-ACCESS read-only
		STATUS current
		DESCRIPTION  "Total local-log Firewall top threat summary database"
		::={ acosLoggingLocalLogGlobalS 36 }

		fwTopThrSrcDb OBJECT-TYPE
		SYNTAX  CounterBasedGauge64
		MAX-ACCESS read-only
		STATUS current
		DESCRIPTION  "Total local-log Firewall top threat and source summary database"
		::={ acosLoggingLocalLogGlobalS 37 }

END
