ACOS-IPV6-IN-IPV4-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosIpv6InIpv4 MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Ipv6InIpv4 OID for ACOS"
				::=  {  acosRootStats 99  }

acosIpv6InIpv4Frag                  OBJECT IDENTIFIER ::= { acosIpv6InIpv4 1 }
acosIpv6InIpv4FragS                 OBJECT IDENTIFIER ::= { acosIpv6InIpv4Frag 1 }

		sessionInserted OBJECT-TYPE
		SYNTAX  CounterBasedGauge64
		MAX-ACCESS read-only
		STATUS current
		DESCRIPTION  "Session Inserted"
		::={ acosIpv6InIpv4FragS 1 }

		sessionExpired OBJECT-TYPE
		SYNTAX  CounterBasedGauge64
		MAX-ACCESS read-only
		STATUS current
		DESCRIPTION  "Session Expired"
		::={ acosIpv6InIpv4FragS 2 }

		icmpRcv OBJECT-TYPE
		SYNTAX  CounterBasedGauge64
		MAX-ACCESS read-only
		STATUS current
		DESCRIPTION  "ICMP Received"
		::={ acosIpv6InIpv4FragS 3 }

		icmpv6Rcv OBJECT-TYPE
		SYNTAX  CounterBasedGauge64
		MAX-ACCESS read-only
		STATUS current
		DESCRIPTION  "ICMPv6 Received"
		::={ acosIpv6InIpv4FragS 4 }

		udpRcv OBJECT-TYPE
		SYNTAX  CounterBasedGauge64
		MAX-ACCESS read-only
		STATUS current
		DESCRIPTION  "UDP Received"
		::={ acosIpv6InIpv4FragS 5 }

		tcpRcv OBJECT-TYPE
		SYNTAX  CounterBasedGauge64
		MAX-ACCESS read-only
		STATUS current
		DESCRIPTION  "TCP Received"
		::={ acosIpv6InIpv4FragS 6 }

		ipipRcv OBJECT-TYPE
		SYNTAX  CounterBasedGauge64
		MAX-ACCESS read-only
		STATUS current
		DESCRIPTION  "IP-in-IP Received"
		::={ acosIpv6InIpv4FragS 7 }

		ipv6ipRcv OBJECT-TYPE
		SYNTAX  CounterBasedGauge64
		MAX-ACCESS read-only
		STATUS current
		DESCRIPTION  "IPv6-in-IP Received"
		::={ acosIpv6InIpv4FragS 8 }

		otherRcv OBJECT-TYPE
		SYNTAX  CounterBasedGauge64
		MAX-ACCESS read-only
		STATUS current
		DESCRIPTION  "Other Received"
		::={ acosIpv6InIpv4FragS 9 }

		icmpDropped OBJECT-TYPE
		SYNTAX  CounterBasedGauge64
		MAX-ACCESS read-only
		STATUS current
		DESCRIPTION  "ICMP Dropped"
		::={ acosIpv6InIpv4FragS 10 }

		icmpv6Dropped OBJECT-TYPE
		SYNTAX  CounterBasedGauge64
		MAX-ACCESS read-only
		STATUS current
		DESCRIPTION  "ICMPv6 Dropped"
		::={ acosIpv6InIpv4FragS 11 }

		udpDropped OBJECT-TYPE
		SYNTAX  CounterBasedGauge64
		MAX-ACCESS read-only
		STATUS current
		DESCRIPTION  "UDP Dropped"
		::={ acosIpv6InIpv4FragS 12 }

		tcpDropped OBJECT-TYPE
		SYNTAX  CounterBasedGauge64
		MAX-ACCESS read-only
		STATUS current
		DESCRIPTION  "TCP Dropped"
		::={ acosIpv6InIpv4FragS 13 }

		ipipDropped OBJECT-TYPE
		SYNTAX  CounterBasedGauge64
		MAX-ACCESS read-only
		STATUS current
		DESCRIPTION  "IP-in-IP Dropped"
		::={ acosIpv6InIpv4FragS 14 }

		ipv6ipDropped OBJECT-TYPE
		SYNTAX  CounterBasedGauge64
		MAX-ACCESS read-only
		STATUS current
		DESCRIPTION  "IPv6-in-IP Dropped"
		::={ acosIpv6InIpv4FragS 15 }

		otherDropped OBJECT-TYPE
		SYNTAX  CounterBasedGauge64
		MAX-ACCESS read-only
		STATUS current
		DESCRIPTION  "Other Dropped"
		::={ acosIpv6InIpv4FragS 16 }

		overlapError OBJECT-TYPE
		SYNTAX  CounterBasedGauge64
		MAX-ACCESS read-only
		STATUS current
		DESCRIPTION  "Overlapping Fragment Dropped"
		::={ acosIpv6InIpv4FragS 17 }

		badIpLen OBJECT-TYPE
		SYNTAX  CounterBasedGauge64
		MAX-ACCESS read-only
		STATUS current
		DESCRIPTION  "Bad IP Length"
		::={ acosIpv6InIpv4FragS 18 }

		tooSmall OBJECT-TYPE
		SYNTAX  CounterBasedGauge64
		MAX-ACCESS read-only
		STATUS current
		DESCRIPTION  "Fragment Too Small Drop"
		::={ acosIpv6InIpv4FragS 19 }

		firstTcpTooSmall OBJECT-TYPE
		SYNTAX  CounterBasedGauge64
		MAX-ACCESS read-only
		STATUS current
		DESCRIPTION  "First TCP Fragment Too Small Drop"
		::={ acosIpv6InIpv4FragS 20 }

		firstL4TooSmall OBJECT-TYPE
		SYNTAX  CounterBasedGauge64
		MAX-ACCESS read-only
		STATUS current
		DESCRIPTION  "First L4 Fragment Too Small Drop"
		::={ acosIpv6InIpv4FragS 21 }

		totalSessionsExceeded OBJECT-TYPE
		SYNTAX  CounterBasedGauge64
		MAX-ACCESS read-only
		STATUS current
		DESCRIPTION  "Total Sessions Exceeded Drop"
		::={ acosIpv6InIpv4FragS 22 }

		noSessionMemory OBJECT-TYPE
		SYNTAX  CounterBasedGauge64
		MAX-ACCESS read-only
		STATUS current
		DESCRIPTION  "Out of Session Memory"
		::={ acosIpv6InIpv4FragS 23 }

		ipv6InIpv4FastAgingSet OBJECT-TYPE
		SYNTAX  CounterBasedGauge64
		MAX-ACCESS read-only
		STATUS current
		DESCRIPTION  "Fragmentation Fast Aging Set"
		::={ acosIpv6InIpv4FragS 24 }

		fastAgingUnset OBJECT-TYPE
		SYNTAX  CounterBasedGauge64
		MAX-ACCESS read-only
		STATUS current
		DESCRIPTION  "Fragmentation Fast Aging Unset"
		::={ acosIpv6InIpv4FragS 25 }

		fragmentQueueSuccess OBJECT-TYPE
		SYNTAX  CounterBasedGauge64
		MAX-ACCESS read-only
		STATUS current
		DESCRIPTION  "Fragment Queue Success"
		::={ acosIpv6InIpv4FragS 26 }

		unalignedLen OBJECT-TYPE
		SYNTAX  CounterBasedGauge64
		MAX-ACCESS read-only
		STATUS current
		DESCRIPTION  "Payload Length Unaligned"
		::={ acosIpv6InIpv4FragS 27 }

		exceededLen OBJECT-TYPE
		SYNTAX  CounterBasedGauge64
		MAX-ACCESS read-only
		STATUS current
		DESCRIPTION  "Payload Length Out of Bounds"
		::={ acosIpv6InIpv4FragS 28 }

		duplicateFirstFrag OBJECT-TYPE
		SYNTAX  CounterBasedGauge64
		MAX-ACCESS read-only
		STATUS current
		DESCRIPTION  "Duplicate First Fragment"
		::={ acosIpv6InIpv4FragS 29 }

		duplicateLastFrag OBJECT-TYPE
		SYNTAX  CounterBasedGauge64
		MAX-ACCESS read-only
		STATUS current
		DESCRIPTION  "Duplicate Last Fragment"
		::={ acosIpv6InIpv4FragS 30 }

		totalFragmentsExceeded OBJECT-TYPE
		SYNTAX  CounterBasedGauge64
		MAX-ACCESS read-only
		STATUS current
		DESCRIPTION  "Total Queued Fragments Exceeded"
		::={ acosIpv6InIpv4FragS 31 }

		fragmentQueueFailure OBJECT-TYPE
		SYNTAX  CounterBasedGauge64
		MAX-ACCESS read-only
		STATUS current
		DESCRIPTION  "Fragment Queue Failure"
		::={ acosIpv6InIpv4FragS 32 }

		reassemblySuccess OBJECT-TYPE
		SYNTAX  CounterBasedGauge64
		MAX-ACCESS read-only
		STATUS current
		DESCRIPTION  "Fragment Reassembly Success"
		::={ acosIpv6InIpv4FragS 33 }

		maxLenExceeded OBJECT-TYPE
		SYNTAX  CounterBasedGauge64
		MAX-ACCESS read-only
		STATUS current
		DESCRIPTION  "Fragment Max Data Length Exceeded"
		::={ acosIpv6InIpv4FragS 34 }

		reassemblyFailure OBJECT-TYPE
		SYNTAX  CounterBasedGauge64
		MAX-ACCESS read-only
		STATUS current
		DESCRIPTION  "Fragment Reassembly Failure"
		::={ acosIpv6InIpv4FragS 35 }

		policyDrop OBJECT-TYPE
		SYNTAX  CounterBasedGauge64
		MAX-ACCESS read-only
		STATUS current
		DESCRIPTION  "MTU Exceeded Policy Drop"
		::={ acosIpv6InIpv4FragS 36 }

		errorDrop OBJECT-TYPE
		SYNTAX  CounterBasedGauge64
		MAX-ACCESS read-only
		STATUS current
		DESCRIPTION  "Fragment Processing Drop"
		::={ acosIpv6InIpv4FragS 37 }

		highCpuThreshold OBJECT-TYPE
		SYNTAX  CounterBasedGauge64
		MAX-ACCESS read-only
		STATUS current
		DESCRIPTION  "High CPU Threshold Reached"
		::={ acosIpv6InIpv4FragS 38 }

		lowCpuThreshold OBJECT-TYPE
		SYNTAX  CounterBasedGauge64
		MAX-ACCESS read-only
		STATUS current
		DESCRIPTION  "Low CPU Threshold Reached"
		::={ acosIpv6InIpv4FragS 39 }

		cpuThresholdDrop OBJECT-TYPE
		SYNTAX  CounterBasedGauge64
		MAX-ACCESS read-only
		STATUS current
		DESCRIPTION  "High CPU Drop"
		::={ acosIpv6InIpv4FragS 40 }

		ipdEntryDrop OBJECT-TYPE
		SYNTAX  CounterBasedGauge64
		MAX-ACCESS read-only
		STATUS current
		DESCRIPTION  "DDoS Protection Drop"
		::={ acosIpv6InIpv4FragS 41 }

		maxPacketsExceeded OBJECT-TYPE
		SYNTAX  CounterBasedGauge64
		MAX-ACCESS read-only
		STATUS current
		DESCRIPTION  "Too Many Packets Per Reassembly Drop"
		::={ acosIpv6InIpv4FragS 42 }

		sessionPacketsExceeded OBJECT-TYPE
		SYNTAX  CounterBasedGauge64
		MAX-ACCESS read-only
		STATUS current
		DESCRIPTION  "Session Max Packets Exceeded"
		::={ acosIpv6InIpv4FragS 43 }

		fragSessionCount OBJECT-TYPE
		SYNTAX  CounterBasedGauge64
		MAX-ACCESS read-only
		STATUS current
		DESCRIPTION  "Fragmentation Session Count"
		::={ acosIpv6InIpv4FragS 44 }

		sctpRcv OBJECT-TYPE
		SYNTAX  CounterBasedGauge64
		MAX-ACCESS read-only
		STATUS current
		DESCRIPTION  "SCTP Received"
		::={ acosIpv6InIpv4FragS 45 }

		sctpDropped OBJECT-TYPE
		SYNTAX  CounterBasedGauge64
		MAX-ACCESS read-only
		STATUS current
		DESCRIPTION  "SCTP Dropped"
		::={ acosIpv6InIpv4FragS 46 }

		ipFragFirstGTPPacketTooSmall OBJECT-TYPE
		SYNTAX  CounterBasedGauge64
		MAX-ACCESS read-only
		STATUS current
		DESCRIPTION  "First GTP Fragment Too Small Drop"
		::={ acosIpv6InIpv4FragS 47 }

END
