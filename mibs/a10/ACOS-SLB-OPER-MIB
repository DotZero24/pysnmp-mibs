ACOS-SLB-OPER-MIB DEFINITIONS ::= BEGIN
	IMPORTS
		DisplayString, PhysAddress
		FROM SNMPv2-TC
	InetAddressType
		FROM INET-ADDRESS-MIB
	acosRootOper
		FROM A10-AX-MIB
	MODULE-IDENTITY, OBJECT-TYPE, Counter32, Integer32, Counter64, OBJECT-IDENTITY, NOTIFICATION-TYPE
		FROM SNMPv2-SMI;
		acosSlb MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Slb OID for ACOS"
				::=  {  acosRootOper 108  }

acosSlbSslStats                     OBJECT IDENTIFIER ::= { acosSlb 9 }

		sslModuleType OBJECT-TYPE
		SYNTAX  DisplayString
		MAX-ACCESS read-only
		STATUS current
		DESCRIPTION  "SSL module"
		::={ acosSlbSslStats 1 }

		configModuleType OBJECT-TYPE
		SYNTAX  DisplayString
		MAX-ACCESS read-only
		STATUS current
		DESCRIPTION  "Config module"
		::={ acosSlbSslStats 2 }

		thalesHsmStatus OBJECT-TYPE
		SYNTAX  DisplayString
		MAX-ACCESS read-only
		STATUS current
		DESCRIPTION  "Thales HSM Status"
		::={ acosSlbSslStats 3 }

		sslModulesCount OBJECT-TYPE
		SYNTAX  CounterBasedGauge64
		MAX-ACCESS read-only
		STATUS current
		DESCRIPTION  "Number of SSL modules"
		::={ acosSlbSslStats 4 }

		currentClientsideConnections OBJECT-TYPE
		SYNTAX  CounterBasedGauge64
		MAX-ACCESS read-only
		STATUS current
		DESCRIPTION  "Current clientside SSL connections"
		::={ acosSlbSslStats 5 }

		totalClientsideConnections OBJECT-TYPE
		SYNTAX  CounterBasedGauge64
		MAX-ACCESS read-only
		STATUS current
		DESCRIPTION  "Total clientside SSL connections"
		::={ acosSlbSslStats 6 }

		currentServersideConnections OBJECT-TYPE
		SYNTAX  CounterBasedGauge64
		MAX-ACCESS read-only
		STATUS current
		DESCRIPTION  "Current serverside SSL connections"
		::={ acosSlbSslStats 7 }

		totalServersideConnections OBJECT-TYPE
		SYNTAX  CounterBasedGauge64
		MAX-ACCESS read-only
		STATUS current
		DESCRIPTION  "Total serverside SSL connections"
		::={ acosSlbSslStats 8 }

		nonSslBypassConnections OBJECT-TYPE
		SYNTAX  CounterBasedGauge64
		MAX-ACCESS read-only
		STATUS current
		DESCRIPTION  "NON SSL bypass connections"
		::={ acosSlbSslStats 9 }

		totalReuseClientSsl OBJECT-TYPE
		SYNTAX  CounterBasedGauge64
		MAX-ACCESS read-only
		STATUS current
		DESCRIPTION  "Total times of stateful session reuse in client ssl"
		::={ acosSlbSslStats 10 }

		totalReuseServerSsl OBJECT-TYPE
		SYNTAX  CounterBasedGauge64
		MAX-ACCESS read-only
		STATUS current
		DESCRIPTION  "Total times of stateful session reuse in server ssl"
		::={ acosSlbSslStats 11 }

		totalReuseSessionTicketClientSsl OBJECT-TYPE
		SYNTAX  CounterBasedGauge64
		MAX-ACCESS read-only
		STATUS current
		DESCRIPTION  "Total times of stateless session reuse in client ssl"
		::={ acosSlbSslStats 12 }

		totalReuseSessionTicketServerSsl OBJECT-TYPE
		SYNTAX  CounterBasedGauge64
		MAX-ACCESS read-only
		STATUS current
		DESCRIPTION  "Total times of stateless session reuse in server ssl"
		::={ acosSlbSslStats 13 }

		totalClientsideEarlyDataConnections OBJECT-TYPE
		SYNTAX  CounterBasedGauge64
		MAX-ACCESS read-only
		STATUS current
		DESCRIPTION  "Total clientside early data connections"
		::={ acosSlbSslStats 14 }

		totalServersideEarlyDataConnections OBJECT-TYPE
		SYNTAX  CounterBasedGauge64
		MAX-ACCESS read-only
		STATUS current
		DESCRIPTION  "Total serverside early data connections"
		::={ acosSlbSslStats 15 }

		totalClientsideFailedEarlyDataConnections OBJECT-TYPE
		SYNTAX  CounterBasedGauge64
		MAX-ACCESS read-only
		STATUS current
		DESCRIPTION  "Total clientside failed early data connections"
		::={ acosSlbSslStats 16 }

		totalServersideFailedEarlyDataConnections OBJECT-TYPE
		SYNTAX  CounterBasedGauge64
		MAX-ACCESS read-only
		STATUS current
		DESCRIPTION  "Total serverside failed early data connections"
		::={ acosSlbSslStats 17 }

		failedHandshakes OBJECT-TYPE
		SYNTAX  CounterBasedGauge64
		MAX-ACCESS read-only
		STATUS current
		DESCRIPTION  "Failed SSL handshakes"
		::={ acosSlbSslStats 18 }

		failedCrypto OBJECT-TYPE
		SYNTAX  CounterBasedGauge64
		MAX-ACCESS read-only
		STATUS current
		DESCRIPTION  "Failed crypto operations"
		::={ acosSlbSslStats 19 }

		sslMemoryUsage OBJECT-TYPE
		SYNTAX  CounterBasedGauge64
		MAX-ACCESS read-only
		STATUS current
		DESCRIPTION  "SSL memory usage"
		::={ acosSlbSslStats 20 }

		serverCertErrors OBJECT-TYPE
		SYNTAX  CounterBasedGauge64
		MAX-ACCESS read-only
		STATUS current
		DESCRIPTION  "SSL server certificate errors"
		::={ acosSlbSslStats 21 }

		clientCertAuthFail OBJECT-TYPE
		SYNTAX  CounterBasedGauge64
		MAX-ACCESS read-only
		STATUS current
		DESCRIPTION  "SSL client certificate authorization failed"
		::={ acosSlbSslStats 22 }

		caVerificationFailures OBJECT-TYPE
		SYNTAX  CounterBasedGauge64
		MAX-ACCESS read-only
		STATUS current
		DESCRIPTION  "SSL fail CA verification"
		::={ acosSlbSslStats 23 }

		hwContextTotal OBJECT-TYPE
		SYNTAX  CounterBasedGauge64
		MAX-ACCESS read-only
		STATUS current
		DESCRIPTION  "HW Context Memory Total Count"
		::={ acosSlbSslStats 24 }

		hwContextUsage OBJECT-TYPE
		SYNTAX  CounterBasedGauge64
		MAX-ACCESS read-only
		STATUS current
		DESCRIPTION  "HW Context Memory In Use"
		::={ acosSlbSslStats 25 }

		hwContextAllocFail OBJECT-TYPE
		SYNTAX  CounterBasedGauge64
		MAX-ACCESS read-only
		STATUS current
		DESCRIPTION  "HW Context Memory alloc failed"
		::={ acosSlbSslStats 26 }

		hwRingFull OBJECT-TYPE
		SYNTAX  CounterBasedGauge64
		MAX-ACCESS read-only
		STATUS current
		DESCRIPTION  "HW ring full"
		::={ acosSlbSslStats 27 }

		recordTooBig OBJECT-TYPE
		SYNTAX  CounterBasedGauge64
		MAX-ACCESS read-only
		STATUS current
		DESCRIPTION  "Record too big"
		::={ acosSlbSslStats 28 }

		clientsslContextMallocFail OBJECT-TYPE
		SYNTAX  CounterBasedGauge64
		MAX-ACCESS read-only
		STATUS current
		DESCRIPTION  "Total client ssl context malloc failures"
		::={ acosSlbSslStats 29 }

		maxSslContexts OBJECT-TYPE
		SYNTAX  CounterBasedGauge64
		MAX-ACCESS read-only
		STATUS current
		DESCRIPTION  "Maximum SSL contexts"
		::={ acosSlbSslStats 30 }

		currSslContexts OBJECT-TYPE
		SYNTAX  CounterBasedGauge64
		MAX-ACCESS read-only
		STATUS current
		DESCRIPTION  "Current SSL contexts in use"
		::={ acosSlbSslStats 31 }

		staticSslContexts OBJECT-TYPE
		SYNTAX  CounterBasedGauge64
		MAX-ACCESS read-only
		STATUS current
		DESCRIPTION  "Current Static SSL contexts"
		::={ acosSlbSslStats 32 }

		dynamicSslContexts OBJECT-TYPE
		SYNTAX  CounterBasedGauge64
		MAX-ACCESS read-only
		STATUS current
		DESCRIPTION  "Current Dynamic SSL contexts"
		::={ acosSlbSslStats 33 }

		bypassFailsafeSessions OBJECT-TYPE
		SYNTAX  CounterBasedGauge64
		MAX-ACCESS read-only
		STATUS current
		DESCRIPTION  "Bypass failsafe SSL sessions"
		::={ acosSlbSslStats 34 }

		bypassUsenameSessions OBJECT-TYPE
		SYNTAX  CounterBasedGauge64
		MAX-ACCESS read-only
		STATUS current
		DESCRIPTION  "Bypass Username sessions"
		::={ acosSlbSslStats 35 }

		bypassAdGroupSessions OBJECT-TYPE
		SYNTAX  CounterBasedGauge64
		MAX-ACCESS read-only
		STATUS current
		DESCRIPTION  "Bypass AD-Group sessions"
		::={ acosSlbSslStats 36 }

		bypassSniSessions OBJECT-TYPE
		SYNTAX  CounterBasedGauge64
		MAX-ACCESS read-only
		STATUS current
		DESCRIPTION  "Bypass SNI sessions"
		::={ acosSlbSslStats 37 }

		bypassCertSubjectSessions OBJECT-TYPE
		SYNTAX  CounterBasedGauge64
		MAX-ACCESS read-only
		STATUS current
		DESCRIPTION  "Bypass Cert Subject sessions"
		::={ acosSlbSslStats 38 }

		bypassCertIssuerSessions OBJECT-TYPE
		SYNTAX  CounterBasedGauge64
		MAX-ACCESS read-only
		STATUS current
		DESCRIPTION  "Bypass Cert Issuer sessions"
		::={ acosSlbSslStats 39 }

		bypassCertSanSessions OBJECT-TYPE
		SYNTAX  CounterBasedGauge64
		MAX-ACCESS read-only
		STATUS current
		DESCRIPTION  "Bypass Cert SAN sessions"
		::={ acosSlbSslStats 40 }

		bypassNoSniSessions OBJECT-TYPE
		SYNTAX  CounterBasedGauge64
		MAX-ACCESS read-only
		STATUS current
		DESCRIPTION  "Bypass No SNI sessions"
		::={ acosSlbSslStats 41 }

		resetNoSniSessions OBJECT-TYPE
		SYNTAX  CounterBasedGauge64
		MAX-ACCESS read-only
		STATUS current
		DESCRIPTION  "Reset NO SNI sessions"
		::={ acosSlbSslStats 42 }

		bypassEsniSessions OBJECT-TYPE
		SYNTAX  CounterBasedGauge64
		MAX-ACCESS read-only
		STATUS current
		DESCRIPTION  "Bypass ESNI sessions"
		::={ acosSlbSslStats 43 }

		dropEsniSessions OBJECT-TYPE
		SYNTAX  CounterBasedGauge64
		MAX-ACCESS read-only
		STATUS current
		DESCRIPTION  "Drop ESNI sessions"
		::={ acosSlbSslStats 44 }

		bypassClientAuthSessions OBJECT-TYPE
		SYNTAX  CounterBasedGauge64
		MAX-ACCESS read-only
		STATUS current
		DESCRIPTION  "Bypass Client Auth sessions"
		::={ acosSlbSslStats 45 }

		sslHandshakeFailure OBJECT-TYPE
		SYNTAX  CounterBasedGauge64
		MAX-ACCESS read-only
		STATUS current
		DESCRIPTION  "Failed in SSL handshakes"
		::={ acosSlbSslStats 46 }

		cryptioOperations OBJECT-TYPE
		SYNTAX  CounterBasedGauge64
		MAX-ACCESS read-only
		STATUS current
		DESCRIPTION  "Crypto operations"
		::={ acosSlbSslStats 47 }

		tcpFailures OBJECT-TYPE
		SYNTAX  CounterBasedGauge64
		MAX-ACCESS read-only
		STATUS current
		DESCRIPTION  "Failed in TCP"
		::={ acosSlbSslStats 48 }

		certificateVerificationFailures OBJECT-TYPE
		SYNTAX  CounterBasedGauge64
		MAX-ACCESS read-only
		STATUS current
		DESCRIPTION  "Failed in Certificate Verification"
		::={ acosSlbSslStats 49 }

		certificateSigningFailures OBJECT-TYPE
		SYNTAX  CounterBasedGauge64
		MAX-ACCESS read-only
		STATUS current
		DESCRIPTION  "Failed in Certificate Signing"
		::={ acosSlbSslStats 50 }

		invalidOcspStaplingResponse OBJECT-TYPE
		SYNTAX  CounterBasedGauge64
		MAX-ACCESS read-only
		STATUS current
		DESCRIPTION  "Invalid OCSP Stapling Response"
		::={ acosSlbSslStats 51 }

		revokedOcspResponse OBJECT-TYPE
		SYNTAX  CounterBasedGauge64
		MAX-ACCESS read-only
		STATUS current
		DESCRIPTION  "Revoked OCSP Response"
		::={ acosSlbSslStats 52 }

		unsupportedSslVersion OBJECT-TYPE
		SYNTAX  CounterBasedGauge64
		MAX-ACCESS read-only
		STATUS current
		DESCRIPTION  "Unsupported SSL Version"
		::={ acosSlbSslStats 53 }

		clientSslFatalAlert OBJECT-TYPE
		SYNTAX  CounterBasedGauge64
		MAX-ACCESS read-only
		STATUS current
		DESCRIPTION  "Cert Fetch, SSL Fatal Alert"
		::={ acosSlbSslStats 54 }

		clientSslFinReset OBJECT-TYPE
		SYNTAX  CounterBasedGauge64
		MAX-ACCESS read-only
		STATUS current
		DESCRIPTION  "Cert Fetch, TCP FIN/RST"
		::={ acosSlbSslStats 55 }

		sslSessionFinReset OBJECT-TYPE
		SYNTAX  CounterBasedGauge64
		MAX-ACCESS read-only
		STATUS current
		DESCRIPTION  "SSL Session, TCP FIN/RST"
		::={ acosSlbSslStats 56 }

		serverSslFatalAlert OBJECT-TYPE
		SYNTAX  CounterBasedGauge64
		MAX-ACCESS read-only
		STATUS current
		DESCRIPTION  "Server SSL, SSL Fatal alert"
		::={ acosSlbSslStats 57 }

		serverSslFinReset OBJECT-TYPE
		SYNTAX  CounterBasedGauge64
		MAX-ACCESS read-only
		STATUS current
		DESCRIPTION  "Server SSL, TCP FIN/RST"
		::={ acosSlbSslStats 58 }

		clientSslInternalError OBJECT-TYPE
		SYNTAX  CounterBasedGauge64
		MAX-ACCESS read-only
		STATUS current
		DESCRIPTION  "Client SSL Internal Error"
		::={ acosSlbSslStats 59 }

		clientSslUnknownError OBJECT-TYPE
		SYNTAX  CounterBasedGauge64
		MAX-ACCESS read-only
		STATUS current
		DESCRIPTION  "Client SSL Unknown Error"
		::={ acosSlbSslStats 60 }

		serverSslInternalError OBJECT-TYPE
		SYNTAX  CounterBasedGauge64
		MAX-ACCESS read-only
		STATUS current
		DESCRIPTION  "Server SSL Internal Error"
		::={ acosSlbSslStats 61 }

		serverSslUnknownError OBJECT-TYPE
		SYNTAX  CounterBasedGauge64
		MAX-ACCESS read-only
		STATUS current
		DESCRIPTION  "Server SSL Unknown Error"
		::={ acosSlbSslStats 62 }

		fpFailHandshake OBJECT-TYPE
		SYNTAX  CounterBasedGauge64
		MAX-ACCESS read-only
		STATUS current
		DESCRIPTION  "Cert fetch, Fatal alert"
		::={ acosSlbSslStats 63 }

		fpFailTcpError OBJECT-TYPE
		SYNTAX  CounterBasedGauge64
		MAX-ACCESS read-only
		STATUS current
		DESCRIPTION  "Cert fetch, TCP FIN/RST"
		::={ acosSlbSslStats 64 }

		fpFailVerifyCert OBJECT-TYPE
		SYNTAX  CounterBasedGauge64
		MAX-ACCESS read-only
		STATUS current
		DESCRIPTION  "Cert fetch, validation error"
		::={ acosSlbSslStats 65 }

		fpFailAflex OBJECT-TYPE
		SYNTAX  CounterBasedGauge64
		MAX-ACCESS read-only
		STATUS current
		DESCRIPTION  "aFleX fail"
		::={ acosSlbSslStats 66 }

acosSlbSslError                     OBJECT IDENTIFIER ::= { acosSlb 62 }

		appDataInHandshake OBJECT-TYPE
		SYNTAX  CounterBasedGauge64
		MAX-ACCESS read-only
		STATUS current
		DESCRIPTION  "app data in handshake"
		::={ acosSlbSslError 1 }

		attemptToReuseSessInDiffContext OBJECT-TYPE
		SYNTAX  CounterBasedGauge64
		MAX-ACCESS read-only
		STATUS current
		DESCRIPTION  "attempt to reuse sess in diff context"
		::={ acosSlbSslError 2 }

		badAlertRecord OBJECT-TYPE
		SYNTAX  CounterBasedGauge64
		MAX-ACCESS read-only
		STATUS current
		DESCRIPTION  "bad alert record"
		::={ acosSlbSslError 3 }

		badAuthenticationType OBJECT-TYPE
		SYNTAX  CounterBasedGauge64
		MAX-ACCESS read-only
		STATUS current
		DESCRIPTION  "bad authentication type"
		::={ acosSlbSslError 4 }

		badChangeCipherSpec OBJECT-TYPE
		SYNTAX  CounterBasedGauge64
		MAX-ACCESS read-only
		STATUS current
		DESCRIPTION  "bad change cipher spec"
		::={ acosSlbSslError 5 }

		badChecksum OBJECT-TYPE
		SYNTAX  CounterBasedGauge64
		MAX-ACCESS read-only
		STATUS current
		DESCRIPTION  "bad checksum"
		::={ acosSlbSslError 6 }

		badDataReturnedByCallback OBJECT-TYPE
		SYNTAX  CounterBasedGauge64
		MAX-ACCESS read-only
		STATUS current
		DESCRIPTION  "bad data returned by callback"
		::={ acosSlbSslError 7 }

		badDecompression OBJECT-TYPE
		SYNTAX  CounterBasedGauge64
		MAX-ACCESS read-only
		STATUS current
		DESCRIPTION  "bad decompression"
		::={ acosSlbSslError 8 }

		badDhGLength OBJECT-TYPE
		SYNTAX  CounterBasedGauge64
		MAX-ACCESS read-only
		STATUS current
		DESCRIPTION  "bad dh g length"
		::={ acosSlbSslError 9 }

		badDhPubKeyLength OBJECT-TYPE
		SYNTAX  CounterBasedGauge64
		MAX-ACCESS read-only
		STATUS current
		DESCRIPTION  "bad dh pub key length"
		::={ acosSlbSslError 10 }

		badDhPLength OBJECT-TYPE
		SYNTAX  CounterBasedGauge64
		MAX-ACCESS read-only
		STATUS current
		DESCRIPTION  "bad dh p length"
		::={ acosSlbSslError 11 }

		badDigestLength OBJECT-TYPE
		SYNTAX  CounterBasedGauge64
		MAX-ACCESS read-only
		STATUS current
		DESCRIPTION  "bad digest length"
		::={ acosSlbSslError 12 }

		badDsaSignature OBJECT-TYPE
		SYNTAX  CounterBasedGauge64
		MAX-ACCESS read-only
		STATUS current
		DESCRIPTION  "bad dsa signature"
		::={ acosSlbSslError 13 }

		badHelloRequest OBJECT-TYPE
		SYNTAX  CounterBasedGauge64
		MAX-ACCESS read-only
		STATUS current
		DESCRIPTION  "bad hello request"
		::={ acosSlbSslError 14 }

		badLength OBJECT-TYPE
		SYNTAX  CounterBasedGauge64
		MAX-ACCESS read-only
		STATUS current
		DESCRIPTION  "bad length"
		::={ acosSlbSslError 15 }

		badMacDecode OBJECT-TYPE
		SYNTAX  CounterBasedGauge64
		MAX-ACCESS read-only
		STATUS current
		DESCRIPTION  "bad mac decode"
		::={ acosSlbSslError 16 }

		badMessageType OBJECT-TYPE
		SYNTAX  CounterBasedGauge64
		MAX-ACCESS read-only
		STATUS current
		DESCRIPTION  "bad message type"
		::={ acosSlbSslError 17 }

		badPacketLength OBJECT-TYPE
		SYNTAX  CounterBasedGauge64
		MAX-ACCESS read-only
		STATUS current
		DESCRIPTION  "bad packet length"
		::={ acosSlbSslError 18 }

		badProtocolVersionNumber OBJECT-TYPE
		SYNTAX  CounterBasedGauge64
		MAX-ACCESS read-only
		STATUS current
		DESCRIPTION  "bad protocol version number"
		::={ acosSlbSslError 19 }

		badResponseArgument OBJECT-TYPE
		SYNTAX  CounterBasedGauge64
		MAX-ACCESS read-only
		STATUS current
		DESCRIPTION  "bad response argument"
		::={ acosSlbSslError 20 }

		badRsaDecrypt OBJECT-TYPE
		SYNTAX  CounterBasedGauge64
		MAX-ACCESS read-only
		STATUS current
		DESCRIPTION  "bad rsa decrypt"
		::={ acosSlbSslError 21 }

		badRsaEncrypt OBJECT-TYPE
		SYNTAX  CounterBasedGauge64
		MAX-ACCESS read-only
		STATUS current
		DESCRIPTION  "bad rsa encrypt"
		::={ acosSlbSslError 22 }

		badRsaELength OBJECT-TYPE
		SYNTAX  CounterBasedGauge64
		MAX-ACCESS read-only
		STATUS current
		DESCRIPTION  "bad rsa e length"
		::={ acosSlbSslError 23 }

		badRsaModulusLength OBJECT-TYPE
		SYNTAX  CounterBasedGauge64
		MAX-ACCESS read-only
		STATUS current
		DESCRIPTION  "bad rsa modulus length"
		::={ acosSlbSslError 24 }

		badRsaSignature OBJECT-TYPE
		SYNTAX  CounterBasedGauge64
		MAX-ACCESS read-only
		STATUS current
		DESCRIPTION  "bad rsa signature"
		::={ acosSlbSslError 25 }

		badSignature OBJECT-TYPE
		SYNTAX  CounterBasedGauge64
		MAX-ACCESS read-only
		STATUS current
		DESCRIPTION  "bad signature"
		::={ acosSlbSslError 26 }

		badSslFiletype OBJECT-TYPE
		SYNTAX  CounterBasedGauge64
		MAX-ACCESS read-only
		STATUS current
		DESCRIPTION  "bad ssl filetype"
		::={ acosSlbSslError 27 }

		badSslSessionIdLength OBJECT-TYPE
		SYNTAX  CounterBasedGauge64
		MAX-ACCESS read-only
		STATUS current
		DESCRIPTION  "bad ssl session id length"
		::={ acosSlbSslError 28 }

		badState OBJECT-TYPE
		SYNTAX  CounterBasedGauge64
		MAX-ACCESS read-only
		STATUS current
		DESCRIPTION  "bad state"
		::={ acosSlbSslError 29 }

		badWriteRetry OBJECT-TYPE
		SYNTAX  CounterBasedGauge64
		MAX-ACCESS read-only
		STATUS current
		DESCRIPTION  "bad write retry"
		::={ acosSlbSslError 30 }

		bioNotSet OBJECT-TYPE
		SYNTAX  CounterBasedGauge64
		MAX-ACCESS read-only
		STATUS current
		DESCRIPTION  "bio not set"
		::={ acosSlbSslError 31 }

		blockCipherPadIsWrong OBJECT-TYPE
		SYNTAX  CounterBasedGauge64
		MAX-ACCESS read-only
		STATUS current
		DESCRIPTION  "block cipher pad is wrong"
		::={ acosSlbSslError 32 }

		bnLib OBJECT-TYPE
		SYNTAX  CounterBasedGauge64
		MAX-ACCESS read-only
		STATUS current
		DESCRIPTION  "bn lib"
		::={ acosSlbSslError 33 }

		caDnLengthMismatch OBJECT-TYPE
		SYNTAX  CounterBasedGauge64
		MAX-ACCESS read-only
		STATUS current
		DESCRIPTION  "ca dn length mismatch"
		::={ acosSlbSslError 34 }

		caDnTooLong OBJECT-TYPE
		SYNTAX  CounterBasedGauge64
		MAX-ACCESS read-only
		STATUS current
		DESCRIPTION  "ca dn too long"
		::={ acosSlbSslError 35 }

		ccsReceivedEarly OBJECT-TYPE
		SYNTAX  CounterBasedGauge64
		MAX-ACCESS read-only
		STATUS current
		DESCRIPTION  "ccs received early"
		::={ acosSlbSslError 36 }

		certificateVerifyFailed OBJECT-TYPE
		SYNTAX  CounterBasedGauge64
		MAX-ACCESS read-only
		STATUS current
		DESCRIPTION  "certificate verify failed"
		::={ acosSlbSslError 37 }

		certLengthMismatch OBJECT-TYPE
		SYNTAX  CounterBasedGauge64
		MAX-ACCESS read-only
		STATUS current
		DESCRIPTION  "cert length mismatch"
		::={ acosSlbSslError 38 }

		challengeIsDifferent OBJECT-TYPE
		SYNTAX  CounterBasedGauge64
		MAX-ACCESS read-only
		STATUS current
		DESCRIPTION  "challenge is different"
		::={ acosSlbSslError 39 }

		cipherCodeWrongLength OBJECT-TYPE
		SYNTAX  CounterBasedGauge64
		MAX-ACCESS read-only
		STATUS current
		DESCRIPTION  "cipher code wrong length"
		::={ acosSlbSslError 40 }

		cipherOrHashUnavailable OBJECT-TYPE
		SYNTAX  CounterBasedGauge64
		MAX-ACCESS read-only
		STATUS current
		DESCRIPTION  "cipher or hash unavailable"
		::={ acosSlbSslError 41 }

		cipherTableSrcError OBJECT-TYPE
		SYNTAX  CounterBasedGauge64
		MAX-ACCESS read-only
		STATUS current
		DESCRIPTION  "cipher table src error"
		::={ acosSlbSslError 42 }

		compressedLengthTooLong OBJECT-TYPE
		SYNTAX  CounterBasedGauge64
		MAX-ACCESS read-only
		STATUS current
		DESCRIPTION  "compressed length too long"
		::={ acosSlbSslError 43 }

		compressionFailure OBJECT-TYPE
		SYNTAX  CounterBasedGauge64
		MAX-ACCESS read-only
		STATUS current
		DESCRIPTION  "compression failure"
		::={ acosSlbSslError 44 }

		compressionLibraryError OBJECT-TYPE
		SYNTAX  CounterBasedGauge64
		MAX-ACCESS read-only
		STATUS current
		DESCRIPTION  "compression library error"
		::={ acosSlbSslError 45 }

		connectionIdIsDifferent OBJECT-TYPE
		SYNTAX  CounterBasedGauge64
		MAX-ACCESS read-only
		STATUS current
		DESCRIPTION  "connection id is different"
		::={ acosSlbSslError 46 }

		connectionTypeNotSet OBJECT-TYPE
		SYNTAX  CounterBasedGauge64
		MAX-ACCESS read-only
		STATUS current
		DESCRIPTION  "connection type not set"
		::={ acosSlbSslError 47 }

		dataBetweenCcsAndFinished OBJECT-TYPE
		SYNTAX  CounterBasedGauge64
		MAX-ACCESS read-only
		STATUS current
		DESCRIPTION  "data between ccs and finished"
		::={ acosSlbSslError 48 }

		dataLengthTooLong OBJECT-TYPE
		SYNTAX  CounterBasedGauge64
		MAX-ACCESS read-only
		STATUS current
		DESCRIPTION  "data length too long"
		::={ acosSlbSslError 49 }

		decryptionFailed OBJECT-TYPE
		SYNTAX  CounterBasedGauge64
		MAX-ACCESS read-only
		STATUS current
		DESCRIPTION  "decryption failed"
		::={ acosSlbSslError 50 }

		decryptionFailedOrBadRecordMac OBJECT-TYPE
		SYNTAX  CounterBasedGauge64
		MAX-ACCESS read-only
		STATUS current
		DESCRIPTION  "decryption failed or bad record mac"
		::={ acosSlbSslError 51 }

		dhPublicValueLengthIsWrong OBJECT-TYPE
		SYNTAX  CounterBasedGauge64
		MAX-ACCESS read-only
		STATUS current
		DESCRIPTION  "dh public value length is wrong"
		::={ acosSlbSslError 52 }

		digestCheckFailed OBJECT-TYPE
		SYNTAX  CounterBasedGauge64
		MAX-ACCESS read-only
		STATUS current
		DESCRIPTION  "digest check failed"
		::={ acosSlbSslError 53 }

		encryptedLengthTooLong OBJECT-TYPE
		SYNTAX  CounterBasedGauge64
		MAX-ACCESS read-only
		STATUS current
		DESCRIPTION  "encrypted length too long"
		::={ acosSlbSslError 54 }

		errorGeneratingTmpRsaKey OBJECT-TYPE
		SYNTAX  CounterBasedGauge64
		MAX-ACCESS read-only
		STATUS current
		DESCRIPTION  "error generating tmp rsa key"
		::={ acosSlbSslError 55 }

		errorInReceivedCipherList OBJECT-TYPE
		SYNTAX  CounterBasedGauge64
		MAX-ACCESS read-only
		STATUS current
		DESCRIPTION  "error in received cipher list"
		::={ acosSlbSslError 56 }

		excessiveMessageSize OBJECT-TYPE
		SYNTAX  CounterBasedGauge64
		MAX-ACCESS read-only
		STATUS current
		DESCRIPTION  "excessive message size"
		::={ acosSlbSslError 57 }

		extraDataInMessage OBJECT-TYPE
		SYNTAX  CounterBasedGauge64
		MAX-ACCESS read-only
		STATUS current
		DESCRIPTION  "extra data in message"
		::={ acosSlbSslError 58 }

		gotAFinBeforeACcs OBJECT-TYPE
		SYNTAX  CounterBasedGauge64
		MAX-ACCESS read-only
		STATUS current
		DESCRIPTION  "got a fin before a ccs"
		::={ acosSlbSslError 59 }

		httpsProxyRequest OBJECT-TYPE
		SYNTAX  CounterBasedGauge64
		MAX-ACCESS read-only
		STATUS current
		DESCRIPTION  "https proxy request"
		::={ acosSlbSslError 60 }

		httpRequest OBJECT-TYPE
		SYNTAX  CounterBasedGauge64
		MAX-ACCESS read-only
		STATUS current
		DESCRIPTION  "http request"
		::={ acosSlbSslError 61 }

		illegalPadding OBJECT-TYPE
		SYNTAX  CounterBasedGauge64
		MAX-ACCESS read-only
		STATUS current
		DESCRIPTION  "illegal padding"
		::={ acosSlbSslError 62 }

		inappropriateFallback OBJECT-TYPE
		SYNTAX  CounterBasedGauge64
		MAX-ACCESS read-only
		STATUS current
		DESCRIPTION  "inappropriate fallback"
		::={ acosSlbSslError 63 }

		invalidChallengeLength OBJECT-TYPE
		SYNTAX  CounterBasedGauge64
		MAX-ACCESS read-only
		STATUS current
		DESCRIPTION  "invalid challenge length"
		::={ acosSlbSslError 64 }

		invalidCommand OBJECT-TYPE
		SYNTAX  CounterBasedGauge64
		MAX-ACCESS read-only
		STATUS current
		DESCRIPTION  "invalid command"
		::={ acosSlbSslError 65 }

		invalidPurpose OBJECT-TYPE
		SYNTAX  CounterBasedGauge64
		MAX-ACCESS read-only
		STATUS current
		DESCRIPTION  "invalid purpose"
		::={ acosSlbSslError 66 }

		invalidStatusResponse OBJECT-TYPE
		SYNTAX  CounterBasedGauge64
		MAX-ACCESS read-only
		STATUS current
		DESCRIPTION  "invalid status response"
		::={ acosSlbSslError 67 }

		invalidTrust OBJECT-TYPE
		SYNTAX  CounterBasedGauge64
		MAX-ACCESS read-only
		STATUS current
		DESCRIPTION  "invalid trust"
		::={ acosSlbSslError 68 }

		keyArgTooLong OBJECT-TYPE
		SYNTAX  CounterBasedGauge64
		MAX-ACCESS read-only
		STATUS current
		DESCRIPTION  "key arg too long"
		::={ acosSlbSslError 69 }

		krb5 OBJECT-TYPE
		SYNTAX  CounterBasedGauge64
		MAX-ACCESS read-only
		STATUS current
		DESCRIPTION  "krb5"
		::={ acosSlbSslError 70 }

		krb5ClientCcPrincipal OBJECT-TYPE
		SYNTAX  CounterBasedGauge64
		MAX-ACCESS read-only
		STATUS current
		DESCRIPTION  "krb5 client cc principal"
		::={ acosSlbSslError 71 }

		krb5ClientGetCred OBJECT-TYPE
		SYNTAX  CounterBasedGauge64
		MAX-ACCESS read-only
		STATUS current
		DESCRIPTION  "krb5 client get cred"
		::={ acosSlbSslError 72 }

		krb5ClientInit OBJECT-TYPE
		SYNTAX  CounterBasedGauge64
		MAX-ACCESS read-only
		STATUS current
		DESCRIPTION  "krb5 client init"
		::={ acosSlbSslError 73 }

		krb5ClientMkReq OBJECT-TYPE
		SYNTAX  CounterBasedGauge64
		MAX-ACCESS read-only
		STATUS current
		DESCRIPTION  "krb5 client mk_req"
		::={ acosSlbSslError 74 }

		krb5ServerBadTicket OBJECT-TYPE
		SYNTAX  CounterBasedGauge64
		MAX-ACCESS read-only
		STATUS current
		DESCRIPTION  "krb5 server bad ticket"
		::={ acosSlbSslError 75 }

		krb5ServerInit OBJECT-TYPE
		SYNTAX  CounterBasedGauge64
		MAX-ACCESS read-only
		STATUS current
		DESCRIPTION  "krb5 server init"
		::={ acosSlbSslError 76 }

		krb5ServerRdReq OBJECT-TYPE
		SYNTAX  CounterBasedGauge64
		MAX-ACCESS read-only
		STATUS current
		DESCRIPTION  "krb5 server rd_req"
		::={ acosSlbSslError 77 }

		krb5ServerTktExpired OBJECT-TYPE
		SYNTAX  CounterBasedGauge64
		MAX-ACCESS read-only
		STATUS current
		DESCRIPTION  "krb5 server tkt expired"
		::={ acosSlbSslError 78 }

		krb5ServerTktNotYetValid OBJECT-TYPE
		SYNTAX  CounterBasedGauge64
		MAX-ACCESS read-only
		STATUS current
		DESCRIPTION  "krb5 server tkt not yet valid"
		::={ acosSlbSslError 79 }

		krb5ServerTktSkew OBJECT-TYPE
		SYNTAX  CounterBasedGauge64
		MAX-ACCESS read-only
		STATUS current
		DESCRIPTION  "krb5 server tkt skew"
		::={ acosSlbSslError 80 }

		lengthMismatch OBJECT-TYPE
		SYNTAX  CounterBasedGauge64
		MAX-ACCESS read-only
		STATUS current
		DESCRIPTION  "length mismatch"
		::={ acosSlbSslError 81 }

		lengthTooShort OBJECT-TYPE
		SYNTAX  CounterBasedGauge64
		MAX-ACCESS read-only
		STATUS current
		DESCRIPTION  "length too short"
		::={ acosSlbSslError 82 }

		libraryBug OBJECT-TYPE
		SYNTAX  CounterBasedGauge64
		MAX-ACCESS read-only
		STATUS current
		DESCRIPTION  "library bug"
		::={ acosSlbSslError 83 }

		libraryHasNoCiphers OBJECT-TYPE
		SYNTAX  CounterBasedGauge64
		MAX-ACCESS read-only
		STATUS current
		DESCRIPTION  "library has no ciphers"
		::={ acosSlbSslError 84 }

		mastKeyTooLong OBJECT-TYPE
		SYNTAX  CounterBasedGauge64
		MAX-ACCESS read-only
		STATUS current
		DESCRIPTION  "mast key too long"
		::={ acosSlbSslError 85 }

		messageTooLong OBJECT-TYPE
		SYNTAX  CounterBasedGauge64
		MAX-ACCESS read-only
		STATUS current
		DESCRIPTION  "message too long"
		::={ acosSlbSslError 86 }

		missingDhDsaCert OBJECT-TYPE
		SYNTAX  CounterBasedGauge64
		MAX-ACCESS read-only
		STATUS current
		DESCRIPTION  "missing dh dsa cert"
		::={ acosSlbSslError 87 }

		missingDhKey OBJECT-TYPE
		SYNTAX  CounterBasedGauge64
		MAX-ACCESS read-only
		STATUS current
		DESCRIPTION  "missing dh key"
		::={ acosSlbSslError 88 }

		missingDhRsaCert OBJECT-TYPE
		SYNTAX  CounterBasedGauge64
		MAX-ACCESS read-only
		STATUS current
		DESCRIPTION  "missing dh rsa cert"
		::={ acosSlbSslError 89 }

		missingDsaSigningCert OBJECT-TYPE
		SYNTAX  CounterBasedGauge64
		MAX-ACCESS read-only
		STATUS current
		DESCRIPTION  "missing dsa signing cert"
		::={ acosSlbSslError 90 }

		missingExportTmpDhKey OBJECT-TYPE
		SYNTAX  CounterBasedGauge64
		MAX-ACCESS read-only
		STATUS current
		DESCRIPTION  "missing export tmp dh key"
		::={ acosSlbSslError 91 }

		missingExportTmpRsaKey OBJECT-TYPE
		SYNTAX  CounterBasedGauge64
		MAX-ACCESS read-only
		STATUS current
		DESCRIPTION  "missing export tmp rsa key"
		::={ acosSlbSslError 92 }

		missingRsaCertificate OBJECT-TYPE
		SYNTAX  CounterBasedGauge64
		MAX-ACCESS read-only
		STATUS current
		DESCRIPTION  "missing rsa certificate"
		::={ acosSlbSslError 93 }

		missingRsaEncryptingCert OBJECT-TYPE
		SYNTAX  CounterBasedGauge64
		MAX-ACCESS read-only
		STATUS current
		DESCRIPTION  "missing rsa encrypting cert"
		::={ acosSlbSslError 94 }

		missingRsaSigningCert OBJECT-TYPE
		SYNTAX  CounterBasedGauge64
		MAX-ACCESS read-only
		STATUS current
		DESCRIPTION  "missing rsa signing cert"
		::={ acosSlbSslError 95 }

		missingTmpDhKey OBJECT-TYPE
		SYNTAX  CounterBasedGauge64
		MAX-ACCESS read-only
		STATUS current
		DESCRIPTION  "missing tmp dh key"
		::={ acosSlbSslError 96 }

		missingTmpRsaKey OBJECT-TYPE
		SYNTAX  CounterBasedGauge64
		MAX-ACCESS read-only
		STATUS current
		DESCRIPTION  "missing tmp rsa key"
		::={ acosSlbSslError 97 }

		missingTmpRsaPkey OBJECT-TYPE
		SYNTAX  CounterBasedGauge64
		MAX-ACCESS read-only
		STATUS current
		DESCRIPTION  "missing tmp rsa pkey"
		::={ acosSlbSslError 98 }

		missingVerifyMessage OBJECT-TYPE
		SYNTAX  CounterBasedGauge64
		MAX-ACCESS read-only
		STATUS current
		DESCRIPTION  "missing verify message"
		::={ acosSlbSslError 99 }

		nonSslv2InitialPacket OBJECT-TYPE
		SYNTAX  CounterBasedGauge64
		MAX-ACCESS read-only
		STATUS current
		DESCRIPTION  "non sslv2 initial packet"
		::={ acosSlbSslError 100 }

		noCertificatesReturned OBJECT-TYPE
		SYNTAX  CounterBasedGauge64
		MAX-ACCESS read-only
		STATUS current
		DESCRIPTION  "no certificates returned"
		::={ acosSlbSslError 101 }

		noCertificateAssigned OBJECT-TYPE
		SYNTAX  CounterBasedGauge64
		MAX-ACCESS read-only
		STATUS current
		DESCRIPTION  "no certificate assigned"
		::={ acosSlbSslError 102 }

		noCertificateReturned OBJECT-TYPE
		SYNTAX  CounterBasedGauge64
		MAX-ACCESS read-only
		STATUS current
		DESCRIPTION  "no certificate returned"
		::={ acosSlbSslError 103 }

		noCertificateSet OBJECT-TYPE
		SYNTAX  CounterBasedGauge64
		MAX-ACCESS read-only
		STATUS current
		DESCRIPTION  "no certificate set"
		::={ acosSlbSslError 104 }

		noCertificateSpecified OBJECT-TYPE
		SYNTAX  CounterBasedGauge64
		MAX-ACCESS read-only
		STATUS current
		DESCRIPTION  "no certificate specified"
		::={ acosSlbSslError 105 }

		noCiphersAvailable OBJECT-TYPE
		SYNTAX  CounterBasedGauge64
		MAX-ACCESS read-only
		STATUS current
		DESCRIPTION  "no ciphers available"
		::={ acosSlbSslError 106 }

		noCiphersPassed OBJECT-TYPE
		SYNTAX  CounterBasedGauge64
		MAX-ACCESS read-only
		STATUS current
		DESCRIPTION  "no ciphers passed"
		::={ acosSlbSslError 107 }

		noCiphersSpecified OBJECT-TYPE
		SYNTAX  CounterBasedGauge64
		MAX-ACCESS read-only
		STATUS current
		DESCRIPTION  "no ciphers specified"
		::={ acosSlbSslError 108 }

		noCipherList OBJECT-TYPE
		SYNTAX  CounterBasedGauge64
		MAX-ACCESS read-only
		STATUS current
		DESCRIPTION  "no cipher list"
		::={ acosSlbSslError 109 }

		noCipherMatch OBJECT-TYPE
		SYNTAX  CounterBasedGauge64
		MAX-ACCESS read-only
		STATUS current
		DESCRIPTION  "no cipher match"
		::={ acosSlbSslError 110 }

		noClientCertReceived OBJECT-TYPE
		SYNTAX  CounterBasedGauge64
		MAX-ACCESS read-only
		STATUS current
		DESCRIPTION  "no client cert received"
		::={ acosSlbSslError 111 }

		noCompressionSpecified OBJECT-TYPE
		SYNTAX  CounterBasedGauge64
		MAX-ACCESS read-only
		STATUS current
		DESCRIPTION  "no compression specified"
		::={ acosSlbSslError 112 }

		noMethodSpecified OBJECT-TYPE
		SYNTAX  CounterBasedGauge64
		MAX-ACCESS read-only
		STATUS current
		DESCRIPTION  "no method specified"
		::={ acosSlbSslError 113 }

		noPrivatekey OBJECT-TYPE
		SYNTAX  CounterBasedGauge64
		MAX-ACCESS read-only
		STATUS current
		DESCRIPTION  "no privatekey"
		::={ acosSlbSslError 114 }

		noPrivateKeyAssigned OBJECT-TYPE
		SYNTAX  CounterBasedGauge64
		MAX-ACCESS read-only
		STATUS current
		DESCRIPTION  "no private key assigned"
		::={ acosSlbSslError 115 }

		noProtocolsAvailable OBJECT-TYPE
		SYNTAX  CounterBasedGauge64
		MAX-ACCESS read-only
		STATUS current
		DESCRIPTION  "no protocols available"
		::={ acosSlbSslError 116 }

		noPublickey OBJECT-TYPE
		SYNTAX  CounterBasedGauge64
		MAX-ACCESS read-only
		STATUS current
		DESCRIPTION  "no publickey"
		::={ acosSlbSslError 117 }

		noSharedCipher OBJECT-TYPE
		SYNTAX  CounterBasedGauge64
		MAX-ACCESS read-only
		STATUS current
		DESCRIPTION  "no shared cipher"
		::={ acosSlbSslError 118 }

		noVerifyCallback OBJECT-TYPE
		SYNTAX  CounterBasedGauge64
		MAX-ACCESS read-only
		STATUS current
		DESCRIPTION  "no verify callback"
		::={ acosSlbSslError 119 }

		nullSslCtx OBJECT-TYPE
		SYNTAX  CounterBasedGauge64
		MAX-ACCESS read-only
		STATUS current
		DESCRIPTION  "null ssl ctx"
		::={ acosSlbSslError 120 }

		nullSslMethodPassed OBJECT-TYPE
		SYNTAX  CounterBasedGauge64
		MAX-ACCESS read-only
		STATUS current
		DESCRIPTION  "null ssl method passed"
		::={ acosSlbSslError 121 }

		oldSessionCipherNotReturned OBJECT-TYPE
		SYNTAX  CounterBasedGauge64
		MAX-ACCESS read-only
		STATUS current
		DESCRIPTION  "old session cipher not returned"
		::={ acosSlbSslError 122 }

		packetLengthTooLong OBJECT-TYPE
		SYNTAX  CounterBasedGauge64
		MAX-ACCESS read-only
		STATUS current
		DESCRIPTION  "packet length too long"
		::={ acosSlbSslError 123 }

		pathTooLong OBJECT-TYPE
		SYNTAX  CounterBasedGauge64
		MAX-ACCESS read-only
		STATUS current
		DESCRIPTION  "path too long"
		::={ acosSlbSslError 124 }

		peerDidNotReturnACertificate OBJECT-TYPE
		SYNTAX  CounterBasedGauge64
		MAX-ACCESS read-only
		STATUS current
		DESCRIPTION  "peer did not return a certificate"
		::={ acosSlbSslError 125 }

		peerError OBJECT-TYPE
		SYNTAX  CounterBasedGauge64
		MAX-ACCESS read-only
		STATUS current
		DESCRIPTION  "peer error"
		::={ acosSlbSslError 126 }

		peerErrorCertificate OBJECT-TYPE
		SYNTAX  CounterBasedGauge64
		MAX-ACCESS read-only
		STATUS current
		DESCRIPTION  "peer error certificate"
		::={ acosSlbSslError 127 }

		peerErrorNoCertificate OBJECT-TYPE
		SYNTAX  CounterBasedGauge64
		MAX-ACCESS read-only
		STATUS current
		DESCRIPTION  "peer error no certificate"
		::={ acosSlbSslError 128 }

		peerErrorNoCipher OBJECT-TYPE
		SYNTAX  CounterBasedGauge64
		MAX-ACCESS read-only
		STATUS current
		DESCRIPTION  "peer error no cipher"
		::={ acosSlbSslError 129 }

		peerErrorUnsupportedCertificateType OBJECT-TYPE
		SYNTAX  CounterBasedGauge64
		MAX-ACCESS read-only
		STATUS current
		DESCRIPTION  "peer error unsupported certificate type"
		::={ acosSlbSslError 130 }

		preMacLengthTooLong OBJECT-TYPE
		SYNTAX  CounterBasedGauge64
		MAX-ACCESS read-only
		STATUS current
		DESCRIPTION  "pre mac length too long"
		::={ acosSlbSslError 131 }

		problemsMappingCipherFunctions OBJECT-TYPE
		SYNTAX  CounterBasedGauge64
		MAX-ACCESS read-only
		STATUS current
		DESCRIPTION  "problems mapping cipher functions"
		::={ acosSlbSslError 132 }

		protocolIsShutdown OBJECT-TYPE
		SYNTAX  CounterBasedGauge64
		MAX-ACCESS read-only
		STATUS current
		DESCRIPTION  "protocol is shutdown"
		::={ acosSlbSslError 133 }

		publicKeyEncryptError OBJECT-TYPE
		SYNTAX  CounterBasedGauge64
		MAX-ACCESS read-only
		STATUS current
		DESCRIPTION  "public key encrypt error"
		::={ acosSlbSslError 134 }

		publicKeyIsNotRsa OBJECT-TYPE
		SYNTAX  CounterBasedGauge64
		MAX-ACCESS read-only
		STATUS current
		DESCRIPTION  "public key is not rsa"
		::={ acosSlbSslError 135 }

		publicKeyNotRsa OBJECT-TYPE
		SYNTAX  CounterBasedGauge64
		MAX-ACCESS read-only
		STATUS current
		DESCRIPTION  "public key not rsa"
		::={ acosSlbSslError 136 }

		readBioNotSet OBJECT-TYPE
		SYNTAX  CounterBasedGauge64
		MAX-ACCESS read-only
		STATUS current
		DESCRIPTION  "read bio not set"
		::={ acosSlbSslError 137 }

		readWrongPacketType OBJECT-TYPE
		SYNTAX  CounterBasedGauge64
		MAX-ACCESS read-only
		STATUS current
		DESCRIPTION  "read wrong packet type"
		::={ acosSlbSslError 138 }

		recordLengthMismatch OBJECT-TYPE
		SYNTAX  CounterBasedGauge64
		MAX-ACCESS read-only
		STATUS current
		DESCRIPTION  "record length mismatch"
		::={ acosSlbSslError 139 }

		recordTooLarge OBJECT-TYPE
		SYNTAX  CounterBasedGauge64
		MAX-ACCESS read-only
		STATUS current
		DESCRIPTION  "record too large"
		::={ acosSlbSslError 140 }

		recordTooSmall OBJECT-TYPE
		SYNTAX  CounterBasedGauge64
		MAX-ACCESS read-only
		STATUS current
		DESCRIPTION  "record too small"
		::={ acosSlbSslError 141 }

		requiredCipherMissing OBJECT-TYPE
		SYNTAX  CounterBasedGauge64
		MAX-ACCESS read-only
		STATUS current
		DESCRIPTION  "required cipher missing"
		::={ acosSlbSslError 142 }

		reuseCertLengthNotZero OBJECT-TYPE
		SYNTAX  CounterBasedGauge64
		MAX-ACCESS read-only
		STATUS current
		DESCRIPTION  "reuse cert length not zero"
		::={ acosSlbSslError 143 }

		reuseCertTypeNotZero OBJECT-TYPE
		SYNTAX  CounterBasedGauge64
		MAX-ACCESS read-only
		STATUS current
		DESCRIPTION  "reuse cert type not zero"
		::={ acosSlbSslError 144 }

		reuseCipherListNotZero OBJECT-TYPE
		SYNTAX  CounterBasedGauge64
		MAX-ACCESS read-only
		STATUS current
		DESCRIPTION  "reuse cipher list not zero"
		::={ acosSlbSslError 145 }

		scsvReceivedWhenRenegotiating OBJECT-TYPE
		SYNTAX  CounterBasedGauge64
		MAX-ACCESS read-only
		STATUS current
		DESCRIPTION  "scsv received when renegotiating"
		::={ acosSlbSslError 146 }

		sessionIdContextUninitialized OBJECT-TYPE
		SYNTAX  CounterBasedGauge64
		MAX-ACCESS read-only
		STATUS current
		DESCRIPTION  "session id context uninitialized"
		::={ acosSlbSslError 147 }

		shortRead OBJECT-TYPE
		SYNTAX  CounterBasedGauge64
		MAX-ACCESS read-only
		STATUS current
		DESCRIPTION  "short read"
		::={ acosSlbSslError 148 }

		signatureForNonSigningCertificate OBJECT-TYPE
		SYNTAX  CounterBasedGauge64
		MAX-ACCESS read-only
		STATUS current
		DESCRIPTION  "signature for non signing certificate"
		::={ acosSlbSslError 149 }

		ssl23DoingSessionIdReuse OBJECT-TYPE
		SYNTAX  CounterBasedGauge64
		MAX-ACCESS read-only
		STATUS current
		DESCRIPTION  "ssl23 doing session id reuse"
		::={ acosSlbSslError 150 }

		ssl2ConnectionIdTooLong OBJECT-TYPE
		SYNTAX  CounterBasedGauge64
		MAX-ACCESS read-only
		STATUS current
		DESCRIPTION  "ssl2 connection id too long"
		::={ acosSlbSslError 151 }

		ssl3SessionIdTooLong OBJECT-TYPE
		SYNTAX  CounterBasedGauge64
		MAX-ACCESS read-only
		STATUS current
		DESCRIPTION  "ssl3 session id too long"
		::={ acosSlbSslError 152 }

		ssl3SessionIdTooShort OBJECT-TYPE
		SYNTAX  CounterBasedGauge64
		MAX-ACCESS read-only
		STATUS current
		DESCRIPTION  "ssl3 session id too short"
		::={ acosSlbSslError 153 }

		sslv3AlertBadCertificate OBJECT-TYPE
		SYNTAX  CounterBasedGauge64
		MAX-ACCESS read-only
		STATUS current
		DESCRIPTION  "sslv3 alert bad certificate"
		::={ acosSlbSslError 154 }

		sslv3AlertBadRecordMac OBJECT-TYPE
		SYNTAX  CounterBasedGauge64
		MAX-ACCESS read-only
		STATUS current
		DESCRIPTION  "sslv3 alert bad record mac"
		::={ acosSlbSslError 155 }

		sslv3AlertCertificateExpired OBJECT-TYPE
		SYNTAX  CounterBasedGauge64
		MAX-ACCESS read-only
		STATUS current
		DESCRIPTION  "sslv3 alert certificate expired"
		::={ acosSlbSslError 156 }

		sslv3AlertCertificateRevoked OBJECT-TYPE
		SYNTAX  CounterBasedGauge64
		MAX-ACCESS read-only
		STATUS current
		DESCRIPTION  "sslv3 alert certificate revoked"
		::={ acosSlbSslError 157 }

		sslv3AlertCertificateUnknown OBJECT-TYPE
		SYNTAX  CounterBasedGauge64
		MAX-ACCESS read-only
		STATUS current
		DESCRIPTION  "sslv3 alert certificate unknown"
		::={ acosSlbSslError 158 }

		sslv3AlertDecompressionFailure OBJECT-TYPE
		SYNTAX  CounterBasedGauge64
		MAX-ACCESS read-only
		STATUS current
		DESCRIPTION  "sslv3 alert decompression failure"
		::={ acosSlbSslError 159 }

		sslv3AlertHandshakeFailure OBJECT-TYPE
		SYNTAX  CounterBasedGauge64
		MAX-ACCESS read-only
		STATUS current
		DESCRIPTION  "sslv3 alert handshake failure"
		::={ acosSlbSslError 160 }

		sslv3AlertIllegalParameter OBJECT-TYPE
		SYNTAX  CounterBasedGauge64
		MAX-ACCESS read-only
		STATUS current
		DESCRIPTION  "sslv3 alert illegal parameter"
		::={ acosSlbSslError 161 }

		sslv3AlertNoCertificate OBJECT-TYPE
		SYNTAX  CounterBasedGauge64
		MAX-ACCESS read-only
		STATUS current
		DESCRIPTION  "sslv3 alert no certificate"
		::={ acosSlbSslError 162 }

		sslv3AlertPeerErrorCert OBJECT-TYPE
		SYNTAX  CounterBasedGauge64
		MAX-ACCESS read-only
		STATUS current
		DESCRIPTION  "sslv3 alert peer error cert"
		::={ acosSlbSslError 163 }

		sslv3AlertPeerErrorNoCert OBJECT-TYPE
		SYNTAX  CounterBasedGauge64
		MAX-ACCESS read-only
		STATUS current
		DESCRIPTION  "sslv3 alert peer error no cert"
		::={ acosSlbSslError 164 }

		sslv3AlertPeerErrorNoCipher OBJECT-TYPE
		SYNTAX  CounterBasedGauge64
		MAX-ACCESS read-only
		STATUS current
		DESCRIPTION  "sslv3 alert peer error no cipher"
		::={ acosSlbSslError 165 }

		sslv3AlertPeerErrorUnsuppCertType OBJECT-TYPE
		SYNTAX  CounterBasedGauge64
		MAX-ACCESS read-only
		STATUS current
		DESCRIPTION  "sslv3 alert peer error unsupp cert type"
		::={ acosSlbSslError 166 }

		sslv3AlertUnexpectedMsg OBJECT-TYPE
		SYNTAX  CounterBasedGauge64
		MAX-ACCESS read-only
		STATUS current
		DESCRIPTION  "sslv3 alert unexpected msg"
		::={ acosSlbSslError 167 }

		sslv3AlertUnknownRemoteErrType OBJECT-TYPE
		SYNTAX  CounterBasedGauge64
		MAX-ACCESS read-only
		STATUS current
		DESCRIPTION  "sslv3 alert unknown remote err type"
		::={ acosSlbSslError 168 }

		sslv3AlertUnspportedCert OBJECT-TYPE
		SYNTAX  CounterBasedGauge64
		MAX-ACCESS read-only
		STATUS current
		DESCRIPTION  "sslv3 alert unspported cert"
		::={ acosSlbSslError 169 }

		sslCtxHasNoDefaultSslVersion OBJECT-TYPE
		SYNTAX  CounterBasedGauge64
		MAX-ACCESS read-only
		STATUS current
		DESCRIPTION  "ssl ctx has no default ssl version"
		::={ acosSlbSslError 170 }

		sslHandshakeFailure OBJECT-TYPE
		SYNTAX  CounterBasedGauge64
		MAX-ACCESS read-only
		STATUS current
		DESCRIPTION  "ssl handshake failure"
		::={ acosSlbSslError 171 }

		sslLibraryHasNoCiphers OBJECT-TYPE
		SYNTAX  CounterBasedGauge64
		MAX-ACCESS read-only
		STATUS current
		DESCRIPTION  "ssl library has no ciphers"
		::={ acosSlbSslError 172 }

		sslSessionIdCallbackFailed OBJECT-TYPE
		SYNTAX  CounterBasedGauge64
		MAX-ACCESS read-only
		STATUS current
		DESCRIPTION  "ssl session id callback failed"
		::={ acosSlbSslError 173 }

		sslSessionIdConflict OBJECT-TYPE
		SYNTAX  CounterBasedGauge64
		MAX-ACCESS read-only
		STATUS current
		DESCRIPTION  "ssl session id conflict"
		::={ acosSlbSslError 174 }

		sslSessionIdContextTooLong OBJECT-TYPE
		SYNTAX  CounterBasedGauge64
		MAX-ACCESS read-only
		STATUS current
		DESCRIPTION  "ssl session id context too long"
		::={ acosSlbSslError 175 }

		sslSessionIdHasBadLength OBJECT-TYPE
		SYNTAX  CounterBasedGauge64
		MAX-ACCESS read-only
		STATUS current
		DESCRIPTION  "ssl session id has bad length"
		::={ acosSlbSslError 176 }

		sslSessionIdIsDifferent OBJECT-TYPE
		SYNTAX  CounterBasedGauge64
		MAX-ACCESS read-only
		STATUS current
		DESCRIPTION  "ssl session id is different"
		::={ acosSlbSslError 177 }

		tlsv1AlertAccessDenied OBJECT-TYPE
		SYNTAX  CounterBasedGauge64
		MAX-ACCESS read-only
		STATUS current
		DESCRIPTION  "tlsv1 alert access denied"
		::={ acosSlbSslError 178 }

		tlsv1AlertDecodeError OBJECT-TYPE
		SYNTAX  CounterBasedGauge64
		MAX-ACCESS read-only
		STATUS current
		DESCRIPTION  "tlsv1 alert decode error"
		::={ acosSlbSslError 179 }

		tlsv1AlertDecryptionFailed OBJECT-TYPE
		SYNTAX  CounterBasedGauge64
		MAX-ACCESS read-only
		STATUS current
		DESCRIPTION  "tlsv1 alert decryption failed"
		::={ acosSlbSslError 180 }

		tlsv1AlertDecryptError OBJECT-TYPE
		SYNTAX  CounterBasedGauge64
		MAX-ACCESS read-only
		STATUS current
		DESCRIPTION  "tlsv1 alert decrypt error"
		::={ acosSlbSslError 181 }

		tlsv1AlertExportRestriction OBJECT-TYPE
		SYNTAX  CounterBasedGauge64
		MAX-ACCESS read-only
		STATUS current
		DESCRIPTION  "tlsv1 alert export restriction"
		::={ acosSlbSslError 182 }

		tlsv1AlertInsufficientSecurity OBJECT-TYPE
		SYNTAX  CounterBasedGauge64
		MAX-ACCESS read-only
		STATUS current
		DESCRIPTION  "tlsv1 alert insufficient security"
		::={ acosSlbSslError 183 }

		tlsv1AlertInternalError OBJECT-TYPE
		SYNTAX  CounterBasedGauge64
		MAX-ACCESS read-only
		STATUS current
		DESCRIPTION  "tlsv1 alert internal error"
		::={ acosSlbSslError 184 }

		tlsv1AlertNoRenegotiation OBJECT-TYPE
		SYNTAX  CounterBasedGauge64
		MAX-ACCESS read-only
		STATUS current
		DESCRIPTION  "tlsv1 alert no renegotiation"
		::={ acosSlbSslError 185 }

		tlsv1AlertProtocolVersion OBJECT-TYPE
		SYNTAX  CounterBasedGauge64
		MAX-ACCESS read-only
		STATUS current
		DESCRIPTION  "tlsv1 alert protocol version"
		::={ acosSlbSslError 186 }

		tlsv1AlertRecordOverflow OBJECT-TYPE
		SYNTAX  CounterBasedGauge64
		MAX-ACCESS read-only
		STATUS current
		DESCRIPTION  "tlsv1 alert record overflow"
		::={ acosSlbSslError 187 }

		tlsv1AlertUnknownCa OBJECT-TYPE
		SYNTAX  CounterBasedGauge64
		MAX-ACCESS read-only
		STATUS current
		DESCRIPTION  "tlsv1 alert unknown ca"
		::={ acosSlbSslError 188 }

		tlsv1AlertUserCancelled OBJECT-TYPE
		SYNTAX  CounterBasedGauge64
		MAX-ACCESS read-only
		STATUS current
		DESCRIPTION  "tlsv1 alert user cancelled"
		::={ acosSlbSslError 189 }

		tlsClientCertReqWithAnonCipher OBJECT-TYPE
		SYNTAX  CounterBasedGauge64
		MAX-ACCESS read-only
		STATUS current
		DESCRIPTION  "tls client cert req with anon cipher"
		::={ acosSlbSslError 190 }

		tlsPeerDidNotRespondWithCertList OBJECT-TYPE
		SYNTAX  CounterBasedGauge64
		MAX-ACCESS read-only
		STATUS current
		DESCRIPTION  "tls peer did not respond with cert list"
		::={ acosSlbSslError 191 }

		tlsRsaEncryptedValueLengthIsWrong OBJECT-TYPE
		SYNTAX  CounterBasedGauge64
		MAX-ACCESS read-only
		STATUS current
		DESCRIPTION  "tls rsa encrypted value length is wrong"
		::={ acosSlbSslError 192 }

		triedToUseUnsupportedCipher OBJECT-TYPE
		SYNTAX  CounterBasedGauge64
		MAX-ACCESS read-only
		STATUS current
		DESCRIPTION  "tried to use unsupported cipher"
		::={ acosSlbSslError 193 }

		unableToDecodeDhCerts OBJECT-TYPE
		SYNTAX  CounterBasedGauge64
		MAX-ACCESS read-only
		STATUS current
		DESCRIPTION  "unable to decode dh certs"
		::={ acosSlbSslError 194 }

		unableToExtractPublicKey OBJECT-TYPE
		SYNTAX  CounterBasedGauge64
		MAX-ACCESS read-only
		STATUS current
		DESCRIPTION  "unable to extract public key"
		::={ acosSlbSslError 195 }

		unableToFindDhParameters OBJECT-TYPE
		SYNTAX  CounterBasedGauge64
		MAX-ACCESS read-only
		STATUS current
		DESCRIPTION  "unable to find dh parameters"
		::={ acosSlbSslError 196 }

		unableToFindPublicKeyParameters OBJECT-TYPE
		SYNTAX  CounterBasedGauge64
		MAX-ACCESS read-only
		STATUS current
		DESCRIPTION  "unable to find public key parameters"
		::={ acosSlbSslError 197 }

		unableToFindSslMethod OBJECT-TYPE
		SYNTAX  CounterBasedGauge64
		MAX-ACCESS read-only
		STATUS current
		DESCRIPTION  "unable to find ssl method"
		::={ acosSlbSslError 198 }

		unableToLoadSsl2Md5Routines OBJECT-TYPE
		SYNTAX  CounterBasedGauge64
		MAX-ACCESS read-only
		STATUS current
		DESCRIPTION  "unable to load ssl2 md5 routines"
		::={ acosSlbSslError 199 }

		unableToLoadSsl3Md5Routines OBJECT-TYPE
		SYNTAX  CounterBasedGauge64
		MAX-ACCESS read-only
		STATUS current
		DESCRIPTION  "unable to load ssl3 md5 routines"
		::={ acosSlbSslError 200 }

		unableToLoadSsl3Sha1Routines OBJECT-TYPE
		SYNTAX  CounterBasedGauge64
		MAX-ACCESS read-only
		STATUS current
		DESCRIPTION  "unable to load ssl3 sha1 routines"
		::={ acosSlbSslError 201 }

		unexpectedMessage OBJECT-TYPE
		SYNTAX  CounterBasedGauge64
		MAX-ACCESS read-only
		STATUS current
		DESCRIPTION  "unexpected message"
		::={ acosSlbSslError 202 }

		unexpectedRecord OBJECT-TYPE
		SYNTAX  CounterBasedGauge64
		MAX-ACCESS read-only
		STATUS current
		DESCRIPTION  "unexpected record"
		::={ acosSlbSslError 203 }

		uninitialized OBJECT-TYPE
		SYNTAX  CounterBasedGauge64
		MAX-ACCESS read-only
		STATUS current
		DESCRIPTION  "uninitialized"
		::={ acosSlbSslError 204 }

		unknownAlertType OBJECT-TYPE
		SYNTAX  CounterBasedGauge64
		MAX-ACCESS read-only
		STATUS current
		DESCRIPTION  "unknown alert type"
		::={ acosSlbSslError 205 }

		unknownCertificateType OBJECT-TYPE
		SYNTAX  CounterBasedGauge64
		MAX-ACCESS read-only
		STATUS current
		DESCRIPTION  "unknown certificate type"
		::={ acosSlbSslError 206 }

		unknownCipherReturned OBJECT-TYPE
		SYNTAX  CounterBasedGauge64
		MAX-ACCESS read-only
		STATUS current
		DESCRIPTION  "unknown cipher returned"
		::={ acosSlbSslError 207 }

		unknownCipherType OBJECT-TYPE
		SYNTAX  CounterBasedGauge64
		MAX-ACCESS read-only
		STATUS current
		DESCRIPTION  "unknown cipher type"
		::={ acosSlbSslError 208 }

		unknownKeyExchangeType OBJECT-TYPE
		SYNTAX  CounterBasedGauge64
		MAX-ACCESS read-only
		STATUS current
		DESCRIPTION  "unknown key exchange type"
		::={ acosSlbSslError 209 }

		unknownPkeyType OBJECT-TYPE
		SYNTAX  CounterBasedGauge64
		MAX-ACCESS read-only
		STATUS current
		DESCRIPTION  "unknown pkey type"
		::={ acosSlbSslError 210 }

		unknownProtocol OBJECT-TYPE
		SYNTAX  CounterBasedGauge64
		MAX-ACCESS read-only
		STATUS current
		DESCRIPTION  "unknown protocol"
		::={ acosSlbSslError 211 }

		unknownRemoteErrorType OBJECT-TYPE
		SYNTAX  CounterBasedGauge64
		MAX-ACCESS read-only
		STATUS current
		DESCRIPTION  "unknown remote error type"
		::={ acosSlbSslError 212 }

		unknownSslVersion OBJECT-TYPE
		SYNTAX  CounterBasedGauge64
		MAX-ACCESS read-only
		STATUS current
		DESCRIPTION  "unknown ssl version"
		::={ acosSlbSslError 213 }

		unknownState OBJECT-TYPE
		SYNTAX  CounterBasedGauge64
		MAX-ACCESS read-only
		STATUS current
		DESCRIPTION  "unknown state"
		::={ acosSlbSslError 214 }

		unsupportedCipher OBJECT-TYPE
		SYNTAX  CounterBasedGauge64
		MAX-ACCESS read-only
		STATUS current
		DESCRIPTION  "unsupported cipher"
		::={ acosSlbSslError 215 }

		unsupportedCompressionAlgorithm OBJECT-TYPE
		SYNTAX  CounterBasedGauge64
		MAX-ACCESS read-only
		STATUS current
		DESCRIPTION  "unsupported compression algorithm"
		::={ acosSlbSslError 216 }

		unsupportedOption OBJECT-TYPE
		SYNTAX  CounterBasedGauge64
		MAX-ACCESS read-only
		STATUS current
		DESCRIPTION  "unsupported option"
		::={ acosSlbSslError 217 }

		unsupportedProtocol OBJECT-TYPE
		SYNTAX  CounterBasedGauge64
		MAX-ACCESS read-only
		STATUS current
		DESCRIPTION  "unsupported protocol"
		::={ acosSlbSslError 218 }

		unsupportedSslVersion OBJECT-TYPE
		SYNTAX  CounterBasedGauge64
		MAX-ACCESS read-only
		STATUS current
		DESCRIPTION  "unsupported ssl version"
		::={ acosSlbSslError 219 }

		unsupportedStatusType OBJECT-TYPE
		SYNTAX  CounterBasedGauge64
		MAX-ACCESS read-only
		STATUS current
		DESCRIPTION  "unsupported status type"
		::={ acosSlbSslError 220 }

		writeBioNotSet OBJECT-TYPE
		SYNTAX  CounterBasedGauge64
		MAX-ACCESS read-only
		STATUS current
		DESCRIPTION  "write bio not set"
		::={ acosSlbSslError 221 }

		wrongCipherReturned OBJECT-TYPE
		SYNTAX  CounterBasedGauge64
		MAX-ACCESS read-only
		STATUS current
		DESCRIPTION  "wrong cipher returned"
		::={ acosSlbSslError 222 }

		wrongMessageType OBJECT-TYPE
		SYNTAX  CounterBasedGauge64
		MAX-ACCESS read-only
		STATUS current
		DESCRIPTION  "wrong message type"
		::={ acosSlbSslError 223 }

		wrongNumberOfKeyBits OBJECT-TYPE
		SYNTAX  CounterBasedGauge64
		MAX-ACCESS read-only
		STATUS current
		DESCRIPTION  "wrong number of key bits"
		::={ acosSlbSslError 224 }

		wrongSignatureLength OBJECT-TYPE
		SYNTAX  CounterBasedGauge64
		MAX-ACCESS read-only
		STATUS current
		DESCRIPTION  "wrong signature length"
		::={ acosSlbSslError 225 }

		wrongSignatureSize OBJECT-TYPE
		SYNTAX  CounterBasedGauge64
		MAX-ACCESS read-only
		STATUS current
		DESCRIPTION  "wrong signature size"
		::={ acosSlbSslError 226 }

		wrongSslVersion OBJECT-TYPE
		SYNTAX  CounterBasedGauge64
		MAX-ACCESS read-only
		STATUS current
		DESCRIPTION  "wrong ssl version"
		::={ acosSlbSslError 227 }

		wrongVersionNumber OBJECT-TYPE
		SYNTAX  CounterBasedGauge64
		MAX-ACCESS read-only
		STATUS current
		DESCRIPTION  "wrong version number"
		::={ acosSlbSslError 228 }

		x509Lib OBJECT-TYPE
		SYNTAX  CounterBasedGauge64
		MAX-ACCESS read-only
		STATUS current
		DESCRIPTION  "x509 lib"
		::={ acosSlbSslError 229 }

		x509VerificationSetupProblems OBJECT-TYPE
		SYNTAX  CounterBasedGauge64
		MAX-ACCESS read-only
		STATUS current
		DESCRIPTION  "x509 verification setup problems"
		::={ acosSlbSslError 230 }

		clienthelloTlsext OBJECT-TYPE
		SYNTAX  CounterBasedGauge64
		MAX-ACCESS read-only
		STATUS current
		DESCRIPTION  "clienthello tlsext"
		::={ acosSlbSslError 231 }

		parseTlsext OBJECT-TYPE
		SYNTAX  CounterBasedGauge64
		MAX-ACCESS read-only
		STATUS current
		DESCRIPTION  "parse tlsext"
		::={ acosSlbSslError 232 }

		serverhelloTlsext OBJECT-TYPE
		SYNTAX  CounterBasedGauge64
		MAX-ACCESS read-only
		STATUS current
		DESCRIPTION  "serverhello tlsext"
		::={ acosSlbSslError 233 }

		ssl3ExtInvalidServername OBJECT-TYPE
		SYNTAX  CounterBasedGauge64
		MAX-ACCESS read-only
		STATUS current
		DESCRIPTION  "ssl3 ext invalid servername"
		::={ acosSlbSslError 234 }

		ssl3ExtInvalidServernameType OBJECT-TYPE
		SYNTAX  CounterBasedGauge64
		MAX-ACCESS read-only
		STATUS current
		DESCRIPTION  "ssl3 ext invalid servername type"
		::={ acosSlbSslError 235 }

		multipleSgcRestarts OBJECT-TYPE
		SYNTAX  CounterBasedGauge64
		MAX-ACCESS read-only
		STATUS current
		DESCRIPTION  "multiple sgc restarts"
		::={ acosSlbSslError 236 }

		tlsInvalidEcpointformatList OBJECT-TYPE
		SYNTAX  CounterBasedGauge64
		MAX-ACCESS read-only
		STATUS current
		DESCRIPTION  "tls invalid ecpointformat list"
		::={ acosSlbSslError 237 }

		badEccCert OBJECT-TYPE
		SYNTAX  CounterBasedGauge64
		MAX-ACCESS read-only
		STATUS current
		DESCRIPTION  "bad ecc cert"
		::={ acosSlbSslError 238 }

		badEcdsaSig OBJECT-TYPE
		SYNTAX  CounterBasedGauge64
		MAX-ACCESS read-only
		STATUS current
		DESCRIPTION  "bad ecdsa sig"
		::={ acosSlbSslError 239 }

		badEcpoint OBJECT-TYPE
		SYNTAX  CounterBasedGauge64
		MAX-ACCESS read-only
		STATUS current
		DESCRIPTION  "bad ecpoint"
		::={ acosSlbSslError 240 }

		cookieMismatch OBJECT-TYPE
		SYNTAX  CounterBasedGauge64
		MAX-ACCESS read-only
		STATUS current
		DESCRIPTION  "cookie mismatch"
		::={ acosSlbSslError 241 }

		unsupportedEllipticCurve OBJECT-TYPE
		SYNTAX  CounterBasedGauge64
		MAX-ACCESS read-only
		STATUS current
		DESCRIPTION  "unsupported elliptic curve"
		::={ acosSlbSslError 242 }

		noRequiredDigest OBJECT-TYPE
		SYNTAX  CounterBasedGauge64
		MAX-ACCESS read-only
		STATUS current
		DESCRIPTION  "no required digest"
		::={ acosSlbSslError 243 }

		unsupportedDigestType OBJECT-TYPE
		SYNTAX  CounterBasedGauge64
		MAX-ACCESS read-only
		STATUS current
		DESCRIPTION  "unsupported digest type"
		::={ acosSlbSslError 244 }

		badHandshakeLength OBJECT-TYPE
		SYNTAX  CounterBasedGauge64
		MAX-ACCESS read-only
		STATUS current
		DESCRIPTION  "bad handshake length"
		::={ acosSlbSslError 245 }

END
