ACOS-VISIBILITY-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosVisibility MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Visibility OID for ACOS"
				::=  {  acosRootStats 169  }

acosVisibility                      OBJECT IDENTIFIER ::= { acosRootStats 169 }
acosVisibilityS                     OBJECT IDENTIFIER ::= { acosVisibility 1 }

		monEntityLimitExceed OBJECT-TYPE
		SYNTAX  CounterBasedGauge64
		MAX-ACCESS read-only
		STATUS current
		DESCRIPTION  "Total monitor entity limit exceed failures"
		::={ acosVisibilityS 1 }

		haEntityCreateSent OBJECT-TYPE
		SYNTAX  CounterBasedGauge64
		MAX-ACCESS read-only
		STATUS current
		DESCRIPTION  "Total montior entity HA create messages sent"
		::={ acosVisibilityS 2 }

		haEntityDeleteSent OBJECT-TYPE
		SYNTAX  CounterBasedGauge64
		MAX-ACCESS read-only
		STATUS current
		DESCRIPTION  "Total montior entity HA delete messages sent"
		::={ acosVisibilityS 3 }

		haEntityAnomalyOnSent OBJECT-TYPE
		SYNTAX  CounterBasedGauge64
		MAX-ACCESS read-only
		STATUS current
		DESCRIPTION  "Total anomaly on HA messages sent"
		::={ acosVisibilityS 4 }

		haEntityAnomalyOffSent OBJECT-TYPE
		SYNTAX  CounterBasedGauge64
		MAX-ACCESS read-only
		STATUS current
		DESCRIPTION  "Total anomaly off HA messages sent"
		::={ acosVisibilityS 5 }

		haEntityPeriodicSyncSent OBJECT-TYPE
		SYNTAX  CounterBasedGauge64
		MAX-ACCESS read-only
		STATUS current
		DESCRIPTION  "Total monitor entity periodic sync messages sent"
		::={ acosVisibilityS 6 }

		outOfMemoryAllocFailures OBJECT-TYPE
		SYNTAX  CounterBasedGauge64
		MAX-ACCESS read-only
		STATUS current
		DESCRIPTION  "Out of memory allocation failures"
		::={ acosVisibilityS 7 }

		lwMonEntityCreated OBJECT-TYPE
		SYNTAX  CounterBasedGauge64
		MAX-ACCESS read-only
		STATUS current
		DESCRIPTION  "Total Light-weight entities created"
		::={ acosVisibilityS 8 }

		lwMonEntityDeleted OBJECT-TYPE
		SYNTAX  CounterBasedGauge64
		MAX-ACCESS read-only
		STATUS current
		DESCRIPTION  "Total Light-weight entities deleted"
		::={ acosVisibilityS 9 }

		lwMonEntityLimitExceed OBJECT-TYPE
		SYNTAX  CounterBasedGauge64
		MAX-ACCESS read-only
		STATUS current
		DESCRIPTION  "Light weight limit exceeded errors"
		::={ acosVisibilityS 10 }

		lwOutOfMemoryAllocFailures OBJECT-TYPE
		SYNTAX  CounterBasedGauge64
		MAX-ACCESS read-only
		STATUS current
		DESCRIPTION  "Light Weight Out-of-memory allocation failures"
		::={ acosVisibilityS 11 }

		monEntityRrdFileTimestampErr OBJECT-TYPE
		SYNTAX  CounterBasedGauge64
		MAX-ACCESS read-only
		STATUS current
		DESCRIPTION  "Total monitor entity rrd file timestamp errors"
		::={ acosVisibilityS 12 }

		monEntityRrdUpdateErr OBJECT-TYPE
		SYNTAX  CounterBasedGauge64
		MAX-ACCESS read-only
		STATUS current
		DESCRIPTION  "Total monitor entity rrd update error"
		::={ acosVisibilityS 13 }

		monEntityRrdLastUpdateFetchFailedErr OBJECT-TYPE
		SYNTAX  CounterBasedGauge64
		MAX-ACCESS read-only
		STATUS current
		DESCRIPTION  "Total monitor entity rrd last update fetch failed error"
		::={ acosVisibilityS 14 }

		monEntityRrdTuneErr OBJECT-TYPE
		SYNTAX  CounterBasedGauge64
		MAX-ACCESS read-only
		STATUS current
		DESCRIPTION  "Total monitor entity rrd tune error"
		::={ acosVisibilityS 15 }

		monEntityRrdOutOfMemoryErr OBJECT-TYPE
		SYNTAX  CounterBasedGauge64
		MAX-ACCESS read-only
		STATUS current
		DESCRIPTION  "Total monitor entity rrd load failed, out of memory error"
		::={ acosVisibilityS 16 }

		monEntityRrdFileCreateErr OBJECT-TYPE
		SYNTAX  CounterBasedGauge64
		MAX-ACCESS read-only
		STATUS current
		DESCRIPTION  "Total monitor entity rrd file create error"
		::={ acosVisibilityS 17 }

acosVisibilityReporting             OBJECT IDENTIFIER ::= { acosVisibility 4 }
acosVisibilityReportingS            OBJECT IDENTIFIER ::= { acosVisibilityReporting 1 }

		logTransmitFailure OBJECT-TYPE
		SYNTAX  CounterBasedGauge64
		MAX-ACCESS read-only
		STATUS current
		DESCRIPTION  "Total log transmit failures"
		::={ acosVisibilityReportingS 1 }

		bufferAllocFailure OBJECT-TYPE
		SYNTAX  CounterBasedGauge64
		MAX-ACCESS read-only
		STATUS current
		DESCRIPTION  "Total reporting buffer allocation failures"
		::={ acosVisibilityReportingS 2 }

		notifJobsInQueue OBJECT-TYPE
		SYNTAX  CounterBasedGauge64
		MAX-ACCESS read-only
		STATUS current
		DESCRIPTION  "Total notification jobs in queue"
		::={ acosVisibilityReportingS 3 }

		enqueueFail OBJECT-TYPE
		SYNTAX  CounterBasedGauge64
		MAX-ACCESS read-only
		STATUS current
		DESCRIPTION  "Total enqueue jobs failed"
		::={ acosVisibilityReportingS 4 }

		enqueuePass OBJECT-TYPE
		SYNTAX  CounterBasedGauge64
		MAX-ACCESS read-only
		STATUS current
		DESCRIPTION  "Total enqueue jobs passed"
		::={ acosVisibilityReportingS 5 }

		dequeued OBJECT-TYPE
		SYNTAX  CounterBasedGauge64
		MAX-ACCESS read-only
		STATUS current
		DESCRIPTION  "Total jobs dequeued"
		::={ acosVisibilityReportingS 6 }

acosVisibilityReportingTemplate     OBJECT IDENTIFIER ::= { acosVisibilityReporting 2 }
acosVisibilityFlowCollector         OBJECT IDENTIFIER ::= { acosVisibility 6 }
acosVisibilityFlowCollectorSflow    OBJECT IDENTIFIER ::= { acosVisibilityFlowCollector 1 }
acosVisibilityFlowCollectorSflowS   OBJECT IDENTIFIER ::= { acosVisibilityFlowCollectorSflow 1 }

		pktsReceived OBJECT-TYPE
		SYNTAX  CounterBasedGauge64
		MAX-ACCESS read-only
		STATUS current
		DESCRIPTION  "Total sflow pkts received"
		::={ acosVisibilityFlowCollectorSflowS 1 }

		fragDropped OBJECT-TYPE
		SYNTAX  CounterBasedGauge64
		MAX-ACCESS read-only
		STATUS current
		DESCRIPTION  "Total sflow fragment packets droppped"
		::={ acosVisibilityFlowCollectorSflowS 2 }

		agentNotFound OBJECT-TYPE
		SYNTAX  CounterBasedGauge64
		MAX-ACCESS read-only
		STATUS current
		DESCRIPTION  "sflow pkts from not configured agents"
		::={ acosVisibilityFlowCollectorSflowS 3 }

		versionNotSupported OBJECT-TYPE
		SYNTAX  CounterBasedGauge64
		MAX-ACCESS read-only
		STATUS current
		DESCRIPTION  "sflow version not supported"
		::={ acosVisibilityFlowCollectorSflowS 4 }

		unknownDir OBJECT-TYPE
		SYNTAX  CounterBasedGauge64
		MAX-ACCESS read-only
		STATUS current
		DESCRIPTION  "sflow sample direction is unknown"
		::={ acosVisibilityFlowCollectorSflowS 5 }

acosVisibilityFlowCollectorNetflow  OBJECT IDENTIFIER ::= { acosVisibilityFlowCollector 2 }
acosVisibilityFlowCollectorNetflowS OBJECT IDENTIFIER ::= { acosVisibilityFlowCollectorNetflow 1 }

		pktsRcvd OBJECT-TYPE
		SYNTAX  CounterBasedGauge64
		MAX-ACCESS read-only
		STATUS current
		DESCRIPTION  "Total nflow packets received"
		::={ acosVisibilityFlowCollectorNetflowS 1 }

		v9TemplatesCreated OBJECT-TYPE
		SYNTAX  CounterBasedGauge64
		MAX-ACCESS read-only
		STATUS current
		DESCRIPTION  "Total v9 templates created"
		::={ acosVisibilityFlowCollectorNetflowS 2 }

		v9TemplatesDeleted OBJECT-TYPE
		SYNTAX  CounterBasedGauge64
		MAX-ACCESS read-only
		STATUS current
		DESCRIPTION  "Total v9 templates deleted"
		::={ acosVisibilityFlowCollectorNetflowS 3 }

		v10TemplatesCreated OBJECT-TYPE
		SYNTAX  CounterBasedGauge64
		MAX-ACCESS read-only
		STATUS current
		DESCRIPTION  "Total v10(IPFIX) templates created"
		::={ acosVisibilityFlowCollectorNetflowS 4 }

		v10TemplatesDeleted OBJECT-TYPE
		SYNTAX  CounterBasedGauge64
		MAX-ACCESS read-only
		STATUS current
		DESCRIPTION  "Total v10(IPFIX) templates deleted"
		::={ acosVisibilityFlowCollectorNetflowS 5 }

		templateDropExceeded OBJECT-TYPE
		SYNTAX  CounterBasedGauge64
		MAX-ACCESS read-only
		STATUS current
		DESCRIPTION  "Total templates dropped because of maximum limit"
		::={ acosVisibilityFlowCollectorNetflowS 6 }

		templateDropOutOfMemory OBJECT-TYPE
		SYNTAX  CounterBasedGauge64
		MAX-ACCESS read-only
		STATUS current
		DESCRIPTION  "Total templates dropped becuase of out of memory"
		::={ acosVisibilityFlowCollectorNetflowS 7 }

		fragDropped OBJECT-TYPE
		SYNTAX  CounterBasedGauge64
		MAX-ACCESS read-only
		STATUS current
		DESCRIPTION  "Total nflow fragment packets droppped"
		::={ acosVisibilityFlowCollectorNetflowS 8 }

		agentNotFound OBJECT-TYPE
		SYNTAX  CounterBasedGauge64
		MAX-ACCESS read-only
		STATUS current
		DESCRIPTION  "nflow pkts from not configured agents"
		::={ acosVisibilityFlowCollectorNetflowS 9 }

		versionNotSupported OBJECT-TYPE
		SYNTAX  CounterBasedGauge64
		MAX-ACCESS read-only
		STATUS current
		DESCRIPTION  "nflow version not supported"
		::={ acosVisibilityFlowCollectorNetflowS 10 }

		unknownDir OBJECT-TYPE
		SYNTAX  CounterBasedGauge64
		MAX-ACCESS read-only
		STATUS current
		DESCRIPTION  "nflow sample direction is unknown"
		::={ acosVisibilityFlowCollectorNetflowS 11 }

acosVisibilityTopn                  OBJECT IDENTIFIER ::= { acosVisibility 14 }
acosVisibilityTopnS                 OBJECT IDENTIFIER ::= { acosVisibilityTopn 1 }

		heapAllocSuccess OBJECT-TYPE
		SYNTAX  CounterBasedGauge64
		MAX-ACCESS read-only
		STATUS current
		DESCRIPTION  "Total heap node allocated"
		::={ acosVisibilityTopnS 1 }

		heapAllocFailed OBJECT-TYPE
		SYNTAX  CounterBasedGauge64
		MAX-ACCESS read-only
		STATUS current
		DESCRIPTION  "Total heap node alloc failed"
		::={ acosVisibilityTopnS 2 }

		heapAllocOom OBJECT-TYPE
		SYNTAX  CounterBasedGauge64
		MAX-ACCESS read-only
		STATUS current
		DESCRIPTION  "Total heap node alloc failed Out of Memory"
		::={ acosVisibilityTopnS 3 }

		objRegSuccess OBJECT-TYPE
		SYNTAX  CounterBasedGauge64
		MAX-ACCESS read-only
		STATUS current
		DESCRIPTION  "Total object node allocated"
		::={ acosVisibilityTopnS 4 }

		objRegFailed OBJECT-TYPE
		SYNTAX  CounterBasedGauge64
		MAX-ACCESS read-only
		STATUS current
		DESCRIPTION  "Total object node alloc failed"
		::={ acosVisibilityTopnS 5 }

		objRegOom OBJECT-TYPE
		SYNTAX  CounterBasedGauge64
		MAX-ACCESS read-only
		STATUS current
		DESCRIPTION  "Total object node alloc failed Out of Memory"
		::={ acosVisibilityTopnS 6 }

		heapDeleted OBJECT-TYPE
		SYNTAX  CounterBasedGauge64
		MAX-ACCESS read-only
		STATUS current
		DESCRIPTION  "Total Heap node deleted"
		::={ acosVisibilityTopnS 7 }

		objDeleted OBJECT-TYPE
		SYNTAX  CounterBasedGauge64
		MAX-ACCESS read-only
		STATUS current
		DESCRIPTION  "Total Object node deleted"
		::={ acosVisibilityTopnS 8 }

		heapMetricAllocSuccess OBJECT-TYPE
		SYNTAX  CounterBasedGauge64
		MAX-ACCESS read-only
		STATUS current
		DESCRIPTION  "Total heap metric node allocated"
		::={ acosVisibilityTopnS 9 }

		heapMetricAllocOom OBJECT-TYPE
		SYNTAX  CounterBasedGauge64
		MAX-ACCESS read-only
		STATUS current
		DESCRIPTION  "Total heap metric node alloc failed Out of Memory"
		::={ acosVisibilityTopnS 10 }

		heapMoveToDelq OBJECT-TYPE
		SYNTAX  CounterBasedGauge64
		MAX-ACCESS read-only
		STATUS current
		DESCRIPTION  "Total heap node moved to delq"
		::={ acosVisibilityTopnS 11 }

		heapMetricDeleted OBJECT-TYPE
		SYNTAX  CounterBasedGauge64
		MAX-ACCESS read-only
		STATUS current
		DESCRIPTION  "Total Heap metric node deleted"
		::={ acosVisibilityTopnS 12 }

		objMetricRegSuccess OBJECT-TYPE
		SYNTAX  CounterBasedGauge64
		MAX-ACCESS read-only
		STATUS current
		DESCRIPTION  "Total object Metric node allocated"
		::={ acosVisibilityTopnS 13 }

		objMetricRegOom OBJECT-TYPE
		SYNTAX  CounterBasedGauge64
		MAX-ACCESS read-only
		STATUS current
		DESCRIPTION  "Total object Metric node alloc failed Out of Memory"
		::={ acosVisibilityTopnS 14 }

		objMoveToDelq OBJECT-TYPE
		SYNTAX  CounterBasedGauge64
		MAX-ACCESS read-only
		STATUS current
		DESCRIPTION  "Total object node moved to delq"
		::={ acosVisibilityTopnS 15 }

		objMetricDeleted OBJECT-TYPE
		SYNTAX  CounterBasedGauge64
		MAX-ACCESS read-only
		STATUS current
		DESCRIPTION  "Total Object metric node deleted"
		::={ acosVisibilityTopnS 16 }

		hcObjAllocFailed OBJECT-TYPE
		SYNTAX  CounterBasedGauge64
		MAX-ACCESS read-only
		STATUS current
		DESCRIPTION  "Send failed to HC, Out of Memory"
		::={ acosVisibilityTopnS 17 }

acosVisibilityPacketCapture         OBJECT IDENTIFIER ::= { acosVisibility 18 }
acosVisibilityPacketCaptureS        OBJECT IDENTIFIER ::= { acosVisibilityPacketCapture 1 }

		concurrentCaptureCreatedByCtrIncrement OBJECT-TYPE
		SYNTAX  CounterBasedGauge64
		MAX-ACCESS read-only
		STATUS current
		DESCRIPTION  "Dynamic 3 tuple based capture created (ctr increment based)"
		::={ acosVisibilityPacketCaptureS 1 }

		concurrentCaptureCreatedByCtrAnomaly OBJECT-TYPE
		SYNTAX  CounterBasedGauge64
		MAX-ACCESS read-only
		STATUS current
		DESCRIPTION  "Dynamic 3 tuple based capture created (ctr anomaly based)"
		::={ acosVisibilityPacketCaptureS 2 }

		concurrentCaptureCreatedByOtherFeature OBJECT-TYPE
		SYNTAX  CounterBasedGauge64
		MAX-ACCESS read-only
		STATUS current
		DESCRIPTION  "Dynamic 3 tuple based capture created (Other feature based)"
		::={ acosVisibilityPacketCaptureS 3 }

		concurrentCaptureCreateFailedByCtrIncrement OBJECT-TYPE
		SYNTAX  CounterBasedGauge64
		MAX-ACCESS read-only
		STATUS current
		DESCRIPTION  "Error, Dynamic Capture(ctr increment based) create failed"
		::={ acosVisibilityPacketCaptureS 4 }

		concurrentCaptureCreateFailedByCtrAnomaly OBJECT-TYPE
		SYNTAX  CounterBasedGauge64
		MAX-ACCESS read-only
		STATUS current
		DESCRIPTION  "Error, Dynamic Capture(ctr anomaly based) create failed"
		::={ acosVisibilityPacketCaptureS 5 }

		concurrentCaptureCreateFailedByOtherFeature OBJECT-TYPE
		SYNTAX  CounterBasedGauge64
		MAX-ACCESS read-only
		STATUS current
		DESCRIPTION  "Error, Dynamic Capture(Other feature based) create failed"
		::={ acosVisibilityPacketCaptureS 6 }

		concurrentCaptureCreateFailedOom OBJECT-TYPE
		SYNTAX  CounterBasedGauge64
		MAX-ACCESS read-only
		STATUS current
		DESCRIPTION  "Error, Dynamic Capture create failed, OOM"
		::={ acosVisibilityPacketCaptureS 7 }

		concurrentCaptureLimitReached OBJECT-TYPE
		SYNTAX  CounterBasedGauge64
		MAX-ACCESS read-only
		STATUS current
		DESCRIPTION  "Dynamic Capture configured concurrent limit reached"
		::={ acosVisibilityPacketCaptureS 8 }

		concurrentCaptureByCtrIncrementFreed OBJECT-TYPE
		SYNTAX  CounterBasedGauge64
		MAX-ACCESS read-only
		STATUS current
		DESCRIPTION  "Dynamic Capture(ctr increment based) freed"
		::={ acosVisibilityPacketCaptureS 9 }

		concurrentCaptureByCtrAnomalyFreed OBJECT-TYPE
		SYNTAX  CounterBasedGauge64
		MAX-ACCESS read-only
		STATUS current
		DESCRIPTION  "Dynamic Capture(ctr anomaly based) freed"
		::={ acosVisibilityPacketCaptureS 10 }

		concurrentCaptureByCtrOtherFeatureFreed OBJECT-TYPE
		SYNTAX  CounterBasedGauge64
		MAX-ACCESS read-only
		STATUS current
		DESCRIPTION  "Dynamic Capture(Other feature based) freed"
		::={ acosVisibilityPacketCaptureS 11 }

		globalCaptureFinished OBJECT-TYPE
		SYNTAX  CounterBasedGauge64
		MAX-ACCESS read-only
		STATUS current
		DESCRIPTION  "Number of times global capture finished capturing"
		::={ acosVisibilityPacketCaptureS 12 }

		concurrentCaptureFinished OBJECT-TYPE
		SYNTAX  CounterBasedGauge64
		MAX-ACCESS read-only
		STATUS current
		DESCRIPTION  "Number of Dynamic captures(3 tuple based) finished capturing"
		::={ acosVisibilityPacketCaptureS 13 }

		pktcaptureWithNoConnSuccess OBJECT-TYPE
		SYNTAX  CounterBasedGauge64
		MAX-ACCESS read-only
		STATUS current
		DESCRIPTION  "Capture success, Packets without conn"
		::={ acosVisibilityPacketCaptureS 14 }

		pktcaptureWithNoConnFailure OBJECT-TYPE
		SYNTAX  CounterBasedGauge64
		MAX-ACCESS read-only
		STATUS current
		DESCRIPTION  "Capture fail, Packets without conn"
		::={ acosVisibilityPacketCaptureS 15 }

		pktcaptureWithConnButNotTaggedSuccess OBJECT-TYPE
		SYNTAX  CounterBasedGauge64
		MAX-ACCESS read-only
		STATUS current
		DESCRIPTION  "Capture success, Packets with untagged conn"
		::={ acosVisibilityPacketCaptureS 16 }

		pktcaptureWithConnButNotTaggedFailure OBJECT-TYPE
		SYNTAX  CounterBasedGauge64
		MAX-ACCESS read-only
		STATUS current
		DESCRIPTION  "Capture fail, Packets with untagged conn"
		::={ acosVisibilityPacketCaptureS 17 }

		pktcaptureWithConnSuccessGlobal OBJECT-TYPE
		SYNTAX  CounterBasedGauge64
		MAX-ACCESS read-only
		STATUS current
		DESCRIPTION  "Capture success, Packets with tagged conn (global capture)"
		::={ acosVisibilityPacketCaptureS 18 }

		pktcaptureWithConnSuccess OBJECT-TYPE
		SYNTAX  CounterBasedGauge64
		MAX-ACCESS read-only
		STATUS current
		DESCRIPTION  "Capture success, Packets with tagged conn (dynamic capture)"
		::={ acosVisibilityPacketCaptureS 19 }

		pktcaptureWithConnFailureGlobal OBJECT-TYPE
		SYNTAX  CounterBasedGauge64
		MAX-ACCESS read-only
		STATUS current
		DESCRIPTION  "Capture fail, Packets with tagged conn (global capture)"
		::={ acosVisibilityPacketCaptureS 20 }

		pktcaptureWithConnFailure OBJECT-TYPE
		SYNTAX  CounterBasedGauge64
		MAX-ACCESS read-only
		STATUS current
		DESCRIPTION  "Capture fail, Packets with tagged conn (dynamic capture)"
		::={ acosVisibilityPacketCaptureS 21 }

		pktcaptureFailureWaitForBlock OBJECT-TYPE
		SYNTAX  CounterBasedGauge64
		MAX-ACCESS read-only
		STATUS current
		DESCRIPTION  "Capture fail, waiting to get free buffer"
		::={ acosVisibilityPacketCaptureS 22 }

		pktcaptureFailureFileSizeRchd OBJECT-TYPE
		SYNTAX  CounterBasedGauge64
		MAX-ACCESS read-only
		STATUS current
		DESCRIPTION  "Capture fail, file size reached"
		::={ acosVisibilityPacketCaptureS 23 }

		numConnsTaggedGlobalIncrement OBJECT-TYPE
		SYNTAX  CounterBasedGauge64
		MAX-ACCESS read-only
		STATUS current
		DESCRIPTION  "Conn tag success (based on ctr increment, Global)"
		::={ acosVisibilityPacketCaptureS 24 }

		numConnsTaggedGlobalAnomaly OBJECT-TYPE
		SYNTAX  CounterBasedGauge64
		MAX-ACCESS read-only
		STATUS current
		DESCRIPTION  "Conn tag success (based on ctr anomaly, Global)"
		::={ acosVisibilityPacketCaptureS 25 }

		numConnsTaggedGlobalOtherFeature OBJECT-TYPE
		SYNTAX  CounterBasedGauge64
		MAX-ACCESS read-only
		STATUS current
		DESCRIPTION  "Conn tag success (based on Other feature, Global)"
		::={ acosVisibilityPacketCaptureS 26 }

		numConnsTaggedGlobalIncrementFail OBJECT-TYPE
		SYNTAX  CounterBasedGauge64
		MAX-ACCESS read-only
		STATUS current
		DESCRIPTION  "Conn tag fail (based on ctr increment, Global)"
		::={ acosVisibilityPacketCaptureS 27 }

		numConnsTaggedGlobalAnomalyFail OBJECT-TYPE
		SYNTAX  CounterBasedGauge64
		MAX-ACCESS read-only
		STATUS current
		DESCRIPTION  "Conn tag fail (based on ctr anomaly, Global)"
		::={ acosVisibilityPacketCaptureS 28 }

		numConnsTaggedGlobalOtherFeatureFail OBJECT-TYPE
		SYNTAX  CounterBasedGauge64
		MAX-ACCESS read-only
		STATUS current
		DESCRIPTION  "Conn tag fail (based on Other feature, Global)"
		::={ acosVisibilityPacketCaptureS 29 }

		numConnsTaggedGlobalIncrementMaxed OBJECT-TYPE
		SYNTAX  CounterBasedGauge64
		MAX-ACCESS read-only
		STATUS current
		DESCRIPTION  "Conn tag fail, reached limit (based on ctr increment, Global)"
		::={ acosVisibilityPacketCaptureS 30 }

		numConnsTaggedGlobalAnomalyMaxed OBJECT-TYPE
		SYNTAX  CounterBasedGauge64
		MAX-ACCESS read-only
		STATUS current
		DESCRIPTION  "Conn tag fail, reached limit (based on ctr anomaly, Global)"
		::={ acosVisibilityPacketCaptureS 31 }

		numConnsTaggedGlobalOtherFeatureMaxed OBJECT-TYPE
		SYNTAX  CounterBasedGauge64
		MAX-ACCESS read-only
		STATUS current
		DESCRIPTION  "Conn tag fail, reached limit (based on Other feature, Global)"
		::={ acosVisibilityPacketCaptureS 32 }

		numConnsTaggedIncrement OBJECT-TYPE
		SYNTAX  CounterBasedGauge64
		MAX-ACCESS read-only
		STATUS current
		DESCRIPTION  "Conn tag success (based on ctr increment, dynamic)"
		::={ acosVisibilityPacketCaptureS 33 }

		numConnsTaggedAnomaly OBJECT-TYPE
		SYNTAX  CounterBasedGauge64
		MAX-ACCESS read-only
		STATUS current
		DESCRIPTION  "Conn tag success (based on ctr anomaly, dynamic)"
		::={ acosVisibilityPacketCaptureS 34 }

		numConnsTaggedOtherFeature OBJECT-TYPE
		SYNTAX  CounterBasedGauge64
		MAX-ACCESS read-only
		STATUS current
		DESCRIPTION  "Conn tag success (based on Other feature, dynamic)"
		::={ acosVisibilityPacketCaptureS 35 }

		numConnsTaggedIncrementFail OBJECT-TYPE
		SYNTAX  CounterBasedGauge64
		MAX-ACCESS read-only
		STATUS current
		DESCRIPTION  "Conn tag fail (based on ctr increment, dynamic)"
		::={ acosVisibilityPacketCaptureS 36 }

		numConnsTaggedAnomalyFail OBJECT-TYPE
		SYNTAX  CounterBasedGauge64
		MAX-ACCESS read-only
		STATUS current
		DESCRIPTION  "Conn tag fail (based on ctr anomaly, dynamic)"
		::={ acosVisibilityPacketCaptureS 37 }

		numConnsTaggedOtherFeatureFail OBJECT-TYPE
		SYNTAX  CounterBasedGauge64
		MAX-ACCESS read-only
		STATUS current
		DESCRIPTION  "Conn tag fail (based on Other feature, dynamic)"
		::={ acosVisibilityPacketCaptureS 38 }

		numConnsTaggedIncrementMaxed OBJECT-TYPE
		SYNTAX  CounterBasedGauge64
		MAX-ACCESS read-only
		STATUS current
		DESCRIPTION  "Conn tag fail, reached limit (based on ctr increment, dynamic)"
		::={ acosVisibilityPacketCaptureS 39 }

		numConnsTaggedAnomalyMaxed OBJECT-TYPE
		SYNTAX  CounterBasedGauge64
		MAX-ACCESS read-only
		STATUS current
		DESCRIPTION  "Conn tag fail, reached limit (based on ctr anomaly, dynamic)"
		::={ acosVisibilityPacketCaptureS 40 }

		numConnsTaggedOtherFeatureMaxed OBJECT-TYPE
		SYNTAX  CounterBasedGauge64
		MAX-ACCESS read-only
		STATUS current
		DESCRIPTION  "Conn tag fail, reached limit (based on Other feature, dynamic)"
		::={ acosVisibilityPacketCaptureS 41 }

		numConnsUntagged OBJECT-TYPE
		SYNTAX  CounterBasedGauge64
		MAX-ACCESS read-only
		STATUS current
		DESCRIPTION  "Number of conns untagged (done with conn limit or capture)"
		::={ acosVisibilityPacketCaptureS 42 }

		pktcaptureTriggeredByIncrement OBJECT-TYPE
		SYNTAX  CounterBasedGauge64
		MAX-ACCESS read-only
		STATUS current
		DESCRIPTION  "Capture triggered by counter increment"
		::={ acosVisibilityPacketCaptureS 43 }

		pktcaptureTriggeredByAnomaly OBJECT-TYPE
		SYNTAX  CounterBasedGauge64
		MAX-ACCESS read-only
		STATUS current
		DESCRIPTION  "Capture triggered by counter anomaly"
		::={ acosVisibilityPacketCaptureS 44 }

		pktcaptureTriggeredByOtherFeature OBJECT-TYPE
		SYNTAX  CounterBasedGauge64
		MAX-ACCESS read-only
		STATUS current
		DESCRIPTION  "Capture triggered by Other feature"
		::={ acosVisibilityPacketCaptureS 45 }

		numOfAnomaliesDetected OBJECT-TYPE
		SYNTAX  CounterBasedGauge64
		MAX-ACCESS read-only
		STATUS current
		DESCRIPTION  "Number of times ctr Anomaly detected"
		::={ acosVisibilityPacketCaptureS 46 }

		numOfAnomaliesCleared OBJECT-TYPE
		SYNTAX  CounterBasedGauge64
		MAX-ACCESS read-only
		STATUS current
		DESCRIPTION  "Number of times ctr Anomaly cleared"
		::={ acosVisibilityPacketCaptureS 47 }

		numPcapsCreated OBJECT-TYPE
		SYNTAX  CounterBasedGauge64
		MAX-ACCESS read-only
		STATUS current
		DESCRIPTION  "Number of pcapng files created"
		::={ acosVisibilityPacketCaptureS 48 }

		numTmpPcapsCreated OBJECT-TYPE
		SYNTAX  CounterBasedGauge64
		MAX-ACCESS read-only
		STATUS current
		DESCRIPTION  "Number of temporary pcapng files created"
		::={ acosVisibilityPacketCaptureS 49 }

		numPcapsCreateFailed OBJECT-TYPE
		SYNTAX  CounterBasedGauge64
		MAX-ACCESS read-only
		STATUS current
		DESCRIPTION  "Error, Number of pcapng files creation failed"
		::={ acosVisibilityPacketCaptureS 50 }

		pktcapOom OBJECT-TYPE
		SYNTAX  CounterBasedGauge64
		MAX-ACCESS read-only
		STATUS current
		DESCRIPTION  "Error, Automated Packet capture infra OOM"
		::={ acosVisibilityPacketCaptureS 51 }

		failedDiskFull OBJECT-TYPE
		SYNTAX  CounterBasedGauge64
		MAX-ACCESS read-only
		STATUS current
		DESCRIPTION  "Error, Capture fail, Disk limit reached"
		::={ acosVisibilityPacketCaptureS 52 }

		connExtFailed OBJECT-TYPE
		SYNTAX  CounterBasedGauge64
		MAX-ACCESS read-only
		STATUS current
		DESCRIPTION  "Error, Conn extension creation fail"
		::={ acosVisibilityPacketCaptureS 53 }

		skipAsConnAlreadyRecapture OBJECT-TYPE
		SYNTAX  CounterBasedGauge64
		MAX-ACCESS read-only
		STATUS current
		DESCRIPTION  "Skip creating capture, conn was already captured"
		::={ acosVisibilityPacketCaptureS 54 }

		skipCaptureAsConnCreatedBeforeSmp OBJECT-TYPE
		SYNTAX  CounterBasedGauge64
		MAX-ACCESS read-only
		STATUS current
		DESCRIPTION  "Skip capturing, conn was created before the capture started"
		::={ acosVisibilityPacketCaptureS 55 }

		failedAsReturnCompletedSet OBJECT-TYPE
		SYNTAX  CounterBasedGauge64
		MAX-ACCESS read-only
		STATUS current
		DESCRIPTION  "Skip capturing, capture-config marked completed"
		::={ acosVisibilityPacketCaptureS 56 }

		nonPktPath OBJECT-TYPE
		SYNTAX  CounterBasedGauge64
		MAX-ACCESS read-only
		STATUS current
		DESCRIPTION  "Skip capturing, not packet processing path"
		::={ acosVisibilityPacketCaptureS 57 }

		pktAlreadyCaptured OBJECT-TYPE
		SYNTAX  CounterBasedGauge64
		MAX-ACCESS read-only
		STATUS current
		DESCRIPTION  "Skip capturing, packet already captured"
		::={ acosVisibilityPacketCaptureS 58 }

		wrongCtrIncremented OBJECT-TYPE
		SYNTAX  CounterBasedGauge64
		MAX-ACCESS read-only
		STATUS current
		DESCRIPTION  "Counter increment issue"
		::={ acosVisibilityPacketCaptureS 59 }

		autoPcapFileMerged OBJECT-TYPE
		SYNTAX  CounterBasedGauge64
		MAX-ACCESS read-only
		STATUS current
		DESCRIPTION  "Auto pcapng files merged"
		::={ acosVisibilityPacketCaptureS 60 }

		autoPcapFileMergedFailed OBJECT-TYPE
		SYNTAX  CounterBasedGauge64
		MAX-ACCESS read-only
		STATUS current
		DESCRIPTION  "Auto pcapng files merged failed"
		::={ acosVisibilityPacketCaptureS 61 }

		numGlobalTmplCreated OBJECT-TYPE
		SYNTAX  CounterBasedGauge64
		MAX-ACCESS read-only
		STATUS current
		DESCRIPTION  "Number of global templates created"
		::={ acosVisibilityPacketCaptureS 62 }

		numObjectTmplCreated OBJECT-TYPE
		SYNTAX  CounterBasedGauge64
		MAX-ACCESS read-only
		STATUS current
		DESCRIPTION  "Number of object templates created"
		::={ acosVisibilityPacketCaptureS 63 }

		numGlobalTmplDeleted OBJECT-TYPE
		SYNTAX  CounterBasedGauge64
		MAX-ACCESS read-only
		STATUS current
		DESCRIPTION  "Number of global templates deleted"
		::={ acosVisibilityPacketCaptureS 64 }

		numObjectTmplDeleted OBJECT-TYPE
		SYNTAX  CounterBasedGauge64
		MAX-ACCESS read-only
		STATUS current
		DESCRIPTION  "Number of object templates deleted"
		::={ acosVisibilityPacketCaptureS 65 }

		numCaptureConfigCreated OBJECT-TYPE
		SYNTAX  CounterBasedGauge64
		MAX-ACCESS read-only
		STATUS current
		DESCRIPTION  "Number of capture-config created"
		::={ acosVisibilityPacketCaptureS 66 }

		numDynamicCaptureConfigCreated OBJECT-TYPE
		SYNTAX  CounterBasedGauge64
		MAX-ACCESS read-only
		STATUS current
		DESCRIPTION  "Number of dynamic capture-config created"
		::={ acosVisibilityPacketCaptureS 67 }

		numCaptureConfigDeleted OBJECT-TYPE
		SYNTAX  CounterBasedGauge64
		MAX-ACCESS read-only
		STATUS current
		DESCRIPTION  "Number of capture-config deleted"
		::={ acosVisibilityPacketCaptureS 68 }

		numDynamicCaptureConfigDeleted OBJECT-TYPE
		SYNTAX  CounterBasedGauge64
		MAX-ACCESS read-only
		STATUS current
		DESCRIPTION  "Number of dynamic capture-config deleted"
		::={ acosVisibilityPacketCaptureS 69 }

		numCaptureConfigDeleteQ OBJECT-TYPE
		SYNTAX  CounterBasedGauge64
		MAX-ACCESS read-only
		STATUS current
		DESCRIPTION  "Number of capture-config set for deletion"
		::={ acosVisibilityPacketCaptureS 70 }

		numDynamicCaptureConfigDeleteQ OBJECT-TYPE
		SYNTAX  CounterBasedGauge64
		MAX-ACCESS read-only
		STATUS current
		DESCRIPTION  "Number of dynamic capture-config set for deletion"
		::={ acosVisibilityPacketCaptureS 71 }

		numCaptureConfigLinked OBJECT-TYPE
		SYNTAX  CounterBasedGauge64
		MAX-ACCESS read-only
		STATUS current
		DESCRIPTION  "Number of times capture-config linked to template"
		::={ acosVisibilityPacketCaptureS 72 }

		numDynamicCaptureConfigLinked OBJECT-TYPE
		SYNTAX  CounterBasedGauge64
		MAX-ACCESS read-only
		STATUS current
		DESCRIPTION  "Number of times dynamic capture-config linked to template"
		::={ acosVisibilityPacketCaptureS 73 }

		numCaptureConfigUnlinked OBJECT-TYPE
		SYNTAX  CounterBasedGauge64
		MAX-ACCESS read-only
		STATUS current
		DESCRIPTION  "Number of times capture-config unlinked from template"
		::={ acosVisibilityPacketCaptureS 74 }

		numDynamicCaptureConfigUnlinked OBJECT-TYPE
		SYNTAX  CounterBasedGauge64
		MAX-ACCESS read-only
		STATUS current
		DESCRIPTION  "Number of times dynamic capture-config unlinked from template"
		::={ acosVisibilityPacketCaptureS 75 }

		numGlobalCountersRegistered OBJECT-TYPE
		SYNTAX  CounterBasedGauge64
		MAX-ACCESS read-only
		STATUS current
		DESCRIPTION  "Number of global objects registered"
		::={ acosVisibilityPacketCaptureS 76 }

		numGlobalCountersDeregistered OBJECT-TYPE
		SYNTAX  CounterBasedGauge64
		MAX-ACCESS read-only
		STATUS current
		DESCRIPTION  "Number of global objects deregistered"
		::={ acosVisibilityPacketCaptureS 77 }

		numPerObjectCountersRegistered OBJECT-TYPE
		SYNTAX  CounterBasedGauge64
		MAX-ACCESS read-only
		STATUS current
		DESCRIPTION  "Number of per instance objects registered"
		::={ acosVisibilityPacketCaptureS 78 }

		numPerObjectCountersDeregistered OBJECT-TYPE
		SYNTAX  CounterBasedGauge64
		MAX-ACCESS read-only
		STATUS current
		DESCRIPTION  "Number of per instance objects deregistered"
		::={ acosVisibilityPacketCaptureS 79 }

		smpExists OBJECT-TYPE
		SYNTAX  CounterBasedGauge64
		MAX-ACCESS read-only
		STATUS current
		DESCRIPTION  "Dynamic Capture(3 tuple based/SMP) already exists"
		::={ acosVisibilityPacketCaptureS 80 }

		failureMisc OBJECT-TYPE
		SYNTAX  CounterBasedGauge64
		MAX-ACCESS read-only
		STATUS current
		DESCRIPTION  "Failed, other"
		::={ acosVisibilityPacketCaptureS 81 }

END
