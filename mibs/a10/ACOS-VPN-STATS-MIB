ACOS-VPN-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosVpn MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Vpn OID for ACOS"
				::=  {  acosRootStats 112  }

acosVpn                             OBJECT IDENTIFIER ::= { acosRootStats 112 }
acosVpnS                            OBJECT IDENTIFIER ::= { acosVpn 1 }

		passthrough OBJECT-TYPE
		SYNTAX  CounterBasedGauge64
		MAX-ACCESS read-only
		STATUS current
		DESCRIPTION  "some help string"
		::={ acosVpnS 1 }

		haStandbyDrop OBJECT-TYPE
		SYNTAX  CounterBasedGauge64
		MAX-ACCESS read-only
		STATUS current
		DESCRIPTION  "some help string"
		::={ acosVpnS 2 }

acosVpnError                        OBJECT IDENTIFIER ::= { acosVpn 8 }
acosVpnErrorS                       OBJECT IDENTIFIER ::= { acosVpnError 1 }

		badOpcode OBJECT-TYPE
		SYNTAX  CounterBasedGauge64
		MAX-ACCESS read-only
		STATUS current
		DESCRIPTION  "some help string"
		::={ acosVpnErrorS 1 }

		badSgWriteLen OBJECT-TYPE
		SYNTAX  CounterBasedGauge64
		MAX-ACCESS read-only
		STATUS current
		DESCRIPTION  "some help string"
		::={ acosVpnErrorS 2 }

		badLen OBJECT-TYPE
		SYNTAX  CounterBasedGauge64
		MAX-ACCESS read-only
		STATUS current
		DESCRIPTION  "some help string"
		::={ acosVpnErrorS 3 }

		badIpsecProtocol OBJECT-TYPE
		SYNTAX  CounterBasedGauge64
		MAX-ACCESS read-only
		STATUS current
		DESCRIPTION  "some help string"
		::={ acosVpnErrorS 4 }

		badIpsecAuth OBJECT-TYPE
		SYNTAX  CounterBasedGauge64
		MAX-ACCESS read-only
		STATUS current
		DESCRIPTION  "some help string"
		::={ acosVpnErrorS 5 }

		badIpsecPadding OBJECT-TYPE
		SYNTAX  CounterBasedGauge64
		MAX-ACCESS read-only
		STATUS current
		DESCRIPTION  "some help string"
		::={ acosVpnErrorS 6 }

		badIpVersion OBJECT-TYPE
		SYNTAX  CounterBasedGauge64
		MAX-ACCESS read-only
		STATUS current
		DESCRIPTION  "some help string"
		::={ acosVpnErrorS 7 }

		badAuthType OBJECT-TYPE
		SYNTAX  CounterBasedGauge64
		MAX-ACCESS read-only
		STATUS current
		DESCRIPTION  "some help string"
		::={ acosVpnErrorS 8 }

		badEncryptType OBJECT-TYPE
		SYNTAX  CounterBasedGauge64
		MAX-ACCESS read-only
		STATUS current
		DESCRIPTION  "some help string"
		::={ acosVpnErrorS 9 }

		badIpsecSpi OBJECT-TYPE
		SYNTAX  CounterBasedGauge64
		MAX-ACCESS read-only
		STATUS current
		DESCRIPTION  "some help string"
		::={ acosVpnErrorS 10 }

		badChecksum OBJECT-TYPE
		SYNTAX  CounterBasedGauge64
		MAX-ACCESS read-only
		STATUS current
		DESCRIPTION  "some help string"
		::={ acosVpnErrorS 11 }

		badIpsecContext OBJECT-TYPE
		SYNTAX  CounterBasedGauge64
		MAX-ACCESS read-only
		STATUS current
		DESCRIPTION  "some help string"
		::={ acosVpnErrorS 12 }

		badIpsecContextDirection OBJECT-TYPE
		SYNTAX  CounterBasedGauge64
		MAX-ACCESS read-only
		STATUS current
		DESCRIPTION  "some help string"
		::={ acosVpnErrorS 13 }

		badIpsecContextFlagMismatch OBJECT-TYPE
		SYNTAX  CounterBasedGauge64
		MAX-ACCESS read-only
		STATUS current
		DESCRIPTION  "some help string"
		::={ acosVpnErrorS 14 }

		ipcompPayload OBJECT-TYPE
		SYNTAX  CounterBasedGauge64
		MAX-ACCESS read-only
		STATUS current
		DESCRIPTION  "some help string"
		::={ acosVpnErrorS 15 }

		badSelectorMatch OBJECT-TYPE
		SYNTAX  CounterBasedGauge64
		MAX-ACCESS read-only
		STATUS current
		DESCRIPTION  "some help string"
		::={ acosVpnErrorS 16 }

		badFragmentSize OBJECT-TYPE
		SYNTAX  CounterBasedGauge64
		MAX-ACCESS read-only
		STATUS current
		DESCRIPTION  "some help string"
		::={ acosVpnErrorS 17 }

		badInlineData OBJECT-TYPE
		SYNTAX  CounterBasedGauge64
		MAX-ACCESS read-only
		STATUS current
		DESCRIPTION  "some help string"
		::={ acosVpnErrorS 18 }

		badFragSizeConfiguration OBJECT-TYPE
		SYNTAX  CounterBasedGauge64
		MAX-ACCESS read-only
		STATUS current
		DESCRIPTION  "some help string"
		::={ acosVpnErrorS 19 }

		dummyPayload OBJECT-TYPE
		SYNTAX  CounterBasedGauge64
		MAX-ACCESS read-only
		STATUS current
		DESCRIPTION  "some help string"
		::={ acosVpnErrorS 20 }

		badIpPayloadType OBJECT-TYPE
		SYNTAX  CounterBasedGauge64
		MAX-ACCESS read-only
		STATUS current
		DESCRIPTION  "some help string"
		::={ acosVpnErrorS 21 }

		badMinFragSizeAuthSha384512 OBJECT-TYPE
		SYNTAX  CounterBasedGauge64
		MAX-ACCESS read-only
		STATUS current
		DESCRIPTION  "some help string"
		::={ acosVpnErrorS 22 }

		badEspNextHeader OBJECT-TYPE
		SYNTAX  CounterBasedGauge64
		MAX-ACCESS read-only
		STATUS current
		DESCRIPTION  "some help string"
		::={ acosVpnErrorS 23 }

		badGreHeader OBJECT-TYPE
		SYNTAX  CounterBasedGauge64
		MAX-ACCESS read-only
		STATUS current
		DESCRIPTION  "some help string"
		::={ acosVpnErrorS 24 }

		badGreProtocol OBJECT-TYPE
		SYNTAX  CounterBasedGauge64
		MAX-ACCESS read-only
		STATUS current
		DESCRIPTION  "some help string"
		::={ acosVpnErrorS 25 }

		ipv6ExtensionHeadersTooBig OBJECT-TYPE
		SYNTAX  CounterBasedGauge64
		MAX-ACCESS read-only
		STATUS current
		DESCRIPTION  "some help string"
		::={ acosVpnErrorS 26 }

		ipv6HopByHopError OBJECT-TYPE
		SYNTAX  CounterBasedGauge64
		MAX-ACCESS read-only
		STATUS current
		DESCRIPTION  "some help string"
		::={ acosVpnErrorS 27 }

		errorIpv6DecryptRhSegsLeftError OBJECT-TYPE
		SYNTAX  CounterBasedGauge64
		MAX-ACCESS read-only
		STATUS current
		DESCRIPTION  "some help string"
		::={ acosVpnErrorS 28 }

		ipv6RhLengthError OBJECT-TYPE
		SYNTAX  CounterBasedGauge64
		MAX-ACCESS read-only
		STATUS current
		DESCRIPTION  "some help string"
		::={ acosVpnErrorS 29 }

		ipv6OutboundRhCopyAddrError OBJECT-TYPE
		SYNTAX  CounterBasedGauge64
		MAX-ACCESS read-only
		STATUS current
		DESCRIPTION  "some help string"
		::={ acosVpnErrorS 30 }

		errorIPv6ExtensionHeaderBad OBJECT-TYPE
		SYNTAX  CounterBasedGauge64
		MAX-ACCESS read-only
		STATUS current
		DESCRIPTION  "some help string"
		::={ acosVpnErrorS 31 }

		badEncryptTypeCtrGcm OBJECT-TYPE
		SYNTAX  CounterBasedGauge64
		MAX-ACCESS read-only
		STATUS current
		DESCRIPTION  "some help string"
		::={ acosVpnErrorS 32 }

		ahNotSupportedWithGcmGmacSha2 OBJECT-TYPE
		SYNTAX  CounterBasedGauge64
		MAX-ACCESS read-only
		STATUS current
		DESCRIPTION  "some help string"
		::={ acosVpnErrorS 33 }

		tfcPaddingWithPrefragNotSupported OBJECT-TYPE
		SYNTAX  CounterBasedGauge64
		MAX-ACCESS read-only
		STATUS current
		DESCRIPTION  "some help string"
		::={ acosVpnErrorS 34 }

		badSrtpAuthTag OBJECT-TYPE
		SYNTAX  CounterBasedGauge64
		MAX-ACCESS read-only
		STATUS current
		DESCRIPTION  "some help string"
		::={ acosVpnErrorS 35 }

		badIpcompConfiguration OBJECT-TYPE
		SYNTAX  CounterBasedGauge64
		MAX-ACCESS read-only
		STATUS current
		DESCRIPTION  "some help string"
		::={ acosVpnErrorS 36 }

		dsivIncorrectParam OBJECT-TYPE
		SYNTAX  CounterBasedGauge64
		MAX-ACCESS read-only
		STATUS current
		DESCRIPTION  "some help string"
		::={ acosVpnErrorS 37 }

		badIpsecUnknown OBJECT-TYPE
		SYNTAX  CounterBasedGauge64
		MAX-ACCESS read-only
		STATUS current
		DESCRIPTION  "some help string"
		::={ acosVpnErrorS 38 }

acosVpnIkeStatsGlobal               OBJECT IDENTIFIER ::= { acosVpn 2 }
acosVpnIkeStatsGlobalS              OBJECT IDENTIFIER ::= { acosVpnIkeStatsGlobal 1 }

		v2InitRekey OBJECT-TYPE
		SYNTAX  CounterBasedGauge64
		MAX-ACCESS read-only
		STATUS current
		DESCRIPTION  "Initiate Rekey"
		::={ acosVpnIkeStatsGlobalS 1 }

		v2RspRekey OBJECT-TYPE
		SYNTAX  CounterBasedGauge64
		MAX-ACCESS read-only
		STATUS current
		DESCRIPTION  "Respond Rekey"
		::={ acosVpnIkeStatsGlobalS 2 }

		v2ChildSaRekey OBJECT-TYPE
		SYNTAX  CounterBasedGauge64
		MAX-ACCESS read-only
		STATUS current
		DESCRIPTION  "Child SA Rekey"
		::={ acosVpnIkeStatsGlobalS 3 }

		v2InInvalid OBJECT-TYPE
		SYNTAX  CounterBasedGauge64
		MAX-ACCESS read-only
		STATUS current
		DESCRIPTION  "Incoming Invalid"
		::={ acosVpnIkeStatsGlobalS 4 }

		v2InInvalidSpi OBJECT-TYPE
		SYNTAX  CounterBasedGauge64
		MAX-ACCESS read-only
		STATUS current
		DESCRIPTION  "Incoming Invalid SPI"
		::={ acosVpnIkeStatsGlobalS 5 }

		v2InInitReq OBJECT-TYPE
		SYNTAX  CounterBasedGauge64
		MAX-ACCESS read-only
		STATUS current
		DESCRIPTION  "Incoming Init Request"
		::={ acosVpnIkeStatsGlobalS 6 }

		v2InInitRsp OBJECT-TYPE
		SYNTAX  CounterBasedGauge64
		MAX-ACCESS read-only
		STATUS current
		DESCRIPTION  "Incoming Init Response"
		::={ acosVpnIkeStatsGlobalS 7 }

		v2OutInitReq OBJECT-TYPE
		SYNTAX  CounterBasedGauge64
		MAX-ACCESS read-only
		STATUS current
		DESCRIPTION  "Outgoing Init Request"
		::={ acosVpnIkeStatsGlobalS 8 }

		v2OutInitRsp OBJECT-TYPE
		SYNTAX  CounterBasedGauge64
		MAX-ACCESS read-only
		STATUS current
		DESCRIPTION  "Outgoing Init Response"
		::={ acosVpnIkeStatsGlobalS 9 }

		v2InAuthReq OBJECT-TYPE
		SYNTAX  CounterBasedGauge64
		MAX-ACCESS read-only
		STATUS current
		DESCRIPTION  "Incoming Auth Request"
		::={ acosVpnIkeStatsGlobalS 10 }

		v2InAuthRsp OBJECT-TYPE
		SYNTAX  CounterBasedGauge64
		MAX-ACCESS read-only
		STATUS current
		DESCRIPTION  "Incoming Auth Response"
		::={ acosVpnIkeStatsGlobalS 11 }

		v2OutAuthReq OBJECT-TYPE
		SYNTAX  CounterBasedGauge64
		MAX-ACCESS read-only
		STATUS current
		DESCRIPTION  "Outgoing Auth Request"
		::={ acosVpnIkeStatsGlobalS 12 }

		v2OutAuthRsp OBJECT-TYPE
		SYNTAX  CounterBasedGauge64
		MAX-ACCESS read-only
		STATUS current
		DESCRIPTION  "Outgoing Auth Response"
		::={ acosVpnIkeStatsGlobalS 13 }

		v2InCreateChildReq OBJECT-TYPE
		SYNTAX  CounterBasedGauge64
		MAX-ACCESS read-only
		STATUS current
		DESCRIPTION  "Incoming Create Child Request"
		::={ acosVpnIkeStatsGlobalS 14 }

		v2InCreateChildRsp OBJECT-TYPE
		SYNTAX  CounterBasedGauge64
		MAX-ACCESS read-only
		STATUS current
		DESCRIPTION  "Incoming Create Child Response"
		::={ acosVpnIkeStatsGlobalS 15 }

		v2OutCreateChildReq OBJECT-TYPE
		SYNTAX  CounterBasedGauge64
		MAX-ACCESS read-only
		STATUS current
		DESCRIPTION  "Outgoing Create Child Request"
		::={ acosVpnIkeStatsGlobalS 16 }

		v2OutCreateChildRsp OBJECT-TYPE
		SYNTAX  CounterBasedGauge64
		MAX-ACCESS read-only
		STATUS current
		DESCRIPTION  "Outgoing Create Child Response"
		::={ acosVpnIkeStatsGlobalS 17 }

		v2InInfoReq OBJECT-TYPE
		SYNTAX  CounterBasedGauge64
		MAX-ACCESS read-only
		STATUS current
		DESCRIPTION  "Incoming Info Request"
		::={ acosVpnIkeStatsGlobalS 18 }

		v2InInfoRsp OBJECT-TYPE
		SYNTAX  CounterBasedGauge64
		MAX-ACCESS read-only
		STATUS current
		DESCRIPTION  "Incoming Info Response"
		::={ acosVpnIkeStatsGlobalS 19 }

		v2OutInfoReq OBJECT-TYPE
		SYNTAX  CounterBasedGauge64
		MAX-ACCESS read-only
		STATUS current
		DESCRIPTION  "Outgoing Info Request"
		::={ acosVpnIkeStatsGlobalS 20 }

		v2OutInfoRsp OBJECT-TYPE
		SYNTAX  CounterBasedGauge64
		MAX-ACCESS read-only
		STATUS current
		DESCRIPTION  "Outgoing Info Response"
		::={ acosVpnIkeStatsGlobalS 21 }

		v1InIdProtReq OBJECT-TYPE
		SYNTAX  CounterBasedGauge64
		MAX-ACCESS read-only
		STATUS current
		DESCRIPTION  "Incoming ID Protection Request"
		::={ acosVpnIkeStatsGlobalS 22 }

		v1InIdProtRsp OBJECT-TYPE
		SYNTAX  CounterBasedGauge64
		MAX-ACCESS read-only
		STATUS current
		DESCRIPTION  "Incoming ID Protection Response"
		::={ acosVpnIkeStatsGlobalS 23 }

		v1OutIdProtReq OBJECT-TYPE
		SYNTAX  CounterBasedGauge64
		MAX-ACCESS read-only
		STATUS current
		DESCRIPTION  "Outgoing ID Protection Request"
		::={ acosVpnIkeStatsGlobalS 24 }

		v1OutIdProtRsp OBJECT-TYPE
		SYNTAX  CounterBasedGauge64
		MAX-ACCESS read-only
		STATUS current
		DESCRIPTION  "Outgoing ID Protection Response"
		::={ acosVpnIkeStatsGlobalS 25 }

		v1InAuthOnlyReq OBJECT-TYPE
		SYNTAX  CounterBasedGauge64
		MAX-ACCESS read-only
		STATUS current
		DESCRIPTION  "Incoming Auth Only Request"
		::={ acosVpnIkeStatsGlobalS 26 }

		v1InAuthOnlyRsp OBJECT-TYPE
		SYNTAX  CounterBasedGauge64
		MAX-ACCESS read-only
		STATUS current
		DESCRIPTION  "Incoming Auth Only Response"
		::={ acosVpnIkeStatsGlobalS 27 }

		v1OutAuthOnlyReq OBJECT-TYPE
		SYNTAX  CounterBasedGauge64
		MAX-ACCESS read-only
		STATUS current
		DESCRIPTION  "Outgoing Auth Only Request"
		::={ acosVpnIkeStatsGlobalS 28 }

		v1OutAuthOnlyRsp OBJECT-TYPE
		SYNTAX  CounterBasedGauge64
		MAX-ACCESS read-only
		STATUS current
		DESCRIPTION  "Outgoing Auth Only Response"
		::={ acosVpnIkeStatsGlobalS 29 }

		v1InAggressiveReq OBJECT-TYPE
		SYNTAX  CounterBasedGauge64
		MAX-ACCESS read-only
		STATUS current
		DESCRIPTION  "Incoming Aggressive Request"
		::={ acosVpnIkeStatsGlobalS 30 }

		v1InAggressiveRsp OBJECT-TYPE
		SYNTAX  CounterBasedGauge64
		MAX-ACCESS read-only
		STATUS current
		DESCRIPTION  "Incoming Aggressive Response"
		::={ acosVpnIkeStatsGlobalS 31 }

		v1OutAggressiveReq OBJECT-TYPE
		SYNTAX  CounterBasedGauge64
		MAX-ACCESS read-only
		STATUS current
		DESCRIPTION  "Outgoing Aggressive Request"
		::={ acosVpnIkeStatsGlobalS 32 }

		v1OutAggressiveRsp OBJECT-TYPE
		SYNTAX  CounterBasedGauge64
		MAX-ACCESS read-only
		STATUS current
		DESCRIPTION  "Outgoing Aggressive Response"
		::={ acosVpnIkeStatsGlobalS 33 }

		v1InInfoV1Req OBJECT-TYPE
		SYNTAX  CounterBasedGauge64
		MAX-ACCESS read-only
		STATUS current
		DESCRIPTION  "Incoming Info Request"
		::={ acosVpnIkeStatsGlobalS 34 }

		v1InInfoV1Rsp OBJECT-TYPE
		SYNTAX  CounterBasedGauge64
		MAX-ACCESS read-only
		STATUS current
		DESCRIPTION  "Incoming Info Response"
		::={ acosVpnIkeStatsGlobalS 35 }

		v1OutInfoV1Req OBJECT-TYPE
		SYNTAX  CounterBasedGauge64
		MAX-ACCESS read-only
		STATUS current
		DESCRIPTION  "Outgoing Info Request"
		::={ acosVpnIkeStatsGlobalS 36 }

		v1OutInfoV1Rsp OBJECT-TYPE
		SYNTAX  CounterBasedGauge64
		MAX-ACCESS read-only
		STATUS current
		DESCRIPTION  "Outgoing Info Response"
		::={ acosVpnIkeStatsGlobalS 37 }

		v1InTransactionReq OBJECT-TYPE
		SYNTAX  CounterBasedGauge64
		MAX-ACCESS read-only
		STATUS current
		DESCRIPTION  "Incoming Transaction Request"
		::={ acosVpnIkeStatsGlobalS 38 }

		v1InTransactionRsp OBJECT-TYPE
		SYNTAX  CounterBasedGauge64
		MAX-ACCESS read-only
		STATUS current
		DESCRIPTION  "Incoming Transaction Response"
		::={ acosVpnIkeStatsGlobalS 39 }

		v1OutTransactionReq OBJECT-TYPE
		SYNTAX  CounterBasedGauge64
		MAX-ACCESS read-only
		STATUS current
		DESCRIPTION  "Outgoing Transaction Request"
		::={ acosVpnIkeStatsGlobalS 40 }

		v1OutTransactionRsp OBJECT-TYPE
		SYNTAX  CounterBasedGauge64
		MAX-ACCESS read-only
		STATUS current
		DESCRIPTION  "Outgoing Transaction Response"
		::={ acosVpnIkeStatsGlobalS 41 }

		v1InQuickModeReq OBJECT-TYPE
		SYNTAX  CounterBasedGauge64
		MAX-ACCESS read-only
		STATUS current
		DESCRIPTION  "Incoming Quick Mode Request"
		::={ acosVpnIkeStatsGlobalS 42 }

		v1InQuickModeRsp OBJECT-TYPE
		SYNTAX  CounterBasedGauge64
		MAX-ACCESS read-only
		STATUS current
		DESCRIPTION  "Incoming Quick Mode Response"
		::={ acosVpnIkeStatsGlobalS 43 }

		v1OutQuickModeReq OBJECT-TYPE
		SYNTAX  CounterBasedGauge64
		MAX-ACCESS read-only
		STATUS current
		DESCRIPTION  "Outgoing Quick Mode Request"
		::={ acosVpnIkeStatsGlobalS 44 }

		v1OutQuickModeRsp OBJECT-TYPE
		SYNTAX  CounterBasedGauge64
		MAX-ACCESS read-only
		STATUS current
		DESCRIPTION  "Outgoing Quick Mode Response"
		::={ acosVpnIkeStatsGlobalS 45 }

		v1InNewGroupModeReq OBJECT-TYPE
		SYNTAX  CounterBasedGauge64
		MAX-ACCESS read-only
		STATUS current
		DESCRIPTION  "Incoming New Group Mode Request"
		::={ acosVpnIkeStatsGlobalS 46 }

		v1InNewGroupModeRsp OBJECT-TYPE
		SYNTAX  CounterBasedGauge64
		MAX-ACCESS read-only
		STATUS current
		DESCRIPTION  "Incoming New Group Mode Response"
		::={ acosVpnIkeStatsGlobalS 47 }

		v1OutNewGroupModeReq OBJECT-TYPE
		SYNTAX  CounterBasedGauge64
		MAX-ACCESS read-only
		STATUS current
		DESCRIPTION  "Outgoing New Group Mode Request"
		::={ acosVpnIkeStatsGlobalS 48 }

		v1OutNewGroupModeRsp OBJECT-TYPE
		SYNTAX  CounterBasedGauge64
		MAX-ACCESS read-only
		STATUS current
		DESCRIPTION  "Outgoing New Group Mode Response"
		::={ acosVpnIkeStatsGlobalS 49 }

acosVpnIkeGateway                   OBJECT IDENTIFIER ::= { acosVpn 3 }
acosVpnIkeGatewayS                  OBJECT IDENTIFIER ::= { acosVpnIkeGateway 1 }

vpnIkeGatewaySTable OBJECT-TYPE
		SYNTAX SEQUENCE OF VpnIkeGatewaySEntry
		MAX-ACCESS not-accessible
		STATUS current
		::={ acosVpnIkeGatewayS 1 }


	vpnIkeGatewaySEntry OBJECT-TYPE
		SYNTAX VpnIkeGatewaySEntry
		MAX-ACCESS not-accessible
		STATUS current
		INDEX {
			name
		}
		::={ vpnIkeGatewaySTable 1 }


	VpnIkeGatewaySEntry ::=
		SEQUENCE {
			name DisplayString,
			v2InitRekey CounterBasedGauge64,
			v2RspRekey CounterBasedGauge64,
			v2ChildSaRekey CounterBasedGauge64,
			v2InInvalid CounterBasedGauge64,
			v2InInvalidSpi CounterBasedGauge64,
			v2InInitReq CounterBasedGauge64,
			v2InInitRsp CounterBasedGauge64,
			v2OutInitReq CounterBasedGauge64,
			v2OutInitRsp CounterBasedGauge64,
			v2InAuthReq CounterBasedGauge64,
			v2InAuthRsp CounterBasedGauge64,
			v2OutAuthReq CounterBasedGauge64,
			v2OutAuthRsp CounterBasedGauge64,
			v2InCreateChildReq CounterBasedGauge64,
			v2InCreateChildRsp CounterBasedGauge64,
			v2OutCreateChildReq CounterBasedGauge64,
			v2OutCreateChildRsp CounterBasedGauge64,
			v2InInfoReq CounterBasedGauge64,
			v2InInfoRsp CounterBasedGauge64,
			v2OutInfoReq CounterBasedGauge64,
			v2OutInfoRsp CounterBasedGauge64,
			v1InIdProtReq CounterBasedGauge64,
			v1InIdProtRsp CounterBasedGauge64,
			v1OutIdProtReq CounterBasedGauge64,
			v1OutIdProtRsp CounterBasedGauge64,
			v1InAuthOnlyReq CounterBasedGauge64,
			v1InAuthOnlyRsp CounterBasedGauge64,
			v1OutAuthOnlyReq CounterBasedGauge64,
			v1OutAuthOnlyRsp CounterBasedGauge64,
			v1InAggressiveReq CounterBasedGauge64,
			v1InAggressiveRsp CounterBasedGauge64,
			v1OutAggressiveReq CounterBasedGauge64,
			v1OutAggressiveRsp CounterBasedGauge64,
			v1InInfoV1Req CounterBasedGauge64,
			v1InInfoV1Rsp CounterBasedGauge64,
			v1OutInfoV1Req CounterBasedGauge64,
			v1OutInfoV1Rsp CounterBasedGauge64,
			v1InTransactionReq CounterBasedGauge64,
			v1InTransactionRsp CounterBasedGauge64,
			v1OutTransactionReq CounterBasedGauge64,
			v1OutTransactionRsp CounterBasedGauge64,
			v1InQuickModeReq CounterBasedGauge64,
			v1InQuickModeRsp CounterBasedGauge64,
			v1OutQuickModeReq CounterBasedGauge64,
			v1OutQuickModeRsp CounterBasedGauge64,
			v1InNewGroupModeReq CounterBasedGauge64,
			v1InNewGroupModeRsp CounterBasedGauge64,
			v1OutNewGroupModeReq CounterBasedGauge64,
			v1OutNewGroupModeRsp CounterBasedGauge64,
			v1ChildSaInvalidSpi CounterBasedGauge64,
			v2ChildSaInvalidSpi CounterBasedGauge64,
			ikeCurrentVersion CounterBasedGauge64
		}

			name OBJECT-TYPE
			SYNTAX  DisplayString
			MAX-ACCESS read-only
			STATUS current
			DESCRIPTION  "IKE-gateway name"
			::={ vpnIkeGatewaySEntry 1 }

			v2InitRekey OBJECT-TYPE
			SYNTAX  CounterBasedGauge64
			MAX-ACCESS read-only
			STATUS current
			DESCRIPTION  "Initiate Rekey"
			::={ vpnIkeGatewaySEntry 2 }

			v2RspRekey OBJECT-TYPE
			SYNTAX  CounterBasedGauge64
			MAX-ACCESS read-only
			STATUS current
			DESCRIPTION  "Respond Rekey"
			::={ vpnIkeGatewaySEntry 3 }

			v2ChildSaRekey OBJECT-TYPE
			SYNTAX  CounterBasedGauge64
			MAX-ACCESS read-only
			STATUS current
			DESCRIPTION  "Child SA Rekey"
			::={ vpnIkeGatewaySEntry 4 }

			v2InInvalid OBJECT-TYPE
			SYNTAX  CounterBasedGauge64
			MAX-ACCESS read-only
			STATUS current
			DESCRIPTION  "Incoming Invalid"
			::={ vpnIkeGatewaySEntry 5 }

			v2InInvalidSpi OBJECT-TYPE
			SYNTAX  CounterBasedGauge64
			MAX-ACCESS read-only
			STATUS current
			DESCRIPTION  "Incoming Invalid SPI"
			::={ vpnIkeGatewaySEntry 6 }

			v2InInitReq OBJECT-TYPE
			SYNTAX  CounterBasedGauge64
			MAX-ACCESS read-only
			STATUS current
			DESCRIPTION  "Incoming Init Request"
			::={ vpnIkeGatewaySEntry 7 }

			v2InInitRsp OBJECT-TYPE
			SYNTAX  CounterBasedGauge64
			MAX-ACCESS read-only
			STATUS current
			DESCRIPTION  "Incoming Init Response"
			::={ vpnIkeGatewaySEntry 8 }

			v2OutInitReq OBJECT-TYPE
			SYNTAX  CounterBasedGauge64
			MAX-ACCESS read-only
			STATUS current
			DESCRIPTION  "Outgoing Init Request"
			::={ vpnIkeGatewaySEntry 9 }

			v2OutInitRsp OBJECT-TYPE
			SYNTAX  CounterBasedGauge64
			MAX-ACCESS read-only
			STATUS current
			DESCRIPTION  "Outgoing Init Response"
			::={ vpnIkeGatewaySEntry 10 }

			v2InAuthReq OBJECT-TYPE
			SYNTAX  CounterBasedGauge64
			MAX-ACCESS read-only
			STATUS current
			DESCRIPTION  "Incoming Auth Request"
			::={ vpnIkeGatewaySEntry 11 }

			v2InAuthRsp OBJECT-TYPE
			SYNTAX  CounterBasedGauge64
			MAX-ACCESS read-only
			STATUS current
			DESCRIPTION  "Incoming Auth Response"
			::={ vpnIkeGatewaySEntry 12 }

			v2OutAuthReq OBJECT-TYPE
			SYNTAX  CounterBasedGauge64
			MAX-ACCESS read-only
			STATUS current
			DESCRIPTION  "Outgoing Auth Request"
			::={ vpnIkeGatewaySEntry 13 }

			v2OutAuthRsp OBJECT-TYPE
			SYNTAX  CounterBasedGauge64
			MAX-ACCESS read-only
			STATUS current
			DESCRIPTION  "Outgoing Auth Response"
			::={ vpnIkeGatewaySEntry 14 }

			v2InCreateChildReq OBJECT-TYPE
			SYNTAX  CounterBasedGauge64
			MAX-ACCESS read-only
			STATUS current
			DESCRIPTION  "Incoming Create Child Request"
			::={ vpnIkeGatewaySEntry 15 }

			v2InCreateChildRsp OBJECT-TYPE
			SYNTAX  CounterBasedGauge64
			MAX-ACCESS read-only
			STATUS current
			DESCRIPTION  "Incoming Create Child Response"
			::={ vpnIkeGatewaySEntry 16 }

			v2OutCreateChildReq OBJECT-TYPE
			SYNTAX  CounterBasedGauge64
			MAX-ACCESS read-only
			STATUS current
			DESCRIPTION  "Outgoing Create Child Request"
			::={ vpnIkeGatewaySEntry 17 }

			v2OutCreateChildRsp OBJECT-TYPE
			SYNTAX  CounterBasedGauge64
			MAX-ACCESS read-only
			STATUS current
			DESCRIPTION  "Outgoing Create Child Response"
			::={ vpnIkeGatewaySEntry 18 }

			v2InInfoReq OBJECT-TYPE
			SYNTAX  CounterBasedGauge64
			MAX-ACCESS read-only
			STATUS current
			DESCRIPTION  "Incoming Info Request"
			::={ vpnIkeGatewaySEntry 19 }

			v2InInfoRsp OBJECT-TYPE
			SYNTAX  CounterBasedGauge64
			MAX-ACCESS read-only
			STATUS current
			DESCRIPTION  "Incoming Info Response"
			::={ vpnIkeGatewaySEntry 20 }

			v2OutInfoReq OBJECT-TYPE
			SYNTAX  CounterBasedGauge64
			MAX-ACCESS read-only
			STATUS current
			DESCRIPTION  "Outgoing Info Request"
			::={ vpnIkeGatewaySEntry 21 }

			v2OutInfoRsp OBJECT-TYPE
			SYNTAX  CounterBasedGauge64
			MAX-ACCESS read-only
			STATUS current
			DESCRIPTION  "Outgoing Info Response"
			::={ vpnIkeGatewaySEntry 22 }

			v1InIdProtReq OBJECT-TYPE
			SYNTAX  CounterBasedGauge64
			MAX-ACCESS read-only
			STATUS current
			DESCRIPTION  "Incoming ID Protection Request"
			::={ vpnIkeGatewaySEntry 23 }

			v1InIdProtRsp OBJECT-TYPE
			SYNTAX  CounterBasedGauge64
			MAX-ACCESS read-only
			STATUS current
			DESCRIPTION  "Incoming ID Protection Response"
			::={ vpnIkeGatewaySEntry 24 }

			v1OutIdProtReq OBJECT-TYPE
			SYNTAX  CounterBasedGauge64
			MAX-ACCESS read-only
			STATUS current
			DESCRIPTION  "Outgoing ID Protection Request"
			::={ vpnIkeGatewaySEntry 25 }

			v1OutIdProtRsp OBJECT-TYPE
			SYNTAX  CounterBasedGauge64
			MAX-ACCESS read-only
			STATUS current
			DESCRIPTION  "Outgoing ID Protection Response"
			::={ vpnIkeGatewaySEntry 26 }

			v1InAuthOnlyReq OBJECT-TYPE
			SYNTAX  CounterBasedGauge64
			MAX-ACCESS read-only
			STATUS current
			DESCRIPTION  "Incoming Auth Only Request"
			::={ vpnIkeGatewaySEntry 27 }

			v1InAuthOnlyRsp OBJECT-TYPE
			SYNTAX  CounterBasedGauge64
			MAX-ACCESS read-only
			STATUS current
			DESCRIPTION  "Incoming Auth Only Response"
			::={ vpnIkeGatewaySEntry 28 }

			v1OutAuthOnlyReq OBJECT-TYPE
			SYNTAX  CounterBasedGauge64
			MAX-ACCESS read-only
			STATUS current
			DESCRIPTION  "Outgoing Auth Only Request"
			::={ vpnIkeGatewaySEntry 29 }

			v1OutAuthOnlyRsp OBJECT-TYPE
			SYNTAX  CounterBasedGauge64
			MAX-ACCESS read-only
			STATUS current
			DESCRIPTION  "Outgoing Auth Only Response"
			::={ vpnIkeGatewaySEntry 30 }

			v1InAggressiveReq OBJECT-TYPE
			SYNTAX  CounterBasedGauge64
			MAX-ACCESS read-only
			STATUS current
			DESCRIPTION  "Incoming Aggressive Request"
			::={ vpnIkeGatewaySEntry 31 }

			v1InAggressiveRsp OBJECT-TYPE
			SYNTAX  CounterBasedGauge64
			MAX-ACCESS read-only
			STATUS current
			DESCRIPTION  "Incoming Aggressive Response"
			::={ vpnIkeGatewaySEntry 32 }

			v1OutAggressiveReq OBJECT-TYPE
			SYNTAX  CounterBasedGauge64
			MAX-ACCESS read-only
			STATUS current
			DESCRIPTION  "Outgoing Aggressive Request"
			::={ vpnIkeGatewaySEntry 33 }

			v1OutAggressiveRsp OBJECT-TYPE
			SYNTAX  CounterBasedGauge64
			MAX-ACCESS read-only
			STATUS current
			DESCRIPTION  "Outgoing Aggressive Response"
			::={ vpnIkeGatewaySEntry 34 }

			v1InInfoV1Req OBJECT-TYPE
			SYNTAX  CounterBasedGauge64
			MAX-ACCESS read-only
			STATUS current
			DESCRIPTION  "Incoming Info Request"
			::={ vpnIkeGatewaySEntry 35 }

			v1InInfoV1Rsp OBJECT-TYPE
			SYNTAX  CounterBasedGauge64
			MAX-ACCESS read-only
			STATUS current
			DESCRIPTION  "Incoming Info Response"
			::={ vpnIkeGatewaySEntry 36 }

			v1OutInfoV1Req OBJECT-TYPE
			SYNTAX  CounterBasedGauge64
			MAX-ACCESS read-only
			STATUS current
			DESCRIPTION  "Outgoing Info Request"
			::={ vpnIkeGatewaySEntry 37 }

			v1OutInfoV1Rsp OBJECT-TYPE
			SYNTAX  CounterBasedGauge64
			MAX-ACCESS read-only
			STATUS current
			DESCRIPTION  "Outgoing Info Response"
			::={ vpnIkeGatewaySEntry 38 }

			v1InTransactionReq OBJECT-TYPE
			SYNTAX  CounterBasedGauge64
			MAX-ACCESS read-only
			STATUS current
			DESCRIPTION  "Incoming Transaction Request"
			::={ vpnIkeGatewaySEntry 39 }

			v1InTransactionRsp OBJECT-TYPE
			SYNTAX  CounterBasedGauge64
			MAX-ACCESS read-only
			STATUS current
			DESCRIPTION  "Incoming Transaction Response"
			::={ vpnIkeGatewaySEntry 40 }

			v1OutTransactionReq OBJECT-TYPE
			SYNTAX  CounterBasedGauge64
			MAX-ACCESS read-only
			STATUS current
			DESCRIPTION  "Outgoing Transaction Request"
			::={ vpnIkeGatewaySEntry 41 }

			v1OutTransactionRsp OBJECT-TYPE
			SYNTAX  CounterBasedGauge64
			MAX-ACCESS read-only
			STATUS current
			DESCRIPTION  "Outgoing Transaction Response"
			::={ vpnIkeGatewaySEntry 42 }

			v1InQuickModeReq OBJECT-TYPE
			SYNTAX  CounterBasedGauge64
			MAX-ACCESS read-only
			STATUS current
			DESCRIPTION  "Incoming Quick Mode Request"
			::={ vpnIkeGatewaySEntry 43 }

			v1InQuickModeRsp OBJECT-TYPE
			SYNTAX  CounterBasedGauge64
			MAX-ACCESS read-only
			STATUS current
			DESCRIPTION  "Incoming Quick Mode Response"
			::={ vpnIkeGatewaySEntry 44 }

			v1OutQuickModeReq OBJECT-TYPE
			SYNTAX  CounterBasedGauge64
			MAX-ACCESS read-only
			STATUS current
			DESCRIPTION  "Outgoing Quick Mode Request"
			::={ vpnIkeGatewaySEntry 45 }

			v1OutQuickModeRsp OBJECT-TYPE
			SYNTAX  CounterBasedGauge64
			MAX-ACCESS read-only
			STATUS current
			DESCRIPTION  "Outgoing Quick Mode Response"
			::={ vpnIkeGatewaySEntry 46 }

			v1InNewGroupModeReq OBJECT-TYPE
			SYNTAX  CounterBasedGauge64
			MAX-ACCESS read-only
			STATUS current
			DESCRIPTION  "Incoming New Group Mode Request"
			::={ vpnIkeGatewaySEntry 47 }

			v1InNewGroupModeRsp OBJECT-TYPE
			SYNTAX  CounterBasedGauge64
			MAX-ACCESS read-only
			STATUS current
			DESCRIPTION  "Incoming New Group Mode Response"
			::={ vpnIkeGatewaySEntry 48 }

			v1OutNewGroupModeReq OBJECT-TYPE
			SYNTAX  CounterBasedGauge64
			MAX-ACCESS read-only
			STATUS current
			DESCRIPTION  "Outgoing New Group Mode Request"
			::={ vpnIkeGatewaySEntry 49 }

			v1OutNewGroupModeRsp OBJECT-TYPE
			SYNTAX  CounterBasedGauge64
			MAX-ACCESS read-only
			STATUS current
			DESCRIPTION  "Outgoing New Group Mode Response"
			::={ vpnIkeGatewaySEntry 50 }

			v1ChildSaInvalidSpi OBJECT-TYPE
			SYNTAX  CounterBasedGauge64
			MAX-ACCESS read-only
			STATUS current
			DESCRIPTION  "Invalid SPI for Child SAs"
			::={ vpnIkeGatewaySEntry 51 }

			v2ChildSaInvalidSpi OBJECT-TYPE
			SYNTAX  CounterBasedGauge64
			MAX-ACCESS read-only
			STATUS current
			DESCRIPTION  "Invalid SPI for Child SAs"
			::={ vpnIkeGatewaySEntry 52 }

			ikeCurrentVersion OBJECT-TYPE
			SYNTAX  CounterBasedGauge64
			MAX-ACCESS read-only
			STATUS current
			DESCRIPTION  "IKE version"
			::={ vpnIkeGatewaySEntry 53 }

acosVpnIpsec                        OBJECT IDENTIFIER ::= { acosVpn 4 }
acosVpnIpsecS                       OBJECT IDENTIFIER ::= { acosVpnIpsec 1 }

vpnIpsecSTable OBJECT-TYPE
		SYNTAX SEQUENCE OF VpnIpsecSEntry
		MAX-ACCESS not-accessible
		STATUS current
		::={ acosVpnIpsecS 1 }


	vpnIpsecSEntry OBJECT-TYPE
		SYNTAX VpnIpsecSEntry
		MAX-ACCESS not-accessible
		STATUS current
		INDEX {
			vpnIpsetName
		}
		::={ vpnIpsecSTable 1 }


	VpnIpsecSEntry ::=
		SEQUENCE {
			vpnIpsetName DisplayString,
			packetsEncrypted CounterBasedGauge64,
			packetsDecrypted CounterBasedGauge64,
			antiReplayNum CounterBasedGauge64,
			rekeyNum CounterBasedGauge64,
			packetsErrInactive CounterBasedGauge64,
			packetsErrEncryption CounterBasedGauge64,
			packetsErrPadCheck CounterBasedGauge64,
			packetsErrPktSanity CounterBasedGauge64,
			packetsErrIcvCheck CounterBasedGauge64,
			packetsErrLifetimeLifebytes CounterBasedGauge64,
			bytesEncrypted CounterBasedGauge64,
			bytesDecrypted CounterBasedGauge64,
			prefragSuccess CounterBasedGauge64,
			prefragError CounterBasedGauge64,
			caviumBytesEncrypted CounterBasedGauge64,
			caviumBytesDecrypted CounterBasedGauge64,
			caviumPacketsEncrypted CounterBasedGauge64,
			caviumPacketsDecrypted CounterBasedGauge64,
			qatBytesEncrypted CounterBasedGauge64,
			qatBytesDecrypted CounterBasedGauge64,
			qatPacketsEncrypted CounterBasedGauge64,
			qatPacketsDecrypted CounterBasedGauge64,
			tunnelIntfDown CounterBasedGauge64,
			pktFailPrepToSend CounterBasedGauge64,
			noNextHop CounterBasedGauge64,
			invalidTunnelId CounterBasedGauge64,
			noTunnelFound CounterBasedGauge64,
			pktFailToSend CounterBasedGauge64,
			fragAfterEncapFragPackets CounterBasedGauge64,
			fragReceived CounterBasedGauge64,
			sequenceNum CounterBasedGauge64,
			sequenceNumRollover CounterBasedGauge64,
			packetsErrNhCheck CounterBasedGauge64
		}

			vpnIpsetName OBJECT-TYPE
			SYNTAX  DisplayString
			MAX-ACCESS read-only
			STATUS current
			DESCRIPTION  "IPsec name"
			::={ vpnIpsecSEntry 1 }

			packetsEncrypted OBJECT-TYPE
			SYNTAX  CounterBasedGauge64
			MAX-ACCESS read-only
			STATUS current
			DESCRIPTION  "Encrypted Packets"
			::={ vpnIpsecSEntry 2 }

			packetsDecrypted OBJECT-TYPE
			SYNTAX  CounterBasedGauge64
			MAX-ACCESS read-only
			STATUS current
			DESCRIPTION  "Decrypted Packets"
			::={ vpnIpsecSEntry 3 }

			antiReplayNum OBJECT-TYPE
			SYNTAX  CounterBasedGauge64
			MAX-ACCESS read-only
			STATUS current
			DESCRIPTION  "Anti-Replay Failure"
			::={ vpnIpsecSEntry 4 }

			rekeyNum OBJECT-TYPE
			SYNTAX  CounterBasedGauge64
			MAX-ACCESS read-only
			STATUS current
			DESCRIPTION  "Rekey Times"
			::={ vpnIpsecSEntry 5 }

			packetsErrInactive OBJECT-TYPE
			SYNTAX  CounterBasedGauge64
			MAX-ACCESS read-only
			STATUS current
			DESCRIPTION  "Inactive Error"
			::={ vpnIpsecSEntry 6 }

			packetsErrEncryption OBJECT-TYPE
			SYNTAX  CounterBasedGauge64
			MAX-ACCESS read-only
			STATUS current
			DESCRIPTION  "Encryption Error"
			::={ vpnIpsecSEntry 7 }

			packetsErrPadCheck OBJECT-TYPE
			SYNTAX  CounterBasedGauge64
			MAX-ACCESS read-only
			STATUS current
			DESCRIPTION  "Pad Check Error"
			::={ vpnIpsecSEntry 8 }

			packetsErrPktSanity OBJECT-TYPE
			SYNTAX  CounterBasedGauge64
			MAX-ACCESS read-only
			STATUS current
			DESCRIPTION  "Packets Sanity Error"
			::={ vpnIpsecSEntry 9 }

			packetsErrIcvCheck OBJECT-TYPE
			SYNTAX  CounterBasedGauge64
			MAX-ACCESS read-only
			STATUS current
			DESCRIPTION  "ICV Check Error"
			::={ vpnIpsecSEntry 10 }

			packetsErrLifetimeLifebytes OBJECT-TYPE
			SYNTAX  CounterBasedGauge64
			MAX-ACCESS read-only
			STATUS current
			DESCRIPTION  "Lifetime Lifebytes Error"
			::={ vpnIpsecSEntry 11 }

			bytesEncrypted OBJECT-TYPE
			SYNTAX  CounterBasedGauge64
			MAX-ACCESS read-only
			STATUS current
			DESCRIPTION  "Encrypted Bytes"
			::={ vpnIpsecSEntry 12 }

			bytesDecrypted OBJECT-TYPE
			SYNTAX  CounterBasedGauge64
			MAX-ACCESS read-only
			STATUS current
			DESCRIPTION  "Decrypted Bytes"
			::={ vpnIpsecSEntry 13 }

			prefragSuccess OBJECT-TYPE
			SYNTAX  CounterBasedGauge64
			MAX-ACCESS read-only
			STATUS current
			DESCRIPTION  "Pre-frag Success"
			::={ vpnIpsecSEntry 14 }

			prefragError OBJECT-TYPE
			SYNTAX  CounterBasedGauge64
			MAX-ACCESS read-only
			STATUS current
			DESCRIPTION  "Pre-frag Error"
			::={ vpnIpsecSEntry 15 }

			caviumBytesEncrypted OBJECT-TYPE
			SYNTAX  CounterBasedGauge64
			MAX-ACCESS read-only
			STATUS current
			DESCRIPTION  "CAVIUM Encrypted Bytes"
			::={ vpnIpsecSEntry 16 }

			caviumBytesDecrypted OBJECT-TYPE
			SYNTAX  CounterBasedGauge64
			MAX-ACCESS read-only
			STATUS current
			DESCRIPTION  "CAVIUM Decrypted Bytes"
			::={ vpnIpsecSEntry 17 }

			caviumPacketsEncrypted OBJECT-TYPE
			SYNTAX  CounterBasedGauge64
			MAX-ACCESS read-only
			STATUS current
			DESCRIPTION  "CAVIUM Encrypted Packets"
			::={ vpnIpsecSEntry 18 }

			caviumPacketsDecrypted OBJECT-TYPE
			SYNTAX  CounterBasedGauge64
			MAX-ACCESS read-only
			STATUS current
			DESCRIPTION  "CAVIUM Decrypted Packets"
			::={ vpnIpsecSEntry 19 }

			qatBytesEncrypted OBJECT-TYPE
			SYNTAX  CounterBasedGauge64
			MAX-ACCESS read-only
			STATUS current
			DESCRIPTION  "QAT Encrypted Bytes"
			::={ vpnIpsecSEntry 20 }

			qatBytesDecrypted OBJECT-TYPE
			SYNTAX  CounterBasedGauge64
			MAX-ACCESS read-only
			STATUS current
			DESCRIPTION  "QAT Decrypted Bytes"
			::={ vpnIpsecSEntry 21 }

			qatPacketsEncrypted OBJECT-TYPE
			SYNTAX  CounterBasedGauge64
			MAX-ACCESS read-only
			STATUS current
			DESCRIPTION  "QAT Encrypted Packets"
			::={ vpnIpsecSEntry 22 }

			qatPacketsDecrypted OBJECT-TYPE
			SYNTAX  CounterBasedGauge64
			MAX-ACCESS read-only
			STATUS current
			DESCRIPTION  "QAT Decrypted Packets"
			::={ vpnIpsecSEntry 23 }

			tunnelIntfDown OBJECT-TYPE
			SYNTAX  CounterBasedGauge64
			MAX-ACCESS read-only
			STATUS current
			DESCRIPTION  "Packet dropped: Tunnel Interface Down"
			::={ vpnIpsecSEntry 24 }

			pktFailPrepToSend OBJECT-TYPE
			SYNTAX  CounterBasedGauge64
			MAX-ACCESS read-only
			STATUS current
			DESCRIPTION  "Packet dropped: Failed in prepare to send"
			::={ vpnIpsecSEntry 25 }

			noNextHop OBJECT-TYPE
			SYNTAX  CounterBasedGauge64
			MAX-ACCESS read-only
			STATUS current
			DESCRIPTION  "Packet dropped: No next hop"
			::={ vpnIpsecSEntry 26 }

			invalidTunnelId OBJECT-TYPE
			SYNTAX  CounterBasedGauge64
			MAX-ACCESS read-only
			STATUS current
			DESCRIPTION  "Packet dropped: Invalid tunnel ID"
			::={ vpnIpsecSEntry 27 }

			noTunnelFound OBJECT-TYPE
			SYNTAX  CounterBasedGauge64
			MAX-ACCESS read-only
			STATUS current
			DESCRIPTION  "Packet dropped: No tunnel found"
			::={ vpnIpsecSEntry 28 }

			pktFailToSend OBJECT-TYPE
			SYNTAX  CounterBasedGauge64
			MAX-ACCESS read-only
			STATUS current
			DESCRIPTION  "Packet dropped: Failed to send"
			::={ vpnIpsecSEntry 29 }

			fragAfterEncapFragPackets OBJECT-TYPE
			SYNTAX  CounterBasedGauge64
			MAX-ACCESS read-only
			STATUS current
			DESCRIPTION  "Frag-after-encap Fragment Generated"
			::={ vpnIpsecSEntry 30 }

			fragReceived OBJECT-TYPE
			SYNTAX  CounterBasedGauge64
			MAX-ACCESS read-only
			STATUS current
			DESCRIPTION  "Fragment Received"
			::={ vpnIpsecSEntry 31 }

			sequenceNum OBJECT-TYPE
			SYNTAX  CounterBasedGauge64
			MAX-ACCESS read-only
			STATUS current
			DESCRIPTION  "Sequence Number"
			::={ vpnIpsecSEntry 32 }

			sequenceNumRollover OBJECT-TYPE
			SYNTAX  CounterBasedGauge64
			MAX-ACCESS read-only
			STATUS current
			DESCRIPTION  "Sequence Number Rollover"
			::={ vpnIpsecSEntry 33 }

			packetsErrNhCheck OBJECT-TYPE
			SYNTAX  CounterBasedGauge64
			MAX-ACCESS read-only
			STATUS current
			DESCRIPTION  "Next Header Check Error"
			::={ vpnIpsecSEntry 34 }

acosVpnIpsecSaStats                 OBJECT IDENTIFIER ::= { acosVpn 20 }
acosVpnIpsecSaStatsS                OBJECT IDENTIFIER ::= { acosVpnIpsecSaStats 1 }

vpnIpsecSaStatsSTable OBJECT-TYPE
		SYNTAX SEQUENCE OF VpnIpsecSaStatsSEntry
		MAX-ACCESS not-accessible
		STATUS current
		::={ acosVpnIpsecSaStatsS 1 }


	vpnIpsecSaStatsSEntry OBJECT-TYPE
		SYNTAX VpnIpsecSaStatsSEntry
		MAX-ACCESS not-accessible
		STATUS current
		INDEX {
			samplingEnable
		}
		::={ vpnIpsecSaStatsSTable 1 }


	VpnIpsecSaStatsSEntry ::=
		SEQUENCE {
			samplingEnable DisplayString,
			packetsEncrypted CounterBasedGauge64,
			packetsDecrypted CounterBasedGauge64,
			antiReplayNum CounterBasedGauge64,
			rekeyNum CounterBasedGauge64,
			packetsErrInactive CounterBasedGauge64,
			packetsErrEncryption CounterBasedGauge64,
			packetsErrPadCheck CounterBasedGauge64,
			packetsErrPktSanity CounterBasedGauge64,
			packetsErrIcvCheck CounterBasedGauge64,
			packetsErrLifetimeLifebytes CounterBasedGauge64,
			bytesEncrypted CounterBasedGauge64,
			bytesDecrypted CounterBasedGauge64,
			prefragSuccess CounterBasedGauge64,
			prefragError CounterBasedGauge64,
			caviumBytesEncrypted CounterBasedGauge64,
			caviumBytesDecrypted CounterBasedGauge64,
			caviumPacketsEncrypted CounterBasedGauge64,
			caviumPacketsDecrypted CounterBasedGauge64,
			qatBytesEncrypted CounterBasedGauge64,
			qatBytesDecrypted CounterBasedGauge64,
			qatPacketsEncrypted CounterBasedGauge64,
			qatPacketsDecrypted CounterBasedGauge64,
			tunnelIntfDown CounterBasedGauge64,
			pktFailPrepToSend CounterBasedGauge64,
			noNextHop CounterBasedGauge64,
			invalidTunnelId CounterBasedGauge64,
			noTunnelFound CounterBasedGauge64,
			pktFailToSend CounterBasedGauge64,
			fragAfterEncapFragPackets CounterBasedGauge64,
			fragReceived CounterBasedGauge64,
			sequenceNum CounterBasedGauge64,
			sequenceNumRollover CounterBasedGauge64,
			packetsErrNhCheck CounterBasedGauge64
		}

			samplingEnable OBJECT-TYPE
			SYNTAX  DisplayString
			MAX-ACCESS read-only
			STATUS current
			DESCRIPTION  "Enable baselining"
			::={ vpnIpsecSaStatsSEntry 1 }

			packetsEncrypted OBJECT-TYPE
			SYNTAX  CounterBasedGauge64
			MAX-ACCESS read-only
			STATUS current
			DESCRIPTION  "Encrypted Packets"
			::={ vpnIpsecSaStatsSEntry 2 }

			packetsDecrypted OBJECT-TYPE
			SYNTAX  CounterBasedGauge64
			MAX-ACCESS read-only
			STATUS current
			DESCRIPTION  "Decrypted Packets"
			::={ vpnIpsecSaStatsSEntry 3 }

			antiReplayNum OBJECT-TYPE
			SYNTAX  CounterBasedGauge64
			MAX-ACCESS read-only
			STATUS current
			DESCRIPTION  "Anti-Replay Failure"
			::={ vpnIpsecSaStatsSEntry 4 }

			rekeyNum OBJECT-TYPE
			SYNTAX  CounterBasedGauge64
			MAX-ACCESS read-only
			STATUS current
			DESCRIPTION  "Rekey Times"
			::={ vpnIpsecSaStatsSEntry 5 }

			packetsErrInactive OBJECT-TYPE
			SYNTAX  CounterBasedGauge64
			MAX-ACCESS read-only
			STATUS current
			DESCRIPTION  "Inactive Error"
			::={ vpnIpsecSaStatsSEntry 6 }

			packetsErrEncryption OBJECT-TYPE
			SYNTAX  CounterBasedGauge64
			MAX-ACCESS read-only
			STATUS current
			DESCRIPTION  "Encryption Error"
			::={ vpnIpsecSaStatsSEntry 7 }

			packetsErrPadCheck OBJECT-TYPE
			SYNTAX  CounterBasedGauge64
			MAX-ACCESS read-only
			STATUS current
			DESCRIPTION  "Pad Check Error"
			::={ vpnIpsecSaStatsSEntry 8 }

			packetsErrPktSanity OBJECT-TYPE
			SYNTAX  CounterBasedGauge64
			MAX-ACCESS read-only
			STATUS current
			DESCRIPTION  "Packets Sanity Error"
			::={ vpnIpsecSaStatsSEntry 9 }

			packetsErrIcvCheck OBJECT-TYPE
			SYNTAX  CounterBasedGauge64
			MAX-ACCESS read-only
			STATUS current
			DESCRIPTION  "ICV Check Error"
			::={ vpnIpsecSaStatsSEntry 10 }

			packetsErrLifetimeLifebytes OBJECT-TYPE
			SYNTAX  CounterBasedGauge64
			MAX-ACCESS read-only
			STATUS current
			DESCRIPTION  "Lifetime Lifebytes Error"
			::={ vpnIpsecSaStatsSEntry 11 }

			bytesEncrypted OBJECT-TYPE
			SYNTAX  CounterBasedGauge64
			MAX-ACCESS read-only
			STATUS current
			DESCRIPTION  "Encrypted Bytes"
			::={ vpnIpsecSaStatsSEntry 12 }

			bytesDecrypted OBJECT-TYPE
			SYNTAX  CounterBasedGauge64
			MAX-ACCESS read-only
			STATUS current
			DESCRIPTION  "Decrypted Bytes"
			::={ vpnIpsecSaStatsSEntry 13 }

			prefragSuccess OBJECT-TYPE
			SYNTAX  CounterBasedGauge64
			MAX-ACCESS read-only
			STATUS current
			DESCRIPTION  "Pre-frag Success"
			::={ vpnIpsecSaStatsSEntry 14 }

			prefragError OBJECT-TYPE
			SYNTAX  CounterBasedGauge64
			MAX-ACCESS read-only
			STATUS current
			DESCRIPTION  "Pre-frag Error"
			::={ vpnIpsecSaStatsSEntry 15 }

			caviumBytesEncrypted OBJECT-TYPE
			SYNTAX  CounterBasedGauge64
			MAX-ACCESS read-only
			STATUS current
			DESCRIPTION  "CAVIUM Encrypted Bytes"
			::={ vpnIpsecSaStatsSEntry 16 }

			caviumBytesDecrypted OBJECT-TYPE
			SYNTAX  CounterBasedGauge64
			MAX-ACCESS read-only
			STATUS current
			DESCRIPTION  "CAVIUM Decrypted Bytes"
			::={ vpnIpsecSaStatsSEntry 17 }

			caviumPacketsEncrypted OBJECT-TYPE
			SYNTAX  CounterBasedGauge64
			MAX-ACCESS read-only
			STATUS current
			DESCRIPTION  "CAVIUM Encrypted Packets"
			::={ vpnIpsecSaStatsSEntry 18 }

			caviumPacketsDecrypted OBJECT-TYPE
			SYNTAX  CounterBasedGauge64
			MAX-ACCESS read-only
			STATUS current
			DESCRIPTION  "CAVIUM Decrypted Packets"
			::={ vpnIpsecSaStatsSEntry 19 }

			qatBytesEncrypted OBJECT-TYPE
			SYNTAX  CounterBasedGauge64
			MAX-ACCESS read-only
			STATUS current
			DESCRIPTION  "QAT Encrypted Bytes"
			::={ vpnIpsecSaStatsSEntry 20 }

			qatBytesDecrypted OBJECT-TYPE
			SYNTAX  CounterBasedGauge64
			MAX-ACCESS read-only
			STATUS current
			DESCRIPTION  "QAT Decrypted Bytes"
			::={ vpnIpsecSaStatsSEntry 21 }

			qatPacketsEncrypted OBJECT-TYPE
			SYNTAX  CounterBasedGauge64
			MAX-ACCESS read-only
			STATUS current
			DESCRIPTION  "QAT Encrypted Packets"
			::={ vpnIpsecSaStatsSEntry 22 }

			qatPacketsDecrypted OBJECT-TYPE
			SYNTAX  CounterBasedGauge64
			MAX-ACCESS read-only
			STATUS current
			DESCRIPTION  "QAT Decrypted Packets"
			::={ vpnIpsecSaStatsSEntry 23 }

			tunnelIntfDown OBJECT-TYPE
			SYNTAX  CounterBasedGauge64
			MAX-ACCESS read-only
			STATUS current
			DESCRIPTION  "Packet dropped: Tunnel Interface Down"
			::={ vpnIpsecSaStatsSEntry 24 }

			pktFailPrepToSend OBJECT-TYPE
			SYNTAX  CounterBasedGauge64
			MAX-ACCESS read-only
			STATUS current
			DESCRIPTION  "Packet dropped: Failed in prepare to send"
			::={ vpnIpsecSaStatsSEntry 25 }

			noNextHop OBJECT-TYPE
			SYNTAX  CounterBasedGauge64
			MAX-ACCESS read-only
			STATUS current
			DESCRIPTION  "Packet dropped: No next hop"
			::={ vpnIpsecSaStatsSEntry 26 }

			invalidTunnelId OBJECT-TYPE
			SYNTAX  CounterBasedGauge64
			MAX-ACCESS read-only
			STATUS current
			DESCRIPTION  "Packet dropped: Invalid tunnel ID"
			::={ vpnIpsecSaStatsSEntry 27 }

			noTunnelFound OBJECT-TYPE
			SYNTAX  CounterBasedGauge64
			MAX-ACCESS read-only
			STATUS current
			DESCRIPTION  "Packet dropped: No tunnel found"
			::={ vpnIpsecSaStatsSEntry 28 }

			pktFailToSend OBJECT-TYPE
			SYNTAX  CounterBasedGauge64
			MAX-ACCESS read-only
			STATUS current
			DESCRIPTION  "Packet dropped: Failed to send"
			::={ vpnIpsecSaStatsSEntry 29 }

			fragAfterEncapFragPackets OBJECT-TYPE
			SYNTAX  CounterBasedGauge64
			MAX-ACCESS read-only
			STATUS current
			DESCRIPTION  "Frag-after-encap Fragment Generated"
			::={ vpnIpsecSaStatsSEntry 30 }

			fragReceived OBJECT-TYPE
			SYNTAX  CounterBasedGauge64
			MAX-ACCESS read-only
			STATUS current
			DESCRIPTION  "Fragment Received"
			::={ vpnIpsecSaStatsSEntry 31 }

			sequenceNum OBJECT-TYPE
			SYNTAX  CounterBasedGauge64
			MAX-ACCESS read-only
			STATUS current
			DESCRIPTION  "Sequence Number"
			::={ vpnIpsecSaStatsSEntry 32 }

			sequenceNumRollover OBJECT-TYPE
			SYNTAX  CounterBasedGauge64
			MAX-ACCESS read-only
			STATUS current
			DESCRIPTION  "Sequence Number Rollover"
			::={ vpnIpsecSaStatsSEntry 33 }

			packetsErrNhCheck OBJECT-TYPE
			SYNTAX  CounterBasedGauge64
			MAX-ACCESS read-only
			STATUS current
			DESCRIPTION  "Next Header Check Error"
			::={ vpnIpsecSaStatsSEntry 34 }

END
