ACOS-OVERLAY-TUNNEL-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosOverlayTunnel MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "OverlayTunnel OID for ACOS"
				::=  {  acosRootStats 128  }

acosOverlayTunnelVtep               OBJECT IDENTIFIER ::= { acosOverlayTunnel 2 }
acosOverlayTunnelVtepS              OBJECT IDENTIFIER ::= { acosOverlayTunnelVtep 1 }

overlayTunnelVtepSTable OBJECT-TYPE
		SYNTAX SEQUENCE OF OverlayTunnelVtepSEntry
		MAX-ACCESS not-accessible
		STATUS current
		::={ acosOverlayTunnelVtepS 1 }


	overlayTunnelVtepSEntry OBJECT-TYPE
		SYNTAX OverlayTunnelVtepSEntry
		MAX-ACCESS not-accessible
		STATUS current
		INDEX {
			id
		}
		::={ overlayTunnelVtepSTable 1 }


	OverlayTunnelVtepSEntry ::=
		SEQUENCE {
			id INTEGER,
			cfgErrCount CounterBasedGauge64,
			floodedPktCount CounterBasedGauge64,
			encapUnresolvedCount CounterBasedGauge64,
			unknownEncapRxPkt CounterBasedGauge64,
			unknownEncapTxPkt CounterBasedGauge64,
			arpReqSent CounterBasedGauge64,
			vtepHostLearned CounterBasedGauge64,
			vtepHostLearnError CounterBasedGauge64,
			invalidLifRx CounterBasedGauge64,
			invalidLifTx CounterBasedGauge64,
			unknownVtepTx CounterBasedGauge64,
			unknownVtepRx CounterBasedGauge64,
			unhandledPktRx CounterBasedGauge64,
			unhandledPktTx CounterBasedGauge64,
			totalPktsRx CounterBasedGauge64,
			totalBytesRx CounterBasedGauge64,
			unicastPktRx CounterBasedGauge64,
			bcastPktRx CounterBasedGauge64,
			mcastPktRx CounterBasedGauge64,
			droppedPktRx CounterBasedGauge64,
			encapMissPktsRx CounterBasedGauge64,
			badChksumPksRx CounterBasedGauge64,
			requeuePktsIn CounterBasedGauge64,
			pktsOut CounterBasedGauge64,
			totalBytesTx CounterBasedGauge64,
			unicastPktTx CounterBasedGauge64,
			bcastPktTx CounterBasedGauge64,
			mcastPktTx CounterBasedGauge64,
			droppedPktsTx CounterBasedGauge64,
			largePktsRx CounterBasedGauge64,
			dot1qPktsRx CounterBasedGauge64,
			fragPktsTx CounterBasedGauge64,
			reassembledPktsRx CounterBasedGauge64,
			badInnerIpv4LenRx CounterBasedGauge64,
			badInnerIpv6LenRx CounterBasedGauge64,
			fragDropPktsTx CounterBasedGauge64,
			lifUnInitRx CounterBasedGauge64
		}

			id OBJECT-TYPE
			SYNTAX  INTEGER
			MAX-ACCESS read-only
			STATUS current
			DESCRIPTION  "VTEP Identifier"
			::={ overlayTunnelVtepSEntry 1 }

			cfgErrCount OBJECT-TYPE
			SYNTAX  CounterBasedGauge64
			MAX-ACCESS read-only
			STATUS current
			DESCRIPTION  "Config errors"
			::={ overlayTunnelVtepSEntry 2 }

			floodedPktCount OBJECT-TYPE
			SYNTAX  CounterBasedGauge64
			MAX-ACCESS read-only
			STATUS current
			DESCRIPTION  "Flooded packet count"
			::={ overlayTunnelVtepSEntry 3 }

			encapUnresolvedCount OBJECT-TYPE
			SYNTAX  CounterBasedGauge64
			MAX-ACCESS read-only
			STATUS current
			DESCRIPTION  "Encap unresolved failures"
			::={ overlayTunnelVtepSEntry 4 }

			unknownEncapRxPkt OBJECT-TYPE
			SYNTAX  CounterBasedGauge64
			MAX-ACCESS read-only
			STATUS current
			DESCRIPTION  "Encap miss rx pkts"
			::={ overlayTunnelVtepSEntry 5 }

			unknownEncapTxPkt OBJECT-TYPE
			SYNTAX  CounterBasedGauge64
			MAX-ACCESS read-only
			STATUS current
			DESCRIPTION  "Encap miss tx pkts"
			::={ overlayTunnelVtepSEntry 6 }

			arpReqSent OBJECT-TYPE
			SYNTAX  CounterBasedGauge64
			MAX-ACCESS read-only
			STATUS current
			DESCRIPTION  "Arp request sent"
			::={ overlayTunnelVtepSEntry 7 }

			vtepHostLearned OBJECT-TYPE
			SYNTAX  CounterBasedGauge64
			MAX-ACCESS read-only
			STATUS current
			DESCRIPTION  "Hosts learned"
			::={ overlayTunnelVtepSEntry 8 }

			vtepHostLearnError OBJECT-TYPE
			SYNTAX  CounterBasedGauge64
			MAX-ACCESS read-only
			STATUS current
			DESCRIPTION  "Host learn error"
			::={ overlayTunnelVtepSEntry 9 }

			invalidLifRx OBJECT-TYPE
			SYNTAX  CounterBasedGauge64
			MAX-ACCESS read-only
			STATUS current
			DESCRIPTION  "Invalid Lif pkts in"
			::={ overlayTunnelVtepSEntry 10 }

			invalidLifTx OBJECT-TYPE
			SYNTAX  CounterBasedGauge64
			MAX-ACCESS read-only
			STATUS current
			DESCRIPTION  "Invalid Lif pkts out"
			::={ overlayTunnelVtepSEntry 11 }

			unknownVtepTx OBJECT-TYPE
			SYNTAX  CounterBasedGauge64
			MAX-ACCESS read-only
			STATUS current
			DESCRIPTION  "Vtep unknown tx"
			::={ overlayTunnelVtepSEntry 12 }

			unknownVtepRx OBJECT-TYPE
			SYNTAX  CounterBasedGauge64
			MAX-ACCESS read-only
			STATUS current
			DESCRIPTION  "Vtep Unkown rx"
			::={ overlayTunnelVtepSEntry 13 }

			unhandledPktRx OBJECT-TYPE
			SYNTAX  CounterBasedGauge64
			MAX-ACCESS read-only
			STATUS current
			DESCRIPTION  "Unhandled packets in"
			::={ overlayTunnelVtepSEntry 14 }

			unhandledPktTx OBJECT-TYPE
			SYNTAX  CounterBasedGauge64
			MAX-ACCESS read-only
			STATUS current
			DESCRIPTION  "Unhandled packets out"
			::={ overlayTunnelVtepSEntry 15 }

			totalPktsRx OBJECT-TYPE
			SYNTAX  CounterBasedGauge64
			MAX-ACCESS read-only
			STATUS current
			DESCRIPTION  "Total packets out"
			::={ overlayTunnelVtepSEntry 16 }

			totalBytesRx OBJECT-TYPE
			SYNTAX  CounterBasedGauge64
			MAX-ACCESS read-only
			STATUS current
			DESCRIPTION  "Total packet bytes in"
			::={ overlayTunnelVtepSEntry 17 }

			unicastPktRx OBJECT-TYPE
			SYNTAX  CounterBasedGauge64
			MAX-ACCESS read-only
			STATUS current
			DESCRIPTION  "Total unicast packets in"
			::={ overlayTunnelVtepSEntry 18 }

			bcastPktRx OBJECT-TYPE
			SYNTAX  CounterBasedGauge64
			MAX-ACCESS read-only
			STATUS current
			DESCRIPTION  "Total broadcast packets in"
			::={ overlayTunnelVtepSEntry 19 }

			mcastPktRx OBJECT-TYPE
			SYNTAX  CounterBasedGauge64
			MAX-ACCESS read-only
			STATUS current
			DESCRIPTION  "Total multicast packets in"
			::={ overlayTunnelVtepSEntry 20 }

			droppedPktRx OBJECT-TYPE
			SYNTAX  CounterBasedGauge64
			MAX-ACCESS read-only
			STATUS current
			DESCRIPTION  "Dropped received packets"
			::={ overlayTunnelVtepSEntry 21 }

			encapMissPktsRx OBJECT-TYPE
			SYNTAX  CounterBasedGauge64
			MAX-ACCESS read-only
			STATUS current
			DESCRIPTION  "Encap missed in received packets"
			::={ overlayTunnelVtepSEntry 22 }

			badChksumPksRx OBJECT-TYPE
			SYNTAX  CounterBasedGauge64
			MAX-ACCESS read-only
			STATUS current
			DESCRIPTION  "Bad checksum in received packets"
			::={ overlayTunnelVtepSEntry 23 }

			requeuePktsIn OBJECT-TYPE
			SYNTAX  CounterBasedGauge64
			MAX-ACCESS read-only
			STATUS current
			DESCRIPTION  "Requeued packets in"
			::={ overlayTunnelVtepSEntry 24 }

			pktsOut OBJECT-TYPE
			SYNTAX  CounterBasedGauge64
			MAX-ACCESS read-only
			STATUS current
			DESCRIPTION  "Packets out"
			::={ overlayTunnelVtepSEntry 25 }

			totalBytesTx OBJECT-TYPE
			SYNTAX  CounterBasedGauge64
			MAX-ACCESS read-only
			STATUS current
			DESCRIPTION  "Packet bytes out"
			::={ overlayTunnelVtepSEntry 26 }

			unicastPktTx OBJECT-TYPE
			SYNTAX  CounterBasedGauge64
			MAX-ACCESS read-only
			STATUS current
			DESCRIPTION  "Unicast packets out"
			::={ overlayTunnelVtepSEntry 27 }

			bcastPktTx OBJECT-TYPE
			SYNTAX  CounterBasedGauge64
			MAX-ACCESS read-only
			STATUS current
			DESCRIPTION  "Broadcast packets out"
			::={ overlayTunnelVtepSEntry 28 }

			mcastPktTx OBJECT-TYPE
			SYNTAX  CounterBasedGauge64
			MAX-ACCESS read-only
			STATUS current
			DESCRIPTION  "Multicast packets out"
			::={ overlayTunnelVtepSEntry 29 }

			droppedPktsTx OBJECT-TYPE
			SYNTAX  CounterBasedGauge64
			MAX-ACCESS read-only
			STATUS current
			DESCRIPTION  "Dropped packets out"
			::={ overlayTunnelVtepSEntry 30 }

			largePktsRx OBJECT-TYPE
			SYNTAX  CounterBasedGauge64
			MAX-ACCESS read-only
			STATUS current
			DESCRIPTION  "Too large packets in"
			::={ overlayTunnelVtepSEntry 31 }

			dot1qPktsRx OBJECT-TYPE
			SYNTAX  CounterBasedGauge64
			MAX-ACCESS read-only
			STATUS current
			DESCRIPTION  "Dot1q packets in"
			::={ overlayTunnelVtepSEntry 32 }

			fragPktsTx OBJECT-TYPE
			SYNTAX  CounterBasedGauge64
			MAX-ACCESS read-only
			STATUS current
			DESCRIPTION  "Frag packets out"
			::={ overlayTunnelVtepSEntry 33 }

			reassembledPktsRx OBJECT-TYPE
			SYNTAX  CounterBasedGauge64
			MAX-ACCESS read-only
			STATUS current
			DESCRIPTION  "Reassembled packets in"
			::={ overlayTunnelVtepSEntry 34 }

			badInnerIpv4LenRx OBJECT-TYPE
			SYNTAX  CounterBasedGauge64
			MAX-ACCESS read-only
			STATUS current
			DESCRIPTION  "bad inner ipv4 packet len"
			::={ overlayTunnelVtepSEntry 35 }

			badInnerIpv6LenRx OBJECT-TYPE
			SYNTAX  CounterBasedGauge64
			MAX-ACCESS read-only
			STATUS current
			DESCRIPTION  "Bad inner ipv6 packet len"
			::={ overlayTunnelVtepSEntry 36 }

			fragDropPktsTx OBJECT-TYPE
			SYNTAX  CounterBasedGauge64
			MAX-ACCESS read-only
			STATUS current
			DESCRIPTION  "Frag dropped packets out"
			::={ overlayTunnelVtepSEntry 37 }

			lifUnInitRx OBJECT-TYPE
			SYNTAX  CounterBasedGauge64
			MAX-ACCESS read-only
			STATUS current
			DESCRIPTION  "Lif uninitialized packets in"
			::={ overlayTunnelVtepSEntry 38 }

END
