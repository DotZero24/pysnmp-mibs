ACOS-NETFLOW-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosNetflow MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Netflow OID for ACOS"
				::=  {  acosRootStats 126  }

acosNetflowMonitor                  OBJECT IDENTIFIER ::= { acosNetflow 2 }
acosNetflowMonitorS                 OBJECT IDENTIFIER ::= { acosNetflowMonitor 1 }

netflowMonitorSTable OBJECT-TYPE
		SYNTAX SEQUENCE OF NetflowMonitorSEntry
		MAX-ACCESS not-accessible
		STATUS current
		::={ acosNetflowMonitorS 1 }


	netflowMonitorSEntry OBJECT-TYPE
		SYNTAX NetflowMonitorSEntry
		MAX-ACCESS not-accessible
		STATUS current
		INDEX {
			netflowMonitorName
		}
		::={ netflowMonitorSTable 1 }


	NetflowMonitorSEntry ::=
		SEQUENCE {
			netflowMonitorName DisplayString,
			packetsSent CounterBasedGauge64,
			bytesSent CounterBasedGauge64,
			nat44RecordsSent CounterBasedGauge64,
			nat44RecordsSentFailure CounterBasedGauge64,
			nat64RecordsSent CounterBasedGauge64,
			nat64RecordsSentFailure CounterBasedGauge64,
			dsliteRecordsSent CounterBasedGauge64,
			dsliteRecordsSentFailure CounterBasedGauge64,
			sessionEventNat44RecordsSent CounterBasedGauge64,
			sessionEventNat44RecordsSentFailure CounterBasedGauge64,
			sessionEventNat64RecordsSent CounterBasedGauge64,
			sessionEventNat64RecordsSentFailure CounterBasedGauge64,
			sessionEventDsliteRecordsSent CounterBasedGauge64,
			sessionEventDsliteRecordsSentFailure CounterBasedGauge64,
			sessionEventFw4RecordsSent CounterBasedGauge64,
			sessionEventFw4RecordsSentFailure CounterBasedGauge64,
			sessionEventFw6RecordsSent CounterBasedGauge64,
			sessionEventFw6RecordsSentFailure CounterBasedGauge64,
			portMappingNat44RecordsSent CounterBasedGauge64,
			portMappingNat44RecordsSentFailure CounterBasedGauge64,
			portMappingNat64RecordsSent CounterBasedGauge64,
			portMappingNat64RecordsSentFailure CounterBasedGauge64,
			portMappingDsliteRecordsSent CounterBasedGauge64,
			portMappingDsliteRecordsSentFailure CounterBasedGauge64,
			netflowV5RecordsSent CounterBasedGauge64,
			netflowV5RecordsSentFailure CounterBasedGauge64,
			netflowV5ExtRecordsSent CounterBasedGauge64,
			netflowV5ExtRecordsSentFailure CounterBasedGauge64,
			portBatchingNat44RecordsSent CounterBasedGauge64,
			portBatchingNat44RecordsSentFailure CounterBasedGauge64,
			portBatchingNat64RecordsSent CounterBasedGauge64,
			portBatchingNat64RecordsSentFailure CounterBasedGauge64,
			portBatchingDsliteRecordsSent CounterBasedGauge64,
			portBatchingDsliteRecordsSentFailure CounterBasedGauge64,
			portBatchingV2Nat44RecordsSent CounterBasedGauge64,
			portBatchingV2Nat44RecordsSentFailure CounterBasedGauge64,
			portBatchingV2Nat64RecordsSent CounterBasedGauge64,
			portBatchingV2Nat64RecordsSentFailure CounterBasedGauge64,
			portBatchingV2DsliteRecordsSent CounterBasedGauge64,
			portBatchingV2DsliteRecordsSentFailure CounterBasedGauge64,
			customSessionEventNat44CreationRecordsSent CounterBasedGauge64,
			customSessionEventNat44CreationRecordsSentFailure CounterBasedGauge64,
			customSessionEventNat64CreationRecordsSent CounterBasedGauge64,
			customSessionEventNat64CreationRecordsSentFailure CounterBasedGauge64,
			customSessionEventDsliteCreationRecordsSent CounterBasedGauge64,
			customSessionEventDsliteCreationRecordsSentFailure CounterBasedGauge64,
			customSessionEventNat44DeletionRecordsSent CounterBasedGauge64,
			customSessionEventNat44DeletionRecordsSentFailure CounterBasedGauge64,
			customSessionEventNat64DeletionRecordsSent CounterBasedGauge64,
			customSessionEventNat64DeletionRecordsSentFailure CounterBasedGauge64,
			customSessionEventDsliteDeletionRecordsSent CounterBasedGauge64,
			customSessionEventDsliteDeletionRecordsSentFailure CounterBasedGauge64,
			customSessionEventFw4CreationRecordsSent CounterBasedGauge64,
			customSessionEventFw4CreationRecordsSentFailure CounterBasedGauge64,
			customSessionEventFw6CreationRecordsSent CounterBasedGauge64,
			customSessionEventFw6CreationRecordsSentFailure CounterBasedGauge64,
			customSessionEventFw4DeletionRecordsSent CounterBasedGauge64,
			customSessionEventFw4DeletionRecordsSentFailure CounterBasedGauge64,
			customSessionEventFw6DeletionRecordsSent CounterBasedGauge64,
			customSessionEventFw6DeletionRecordsSentFailure CounterBasedGauge64,
			customDenyResetEventFw4RecordsSent CounterBasedGauge64,
			customDenyResetEventFw4RecordsSentFailure CounterBasedGauge64,
			customDenyResetEventFw6RecordsSent CounterBasedGauge64,
			customDenyResetEventFw6RecordsSentFailure CounterBasedGauge64,
			customPortMappingNat44CreationRecordsSent CounterBasedGauge64,
			customPortMappingNat44CreationRecordsSentFailure CounterBasedGauge64,
			customPortMappingNat64CreationRecordsSent CounterBasedGauge64,
			customPortMappingNat64CreationRecordsSentFailure CounterBasedGauge64,
			customPortMappingDsliteCreationRecordsSent CounterBasedGauge64,
			customPortMappingDsliteCreationRecordsSentFailure CounterBasedGauge64,
			customPortMappingNat44DeletionRecordsSent CounterBasedGauge64,
			customPortMappingNat44DeletionRecordsSentFailure CounterBasedGauge64,
			customPortMappingNat64DeletionRecordsSent CounterBasedGauge64,
			customPortMappingNat64DeletionRecordsSentFailure CounterBasedGauge64,
			customPortMappingDsliteDeletionRecordsSent CounterBasedGauge64,
			customPortMappingDsliteDeletionRecordsSentFailure CounterBasedGauge64,
			customPortBatchingNat44CreationRecordsSent CounterBasedGauge64,
			customPortBatchingNat44CreationRecordsSentFailure CounterBasedGauge64,
			customPortBatchingNat64CreationRecordsSent CounterBasedGauge64,
			customPortBatchingNat64CreationRecordsSentFailure CounterBasedGauge64,
			customPortBatchingDsliteCreationRecordsSent CounterBasedGauge64,
			customPortBatchingDsliteCreationRecordsSentFailure CounterBasedGauge64,
			customPortBatchingNat44DeletionRecordsSent CounterBasedGauge64,
			customPortBatchingNat44DeletionRecordsSentFailure CounterBasedGauge64,
			customPortBatchingNat64DeletionRecordsSent CounterBasedGauge64,
			customPortBatchingNat64DeletionRecordsSentFailure CounterBasedGauge64,
			customPortBatchingDsliteDeletionRecordsSent CounterBasedGauge64,
			customPortBatchingDsliteDeletionRecordsSentFailure CounterBasedGauge64,
			customPortBatchingV2Nat44CreationRecordsSent CounterBasedGauge64,
			customPortBatchingV2Nat44CreationRecordsSentFailure CounterBasedGauge64,
			customPortBatchingV2Nat64CreationRecordsSent CounterBasedGauge64,
			customPortBatchingV2Nat64CreationRecordsSentFailure CounterBasedGauge64,
			customPortBatchingV2DsliteCreationRecordsSent CounterBasedGauge64,
			customPortBatchingV2DsliteCreationRecordsSentFailure CounterBasedGauge64,
			customPortBatchingV2Nat44DeletionRecordsSent CounterBasedGauge64,
			customPortBatchingV2Nat44DeletionRecordsSentFailure CounterBasedGauge64,
			customPortBatchingV2Nat64DeletionRecordsSent CounterBasedGauge64,
			customPortBatchingV2Nat64DeletionRecordsSentFailure CounterBasedGauge64,
			customPortBatchingV2DsliteDeletionRecordsSent CounterBasedGauge64,
			customPortBatchingV2DsliteDeletionRecordsSentFailure CounterBasedGauge64,
			reducedLogsByDestination CounterBasedGauge64,
			customGtpCTunnelEventRecordsSent CounterBasedGauge64,
			customGtpCTunnelEventRecordsSentFailure CounterBasedGauge64,
			customGtpUTunnelEventRecordsSent CounterBasedGauge64,
			customGtpUTunnelEventRecordsSentFailure CounterBasedGauge64,
			customGtpDenyEventRecordsSent CounterBasedGauge64,
			customGtpDenyEventRecordsSentFailure CounterBasedGauge64,
			customGtpInfoEventRecordsSent CounterBasedGauge64,
			customGtpInfoEventRecordsSentFailure CounterBasedGauge64,
			customFwIddosEntryCreatedRecordsSent CounterBasedGauge64,
			customFwIddosEntryCreatedRecordsSentFailure CounterBasedGauge64,
			customFwIddosEntryDeletedRecordsSent CounterBasedGauge64,
			customFwIddosEntryDeletedRecordsSentFailure CounterBasedGauge64,
			customFwSesnLimitExceededRecordsSent CounterBasedGauge64,
			customFwSesnLimitExceededRecordsSentFailure CounterBasedGauge64,
			customNatIddosL3EntryCreatedRecordsSent CounterBasedGauge64,
			customNatIddosL3EntryCreatedRecordsSentFailure CounterBasedGauge64,
			customNatIddosL3EntryDeletedRecordsSent CounterBasedGauge64,
			customNatIddosL3EntryDeletedRecordsSentFailure CounterBasedGauge64,
			customNatIddosL4EntryCreatedRecordsSent CounterBasedGauge64,
			customNatIddosL4EntryCreatedRecordsSentFailure CounterBasedGauge64,
			customNatIddosL4EntryDeletedRecordsSent CounterBasedGauge64,
			customNatIddosL4EntryDeletedRecordsSentFailure CounterBasedGauge64,
			customGtpRateLimitPeriodicRecordsSent CounterBasedGauge64,
			customGtpRateLimitPeriodicRecordsSentFailure CounterBasedGauge64
		}

			netflowMonitorName OBJECT-TYPE
			SYNTAX  DisplayString
			MAX-ACCESS read-only
			STATUS current
			DESCRIPTION  "Name of netflow monitor"
			::={ netflowMonitorSEntry 1 }

			packetsSent OBJECT-TYPE
			SYNTAX  CounterBasedGauge64
			MAX-ACCESS read-only
			STATUS current
			DESCRIPTION  "Sent Packets Count"
			::={ netflowMonitorSEntry 2 }

			bytesSent OBJECT-TYPE
			SYNTAX  CounterBasedGauge64
			MAX-ACCESS read-only
			STATUS current
			DESCRIPTION  "Sent Bytes Count"
			::={ netflowMonitorSEntry 3 }

			nat44RecordsSent OBJECT-TYPE
			SYNTAX  CounterBasedGauge64
			MAX-ACCESS read-only
			STATUS current
			DESCRIPTION  "NAT44 Flow Records Sent"
			::={ netflowMonitorSEntry 4 }

			nat44RecordsSentFailure OBJECT-TYPE
			SYNTAX  CounterBasedGauge64
			MAX-ACCESS read-only
			STATUS current
			DESCRIPTION  "NAT44 Flow Records Failed"
			::={ netflowMonitorSEntry 5 }

			nat64RecordsSent OBJECT-TYPE
			SYNTAX  CounterBasedGauge64
			MAX-ACCESS read-only
			STATUS current
			DESCRIPTION  "NAT64 Flow Records Sent"
			::={ netflowMonitorSEntry 6 }

			nat64RecordsSentFailure OBJECT-TYPE
			SYNTAX  CounterBasedGauge64
			MAX-ACCESS read-only
			STATUS current
			DESCRIPTION  "NAT64 Flow Records Failed"
			::={ netflowMonitorSEntry 7 }

			dsliteRecordsSent OBJECT-TYPE
			SYNTAX  CounterBasedGauge64
			MAX-ACCESS read-only
			STATUS current
			DESCRIPTION  "Dslite Flow Records Sent"
			::={ netflowMonitorSEntry 8 }

			dsliteRecordsSentFailure OBJECT-TYPE
			SYNTAX  CounterBasedGauge64
			MAX-ACCESS read-only
			STATUS current
			DESCRIPTION  "Dslite Flow Records Failed"
			::={ netflowMonitorSEntry 9 }

			sessionEventNat44RecordsSent OBJECT-TYPE
			SYNTAX  CounterBasedGauge64
			MAX-ACCESS read-only
			STATUS current
			DESCRIPTION  "Nat44 Session Event Records Sent"
			::={ netflowMonitorSEntry 10 }

			sessionEventNat44RecordsSentFailure OBJECT-TYPE
			SYNTAX  CounterBasedGauge64
			MAX-ACCESS read-only
			STATUS current
			DESCRIPTION  "Nat44 Session Event Records Failed"
			::={ netflowMonitorSEntry 11 }

			sessionEventNat64RecordsSent OBJECT-TYPE
			SYNTAX  CounterBasedGauge64
			MAX-ACCESS read-only
			STATUS current
			DESCRIPTION  "Nat64 Session Event Records Sent"
			::={ netflowMonitorSEntry 12 }

			sessionEventNat64RecordsSentFailure OBJECT-TYPE
			SYNTAX  CounterBasedGauge64
			MAX-ACCESS read-only
			STATUS current
			DESCRIPTION  "Nat64 Session Event Records Falied"
			::={ netflowMonitorSEntry 13 }

			sessionEventDsliteRecordsSent OBJECT-TYPE
			SYNTAX  CounterBasedGauge64
			MAX-ACCESS read-only
			STATUS current
			DESCRIPTION  "Dslite Session Event Records Sent"
			::={ netflowMonitorSEntry 14 }

			sessionEventDsliteRecordsSentFailure OBJECT-TYPE
			SYNTAX  CounterBasedGauge64
			MAX-ACCESS read-only
			STATUS current
			DESCRIPTION  "Dslite Session Event Records Failed"
			::={ netflowMonitorSEntry 15 }

			sessionEventFw4RecordsSent OBJECT-TYPE
			SYNTAX  CounterBasedGauge64
			MAX-ACCESS read-only
			STATUS current
			DESCRIPTION  "FW4 Session Event Records Sent"
			::={ netflowMonitorSEntry 16 }

			sessionEventFw4RecordsSentFailure OBJECT-TYPE
			SYNTAX  CounterBasedGauge64
			MAX-ACCESS read-only
			STATUS current
			DESCRIPTION  "FW4 Session Event Records Failed"
			::={ netflowMonitorSEntry 17 }

			sessionEventFw6RecordsSent OBJECT-TYPE
			SYNTAX  CounterBasedGauge64
			MAX-ACCESS read-only
			STATUS current
			DESCRIPTION  "FW6 Session Event Records Sent"
			::={ netflowMonitorSEntry 18 }

			sessionEventFw6RecordsSentFailure OBJECT-TYPE
			SYNTAX  CounterBasedGauge64
			MAX-ACCESS read-only
			STATUS current
			DESCRIPTION  "FW6 Session Event Records Failed"
			::={ netflowMonitorSEntry 19 }

			portMappingNat44RecordsSent OBJECT-TYPE
			SYNTAX  CounterBasedGauge64
			MAX-ACCESS read-only
			STATUS current
			DESCRIPTION  "Port Mapping Nat44 Event Records Sent"
			::={ netflowMonitorSEntry 20 }

			portMappingNat44RecordsSentFailure OBJECT-TYPE
			SYNTAX  CounterBasedGauge64
			MAX-ACCESS read-only
			STATUS current
			DESCRIPTION  "Port Mapping Nat44 Event Records Failed"
			::={ netflowMonitorSEntry 21 }

			portMappingNat64RecordsSent OBJECT-TYPE
			SYNTAX  CounterBasedGauge64
			MAX-ACCESS read-only
			STATUS current
			DESCRIPTION  "Port Mapping Nat64 Event Records Sent"
			::={ netflowMonitorSEntry 22 }

			portMappingNat64RecordsSentFailure OBJECT-TYPE
			SYNTAX  CounterBasedGauge64
			MAX-ACCESS read-only
			STATUS current
			DESCRIPTION  "Port Mapping Nat64 Event Records Failed"
			::={ netflowMonitorSEntry 23 }

			portMappingDsliteRecordsSent OBJECT-TYPE
			SYNTAX  CounterBasedGauge64
			MAX-ACCESS read-only
			STATUS current
			DESCRIPTION  "Port Mapping Dslite Event Records Sent"
			::={ netflowMonitorSEntry 24 }

			portMappingDsliteRecordsSentFailure OBJECT-TYPE
			SYNTAX  CounterBasedGauge64
			MAX-ACCESS read-only
			STATUS current
			DESCRIPTION  "Port Mapping Dslite Event Records failed"
			::={ netflowMonitorSEntry 25 }

			netflowV5RecordsSent OBJECT-TYPE
			SYNTAX  CounterBasedGauge64
			MAX-ACCESS read-only
			STATUS current
			DESCRIPTION  "Netflow v5 Records Sent"
			::={ netflowMonitorSEntry 26 }

			netflowV5RecordsSentFailure OBJECT-TYPE
			SYNTAX  CounterBasedGauge64
			MAX-ACCESS read-only
			STATUS current
			DESCRIPTION  "Netflow v5 Records Failed"
			::={ netflowMonitorSEntry 27 }

			netflowV5ExtRecordsSent OBJECT-TYPE
			SYNTAX  CounterBasedGauge64
			MAX-ACCESS read-only
			STATUS current
			DESCRIPTION  "Netflow v5 Ext Records Sent"
			::={ netflowMonitorSEntry 28 }

			netflowV5ExtRecordsSentFailure OBJECT-TYPE
			SYNTAX  CounterBasedGauge64
			MAX-ACCESS read-only
			STATUS current
			DESCRIPTION  "Netflow v5 Ext Records Failed"
			::={ netflowMonitorSEntry 29 }

			portBatchingNat44RecordsSent OBJECT-TYPE
			SYNTAX  CounterBasedGauge64
			MAX-ACCESS read-only
			STATUS current
			DESCRIPTION  "Port Batching Nat44 Records Sent"
			::={ netflowMonitorSEntry 30 }

			portBatchingNat44RecordsSentFailure OBJECT-TYPE
			SYNTAX  CounterBasedGauge64
			MAX-ACCESS read-only
			STATUS current
			DESCRIPTION  "Port Batching Nat44 Records Failed"
			::={ netflowMonitorSEntry 31 }

			portBatchingNat64RecordsSent OBJECT-TYPE
			SYNTAX  CounterBasedGauge64
			MAX-ACCESS read-only
			STATUS current
			DESCRIPTION  "Port Batching Nat64 Records Sent"
			::={ netflowMonitorSEntry 32 }

			portBatchingNat64RecordsSentFailure OBJECT-TYPE
			SYNTAX  CounterBasedGauge64
			MAX-ACCESS read-only
			STATUS current
			DESCRIPTION  "Port Batching Nat64 Records Failed"
			::={ netflowMonitorSEntry 33 }

			portBatchingDsliteRecordsSent OBJECT-TYPE
			SYNTAX  CounterBasedGauge64
			MAX-ACCESS read-only
			STATUS current
			DESCRIPTION  "Port Batching Dslite Records Sent"
			::={ netflowMonitorSEntry 34 }

			portBatchingDsliteRecordsSentFailure OBJECT-TYPE
			SYNTAX  CounterBasedGauge64
			MAX-ACCESS read-only
			STATUS current
			DESCRIPTION  "Port Batching Dslite Records Failed"
			::={ netflowMonitorSEntry 35 }

			portBatchingV2Nat44RecordsSent OBJECT-TYPE
			SYNTAX  CounterBasedGauge64
			MAX-ACCESS read-only
			STATUS current
			DESCRIPTION  "Port Batching V2 Nat44 Records Sent"
			::={ netflowMonitorSEntry 36 }

			portBatchingV2Nat44RecordsSentFailure OBJECT-TYPE
			SYNTAX  CounterBasedGauge64
			MAX-ACCESS read-only
			STATUS current
			DESCRIPTION  "Port Batching V2 Nat44 Records Failed"
			::={ netflowMonitorSEntry 37 }

			portBatchingV2Nat64RecordsSent OBJECT-TYPE
			SYNTAX  CounterBasedGauge64
			MAX-ACCESS read-only
			STATUS current
			DESCRIPTION  "Port Batching V2 Nat64 Records Sent"
			::={ netflowMonitorSEntry 38 }

			portBatchingV2Nat64RecordsSentFailure OBJECT-TYPE
			SYNTAX  CounterBasedGauge64
			MAX-ACCESS read-only
			STATUS current
			DESCRIPTION  "Port Batching V2 Nat64 Records Failed"
			::={ netflowMonitorSEntry 39 }

			portBatchingV2DsliteRecordsSent OBJECT-TYPE
			SYNTAX  CounterBasedGauge64
			MAX-ACCESS read-only
			STATUS current
			DESCRIPTION  "Port Batching V2 Dslite Records Sent"
			::={ netflowMonitorSEntry 40 }

			portBatchingV2DsliteRecordsSentFailure OBJECT-TYPE
			SYNTAX  CounterBasedGauge64
			MAX-ACCESS read-only
			STATUS current
			DESCRIPTION  "Port Batching V2 Dslite Records Falied"
			::={ netflowMonitorSEntry 41 }

			customSessionEventNat44CreationRecordsSent OBJECT-TYPE
			SYNTAX  CounterBasedGauge64
			MAX-ACCESS read-only
			STATUS current
			DESCRIPTION  "Custom Nat44 Session Creation Records Sent"
			::={ netflowMonitorSEntry 42 }

			customSessionEventNat44CreationRecordsSentFailure OBJECT-TYPE
			SYNTAX  CounterBasedGauge64
			MAX-ACCESS read-only
			STATUS current
			DESCRIPTION  "Custom Nat44 Session Creation Records Failed"
			::={ netflowMonitorSEntry 43 }

			customSessionEventNat64CreationRecordsSent OBJECT-TYPE
			SYNTAX  CounterBasedGauge64
			MAX-ACCESS read-only
			STATUS current
			DESCRIPTION  "Custom Nat64 Session Creation Records Sent"
			::={ netflowMonitorSEntry 44 }

			customSessionEventNat64CreationRecordsSentFailure OBJECT-TYPE
			SYNTAX  CounterBasedGauge64
			MAX-ACCESS read-only
			STATUS current
			DESCRIPTION  "Custom Nat64 Session Creation Records Failed"
			::={ netflowMonitorSEntry 45 }

			customSessionEventDsliteCreationRecordsSent OBJECT-TYPE
			SYNTAX  CounterBasedGauge64
			MAX-ACCESS read-only
			STATUS current
			DESCRIPTION  "Custom Dslite Session Creation Records Sent"
			::={ netflowMonitorSEntry 46 }

			customSessionEventDsliteCreationRecordsSentFailure OBJECT-TYPE
			SYNTAX  CounterBasedGauge64
			MAX-ACCESS read-only
			STATUS current
			DESCRIPTION  "Custom Dslite Session Creation Records Failed"
			::={ netflowMonitorSEntry 47 }

			customSessionEventNat44DeletionRecordsSent OBJECT-TYPE
			SYNTAX  CounterBasedGauge64
			MAX-ACCESS read-only
			STATUS current
			DESCRIPTION  "Custom Nat44 Session Deletion Records Sent"
			::={ netflowMonitorSEntry 48 }

			customSessionEventNat44DeletionRecordsSentFailure OBJECT-TYPE
			SYNTAX  CounterBasedGauge64
			MAX-ACCESS read-only
			STATUS current
			DESCRIPTION  "Custom Nat44 Session Deletion Records Failed"
			::={ netflowMonitorSEntry 49 }

			customSessionEventNat64DeletionRecordsSent OBJECT-TYPE
			SYNTAX  CounterBasedGauge64
			MAX-ACCESS read-only
			STATUS current
			DESCRIPTION  "Custom Nat64 Session Deletion Records Sent"
			::={ netflowMonitorSEntry 50 }

			customSessionEventNat64DeletionRecordsSentFailure OBJECT-TYPE
			SYNTAX  CounterBasedGauge64
			MAX-ACCESS read-only
			STATUS current
			DESCRIPTION  "Custom Nat64 Session Deletion Records Failed"
			::={ netflowMonitorSEntry 51 }

			customSessionEventDsliteDeletionRecordsSent OBJECT-TYPE
			SYNTAX  CounterBasedGauge64
			MAX-ACCESS read-only
			STATUS current
			DESCRIPTION  "Custom Dslite Session Deletion Records Sent"
			::={ netflowMonitorSEntry 52 }

			customSessionEventDsliteDeletionRecordsSentFailure OBJECT-TYPE
			SYNTAX  CounterBasedGauge64
			MAX-ACCESS read-only
			STATUS current
			DESCRIPTION  "Custom Dslite Session Deletion Records Failed"
			::={ netflowMonitorSEntry 53 }

			customSessionEventFw4CreationRecordsSent OBJECT-TYPE
			SYNTAX  CounterBasedGauge64
			MAX-ACCESS read-only
			STATUS current
			DESCRIPTION  "Custom FW4 Session Creation Records Sent"
			::={ netflowMonitorSEntry 54 }

			customSessionEventFw4CreationRecordsSentFailure OBJECT-TYPE
			SYNTAX  CounterBasedGauge64
			MAX-ACCESS read-only
			STATUS current
			DESCRIPTION  "Custom FW4 Session Creation Records Failed"
			::={ netflowMonitorSEntry 55 }

			customSessionEventFw6CreationRecordsSent OBJECT-TYPE
			SYNTAX  CounterBasedGauge64
			MAX-ACCESS read-only
			STATUS current
			DESCRIPTION  "Custom FW6 Session Creation Records Sent"
			::={ netflowMonitorSEntry 56 }

			customSessionEventFw6CreationRecordsSentFailure OBJECT-TYPE
			SYNTAX  CounterBasedGauge64
			MAX-ACCESS read-only
			STATUS current
			DESCRIPTION  "Custom FW6 Session Creation Records Failed"
			::={ netflowMonitorSEntry 57 }

			customSessionEventFw4DeletionRecordsSent OBJECT-TYPE
			SYNTAX  CounterBasedGauge64
			MAX-ACCESS read-only
			STATUS current
			DESCRIPTION  "Custom FW4 Session Deletion Records Sent"
			::={ netflowMonitorSEntry 58 }

			customSessionEventFw4DeletionRecordsSentFailure OBJECT-TYPE
			SYNTAX  CounterBasedGauge64
			MAX-ACCESS read-only
			STATUS current
			DESCRIPTION  "Custom FW4 Session Deletion Records Failed"
			::={ netflowMonitorSEntry 59 }

			customSessionEventFw6DeletionRecordsSent OBJECT-TYPE
			SYNTAX  CounterBasedGauge64
			MAX-ACCESS read-only
			STATUS current
			DESCRIPTION  "Custom FW6 Session Deletion Records Sent"
			::={ netflowMonitorSEntry 60 }

			customSessionEventFw6DeletionRecordsSentFailure OBJECT-TYPE
			SYNTAX  CounterBasedGauge64
			MAX-ACCESS read-only
			STATUS current
			DESCRIPTION  "Custom FW6 Session Deletion Records Failed"
			::={ netflowMonitorSEntry 61 }

			customDenyResetEventFw4RecordsSent OBJECT-TYPE
			SYNTAX  CounterBasedGauge64
			MAX-ACCESS read-only
			STATUS current
			DESCRIPTION  "Custom FW4 Deny/Reset Event Records Sent"
			::={ netflowMonitorSEntry 62 }

			customDenyResetEventFw4RecordsSentFailure OBJECT-TYPE
			SYNTAX  CounterBasedGauge64
			MAX-ACCESS read-only
			STATUS current
			DESCRIPTION  "Custom FW4 Deny/Reset Event Records Failed"
			::={ netflowMonitorSEntry 63 }

			customDenyResetEventFw6RecordsSent OBJECT-TYPE
			SYNTAX  CounterBasedGauge64
			MAX-ACCESS read-only
			STATUS current
			DESCRIPTION  "Custom FW6 Deny/Reset Event Records Sent"
			::={ netflowMonitorSEntry 64 }

			customDenyResetEventFw6RecordsSentFailure OBJECT-TYPE
			SYNTAX  CounterBasedGauge64
			MAX-ACCESS read-only
			STATUS current
			DESCRIPTION  "Custom FW6 Deny/Reset Event Records Failed"
			::={ netflowMonitorSEntry 65 }

			customPortMappingNat44CreationRecordsSent OBJECT-TYPE
			SYNTAX  CounterBasedGauge64
			MAX-ACCESS read-only
			STATUS current
			DESCRIPTION  "Custom Nat44 Port Map Creation Records Sent"
			::={ netflowMonitorSEntry 66 }

			customPortMappingNat44CreationRecordsSentFailure OBJECT-TYPE
			SYNTAX  CounterBasedGauge64
			MAX-ACCESS read-only
			STATUS current
			DESCRIPTION  "Custom Nat44 Port Map Creation Records Failed"
			::={ netflowMonitorSEntry 67 }

			customPortMappingNat64CreationRecordsSent OBJECT-TYPE
			SYNTAX  CounterBasedGauge64
			MAX-ACCESS read-only
			STATUS current
			DESCRIPTION  "Custom Nat64 Port Map Creation Records Sent"
			::={ netflowMonitorSEntry 68 }

			customPortMappingNat64CreationRecordsSentFailure OBJECT-TYPE
			SYNTAX  CounterBasedGauge64
			MAX-ACCESS read-only
			STATUS current
			DESCRIPTION  "Custom Nat64 Port Map Creation Records Failed"
			::={ netflowMonitorSEntry 69 }

			customPortMappingDsliteCreationRecordsSent OBJECT-TYPE
			SYNTAX  CounterBasedGauge64
			MAX-ACCESS read-only
			STATUS current
			DESCRIPTION  "Custom Dslite Port Map Creation Records Sent"
			::={ netflowMonitorSEntry 70 }

			customPortMappingDsliteCreationRecordsSentFailure OBJECT-TYPE
			SYNTAX  CounterBasedGauge64
			MAX-ACCESS read-only
			STATUS current
			DESCRIPTION  "Custom Dslite Port Map Creation Records Failed"
			::={ netflowMonitorSEntry 71 }

			customPortMappingNat44DeletionRecordsSent OBJECT-TYPE
			SYNTAX  CounterBasedGauge64
			MAX-ACCESS read-only
			STATUS current
			DESCRIPTION  "Custom Nat44 Port Map Deletion Records Sent"
			::={ netflowMonitorSEntry 72 }

			customPortMappingNat44DeletionRecordsSentFailure OBJECT-TYPE
			SYNTAX  CounterBasedGauge64
			MAX-ACCESS read-only
			STATUS current
			DESCRIPTION  "Custom Nat44 Port Map Deletion Records Failed"
			::={ netflowMonitorSEntry 73 }

			customPortMappingNat64DeletionRecordsSent OBJECT-TYPE
			SYNTAX  CounterBasedGauge64
			MAX-ACCESS read-only
			STATUS current
			DESCRIPTION  "Custom Nat64 Port Map Deletion Records Sent"
			::={ netflowMonitorSEntry 74 }

			customPortMappingNat64DeletionRecordsSentFailure OBJECT-TYPE
			SYNTAX  CounterBasedGauge64
			MAX-ACCESS read-only
			STATUS current
			DESCRIPTION  "Custom Nat64 Port Map Deletion Records Failed"
			::={ netflowMonitorSEntry 75 }

			customPortMappingDsliteDeletionRecordsSent OBJECT-TYPE
			SYNTAX  CounterBasedGauge64
			MAX-ACCESS read-only
			STATUS current
			DESCRIPTION  "Custom Dslite Port Map Deletion Records Sent"
			::={ netflowMonitorSEntry 76 }

			customPortMappingDsliteDeletionRecordsSentFailure OBJECT-TYPE
			SYNTAX  CounterBasedGauge64
			MAX-ACCESS read-only
			STATUS current
			DESCRIPTION  "Custom Dslite Port Map Deletion Records Failed"
			::={ netflowMonitorSEntry 77 }

			customPortBatchingNat44CreationRecordsSent OBJECT-TYPE
			SYNTAX  CounterBasedGauge64
			MAX-ACCESS read-only
			STATUS current
			DESCRIPTION  "Custom Nat44 Port Batch Creation Records Sent"
			::={ netflowMonitorSEntry 78 }

			customPortBatchingNat44CreationRecordsSentFailure OBJECT-TYPE
			SYNTAX  CounterBasedGauge64
			MAX-ACCESS read-only
			STATUS current
			DESCRIPTION  "Custom Nat44 Port Batch Creation Records Failed"
			::={ netflowMonitorSEntry 79 }

			customPortBatchingNat64CreationRecordsSent OBJECT-TYPE
			SYNTAX  CounterBasedGauge64
			MAX-ACCESS read-only
			STATUS current
			DESCRIPTION  "Custom Nat64 Port Batch Creation Records Sent"
			::={ netflowMonitorSEntry 80 }

			customPortBatchingNat64CreationRecordsSentFailure OBJECT-TYPE
			SYNTAX  CounterBasedGauge64
			MAX-ACCESS read-only
			STATUS current
			DESCRIPTION  "Custom Nat64 Port Batch Creation Records Failed"
			::={ netflowMonitorSEntry 81 }

			customPortBatchingDsliteCreationRecordsSent OBJECT-TYPE
			SYNTAX  CounterBasedGauge64
			MAX-ACCESS read-only
			STATUS current
			DESCRIPTION  "Custom Dslite Port Batch Creation Records Sent"
			::={ netflowMonitorSEntry 82 }

			customPortBatchingDsliteCreationRecordsSentFailure OBJECT-TYPE
			SYNTAX  CounterBasedGauge64
			MAX-ACCESS read-only
			STATUS current
			DESCRIPTION  "Custom Dslite Port Batch Creation Records Failed"
			::={ netflowMonitorSEntry 83 }

			customPortBatchingNat44DeletionRecordsSent OBJECT-TYPE
			SYNTAX  CounterBasedGauge64
			MAX-ACCESS read-only
			STATUS current
			DESCRIPTION  "Custom Nat44 Port Batch Deletion Records Sent"
			::={ netflowMonitorSEntry 84 }

			customPortBatchingNat44DeletionRecordsSentFailure OBJECT-TYPE
			SYNTAX  CounterBasedGauge64
			MAX-ACCESS read-only
			STATUS current
			DESCRIPTION  "Custom Nat44 Port Batch Deletion Records Failed"
			::={ netflowMonitorSEntry 85 }

			customPortBatchingNat64DeletionRecordsSent OBJECT-TYPE
			SYNTAX  CounterBasedGauge64
			MAX-ACCESS read-only
			STATUS current
			DESCRIPTION  "Custom Nat64 Port Batch Deletion Records Sent"
			::={ netflowMonitorSEntry 86 }

			customPortBatchingNat64DeletionRecordsSentFailure OBJECT-TYPE
			SYNTAX  CounterBasedGauge64
			MAX-ACCESS read-only
			STATUS current
			DESCRIPTION  "Custom Nat64 Port Batch Deletion Records Failed"
			::={ netflowMonitorSEntry 87 }

			customPortBatchingDsliteDeletionRecordsSent OBJECT-TYPE
			SYNTAX  CounterBasedGauge64
			MAX-ACCESS read-only
			STATUS current
			DESCRIPTION  "Custom Dslite Port Batch Deletion Records Sent"
			::={ netflowMonitorSEntry 88 }

			customPortBatchingDsliteDeletionRecordsSentFailure OBJECT-TYPE
			SYNTAX  CounterBasedGauge64
			MAX-ACCESS read-only
			STATUS current
			DESCRIPTION  "Custom Dslite Port Batch Deletion Records Failed"
			::={ netflowMonitorSEntry 89 }

			customPortBatchingV2Nat44CreationRecordsSent OBJECT-TYPE
			SYNTAX  CounterBasedGauge64
			MAX-ACCESS read-only
			STATUS current
			DESCRIPTION  "Custom Nat44 Port Batch V2 Creation Records Sent"
			::={ netflowMonitorSEntry 90 }

			customPortBatchingV2Nat44CreationRecordsSentFailure OBJECT-TYPE
			SYNTAX  CounterBasedGauge64
			MAX-ACCESS read-only
			STATUS current
			DESCRIPTION  "Custom Nat44 Port Batch V2 Creation Records Failed"
			::={ netflowMonitorSEntry 91 }

			customPortBatchingV2Nat64CreationRecordsSent OBJECT-TYPE
			SYNTAX  CounterBasedGauge64
			MAX-ACCESS read-only
			STATUS current
			DESCRIPTION  "Custom Nat64 Port Batch V2 Creation Records Sent"
			::={ netflowMonitorSEntry 92 }

			customPortBatchingV2Nat64CreationRecordsSentFailure OBJECT-TYPE
			SYNTAX  CounterBasedGauge64
			MAX-ACCESS read-only
			STATUS current
			DESCRIPTION  "Custom Nat64 Port Batch V2 Creation Records Failed"
			::={ netflowMonitorSEntry 93 }

			customPortBatchingV2DsliteCreationRecordsSent OBJECT-TYPE
			SYNTAX  CounterBasedGauge64
			MAX-ACCESS read-only
			STATUS current
			DESCRIPTION  "Custom Dslite Port Batch V2 Creation Records Sent"
			::={ netflowMonitorSEntry 94 }

			customPortBatchingV2DsliteCreationRecordsSentFailure OBJECT-TYPE
			SYNTAX  CounterBasedGauge64
			MAX-ACCESS read-only
			STATUS current
			DESCRIPTION  "Custom Dslite Port Batch V2 Creation Records Failed"
			::={ netflowMonitorSEntry 95 }

			customPortBatchingV2Nat44DeletionRecordsSent OBJECT-TYPE
			SYNTAX  CounterBasedGauge64
			MAX-ACCESS read-only
			STATUS current
			DESCRIPTION  "Custom Nat44 Port Batch V2 Deletion Records Sent"
			::={ netflowMonitorSEntry 96 }

			customPortBatchingV2Nat44DeletionRecordsSentFailure OBJECT-TYPE
			SYNTAX  CounterBasedGauge64
			MAX-ACCESS read-only
			STATUS current
			DESCRIPTION  "Custom Nat44 Port Batch V2 Deletion Records Failed"
			::={ netflowMonitorSEntry 97 }

			customPortBatchingV2Nat64DeletionRecordsSent OBJECT-TYPE
			SYNTAX  CounterBasedGauge64
			MAX-ACCESS read-only
			STATUS current
			DESCRIPTION  "Custom Nat64 Port Batch V2 Deletion Records Sent"
			::={ netflowMonitorSEntry 98 }

			customPortBatchingV2Nat64DeletionRecordsSentFailure OBJECT-TYPE
			SYNTAX  CounterBasedGauge64
			MAX-ACCESS read-only
			STATUS current
			DESCRIPTION  "Custom Nat64 Port Batch V2 Deletion Records Failed"
			::={ netflowMonitorSEntry 99 }

			customPortBatchingV2DsliteDeletionRecordsSent OBJECT-TYPE
			SYNTAX  CounterBasedGauge64
			MAX-ACCESS read-only
			STATUS current
			DESCRIPTION  "Custom Dslite Port Batch V2 Deletion Records Sent"
			::={ netflowMonitorSEntry 100 }

			customPortBatchingV2DsliteDeletionRecordsSentFailure OBJECT-TYPE
			SYNTAX  CounterBasedGauge64
			MAX-ACCESS read-only
			STATUS current
			DESCRIPTION  "Custom Dslite Port Batch V2 Deletion Records Failed"
			::={ netflowMonitorSEntry 101 }

			reducedLogsByDestination OBJECT-TYPE
			SYNTAX  CounterBasedGauge64
			MAX-ACCESS read-only
			STATUS current
			DESCRIPTION  "Reduced Logs by Destination Protocol and Port"
			::={ netflowMonitorSEntry 102 }

			customGtpCTunnelEventRecordsSent OBJECT-TYPE
			SYNTAX  CounterBasedGauge64
			MAX-ACCESS read-only
			STATUS current
			DESCRIPTION  "Custom GTP C Tunnel Records Sent"
			::={ netflowMonitorSEntry 103 }

			customGtpCTunnelEventRecordsSentFailure OBJECT-TYPE
			SYNTAX  CounterBasedGauge64
			MAX-ACCESS read-only
			STATUS current
			DESCRIPTION  "Custom GTP C Tunnel Records Sent Failure"
			::={ netflowMonitorSEntry 104 }

			customGtpUTunnelEventRecordsSent OBJECT-TYPE
			SYNTAX  CounterBasedGauge64
			MAX-ACCESS read-only
			STATUS current
			DESCRIPTION  "Custom GTP U Tunnel Records Sent"
			::={ netflowMonitorSEntry 105 }

			customGtpUTunnelEventRecordsSentFailure OBJECT-TYPE
			SYNTAX  CounterBasedGauge64
			MAX-ACCESS read-only
			STATUS current
			DESCRIPTION  "Custom GTP U Tunnel Records Sent Failure"
			::={ netflowMonitorSEntry 106 }

			customGtpDenyEventRecordsSent OBJECT-TYPE
			SYNTAX  CounterBasedGauge64
			MAX-ACCESS read-only
			STATUS current
			DESCRIPTION  "Custom GTP Deny Records Sent"
			::={ netflowMonitorSEntry 107 }

			customGtpDenyEventRecordsSentFailure OBJECT-TYPE
			SYNTAX  CounterBasedGauge64
			MAX-ACCESS read-only
			STATUS current
			DESCRIPTION  "Custom GTP Deny Records Sent Failure"
			::={ netflowMonitorSEntry 108 }

			customGtpInfoEventRecordsSent OBJECT-TYPE
			SYNTAX  CounterBasedGauge64
			MAX-ACCESS read-only
			STATUS current
			DESCRIPTION  "Custom GTP Info Records Sent"
			::={ netflowMonitorSEntry 109 }

			customGtpInfoEventRecordsSentFailure OBJECT-TYPE
			SYNTAX  CounterBasedGauge64
			MAX-ACCESS read-only
			STATUS current
			DESCRIPTION  "Custom GTP Info Records Sent Failure"
			::={ netflowMonitorSEntry 110 }

			customFwIddosEntryCreatedRecordsSent OBJECT-TYPE
			SYNTAX  CounterBasedGauge64
			MAX-ACCESS read-only
			STATUS current
			DESCRIPTION  "Custom FW iDDoS Entry Created Records Sent"
			::={ netflowMonitorSEntry 111 }

			customFwIddosEntryCreatedRecordsSentFailure OBJECT-TYPE
			SYNTAX  CounterBasedGauge64
			MAX-ACCESS read-only
			STATUS current
			DESCRIPTION  "Custom FW iDDoS Entry Created Records Sent Failure"
			::={ netflowMonitorSEntry 112 }

			customFwIddosEntryDeletedRecordsSent OBJECT-TYPE
			SYNTAX  CounterBasedGauge64
			MAX-ACCESS read-only
			STATUS current
			DESCRIPTION  "Custom FW iDDoS Entry Deleted Records Sent"
			::={ netflowMonitorSEntry 113 }

			customFwIddosEntryDeletedRecordsSentFailure OBJECT-TYPE
			SYNTAX  CounterBasedGauge64
			MAX-ACCESS read-only
			STATUS current
			DESCRIPTION  "Custom FW iDDoS Entry Deleted Records Sent Failure"
			::={ netflowMonitorSEntry 114 }

			customFwSesnLimitExceededRecordsSent OBJECT-TYPE
			SYNTAX  CounterBasedGauge64
			MAX-ACCESS read-only
			STATUS current
			DESCRIPTION  "Custom FW Session Limit Exceeded Records Sent"
			::={ netflowMonitorSEntry 115 }

			customFwSesnLimitExceededRecordsSentFailure OBJECT-TYPE
			SYNTAX  CounterBasedGauge64
			MAX-ACCESS read-only
			STATUS current
			DESCRIPTION  "Custom FW Session Limit Exceeded Records Sent Failure"
			::={ netflowMonitorSEntry 116 }

			customNatIddosL3EntryCreatedRecordsSent OBJECT-TYPE
			SYNTAX  CounterBasedGauge64
			MAX-ACCESS read-only
			STATUS current
			DESCRIPTION  "Custom NAT iDDoS L3 Entry Created Records Sent"
			::={ netflowMonitorSEntry 117 }

			customNatIddosL3EntryCreatedRecordsSentFailure OBJECT-TYPE
			SYNTAX  CounterBasedGauge64
			MAX-ACCESS read-only
			STATUS current
			DESCRIPTION  "Custom NAT iDDoS L3 Entry Created Records Sent Failure"
			::={ netflowMonitorSEntry 118 }

			customNatIddosL3EntryDeletedRecordsSent OBJECT-TYPE
			SYNTAX  CounterBasedGauge64
			MAX-ACCESS read-only
			STATUS current
			DESCRIPTION  "Custom NAT iDDoS L3 Entry Deleted Records Sent"
			::={ netflowMonitorSEntry 119 }

			customNatIddosL3EntryDeletedRecordsSentFailure OBJECT-TYPE
			SYNTAX  CounterBasedGauge64
			MAX-ACCESS read-only
			STATUS current
			DESCRIPTION  "Custom NAT iDDoS L3 Entry Deleted Records Sent Failure"
			::={ netflowMonitorSEntry 120 }

			customNatIddosL4EntryCreatedRecordsSent OBJECT-TYPE
			SYNTAX  CounterBasedGauge64
			MAX-ACCESS read-only
			STATUS current
			DESCRIPTION  "Custom NAT iDDoS L4 Entry Created Records Sent"
			::={ netflowMonitorSEntry 121 }

			customNatIddosL4EntryCreatedRecordsSentFailure OBJECT-TYPE
			SYNTAX  CounterBasedGauge64
			MAX-ACCESS read-only
			STATUS current
			DESCRIPTION  "Custom NAT iDDoS L4 Entry Created Records Sent Failure"
			::={ netflowMonitorSEntry 122 }

			customNatIddosL4EntryDeletedRecordsSent OBJECT-TYPE
			SYNTAX  CounterBasedGauge64
			MAX-ACCESS read-only
			STATUS current
			DESCRIPTION  "Custom NAT iDDoS L4 Entry Deleted Records Sent"
			::={ netflowMonitorSEntry 123 }

			customNatIddosL4EntryDeletedRecordsSentFailure OBJECT-TYPE
			SYNTAX  CounterBasedGauge64
			MAX-ACCESS read-only
			STATUS current
			DESCRIPTION  "Custom NAT iDDoS L4 Entry Deleted Records Sent Failure"
			::={ netflowMonitorSEntry 124 }

			customGtpRateLimitPeriodicRecordsSent OBJECT-TYPE
			SYNTAX  CounterBasedGauge64
			MAX-ACCESS read-only
			STATUS current
			DESCRIPTION  "Custom GTP Rate Limit Periodic Records Sent"
			::={ netflowMonitorSEntry 125 }

			customGtpRateLimitPeriodicRecordsSentFailure OBJECT-TYPE
			SYNTAX  CounterBasedGauge64
			MAX-ACCESS read-only
			STATUS current
			DESCRIPTION  "Custom GTP Rate Limit Periodic Records Sent Failure"
			::={ netflowMonitorSEntry 126 }

END
