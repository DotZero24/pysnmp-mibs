ACOS-THREAT-INTEL-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosThreatIntel MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "ThreatIntel OID for ACOS"
				::=  {  acosRootStats 164  }

acosThreatIntelThreatList           OBJECT IDENTIFIER ::= { acosThreatIntel 2 }
acosThreatIntelThreatListS          OBJECT IDENTIFIER ::= { acosThreatIntelThreatList 1 }

threatIntelThreatListSTable OBJECT-TYPE
		SYNTAX SEQUENCE OF ThreatIntelThreatListSEntry
		MAX-ACCESS not-accessible
		STATUS current
		::={ acosThreatIntelThreatListS 1 }


	threatIntelThreatListSEntry OBJECT-TYPE
		SYNTAX ThreatIntelThreatListSEntry
		MAX-ACCESS not-accessible
		STATUS current
		INDEX {
			name
		}
		::={ threatIntelThreatListSTable 1 }


	ThreatIntelThreatListSEntry ::=
		SEQUENCE {
			name DisplayString,
			spamSources CounterBasedGauge64,
			windowsExploits CounterBasedGauge64,
			webAttacks CounterBasedGauge64,
			botnets CounterBasedGauge64,
			scanners CounterBasedGauge64,
			dosAttacks CounterBasedGauge64,
			reputation CounterBasedGauge64,
			phishing CounterBasedGauge64,
			proxy CounterBasedGauge64,
			mobileThreats CounterBasedGauge64,
			torProxy CounterBasedGauge64,
			totalHits CounterBasedGauge64
		}

			name OBJECT-TYPE
			SYNTAX  DisplayString
			MAX-ACCESS read-only
			STATUS current
			DESCRIPTION  "Threat category List name"
			::={ threatIntelThreatListSEntry 1 }

			spamSources OBJECT-TYPE
			SYNTAX  CounterBasedGauge64
			MAX-ACCESS read-only
			STATUS current
			DESCRIPTION  "Hits for spam sources"
			::={ threatIntelThreatListSEntry 2 }

			windowsExploits OBJECT-TYPE
			SYNTAX  CounterBasedGauge64
			MAX-ACCESS read-only
			STATUS current
			DESCRIPTION  "Hits for windows exploits"
			::={ threatIntelThreatListSEntry 3 }

			webAttacks OBJECT-TYPE
			SYNTAX  CounterBasedGauge64
			MAX-ACCESS read-only
			STATUS current
			DESCRIPTION  "Hits for web attacks"
			::={ threatIntelThreatListSEntry 4 }

			botnets OBJECT-TYPE
			SYNTAX  CounterBasedGauge64
			MAX-ACCESS read-only
			STATUS current
			DESCRIPTION  "Hits for botnets"
			::={ threatIntelThreatListSEntry 5 }

			scanners OBJECT-TYPE
			SYNTAX  CounterBasedGauge64
			MAX-ACCESS read-only
			STATUS current
			DESCRIPTION  "Hits for scanners"
			::={ threatIntelThreatListSEntry 6 }

			dosAttacks OBJECT-TYPE
			SYNTAX  CounterBasedGauge64
			MAX-ACCESS read-only
			STATUS current
			DESCRIPTION  "Hits for dos attacks"
			::={ threatIntelThreatListSEntry 7 }

			reputation OBJECT-TYPE
			SYNTAX  CounterBasedGauge64
			MAX-ACCESS read-only
			STATUS current
			DESCRIPTION  "Hits for reputation"
			::={ threatIntelThreatListSEntry 8 }

			phishing OBJECT-TYPE
			SYNTAX  CounterBasedGauge64
			MAX-ACCESS read-only
			STATUS current
			DESCRIPTION  "Hits for phishing"
			::={ threatIntelThreatListSEntry 9 }

			proxy OBJECT-TYPE
			SYNTAX  CounterBasedGauge64
			MAX-ACCESS read-only
			STATUS current
			DESCRIPTION  "Hits for proxy"
			::={ threatIntelThreatListSEntry 10 }

			mobileThreats OBJECT-TYPE
			SYNTAX  CounterBasedGauge64
			MAX-ACCESS read-only
			STATUS current
			DESCRIPTION  "Hits for mobile threats"
			::={ threatIntelThreatListSEntry 11 }

			torProxy OBJECT-TYPE
			SYNTAX  CounterBasedGauge64
			MAX-ACCESS read-only
			STATUS current
			DESCRIPTION  "Hits for tor-proxy"
			::={ threatIntelThreatListSEntry 12 }

			totalHits OBJECT-TYPE
			SYNTAX  CounterBasedGauge64
			MAX-ACCESS read-only
			STATUS current
			DESCRIPTION  "Total hits for threat-list"
			::={ threatIntelThreatListSEntry 13 }

acosThreatIntelWebrootGlobal        OBJECT IDENTIFIER ::= { acosThreatIntel 3 }
acosThreatIntelWebrootGlobalS       OBJECT IDENTIFIER ::= { acosThreatIntelWebrootGlobal 1 }

		spamSources OBJECT-TYPE
		SYNTAX  CounterBasedGauge64
		MAX-ACCESS read-only
		STATUS current
		DESCRIPTION  "Hits for spam sources"
		::={ acosThreatIntelWebrootGlobalS 1 }

		windowsExploits OBJECT-TYPE
		SYNTAX  CounterBasedGauge64
		MAX-ACCESS read-only
		STATUS current
		DESCRIPTION  "Hits for windows exploits"
		::={ acosThreatIntelWebrootGlobalS 2 }

		webAttacks OBJECT-TYPE
		SYNTAX  CounterBasedGauge64
		MAX-ACCESS read-only
		STATUS current
		DESCRIPTION  "Hits for web attacks"
		::={ acosThreatIntelWebrootGlobalS 3 }

		botnets OBJECT-TYPE
		SYNTAX  CounterBasedGauge64
		MAX-ACCESS read-only
		STATUS current
		DESCRIPTION  "Hits for botnets"
		::={ acosThreatIntelWebrootGlobalS 4 }

		scanners OBJECT-TYPE
		SYNTAX  CounterBasedGauge64
		MAX-ACCESS read-only
		STATUS current
		DESCRIPTION  "Hits for scanners"
		::={ acosThreatIntelWebrootGlobalS 5 }

		dosAttacks OBJECT-TYPE
		SYNTAX  CounterBasedGauge64
		MAX-ACCESS read-only
		STATUS current
		DESCRIPTION  "Hits for dos attacks"
		::={ acosThreatIntelWebrootGlobalS 6 }

		reputation OBJECT-TYPE
		SYNTAX  CounterBasedGauge64
		MAX-ACCESS read-only
		STATUS current
		DESCRIPTION  "Hits for reputation"
		::={ acosThreatIntelWebrootGlobalS 7 }

		phishing OBJECT-TYPE
		SYNTAX  CounterBasedGauge64
		MAX-ACCESS read-only
		STATUS current
		DESCRIPTION  "Hits for phishing"
		::={ acosThreatIntelWebrootGlobalS 8 }

		proxy OBJECT-TYPE
		SYNTAX  CounterBasedGauge64
		MAX-ACCESS read-only
		STATUS current
		DESCRIPTION  "Hits for proxy"
		::={ acosThreatIntelWebrootGlobalS 9 }

		mobileThreats OBJECT-TYPE
		SYNTAX  CounterBasedGauge64
		MAX-ACCESS read-only
		STATUS current
		DESCRIPTION  "Hits for mobile threats"
		::={ acosThreatIntelWebrootGlobalS 10 }

		torProxy OBJECT-TYPE
		SYNTAX  CounterBasedGauge64
		MAX-ACCESS read-only
		STATUS current
		DESCRIPTION  "Hits for tor-proxy"
		::={ acosThreatIntelWebrootGlobalS 11 }

		rtuLookup OBJECT-TYPE
		SYNTAX  CounterBasedGauge64
		MAX-ACCESS read-only
		STATUS current
		DESCRIPTION  "Number of lookups in RTU cache"
		::={ acosThreatIntelWebrootGlobalS 12 }

		databaseLookup OBJECT-TYPE
		SYNTAX  CounterBasedGauge64
		MAX-ACCESS read-only
		STATUS current
		DESCRIPTION  "Number of lookups in database"
		::={ acosThreatIntelWebrootGlobalS 13 }

		nonMaliciousIps OBJECT-TYPE
		SYNTAX  CounterBasedGauge64
		MAX-ACCESS read-only
		STATUS current
		DESCRIPTION  "IP's not found in database or RTU cache"
		::={ acosThreatIntelWebrootGlobalS 14 }

END
