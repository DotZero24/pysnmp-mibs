ACOS-SYSTEM-VIEW-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosSystemView MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "SystemView OID for ACOS"
				::=  {  acosRootStats 38  }

acosSystemViewMemoryView            OBJECT IDENTIFIER ::= { acosSystemView 1 }
acosSystemViewMemoryViewS           OBJECT IDENTIFIER ::= { acosSystemViewMemoryView 1 }

		usagePercentage OBJECT-TYPE
		SYNTAX  CounterBasedGauge64
		MAX-ACCESS read-only
		STATUS current
		DESCRIPTION  "Usage percentage"
		::={ acosSystemViewMemoryViewS 1 }

END
