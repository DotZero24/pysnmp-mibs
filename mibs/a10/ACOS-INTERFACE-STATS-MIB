ACOS-INTERFACE-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosInterface MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Interface OID for ACOS"
				::=  {  acosRootStats 95  }

acosInterfaceManagement             OBJECT IDENTIFIER ::= { acosInterface 1 }
acosInterfaceManagementS            OBJECT IDENTIFIER ::= { acosInterfaceManagement 1 }

		packetsInput OBJECT-TYPE
		SYNTAX  CounterBasedGauge64
		MAX-ACCESS read-only
		STATUS current
		DESCRIPTION  "Input packets"
		::={ acosInterfaceManagementS 1 }

		bytesInput OBJECT-TYPE
		SYNTAX  CounterBasedGauge64
		MAX-ACCESS read-only
		STATUS current
		DESCRIPTION  "Input bytes"
		::={ acosInterfaceManagementS 2 }

		receivedBroadcasts OBJECT-TYPE
		SYNTAX  CounterBasedGauge64
		MAX-ACCESS read-only
		STATUS current
		DESCRIPTION  "Received broadcasts"
		::={ acosInterfaceManagementS 3 }

		receivedMulticasts OBJECT-TYPE
		SYNTAX  CounterBasedGauge64
		MAX-ACCESS read-only
		STATUS current
		DESCRIPTION  "Received multicasts"
		::={ acosInterfaceManagementS 4 }

		receivedUnicasts OBJECT-TYPE
		SYNTAX  CounterBasedGauge64
		MAX-ACCESS read-only
		STATUS current
		DESCRIPTION  "Received unicasts"
		::={ acosInterfaceManagementS 5 }

		inputErrors OBJECT-TYPE
		SYNTAX  CounterBasedGauge64
		MAX-ACCESS read-only
		STATUS current
		DESCRIPTION  "Input errors"
		::={ acosInterfaceManagementS 6 }

		crc OBJECT-TYPE
		SYNTAX  CounterBasedGauge64
		MAX-ACCESS read-only
		STATUS current
		DESCRIPTION  "CRC"
		::={ acosInterfaceManagementS 7 }

		frame OBJECT-TYPE
		SYNTAX  CounterBasedGauge64
		MAX-ACCESS read-only
		STATUS current
		DESCRIPTION  "Frames"
		::={ acosInterfaceManagementS 8 }

		inputErrShort OBJECT-TYPE
		SYNTAX  CounterBasedGauge64
		MAX-ACCESS read-only
		STATUS current
		DESCRIPTION  "Runts"
		::={ acosInterfaceManagementS 9 }

		inputErrLong OBJECT-TYPE
		SYNTAX  CounterBasedGauge64
		MAX-ACCESS read-only
		STATUS current
		DESCRIPTION  "Giants"
		::={ acosInterfaceManagementS 10 }

		packetsOutput OBJECT-TYPE
		SYNTAX  CounterBasedGauge64
		MAX-ACCESS read-only
		STATUS current
		DESCRIPTION  "Output packets"
		::={ acosInterfaceManagementS 11 }

		bytesOutput OBJECT-TYPE
		SYNTAX  CounterBasedGauge64
		MAX-ACCESS read-only
		STATUS current
		DESCRIPTION  "Output bytes"
		::={ acosInterfaceManagementS 12 }

		transmittedBroadcasts OBJECT-TYPE
		SYNTAX  CounterBasedGauge64
		MAX-ACCESS read-only
		STATUS current
		DESCRIPTION  "Transmitted broadcasts"
		::={ acosInterfaceManagementS 13 }

		transmittedMulticasts OBJECT-TYPE
		SYNTAX  CounterBasedGauge64
		MAX-ACCESS read-only
		STATUS current
		DESCRIPTION  "Transmitted multicasts"
		::={ acosInterfaceManagementS 14 }

		transmittedUnicasts OBJECT-TYPE
		SYNTAX  CounterBasedGauge64
		MAX-ACCESS read-only
		STATUS current
		DESCRIPTION  "Transmitted unicasts"
		::={ acosInterfaceManagementS 15 }

		outputErrors OBJECT-TYPE
		SYNTAX  CounterBasedGauge64
		MAX-ACCESS read-only
		STATUS current
		DESCRIPTION  "Output errors"
		::={ acosInterfaceManagementS 16 }

		collisions OBJECT-TYPE
		SYNTAX  CounterBasedGauge64
		MAX-ACCESS read-only
		STATUS current
		DESCRIPTION  "Collisions"
		::={ acosInterfaceManagementS 17 }

acosInterfaceEthernet               OBJECT IDENTIFIER ::= { acosInterface 2 }
acosInterfaceEthernetS              OBJECT IDENTIFIER ::= { acosInterfaceEthernet 1 }

interfaceEthernetSTable OBJECT-TYPE
		SYNTAX SEQUENCE OF InterfaceEthernetSEntry
		MAX-ACCESS not-accessible
		STATUS current
		::={ acosInterfaceEthernetS 1 }


	interfaceEthernetSEntry OBJECT-TYPE
		SYNTAX InterfaceEthernetSEntry
		MAX-ACCESS not-accessible
		STATUS current
		INDEX {
			ifnum
		}
		::={ interfaceEthernetSTable 1 }


	InterfaceEthernetSEntry ::=
		SEQUENCE {
			ifnum DisplayString,
			packetsInput CounterBasedGauge64,
			bytesInput CounterBasedGauge64,
			receivedBroadcasts CounterBasedGauge64,
			receivedMulticasts CounterBasedGauge64,
			receivedUnicasts CounterBasedGauge64,
			inputErrors CounterBasedGauge64,
			crc CounterBasedGauge64,
			frame CounterBasedGauge64,
			runts CounterBasedGauge64,
			giants CounterBasedGauge64,
			packetsOutput CounterBasedGauge64,
			bytesOutput CounterBasedGauge64,
			transmittedBroadcasts CounterBasedGauge64,
			transmittedMulticasts CounterBasedGauge64,
			transmittedUnicasts CounterBasedGauge64,
			outputErrors CounterBasedGauge64,
			collisions CounterBasedGauge64,
			giantsOutput CounterBasedGauge64,
			ratePktSent CounterBasedGauge64,
			rateByteSent CounterBasedGauge64,
			ratePktRcvd CounterBasedGauge64,
			rateByteRcvd CounterBasedGauge64,
			loadInterval CounterBasedGauge64
		}

			ifnum OBJECT-TYPE
			SYNTAX  DisplayString
			MAX-ACCESS read-only
			STATUS current
			DESCRIPTION  "Ethernet interface number"
			::={ interfaceEthernetSEntry 1 }

			packetsInput OBJECT-TYPE
			SYNTAX  CounterBasedGauge64
			MAX-ACCESS read-only
			STATUS current
			DESCRIPTION  "Input packets"
			::={ interfaceEthernetSEntry 2 }

			bytesInput OBJECT-TYPE
			SYNTAX  CounterBasedGauge64
			MAX-ACCESS read-only
			STATUS current
			DESCRIPTION  "Input bytes"
			::={ interfaceEthernetSEntry 3 }

			receivedBroadcasts OBJECT-TYPE
			SYNTAX  CounterBasedGauge64
			MAX-ACCESS read-only
			STATUS current
			DESCRIPTION  "Received broadcasts"
			::={ interfaceEthernetSEntry 4 }

			receivedMulticasts OBJECT-TYPE
			SYNTAX  CounterBasedGauge64
			MAX-ACCESS read-only
			STATUS current
			DESCRIPTION  "Received multicasts"
			::={ interfaceEthernetSEntry 5 }

			receivedUnicasts OBJECT-TYPE
			SYNTAX  CounterBasedGauge64
			MAX-ACCESS read-only
			STATUS current
			DESCRIPTION  "Received unicasts"
			::={ interfaceEthernetSEntry 6 }

			inputErrors OBJECT-TYPE
			SYNTAX  CounterBasedGauge64
			MAX-ACCESS read-only
			STATUS current
			DESCRIPTION  "Input errors"
			::={ interfaceEthernetSEntry 7 }

			crc OBJECT-TYPE
			SYNTAX  CounterBasedGauge64
			MAX-ACCESS read-only
			STATUS current
			DESCRIPTION  "CRC"
			::={ interfaceEthernetSEntry 8 }

			frame OBJECT-TYPE
			SYNTAX  CounterBasedGauge64
			MAX-ACCESS read-only
			STATUS current
			DESCRIPTION  "Frames"
			::={ interfaceEthernetSEntry 9 }

			runts OBJECT-TYPE
			SYNTAX  CounterBasedGauge64
			MAX-ACCESS read-only
			STATUS current
			DESCRIPTION  "Runts"
			::={ interfaceEthernetSEntry 10 }

			giants OBJECT-TYPE
			SYNTAX  CounterBasedGauge64
			MAX-ACCESS read-only
			STATUS current
			DESCRIPTION  "Giants"
			::={ interfaceEthernetSEntry 11 }

			packetsOutput OBJECT-TYPE
			SYNTAX  CounterBasedGauge64
			MAX-ACCESS read-only
			STATUS current
			DESCRIPTION  "Output packets"
			::={ interfaceEthernetSEntry 12 }

			bytesOutput OBJECT-TYPE
			SYNTAX  CounterBasedGauge64
			MAX-ACCESS read-only
			STATUS current
			DESCRIPTION  "Output bytes"
			::={ interfaceEthernetSEntry 13 }

			transmittedBroadcasts OBJECT-TYPE
			SYNTAX  CounterBasedGauge64
			MAX-ACCESS read-only
			STATUS current
			DESCRIPTION  "Transmitted broadcasts"
			::={ interfaceEthernetSEntry 14 }

			transmittedMulticasts OBJECT-TYPE
			SYNTAX  CounterBasedGauge64
			MAX-ACCESS read-only
			STATUS current
			DESCRIPTION  "Transmitted multicasts"
			::={ interfaceEthernetSEntry 15 }

			transmittedUnicasts OBJECT-TYPE
			SYNTAX  CounterBasedGauge64
			MAX-ACCESS read-only
			STATUS current
			DESCRIPTION  "Transmitted unicasts"
			::={ interfaceEthernetSEntry 16 }

			outputErrors OBJECT-TYPE
			SYNTAX  CounterBasedGauge64
			MAX-ACCESS read-only
			STATUS current
			DESCRIPTION  "Output errors"
			::={ interfaceEthernetSEntry 17 }

			collisions OBJECT-TYPE
			SYNTAX  CounterBasedGauge64
			MAX-ACCESS read-only
			STATUS current
			DESCRIPTION  "Collisions"
			::={ interfaceEthernetSEntry 18 }

			giantsOutput OBJECT-TYPE
			SYNTAX  CounterBasedGauge64
			MAX-ACCESS read-only
			STATUS current
			DESCRIPTION  "Output Giants"
			::={ interfaceEthernetSEntry 19 }

			ratePktSent OBJECT-TYPE
			SYNTAX  CounterBasedGauge64
			MAX-ACCESS read-only
			STATUS current
			DESCRIPTION  "Packet sent rate packets/sec"
			::={ interfaceEthernetSEntry 20 }

			rateByteSent OBJECT-TYPE
			SYNTAX  CounterBasedGauge64
			MAX-ACCESS read-only
			STATUS current
			DESCRIPTION  "Byte sent rate bits/sec"
			::={ interfaceEthernetSEntry 21 }

			ratePktRcvd OBJECT-TYPE
			SYNTAX  CounterBasedGauge64
			MAX-ACCESS read-only
			STATUS current
			DESCRIPTION  "Packet received rate packets/sec"
			::={ interfaceEthernetSEntry 22 }

			rateByteRcvd OBJECT-TYPE
			SYNTAX  CounterBasedGauge64
			MAX-ACCESS read-only
			STATUS current
			DESCRIPTION  "Byte received rate bits/sec"
			::={ interfaceEthernetSEntry 23 }

			loadInterval OBJECT-TYPE
			SYNTAX  CounterBasedGauge64
			MAX-ACCESS read-only
			STATUS current
			DESCRIPTION  "Load Interval"
			::={ interfaceEthernetSEntry 24 }

acosInterfaceTrunk                  OBJECT IDENTIFIER ::= { acosInterface 4 }
acosInterfaceTrunkS                 OBJECT IDENTIFIER ::= { acosInterfaceTrunk 1 }

interfaceTrunkSTable OBJECT-TYPE
		SYNTAX SEQUENCE OF InterfaceTrunkSEntry
		MAX-ACCESS not-accessible
		STATUS current
		::={ acosInterfaceTrunkS 1 }


	interfaceTrunkSEntry OBJECT-TYPE
		SYNTAX InterfaceTrunkSEntry
		MAX-ACCESS not-accessible
		STATUS current
		INDEX {
			ifnum
		}
		::={ interfaceTrunkSTable 1 }


	InterfaceTrunkSEntry ::=
		SEQUENCE {
			ifnum INTEGER,
			numPkts CounterBasedGauge64,
			numTotalBytes CounterBasedGauge64,
			numUnicastPkts CounterBasedGauge64,
			numBroadcastPkts CounterBasedGauge64,
			numMulticastPkts CounterBasedGauge64,
			numTxPkts CounterBasedGauge64,
			numTotalTxBytes CounterBasedGauge64,
			numUnicastTxPkts CounterBasedGauge64,
			numBroadcastTxPkts CounterBasedGauge64,
			numMulticastTxPkts CounterBasedGauge64,
			droppedDisRxPkts CounterBasedGauge64,
			droppedRxPkts CounterBasedGauge64,
			droppedDisTxPkts CounterBasedGauge64,
			droppedTxPkts CounterBasedGauge64
		}

			ifnum OBJECT-TYPE
			SYNTAX  INTEGER
			MAX-ACCESS read-only
			STATUS current
			DESCRIPTION  "Trunk interface number"
			::={ interfaceTrunkSEntry 1 }

			numPkts OBJECT-TYPE
			SYNTAX  CounterBasedGauge64
			MAX-ACCESS read-only
			STATUS current
			DESCRIPTION  "some help string"
			::={ interfaceTrunkSEntry 2 }

			numTotalBytes OBJECT-TYPE
			SYNTAX  CounterBasedGauge64
			MAX-ACCESS read-only
			STATUS current
			DESCRIPTION  "some help string"
			::={ interfaceTrunkSEntry 3 }

			numUnicastPkts OBJECT-TYPE
			SYNTAX  CounterBasedGauge64
			MAX-ACCESS read-only
			STATUS current
			DESCRIPTION  "some help string"
			::={ interfaceTrunkSEntry 4 }

			numBroadcastPkts OBJECT-TYPE
			SYNTAX  CounterBasedGauge64
			MAX-ACCESS read-only
			STATUS current
			DESCRIPTION  "some help string"
			::={ interfaceTrunkSEntry 5 }

			numMulticastPkts OBJECT-TYPE
			SYNTAX  CounterBasedGauge64
			MAX-ACCESS read-only
			STATUS current
			DESCRIPTION  "some help string"
			::={ interfaceTrunkSEntry 6 }

			numTxPkts OBJECT-TYPE
			SYNTAX  CounterBasedGauge64
			MAX-ACCESS read-only
			STATUS current
			DESCRIPTION  "some help string"
			::={ interfaceTrunkSEntry 7 }

			numTotalTxBytes OBJECT-TYPE
			SYNTAX  CounterBasedGauge64
			MAX-ACCESS read-only
			STATUS current
			DESCRIPTION  "some help string"
			::={ interfaceTrunkSEntry 8 }

			numUnicastTxPkts OBJECT-TYPE
			SYNTAX  CounterBasedGauge64
			MAX-ACCESS read-only
			STATUS current
			DESCRIPTION  "some help string"
			::={ interfaceTrunkSEntry 9 }

			numBroadcastTxPkts OBJECT-TYPE
			SYNTAX  CounterBasedGauge64
			MAX-ACCESS read-only
			STATUS current
			DESCRIPTION  "some help string"
			::={ interfaceTrunkSEntry 10 }

			numMulticastTxPkts OBJECT-TYPE
			SYNTAX  CounterBasedGauge64
			MAX-ACCESS read-only
			STATUS current
			DESCRIPTION  "some help string"
			::={ interfaceTrunkSEntry 11 }

			droppedDisRxPkts OBJECT-TYPE
			SYNTAX  CounterBasedGauge64
			MAX-ACCESS read-only
			STATUS current
			DESCRIPTION  "some help string"
			::={ interfaceTrunkSEntry 12 }

			droppedRxPkts OBJECT-TYPE
			SYNTAX  CounterBasedGauge64
			MAX-ACCESS read-only
			STATUS current
			DESCRIPTION  "some help string"
			::={ interfaceTrunkSEntry 13 }

			droppedDisTxPkts OBJECT-TYPE
			SYNTAX  CounterBasedGauge64
			MAX-ACCESS read-only
			STATUS current
			DESCRIPTION  "some help string"
			::={ interfaceTrunkSEntry 14 }

			droppedTxPkts OBJECT-TYPE
			SYNTAX  CounterBasedGauge64
			MAX-ACCESS read-only
			STATUS current
			DESCRIPTION  "some help string"
			::={ interfaceTrunkSEntry 15 }

acosInterfaceVe                     OBJECT IDENTIFIER ::= { acosInterface 5 }
acosInterfaceVeS                    OBJECT IDENTIFIER ::= { acosInterfaceVe 1 }

interfaceVeSTable OBJECT-TYPE
		SYNTAX SEQUENCE OF InterfaceVeSEntry
		MAX-ACCESS not-accessible
		STATUS current
		::={ acosInterfaceVeS 1 }


	interfaceVeSEntry OBJECT-TYPE
		SYNTAX InterfaceVeSEntry
		MAX-ACCESS not-accessible
		STATUS current
		INDEX {
			veIfNum
		}
		::={ interfaceVeSTable 1 }


	InterfaceVeSEntry ::=
		SEQUENCE {
			veIfNum INTEGER,
			numPkts CounterBasedGauge64,
			numTotalBytes CounterBasedGauge64,
			numUnicastPkts CounterBasedGauge64,
			numBroadcastPkts CounterBasedGauge64,
			numMulticastPkts CounterBasedGauge64,
			numTxPkts CounterBasedGauge64,
			numTotalTxBytes CounterBasedGauge64,
			numUnicastTxPkts CounterBasedGauge64,
			numBroadcastTxPkts CounterBasedGauge64,
			numMulticastTxPkts CounterBasedGauge64,
			ratePktSent CounterBasedGauge64,
			rateByteSent CounterBasedGauge64,
			ratePktRcvd CounterBasedGauge64,
			rateByteRcvd CounterBasedGauge64,
			loadInterval CounterBasedGauge64
		}

			veIfNum OBJECT-TYPE
			SYNTAX  INTEGER
			MAX-ACCESS read-only
			STATUS current
			DESCRIPTION  "Virtual ethernet interface number"
			::={ interfaceVeSEntry 1 }

			numPkts OBJECT-TYPE
			SYNTAX  CounterBasedGauge64
			MAX-ACCESS read-only
			STATUS current
			DESCRIPTION  "Input packets"
			::={ interfaceVeSEntry 2 }

			numTotalBytes OBJECT-TYPE
			SYNTAX  CounterBasedGauge64
			MAX-ACCESS read-only
			STATUS current
			DESCRIPTION  "Input bytes"
			::={ interfaceVeSEntry 3 }

			numUnicastPkts OBJECT-TYPE
			SYNTAX  CounterBasedGauge64
			MAX-ACCESS read-only
			STATUS current
			DESCRIPTION  "Received unicasts"
			::={ interfaceVeSEntry 4 }

			numBroadcastPkts OBJECT-TYPE
			SYNTAX  CounterBasedGauge64
			MAX-ACCESS read-only
			STATUS current
			DESCRIPTION  "Received broadcasts"
			::={ interfaceVeSEntry 5 }

			numMulticastPkts OBJECT-TYPE
			SYNTAX  CounterBasedGauge64
			MAX-ACCESS read-only
			STATUS current
			DESCRIPTION  "Received multicasts"
			::={ interfaceVeSEntry 6 }

			numTxPkts OBJECT-TYPE
			SYNTAX  CounterBasedGauge64
			MAX-ACCESS read-only
			STATUS current
			DESCRIPTION  "Transmitted packets"
			::={ interfaceVeSEntry 7 }

			numTotalTxBytes OBJECT-TYPE
			SYNTAX  CounterBasedGauge64
			MAX-ACCESS read-only
			STATUS current
			DESCRIPTION  "Transmitted bytes"
			::={ interfaceVeSEntry 8 }

			numUnicastTxPkts OBJECT-TYPE
			SYNTAX  CounterBasedGauge64
			MAX-ACCESS read-only
			STATUS current
			DESCRIPTION  "Transmitted unicasts"
			::={ interfaceVeSEntry 9 }

			numBroadcastTxPkts OBJECT-TYPE
			SYNTAX  CounterBasedGauge64
			MAX-ACCESS read-only
			STATUS current
			DESCRIPTION  "Transmitted broadcasts"
			::={ interfaceVeSEntry 10 }

			numMulticastTxPkts OBJECT-TYPE
			SYNTAX  CounterBasedGauge64
			MAX-ACCESS read-only
			STATUS current
			DESCRIPTION  "Transmitted multicasts"
			::={ interfaceVeSEntry 11 }

			ratePktSent OBJECT-TYPE
			SYNTAX  CounterBasedGauge64
			MAX-ACCESS read-only
			STATUS current
			DESCRIPTION  "Packet sent rate packets/sec"
			::={ interfaceVeSEntry 12 }

			rateByteSent OBJECT-TYPE
			SYNTAX  CounterBasedGauge64
			MAX-ACCESS read-only
			STATUS current
			DESCRIPTION  "Byte sent rate bits/sec"
			::={ interfaceVeSEntry 13 }

			ratePktRcvd OBJECT-TYPE
			SYNTAX  CounterBasedGauge64
			MAX-ACCESS read-only
			STATUS current
			DESCRIPTION  "Packet received rate packets/sec"
			::={ interfaceVeSEntry 14 }

			rateByteRcvd OBJECT-TYPE
			SYNTAX  CounterBasedGauge64
			MAX-ACCESS read-only
			STATUS current
			DESCRIPTION  "Byte received rate bits/sec"
			::={ interfaceVeSEntry 15 }

			loadInterval OBJECT-TYPE
			SYNTAX  CounterBasedGauge64
			MAX-ACCESS read-only
			STATUS current
			DESCRIPTION  "Load Interval"
			::={ interfaceVeSEntry 16 }

acosInterfaceLif                    OBJECT IDENTIFIER ::= { acosInterface 7 }
acosInterfaceLifS                   OBJECT IDENTIFIER ::= { acosInterfaceLif 1 }

interfaceLifSTable OBJECT-TYPE
		SYNTAX SEQUENCE OF InterfaceLifSEntry
		MAX-ACCESS not-accessible
		STATUS current
		::={ acosInterfaceLifS 1 }


	interfaceLifSEntry OBJECT-TYPE
		SYNTAX InterfaceLifSEntry
		MAX-ACCESS not-accessible
		STATUS current
		INDEX {
			lifIfName
		}
		::={ interfaceLifSTable 1 }


	InterfaceLifSEntry ::=
		SEQUENCE {
			lifIfName DisplayString,
			lifNumPkts CounterBasedGauge64,
			lifNumTotalBytes CounterBasedGauge64,
			lifNumUnicastPkts CounterBasedGauge64,
			lifNumBroadcastPkts CounterBasedGauge64,
			lifNumMulticastPkts CounterBasedGauge64,
			lifNumTxPkts CounterBasedGauge64,
			lifNumTotalTxBytes CounterBasedGauge64,
			lifNumUnicastTxPkts CounterBasedGauge64,
			lifNumBroadcastTxPkts CounterBasedGauge64,
			lifNumMulticastTxPkts CounterBasedGauge64,
			droppedDisRxPkts CounterBasedGauge64,
			droppedRxPkts CounterBasedGauge64,
			droppedDisTxPkts CounterBasedGauge64,
			droppedTxPkts CounterBasedGauge64,
			droppedRxPktsGreKey CounterBasedGauge64
		}

			lifIfName OBJECT-TYPE
			SYNTAX  DisplayString
			MAX-ACCESS read-only
			STATUS current
			DESCRIPTION  "Lif interface name"
			::={ interfaceLifSEntry 1 }

			lifNumPkts OBJECT-TYPE
			SYNTAX  CounterBasedGauge64
			MAX-ACCESS read-only
			STATUS current
			DESCRIPTION  "some help string"
			::={ interfaceLifSEntry 2 }

			lifNumTotalBytes OBJECT-TYPE
			SYNTAX  CounterBasedGauge64
			MAX-ACCESS read-only
			STATUS current
			DESCRIPTION  "some help string"
			::={ interfaceLifSEntry 3 }

			lifNumUnicastPkts OBJECT-TYPE
			SYNTAX  CounterBasedGauge64
			MAX-ACCESS read-only
			STATUS current
			DESCRIPTION  "some help string"
			::={ interfaceLifSEntry 4 }

			lifNumBroadcastPkts OBJECT-TYPE
			SYNTAX  CounterBasedGauge64
			MAX-ACCESS read-only
			STATUS current
			DESCRIPTION  "some help string"
			::={ interfaceLifSEntry 5 }

			lifNumMulticastPkts OBJECT-TYPE
			SYNTAX  CounterBasedGauge64
			MAX-ACCESS read-only
			STATUS current
			DESCRIPTION  "some help string"
			::={ interfaceLifSEntry 6 }

			lifNumTxPkts OBJECT-TYPE
			SYNTAX  CounterBasedGauge64
			MAX-ACCESS read-only
			STATUS current
			DESCRIPTION  "some help string"
			::={ interfaceLifSEntry 7 }

			lifNumTotalTxBytes OBJECT-TYPE
			SYNTAX  CounterBasedGauge64
			MAX-ACCESS read-only
			STATUS current
			DESCRIPTION  "some help string"
			::={ interfaceLifSEntry 8 }

			lifNumUnicastTxPkts OBJECT-TYPE
			SYNTAX  CounterBasedGauge64
			MAX-ACCESS read-only
			STATUS current
			DESCRIPTION  "some help string"
			::={ interfaceLifSEntry 9 }

			lifNumBroadcastTxPkts OBJECT-TYPE
			SYNTAX  CounterBasedGauge64
			MAX-ACCESS read-only
			STATUS current
			DESCRIPTION  "some help string"
			::={ interfaceLifSEntry 10 }

			lifNumMulticastTxPkts OBJECT-TYPE
			SYNTAX  CounterBasedGauge64
			MAX-ACCESS read-only
			STATUS current
			DESCRIPTION  "some help string"
			::={ interfaceLifSEntry 11 }

			droppedDisRxPkts OBJECT-TYPE
			SYNTAX  CounterBasedGauge64
			MAX-ACCESS read-only
			STATUS current
			DESCRIPTION  "some help string"
			::={ interfaceLifSEntry 12 }

			droppedRxPkts OBJECT-TYPE
			SYNTAX  CounterBasedGauge64
			MAX-ACCESS read-only
			STATUS current
			DESCRIPTION  "some help string"
			::={ interfaceLifSEntry 13 }

			droppedDisTxPkts OBJECT-TYPE
			SYNTAX  CounterBasedGauge64
			MAX-ACCESS read-only
			STATUS current
			DESCRIPTION  "some help string"
			::={ interfaceLifSEntry 14 }

			droppedTxPkts OBJECT-TYPE
			SYNTAX  CounterBasedGauge64
			MAX-ACCESS read-only
			STATUS current
			DESCRIPTION  "some help string"
			::={ interfaceLifSEntry 15 }

			droppedRxPktsGreKey OBJECT-TYPE
			SYNTAX  CounterBasedGauge64
			MAX-ACCESS read-only
			STATUS current
			DESCRIPTION  "some help string"
			::={ interfaceLifSEntry 16 }

acosInterfaceTunnel                 OBJECT IDENTIFIER ::= { acosInterface 8 }
acosInterfaceTunnelS                OBJECT IDENTIFIER ::= { acosInterfaceTunnel 1 }

interfaceTunnelSTable OBJECT-TYPE
		SYNTAX SEQUENCE OF InterfaceTunnelSEntry
		MAX-ACCESS not-accessible
		STATUS current
		::={ acosInterfaceTunnelS 1 }


	interfaceTunnelSEntry OBJECT-TYPE
		SYNTAX InterfaceTunnelSEntry
		MAX-ACCESS not-accessible
		STATUS current
		INDEX {
			ifnum
		}
		::={ interfaceTunnelSTable 1 }


	InterfaceTunnelSEntry ::=
		SEQUENCE {
			ifnum INTEGER,
			numRxPkts CounterBasedGauge64,
			numTotalRxBytes CounterBasedGauge64,
			numTxPkts CounterBasedGauge64,
			numTotalTxBytes CounterBasedGauge64,
			numRxErrPkts CounterBasedGauge64,
			numTxErrPkts CounterBasedGauge64,
			ratePktSent CounterBasedGauge64,
			rateByteSent CounterBasedGauge64,
			ratePktRcvd CounterBasedGauge64,
			rateByteRcvd CounterBasedGauge64
		}

			ifnum OBJECT-TYPE
			SYNTAX  INTEGER
			MAX-ACCESS read-only
			STATUS current
			DESCRIPTION  "Tunnel interface number"
			::={ interfaceTunnelSEntry 1 }

			numRxPkts OBJECT-TYPE
			SYNTAX  CounterBasedGauge64
			MAX-ACCESS read-only
			STATUS current
			DESCRIPTION  "received packets"
			::={ interfaceTunnelSEntry 2 }

			numTotalRxBytes OBJECT-TYPE
			SYNTAX  CounterBasedGauge64
			MAX-ACCESS read-only
			STATUS current
			DESCRIPTION  "received bytes"
			::={ interfaceTunnelSEntry 3 }

			numTxPkts OBJECT-TYPE
			SYNTAX  CounterBasedGauge64
			MAX-ACCESS read-only
			STATUS current
			DESCRIPTION  "sent packets"
			::={ interfaceTunnelSEntry 4 }

			numTotalTxBytes OBJECT-TYPE
			SYNTAX  CounterBasedGauge64
			MAX-ACCESS read-only
			STATUS current
			DESCRIPTION  "sent bytes"
			::={ interfaceTunnelSEntry 5 }

			numRxErrPkts OBJECT-TYPE
			SYNTAX  CounterBasedGauge64
			MAX-ACCESS read-only
			STATUS current
			DESCRIPTION  "received error packets"
			::={ interfaceTunnelSEntry 6 }

			numTxErrPkts OBJECT-TYPE
			SYNTAX  CounterBasedGauge64
			MAX-ACCESS read-only
			STATUS current
			DESCRIPTION  "sent error packets"
			::={ interfaceTunnelSEntry 7 }

			ratePktSent OBJECT-TYPE
			SYNTAX  CounterBasedGauge64
			MAX-ACCESS read-only
			STATUS current
			DESCRIPTION  "Packet sent rate packets/sec"
			::={ interfaceTunnelSEntry 8 }

			rateByteSent OBJECT-TYPE
			SYNTAX  CounterBasedGauge64
			MAX-ACCESS read-only
			STATUS current
			DESCRIPTION  "Byte sent rate bits/sec"
			::={ interfaceTunnelSEntry 9 }

			ratePktRcvd OBJECT-TYPE
			SYNTAX  CounterBasedGauge64
			MAX-ACCESS read-only
			STATUS current
			DESCRIPTION  "Packet received rate packets/sec"
			::={ interfaceTunnelSEntry 10 }

			rateByteRcvd OBJECT-TYPE
			SYNTAX  CounterBasedGauge64
			MAX-ACCESS read-only
			STATUS current
			DESCRIPTION  "Byte received rate bits/sec"
			::={ interfaceTunnelSEntry 11 }

END
