ACOS-WAF-RULE-SET-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosWafRuleSet MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "WafRuleSet OID for ACOS"
				::=  {  acosRootStats 194  }

acosWafRuleSet                      OBJECT IDENTIFIER ::= { acosRootStats 194 }
acosWafRuleSetS                     OBJECT IDENTIFIER ::= { acosWafRuleSet 1 }

wafRuleSetSTable OBJECT-TYPE
		SYNTAX SEQUENCE OF WafRuleSetSEntry
		MAX-ACCESS not-accessible
		STATUS current
		::={ acosWafRuleSetS 1 }


	wafRuleSetSEntry OBJECT-TYPE
		SYNTAX WafRuleSetSEntry
		MAX-ACCESS not-accessible
		STATUS current
		INDEX {
			name
		}
		::={ wafRuleSetSTable 1 }


	WafRuleSetSEntry ::=
		SEQUENCE {
			name DisplayString,
			request CounterBasedGauge64,
			response CounterBasedGauge64,
			phase1Pass CounterBasedGauge64,
			phase1Allow CounterBasedGauge64,
			phase1Deny CounterBasedGauge64,
			phase1Drop CounterBasedGauge64,
			phase1Redirect CounterBasedGauge64,
			phase1Other CounterBasedGauge64,
			phase2Pass CounterBasedGauge64,
			phase2Allow CounterBasedGauge64,
			phase2Deny CounterBasedGauge64,
			phase2Drop CounterBasedGauge64,
			phase2Redirect CounterBasedGauge64,
			phase2Other CounterBasedGauge64,
			phase3Pass CounterBasedGauge64,
			phase3Allow CounterBasedGauge64,
			phase3Deny CounterBasedGauge64,
			phase3Drop CounterBasedGauge64,
			phase3Redirect CounterBasedGauge64,
			phase3Other CounterBasedGauge64,
			phase4Pass CounterBasedGauge64,
			phase4Allow CounterBasedGauge64,
			phase4Deny CounterBasedGauge64,
			phase4Drop CounterBasedGauge64,
			phase4Redirect CounterBasedGauge64,
			phase4Other CounterBasedGauge64
		}

			name OBJECT-TYPE
			SYNTAX  DisplayString
			MAX-ACCESS read-only
			STATUS current
			DESCRIPTION  "WAF Rule set name"
			::={ wafRuleSetSEntry 1 }

			request OBJECT-TYPE
			SYNTAX  CounterBasedGauge64
			MAX-ACCESS read-only
			STATUS current
			DESCRIPTION  "Requests hanlded by WAF rule set"
			::={ wafRuleSetSEntry 2 }

			response OBJECT-TYPE
			SYNTAX  CounterBasedGauge64
			MAX-ACCESS read-only
			STATUS current
			DESCRIPTION  "Responses hanlded by WAF rule set"
			::={ wafRuleSetSEntry 3 }

			phase1Pass OBJECT-TYPE
			SYNTAX  CounterBasedGauge64
			MAX-ACCESS read-only
			STATUS current
			DESCRIPTION  "WAF rule set pass hits in phase 1"
			::={ wafRuleSetSEntry 4 }

			phase1Allow OBJECT-TYPE
			SYNTAX  CounterBasedGauge64
			MAX-ACCESS read-only
			STATUS current
			DESCRIPTION  "WAF rule set allow hits in phase 1"
			::={ wafRuleSetSEntry 5 }

			phase1Deny OBJECT-TYPE
			SYNTAX  CounterBasedGauge64
			MAX-ACCESS read-only
			STATUS current
			DESCRIPTION  "WAF rule set deny hits in phase 1"
			::={ wafRuleSetSEntry 6 }

			phase1Drop OBJECT-TYPE
			SYNTAX  CounterBasedGauge64
			MAX-ACCESS read-only
			STATUS current
			DESCRIPTION  "WAF rule set drop hits in phase 1"
			::={ wafRuleSetSEntry 7 }

			phase1Redirect OBJECT-TYPE
			SYNTAX  CounterBasedGauge64
			MAX-ACCESS read-only
			STATUS current
			DESCRIPTION  "WAF rule set redirect hits in phase 1"
			::={ wafRuleSetSEntry 8 }

			phase1Other OBJECT-TYPE
			SYNTAX  CounterBasedGauge64
			MAX-ACCESS read-only
			STATUS current
			DESCRIPTION  "WAF rule set other hits in phase 1"
			::={ wafRuleSetSEntry 9 }

			phase2Pass OBJECT-TYPE
			SYNTAX  CounterBasedGauge64
			MAX-ACCESS read-only
			STATUS current
			DESCRIPTION  "WAF rule set pass hits in phase 2"
			::={ wafRuleSetSEntry 10 }

			phase2Allow OBJECT-TYPE
			SYNTAX  CounterBasedGauge64
			MAX-ACCESS read-only
			STATUS current
			DESCRIPTION  "WAF rule set allow hits in phase 2"
			::={ wafRuleSetSEntry 11 }

			phase2Deny OBJECT-TYPE
			SYNTAX  CounterBasedGauge64
			MAX-ACCESS read-only
			STATUS current
			DESCRIPTION  "WAF rule set deny hits in phase 2"
			::={ wafRuleSetSEntry 12 }

			phase2Drop OBJECT-TYPE
			SYNTAX  CounterBasedGauge64
			MAX-ACCESS read-only
			STATUS current
			DESCRIPTION  "WAF rule set drop hits in phase 2"
			::={ wafRuleSetSEntry 13 }

			phase2Redirect OBJECT-TYPE
			SYNTAX  CounterBasedGauge64
			MAX-ACCESS read-only
			STATUS current
			DESCRIPTION  "WAF rule set redirect hits in phase 2"
			::={ wafRuleSetSEntry 14 }

			phase2Other OBJECT-TYPE
			SYNTAX  CounterBasedGauge64
			MAX-ACCESS read-only
			STATUS current
			DESCRIPTION  "WAF rule set other hits in phase 2"
			::={ wafRuleSetSEntry 15 }

			phase3Pass OBJECT-TYPE
			SYNTAX  CounterBasedGauge64
			MAX-ACCESS read-only
			STATUS current
			DESCRIPTION  "WAF rule set pass hits in phase 3"
			::={ wafRuleSetSEntry 16 }

			phase3Allow OBJECT-TYPE
			SYNTAX  CounterBasedGauge64
			MAX-ACCESS read-only
			STATUS current
			DESCRIPTION  "WAF rule set allow hits in phase 3"
			::={ wafRuleSetSEntry 17 }

			phase3Deny OBJECT-TYPE
			SYNTAX  CounterBasedGauge64
			MAX-ACCESS read-only
			STATUS current
			DESCRIPTION  "WAF rule set deny hits in phase 3"
			::={ wafRuleSetSEntry 18 }

			phase3Drop OBJECT-TYPE
			SYNTAX  CounterBasedGauge64
			MAX-ACCESS read-only
			STATUS current
			DESCRIPTION  "WAF rule set drop hits in phase 3"
			::={ wafRuleSetSEntry 19 }

			phase3Redirect OBJECT-TYPE
			SYNTAX  CounterBasedGauge64
			MAX-ACCESS read-only
			STATUS current
			DESCRIPTION  "WAF rule set redirect hits in phase 3"
			::={ wafRuleSetSEntry 20 }

			phase3Other OBJECT-TYPE
			SYNTAX  CounterBasedGauge64
			MAX-ACCESS read-only
			STATUS current
			DESCRIPTION  "WAF rule set other hits in phase 3"
			::={ wafRuleSetSEntry 21 }

			phase4Pass OBJECT-TYPE
			SYNTAX  CounterBasedGauge64
			MAX-ACCESS read-only
			STATUS current
			DESCRIPTION  "WAF rule set pass hits in phase 4"
			::={ wafRuleSetSEntry 22 }

			phase4Allow OBJECT-TYPE
			SYNTAX  CounterBasedGauge64
			MAX-ACCESS read-only
			STATUS current
			DESCRIPTION  "WAF rule set allow hits in phase 4"
			::={ wafRuleSetSEntry 23 }

			phase4Deny OBJECT-TYPE
			SYNTAX  CounterBasedGauge64
			MAX-ACCESS read-only
			STATUS current
			DESCRIPTION  "WAF rule set deny hits in phase 4"
			::={ wafRuleSetSEntry 24 }

			phase4Drop OBJECT-TYPE
			SYNTAX  CounterBasedGauge64
			MAX-ACCESS read-only
			STATUS current
			DESCRIPTION  "WAF rule set drop hits in phase 4"
			::={ wafRuleSetSEntry 25 }

			phase4Redirect OBJECT-TYPE
			SYNTAX  CounterBasedGauge64
			MAX-ACCESS read-only
			STATUS current
			DESCRIPTION  "WAF rule set redirect hits in phase 4"
			::={ wafRuleSetSEntry 26 }

			phase4Other OBJECT-TYPE
			SYNTAX  CounterBasedGauge64
			MAX-ACCESS read-only
			STATUS current
			DESCRIPTION  "WAF rule set other hits in phase 4"
			::={ wafRuleSetSEntry 27 }

END
