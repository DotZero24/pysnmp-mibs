ACOS-AAM-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosAam MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Aam OID for ACOS"
				::=  {  acosRootStats 103  }

acosAamAuthentication               OBJECT IDENTIFIER ::= { acosAam 1 }
acosAamAuthenticationGlobal         OBJECT IDENTIFIER ::= { acosAamAuthentication 1 }
acosAamAuthenticationGlobalS        OBJECT IDENTIFIER ::= { acosAamAuthenticationGlobal 1 }

		requests OBJECT-TYPE
		SYNTAX  CounterBasedGauge64
		MAX-ACCESS read-only
		STATUS current
		DESCRIPTION  "Total Authentication Request"
		::={ acosAamAuthenticationGlobalS 1 }

		responses OBJECT-TYPE
		SYNTAX  CounterBasedGauge64
		MAX-ACCESS read-only
		STATUS current
		DESCRIPTION  "Total Authentication Response"
		::={ acosAamAuthenticationGlobalS 2 }

		misses OBJECT-TYPE
		SYNTAX  CounterBasedGauge64
		MAX-ACCESS read-only
		STATUS current
		DESCRIPTION  "Total Authentication Request Missed"
		::={ acosAamAuthenticationGlobalS 3 }

		ocspStaplingRequestsToA10authd OBJECT-TYPE
		SYNTAX  CounterBasedGauge64
		MAX-ACCESS read-only
		STATUS current
		DESCRIPTION  "Total OCSP Stapling Request"
		::={ acosAamAuthenticationGlobalS 4 }

		ocspStaplingResponsesFromA10authd OBJECT-TYPE
		SYNTAX  CounterBasedGauge64
		MAX-ACCESS read-only
		STATUS current
		DESCRIPTION  "Total OCSP Stapling Response"
		::={ acosAamAuthenticationGlobalS 5 }

		openedSocket OBJECT-TYPE
		SYNTAX  CounterBasedGauge64
		MAX-ACCESS read-only
		STATUS current
		DESCRIPTION  "Total AAM Socket Opened"
		::={ acosAamAuthenticationGlobalS 6 }

		aamAuthGlobalOpenSocketFailed OBJECT-TYPE
		SYNTAX  CounterBasedGauge64
		MAX-ACCESS read-only
		STATUS current
		DESCRIPTION  "Total AAM Open Socket Failed"
		::={ acosAamAuthenticationGlobalS 7 }

		connect OBJECT-TYPE
		SYNTAX  CounterBasedGauge64
		MAX-ACCESS read-only
		STATUS current
		DESCRIPTION  "Total AAM Connection"
		::={ acosAamAuthenticationGlobalS 8 }

		aamAuthGlobalConnectFailed OBJECT-TYPE
		SYNTAX  CounterBasedGauge64
		MAX-ACCESS read-only
		STATUS current
		DESCRIPTION  "Total AAM Connect Failed"
		::={ acosAamAuthenticationGlobalS 9 }

		createdTimer OBJECT-TYPE
		SYNTAX  CounterBasedGauge64
		MAX-ACCESS read-only
		STATUS current
		DESCRIPTION  "Total AAM Timer Created"
		::={ acosAamAuthenticationGlobalS 10 }

		createTimerFailed OBJECT-TYPE
		SYNTAX  CounterBasedGauge64
		MAX-ACCESS read-only
		STATUS current
		DESCRIPTION  "Total AAM Timer Creation Failed"
		::={ acosAamAuthenticationGlobalS 11 }

		totalRequest OBJECT-TYPE
		SYNTAX  CounterBasedGauge64
		MAX-ACCESS read-only
		STATUS current
		DESCRIPTION  "Total Request Received by A10 Auth Service"
		::={ acosAamAuthenticationGlobalS 12 }

		getSocketOptionFailed OBJECT-TYPE
		SYNTAX  CounterBasedGauge64
		MAX-ACCESS read-only
		STATUS current
		DESCRIPTION  "Total AAM Get Socket Option Failed"
		::={ acosAamAuthenticationGlobalS 13 }

		aflexAuthzSucc OBJECT-TYPE
		SYNTAX  CounterBasedGauge64
		MAX-ACCESS read-only
		STATUS current
		DESCRIPTION  "Total Authorization success number in aFleX"
		::={ acosAamAuthenticationGlobalS 14 }

		aflexAuthzFail OBJECT-TYPE
		SYNTAX  CounterBasedGauge64
		MAX-ACCESS read-only
		STATUS current
		DESCRIPTION  "Total Authorization failure number in aFleX"
		::={ acosAamAuthenticationGlobalS 15 }

		authnSuccess OBJECT-TYPE
		SYNTAX  CounterBasedGauge64
		MAX-ACCESS read-only
		STATUS current
		DESCRIPTION  "Total Authentication success number"
		::={ acosAamAuthenticationGlobalS 16 }

		authnFailure OBJECT-TYPE
		SYNTAX  CounterBasedGauge64
		MAX-ACCESS read-only
		STATUS current
		DESCRIPTION  "Total Authentication failure number"
		::={ acosAamAuthenticationGlobalS 17 }

		authzSuccess OBJECT-TYPE
		SYNTAX  CounterBasedGauge64
		MAX-ACCESS read-only
		STATUS current
		DESCRIPTION  "Total Authorization success number"
		::={ acosAamAuthenticationGlobalS 18 }

		authzFailure OBJECT-TYPE
		SYNTAX  CounterBasedGauge64
		MAX-ACCESS read-only
		STATUS current
		DESCRIPTION  "Total Authorization failure number"
		::={ acosAamAuthenticationGlobalS 19 }

		activeSession OBJECT-TYPE
		SYNTAX  CounterBasedGauge64
		MAX-ACCESS read-only
		STATUS current
		DESCRIPTION  "Total Active Auth-Sessions"
		::={ acosAamAuthenticationGlobalS 20 }

		activeUser OBJECT-TYPE
		SYNTAX  CounterBasedGauge64
		MAX-ACCESS read-only
		STATUS current
		DESCRIPTION  "Total Active Users"
		::={ acosAamAuthenticationGlobalS 21 }

		dnsResolveFailed OBJECT-TYPE
		SYNTAX  CounterBasedGauge64
		MAX-ACCESS read-only
		STATUS current
		DESCRIPTION  "Total AAM DNS resolve failed"
		::={ acosAamAuthenticationGlobalS 22 }

acosAamAuthenticationLogon          OBJECT IDENTIFIER ::= { acosAamAuthentication 4 }
acosAamAuthenticationServer         OBJECT IDENTIFIER ::= { acosAamAuthentication 5 }
acosAamAuthenticationServerLdap     OBJECT IDENTIFIER ::= { acosAamAuthenticationServer 2 }
acosAamAuthenticationServerLdapS    OBJECT IDENTIFIER ::= { acosAamAuthenticationServerLdap 1 }

		aamAuthServerLdapAdminBindSuccess OBJECT-TYPE
		SYNTAX  CounterBasedGauge64
		MAX-ACCESS read-only
		STATUS current
		DESCRIPTION  "Total Admin Bind Success"
		::={ acosAamAuthenticationServerLdapS 1 }

		aamAuthServerLdapAdminBindFailure OBJECT-TYPE
		SYNTAX  CounterBasedGauge64
		MAX-ACCESS read-only
		STATUS current
		DESCRIPTION  "Total Admin Bind Failure"
		::={ acosAamAuthenticationServerLdapS 2 }

		aamAuthServerLdapBindSuccess OBJECT-TYPE
		SYNTAX  CounterBasedGauge64
		MAX-ACCESS read-only
		STATUS current
		DESCRIPTION  "Total User Bind Success"
		::={ acosAamAuthenticationServerLdapS 3 }

		aamAuthServerLdapBindFailure OBJECT-TYPE
		SYNTAX  CounterBasedGauge64
		MAX-ACCESS read-only
		STATUS current
		DESCRIPTION  "Total User Bind Failure"
		::={ acosAamAuthenticationServerLdapS 4 }

		aamAuthServerLdapSearchSuccess OBJECT-TYPE
		SYNTAX  CounterBasedGauge64
		MAX-ACCESS read-only
		STATUS current
		DESCRIPTION  "Total Search Success"
		::={ acosAamAuthenticationServerLdapS 5 }

		aamAuthServerLdapSearchFailure OBJECT-TYPE
		SYNTAX  CounterBasedGauge64
		MAX-ACCESS read-only
		STATUS current
		DESCRIPTION  "Total Search Failure"
		::={ acosAamAuthenticationServerLdapS 6 }

		aamAuthServerLdapAuthorizeSuccess OBJECT-TYPE
		SYNTAX  CounterBasedGauge64
		MAX-ACCESS read-only
		STATUS current
		DESCRIPTION  "Total Authorization Success"
		::={ acosAamAuthenticationServerLdapS 7 }

		aamAuthServerLdapAuthorizeFailure OBJECT-TYPE
		SYNTAX  CounterBasedGauge64
		MAX-ACCESS read-only
		STATUS current
		DESCRIPTION  "Total Authorization Failure"
		::={ acosAamAuthenticationServerLdapS 8 }

		aamAuthServerLdapTimeoutError OBJECT-TYPE
		SYNTAX  CounterBasedGauge64
		MAX-ACCESS read-only
		STATUS current
		DESCRIPTION  "Total Timeout"
		::={ acosAamAuthenticationServerLdapS 9 }

		aamAuthServerLdapOtherError OBJECT-TYPE
		SYNTAX  CounterBasedGauge64
		MAX-ACCESS read-only
		STATUS current
		DESCRIPTION  "Total Other Error"
		::={ acosAamAuthenticationServerLdapS 10 }

		aamAuthServerLdapRequest OBJECT-TYPE
		SYNTAX  CounterBasedGauge64
		MAX-ACCESS read-only
		STATUS current
		DESCRIPTION  "Total Request"
		::={ acosAamAuthenticationServerLdapS 11 }

		aamAuthServerLdapRequestNormal OBJECT-TYPE
		SYNTAX  CounterBasedGauge64
		MAX-ACCESS read-only
		STATUS current
		DESCRIPTION  "Total Normal Request"
		::={ acosAamAuthenticationServerLdapS 12 }

		aamAuthServerLdapRequestDropped OBJECT-TYPE
		SYNTAX  CounterBasedGauge64
		MAX-ACCESS read-only
		STATUS current
		DESCRIPTION  "Total Dropped Request"
		::={ acosAamAuthenticationServerLdapS 13 }

		aamAuthServerLdapResponseSuccess OBJECT-TYPE
		SYNTAX  CounterBasedGauge64
		MAX-ACCESS read-only
		STATUS current
		DESCRIPTION  "Total Success Response"
		::={ acosAamAuthenticationServerLdapS 14 }

		aamAuthServerLdapResponseFailure OBJECT-TYPE
		SYNTAX  CounterBasedGauge64
		MAX-ACCESS read-only
		STATUS current
		DESCRIPTION  "Total Failure Response"
		::={ acosAamAuthenticationServerLdapS 15 }

		aamAuthServerLdapResponseError OBJECT-TYPE
		SYNTAX  CounterBasedGauge64
		MAX-ACCESS read-only
		STATUS current
		DESCRIPTION  "Total Error Response"
		::={ acosAamAuthenticationServerLdapS 16 }

		aamAuthServerLdapResponseTimeout OBJECT-TYPE
		SYNTAX  CounterBasedGauge64
		MAX-ACCESS read-only
		STATUS current
		DESCRIPTION  "Total Timeout Response"
		::={ acosAamAuthenticationServerLdapS 17 }

		aamAuthServerLdapResponseOther OBJECT-TYPE
		SYNTAX  CounterBasedGauge64
		MAX-ACCESS read-only
		STATUS current
		DESCRIPTION  "Total Other Response"
		::={ acosAamAuthenticationServerLdapS 18 }

		aamAuthServerLdapJobStartError OBJECT-TYPE
		SYNTAX  CounterBasedGauge64
		MAX-ACCESS read-only
		STATUS current
		DESCRIPTION  "Total Job Start Error"
		::={ acosAamAuthenticationServerLdapS 19 }

		aamAuthServerLdapPollingControlError OBJECT-TYPE
		SYNTAX  CounterBasedGauge64
		MAX-ACCESS read-only
		STATUS current
		DESCRIPTION  "Total Polling Control Error"
		::={ acosAamAuthenticationServerLdapS 20 }

		sslSessionCreated OBJECT-TYPE
		SYNTAX  CounterBasedGauge64
		MAX-ACCESS read-only
		STATUS current
		DESCRIPTION  "TLS/SSL Session Created"
		::={ acosAamAuthenticationServerLdapS 21 }

		sslSessionFailure OBJECT-TYPE
		SYNTAX  CounterBasedGauge64
		MAX-ACCESS read-only
		STATUS current
		DESCRIPTION  "TLS/SSL Session Failure"
		::={ acosAamAuthenticationServerLdapS 22 }

		ldapsIdleConnNum OBJECT-TYPE
		SYNTAX  CounterBasedGauge64
		MAX-ACCESS read-only
		STATUS current
		DESCRIPTION  "LDAPS Idle Connection Number"
		::={ acosAamAuthenticationServerLdapS 23 }

		ldapsInuseConnNum OBJECT-TYPE
		SYNTAX  CounterBasedGauge64
		MAX-ACCESS read-only
		STATUS current
		DESCRIPTION  "LDAPS In-use Connection Number"
		::={ acosAamAuthenticationServerLdapS 24 }

		pwExpiry OBJECT-TYPE
		SYNTAX  CounterBasedGauge64
		MAX-ACCESS read-only
		STATUS current
		DESCRIPTION  "Total Password expiry"
		::={ acosAamAuthenticationServerLdapS 25 }

		pwChangeSuccess OBJECT-TYPE
		SYNTAX  CounterBasedGauge64
		MAX-ACCESS read-only
		STATUS current
		DESCRIPTION  "Total password change success"
		::={ acosAamAuthenticationServerLdapS 26 }

		pwChangeFailure OBJECT-TYPE
		SYNTAX  CounterBasedGauge64
		MAX-ACCESS read-only
		STATUS current
		DESCRIPTION  "Total password change failure"
		::={ acosAamAuthenticationServerLdapS 27 }

acosAamAuthServerLdap               OBJECT IDENTIFIER ::= { acosAamAuthenticationServerLdap 2 }
acosAamAuthServerLdapS              OBJECT IDENTIFIER ::= { acosAamAuthServerLdap 1 }

aamAuthServerLdapSTable OBJECT-TYPE
		SYNTAX SEQUENCE OF AamAuthServerLdapSEntry
		MAX-ACCESS not-accessible
		STATUS current
		::={ acosAamAuthServerLdapS 1 }


	aamAuthServerLdapSEntry OBJECT-TYPE
		SYNTAX AamAuthServerLdapSEntry
		MAX-ACCESS not-accessible
		STATUS current
		INDEX {
			name
		}
		::={ aamAuthServerLdapSTable 1 }


	AamAuthServerLdapSEntry ::=
		SEQUENCE {
			name DisplayString,
			adminBindSuccess CounterBasedGauge64,
			adminBindFailure CounterBasedGauge64,
			bindSuccess CounterBasedGauge64,
			bindFailure CounterBasedGauge64,
			searchSuccess CounterBasedGauge64,
			searchFailure CounterBasedGauge64,
			authorizeSuccess CounterBasedGauge64,
			authorizeFailure CounterBasedGauge64,
			aamAuthServerTimeoutError CounterBasedGauge64,
			aamAuthServerOtherError CounterBasedGauge64,
			request CounterBasedGauge64,
			sslSessionCreated CounterBasedGauge64,
			sslSessionFailure CounterBasedGauge64,
			pwExpiry CounterBasedGauge64,
			pwChangeSuccess CounterBasedGauge64,
			pwChangeFailure CounterBasedGauge64
		}

			name OBJECT-TYPE
			SYNTAX  DisplayString
			MAX-ACCESS read-only
			STATUS current
			DESCRIPTION  "Specify LDAP authentication server name"
			::={ aamAuthServerLdapSEntry 1 }

			adminBindSuccess OBJECT-TYPE
			SYNTAX  CounterBasedGauge64
			MAX-ACCESS read-only
			STATUS current
			DESCRIPTION  "Admin Bind Success"
			::={ aamAuthServerLdapSEntry 2 }

			adminBindFailure OBJECT-TYPE
			SYNTAX  CounterBasedGauge64
			MAX-ACCESS read-only
			STATUS current
			DESCRIPTION  "Admin Bind Failure"
			::={ aamAuthServerLdapSEntry 3 }

			bindSuccess OBJECT-TYPE
			SYNTAX  CounterBasedGauge64
			MAX-ACCESS read-only
			STATUS current
			DESCRIPTION  "User Bind Success"
			::={ aamAuthServerLdapSEntry 4 }

			bindFailure OBJECT-TYPE
			SYNTAX  CounterBasedGauge64
			MAX-ACCESS read-only
			STATUS current
			DESCRIPTION  "User Bind Failure"
			::={ aamAuthServerLdapSEntry 5 }

			searchSuccess OBJECT-TYPE
			SYNTAX  CounterBasedGauge64
			MAX-ACCESS read-only
			STATUS current
			DESCRIPTION  "Search Success"
			::={ aamAuthServerLdapSEntry 6 }

			searchFailure OBJECT-TYPE
			SYNTAX  CounterBasedGauge64
			MAX-ACCESS read-only
			STATUS current
			DESCRIPTION  "Search Failure"
			::={ aamAuthServerLdapSEntry 7 }

			authorizeSuccess OBJECT-TYPE
			SYNTAX  CounterBasedGauge64
			MAX-ACCESS read-only
			STATUS current
			DESCRIPTION  "Authorization Success"
			::={ aamAuthServerLdapSEntry 8 }

			authorizeFailure OBJECT-TYPE
			SYNTAX  CounterBasedGauge64
			MAX-ACCESS read-only
			STATUS current
			DESCRIPTION  "Authorization Failure"
			::={ aamAuthServerLdapSEntry 9 }

			aamAuthServerTimeoutError OBJECT-TYPE
			SYNTAX  CounterBasedGauge64
			MAX-ACCESS read-only
			STATUS current
			DESCRIPTION  "Timeout"
			::={ aamAuthServerLdapSEntry 10 }

			aamAuthServerOtherError OBJECT-TYPE
			SYNTAX  CounterBasedGauge64
			MAX-ACCESS read-only
			STATUS current
			DESCRIPTION  "Other Error"
			::={ aamAuthServerLdapSEntry 11 }

			request OBJECT-TYPE
			SYNTAX  CounterBasedGauge64
			MAX-ACCESS read-only
			STATUS current
			DESCRIPTION  "Request"
			::={ aamAuthServerLdapSEntry 12 }

			sslSessionCreated OBJECT-TYPE
			SYNTAX  CounterBasedGauge64
			MAX-ACCESS read-only
			STATUS current
			DESCRIPTION  "TLS/SSL Session Created"
			::={ aamAuthServerLdapSEntry 13 }

			sslSessionFailure OBJECT-TYPE
			SYNTAX  CounterBasedGauge64
			MAX-ACCESS read-only
			STATUS current
			DESCRIPTION  "TLS/SSL Session Failure"
			::={ aamAuthServerLdapSEntry 14 }

			pwExpiry OBJECT-TYPE
			SYNTAX  CounterBasedGauge64
			MAX-ACCESS read-only
			STATUS current
			DESCRIPTION  "Password expiry"
			::={ aamAuthServerLdapSEntry 15 }

			pwChangeSuccess OBJECT-TYPE
			SYNTAX  CounterBasedGauge64
			MAX-ACCESS read-only
			STATUS current
			DESCRIPTION  "Password change success"
			::={ aamAuthServerLdapSEntry 16 }

			pwChangeFailure OBJECT-TYPE
			SYNTAX  CounterBasedGauge64
			MAX-ACCESS read-only
			STATUS current
			DESCRIPTION  "Password change failure"
			::={ aamAuthServerLdapSEntry 17 }

acosAamAuthenticationServerOcsp     OBJECT IDENTIFIER ::= { acosAamAuthenticationServer 3 }
acosAamAuthenticationServerOcspS    OBJECT IDENTIFIER ::= { acosAamAuthenticationServerOcsp 1 }

		staplingCertificateGood OBJECT-TYPE
		SYNTAX  CounterBasedGauge64
		MAX-ACCESS read-only
		STATUS current
		DESCRIPTION  "Total OCSP Stapling Good Certificate Response"
		::={ acosAamAuthenticationServerOcspS 1 }

		staplingCertificateRevoked OBJECT-TYPE
		SYNTAX  CounterBasedGauge64
		MAX-ACCESS read-only
		STATUS current
		DESCRIPTION  "Total OCSP Stapling Revoked Certificate Response"
		::={ acosAamAuthenticationServerOcspS 2 }

		staplingCertificateUnknown OBJECT-TYPE
		SYNTAX  CounterBasedGauge64
		MAX-ACCESS read-only
		STATUS current
		DESCRIPTION  "Total OCSP Stapling Unknown Certificate Response"
		::={ acosAamAuthenticationServerOcspS 3 }

		staplingRequestNormal OBJECT-TYPE
		SYNTAX  CounterBasedGauge64
		MAX-ACCESS read-only
		STATUS current
		DESCRIPTION  "Total OSCP Stapling Normal Request"
		::={ acosAamAuthenticationServerOcspS 4 }

		staplingRequestDropped OBJECT-TYPE
		SYNTAX  CounterBasedGauge64
		MAX-ACCESS read-only
		STATUS current
		DESCRIPTION  "Total OCSP Stapling Dropped Request"
		::={ acosAamAuthenticationServerOcspS 5 }

		staplingResponseSuccess OBJECT-TYPE
		SYNTAX  CounterBasedGauge64
		MAX-ACCESS read-only
		STATUS current
		DESCRIPTION  "Total OCSP Stapling Success Response"
		::={ acosAamAuthenticationServerOcspS 6 }

		staplingResponseFailure OBJECT-TYPE
		SYNTAX  CounterBasedGauge64
		MAX-ACCESS read-only
		STATUS current
		DESCRIPTION  "Total OCSP Stapling Failure Response"
		::={ acosAamAuthenticationServerOcspS 7 }

		staplingResponseError OBJECT-TYPE
		SYNTAX  CounterBasedGauge64
		MAX-ACCESS read-only
		STATUS current
		DESCRIPTION  "Total OCSP Stapling Error Response"
		::={ acosAamAuthenticationServerOcspS 8 }

		staplingResponseTimeout OBJECT-TYPE
		SYNTAX  CounterBasedGauge64
		MAX-ACCESS read-only
		STATUS current
		DESCRIPTION  "Total OCSP Stapling Timeout Response"
		::={ acosAamAuthenticationServerOcspS 9 }

		staplingResponseOther OBJECT-TYPE
		SYNTAX  CounterBasedGauge64
		MAX-ACCESS read-only
		STATUS current
		DESCRIPTION  "Total OCSP Stapling Other Response"
		::={ acosAamAuthenticationServerOcspS 10 }

		aamAuthServerOcspRequestNormal OBJECT-TYPE
		SYNTAX  CounterBasedGauge64
		MAX-ACCESS read-only
		STATUS current
		DESCRIPTION  "Total OSCP Normal Request"
		::={ acosAamAuthenticationServerOcspS 11 }

		aamAuthServerOcspRequestDropped OBJECT-TYPE
		SYNTAX  CounterBasedGauge64
		MAX-ACCESS read-only
		STATUS current
		DESCRIPTION  "Total OCSP Dropped Request"
		::={ acosAamAuthenticationServerOcspS 12 }

		aamAuthServerOcspResponseSuccess OBJECT-TYPE
		SYNTAX  CounterBasedGauge64
		MAX-ACCESS read-only
		STATUS current
		DESCRIPTION  "Total OCSP Success Response"
		::={ acosAamAuthenticationServerOcspS 13 }

		aamAuthServerOcspResponseFailure OBJECT-TYPE
		SYNTAX  CounterBasedGauge64
		MAX-ACCESS read-only
		STATUS current
		DESCRIPTION  "Total OCSP Failure Response"
		::={ acosAamAuthenticationServerOcspS 14 }

		aamAuthServerOcspResponseError OBJECT-TYPE
		SYNTAX  CounterBasedGauge64
		MAX-ACCESS read-only
		STATUS current
		DESCRIPTION  "Total OCSP Error Response"
		::={ acosAamAuthenticationServerOcspS 15 }

		aamAuthServerOcspResponseTimeout OBJECT-TYPE
		SYNTAX  CounterBasedGauge64
		MAX-ACCESS read-only
		STATUS current
		DESCRIPTION  "Total OCSP Timeout Response"
		::={ acosAamAuthenticationServerOcspS 16 }

		aamAuthServerOcspResponseOther OBJECT-TYPE
		SYNTAX  CounterBasedGauge64
		MAX-ACCESS read-only
		STATUS current
		DESCRIPTION  "Total OCSP Other Response"
		::={ acosAamAuthenticationServerOcspS 17 }

		aamAuthServerOcspJobStartError OBJECT-TYPE
		SYNTAX  CounterBasedGauge64
		MAX-ACCESS read-only
		STATUS current
		DESCRIPTION  "Total OCSP Job Start Error"
		::={ acosAamAuthenticationServerOcspS 18 }

		aamAuthServerOcspPollingControlError OBJECT-TYPE
		SYNTAX  CounterBasedGauge64
		MAX-ACCESS read-only
		STATUS current
		DESCRIPTION  "Total OCSP Polling Control Error"
		::={ acosAamAuthenticationServerOcspS 19 }

acosAuthServerOcsp                  OBJECT IDENTIFIER ::= { acosAamAuthenticationServerOcsp 2 }
acosAuthServerOcspS                 OBJECT IDENTIFIER ::= { acosAuthServerOcsp 1 }

authServerOcspSTable OBJECT-TYPE
		SYNTAX SEQUENCE OF AuthServerOcspSEntry
		MAX-ACCESS not-accessible
		STATUS current
		::={ acosAuthServerOcspS 1 }


	authServerOcspSEntry OBJECT-TYPE
		SYNTAX AuthServerOcspSEntry
		MAX-ACCESS not-accessible
		STATUS current
		INDEX {
			aamAuthServerOcspName
		}
		::={ authServerOcspSTable 1 }


	AuthServerOcspSEntry ::=
		SEQUENCE {
			aamAuthServerOcspName DisplayString,
			request CounterBasedGauge64,
			certificateGood CounterBasedGauge64,
			certificateRevoked CounterBasedGauge64,
			certificateUnknown CounterBasedGauge64,
			timeout CounterBasedGauge64,
			fail CounterBasedGauge64,
			staplingRequest CounterBasedGauge64,
			staplingCertificateGood CounterBasedGauge64,
			staplingCertificateRevoked CounterBasedGauge64,
			staplingCertificateUnknown CounterBasedGauge64,
			staplingTimeout CounterBasedGauge64,
			staplingFail CounterBasedGauge64
		}

			aamAuthServerOcspName OBJECT-TYPE
			SYNTAX  DisplayString
			MAX-ACCESS read-only
			STATUS current
			DESCRIPTION  "Specify OCSP authentication server name"
			::={ authServerOcspSEntry 1 }

			request OBJECT-TYPE
			SYNTAX  CounterBasedGauge64
			MAX-ACCESS read-only
			STATUS current
			DESCRIPTION  "Request"
			::={ authServerOcspSEntry 2 }

			certificateGood OBJECT-TYPE
			SYNTAX  CounterBasedGauge64
			MAX-ACCESS read-only
			STATUS current
			DESCRIPTION  "Good Certificate Response"
			::={ authServerOcspSEntry 3 }

			certificateRevoked OBJECT-TYPE
			SYNTAX  CounterBasedGauge64
			MAX-ACCESS read-only
			STATUS current
			DESCRIPTION  "Revoked Certificate Response"
			::={ authServerOcspSEntry 4 }

			certificateUnknown OBJECT-TYPE
			SYNTAX  CounterBasedGauge64
			MAX-ACCESS read-only
			STATUS current
			DESCRIPTION  "Unknown Certificate Response"
			::={ authServerOcspSEntry 5 }

			timeout OBJECT-TYPE
			SYNTAX  CounterBasedGauge64
			MAX-ACCESS read-only
			STATUS current
			DESCRIPTION  "Timeout"
			::={ authServerOcspSEntry 6 }

			fail OBJECT-TYPE
			SYNTAX  CounterBasedGauge64
			MAX-ACCESS read-only
			STATUS current
			DESCRIPTION  "Handle OCSP response failed"
			::={ authServerOcspSEntry 7 }

			staplingRequest OBJECT-TYPE
			SYNTAX  CounterBasedGauge64
			MAX-ACCESS read-only
			STATUS current
			DESCRIPTION  "OCSP Stapling Request Send"
			::={ authServerOcspSEntry 8 }

			staplingCertificateGood OBJECT-TYPE
			SYNTAX  CounterBasedGauge64
			MAX-ACCESS read-only
			STATUS current
			DESCRIPTION  "OCSP Stapling Good Certificate Response"
			::={ authServerOcspSEntry 9 }

			staplingCertificateRevoked OBJECT-TYPE
			SYNTAX  CounterBasedGauge64
			MAX-ACCESS read-only
			STATUS current
			DESCRIPTION  "OCSP Stapling Revoked Certificate Response"
			::={ authServerOcspSEntry 10 }

			staplingCertificateUnknown OBJECT-TYPE
			SYNTAX  CounterBasedGauge64
			MAX-ACCESS read-only
			STATUS current
			DESCRIPTION  "OCSP Stapling Unknown Certificate Response"
			::={ authServerOcspSEntry 11 }

			staplingTimeout OBJECT-TYPE
			SYNTAX  CounterBasedGauge64
			MAX-ACCESS read-only
			STATUS current
			DESCRIPTION  "OCSP Stapling Timeout"
			::={ authServerOcspSEntry 12 }

			staplingFail OBJECT-TYPE
			SYNTAX  CounterBasedGauge64
			MAX-ACCESS read-only
			STATUS current
			DESCRIPTION  "Handle OCSP response failed"
			::={ authServerOcspSEntry 13 }

acosAamAuthenticationServerRadius   OBJECT IDENTIFIER ::= { acosAamAuthenticationServer 4 }
acosAamAuthenticationServerRadiusS  OBJECT IDENTIFIER ::= { acosAamAuthenticationServerRadius 1 }

		authenSuccess OBJECT-TYPE
		SYNTAX  CounterBasedGauge64
		MAX-ACCESS read-only
		STATUS current
		DESCRIPTION  "Total Authentication Success"
		::={ acosAamAuthenticationServerRadiusS 1 }

		authenFailure OBJECT-TYPE
		SYNTAX  CounterBasedGauge64
		MAX-ACCESS read-only
		STATUS current
		DESCRIPTION  "Total Authentication Failure"
		::={ acosAamAuthenticationServerRadiusS 2 }

		aamAuthServerRadiusAuthorizeSuccess OBJECT-TYPE
		SYNTAX  CounterBasedGauge64
		MAX-ACCESS read-only
		STATUS current
		DESCRIPTION  "Total Authorization Success"
		::={ acosAamAuthenticationServerRadiusS 3 }

		aamAuthServerRadiusAuthorizeFailure OBJECT-TYPE
		SYNTAX  CounterBasedGauge64
		MAX-ACCESS read-only
		STATUS current
		DESCRIPTION  "Total Authorization Failure"
		::={ acosAamAuthenticationServerRadiusS 4 }

		accessChallenge OBJECT-TYPE
		SYNTAX  CounterBasedGauge64
		MAX-ACCESS read-only
		STATUS current
		DESCRIPTION  "Total Access-Challenge Message Receive"
		::={ acosAamAuthenticationServerRadiusS 5 }

		aamAuthServerRadiusTimeoutError OBJECT-TYPE
		SYNTAX  CounterBasedGauge64
		MAX-ACCESS read-only
		STATUS current
		DESCRIPTION  "Total Timeout"
		::={ acosAamAuthenticationServerRadiusS 6 }

		aamAuthServerRadiusOtherError OBJECT-TYPE
		SYNTAX  CounterBasedGauge64
		MAX-ACCESS read-only
		STATUS current
		DESCRIPTION  "Total Other Error"
		::={ acosAamAuthenticationServerRadiusS 7 }

		aamAuthServerRadiusRequest OBJECT-TYPE
		SYNTAX  CounterBasedGauge64
		MAX-ACCESS read-only
		STATUS current
		DESCRIPTION  "Total Request"
		::={ acosAamAuthenticationServerRadiusS 8 }

		aamAuthServerRadiusRequestNormal OBJECT-TYPE
		SYNTAX  CounterBasedGauge64
		MAX-ACCESS read-only
		STATUS current
		DESCRIPTION  "Total Normal Request"
		::={ acosAamAuthenticationServerRadiusS 9 }

		aamAuthServerRadiusRequestDropped OBJECT-TYPE
		SYNTAX  CounterBasedGauge64
		MAX-ACCESS read-only
		STATUS current
		DESCRIPTION  "Total Dropped Request"
		::={ acosAamAuthenticationServerRadiusS 10 }

		aamAuthServerRadiusResponseSuccess OBJECT-TYPE
		SYNTAX  CounterBasedGauge64
		MAX-ACCESS read-only
		STATUS current
		DESCRIPTION  "Total Success Response"
		::={ acosAamAuthenticationServerRadiusS 11 }

		aamAuthServerRadiusResponseFailure OBJECT-TYPE
		SYNTAX  CounterBasedGauge64
		MAX-ACCESS read-only
		STATUS current
		DESCRIPTION  "Total Failure Response"
		::={ acosAamAuthenticationServerRadiusS 12 }

		aamAuthServerRadiusResponseError OBJECT-TYPE
		SYNTAX  CounterBasedGauge64
		MAX-ACCESS read-only
		STATUS current
		DESCRIPTION  "Total Error Response"
		::={ acosAamAuthenticationServerRadiusS 13 }

		aamAuthServerRadiusResponseTimeout OBJECT-TYPE
		SYNTAX  CounterBasedGauge64
		MAX-ACCESS read-only
		STATUS current
		DESCRIPTION  "Total Timeout Response"
		::={ acosAamAuthenticationServerRadiusS 14 }

		aamAuthServerRadiusResponseOther OBJECT-TYPE
		SYNTAX  CounterBasedGauge64
		MAX-ACCESS read-only
		STATUS current
		DESCRIPTION  "Total Other Response"
		::={ acosAamAuthenticationServerRadiusS 15 }

		aamAuthServerRadiusJobStartError OBJECT-TYPE
		SYNTAX  CounterBasedGauge64
		MAX-ACCESS read-only
		STATUS current
		DESCRIPTION  "Total Job Start Error"
		::={ acosAamAuthenticationServerRadiusS 16 }

		aamAuthServerRadiusPollingControlError OBJECT-TYPE
		SYNTAX  CounterBasedGauge64
		MAX-ACCESS read-only
		STATUS current
		DESCRIPTION  "Total Polling Control Error"
		::={ acosAamAuthenticationServerRadiusS 17 }

		accountingRequestSent OBJECT-TYPE
		SYNTAX  CounterBasedGauge64
		MAX-ACCESS read-only
		STATUS current
		DESCRIPTION  "Accounting-Request Sent"
		::={ acosAamAuthenticationServerRadiusS 18 }

		accountingSuccess OBJECT-TYPE
		SYNTAX  CounterBasedGauge64
		MAX-ACCESS read-only
		STATUS current
		DESCRIPTION  "Accounting Success"
		::={ acosAamAuthenticationServerRadiusS 19 }

		accountingFailure OBJECT-TYPE
		SYNTAX  CounterBasedGauge64
		MAX-ACCESS read-only
		STATUS current
		DESCRIPTION  "Accounting Failure"
		::={ acosAamAuthenticationServerRadiusS 20 }

acosAamAuthServerRadius             OBJECT IDENTIFIER ::= { acosAamAuthenticationServerRadius 2 }
acosAamAuthServerRadiusS            OBJECT IDENTIFIER ::= { acosAamAuthServerRadius 1 }

aamAuthServerRadiusSTable OBJECT-TYPE
		SYNTAX SEQUENCE OF AamAuthServerRadiusSEntry
		MAX-ACCESS not-accessible
		STATUS current
		::={ acosAamAuthServerRadiusS 1 }


	aamAuthServerRadiusSEntry OBJECT-TYPE
		SYNTAX AamAuthServerRadiusSEntry
		MAX-ACCESS not-accessible
		STATUS current
		INDEX {
			name
		}
		::={ aamAuthServerRadiusSTable 1 }


	AamAuthServerRadiusSEntry ::=
		SEQUENCE {
			name DisplayString,
			authenSuccess CounterBasedGauge64,
			authenFailure CounterBasedGauge64,
			authorizeSuccess CounterBasedGauge64,
			authorizeFailure CounterBasedGauge64,
			accessChallenge CounterBasedGauge64,
			timeoutError CounterBasedGauge64,
			otherError CounterBasedGauge64,
			request CounterBasedGauge64,
			accountingRequestSent CounterBasedGauge64,
			accountingSuccess CounterBasedGauge64,
			accountingFailure CounterBasedGauge64
		}

			name OBJECT-TYPE
			SYNTAX  DisplayString
			MAX-ACCESS read-only
			STATUS current
			DESCRIPTION  "Specify RADIUS authentication server name"
			::={ aamAuthServerRadiusSEntry 1 }

			authenSuccess OBJECT-TYPE
			SYNTAX  CounterBasedGauge64
			MAX-ACCESS read-only
			STATUS current
			DESCRIPTION  "Authentication Success"
			::={ aamAuthServerRadiusSEntry 2 }

			authenFailure OBJECT-TYPE
			SYNTAX  CounterBasedGauge64
			MAX-ACCESS read-only
			STATUS current
			DESCRIPTION  "Authentication Failure"
			::={ aamAuthServerRadiusSEntry 3 }

			authorizeSuccess OBJECT-TYPE
			SYNTAX  CounterBasedGauge64
			MAX-ACCESS read-only
			STATUS current
			DESCRIPTION  "Authorization Success"
			::={ aamAuthServerRadiusSEntry 4 }

			authorizeFailure OBJECT-TYPE
			SYNTAX  CounterBasedGauge64
			MAX-ACCESS read-only
			STATUS current
			DESCRIPTION  "Authorization Failure"
			::={ aamAuthServerRadiusSEntry 5 }

			accessChallenge OBJECT-TYPE
			SYNTAX  CounterBasedGauge64
			MAX-ACCESS read-only
			STATUS current
			DESCRIPTION  "Access-Challenge Message Receive"
			::={ aamAuthServerRadiusSEntry 6 }

			timeoutError OBJECT-TYPE
			SYNTAX  CounterBasedGauge64
			MAX-ACCESS read-only
			STATUS current
			DESCRIPTION  "Timeout"
			::={ aamAuthServerRadiusSEntry 7 }

			otherError OBJECT-TYPE
			SYNTAX  CounterBasedGauge64
			MAX-ACCESS read-only
			STATUS current
			DESCRIPTION  "Other Error"
			::={ aamAuthServerRadiusSEntry 8 }

			request OBJECT-TYPE
			SYNTAX  CounterBasedGauge64
			MAX-ACCESS read-only
			STATUS current
			DESCRIPTION  "Request"
			::={ aamAuthServerRadiusSEntry 9 }

			accountingRequestSent OBJECT-TYPE
			SYNTAX  CounterBasedGauge64
			MAX-ACCESS read-only
			STATUS current
			DESCRIPTION  "Accounting-Request Sent"
			::={ aamAuthServerRadiusSEntry 10 }

			accountingSuccess OBJECT-TYPE
			SYNTAX  CounterBasedGauge64
			MAX-ACCESS read-only
			STATUS current
			DESCRIPTION  "Accounting Success"
			::={ aamAuthServerRadiusSEntry 11 }

			accountingFailure OBJECT-TYPE
			SYNTAX  CounterBasedGauge64
			MAX-ACCESS read-only
			STATUS current
			DESCRIPTION  "Accounting Failure"
			::={ aamAuthServerRadiusSEntry 12 }

acosAamAuthenticationServerWindows  OBJECT IDENTIFIER ::= { acosAamAuthenticationServer 5 }
acosAamAuthenticationServerWindowsS OBJECT IDENTIFIER ::= { acosAamAuthenticationServerWindows 1 }

		kerberosRequestSend OBJECT-TYPE
		SYNTAX  CounterBasedGauge64
		MAX-ACCESS read-only
		STATUS current
		DESCRIPTION  "Total Kerberos Request"
		::={ acosAamAuthenticationServerWindowsS 1 }

		kerberosResponseGet OBJECT-TYPE
		SYNTAX  CounterBasedGauge64
		MAX-ACCESS read-only
		STATUS current
		DESCRIPTION  "Total Kerberos Response"
		::={ acosAamAuthenticationServerWindowsS 2 }

		kerberosTimeoutError OBJECT-TYPE
		SYNTAX  CounterBasedGauge64
		MAX-ACCESS read-only
		STATUS current
		DESCRIPTION  "Total Kerberos Timeout"
		::={ acosAamAuthenticationServerWindowsS 3 }

		kerberosOtherError OBJECT-TYPE
		SYNTAX  CounterBasedGauge64
		MAX-ACCESS read-only
		STATUS current
		DESCRIPTION  "Total Kerberos Other Error"
		::={ acosAamAuthenticationServerWindowsS 4 }

		ntlmAuthenticationSuccess OBJECT-TYPE
		SYNTAX  CounterBasedGauge64
		MAX-ACCESS read-only
		STATUS current
		DESCRIPTION  "Total NTLM Authentication Success"
		::={ acosAamAuthenticationServerWindowsS 5 }

		ntlmAuthenticationFailure OBJECT-TYPE
		SYNTAX  CounterBasedGauge64
		MAX-ACCESS read-only
		STATUS current
		DESCRIPTION  "Total NTLM Authentication Failure"
		::={ acosAamAuthenticationServerWindowsS 6 }

		ntlmProtoNegotiationSuccess OBJECT-TYPE
		SYNTAX  CounterBasedGauge64
		MAX-ACCESS read-only
		STATUS current
		DESCRIPTION  "Total NTLM Protocol Negotiation Success"
		::={ acosAamAuthenticationServerWindowsS 7 }

		ntlmProtoNegotiationFailure OBJECT-TYPE
		SYNTAX  CounterBasedGauge64
		MAX-ACCESS read-only
		STATUS current
		DESCRIPTION  "Total NTLM Protocol Negotiation Failure"
		::={ acosAamAuthenticationServerWindowsS 8 }

		ntlmSessionSetupSuccess OBJECT-TYPE
		SYNTAX  CounterBasedGauge64
		MAX-ACCESS read-only
		STATUS current
		DESCRIPTION  "Total NTLM Session Setup Success"
		::={ acosAamAuthenticationServerWindowsS 9 }

		ntlmSessionSetupFailed OBJECT-TYPE
		SYNTAX  CounterBasedGauge64
		MAX-ACCESS read-only
		STATUS current
		DESCRIPTION  "Total NTLM Session Setup Failure"
		::={ acosAamAuthenticationServerWindowsS 10 }

		kerberosRequestNormal OBJECT-TYPE
		SYNTAX  CounterBasedGauge64
		MAX-ACCESS read-only
		STATUS current
		DESCRIPTION  "Total Kerberos Normal Request"
		::={ acosAamAuthenticationServerWindowsS 11 }

		kerberosRequestDropped OBJECT-TYPE
		SYNTAX  CounterBasedGauge64
		MAX-ACCESS read-only
		STATUS current
		DESCRIPTION  "Total Kerberos Dropped Request"
		::={ acosAamAuthenticationServerWindowsS 12 }

		kerberosResponseSuccess OBJECT-TYPE
		SYNTAX  CounterBasedGauge64
		MAX-ACCESS read-only
		STATUS current
		DESCRIPTION  "Total Kerberos Success Response"
		::={ acosAamAuthenticationServerWindowsS 13 }

		kerberosResponseFailure OBJECT-TYPE
		SYNTAX  CounterBasedGauge64
		MAX-ACCESS read-only
		STATUS current
		DESCRIPTION  "Total Kerberos Failure Response"
		::={ acosAamAuthenticationServerWindowsS 14 }

		kerberosResponseError OBJECT-TYPE
		SYNTAX  CounterBasedGauge64
		MAX-ACCESS read-only
		STATUS current
		DESCRIPTION  "Total Kerberos Error Response"
		::={ acosAamAuthenticationServerWindowsS 15 }

		kerberosResponseTimeout OBJECT-TYPE
		SYNTAX  CounterBasedGauge64
		MAX-ACCESS read-only
		STATUS current
		DESCRIPTION  "Total Kerberos Timeout Response"
		::={ acosAamAuthenticationServerWindowsS 16 }

		kerberosResponseOther OBJECT-TYPE
		SYNTAX  CounterBasedGauge64
		MAX-ACCESS read-only
		STATUS current
		DESCRIPTION  "Total Kerberos Other Response"
		::={ acosAamAuthenticationServerWindowsS 17 }

		kerberosJobStartError OBJECT-TYPE
		SYNTAX  CounterBasedGauge64
		MAX-ACCESS read-only
		STATUS current
		DESCRIPTION  "Total Kerberos Job Start Error"
		::={ acosAamAuthenticationServerWindowsS 18 }

		kerberosPollingControlError OBJECT-TYPE
		SYNTAX  CounterBasedGauge64
		MAX-ACCESS read-only
		STATUS current
		DESCRIPTION  "Total Kerberos Polling Control Error"
		::={ acosAamAuthenticationServerWindowsS 19 }

		ntlmPrepareReqSuccess OBJECT-TYPE
		SYNTAX  CounterBasedGauge64
		MAX-ACCESS read-only
		STATUS current
		DESCRIPTION  "Total NTLM Prepare Request Success"
		::={ acosAamAuthenticationServerWindowsS 20 }

		ntlmPrepareReqFailed OBJECT-TYPE
		SYNTAX  CounterBasedGauge64
		MAX-ACCESS read-only
		STATUS current
		DESCRIPTION  "Total NTLM Prepare Request Failed"
		::={ acosAamAuthenticationServerWindowsS 21 }

		ntlmTimeoutError OBJECT-TYPE
		SYNTAX  CounterBasedGauge64
		MAX-ACCESS read-only
		STATUS current
		DESCRIPTION  "Total NTLM Timeout"
		::={ acosAamAuthenticationServerWindowsS 22 }

		ntlmOtherError OBJECT-TYPE
		SYNTAX  CounterBasedGauge64
		MAX-ACCESS read-only
		STATUS current
		DESCRIPTION  "Total NTLM Other Error"
		::={ acosAamAuthenticationServerWindowsS 23 }

		ntlmRequestNormal OBJECT-TYPE
		SYNTAX  CounterBasedGauge64
		MAX-ACCESS read-only
		STATUS current
		DESCRIPTION  "Total NTLM Normal Request"
		::={ acosAamAuthenticationServerWindowsS 24 }

		ntlmRequestDropped OBJECT-TYPE
		SYNTAX  CounterBasedGauge64
		MAX-ACCESS read-only
		STATUS current
		DESCRIPTION  "Total NTLM Dropped Request"
		::={ acosAamAuthenticationServerWindowsS 25 }

		ntlmResponseSuccess OBJECT-TYPE
		SYNTAX  CounterBasedGauge64
		MAX-ACCESS read-only
		STATUS current
		DESCRIPTION  "Total NTLM Success Response"
		::={ acosAamAuthenticationServerWindowsS 26 }

		ntlmResponseFailure OBJECT-TYPE
		SYNTAX  CounterBasedGauge64
		MAX-ACCESS read-only
		STATUS current
		DESCRIPTION  "Total NTLM Failure Response"
		::={ acosAamAuthenticationServerWindowsS 27 }

		ntlmResponseError OBJECT-TYPE
		SYNTAX  CounterBasedGauge64
		MAX-ACCESS read-only
		STATUS current
		DESCRIPTION  "Total NTLM Error Response"
		::={ acosAamAuthenticationServerWindowsS 28 }

		ntlmResponseTimeout OBJECT-TYPE
		SYNTAX  CounterBasedGauge64
		MAX-ACCESS read-only
		STATUS current
		DESCRIPTION  "Total NTLM Timeout Response"
		::={ acosAamAuthenticationServerWindowsS 29 }

		ntlmResponseOther OBJECT-TYPE
		SYNTAX  CounterBasedGauge64
		MAX-ACCESS read-only
		STATUS current
		DESCRIPTION  "Total NTLM Other Response"
		::={ acosAamAuthenticationServerWindowsS 30 }

		ntlmJobStartError OBJECT-TYPE
		SYNTAX  CounterBasedGauge64
		MAX-ACCESS read-only
		STATUS current
		DESCRIPTION  "Total NTLM Job Start Error"
		::={ acosAamAuthenticationServerWindowsS 31 }

		ntlmPollingControlError OBJECT-TYPE
		SYNTAX  CounterBasedGauge64
		MAX-ACCESS read-only
		STATUS current
		DESCRIPTION  "Total NTLM Polling Control Error"
		::={ acosAamAuthenticationServerWindowsS 32 }

		kerberosPwExpiry OBJECT-TYPE
		SYNTAX  CounterBasedGauge64
		MAX-ACCESS read-only
		STATUS current
		DESCRIPTION  "Total Kerberos password expiry"
		::={ acosAamAuthenticationServerWindowsS 33 }

		kerberosPwChangeSuccess OBJECT-TYPE
		SYNTAX  CounterBasedGauge64
		MAX-ACCESS read-only
		STATUS current
		DESCRIPTION  "Total Kerberos password change success"
		::={ acosAamAuthenticationServerWindowsS 34 }

		kerberosPwChangeFailure OBJECT-TYPE
		SYNTAX  CounterBasedGauge64
		MAX-ACCESS read-only
		STATUS current
		DESCRIPTION  "Total Kerberos password change failure"
		::={ acosAamAuthenticationServerWindowsS 35 }

		kerberosValidateKdcSuccess OBJECT-TYPE
		SYNTAX  CounterBasedGauge64
		MAX-ACCESS read-only
		STATUS current
		DESCRIPTION  "Total Kerberos KDC Validation Success"
		::={ acosAamAuthenticationServerWindowsS 36 }

		kerberosValidateKdcFailure OBJECT-TYPE
		SYNTAX  CounterBasedGauge64
		MAX-ACCESS read-only
		STATUS current
		DESCRIPTION  "Total Kerberos KDC Validation Failure"
		::={ acosAamAuthenticationServerWindowsS 37 }

		kerberosGenerateKdcKeytabSuccess OBJECT-TYPE
		SYNTAX  CounterBasedGauge64
		MAX-ACCESS read-only
		STATUS current
		DESCRIPTION  "Total Kerberos KDC Keytab Generation Success"
		::={ acosAamAuthenticationServerWindowsS 38 }

		kerberosGenerateKdcKeytabFailure OBJECT-TYPE
		SYNTAX  CounterBasedGauge64
		MAX-ACCESS read-only
		STATUS current
		DESCRIPTION  "Total Kerberos KDC Keytab Generation Failure"
		::={ acosAamAuthenticationServerWindowsS 39 }

		kerberosDeleteKdcKeytabSuccess OBJECT-TYPE
		SYNTAX  CounterBasedGauge64
		MAX-ACCESS read-only
		STATUS current
		DESCRIPTION  "Total Kerberos KDC Keytab Deletion Success"
		::={ acosAamAuthenticationServerWindowsS 40 }

		kerberosDeleteKdcKeytabFailure OBJECT-TYPE
		SYNTAX  CounterBasedGauge64
		MAX-ACCESS read-only
		STATUS current
		DESCRIPTION  "Total Kerberos KDC Keytab Deletion Failure"
		::={ acosAamAuthenticationServerWindowsS 41 }

		kerberosKdcKeytabCount OBJECT-TYPE
		SYNTAX  CounterBasedGauge64
		MAX-ACCESS read-only
		STATUS current
		DESCRIPTION  "Current Kerberos KDC Keytab Count"
		::={ acosAamAuthenticationServerWindowsS 42 }

acosAamAuthServerWindows            OBJECT IDENTIFIER ::= { acosAamAuthenticationServerWindows 2 }
acosAamAuthServerWindowsS           OBJECT IDENTIFIER ::= { acosAamAuthServerWindows 1 }

aamAuthServerWindowsSTable OBJECT-TYPE
		SYNTAX SEQUENCE OF AamAuthServerWindowsSEntry
		MAX-ACCESS not-accessible
		STATUS current
		::={ acosAamAuthServerWindowsS 1 }


	aamAuthServerWindowsSEntry OBJECT-TYPE
		SYNTAX AamAuthServerWindowsSEntry
		MAX-ACCESS not-accessible
		STATUS current
		INDEX {
			name
		}
		::={ aamAuthServerWindowsSTable 1 }


	AamAuthServerWindowsSEntry ::=
		SEQUENCE {
			name DisplayString,
			krbSendReqSuccess CounterBasedGauge64,
			krbGetRespSuccess CounterBasedGauge64,
			krbTimeoutError CounterBasedGauge64,
			krbOtherError CounterBasedGauge64,
			krbPwExpiry CounterBasedGauge64,
			krbPwChangeSuccess CounterBasedGauge64,
			krbPwChangeFailure CounterBasedGauge64,
			ntlmProtoNegoSuccess CounterBasedGauge64,
			ntlmProtoNegoFailure CounterBasedGauge64,
			ntlmSessionSetupSuccess CounterBasedGauge64,
			ntlmSessionSetupFailure CounterBasedGauge64,
			ntlmPrepareReqSuccess CounterBasedGauge64,
			ntlmPrepareReqError CounterBasedGauge64,
			ntlmAuthSuccess CounterBasedGauge64,
			ntlmAuthFailure CounterBasedGauge64,
			ntlmTimeoutError CounterBasedGauge64,
			ntlmOtherError CounterBasedGauge64,
			krbValidateKdcSuccess CounterBasedGauge64,
			krbValidateKdcFailure CounterBasedGauge64
		}

			name OBJECT-TYPE
			SYNTAX  DisplayString
			MAX-ACCESS read-only
			STATUS current
			DESCRIPTION  "Specify Windows authentication server name"
			::={ aamAuthServerWindowsSEntry 1 }

			krbSendReqSuccess OBJECT-TYPE
			SYNTAX  CounterBasedGauge64
			MAX-ACCESS read-only
			STATUS current
			DESCRIPTION  "Kerberos Request"
			::={ aamAuthServerWindowsSEntry 2 }

			krbGetRespSuccess OBJECT-TYPE
			SYNTAX  CounterBasedGauge64
			MAX-ACCESS read-only
			STATUS current
			DESCRIPTION  "Kerberos Response"
			::={ aamAuthServerWindowsSEntry 3 }

			krbTimeoutError OBJECT-TYPE
			SYNTAX  CounterBasedGauge64
			MAX-ACCESS read-only
			STATUS current
			DESCRIPTION  "Kerberos Timeout"
			::={ aamAuthServerWindowsSEntry 4 }

			krbOtherError OBJECT-TYPE
			SYNTAX  CounterBasedGauge64
			MAX-ACCESS read-only
			STATUS current
			DESCRIPTION  "Kerberos Other Error"
			::={ aamAuthServerWindowsSEntry 5 }

			krbPwExpiry OBJECT-TYPE
			SYNTAX  CounterBasedGauge64
			MAX-ACCESS read-only
			STATUS current
			DESCRIPTION  "Kerberos password expiry"
			::={ aamAuthServerWindowsSEntry 6 }

			krbPwChangeSuccess OBJECT-TYPE
			SYNTAX  CounterBasedGauge64
			MAX-ACCESS read-only
			STATUS current
			DESCRIPTION  "Kerberos password change success"
			::={ aamAuthServerWindowsSEntry 7 }

			krbPwChangeFailure OBJECT-TYPE
			SYNTAX  CounterBasedGauge64
			MAX-ACCESS read-only
			STATUS current
			DESCRIPTION  "Kerberos password change failure"
			::={ aamAuthServerWindowsSEntry 8 }

			ntlmProtoNegoSuccess OBJECT-TYPE
			SYNTAX  CounterBasedGauge64
			MAX-ACCESS read-only
			STATUS current
			DESCRIPTION  "NTLM Protocol Negotiation Success"
			::={ aamAuthServerWindowsSEntry 9 }

			ntlmProtoNegoFailure OBJECT-TYPE
			SYNTAX  CounterBasedGauge64
			MAX-ACCESS read-only
			STATUS current
			DESCRIPTION  "NTLM Protocol Negotiation Failure"
			::={ aamAuthServerWindowsSEntry 10 }

			ntlmSessionSetupSuccess OBJECT-TYPE
			SYNTAX  CounterBasedGauge64
			MAX-ACCESS read-only
			STATUS current
			DESCRIPTION  "NTLM Session Setup Success"
			::={ aamAuthServerWindowsSEntry 11 }

			ntlmSessionSetupFailure OBJECT-TYPE
			SYNTAX  CounterBasedGauge64
			MAX-ACCESS read-only
			STATUS current
			DESCRIPTION  "NTLM Session Setup Failure"
			::={ aamAuthServerWindowsSEntry 12 }

			ntlmPrepareReqSuccess OBJECT-TYPE
			SYNTAX  CounterBasedGauge64
			MAX-ACCESS read-only
			STATUS current
			DESCRIPTION  "NTLM Prepare Request Success"
			::={ aamAuthServerWindowsSEntry 13 }

			ntlmPrepareReqError OBJECT-TYPE
			SYNTAX  CounterBasedGauge64
			MAX-ACCESS read-only
			STATUS current
			DESCRIPTION  "NTLM Prepare Request Error"
			::={ aamAuthServerWindowsSEntry 14 }

			ntlmAuthSuccess OBJECT-TYPE
			SYNTAX  CounterBasedGauge64
			MAX-ACCESS read-only
			STATUS current
			DESCRIPTION  "NTLM Authentication Success"
			::={ aamAuthServerWindowsSEntry 15 }

			ntlmAuthFailure OBJECT-TYPE
			SYNTAX  CounterBasedGauge64
			MAX-ACCESS read-only
			STATUS current
			DESCRIPTION  "NTLM Authentication Failure"
			::={ aamAuthServerWindowsSEntry 16 }

			ntlmTimeoutError OBJECT-TYPE
			SYNTAX  CounterBasedGauge64
			MAX-ACCESS read-only
			STATUS current
			DESCRIPTION  "NTLM Timeout"
			::={ aamAuthServerWindowsSEntry 17 }

			ntlmOtherError OBJECT-TYPE
			SYNTAX  CounterBasedGauge64
			MAX-ACCESS read-only
			STATUS current
			DESCRIPTION  "NTLM Other Error"
			::={ aamAuthServerWindowsSEntry 18 }

			krbValidateKdcSuccess OBJECT-TYPE
			SYNTAX  CounterBasedGauge64
			MAX-ACCESS read-only
			STATUS current
			DESCRIPTION  "Kerberos KDC Validation Success"
			::={ aamAuthServerWindowsSEntry 19 }

			krbValidateKdcFailure OBJECT-TYPE
			SYNTAX  CounterBasedGauge64
			MAX-ACCESS read-only
			STATUS current
			DESCRIPTION  "Kerberos KDC Validation Failure"
			::={ aamAuthServerWindowsSEntry 20 }

acosAamAuthenticationAccount        OBJECT IDENTIFIER ::= { acosAamAuthentication 7 }
acosAamAuthenticationAccountS       OBJECT IDENTIFIER ::= { acosAamAuthenticationAccount 1 }

		aamAuthAccountRequestNormal OBJECT-TYPE
		SYNTAX  CounterBasedGauge64
		MAX-ACCESS read-only
		STATUS current
		DESCRIPTION  "Total Normal Request"
		::={ acosAamAuthenticationAccountS 1 }

		aamAuthAcountRequestDropped OBJECT-TYPE
		SYNTAX  CounterBasedGauge64
		MAX-ACCESS read-only
		STATUS current
		DESCRIPTION  "Total Dropped Request"
		::={ acosAamAuthenticationAccountS 2 }

		aamAuthAcountResponseSuccess OBJECT-TYPE
		SYNTAX  CounterBasedGauge64
		MAX-ACCESS read-only
		STATUS current
		DESCRIPTION  "Total Success Response"
		::={ acosAamAuthenticationAccountS 3 }

		aamAuthAcountResponseFailure OBJECT-TYPE
		SYNTAX  CounterBasedGauge64
		MAX-ACCESS read-only
		STATUS current
		DESCRIPTION  "Total Failure Response"
		::={ acosAamAuthenticationAccountS 4 }

		aamAuthAcountResponseError OBJECT-TYPE
		SYNTAX  CounterBasedGauge64
		MAX-ACCESS read-only
		STATUS current
		DESCRIPTION  "Total Error Response"
		::={ acosAamAuthenticationAccountS 5 }

		aamAuthAcountResponseTimeout OBJECT-TYPE
		SYNTAX  CounterBasedGauge64
		MAX-ACCESS read-only
		STATUS current
		DESCRIPTION  "Total Timeout Response"
		::={ acosAamAuthenticationAccountS 6 }

		aamAuthAcountResponseOther OBJECT-TYPE
		SYNTAX  CounterBasedGauge64
		MAX-ACCESS read-only
		STATUS current
		DESCRIPTION  "Total Other Response"
		::={ acosAamAuthenticationAccountS 7 }

acosAamAuthenticationSaml           OBJECT IDENTIFIER ::= { acosAamAuthentication 8 }
acosAamAuthenticationSamlGlobal     OBJECT IDENTIFIER ::= { acosAamAuthenticationSaml 1 }
acosAamAuthenticationSamlGlobalS    OBJECT IDENTIFIER ::= { acosAamAuthenticationSamlGlobal 1 }

		requestsToA10saml OBJECT-TYPE
		SYNTAX  CounterBasedGauge64
		MAX-ACCESS read-only
		STATUS current
		DESCRIPTION  "Total Request to A10 SAML Service"
		::={ acosAamAuthenticationSamlGlobalS 1 }

		responsesFromA10saml OBJECT-TYPE
		SYNTAX  CounterBasedGauge64
		MAX-ACCESS read-only
		STATUS current
		DESCRIPTION  "Total Response from A10 SAML Service"
		::={ acosAamAuthenticationSamlGlobalS 2 }

		aamAuthSamlGlobalSpMetadataExportReq OBJECT-TYPE
		SYNTAX  CounterBasedGauge64
		MAX-ACCESS read-only
		STATUS current
		DESCRIPTION  "Total Metadata Export Request"
		::={ acosAamAuthenticationSamlGlobalS 3 }

		aamAuthSamlGlobalSpMetadataExportSuccess OBJECT-TYPE
		SYNTAX  CounterBasedGauge64
		MAX-ACCESS read-only
		STATUS current
		DESCRIPTION  "Toal Metadata Export Success"
		::={ acosAamAuthenticationSamlGlobalS 4 }

		aamAuthSamlGlobalLoginAuthReq OBJECT-TYPE
		SYNTAX  CounterBasedGauge64
		MAX-ACCESS read-only
		STATUS current
		DESCRIPTION  "Total Login Authentication Request"
		::={ acosAamAuthenticationSamlGlobalS 5 }

		aamAuthSamlGlobalLoginAuthResp OBJECT-TYPE
		SYNTAX  CounterBasedGauge64
		MAX-ACCESS read-only
		STATUS current
		DESCRIPTION  "Total Login Authentication Response"
		::={ acosAamAuthenticationSamlGlobalS 6 }

		aamAuthSamlGlobalAcsReq OBJECT-TYPE
		SYNTAX  CounterBasedGauge64
		MAX-ACCESS read-only
		STATUS current
		DESCRIPTION  "Total SAML Single-Sign-On Request"
		::={ acosAamAuthenticationSamlGlobalS 7 }

		aamAuthSamlGlobalAcsSuccess OBJECT-TYPE
		SYNTAX  CounterBasedGauge64
		MAX-ACCESS read-only
		STATUS current
		DESCRIPTION  "Total SAML Single-Sign-On Success"
		::={ acosAamAuthenticationSamlGlobalS 8 }

		aamAuthSamlGlobalAcsAuthzFail OBJECT-TYPE
		SYNTAX  CounterBasedGauge64
		MAX-ACCESS read-only
		STATUS current
		DESCRIPTION  "Total SAML Single-Sign-On Authorization Fail"
		::={ acosAamAuthenticationSamlGlobalS 9 }

		aamAuthSamlGlobalAcsError OBJECT-TYPE
		SYNTAX  CounterBasedGauge64
		MAX-ACCESS read-only
		STATUS current
		DESCRIPTION  "Total SAML Single-Sign-On Error"
		::={ acosAamAuthenticationSamlGlobalS 10 }

		aamAuthSamlGlobalSloReq OBJECT-TYPE
		SYNTAX  CounterBasedGauge64
		MAX-ACCESS read-only
		STATUS current
		DESCRIPTION  "Total Single Logout Request"
		::={ acosAamAuthenticationSamlGlobalS 11 }

		aamAuthSamlGlobalSloSuccess OBJECT-TYPE
		SYNTAX  CounterBasedGauge64
		MAX-ACCESS read-only
		STATUS current
		DESCRIPTION  "Total Single Logout Success"
		::={ acosAamAuthenticationSamlGlobalS 12 }

		aamAuthSamlGlobalSloError OBJECT-TYPE
		SYNTAX  CounterBasedGauge64
		MAX-ACCESS read-only
		STATUS current
		DESCRIPTION  "Total Single Logout Error"
		::={ acosAamAuthenticationSamlGlobalS 13 }

		aamAuthSamlGlobalSpSloReq OBJECT-TYPE
		SYNTAX  CounterBasedGauge64
		MAX-ACCESS read-only
		STATUS current
		DESCRIPTION  "Total SP-initiated Single Logout Request"
		::={ acosAamAuthenticationSamlGlobalS 14 }

		aamAuthSamlGlobalGloSloSuccess OBJECT-TYPE
		SYNTAX  CounterBasedGauge64
		MAX-ACCESS read-only
		STATUS current
		DESCRIPTION  "Total Global Logout Success"
		::={ acosAamAuthenticationSamlGlobalS 15 }

		aamAuthSamlGlobalLocSloSuccess OBJECT-TYPE
		SYNTAX  CounterBasedGauge64
		MAX-ACCESS read-only
		STATUS current
		DESCRIPTION  "Total Local Logout Success"
		::={ acosAamAuthenticationSamlGlobalS 16 }

		aamAuthSamlGlobalParSloSuccess OBJECT-TYPE
		SYNTAX  CounterBasedGauge64
		MAX-ACCESS read-only
		STATUS current
		DESCRIPTION  "Total Partial Logout Success"
		::={ acosAamAuthenticationSamlGlobalS 17 }

		aamAuthSamlGlobalRelayRequest OBJECT-TYPE
		SYNTAX  CounterBasedGauge64
		MAX-ACCESS read-only
		STATUS current
		DESCRIPTION  "some help string"
		::={ acosAamAuthenticationSamlGlobalS 18 }

		aamAuthSamlGlobalRelaySuccess OBJECT-TYPE
		SYNTAX  CounterBasedGauge64
		MAX-ACCESS read-only
		STATUS current
		DESCRIPTION  "some help string"
		::={ acosAamAuthenticationSamlGlobalS 19 }

		aamAuthSamlGlobalRelayFailure OBJECT-TYPE
		SYNTAX  CounterBasedGauge64
		MAX-ACCESS read-only
		STATUS current
		DESCRIPTION  "some help string"
		::={ acosAamAuthenticationSamlGlobalS 20 }

		aamAuthSamlGlobalRelayError OBJECT-TYPE
		SYNTAX  CounterBasedGauge64
		MAX-ACCESS read-only
		STATUS current
		DESCRIPTION  "some help string"
		::={ acosAamAuthenticationSamlGlobalS 21 }

		aamAuthSamlOtherError OBJECT-TYPE
		SYNTAX  CounterBasedGauge64
		MAX-ACCESS read-only
		STATUS current
		DESCRIPTION  "Total Other Error"
		::={ acosAamAuthenticationSamlGlobalS 22 }

acosAamAuthenticationOauth          OBJECT IDENTIFIER ::= { acosAamAuthentication 17 }
acosAamAuthenticationOauthGlobal    OBJECT IDENTIFIER ::= { acosAamAuthenticationOauth 1 }
acosAamAuthenticationOauthGlobalS   OBJECT IDENTIFIER ::= { acosAamAuthenticationOauthGlobal 1 }

		authReq OBJECT-TYPE
		SYNTAX  CounterBasedGauge64
		MAX-ACCESS read-only
		STATUS current
		DESCRIPTION  "some help string"
		::={ acosAamAuthenticationOauthGlobalS 1 }

		authSucc OBJECT-TYPE
		SYNTAX  CounterBasedGauge64
		MAX-ACCESS read-only
		STATUS current
		DESCRIPTION  "some help string"
		::={ acosAamAuthenticationOauthGlobalS 2 }

		authFail OBJECT-TYPE
		SYNTAX  CounterBasedGauge64
		MAX-ACCESS read-only
		STATUS current
		DESCRIPTION  "some help string"
		::={ acosAamAuthenticationOauthGlobalS 3 }

		authError OBJECT-TYPE
		SYNTAX  CounterBasedGauge64
		MAX-ACCESS read-only
		STATUS current
		DESCRIPTION  "some help string"
		::={ acosAamAuthenticationOauthGlobalS 4 }

		relayReq OBJECT-TYPE
		SYNTAX  CounterBasedGauge64
		MAX-ACCESS read-only
		STATUS current
		DESCRIPTION  "some help string"
		::={ acosAamAuthenticationOauthGlobalS 5 }

		relaySucc OBJECT-TYPE
		SYNTAX  CounterBasedGauge64
		MAX-ACCESS read-only
		STATUS current
		DESCRIPTION  "some help string"
		::={ acosAamAuthenticationOauthGlobalS 6 }

		relayFail OBJECT-TYPE
		SYNTAX  CounterBasedGauge64
		MAX-ACCESS read-only
		STATUS current
		DESCRIPTION  "some help string"
		::={ acosAamAuthenticationOauthGlobalS 7 }

		otherError OBJECT-TYPE
		SYNTAX  CounterBasedGauge64
		MAX-ACCESS read-only
		STATUS current
		DESCRIPTION  "some help string"
		::={ acosAamAuthenticationOauthGlobalS 8 }

acosAamAuthenticationServiceGroup   OBJECT IDENTIFIER ::= { acosAamAuthentication 9 }
acosAamAuthenticationServiceGroupS  OBJECT IDENTIFIER ::= { acosAamAuthenticationServiceGroup 1 }

aamAuthenticationServiceGroupSTable OBJECT-TYPE
		SYNTAX SEQUENCE OF AamAuthenticationServiceGroupSEntry
		MAX-ACCESS not-accessible
		STATUS current
		::={ acosAamAuthenticationServiceGroupS 1 }


	aamAuthenticationServiceGroupSEntry OBJECT-TYPE
		SYNTAX AamAuthenticationServiceGroupSEntry
		MAX-ACCESS not-accessible
		STATUS current
		INDEX {
			name
		}
		::={ aamAuthenticationServiceGroupSTable 1 }


	AamAuthenticationServiceGroupSEntry ::=
		SEQUENCE {
			name DisplayString,
			serverSelectionFailDrop CounterBasedGauge64,
			serverSelectionFailReset CounterBasedGauge64,
			servicePeakConn CounterBasedGauge64,
			serviceHealthyHost CounterBasedGauge64,
			serviceUnhealthyHost CounterBasedGauge64,
			serviceReqCount CounterBasedGauge64,
			serviceRespCount CounterBasedGauge64,
			serviceResp2xx CounterBasedGauge64,
			serviceResp3xx CounterBasedGauge64,
			serviceResp4xx CounterBasedGauge64,
			serviceResp5xx CounterBasedGauge64,
			serviceCurrConnOverflow CounterBasedGauge64
		}

			name OBJECT-TYPE
			SYNTAX  DisplayString
			MAX-ACCESS read-only
			STATUS current
			DESCRIPTION  "Specify AAM service group name"
			::={ aamAuthenticationServiceGroupSEntry 1 }

			serverSelectionFailDrop OBJECT-TYPE
			SYNTAX  CounterBasedGauge64
			MAX-ACCESS read-only
			STATUS current
			DESCRIPTION  "Drops due to Service selection failure"
			::={ aamAuthenticationServiceGroupSEntry 2 }

			serverSelectionFailReset OBJECT-TYPE
			SYNTAX  CounterBasedGauge64
			MAX-ACCESS read-only
			STATUS current
			DESCRIPTION  "Resets sent out for Service selection failure"
			::={ aamAuthenticationServiceGroupSEntry 3 }

			servicePeakConn OBJECT-TYPE
			SYNTAX  CounterBasedGauge64
			MAX-ACCESS read-only
			STATUS current
			DESCRIPTION  "Peak connection count for the Service Group"
			::={ aamAuthenticationServiceGroupSEntry 4 }

			serviceHealthyHost OBJECT-TYPE
			SYNTAX  CounterBasedGauge64
			MAX-ACCESS read-only
			STATUS current
			DESCRIPTION  "Service Group healthy host count"
			::={ aamAuthenticationServiceGroupSEntry 5 }

			serviceUnhealthyHost OBJECT-TYPE
			SYNTAX  CounterBasedGauge64
			MAX-ACCESS read-only
			STATUS current
			DESCRIPTION  "Service Group unhealthy host count"
			::={ aamAuthenticationServiceGroupSEntry 6 }

			serviceReqCount OBJECT-TYPE
			SYNTAX  CounterBasedGauge64
			MAX-ACCESS read-only
			STATUS current
			DESCRIPTION  "Service Group request count"
			::={ aamAuthenticationServiceGroupSEntry 7 }

			serviceRespCount OBJECT-TYPE
			SYNTAX  CounterBasedGauge64
			MAX-ACCESS read-only
			STATUS current
			DESCRIPTION  "Service Group response count"
			::={ aamAuthenticationServiceGroupSEntry 8 }

			serviceResp2xx OBJECT-TYPE
			SYNTAX  CounterBasedGauge64
			MAX-ACCESS read-only
			STATUS current
			DESCRIPTION  "Service Group response 2xx count"
			::={ aamAuthenticationServiceGroupSEntry 9 }

			serviceResp3xx OBJECT-TYPE
			SYNTAX  CounterBasedGauge64
			MAX-ACCESS read-only
			STATUS current
			DESCRIPTION  "Service Group response 3xx count"
			::={ aamAuthenticationServiceGroupSEntry 10 }

			serviceResp4xx OBJECT-TYPE
			SYNTAX  CounterBasedGauge64
			MAX-ACCESS read-only
			STATUS current
			DESCRIPTION  "Service Group response 4xx count"
			::={ aamAuthenticationServiceGroupSEntry 11 }

			serviceResp5xx OBJECT-TYPE
			SYNTAX  CounterBasedGauge64
			MAX-ACCESS read-only
			STATUS current
			DESCRIPTION  "Service Group response 5xx count"
			::={ aamAuthenticationServiceGroupSEntry 12 }

			serviceCurrConnOverflow OBJECT-TYPE
			SYNTAX  CounterBasedGauge64
			MAX-ACCESS read-only
			STATUS current
			DESCRIPTION  "Current connection counter overflow count"
			::={ aamAuthenticationServiceGroupSEntry 13 }

acosAamAuthenticationRelay          OBJECT IDENTIFIER ::= { acosAamAuthentication 10 }
acosAamAuthenticationRelayKerberos  OBJECT IDENTIFIER ::= { acosAamAuthenticationRelay 2 }
acosAamAuthenticationRelayKerberosS OBJECT IDENTIFIER ::= { acosAamAuthenticationRelayKerberos 1 }

		requestSend OBJECT-TYPE
		SYNTAX  CounterBasedGauge64
		MAX-ACCESS read-only
		STATUS current
		DESCRIPTION  "Total Request Send"
		::={ acosAamAuthenticationRelayKerberosS 1 }

		responseGet OBJECT-TYPE
		SYNTAX  CounterBasedGauge64
		MAX-ACCESS read-only
		STATUS current
		DESCRIPTION  "Total Response Get"
		::={ acosAamAuthenticationRelayKerberosS 2 }

		timeoutError OBJECT-TYPE
		SYNTAX  CounterBasedGauge64
		MAX-ACCESS read-only
		STATUS current
		DESCRIPTION  "Total Timeout"
		::={ acosAamAuthenticationRelayKerberosS 3 }

		otherError OBJECT-TYPE
		SYNTAX  CounterBasedGauge64
		MAX-ACCESS read-only
		STATUS current
		DESCRIPTION  "Total Other Error"
		::={ acosAamAuthenticationRelayKerberosS 4 }

		requestNormal OBJECT-TYPE
		SYNTAX  CounterBasedGauge64
		MAX-ACCESS read-only
		STATUS current
		DESCRIPTION  "Total Normal Request"
		::={ acosAamAuthenticationRelayKerberosS 5 }

		requestDropped OBJECT-TYPE
		SYNTAX  CounterBasedGauge64
		MAX-ACCESS read-only
		STATUS current
		DESCRIPTION  "Total Dropped Request"
		::={ acosAamAuthenticationRelayKerberosS 6 }

		responseSuccess OBJECT-TYPE
		SYNTAX  CounterBasedGauge64
		MAX-ACCESS read-only
		STATUS current
		DESCRIPTION  "Total Success Response"
		::={ acosAamAuthenticationRelayKerberosS 7 }

		responseFailure OBJECT-TYPE
		SYNTAX  CounterBasedGauge64
		MAX-ACCESS read-only
		STATUS current
		DESCRIPTION  "Total Failure Response"
		::={ acosAamAuthenticationRelayKerberosS 8 }

		responseError OBJECT-TYPE
		SYNTAX  CounterBasedGauge64
		MAX-ACCESS read-only
		STATUS current
		DESCRIPTION  "Total Error Response"
		::={ acosAamAuthenticationRelayKerberosS 9 }

		responseTimeout OBJECT-TYPE
		SYNTAX  CounterBasedGauge64
		MAX-ACCESS read-only
		STATUS current
		DESCRIPTION  "Total Timeout Response"
		::={ acosAamAuthenticationRelayKerberosS 10 }

		responseOther OBJECT-TYPE
		SYNTAX  CounterBasedGauge64
		MAX-ACCESS read-only
		STATUS current
		DESCRIPTION  "Total Other Response"
		::={ acosAamAuthenticationRelayKerberosS 11 }

		jobStartError OBJECT-TYPE
		SYNTAX  CounterBasedGauge64
		MAX-ACCESS read-only
		STATUS current
		DESCRIPTION  "Total Job Start Error"
		::={ acosAamAuthenticationRelayKerberosS 12 }

		pollingControlError OBJECT-TYPE
		SYNTAX  CounterBasedGauge64
		MAX-ACCESS read-only
		STATUS current
		DESCRIPTION  "Total Polling Control Error"
		::={ acosAamAuthenticationRelayKerberosS 13 }

acosAamAuthRelayKerberos            OBJECT IDENTIFIER ::= { acosAamAuthenticationRelayKerberos 2 }
acosAamAuthRelayKerberosS           OBJECT IDENTIFIER ::= { acosAamAuthRelayKerberos 1 }

aamAuthRelayKerberosSTable OBJECT-TYPE
		SYNTAX SEQUENCE OF AamAuthRelayKerberosSEntry
		MAX-ACCESS not-accessible
		STATUS current
		::={ acosAamAuthRelayKerberosS 1 }


	aamAuthRelayKerberosSEntry OBJECT-TYPE
		SYNTAX AamAuthRelayKerberosSEntry
		MAX-ACCESS not-accessible
		STATUS current
		INDEX {
			name
		}
		::={ aamAuthRelayKerberosSTable 1 }


	AamAuthRelayKerberosSEntry ::=
		SEQUENCE {
			name DisplayString,
			requestSend CounterBasedGauge64,
			responseReceive CounterBasedGauge64,
			currentRequestsOfUser CounterBasedGauge64,
			tickets CounterBasedGauge64
		}

			name OBJECT-TYPE
			SYNTAX  DisplayString
			MAX-ACCESS read-only
			STATUS current
			DESCRIPTION  "Specify Kerberos authentication relay name"
			::={ aamAuthRelayKerberosSEntry 1 }

			requestSend OBJECT-TYPE
			SYNTAX  CounterBasedGauge64
			MAX-ACCESS read-only
			STATUS current
			DESCRIPTION  "Request Send"
			::={ aamAuthRelayKerberosSEntry 2 }

			responseReceive OBJECT-TYPE
			SYNTAX  CounterBasedGauge64
			MAX-ACCESS read-only
			STATUS current
			DESCRIPTION  "Response Receive"
			::={ aamAuthRelayKerberosSEntry 3 }

			currentRequestsOfUser OBJECT-TYPE
			SYNTAX  CounterBasedGauge64
			MAX-ACCESS read-only
			STATUS current
			DESCRIPTION  "Current Pending Requests of User"
			::={ aamAuthRelayKerberosSEntry 4 }

			tickets OBJECT-TYPE
			SYNTAX  CounterBasedGauge64
			MAX-ACCESS read-only
			STATUS current
			DESCRIPTION  "Tickets"
			::={ aamAuthRelayKerberosSEntry 5 }

acosAamAuthenticationRelayNtlm      OBJECT IDENTIFIER ::= { acosAamAuthenticationRelay 4 }
acosAamAuthenticationRelayNtlmS     OBJECT IDENTIFIER ::= { acosAamAuthenticationRelayNtlm 1 }

aamAuthenticationRelayNtlmSTable OBJECT-TYPE
		SYNTAX SEQUENCE OF AamAuthenticationRelayNtlmSEntry
		MAX-ACCESS not-accessible
		STATUS current
		::={ acosAamAuthenticationRelayNtlmS 1 }


	aamAuthenticationRelayNtlmSEntry OBJECT-TYPE
		SYNTAX AamAuthenticationRelayNtlmSEntry
		MAX-ACCESS not-accessible
		STATUS current
		INDEX {
			aamAuthRelayNtlmName
		}
		::={ aamAuthenticationRelayNtlmSTable 1 }


	AamAuthenticationRelayNtlmSEntry ::=
		SEQUENCE {
			aamAuthRelayNtlmName DisplayString,
			success CounterBasedGauge64,
			failure CounterBasedGauge64,
			aamAuthRelayNtlmRequest CounterBasedGauge64,
			response CounterBasedGauge64,
			httpCode200 CounterBasedGauge64,
			httpCode400 CounterBasedGauge64,
			httpCode401 CounterBasedGauge64,
			httpCode403 CounterBasedGauge64,
			httpCode404 CounterBasedGauge64,
			httpCode500 CounterBasedGauge64,
			httpCode503 CounterBasedGauge64,
			httpCodeOther CounterBasedGauge64,
			bufferAllocFail CounterBasedGauge64,
			encodingFail CounterBasedGauge64,
			insertHeaderFail CounterBasedGauge64,
			parseHeaderFail CounterBasedGauge64,
			internalError CounterBasedGauge64,
			ntlmAuthSkipped CounterBasedGauge64,
			largeRequestProcessing CounterBasedGauge64,
			largeRequestFlushed CounterBasedGauge64,
			headNegotiateRequestSent CounterBasedGauge64,
			headAuthRequestSent CounterBasedGauge64
		}

			aamAuthRelayNtlmName OBJECT-TYPE
			SYNTAX  DisplayString
			MAX-ACCESS read-only
			STATUS current
			DESCRIPTION  "Specify NTLM authentication relay name"
			::={ aamAuthenticationRelayNtlmSEntry 1 }

			success OBJECT-TYPE
			SYNTAX  CounterBasedGauge64
			MAX-ACCESS read-only
			STATUS current
			DESCRIPTION  "Success"
			::={ aamAuthenticationRelayNtlmSEntry 2 }

			failure OBJECT-TYPE
			SYNTAX  CounterBasedGauge64
			MAX-ACCESS read-only
			STATUS current
			DESCRIPTION  "Failure"
			::={ aamAuthenticationRelayNtlmSEntry 3 }

			aamAuthRelayNtlmRequest OBJECT-TYPE
			SYNTAX  CounterBasedGauge64
			MAX-ACCESS read-only
			STATUS current
			DESCRIPTION  "Request"
			::={ aamAuthenticationRelayNtlmSEntry 4 }

			response OBJECT-TYPE
			SYNTAX  CounterBasedGauge64
			MAX-ACCESS read-only
			STATUS current
			DESCRIPTION  "Response"
			::={ aamAuthenticationRelayNtlmSEntry 5 }

			httpCode200 OBJECT-TYPE
			SYNTAX  CounterBasedGauge64
			MAX-ACCESS read-only
			STATUS current
			DESCRIPTION  "HTTP 200 OK"
			::={ aamAuthenticationRelayNtlmSEntry 6 }

			httpCode400 OBJECT-TYPE
			SYNTAX  CounterBasedGauge64
			MAX-ACCESS read-only
			STATUS current
			DESCRIPTION  "HTTP 400 Bad Request"
			::={ aamAuthenticationRelayNtlmSEntry 7 }

			httpCode401 OBJECT-TYPE
			SYNTAX  CounterBasedGauge64
			MAX-ACCESS read-only
			STATUS current
			DESCRIPTION  "HTTP 401 Unauthorized"
			::={ aamAuthenticationRelayNtlmSEntry 8 }

			httpCode403 OBJECT-TYPE
			SYNTAX  CounterBasedGauge64
			MAX-ACCESS read-only
			STATUS current
			DESCRIPTION  "HTTP 403 Forbidden"
			::={ aamAuthenticationRelayNtlmSEntry 9 }

			httpCode404 OBJECT-TYPE
			SYNTAX  CounterBasedGauge64
			MAX-ACCESS read-only
			STATUS current
			DESCRIPTION  "HTTP 404 Not Found"
			::={ aamAuthenticationRelayNtlmSEntry 10 }

			httpCode500 OBJECT-TYPE
			SYNTAX  CounterBasedGauge64
			MAX-ACCESS read-only
			STATUS current
			DESCRIPTION  "HTTP 500 Internal Server Error"
			::={ aamAuthenticationRelayNtlmSEntry 11 }

			httpCode503 OBJECT-TYPE
			SYNTAX  CounterBasedGauge64
			MAX-ACCESS read-only
			STATUS current
			DESCRIPTION  "HTTP 503 Service Unavailable"
			::={ aamAuthenticationRelayNtlmSEntry 12 }

			httpCodeOther OBJECT-TYPE
			SYNTAX  CounterBasedGauge64
			MAX-ACCESS read-only
			STATUS current
			DESCRIPTION  "Other HTTP Response"
			::={ aamAuthenticationRelayNtlmSEntry 13 }

			bufferAllocFail OBJECT-TYPE
			SYNTAX  CounterBasedGauge64
			MAX-ACCESS read-only
			STATUS current
			DESCRIPTION  "Buffer Allocation Failure"
			::={ aamAuthenticationRelayNtlmSEntry 14 }

			encodingFail OBJECT-TYPE
			SYNTAX  CounterBasedGauge64
			MAX-ACCESS read-only
			STATUS current
			DESCRIPTION  "Encoding Failure"
			::={ aamAuthenticationRelayNtlmSEntry 15 }

			insertHeaderFail OBJECT-TYPE
			SYNTAX  CounterBasedGauge64
			MAX-ACCESS read-only
			STATUS current
			DESCRIPTION  "Insert Header Failure"
			::={ aamAuthenticationRelayNtlmSEntry 16 }

			parseHeaderFail OBJECT-TYPE
			SYNTAX  CounterBasedGauge64
			MAX-ACCESS read-only
			STATUS current
			DESCRIPTION  "Parse Header Failure"
			::={ aamAuthenticationRelayNtlmSEntry 17 }

			internalError OBJECT-TYPE
			SYNTAX  CounterBasedGauge64
			MAX-ACCESS read-only
			STATUS current
			DESCRIPTION  "Internal Error"
			::={ aamAuthenticationRelayNtlmSEntry 18 }

			ntlmAuthSkipped OBJECT-TYPE
			SYNTAX  CounterBasedGauge64
			MAX-ACCESS read-only
			STATUS current
			DESCRIPTION  "Requests for which NTLM relay is skipped"
			::={ aamAuthenticationRelayNtlmSEntry 19 }

			largeRequestProcessing OBJECT-TYPE
			SYNTAX  CounterBasedGauge64
			MAX-ACCESS read-only
			STATUS current
			DESCRIPTION  "Requests invoking large request processing"
			::={ aamAuthenticationRelayNtlmSEntry 20 }

			largeRequestFlushed OBJECT-TYPE
			SYNTAX  CounterBasedGauge64
			MAX-ACCESS read-only
			STATUS current
			DESCRIPTION  "Large requests sent to server"
			::={ aamAuthenticationRelayNtlmSEntry 21 }

			headNegotiateRequestSent OBJECT-TYPE
			SYNTAX  CounterBasedGauge64
			MAX-ACCESS read-only
			STATUS current
			DESCRIPTION  "HEAD requests sent with NEGOTIATE header"
			::={ aamAuthenticationRelayNtlmSEntry 22 }

			headAuthRequestSent OBJECT-TYPE
			SYNTAX  CounterBasedGauge64
			MAX-ACCESS read-only
			STATUS current
			DESCRIPTION  "HEAD requests sent with AUTH header"
			::={ aamAuthenticationRelayNtlmSEntry 23 }

acosAamAuthenticationRelaySaml      OBJECT IDENTIFIER ::= { acosAamAuthenticationRelay 6 }
acosAamAuthenticationRelaySamlS     OBJECT IDENTIFIER ::= { acosAamAuthenticationRelaySaml 1 }

aamAuthenticationRelaySamlSTable OBJECT-TYPE
		SYNTAX SEQUENCE OF AamAuthenticationRelaySamlSEntry
		MAX-ACCESS not-accessible
		STATUS current
		::={ acosAamAuthenticationRelaySamlS 1 }


	aamAuthenticationRelaySamlSEntry OBJECT-TYPE
		SYNTAX AamAuthenticationRelaySamlSEntry
		MAX-ACCESS not-accessible
		STATUS current
		INDEX {
			aamAuthRelaySAMLName
		}
		::={ aamAuthenticationRelaySamlSTable 1 }


	AamAuthenticationRelaySamlSEntry ::=
		SEQUENCE {
			aamAuthRelaySAMLName DisplayString,
			aamAuthRelaySamlRequest CounterBasedGauge64,
			aamAuthRelaySamlSuccess CounterBasedGauge64,
			aamAuthRelaySamlFailure CounterBasedGauge64,
			aamAuthRelaySamlError CounterBasedGauge64
		}

			aamAuthRelaySAMLName OBJECT-TYPE
			SYNTAX  DisplayString
			MAX-ACCESS read-only
			STATUS current
			DESCRIPTION  "Specify SAML authentication relay name"
			::={ aamAuthenticationRelaySamlSEntry 1 }

			aamAuthRelaySamlRequest OBJECT-TYPE
			SYNTAX  CounterBasedGauge64
			MAX-ACCESS read-only
			STATUS current
			DESCRIPTION  "Request"
			::={ aamAuthenticationRelaySamlSEntry 2 }

			aamAuthRelaySamlSuccess OBJECT-TYPE
			SYNTAX  CounterBasedGauge64
			MAX-ACCESS read-only
			STATUS current
			DESCRIPTION  "Success"
			::={ aamAuthenticationRelaySamlSEntry 3 }

			aamAuthRelaySamlFailure OBJECT-TYPE
			SYNTAX  CounterBasedGauge64
			MAX-ACCESS read-only
			STATUS current
			DESCRIPTION  "Failure"
			::={ aamAuthenticationRelaySamlSEntry 4 }

			aamAuthRelaySamlError OBJECT-TYPE
			SYNTAX  CounterBasedGauge64
			MAX-ACCESS read-only
			STATUS current
			DESCRIPTION  "Error"
			::={ aamAuthenticationRelaySamlSEntry 5 }

acosAamAuthenticationRelayOauth     OBJECT IDENTIFIER ::= { acosAamAuthenticationRelay 7 }
acosAamAuthenticationRelayOauthS    OBJECT IDENTIFIER ::= { acosAamAuthenticationRelayOauth 1 }

aamAuthenticationRelayOauthSTable OBJECT-TYPE
		SYNTAX SEQUENCE OF AamAuthenticationRelayOauthSEntry
		MAX-ACCESS not-accessible
		STATUS current
		::={ acosAamAuthenticationRelayOauthS 1 }


	aamAuthenticationRelayOauthSEntry OBJECT-TYPE
		SYNTAX AamAuthenticationRelayOauthSEntry
		MAX-ACCESS not-accessible
		STATUS current
		INDEX {
			name
		}
		::={ aamAuthenticationRelayOauthSTable 1 }


	AamAuthenticationRelayOauthSEntry ::=
		SEQUENCE {
			name DisplayString,
			relayReq CounterBasedGauge64,
			relaySucc CounterBasedGauge64,
			relayFail CounterBasedGauge64
		}

			name OBJECT-TYPE
			SYNTAX  DisplayString
			MAX-ACCESS read-only
			STATUS current
			DESCRIPTION  "Specify oauth authentication relay name"
			::={ aamAuthenticationRelayOauthSEntry 1 }

			relayReq OBJECT-TYPE
			SYNTAX  CounterBasedGauge64
			MAX-ACCESS read-only
			STATUS current
			DESCRIPTION  "some help string"
			::={ aamAuthenticationRelayOauthSEntry 2 }

			relaySucc OBJECT-TYPE
			SYNTAX  CounterBasedGauge64
			MAX-ACCESS read-only
			STATUS current
			DESCRIPTION  "some help string"
			::={ aamAuthenticationRelayOauthSEntry 3 }

			relayFail OBJECT-TYPE
			SYNTAX  CounterBasedGauge64
			MAX-ACCESS read-only
			STATUS current
			DESCRIPTION  "some help string"
			::={ aamAuthenticationRelayOauthSEntry 4 }

acosAamAuthenticationCaptcha        OBJECT IDENTIFIER ::= { acosAamAuthentication 18 }
acosAamAuthenticationCaptchaS       OBJECT IDENTIFIER ::= { acosAamAuthenticationCaptcha 1 }

		requestNormal OBJECT-TYPE
		SYNTAX  CounterBasedGauge64
		MAX-ACCESS read-only
		STATUS current
		DESCRIPTION  "Total Normal Request"
		::={ acosAamAuthenticationCaptchaS 1 }

		requestDropped OBJECT-TYPE
		SYNTAX  CounterBasedGauge64
		MAX-ACCESS read-only
		STATUS current
		DESCRIPTION  "Total Dropped Request"
		::={ acosAamAuthenticationCaptchaS 2 }

		responseSuccess OBJECT-TYPE
		SYNTAX  CounterBasedGauge64
		MAX-ACCESS read-only
		STATUS current
		DESCRIPTION  "Total Success Response"
		::={ acosAamAuthenticationCaptchaS 3 }

		responseFailure OBJECT-TYPE
		SYNTAX  CounterBasedGauge64
		MAX-ACCESS read-only
		STATUS current
		DESCRIPTION  "Total Failure Response"
		::={ acosAamAuthenticationCaptchaS 4 }

		responseError OBJECT-TYPE
		SYNTAX  CounterBasedGauge64
		MAX-ACCESS read-only
		STATUS current
		DESCRIPTION  "Total Error Response"
		::={ acosAamAuthenticationCaptchaS 5 }

		responseTimeout OBJECT-TYPE
		SYNTAX  CounterBasedGauge64
		MAX-ACCESS read-only
		STATUS current
		DESCRIPTION  "Total Timeout Response"
		::={ acosAamAuthenticationCaptchaS 6 }

		responseOther OBJECT-TYPE
		SYNTAX  CounterBasedGauge64
		MAX-ACCESS read-only
		STATUS current
		DESCRIPTION  "Total Other Response"
		::={ acosAamAuthenticationCaptchaS 7 }

		request OBJECT-TYPE
		SYNTAX  CounterBasedGauge64
		MAX-ACCESS read-only
		STATUS current
		DESCRIPTION  "Total Request"
		::={ acosAamAuthenticationCaptchaS 8 }

		verifySucc OBJECT-TYPE
		SYNTAX  CounterBasedGauge64
		MAX-ACCESS read-only
		STATUS current
		DESCRIPTION  "Total Verification Success Response"
		::={ acosAamAuthenticationCaptchaS 9 }

		parseFail OBJECT-TYPE
		SYNTAX  CounterBasedGauge64
		MAX-ACCESS read-only
		STATUS current
		DESCRIPTION  "Total JSON Response Parse Failure"
		::={ acosAamAuthenticationCaptchaS 10 }

		jsonFail OBJECT-TYPE
		SYNTAX  CounterBasedGauge64
		MAX-ACCESS read-only
		STATUS current
		DESCRIPTION  "Total Failure JSON Response"
		::={ acosAamAuthenticationCaptchaS 11 }

		attrFail OBJECT-TYPE
		SYNTAX  CounterBasedGauge64
		MAX-ACCESS read-only
		STATUS current
		DESCRIPTION  "Total Attribute Check Failure"
		::={ acosAamAuthenticationCaptchaS 12 }

		timeoutError OBJECT-TYPE
		SYNTAX  CounterBasedGauge64
		MAX-ACCESS read-only
		STATUS current
		DESCRIPTION  "Total Timeout"
		::={ acosAamAuthenticationCaptchaS 13 }

		otherError OBJECT-TYPE
		SYNTAX  CounterBasedGauge64
		MAX-ACCESS read-only
		STATUS current
		DESCRIPTION  "Total Other Error"
		::={ acosAamAuthenticationCaptchaS 14 }

		jobStartError OBJECT-TYPE
		SYNTAX  CounterBasedGauge64
		MAX-ACCESS read-only
		STATUS current
		DESCRIPTION  "Total Job Start Error"
		::={ acosAamAuthenticationCaptchaS 15 }

		pollingControlError OBJECT-TYPE
		SYNTAX  CounterBasedGauge64
		MAX-ACCESS read-only
		STATUS current
		DESCRIPTION  "Total Polling Control Error"
		::={ acosAamAuthenticationCaptchaS 16 }

acosAamJwtAuthorization             OBJECT IDENTIFIER ::= { acosAam 8 }
acosAamJwtAuthorizationS            OBJECT IDENTIFIER ::= { acosAamJwtAuthorization 1 }

aamJwtAuthorizationSTable OBJECT-TYPE
		SYNTAX SEQUENCE OF AamJwtAuthorizationSEntry
		MAX-ACCESS not-accessible
		STATUS current
		::={ acosAamJwtAuthorizationS 1 }


	aamJwtAuthorizationSEntry OBJECT-TYPE
		SYNTAX AamJwtAuthorizationSEntry
		MAX-ACCESS not-accessible
		STATUS current
		INDEX {
			name
		}
		::={ aamJwtAuthorizationSTable 1 }


	AamJwtAuthorizationSEntry ::=
		SEQUENCE {
			name DisplayString,
			jwtRequest CounterBasedGauge64,
			jwtAuthorizeSuccess CounterBasedGauge64,
			jwtAuthorizeFailure CounterBasedGauge64,
			jwtMissingToken CounterBasedGauge64,
			jwtMissingClaim CounterBasedGauge64,
			jwtTokenExpired CounterBasedGauge64,
			jwtSignatureFailure CounterBasedGauge64,
			jwtOtherError CounterBasedGauge64
		}

			name OBJECT-TYPE
			SYNTAX  DisplayString
			MAX-ACCESS read-only
			STATUS current
			DESCRIPTION  "Specify JWT authorization template name"
			::={ aamJwtAuthorizationSEntry 1 }

			jwtRequest OBJECT-TYPE
			SYNTAX  CounterBasedGauge64
			MAX-ACCESS read-only
			STATUS current
			DESCRIPTION  "JWT Request"
			::={ aamJwtAuthorizationSEntry 2 }

			jwtAuthorizeSuccess OBJECT-TYPE
			SYNTAX  CounterBasedGauge64
			MAX-ACCESS read-only
			STATUS current
			DESCRIPTION  "JWT Authorize Success"
			::={ aamJwtAuthorizationSEntry 3 }

			jwtAuthorizeFailure OBJECT-TYPE
			SYNTAX  CounterBasedGauge64
			MAX-ACCESS read-only
			STATUS current
			DESCRIPTION  "JWT Authorize Failure"
			::={ aamJwtAuthorizationSEntry 4 }

			jwtMissingToken OBJECT-TYPE
			SYNTAX  CounterBasedGauge64
			MAX-ACCESS read-only
			STATUS current
			DESCRIPTION  "JWT Missing Token"
			::={ aamJwtAuthorizationSEntry 5 }

			jwtMissingClaim OBJECT-TYPE
			SYNTAX  CounterBasedGauge64
			MAX-ACCESS read-only
			STATUS current
			DESCRIPTION  "JWT Missing Claim"
			::={ aamJwtAuthorizationSEntry 6 }

			jwtTokenExpired OBJECT-TYPE
			SYNTAX  CounterBasedGauge64
			MAX-ACCESS read-only
			STATUS current
			DESCRIPTION  "JWT Token Expired"
			::={ aamJwtAuthorizationSEntry 7 }

			jwtSignatureFailure OBJECT-TYPE
			SYNTAX  CounterBasedGauge64
			MAX-ACCESS read-only
			STATUS current
			DESCRIPTION  "JWT Signature Failure"
			::={ aamJwtAuthorizationSEntry 8 }

			jwtOtherError OBJECT-TYPE
			SYNTAX  CounterBasedGauge64
			MAX-ACCESS read-only
			STATUS current
			DESCRIPTION  "JWT Other Error"
			::={ aamJwtAuthorizationSEntry 9 }

acosAamAaaPolicy                    OBJECT IDENTIFIER ::= { acosAam 3 }
acosAamAaaPolicyS                   OBJECT IDENTIFIER ::= { acosAamAaaPolicy 1 }

aamAaaPolicySTable OBJECT-TYPE
		SYNTAX SEQUENCE OF AamAaaPolicySEntry
		MAX-ACCESS not-accessible
		STATUS current
		::={ acosAamAaaPolicyS 1 }


	aamAaaPolicySEntry OBJECT-TYPE
		SYNTAX AamAaaPolicySEntry
		MAX-ACCESS not-accessible
		STATUS current
		INDEX {
			aamAaaPolicyName
		}
		::={ aamAaaPolicySTable 1 }


	AamAaaPolicySEntry ::=
		SEQUENCE {
			aamAaaPolicyName DisplayString,
			req CounterBasedGauge64,
			reqReject CounterBasedGauge64,
			reqAuth CounterBasedGauge64,
			reqBypass CounterBasedGauge64,
			reqSkip CounterBasedGauge64,
			error CounterBasedGauge64,
			failureBypass CounterBasedGauge64
		}

			aamAaaPolicyName OBJECT-TYPE
			SYNTAX  DisplayString
			MAX-ACCESS read-only
			STATUS current
			DESCRIPTION  "Specify AAA policy name"
			::={ aamAaaPolicySEntry 1 }

			req OBJECT-TYPE
			SYNTAX  CounterBasedGauge64
			MAX-ACCESS read-only
			STATUS current
			DESCRIPTION  "Request"
			::={ aamAaaPolicySEntry 2 }

			reqReject OBJECT-TYPE
			SYNTAX  CounterBasedGauge64
			MAX-ACCESS read-only
			STATUS current
			DESCRIPTION  "Request Rejected"
			::={ aamAaaPolicySEntry 3 }

			reqAuth OBJECT-TYPE
			SYNTAX  CounterBasedGauge64
			MAX-ACCESS read-only
			STATUS current
			DESCRIPTION  "Request Matching Authentication Template"
			::={ aamAaaPolicySEntry 4 }

			reqBypass OBJECT-TYPE
			SYNTAX  CounterBasedGauge64
			MAX-ACCESS read-only
			STATUS current
			DESCRIPTION  "Request Bypassed"
			::={ aamAaaPolicySEntry 5 }

			reqSkip OBJECT-TYPE
			SYNTAX  CounterBasedGauge64
			MAX-ACCESS read-only
			STATUS current
			DESCRIPTION  "Request Skipped"
			::={ aamAaaPolicySEntry 6 }

			error OBJECT-TYPE
			SYNTAX  CounterBasedGauge64
			MAX-ACCESS read-only
			STATUS current
			DESCRIPTION  "Error"
			::={ aamAaaPolicySEntry 7 }

			failureBypass OBJECT-TYPE
			SYNTAX  CounterBasedGauge64
			MAX-ACCESS read-only
			STATUS current
			DESCRIPTION  "Auth Failure Bypass"
			::={ aamAaaPolicySEntry 8 }

END
