ACOS-ACOS-EVENTS-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosAcosEvents MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "AcosEvents OID for ACOS"
				::=  {  acosRootStats 104  }

acosAcosEventsLocalLogging          OBJECT IDENTIFIER ::= { acosAcosEvents 14 }
acosAcosEventsLocalLoggingS         OBJECT IDENTIFIER ::= { acosAcosEventsLocalLogging 1 }

		initPass OBJECT-TYPE
		SYNTAX  CounterBasedGauge64
		MAX-ACCESS read-only
		STATUS current
		DESCRIPTION  "Local logging Init Successful"
		::={ acosAcosEventsLocalLoggingS 1 }

		initFail OBJECT-TYPE
		SYNTAX  CounterBasedGauge64
		MAX-ACCESS read-only
		STATUS current
		DESCRIPTION  "Local logging Init Fail"
		::={ acosAcosEventsLocalLoggingS 2 }

		freed OBJECT-TYPE
		SYNTAX  CounterBasedGauge64
		MAX-ACCESS read-only
		STATUS current
		DESCRIPTION  "Local logging Stopped"
		::={ acosAcosEventsLocalLoggingS 3 }

		diskOverThres OBJECT-TYPE
		SYNTAX  CounterBasedGauge64
		MAX-ACCESS read-only
		STATUS current
		DESCRIPTION  "Number of logs Dropped, Disk reached threshold"
		::={ acosAcosEventsLocalLoggingS 4 }

		rateLimited OBJECT-TYPE
		SYNTAX  CounterBasedGauge64
		MAX-ACCESS read-only
		STATUS current
		DESCRIPTION  "Number of logs Dropped, Rate limited"
		::={ acosAcosEventsLocalLoggingS 5 }

		notInited OBJECT-TYPE
		SYNTAX  CounterBasedGauge64
		MAX-ACCESS read-only
		STATUS current
		DESCRIPTION  "Number of logs Dropped, Local logging not inited"
		::={ acosAcosEventsLocalLoggingS 6 }

		sentToStore OBJECT-TYPE
		SYNTAX  CounterBasedGauge64
		MAX-ACCESS read-only
		STATUS current
		DESCRIPTION  "Number of logs sent to be stored"
		::={ acosAcosEventsLocalLoggingS 7 }

		sentToStoreFail OBJECT-TYPE
		SYNTAX  CounterBasedGauge64
		MAX-ACCESS read-only
		STATUS current
		DESCRIPTION  "Number of Logs sent to be stored Failed"
		::={ acosAcosEventsLocalLoggingS 8 }

		storeFail OBJECT-TYPE
		SYNTAX  CounterBasedGauge64
		MAX-ACCESS read-only
		STATUS current
		DESCRIPTION  "Number of logs failed to be stored"
		::={ acosAcosEventsLocalLoggingS 9 }

		inLogs OBJECT-TYPE
		SYNTAX  CounterBasedGauge64
		MAX-ACCESS read-only
		STATUS current
		DESCRIPTION  "Number of logs successfully stored"
		::={ acosAcosEventsLocalLoggingS 10 }

		inBytes OBJECT-TYPE
		SYNTAX  CounterBasedGauge64
		MAX-ACCESS read-only
		STATUS current
		DESCRIPTION  "Number of bytes successfully stored"
		::={ acosAcosEventsLocalLoggingS 11 }

		inLogsBacklog OBJECT-TYPE
		SYNTAX  CounterBasedGauge64
		MAX-ACCESS read-only
		STATUS current
		DESCRIPTION  "Number of backlogs loaded from disk"
		::={ acosAcosEventsLocalLoggingS 12 }

		inBytesBacklog OBJECT-TYPE
		SYNTAX  CounterBasedGauge64
		MAX-ACCESS read-only
		STATUS current
		DESCRIPTION  "Number of backlog bytes loaded from disk"
		::={ acosAcosEventsLocalLoggingS 13 }

		inStoreFailNoSpace OBJECT-TYPE
		SYNTAX  CounterBasedGauge64
		MAX-ACCESS read-only
		STATUS current
		DESCRIPTION  "Number of logs Dropped, failed without disk space"
		::={ acosAcosEventsLocalLoggingS 14 }

		inDiscardLogs OBJECT-TYPE
		SYNTAX  CounterBasedGauge64
		MAX-ACCESS read-only
		STATUS current
		DESCRIPTION  "Number of old logs discarded to fit in new logs"
		::={ acosAcosEventsLocalLoggingS 15 }

		inDiscardBytes OBJECT-TYPE
		SYNTAX  CounterBasedGauge64
		MAX-ACCESS read-only
		STATUS current
		DESCRIPTION  "Number of old bytes discarded to fit in new logs"
		::={ acosAcosEventsLocalLoggingS 16 }

		outLogs OBJECT-TYPE
		SYNTAX  CounterBasedGauge64
		MAX-ACCESS read-only
		STATUS current
		DESCRIPTION  "Number of logs sent to log servers"
		::={ acosAcosEventsLocalLoggingS 17 }

		outBytes OBJECT-TYPE
		SYNTAX  CounterBasedGauge64
		MAX-ACCESS read-only
		STATUS current
		DESCRIPTION  "Number of bytes sent to log-servers"
		::={ acosAcosEventsLocalLoggingS 18 }

		outError OBJECT-TYPE
		SYNTAX  CounterBasedGauge64
		MAX-ACCESS read-only
		STATUS current
		DESCRIPTION  "Number of errors during send"
		::={ acosAcosEventsLocalLoggingS 19 }

		remainingLogs OBJECT-TYPE
		SYNTAX  CounterBasedGauge64
		MAX-ACCESS read-only
		STATUS current
		DESCRIPTION  "Total number of remaining logs yet to be sent"
		::={ acosAcosEventsLocalLoggingS 20 }

		remainingBytes OBJECT-TYPE
		SYNTAX  CounterBasedGauge64
		MAX-ACCESS read-only
		STATUS current
		DESCRIPTION  "Total number of remaining bytes yet to be sent"
		::={ acosAcosEventsLocalLoggingS 21 }

		movedToDelq OBJECT-TYPE
		SYNTAX  CounterBasedGauge64
		MAX-ACCESS read-only
		STATUS current
		DESCRIPTION  "Local Logging moved to delq to be deleted"
		::={ acosAcosEventsLocalLoggingS 22 }

		outRetry OBJECT-TYPE
		SYNTAX  CounterBasedGauge64
		MAX-ACCESS read-only
		STATUS current
		DESCRIPTION  "Number of attempted retries to send logs"
		::={ acosAcosEventsLocalLoggingS 23 }

		outRetryFail OBJECT-TYPE
		SYNTAX  CounterBasedGauge64
		MAX-ACCESS read-only
		STATUS current
		DESCRIPTION  "Number of retries failed with error"
		::={ acosAcosEventsLocalLoggingS 24 }

		currTotalChunks OBJECT-TYPE
		SYNTAX  CounterBasedGauge64
		MAX-ACCESS read-only
		STATUS current
		DESCRIPTION  "Current Number of blocks"
		::={ acosAcosEventsLocalLoggingS 25 }

		currMemChunks OBJECT-TYPE
		SYNTAX  CounterBasedGauge64
		MAX-ACCESS read-only
		STATUS current
		DESCRIPTION  "Current blocks in memory"
		::={ acosAcosEventsLocalLoggingS 26 }

		currFsChunks OBJECT-TYPE
		SYNTAX  CounterBasedGauge64
		MAX-ACCESS read-only
		STATUS current
		DESCRIPTION  "Current blocks in file system"
		::={ acosAcosEventsLocalLoggingS 27 }

		currFsChunksUp OBJECT-TYPE
		SYNTAX  CounterBasedGauge64
		MAX-ACCESS read-only
		STATUS current
		DESCRIPTION  "Current blocks in file system loaded in memory"
		::={ acosAcosEventsLocalLoggingS 28 }

		currFsChunksDown OBJECT-TYPE
		SYNTAX  CounterBasedGauge64
		MAX-ACCESS read-only
		STATUS current
		DESCRIPTION  "Current blocks in file system not loaded in memory"
		::={ acosAcosEventsLocalLoggingS 29 }

		inLogsAgg OBJECT-TYPE
		SYNTAX  CounterBasedGauge64
		MAX-ACCESS read-only
		STATUS current
		DESCRIPTION  "Total Aggregate, Number of logs successfully stored"
		::={ acosAcosEventsLocalLoggingS 30 }

		inBytesAgg OBJECT-TYPE
		SYNTAX  CounterBasedGauge64
		MAX-ACCESS read-only
		STATUS current
		DESCRIPTION  "Total Aggregate, Number of bytes successfully stored"
		::={ acosAcosEventsLocalLoggingS 31 }

		inLogsBacklogAgg OBJECT-TYPE
		SYNTAX  CounterBasedGauge64
		MAX-ACCESS read-only
		STATUS current
		DESCRIPTION  "Total Aggregate, Number of backlogs loaded from disk"
		::={ acosAcosEventsLocalLoggingS 32 }

		inBytesBacklogAgg OBJECT-TYPE
		SYNTAX  CounterBasedGauge64
		MAX-ACCESS read-only
		STATUS current
		DESCRIPTION  "Total Aggregate, Number of backlog bytes loaded from disk"
		::={ acosAcosEventsLocalLoggingS 33 }

		inStoreFailNoSpaceAgg OBJECT-TYPE
		SYNTAX  CounterBasedGauge64
		MAX-ACCESS read-only
		STATUS current
		DESCRIPTION  "Total Aggregate, Number of logs Dropped, failed without disk space"
		::={ acosAcosEventsLocalLoggingS 34 }

		inDiscardLogsAgg OBJECT-TYPE
		SYNTAX  CounterBasedGauge64
		MAX-ACCESS read-only
		STATUS current
		DESCRIPTION  "Total Aggregate, Number of old logs discarded to fit in new logs"
		::={ acosAcosEventsLocalLoggingS 35 }

		inDiscardBytesAgg OBJECT-TYPE
		SYNTAX  CounterBasedGauge64
		MAX-ACCESS read-only
		STATUS current
		DESCRIPTION  "Total Aggregate, Number of old bytes discarded to fit in new logs"
		::={ acosAcosEventsLocalLoggingS 36 }

		outLogsAgg OBJECT-TYPE
		SYNTAX  CounterBasedGauge64
		MAX-ACCESS read-only
		STATUS current
		DESCRIPTION  "Total Aggregate, Number of logs sent to log servers"
		::={ acosAcosEventsLocalLoggingS 37 }

		outBytesAgg OBJECT-TYPE
		SYNTAX  CounterBasedGauge64
		MAX-ACCESS read-only
		STATUS current
		DESCRIPTION  "Total Aggregate, Number of bytes sent to log-servers"
		::={ acosAcosEventsLocalLoggingS 38 }

		outErrorAgg OBJECT-TYPE
		SYNTAX  CounterBasedGauge64
		MAX-ACCESS read-only
		STATUS current
		DESCRIPTION  "Total Aggregate, Number of errors during send"
		::={ acosAcosEventsLocalLoggingS 39 }

		outRetryAgg OBJECT-TYPE
		SYNTAX  CounterBasedGauge64
		MAX-ACCESS read-only
		STATUS current
		DESCRIPTION  "Total Aggregate, Number of attempted retries to send logs"
		::={ acosAcosEventsLocalLoggingS 40 }

		outRetryFailAgg OBJECT-TYPE
		SYNTAX  CounterBasedGauge64
		MAX-ACCESS read-only
		STATUS current
		DESCRIPTION  "Total Aggregate, Number of retries failed with error"
		::={ acosAcosEventsLocalLoggingS 41 }

		inLogsCurrAgg OBJECT-TYPE
		SYNTAX  CounterBasedGauge64
		MAX-ACCESS read-only
		STATUS current
		DESCRIPTION  "Current Aggregate, Number of logs successfully stored"
		::={ acosAcosEventsLocalLoggingS 42 }

		inBytesCurrAgg OBJECT-TYPE
		SYNTAX  CounterBasedGauge64
		MAX-ACCESS read-only
		STATUS current
		DESCRIPTION  "Current Aggregate, Number of bytes successfully stored"
		::={ acosAcosEventsLocalLoggingS 43 }

		inLogsBacklogCurrAgg OBJECT-TYPE
		SYNTAX  CounterBasedGauge64
		MAX-ACCESS read-only
		STATUS current
		DESCRIPTION  "Current Aggregate, Number of backlogs loaded from disk"
		::={ acosAcosEventsLocalLoggingS 44 }

		inBytesBacklogCurrAgg OBJECT-TYPE
		SYNTAX  CounterBasedGauge64
		MAX-ACCESS read-only
		STATUS current
		DESCRIPTION  "Current Aggregate, Number of backlog bytes loaded from disk"
		::={ acosAcosEventsLocalLoggingS 45 }

		inDiscardLogsCurrAgg OBJECT-TYPE
		SYNTAX  CounterBasedGauge64
		MAX-ACCESS read-only
		STATUS current
		DESCRIPTION  "Current Aggregate, Number of old logs discarded to fit in new logs"
		::={ acosAcosEventsLocalLoggingS 46 }

		inDiscardBytesCurrAgg OBJECT-TYPE
		SYNTAX  CounterBasedGauge64
		MAX-ACCESS read-only
		STATUS current
		DESCRIPTION  "Current Aggregate, Number of old bytes discarded to fit in new logs"
		::={ acosAcosEventsLocalLoggingS 47 }

		outLogsCurrAgg OBJECT-TYPE
		SYNTAX  CounterBasedGauge64
		MAX-ACCESS read-only
		STATUS current
		DESCRIPTION  "Current Aggregate, Number of logs sent to log servers"
		::={ acosAcosEventsLocalLoggingS 48 }

		outBytesCurrAgg OBJECT-TYPE
		SYNTAX  CounterBasedGauge64
		MAX-ACCESS read-only
		STATUS current
		DESCRIPTION  "Current Aggregate, Number of bytes sent to log-servers"
		::={ acosAcosEventsLocalLoggingS 49 }

acosAcosEventsLogServer             OBJECT IDENTIFIER ::= { acosAcosEvents 3 }
acosAcosEventsLogServerS            OBJECT IDENTIFIER ::= { acosAcosEventsLogServer 1 }

acosEventsLogServerSTable OBJECT-TYPE
		SYNTAX SEQUENCE OF AcosEventsLogServerSEntry
		MAX-ACCESS not-accessible
		STATUS current
		::={ acosAcosEventsLogServerS 1 }


	acosEventsLogServerSEntry OBJECT-TYPE
		SYNTAX AcosEventsLogServerSEntry
		MAX-ACCESS not-accessible
		STATUS current
		INDEX {
			name
		}
		::={ acosEventsLogServerSTable 1 }


	AcosEventsLogServerSEntry ::=
		SEQUENCE {
			name DisplayString,
			msgsSent CounterBasedGauge64
		}

			name OBJECT-TYPE
			SYNTAX  DisplayString
			MAX-ACCESS read-only
			STATUS current
			DESCRIPTION  "Server Name"
			::={ acosEventsLogServerSEntry 1 }

			msgsSent OBJECT-TYPE
			SYNTAX  CounterBasedGauge64
			MAX-ACCESS read-only
			STATUS current
			DESCRIPTION  "Number of log messages sent"
			::={ acosEventsLogServerSEntry 2 }

acosAcosEventsCollectorGroup        OBJECT IDENTIFIER ::= { acosAcosEvents 4 }
acosAcosEventsCollectorGroupS       OBJECT IDENTIFIER ::= { acosAcosEventsCollectorGroup 1 }

acosEventsCollectorGroupSTable OBJECT-TYPE
		SYNTAX SEQUENCE OF AcosEventsCollectorGroupSEntry
		MAX-ACCESS not-accessible
		STATUS current
		::={ acosAcosEventsCollectorGroupS 1 }


	acosEventsCollectorGroupSEntry OBJECT-TYPE
		SYNTAX AcosEventsCollectorGroupSEntry
		MAX-ACCESS not-accessible
		STATUS current
		INDEX {
			name
		}
		::={ acosEventsCollectorGroupSTable 1 }


	AcosEventsCollectorGroupSEntry ::=
		SEQUENCE {
			name DisplayString,
			msgsSent CounterBasedGauge64,
			msgsRateLimited CounterBasedGauge64,
			msgsDropped CounterBasedGauge64
		}

			name OBJECT-TYPE
			SYNTAX  DisplayString
			MAX-ACCESS read-only
			STATUS current
			DESCRIPTION  "Specify log server group name"
			::={ acosEventsCollectorGroupSEntry 1 }

			msgsSent OBJECT-TYPE
			SYNTAX  CounterBasedGauge64
			MAX-ACCESS read-only
			STATUS current
			DESCRIPTION  "Number of log messages sent"
			::={ acosEventsCollectorGroupSEntry 2 }

			msgsRateLimited OBJECT-TYPE
			SYNTAX  CounterBasedGauge64
			MAX-ACCESS read-only
			STATUS current
			DESCRIPTION  "Number of rate limited log messages"
			::={ acosEventsCollectorGroupSEntry 3 }

			msgsDropped OBJECT-TYPE
			SYNTAX  CounterBasedGauge64
			MAX-ACCESS read-only
			STATUS current
			DESCRIPTION  "Number of messages dropped for other reasons"
			::={ acosEventsCollectorGroupSEntry 4 }

acosAcosEventsStatistics            OBJECT IDENTIFIER ::= { acosAcosEvents 8 }
acosAcosEventsStatisticsS           OBJECT IDENTIFIER ::= { acosAcosEventsStatistics 1 }

		msgSent OBJECT-TYPE
		SYNTAX  CounterBasedGauge64
		MAX-ACCESS read-only
		STATUS current
		DESCRIPTION  "Messages sent, to Remote"
		::={ acosAcosEventsStatisticsS 1 }

		msgSentLogdb OBJECT-TYPE
		SYNTAX  CounterBasedGauge64
		MAX-ACCESS read-only
		STATUS current
		DESCRIPTION  "Messages sent, to LogDB"
		::={ acosAcosEventsStatisticsS 2 }

		msgDroppedFormatNotDefined OBJECT-TYPE
		SYNTAX  CounterBasedGauge64
		MAX-ACCESS read-only
		STATUS current
		DESCRIPTION  "Messages Dropped, format not defined"
		::={ acosAcosEventsStatisticsS 3 }

		msgDroppedMallocFailure OBJECT-TYPE
		SYNTAX  CounterBasedGauge64
		MAX-ACCESS read-only
		STATUS current
		DESCRIPTION  "Messages Dropped, malloc failure"
		::={ acosAcosEventsStatisticsS 4 }

		msgDroppedNoTemplate OBJECT-TYPE
		SYNTAX  CounterBasedGauge64
		MAX-ACCESS read-only
		STATUS current
		DESCRIPTION  "Messages Dropped, no active template"
		::={ acosAcosEventsStatisticsS 5 }

		msgDroppedSelector OBJECT-TYPE
		SYNTAX  CounterBasedGauge64
		MAX-ACCESS read-only
		STATUS current
		DESCRIPTION  "Messages Dropped, selector does not enable msg"
		::={ acosAcosEventsStatisticsS 6 }

		msgDroppedTooLong OBJECT-TYPE
		SYNTAX  CounterBasedGauge64
		MAX-ACCESS read-only
		STATUS current
		DESCRIPTION  "Messages Dropped, invalid length"
		::={ acosAcosEventsStatisticsS 7 }

		msgDroppedCraftFail OBJECT-TYPE
		SYNTAX  CounterBasedGauge64
		MAX-ACCESS read-only
		STATUS current
		DESCRIPTION  "Messages Dropped, msg crafting failed"
		::={ acosAcosEventsStatisticsS 8 }

		msgDroppedLocalLogRatelimit OBJECT-TYPE
		SYNTAX  CounterBasedGauge64
		MAX-ACCESS read-only
		STATUS current
		DESCRIPTION  "Messages Dropped, local log ratelimited"
		::={ acosAcosEventsStatisticsS 9 }

		msgDroppedRemoteLogRatelimit OBJECT-TYPE
		SYNTAX  CounterBasedGauge64
		MAX-ACCESS read-only
		STATUS current
		DESCRIPTION  "Messages Dropped, remote log ratelimited"
		::={ acosAcosEventsStatisticsS 10 }

		msgDroppedSendFailed OBJECT-TYPE
		SYNTAX  CounterBasedGauge64
		MAX-ACCESS read-only
		STATUS current
		DESCRIPTION  "Messages Dropped, send failed"
		::={ acosAcosEventsStatisticsS 11 }

		msgDroppedNoActiveMember OBJECT-TYPE
		SYNTAX  CounterBasedGauge64
		MAX-ACCESS read-only
		STATUS current
		DESCRIPTION  "Messages Dropped, no active member in collector grp"
		::={ acosAcosEventsStatisticsS 12 }

		msgDroppedRouteFail OBJECT-TYPE
		SYNTAX  CounterBasedGauge64
		MAX-ACCESS read-only
		STATUS current
		DESCRIPTION  "Messages Dropped, Route lookup failed"
		::={ acosAcosEventsStatisticsS 13 }

		msgDroppedOther OBJECT-TYPE
		SYNTAX  CounterBasedGauge64
		MAX-ACCESS read-only
		STATUS current
		DESCRIPTION  "Messages Dropped, unexpected error"
		::={ acosAcosEventsStatisticsS 14 }

		noTemplate OBJECT-TYPE
		SYNTAX  CounterBasedGauge64
		MAX-ACCESS read-only
		STATUS current
		DESCRIPTION  "Message API called, with no active template"
		::={ acosAcosEventsStatisticsS 15 }

		msgDroppedLostDuringConfigChange OBJECT-TYPE
		SYNTAX  CounterBasedGauge64
		MAX-ACCESS read-only
		STATUS current
		DESCRIPTION  "Messages Dropped, lost during config change"
		::={ acosAcosEventsStatisticsS 16 }

		localEnqueuePass OBJECT-TYPE
		SYNTAX  CounterBasedGauge64
		MAX-ACCESS read-only
		STATUS current
		DESCRIPTION  "Messages enqueue to Logd passed"
		::={ acosAcosEventsStatisticsS 17 }

		msgSentToLogd OBJECT-TYPE
		SYNTAX  CounterBasedGauge64
		MAX-ACCESS read-only
		STATUS current
		DESCRIPTION  "Messages sent to Logd via IPC"
		::={ acosAcosEventsStatisticsS 18 }

		msgRetryAfterSocketFail OBJECT-TYPE
		SYNTAX  CounterBasedGauge64
		MAX-ACCESS read-only
		STATUS current
		DESCRIPTION  "Messages retried to be sent to Logd via IPC"
		::={ acosAcosEventsStatisticsS 19 }

		msgSentDirectSyslog OBJECT-TYPE
		SYNTAX  CounterBasedGauge64
		MAX-ACCESS read-only
		STATUS current
		DESCRIPTION  "Messages sent to syslog directly from axlog"
		::={ acosAcosEventsStatisticsS 20 }

		msgDroppedSendToLogdFail OBJECT-TYPE
		SYNTAX  CounterBasedGauge64
		MAX-ACCESS read-only
		STATUS current
		DESCRIPTION  "Messages Dropped, send to Logd via IPC failed"
		::={ acosAcosEventsStatisticsS 21 }

		msgDroppedTrylockFail OBJECT-TYPE
		SYNTAX  CounterBasedGauge64
		MAX-ACCESS read-only
		STATUS current
		DESCRIPTION  "Messages Dropped, Trylock failed in axlog"
		::={ acosAcosEventsStatisticsS 22 }

		msgDroppedRemoteCplaneLogRatelimit OBJECT-TYPE
		SYNTAX  CounterBasedGauge64
		MAX-ACCESS read-only
		STATUS current
		DESCRIPTION  "Messages Dropped, Remote cplane log ratelimited"
		::={ acosAcosEventsStatisticsS 23 }

		msgDroppedRemoteDplaneLogRatelimit OBJECT-TYPE
		SYNTAX  CounterBasedGauge64
		MAX-ACCESS read-only
		STATUS current
		DESCRIPTION  "Messages Dropped, Remote dplane log ratelimited"
		::={ acosAcosEventsStatisticsS 24 }

		msgDroppedLocalEnqueueFailed OBJECT-TYPE
		SYNTAX  CounterBasedGauge64
		MAX-ACCESS read-only
		STATUS current
		DESCRIPTION  "Messages Dropped, Enqueue to Logd failed"
		::={ acosAcosEventsStatisticsS 25 }

		msgDroppedGrpNotUsed OBJECT-TYPE
		SYNTAX  CounterBasedGauge64
		MAX-ACCESS read-only
		STATUS current
		DESCRIPTION  "Messages Dropped, Collector group not used"
		::={ acosAcosEventsStatisticsS 26 }

		msgSentRemoteCplane OBJECT-TYPE
		SYNTAX  CounterBasedGauge64
		MAX-ACCESS read-only
		STATUS current
		DESCRIPTION  "Messages Sent, to remote in logd"
		::={ acosAcosEventsStatisticsS 27 }

		msgDroppedNoTemplateLogd OBJECT-TYPE
		SYNTAX  CounterBasedGauge64
		MAX-ACCESS read-only
		STATUS current
		DESCRIPTION  "Messages Dropped, no active template in Logd"
		::={ acosAcosEventsStatisticsS 28 }

		msgDroppedLostDuringConfigChangeLogd OBJECT-TYPE
		SYNTAX  CounterBasedGauge64
		MAX-ACCESS read-only
		STATUS current
		DESCRIPTION  "Messages Dropped, lost during config change in Logd"
		::={ acosAcosEventsStatisticsS 29 }

		msgDroppedCraftFailLogd OBJECT-TYPE
		SYNTAX  CounterBasedGauge64
		MAX-ACCESS read-only
		STATUS current
		DESCRIPTION  "Messages Dropped, msg crafting failed in Logd"
		::={ acosAcosEventsStatisticsS 30 }

		msgDroppedSendFailedLogd OBJECT-TYPE
		SYNTAX  CounterBasedGauge64
		MAX-ACCESS read-only
		STATUS current
		DESCRIPTION  "Messages Dropped, send failed in Logd"
		::={ acosAcosEventsStatisticsS 31 }

		msgDroppedNoActiveMemberLogd OBJECT-TYPE
		SYNTAX  CounterBasedGauge64
		MAX-ACCESS read-only
		STATUS current
		DESCRIPTION  "Messages Dropped, no active member in collector grp in Logd"
		::={ acosAcosEventsStatisticsS 32 }

		msgDroppedOtherLogd OBJECT-TYPE
		SYNTAX  CounterBasedGauge64
		MAX-ACCESS read-only
		STATUS current
		DESCRIPTION  "Messages Dropped, unexpected error in Logd"
		::={ acosAcosEventsStatisticsS 33 }

		msgDroppedInvalidPart OBJECT-TYPE
		SYNTAX  CounterBasedGauge64
		MAX-ACCESS read-only
		STATUS current
		DESCRIPTION  "Messages Dropped, Invalid partition Id"
		::={ acosAcosEventsStatisticsS 34 }

		acosEvtTestLogsTicks OBJECT-TYPE
		SYNTAX  CounterBasedGauge64
		MAX-ACCESS read-only
		STATUS current
		DESCRIPTION  "Number of ticks when running ACOS Event Test Logs"
		::={ acosAcosEventsStatisticsS 35 }

		paramMsgSentToHc OBJECT-TYPE
		SYNTAX  CounterBasedGauge64
		MAX-ACCESS read-only
		STATUS current
		DESCRIPTION  "Parameterized log sent to HC"
		::={ acosAcosEventsStatisticsS 36 }

		paramMsgSentFail OBJECT-TYPE
		SYNTAX  CounterBasedGauge64
		MAX-ACCESS read-only
		STATUS current
		DESCRIPTION  "Parameterized log send to HC failed"
		::={ acosAcosEventsStatisticsS 37 }

		paramMsgEncodeFail OBJECT-TYPE
		SYNTAX  CounterBasedGauge64
		MAX-ACCESS read-only
		STATUS current
		DESCRIPTION  "Parameterized log AVRO encoding failed"
		::={ acosAcosEventsStatisticsS 38 }

END
