ACOS-VCS-VBLADES-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosVcsVblades MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "VcsVblades OID for ACOS"
				::=  {  acosRootStats 144  }

acosVcsVbladesStat                  OBJECT IDENTIFIER ::= { acosVcsVblades 1 }
acosVcsVbladesStatS                 OBJECT IDENTIFIER ::= { acosVcsVbladesStat 1 }

vcsVbladesStatSTable OBJECT-TYPE
		SYNTAX SEQUENCE OF VcsVbladesStatSEntry
		MAX-ACCESS not-accessible
		STATUS current
		::={ acosVcsVbladesStatS 1 }


	vcsVbladesStatSEntry OBJECT-TYPE
		SYNTAX VcsVbladesStatSEntry
		MAX-ACCESS not-accessible
		STATUS current
		INDEX {
			vbladeId
		}
		::={ vcsVbladesStatSTable 1 }


	VcsVbladesStatSEntry ::=
		SEQUENCE {
			vbladeId INTEGER,
			vcsVbladesSlaveRecvErr CounterBasedGauge64,
			vcsVbladesSlaveSendErr CounterBasedGauge64,
			vcsVbladesSlaveRecvBytes CounterBasedGauge64,
			vcsVbladesSlaveSentBytes CounterBasedGauge64,
			vcsVbladesSlaveNRecv CounterBasedGauge64,
			vcsVbladesSlaveNSent CounterBasedGauge64,
			vcsVbladesSlaveMsgInval CounterBasedGauge64,
			vcsVbladesSlaveKeepAlive CounterBasedGauge64,
			vcsVbladesSlaveCfgUpd CounterBasedGauge64,
			vcsVbladesSlaveCfgUpdL1Fail CounterBasedGauge64,
			vcsVbladesSlaveCfgUpdRFail CounterBasedGauge64,
			vcsVbladesSlaveCfgUpdL2Fail CounterBasedGauge64,
			vcsVbladesSlaveCfgUpdNotifErr CounterBasedGauge64,
			vcsVbladesSlaveCfgUpdResultErr CounterBasedGauge64
		}

			vbladeId OBJECT-TYPE
			SYNTAX  INTEGER
			MAX-ACCESS read-only
			STATUS current
			DESCRIPTION  "vBlade-id"
			::={ vcsVbladesStatSEntry 1 }

			vcsVbladesSlaveRecvErr OBJECT-TYPE
			SYNTAX  CounterBasedGauge64
			MAX-ACCESS read-only
			STATUS current
			DESCRIPTION  "vBlade Receive Errors counter of aVCS election"
			::={ vcsVbladesStatSEntry 2 }

			vcsVbladesSlaveSendErr OBJECT-TYPE
			SYNTAX  CounterBasedGauge64
			MAX-ACCESS read-only
			STATUS current
			DESCRIPTION  "vBlade Send Errors counter of aVCS election"
			::={ vcsVbladesStatSEntry 3 }

			vcsVbladesSlaveRecvBytes OBJECT-TYPE
			SYNTAX  CounterBasedGauge64
			MAX-ACCESS read-only
			STATUS current
			DESCRIPTION  "vBlade Received Bytes counter of aVCS election"
			::={ vcsVbladesStatSEntry 4 }

			vcsVbladesSlaveSentBytes OBJECT-TYPE
			SYNTAX  CounterBasedGauge64
			MAX-ACCESS read-only
			STATUS current
			DESCRIPTION  "vBlade Sent Bytes counter of aVCS election"
			::={ vcsVbladesStatSEntry 5 }

			vcsVbladesSlaveNRecv OBJECT-TYPE
			SYNTAX  CounterBasedGauge64
			MAX-ACCESS read-only
			STATUS current
			DESCRIPTION  "vBlade Received Messages counter of aVCS election"
			::={ vcsVbladesStatSEntry 6 }

			vcsVbladesSlaveNSent OBJECT-TYPE
			SYNTAX  CounterBasedGauge64
			MAX-ACCESS read-only
			STATUS current
			DESCRIPTION  "vBlade Sent Messages counter of aVCS election"
			::={ vcsVbladesStatSEntry 7 }

			vcsVbladesSlaveMsgInval OBJECT-TYPE
			SYNTAX  CounterBasedGauge64
			MAX-ACCESS read-only
			STATUS current
			DESCRIPTION  "vBlade Invalid Messages counter of aVCS election"
			::={ vcsVbladesStatSEntry 8 }

			vcsVbladesSlaveKeepAlive OBJECT-TYPE
			SYNTAX  CounterBasedGauge64
			MAX-ACCESS read-only
			STATUS current
			DESCRIPTION  "vBlade Received Keepalives counter of aVCS election"
			::={ vcsVbladesStatSEntry 9 }

			vcsVbladesSlaveCfgUpd OBJECT-TYPE
			SYNTAX  CounterBasedGauge64
			MAX-ACCESS read-only
			STATUS current
			DESCRIPTION  "vBlade Received Configuration Updates counter of aVCS election"
			::={ vcsVbladesStatSEntry 10 }

			vcsVbladesSlaveCfgUpdL1Fail OBJECT-TYPE
			SYNTAX  CounterBasedGauge64
			MAX-ACCESS read-only
			STATUS current
			DESCRIPTION  "vBlade Local Configuration Update Errors (1) counter of aVCS election"
			::={ vcsVbladesStatSEntry 11 }

			vcsVbladesSlaveCfgUpdRFail OBJECT-TYPE
			SYNTAX  CounterBasedGauge64
			MAX-ACCESS read-only
			STATUS current
			DESCRIPTION  "vBlade Remote Configuration Update Errors counter of aVCS election"
			::={ vcsVbladesStatSEntry 12 }

			vcsVbladesSlaveCfgUpdL2Fail OBJECT-TYPE
			SYNTAX  CounterBasedGauge64
			MAX-ACCESS read-only
			STATUS current
			DESCRIPTION  "vBlade Local Configuration Update Errors (2) counter of aVCS election"
			::={ vcsVbladesStatSEntry 13 }

			vcsVbladesSlaveCfgUpdNotifErr OBJECT-TYPE
			SYNTAX  CounterBasedGauge64
			MAX-ACCESS read-only
			STATUS current
			DESCRIPTION  "vBlade Configuration Update Notif Errors counter of aVCS election"
			::={ vcsVbladesStatSEntry 14 }

			vcsVbladesSlaveCfgUpdResultErr OBJECT-TYPE
			SYNTAX  CounterBasedGauge64
			MAX-ACCESS read-only
			STATUS current
			DESCRIPTION  "vBlade Configuration Update Result Errors counter of aVCS election"
			::={ vcsVbladesStatSEntry 15 }

END
