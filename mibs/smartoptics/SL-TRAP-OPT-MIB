-- *****************************************************************
-- SNMP V1 Traps for the optical products
-- *****************************************************************

SL-TRAP-OPT-MIB DEFINITIONS ::= BEGIN
IMPORTS
	slAlarmIfIndex,
    slAlarmType,
	slAlarmSeverity,
	slAlarmServiceAffect,
    slAlarmActive FROM SL-ALARM-MIB
	optApsConfigUserWorkingIndex,
	optApsConfigActiveConnectionRx FROM SL-OPT-APS-MIB
    slEventIfIndex,
    slEventType,
    slEventVal,
    slEventUser FROM SL-EVENT-MIB
	slTestsIfLoopIfIndex,
	slTestsIfLoopType,
	slTestsTrapsLoopbackActive FROM SL-TESTS-MIB
	smartoptics FROM SL-NE-MIB;


slAlarmTrapV1 TRAP-TYPE
	ENTERPRISE smartoptics
	VARIABLES {slAlarmIfIndex,
       		   slAlarmType,
       		   slAlarmSeverity,
       		   slAlarmServiceAffect,
       		   slAlarmActive }
	DESCRIPTION "SNMPv1 trap equivalent definition"
	::= 101

optApsTrapSwitchoverV1 TRAP-TYPE
	ENTERPRISE smartoptics
	VARIABLES {
       		optApsConfigUserWorkingIndex,
       		optApsConfigActiveConnectionRx }
	DESCRIPTION
               "An optApsTrapSwitchover notification is sent when the
               value of an instance of optApsChanSwitchovers increments."
	::= 102

slTestsTrapsLoopbackTableChangedV1 TRAP-TYPE
	ENTERPRISE smartoptics
	VARIABLES {
		slTestsIfLoopIfIndex,
		slTestsIfLoopType,
		slTestsTrapsLoopbackActive }
	DESCRIPTION "SNMPv1 trap equivalent definition"
	::= 103

slEventTrapV1 TRAP-TYPE
	ENTERPRISE smartoptics
    VARIABLES {
       			slEventIfIndex,
       			slEventType,
       			slEventVal,
       			slEventUser }
    DESCRIPTION
               "An slEventTrap is sent when an configuration change occures."
	::= 104

END
