-- *****************************************************************
-- Smartoptics SiteLight Network Element MIB
--
-- Nov 2000, Dirk Lutz
--
-- Copyright (c) 1999-2000 by Smartoptics AS
-- All rights reserved.
-- *****************************************************************

SL-NE-MIB DEFINITIONS ::= BEGIN

IMPORTS
	MODULE-IDENTITY, OBJECT-TYPE,
	enterprises, NOTIFICATION-TYPE 		FROM SNMPv2-SMI
	DisplayString, TruthValue	  		FROM SNMPv2-TC
	MODULE-COMPLIANCE, OBJECT-GROUP,
	NOTIFICATION-GROUP                  FROM SNMPv2-CONF
	InterfaceIndex		               	FROM IF-MIB;


smartoptics MODULE-IDENTITY
	LAST-UPDATED "200009260000Z"
	ORGANIZATION "Smartoptics"
	CONTACT-INFO
		"d.lutz@Smartoptics.com"
	DESCRIPTION
		"The MIB module is the root of the PL extension mibs."
	::= { enterprises 4515 }

sitelight 	OBJECT IDENTIFIER ::= { smartoptics 1 }
soproduct 	OBJECT IDENTIFIER ::= { smartoptics 100 }

-- Values for the sysObjectId

sone 		OBJECT IDENTIFIER ::= { soproduct 1 }

T-4400r		OBJECT IDENTIFIER ::= { sone 404 }    -- T-4400 Root
T-4408 		OBJECT IDENTIFIER ::= { T-4400r 1 }  	-- T-4408

T-4900r   	OBJECT IDENTIFIER ::= { sone 1000 }    	-- T-4900 Root
T-4904 		OBJECT IDENTIFIER ::= { T-4900r 1 }  	-- T-4904 & T-4902
T-4808		OBJECT IDENTIFIER ::= { T-4900r 2 }  	-- T-4808
T-4910  	OBJECT IDENTIFIER ::= { T-4900r 3 }  	-- T-4910 (not longer available)
T-ROADM-2	OBJECT IDENTIFIER ::= { T-4900r 4 }  	-- T-ROADM-2
T-4906  	OBJECT IDENTIFIER ::= { T-4900r 5 }  	-- T-4906
T-1608  	OBJECT IDENTIFIER ::= { T-4900r 6 }  	-- T-1608
T-4900-IL  	OBJECT IDENTIFIER ::= { T-4900r 7 }  	-- T-4900-IL
T-1608-CRY	OBJECT IDENTIFIER ::= { T-4900r 8 }  -- T-1608-CRY

T-4920r  	OBJECT IDENTIFIER ::= { sone 2000 }     -- T-4920 Root
T-4920  	OBJECT IDENTIFIER ::= { T-4920r 1 }   	-- T-4920

T-9900r 	OBJECT IDENTIFIER ::= { sone 2100 }  	-- T-9900 Root
T-9910  	OBJECT IDENTIFIER ::= { T-9900r 1 }  	-- T-9910
T-9910-C  	OBJECT IDENTIFIER ::= { T-9900r 2 }  	-- T-9910-C
T-9901  	OBJECT IDENTIFIER ::= { T-9900r 3 }  	-- T-9901 CFP to CFP


T-ROADM-nro	OBJECT IDENTIFIER ::= { sone 2200 }  	-- New T-ROADM Root
T-ROADM-4ro1 	OBJECT IDENTIFIER ::= { T-ROADM-nro 1 }  	-- T-ROADM-4 Type A
T-ROADM-4ro2  	OBJECT IDENTIFIER ::= { T-ROADM-nro 2 }  	-- T-ROADM-4 Type B
T-ROADM-4ro3  	OBJECT IDENTIFIER ::= { T-ROADM-nro 3 }  	-- T-ROADM-4 Type C


-- The root for the service mibs

slService 	OBJECT IDENTIFIER ::= { sitelight 1 }

END
