-- ****************************************************************************
-- ****************************************************************************
--
--             Copyright(c) 2001-2005 Mediatrix Telecom, Inc.
--
--  NOTICE:
--   This document contains information that is confidential and proprietary
--   to Mediatrix Telecom, Inc.
--
--   Mediatrix Telecom, Inc. reserves all rights to this document as well as
--   to the Intellectual Property of the document and the technology and
--   know-how that it includes and represents.
--
--   This publication cannot be reproduced, neither in whole nor in part in
--   any form whatsoever without written prior approval by
--   Mediatrix Telecom, Inc.
--
--   Mediatrix Telecom, Inc. reserves the right to revise this publication
--   and make changes at any time and without the obligation to notify any
--   person and/or entity of such revisions and/or changes.
--
-- ****************************************************************************
-- ****************************************************************************

MX-SYSTEM-ADMIN-MIB
DEFINITIONS ::= BEGIN

IMPORTS
        MODULE-IDENTITY,
        OBJECT-TYPE,
        Integer32,
        Unsigned32
    FROM SNMPv2-SMI
        MODULE-COMPLIANCE,
        OBJECT-GROUP
    FROM SNMPv2-CONF
        MxEnableState
    FROM MX-TC
       mediatrixAdmin
    FROM MX-SMI;

sysAdminMIB MODULE-IDENTITY
    LAST-UPDATED "200603060000Z"
    ORGANIZATION "Mediatrix Telecom, Inc."
    CONTACT-INFO "Mediatrix Telecom, Inc.
                  4229, Garlock Street
                  Sherbrooke (Quebec)
                  Canada
                  Phone: (819) 829-8749
                 "
    DESCRIPTION  "This MIB provides General system management information."
    -- ************************************************************************
    -- Revision history
    -- ************************************************************************
    REVISION    "200603060000Z"
    DESCRIPTION "Corrected the descriptions of variables sysAdminCommand and
                 sysAdminAppMode."

    REVISION    "200504200000Z"
    DESCRIPTION "Added the persistence for the sysAdminDownloadConfigFileStatus
                 variable"

    REVISION    "200402120000Z"
    DESCRIPTION "Added the updateConfiguration(6) option to the sysAdminCommand
                 MIB object."

    REVISION    "0312020000Z"
    DESCRIPTION "December 2nd, 2003
                    Added setConfigSourcesStatic.
                 November 12, 2003
                    Clarified the sysAdminDownloadConfigFileStatus description.
                 November 12, 2003
                    Augmented sysAdminAppMode variable description
                 November 5, 2003
                    Added sysAdminAppMode
                 October 20, 2003
                    Change order of IMPORTS clause to fix compiler error.
                 September 10, 2003
                    Addition of the sysAdminDefaultSettingsEnable variable.
                 October 26, 2001
                    Modified the description for the sysAdminCommand.
                 August 29, 2001
                    Creation"
    ::= { mediatrixAdmin 1 }

sysAdminMIBObjects     OBJECT IDENTIFIER ::= { sysAdminMIB 1 }
sysAdminConformance    OBJECT IDENTIFIER ::= { sysAdminMIB 2 }

    sysAdminCommand OBJECT-TYPE
        SYNTAX      INTEGER {
                             noOp(0),
                             checkRam(1),
                             checkRom(2),
                             downloadSoftware(3),
                             resetStats(4),
                             setConfigSourcesStatic(5),
                             updateConfiguration(6)
                            }
        MAX-ACCESS  read-write
        STATUS      current
        DESCRIPTION "This variable controls the various commands that can be performed by the unit.

                     noOp                   : No action is taken.

                     checkRam               : Launches the RAM check routine. The unit will restart,
                                              test the RAM, and start normally afterwards.

                                              This command can only be applied while the unit is in
                                              maintenance mode (groupAdminState must be 'locked'). If
                                              the unit is shutting down (groupAdminState is
                                              'shuttingDown'), the command is delayed until the unit
                                              enters maintenance mode.

                     checkRom               : This value's semantics are different depending on the
                                              protocol and hardware platform.
                                              Please refer to the documentation shipped with
                                              your device for more details.

                     downloadSoftware       : Launches a software update. The unit will restart,
                                              download the new software version, and restart again
                                              running the new software version.
                                              This command can only be applied while the unit is in
                                              maintenance mode (groupAdminState must be 'locked'). If
                                              the unit is shutting down (groupAdminState is
                                              'shuttingDown'), the command is delayed until the unit
                                              enters maintenance mode.

                     resetStats             : Resets all cumulated call statistics.

                     setConfigSourcesStatic : This command will set all configuration sources
                                              supported by the unit to 'static'. This command can be
                                              used when no DHCP server is present in the network to
                                              easily configure the unit to use static values.
                                              This value's semantics are different depending on the
                                              protocol.
                                              Please refer to the documentation shipped with
                                              your device for more details.

                     updateConfiguration    : Configuration files are fetched by the unit
                                              (see configFileFetchingFileName). The transfer protocol
                                              used is defined by configFileTransferProtocol.
                                              The unit is the initiator of the transfer sessions.
                                              The unit is automatically restarted after reception of the
                                              configuration files and the new settings are applied.
                                              This command can only be applied while the unit is in
                                              maintenance mode (groupAdminState must be 'locked'). If
                                              the unit is shutting down (groupAdminState is 'shuttingDown'),
                                              the command is delayed until the unit enters maintenance mode."
        DEFVAL      { noOp }
        ::=  {  sysAdminMIBObjects  1  }

    sysAdminDefaultSettingsEnable OBJECT-TYPE
        SYNTAX      MxEnableState
        MAX-ACCESS  read-write
        STATUS      current
        DESCRIPTION "Indicates if the default settings button can trigger the
                     factory reset.

                     The factory reset reverts the configuration of the system
                     to default factory settings.

                     enable  : The default settings button can trigger the
                               factory reset.

                     disable : The default settings button can not trigger the
                               factory reset.

                     Please refer to the documentation shipped with your device
                     for more details on the factory reset and the default
                     settings button.

                     This variable's semantics are different depending on protocol and/or
                     hardware platforms.
                     Please refer to the documentation shipped with your device for more details."
        DEFVAL      { enable }
        ::=  {  sysAdminMIBObjects  5  }

    sysAdminLastCheckRam OBJECT-TYPE
        SYNTAX      INTEGER {
                             notTested(0),
                             fail(1),
                             success(2)
                            }
        MAX-ACCESS  read-only
        STATUS      current
        DESCRIPTION "Last RAM check status."
        DEFVAL      { notTested }
        ::= { sysAdminMIBObjects 11 }

    sysAdminLastCheckRom OBJECT-TYPE
        SYNTAX      INTEGER {
                             fail(1),
                             success(2)
                            }
        MAX-ACCESS  read-only
        STATUS      current
        DESCRIPTION "Last ROM check status."
        DEFVAL      { success }
        ::= { sysAdminMIBObjects 12 }

    sysAdminLastDownloadSoftware OBJECT-TYPE
        SYNTAX      INTEGER {
                             fail(1),
                             success(2)
                            }
        MAX-ACCESS  read-only
        STATUS      current
        DESCRIPTION "Status of the last download software command."
        DEFVAL      { success }
        ::= { sysAdminMIBObjects 14 }

    sysAdminDownloadConfigFileStatus OBJECT-TYPE
        SYNTAX      INTEGER {
                             idle(0),
                             fail(1),
                             success(2),
                             inProgress(3),
                             listening(4)
                            }
        MAX-ACCESS  read-only
        STATUS      current
        DESCRIPTION "Status of the last configuration file download.

                     idle       : No configuration file download has been performed yet.

                     fail       : The last configuration file download failed.

                     success    : The last configuration file download succeeded.

                     inProgress : A configuration file download is in progress.

                     listening  : The unit is listening and waiting for a configuration file
                                  to be sent by the management server."
        DEFVAL      { idle }
        ::= { sysAdminMIBObjects 30 }

    sysAdminAppMode OBJECT-TYPE
        SYNTAX      INTEGER {
                            normal(0),
                            recovery(1)
                            }
        MAX-ACCESS  read-only
        STATUS      current
        DESCRIPTION "Application's current operational mode.

                     Refer to the documentation shipped with your device
                     for a thorough description of the operational modes."
        DEFVAL { normal }
        ::= {  sysAdminMIBObjects 50 }


    -- ************************************************************************
    -- Conformance information
    -- ************************************************************************
    sysAdminCompliances OBJECT IDENTIFIER ::= { sysAdminConformance 1 }

    sysAdminComplVer1 MODULE-COMPLIANCE
        STATUS      current
        DESCRIPTION
            ""
        MODULE -- This Module
            MANDATORY-GROUPS {
                                sysAdminGroupVer1
                             }
        ::= { sysAdminCompliances 1 }

    -- ************************************************************************
    -- MIB variable grouping
    -- ************************************************************************
    sysAdminGroups OBJECT IDENTIFIER ::= { sysAdminConformance 2 }

    sysAdminGroupVer1 OBJECT-GROUP
        OBJECTS {
                 sysAdminDownloadConfigFileStatus,
                 sysAdminCommand,
                 sysAdminDefaultSettingsEnable,
                 sysAdminLastCheckRam,
                 sysAdminLastCheckRom,
                 sysAdminLastDownloadSoftware,
                 sysAdminAppMode
                }
        STATUS current
        DESCRIPTION
            "This group holds the objects that contain system Administration Information."
        ::= { sysAdminGroups 1 }


END
