-- **SDOC***********************************************************************
-- *****************************************************************************
--
--             Copyright(c) 2003-2005 Mediatrix Telecom, Inc.
--
--  NOTICE:
--   This document contains information that is confidential and proprietary to
--   Mediatrix Telecom, Inc.
--
--   Mediatrix Telecom, Inc. reserves all rights to this document as well as to
--   the Intellectual Property of the document and the technology and know-how
--   that it includes and represents.
--
--   This publication cannot be reproduced, neither in whole nor in part, in any
--   form whatsoever, without prior written approval by Mediatrix Telecom, Inc.
--
--   Mediatrix Telecom, Inc. reserves the right to revise this publication and
--   make changes at any time and without the obligation to notify any person
--   and/or entity of such revisions and/or changes.
--
-- *****************************************************************************
-- **EDOC***********************************************************************

MX-ANALOG-SCN-GATEWAY-MIB
DEFINITIONS ::= BEGIN

IMPORTS
        MODULE-IDENTITY,
        OBJECT-TYPE,
        Unsigned32
    FROM SNMPv2-SMI
        MODULE-COMPLIANCE,
        OBJECT-GROUP
    FROM SNMPv2-CONF
        ifIndex
    FROM RFC1213-MIB
        mediatrixConfig
    FROM MX-SMI
        MxEnableState
    FROM MX-TC;

analogScnGwMIB MODULE-IDENTITY
    LAST-UPDATED "200510270000Z"
    ORGANIZATION "Mediatrix Telecom, Inc."
    CONTACT-INFO "Mediatrix Telecom, Inc.
                  4229, Garlock Street
                  Sherbrooke (Quebec)
                  Canada, J1L 2C8
                  Phone: (819) 829-8749
                  http://www.mediatrix.com"
    DESCRIPTION  "This MIB is used customize the properties of an analog SCN gateway."


    -- *************************************************************************
    -- Revision history
    -- *************************************************************************
    REVISION    "200510270000Z"
    DESCRIPTION "Added analogScnGwDialEnable."
    REVISION    "200308120000Z"
    DESCRIPTION "Changed range for analogScnGwInterDigitDialDelay and analogScnGwDtmfDuration."
    REVISION    "200303250000Z"
    DESCRIPTION "Change range for analogScnGwInterDigitDialDelay and analogScnGwDtmfDuration."
    REVISION    "200302250000Z"
    DESCRIPTION "Creation."
    ::= { mediatrixConfig 85 }

analogScnGwMIBObjects OBJECT IDENTIFIER ::= { analogScnGwMIB 1 }
analogScnGwConformance OBJECT IDENTIFIER ::= { analogScnGwMIB 5 }

    -- *************************************************************************
    -- IfDialingTable
    -- *************************************************************************

    analogScnGwIfDialingTable OBJECT-TYPE
        SYNTAX      SEQUENCE OF AnalogScnGwIfDialingEntry
        MAX-ACCESS  not-accessible
        STATUS      current
        DESCRIPTION "A table for customizing the dialing options"
        ::= { analogScnGwMIBObjects 10 }

        analogScnGwIfDialingEntry OBJECT-TYPE
            SYNTAX      AnalogScnGwIfDialingEntry
            MAX-ACCESS  not-accessible
            STATUS      current
            DESCRIPTION "A row in the analogScnGwIfDialingTable table."
            INDEX       {
                            ifIndex
                        }
            ::= { analogScnGwIfDialingTable 5 }

            AnalogScnGwIfDialingEntry ::= SEQUENCE
                {
                    analogScnGwDialPrefix           OCTET STRING,
                    analogScnGwPreDialDelay         Unsigned32,
                    analogScnGwInterDigitDialDelay  Unsigned32,
                    analogScnGwDtmfDuration         Unsigned32,
                    analogScnGwDialEnable           MxEnableState
                }

            analogScnGwDialPrefix OBJECT-TYPE
                SYNTAX  OCTET STRING (SIZE(0..63))
                MAX-ACCESS  read-write
                STATUS      current
                DESCRIPTION "A DTMF sequence to dial on the SCN before dialing the destination phone number.

                             The dial prefix can be any combination of DTMFs or pause characters.

                             'p', ';' and ',' are accepted as pause characters.

                             The pause duration is one second."
                DEFVAL      { "" }
                ::= { analogScnGwIfDialingEntry 10 }

            analogScnGwPreDialDelay OBJECT-TYPE
                SYNTAX  Unsigned32 (0..10000)
                MAX-ACCESS  read-write
                STATUS      current
                DESCRIPTION "The delay between the time the line is successfully seized, or dialtone
                             detected, and the moment the destination phone number is dialed.

                             Some country specifications include a mandatory PreDialDelay. In that case, the
                             highest between that and analogScnGwPreDialDelay is used.
                             See telephonyCountrySelection.

                             This value is expressed in milliseconds (ms)."
                DEFVAL      { 0 }
                ::= { analogScnGwIfDialingEntry 15 }

            analogScnGwInterDigitDialDelay OBJECT-TYPE
                SYNTAX  Unsigned32 (50..600)
                MAX-ACCESS  read-write
                STATUS      current
                DESCRIPTION "The delay between two DTMFs when dialing the destination phone number.

                             This value is expressed in milliseconds (ms)."
                DEFVAL      { 100 }
                ::= { analogScnGwIfDialingEntry 20 }

            analogScnGwDtmfDuration OBJECT-TYPE
                SYNTAX  Unsigned32 (50..600)
                MAX-ACCESS  read-write
                STATUS      current
                DESCRIPTION "The duration of a DTMF when dialing the destination phone number.

                             This value is expressed in milliseconds (ms)."
                DEFVAL      { 100 }
                ::= { analogScnGwIfDialingEntry 25 }

            analogScnGwDialEnable OBJECT-TYPE
                SYNTAX      MxEnableState
                MAX-ACCESS  read-write
                STATUS      current
                DESCRIPTION "Determines how the gateway behaves when it receives
                             an IP call.  This feature is useful in conjunction with the 'Remote
                             Line Extension' service.

                             disable: The gateway picks up the SCN line and opens the
                                      audio channel with the peer.

                             enable : The gateway picks up the SCN line and dials
                                      the telephone number associated with the destination of
                                      the call before opening the audio channel with the peer."

                DEFVAL      { enable }
                ::= { analogScnGwIfDialingEntry 75 }


    -- *************************************************************************
    -- Conformance information
    -- *************************************************************************
    analogScnGwCompliances OBJECT IDENTIFIER ::= { analogScnGwConformance 1 }

    analogScnGwComplVer1 MODULE-COMPLIANCE
        STATUS      current
        DESCRIPTION
            "List of groups required to support analog SCN gateway."
        MODULE  -- This Module
            MANDATORY-GROUPS {
                                analogScnGwDialingVer1
                             }
        ::= { analogScnGwCompliances 1 }

    -- *************************************************************************
    --  MIB variable grouping
    -- *************************************************************************
    analogScnGwGroups OBJECT IDENTIFIER ::= { analogScnGwConformance 5 }

    analogScnGwDialingVer1 OBJECT-GROUP
        OBJECTS {
                    analogScnGwDialPrefix,
                    analogScnGwPreDialDelay,
                    analogScnGwInterDigitDialDelay,
                    analogScnGwDtmfDuration,
                    analogScnGwDialEnable
                }
        STATUS current
        DESCRIPTION
            "A collection of objects that defines the characteristics of analog SCN gateway."
        ::= { analogScnGwGroups 10 }
END
