-- ****************************************************************************
-- ****************************************************************************
--
--             Copyright(c) 2004 Mediatrix Telecom, Inc.
--
--  NOTICE:
--   This document contains information that is confidential and proprietary
--   to Mediatrix Telecom, Inc.
--
--   Mediatrix Telecom, Inc. reserves all rights to this document as well as
--   to the Intellectual Property of the document and the technology and
--   know how that it includes and represents.
--
--   This publication cannot be reproduced, neither in whole nor in part in
--   any form whatsoever without written prior approval by
--   Mediatrix Telecom, Inc.
--
--   Mediatrix Telecom, Inc. reserves the right to revise this publication
--   and make changes at any time and without the obligation to notify any
--   person and/or entity of such revisions and/or changes.
--
-- ****************************************************************************
-- ****************************************************************************

MX-BOOT-BEHAVIOR-MIB
DEFINITIONS ::= BEGIN

IMPORTS
        MODULE-IDENTITY,
        OBJECT-TYPE
    FROM SNMPv2-SMI
        MODULE-COMPLIANCE,
        OBJECT-GROUP
    FROM SNMPv2-CONF
        MxEnableState
    FROM MX-TC
        mediatrixExperimental
    FROM MX-SMI;

bootBehaviorMIB MODULE-IDENTITY
    LAST-UPDATED "200408120000Z"
    ORGANIZATION "Mediatrix Telecom, Inc."
    CONTACT-INFO "Mediatrix Telecom, Inc.
                  4229, Garlock Street
                  Sherbrooke (Quebec)
                  Canada
                  Phone: (819) 829-8749
                  "
    DESCRIPTION "This MIB contains boot behavior related objects for Mediatrix products."

    -- ************************************************************************
    -- Revision history
    -- ************************************************************************
    REVISION    "200408120000Z"
    DESCRIPTION "Creation"
    ::= { mediatrixExperimental 70 }

bootBehaviorMIBObjects  OBJECT IDENTIFIER ::= { bootBehaviorMIB 1 }
bootBehaviorConformance OBJECT IDENTIFIER ::= { bootBehaviorMIB 2 }


    checkTcpIpStackForSuccessfulBoot OBJECT-TYPE
        SYNTAX      MxEnableState
        MAX-ACCESS  read-write
        STATUS      current
        DESCRIPTION "Enable the check of TCP/IP stack before declaring the boot
                     successful.

                     This variable affects the behavior of the unit when it
                     reboots and a TCP/IP flood occurs.

                     The flood prevents the TCP/IP stack from initializing properly,
                     and the unit eventually reboots again.  After three unsuccessful
                     reboots, the unit falls into rescue mode.

                     When checkTcpIpStackForSuccessfulBoot is enabled, the TCP/IP stack
                     must initialize properly to consider the reboot a success.  In a
                     flood scenario, the unit may end up in the rescue mode.

                     When checkTcpIpStackForSuccessfulBoot is disabled, during a TCP/IP
                     flood, even if the TCP/IP stack fails to initialize, the reboot is
                     considered successful, and thus, the unit never goes into rescue
                     mode in this scenario."
        DEFVAL      { enable }
        ::=  {  bootBehaviorMIBObjects  1  }

    -- ************************************************************************
    -- Conformance information
    -- ************************************************************************
    bootBehaviorCompliances OBJECT IDENTIFIER ::= { bootBehaviorConformance 1 }

    bootBehaviorComplVer1 MODULE-COMPLIANCE
        STATUS      current
        DESCRIPTION
            "List of groups required to support boot behavior parameters."
        MODULE -- This Module
            MANDATORY-GROUPS {
                                 bootBehaviorGroupVer1
                             }
        ::= { bootBehaviorCompliances 10 }

    -- ************************************************************************
    -- MIB variable grouping
    -- ************************************************************************
    bootBehaviorGroups OBJECT IDENTIFIER ::= { bootBehaviorConformance 2 }

    bootBehaviorGroupVer1 OBJECT-GROUP
        OBJECTS {
                    checkTcpIpStackForSuccessfulBoot
                }
        STATUS current
        DESCRIPTION
            "A collection of objects that defines a list related to boot behavior."
        ::= { bootBehaviorGroups 10 }


END
