DS8200v2-TC-MIB DEFINITIONS ::= BEGIN

IMPORTS enterprises,MODULE-IDENTITY	FROM SNMPv2-SMI;

verilink MODULE-IDENTITY
	LAST-UPDATED "0011150000Z"
	ORGANIZATION "Verilink Corporation"
	CONTACT-INFO
		"Bob Ray
		bray@verilink.com
		1-256-774-2380"
	DESCRIPTION
		"DS8200v2 TC  MIB."
	::= { enterprises 321 }

hbu	OBJECT IDENTIFIER ::= { verilink 100 }

END
