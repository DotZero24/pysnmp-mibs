--
-- comIpRec.mib
-- MIB generated by MG-SOFT Visual MIB Builder Version 3.0 Build 285
-- Wednesday, September 01, 2010 at 09:17:51
--

    ZHONE-COM-IP-REC-MIB DEFINITIONS ::= BEGIN

        IMPORTS
            AtmVcIdentifier, AtmVpIdentifier
                FROM ATM-TC-MIB
            ifIndex, InterfaceIndex, InterfaceIndexOrZero
                FROM IF-MIB
            SnmpAdminString
                FROM SNMP-FRAMEWORK-MIB
            IpAddress, Integer32, Unsigned32, OBJECT-TYPE, MODULE-IDENTITY,
            OBJECT-IDENTITY
                FROM SNMPv2-SMI
            TruthValue
                FROM SNMPv2-TC
            ZhoneRDIndex
                FROM ZHONE-COM-IP-RD-MIB
            zhoneIp, zhoneModules
                FROM Zhone
            ZhoneRowStatus, ZhoneAdminString
                FROM Zhone-TC;


-- Protection Layer Generation:
-- /vob/zhonetools/bin/pahrser.pl iftype.mib rfc2514.mib rfc2233.mib
-- 	 rfc2571.mib comIpRD.mib Zhone.mib Zhone-TC.mib comIpRec.mib
-- Mib handler generation:
-- /vob/EPILOGUE/binaries/emissary/solaris/mibcomp rfc2514.mib rfc1907.mib
-- 	 iftype.mib rfc2233.mib Zhone.mib Zhone-TC.mib comIpRD.mib -stub -o
-- 	 ipInterfaceRecordHdlr.c comIpRec.mib
--
-- This MIB contains configuration information for the IP
-- interfaces.
--
-- ZHONE_KEYWORD_MODULE_NAME = (IP_Interface_Record, ipInterfaceRecord)
-- ZHONE_KEYWORD_PROFILE_LABEL = ip-interface-record
-- ZHONE_KEYWORD_PROFILE_GROUP = "/ IPInterface {ifIndex, INDEX} "
-- ZHONE_KEYWORD_STORAGE_RECORD = IP_Interface_Record
-- ZHONE_KEYWORD_STORAGE_GROUP = "/ ifIndex {LIST}"
-- ZHONE_KEYWORD_STORAGE_CLASS = PERSISTENT
-- ZHONE_KEYWORD_ACCESS_GROUP = ( INTERFACE )
-- ZHONE_KEYWORD_FEATURE_FLAGS = ( ZHONE_INFRA )
--
-- ZHONE_KEYWORD_MODULE_NAME = (IP_Alias_Record, ipInterfaceRecord)
-- ZHONE_KEYWORD_PROFILE_LABEL = ip-alias-record
-- ZHONE_KEYWORD_PROFILE_GROUP = "/ IPAliases {ifIndex, INDEX} / address {addr, INDEX}"
-- ZHONE_KEYWORD_STORAGE_RECORD = IP_Alias_Record
-- ZHONE_KEYWORD_STORAGE_GROUP = "/ ifIndex {LIST} / addr {LIST}"
-- ZHONE_KEYWORD_STORAGE_CLASS = PERSISTENT
-- ZHONE_KEYWORD_ACCESS_GROUP = ( INTERFACE )
-- ZHONE_KEYWORD_FEATURE_FLAGS = ( ZHONE_INFRA )
--
--
-- ZHONE_KEYWORD_MODULE_NAME = (IP_Unnumbered_Record, ipInterfaceRecord)
-- ZHONE_KEYWORD_PROFILE_LABEL = ip-unnumbered-record
-- ZHONE_KEYWORD_PROFILE_GROUP = "/ IPUnnumbered {ifIndex, INDEX}"
-- ZHONE_KEYWORD_STORAGE_RECORD = IP_Unnumbered_Record
-- ZHONE_KEYWORD_STORAGE_GROUP = "/ ifIndex {LIST}"
-- ZHONE_KEYWORD_STORAGE_CLASS = PERSISTENT
-- ZHONE_KEYWORD_ACCESS_GROUP = ( INTERFACE )
-- ZHONE_KEYWORD_FEATURE_FLAGS = ( IP_UNNUMBERED_IF )
--
--
        -- 1.3.6.1.4.1.5504.6.59
        ipRecord MODULE-IDENTITY
            LAST-UPDATED "201008310224Z"		-- August 31, 2010 at 02:24 GMT
            ORGANIZATION
                "Zhone Technologies, Inc."
            CONTACT-INFO
                "  Postal:
                           Zhone Technologies, Inc.
                           @ Zhone Way
                           7001 Oakport Street
                           Oakland, CA  94621
                           USA
                Toll-Free: +1 877-ZHONE20 (+1 877-946-6320)
                      Tel: +1-510-777-7000
                      Fax: +1-510-777-7001
                   E-mail: support@zhone.com"
            DESCRIPTION
                "IP record MIB
                IP Software
                Minneapolis, MN
                "
            REVISION "201009010917Z"		-- September 01, 2010 at 09:17 GMT
            DESCRIPTION
                "Changed maxVideoStreams upper threshold to 1024."
            REVISION "201005040224Z"		-- May 04, 2010 at 02:24 GMT
            DESCRIPTION
                "Added a new field ipOnDemandStatsEnabled in ipInterfaceEntry."
            REVISION "200806270814Z"		-- June 27, 2008 at 08:14 GMT
            DESCRIPTION
                "Added cpemgr(5) enum value to ipaddrdynamic field in ipInterfaceTable."
            REVISION "200602171737Z"		-- February 17, 2006 at 17:37 GMT
            DESCRIPTION
                "Increased maxVideoStreams to 210."
            REVISION "200601230926Z"		-- January 23, 2006 at 09:26 GMT
            DESCRIPTION
                "V01.04.09 - added support for QinQ to ipRecord."
            REVISION "200507201722Z"		-- July 20, 2005 at 17:22 GMT
            DESCRIPTION
                "V01.04.08 - Added tosOption, tosCOS, vlanCOS to IpInterfaceEntry."
            REVISION "200407210846Z"		-- July 21, 2004 at 08:46 GMT
            DESCRIPTION
                "V01.04.07 - bumped upper limit of
                maxVideoStreams to (6)."
            REVISION "200405270956Z"		-- May 27, 2004 at 09:56 GMT
            DESCRIPTION
                "V01.04.06 - added maxVideoStreams"
            REVISION "200404281402Z"		-- April 28, 2004 at 14:02 GMT
            DESCRIPTION
                "V01.04.05 - Increased the mcastControList field length from
                ZhoneAdminString to SnmpAdminString"
            REVISION "200304181003Z"		-- April 18, 2003 at 10:03 GMT
            DESCRIPTION
                "V01.04.04 - added subnetgroup and unnumberedindex in order to
                support point-to-multipoint feature."
            REVISION "200204171648Z"		-- April 17, 2002 at 16:48 GMT
            DESCRIPTION
                "V01.04.03 - Obsoleted lgId."
            REVISION "200202111657Z"		-- February 11, 2002 at 16:57 GMT
            DESCRIPTION
                "V01.04.02 - Added ipAddrDynamic enum unnumbered.
                     Added ipUnnumbered object identifiers."
            REVISION "200110301044Z"		-- October 30, 2001 at 10:44 GMT
            DESCRIPTION
                "V01.04.01 - Add ipAddrDynamic,dhcpServerEnable fields in
                            ipInterfaceEntry and deprecate  ipIfDhcp MIB."
            REVISION "200106061600Z"		-- June 06, 2001 at 16:00 GMT
            DESCRIPTION
                "V01.04.00 - Deprecated ipIfLgId and added ipIfLowerIfIndex
                            Added ipIfPppEnabled."
            REVISION "200103151028Z"		-- March 15, 2001 at 10:28 GMT
            DESCRIPTION
                "V01.03.03 - Removed ZHONE-KEYWORD markup from ipIfAliasAddr"
            REVISION "200102261358Z"		-- February 26, 2001 at 13:58 GMT
            DESCRIPTION
                "V01.03.02 - Removed DEFVAL from ipIfLgId and made
                            this a required object."
            REVISION "200102131113Z"		-- February 13, 2001 at 11:13 GMT
            DESCRIPTION
                "V01.03.01 - Set ipIfMru default to 1500"
            REVISION "200101191816Z"		-- January 19, 2001 at 18:16 GMT
            DESCRIPTION
                "V01.03.00 - Added ipIfIngressFilterId and ipIfEgressFilterId.
                            Deprecated ipIfIngressFilterName and ipIfEgressFilterName."
            REVISION "200101171618Z"		-- January 17, 2001 at 16:18 GMT
            DESCRIPTION
                "V01.02.01 - Changed NATEnabled default to false."
            REVISION "200011201018Z"		-- November 20, 2000 at 10:18 GMT
            DESCRIPTION
                "V01.02.00 - Added ipIfAdminStatus"
            REVISION "200010051512Z"		-- October 05, 2000 at 15:12 GMT
            DESCRIPTION
                "V01.01.00 - Added ipIfAliasNetMask and ipIfAliasBcastAddr"
            REVISION "200009151430Z"		-- September 15, 2000 at 14:30 GMT
            DESCRIPTION
                "V01.00.01 - Added ZHONE-KEYWORD markup"
            REVISION "200009121006Z"		-- September 12, 2000 at 10:06 GMT
            DESCRIPTION
                "V01.00.00 - Initial Release"
            ::= { zhoneModules 59 }




--
-- Node definitions
--

        -- 1.3.6.1.4.1.5504.4.1.9
        ipRecordObjects OBJECT-IDENTITY
            STATUS current
            DESCRIPTION
                "Object identity for naming"
            ::= { zhoneIp 9 }


        -- 1.3.6.1.4.1.5504.4.1.9.2
        ipInterfaceTable OBJECT-TYPE
            SYNTAX SEQUENCE OF IpInterfaceEntry
            MAX-ACCESS not-accessible
            STATUS current
            DESCRIPTION
                "This table comtains information required for the management
                of IP interfaces."
            ::= { ipRecordObjects 2 }


        -- 1.3.6.1.4.1.5504.4.1.9.2.1
        ipInterfaceEntry OBJECT-TYPE
            SYNTAX IpInterfaceEntry
            MAX-ACCESS not-accessible
            STATUS current
            DESCRIPTION
                "An entry exists for each IP interface in the system.
                At a mininum the ifIndex, either ipIfLowerIfIndex
                or ipIfLgId (not both) and a valid IP address configuration
                are required for row creation.

                These are valid IP address configurations:

                   1.  Dynamically configured IP address
                          ipIfDhcp set to client or both

                   2.  Statically configured non-point-to-point IP address
                          ipIfAddr, ipIfNetMask, and ipIfBcast must be provided.
                          ipIfAddr and ipIfBcastAddr must be in the same
                          subnet determined by ipIfNetMask

                   3.  Statically configured point-to-point IP address
                          ipIfAddr, ipIfDestAddr, ipIfNetMask, ipIfPointToPoint,
                          and ipIfBcastEnabled must be provided.
                          ipIfNetMask must be 255.255.255.255, ipIfPointToPoint
                          must be true and ipIfBcastEnabled must be false.



                "
            INDEX { ifIndex }
            ::= { ipInterfaceTable 1 }


        IpInterfaceEntry ::=
            SEQUENCE {
                ipIfLgId
                    Integer32,
                ipIfVpi
                    AtmVpIdentifier,
                ipIfVci
                    AtmVcIdentifier,
                ipIfRDIndex
                    ZhoneRDIndex,
                ipIfDhcp
                    INTEGER,
                ipIfAddr
                    IpAddress,
                ipIfNetMask
                    IpAddress,
                ipIfBcastAddr
                    IpAddress,
                ipIfDestAddr
                    IpAddress,
                ipIfFarEndAddr
                    IpAddress,
                ipIfMru
                    Unsigned32,
                ipIfReasmMaxSize
                    Integer32,
                ipIfIngressFilterName
                    ZhoneAdminString,
                ipIfEgressFilterName
                    ZhoneAdminString,
                ipIfPointToPoint
                    TruthValue,
                ipIfMcastEnabled
                    TruthValue,
                ipIfIpFwdEnabled
                    TruthValue,
                ipIfMcastFwdEnabled
                    TruthValue,
                ipIfNATEnabled
                    TruthValue,
                ipIfBcastEnabled
                    TruthValue,
                ipIfRowStatus
                    ZhoneRowStatus,
                ipIfAdminStatus
                    INTEGER,
                ipIfIngressPacketRuleGroupIndex
                    Integer32,
                ipIfEgressPacketRuleGroupIndex
                    Integer32,
                ipIfLowerIfIndex
                    InterfaceIndexOrZero,
                ipIfPppEnabled
                    TruthValue,
                ipAddrDynamic
                    INTEGER,
                dhcpServerEnable
                    TruthValue,
                dhcpSubnetGroup
                    Integer32,
                unnumberedIndex
                    Integer32,
                mcastControlList
                    SnmpAdminString,
                vlanid
                    Integer32,
                maxVideoStreams
                    Unsigned32,
                tosOption
                    INTEGER,
                tosCOS
                    Integer32,
                vlanCOS
                    Integer32,
                ipStagTPID
                    Integer32,
                ipStagId
                    Integer32,
                ipStagIdCOS
                    Integer32,
                ipOnDemandStatsEnabled
                    TruthValue
             }

        -- 1.3.6.1.4.1.5504.4.1.9.2.1.1
        ipIfLgId OBJECT-TYPE
            SYNTAX Integer32 (0..2147483647)
            MAX-ACCESS read-create
            STATUS obsolete
            DESCRIPTION
                "This field has been deprecated and replaced by ipIfLowerIfIndex.

                The ID number of the Line Redundancy Group containing the physical
                line associated with this interface.  There may be a single line
                or a line pair in a redundancy group.  The value 0 is only allowed
                when the ip interface has not yet been bound to a physical port.
                Currently, IP interfaces are always bound to a physical port so the
                value of zero is not allowed."
            REFERENCE
                "see genLineRedundancy MIB:  lineGroupTable.lineGroupEntry.lgId"
            ::= { ipInterfaceEntry 1 }


-- ZHONE_KEYWORD_PROFILE_LABEL = vpi
-- ZHONE_KEYWORD_STORAGE_LABEL = IP_Interface_Record.vpi
-- ZHONE_KEYWORD_STORAGE_ORDER = 1
        -- 1.3.6.1.4.1.5504.4.1.9.2.1.2
        ipIfVpi OBJECT-TYPE
            SYNTAX AtmVpIdentifier
            MAX-ACCESS read-create
            STATUS current
            DESCRIPTION
                "If this IP interface is on an ATM VC, the ATM VPI is specified here.
                If the IP interface is not an ATM VC, this field is ignored.
                The VPI value for a VPL or VCL. The value VPI=0
                is only allowed for a VCL. For ATM UNIs supporting
                VPCs the VPI value ranges from 0 to 255.  The VPI
                value 0 is supported for ATM UNIs conforming to
                the ATM Forum UNI 4.0 Annex 8 (Virtual UNIs)
                specification. For ATM UNIs supporting VCCs the
                VPI value ranges from 0 to 255.  For ATM NNIs the
                VPI value ranges from 0 to 4095.  The maximum VPI
                value cannot exceed the value allowable by
                atmInterfaceMaxVpiBits defined in ATM-MIB."
            DEFVAL { 0 }
            ::= { ipInterfaceEntry 2 }


-- ZHONE_KEYWORD_PROFILE_LABEL = vci
-- ZHONE_KEYWORD_STORAGE_LABEL = IP_Interface_Record.vci
-- ZHONE_KEYWORD_STORAGE_ORDER = 2
        -- 1.3.6.1.4.1.5504.4.1.9.2.1.3
        ipIfVci OBJECT-TYPE
            SYNTAX AtmVcIdentifier
            MAX-ACCESS read-create
            STATUS current
            DESCRIPTION
                "If this IP interface is on an ATM VC, the ATM VCI is specified here.
                If the IP interface is not an ATM VC, this field is ignored.
                The maximum VCI value cannot exceed the value allowable by
                atmInterfaceMaxVciBits defined in ATM-MIB."
            DEFVAL { 0 }
            ::= { ipInterfaceEntry 3 }


-- ZHONE_KEYWORD_PROFILE_LABEL = rdindex
-- ZHONE_KEYWORD_STORAGE_LABEL = IP_Interface_Record.rdindex
-- ZHONE_KEYWORD_STORAGE_ORDER = 3
        -- 1.3.6.1.4.1.5504.4.1.9.2.1.4
        ipIfRDIndex OBJECT-TYPE
            SYNTAX ZhoneRDIndex
            MAX-ACCESS read-create
            STATUS current
            DESCRIPTION
                "The Routing Domain Index.  An IP address is unique only to
                the routing domain, therefore we must specify the routing domain
                in which this interface belongs."
            DEFVAL { 0 }
            ::= { ipInterfaceEntry 4 }


-- ZHONE_KEYWORD_PROFILE_LABEL = dhcp
-- ZHONE_KEYWORD_STORAGE_LABEL = IP_Interface_Record.dhcpmode
-- ZHONE_KEYWORD_STORAGE_ORDER = 4
        -- 1.3.6.1.4.1.5504.4.1.9.2.1.5
        ipIfDhcp OBJECT-TYPE
            SYNTAX INTEGER
                {
                noDhcp(1),
                dhcpClient(2),
                dhcpServer(3),
                dhcpBoth(4)
                }
            MAX-ACCESS read-create
            STATUS deprecated
            DESCRIPTION
                "This enumeration indicates whether this interface is a dhcp client,
                a dhcp server, both, or neither. The default value is noDhcp.
                "
            DEFVAL { noDhcp }
            ::= { ipInterfaceEntry 5 }


-- ZHONE_KEYWORD_PROFILE_LABEL = addr
-- ZHONE_KEYWORD_STORAGE_LABEL = IP_Interface_Record.addr
-- ZHONE_KEYWORD_STORAGE_ORDER = 5
        -- 1.3.6.1.4.1.5504.4.1.9.2.1.6
        ipIfAddr OBJECT-TYPE
            SYNTAX IpAddress
            MAX-ACCESS read-create
            STATUS current
            DESCRIPTION
                "The IP address to which this entry's addressing information
                pertains. "
            REFERENCE
                "See RFC2011:  ip.ipAddrTable.ipAddrEntry.ipAdEntAddr"
            DEFVAL { '00000000'h }
            ::= { ipInterfaceEntry 6 }


-- ZHONE_KEYWORD_PROFILE_LABEL = netmask
-- ZHONE_KEYWORD_STORAGE_LABEL = IP_Interface_Record.netmask
-- ZHONE_KEYWORD_STORAGE_ORDER = 6
        -- 1.3.6.1.4.1.5504.4.1.9.2.1.7
        ipIfNetMask OBJECT-TYPE
            SYNTAX IpAddress
            MAX-ACCESS read-create
            STATUS current
            DESCRIPTION
                "The subnet mask associated with the IP address of this
                entry.  The value of the mask is an IP address with all the
                network bits set to 1 and all the hosts bits set to 0."
            REFERENCE
                "See RFC2011:  ip.ipAddrTable.ipAddrEntry.ipAdEntNetMask"
            DEFVAL { '00000000'h }
            ::= { ipInterfaceEntry 7 }


-- ZHONE_KEYWORD_PROFILE_LABEL = bcastaddr
-- ZHONE_KEYWORD_STORAGE_LABEL = IP_Interface_Record.bcastaddr
-- ZHONE_KEYWORD_STORAGE_ORDER = 7
        -- 1.3.6.1.4.1.5504.4.1.9.2.1.8
        ipIfBcastAddr OBJECT-TYPE
            SYNTAX IpAddress
            MAX-ACCESS read-create
            STATUS current
            DESCRIPTION
                "The IP broadcast address used for sending datagrams on the
                (logical) interface associated with the IP address of this entry.  "
            REFERENCE
                "See RFC2011:  ip.ipAddrTable.ipAddrEntry.ipAdEntBcastAddr"
            DEFVAL { '00000000'h }
            ::= { ipInterfaceEntry 8 }


-- ZHONE_KEYWORD_PROFILE_LABEL = destaddr
-- ZHONE_KEYWORD_STORAGE_LABEL = IP_Interface_Record.destaddr
-- ZHONE_KEYWORD_STORAGE_ORDER = 8
        -- 1.3.6.1.4.1.5504.4.1.9.2.1.9
        ipIfDestAddr OBJECT-TYPE
            SYNTAX IpAddress
            MAX-ACCESS read-create
            STATUS current
            DESCRIPTION
                "The destination address for point-to-point ip interfaces.
                This object will be ignored for non point-to-point ip interfaces."
            REFERENCE
                "See RFC2011:  ip.ipAddrTable.ipAddrEntry.ipAdEnDestAddr"
            DEFVAL { '00000000'h }
            ::= { ipInterfaceEntry 9 }


-- ZHONE_KEYWORD_PROFILE_LABEL = farendaddr
-- ZHONE_KEYWORD_STORAGE_LABEL = IP_Interface_Record.farendaddr
-- ZHONE_KEYWORD_STORAGE_ORDER = 9
        -- 1.3.6.1.4.1.5504.4.1.9.2.1.10
        ipIfFarEndAddr OBJECT-TYPE
            SYNTAX IpAddress
            MAX-ACCESS read-create
            STATUS current
            DESCRIPTION
                "The IP address of the interface on the far end of this interface.
                This information is needed for Zhone Automatic Provisioning."
            DEFVAL { '00000000'h }
            ::= { ipInterfaceEntry 10 }


-- Default value depends on the type of interface.  Should
-- be same as default MTU.
--
-- ZHONE_KEYWORD_PROFILE_LABEL = mru
-- ZHONE_KEYWORD_STORAGE_LABEL = IP_Interface_Record.mru
-- ZHONE_KEYWORD_STORAGE_ORDER = 10
        -- 1.3.6.1.4.1.5504.4.1.9.2.1.11
        ipIfMru OBJECT-TYPE
            SYNTAX Unsigned32
            MAX-ACCESS read-create
            STATUS current
            DESCRIPTION
                "The size of the largest packet which can be
                received on the interface, specified in octets.
                For interfaces that are used for network
                datagrams, this is the size of the largest network
                datagram that can be received on the interface."
            DEFVAL { 1500 }
            ::= { ipInterfaceEntry 11 }


-- ZHONE_KEYWORD_PROFILE_LABEL = reasmmaxsize
-- ZHONE_KEYWORD_STORAGE_LABEL = IP_Interface_Record.reasmmaxsize
-- ZHONE_KEYWORD_STORAGE_ORDER = 11
        -- 1.3.6.1.4.1.5504.4.1.9.2.1.12
        ipIfReasmMaxSize OBJECT-TYPE
            SYNTAX Integer32 (0..65535)
            MAX-ACCESS read-create
            STATUS current
            DESCRIPTION
                "The size of the largest IP datagram which this entity can
                re-assemble from incoming IP fragmented datagrams received
                on this interface."
            REFERENCE
                "See RFC2011:  ip.ipAddrTable.ipAddrEntry.ipAdEntReasmMaxSize"
            DEFVAL { 65535 }
            ::= { ipInterfaceEntry 12 }


        -- 1.3.6.1.4.1.5504.4.1.9.2.1.13
        ipIfIngressFilterName OBJECT-TYPE
            SYNTAX ZhoneAdminString
            MAX-ACCESS read-create
            STATUS deprecated
            DESCRIPTION
                "The name of the ingress filter associated with this interface.
                This object has been replaced by ipIfIngressFilterID."
            REFERENCE
                "See comIpFilter.mib:  filterSpecTable.filterSpecEntry.filterSpecName"
            ::= { ipInterfaceEntry 13 }


        -- 1.3.6.1.4.1.5504.4.1.9.2.1.14
        ipIfEgressFilterName OBJECT-TYPE
            SYNTAX ZhoneAdminString
            MAX-ACCESS read-create
            STATUS deprecated
            DESCRIPTION
                "The name of the egress filter associated with this interface.
                This object has been replaced by ipIfEgressFilterID."
            REFERENCE
                "See comIpFilter.mib:  filterSpecTable.filterSpecEntry.filterSpecName"
            ::= { ipInterfaceEntry 14 }


-- ZHONE_KEYWORD_PROFILE_LABEL = pointtopoint
-- ZHONE_KEYWORD_STORAGE_LABEL = IP_Interface_Record.pointtopoint
-- ZHONE_KEYWORD_STORAGE_ORDER = 14
--
        -- 1.3.6.1.4.1.5504.4.1.9.2.1.15
        ipIfPointToPoint OBJECT-TYPE
            SYNTAX TruthValue
            MAX-ACCESS read-create
            STATUS current
            DESCRIPTION
                "This flag is set to 'true(1)' if the interface
                is point to point and the value 'false(2)' otherwise."
            DEFVAL { false }
            ::= { ipInterfaceEntry 15 }


-- ZHONE_KEYWORD_PROFILE_LABEL = mcastenabled
-- ZHONE_KEYWORD_STORAGE_LABEL = IP_Interface_Record.mcastenabled
-- ZHONE_KEYWORD_STORAGE_ORDER = 15
        -- 1.3.6.1.4.1.5504.4.1.9.2.1.16
        ipIfMcastEnabled OBJECT-TYPE
            SYNTAX TruthValue
            MAX-ACCESS read-create
            STATUS current
            DESCRIPTION
                "This object has the value 'true(1)' If multicast is
                enabled on this interface and the value 'false(2)' otherwise."
            DEFVAL { true }
            ::= { ipInterfaceEntry 16 }


-- ZHONE_KEYWORD_PROFILE_LABEL = ipfwdenabled
-- ZHONE_KEYWORD_STORAGE_LABEL = IP_Interface_Record.ipfwdenabled
-- ZHONE_KEYWORD_STORAGE_ORDER = 16
        -- 1.3.6.1.4.1.5504.4.1.9.2.1.17
        ipIfIpFwdEnabled OBJECT-TYPE
            SYNTAX TruthValue
            MAX-ACCESS read-create
            STATUS current
            DESCRIPTION
                "This object has the value 'true(1)' If ip forwarding is
                enabled on this interface and the value 'false(2)' otherwise."
            DEFVAL { true }
            ::= { ipInterfaceEntry 17 }


-- ZHONE_KEYWORD_PROFILE_LABEL = mcastfwdenabled
-- ZHONE_KEYWORD_STORAGE_LABEL = IP_Interface_Record.mcastfwdenabled
-- ZHONE_KEYWORD_STORAGE_ORDER = 17
        -- 1.3.6.1.4.1.5504.4.1.9.2.1.18
        ipIfMcastFwdEnabled OBJECT-TYPE
            SYNTAX TruthValue
            MAX-ACCESS read-create
            STATUS current
            DESCRIPTION
                "This object has the value 'true(1)' If multicast forwarding is
                enabled on this interface and the value 'false(2)' otherwise."
            DEFVAL { true }
            ::= { ipInterfaceEntry 18 }


-- ZHONE_KEYWORD_PROFILE_LABEL = natenabled
-- ZHONE_KEYWORD_STORAGE_LABEL = IP_Interface_Record.natenabled
-- ZHONE_KEYWORD_STORAGE_ORDER = 18
        -- 1.3.6.1.4.1.5504.4.1.9.2.1.19
        ipIfNATEnabled OBJECT-TYPE
            SYNTAX TruthValue
            MAX-ACCESS read-create
            STATUS current
            DESCRIPTION
                "This object has the value 'true(1)' if NAT is enabled on this
                interface and the value 'false(2)' otherwise.  The default value
                is false."
            DEFVAL { false }
            ::= { ipInterfaceEntry 19 }


-- ZHONE_KEYWORD_PROFILE_LABEL = bcastenabled
-- ZHONE_KEYWORD_STORAGE_LABEL = IP_Interface_Record.bcastenabled
-- ZHONE_KEYWORD_STORAGE_ORDER = 19
        -- 1.3.6.1.4.1.5504.4.1.9.2.1.20
        ipIfBcastEnabled OBJECT-TYPE
            SYNTAX TruthValue
            MAX-ACCESS read-create
            STATUS current
            DESCRIPTION
                "This object has the value 'true(1)' If broadcast is
                enabled on this interface and the value 'false(2)' otherwise."
            DEFVAL { true }
            ::= { ipInterfaceEntry 20 }


        -- 1.3.6.1.4.1.5504.4.1.9.2.1.21
        ipIfRowStatus OBJECT-TYPE
            SYNTAX ZhoneRowStatus
            MAX-ACCESS read-create
            STATUS current
            DESCRIPTION
                "This object is used to create and remove rows in the table.
                See ipInterfaceEntry description for minimum requirements."
            ::= { ipInterfaceEntry 21 }


-- No markup required because this object duplicates
-- ifAdminStatus in rfc2233.
        -- 1.3.6.1.4.1.5504.4.1.9.2.1.22
        ipIfAdminStatus OBJECT-TYPE
            SYNTAX INTEGER
                {
                up(1),
                down(2),
                testing(3)
                }
            MAX-ACCESS read-create
            STATUS current
            DESCRIPTION
                "The desired state of the interface.  The testing(3)
                state indicates that no operational packets can be
                passed.  When a managed system initializes, all
                interfaces start with ifAdminStatus in the down(2)
                state.  As a result of either explicit management
                action or per configuration information retained by
                the managed system, ifAdminStatus is then changed to
                either the up(1) or testing(3) states (or remains in
                the down(2) state).

                This is the same as the ifAdminStatus in the ifTable
                (RFC2233).  We require it to be in this table in order
                to set it on a row-create."
            REFERENCE
                "See RFC2233:  interfaces.ifTable.ifEntry.ifAdminStatus"
            DEFVAL { up }
            ::= { ipInterfaceEntry 22 }


-- ZHONE_KEYWORD_PROFILE_LABEL = ingressPacketRuleGroupIndex
-- ZHONE_KEYWORD_STORAGE_LABEL = IP_Interface_Record.ingressPacketRuleGroupIndex
-- ZHONE_KEYWORD_STORAGE_ORDER = 12
        -- 1.3.6.1.4.1.5504.4.1.9.2.1.23
        ipIfIngressPacketRuleGroupIndex OBJECT-TYPE
            SYNTAX Integer32 (0..2147483647)
            MAX-ACCESS read-create
            STATUS current
            DESCRIPTION
                "The group index of the ingress filter (packet rule entry
                /entries) provisioned for this interface.
                A value of 0 means there is no ingress filter provisioned
                for this interface.
                "
            REFERENCE
                "See comBridgeRec.mib:  packetRuleTable.packetRuleEntry.packetRuleIndex"
            DEFVAL { 0 }
            ::= { ipInterfaceEntry 23 }


-- ZHONE_KEYWORD_PROFILE_LABEL = egressPacketRuleGroupIndex
-- ZHONE_KEYWORD_STORAGE_LABEL = IP_Interface_Record.egressPacketRuleGroupIndex
-- ZHONE_KEYWORD_STORAGE_ORDER = 13
        -- 1.3.6.1.4.1.5504.4.1.9.2.1.24
        ipIfEgressPacketRuleGroupIndex OBJECT-TYPE
            SYNTAX Integer32 (0..2147483647)
            MAX-ACCESS read-create
            STATUS current
            DESCRIPTION
                "The group index of the egress filter (packet rule entry
                /entries) provisioned for this interface.
                A value of 0 means there is no egress filter provisioned
                for this interface.
                "
            REFERENCE
                "See comBridgeRec.mib:  packetRuleTable.packetRuleEntry.packetRuleIndex"
            DEFVAL { 0 }
            ::= { ipInterfaceEntry 24 }


-- There is no ZHONE_KEYWORD markup required for this object
-- since the information is reflected in the ifStack.
        -- 1.3.6.1.4.1.5504.4.1.9.2.1.25
        ipIfLowerIfIndex OBJECT-TYPE
            SYNTAX InterfaceIndexOrZero
            MAX-ACCESS read-create
            STATUS current
            DESCRIPTION
                "The ifIndex of the lower layer interface to which this IP
                interface should be bound.  If this IP interface is
                bound dynamically to a lower layer (e.g. for PPP), this
                object should be set to zero.  Upon setting this field, the
                ifStack will be modified to reflect the appropriate binding.
                This object is required for row creation."
            REFERENCE
                "See ifStackTable in rfc2233.mib."
            ::= { ipInterfaceEntry 25 }


-- There is no ZHONE_KEYWORD markup required for this object
-- since the information is reflected in the PPP NCP records.
        -- 1.3.6.1.4.1.5504.4.1.9.2.1.26
        ipIfPppEnabled OBJECT-TYPE
            SYNTAX TruthValue
            MAX-ACCESS read-create
            STATUS current
            DESCRIPTION
                "This field is used to indicate that this IP interface is
                to be bound to a PPP interface.  When this object is set to
                'true', rows will be created in the pppNCPExtensionsTable,
                pppIfConfigTable, and pppIfTable.  When this object is set
                to 'false', these rows will be destroyed."
            REFERENCE
                "pppNCPExtensionsTable:  comPpp.mib
                pppIpConfigTable:       rfc1473.mib
                pppIpTable:             rfc1473.mib"
            DEFVAL { false }
            ::= { ipInterfaceEntry 26 }


-- ZHONE_KEYWORD_PROFILE_LABEL = ipaddrdynamic
-- ZHONE_KEYWORD_STORAGE_LABEL = IP_Interface_Record.ipaddrdynamic
-- ZHONE_KEYWORD_STORAGE_ORDER = 20
        -- 1.3.6.1.4.1.5504.4.1.9.2.1.27
        ipAddrDynamic OBJECT-TYPE
            SYNTAX INTEGER
                {
                static(1),
                ppp(2),
                dhcpclient(3),
                unnumbered(4),
                cpemgr(5)
                }
            MAX-ACCESS read-create
            STATUS current
            DESCRIPTION
                "This is the mode by which  the IP address is discovered
                by the system.
                STATIC - Means,The IP address is  Statically configured.
                DHCPCLIENT  - IP address discovered from DHCPCLIENT
                PPP - Use PPP to get IP address.
                UNNUMBERED - this is an unnumbered interface.
                CPEMGR - IP address configured by CPE Manager."
            DEFVAL { static }
            ::= { ipInterfaceEntry 27 }


-- ZHONE_KEYWORD_PROFILE_LABEL = dhcpserverenable
-- ZHONE_KEYWORD_STORAGE_LABEL = IP_Interface_Record.dhcpserverenable
-- ZHONE_KEYWORD_STORAGE_ORDER = 21
        -- 1.3.6.1.4.1.5504.4.1.9.2.1.28
        dhcpServerEnable OBJECT-TYPE
            SYNTAX TruthValue
            MAX-ACCESS read-create
            STATUS current
            DESCRIPTION
                "If this  field is set to  TRUE ,then
                ipAddrDynamic has to be STATIC and if and when
                Dhcp server is not enabled then ipAddrdynamic
                can set to STATIC,PPP or DHCPCLIENT."
            DEFVAL { false }
            ::= { ipInterfaceEntry 28 }


-- ZHONE_KEYWORD_PROFILE_LABEL = dhcpSubnetGroup
-- ZHONE_KEYWORD_STORAGE_LABEL = IP_Interface_Record.dhcpSubnetGroup
-- ZHONE_KEYWORD_STORAGE_ORDER = 22
        -- 1.3.6.1.4.1.5504.4.1.9.2.1.29
        dhcpSubnetGroup OBJECT-TYPE
            SYNTAX Integer32
            MAX-ACCESS read-write
            STATUS current
            DESCRIPTION
                "This is the DHCP Subnet group ID, it indicates which address
                pool grouping may be used for the CPE subnet.Needed to
                support the point-to-multipoint model."
            DEFVAL { '0'b }
            ::= { ipInterfaceEntry 29 }


-- ZHONE_KEYWORD_PROFILE_LABEL = unnumberedIndex
-- ZHONE_KEYWORD_STORAGE_LABEL = IP_Interface_Record.unnumberedIndex
-- ZHONE_KEYWORD_STORAGE_ORDER = 23
        -- 1.3.6.1.4.1.5504.4.1.9.2.1.30
        unnumberedIndex OBJECT-TYPE
            SYNTAX Integer32
            MAX-ACCESS read-write
            STATUS current
            DESCRIPTION
                "The index of the ip-unnumbered-record to use to obtain the
                local side Unnumbered Address. This is need in order to
                support the IP point-to-multipoint model."
            DEFVAL { '0'b }
            ::= { ipInterfaceEntry 30 }


-- ZHONE_KEYWORD_PROFILE_LABEL = mcastcontrollist
-- ZHONE_KEYWORD_STORAGE_LABEL = IP_Interface_Record.mcastControlList
-- ZHONE_KEYWORD_STORAGE_ORDER = 24
        -- 1.3.6.1.4.1.5504.4.1.9.2.1.31
        mcastControlList OBJECT-TYPE
            SYNTAX SnmpAdminString
            MAX-ACCESS read-create
            STATUS current
            DESCRIPTION
                "List of Mcast-control-ids this IP Interface record is associated
                with."
            ::= { ipInterfaceEntry 31 }


-- ZHONE_KEYWORD_PROFILE_LABEL = vlanid
-- ZHONE_KEYWORD_STORAGE_LABEL = IP_Interface_Record.vlanid
-- ZHONE_KEYWORD_STORAGE_ORDER = 25
        -- 1.3.6.1.4.1.5504.4.1.9.2.1.32
        vlanid OBJECT-TYPE
            SYNTAX Integer32 (0..4095)
            MAX-ACCESS read-create
            STATUS current
            DESCRIPTION
                "This is the Virtual LAN Identifier for the IP Interface.  If the
                VLAN ID specified is non-zero, all traffic destined to this
                interface should have the VLAN ID specified."
            DEFVAL { 0 }
            ::= { ipInterfaceEntry 32 }


-- ZHONE_KEYWORD_PROFILE_LABEL = maxVideoStreams
-- ZHONE_KEYWORD_STORAGE_LABEL = IP_Interface_Record.maxVideoStreams
-- ZHONE_KEYWORD_STORAGE_ORDER = 26
        -- 1.3.6.1.4.1.5504.4.1.9.2.1.33
        maxVideoStreams OBJECT-TYPE
            SYNTAX Unsigned32 (0..1024)
            MAX-ACCESS read-create
            STATUS current
            DESCRIPTION
                "This is the maximum number of unique multicast (video) streams
                that this interface has subscribed to."
            DEFVAL { 0 }
            ::= { ipInterfaceEntry 33 }


-- ZHONE_KEYWORD_PROFILE_LABEL = tosOption
-- ZHONE_KEYWORD_STORAGE_LABEL = IP_Interface_Record.tosOption
-- ZHONE_KEYWORD_STORAGE_ORDER = 27
        -- 1.3.6.1.4.1.5504.4.1.9.2.1.34
        tosOption OBJECT-TYPE
            SYNTAX INTEGER
                {
                tosOptionDisable(1),
                tosOptionOriginate(2),
                tosOptionAll(3)
                }
            MAX-ACCESS read-create
            STATUS current
            DESCRIPTION
                "Determines IP TOS Class-Of-Service bit setting on packets
                sent out this interface.  The setting is stored in the
                tosCOS field.
                     disable - COS setting is untouched.  For packets we
                               originate, COS value is set to 0.
                     originate - Load COS bits only if we originate packet.
                                 COS for packets routed through this interface
                                 are not affected.
                     all - Load COS bits on all packets."
            DEFVAL { tosOptionDisable }
            ::= { ipInterfaceEntry 34 }


-- ZHONE_KEYWORD_PROFILE_LABEL = tosCOS
-- ZHONE_KEYWORD_STORAGE_LABEL = IP_Interface_Record.tosCOS
-- ZHONE_KEYWORD_STORAGE_ORDER = 28
        -- 1.3.6.1.4.1.5504.4.1.9.2.1.35
        tosCOS OBJECT-TYPE
            SYNTAX Integer32 (0..7)
            MAX-ACCESS read-create
            STATUS current
            DESCRIPTION
                "The COS bit value to load based on tosOption setting."
            DEFVAL { 0 }
            ::= { ipInterfaceEntry 35 }


-- ZHONE_KEYWORD_PROFILE_LABEL = vlanCOS
-- ZHONE_KEYWORD_STORAGE_LABEL = IP_Interface_Record.vlanCOS
-- ZHONE_KEYWORD_STORAGE_ORDER = 29
        -- 1.3.6.1.4.1.5504.4.1.9.2.1.36
        vlanCOS OBJECT-TYPE
            SYNTAX Integer32 (0..7)
            MAX-ACCESS read-create
            STATUS current
            DESCRIPTION
                "COS value loaded into VLAN header.  Applicable only if
                the vlanid is non-zero."
            DEFVAL { 0 }
            ::= { ipInterfaceEntry 36 }


-- ZHONE_KEYWORD_PROFILE_LABEL = s-tagTPID
-- ZHONE_KEYWORD_STORAGE_LABEL = IP_Interface_Record.s_tagTPID
-- ZHONE_KEYWORD_STORAGE_ORDER = 30
        -- 1.3.6.1.4.1.5504.4.1.9.2.1.37
        ipStagTPID OBJECT-TYPE
            SYNTAX Integer32 (33024 | 34984 | 37120 | 37376)
            MAX-ACCESS read-create
            STATUS current
            DESCRIPTION
                "The value of the tag protocol identifier that is being used
                for QinQ packets.( 0x8100 is default)"
            DEFVAL { '8100'h }
            ::= { ipInterfaceEntry 37 }


-- ZHONE_KEYWORD_PROFILE_LABEL = s-tagId
-- ZHONE_KEYWORD_STORAGE_LABEL = IP_Interface_Record.s_tagId
-- ZHONE_KEYWORD_STORAGE_ORDER = 31
        -- 1.3.6.1.4.1.5504.4.1.9.2.1.38
        ipStagId OBJECT-TYPE
            SYNTAX Integer32 (0..4095)
            MAX-ACCESS read-create
            STATUS current
            DESCRIPTION
                "The s-tag value that we are expecting to put on
                packets that are Rxed on this interface."
            DEFVAL { 0 }
            ::= { ipInterfaceEntry 38 }


-- ZHONE_KEYWORD_PROFILE_LABEL = s-tagIdCOS
-- ZHONE_KEYWORD_STORAGE_LABEL = IP_Interface_Record.s_tagIdCOS
-- ZHONE_KEYWORD_STORAGE_ORDER = 32
        -- 1.3.6.1.4.1.5504.4.1.9.2.1.39
        ipStagIdCOS OBJECT-TYPE
            SYNTAX Integer32 (0..7)
            MAX-ACCESS read-create
            STATUS current
            DESCRIPTION
                "The s-tag COS to be used when doing s-tag intertion."
            DEFVAL { 0 }
            ::= { ipInterfaceEntry 39 }


--  ZHONE_KEYWORD_PROFILE_LABEL = ipOnDemandStatsEnabled
-- ZHONE_KEYWORD_STORAGE_LABEL = IP_Interface_Record.ipOnDemandStatsEnabled
-- ZHONE_KEYWORD_STORAGE_ORDER = 33
        -- 1.3.6.1.4.1.5504.4.1.9.2.1.40
        ipOnDemandStatsEnabled OBJECT-TYPE
            SYNTAX TruthValue
            MAX-ACCESS read-create
            STATUS current
            DESCRIPTION
                "If true, the on-demand stats collection for this Ip interface will be enabled."
            DEFVAL { false }
            ::= { ipInterfaceEntry 40 }


        -- 1.3.6.1.4.1.5504.4.1.9.5
        ipIfAliasTable OBJECT-TYPE
            SYNTAX SEQUENCE OF IpIfAliasEntry
            MAX-ACCESS not-accessible
            STATUS current
            DESCRIPTION
                "The table containing alias addresses for ip interfaces."
            ::= { ipRecordObjects 5 }


        -- 1.3.6.1.4.1.5504.4.1.9.5.1
        ipIfAliasEntry OBJECT-TYPE
            SYNTAX IpIfAliasEntry
            MAX-ACCESS not-accessible
            STATUS current
            DESCRIPTION
                "Each row is indexed by an ifIndex and an
                ip alias address.  At a mininum the ipIfAlias
                Addr must be present to create a row."
            INDEX { ifIndex, ipIfAliasAddr }
            ::= { ipIfAliasTable 1 }


        IpIfAliasEntry ::=
            SEQUENCE {
                ipIfAliasAddr
                    IpAddress,
                ipIfAliasRowStatus
                    ZhoneRowStatus,
                ipIfAliasNetMask
                    IpAddress,
                ipIfAliasBcastAddr
                    IpAddress
             }

        -- 1.3.6.1.4.1.5504.4.1.9.5.1.1
        ipIfAliasAddr OBJECT-TYPE
            SYNTAX IpAddress
            MAX-ACCESS not-accessible
            STATUS current
            DESCRIPTION
                "The ip alias address."
            ::= { ipIfAliasEntry 1 }


        -- 1.3.6.1.4.1.5504.4.1.9.5.1.2
        ipIfAliasRowStatus OBJECT-TYPE
            SYNTAX ZhoneRowStatus
            MAX-ACCESS read-create
            STATUS current
            DESCRIPTION
                "The row status for creating and destroying ip aliases. To create
                a row, both the ifIndex and the ipIfAliasAddr must be
                provided."
            ::= { ipIfAliasEntry 2 }


-- ZHONE_KEYWORD_PROFILE_LABEL = netmask
-- ZHONE_KEYWORD_STORAGE_LABEL = IP_Alias_Record.netmask
-- ZHONE_KEYWORD_STORAGE_ORDER = 1
        -- 1.3.6.1.4.1.5504.4.1.9.5.1.3
        ipIfAliasNetMask OBJECT-TYPE
            SYNTAX IpAddress
            MAX-ACCESS read-create
            STATUS current
            DESCRIPTION
                "The subnet mask associated with the IP address of this
                interface alias entry.  The value of the mask is an IP
                address with all the network bits set to 1 and all the
                hosts bits set to 0."
            DEFVAL { '00000000'h }
            ::= { ipIfAliasEntry 3 }


-- ZHONE_KEYWORD_PROFILE_LABEL = bcastaddr
-- ZHONE_KEYWORD_STORAGE_LABEL = IP_Alias_Record.bcastaddr
-- ZHONE_KEYWORD_STORAGE_ORDER = 2
        -- 1.3.6.1.4.1.5504.4.1.9.5.1.4
        ipIfAliasBcastAddr OBJECT-TYPE
            SYNTAX IpAddress
            MAX-ACCESS read-create
            STATUS current
            DESCRIPTION
                "The IP broadcast address used for sending datagrams on the
                (logical) interface associated with the IP address of this
                interface alias entry.  "
            DEFVAL { '00000000'h }
            ::= { ipIfAliasEntry 4 }


        -- 1.3.6.1.4.1.5504.4.1.10
        ipUnnumbered OBJECT-IDENTITY
            STATUS deprecated
            DESCRIPTION
                "The user can specify the name of the interface to
                borrow for the local IP address of P-T-P links.

                The user sets ipUnnumberedEnabled to true and
                then sets the ipUnnumberedInterfaceIndex to the
                ifIndex of the ip-interface-record which contains
                the static address they want to use.  This static
                address will be used for all unnumbered interfaces
                in the system."
            ::= { zhoneIp 10 }


        -- 1.3.6.1.4.1.5504.4.1.10.1
        ipUnnumberedEnabled OBJECT-TYPE
            SYNTAX TruthValue
            MAX-ACCESS read-write
            STATUS deprecated
            DESCRIPTION
                "If set to True, this profile in enabled and the unit
                can be configured to support unnumbered point to
                point interfaces. If set to False, unnumbered
                interface support is disabled."
            DEFVAL { false }
            ::= { ipUnnumbered 1 }


        -- 1.3.6.1.4.1.5504.4.1.10.2
        ipUnnumberedInterfaceIndex OBJECT-TYPE
            SYNTAX InterfaceIndexOrZero
            MAX-ACCESS read-write
            STATUS deprecated
            DESCRIPTION
                "The name of the interface use to 'borrow' the IP
                address of for unnumbered interfaces. The source IP
                address of all outgoing packets on unnumbered
                interfaces will use the IP address of this interface."
            DEFVAL { 0 }
            ::= { ipUnnumbered 2 }


        -- 1.3.6.1.4.1.5504.4.1.14
        ipUnnumberedObjects OBJECT IDENTIFIER ::= { zhoneIp 14 }


        -- 1.3.6.1.4.1.5504.4.1.14.1
        ipUnnumberedObjectNext OBJECT-TYPE
            SYNTAX Integer32
            MAX-ACCESS read-only
            STATUS current
            DESCRIPTION
                "A hint for the next free ipUnnumberedIndex that can be used."
            ::= { ipUnnumberedObjects 1 }


        -- 1.3.6.1.4.1.5504.4.1.14.2
        ipUnnumberedTable OBJECT-TYPE
            SYNTAX SEQUENCE OF IpUnnumberedEntry
            MAX-ACCESS not-accessible
            STATUS current
            DESCRIPTION
                "The current set of ipUnnumbered binding for this box."
            ::= { ipUnnumberedObjects 2 }


        -- 1.3.6.1.4.1.5504.4.1.14.2.1
        ipUnnumberedEntry OBJECT-TYPE
            SYNTAX IpUnnumberedEntry
            MAX-ACCESS not-accessible
            STATUS current
            DESCRIPTION
                "An ipUnnumberedEntry."
            INDEX { ipUnnumberedIndex }
            ::= { ipUnnumberedTable 1 }


        IpUnnumberedEntry ::=
            SEQUENCE {
                ipUnnumberedIndex
                    Integer32,
                ipUnnumberedRowStatus
                    ZhoneRowStatus,
                ipUnnumberedIfIName
                    InterfaceIndex
             }

        -- 1.3.6.1.4.1.5504.4.1.14.2.1.1
        ipUnnumberedIndex OBJECT-TYPE
            SYNTAX Integer32 (1..255)
            MAX-ACCESS not-accessible
            STATUS current
            DESCRIPTION
                "This value is only used to identify this particular
                entry in the table, it is not externally visible!"
            ::= { ipUnnumberedEntry 1 }


        -- 1.3.6.1.4.1.5504.4.1.14.2.1.2
        ipUnnumberedRowStatus OBJECT-TYPE
            SYNTAX ZhoneRowStatus
            MAX-ACCESS read-create
            STATUS current
            DESCRIPTION
                "RowStatus is used to create/delete entries in
                the table."
            ::= { ipUnnumberedEntry 2 }


-- ZHONE_KEYWORD_PROFILE_LABEL = ipUnnumberedInterfaceName
-- ZHONE_KEYWORD_STORAGE_LABEL = IP_Unnumbered_Record.ipUnnumberedInterfaceName
-- ZHONE_KEYWORD_STORAGE_ORDER = 1
        -- 1.3.6.1.4.1.5504.4.1.14.2.1.3
        ipUnnumberedIfIName OBJECT-TYPE
            SYNTAX InterfaceIndex
            MAX-ACCESS read-write
            STATUS current
            DESCRIPTION
                "This value specifies where to borrow the local IP address
                of the P-T-M link."
            DEFVAL { '1'b }
            ::= { ipUnnumberedEntry 3 }



    END

--
-- comIpRec.mib
--
