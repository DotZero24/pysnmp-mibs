--
-- phyVaIf.mib
-- MIB generated by MG-SOFT Visual MIB Builder Version 3.0 Build 285
-- Monday, November 16, 2009 at 10:24:53
--

    Zhone-VOICE-ANALOG-IF-MIB DEFINITIONS ::= BEGIN

        IMPORTS
            ifIndex, InterfaceIndex
                FROM IF-MIB
            Integer32, Counter32, OBJECT-TYPE, MODULE-IDENTITY
                FROM SNMPv2-SMI
            TruthValue
                FROM SNMPv2-TC
            zhonePhysical, zhoneModules
                FROM Zhone
            ZhoneRowStatus
                FROM Zhone-TC;


--
--
--
-- --
--
-- --
-- --
-- --
--
--
--
--
--
--
--
--
--
        -- 1.3.6.1.4.1.5504.6.13
        zhoneVoiceAnalogIf-MIB MODULE-IDENTITY
            LAST-UPDATED "200911171030Z"		-- November 16, 2009 at 10:30 GMT
            ORGANIZATION
                "Zhone Technologies, Inc."
            CONTACT-INFO
                "Postal:
                Zhone Technologies, Inc.
                @Zhone Way
                7001 Oakport
                Oakland, Ca 94621

                Toll-Free 877-ZHONE20 (+1 877-946-6320)
                Tel: +1 510-777-7000
                Fax: +1 510-777-7001
                Email: support@zhone.com
                "
            DESCRIPTION
                "Analog Voice Interface MIB module.
                This MIB manages the E&M, FXO, FXS
                Interfaces in the Zhone's product.
                "
            REVISION "200905050236Z"		-- May 05, 2009 at 02:36 GMT
            DESCRIPTION
                "V01.00.10 - Added new field if-cfg-loop-current in table analog-if-cfg-profile"
            REVISION "200803261745Z"		-- March 26, 2008 at 17:45 GMT
            DESCRIPTION
                "Add ebs to zhoneValIfCfgLineType field."
            REVISION "200711010230Z"		-- November 01, 2007 at 02:30 GMT
            DESCRIPTION
                "V01.00.08 - Edited IfCfgImpedance field descriptions that ohmscomplex1 and ohmscomplex2 are Not Supported."
            REVISION "200509061114Z"		-- September 06, 2005 at 11:14 GMT
            DESCRIPTION
                "Deprecate zhonePotsRingTable. Move to zhoneVoiceRingTable in genVoiceStatMib."
            REVISION "200508081500Z"		-- August 08, 2005 at 15:00 GMT
            DESCRIPTION
                "Add zhonePotsRing table."
            REVISION "200505111520Z"		-- May 11, 2005 at 15:20 GMT
            DESCRIPTION
                "Changed zhoneVaIfCfgImpedance default value description from ohms900Complex to ohms600Complex."
            REVISION "200505021722Z"		-- May 02, 2005 at 17:22 GMT
            DESCRIPTION
                "Add default value descriptions for zhoneVAIfCfgImpedance, zhoneVAIffgReceivelp, zhoneVaIfCfgTransmitTlp."
            REVISION "200410071134Z"		-- October 07, 2004 at 11:34 GMT
            DESCRIPTION
                "zhoneVaIfEMCfgEntry
                change SignalType, CfgOperation and DialType from read-write to read-only"
            REVISION "200110101119Z"		-- October 10, 2001 at 11:19 GMT
            DESCRIPTION
                "V01.00.02 - Removed Mark-Up for the zhoneVaIfFXSTimingDigitDuration and zhoneVaIfFXSTimingInterDigitDuration OIDs. Also added comment for the zhoneVaIfStatusSignalError OID."
            REVISION "200102151852Z"		-- February 15, 2001 at 18:52 GMT
            DESCRIPTION
                "V01.00.01 - Add DEFVAL for TruthValue types."
            REVISION "200009121421Z"		-- September 12, 2000 at 14:21 GMT
            DESCRIPTION
                "V01.00.00 - Initial Release"
            ::= { zhoneModules 13 }
--
--
-- Overview of Analog Voice interface MIB
--
-- The Analog Voice interface MIB provides the standard configuration,
-- timing parameters and telephony hook, ring status information on zhone's
-- Analog Voice interface implementation. The following groups
-- are managed:
-- 1) Analog interface general group
-- 2) E&M (recEive and transMit) interface group
-- 3) FXO (Foreign Exchange Office) interface group
-- 4) FXS (Foreign Exchange Station) interface group
--
-- ifEntry for an Analog Voice Interface
--
-- The ifEntry for an Analog Voice Interface supports the
-- ifGeneralInformationGroup of zhone IF-MIB.
--
-- ifTable           Comments
-- ==============    =====================================================
-- ifIndex           Each Analog telephony interface is represented by an
--                   ifEntry.
-- ifDescr           Textual port description.
-- ifType            The IANA value of voiceEM(100), voiceFXO(101) and
--                   voiceFXS(102).
-- ifSpeed           contains a zero value.
-- ifPhysAddress     contains an octet string of zero length.
--
-- ifAdminStatus     The desired administrative status of the
--                   Analog Telephony interface port.
-- ifOperStatus      The current operational status of the Analog Telephony
--                   interface port. Note that dormant(5) is explicitly being
--                   used as defined in RFC 1573.
-- ifLastChange      Refer to RFC 1573.
-- ifLinkUpDownTrapEnable
--                    Refer to RFC 1573.
-- ifConnectorPresent
--                  Refer to RFC 1573.
-- ifHighSpeed       contains a zero value.
-- ifName            Refer to RFC 1573.
--
--
--
--
--




--
-- Node definitions
--

--  To Create Mib Handler file ( run in /vob/mibs/src):
--  /vob/EPILOGUE/binaries/emissary/solaris/mibcomp
--  rfc1907.mib iftype.mib rfc2233.mib Zhone.mib Zhone-TC.mib
--  -stub -o "MibHdlr.c"
        -- 1.3.6.1.4.1.5504.5.6
        zhoneVaIfObjects OBJECT IDENTIFIER ::= { zhonePhysical 6 }


        -- 1.3.6.1.4.1.5504.5.6.1
        zhoneVaIfGeneralObjects OBJECT IDENTIFIER ::= { zhoneVaIfObjects 1 }


-- ****************************************************************************
--  The Analog Voice General Interface Group
-- ****************************************************************************
-- [1] Analog Voice Interface Standard Configuration Table
-- [2] Analog Voice Interface Status Table
--
--
--
-- ****************************************************************************
-- The Analog Voice Interface Standard Configuration Table
-- ****************************************************************************
--
--
        -- 1.3.6.1.4.1.5504.5.6.1.1
        zhoneVaIfCfgTable OBJECT-TYPE
            SYNTAX SEQUENCE OF ZhoneVaIfCfgEntry
            MAX-ACCESS not-accessible
            STATUS current
            DESCRIPTION
                "The Analog Voice Standard Configuration Table. It contains
                the standard configuration information of the analog
                telephony interface.
                "
            ::= { zhoneVaIfGeneralObjects 1 }


        -- 1.3.6.1.4.1.5504.5.6.1.1.1
        zhoneVaIfCfgEntry OBJECT-TYPE
            SYNTAX ZhoneVaIfCfgEntry
            MAX-ACCESS not-accessible
            STATUS current
            DESCRIPTION
                "An entry in the configuration table for each voice analog
                interface. The entry is created when the voice analog
                hardware is detected.
                "
            INDEX { ifIndex }
            ::= { zhoneVaIfCfgTable 1 }


        ZhoneVaIfCfgEntry ::=
            SEQUENCE {
                zhoneVaIfCfgImpedance
                    INTEGER,
                zhoneVaIfCfgReceiveTLP
                    INTEGER,
                zhoneVaIfCfgTransmitTLP
                    INTEGER,
                zhoneVaIfCfgTrunkConditioning
                    INTEGER,
                zhoneVaIfCfgLineType
                    INTEGER,
                zhoneVaIfCfgIntegratedDSP
                    TruthValue,
                zhoneVaIfCfgLineCapabilities
                    BITS,
                zhoneVaIfCfgMaintenanceMode
                    INTEGER,
                zhoneVaIfCfgPCMEncoding
                    INTEGER,
                zhoneVaIfCfgReceiveTLPNum
                    INTEGER,
                zhoneVaIfCfgTransmitTLPNum
                    INTEGER,
                zhoneVaIfCfgLoopCurrent
                    INTEGER,
                zhoneVaIfCfgRingVoltage
                    INTEGER
             }

--
--
        -- 1.3.6.1.4.1.5504.5.6.1.1.1.1
        zhoneVaIfCfgImpedance OBJECT-TYPE
            SYNTAX INTEGER
                {
                other(1),
                ohms600Real(2),
                ohms600Complex(3),
                ohms900Complex(4),
                ohmsComplex1(5),
                ohmsComplex2(6)
                }
            MAX-ACCESS read-write
            STATUS current
            DESCRIPTION
                "Specifies the terminating impedance of voice analog
                interfaces.
                other          - none of the following; arbitrary,
                                 within limits, for special cases.
                ohms600Real    - 600 Ohms.
                ohms600Complex - 600 Ohms + 2.16uF
                ohms900Complex - 900 Ohms + 2.16uF.
                ohmsComplex1   - Not Supported.
                ohmsComplex2   - Not Supported.
                Default value is ohms600Complex.
                "
            ::= { zhoneVaIfCfgEntry 1 }


--
        -- 1.3.6.1.4.1.5504.5.6.1.1.1.2
        zhoneVaIfCfgReceiveTLP OBJECT-TYPE
            SYNTAX INTEGER
                {
                fxsRtlpN9db(1),
                fxsRtlpN8db(2),
                fxsRtlpN7db(3),
                fxsRtlpN6db(4),
                fxsRtlpN5db(5),
                fxsRtlpN4db(6),
                fxsRtlpN3db(7),
                fxsRtlpN2db(8),
                fxsRtlpN1db(9),
                fxsRtlp0db(10),
                fxsRtlp1db(11),
                fxsRtlp2db(12),
                fxsRtlp3db(13),
                rTlpNummeric(14)
                }
            MAX-ACCESS read-write
            STATUS current
            DESCRIPTION
                "  Receive Transmission Level Point (RTLP) settings control the amount gain or loss added to the incoming signal after it is decoded to analog.
                to increase the signal level  set the RTLP setting to higher values. The default is fxsRtlpN6db.  Rtlpnummeric selects entering the actual
                value in zhoneVaIFCfgReceiveTLPNum."
            ::= { zhoneVaIfCfgEntry 2 }


--
        -- 1.3.6.1.4.1.5504.5.6.1.1.1.3
        zhoneVaIfCfgTransmitTLP OBJECT-TYPE
            SYNTAX INTEGER
                {
                fxsTtlp9db(1),
                fxsTtlp8db(2),
                fxsTtlp7db(3),
                fxsTtlp6db(4),
                fxsTtlp5db(5),
                fxsTtlp4db(6),
                fxsTtlp3db(7),
                fxsTtlp2db(8),
                fxsTtlp1db(9),
                fxsTtlp0db(10),
                fxsTtlpN1db(11),
                fxsTtlpN2db(12),
                fxsTtlpN3db(13),
                tTlpNummeric(14)
                }
            MAX-ACCESS read-write
            STATUS current
            DESCRIPTION
                " In case of FXO, it specifies FXO attenuation and default value is 0dB(fxsTtlp0db).
                In case of FXS this setting  controls the amount of gain  or loss added
                to a voice signal from CPE  before it is encoded to digital PCM.
                To increase the signal level, reduce the TTLP setting to lower value.
                The default is fxsTtlp0db. Ttlpnummeric selects entering the actual
                value in zhoneVaIFCfgTransmitTLPNum."
            ::= { zhoneVaIfCfgEntry 3 }


--
        -- 1.3.6.1.4.1.5504.5.6.1.1.1.4
        zhoneVaIfCfgTrunkConditioning OBJECT-TYPE
            SYNTAX INTEGER
                {
                off(1),
                idle(2),
                busy(3)
                }
            MAX-ACCESS read-write
            STATUS current
            DESCRIPTION
                "    The trunk conditioning setting specifies whether the FXS/FXO port should send the idle pattern to the network upon declaration of a Carrier Group Alarm(CGA) on the WAN link to which the port is assigned . In most cases leave the trunk conditioning  setting at its default setting(off)."
            ::= { zhoneVaIfCfgEntry 4 }


--
        -- 1.3.6.1.4.1.5504.5.6.1.1.1.5
        zhoneVaIfCfgLineType OBJECT-TYPE
            SYNTAX INTEGER
                {
                fxs(1),
                fxo(2),
                em(3),
                ebs(4)
                }
            MAX-ACCESS read-only
            STATUS current
            DESCRIPTION
                "The Card type FXS, FXO, EM, EBS.
                Entries in the table will be created or deleted on the basis of  zhoneVaIfCfgLineType
                in the zhoneVaIfCfgTable and we are not using rowStatus entry for this .
                The tables which are augument to the above mentioned table will be created by RP
                only and they can be read or modified by user later."
            DEFVAL { fxs }
            ::= { zhoneVaIfCfgEntry 5 }


--
        -- 1.3.6.1.4.1.5504.5.6.1.1.1.6
        zhoneVaIfCfgIntegratedDSP OBJECT-TYPE
            SYNTAX TruthValue
            MAX-ACCESS read-only
            STATUS current
            DESCRIPTION
                "Indicates whether the interface has an integrated
                Digital Signal processing (DSP) unit.
                "
            DEFVAL { false }
            ::= { zhoneVaIfCfgEntry 6 }


--
        -- 1.3.6.1.4.1.5504.5.6.1.1.1.7
        zhoneVaIfCfgLineCapabilities OBJECT-TYPE
            SYNTAX BITS
                {
                fxs(0),
                fxo(1),
                em(2)
                }
            MAX-ACCESS read-only
            STATUS current
            DESCRIPTION
                "The Interface types supported on this interface. This is a bit-map of possible
                types. This variable can be used to determine zhoneVaIfCfgLineType."
            ::= { zhoneVaIfCfgEntry 7 }


--
        -- 1.3.6.1.4.1.5504.5.6.1.1.1.8
        zhoneVaIfCfgMaintenanceMode OBJECT-TYPE
            SYNTAX INTEGER
                {
                off(1),
                ifDigitalLoopback(2),
                ifAnalogLoopback(3)
                }
            MAX-ACCESS read-write
            STATUS current
            DESCRIPTION
                "Indicates the maintenance modes of the Analog voice interface.


                 loopback options for Fxo and Fxs cards (Zhone specific)
                                                -------------------------------------------------------
                                                                                        CODEC
                                                         T1/E1            DS0     ---------------------------
                                                        <-------         <--------------- -----------------
                                                Network          PCM Bus          ^   Digital            ^
                                                                                  |   to analog Converter|
                                                                                  |                      |
                                                                                  |                      |
                                                                                  |                      |
                                                                              Digital loopback          Analog loopback
                                                                                  |                      |
                                                        ------->          -------- ->--------------------------------------------->

                off(1)  - the interface is not in maintenance mode.

                ifDigitalLoopback(2) This mode is set by the managed system to perform the
                Digital loopback test.

                ifAnalogLoopback(3) This mode is set by the managed system to perform the
                Analog loopback test. "
            ::= { zhoneVaIfCfgEntry 8 }


--
        -- 1.3.6.1.4.1.5504.5.6.1.1.1.9
        zhoneVaIfCfgPCMEncoding OBJECT-TYPE
            SYNTAX INTEGER
                {
                alaw(1),
                mulaw(2)
                }
            MAX-ACCESS read-write
            STATUS current
            DESCRIPTION
                "alaw(1) :for E1
                mulaw(2) : for T1 "
            ::= { zhoneVaIfCfgEntry 9 }


--
        -- 1.3.6.1.4.1.5504.5.6.1.1.1.10
        zhoneVaIfCfgReceiveTLPNum OBJECT-TYPE
            SYNTAX INTEGER (-160..85)
            UNITS "dB/10"
            MAX-ACCESS read-write
            STATUS current
            DESCRIPTION
                "Receive Transmission Level Point (RTLP) settings control the amount gain or loss added to the incoming signal after it is decoded to analog.
                to incrase the signal level set the RTLP setting to higher values. The default is 0 dB."
            DEFVAL { '0'b }
            ::= { zhoneVaIfCfgEntry 10 }


        -- 1.3.6.1.4.1.5504.5.6.1.1.1.11
        zhoneVaIfCfgTransmitTLPNum OBJECT-TYPE
            SYNTAX INTEGER (-175..70)
            UNITS "dB/10"
            MAX-ACCESS read-write
            STATUS current
            DESCRIPTION
                "Transmit Transmission Level Point controls the amount of gain or loss added
                to a voice signal from CPE  before it is encoded to digital PCM.
                To increase the signal level, reduce the TTLP setting to lower value.
                The default is 0dB."
            DEFVAL { 0 }
            ::= { zhoneVaIfCfgEntry 11 }


        -- 1.3.6.1.4.1.5504.5.6.1.1.1.12
        zhoneVaIfCfgLoopCurrent OBJECT-TYPE
            SYNTAX INTEGER (20..44)
            UNITS "mA"
            MAX-ACCESS read-write
            STATUS current
            DESCRIPTION
                "To set the loop current value for a subscriber"
            DEFVAL { 30 }
            ::= { zhoneVaIfCfgEntry 12 }


        -- 1.3.6.1.4.1.5504.5.6.1.1.1.13
        zhoneVaIfCfgRingVoltage OBJECT-TYPE
            SYNTAX INTEGER
                {
                b85vrms(1),
                b75vrms(2),
                b92vrms(3)
                }
            MAX-ACCESS read-write
            STATUS current
            DESCRIPTION
                "To set the ring voltage for a subscriber."
            DEFVAL { b85vrms }
            ::= { zhoneVaIfCfgEntry 13 }


-- ****************************************************************************
-- The Analog Voice Interface Status Table
-- ****************************************************************************
--
        -- 1.3.6.1.4.1.5504.5.6.1.2
        zhoneVaIfStatusTable OBJECT-TYPE
            SYNTAX SEQUENCE OF ZhoneVaIfStatusEntry
            MAX-ACCESS not-accessible
            STATUS current
            DESCRIPTION
                "The Analog Voice Status Table.  It contains general
                information about the status of Analog Telephony interface
                including the error statistics.
                "
            ::= { zhoneVaIfGeneralObjects 2 }


        -- 1.3.6.1.4.1.5504.5.6.1.2.1
        zhoneVaIfStatusEntry OBJECT-TYPE
            SYNTAX ZhoneVaIfStatusEntry
            MAX-ACCESS not-accessible
            STATUS current
            DESCRIPTION
                "An entry in the status table for each Analog voice interface.
                "
            AUGMENTS { zhoneVaIfCfgEntry }
            ::= { zhoneVaIfStatusTable 1 }


        ZhoneVaIfStatusEntry ::=
            SEQUENCE {
                zhoneVaIfStatusSignalErrors
                    Counter32,
                zhoneVaIfStatusInfoType
                    INTEGER
             }

-- Not Supported in the current release.
-- This needs to be changed when this MIB variable is supported.
        -- 1.3.6.1.4.1.5504.5.6.1.2.1.1
        zhoneVaIfStatusSignalErrors OBJECT-TYPE
            SYNTAX Counter32
            MAX-ACCESS read-only
            STATUS current
            DESCRIPTION
                "Accumulated number of signaling protocol errors that are
                detected in the interface since system startup."
            ::= { zhoneVaIfStatusEntry 1 }


--
        -- 1.3.6.1.4.1.5504.5.6.1.2.1.2
        zhoneVaIfStatusInfoType OBJECT-TYPE
            SYNTAX INTEGER
                {
                notype(1),
                voice(2),
                g3Fax(3)
                }
            MAX-ACCESS read-only
            STATUS current
            DESCRIPTION
                "The information transfer services for the current
                call.
                none     - no information transfer service, this is set befgore the first call is made on the interface.
                voice    - analog voice.
                g3Fax    - Group 3 FAX.
                "
            ::= { zhoneVaIfStatusEntry 2 }


        -- 1.3.6.1.4.1.5504.5.6.2
        zhoneVaIfFXSObjects OBJECT IDENTIFIER ::= { zhoneVaIfObjects 2 }


-- ****************************************************************************
-- The Foreign Exchange Station (FXS) Standard Configuration Table
-- ****************************************************************************
--
-- This table is used to configure the FXS signaling type, Ring frequency
--
        -- 1.3.6.1.4.1.5504.5.6.2.1
        zhoneVaIfFXSCfgTable OBJECT-TYPE
            SYNTAX SEQUENCE OF ZhoneVaIfFXSCfgEntry
            MAX-ACCESS not-accessible
            STATUS current
            DESCRIPTION
                "The FXS standard configuration table. It contains
                FXS configuration parameters, one entry per FXS interface.
                The configuration information of this table is set by
                hardware with its default setting or CLI during the hardware
                installation time.
                "
            ::= { zhoneVaIfFXSObjects 1 }


        -- 1.3.6.1.4.1.5504.5.6.2.1.1
        zhoneVaIfFXSCfgEntry OBJECT-TYPE
            SYNTAX ZhoneVaIfFXSCfgEntry
            MAX-ACCESS not-accessible
            STATUS current
            DESCRIPTION
                "An entry in the standard configuration table for
                each FXS interface."
            INDEX { ifIndex }
            ::= { zhoneVaIfFXSCfgTable 1 }


        ZhoneVaIfFXSCfgEntry ::=
            SEQUENCE {
                zhoneVaIfFXSCfgSignalType
                    INTEGER,
                zhoneVaIfFXSRingFrequency
                    INTEGER,
                zhoneVaIfFXSRingBack
                    INTEGER
             }

--
--
        -- 1.3.6.1.4.1.5504.5.6.2.1.1.1
        zhoneVaIfFXSCfgSignalType OBJECT-TYPE
            SYNTAX INTEGER
                {
                fxsLoopStart(1),
                fxsGroundStart(2),
                fxsLoopStartFd(3),
                fxsGroundStartAutomatic(4),
                fxsGroundStartImmediate(5),
                fxsdnLoopStart(6),
                fxsdnLoopStartFd(7),
                fxsdnGroundStart(8),
                fxsdnGroundStartImmediate(9),
                fxsdnwinkLoopStart(10),
                fxsdnwinkLoopStartFd(11),
                fxsdnwinkGroundStart(12),
                fxsdnwinkGroundStartImmediate(13),
                fxstr08SingleParty(14),
                fxstr08UniversalVoiceGrade(15),
                fxstr08UniversalVoiceGradeAutomatic(16)
                }
            MAX-ACCESS read-write
            STATUS current
            DESCRIPTION
                "the signaling type of FXS interface.
                fxsLoopStart   - loop start.
                fxsGroundStart - ground start.
                fxsLoopStartFd
                fxsGroundStartAutomatic - Used with equipment requiring fast response time to the Central Office.
                fxsGroundStartImmediate - Used with equipment requiring fast response time to the station or PBX.
                fxsdnLoopStart- loop start in fxsdn mode
                fxsdnLoopStartFd
                fxsdnGroundStart- Ground start in fxsdn mode
                fxsdnGroundStartImmediate - Ground start immediate in fxsdn mode
                fxsdnwinkLoopStart - loop start in fxsdnwink (foreign exchange
                                     subscriber - defined wink start operation) this
                                     option proved the same type of signalling as
                                     FXSDN and provides 150 millisecond delay then
                                     200 ms wink ack to the central office when fxs port sees an off hook condition from central office .
                                     The system requires a ringing generator for this option.
                fxsdnwinkLoopStartFd
                fxsdnwinkGroundStart-  Ground start in FXSDNWINK mode
                fxsdnwinkGroundStartImmediate - Ground start immediate in FXSDNWINK mode.
                fxstr08SingleParty - TR08 is Frame format signalling and data link as defined in TR-TSY-00008 Mode 1
                                     for circuits using AT & T SLC-96 facilities.
                                     this option is for single party service ,
                                     this option connects the port to one way out going trunks from a PBX , CENTEREX, key system , ot telephone set to an SLC channel.
                                     The SLC96 mode also must be active on the associated WAN interface.
                fxstr08UniversalVoiceGrade - Toll quality voice for SLC-96
                fxstr08UniversalVoiceGradeAutomatic- Used with some non - Bell switches for SLC-96


                The default value of this object is fxsLoopStart(1).
                "
            ::= { zhoneVaIfFXSCfgEntry 1 }


-- --
--
        -- 1.3.6.1.4.1.5504.5.6.2.1.1.2
        zhoneVaIfFXSRingFrequency OBJECT-TYPE
            SYNTAX INTEGER
                {
                ringFrequency25(1),
                ringFrequency50(2),
                ringFrequency20(3),
                ringFrequency30(4)
                }
            MAX-ACCESS read-write
            STATUS current
            DESCRIPTION
                "the ring  frequency to be used in the FXS interface.
                ringFrequency25  - ring frequency 25 Hertz.
                ringFrequency50  - ring frequency 50 Hertz.
                ringFrequency20  - ring frequency 20 Hertz.(Default)
                ringFrequency30  - ring frequency 30 Hertz.
                "
            ::= { zhoneVaIfFXSCfgEntry 2 }


-- --
        -- 1.3.6.1.4.1.5504.5.6.2.1.1.3
        zhoneVaIfFXSRingBack OBJECT-TYPE
            SYNTAX INTEGER
                {
                on(1),
                off(2)
                }
            MAX-ACCESS read-write
            STATUS current
            DESCRIPTION
                "the ring back is requested if this variable is set to on."
            ::= { zhoneVaIfFXSCfgEntry 3 }


-- ****************************************************************************
-- The Foreign Exchange Station (FXS) interface Status Table
-- ****************************************************************************
--
        -- 1.3.6.1.4.1.5504.5.6.2.2
        zhoneVaIfFXSStatusTable OBJECT-TYPE
            SYNTAX SEQUENCE OF ZhoneVaIfFXSStatusEntry
            MAX-ACCESS not-accessible
            STATUS current
            DESCRIPTION
                "The Foreign Exchange Station (FXS) interface Status Table.
                It contains hook status, ring active and other states of
                the interface.
                "
            ::= { zhoneVaIfFXSObjects 2 }


        -- 1.3.6.1.4.1.5504.5.6.2.2.1
        zhoneVaIfFXSStatusEntry OBJECT-TYPE
            SYNTAX ZhoneVaIfFXSStatusEntry
            MAX-ACCESS not-accessible
            STATUS current
            DESCRIPTION
                "An entry in the status table for each FXS interface.
                "
            AUGMENTS { zhoneVaIfFXSCfgEntry }
            ::= { zhoneVaIfFXSStatusTable 1 }


        ZhoneVaIfFXSStatusEntry ::=
            SEQUENCE {
                zhoneVaIfFXSHookStatus
                    INTEGER,
                zhoneVaIfFXSRingActive
                    TruthValue,
                zhoneVaIfFXSRingGround
                    TruthValue,
                zhoneVaIfFXSTipGround
                    TruthValue
             }

--
        -- 1.3.6.1.4.1.5504.5.6.2.2.1.1
        zhoneVaIfFXSHookStatus OBJECT-TYPE
            SYNTAX INTEGER
                {
                onHook(1),
                offHook(2)
                }
            MAX-ACCESS read-only
            STATUS current
            DESCRIPTION
                "This object contains the hook status of FXS interface.
                onHook - the connected equipment(e.g., phone) is onHook.
                offHook - the connected equipment is offHook.
                "
            ::= { zhoneVaIfFXSStatusEntry 1 }


--
        -- 1.3.6.1.4.1.5504.5.6.2.2.1.2
        zhoneVaIfFXSRingActive OBJECT-TYPE
            SYNTAX TruthValue
            MAX-ACCESS read-only
            STATUS current
            DESCRIPTION
                "This object contains the outgoing ring active indication. If
                the object value is true, then the interface is currently
                generating ring out to the Key Telephone System (KTS) or
                Plain Old Telephone (POT); otherwise, it doesn't.
                "
            DEFVAL { false }
            ::= { zhoneVaIfFXSStatusEntry 2 }


--
        -- 1.3.6.1.4.1.5504.5.6.2.2.1.3
        zhoneVaIfFXSRingGround OBJECT-TYPE
            SYNTAX TruthValue
            MAX-ACCESS read-only
            STATUS current
            DESCRIPTION
                "This object contains the incoming ring ground indication.
                It is only valid when the zvaIfFXSCfgSignalType is
                fxsGroundStart. If the object is true, then the interface
                is presenting a ring ground to the connected equipment;
                otherwise, it doesn't.
                "
            DEFVAL { false }
            ::= { zhoneVaIfFXSStatusEntry 3 }


-- --
--
        -- 1.3.6.1.4.1.5504.5.6.2.2.1.4
        zhoneVaIfFXSTipGround OBJECT-TYPE
            SYNTAX TruthValue
            MAX-ACCESS read-only
            STATUS current
            DESCRIPTION
                "This object contains the incoming tip ground indication.
                It is only valid when the zvaIfFXSCfgSignalType is
                fxsGroundStart. If the object is true, then the interface
                is detecting a tip ground at the interface; otherwise,
                it doesn't.
                "
            DEFVAL { false }
            ::= { zhoneVaIfFXSStatusEntry 4 }


-- ****************************************************************************
-- The FXS Timing Parameters Table
-- ****************************************************************************
-- This table contains the FXS interface timing parameters information.
--
        -- 1.3.6.1.4.1.5504.5.6.2.3
        zhoneVaIfFXSTimingTable OBJECT-TYPE
            SYNTAX SEQUENCE OF ZhoneVaIfFXSTimingEntry
            MAX-ACCESS not-accessible
            STATUS current
            DESCRIPTION
                "The FXS interface Timing Parameters table. It
                contains the configuration of the various FXS signaling
                protocol timing parameters.
                "
            ::= { zhoneVaIfFXSObjects 3 }


        -- 1.3.6.1.4.1.5504.5.6.2.3.1
        zhoneVaIfFXSTimingEntry OBJECT-TYPE
            SYNTAX ZhoneVaIfFXSTimingEntry
            MAX-ACCESS not-accessible
            STATUS current
            DESCRIPTION
                "An entry in the FXS Timing Parameters Table for
                each FXS interface."
            AUGMENTS { zhoneVaIfFXSCfgEntry }
            ::= { zhoneVaIfFXSTimingTable 1 }


        ZhoneVaIfFXSTimingEntry ::=
            SEQUENCE {
                zhoneVaIfFXSTimingDigitDuration
                    Integer32,
                zhoneVaIfFXSTimingInterDigitDuration
                    Integer32
             }

        -- 1.3.6.1.4.1.5504.5.6.2.3.1.1
        zhoneVaIfFXSTimingDigitDuration OBJECT-TYPE
            SYNTAX Integer32 (50..500)
            UNITS "milliseconds"
            MAX-ACCESS read-write
            STATUS current
            DESCRIPTION
                "Outgoing DTMF digit duration in milliseconds.
                The default value of this object is 100 milliseconds.

                This field is not supported.
                "
            ::= { zhoneVaIfFXSTimingEntry 1 }


--
--
        -- 1.3.6.1.4.1.5504.5.6.2.3.1.2
        zhoneVaIfFXSTimingInterDigitDuration OBJECT-TYPE
            SYNTAX Integer32 (50..500)
            UNITS "milliseconds"
            MAX-ACCESS read-write
            STATUS current
            DESCRIPTION
                "Outgoing DTMF inter-digit duration in milliseconds.
                The default value of this object is 100 milliseconds.

                This field is not supported.
                "
            ::= { zhoneVaIfFXSTimingEntry 2 }


        -- 1.3.6.1.4.1.5504.5.6.2.4
        zhonePotsRingTable OBJECT-TYPE
            SYNTAX SEQUENCE OF ZhonePotsRingEntry
            MAX-ACCESS not-accessible
            STATUS deprecated
            DESCRIPTION
                "Table to execute diagnostic potsring command.
                Row in table with non-zero timer will ring pots port.
                Currently, maximum of 4 rows at a time are supported."
            ::= { zhoneVaIfFXSObjects 4 }


        -- 1.3.6.1.4.1.5504.5.6.2.4.1
        zhonePotsRingEntry OBJECT-TYPE
            SYNTAX ZhonePotsRingEntry
            MAX-ACCESS not-accessible
            STATUS deprecated
            DESCRIPTION
                "potsring table entry"
            INDEX { zhonePotsRingIfIndex }
            ::= { zhonePotsRingTable 1 }


        ZhonePotsRingEntry ::=
            SEQUENCE {
                zhonePotsRingIfIndex
                    InterfaceIndex,
                zhonePotsRingRingingCadence
                    INTEGER,
                zhonePotsRingTimer
                    Integer32,
                zhonePotsRingRowStatus
                    ZhoneRowStatus
             }

        -- 1.3.6.1.4.1.5504.5.6.2.4.1.1
        zhonePotsRingIfIndex OBJECT-TYPE
            SYNTAX InterfaceIndex
            MAX-ACCESS not-accessible
            STATUS deprecated
            DESCRIPTION
                "Physical pots interface."
            ::= { zhonePotsRingEntry 1 }


        -- 1.3.6.1.4.1.5504.5.6.2.4.1.2
        zhonePotsRingRingingCadence OBJECT-TYPE
            SYNTAX INTEGER
                {
                ring-cadence-r0(1),
                ring-cadence-r1(2),
                ring-cadence-r2(3),
                ring-cadence-r3(4),
                ring-cadence-r4(5),
                ring-cadence-r5(6),
                ring-cadence-r6(7),
                ring-cadence-r7(8),
                ring-cadence-common(9),
                ring-cadence-splash(10)
                }
            MAX-ACCESS read-create
            STATUS deprecated
            DESCRIPTION
                "Ring cadence to use in test."
            DEFVAL { 9 }
            ::= { zhonePotsRingEntry 2 }


        -- 1.3.6.1.4.1.5504.5.6.2.4.1.3
        zhonePotsRingTimer OBJECT-TYPE
            SYNTAX Integer32 (1..9999)
            MAX-ACCESS read-create
            STATUS deprecated
            DESCRIPTION
                "Time in seconds to continue ringing."
            DEFVAL { 15 }
            ::= { zhonePotsRingEntry 3 }


        -- 1.3.6.1.4.1.5504.5.6.2.4.1.4
        zhonePotsRingRowStatus OBJECT-TYPE
            SYNTAX ZhoneRowStatus
            MAX-ACCESS read-create
            STATUS deprecated
            DESCRIPTION
                "Row status"
            ::= { zhonePotsRingEntry 4 }


        -- 1.3.6.1.4.1.5504.5.6.3
        zhoneVaIfFXOObjects OBJECT IDENTIFIER ::= { zhoneVaIfObjects 3 }


-- ****************************************************************************
-- The Foreign Exchange Office (FXO) Standard Configuration Table
-- ****************************************************************************
--
-- This table is used to configure the FXO signaling and number of rings
-- for the FXO interface.
--
        -- 1.3.6.1.4.1.5504.5.6.3.1
        zhoneVaIfFXOCfgTable OBJECT-TYPE
            SYNTAX SEQUENCE OF ZhoneVaIfFXOCfgEntry
            MAX-ACCESS not-accessible
            STATUS current
            DESCRIPTION
                "The FXO standard configuration table. It contains
                FXO configuration parameters, one entry per FXO interface.
                The configuration information of this table is set by
                hardware with its default setting or CLI during the hardware
                installation time.
                "
            ::= { zhoneVaIfFXOObjects 1 }


        -- 1.3.6.1.4.1.5504.5.6.3.1.1
        zhoneVaIfFXOCfgEntry OBJECT-TYPE
            SYNTAX ZhoneVaIfFXOCfgEntry
            MAX-ACCESS not-accessible
            STATUS current
            DESCRIPTION
                "An entry in the standard configuration table for
                each FXO interface."
            INDEX { ifIndex }
            ::= { zhoneVaIfFXOCfgTable 1 }


        ZhoneVaIfFXOCfgEntry ::=
            SEQUENCE {
                zhoneVaIfFXOCfgSignalType
                    INTEGER,
                zhoneVaIfFXOCfgNumberRings
                    Integer32,
                zhoneVaIfFXOCfgSupDisconnect
                    TruthValue,
                zhoneVaIfFXOCfgDialType
                    INTEGER
             }

--
        -- 1.3.6.1.4.1.5504.5.6.3.1.1.1
        zhoneVaIfFXOCfgSignalType OBJECT-TYPE
            SYNTAX INTEGER
                {
                fxoLoopStart(1),
                fxoGroundStart(2),
                fxodpt(3)
                }
            MAX-ACCESS read-write
            STATUS current
            DESCRIPTION
                "the signaling type of FXO interface.
                fxoLoopStart   - loop start.
                fxoGroundStart - ground start.
                fxodpt- Dial Pulse Terminating , this option allows the unit to attach to incoming one way trunks from a PBX , key system or a telephone set..
                The default value of this object is fxoLoopStart(1).
                "
            ::= { zhoneVaIfFXOCfgEntry 1 }


        -- 1.3.6.1.4.1.5504.5.6.3.1.1.2
        zhoneVaIfFXOCfgNumberRings OBJECT-TYPE
            SYNTAX Integer32 (1..10)
            MAX-ACCESS read-write
            STATUS current
            DESCRIPTION
                "The number of rings detected before closing loop.
                The default value of this object is 1 ring."
            ::= { zhoneVaIfFXOCfgEntry 2 }


        -- 1.3.6.1.4.1.5504.5.6.3.1.1.3
        zhoneVaIfFXOCfgSupDisconnect OBJECT-TYPE
            SYNTAX TruthValue
            MAX-ACCESS read-write
            STATUS current
            DESCRIPTION
                " Specifies whether a supervisory disconnect signal (CPC) will
                be presented to the interface when the connected party at
                the interface hangs up.
                The default value of this object is 'true'.
                "
            DEFVAL { false }
            ::= { zhoneVaIfFXOCfgEntry 3 }


        -- 1.3.6.1.4.1.5504.5.6.3.1.1.4
        zhoneVaIfFXOCfgDialType OBJECT-TYPE
            SYNTAX INTEGER
                {
                dtmf(1),
                pulse(2)
                }
            MAX-ACCESS read-write
            STATUS current
            DESCRIPTION
                "Specifies the out dialing type of FXO interface.
                dtmf  - DTMF digit.
                pulse - pulse.
                The default value of this object is dtmf(1).
                "
            ::= { zhoneVaIfFXOCfgEntry 4 }


-- ****************************************************************************
--  The Foreign Exchange Office (FXO) interface Status Table
-- ****************************************************************************
--
        -- 1.3.6.1.4.1.5504.5.6.3.2
        zhoneVaIfFXOStatusTable OBJECT-TYPE
            SYNTAX SEQUENCE OF ZhoneVaIfFXOStatusEntry
            MAX-ACCESS not-accessible
            STATUS current
            DESCRIPTION
                "The Foreign Exchange Office (FXO) interface Status Table.
                It contains hook status, ring detection and other states of
                the interface.
                "
            ::= { zhoneVaIfFXOObjects 2 }


        -- 1.3.6.1.4.1.5504.5.6.3.2.1
        zhoneVaIfFXOStatusEntry OBJECT-TYPE
            SYNTAX ZhoneVaIfFXOStatusEntry
            MAX-ACCESS not-accessible
            STATUS current
            DESCRIPTION
                "An entry in the status table for each FXO interface.
                "
            AUGMENTS { zhoneVaIfFXOCfgEntry }
            ::= { zhoneVaIfFXOStatusTable 1 }


        ZhoneVaIfFXOStatusEntry ::=
            SEQUENCE {
                zhoneVaIfFXOHookStatus
                    INTEGER,
                zhoneVaIfFXORingDetect
                    TruthValue,
                zhoneVaIfFXORingGround
                    TruthValue,
                zhoneVaIfFXOTipGround
                    TruthValue
             }

--
        -- 1.3.6.1.4.1.5504.5.6.3.2.1.1
        zhoneVaIfFXOHookStatus OBJECT-TYPE
            SYNTAX INTEGER
                {
                onHook(1),
                offHook(2)
                }
            MAX-ACCESS read-only
            STATUS current
            DESCRIPTION
                "This object contains the hook status of FXO interface.
                onHook  - Present the onHook to the connected equipment.
                offHook - Present the offHook to the connected equipment.
                "
            ::= { zhoneVaIfFXOStatusEntry 1 }


--
        -- 1.3.6.1.4.1.5504.5.6.3.2.1.2
        zhoneVaIfFXORingDetect OBJECT-TYPE
            SYNTAX TruthValue
            MAX-ACCESS read-only
            STATUS current
            DESCRIPTION
                "This object contains the ring detect indication. If the
                value is true, then the interface detects ring from PBX or
                CO; otherwise, it doesn't."
            DEFVAL { false }
            ::= { zhoneVaIfFXOStatusEntry 2 }


--
        -- 1.3.6.1.4.1.5504.5.6.3.2.1.3
        zhoneVaIfFXORingGround OBJECT-TYPE
            SYNTAX TruthValue
            MAX-ACCESS read-only
            STATUS current
            DESCRIPTION
                "This object contains the incoming ring ground indication.
                It is only valid when the zvaIfFXOCfgSignalType is
                fxoGroundStart. If the object is true, then the interface
                is presenting a ring ground to the connected equipment;
                otherwise, it doesn't.
                "
            DEFVAL { false }
            ::= { zhoneVaIfFXOStatusEntry 3 }


--
        -- 1.3.6.1.4.1.5504.5.6.3.2.1.4
        zhoneVaIfFXOTipGround OBJECT-TYPE
            SYNTAX TruthValue
            MAX-ACCESS read-only
            STATUS current
            DESCRIPTION
                "This object contains the incoming tip ground indication.
                It is only valid when the zvaIfFXOCfgSignalType is
                fxoGroundStart. If the object is true, then the interface
                is detecting a tip ground at the interface; otherwise,
                it doesn't.
                "
            DEFVAL { false }
            ::= { zhoneVaIfFXOStatusEntry 4 }


-- ****************************************************************************
--  The FXO Timing Parameters Table
-- ****************************************************************************
--  This table contains the FXO interface timing parameters information.
--
        -- 1.3.6.1.4.1.5504.5.6.3.3
        zhoneVaIfFXOTimingTable OBJECT-TYPE
            SYNTAX SEQUENCE OF ZhoneVaIfFXOTimingEntry
            MAX-ACCESS not-accessible
            STATUS current
            DESCRIPTION
                "The FXO interface Timing Parameters table. It
                contains the configuration of the various FXO signaling
                protocol timing parameters.
                "
            ::= { zhoneVaIfFXOObjects 3 }


        -- 1.3.6.1.4.1.5504.5.6.3.3.1
        zhoneVaIfFXOTimingEntry OBJECT-TYPE
            SYNTAX ZhoneVaIfFXOTimingEntry
            MAX-ACCESS not-accessible
            STATUS current
            DESCRIPTION
                "An entry in the FXO Timing Parameters Table for
                each FXO interface."
            AUGMENTS { zhoneVaIfFXOCfgEntry }
            ::= { zhoneVaIfFXOTimingTable 1 }


        ZhoneVaIfFXOTimingEntry ::=
            SEQUENCE {
                zhoneVaIfFXOTimingDigitDuration
                    Integer32,
                zhoneVaIfFXOTimingInterDigitDuration
                    Integer32,
                zhoneVaIfFXOTimingPulseRate
                    Integer32,
                zhoneVaIfFXOTimingPulseInterDigitDuration
                    Integer32
             }

        -- 1.3.6.1.4.1.5504.5.6.3.3.1.1
        zhoneVaIfFXOTimingDigitDuration OBJECT-TYPE
            SYNTAX Integer32 (50..500)
            UNITS "milliseconds"
            MAX-ACCESS read-write
            STATUS current
            DESCRIPTION
                "Outgoing DTMF digit duration in milliseconds.
                The default value of this object is 100 msec.
                "
            ::= { zhoneVaIfFXOTimingEntry 1 }


        -- 1.3.6.1.4.1.5504.5.6.3.3.1.2
        zhoneVaIfFXOTimingInterDigitDuration OBJECT-TYPE
            SYNTAX Integer32 (50..500)
            UNITS "milliseconds"
            MAX-ACCESS read-write
            STATUS current
            DESCRIPTION
                "Outgoing DTMF inter-digit duration in milliseconds.
                The default value of this object is 100 msec.
                "
            ::= { zhoneVaIfFXOTimingEntry 2 }


        -- 1.3.6.1.4.1.5504.5.6.3.3.1.3
        zhoneVaIfFXOTimingPulseRate OBJECT-TYPE
            SYNTAX Integer32 (10..20)
            UNITS "pps"
            MAX-ACCESS read-write
            STATUS current
            DESCRIPTION
                "Outgoing pulse dialing rate in pulses per second (pps).
                The default value of this object is 10 pps.
                "
            ::= { zhoneVaIfFXOTimingEntry 3 }


        -- 1.3.6.1.4.1.5504.5.6.3.3.1.4
        zhoneVaIfFXOTimingPulseInterDigitDuration OBJECT-TYPE
            SYNTAX Integer32 (100..1000)
            UNITS "pps"
            MAX-ACCESS read-write
            STATUS current
            DESCRIPTION
                "Outgoing pulse dialing inter-digit timing in milliseconds.
                The default value of this object is 500 milliseconds.
                "
            ::= { zhoneVaIfFXOTimingEntry 4 }


        -- 1.3.6.1.4.1.5504.5.6.4
        zhoneVaIfEMObjects OBJECT IDENTIFIER ::= { zhoneVaIfObjects 4 }


--
-- ****************************************************************************
--  The E&M Standard Configuration Table
-- ****************************************************************************
--
-- This table is used to configure the E&M type, signaling, operation,
-- dial type for the E&M interface.
--
        -- 1.3.6.1.4.1.5504.5.6.4.1
        zhoneVaIfEMCfgTable OBJECT-TYPE
            SYNTAX SEQUENCE OF ZhoneVaIfEMCfgEntry
            MAX-ACCESS not-accessible
            STATUS current
            DESCRIPTION
                "The E&M standard configuration table. It contains
                the current setting of E&M configurable parameters.
                "
            ::= { zhoneVaIfEMObjects 1 }


        -- 1.3.6.1.4.1.5504.5.6.4.1.1
        zhoneVaIfEMCfgEntry OBJECT-TYPE
            SYNTAX ZhoneVaIfEMCfgEntry
            MAX-ACCESS not-accessible
            STATUS current
            DESCRIPTION
                "An entry in the standard configuration table for
                each E&M tie trunk interface."
            INDEX { ifIndex }
            ::= { zhoneVaIfEMCfgTable 1 }


        ZhoneVaIfEMCfgEntry ::=
            SEQUENCE {
                zhoneVaIfEMCfgSignalType
                    INTEGER,
                zhoneVaIfEMCfgOperation
                    INTEGER,
                zhoneVaIfEMCfgType
                    INTEGER,
                zhoneVaIfEMCfgDialType
                    INTEGER
             }

        -- 1.3.6.1.4.1.5504.5.6.4.1.1.1
        zhoneVaIfEMCfgSignalType OBJECT-TYPE
            SYNTAX INTEGER
                {
                winkStart(1),
                immediateDial(2),
                delayDial(3)
                }
            MAX-ACCESS read-only
            STATUS current
            DESCRIPTION
                "The signaling type of E&M tie trunk interface.
                winkStart - the calling side seizes the line by going
                            off-hook on its E lead but waits for a short
                            off-hook 'wink' indication on its M lead from
                            the called side before sending address
                            information as DTMF digits.
                immediateDial - the calling side seizes the line by going
                            off-hook on its E lead and sends sends address
                            information as DTMF digits.
                delayDial - the calling side seizes the line by going
                            off-hook on its E lead. After a timing interval,
                            the calling side looks at the supervision
                            from the called side. If the supervision is
                            on-hook, the calling side starts sending
                            information as DTMF digits; otherwise, the calling
                            side waits until the called side goes
                            on-hook and then starts sending address
                            information.
                The default value of this object is winkStart(1).
                "
            REFERENCE
                "EIA/TIA-464B: Sections 4.1.3.4.1 Signaling Protocols.
                "
            ::= { zhoneVaIfEMCfgEntry 1 }


        -- 1.3.6.1.4.1.5504.5.6.4.1.1.2
        zhoneVaIfEMCfgOperation OBJECT-TYPE
            SYNTAX INTEGER
                {
                twoWires(1),
                fourWires(2)
                }
            MAX-ACCESS read-only
            STATUS current
            DESCRIPTION
                "Specify the operation of the E&M signal.
                twoWires  - 2-wire operation.
                fourWires - 4-wire operation.
                The default value of this object is twoWires(1).
                "
            ::= { zhoneVaIfEMCfgEntry 2 }


        -- 1.3.6.1.4.1.5504.5.6.4.1.1.3
        zhoneVaIfEMCfgType OBJECT-TYPE
            SYNTAX INTEGER
                {
                typeI(1),
                typeII(2),
                typeIII(3),
                typeIV(4),
                typeV(5),
                typeIIE(6),
                typeIIM(7),
                typeTO(8)
                }
            MAX-ACCESS read-write
            STATUS current
            DESCRIPTION
                "Specifies the E&M Lead Signaling type.
                LEGEND: V     = -48V
                /\/\/ = detector/resister
                X     = normally open relay contact
                +     = normally closed relay contact
                G     = ground
                SB    = Signal Battery
                SG    = Signal Ground

                typeI -
                     Leads:  E (output, relay to ground)
                             M (input, referenced to ground)

                     The tie line equipment (switch/router/etc) generates the
                     E-signal to the PBX type grounding the E-lead.
                     The tie line equipment detects the M-signal by detecting
                     current flow to ground.  A common ground must exist
                     between the line equipment and the PBX.

                              PBX    |  TIE LINE
                                     |
                     E:   V--/\/\/---|-----X----G
                                     |
                     M:   V----X-----|---/\/\/--G

                typeII -
                     Leads: E (output, relay to SG)
                     M (input, referenced to ground)
                     SB (feed for M, connected to -48V)
                     SG (return for E, galvanically isolated from ground)

                     This interface requires no common ground between the
                     equipment, thus avoiding ground loop noise problems.
                     E-signal is generated toward the PBX by connecting it
                     to SG.  M-signal is indicated by the PBX connecting
                     it to SB.  While this interface does NOT require a
                     common ground, it does have the tendency to inject
                     noise into the audio paths since it is asymmetrical
                     with respect to current flow between devices.

                              PBX    |  TIE LINE
                                     |
                     E:   V--/\/\/---|-----X----
                                     |          |
                     SG:  G----------|----------
                                     |
                     M:    ----X-----|---/\/\/--G
                                     |          |
                     SB:   ----------|----------V

                typeIII -
                     Leads: E (output, relay to ground)
                     M (input, referenced to ground)
                     SB (connected to -48V)
                     SG (connected to ground)

                     This interface operates similar to type I with respect
                     to the E-signal. The M-signal, however, is indicated by
                     the PBX connecting it to SB on assertion, and alternately
                     connecting it to SG during inactivity. Unfortunately, a
                     common ground must be shared between the equipment.

                              PBX    |  TIE LINE
                                     |
                     E:   V--/\/\/---|-----X----G
                                     |
                     SG:   ----------|----------G
                              +      |
                     M:    ----------|---/\/\/--G
                          X          |
                     SB:   ----------|----------V

                typeIV -
                     Leads: E (output, relay to SG)
                     M (input, referenced to -48V)
                     SB (feed for M, connected to ground)
                     SG (return for E, galvanically isolated from ground)

                     This interface is fully symmetrical; it does not require
                     a common ground, does not inject noise into audio paths,
                     and can be connected back to back by swapping E/SG for
                     M/SB.  E-signal is indicated to the PBX by connecting it
                     to SG.  M-signal is provided by the PBX connecting it to
                     SB.

                              PBX    |  TIE LINE
                                     |
                     E:   V--/\/\/---|-----X----
                                     |          |
                     SG:  G----------|----------
                                     |
                     M:    ----------|---/\/\/--V
                          X          |
                     SB:   ----------|----------G

                typeV -
                     Leads: E (output, relay to ground)
                            M (input, referenced to -48V)

                     Type V line equipment indicates E-signal to the PBX by
                     grounding the E-lead. The PBX indicates M-signal by
                     grounding the M-lead.  This interface does require a
                     common ground, but does allow back to back connections
                     by swapping E for M.  This interface is quasi-symmetric
                     in that while the line is up, current flow is more or
                                      less equal between the PBX and line equipment. But noise
                                      injection is still a problem.

                                               PBX    |  TIE LINE
                                                      |
                                      E:   V--/\/\/---|-----X----G
                                                      |
                                      M:   G-----X----|---/\/\/--V
                                                      |
                                 The default value of this object is typeI(1).
                "
            REFERENCE
                "EIA/TIA-464B: Sections 4.2.3 E&M Lead Signaling.
                "
            ::= { zhoneVaIfEMCfgEntry 3 }


        -- 1.3.6.1.4.1.5504.5.6.4.1.1.4
        zhoneVaIfEMCfgDialType OBJECT-TYPE
            SYNTAX INTEGER
                {
                dtmf(1),
                pulse(2)
                }
            MAX-ACCESS read-only
            STATUS current
            DESCRIPTION
                "Specifies the out dialing type of E&M interface.
                dtmf  - DTMF digit.
                pulse - pulse.
                The default value of this object is dtmf(1).
                "
            ::= { zhoneVaIfEMCfgEntry 4 }


-- ****************************************************************************
--  The E&M interface Status Table
-- ****************************************************************************
--
        -- 1.3.6.1.4.1.5504.5.6.4.2
        zhoneVaIfEMStatusTable OBJECT-TYPE
            SYNTAX SEQUENCE OF ZhoneVaIfEMStatusEntry
            MAX-ACCESS not-accessible
            STATUS current
            DESCRIPTION
                "The E&M interface Table.  The table contains
                the status of the E&M tie trunk interface.
                "
            ::= { zhoneVaIfEMObjects 2 }


        -- 1.3.6.1.4.1.5504.5.6.4.2.1
        zhoneVaIfEMStatusEntry OBJECT-TYPE
            SYNTAX ZhoneVaIfEMStatusEntry
            MAX-ACCESS not-accessible
            STATUS current
            DESCRIPTION
                "An entry in the status table for each E&M interface.
                "
            AUGMENTS { zhoneVaIfEMCfgEntry }
            ::= { zhoneVaIfEMStatusTable 1 }


        ZhoneVaIfEMStatusEntry ::=
            SEQUENCE {
                zhoneVaIfEMInSeizureActive
                    TruthValue,
                zhoneVaIfEMOutSeizureActive
                    TruthValue
             }

        -- 1.3.6.1.4.1.5504.5.6.4.2.1.1
        zhoneVaIfEMInSeizureActive OBJECT-TYPE
            SYNTAX TruthValue
            MAX-ACCESS read-only
            STATUS current
            DESCRIPTION
                "This object contains the incoming seizure state of the E&M
                interface. If the value is true, then the interface has an
                incoming trunk seizure active; otherwise, it doesn't.
                "
            DEFVAL { false }
            ::= { zhoneVaIfEMStatusEntry 1 }


        -- 1.3.6.1.4.1.5504.5.6.4.2.1.2
        zhoneVaIfEMOutSeizureActive OBJECT-TYPE
            SYNTAX TruthValue
            MAX-ACCESS read-only
            STATUS current
            DESCRIPTION
                "This object contains the outgoing seizure state of the E&M
                interface. If the value is true, then the interface has an
                outgoing trunk seizure active; otherwise, it doesn't.
                "
            DEFVAL { false }
            ::= { zhoneVaIfEMStatusEntry 2 }


-- ****************************************************************************
--  The E&M Timing Parameters Table
-- ****************************************************************************
--
--  This table contains the E&M interface timing parameters information.
--
        -- 1.3.6.1.4.1.5504.5.6.4.3
        zhoneVaIfEMTimingTable OBJECT-TYPE
            SYNTAX SEQUENCE OF ZhoneVaIfEMTimingEntry
            MAX-ACCESS not-accessible
            STATUS current
            DESCRIPTION
                "The E&M tie trunk Timing Parameters table. It
                contains the configuration of the various E&M signaling
                protocol timing parameters.
                "
            ::= { zhoneVaIfEMObjects 3 }


        -- 1.3.6.1.4.1.5504.5.6.4.3.1
        zhoneVaIfEMTimingEntry OBJECT-TYPE
            SYNTAX ZhoneVaIfEMTimingEntry
            MAX-ACCESS not-accessible
            STATUS current
            DESCRIPTION
                "An entry in the E&M Timing Parameters Table for
                each E&M interface."
            AUGMENTS { zhoneVaIfEMCfgEntry }
            ::= { zhoneVaIfEMTimingTable 1 }


        ZhoneVaIfEMTimingEntry ::=
            SEQUENCE {
                zhoneVaIfEMTimingDigitDuration
                    Integer32,
                zhoneVaIfEMTimingInterDigitDuration
                    Integer32,
                zhoneVaIfEMTimingPulseRate
                    Integer32,
                zhoneVaIfEMTimingPulseInterDigitDuration
                    Integer32,
                zhoneVaIfEMTimingClearWaitDuration
                    Integer32,
                zhoneVaIfEMTimingMaxWinkWaitDuration
                    Integer32,
                zhoneVaIfEMTimingMaxWinkDuration
                    Integer32,
                zhoneVaIfEMTimingDelayStart
                    Integer32,
                zhoneVaIfEMTimingMaxDelayDuration
                    Integer32,
                zhoneVaIfEMTimingMinDelayPulseWidth
                    Integer32
             }

        -- 1.3.6.1.4.1.5504.5.6.4.3.1.1
        zhoneVaIfEMTimingDigitDuration OBJECT-TYPE
            SYNTAX Integer32 (50..500)
            UNITS "milliseconds"
            MAX-ACCESS read-write
            STATUS current
            DESCRIPTION
                "Outgoing DTMF digit duration in milliseconds.
                The default value of this object is 100 milliseconds.
                "
            ::= { zhoneVaIfEMTimingEntry 1 }


        -- 1.3.6.1.4.1.5504.5.6.4.3.1.2
        zhoneVaIfEMTimingInterDigitDuration OBJECT-TYPE
            SYNTAX Integer32 (50..500)
            UNITS "milliseconds"
            MAX-ACCESS read-write
            STATUS current
            DESCRIPTION
                "Outgoing DTMF inter-digit duration in milliseconds.
                The default value of this object is 100 milliseconds.
                "
            ::= { zhoneVaIfEMTimingEntry 2 }


        -- 1.3.6.1.4.1.5504.5.6.4.3.1.3
        zhoneVaIfEMTimingPulseRate OBJECT-TYPE
            SYNTAX Integer32 (10..20)
            UNITS "pps"
            MAX-ACCESS read-write
            STATUS current
            DESCRIPTION
                "Outgoing pulse dialing rate in pulses per second (pps).
                The default value of this object is 10 pps.
                "
            ::= { zhoneVaIfEMTimingEntry 3 }


        -- 1.3.6.1.4.1.5504.5.6.4.3.1.4
        zhoneVaIfEMTimingPulseInterDigitDuration OBJECT-TYPE
            SYNTAX Integer32 (100..1000)
            UNITS "milliseconds"
            MAX-ACCESS read-write
            STATUS current
            DESCRIPTION
                "Outgoing Pulse dialing inter-digit timing in milliseconds.
                The default value of this object is 500 milliseconds.
                "
            ::= { zhoneVaIfEMTimingEntry 4 }


        -- 1.3.6.1.4.1.5504.5.6.4.3.1.5
        zhoneVaIfEMTimingClearWaitDuration OBJECT-TYPE
            SYNTAX Integer32 (200..2000)
            UNITS "milliseconds"
            MAX-ACCESS read-write
            STATUS current
            DESCRIPTION
                "Time of Inactive seizure signal to declare call cleared.
                The default value of this object is 400 milliseconds."
            ::= { zhoneVaIfEMTimingEntry 5 }


        -- 1.3.6.1.4.1.5504.5.6.4.3.1.6
        zhoneVaIfEMTimingMaxWinkWaitDuration OBJECT-TYPE
            SYNTAX Integer32 (100..5000)
            UNITS "milliseconds"
            MAX-ACCESS read-write
            STATUS current
            DESCRIPTION
                "Maximum time to wait from the outgoing seizure of the line
                to the time of sending out a wink-pulse.
                The default value of this object is 200 milliseconds."
            ::= { zhoneVaIfEMTimingEntry 6 }


        -- 1.3.6.1.4.1.5504.5.6.4.3.1.7
        zhoneVaIfEMTimingMaxWinkDuration OBJECT-TYPE
            SYNTAX Integer32 (100..3000)
            UNITS "milliseconds"
            MAX-ACCESS read-write
            STATUS current
            DESCRIPTION
                "Maximum outgoing wink duration (between the wink-pulse leading
                edge and trailing edge) for wink start signaling.
                The default value of this object is 200 milliseconds."
            ::= { zhoneVaIfEMTimingEntry 7 }


        -- 1.3.6.1.4.1.5504.5.6.4.3.1.8
        zhoneVaIfEMTimingDelayStart OBJECT-TYPE
            SYNTAX Integer32 (20..2000)
            UNITS "milliseconds"
            MAX-ACCESS read-write
            STATUS current
            DESCRIPTION
                "Minimum time to wait from outgoing seizure to
                out-dialing digits for delay start signaling.
                The default value of this object is 300 milliseconds.
                "
            ::= { zhoneVaIfEMTimingEntry 8 }


        -- 1.3.6.1.4.1.5504.5.6.4.3.1.9
        zhoneVaIfEMTimingMaxDelayDuration OBJECT-TYPE
            SYNTAX Integer32 (100..5000)
            UNITS "milliseconds"
            MAX-ACCESS read-write
            STATUS current
            DESCRIPTION
                "Maximum time to wait from outgoing seizure to
                out-dialing digits. If the far end does not allow to
                send digits after the duration specified in the object,
                a reorder tone will be sent to the calling party.
                The default value of this object is 2000 milliseconds."
            ::= { zhoneVaIfEMTimingEntry 9 }


        -- 1.3.6.1.4.1.5504.5.6.4.3.1.10
        zhoneVaIfEMTimingMinDelayPulseWidth OBJECT-TYPE
            SYNTAX Integer32 (0 | 140..5000)
            UNITS "milliseconds"
            MAX-ACCESS read-write
            STATUS current
            DESCRIPTION
                "Minimum delay-dial pulse duration for incoming call.
                If the value of this object is 0, then no delay-dial
                is sent to the far end for the incoming call.
                The default value of this object is 140 milliseconds."
            ::= { zhoneVaIfEMTimingEntry 10 }



    END

--
-- phyVaIf.mib
--
