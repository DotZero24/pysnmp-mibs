--
-- comVoiceGR303.mib
-- MIB generated by MG-SOFT Visual MIB Builder Version 3.0 Build 285
-- Tuesday, December 23, 2003 at 13:54:51
--

    ZhoneGR303-MIB DEFINITIONS ::= BEGIN

        IMPORTS
            InterfaceIndexOrZero
                FROM IF-MIB
            PerfCurrentCount
                FROM PerfHist-TC-MIB
            Integer32, Gauge32, OBJECT-TYPE, MODULE-IDENTITY,
            OBJECT-IDENTITY, NOTIFICATION-TYPE
                FROM SNMPv2-SMI
            TruthValue
                FROM SNMPv2-TC
            zhoneSystemConfigurationDateAndTime
                FROM ZHONE-SYSTEM-MIB
            zhoneVoice
                FROM Zhone
            ZhoneRowStatus, ZhoneAdminString, ZhoneShelfValueOrZero, ZhoneSlotValueOrZero
                FROM Zhone-TC;


-- GR303-MIB definition
--
-- Copyright (C) 2000 by Zhone Technologies, Inc.
-- All rights reserved.
--
-- Comments to: <support@zhone.com>
-- Web URL: <http://www.zhone.com>
--
-- profile/record definition for 'interface-group' configuration attributes
--
--
--
-- profile/record definition for 'interface-group' dynamic attributes
--
--
--
-- profile/record definition for 'control-channel' configuration attributes
--
--
--
-- profile/record definition for 'control-channel' dynamic attributes
--
--
--
-- profile/record definition for 'current-statistics' attributes
--
--
--
-- profile/record definition for 'interval-statistics' attributes
--
--
--
-- profile/record definition for 'total-statistics' attributes
--
--
--
-- profile/record definition for 'ds-1 line mapping' configuration attributes
-- TBD: no need to create a statistics record yet since if the ifIndex is not
-- yet supported by the DDL compiler
--
--
-- profile/record definition for 'CRV' configuration attributes
--
--
-- profile/record definition for 'CRV' statistic attributes
--
--
--
        -- 1.3.6.1.4.1.5504.4.3.1
        zhoneGR303 MODULE-IDENTITY
            LAST-UPDATED "200312231109Z"		-- December 23, 2003 at 11:09 GMT
            ORGANIZATION
                "Zhone Technologies, Inc."
            CONTACT-INFO
                "  Postal:
                           Zhone Technologies, Inc.
                           @ Zhone Way
                           7001 Oakport Street
                           Oakland, CA  94621
                           USA
                Toll-Free: +1 877-ZHONE20 (+1 877-946-6320)
                      Tel: +1-510-777-7000
                      Fax: +1-510-777-7001
                   E-mail: support@zhone.com"
            DESCRIPTION
                "The MIB module to describe objects for GR-303. It is based
                on the Generic Requirements document for GR-303, referred
                to as GR-303-CORE.

                The Generic Requirements (GR) document describes Bellcore's
                view of the overall system functions and performance
                levels required when a Digital Loop Carrier System (DLC)
                is integrated into a Local Digital Switch (LDS). It
                further describes a generic interface, one particular
                means of interfacing a DLC Remote Digital Terminal (RDT)
                with the LDS.

                The proposed overall system requirements for Integrated
                Digital Loop Carrier (IDLC) systems are expressed in
                terms of functions, i.e., what the combination of RDT
                and LDS must do when connected together. These end-to-end
                system requirements are grouped into functional categories
                dealing with (1) Customer services, (2) Digital network
                interfaces, (3) Operations Systems interfaces,
                (4) Craft interfaces, and (5) Overall system capabilities.
                These proposed requirements do not specify or imply any
                specific supplier implementation.  They are, therefore,
                termed generic system requirements."
            REVISION "200312231109Z"		-- December 23, 2003 at 11:09 GMT
            DESCRIPTION
                "V01.02.03
                -- Add new switch type in ig table
                "
            REVISION "200311141310Z"		-- November 14, 2003 at 13:10 GMT
            DESCRIPTION
                "V01.02.02
                -- Add new sigType in CRV table
                "
            REVISION "200111151045Z"		-- November 15, 2001 at 10:45 GMT
            DESCRIPTION
                "V01.02.01
                - Change MAX-ACCESS of ds1LogicalId to 'read-create'."
            REVISION "200108311230Z"		-- August 31, 2001 at 12:30 GMT
            DESCRIPTION
                "V01.02.00
                - Add ds1LogicalId to ds1LineMappingTable.
                - Remove 'unknown' from igCrvSignalType."
            REVISION "200108141447Z"		-- August 14, 2001 at 14:47 GMT
            DESCRIPTION
                "V01.01.06
                Remove default values for igAdminStatus, igWorkingMode, igAdminStatus, ds1Role,
                igCrvSignalType, igCrvLocalAdminStatus"
            REVISION "200106261500Z"		-- June 26, 2001 at 15:00 GMT
            DESCRIPTION
                "V01.01.05
                Add notification traps to the MIB."
            REVISION "200103281055Z"		-- March 28, 2001 at 10:55 GMT
            DESCRIPTION
                "V01.01.04 - Allow to change igSwitchType and igWorkingMode after setting the IG outOfService"
            REVISION "200102151847Z"		-- February 15, 2001 at 18:47 GMT
            DESCRIPTION
                "V01.01.03 - Add DEFVAL for TruthValue types."
            REVISION "200102011301Z"		-- February 01, 2001 at 13:01 GMT
            DESCRIPTION
                "V01.01.02 - change Zhone keywording for profile split"
            REVISION "200101261148Z"		-- January 26, 2001 at 11:48 GMT
            DESCRIPTION
                "V01.01.01 - add the igWorkingMode to the interfaceGroupTable"
            REVISION "200012121157Z"		-- December 12, 2000 at 11:57 GMT
            DESCRIPTION
                "V01.01.00 - change the igControlChannel table to add TMC
                and EOC primary and secondary service state.Plus add
                provisioning instructions as comments. "
            REVISION "200009121212Z"		-- September 12, 2000 at 12:12 GMT
            DESCRIPTION
                "V01.00.00 - Initial Release"
            ::= { zhoneVoice 1 }




--
-- Node definitions
--

--
-- GR-303 Interface Group
--
-- The GR-303 Interface Group consists of the following tables:
--     Interface Group Table
--     Interface Group Control Channel Table (AUGMENT)
--     Interface Group Statistics Current Table (AUGMENT)
--     Interface Group Statistics Interval Table
--     Interface Group Statistics Total Table (AUGMENT)
--
-- The Interface Group Table
--
        -- 1.3.6.1.4.1.5504.4.3.1.1
        interfaceGroupTable OBJECT-TYPE
            SYNTAX SEQUENCE OF InterfaceGroupEntry
            MAX-ACCESS not-accessible
            STATUS current
            DESCRIPTION
                "The GR-303 Interface Group Table.

                Minimum granularity for GR-303 provisioning is the
                Interface Group (IG) abstraction aka Internal Group.
                The Interface Group Table describes attributes for
                each provisioned GR-303 Interface Group and is also
                the base table for the augmenting Interface Group
                Control Channel Table.  Each IG is configured
                manually by an administrator.

                Each IG entry (row) is indexed by a unique IG name.
                Where both active and standby Interface Groups exist,
                the same IG name refers to both the active and standby
                Interface Group.

                For all IG entries, the (shelf, slot) is unique. The
                IG name is an externally visible global name that
                refers to both the active and standby IGs. IG names
                are used for call routing and does not change during
                the IG lifetime.

                The maximum number of entries or Interface Groups
                is 'system-wide' and not bounded by a slot or card,
                but can span multiple cards and shelves.

                Each Interface Group is associated with the following
                tables:
                * augmenting Interface Group Control Channel row
                * DS1 Line Mapping Table
                * Line Circuit CRV Table
                * augmenting IG Statistics Current row
                * IG Statistics Interval Table
                * augmenting IG Statistics Total row

                After creating an IG entry an associated primary DS1
                must be created. Without the primary DS1 an SNMP-SET
                operation is not allowed on any 303 tables except the
                deletion of the IG entry.

                "
            ::= { zhoneGR303 1 }


        -- 1.3.6.1.4.1.5504.4.3.1.1.1
        interfaceGroupEntry OBJECT-TYPE
            SYNTAX InterfaceGroupEntry
            MAX-ACCESS not-accessible
            STATUS current
            DESCRIPTION
                "An entry in the interfaceGroupTable.  Indexed
                by igNameId.  Interface Groups can span multiple
                cards and shelves. A row in this table is
                created by setting the value of igRowStatus
                to 'CreateAndGo', and setting the appropriate
                values for the columns.  Since this is the
                base table for the following augmenting tables:
                * Interface Group Control Channel Table
                  (igControlChannelTable),
                * Interface Group Statistics Current Table
                  (igStatsCurrentTable),
                * Interface Group Statistics Total Table
                  (igStatsTotalTable)
                the corresponding row in the augmenting tables
                must also be simultaneously created when a row
                in interfaceGroupTable is created. Likewise,
                when a row expires by setting the value of
                igRowStatus to 'destroy' in the interfaceGroupTable
                base table, the same row also expires in all
                augmenting tables."
            INDEX { igNameId }
            ::= { interfaceGroupTable 1 }


        InterfaceGroupEntry ::=
            SEQUENCE {
                igNameId
                    ZhoneAdminString,
                igShelf
                    ZhoneShelfValueOrZero,
                igSlot
                    ZhoneSlotValueOrZero,
                igPeerShelf
                    ZhoneShelfValueOrZero,
                igPeerSlot
                    ZhoneSlotValueOrZero,
                igSwitchType
                    INTEGER,
                igPrimaryEocTmcDs1IfIndex
                    InterfaceIndexOrZero,
                igSecondaryEocTmcDs1IfIndex
                    InterfaceIndexOrZero,
                igAdminStatus
                    INTEGER,
                igOperationalStatus
                    INTEGER,
                igPeerStatus
                    INTEGER,
                igMaxConfigCalls
                    Gauge32,
                igCurrActiveCalls
                    Gauge32,
                igStatsTimeElapsed
                    Integer32,
                igStatsValidIntervals
                    Integer32,
                igStatsInvalidIntervals
                    INTEGER,
                igRowStatus
                    ZhoneRowStatus,
                igWorkingMode
                    INTEGER
             }

--
-- Interface Group Identification and Configuration Objects
--
--
        -- 1.3.6.1.4.1.5504.4.3.1.1.1.1
        igNameId OBJECT-TYPE
            SYNTAX ZhoneAdminString
            MAX-ACCESS not-accessible
            STATUS current
            DESCRIPTION
                "The Interface Group name is a unique symbolic
                name that is used for call routing.  The maximum
                length for this name is 32 characters. Its value
                cannot be modified during the Interface Group
                lifetime. The igNameId is used, in conjunction
                with other indices, to index into other GR-303
                related tables."
            ::= { interfaceGroupEntry 1 }


--
        -- 1.3.6.1.4.1.5504.4.3.1.1.1.2
        igShelf OBJECT-TYPE
            SYNTAX ZhoneShelfValueOrZero
            MAX-ACCESS read-only
            STATUS current
            DESCRIPTION
                "The shelf where this Interface Group and GR-303
                stack resides.  Range of valid values is 0-255.
                A value of 0 indicates the Interface Group is not
                currently installed on a specific card by the
                GR-303 protocol stack."
            REFERENCE
                "GR-303-CORE 12.5.10"
            ::= { interfaceGroupEntry 2 }


--
        -- 1.3.6.1.4.1.5504.4.3.1.1.1.3
        igSlot OBJECT-TYPE
            SYNTAX ZhoneSlotValueOrZero
            MAX-ACCESS read-only
            STATUS current
            DESCRIPTION
                "The slot where this Interface Group and GR-303
                stack resides.  Range of valid values is 0-17.
                A value of 0 indicates the Interface Group is not
                currently installed on a specific card  by the
                GR-303 protocol stack."
            ::= { interfaceGroupEntry 3 }


--
-- Multiple Interface Group (Multi-IG) Feature.
--
-- The multi-IG feature allows a Call Reference
-- Value (CRV), or line, of any IG to be associated
-- with the Line Circuit Address (LCA) of any
-- Access Circuit (AC). An LCA is the physical
-- location where a customer's distribution pair
-- is terminated; e.g., on shelf-#2, slot-#5,
-- circuit (VPI:VCI:CID). The multi-IG feature
-- allows any access circuit to be assigned to a
-- CRV on any one of the IGs either during capacity
-- activation or service activation. The actual
-- implementation of the access-circuit association
-- is a supplier's choice; e.g., it can be a
-- memory map of a CRV (or line) to the LCA of
-- the access circuit, a DS0 crossconnect, or a
-- time slot interchanger. For GR-303-CORE-
-- compatible IGs, an access circuit must be
-- associated with a CRV to gain access to the
-- LDS. The GR-303-CORE interface uses the CRV
-- in its Timeslot Management Channel (TMC) to
-- dynamically assign DS0s to access circuits on
-- a call-by-call basis; i.e., if an access
-- circuit is not assigned a CRV, it will never
-- be assigned a DS0 between the IDT and IG.
--
-- To support its multi-IG feature, an RDT is
-- required to support the individual interface
-- requirements of each of its IGs. An RDT must
-- support at least two GR-303-CORE-compatible
-- IGs for the multi-IG feature (but more may be
-- needed in some applications), and each of these
-- IGs must support the interface requirements
-- of the IDT discussed above. The maximum number
-- of DS1s on the feeder-side (i.e., toward the
-- central office) of the RDT is not limited except
-- that each IG supporting GR-303-CORE is limited
-- to a maximum of 28 DS1s.  Additionally, the
-- number of access circuits accommodated by the
-- RDT can exceed 2048 with the constraint that
-- no more than 2048 access circuits can be
-- accommodated by any one GR-303-CORE IG. However,
-- each access circuit must have access to all
-- of the IGs supported by the RDT. In addition,
-- an access circuit associated with a GR-303-CORE
-- IG must have full access to all the DS0s
-- available to that IG for transport between
-- that IG and its IDT.
--
-- The multi-IG feature provides several benefits
-- for the integrated access architectures made
-- possible with GR-303-CORE products.  They are:
-- equiptment breakage, growth, service separation,
-- multiple switching systems central offices, load
-- balancing.
--
-- 12.5.10.3 Requirements on an RDT for Multi-IG Feature
--
-- R12-507 [1376] The RDT shall provide the capability
-- to interface to a minimum of  two different
-- GR-303-CORE IDTs (in the same LDS or in different
-- LDSs) and each IG-to-IDT interface shall meet
-- requirements for datalinks (EOC and TMC/CSC)
-- individually.
--
-- R12-508 [1377] The RDT is limited to a maximum
-- of 28 DS1s per IG 14 and each IG can support up
-- to a maximum of 2048 two-wire terminations toward
-- the customer's premises.
--
-- R12-509 [1378] Each IDT-IG interface shall be
-- capable of reusing CRV numbers and of being
-- resized, up or down, to support the deployed
-- size of the product.
--
-- CR12-510 [1379] In some BCC access architectures,
-- an RDT may be required to support more than
-- two GR-303-CORE IGs; eight or more may be needed
-- in some applications.
--
-- R12-522 [1391] The EOC paths and TMC/CSC paths
-- for a given IDT shall be on the same DS1s.
--
-- CR12-523 [1392] If the RDT has a DS1 protection
-- switching capability, the RDT shall provide the
-- capability to have a protection switching group
-- for each IDT.
--
-- R12-524 [1393] All customer line terminations
-- shall be capable of being provisioned to be
-- served by any of the IDTs terminating the RDT.
--
-- R12-525 [1394] The RDT shall support a
-- provisionable association between any of
-- its access circuits and any CRV (or line; if
-- the IG is not GR-303-CORE) of any IG in the RDT.
--
--
        -- 1.3.6.1.4.1.5504.4.3.1.1.1.4
        igPeerShelf OBJECT-TYPE
            SYNTAX ZhoneShelfValueOrZero
            MAX-ACCESS read-only
            STATUS current
            DESCRIPTION
                "The shelf where this Redundancy Group's peer
                (or standby) resides.  Peer shelf and peer
                slot define where this peer Interface Group
                and GR-303 stack resides.  Range of valid
                values is 0-255.  A peer shelf value of 0
                represents a no backup configuration."
            REFERENCE
                "GR-303-CORE 12.5.10"
            ::= { interfaceGroupEntry 4 }


--
        -- 1.3.6.1.4.1.5504.4.3.1.1.1.5
        igPeerSlot OBJECT-TYPE
            SYNTAX ZhoneSlotValueOrZero
            MAX-ACCESS read-only
            STATUS current
            DESCRIPTION
                "The slot where this Interface Group's peer
                (or standby) resides. Peer shelf and peer
                slot define where this Interface Group peer
                and GR-303 stack resides. Range of valid
                values is 0-17. A peer slot value of 0
                represents a no backup configuration."
            ::= { interfaceGroupEntry 5 }


--
        -- 1.3.6.1.4.1.5504.4.3.1.1.1.6
        igSwitchType OBJECT-TYPE
            SYNTAX INTEGER
                {
                lucent5Ess(2),
                nortelDms100(3),
                lucentGtd5(4),
                santeraSanteraOne(5),
                telicaPlexus9000(6),
                taquaIx7000(7)
                }
            MAX-ACCESS read-create
            STATUS current
            DESCRIPTION
                "The switch vendor for the Interface Group. The
                following switch types are defined: unknown,
                lucent_5ess, nortel_dms-100, lucent_gtd5,
                santera_santeraOne, telica_plexus9000 and
                taqua_ix7000

                This field can only be modified after setting
                the igAdminStatus of the IG record to outOfService.

                Note: 'unknown(1)' value is no longer supported
                for this variable.

                This variable is mandatory for IG row creation."
            ::= { interfaceGroupEntry 6 }


--
-- GR-303-CORE 12.6.3 Automatic EOC and TMC/CSC
-- path protection switching is required for
-- (IDLC) interfaces that support more than one
-- DS1, even though DS1 facility automatic
-- protection switching is optional. The EOC
-- and TMC/CSC path protection requirements are
-- to provide data-link layer protection of
-- these paths, which includes the DS0 paths.
--
-- A DS1 facility protection switching feature
-- enables traffic on a failed or degraded DS1
-- facility to be moved to one or more alternate
-- DS1 facilities. For more information see
-- GR-303-CORE 12.6.2.
--
-- Note that EOC and TMC/CSC path protection,
-- DS1 facility protection switching, and IG
-- redundancy (multi-IG Protection Switching)
-- are three different protection switching
-- strategies applying to different GR-303
-- capabilities and are not to be confused.
--
--
        -- 1.3.6.1.4.1.5504.4.3.1.1.1.7
        igPrimaryEocTmcDs1IfIndex OBJECT-TYPE
            SYNTAX InterfaceIndexOrZero
            MAX-ACCESS read-only
            STATUS current
            DESCRIPTION
                "For systems that support more than one DS1,
                protection switching for the Embedded Operations
                Channel (EOC) and a Time-slot Management Channel
                (TMC) is mandatory.

                This object refers to the ifIndex for the DS1
                line supporting the active EOC and TMC path
                protection switching.  The value for this object
                is equal to the value of ifIndex from the
                Interfaces table of MIB II (RFC 1213).

                Per-call time-slot assignment is accomplished
                over a 64 kb/s TMC that carries mesages between
                the LDS and RDT.  These messages are used to make
                and break time-slot assignments between line
                units and DS0s on a per-call basis.

                A separate DS0 data link, called the Embedded
                Operations Channel (EOC), is used to transmit
                operations messages between RDT and LDS/OSs.

                The initial protection channel for the EOC is
                channel number 12 of a DS1 and channel number
                24 on the same DS1 is reserved for TMC
                protection.  Note that GR-303-CORE states that
                protection switching for DS1 lines is optional.

                GR-303-CORE R5-263 [1835] An RDT and an IDT
                shall support EOC and TMC/CSC path protection
                switching on systems supporting more than one DS1.

                R5-264 [505] An RDT and an IDT shall receive
                from a remote managing system and process
                retrieval of time slots for the second EOC
                (i.e., the initial standby) and the second TMC
                or CSC.

                R5-266 [507] An RDT and an IDT shall receive
                from a remote managing system and process
                requests to assign and to retrieve the DS1 line
                for the standby EOC and the standby TMC/CSC.

                The value will be zero if the Interface Group
                is not installed on a specific card."
            REFERENCE
                "GR-303-CORE R5-263 [1835], R5-264 [505],
                R5-266 [507]"
            ::= { interfaceGroupEntry 7 }


--
        -- 1.3.6.1.4.1.5504.4.3.1.1.1.8
        igSecondaryEocTmcDs1IfIndex OBJECT-TYPE
            SYNTAX InterfaceIndexOrZero
            MAX-ACCESS read-only
            STATUS current
            DESCRIPTION
                "Refer to the description for igPrimaryEocTmcDs1IfIndex.

                This object refers to the ifIndex for the DS1
                line supporting the standy EOC and TMC path
                protection switching.  The value for this object
                is equal to the value of ifIndex from the
                Interfaces table of MIB II (RFC 1213).

                The value will be zero if the Interface Group
                is not installed on a specific card or no secondary
                DS1 is provisioned."
            REFERENCE
                "GR-303-CORE R5-263 [1835], R5-264 [505],
                R5-266 [507]"
            ::= { interfaceGroupEntry 8 }


--
-- Interface Group Status Objects
--
--
        -- 1.3.6.1.4.1.5504.4.3.1.1.1.9
        igAdminStatus OBJECT-TYPE
            SYNTAX INTEGER
                {
                inService(1),
                outOfService(2)
                }
            MAX-ACCESS read-create
            STATUS current
            DESCRIPTION
                "GR-303-CORE The following requirements on status
                and control of the overall RDT and IDT may also
                be used during service assurance (e.g., placing
                out-of-service for maintenance purposes). Placing
                an RDT out-of-service means stopping it from
                providing access services to the customers. It
                does not mean cutting off communication with a
                managing system (eg, ZMS) that controls the RDT.

                R5-20 [272] An RDT shall receive from a remote
                managing system (eg, ZMS) and process requests
                to place the RDT out-of-service or in-service.
                An RDT shall confirm with the managing system
                before executing the request to place the system
                out-of-service.

                R5-21 [273] An RDT shall receive from a remote
                managing system (eg, ZMS) and process requests
                to retrieve the servic status of the RDT (in
                or out of service).

                Valid values are InService and OutOfService.

                When an Interface Group is in outOfService state,
                it is removed from the GR303 protocol stack and
                is no longer installed on a specific card.

                This field is mandatory for IG row creation."
            REFERENCE
                "GR-303-CORE R5-20 [272], R5-21 [273]"
            ::= { interfaceGroupEntry 9 }


--
        -- 1.3.6.1.4.1.5504.4.3.1.1.1.10
        igOperationalStatus OBJECT-TYPE
            SYNTAX INTEGER
                {
                operable(1),
                inoperable(2),
                standby(3),
                inoperableIsInProgress(4),
                inoperableOosInProgress(5)
                }
            MAX-ACCESS read-only
            STATUS current
            DESCRIPTION
                "GR-303-CORE R5-22 [274] Upon request by a remote
                managing system (eg, ZMS), an RDT shall provide
                a managing system with the RDT operational status
                indicating whether it is fully inoperable and
                unable to provide service to the user, or it is
                fully operable and available for use.

                Valid values are operable, inoperable, standby,
                inoperableIsInProgress and inoperableOosInProgress.

                Clarification table of igAdminStatus and
                igOperationalStatus:

                igAdminStatus  igOperationalStatus Description
                -------------  ------------------- -----------
                outOfService   operable            not valid
                outOfService   inoperable          admin of service
                outOfService   standby             not valid
                inService      operable            normal operations
                inService      inOperable          fault
                inService      standby             normal operations"
            REFERENCE
                "GR-303-CORE R5-22 [274]"
            ::= { interfaceGroupEntry 10 }


--
        -- 1.3.6.1.4.1.5504.4.3.1.1.1.11
        igPeerStatus OBJECT-TYPE
            SYNTAX INTEGER
                {
                noStandbyConfigured(1),
                configuredAndAvailable(2),
                configuredAndUnavailable(3)
                }
            MAX-ACCESS read-only
            STATUS current
            DESCRIPTION
                "The status of the peer (or standby) Interface Group
                Valid peer status values are
                    * noStandbyConfigured
                    * configuredAndAvailable
                    * configuredAndUnavailable"
            ::= { interfaceGroupEntry 11 }


--
-- Interface Group Call Summary Objects
--
--
        -- 1.3.6.1.4.1.5504.4.3.1.1.1.12
        igMaxConfigCalls OBJECT-TYPE
            SYNTAX Gauge32 (22..670)
            UNITS "calls"
            MAX-ACCESS read-only
            STATUS current
            DESCRIPTION
                "GR-303-CORE 1.3.2 Generic IDLC Interface
                Requirements Summary. The Generic IDLC Interface
                uses a separate 64-kb/s data link (DS0-channel)
                to perform per-call time-slot assignments.
                igMaxActiveCalls refers to the maximum number of
                calls available to this Interface Group. This is
                used in conjunction with igCurrActiveCalls, the
                current number of calls, to provide a metric
                for describing utilization.  Does not imply that
                a call has completed, but rather that the DS0
                time-slot has been allocated for a call by the
                GR-303 interface.

                The DS1 frame is composed of 24 consecutively
                numbered (1-24) time-slots (channels or DS0s).

                Maximum number of active calls is the maximum
                number of DS1s assigned to the IG times the
                maximum number of channels or DS0s per DS1
                less 2 or 4 channels for primary only EOC/TCM
                and primary/secondary EOC/TCM =
                ({1..28} * 24 - {2,4}) = {22..670}

                28*24 equals maximum number of DS0's on a DS3,
                with 0 signaling channels. If you have one
                28-T1 IG with no redundancy you can have
                672 - 2 signaling DS0's , or 670, or 670
                DS0's available for active calls.

                If you have a single-T1 IG, you have only
                24 - 2 signaling DS0's, or 22,  DS0's
                available for active calls."
            REFERENCE
                "GR-303-CORE 1.3.2, 4.4.2"
            ::= { interfaceGroupEntry 12 }


--
        -- 1.3.6.1.4.1.5504.4.3.1.1.1.13
        igCurrActiveCalls OBJECT-TYPE
            SYNTAX Gauge32 (0..670)
            UNITS "calls"
            MAX-ACCESS read-only
            STATUS current
            DESCRIPTION
                "The number of calls currently in use.
                igCurrActiveCalls is used in conjunction with
                igMaxActiveCalls, the maximum number of calls
                available, to provide a metric for describing
                current utilization.  Does not imply that a call
                has completed, but rather that the DS0 time-slot
                has been allocated for a call by the GR-303
                interface.

                The DS1 frame is composed of 24 consecutively
                numbered (1-24) time-slots (channels or DS0s).

                Maximum number of currently active calls is the
                maximum number of DS1s assigned to the IG times
                the maximum number of channels or DS0s per DS1
                less 2 or 4 channels for primary only EOC/TCM
                and primary/secondary EOC/TCM =
                ({1..28} * 24 - {2,4}) = {22..670}

                28*24 equals maximum number of DS0's on a DS3,
                with 0 signaling channels. If you have one
                28-T1 IG with no redundancy you can have
                672 - 2 signaling DS0's , or 670, or 670
                DS0's available for active calls.

                If you have a single-T1 IG, you have only
                24 - 2 signaling DS0's, or 22,  DS0's
                available for active calls."
            REFERENCE
                "GR-303-CORE"
            ::= { interfaceGroupEntry 13 }


--
        -- 1.3.6.1.4.1.5504.4.3.1.1.1.14
        igStatsTimeElapsed OBJECT-TYPE
            SYNTAX Integer32 (0..899)
            UNITS "seconds"
            MAX-ACCESS read-only
            STATUS current
            DESCRIPTION
                "The number of seconds that have elapsed since
                the beginning of the current collection
                period.  If, for some reason, such as an
                adjustment in the system's time-of-day clock,
                the current interval exceeds the maximum value,
                the agent will return the maximum value."
            ::= { interfaceGroupEntry 14 }


--
        -- 1.3.6.1.4.1.5504.4.3.1.1.1.15
        igStatsValidIntervals OBJECT-TYPE
            SYNTAX Integer32 (0..96)
            UNITS "intervals"
            MAX-ACCESS read-only
            STATUS current
            DESCRIPTION
                "The number of previous intervals for which
                data was collected.  The value will typically
                be 24, 48, 72, or 96 unless the interface
                group was brought online within the last 6,
                12, 18, or 24 hours, in which case the value
                will be the number of complete 15 minute
                intervals since the interface has been
                online.

                In the case where the agent is an SNMP
                transport bridging proxy or SNMP translating
                proxy, it is possible that some intervals
                are unavailable. In this case, this interval
                is the maximum interval number for which
                data is available."
            ::= { interfaceGroupEntry 15 }


--
        -- 1.3.6.1.4.1.5504.4.3.1.1.1.16
        igStatsInvalidIntervals OBJECT-TYPE
            SYNTAX INTEGER (0..96)
            UNITS "intervals"
            MAX-ACCESS read-only
            STATUS current
            DESCRIPTION
                "The number of intervals in the range from 0 to
                igStatsValidIntervals for which no data is
                available.  This object will typically be zero
                except in cases where the data for some intervals
                are not available (e.g., in proxy situations)."
            ::= { interfaceGroupEntry 16 }


--
-- Interface Group Row Status
--
        -- 1.3.6.1.4.1.5504.4.3.1.1.1.17
        igRowStatus OBJECT-TYPE
            SYNTAX ZhoneRowStatus
            MAX-ACCESS read-create
            STATUS current
            DESCRIPTION
                "Used to control row creation and deletion.

                A row in this table is created using a single
                SNMP SET request with varbinds for:
                a) igRowStatus set to'CreateAndGo',
                b) the following READ-CREATE object(s) without a
                   default value (DEFVAL):
                   * igNameId
                c) the following READ-CREATE objects with a
                   DEFVAL but whose defined default value is
                   inappropriate:
                   * igSwitchType
                   * igAdminStatus
                   * igStatsPeriod.
                   From augmented igControlChannelEntry:
                   * igControlChannelT303
                   * igControlChannelT396
                   * igSapi0MaxOutstandingFrames,
                     igSapi1MaxOutstandingFrames
                   * igSapi0N200, igSapi1N200
                   * igSapi0T200, igSapi1T200
                   * igSapi0T203, igSapi1T203
                   * igSapiPpsMode

                If 'createAndGo' successfully created a new row,
                the RowStatus will be 'active'.  Subsequent to
                successful row creation, the RowStatus can be
                retrieved via an SNMP GET and the returned
                RowStatus value is active.  If the 'createAndGo'
                was unsuccessful an SNMP error will be returned
                and a subsequent GET on the non-existent row
                will also return an SNMP error of noSuchInstance.
                An SNMP SET with the RowStatus value of 'destroy'
                indicates that the agent should remove the row
                from service and then delete it.

                The same rows must also be simultaneously created
                or deleted in all augmenting tables:
                * igControlChannelTable
                * igStatsCurrentTable
                * igStatsTotalTable"
            ::= { interfaceGroupEntry 17 }


--
        -- 1.3.6.1.4.1.5504.4.3.1.1.1.18
        igWorkingMode OBJECT-TYPE
            SYNTAX INTEGER
                {
                active(1),
                passive(2)
                }
            MAX-ACCESS read-create
            STATUS current
            DESCRIPTION
                "Working mode indicates whether the selected switch can configure
                the RDT using common management information service (CMIS) over
                the Embedded Operations Channel (EOC) channel.

                There are two working mode states, active and passive.

                In the active mode, the seleted switch can configure the RDT for
                Call Reference Values (CRVs) over the EOC channel.

                In the passive state, CRVs can only be configured locally.

                Even with the switch in the active state, however, RDT is required
                to configure CRVs.

                This field can only be modified after setting the igAdminStatus
                of the IG record to outOfService.

                This field is mandatory when provisioning an interfaceGroupEntry."
            ::= { interfaceGroupEntry 18 }


--
-- The Interface Group Control Channel Table (AUGMENT)
-- This table augments the Interface Group Table.
--
        -- 1.3.6.1.4.1.5504.4.3.1.2
        igControlChannelTable OBJECT-TYPE
            SYNTAX SEQUENCE OF IgControlChannelEntry
            MAX-ACCESS not-accessible
            STATUS current
            DESCRIPTION
                "The GR-303 Interface Group Control Channel Table.

                The maximum number of entries is identical
                to that of the Interface Group Table.  the
                interfaceGroupTable is the base table for
                this augmented table."
            ::= { zhoneGR303 2 }


        -- 1.3.6.1.4.1.5504.4.3.1.2.1
        igControlChannelEntry OBJECT-TYPE
            SYNTAX IgControlChannelEntry
            MAX-ACCESS not-accessible
            STATUS current
            DESCRIPTION
                "An entry in the igControlChannelTable which
                AUGMENTs the base table interfaceGroupTable.
                There is a 1-to-1 correspondence between rows
                in interfaceGroupTable and rows in this table.
                When a row is created in the base table
                interfaceGroupTable, the corresponding row in
                the augmenting table igControlChannelTable must
                also be simultaneously created.  A row in this
                table is created by setting the value of
                igRowStatus to 'CreateAndGo' and setting the
                appropriate values for the columns.  Likewise,
                when a row expires by setting the value of
                igRowStatus to 'destroy' in the interfaceGroupTable
                base table, the same row also expires in this
                augmenting table."
            AUGMENTS { interfaceGroupEntry }
            ::= { igControlChannelTable 1 }


        IgControlChannelEntry ::=
            SEQUENCE {
                igControlChannelTmcPrimarySvcState
                    INTEGER,
                igControlChannelTmcSecondarySvcState
                    INTEGER,
                igControlChannelT303
                    Integer32,
                igControlChannelT396
                    Integer32,
                igSapi0MaxOutstandingFrames
                    Integer32,
                igSapi0N200
                    Integer32,
                igSapi0T200
                    Integer32,
                igSapi0T203
                    Integer32,
                igSapi0PpsMode
                    INTEGER,
                igSapi1MaxOutstandingFrames
                    Integer32,
                igSapi1N200
                    Integer32,
                igSapi1T200
                    Integer32,
                igSapi1T203
                    Integer32,
                igSapi1PpsMode
                    INTEGER,
                igControlChannelEocPrimarySvcState
                    INTEGER,
                igControlChannelEocSecondarySvcState
                    INTEGER
             }

--
        -- 1.3.6.1.4.1.5504.4.3.1.2.1.1
        igControlChannelTmcPrimarySvcState OBJECT-TYPE
            SYNTAX INTEGER
                {
                active(1),
                standby(2),
                outOfService(3)
                }
            MAX-ACCESS read-only
            STATUS current
            DESCRIPTION
                "Represents conditions that are currently present
                at the given entity and can affect the service
                state.  Valid values are active, standby, outOfService."
            ::= { igControlChannelEntry 1 }


--
        -- 1.3.6.1.4.1.5504.4.3.1.2.1.2
        igControlChannelTmcSecondarySvcState OBJECT-TYPE
            SYNTAX INTEGER
                {
                active(1),
                standby(2),
                outOfService(3)
                }
            MAX-ACCESS read-only
            STATUS current
            DESCRIPTION
                "Represents conditions that are currently present
                at the given entity and can affect the service
                state.  Valid values are active, standby, outOfService."
            ::= { igControlChannelEntry 2 }


--
        -- 1.3.6.1.4.1.5504.4.3.1.2.1.3
        igControlChannelT303 OBJECT-TYPE
            SYNTAX Integer32 (700 | 1200 | 1700 | 2200 | 2700 | 3200 | 3700 | 4200 | 4700)
            UNITS "milliseconds"
            MAX-ACCESS read-create
            STATUS current
            DESCRIPTION
                "Value of the T303 timer for the Q931 protocol

                12.5.5.17.1 T303
                T303 is the length of time that the IDT and RDT
                will wait for a reply to a SETUP message.

                R12-446 [1315] At the IDT, the value of T303 is
                not user settable, its value depends on specific
                vendor implementations, but shall be within the
                range of 700 ms to 4 seconds.

                R12-447 [1316] The above range is not intended to
                define acceptable response-time performance at
                the RDT, where the low-load (i.e., no other
                external stimuli requiring call processing
                activity) mean response time to a SETUP message
                shall be no greater than 200 ms.

                R12-448 [1317] At the RDT, the value of T303
                shall be provisionable from 700 ms through 4.7
                seconds in steps of 500 ms; the default shall be
                700 ms.

                R12-449 [1318] The above range is not intended
                to define acceptable response-time performance
                at the IDT, where the low-load (i.e., no other
                external stimuli requiring call processing
                activity) mean response time to a SETUP message
                shall be no greater than 500 ms.

                Units in milliseconds."
            REFERENCE
                "GR-303-CORE 12.5.5.17.1"
            DEFVAL { 700 }
            ::= { igControlChannelEntry 3 }


--
        -- 1.3.6.1.4.1.5504.4.3.1.2.1.4
        igControlChannelT396 OBJECT-TYPE
            SYNTAX Integer32 (700 | 1700 | 2700 | 3700 | 4700 | 5700 | 6700 | 7700 | 8700 | 9700 | 10700 | 11700 | 12700 | 13700 | 14700)
            UNITS "milliseconds"
            MAX-ACCESS read-create
            STATUS current
            DESCRIPTION
                "Value of the T396 timer for the Q931 protocol.

                12.5.5.17.9 T396
                T396 is the length of time that the RDT will
                wait for a reply to a SETUP message following
                the initial expiration of timer T303.

                R12-459 [1328] The value of T396 shall be
                provisionable from 700 ms through 14.7 seconds
                in steps of 1 second; the default shall be 14.7
                seconds.

                R12-460 [1329] The above range is not intended
                to define acceptable response-time performance
                at the IDT, where the low-load (i.e., no other
                external stimuli requiring call processing
                activity) mean response time to a SETUP message
                shall be no greater than 500 ms.

                Units in milliseconds."
            REFERENCE
                "GR-303-CORE 12.5.5.17.9"
            DEFVAL { 14700 }
            ::= { igControlChannelEntry 4 }


--
        -- 1.3.6.1.4.1.5504.4.3.1.2.1.5
        igSapi0MaxOutstandingFrames OBJECT-TYPE
            SYNTAX Integer32 (1..7)
            UNITS "frames"
            MAX-ACCESS read-create
            STATUS current
            DESCRIPTION
                "R5-97 [339] For each data link service access
                point (i.e., each SAPI=0 and SAPI=1, for both the
                active and standby data links, per IG), an RDT
                and an IDT shall receive from a remote managing
                system and process assignment and retrieval of
                the following LAPD parameters for the purpose of
                remote provisioning the layer 2 connection:

                a. Maximum number of outstanding information
                frames at layer 2

                Range of valid values is 1-7.  Default value is 7.

                Units in frames."
            REFERENCE
                "GR-303-CORE 97a."
            DEFVAL { 7 }
            ::= { igControlChannelEntry 5 }


--
        -- 1.3.6.1.4.1.5504.4.3.1.2.1.6
        igSapi0N200 OBJECT-TYPE
            SYNTAX Integer32 (1..10)
            MAX-ACCESS read-create
            STATUS current
            DESCRIPTION
                "R5-97 [339] For each data link service access
                point (i.e., each SAPI=0 and SAPI=1, for both
                the active and standby data links, per IG), an
                RDT and an IDT shall receive from a remote
                managing system and process assignment and
                retrieval of the following LAPD parameters for
                the purpose of remote provisioning the layer 2
                connection:

                b. Maximum number of retransmission for a frame
                at layer 2 (N200)

                12.4.3.5.3 Maximum Number of Retransmissions (N200)
                R12-15 [887] The maximum number of retransmission
                of a frame allowed, N200 shall be user selectable
                within the range of 1 to 10, inclusive, with a
                step size of 1 and a default value of 3."
            REFERENCE
                "GR-303-CORE 97b."
            DEFVAL { 3 }
            ::= { igControlChannelEntry 6 }


--
        -- 1.3.6.1.4.1.5504.4.3.1.2.1.7
        igSapi0T200 OBJECT-TYPE
            SYNTAX Integer32 (100 | 150 | 200 | 250 | 300 | 350)
            UNITS "milliseconds"
            MAX-ACCESS read-create
            STATUS current
            DESCRIPTION
                "R5-97 [339] For each data link service access
                point (i.e., each SAPI=0 and SAPI=1, for both
                the active and standby data links, per IG), an
                RDT and an IDT shall receive from a remote
                managing system and process assignment and
                retrieval of the following LAPD parameters for
                the purpose of remote provisioning the layer 2
                connection:

                c. Maximum layer 2 wait time for an acknowledgment
                of a transmitted frame (T200)

                12.4.3.5.6 Timer T200
                Timer T200 specifies the waiting period for
                receipt of an acknowledgment of a transmitted
                frame. A study of LAPD suggests that T200 should
                be at least as great as the time required to
                transmit three information frames. (See IEEE
                Publication CH2175-8/85/0000-0121.) Therefore,
                to protect against timeouts in an error-free
                condition, the default value of T200 for each
                SAP is sufficient to allow for the transmission
                of at least three frames.

                R12-18 [890] For all SAPs, the value of T200
                shall be user selectable within the range of
                100 ms to 350 ms, inclusive, the step size shall
                be 50 ms, and the default value of T200 shall
                be 150 ms.

                Units in milliseconds."
            REFERENCE
                "GR-303-CORE 97c."
            DEFVAL { 150 }
            ::= { igControlChannelEntry 7 }


--
        -- 1.3.6.1.4.1.5504.4.3.1.2.1.8
        igSapi0T203 OBJECT-TYPE
            SYNTAX Integer32 (10 | 20 | 30 | 40 | 50 | 60 | 70 | 80 | 90 | 100 | 110 | 120 | 130 | 140 | 150 | 160 | 170 | 180 | 190 | 200 | 210 | 220 | 230 | 240 | 250 | 260 | 270 | 280 | 290 | 300)
            UNITS "seconds"
            MAX-ACCESS read-create
            STATUS current
            DESCRIPTION
                "R5-97 [339] For each data link service access
                point (i.e., each SAPI=0 and SAPI=1, for both
                the active and standby data links, per IG), an
                RDT and an IDT shall receive from a remote
                managing system and process assignment and
                retrieval of the following LAPD parameters for
                the purpose of remote provisioning the layer 2
                connection:

                d. Maximum layer 2 idle time before connection
                verification is necessary (T203).

                12.4.3.5.9 Timer T203
                Timer T203 is used to time periods of inactivity
                on a data link. When T203 expires, a supervisory
                frame with the poll bit set to 1 is sent to
                determine if the other side of the interface is
                capable of sending and receiving frames. The
                use of T203 is discussed in greater detail in
                Section 12.6.3.3.

                R12-19 [891] For all SAPS, the value of T203
                shall be user selectable within the range of 10
                to 300 seconds, inclusive, the step size shall
                be 10 seconds, and the default value shall be
                30 seconds.

                Units in seconds."
            REFERENCE
                "GR-303-CORE 97d.
                "
            DEFVAL { 30 }
            ::= { igControlChannelEntry 8 }


--
        -- 1.3.6.1.4.1.5504.4.3.1.2.1.9
        igSapi0PpsMode OBJECT-TYPE
            SYNTAX INTEGER
                {
                inhibit(1),
                notInhibited(2),
                notApplicable(3)
                }
            MAX-ACCESS read-create
            STATUS current
            DESCRIPTION
                "DS1 protection switching option. Valid
                values are inhibit, notInhibited and
                notApplicable.  Note that SAPI 0 and SAPI 1
                (EOC-TMC) are not switched together.

                6.2.1 Facility Protection Switching - Option
                6.2.1.1 General
                The facility protection switching feature
                enables traffic on a failed DS1 facility to
                be moved to one or more alternate DS1 facilities.
                The procedures for implementing DS1 facility
                protection switching across the Generic IDLC
                Interface are described in Section 12.6.2.

                R6-75 [685] IDLC systems shall perform a
                facility protection switch if and only if
                that action will restore service.

                12.6.2 DS1 Facility Protection Switch - Option
                DS1 facility protection is an option for IDLC
                systems. The procedures to be followed when
                facility protection switching is implemented
                for the Generic IDLC Interface are presented
                in this section (see Section 6.2.1 for general
                facility protection switching requirements).

                A facility protection switching feature enables
                traffic on a failed or degraded DS1 facility
                to be moved to one or more alternate DS1
                facilities.

                R12-609 [1475] When an IDLC system includes
                the facility protection switching option, a
                dedicated protection facility with a 1:n
                arrangement shall be used for the Generic
                IDLC Interface.

                R12-625 [1491] The default for facility protection
                switching shall be notInhibited."
            REFERENCE
                "GR-303-CORE 6.2.1, 12.6.2"
            DEFVAL { notInhibited }
            ::= { igControlChannelEntry 9 }


--
        -- 1.3.6.1.4.1.5504.4.3.1.2.1.10
        igSapi1MaxOutstandingFrames OBJECT-TYPE
            SYNTAX Integer32 (1..7)
            UNITS "frames"
            MAX-ACCESS read-create
            STATUS current
            DESCRIPTION
                "Refer to igSapi0MaxOutstandingFrames

                Not supported."
            REFERENCE
                "GR-303-CORE 97a."
            DEFVAL { 7 }
            ::= { igControlChannelEntry 10 }


--
        -- 1.3.6.1.4.1.5504.4.3.1.2.1.11
        igSapi1N200 OBJECT-TYPE
            SYNTAX Integer32 (1..10)
            MAX-ACCESS read-create
            STATUS current
            DESCRIPTION
                "Refer to igSapi0N200

                Not supported."
            REFERENCE
                "GR-303-CORE 97b."
            DEFVAL { 3 }
            ::= { igControlChannelEntry 11 }


--
        -- 1.3.6.1.4.1.5504.4.3.1.2.1.12
        igSapi1T200 OBJECT-TYPE
            SYNTAX Integer32 (100 | 150 | 200 | 250 | 300 | 350)
            UNITS "milliseconds"
            MAX-ACCESS read-create
            STATUS current
            DESCRIPTION
                "Refer to igSapi0T200"
            REFERENCE
                "GR-303-CORE 97c."
            DEFVAL { 150 }
            ::= { igControlChannelEntry 12 }


--
        -- 1.3.6.1.4.1.5504.4.3.1.2.1.13
        igSapi1T203 OBJECT-TYPE
            SYNTAX Integer32 (10 | 20 | 30 | 40 | 50 | 60 | 70 | 80 | 90 | 100 | 110 | 120 | 130 | 140 | 150 | 160 | 170 | 180 | 190 | 200 | 210 | 220 | 230 | 240 | 250 | 260 | 270 | 280 | 290 | 300)
            UNITS "seconds"
            MAX-ACCESS read-create
            STATUS current
            DESCRIPTION
                "Refer to igSapi0T203"
            REFERENCE
                "GR-303-CORE 97d."
            DEFVAL { 30 }
            ::= { igControlChannelEntry 13 }


--
        -- 1.3.6.1.4.1.5504.4.3.1.2.1.14
        igSapi1PpsMode OBJECT-TYPE
            SYNTAX INTEGER
                {
                inhibit(1),
                notInhibited(2),
                notApplicable(3)
                }
            MAX-ACCESS read-create
            STATUS current
            DESCRIPTION
                "Refer to igSapi0PpsMode"
            REFERENCE
                "GR-303-CORE 6.2.1, 12.6.2"
            DEFVAL { notInhibited }
            ::= { igControlChannelEntry 14 }


--
        -- 1.3.6.1.4.1.5504.4.3.1.2.1.15
        igControlChannelEocPrimarySvcState OBJECT-TYPE
            SYNTAX INTEGER
                {
                active(1),
                standby(2),
                outOfService(3)
                }
            MAX-ACCESS read-only
            STATUS current
            DESCRIPTION
                "Represents conditions that are currently present
                at the given entity and can affect the service
                state.  Valid values are active, standby, outOfService."
            ::= { igControlChannelEntry 15 }


--
        -- 1.3.6.1.4.1.5504.4.3.1.2.1.17
        igControlChannelEocSecondarySvcState OBJECT-TYPE
            SYNTAX INTEGER
                {
                active(1),
                standby(2),
                outOfService(3)
                }
            MAX-ACCESS read-only
            STATUS current
            DESCRIPTION
                "Represents conditions that are currently present
                at the given entity and can affect the service
                state.  Valid values are active, standby, outOfService."
            ::= { igControlChannelEntry 17 }


--
-- The Interface Group Statistics Current Table (AUGMENT)
-- This table augments the Interface Group Table.
--
        -- 1.3.6.1.4.1.5504.4.3.1.3
        igStatsCurrentTable OBJECT-TYPE
            SYNTAX SEQUENCE OF IgStatsCurrentEntry
            MAX-ACCESS not-accessible
            STATUS current
            DESCRIPTION
                "The GR-303 Interface Group Statistics Current Table.

                The GR-303 Interface Group Statistics current
                table contains various statistics being collected
                for the current 15 minute interval.

                The maximum number of entries is identical to that
                of the Interface Group Table. the interfaceGroupTable
                is the base table for this augmented table."
            ::= { zhoneGR303 3 }


        -- 1.3.6.1.4.1.5504.4.3.1.3.1
        igStatsCurrentEntry OBJECT-TYPE
            SYNTAX IgStatsCurrentEntry
            MAX-ACCESS not-accessible
            STATUS current
            DESCRIPTION
                "An entry in the igStatsCurrentTable which
                AUGMENTs the base table interfaceGroupTable.
                There is a 1-to-1 correspondence between rows
                in interfaceGroupTable and rows in this table.
                When a row is created in the base table
                interfaceGroupTable, the corresponding row in
                the augmenting table igStatsCurrentTable must
                also be simultaneously created.  A row in this
                table is created by setting the value of
                igRowStatus to 'CreateAndGo' and setting the
                appropriate values for the columns.  Likewise,
                when a row expires by setting the value of
                igRowStatus to 'destroy' in the interfaceGroupTable
                base table, the same row also expires in this
                augmenting table."
            AUGMENTS { interfaceGroupEntry }
            ::= { igStatsCurrentTable 1 }


        IgStatsCurrentEntry ::=
            SEQUENCE {
                igCurrentOutboundCalls
                    PerfCurrentCount,
                igCurrentInboundCalls
                    PerfCurrentCount,
                igCurrentOutboundCallsBlocked
                    PerfCurrentCount,
                igCurrentGR303ProtocolErrors
                    PerfCurrentCount,
                igCurrentTMCLapdSent
                    PerfCurrentCount,
                igCurrentTMCLapdRcvd
                    PerfCurrentCount,
                igCurrentTMCLapdRcvdErrs
                    PerfCurrentCount,
                igCurrentEOCLapdSent
                    PerfCurrentCount,
                igCurrentEOCLapdRcvd
                    PerfCurrentCount,
                igCurrentEOCLapdRcvdErrs
                    PerfCurrentCount
             }

--
        -- 1.3.6.1.4.1.5504.4.3.1.3.1.1
        igCurrentOutboundCalls OBJECT-TYPE
            SYNTAX PerfCurrentCount
            UNITS "calls"
            MAX-ACCESS read-only
            STATUS current
            DESCRIPTION
                "The number of outbound calls completed."
            ::= { igStatsCurrentEntry 1 }


--
        -- 1.3.6.1.4.1.5504.4.3.1.3.1.2
        igCurrentInboundCalls OBJECT-TYPE
            SYNTAX PerfCurrentCount
            UNITS "calls"
            MAX-ACCESS read-only
            STATUS current
            DESCRIPTION
                "The number of inbound calls completed."
            ::= { igStatsCurrentEntry 2 }


--
        -- 1.3.6.1.4.1.5504.4.3.1.3.1.3
        igCurrentOutboundCallsBlocked OBJECT-TYPE
            SYNTAX PerfCurrentCount
            UNITS "calls"
            MAX-ACCESS read-only
            STATUS current
            DESCRIPTION
                "The number of outbound calls that were blocked due
                to no available time-slot."
            ::= { igStatsCurrentEntry 3 }


--
        -- 1.3.6.1.4.1.5504.4.3.1.3.1.4
        igCurrentGR303ProtocolErrors OBJECT-TYPE
            SYNTAX PerfCurrentCount
            UNITS "errors"
            MAX-ACCESS read-only
            STATUS current
            DESCRIPTION
                "The number of GR-303 Protocol errors."
            ::= { igStatsCurrentEntry 4 }


--
        -- 1.3.6.1.4.1.5504.4.3.1.3.1.5
        igCurrentTMCLapdSent OBJECT-TYPE
            SYNTAX PerfCurrentCount
            UNITS "frames"
            MAX-ACCESS read-only
            STATUS current
            DESCRIPTION
                "The number of LAPD frames sent on the Time-slot
                Management Channel (TMC)."
            ::= { igStatsCurrentEntry 5 }


--
        -- 1.3.6.1.4.1.5504.4.3.1.3.1.6
        igCurrentTMCLapdRcvd OBJECT-TYPE
            SYNTAX PerfCurrentCount
            UNITS "frames"
            MAX-ACCESS read-only
            STATUS current
            DESCRIPTION
                "The number LAPD frames received on the Time-slot
                Management Channel (TMC)."
            ::= { igStatsCurrentEntry 6 }


--
        -- 1.3.6.1.4.1.5504.4.3.1.3.1.7
        igCurrentTMCLapdRcvdErrs OBJECT-TYPE
            SYNTAX PerfCurrentCount
            UNITS "frames"
            MAX-ACCESS read-only
            STATUS current
            DESCRIPTION
                "The number LAPD frames received in error on the
                Time-slot Management Channel (TMC)."
            ::= { igStatsCurrentEntry 7 }


--
        -- 1.3.6.1.4.1.5504.4.3.1.3.1.8
        igCurrentEOCLapdSent OBJECT-TYPE
            SYNTAX PerfCurrentCount
            UNITS "frames"
            MAX-ACCESS read-only
            STATUS current
            DESCRIPTION
                "The number of LAPD frames sent on the Embedded
                Operations Channel (EOC)."
            ::= { igStatsCurrentEntry 8 }


--
        -- 1.3.6.1.4.1.5504.4.3.1.3.1.9
        igCurrentEOCLapdRcvd OBJECT-TYPE
            SYNTAX PerfCurrentCount
            UNITS "frames"
            MAX-ACCESS read-only
            STATUS current
            DESCRIPTION
                "The number of LAPD frames received on the Embedded
                Operations Channel (EOC)."
            ::= { igStatsCurrentEntry 9 }


--
        -- 1.3.6.1.4.1.5504.4.3.1.3.1.10
        igCurrentEOCLapdRcvdErrs OBJECT-TYPE
            SYNTAX PerfCurrentCount
            UNITS "frames"
            MAX-ACCESS read-only
            STATUS current
            DESCRIPTION
                "The number of LAPD frames received in error on the
                Embedded Operations Channel (EOC)."
            ::= { igStatsCurrentEntry 10 }


--
-- The Interface Group Statistics Interval Table
--
        -- 1.3.6.1.4.1.5504.4.3.1.4
        igStatsIntervalTable OBJECT-TYPE
            SYNTAX SEQUENCE OF IgStatsIntervalEntry
            MAX-ACCESS not-accessible
            STATUS current
            DESCRIPTION
                "GR-303 Interface Group Statistics Interval Table.

                The GR-303 Interface Group Statistics Interval
                Table contains various statistics collected by
                each Interface Group over the previous 6. 12.
                18, or 24 hours of operation.  The past 6, 12,
                18, or 24 hours are broken into 24, 48, 72, or
                96 completed 15 minute intervals.  Each row in
                this table represents one such interval
                (identified by igIntervalNumber) for one
                specific instance (identified by igIntervalIndex)."
            ::= { zhoneGR303 4 }


        -- 1.3.6.1.4.1.5504.4.3.1.4.1
        igStatsIntervalEntry OBJECT-TYPE
            SYNTAX IgStatsIntervalEntry
            MAX-ACCESS not-accessible
            STATUS current
            DESCRIPTION
                "An entry in the igStatsIntervalTable.  Indexed by
                (igNameId, igIntervalNumber)."
            INDEX { igNameId, igIntervalNumber }
            ::= { igStatsIntervalTable 1 }


        IgStatsIntervalEntry ::=
            SEQUENCE {
                igIntervalNumber
                    INTEGER,
                igIntervalOutboundCalls
                    PerfCurrentCount,
                igIntervalInboundCalls
                    PerfCurrentCount,
                igIntervalOutboundCallsBlocked
                    PerfCurrentCount,
                igIntervalGR303ProtocolErrors
                    PerfCurrentCount,
                igIntervalTMCLapdSent
                    PerfCurrentCount,
                igIntervalTMCLapdRcvd
                    PerfCurrentCount,
                igintervalTMCLapdRcvdErrs
                    PerfCurrentCount,
                igIntervalEOCLapdSent
                    PerfCurrentCount,
                igIntervalEOCLapdRcvd
                    PerfCurrentCount,
                igIntervalEOCLapdRcvdErrs
                    PerfCurrentCount,
                igIntervalValidData
                    TruthValue
             }

--
        -- 1.3.6.1.4.1.5504.4.3.1.4.1.1
        igIntervalNumber OBJECT-TYPE
            SYNTAX INTEGER (1..96)
            MAX-ACCESS not-accessible
            STATUS current
            DESCRIPTION
                "A number between 1 and 96, where 1 is the most
                recently completed 15 minute interval and 96 is
                the 15 minutes interval completed 23 hours and 45
                minutes prior to interval 1.  If a 6, 12, or 18
                hour period is selected, the max interval number
                will be 24, 48, or 72."
            ::= { igStatsIntervalEntry 1 }


--
        -- 1.3.6.1.4.1.5504.4.3.1.4.1.2
        igIntervalOutboundCalls OBJECT-TYPE
            SYNTAX PerfCurrentCount
            UNITS "calls"
            MAX-ACCESS read-only
            STATUS current
            DESCRIPTION
                "The number of outbound calls completed."
            ::= { igStatsIntervalEntry 2 }


--
        -- 1.3.6.1.4.1.5504.4.3.1.4.1.3
        igIntervalInboundCalls OBJECT-TYPE
            SYNTAX PerfCurrentCount
            UNITS "calls"
            MAX-ACCESS read-only
            STATUS current
            DESCRIPTION
                "The number of inbound calls completed."
            ::= { igStatsIntervalEntry 3 }


--
        -- 1.3.6.1.4.1.5504.4.3.1.4.1.4
        igIntervalOutboundCallsBlocked OBJECT-TYPE
            SYNTAX PerfCurrentCount
            UNITS "calls"
            MAX-ACCESS read-only
            STATUS current
            DESCRIPTION
                "The number of outbound calls that were blocked due
                to no available time-slot."
            ::= { igStatsIntervalEntry 4 }


--
        -- 1.3.6.1.4.1.5504.4.3.1.4.1.5
        igIntervalGR303ProtocolErrors OBJECT-TYPE
            SYNTAX PerfCurrentCount
            UNITS "errors"
            MAX-ACCESS read-only
            STATUS current
            DESCRIPTION
                "The number of GR-303 Protocol errors."
            ::= { igStatsIntervalEntry 5 }


--
        -- 1.3.6.1.4.1.5504.4.3.1.4.1.6
        igIntervalTMCLapdSent OBJECT-TYPE
            SYNTAX PerfCurrentCount
            UNITS "frames"
            MAX-ACCESS read-only
            STATUS current
            DESCRIPTION
                "The number of LAPD frames sent on the Time-slot
                Management Channel (TMC)."
            ::= { igStatsIntervalEntry 6 }


--
        -- 1.3.6.1.4.1.5504.4.3.1.4.1.7
        igIntervalTMCLapdRcvd OBJECT-TYPE
            SYNTAX PerfCurrentCount
            UNITS "frames"
            MAX-ACCESS read-only
            STATUS current
            DESCRIPTION
                "The number LAPD frames received on the Time-slot
                Management Channel (TMC)."
            ::= { igStatsIntervalEntry 7 }


--
        -- 1.3.6.1.4.1.5504.4.3.1.4.1.8
        igintervalTMCLapdRcvdErrs OBJECT-TYPE
            SYNTAX PerfCurrentCount
            UNITS "frames"
            MAX-ACCESS read-only
            STATUS current
            DESCRIPTION
                "The number LAPD frames received in error on the
                Time-slot Management Channel (TMC)."
            ::= { igStatsIntervalEntry 8 }


--
        -- 1.3.6.1.4.1.5504.4.3.1.4.1.9
        igIntervalEOCLapdSent OBJECT-TYPE
            SYNTAX PerfCurrentCount
            UNITS "frames"
            MAX-ACCESS read-only
            STATUS current
            DESCRIPTION
                "The number of LAPD frames sent on the Embedded
                Operations Channel (EOC)."
            ::= { igStatsIntervalEntry 9 }


--
        -- 1.3.6.1.4.1.5504.4.3.1.4.1.10
        igIntervalEOCLapdRcvd OBJECT-TYPE
            SYNTAX PerfCurrentCount
            UNITS "frames"
            MAX-ACCESS read-only
            STATUS current
            DESCRIPTION
                "The number of LAPD frames received on the Embedded
                Operations Channel (EOC)."
            ::= { igStatsIntervalEntry 10 }


--
        -- 1.3.6.1.4.1.5504.4.3.1.4.1.11
        igIntervalEOCLapdRcvdErrs OBJECT-TYPE
            SYNTAX PerfCurrentCount
            UNITS "frames"
            MAX-ACCESS read-only
            STATUS current
            DESCRIPTION
                "The number of LAPD frames received in error on the
                Embedded Operations Channel (EOC)."
            ::= { igStatsIntervalEntry 11 }


--
        -- 1.3.6.1.4.1.5504.4.3.1.4.1.12
        igIntervalValidData OBJECT-TYPE
            SYNTAX TruthValue
            MAX-ACCESS read-only
            STATUS current
            DESCRIPTION
                "This variable indicates if the data for this
                interval is valid."
            DEFVAL { false }
            ::= { igStatsIntervalEntry 12 }


--
-- The Interface Group Statistics Total Table (AUGMENT)
-- This table augments the Interface Group Tab
--
        -- 1.3.6.1.4.1.5504.4.3.1.5
        igStatsTotalTable OBJECT-TYPE
            SYNTAX SEQUENCE OF IgStatsTotalEntry
            MAX-ACCESS not-accessible
            STATUS current
            DESCRIPTION
                "GR-303 Interface Group Statistics Total Table.

                The GR-303 Interface Group Statistics Total
                Table contains the cumulative sum of the
                various statistics for the 24 hour period
                preceding the current interval.

                The maximum number of entries is identical to that
                of the Interface Group Table. The interfaceGroupTable
                is the base table for this augmented table."
            ::= { zhoneGR303 5 }


        -- 1.3.6.1.4.1.5504.4.3.1.5.1
        igStatsTotalEntry OBJECT-TYPE
            SYNTAX IgStatsTotalEntry
            MAX-ACCESS not-accessible
            STATUS current
            DESCRIPTION
                "An entry in the igStatsTotalTable which
                AUGMENTs the base table interfaceGroupTable.
                There is a 1-to-1 correspondence between rows
                in interfaceGroupTable and rows in this table.
                When a row is created in the base table
                interfaceGroupTable, the corresponding row in
                the augmenting table igStatsTotalTable must
                also be simultaneously created.  A row in this
                table is created by setting the value of
                igRowStatus to 'CreateAndGo' and setting the
                appropriate values for the columns.  Likewise,
                when a row expires by setting the value of
                igRowStatus to 'destroy' in the interfaceGroupTable
                base table, the same row also expires in this
                augmenting table."
            AUGMENTS { interfaceGroupEntry }
            ::= { igStatsTotalTable 1 }


        IgStatsTotalEntry ::=
            SEQUENCE {
                igTotalOutboundCalls
                    PerfCurrentCount,
                igTotalInboundCalls
                    PerfCurrentCount,
                igTotalOutboundCallsBlocked
                    PerfCurrentCount,
                igTotalGR303ProtocolErrors
                    PerfCurrentCount,
                igTotalTMCLapdSent
                    PerfCurrentCount,
                igTotalTMCLapdRcvd
                    PerfCurrentCount,
                igTotalTMCLapdRcvdErrs
                    PerfCurrentCount,
                igTotalEOCLapdSent
                    PerfCurrentCount,
                igTotalEOCLapdRcvd
                    PerfCurrentCount,
                igTotalEOCLapdRcvdErrs
                    PerfCurrentCount
             }

--
        -- 1.3.6.1.4.1.5504.4.3.1.5.1.1
        igTotalOutboundCalls OBJECT-TYPE
            SYNTAX PerfCurrentCount
            UNITS "calls"
            MAX-ACCESS read-only
            STATUS current
            DESCRIPTION
                "The number of outbound calls completed."
            ::= { igStatsTotalEntry 1 }


--
        -- 1.3.6.1.4.1.5504.4.3.1.5.1.2
        igTotalInboundCalls OBJECT-TYPE
            SYNTAX PerfCurrentCount
            UNITS "calls"
            MAX-ACCESS read-only
            STATUS current
            DESCRIPTION
                "The number of inbound calls completed."
            ::= { igStatsTotalEntry 2 }


--
        -- 1.3.6.1.4.1.5504.4.3.1.5.1.3
        igTotalOutboundCallsBlocked OBJECT-TYPE
            SYNTAX PerfCurrentCount
            UNITS "calls"
            MAX-ACCESS read-only
            STATUS current
            DESCRIPTION
                "The number of outbound calls that were blocked due
                to no available time-slot."
            ::= { igStatsTotalEntry 3 }


--
        -- 1.3.6.1.4.1.5504.4.3.1.5.1.4
        igTotalGR303ProtocolErrors OBJECT-TYPE
            SYNTAX PerfCurrentCount
            UNITS "errors"
            MAX-ACCESS read-only
            STATUS current
            DESCRIPTION
                "The number of GR-303 Protocol errors."
            ::= { igStatsTotalEntry 4 }


--
        -- 1.3.6.1.4.1.5504.4.3.1.5.1.5
        igTotalTMCLapdSent OBJECT-TYPE
            SYNTAX PerfCurrentCount
            UNITS "frames"
            MAX-ACCESS read-only
            STATUS current
            DESCRIPTION
                "The number of LAPD frames sent on the Time-slot
                Management Channel (TMC)."
            ::= { igStatsTotalEntry 5 }


--
        -- 1.3.6.1.4.1.5504.4.3.1.5.1.6
        igTotalTMCLapdRcvd OBJECT-TYPE
            SYNTAX PerfCurrentCount
            UNITS "frames"
            MAX-ACCESS read-only
            STATUS current
            DESCRIPTION
                "The number LAPD frames received on the Time-slot
                Management Channel (TMC)."
            ::= { igStatsTotalEntry 6 }


--
        -- 1.3.6.1.4.1.5504.4.3.1.5.1.7
        igTotalTMCLapdRcvdErrs OBJECT-TYPE
            SYNTAX PerfCurrentCount
            UNITS "frames"
            MAX-ACCESS read-only
            STATUS current
            DESCRIPTION
                "The number LAPD frames received in error on the
                Time-slot Management Channel (TMC)."
            ::= { igStatsTotalEntry 7 }


--
        -- 1.3.6.1.4.1.5504.4.3.1.5.1.8
        igTotalEOCLapdSent OBJECT-TYPE
            SYNTAX PerfCurrentCount
            UNITS "frames"
            MAX-ACCESS read-only
            STATUS current
            DESCRIPTION
                "The number of LAPD frames sent on the Embedded
                Operations Channel (EOC)."
            ::= { igStatsTotalEntry 8 }


--
        -- 1.3.6.1.4.1.5504.4.3.1.5.1.9
        igTotalEOCLapdRcvd OBJECT-TYPE
            SYNTAX PerfCurrentCount
            UNITS "frames"
            MAX-ACCESS read-only
            STATUS current
            DESCRIPTION
                "The number of LAPD frames received on the Embedded
                Operations Channel (EOC)."
            ::= { igStatsTotalEntry 9 }


--
        -- 1.3.6.1.4.1.5504.4.3.1.5.1.10
        igTotalEOCLapdRcvdErrs OBJECT-TYPE
            SYNTAX PerfCurrentCount
            UNITS "frames"
            MAX-ACCESS read-only
            STATUS current
            DESCRIPTION
                "The number of LAPD frames received in error on the
                Embedded Operations Channel (EOC)."
            ::= { igStatsTotalEntry 10 }


--
-- GR-303 DS1 Line Group
--
-- The GR-303 DS1 Line Group consists of the following table:
--     DS1 Line Mapping Table
--
-- The DS1 Line Mapping Table
--
        -- 1.3.6.1.4.1.5504.4.3.1.6
        ds1LineMappingTable OBJECT-TYPE
            SYNTAX SEQUENCE OF Ds1LineMappingEntry
            MAX-ACCESS not-accessible
            STATUS current
            DESCRIPTION
                "The GR-303 DS1 Line Mapping Table.

                The DS1 Line Mapping Table describes attributes
                for DS1 Line Termination and the mapping between
                the Interface Group and DS1 standard MIB (rfc2495).

                The maximum number of entries is determined by
                the maximum number of DS1 lines for the Interface
                Group, which is 28.  Each Interface Group is
                associated with a ds1LineMapping Table indexed
                by (IG name, line group ID, ds1 channel number),
                where line group ID is either a physical T1 line
                group ID (eg, Dibrizzi) or a channelized DS3.
                DS1 channel number is one of 28 DS1s associated
                with a channelized DS3, that is being provisioned
                to the Interface Group.  If line group ID is a T1,
                the associated DS1 channel number is 1.

                GR-303-CORE R12-508 [1377] The RDT is limited to
                a maximum of 28 DS1s per IG and each IG can
                support up to a maximum of 2048 two-wire
                terminations toward the customer's premises.

                Once a primary or secondary DS1 is provisioned for an
                IG it cannot be modified or deleted."
            REFERENCE
                "GR-303-CORE R12-508 [1377]"
            ::= { zhoneGR303 6 }


        -- 1.3.6.1.4.1.5504.4.3.1.6.1
        ds1LineMappingEntry OBJECT-TYPE
            SYNTAX Ds1LineMappingEntry
            MAX-ACCESS not-accessible
            STATUS current
            DESCRIPTION
                "An entry in the ds1LineMappingTable.  Indexed
                by (igNameId, dsnLgId, ds1ChannelNumber). A
                row in this table is created by setting the
                value of ds1LineMappingRowStatus to 'CreateAndGo',
                and setting the appropriate values for the columns."
            INDEX { igNameId, dsnLgId, ds1ChannelNumber }
            ::= { ds1LineMappingTable 1 }


        Ds1LineMappingEntry ::=
            SEQUENCE {
                dsnLgId
                    Integer32,
                ds1ChannelNumber
                    Integer32,
                ds1Role
                    INTEGER,
                ds1IfIndex
                    InterfaceIndexOrZero,
                ds1LineMappingRowStatus
                    ZhoneRowStatus,
                ds1LogicalId
                    Integer32
             }

--
        -- 1.3.6.1.4.1.5504.4.3.1.6.1.1
        dsnLgId OBJECT-TYPE
            SYNTAX Integer32 (1..2147483647)
            MAX-ACCESS not-accessible
            STATUS current
            DESCRIPTION
                "The dsnLgId object identifies the line group entry
                id of either a physical T1 line group ID (eg, Dibrizzi)
                or a channelized DS3.  If LgId represents a physical
                T1, the DS1 channel number is 1.  Else, the DS1
                channel number is one of 28 DS1s associated with a
                channelized DS3, that is being provisioned to the
                Interface Group.

                The range for dsnLgId is 1..2147483647 that is
                obtained by the nextLineGroupId field."
            ::= { ds1LineMappingEntry 1 }


--
        -- 1.3.6.1.4.1.5504.4.3.1.6.1.2
        ds1ChannelNumber OBJECT-TYPE
            SYNTAX Integer32 (1..28)
            MAX-ACCESS not-accessible
            STATUS current
            DESCRIPTION
                "Identifies the DS1 for the channelized DS3 or
                physical T1.  The ds1ChannelNumber for a T1 is 1,
                otherwise it refers to the channel number of the
                DS3 port which contains the DS1."
            ::= { ds1LineMappingEntry 2 }


--
        -- 1.3.6.1.4.1.5504.4.3.1.6.1.3
        ds1Role OBJECT-TYPE
            SYNTAX INTEGER
                {
                payload(1),
                secondary(2),
                primary(3)
                }
            MAX-ACCESS read-create
            STATUS current
            DESCRIPTION
                "The role the DS1 line assumes.  Valid values are
                payload, secondary, primary.

                This field is mandatory for ds1LineMapping row creation."
            ::= { ds1LineMappingEntry 3 }


--
        -- 1.3.6.1.4.1.5504.4.3.1.6.1.4
        ds1IfIndex OBJECT-TYPE
            SYNTAX InterfaceIndexOrZero
            MAX-ACCESS read-only
            STATUS current
            DESCRIPTION
                "The ifIndex for the DS1 line.  The value for this
                object is equal to the value of ifIndex from the
                Interfaces table of MIB II (RFC 1213).

                The value will be zero when the Interface Group
                is not installed on a specific card by the
                GR-303 protocol stack."
            ::= { ds1LineMappingEntry 4 }


--
        -- 1.3.6.1.4.1.5504.4.3.1.6.1.5
        ds1LineMappingRowStatus OBJECT-TYPE
            SYNTAX ZhoneRowStatus
            MAX-ACCESS read-create
            STATUS current
            DESCRIPTION
                "Used to control row creation and deletion.

                A row in this table is created using a single
                SNMP SET request with varbinds for:
                a) ds1LineMappingRowStatus set to'CreateAndGo',
                b) READ-CREATE objects with a DEFVAL but whose
                   defined default value is inappropriate:
                   * ds1Role

                See igRowStatus description for RowStatus semantics."
            ::= { ds1LineMappingEntry 5 }


--
        -- 1.3.6.1.4.1.5504.4.3.1.6.1.6
        ds1LogicalId OBJECT-TYPE
            SYNTAX Integer32 (1..28)
            MAX-ACCESS read-create
            STATUS current
            DESCRIPTION
                "This is an unique number to identify each physical DS1
                within an Interface Group between RDT and IDT. The DS1
                Logical ID must have a value in the range of 1..28.
                The value 1 is reserved for the primary DS1 and cannot
                be used by any other DS1s.

                This field is mandatory for ds1LineMappingEntry row creation."
            ::= { ds1LineMappingEntry 6 }


--
-- GR-303 CRV Group
--
-- The GR-303 CRV Group consists of the following table:
--     IG CRV Table
--
-- The IG CRV Table
--
        -- 1.3.6.1.4.1.5504.4.3.1.7
        igCrvTable OBJECT-TYPE
            SYNTAX SEQUENCE OF IgCrvEntry
            MAX-ACCESS not-accessible
            STATUS current
            DESCRIPTION
                "The GR-303 CRV Table.

                The GR-303-CORE interface uses the Call Reference
                Value (CRV) in its Timeslot Management Channel
                (TMC) to dynamically assign DS0s to access
                circuits on a call-by-call basis; i.e., if an
                access circuit is not assigned a CRV, it will
                never be assigned a DS0 between the IDT and IG.

                The maximum number of entries is specified by the
                maximum number of  subscribers or CRVs for the
                Interface Group, which is 2048.  Each Interface
                Group is associated with an igCrvTable indexed
                by (shelf, slot, IG name, CRV).

                GR-303-CORE R12-508 [1377] The RDT is limited to
                a maximum of 28 DS1s per IG and each IG can
                support up to a maximum of 2048 two-wire
                terminations toward the customer's premises."
            REFERENCE
                "GR-303-CORE R12-508 [1377]"
            ::= { zhoneGR303 7 }


        -- 1.3.6.1.4.1.5504.4.3.1.7.1
        igCrvEntry OBJECT-TYPE
            SYNTAX IgCrvEntry
            MAX-ACCESS not-accessible
            STATUS current
            DESCRIPTION
                "An entry in the igCrvTable. Indexed by (igNameId,
                igCrv).  A row in this table is created by
                setting the value of igCrvRowStatus to
                'CreateAndGo', and setting the appropriate
                values for the columns."
            INDEX { igNameId, igCrv }
            ::= { igCrvTable 1 }


        IgCrvEntry ::=
            SEQUENCE {
                igCrv
                    Integer32,
                igCrvLocalAdminState
                    INTEGER,
                igCrvRemoteAdminState
                    INTEGER,
                igCrvOperStatus
                    BITS,
                igCrvTmcState
                    INTEGER,
                igCrvSignalType
                    INTEGER,
                igCrvRowStatus
                    ZhoneRowStatus
             }

        -- 1.3.6.1.4.1.5504.4.3.1.7.1.1
        igCrv OBJECT-TYPE
            SYNTAX Integer32 (1..2048)
            MAX-ACCESS not-accessible
            STATUS current
            DESCRIPTION
                "The Call Reference Value (CRV) for the line.
                Indexes into the igCrvTable. Valid range is
                1-2048."
            ::= { igCrvEntry 1 }


--
        -- 1.3.6.1.4.1.5504.4.3.1.7.1.2
        igCrvLocalAdminState OBJECT-TYPE
            SYNTAX INTEGER
                {
                inService(1),
                outOfService(2)
                }
            MAX-ACCESS read-create
            STATUS current
            DESCRIPTION
                "The admin state on the local (RDT) side. Valid values
                are inService and OutOfService.

                This field is mandatory for IG CRV row creation."
            ::= { igCrvEntry 2 }


-- Even though this field is read only from an SNMP perspective it
-- is still read-write in the protection layer as the switch may
-- update this status. Thus this field is put in the PERSISTANT profile.
--
--
        -- 1.3.6.1.4.1.5504.4.3.1.7.1.3
        igCrvRemoteAdminState OBJECT-TYPE
            SYNTAX INTEGER
                {
                inService(1),
                outOfService(2)
                }
            MAX-ACCESS read-only
            STATUS current
            DESCRIPTION
                "The admin state on the remote (IDT) side. Valid
                values are inService and OutOfService.

                For CRVs assocated with an IG with igWorkingMode set
                to passive, the remote-admin-state of a crv is set to
                inservice.

                For igWorkingMode of active, the default value for
                remote-admin-state of a crv is set to outofservice.
                It will then be changed to inservice when the switch
                provisions this crv.

                "
            ::= { igCrvEntry 3 }


--
        -- 1.3.6.1.4.1.5504.4.3.1.7.1.4
        igCrvOperStatus OBJECT-TYPE
            SYNTAX BITS
                {
                up(0),
                fault(1),
                manualOos(2),
                removedFromServiceBySwitch(3),
                unEquipped(4),
                notConnected(5)
                }
            MAX-ACCESS read-only
            STATUS current
            DESCRIPTION
                "The line operational status is the composition (ie,
                logical OR'ing) of definitions from GR-303-CORE.
                Some of them are service affecting, some of them
                don't affect the ability of service.  Valid
                states are:
                * up, line is operational
                * fault (FLT), a fault condition
                * manualOos (MTCE), object is manually taken OOS for
                  maintenance purpose
                * removedFromServiceBySwitch (SWTCH), entity
                  removed from service by switch
                * UnEquipped - default state when new CRV
                  entry is added
                * notConnected, line is not connected"
            ::= { igCrvEntry 4 }


--
        -- 1.3.6.1.4.1.5504.4.3.1.7.1.5
        igCrvTmcState OBJECT-TYPE
            SYNTAX INTEGER
                {
                inService(1),
                permanentSignal(2)
                }
            MAX-ACCESS read-only
            STATUS current
            DESCRIPTION
                "Time-slot Management Channel (TMC) state
                indicates when the line is off-hook.

                Valid states are inService and permanentSignal.
                The default value is inService.

                A line in a permanent signal condition initiates
                call clearing, during which time the RDT
                disconnects the RDT line unit from the DS0
                (time-slot) assigned to the call, and continues
                to monitor the line.  The RDT will report
                the return to on-hook status."
            ::= { igCrvEntry 5 }


--
        -- 1.3.6.1.4.1.5504.4.3.1.7.1.6
        igCrvSignalType OBJECT-TYPE
            SYNTAX INTEGER
                {
                loopstart(2),
                groundstart(3),
                loopreversebattery(4),
                electronicbusinessset(5)
                }
            MAX-ACCESS read-create
            STATUS current
            DESCRIPTION
                "Signaling type specifies the signaling method
                currently used by this crv. Valid types are
                loop start,ground start or loop reverse battery
                for analog line and electronic business set.
                This value is set by the voice switch via the EOC
                or in the subscriber record.

                Note that 'unknown(1)' is no longer a supported
                option.

                This field is mandatory for IG CRV row creation."
            ::= { igCrvEntry 6 }


        -- 1.3.6.1.4.1.5504.4.3.1.7.1.7
        igCrvRowStatus OBJECT-TYPE
            SYNTAX ZhoneRowStatus
            MAX-ACCESS read-create
            STATUS current
            DESCRIPTION
                "Used to control row creation and deletion.

                A row in this table is created using a single
                SNMP SET request with varbinds for:
                a) igCrvRowStatus set to'CreateAndGo',
                b) the following READ-CREATE object(s) without a
                   default value (DEFVAL): igCrvLineState
                c) READ-CREATE objects with a DEFVAL but whose
                   defined default value is inappropriate:
                   * igCrvSignalType

                See igRowStatus description for RowStatus semantics."
            ::= { igCrvEntry 7 }


        -- 1.3.6.1.4.1.5504.4.3.1.8
        gr303Traps OBJECT-IDENTITY
            STATUS current
            DESCRIPTION
                "All the Zhone trap notifications for GR303 managed objectes
                 will be defined under gr303Traps."
            ::= { zhoneGR303 8 }


        -- 1.3.6.1.4.1.5504.4.3.1.8.0
        gr303TrapsPrefix OBJECT-IDENTITY
            STATUS current
            DESCRIPTION
                "This is the 0 prefix which is required for all GR303 traps
                 defined in SNMPv2."
            ::= { gr303Traps 0 }


        -- 1.3.6.1.4.1.5504.4.3.1.8.0.1
        igOperStatusChange NOTIFICATION-TYPE
            OBJECTS { igAdminStatus, igOperationalStatus }
            STATUS current
            DESCRIPTION
                "A notification is sent when the operating status of the IG
                changes."
            ::= { gr303TrapsPrefix 1 }


        -- 1.3.6.1.4.1.5504.4.3.1.8.0.2
        igTmcPrimaryStateChange NOTIFICATION-TYPE
            OBJECTS { igControlChannelTmcPrimarySvcState }
            STATUS current
            DESCRIPTION
                "A notification is sent when the status of the TMC channel on
                the primary DS1 changes. "
            ::= { gr303TrapsPrefix 2 }


        -- 1.3.6.1.4.1.5504.4.3.1.8.0.3
        igTmcSecondaryStateChange NOTIFICATION-TYPE
            OBJECTS { igControlChannelTmcSecondarySvcState }
            STATUS current
            DESCRIPTION
                "A notification is sent when the status of the TMC channel on
                the sedondary DS1 changes. "
            ::= { gr303TrapsPrefix 3 }


        -- 1.3.6.1.4.1.5504.4.3.1.8.0.4
        igEocPrimaryStateChange NOTIFICATION-TYPE
            OBJECTS { igControlChannelEocPrimarySvcState }
            STATUS current
            DESCRIPTION
                "A notification is sent when the status of the EOC channel on
                the primary DS1 changes. "
            ::= { gr303TrapsPrefix 4 }


        -- 1.3.6.1.4.1.5504.4.3.1.8.0.5
        igEocSecondaryStateChange NOTIFICATION-TYPE
            OBJECTS { igControlChannelEocSecondarySvcState }
            STATUS current
            DESCRIPTION
                "A notification is sent when the status of the EOC channel on
                the secondary DS1 changes."
            ::= { gr303TrapsPrefix 5 }


        -- 1.3.6.1.4.1.5504.4.3.1.8.0.6
        igCrvRemoteStateChange NOTIFICATION-TYPE
            OBJECTS { igCrvLocalAdminState, igCrvRemoteAdminState, igCrvOperStatus }
            STATUS current
            DESCRIPTION
                "A notification is sent when  switch removes a CRV from
                operation or restores the CRV to opearation."
            ::= { gr303TrapsPrefix 6 }


        -- 1.3.6.1.4.1.5504.4.3.1.8.0.7
        igCrvTmcStateChange NOTIFICATION-TYPE
            OBJECTS { igCrvTmcState }
            STATUS current
            DESCRIPTION
                "A notification is sent when igCrvTmcState changes."
            ::= { gr303TrapsPrefix 7 }


        -- 1.3.6.1.4.1.5504.4.3.1.8.0.8
        igSystemTimeChange NOTIFICATION-TYPE
            OBJECTS { zhoneSystemConfigurationDateAndTime, igRowStatus }
            STATUS current
            DESCRIPTION
                "When an IG is connected to a 5ESS switch, the switch will
                synchronize system time with the RDT."
            ::= { gr303TrapsPrefix 8 }



    END

--
-- comVoiceGR303.mib
--
