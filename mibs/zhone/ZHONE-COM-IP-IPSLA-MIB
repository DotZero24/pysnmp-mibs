--
-- comIpIpslm.mib
-- MIB generated by MG-SOFT Visual MIB Builder Version 3.0 Build 285
-- Wednesday, January 30, 2008 at 09:27:15
--

    ZHONE-COM-IP-IPSLA-MIB DEFINITIONS ::= BEGIN

        IMPORTS
            ifName
                FROM IF-MIB
            OBJECT-GROUP, MODULE-COMPLIANCE, NOTIFICATION-GROUP
                FROM SNMPv2-CONF
            IpAddress, Counter32, OBJECT-TYPE, MODULE-IDENTITY, OBJECT-IDENTITY,
            NOTIFICATION-TYPE
                FROM SNMPv2-SMI
            RowStatus, DateAndTime
                FROM SNMPv2-TC
            rdIndex, ZhoneRDIndex
                FROM ZHONE-COM-IP-RD-MIB
            zhoneIp
                FROM Zhone;


-- Protection Layer Generation:
-- /vob/zhonetools/bin/pahrser.pl rfc1213.mib rfc1907.mib
--   iftype.mib rfc2233.mib Zhone.mib comIpIpslm.mib
--
-- Mib handler generation:
-- /vob/EPILOGUE/binaries/emissary/solaris/mibcomp rfc1213.mib rfc1907.mib
--   iftype.mib rfc2233.mib Zhone.mib -start zhoneIpSLA -stub -o
--   zhoneIpSlmHdlr.c comIpIpslm.mib
--
-- CFG -----------------------------------------------------------------
--
--
--
--
--
-- STATISTICS ----------------------------------------------------------
--
--
--
--
--
-- *********************************************************************
-- ****************** zhoneIpSLA Module Identity ***********************
-- *********************************************************************
--
        -- 1.3.6.1.4.1.5504.4.1.21
        zhoneIpSLA MODULE-IDENTITY
            LAST-UPDATED "200611031117Z"		-- November 03, 2006 at 11:17 GMT
            ORGANIZATION
                "Zhone Technologies"
            CONTACT-INFO
                "  Postal:
                           Zhone Technologies, Inc.
                           @ Zhone Way
                           7001 Oakport Street
                           Oakland, CA  94621
                           USA
                Toll-Free: +1 877-ZHONE20 (+1 877-946-6320)
                      Tel: +1-510-777-7000
                      Fax: +1-510-777-7001
                   E-mail: support@zhone.com
                     "
            DESCRIPTION
                "This is the MIB Module for IPSLA Feature Configuration
                and reporting.

                "
            REVISION "200706050716Z"		-- June 05, 2007 at 07:16 GMT
            DESCRIPTION
                "Added PathStatByInterval Table."
            REVISION "200611161048Z"		-- November 16, 2006 at 10:48 GMT
            DESCRIPTION
                "Removed name simplification."
            REVISION "200611030757Z"		-- November 03, 2006 at 07:57 GMT
            DESCRIPTION
                "Simplified most leaf names, removing the zhoneIpSLM prefix.
                Changed some leaf names to clarify their purpose.
                Modified the markup, correcting the Zhone provisioning
                model for this feature.
                Referencing ifIndex made little sense within this feature
                as IP is tied more to the management database and
                route domain. Traps have been modified to reference
                the source IP address for the connection, allowing
                administrators to track the location of the device
                originating the static path configuration."
            ::= { zhoneIp 21 }




--
-- Node definitions
--

        -- 1.3.6.1.4.1.5504.4.1.21.1
        zhoneIpSLAMibObjects OBJECT IDENTIFIER ::= { zhoneIpSLA 1 }


-- *********************************************************************
-- ************************ Global Settings ****************************
-- *********************************************************************
--
--
        -- 1.3.6.1.4.1.5504.4.1.21.1.1
        zhoneIpSLAGlobalEnable OBJECT-TYPE
            SYNTAX INTEGER
                {
                enabled(1),
                disabled(2)
                }
            MAX-ACCESS read-write
            STATUS current
            DESCRIPTION
                "This object specifies whether to enable feature actions."
            DEFVAL { disabled }
            ::= { zhoneIpSLAMibObjects 1 }


--
        -- 1.3.6.1.4.1.5504.4.1.21.1.2
        zhoneIpSLAGlobalPollInterval OBJECT-TYPE
            SYNTAX INTEGER (60..3600)
            UNITS "seconds"
            MAX-ACCESS read-write
            STATUS current
            DESCRIPTION
                "This object specifies the time interval in seconds between the
                inband IPSLA communications among IPSLA devices."
            DEFVAL { 60 }
            ::= { zhoneIpSLAMibObjects 2 }


-- *********************************************************************
-- ******************* zhoneIpSLACosActionTable ************************
-- *********************************************************************
--
--
        -- 1.3.6.1.4.1.5504.4.1.21.1.3
        zhoneIpSLACosActionTable OBJECT-TYPE
            SYNTAX SEQUENCE OF ZhoneIpSLACosActionEntry
            MAX-ACCESS not-accessible
            STATUS current
            DESCRIPTION
                "This table has the Service Level Agreement (SLA)
                CoS action configuration options."
            ::= { zhoneIpSLAMibObjects 3 }


        -- 1.3.6.1.4.1.5504.4.1.21.1.3.1
        zhoneIpSLACosActionEntry OBJECT-TYPE
            SYNTAX ZhoneIpSLACosActionEntry
            MAX-ACCESS not-accessible
            STATUS current
            DESCRIPTION
                "An entry in the IPSLA Action By CoS Configuration Table."
            INDEX { zhoneIpSLACosActionIndex }
            ::= { zhoneIpSLACosActionTable 1 }


        ZhoneIpSLACosActionEntry ::=
            SEQUENCE {
                zhoneIpSLACosActionIndex
                    INTEGER,
                zhoneIpSLACosActionName
                    OCTET STRING,
                zhoneIpSLACosActionTrapOnError
                    INTEGER,
                zhoneIpSLACosActionTimeoutErrThresh
                    INTEGER,
                zhoneIpSLACosActionTimeoutClrThresh
                    INTEGER,
                zhoneIpSLACosActionLatencyErrThresh
                    INTEGER,
                zhoneIpSLACosActionLatencyClrThresh
                    INTEGER,
                zhoneIpSLACosActionJitterErrThresh
                    INTEGER,
                zhoneIpSLACosActionJitterClrThresh
                    INTEGER,
                zhoneIpSLACosActionMetrics
                    INTEGER,
                zhoneIpSLACosActionPacketSize
                    INTEGER
             }

        -- 1.3.6.1.4.1.5504.4.1.21.1.3.1.1
        zhoneIpSLACosActionIndex OBJECT-TYPE
            SYNTAX INTEGER (1..8)
            MAX-ACCESS not-accessible
            STATUS current
            DESCRIPTION
                "There are 8 entries present for each device. actionIndex
                values 1 to 8 correspond exactly to Class Of Service (CoS)
                indices 0 to 7."
            ::= { zhoneIpSLACosActionEntry 1 }


--
        -- 1.3.6.1.4.1.5504.4.1.21.1.3.1.2
        zhoneIpSLACosActionName OBJECT-TYPE
            SYNTAX OCTET STRING (SIZE (1..9))
            MAX-ACCESS read-write
            STATUS current
            DESCRIPTION
                "The ascii name of the SLA CoS action entry, up to 9 characters
                in length.

                Blank names are not allowed."
            ::= { zhoneIpSLACosActionEntry 2 }


--
        -- 1.3.6.1.4.1.5504.4.1.21.1.3.1.3
        zhoneIpSLACosActionTrapOnError OBJECT-TYPE
            SYNTAX INTEGER
                {
                enabled(1),
                disabled(2)
                }
            MAX-ACCESS read-write
            STATUS current
            DESCRIPTION
                "Specifies whether a trap is issued when any SLA performance error
                threshold within this CoS is crossed."
            DEFVAL { disabled }
            ::= { zhoneIpSLACosActionEntry 3 }


--
        -- 1.3.6.1.4.1.5504.4.1.21.1.3.1.4
        zhoneIpSLACosActionTimeoutErrThresh OBJECT-TYPE
            SYNTAX INTEGER (1..20)
            MAX-ACCESS read-write
            STATUS current
            DESCRIPTION
                "Specifies the number of consecutive missed IP SLA responses
                within this CoS before a zhoneIpSLATimeoutTrap is issued."
            DEFVAL { 3 }
            ::= { zhoneIpSLACosActionEntry 4 }


--
        -- 1.3.6.1.4.1.5504.4.1.21.1.3.1.5
        zhoneIpSLACosActionTimeoutClrThresh OBJECT-TYPE
            SYNTAX INTEGER (1..20)
            MAX-ACCESS read-write
            STATUS current
            DESCRIPTION
                "Specifies the number of consecutive IPSLA responses within this
                CoS which must be received before the timeout error condition
                is cleared."
            DEFVAL { 1 }
            ::= { zhoneIpSLACosActionEntry 5 }


--
        -- 1.3.6.1.4.1.5504.4.1.21.1.3.1.6
        zhoneIpSLACosActionLatencyErrThresh OBJECT-TYPE
            SYNTAX INTEGER (50..10000)
            UNITS "milliseconds"
            MAX-ACCESS read-write
            STATUS current
            DESCRIPTION
                "Specifies the 15 sample average roundtrip latency value
                which must be exceeded within this CoS before a
                zhoneIpSLALatencyTrap is issued.

                The value is specified in milliseconds."
            DEFVAL { 10000 }
            ::= { zhoneIpSLACosActionEntry 6 }


--
        -- 1.3.6.1.4.1.5504.4.1.21.1.3.1.7
        zhoneIpSLACosActionLatencyClrThresh OBJECT-TYPE
            SYNTAX INTEGER (1..20)
            MAX-ACCESS read-write
            STATUS current
            DESCRIPTION
                "Specifies the number of consecutive IPSLA latency samples for
                which the 15 sample average roundtrip latency must be below
                the configured SLA latency error threshold within this CoS
                before the latency error condition is cleared."
            DEFVAL { 1 }
            ::= { zhoneIpSLACosActionEntry 7 }


--
        -- 1.3.6.1.4.1.5504.4.1.21.1.3.1.8
        zhoneIpSLACosActionJitterErrThresh OBJECT-TYPE
            SYNTAX INTEGER (50..10000)
            UNITS "milliseconds"
            MAX-ACCESS read-write
            STATUS current
            DESCRIPTION
                "Specifies the 15 sample roundtrip jitter value
                which must be exceeded within this CoS before a
                zhoneIpSLAJitterTrap is issued.

                The value is specified in milliseconds."
            DEFVAL { 10000 }
            ::= { zhoneIpSLACosActionEntry 8 }


--
        -- 1.3.6.1.4.1.5504.4.1.21.1.3.1.9
        zhoneIpSLACosActionJitterClrThresh OBJECT-TYPE
            SYNTAX INTEGER (1..20)
            MAX-ACCESS read-write
            STATUS current
            DESCRIPTION
                "Specifies the number of consecutive IPSLA RTT samples for
                which the 15 sample roundtrip jitter must be below the
                configured SLA jitter error threshold within this CoS
                before the jitter error condition is cleared."
            DEFVAL { 1 }
            ::= { zhoneIpSLACosActionEntry 9 }


--
        -- 1.3.6.1.4.1.5504.4.1.21.1.3.1.10
        zhoneIpSLACosActionMetrics OBJECT-TYPE
            SYNTAX INTEGER
                {
                enabled(1),
                disabled(2)
                }
            MAX-ACCESS read-write
            STATUS current
            DESCRIPTION
                "Specifies if Latency and Availability meaurements should be
                carried out for this CoS.

                The default is enabled(1)."
            DEFVAL { enabled }
            ::= { zhoneIpSLACosActionEntry 10 }


--
        -- 1.3.6.1.4.1.5504.4.1.21.1.3.1.11
        zhoneIpSLACosActionPacketSize OBJECT-TYPE
            SYNTAX INTEGER (64..2048)
            UNITS "octets"
            MAX-ACCESS read-write
            STATUS current
            DESCRIPTION
                "Specifies the minimum IPSLA Ping packet size in bytes.

                The range is 64 thru 2048 if the target IP device is running IPSLA,
                64 thru 512 otherwise."
            DEFVAL { 64 }
            ::= { zhoneIpSLACosActionEntry 11 }


-- *********************************************************************
-- ******************** zhoneIpSLACosMapTable  *************************
-- *********************************************************************
--
-- One or more code points may be assigned to the Class Of Service type
-- identified by the COS ID. With one or more Code Points assigned, the
-- COS type will be used with Latency and Availability measurements
-- when the metrics object is set to "enabled".
-- There are 64 code points (0 thru 63) each of which may be assigned to
-- one of the 8 COS IDs. Each COS ID may be assigned to one or more
-- Code points. Defaults are assigned with the guidance of RFC 2597.
--
--
        -- 1.3.6.1.4.1.5504.4.1.21.1.4
        zhoneIpSLACosMapTable OBJECT-TYPE
            SYNTAX SEQUENCE OF ZhoneIpSLACosMapEntry
            MAX-ACCESS not-accessible
            STATUS current
            DESCRIPTION
                "This table contains the Service Level Management DSCP-to-CoS
                mapping."
            ::= { zhoneIpSLAMibObjects 4 }


        -- 1.3.6.1.4.1.5504.4.1.21.1.4.1
        zhoneIpSLACosMapEntry OBJECT-TYPE
            SYNTAX ZhoneIpSLACosMapEntry
            MAX-ACCESS not-accessible
            STATUS current
            DESCRIPTION
                "An entry in the IPSLA COS Map Table."
            INDEX { zhoneIpSLACosMapDscpIndex }
            ::= { zhoneIpSLACosMapTable 1 }


        ZhoneIpSLACosMapEntry ::=
            SEQUENCE {
                zhoneIpSLACosMapDscpIndex
                    INTEGER,
                zhoneIpSLACosMapCosActionIndex
                    INTEGER
             }

        -- 1.3.6.1.4.1.5504.4.1.21.1.4.1.1
        zhoneIpSLACosMapDscpIndex OBJECT-TYPE
            SYNTAX INTEGER (1..64)
            MAX-ACCESS not-accessible
            STATUS current
            DESCRIPTION
                "There are 64 entries present each representing a DIFFSRV code
                point (0 thru 63, bits 000000 thru 111111), for each device.
                dscpIndex values 1 to 64 correspond exactly to DIFFSRV
                codepoint values 0 to 63."
            ::= { zhoneIpSLACosMapEntry 1 }


--
        -- 1.3.6.1.4.1.5504.4.1.21.1.4.1.2
        zhoneIpSLACosMapCosActionIndex OBJECT-TYPE
            SYNTAX INTEGER (0..8)
            MAX-ACCESS read-write
            STATUS current
            DESCRIPTION
                "This object is a pointer to the entry in zhoneIpSLACosActionTable.
                Value 0 indicates that no CoS action is assigned. The map
                entries recommended in rfc 2597 are present by default."
            ::= { zhoneIpSLACosMapEntry 2 }


-- *********************************************************************
-- ******************* zhoneIpSLAStaticPathTable  **********************
-- *********************************************************************
--
-- This table is used to configure a list of static Path IP Addresses
-- which make up a list of Paths explicitly known by the managed unit.
--
--
        -- 1.3.6.1.4.1.5504.4.1.21.1.5
        zhoneIpSLAStaticPathTable OBJECT-TYPE
            SYNTAX SEQUENCE OF ZhoneIpSLAStaticPathEntry
            MAX-ACCESS not-accessible
            STATUS current
            DESCRIPTION
                "This table has the list of static Path IP Addresses"
            ::= { zhoneIpSLAMibObjects 5 }


        -- 1.3.6.1.4.1.5504.4.1.21.1.5.1
        zhoneIpSLAStaticPathEntry OBJECT-TYPE
            SYNTAX ZhoneIpSLAStaticPathEntry
            MAX-ACCESS not-accessible
            STATUS current
            DESCRIPTION
                "An entry in the IPSLA Configuration Table."
            INDEX { zhoneIpSLAStaticPathRdIndex, zhoneIpSLAStaticPathTargetIP }
            ::= { zhoneIpSLAStaticPathTable 1 }


        ZhoneIpSLAStaticPathEntry ::=
            SEQUENCE {
                zhoneIpSLAStaticPathRdIndex
                    ZhoneRDIndex,
                zhoneIpSLAStaticPathTargetIP
                    IpAddress,
                zhoneIpSLAStaticPathForwarding
                    INTEGER,
                zhoneIpSLAStaticPathState
                    INTEGER,
                zhoneIpSLAStaticPathRowstatus
                    RowStatus
             }

        -- 1.3.6.1.4.1.5504.4.1.21.1.5.1.1
        zhoneIpSLAStaticPathRdIndex OBJECT-TYPE
            SYNTAX ZhoneRDIndex (1..127)
            MAX-ACCESS not-accessible
            STATUS current
            DESCRIPTION
                "Route Domain Index of the target IP address."
            ::= { zhoneIpSLAStaticPathEntry 1 }


        -- 1.3.6.1.4.1.5504.4.1.21.1.5.1.2
        zhoneIpSLAStaticPathTargetIP OBJECT-TYPE
            SYNTAX IpAddress
            MAX-ACCESS not-accessible
            STATUS current
            DESCRIPTION
                "Specifies the IP Address of the device which is at
                the other end of the path."
            ::= { zhoneIpSLAStaticPathEntry 2 }


--
        -- 1.3.6.1.4.1.5504.4.1.21.1.5.1.3
        zhoneIpSLAStaticPathForwarding OBJECT-TYPE
            SYNTAX INTEGER
                {
                enabled(1),
                disabled(2)
                }
            MAX-ACCESS read-create
            STATUS current
            DESCRIPTION
                "If enabled, all native static IP path entities will include this
                IP in IPSLA ping messages as a forwarded IP, resulting in remote
                IPSLA devices' inclusion of this IP as a dynamic IPSLA initiator.
                Remote IPSLA devices will then act as a proxy for the local IPSLA
                device in sending out IPSLA pings. Forwarded IPs are NOT propagated
                past the first remote IPSLA device.

                Received forwarded IPs are dynamic entries which get aged out unless
                IPSLA protocol messages are received which contain their IP as a
                forwarded IP. The agetime is a multiple of the proxying device's
                global poll-secs (object zhoneIpSLAGlobalPollInterval), based upon a
                certain maximum of forwarded paths per device and the number of
                path forwarding messages allowed within the minimum 64-byte IPSLA
                Ping packet.

                Valid values are enabled(1), disabled(2)."
            DEFVAL { disabled }
            ::= { zhoneIpSLAStaticPathEntry 3 }


--
        -- 1.3.6.1.4.1.5504.4.1.21.1.5.1.4
        zhoneIpSLAStaticPathState OBJECT-TYPE
            SYNTAX INTEGER
                {
                enabled(1),
                disabled(2)
                }
            MAX-ACCESS read-create
            STATUS current
            DESCRIPTION
                "Specifies if the IPSLA feature actions will be exerted on the
                current member of the static entry list. This leaf allows the
                user to toggle the feature per static path without deleting
                the current static path configuration.

                Valid values are enabled(1), disabled(2)."
            DEFVAL { enabled }
            ::= { zhoneIpSLAStaticPathEntry 4 }


        -- 1.3.6.1.4.1.5504.4.1.21.1.5.1.5
        zhoneIpSLAStaticPathRowstatus OBJECT-TYPE
            SYNTAX RowStatus
            MAX-ACCESS read-create
            STATUS current
            DESCRIPTION
                "This object is used to create new rows in this table, modify
                existing rows, and to delete existing rows."
            ::= { zhoneIpSLAStaticPathEntry 5 }


-- *********************************************************************
-- ****************** zhoneIpSLAPathConnectTable  **********************
-- *********************************************************************
--
-- This table has the list of Paths (i.e IP Addresses of other devices,
-- reachable via IP Address for SLA purposes) for a selected ip address
--
--
        -- 1.3.6.1.4.1.5504.4.1.21.1.6
        zhoneIpSLAPathConnectTable OBJECT-TYPE
            SYNTAX SEQUENCE OF ZhoneIpSLAPathConnectEntry
            MAX-ACCESS not-accessible
            STATUS current
            DESCRIPTION
                "IP Path table for reporting connection statistics."
            ::= { zhoneIpSLAMibObjects 6 }


        -- 1.3.6.1.4.1.5504.4.1.21.1.6.1
        zhoneIpSLAPathConnectEntry OBJECT-TYPE
            SYNTAX ZhoneIpSLAPathConnectEntry
            MAX-ACCESS not-accessible
            STATUS current
            DESCRIPTION
                "IP Path Connection Status Table."
            INDEX { rdIndex, zhoneIpSLAPathConnectEndpointIP }
            ::= { zhoneIpSLAPathConnectTable 1 }


        ZhoneIpSLAPathConnectEntry ::=
            SEQUENCE {
                zhoneIpSLAPathConnectEndpointIP
                    IpAddress,
                zhoneIpSLAPathConnectDevName
                    OCTET STRING,
                zhoneIpSLAPathConnectDevType
                    OCTET STRING,
                zhoneIpSLAPathConnectStatus
                    INTEGER,
                zhoneIpSLAPathConnectSrcIP
                    IpAddress,
                zhoneIpSLAPathConnectDiscoveryType
                    INTEGER,
                zhoneIpSLAPathConnectUpTime
                    Counter32,
                zhoneIpSLAPathConnectPollType
                    INTEGER,
                zhoneIpSLAPathConnectCosMismatch
                    Counter32,
                zhoneIpSLAPathConnectLastCosActionIndex
                    INTEGER
             }

        -- 1.3.6.1.4.1.5504.4.1.21.1.6.1.1
        zhoneIpSLAPathConnectEndpointIP OBJECT-TYPE
            SYNTAX IpAddress
            MAX-ACCESS not-accessible
            STATUS current
            DESCRIPTION
                "Specifies the IP Address of the target device which
                is at the other end of the path."
            ::= { zhoneIpSLAPathConnectEntry 1 }


--
        -- 1.3.6.1.4.1.5504.4.1.21.1.6.1.2
        zhoneIpSLAPathConnectDevName OBJECT-TYPE
            SYNTAX OCTET STRING (SIZE (0..20))
            MAX-ACCESS read-only
            STATUS current
            DESCRIPTION
                "Specifies the name of the remote device."
            ::= { zhoneIpSLAPathConnectEntry 2 }


--
        -- 1.3.6.1.4.1.5504.4.1.21.1.6.1.3
        zhoneIpSLAPathConnectDevType OBJECT-TYPE
            SYNTAX OCTET STRING (SIZE (0..10))
            MAX-ACCESS read-only
            STATUS current
            DESCRIPTION
                "Specifies the type of the remote device."
            ::= { zhoneIpSLAPathConnectEntry 3 }


--
        -- 1.3.6.1.4.1.5504.4.1.21.1.6.1.4
        zhoneIpSLAPathConnectStatus OBJECT-TYPE
            SYNTAX INTEGER
                {
                enabled(1),
                disabled(2)
                }
            MAX-ACCESS read-only
            STATUS current
            DESCRIPTION
                "Specifies the availability status of the remote."
            ::= { zhoneIpSLAPathConnectEntry 4 }


--
        -- 1.3.6.1.4.1.5504.4.1.21.1.6.1.5
        zhoneIpSLAPathConnectSrcIP OBJECT-TYPE
            SYNTAX IpAddress
            MAX-ACCESS read-only
            STATUS current
            DESCRIPTION
                "The object specifies the source discovery Ip Address."
            ::= { zhoneIpSLAPathConnectEntry 5 }


--
        -- 1.3.6.1.4.1.5504.4.1.21.1.6.1.6
        zhoneIpSLAPathConnectDiscoveryType OBJECT-TYPE
            SYNTAX INTEGER
                {
                static(1),
                dynamic(2)
                }
            MAX-ACCESS read-only
            STATUS current
            DESCRIPTION
                "The object specifies the source discovery type."
            ::= { zhoneIpSLAPathConnectEntry 6 }


--
        -- 1.3.6.1.4.1.5504.4.1.21.1.6.1.7
        zhoneIpSLAPathConnectUpTime OBJECT-TYPE
            SYNTAX Counter32
            UNITS "seconds"
            MAX-ACCESS read-only
            STATUS current
            DESCRIPTION
                "The object specifies the amount of time in seconds that elapsed
                since the last transition from Inactive to Active."
            ::= { zhoneIpSLAPathConnectEntry 7 }


--
        -- 1.3.6.1.4.1.5504.4.1.21.1.6.1.8
        zhoneIpSLAPathConnectPollType OBJECT-TYPE
            SYNTAX INTEGER
                {
                initiator(1),
                responder(2)
                }
            MAX-ACCESS read-only
            STATUS current
            DESCRIPTION
                "The object specifies the role played by the local device in
                collection of latency and availability statistics.

                Initiator(1) - this is the unit that initiates the IPSLA
                ping packet used for statistics collection;

                Responder(2) - this is the unit that returns the IPSLA ping
                packet sent by the Initiator."
            ::= { zhoneIpSLAPathConnectEntry 8 }


--
        -- 1.3.6.1.4.1.5504.4.1.21.1.6.1.9
        zhoneIpSLAPathConnectCosMismatch OBJECT-TYPE
            SYNTAX Counter32
            MAX-ACCESS read-only
            STATUS current
            DESCRIPTION
                "The object specifies the number of IPSLA ping packets received
                which indicate a mismatch between the Class Of Service
                definitions at the remote unit with those of the local unit."
            ::= { zhoneIpSLAPathConnectEntry 9 }


--
        -- 1.3.6.1.4.1.5504.4.1.21.1.6.1.10
        zhoneIpSLAPathConnectLastCosActionIndex OBJECT-TYPE
            SYNTAX INTEGER (1..8)
            MAX-ACCESS read-only
            STATUS current
            DESCRIPTION
                "The object specifies the COS action Id used within the
                most recently transmitted IPSLA ping on this connection."
            ::= { zhoneIpSLAPathConnectEntry 10 }


-- *********************************************************************
-- ***************** zhoneIpSLAPathStatByCOSTable  *********************
-- *********************************************************************
--
-- This table has the statistics for Round Trip Time (RTT) latency
-- for an IP Path by COS action index.
--
--
        -- 1.3.6.1.4.1.5504.4.1.21.1.7
        zhoneIpSLAPathStatByCOSTable OBJECT-TYPE
            SYNTAX SEQUENCE OF ZhoneIpSLAPathStatByCOSEntry
            MAX-ACCESS not-accessible
            STATUS current
            DESCRIPTION
                "IP Path Table for reporting round-trip-time stats and dropped responses."
            ::= { zhoneIpSLAMibObjects 7 }


        -- 1.3.6.1.4.1.5504.4.1.21.1.7.1
        zhoneIpSLAPathStatByCOSEntry OBJECT-TYPE
            SYNTAX ZhoneIpSLAPathStatByCOSEntry
            MAX-ACCESS not-accessible
            STATUS current
            DESCRIPTION
                "An entry in the IP Path Statistics By COS Table."
            INDEX { zhoneIpSLAPathStatByCOSCosActIndex, rdIndex, zhoneIpSLAPathStatByCOSTargetIP }
            ::= { zhoneIpSLAPathStatByCOSTable 1 }


        ZhoneIpSLAPathStatByCOSEntry ::=
            SEQUENCE {
                zhoneIpSLAPathStatByCOSCosActIndex
                    INTEGER,
                zhoneIpSLAPathStatByCOSTargetIP
                    IpAddress,
                zhoneIpSLAPathStatByCOSStatus
                    INTEGER,
                zhoneIpSLAPathStatByCOSLastRTT
                    Counter32,
                zhoneIpSLAPathStatByCOSMinRTT
                    Counter32,
                zhoneIpSLAPathStatByCOSAvgRTT
                    Counter32,
                zhoneIpSLAPathStatByCOSMaxRTT
                    Counter32,
                zhoneIpSLAPathStatByCOSDroppedResp
                    Counter32
             }

        -- 1.3.6.1.4.1.5504.4.1.21.1.7.1.1
        zhoneIpSLAPathStatByCOSCosActIndex OBJECT-TYPE
            SYNTAX INTEGER (1..8)
            MAX-ACCESS not-accessible
            STATUS current
            DESCRIPTION
                "Specifies the COS Action Index."
            ::= { zhoneIpSLAPathStatByCOSEntry 1 }


        -- 1.3.6.1.4.1.5504.4.1.21.1.7.1.2
        zhoneIpSLAPathStatByCOSTargetIP OBJECT-TYPE
            SYNTAX IpAddress
            MAX-ACCESS accessible-for-notify
            STATUS current
            DESCRIPTION
                "Specifies the IP Address of the device which is at
                the other end of the path."
            ::= { zhoneIpSLAPathStatByCOSEntry 2 }


--
        -- 1.3.6.1.4.1.5504.4.1.21.1.7.1.3
        zhoneIpSLAPathStatByCOSStatus OBJECT-TYPE
            SYNTAX INTEGER
                {
                active(1),
                inactive(2)
                }
            MAX-ACCESS read-write
            STATUS current
            DESCRIPTION
                "Specifies the status of the Cos.

                Writing to this leaf will cause objects
                zhoneIpSLAPathStatByCOSLastRTT, zhoneIpSLAPathStatByCOSMinRTT,
                zhoneIpSLAPathStatByCOSAvgRTT, zhoneIpSLAPathStatByCOSMaxRTT,
                and zhoneIpSLAPathStatByCOSDropResp to be cleared.
                "
            ::= { zhoneIpSLAPathStatByCOSEntry 3 }


--
        -- 1.3.6.1.4.1.5504.4.1.21.1.7.1.4
        zhoneIpSLAPathStatByCOSLastRTT OBJECT-TYPE
            SYNTAX Counter32
            UNITS "milliseconds"
            MAX-ACCESS read-only
            STATUS current
            DESCRIPTION
                "The object specifies the latest round trip latency in
                milliseconds between this unit and the unit at the far
                end of the IP Enabled circuit."
            ::= { zhoneIpSLAPathStatByCOSEntry 4 }


--
        -- 1.3.6.1.4.1.5504.4.1.21.1.7.1.5
        zhoneIpSLAPathStatByCOSMinRTT OBJECT-TYPE
            SYNTAX Counter32
            UNITS "milliseconds"
            MAX-ACCESS read-only
            STATUS current
            DESCRIPTION
                "The object specifies the minimum round trip latency in
                milliseconds between this unit and the unit at the far
                end of the IP Enabled circuit. This is the least value
                of the last 15 ping trials."
            ::= { zhoneIpSLAPathStatByCOSEntry 5 }


--
        -- 1.3.6.1.4.1.5504.4.1.21.1.7.1.6
        zhoneIpSLAPathStatByCOSAvgRTT OBJECT-TYPE
            SYNTAX Counter32
            UNITS "milliseconds"
            MAX-ACCESS read-only
            STATUS current
            DESCRIPTION
                "The object specifies the average round trip latency in
                milliseconds between this unit and the unit at the far
                end of the IP Enabled circuit. This is the average value
                over the last 15 ping trials."
            ::= { zhoneIpSLAPathStatByCOSEntry 6 }


--
        -- 1.3.6.1.4.1.5504.4.1.21.1.7.1.7
        zhoneIpSLAPathStatByCOSMaxRTT OBJECT-TYPE
            SYNTAX Counter32
            UNITS "milliseconds"
            MAX-ACCESS read-only
            STATUS current
            DESCRIPTION
                "The object specifies the maximum round trip latency in
                milliseconds between this unit and the unit at the far
                end of the IP Enabled circuit. This is the greatest value
                of the last 15 ping trials."
            ::= { zhoneIpSLAPathStatByCOSEntry 7 }


        -- 1.3.6.1.4.1.5504.4.1.21.1.7.1.8
        zhoneIpSLAPathStatByCOSDroppedResp OBJECT-TYPE
            SYNTAX Counter32
            MAX-ACCESS read-only
            STATUS current
            DESCRIPTION
                "The object specifies the number of IPSLA pings for which
                a response was not received from the far end device."
            ::= { zhoneIpSLAPathStatByCOSEntry 8 }


-- *********************************************************************
-- ***************** zhoneIpSLAPathStatByIntervalTable  *********************
-- *********************************************************************
--
-- This table has the statistics for Round Trip Time (RTT) latency
-- for an IP Path by interval index.
--
--
        -- 1.3.6.1.4.1.5504.4.1.21.1.8
        zhoneIpSLAPathStatByIntervalTable OBJECT-TYPE
            SYNTAX SEQUENCE OF ZhoneIpSLAPathStatByIntervalEntry
            MAX-ACCESS not-accessible
            STATUS current
            DESCRIPTION
                "IP Path Table for reporting round-trip-time stats and dropped
                responses. This table's top index represents one of 96 slices of
                data taken at 15 minute intervals, allowing the user to track
                performance over a 24 hour period."
            ::= { zhoneIpSLAMibObjects 8 }


        -- 1.3.6.1.4.1.5504.4.1.21.1.8.1
        zhoneIpSLAPathStatByIntervalEntry OBJECT-TYPE
            SYNTAX ZhoneIpSLAPathStatByIntervalEntry
            MAX-ACCESS not-accessible
            STATUS current
            DESCRIPTION
                "An entry in the IP Path Statistics By Interval and COS Table."
            INDEX { zhoneIpSLAPathStatByIntervalIndex, zhoneIpSLAPathStatByIntervalCosActIndex, zhoneIpSLAPathStatByIntervalRdIndex, zhoneIpSLAPathStatByIntervalTargetIP }
            ::= { zhoneIpSLAPathStatByIntervalTable 1 }


        ZhoneIpSLAPathStatByIntervalEntry ::=
            SEQUENCE {
                zhoneIpSLAPathStatByIntervalIndex
                    INTEGER,
                zhoneIpSLAPathStatByIntervalCosActIndex
                    INTEGER,
                zhoneIpSLAPathStatByIntervalRdIndex
                    ZhoneRDIndex,
                zhoneIpSLAPathStatByIntervalTargetIP
                    IpAddress,
                zhoneIpSLAPathStatByIntervalDateTime
                    DateAndTime,
                zhoneIpSLAPathStatByIntervalStatus
                    INTEGER,
                zhoneIpSLAPathStatByIntervalMinRTT
                    Counter32,
                zhoneIpSLAPathStatByIntervalAvgRTT
                    Counter32,
                zhoneIpSLAPathStatByIntervalMaxRTT
                    Counter32,
                zhoneIpSLAPathStatByIntervalDroppedResp
                    Counter32
             }

        -- 1.3.6.1.4.1.5504.4.1.21.1.8.1.1
        zhoneIpSLAPathStatByIntervalIndex OBJECT-TYPE
            SYNTAX INTEGER (1..96)
            MAX-ACCESS not-accessible
            STATUS current
            DESCRIPTION
                "Specifies which of the 96 15-minute interval data slices to report."
            ::= { zhoneIpSLAPathStatByIntervalEntry 1 }


        -- 1.3.6.1.4.1.5504.4.1.21.1.8.1.2
        zhoneIpSLAPathStatByIntervalCosActIndex OBJECT-TYPE
            SYNTAX INTEGER (1..8)
            MAX-ACCESS not-accessible
            STATUS current
            DESCRIPTION
                "Specifies the COS Action Index."
            ::= { zhoneIpSLAPathStatByIntervalEntry 2 }


        -- 1.3.6.1.4.1.5504.4.1.21.1.8.1.3
        zhoneIpSLAPathStatByIntervalRdIndex OBJECT-TYPE
            SYNTAX ZhoneRDIndex (1..127)
            MAX-ACCESS not-accessible
            STATUS current
            DESCRIPTION
                "RdIndex of the entry."
            ::= { zhoneIpSLAPathStatByIntervalEntry 3 }


        -- 1.3.6.1.4.1.5504.4.1.21.1.8.1.4
        zhoneIpSLAPathStatByIntervalTargetIP OBJECT-TYPE
            SYNTAX IpAddress
            MAX-ACCESS not-accessible
            STATUS current
            DESCRIPTION
                "Specifies the IP Address of the device which is at
                the other end of the path."
            ::= { zhoneIpSLAPathStatByIntervalEntry 4 }


--
        -- 1.3.6.1.4.1.5504.4.1.21.1.8.1.5
        zhoneIpSLAPathStatByIntervalDateTime OBJECT-TYPE
            SYNTAX DateAndTime
            MAX-ACCESS read-only
            STATUS current
            DESCRIPTION
                "Describes the date and time the current interval data slice was stored."
            ::= { zhoneIpSLAPathStatByIntervalEntry 5 }


--
        -- 1.3.6.1.4.1.5504.4.1.21.1.8.1.6
        zhoneIpSLAPathStatByIntervalStatus OBJECT-TYPE
            SYNTAX INTEGER
                {
                active(1),
                inactive(2)
                }
            MAX-ACCESS read-only
            STATUS current
            DESCRIPTION
                "Specifies the status of the Cos."
            ::= { zhoneIpSLAPathStatByIntervalEntry 6 }


--
        -- 1.3.6.1.4.1.5504.4.1.21.1.8.1.7
        zhoneIpSLAPathStatByIntervalMinRTT OBJECT-TYPE
            SYNTAX Counter32
            UNITS "milliseconds"
            MAX-ACCESS read-only
            STATUS current
            DESCRIPTION
                "The object specifies the minimum round trip latency in
                milliseconds between this unit and the unit at the far
                end of the IP Enabled circuit. This is the least value
                of the last 15 ping trials."
            ::= { zhoneIpSLAPathStatByIntervalEntry 7 }


--
        -- 1.3.6.1.4.1.5504.4.1.21.1.8.1.8
        zhoneIpSLAPathStatByIntervalAvgRTT OBJECT-TYPE
            SYNTAX Counter32
            UNITS "milliseconds"
            MAX-ACCESS read-only
            STATUS current
            DESCRIPTION
                "The object specifies the average round trip latency in
                milliseconds between this unit and the unit at the far
                end of the IP Enabled circuit. This is the average value
                over the last 15 ping trials."
            ::= { zhoneIpSLAPathStatByIntervalEntry 8 }


--
        -- 1.3.6.1.4.1.5504.4.1.21.1.8.1.9
        zhoneIpSLAPathStatByIntervalMaxRTT OBJECT-TYPE
            SYNTAX Counter32
            UNITS "milliseconds"
            MAX-ACCESS read-only
            STATUS current
            DESCRIPTION
                "The object specifies the maximum round trip latency in
                milliseconds between this unit and the unit at the far
                end of the IP Enabled circuit. This is the greatest value
                of the last 15 ping trials."
            ::= { zhoneIpSLAPathStatByIntervalEntry 9 }


--
        -- 1.3.6.1.4.1.5504.4.1.21.1.8.1.10
        zhoneIpSLAPathStatByIntervalDroppedResp OBJECT-TYPE
            SYNTAX Counter32
            MAX-ACCESS read-only
            STATUS current
            DESCRIPTION
                "The object specifies the number of IPSLA pings for which
                a response was not received from the far end device."
            ::= { zhoneIpSLAPathStatByIntervalEntry 10 }


-- *********************************************************************
-- *********************** zhoneIpSLA Traps  ***************************
-- *********************************************************************
--
        -- 1.3.6.1.4.1.5504.4.1.21.2
        zhoneIpSLATraps OBJECT IDENTIFIER ::= { zhoneIpSLA 2 }


        -- 1.3.6.1.4.1.5504.4.1.21.2.0
        zhoneIpSLATrapsPrefix OBJECT-IDENTITY
            STATUS current
            DESCRIPTION
                "Prefix 0 for Zhone IPSLA MIB traps as required by SNMPv2"
            ::= { zhoneIpSLATraps 0 }


        -- 1.3.6.1.4.1.5504.4.1.21.2.0.1
        zhoneIpSLATimeoutTrap NOTIFICATION-TYPE
            OBJECTS { zhoneIpSLAPathConnectSrcIP, zhoneIpSLAPathStatByCOSTargetIP, zhoneIpSLACosActionName, zhoneIpSLAPathStatByCOSDroppedResp, zhoneIpSLACosActionTimeoutErrThresh
                 }
            STATUS current
            DESCRIPTION
                "This trap is generated whenever zhoneIpSLAPathStatByCOSDropResp
                exceeds zhoneIpSLACosActionTimeoutErrThresh."
            ::= { zhoneIpSLATrapsPrefix 1 }


        -- 1.3.6.1.4.1.5504.4.1.21.2.0.2
        zhoneIpSLALatencyTrap NOTIFICATION-TYPE
            OBJECTS { zhoneIpSLAPathConnectSrcIP, zhoneIpSLAPathStatByCOSTargetIP, zhoneIpSLACosActionName, zhoneIpSLAPathStatByCOSAvgRTT, zhoneIpSLACosActionLatencyErrThresh
                 }
            STATUS current
            DESCRIPTION
                "This trap is generated whenever zhoneIpSLAPathStatByCOSAvgRTT
                exceeds zhoneIpSLACosActionLatencyErrThresh."
            ::= { zhoneIpSLATrapsPrefix 2 }


        -- 1.3.6.1.4.1.5504.4.1.21.2.0.3
        zhoneIpSLAJitterTrap NOTIFICATION-TYPE
            OBJECTS { zhoneIpSLAPathConnectSrcIP, zhoneIpSLAPathStatByCOSTargetIP, zhoneIpSLACosActionName, zhoneIpSLAPathStatByCOSMinRTT, zhoneIpSLAPathStatByCOSMaxRTT,
                zhoneIpSLACosActionJitterErrThresh }
            STATUS current
            DESCRIPTION
                "This trap is generated whenever
                (zhoneIpSLAPathStatByCOSMaxRTT - zhoneIpSLAPathStatByCOSMinRTT)
                exceeds zhoneIpSLACosActionJitterErrThresh."
            ::= { zhoneIpSLATrapsPrefix 3 }


        -- 1.3.6.1.4.1.5504.4.1.21.2.0.4
        zhoneIpSLATimeoutClearTrap NOTIFICATION-TYPE
            OBJECTS { zhoneIpSLAPathConnectSrcIP, zhoneIpSLAPathStatByCOSTargetIP, zhoneIpSLACosActionName }
            STATUS current
            DESCRIPTION
                "This trap is generated to clear a timeout threshold violation condition."
            ::= { zhoneIpSLATrapsPrefix 4 }


        -- 1.3.6.1.4.1.5504.4.1.21.2.0.5
        zhoneIpSLALatencyClearTrap NOTIFICATION-TYPE
            OBJECTS { zhoneIpSLAPathConnectSrcIP, zhoneIpSLAPathStatByCOSTargetIP, zhoneIpSLACosActionName }
            STATUS current
            DESCRIPTION
                "This trap is generated to clear a latency threshold violation condition."
            ::= { zhoneIpSLATrapsPrefix 5 }


        -- 1.3.6.1.4.1.5504.4.1.21.2.0.6
        zhoneIpSLAJitterClearTrap NOTIFICATION-TYPE
            OBJECTS { zhoneIpSLAPathConnectSrcIP, zhoneIpSLAPathStatByCOSTargetIP, zhoneIpSLACosActionName }
            STATUS current
            DESCRIPTION
                "This trap is generated to clear a jitter threshold violation condition."
            ::= { zhoneIpSLATrapsPrefix 6 }


-- *********************************************************************
-- *********************** zhoneIpSLA Groups ***************************
-- *********************************************************************
--
        -- 1.3.6.1.4.1.5504.4.1.21.3
        zhoneIpSLAConformance OBJECT IDENTIFIER ::= { zhoneIpSLA 3 }


        -- 1.3.6.1.4.1.5504.4.1.21.3.1
        zhoneIpSLAMIBGroups OBJECT IDENTIFIER ::= { zhoneIpSLAConformance 1 }


        -- 1.3.6.1.4.1.5504.4.1.21.3.1.1
        zhoneIpSLAGlobalsGroup OBJECT-GROUP
            OBJECTS { zhoneIpSLAGlobalEnable, zhoneIpSLAGlobalPollInterval }
            STATUS current
            DESCRIPTION
                "The objects determining overall IPSLA behavior."
            ::= { zhoneIpSLAMIBGroups 1 }


        -- 1.3.6.1.4.1.5504.4.1.21.3.1.2
        zhoneIpSLACosActionGroup OBJECT-GROUP
            OBJECTS { zhoneIpSLACosActionName, zhoneIpSLACosActionTrapOnError, zhoneIpSLACosActionTimeoutErrThresh, zhoneIpSLACosActionTimeoutClrThresh, zhoneIpSLACosActionLatencyErrThresh,
                zhoneIpSLACosActionLatencyClrThresh, zhoneIpSLACosActionJitterErrThresh, zhoneIpSLACosActionJitterClrThresh, zhoneIpSLACosActionMetrics, zhoneIpSLACosActionPacketSize
                 }
            STATUS current
            DESCRIPTION
                "The objects in the IPSLA Cos Action table."
            ::= { zhoneIpSLAMIBGroups 2 }


        -- 1.3.6.1.4.1.5504.4.1.21.3.1.3
        zhoneIpSLACOSMapGroup OBJECT-GROUP
            OBJECTS { zhoneIpSLACosMapCosActionIndex }
            STATUS current
            DESCRIPTION
                "The objects in the IPSLA COS Map table."
            ::= { zhoneIpSLAMIBGroups 3 }


        -- 1.3.6.1.4.1.5504.4.1.21.3.1.4
        zhoneIpSLAStaticPathGroup OBJECT-GROUP
            OBJECTS { zhoneIpSLAStaticPathForwarding, zhoneIpSLAStaticPathState, zhoneIpSLAStaticPathRowstatus }
            STATUS current
            DESCRIPTION
                "The objects in the IPSLA Static Path table."
            ::= { zhoneIpSLAMIBGroups 4 }


        -- 1.3.6.1.4.1.5504.4.1.21.3.1.5
        zhoneIpSLAPathConnectGroup OBJECT-GROUP
            OBJECTS { zhoneIpSLAPathConnectDevName, zhoneIpSLAPathConnectDevType, zhoneIpSLAPathConnectStatus, zhoneIpSLAPathConnectSrcIP, zhoneIpSLAPathConnectDiscoveryType,
                zhoneIpSLAPathConnectUpTime, zhoneIpSLAPathConnectPollType, zhoneIpSLAPathConnectCosMismatch, zhoneIpSLAPathConnectLastCosActionIndex }
            STATUS current
            DESCRIPTION
                "The objects in the IPSLA Path Connection table."
            ::= { zhoneIpSLAMIBGroups 5 }


        -- 1.3.6.1.4.1.5504.4.1.21.3.1.6
        zhoneIpSLAPathStatByCOSGroup OBJECT-GROUP
            OBJECTS { zhoneIpSLAPathStatByCOSTargetIP, zhoneIpSLAPathStatByCOSStatus, zhoneIpSLAPathStatByCOSLastRTT, zhoneIpSLAPathStatByCOSMinRTT, zhoneIpSLAPathStatByCOSAvgRTT,
                zhoneIpSLAPathStatByCOSMaxRTT, zhoneIpSLAPathStatByCOSDroppedResp }
            STATUS current
            DESCRIPTION
                "The objects in the IPSLA Path Stats By COS table."
            ::= { zhoneIpSLAMIBGroups 6 }


        -- 1.3.6.1.4.1.5504.4.1.21.3.1.7
        zhoneIpSLAPathStatByIntervalGroup OBJECT-GROUP
            OBJECTS { zhoneIpSLAPathStatByIntervalDateTime, zhoneIpSLAPathStatByIntervalStatus, zhoneIpSLAPathStatByIntervalMinRTT, zhoneIpSLAPathStatByIntervalAvgRTT, zhoneIpSLAPathStatByIntervalMaxRTT,
                zhoneIpSLAPathStatByIntervalDroppedResp }
            STATUS current
            DESCRIPTION
                "The objects in the IPSLA Path Stats By Interval table."
            ::= { zhoneIpSLAMIBGroups 7 }


        -- 1.3.6.1.4.1.5504.4.1.21.3.1.8
        zhoneIpSLANotificationGroup NOTIFICATION-GROUP
            NOTIFICATIONS { zhoneIpSLATimeoutTrap, zhoneIpSLALatencyTrap, zhoneIpSLAJitterTrap, zhoneIpSLATimeoutClearTrap, zhoneIpSLALatencyClearTrap,
                zhoneIpSLAJitterClearTrap }
            STATUS current
            DESCRIPTION
                "IPSLA Notifications Group"
            ::= { zhoneIpSLAMIBGroups 8 }


        -- 1.3.6.1.4.1.5504.4.1.21.3.2
        zhoneIpSLACompliances OBJECT IDENTIFIER ::= { zhoneIpSLAConformance 2 }


        -- 1.3.6.1.4.1.5504.4.1.21.3.2.1
        zhoneIpSLACompliance MODULE-COMPLIANCE
            STATUS current
            DESCRIPTION
                "The compliance statement for SNMP entities which support
                IPSLA configuration."
            MODULE -- this module
                MANDATORY-GROUPS { zhoneIpSLAGlobalsGroup, zhoneIpSLACosActionGroup, zhoneIpSLACOSMapGroup, zhoneIpSLAStaticPathGroup, zhoneIpSLAPathConnectGroup,
                    zhoneIpSLAPathStatByCOSGroup, zhoneIpSLANotificationGroup }
                GROUP zhoneIpSLAPathStatByIntervalGroup
                    DESCRIPTION
                        "Optional Group."
            ::= { zhoneIpSLACompliances 1 }



    END

--
-- comIpIpslm.mib
--
