--
-- comIpIcmp.mib
-- MIB generated by MG-SOFT Visual MIB Builder Version 2.0 Build 187
-- Monday, September 11, 2000 at 16:26:27
--

	ZHONE-COM-IP-ICMP-MIB DEFINITIONS ::= BEGIN

		IMPORTS
			Counter32, OBJECT-TYPE, MODULE-IDENTITY, OBJECT-IDENTITY
				FROM SNMPv2-SMI
			rdEntry
				FROM ZHONE-COM-IP-RD-MIB
			zhoneIp, zhoneModules
				FROM Zhone;


-- Make this generate an ICMP_Resource record definition in the
-- files icmpResource.c/h
--
		comIpIcmp MODULE-IDENTITY
			LAST-UPDATED "200009111648Z"
			ORGANIZATION
				"Zhone Technologies"
			CONTACT-INFO
				"  Postal:
				           Zhone Technologies, Inc.
				           @ Zhone Way
				           7001 Oakport Street
				           Oakland, CA  94621
				           USA
				Toll-Free: +1 877-ZHONE20 (+1 877-946-6320)
				      Tel: +1-510-777-7000
				      Fax: +1-510-777-7001
				   E-mail: support@zhone.com

				"
			DESCRIPTION
				"Zhone ICMP MIB Module.
				IP Software
				Minneapolis, MN"
			REVISION "200009111625Z"
			DESCRIPTION
				"V01.00.00 - Initial Release"
			::= { zhoneModules 55 }


--
-- Node definitions
--

		icmp OBJECT-IDENTITY
			STATUS current
			DESCRIPTION
				"ICMP objects based on RFC 2011."
			::= { zhoneIp 5 }

		zhoneIcmpTable OBJECT-TYPE
			SYNTAX SEQUENCE OF ZhoneIcmpEntry
			MAX-ACCESS not-accessible
			STATUS current
			DESCRIPTION
				"Zhone ICMP Table."
			::= { icmp 1 }

		zhoneIcmpEntry OBJECT-TYPE
			SYNTAX ZhoneIcmpEntry
			MAX-ACCESS not-accessible
			STATUS current
			DESCRIPTION
				"Zhone ICMP Entry.  This table augments the Routing Domain Table
				defined in comIpRD.mib."
			AUGMENTS { rdEntry }
			::= { zhoneIcmpTable 1 }

		ZhoneIcmpEntry ::=
			SEQUENCE {
				zhIcmpInMsgs
					Counter32,
				zhIcmpInErrors
					Counter32,
				zhIcmpInDestUnreachs
					Counter32,
				zhIcmpInTimeExcds
					Counter32,
				zhIcmpInParmProbs
					Counter32,
				zhIcmpInSrcQuenchs
					Counter32,
				zhIcmpInRedirects
					Counter32,
				zhIcmpInEchos
					Counter32,
				zhIcmpInEchoReps
					Counter32,
				zhIcmpInTimestamps
					Counter32,
				zhIcmpInTimestampReps
					Counter32,
				zhIcmpInAddrMasks
					Counter32,
				zhIcmpInAddrMaskReps
					Counter32,
				zhIcmpOutMsgs
					Counter32,
				zhIcmpOutErrors
					Counter32,
				zhIcmpOutDestUnreachs
					Counter32,
				zhIcmpOutTimeExcds
					Counter32,
				zhIcmpOutParmProbs
					Counter32,
				zhIcmpOutSrcQuenchs
					Counter32,
				zhIcmpOutRedirects
					Counter32,
				zhIcmpOutEchos
					Counter32,
				zhIcmpOutEchoReps
					Counter32,
				zhIcmpOutTimestamps
					Counter32,
				zhIcmpOutTimestampReps
					Counter32,
				zhIcmpOutAddrMasks
					Counter32,
				zhIcmpOutAddrMaskReps
					Counter32
			 }

		zhIcmpInMsgs OBJECT-TYPE
			SYNTAX Counter32
			MAX-ACCESS read-only
			STATUS current
			DESCRIPTION
				"The total number of ICMP messages which the entity
				received.  Note that this counter includes all those counted
				by icmpInErrors."
			REFERENCE
				"See RFC2011:  icmp.icmpInMsgs"
			::= { zhoneIcmpEntry 1 }

		zhIcmpInErrors OBJECT-TYPE
			SYNTAX Counter32
			MAX-ACCESS read-only
			STATUS current
			DESCRIPTION
				"The number of ICMP messages which the entity received but
				determined as having ICMP-specific errors (bad ICMP
				checksums, bad length, etc.)."
			REFERENCE
				"See RFC2011:  icmp.icmpInErrors"
			::= { zhoneIcmpEntry 2 }

		zhIcmpInDestUnreachs OBJECT-TYPE
			SYNTAX Counter32
			MAX-ACCESS read-only
			STATUS current
			DESCRIPTION
				"The number of ICMP Destination Unreachable messages
				received."
			REFERENCE
				"See RFC2011:  icmp.icmpInDestUnreachs"
			::= { zhoneIcmpEntry 3 }

		zhIcmpInTimeExcds OBJECT-TYPE
			SYNTAX Counter32
			MAX-ACCESS read-only
			STATUS current
			DESCRIPTION
				"The number of ICMP Time Exceeded messages received."
			REFERENCE
				"See RFC2011:  icmp.icmpInTimeExcds"
			::= { zhoneIcmpEntry 4 }

		zhIcmpInParmProbs OBJECT-TYPE
			SYNTAX Counter32
			MAX-ACCESS read-only
			STATUS current
			DESCRIPTION
				"The number of ICMP Parameter Problem messages received."
			REFERENCE
				"See RFC2011:  icmp.icmpInParmProbs"
			::= { zhoneIcmpEntry 5 }

		zhIcmpInSrcQuenchs OBJECT-TYPE
			SYNTAX Counter32
			MAX-ACCESS read-only
			STATUS current
			DESCRIPTION
				"The number of ICMP Source Quench messages received."
			REFERENCE
				"See RFC2011:  icmp.icmpInSrcQuenchs"
			::= { zhoneIcmpEntry 6 }

		zhIcmpInRedirects OBJECT-TYPE
			SYNTAX Counter32
			MAX-ACCESS read-only
			STATUS current
			DESCRIPTION
				"The number of ICMP Redirect messages received."
			REFERENCE
				"See RFC2011:  icmp.icmpInRedirects"
			::= { zhoneIcmpEntry 7 }

		zhIcmpInEchos OBJECT-TYPE
			SYNTAX Counter32
			MAX-ACCESS read-only
			STATUS current
			DESCRIPTION
				"The number of ICMP Echo (request) messages received."
			REFERENCE
				"See RFC2011:  icmp.icmpInEchos"
			::= { zhoneIcmpEntry 8 }

		zhIcmpInEchoReps OBJECT-TYPE
			SYNTAX Counter32
			MAX-ACCESS read-only
			STATUS current
			DESCRIPTION
				"The number of ICMP Echo Reply messages received."
			REFERENCE
				"See RFC2011:  icmp.icmpInEchoReps"
			::= { zhoneIcmpEntry 9 }

		zhIcmpInTimestamps OBJECT-TYPE
			SYNTAX Counter32
			MAX-ACCESS read-only
			STATUS current
			DESCRIPTION
				"The number of ICMP Timestamp (request) messages received."
			REFERENCE
				"See RFC2011:  icmp.icmpInTimestamps"
			::= { zhoneIcmpEntry 10 }

		zhIcmpInTimestampReps OBJECT-TYPE
			SYNTAX Counter32
			MAX-ACCESS read-only
			STATUS current
			DESCRIPTION
				"The number of ICMP Timestamp Reply messages received."
			REFERENCE
				"See RFC2011:  icmp.icmpInTimestampReps"
			::= { zhoneIcmpEntry 11 }

		zhIcmpInAddrMasks OBJECT-TYPE
			SYNTAX Counter32
			MAX-ACCESS read-only
			STATUS current
			DESCRIPTION
				"The number of ICMP Address Mask Request messages received."
			REFERENCE
				"See RFC2011:  icmp.icmpInAddrMasks"
			::= { zhoneIcmpEntry 12 }

		zhIcmpInAddrMaskReps OBJECT-TYPE
			SYNTAX Counter32
			MAX-ACCESS read-only
			STATUS current
			DESCRIPTION
				"The number of ICMP Address Mask Reply messages received."
			REFERENCE
				"See RFC2011:  icmp.icmpInAddrMaskReps"
			::= { zhoneIcmpEntry 13 }

		zhIcmpOutMsgs OBJECT-TYPE
			SYNTAX Counter32
			MAX-ACCESS read-only
			STATUS current
			DESCRIPTION
				"The total number of ICMP messages which this entity
				attempted to send.  Note that this counter includes all
				those counted by icmpOutErrors."
			REFERENCE
				"See RFC2011:  icmp.icmpOutMsgs"
			::= { zhoneIcmpEntry 14 }

		zhIcmpOutErrors OBJECT-TYPE
			SYNTAX Counter32
			MAX-ACCESS read-only
			STATUS current
			DESCRIPTION
				"The number of ICMP messages which this entity did not send
				due to problems discovered within ICMP such as a lack of
				buffers.  This value should not include errors discovered
				outside the ICMP layer such as the inability of IP to route
				the resultant datagram.  In some implementations there may
				be no types of error which contribute to this counter's
				value."
			REFERENCE
				"See RFC2011:  icmp.icmpOutErrors"
			::= { zhoneIcmpEntry 15 }

		zhIcmpOutDestUnreachs OBJECT-TYPE
			SYNTAX Counter32
			MAX-ACCESS read-only
			STATUS current
			DESCRIPTION
				"The number of ICMP Destination Unreachable messages sent."
			REFERENCE
				"See RFC2011:  icmp.icmpOutDestUnreachs"
			::= { zhoneIcmpEntry 16 }

		zhIcmpOutTimeExcds OBJECT-TYPE
			SYNTAX Counter32
			MAX-ACCESS read-only
			STATUS current
			DESCRIPTION
				"The number of ICMP Time Exceeded messages sent."
			REFERENCE
				"See RFC2011:  icmp.icmpOutTimeExcds"
			::= { zhoneIcmpEntry 17 }

		zhIcmpOutParmProbs OBJECT-TYPE
			SYNTAX Counter32
			MAX-ACCESS read-only
			STATUS current
			DESCRIPTION
				"The number of ICMP Parameter Problem messages sent."
			REFERENCE
				"See RFC2011:  icmp.icmpOutParmProbs"
			::= { zhoneIcmpEntry 18 }

		zhIcmpOutSrcQuenchs OBJECT-TYPE
			SYNTAX Counter32
			MAX-ACCESS read-only
			STATUS current
			DESCRIPTION
				"The number of ICMP Source Quench messages sent."
			REFERENCE
				"See RFC2011:  icmp.icmpOutSrcQuenchs"
			::= { zhoneIcmpEntry 19 }

		zhIcmpOutRedirects OBJECT-TYPE
			SYNTAX Counter32
			MAX-ACCESS read-only
			STATUS current
			DESCRIPTION
				"The number of ICMP Redirect messages sent.  For a host,
				this object will always be zero, since hosts do not send
				redirects."
			REFERENCE
				"See RFC2011:  icmp.icmpOutRedirects"
			::= { zhoneIcmpEntry 20 }

		zhIcmpOutEchos OBJECT-TYPE
			SYNTAX Counter32
			MAX-ACCESS read-only
			STATUS current
			DESCRIPTION
				"The number of ICMP Echo (request) messages sent."
			REFERENCE
				"See RFC2011:  icmp.icmpOutEchos"
			::= { zhoneIcmpEntry 21 }

		zhIcmpOutEchoReps OBJECT-TYPE
			SYNTAX Counter32
			MAX-ACCESS read-only
			STATUS current
			DESCRIPTION
				"The number of ICMP Echo Reply messages sent."
			REFERENCE
				"See RFC2011:  icmp.icmpOutEchoReps"
			::= { zhoneIcmpEntry 22 }

		zhIcmpOutTimestamps OBJECT-TYPE
			SYNTAX Counter32
			MAX-ACCESS read-only
			STATUS current
			DESCRIPTION
				"The number of ICMP Timestamp (request) messages sent."
			REFERENCE
				"See RFC2011:  icmp.icmpOutTimestamps"
			::= { zhoneIcmpEntry 23 }

		zhIcmpOutTimestampReps OBJECT-TYPE
			SYNTAX Counter32
			MAX-ACCESS read-only
			STATUS current
			DESCRIPTION
				"The number of ICMP Timestamp Reply messages sent."
			REFERENCE
				"See RFC2011:  icmp.icmpOutTimestampReps"
			::= { zhoneIcmpEntry 24 }

		zhIcmpOutAddrMasks OBJECT-TYPE
			SYNTAX Counter32
			MAX-ACCESS read-only
			STATUS current
			DESCRIPTION
				"The number of ICMP Address Mask Request messages sent."
			REFERENCE
				"See RFC2011:  icmp.icmpOutAddrMasks"
			::= { zhoneIcmpEntry 25 }

		zhIcmpOutAddrMaskReps OBJECT-TYPE
			SYNTAX Counter32
			MAX-ACCESS read-only
			STATUS current
			DESCRIPTION
				"The number of ICMP Address Mask Reply messages sent."
			REFERENCE
				"See RFC2011:  icmp.icmpOutAddrMaskReps"
			::= { zhoneIcmpEntry 26 }


	END

--
-- comIpIcmp.mib
--
