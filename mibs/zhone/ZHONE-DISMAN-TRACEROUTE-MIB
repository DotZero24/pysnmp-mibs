ZHONE-DISMAN-TRACEROUTE-MIB DEFINITIONS ::= BEGIN

IMPORTS
    MODULE-IDENTITY, OBJECT-TYPE, Integer32,
    Gauge32, Unsigned32, mib-2,
    NOTIFICATION-TYPE,
    OBJECT-IDENTITY
        FROM SNMPv2-SMI                  -- RFC2578
    RowStatus, StorageType,
    TruthValue, DateAndTime
        FROM SNMPv2-TC                   -- RFC2579
    MODULE-COMPLIANCE, OBJECT-GROUP,
    NOTIFICATION-GROUP
        FROM SNMPv2-CONF                 -- RFC2580
    SnmpAdminString
        FROM SNMP-FRAMEWORK-MIB          -- RFC2571
    InterfaceIndexOrZero                 -- RFC2863
        FROM IF-MIB
    InetAddressType, InetAddress
        FROM INET-ADDRESS-MIB            -- RFC2851
    OperationResponseStatus
        FROM ZHONE-DISMAN-PING-MIB       -- RFC2925
    zhoneIp
        FROM Zhone;







 zhoneTraceRouteMIB MODULE-IDENTITY
    LAST-UPDATED "200009210000Z"         -- 21 September 2000

    ORGANIZATION "IETF Distributed Management Working Group"
    CONTACT-INFO
        "Kenneth White

        International Business Machines Corporation
        Network Computing Software Division
        Research Triangle Park, NC, USA
        E-mail: wkenneth@us.ibm.com"
    DESCRIPTION
        "The Traceroute MIB (ZHONE-DISMAN-TRACEROUTE-MIB) provides
        access to the traceroute capability at a remote host."

     --  Revision history

     REVISION     "200009210000Z"         -- 21 September 2000
     DESCRIPTION
         "Initial version, published as RFC 2925."

    ::= { zhoneIp 20 }

 -- Top level structure of the MIB

 zhoneTraceRouteNotifications  OBJECT IDENTIFIER ::= { zhoneTraceRouteMIB 0 }
 zhoneTraceRouteObjects        OBJECT IDENTIFIER ::= { zhoneTraceRouteMIB 1 }
 zhoneTraceRouteConformance    OBJECT IDENTIFIER ::= { zhoneTraceRouteMIB 2 }

 -- The registration node (point) for zhoneTraceRoute implementation types

 zhoneTraceRouteImplementationTypeDomains OBJECT IDENTIFIER
 ::= { zhoneTraceRouteMIB 3 }

 zhoneTraceRouteUsingUdpProbes OBJECT-IDENTITY
    STATUS      current
    DESCRIPTION
        "Indicates that an implementation is using UDP probes to
        perform the traceroute operation."
    ::= { zhoneTraceRouteImplementationTypeDomains 1 }


 -- Simple Object Definitions


 zhoneTraceRouteMaxConcurrentRequests OBJECT-TYPE
    SYNTAX      Unsigned32
    UNITS       "requests"
    MAX-ACCESS  read-write
    STATUS      current
    DESCRIPTION
       "The maximum number of concurrent active traceroute requests
       that are allowed within an agent implementation.  A value
       of 0 for this object implies that there is no limit for
       the number of concurrent active requests in effect."
    DEFVAL { 10 }
    ::= { zhoneTraceRouteObjects 1 }


 zhoneTraceRouteCtlIndexNext  OBJECT-TYPE
      SYNTAX         INTEGER (0..2147483647)
      MAX-ACCESS     read-only
      STATUS         current
      DESCRIPTION
       "This object contains an appropriate value to
        be used for zhonePingCtlIndex when creating
        entries in the zhonePingCtlTable.  The value
        0 indicates that no unassigned entries are
        available. To obtain the zhonePingCtlIndex
        value for a new entry, the manager issues a
        management protocol retrieval operation to obtain
        the current value of this object.  After each
        retrieval, the agent should modify the value to
        the next unassigned index.
        After a manager retrieves a value the agent will
        determine through its local policy when this index
        value will be made available for reuse."
      ::= { zhoneTraceRouteObjects 2 }


  -- Traceroute Control Table

 zhoneTraceRouteCtlTable OBJECT-TYPE
    SYNTAX      SEQUENCE OF ZhoneTraceRouteCtlEntry
    MAX-ACCESS  not-accessible
    STATUS      current
    DESCRIPTION
        "Defines the Remote Operations Traceroute Control Table for
        providing the capability of invoking traceroute from a remote
        host.  The results of traceroute operations can be stored in
        the zhoneTraceRouteResultsTable, and
        the zhoneTraceRouteHopsTable."
   ::= { zhoneTraceRouteObjects 3 }

 zhoneTraceRouteCtlEntry OBJECT-TYPE
    SYNTAX      ZhoneTraceRouteCtlEntry
    MAX-ACCESS  not-accessible
    STATUS      current
    DESCRIPTION
        "Defines an entry in the zhoneTraceRouteCtlTable."
    INDEX {
            zhoneTraceRouteCtlIndex
          }
    ::= { zhoneTraceRouteCtlTable 1 }

 ZhoneTraceRouteCtlEntry ::=
    SEQUENCE {
      zhoneTraceRouteCtlIndex              INTEGER,
      zhoneTraceRouteCtlTargetAddressType  InetAddressType,
      zhoneTraceRouteCtlTargetAddress      InetAddress,
      zhoneTraceRouteCtlByPassRouteTable   TruthValue,
      zhoneTraceRouteCtlDataSize           Unsigned32,
      zhoneTraceRouteCtlTimeOut            Unsigned32,
      zhoneTraceRouteCtlProbesPerHop       Unsigned32,
      zhoneTraceRouteCtlPort               Unsigned32,
      zhoneTraceRouteCtlMaxTtl             Unsigned32,
      zhoneTraceRouteCtlDSField            Unsigned32,
      zhoneTraceRouteCtlSourceAddressType  InetAddressType,
      zhoneTraceRouteCtlSourceAddress      InetAddress,
      zhoneTraceRouteCtlIfIndex            InterfaceIndexOrZero,
      zhoneTraceRouteCtlMiscOptions        SnmpAdminString,
      zhoneTraceRouteCtlMaxFailures        Unsigned32,
      zhoneTraceRouteCtlDontFragment       TruthValue,
      zhoneTraceRouteCtlInitialTtl         Unsigned32,
      zhoneTraceRouteCtlFrequency          Unsigned32,
      zhoneTraceRouteCtlStorageType        StorageType,
      zhoneTraceRouteCtlAdminStatus        INTEGER,
      zhoneTraceRouteCtlMaxRows            Unsigned32,
      zhoneTraceRouteCtlTrapGeneration     BITS,
      zhoneTraceRouteCtlDescr              SnmpAdminString,
      zhoneTraceRouteCtlCreateHopsEntries  TruthValue,
      zhoneTraceRouteCtlType               OBJECT IDENTIFIER,
      zhoneTraceRouteCtlRowStatus          RowStatus
    }



 zhoneTraceRouteCtlIndex OBJECT-TYPE
    SYNTAX       INTEGER (0..2147483647)
    MAX-ACCESS   read-only
    STATUS      current
    DESCRIPTION
       "When used in conjunction with such a security policy
       all entries in the table belonging to a particular user
       (or group) will have the same value for this initial
       index.  For a given user's entries in a particular
       table, the object identifiers for the information in
       these entries will have the same subidentifiers (except
       for the 'column' subidentifier) up to the end of the
       encoded owner index."
    ::= { zhoneTraceRouteCtlEntry 1 }

 zhoneTraceRouteCtlTargetAddressType OBJECT-TYPE
    SYNTAX      InetAddressType
    MAX-ACCESS  read-create
    STATUS      current
    DESCRIPTION
        "Specifies the type of host address to be used on the
        traceroute request at the remote host."
    DEFVAL { ipv4 }
    ::= { zhoneTraceRouteCtlEntry 2 }


 zhoneTraceRouteCtlTargetAddress OBJECT-TYPE
    SYNTAX      InetAddress
    MAX-ACCESS  read-create
    STATUS      current
    DESCRIPTION
        "Specifies the host address used on the
        traceroute request at the remote host.  The
        host address type can be determined by the
        examining the value of the corresponding
        zhoneTraceRouteCtlTargetAddressType index element.

        A value for this object MUST be set prior to
        transitioning its corresponding zhoneTraceRouteCtlEntry to
        active(1) via zhoneTraceRouteCtlRowStatus."
    ::= { zhoneTraceRouteCtlEntry 3 }

 zhoneTraceRouteCtlByPassRouteTable OBJECT-TYPE
    SYNTAX TruthValue
    MAX-ACCESS  read-create
    STATUS      current
    DESCRIPTION
       "The purpose of this object is to optionally enable
       bypassing the route table.  If enabled, the remote
       host will bypass the normal routing tables and send
       directly to a host on an attached network.  If the
       host is not on a directly-attached network, an
       error is returned.  This option can be used to perform
       the traceroute operation to a local host through an
       interface that has no route defined (e.g., after the
       interface was dropped by routed)."
    DEFVAL { false }
    ::= { zhoneTraceRouteCtlEntry 4 }


 zhoneTraceRouteCtlDataSize OBJECT-TYPE
    SYNTAX      Unsigned32 (0..65507)
    UNITS       "octets"
    MAX-ACCESS  read-create
    STATUS      current
    DESCRIPTION
        "Specifies the size of the data portion of a traceroute
        request in octets.  A traceroute request is essentially
        transmitted by encoding a UDP datagram into a
        IP packet. So subtracting the size of a UDP header
        (8 octets) and the size of a IP header (20 octets)
        yields a maximum of 65507 octets."
    DEFVAL { 0 }
    ::= { zhoneTraceRouteCtlEntry 5 }


 zhoneTraceRouteCtlTimeOut OBJECT-TYPE
    SYNTAX      Unsigned32 (1..60)
    UNITS       "seconds"
    MAX-ACCESS  read-create
    STATUS      current
    DESCRIPTION
        "Specifies the time-out value, in seconds, for
        a traceroute request."
    DEFVAL { 3 }
    ::= { zhoneTraceRouteCtlEntry 6 }


 zhoneTraceRouteCtlProbesPerHop OBJECT-TYPE
    SYNTAX      Unsigned32 (1..10)
    UNITS       "probes"
    MAX-ACCESS  read-create
    STATUS      current
    DESCRIPTION
        "Specifies the number of times to reissue a traceroute
        request with the same time-to-live (TTL) value."
    DEFVAL { 3 }
    ::= { zhoneTraceRouteCtlEntry 7 }


 zhoneTraceRouteCtlPort OBJECT-TYPE
    SYNTAX      Unsigned32 (1..65535)
    UNITS       "UDP Port"
    MAX-ACCESS  read-create
    STATUS      current
    DESCRIPTION
        "Specifies the UDP port to send the traceroute
        request to.  Need to specify a port that is not in
        use at the destination (target) host.  The default
        value for this object is the IANA assigned port,
        33434, for the traceroute function."
    DEFVAL { 33434 }
    ::= { zhoneTraceRouteCtlEntry 8 }


 zhoneTraceRouteCtlMaxTtl OBJECT-TYPE
    SYNTAX      Unsigned32 (1..255)
    UNITS       "time-to-live value"
    MAX-ACCESS  read-create
    STATUS      current
    DESCRIPTION
        "Specifies the maximum time-to-live value."
    DEFVAL { 30 }
    ::= { zhoneTraceRouteCtlEntry 9 }

 zhoneTraceRouteCtlDSField OBJECT-TYPE
    SYNTAX      Unsigned32 (0..255)
    MAX-ACCESS  read-create
    STATUS      current
    DESCRIPTION
        "Specifies the value to store in the Differentiated
        Services (DS) Field in the IP packet used to
        encapsulate the traceroute probe.  The DS Field is
        defined as the Type of Service (TOS) octet in a IPv4
        header or as the Traffic Class octet in a IPv6 header.

        The value of this object must be a decimal integer
        in the range from 0 to 255.  This option can be used
        to determine what effect an explicit DS Field setting
        has on a traceroute response.  Not all values are legal
        or meaningful.  DS Field usage is often not supported
        by IP implementations.  A value of 0 means that the
     function represented by this option is not supported.
     Useful TOS octet values are probably '16' (low delay)
     and '8' ( high throughput)."
    REFERENCE
        "Refer to RFC 2474 for the definition of the
        Differentiated Services Field and to RFC 1812
        Section 5.3.2 for Type of Service (TOS)."
    DEFVAL { 0 }
    ::= { zhoneTraceRouteCtlEntry 10 }

 zhoneTraceRouteCtlSourceAddressType OBJECT-TYPE
    SYNTAX      InetAddressType
    MAX-ACCESS  read-create
    STATUS      current
    DESCRIPTION
        "Specifies the type of the source address,
        zhoneTraceRouteCtlSourceAddress, to be used at a remote host
        when performing a traceroute operation."
    DEFVAL { unknown }
    ::= { zhoneTraceRouteCtlEntry 11 }

 zhoneTraceRouteCtlSourceAddress OBJECT-TYPE
    SYNTAX      InetAddress
    MAX-ACCESS  read-create
    STATUS      current
    DESCRIPTION
        "Use the specified IP address (which must be given
        as an IP number, not a hostname) as the source
        address in outgoing probe packets. On hosts with
        more than one IP address, this option can be used
        to force the source address to be something other
        than the primary IP address of the interface the
        probe packet is sent on.  If the IP address is not
        one of this machine's interface addresses, an error
        is returned and nothing is sent.  A zero length
        octet string value for this object disables source
        address specification.

        The address type (InetAddressType) that relates to
        this object is specified by the corresponding value
        of zhoneTraceRouteCtlSourceAddressType."
    DEFVAL { '0'H }
    ::= { zhoneTraceRouteCtlEntry 12 }

 zhoneTraceRouteCtlIfIndex OBJECT-TYPE
    SYNTAX      InterfaceIndexOrZero
    MAX-ACCESS  read-create
    STATUS      current
    DESCRIPTION
        "Setting this object to an interface's ifIndex prior
        to starting a remote traceroute operation directs
        the traceroute probes to be transmitted over the
        specified interface.  A value of zero for this object
        implies that this option is not enabled."
    DEFVAL { 0 }
    ::= { zhoneTraceRouteCtlEntry 13 }

 zhoneTraceRouteCtlMiscOptions OBJECT-TYPE
    SYNTAX      SnmpAdminString
    MAX-ACCESS  read-create
    STATUS      current
    DESCRIPTION
        "Enables an application to specify implementation
        dependent options."
    DEFVAL { '0'H }
    ::= { zhoneTraceRouteCtlEntry 14 }

 zhoneTraceRouteCtlMaxFailures OBJECT-TYPE
    SYNTAX      Unsigned32 (0..255)
    UNITS       "timeouts"
    MAX-ACCESS  read-create
    STATUS      current
    DESCRIPTION
        "The value of this object indicates the maximum number
        of consecutive timeouts allowed before terminating
        a remote traceroute request.  A value of either 255 (maximum
        hop count/possible TTL value) or a 0 indicates that the
        function of terminating a remote traceroute request when a
        specific number of successive timeouts are detected is
        disabled."
    DEFVAL { 5 }
    ::= { zhoneTraceRouteCtlEntry 15 }

 zhoneTraceRouteCtlDontFragment OBJECT-TYPE
    SYNTAX         TruthValue
    MAX-ACCESS     read-create
    STATUS         current
    DESCRIPTION
        "This object enables setting of the don't fragment flag (DF)
        in the IP header for a probe.  Use of this object enables
        performing a manual PATH MTU test."
    DEFVAL  { false }
    ::= { zhoneTraceRouteCtlEntry 16 }


 zhoneTraceRouteCtlInitialTtl OBJECT-TYPE
    SYNTAX         Unsigned32 (0..255)
    MAX-ACCESS     read-create
    STATUS         current
    DESCRIPTION
        "The value of this object specifies the initial TTL value to
        use.  This enables bypassing the initial (often well known)
        portion of a path."
    DEFVAL { 1 }
    ::= { zhoneTraceRouteCtlEntry 17 }

 zhoneTraceRouteCtlFrequency  OBJECT-TYPE
    SYNTAX      Unsigned32
    UNITS       "seconds"
    MAX-ACCESS  read-create
    STATUS      current
    DESCRIPTION
        "The number of seconds to wait before repeating a
        traceroute test as defined by the value of the
        various objects in the corresponding row.

        The number of hops in a single traceroute test
        is determined by the value of the corresponding
        zhoneTraceRouteCtlProbesPerHop object.  After a
        single test completes the number of seconds as defined
        by the value of zhoneTraceRouteCtlFrequency MUST elapse
        before the next traceroute test is started.

        A value of 0 for this object implies that the test
        as defined by the corresponding entry will not be
        repeated."
    DEFVAL { 0 }
    ::= { zhoneTraceRouteCtlEntry 18 }

 zhoneTraceRouteCtlStorageType OBJECT-TYPE
    SYNTAX      StorageType
    MAX-ACCESS  read-create
    STATUS      current
    DESCRIPTION
        "The storage type for this conceptual row.
        Conceptual rows having the value 'permanent' need not
        allow write-access to any columnar objects in the row."
    DEFVAL { nonVolatile }
    ::= { zhoneTraceRouteCtlEntry 19 }


 zhoneTraceRouteCtlAdminStatus OBJECT-TYPE
    SYNTAX      INTEGER {
                          enabled(1), -- operation should be started
                          disabled(2) -- operation should be stopped
                        }
    MAX-ACCESS  read-create
    STATUS      current
    DESCRIPTION
        "Reflects the desired state that an zhoneTraceRouteCtlEntry
        should be in:

           enabled(1)  - Attempt to activate the test as defined by
                         this zhoneTraceRouteCtlEntry.
           disabled(2) - Deactivate the test as defined by this
                         zhoneTraceRouteCtlEntry.

        Refer to the corresponding zhoneTraceRouteResultsOperStatus to
        determine the operational state of the test defined by
        this entry."
     DEFVAL { disabled }
    ::= { zhoneTraceRouteCtlEntry 20 }

 zhoneTraceRouteCtlDescr OBJECT-TYPE
    SYNTAX      SnmpAdminString
    MAX-ACCESS  read-create
    STATUS      current
    DESCRIPTION
        "The purpose of this object is to provide a
        descriptive name of the remote traceroute
        test."
    DEFVAL { '0'H }
    ::= { zhoneTraceRouteCtlEntry 21 }

 zhoneTraceRouteCtlMaxRows OBJECT-TYPE
    SYNTAX      Unsigned32
    UNITS       "rows"
    MAX-ACCESS  read-create
    STATUS      current
    DESCRIPTION
        "None"
    DEFVAL      { 50 }
    ::= { zhoneTraceRouteCtlEntry 22 }

 zhoneTraceRouteCtlTrapGeneration OBJECT-TYPE
    SYNTAX      BITS {
                  pathChange(0),
                  testFailure(1),
                  testCompletion(2)
                }
    MAX-ACCESS  read-create
    STATUS      current
    DESCRIPTION
        "The value of this object determines when and if to
        to generate a notification for this entry:
        pathChange(0)     - Generate a zhoneTraceRoutePathChange
            notification when the current path varies from a
            previously determined path.
        testFailure(1)    - Generate a zhoneTraceRouteTestFailed
            notification when the full path to a target
            can't be determined.
        testCompletion(2) - Generate a zhoneTraceRouteTestCompleted
            notification when the path to a target has been
            determined.

        The value of this object defaults to zero, indicating
        that none of the above options have been selected."
    ::= { zhoneTraceRouteCtlEntry 23 }

 zhoneTraceRouteCtlCreateHopsEntries OBJECT-TYPE
    SYNTAX      TruthValue
    MAX-ACCESS  read-create
    STATUS      current
    DESCRIPTION
        "The current path for a traceroute test is kept in the
        zhoneTraceRouteHopsTable on a per hop basis when the value of
        this object is true(1)."
    DEFVAL { false }
    ::= { zhoneTraceRouteCtlEntry 24 }

 zhoneTraceRouteCtlType OBJECT-TYPE
    SYNTAX      OBJECT IDENTIFIER
    MAX-ACCESS  read-create
    STATUS      current
    DESCRIPTION
        "The value of this object is used either to report or
        select the implementation method to be used for
        performing a traceroute operation. The value of this
        object may be selected from
        zhoneTraceRouteImplementationTypeDomains.

        Additional implementation types should be allocated as
        required by implementers of the ZHONE-DISMAN-TRACEROUTE-MIB
        under their enterprise specific registration point and
        not beneath zhoneTraceRouteImplementationTypeDomains."
    DEFVAL { zhoneTraceRouteUsingUdpProbes }
    ::= { zhoneTraceRouteCtlEntry 25 }


 zhoneTraceRouteCtlRowStatus OBJECT-TYPE
    SYNTAX      RowStatus
    MAX-ACCESS  read-create
    STATUS      current
    DESCRIPTION
        "This object allows entries to be created and deleted
        in the traceRouteCtlTable.  Deletion of an entry in
        this table results in all corresponding (same
        zhoneTraceRouteCtlOwnerIndex and zhoneTraceRouteCtlTestName
        index values) zhoneTraceRouteResultsTable and
        zhoneTraceRouteHopsTable entries being deleted.

        A value MUST be specified for zhoneTraceRouteCtlTargetAddress
        prior to a transition to active(1) state being
        accepted.

        Activation of a remote traceroute operation is
        controlled via zhoneTraceRouteCtlAdminStatus and not
        by transitioning of this object's value to active(1).

        Transitions in and out of active(1) state are not
        allowed while an entry's zhoneTraceRouteResultsOperStatus
        is active(1) with the exception that deletion of
        an entry in this table by setting its RowStatus
        object to destroy(6) will stop an active
        traceroute operation.

        The operational state of an traceroute operation
        can be determined by examination of the corresponding
        zhoneTraceRouteResultsOperStatus object."
    REFERENCE
        "See definition of RowStatus in RFC 2579, 'Textual
        Conventions for SMIv2.'"
    ::= { zhoneTraceRouteCtlEntry 26 }


 -- Traceroute Results Table

 zhoneTraceRouteResultsTable OBJECT-TYPE
    SYNTAX      SEQUENCE OF ZhoneTraceRouteResultsEntry
    MAX-ACCESS  not-accessible
    STATUS      current
    DESCRIPTION
        "Defines the Remote Operations Traceroute Results Table for
        keeping track of the status of a zhoneTraceRouteCtlEntry.

        An entry is added to the zhoneTraceRouteResultsTable when an
        zhoneTraceRouteCtlEntry is started by successful transition
        of its zhoneTraceRouteCtlAdminStatus object to enabled(1).
        An entry is removed from the zhoneTraceRouteResultsTable when
        its corresponding zhoneTraceRouteCtlEntry is deleted."
   ::= { zhoneTraceRouteObjects 4 }

 zhoneTraceRouteResultsEntry OBJECT-TYPE
    SYNTAX      ZhoneTraceRouteResultsEntry
    MAX-ACCESS  not-accessible
    STATUS      current
    DESCRIPTION
        "Defines an entry in the zhoneTraceRouteResultsTable.  The
        zhoneTraceRouteResultsTable has the same indexing as the
        zhoneTraceRouteCtlTable in order for a zhoneTraceRouteResultsEntry
        to correspond to the zhoneTraceRouteCtlEntry that caused it to
        be created."
    INDEX {
            zhoneTraceRouteCtlIndex
          }
    ::= { zhoneTraceRouteResultsTable 1 }

 ZhoneTraceRouteResultsEntry ::=
    SEQUENCE {
      zhoneTraceRouteResultsOperStatus       INTEGER,
      zhoneTraceRouteResultsCurHopCount      Gauge32,
      zhoneTraceRouteResultsCurProbeCount    Gauge32,
      zhoneTraceRouteResultsIpTgtAddrType    InetAddressType,
      zhoneTraceRouteResultsIpTgtAddr        InetAddress,
      zhoneTraceRouteResultsTestAttempts     Unsigned32,
      zhoneTraceRouteResultsTestSuccesses    Unsigned32,
      zhoneTraceRouteResultsLastGoodPath     DateAndTime
    }



 zhoneTraceRouteResultsOperStatus OBJECT-TYPE
    SYNTAX      INTEGER {
                          enabled(1), -- test is in progress
                          disabled(2) -- test has stopped
                        }
    MAX-ACCESS  read-only
    STATUS      current
    DESCRIPTION
        "Reflects the operational state of an zhoneTraceRouteCtlEntry:

           enabled(1)  - Test is active.
           disabled(2) - Test has stopped."
    ::= { zhoneTraceRouteResultsEntry 1 }


 zhoneTraceRouteResultsCurHopCount OBJECT-TYPE
    SYNTAX      Gauge32
    UNITS       "hops"
    MAX-ACCESS  read-only
    STATUS      current
    DESCRIPTION
        "Reflects the current TTL value (range from 1 to
        255) for a remote traceroute operation.
        Maximum TTL value is determined by
        zhoneTraceRouteCtlMaxTtl."
    ::= { zhoneTraceRouteResultsEntry 2 }


 zhoneTraceRouteResultsCurProbeCount OBJECT-TYPE
    SYNTAX      Gauge32
    UNITS       "probes"
    MAX-ACCESS  read-only
    STATUS      current
    DESCRIPTION
        "Reflects the current probe count (1..10) for
        a remote traceroute operation. The maximum
        probe count is determined by
        zhoneTraceRouteCtlProbesPerHop."
    ::= { zhoneTraceRouteResultsEntry 3 }

 zhoneTraceRouteResultsIpTgtAddrType OBJECT-TYPE
    SYNTAX      InetAddressType
    MAX-ACCESS  read-only
    STATUS      current
    DESCRIPTION
        "This objects indicates the type of address stored
        in the corresponding zhoneTraceRouteResultsIpTgtAddr
        object."
    ::= { zhoneTraceRouteResultsEntry 4 }


 zhoneTraceRouteResultsIpTgtAddr OBJECT-TYPE
    SYNTAX      InetAddress
    MAX-ACCESS  read-only
    STATUS      current
    DESCRIPTION
        "This objects reports the IP address associated
        with a zhoneTraceRouteCtlTargetAddress value when the
        destination address is specified as a DNS name.
        The value of this object should be a zero length
        octet string when a DNS name is not specified or
        when a specified DNS name fails to resolve."
    ::= { zhoneTraceRouteResultsEntry 5 }

 zhoneTraceRouteResultsTestAttempts OBJECT-TYPE
    SYNTAX      Unsigned32
    UNITS       "tests"
    MAX-ACCESS  read-only
    STATUS      current
    DESCRIPTION
        "The current number of attempts to determine a path
        to a target.  The value of this object MUST be started
        at 0."
    ::= { zhoneTraceRouteResultsEntry 6 }

 zhoneTraceRouteResultsTestSuccesses OBJECT-TYPE
    SYNTAX      Unsigned32
    UNITS       "tests"
    MAX-ACCESS  read-only
    STATUS      current
    DESCRIPTION
        "The current number of attempts to determine a path
        to a target that have succeeded.  The value of this
        object MUST be reported as 0 when no attempts have
        succeeded."
    ::= { zhoneTraceRouteResultsEntry 7 }

 zhoneTraceRouteResultsLastGoodPath OBJECT-TYPE
    SYNTAX      DateAndTime
    MAX-ACCESS  read-only
    STATUS      current
    DESCRIPTION
        "The date and time when the last complete path
        was determined."
    ::= { zhoneTraceRouteResultsEntry 8 }


 -- Trace Route Probe History Table

 -- Traceroute Hop Results Table

 zhoneTraceRouteHopsTable OBJECT-TYPE
    SYNTAX      SEQUENCE OF ZhoneTraceRouteHopsEntry
    MAX-ACCESS  not-accessible
    STATUS      current
    DESCRIPTION
        "Defines the Remote Operations Traceroute Hop Table for
        keeping track of the results of traceroute tests on a
        per hop basis."
    ::= { zhoneTraceRouteObjects 5 }

 zhoneTraceRouteHopsEntry OBJECT-TYPE
    SYNTAX      ZhoneTraceRouteHopsEntry
    MAX-ACCESS  not-accessible
    STATUS      current
    DESCRIPTION
        "Defines an entry in the zhoneTraceRouteHopsTable.

        The first two index elements identify the
        zhoneTraceRouteCtlEntry that a zhoneTraceRouteHopsEntry
        belongs to.  The third index element,
        zhoneTraceRouteHopsHopIndex, selects a
        hop in a traceroute path."
    INDEX {
            zhoneTraceRouteCtlIndex,
            zhoneTraceRouteHopsHopIndex
          }
    ::= { zhoneTraceRouteHopsTable 1 }

 ZhoneTraceRouteHopsEntry ::=
    SEQUENCE {
        zhoneTraceRouteHopsHopIndex         Unsigned32,
        zhoneTraceRouteHopsIpTgtAddressType InetAddressType,
        zhoneTraceRouteHopsIpTgtAddress     InetAddress,
        zhoneTraceRouteHopsMinRtt           Unsigned32,
        zhoneTraceRouteHopsMaxRtt           Unsigned32,
        zhoneTraceRouteHopsAverageRtt       Unsigned32,
        zhoneTraceRouteHopsRttSumOfSquares  Unsigned32,
        zhoneTraceRouteHopsSentProbes       Unsigned32,
        zhoneTraceRouteHopsProbeResponses   Unsigned32,
        zhoneTraceRouteHopsLastGoodProbe    DateAndTime
      }


 zhoneTraceRouteHopsHopIndex OBJECT-TYPE
    SYNTAX      Unsigned32
    MAX-ACCESS  not-accessible
    STATUS      current
    DESCRIPTION
        "Specifies the hop index for a traceroute hop.  Values
        for this object with respect to the same
        zhoneTraceRouteCtlOwnerIndex and zhoneTraceRouteCtlTestName
        MUST start at 1 and increase monotonically.

        The zhoneTraceRouteHopsTable keeps the current traceroute
        path per zhoneTraceRouteCtlEntry if enabled by
        setting the corresponding zhoneTraceRouteCtlCreateHopsEntries
        to true(1).

        All hops (zhoneTraceRouteHopsTable entries) in a traceroute
        path MUST be updated at the same time when a traceroute
        operation completes.  Care needs to be applied when either
        a path changes or can't be determined.  The initial portion
        of the path, up to the first hop change, MUST retain the
        same zhoneTraceRouteHopsHopIndex values.  The remaining portion
        of the path SHOULD be assigned new zhoneTraceRouteHopsHopIndex
        values."
    ::= { zhoneTraceRouteHopsEntry 1 }

 zhoneTraceRouteHopsIpTgtAddressType OBJECT-TYPE
    SYNTAX      InetAddressType
    MAX-ACCESS  read-only
    STATUS      current
    DESCRIPTION
        "This objects indicates the type of address stored
        in the corresponding zhoneTraceRouteHopsIpTargetAddress
        object."
    ::= { zhoneTraceRouteHopsEntry 2 }


 zhoneTraceRouteHopsIpTgtAddress OBJECT-TYPE
    SYNTAX      InetAddress
    MAX-ACCESS  read-only
    STATUS      current
    DESCRIPTION
        "This object reports the IP address associated with
        the hop.  A value for this object should be reported
        as a numeric IP address and not as a DNS name."
    ::= { zhoneTraceRouteHopsEntry 3 }


 zhoneTraceRouteHopsMinRtt OBJECT-TYPE
    SYNTAX      Unsigned32
    MAX-ACCESS  read-only
    STATUS      current
    DESCRIPTION
        "The minimum traceroute round-trip-time (RTT) received for
        this hop.  A value of 0 for this object implies that no
        RTT has been received."
    ::= { zhoneTraceRouteHopsEntry 4 }


 zhoneTraceRouteHopsMaxRtt OBJECT-TYPE
    SYNTAX      Unsigned32
    MAX-ACCESS  read-only
    STATUS      current
    DESCRIPTION
        "The maximum traceroute round-trip-time (RTT) received for
        this hop.  A value of 0 for this object implies that no
        RTT has been received."
    ::= { zhoneTraceRouteHopsEntry 5 }


 zhoneTraceRouteHopsAverageRtt OBJECT-TYPE
    SYNTAX      Unsigned32
    MAX-ACCESS  read-only
    STATUS      current
    DESCRIPTION
        "The current average traceroute round-trip-time (RTT) for
        this hop."
    ::= { zhoneTraceRouteHopsEntry 6 }

 zhoneTraceRouteHopsRttSumOfSquares OBJECT-TYPE
    SYNTAX      Unsigned32
    MAX-ACCESS  read-only
    STATUS      current
    DESCRIPTION
        "This object contains the sum of all traceroute responses
        received for this hop.  Its purpose is to enable standard
        deviation calculation."
    ::= { zhoneTraceRouteHopsEntry 7 }


 zhoneTraceRouteHopsSentProbes OBJECT-TYPE
    SYNTAX      Unsigned32
    MAX-ACCESS  read-only
    STATUS      current
    DESCRIPTION
        "The value of this object reflects the number of probes sent
        for this hop during this traceroute test.  The value of this
        object should start at 0."
    ::= { zhoneTraceRouteHopsEntry 8 }


 zhoneTraceRouteHopsProbeResponses OBJECT-TYPE
    SYNTAX      Unsigned32
    MAX-ACCESS  read-only
    STATUS      current
    DESCRIPTION
        "Number of responses received for this hop during this
        traceroute test.  This value of this object should start
        at 0."
    ::= { zhoneTraceRouteHopsEntry 9 }

 zhoneTraceRouteHopsLastGoodProbe OBJECT-TYPE
    SYNTAX      DateAndTime
    MAX-ACCESS  read-only
    STATUS      current
    DESCRIPTION
        "Date and time was the last response was received for a probe
        for this hop during this traceroute test."
    ::= { zhoneTraceRouteHopsEntry 10 }

 -- Notification Definition section

 zhoneTraceRoutePathChange NOTIFICATION-TYPE
      OBJECTS {
        zhoneTraceRouteResultsIpTgtAddr
      }
      STATUS  current
      DESCRIPTION
          "The path to a target has changed."
      ::= { zhoneTraceRouteNotifications 1 }

 zhoneTraceRouteTestFailed NOTIFICATION-TYPE
      OBJECTS {
        zhoneTraceRouteResultsIpTgtAddr
      }
      STATUS  current
      DESCRIPTION
          "Could not determine the path to a target."
      ::= { zhoneTraceRouteNotifications 2 }

 zhoneTraceRouteTestCompleted NOTIFICATION-TYPE
      OBJECTS {
        zhoneTraceRouteResultsIpTgtAddr
      }
      STATUS  current
      DESCRIPTION
          "The path to a target has just been determined."
      ::= { zhoneTraceRouteNotifications 3 }

 -- Conformance information
 -- Compliance statements

zhoneTraceRouteGroups      OBJECT IDENTIFIER ::= { zhoneTraceRouteConformance 1 }

  -- MIB groupings

 zhoneTraceRouteGroup OBJECT-GROUP
   OBJECTS {
             zhoneTraceRouteMaxConcurrentRequests,
             zhoneTraceRouteCtlTargetAddressType,
             zhoneTraceRouteCtlTargetAddress,
             zhoneTraceRouteCtlByPassRouteTable,
             zhoneTraceRouteCtlDataSize,
             zhoneTraceRouteCtlTimeOut,
             zhoneTraceRouteCtlProbesPerHop,
             zhoneTraceRouteCtlPort,
             zhoneTraceRouteCtlMaxTtl,
             zhoneTraceRouteCtlDSField,
             zhoneTraceRouteCtlSourceAddressType,
             zhoneTraceRouteCtlSourceAddress,
             zhoneTraceRouteCtlIfIndex,
             zhoneTraceRouteCtlMiscOptions,
             zhoneTraceRouteCtlMaxFailures,
             zhoneTraceRouteCtlDontFragment,
             zhoneTraceRouteCtlInitialTtl,
             zhoneTraceRouteCtlFrequency,
             zhoneTraceRouteCtlStorageType,
             zhoneTraceRouteCtlAdminStatus,
             zhoneTraceRouteCtlMaxRows,
             zhoneTraceRouteCtlTrapGeneration,
             zhoneTraceRouteCtlDescr,
             zhoneTraceRouteCtlCreateHopsEntries,
             zhoneTraceRouteCtlType,
             zhoneTraceRouteCtlRowStatus,
             zhoneTraceRouteResultsOperStatus,
             zhoneTraceRouteResultsCurHopCount,
             zhoneTraceRouteResultsCurProbeCount,
             zhoneTraceRouteResultsIpTgtAddrType,
             zhoneTraceRouteResultsIpTgtAddr,
             zhoneTraceRouteResultsTestAttempts,
             zhoneTraceRouteResultsTestSuccesses
          }
   STATUS  current
   DESCRIPTION
       "The group of objects that comprise the remote traceroute
       operation."
   ::= { zhoneTraceRouteGroups 1 }

 zhoneTraceRouteTimeStampGroup OBJECT-GROUP
   OBJECTS {
             zhoneTraceRouteResultsLastGoodPath
           }
   STATUS  current
   DESCRIPTION
       "The group of DateAndTime objects."
    ::= { zhoneTraceRouteGroups 2 }

 zhoneTraceRouteNotificationsGroup NOTIFICATION-GROUP
   NOTIFICATIONS {
             zhoneTraceRoutePathChange,
             zhoneTraceRouteTestFailed,
             zhoneTraceRouteTestCompleted
          }
   STATUS   current
   DESCRIPTION
       "The notifications which are required to be supported by
       implementations of this MIB."
   ::= { zhoneTraceRouteGroups 3 }

 zhoneTraceRouteHopsTableGroup OBJECT-GROUP
   OBJECTS {
             zhoneTraceRouteHopsIpTgtAddressType,
             zhoneTraceRouteHopsIpTgtAddress,
             zhoneTraceRouteHopsMinRtt,
             zhoneTraceRouteHopsMaxRtt,
             zhoneTraceRouteHopsAverageRtt,
             zhoneTraceRouteHopsRttSumOfSquares,
             zhoneTraceRouteHopsSentProbes,
             zhoneTraceRouteHopsProbeResponses,
             zhoneTraceRouteHopsLastGoodProbe
           }
    STATUS   current
    DESCRIPTION
        "The group of objects that comprise the zhoneTraceRouteHopsTable."
  ::= { zhoneTraceRouteGroups 4 }

END
