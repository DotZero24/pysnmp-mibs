--
-- comIpRoute.mib
-- MIB generated by MG-SOFT Visual MIB Builder Version 2.0 Build 187
-- Monday, September 11, 2000 at 16:34:22
--

	ZHONE-COM-IP-ROUTE-MIB DEFINITIONS ::= BEGIN

		IMPORTS
			InterfaceIndexOrZero
				FROM IF-MIB
			IpAddress, Integer32, Unsigned32, Gauge32, OBJECT-TYPE,
			MODULE-IDENTITY, OBJECT-IDENTITY
				FROM SNMPv2-SMI
			rdEntry, rdIndex
				FROM ZHONE-COM-IP-RD-MIB
			zhoneIp, zhoneModules
				FROM Zhone;


		comIpRoute MODULE-IDENTITY
			LAST-UPDATED "200009111700Z"
			ORGANIZATION
				"Zhone Technologies, Inc."
			CONTACT-INFO
				"  Postal:
				           Zhone Technologies, Inc.
				           @ Zhone Way
				           7001 Oakport Street
				           Oakland, CA  94621
				           USA
				Toll-Free: +1 877-ZHONE20 (+1 877-946-6320)
				      Tel: +1-510-777-7000
				      Fax: +1-510-777-7001
				   E-mail: support@zhone.com

				"
			DESCRIPTION
				"Zhone CIDR Route MIB Module.
				IP Software
				Minneapolis, MN"
			REVISION "200009111633Z"
			DESCRIPTION
				"V01.00.00 - Initial Release"
			::= { zhoneModules 57 }



--
-- Node definitions
--

		route OBJECT-IDENTITY
			STATUS current
			DESCRIPTION
				"CIDR Routing Table information based on RFC 2096.
				Modified to incorporate routing domains."
			::= { zhoneIp 7 }

		zhoneRouteInfoTable OBJECT-TYPE
			SYNTAX SEQUENCE OF ZhoneRouteInfoEntry
			MAX-ACCESS not-accessible
			STATUS current
			DESCRIPTION
				"Table of scalar objects from RFC 2096 that now need to be indexed
				by routing domain.  This table augments the rdTable from
				ZHONE-COM-IP-RD-MIB."
			::= { route 1 }

		zhoneRouteInfoEntry OBJECT-TYPE
			SYNTAX ZhoneRouteInfoEntry
			MAX-ACCESS not-accessible
			STATUS current
			DESCRIPTION
				"Set of general routing information for one routing domain."
			AUGMENTS { rdEntry }
			::= { zhoneRouteInfoTable 1 }

		ZhoneRouteInfoEntry ::=
			SEQUENCE {
				zhIpCidrRouteNumber
					Gauge32
			 }

		zhIpCidrRouteNumber OBJECT-TYPE
			SYNTAX Gauge32
			MAX-ACCESS read-only
			STATUS current
			DESCRIPTION
				"The number of current ipCidrRouteTable entries
				in this routing domain that are not invalid."
			REFERENCE
				"See RFC 2096:  ipCidrRouteNumber"
			::= { zhoneRouteInfoEntry 1 }

		zhoneIpCidrRouteTable OBJECT-TYPE
			SYNTAX SEQUENCE OF ZhoneIpCidrRouteEntry
			MAX-ACCESS not-accessible
			STATUS current
			DESCRIPTION
				"This entity's IP Routing table for each routing domain."
			::= { route 3 }

		zhoneIpCidrRouteEntry OBJECT-TYPE
			SYNTAX ZhoneIpCidrRouteEntry
			MAX-ACCESS not-accessible
			STATUS current
			DESCRIPTION
				"A particular route to  a  particular  destina-
				tion, under a particular policy.  There is a separate routing
				table for each routing domain.  Rows can be added or removed
				using the zhIpCidrRouteStatus object.  The minimum columns required
				to create new entry are zhIpCidrRouteDest, zhIpCidrRouteMask,
				zhIpCidrRouteNextHop, zhIpCidrRouteType, and zhIpCidrRouteInfo."
			INDEX { rdIndex, zhIpCidrRouteDest, zhIpCidrRouteMask, zhIpCidrRouteNextHop }
			::= { zhoneIpCidrRouteTable 1 }

		ZhoneIpCidrRouteEntry ::=
			SEQUENCE {
				zhIpCidrRouteDest
					IpAddress,
				zhIpCidrRouteMask
					IpAddress,
				zhIpCidrRouteNextHop
					IpAddress,
				zhIpCidrRouteIfIndex
					InterfaceIndexOrZero,
				zhIpCidrRouteType
					INTEGER,
				zhIpCidrRouteProto
					INTEGER,
				zhIpCidrRouteAge
					Unsigned32,
				zhIpCidrRouteInfo
					OBJECT IDENTIFIER,
				zhIpCidrRouteNextHopAS
					Integer32,
				zhIpCidrRouteMetric1
					Integer32,
				zhIpCidrRouteMetric2
					Integer32,
				zhIpCidrRouteMetric3
					Integer32,
				zhIpCidrRouteMetric4
					Integer32,
				zhIpCidrRouteMetric5
					Integer32
			 }

		zhIpCidrRouteDest OBJECT-TYPE
			SYNTAX IpAddress
			MAX-ACCESS not-accessible
			STATUS current
			DESCRIPTION
				"The destination IP address of this route.

				This object may not take a Multicast (Class  D)
				address value.

				Any assignment (implicit or  otherwise)  of  an
				instance  of  this  object to a value x must be
				rejected if the bitwise logical-AND of  x  with
				the  value of the corresponding instance of the
				ipCidrRouteMask object is not equal to x."
			REFERENCE
				"See RFC 2096:  ipCidrRouteTable.ipCidrRouteEntry.ipCidrRouteDest"
			::= { zhoneIpCidrRouteEntry 1 }

		zhIpCidrRouteMask OBJECT-TYPE
			SYNTAX IpAddress
			MAX-ACCESS not-accessible
			STATUS current
			DESCRIPTION
				"Indicate the mask to be logical-ANDed with the
				destination  address  before  being compared to
				the value  in  the  ipCidrRouteDest  field.   For
				those  systems  that  do  not support arbitrary
				subnet masks, an agent constructs the value  of
				the  ipCidrRouteMask  by  reference to the IP Ad-
				dress Class.

				Any assignment (implicit or  otherwise)  of  an
				instance  of  this  object to a value x must be
				rejected if the bitwise logical-AND of  x  with
				the  value of the corresponding instance of the
				ipCidrRouteDest object is not equal to ipCidrRoute-
				Dest."
			REFERENCE
				"See RFC 2096:  ipCidrRouteTable.ipCidrRouteEntry.ipCidrRouteMask"
			::= { zhoneIpCidrRouteEntry 2 }

		zhIpCidrRouteNextHop OBJECT-TYPE
			SYNTAX IpAddress
			MAX-ACCESS not-accessible
			STATUS current
			DESCRIPTION
				"On remote routes, the address of the next sys-
				tem en route; Otherwise, 0.0.0.0."
			REFERENCE
				"See RFC 2096:  ipCidrRouteTable.ipCidrRouteEntry.ipCidrRouteNextHop"
			::= { zhoneIpCidrRouteEntry 3 }

		zhIpCidrRouteIfIndex OBJECT-TYPE
			SYNTAX InterfaceIndexOrZero
			MAX-ACCESS read-write
			STATUS current
			DESCRIPTION
				"The ifIndex value which identifies  the  local
				interface  through  which  the next hop of this
				route should be reached.  A value of 0 means there
				is no next hop interface."
			REFERENCE
				"See RFC 2096:  ipCidrRouteTable.ipCidrRouteEntry.ipCidrRouteIfIndex"
			::= { zhoneIpCidrRouteEntry 4 }

		zhIpCidrRouteType OBJECT-TYPE
			SYNTAX INTEGER
				{
				other(1),
				reject(2),
				local(3),
				remote(4)
				}
			MAX-ACCESS read-write
			STATUS current
			DESCRIPTION
				"The type of route.  Note that local(3)  refers
				to  a route for which the next hop is the final
				destination; remote(4) refers to  a  route  for
				which  the  next  hop is not the final destina-
				tion.

				Routes which do not result in traffic forwarding or
				rejection should not be displayed even if the
				implementation keeps them stored internally.


				reject (2) refers to a route which, if matched, discards
				the message as unreachable. This is used in some
				protocols as a means of correctly aggregating routes."
			REFERENCE
				"See RFC 2096:  ipCidrRouteTable.ipCidrRouteEntry.ipCidrRouteType"
			::= { zhoneIpCidrRouteEntry 5 }

		zhIpCidrRouteProto OBJECT-TYPE
			SYNTAX INTEGER
				{
				other(1),
				local(2),
				netmgmt(3),
				icmp(4),
				rip(8),
				isIs(9),
				ospf(13),
				bgp(14),
				idpr(15)
				}
			MAX-ACCESS read-only
			STATUS current
			DESCRIPTION
				"The routing mechanism via which this route was
				learned.  Inclusion of values for gateway rout-
				ing protocols is not  intended  to  imply  that
				hosts should support those protocols.

				other     -- not specified
				local     -- local interface
				netmgmt   -- static route
				icmp      -- result of ICMP Redirect

				The following are all dynamic routing protocols

				rip       -- Berkeley RIP or RIP-II
				isIs      -- Dual IS-IS
				ospf      -- Open Shortest Path First
				bgp       -- Border Gateway Protocol
				idpr      -- InterDomain Policy Routing
				"
			REFERENCE
				"See RFC 2096:  ipCidrRouteTable.ipCidrRouteEntry.ipCidrRouteProto"
			::= { zhoneIpCidrRouteEntry 6 }

		zhIpCidrRouteAge OBJECT-TYPE
			SYNTAX Unsigned32
			UNITS "seconds"
			MAX-ACCESS read-only
			STATUS current
			DESCRIPTION
				"The number of seconds  since  this  route  was
				last  updated  or  otherwise  determined  to be
				correct.  Note that no semantics of  `too  old'
				can  be implied except through knowledge of the
				routing  protocol  by  which  the   route   was
				learned."
			REFERENCE
				"See RFC 2096:  ipCidrRouteTable.ipCidrRouteEntry.ipCidrRouteAge"
			::= { zhoneIpCidrRouteEntry 7 }

		zhIpCidrRouteInfo OBJECT-TYPE
			SYNTAX OBJECT IDENTIFIER
			MAX-ACCESS read-write
			STATUS current
			DESCRIPTION
				"A reference to MIB definitions specific to the
				particular  routing protocol which is responsi-
				ble for this route, as determined by the  value
				specified  in the route's ipCidrRouteProto value.
				If this information is not present,  its  value
				should be set to the OBJECT IDENTIFIER { 0 0 },
				which is a syntactically valid object  identif-
				ier, and any implementation conforming to ASN.1
				and the Basic Encoding Rules must  be  able  to
				generate and recognize this value."
			REFERENCE
				"See RFC 2096:  ipCidrRouteTable.ipCidrRouteEntry.ipCidrRouteInfo"
			DEFVAL { {0 0} }
			::= { zhoneIpCidrRouteEntry 8 }

		zhIpCidrRouteNextHopAS OBJECT-TYPE
			SYNTAX Integer32
			MAX-ACCESS read-write
			STATUS current
			DESCRIPTION
				"The Autonomous System Number of the Next  Hop.
				The  semantics of this object are determined by
				the routing-protocol specified in  the  route's
				ipCidrRouteProto  value. When  this object is
				unknown or not relevant its value should be set
				to zero."
			REFERENCE
				"See RFC 2096:  ipCidrRouteTable.ipCidrRouteEntry.ipCidrRouteNextHopAS"
			DEFVAL { 0 }
			::= { zhoneIpCidrRouteEntry 9 }

		zhIpCidrRouteMetric1 OBJECT-TYPE
			SYNTAX Integer32
			MAX-ACCESS read-write
			STATUS current
			DESCRIPTION
				"The primary routing  metric  for  this  route.
				The  semantics of this metric are determined by
				the routing-protocol specified in  the  route's
				ipCidrRouteProto  value.   If  this metric is not
				used, its value should be set to -1."
			REFERENCE
				"See RFC 2096:  ipCidrRouteTable.ipCidrRouteEntry.ipCidrRouteMetric1"
			DEFVAL { -1 }
			::= { zhoneIpCidrRouteEntry 10 }

		zhIpCidrRouteMetric2 OBJECT-TYPE
			SYNTAX Integer32
			MAX-ACCESS read-write
			STATUS current
			DESCRIPTION
				"An alternate routing metric  for  this  route.
				The  semantics of this metric are determined by
				the routing-protocol specified in  the  route's
				ipCidrRouteProto  value.   If  this metric is not
				used, its value should be set to -1."
			REFERENCE
				"See RFC 2096:  ipCidrRouteTable.ipCidrRouteEntry.ipCidrRouteMetric2"
			DEFVAL { -1 }
			::= { zhoneIpCidrRouteEntry 11 }

		zhIpCidrRouteMetric3 OBJECT-TYPE
			SYNTAX Integer32
			MAX-ACCESS read-write
			STATUS current
			DESCRIPTION
				"An alternate routing metric  for  this  route.
				The  semantics of this metric are determined by
				the routing-protocol specified in  the  route's
				ipCidrRouteProto  value.   If  this metric is not
				used, its value should be set to -1."
			REFERENCE
				"See RFC 2096:  ipCidrRouteTable.ipCidrRouteEntry.ipCidrRouteMetric3"
			DEFVAL { -1 }
			::= { zhoneIpCidrRouteEntry 12 }

		zhIpCidrRouteMetric4 OBJECT-TYPE
			SYNTAX Integer32
			MAX-ACCESS read-write
			STATUS current
			DESCRIPTION
				"An alternate routing metric  for  this  route.
				The  semantics of this metric are determined by
				the routing-protocol specified in  the  route's
				ipCidrRouteProto  value.   If  this metric is not
				used, its value should be set to -1."
			REFERENCE
				"See RFC 2096:  ipCidrRouteTable.ipCidrRouteEntry.ipCidrRouteMetric4"
			DEFVAL { -1 }
			::= { zhoneIpCidrRouteEntry 13 }

		zhIpCidrRouteMetric5 OBJECT-TYPE
			SYNTAX Integer32
			MAX-ACCESS read-write
			STATUS current
			DESCRIPTION
				"An alternate routing metric  for  this  route.
				The  semantics of this metric are determined by
				the routing-protocol specified in  the  route's
				ipCidrRouteProto  value.   If  this metric is not
				used, its value should be set to -1."
			REFERENCE
				"See RFC 2096:  ipCidrRouteTable.ipCidrRouteEntry.ipCidrRouteMetric5"
			DEFVAL { -1 }
			::= { zhoneIpCidrRouteEntry 14 }


	END

--
-- comIpRoute.mib
--
