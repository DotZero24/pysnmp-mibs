--
-- phyIsdn.mib
-- MIB generated by MG-SOFT Visual MIB Builder Version 3.0 Build 271
-- Monday, March 03, 2003 at 12:00:28
--

	ZHONE-ISDN-MIB DEFINITIONS ::= BEGIN

		IMPORTS
			ifIndex
				FROM IF-MIB
			PerfCurrentCount, PerfIntervalCount, PerfTotalCount
				FROM PerfHist-TC-MIB
			TimeTicks, Integer32, Unsigned32, OBJECT-TYPE, MODULE-IDENTITY,
			OBJECT-IDENTITY, NOTIFICATION-TYPE
				FROM SNMPv2-SMI
			zhoneTrapModules, zhonePhysical
				FROM Zhone;


--
--
--
--
--
--
--
--
		zhoneIsdn MODULE-IDENTITY
			LAST-UPDATED "200303031944Z"		-- March 03, 2003 at 19:44 GMT
			ORGANIZATION
				"Zhone Technologies."
			CONTACT-INFO
				"   Postal:
				           Zhone Technologies, Inc.
				           @ Zhone Way
				           7001 Oakport Street
				           Oakland, CA  94621
				           USA
				Toll-Free: +1 877-ZHONE20 (+1 877-946-6320)
				      Tel: +1-510-777-7000
				      Fax: +1-510-777-7001
				   E-mail: support@zhone.com"
			DESCRIPTION
				"ISDN BRI S/T Interface MIB module.
				This MIB manages the ISDN BRI S/T
				Interface on Zedge ."
			REVISION "200303031158Z"		-- March 03, 2003 at 11:58 GMT
			DESCRIPTION
				"V01.00.03 - Add/modified loopback types."
			REVISION "200302041804Z"		-- February 04, 2003 at 18:04 GMT
			DESCRIPTION
				"V01.00.02 - Add additional loopback
				types and added line-power for
				Malc ULC."
			REVISION "200009271057Z"		-- September 27, 2000 at 10:57 GMT
			DESCRIPTION
				"V01.00.00 Initial Release"
			REVISION "200009271942Z"		-- September 27, 2000 at 19:42 GMT
			DESCRIPTION
				"V01.00.01 Corrected DDL markup"
			::= { zhonePhysical 7 }



--
-- Node definitions
--

		-- 1.3.6.1.4.1.5504.3.8.3
		zhoneIsdnTrap OBJECT-IDENTITY
			STATUS current
			DESCRIPTION
				" Trap for zedge to be sent to ZMS for far end code violation."
			::= { zhoneTrapModules 3 }

		-- 1.3.6.1.4.1.5504.3.8.3.1
		isdnMibV2Traps OBJECT-IDENTITY
			STATUS current
			DESCRIPTION
				"This object identity adds a zero(0) for the next to last
				sub-identifier which should be used for new SNMPv2 Traps."
			::= { zhoneIsdnTrap 1 }

		-- 1.3.6.1.4.1.5504.3.8.3.1.1
		isdnTrapFrameSynchLoss NOTIFICATION-TYPE
			OBJECTS { ifIndex }
			STATUS current
			DESCRIPTION
				"When the driver receives three successive out of synch frames
				then it will set the frame synch loss bit to true and then the
				application will send a trap to the NMS. After this when the driver
				detects 5 good frames then it will set the  frame synch lossbit to false."
			::= { isdnMibV2Traps 1 }

		-- 1.3.6.1.4.1.5504.3.8.3.1.2
		isdnTrapFECV NOTIFICATION-TYPE
			OBJECTS { ifIndex }
			STATUS current
			DESCRIPTION
				"Far end code violation Trap"
			::= { isdnMibV2Traps 2 }

		-- 1.3.6.1.4.1.5504.3.8.3.1.3
		isdnTrapAmiViolations NOTIFICATION-TYPE
			OBJECTS { ifIndex }
			STATUS current
			DESCRIPTION
				"Bad Ami violation Trap. If number of ami violation crosses
				the isdnThresholdAmiViolations   then the application will send this to NMS."
			::= { isdnMibV2Traps 3 }

		-- 1.3.6.1.4.1.5504.3.8.3.1.4
		isdnTrapUnbalancedFrame NOTIFICATION-TYPE
			STATUS current
			DESCRIPTION
				"This trap will be sent to NMS after the isdnThresholdUnbalancedFrame
				value is crossed.
				"
			::= { isdnMibV2Traps 4 }

--
--  Overview of ISDN BRI with  S/T interface MIB
--
-- The ISDN BRI with S/T interface MIB provides the static
-- configuration and operational status information on Zhone's ISDN
--  BRI S/T interface implementation. The following entities
-- are managed:
-- 1) The  S/T ports
--    the ports are connected to  ISDN terminal  devices
--    for voice, fax, and  data communication.
--
--  The  S/T ports are identified by ISDN shelf/slot/port
--  (which will be mapped to unique ifIndex) number
--
--
--
--  This mib prvides configuration, status and performance parameters
--  used/provided by Zhone implementation of ISDN S/T interfaces.
--
--
--
		-- 1.3.6.1.4.1.5504.5.7.1
		zhoneIsdnMib OBJECT IDENTIFIER ::= { zhoneIsdn 1 }

--
-- ****************************************************************************
--  The ISDN BRI integrated S/T Interface  Configuration Table
-- ****************************************************************************
		-- 1.3.6.1.4.1.5504.5.7.1.1
		isdnConfigTable OBJECT-TYPE
			SYNTAX SEQUENCE OF IsdnConfigEntry
			MAX-ACCESS not-accessible
			STATUS current
			DESCRIPTION
				"The ISDN BRI integrated S/T Interface  Configuration Table.
				This table is indexed by IfIndex.It is created by aplication when the system comes up
				with default values.
				"
			::= { zhoneIsdnMib 1 }

		-- 1.3.6.1.4.1.5504.5.7.1.1.1
		isdnConfigEntry OBJECT-TYPE
			SYNTAX IsdnConfigEntry
			MAX-ACCESS not-accessible
			STATUS current
			DESCRIPTION
				"An entry in the ISDN config table for each S/T Interface. "
			INDEX { ifIndex }
			::= { isdnConfigTable 1 }

		IsdnConfigEntry ::=
			SEQUENCE {
				isdnLineTermClass
					INTEGER,
				isdnActivationTimer2
					INTEGER,
				isdnLineLoopBack
					INTEGER,
				isdnLinePower
					INTEGER
			 }

		-- 1.3.6.1.4.1.5504.5.7.1.1.1.1
		isdnLineTermClass OBJECT-TYPE
			SYNTAX INTEGER
				{
				class1(1),
				class2(2)
				}
			MAX-ACCESS read-write
			STATUS current
			DESCRIPTION
				"NT Terminal Mode.clas1 and class2  operations are as per CCITT I.430,
				ETSI ETS 300012, and ANSI T1.605 .These specification mandate two classes
				 of operation for a TE with respect to D channel operation
				class1 : class1 is the higher class , used for signalling information
				class2 : This is the lower class.

				The default value is class1.
				"
			::= { isdnConfigEntry 1 }

		-- 1.3.6.1.4.1.5504.5.7.1.1.1.2
		isdnActivationTimer2 OBJECT-TYPE
			SYNTAX INTEGER
				{
				t2-50ms(1),
				t2-100ms(2)
				}
			MAX-ACCESS read-write
			STATUS current
			DESCRIPTION
				"Value of Activation Timer #2.
				t2-50ms(1): select  50ms for timer #2
				t2-100ms(2): select  1000ms for timer #2

				The default value is t2-50ms"
			::= { isdnConfigEntry 2 }

		-- 1.3.6.1.4.1.5504.5.7.1.1.1.3
		isdnLineLoopBack OBJECT-TYPE
			SYNTAX INTEGER
				{
				loop-back-none(1),
				loop-back-b1-st-tr(2),
				loop-back-b1-st-nt(3),
				loop-back-b2-st-tr(4),
				loop-back-b2-st-nt(5),
				loop-back-b1-idl2-tr(6),
				loop-back-b1-idl2-nt(7),
				loop-back-b2-idl2-tr(8),
				loop-back-b2-idl2-nt(9),
				loop-back-2bd-idl2-tr(10),
				loop-back-2bd-idl2-nt(11),
				loop-back-2bd-u-interface-tr(12),
				loop-back-2bd-u-interface-nt(13),
				loop-back-2bd-external-analog(14)
				}
			MAX-ACCESS read-write
			STATUS current
			DESCRIPTION
				"loop-back-none(1) :no loop back .

				loop-back-b1-st-tr(2): transparaent loopback on the S/T interface towards the user(B1 chanel).

				loop-back-b1-st-nt(3): non-transparent loopback onthe S/T interface towards the user(B1 chanel)..

				loop-back-b2-st-tr(4) :transparaent loopback on the S/T interface towards the user(B2 chanel).

				loop-back-b2-st-nt(5):non-transparent loopback on the S/T interface towards the user(B2 channel)

				loop-back-b1-idl2-tr(6):transparaent loopback on the IDL2 interface towards the system(B1 channel)

				loop-back-b1-idl2-nt(7):non-transparent loopback on the  IDL2 interface towards the system(B1 channel)

				loop-back-b2-idl2-tr(8):transparaent loopback on the IDL2 interface towards the system(B2 channel)

				loop-back-b2-idl2-nt(9): non-transparent loopback on the  IDL2 interface towards the system(B2 channel)

				loop-back-2bd-idl2-tr(10): transparent loopback on the IDL2 towards the system(2B + D channel)

				loop-back-2bd-idl2-nt(11): non-transparent loopback on the IDL2 towards the system(2B + D channel)

				loop-back-2bd-u-interface-tr (12): transparent loopback on the U interface towards the user(2B + D channel)

				loop-back-2bd-u-interface-nt (13): non-transparent loopback on the U interface(2B + D channel)

				loop-back-2bd-external-analog(14): loopback on the external analog interface towards the user(2B + D channel)


				st is loopback on the S/T interface towards the user.
				idl2 is loopback on the IDL2 interface towards the system.
				tr is transparent loopback.
				nt is non-transparent loopback.

				The default value is loop-back-none."
			::= { isdnConfigEntry 3 }

		-- 1.3.6.1.4.1.5504.5.7.1.1.1.4
		isdnLinePower OBJECT-TYPE
			SYNTAX INTEGER
				{
				off(1),
				sealing(2),
				powering(3)
				}
			MAX-ACCESS read-write
			STATUS current
			DESCRIPTION
				"State of the line power.

				off - no power on line.
				sealing - minimum current on line to preclude corrosion.
				powering - full current on line."
			::= { isdnConfigEntry 4 }

		-- 1.3.6.1.4.1.5504.5.7.1.2
		isdnPerfDataCurrentTable OBJECT-TYPE
			SYNTAX SEQUENCE OF IsdnPerfDataCurrentEntry
			MAX-ACCESS not-accessible
			STATUS current
			DESCRIPTION
				"The ISDN BRI S/T interface performance table which contains
				the performance data for curent 15 minutes.
				It contains information about the status of the ISDN S/T interface,
				including the error statistics."
			::= { zhoneIsdnMib 2 }

		-- 1.3.6.1.4.1.5504.5.7.1.2.1
		isdnPerfDataCurrentEntry OBJECT-TYPE
			SYNTAX IsdnPerfDataCurrentEntry
			MAX-ACCESS not-accessible
			STATUS current
			DESCRIPTION
				"An entry in current performance table for each  ISDN BRI
				S/T interface for last 15 minutes."
			AUGMENTS { isdnConfigEntry }
			::= { isdnPerfDataCurrentTable 1 }

		IsdnPerfDataCurrentEntry ::=
			SEQUENCE {
				isdnPerfCurBadAmiViolation
					PerfCurrentCount,
				isdnPerfCurUnbalancedFrame
					PerfCurrentCount,
				isdnPerCurErrorSeconds
					PerfCurrentCount,
				isdnPerCurFsyncSeconds
					PerfCurrentCount,
				isdnPerfCurTimeElapsed
					TimeTicks
			 }

		-- 1.3.6.1.4.1.5504.5.7.1.2.1.1
		isdnPerfCurBadAmiViolation OBJECT-TYPE
			SYNTAX PerfCurrentCount
			MAX-ACCESS read-only
			STATUS current
			DESCRIPTION
				"Current count of frames with incorrect number of AMI violations."
			::= { isdnPerfDataCurrentEntry 1 }

		-- 1.3.6.1.4.1.5504.5.7.1.2.1.2
		isdnPerfCurUnbalancedFrame OBJECT-TYPE
			SYNTAX PerfCurrentCount
			MAX-ACCESS read-only
			STATUS current
			DESCRIPTION
				"Current count of unbalanced frames."
			::= { isdnPerfDataCurrentEntry 2 }

		-- 1.3.6.1.4.1.5504.5.7.1.2.1.3
		isdnPerCurErrorSeconds OBJECT-TYPE
			SYNTAX PerfCurrentCount
			UNITS "seconds"
			MAX-ACCESS read-only
			STATUS current
			DESCRIPTION
				"Curent ISDN Activation error seconds.
				"
			::= { isdnPerfDataCurrentEntry 3 }

		-- 1.3.6.1.4.1.5504.5.7.1.2.1.4
		isdnPerCurFsyncSeconds OBJECT-TYPE
			SYNTAX PerfCurrentCount
			UNITS "seconds"
			MAX-ACCESS read-only
			STATUS current
			DESCRIPTION
				"Currents Frame synch loss seconds ."
			::= { isdnPerfDataCurrentEntry 4 }

		-- 1.3.6.1.4.1.5504.5.7.1.2.1.5
		isdnPerfCurTimeElapsed OBJECT-TYPE
			SYNTAX TimeTicks
			MAX-ACCESS read-only
			STATUS current
			DESCRIPTION
				"In the current 15 Min period number of seconds elapsed that
				these counts represent."
			::= { isdnPerfDataCurrentEntry 5 }

		-- 1.3.6.1.4.1.5504.5.7.1.3
		isdnPerfDataPreviousTable OBJECT-TYPE
			SYNTAX SEQUENCE OF IsdnPerfDataPreviousEntry
			MAX-ACCESS not-accessible
			STATUS current
			DESCRIPTION
				"The ISDN BRI S/T interface performance table,
				it contains statistics and information about
				the status of the ISDN S/T interface,
				including the error statistics for previous 15 minutes.
				"
			::= { zhoneIsdnMib 3 }

		-- 1.3.6.1.4.1.5504.5.7.1.3.1
		isdnPerfDataPreviousEntry OBJECT-TYPE
			SYNTAX IsdnPerfDataPreviousEntry
			MAX-ACCESS not-accessible
			STATUS current
			DESCRIPTION
				"An entry in Previous performance table(for last 15 minutes before
				the current performance period) for each S/T interface."
			AUGMENTS { isdnConfigEntry }
			::= { isdnPerfDataPreviousTable 1 }

		IsdnPerfDataPreviousEntry ::=
			SEQUENCE {
				isdnPerfPrevBadAmiViolation
					PerfIntervalCount,
				isdnPerfPrevUnbalancedFrame
					PerfIntervalCount,
				isdnPerPrevFsyncSeconds
					PerfIntervalCount,
				isdnPerfPrevErrorSeconds
					PerfIntervalCount
			 }

		-- 1.3.6.1.4.1.5504.5.7.1.3.1.1
		isdnPerfPrevBadAmiViolation OBJECT-TYPE
			SYNTAX PerfIntervalCount
			MAX-ACCESS read-only
			STATUS current
			DESCRIPTION
				"count of frames with incorrect number of AMI violations
				in previous 15 minutes."
			::= { isdnPerfDataPreviousEntry 1 }

		-- 1.3.6.1.4.1.5504.5.7.1.3.1.2
		isdnPerfPrevUnbalancedFrame OBJECT-TYPE
			SYNTAX PerfIntervalCount
			MAX-ACCESS read-only
			STATUS current
			DESCRIPTION
				"In previous 15 minutes ,count of unbalanced frames."
			::= { isdnPerfDataPreviousEntry 2 }

		-- 1.3.6.1.4.1.5504.5.7.1.3.1.3
		isdnPerPrevFsyncSeconds OBJECT-TYPE
			SYNTAX PerfIntervalCount
			UNITS "seconds"
			MAX-ACCESS read-only
			STATUS current
			DESCRIPTION
				" Frame synch error seconds in previous 15 minues."
			::= { isdnPerfDataPreviousEntry 3 }

		-- 1.3.6.1.4.1.5504.5.7.1.3.1.4
		isdnPerfPrevErrorSeconds OBJECT-TYPE
			SYNTAX PerfIntervalCount
			UNITS "seconds"
			MAX-ACCESS read-only
			STATUS current
			DESCRIPTION
				"In previous 15 minutes ISDN Activation error seconds"
			::= { isdnPerfDataPreviousEntry 4 }

		-- 1.3.6.1.4.1.5504.5.7.1.4
		isdnPerfDataTotalTable OBJECT-TYPE
			SYNTAX SEQUENCE OF IsdnPerfDataTotalEntry
			MAX-ACCESS not-accessible
			STATUS current
			DESCRIPTION
				"The ISDN BRI S/T interface performance table,
				it contains statistics and information about
				the status of the ISDN S/T interface,
				including the error statistics for up to the
				the last 24 hours.  This is maintained in 15
				minute intervals NOT including the current
				interval being accumulated. When the current period
				reaches 15 minutes, it's counts are rolled into the
				previous entry and added to these values. The 97th entry,
				previous to the 24 hour period is no longer included in
				these counts."
			::= { zhoneIsdnMib 4 }

		-- 1.3.6.1.4.1.5504.5.7.1.4.1
		isdnPerfDataTotalEntry OBJECT-TYPE
			SYNTAX IsdnPerfDataTotalEntry
			MAX-ACCESS not-accessible
			STATUS current
			DESCRIPTION
				"An entry in total performance table for each S/T interface."
			AUGMENTS { isdnConfigEntry }
			::= { isdnPerfDataTotalTable 1 }

		IsdnPerfDataTotalEntry ::=
			SEQUENCE {
				isdnPerfTotalBadAmiViolation
					PerfTotalCount,
				isdnPerfTotalUnbalancedFrame
					PerfTotalCount,
				isdnPerTotalFsyncSeconds
					PerfTotalCount,
				isdnPerfTotalErrorSeconds
					PerfTotalCount,
				isdnPerfTotalTimePeriodsElapsed
					Integer32
			 }

		-- 1.3.6.1.4.1.5504.5.7.1.4.1.1
		isdnPerfTotalBadAmiViolation OBJECT-TYPE
			SYNTAX PerfTotalCount
			MAX-ACCESS read-only
			STATUS current
			DESCRIPTION
				"Total count of frames with incorrect number of AMI violations."
			::= { isdnPerfDataTotalEntry 1 }

		-- 1.3.6.1.4.1.5504.5.7.1.4.1.2
		isdnPerfTotalUnbalancedFrame OBJECT-TYPE
			SYNTAX PerfTotalCount
			MAX-ACCESS read-only
			STATUS current
			DESCRIPTION
				"Total count of unbalanced frames."
			::= { isdnPerfDataTotalEntry 2 }

		-- 1.3.6.1.4.1.5504.5.7.1.4.1.3
		isdnPerTotalFsyncSeconds OBJECT-TYPE
			SYNTAX PerfTotalCount
			UNITS "seconds"
			MAX-ACCESS read-only
			STATUS current
			DESCRIPTION
				"Total Frame synch error seconds."
			::= { isdnPerfDataTotalEntry 3 }

		-- 1.3.6.1.4.1.5504.5.7.1.4.1.4
		isdnPerfTotalErrorSeconds OBJECT-TYPE
			SYNTAX PerfTotalCount
			UNITS "seconds"
			MAX-ACCESS read-only
			STATUS current
			DESCRIPTION
				"ISDN Activation error seconds"
			::= { isdnPerfDataTotalEntry 4 }

		-- 1.3.6.1.4.1.5504.5.7.1.4.1.5
		isdnPerfTotalTimePeriodsElapsed OBJECT-TYPE
			SYNTAX Integer32 (0..96)
			MAX-ACCESS read-only
			STATUS current
			DESCRIPTION
				"Number of 15 minute time periods that have been used
				in the performance total table. This value is normally
				96 indicating a valid 24 hour time period except in the
				cases of a restart of this agent."
			::= { isdnPerfDataTotalEntry 5 }

		-- 1.3.6.1.4.1.5504.5.7.1.5
		isdnAlarmProfileTable OBJECT-TYPE
			SYNTAX SEQUENCE OF IsdnAlarmProfileEntry
			MAX-ACCESS not-accessible
			STATUS current
			DESCRIPTION
				"This table contains information for Alarm conditions.
				The table is indexed by IfIndex . The alarm profile will be set
				per port basis usig ifIndex by the application when the system comes up.
				The operator can not create the profile , he can only  change it .
				 "
			::= { zhoneIsdnMib 5 }

		-- 1.3.6.1.4.1.5504.5.7.1.5.1
		isdnAlarmProfileEntry OBJECT-TYPE
			SYNTAX IsdnAlarmProfileEntry
			MAX-ACCESS not-accessible
			STATUS current
			DESCRIPTION
				"An entry in AlarmProfile Table.
								"
			AUGMENTS { isdnConfigEntry }
			::= { isdnAlarmProfileTable 1 }

		IsdnAlarmProfileEntry ::=
			SEQUENCE {
				isdnThresholdAmiViolations
					Unsigned32,
				isdnThresholdUnbalancedFrame
					Unsigned32
			 }

		-- 1.3.6.1.4.1.5504.5.7.1.5.1.1
		isdnThresholdAmiViolations OBJECT-TYPE
			SYNTAX Unsigned32
			MAX-ACCESS read-write
			STATUS current
			DESCRIPTION
				"Threshold for number of AMI violation .
				If the number of violations cross this
				threshold then the notification is sent to NMS.
				0 will disable the trap. The default value is 0.
				There is no range speciffied for this."
			::= { isdnAlarmProfileEntry 1 }

		-- 1.3.6.1.4.1.5504.5.7.1.5.1.2
		isdnThresholdUnbalancedFrame OBJECT-TYPE
			SYNTAX Unsigned32
			MAX-ACCESS read-write
			STATUS current
			DESCRIPTION
				"Threshold for number of unbalanced frame  after which the trap will
				 be send to NMS.0 will disable the trap. The default value is 0.
				There is no range speciffied for this.
				"
			::= { isdnAlarmProfileEntry 2 }


	END

--
-- phyIsdn.mib
--
