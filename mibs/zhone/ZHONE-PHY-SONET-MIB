--
-- phySonet.mib
-- MIB generated by MG-SOFT Visual MIB Builder Version 3.0 Build 271
-- Thursday, August 19, 2004 at 16:23:59
--

        ZHONE-PHY-SONET-MIB DEFINITIONS ::= BEGIN

                IMPORTS
                        InterfaceIndex
                                FROM IF-MIB
                        Integer32, OBJECT-TYPE, MODULE-IDENTITY, OBJECT-IDENTITY, NOTIFICATION-TYPE
                                FROM SNMPv2-SMI
                        TruthValue
                                FROM SNMPv2-TC
                        sonetMediumEntry, sonetSectionCurrentStatus, sonetLineCurrentStatus, sonetPathCurrentStatus
                                FROM SONET-MIB
                        zhoneSonet, zhoneModules
                                FROM Zhone;


-- To generate protection layer:
-- /vob/zhonetools/bin/pahrser.pl iftype.mib Zhone.mib Zhone-TC.mib rfc1907.mib rfc2493.mib rfc2233.mib rfc2514.mib rfc2558.mib phySonet.mib
--
-- To generate mib handlers:
-- /vob/EPILOGUE/binaries/emissary/solaris/mibcomp iftype.mib Zhone.mib Zhone-TC.mib rfc1907.mib rfc2493.mib rfc2233.mib rfc2514.mib rfc2558.mib -stub -o transportHdlrs.c phySonet.mib
--
--
                phySonet MODULE-IDENTITY
                        LAST-UPDATED "200408181330Z"		-- August 18, 2004 at 13:30 GMT
                        ORGANIZATION
                                "Zhone Technologies, Inc."
                        CONTACT-INFO
                                "  Postal:
                                           Zhone Technologies, Inc.
                                           @ Zhone Way
                                           7001 Oakport Street
                                           Oakland, CA  94621
                                           USA
                                Toll-Free: +1 877-ZHONE20 (+1 877-946-6320)
                                      Tel: +1-510-777-7000
                                      Fax: +1-510-777-7001
                                   E-mail: support@zhone.com"
                        DESCRIPTION
                                "SONET physical MIB to configure and monitor SONET physical
                                attributes.
                                "
                        REVISION "200408181147Z"		-- August 18, 2004 at 11:47 GMT
                        DESCRIPTION
                                "1.03.04 -  Add zhoneSonetErrorStatsTable."
                        REVISION "200307101330Z"		-- July 10, 2003 at 13:30 GMT
                        DESCRIPTION
                                "1.03.02
                                Add sonetPathStatusChange trap."
                        REVISION "200203261430Z"		-- March 26, 2002 at 14:30 GMT
                        DESCRIPTION
                                "1.03.01
                                Add sonetSectionStatusChange trap
                                and sonetLineStatusChange trap."
                        REVISION "200109121508Z"		-- September 12, 2001 at 15:08 GMT
                        DESCRIPTION
                                "V01.03.00
                                Changed names for valid values for sonetClockTransmitSource"
                        REVISION "200107191800Z"		-- July 19, 2001 at 18:00 GMT
                        DESCRIPTION
                                "V01.02.00
                                Add Sonet clock source change trap."
                        REVISION "200102221135Z"		-- February 22, 2001 at 11:35 GMT
                        DESCRIPTION
                                "V01.01.00 - Add Sonet Medium
                                                     Extension Table."
                        REVISION "200012191523Z"		-- December 19, 2000 at 15:23 GMT
                        DESCRIPTION
                                "V01.00.01 - Add Zhone keywords."
                        REVISION "200012181620Z"		-- December 18, 2000 at 16:20 GMT
                        DESCRIPTION
                                "V01.00.00 - Initial Release"
                        ::= { zhoneModules 16 }



--
-- Node definitions
--

-- The ZHONE keyword definition for SONET_Profile used here can be found
-- in rfc2558.mib. We use the keyword there as the sonetClockTable is an
-- aggregate of the sonetMediumTable.
                -- 1.3.6.1.4.1.5504.5.9.1
                sonetClockTable OBJECT-TYPE
                        SYNTAX SEQUENCE OF SonetClockEntry
                        MAX-ACCESS not-accessible
                        STATUS current
                        DESCRIPTION
                                "MIB table for clock related configuration for SONET interfaces."
                        ::= { zhoneSonet 1 }

                -- 1.3.6.1.4.1.5504.5.9.1.1
                sonetClockEntry OBJECT-TYPE
                        SYNTAX SonetClockEntry
                        MAX-ACCESS not-accessible
                        STATUS current
                        DESCRIPTION
                                "An entry of the sonetClockEntry.

                                sonetClockEntry is augmented to sonetMediumEntry defined
                                in rfc2558.mib. Whenever a row is instantiated in the
                                sonetMediumTable, a corresponding row will be
                                instantiated in the sonetClockTable."
                        AUGMENTS { sonetMediumEntry }
                        ::= { sonetClockTable 1 }

                SonetClockEntry ::=
                        SEQUENCE {
                                sonetClockExternalRecovery
                                        INTEGER,
                                sonetClockTransmitSource
                                        INTEGER
                         }

                -- 1.3.6.1.4.1.5504.5.9.1.1.1
                sonetClockExternalRecovery OBJECT-TYPE
                        SYNTAX INTEGER
                                {
                                enabled(1),
                                disabled(2)
                                }
                        MAX-ACCESS read-write
                        STATUS current
                        DESCRIPTION
                                "This variable indicates if external clock recovery is enabled
                                for this SONET interface.

                                The default value is 'enabled'."
                        ::= { sonetClockEntry 1 }

                -- 1.3.6.1.4.1.5504.5.9.1.1.2
                sonetClockTransmitSource OBJECT-TYPE
                        SYNTAX INTEGER
                                {
                                loopTiming(1),
                                throughTiming(2),
                                localTiming(3),
                                external155MHz(4)
                                }
                        MAX-ACCESS read-write
                        STATUS current
                        DESCRIPTION
                                "This variable describes the SONET transmit clock source.
                                Valid values are:

                                loopTiming - transmit clock synthesized from the recovered
                                receive clock.
                                throughTiming - transmit clock is derived from the recovered
                                receive clock of another SONET interface.
                                localTiming - transmit clock synthesized from a local clock
                                source or that an external clock is attached to the box
                                containing the interface.
                                external155MHz - transmit clock synthesized from an external
                                155.52 MHz source.

                                The default value is 'loopTiming'.

                                'external155MHz' option is not valid for Sechtor 100."
                        ::= { sonetClockEntry 2 }

                -- 1.3.6.1.4.1.5504.5.9.2
                sonetMediumExtTable OBJECT-TYPE
                        SYNTAX SEQUENCE OF SonetMediumExtEntry
                        MAX-ACCESS not-accessible
                        STATUS current
                        DESCRIPTION
                                "This is an extenion of the standard Sonet MIB (RFC 2558)."
                        ::= { zhoneSonet 2 }

                -- 1.3.6.1.4.1.5504.5.9.2.1
                sonetMediumExtEntry OBJECT-TYPE
                        SYNTAX SonetMediumExtEntry
                        MAX-ACCESS not-accessible
                        STATUS current
                        DESCRIPTION
                                "Each row is an extension to the sonetMediumTable for Zhone
                                specific fields. This row is created when the augmented
                                sonetMediumEntry is created."
                        AUGMENTS { sonetMediumEntry }
                        ::= { sonetMediumExtTable 1 }

                SonetMediumExtEntry ::=
                        SEQUENCE {
                                sonetMediumExtScrambleEnabled
                                        TruthValue,
                                sonetMediumExtLineScrmEnabled
                                        TruthValue
                         }

--
                -- 1.3.6.1.4.1.5504.5.9.2.1.1
                sonetMediumExtScrambleEnabled OBJECT-TYPE
                        SYNTAX TruthValue
                        MAX-ACCESS read-write
                        STATUS current
                        DESCRIPTION
                                "This field describes the enabled status of the Sonet Scramble mode. If this
                                field is true(1) then Scramble mode is enabled, if this field is
                                false(2) scramble mode is disable."
                        DEFVAL { true }
                        ::= { sonetMediumExtEntry 1 }

--
                -- 1.3.6.1.4.1.5504.5.9.2.1.2
                sonetMediumExtLineScrmEnabled OBJECT-TYPE
                        SYNTAX TruthValue
                        MAX-ACCESS read-write
                        STATUS current
                        DESCRIPTION
                                "This field describes the enabled status of the Line level
                                Sonet Scramble mode. If this field is true(1), then
                                Scramble mode is enabled. If this field is false(2),
                                scramble mode is disable."
                        DEFVAL { true }
                        ::= { sonetMediumExtEntry 2 }

                -- 1.3.6.1.4.1.5504.5.9.3
                sonetTraps OBJECT-IDENTITY
                        STATUS current
                        DESCRIPTION
                                "All Zhone Sonet traps will be defined under this object identity."
                        ::= { zhoneSonet 3 }

                -- 1.3.6.1.4.1.5504.5.9.3.0
                sonetV2Traps OBJECT-IDENTITY
                        STATUS current
                        DESCRIPTION
                                "This object identity adds a zero(0) for the next to last
                                sub-identifier which should be used for new SNMPv2 Traps."
                        ::= { sonetTraps 0 }

                -- 1.3.6.1.4.1.5504.5.9.3.0.1
                sonetClockTransmitSourceChange NOTIFICATION-TYPE
                        OBJECTS { sonetClockExternalRecovery, sonetClockTransmitSource }
                        STATUS current
                        DESCRIPTION
                                "A notification trap is sent when either
                                sonetClockExternalRecovery or sonetClockTransmitSource
                                is changed.

                                The trap object is identified by the OID instance
                                of sonetClockTransmitSource described in the
                                OBJECTS clause."
                        ::= { sonetV2Traps 1 }

                -- 1.3.6.1.4.1.5504.5.9.3.0.2
                sonetSectionStatusChange NOTIFICATION-TYPE
                        OBJECTS { sonetSectionCurrentStatus }
                        STATUS current
                        DESCRIPTION
                                "A notification trap is sent when there is a change
                                in the sonet SECTION status.  Currenly the following
                                are supported:

                                      NO-DEFECT = 1
                                      LOS       = 2
                                      LOF       = 4

                                The trap object is identified by the OID instance
                                of sonetSectionCurrentStatus described in the
                                OBJECTS clause."
                        ::= { sonetV2Traps 2 }

                -- 1.3.6.1.4.1.5504.5.9.3.0.3
                sonetLineStatusChange NOTIFICATION-TYPE
                        OBJECTS { sonetLineCurrentStatus }
                        STATUS current
                        DESCRIPTION
                                "A notification trap is sent when there is a change
                                in the sonet LINE status.  Currenly the following
                                are supported:

                                      NO-DEFECT = 1
                                      AIS       = 2
                                      RDI       = 4

                                The trap object is identified by the OID instance
                                of sonetLineCurrentStatus described in the
                                OBJECTS clause."
                        ::= { sonetV2Traps 3 }

                -- 1.3.6.1.4.1.5504.5.9.3.0.4
                sonetPathStatusChange NOTIFICATION-TYPE
                        OBJECTS { sonetPathCurrentStatus }
                        STATUS current
                        DESCRIPTION
                                "A notification trap is sent when there is a change
                                in the sonetPathCurrentStatus. Currenly the following
                                are supported:

                                   1   sonetPathNoDefect
                                   2   sonetPathSTSLOP
                                   4   sonetPathSTSAIS
                                   8   sonetPathSTSRDI
                                  16   sonetPathUnequipped
                                  32   sonetPathSignalLabelMismatch

                                The trap object is identified by the OID instance
                                of sonetPathCurrentStatus described in the
                                OBJECTS clause."
                        ::= { sonetV2Traps 4 }

                -- 1.3.6.1.4.1.5504.5.9.6
                zhoneSonetErrorStatsTable OBJECT-TYPE
                        SYNTAX SEQUENCE OF ZhoneSonetErrorStatsEntry
                        MAX-ACCESS not-accessible
                        STATUS current
                        DESCRIPTION
                                "Description."
                        ::= { zhoneSonet 6 }

                -- 1.3.6.1.4.1.5504.5.9.6.1
                zhoneSonetErrorStatsEntry OBJECT-TYPE
                        SYNTAX ZhoneSonetErrorStatsEntry
                        MAX-ACCESS not-accessible
                        STATUS current
                        DESCRIPTION
                                "Description."
                        INDEX { zhoneSonetErrorStatsIndex }
                        ::= { zhoneSonetErrorStatsTable 1 }

                ZhoneSonetErrorStatsEntry ::=
                        SEQUENCE {
                                zhoneSonetErrorStatsIndex
                                        InterfaceIndex,
                                zhoneSonetErrorStatsLineFebeCount
                                        Integer32,
                                zhoneSonetErrorStatsPathFebeCount
                                        Integer32,
                                zhoneSonetErrorStatsLineBipCount
                                        Integer32,
                                zhoneSonetErrorStatsSectionBipCount
                                        Integer32,
                                zhoneSonetErrorStatsPathBipCount
                                        Integer32,
                                zhoneSonetErrorStatsOofCount
                                        Integer32,
                                zhoneSonetErrorStatsRxCellCount
                                        Integer32,
                                zhoneSonetErrorStatsTxCellCount
                                        Integer32,
                                zhoneSonetErrorStatsHecCorrectedCount
                                        Integer32,
                                zhoneSonetErrorStatsHecUncorrectedCount
                                        Integer32,
                                zhoneSonetErrorStatsCellFifoOverflowCount
                                        Integer32,
                                zhoneSonetErrorStatsLocdCount
                                        Integer32
                         }

                -- 1.3.6.1.4.1.5504.5.9.6.1.1
                zhoneSonetErrorStatsIndex OBJECT-TYPE
                        SYNTAX InterfaceIndex
                        MAX-ACCESS not-accessible
                        STATUS current
                        DESCRIPTION
                                "Description."
                        ::= { zhoneSonetErrorStatsEntry 1 }

                -- 1.3.6.1.4.1.5504.5.9.6.1.2
                zhoneSonetErrorStatsLineFebeCount OBJECT-TYPE
                        SYNTAX Integer32
                        MAX-ACCESS read-only
                        STATUS current
                        DESCRIPTION
                                "Number of RLOP far-end block errors (FEBE)."
                        ::= { zhoneSonetErrorStatsEntry 2 }

                -- 1.3.6.1.4.1.5504.5.9.6.1.3
                zhoneSonetErrorStatsPathFebeCount OBJECT-TYPE
                        SYNTAX Integer32
                        MAX-ACCESS read-only
                        STATUS current
                        DESCRIPTION
                                "Number of RPOP far-end block errors (FEBE)."
                        ::= { zhoneSonetErrorStatsEntry 3 }

                -- 1.3.6.1.4.1.5504.5.9.6.1.4
                zhoneSonetErrorStatsLineBipCount OBJECT-TYPE
                        SYNTAX Integer32
                        MAX-ACCESS read-only
                        STATUS current
                        DESCRIPTION
                                "Number of Receive Line Overhead Processor (RLOP) BIP-8
                                errors.  The RLOP is responsible for line-level alarms
                                and for monitoring performance."
                        ::= { zhoneSonetErrorStatsEntry 4 }

                -- 1.3.6.1.4.1.5504.5.9.6.1.5
                zhoneSonetErrorStatsSectionBipCount OBJECT-TYPE
                        SYNTAX Integer32
                        MAX-ACCESS read-only
                        STATUS current
                        DESCRIPTION
                                "Number of Receive Section Overhead Processor (RSOP)
                                bit-interleaved parity (BIP)-8 errors. The RSOP
                                synchronizes and descrambles frames and provides
                                section-level alarms and performance monitoring."
                        ::= { zhoneSonetErrorStatsEntry 5 }

                -- 1.3.6.1.4.1.5504.5.9.6.1.6
                zhoneSonetErrorStatsPathBipCount OBJECT-TYPE
                        SYNTAX Integer32
                        MAX-ACCESS read-only
                        STATUS current
                        DESCRIPTION
                                "Number of Receive Path Overhead Processor (RPOP) BIP-8
                                errors. The RSOP interprets pointers and extracts path
                                overhead and the synchronous payload envelope. It is
                                also responsible for path-level alarms and for
                                monitoring performance."
                        ::= { zhoneSonetErrorStatsEntry 6 }

                -- 1.3.6.1.4.1.5504.5.9.6.1.7
                zhoneSonetErrorStatsOofCount OBJECT-TYPE
                        SYNTAX Integer32
                        MAX-ACCESS read-only
                        STATUS current
                        DESCRIPTION
                                "Near end is out of frame. False indicates that the line
                                is up and in frame."
                        ::= { zhoneSonetErrorStatsEntry 7 }

                -- 1.3.6.1.4.1.5504.5.9.6.1.8
                zhoneSonetErrorStatsRxCellCount OBJECT-TYPE
                        SYNTAX Integer32
                        MAX-ACCESS read-only
                        STATUS current
                        DESCRIPTION
                                "Receive ATM Cell Processor (RACP) receive cell count."
                        ::= { zhoneSonetErrorStatsEntry 8 }

                -- 1.3.6.1.4.1.5504.5.9.6.1.9
                zhoneSonetErrorStatsTxCellCount OBJECT-TYPE
                        SYNTAX Integer32
                        MAX-ACCESS read-only
                        STATUS current
                        DESCRIPTION
                                "Transmit ATM Cell Processor (TACP) transmit cell count."
                        ::= { zhoneSonetErrorStatsEntry 9 }

                -- 1.3.6.1.4.1.5504.5.9.6.1.10
                zhoneSonetErrorStatsHecCorrectedCount OBJECT-TYPE
                        SYNTAX Integer32
                        MAX-ACCESS read-only
                        STATUS current
                        DESCRIPTION
                                "Number of corrected HEC cells."
                        ::= { zhoneSonetErrorStatsEntry 10 }

                -- 1.3.6.1.4.1.5504.5.9.6.1.11
                zhoneSonetErrorStatsHecUncorrectedCount OBJECT-TYPE
                        SYNTAX Integer32
                        MAX-ACCESS read-only
                        STATUS current
                        DESCRIPTION
                                "Number of uncorrected dropped HEC cells."
                        ::= { zhoneSonetErrorStatsEntry 11 }

                -- 1.3.6.1.4.1.5504.5.9.6.1.12
                zhoneSonetErrorStatsCellFifoOverflowCount OBJECT-TYPE
                        SYNTAX Integer32
                        MAX-ACCESS read-only
                        STATUS current
                        DESCRIPTION
                                "Number of cells dropped because of first in, first out
                                (FIFO) overflow."
                        ::= { zhoneSonetErrorStatsEntry 12 }

                -- 1.3.6.1.4.1.5504.5.9.6.1.13
                zhoneSonetErrorStatsLocdCount OBJECT-TYPE
                        SYNTAX Integer32
                        MAX-ACCESS read-only
                        STATUS current
                        DESCRIPTION
                                "Loss of cell delineation."
                        ::= { zhoneSonetErrorStatsEntry 13 }


        END

--
-- phySonet.mib
--
