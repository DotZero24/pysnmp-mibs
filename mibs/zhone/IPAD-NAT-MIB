IPAD-NAT-MIB DEFINITIONS ::= BEGIN

IMPORTS IpAddress, TimeTicks,OBJECT-TYPE, MODULE-IDENTITY  FROM SNMPv2-SMI
	DisplayString                                  FROM SNMPv2-TC
	ipad                                           FROM IPADv2-MIB;

ipadNat MODULE-IDENTITY
         LAST-UPDATED "0005290001Z"
         ORGANIZATION "Verilink Corporation"
         CONTACT-INFO
             "support@verilink.com
             1-800-926-0085"
         DESCRIPTION
            "The IPAD NAT MIB."
         ::= { ipad 26 }

ipadNatParms           			OBJECT IDENTIFIER ::= { ipadNat 1 }
ipadNatStaticTranslationParms     	OBJECT IDENTIFIER ::= { ipadNat 2 }
ipadNatPortParms      			OBJECT IDENTIFIER ::= { ipadNat 3 }



ipadNatEnable    OBJECT-TYPE
    SYNTAX  INTEGER {
		    other(1),
		    disable(2),
		    enable(3)
		    }
    MAX-ACCESS  read-write
    STATUS  current
    DESCRIPTION
        ""
    ::= { ipadNatParms 1 }

ipadNatMode    OBJECT-TYPE
    SYNTAX  INTEGER {
		    other(1),
		    nat(2),
		    napt(3)
		    }
    MAX-ACCESS  read-write
    STATUS  current
    DESCRIPTION
        ""
    ::= { ipadNatParms 2 }

ipadNatGlobalAddress    OBJECT-TYPE
    SYNTAX  IpAddress
    MAX-ACCESS  read-write
    STATUS  current
    DESCRIPTION
        ""
    ::= { ipadNatParms 3 }


ipadNatGlobalMask    OBJECT-TYPE
    SYNTAX  IpAddress
    MAX-ACCESS  read-write
    STATUS  current
    DESCRIPTION
        ""
    ::= { ipadNatParms 4 }

ipadNatICMPDefaultAddress    OBJECT-TYPE
    SYNTAX  IpAddress
    MAX-ACCESS  read-write
    STATUS  current
    DESCRIPTION
        ""
    ::= { ipadNatParms 5 }

ipadNatFilterNonLocalAddress    OBJECT-TYPE
    SYNTAX  INTEGER {
		    other(1),
		    disable(2),
		    enable(3)
		    }
    MAX-ACCESS  read-write
    STATUS  current
    DESCRIPTION
        ""
    ::= { ipadNatParms 6 }

ipadNatIPEntryTimer    OBJECT-TYPE
    SYNTAX  INTEGER
    MAX-ACCESS  read-write
    STATUS  current
    DESCRIPTION
        ""
    ::= { ipadNatParms 7 }

ipadNatTCPConnectionTimer    OBJECT-TYPE
    SYNTAX  INTEGER
    MAX-ACCESS  read-write
    STATUS  current
    DESCRIPTION
        ""
    ::= { ipadNatParms 8 }

ipadNatTCPClosingTimer    OBJECT-TYPE
    SYNTAX  INTEGER
    MAX-ACCESS  read-write
    STATUS  current
    DESCRIPTION
        ""
    ::= { ipadNatParms 9 }

ipadNatTCPDisconnectedTimer    OBJECT-TYPE
    SYNTAX  INTEGER
    MAX-ACCESS  read-write
    STATUS  current
    DESCRIPTION
        ""
    ::= { ipadNatParms 10 }

ipadNatTCPSequenceDeltaTimer    OBJECT-TYPE
    SYNTAX  INTEGER
    MAX-ACCESS  read-write
    STATUS  current
    DESCRIPTION
        ""
    ::= { ipadNatParms 11 }

ipadNatUDPTimer    OBJECT-TYPE
    SYNTAX  INTEGER
    MAX-ACCESS  read-write
    STATUS  current
    DESCRIPTION
        ""
    ::= { ipadNatParms 12 }

ipadNatICMPTimer    OBJECT-TYPE
    SYNTAX  INTEGER
    MAX-ACCESS  read-write
    STATUS  current
    DESCRIPTION
        ""
    ::= { ipadNatParms 13 }

ipadNatStaticTranslationTable OBJECT-TYPE
    SYNTAX    SEQUENCE OF IpadNatStaticTranslationTableEntry
    MAX-ACCESS  not-accessible
    STATUS    current
    DESCRIPTION
        "Table of Static Translation Entries."
    ::= { ipadNatStaticTranslationParms 1 }

ipadNatStaticTranslationTableEntry OBJECT-TYPE
    SYNTAX  IpadNatStaticTranslationTableEntry
    MAX-ACCESS  not-accessible
    STATUS  current
    DESCRIPTION
        "An entry in the ipad NAT Static Translation table."
    INDEX   { ipadNatStaticTranslationEntryIndex }
    ::= { ipadNatStaticTranslationTable 1 }

IpadNatStaticTranslationTableEntry ::=
    SEQUENCE
    {
    ipadNatStaticTranslationEntryIndex		INTEGER,
    ipadNatStaticTranslationEnable		INTEGER,
    ipadNatStaticTranslationLocalAddress	IpAddress,
    ipadNatStaticTranslationGlobalAddress	IpAddress
    }

ipadNatStaticTranslationEntryIndex       OBJECT-TYPE
    SYNTAX  INTEGER
    MAX-ACCESS  read-only
    STATUS  current
    DESCRIPTION
        "The index into the Static Translation table."
    ::= { ipadNatStaticTranslationTableEntry 1 }

ipadNatStaticTranslationEnable    OBJECT-TYPE
    SYNTAX  INTEGER {
		    other(1),
		    disable(2),
		    enable(3)
		    }
    MAX-ACCESS  read-write
    STATUS  current
    DESCRIPTION
        ""
    ::= { ipadNatStaticTranslationTableEntry 2 }


ipadNatStaticTranslationLocalAddress    OBJECT-TYPE
    SYNTAX  IpAddress
    MAX-ACCESS  read-write
    STATUS  current
    DESCRIPTION
        ""
    ::= { ipadNatStaticTranslationTableEntry 3 }


ipadNatStaticTranslationGlobalAddress    OBJECT-TYPE
    SYNTAX  IpAddress
    MAX-ACCESS  read-write
    STATUS  current
    DESCRIPTION
        ""
    ::= { ipadNatStaticTranslationTableEntry 4 }


ipadNatStaticTCPTranslationTable OBJECT-TYPE
    SYNTAX    SEQUENCE OF IpadNatStaticTCPTranslationTableEntry
    MAX-ACCESS  not-accessible
    STATUS    current
    DESCRIPTION
        "Table of Static Translation Entries."
    ::= { ipadNatStaticTranslationParms 2 }

ipadNatStaticTCPTranslationTableEntry OBJECT-TYPE
    SYNTAX  IpadNatStaticTCPTranslationTableEntry
    MAX-ACCESS  not-accessible
    STATUS  current
    DESCRIPTION
        "An entry in the ipad NAT Static TCP Translation table."
    INDEX   { ipadNatStaticTCPTranslationEntryIndex }
    ::= { ipadNatStaticTCPTranslationTable 1 }

IpadNatStaticTCPTranslationTableEntry ::=
    SEQUENCE
    {
    ipadNatStaticTCPTranslationEntryIndex  	INTEGER,
    ipadNatStaticTCPTranslationGlobalPort  	INTEGER,
    ipadNatStaticTCPTranslationServerPort	INTEGER,
    ipadNatStaticTCPTranslationServerAddress	IpAddress
    }

ipadNatStaticTCPTranslationEntryIndex       OBJECT-TYPE
    SYNTAX  INTEGER
    MAX-ACCESS  read-only
    STATUS  current
    DESCRIPTION
        "The index into the Static TCP Translation table."
    ::= { ipadNatStaticTCPTranslationTableEntry 1 }

ipadNatStaticTCPTranslationGlobalPort    OBJECT-TYPE
    SYNTAX  INTEGER
    MAX-ACCESS  read-write
    STATUS  current
    DESCRIPTION
        ""
    ::= { ipadNatStaticTCPTranslationTableEntry 2 }

ipadNatStaticTCPTranslationServerPort    OBJECT-TYPE
    SYNTAX  INTEGER
    MAX-ACCESS  read-write
    STATUS  current
    DESCRIPTION
        ""
    ::= { ipadNatStaticTCPTranslationTableEntry 3 }

ipadNatStaticTCPTranslationServerAddress    OBJECT-TYPE
    SYNTAX  IpAddress
    MAX-ACCESS  read-write
    STATUS  current
    DESCRIPTION
        ""
    ::= { ipadNatStaticTCPTranslationTableEntry 4 }


ipadNatStaticUDPTranslationTable OBJECT-TYPE
    SYNTAX    SEQUENCE OF IpadNatStaticUDPTranslationTableEntry
    MAX-ACCESS  not-accessible
    STATUS    current
    DESCRIPTION
        "Table of Static Translation Entries."
    ::= { ipadNatStaticTranslationParms 3 }

ipadNatStaticUDPTranslationTableEntry OBJECT-TYPE
    SYNTAX  IpadNatStaticUDPTranslationTableEntry
    MAX-ACCESS  not-accessible
    STATUS  current
    DESCRIPTION
        "An entry in the ipad NAT Static UDP Translation table."
    INDEX   { ipadNatStaticUDPTranslationEntryIndex }
    ::= { ipadNatStaticUDPTranslationTable 1 }

IpadNatStaticUDPTranslationTableEntry ::=
    SEQUENCE
    {
    ipadNatStaticUDPTranslationEntryIndex  	INTEGER,
    ipadNatStaticUDPTranslationGlobalPort  	INTEGER,
    ipadNatStaticUDPTranslationServerPort	INTEGER,
    ipadNatStaticUDPTranslationServerAddress	IpAddress
    }

ipadNatStaticUDPTranslationEntryIndex       OBJECT-TYPE
    SYNTAX  INTEGER
    MAX-ACCESS  read-only
    STATUS  current
    DESCRIPTION
        "The index into the Static TCP Translation table."
    ::= { ipadNatStaticUDPTranslationTableEntry 1 }

ipadNatStaticUDPTranslationGlobalPort    OBJECT-TYPE
    SYNTAX  INTEGER
    MAX-ACCESS  read-write
    STATUS  current
    DESCRIPTION
        ""
    ::= { ipadNatStaticUDPTranslationTableEntry 2 }

ipadNatStaticUDPTranslationServerPort    OBJECT-TYPE
    SYNTAX  INTEGER
    MAX-ACCESS  read-write
    STATUS  current
    DESCRIPTION
        ""
    ::= { ipadNatStaticUDPTranslationTableEntry 3 }

ipadNatStaticUDPTranslationServerAddress    OBJECT-TYPE
    SYNTAX  IpAddress
    MAX-ACCESS  read-write
    STATUS  current
    DESCRIPTION
        ""
    ::= { ipadNatStaticUDPTranslationTableEntry 4 }


ipadNatStaticTranslationAdd    OBJECT-TYPE
    SYNTAX  INTEGER {
    		     other(1),
    		     addnew(2)
    		    }
    MAX-ACCESS  read-write
    STATUS  current
    DESCRIPTION
        ""
    ::= { ipadNatStaticTranslationParms 4 }

ipadNatStaticTranslationDelete    OBJECT-TYPE
    SYNTAX  INTEGER
    MAX-ACCESS  read-write
    STATUS  current
    DESCRIPTION
        ""
    ::= { ipadNatStaticTranslationParms 5 }

ipadNatStaticTCPTranslationAdd    OBJECT-TYPE
    SYNTAX  INTEGER {
    		     other(1),
    		     addnew(2)
    		    }
    MAX-ACCESS  read-write
    STATUS  current
    DESCRIPTION
        ""
    ::= { ipadNatStaticTranslationParms 6 }

ipadNatStaticTCPTranslationDelete    OBJECT-TYPE
    SYNTAX  INTEGER
    MAX-ACCESS  read-write
    STATUS  current
    DESCRIPTION
        ""
    ::= { ipadNatStaticTranslationParms 7 }

ipadNatStaticUDPTranslationAdd    OBJECT-TYPE
    SYNTAX  INTEGER {
    		     other(1),
    		     addnew(2)
    		    }
    MAX-ACCESS  read-write
    STATUS  current
    DESCRIPTION
        ""
    ::= { ipadNatStaticTranslationParms 8 }

ipadNatStaticUDPTranslationDelete    OBJECT-TYPE
    SYNTAX  INTEGER
    MAX-ACCESS  read-write
    STATUS  current
    DESCRIPTION
        ""
    ::= { ipadNatStaticTranslationParms 9 }


ipadNatPortConfigTable OBJECT-TYPE
    SYNTAX    SEQUENCE OF IpadNatPortConfigTableEntry
    MAX-ACCESS  not-accessible
    STATUS    current
    DESCRIPTION
        "Table of Static Translation Entries."
    ::= { ipadNatPortParms 1 }

ipadNatPortConfigTableEntry OBJECT-TYPE
    SYNTAX  IpadNatPortConfigTableEntry
    MAX-ACCESS  not-accessible
    STATUS  current
    DESCRIPTION
        "An entry in the ipad Port Config."
    INDEX   { ipadNatPortConfigIndex }
    ::= { ipadNatPortConfigTable 1 }

IpadNatPortConfigTableEntry ::=
    SEQUENCE
    {
    ipadNatPortConfigIndex			INTEGER,
    ipadNatPortConfigEnable			INTEGER,
    ipadNatPortConfigDefaultTranslation		INTEGER,
    ipadNatPortConfigType			INTEGER,
    ipadNatPortConfigIpAddress  		IpAddress,
    ipadNatPortConfigMask			IpAddress,
    ipadNatPortConfigEndpoint			DisplayString,
    ipadNatPortConfigClearStats  		INTEGER
    }

ipadNatPortConfigIndex       OBJECT-TYPE
    SYNTAX  INTEGER
    MAX-ACCESS  read-only
    STATUS  current
    DESCRIPTION
        "The index into the Port Config table."
    ::= { ipadNatPortConfigTableEntry 1 }

ipadNatPortConfigEnable       OBJECT-TYPE
    SYNTAX  INTEGER{
		    other(1),
		    disable(2),
		    enable(3)
		    }
    MAX-ACCESS  read-write
    STATUS  current
    DESCRIPTION
        ""
    ::= { ipadNatPortConfigTableEntry 2 }

ipadNatPortConfigDefaultTranslation       OBJECT-TYPE
    SYNTAX  INTEGER{
		    other(1),
		    disable(2),
		    enable(3)
		    }
    MAX-ACCESS  read-write
    STATUS  current
    DESCRIPTION
        ""
    ::= { ipadNatPortConfigTableEntry 3 }

ipadNatPortConfigType       OBJECT-TYPE
    SYNTAX  INTEGER{
		    other(1),
		    global(2),
		    local(3)
		    }
    MAX-ACCESS  read-write
    STATUS  current
    DESCRIPTION
        ""
    ::= { ipadNatPortConfigTableEntry 4 }

ipadNatPortConfigIpAddress       OBJECT-TYPE
    SYNTAX  IpAddress
    MAX-ACCESS  read-write
    STATUS  current
    DESCRIPTION
        ""
    ::= { ipadNatPortConfigTableEntry 5 }

ipadNatPortConfigMask       OBJECT-TYPE
    SYNTAX  IpAddress
    MAX-ACCESS  read-write
    STATUS  current
    DESCRIPTION
        ""
    ::= { ipadNatPortConfigTableEntry 6 }

ipadNatPortConfigEndpoint    OBJECT-TYPE
    SYNTAX  DisplayString ( SIZE(0..11) )
    MAX-ACCESS  read-write
    STATUS  current
    DESCRIPTION
        "The name for the endpoint to attach the port to."
    ::= { ipadNatPortConfigTableEntry 7 }

ipadNatPortConfigClearStats       OBJECT-TYPE
    SYNTAX  INTEGER{
		    other(1),
		    clear(2)
		    }
    MAX-ACCESS  read-write
    STATUS  current
    DESCRIPTION
        ""
    ::= { ipadNatPortConfigTableEntry 8 }


ipadNatPortAdd    OBJECT-TYPE
    SYNTAX  INTEGER {
    		     other(1),
    		     addnew(2)
    		    }
    MAX-ACCESS  read-write
    STATUS  current
    DESCRIPTION
        ""
    ::= { ipadNatPortParms 2 }

ipadNatPortDelete    OBJECT-TYPE
    SYNTAX  INTEGER
    MAX-ACCESS  read-write
    STATUS  current
    DESCRIPTION
        ""
    ::= { ipadNatPortParms 3 }


ipadNatPortStatusTable OBJECT-TYPE
    SYNTAX    SEQUENCE OF IpadNatPortStatusTableEntry
    MAX-ACCESS  not-accessible
    STATUS    current
    DESCRIPTION
        "Table of Port Status Entries."
    ::= { ipadNatPortParms 4 }

ipadNatPortStatusTableEntry OBJECT-TYPE
    SYNTAX  IpadNatPortStatusTableEntry
    MAX-ACCESS  not-accessible
    STATUS  current
    DESCRIPTION
        "An entry in the ipad Port Status table."
    INDEX   { ipadNatPortStatusIndex,ipadNatPortStatusLocalIpAddress }
    ::= { ipadNatPortStatusTable 1 }

IpadNatPortStatusTableEntry ::=
    SEQUENCE
    {
    ipadNatPortStatusIndex			INTEGER,
    ipadNatPortStatusLocalIpAddress		IpAddress,
    ipadNatPortStatusNatIpAddress		IpAddress,
    ipadNatPortStatusTxPackets			INTEGER,
    ipadNatPortStatusRxPackets  		INTEGER
    }

ipadNatPortStatusIndex       OBJECT-TYPE
    SYNTAX  INTEGER
    MAX-ACCESS  read-only
    STATUS  current
    DESCRIPTION
        ""
    ::= { ipadNatPortStatusTableEntry 1 }

ipadNatPortStatusLocalIpAddress       OBJECT-TYPE
    SYNTAX  IpAddress
    MAX-ACCESS  read-only
    STATUS  current
    DESCRIPTION
        ""
    ::= { ipadNatPortStatusTableEntry 2 }

ipadNatPortStatusNatIpAddress       OBJECT-TYPE
    SYNTAX  IpAddress
    MAX-ACCESS  read-only
    STATUS  current
    DESCRIPTION
        ""
    ::= { ipadNatPortStatusTableEntry 3 }

ipadNatPortStatusTxPackets       OBJECT-TYPE
    SYNTAX  INTEGER
    MAX-ACCESS  read-only
    STATUS  current
    DESCRIPTION
        ""
    ::= { ipadNatPortStatusTableEntry 4 }

ipadNatPortStatusRxPackets       OBJECT-TYPE
    SYNTAX  INTEGER
    MAX-ACCESS  read-only
    STATUS  current
    DESCRIPTION
        ""
    ::= { ipadNatPortStatusTableEntry 5 }

END
