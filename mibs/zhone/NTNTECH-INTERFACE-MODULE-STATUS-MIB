NTNTECH-INTERFACE-MODULE-STATUS-MIB DEFINITIONS ::= BEGIN

--	****************************************************************
--  Enterprise:
--   	Paradyne Corporation.
--
--  ContactInfo:
--    	Paradyne Corporation
--     	8545 126th Avenue North
--     	phone: +1 (727) 530 2000
--     	email: support@paradyne.com
--		www:   http://www.nettonet.com/support/
--
--  Description:
--    	ntntech-interface-module-status-MIB.my
--    	Revision: 1.02.02
--    	Part Number: xx-xxxx-xx
--    	Date: November 17, 2004
--
--    	This module provides explicit definitions for the Net to
--		Net Technologies naming	tree below:
--
--    	nettonettech { enterprises 8059 }
--
--    	This module will be extended, as additional sub-sections
--    	of this naming tree are defined.
--
--  Disclaimer:
--	   	This is an extremely preliminary MIB module and is subject
--		to change at any time therefore, use at your own risk.
--
-- 	Copyright (c) 2000 - 2004 by Paradyne Corporation.
-- 	All rights reserved.

-- *******************************************************************
IMPORTS
	ntntechInterfaceModule,NtnTimeTicks,
	NtnCounter32,NtnGauge32,NtnDisplayString,
	NtnMacAddress								FROM NTNTECH-ROOT-MIB
   	OBJECT-TYPE, MODULE-IDENTITY				FROM SNMPv2-SMI
   	TEXTUAL-CONVENTION							FROM SNMPv2-TC;
-- *******************************************************************
ntntechInterfaceModuleStatusMIB MODULE-IDENTITY
    LAST-UPDATED "0411171043Z"  -- November 17, 2004
    ORGANIZATION "Paradyne Corporation"
    CONTACT-INFO
        "Paradyne Corporation
        8545 126th Avenue North
        Largo, FL 33773

        phone: +1 (727) 530 2000
        email: support@paradyne.com
        www:   http://www.nettonet.com/support/"

    DESCRIPTION
         "This mib module defines an SNMP API to manage the Paradyne Corporation's
          IPD12000, IPD4000, and Mini/Micro DSLAM interface
         statistics.  The interface types are described below,

         AMD8000-12
         12-Port ADSL Mini DSLAMs With Full Rate and G.lite Operational Modes

         AAM8000-12
         12-Port ADSL Access Multiplexer with Full Rate and G.lite Operational
         Modes

         AAM8000-24
         24-Port ADSL Access Multiplexer with Full Rate and G.lite Operational
         Modes

         EAM2000-12
         12-Port E1 Access Multiplexer

         TAM1500-12
         12-Port T1 Access Multiplexer

         IAM144-12
         12-Port IDSL Access Multiplexer

         SAM1000-12
         12-Port SDSL Access Multiplexer

         SAM2000-12, SAM2000Q-12, and SAM2000G-12
         12-Port SDSL Access Multiplexers with CAP, 2B1Q or TC/PAM (G.SHDSL)
         encoding

         SAM2000D-12
         12-Port SDSL Access Multiplexer W/O voice daughter card, running CAP encoding

         SAM2000DQ-12
         12-Port SDSL Access Multiplexer W/O voice daughter card, running 2B1Q encoding

         SAM2000V-12, SAM2000QV-12, SAM2000GV-12
         12-Port SDSL Access Multiplexers with Voice Capability running CAP,
         2B1Q or TC/PAM (G.SHDSL) encoding

         SIM2000-12
         12-Port SDSL Access Multiplexer with CAP, 2B1Q and TC/PAM (G.SHDSL)
         encoding

         SIM2000-24
         24-Port SDSL Access Multiplexer with CAP, 2B1Q and TC/PAM (G.SHDSL)
         encoding

         SMD2000-12, SMD2000Q-12, SMD2000G-12
         12-Port SDSL Mini DSLAMs: AC and DC Versions with Cap, 2B1Q and
         G.SHDSL Line encoding

         SuD2011_12T, SuD2011_12E, SuD2003_12T, SuD2003_12E
         12-Port SDSL Micro DSLAMs: Cap, 2B1Q and G.SHDSL Line encoding

         SuD2011_6T, SuD2011_6E, SuD2002_6T, SuD2002_6E
         6-Port SDSL Micro DSLAMs: Cap, 2B1Q and G.SHDSL Line encoding "

    REVISION     "0206170305Z"
    DESCRIPTION
        "Add Loop Bonded OIDs,(ifStaLoopBondedGroupPortList and ifStaLoopBondedGroupID)to
         table ifStaPortTable."

    REVISION	"0208131103Z"
    DESCRIPTION
        "Added to the ifStaTable OID ifStaType the value smd2000p24(130).
         Added to the ifStaPortTable the following entries-
           ifStaNetworkLoopCount            INTEGER,
           ifStaLastMacCausingLoop          PhysAddress,
           ifStaLastMacSrcPort              INTEGER	"

    REVISION	"0208281048Z"
    DESCRIPTION
        "New Release - v1.01.00"

    REVISION	"0209270811Z"
    DESCRIPTION
        "Added to the ifStaTable OID ifStaType the value auD8000p12(131)."

    REVISION	"0210220200Z"
    DESCRIPTION
        "New Release - v1.01.01"

    REVISION	"0309301043Z"
    DESCRIPTION
    	"Added to the ifStaTable OID ifStaType the values
    		tim1500p12(31),
    		eim2000p12(32),
			tim1500p24(33),
			eim2000p24(34)"

	REVISION	"0403151000Z"
    DESCRIPTION
    	"Added to the ifStaTable OID ifStaType the values aim24000p48(35) and sne2040p4(136)"

     REVISION "0404271048Z"
     DESCRIPTION
        "Added the values ane8420(135) and sne2040(14) to the ifStaTable."

     REVISION "0410110939Z"
     DESCRIPTION
     	"Updated copyright and appropriate nomenclature to indicate Paradyne Corporation."

     	REVISION "0411171004Z"
     	DESCRIPTION
     	 	"New release version 1.02.01"

::= { ntntechInterfaceModule 2 }


--	Interface Module Statistics Objects (ifModStaObjects)

ifModStaMIBObjects OBJECT IDENTIFIER ::= { ntntechInterfaceModuleStatusMIB 1 }

--	Interface Module statistics for all Net To Net Tech interface
--	types:
--
--			ADSL,IDSL,SDSL,T1, and E1
--

ifModStaValues OBJECT IDENTIFIER ::= { ifModStaMIBObjects 1 }

valInterface OBJECT IDENTIFIER ::= { ifModStaValues 1 }

ifStaCount  OBJECT-TYPE
   	SYNTAX      INTEGER (0..12)
   	MAX-ACCESS  read-only
   	STATUS      current
   	DESCRIPTION
    "The number of interfaces physically within the chassis;
    type - IPD12000 (max 12), IPD4000 (max 4), Mini/Micro DSLAM (1)."
    ::= { valInterface 1 }

ifStaTable OBJECT-TYPE
    SYNTAX      SEQUENCE OF IfStaEntry
    MAX-ACCESS  not-accessible
    STATUS      current
    DESCRIPTION
    "A list of interface statistic entries."
    ::= { valInterface 2 }

ifStaEntry OBJECT-TYPE
   	SYNTAX			IfStaEntry
   	MAX-ACCESS  	not-accessible
   	STATUS      	current
   	DESCRIPTION
    "An entry containing management information applicable to the interface
    types available in the system."
       	INDEX   { ifStaSlotIndex }
       	::= { ifStaTable 1 }

   	IfStaEntry ::=
       SEQUENCE {
           ifStaSlotIndex	 	INTEGER,
           ifStaType			INTEGER,
           ifStaFirmwareRev		NtnDisplayString
       }

 	ifStaSlotIndex OBJECT-TYPE
       	SYNTAX      INTEGER (1..12)
       	MAX-ACCESS  read-only
       	STATUS      current
       	DESCRIPTION
        "The physical slot number of the IPD chassis to which the interface module resides.
        The Mini/Micro DSLAM will have a slot index value of 1."
       	::= { ifStaEntry 1 }

    ifStaType OBJECT-TYPE
       	SYNTAX      INTEGER {
       					iam144p12(1),
       					sam1000p12(2),
       					tam1500p12(3),
       					sam2000p12(4),
       					eam2000p12(5),
       					sim2000p24(6),
       					smD2000p12(7),
       					smD2000Qp12(8),
       					sam2000Qp12(9),
       					aam8000p12(10),
       					amD8000p12(11),
       					sam2000Dp12(12),
       					sam2000DQp12(13),
       					sam2000Gp12(14),
       					sam2000Vp12(15),
       					sam2000QVp12(16),
       					sam2000GVp12(17),
       					sim2000p12(18),
       					smD2000Gp12(19),
       					sim2000Vp24(20),
       					sim2000Vp12(21),
       					suD2011p12T(22),
						suD2011p12E(23),
						suD2003p12T(24),
						suD2003p12E(25),
						suD2011p6T(26),
						suD2011p6E(27),
						suD2002p6T(28),
						suD2002p6E(29),
						aam8000p24(30),
						smD2000p24(130),
						auD8000p12(131),
						tim1500p12(31),
						eim2000p12(32),
						tim1500p24(33),
						eim2000p24(34),
						aim24000p48(35),
						ane8420(135),
						sne2040(14)
       				}

       	MAX-ACCESS  read-only
       	STATUS      current
       	DESCRIPTION
        "The physical interface type."
       	::= { ifStaEntry 2 }

    ifStaFirmwareRev OBJECT-TYPE
       	SYNTAX      NtnDisplayString
       	MAX-ACCESS  read-only
       	STATUS      current
       	DESCRIPTION
        "The interface firmware revision."
       	::= { ifStaEntry 3 }

--	Interface Module Port statistics

ifStaPortTable OBJECT-TYPE
	SYNTAX      SEQUENCE OF IfStaPortEntry
    MAX-ACCESS  not-accessible
    STATUS      current
    DESCRIPTION
    "A list of interface port entries."
    ::= { valInterface 3 }

ifStaPortEntry OBJECT-TYPE
       	SYNTAX			IfStaPortEntry
       	MAX-ACCESS  	not-accessible
       	STATUS      	current
       	DESCRIPTION
        "An entry containing management information applicable to
        an interface."
       	INDEX   { ifStaPortSlotIndex,ifStaPortPortIndex }
       	::= { ifStaPortTable 1 }

   	IfStaPortEntry ::=
       SEQUENCE {
           ifStaPortSlotIndex	 			INTEGER,
           ifStaPortPortIndex				INTEGER,
           ifStaPortFirmwareRev				NtnDisplayString,
           ifStaPortLinkState				INTEGER,
           ifStaPortRxWanNUCastUtil   		NtnCounter32,
           ifStaPortRxWanNUCastRate			NtnGauge32,
           ifStaPortRxWanNUCastMaxRate		NtnGauge32,
           ifStaPortRxWanNUCastAveRate		NtnGauge32,
           ifStaPortTxWanNUCastUtil			NtnCounter32,
           ifStaPortTxWanNUCastRate			NtnGauge32,
           ifStaPortTxWanNUCastMaxRate		NtnGauge32,
           ifStaPortTxWanNUCastAveRate		NtnGauge32,
           ifStaPortRxWanUCastUtil			NtnCounter32,
           ifStaPortRxWanUCastRate			NtnGauge32,
           ifStaPortRxWanUCastMaxRate		NtnGauge32,
           ifStaPortRxWanUCastAveRate		NtnGauge32,
           ifStaPortTxWanUCastUtil			NtnCounter32,
           ifStaPortTxWanUCastRate			NtnGauge32,
           ifStaPortTxWanUCastMaxRate		NtnGauge32,
           ifStaPortTxWanUCastAveRate		NtnGauge32,
           ifStaPortTotRxWanPercentUtil		NtnCounter32,
           ifStaPortTotRxWanRate     		NtnGauge32,
           ifStaPortTotTxWanPercentUtil		NtnCounter32,
           ifStaPortTotTxWanRate			NtnGauge32,
           ifStaPortTotUpTime				NtnTimeTicks,
           ifStaPortTotDwnTime				NtnTimeTicks,
           ifStaUCastTxPkt      			NtnCounter32,
		   ifStaUCastRxPkt    				NtnCounter32,
		   ifStaNUCastTxPkt 				NtnCounter32,
		   ifStaNUCastRxPkt         		NtnCounter32,
		   ifStaNetworkLoopCount			INTEGER,
		   ifStaLastMacCausingLoop			NtnMacAddress,
		   ifStaLastMacSrcPort				INTEGER,
           ifStaLoopBondedGroupPortList		INTEGER,
		   ifStaLoopBondedGroupID			INTEGER

		  }

    ifStaPortSlotIndex OBJECT-TYPE
       	SYNTAX      INTEGER (1..12)
       	MAX-ACCESS  read-only
       	STATUS      current
       	DESCRIPTION
        "The physical slot number of the IPD chassis to which the interface module resides.
        The Mini/Micro DSLAM will have a slot index value of 1."
       	::= { ifStaPortEntry 1 }

    ifStaPortPortIndex OBJECT-TYPE
       	SYNTAX      INTEGER (1..48)
       	MAX-ACCESS  read-only
       	STATUS      current
       	DESCRIPTION
        "The physical port number of the interface."
       	::= { ifStaPortEntry 2 }

    ifStaPortFirmwareRev OBJECT-TYPE
       SYNTAX      NtnDisplayString
       MAX-ACCESS  read-only

       STATUS      current
       DESCRIPTION
       "A textual string containing information about the port firmware
       revision."
       ::= { ifStaPortEntry 3 }

    ifStaPortLinkState OBJECT-TYPE
       	SYNTAX      INTEGER {
       					linkup(1),
       					linkdown(2),
       					linkloopback(3),
       					linkdefect(4),
       					linkdisabled(5)
       				}
       	MAX-ACCESS  read-only
       	STATUS      current
       	DESCRIPTION
        "The value assigned to a port which designates the link status."
       	::= { ifStaPortEntry 4 }

    ifStaPortRxWanNUCastUtil OBJECT-TYPE
       SYNTAX      NtnCounter32
       MAX-ACCESS  read-only
       STATUS      current
       DESCRIPTION
       "The percent utilization for this port based on the received (Rx) WAN
       non unicast packet count.

       Discontinuities in the value of this counter can occur at
       re-initialization of the management system, and at other times as
       indicated by the value of ifStaModStaPortReset."
       ::= { ifStaPortEntry 5 }

    ifStaPortRxWanNUCastRate OBJECT-TYPE
       SYNTAX      NtnGauge32
       MAX-ACCESS  read-only
       STATUS      current
       DESCRIPTION
       "An estimate of the interface's current Rx WAN non unicast bandwidth
       in Kilo bits per second."
       ::= { ifStaPortEntry 6 }

    ifStaPortRxWanNUCastMaxRate	OBJECT-TYPE
       SYNTAX      NtnGauge32
       MAX-ACCESS  read-only
       STATUS      current
       DESCRIPTION
       "An estimate of the interface's maximum reported Rx WAN non unicast
       bandwidth in Kilo bits per second."
       ::= { ifStaPortEntry 7 }

    ifStaPortRxWanNUCastAveRate	OBJECT-TYPE
       SYNTAX      NtnGauge32
       MAX-ACCESS  read-only
       STATUS      current
       DESCRIPTION
       "An estimate of the interface's average reported Rx WAN non unicast
       bandwidth in Kilo bits per second."
       ::= { ifStaPortEntry 8 }

    ifStaPortTxWanNUCastUtil OBJECT-TYPE
       SYNTAX      NtnCounter32
       MAX-ACCESS  read-only
       STATUS      current
       DESCRIPTION
       "The percent utilization for this port based on the transmitted
       (Tx) WAN non unicast packet count.

       Discontinuities in the value of this counter can occur at
       re-initialization of the management system, and at other times as
       indicated by the value of ifStaModStaPortReset."
       ::= { ifStaPortEntry 9 }

    ifStaPortTxWanNUCastRate OBJECT-TYPE
       SYNTAX      NtnGauge32
       MAX-ACCESS  read-only
       STATUS      current
       DESCRIPTION
       "An estimate of the interface's current Tx WAN non unicast
       bandwidth in Kilo bits per second."
       ::= { ifStaPortEntry 10 }

    ifStaPortTxWanNUCastMaxRate	OBJECT-TYPE
       SYNTAX      NtnGauge32
       MAX-ACCESS  read-only
       STATUS      current
       DESCRIPTION
       "An estimate of the interface's maximum reported Tx WAN non
       unicast bandwidth in Kilo bits per second."
       ::= { ifStaPortEntry 11 }

    ifStaPortTxWanNUCastAveRate	OBJECT-TYPE
       SYNTAX      NtnGauge32
       MAX-ACCESS  read-only
       STATUS      current
       DESCRIPTION
       "An estimate of the interface's average reported Tx WAN non
       unicast bandwidth in Kilo bits per second."
       ::= { ifStaPortEntry 12 }

    ifStaPortRxWanUCastUtil OBJECT-TYPE
       SYNTAX      NtnCounter32
       MAX-ACCESS  read-only
       STATUS      current
       DESCRIPTION
       "The percent utilization for this port based on the received
       (Rx) WAN unicast packet count.

       Discontinuities in the value of this counter can occur at
       re-initialization of the management system, and at other times
       as indicated by the value of ifStaModStaPortReset."
       ::= { ifStaPortEntry 13 }

    ifStaPortRxWanUCastRate OBJECT-TYPE
       SYNTAX      NtnGauge32
       MAX-ACCESS  read-only
       STATUS      current
       DESCRIPTION
       "An estimate of the interface's current Rx WAN unicast bandwidth
       in Kilo bits per second."
       ::= { ifStaPortEntry 14 }

    ifStaPortRxWanUCastMaxRate	OBJECT-TYPE
       SYNTAX      NtnGauge32
       MAX-ACCESS  read-only
       STATUS      current
       DESCRIPTION
       "An estimate of the interface's maximum reported Rx WAN unicast
       bandwidth in Kilo bits per second."
       ::= { ifStaPortEntry 15 }

    ifStaPortRxWanUCastAveRate	OBJECT-TYPE
       SYNTAX      NtnGauge32
       MAX-ACCESS  read-only
       STATUS      current
       DESCRIPTION
       "An estimate of the interface's average reported Rx WAN unicast
       bandwidth in Kilo bits per second."
       ::= { ifStaPortEntry 16 }

    ifStaPortTxWanUCastUtil OBJECT-TYPE
       SYNTAX      NtnCounter32
       MAX-ACCESS  read-only
       STATUS      current
       DESCRIPTION
       "The percent utilization for this port based on the transmitted
       (Tx) WAN unicast packet count.

       Discontinuities in the value of this counter can occur at
       re-initialization of the management system, and at other times
       as indicated by the value of ifStaModStaPortReset."
       ::= { ifStaPortEntry 17 }

    ifStaPortTxWanUCastRate OBJECT-TYPE
       SYNTAX      NtnGauge32
       MAX-ACCESS  read-only
       STATUS      current
       DESCRIPTION
       "An estimate of the interface's current Tx WAN unicast bandwidth
       in Kilo bits per second."
       ::= { ifStaPortEntry 18 }

    ifStaPortTxWanUCastMaxRate	OBJECT-TYPE
       SYNTAX      NtnGauge32
       MAX-ACCESS  read-only
       STATUS      current
       DESCRIPTION
       "An estimate of the interface's maximum reported Tx WAN unicast
       bandwidth in Kilo bits per second."
       ::= { ifStaPortEntry 19 }

    ifStaPortTxWanUCastAveRate	OBJECT-TYPE
       SYNTAX      NtnGauge32
       MAX-ACCESS  read-only
       STATUS      current
       DESCRIPTION
       "An estimate of the interface's average reported Tx WAN unicast
       bandwidth in Kilo bits per second."
       ::= { ifStaPortEntry 20 }

 	ifStaPortTotRxWanPercentUtil OBJECT-TYPE
       SYNTAX      NtnCounter32
       MAX-ACCESS  read-only
       STATUS      current
       DESCRIPTION
       "The total percent utilization for this port based on the transmitted
       (Rx) WAN unicast and non unicast packet count.

       Discontinuities in the value of this counter can occur at
       re-initialization of the management system, and at other times as
       indicated by the value of ifStaModStaPortReset."
       ::= { ifStaPortEntry 21 }

    ifStaPortTotRxWanRate OBJECT-TYPE
       SYNTAX      NtnGauge32
       MAX-ACCESS  read-only
       STATUS      current
       DESCRIPTION
       "An estimate of the interface's current total Rx WAN unicast and
       non unicast bandwidth in Kilo bits per second."
       ::= { ifStaPortEntry 22 }

    ifStaPortTotTxWanPercentUtil OBJECT-TYPE
       SYNTAX      NtnCounter32
       MAX-ACCESS  read-only
       STATUS      current
       DESCRIPTION
       "The total percent utilization for this port based on the transmitted
       (Tx) WAN unicast and non unicast packet count.

       Discontinuities in the value of this counter can occur at
       re-initialization of the management system, and at other times as
       indicated by the value of ifStaModStaPortReset."
       ::= { ifStaPortEntry 23 }

    ifStaPortTotTxWanRate OBJECT-TYPE
       SYNTAX      NtnGauge32
       MAX-ACCESS  read-only
       STATUS      current
       DESCRIPTION
       "An estimate of the interface's current total Tx WAN unicast and
       non unicast bandwidth in Kilo bits per second."
       ::= { ifStaPortEntry 24 }

    ifStaPortTotUpTime OBJECT-TYPE
       SYNTAX      NtnTimeTicks
       MAX-ACCESS  read-only
       STATUS      current
       DESCRIPTION
       "The value of sysUpTime at the time of the last creation or reset
       of an entry in the ifStaModStaPortTable."
       ::= { ifStaPortEntry 25 }

    ifStaPortTotDwnTime	OBJECT-TYPE
       SYNTAX      NtnTimeTicks
       MAX-ACCESS  read-only
       STATUS      current
       DESCRIPTION
       "The value of sysDwnTime at the time of the last deletion or
       reset of an entry in the ifStaModStaPortTable."
       ::= { ifStaPortEntry 26 }

    ifStaUCastTxPkt OBJECT-TYPE
       SYNTAX      NtnCounter32
       MAX-ACCESS  read-only
       STATUS      current
       DESCRIPTION
       "The identifier which describes the transmitted (Tx) WAN unicast packet count.

       Discontinuities in the value of this counter can occur at
       re-initialization of the management system, and at other times as
       indicated by the value of ifStaModStaPortReset."
       ::= { ifStaPortEntry 27 }

    ifStaUCastRxPkt OBJECT-TYPE
       SYNTAX      NtnCounter32
       MAX-ACCESS  read-only
       STATUS      current
       DESCRIPTION
       "The identifier which describes the received (Rx) WAN unicast packet count.

       Discontinuities in the value of this counter can occur at
       re-initialization of the management system, and at other times as
       indicated by the value of ifStaModStaPortReset."
       ::= { ifStaPortEntry 28 }

	ifStaNUCastTxPkt OBJECT-TYPE
       SYNTAX      NtnCounter32
       MAX-ACCESS  read-only
       STATUS      current
       DESCRIPTION
       "The identifier which describes the transmitted (Tx) WAN non unicast packet count.

       Discontinuities in the value of this counter can occur at
       re-initialization of the management system, and at other times as
       indicated by the value of ifStaModStaPortReset."
       ::= { ifStaPortEntry 29 }

	ifStaNUCastRxPkt OBJECT-TYPE
       SYNTAX      NtnCounter32
       MAX-ACCESS  read-only
       STATUS      current
       DESCRIPTION
       "The identifier which describes the received (Rx) WAN non unicast packet count.

       Discontinuities in the value of this counter can occur at
       re-initialization of the management system, and at other times as
       indicated by the value of ifStaModStaPortReset."
       ::= { ifStaPortEntry 30 }

    ifStaNetworkLoopCount OBJECT-TYPE
       SYNTAX      INTEGER (0..4294967295)
       MAX-ACCESS  read-only
       STATUS      current
       DESCRIPTION
       "The identifier which describes the network loop count."
       ::= { ifStaPortEntry 31 }

    ifStaLastMacCausingLoop OBJECT-TYPE
       SYNTAX      NtnMacAddress
       MAX-ACCESS  read-only
       STATUS      current
       DESCRIPTION
       "The identifier which describes the last MAC address that caused a
       network loop condition."
       ::= { ifStaPortEntry 32 }

    ifStaLastMacSrcPort OBJECT-TYPE
       SYNTAX      INTEGER (0..255)
       MAX-ACCESS  read-only
       STATUS      current
       DESCRIPTION
       "The identifier which describes the source port of the last MAC address."
       ::= { ifStaPortEntry 33 }

    ifStaLoopBondedGroupPortList OBJECT-TYPE
       SYNTAX      INTEGER (0..4294967295)
       MAX-ACCESS  read-only
       STATUS      current
       DESCRIPTION
       "The bitmask of ports assigned to a loop bonded group."
       ::= { ifStaPortEntry 34 }

 	ifStaLoopBondedGroupID OBJECT-TYPE
       SYNTAX      INTEGER (0..4294967295)
       MAX-ACCESS  read-only
       STATUS      current
       DESCRIPTION
       "The identifier of the loop bonded group."
       ::= { ifStaPortEntry 35 }




END
