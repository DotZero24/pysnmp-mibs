--
-- phyDsl.mib
-- MIB generated by MG-SOFT Visual MIB Builder Version 1.8 Build 150
-- Thursday, May 11, 2000 at 13:50:08
--

	ZhoneDsl-MIB DEFINITIONS ::= BEGIN

		IMPORTS
			SnmpAdminString
				FROM SNMP-FRAMEWORK-MIB
			Integer32, Gauge32, Counter32,  OBJECT-TYPE,
			MODULE-IDENTITY
				FROM SNMPv2-SMI
			VariablePointer
				FROM SNMPv2-TC
			ifIndex
				FROM IF-MIB
			zhoneDsl, zhoneModules
				FROM Zhone
			ZhoneRowStatus, ZhoneAdminString
				FROM Zhone-TC;


		zhoneDsl-MIB MODULE-IDENTITY
			LAST-UPDATED "200005111753Z"
			ORGANIZATION
				"Zhone"
			CONTACT-INFO
				"		Postal:
						        xxx
						        Zhone Technologies, Inc.
						        xxx address.
						        Fremont, Ca.

						Toll-Free: 877-ZHONE20 (+1 877-946-6320)
						Tel: +1 978-452-0571
						Fax: +1 978-xxx-xxxx
						E-mail: xxx@zhone.com
				"
			DESCRIPTION
				"The MIB module to describe the Zhone specific
				implementation of HDSL, HDSL2, SDSL and G.SHDSL"
			REVISION "200004261753Z"
			DESCRIPTION
				"strawman structure"
			::= { zhoneModules 3 }



--
-- Node definitions
--

--
-- This defines Zhone's MIB support for xDSL that currently do not have a
-- standard. The MIB consists of a generic line definition and sub-branches
-- that are applicable to a specific xDSL. There is one generic line definition
-- entry, from the zhoneDslLineTable, per xDSL modem. These entries are indexed
-- by ifIndex and correspond to an entry in the ifEntry table.
--


		zhoneDslLineTable OBJECT-TYPE
			SYNTAX SEQUENCE OF ZhoneDslLineEntry
			MAX-ACCESS not-accessible
			STATUS current
			DESCRIPTION
				"This table contains common attributes describing
				DSL physical line interfaces for DSLs without a MIB
				standard."
			::= { zhoneDsl 1 }

		zhoneDslLineEntry OBJECT-TYPE
			SYNTAX ZhoneDslLineEntry
			MAX-ACCESS not-accessible
			STATUS current
			DESCRIPTION
				"An entry in the zhoneDslLine Table."
			INDEX { ifIndex }
			::= { zhoneDslLineTable 1 }

		ZhoneDslLineEntry ::=
			SEQUENCE {
				zhoneDslLineType
					INTEGER,
				zhoneDslLineCapabilities
					BITS,
				zhoneDslLineStatus
					INTEGER,
				zhoneDslUpLineRate
					Gauge32,
				zhoneDslDownLineRate
					Gauge32,
				zhoneDslLineConfigProfile
					ZhoneAdminString,
				zhoneDslLineAlarmProfile
					ZhoneAdminString,
				zhoneDslLineRowStatus
					ZhoneRowStatus
			 }

		zhoneDslLineType OBJECT-TYPE
			SYNTAX INTEGER
				{
				hdsl(1),
				hdsl2(2),
				shdsl(3),
				sdsl(96)
				}
			MAX-ACCESS read-create
			STATUS current
			DESCRIPTION
				"The DSL type. Many modem vendors allow software selection between
				HDSL, HDSL2, SDSL and SHDSL. Using zhoneDslLineTypeSupported the user
				can see what dsl option is available on this interface."
			DEFVAL { hdsl2 }
			::= { zhoneDslLineEntry 1 }

		zhoneDslLineCapabilities OBJECT-TYPE
			SYNTAX BITS
				{
				hdsl(1),
				hdsl2(2),
				shdsl(4),
				sdsl(8)
				}
			MAX-ACCESS read-only
			STATUS current
			DESCRIPTION
				"The DSL types supported on this interface. This is a bit-map of possible
				types. This variable can be used to determine zhoneDslLineType."
			::= { zhoneDslLineEntry 2 }

		zhoneDslLineStatus OBJECT-TYPE
			SYNTAX INTEGER
				{
				down(1),
				downloading(2),
				activated(3),
				training(4),
				up(5)
				}
			MAX-ACCESS read-only
			STATUS current
			DESCRIPTION
				"The DSL modem status. Detailed modem state maybe available in the
				status table. "
			::= { zhoneDslLineEntry 3 }

		zhoneDslUpLineRate OBJECT-TYPE
			SYNTAX Gauge32
			UNITS "bps"
			MAX-ACCESS read-only
			STATUS current
			DESCRIPTION
				"The DSL upstream (cpe->co) line rate on this interface."
			::= { zhoneDslLineEntry 4 }

		zhoneDslDownLineRate OBJECT-TYPE
			SYNTAX Gauge32
			UNITS "bps"
			MAX-ACCESS read-only
			STATUS current
			DESCRIPTION
				"The DSL downstream (co->cpe) line rate on this interface."
			::= { zhoneDslLineEntry 5 }

		zhoneDslLineConfigProfile OBJECT-TYPE
			SYNTAX ZhoneAdminString
			MAX-ACCESS read-create
			STATUS current
			DESCRIPTION
				"The value of this object identifies the row in the
				respective dsl configuration profile table. (Ex:
				if zhoneDslLineType is HDSL2, then the profile identifies
				an HDSL2 configuration profile.) It is assumed that all
				profile names are unique to the system.

				              In the case which the
				              configuration profile has not been set, the
				              value will be set to `ZhoneDefault'. This is
				              a profile (by type) which will be persisted
				              and then able to be modified by a management
				              station in order to modify the DEFAULT
				              values.
				"
			::= { zhoneDslLineEntry 6 }

		zhoneDslLineAlarmProfile OBJECT-TYPE
			SYNTAX ZhoneAdminString
			MAX-ACCESS read-create
			STATUS current
			DESCRIPTION
				"The value of this object identifies the row in the
				respective dsl alarm profile table. (Ex: if zhoneDslLineType is HDSL2
				then the profile identifies an HDSL2 alarm profile.)
				It is assumed that all profile names are unique to the system.

				              In the case where the
				              configuration profile has not been set, the
				              value will be set to `ZhoneDefault'.
				"
			::= { zhoneDslLineEntry 7 }

		zhoneDslLineRowStatus OBJECT-TYPE
			SYNTAX ZhoneRowStatus
			MAX-ACCESS read-write
			STATUS current
			DESCRIPTION
				"Row status in order to add an entry in this table.

				The required fields to be added are: (ARE ALL THE DEFAULTS OKAY)
				"
			::= { zhoneDslLineEntry 8 }

--
-- The configuration profile used for HDSL2 lines.
--
		zhoneHdsl2ConfigProfileTable OBJECT-TYPE
			SYNTAX SEQUENCE OF ZhoneHdsl2ConfigProfileEntry
			MAX-ACCESS not-accessible
			STATUS current
			DESCRIPTION
				"This table contains information for HDSL2 configuration."
			::= { zhoneDsl 3 }

		zhoneHdsl2ConfigProfileEntry OBJECT-TYPE
			SYNTAX ZhoneHdsl2ConfigProfileEntry
			MAX-ACCESS not-accessible
			STATUS current
			DESCRIPTION
				"An entry in the zhoneHdsl2ConfigProfile Table."
			INDEX { IMPLIED zhoneHdsl2ConfigProfileName }
			::= { zhoneHdsl2ConfigProfileTable 1 }

		ZhoneHdsl2ConfigProfileEntry ::=
			SEQUENCE {
				zhoneHdsl2ConfigProfileName
					ZhoneAdminString,
				zhoneHdsl2ConfigUnitMode
					INTEGER,
				zhoneHdsl2ConfigTransmitPowerbackoffMode
					INTEGER,
				zhoneHdsl2ConfigDecoderCoeffA
					Integer32,
				zhoneHdsl2ConfigDecoderCoeffB
					Integer32,
				zhoneHdsl2ConfigFrameSyncWord
					Integer32,
				zhoneHdsl2ConfigStuffBits
					Integer32,
				zhoneHdsl2ConfigRowStatus
					ZhoneRowStatus
			 }

		zhoneHdsl2ConfigProfileName OBJECT-TYPE
			SYNTAX ZhoneAdminString
			MAX-ACCESS not-accessible
			STATUS current
			DESCRIPTION
				"Configuration profile name. Used by the zhoneHdsl2LineConfigProfile entry
				to map zhoneDslLine Entry to the appropriate profile.

				              When `dynamic' profiles are implemented, the profile
				              name is user specified.  Also, the system will always
				              provide a default profile whose name is `DEFVAL'.

				              When `static' profiles are implemented, there is an
				              one-to-one relationship between each line and its
				              profile.  In which case, the profile name will
				              need to algorithmically represent the Line's ifIndex.
				              Therefore, the profile's name is a decimal zed string
				              of the ifIndex that is fixed-length (i.e., 10) with
				              leading zero(s).  For example, the profile name for
				              ifIndex which equals '15' will be '0000000015'."
			::= { zhoneHdsl2ConfigProfileEntry 1 }

		zhoneHdsl2ConfigUnitMode OBJECT-TYPE
			SYNTAX INTEGER
				{
				co(1),
				cpe(2)
				}
			MAX-ACCESS read-create
			STATUS current
			DESCRIPTION
				"Unit is configured as the CO(central office)or CPE (customer premise)side."
			DEFVAL { co }
			::= { zhoneHdsl2ConfigProfileEntry 2 }

		zhoneHdsl2ConfigTransmitPowerbackoffMode OBJECT-TYPE
			SYNTAX INTEGER
				{
				backoff-disable(1),
				backoff-enable(2),
				no-change-backoff(3)
				}
			MAX-ACCESS read-create
			STATUS current
			DESCRIPTION
				"Determines if the transmit power backoff defined in HDSL2 standard
				is used."
			DEFVAL { backoff-disable }
			::= { zhoneHdsl2ConfigProfileEntry 3 }

		zhoneHdsl2ConfigDecoderCoeffA OBJECT-TYPE
			SYNTAX Integer32
			MAX-ACCESS read-create
			STATUS current
			DESCRIPTION
				"21 bit value corresponding to the decoder coefficient A. The default is the ANSI HDSL2 default."
			DEFVAL { '011101101000000000000'b }
			::= { zhoneHdsl2ConfigProfileEntry 4 }

		zhoneHdsl2ConfigDecoderCoeffB OBJECT-TYPE
			SYNTAX Integer32
			MAX-ACCESS read-create
			STATUS current
			DESCRIPTION
				"21 bit value corresponding to the decoder coefficient A. The default is the ANSI HDSL2 default."
			DEFVAL { '011101101000000000000'b }
			::= { zhoneHdsl2ConfigProfileEntry 5 }

		zhoneHdsl2ConfigFrameSyncWord OBJECT-TYPE
			SYNTAX Integer32
			MAX-ACCESS read-create
			STATUS current
			DESCRIPTION
				"10 bit frame sync word. The default is the HDSL2 standard."
			DEFVAL { '0000101101'b }
			::= { zhoneHdsl2ConfigProfileEntry 6 }

		zhoneHdsl2ConfigStuffBits OBJECT-TYPE
			SYNTAX Integer32 (0..15)
			MAX-ACCESS read-create
			STATUS current
			DESCRIPTION
				"4 bit stuff pattern. The default is the HDSL2 standard."
			DEFVAL { '1111'b }
			::= { zhoneHdsl2ConfigProfileEntry 7 }

		zhoneHdsl2ConfigRowStatus OBJECT-TYPE
			SYNTAX ZhoneRowStatus
			MAX-ACCESS read-create
			STATUS current
			DESCRIPTION
				"Status in order to create/delete rows.

				For creation the following fields are required:"
			::= { zhoneHdsl2ConfigProfileEntry 8 }

--
-- HDSL2 status entries. NOTE: the terms local and remote are used to
-- denote your unit and the peer on the other side of the loop.
--
		zhoneHdsl2StatusTable OBJECT-TYPE
			SYNTAX SEQUENCE OF ZhoneHdsl2StatusEntry
			MAX-ACCESS not-accessible
			STATUS current
			DESCRIPTION
				"This table contains HDSL2 specific line status information.

				An entry into this table is automatically created whenever a
				zhoneDslLineEntry is created and the type is HDSL2."
			::= { zhoneDsl 4 }

		zhoneHdsl2StatusEntry OBJECT-TYPE
			SYNTAX ZhoneHdsl2StatusEntry
			MAX-ACCESS not-accessible
			STATUS current
			DESCRIPTION
				"An entry in the zhoneHdsl2Status Table."
			AUGMENTS { ifIndex }
			::= { zhoneHdsl2StatusTable 1 }

		ZhoneHdsl2StatusEntry ::=
			SEQUENCE {
				zhoneHdsl2DriftAlarm
					INTEGER,
				zhoneHdsl2FramerIBStatus
					OCTET STRING,
				zhoneHdsl2LocalPSDMaskStatus
					Integer32,
				zhoneHdsl2LoopAttenuation
					Integer32,
				zhoneHdsl2LossWordStatus
					INTEGER,
				zhoneHdsl2RmtPSDMaskStatus
					Integer32,
				zhoneHdsl2RmtCountryCode
					Integer32,
				zhoneHdsl2RmtVersion
					Integer32,
				zhoneHdsl2RmtProviderCode
					Integer32,
				zhoneHdsl2RmtVendorData
					OCTET STRING,
				zhoneHdsl2RmtTxEncoderA
					Integer32,
				zhoneHdsl2RmtTxEncoderB
					Integer32,
				zhoneHdsl2TipRingStatus
					INTEGER,
				zhoneHdsl2FrameSyncWord
					Integer32,
				zhoneHdsl2StuffBits
					Integer32
			 }

		zhoneHdsl2DriftAlarm OBJECT-TYPE
			SYNTAX INTEGER
				{
				rx-clk-alarm(1),
				tx-clk-alarm(2),
				tx-rx-clk-alarm(3),
				no-drift-alarm(4),
				not-applicable(5)
				}
			MAX-ACCESS read-only
			STATUS current
			DESCRIPTION
				" Indicates that the framer automatically attempted to adjust for clock
				drift. This is not applicable for ATM."
			::= { zhoneHdsl2StatusEntry 1 }

		zhoneHdsl2FramerIBStatus OBJECT-TYPE
			SYNTAX OCTET STRING (SIZE (1))
			MAX-ACCESS read-only
			STATUS current
			DESCRIPTION
				"Returns the segd,sega,uib and losd bits. The format of the octet is:
				x x x x segd sega uib losd."
			::= { zhoneHdsl2StatusEntry 2 }

		zhoneHdsl2LocalPSDMaskStatus OBJECT-TYPE
			SYNTAX Integer32
			MAX-ACCESS read-only
			STATUS current
			DESCRIPTION
				"Returns a number corresponding to the transmit power backoff requested
				by the local unit."
			::= { zhoneHdsl2StatusEntry 3 }

		zhoneHdsl2LoopAttenuation OBJECT-TYPE
			SYNTAX Integer32
			UNITS "tenth DB"
			MAX-ACCESS read-only
			STATUS current
			DESCRIPTION
				"Estimation of the loop attenuation in tenths of a DB.
				by the local unit."
			::= { zhoneHdsl2StatusEntry 4 }

		zhoneHdsl2LossWordStatus OBJECT-TYPE
			SYNTAX INTEGER
				{
				no-lossw-defect(1),
				lossw-defect(2)
				}
			MAX-ACCESS read-only
			STATUS current
			DESCRIPTION
				"This indicates loss of sync."
			::= { zhoneHdsl2StatusEntry 5 }

		zhoneHdsl2RmtPSDMaskStatus OBJECT-TYPE
			SYNTAX Integer32
			MAX-ACCESS read-only
			STATUS current
			DESCRIPTION
				"Returns a number corresponding to the transmit power backoff requested
				by the remote unit."
			::= { zhoneHdsl2StatusEntry 6 }

		zhoneHdsl2RmtCountryCode OBJECT-TYPE
			SYNTAX Integer32
			MAX-ACCESS read-only
			STATUS current
			DESCRIPTION
				"ANSI HDSL2 Country code of the remote unit."
			::= { zhoneHdsl2StatusEntry 7 }

		zhoneHdsl2RmtVersion OBJECT-TYPE
			SYNTAX Integer32
			MAX-ACCESS read-only
			STATUS current
			DESCRIPTION
				"HDSL2 version of the remote unit."
			::= { zhoneHdsl2StatusEntry 8 }

		zhoneHdsl2RmtProviderCode OBJECT-TYPE
			SYNTAX Integer32
			MAX-ACCESS read-only
			STATUS current
			DESCRIPTION
				"Provider word of the remote unit."
			::= { zhoneHdsl2StatusEntry 9 }

		zhoneHdsl2RmtVendorData OBJECT-TYPE
			SYNTAX OCTET STRING (SIZE (8))
			MAX-ACCESS read-only
			STATUS current
			DESCRIPTION
				"The remote unit's vendor-provided data."
			::= { zhoneHdsl2StatusEntry 10 }

		zhoneHdsl2RmtTxEncoderA OBJECT-TYPE
			SYNTAX Integer32
			MAX-ACCESS read-only
			STATUS current
			DESCRIPTION
				"The remote unit's 21 bit encoder coefficient A"
			::= { zhoneHdsl2StatusEntry 11 }

		zhoneHdsl2RmtTxEncoderB OBJECT-TYPE
			SYNTAX Integer32
			MAX-ACCESS read-only
			STATUS current
			DESCRIPTION
				"The remote unit's 21 bit encoder coefficient B"
			::= { zhoneHdsl2StatusEntry 12 }

		zhoneHdsl2TipRingStatus OBJECT-TYPE
			SYNTAX INTEGER
				{
				normal(1),
				reverse(2)
				}
			MAX-ACCESS read-only
			STATUS current
			DESCRIPTION
				"Indicates whether the tip and ring points from the local unit match the
				tip and ring points of the remote."
			::= { zhoneHdsl2StatusEntry 13 }

		zhoneHdsl2FrameSyncWord OBJECT-TYPE
			SYNTAX Integer32
			MAX-ACCESS read-only
			STATUS current
			DESCRIPTION
				"A 10 bit number indicating the frame sync word used. LSB justified"
			::= { zhoneHdsl2StatusEntry 14 }

		zhoneHdsl2StuffBits OBJECT-TYPE
			SYNTAX Integer32
			MAX-ACCESS read-only
			STATUS current
			DESCRIPTION
				"A 4 bit number for the stuff bits. LSB justified."
			::= { zhoneHdsl2StatusEntry 15 }

-- Information tracked for every DSL link. Table is augmented to the
-- zhoneDslLineEntry
--
--
		zhoneDslPerfDataTable OBJECT-TYPE
			SYNTAX SEQUENCE OF ZhoneDslPerfDataEntry
			MAX-ACCESS not-accessible
			STATUS current
			DESCRIPTION
				"This table provides one row for each modem interface."
			::= { zhoneDsl 5 }

		zhoneDslPerfDataEntry OBJECT-TYPE
			SYNTAX ZhoneDslPerfDataEntry
			MAX-ACCESS not-accessible
			STATUS current
			DESCRIPTION
				"An entry in zhoneDslPerfDataTable."
			AUGMENTS { zhoneDslLineEntry }
			::= { zhoneDslPerfDataTable 1 }

		ZhoneDslPerfDataEntry ::=
			SEQUENCE {
				zhoneDslPerfLofs
					Counter32,
				zhoneDslPerfLoss
					Counter32,
				zhoneDslPerfLols
					Counter32,
				zhoneDslPerfInits
					Counter32,
				zhoneDslPerfCur15MinTimeElapsed
					Gauge32,
				zhoneDslPerfCur15MinLofs
					Gauge32,
				zhoneDslPerfCur15MinLoss
					Gauge32,
				zhoneDslPerfCur15MinLols
					Gauge32,
				zhoneDslPerfCur15MinInits
					Gauge32

			 }

		zhoneDslPerfLofs OBJECT-TYPE
			SYNTAX Counter32
			MAX-ACCESS read-only
			STATUS current
			DESCRIPTION
				"Count of the number of Loss of Framing failures since agent reset."
			::= { zhoneDslPerfDataEntry 1 }

		zhoneDslPerfLoss OBJECT-TYPE
			SYNTAX Counter32
			MAX-ACCESS read-only
			STATUS current
			DESCRIPTION
				"Count of the number of Loss of Signal failures since agent reset."
			::= { zhoneDslPerfDataEntry 2 }

		zhoneDslPerfLols OBJECT-TYPE
			SYNTAX Counter32
			MAX-ACCESS read-only
			STATUS current
			DESCRIPTION
				"Count of the number of Loss of Link failures since agent reset."
			::= { zhoneDslPerfDataEntry 3 }

		zhoneDslPerfInits OBJECT-TYPE
			SYNTAX Counter32
			MAX-ACCESS read-only
			STATUS current
			DESCRIPTION
				"Count of the line initialization attempts since agent reset. Includes
				both successful and failed attempts."
			::= { zhoneDslPerfDataEntry 4 }

		zhoneDslPerfCur15MinTimeElapsed	OBJECT-TYPE
			SYNTAX Gauge32
			UNITS	"seconds"
			MAX-ACCESS	read-only
			STATUS	current
			DESCRIPTION
				"The number of seconds elapsed since the start of the
				 current measurement period."
			::= { zhoneDslPerfDataEntry	5 }

		zhoneDslPerfCur15MinLofs OBJECT-TYPE
			SYNTAX Gauge32
			UNITS	"seconds"
			MAX-ACCESS read-only
			STATUS current
			DESCRIPTION
				"Count of the number of Loss of Framing failures in the current 15 minute interval."
			::= { zhoneDslPerfDataEntry 6 }

		zhoneDslPerfCur15MinLoss OBJECT-TYPE
			SYNTAX Gauge32
			UNITS	"seconds"
			MAX-ACCESS read-only
			STATUS current
			DESCRIPTION
				"Count of seconds in the current 15 minute interval when there was a Loss of Signal."
			::= { zhoneDslPerfDataEntry 7 }

		zhoneDslPerfCur15MinLols OBJECT-TYPE
			SYNTAX Gauge32
			UNITS "seconds"
			MAX-ACCESS read-only
			STATUS current
			DESCRIPTION
				"Count of seconds in the current 15 minute interval when there was of Loss of Link."
			::= { zhoneDslPerfDataEntry 8 }

		zhoneDslPerfCur15MinInits OBJECT-TYPE
			SYNTAX Counter32
			MAX-ACCESS read-only
			STATUS current
			DESCRIPTION
				"Count of the line initialization attempts in the current 15 minute interval.
				Includes both successful and failed attempts."
			::= { zhoneDslPerfDataEntry 9 }


		zhoneDslAlarmProfileTable OBJECT-TYPE
			SYNTAX SEQUENCE OF ZhoneDslAlarmProfileEntry
			MAX-ACCESS not-accessible
			STATUS current
			DESCRIPTION
				"This table contains information for Alarm conditions. One entry in this
				table reflects a profile defined by a manager which can be used to define
				alarm conditions for a modem."
			::= { zhoneDsl 6 }

		zhoneDslAlarmProfileEntry OBJECT-TYPE
			SYNTAX ZhoneDslAlarmProfileEntry
			MAX-ACCESS not-accessible
			STATUS current
			DESCRIPTION
				"An entry in the zhoneDslAlarmProfile Table."
			INDEX { IMPLIED zhoneDslAlarmProfileName }
			::= { zhoneDslAlarmProfileTable 1 }

		ZhoneDslAlarmProfileEntry ::=
			SEQUENCE {
				zhoneDslAlarmProfileName
					ZhoneAdminString,
				zhoneDslThreshold15MinLoss
					INTEGER,
				zhoneDslThreshold15MinLols
					INTEGER,
				zhoneDslThreshold15MinLofs
					INTEGER,
				zhoneDslAlarmProfileRowStatus
					ZhoneAdminString
			 }

		zhoneDslAlarmProfileName OBJECT-TYPE
			SYNTAX ZhoneAdminString
			MAX-ACCESS not-accessible
			STATUS current
			DESCRIPTION
				"Configuration profile name. Used by the zhoneDslLineConfigProfile entry
				to map zhoneDslLine Entry to the appropriate profile.

				              When `dynamic' profiles are implemented, the profile
				              name is user specified.  Also, the system will always
				              provide a default profile whose name is `DEFVAL'.

				              When `static' profiles are implemented, there is an
				              one-to-one relationship between each line and its
				              profile.  In which case, the profile name will
				              need to algorithmically represent the Line's ifIndex.
				              Therefore, the profile's name is a decimal zed string
				              of the ifIndex that is fixed-length (i.e., 10) with
				              leading zero(s).  For example, the profile name for
				              ifIndex which equals '15' will be '0000000015'."
			::= { zhoneDslAlarmProfileEntry 1 }

		zhoneDslThreshold15MinLoss OBJECT-TYPE
			SYNTAX INTEGER (0..900)
			UNITS "seconds"
			MAX-ACCESS read-create
			STATUS current
			DESCRIPTION
				"The number of Loss of signal seconds on a DSL interface within any
				given 15 minutes performance data collection period, which causes the
				SNMP agent to send a TRAP. 0 will disable the trap."
			DEFVAL { 0 }
			::= { zhoneDslAlarmProfileEntry 2 }

		zhoneDslThreshold15MinLols OBJECT-TYPE
			SYNTAX INTEGER (0..900)
			UNITS "seconds"
			MAX-ACCESS read-create
			STATUS current
			DESCRIPTION
				"The number of Loss of link seconds on a DSL interface within any
				given 15 minutes performance data collection period, which causes the
				SNMP agent to send a TRAP. 0 will disable the trap."
			DEFVAL { 0 }
			::= { zhoneDslAlarmProfileEntry 3 }

		zhoneDslThreshold15MinLofs OBJECT-TYPE
			SYNTAX INTEGER (0..900)
			UNITS "seconds"
			MAX-ACCESS read-create
			STATUS current
			DESCRIPTION
				"The number of Loss of framing seconds on a DSL interface within any
				given 15 minutes performance data collection period, which causes the
				SNMP agent to send a TRAP. 0 will disable the trap."
			DEFVAL { 0 }
			::= { zhoneDslAlarmProfileEntry 4 }

		zhoneDslAlarmProfileRowStatus OBJECT-TYPE
			SYNTAX ZhoneAdminString
			MAX-ACCESS read-write
			STATUS current
			DESCRIPTION
				"RowStatus field to control deletion/addition of entries in this
				table. Minimal fields to be 'set' for a creation is:"
			::= { zhoneDslAlarmProfileEntry 5 }


	END

--
-- phyDsl.mib
--
