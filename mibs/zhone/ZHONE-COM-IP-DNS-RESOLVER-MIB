--
-- comIpDNSResolver.mib
-- MIB generated by MG-SOFT Visual MIB Builder Version 2.1 Build 199
-- Friday, September 29, 2000 at 09:38:06
--

    ZHONE-COM-IP-DNS-RESOLVER-MIB DEFINITIONS ::= BEGIN

        IMPORTS
            SnmpAdminString
                FROM SNMP-FRAMEWORK-MIB
            IpAddress, OBJECT-TYPE, MODULE-IDENTITY, OBJECT-IDENTITY
                FROM SNMPv2-SMI
            rdEntry, rdIndex
                FROM ZHONE-COM-IP-RD-MIB
            zhoneIp, zhoneModules
                FROM Zhone
            ZhoneAdminString, ZhoneRowStatus
                FROM Zhone-TC;


-- This MIB contains configuration information for the
-- DNS Resolver.
--
-- statistic profile for dnsResolver
--
--
-- profile for objects in the resolver table
--
--
-- profile for objects in the hosts table
--
--
        comIpDnsResolver MODULE-IDENTITY
            LAST-UPDATED "0009291000Z"
            ORGANIZATION
                "Zhone Technologies, Inc."
            CONTACT-INFO
                "Postal:
                           Zhone Technologies, Inc.
                           @ Zhone Way
                           7001 Oakport Street
                           Oakland, CA  94621
                           USA
                Toll-Free: +1 877-ZHONE20 (+1 877-946-6320)
                      Tel: +1-510-777-7000
                      Fax: +1-510-777-7001
                   E-mail: support@zhone.com"
            DESCRIPTION
                "DNS Resolver MIB
                IP Software
                Minneapolis, MN"
            REVISION "0009111608Z"
            DESCRIPTION
                "V01.00.00 - Initial Release"
            REVISION "0009290933Z"
            DESCRIPTION
                "V01.00.01 - Added ZHONE-KEYWORD markup"
            ::= { zhoneModules 62 }



--
-- Node definitions
--

-- Zhone DNS Resolver Management Information Base
-- (derived from RFC 1612)
        dnsResolver OBJECT-IDENTITY
            STATUS current
            DESCRIPTION
                "DNS Resolver objects based on RFC 1612."
            ::= { zhoneIp 12 }

-- Resolver Configuration Group
--
--
        zhDnsResConfigImplementIdent OBJECT-TYPE
            SYNTAX ZhoneAdminString
            MAX-ACCESS read-only
            STATUS current
            DESCRIPTION
                "The implementation identification string for the
                resolver software in use on the system, for example;
                `RES-2.1'.  The maximum length for this name
                is 32 characters."
            REFERENCE
                "See RFC1612: dnsResConfig.dnsResConfigImplementIdent"
            ::= { dnsResolver 1 }

--  Config Table (start)
        zhDnsResConfigTable OBJECT-TYPE
            SYNTAX SEQUENCE OF ZhDnsResConfigEntry
            MAX-ACCESS not-accessible
            STATUS current
            DESCRIPTION
                "Table of nameservers information used by the resolver
                to send a query.  Rows are created and destroyed whenever
                a routing domain is created or destroyed.  Rows cannot be
                created or destroyed via SNMP."
            ::= { dnsResolver 2 }

        zhDnsResConfigEntry OBJECT-TYPE
            SYNTAX ZhDnsResConfigEntry
            MAX-ACCESS not-accessible
            STATUS current
            DESCRIPTION
                "A single routing domain in a single subnet."
            AUGMENTS { rdEntry }
            ::= { zhDnsResConfigTable 1 }

        ZhDnsResConfigEntry ::=
            SEQUENCE {
                zhDnsResConfigQueryOrder
                    INTEGER,
                zhDnsResConfigDomainName
                    SnmpAdminString,
                zhDnsResConfigFirstNameServer
                    IpAddress,
                zhDnsResConfigSecondNameServer
                    IpAddress,
                zhDnsResConfigThirdNameServer
                    IpAddress
             }

--
        zhDnsResConfigQueryOrder OBJECT-TYPE
            SYNTAX INTEGER
                {
                hostsFirst(1),
                dnsFirst(2),
                dnsOnly(3)
                }
            MAX-ACCESS read-write
            STATUS current
            DESCRIPTION
                "Kind of resolver query for this routing domain:

                hostsFirst(1) searches the local hosts table first,
                then the list of nameservers

                dnsFirst(2) searches the list of nameservers first, then
                the local hosts table

                dnsOnly(3) searches only the list of nameservers"
            DEFVAL { hostsFirst }
            ::= { zhDnsResConfigEntry 1 }

-- The default for this object is the empty string.
--
--
        zhDnsResConfigDomainName OBJECT-TYPE
            SYNTAX SnmpAdminString
            MAX-ACCESS read-write
            STATUS current
            DESCRIPTION
                "Domain name to use for searches in this routing domain.
                The maximum length for this name is 255 characters."
            ::= { zhDnsResConfigEntry 2 }

--
--
        zhDnsResConfigFirstNameServer OBJECT-TYPE
            SYNTAX IpAddress
            MAX-ACCESS read-write
            STATUS current
            DESCRIPTION
                "The IP address of the first/primary name server for this
                routing domain."
            DEFVAL { '00000000'h }
            ::= { zhDnsResConfigEntry 3 }

--
        zhDnsResConfigSecondNameServer OBJECT-TYPE
            SYNTAX IpAddress
            MAX-ACCESS read-write
            STATUS current
            DESCRIPTION
                "The IP address of the secondary name server for this routing
                domain.  This nameserver is queried if the first nameserver cannot
                resolve the query.  If a secondary name server has not been defined, this
                field is set to 0.0.0.0"
            DEFVAL { '00000000'h }
            ::= { zhDnsResConfigEntry 4 }

--
        zhDnsResConfigThirdNameServer OBJECT-TYPE
            SYNTAX IpAddress
            MAX-ACCESS read-write
            STATUS current
            DESCRIPTION
                "The IP address of the third name server for this routing
                domain.  This nameserver is queried if the first nameserver and the
                secondary nameserver cannot resolve the query.  If a third name server
                has not been defined, this field is set to 0.0.0.0"
            DEFVAL { '00000000'h }
            ::= { zhDnsResConfigEntry 5 }
-- Config Table (end)

-- Local Hosts Table Config
        zhDnsResHostsTable OBJECT-TYPE
            SYNTAX SEQUENCE OF ZhDnsResHostsEntry
            MAX-ACCESS not-accessible
            STATUS current
            DESCRIPTION
                "This is the local hosts table (ie. /etc/hosts) for each
                routing domain."
            ::= { dnsResolver 3 }

        zhDnsResHostsEntry OBJECT-TYPE
            SYNTAX ZhDnsResHostsEntry
            MAX-ACCESS not-accessible
            STATUS current
            DESCRIPTION
                "A particular host entry per routing domain.
                Rows are created and destroyed whenever a hostname within a
                routing domain is created and destroyed, ie. rows are added
                by setting zhDnsResHostsRowStatus to createAndGo.  Rows are
                removed by setting zhDnsResHostsRowStatus to destroy.
                The minimum columns required to create new entry are
                zhDnsResHostsIpAddress and zhDnsResHostsName."
            INDEX { rdIndex, zhDnsResHostsIpAddress }
            ::= { zhDnsResHostsTable 1 }

        ZhDnsResHostsEntry ::=
            SEQUENCE {
                zhDnsResHostsIpAddress
                    IpAddress,
                zhDnsResHostsName
                    SnmpAdminString,
                zhDnsResHostsAlias1
                    SnmpAdminString,
                zhDnsResHostsAlias2
                    SnmpAdminString,
                zhDnsResHostsAlias3
                    SnmpAdminString,
                zhDnsResHostsAlias4
                    SnmpAdminString,
                zhDnsResHostsRowStatus
                    ZhoneRowStatus
             }

        zhDnsResHostsIpAddress OBJECT-TYPE
            SYNTAX IpAddress
            MAX-ACCESS not-accessible
            STATUS current
            DESCRIPTION
                "The IP address of this entry.  127.1 (127.0.0.1) is a valid
                ip address."
            ::= { zhDnsResHostsEntry 1 }

--
        zhDnsResHostsName OBJECT-TYPE
            SYNTAX SnmpAdminString
            MAX-ACCESS read-create
            STATUS current
            DESCRIPTION
                "Hostname for this entry.  The hostname can be either fully-qualified or
                hostname only.  The maximum length for this name is 255 characters."
            ::= { zhDnsResHostsEntry 2 }

--
        zhDnsResHostsAlias1 OBJECT-TYPE
            SYNTAX SnmpAdminString
            MAX-ACCESS read-create
            STATUS current
            DESCRIPTION
                "Hostname alias for this entry.  The hostname can be either
                fully-qualified or hostname only.  The maximum length for this
                name is 255 characters."
            ::= { zhDnsResHostsEntry 3 }

--
        zhDnsResHostsAlias2 OBJECT-TYPE
            SYNTAX SnmpAdminString
            MAX-ACCESS read-create
            STATUS current
            DESCRIPTION
                "Another hostname alias for this entry.  The hostname can be either
                fully-qualified or hostname only.  The maximum length for this
                name is 255 characters."
            ::= { zhDnsResHostsEntry 4 }

--
        zhDnsResHostsAlias3 OBJECT-TYPE
            SYNTAX SnmpAdminString
            MAX-ACCESS read-create
            STATUS current
            DESCRIPTION
                "Another hostname alias for this entry.  The hostname can be either
                fully-qualified or hostname only.  The maximum length for this
                name is 255 characters."
            ::= { zhDnsResHostsEntry 5 }

--
        zhDnsResHostsAlias4 OBJECT-TYPE
            SYNTAX SnmpAdminString
            MAX-ACCESS read-create
            STATUS current
            DESCRIPTION
                "Another hostname alias for this entry.  The hostname can be either
                fully-qualified or hostname only.  The maximum length for this
                name is 255 characters."
            ::= { zhDnsResHostsEntry 6 }

        zhDnsResHostsRowStatus OBJECT-TYPE
            SYNTAX ZhoneRowStatus
            MAX-ACCESS read-create
            STATUS current
            DESCRIPTION
                "The row status variable, used according to
                row installation and removal conventions."
            REFERENCE
                "See ZHONE-TC-MIB for definition of ZhoneRowStatus."
            DEFVAL { active }
            ::= { zhDnsResHostsEntry 7 }


    END

--
-- comIpDNSResolver.mib
--
