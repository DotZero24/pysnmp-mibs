NTNTECH-CHASSIS-CONFIGURATION-MIB DEFINITIONS ::= BEGIN

--	****************************************************************
--  Enterprise:
--   	Paradyne Corporation.
--
--  ContactInfo:
--    	Paradyne Corporation
--     	8545 126th Avenue North
--     	Largo, FL 33773
--     	phone: +1 (727) 530 2000
--     	email: support@paradyne.com
--		www:   http://www.nettonet.com/support/
--
--  Description:
--    	ntntech-chassis-configuration-MIB.my
--    	Revision: 1.02.02
--    	Part Number: xx-xxxx-xx
--    	Date: November 17, 2004
--
--    	This module provides explicit definitions for the Net to
--		Net Technologies naming	tree below:
--
--    	nettonettech { enterprises 8059 }
--
--    	This module will be extended, as additional sub-sections
--    	of this naming tree are defined.
--
--  Disclaimer:
--	   	This is an extremely preliminary MIB module and is subject
--		to change at any time therefore, use at your own risk.
--
-- 	Copyright (c) 2000 - 2004 by Paradyne Corporation.
-- 	All rights reserved.

-- ****************************************************************
IMPORTS
	ntntechChassis,NtnDefaultGateway,NtnSubnetMask,NtnTimeTicks,
	NtnDisplayString							FROM NTNTECH-ROOT-MIB
   	OBJECT-TYPE, MODULE-IDENTITY,IpAddress		FROM SNMPv2-SMI
   	TEXTUAL-CONVENTION							FROM SNMPv2-TC;
-- ****************************************************************
ntntechChassisConfigurationMIB MODULE-IDENTITY
    LAST-UPDATED "0411170200Z"  -- November 17, 2004
    ORGANIZATION "Paradyne Corporation"
    CONTACT-INFO
        "Paradyne Corporation
        8545 126th Avenue North
        Largo, FL 33773

        phone: +1 (727) 530 2000
        email: support@paradyne.com
        www:   http://www.nettonet.com/support/"

    DESCRIPTION
         "This mib module defines an SNMP API to manage the Paradyne Corporation's
         DSLAM chassis parameters.  These parameter settings are specifically associated
         with the the MUM200-2 and MUM2000-2 modules and the Mini and Micro DSLAMs.
         The interface types are described below,


         AMD8000-12
	     12-Port ADSL Mini DSLAMs With Full Rate and G.lite Operational Modes

         SMD2000-12, SMD2000Q-12, SMD2000G-12
         12-Port SDSL Mini DSLAMs: AC and DC Versions with Cap, 2B1Q
         and G.SHDSL line encoding

         SuD2011_12T, SuD2011_12E, SuD2003_12T, SuD2003_12E
         12-Port SDSL Micro DSLAMs: Cap, 2B1Q and G.SHDSL line encoding

         SuD2011_6T, SuD2011_6E, SuD2002_6T, SuD2002_6E
         6-Port SDSL Micro DSLAMs: Cap, 2B1Q and G.SHDSL line encoding

         MUM200-2, MUM2000-2
         Multiplexer Uplink Module with Dual Uplink Interface Module Capacity

         UIM-10/100
         Uplink Interface Module

         UIM-DS3
         DS3 Uplink Interface Module

         UIM-E1
         E1 Uplink Interface Module

         UIM-E3
         E3 Uplink Interface Module

         UIM-T1
         T1 Uplink Interface Module    "

    REVISION     "0208131112Z"
    DESCRIPTION
        "Added the mumCfgAdvanced OID.
         Added the mumCfgManagementPort OID."

    REVISION     "0208280912Z"
    DESCRIPTION
        "New Release - v1.01.00"

    REVISION     "0210110913Z"
    DESCRIPTION
        "Added OID mgmtPortCfgType to the mgmtPortCfgTable."

    REVISION     "0210220200Z"
    DESCRIPTION
        "New Release - v1.01.01"

    REVISION     "0211041258Z"
    DESCRIPTION
        "Added the values uplink3(4), uplink4(5), and mgmt(6) to the mumCfgInterConnection
        OID."

    REVISION     "0403151015Z"
    DESCRIPTION
        "Added OID mumCfgCommitChange to the mumCfgTable."

    REVISION "0404271116Z"
    DESCRIPTION
    	"Updated the description associated with the mumCfgCommitChange OID."

    REVISION "0410110909Z"
    DESCRIPTION
    	"Updated the description associated with the mumCfgCommitChange OID again.  Adjusted
    	the copyright date and references to Paradyne."

    REVISION "0411170958Z"
    DESCRIPTION
    	"New Release -- version 1.02.01"

::= { ntntechChassis 1 }


--	Objects

chsCfgMIBObjects OBJECT IDENTIFIER ::= { ntntechChassisConfigurationMIB 1 }

--	NTNTECH Chassis Configuration (chsCfg) MIB objects for MUM200/2000 modules
--  or Mini and Micro DSLAMs.

chsCfgParameterConfiguration OBJECT IDENTIFIER ::= { chsCfgMIBObjects 1 }

--	NTNTECH Chassis Configuration (chsCfg) Parameter Configuration for MUM200/2000 modules
--  or Mini and Micro DSLAMs.
--
--			IPD12000 	- slots 13,14  MIB index - 1,2 respecitively
--			IPD4000	 	- slot 5       MIB index - 1
--			Mini DSLAM 	- NA           MIB index - 1
--			Micro DSLAM	- NA		   MIB index - 1
--

prmCfgMultiplexerUplinkModule OBJECT IDENTIFIER ::= { chsCfgParameterConfiguration 1 }

mumCfgNotes	OBJECT-TYPE
    SYNTAX      NtnDisplayString
    MAX-ACCESS  read-write
    STATUS      current
    DESCRIPTION
    "The chassis system 'Notes' field is to be used as a scratchpad
    (i.e. chassis id or name) by the administrator. The default value is blank.
    The length of string must not exceed 128 alpha-numeric characters."
	::= { prmCfgMultiplexerUplinkModule 1 }

mumCfgTable OBJECT-TYPE
	SYNTAX	SEQUENCE OF MumCfgEntry
    MAX-ACCESS  not-accessible
    STATUS      current
    DESCRIPTION
    "A list of MUM200-2/2000-2 module or Mini/Micro DSLAM entries."
    ::= { prmCfgMultiplexerUplinkModule 2 }

mumCfgEntry OBJECT-TYPE
   	SYNTAX			MumCfgEntry
   	MAX-ACCESS  	not-accessible
   	STATUS      	current
   	DESCRIPTION
    "An entry containing management information applicable to a MUM200-2/MUM2000-2
    module or Mini/Micro DSLAM."
    INDEX   { mumCfgIndex }
    ::= { mumCfgTable 1 }

MumCfgEntry ::=
		SEQUENCE {
			mumCfgIndex	 				INTEGER,
           	mumCfgIpAddress				IpAddress,
           	mumCfgSubnetMask			IpAddress,
          	mumCfgDefaultGateway     	IpAddress,
           	mumCfgInbandMgmt			INTEGER,
           	mumCfgInbandMGMTVlanID		INTEGER,
           	mumCfgInterConnection		INTEGER,
           	mumCfgCommitChange			INTEGER
        }

	mumCfgIndex 	OBJECT-TYPE
   		SYNTAX      INTEGER (1..2)
   		MAX-ACCESS  read-only
   		STATUS      current
   		DESCRIPTION
        "Translates to the physical slot number that a MUM200-2/2000-2 module
        exists within a chassis. The Mini/Micro DSLAMs' physical location is
        set to 1 by default.  See below,

         chassis type     physical location(s) translation
         ------------     --------------------------------
           IPD12000		  MUM in slots 13,14 = mumCfgIndex 1,2 respecitively
           IPD4000		  MUM in slot 5      = mumCfgIndex 1
           Mini DSLAM	  NA				 = mumCfgIndex 1
           Micro DSLAM	  NA				 = mumCfgIndex 1"
    	::= { mumCfgEntry 1 }

   	mumCfgIpAddress 	OBJECT-TYPE
       	SYNTAX      IpAddress
       	MAX-ACCESS  read-write
       	STATUS      current
       	DESCRIPTION
        "IP Address assigned to a MUM200-2/2000-2 module or Mini/Micro DSLAM.
        This parameter is initially set to a default value, i.e 192.168.254.252
        for a MUM200-2/2000-2 module located in slot 13 of an IPD12000, slot 5
        of an IPD4000 DSLAM and a Mini/Micro DSLAM. The default value of
        192.168.254.253 will be for a MUM200-2/2000-2 module located in slot 14 of
        an IPD12000 (duplicate IP addresses	are not allowed). These default
        values can be modified by the user."
       	::= { mumCfgEntry 2 }

   	mumCfgSubnetMask OBJECT-TYPE
       	SYNTAX      IpAddress
       	MAX-ACCESS  read-write
       	STATUS      current
       	DESCRIPTION
        "The Subnet Mask assigned to a MUM200-2/2000-2 module or Mini/Micro DSLAM.
        This parameter is assiged by the user, the default value is 255.255.255.0."
        ::= { mumCfgEntry 3 }

   	mumCfgDefaultGateway OBJECT-TYPE
       	SYNTAX      IpAddress
       	MAX-ACCESS  read-write
       	STATUS      current
       	DESCRIPTION
        "The Default Gateway assigned to a MUM200-2/2000-2 module or Mini/Micro DSLAM.
        This value is assiged by the user, the default value is 0.0.0.0."
       	::= { mumCfgEntry 4 }

   	mumCfgInbandMgmt OBJECT-TYPE
       	SYNTAX      INTEGER {
       						on(1),	-- parameter enabled
               				off(2)	-- parameter disabled
       				}

       	MAX-ACCESS  read-write
       	STATUS      current
       	DESCRIPTION
        "Inband management feature, when enabled [ON(1)], allows access to the
        DSLAM via the network against an assigned IP address, subnet mask,
        and default gateway."
		::= { mumCfgEntry 5 }

   	mumCfgInbandMGMTVlanID OBJECT-TYPE
       	SYNTAX      INTEGER (0..4085)
       	MAX-ACCESS  read-write
       	STATUS      current
       	DESCRIPTION
        "The IP DSLAM supports 802.1Q Virtual LANs (VLANs). This parameter
        configuration applies to the inband management traffic only.

        It does not apply to out of band traffic received from the MGMT port.

        Note: for the case where the chassis type is an IPD12000 loaded with
              two MUMs, the setting of this parameter will affect both."
       	::= { mumCfgEntry 6 }

	mumCfgInterConnection OBJECT-TYPE
       	SYNTAX  INTEGER {
       				neither(1),
       				uplink1(2),
       				uplink2(3),
                    uplink3(4),
                    uplink4(5),
					mgmt(6)
       			}
       	MAX-ACCESS  read-write
       	STATUS      current
       	DESCRIPTION
        "IPD12000 or IPD4000 DSLAM interconnect configuration provides the system
        manager the ability to daisy-chain one IP DSLAM to another so that a single
        router may be used for all DSLAMs in the chain."
       	::= { mumCfgEntry 7 }

     mumCfgCommitChange OBJECT-TYPE
       	SYNTAX	INTEGER {
       					disabled(0),	-- do not commit a change
       					enabled(1)		-- commit a change
       			}

       	MAX-ACCESS  read-write
       	STATUS      current
       	DESCRIPTION
        "Set to enabled(1) in order to commit the latest changes to the IP address, subnetmask,
         default gateway chassis parameters.  This is only applicable to the SNE2040G-P and the
         SNE2040G-S."
       	::= { mumCfgEntry 8 }



mumCfgUplinkInterfaceModule OBJECT IDENTIFIER ::= { prmCfgMultiplexerUplinkModule 3 }

-- The ethernet table is simply a place holder for future reference.

uimCfgEthTable OBJECT-TYPE
	SYNTAX		SEQUENCE OF UimCfgEthEntry
   	MAX-ACCESS  not-accessible
   	STATUS      current
   	DESCRIPTION
    "A list of ethernet Uplink Interface Module (UIM) entries."
   	::= { mumCfgUplinkInterfaceModule 1 }

uimCfgEthEntry OBJECT-TYPE
    SYNTAX		UimCfgEthEntry
    MAX-ACCESS  not-accessible
    STATUS      current
    DESCRIPTION
    "An entry containing information applicable to an ethernet Uplink Interface Module (UIM)."
	INDEX   { uimCfgEthMumIndex, uimCfgEthIndex }
    ::= { uimCfgEthTable 1 }

   	UimCfgEthEntry ::=
       SEQUENCE {
           uimCfgEthMumIndex			INTEGER,
           uimCfgEthIndex				INTEGER,
           uimCfgEthRxTxRate			INTEGER,
           uimCfgEthDuplex				INTEGER
       }

	uimCfgEthMumIndex OBJECT-TYPE
       	SYNTAX      INTEGER (1..2)
       	MAX-ACCESS  read-only
       	STATUS      current
       	DESCRIPTION
        "Translates to the physical slot number that a MUM200-2/2000-2 module
        exists within a chassis. The Mini/Micro DSLAMs' physical location is
        set to 1 by default.  See below,

         chassis type     physical location(s) translation
         ------------     --------------------------------
           IPD12000       MUM in slots 13,14 = uimCfgEthMumIndex 1,2 respecitively
           IPD4000        MUM in slot 5      = uimCfgEthMumIndex 1
           Mini DSLAM     NA				 = uimCfgEthMumIndex 1
           Micro DSLAM    NA				 = uimCfgEthMumIndex 1

        Note: when configuring an ethernet UIM, the user must enter the
              index of the MUM, see above table, that corresponds with the
              IP address of the remote SNMP agent."
        ::= { uimCfgEthEntry 1 }

   	uimCfgEthIndex OBJECT-TYPE
       	SYNTAX      INTEGER (1..4)
       	MAX-ACCESS  read-only
       	STATUS      current
       	DESCRIPTION
        "The physical slot used to access the UIM in the MUM200-2/2000-2 module or
        Mini/Micro DSLAM."
       	::= { uimCfgEthEntry 2 }

    uimCfgEthRxTxRate OBJECT-TYPE
       	SYNTAX	INTEGER {
       				uimEthAutoNegotiate(0),
       				uimEth10(1),
       				uimEth100(2),
       				uimEthGig(3)
       			}
       	MAX-ACCESS  read-write
       	STATUS      current
       	DESCRIPTION
        "The RxTx rate for an ethernet UIM."
        ::= { uimCfgEthEntry 3 }

    uimCfgEthDuplex OBJECT-TYPE
       	SYNTAX	INTEGER {
       				uimEthAutoNegotiate(0),
       				uimEthHalf(1),
       				uimEthFull(2)
       			}
       	MAX-ACCESS  read-write
       	STATUS      current
       	DESCRIPTION
        "The current duplex setting for an ethernet UIM."
        ::= { uimCfgEthEntry 4 }


uimCfgT1Table OBJECT-TYPE
	SYNTAX		SEQUENCE OF UimCfgT1Entry
   	MAX-ACCESS  not-accessible
   	STATUS      current
   	DESCRIPTION
    "A list of T1 Uplink Interface Module (UIM) entries."
   	::= { mumCfgUplinkInterfaceModule 2 }

uimCfgT1Entry OBJECT-TYPE
    SYNTAX		UimCfgT1Entry
    MAX-ACCESS  not-accessible
    STATUS      current
    DESCRIPTION
    "An entry containing information applicable to a T1 Uplink Interface Module (UIM)."
	INDEX   { uimCfgT1MumIndex, uimCfgT1Index }
    ::= { uimCfgT1Table 1 }

   	UimCfgT1Entry ::=
       SEQUENCE {
           uimCfgT1MumIndex			INTEGER,
           uimCfgT1Index			INTEGER,
           uimCfgT1Frame	    	INTEGER,
           uimCfgT1LineCode			INTEGER,
           uimCfgT1LineBuildout		INTEGER
       }

	uimCfgT1MumIndex OBJECT-TYPE
       	SYNTAX      INTEGER (1..2)
       	MAX-ACCESS  read-only
       	STATUS      current
       	DESCRIPTION
        "Translates to the physical slot number that a MUM200-2/2000-2 module
        exists within a chassis. The Mini/Micro DSLAMs' physical location is
        set to 1 by default.  See below,

         chassis type     physical location(s) translation
         ------------     --------------------------------
           IPD12000       MUM in slots 13,14 = uimCfgT1MumIndex 1,2 respecitively
           IPD4000        MUM in slot 5      = uimCfgT1MumIndex 1
           Mini DSLAM     NA				 = uimCfgT1MumIndex 1
           Micro DSLAM    NA				 = uimCfgT1MumIndex 1


         Note: when configuring a T1 UIM, the user must enter the
               index of the MUM, see above table, that corresponds with the
               IP address of the remote SNMP agent."
       	::= { uimCfgT1Entry 1 }

   	uimCfgT1Index OBJECT-TYPE
       	SYNTAX      INTEGER (1..4)
       	MAX-ACCESS  read-only
       	STATUS      current
       	DESCRIPTION
        "The physical slot used to access the UIM in the MUM200-2/2000-2 module or
        Mini/Micro DSLAM."
       	::= { uimCfgT1Entry 2 }

   uimCfgT1Frame OBJECT-TYPE
       	SYNTAX	INTEGER {
       				uimT1ESF(1),
					uimT1SFD4(2)
       			}
       	MAX-ACCESS  read-write
       	STATUS      current
       	DESCRIPTION
        "The frame type parameter for a T1 UIM."
        ::= { uimCfgT1Entry 3 }

    uimCfgT1LineCode OBJECT-TYPE
       	SYNTAX	INTEGER {
       				uimT1B8ZS(1),
					uimT1AMI(2)
       			}
       	MAX-ACCESS  read-write
       	STATUS      current
       	DESCRIPTION
        "The line code parameter for a T1 UIM."
        ::= { uimCfgT1Entry 4 }

    uimCfgT1LineBuildout OBJECT-TYPE
       	SYNTAX	INTEGER {
       				uimT10db(1),
					uimT1N7p5db(2),
					uimT1N15db(3),
					uimT1N22p5db(4)
       			}
       	MAX-ACCESS  read-write
       	STATUS      current
       	DESCRIPTION
        "The line buildout parameter for a T1 UIM."
        ::= { uimCfgT1Entry 5 }

uimCfgE1Table OBJECT-TYPE
	SYNTAX		SEQUENCE OF UimCfgE1Entry
   	MAX-ACCESS  not-accessible
   	STATUS      current
   	DESCRIPTION
    "A list of E1 Uplink Interface Module (UIM) entries."
   	::= { mumCfgUplinkInterfaceModule 3 }

uimCfgE1Entry OBJECT-TYPE
    SYNTAX		UimCfgE1Entry
    MAX-ACCESS  not-accessible
    STATUS      current
    DESCRIPTION
    "An entry containing information applicable to an E1 Uplink Interface Module (UIM)."
	INDEX   { uimCfgE1MumIndex, uimCfgE1Index }
    ::= { uimCfgE1Table 1 }

   	UimCfgE1Entry ::=
       SEQUENCE {
           uimCfgE1MumIndex			INTEGER,
           uimCfgE1Index			INTEGER,
           uimCfgE1Frame	    	INTEGER,
           uimCfgE1LineCode			INTEGER
       }

	uimCfgE1MumIndex OBJECT-TYPE
       	SYNTAX      INTEGER (1..2)
       	MAX-ACCESS  read-only
       	STATUS      current
       	DESCRIPTION
        "Translates to the physical slot number that a MUM200-2/2000-2 module
        exists within a chassis. The Mini/Micro DSLAMs' physical location is
        set to 1 by default.  See below,

         chassis type     physical location(s) translation
         ------------     --------------------------------
           IPD12000       MUM in slots 13,14 = uimCfgE1MumIndex 1,2 respecitively
           IPD4000        MUM in slot 5      = uimCfgE1MumIndex 1
           Mini DSLAM     NA				 = uimCfgE1MumIndex 1
           Micro DSLAM    NA				 = uimCfgE1MumIndex 1

           Note: when configuring an E1 UIM, the user must enter the
                 index of the MUM, see above table, that corresponds with the
                 IP address of the remote SNMP agent."
       	::= { uimCfgE1Entry 1 }

   	uimCfgE1Index OBJECT-TYPE
       	SYNTAX      INTEGER (1..4)
       	MAX-ACCESS  read-only
       	STATUS      current
       	DESCRIPTION
        "The physical slot used to access the UIM in the MUM200-2/2000-2 module or
        Mini/Micro DSLAM."
       	::= { uimCfgE1Entry 2 }

    uimCfgE1Frame OBJECT-TYPE
       	SYNTAX	INTEGER {
       				uimE1CRC(1),
       				uimE1NoCRC(2)
       			}
       	MAX-ACCESS  read-write
       	STATUS      current
       	DESCRIPTION
        "The frame type parameter for an E1 UIM."
        ::= { uimCfgE1Entry 3 }

    uimCfgE1LineCode OBJECT-TYPE
       	SYNTAX	INTEGER {
       				uimE1HDB3(1),
       				uimE1AMI(2)
       			}
       	MAX-ACCESS  read-write
       	STATUS      current
       	DESCRIPTION
        "The line code parameter for an E1 UIM."
        ::= { uimCfgE1Entry 4 }

mumSNMPConfiguration OBJECT IDENTIFIER ::= { prmCfgMultiplexerUplinkModule 4 }

snmpCfgNoticeIpTable OBJECT-TYPE
	SYNTAX	SEQUENCE OF SnmpCfgNoticeIpEntry
    MAX-ACCESS  not-accessible
    STATUS      current
    DESCRIPTION
    "A list of SNMP trap notification Ip Addresses."
    ::= { mumSNMPConfiguration 1 }

snmpCfgNoticeIpEntry OBJECT-TYPE
   	SYNTAX			SnmpCfgNoticeIpEntry
   	MAX-ACCESS  	not-accessible
   	STATUS      	current
   	DESCRIPTION
    "An entry containing SNMP information applicable to a MUM200-2/MUM2000-2 module
    or Mini/Micro DSLAM."
    INDEX   { snmpCfgNoticeIndex }
    ::= { snmpCfgNoticeIpTable 1 }

SnmpCfgNoticeIpEntry ::=
		SEQUENCE {
			snmpCfgNoticeIndex	 		INTEGER,
           	snmpCfgNoticeIpAddress		IpAddress
        }

	snmpCfgNoticeIndex 	OBJECT-TYPE
   		SYNTAX      INTEGER (1..4)
   		MAX-ACCESS  read-only
   		STATUS      current
   		DESCRIPTION
        "An integer value that points to one of four trap notification IP addresses."
    	::= { snmpCfgNoticeIpEntry 1 }

   	snmpCfgNoticeIpAddress 	OBJECT-TYPE
       	SYNTAX      IpAddress
       	MAX-ACCESS  read-write
       	STATUS      current
       	DESCRIPTION
        "IP Address of the location or computer to which you would like trap
        notifications sent. The default value is 0.0.0.0 and it can be modified
        by the user."
       	::= { snmpCfgNoticeIpEntry 2 }

snmpCfgAuthenticationTrapState OBJECT-TYPE
    	SYNTAX      INTEGER {
    					enabled(1),
    					disabled(2)
    		    }
       	MAX-ACCESS  read-write
       	STATUS      current
       	DESCRIPTION
       	"Indicates whether Authentication traps should be generated.

       	By default, this object should have the value enabled(1)."
       	::= { mumSNMPConfiguration 2 }

snmpCfgEnvironmentTrapState OBJECT-TYPE
    	SYNTAX      INTEGER {
    					enabled(1),
    					disabled(2)
    		    }
       	MAX-ACCESS  read-write
       	STATUS      current
       	DESCRIPTION
       	"Indicates whether the fan and temperature traps should be generated.

       	By default, this object should have the value enabled(1)."
       	::= { mumSNMPConfiguration 3 }

snmpCfgColdstartTrapState OBJECT-TYPE
    	SYNTAX      INTEGER {
    					enabled(1),
    					disabled(2)
    		    }
       	MAX-ACCESS  read-write
       	STATUS      current
       	DESCRIPTION
       	"Indicates whether Cold Start traps should be generated.

       	By default, this object should have the value disabled(2)."
       	::= { mumSNMPConfiguration 4 }

snmpCfgModulePortTrapState OBJECT-TYPE
    	SYNTAX      INTEGER {
    					enabled(1),
    					disabled(2)
    		    }
       	MAX-ACCESS  read-write
       	STATUS      current
       	DESCRIPTION
       	"Indicates whether the module present/removed and link up/down traps should be generated.

       	By default, this object should have the value disabled(2)."
       	::= { mumSNMPConfiguration 5 }

snmpCfgCommunity OBJECT IDENTIFIER ::= { mumSNMPConfiguration 6 }

   	comReadWriteAccess 	OBJECT-TYPE
   		SYNTAX      OCTET STRING (SIZE (0..15))
       	MAX-ACCESS  read-write
       	STATUS      current
       	DESCRIPTION
        "The community string that will allow the user read/write access to the
        agent. In otherwords, the user will be allowed to view and set
        parameter attributes.

        Note: since this is a hidden attribute, for security purposes, when
        	  performing a get on this OID the string that is returned will
        	  be represented by asterisk(s)."
       	::= { snmpCfgCommunity 1 }

    comReadOnlyAccess 	OBJECT-TYPE
    	SYNTAX      OCTET STRING (SIZE (0..15))
       	MAX-ACCESS  read-write
       	STATUS      current
       	DESCRIPTION
        "The community string that will allow the user read access to the
        agent. In otherwords, the user will be allowed to view parameter attributes.

        Note: since this is a hidden attribute, for security purposes, when
        	  performing a get on this OID the string that is returned will
        	  be represented by asterisk(s)."
       	::= { snmpCfgCommunity 2 }

mumCfgUniques OBJECT IDENTIFIER ::= { prmCfgMultiplexerUplinkModule 5 }

	unqEmbHttpWebsrvrState OBJECT-TYPE
       	SYNTAX	INTEGER {
    					enabled(1),
    					disabled(2)
    		    }
       	MAX-ACCESS  read-write
       	STATUS      current
       	DESCRIPTION
       	"This configuration parameter allows the user the ability to disable, or enable,
       	the embedded webserver.

       	By default, this object should have the value enabled(1)."
       	::= { mumCfgUniques 1 }

mumCfgAdvanced OBJECT IDENTIFIER ::= { prmCfgMultiplexerUplinkModule 6 }

advCfgTable OBJECT-TYPE
	SYNTAX		SEQUENCE OF AdvCfgEntry
   	MAX-ACCESS  not-accessible
   	STATUS      current
   	DESCRIPTION
    "A list of the Advanced Configuration entries."
   	::= { mumCfgAdvanced 1 }

advCfgEntry OBJECT-TYPE
    SYNTAX		AdvCfgEntry
    MAX-ACCESS  not-accessible
    STATUS      current
    DESCRIPTION
    "An entry containing information applicable to an Advanced Configuration parameter."
	INDEX   { advCfgMumIndex }
    ::= { advCfgTable 1 }

   	AdvCfgEntry ::=
       SEQUENCE {
           advCfgMumIndex			INTEGER,
           advCfgTFTPState			INTEGER,
           advCfgTelnetState		INTEGER,
           advCfgMgmtFltrIpStart	IpAddress,
           advCfgMgmtFltrIpEnd		IpAddress,
           advCfgMgmtSessionTimeout	NtnTimeTicks
       }

    advCfgMumIndex OBJECT-TYPE
       	SYNTAX      INTEGER (1..2)
       	MAX-ACCESS  read-only
       	STATUS      current
       	DESCRIPTION
        "Translates to the physical slot number that a MUM200-2/2000-2 module
        exists within a chassis. The Mini/Micro DSLAMs' physical location is
        set to 1 by default.  See below,

         chassis type     physical location(s) translation
         ------------     --------------------------------
           IPD12000       MUM in slots 13,14 = uimCfgE1MumIndex 1,2 respecitively
           IPD4000        MUM in slot 5      = uimCfgE1MumIndex 1
           Mini DSLAM     NA				 = uimCfgE1MumIndex 1
           Micro DSLAM    NA				 = uimCfgE1MumIndex 1

           Note: when configuring an Advanced Configuration parameter, the user
                 must enter the index of the MUM, see above table, that corresponds
                 with the IP address of the remote SNMP agent."
       	::= { advCfgEntry 1 }

    advCfgTFTPState OBJECT-TYPE
       	SYNTAX	INTEGER {
    					enabled(1),
    					disabled(2)
    		    }
       	MAX-ACCESS  read-write
       	STATUS      current
       	DESCRIPTION
        "This configuration parameter allows the user the ability to disable, or enable,
        the TFTP server.

        By default, this object should have the value enabled(1)."
       	::= { advCfgEntry 2 }

    advCfgTelnetState OBJECT-TYPE
       	SYNTAX	INTEGER {
    					enabled(1),
    					disabled(2)
    		    }
       	MAX-ACCESS  read-write
       	STATUS      current
       	DESCRIPTION
       	"This configuration parameter allows the user the ability to disable, or enable,
        telnet.

        By default, this object should have the value enabled(1)."
       	::= { advCfgEntry 3 }

    advCfgMgmtFltrIpStart OBJECT-TYPE
       	SYNTAX      IpAddress
       	MAX-ACCESS  read-write
       	STATUS      current
       	DESCRIPTION
        "The start value for the management IP filter range. This parameter
        is initially set to a default filter range of 0.0.0.0 - 255.255.255.255.
        Connection to the management system will be allowed only if the user's Ip
        address value falls within the defined mumCfgMgmtIpStart and mumCfgMgmtIpEnd
        range."
        ::= { advCfgEntry 4 }

	advCfgMgmtFltrIpEnd OBJECT-TYPE
       	SYNTAX      IpAddress
       	MAX-ACCESS  read-write
       	STATUS      current
       	DESCRIPTION
        "The end value for the management IP filter range. This parameter
        is initially set to a default filter range of 0.0.0.0 - 255.255.255.255.
        Connection to the management system will be allowed only if the user's Ip
        address value falls within the defined mumCfgMgmtIpStart and mumCfgMgmtIpEnd
        range."
        ::= { advCfgEntry 5 }

    advCfgMgmtSessionTimeout OBJECT-TYPE
       	SYNTAX      NtnTimeTicks
       	MAX-ACCESS  read-write
       	STATUS      current
       	DESCRIPTION
        "This value defines the length of a password session in seconds.  If the
        session has been idle for a time greater than this value, the browser will
        be challenged again, even if it has provided authentication credentials
        with the request."
        ::= { advCfgEntry 6 }

mumCfgManagementPort OBJECT IDENTIFIER ::= { prmCfgMultiplexerUplinkModule 7 }

mgmtPortCfgTable OBJECT-TYPE
	SYNTAX		SEQUENCE OF MgmtPortCfgEntry
   	MAX-ACCESS  not-accessible
   	STATUS      current
   	DESCRIPTION
    "A list of the hardware platform management port entries."
   	::= { mumCfgManagementPort 1 }

mgmtPortCfgEntry OBJECT-TYPE
    SYNTAX		MgmtPortCfgEntry
    MAX-ACCESS  not-accessible
    STATUS      current
    DESCRIPTION
    "An entry containing information applicable to the managment (ethernet type) port."
	INDEX   { mgmtPortCfgMumIndex }
    ::= { mgmtPortCfgTable 1 }

   	MgmtPortCfgEntry ::=
       SEQUENCE {
           mgmtPortCfgMumIndex			INTEGER,
           mgmtPortCfgRxTxRate			INTEGER,
           mgmtPortCfgDuplex			INTEGER,
           mgmtPortCfgType				INTEGER
       }

	mgmtPortCfgMumIndex OBJECT-TYPE
       	SYNTAX      INTEGER (1..2)
       	MAX-ACCESS  read-only
       	STATUS      current
       	DESCRIPTION
        "Translates to the physical slot number that a MUM200-2/2000-2 module
        exists within a chassis. The Mini/Micro DSLAMs' physical location is
        set to 1 by default.  See below,

         chassis type     physical location(s) translation
         ------------     --------------------------------
           IPD12000       MUM in slots 13,14 = uimCfgEthMumIndex 1,2 respecitively
           IPD4000        MUM in slot 5      = uimCfgEthMumIndex 1
           Mini DSLAM     NA				 = uimCfgEthMumIndex 1
           Micro DSLAM    NA				 = uimCfgEthMumIndex 1

           Note: when configuring a management port, the user must enter the
                 index of the MUM, see above table, that corresponds with the
                 IP address of the remote SNMP agent."
       	::= { mgmtPortCfgEntry 1 }

   	mgmtPortCfgRxTxRate OBJECT-TYPE
       	SYNTAX	INTEGER {
       				uimEthAutoNegotiate(0),
       				uimEth10(1),
       				uimEth100(2),
       				uimEthGig(3)
       			}
       	MAX-ACCESS  read-write
       	STATUS      current
       	DESCRIPTION
        "Set the RxTx rate for an ethernet management port."
        ::= { mgmtPortCfgEntry 2 }

    mgmtPortCfgDuplex OBJECT-TYPE
       	SYNTAX	INTEGER {
       				uimEthAutoNegotiate(0),
       				uimEthHalf(1),
       				uimEthFull(2)
       			}
       	MAX-ACCESS  read-write
       	STATUS      current
       	DESCRIPTION
        "Set the duplex setting for an ethernet management port."
        ::= { mgmtPortCfgEntry 3 }

    mgmtPortCfgType OBJECT-TYPE
       	SYNTAX	INTEGER {
       				mgmt(1),
       				uplink(2)
       			}
       	MAX-ACCESS  read-write
       	STATUS      current
       	DESCRIPTION
        "Set the management port type as follows. By setting this
        port to mgmt(1), it will operate as a non-bridge mode connection.
        Setting it to uplink(2), this port will operate like an uplink
        interface module, i.e. a bridge mode connection.

        Note: this applies to the AuD8000-12 micro DSLAM only."
        ::= { mgmtPortCfgEntry 4 }

END
