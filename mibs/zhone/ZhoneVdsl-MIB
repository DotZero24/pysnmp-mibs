--
-- phyVdsl.mib
-- MIB generated by MG-SOFT Visual MIB Builder Version 3.0 Build 285
-- Thursday, October 10, 2013 at 07:01:35
--

    ZhoneVdsl-MIB DEFINITIONS ::= BEGIN

        IMPORTS
            HCPerfTimeElapsed, HCPerfCurrentCount, HCPerfIntervalCount
                FROM HC-PerfHist-TC-MIB
            ifIndex
                FROM IF-MIB
            SnmpAdminString
                FROM SNMP-FRAMEWORK-MIB
            OBJECT-GROUP, MODULE-COMPLIANCE, NOTIFICATION-GROUP
                FROM SNMPv2-CONF
            transmission, Integer32, Unsigned32, Gauge32, OBJECT-TYPE,
            MODULE-IDENTITY, NOTIFICATION-TYPE
                FROM SNMPv2-SMI
            RowStatus, TruthValue, TEXTUAL-CONVENTION
                FROM SNMPv2-TC
            zhoneVdsl, zhoneModules
                FROM Zhone;


-- Overview of Zhone VDSL mib
--
-- This MIB file is based on RFC3728.
--
-- The Zhone DSL mib provides configuration, status and performance parameters
-- used/provided by Zhone implementation of VDSL2 interfaces.
-- The following tables are described in this mib:
--
-- zhoneVdsLineConfProfileTable
-- This table provides VDSL specific configuration parameters.  It contains the VDSL
-- profiles ( Config, CPE, and CO ).  This table is indexed by ifIndex.
--
-- zhoneVdslCustomNotchTable
-- This table contains HAM (Handheld Amateur Radio) custom notch information.
-- This table supports more entries than the standard RFC.
--
--
--
--
--
--
--
--
--
--
        -- 1.3.6.1.4.1.5504.6.110
        zhoneVdslMib MODULE-IDENTITY
            LAST-UPDATED "201302271600Z"		-- February 27, 2013 at 16:00 GMT
            ORGANIZATION
                "ADSLMIB Working Group"
            CONTACT-INFO
                "WG-email:  adslmib@ietf.org
                Info:      https://www1.ietf.org/mailman/listinfo/adslmib

                Chair:     Mike Sneed
                           Sand Channel Systems
                Postal:    P.O.  Box 37324
                           Raleigh, NC 27627-7324
                           USA
                Email:     sneedmike@hotmail.com
                Phone:     +1 206 600 7022

                Co-editor: Bob Ray
                           PESA Switching Systems, Inc.
                Postal:    330-A Wynn Drive
                           Huntsville, AL 35805
                           USA
                Email:     rray@pesa.com
                Phone:     +1 256 726 9200 ext.  142

                Co-editor: Rajesh Abbi
                           Alcatel USA
                Postal:    2301 Sugar Bush Road
                           Raleigh, NC 27612-3339
                           USA
                Email:     Rajesh.Abbi@alcatel.com
                Phone:     +1 919 850 6194
                "
            DESCRIPTION
                "The MIB module defining objects for the management of a pair
                of VDSL transceivers at each end of the VDSL line.  Each such
                line has an entry in an ifTable which may include multiple
                transceiver lines.  An agent may reside at either end of the
                VDSL line.  However, the MIB is designed to require no
                management communication between them beyond that inherent in
                the low-level VDSL line protocol.  The agent may monitor and
                control this protocol for its needs.

                VDSL lines may support optional Fast or Interleaved channels.
                If these are supported, additional entries corresponding to the
                supported channels must be created in the ifTable.  Thus a VDSL
                line that supports both channels will have three entries in the
                ifTable, one for each physical, fast, and interleaved, whose
                ifType values are equal to vdsl(97), fast(125), and
                interleaved(124), respectively.  The ifStackTable is used to
                represent the relationship between the entries.

                Naming Conventions:
                    Vtuc -- (VTUC) transceiver at near (Central) end of line
                    Vtur -- (VTUR) transceiver at Remote end of line
                    Vtu  -- One of either Vtuc or Vtur
                    Curr -- Current
                    Prev -- Previous
                    Atn  -- Attenuation
                    ES   -- Errored Second.
                    SES  -- Severely Errored Second
                    UAS  -- Unavailable Second
                    LCS  -- Line Code Specific
                    Lof  -- Loss of Frame
                    Lol  -- Loss of Link
                    Los  -- Loss of Signal
                    Lpr  -- Loss of Power
                    xxxs -- Sum of Seconds in which xxx has occured
                            (e.g., xxx = Lof, Los, Lpr, Lol)
                    Max  -- Maximum
                    Mgn  -- Margin
                    Min  -- Minimum
                    Psd  -- Power Spectral Density
                    Snr  -- Signal to Noise Ratio
                    Tx   -- Transmit
                    Blks -- Blocks

                Copyright (C) The Internet Society (2004).  This version
                of this MIB module is part of RFC 3728: see the RFC
                itself for full legal notices."
            REVISION "201310080643Z"		-- October 08, 2013 at 06:43 GMT
            DESCRIPTION
                "Add ATM or PTM transport mode retrieval support"
            REVISION "201302271800Z"		-- February 27, 2013 at 18:00 GMT
            DESCRIPTION
                "Adding support for G.INP / ITU-T G.998.4"
            REVISION "201302111415Z"		-- February 11, 2013 at 14:15 GMT
            DESCRIPTION
                "Add VDSL2 Vectoring statistics retrieval support."
            REVISION "201112010559Z"		-- December 01, 2011 at 05:59 GMT
            DESCRIPTION
                "V.01.24
                - fix vpi/vci valid ranges"
            REVISION "201111161214Z"		-- November 16, 2011 at 12:14 GMT
            DESCRIPTION
                "V.01.24
                - add default VPI/VCI for line when its in single-vc mode"
            REVISION "201110181113Z"		-- October 18, 2011 at 11:13 GMT
            DESCRIPTION
                "V.01.23
                - add A3/A4/B3/B4 parameters for UPBO configuration"
            REVISION "201110141124Z"		-- October 14, 2011 at 11:24 GMT
            DESCRIPTION
                "V.01.22
                - split psdShape for Hytec into two shapes for 17a and 30a"
            REVISION "201104281155Z"		-- April 28, 2011 at 11:55 GMT
            DESCRIPTION
                "V.01.21
                - add new PSD Shape values and fix units
                  for SNR and Attn"
            REVISION "201011050716Z"		-- November 05, 2010 at 07:16 GMT
            DESCRIPTION
                "V.01.20
                Modify defaults for max power and max SNR"
            REVISION "201010130459Z"		-- October 13, 2010 at 04:59 GMT
            DESCRIPTION
                "V.01.19
                -added zhoneVdslPhysPhyRActive object
                "
            REVISION "201006071129Z"		-- June 07, 2010 at 11:29 GMT
            DESCRIPTION
                "V.01.18
                VDSL upstream minINP values expanded"
            REVISION "201005310011Z"		-- May 31, 2010 at 00:11 GMT
            DESCRIPTION
                "V.01.17
                VDSL phyR Statistics Objects are added"
            REVISION "201004020640Z"		-- April 02, 2010 at 06:40 GMT
            DESCRIPTION
                "V.01.16
                - modified defaults for zhoneVdslLineConfLineType
                to fastOnly, zhoneVdslLineConfDownPhyRSupport and
                zhoneVdslLineConfUpPhyRSupport to enable.
                "
            REVISION "201003290554Z"		-- March 29, 2010 at 05:54 GMT
            DESCRIPTION
                "V.01.15
                Expanded lower end of range on zhoneVdslLineConfDownMaxPwr, zhoneVdslLineConfUpMaxPwr"
            REVISION "201003020844Z"		-- March 02, 2010 at 08:44 GMT
            DESCRIPTION
                "V.01.14
                Added zhoneVdslLineConfProfileEntry objects 113-123 to support BroadCOM VDSL."
            REVISION "200804141228Z"		-- April 14, 2008 at 12:28 GMT
            DESCRIPTION
                "V.01.13
                - cleanup traps
                - config SNR values changed from 0..127 to 0.310 in 1/10 DBm steps."
            REVISION "200802050856Z"		-- February 05, 2008 at 08:56 GMT
            DESCRIPTION
                "V.01.12
                - add more values to zhoneVdslLineConfDownPsdMaskSelect
                - add more values to zhoneVdslLineConfUpPsdMaskSelect"
            REVISION "200710231653Z"		-- October 23, 2007 at 16:53 GMT
            DESCRIPTION
                "V.01.11
                - add more values to zhoneVdslLineConfDownPsdMaskSelect
                - add more values to zhoneVdslLineConfUppsdMaskSelect"
            REVISION "200710051324Z"		-- October 05, 2007 at 13:24 GMT
            DESCRIPTION
                "V.01.10
                - Add zhoneVdslPhysCurrConnType
                - Add zhoneVdslPhysCurrProfile"
            REVISION "200706201056Z"		-- June 20, 2007 at 10:56 GMT
            DESCRIPTION
                "V.01.09 Accelity-2 additions
                - Add 'dynamic' option to zhoneVdslLineConfDownRateMode
                - Add 'dynamic' option to zhoneVdslLineConfUpRateMode
                - Add zhoneVdslLineConfDownBitSwap
                - Add zhoneVdslLineConfUpBitSwap
                - Add zhoneVdslLineConfAdslAnnexMModeEnabled
                - Add zhoneVdslLineConfAdslAnnexMPsdMask
                - Add zhoneVdslLineConfUS0BoundaryTone
                - Add zhoneVdslLineConfDownInp
                - Add zhoneVdslLineConfUpInp
                - Add zhoneVdslLineConfDownMaxInterleavingDelay
                - Add zhoneVdslLineConfUpMaxInterleavingDelay
                - Add zhoneVdslLineConfDownPsdMaskEnable
                - Add zhoneVdslLineConfUpPsdMaskEnable
                - Add zhoneVdslLineConfDownPsdMaskSelect
                - Add zhoneVdslLineConfUpPsdMaskSelect"
            REVISION "200703141608Z"		-- March 14, 2007 at 16:08 GMT
            DESCRIPTION
                "V.01.08 - ADSL Fallback additions
                - add ADSL transmission modes
                - add ADSL objects to VDSL CO Profile
                - add ADSL objecst to VDSL CPE Profile"
            REVISION "200612051509Z"		-- December 05, 2006 at 15:09 GMT
            DESCRIPTION
                "V.01.07
                - modify zhoneVdslLineConfUpMaxAggregateTxPwr to conform
                  with Conexant driver
                - modify zhoneVdslLineConfDownMaxAggregateTxPwr to conform
                  with Conexant driver
                - mark up mib for vdslPerfDataTable
                - mark up mib for vdslChanPerfDataTable
                - In ZhoneVdslChanPerfDataTable, convert Counter64 objects to
                  Integer32 objects.  "
            REVISION "200611100858Z"		-- November 10, 2006 at 08:58 GMT
            DESCRIPTION
                "V.01.06
                - modify zhoneVdslLineConfDownPsdShape to conform
                  with Conexant driver values
                - modify zhoneVdslLineConfUpPsdShape to conform
                  with Conexant driver values"
            REVISION "200610101525Z"		-- October 10, 2006 at 15:25 GMT
            DESCRIPTION
                "V.01.05
                - zhoneVdslLineAlarmConfProfileEntry is now indexed by ifIndex
                - add MIN/MAX values
                - add zhoneVdslPhysStatus ZHONE KEYWORDS
                - add zhoneVdslChanStatus ZHONE KEYWORDS
                - make phyVdsl.mib reflect new default values
                  - vdslConfig: line-type
                  - vdslConfig: band-opt-uasge
                  - vdslCoConfig: pbo-control
                  - vdslCoConfig: trellis
                  - vdslCpeConfig: pbo-control
                  - vdslCpeConfig: psd-template
                  - vdslCpeConfig: trellis
                - fix spelling zhoneVdslLineConfDownGhsA43cTonePwr
                - cleanup min/max data rates and def values for them"
            REVISION "200609101116Z"		-- September 10, 2006 at 11:16 GMT
            DESCRIPTION
                "V.01.04
                - rename zhoneVdslLineConfSeltNoiseMeasurementTme to
                  zhoneVdslLineConfSeltNoiseMeasurementTime"
            REVISION "200608221721Z"		-- August 22, 2006 at 17:21 GMT
            DESCRIPTION
                "V.01.03 - move tables from phyDsl.mib
                - move zhoneVdslStatusTable from phyDsl.mib
                - move zhoneVdslPerfTable from phyDsl.mib "
            REVISION "200606151529Z"		-- June 15, 2006 at 15:29 GMT
            DESCRIPTION
                "V01.02 - add ZHONE-KEYWORDS"
            REVISION "200402190000Z"		-- February 19, 2004 at 00:00 GMT
            DESCRIPTION
                "Initial version, published as RFC 3728."
            ::= { zhoneModules 110 }



--
-- Textual conventions
--

--  Textual conventions
--
-- textual conventions used in this MIB
--
        ZhoneVdslLineCodingType ::= TEXTUAL-CONVENTION
            STATUS current
            DESCRIPTION
                "This data type is used as the syntax for the VDSL Line
                Code.  Attributes with this syntax identify the line coding
                used.  Specified as an INTEGER, the three values are:

                other(1)  -- none of the following
                mcm(2)    -- Multiple Carrier Modulation
                scm(3)    -- Single Carrier Modulation"
            SYNTAX INTEGER
                {
                other(1),
                mcm(2),
                scm(3)
                }

        ZhoneVdslLineEntity ::= TEXTUAL-CONVENTION
            STATUS current
            DESCRIPTION
                "Identifies a transceiver as being either Vtuc or Vtur.
                A VDSL line consists of two transceivers, a Vtuc and a
                Vtur.  Attributes with this syntax reference the two sides
                of a line.  Specified as an INTEGER, the two values are:

                vtuc(1)  -- central site transceiver
                vtur(2)  -- remote site transceiver"
            SYNTAX INTEGER
                {
                vtuc(1),
                vtur(2)
                }


--
-- Node definitions
--

--  Node definitions
--
-- 1.3.6.1.4.1.5504.5.13.1
        -- 1.3.6.1.4.1.5504.5.13.1
        zhoneVdslLineMib OBJECT IDENTIFIER ::= { zhoneVdsl 1 }


--   Notification definitions
-- 1.3.6.1.4.1.5504.5.13.1.0
        -- 1.3.6.1.4.1.5504.5.13.1.0
        zhoneVdslNotifications OBJECT IDENTIFIER ::= { zhoneVdslLineMib 0 }


        -- 1.3.6.1.4.1.5504.5.13.1.0.1
        vdslXtucPerf15MinLofsThreshTrap NOTIFICATION-TYPE
            OBJECTS { zhoneVdslPerfDataCurr15MinLofs }
            STATUS current
            DESCRIPTION
                "Loss of Framing 15-minute interval threshold
                (vdslLineAlarmConfThresh15MinLofs) reached."
            ::= { zhoneVdslNotifications 1 }


        -- 1.3.6.1.4.1.5504.5.13.1.0.2
        vdslXtucPerf15MinLossThreshTrap NOTIFICATION-TYPE
            OBJECTS { zhoneVdslPerfDataCurr15MinLoss }
            STATUS current
            DESCRIPTION
                "Loss of Signal 15-minute interval threshold
                (vdslLineAlarmConfThresh15MinLoss) reached."
            ::= { zhoneVdslNotifications 2 }


        -- 1.3.6.1.4.1.5504.5.13.1.0.3
        vdslXtucPerf15MinLprsThreshTrap NOTIFICATION-TYPE
            OBJECTS { zhoneVdslPerfDataCurr15MinLprs }
            STATUS current
            DESCRIPTION
                "Loss of Power 15-minute interval threshold
                (vdslLineAlarmConfThresh15MinLprs) reached."
            ::= { zhoneVdslNotifications 3 }


        -- 1.3.6.1.4.1.5504.5.13.1.0.4
        vdslXtucPerf15MinLolsThreshTrap NOTIFICATION-TYPE
            OBJECTS { zhoneVdslPerfDataCurr15MinLols }
            STATUS current
            DESCRIPTION
                "Loss of Link 15-minute interval threshold
                (vdslLineAlarmConfThresh15MinLols) reached."
            ::= { zhoneVdslNotifications 4 }


        -- 1.3.6.1.4.1.5504.5.13.1.0.5
        vdslXtucPerf15MinESsThreshTrap NOTIFICATION-TYPE
            OBJECTS { zhoneVdslPerfDataCurr15MinESs }
            STATUS current
            DESCRIPTION
                "Errored Seconds 15-minute interval threshold
                (vdslLineAlarmConfThresh15MinESs) reached."
            ::= { zhoneVdslNotifications 5 }


        -- 1.3.6.1.4.1.5504.5.13.1.0.6
        vdslXtucPerf15MinSESsThreshTrap NOTIFICATION-TYPE
            OBJECTS { zhoneVdslPerfDataCurr15MinSESs }
            STATUS current
            DESCRIPTION
                "Severely Errored Seconds 15-minute interval threshold
                (vdslLineAlarmConfThresh15MinSESs) reached."
            ::= { zhoneVdslNotifications 6 }


        -- 1.3.6.1.4.1.5504.5.13.1.0.7
        vdslXtucPerf15MinUASsThreshTrap NOTIFICATION-TYPE
            OBJECTS { zhoneVdslPerfDataCurr15MinUASs }
            STATUS current
            DESCRIPTION
                "Unavailable Seconds 15-minute interval threshold
                (vdslLineAlarmConfThresh15MinUASs) reached."
            ::= { zhoneVdslNotifications 7 }


        -- 1.3.6.1.4.1.5504.5.13.1.0.8
        vdslXtucPerf1DayLofsThreshTrap NOTIFICATION-TYPE
            OBJECTS { zhoneVdslPerfDataCurr1DayLofs }
            STATUS current
            DESCRIPTION
                "Loss of Framing 1-day interval threshold
                (vdslLineAlarmConfThresh1DayLofs) reached."
            ::= { zhoneVdslNotifications 8 }


        -- 1.3.6.1.4.1.5504.5.13.1.0.9
        vdslXtucPerf1DayLossThreshTrap NOTIFICATION-TYPE
            OBJECTS { zhoneVdslPerfDataCurr1DayLoss }
            STATUS current
            DESCRIPTION
                "Loss of Signal 1-day interval threshold
                (vdslLineAlarmConfThresh1DayLoss) reached."
            ::= { zhoneVdslNotifications 9 }


        -- 1.3.6.1.4.1.5504.5.13.1.0.10
        vdslXtucPerf1DayLprsThreshTrap NOTIFICATION-TYPE
            OBJECTS { zhoneVdslPerfDataCurr1DayLprs }
            STATUS current
            DESCRIPTION
                "Loss of Power 1-day interval threshold
                (vdslLineAlarmConfThresh1DayLprs) reached."
            ::= { zhoneVdslNotifications 10 }


        -- 1.3.6.1.4.1.5504.5.13.1.0.11
        vdslXtucPerf1DayLolsThreshTrap NOTIFICATION-TYPE
            OBJECTS { zhoneVdslPerfDataCurr1DayLols }
            STATUS current
            DESCRIPTION
                "Loss of Link 1-day interval threshold
                (vdslLineAlarmConfThresh1DayLols) reached."
            ::= { zhoneVdslNotifications 11 }


        -- 1.3.6.1.4.1.5504.5.13.1.0.12
        vdslXtucPerf1DayESsThreshTrap NOTIFICATION-TYPE
            OBJECTS { zhoneVdslPerfDataCurr1DayESs }
            STATUS current
            DESCRIPTION
                "Errored Seconds 1-day interval threshold
                (vdslLineAlarmConfThresh1DayESs) reached."
            ::= { zhoneVdslNotifications 12 }


        -- 1.3.6.1.4.1.5504.5.13.1.0.13
        vdslXtucPerf1DaySESsThreshTrap NOTIFICATION-TYPE
            OBJECTS { zhoneVdslPerfDataCurr1DaySESs }
            STATUS current
            DESCRIPTION
                "Severely Errored Seconds 1-day interval threshold
                (vdslLineAlarmConfThresh1DaySESs) reached."
            ::= { zhoneVdslNotifications 13 }


        -- 1.3.6.1.4.1.5504.5.13.1.0.14
        vdslXtucPerf1DayUASsThreshTrap NOTIFICATION-TYPE
            OBJECTS { zhoneVdslPerfDataCurr1DayUASs }
            STATUS current
            DESCRIPTION
                "Unavailable Seconds 1-day interval threshold
                (vdslLineAlarmConfThresh1DayUASs) reached."
            ::= { zhoneVdslNotifications 14 }


--  1.3.6.1.4.1.5504.5.13.1.0.12
        -- 1.3.6.1.4.1.5504.5.13.1.0.15
        zhoneVdslInitFailureTrap NOTIFICATION-TYPE
            OBJECTS { zhoneVdslPerfDataInits }
            STATUS current
            DESCRIPTION
                "Vtu initialization failed. "
            ::= { zhoneVdslNotifications 15 }


        -- 1.3.6.1.4.1.5504.5.13.1.0.16
        vdslXtucMinTxThresholdAlarmFailureTrap NOTIFICATION-TYPE
            OBJECTS { zhoneVdslChanCurrTxRate, zhoneVdslLineConfDownMinTxThresholdAlarm }
            STATUS current
            DESCRIPTION
                "This trap is thrown when the XTUC line rate syncs below the
                threshold rate as defined by zhoneVdslLineConfDownMinTxThresholdAlarm."
            ::= { zhoneVdslNotifications 16 }


        -- 1.3.6.1.4.1.5504.5.13.1.0.17
        vdslXturMinTxThresholdAlarmFailureTrap NOTIFICATION-TYPE
            OBJECTS { zhoneVdslChanCurrTxRate, zhoneVdslLineConfUpMinTxThresholdAlarm }
            STATUS current
            DESCRIPTION
                "This trap is thrown when the XTUR line rate syncs below the
                threshold rate as defined by zhoneVdslLineConfUpMinTxThresholdAlarm."
            ::= { zhoneVdslNotifications 17 }


--  1.3.6.1.4.1.5504.5.13.1.1
        -- 1.3.6.1.4.1.5504.5.13.1.1
        zhoneVdslMibObjects OBJECT IDENTIFIER ::= { zhoneVdslLineMib 1 }


--   objects
--
-- 1.3.6.1.4.1.5504.5.13.1.1.1
        -- 1.3.6.1.4.1.5504.5.13.1.1.1
        zhoneVdslLineTable OBJECT-TYPE
            SYNTAX SEQUENCE OF ZhoneVdslLineEntry
            MAX-ACCESS not-accessible
            STATUS current
            DESCRIPTION
                "This table includes common attributes describing
                both ends of the line.  It is required for all VDSL
                physical interfaces.  VDSL physical interfaces are
                those ifEntries where ifType is equal to vdsl(97)."
            ::= { zhoneVdslMibObjects 1 }


--  1.3.6.1.4.1.5504.5.13.1.1.1.1
        -- 1.3.6.1.4.1.5504.5.13.1.1.1.1
        zhoneVdslLineEntry OBJECT-TYPE
            SYNTAX ZhoneVdslLineEntry
            MAX-ACCESS not-accessible
            STATUS current
            DESCRIPTION
                "An entry in the vdslLineTable."
            INDEX { ifIndex }
            ::= { zhoneVdslLineTable 1 }


        ZhoneVdslLineEntry ::=
            SEQUENCE {
                zhoneVdslLineCoding
                    ZhoneVdslLineCodingType,
                zhoneVdslLineType
                    INTEGER,
                zhoneVdslLineConfProfile
                    SnmpAdminString,
                zhoneVdslLineAlarmConfProfile
                    SnmpAdminString
             }

--  1.3.6.1.4.1.5504.5.13.1.1.1.1.1
        -- 1.3.6.1.4.1.5504.5.13.1.1.1.1.1
        zhoneVdslLineCoding OBJECT-TYPE
            SYNTAX ZhoneVdslLineCodingType
            MAX-ACCESS read-only
            STATUS current
            DESCRIPTION
                "Specifies the VDSL coding type used on this line."
            REFERENCE
                "T1E1.4/2000-009R3, Part 1, common spec"
            ::= { zhoneVdslLineEntry 1 }


--  1.3.6.1.4.1.5504.5.13.1.1.1.1.2
        -- 1.3.6.1.4.1.5504.5.13.1.1.1.1.2
        zhoneVdslLineType OBJECT-TYPE
            SYNTAX INTEGER
                {
                noChannel(1),
                fastOnly(2),
                interleavedOnly(3),
                fastOrInterleaved(4),
                fastAndInterleaved(5)
                }
            MAX-ACCESS read-only
            STATUS current
            DESCRIPTION
                "Defines the type of VDSL physical line entity that exists,
                by defining whether and how the line is channelized.  If

                the line is channelized,  the value will be other than
                noChannel(1).  This object defines which channel type(s)
                are supported.  Defined values are:

                noChannel(1)          -- no channels exist
                fastOnly(2)           -- only fast channel exists
                interleavedOnly(3)    -- only interleaved channel exists
                fastOrInterleaved(4)  -- either fast or interleaved channel
                                      -- exist, but only one at a time
                fastAndInterleaved(5) -- both fast and interleaved channels
                                      -- exist

                Note that 'slow' and 'interleaved' refer to the same
                channel.  In the case that the line is channelized, the
                manager can use the ifStackTable to determine the ifIndex
                for the associated channel(s)."
            REFERENCE
                "T1E1.4/2000-009R3, Part 1, common spec"
            ::= { zhoneVdslLineEntry 2 }


--  1.3.6.1.4.1.5504.5.13.1.1.1.1.3
        -- 1.3.6.1.4.1.5504.5.13.1.1.1.1.3
        zhoneVdslLineConfProfile OBJECT-TYPE
            SYNTAX SnmpAdminString (SIZE (1..32))
            MAX-ACCESS read-write
            STATUS current
            DESCRIPTION
                "The value of this object identifies the row in the VDSL
                Line Configuration Profile Table, zhoneVdslLineConfProfileTable,
                which applies for this VDSL line, and channels if
                applicable.

                This object MUST be maintained in a persistent manner."
            DEFVAL { "DEFVAL" }
            ::= { zhoneVdslLineEntry 3 }


--  1.3.6.1.4.1.5504.5.13.1.1.1.1.4
        -- 1.3.6.1.4.1.5504.5.13.1.1.1.1.4
        zhoneVdslLineAlarmConfProfile OBJECT-TYPE
            SYNTAX SnmpAdminString (SIZE (1..32))
            MAX-ACCESS read-write
            STATUS current
            DESCRIPTION
                "The value of this object identifies the row in the VDSL
                Line Alarm Configuration Profile Table,
                zhoneVdslLineAlarmConfProfileTable, which applies to this
                VDSL line, and channels if applicable.

                This object MUST be maintained in a persistent manner."
            DEFVAL { "DEFVAL" }
            ::= { zhoneVdslLineEntry 4 }


--  1.3.6.1.4.1.5504.5.13.1.1.2
        -- 1.3.6.1.4.1.5504.5.13.1.1.2
        zhoneVdslPhysTable OBJECT-TYPE
            SYNTAX SEQUENCE OF ZhoneVdslPhysEntry
            MAX-ACCESS not-accessible
            STATUS current
            DESCRIPTION
                "This table provides one row for each Vtu.  Each row
                contains the Physical Layer Parameters table for that
                Vtu.  VDSL physical interfaces are those ifEntries where
                ifType is equal to vdsl(97)."
            ::= { zhoneVdslMibObjects 2 }


--  1.3.6.1.4.1.5504.5.13.1.1.2.1
        -- 1.3.6.1.4.1.5504.5.13.1.1.2.1
        zhoneVdslPhysEntry OBJECT-TYPE
            SYNTAX ZhoneVdslPhysEntry
            MAX-ACCESS not-accessible
            STATUS current
            DESCRIPTION
                "An entry in the vdslPhysTable."
            INDEX { ifIndex, zhoneVdslPhysSide }
            ::= { zhoneVdslPhysTable 1 }


        ZhoneVdslPhysEntry ::=
            SEQUENCE {
                zhoneVdslPhysSide
                    ZhoneVdslLineEntity,
                zhoneVdslPhysInvSerialNumber
                    OCTET STRING,
                zhoneVdslPhysInvVendorID
                    OCTET STRING,
                zhoneVdslPhysInvVersionNumber
                    OCTET STRING,
                zhoneVdslPhysCurrSnrMgn
                    Integer32,
                zhoneVdslPhysCurrAtn
                    Gauge32,
                zhoneVdslPhysCurrStatus
                    BITS,
                zhoneVdslPhysCurrOutputPwr
                    Integer32,
                zhoneVdslPhysCurrAttainableRate
                    Gauge32,
                zhoneVdslPhysCurrLineRate
                    Gauge32,
                zhoneVdslPhysCurrConnType
                    INTEGER,
                zhoneVdslPhysCurrProfile
                    INTEGER,
                zhoneVdslPhysPhyRActive
                    TruthValue,
                zhoneVdslPhysGinpActive
                    TruthValue,
                zhoneVdslPhysTransportMode
                    INTEGER
             }

        -- 1.3.6.1.4.1.5504.5.13.1.1.2.1.1
        zhoneVdslPhysSide OBJECT-TYPE
            SYNTAX ZhoneVdslLineEntity
            MAX-ACCESS not-accessible
            STATUS current
            DESCRIPTION
                "Identifies whether the transceiver is the Vtuc or Vtur."
            ::= { zhoneVdslPhysEntry 1 }


        -- 1.3.6.1.4.1.5504.5.13.1.1.2.1.2
        zhoneVdslPhysInvSerialNumber OBJECT-TYPE
            SYNTAX OCTET STRING (SIZE (0..32))
            MAX-ACCESS read-only
            STATUS current
            DESCRIPTION
                "The vendor specific string that identifies the

                vendor equipment."
            REFERENCE
                "T1E1.4/2000-009R3, Part 1, common spec"
            ::= { zhoneVdslPhysEntry 2 }


        -- 1.3.6.1.4.1.5504.5.13.1.1.2.1.3
        zhoneVdslPhysInvVendorID OBJECT-TYPE
            SYNTAX OCTET STRING (SIZE (0..16))
            MAX-ACCESS read-only
            STATUS current
            DESCRIPTION
                "The vendor ID code is a copy of the binary vendor
                identification field expressed as readable characters
                in hexadecimal notation."
            REFERENCE
                "T1E1.4/2000-009R3, Part 1, common spec"
            ::= { zhoneVdslPhysEntry 3 }


        -- 1.3.6.1.4.1.5504.5.13.1.1.2.1.4
        zhoneVdslPhysInvVersionNumber OBJECT-TYPE
            SYNTAX OCTET STRING (SIZE (0..16))
            MAX-ACCESS read-only
            STATUS current
            DESCRIPTION
                "The vendor specific version number sent by this Vtu
                as part of the initialization messages.  It is a copy
                of the binary version number field expressed as
                readable characters in hexadecimal notation."
            REFERENCE
                "T1E1.4/2000-009R3, Part 1, common spec"
            ::= { zhoneVdslPhysEntry 4 }


        -- 1.3.6.1.4.1.5504.5.13.1.1.2.1.5
        zhoneVdslPhysCurrSnrMgn OBJECT-TYPE
            SYNTAX Integer32 (-127..127)
            UNITS "0.10dBm"
            MAX-ACCESS read-only
            STATUS current
            DESCRIPTION
                "Noise Margin as seen by this Vtu with respect to its
                received signal in 0.10dB.  The effective range is
                -31.75 to +31.75 dB."
            REFERENCE
                "T1E1.4/2000-009R3, Part 1, common spec"
            ::= { zhoneVdslPhysEntry 5 }


        -- 1.3.6.1.4.1.5504.5.13.1.1.2.1.6
        zhoneVdslPhysCurrAtn OBJECT-TYPE
            SYNTAX Gauge32 (0..255)
            UNITS "0.10dBm"
            MAX-ACCESS read-only
            STATUS current
            DESCRIPTION
                "Measured difference in the total power transmitted by
                the peer Vtu and the total power received by this Vtu.
                The effective range is 0 to +63.75 dB."
            REFERENCE
                "T1E1.4/2000-009R3, Part 1, common spec"
            ::= { zhoneVdslPhysEntry 6 }


        -- 1.3.6.1.4.1.5504.5.13.1.1.2.1.7
        zhoneVdslPhysCurrStatus OBJECT-TYPE
            SYNTAX BITS
                {
                noDefect(0),
                lossOfFraming(1),
                lossOfSignal(2),
                lossOfPower(3),
                lossOfSignalQuality(4),
                lossOfLink(5),
                dataInitFailure(6),
                configInitFailure(7),
                protocolInitFailure(8),
                noPeerVtuPresent(9)
                }
            MAX-ACCESS read-only
            STATUS current
            DESCRIPTION
                "Indicates current state of the Vtu line.  This is a
                bit-map of possible conditions.  The various bit
                positions are:

                0   noDefect             There are no defects on the line.

                1   lossOfFraming        Vtu failure due to not receiving
                                         a valid frame.

                2   lossOfSignal         Vtu failure due to not receiving
                                         signal.

                3   lossOfPower          Vtu failure due to loss of power.

                4   lossOfSignalQuality  Loss of Signal Quality is declared
                                         when the Noise Margin falls below
                                         the Minimum Noise Margin, or the
                                         bit-error-rate exceeds 10^-7.

                5   lossOfLink           Vtu failure due to inability to
                                         link with peer Vtu.  Set whenever
                                         the transceiver is in the 'Warm
                                         Start' state.

                6   dataInitFailure      Vtu failure during initialization
                                         due to bit errors corrupting
                                         startup exchange data.

                7   configInitFailure    Vtu failure during initialization
                                         due to peer Vtu not able to
                                         support requested configuration.

                8   protocolInitFailure  Vtu failure during initialization
                                         due to incompatible protocol used
                                         by the peer Vtu.

                9   noPeerVtuPresent     Vtu failure during initialization
                                         due to no activation sequence
                                         detected from peer Vtu.

                This is intended to supplement ifOperStatus."
            REFERENCE
                "T1E1.4/2000-009R3, Part 1, common spec"
            ::= { zhoneVdslPhysEntry 7 }


        -- 1.3.6.1.4.1.5504.5.13.1.1.2.1.8
        zhoneVdslPhysCurrOutputPwr OBJECT-TYPE
            SYNTAX Integer32 (0..160)
            UNITS "0.1dBm"
            MAX-ACCESS read-only
            STATUS current
            DESCRIPTION
                "Measured total output power transmitted by this VTU.
                This is the measurement that was reported during
                the last activation sequence."
            REFERENCE
                "T1E1.4/2000-009R3, Part 1, common spec"
            ::= { zhoneVdslPhysEntry 8 }


        -- 1.3.6.1.4.1.5504.5.13.1.1.2.1.9
        zhoneVdslPhysCurrAttainableRate OBJECT-TYPE
            SYNTAX Gauge32
            UNITS "kbps"
            MAX-ACCESS read-only
            STATUS current
            DESCRIPTION
                "Indicates the maximum currently attainable data rate
                in steps of 1000 bits/second by the Vtu.  This value
                will be equal to or greater than vdslPhysCurrLineRate.
                Note that for SCM, the minimum and maximum data rates
                are equal.  Note: 1 kbps = 1000 bps."
            REFERENCE
                "T1E1.4/2000-009R3, Part 1, common spec"
            ::= { zhoneVdslPhysEntry 9 }


        -- 1.3.6.1.4.1.5504.5.13.1.1.2.1.10
        zhoneVdslPhysCurrLineRate OBJECT-TYPE
            SYNTAX Gauge32
            UNITS "kbps"
            MAX-ACCESS read-only
            STATUS current
            DESCRIPTION
                "Indicates the current data rate in steps of 1000
                bits/second by the Vtu.  This value will be less than
                or equal to vdslPhysCurrAttainableRate.  Note: 1 kbps =
                1000 bps."
            REFERENCE
                "T1E1.4/2000-009R3, Part 1, common spec"
            ::= { zhoneVdslPhysEntry 10 }


        -- 1.3.6.1.4.1.5504.5.13.1.1.2.1.12
        zhoneVdslPhysCurrConnType OBJECT-TYPE
            SYNTAX INTEGER
                {
                unknown(1),
                not-connected(2),
                invalid(3),
                adsl(4),
                adsl2(5),
                adsl2-annexm(6),
                adsl2plus(7),
                adsl2plus-annexm(8),
                vdsl1(9),
                vdsl2(10)
                }
            MAX-ACCESS read-only
            STATUS current
            DESCRIPTION
                "Indicates current connection type.

                unknown(1)        - could not determine connection type
                not-connected(2)  - connection has not been established
                invalid(3)        - unknown connection established
                adsl(4)           - G.992.1/2
                adsl2(5)          - G.992.3/4
                adsl2-annexm(6)   - G.992.3/4 with Annex M
                adsl2plus(7)      - G.992.5
                adsl2plus-annexm(8) - G.992.5 with Annex M
                vdsl1(9)          - G.993.1
                vdsl2(10)         - G.993.2
                "
            REFERENCE
                "T1E1.4/2000-009R3, Part 1, common spec"
            ::= { zhoneVdslPhysEntry 12 }


        -- 1.3.6.1.4.1.5504.5.13.1.1.2.1.13
        zhoneVdslPhysCurrProfile OBJECT-TYPE
            SYNTAX INTEGER
                {
                g993-2-8a(1),
                g993-2-8b(2),
                g993-2-8c(3),
                g993-2-8d(4),
                g993-2-12a(5),
                g993-2-12b(6),
                g993-2-17a(7),
                g993-2-30a(8),
                no-vdsl-connection(9)
                }
            MAX-ACCESS read-only
            STATUS current
            DESCRIPTION
                "Indicates current VDSL profile being used in the
                connection.   This object is only valid for VDSL
                connections."
            REFERENCE
                "T1E1.4/2000-009R3, Part 1, common spec"
            ::= { zhoneVdslPhysEntry 13 }


        -- 1.3.6.1.4.1.5504.5.13.1.1.2.1.14
        zhoneVdslPhysPhyRActive OBJECT-TYPE
            SYNTAX TruthValue
            MAX-ACCESS read-only
            STATUS current
            DESCRIPTION
                "Phy Retransmit Rx Queue Active."
            ::= { zhoneVdslPhysEntry 14 }


        -- 1.3.6.1.4.1.5504.5.13.1.1.2.1.15
        zhoneVdslPhysGinpActive OBJECT-TYPE
            SYNTAX TruthValue
            MAX-ACCESS read-only
            STATUS current
            DESCRIPTION
                "G.INP/ITU-G.998.4 feature active"
            REFERENCE
                "ITU-G.998.4"
            ::= { zhoneVdslPhysEntry 15 }


        -- 1.3.6.1.4.1.5504.5.13.1.1.2.1.16
        zhoneVdslPhysTransportMode OBJECT-TYPE
            SYNTAX INTEGER
                {
                atm(1),
                ptm(2)
                }
            MAX-ACCESS read-only
            STATUS current
            DESCRIPTION
                "Transport mode, either ATM or PTM"
            ::= { zhoneVdslPhysEntry 16 }


--  1.3.6.1.4.1.5504.5.13.1.1.3
        -- 1.3.6.1.4.1.5504.5.13.1.1.3
        zhoneVdslChanTable OBJECT-TYPE
            SYNTAX SEQUENCE OF ZhoneVdslChanEntry
            MAX-ACCESS not-accessible
            STATUS current
            DESCRIPTION
                "This table provides one row for each Vtu channel.
                VDSL channel interfaces are those ifEntries where
                ifType is equal to interleave(124) or fast(125)."
            ::= { zhoneVdslMibObjects 3 }


--  1.3.6.1.4.1.5504.5.13.1.1.3.1
        -- 1.3.6.1.4.1.5504.5.13.1.1.3.1
        zhoneVdslChanEntry OBJECT-TYPE
            SYNTAX ZhoneVdslChanEntry
            MAX-ACCESS not-accessible
            STATUS current
            DESCRIPTION
                "An entry in the vdslChanTable."
            INDEX { ifIndex, zhoneVdslPhysSide }
            ::= { zhoneVdslChanTable 1 }


        ZhoneVdslChanEntry ::=
            SEQUENCE {
                zhoneVdslChanInterleaveDelay
                    Gauge32,
                zhoneVdslChanCrcBlockLength
                    Gauge32,
                zhoneVdslChanCurrTxRate
                    Gauge32,
                zhoneVdslChanCurrTxSlowBurstProtect
                    Gauge32,
                zhoneVdslChanCurrTxFastFec
                    Gauge32
             }

        -- 1.3.6.1.4.1.5504.5.13.1.1.3.1.1
        zhoneVdslChanInterleaveDelay OBJECT-TYPE
            SYNTAX Gauge32
            UNITS "milliseconds"
            MAX-ACCESS read-only
            STATUS current
            DESCRIPTION
                "Interleave Delay for this channel.

                Interleave delay applies only to the interleave
                (slow) channel and defines the mapping (relative
                spacing) between subsequent input bytes at the

                interleaver input and their placement in the bit
                stream at the interleaver output.  Larger numbers
                provide greater separation between consecutive
                input bytes in the output bit stream allowing for
                improved impulse noise immunity at the expense of
                payload latency.

                In the case where the ifType is fast(125), return
                a value of zero."
            REFERENCE
                "T1E1.4/2000-009R3, Part 1, common spec"
            ::= { zhoneVdslChanEntry 1 }


        -- 1.3.6.1.4.1.5504.5.13.1.1.3.1.2
        zhoneVdslChanCrcBlockLength OBJECT-TYPE
            SYNTAX Gauge32
            UNITS "bytes"
            MAX-ACCESS read-only
            STATUS current
            DESCRIPTION
                "Indicates the length of the channel data-block
                on which the CRC operates."
            REFERENCE
                "T1E1.4/2000-009R3, Part 1, common spec"
            ::= { zhoneVdslChanEntry 2 }


        -- 1.3.6.1.4.1.5504.5.13.1.1.3.1.3
        zhoneVdslChanCurrTxRate OBJECT-TYPE
            SYNTAX Gauge32
            UNITS "kbps"
            MAX-ACCESS read-only
            STATUS current
            DESCRIPTION
                "Actual transmit data rate on this channel.  Note: 1
                kbps = 1000 bps."
            ::= { zhoneVdslChanEntry 3 }


        -- 1.3.6.1.4.1.5504.5.13.1.1.3.1.4
        zhoneVdslChanCurrTxSlowBurstProtect OBJECT-TYPE
            SYNTAX Gauge32 (0..1275)
            UNITS "microseconds"
            MAX-ACCESS read-only
            STATUS current
            DESCRIPTION
                "Actual level of impulse noise (burst) protection
                for an interleaved (slow) channel.  This parameter is
                not applicable to fast channels.  For fast channels,
                a value of zero shall be returned."
            REFERENCE
                "ITU-T G.997.1, section 7.3.2.3"
            ::= { zhoneVdslChanEntry 4 }


        -- 1.3.6.1.4.1.5504.5.13.1.1.3.1.5
        zhoneVdslChanCurrTxFastFec OBJECT-TYPE
            SYNTAX Gauge32 (0..50)
            UNITS "%"
            MAX-ACCESS read-only
            STATUS current
            DESCRIPTION
                "Actual Forward Error Correction (FEC) redundancy
                related overhead for a fast channel.  This parameter
                is not applicable to an interleaved (slow) channel.
                For interleaved channels, a value of zero shall be
                returned."
            ::= { zhoneVdslChanEntry 5 }


--  1.3.6.1.4.1.5504.5.13.1.1.4
        -- 1.3.6.1.4.1.5504.5.13.1.1.4
        zhoneVdslPerfDataTable OBJECT-TYPE
            SYNTAX SEQUENCE OF ZhoneVdslPerfDataEntry
            MAX-ACCESS not-accessible
            STATUS current
            DESCRIPTION
                "This table provides one row for each VDSL physical
                interface.  VDSL physical interfaces are those ifEntries
                where ifType is equal to vdsl(97)."
            ::= { zhoneVdslMibObjects 4 }


--  1.3.6.1.4.1.5504.5.13.1.1.4.1
        -- 1.3.6.1.4.1.5504.5.13.1.1.4.1
        zhoneVdslPerfDataEntry OBJECT-TYPE
            SYNTAX ZhoneVdslPerfDataEntry
            MAX-ACCESS not-accessible
            STATUS current
            DESCRIPTION
                "An entry in the vdslPerfDataTable."
            INDEX { ifIndex, zhoneVdslPhysSide }
            ::= { zhoneVdslPerfDataTable 1 }


        ZhoneVdslPerfDataEntry ::=
            SEQUENCE {
                zhoneVdslPerfDataValidIntervals
                    Integer32,
                zhoneVdslPerfDataInvalidIntervals
                    Integer32,
                zhoneVdslPerfDataLofs
                    Unsigned32,
                zhoneVdslPerfDataLoss
                    Unsigned32,
                zhoneVdslPerfDataLprs
                    Unsigned32,
                zhoneVdslPerfDataLols
                    Unsigned32,
                zhoneVdslPerfDataESs
                    Unsigned32,
                zhoneVdslPerfDataSESs
                    Unsigned32,
                zhoneVdslPerfDataUASs
                    Unsigned32,
                zhoneVdslPerfDataInits
                    Unsigned32,
                zhoneVdslPerfDataCurr15MinTimeElapsed
                    Integer32,
                zhoneVdslPerfDataCurr15MinLofs
                    Unsigned32,
                zhoneVdslPerfDataCurr15MinLoss
                    Unsigned32,
                zhoneVdslPerfDataCurr15MinLprs
                    Unsigned32,
                zhoneVdslPerfDataCurr15MinLols
                    Unsigned32,
                zhoneVdslPerfDataCurr15MinESs
                    Unsigned32,
                zhoneVdslPerfDataCurr15MinSESs
                    Unsigned32,
                zhoneVdslPerfDataCurr15MinUASs
                    Unsigned32,
                zhoneVdslPerfDataCurr15MinInits
                    Unsigned32,
                zhoneVdslPerfData1DayValidIntervals
                    Integer32,
                zhoneVdslPerfData1DayInvalidIntervals
                    Integer32,
                zhoneVdslPerfDataCurr1DayTimeElapsed
                    Integer32,
                zhoneVdslPerfDataCurr1DayLofs
                    Unsigned32,
                zhoneVdslPerfDataCurr1DayLoss
                    Unsigned32,
                zhoneVdslPerfDataCurr1DayLprs
                    Unsigned32,
                zhoneVdslPerfDataCurr1DayLols
                    Unsigned32,
                zhoneVdslPerfDataCurr1DayESs
                    Unsigned32,
                zhoneVdslPerfDataCurr1DaySESs
                    Unsigned32,
                zhoneVdslPerfDataCurr1DayUASs
                    Unsigned32,
                zhoneVdslPerfDataCurr1DayInits
                    Unsigned32,
                zhoneVdslPhyrRetransmittedCodewords
                    Unsigned32,
                zhoneVdslPhyrCorrectedRetransmittedCodewords
                    Unsigned32,
                zhoneVdslPhyrUncorrectableRetransmittedCodewords
                    Unsigned32,
                zhoneVdslPhyrCurr15MinRetransmittedCodewords
                    Unsigned32,
                zhoneVdslPhyrCurr15MinCorrectedRetransmittedCodewords
                    Unsigned32,
                zhoneVdslPhyrCurr15MinUncorrectableRetransmittedCodewords
                    Unsigned32,
                zhoneVdslPhyrCurr1DayRetransmittedCodewords
                    Unsigned32,
                zhoneVdslPhyrCurr1DayCorrectedRetransmittedCodewords
                    Unsigned32,
                zhoneVdslPhyrCurr1DayUncorrectableRetransmittedCodewords
                    Unsigned32,
                zhoneVdslPhyrPrev1DayRetransmittedCodewords
                    Unsigned32,
                zhoneVdslPhyrPrev1DayCorrectedRetransmittedCodewords
                    Unsigned32,
                zhoneVdslPhyrPrev1DayUncorrectableRetransmittedCodewords
                    Unsigned32,
                zhoneVdslGinpLeftrSecs
                    Unsigned32,
                zhoneVdslGinpErrorFreeBits
                    Unsigned32,
                zhoneVdslGinpMinEftr
                    Unsigned32,
                zhoneVdslGinpCurr15MinLeftrSecs
                    Unsigned32,
                zhoneVdslGinpCurr15MinErrorFreeBits
                    Unsigned32,
                zhoneVdslGinpCurr15MinMinEftr
                    Unsigned32,
                zhoneVdslGinpCurr1DayLeftrSecs
                    Unsigned32,
                zhoneVdslGinpCurr1DayErrorFreeBits
                    Unsigned32,
                zhoneVdslGinpCurr1DayMinEftr
                    Unsigned32,
                zhoneVdslGinpPrev1DayLeftrSecs
                    Integer32,
                zhoneVdslGinpPrev1DayErrorFreeBits
                    Integer32,
                zhoneVdslGinpPrev1DayMinEftr
                    Integer32
             }

        -- 1.3.6.1.4.1.5504.5.13.1.1.4.1.1
        zhoneVdslPerfDataValidIntervals OBJECT-TYPE
            SYNTAX Integer32 (0..96)
            UNITS "intervals"
            MAX-ACCESS read-only
            STATUS current
            DESCRIPTION
                "Valid Intervals per definition found in
                HC-PerfHist-TC-MIB."
            ::= { zhoneVdslPerfDataEntry 1 }


        -- 1.3.6.1.4.1.5504.5.13.1.1.4.1.2
        zhoneVdslPerfDataInvalidIntervals OBJECT-TYPE
            SYNTAX Integer32 (0..96)
            UNITS "intervals"
            MAX-ACCESS read-only
            STATUS current
            DESCRIPTION
                "Invalid Intervals per definition found in
                HC-PerfHist-TC-MIB."
            ::= { zhoneVdslPerfDataEntry 2 }


        -- 1.3.6.1.4.1.5504.5.13.1.1.4.1.3
        zhoneVdslPerfDataLofs OBJECT-TYPE
            SYNTAX Unsigned32
            UNITS "seconds"
            MAX-ACCESS read-only
            STATUS current
            DESCRIPTION
                "Count of seconds since the unit was last reset that there
                was Loss of Framing."
            REFERENCE
                "T1E1.4/2000-009R3, Part 1, common spec"
            ::= { zhoneVdslPerfDataEntry 3 }


        -- 1.3.6.1.4.1.5504.5.13.1.1.4.1.4
        zhoneVdslPerfDataLoss OBJECT-TYPE
            SYNTAX Unsigned32
            UNITS "seconds"
            MAX-ACCESS read-only
            STATUS current
            DESCRIPTION
                "Count of seconds since the unit was last reset that there
                was Loss of Signal."
            REFERENCE
                "T1E1.4/2000-009R3, Part 1, common spec"
            ::= { zhoneVdslPerfDataEntry 4 }


        -- 1.3.6.1.4.1.5504.5.13.1.1.4.1.5
        zhoneVdslPerfDataLprs OBJECT-TYPE
            SYNTAX Unsigned32
            UNITS "seconds"
            MAX-ACCESS read-only
            STATUS current
            DESCRIPTION
                "Count of seconds since the unit was last reset that there
                was Loss of Power."
            REFERENCE
                "T1E1.4/2000-009R3, Part 1, common spec"
            ::= { zhoneVdslPerfDataEntry 5 }


        -- 1.3.6.1.4.1.5504.5.13.1.1.4.1.6
        zhoneVdslPerfDataLols OBJECT-TYPE
            SYNTAX Unsigned32
            UNITS "seconds"
            MAX-ACCESS read-only
            STATUS current
            DESCRIPTION
                "Count of seconds since the unit was last reset that there
                was Loss of Link."
            ::= { zhoneVdslPerfDataEntry 6 }


        -- 1.3.6.1.4.1.5504.5.13.1.1.4.1.7
        zhoneVdslPerfDataESs OBJECT-TYPE
            SYNTAX Unsigned32
            UNITS "seconds"
            MAX-ACCESS read-only
            STATUS current
            DESCRIPTION
                "Count of Errored Seconds since the unit was last reset.
                An Errored Second is a one-second interval containing one
                or more CRC anomalies, or one or more LOS or LOF defects."
            REFERENCE
                "T1E1.4/2000-009R3, Part 1, common spec"
            ::= { zhoneVdslPerfDataEntry 7 }


        -- 1.3.6.1.4.1.5504.5.13.1.1.4.1.8
        zhoneVdslPerfDataSESs OBJECT-TYPE
            SYNTAX Unsigned32
            UNITS "seconds"
            MAX-ACCESS read-only
            STATUS current
            DESCRIPTION
                "Count of Severely Errored Seconds since the unit was last
                reset."
            ::= { zhoneVdslPerfDataEntry 8 }


        -- 1.3.6.1.4.1.5504.5.13.1.1.4.1.9
        zhoneVdslPerfDataUASs OBJECT-TYPE
            SYNTAX Unsigned32
            UNITS "seconds"
            MAX-ACCESS read-only
            STATUS current
            DESCRIPTION
                "Count of Unavailable Seconds since the unit was last
                reset."
            ::= { zhoneVdslPerfDataEntry 9 }


        -- 1.3.6.1.4.1.5504.5.13.1.1.4.1.10
        zhoneVdslPerfDataInits OBJECT-TYPE
            SYNTAX Unsigned32
            UNITS "occurrences"
            MAX-ACCESS read-only
            STATUS current
            DESCRIPTION
                "Count of the line initialization attempts since the unit
                was last reset.  This count includes both successful and
                failed attempts."
            REFERENCE
                "T1E1.4/2000-009R3, Part 1, common spec"
            ::= { zhoneVdslPerfDataEntry 10 }


        -- 1.3.6.1.4.1.5504.5.13.1.1.4.1.11
        zhoneVdslPerfDataCurr15MinTimeElapsed OBJECT-TYPE
            SYNTAX Integer32 (0..86399)
            UNITS "seconds"
            MAX-ACCESS read-only
            STATUS current
            DESCRIPTION
                "Total elapsed seconds in this interval."
            ::= { zhoneVdslPerfDataEntry 11 }


        -- 1.3.6.1.4.1.5504.5.13.1.1.4.1.12
        zhoneVdslPerfDataCurr15MinLofs OBJECT-TYPE
            SYNTAX Unsigned32
            UNITS "seconds"
            MAX-ACCESS read-only
            STATUS current
            DESCRIPTION
                "Count of seconds during this interval that there
                was Loss of Framing."
            REFERENCE
                "T1E1.4/2000-009R3, Part 1, common spec"
            ::= { zhoneVdslPerfDataEntry 12 }


        -- 1.3.6.1.4.1.5504.5.13.1.1.4.1.13
        zhoneVdslPerfDataCurr15MinLoss OBJECT-TYPE
            SYNTAX Unsigned32
            UNITS "seconds"
            MAX-ACCESS read-only
            STATUS current
            DESCRIPTION
                "Count of seconds during this interval that there
                was Loss of Signal."
            REFERENCE
                "T1E1.4/2000-009R3, Part 1, common spec"
            ::= { zhoneVdslPerfDataEntry 13 }


        -- 1.3.6.1.4.1.5504.5.13.1.1.4.1.14
        zhoneVdslPerfDataCurr15MinLprs OBJECT-TYPE
            SYNTAX Unsigned32
            UNITS "seconds"
            MAX-ACCESS read-only
            STATUS current
            DESCRIPTION
                "Count of seconds during this interval that there
                was Loss of Power."
            REFERENCE
                "T1E1.4/2000-009R3, Part 1, common spec"
            ::= { zhoneVdslPerfDataEntry 14 }


        -- 1.3.6.1.4.1.5504.5.13.1.1.4.1.15
        zhoneVdslPerfDataCurr15MinLols OBJECT-TYPE
            SYNTAX Unsigned32
            UNITS "seconds"
            MAX-ACCESS read-only
            STATUS current
            DESCRIPTION
                "Count of seconds during this interval that there
                was Loss of Link."
            ::= { zhoneVdslPerfDataEntry 15 }


        -- 1.3.6.1.4.1.5504.5.13.1.1.4.1.16
        zhoneVdslPerfDataCurr15MinESs OBJECT-TYPE
            SYNTAX Unsigned32
            UNITS "seconds"
            MAX-ACCESS read-only
            STATUS current
            DESCRIPTION
                "Count of Errored Seconds during this interval.  An Errored
                Second is a one-second interval containing one or more CRC
                anomalies, or one or more LOS or LOF defects."
            REFERENCE
                "T1E1.4/2000-009R3, Part 1, common spec"
            ::= { zhoneVdslPerfDataEntry 16 }


        -- 1.3.6.1.4.1.5504.5.13.1.1.4.1.17
        zhoneVdslPerfDataCurr15MinSESs OBJECT-TYPE
            SYNTAX Unsigned32
            UNITS "seconds"
            MAX-ACCESS read-only
            STATUS current
            DESCRIPTION
                "Count of Severely Errored Seconds during this interval."
            ::= { zhoneVdslPerfDataEntry 17 }


        -- 1.3.6.1.4.1.5504.5.13.1.1.4.1.18
        zhoneVdslPerfDataCurr15MinUASs OBJECT-TYPE
            SYNTAX Unsigned32
            UNITS "seconds"
            MAX-ACCESS read-only
            STATUS current
            DESCRIPTION
                "Count of Unavailable Seconds during this interval."
            ::= { zhoneVdslPerfDataEntry 18 }


        -- 1.3.6.1.4.1.5504.5.13.1.1.4.1.19
        zhoneVdslPerfDataCurr15MinInits OBJECT-TYPE
            SYNTAX Unsigned32
            UNITS "occurrences"
            MAX-ACCESS read-only
            STATUS current
            DESCRIPTION
                "Count of the line initialization attempts during this
                interval.  This count includes both successful and
                failed attempts."
            REFERENCE
                "T1E1.4/2000-009R3, Part 1, common spec"
            ::= { zhoneVdslPerfDataEntry 19 }


        -- 1.3.6.1.4.1.5504.5.13.1.1.4.1.20
        zhoneVdslPerfData1DayValidIntervals OBJECT-TYPE
            SYNTAX Integer32 (0..96)
            UNITS "intervals"
            MAX-ACCESS read-only
            STATUS current
            DESCRIPTION
                "Valid Intervals per definition found in
                HC-PerfHist-TC-MIB."
            ::= { zhoneVdslPerfDataEntry 20 }


        -- 1.3.6.1.4.1.5504.5.13.1.1.4.1.21
        zhoneVdslPerfData1DayInvalidIntervals OBJECT-TYPE
            SYNTAX Integer32 (0..96)
            UNITS "intervals"
            MAX-ACCESS read-only
            STATUS current
            DESCRIPTION
                "Invalid Intervals per definition found in
                HC-PerfHist-TC-MIB."
            ::= { zhoneVdslPerfDataEntry 21 }


        -- 1.3.6.1.4.1.5504.5.13.1.1.4.1.22
        zhoneVdslPerfDataCurr1DayTimeElapsed OBJECT-TYPE
            SYNTAX Integer32 (0..86399)
            UNITS "seconds"
            MAX-ACCESS read-only
            STATUS current
            DESCRIPTION
                "Number of seconds that have elapsed since the beginning
                of the current 1-day interval."
            ::= { zhoneVdslPerfDataEntry 22 }


        -- 1.3.6.1.4.1.5504.5.13.1.1.4.1.23
        zhoneVdslPerfDataCurr1DayLofs OBJECT-TYPE
            SYNTAX Unsigned32
            UNITS "seconds"
            MAX-ACCESS read-only
            STATUS current
            DESCRIPTION
                "Count of Loss of Framing (LOF) Seconds since the
                beginning of the current 1-day interval."
            ::= { zhoneVdslPerfDataEntry 23 }


        -- 1.3.6.1.4.1.5504.5.13.1.1.4.1.24
        zhoneVdslPerfDataCurr1DayLoss OBJECT-TYPE
            SYNTAX Unsigned32
            UNITS "seconds"
            MAX-ACCESS read-only
            STATUS current
            DESCRIPTION
                "Count of Loss of Signal (LOS) Seconds since the beginning
                of the current 1-day interval."
            ::= { zhoneVdslPerfDataEntry 24 }


        -- 1.3.6.1.4.1.5504.5.13.1.1.4.1.25
        zhoneVdslPerfDataCurr1DayLprs OBJECT-TYPE
            SYNTAX Unsigned32
            UNITS "seconds"
            MAX-ACCESS read-only
            STATUS current
            DESCRIPTION
                "Count of Loss of Power (LPR) Seconds since the beginning
                of the current 1-day interval."
            ::= { zhoneVdslPerfDataEntry 25 }


        -- 1.3.6.1.4.1.5504.5.13.1.1.4.1.26
        zhoneVdslPerfDataCurr1DayLols OBJECT-TYPE
            SYNTAX Unsigned32
            UNITS "seconds"
            MAX-ACCESS read-only
            STATUS current
            DESCRIPTION
                "Count of Loss of Link (LOL) Seconds since the beginning
                of the current 1-day interval."
            ::= { zhoneVdslPerfDataEntry 26 }


        -- 1.3.6.1.4.1.5504.5.13.1.1.4.1.27
        zhoneVdslPerfDataCurr1DayESs OBJECT-TYPE
            SYNTAX Unsigned32
            UNITS "seconds"
            MAX-ACCESS read-only
            STATUS current
            DESCRIPTION
                "Count of Errored Seconds (ES) since the beginning
                of the current 1-day interval."
            ::= { zhoneVdslPerfDataEntry 27 }


        -- 1.3.6.1.4.1.5504.5.13.1.1.4.1.28
        zhoneVdslPerfDataCurr1DaySESs OBJECT-TYPE
            SYNTAX Unsigned32
            UNITS "seconds"
            MAX-ACCESS read-only
            STATUS current
            DESCRIPTION
                "Count of Severely Errored Seconds (SES) since the
                beginning of the current 1-day interval."
            ::= { zhoneVdslPerfDataEntry 28 }


        -- 1.3.6.1.4.1.5504.5.13.1.1.4.1.29
        zhoneVdslPerfDataCurr1DayUASs OBJECT-TYPE
            SYNTAX Unsigned32
            UNITS "seconds"
            MAX-ACCESS read-only
            STATUS current
            DESCRIPTION
                "Count of Unavailable Seconds (UAS) since the beginning
                of the current 1-day interval."
            ::= { zhoneVdslPerfDataEntry 29 }


        -- 1.3.6.1.4.1.5504.5.13.1.1.4.1.30
        zhoneVdslPerfDataCurr1DayInits OBJECT-TYPE
            SYNTAX Unsigned32
            UNITS "seconds"
            MAX-ACCESS read-only
            STATUS current
            DESCRIPTION
                "Count of the line initialization attempts since the
                beginning of the current 1-day interval.  This count
                includes both successful and failed attempts."
            ::= { zhoneVdslPerfDataEntry 30 }


        -- 1.3.6.1.4.1.5504.5.13.1.1.4.1.31
        zhoneVdslPhyrRetransmittedCodewords OBJECT-TYPE
            SYNTAX Unsigned32
            MAX-ACCESS read-only
            STATUS current
            DESCRIPTION
                "Retransmitted Codewords"
            ::= { zhoneVdslPerfDataEntry 31 }


        -- 1.3.6.1.4.1.5504.5.13.1.1.4.1.32
        zhoneVdslPhyrCorrectedRetransmittedCodewords OBJECT-TYPE
            SYNTAX Unsigned32
            MAX-ACCESS read-only
            STATUS current
            DESCRIPTION
                "Retransmitted corrected Codewords"
            ::= { zhoneVdslPerfDataEntry 32 }


        -- 1.3.6.1.4.1.5504.5.13.1.1.4.1.33
        zhoneVdslPhyrUncorrectableRetransmittedCodewords OBJECT-TYPE
            SYNTAX Unsigned32
            MAX-ACCESS read-only
            STATUS current
            DESCRIPTION
                "Retransmitted uncorrectable Codewords"
            ::= { zhoneVdslPerfDataEntry 33 }


        -- 1.3.6.1.4.1.5504.5.13.1.1.4.1.34
        zhoneVdslPhyrCurr15MinRetransmittedCodewords OBJECT-TYPE
            SYNTAX Unsigned32
            MAX-ACCESS read-only
            STATUS current
            DESCRIPTION
                "Current 15 minutes Retransmitted Codewords"
            ::= { zhoneVdslPerfDataEntry 34 }


        -- 1.3.6.1.4.1.5504.5.13.1.1.4.1.35
        zhoneVdslPhyrCurr15MinCorrectedRetransmittedCodewords OBJECT-TYPE
            SYNTAX Unsigned32
            MAX-ACCESS read-only
            STATUS current
            DESCRIPTION
                "Current 15 minutes Retransmitted Corrected Codewords"
            ::= { zhoneVdslPerfDataEntry 35 }


        -- 1.3.6.1.4.1.5504.5.13.1.1.4.1.36
        zhoneVdslPhyrCurr15MinUncorrectableRetransmittedCodewords OBJECT-TYPE
            SYNTAX Unsigned32
            MAX-ACCESS read-only
            STATUS current
            DESCRIPTION
                "Current 15 minutes Retransmitted Uncorrectable Codewords"
            ::= { zhoneVdslPerfDataEntry 36 }


        -- 1.3.6.1.4.1.5504.5.13.1.1.4.1.37
        zhoneVdslPhyrCurr1DayRetransmittedCodewords OBJECT-TYPE
            SYNTAX Unsigned32
            MAX-ACCESS read-only
            STATUS current
            DESCRIPTION
                "Current Day Retransmitted Codewords"
            ::= { zhoneVdslPerfDataEntry 37 }


        -- 1.3.6.1.4.1.5504.5.13.1.1.4.1.38
        zhoneVdslPhyrCurr1DayCorrectedRetransmittedCodewords OBJECT-TYPE
            SYNTAX Unsigned32
            MAX-ACCESS read-only
            STATUS current
            DESCRIPTION
                "Current Day Retransmitted Corrected Codewords"
            ::= { zhoneVdslPerfDataEntry 38 }


        -- 1.3.6.1.4.1.5504.5.13.1.1.4.1.39
        zhoneVdslPhyrCurr1DayUncorrectableRetransmittedCodewords OBJECT-TYPE
            SYNTAX Unsigned32
            MAX-ACCESS read-only
            STATUS current
            DESCRIPTION
                "Current Day Retransmitted Uncorrectable Codewords"
            ::= { zhoneVdslPerfDataEntry 39 }


        -- 1.3.6.1.4.1.5504.5.13.1.1.4.1.40
        zhoneVdslPhyrPrev1DayRetransmittedCodewords OBJECT-TYPE
            SYNTAX Unsigned32
            MAX-ACCESS read-only
            STATUS current
            DESCRIPTION
                "Previous Day Retransmitted Codewords"
            ::= { zhoneVdslPerfDataEntry 40 }


        -- 1.3.6.1.4.1.5504.5.13.1.1.4.1.41
        zhoneVdslPhyrPrev1DayCorrectedRetransmittedCodewords OBJECT-TYPE
            SYNTAX Unsigned32
            MAX-ACCESS read-only
            STATUS current
            DESCRIPTION
                "Previous Day Retransmitted Corrected Codewords"
            ::= { zhoneVdslPerfDataEntry 41 }


        -- 1.3.6.1.4.1.5504.5.13.1.1.4.1.42
        zhoneVdslPhyrPrev1DayUncorrectableRetransmittedCodewords OBJECT-TYPE
            SYNTAX Unsigned32
            MAX-ACCESS read-only
            STATUS current
            DESCRIPTION
                "Previous Day Retransmitted Uncorrectable Codewords"
            ::= { zhoneVdslPerfDataEntry 42 }


        -- 1.3.6.1.4.1.5504.5.13.1.1.4.1.43
        zhoneVdslGinpLeftrSecs OBJECT-TYPE
            SYNTAX Unsigned32
            MAX-ACCESS read-only
            STATUS current
            DESCRIPTION
                "LEFTRS - This counter counts the number of seconds that experienced a Low
                Error Free Throughput Rate (LEFTR), i,e., seconds during which the Error
                Free Throughput dropped below the configured threshold."
            ::= { zhoneVdslPerfDataEntry 43 }


        -- 1.3.6.1.4.1.5504.5.13.1.1.4.1.44
        zhoneVdslGinpErrorFreeBits OBJECT-TYPE
            SYNTAX Unsigned32
            MAX-ACCESS read-only
            STATUS current
            DESCRIPTION
                "errorFreeBits - This counter counts the number of bits that crossed the
                alpha1/beta1 interface (bits available to carry user payload). "
            ::= { zhoneVdslPerfDataEntry 44 }


        -- 1.3.6.1.4.1.5504.5.13.1.1.4.1.45
        zhoneVdslGinpMinEftr OBJECT-TYPE
            SYNTAX Unsigned32
            MAX-ACCESS read-only
            STATUS current
            DESCRIPTION
                "minEFTR - This performance monitoring parameter records the lowest value
                of Error Free Throughput during the current interval."
            ::= { zhoneVdslPerfDataEntry 45 }


        -- 1.3.6.1.4.1.5504.5.13.1.1.4.1.46
        zhoneVdslGinpCurr15MinLeftrSecs OBJECT-TYPE
            SYNTAX Unsigned32
            MAX-ACCESS read-only
            STATUS current
            DESCRIPTION
                "LEFTRS - This counter counts the number of seconds that experienced a Low
                Error Free Throughput Rate (LEFTR), i,e., seconds during which the Error
                Free Throughput dropped below the configured threshold. This is the count
                for the current 15 minutes."
            ::= { zhoneVdslPerfDataEntry 46 }


        -- 1.3.6.1.4.1.5504.5.13.1.1.4.1.47
        zhoneVdslGinpCurr15MinErrorFreeBits OBJECT-TYPE
            SYNTAX Unsigned32
            MAX-ACCESS read-only
            STATUS current
            DESCRIPTION
                "errorFreeBits - This counter counts the number of bits that crossed the
                alpha1/beta1 interface (bits available to carry user payload). This is
                the count for the current 15 minutes."
            ::= { zhoneVdslPerfDataEntry 47 }


        -- 1.3.6.1.4.1.5504.5.13.1.1.4.1.48
        zhoneVdslGinpCurr15MinMinEftr OBJECT-TYPE
            SYNTAX Unsigned32
            MAX-ACCESS read-only
            STATUS current
            DESCRIPTION
                "minEFTR - This performance monitoring parameter records the lowest value
                of Error Free Throughput during the current interval. This is the count
                for the current 15 minutes."
            ::= { zhoneVdslPerfDataEntry 48 }


        -- 1.3.6.1.4.1.5504.5.13.1.1.4.1.49
        zhoneVdslGinpCurr1DayLeftrSecs OBJECT-TYPE
            SYNTAX Unsigned32
            MAX-ACCESS read-only
            STATUS current
            DESCRIPTION
                "LEFTRS - This counter counts the number of seconds that experienced a Low
                Error Free Throughput Rate (LEFTR), i,e., seconds during which the Error
                Free Throughput dropped below the configured threshold. This is the count
                for the current day."
            ::= { zhoneVdslPerfDataEntry 49 }


        -- 1.3.6.1.4.1.5504.5.13.1.1.4.1.50
        zhoneVdslGinpCurr1DayErrorFreeBits OBJECT-TYPE
            SYNTAX Unsigned32
            MAX-ACCESS read-only
            STATUS current
            DESCRIPTION
                "errorFreeBits - This counter counts the number of bits that crossed the
                alpha1/beta1 interface (bits available to carry user payload). This is
                the count for the current day."
            ::= { zhoneVdslPerfDataEntry 50 }


        -- 1.3.6.1.4.1.5504.5.13.1.1.4.1.51
        zhoneVdslGinpCurr1DayMinEftr OBJECT-TYPE
            SYNTAX Unsigned32
            MAX-ACCESS read-only
            STATUS current
            DESCRIPTION
                "minEFTR - This performance monitoring parameter records the lowest value
                of Error Free Throughput during the current interval. This is the count
                for the current day."
            ::= { zhoneVdslPerfDataEntry 51 }


        -- 1.3.6.1.4.1.5504.5.13.1.1.4.1.52
        zhoneVdslGinpPrev1DayLeftrSecs OBJECT-TYPE
            SYNTAX Integer32
            MAX-ACCESS read-only
            STATUS current
            DESCRIPTION
                "LEFTRS - This counter counts the number of seconds that experienced a Low
                Error Free Throughput Rate (LEFTR), i,e., seconds during which the Error
                Free Throughput dropped below the configured threshold. This is the count
                for the previous day."
            ::= { zhoneVdslPerfDataEntry 52 }


        -- 1.3.6.1.4.1.5504.5.13.1.1.4.1.53
        zhoneVdslGinpPrev1DayErrorFreeBits OBJECT-TYPE
            SYNTAX Integer32
            MAX-ACCESS read-only
            STATUS current
            DESCRIPTION
                "errorFreeBits - This counter counts the number of bits that crossed the
                alpha1/beta1 interface (bits available to carry user payload). This is
                the count for the previous day."
            ::= { zhoneVdslPerfDataEntry 53 }


        -- 1.3.6.1.4.1.5504.5.13.1.1.4.1.54
        zhoneVdslGinpPrev1DayMinEftr OBJECT-TYPE
            SYNTAX Integer32
            MAX-ACCESS read-only
            STATUS current
            DESCRIPTION
                "minEFTR - This performance monitoring parameter records the lowest value
                of Error Free Throughput during the current interval. This is the count
                for the previous day."
            ::= { zhoneVdslPerfDataEntry 54 }


--  1.3.6.1.4.1.5504.5.13.1.1.5
        -- 1.3.6.1.4.1.5504.5.13.1.1.5
        zhoneVdslPerfIntervalTable OBJECT-TYPE
            SYNTAX SEQUENCE OF ZhoneVdslPerfIntervalEntry
            MAX-ACCESS not-accessible
            STATUS current
            DESCRIPTION
                "This table provides one row for each Vtu performance
                data collection interval.  VDSL physical interfaces are

                those ifEntries where ifType is equal to vdsl(97)."
            ::= { zhoneVdslMibObjects 5 }


--  1.3.6.1.4.1.5504.5.13.1.1.5.1
        -- 1.3.6.1.4.1.5504.5.13.1.1.5.1
        zhoneVdslPerfIntervalEntry OBJECT-TYPE
            SYNTAX ZhoneVdslPerfIntervalEntry
            MAX-ACCESS not-accessible
            STATUS current
            DESCRIPTION
                "An entry in the vdslPerfIntervalTable."
            INDEX { ifIndex, zhoneVdslPhysSide, zhoneVdslPerfIntervalNumber }
            ::= { zhoneVdslPerfIntervalTable 1 }


        ZhoneVdslPerfIntervalEntry ::=
            SEQUENCE {
                zhoneVdslPerfIntervalNumber
                    Unsigned32,
                zhoneVdslPerfIntervalLofs
                    HCPerfIntervalCount,
                zhoneVdslPerfIntervalLoss
                    HCPerfIntervalCount,
                zhoneVdslPerfIntervalLprs
                    HCPerfIntervalCount,
                zhoneVdslPerfIntervalLols
                    HCPerfIntervalCount,
                zhoneVdslPerfIntervalESs
                    HCPerfIntervalCount,
                zhoneVdslPerfIntervalSESs
                    HCPerfIntervalCount,
                zhoneVdslPerfIntervalUASs
                    HCPerfIntervalCount,
                zhoneVdslPerfIntervalInits
                    HCPerfIntervalCount
             }

--  1.3.6.1.4.1.5504.5.13.1.1.5.1.1
        -- 1.3.6.1.4.1.5504.5.13.1.1.5.1.1
        zhoneVdslPerfIntervalNumber OBJECT-TYPE
            SYNTAX Unsigned32 (1..96)
            MAX-ACCESS not-accessible
            STATUS current
            DESCRIPTION
                "Performance Data Interval number 1 is the most recent
                previous interval; interval 96 is 24 hours ago.
                Intervals 2 to 96 are optional."
            ::= { zhoneVdslPerfIntervalEntry 1 }


--  1.3.6.1.4.1.5504.5.13.1.1.5.1.2
        -- 1.3.6.1.4.1.5504.5.13.1.1.5.1.2
        zhoneVdslPerfIntervalLofs OBJECT-TYPE
            SYNTAX HCPerfIntervalCount
            UNITS "seconds"
            MAX-ACCESS read-only
            STATUS current
            DESCRIPTION
                "Count of seconds in the interval when there was Loss
                of Framing."
            REFERENCE
                "T1E1.4/2000-009R3, Part 1, common spec"
            ::= { zhoneVdslPerfIntervalEntry 2 }


--  1.3.6.1.4.1.5504.5.13.1.1.5.1.3
        -- 1.3.6.1.4.1.5504.5.13.1.1.5.1.3
        zhoneVdslPerfIntervalLoss OBJECT-TYPE
            SYNTAX HCPerfIntervalCount
            UNITS "seconds"
            MAX-ACCESS read-only
            STATUS current
            DESCRIPTION
                "Count of seconds in the interval when there was Loss
                of Signal."
            REFERENCE
                "T1E1.4/2000-009R3, Part 1, common spec"
            ::= { zhoneVdslPerfIntervalEntry 3 }


--  1.3.6.1.4.1.5504.5.13.1.1.5.1.4
        -- 1.3.6.1.4.1.5504.5.13.1.1.5.1.4
        zhoneVdslPerfIntervalLprs OBJECT-TYPE
            SYNTAX HCPerfIntervalCount
            UNITS "seconds"
            MAX-ACCESS read-only
            STATUS current
            DESCRIPTION
                "Count of seconds in the interval when there was Loss
                of Power."
            REFERENCE
                "T1E1.4/2000-009R3, Part 1, common spec"
            ::= { zhoneVdslPerfIntervalEntry 4 }


--  1.3.6.1.4.1.5504.5.13.1.1.5.1.5
        -- 1.3.6.1.4.1.5504.5.13.1.1.5.1.5
        zhoneVdslPerfIntervalLols OBJECT-TYPE
            SYNTAX HCPerfIntervalCount
            UNITS "seconds"
            MAX-ACCESS read-only
            STATUS current
            DESCRIPTION
                "Count of seconds in the interval when there was Loss
                of Link."
            ::= { zhoneVdslPerfIntervalEntry 5 }


--  1.3.6.1.4.1.5504.5.13.1.1.5.1.6
        -- 1.3.6.1.4.1.5504.5.13.1.1.5.1.6
        zhoneVdslPerfIntervalESs OBJECT-TYPE
            SYNTAX HCPerfIntervalCount
            UNITS "seconds"
            MAX-ACCESS read-only
            STATUS current
            DESCRIPTION
                "Count of Errored Seconds (ES) in the interval.  An Errored
                Second is a one-second interval containing one or more CRC
                anomalies, one or more LOS or LOF defects."
            REFERENCE
                "T1E1.4/2000-009R3, Part 1, common spec"
            ::= { zhoneVdslPerfIntervalEntry 6 }


--  1.3.6.1.4.1.5504.5.13.1.1.5.1.7
        -- 1.3.6.1.4.1.5504.5.13.1.1.5.1.7
        zhoneVdslPerfIntervalSESs OBJECT-TYPE
            SYNTAX HCPerfIntervalCount
            UNITS "seconds"
            MAX-ACCESS read-only
            STATUS current
            DESCRIPTION
                "Count of Severely Errored Seconds in the interval."
            ::= { zhoneVdslPerfIntervalEntry 7 }


--  1.3.6.1.4.1.5504.5.13.1.1.5.1.8
        -- 1.3.6.1.4.1.5504.5.13.1.1.5.1.8
        zhoneVdslPerfIntervalUASs OBJECT-TYPE
            SYNTAX HCPerfIntervalCount
            UNITS "seconds"
            MAX-ACCESS read-only
            STATUS current
            DESCRIPTION
                "Count of Unavailable Seconds in the interval."
            ::= { zhoneVdslPerfIntervalEntry 8 }


--  1.3.6.1.4.1.5504.5.13.1.1.5.1.9
        -- 1.3.6.1.4.1.5504.5.13.1.1.5.1.9
        zhoneVdslPerfIntervalInits OBJECT-TYPE
            SYNTAX HCPerfIntervalCount
            MAX-ACCESS read-only
            STATUS current
            DESCRIPTION
                "Count of the line initialization attempts during this
                interval.  This count includes both successful and
                failed attempts."
            REFERENCE
                "T1E1.4/2000-009R3, Part 1, common spec"
            ::= { zhoneVdslPerfIntervalEntry 9 }


--  1.3.6.1.4.1.5504.5.13.1.1.6
        -- 1.3.6.1.4.1.5504.5.13.1.1.6
        zhoneVdslPerf1DayIntervalTable OBJECT-TYPE
            SYNTAX SEQUENCE OF ZhoneVdslPerf1DayIntervalEntry
            MAX-ACCESS not-accessible
            STATUS current
            DESCRIPTION
                "This table provides one row for each VDSL performance
                data collection interval.  This table contains live data
                from equipment.  As such, it is NOT persistent."
            ::= { zhoneVdslMibObjects 6 }


--  1.3.6.1.4.1.5504.5.13.1.1.6.1
        -- 1.3.6.1.4.1.5504.5.13.1.1.6.1
        zhoneVdslPerf1DayIntervalEntry OBJECT-TYPE
            SYNTAX ZhoneVdslPerf1DayIntervalEntry
            MAX-ACCESS not-accessible
            STATUS current
            DESCRIPTION
                "An entry in the vdslPerf1DayIntervalTable."
            INDEX { ifIndex, zhoneVdslPhysSide, zhoneVdslPerf1DayIntervalNumber }
            ::= { zhoneVdslPerf1DayIntervalTable 1 }


        ZhoneVdslPerf1DayIntervalEntry ::=
            SEQUENCE {
                zhoneVdslPerf1DayIntervalNumber
                    Unsigned32,
                zhoneVdslPerf1DayIntervalMoniSecs
                    HCPerfTimeElapsed,
                zhoneVdslPerf1DayIntervalLofs
                    Unsigned32,
                zhoneVdslPerf1DayIntervalLoss
                    Unsigned32,
                zhoneVdslPerf1DayIntervalLprs
                    Unsigned32,
                zhoneVdslPerf1DayIntervalLols
                    Unsigned32,
                zhoneVdslPerf1DayIntervalESs
                    Unsigned32,
                zhoneVdslPerf1DayIntervalSESs
                    Unsigned32,
                zhoneVdslPerf1DayIntervalUASs
                    Unsigned32,
                zhoneVdslPerf1DayIntervalInits
                    Unsigned32
             }

--  1.3.6.1.4.1.5504.5.13.1.1.6.1.1
        -- 1.3.6.1.4.1.5504.5.13.1.1.6.1.1
        zhoneVdslPerf1DayIntervalNumber OBJECT-TYPE
            SYNTAX Unsigned32 (1..30)
            MAX-ACCESS not-accessible
            STATUS current
            DESCRIPTION
                "History Data Interval number.  Interval 1 is the most
                recent previous day; interval 30 is 30 days ago.  Intervals
                2 to 30 are optional."
            ::= { zhoneVdslPerf1DayIntervalEntry 1 }


--  1.3.6.1.4.1.5504.5.13.1.1.6.1.2
        -- 1.3.6.1.4.1.5504.5.13.1.1.6.1.2
        zhoneVdslPerf1DayIntervalMoniSecs OBJECT-TYPE
            SYNTAX HCPerfTimeElapsed
            UNITS "seconds"
            MAX-ACCESS read-only
            STATUS current
            DESCRIPTION
                "The amount of time in the 1-day interval over which the
                performance monitoring information is actually counted.
                This value will be the same as the interval duration except
                in a situation where performance monitoring data could not
                be collected for any reason."
            ::= { zhoneVdslPerf1DayIntervalEntry 2 }


--  1.3.6.1.4.1.5504.5.13.1.1.6.1.3
        -- 1.3.6.1.4.1.5504.5.13.1.1.6.1.3
        zhoneVdslPerf1DayIntervalLofs OBJECT-TYPE
            SYNTAX Unsigned32
            UNITS "seconds"
            MAX-ACCESS read-only
            STATUS current
            DESCRIPTION
                "Count of Loss of Frame (LOF) Seconds during the 1-day
                interval as measured by vdslPerf1DayIntervalMoniSecs."
            REFERENCE
                "T1E1.4/2000-009R3, Part 1, common spec"
            ::= { zhoneVdslPerf1DayIntervalEntry 3 }


--  1.3.6.1.4.1.5504.5.13.1.1.6.1.4
        -- 1.3.6.1.4.1.5504.5.13.1.1.6.1.4
        zhoneVdslPerf1DayIntervalLoss OBJECT-TYPE
            SYNTAX Unsigned32
            UNITS "seconds"
            MAX-ACCESS read-only
            STATUS current
            DESCRIPTION
                "Count of Loss of Signal (LOS) Seconds during the 1-day
                interval as measured by vdslPerf1DayIntervalMoniSecs."
            REFERENCE
                "T1E1.4/2000-009R3, Part 1, common spec"
            ::= { zhoneVdslPerf1DayIntervalEntry 4 }


--  1.3.6.1.4.1.5504.5.13.1.1.6.1.5
        -- 1.3.6.1.4.1.5504.5.13.1.1.6.1.5
        zhoneVdslPerf1DayIntervalLprs OBJECT-TYPE
            SYNTAX Unsigned32
            UNITS "seconds"
            MAX-ACCESS read-only
            STATUS current
            DESCRIPTION
                "Count of Loss of Power (LPR) Seconds during the 1-day
                interval as measured by vdslPerf1DayIntervalMoniSecs."
            REFERENCE
                "T1E1.4/2000-009R3, Part 1, common spec"
            ::= { zhoneVdslPerf1DayIntervalEntry 5 }


--  1.3.6.1.4.1.5504.5.13.1.1.6.1.6
        -- 1.3.6.1.4.1.5504.5.13.1.1.6.1.6
        zhoneVdslPerf1DayIntervalLols OBJECT-TYPE
            SYNTAX Unsigned32
            UNITS "seconds"
            MAX-ACCESS read-only
            STATUS current
            DESCRIPTION
                "Count of Loss of Link (LOL) Seconds during the 1-day
                interval as measured by vdslPerf1DayIntervalMoniSecs."
            ::= { zhoneVdslPerf1DayIntervalEntry 6 }


--  1.3.6.1.4.1.5504.5.13.1.1.6.1.7
        -- 1.3.6.1.4.1.5504.5.13.1.1.6.1.7
        zhoneVdslPerf1DayIntervalESs OBJECT-TYPE
            SYNTAX Unsigned32
            UNITS "seconds"
            MAX-ACCESS read-only
            STATUS current
            DESCRIPTION
                "Count of Errored Seconds (ES) during the 1-day
                interval as measured by vdslPerf1DayIntervalMoniSecs."
            REFERENCE
                "T1E1.4/2000-009R3, Part 1, common spec"
            ::= { zhoneVdslPerf1DayIntervalEntry 7 }


--  1.3.6.1.4.1.5504.5.13.1.1.6.1.8
        -- 1.3.6.1.4.1.5504.5.13.1.1.6.1.8
        zhoneVdslPerf1DayIntervalSESs OBJECT-TYPE
            SYNTAX Unsigned32
            UNITS "seconds"
            MAX-ACCESS read-only
            STATUS current
            DESCRIPTION
                "Count of Severely Errored Seconds (SES) during the 1-day
                interval as measured by vdslPerf1DayIntervalMoniSecs."
            ::= { zhoneVdslPerf1DayIntervalEntry 8 }


--  1.3.6.1.4.1.5504.5.13.1.1.6.1.9
        -- 1.3.6.1.4.1.5504.5.13.1.1.6.1.9
        zhoneVdslPerf1DayIntervalUASs OBJECT-TYPE
            SYNTAX Unsigned32
            UNITS "seconds"
            MAX-ACCESS read-only
            STATUS current
            DESCRIPTION
                "Count of Unavailable Seconds (UAS) during the 1-day
                interval as measured by vdslPerf1DayIntervalMoniSecs."
            ::= { zhoneVdslPerf1DayIntervalEntry 9 }


--  1.3.6.1.4.1.5504.5.13.1.1.6.1.10
        -- 1.3.6.1.4.1.5504.5.13.1.1.6.1.10
        zhoneVdslPerf1DayIntervalInits OBJECT-TYPE
            SYNTAX Unsigned32
            UNITS "seconds"
            MAX-ACCESS read-only
            STATUS current
            DESCRIPTION
                "Count of the line initialization attempts during the
                1-day interval as measured by vdslPerf1DayIntervalMoniSecs.
                This count includes both successful and failed attempts."
            REFERENCE
                "T1E1.4/2000-009R3, Part 1, common spec"
            ::= { zhoneVdslPerf1DayIntervalEntry 10 }


--  1.3.6.1.4.1.5504.5.13.1.1.7
        -- 1.3.6.1.4.1.5504.5.13.1.1.7
        zhoneVdslChanPerfDataTable OBJECT-TYPE
            SYNTAX SEQUENCE OF ZhoneVdslChanPerfDataEntry
            MAX-ACCESS not-accessible
            STATUS current
            DESCRIPTION
                "This table provides one row for each Vtu channel.
                VDSL channel interfaces are those ifEntries where
                ifType is equal to interleave(124) or fast(125)."
            ::= { zhoneVdslMibObjects 7 }


--  1.3.6.1.4.1.5504.5.13.1.1.7.1
        -- 1.3.6.1.4.1.5504.5.13.1.1.7.1
        zhoneVdslChanPerfDataEntry OBJECT-TYPE
            SYNTAX ZhoneVdslChanPerfDataEntry
            MAX-ACCESS not-accessible
            STATUS current
            DESCRIPTION
                "An entry in the vdslChanPerfDataTable."
            INDEX { ifIndex, zhoneVdslPhysSide }
            ::= { zhoneVdslChanPerfDataTable 1 }


        ZhoneVdslChanPerfDataEntry ::=
            SEQUENCE {
                zhoneVdslChanValidIntervals
                    Integer32,
                zhoneVdslChanInvalidIntervals
                    Integer32,
                zhoneVdslChanFixedOctets
                    Integer32,
                zhoneVdslChanBadBlks
                    Integer32,
                zhoneVdslChanCurr15MinTimeElapsed
                    Integer32,
                zhoneVdslChanCurr15MinFixedOctets
                    Integer32,
                zhoneVdslChanCurr15MinBadBlks
                    Integer32,
                zhoneVdslChan1DayValidIntervals
                    Integer32,
                zhoneVdslChan1DayInvalidIntervals
                    Integer32,
                zhoneVdslChanCurr1DayTimeElapsed
                    Integer32,
                zhoneVdslChanCurr1DayFixedOctets
                    Integer32,
                zhoneVdslChanCurr1DayBadBlks
                    Integer32
             }

        -- 1.3.6.1.4.1.5504.5.13.1.1.7.1.1
        zhoneVdslChanValidIntervals OBJECT-TYPE
            SYNTAX Integer32 (0..96)
            UNITS "intervals"
            MAX-ACCESS read-only
            STATUS current
            DESCRIPTION
                "Valid Intervals per definition found in
                HC-PerfHist-TC-MIB."
            ::= { zhoneVdslChanPerfDataEntry 1 }


        -- 1.3.6.1.4.1.5504.5.13.1.1.7.1.2
        zhoneVdslChanInvalidIntervals OBJECT-TYPE
            SYNTAX Integer32 (0..96)
            UNITS "intervals"
            MAX-ACCESS read-only
            STATUS current
            DESCRIPTION
                "Invalid Intervals per definition found in
                HC-PerfHist-TC-MIB."
            ::= { zhoneVdslChanPerfDataEntry 2 }


        -- 1.3.6.1.4.1.5504.5.13.1.1.7.1.3
        zhoneVdslChanFixedOctets OBJECT-TYPE
            SYNTAX Integer32
            UNITS "octets"
            MAX-ACCESS read-only
            STATUS current
            DESCRIPTION
                "Count of corrected octets since the unit was last reset."
            REFERENCE
                "T1E1.4/2000-009R3, Part 1, common spec"
            ::= { zhoneVdslChanPerfDataEntry 3 }


        -- 1.3.6.1.4.1.5504.5.13.1.1.7.1.4
        zhoneVdslChanBadBlks OBJECT-TYPE
            SYNTAX Integer32
            UNITS "blocks"
            MAX-ACCESS read-only
            STATUS current
            DESCRIPTION
                "Count of uncorrectable blocks since the unit was last
                reset."
            REFERENCE
                "T1E1.4/2000-009R3, Part 1, common spec"
            ::= { zhoneVdslChanPerfDataEntry 4 }


        -- 1.3.6.1.4.1.5504.5.13.1.1.7.1.5
        zhoneVdslChanCurr15MinTimeElapsed OBJECT-TYPE
            SYNTAX Integer32 (0..86399)
            UNITS "seconds"
            MAX-ACCESS read-only
            STATUS current
            DESCRIPTION
                "Total elapsed seconds in this interval."
            ::= { zhoneVdslChanPerfDataEntry 5 }


        -- 1.3.6.1.4.1.5504.5.13.1.1.7.1.6
        zhoneVdslChanCurr15MinFixedOctets OBJECT-TYPE
            SYNTAX Integer32
            UNITS "octets"
            MAX-ACCESS read-only
            STATUS current
            DESCRIPTION
                "Count of corrected octets in this interval."
            REFERENCE
                "T1E1.4/2000-009R3, Part 1, common spec"
            ::= { zhoneVdslChanPerfDataEntry 6 }


        -- 1.3.6.1.4.1.5504.5.13.1.1.7.1.7
        zhoneVdslChanCurr15MinBadBlks OBJECT-TYPE
            SYNTAX Integer32
            UNITS "blocks"
            MAX-ACCESS read-only
            STATUS current
            DESCRIPTION
                "Count of uncorrectable blocks in this interval."
            REFERENCE
                "T1E1.4/2000-009R3, Part 1, common spec"
            ::= { zhoneVdslChanPerfDataEntry 7 }


        -- 1.3.6.1.4.1.5504.5.13.1.1.7.1.8
        zhoneVdslChan1DayValidIntervals OBJECT-TYPE
            SYNTAX Integer32 (0..96)
            MAX-ACCESS read-only
            STATUS current
            DESCRIPTION
                "Valid Intervals per definition found in
                HC-PerfHist-TC-MIB."
            ::= { zhoneVdslChanPerfDataEntry 8 }


        -- 1.3.6.1.4.1.5504.5.13.1.1.7.1.9
        zhoneVdslChan1DayInvalidIntervals OBJECT-TYPE
            SYNTAX Integer32 (0..96)
            MAX-ACCESS read-only
            STATUS current
            DESCRIPTION
                "Invalid Intervals per definition found in
                HC-PerfHist-TC-MIB."
            ::= { zhoneVdslChanPerfDataEntry 9 }


        -- 1.3.6.1.4.1.5504.5.13.1.1.7.1.10
        zhoneVdslChanCurr1DayTimeElapsed OBJECT-TYPE
            SYNTAX Integer32 (0..86399)
            UNITS "seconds"
            MAX-ACCESS read-only
            STATUS current
            DESCRIPTION
                "Number of seconds that have elapsed since the beginning
                of the current 1-day interval."
            ::= { zhoneVdslChanPerfDataEntry 10 }


        -- 1.3.6.1.4.1.5504.5.13.1.1.7.1.11
        zhoneVdslChanCurr1DayFixedOctets OBJECT-TYPE
            SYNTAX Integer32
            UNITS "octets"
            MAX-ACCESS read-only
            STATUS current
            DESCRIPTION
                "Count of corrected octets since the beginning of the
                current 1-day interval."
            REFERENCE
                "T1E1.4/2000-009R3, Part 1, common spec"
            ::= { zhoneVdslChanPerfDataEntry 11 }


        -- 1.3.6.1.4.1.5504.5.13.1.1.7.1.12
        zhoneVdslChanCurr1DayBadBlks OBJECT-TYPE
            SYNTAX Integer32
            UNITS "blocks"
            MAX-ACCESS read-only
            STATUS current
            DESCRIPTION
                "Count of uncorrectable blocks since the beginning of the
                current 1-day interval."
            REFERENCE
                "T1E1.4/2000-009R3, Part 1, common spec"
            ::= { zhoneVdslChanPerfDataEntry 12 }


--  1.3.6.1.4.1.5504.5.13.1.1.8
        -- 1.3.6.1.4.1.5504.5.13.1.1.8
        zhoneVdslChanIntervalTable OBJECT-TYPE
            SYNTAX SEQUENCE OF ZhoneVdslChanIntervalEntry
            MAX-ACCESS not-accessible
            STATUS current
            DESCRIPTION
                "This table provides one row for each Vtu channel data
                collection interval.  VDSL channel interfaces are those
                ifEntries where ifType is equal to interleave(124) or
                fast(125)."
            ::= { zhoneVdslMibObjects 8 }


--  1.3.6.1.4.1.5504.5.13.1.1.8.1
        -- 1.3.6.1.4.1.5504.5.13.1.1.8.1
        zhoneVdslChanIntervalEntry OBJECT-TYPE
            SYNTAX ZhoneVdslChanIntervalEntry
            MAX-ACCESS not-accessible
            STATUS current
            DESCRIPTION
                "An entry in the vdslChanIntervalTable."
            INDEX { ifIndex, zhoneVdslPhysSide, zhoneVdslChanIntervalNumber }
            ::= { zhoneVdslChanIntervalTable 1 }


        ZhoneVdslChanIntervalEntry ::=
            SEQUENCE {
                zhoneVdslChanIntervalNumber
                    Unsigned32,
                zhoneVdslChanIntervalFixedOctets
                    HCPerfIntervalCount,
                zhoneVdslChanIntervalBadBlks
                    HCPerfIntervalCount
             }

--  1.3.6.1.4.1.5504.5.13.1.1.8.1.1
        -- 1.3.6.1.4.1.5504.5.13.1.1.8.1.1
        zhoneVdslChanIntervalNumber OBJECT-TYPE
            SYNTAX Unsigned32 (1..96)
            MAX-ACCESS not-accessible
            STATUS current
            DESCRIPTION
                "Performance Data Interval number 1 is the most recent
                previous interval; interval 96 is 24 hours ago.
                Intervals 2 to 96 are optional."
            ::= { zhoneVdslChanIntervalEntry 1 }


--  1.3.6.1.4.1.5504.5.13.1.1.8.1.2
        -- 1.3.6.1.4.1.5504.5.13.1.1.8.1.2
        zhoneVdslChanIntervalFixedOctets OBJECT-TYPE
            SYNTAX HCPerfIntervalCount
            UNITS "octets"
            MAX-ACCESS read-only
            STATUS current
            DESCRIPTION
                "Count of corrected octets in this interval."
            REFERENCE
                "T1E1.4/2000-009R3, Part 1, common spec"
            ::= { zhoneVdslChanIntervalEntry 2 }


--  1.3.6.1.4.1.5504.5.13.1.1.8.1.3
        -- 1.3.6.1.4.1.5504.5.13.1.1.8.1.3
        zhoneVdslChanIntervalBadBlks OBJECT-TYPE
            SYNTAX HCPerfIntervalCount
            UNITS "blocks"
            MAX-ACCESS read-only
            STATUS current
            DESCRIPTION
                "Count of uncorrectable blocks in this interval."
            REFERENCE
                "T1E1.4/2000-009R3, Part 1, common spec"
            ::= { zhoneVdslChanIntervalEntry 3 }


--  1.3.6.1.4.1.5504.5.13.1.1.9
        -- 1.3.6.1.4.1.5504.5.13.1.1.9
        zhoneVdslChan1DayIntervalTable OBJECT-TYPE
            SYNTAX SEQUENCE OF ZhoneVdslChan1DayIntervalEntry
            MAX-ACCESS not-accessible
            STATUS current
            DESCRIPTION
                "This table provides one row for each VDSL performance
                data collection interval.  This table contains live data
                from equipment.  As such, it is NOT persistent."
            ::= { zhoneVdslMibObjects 9 }


--  1.3.6.1.4.1.5504.5.13.1.1.9.1
        -- 1.3.6.1.4.1.5504.5.13.1.1.9.1
        zhoneVdslChan1DayIntervalEntry OBJECT-TYPE
            SYNTAX ZhoneVdslChan1DayIntervalEntry
            MAX-ACCESS not-accessible
            STATUS current
            DESCRIPTION
                "An entry in the vdslChan1DayIntervalTable."
            INDEX { ifIndex, zhoneVdslPhysSide, zhoneVdslChan1DayIntervalNumber }
            ::= { zhoneVdslChan1DayIntervalTable 1 }


        ZhoneVdslChan1DayIntervalEntry ::=
            SEQUENCE {
                zhoneVdslChan1DayIntervalNumber
                    Unsigned32,
                zhoneVdslChan1DayIntervalMoniSecs
                    HCPerfTimeElapsed,
                zhoneVdslChan1DayIntervalFixedOctets
                    HCPerfCurrentCount,
                zhoneVdslChan1DayIntervalBadBlks
                    HCPerfCurrentCount
             }

--  1.3.6.1.4.1.5504.5.13.1.1.9.1.1
        -- 1.3.6.1.4.1.5504.5.13.1.1.9.1.1
        zhoneVdslChan1DayIntervalNumber OBJECT-TYPE
            SYNTAX Unsigned32 (1..30)
            MAX-ACCESS not-accessible
            STATUS current
            DESCRIPTION
                "History Data Interval number.  Interval 1 is the most
                recent previous day; interval 30 is 30 days ago.  Intervals
                2 to 30 are optional."
            ::= { zhoneVdslChan1DayIntervalEntry 1 }


--  1.3.6.1.4.1.5504.5.13.1.1.9.1.2
        -- 1.3.6.1.4.1.5504.5.13.1.1.9.1.2
        zhoneVdslChan1DayIntervalMoniSecs OBJECT-TYPE
            SYNTAX HCPerfTimeElapsed
            UNITS "seconds"
            MAX-ACCESS read-only
            STATUS current
            DESCRIPTION
                "The amount of time in the 1-day interval over which the
                performance monitoring information is actually counted.
                This value will be the same as the interval duration except
                in a situation where performance monitoring data could not
                be collected for any reason."
            ::= { zhoneVdslChan1DayIntervalEntry 2 }


--  1.3.6.1.4.1.5504.5.13.1.1.9.1.3
        -- 1.3.6.1.4.1.5504.5.13.1.1.9.1.3
        zhoneVdslChan1DayIntervalFixedOctets OBJECT-TYPE
            SYNTAX HCPerfCurrentCount
            UNITS "octets"
            MAX-ACCESS read-only
            STATUS current
            DESCRIPTION
                "Count of corrected octets in this interval."
            REFERENCE
                "T1E1.4/2000-009R3, Part 1, common spec"
            ::= { zhoneVdslChan1DayIntervalEntry 3 }


--  1.3.6.1.4.1.5504.5.13.1.1.9.1.4
        -- 1.3.6.1.4.1.5504.5.13.1.1.9.1.4
        zhoneVdslChan1DayIntervalBadBlks OBJECT-TYPE
            SYNTAX HCPerfCurrentCount
            UNITS "blocks"
            MAX-ACCESS read-only
            STATUS current
            DESCRIPTION
                "Count of uncorrectable blocks in this interval."
            REFERENCE
                "T1E1.4/2000-009R3, Part 1, common spec"
            ::= { zhoneVdslChan1DayIntervalEntry 4 }


--   profile tables
--
-- 1.3.6.1.4.1.5504.5.13.1.1.11
        -- 1.3.6.1.4.1.5504.5.13.1.1.11
        zhoneVdslLineConfProfileTable OBJECT-TYPE
            SYNTAX SEQUENCE OF ZhoneVdslLineConfProfileEntry
            MAX-ACCESS not-accessible
            STATUS current
            DESCRIPTION
                "This table contains information on the VDSL line
                configuration.  One entry in this table reflects a
                profile defined by a manager which can be used to
                configure the VDSL line.

                Entries in this table MUST be maintained in a
                persistent manner."
            ::= { zhoneVdslMibObjects 11 }


--  1.3.6.1.4.1.5504.5.13.1.1.11.1
        -- 1.3.6.1.4.1.5504.5.13.1.1.11.1
        zhoneVdslLineConfProfileEntry OBJECT-TYPE
            SYNTAX ZhoneVdslLineConfProfileEntry
            MAX-ACCESS not-accessible
            STATUS current
            DESCRIPTION
                "Each entry consists of a list of parameters that
                represents the configuration of a VDSL line.

                A default profile with an index of 'DEFVAL', will
                always exist and its parameters will be set to vendor
                specific values, unless otherwise specified in this
                document."
            INDEX { ifIndex }
            ::= { zhoneVdslLineConfProfileTable 1 }


        ZhoneVdslLineConfProfileEntry ::=
            SEQUENCE {
                zhoneVdslLineConfProfileName
                    SnmpAdminString,
                zhoneVdslLineConfDownRateMode
                    INTEGER,
                zhoneVdslLineConfUpRateMode
                    INTEGER,
                zhoneVdslLineConfDownMaxPwr
                    Integer32,
                zhoneVdslLineConfUpMaxPwr
                    Integer32,
                zhoneVdslLineConfDownMaxSnrMgn
                    Unsigned32,
                zhoneVdslLineConfDownMinSnrMgn
                    Unsigned32,
                zhoneVdslLineConfDownTargetSnrMgn
                    Unsigned32,
                zhoneVdslLineConfUpMaxSnrMgn
                    Unsigned32,
                zhoneVdslLineConfUpMinSnrMgn
                    Unsigned32,
                zhoneVdslLineConfUpTargetSnrMgn
                    Unsigned32,
                zhoneVdslLineConfDownFastMaxDataRate
                    Unsigned32,
                zhoneVdslLineConfDownFastMinDataRate
                    Unsigned32,
                zhoneVdslLineConfDownSlowMaxDataRate
                    Unsigned32,
                zhoneVdslLineConfDownSlowMinDataRate
                    Unsigned32,
                zhoneVdslLineConfUpFastMaxDataRate
                    Unsigned32,
                zhoneVdslLineConfUpFastMinDataRate
                    Unsigned32,
                zhoneVdslLineConfUpSlowMaxDataRate
                    Unsigned32,
                zhoneVdslLineConfUpSlowMinDataRate
                    Unsigned32,
                zhoneVdslLineConfDownRateRatio
                    Unsigned32,
                zhoneVdslLineConfUpRateRatio
                    Unsigned32,
                zhoneVdslLineConfDownMaxInterDelay
                    Unsigned32,
                zhoneVdslLineConfUpMaxInterDelay
                    Unsigned32,
                zhoneVdslLineConfDownPboControl
                    INTEGER,
                zhoneVdslLineConfUpPboControl
                    INTEGER,
                zhoneVdslLineConfDownPboLevel
                    Unsigned32,
                zhoneVdslLineConfUpPboLevel
                    Unsigned32,
                zhoneVdslLineConfDeploymentScenario
                    INTEGER,
                zhoneVdslLineConfAdslPresence
                    INTEGER,
                zhoneVdslLineConfApplicableStandard
                    INTEGER,
                zhoneVdslLineConfBandPlan
                    INTEGER,
                zhoneVdslLineConfBandPlanFx
                    Unsigned32,
                zhoneVdslLineConfBandOptUsage
                    INTEGER,
                zhoneVdslLineConfUpPsdTemplate
                    INTEGER,
                zhoneVdslLineConfDownPsdTemplate
                    INTEGER,
                zhoneVdslLineConfHamBandMask
                    BITS,
                zhoneVdslLineConfCustomNotch1Start
                    Unsigned32,
                zhoneVdslLineConfCustomNotch1Stop
                    Unsigned32,
                zhoneVdslLineConfCustomNotch2Start
                    Unsigned32,
                zhoneVdslLineConfCustomNotch2Stop
                    Unsigned32,
                zhoneVdslLineConfDownTargetSlowBurst
                    Unsigned32,
                zhoneVdslLineConfUpTargetSlowBurst
                    Unsigned32,
                zhoneVdslLineConfDownMaxFastFec
                    Unsigned32,
                zhoneVdslLineConfUpMaxFastFec
                    Unsigned32,
                zhoneVdslLineConfLineType
                    INTEGER,
                zhoneVdslLineConfProfRowStatus
                    RowStatus,
                zhoneVdslLineConfTransmissionMode
                    INTEGER,
                zhoneVdslLineConfVdsl2Profile
                    INTEGER,
                zhoneVdslLineConfVdslMode
                    INTEGER,
                zhoneVdslLineConfPboElectricalOverride
                    Integer32,
                zhoneVdslLineConfAutoModeCrtrn
                    INTEGER,
                zhoneVdslLineConfNetworkTimingRef
                    INTEGER,
                zhoneVdslLineConfAdslBandMode
                    INTEGER,
                zhoneVdslLineConfAdslBandModeEndFreq
                    Integer32,
                zhoneVdslLineConfSeltEchoMeasurementTime
                    Integer32,
                zhoneVdslLineConfSeltNoiseMeasurementTime
                    Integer32,
                zhoneVdslLineConfSeltAgc
                    Integer32,
                zhoneVdslLineConfDownTrellis
                    INTEGER,
                zhoneVdslLineConfUpTrellis
                    INTEGER,
                zhoneVdslLineConfDownMaxAggregateTxPwr
                    INTEGER,
                zhoneVdslLineConfUpMaxAggregateTxPwr
                    INTEGER,
                zhoneVdslLineConfDownMaxPsd
                    Integer32,
                zhoneVdslLineConfUpMaxPsd
                    Integer32,
                zhoneVdslLineConfDownPsdShape
                    INTEGER,
                zhoneVdslLineConfUpPsdShape
                    INTEGER,
                zhoneVdslLineConfDownVirtualNoiseSnrMode
                    INTEGER,
                zhoneVdslLineConfUpVirtualNoiseSnrMode
                    INTEGER,
                zhoneVdslLineConfDownErasureDetectionFast
                    INTEGER,
                zhoneVdslLineConfUpErasureDetectionFast
                    INTEGER,
                zhoneVdslLineConfDownErasureDetectionInterleave
                    INTEGER,
                zhoneVdslLineConfUpErasureDetectionInterleave
                    INTEGER,
                zhoneVdslLineConfDownGhsA43TonePwr
                    INTEGER,
                zhoneVdslLineConfDownGhsB43TonePwr
                    INTEGER,
                zhoneVdslLineConfDownGhsA43cTonePwr
                    INTEGER,
                zhoneVdslLineConfDownGhsV43TonePwr
                    INTEGER,
                zhoneVdslLineConfDownGhsA43TonePwrMaxLvl
                    Integer32,
                zhoneVdslLineConfDownGhsB43TonePwrMaxLvl
                    Integer32,
                zhoneVdslLineConfDownGhsA43cTonePwrMaxLvl
                    Integer32,
                zhoneVdslLineConfDownGhsV43TonePwrMaxLvl
                    Integer32,
                zhoneVdslLineConfDownRsCoding
                    INTEGER,
                zhoneVdslLineConfUpRsCoding
                    INTEGER,
                zhoneVdslLineConfUpPboPsdTemplate
                    INTEGER,
                zhoneVdslLineConfUpPboPsdParamA1
                    Integer32,
                zhoneVdslLineConfUpPboPsdParamA2
                    Integer32,
                zhoneVdslLineConfUpPboPsdParamB1
                    Integer32,
                zhoneVdslLineConfUpPboPsdParamB2
                    Integer32,
                zhoneVdslLineConfDownDownshiftSnrMgn
                    Integer32,
                zhoneVdslLineConfDownUpshiftSnrMgn
                    Integer32,
                zhoneVdslLineConfDownMinDownshiftTime
                    Integer32,
                zhoneVdslLineConfDownMinUpshiftTime
                    Integer32,
                zhoneVdslLineConfUpDownshiftSnrMgn
                    Integer32,
                zhoneVdslLineConfUpUpshiftSnrMgn
                    Integer32,
                zhoneVdslLineConfUpMinDownshiftTime
                    Integer32,
                zhoneVdslLineConfUpMinUpshiftTime
                    Integer32,
                zhoneVdslLineConfDownMinTxThresholdAlarm
                    Unsigned32,
                zhoneVdslLineConfUpMinTxThresholdAlarm
                    Unsigned32,
                zhoneVdslLineConfPotsBypassRelayMaxDuration
                    INTEGER,
                zhoneVdslLineConfDMTConfMode
                    INTEGER,
                zhoneVdslLineConfDownBitSwap
                    INTEGER,
                zhoneVdslLineConfUpBitSwap
                    INTEGER,
                zhoneVdslLineConfAdslAnnexMModeEnabled
                    TruthValue,
                zhoneVdslLineConfAdslAnnexMPsdMask
                    INTEGER,
                zhoneVdslLineConfUs0BoundaryTone
                    INTEGER,
                zhoneVdslLineConfDownInp
                    INTEGER,
                zhoneVdslLineConfUpInp
                    INTEGER,
                zhoneVdslLineConfDownMaxInterleavingDelay
                    INTEGER,
                zhoneVdslLineConfUpMaxInterleavingDelay
                    INTEGER,
                zhoneVdslLineConfDownPsdMaskEnable
                    INTEGER,
                zhoneVdslLineConfUpPsdMaskEnable
                    INTEGER,
                zhoneVdslLineConfDownPsdMaskSelect
                    INTEGER,
                zhoneVdslLineConfUpPsdMaskSelect
                    INTEGER,
                zhoneVdslLineEnableTrellisCoding
                    TruthValue,
                zhoneVdslLineEnableRsCoding
                    TruthValue,
                zhoneVdslLineConfPsdShape
                    INTEGER,
                zhoneVdslLineConfDownPhyRSupport
                    INTEGER,
                zhoneVdslLineConfUpPhyRSupport
                    INTEGER,
                zhoneVdslLineConfDownPhyRmaxINP
                    INTEGER,
                zhoneVdslLineConfUpPhyRmaxINP
                    INTEGER,
                zhoneVdslLineConfDownPhyRminRSoverhead
                    INTEGER,
                zhoneVdslLineConfUpPhyRminRSoverhead
                    INTEGER,
                zhoneVdslLineConfDownPhyRRtxRatio
                    INTEGER,
                zhoneVdslLineConfUpPhyRRtxRatio
                    INTEGER,
                zhoneVdslLineConfUpPboPsdParamA3
                    Integer32,
                zhoneVdslLineConfUpPboPsdParamA4
                    Integer32,
                zhoneVdslLineConfUpPboPsdParamB3
                    Integer32,
                zhoneVdslLineConfUpPboPsdParamB4
                    Integer32,
                zhoneVdslLineConfFallbackDefaultVpi
                    Unsigned32,
                zhoneVdslLineConfFallbackDefaultVci
                    Unsigned32,
                zhoneVdslLineConfDownGinpSupport
                    INTEGER,
                zhoneVdslLineConfUpGinpSupport
                    INTEGER,
                zhoneVdslLineConfDownGinpEtrMax
                    Unsigned32,
                zhoneVdslLineConfUpGinpEtrMax
                    Unsigned32,
                zhoneVdslLineConfDownGinpEtrMin
                    Unsigned32,
                zhoneVdslLineConfUpGinpEtrMin
                    Unsigned32,
                zhoneVdslLineConfDownGinpNdrMax
                    Unsigned32,
                zhoneVdslLineConfUpGinpNdrMax
                    Unsigned32,
                zhoneVdslLineConfDownGinpShineRatio
                    Unsigned32,
                zhoneVdslLineConfUpGinpShineRatio
                    Unsigned32,
                zhoneVdslLineConfDownGinpLeftrThreshold
                    Unsigned32,
                zhoneVdslLineConfUpGinpLeftrThreshold
                    Unsigned32,
                zhoneVdslLineConfDownGinpMaxDelay
                    Unsigned32,
                zhoneVdslLineConfUpGinpMaxDelay
                    Unsigned32,
                zhoneVdslLineConfDownGinpMinDelay
                    Unsigned32,
                zhoneVdslLineConfUpGinpMinDelay
                    Unsigned32,
                zhoneVdslLineConfDownGinpMin
                    Unsigned32,
                zhoneVdslLineConfUpGinpMin
                    Unsigned32,
                zhoneVdslLineConfDownGinpMinRSoverhead
                    Unsigned32,
                zhoneVdslLineConfUpGinpMinRSoverhead
                    Unsigned32,
                zhoneVdslLineConfDownGinpReinCfg
                    Unsigned32,
                zhoneVdslLineConfUpGinpReinCfg
                    Unsigned32,
                zhoneVdslLineConfDownGinpReinFreq
                    INTEGER,
                zhoneVdslLineConfUpGinpReinFreq
                    INTEGER,
                zhoneVdslLineConfDownGinpRtxMode
                    INTEGER,
                zhoneVdslLineConfUpGinpRtxMode
                    INTEGER
             }

--  1.3.6.1.4.1.5504.5.13.1.1.11.1.1
        -- 1.3.6.1.4.1.5504.5.13.1.1.11.1.1
        zhoneVdslLineConfProfileName OBJECT-TYPE
            SYNTAX SnmpAdminString (SIZE (1..32))
            MAX-ACCESS not-accessible
            STATUS current
            DESCRIPTION
                "This object identifies a row in this table.

                A default profile with an index of 'DEFVAL', will
                always exist and its parameters will be set to vendor
                specific values, unless otherwise specified in this
                document."
            ::= { zhoneVdslLineConfProfileEntry 1 }


        -- 1.3.6.1.4.1.5504.5.13.1.1.11.1.2
        zhoneVdslLineConfDownRateMode OBJECT-TYPE
            SYNTAX INTEGER
                {
                manual(1),
                adapt-at-init(2),
                dynamic(3)
                }
            MAX-ACCESS read-create
            STATUS current
            DESCRIPTION
                "Specifies the rate selection behavior for the line
                in the downstream direction.

                manual(1)       forces the rate to the configured rate
                adaptAtInit(2)  adapts the line at initialization only
                dynamic(3)      adapts the line at initialization and showtime"
            DEFVAL { dynamic }
            ::= { zhoneVdslLineConfProfileEntry 2 }


        -- 1.3.6.1.4.1.5504.5.13.1.1.11.1.3
        zhoneVdslLineConfUpRateMode OBJECT-TYPE
            SYNTAX INTEGER
                {
                manual(1),
                adapt-at-init(2),
                dynamic(3)
                }
            MAX-ACCESS read-create
            STATUS current
            DESCRIPTION
                "Specifies the rate selection behavior for the line
                in the upstream direction.

                manual(1)       forces the rate to the configured rate
                adaptAtInit(2)  adapts the line at initialization only
                dynamic(3)      adapts the line at initialization and showtime"
            DEFVAL { dynamic }
            ::= { zhoneVdslLineConfProfileEntry 3 }


        -- 1.3.6.1.4.1.5504.5.13.1.1.11.1.4
        zhoneVdslLineConfDownMaxPwr OBJECT-TYPE
            SYNTAX Integer32 (-50..200)
            UNITS "0.10dBm"
            MAX-ACCESS read-create
            STATUS current
            DESCRIPTION
                "Specifies the maximum aggregate downstream power
                level in the range -5.0 to 20.0 dBm."
            REFERENCE
                "T1E1.4/2000-009R3, Part 1, common spec"
            DEFVAL { 145 }
            ::= { zhoneVdslLineConfProfileEntry 4 }


        -- 1.3.6.1.4.1.5504.5.13.1.1.11.1.5
        zhoneVdslLineConfUpMaxPwr OBJECT-TYPE
            SYNTAX Integer32 (-130..200)
            UNITS "0.10dBm"
            MAX-ACCESS read-create
            STATUS current
            DESCRIPTION
                "Specifies the maximum aggregate upstream power
                level in the range -13.0 to 20.0 dBm."
            REFERENCE
                "T1E1.4/2000-009R3, Part 1, common spec"
            DEFVAL { 145 }
            ::= { zhoneVdslLineConfProfileEntry 5 }


        -- 1.3.6.1.4.1.5504.5.13.1.1.11.1.6
        zhoneVdslLineConfDownMaxSnrMgn OBJECT-TYPE
            SYNTAX Unsigned32 (0..310)
            UNITS "0.10dBm"
            MAX-ACCESS read-create
            STATUS current
            DESCRIPTION
                "Specifies the maximum downstream Signal/Noise Margin
                in units of 0.10 dB, for a range of 0 to 31.0 dB."
            REFERENCE
                "T1E1.4/2000-009R3, Part 1, common spec"
            DEFVAL { 160 }
            ::= { zhoneVdslLineConfProfileEntry 6 }


        -- 1.3.6.1.4.1.5504.5.13.1.1.11.1.7
        zhoneVdslLineConfDownMinSnrMgn OBJECT-TYPE
            SYNTAX Unsigned32 (0..310)
            UNITS "0.10dBm"
            MAX-ACCESS read-create
            STATUS current
            DESCRIPTION
                "Specifies the minimum downstream Signal/Noise Margin
                in units of 0.10 dB, for a range of 0 to 31.0 dB."
            REFERENCE
                "T1E1.4/2000-009R3, Part 1, common spec"
            DEFVAL { 0 }
            ::= { zhoneVdslLineConfProfileEntry 7 }


        -- 1.3.6.1.4.1.5504.5.13.1.1.11.1.8
        zhoneVdslLineConfDownTargetSnrMgn OBJECT-TYPE
            SYNTAX Unsigned32 (0..310)
            UNITS "0.10dBm"
            MAX-ACCESS read-create
            STATUS current
            DESCRIPTION
                "Specifies the target downstream Signal/Noise Margin
                in units of 0.10 dB, for a range of 0 to 31.0 dB.
                This is the Noise Margin the transceivers must achieve
                with a BER of 10^-7 or better to successfully complete
                initialization."
            REFERENCE
                "T1E1.4/2000-009R3, Part 1, common spec"
            DEFVAL { 24 }
            ::= { zhoneVdslLineConfProfileEntry 8 }


        -- 1.3.6.1.4.1.5504.5.13.1.1.11.1.9
        zhoneVdslLineConfUpMaxSnrMgn OBJECT-TYPE
            SYNTAX Unsigned32 (0..310)
            UNITS "0.10dBm"
            MAX-ACCESS read-create
            STATUS current
            DESCRIPTION
                "Specifies the maximum upstream Signal/Noise Margin
                in units of 0.10 dB, for a range of 0 to 31.0 dB."
            REFERENCE
                "T1E1.4/2000-009R3, Part 1, common spec"
            DEFVAL { 160 }
            ::= { zhoneVdslLineConfProfileEntry 9 }


        -- 1.3.6.1.4.1.5504.5.13.1.1.11.1.10
        zhoneVdslLineConfUpMinSnrMgn OBJECT-TYPE
            SYNTAX Unsigned32 (0..310)
            UNITS "0.10dBm"
            MAX-ACCESS read-create
            STATUS current
            DESCRIPTION
                "Specifies the minimum upstream Signal/Noise Margin
                in units of 0.10 dB, for a range of 0 to 31.0 dB."
            REFERENCE
                "T1E1.4/2000-009R3, Part 1, common spec"
            DEFVAL { 0 }
            ::= { zhoneVdslLineConfProfileEntry 10 }


        -- 1.3.6.1.4.1.5504.5.13.1.1.11.1.11
        zhoneVdslLineConfUpTargetSnrMgn OBJECT-TYPE
            SYNTAX Unsigned32 (0..310)
            UNITS "0.10dBm"
            MAX-ACCESS read-create
            STATUS current
            DESCRIPTION
                "Specifies the target upstream Signal/Noise Margin in
                units of 0.10 dB, for a range of 0 to 31.0 dB.  This
                is the Noise Margin the transceivers must achieve with
                a BER of 10^-7 or better to successfully complete
                initialization."
            REFERENCE
                "T1E1.4/2000-009R3, Part 1, common spec"
            DEFVAL { 24 }
            ::= { zhoneVdslLineConfProfileEntry 11 }


        -- 1.3.6.1.4.1.5504.5.13.1.1.11.1.12
        zhoneVdslLineConfDownFastMaxDataRate OBJECT-TYPE
            SYNTAX Unsigned32 (0..200000)
            UNITS "kbps"
            MAX-ACCESS read-create
            STATUS current
            DESCRIPTION
                "Specifies the maximum downstream fast channel
                data rate in steps of 1000 bits/second."
            DEFVAL { 200000 }
            ::= { zhoneVdslLineConfProfileEntry 12 }


        -- 1.3.6.1.4.1.5504.5.13.1.1.11.1.13
        zhoneVdslLineConfDownFastMinDataRate OBJECT-TYPE
            SYNTAX Unsigned32 (0..200000)
            UNITS "kbps"
            MAX-ACCESS read-create
            STATUS current
            DESCRIPTION
                "Specifies the minimum downstream fast channel
                data rate in steps of 1000 bits/second."
            DEFVAL { 0 }
            ::= { zhoneVdslLineConfProfileEntry 13 }


        -- 1.3.6.1.4.1.5504.5.13.1.1.11.1.14
        zhoneVdslLineConfDownSlowMaxDataRate OBJECT-TYPE
            SYNTAX Unsigned32 (0..200000)
            UNITS "kbps"
            MAX-ACCESS read-create
            STATUS current
            DESCRIPTION
                "Specifies the maximum downstream slow channel
                data rate in steps of 1000 bits/second.

                The maximum aggregate downstream transmit speed
                of the line can be derived from the sum of maximum
                downstream fast and slow channel data rates."
            DEFVAL { 200000 }
            ::= { zhoneVdslLineConfProfileEntry 14 }


        -- 1.3.6.1.4.1.5504.5.13.1.1.11.1.15
        zhoneVdslLineConfDownSlowMinDataRate OBJECT-TYPE
            SYNTAX Unsigned32 (0..200000)
            UNITS "kbps"
            MAX-ACCESS read-create
            STATUS current
            DESCRIPTION
                "Specifies the minimum downstream slow channel
                data rate in steps of 1000 bits/second.

                The minimum aggregate downstream transmit speed
                of the line can be derived from the sum of minimum
                downstream fast and slow channel data rates."
            DEFVAL { 0 }
            ::= { zhoneVdslLineConfProfileEntry 15 }


        -- 1.3.6.1.4.1.5504.5.13.1.1.11.1.16
        zhoneVdslLineConfUpFastMaxDataRate OBJECT-TYPE
            SYNTAX Unsigned32 (0..200000)
            UNITS "kbps"
            MAX-ACCESS read-create
            STATUS current
            DESCRIPTION
                "Specifies the maximum upstream fast channel
                data rate in steps of 1000 bits/second.

                The maximum aggregate upstream transmit speed
                of the line can be derived from the sum of maximum
                upstream fast and slow channel data rates."
            DEFVAL { 200000 }
            ::= { zhoneVdslLineConfProfileEntry 16 }


        -- 1.3.6.1.4.1.5504.5.13.1.1.11.1.17
        zhoneVdslLineConfUpFastMinDataRate OBJECT-TYPE
            SYNTAX Unsigned32 (0..200000)
            UNITS "kbps"
            MAX-ACCESS read-create
            STATUS current
            DESCRIPTION
                "Specifies the minimum upstream fast channel
                data rate in steps of 1000 bits/second.

                The minimum aggregate upstream transmit speed
                of the line can be derived from the sum of minimum
                upstream fast and slow channel data rates."
            DEFVAL { 0 }
            ::= { zhoneVdslLineConfProfileEntry 17 }


        -- 1.3.6.1.4.1.5504.5.13.1.1.11.1.18
        zhoneVdslLineConfUpSlowMaxDataRate OBJECT-TYPE
            SYNTAX Unsigned32 (0..200000)
            UNITS "kbps"
            MAX-ACCESS read-create
            STATUS current
            DESCRIPTION
                "Specifies the maximum upstream slow channel
                data rate in steps of 1000 bits/second."
            DEFVAL { 200000 }
            ::= { zhoneVdslLineConfProfileEntry 18 }


        -- 1.3.6.1.4.1.5504.5.13.1.1.11.1.19
        zhoneVdslLineConfUpSlowMinDataRate OBJECT-TYPE
            SYNTAX Unsigned32 (0..200000)
            UNITS "kbps"
            MAX-ACCESS read-create
            STATUS current
            DESCRIPTION
                "Specifies the minimum upstream slow channel
                data rate in steps of 1000 bits/second."
            DEFVAL { 0 }
            ::= { zhoneVdslLineConfProfileEntry 19 }


        -- 1.3.6.1.4.1.5504.5.13.1.1.11.1.20
        zhoneVdslLineConfDownRateRatio OBJECT-TYPE
            SYNTAX Unsigned32 (0..100)
            UNITS "percent"
            MAX-ACCESS read-create
            STATUS current
            DESCRIPTION
                "For dynamic rate adaptation at startup, the allocation
                of data rate in excess of the minimum data rate for each
                channel is controlled by the object.  This object specifies
                the ratio of the allocation of the excess data rate between
                the fast and the slow channels.  This allocation represents
                downstream Fast Channel Allocation / Slow Channel
                Allocation."
            DEFVAL { 50 }
            ::= { zhoneVdslLineConfProfileEntry 20 }


        -- 1.3.6.1.4.1.5504.5.13.1.1.11.1.21
        zhoneVdslLineConfUpRateRatio OBJECT-TYPE
            SYNTAX Unsigned32 (0..100)
            UNITS "percent"
            MAX-ACCESS read-create
            STATUS current
            DESCRIPTION
                "For dynamic rate adaptation at startup, the allocation
                of data rate in excess of the minimum data rate for each
                channel is controlled by the object.  This object specifies
                the ratio of the allocation of the excess data rate between
                the fast and the slow channels.  This allocation represents
                upstream Fast Channel Allocation/Slow Channel Allocation."
            DEFVAL { 0 }
            ::= { zhoneVdslLineConfProfileEntry 21 }


        -- 1.3.6.1.4.1.5504.5.13.1.1.11.1.22
        zhoneVdslLineConfDownMaxInterDelay OBJECT-TYPE
            SYNTAX Unsigned32 (0..255)
            UNITS "milliseconds"
            MAX-ACCESS read-create
            STATUS current
            DESCRIPTION
                "Specifies the maximum interleave delay for the
                downstream slow channel."
            DEFVAL { 80 }
            ::= { zhoneVdslLineConfProfileEntry 22 }


        -- 1.3.6.1.4.1.5504.5.13.1.1.11.1.23
        zhoneVdslLineConfUpMaxInterDelay OBJECT-TYPE
            SYNTAX Unsigned32 (0..255)
            UNITS "milliseconds"
            MAX-ACCESS read-create
            STATUS current
            DESCRIPTION
                "Specifies the maximum interleave delay for the
                upstream slow channel."
            DEFVAL { 80 }
            ::= { zhoneVdslLineConfProfileEntry 23 }


        -- 1.3.6.1.4.1.5504.5.13.1.1.11.1.24
        zhoneVdslLineConfDownPboControl OBJECT-TYPE
            SYNTAX INTEGER
                {
                disabled(1),
                auto(2),
                manual(3)
                }
            MAX-ACCESS read-create
            STATUS current
            DESCRIPTION
                "Downstream power backoff (PBO) control for this
                line.  For transceivers which do not support downstream
                PBO control, this object MUST be fixed at disabled(1).
                If auto(2) is selected, the transceiver will automatically
                adjust the power backoff.  If manual(3) is selected,

                then the transceiver will use the value from
                zhoneVdslLineConfDownPboLevel."
            DEFVAL { disabled }
            ::= { zhoneVdslLineConfProfileEntry 24 }


        -- 1.3.6.1.4.1.5504.5.13.1.1.11.1.25
        zhoneVdslLineConfUpPboControl OBJECT-TYPE
            SYNTAX INTEGER
                {
                disabled(1),
                auto(2),
                manual(3)
                }
            MAX-ACCESS read-create
            STATUS current
            DESCRIPTION
                "Upstream power backoff (PBO) control for this
                line.  For transceivers which do not support upstream
                PBO control, this object MUST be fixed at disabled(1).
                If auto(2) is selected, the transceiver will automatically
                adjust the power backoff.  If manual(3) is selected,
                then the transceiver will use the value from
                zhoneVdslLineConfUpPboLevel."
            DEFVAL { disabled }
            ::= { zhoneVdslLineConfProfileEntry 25 }


        -- 1.3.6.1.4.1.5504.5.13.1.1.11.1.26
        zhoneVdslLineConfDownPboLevel OBJECT-TYPE
            SYNTAX Unsigned32 (0..160)
            UNITS "0.25dB"
            MAX-ACCESS read-create
            STATUS current
            DESCRIPTION
                "Specifies the downstream backoff level to be used
                when vdslLineConfDownPboControl = manual(3)."
            DEFVAL { 0 }
            ::= { zhoneVdslLineConfProfileEntry 26 }


        -- 1.3.6.1.4.1.5504.5.13.1.1.11.1.27
        zhoneVdslLineConfUpPboLevel OBJECT-TYPE
            SYNTAX Unsigned32 (0..160)
            UNITS "0.25dB"
            MAX-ACCESS read-create
            STATUS current
            DESCRIPTION
                "Specifies the upstream backoff level to be used
                when vdslLineConfUpPboControl = manual(3)."
            DEFVAL { 0 }
            ::= { zhoneVdslLineConfProfileEntry 27 }


        -- 1.3.6.1.4.1.5504.5.13.1.1.11.1.28
        zhoneVdslLineConfDeploymentScenario OBJECT-TYPE
            SYNTAX INTEGER
                {
                fttCab(1),
                fttEx(2),
                other(3)
                }
            MAX-ACCESS read-create
            STATUS current
            DESCRIPTION
                "The VDSL line deployment scenario.  When using
                fttCab(1), the VTU-C is located in a street cabinet.
                When using fttEx(2), the VTU-C is located at the
                central office.  Changes to this value will have
                no effect on the transceiver."
            REFERENCE
                "DSL Forum TR-057"
            DEFVAL { fttCab }
            ::= { zhoneVdslLineConfProfileEntry 28 }


--  1.3.6.1.4.1.5504.5.13.1.1.11.1.29
        -- 1.3.6.1.4.1.5504.5.13.1.1.11.1.29
        zhoneVdslLineConfAdslPresence OBJECT-TYPE
            SYNTAX INTEGER
                {
                none(1),
                adslOverPots(2),
                adslOverISDN(3)
                }
            MAX-ACCESS read-create
            STATUS current
            DESCRIPTION
                "Indicates presence of ADSL service in the associated
                cable bundle/binder.

                none(1)         indicates no ADSL service in the bundle
                adslOverPots(2) indicates ADSL service over POTS is
                                present in the bundle
                adslOverISDN(3) indicates ADSL service over ISDN is
                                present in the bundle"
            DEFVAL { none }
            ::= { zhoneVdslLineConfProfileEntry 29 }


        -- 1.3.6.1.4.1.5504.5.13.1.1.11.1.30
        zhoneVdslLineConfApplicableStandard OBJECT-TYPE
            SYNTAX INTEGER
                {
                ansi(1),
                etsi(2),
                itu(3),
                other(4)
                }
            MAX-ACCESS read-create
            STATUS current
            DESCRIPTION
                "The VDSL standard to be used for the line.

                ansi(1)      indicates ANSI standard
                etsi(2)      indicates ETSI standard
                itu(3)       indicates ITU standard
                other(4)     indicates a standard other than the above."
            DEFVAL { ansi }
            ::= { zhoneVdslLineConfProfileEntry 30 }


        -- 1.3.6.1.4.1.5504.5.13.1.1.11.1.31
        zhoneVdslLineConfBandPlan OBJECT-TYPE
            SYNTAX INTEGER
                {
                bandPlan997(1),
                bandPlan998(2),
                bandPlanFx(3),
                other(4),
                bandPlan997-2(5),
                bandPlan997-3(6),
                bandPlan998-2(7),
                bandPlan998-3(8),
                bandPlan998-17-6(9),
                fx-2(10),
                fx-3(11),
                china-a-2(12),
                china-a-3(13),
                china-b-2(14),
                china-b-3(15)
                }
            MAX-ACCESS read-create
            STATUS current
            DESCRIPTION
                "The VDSL band plan to be used for the line.

                bandPlan997(1) is to be used for
                     ITU-T G.993.1 Bandplan-B
                     ETSI Bandplan
                     ANSI Plan 997

                bandPlan998(2) is to be used for
                     ITU-T G.993.1 Bandplan-A
                     ANSI Plan 998

                bandPlanFx(3) is to be used for
                     ITU-T G.993.1 Bandplan-C.

                other(4) is to be used for
                     non-standard bandplans.

                If this object is set to bandPlanFx(3), then the
                object vdslLineConfBandPlanFx MUST also be set."
            DEFVAL { bandPlan998 }
            ::= { zhoneVdslLineConfProfileEntry 31 }


        -- 1.3.6.1.4.1.5504.5.13.1.1.11.1.32
        zhoneVdslLineConfBandPlanFx OBJECT-TYPE
            SYNTAX Unsigned32 (3750..12000)
            UNITS "kHz"
            MAX-ACCESS read-create
            STATUS current
            DESCRIPTION
                "The frequency limit between bands D2 and U2 when
                zhoneVdslLineConfBandPlan is set to bandPlanFx(3)."
            DEFVAL { 3750 }
            ::= { zhoneVdslLineConfProfileEntry 32 }


        -- 1.3.6.1.4.1.5504.5.13.1.1.11.1.33
        zhoneVdslLineConfBandOptUsage OBJECT-TYPE
            SYNTAX INTEGER
                {
                unused(1),
                upstream(2),
                downstream(3),
                upstream-forced(4)
                }
            MAX-ACCESS read-create
            STATUS current
            DESCRIPTION
                "Defines the VDSL link use of the optional frequency
                range [25kHz - 138kHz] (Opt).

                unused(1)     indicates Opt is unused
                upstream(2)   indicates Opt usage is for upstream
                downstream(3) indicates Opt usage is for downstream.
                upstreamForced(4) indicates forced upstream"
            REFERENCE
                "ITU-T G.993.1, section 6.1"
            DEFVAL { upstream }
            ::= { zhoneVdslLineConfProfileEntry 33 }


        -- 1.3.6.1.4.1.5504.5.13.1.1.11.1.34
        zhoneVdslLineConfUpPsdTemplate OBJECT-TYPE
            SYNTAX INTEGER
                {
                ansi-fftex-m1(3),
                ansi-fftex-m2(4),
                ansi-fftcab-m1(5),
                fftcab-m2(6),
                etsi-m1(7),
                etsi-m2(8),
                psd-custom(9)
                }
            MAX-ACCESS read-create
            STATUS current
            DESCRIPTION
                "This object has been modified by Zhone.

                The upstream PSD template to be used for the line.
                Here, templateMask1(1) refers to a notched mask that
                limits the transmitted PSD within the internationally
                standardized HAM (Handheld Amateur Radio) radio bands,
                while templateMask2(2) refers to an unnotched mask.

                The masks themselves depend upon the applicable
                standard being used (vdslLineConfApplicableStandard)."
            REFERENCE
                "DSL TR-057"
            DEFVAL { ansi-fftcab-m1 }
            ::= { zhoneVdslLineConfProfileEntry 34 }


        -- 1.3.6.1.4.1.5504.5.13.1.1.11.1.35
        zhoneVdslLineConfDownPsdTemplate OBJECT-TYPE
            SYNTAX INTEGER
                {
                ansi-fftex-m1(3),
                ansi-fftex-m2(4),
                ansi-fftcab-m1(5),
                fftcab-m2(6),
                fftcab-m1-adsl(7),
                fftcab-m1-adslplus(8),
                fftcab-m2-adsl(9),
                fftcab-m2-adslplus(10),
                etsi-pexp1-m1(11),
                etsi-pexp1-m2(12),
                etsi-pexp2-m1(13),
                etsi-pexp2-m2(14),
                psd-custom(15),
                etsi-pexm2-sample1(16),
                etsi-pexm2-sample2(17),
                etsi-pexm2-sample3(18),
                etsi-pexm2-sample4(19),
                etsi-pcab-m1(20),
                etsi-pcab-m2(21)
                }
            MAX-ACCESS read-create
            STATUS current
            DESCRIPTION
                "This object has been modified by Zhone.

                The downstream PSD template to be used for the line.
                Here, templateMask1(1) refers to a notched mask that
                limits the transmitted PSD within the internationally
                standardized HAM (Handheld Amateur Radio) radio bands,
                while templateMask2(2) refers to an unnotched mask.

                The masks themselves depend upon the applicable
                standard being used (vdslLineConfApplicableStandard)."
            REFERENCE
                "DSL TR-057"
            DEFVAL { ansi-fftcab-m1 }
            ::= { zhoneVdslLineConfProfileEntry 35 }


        -- 1.3.6.1.4.1.5504.5.13.1.1.11.1.36
        zhoneVdslLineConfHamBandMask OBJECT-TYPE
            SYNTAX BITS
                {
                customNotch1(0),
                customNotch2(1),
                amateurBand30m(2),
                amateurBand40m(3),
                amateurBand80m(4),
                amateurBand160m(5)
                }
            MAX-ACCESS read-create
            STATUS current
            DESCRIPTION
                "The transmit power spectral density mask code, used
                to avoid interference with HAM (Handheld Amateur Radio)
                radio bands by introducing power control (notching) in one
                or more of these bands.

                Amateur radio band notching is defined in the VDSL
                spectrum as follows:

                Band  Start Frequency     Stop Frequency
                ----  ------------------  --------------------------------
                30m   1810 kHz            2000 kHz
                40m   3500 kHz            3800 kHz (ETSI); 4000 kHz (ANSI)
                80m   7000 kHz            7100 kHz (ETSI); 7300 kHz (ANSI)
                160m  10100 kHz           10150 kHz

                Notching for each standard band can be enabled or disabled
                via the bit mask.

                Two custom notches may be specified.  If either of these
                are enabled via the bit mask, then the following objects
                MUST be specified:

                If customNotch1 is enabled, then both
                    zhoneVdslLineConfCustomNotch1Start
                    zhoneVdslLineConfCustomNotch1Stop
                MUST be specified.

                If customNotch2 is enabled, then both
                    zhoneVdslLineConfCustomNotch2Start
                    zhoneVdslLineConfCustomNotch2Stop
                MUST be specified."
            REFERENCE
                "DSLF TR-057, section 2.6"
            ::= { zhoneVdslLineConfProfileEntry 36 }


--  1.3.6.1.4.1.5504.5.13.1.1.11.1.37
        -- 1.3.6.1.4.1.5504.5.13.1.1.11.1.37
        zhoneVdslLineConfCustomNotch1Start OBJECT-TYPE
            SYNTAX Unsigned32
            UNITS "kHz"
            MAX-ACCESS read-create
            STATUS current
            DESCRIPTION
                "Specifies the start frequency of custom HAM (Handheld
                Amateur Radio) notch 1.  zhoneVdslLineConfCustomNotch1Start MUST
                be less than or equal to vdslLineConfCustomNotch1Stop."
            DEFVAL { 0 }
            ::= { zhoneVdslLineConfProfileEntry 37 }


--  1.3.6.1.4.1.5504.5.13.1.1.11.1.38
        -- 1.3.6.1.4.1.5504.5.13.1.1.11.1.38
        zhoneVdslLineConfCustomNotch1Stop OBJECT-TYPE
            SYNTAX Unsigned32
            UNITS "kHz"
            MAX-ACCESS read-create
            STATUS current
            DESCRIPTION
                "Specifies the stop frequency of custom HAM (Handheld
                Amateur Radio) notch 1.  zhoneVdslLineConfCustomNotch1Stop MUST
                be greater than or equal to vdslLineConfCustomNotch1Start."
            DEFVAL { 0 }
            ::= { zhoneVdslLineConfProfileEntry 38 }


--  1.3.6.1.4.1.5504.5.13.1.1.11.1.39
        -- 1.3.6.1.4.1.5504.5.13.1.1.11.1.39
        zhoneVdslLineConfCustomNotch2Start OBJECT-TYPE
            SYNTAX Unsigned32
            UNITS "kHz"
            MAX-ACCESS read-create
            STATUS current
            DESCRIPTION
                "Specifies the start frequency of custom HAM (Handheld
                Amateur Radio) notch 2.  zhoneVdslLineConfCustomNotch2Start MUST
                be less than or equal to vdslLineConfCustomNotch2Stop."
            DEFVAL { 0 }
            ::= { zhoneVdslLineConfProfileEntry 39 }


--  1.3.6.1.4.1.5504.5.13.1.1.11.1.40
        -- 1.3.6.1.4.1.5504.5.13.1.1.11.1.40
        zhoneVdslLineConfCustomNotch2Stop OBJECT-TYPE
            SYNTAX Unsigned32
            UNITS "kHz"
            MAX-ACCESS read-create
            STATUS current
            DESCRIPTION
                "Specifies the stop frequency of custom HAM (Handheld
                Amateur Radio) notch 2.  zhoneVdslLineConfCustomNotch2Stop MUST
                be greater than or equal to vdslLineConfCustomNotch2Start."
            DEFVAL { 0 }
            ::= { zhoneVdslLineConfProfileEntry 40 }


        -- 1.3.6.1.4.1.5504.5.13.1.1.11.1.41
        zhoneVdslLineConfDownTargetSlowBurst OBJECT-TYPE
            SYNTAX Unsigned32 (0..1275)
            UNITS "microseconds"
            MAX-ACCESS read-create
            STATUS current
            DESCRIPTION
                "Specifies the target level of impulse noise (burst)
                protection for an interleaved (slow) channel."
            REFERENCE
                "ITU-T G.997.1, section 7.3.2.3"
            DEFVAL { 5 }
            ::= { zhoneVdslLineConfProfileEntry 41 }


        -- 1.3.6.1.4.1.5504.5.13.1.1.11.1.42
        zhoneVdslLineConfUpTargetSlowBurst OBJECT-TYPE
            SYNTAX Unsigned32 (0..1275)
            UNITS "microseconds"
            MAX-ACCESS read-create
            STATUS current
            DESCRIPTION
                "Specifies the target level of impulse noise (burst)
                protection for an interleaved (slow) channel."
            REFERENCE
                "ITU-T G.997.1, section 7.3.2.3"
            DEFVAL { 5 }
            ::= { zhoneVdslLineConfProfileEntry 42 }


        -- 1.3.6.1.4.1.5504.5.13.1.1.11.1.43
        zhoneVdslLineConfDownMaxFastFec OBJECT-TYPE
            SYNTAX Unsigned32 (0..50)
            UNITS "%"
            MAX-ACCESS read-create
            STATUS current
            DESCRIPTION
                "This parameter provisions the maximum level of Forward
                Error Correction (FEC) redundancy related overhead to
                be maintained for a fast channel."
            DEFVAL { 0 }
            ::= { zhoneVdslLineConfProfileEntry 43 }


        -- 1.3.6.1.4.1.5504.5.13.1.1.11.1.44
        zhoneVdslLineConfUpMaxFastFec OBJECT-TYPE
            SYNTAX Unsigned32 (0..50)
            UNITS "%"
            MAX-ACCESS read-create
            STATUS current
            DESCRIPTION
                "This parameter provisions the maximum level of Forward
                Error Correction (FEC) redundancy related overhead to
                be maintained for a fast channel."
            DEFVAL { 0 }
            ::= { zhoneVdslLineConfProfileEntry 44 }


        -- 1.3.6.1.4.1.5504.5.13.1.1.11.1.45
        zhoneVdslLineConfLineType OBJECT-TYPE
            SYNTAX INTEGER
                {
                noChannel(1),
                fastOnly(2),
                interleavedOnly(3),
                fastOrInterleaved(4),
                fastAndInterleaved(5)
                }
            MAX-ACCESS read-create
            STATUS current
            DESCRIPTION
                "This parameter provisions the VDSL physical entity at
                start-up by defining whether and how the line will be
                channelized, i.e., which channel type(s) are supported.
                If the line is to be channelized, the value will be other
                than noChannel(1).

                This configuration can be activated only during start-up.
                Afterwards, the value of zhoneVdslLineType coincides with the
                value of zhoneVdslLineConfLineType.  Depending on this value,
                the corresponding entries in the ifTable for the
                interleaved and the fast channels are enabled or disabled
                according to the value of their ifOperStatus.

                Defined values are:

                noChannel(1)          -- no channels exist
                fastOnly(2)           -- only fast channel exists
                interleavedOnly(3)    -- only interleaved channel exists
                fastOrInterleaved(4)  -- either fast or interleaved channel
                                      -- exists, but only one at a time
                fastAndInterleaved(5) -- both fast and interleaved channels
                                      -- exist

                Note that 'slow' and 'interleaved' refer to the same
                channel."
            REFERENCE
                "T1E1.4/2000-009R3, Part 1, common spec"
            DEFVAL { fastOnly }
            ::= { zhoneVdslLineConfProfileEntry 45 }


--  1.3.6.1.4.1.5504.5.13.1.1.11.1.46
        -- 1.3.6.1.4.1.5504.5.13.1.1.11.1.47
        zhoneVdslLineConfProfRowStatus OBJECT-TYPE
            SYNTAX RowStatus
            MAX-ACCESS read-create
            STATUS current
            DESCRIPTION
                "This object is used to create a new row or modify or
                delete an existing row in this table.

                A profile activated by setting this object to 'active'.
                When 'active' is set, the system will validate the profile.

                Before a profile can be deleted or taken out of service
                (by setting this object to 'destroy' or 'outOfService'),
                it must be first unreferenced from all associated lines.

                An 'active' profile may be modified at any time.  Note
                that some changes may require that any referenced lines be
                restarted (e.g., zhoneVdslLineConfLineType)."
            ::= { zhoneVdslLineConfProfileEntry 47 }


        -- 1.3.6.1.4.1.5504.5.13.1.1.11.1.48
        zhoneVdslLineConfTransmissionMode OBJECT-TYPE
            SYNTAX INTEGER
                {
                autoNegotiateMode(1),
                vdslMode(2),
                vdsl2Mode(3),
                adsl2PlusMode(4),
                adsl2Mode(5),
                gdmtMode(6)
                }
            MAX-ACCESS read-create
            STATUS current
            DESCRIPTION
                "The transmission standard to be used for the line."
            DEFVAL { autoNegotiateMode }
            ::= { zhoneVdslLineConfProfileEntry 48 }


        -- 1.3.6.1.4.1.5504.5.13.1.1.11.1.49
        zhoneVdslLineConfVdsl2Profile OBJECT-TYPE
            SYNTAX INTEGER
                {
                g993-2-8a(1),
                g993-2-8b(2),
                g993-2-8c(3),
                g993-2-8d(4),
                g993-2-12a(5),
                g993-2-12b(6),
                g993-2-17a(7),
                g993-2-30a(8)
                }
            MAX-ACCESS read-create
            STATUS current
            DESCRIPTION
                "The VDSL2 standard to be used for the line."
            DEFVAL { g993-2-12a }
            ::= { zhoneVdslLineConfProfileEntry 49 }


        -- 1.3.6.1.4.1.5504.5.13.1.1.11.1.50
        zhoneVdslLineConfVdslMode OBJECT-TYPE
            SYNTAX INTEGER
                {
                standard(1),
                long-reach-8k(2),
                r8k(3),
                std-8k(4),
                lr-8k(5),
                std-lr(6),
                std-lr-8k(7)
                }
            MAX-ACCESS read-create
            STATUS current
            DESCRIPTION
                "Controls which VDSL modes are available on the line."
            DEFVAL { standard }
            ::= { zhoneVdslLineConfProfileEntry 50 }


        -- 1.3.6.1.4.1.5504.5.13.1.1.11.1.51
        zhoneVdslLineConfPboElectricalOverride OBJECT-TYPE
            SYNTAX Integer32 (0..256)
            UNITS ".5 dBm/Mhz"
            MAX-ACCESS read-create
            STATUS current
            DESCRIPTION
                "Override electrical length estimated by VUTU_C.
                The special value 256 means do not perform
                override."
            DEFVAL { 256 }
            ::= { zhoneVdslLineConfProfileEntry 51 }


        -- 1.3.6.1.4.1.5504.5.13.1.1.11.1.52
        zhoneVdslLineConfAutoModeCrtrn OBJECT-TYPE
            SYNTAX INTEGER
                {
                crtrn-chip-prop(1),
                optimize-us(2),
                optimize-ds(3)
                }
            MAX-ACCESS read-create
            STATUS current
            DESCRIPTION
                "Determines the policy to select optimal mode of oepration."
            DEFVAL { optimize-us }
            ::= { zhoneVdslLineConfProfileEntry 52 }


        -- 1.3.6.1.4.1.5504.5.13.1.1.11.1.53
        zhoneVdslLineConfNetworkTimingRef OBJECT-TYPE
            SYNTAX INTEGER
                {
                enable(1),
                disable(2)
                }
            MAX-ACCESS read-only
            STATUS current
            DESCRIPTION
                "Enable/disable reference clock source."
            DEFVAL { disable }
            ::= { zhoneVdslLineConfProfileEntry 53 }


        -- 1.3.6.1.4.1.5504.5.13.1.1.11.1.54
        zhoneVdslLineConfAdslBandMode OBJECT-TYPE
            SYNTAX INTEGER
                {
                allowed(1),
                not-allowed(2)
                }
            MAX-ACCESS read-create
            STATUS current
            DESCRIPTION
                "Specifies whether the XDSL can use the ADSL spectrum or not."
            DEFVAL { allowed }
            ::= { zhoneVdslLineConfProfileEntry 54 }


        -- 1.3.6.1.4.1.5504.5.13.1.1.11.1.55
        zhoneVdslLineConfAdslBandModeEndFreq OBJECT-TYPE
            SYNTAX Integer32 (276..2208)
            UNITS "kHz"
            MAX-ACCESS read-create
            STATUS current
            DESCRIPTION
                "Specifies the ADSL band end frequency when
                the ADSL band usage is not allowed."
            DEFVAL { 1104 }
            ::= { zhoneVdslLineConfProfileEntry 55 }


        -- 1.3.6.1.4.1.5504.5.13.1.1.11.1.56
        zhoneVdslLineConfSeltEchoMeasurementTime OBJECT-TYPE
            SYNTAX Integer32 (5..240)
            UNITS "secs"
            MAX-ACCESS read-create
            STATUS current
            DESCRIPTION
                "Contains the SELT echo measurement time"
            DEFVAL { 50 }
            ::= { zhoneVdslLineConfProfileEntry 56 }


        -- 1.3.6.1.4.1.5504.5.13.1.1.11.1.57
        zhoneVdslLineConfSeltNoiseMeasurementTime OBJECT-TYPE
            SYNTAX Integer32 (5..240)
            UNITS "secs"
            MAX-ACCESS read-create
            STATUS current
            DESCRIPTION
                "Contains the SELT noise measurement time."
            DEFVAL { 50 }
            ::= { zhoneVdslLineConfProfileEntry 57 }


        -- 1.3.6.1.4.1.5504.5.13.1.1.11.1.58
        zhoneVdslLineConfSeltAgc OBJECT-TYPE
            SYNTAX Integer32 (-100..100)
            UNITS "1 dBm"
            MAX-ACCESS read-create
            STATUS current
            DESCRIPTION
                "Contains the SELT AGC gain value."
            DEFVAL { 0 }
            ::= { zhoneVdslLineConfProfileEntry 58 }


        -- 1.3.6.1.4.1.5504.5.13.1.1.11.1.59
        zhoneVdslLineConfDownTrellis OBJECT-TYPE
            SYNTAX INTEGER
                {
                enable(1),
                disable(2)
                }
            MAX-ACCESS read-create
            STATUS current
            DESCRIPTION
                "Enables/disables downstream Trellis coding."
            DEFVAL { enable }
            ::= { zhoneVdslLineConfProfileEntry 59 }


        -- 1.3.6.1.4.1.5504.5.13.1.1.11.1.60
        zhoneVdslLineConfUpTrellis OBJECT-TYPE
            SYNTAX INTEGER
                {
                enable(1),
                disable(2)
                }
            MAX-ACCESS read-create
            STATUS current
            DESCRIPTION
                "Enables/disables upstream Trellis coding."
            DEFVAL { enable }
            ::= { zhoneVdslLineConfProfileEntry 60 }


        -- 1.3.6.1.4.1.5504.5.13.1.1.11.1.61
        zhoneVdslLineConfDownMaxAggregateTxPwr OBJECT-TYPE
            SYNTAX INTEGER { unlimited(4) }
            MAX-ACCESS read-create
            STATUS current
            DESCRIPTION
                "Maximum total power that is allowed to be transmitted
                in the downstream direction."
            DEFVAL { unlimited }
            ::= { zhoneVdslLineConfProfileEntry 61 }


        -- 1.3.6.1.4.1.5504.5.13.1.1.11.1.62
        zhoneVdslLineConfUpMaxAggregateTxPwr OBJECT-TYPE
            SYNTAX INTEGER { unlimited(4) }
            MAX-ACCESS read-create
            STATUS current
            DESCRIPTION
                "Maximum total power that is allowed to be transmitted
                in the upstream direction."
            DEFVAL { unlimited }
            ::= { zhoneVdslLineConfProfileEntry 62 }


        -- 1.3.6.1.4.1.5504.5.13.1.1.11.1.63
        zhoneVdslLineConfDownMaxPsd OBJECT-TYPE
            SYNTAX Integer32 (-955..0)
            UNITS ".1 dBm/Hz"
            MAX-ACCESS read-create
            STATUS current
            DESCRIPTION
                "The maximum power spectral density level
                allowed on the line at the transmitter
                output downstream for initialization and
                showtime signals."
            DEFVAL { -1 }
            ::= { zhoneVdslLineConfProfileEntry 63 }


        -- 1.3.6.1.4.1.5504.5.13.1.1.11.1.64
        zhoneVdslLineConfUpMaxPsd OBJECT-TYPE
            SYNTAX Integer32 (-955..0)
            UNITS ".1 dBm/Hz"
            MAX-ACCESS read-create
            STATUS current
            DESCRIPTION
                "The maximum power spectral density level
                allowed on the line at the transmitter
                output upstream for initialization and
                showtime signals."
            DEFVAL { -1 }
            ::= { zhoneVdslLineConfProfileEntry 64 }


        -- 1.3.6.1.4.1.5504.5.13.1.1.11.1.65
        zhoneVdslLineConfDownPsdShape OBJECT-TYPE
            SYNTAX INTEGER
                {
                custom-psd(1),
                region-a-psd(2),
                region-c-psd(3),
                region-b-m1-a-psd(4),
                region-b-m1-b-psd(5),
                region-b-m1-us0-psd(6),
                region-b-m2-a-psd(7),
                region-b-m2-m-psd(8),
                region-b-m2-b-psd(9),
                region-b-m2-us0-psd(10)
                }
            MAX-ACCESS read-create
            STATUS current
            DESCRIPTION
                "Maximum transmit PSD allowed in the downstream
                channel on a VDSL2 line."
            DEFVAL { region-a-psd }
            ::= { zhoneVdslLineConfProfileEntry 65 }


        -- 1.3.6.1.4.1.5504.5.13.1.1.11.1.66
        zhoneVdslLineConfUpPsdShape OBJECT-TYPE
            SYNTAX INTEGER
                {
                custom-psd(1),
                region-a-psd(2),
                region-c-psd(3),
                region-b-m1-a-psd(4),
                region-b-m1-b-psd(5),
                region-b-m1-us0-psd(6),
                region-b-m2-a-psd(7),
                region-b-m2-m-psd(8),
                region-b-m2-b-psd(9),
                region-b-m2-us0-psd(10)
                }
            MAX-ACCESS read-create
            STATUS current
            DESCRIPTION
                "Maximum transmit PSD allowed in the upstream
                channel on a VDSL2 line."
            DEFVAL { region-a-psd }
            ::= { zhoneVdslLineConfProfileEntry 66 }


        -- 1.3.6.1.4.1.5504.5.13.1.1.11.1.67
        zhoneVdslLineConfDownVirtualNoiseSnrMode OBJECT-TYPE
            SYNTAX INTEGER
                {
                mode1(1),
                mode2(2),
                mode3(3)
                }
            MAX-ACCESS read-create
            STATUS current
            DESCRIPTION
                "Downstream virtual noise SNR mode on a VDSL2
                line."
            DEFVAL { mode1 }
            ::= { zhoneVdslLineConfProfileEntry 67 }


        -- 1.3.6.1.4.1.5504.5.13.1.1.11.1.68
        zhoneVdslLineConfUpVirtualNoiseSnrMode OBJECT-TYPE
            SYNTAX INTEGER
                {
                mode1(1),
                mode2(2),
                mode3(3)
                }
            MAX-ACCESS read-create
            STATUS current
            DESCRIPTION
                "Upstream virtual noise SNR mode on a VDSL2
                line."
            DEFVAL { mode1 }
            ::= { zhoneVdslLineConfProfileEntry 68 }


        -- 1.3.6.1.4.1.5504.5.13.1.1.11.1.69
        zhoneVdslLineConfDownErasureDetectionFast OBJECT-TYPE
            SYNTAX INTEGER
                {
                enable(1),
                disable(2)
                }
            MAX-ACCESS read-create
            STATUS current
            DESCRIPTION
                "Indicates whether the erasure detection
                mechanism should be enabled or disabled in
                the downstream fast channel."
            DEFVAL { enable }
            ::= { zhoneVdslLineConfProfileEntry 69 }


        -- 1.3.6.1.4.1.5504.5.13.1.1.11.1.70
        zhoneVdslLineConfUpErasureDetectionFast OBJECT-TYPE
            SYNTAX INTEGER
                {
                enable(1),
                disable(2)
                }
            MAX-ACCESS read-create
            STATUS current
            DESCRIPTION
                "Indicates whether the erasure detection
                mechanism should be enabled or disabled in
                the downstream fast channel."
            DEFVAL { enable }
            ::= { zhoneVdslLineConfProfileEntry 70 }


        -- 1.3.6.1.4.1.5504.5.13.1.1.11.1.71
        zhoneVdslLineConfDownErasureDetectionInterleave OBJECT-TYPE
            SYNTAX INTEGER
                {
                enable(1),
                disable(2)
                }
            MAX-ACCESS read-create
            STATUS current
            DESCRIPTION
                "Indicates whether the erasure detection
                mechanism should be enabled or disabled in
                the downstream slow channel (interleave)."
            DEFVAL { enable }
            ::= { zhoneVdslLineConfProfileEntry 71 }


        -- 1.3.6.1.4.1.5504.5.13.1.1.11.1.72
        zhoneVdslLineConfUpErasureDetectionInterleave OBJECT-TYPE
            SYNTAX INTEGER
                {
                enable(1),
                disable(2)
                }
            MAX-ACCESS read-create
            STATUS current
            DESCRIPTION
                "Indicates whether the erasure detection
                mechanism should be enabled or disabled in
                the uptream slow channel (interleave)."
            DEFVAL { enable }
            ::= { zhoneVdslLineConfProfileEntry 72 }


        -- 1.3.6.1.4.1.5504.5.13.1.1.11.1.73
        zhoneVdslLineConfDownGhsA43TonePwr OBJECT-TYPE
            SYNTAX INTEGER
                {
                default(1),
                auto(2),
                manual(3)
                }
            MAX-ACCESS read-create
            STATUS current
            DESCRIPTION
                "Determines the mode of the downstream tones
                power used during handshake, during A43
                mode."
            DEFVAL { default }
            ::= { zhoneVdslLineConfProfileEntry 73 }


        -- 1.3.6.1.4.1.5504.5.13.1.1.11.1.74
        zhoneVdslLineConfDownGhsB43TonePwr OBJECT-TYPE
            SYNTAX INTEGER
                {
                default(1),
                auto(2),
                manual(3)
                }
            MAX-ACCESS read-create
            STATUS current
            DESCRIPTION
                "Determines the mode of the downstream tones
                power used during handshake, during B43
                mode."
            DEFVAL { default }
            ::= { zhoneVdslLineConfProfileEntry 74 }


        -- 1.3.6.1.4.1.5504.5.13.1.1.11.1.75
        zhoneVdslLineConfDownGhsA43cTonePwr OBJECT-TYPE
            SYNTAX INTEGER
                {
                default(1),
                auto(2),
                manual(3)
                }
            MAX-ACCESS read-create
            STATUS current
            DESCRIPTION
                "Determines the mode of the downstream tones
                power used during handshake, during A43c
                mode."
            DEFVAL { default }
            ::= { zhoneVdslLineConfProfileEntry 75 }


        -- 1.3.6.1.4.1.5504.5.13.1.1.11.1.76
        zhoneVdslLineConfDownGhsV43TonePwr OBJECT-TYPE
            SYNTAX INTEGER
                {
                default(1),
                auto(2),
                manual(3)
                }
            MAX-ACCESS read-create
            STATUS current
            DESCRIPTION
                "Determines the mode of the downstream tone
                power used during handshake, during V43
                mode."
            DEFVAL { default }
            ::= { zhoneVdslLineConfProfileEntry 76 }


        -- 1.3.6.1.4.1.5504.5.13.1.1.11.1.77
        zhoneVdslLineConfDownGhsA43TonePwrMaxLvl OBJECT-TYPE
            SYNTAX Integer32 (-99..-40)
            UNITS "0.5 dBm/Hz"
            MAX-ACCESS read-create
            STATUS current
            DESCRIPTION
                "Determines the maximum power of downstream
                tones used, in manual mode, during handshake
                in A43 mode.   A value of -99 indicates no
                power used."
            DEFVAL { -99 }
            ::= { zhoneVdslLineConfProfileEntry 77 }


        -- 1.3.6.1.4.1.5504.5.13.1.1.11.1.78
        zhoneVdslLineConfDownGhsB43TonePwrMaxLvl OBJECT-TYPE
            SYNTAX Integer32 (-99..-40)
            UNITS "0.5 dBm/Hz"
            MAX-ACCESS read-create
            STATUS current
            DESCRIPTION
                "Determines the maximum power of downstream
                tones used, in manual mode, during handshake
                in B43 mode.   A value of -99 indicates no
                power used."
            DEFVAL { -99 }
            ::= { zhoneVdslLineConfProfileEntry 78 }


        -- 1.3.6.1.4.1.5504.5.13.1.1.11.1.79
        zhoneVdslLineConfDownGhsA43cTonePwrMaxLvl OBJECT-TYPE
            SYNTAX Integer32 (-99..-40)
            UNITS "0.5 dBm/Hz"
            MAX-ACCESS read-create
            STATUS current
            DESCRIPTION
                "Determines the maximum power of downstream
                tones used, in manual mode, during handshake
                in A43c mode.   A value of -99 indicates no
                power used."
            DEFVAL { -99 }
            ::= { zhoneVdslLineConfProfileEntry 79 }


        -- 1.3.6.1.4.1.5504.5.13.1.1.11.1.80
        zhoneVdslLineConfDownGhsV43TonePwrMaxLvl OBJECT-TYPE
            SYNTAX Integer32 (-99..-40)
            UNITS "0.5 dBm/Hz"
            MAX-ACCESS read-create
            STATUS current
            DESCRIPTION
                "Determines the maximum power of downstream
                tones used, in manual mode, during handshake
                in V43 mode.   A value of -99 indicates no
                power used."
            DEFVAL { -99 }
            ::= { zhoneVdslLineConfProfileEntry 80 }


        -- 1.3.6.1.4.1.5504.5.13.1.1.11.1.81
        zhoneVdslLineConfDownRsCoding OBJECT-TYPE
            SYNTAX INTEGER
                {
                enable(1),
                disable(2)
                }
            MAX-ACCESS read-create
            STATUS current
            DESCRIPTION
                "Parameter to enable/disable RS Coding in
                downstream channel."
            DEFVAL { disable }
            ::= { zhoneVdslLineConfProfileEntry 81 }


        -- 1.3.6.1.4.1.5504.5.13.1.1.11.1.82
        zhoneVdslLineConfUpRsCoding OBJECT-TYPE
            SYNTAX INTEGER
                {
                enable(1),
                disable(2)
                }
            MAX-ACCESS read-create
            STATUS current
            DESCRIPTION
                "Parameter to enable/disable RS Coding in
                upsream channel."
            DEFVAL { disable }
            ::= { zhoneVdslLineConfProfileEntry 82 }


        -- 1.3.6.1.4.1.5504.5.13.1.1.11.1.83
        zhoneVdslLineConfUpPboPsdTemplate OBJECT-TYPE
            SYNTAX INTEGER
                {
                ansi-a(1),
                ansi-f(2),
                etsi-a(3),
                etsi-b(4),
                etsi-c(5),
                etsi-d(6),
                etsi-e(7),
                etsi-f(8),
                custom(9),
                ab-param(10)
                }
            MAX-ACCESS read-create
            STATUS current
            DESCRIPTION
                "Specifies the maximum received PSD allowed
                in the upstream channel on the VDSLx line."
            DEFVAL { ansi-a }
            ::= { zhoneVdslLineConfProfileEntry 83 }


        -- 1.3.6.1.4.1.5504.5.13.1.1.11.1.84
        zhoneVdslLineConfUpPboPsdParamA1 OBJECT-TYPE
            SYNTAX Integer32 (4000..8589)
            UNITS ".01 dBm/Hz"
            MAX-ACCESS read-create
            STATUS current
            DESCRIPTION
                "Upstream power backoff PSD parameter A1.  This
                parameter is only used if the mask selection
                is set to PSDMaskABParameters"
            DEFVAL { 4000 }
            ::= { zhoneVdslLineConfProfileEntry 84 }


        -- 1.3.6.1.4.1.5504.5.13.1.1.11.1.85
        zhoneVdslLineConfUpPboPsdParamA2 OBJECT-TYPE
            SYNTAX Integer32 (4000..8589)
            UNITS ".01 dBm/Hz"
            MAX-ACCESS read-create
            STATUS current
            DESCRIPTION
                "Upstream power backoff PSD parameter A2.  This
                parameter is only used if the mask selection
                is set to PSDMaskABParameters"
            DEFVAL { 4000 }
            ::= { zhoneVdslLineConfProfileEntry 85 }


        -- 1.3.6.1.4.1.5504.5.13.1.1.11.1.86
        zhoneVdslLineConfUpPboPsdParamB1 OBJECT-TYPE
            SYNTAX Integer32 (0..8589)
            UNITS ".01 dBm/Hz"
            MAX-ACCESS read-create
            STATUS current
            DESCRIPTION
                "Upstream power backoff PSD parameter B1.  This
                parameter is only used if the mask selection
                is set to PSDMaskABParameters"
            DEFVAL { 4000 }
            ::= { zhoneVdslLineConfProfileEntry 86 }


        -- 1.3.6.1.4.1.5504.5.13.1.1.11.1.87
        zhoneVdslLineConfUpPboPsdParamB2 OBJECT-TYPE
            SYNTAX Integer32 (0..8589)
            UNITS ".01 dBm/Hz"
            MAX-ACCESS read-create
            STATUS current
            DESCRIPTION
                "Upstream power backoff PSD parameter B2.  This
                parameter is only used if the mask selection
                is set to PSDMaskABParameters"
            DEFVAL { 4000 }
            ::= { zhoneVdslLineConfProfileEntry 87 }


        -- 1.3.6.1.4.1.5504.5.13.1.1.11.1.88
        zhoneVdslLineConfDownDownshiftSnrMgn OBJECT-TYPE
            SYNTAX Integer32 (0..310)
            UNITS "tenth dB"
            MAX-ACCESS read-create
            STATUS current
            DESCRIPTION
                "Configured Signal/Noise Margin for rate downshift.
                If the noise margin falls below this level, the modem
                should attempt to decrease its transmit rate."
            DEFVAL { 30 }
            ::= { zhoneVdslLineConfProfileEntry 88 }


        -- 1.3.6.1.4.1.5504.5.13.1.1.11.1.89
        zhoneVdslLineConfDownUpshiftSnrMgn OBJECT-TYPE
            SYNTAX Integer32 (0..310)
            UNITS "tenth dB"
            MAX-ACCESS read-create
            STATUS current
            DESCRIPTION
                "Configured Signal/Noise Margin for rate upshift.
                If the noise margin rises above this level, the modem
                should attempt to increase its transmit rate."
            DEFVAL { 90 }
            ::= { zhoneVdslLineConfProfileEntry 89 }


        -- 1.3.6.1.4.1.5504.5.13.1.1.11.1.90
        zhoneVdslLineConfDownMinDownshiftTime OBJECT-TYPE
            SYNTAX Integer32 (0..16383)
            UNITS "seconds"
            MAX-ACCESS read-create
            STATUS current
            DESCRIPTION
                "Minimum time that the current margin is below
                DownshiftSnrMgn before a downshift occurs."
            DEFVAL { 30 }
            ::= { zhoneVdslLineConfProfileEntry 90 }


        -- 1.3.6.1.4.1.5504.5.13.1.1.11.1.91
        zhoneVdslLineConfDownMinUpshiftTime OBJECT-TYPE
            SYNTAX Integer32 (0..16383)
            UNITS "seconds"
            MAX-ACCESS read-create
            STATUS current
            DESCRIPTION
                "Minimum time that the current margin is above
                UpshiftSnrMgn before an upshift occurs."
            DEFVAL { 30 }
            ::= { zhoneVdslLineConfProfileEntry 91 }


        -- 1.3.6.1.4.1.5504.5.13.1.1.11.1.92
        zhoneVdslLineConfUpDownshiftSnrMgn OBJECT-TYPE
            SYNTAX Integer32 (0..310)
            UNITS "tenth dB"
            MAX-ACCESS read-create
            STATUS current
            DESCRIPTION
                "Configured Signal/Noise Margin for rate downshift.
                If the noise margin falls below this level, the modem
                should attempt to decrease its transmit rate."
            DEFVAL { 30 }
            ::= { zhoneVdslLineConfProfileEntry 92 }


        -- 1.3.6.1.4.1.5504.5.13.1.1.11.1.93
        zhoneVdslLineConfUpUpshiftSnrMgn OBJECT-TYPE
            SYNTAX Integer32 (0..310)
            UNITS "tenth dB"
            MAX-ACCESS read-create
            STATUS current
            DESCRIPTION
                "Configured Signal/Noise Margin for rate upshift.
                If the noise margin rises above this level, the modem
                should attempt to increase its transmit rate."
            DEFVAL { 90 }
            ::= { zhoneVdslLineConfProfileEntry 93 }


        -- 1.3.6.1.4.1.5504.5.13.1.1.11.1.94
        zhoneVdslLineConfUpMinDownshiftTime OBJECT-TYPE
            SYNTAX Integer32 (0..16383)
            UNITS "seconds"
            MAX-ACCESS read-create
            STATUS current
            DESCRIPTION
                "Minimum time that the current margin is below
                DownshiftSnrMgn before a downshift occurs."
            DEFVAL { 30 }
            ::= { zhoneVdslLineConfProfileEntry 94 }


        -- 1.3.6.1.4.1.5504.5.13.1.1.11.1.95
        zhoneVdslLineConfUpMinUpshiftTime OBJECT-TYPE
            SYNTAX Integer32 (0..16383)
            UNITS "seconds"
            MAX-ACCESS read-create
            STATUS current
            DESCRIPTION
                "Minimum time that the current margin is above
                UpshiftSnrMgn before an upshift occurs."
            DEFVAL { 30 }
            ::= { zhoneVdslLineConfProfileEntry 95 }


        -- 1.3.6.1.4.1.5504.5.13.1.1.11.1.96
        zhoneVdslLineConfDownMinTxThresholdAlarm OBJECT-TYPE
            SYNTAX Unsigned32 (0..200000)
            UNITS "kbps"
            MAX-ACCESS read-create
            STATUS current
            DESCRIPTION
                "Minimum CO Tx Sync rate threshold alarm.  If set to 0,
                this field is disregarded.  Otherwise, if Tx Sync
                rate falls below this value, a trap and alarm will
                be issued"
            DEFVAL { 0 }
            ::= { zhoneVdslLineConfProfileEntry 96 }


        -- 1.3.6.1.4.1.5504.5.13.1.1.11.1.97
        zhoneVdslLineConfUpMinTxThresholdAlarm OBJECT-TYPE
            SYNTAX Unsigned32 (0..200000)
            UNITS "kbps"
            MAX-ACCESS read-create
            STATUS current
            DESCRIPTION
                "Minimum CPE Tx Sync rate threshold alarm.  If set to 0,
                this field is disregarded.  Otherwise, if Tx Sync
                rate falls below this value, a trap and alarm will
                be issued"
            DEFVAL { 0 }
            ::= { zhoneVdslLineConfProfileEntry 97 }


        -- 1.3.6.1.4.1.5504.5.13.1.1.11.1.98
        zhoneVdslLineConfPotsBypassRelayMaxDuration OBJECT-TYPE
            SYNTAX INTEGER (1..300)
            UNITS "secs"
            MAX-ACCESS read-create
            STATUS current
            DESCRIPTION
                "The maximum duration in seconds that an Adsl Pots Low
                Pass Filter Bypass Relay will remain active (meaning
                closed/energized). As a fail-safe mechanism, the relay
                will automatically return a line back to normal
                operational mode when this timer has expired.

                This object is only valid for Adsl Pots Splitter
                cards containing the Pots LPF Bypass Relays."
            DEFVAL { 60 }
            ::= { zhoneVdslLineConfProfileEntry 98 }


        -- 1.3.6.1.4.1.5504.5.13.1.1.11.1.99
        zhoneVdslLineConfDMTConfMode OBJECT-TYPE
            SYNTAX INTEGER
                {
                echocancel(1),
                freqdivmux(2)
                }
            MAX-ACCESS read-create
            STATUS current
            DESCRIPTION
                "Discrete Multi-Tone parameter that selects whether there
                is overlap (echoCancel) or no overlap (freqDivMux) of bins."
            DEFVAL { freqdivmux }
            ::= { zhoneVdslLineConfProfileEntry 99 }


        -- 1.3.6.1.4.1.5504.5.13.1.1.11.1.100
        zhoneVdslLineConfDownBitSwap OBJECT-TYPE
            SYNTAX INTEGER
                {
                disabled(1),
                enabled(2)
                }
            MAX-ACCESS read-create
            STATUS current
            DESCRIPTION
                "Enable or disable downstream bit swap."
            DEFVAL { enabled }
            ::= { zhoneVdslLineConfProfileEntry 100 }


        -- 1.3.6.1.4.1.5504.5.13.1.1.11.1.101
        zhoneVdslLineConfUpBitSwap OBJECT-TYPE
            SYNTAX INTEGER
                {
                disabled(1),
                enabled(2)
                }
            MAX-ACCESS read-create
            STATUS current
            DESCRIPTION
                "Enable or disable upstream bit swap."
            DEFVAL { enabled }
            ::= { zhoneVdslLineConfProfileEntry 101 }


        -- 1.3.6.1.4.1.5504.5.13.1.1.11.1.102
        zhoneVdslLineConfAdslAnnexMModeEnabled OBJECT-TYPE
            SYNTAX TruthValue
            MAX-ACCESS read-create
            STATUS current
            DESCRIPTION
                "This object indicates whether Annex-M mode is enabled
                on the Adsl modem.  If this object is set to 'true' then
                Annex-M mode is enabled.  If it is set to 'false then
                Annex-M mode is disabled."
            DEFVAL { false }
            ::= { zhoneVdslLineConfProfileEntry 102 }


        -- 1.3.6.1.4.1.5504.5.13.1.1.11.1.103
        zhoneVdslLineConfAdslAnnexMPsdMask OBJECT-TYPE
            SYNTAX INTEGER
                {
                eu64(1),
                eu60(2),
                eu56(3),
                eu52(4),
                eu48(5),
                eu44(6),
                eu40(7),
                eu36(8),
                eu32(9),
                all(10)
                }
            MAX-ACCESS read-create
            STATUS current
            DESCRIPTION
                "This object specifies the maximum transmit PSD
                allowed in the downstream channel on an BIS
                Annex-M line."
            DEFVAL { eu32 }
            ::= { zhoneVdslLineConfProfileEntry 103 }


        -- 1.3.6.1.4.1.5504.5.13.1.1.11.1.104
        zhoneVdslLineConfUs0BoundaryTone OBJECT-TYPE
            SYNTAX INTEGER
                {
                d32(1),
                d36(2),
                d40(3),
                d44(4),
                d48(5),
                d52(6),
                d56(7),
                d64(8)
                }
            MAX-ACCESS read-create
            STATUS current
            DESCRIPTION
                "This object configures the upper boundary of US0.
                US0 is used in long reach mode when there is no more
                capacity in US1.   The switchover is typically around
                3500 feet."
            DEFVAL { d32 }
            ::= { zhoneVdslLineConfProfileEntry 104 }


        -- 1.3.6.1.4.1.5504.5.13.1.1.11.1.105
        zhoneVdslLineConfDownInp OBJECT-TYPE
            SYNTAX INTEGER
                {
                noProtection(1),
                halfSymbol(2),
                singleSymbol(3),
                twoSymbols(4),
                threeSymbols(5),
                fourSymbols(6),
                fiveSymbols(7),
                sixSymbols(8),
                sevenSymbols(9),
                eightSymbols(10),
                nineSymbols(11),
                tenSymbols(12),
                elevenSymbols(13),
                twelveSymbols(14),
                thirteenSymbols(15),
                fourteenSymbols(16),
                fifteenSymbols(17),
                sixteenSymbols(18)
                }
            MAX-ACCESS read-create
            STATUS current
            DESCRIPTION
                "The minimum impulse noise protection for the downstream
                bearer channel expressed in symbols.   One symbol equals
                250 uS."
            DEFVAL { twoSymbols }
            ::= { zhoneVdslLineConfProfileEntry 105 }


        -- 1.3.6.1.4.1.5504.5.13.1.1.11.1.106
        zhoneVdslLineConfUpInp OBJECT-TYPE
            SYNTAX INTEGER
                {
                noProtection(1),
                halfSymbol(2),
                singleSymbol(3),
                twoSymbols(4),
                fourSymbols(5),
                eightSymbols(6),
                sixteenSymbols(7),
                threeSymbols(8),
                fiveSymbols(9),
                sixSymbols(10),
                sevenSymbols(11),
                nineSymbols(12),
                tenSymbols(13),
                elevenSymbols(14),
                twelveSymbols(15),
                thirteenSymbols(16),
                fourteenSymbols(17),
                fifteenSymbols(18)
                }
            MAX-ACCESS read-create
            STATUS current
            DESCRIPTION
                "The minimum impulse noise protection for the upstream
                bearer channel expressed in symbols.   One symbol equals
                250 uS."
            DEFVAL { twoSymbols }
            ::= { zhoneVdslLineConfProfileEntry 106 }


        -- 1.3.6.1.4.1.5504.5.13.1.1.11.1.107
        zhoneVdslLineConfDownMaxInterleavingDelay OBJECT-TYPE
            SYNTAX INTEGER (0..63)
            UNITS "milliseconds"
            MAX-ACCESS read-create
            STATUS current
            DESCRIPTION
                "The maximum inteleaving delay in the downstream direction.
                A value of zero indicates no delay introduced."
            DEFVAL { 0 }
            ::= { zhoneVdslLineConfProfileEntry 107 }


        -- 1.3.6.1.4.1.5504.5.13.1.1.11.1.108
        zhoneVdslLineConfUpMaxInterleavingDelay OBJECT-TYPE
            SYNTAX INTEGER (0..63)
            UNITS "milliseconds"
            MAX-ACCESS read-create
            STATUS current
            DESCRIPTION
                "The maximum inteleaving delay in the upstream direction.
                A value of zero indicates no delay introduced."
            DEFVAL { 0 }
            ::= { zhoneVdslLineConfProfileEntry 108 }


        -- 1.3.6.1.4.1.5504.5.13.1.1.11.1.109
        zhoneVdslLineConfDownPsdMaskEnable OBJECT-TYPE
            SYNTAX INTEGER
                {
                standard(2),
                mod(3),
                modFallback(4)
                }
            MAX-ACCESS read-create
            STATUS current
            DESCRIPTION
                "This object selects the Psd Mask in the downstream direction.

                  'standard'   : use the PSD Mask specified in the object
                                 zhoneVdslLineConfDownPsdSelect

                  'mod'        : use the pre-defined Mask-On-Demand PSD Mask

                  'modFallback': use the pre-defined Mask-On-Demand PSD
                                 Mask with fallback"
            DEFVAL { standard }
            ::= { zhoneVdslLineConfProfileEntry 109 }


        -- 1.3.6.1.4.1.5504.5.13.1.1.11.1.110
        zhoneVdslLineConfUpPsdMaskEnable OBJECT-TYPE
            SYNTAX INTEGER
                {
                standard(2),
                mod(3),
                modFallback(4)
                }
            MAX-ACCESS read-create
            STATUS current
            DESCRIPTION
                "This object selects the Psd Mask in the upstream direction.

                  'standard'   : use the PSD Mask specified in the object
                                 zhoneVdslLineConfDownPsdSelect

                  'mod'        : use the pre-defined Mask-On-Demand PSD Mask

                  'modFallback': use the pre-defined Mask-On-Demand PSD
                                 Mask with fallback"
            DEFVAL { standard }
            ::= { zhoneVdslLineConfProfileEntry 110 }


        -- 1.3.6.1.4.1.5504.5.13.1.1.11.1.111
        zhoneVdslLineConfDownPsdMaskSelect OBJECT-TYPE
            SYNTAX INTEGER
                {
                custom(1),
                customMOD(2),
                dmtPSDCOMSK2(3),
                dmtPSDFLATMSK(4),
                dmtPSDCABMSK2(5),
                dmtPSDCOMSK2RFI(6),
                dmtPSDFLATMSKRFI(7),
                dmtPSDCABMSK2RFI(8),
                dmtPSDADSL2NONOVLPM1(9),
                dmtPSDADSL2NONOVLPM2(10),
                dmtPSDADSL2NONOVLPFLAT(11),
                g993RegionC(12),
                g993RegionA(13),
                g993RegionA-E17a-D-32(14),
                g993RegionA-E17a-D-48(15),
                g993RegionA-E17a-D-64(16),
                g993RegionA-E17a-D-128(17),
                g998RegionB-M1x-A(18),
                g998RegionB-M1x-B(19),
                g998RegionB-M1x-NUS0(20),
                g998RegionB-M2x-A(21),
                g998RegionB-M2x-M(22),
                g998RegionB-M2x-B(23),
                g998RegionB-M2x-NUS0(24),
                g998RegionB-E17-M2x-NUS0(25),
                g998RegionB-E17-M2x-NUS0-M(26),
                g998RegionB-ADE17-M2x-NUS0-M(27),
                g998RegionB-ADE17-M2x-A(28),
                g998RegionB-ADE17-M2x-B(29),
                g998RegionB-E30-M2x-NUS0(30),
                g998RegionB-E30-M2x-NUS0-M(31),
                g998RegionB-ADE30-M2x-NUS0-M(32),
                g998RegionB-ADE30-M2x-NUS0-A(33),
                g998RegionB-NONSTD-E17-M2x(34),
                g998RegionB-NONSTD-E17-M2x-M(35),
                g997RegionB-M1c-A-7(36),
                g997RegionB-M1x-M-8(37),
                g997RegionB-M1x-M(38),
                g997RegionB-M2x-M-8(39),
                g997RegionB-M2x-A(40),
                g997RegionB-M2x-M(41),
                g997RegionB-HPE17-M1-NUS0(42),
                g997RegionB-HPE30-M1-NUS0(43),
                g997RegionB-E17-M2x-A(44),
                g997RegionB-E30-M2x-NUS0(45)
                }
            MAX-ACCESS read-create
            STATUS current
            DESCRIPTION
                "This object selects one of the standards based PSD mask for the
                downstream direction.   The object zhoneVdslLineConfDownPsdMaskEnable
                must be set to 'standard' for this object to be active."
            DEFVAL { g993RegionA }
            ::= { zhoneVdslLineConfProfileEntry 111 }


        -- 1.3.6.1.4.1.5504.5.13.1.1.11.1.112
        zhoneVdslLineConfUpPsdMaskSelect OBJECT-TYPE
            SYNTAX INTEGER
                {
                custom(1),
                g993J-ADLU-32(2),
                g993J-ADLU-36(3),
                g993J-ADLU-40(4),
                g993J-ADLU-44(5),
                g993J-ADLU-48(6),
                g993J-ADLU-52(7),
                g993J-ADLU-60(8),
                g993J-ADLU-64(9),
                g993JM-EU-32(10),
                g993JM-EU-36(11),
                g993JM-EU-40(12),
                g993JM-EU-44(13),
                g993JM-EU-48(14),
                g993JM-EU-52(15),
                g993JM-EU-60(16),
                g993JM-EU-64(17),
                dmtExtended(18),
                dmtJJ100(19),
                dmtStandard(20),
                g993RegionA-EU-32(21),
                g993RegionA-EU-36(22),
                g993RegionA-EU-40(23),
                g993RegionA-EU-44(24),
                g993RegionA-EU-48(25),
                g993RegionA-EU-52(26),
                g993RegionA-EU-56(27),
                g993RegionA-EU-60(28),
                g993RegionA-EU-64(29),
                g998RegionB-M1x-A(30),
                g998RegionB-M1x-B(31),
                g998RegionB-M1x-NUS0(32),
                g998RegionB-M2x-A(33),
                g998RegionB-M2x-M(34),
                g998RegionB-M2x-B(35),
                g998RegionB-M2x-NUS0(36),
                g998RegionB-E17-M2x-NUS0(37),
                g998RegionB-E17-M2x-NUS0-M(38),
                g998RegionB-ADE17-M2x-NUS0-M(39),
                g998RegionB-ADE17-M2x-A(40),
                g998RegionB-ADE17-M2x-B(41),
                g998RegionB-E30-M2x-NUS0(42),
                g998RegionB-E30-M2x-NUS0-M(43),
                g998RegionB-ADE30-M2x-NUS0-M(44),
                g998RegionB-ADE30-M2x-NUS0-A(45),
                g998RegionB-NONSTD-E17-M2x(46),
                g998RegionB-NONSTD-E17-M2x-M(47),
                g997RegionB-M1c-A-7(48),
                g997RegionB-M1x-M-8(49),
                g997RegionB-M1x-M(50),
                g997RegionB-M2x-M-8(51),
                g997RegionB-M2x-A(52),
                g997RegionB-M2x-M(53),
                g997RegionB-HPE17-M1-NUS0(54),
                g997RegionB-HPE30-M1-NUS0(55),
                g997RegionB-E17-M2x-A(56),
                g997RegionB-E30-M2x-NUS0(57)
                }
            MAX-ACCESS read-create
            STATUS current
            DESCRIPTION
                "This object selects one of the standards based PSD mask for the
                upstream direction.  The object zhoneVdslLineConfUpPsdMaskEnable
                must be set to 'standard' for this object to be active."
            DEFVAL { g993RegionA-EU-32 }
            ::= { zhoneVdslLineConfProfileEntry 112 }


--
        -- 1.3.6.1.4.1.5504.5.13.1.1.11.1.113
        zhoneVdslLineEnableTrellisCoding OBJECT-TYPE
            SYNTAX TruthValue
            MAX-ACCESS read-create
            STATUS current
            DESCRIPTION
                "Enables/disables Trellis coding."
            DEFVAL { true }
            ::= { zhoneVdslLineConfProfileEntry 113 }
--
--

--
        -- 1.3.6.1.4.1.5504.5.13.1.1.11.1.114
        zhoneVdslLineEnableRsCoding OBJECT-TYPE
            SYNTAX TruthValue
            MAX-ACCESS read-create
            STATUS current
            DESCRIPTION
                "Enables/disables Rs coding."
            DEFVAL { true }
            ::= { zhoneVdslLineConfProfileEntry 114 }


--
        -- 1.3.6.1.4.1.5504.5.13.1.1.11.1.115
        zhoneVdslLineConfPsdShape OBJECT-TYPE
            SYNTAX INTEGER
                {
                region-a-nus0(1),
                region-a-eu-32(2),
                region-a-eu-36(3),
                region-a-eu-40(4),
                region-a-eu-44(5),
                region-a-eu-48(6),
                region-a-eu-52(7),
                region-a-eu-56(8),
                region-a-eu-60(9),
                region-a-eu-64(10),
                region-a-eu-128(11),
                region-a-adlu-32(12),
                region-a-adlu-36(13),
                region-a-adlu-40(14),
                region-a-adlu-44(15),
                region-a-adlu-48(16),
                region-a-adlu-52(17),
                region-a-adlu-56(18),
                region-a-adlu-60(19),
                region-a-adlu-64(20),
                region-a-adlu-128(21),
                region-b-998-m1x-a(22),
                region-b-998-m1x-b(23),
                region-b-998-m1x-nus0(24),
                region-b-998-m2x-a(25),
                region-b-998-m2x-m(26),
                region-b-998-m2x-b(27),
                region-b-998-m2x-nus0(28),
                region-b-998-e17-m2x-nus0(29),
                region-b-998-e17-m2x-nus0-m(30),
                region-b-998-ade17-m2x-nus0-m(31),
                region-b-998-ade17-m2x-a(32),
                region-b-998-ade17-m2x-b(33),
                region-b-998-e30-m2x-nus0(34),
                region-b-998-e30-m2x-nus0-m(35),
                region-b-998-ade30-m2x-nus0-m(36),
                region-b-998-ade30-m2x-nus0-a(37),
                region-b-997-m1c-a-7(38),
                region-b-997-m1x-m-8(39),
                region-b-997-m1x-m(40),
                region-b-997-m2x-m-8(41),
                region-b-997-m2x-a(42),
                region-b-997-m2x-m(43),
                region-b-997-hpe17-m1-nus0(44),
                region-b-997-hpe30-m1-nus0(45),
                region-b-997-e17-m2x-a(46),
                region-b-997-e30-m2x-nus0(47),
                region-b-997-bt-anfp(48),
                region-c-138-b(49),
                region-c-276-b(50),
                region-c-138-co(51),
                region-c-276-co(52),
                region-c-tcmisdn(53),
                region-c-1104-co-17a(54),
                region-c-1104-co-30a(55)
                }
            MAX-ACCESS read-create
            STATUS current
            DESCRIPTION
                "Maximum transmit PSD allowed on a VDSL2 line."
            DEFVAL { region-a-eu-32 }
            ::= { zhoneVdslLineConfProfileEntry 115 }


--
        -- 1.3.6.1.4.1.5504.5.13.1.1.11.1.116
        zhoneVdslLineConfDownPhyRSupport OBJECT-TYPE
            SYNTAX INTEGER
                {
                enable(1),
                disable(2)
                }
            MAX-ACCESS read-create
            STATUS current
            DESCRIPTION
                "Enable or disable downstream PHYR.
                Only supported by Broadcom PHYR ports."
            DEFVAL { enable }
            ::= { zhoneVdslLineConfProfileEntry 116 }


--
        -- 1.3.6.1.4.1.5504.5.13.1.1.11.1.117
        zhoneVdslLineConfUpPhyRSupport OBJECT-TYPE
            SYNTAX INTEGER
                {
                enable(1),
                disable(2)
                }
            MAX-ACCESS read-create
            STATUS current
            DESCRIPTION
                "Enable or disable upstream PHYR.
                Only supported by Broadcom PHYR ports."
            DEFVAL { enable }
            ::= { zhoneVdslLineConfProfileEntry 117 }


--
        -- 1.3.6.1.4.1.5504.5.13.1.1.11.1.118
        zhoneVdslLineConfDownPhyRmaxINP OBJECT-TYPE
            SYNTAX INTEGER (0 | 5..160)
            MAX-ACCESS read-create
            STATUS current
            DESCRIPTION
                "PHYR maximum downstream impulse noise protection.

                A value of 0 specifies no protection.

                The values 5 through 160 specify the number of
                symbols in 1/10 increments.

                Only supported by Broadcom PHYR ports."
            DEFVAL { 0 }
            ::= { zhoneVdslLineConfProfileEntry 118 }


--
        -- 1.3.6.1.4.1.5504.5.13.1.1.11.1.119
        zhoneVdslLineConfUpPhyRmaxINP OBJECT-TYPE
            SYNTAX INTEGER (0 | 5..160)
            MAX-ACCESS read-create
            STATUS current
            DESCRIPTION
                "PHYR maximum upstream impulse noise protection.

                A value of 0 specifies no protection.

                The values 5 through 160 specify the number of
                symbols in 1/10 increments.

                Only supported by Broadcom PHYR ports."
            DEFVAL { 0 }
            ::= { zhoneVdslLineConfProfileEntry 119 }


--
        -- 1.3.6.1.4.1.5504.5.13.1.1.11.1.120
        zhoneVdslLineConfDownPhyRminRSoverhead OBJECT-TYPE
            SYNTAX INTEGER (0..255)
            MAX-ACCESS read-create
            STATUS current
            DESCRIPTION
                "PHYR minimum downstream RS overhead.
                Only supported by Broadcom PHYR ports."
            DEFVAL { 0 }
            ::= { zhoneVdslLineConfProfileEntry 120 }


--
        -- 1.3.6.1.4.1.5504.5.13.1.1.11.1.121
        zhoneVdslLineConfUpPhyRminRSoverhead OBJECT-TYPE
            SYNTAX INTEGER (0..255)
            MAX-ACCESS read-create
            STATUS current
            DESCRIPTION
                "PHYR minimum upstream RS overhead.
                Only supported by Broadcom PHYR ports."
            DEFVAL { 0 }
            ::= { zhoneVdslLineConfProfileEntry 121 }


--
        -- 1.3.6.1.4.1.5504.5.13.1.1.11.1.122
        zhoneVdslLineConfDownPhyRRtxRatio OBJECT-TYPE
            SYNTAX INTEGER (0..255)
            MAX-ACCESS read-create
            STATUS current
            DESCRIPTION
                "PHYR minimum downstream fraction of the
                line rate allocated for retransmission.
                Only supported by Broadcom PHYR ports."
            ::= { zhoneVdslLineConfProfileEntry 122 }


        -- 1.3.6.1.4.1.5504.5.13.1.1.11.1.123
        zhoneVdslLineConfUpPhyRRtxRatio OBJECT-TYPE
            SYNTAX INTEGER (0..255)
            MAX-ACCESS read-create
            STATUS current
            DESCRIPTION
                "PHYR minimum upstream fraction of the
                line rate allocated for retransmission.
                Only supported by Broadcom PHYR ports."
            DEFVAL { 0 }
            ::= { zhoneVdslLineConfProfileEntry 123 }


        -- 1.3.6.1.4.1.5504.5.13.1.1.11.1.124
        zhoneVdslLineConfUpPboPsdParamA3 OBJECT-TYPE
            SYNTAX Integer32 (4000..8096)
            UNITS ".01 dBm/Hz"
            MAX-ACCESS read-create
            STATUS current
            DESCRIPTION
                "Upstream power backoff PSD parameter A3.  This
                parameter is only used if the mask selection
                is set to PSDMaskABParameters"
            DEFVAL { 4000 }
            ::= { zhoneVdslLineConfProfileEntry 124 }


        -- 1.3.6.1.4.1.5504.5.13.1.1.11.1.125
        zhoneVdslLineConfUpPboPsdParamA4 OBJECT-TYPE
            SYNTAX Integer32 (4000..8096)
            UNITS ".01 dBm/Hz"
            MAX-ACCESS read-create
            STATUS current
            DESCRIPTION
                "Upstream power backoff PSD parameter A4.  This
                parameter is only used if the mask selection
                is set to PSDMaskABParameters"
            DEFVAL { 4000 }
            ::= { zhoneVdslLineConfProfileEntry 125 }


        -- 1.3.6.1.4.1.5504.5.13.1.1.11.1.126
        zhoneVdslLineConfUpPboPsdParamB3 OBJECT-TYPE
            SYNTAX Integer32 (0..4096)
            UNITS ".01 dBm/Hz"
            MAX-ACCESS read-create
            STATUS current
            DESCRIPTION
                "Upstream power backoff PSD parameter B3.  This
                parameter is only used if the mask selection
                is set to PSDMaskABParameters"
            DEFVAL { 4000 }
            ::= { zhoneVdslLineConfProfileEntry 126 }


        -- 1.3.6.1.4.1.5504.5.13.1.1.11.1.127
        zhoneVdslLineConfUpPboPsdParamB4 OBJECT-TYPE
            SYNTAX Integer32 (0..4096)
            UNITS ".01 dBm/Hz"
            MAX-ACCESS read-create
            STATUS current
            DESCRIPTION
                "Upstream power backoff PSD parameter B4.  This
                parameter is only used if the mask selection
                is set to PSDMaskABParameters"
            DEFVAL { 4000 }
            ::= { zhoneVdslLineConfProfileEntry 127 }


        -- 1.3.6.1.4.1.5504.5.13.1.1.11.1.128
        zhoneVdslLineConfFallbackDefaultVpi OBJECT-TYPE
            SYNTAX Unsigned32 (0..255)
            MAX-ACCESS read-create
            STATUS current
            DESCRIPTION
                "ATM VPI to be used by the line when it trains
                in ADSL/ATM mode and bridges are configured for
                single-vc mode"
            DEFVAL { 0 }
            ::= { zhoneVdslLineConfProfileEntry 128 }


        -- 1.3.6.1.4.1.5504.5.13.1.1.11.1.129
        zhoneVdslLineConfFallbackDefaultVci OBJECT-TYPE
            SYNTAX Unsigned32 (0..65535)
            MAX-ACCESS read-create
            STATUS current
            DESCRIPTION
                "ATM VCI to be used by the line when it trains
                in ADSL/ATM mode and bridges are configured for
                single-vc mode"
            DEFVAL { 35 }
            ::= { zhoneVdslLineConfProfileEntry 129 }


        -- 1.3.6.1.4.1.5504.5.13.1.1.11.1.130
        zhoneVdslLineConfDownGinpSupport OBJECT-TYPE
            SYNTAX INTEGER
                {
                enable(1),
                disable(2)
                }
            MAX-ACCESS read-create
            STATUS current
            DESCRIPTION
                "Enable or disable downstream G.INP / ITU-G.998.4.
                Only supported by Broadcom ports."
            REFERENCE
                "ITU-G.998.4"
            DEFVAL { disable }
            ::= { zhoneVdslLineConfProfileEntry 130 }


        -- 1.3.6.1.4.1.5504.5.13.1.1.11.1.131
        zhoneVdslLineConfUpGinpSupport OBJECT-TYPE
            SYNTAX INTEGER
                {
                enable(1),
                disable(2)
                }
            MAX-ACCESS read-create
            STATUS current
            DESCRIPTION
                "Enable or disable upstream G.INP / ITU-G.998.4.
                Only supported by Broadcom ports."
            DEFVAL { disable }
            ::= { zhoneVdslLineConfProfileEntry 131 }


        -- 1.3.6.1.4.1.5504.5.13.1.1.11.1.132
        zhoneVdslLineConfDownGinpEtrMax OBJECT-TYPE
            SYNTAX Unsigned32 (64..200000)
            UNITS "kbps"
            MAX-ACCESS read-create
            STATUS current
            DESCRIPTION
                "gInpEtrMax - Maximum allowed value for downstream expected throughput
                (ETR) in kbit/s. The valid values are all multiples of 8 from 0 to
                the maximum of the valid values of the maximum net data rate
                specified in the associated Recommendation. ITU-T G.998.4 7.1.1
                Control parameters and 7.1.2 Valid configurations.
                "
            REFERENCE
                "ITU-G.998.4"
            DEFVAL { 100000 }
            ::= { zhoneVdslLineConfProfileEntry 132 }


        -- 1.3.6.1.4.1.5504.5.13.1.1.11.1.133
        zhoneVdslLineConfUpGinpEtrMax OBJECT-TYPE
            SYNTAX Unsigned32 (64..2000000)
            UNITS "kbps"
            MAX-ACCESS read-create
            STATUS current
            DESCRIPTION
                "gInpEtrMax - Maximum allowed value for upstream expected throughput
                (ETR) in kbit/s. The valid values are all multiples of 8 from 0 to
                the maximum of the valid values of the maximum net data rate
                specified in the associated Recommendation. ITU-T G.998.4 7.1.1
                Control parameters and 7.1.2 Valid configurations."
            REFERENCE
                "ITU-G.998.4"
            DEFVAL { 60000 }
            ::= { zhoneVdslLineConfProfileEntry 133 }


        -- 1.3.6.1.4.1.5504.5.13.1.1.11.1.134
        zhoneVdslLineConfDownGinpEtrMin OBJECT-TYPE
            SYNTAX Unsigned32 (64..200000)
            UNITS "kbps"
            MAX-ACCESS read-create
            STATUS current
            DESCRIPTION
                "gInpEtrMin - Minimum allowed value for downstream expected throughput
                (ETR) in kbit/s. The valid values are all multiples of 8 from 0 to
                the maximum of the valid values of the minimum net data rate specified
                in the associated Recommendation. ITU-T G.998.4 7.1.1 Control parameters
                and 7.1.2 Valid configurations."
            REFERENCE
                "ITU-G.998.4"
            DEFVAL { 64 }
            ::= { zhoneVdslLineConfProfileEntry 134 }


        -- 1.3.6.1.4.1.5504.5.13.1.1.11.1.135
        zhoneVdslLineConfUpGinpEtrMin OBJECT-TYPE
            SYNTAX Unsigned32 (64..200000)
            UNITS "kbps"
            MAX-ACCESS read-create
            STATUS current
            DESCRIPTION
                "gInpEtrMin - Minimum allowed value for upstream expected throughput
                (ETR) in kbit/s. The valid values are all multiples of 8 from 0 to
                the maximum of the valid values of the minimum net data rate specified
                in the associated Recommendation. ITU-T G.998.4 7.1.1 Control parameters
                and 7.1.2 Valid configurations."
            REFERENCE
                "ITU-G.998.4"
            DEFVAL { 64 }
            ::= { zhoneVdslLineConfProfileEntry 135 }


--
        -- 1.3.6.1.4.1.5504.5.13.1.1.11.1.136
        zhoneVdslLineConfDownGinpNdrMax OBJECT-TYPE
            SYNTAX Unsigned32 (64..200000)
            UNITS "kbps"
            MAX-ACCESS read-create
            STATUS current
            DESCRIPTION
                "gInpNdrMax - Maximum allowed value for downstream net data rate (NDR)
                in kbit/s. The valid values are all multiples of 8 from 0 to the
                maximum of the valid values of the maximum net data rate specified
                in the associated Recommendation. ITU-T G.998.4 7.1.1 Control parameters
                and 7.1.2 Valid configurations."
            REFERENCE
                "ITU-G.998.4"
            DEFVAL { 100000 }
            ::= { zhoneVdslLineConfProfileEntry 136 }


        -- 1.3.6.1.4.1.5504.5.13.1.1.11.1.137
        zhoneVdslLineConfUpGinpNdrMax OBJECT-TYPE
            SYNTAX Unsigned32 (64..200000)
            UNITS "kbps"
            MAX-ACCESS read-create
            STATUS current
            DESCRIPTION
                "gInpNdrMax - Maximum allowed value for upstream net data rate (NDR)
                in kbit/s. The valid values are all multiples of 8 from 0 to the
                maximum of the valid values of the maximum net data rate specified
                in the associated Recommendation. ITU-T G.998.4 7.1.1 Control parameters
                and 7.1.2 Valid configurations."
            REFERENCE
                "ITU-G.998.4"
            DEFVAL { 60000 }
            ::= { zhoneVdslLineConfProfileEntry 137 }


        -- 1.3.6.1.4.1.5504.5.13.1.1.11.1.138
        zhoneVdslLineConfDownGinpShineRatio OBJECT-TYPE
            SYNTAX Unsigned32 (0..255)
            UNITS "ratio"
            MAX-ACCESS read-create
            STATUS current
            DESCRIPTION
                "gInpShineRatio - The downstream loss of rate in a 1 second interval
                expressed as a fraction of NDR due to a single high impulse noise
                event (SHINE) impulse noise environment expected by the operator
                to occur at a probability acceptable for the services. The valid
                values are all multiples of 0.001 from 0 to 0.1.  This field uses
                1 to equal 0.001 and 100 to equal 0.1. ITU-T G.998.4 7.1.1 Control
                parameters and 7.1.2 Valid configurations."
            REFERENCE
                "ITU-G.998.4"
            DEFVAL { 10 }
            ::= { zhoneVdslLineConfProfileEntry 138 }


        -- 1.3.6.1.4.1.5504.5.13.1.1.11.1.139
        zhoneVdslLineConfUpGinpShineRatio OBJECT-TYPE
            SYNTAX Unsigned32 (0..255)
            UNITS "ratio"
            MAX-ACCESS read-create
            STATUS current
            DESCRIPTION
                "gInpShineRatio - The upstream loss of rate in a 1 second interval
                expressed as a fraction of NDR due to a single high impulse noise
                event (SHINE) impulse noise environment expected by the operator
                to occur at a probability acceptable for the services. The valid
                values are all multiples of 0.001 from 0 to 0.1.  This field uses
                1 to equal 0.001 and 100 to equal 0.1. ITU-T G.998.4 7.1.1 Control
                parameters and 7.1.2 Valid configurations."
            REFERENCE
                "ITU-G.998.4"
            DEFVAL { 10 }
            ::= { zhoneVdslLineConfProfileEntry 139 }


        -- 1.3.6.1.4.1.5504.5.13.1.1.11.1.140
        zhoneVdslLineConfDownGinpLeftrThreshold OBJECT-TYPE
            SYNTAX Unsigned32 (0..99)
            UNITS "ratio"
            MAX-ACCESS read-create
            STATUS current
            DESCRIPTION
                "gInpLeftrThreshold - The downstream rate Threshold below which the
                Low Error Free Rate (LEFTR) defect is declared. The threshold used
                to declare leftr defects is expressed in fraction of the net data
                rate (NDR). The value 0 is a special value to indicate that the
                receiver shall use a special value for declaring leftr defect.
                The minimum valid threshold to declare leftr is ETR/2. The receiver
                shall ignore threshold values that are less than the minimum and shall
                use ETR/2 for declaring leftr defect instead. The valid values are
                all multiples of 0.01 from 0.01 to 0.99. This field uses 1 to equal
                0.01 and 99 to equal 0.99."
            REFERENCE
                "ITU-G.998.4"
            DEFVAL { 0 }
            ::= { zhoneVdslLineConfProfileEntry 140 }


        -- 1.3.6.1.4.1.5504.5.13.1.1.11.1.141
        zhoneVdslLineConfUpGinpLeftrThreshold OBJECT-TYPE
            SYNTAX Unsigned32 (0..99)
            UNITS "ratio"
            MAX-ACCESS read-create
            STATUS current
            DESCRIPTION
                "gInpLeftrThreshold - The upstream rate Threshold below which the
                Low Error Free Rate (LEFTR) defect is declared. The threshold used
                to declare leftr defects is expressed in fraction of the net data
                rate (NDR). The value 0 is a special value to indicate that the
                receiver shall use a special value for declaring leftr defect.
                The minimum valid threshold to declare leftr is ETR/2. The receiver
                shall ignore threshold values that are less than the minimum and shall
                use ETR/2 for declaring leftr defect instead. The valid values are
                all multiples of 0.01 from 0.01 to 0.99. This field uses 1 to equal
                0.01 and 99 to equal 0.99."
            REFERENCE
                "ITU-G.998.4"
            DEFVAL { 0 }
            ::= { zhoneVdslLineConfProfileEntry 141 }


        -- 1.3.6.1.4.1.5504.5.13.1.1.11.1.142
        zhoneVdslLineConfDownGinpMaxDelay OBJECT-TYPE
            SYNTAX Unsigned32 (0..63)
            UNITS "mSecs"
            MAX-ACCESS read-create
            STATUS current
            DESCRIPTION
                "gInpMaxDelay - The maximum downstream delay in ms. This is the upper
                limit for the delay that is added to the transmission delay only caused
                by retransmissions. Here the receiver and/or the transmitter shall
                identify and discard all DTUs whose payload cannot be transferred over
                the reference point at the receiver without violating the delay_max
                limit. The time stamp shall be the criterion for discarding the DTUs.
                The processing delay between the U-interface and the retransmission
                sub-layer of the receiver in the retransmission data path direction
                shall be excluded from consideration for delay_max in the retransmission
                data path direction. The valid values are all integers from 1 to 63.
                ITU-T G.998.4 7.1.1 Control parameters, 7.1.2 Valid configurations, and
                8.1.6 Time Stamp."
            REFERENCE
                "ITU-G.998.4"
            DEFVAL { 20 }
            ::= { zhoneVdslLineConfProfileEntry 142 }


        -- 1.3.6.1.4.1.5504.5.13.1.1.11.1.143
        zhoneVdslLineConfUpGinpMaxDelay OBJECT-TYPE
            SYNTAX Unsigned32 (0..63)
            UNITS "mSecs"
            MAX-ACCESS read-create
            STATUS current
            DESCRIPTION
                "gInpMaxDelay - The maximum upstream delay in ms. This is the upper
                limit for the delay that is added to the transmission delay only caused
                by retransmissions. Here the receiver and/or the transmitter shall
                identify and discard all DTUs whose payload cannot be transferred over
                the reference point at the receiver without violating the delay_max
                limit. The time stamp shall be the criterion for discarding the DTUs.
                The processing delay between the U-interface and the retransmission
                sub-layer of the receiver in the retransmission data path direction
                shall be excluded from consideration for delay_max in the retransmission
                data path direction. The valid values are all integers from 1 to 63.
                ITU-T G.998.4 7.1.1 Control parameters, 7.1.2 Valid configurations, and
                8.1.6 Time Stamp."
            REFERENCE
                "ITU-G.998.4"
            DEFVAL { 20 }
            ::= { zhoneVdslLineConfProfileEntry 143 }


        -- 1.3.6.1.4.1.5504.5.13.1.1.11.1.144
        zhoneVdslLineConfDownGinpMinDelay OBJECT-TYPE
            SYNTAX Unsigned32 (0..63)
            UNITS "mSecs"
            MAX-ACCESS read-create
            STATUS current
            DESCRIPTION
                "gInpMinDelay - The minimum downstream delay in ms. This is the lower
                limit for the delay that is added to the transmission delay caused by
                retransmissions only. The time stamp shall be used by the outlet shaping
                function to determine when the payload of the DTU shall be sent to the
                reference point to meet the delay limits. The outlet shaping function
                shall minimize the additional delay that may be introduced above delay_
                min , and shall never exceed delay_max. The valid values are all integers
                from 0 to 63. ITU-T G.998.4 7.1.1 Control parameters, 7.1.2 Valid
                configurations, and 8.1.6 Time Stamp."
            REFERENCE
                "ITU-G.998.4"
            DEFVAL { 0 }
            ::= { zhoneVdslLineConfProfileEntry 144 }


        -- 1.3.6.1.4.1.5504.5.13.1.1.11.1.145
        zhoneVdslLineConfUpGinpMinDelay OBJECT-TYPE
            SYNTAX Unsigned32 (0..63)
            UNITS "mSecs"
            MAX-ACCESS read-create
            STATUS current
            DESCRIPTION
                "gInpMinDelay - The minimum upstream delay in ms. This is the lower
                limit for the delay that is added to the transmission delay caused by
                retransmissions only. The time stamp shall be used by the outlet shaping
                function to determine when the payload of the DTU shall be sent to the
                reference point to meet the delay limits. The outlet shaping function
                shall minimize the additional delay that may be introduced above delay_
                min , and shall never exceed delay_max. The valid values are all integers
                from 0 to 63. ITU-T G.998.4 7.1.1 Control parameters, 7.1.2 Valid
                configurations, and 8.1.6 Time Stamp."
            REFERENCE
                "ITU-G.998.4"
            DEFVAL { 0 }
            ::= { zhoneVdslLineConfProfileEntry 145 }


        -- 1.3.6.1.4.1.5504.5.13.1.1.11.1.146
        zhoneVdslLineConfDownGinpMin OBJECT-TYPE
            SYNTAX Unsigned32 (0..127)
            UNITS "symbols"
            MAX-ACCESS read-create
            STATUS current
            DESCRIPTION
                "ginpMin - The minimum downstream impulse noise protection (INP) against
                single high impulse noise event (SHINE) in discrete multitone (DMT)
                symbols. The valid values are all integers from 0 to 63 for system with
                a sub-carrier spacing of 4.3125 kHz. The valid values are all integers
                from 0 to 127 for system with a sub-carrier spacing of 8.625 kHz. ITU-T
                G.998.4 7.1.1 Control parameters and 7.1.2 Valid configurations."
            REFERENCE
                "ITU-G.998.4"
            DEFVAL { 4 }
            ::= { zhoneVdslLineConfProfileEntry 146 }


        -- 1.3.6.1.4.1.5504.5.13.1.1.11.1.147
        zhoneVdslLineConfUpGinpMin OBJECT-TYPE
            SYNTAX Unsigned32 (0..127)
            UNITS "symbols"
            MAX-ACCESS read-create
            STATUS current
            DESCRIPTION
                "ginpMin - The minimum upstream impulse noise protection (INP) against
                single high impulse noise event (SHINE) in discrete multitone (DMT)
                symbols. The valid values are all integers from 0 to 63 for system with
                a sub-carrier spacing of 4.3125 kHz. The valid values are all integers
                from 0 to 127 for system with a sub-carrier spacing of 8.625 kHz. ITU-T
                G.998.4 7.1.1 Control parameters and 7.1.2 Valid configurations."
            REFERENCE
                "ITU-G.998.4"
            DEFVAL { 4 }
            ::= { zhoneVdslLineConfProfileEntry 147 }


        -- 1.3.6.1.4.1.5504.5.13.1.1.11.1.148
        zhoneVdslLineConfDownGinpMinRSoverhead OBJECT-TYPE
            SYNTAX Unsigned32 (0..64)
            UNITS "ratio"
            MAX-ACCESS read-create
            STATUS current
            DESCRIPTION
                "gInpMinRSoverhead - This value specifies the downstream bandwidth
                reserved for RS (reed-solomon) codewords. The minimum guaranteed R/N
                ratio. The unit is 1/256th and the range is 0..64 (0 to 25%)."
            REFERENCE
                "ITU-G.998.4"
            DEFVAL { 0 }
            ::= { zhoneVdslLineConfProfileEntry 148 }


        -- 1.3.6.1.4.1.5504.5.13.1.1.11.1.149
        zhoneVdslLineConfUpGinpMinRSoverhead OBJECT-TYPE
            SYNTAX Unsigned32 (0..64)
            UNITS "ratio"
            MAX-ACCESS read-create
            STATUS current
            DESCRIPTION
                "gInpMinRSoverhead - This value specifies the upstream bandwidth
                reserved for RS (reed-solomon) codewords. The minimum guaranteed R/N
                ratio. The unit is 1/256th and the range is 0..64 (0 to 25%)."
            REFERENCE
                "ITU-G.998.4"
            DEFVAL { 0 }
            ::= { zhoneVdslLineConfProfileEntry 149 }


        -- 1.3.6.1.4.1.5504.5.13.1.1.11.1.150
        zhoneVdslLineConfDownGinpReinCfg OBJECT-TYPE
            SYNTAX Unsigned32 (0..7)
            UNITS "symbols"
            MAX-ACCESS read-create
            STATUS current
            DESCRIPTION
                "gInpReinCfg - The minimum downstream impulse protection against
                electrical repetitive impulse noise (REIN) in DMT symbols. The valid
                values are all integers from 0 to 7 for system with a sub-carrier
                spacing of 4.3125 kHz. The valid values are all integers from 0 to 13
                for system with a sub-carrier spacing of 8.625 kHz. ITU-T G.998.4 7.1.1
                Control parameters and 7.1.2 Valid configurations."
            REFERENCE
                "ITU-G.998.4"
            DEFVAL { 0 }
            ::= { zhoneVdslLineConfProfileEntry 150 }


        -- 1.3.6.1.4.1.5504.5.13.1.1.11.1.151
        zhoneVdslLineConfUpGinpReinCfg OBJECT-TYPE
            SYNTAX Unsigned32 (0..7)
            UNITS "symbols"
            MAX-ACCESS read-create
            STATUS current
            DESCRIPTION
                "gInpReinCfg - The minimum upstream impulse protection against
                electrical repetitive impulse noise (REIN) in DMT symbols. The valid
                values are all integers from 0 to 7 for system with a sub-carrier
                spacing of 4.3125 kHz. The valid values are all integers from 0 to 13
                for system with a sub-carrier spacing of 8.625 kHz. ITU-T G.998.4 7.1.1
                Control parameters and 7.1.2 Valid configurations."
            REFERENCE
                "ITU-G.998.4"
            DEFVAL { 0 }
            ::= { zhoneVdslLineConfProfileEntry 151 }


        -- 1.3.6.1.4.1.5504.5.13.1.1.11.1.152
        zhoneVdslLineConfDownGinpReinFreq OBJECT-TYPE
            SYNTAX INTEGER
                {
                freq100hz(1),
                freq120hz(2)
                }
            UNITS "Hz"
            MAX-ACCESS read-write
            STATUS current
            DESCRIPTION
                "ginpReinFreq specifies the frequency of REIN inter-arrival time. It is used
                in the Channel Initialization Policy and on-line reconfiguration procedures.
                REIN is commonly coupled from electrical power cables appliances drawing
                power from the AC electrical power network, having a repetition rate of
                twice the AC power frequency (100 or 120 Hz). The valid values are integers
                100 hz or 120 hz. ITU-T G.998.4 7.1.1 Control parameters and 7.1.2 Valid
                configurations."
            DEFVAL { freq120hz }
            ::= { zhoneVdslLineConfProfileEntry 152 }


        -- 1.3.6.1.4.1.5504.5.13.1.1.11.1.153
        zhoneVdslLineConfUpGinpReinFreq OBJECT-TYPE
            SYNTAX INTEGER
                {
                freq100hz(1),
                freq120hz(2)
                }
            UNITS "Hz"
            MAX-ACCESS read-write
            STATUS current
            DESCRIPTION
                "ginpReinFreq specifies the frequency of REIN inter-arrival time. It is used
                in the Channel Initialization Policy and on-line reconfiguration procedures.
                REIN is commonly coupled from electrical power cables appliances drawing
                power from the AC electrical power network, having a repetition rate of
                twice the AC power frequency (100 or 120 Hz). The valid values are integers
                100 hz or 120 hz. ITU-T G.998.4 7.1.1 Control parameters and 7.1.2 Valid
                configurations."
            DEFVAL { freq120hz }
            ::= { zhoneVdslLineConfProfileEntry 153 }


        -- 1.3.6.1.4.1.5504.5.13.1.1.11.1.154
        zhoneVdslLineConfDownGinpRtxMode OBJECT-TYPE
            SYNTAX INTEGER
                {
                forbidden(1),
                preferred(2),
                forced(3),
                testmode(4)
                }
            MAX-ACCESS read-create
            STATUS current
            DESCRIPTION
                "gInpRtxMode - Downstream retransmission Mode (RTX MODE). The RTX_MODE
                is a configuration parameter used to control activation of retransmission
                during initialization. This parameter has 4 valid values:
                 FORBIDDEN: ITU-T G.998.4 retransmission not allowed.
                 PREFERRED: ITU-T G.998.4 retransmission is preferred by the operator.
                   (i.e., if ITU-T G.998.4 RTX capability is supported by both XTU's,
                   the XTU's shall select ITU-T G.998.4 operation for this direction).
                 FORCED: Force the use of the ITU-T G.998.4 retransmission.
                   (i.e., if ITU-T G.998.4 RTX capability in this direction is not
                   supported by both XTU's or not selected by the XTU's, an
                   initialization failure shall result).
                   NOTE: Due to the optionality of ITU-T G.998.4 retransmission in
                   upstream direction, the use of FORCED in upstream may lead to
                   initialization failure, even if the XTU is supporting ITU-T G.998.4
                   (in downstream).
                 TESTMODE: Force the use of the ITU-T G.998.4 retransmission in the
                   test mode described in clause 10.4. (i.e., if ITU-T G.998.4 RTX
                   capability is not supported by both XTU's or not selected by the
                   XTU's, an initialization failure shall result).
                ITU-T G.998.4 11.1.13 Retransmission Mode (RTX_MODE)
                "
            REFERENCE
                "ITU-G.998.4"
            DEFVAL { preferred }
            ::= { zhoneVdslLineConfProfileEntry 154 }


        -- 1.3.6.1.4.1.5504.5.13.1.1.11.1.155
        zhoneVdslLineConfUpGinpRtxMode OBJECT-TYPE
            SYNTAX INTEGER
                {
                forbidden(1),
                preferred(2),
                forced(3),
                testmode(4)
                }
            MAX-ACCESS read-create
            STATUS current
            DESCRIPTION
                "gInpRtxMode - Upstream retransmission Mode (RTX MODE). The RTX_MODE
                is a configuration parameter used to control activation of retransmission
                during initialization. This parameter has 4 valid values:
                 FORBIDDEN: ITU-T G.998.4 retransmission not allowed.
                 PREFERRED: ITU-T G.998.4 retransmission is preferred by the operator.
                   (i.e., if ITU-T G.998.4 RTX capability is supported by both XTU's,
                   the XTU's shall select ITU-T G.998.4 operation for this direction).
                 FORCED: Force the use of the ITU-T G.998.4 retransmission.
                   (i.e., if ITU-T G.998.4 RTX capability in this direction is not
                   supported by both XTU's or not selected by the XTU's, an
                   initialization failure shall result).
                   NOTE: Due to the optionality of ITU-T G.998.4 retransmission in
                   upstream direction, the use of FORCED in upstream may lead to
                   initialization failure, even if the XTU is supporting ITU-T G.998.4
                   (in downstream).
                 TESTMODE: Force the use of the ITU-T G.998.4 retransmission in the
                   test mode described in clause 10.4. (i.e., if ITU-T G.998.4 RTX
                   capability is not supported by both XTU's or not selected by the
                   XTU's, an initialization failure shall result).
                ITU-T G.998.4 11.1.13 Retransmission Mode (RTX_MODE)"
            REFERENCE
                "ITU-G.998.4"
            DEFVAL { preferred }
            ::= { zhoneVdslLineConfProfileEntry 155 }


--   Alarm configuration profile table
--
-- 1.3.6.1.4.1.5504.5.13.1.1.20
        -- 1.3.6.1.4.1.5504.5.13.1.1.20
        zhoneVdslLineAlarmConfProfileTable OBJECT-TYPE
            SYNTAX SEQUENCE OF ZhoneVdslLineAlarmConfProfileEntry
            MAX-ACCESS not-accessible
            STATUS current
            DESCRIPTION
                "This table contains information on the VDSL line alarm
                configuration.  One entry in this table reflects a profile
                defined by a manager which can be used to configure the
                VDSL line alarm thresholds.

                Entries in this table MUST be maintained in a
                persistent manner."
            ::= { zhoneVdslMibObjects 20 }


--  1.3.6.1.4.1.5504.5.13.1.1.20.1
        -- 1.3.6.1.4.1.5504.5.13.1.1.20.1
        zhoneVdslLineAlarmConfProfileEntry OBJECT-TYPE
            SYNTAX ZhoneVdslLineAlarmConfProfileEntry
            MAX-ACCESS not-accessible
            STATUS current
            DESCRIPTION
                "Each entry consists of a list of parameters that
                represents the configuration of a VDSL line alarm
                profile.

                A default profile with an index of 'DEFVAL', will
                always exist and its parameters will be set to vendor
                specific values, unless otherwise specified in this
                document."
            INDEX { ifIndex }
            ::= { zhoneVdslLineAlarmConfProfileTable 1 }


        ZhoneVdslLineAlarmConfProfileEntry ::=
            SEQUENCE {
                zhoneVdslLineAlarmConfProfileName
                    SnmpAdminString,
                zhoneVdslLineAlarmConfThresh15MinLofs
                    INTEGER,
                zhoneVdslLineAlarmConfThresh15MinLoss
                    INTEGER,
                zhoneVdslLineAlarmConfThresh15MinLprs
                    INTEGER,
                zhoneVdslLineAlarmConfThresh15MinLols
                    INTEGER,
                zhoneVdslLineAlarmConfThresh15MinESs
                    INTEGER,
                zhoneVdslLineAlarmConfThresh15MinSESs
                    INTEGER,
                zhoneVdslLineAlarmConfThresh15MinUASs
                    INTEGER,
                zhoneVdslLineAlarmConfInitFailure
                    TruthValue,
                zhoneVdslLineAlarmConfProfRowStatus
                    RowStatus,
                zhoneVdslLineAlarmConfThresh1DayLofs
                    INTEGER,
                zhoneVdslLineAlarmConfThresh1DayLoss
                    INTEGER,
                zhoneVdslLineAlarmConfThresh1DayLprs
                    INTEGER,
                zhoneVdslLineAlarmConfThresh1DayLols
                    INTEGER,
                zhoneVdslLineAlarmConfThresh1DayESs
                    INTEGER,
                zhoneVdslLineAlarmConfThresh1DaySESs
                    INTEGER,
                zhoneVdslLineAlarmConfThresh1DayUASs
                    INTEGER,
                zhoneVdslLineAlarmConfThresh1DayInitFailure
                    TruthValue
             }

--  1.3.6.1.4.1.5504.5.13.1.1.20.1.1
        -- 1.3.6.1.4.1.5504.5.13.1.1.20.1.1
        zhoneVdslLineAlarmConfProfileName OBJECT-TYPE
            SYNTAX SnmpAdminString (SIZE (1..32))
            MAX-ACCESS not-accessible
            STATUS current
            DESCRIPTION
                "The name for this profile as specified by an
                administrator."
            ::= { zhoneVdslLineAlarmConfProfileEntry 1 }


        -- 1.3.6.1.4.1.5504.5.13.1.1.20.1.2
        zhoneVdslLineAlarmConfThresh15MinLofs OBJECT-TYPE
            SYNTAX INTEGER (0..900)
            UNITS "seconds"
            MAX-ACCESS read-create
            STATUS current
            DESCRIPTION
                "This object configures the threshold for the number of
                loss of frame seconds (LOFs) within any given 15-minute
                performance data collection interval.  If the value of
                loss of frame seconds in a particular 15-minute collection
                interval reaches/exceeds this value, a
                zhoneVdslPerfLofsThreshNotification notification will be
                generated.  No more than one notification will be sent
                per interval."
            ::= { zhoneVdslLineAlarmConfProfileEntry 2 }


        -- 1.3.6.1.4.1.5504.5.13.1.1.20.1.3
        zhoneVdslLineAlarmConfThresh15MinLoss OBJECT-TYPE
            SYNTAX INTEGER (0..900)
            UNITS "seconds"
            MAX-ACCESS read-create
            STATUS current
            DESCRIPTION
                "This object configures the threshold for the number of
                loss of signal seconds (LOSs) within any given 15-minute
                performance data collection interval.  If the value of
                loss of signal seconds in a particular 15-minute
                collection interval reaches/exceeds this value, a
                zhoneVdslPerfLossThreshNotification notification will be
                generated.  One notification will be sent per interval
                per endpoint."
            ::= { zhoneVdslLineAlarmConfProfileEntry 3 }


        -- 1.3.6.1.4.1.5504.5.13.1.1.20.1.4
        zhoneVdslLineAlarmConfThresh15MinLprs OBJECT-TYPE
            SYNTAX INTEGER (0..900)
            UNITS "seconds"
            MAX-ACCESS read-create
            STATUS current
            DESCRIPTION
                "This object configures the threshold for the number of
                loss of power seconds (LPRs) within any given 15-minute
                performance data collection interval.  If the value of
                loss of power seconds in a particular 15-minute collection
                interval reaches/exceeds this value, a
                zhoneVdslPerfLprsThreshNotification notification will be
                generated.  No more than one notification will be sent
                per interval."
            ::= { zhoneVdslLineAlarmConfProfileEntry 4 }


        -- 1.3.6.1.4.1.5504.5.13.1.1.20.1.5
        zhoneVdslLineAlarmConfThresh15MinLols OBJECT-TYPE
            SYNTAX INTEGER (0..900)
            UNITS "seconds"
            MAX-ACCESS read-create
            STATUS current
            DESCRIPTION
                "This object configures the threshold for the number of
                loss of link seconds (LOLs) within any given 15-minute
                performance data collection interval.  If the value of
                loss of link seconds in a particular 15-minute collection
                interval reaches/exceeds this value, a
                zhoneVdslPerfLolsThreshNotification notification will be
                generated.  No more than one notification will be sent
                per interval."
            ::= { zhoneVdslLineAlarmConfProfileEntry 5 }


        -- 1.3.6.1.4.1.5504.5.13.1.1.20.1.6
        zhoneVdslLineAlarmConfThresh15MinESs OBJECT-TYPE
            SYNTAX INTEGER (0..900)
            UNITS "seconds"
            MAX-ACCESS read-create
            STATUS current
            DESCRIPTION
                "This object configures the threshold for the number of
                errored seconds (ESs) within any given 15-minute
                performance data collection interval.  If the value of
                errored seconds in a particular 15-minute collection
                interval reaches/exceeds this value, a
                zhoneVdslPerfEssThreshNotification notification will be
                generated.  No more than one notification will be sent
                per interval."
            ::= { zhoneVdslLineAlarmConfProfileEntry 6 }


        -- 1.3.6.1.4.1.5504.5.13.1.1.20.1.7
        zhoneVdslLineAlarmConfThresh15MinSESs OBJECT-TYPE
            SYNTAX INTEGER (0..900)
            UNITS "seconds"
            MAX-ACCESS read-create
            STATUS current
            DESCRIPTION
                "This object configures the threshold for the number of
                severely errored seconds (SESs) within any given 15-minute
                performance data collection interval.  If the value of
                severely errored seconds in a particular 15-minute
                collection interval reaches/exceeds this value, a
                zhoneVdslPerfSessThreshNotification notification will be
                generated.  No more than one notification will be sent
                per interval."
            ::= { zhoneVdslLineAlarmConfProfileEntry 7 }


        -- 1.3.6.1.4.1.5504.5.13.1.1.20.1.8
        zhoneVdslLineAlarmConfThresh15MinUASs OBJECT-TYPE
            SYNTAX INTEGER (0..900)
            UNITS "seconds"
            MAX-ACCESS read-create
            STATUS current
            DESCRIPTION
                "This object configures the threshold for the number of
                unavailable seconds (UASs) within any given 15-minute
                performance data collection interval.  If the value of
                unavailable seconds in a particular 15-minute collection
                interval reaches/exceeds this value, a
                zhoneVdslPerfUassThreshNotification notification will be
                generated.  No more than one notification will be sent
                per interval."
            ::= { zhoneVdslLineAlarmConfProfileEntry 8 }


        -- 1.3.6.1.4.1.5504.5.13.1.1.20.1.9
        zhoneVdslLineAlarmConfInitFailure OBJECT-TYPE
            SYNTAX TruthValue
            MAX-ACCESS read-create
            STATUS current
            DESCRIPTION
                "This object specifies if a vdslInitFailureNotification
                notification will be generated if an initialization
                failure occurs."
            DEFVAL { false }
            ::= { zhoneVdslLineAlarmConfProfileEntry 9 }


--  1.3.6.1.4.1.5504.5.13.1.1.20.1.10
        -- 1.3.6.1.4.1.5504.5.13.1.1.20.1.10
        zhoneVdslLineAlarmConfProfRowStatus OBJECT-TYPE
            SYNTAX RowStatus
            MAX-ACCESS read-create
            STATUS current
            DESCRIPTION
                "This object is used to create a new row or modify or
                delete an existing row in this table.

                A profile activated by setting this object to 'active'.
                When 'active' is set, the system will validate the profile.

                Before a profile can be deleted or taken out of service,
                (by setting this object to 'destroy' or 'outOfService') it
                must be first unreferenced from all associated lines.

                An 'active' profile may be modified at any time."
            ::= { zhoneVdslLineAlarmConfProfileEntry 10 }


        -- 1.3.6.1.4.1.5504.5.13.1.1.20.1.11
        zhoneVdslLineAlarmConfThresh1DayLofs OBJECT-TYPE
            SYNTAX INTEGER (0..86400)
            MAX-ACCESS read-create
            STATUS current
            DESCRIPTION
                "This object configures the threshold for the number of loss
                of frame seconds (LOFs) within any given 1-day performance
                data collection interval.  If the value of loss of frame
                seconds in a particular 1-day collection interval reaches/exceeds
                this value, a zhoneVdslPerfLofsThreshNotification notification
                will be generated.  No more than one notification will be sent
                per interval"
            ::= { zhoneVdslLineAlarmConfProfileEntry 11 }


        -- 1.3.6.1.4.1.5504.5.13.1.1.20.1.12
        zhoneVdslLineAlarmConfThresh1DayLoss OBJECT-TYPE
            SYNTAX INTEGER (0..86400)
            MAX-ACCESS read-create
            STATUS current
            DESCRIPTION
                "This object configures the threshold for the number of loss
                of signal seconds (LOSs) within any given 1-day performance
                data collection interval.  If the value of loss of signal
                seconds in a particular 1-day collection interval reaches/exceeds
                this value, a zhoneVdslPerfLossThreshNotification notification
                will be generated.  No more than one notification will be sent
                per interval"
            ::= { zhoneVdslLineAlarmConfProfileEntry 12 }


        -- 1.3.6.1.4.1.5504.5.13.1.1.20.1.13
        zhoneVdslLineAlarmConfThresh1DayLprs OBJECT-TYPE
            SYNTAX INTEGER (0..86400)
            MAX-ACCESS read-create
            STATUS current
            DESCRIPTION
                "This object configures the threshold for the number of loss
                of power seconds (LPRs) within any given 1-day performance
                data collection interval.  If the value of loss of power
                seconds in a particular 1-day collection interval reaches/exceeds
                this value, a zhoneVdslPerfLprsThreshNotification notification
                will be generated.  No more than one notification will be sent
                per interval"
            ::= { zhoneVdslLineAlarmConfProfileEntry 13 }


        -- 1.3.6.1.4.1.5504.5.13.1.1.20.1.14
        zhoneVdslLineAlarmConfThresh1DayLols OBJECT-TYPE
            SYNTAX INTEGER (0..86400)
            MAX-ACCESS read-create
            STATUS current
            DESCRIPTION
                "This object configures the threshold for the number of loss
                of link seconds (LOLs) within any given 1-day performance
                data collection interval.  If the value of loss of link
                seconds in a particular 1-day collection interval reaches/exceeds
                this value, a zhoneVdslPerfLolsThreshNotification notification
                will be generated.  No more than one notification will be sent
                per interval"
            ::= { zhoneVdslLineAlarmConfProfileEntry 14 }


        -- 1.3.6.1.4.1.5504.5.13.1.1.20.1.15
        zhoneVdslLineAlarmConfThresh1DayESs OBJECT-TYPE
            SYNTAX INTEGER (0..86400)
            MAX-ACCESS read-create
            STATUS current
            DESCRIPTION
                "This object configures the threshold for the number of errored
                seconds (ESs) within any given 1-day performance
                data collection interval.  If the value of errored seconds in
                a particular 1-day collection interval reaches/exceeds
                this value, a zhoneVdslPerfEssThreshNotification notification
                will be generated.  No more than one notification will be sent
                per interval"
            ::= { zhoneVdslLineAlarmConfProfileEntry 15 }


        -- 1.3.6.1.4.1.5504.5.13.1.1.20.1.16
        zhoneVdslLineAlarmConfThresh1DaySESs OBJECT-TYPE
            SYNTAX INTEGER (0..86400)
            MAX-ACCESS read-create
            STATUS current
            DESCRIPTION
                "This object configures the threshold for the number of severely
                errored seconds (SESs) within any given 1-day performance
                data collection interval.  If the value of severely errored
                seconds in a particular 1-day collection interval reaches/exceeds
                this value, a zhoneVdslPerfSessThreshNotification notification
                will be generated.  No more than one notification will be sent
                per interval"
            ::= { zhoneVdslLineAlarmConfProfileEntry 16 }


        -- 1.3.6.1.4.1.5504.5.13.1.1.20.1.17
        zhoneVdslLineAlarmConfThresh1DayUASs OBJECT-TYPE
            SYNTAX INTEGER (0..86400)
            MAX-ACCESS read-create
            STATUS current
            DESCRIPTION
                "This object configures the threshold for the number of
                unavailable seconds (UASs) within any given 1-day performance
                data collection interval.  If the value of unavailable seconds
                in a particular 1-day collection interval reaches/exceeds this
                value, a zhoneVdslPerfUasThreshNotification notification will
                be generated.  No more than one notification will be sent
                per interval"
            ::= { zhoneVdslLineAlarmConfProfileEntry 17 }


        -- 1.3.6.1.4.1.5504.5.13.1.1.20.1.18
        zhoneVdslLineAlarmConfThresh1DayInitFailure OBJECT-TYPE
            SYNTAX TruthValue
            MAX-ACCESS read-create
            STATUS current
            DESCRIPTION
                "This object specifies if a vdslThresh1DayInitFailureNotification
                notification will be generated if an initialization
                failure occurs."
            DEFVAL { false }
            ::= { zhoneVdslLineAlarmConfProfileEntry 18 }


        -- 1.3.6.1.4.1.5504.5.13.1.1.21
        zhoneVdslCustomNotchConfProfileTable OBJECT-TYPE
            SYNTAX SEQUENCE OF ZhoneVdslCustomNotchConfProfileEntry
            MAX-ACCESS not-accessible
            STATUS current
            DESCRIPTION
                "This table contains HAM (Handheld Amateur
                Radio) custom notch information."
            ::= { zhoneVdslMibObjects 21 }


        -- 1.3.6.1.4.1.5504.5.13.1.1.21.1
        zhoneVdslCustomNotchConfProfileEntry OBJECT-TYPE
            SYNTAX ZhoneVdslCustomNotchConfProfileEntry
            MAX-ACCESS not-accessible
            STATUS current
            DESCRIPTION
                "Each VDSL port can have custom notches."
            INDEX { ifIndex, zhoneVdslCustomNotchConfId }
            ::= { zhoneVdslCustomNotchConfProfileTable 1 }


        ZhoneVdslCustomNotchConfProfileEntry ::=
            SEQUENCE {
                zhoneVdslCustomNotchConfId
                    Unsigned32,
                zhoneVdslCustomNotchConfStart
                    Unsigned32,
                zhoneVdslCustomNotchConfStop
                    Unsigned32
             }

        -- 1.3.6.1.4.1.5504.5.13.1.1.21.1.1
        zhoneVdslCustomNotchConfId OBJECT-TYPE
            SYNTAX Unsigned32 (1..8)
            MAX-ACCESS read-create
            STATUS current
            DESCRIPTION
                "Each VDSL2 port can have eight (8) custom
                notch pairs."
            ::= { zhoneVdslCustomNotchConfProfileEntry 1 }


        -- 1.3.6.1.4.1.5504.5.13.1.1.21.1.2
        zhoneVdslCustomNotchConfStart OBJECT-TYPE
            SYNTAX Unsigned32 (0..200000)
            UNITS "kHz"
            MAX-ACCESS read-create
            STATUS current
            DESCRIPTION
                "Specifies the start frequency of custom HAM (Handheld
                Amateur Radio) notch.  zhoneVdslCustomNotchConfStart MUST
                be less than or equal to zhoneVdslCustomNotchConfStop."
            ::= { zhoneVdslCustomNotchConfProfileEntry 2 }


        -- 1.3.6.1.4.1.5504.5.13.1.1.21.1.3
        zhoneVdslCustomNotchConfStop OBJECT-TYPE
            SYNTAX Unsigned32 (0..200000)
            UNITS "kHz"
            MAX-ACCESS read-create
            STATUS current
            DESCRIPTION
                "Specifies the end frequency of custom HAM (Handheld
                Amateur Radio) notch.  zhoneVdslCustomNotchConfStop MUST
                be greater than or equal to zhoneVdslCustomNotchConfStart."
            ::= { zhoneVdslCustomNotchConfProfileEntry 3 }


        -- 1.3.6.1.4.1.5504.5.13.1.1.22
        zhoneVdslVectDataTable OBJECT-TYPE
            SYNTAX SEQUENCE OF ZhoneVdslVectDataEntry
            MAX-ACCESS not-accessible
            STATUS current
            DESCRIPTION
                "Used to retrieve the vectoring packet counts."
            ::= { zhoneVdslMibObjects 22 }


        -- 1.3.6.1.4.1.5504.5.13.1.1.22.1
        zhoneVdslVectDataEntry OBJECT-TYPE
            SYNTAX ZhoneVdslVectDataEntry
            MAX-ACCESS not-accessible
            STATUS current
            DESCRIPTION
                "Vectoring Packet statistics data"
            INDEX { ifIndex }
            ::= { zhoneVdslVectDataTable 1 }


        ZhoneVdslVectDataEntry ::=
            SEQUENCE {
                zhoneVdslVectDataEsDsCounter
                    Integer32,
                zhoneVdslVectDataEsUsCounter
                    Integer32,
                zhoneVdslVectDataIsDsFeValid
                    Integer32,
                zhoneVdslVectDataEsFeDsCounter
                    Integer32
             }

        -- 1.3.6.1.4.1.5504.5.13.1.1.22.1.1
        zhoneVdslVectDataEsDsCounter OBJECT-TYPE
            SYNTAX Integer32
            MAX-ACCESS read-only
            STATUS current
            DESCRIPTION
                "Error Sample Downstream Packet Counter"
            DEFVAL { 0 }
            ::= { zhoneVdslVectDataEntry 1 }


        -- 1.3.6.1.4.1.5504.5.13.1.1.22.1.2
        zhoneVdslVectDataEsUsCounter OBJECT-TYPE
            SYNTAX Integer32
            MAX-ACCESS read-only
            STATUS current
            DESCRIPTION
                "Error Sample Upstream Packet Counter"
            ::= { zhoneVdslVectDataEntry 2 }


        -- 1.3.6.1.4.1.5504.5.13.1.1.22.1.3
        zhoneVdslVectDataIsDsFeValid OBJECT-TYPE
            SYNTAX Integer32
            MAX-ACCESS read-only
            STATUS current
            DESCRIPTION
                "Is Downstream Fe Valid"
            ::= { zhoneVdslVectDataEntry 3 }


        -- 1.3.6.1.4.1.5504.5.13.1.1.22.1.4
        zhoneVdslVectDataEsFeDsCounter OBJECT-TYPE
            SYNTAX Integer32
            MAX-ACCESS read-only
            STATUS current
            DESCRIPTION
                "Error Sample Fe Downstream Counter"
            ::= { zhoneVdslVectDataEntry 4 }


--   conformance information
-- 1.3.6.1.4.1.5504.5.13.1.3
        -- 1.3.6.1.4.1.5504.5.13.1.3
        zhoneVdslConformance OBJECT IDENTIFIER ::= { zhoneVdslLineMib 3 }


--  1.3.6.1.4.1.5504.5.13.1.3.1
        -- 1.3.6.1.4.1.5504.5.13.1.3.1
        zhoneVdslGroups OBJECT IDENTIFIER ::= { zhoneVdslConformance 1 }


--   units of conformance
-- 1.3.6.1.4.1.5504.5.13.1.3.1.1
        -- 1.3.6.1.4.1.5504.5.13.1.3.1.1
        zhoneVdslGroup OBJECT-GROUP
            OBJECTS { zhoneVdslLineCoding, zhoneVdslLineType, zhoneVdslLineConfProfile, zhoneVdslLineAlarmConfProfile, zhoneVdslPhysInvSerialNumber,
                zhoneVdslPhysInvVendorID, zhoneVdslPhysInvVersionNumber, zhoneVdslPhysCurrSnrMgn, zhoneVdslPhysCurrAtn, zhoneVdslPhysCurrStatus,
                zhoneVdslPhysCurrOutputPwr, zhoneVdslPhysCurrAttainableRate, zhoneVdslPhysCurrLineRate, zhoneVdslChanInterleaveDelay, zhoneVdslChanCrcBlockLength,
                zhoneVdslChanCurrTxRate, zhoneVdslChanCurrTxSlowBurstProtect, zhoneVdslChanCurrTxFastFec, zhoneVdslPerfDataValidIntervals, zhoneVdslPerfDataInvalidIntervals,
                zhoneVdslPerfDataLofs, zhoneVdslPerfDataLoss, zhoneVdslPerfDataLprs, zhoneVdslPerfDataLols, zhoneVdslPerfDataESs,
                zhoneVdslPerfDataSESs, zhoneVdslPerfDataUASs, zhoneVdslPerfDataInits, zhoneVdslPerfDataCurr15MinTimeElapsed, zhoneVdslPerfDataCurr15MinLofs,
                zhoneVdslPerfDataCurr15MinLoss, zhoneVdslPerfDataCurr15MinLprs, zhoneVdslPerfDataCurr15MinLols, zhoneVdslPerfDataCurr15MinESs, zhoneVdslPerfDataCurr15MinSESs,
                zhoneVdslPerfDataCurr15MinUASs, zhoneVdslPerfDataCurr15MinInits, zhoneVdslPerfData1DayValidIntervals, zhoneVdslPerfData1DayInvalidIntervals, zhoneVdslPerfDataCurr1DayTimeElapsed,
                zhoneVdslPerfDataCurr1DayLofs, zhoneVdslPerfDataCurr1DayLoss, zhoneVdslPerfDataCurr1DayLprs, zhoneVdslPerfDataCurr1DayLols, zhoneVdslPerfDataCurr1DayESs,
                zhoneVdslPerfDataCurr1DaySESs, zhoneVdslPerfDataCurr1DayUASs, zhoneVdslPerfDataCurr1DayInits, zhoneVdslPerfIntervalLofs, zhoneVdslPerfIntervalLoss,
                zhoneVdslPerfIntervalLprs, zhoneVdslPerfIntervalLols, zhoneVdslPerfIntervalESs, zhoneVdslPerfIntervalSESs, zhoneVdslPerfIntervalUASs,
                zhoneVdslPerfIntervalInits, zhoneVdslPerf1DayIntervalMoniSecs, zhoneVdslPerf1DayIntervalLofs, zhoneVdslPerf1DayIntervalLoss, zhoneVdslPerf1DayIntervalLprs,
                zhoneVdslPerf1DayIntervalLols, zhoneVdslPerf1DayIntervalESs, zhoneVdslPerf1DayIntervalSESs, zhoneVdslPerf1DayIntervalUASs, zhoneVdslPerf1DayIntervalInits,
                zhoneVdslChanValidIntervals, zhoneVdslChanInvalidIntervals, zhoneVdslChanFixedOctets, zhoneVdslChanBadBlks, zhoneVdslChanCurr15MinTimeElapsed,
                zhoneVdslChanCurr15MinFixedOctets, zhoneVdslChanCurr15MinBadBlks, zhoneVdslChan1DayValidIntervals, zhoneVdslChan1DayInvalidIntervals, zhoneVdslChanCurr1DayTimeElapsed,
                zhoneVdslChanCurr1DayFixedOctets, zhoneVdslChanCurr1DayBadBlks, zhoneVdslChanIntervalFixedOctets, zhoneVdslChanIntervalBadBlks, zhoneVdslChan1DayIntervalMoniSecs,
                zhoneVdslChan1DayIntervalFixedOctets, zhoneVdslChan1DayIntervalBadBlks, zhoneVdslLineConfDownRateMode, zhoneVdslLineConfUpRateMode, zhoneVdslLineConfDownMaxPwr,
                zhoneVdslLineConfUpMaxPwr, zhoneVdslLineConfDownMaxSnrMgn, zhoneVdslLineConfDownMinSnrMgn, zhoneVdslLineConfDownTargetSnrMgn, zhoneVdslLineConfUpMaxSnrMgn,
                zhoneVdslLineConfUpMinSnrMgn, zhoneVdslLineConfUpTargetSnrMgn, zhoneVdslLineConfDownFastMaxDataRate, zhoneVdslLineConfDownFastMinDataRate, zhoneVdslLineConfDownSlowMaxDataRate,
                zhoneVdslLineConfDownSlowMinDataRate, zhoneVdslLineConfUpFastMaxDataRate, zhoneVdslLineConfUpFastMinDataRate, zhoneVdslLineConfUpSlowMaxDataRate, zhoneVdslLineConfUpSlowMinDataRate,
                zhoneVdslLineConfDownRateRatio, zhoneVdslLineConfUpRateRatio, zhoneVdslLineConfDownMaxInterDelay, zhoneVdslLineConfUpMaxInterDelay, zhoneVdslLineConfDownPboControl,
                zhoneVdslLineConfUpPboControl, zhoneVdslLineConfDownPboLevel, zhoneVdslLineConfUpPboLevel, zhoneVdslLineConfDeploymentScenario, zhoneVdslLineConfAdslPresence,
                zhoneVdslLineConfApplicableStandard, zhoneVdslLineConfBandPlan, zhoneVdslLineConfBandPlanFx, zhoneVdslLineConfBandOptUsage, zhoneVdslLineConfUpPsdTemplate,
                zhoneVdslLineConfDownPsdTemplate, zhoneVdslLineConfHamBandMask, zhoneVdslLineConfCustomNotch1Start, zhoneVdslLineConfCustomNotch1Stop, zhoneVdslLineConfCustomNotch2Start,
                zhoneVdslLineConfCustomNotch2Stop, zhoneVdslLineConfDownTargetSlowBurst, zhoneVdslLineConfUpTargetSlowBurst, zhoneVdslLineConfDownMaxFastFec, zhoneVdslLineConfUpMaxFastFec,
                zhoneVdslLineConfLineType, zhoneVdslLineConfProfRowStatus, zhoneVdslLineAlarmConfThresh15MinLofs, zhoneVdslLineAlarmConfThresh15MinLoss, zhoneVdslLineAlarmConfThresh15MinLprs,
                zhoneVdslLineAlarmConfThresh15MinLols, zhoneVdslLineAlarmConfThresh15MinESs, zhoneVdslLineAlarmConfThresh15MinSESs, zhoneVdslLineAlarmConfThresh15MinUASs, zhoneVdslLineAlarmConfInitFailure,
                zhoneVdslLineAlarmConfThresh1DayLofs, zhoneVdslLineAlarmConfThresh1DayLoss, zhoneVdslLineAlarmConfThresh1DayLprs, zhoneVdslLineAlarmConfThresh1DayLols, zhoneVdslLineAlarmConfThresh1DayInitFailure,
                zhoneVdslLineConfAutoModeCrtrn, zhoneVdslLineConfAdslBandMode, zhoneVdslLineConfAdslBandModeEndFreq, zhoneVdslLineConfSeltAgc, zhoneVdslLineConfVdsl2Profile,
                zhoneVdslLineConfVdslMode, zhoneVdslLineConfPboElectricalOverride, zhoneVdslLineConfDownMaxPsd, zhoneVdslLineConfDownMaxAggregateTxPwr, zhoneVdslLineConfDownPsdShape,
                zhoneVdslLineConfDownVirtualNoiseSnrMode, zhoneVdslLineConfDownGhsA43TonePwr, zhoneVdslLineConfDownErasureDetectionFast, zhoneVdslLineConfDownErasureDetectionInterleave, zhoneVdslLineConfDownGhsB43TonePwr,
                zhoneVdslLineConfDownGhsV43TonePwr, zhoneVdslLineConfDownGhsA43TonePwrMaxLvl, zhoneVdslLineConfDownGhsA43cTonePwrMaxLvl, zhoneVdslLineConfDownGhsB43TonePwrMaxLvl, zhoneVdslLineConfDownGhsV43TonePwrMaxLvl,
                zhoneVdslLineConfDownRsCoding, zhoneVdslLineAlarmConfProfRowStatus, zhoneVdslLineConfUpErasureDetectionFast, zhoneVdslLineConfUpPboPsdParamB1, zhoneVdslLineConfUpPboPsdParamA1,
                zhoneVdslLineConfUpPboPsdParamA2, zhoneVdslLineConfUpPboPsdParamB2, zhoneVdslLineConfUpVirtualNoiseSnrMode, zhoneVdslLineConfUpErasureDetectionInterleave, zhoneVdslLineConfUpRsCoding,
                zhoneVdslLineConfUpPsdShape, zhoneVdslLineConfUpPboPsdTemplate, zhoneVdslLineConfNetworkTimingRef, zhoneVdslLineConfUpMaxAggregateTxPwr, zhoneVdslLineConfDownTrellis,
                zhoneVdslLineConfUpTrellis, zhoneVdslLineConfUpMaxPsd, zhoneVdslLineAlarmConfThresh1DayESs, zhoneVdslLineAlarmConfThresh1DaySESs, zhoneVdslLineAlarmConfThresh1DayUASs,
                zhoneVdslLineConfSeltEchoMeasurementTime, zhoneVdslCustomNotchConfStop, zhoneVdslLineConfSeltNoiseMeasurementTime, zhoneVdslCustomNotchConfStart, zhoneVdslLineConfTransmissionMode,
                zhoneVdslLineConfDownDownshiftSnrMgn, zhoneVdslLineConfDownUpshiftSnrMgn, zhoneVdslLineConfDownMinDownshiftTime, zhoneVdslLineConfDownMinUpshiftTime, zhoneVdslLineConfUpDownshiftSnrMgn,
                zhoneVdslLineConfUpUpshiftSnrMgn, zhoneVdslLineConfUpMinDownshiftTime, zhoneVdslLineConfUpMinUpshiftTime, zhoneVdslCustomNotchConfId, zhoneVdslLineConfDownGhsA43cTonePwr,
                zhoneVdslLineConfDMTConfMode, zhoneVdslLineConfPotsBypassRelayMaxDuration, zhoneVdslLineConfDownBitSwap, zhoneVdslLineConfUpBitSwap, zhoneVdslLineConfAdslAnnexMModeEnabled,
                zhoneVdslLineConfAdslAnnexMPsdMask, zhoneVdslLineConfUs0BoundaryTone, zhoneVdslLineConfDownInp, zhoneVdslLineConfUpInp, zhoneVdslLineConfDownMaxInterleavingDelay,
                zhoneVdslLineConfUpMaxInterleavingDelay, zhoneVdslLineConfDownPsdMaskEnable, zhoneVdslLineConfUpPsdMaskEnable, zhoneVdslLineConfDownPsdMaskSelect, zhoneVdslLineConfUpPsdMaskSelect,
                zhoneVdslPhysCurrProfile, zhoneVdslPhysCurrConnType, zhoneVdslLineEnableTrellisCoding, zhoneVdslLineEnableRsCoding, zhoneVdslLineConfPsdShape,
                zhoneVdslLineConfDownPhyRSupport, zhoneVdslLineConfUpPhyRSupport, zhoneVdslLineConfDownPhyRmaxINP, zhoneVdslLineConfUpPhyRmaxINP, zhoneVdslLineConfDownPhyRminRSoverhead,
                zhoneVdslLineConfUpPhyRminRSoverhead, zhoneVdslLineConfDownPhyRRtxRatio, zhoneVdslLineConfUpPhyRRtxRatio, zhoneVdslLineConfUpPboPsdParamA3, zhoneVdslLineConfUpPboPsdParamA4,
                zhoneVdslLineConfUpPboPsdParamB3, zhoneVdslLineConfUpPboPsdParamB4, zhoneVdslLineConfFallbackDefaultVpi, zhoneVdslLineConfFallbackDefaultVci, zhoneVdslLineConfUpMinTxThresholdAlarm,
                zhoneVdslLineConfDownMinTxThresholdAlarm }
            STATUS current
            DESCRIPTION
                "A collection of objects providing information about
                a VDSL Line."
            ::= { zhoneVdslGroups 1 }


--  1.3.6.1.4.1.5504.5.13.1.3.1.2
        -- 1.3.6.1.4.1.5504.5.13.1.3.1.2
        zhoneVdslNotificationGroup NOTIFICATION-GROUP
            NOTIFICATIONS { vdslXtucPerf15MinLofsThreshTrap, vdslXtucPerf15MinLossThreshTrap, vdslXtucPerf15MinLprsThreshTrap, vdslXtucPerf15MinLolsThreshTrap, vdslXtucPerf15MinESsThreshTrap,
                vdslXtucPerf15MinSESsThreshTrap, vdslXtucPerf15MinUASsThreshTrap, vdslXtucPerf1DayLofsThreshTrap, vdslXtucPerf1DayLossThreshTrap, vdslXtucPerf1DayLprsThreshTrap,
                vdslXtucPerf1DayLolsThreshTrap, vdslXtucPerf1DayESsThreshTrap, vdslXtucPerf1DaySESsThreshTrap, vdslXtucPerf1DayUASsThreshTrap, zhoneVdslInitFailureTrap,
                vdslXtucMinTxThresholdAlarmFailureTrap, vdslXturMinTxThresholdAlarmFailureTrap }
            STATUS current
            DESCRIPTION
                "This group supports notifications of significant
                conditions associated with VDSL Lines."
            ::= { zhoneVdslGroups 2 }


--  1.3.6.1.4.1.5504.5.13.1.3.2
        -- 1.3.6.1.4.1.5504.5.13.1.3.2
        zhoneVdslCompliances OBJECT IDENTIFIER ::= { zhoneVdslConformance 2 }


--   this module
-- 1.3.6.1.4.1.5504.5.13.1.3.2.1
-- this module
        -- 1.3.6.1.4.1.5504.5.13.1.3.2.1
        zhoneVdslLineMibCompliance MODULE-COMPLIANCE
            STATUS current
            DESCRIPTION
                "The compliance statement for SNMP entities which
                manage VDSL interfaces."
            MODULE -- this module
                MANDATORY-GROUPS { zhoneVdslGroup, zhoneVdslNotificationGroup }
            ::= { zhoneVdslCompliances 1 }



    END

--
-- phyVdsl.mib
--
