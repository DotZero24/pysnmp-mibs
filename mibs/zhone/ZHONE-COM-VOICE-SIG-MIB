--
-- comVoiceSignaling.mib
-- MIB generated by MG-SOFT Visual MIB Builder Version 3.0 Build 285
-- Friday, October 22, 2004 at 13:04:47
--

	ZHONE-COM-VOICE-SIG-MIB DEFINITIONS ::= BEGIN

		IMPORTS
			OBJECT-GROUP
				FROM SNMPv2-CONF
			Integer32, Unsigned32, OBJECT-TYPE, MODULE-IDENTITY, OBJECT-IDENTITY
				FROM SNMPv2-SMI
			TruthValue
				FROM SNMPv2-TC
			zhoneVoice
				FROM Zhone;


-- Parser and mibcomp commands:
-- /vob/zhonetools/bin/pahrser.pl rfc2233.mib Zhone.mib
--        comVoiceSignaling.mib
-- /vob/EPILOGUE/binaries/emissary/solaris/mibcomp rfc1907.mib
--        iftype.mib rfc2233.mib Zhone.mib -stub -o
--        voiceSystemProfileHdlrs.c comVoiceSignaling.mib
--
--
		-- 1.3.6.1.4.1.5504.4.3.7
		zhoneVoiceSignalingMib MODULE-IDENTITY
			LAST-UPDATED "200410211453Z"		-- October 21, 2004 at 14:53 GMT
			ORGANIZATION
				"Zhone Technologies."
			CONTACT-INFO
				"   Postal:
				           Zhone Technologies, Inc.
				           @ Zhone Way
				           7001 Oakport Street
				           Oakland, CA  94621
				           USA
				Toll-Free: +1 877-ZHONE20 (+1 877-946-6320)
				      Tel: +1-510-777-7000
				      Fax: +1-510-777-7001
				   E-mail: support@zhone.com"
			DESCRIPTION
				"The Zhone Voice Signaling MIB defines Zhone Voice Signaling specfic
				information.

				This MIB contains system side voice specific info, like the
				hookflash timers.

				User will not create this profile, but when system comes up, it checks
				to see if the scalar info exists.  If not, it creates one with
				default values."
			REVISION "200410211451Z"		-- October 21, 2004 at 14:51 GMT
			DESCRIPTION
				"V01.00.01 - Added endpoint specific object to voice-system"
			REVISION "200010101805Z"		-- October 10, 2000 at 18:05 GMT
			DESCRIPTION
				"V01.00.00 - Initial Release"
			::= { zhoneVoice 7 }




--
-- Node definitions
--

		-- 1.3.6.1.4.1.5504.4.3.7.1
		zhoneVoiceSignalingTimers OBJECT-IDENTITY
			STATUS current
			DESCRIPTION
				"This is a place holder to contain all the system wide voice specific
				timers.

				'hookFlashTimerMin' field is read/write field so a user can set this
				field to a particular value.  It specifies the minimum timer for
				hookflash.

				'hookFlashTimerMax' field is a read/write field to a user can set this
				field to a particular value.  It specifies the maximum timer for
				hookflash."
			::= { zhoneVoiceSignalingMib 1 }


		-- 1.3.6.1.4.1.5504.4.3.7.1.1
		hookFlashTimerMin OBJECT-TYPE
			SYNTAX Integer32 (0..2147483647)
			MAX-ACCESS read-write
			STATUS current
			DESCRIPTION
				"The Hookflash specifies the minimum timer that qualifies for a
				hookflash.  Any loopopen below this time will be ignored as a
				glitch."
			DEFVAL { 100 }
			::= { zhoneVoiceSignalingTimers 1 }


		-- 1.3.6.1.4.1.5504.4.3.7.1.2
		hookFlashTimerMax OBJECT-TYPE
			SYNTAX Integer32 (0..2147483647)
			MAX-ACCESS read-write
			STATUS current
			DESCRIPTION
				"The Hookflash specifies the maximum timer that qualifies for a
				hookflash.  Any loopopen more than this timer will be considered
				as a onhook."
			DEFVAL { 1550 }
			::= { zhoneVoiceSignalingTimers 2 }


		-- 1.3.6.1.4.1.5504.4.3.7.1.3
		sysPartialDialTo OBJECT-TYPE
			SYNTAX Unsigned32
			UNITS "seconds"
			MAX-ACCESS read-write
			STATUS current
			DESCRIPTION
				"This object contains the maximum value of the partial dial
				time out."
			DEFVAL { 16 }
			::= { zhoneVoiceSignalingTimers 3 }


		-- 1.3.6.1.4.1.5504.4.3.7.1.4
		sysCriticalDialTo OBJECT-TYPE
			SYNTAX Unsigned32
			UNITS "seconds"
			MAX-ACCESS read-write
			STATUS current
			DESCRIPTION
				"This object contains the maximum value of the critical \
				dial time out."
			DEFVAL { 4 }
			::= { zhoneVoiceSignalingTimers 4 }


		-- 1.3.6.1.4.1.5504.4.3.7.1.5
		sysBusyToneTo OBJECT-TYPE
			SYNTAX Unsigned32
			UNITS "seconds"
			MAX-ACCESS read-write
			STATUS current
			DESCRIPTION
				"This object contains the default timeout value for
				busy tone."
			DEFVAL { 30 }
			::= { zhoneVoiceSignalingTimers 5 }


		-- 1.3.6.1.4.1.5504.4.3.7.1.6
		sysDialToneTo OBJECT-TYPE
			SYNTAX Unsigned32
			UNITS "seconds"
			MAX-ACCESS read-write
			STATUS current
			DESCRIPTION
				"This object contains the default timeout value for
				dial tone. "
			DEFVAL { 16 }
			::= { zhoneVoiceSignalingTimers 6 }


		-- 1.3.6.1.4.1.5504.4.3.7.1.7
		sysMsgWaitToneTo OBJECT-TYPE
			SYNTAX Unsigned32
			UNITS "seconds"
			MAX-ACCESS read-write
			STATUS current
			DESCRIPTION
				"This object contains the default timeout value for
				message wait tone. "
			DEFVAL { 16 }
			::= { zhoneVoiceSignalingTimers 7 }


		-- 1.3.6.1.4.1.5504.4.3.7.1.8
		sysOffhookWarnToneTo OBJECT-TYPE
			SYNTAX Unsigned32
			UNITS "seconds"
			MAX-ACCESS read-write
			STATUS current
			DESCRIPTION
				"This object contains the default timeout value for
				offhook warn tone. "
			DEFVAL { 0 }
			::= { zhoneVoiceSignalingTimers 8 }


		-- 1.3.6.1.4.1.5504.4.3.7.1.9
		sysRingingTo OBJECT-TYPE
			SYNTAX Unsigned32
			UNITS "seconds"
			MAX-ACCESS read-write
			STATUS current
			DESCRIPTION
				"This object contains the default timeout value for
				ringing. "
			DEFVAL { 180 }
			::= { zhoneVoiceSignalingTimers 9 }


		-- 1.3.6.1.4.1.5504.4.3.7.1.10
		sysRingbackTo OBJECT-TYPE
			SYNTAX Unsigned32
			UNITS "seconds"
			MAX-ACCESS read-write
			STATUS current
			DESCRIPTION
				"This object contains the default timeout value for
				ringback tone."
			DEFVAL { 180 }
			::= { zhoneVoiceSignalingTimers 10 }


		-- 1.3.6.1.4.1.5504.4.3.7.1.11
		sysReorderToneTo OBJECT-TYPE
			SYNTAX Unsigned32
			UNITS "seconds"
			MAX-ACCESS read-write
			STATUS current
			DESCRIPTION
				"This object contains the default timeout value for
				reorder tone."
			DEFVAL { 30 }
			::= { zhoneVoiceSignalingTimers 11 }


		-- 1.3.6.1.4.1.5504.4.3.7.1.12
		sysStutterToneTo OBJECT-TYPE
			SYNTAX Unsigned32
			UNITS "seconds"
			MAX-ACCESS read-write
			STATUS current
			DESCRIPTION
				"This object contains the default timeout value for
				stutter tone."
			DEFVAL { 16 }
			::= { zhoneVoiceSignalingTimers 12 }


		-- 1.3.6.1.4.1.5504.4.3.7.1.13
		sysServerMaxTimer OBJECT-TYPE
			SYNTAX Unsigned32
			MAX-ACCESS read-write
			STATUS current
			DESCRIPTION
				"This object is used as part of a retransmission
				algorithm when communicating with a call agent.
				This object contains the maximum time in seconds
				since the sending of the initial datagram to a
				call agent. If more than pktcNcsEndPntConfigTSMax
				time has elapsed, the endpoint becomes disconnected."
			DEFVAL { 20 }
			::= { zhoneVoiceSignalingTimers 13 }


		-- 1.3.6.1.4.1.5504.4.3.7.1.14
		sysConfigMax1 OBJECT-TYPE
			SYNTAX Unsigned32
			MAX-ACCESS read-write
			STATUS current
			DESCRIPTION
				"This object contains the suspicious error threshold
				for signaling messages. The configMax1 object
				indicates the retransmission threshold at which
				the gateway MAY actively query the domain name server
				(DNS) in order to detect the possible change of
				call agent interfaces."
			DEFVAL { 5 }
			::= { zhoneVoiceSignalingTimers 14 }


		-- 1.3.6.1.4.1.5504.4.3.7.1.15
		sysConfigMax2 OBJECT-TYPE
			SYNTAX Unsigned32
			MAX-ACCESS read-write
			STATUS current
			DESCRIPTION
				"This object contains the disconnect error threshold
				for signaling messages. The configMax2 object
				indicates the retransmission threshold at which
				the gateway SHOULD contact the DNS one more time
				to see if any other interfaces to the call agent
				have become available."
			DEFVAL { 7 }
			::= { zhoneVoiceSignalingTimers 15 }


		-- 1.3.6.1.4.1.5504.4.3.7.1.16
		sysMax1Enable OBJECT-TYPE
			SYNTAX TruthValue
			MAX-ACCESS read-write
			STATUS current
			DESCRIPTION
				"This object enables/disables the Max1 domain name
				server (DNS) query operation when the configMax1
				threshold has been reached."
			DEFVAL { true }
			::= { zhoneVoiceSignalingTimers 16 }


		-- 1.3.6.1.4.1.5504.4.3.7.1.17
		sysMax2Enable OBJECT-TYPE
			SYNTAX TruthValue
			MAX-ACCESS read-write
			STATUS current
			DESCRIPTION
				"This object enables/disables the Max2 domain name
				server (DNS) query operation when the configMax2
				threshold has been reached."
			DEFVAL { true }
			::= { zhoneVoiceSignalingTimers 17 }


		-- 1.3.6.1.4.1.5504.4.3.7.1.18
		sysMaxWaitingDelay OBJECT-TYPE
			SYNTAX Unsigned32
			UNITS "seconds"
			MAX-ACCESS read-write
			STATUS current
			DESCRIPTION
				"Maximum Waiting Delay (MWD) contains the maximum
				number of seconds a Gateway waits after powering
				on, before initiating the restart procedure with
				the call agent."
			DEFVAL { 600 }
			::= { zhoneVoiceSignalingTimers 18 }


		-- 1.3.6.1.4.1.5504.4.3.7.1.19
		sysDisconnectWaitTimer OBJECT-TYPE
			SYNTAX Unsigned32
			UNITS "seconds"
			MAX-ACCESS read-write
			STATUS current
			DESCRIPTION
				"This object contains the initial number of seconds
				the gateway waits after a disconnect, before
				initiating the disconnected procedure with the
				call agent."
			DEFVAL { 15 }
			::= { zhoneVoiceSignalingTimers 19 }


		-- 1.3.6.1.4.1.5504.4.3.7.1.20
		sysDisconnectMinTimer OBJECT-TYPE
			SYNTAX Unsigned32
			UNITS "seconds"
			MAX-ACCESS read-write
			STATUS current
			DESCRIPTION
				"This object contains the minimum number of seconds
				the gatway waits after a disconnect, before
				initiating the disconnected procedure with the
				call agent."
			DEFVAL { 15 }
			::= { zhoneVoiceSignalingTimers 20 }


		-- 1.3.6.1.4.1.5504.4.3.7.1.21
		sysDisconnectMaxTimer OBJECT-TYPE
			SYNTAX Unsigned32
			UNITS "seconds"
			MAX-ACCESS read-write
			STATUS current
			DESCRIPTION
				"This object contains the maximum number of seconds
				the gatway waits after a disconnect, before
				initiating the disconnected procedure with the
				call agent."
			DEFVAL { 600 }
			::= { zhoneVoiceSignalingTimers 21 }


		-- 1.3.6.1.4.1.5504.4.3.7.1.22
		sysMaxRetransmitTimer OBJECT-TYPE
			SYNTAX Unsigned32
			UNITS "seconds"
			MAX-ACCESS read-write
			STATUS current
			DESCRIPTION
				"This object contains the maximum number of seconds
				for the retransmission timer. When this timer
				expires the gateway retransmits the message."
			DEFVAL { 4 }
			::= { zhoneVoiceSignalingTimers 22 }


		-- 1.3.6.1.4.1.5504.4.3.7.1.23
		sysInitRetransmitTimer OBJECT-TYPE
			SYNTAX Unsigned32
			UNITS "milliseconds"
			MAX-ACCESS read-write
			STATUS current
			DESCRIPTION
				"This object contains the initial number of seconds
				for the retransmission timer."
			DEFVAL { 200 }
			::= { zhoneVoiceSignalingTimers 23 }


		-- 1.3.6.1.4.1.5504.4.3.7.1.24
		sysKeepAliveTimer OBJECT-TYPE
			SYNTAX Unsigned32
			UNITS "minutes"
			MAX-ACCESS read-write
			STATUS current
			DESCRIPTION
				"Specifies a timeout value in minutes for sending
				long duration call notification message."
			DEFVAL { 60 }
			::= { zhoneVoiceSignalingTimers 24 }


		-- 1.3.6.1.4.1.5504.4.3.7.1.25
		sysNoResponseTimer OBJECT-TYPE
			SYNTAX Unsigned32
			UNITS "seconds"
			MAX-ACCESS read-write
			STATUS current
			DESCRIPTION
				"Timeout period in seconds before no response is declared."
			DEFVAL { 30 }
			::= { zhoneVoiceSignalingTimers 25 }


		-- 1.3.6.1.4.1.5504.4.3.7.1.26
		sysCallWaitMaxRepeat OBJECT-TYPE
			SYNTAX Unsigned32
			MAX-ACCESS read-write
			STATUS current
			DESCRIPTION
				"This object contains the default value of the
				maximum number of repetitions of the call waiting
				tone that the gateway will play."
			DEFVAL { 2 }
			::= { zhoneVoiceSignalingTimers 26 }


		-- 1.3.6.1.4.1.5504.4.3.7.1.27
		sysCallWaitDelay OBJECT-TYPE
			SYNTAX Unsigned32
			UNITS "seconds"
			MAX-ACCESS read-write
			STATUS current
			DESCRIPTION
				"This object contains the delay between repetitions
				of the call waiting tone that the gateway will play."
			DEFVAL { 10 }
			::= { zhoneVoiceSignalingTimers 27 }


		-- 1.3.6.1.4.1.5504.4.3.7.1.28
		sysPulseInterDigitTimer OBJECT-TYPE
			SYNTAX Unsigned32 (100..1500)
			UNITS "milliseconds"
			MAX-ACCESS read-write
			STATUS current
			DESCRIPTION
				"This is the pulse dial inter-digit timeout."
			DEFVAL { 100 }
			::= { zhoneVoiceSignalingTimers 28 }


		-- 1.3.6.1.4.1.5504.4.3.7.1.29
		sysMinMakePulseWidth OBJECT-TYPE
			SYNTAX Unsigned32 (20..200)
			UNITS "milliseconds"
			MAX-ACCESS read-write
			STATUS current
			DESCRIPTION
				"This is the minimum make pulse width for the dial pulse."
			DEFVAL { 25 }
			::= { zhoneVoiceSignalingTimers 29 }


		-- 1.3.6.1.4.1.5504.4.3.7.1.30
		sysMaxMakePulseWidth OBJECT-TYPE
			SYNTAX Unsigned32 (20..200)
			UNITS "milliseconds"
			MAX-ACCESS read-write
			STATUS current
			DESCRIPTION
				"This is the maximum make pulse width for the dial pulse."
			DEFVAL { 55 }
			::= { zhoneVoiceSignalingTimers 30 }


		-- 1.3.6.1.4.1.5504.4.3.7.1.31
		sysMinBreakPulseWidth OBJECT-TYPE
			SYNTAX Unsigned32 (20..200)
			UNITS "milliseconds"
			MAX-ACCESS read-write
			STATUS current
			DESCRIPTION
				"This is the minimum break pulse width for the dial pulse."
			DEFVAL { 45 }
			::= { zhoneVoiceSignalingTimers 31 }


		-- 1.3.6.1.4.1.5504.4.3.7.1.32
		sysMaxBreakPulseWidth OBJECT-TYPE
			SYNTAX Unsigned32 (20..200)
			UNITS "milliseconds"
			MAX-ACCESS read-write
			STATUS current
			DESCRIPTION
				"This is the maximum break pulse width for the dial pulse."
			DEFVAL { 75 }
			::= { zhoneVoiceSignalingTimers 32 }


		-- 1.3.6.1.4.1.5504.4.3.7.1.33
		zhoneVoiceSignalingObjectsGroup OBJECT-GROUP
			OBJECTS { sysPartialDialTo, sysCriticalDialTo, sysBusyToneTo, sysDialToneTo, sysMsgWaitToneTo,
				sysOffhookWarnToneTo, sysRingingTo, sysRingbackTo, sysReorderToneTo, sysStutterToneTo,
				sysServerMaxTimer, sysConfigMax1, sysConfigMax2, sysMax1Enable, sysMax2Enable,
				sysMaxWaitingDelay, sysDisconnectWaitTimer, sysDisconnectMinTimer, sysDisconnectMaxTimer, sysMaxRetransmitTimer,
				sysInitRetransmitTimer, sysKeepAliveTimer, sysNoResponseTimer, sysCallWaitMaxRepeat, sysCallWaitDelay,
				sysPulseInterDigitTimer, sysMinMakePulseWidth, sysMaxMakePulseWidth, sysMinBreakPulseWidth, sysMaxBreakPulseWidth,
				hookFlashTimerMin, hookFlashTimerMax }
			STATUS current
			DESCRIPTION
				"Description."
			::= { zhoneVoiceSignalingTimers 33 }



	END

--
-- comVoiceSignaling.mib
--
