--
-- comIpRip2.mib
-- MIB generated by MG-SOFT Visual MIB Builder Version 2.1 Build 205
-- Wednesday, September 12, 2001 at 13:21:43
--

	ZHONE-COM-IP-RIPv2-MIB DEFINITIONS ::= BEGIN

		IMPORTS
			TimeTicks, IpAddress, Unsigned32, Counter32, OBJECT-TYPE,
			MODULE-IDENTITY, OBJECT-IDENTITY
				FROM SNMPv2-SMI
			TEXTUAL-CONVENTION
				FROM SNMPv2-TC
			rdIndex
				FROM ZHONE-COM-IP-RD-MIB
			zhoneIp, zhoneModules
				FROM Zhone;


--
--
--
--
		comIpRip2 MODULE-IDENTITY
			LAST-UPDATED "200109121318Z"
			ORGANIZATION
				"Zhone Technologies, Inc."
			CONTACT-INFO
				"   Postal:
				           Zhone Technologies, Inc.
				           @ Zhone Way
				           7001 Oakport Street
				           Oakland, CA  94621
				           USA
				Toll-Free: +1 877-ZHONE20 (+1 877-946-6320)
				      Tel: +1-510-777-7000
				      Fax: +1-510-777-7001
				   E-mail: support@zhone.com"
			DESCRIPTION
				"RIPv2 MIB
				IP Software
				Minneapolis, MN"
			REVISION "200109121318Z"
			DESCRIPTION
				"V01.01.01 - Added zhone comments for the rip2 MIB."
			REVISION "200010121708Z"
			DESCRIPTION
				"V01.01.00 - add static route advertisement and poison fields to rip if config table"
			REVISION "200010020805Z"
			DESCRIPTION
				"V01.00.01 - update existing markup"
			REVISION "200009121020Z"
			DESCRIPTION
				"V01.00.00 - Initial Release"
			::= { zhoneModules 52 }


--
-- Textual conventions
--

		RipAuthKey ::= TEXTUAL-CONVENTION
			STATUS current
			DESCRIPTION
				"The RIP authentication key specification.  Only the RIP
				mib should use this."
			SYNTAX OCTET STRING (SIZE (0..16))


--
-- Node definitions
--

-- Zhone RIP-2 Management Information Base
-- (derived from RFC 1724)
--
-- mshivana - RIP-1 and RIP-2 are NOT supported on MALC.
--            This means that ,The SNMP GET operations
--            on all the MIB variables under this node will
--            return NO-SUCH.
		rip2 OBJECT-IDENTITY
			STATUS current
			DESCRIPTION
				"The MIB module to describe the RIP2 Version 2 Protocol
				as represented in Zhone products.  The notion of a
				Routing Domain (RD) is used to group instances of RIP
				within a system."
			::= { zhoneIp 2 }

-- 4.1 Global Counters
--
-- The RIP-2 Global Table.
--
		zhRip2GlobalTable OBJECT-TYPE
			SYNTAX SEQUENCE OF ZhRip2GlobalEntry
			MAX-ACCESS not-accessible
			STATUS current
			DESCRIPTION
				"A list of global RIP values.  Rows are created and
				destroyed whenever a routing domain is created and
				destroyed.  Rows cannot be created or destroyed via SNMP."
			::= { rip2 1 }

		zhRip2GlobalEntry OBJECT-TYPE
			SYNTAX ZhRip2GlobalEntry
			MAX-ACCESS not-accessible
			STATUS current
			DESCRIPTION
				"A single routing domain in a single subnet."
			INDEX { rdIndex }
			::= { zhRip2GlobalTable 1 }

		ZhRip2GlobalEntry ::=
			SEQUENCE {
				zhRip2GlobalRouteChanges
					Counter32,
				zhRip2GlobalQueries
					Counter32,
				zhRip2GlobalAdminState
					INTEGER,
				zhRip2GlobalUpdateTime
					Unsigned32
			 }

		zhRip2GlobalRouteChanges OBJECT-TYPE
			SYNTAX Counter32
			MAX-ACCESS read-only
			STATUS current
			DESCRIPTION
				"The number of route changes made to the IP Route
				Database by RIP.  This does not include the refresh
				of a route's age."
			::= { zhRip2GlobalEntry 1 }

		zhRip2GlobalQueries OBJECT-TYPE
			SYNTAX Counter32
			MAX-ACCESS read-only
			STATUS current
			DESCRIPTION
				"The number of responses sent to RIP queries
				from other systems."
			::= { zhRip2GlobalEntry 2 }

		zhRip2GlobalAdminState OBJECT-TYPE
			SYNTAX INTEGER
				{
				disabled(1),
				enabled(2)
				}
			MAX-ACCESS read-write
			STATUS current
			DESCRIPTION
				"An enumeration of the operational state of RIP for a RD.
				The possible values are either 'disabled' or 'enabled',
				where the operation of RIP is completely disabled or enabled
				on all interfaces within a RD.  The default is 'enabled'."
			DEFVAL { enabled }
			::= { zhRip2GlobalEntry 3 }

		zhRip2GlobalUpdateTime OBJECT-TYPE
			SYNTAX Unsigned32
			MAX-ACCESS read-write
			STATUS current
			DESCRIPTION
				"The time in seconds between transmissions of RIP updates
				on all interfaces within a RD.  The default is 30 seconds,
				which follows RFC 1058 and subsequent RIP RFCs."
			DEFVAL { 30 }
			::= { zhRip2GlobalEntry 4 }

-- The RIP Interface Status Table.
		zhRip2IfStatTable OBJECT-TYPE
			SYNTAX SEQUENCE OF ZhRip2IfStatEntry
			MAX-ACCESS not-accessible
			STATUS current
			DESCRIPTION
				"A list of subnets that require separate status monitoring
				in RIP. Rows are created and destroyed whenever an interface
				within the RD is created and destroyed.  Rows cannot be
				created or destroyed via SNMP."
			::= { rip2 2 }

		zhRip2IfStatEntry OBJECT-TYPE
			SYNTAX ZhRip2IfStatEntry
			MAX-ACCESS not-accessible
			STATUS current
			DESCRIPTION
				"A single routing domain in a single subnet."
			INDEX { rdIndex, zhRip2IfStatAddress }
			::= { zhRip2IfStatTable 1 }

		ZhRip2IfStatEntry ::=
			SEQUENCE {
				zhRip2IfStatAddress
					IpAddress,
				zhRip2IfStatRcvBadPackets
					Counter32,
				zhRip2IfStatRcvBadRoutes
					Counter32,
				zhRip2IfStatSentUpdates
					Counter32
			 }

		zhRip2IfStatAddress OBJECT-TYPE
			SYNTAX IpAddress
			MAX-ACCESS not-accessible
			STATUS current
			DESCRIPTION
				"The IP Address of this system on the indicated
				subnet. For unnumbered interfaces, a unique internal
				identifier is used."
			::= { zhRip2IfStatEntry 1 }

		zhRip2IfStatRcvBadPackets OBJECT-TYPE
			SYNTAX Counter32
			MAX-ACCESS read-only
			STATUS current
			DESCRIPTION
				"The number of RIP response packets received by
				the RIP process that were subsequently discarded
				for any reason (e.g. a version 0 packet, or an
				unknown command type)."
			::= { zhRip2IfStatEntry 2 }

		zhRip2IfStatRcvBadRoutes OBJECT-TYPE
			SYNTAX Counter32
			MAX-ACCESS read-only
			STATUS current
			DESCRIPTION
				"The number of routes, in valid RIP packets,
				that were ignored for any reason (e.g. unknown
				address family, or invalid metric)."
			::= { zhRip2IfStatEntry 3 }

		zhRip2IfStatSentUpdates OBJECT-TYPE
			SYNTAX Counter32
			MAX-ACCESS read-only
			STATUS current
			DESCRIPTION
				"The number of triggered RIP updates actually
				sent on this interface.  This explicitly does
				NOT include full updates sent containing new
				information."
			::= { zhRip2IfStatEntry 4 }

-- The RIP Interface Configuration Table.
		zhRip2IfConfTable OBJECT-TYPE
			SYNTAX SEQUENCE OF ZhRip2IfConfEntry
			MAX-ACCESS not-accessible
			STATUS current
			DESCRIPTION
				"A list of subnets that require separate configuration in
				RIP.  Rows are created and destroyed whenever an interface
				within the RD is created and destroyed.  Rows cannot be
				created or destroyed via SNMP."
			::= { rip2 3 }

		zhRip2IfConfEntry OBJECT-TYPE
			SYNTAX ZhRip2IfConfEntry
			MAX-ACCESS not-accessible
			STATUS current
			DESCRIPTION
				"A single routing domain in a single subnet."
			INDEX { rdIndex, zhRip2IfConfAddress }
			::= { zhRip2IfConfTable 1 }

		ZhRip2IfConfEntry ::=
			SEQUENCE {
				zhRip2IfConfAddress
					IpAddress,
				zhRip2IfConfAuthType
					INTEGER,
				zhRip2IfConfAuthKey
					RipAuthKey,
				zhRip2IfConfSend
					INTEGER,
				zhRip2IfConfReceive
					INTEGER,
				zhRip2IfConfDefaultMetric
					INTEGER,
				zhRip2IfConfSrcAddress
					IpAddress,
				zhRip2IfConfStaticRouteAdvertisement
					INTEGER,
				zhRip2IfConfPoison
					INTEGER
			 }

		zhRip2IfConfAddress OBJECT-TYPE
			SYNTAX IpAddress
			MAX-ACCESS not-accessible
			STATUS current
			DESCRIPTION
				"The IP Address of this system on the indicated
				subnet. For unnumbered interfaces, a unique internal
				identifier is used."
			::= { zhRip2IfConfEntry 1 }

		zhRip2IfConfAuthType OBJECT-TYPE
			SYNTAX INTEGER
				{
				noAuthentication(1),
				simplePassword(2),
				md5(3)
				}
			MAX-ACCESS read-write
			STATUS current
			DESCRIPTION
				"The type of Authentication used when receiving RIP packets
				on this interface.  When set to 'noAuthentication', no
				authentication is performed.  For 'simplePassword', a
				clear text password is used in zhRip2IfConfAuthKey.
				When set to 'md5', an MD5 string is used in
				zhRip2IfConfAuthKey (see RFC 1321)."
			DEFVAL { noAuthentication }
			::= { zhRip2IfConfEntry 2 }

--
-- Default value is { ''h }
		zhRip2IfConfAuthKey OBJECT-TYPE
			SYNTAX RipAuthKey
			MAX-ACCESS read-write
			STATUS current
			DESCRIPTION
				"The value to be used as the Authentication Key
				whenever the corresponding instance of
				zhRip2IfConfAuthType has a value other than
				noAuthentication.  A modification of the corresponding
				instance of zhRip2IfConfAuthType does not modify
				the zhRip2IfConfAuthKey value.  If a string shorter
				than 16 octets is supplied, it will be left-
				justified and padded to 16 octets, on the right,
				with nulls (0x00).

				Reading this object always results in an  OCTET
				STRING of length zero; authentication may not
				be bypassed by reading the MIB object."
			::= { zhRip2IfConfEntry 3 }
-- the ddl tool doesn't like these default values
-- DEFVAL { ''h }                tool syntax error
-- DEFVAL { "" }                 tool syntax error
-- DEFVAL { "write-only" }       c syntax error (""write-only"")

		zhRip2IfConfSend OBJECT-TYPE
			SYNTAX INTEGER
				{
				doNotSend(1),
				ripVersion1(2),
				rip1Compatible(3),
				ripVersion2(4),
				ripV1Demand(5),
				ripV2Demand(6)
				}
			MAX-ACCESS read-write
			STATUS current
			DESCRIPTION
				"What the router sends on this interface.
				If set to 'doNotSend', no RIP updates are sent
				out on this interface.  If set to 'ripVersion1',
				RIP updates compliant with RFC 1058 are sent.
				'rip1Compatible' implies broadcasting RIP-2 updates
				using RFC 1058 route subsumption rules.  'ripVersion2'
				implies multicasting RIP-2 updates.  'ripV1Demand' indicates
				the use of Demand RIP on a WAN interface under RIP
				Version 1 rules.  'ripV2Demand' indicates the use of
				Demand RIP on a WAN interface under Version 2 rules.
				The default is 'rip1Compatible'."
			DEFVAL { rip1Compatible }
			::= { zhRip2IfConfEntry 4 }

		zhRip2IfConfReceive OBJECT-TYPE
			SYNTAX INTEGER
				{
				rip1(1),
				rip2(2),
				rip1OrRip2(3),
				doNotReceive(4)
				}
			MAX-ACCESS read-write
			STATUS current
			DESCRIPTION
				"This indicates which version of RIP updates are to be
				accepted.  When set to 'rip1', only RIP updates compliant
				with RFC 1058 are received.  'rip2' specifies to receive
				RIP updates compliant with RFC 1388 only.  Setting
				'rip1OrRip2' allows reception of RFC 1058 and RFC 1388
				compliant RIP updates.  If set to 'doNotReceive', the
				intreface accepts no RIP updates.  Note that 'rip2' and
				'rip1OrRip2' implies reception of multicast packets.
				The default is 'rip1OrRip2'."
			DEFVAL { rip1OrRip2 }
			::= { zhRip2IfConfEntry 5 }

		zhRip2IfConfDefaultMetric OBJECT-TYPE
			SYNTAX INTEGER (0..15)
			MAX-ACCESS read-write
			STATUS current
			DESCRIPTION
				"This variable indicates the metric that is to
				be used for the default route entry in RIP updates
				originated on this interface.  A value of zero
				indicates that no default route should be
				originated; in this case, a default route via
				another router may be propagated.  The default is
				set using the metric in the received update."
			::= { zhRip2IfConfEntry 6 }

		zhRip2IfConfSrcAddress OBJECT-TYPE
			SYNTAX IpAddress
			MAX-ACCESS read-write
			STATUS current
			DESCRIPTION
				"The IP Address this system will use as a source
				address on this interface.  If it is a numbered
				interface, this MUST be the same value as ipIfAddr
				(from ZHONE-IP-REC-MIB).  On unnumbered interfaces,
				it must be the value of ipIfAddr for some interface
				on the system."
			::= { zhRip2IfConfEntry 7 }

		zhRip2IfConfStaticRouteAdvertisement OBJECT-TYPE
			SYNTAX INTEGER
				{
				none(1),
				low(2),
				high(3),
				both(4)
				}
			MAX-ACCESS read-write
			STATUS current
			DESCRIPTION
				"This variable specifies whether to advertise static routes.
				When set to 'none', no static routes are advertised.  For
				'low', only low preference static routes are advertised,
				and when set to 'high' only high preference static routes
				are advertised.  'both' specifies to advertise both low
				and high preference static routes.  Low preference routes
				are default routes.  The default value is 'none'."
			DEFVAL { none }
			::= { zhRip2IfConfEntry 8 }

		zhRip2IfConfPoison OBJECT-TYPE
			SYNTAX INTEGER
				{
				disabled(1),
				enabled(2)
				}
			MAX-ACCESS read-write
			STATUS current
			DESCRIPTION
				"This variable specifies whether to send poison reverse
				updates on this interface.  Poison reverse updates are
				used to prevent larger loops within the network by
				setting the metric (cost) of neighboring routes to
				infinity.  This will prevent two-hop loops.

				By default, RIP uses a technique called split horizon
				to avoid routing loops and allow smaller update packets.
				Split horizon specifies that when a RIP update is sent
				out a particular network interface, it should not
				include routing information acquired over that same
				interface.  Poison Reverse is a variation of the split
				horizon technique that specifies that all routes are
				included in an update out a particular interface, but
				that the metric is set to infinity for routes acquired
				over that interface.  One drawback is that routing update
				packet sizes are increased when using poison reverse.

				Setting the value of this object to 'disable' prevents
				poison reverse updates, where 'enable' allows poison
				updates to be sent on this interface.  The default value
				is 'disabled'."
			DEFVAL { disabled }
			::= { zhRip2IfConfEntry 9 }

-- The Peer (Neighbor) Table
--
-- This table provides information about active peer
-- relationships intended to assist in debugging.  An
-- active peer is a router from which a valid RIP
-- updated has been heard in the last 180 seconds.
		zhRip2PeerTable OBJECT-TYPE
			SYNTAX SEQUENCE OF ZhRip2PeerEntry
			MAX-ACCESS not-accessible
			STATUS current
			DESCRIPTION
				"A list of RIP Peers.  A row (new peer) is created whenever
				an interface running RIP receives a RIP update from a new
				peer.  The row is destroyed when the interface has not
				received a RIP update for more tha 180 seconds.  Rows
				cannot be created or destroyed via SNMP."
			::= { rip2 4 }

		zhRip2PeerEntry OBJECT-TYPE
			SYNTAX ZhRip2PeerEntry
			MAX-ACCESS not-accessible
			STATUS current
			DESCRIPTION
				"Information regarding a single routing peer."
			INDEX { rdIndex, zhRip2PeerAddress }
			::= { zhRip2PeerTable 1 }

		ZhRip2PeerEntry ::=
			SEQUENCE {
				zhRip2PeerAddress
					IpAddress,
				zhRip2PeerLastUpdate
					TimeTicks,
				zhRip2PeerVersion
					INTEGER,
				zhRip2PeerRcvBadPackets
					Counter32,
				zhRip2PeerRcvBadRoutes
					Counter32
			 }

		zhRip2PeerAddress OBJECT-TYPE
			SYNTAX IpAddress
			MAX-ACCESS not-accessible
			STATUS current
			DESCRIPTION
				"The IP Address that the peer is using as its source
				address.  Note that on an unnumbered link, this may
				not be a member of any subnet on the system."
			::= { zhRip2PeerEntry 1 }

		zhRip2PeerLastUpdate OBJECT-TYPE
			SYNTAX TimeTicks
			MAX-ACCESS read-only
			STATUS current
			DESCRIPTION
				"The value of sysUpTime when the most recent
				RIP update was received from this system."
			::= { zhRip2PeerEntry 2 }

		zhRip2PeerVersion OBJECT-TYPE
			SYNTAX INTEGER (0..255)
			MAX-ACCESS read-only
			STATUS current
			DESCRIPTION
				"The RIP version number in the header of the
				last RIP packet received."
			::= { zhRip2PeerEntry 3 }

		zhRip2PeerRcvBadPackets OBJECT-TYPE
			SYNTAX Counter32
			MAX-ACCESS read-only
			STATUS current
			DESCRIPTION
				"The number of RIP response packets from this
				peer discarded as invalid."
			::= { zhRip2PeerEntry 4 }

		zhRip2PeerRcvBadRoutes OBJECT-TYPE
			SYNTAX Counter32
			MAX-ACCESS read-only
			STATUS current
			DESCRIPTION
				"The number of routes from this peer that were
				ignored because the entry format was invalid."
			::= { zhRip2PeerEntry 5 }


	END

--
-- comIpRip2.mib
--
