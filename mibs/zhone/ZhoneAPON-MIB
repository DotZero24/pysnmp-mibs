--
-- phyAPON.mib
-- MIB generated by MG-SOFT Visual MIB Builder Version 3.0 Build 271
-- Tuesday, April 25, 2006 at 11:05:12
--

	ZhoneAPON-MIB DEFINITIONS ::= BEGIN

		IMPORTS
			ifNumber, ifIndex, ifName, ifInMulticastPkts, ifInBroadcastPkts,
			ifOutMulticastPkts, ifOutBroadcastPkts, ifHCInOctets, ifHCInUcastPkts, ifHCInMulticastPkts,
			ifHCInBroadcastPkts, ifHCOutOctets, ifHCOutUcastPkts, ifHCOutMulticastPkts, ifHCOutBroadcastPkts,
			ifLinkUpDownTrapEnable, ifHighSpeed, ifPromiscuousMode, ifConnectorPresent, ifAlias,
			ifCounterDiscontinuityTime, ifStackHigherLayer, ifStackLowerLayer, ifStackStatus, ifTestId,
			ifTestStatus, ifTestType, ifTestResult, ifTestCode, ifTestOwner,
			ifRcvAddressAddress, ifRcvAddressStatus, ifRcvAddressType, ifTableLastChange, ifStackLastChange,
			ifGeneralGroup, ifFixedLengthGroup, ifHCFixedLengthGroup, ifPacketGroup, ifHCPacketGroup,
			ifVHCPacketGroup, ifRcvAddressGroup, ifTestGroup, ifStackGroup, ifGeneralInformationGroup,
			ifStackGroup2, ifOldObjectsGroup, ifCounterDiscontinuityGroup, ifCompliance, ifCompliance2
				FROM IF-MIB
			OBJECT-GROUP, NOTIFICATION-GROUP
				FROM SNMPv2-CONF
			Integer32, Unsigned32, OBJECT-TYPE, MODULE-IDENTITY, OBJECT-IDENTITY,
			NOTIFICATION-TYPE
				FROM SNMPv2-SMI
			TruthValue, TimeStamp
				FROM SNMPv2-TC
			zhoneRegPls, zhoneRegCpe, zhoneRegMux, zhoneRegSechtor, zhoneRegWtn,
			zhoneRegMalc, zhonePls, zhoneZedge, zhoneZplex, sechtor100,
			sechtor300, zhoneWtn, zhoneMalc, zhoneZmsProduct, zhoneSystem,
			zhoneShelf, zhoneCard, zhoneSubscriber, zhoneInterfaceTranslation, zhoneInterfaceGroup,
			zhoneMasterAgent, zhoneTrapModules, zhoneGenWtn, zhoneZAP, zhoneVoiceStats,
			zhoneIp, zhoneAtm, zhoneVoice, zhoneVoip, zhonePpp,
			zhoneIma, zhoneBridge, zhonePhysical, zhoneEnet, zhoneDsx,
			zhoneOcx, zhoneDsl, zhoneConsole, zhoneRadio, zhoneSonet,
			zhoneDs3Ext, zhoneLineTypes, zhoneModules, zhoneShelfIndex, zhoneSlotIndex,
			zhoneGroups, zhoneShelfSlotGroup, zhoneShelfSlotCompliance, apsMIB, sipTC,
			sipCommonMIB, sipUAMIB, zhoneDrafts
				FROM Zhone
			ZhoneAdminString, ZhoneRowStatus
				FROM Zhone-TC;


--
--
--
--
--
--
		zhoneAponMIB MODULE-IDENTITY
			LAST-UPDATED "200604251445Z"		-- April 25, 2006 at 14:45 GMT
			ORGANIZATION
				"Zhone Terchnologies, Inc."
			CONTACT-INFO
				"  Postal:
				Zhone Technologies, Inc.
				@ Zhone Way
				7001 Oakport Street
				Oakland, CA  94621
				USA
				Toll-Free: +1 877-ZHONE20 (+1 877-946-6320)
				Tel: +1-510-777-7000
				Fax: +1-510-777-7001
				E-mail: support@zhone.com"
			DESCRIPTION
				"This is the Zhone ATM-PON mib."
			REVISION "200604251103Z"		-- April 25, 2006 at 11:03 GMT
			DESCRIPTION
				"Add zhoneOnuConfigRfVideo"
			REVISION "200504181442Z"		-- April 18, 2005 at 14:42 GMT
			DESCRIPTION
				"Added new alarm definitions:
				    LOS
				    PEE
				    SUF
				    OAML
				    LCD"
			REVISION "200406091156Z"		-- June 09, 2004 at 11:56 GMT
			DESCRIPTION
				"Added trap info."
			REVISION "200403251627Z"		-- March 25, 2004 at 16:27 GMT
			DESCRIPTION
				"Add OLT line status change trap support."
			REVISION "200312081529Z"		-- December 08, 2003 at 15:29 GMT
			DESCRIPTION
				"Corrected spelling of guaranteedBw."
			REVISION "200311191249Z"		-- November 19, 2003 at 12:49 GMT
			DESCRIPTION
				"Modified SerialNumber field from string to integer."
			REVISION "200308181559Z"		-- August 18, 2003 at 15:59 GMT
			DESCRIPTION
				"Add Traffic Container mib."
			REVISION "200308121125Z"		-- August 12, 2003 at 11:25 GMT
			DESCRIPTION
				"Change MALC-side ONU tables to OLT/ONU.

				Add far-side ONU tables."
			REVISION "200308051012Z"		-- August 05, 2003 at 10:12 GMT
			DESCRIPTION
				"Initial version."
			::= { zhoneApon 1 }



--
-- Node definitions
--

-- Overview of the Zhone APON Mib
--
-- The Zhone APON Mib is a custom mib created to work with BroadLight APON
-- hardware and software.  It is designed to afford SNMP functionality for
-- the malcOlt line card.
--
-- The mib is made up of six tables: OLT Config table, OLT Status table,
-- OLT/ONU Config table, OLT/ONU Status table, ONU Config table and ONU Status
-- table.  The OLT Config table contains provisioning information necessary to
-- bring up the BroadLight transceivers.  The OLT Status table contains line
-- state and alarm information for the CO-side equipment.
--
-- The OLT/ONU Config table contains information necessary to establish
-- communications with the far-end transceivers.  It does not contain
-- full provisioning information for the CPE-side device.  This table is a
-- near-end table.
--
-- The OLT/ONU Status table contains alarm information for the far-end device.
--
-- The ONU Config table is the far-end provisioning table.
--
-- The ONU Status table is the far-end alarm information table.
--
		-- 1.3.6.1.4.1.5504.5.12
		zhoneApon OBJECT-IDENTITY
			STATUS current
			DESCRIPTION
				"ATM Passive Optical Network-related Zhone MIBs."
			::= { zhonePhysical 12 }

		-- 1.3.6.1.4.1.5504.5.12.1.2
		zhoneOltConfigTable OBJECT-TYPE
			SYNTAX SEQUENCE OF ZhoneOltConfigEntry
			MAX-ACCESS not-accessible
			STATUS current
			DESCRIPTION
				"Optical Line Termination configuration table."
			::= { zhoneAponMIB 2 }

		-- 1.3.6.1.4.1.5504.5.12.1.2.1
		zhoneOltConfigEntry OBJECT-TYPE
			SYNTAX ZhoneOltConfigEntry
			MAX-ACCESS not-accessible
			STATUS current
			DESCRIPTION
				"An entry in the Olt Config table."
			INDEX { ifIndex }
			::= { zhoneOltConfigTable 1 }

		ZhoneOltConfigEntry ::=
			SEQUENCE {
				zhoneOltConfigAutoLearn
					INTEGER,
				zhoneOltConfigCellScrambling
					INTEGER,
				zhoneOltConfigBip8
					INTEGER,
				zhoneOltConfigHec
					INTEGER,
				zhoneOltConfigHecRxBypass
					TruthValue,
				zhoneOltConfigCrcRx
					TruthValue,
				zhoneOltConfigOverheadSize
					INTEGER,
				zhoneOltConfigDelimiterPattern
					Integer32,
				zhoneOltConfigDelimiterSize
					Integer32,
				zhoneOltConfigCdrPattern
					Integer32,
				zhoneOltConfigCdrLocation
					Integer32,
				zhoneOltConfigCdrActiveHigh
					TruthValue,
				zhoneOltConfigCpeLimit
					Integer32,
				zhoneOltConfigLcdLimit
					Integer32,
				zhoneOltConfigLcdAlpha
					Integer32,
				zhoneOltConfigLcdDelta
					Integer32,
				zhoneOltConfigTxDiscardNonMatchingVpi
					TruthValue,
				zhoneOltConfigUtopiaDiscard
					TruthValue,
				zhoneOltConfigSyncBytesClkDivisor
					Integer32,
				zhoneOltConfigTxSyncBytes
					INTEGER,
				zhoneOltConfigLoopback
					INTEGER,
				zhoneOltConfigMaxPonDistance
					Integer32,
				zhoneOltConfigLineStatusChangeTrapEnable
					INTEGER
			 }

		-- 1.3.6.1.4.1.5504.5.12.1.2.1.1
		zhoneOltConfigAutoLearn OBJECT-TYPE
			SYNTAX INTEGER
				{
				oltAutolearnEnable(1),
				oltAutolearnDisable(2)
				}
			MAX-ACCESS read-write
			STATUS current
			DESCRIPTION
				"Auto-learn enable flag."
			DEFVAL { oltAutolearnDisable }
			::= { zhoneOltConfigEntry 1 }

		-- 1.3.6.1.4.1.5504.5.12.1.2.1.2
		zhoneOltConfigCellScrambling OBJECT-TYPE
			SYNTAX INTEGER
				{
				oltCellScramblingOff(1),
				oltCellScramblingRxOnly(2),
				oltCellScramblingTxOnly(3),
				oltCellScramblingRxAndTx(4)
				}
			MAX-ACCESS read-write
			STATUS current
			DESCRIPTION
				"Cell scrambling option control flag."
			DEFVAL { oltCellScramblingRxAndTx }
			::= { zhoneOltConfigEntry 2 }

		-- 1.3.6.1.4.1.5504.5.12.1.2.1.3
		zhoneOltConfigBip8 OBJECT-TYPE
			SYNTAX INTEGER
				{
				oltBip8Off(1),
				oltBip8RxCorrectionOnly(2),
				oltBip8TxGenerationOnly(3),
				oltBip8RxAndTx(4)
				}
			MAX-ACCESS read-write
			STATUS current
			DESCRIPTION
				"Bip8 - Bit Interleave Parity, a procedure whereby each bit of a
				 resulting BIP8 parity byte is a parity bit done across a specific
				 bit position."
			DEFVAL { oltBip8TxGenerationOnly }
			::= { zhoneOltConfigEntry 3 }

		-- 1.3.6.1.4.1.5504.5.12.1.2.1.4
		zhoneOltConfigHec OBJECT-TYPE
			SYNTAX INTEGER
				{
				oltHecOff(1),
				oltHecRxCorrectionOnly(2),
				oltHecTxGenerationOnly(3),
				oltHecRxAndTx(4)
				}
			MAX-ACCESS read-write
			STATUS current
			DESCRIPTION
				"Headder Error Control field."
			DEFVAL { oltHecRxCorrectionOnly }
			::= { zhoneOltConfigEntry 4 }

		-- 1.3.6.1.4.1.5504.5.12.1.2.1.5
		zhoneOltConfigHecRxBypass OBJECT-TYPE
			SYNTAX TruthValue
			MAX-ACCESS read-write
			STATUS current
			DESCRIPTION
				"Cyclic Redundancy Check bypass for reception."
			DEFVAL { false }
			::= { zhoneOltConfigEntry 5 }

		-- 1.3.6.1.4.1.5504.5.12.1.2.1.6
		zhoneOltConfigCrcRx OBJECT-TYPE
			SYNTAX TruthValue
			MAX-ACCESS read-write
			STATUS current
			DESCRIPTION
				"Cyclic Redundancy Check for reception."
			DEFVAL { true }
			::= { zhoneOltConfigEntry 6 }

		-- 1.3.6.1.4.1.5504.5.12.1.2.1.7
		zhoneOltConfigOverheadSize OBJECT-TYPE
			SYNTAX INTEGER
				{
				oltPonOverhead3Bytes(1),
				oltPonOverhead6Bytes(2),
				oltPonOverhead12Bytes(3)
				}
			MAX-ACCESS read-write
			STATUS current
			DESCRIPTION
				"Overhead size definition field."
			DEFVAL { oltPonOverhead3Bytes }
			::= { zhoneOltConfigEntry 7 }

		-- 1.3.6.1.4.1.5504.5.12.1.2.1.8
		zhoneOltConfigDelimiterPattern OBJECT-TYPE
			SYNTAX Integer32 (0..65535)
			MAX-ACCESS read-write
			STATUS current
			DESCRIPTION
				"A unique pattern indicating the start of the
				 ATM cell or minislot, which can be used to
				 perform byte synchronization."
			DEFVAL { 162 }
			::= { zhoneOltConfigEntry 8 }

		-- 1.3.6.1.4.1.5504.5.12.1.2.1.9
		zhoneOltConfigDelimiterSize OBJECT-TYPE
			SYNTAX Integer32 (2..16)
			UNITS "Number of bits"
			MAX-ACCESS read-write
			STATUS current
			DESCRIPTION
				"Delimiter pattern size."
			DEFVAL { 8 }
			::= { zhoneOltConfigEntry 9 }

		-- 1.3.6.1.4.1.5504.5.12.1.2.1.10
		zhoneOltConfigCdrPattern OBJECT-TYPE
			SYNTAX Integer32 (0..65535)
			MAX-ACCESS read-write
			STATUS current
			DESCRIPTION
				"Re-sync signal pattern.
				"
			DEFVAL { 192 }
			::= { zhoneOltConfigEntry 10 }

		-- 1.3.6.1.4.1.5504.5.12.1.2.1.11
		zhoneOltConfigCdrLocation OBJECT-TYPE
			SYNTAX Integer32 (0..32)
			MAX-ACCESS read-write
			STATUS current
			DESCRIPTION
				"Re-sync signal location."
			DEFVAL { 0 }
			::= { zhoneOltConfigEntry 11 }

		-- 1.3.6.1.4.1.5504.5.12.1.2.1.12
		zhoneOltConfigCdrActiveHigh OBJECT-TYPE
			SYNTAX TruthValue
			MAX-ACCESS read-write
			STATUS current
			DESCRIPTION
				"Clock Data Recovery."
			DEFVAL { false }
			::= { zhoneOltConfigEntry 12 }

		-- 1.3.6.1.4.1.5504.5.12.1.2.1.13
		zhoneOltConfigCpeLimit OBJECT-TYPE
			SYNTAX Integer32 (0..16)
			MAX-ACCESS read-write
			STATUS current
			DESCRIPTION
				"Cell phase error limit."
			DEFVAL { 4 }
			::= { zhoneOltConfigEntry 13 }

		-- 1.3.6.1.4.1.5504.5.12.1.2.1.14
		zhoneOltConfigLcdLimit OBJECT-TYPE
			SYNTAX Integer32 (4..15)
			MAX-ACCESS read-write
			STATUS current
			DESCRIPTION
				"Loss of cell delineation limit."
			DEFVAL { 8 }
			::= { zhoneOltConfigEntry 14 }

		-- 1.3.6.1.4.1.5504.5.12.1.2.1.15
		zhoneOltConfigLcdAlpha OBJECT-TYPE
			SYNTAX Integer32 (1..15)
			MAX-ACCESS read-write
			STATUS current
			DESCRIPTION
				"Number of cells in delineation error before the LCD alarm is raised."
			DEFVAL { 1 }
			::= { zhoneOltConfigEntry 15 }

		-- 1.3.6.1.4.1.5504.5.12.1.2.1.16
		zhoneOltConfigLcdDelta OBJECT-TYPE
			SYNTAX Integer32 (1..15)
			MAX-ACCESS read-write
			STATUS current
			DESCRIPTION
				"Number of cells received NOT in delineation error required to
				clear LCD Alarm."
			DEFVAL { 2 }
			::= { zhoneOltConfigEntry 16 }

		-- 1.3.6.1.4.1.5504.5.12.1.2.1.17
		zhoneOltConfigTxDiscardNonMatchingVpi OBJECT-TYPE
			SYNTAX TruthValue
			MAX-ACCESS read-write
			STATUS current
			DESCRIPTION
				"Discard non-matching Vpi."
			DEFVAL { false }
			::= { zhoneOltConfigEntry 17 }

		-- 1.3.6.1.4.1.5504.5.12.1.2.1.18
		zhoneOltConfigUtopiaDiscard OBJECT-TYPE
			SYNTAX TruthValue
			MAX-ACCESS read-write
			STATUS current
			DESCRIPTION
				"Discard Utopia cells with HEC errors or arriving on unknown Vpi."
			DEFVAL { false }
			::= { zhoneOltConfigEntry 18 }

		-- 1.3.6.1.4.1.5504.5.12.1.2.1.19
		zhoneOltConfigSyncBytesClkDivisor OBJECT-TYPE
			SYNTAX Integer32 (0..65535)
			MAX-ACCESS read-write
			STATUS current
			DESCRIPTION
				"Sync Bytes Clock Divisor."
			DEFVAL { 1 }
			::= { zhoneOltConfigEntry 19 }

		-- 1.3.6.1.4.1.5504.5.12.1.2.1.20
		zhoneOltConfigTxSyncBytes OBJECT-TYPE
			SYNTAX INTEGER
				{
				txSyncBytesEnable(1),
				txSyncBytesDisable(2)
				}
			MAX-ACCESS read-write
			STATUS current
			DESCRIPTION
				"Enable transmission of sync bytes for ONUs to get their
				clock from a network source."
			DEFVAL { txSyncBytesDisable }
			::= { zhoneOltConfigEntry 20 }

		-- 1.3.6.1.4.1.5504.5.12.1.2.1.21
		zhoneOltConfigLoopback OBJECT-TYPE
			SYNTAX INTEGER
				{
				loopbackNone(1),
				loopbackInward(2),
				loopbackLine(3)
				}
			MAX-ACCESS read-write
			STATUS current
			DESCRIPTION
				"OLT loopback configuration."
			DEFVAL { loopbackNone }
			::= { zhoneOltConfigEntry 21 }

		-- 1.3.6.1.4.1.5504.5.12.1.2.1.22
		zhoneOltConfigMaxPonDistance OBJECT-TYPE
			SYNTAX Integer32 (0..255)
			UNITS "Distance in microseconds, used in the ranging process."
			MAX-ACCESS read-write
			STATUS current
			DESCRIPTION
				"Max PON distance."
			DEFVAL { 200 }
			::= { zhoneOltConfigEntry 22 }

		-- 1.3.6.1.4.1.5504.5.12.1.2.1.23
		zhoneOltConfigLineStatusChangeTrapEnable OBJECT-TYPE
			SYNTAX INTEGER
				{
				enabled(1),
				disabled(2)
				}
			MAX-ACCESS read-write
			STATUS current
			DESCRIPTION
				"Enable/disable control for line status traps on this interface."
			DEFVAL { enabled }
			::= { zhoneOltConfigEntry 23 }

		-- 1.3.6.1.4.1.5504.5.12.1.3
		zhoneOltStatusTable OBJECT-TYPE
			SYNTAX SEQUENCE OF ZhoneOltStatusEntry
			MAX-ACCESS not-accessible
			STATUS current
			DESCRIPTION
				"Optical Line Termination status table."
			::= { zhoneAponMIB 3 }

		-- 1.3.6.1.4.1.5504.5.12.1.3.1
		zhoneOltStatusEntry OBJECT-TYPE
			SYNTAX ZhoneOltStatusEntry
			MAX-ACCESS not-accessible
			STATUS current
			DESCRIPTION
				"An entry in the OLT Status table."
			INDEX { ifIndex }
			::= { zhoneOltStatusTable 1 }

		ZhoneOltStatusEntry ::=
			SEQUENCE {
				zhoneOltStatusState
					INTEGER,
				zhoneOltStatusLoopback
					INTEGER,
				zhoneOltStatusPonAlarmLPHY
					TruthValue,
				zhoneOltStatusPonAlarmTF
					TruthValue,
				zhoneOltStatusPonAlarmSUF
					TruthValue,
				zhoneOltStatusPonAlarmPEE
					TruthValue,
				zhoneOltStatusPonAlarmLCD
					TruthValue,
				zhoneOltStatusPonAlarmLOS
					TruthValue,
				zhoneOltStatusPonAlarmOAML
					TruthValue,
				zhoneOltStatusPonAlarmCPE
					TruthValue,
				zhoneOltStatusLastChange
					TimeStamp
			 }

		-- 1.3.6.1.4.1.5504.5.12.1.3.1.1
		zhoneOltStatusState OBJECT-TYPE
			SYNTAX INTEGER
				{
				oltStateDown(1),
				oltStateUp(2)
				}
			MAX-ACCESS read-only
			STATUS current
			DESCRIPTION
				"Line state of the OLT."
			::= { zhoneOltStatusEntry 1 }

		-- 1.3.6.1.4.1.5504.5.12.1.3.1.2
		zhoneOltStatusLoopback OBJECT-TYPE
			SYNTAX INTEGER
				{
				oltLoopbackNone(1),
				oltLoopbackInward(2),
				oltLoopbackLine(3)
				}
			MAX-ACCESS read-only
			STATUS current
			DESCRIPTION
				"Loopback state of the OLT."
			::= { zhoneOltStatusEntry 2 }

		-- 1.3.6.1.4.1.5504.5.12.1.3.1.3
		zhoneOltStatusPonAlarmLPHY OBJECT-TYPE
			SYNTAX TruthValue
			MAX-ACCESS read-only
			STATUS current
			DESCRIPTION
				"Loss of physical layer alarm."
			::= { zhoneOltStatusEntry 3 }

		-- 1.3.6.1.4.1.5504.5.12.1.3.1.4
		zhoneOltStatusPonAlarmTF OBJECT-TYPE
			SYNTAX TruthValue
			MAX-ACCESS read-only
			STATUS current
			DESCRIPTION
				"Transmitter failure notification."
			::= { zhoneOltStatusEntry 4 }

		-- 1.3.6.1.4.1.5504.5.12.1.3.1.5
		zhoneOltStatusPonAlarmSUF OBJECT-TYPE
			SYNTAX TruthValue
			MAX-ACCESS read-only
			STATUS current
			DESCRIPTION
				"StartUp Failure - ranging process failed N times.
				Note that SUF reflects a hardware problem, and does
				not include cases where the ONU serial number/password
				are wrong/unknown."
			::= { zhoneOltStatusEntry 5 }

		-- 1.3.6.1.4.1.5504.5.12.1.3.1.6
		zhoneOltStatusPonAlarmPEE OBJECT-TYPE
			SYNTAX TruthValue
			MAX-ACCESS read-only
			STATUS current
			DESCRIPTION
				"Physical Equipment Error (received from an ONU.)"
			::= { zhoneOltStatusEntry 6 }

		-- 1.3.6.1.4.1.5504.5.12.1.3.1.7
		zhoneOltStatusPonAlarmLCD OBJECT-TYPE
			SYNTAX TruthValue
			MAX-ACCESS read-only
			STATUS current
			DESCRIPTION
				"Loss of Cell Delineation."
			::= { zhoneOltStatusEntry 7 }

		-- 1.3.6.1.4.1.5504.5.12.1.3.1.8
		zhoneOltStatusPonAlarmLOS OBJECT-TYPE
			SYNTAX TruthValue
			MAX-ACCESS read-only
			STATUS current
			DESCRIPTION
				"Loss of Signal alarm."
			::= { zhoneOltStatusEntry 8 }

		-- 1.3.6.1.4.1.5504.5.12.1.3.1.9
		zhoneOltStatusPonAlarmOAML OBJECT-TYPE
			SYNTAX TruthValue
			MAX-ACCESS read-only
			STATUS current
			DESCRIPTION
				"PLOAM cell loss."
			::= { zhoneOltStatusEntry 9 }

		-- 1.3.6.1.4.1.5504.5.12.1.3.1.10
		zhoneOltStatusPonAlarmCPE OBJECT-TYPE
			SYNTAX TruthValue
			MAX-ACCESS read-only
			STATUS current
			DESCRIPTION
				"Cell Phase Error."
			::= { zhoneOltStatusEntry 10 }

		-- 1.3.6.1.4.1.5504.5.12.1.3.1.11
		zhoneOltStatusLastChange OBJECT-TYPE
			SYNTAX TimeStamp
			MAX-ACCESS read-only
			STATUS current
			DESCRIPTION
				"Time of last line status change."
			DEFVAL { 0 }
			::= { zhoneOltStatusEntry 11 }

		-- 1.3.6.1.4.1.5504.5.12.1.4
		zhoneOltOnuConfigTable OBJECT-TYPE
			SYNTAX SEQUENCE OF ZhoneOltOnuConfigEntry
			MAX-ACCESS not-accessible
			STATUS current
			DESCRIPTION
				"Optical Network Unit configuration table - MALC side."
			::= { zhoneAponMIB 4 }

		-- 1.3.6.1.4.1.5504.5.12.1.4.1
		zhoneOltOnuConfigEntry OBJECT-TYPE
			SYNTAX ZhoneOltOnuConfigEntry
			MAX-ACCESS not-accessible
			STATUS current
			DESCRIPTION
				"An entry in the ONU Config table."
			INDEX { ifIndex }
			::= { zhoneOltOnuConfigTable 1 }

		ZhoneOltOnuConfigEntry ::=
			SEQUENCE {
				zhoneOltOnuConfigPassword
					ZhoneAdminString,
				zhoneOltOnuConfigSerialNum
					Integer32,
				zhoneOltOnuConfigChurnkey
					INTEGER,
				zhoneOltOnuConfigLineStatusChangeTrapEnable
					INTEGER
			 }

		-- 1.3.6.1.4.1.5504.5.12.1.4.1.1
		zhoneOltOnuConfigPassword OBJECT-TYPE
			SYNTAX ZhoneAdminString (SIZE (0..10))
			MAX-ACCESS read-write
			STATUS current
			DESCRIPTION
				"ONU remote-device password."
			::= { zhoneOltOnuConfigEntry 1 }

		-- 1.3.6.1.4.1.5504.5.12.1.4.1.2
		zhoneOltOnuConfigSerialNum OBJECT-TYPE
			SYNTAX Integer32 (1..2147483647)
			MAX-ACCESS read-write
			STATUS current
			DESCRIPTION
				"ONU remote-device serial number."
			::= { zhoneOltOnuConfigEntry 2 }

		-- 1.3.6.1.4.1.5504.5.12.1.4.1.3
		zhoneOltOnuConfigChurnkey OBJECT-TYPE
			SYNTAX INTEGER
				{
				onuChurnkeyEnable(1),
				onuChurnkeyDisable(2)
				}
			MAX-ACCESS read-write
			STATUS current
			DESCRIPTION
				"Churn key enable flag."
			DEFVAL { onuChurnkeyDisable }
			::= { zhoneOltOnuConfigEntry 3 }

		-- 1.3.6.1.4.1.5504.5.12.1.4.1.4
		zhoneOltOnuConfigLineStatusChangeTrapEnable OBJECT-TYPE
			SYNTAX INTEGER
				{
				enabled(1),
				disabled(2)
				}
			MAX-ACCESS read-write
			STATUS current
			DESCRIPTION
				"Enable/disable control for line status traps on this interface."
			DEFVAL { enabled }
			::= { zhoneOltOnuConfigEntry 4 }

		-- 1.3.6.1.4.1.5504.5.12.1.5
		zhoneOltOnuStatusTable OBJECT-TYPE
			SYNTAX SEQUENCE OF ZhoneOltOnuStatusEntry
			MAX-ACCESS not-accessible
			STATUS current
			DESCRIPTION
				"Optical Network Unit status table - MALC side."
			::= { zhoneAponMIB 5 }

		-- 1.3.6.1.4.1.5504.5.12.1.5.1
		zhoneOltOnuStatusEntry OBJECT-TYPE
			SYNTAX ZhoneOltOnuStatusEntry
			MAX-ACCESS not-accessible
			STATUS current
			DESCRIPTION
				"An entry in the OLT/ONU Status table."
			INDEX { ifIndex }
			::= { zhoneOltOnuStatusTable 1 }

		ZhoneOltOnuStatusEntry ::=
			SEQUENCE {
				zhoneOltOnuStatusPonAlarmLOA
					TruthValue,
				zhoneOltOnuStatusPonAlarmERR
					TruthValue,
				zhoneOltOnuStatusPonAlarmSD
					TruthValue,
				zhoneOltOnuStatusPonAlarmREI
					TruthValue,
				zhoneOltOnuStatusPonAlarmMEM
					TruthValue,
				zhoneOltOnuStatusPonAlarmRXINH
					TruthValue,
				zhoneOltOnuStatusPonAlarmLOS
					TruthValue,
				zhoneOltOnuStatusPonAlarmPEE
					TruthValue,
				zhoneOltOnuStatusPonAlarmSUF
					TruthValue,
				zhoneOltOnuStatusPonAlarmOAML
					TruthValue,
				zhoneOltOnuStatusPonAlarmLCD
					TruthValue
			 }

		-- 1.3.6.1.4.1.5504.5.12.1.5.1.1
		zhoneOltOnuStatusPonAlarmLOA OBJECT-TYPE
			SYNTAX TruthValue
			MAX-ACCESS read-only
			STATUS current
			DESCRIPTION
				"Loss of ACK - ONU."
			::= { zhoneOltOnuStatusEntry 1 }

		-- 1.3.6.1.4.1.5504.5.12.1.5.1.2
		zhoneOltOnuStatusPonAlarmERR OBJECT-TYPE
			SYNTAX TruthValue
			MAX-ACCESS read-only
			STATUS current
			DESCRIPTION
				"Bip8 error - ONU."
			::= { zhoneOltOnuStatusEntry 2 }

		-- 1.3.6.1.4.1.5504.5.12.1.5.1.3
		zhoneOltOnuStatusPonAlarmSD OBJECT-TYPE
			SYNTAX TruthValue
			MAX-ACCESS read-only
			STATUS current
			DESCRIPTION
				"Signal Degraded alarm."
			::= { zhoneOltOnuStatusEntry 3 }

		-- 1.3.6.1.4.1.5504.5.12.1.5.1.4
		zhoneOltOnuStatusPonAlarmREI OBJECT-TYPE
			SYNTAX TruthValue
			MAX-ACCESS read-only
			STATUS current
			DESCRIPTION
				"Remote Error Indication."
			::= { zhoneOltOnuStatusEntry 4 }

		-- 1.3.6.1.4.1.5504.5.12.1.5.1.5
		zhoneOltOnuStatusPonAlarmMEM OBJECT-TYPE
			SYNTAX TruthValue
			MAX-ACCESS read-only
			STATUS current
			DESCRIPTION
				"Message Error Message."
			::= { zhoneOltOnuStatusEntry 5 }

		-- 1.3.6.1.4.1.5504.5.12.1.5.1.6
		zhoneOltOnuStatusPonAlarmRXINH OBJECT-TYPE
			SYNTAX TruthValue
			MAX-ACCESS read-only
			STATUS current
			DESCRIPTION
				"Rx alarm inhibit."
			::= { zhoneOltOnuStatusEntry 6 }

		-- 1.3.6.1.4.1.5504.5.12.1.5.1.7
		zhoneOltOnuStatusPonAlarmLOS OBJECT-TYPE
			SYNTAX TruthValue
			MAX-ACCESS read-only
			STATUS current
			DESCRIPTION
				"Description."
			::= { zhoneOltOnuStatusEntry 7 }

		-- 1.3.6.1.4.1.5504.5.12.1.5.1.8
		zhoneOltOnuStatusPonAlarmPEE OBJECT-TYPE
			SYNTAX TruthValue
			MAX-ACCESS read-only
			STATUS current
			DESCRIPTION
				"Description."
			::= { zhoneOltOnuStatusEntry 8 }

		-- 1.3.6.1.4.1.5504.5.12.1.5.1.9
		zhoneOltOnuStatusPonAlarmSUF OBJECT-TYPE
			SYNTAX TruthValue
			MAX-ACCESS read-only
			STATUS current
			DESCRIPTION
				"Description."
			::= { zhoneOltOnuStatusEntry 9 }

		-- 1.3.6.1.4.1.5504.5.12.1.5.1.10
		zhoneOltOnuStatusPonAlarmOAML OBJECT-TYPE
			SYNTAX TruthValue
			MAX-ACCESS read-only
			STATUS current
			DESCRIPTION
				"Description."
			::= { zhoneOltOnuStatusEntry 10 }

		-- 1.3.6.1.4.1.5504.5.12.1.5.1.11
		zhoneOltOnuStatusPonAlarmLCD OBJECT-TYPE
			SYNTAX TruthValue
			MAX-ACCESS read-only
			STATUS current
			DESCRIPTION
				"Description."
			::= { zhoneOltOnuStatusEntry 11 }

		-- 1.3.6.1.4.1.5504.5.12.1.6
		zhoneOnuConfigTable OBJECT-TYPE
			SYNTAX SEQUENCE OF ZhoneOnuConfigEntry
			MAX-ACCESS not-accessible
			STATUS current
			DESCRIPTION
				"Configuration information for the far-end (ONU) device."
			::= { zhoneAponMIB 6 }

		-- 1.3.6.1.4.1.5504.5.12.1.6.1
		zhoneOnuConfigEntry OBJECT-TYPE
			SYNTAX ZhoneOnuConfigEntry
			MAX-ACCESS not-accessible
			STATUS current
			DESCRIPTION
				"An entry in the ONU Config table."
			INDEX { ifIndex }
			::= { zhoneOnuConfigTable 1 }

		ZhoneOnuConfigEntry ::=
			SEQUENCE {
				zhoneOnuConfigSerialNumber
					Integer32,
				zhoneOnuConfigPassword
					ZhoneAdminString,
				zhoneOnuConfigNetworkRefClk
					TruthValue,
				zhoneOnuConfigHEC
					INTEGER,
				zhoneOnuConfigLoopback
					INTEGER,
				zhoneOnuConfigOverheadSize
					INTEGER,
				zhoneOnuConfigRfVideo
					INTEGER
			 }

		-- 1.3.6.1.4.1.5504.5.12.1.6.1.1
		zhoneOnuConfigSerialNumber OBJECT-TYPE
			SYNTAX Integer32 (1..2147483647)
			MAX-ACCESS read-only
			STATUS current
			DESCRIPTION
				"ONU serial number."
			::= { zhoneOnuConfigEntry 1 }

		-- 1.3.6.1.4.1.5504.5.12.1.6.1.2
		zhoneOnuConfigPassword OBJECT-TYPE
			SYNTAX ZhoneAdminString
			MAX-ACCESS read-write
			STATUS current
			DESCRIPTION
				"ONU password."
			::= { zhoneOnuConfigEntry 2 }

		-- 1.3.6.1.4.1.5504.5.12.1.6.1.3
		zhoneOnuConfigNetworkRefClk OBJECT-TYPE
			SYNTAX TruthValue
			MAX-ACCESS read-write
			STATUS current
			DESCRIPTION
				"Network reference clock usage flag."
			DEFVAL { false }
			::= { zhoneOnuConfigEntry 3 }

		-- 1.3.6.1.4.1.5504.5.12.1.6.1.4
		zhoneOnuConfigHEC OBJECT-TYPE
			SYNTAX INTEGER
				{
				onuOff(1),
				onuRxCorrectionOnly(2),
				onuTxGenerationOnly(3),
				onuRxAndTx(4)
				}
			MAX-ACCESS read-write
			STATUS current
			DESCRIPTION
				"Header Error Control."
			DEFVAL { onuRxAndTx }
			::= { zhoneOnuConfigEntry 4 }

		-- 1.3.6.1.4.1.5504.5.12.1.6.1.5
		zhoneOnuConfigLoopback OBJECT-TYPE
			SYNTAX INTEGER
				{
				onuNone(1),
				onuInward(2),
				onuLine(3)
				}
			MAX-ACCESS read-write
			STATUS current
			DESCRIPTION
				"Loopback mode for device."
			DEFVAL { onuLine }
			::= { zhoneOnuConfigEntry 5 }

		-- 1.3.6.1.4.1.5504.5.12.1.6.1.6
		zhoneOnuConfigOverheadSize OBJECT-TYPE
			SYNTAX INTEGER
				{
				onuOverheadSize3Bytes(1),
				onuOverheadSize6Bytes(2),
				onuOverheadSize12Bytes(3)
				}
			MAX-ACCESS read-write
			STATUS current
			DESCRIPTION
				"Overhead size definition field."
			DEFVAL { onuOverheadSize3Bytes }
			::= { zhoneOnuConfigEntry 6 }

		-- 1.3.6.1.4.1.5504.5.12.1.6.1.7
		zhoneOnuConfigRfVideo OBJECT-TYPE
			SYNTAX INTEGER
				{
				enabled(1),
				disabled(2)
				}
			MAX-ACCESS read-write
			STATUS current
			DESCRIPTION
				"Used to turn rf video on and off and to read current
				status of rf video."
			DEFVAL { enabled }
			::= { zhoneOnuConfigEntry 7 }

		-- 1.3.6.1.4.1.5504.5.12.1.7
		zhoneOnuStatusTable OBJECT-TYPE
			SYNTAX SEQUENCE OF ZhoneOnuStatusEntry
			MAX-ACCESS not-accessible
			STATUS current
			DESCRIPTION
				"Status and alarm information for the far-end (ONU) device."
			::= { zhoneAponMIB 7 }

		-- 1.3.6.1.4.1.5504.5.12.1.7.1
		zhoneOnuStatusEntry OBJECT-TYPE
			SYNTAX ZhoneOnuStatusEntry
			MAX-ACCESS not-accessible
			STATUS current
			DESCRIPTION
				"An entry in the ONU Status table."
			INDEX { ifIndex }
			::= { zhoneOnuStatusTable 1 }

		ZhoneOnuStatusEntry ::=
			SEQUENCE {
				zhoneOnuStatusOperStatus
					INTEGER,
				zhoneOnuStatusLoopback
					INTEGER,
				zhoneOnuStatusAlarmTF
					TruthValue,
				zhoneOnuStatusAlarmLOS
					TruthValue,
				zhoneOnuStatusAlarmPEE
					TruthValue,
				zhoneOnuStatusAlarmSUF
					TruthValue,
				zhoneOnuStatusAlarmOAML
					TruthValue,
				zhoneOnuStatusAlarmLCD
					TruthValue,
				zhoneOnuStatusAlarmFRML
					TruthValue,
				zhoneOnuStatusAlarmERR
					TruthValue,
				zhoneOnuStatusAlarmSD
					TruthValue,
				zhoneOnuStatusAlarmMEM
					TruthValue,
				zhoneOnuStatusAlarmDACT
					TruthValue,
				zhoneOnuStatusAlarmDIS
					TruthValue,
				zhoneOnuStatusAlarmMIS
					TruthValue,
				zhoneOnuStatusLastChange
					TimeStamp
			 }

		-- 1.3.6.1.4.1.5504.5.12.1.7.1.1
		zhoneOnuStatusOperStatus OBJECT-TYPE
			SYNTAX INTEGER
				{
				onuStateDown(1),
				onuStateUp(2)
				}
			MAX-ACCESS read-only
			STATUS current
			DESCRIPTION
				"Operational status."
			::= { zhoneOnuStatusEntry 1 }

		-- 1.3.6.1.4.1.5504.5.12.1.7.1.2
		zhoneOnuStatusLoopback OBJECT-TYPE
			SYNTAX INTEGER
				{
				onuNone(1),
				onuInward(2),
				onuLine(3)
				}
			MAX-ACCESS read-only
			STATUS current
			DESCRIPTION
				"Loopback status."
			::= { zhoneOnuStatusEntry 2 }

		-- 1.3.6.1.4.1.5504.5.12.1.7.1.3
		zhoneOnuStatusAlarmTF OBJECT-TYPE
			SYNTAX TruthValue
			MAX-ACCESS read-only
			STATUS current
			DESCRIPTION
				"Transmitter Failure - The ONU transmitter is declared in failure
				when there is no nominal backfacet photocurrent or when the drive
				currents go beyond the maximum specification."
			::= { zhoneOnuStatusEntry 3 }

		-- 1.3.6.1.4.1.5504.5.12.1.7.1.4
		zhoneOnuStatusAlarmLOS OBJECT-TYPE
			SYNTAX TruthValue
			MAX-ACCESS read-only
			STATUS current
			DESCRIPTION
				"Loss Of Signal - No valid optical signal. E.g. this can be
				generated by the logical function (OAML.AND.FRML.AND.LCD)."
			::= { zhoneOnuStatusEntry 4 }

		-- 1.3.6.1.4.1.5504.5.12.1.7.1.5
		zhoneOnuStatusAlarmPEE OBJECT-TYPE
			SYNTAX TruthValue
			MAX-ACCESS read-only
			STATUS current
			DESCRIPTION
				"Physical Equipment Error - When the ONU receives a PEE message."
			::= { zhoneOnuStatusEntry 5 }

		-- 1.3.6.1.4.1.5504.5.12.1.7.1.6
		zhoneOnuStatusAlarmSUF OBJECT-TYPE
			SYNTAX TruthValue
			MAX-ACCESS read-only
			STATUS current
			DESCRIPTION
				"Startup Failure - The ranging of this ONU has failed (see ranging
				protocol for exact condition)."
			::= { zhoneOnuStatusEntry 6 }

		-- 1.3.6.1.4.1.5504.5.12.1.7.1.7
		zhoneOnuStatusAlarmOAML OBJECT-TYPE
			SYNTAX TruthValue
			MAX-ACCESS read-only
			STATUS current
			DESCRIPTION
				"PLOAM Cell Loss - When three consecutive PLOAM headers are wrong."
			::= { zhoneOnuStatusEntry 7 }

		-- 1.3.6.1.4.1.5504.5.12.1.7.1.8
		zhoneOnuStatusAlarmLCD OBJECT-TYPE
			SYNTAX TruthValue
			MAX-ACCESS read-only
			STATUS current
			DESCRIPTION
				"Loss of Cell Delineation - When seven consecutive ATM
				cells have an invalid HEC."
			::= { zhoneOnuStatusEntry 8 }

		-- 1.3.6.1.4.1.5504.5.12.1.7.1.9
		zhoneOnuStatusAlarmFRML OBJECT-TYPE
			SYNTAX TruthValue
			MAX-ACCESS read-only
			STATUS current
			DESCRIPTION
				"Loss Of Downstream Frame - When the frame bit is 0
				for three consecutive frames."
			::= { zhoneOnuStatusEntry 9 }

		-- 1.3.6.1.4.1.5504.5.12.1.7.1.10
		zhoneOnuStatusAlarmERR OBJECT-TYPE
			SYNTAX TruthValue
			MAX-ACCESS read-only
			STATUS current
			DESCRIPTION
				"Block Error Detection - The downstream received BIP8 is
				compared with the calculated BIP8 on the received stream.
				The number of differing bits is accumulated in ERR. At
				regular intervals, the content is sent via REI to the OLT.
				This interval is programmed by the OLT with a
				BER_interval_timer message.

				ERR is renewed at every reception of a downstream PLOAM cell.
"
			::= { zhoneOnuStatusEntry 10 }

		-- 1.3.6.1.4.1.5504.5.12.1.7.1.11
		zhoneOnuStatusAlarmSD OBJECT-TYPE
			SYNTAX TruthValue
			MAX-ACCESS read-only
			STATUS current
			DESCRIPTION
				"Signal Degraded - Set active when the downstream BER >= 10E-5"
			::= { zhoneOnuStatusEntry 11 }

		-- 1.3.6.1.4.1.5504.5.12.1.7.1.12
		zhoneOnuStatusAlarmMEM OBJECT-TYPE
			SYNTAX TruthValue
			MAX-ACCESS read-only
			STATUS current
			DESCRIPTION
				"Message Error Message - When the ONU receives an unknown message."
			::= { zhoneOnuStatusEntry 12 }

		-- 1.3.6.1.4.1.5504.5.12.1.7.1.13
		zhoneOnuStatusAlarmDACT OBJECT-TYPE
			SYNTAX TruthValue
			MAX-ACCESS read-only
			STATUS current
			DESCRIPTION
				"De-activate PON-ID - It instructs the ONU to deactivate itself."
			::= { zhoneOnuStatusEntry 13 }

		-- 1.3.6.1.4.1.5504.5.12.1.7.1.14
		zhoneOnuStatusAlarmDIS OBJECT-TYPE
			SYNTAX TruthValue
			MAX-ACCESS read-only
			STATUS current
			DESCRIPTION
				"Disabled ONU - When the ONU receives a Disable_serial_number
				message with it's own serial number and the enable flag=0xFF.
				It stays in this state even after power off."
			::= { zhoneOnuStatusEntry 14 }

		-- 1.3.6.1.4.1.5504.5.12.1.7.1.15
		zhoneOnuStatusAlarmMIS OBJECT-TYPE
			SYNTAX TruthValue
			MAX-ACCESS read-only
			STATUS current
			DESCRIPTION
				"Link Mismatching - The ONU detects that the received PST and
				transmitted PST are different."
			::= { zhoneOnuStatusEntry 15 }

		-- 1.3.6.1.4.1.5504.5.12.1.7.1.16
		zhoneOnuStatusLastChange OBJECT-TYPE
			SYNTAX TimeStamp
			MAX-ACCESS read-only
			STATUS current
			DESCRIPTION
				"Time of last line status change."
			DEFVAL { '0'b }
			::= { zhoneOnuStatusEntry 16 }

		-- 1.3.6.1.4.1.5504.5.12.1.8
		zhoneOltTrafficContainerIndexNext OBJECT-TYPE
			SYNTAX Integer32 (0..65535)
			MAX-ACCESS read-only
			STATUS current
			DESCRIPTION
				"This object contains an appropriate value to be used for
				the zhoneOltTrafficContainerIndex when creating entries
				in the zhoneOltTrafficContainerTable.  The value 0 indicates
				that no unassigned entries are available. To obtain the
				zhoneOltTrafficContainerIndex value for a new entry, the
				manager issues a management protocol retrieval operation to
				obtain the current value of this object.  After each
				retrieval, the agent should modify the value to the next
				unassigned index.

				After a manager retrieves a value the agent will determine
				through its local policy when this index value will be made
				available for reuse.
				"
			::= { zhoneAponMIB 8 }

		-- 1.3.6.1.4.1.5504.5.12.1.9
		zhoneOltTrafficContainerTable OBJECT-TYPE
			SYNTAX SEQUENCE OF ZhoneOltTrafficContainerEntry
			MAX-ACCESS not-accessible
			STATUS current
			DESCRIPTION
				"Traffic Container definitions for the OLT."
			::= { zhoneAponMIB 9 }

		-- 1.3.6.1.4.1.5504.5.12.1.9.1
		zhoneOltTrafficContainerEntry OBJECT-TYPE
			SYNTAX ZhoneOltTrafficContainerEntry
			MAX-ACCESS not-accessible
			STATUS current
			DESCRIPTION
				"Description."
			INDEX { zhoneOltTrafficContainerIndex }
			::= { zhoneOltTrafficContainerTable 1 }

		ZhoneOltTrafficContainerEntry ::=
			SEQUENCE {
				zhoneOltTrafficContainerIndex
					Integer32,
				zhoneOltTrafficContainerGuaranteedBW
					Unsigned32,
				zhoneOltTrafficContainerMaximumBW
					Unsigned32,
				zhoneOltTrafficContainerCBR
					TruthValue,
				zhoneOltTrafficContainerCbrCompensate
					TruthValue,
				zhoneOltTrafficContainerRowStatus
					ZhoneRowStatus
			 }

		-- 1.3.6.1.4.1.5504.5.12.1.9.1.1
		zhoneOltTrafficContainerIndex OBJECT-TYPE
			SYNTAX Integer32 (1..65535)
			MAX-ACCESS not-accessible
			STATUS current
			DESCRIPTION
				"A unique value to identify this traffic container entry."
			::= { zhoneOltTrafficContainerEntry 1 }

		-- 1.3.6.1.4.1.5504.5.12.1.9.1.2
		zhoneOltTrafficContainerGuaranteedBW OBJECT-TYPE
			SYNTAX Unsigned32 (0..2147483647)
			UNITS "Megabits per second"
			MAX-ACCESS read-create
			STATUS current
			DESCRIPTION
				"The maximum guareented bandwidth is downstream bit rate
				divided by number of ONUs.  For this incarnation, it is
				622 / 32 = 19.4"
			DEFVAL { 0 }
			::= { zhoneOltTrafficContainerEntry 2 }

		-- 1.3.6.1.4.1.5504.5.12.1.9.1.3
		zhoneOltTrafficContainerMaximumBW OBJECT-TYPE
			SYNTAX Unsigned32 (0..2147483647)
			MAX-ACCESS read-create
			STATUS current
			DESCRIPTION
				"Maximum bandwidth for a PON channel.  The maximum
				bandwidth is downstream bit rate divided by the
				number of ONUs.  For this incarnation, it is
				622 / 32 = 19.4"
			::= { zhoneOltTrafficContainerEntry 3 }

		-- 1.3.6.1.4.1.5504.5.12.1.9.1.4
		zhoneOltTrafficContainerCBR OBJECT-TYPE
			SYNTAX TruthValue
			MAX-ACCESS read-create
			STATUS current
			DESCRIPTION
				"Constant Bit Rate - describes the nature of the traffic
				on the channel.  A TRUE setting implies that the data
				stream will be of a constant nature.  FALSE implies that
				the traffic will be bursty."
			DEFVAL { true }
			::= { zhoneOltTrafficContainerEntry 4 }

		-- 1.3.6.1.4.1.5504.5.12.1.9.1.5
		zhoneOltTrafficContainerCbrCompensate OBJECT-TYPE
			SYNTAX TruthValue
			MAX-ACCESS read-create
			STATUS current
			DESCRIPTION
				"A flag for ranging compensation.  When a ranging window
				is opened, the Grant Handler appends to the end of the
				ranging window all the grants missed due to the ranging
				window by CBR flows with the compensation flag set."
			DEFVAL { false }
			::= { zhoneOltTrafficContainerEntry 5 }

		-- 1.3.6.1.4.1.5504.5.12.1.9.1.6
		zhoneOltTrafficContainerRowStatus OBJECT-TYPE
			SYNTAX ZhoneRowStatus
			MAX-ACCESS read-create
			STATUS current
			DESCRIPTION
				"Row status of the traffic container entry.  This field
				must be initially set to 'createAndGo'."
			::= { zhoneOltTrafficContainerEntry 6 }

		-- 1.3.6.1.4.1.5504.5.12.3
		zhoneAponTraps OBJECT-IDENTITY
			STATUS current
			DESCRIPTION
				"Definitions for Atm PON traps."
			::= { zhoneApon 3 }

		-- 1.3.6.1.4.1.5504.5.12.3.0
		zhoneAPONV2Traps OBJECT-IDENTITY
			STATUS current
			DESCRIPTION
				"APON Olt and Onu Traps."
			::= { zhoneAponTraps 0 }

		-- 1.3.6.1.4.1.5504.5.12.3.0.1
		zhoneOltLineStatusChangeTrap NOTIFICATION-TYPE
			OBJECTS { zhoneOltStatusLastChange, ifAlias }
			STATUS current
			DESCRIPTION
				"Line status change trap for the OLT APON interface."
			::= { zhoneAPONV2Traps 1 }

		-- 1.3.6.1.4.1.5504.5.12.3.0.2
		zhoneOnuLineStatusChangeTrap NOTIFICATION-TYPE
			OBJECTS { zhoneOnuStatusLastChange, ifAlias }
			STATUS current
			DESCRIPTION
				"Line status change trap for a particular Onu APON interface."
			::= { zhoneAPONV2Traps 2 }

		-- 1.3.6.1.4.1.5504.9.1.2
		zhoneAponOltConfigGroup OBJECT-GROUP
			OBJECTS { zhoneOltConfigCellScrambling, zhoneOltConfigBip8, zhoneOltConfigHec, zhoneOltConfigHecRxBypass, zhoneOltConfigCrcRx,
				zhoneOltConfigOverheadSize, zhoneOltConfigDelimiterPattern, zhoneOltConfigDelimiterSize, zhoneOltConfigCdrPattern, zhoneOltConfigCdrLocation,
				zhoneOltConfigCdrActiveHigh, zhoneOltConfigCpeLimit, zhoneOltConfigLcdLimit, zhoneOltConfigLcdAlpha, zhoneOltConfigLcdDelta,
				zhoneOltConfigTxDiscardNonMatchingVpi, zhoneOltConfigUtopiaDiscard, zhoneOltConfigLineStatusChangeTrapEnable, zhoneOltConfigLoopback, zhoneOltConfigAutoLearn,
				zhoneOltConfigSyncBytesClkDivisor, zhoneOltConfigTxSyncBytes, zhoneOltConfigMaxPonDistance }
			STATUS current
			DESCRIPTION
				"OLT Config objects."
			::= { zhoneGroups 2 }

		-- 1.3.6.1.4.1.5504.9.1.3
		zhoneAponOltStatusGroup OBJECT-GROUP
			OBJECTS { zhoneOltStatusState, zhoneOltStatusLoopback, zhoneOltStatusPonAlarmLPHY, zhoneOltStatusPonAlarmTF, zhoneOltStatusPonAlarmSUF,
				zhoneOltStatusPonAlarmPEE, zhoneOltStatusPonAlarmLCD, zhoneOltStatusPonAlarmLOS, zhoneOltStatusPonAlarmOAML, zhoneOltStatusPonAlarmCPE,
				zhoneOltStatusLastChange }
			STATUS current
			DESCRIPTION
				"Zhone ATM-PON OLT Status objects."
			::= { zhoneGroups 3 }

		-- 1.3.6.1.4.1.5504.9.1.4
		zhoneAponOltOnuConfigGroup OBJECT-GROUP
			OBJECTS { zhoneOltOnuConfigPassword, zhoneOltOnuConfigSerialNum, zhoneOltOnuConfigChurnkey, zhoneOltOnuConfigLineStatusChangeTrapEnable }
			STATUS current
			DESCRIPTION
				"Zhone ATM-PON ONU Config objects."
			::= { zhoneGroups 4 }

		-- 1.3.6.1.4.1.5504.9.1.5
		zhoneAponOltOnuStatusGroup OBJECT-GROUP
			OBJECTS { zhoneOltOnuStatusPonAlarmLOA, zhoneOltOnuStatusPonAlarmERR, zhoneOltOnuStatusPonAlarmSD, zhoneOltOnuStatusPonAlarmREI, zhoneOltOnuStatusPonAlarmMEM,
				zhoneOltOnuStatusPonAlarmRXINH }
			STATUS current
			DESCRIPTION
				"Zhone ATM-PON ONU Status objects."
			::= { zhoneGroups 5 }

		-- 1.3.6.1.4.1.5504.9.1.6
		zhoneAponOnuConfigGroup OBJECT-GROUP
			OBJECTS { zhoneOnuConfigSerialNumber, zhoneOnuConfigPassword, zhoneOnuConfigNetworkRefClk, zhoneOnuConfigHEC, zhoneOnuConfigLoopback,
				zhoneOnuConfigOverheadSize }
			STATUS current
			DESCRIPTION
				"ONU configuration information."
			::= { zhoneGroups 6 }

		-- 1.3.6.1.4.1.5504.9.1.7
		zhoneAponOnuStatusGroup OBJECT-GROUP
			OBJECTS { zhoneOnuStatusLoopback, zhoneOnuStatusAlarmTF, zhoneOnuStatusAlarmLOS, zhoneOnuStatusAlarmPEE, zhoneOnuStatusAlarmSUF,
				zhoneOnuStatusAlarmOAML, zhoneOnuStatusAlarmLCD, zhoneOnuStatusAlarmFRML, zhoneOnuStatusAlarmERR, zhoneOnuStatusAlarmSD,
				zhoneOnuStatusAlarmMEM, zhoneOnuStatusAlarmDACT, zhoneOnuStatusAlarmDIS, zhoneOnuStatusAlarmMIS, zhoneOnuStatusOperStatus
				 }
			STATUS current
			DESCRIPTION
				"ONU status and alarm information."
			::= { zhoneGroups 7 }

		-- 1.3.6.1.4.1.5504.9.1.8
		zhoneAponOltTrafficContainerGroup OBJECT-GROUP
			OBJECTS { zhoneOltTrafficContainerMaximumBW, zhoneOltTrafficContainerCBR, zhoneOltTrafficContainerIndexNext, zhoneOltTrafficContainerCbrCompensate, zhoneOltTrafficContainerRowStatus,
				zhoneOltTrafficContainerGuaranteedBW }
			STATUS current
			DESCRIPTION
				"OLT Traffic Container objects."
			::= { zhoneGroups 8 }

		-- 1.3.6.1.4.1.5504.9.1.9
		zhoneAponTrapsGroup NOTIFICATION-GROUP
			NOTIFICATIONS { zhoneOltLineStatusChangeTrap }
			STATUS current
			DESCRIPTION
				"Atm PON traps group."
			::= { zhoneGroups 9 }


	END

--
-- phyAPON.mib
--
