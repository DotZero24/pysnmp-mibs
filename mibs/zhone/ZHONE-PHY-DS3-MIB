--
-- ZHONE-PHY-DS3-MIB.my
-- MIB generated by MG-SOFT Visual MIB Builder Version 2.1 Build 205
-- Wednesday, May 16, 2001 at 19:25:19
--

-- The ZHONE profile definition for DS3_Profile used here can be found
-- in rfc2496.mib. We use this profile here to include the
-- values from the dsx3ConfigExtTable

	ZHONE-PHY-DS3-MIB DEFINITIONS ::= BEGIN

		IMPORTS
			dsx3ConfigEntry
				FROM DS3-MIB
			OBJECT-GROUP
				FROM SNMPv2-CONF
			OBJECT-TYPE, MODULE-IDENTITY
				FROM SNMPv2-SMI
			TruthValue
				FROM SNMPv2-TC
			zhoneDs3Ext, zhoneModules
				FROM Zhone;


		phyDs3 MODULE-IDENTITY
			LAST-UPDATED "200105151435Z"
			ORGANIZATION
				"Zhone Technologies, Inc."
			CONTACT-INFO
				"  Postal:
				Zhone Technologies, Inc.
				@ Zhone Way
				7001 Oakport Street
				Oakland, CA  94621
				USA
				Toll-Free: +1 877-ZHONE20 (+1 877-946-6320)
				Tel: +1-510-777-7000
				Fax: +1-510-777-7001
				E-mail: support@zhone.com"
			DESCRIPTION
				"DS3 physical MIB to configure and monitor DS3 physical
				attributes.
				"
			REVISION "200105141435Z"
			DESCRIPTION
				"V01.02.00 - Add Atm Framing Support."
			REVISION "200104251425Z"
			DESCRIPTION
				"V01.01.00 - Add E3 Framing Support."
			REVISION "200103150834Z"
			DESCRIPTION
				"V01.00.00 - Initial Release"
			::= { zhoneModules 17 }



--
-- Node definitions
--

		dsx3ConfigExtGroup OBJECT-GROUP
			OBJECTS { dsx3ConfigExtScrambleEnabled, dsx3ConfigExtE3Framing, dsx3ConfigExtAtmFraming }
			STATUS current
			DESCRIPTION
				"Description."
			::= { zhoneDs3Ext 1 }

		dsx3ConfigExtTable OBJECT-TYPE
			SYNTAX SEQUENCE OF Ds3MediumExtEntry
			MAX-ACCESS not-accessible
			STATUS current
			DESCRIPTION
				"This is an extenion of the standard Ds3 MIB (RFC 2496)."
			::= { zhoneDs3Ext 2 }

		dsx3ConfigExtEntry OBJECT-TYPE
			SYNTAX Ds3MediumExtEntry
			MAX-ACCESS not-accessible
			STATUS current
			DESCRIPTION
				"Each row is an extension to the dsx3ConfigExtTable for Zhone
				specific fields. This row is created when the augmented
				dsx3ConfigEntry is created."
			AUGMENTS { dsx3ConfigEntry }
			::= { dsx3ConfigExtTable 1 }

		Ds3MediumExtEntry ::=
			SEQUENCE {
				dsx3ConfigExtScrambleEnabled
					TruthValue,
				dsx3ConfigExtE3Framing
					INTEGER,
				dsx3ConfigExtAtmFraming
					INTEGER
			 }

--
		dsx3ConfigExtScrambleEnabled OBJECT-TYPE
			SYNTAX TruthValue
			MAX-ACCESS read-write
			STATUS current
			DESCRIPTION
				"This field describes the enabled status of the Ds3 Scramble mode. If this
				field is true(1) then Scramble mode is enabled, if this field is
				false(2) scramble mode is disable."
			DEFVAL { true }
			::= { dsx3ConfigExtEntry 1 }

--
		dsx3ConfigExtE3Framing OBJECT-TYPE
			SYNTAX INTEGER
				{
				e3FrameOther(1),
				e3FrameG832(2),
				e3FrameG751(3)
				}
			MAX-ACCESS read-write
			STATUS current
			DESCRIPTION
				"This field describes the status of the E3 Framing mode.
				If this field is 	e3FrameG832(2) then E3 Framing Format will be G832,
				if this field is e3FrameG751 then E3 Framing Format  will be G751."
			DEFVAL { e3FrameG832 }
			::= { dsx3ConfigExtEntry 2 }

--
		dsx3ConfigExtAtmFraming OBJECT-TYPE
			SYNTAX INTEGER
				{
				dsx3AtmFramingOther(1),
				dsx3AtmFramingPLCP(2),
				dsx3AtmFramingDirectCellMapped(3)
				}
			MAX-ACCESS read-write
			STATUS current
			DESCRIPTION
				"This field describes the status of the Atm Framing mode.
				If this field is PLCP(2) then Atm Framing Format will be PLCP,
				if this field is DirectCellMapped(3) then Atm Framing Format will be
				            Direct Cell Mapped."
			DEFVAL { dsx3AtmFramingDirectCellMapped }
			::= { dsx3ConfigExtEntry 3 }


	END

--
-- ZHONE-PHY-DS3-MIB.my
--
