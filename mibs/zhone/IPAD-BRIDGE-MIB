-- $Header:   K:/WanSuite/archives/include/pvcs/ipadbridge.mib,v   1.0   17 Sep 2001 14:53:28   Walterm  $

IPAD-BRIDGE-MIB DEFINITIONS ::= BEGIN

IMPORTS OBJECT-TYPE, MODULE-IDENTITY  FROM SNMPv2-SMI
-- IpAddress, TimeTicks,OBJECT-TYPE, MODULE-IDENTITY  FROM SNMPv2-SMI
	DisplayString                                  FROM SNMPv2-TC
  	ipad                                           FROM IPADv2-MIB;

ipadBridge MODULE-IDENTITY
         LAST-UPDATED "0003270001Z"
         ORGANIZATION "Verilink Corporation"
         CONTACT-INFO
             "support@verilink.com
             1-800-926-0085"
         DESCRIPTION
            "The IPAD BRIDGE MIB."
         ::= { ipad 28 }

ipadBridgeParms          			OBJECT IDENTIFIER ::= { ipadBridge 1 }

ipadBridgeManagementMacAddress OBJECT-TYPE
    SYNTAX  OCTET STRING
    MAX-ACCESS  read-write
    STATUS  current
    DESCRIPTION
        ""
    ::= { ipadBridgeParms 1 }

ipadBridgeEnable       OBJECT-TYPE
    SYNTAX  INTEGER{
		    other(1),
		    disable(2),
		    enable(3)
		    }
    MAX-ACCESS  read-write
    STATUS  current
    DESCRIPTION
        ""
    ::= { ipadBridgeParms 2 }


-- Bridge Port parameters

ipadBridgePortTable OBJECT-TYPE
    SYNTAX    SEQUENCE OF IpadBridgePortTableEntry
    MAX-ACCESS  not-accessible
    STATUS    current
    DESCRIPTION
        "Table of Bridge parameters."
    ::= { ipadBridge 2 }

ipadBridgePortTableEntry OBJECT-TYPE
    SYNTAX  IpadBridgePortTableEntry
    MAX-ACCESS  not-accessible
    STATUS  current
    DESCRIPTION
        "An entry in the ipad Bridge port table."
    INDEX   { ipadBridgePortIndex }
    ::= { ipadBridgePortTable 1 }

IpadBridgePortTableEntry ::=
    SEQUENCE
    {
    ipadBridgePortIndex               			INTEGER,
    ipadBridgePortEndpoint  	      			DisplayString,
    ipadBridgePortBPDUOption	      			INTEGER,
    ipadBridgePortMulticastAddrDest	  		INTEGER,
    ipadBridgePortBroadcastAddrDest		      	INTEGER,
    ipadBridgePortForwardIpFramesOnly		      	INTEGER
    }

ipadBridgePortIndex       OBJECT-TYPE
    SYNTAX  INTEGER
    MAX-ACCESS  read-only
    STATUS  current
    DESCRIPTION
        "The index into the Bridge table."
    ::= { ipadBridgePortTableEntry 1 }


ipadBridgePortEndpoint       OBJECT-TYPE
    SYNTAX  DisplayString
    MAX-ACCESS  read-write
    STATUS  current
    DESCRIPTION
        ""
    ::= { ipadBridgePortTableEntry 2 }


ipadBridgePortBPDUOption       OBJECT-TYPE
    SYNTAX  INTEGER{
		    other(1),
		    disable(2),
		    enable(3)
		    }
    MAX-ACCESS  read-write
    STATUS  current
    DESCRIPTION
        ""
    ::= { ipadBridgePortTableEntry 3 }


ipadBridgePortMulticastAddrDest       OBJECT-TYPE
    SYNTAX  INTEGER{
		    other(1),
		    no(2),
		    yes(3)
		    }
    MAX-ACCESS  read-write
    STATUS  current
    DESCRIPTION
        ""
    ::= { ipadBridgePortTableEntry 4 }


ipadBridgePortBroadcastAddrDest       OBJECT-TYPE
    SYNTAX  INTEGER {
		    other(1),
		    no(2),
		    yes(3)
		    }
    MAX-ACCESS  read-write
    STATUS  current
    DESCRIPTION
        ""
    ::= { ipadBridgePortTableEntry 5 }


ipadBridgePortForwardIpFramesOnly       OBJECT-TYPE
    SYNTAX  INTEGER{
		    other(1),
		    no(2),
		    yes(3)
		    }
    MAX-ACCESS  read-write
    STATUS  current
    DESCRIPTION
        ""
    ::= { ipadBridgePortTableEntry 6 }

ipadBridgePortAdd       OBJECT-TYPE
    SYNTAX  INTEGER{
    		     other(1),
    		     addnew(2)
    		    }
    MAX-ACCESS  read-write
    STATUS  current
    DESCRIPTION
        ""
    ::= { ipadBridgeParms 3 }

ipadBridgePortDelete       OBJECT-TYPE
    SYNTAX  INTEGER
    MAX-ACCESS  read-write
    STATUS  current
    DESCRIPTION
        ""
    ::= { ipadBridgeParms 4 }



END
