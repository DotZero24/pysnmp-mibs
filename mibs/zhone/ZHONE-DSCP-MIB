--
-- zhoneDSCP.mib
-- MIB generated by MG-SOFT Visual MIB Builder Version 3.0 Build 285
-- Monday, June 07, 2010 at 05:42:46
--

    ZHONE-DSCP-MIB DEFINITIONS ::= BEGIN

        IMPORTS
            OBJECT-GROUP
                FROM SNMPv2-CONF
            Integer32, OBJECT-TYPE, MODULE-IDENTITY
                FROM SNMPv2-SMI
            RowStatus
                FROM SNMPv2-TC
            zhoneIp
                FROM Zhone;


--
-- CFG -----------------------------------------------------------------
--
--
-- BUILD --------------------------------------------------------------
--
-- mibcomp rfc1907.mib iftype.mib rfc2233.mib Zhone.mib -stub -o zhoneDscpMibHdlr.c zhoneDSCP.mib
-- /vob/zhonetools/bin/pahrser.pl -css rfc1907.mib iftype.mib rfc2233.mib ./Zhone.mib ./zhoneDSCP.mib
--
        -- 1.3.6.1.4.1.5504.4.1.22
        dscpProfile MODULE-IDENTITY
            LAST-UPDATED "201006030603Z"		-- June 03, 2010 at 06:03 GMT
            ORGANIZATION
                "Zhone Technologies, Inc."
            CONTACT-INFO
                "Postal:
                Zhone Technologies, Inc.
                @ Zhone Way
                7001 Oakport Street
                Oakland, CA  94621
                USA
                Toll-Free: +1 877-ZHONE20 (+1 877-946-6320)
                Tel: +1-510-777-7000
                Fax: +1-510-777-7001
                E-mail: support@zhone.com"
            DESCRIPTION
                "This is the Zhone module identifier for the Zhone DSCP (differentiated services code point) definition."
            ::= { zhoneIp 22 }




--
-- Node definitions
--

        -- 1.3.6.1.4.1.5504.4.1.22.1
        dscpProfileTable OBJECT-TYPE
            SYNTAX SEQUENCE OF DscpProfileEntry
            MAX-ACCESS not-accessible
            STATUS current
            DESCRIPTION
                "Zhone extension table for DSCP rule usage."
            ::= { dscpProfile 1 }


        -- 1.3.6.1.4.1.5504.4.1.22.1.1
        dscpProfileEntry OBJECT-TYPE
            SYNTAX DscpProfileEntry
            MAX-ACCESS not-accessible
            STATUS current
            DESCRIPTION
                "Zhone extension entry for DSCP rule usage."
            INDEX { dscpIndex }
            ::= { dscpProfileTable 1 }


        DscpProfileEntry ::=
            SEQUENCE {
                dscpIndex
                    Integer32,
                dscpProfileRowStatus
                    RowStatus,
                dscp00map8021p
                    Integer32,
                dscp01map8021p
                    Integer32,
                dscp02map8021p
                    Integer32,
                dscp03map8021p
                    Integer32,
                dscp04map8021p
                    Integer32,
                dscp05map8021p
                    Integer32,
                dscp06map8021p
                    Integer32,
                dscp07map8021p
                    Integer32,
                dscp08map8021p
                    Integer32,
                dscp09map8021p
                    Integer32,
                dscp10map8021p
                    Integer32,
                dscp11map8021p
                    Integer32,
                dscp12map8021p
                    Integer32,
                dscp13map8021p
                    Integer32,
                dscp14map8021p
                    Integer32,
                dscp15map8021p
                    Integer32,
                dscp16map8021p
                    Integer32,
                dscp17map8021p
                    Integer32,
                dscp18map8021p
                    Integer32,
                dscp19map8021p
                    Integer32,
                dscp20map8021p
                    Integer32,
                dscp21map8021p
                    Integer32,
                dscp22map8021p
                    Integer32,
                dscp23map8021p
                    Integer32,
                dscp24map8021p
                    Integer32,
                dscp25map8021p
                    Integer32,
                dscp26map8021p
                    Integer32,
                dscp27map8021p
                    Integer32,
                dscp28map8021p
                    Integer32,
                dscp29map8021p
                    Integer32,
                dscp30map8021p
                    Integer32,
                dscp31map8021p
                    Integer32,
                dscp32map8021p
                    Integer32,
                dscp33map8021p
                    Integer32,
                dscp34map8021p
                    Integer32,
                dscp35map8021p
                    Integer32,
                dscp36map8021p
                    Integer32,
                dscp37map8021p
                    Integer32,
                dscp38map8021p
                    Integer32,
                dscp39map8021p
                    Integer32,
                dscp40map8021p
                    Integer32,
                dscp41map8021p
                    Integer32,
                dscp42map8021p
                    Integer32,
                dscp43map8021p
                    Integer32,
                dscp44map8021p
                    Integer32,
                dscp45map8021p
                    Integer32,
                dscp46map8021p
                    Integer32,
                dscp47map8021p
                    Integer32,
                dscp48map8021p
                    Integer32,
                dscp49map8021p
                    Integer32,
                dscp50map8021p
                    Integer32,
                dscp51map8021p
                    Integer32,
                dscp52map8021p
                    Integer32,
                dscp53map8021p
                    Integer32,
                dscp54map8021p
                    Integer32,
                dscp55map8021p
                    Integer32,
                dscp56map8021p
                    Integer32,
                dscp57map8021p
                    Integer32,
                dscp58map8021p
                    Integer32,
                dscp59map8021p
                    Integer32,
                dscp60map8021p
                    Integer32,
                dscp61map8021p
                    Integer32,
                dscp62map8021p
                    Integer32,
                dscp63map8021p
                    Integer32
             }

        -- 1.3.6.1.4.1.5504.4.1.22.1.1.1
        dscpIndex OBJECT-TYPE
            SYNTAX Integer32 (1)
            MAX-ACCESS not-accessible
            STATUS current
            DESCRIPTION
                "Index for the conceptual row associating an entry from
                this table to a unique DSCP instance."
            ::= { dscpProfileEntry 1 }


        -- 1.3.6.1.4.1.5504.4.1.22.1.1.2
        dscpProfileRowStatus OBJECT-TYPE
            SYNTAX RowStatus
            MAX-ACCESS read-write
            STATUS current
            DESCRIPTION
                "For creating, modifying, and deleting this row."
            ::= { dscpProfileEntry 2 }


--
        -- 1.3.6.1.4.1.5504.4.1.22.1.1.3
        dscp00map8021p OBJECT-TYPE
            SYNTAX Integer32 (0..7)
            MAX-ACCESS read-write
            STATUS current
            DESCRIPTION
                "The desired 802.1p setting corresponding to DSCP value 0."
            ::= { dscpProfileEntry 3 }


        -- 1.3.6.1.4.1.5504.4.1.22.1.1.4
        dscp01map8021p OBJECT-TYPE
            SYNTAX Integer32 (0..7)
            MAX-ACCESS read-write
            STATUS current
            DESCRIPTION
                "The desired 802.1p setting corresponding to DSCP value 1."
            ::= { dscpProfileEntry 4 }


        -- 1.3.6.1.4.1.5504.4.1.22.1.1.5
        dscp02map8021p OBJECT-TYPE
            SYNTAX Integer32 (0..7)
            MAX-ACCESS read-write
            STATUS current
            DESCRIPTION
                "The desired 802.1p setting corresponding to DSCP value 2."
            ::= { dscpProfileEntry 5 }


        -- 1.3.6.1.4.1.5504.4.1.22.1.1.6
        dscp03map8021p OBJECT-TYPE
            SYNTAX Integer32 (0..7)
            MAX-ACCESS read-write
            STATUS current
            DESCRIPTION
                "The desired 802.1p setting corresponding to DSCP value 3."
            ::= { dscpProfileEntry 6 }


        -- 1.3.6.1.4.1.5504.4.1.22.1.1.7
        dscp04map8021p OBJECT-TYPE
            SYNTAX Integer32 (0..7)
            MAX-ACCESS read-write
            STATUS current
            DESCRIPTION
                "The desired 802.1p setting corresponding to DSCP value 4."
            ::= { dscpProfileEntry 7 }


--
        -- 1.3.6.1.4.1.5504.4.1.22.1.1.8
        dscp05map8021p OBJECT-TYPE
            SYNTAX Integer32 (0..7)
            MAX-ACCESS read-write
            STATUS current
            DESCRIPTION
                "The desired 802.1p setting corresponding to DSCP value 5."
            ::= { dscpProfileEntry 8 }


        -- 1.3.6.1.4.1.5504.4.1.22.1.1.9
        dscp06map8021p OBJECT-TYPE
            SYNTAX Integer32 (0..7)
            MAX-ACCESS read-write
            STATUS current
            DESCRIPTION
                "The desired 802.1p setting corresponding to DSCP value 6."
            ::= { dscpProfileEntry 9 }


        -- 1.3.6.1.4.1.5504.4.1.22.1.1.10
        dscp07map8021p OBJECT-TYPE
            SYNTAX Integer32 (0..7)
            MAX-ACCESS read-write
            STATUS current
            DESCRIPTION
                "The desired 802.1p setting corresponding to DSCP value 7."
            ::= { dscpProfileEntry 10 }


        -- 1.3.6.1.4.1.5504.4.1.22.1.1.11
        dscp08map8021p OBJECT-TYPE
            SYNTAX Integer32 (0..7)
            MAX-ACCESS read-write
            STATUS current
            DESCRIPTION
                "The desired 802.1p setting corresponding to DSCP value 8."
            ::= { dscpProfileEntry 11 }


        -- 1.3.6.1.4.1.5504.4.1.22.1.1.12
        dscp09map8021p OBJECT-TYPE
            SYNTAX Integer32 (0..7)
            MAX-ACCESS read-write
            STATUS current
            DESCRIPTION
                "The desired 802.1p setting corresponding to DSCP value 9."
            ::= { dscpProfileEntry 12 }


--
        -- 1.3.6.1.4.1.5504.4.1.22.1.1.13
        dscp10map8021p OBJECT-TYPE
            SYNTAX Integer32 (0..7)
            MAX-ACCESS read-write
            STATUS current
            DESCRIPTION
                "The desired 802.1p setting corresponding to DSCP value 10."
            ::= { dscpProfileEntry 13 }


        -- 1.3.6.1.4.1.5504.4.1.22.1.1.14
        dscp11map8021p OBJECT-TYPE
            SYNTAX Integer32 (0..7)
            MAX-ACCESS read-write
            STATUS current
            DESCRIPTION
                "The desired 802.1p setting corresponding to DSCP value 11."
            ::= { dscpProfileEntry 14 }


        -- 1.3.6.1.4.1.5504.4.1.22.1.1.15
        dscp12map8021p OBJECT-TYPE
            SYNTAX Integer32 (0..7)
            MAX-ACCESS read-write
            STATUS current
            DESCRIPTION
                "The desired 802.1p setting corresponding to DSCP value 12."
            ::= { dscpProfileEntry 15 }


--
        -- 1.3.6.1.4.1.5504.4.1.22.1.1.16
        dscp13map8021p OBJECT-TYPE
            SYNTAX Integer32 (0..7)
            MAX-ACCESS read-write
            STATUS current
            DESCRIPTION
                "The desired 802.1p setting corresponding to DSCP value 13."
            ::= { dscpProfileEntry 16 }


        -- 1.3.6.1.4.1.5504.4.1.22.1.1.17
        dscp14map8021p OBJECT-TYPE
            SYNTAX Integer32 (0..7)
            MAX-ACCESS read-write
            STATUS current
            DESCRIPTION
                "The desired 802.1p setting corresponding to DSCP value 14."
            ::= { dscpProfileEntry 17 }


--
        -- 1.3.6.1.4.1.5504.4.1.22.1.1.18
        dscp15map8021p OBJECT-TYPE
            SYNTAX Integer32 (0..7)
            MAX-ACCESS read-write
            STATUS current
            DESCRIPTION
                "The desired 802.1p setting corresponding to DSCP value 15."
            ::= { dscpProfileEntry 18 }


--
        -- 1.3.6.1.4.1.5504.4.1.22.1.1.19
        dscp16map8021p OBJECT-TYPE
            SYNTAX Integer32 (0..7)
            MAX-ACCESS read-write
            STATUS current
            DESCRIPTION
                "The desired 802.1p setting corresponding to DSCP value 16."
            ::= { dscpProfileEntry 19 }


--
        -- 1.3.6.1.4.1.5504.4.1.22.1.1.20
        dscp17map8021p OBJECT-TYPE
            SYNTAX Integer32 (0..7)
            MAX-ACCESS read-write
            STATUS current
            DESCRIPTION
                "The desired 802.1p setting corresponding to DSCP value 17."
            ::= { dscpProfileEntry 20 }


        -- 1.3.6.1.4.1.5504.4.1.22.1.1.21
        dscp18map8021p OBJECT-TYPE
            SYNTAX Integer32 (0..7)
            MAX-ACCESS read-write
            STATUS current
            DESCRIPTION
                "The desired 802.1p setting corresponding to DSCP value 18."
            ::= { dscpProfileEntry 21 }


        -- 1.3.6.1.4.1.5504.4.1.22.1.1.22
        dscp19map8021p OBJECT-TYPE
            SYNTAX Integer32 (0..7)
            MAX-ACCESS read-write
            STATUS current
            DESCRIPTION
                "The desired 802.1p setting corresponding to DSCP value 19."
            ::= { dscpProfileEntry 22 }


        -- 1.3.6.1.4.1.5504.4.1.22.1.1.23
        dscp20map8021p OBJECT-TYPE
            SYNTAX Integer32 (0..7)
            MAX-ACCESS read-write
            STATUS current
            DESCRIPTION
                "The desired 802.1p setting corresponding to DSCP value 20."
            ::= { dscpProfileEntry 23 }


        -- 1.3.6.1.4.1.5504.4.1.22.1.1.24
        dscp21map8021p OBJECT-TYPE
            SYNTAX Integer32 (0..7)
            MAX-ACCESS read-write
            STATUS current
            DESCRIPTION
                "The desired 802.1p setting corresponding to DSCP value 21."
            ::= { dscpProfileEntry 24 }


        -- 1.3.6.1.4.1.5504.4.1.22.1.1.25
        dscp22map8021p OBJECT-TYPE
            SYNTAX Integer32 (0..7)
            MAX-ACCESS read-write
            STATUS current
            DESCRIPTION
                "The desired 802.1p setting corresponding to DSCP value 22."
            ::= { dscpProfileEntry 25 }


        -- 1.3.6.1.4.1.5504.4.1.22.1.1.26
        dscp23map8021p OBJECT-TYPE
            SYNTAX Integer32 (0..7)
            MAX-ACCESS read-write
            STATUS current
            DESCRIPTION
                "The desired 802.1p setting corresponding to DSCP value 23."
            ::= { dscpProfileEntry 26 }


        -- 1.3.6.1.4.1.5504.4.1.22.1.1.27
        dscp24map8021p OBJECT-TYPE
            SYNTAX Integer32 (0..7)
            MAX-ACCESS read-write
            STATUS current
            DESCRIPTION
                "The desired 802.1p setting corresponding to DSCP value 24."
            ::= { dscpProfileEntry 27 }


--
        -- 1.3.6.1.4.1.5504.4.1.22.1.1.28
        dscp25map8021p OBJECT-TYPE
            SYNTAX Integer32 (0..7)
            MAX-ACCESS read-write
            STATUS current
            DESCRIPTION
                "The desired 802.1p setting corresponding to DSCP value 25."
            ::= { dscpProfileEntry 28 }


        -- 1.3.6.1.4.1.5504.4.1.22.1.1.29
        dscp26map8021p OBJECT-TYPE
            SYNTAX Integer32 (0..7)
            MAX-ACCESS read-write
            STATUS current
            DESCRIPTION
                "The desired 802.1p setting corresponding to DSCP value 26."
            ::= { dscpProfileEntry 29 }


        -- 1.3.6.1.4.1.5504.4.1.22.1.1.30
        dscp27map8021p OBJECT-TYPE
            SYNTAX Integer32 (0..7)
            MAX-ACCESS read-write
            STATUS current
            DESCRIPTION
                "The desired 802.1p setting corresponding to DSCP value 27."
            ::= { dscpProfileEntry 30 }


        -- 1.3.6.1.4.1.5504.4.1.22.1.1.31
        dscp28map8021p OBJECT-TYPE
            SYNTAX Integer32 (0..7)
            MAX-ACCESS read-write
            STATUS current
            DESCRIPTION
                "The desired 802.1p setting corresponding to DSCP value 28."
            ::= { dscpProfileEntry 31 }


        -- 1.3.6.1.4.1.5504.4.1.22.1.1.32
        dscp29map8021p OBJECT-TYPE
            SYNTAX Integer32 (0..7)
            MAX-ACCESS read-write
            STATUS current
            DESCRIPTION
                "The desired 802.1p setting corresponding to DSCP value 29."
            ::= { dscpProfileEntry 32 }


        -- 1.3.6.1.4.1.5504.4.1.22.1.1.33
        dscp30map8021p OBJECT-TYPE
            SYNTAX Integer32 (0..7)
            MAX-ACCESS read-write
            STATUS current
            DESCRIPTION
                "The desired 802.1p setting corresponding to DSCP value 30."
            ::= { dscpProfileEntry 33 }


        -- 1.3.6.1.4.1.5504.4.1.22.1.1.34
        dscp31map8021p OBJECT-TYPE
            SYNTAX Integer32 (0..7)
            MAX-ACCESS read-write
            STATUS current
            DESCRIPTION
                "The desired 802.1p setting corresponding to DSCP value 31."
            ::= { dscpProfileEntry 34 }


--
        -- 1.3.6.1.4.1.5504.4.1.22.1.1.35
        dscp32map8021p OBJECT-TYPE
            SYNTAX Integer32 (0..7)
            MAX-ACCESS read-write
            STATUS current
            DESCRIPTION
                "The desired 802.1p setting corresponding to DSCP value 32."
            ::= { dscpProfileEntry 35 }


        -- 1.3.6.1.4.1.5504.4.1.22.1.1.36
        dscp33map8021p OBJECT-TYPE
            SYNTAX Integer32 (0..7)
            MAX-ACCESS read-write
            STATUS current
            DESCRIPTION
                "The desired 802.1p setting corresponding to DSCP value 33."
            ::= { dscpProfileEntry 36 }


--
        -- 1.3.6.1.4.1.5504.4.1.22.1.1.37
        dscp34map8021p OBJECT-TYPE
            SYNTAX Integer32 (0..7)
            MAX-ACCESS read-write
            STATUS current
            DESCRIPTION
                "The desired 802.1p setting corresponding to DSCP value 34."
            ::= { dscpProfileEntry 37 }


--
        -- 1.3.6.1.4.1.5504.4.1.22.1.1.38
        dscp35map8021p OBJECT-TYPE
            SYNTAX Integer32 (0..7)
            MAX-ACCESS read-write
            STATUS current
            DESCRIPTION
                "The desired 802.1p setting corresponding to DSCP value 35."
            ::= { dscpProfileEntry 38 }


--
        -- 1.3.6.1.4.1.5504.4.1.22.1.1.39
        dscp36map8021p OBJECT-TYPE
            SYNTAX Integer32 (0..7)
            MAX-ACCESS read-write
            STATUS current
            DESCRIPTION
                "The desired 802.1p setting corresponding to DSCP value 36."
            ::= { dscpProfileEntry 39 }


        -- 1.3.6.1.4.1.5504.4.1.22.1.1.40
        dscp37map8021p OBJECT-TYPE
            SYNTAX Integer32 (0..7)
            MAX-ACCESS read-write
            STATUS current
            DESCRIPTION
                "The desired 802.1p setting corresponding to DSCP value 37."
            ::= { dscpProfileEntry 40 }


        -- 1.3.6.1.4.1.5504.4.1.22.1.1.41
        dscp38map8021p OBJECT-TYPE
            SYNTAX Integer32 (0..7)
            MAX-ACCESS read-write
            STATUS current
            DESCRIPTION
                "The desired 802.1p setting corresponding to DSCP value 38."
            ::= { dscpProfileEntry 41 }


--
        -- 1.3.6.1.4.1.5504.4.1.22.1.1.42
        dscp39map8021p OBJECT-TYPE
            SYNTAX Integer32 (0..7)
            MAX-ACCESS read-write
            STATUS current
            DESCRIPTION
                "The desired 802.1p setting corresponding to DSCP value 39."
            ::= { dscpProfileEntry 42 }


        -- 1.3.6.1.4.1.5504.4.1.22.1.1.43
        dscp40map8021p OBJECT-TYPE
            SYNTAX Integer32 (0..7)
            MAX-ACCESS read-write
            STATUS current
            DESCRIPTION
                "The desired 802.1p setting corresponding to DSCP value 40."
            ::= { dscpProfileEntry 43 }


--
        -- 1.3.6.1.4.1.5504.4.1.22.1.1.44
        dscp41map8021p OBJECT-TYPE
            SYNTAX Integer32 (0..7)
            MAX-ACCESS read-write
            STATUS current
            DESCRIPTION
                "The desired 802.1p setting corresponding to DSCP value 41."
            ::= { dscpProfileEntry 44 }


--
        -- 1.3.6.1.4.1.5504.4.1.22.1.1.45
        dscp42map8021p OBJECT-TYPE
            SYNTAX Integer32 (0..7)
            MAX-ACCESS read-write
            STATUS current
            DESCRIPTION
                "The desired 802.1p setting corresponding to DSCP value 42."
            ::= { dscpProfileEntry 45 }


        -- 1.3.6.1.4.1.5504.4.1.22.1.1.46
        dscp43map8021p OBJECT-TYPE
            SYNTAX Integer32 (0..7)
            MAX-ACCESS read-write
            STATUS current
            DESCRIPTION
                "The desired 802.1p setting corresponding to DSCP value 43."
            ::= { dscpProfileEntry 46 }


        -- 1.3.6.1.4.1.5504.4.1.22.1.1.47
        dscp44map8021p OBJECT-TYPE
            SYNTAX Integer32 (0..7)
            MAX-ACCESS read-write
            STATUS current
            DESCRIPTION
                "The desired 802.1p setting corresponding to DSCP value 44."
            ::= { dscpProfileEntry 47 }


        -- 1.3.6.1.4.1.5504.4.1.22.1.1.48
        dscp45map8021p OBJECT-TYPE
            SYNTAX Integer32 (0..7)
            MAX-ACCESS read-write
            STATUS current
            DESCRIPTION
                "The desired 802.1p setting corresponding to DSCP value 45."
            ::= { dscpProfileEntry 48 }


        -- 1.3.6.1.4.1.5504.4.1.22.1.1.49
        dscp46map8021p OBJECT-TYPE
            SYNTAX Integer32 (0..7)
            MAX-ACCESS read-write
            STATUS current
            DESCRIPTION
                "The desired 802.1p setting corresponding to DSCP value 46."
            ::= { dscpProfileEntry 49 }


        -- 1.3.6.1.4.1.5504.4.1.22.1.1.50
        dscp47map8021p OBJECT-TYPE
            SYNTAX Integer32 (0..7)
            MAX-ACCESS read-write
            STATUS current
            DESCRIPTION
                "The desired 802.1p setting corresponding to DSCP value 47."
            ::= { dscpProfileEntry 50 }


        -- 1.3.6.1.4.1.5504.4.1.22.1.1.51
        dscp48map8021p OBJECT-TYPE
            SYNTAX Integer32 (0..7)
            MAX-ACCESS read-write
            STATUS current
            DESCRIPTION
                "The desired 802.1p setting corresponding to DSCP value 48."
            ::= { dscpProfileEntry 51 }


        -- 1.3.6.1.4.1.5504.4.1.22.1.1.52
        dscp49map8021p OBJECT-TYPE
            SYNTAX Integer32 (0..7)
            MAX-ACCESS read-write
            STATUS current
            DESCRIPTION
                "The desired 802.1p setting corresponding to DSCP value 49."
            ::= { dscpProfileEntry 52 }


        -- 1.3.6.1.4.1.5504.4.1.22.1.1.53
        dscp50map8021p OBJECT-TYPE
            SYNTAX Integer32 (0..7)
            MAX-ACCESS read-write
            STATUS current
            DESCRIPTION
                "The desired 802.1p setting corresponding to DSCP value 50."
            ::= { dscpProfileEntry 53 }


        -- 1.3.6.1.4.1.5504.4.1.22.1.1.54
        dscp51map8021p OBJECT-TYPE
            SYNTAX Integer32 (0..7)
            MAX-ACCESS read-write
            STATUS current
            DESCRIPTION
                "The desired 802.1p setting corresponding to DSCP value 51."
            ::= { dscpProfileEntry 54 }


        -- 1.3.6.1.4.1.5504.4.1.22.1.1.55
        dscp52map8021p OBJECT-TYPE
            SYNTAX Integer32 (0..7)
            MAX-ACCESS read-write
            STATUS current
            DESCRIPTION
                "The desired 802.1p setting corresponding to DSCP value 52."
            ::= { dscpProfileEntry 55 }


        -- 1.3.6.1.4.1.5504.4.1.22.1.1.56
        dscp53map8021p OBJECT-TYPE
            SYNTAX Integer32 (0..7)
            MAX-ACCESS read-write
            STATUS current
            DESCRIPTION
                "The desired 802.1p setting corresponding to DSCP value 53."
            ::= { dscpProfileEntry 56 }


        -- 1.3.6.1.4.1.5504.4.1.22.1.1.57
        dscp54map8021p OBJECT-TYPE
            SYNTAX Integer32 (0..7)
            MAX-ACCESS read-write
            STATUS current
            DESCRIPTION
                "The desired 802.1p setting corresponding to DSCP value 54."
            ::= { dscpProfileEntry 57 }


        -- 1.3.6.1.4.1.5504.4.1.22.1.1.58
        dscp55map8021p OBJECT-TYPE
            SYNTAX Integer32 (0..7)
            MAX-ACCESS read-write
            STATUS current
            DESCRIPTION
                "The desired 802.1p setting corresponding to DSCP value 55."
            ::= { dscpProfileEntry 58 }


--
        -- 1.3.6.1.4.1.5504.4.1.22.1.1.59
        dscp56map8021p OBJECT-TYPE
            SYNTAX Integer32 (0..7)
            MAX-ACCESS read-write
            STATUS current
            DESCRIPTION
                "The desired 802.1p setting corresponding to DSCP value 56."
            ::= { dscpProfileEntry 59 }


        -- 1.3.6.1.4.1.5504.4.1.22.1.1.60
        dscp57map8021p OBJECT-TYPE
            SYNTAX Integer32 (0..7)
            MAX-ACCESS read-write
            STATUS current
            DESCRIPTION
                "The desired 802.1p setting corresponding to DSCP value 57."
            ::= { dscpProfileEntry 60 }


--
        -- 1.3.6.1.4.1.5504.4.1.22.1.1.61
        dscp58map8021p OBJECT-TYPE
            SYNTAX Integer32 (0..7)
            MAX-ACCESS read-write
            STATUS current
            DESCRIPTION
                "The desired 802.1p setting corresponding to DSCP value 58."
            ::= { dscpProfileEntry 61 }


        -- 1.3.6.1.4.1.5504.4.1.22.1.1.62
        dscp59map8021p OBJECT-TYPE
            SYNTAX Integer32 (0..7)
            MAX-ACCESS read-write
            STATUS current
            DESCRIPTION
                "The desired 802.1p setting corresponding to DSCP value 59."
            ::= { dscpProfileEntry 62 }


        -- 1.3.6.1.4.1.5504.4.1.22.1.1.63
        dscp60map8021p OBJECT-TYPE
            SYNTAX Integer32 (0..7)
            MAX-ACCESS read-write
            STATUS current
            DESCRIPTION
                "The desired 802.1p setting corresponding to DSCP value 60."
            ::= { dscpProfileEntry 63 }


--
        -- 1.3.6.1.4.1.5504.4.1.22.1.1.64
        dscp61map8021p OBJECT-TYPE
            SYNTAX Integer32 (0..7)
            MAX-ACCESS read-write
            STATUS current
            DESCRIPTION
                "The desired 802.1p setting corresponding to DSCP value 61."
            ::= { dscpProfileEntry 64 }


        -- 1.3.6.1.4.1.5504.4.1.22.1.1.65
        dscp62map8021p OBJECT-TYPE
            SYNTAX Integer32 (0..7)
            MAX-ACCESS read-write
            STATUS current
            DESCRIPTION
                "The desired 802.1p setting corresponding to DSCP value 62."
            ::= { dscpProfileEntry 65 }


        -- 1.3.6.1.4.1.5504.4.1.22.1.1.66
        dscp63map8021p OBJECT-TYPE
            SYNTAX Integer32 (0..7)
            MAX-ACCESS read-write
            STATUS current
            DESCRIPTION
                "The desired 802.1p setting corresponding to DSCP value 63."
            ::= { dscpProfileEntry 66 }


        -- 1.3.6.1.4.1.5504.4.1.22.2
        dscpProfileGroup OBJECT-GROUP
            OBJECTS { dscpProfileRowStatus }
            STATUS current
            DESCRIPTION
                "A collection of objects from dscpProfileEntry."
            ::= { dscpProfile 2 }


        -- 1.3.6.1.4.1.5504.4.1.22.3
        dscpProfileGroupObjectGroup OBJECT-GROUP
            OBJECTS { dscp00map8021p, dscp01map8021p, dscp02map8021p, dscp03map8021p, dscp04map8021p,
                dscp05map8021p, dscp06map8021p, dscp07map8021p, dscp08map8021p, dscp09map8021p,
                dscp10map8021p, dscp11map8021p, dscp12map8021p, dscp13map8021p, dscp14map8021p,
                dscp15map8021p, dscp16map8021p, dscp17map8021p, dscp18map8021p, dscp19map8021p,
                dscp20map8021p, dscp21map8021p, dscp22map8021p, dscp23map8021p, dscp24map8021p,
                dscp25map8021p, dscp26map8021p, dscp27map8021p, dscp28map8021p, dscp29map8021p,
                dscp30map8021p, dscp31map8021p, dscp32map8021p, dscp33map8021p, dscp34map8021p,
                dscp35map8021p, dscp36map8021p, dscp37map8021p, dscp38map8021p, dscp39map8021p,
                dscp40map8021p, dscp41map8021p, dscp42map8021p, dscp43map8021p, dscp44map8021p,
                dscp45map8021p, dscp46map8021p, dscp47map8021p, dscp48map8021p, dscp49map8021p,
                dscp50map8021p, dscp51map8021p, dscp52map8021p, dscp53map8021p, dscp54map8021p,
                dscp55map8021p, dscp56map8021p, dscp57map8021p, dscp58map8021p, dscp59map8021p,
                dscp60map8021p, dscp61map8021p, dscp62map8021p, dscp63map8021p }
            STATUS current
            DESCRIPTION
                "A collection of objects from dscpProfileEntry."
            ::= { dscpProfile 3 }



    END

--
-- zhoneDSCP.mib
--
