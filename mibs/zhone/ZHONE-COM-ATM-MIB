--
-- comAtm.mib
-- MIB generated by MG-SOFT Visual MIB Builder Version 3.0 Build 271
-- Tuesday, April 05, 2005 at 16:59:39
--

        ZHONE-COM-ATM-MIB DEFINITIONS ::= BEGIN

                IMPORTS
                        atmInterfaceDs3PlcpAlarmState, atmInterfaceTCAlarmState, atmTrafficDescrParamEntry, atmVplVpi, atmVplAdminStatus,
                        atmVplOperStatus, atmVplLastChange, atmVplReceiveTrafficDescrIndex, atmVplTransmitTrafficDescrIndex, atmVplCrossConnectIdentifier,
                        atmVplRowStatus, atmVplCastType, atmVplConnKind, atmVclVpi, atmVclVci,
                        atmVclAdminStatus, atmVclOperStatus, atmVclLastChange, atmVclReceiveTrafficDescrIndex, atmVclTransmitTrafficDescrIndex,
                        atmVccAalType, atmVccAal5CpcsTransmitSduSize, atmVccAal5CpcsReceiveSduSize, atmVccAal5EncapsType, atmVclCrossConnectIdentifier, atmVclEntry, atmVplEntry, atmInterfaceTCEntry,
                        atmVclRowStatus, atmVclCastType, atmVclConnKind, atmVcCrossConnectEntry
                                FROM ATM-MIB
                        AtmVpIdentifier, AtmVcIdentifier
                                FROM ATM-TC-MIB
                        ifIndex, InterfaceIndex
                                FROM IF-MIB
                        OBJECT-GROUP, NOTIFICATION-GROUP
                                FROM SNMPv2-CONF
                        IpAddress, Integer32, Counter32, Counter64, OBJECT-TYPE,
                        MODULE-IDENTITY, OBJECT-IDENTITY, NOTIFICATION-TYPE
                                FROM SNMPv2-SMI
                        TruthValue
                                FROM SNMPv2-TC
                        zhoneAtm, zhoneShelfIndex, zhoneSlotIndex, zhoneModules, zhoneShelfIndex,
                        zhoneSlotIndex
                                FROM Zhone
                        ZhoneRowStatus, ZhoneAdminString
                                FROM Zhone-TC;

-- to generate protection layer code, remove all references to Atm_XStats and run this command:
-- /vob/zhonetools/bin/pahrser.pl rfc2233.mib rfc2515.mib rfc2514.mib comAtm.mib

--
--
--
--
--
                comAtmExtension MODULE-IDENTITY
                        LAST-UPDATED "200504051200Z"		-- April 05, 2005 at 12:00 GMT
                        ORGANIZATION
                                "Zhone Technologies, Inc."
                        CONTACT-INFO
                                "  Postal:
                                           Zhone Technologies, Inc.
                                           @ Zhone Way
                                           7001 Oakport Street
                                           Oakland, CA  94621
                                           USA
                                Toll-Free: +1 877-ZHONE20 (+1 877-946-6320)
                                      Tel: +1-510-777-7000
                                      Fax: +1-510-777-7001
                                   E-mail: support@zhone.com"
                        DESCRIPTION
                                "This is the Zhone module identifier for the Zhone ATM
                                MIB extension module."
                        REVISION "200504051644Z"		-- April 05, 2005 at 16:44 GMT
                        DESCRIPTION
                                "01.02.18 - Add zhoneAtmVclExtOamF4Ping
                                and zhoneAtmVclExtOamF4PingStatus."
                        REVISION "200502281318Z"		-- February 28, 2005 at 13:18 GMT
                        DESCRIPTION
                                "01.02.17 - Add field zhoneAtmVpiMaxVciPerVp
                                to zhoneAtmVplEntry."
                        REVISION "200409071044Z"		-- September 07, 2004 at 10:44 GMT
                        DESCRIPTION
                                "01.02.16 - Deprecate zhonePonExtTable.  Move
                                traffic-container-index to AtmVplExtensionTable."
                        REVISION "200406191015Z"		-- June 19, 2004 at 10:15 GMT
                        DESCRIPTION
                                "01.02.15 - change atm vcl param12 default. "
                        REVISION "200401281242Z"		-- January 28, 2004 at 12:42 GMT
                        DESCRIPTION
                                "01.02.14 - Expand atm vcl rates from 16 to 32."
                        REVISION "200312041523Z"		-- December 04, 2003 at 15:23 GMT
                        DESCRIPTION
                                "01.02.13 - Fixed zhoneAtmStatsTotalInitialCellsTx spelling Error."
                        REVISION "200309091411Z"		-- September 09, 2003 at 14:11 GMT
                        DESCRIPTION
                                "V01.02.12 - Add traffic container index to Atm Vpl Entry augment."
                        REVISION "200304161604Z"		-- April 16, 2003 at 16:04 GMT
                        DESCRIPTION
                                "V01.02.11 - Create an object-identifier to encapsulate the atmVclToMulticastMap objects."
                        REVISION "200303111346Z"		-- March 11, 2003 at 13:46 GMT
                        DESCRIPTION
                                "V01.02.10 - Fix typo in markup for Atm_Vcl_To_Multicast_Map_Profile."
                        REVISION "200302141655Z"		-- February 14, 2003 at 16:55 GMT
                        DESCRIPTION
                                "V01.02.09 - Add Vpi F4 Ping."
                        REVISION "200302111330Z"		-- February 11, 2003 at 13:30 GMT
                        DESCRIPTION
                                "V01.02.08 - Add Vcl Multicast."
                        REVISION "200208231036Z"		-- August 23, 2002 at 10:36 GMT
                        DESCRIPTION
                                "V01.02.07 - Changed zhoneAtmV2Traps back to
                                be zhoneAtmTraps child 0 instead of child 1."
                        REVISION "200208131614Z"		-- August 13, 2002 at 16:14 GMT
                        DESCRIPTION
                                "V01.02.06 - Added Vpi auto create notification objects."
                        REVISION "200206042013Z"		-- June 04, 2002 at 20:13 GMT
                        DESCRIPTION
                                "V01.02.05 - Added zhoneAtmTrafficDescrParamExtCacDivider
                                and zhoneAtmTrafficDescrParamExtUsageParameterControl.
                                Also added RowStatus to zhoneAtmVpiTable."
                        REVISION "200205281212Z"		-- May 28, 2002 at 12:12 GMT
                        DESCRIPTION
                                "V01.02.04 - added OAM F5 Ping Status Notification."
                        REVISION "200205211729Z"		-- May 21, 2002 at 17:29 GMT
                        DESCRIPTION
                                "V01.02.03 - added manual OAM F5 ping support"
                        REVISION "200205151729Z"		-- May 15, 2002 at 17:29 GMT
                        DESCRIPTION
                                "V01.02.02 - added ATM VP Support"
                        REVISION "200203202019Z"		-- March 20, 2002 at 20:19 GMT
                        DESCRIPTION
                                "V01.02.01 - added ATM VCL Rates"
                        REVISION "200112191524Z"		-- December 19, 2001 at 15:24 GMT
                        DESCRIPTION
                                "V01.02.00 -Added Atm Extended Stats Table"
                        REVISION "200111021722Z"		-- November 02, 2001 at 17:22 GMT
                        DESCRIPTION
                                "V01.01.02
                                - updated description for zhoneAtmTrafficDescrParamExtTrnkVclRate"
                        REVISION "200110291734Z"		-- October 29, 2001 at 17:34 GMT
                        DESCRIPTION
                                "V01.01.01
                                -Added trap atmVclBandwidthUnavailable, removed unused imported parameters and updated description for zhoneAtmTrafficDescrParamExtTrnkVclRate"
                        REVISION "200109201054Z"		-- September 20, 2001 at 10:54 GMT
                        DESCRIPTION
                                "V01.01.00
                                -Added zhoneAtmTrafficDescrParamExtTable"
                        REVISION "200108301715Z"		-- August 30, 2001 at 17:15 GMT
                        DESCRIPTION
                                "V01.00.02
                                - Added traps atmDsx3PlcpAlarmStatusChange and atmInterfaceTCAlarmStateChange"
                        REVISION "200108141200Z"		-- August 14, 2001 at 12:00 GMT
                        DESCRIPTION
                                "V01.00.01
                                - Correct OBJECTS in the atmVclOperStatusChange trap."
                        REVISION "200107111200Z"		-- July 11, 2001 at 12:00 GMT
                        DESCRIPTION
                                "V01.00.00 - Initial Release"
                        ::= { zhoneModules 25 }
--
--



--
-- Node definitions
--

                -- 1.3.6.1.4.1.5504.4.2.2
                zhoneAtmExtension OBJECT-IDENTITY
                        STATUS current
                        DESCRIPTION
                                "This is the Zhone extension MIB tree to the standard ATM
                                defined by rfc2515."
                        ::= { zhoneAtm 2 }

                -- 1.3.6.1.4.1.5504.4.2.2.1
                zhoneAtmVclExtTable OBJECT-TYPE
                        SYNTAX SEQUENCE OF ZhoneAtmVclExtEntry
                        MAX-ACCESS not-accessible
                        STATUS current
                        DESCRIPTION
                                "Zhone extension table for the atmVclTable defined in
                                rfc2515."
                        ::= { zhoneAtmExtension 1 }

                -- 1.3.6.1.4.1.5504.4.2.2.1.1
                zhoneAtmVclExtEntry OBJECT-TYPE
                        SYNTAX ZhoneAtmVclExtEntry
                        MAX-ACCESS not-accessible
                        STATUS current
                        DESCRIPTION
                                "An entry in the atmVclExtTable.

                                atmVclExtEntry is an augmentation to the atmVclEntry
                                defined in rfc2515."
                        AUGMENTS { atmVclEntry }
                        ::= { zhoneAtmVclExtTable 1 }

                ZhoneAtmVclExtEntry ::=
                        SEQUENCE {
                                zhoneAtmVclExtFaultDetectionType
                                        INTEGER,
                                zhoneAtmVclExtOamF5Ping
                                        INTEGER,
                                zhoneAtmVclExtOamF5PingStatus
                                        TruthValue,
                                zhoneAtmVclExtTrafficContainerIndex
                                        Integer32,
                                zhoneAtmVclExtOamF4Ping
                                        INTEGER,
                                zhoneAtmVclExtOamF4PingStatus
                                        TruthValue
                         }

--
                -- 1.3.6.1.4.1.5504.4.2.2.1.1.1
                zhoneAtmVclExtFaultDetectionType OBJECT-TYPE
                        SYNTAX INTEGER
                                {
                                disabled(1),
                                oamF5Loopback(2)
                                }
                        MAX-ACCESS read-create
                        STATUS current
                        DESCRIPTION
                                "This is used to configure VCL fault detection. The valid values
                                are:

                                * disabled - Fault detection is disabled. This is the default.
                                * oamF5Loopback - This option uses standard OAM fault
                                  management cells as defined in ITU.610 for fault detection.
                                  Automatic loopback diagnostic cells are sent to the IAD.

                                When fault detection is enabled, atmVclOperStatusChange
                                notification trap is used to indicate to the NMS station
                                an VCL has gone down or has come back up.
                                "
                        DEFVAL { disabled }
                        ::= { zhoneAtmVclExtEntry 1 }

                -- 1.3.6.1.4.1.5504.4.2.2.1.1.2
                zhoneAtmVclExtOamF5Ping OBJECT-TYPE
                        SYNTAX INTEGER
                                {
                                disabled(1),
                                endToEnd(2),
                                segment(3)
                                }
                        MAX-ACCESS read-create
                        STATUS current
                        DESCRIPTION
                                "This is used to send a OAM F5 loopback cell for fault detection.
                                The value will automatically revert to disabled after the set
                                is complete. The valid values are:

                                * disabled - OAM F5 loopback cell is not being sent. This is the default.
                                * endToEnd - This option uses standard OAM fault management cells as
                                             defined in ITU.610 for fault detection. Setting this will
                                             send a OAM F5 end-to-end loopback cell to be sent
                                * segment - This is not supported at this time
                                "
                        DEFVAL { disabled }
                        ::= { zhoneAtmVclExtEntry 2 }

                -- 1.3.6.1.4.1.5504.4.2.2.1.1.3
                zhoneAtmVclExtOamF5PingStatus OBJECT-TYPE
                        SYNTAX TruthValue
                        MAX-ACCESS accessible-for-notify
                        STATUS current
                        DESCRIPTION
                                "TRUE if ping was successfull and FALSE if failed"
                        ::= { zhoneAtmVclExtEntry 3 }

--
                -- 1.3.6.1.4.1.5504.4.2.2.1.1.4
                zhoneAtmVclExtTrafficContainerIndex OBJECT-TYPE
                        SYNTAX Integer32 (0..2147483647)
                        MAX-ACCESS read-create
                        STATUS current
                        DESCRIPTION
                                "Index number of a PON traffic container associated with a
                                VCL definition."
                        DEFVAL { 0 }
                        ::= { zhoneAtmVclExtEntry 4 }

                -- 1.3.6.1.4.1.5504.4.2.2.1.1.5
                zhoneAtmVclExtOamF4Ping OBJECT-TYPE
                        SYNTAX INTEGER
                                {
                                disabled(1),
                                endToEnd(2),
                                segment(3)
                                }
                        MAX-ACCESS read-create
                        STATUS current
                        DESCRIPTION
                                "This is used to send a OAM F4 loopback cell for fault detection.
                                The value will automatically revert to disabled after the set
                                is complete. The valid values are:

                                * disabled - OAM F4 loopback cell is not being sent. This is the default.
                                * endToEnd - This option uses standard OAM fault management cells as
                                             defined in ITU.610 for fault detection. Setting this will
                                             send a OAM F4 end-to-end loopback cell to be sent
                                * segment - This is not supported at this time
                                "
                        DEFVAL { disabled }
                        ::= { zhoneAtmVclExtEntry 5 }

                -- 1.3.6.1.4.1.5504.4.2.2.1.1.6
                zhoneAtmVclExtOamF4PingStatus OBJECT-TYPE
                        SYNTAX TruthValue
                        MAX-ACCESS accessible-for-notify
                        STATUS current
                        DESCRIPTION
                                "TRUE if ping was successfull and FALSE if failed."
                        ::= { zhoneAtmVclExtEntry 6 }

                -- 1.3.6.1.4.1.5504.4.2.2.2
                zhoneAtmTraps OBJECT-IDENTITY
                        STATUS current
                        DESCRIPTION
                                "All the Zhone ATM traps will be defined under this OID."
                        ::= { zhoneAtmExtension 2 }

                -- 1.3.6.1.4.1.5504.4.2.2.2.0
                zhoneAtmV2Traps OBJECT-IDENTITY
                        STATUS current
                        DESCRIPTION
                                "This object identity adds a zero(0) for the next to last
                                sub-identifier which should be used for new SNMPv2 Traps."
                        ::= { zhoneAtmTraps 0 }

                -- 1.3.6.1.4.1.5504.4.2.2.2.0.1
                atmVclOperStatusChange NOTIFICATION-TYPE
                        OBJECTS { atmVclAdminStatus, atmVclOperStatus, atmVclLastChange }
                        STATUS current
                        DESCRIPTION
                                "A notification is sent when the operational status of an ATM
                                VCL changes.

                                The VCL entity is identified by its ifIndex, VPI and VCI
                                values in the trap instance OIDs."
                        ::= { zhoneAtmV2Traps 1 }

                -- 1.3.6.1.4.1.5504.4.2.2.2.0.2
                atmDsx3PlcpAlarmStatusChange NOTIFICATION-TYPE
                        OBJECTS { atmInterfaceDs3PlcpAlarmState }
                        STATUS current
                        DESCRIPTION
                                "This trap indicates if there is an
                                alarm present for the DS3 PLCP.  "
                        ::= { zhoneAtmV2Traps 2 }

                -- 1.3.6.1.4.1.5504.4.2.2.2.0.3
                atmInterfaceTCAlarmStateChange NOTIFICATION-TYPE
                        OBJECTS { atmInterfaceTCAlarmState }
                        STATUS current
                        DESCRIPTION
                                "This trap indicates that there is an
                                alarm present for the TC Sublayer. "
                        ::= { zhoneAtmV2Traps 3 }

                -- 1.3.6.1.4.1.5504.4.2.2.2.0.4
                atmVclBandwidthUnavailable NOTIFICATION-TYPE
                        OBJECTS { atmVclReceiveTrafficDescrIndex, atmVclTransmitTrafficDescrIndex }
                        STATUS current
                        DESCRIPTION
                                "This trap indicates that guranteed bandwidth specified by
                                zhoneAtmTrafficDescrParamExtTrnkVclRate in the traffic
                                descriptor is not available in the system.
                                This is sent when a VCL is activated with the traffic
                                descriptor which specifies higher than available rate
                                or a VCL is activated with the traffic descriptor
                                which specifies the vcl-rate value which can cause
                                available bandwidth to run out.
                                In this trap, shelf/slot is sent as part of the common
                                fields sent in all traps."
                        ::= { zhoneAtmV2Traps 4 }

                -- 1.3.6.1.4.1.5504.4.2.2.2.0.5
                atmVplOperStatusChange NOTIFICATION-TYPE
                        OBJECTS { atmVplAdminStatus, atmVplOperStatus, atmVplLastChange }
                        STATUS current
                        DESCRIPTION
                                "Description."
                        ::= { zhoneAtmV2Traps 5 }

                -- 1.3.6.1.4.1.5504.4.2.2.2.0.6
                atmOamF5PingStatus NOTIFICATION-TYPE
                        OBJECTS { ifIndex, atmVpi, atmVci, zhoneAtmVclExtOamF5PingStatus }
                        STATUS current
                        DESCRIPTION
                                "A notification is sent when the OAM F5 Ping succeeds or
                                fails.  The entity is identified by its ifIndex, VPI and
                                VCI values in the trap instance OIDs.  A status value of
                                true indicates successful Ping, otherwise unsuccessful Ping."
                        ::= { zhoneAtmV2Traps 6 }

                -- 1.3.6.1.4.1.5504.4.2.2.2.0.7
                atmVpiAutoCreateComplete NOTIFICATION-TYPE
                        OBJECTS { atmVpiAutoCreateDone, atmVpiAutoCreateCount }
                        STATUS current
                        DESCRIPTION
                                "Notification indicating Vpi auto creation is complete."
                        ::= { zhoneAtmV2Traps 7 }

                -- 1.3.6.1.4.1.5504.4.2.2.2.0.8
                atmOamF4PingStatus NOTIFICATION-TYPE
                        OBJECTS { ifIndex, atmVpi, atmVci, zhoneAtmVpiOamF4PingStatus }
                        STATUS current
                        DESCRIPTION
                                "A notification is sent when the OAM F4 Ping succeeds or
                                fails.  The entity is identified by its ifIndex, and VPI
                                values in the trap instance OIDs.  A status value of true
                                indicates successful Ping, otherwise unsuccessful Ping."
                        ::= { zhoneAtmV2Traps 8 }

                -- 1.3.6.1.4.1.5504.4.2.2.2.0.9
                atmVclExtOamF4PingStatus NOTIFICATION-TYPE
                        OBJECTS { ifIndex, atmVpi, atmVci, zhoneAtmVclExtOamF4PingStatus }
                        STATUS current
                        DESCRIPTION
                                "A notification is sent when the VCL OAM F4 Ping succeeds or
                                fails.  The entity is identified by its ifIndex, vpi and vci
                                values in the trap instance OIDs.

                                zhoneAtmVclExtOamF4PingStatus value of true
                                indicates successful Ping, otherwise unsuccessful Ping."
                        ::= { zhoneAtmV2Traps 9 }

                -- 1.3.6.1.4.1.5504.4.2.2.3
                zhoneAtmGroups OBJECT-IDENTITY
                        STATUS current
                        DESCRIPTION
                                "Zhone ATM object groups and notification groups will
                                be defined under this object identity."
                        ::= { zhoneAtmExtension 3 }

                -- 1.3.6.1.4.1.5504.4.2.2.3.1
                zhoneAtmVclExtGroup OBJECT-GROUP
                        OBJECTS { zhoneAtmVclExtFaultDetectionType, zhoneAtmVclExtOamF5Ping, zhoneAtmVclExtOamF5PingStatus, zhoneAtmVclExtTrafficContainerIndex }
                        STATUS current
                        DESCRIPTION
                                "A collection of objects contained in the zhoneAtmVclExtTable."
                        ::= { zhoneAtmGroups 1 }

                -- 1.3.6.1.4.1.5504.4.2.2.3.2
                zhoneAtmTrapsGroup NOTIFICATION-GROUP
                        NOTIFICATIONS { atmVclOperStatusChange, atmDsx3PlcpAlarmStatusChange, atmInterfaceTCAlarmStateChange, atmVclBandwidthUnavailable, atmVplOperStatusChange,
                                atmOamF5PingStatus, atmVpiAutoCreateComplete, atmOamF4PingStatus }
                        STATUS current
                        DESCRIPTION
                                "A collection of notification traps under the zhoneAtmV2Traps."
                        ::= { zhoneAtmGroups 2 }

                -- 1.3.6.1.4.1.5504.4.2.2.3.3
                zhoneAtmTrafficDescrParamExtGroup OBJECT-GROUP
                        OBJECTS { zhoneAtmTrafficDescrParamExtTrnkVclRate, zhoneAtmTrafficDescrParamExtCacDivider, zhoneAtmTrafficDescrParamExtUsageParameterControl }
                        STATUS current
                        DESCRIPTION
                                "A collection of objects contained in the zhoneAtmTrafficDescrParamExtTable."
                        ::= { zhoneAtmGroups 3 }

                -- 1.3.6.1.4.1.5504.4.2.2.3.4
                zhoneAtmStatsExtTableGroup OBJECT-GROUP
                        OBJECTS { zhoneAtmStatsTotalInitialCellsRx, zhoneAtmStatsTotalFabricCellsRx, zhoneAtmStatsTotalFinalCLP0CellsRx, zhoneAtmStatsTotalFinalCLP1CellsRx, zhoneAtmStatsTotalFabricCellsTx,
                                zhoneAtmStatsTotalFinalCLP0CellsTx, zhoneAtmStatsTotalFinalCLP1CellsTx, zhoneAtmStatsTotalInitialCellsTx }
                        STATUS current
                        DESCRIPTION
                                "Description."
                        ::= { zhoneAtmGroups 4 }

                -- 1.3.6.1.4.1.5504.4.2.2.3.5
                zhoneAtmVclRateExtParamGroup OBJECT-GROUP
                        OBJECTS { zhoneAtmVclRateExtParam1, zhoneAtmVclRateExtParam2, zhoneAtmVclRateExtParam3, zhoneAtmVclRateExtParam4, zhoneAtmVclRateExtParam5,
                                zhoneAtmVclRateExtParam6, zhoneAtmVclRateExtParam7, zhoneAtmVclRateExtParam8, zhoneAtmVclRateExtParam9, zhoneAtmVclRateExtParam10,
                                zhoneAtmVclRateExtParam11, zhoneAtmVclRateExtParam12, zhoneAtmVclRateExtParam13, zhoneAtmVclRateExtParam14, zhoneAtmVclRateExtParam15,
                                zhoneAtmVclRateExtParam16, zhoneAtmVclRateExtParam1Grp2, zhoneAtmVclRateExtParam2Grp2, zhoneAtmVclRateExtParam3Grp2, zhoneAtmVclRateExtParam4Grp2,
                                zhoneAtmVclRateExtParam5Grp2, zhoneAtmVclRateExtParam6Grp2, zhoneAtmVclRateExtParam7Grp2, zhoneAtmVclRateExtParam8Grp2, zhoneAtmVclRateExtParam9Grp2,
                                zhoneAtmVclRateExtParam10Grp2, zhoneAtmVclRateExtParam11Grp2, zhoneAtmVclRateExtParam12Grp2, zhoneAtmVclRateExtParam13Grp2, zhoneAtmVclRateExtParam14Grp2,
                                zhoneAtmVclRateExtParam15Grp2, zhoneAtmVclRateExtParam16Grp2 }
                        STATUS current
                        DESCRIPTION
                                "Atm Vcl rate parameter values."
                        ::= { zhoneAtmGroups 5 }

                -- 1.3.6.1.4.1.5504.4.2.2.3.6
                zhoneAtmVplExtGroup OBJECT-GROUP
                        OBJECTS { zhoneAtmVplExtFaultDetectionType, zhoneAtmVplExtTrafficContainerIndex }
                        STATUS current
                        DESCRIPTION
                                "Description."
                        ::= { zhoneAtmGroups 6 }

                -- 1.3.6.1.4.1.5504.4.2.2.3.7
                zhoneAtmConnectionStatsGroup OBJECT-GROUP
                        OBJECTS { zhoneAtmConnectionsAvailable, zhoneAtmConnectionsAllocated }
                        STATUS current
                        DESCRIPTION
                                "Description."
                        ::= { zhoneAtmGroups 7 }

                -- 1.3.6.1.4.1.5504.4.2.2.3.8
                zhoneAtmVpiGroup OBJECT-GROUP
                        OBJECTS { zhoneAtmVpiMaxVci, zhoneAtmVpiSwitched, zhoneAtmVpiRowStatus, atmVpi, atmVci,
                                atmVpiAutoCreateDone, atmVpiAutoCreateCount, zhoneAtmVpiOamF4Ping, zhoneAtmVpiOamF4PingStatus, zhoneAtmVpiMaxVciPerVp
                                 }
                        STATUS current
                        DESCRIPTION
                                "Description."
                        ::= { zhoneAtmGroups 8 }

                -- 1.3.6.1.4.1.5504.4.2.2.3.9
                zhoneAtmPonGroup OBJECT-GROUP
                        OBJECTS { zhoneAtmVclPonTrafficContainerIndex, zhoneAtmVplPonTrafficContainerIndex }
                        STATUS deprecated
                        DESCRIPTION
                                "Description."
                        ::= { zhoneAtmGroups 9 }

                -- 1.3.6.1.4.1.5504.4.2.2.3.10
                zhoneAtmVclMulticastGroup OBJECT-GROUP
                        OBJECTS { atmVclToMulticastMapIndexNext, atmVclToMulticastMapRoutingDomain, atmVclToMulticastMapMulticastAddress, atmVclToMulticastMapIfIndex, atmVclToMulticastMapVpi,
                                atmVclToMulticastMapVci, atmVclToMulticastMapRowStatus }
                        STATUS current
                        DESCRIPTION
                                "Description."
                        ::= { zhoneAtmGroups 10 }

                -- 1.3.6.1.4.1.5504.4.2.2.4
                zhoneAtmTrafficDescrParamExtTable OBJECT-TYPE
                        SYNTAX SEQUENCE OF ZhoneAtmTrafficDescrParamExtEntry
                        MAX-ACCESS not-accessible
                        STATUS current
                        DESCRIPTION
                                "Zhone extension table for the  atmTrafficDescrParamTable
                                defined in rfc2515."
                        ::= { zhoneAtmExtension 4 }

                -- 1.3.6.1.4.1.5504.4.2.2.4.1
                zhoneAtmTrafficDescrParamExtEntry OBJECT-TYPE
                        SYNTAX ZhoneAtmTrafficDescrParamExtEntry
                        MAX-ACCESS not-accessible
                        STATUS current
                        DESCRIPTION
                                "This is extension of AtmTrafficDescrParamEntry defined
                                in rfc2515."
                        AUGMENTS { atmTrafficDescrParamEntry }
                        ::= { zhoneAtmTrafficDescrParamExtTable 1 }

                ZhoneAtmTrafficDescrParamExtEntry ::=
                        SEQUENCE {
                                zhoneAtmTrafficDescrParamExtTrnkVclRate
                                        INTEGER,
                                zhoneAtmTrafficDescrParamExtCacDivider
                                        Integer32,
                                zhoneAtmTrafficDescrParamExtUsageParameterControl
                                        TruthValue
                         }

--
                -- 1.3.6.1.4.1.5504.4.2.2.4.1.1
                zhoneAtmTrafficDescrParamExtTrnkVclRate OBJECT-TYPE
                        SYNTAX INTEGER
                                {
                                unused(1),
                                rate16K(2),
                                rate32K(3),
                                rate64K(4),
                                rate80K(5),
                                rate128K(6),
                                rate160K(7),
                                rate256K(8),
                                rate320K(9),
                                rate512K(10),
                                rate640K(11),
                                rate1552K(12),
                                rate2050K(13),
                                rate12M(14),
                                rate16M(15),
                                rate45M(16),
                                rate155M(17),
                                rate960K(18),
                                rate1280K(19),
                                rate1760K(20),
                                rate3M(21),
                                rate4M(22),
                                rate5M(23),
                                rate6M(24),
                                rate7M(25),
                                rate8M(26),
                                rate10M(27),
                                rate14M(28),
                                rate24M(29),
                                rate32M(30),
                                rate64M(31),
                                rate96M(32),
                                rate128M(33)
                                }
                        MAX-ACCESS read-create
                        STATUS current
                        DESCRIPTION
                                "This field is used to describe the minimum guaranteed rate
                                for a VCL which is bound to this traffic descriptor for BAN
                                ATM Trunk Cards. It is applicable only for RTVBR service
                                category.
                                Unlike switched voice calls in the TDM world we cannot
                                oversubscribe bandwidth because all of our voice calls must be
                                connected at all times so that we can receive signaling to tell
                                us that the phone when off hook.  Instead of oversubscribing we
                                suggest that the service provide under provision their voice calls.
                                An example of this would be a normal good quality voice call over
                                ATM requires about 80kb of bandwidth.  To share the bandwidth
                                resource over several customers the service provider would instead
                                allocate (for example) rate16K for a single voice channel, this
                                would allow 5 channels to share the bandwidth required to connect
                                a good quality voice call.  Any value less than rate80K could be
                                used if the service provider wished to share bandwidth resources
                                over more than one voice call.  In order for this method to
                                produce a good quality voice call enough bandwidth must be
                                unallocated and used in a shared pool by all connections. When the
                                buffering is not adequate for a good quality call the connection
                                will not terminate, instead the call quality will suffer.  Values
                                greater than rate80K would be used by devices like a PBX.
                                For all service categories other than RTVBR, unused is the only
                                valid value.For RTVBR unused is not a valid value and one of the
                                rates has to be specified.
                                This parameter is used independently for transmit and receive traffic
                                based on the traffic descriptor specified for transmit and receive
                                in the VCL. Changing this parameter may cause a trap if newly utilized bandwidth
                                for a card exceeds its available bandwidth. It may happen on
                                multiple cards and therefore there can be multiple traps."
                        DEFVAL { unused }
                        ::= { zhoneAtmTrafficDescrParamExtEntry 1 }

                -- 1.3.6.1.4.1.5504.4.2.2.4.1.2
                zhoneAtmTrafficDescrParamExtCacDivider OBJECT-TYPE
                        SYNTAX Integer32
                        MAX-ACCESS read-write
                        STATUS current
                        DESCRIPTION
                                "This object allows users to oversubsribe. The
                                rate subtracted from CAC is PCR or SCR divided by
                                this object."
                        DEFVAL { '1'b }
                        ::= { zhoneAtmTrafficDescrParamExtEntry 2 }

                -- 1.3.6.1.4.1.5504.4.2.2.4.1.3
                zhoneAtmTrafficDescrParamExtUsageParameterControl OBJECT-TYPE
                        SYNTAX TruthValue
                        MAX-ACCESS read-create
                        STATUS current
                        DESCRIPTION
                                "If set to 'false', this object disables polcing."
                        DEFVAL { true }
                        ::= { zhoneAtmTrafficDescrParamExtEntry 3 }

                -- 1.3.6.1.4.1.5504.4.2.2.5
                zhoneAtmStatsExtTable OBJECT-TYPE
                        SYNTAX SEQUENCE OF ZhoneAtmStatsExtEntry
                        MAX-ACCESS not-accessible
                        STATUS current
                        DESCRIPTION
                                "These statistics values are coming from fabric interface."
                        ::= { zhoneAtmExtension 5 }

                -- 1.3.6.1.4.1.5504.4.2.2.5.1
                zhoneAtmStatsExtEntry OBJECT-TYPE
                        SYNTAX ZhoneAtmStatsExtEntry
                        MAX-ACCESS not-accessible
                        STATUS current
                        DESCRIPTION
                                "Definitions of Forward and Backward:

                        Internal to ATM Switch Fabric
               =============================================================
               |Ext|==>IngressFwd==>|                 |==>EgressFwd====>|Int|
               PortPhy<->|VC |                |APC Switch Fabric|                 |VC |<->Bus/SAR/DSP
               |   |<==EgressBack<==|                 |<==IngressBack<==|   |       Phy
               ============================================================="
                        AUGMENTS { atmVclEntry }
                        ::= { zhoneAtmStatsExtTable 1 }

                ZhoneAtmStatsExtEntry ::=
                        SEQUENCE {
                                zhoneAtmStatsTotalInitialCellsRx
                                        Counter64,
                                zhoneAtmStatsTotalFabricCellsRx
                                        Counter64,
                                zhoneAtmStatsTotalFinalCLP0CellsRx
                                        Counter64,
                                zhoneAtmStatsTotalFinalCLP1CellsRx
                                        Counter64,
                                zhoneAtmStatsTotalInitialCellsTx
                                        Counter64,
                                zhoneAtmStatsTotalFabricCellsTx
                                        Counter64,
                                zhoneAtmStatsTotalFinalCLP0CellsTx
                                        Counter64,
                                zhoneAtmStatsTotalFinalCLP1CellsTx
                                        Counter64
                         }

                -- 1.3.6.1.4.1.5504.4.2.2.5.1.1
                zhoneAtmStatsTotalInitialCellsRx OBJECT-TYPE
                        SYNTAX Counter64
                        MAX-ACCESS read-only
                        STATUS current
                        DESCRIPTION
                                "Total Initial Cells Received. Total cells received across the
                                ingress interface for a given VC, and not discarded by policing
                                prior to thresholding (includes CPU insertions but excludes Atm switch fabric
                                generated ingress OAM insertions)."
                        ::= { zhoneAtmStatsExtEntry 1 }

                -- 1.3.6.1.4.1.5504.4.2.2.5.1.2
                zhoneAtmStatsTotalFabricCellsRx OBJECT-TYPE
                        SYNTAX Counter64
                        MAX-ACCESS read-only
                        STATUS current
                        DESCRIPTION
                                "Total Cells Recevied at Fabric.Total cells received across
                                the fabric interface for a given VC, including cells discarded
                                due to parity errors."
                        ::= { zhoneAtmStatsExtEntry 2 }

                -- 1.3.6.1.4.1.5504.4.2.2.5.1.3
                zhoneAtmStatsTotalFinalCLP0CellsRx OBJECT-TYPE
                        SYNTAX Counter64
                        MAX-ACCESS read-only
                        STATUS current
                        DESCRIPTION
                                "Total CLP0 Cells received by fabric. This field
                                is setup to monitor  egress total cells
                                transmitted CLP0."
                        ::= { zhoneAtmStatsExtEntry 3 }

                -- 1.3.6.1.4.1.5504.4.2.2.5.1.4
                zhoneAtmStatsTotalFinalCLP1CellsRx OBJECT-TYPE
                        SYNTAX Counter64
                        MAX-ACCESS read-only
                        STATUS current
                        DESCRIPTION
                                "Total CLP1 Cells received by fabric. This field
                                is setup to monitor  egress total cells
                                transmitted CLP1."
                        ::= { zhoneAtmStatsExtEntry 4 }

                -- 1.3.6.1.4.1.5504.4.2.2.5.1.5
                zhoneAtmStatsTotalInitialCellsTx OBJECT-TYPE
                        SYNTAX Counter64
                        MAX-ACCESS read-only
                        STATUS current
                        DESCRIPTION
                                "Initial Total Cells Transmitted. Total cells transmitted.  across the
                                ingress interface for a given VC, and not discarded by policing
                                prior to thresholding (includes CPU insertions but excludes Atm switch fabric
                                generated ingress OAM insertions)."
                        ::= { zhoneAtmStatsExtEntry 5 }

                -- 1.3.6.1.4.1.5504.4.2.2.5.1.6
                zhoneAtmStatsTotalFabricCellsTx OBJECT-TYPE
                        SYNTAX Counter64
                        MAX-ACCESS read-only
                        STATUS current
                        DESCRIPTION
                                "Total cells transmitted at fabric interace.Total cells transmitted across
                                the fabric interface for a given VC, including cells discarded
                                due to parity errors."
                        ::= { zhoneAtmStatsExtEntry 6 }

                -- 1.3.6.1.4.1.5504.4.2.2.5.1.7
                zhoneAtmStatsTotalFinalCLP0CellsTx OBJECT-TYPE
                        SYNTAX Counter64
                        MAX-ACCESS read-only
                        STATUS current
                        DESCRIPTION
                                "Total CLP0 Cells Transmitted. This field
                                is setup to monitor  egress total cells
                                transmitted CLP0."
                        ::= { zhoneAtmStatsExtEntry 7 }

                -- 1.3.6.1.4.1.5504.4.2.2.5.1.8
                zhoneAtmStatsTotalFinalCLP1CellsTx OBJECT-TYPE
                        SYNTAX Counter64
                        MAX-ACCESS read-only
                        STATUS current
                        DESCRIPTION
                                "Total CLP1 Cells Transmitted. This field
                                is setup to monitor  egress total cells
                                transmitted CLP1."
                        ::= { zhoneAtmStatsExtEntry 8 }

                -- 1.3.6.1.4.1.5504.4.2.2.6
                zhoneAtmVclRateExtParam OBJECT-IDENTITY
                        STATUS current
                        DESCRIPTION
                                "This is the Zhone extension MIB tree to the ATM VCL rates."
                        ::= { zhoneAtmExtension 6 }

                -- 1.3.6.1.4.1.5504.4.2.2.6.1
                zhoneAtmVclRateExtParam1 OBJECT-TYPE
                        SYNTAX Integer32
                        MAX-ACCESS read-write
                        STATUS current
                        DESCRIPTION
                                "This field is used to describe the first least field  of
                                total 16 minimum guaranteed rate which is configurable
                                by user for a VCL which is bound to this traffic
                                descriptor for BAN ATM Trunk or MALC uplink Cards.
                                It is applicable only for RTVBR/NRTVBR or CBR
                                service category. For RTVBR/NRTVBR service category,
                                this value can be set in the rfc2515 td_param2 of
                                the traffice descriptor table. For CBR service
                                category, this value can be set in the td_param1
                                field. The maximum rates capacitiy is 16, any
                                value which is not matched in any one of those 16
                                rates will be rejected.

                                Unlike switched voice calls in the TDM world we
                                cannot oversubscribe bandwidth because all of our
                                voice calls must be connected at all times so that
                                we can receive signaling to tell us that the phone
                                when off hook.  Instead of oversubscribing we
                                suggest that the service provide under provision
                                their voice calls. An example of this would be a
                                normal good quality voice call over ATM requires
                                about 189 CPS. To share the bandwidth
                                resource over several customers the service
                                provider would instead
                                allocate (for example) 38 CPS for a single voice
                                channel, this would allow 5 channels to share the
                                bandwidth required to connect a good quality voice
                                call. Any value less than 189 CPS could be used if
                                the service provider wished to share bandwidth
                                resources over more than one voice call. In order
                                for this method to produce a good quality voice call
                                enough bandwidth must be unallocated and used in a
                                shared pool by all connections. When the buffering
                                is not adequate for a good quality call the connection
                                will not terminate, instead the call quality will
                                suffer. Values greater than 189 CPS would be used by
                                devices like a PBX. This parameter is used independently
                                for transmit and receive traffic based on the traffic
                                descriptor specified for transmit and receive in the VCL.
                                "
                        DEFVAL { 38 }
                        ::= { zhoneAtmVclRateExtParam 1 }

                -- 1.3.6.1.4.1.5504.4.2.2.6.2
                zhoneAtmVclRateExtParam2 OBJECT-TYPE
                        SYNTAX Integer32
                        MAX-ACCESS read-write
                        STATUS current
                        DESCRIPTION
                                "This field is used to describe the second least field of total 16
                                minimum guaranteed rate which is configurable by user
                                for a VCL which is bound to this traffic descriptor for BAN
                                ATM Trunk or MALC uplink Cards."
                        DEFVAL { 76 }
                        ::= { zhoneAtmVclRateExtParam 2 }

                -- 1.3.6.1.4.1.5504.4.2.2.6.3
                zhoneAtmVclRateExtParam3 OBJECT-TYPE
                        SYNTAX Integer32
                        MAX-ACCESS read-write
                        STATUS current
                        DESCRIPTION
                                "This field is used to describe the third least field of total 16
                                minimum guaranteed rate which is configurable by user
                                for a VCL which is bound to this traffic descriptor for BAN
                                ATM Trunk or MALC uplink Cards."
                        DEFVAL { 151 }
                        ::= { zhoneAtmVclRateExtParam 3 }

                -- 1.3.6.1.4.1.5504.4.2.2.6.4
                zhoneAtmVclRateExtParam4 OBJECT-TYPE
                        SYNTAX Integer32
                        MAX-ACCESS read-write
                        STATUS current
                        DESCRIPTION
                                "This field is used to describe the fourth least field of total 16
                                minimum guaranteed rate which is configurable by user
                                for a VCL which is bound to this traffic descriptor for BAN
                                ATM Trunk or MALC uplink Cards."
                        DEFVAL { 189 }
                        ::= { zhoneAtmVclRateExtParam 4 }

                -- 1.3.6.1.4.1.5504.4.2.2.6.5
                zhoneAtmVclRateExtParam5 OBJECT-TYPE
                        SYNTAX Integer32
                        MAX-ACCESS read-write
                        STATUS current
                        DESCRIPTION
                                "This field is used to describe the fifth least field of total 16
                                minimum guaranteed rate which is configurable by user
                                for a VCL which is bound to this traffic descriptor for BAN
                                ATM Trunk or MALC uplink Cards."
                        DEFVAL { 302 }
                        ::= { zhoneAtmVclRateExtParam 5 }

                -- 1.3.6.1.4.1.5504.4.2.2.6.6
                zhoneAtmVclRateExtParam6 OBJECT-TYPE
                        SYNTAX Integer32
                        MAX-ACCESS read-write
                        STATUS current
                        DESCRIPTION
                                "This field is used to describe the sixth least field of total 16
                                minimum guaranteed rate which is configurable by user
                                for a VCL which is bound to this traffic descriptor for BAN
                                ATM Trunk or MALC uplink Cards."
                        DEFVAL { 378 }
                        ::= { zhoneAtmVclRateExtParam 6 }

                -- 1.3.6.1.4.1.5504.4.2.2.6.7
                zhoneAtmVclRateExtParam7 OBJECT-TYPE
                        SYNTAX Integer32
                        MAX-ACCESS read-write
                        STATUS current
                        DESCRIPTION
                                "This field is used to describe the seventh least field of total 16
                                minimum guaranteed rate which is configurable by user
                                for a VCL which is bound to this traffic descriptor for BAN
                                ATM Trunk or MALC uplink Cards."
                        DEFVAL { 604 }
                        ::= { zhoneAtmVclRateExtParam 7 }

                -- 1.3.6.1.4.1.5504.4.2.2.6.8
                zhoneAtmVclRateExtParam8 OBJECT-TYPE
                        SYNTAX Integer32
                        MAX-ACCESS read-write
                        STATUS current
                        DESCRIPTION
                                "This field is used to describe the eighth least field of total 16
                                minimum guaranteed rate which is configurable by user
                                for a VCL which is bound to this traffic descriptor for BAN
                                ATM Trunk or MALC uplink Cards."
                        DEFVAL { 755 }
                        ::= { zhoneAtmVclRateExtParam 8 }

                -- 1.3.6.1.4.1.5504.4.2.2.6.9
                zhoneAtmVclRateExtParam9 OBJECT-TYPE
                        SYNTAX Integer32
                        MAX-ACCESS read-write
                        STATUS current
                        DESCRIPTION
                                "This field is used to describe the ninth least field of total 16
                                minimum guaranteed rate which is configurable by user
                                for a VCL which is bound to this traffic descriptor for BAN
                                ATM Trunk or MALC uplink Cards."
                        DEFVAL { 1208 }
                        ::= { zhoneAtmVclRateExtParam 9 }

                -- 1.3.6.1.4.1.5504.4.2.2.6.10
                zhoneAtmVclRateExtParam10 OBJECT-TYPE
                        SYNTAX Integer32
                        MAX-ACCESS read-write
                        STATUS current
                        DESCRIPTION
                                "This field is used to describe the tenth least field of total 16
                                minimum guaranteed rate which is configurable by user
                                for a VCL which is bound to this traffic descriptor for BAN
                                ATM Trunk or MALC uplink Cards."
                        DEFVAL { 1510 }
                        ::= { zhoneAtmVclRateExtParam 10 }

                -- 1.3.6.1.4.1.5504.4.2.2.6.11
                zhoneAtmVclRateExtParam11 OBJECT-TYPE
                        SYNTAX Integer32
                        MAX-ACCESS read-write
                        STATUS current
                        DESCRIPTION
                                "This field is used to describe the eleventh least field of total 16
                                minimum guaranteed rate which is configurable by user
                                for a VCL which is bound to this traffic descriptor for BAN
                                ATM Trunk or MALC uplink Cards."
                        DEFVAL { 3661 }
                        ::= { zhoneAtmVclRateExtParam 11 }

                -- 1.3.6.1.4.1.5504.4.2.2.6.12
                zhoneAtmVclRateExtParam12 OBJECT-TYPE
                        SYNTAX Integer32
                        MAX-ACCESS read-write
                        STATUS current
                        DESCRIPTION
                                "This field is used to describe the twelfth least field of total 16
                                minimum guaranteed rate which is configurable by user
                                for a VCL which is bound to this traffic descriptor for BAN
                                ATM Trunk or MALC uplink Cards."
                        DEFVAL { 4825 }
                        ::= { zhoneAtmVclRateExtParam 12 }

                -- 1.3.6.1.4.1.5504.4.2.2.6.13
                zhoneAtmVclRateExtParam13 OBJECT-TYPE
                        SYNTAX Integer32
                        MAX-ACCESS read-write
                        STATUS current
                        DESCRIPTION
                                "This field is used to describe the thirteenth least field of total 16
                                minimum guaranteed rate which is configurable by user
                                for a VCL which is bound to this traffic descriptor for BAN
                                ATM Trunk or MALC uplink Cards."
                        DEFVAL { 28302 }
                        ::= { zhoneAtmVclRateExtParam 13 }

                -- 1.3.6.1.4.1.5504.4.2.2.6.14
                zhoneAtmVclRateExtParam14 OBJECT-TYPE
                        SYNTAX Integer32
                        MAX-ACCESS read-write
                        STATUS current
                        DESCRIPTION
                                "This field is used to describe the fouthteenth least field of total 16
                                minimum guaranteed rate which is configurable by user
                                for a VCL which is bound to this traffic descriptor for BAN
                                ATM Trunk or MALC uplink Cards."
                        DEFVAL { 37736 }
                        ::= { zhoneAtmVclRateExtParam 14 }

                -- 1.3.6.1.4.1.5504.4.2.2.6.15
                zhoneAtmVclRateExtParam15 OBJECT-TYPE
                        SYNTAX Integer32
                        MAX-ACCESS read-write
                        STATUS current
                        DESCRIPTION
                                "This field is used to describe the fifteenth least field of total 16
                                minimum guaranteed rate which is configurable by user
                                for a VCL which is bound to this traffic descriptor for BAN
                                ATM Trunk or MALC uplink Cards."
                        DEFVAL { 106133 }
                        ::= { zhoneAtmVclRateExtParam 15 }

                -- 1.3.6.1.4.1.5504.4.2.2.6.16
                zhoneAtmVclRateExtParam16 OBJECT-TYPE
                        SYNTAX Integer32
                        MAX-ACCESS read-write
                        STATUS current
                        DESCRIPTION
                                "This field is used to describe the sixteenth least field of total 16
                                minimum guaranteed rate which is configurable by user
                                for a VCL which is bound to this traffic descriptor for BAN
                                ATM Trunk or MALC uplink Cards."
                        DEFVAL { 365567 }
                        ::= { zhoneAtmVclRateExtParam 16 }

                -- 1.3.6.1.4.1.5504.4.2.2.6.17
                zhoneAtmVclRateExtParam1Grp2 OBJECT-TYPE
                        SYNTAX Integer32
                        MAX-ACCESS read-write
                        STATUS current
                        DESCRIPTION
                                "This field is used to describe the first least
                                field of total 16 minimum guaranteed rate which
                                is configurable by user for a VCL which is bound
                                to this traffic descriptor for BAN ATM Trunk or
                                MALC uplink Cards."
                        DEFVAL { 2264 }
                        ::= { zhoneAtmVclRateExtParam 17 }

                -- 1.3.6.1.4.1.5504.4.2.2.6.18
                zhoneAtmVclRateExtParam2Grp2 OBJECT-TYPE
                        SYNTAX Integer32
                        MAX-ACCESS read-write
                        STATUS current
                        DESCRIPTION
                                "This field is used to describe the second least
                                field of total 16 minimum guaranteed rate which
                                is configurable by user for a VCL which is bound
                                to this traffic descriptor for BAN ATM Trunk or
                                MALC uplink Cards."
                        DEFVAL { 3019 }
                        ::= { zhoneAtmVclRateExtParam 18 }

                -- 1.3.6.1.4.1.5504.4.2.2.6.19
                zhoneAtmVclRateExtParam3Grp2 OBJECT-TYPE
                        SYNTAX Integer32
                        MAX-ACCESS read-write
                        STATUS current
                        DESCRIPTION
                                "This field is used to describe the third least
                                field of total 16 minimum guaranteed rate which
                                is configurable by user for a VCL which is bound
                                to this traffic descriptor for BAN ATM Trunk or
                                MALC uplink Cards."
                        DEFVAL { 4151 }
                        ::= { zhoneAtmVclRateExtParam 19 }

                -- 1.3.6.1.4.1.5504.4.2.2.6.20
                zhoneAtmVclRateExtParam4Grp2 OBJECT-TYPE
                        SYNTAX Integer32
                        MAX-ACCESS read-write
                        STATUS current
                        DESCRIPTION
                                "This field is used to describe the fourth least
                                field of total 16 minimum guaranteed rate which
                                is configurable by user for a VCL which is bound
                                to this traffic descriptor for BAN ATM Trunk or
                                MALC uplink Cards."
                        DEFVAL { 7075 }
                        ::= { zhoneAtmVclRateExtParam 20 }

                -- 1.3.6.1.4.1.5504.4.2.2.6.21
                zhoneAtmVclRateExtParam5Grp2 OBJECT-TYPE
                        SYNTAX Integer32
                        MAX-ACCESS read-write
                        STATUS current
                        DESCRIPTION
                                "This field is used to describe the fifth least
                                field of total 16 minimum guaranteed rate which
                                is configurable by user for a VCL which is bound
                                to this traffic descriptor for BAN ATM Trunk or
                                MALC uplink Cards."
                        DEFVAL { 9434 }
                        ::= { zhoneAtmVclRateExtParam 21 }

                -- 1.3.6.1.4.1.5504.4.2.2.6.22
                zhoneAtmVclRateExtParam6Grp2 OBJECT-TYPE
                        SYNTAX Integer32
                        MAX-ACCESS read-write
                        STATUS current
                        DESCRIPTION
                                "This field is used to describe the sixth least
                                field of total 16 minimum guaranteed rate which
                                is configurable by user for a VCL which is bound
                                to this traffic descriptor for BAN ATM Trunk or
                                MALC uplink Cards."
                        DEFVAL { 11792 }
                        ::= { zhoneAtmVclRateExtParam 22 }

                -- 1.3.6.1.4.1.5504.4.2.2.6.23
                zhoneAtmVclRateExtParam7Grp2 OBJECT-TYPE
                        SYNTAX Integer32
                        MAX-ACCESS read-write
                        STATUS current
                        DESCRIPTION
                                "This field is used to describe the seventh least
                                field of total 16 minimum guaranteed rate which
                                is configurable by user for a VCL which is bound
                                to this traffic descriptor for BAN ATM Trunk or
                                MALC uplink Cards."
                        DEFVAL { 14151 }
                        ::= { zhoneAtmVclRateExtParam 23 }

                -- 1.3.6.1.4.1.5504.4.2.2.6.24
                zhoneAtmVclRateExtParam8Grp2 OBJECT-TYPE
                        SYNTAX Integer32
                        MAX-ACCESS read-write
                        STATUS current
                        DESCRIPTION
                                "This field is used to describe the eighth least
                                field of total 16 minimum guaranteed rate which
                                is configurable by user for a VCL which is bound
                                to this traffic descriptor for BAN ATM Trunk or
                                MALC uplink Cards."
                        DEFVAL { 16509 }
                        ::= { zhoneAtmVclRateExtParam 24 }

                -- 1.3.6.1.4.1.5504.4.2.2.6.25
                zhoneAtmVclRateExtParam9Grp2 OBJECT-TYPE
                        SYNTAX Integer32
                        MAX-ACCESS read-write
                        STATUS current
                        DESCRIPTION
                                "This field is used to describe the ninth least
                                field of total 16 minimum guaranteed rate which
                                is configurable by user for a VCL which is bound
                                to this traffic descriptor for BAN ATM Trunk or
                                MALC uplink Cards."
                        DEFVAL { 18868 }
                        ::= { zhoneAtmVclRateExtParam 25 }

                -- 1.3.6.1.4.1.5504.4.2.2.6.26
                zhoneAtmVclRateExtParam10Grp2 OBJECT-TYPE
                        SYNTAX Integer32
                        MAX-ACCESS read-write
                        STATUS current
                        DESCRIPTION
                                "This field is used to describe the tenth least
                                field of total 16 minimum guaranteed rate which
                                is configurable by user for a VCL which is bound
                                to this traffic descriptor for BAN ATM Trunk or
                                MALC uplink Cards."
                        DEFVAL { 23585 }
                        ::= { zhoneAtmVclRateExtParam 26 }

                -- 1.3.6.1.4.1.5504.4.2.2.6.27
                zhoneAtmVclRateExtParam11Grp2 OBJECT-TYPE
                        SYNTAX Integer32
                        MAX-ACCESS read-write
                        STATUS current
                        DESCRIPTION
                                "This field is used to describe the eleventh least
                                field of total 16 minimum guaranteed rate which
                                is configurable by user for a VCL which is bound
                                to this traffic descriptor for BAN ATM Trunk or
                                MALC uplink Cards."
                        DEFVAL { 33019 }
                        ::= { zhoneAtmVclRateExtParam 27 }

                -- 1.3.6.1.4.1.5504.4.2.2.6.28
                zhoneAtmVclRateExtParam12Grp2 OBJECT-TYPE
                        SYNTAX Integer32
                        MAX-ACCESS read-write
                        STATUS current
                        DESCRIPTION
                                "This field is used to describe the twelfth least
                                field of total 16 minimum guaranteed rate which
                                is configurable by user for a VCL which is bound
                                to this traffic descriptor for BAN ATM Trunk or
                                MALC uplink Cards."
                        DEFVAL { 56604 }
                        ::= { zhoneAtmVclRateExtParam 28 }

                -- 1.3.6.1.4.1.5504.4.2.2.6.29
                zhoneAtmVclRateExtParam13Grp2 OBJECT-TYPE
                        SYNTAX Integer32
                        MAX-ACCESS read-write
                        STATUS current
                        DESCRIPTION
                                "This field is used to describe the thirteenth least
                                field of total 16 minimum guaranteed rate which
                                is configurable by user for a VCL which is bound
                                to this traffic descriptor for BAN ATM Trunk or
                                MALC uplink Cards."
                        DEFVAL { 75472 }
                        ::= { zhoneAtmVclRateExtParam 29 }

                -- 1.3.6.1.4.1.5504.4.2.2.6.30
                zhoneAtmVclRateExtParam14Grp2 OBJECT-TYPE
                        SYNTAX Integer32
                        MAX-ACCESS read-write
                        STATUS current
                        DESCRIPTION
                                "This field is used to describe the fourteenth least
                                field of total 16 minimum guaranteed rate which
                                is configurable by user for a VCL which is bound
                                to this traffic descriptor for BAN ATM Trunk or
                                MALC uplink Cards."
                        DEFVAL { 150943 }
                        ::= { zhoneAtmVclRateExtParam 30 }

                -- 1.3.6.1.4.1.5504.4.2.2.6.31
                zhoneAtmVclRateExtParam15Grp2 OBJECT-TYPE
                        SYNTAX Integer32
                        MAX-ACCESS read-write
                        STATUS current
                        DESCRIPTION
                                "This field is used to describe the fifthteenth least
                                field of total 16 minimum guaranteed rate which
                                is configurable by user for a VCL which is bound
                                to this traffic descriptor for BAN ATM Trunk or
                                MALC uplink Cards."
                        DEFVAL { 226415 }
                        ::= { zhoneAtmVclRateExtParam 31 }

                -- 1.3.6.1.4.1.5504.4.2.2.6.32
                zhoneAtmVclRateExtParam16Grp2 OBJECT-TYPE
                        SYNTAX Integer32
                        MAX-ACCESS read-write
                        STATUS current
                        DESCRIPTION
                                "This field is used to describe the sixthteenth least
                                field of total 16 minimum guaranteed rate which
                                is configurable by user for a VCL which is bound
                                to this traffic descriptor for BAN ATM Trunk or
                                MALC uplink Cards."
                        DEFVAL { 301887 }
                        ::= { zhoneAtmVclRateExtParam 32 }

                -- 1.3.6.1.4.1.5504.4.2.2.7
                zhoneAtmVplExtTable OBJECT-TYPE
                        SYNTAX SEQUENCE OF ZhoneAtmVplExtEntry
                        MAX-ACCESS not-accessible
                        STATUS current
                        DESCRIPTION
                                "Zhone extension table for the atmVplTable defined in
                                rfc2515.

                                "
                        ::= { zhoneAtmExtension 7 }

                -- 1.3.6.1.4.1.5504.4.2.2.7.1
                zhoneAtmVplExtEntry OBJECT-TYPE
                        SYNTAX ZhoneAtmVplExtEntry
                        MAX-ACCESS not-accessible
                        STATUS current
                        DESCRIPTION
                                "NOT CURRENTLY IMPLEMENTED.

                                An entry in the atmVplExtTable.

                                atmVplExtEntry is an augmentation to the atmVplEntry
                                defined in rfc2515."
                        AUGMENTS { atmVplEntry }
                        ::= { zhoneAtmVplExtTable 1 }

                ZhoneAtmVplExtEntry ::=
                        SEQUENCE {
                                zhoneAtmVplExtFaultDetectionType
                                        INTEGER,
                                zhoneAtmVplExtTrafficContainerIndex
                                        Integer32
                         }

                -- 1.3.6.1.4.1.5504.4.2.2.7.1.1
                zhoneAtmVplExtFaultDetectionType OBJECT-TYPE
                        SYNTAX INTEGER
                                {
                                disabled(1),
                                oamF4Loopback(2)
                                }
                        MAX-ACCESS read-create
                        STATUS current
                        DESCRIPTION
                                "NOT CURRENTLY IMPLEMENTED.

                                This is used to configure VPL fault detection.

                                The valid values are:

                                * disabled - Fault detection is disabled.
                                  This is the default.
                                * oamF4Loopback - This option uses standard OAM fault
                                  management cells as defined in ITU.610 for fault detection.
                                  Automatic loopback diagnostic cells are sent to the IAD.

                                When fault detection is enabled, atmVplOperStatusChange
                                notification trap is used to indicate to the NMS station
                                that a VPL has gone down or has come back up.
                                "
                        DEFVAL { disabled }
                        ::= { zhoneAtmVplExtEntry 1 }

--
                -- 1.3.6.1.4.1.5504.4.2.2.7.1.2
                zhoneAtmVplExtTrafficContainerIndex OBJECT-TYPE
                        SYNTAX Integer32 (0..2147483647)
                        MAX-ACCESS read-create
                        STATUS current
                        DESCRIPTION
                                "Index number of a PON traffic container associated with a
                                VPL definition.

                                NOTE: MULTIPLE VARBINDS ACROSS THE VPL TABLE AND
                                THE VPL EXTENSI0N TABLE ARE NOT ALLOWED!  It turns out that
                                anyone trying to set just the traffic container index would
                                inadvertantly try to create a Vpl with default settings.
                                To set the traffic container field, the Vpl must be created
                                first."
                        DEFVAL { 0 }
                        ::= { zhoneAtmVplExtEntry 2 }

                -- 1.3.6.1.4.1.5504.4.2.2.8
                zhoneAtmConnectionStatsTable OBJECT-TYPE
                        SYNTAX SEQUENCE OF ZhoneAtmConnectionStatsEntry
                        MAX-ACCESS not-accessible
                        STATUS current
                        DESCRIPTION
                                "Table which describes the allocated and available ATM
                                connections on a Zhone device."
                        ::= { zhoneAtmExtension 8 }

                -- 1.3.6.1.4.1.5504.4.2.2.8.1
                zhoneAtmConnectionStatsEntry OBJECT-TYPE
                        SYNTAX ZhoneAtmConnectionStatsEntry
                        MAX-ACCESS not-accessible
                        STATUS current
                        DESCRIPTION
                                "An entry based on shelf/slot which describes the
                                total allocated and available ATM connections for
                                that shelf/slot."
                        INDEX { zhoneShelfIndex, zhoneSlotIndex }
                        ::= { zhoneAtmConnectionStatsTable 1 }

                ZhoneAtmConnectionStatsEntry ::=
                        SEQUENCE {
                                zhoneAtmConnectionsAvailable
                                        Integer32,
                                zhoneAtmConnectionsAllocated
                                        Integer32
                         }

--
                -- 1.3.6.1.4.1.5504.4.2.2.8.1.1
                zhoneAtmConnectionsAvailable OBJECT-TYPE
                        SYNTAX Integer32
                        MAX-ACCESS read-only
                        STATUS current
                        DESCRIPTION
                                "The total available ATM connections for a particular
                                shelf/slot.

                                This number is hardware dependent.

                                Whenever a VPI is allocated for a particular shelf/slot,
                                the number of connections allocated for that VPI is
                                subtracted from the total available and is returned
                                in this value."
                        ::= { zhoneAtmConnectionStatsEntry 1 }

                -- 1.3.6.1.4.1.5504.4.2.2.8.1.2
                zhoneAtmConnectionsAllocated OBJECT-TYPE
                        SYNTAX Integer32
                        MAX-ACCESS read-only
                        STATUS current
                        DESCRIPTION
                                "The total allocated ATM connections for a particular
                                shelf/slot.

                                For a particular VPI, we calculate the number of
                                connections allocated by the following rule:

                                A VP Switched VPI has a Max VCI of 0 and uses 3 connections.

                                A VC Switched VPI has a Max VCI of n (the number n is a
                                power of 2 and is user selected) and uses n connections.

                                The sum of all allocated connections for all VPIs on
                                the selected shelf/slot is the number returned for
                                this value."
                        ::= { zhoneAtmConnectionStatsEntry 2 }

                -- 1.3.6.1.4.1.5504.4.2.2.9
                zhoneAtmVpiTable OBJECT-TYPE
                        SYNTAX SEQUENCE OF ZhoneAtmVpiEntry
                        MAX-ACCESS not-accessible
                        STATUS current
                        DESCRIPTION
                                "Table which describes attributes associated to a
                                particular VPI.

                                Anytime you add to, delete from or modify any entry
                                in this table, you must reboot the card in order for
                                these changes to take effect.  The reason for this is
                                that the APC must be re-programmed and the only way
                                to do this is by doing a reboot.

                                In addition, you will not be allowed to modify, create
                                or delete any atm-vcl entry which is on the same card
                                as the VPI until after the card has been rebooted."
                        ::= { zhoneAtmExtension 9 }

                -- 1.3.6.1.4.1.5504.4.2.2.9.1
                zhoneAtmVpiEntry OBJECT-TYPE
                        SYNTAX ZhoneAtmVpiEntry
                        MAX-ACCESS not-accessible
                        STATUS current
                        DESCRIPTION
                                "An entry based on ifIndex/vpi (which resolves to a
                                particular shelf/slot/port/subport/type/vpi) which
                                contains the maximum VCI value and the switch mode
                                (either vp or vc switched) for a particular VPI."
                        INDEX { ifIndex, atmVplVpi }
                        ::= { zhoneAtmVpiTable 1 }

                ZhoneAtmVpiEntry ::=
                        SEQUENCE {
                                zhoneAtmVpiMaxVci
                                        Integer32,
                                zhoneAtmVpiSwitched
                                        INTEGER,
                                zhoneAtmVpiRowStatus
                                        ZhoneRowStatus,
                                zhoneAtmVpiOamF4Ping
                                        INTEGER,
                                zhoneAtmVpiOamF4PingStatus
                                        TruthValue,
                                zhoneAtmVpiMaxVciPerVp
                                        Integer32
                         }

                -- 1.3.6.1.4.1.5504.4.2.2.9.1.1
                zhoneAtmVpiMaxVci OBJECT-TYPE
                        SYNTAX Integer32
                        MAX-ACCESS read-write
                        STATUS current
                        DESCRIPTION
                                "For the selected VPI, this value contains the maximum
                                VCI.

                                For vp switched VPIs, this value must be zero.

                                For vc switched VPIs, this value must be a power of 2
                                with its maximum value being hardware dependent."
                        DEFVAL { 0 }
                        ::= { zhoneAtmVpiEntry 1 }

                -- 1.3.6.1.4.1.5504.4.2.2.9.1.2
                zhoneAtmVpiSwitched OBJECT-TYPE
                        SYNTAX INTEGER
                                {
                                vp(1),
                                vc(2)
                                }
                        MAX-ACCESS read-write
                        STATUS current
                        DESCRIPTION
                                "For the selected VPI, this value can be set to either
                                vp switched or vc switched.

                                If it is vp switched, then the max vci must be zero.

                                If it is vc switched, the max vci value must be a
                                power of 2 with its maximum value being hardware
                                dependent."
                        DEFVAL { vp }
                        ::= { zhoneAtmVpiEntry 2 }

                -- 1.3.6.1.4.1.5504.4.2.2.9.1.3
                zhoneAtmVpiRowStatus OBJECT-TYPE
                        SYNTAX ZhoneRowStatus
                        MAX-ACCESS read-create
                        STATUS current
                        DESCRIPTION
                                "Row Status only supports create-and-go and destroy actions.
                                Returns active if row is in service."
                        ::= { zhoneAtmVpiEntry 3 }

                -- 1.3.6.1.4.1.5504.4.2.2.9.1.4
                zhoneAtmVpiOamF4Ping OBJECT-TYPE
                        SYNTAX INTEGER
                                {
                                disabled(1),
                                endToEnd(2),
                                segment(3)
                                }
                        MAX-ACCESS read-write
                        STATUS current
                        DESCRIPTION
                                "This is used to send a OAM F4 loopback cell for fault detection.
                                The value will automatically revert to disabled after the set
                                is complete. The valid values are:

                                * disabled - OAM F4 loopback cell is not being sent. This is the default.
                                * endToEnd - This option uses standard OAM fault management cells as
                                             defined in ITU.610 for fault detection. Setting this will
                                             send a OAM F4 end-to-end loopback cell to be sent
                                * segment - This is not supported at this time
                                "
                        DEFVAL { disabled }
                        ::= { zhoneAtmVpiEntry 4 }

                -- 1.3.6.1.4.1.5504.4.2.2.9.1.5
                zhoneAtmVpiOamF4PingStatus OBJECT-TYPE
                        SYNTAX TruthValue
                        MAX-ACCESS accessible-for-notify
                        STATUS current
                        DESCRIPTION
                                "TRUE if ping was successfull and FALSE if failed."
                        ::= { zhoneAtmVpiEntry 5 }

                -- 1.3.6.1.4.1.5504.4.2.2.9.1.6
                zhoneAtmVpiMaxVciPerVp OBJECT-TYPE
                        SYNTAX Integer32
                        MAX-ACCESS read-write
                        STATUS current
                        DESCRIPTION
                                "If vp-switched, but VG connection is vc-switched,
                                this specifies max number of vci on gateway."
                        ::= { zhoneAtmVpiEntry 6 }

                -- 1.3.6.1.4.1.5504.4.2.2.10
                atmVpi OBJECT-TYPE
                        SYNTAX AtmVpIdentifier
                        MAX-ACCESS accessible-for-notify
                        STATUS current
                        DESCRIPTION
                                "VPI used for traps defined under atm traps"
                        ::= { zhoneAtmExtension 10 }

                -- 1.3.6.1.4.1.5504.4.2.2.11
                atmVci OBJECT-TYPE
                        SYNTAX AtmVcIdentifier
                        MAX-ACCESS accessible-for-notify
                        STATUS current
                        DESCRIPTION
                                "VCI used for traps defined under atm traps"
                        ::= { zhoneAtmExtension 11 }

                -- 1.3.6.1.4.1.5504.4.2.2.12
                atmVpiAutoCreateDone OBJECT-TYPE
                        SYNTAX TruthValue
                        MAX-ACCESS accessible-for-notify
                        STATUS current
                        DESCRIPTION
                                "Indicates automatic Vpi generation complete."
                        ::= { zhoneAtmExtension 12 }

                -- 1.3.6.1.4.1.5504.4.2.2.13
                atmVpiAutoCreateCount OBJECT-TYPE
                        SYNTAX Integer32
                        MAX-ACCESS accessible-for-notify
                        STATUS current
                        DESCRIPTION
                                "This value is the count of the number of auto-created Vpis."
                        ::= { zhoneAtmExtension 13 }

                -- 1.3.6.1.4.1.5504.4.2.2.16
                atmVclToMulticastMap OBJECT IDENTIFIER ::= { zhoneAtmExtension 16 }

                -- 1.3.6.1.4.1.5504.4.2.2.16.1
                atmVclToMulticastMapIndexNext OBJECT-TYPE
                        SYNTAX INTEGER (0..65535)
                        MAX-ACCESS read-only
                        STATUS current
                        DESCRIPTION
                                "This object contains an appropriate value to be used
                                for atmMulticastAddressVclMapIndex when creating
                                entries in the atmMulticastAddressVclMapTable.  The
                                value 0 indicates that no unassigned entries are
                                available. To obtain the atmMulticastAddressVclMapIndex
                                value for a new entry, the manager issues a management
                                protocol retrieval operation to obtain the current value
                                of this object.  After each retrieval, the agent should
                                modify the value to the next unassigned index.

                                After a manager retrieves a value the agent will
                                determine through its local policy when this index
                                value will be made available for reuse."
                        ::= { atmVclToMulticastMap 1 }

                -- 1.3.6.1.4.1.5504.4.2.2.16.2
                atmVclToMulticastMapTable OBJECT-TYPE
                        SYNTAX SEQUENCE OF AtmVclToMulticastMapEntry
                        MAX-ACCESS not-accessible
                        STATUS current
                        DESCRIPTION
                                "The Multicast Address to Vcl Mapping table.  Each
                                entry in this table associates a multicast address
                                representing a video stream with a Vcl.  All of the
                                entries in this table are assumed to be unique, not
                                only in terms of index, but in terms of (index,
                                multicast address) <-> (ifIndex, vpi, vci).

                                Note that the Vcl type for this table should always
                                be 'other', denoting cell relay pass-through.  We
                                are not terminating the IP stream on the MALC.

                                Also note that the Vcls that this table refer to
                                are the ones originating at the Video Head-End,
                                coming into the MALC Uplink card."
                        ::= { atmVclToMulticastMap 2 }

                -- 1.3.6.1.4.1.5504.4.2.2.16.2.1
                atmVclToMulticastMapEntry OBJECT-TYPE
                        SYNTAX AtmVclToMulticastMapEntry
                        MAX-ACCESS not-accessible
                        STATUS current
                        DESCRIPTION
                                "An entry in the Multicast Address to Vcl Mapping table.
                                This entry is used to associate a multicast address with
                                a Vcl.

                                Step-wise Procedures to set up a Multicast Vcl Mapping profile

                                Once the Vcl that carries the video stream is created, the
                                following steps are taken to provision a Multicast Address
                                to Vcl Mapping:

                                    (1) The manager obtains a unique atmMulticastAddressVclMapIndex
                                        by reading the atmMulticastAddressVclMapIndexNext object.

                                    (2) Next, the manager creates a row in the
                                        atmMulticastAddressVclMapTable by setting
                                        atmMulticastAddressVclMapRowStatus to createAndGo.
                                        The agent checks the sanity of the Vcl, domain index,
                                        and multicast address.  The row creation fails if:
                                        - the specified Vcl does not exist,
                                        - the specified Vcl is not of the correct type for
                                          multicasting,
                                        - the routing domain index is outside of the supported range,
                                        - the multicast address is not of the correct format.
                                     (3) The manager promotes the row in the
                                         atmMulticastAddressVclMapTable when the 'set' completes."
                        INDEX { atmVclToMulticastMapIndex }
                        ::= { atmVclToMulticastMapTable 1 }

                AtmVclToMulticastMapEntry ::=
                        SEQUENCE {
                                atmVclToMulticastMapIndex
                                        INTEGER,
                                atmVclToMulticastMapRoutingDomain
                                        INTEGER,
                                atmVclToMulticastMapMulticastAddress
                                        IpAddress,
                                atmVclToMulticastMapIfIndex
                                        InterfaceIndex,
                                atmVclToMulticastMapVpi
                                        AtmVpIdentifier,
                                atmVclToMulticastMapVci
                                        AtmVcIdentifier,
                                atmVclToMulticastMapRowStatus
                                        ZhoneRowStatus
                         }

                -- 1.3.6.1.4.1.5504.4.2.2.16.2.1.1
                atmVclToMulticastMapIndex OBJECT-TYPE
                        SYNTAX INTEGER (1..65535)
                        MAX-ACCESS not-accessible
                        STATUS current
                        DESCRIPTION
                                "A unique value to identify this Multicast Address to
                                Vcl mapping."
                        ::= { atmVclToMulticastMapEntry 1 }

                -- 1.3.6.1.4.1.5504.4.2.2.16.2.1.2
                atmVclToMulticastMapRoutingDomain OBJECT-TYPE
                        SYNTAX INTEGER (0..65535)
                        MAX-ACCESS read-create
                        STATUS current
                        DESCRIPTION
                                "Routing domain of the Head-End video server."
                        ::= { atmVclToMulticastMapEntry 2 }

                -- 1.3.6.1.4.1.5504.4.2.2.16.2.1.3
                atmVclToMulticastMapMulticastAddress OBJECT-TYPE
                        SYNTAX IpAddress
                        MAX-ACCESS read-create
                        STATUS current
                        DESCRIPTION
                                "Multicast IP address contained in the MPEG2 video stream."
                        ::= { atmVclToMulticastMapEntry 3 }

                -- 1.3.6.1.4.1.5504.4.2.2.16.2.1.4
                atmVclToMulticastMapIfIndex OBJECT-TYPE
                        SYNTAX InterfaceIndex
                        MAX-ACCESS read-create
                        STATUS current
                        DESCRIPTION
                                "The ifIndex value of the ATM interface for the Vcl
                                carrying a video stream."
                        ::= { atmVclToMulticastMapEntry 4 }

                -- 1.3.6.1.4.1.5504.4.2.2.16.2.1.5
                atmVclToMulticastMapVpi OBJECT-TYPE
                        SYNTAX AtmVpIdentifier
                        MAX-ACCESS read-create
                        STATUS current
                        DESCRIPTION
                                "The VPI value of the ATM interface for the Vcl
                                carrying a video stream."
                        ::= { atmVclToMulticastMapEntry 5 }

                -- 1.3.6.1.4.1.5504.4.2.2.16.2.1.6
                atmVclToMulticastMapVci OBJECT-TYPE
                        SYNTAX AtmVcIdentifier
                        MAX-ACCESS read-create
                        STATUS current
                        DESCRIPTION
                                "The VCI value of the ATM interface for the Vcl
                                carrying a video stream."
                        ::= { atmVclToMulticastMapEntry 6 }

                -- 1.3.6.1.4.1.5504.4.2.2.16.2.1.7
                atmVclToMulticastMapRowStatus OBJECT-TYPE
                        SYNTAX ZhoneRowStatus
                        MAX-ACCESS read-create
                        STATUS current
                        DESCRIPTION
                                "Row status of the multicast address to Vcl table entry.
                                This object must be initially set to 'createAndGo'."
                        ::= { atmVclToMulticastMapEntry 7 }

                -- 1.3.6.1.4.1.5504.4.2.2.17
                zhoneAtmPonExtTable OBJECT-TYPE
                        SYNTAX SEQUENCE OF ZhoneAtmPonExtEntry
                        MAX-ACCESS not-accessible
                        STATUS deprecated
                        DESCRIPTION
                                "This is the Zhone extension to the Atm Vcl Table (rfc2515.)
                                It contains APON-related objects."
                        ::= { zhoneAtmExtension 17 }

                -- 1.3.6.1.4.1.5504.4.2.2.17.1
                zhoneAtmPonExtEntry OBJECT-TYPE
                        SYNTAX ZhoneAtmPonExtEntry
                        MAX-ACCESS not-accessible
                        STATUS deprecated
                        DESCRIPTION
                                "This is an entry in the Atm PON Extension table."
                        AUGMENTS { atmVclEntry }
                        ::= { zhoneAtmPonExtTable 1 }

                ZhoneAtmPonExtEntry ::=
                        SEQUENCE {
                                zhoneAtmVclPonTrafficContainerIndex
                                        Integer32
                         }

                -- 1.3.6.1.4.1.5504.4.2.2.17.1.1
                zhoneAtmVclPonTrafficContainerIndex OBJECT-TYPE
                        SYNTAX Integer32 (0..65535)
                        MAX-ACCESS read-create
                        STATUS deprecated
                        DESCRIPTION
                                "This field is an index into the ATM PON Traffic Container table.
                                It associated a Vcl with a Traffic Container, and is used to
                                retrieve PON channel provisioning information."
                        DEFVAL { 0 }
                        ::= { zhoneAtmPonExtEntry 1 }

                -- 1.3.6.1.4.1.5504.4.2.2.18
                zhoneAtmVplPonExtTable OBJECT-TYPE
                        SYNTAX SEQUENCE OF ZhoneAtmVplPonExtEntry
                        MAX-ACCESS not-accessible
                        STATUS deprecated
                        DESCRIPTION
                                "This is the Zhone extension to the Atm Vpl Table (rfc2515.)
                                It contains APON-related objects."
                        ::= { zhoneAtmExtension 18 }

                -- 1.3.6.1.4.1.5504.4.2.2.18.1
                zhoneAtmVplPonExtEntry OBJECT-TYPE
                        SYNTAX ZhoneAtmVplPonExtEntry
                        MAX-ACCESS not-accessible
                        STATUS deprecated
                        DESCRIPTION
                                "This is an entry in the Atm PON Extension table."
                        AUGMENTS { atmVplEntry }
                        ::= { zhoneAtmVplPonExtTable 1 }

                ZhoneAtmVplPonExtEntry ::=
                        SEQUENCE {
                                zhoneAtmVplPonTrafficContainerIndex
                                        Integer32
                         }

                -- 1.3.6.1.4.1.5504.4.2.2.18.1.1
                zhoneAtmVplPonTrafficContainerIndex OBJECT-TYPE
                        SYNTAX Integer32 (0..2147483647)
                        MAX-ACCESS read-create
                        STATUS deprecated
                        DESCRIPTION
                                "This field is an index into the ATM PON Traffic Container table.
                                It associated a Vpl with a Traffic Container, and is used to
                                retrieve PON channel provisioning information."
                        DEFVAL { 0 }
                        ::= { zhoneAtmVplPonExtEntry 1 }

                -- 1.3.6.1.4.1.5504.4.2.2.19
                zhoneAtmInterfaceTcExtTable OBJECT-TYPE
                        SYNTAX SEQUENCE OF ZhoneAtmInterfaceTcExtEntry
                        MAX-ACCESS not-accessible
                        STATUS current
                        DESCRIPTION
                                "This table contains ATM interface TC
                                Sublayer parameters and state variables,
                                one entry per ATM interface port."
                        ::= { zhoneAtmExtension 19 }

                -- 1.3.6.1.4.1.5504.4.2.2.19.1
                zhoneAtmInterfaceTcExtEntry OBJECT-TYPE
                        SYNTAX ZhoneAtmInterfaceTcExtEntry
                        MAX-ACCESS not-accessible
                        STATUS current
                        DESCRIPTION
                                "This list contains TC Sublayer parameters
                                and state variables at the ATM interface and is
                                indexed by the ifIndex value of the ATM interface."
                        AUGMENTS { atmInterfaceTCEntry }
                        ::= { zhoneAtmInterfaceTcExtTable 1 }

                ZhoneAtmInterfaceTcExtEntry ::=
                        SEQUENCE {
                                zhoneAtmInterfaceNCDEvents
                                        Counter32,
                                zhoneAtmInterfaceHECEvents
                                        Counter32,
                                zhoneAtmInterfaceFeOCDEvents
                                        Counter32,
                                zhoneAtmInterfaceFeNCDEvents
                                        Counter32,
                                zhoneAtmInterfaceFeHECEvents
                                        Counter32
                         }

--
                -- 1.3.6.1.4.1.5504.4.2.2.19.1.1
                zhoneAtmInterfaceNCDEvents OBJECT-TYPE
                        SYNTAX Counter32
                        MAX-ACCESS read-only
                        STATUS current
                        DESCRIPTION
                                "The number of times the Near-end No Cell Delineation (NCD) events occur. "
                        ::= { zhoneAtmInterfaceTcExtEntry 1 }

                -- 1.3.6.1.4.1.5504.4.2.2.19.1.2
                zhoneAtmInterfaceHECEvents OBJECT-TYPE
                        SYNTAX Counter32
                        MAX-ACCESS read-only
                        STATUS current
                        DESCRIPTION
                                "The number of times Near-end Header Error Control (HEC) violations
                                occur. "
                        ::= { zhoneAtmInterfaceTcExtEntry 2 }

                -- 1.3.6.1.4.1.5504.4.2.2.19.1.3
                zhoneAtmInterfaceFeOCDEvents OBJECT-TYPE
                        SYNTAX Counter32
                        MAX-ACCESS read-only
                        STATUS current
                        DESCRIPTION
                                "The number of times Far-end Out of Cell Delineation (OCD) events occur. "
                        ::= { zhoneAtmInterfaceTcExtEntry 3 }

                -- 1.3.6.1.4.1.5504.4.2.2.19.1.4
                zhoneAtmInterfaceFeNCDEvents OBJECT-TYPE
                        SYNTAX Counter32
                        MAX-ACCESS read-only
                        STATUS current
                        DESCRIPTION
                                "The number of times Far-end No Cell Delineation (NCD) events
                                occur. "
                        ::= { zhoneAtmInterfaceTcExtEntry 4 }

                -- 1.3.6.1.4.1.5504.4.2.2.19.1.5
                zhoneAtmInterfaceFeHECEvents OBJECT-TYPE
                        SYNTAX Counter32
                        MAX-ACCESS read-only
                        STATUS current
                        DESCRIPTION
                                "The number of times Far-end Header Error Control (HEC) violations
                                occur. "
                        ::= { zhoneAtmInterfaceTcExtEntry 5 }


                -- 1.3.6.1.4.1.5504.4.2.2.20
                zhoneAtmVcCrossConnectExtTable OBJECT-TYPE
                        SYNTAX SEQUENCE OF ZhoneAtmVcCrossConnectExtEntry
                        MAX-ACCESS not-accessible
                        STATUS current
                        DESCRIPTION
                                "This Table contains Atm Vc Cross Connect Extensions
                                to the atmVcCrossConnectEntry."
                        ::= { zhoneAtmExtension 20 }

                -- 1.3.6.1.4.1.5504.4.2.2.20.1
                zhoneAtmVcCrossConnectExtEntry OBJECT-TYPE
                        SYNTAX ZhoneAtmVcCrossConnectExtEntry
                        MAX-ACCESS not-accessible
                        STATUS current
                        DESCRIPTION
                                "This list contains Atm Vc Cross Connect Extensions
                                to the atmVcCrossConnectEntry."
                        AUGMENTS { atmVcCrossConnectEntry }
                        ::= { zhoneAtmVcCrossConnectExtTable 1 }

                ZhoneAtmVcCrossConnectExtEntry ::=
                        SEQUENCE {
                                zhoneAtmVcCrossConnectExtHandleId
                                        OCTET STRING
                         }

                -- 1.3.6.1.4.1.5504.4.2.2.20.1.1
                zhoneAtmVcCrossConnectExtHandleId OBJECT-TYPE
                    SYNTAX  OCTET STRING (SIZE (1..16))
                    MAX-ACCESS read-create
                    STATUS  current
                    DESCRIPTION
                            "An administratively-assigned name for the
                             Atm Vc Cross Connect indicated by the INDEX
                             value."
                    ::= { zhoneAtmVcCrossConnectExtEntry 1 }

        END

--
-- comAtm.mib
--
