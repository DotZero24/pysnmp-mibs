--
-- phyDs1.mib
-- MIB generated by MG-SOFT Visual MIB Builder Version 3.0 Build 285
-- Monday, November 02, 2009 at 16:15:28
--

	ZHONE-Wan-MIB DEFINITIONS ::= BEGIN

		IMPORTS
			ifIndex, ifAlias, InterfaceIndex
				FROM IF-MIB
			PerfCurrentCount, PerfIntervalCount, PerfTotalCount
				FROM PerfHist-TC-MIB
			Integer32, OBJECT-TYPE, MODULE-IDENTITY, NOTIFICATION-TYPE
				FROM SNMPv2-SMI
			TimeStamp, TruthValue
				FROM SNMPv2-TC
			zhoneDsx
				FROM Zhone
			ZhoneAdminString
				FROM Zhone-TC;


-- To Create generated mib handler:
-- /vob/EPILOGUE/binaries/emissary/solaris/mibcomp rfc1907.mib iftype.mib rfc2233.mib rfc2493.mib Zhone.mib Zhone-TC.mib -stub -o ds1MibHdlr.c phyDs1.mib
-- To create generated protection layer:
-- /vob/zhonetools/bin/pahrser.pl  rfc1907.mib iftype.mib rfc2233.mib rfc2493.mib Zhone.mib Zhone-TC.mib phyDs1.mib
--
--
--
--
--
--
--
--
--
--
--
		-- 1.3.6.1.4.1.5504.5.2.1
		zhoneDs1Mib MODULE-IDENTITY
			LAST-UPDATED "200905120738Z"		-- May 12, 2009 at 07:38 GMT
			ORGANIZATION
				"Zhone Technologies."
			CONTACT-INFO
				"   Postal:
				           Zhone Technologies, Inc.
				           @ Zhone Way
				           7001 Oakport Street
				           Oakland, CA  94621
				           USA
				Toll-Free: +1 877-ZHONE20 (+1 877-946-6320)
				      Tel: +1-510-777-7000
				      Fax: +1-510-777-7001
				   E-mail: support@zhone.com"
			DESCRIPTION
				"The zhone WAN MIB for configuration of the line.
				This mib handles CSU and DSX mode."
			REVISION "200907231115Z"		-- July 23, 2009 at 11:15 GMT
			DESCRIPTION
				"Added zhoneDs1BertTable."
			REVISION "200905120738Z"		-- May 12, 2009 at 07:38 GMT
			DESCRIPTION
				"Obsoleted zhoneDs1TxClockRecovery,
				functionality moved to ZHONE-CARD-RESOURCES-MIB
				object cardPweTrafficMode."
			REVISION "200811100858Z"		-- November 10, 2008 at 08:58 GMT
			DESCRIPTION
				"Added zhoneDs1TxClockRecovery and
				zhoneDs1TxClockAdaptiveQuality for
				PWE timing."
			REVISION "200605121246Z"		-- May 12, 2006 at 12:46 GMT
			DESCRIPTION
				"Added Timeslot Assignment"
			REVISION "200402051147Z"		-- February 05, 2004 at 11:47 GMT
			DESCRIPTION
				"V01.01.10 - Add ds1LinePower."
			REVISION "200401211536Z"		-- January 21, 2004 at 15:36 GMT
			DESCRIPTION
				"V01.01.09 - Added DS1 Group Index to ds1 profile"
			REVISION "200305151315Z"		-- May 15, 2003 at 13:15 GMT
			DESCRIPTION
				"V01.01.08 added ifAlias to the OBJECTS clause for
				zhoneLineStatusChange trap."
			REVISION "200302041312Z"		-- February 04, 2003 at 13:12 GMT
			DESCRIPTION
				"V01.01.07 added zhoneDs1ProtocolEmulation & zhoneDs1SignalType
				"
			REVISION "200110221004Z"		-- October 22, 2001 at 10:04 GMT
			DESCRIPTION
				"V01.01.07 Updated description for zhoneClockSourceEligibility"
			REVISION "200108221350Z"		-- August 22, 2001 at 13:50 GMT
			DESCRIPTION
				"V01.01.06 Added Coset Polynomial as a part a ds1_profile"
			REVISION "200108141624Z"		-- August 14, 2001 at 16:24 GMT
			DESCRIPTION
				"V01.01.05 Added Cell Scrambling as a part a ds1_profile"
			REVISION "200108091007Z"		-- August 09, 2001 at 10:07 GMT
			DESCRIPTION
				"V01.01.04 Add unframed  ds1/e1 options into zhoneLineType this is required by DS1/E1 ATM Trunk card"
			REVISION "200101181328Z"		-- January 18, 2001 at 13:28 GMT
			DESCRIPTION
				"V01.01.03 Changes to the DS1 transmit clock source"
			REVISION "200101041119Z"		-- January 04, 2001 at 11:19 GMT
			DESCRIPTION
				"V01.01.02 Add comments for supported fields in this release.
				Added sendCode types for E1 to MIB definition.
				Statistics and far end information is not supported in this
				release."
			REVISION "200011131130Z"		-- November 13, 2000 at 11:30 GMT
			DESCRIPTION
				"V01.01.01 Description for Payloadloop corrected"
			REVISION "200009211027Z"		-- September 21, 2000 at 10:27 GMT
			DESCRIPTION
				"V01.01.00 Ds1Trap Prefix corrected"
			REVISION "200009121359Z"		-- September 12, 2000 at 13:59 GMT
			DESCRIPTION
				"V01.00.00 Initial Release"
			::= { zhoneDsx 1 }




--
-- Node definitions
--

		-- 1.3.6.1.4.1.5504.5.2.2
		zhoneDs1Table OBJECT-TYPE
			SYNTAX SEQUENCE OF ZhoneDs1Entry
			MAX-ACCESS not-accessible
			STATUS current
			DESCRIPTION
				"The DS1 Configuration table.

				Statistical information not supported on BAN in
				this release."
			::= { zhoneDsx 2 }


		-- 1.3.6.1.4.1.5504.5.2.2.1
		zhoneDs1Entry OBJECT-TYPE
			SYNTAX ZhoneDs1Entry
			MAX-ACCESS not-accessible
			STATUS current
			DESCRIPTION
				"An entry in the DS1 Configuration table."
			INDEX { zhoneLineIndex }
			::= { zhoneDs1Table 1 }


		ZhoneDs1Entry ::=
			SEQUENCE {
				zhoneLineIndex
					InterfaceIndex,
				zhoneTimeElapsed
					INTEGER,
				zhoneValidIntervals
					INTEGER,
				zhoneLineType
					INTEGER,
				zhoneLineCoding
					INTEGER,
				zhoneSendCode
					INTEGER,
				zhoneCircuitIdentifier
					ZhoneAdminString,
				zhoneLoopbackConfig
					INTEGER,
				zhoneLineStatus
					INTEGER,
				zhoneSignalMode
					INTEGER,
				zhoneTransmitClockSource
					INTEGER,
				zhoneFdl
					INTEGER,
				zhoneInvalidIntervals
					INTEGER,
				zhoneDsxLineLength
					INTEGER,
				zhoneLineStatusLastChange
					TimeStamp,
				zhoneLineStatusChangeTrapEnable
					INTEGER,
				zhoneLoopbackStatus
					INTEGER,
				zhoneDs1ChannelNumber
					INTEGER,
				zhoneChannelization
					INTEGER,
				zhoneDs1Mode
					INTEGER,
				zhoneCsuLineLength
					INTEGER,
				zhoneClockSourceEligibility
					INTEGER,
				zhoneCellScramble
					TruthValue,
				zhoneCosetPolynomial
					TruthValue,
				zhoneDs1ProtocolEmulation
					INTEGER,
				zhoneDs1SignalType
					INTEGER,
				zhoneDs1GroupIndex
					INTEGER,
				zhoneDs1LinePower
					INTEGER,
				zhoneDs1TimeslotAssignment
					BITS,
				zhoneDs1TxClockRecovery
					INTEGER,
				zhoneDs1TxClockAdaptiveQuality
					INTEGER
			 }

		-- 1.3.6.1.4.1.5504.5.2.2.1.1
		zhoneLineIndex OBJECT-TYPE
			SYNTAX InterfaceIndex
			MAX-ACCESS not-accessible
			STATUS current
			DESCRIPTION
				"This object should be made equal to ifIndex.
				Making the object equal to ifIndex allows proper
				use of ifStackTable and ds0/ds0bundle mibs."
			::= { zhoneDs1Entry 1 }


--
		-- 1.3.6.1.4.1.5504.5.2.2.1.2
		zhoneTimeElapsed OBJECT-TYPE
			SYNTAX INTEGER (0..899)
			MAX-ACCESS read-only
			STATUS current
			DESCRIPTION
				"The number of seconds that have elapsed since
				the beginning of the near end current error-
				measurement period.  If, for some reason, such
				as an adjustment in the system's time-of-day
				clock, the current interval exceeds the maximum
				value, the agent will return the maximum value."
			::= { zhoneDs1Entry 2 }


--
		-- 1.3.6.1.4.1.5504.5.2.2.1.3
		zhoneValidIntervals OBJECT-TYPE
			SYNTAX INTEGER (0..96)
			MAX-ACCESS read-only
			STATUS current
			DESCRIPTION
				"The numberof previous near end intervals for
				which data was collected. The value will be
				96 unless the interface was brouht online within
				the last 24 hours, in which case the value will be
				the number of complete 15 minute near end
				intervals since the interface has been oline.  In
				the case where the agent is a proxxy, it is
				possible that some intervals are unavailable.  In
				this case, the interval is the maximum interval
				number for which data is available.
				"
			::= { zhoneDs1Entry 3 }


--
		-- 1.3.6.1.4.1.5504.5.2.2.1.4
		zhoneLineType OBJECT-TYPE
			SYNTAX INTEGER
				{
				other(1),
				esf(2),
				d4(3),
				slc96(4),
				e1(5),
				e1Crc(6),
				e1Mf(7),
				e1CrcMf(8),
				e1Unframed(9),
				ds1Unframed(10)
				}
			MAX-ACCESS read-write
			STATUS current
			DESCRIPTION
				"This variable indicates  the  variety  of  DS1
				Line  implementing  this  circuit.  The type of
				circuit affects the number of bits  per  second
				that  the circuit can reasonably carry, as well
				as the interpretation of the  usage  and  error
				statistics.  The values, in sequence, describe:

				TITLE:         SPECIFICATION:
				other(1)       (not supported in this release)
				esf(2)         Extended SuperFrame DS1 (T1.107)
				d4(3)          AT&T D4 format DS1 (T1.107)
				slc96(4)       (not supported in this release)
				e1(5)          ITU-T Recommendation G.704
				               (not supported in this release)
				e1Crc(6)       ITU-T Recommendation G.704
				               (not supported in this release)
				e1Mf(7)        G.704 multiframing enabled
				e1CrcMf(8)     G.704 multiframing enabled and crc enabled
				e1Unframed(9)  E1 with no framing
				ds1Unframed(10) Ds1 with no framing

				For clarification, the capacity for each E1 type
				is as listed below:
				e1 or e1Crc - e1, with framing,
				   no signalling = 31 x 64k = 1984k
				e1Mf or e1CrcMf - e1, with framing,
				   signalling = 30 x 64k = 1920k

				For further information See ITU-T Recomm G.704

				Default is set to esf for T1 platforms and e1CrcMf for E1
				platforms.
				BAN E1: esf,d4 T1:e1,e1mf,e1crcmf"
			::= { zhoneDs1Entry 4 }


--
		-- 1.3.6.1.4.1.5504.5.2.2.1.5
		zhoneLineCoding OBJECT-TYPE
			SYNTAX INTEGER
				{
				jbzs(1),
				b8zs(2),
				hdb3(3),
				zbtsi(4),
				ami(5),
				other(6),
				b6zs(7)
				}
			MAX-ACCESS read-write
			STATUS current
			DESCRIPTION
				"This variable describes the variety of Zero Code
				Suppression used on this interface, which in turn
				affects a number of its characteristics.
				jbzs refers the Jammed Bit Zero Suppression,
				in which the AT&T specification of at least one
				pulse every 8 bit periods is literally implemented
				by forcing a pulse in bit 8 of each channel.
				Thus, only seven bits per channel, or 1.344 Mbps,
				is available for data.
				b8zs refers to the use of a specified pattern
				of normal bits and bipolar violations which are
				used to replace a sequence of eight zero bits.
				ANSI Clear Channels may use zbtsi, or Zero
				Byte Time Slot Interchange.
				E1 links, with or without CRC, use hdb3 or
				ami.
				ami refers to a mode wherein no zero code
				suppression is present and the line encoding does
				not solve the problem directly.  In this
				application, the higher layer must provide data
				which meets or exceeds the pulse density
				requirements, such as inverting HDLC data.
				b6zs refers to the user of a specifed pattern
				of normal bits and bipolar violations which are
				used to replace a sequence of six zero bits.  Used
				for DS2.

				Default is set to b8zs for T1 platforms and hdb3 for E1.

				TITLE:         AVAILABILITY:
				jbzs(1)        (not supported in this release)
				b8zs(2)        (not supported for e1 lineTypes)
				hdb3(3)        (supported for e1 lineTypes)
				zbtsi(4)       (not supported in this release)
				ami(5)
				other(6)       (not supported in this release)
				b6zs(7)        (not supported in this rele
				BAN E1: hdb3,ami; T1: b8zs,ami"
			::= { zhoneDs1Entry 5 }


--
		-- 1.3.6.1.4.1.5504.5.2.2.1.6
		zhoneSendCode OBJECT-TYPE
			SYNTAX INTEGER
				{
				sendNoCode(1),
				sendLineCode(2),
				sendPayloadCode(3),
				sendResetCode(4),
				sendQRSSPattern(5),
				send511Pattern(6),
				send3in24Pattern(7),
				sendOtherTestPattern(8),
				send2047Pattern(9),
				send1in2Pattern(10),
				sendInbandCode(11),
				sendInbandCodeOff(12),
				sendLineCodeOff(13),
				sendPayloadCodeOff(14),
				send2ToPower9Minus1Pattern(15),
				send2ToPower11Minus1Pattern(16),
				send2ToPower15Minus1Pattern(17),
				send2ToPower20Minus1Pattern(18),
				send2ToPower23Minus1Pattern(19)
				}
			MAX-ACCESS read-write
			STATUS current
			DESCRIPTION
				"This variable indicates what type of code is
				being sent across the DS1 interface by the device.
				Setting this variable causes the interface to send
				the code requested.  The values mean:
				SendNoCode
				sending looped or normal data

				sendLineCode
				sending a request for a line loopback

				T1 related sendCodes
				------------------------------------------
				sendPayloadCode
				sending a request for a payload loopback

				sendResetCode
				sending a loopback termination request

				sendQRSSPattern
				sending a Quasi-Random Signal  (QRS)  test
				pattern

				send511Pattern
				sending a 511 bit fixed test pattern

				send3in24Pattern
				sending a fixed test pattern of 3 bits set
				in 24

				sendOtherTestPattern
				sending a test pattern  other  than  those
				described by this object

				send2047Pattern,
				sending 2047 test pattern.

				send1in2Pattern,
				sending alternate one , zero pattern.

				sendInbandCode,
				sending inband loopback command.

				sendInbandCodeOff,
				sending inband loopback off command.

				sendLineCodeOff,
				sending line loopback command.

				sendPayloadCodeOff,
				sending payload loopback command.

				E1 related send codes
				------------------------------------------
				send2ToPower9Minus1Pattern
				refer to O.153

				send2ToPower11Minus1Pattern
				refer to O.152 and O.153

				send2ToPower15Minus1Pattern
				refer to O.151

				send2ToPower20Minus1Pattern
				refer to O.153 QRSS bit = 1

				send2ToPower23Minus1Pattern
				refer to O.151

				Only sendNoCode is supported on E1 platforms
				in this release.
				N/A for BAN "
			DEFVAL { sendNoCode }
			::= { zhoneDs1Entry 6 }


--
		-- 1.3.6.1.4.1.5504.5.2.2.1.7
		zhoneCircuitIdentifier OBJECT-TYPE
			SYNTAX ZhoneAdminString
			MAX-ACCESS read-write
			STATUS current
			DESCRIPTION
				"This variable contains the transmission vendor's
				circuit identifier, for the purpose of
				facilitating troubleshooting."
			::= { zhoneDs1Entry 7 }


--
		-- 1.3.6.1.4.1.5504.5.2.2.1.8
		zhoneLoopbackConfig OBJECT-TYPE
			SYNTAX INTEGER
				{
				noLoop(1),
				lineLoop(2),
				localLoop(3),
				payloadLoop(4)
				}
			MAX-ACCESS read-write
			STATUS current
			DESCRIPTION
				"This variable represents the desired loopback
				configuration of the DS1 interface.  Agents
				supporting read/write access should return
				inconsistentValue in response to a requested
				loopback state that the interface does not
				support.  The values mean:

				noLoop
				 Not in the loopback state.  A device that is not
				capable of performing a loopback on the interface
				shall always return this as its value.

				lineLoop
				 The received signal at this interface does not go
				through the device (minimum penetration) but is
				looped back out.

				localLoop
				 The transmitted signal at this interface is
				looped back and received by the same interface.
				What is transmitted onto the line is product
				dependent.

				payloadLoop
				 The received signal at this interface is looped
				through the device. Typically the received signal
				is looped back for retransmission after it has
				passed through the device's framing function.

				"
			DEFVAL { noLoop }
			::= { zhoneDs1Entry 8 }


--
		-- 1.3.6.1.4.1.5504.5.2.2.1.9
		zhoneLineStatus OBJECT-TYPE
			SYNTAX INTEGER (1..65536)
			MAX-ACCESS read-only
			STATUS current
			DESCRIPTION
				"This variable indicates the Line Status of the
				interface.  It contains loopback, failure,
				received 'alarm' and transmitted 'alarms
				information.
				If the zhloopbackState bit is set, the loopback
				in effect can be determined from the
				loopbackConfig object.
				The various bit positions are:
				noAlarm(1)           No alarm present
				rcvFarEndLOF(2)      Far end LOF (a.k.a., Yellow Alarm)
				xmtFarEndLOF(4)      Near end sending LOF Indication
				rcvAIS(8)            Far end sending AIS
				xmtAIS(16)            Near end sending AIS
				lossOfFrame(32       Near end LOF (a.k.a., Red Alarm)
				lossOfSignal(64)      Near end Loss Of Signal
				loopbackState(128)     Near end is looped
				ts16AIS(256)            E1 TS16 AIS
				rcvFarEndLOMF(512)    Far End Sending TS16 LOMF
				xmtFarEndLOMF(1024)    Near End Sending TS16 LOMF
				rcvTestCode(2048)      Near End detects a test code
				otherFailure(4096)     any line status not defined here
				unavailSigState(8192)  Near End in Unavailable Signal State
				netEquipOOS(16384)      Carrier Equipment Out of Service
				"
			::= { zhoneDs1Entry 9 }


--
		-- 1.3.6.1.4.1.5504.5.2.2.1.10
		zhoneSignalMode OBJECT-TYPE
			SYNTAX INTEGER
				{
				none(1),
				robbedBit(2),
				bitOriented(3),
				messageOriented(4),
				other(5)
				}
			MAX-ACCESS read-write
			STATUS current
			DESCRIPTION
				"'none' indicates that no bits are reserved for
				signaling on this channel.

				'robbedBit' indicates that DS1 Robbed Bit  Sig-
				naling is in use.

				'bitOriented' indicates that E1 Channel  Asso-
				ciated Signaling is in use.

				'messageOriented' indicates that Common  Chan-
				nel Signaling is in use either on channel 16 of
				an E1 link or channel 24 of a DS1.

				Default is set to robbedBit for T1 platforms and
				messageOriented for E1.

				TITLE:             AVAILABILITY:
				none(1)
				robbedBit(2)       (not supported for E1 lineTypes)
				bitOriented(3)     (only supported for E1 lineTypes)
				messageOriented(4) has the same effect as none
				other(5)           (not supported in this release)
				N/A For BAN"
			::= { zhoneDs1Entry 10 }


		-- 1.3.6.1.4.1.5504.5.2.2.1.11
		zhoneTransmitClockSource OBJECT-TYPE
			SYNTAX INTEGER
				{
				loopTiming(1),
				localTiming(2),
				throughTiming(3),
				sonetThroughTiming(4)
				}
			MAX-ACCESS read-write
			STATUS current
			DESCRIPTION
				"Reflects the source of Transmit Clock.
				'loopTiming' indicates that the recovered receive clock
				is used as the transmit clock.
				Only set if this DS1 has zhoneClockSourceEligibility
				equal to 'eligible' and the state of that ds1 is 'up'
				and the ds1 resource provider decided this DS1
				is to provide the transmit clock for all the DS1s.
				Only one DS1 will have this set per platform.

				'localTiming' indicates that a local clock
				source is used or when an external clock is
				attached to the box containing the interface.

				'throughTiming' indicates that recovered receive clock
				from another interface is used as the transmit clock.
				Example: If a DS1 other than this one reflects
				   'loopTiming', this DS1 will use that DS1 as its
				   transmit clock. Therefore this DS1 reflects
				   'throughTiming'.

				'sonetThroughTiming' indecates that recovered receive
				clock from the far-side sonet node is used as the
				transmit clock."
			DEFVAL { throughTiming }
			::= { zhoneDs1Entry 11 }


--
		-- 1.3.6.1.4.1.5504.5.2.2.1.12
		zhoneFdl OBJECT-TYPE
			SYNTAX INTEGER
				{
				other(1),
				ansiT1403(2),
				att54016(3),
				fdlNone(4)
				}
			MAX-ACCESS read-write
			STATUS current
			DESCRIPTION
				" 'other' indicates that a protocol  other  than
				one following is used.

				 'ansiT1403' refers to the  FDL  exchange
				recommended by ANSI.

				 'att54016' refers to ESF FDL exchanges.

				 'fdlNone' indicates that the device  does
				not use the FDL.


				TITLE:         AVAILABILITY:
				other(1)       (not supported in this release)
				ansiT1403(2)   (not supported in this release)
				att54016(3)    (not supported in this release)
				fdlNone(4)

				"
			DEFVAL { fdlNone }
			::= { zhoneDs1Entry 12 }


--
		-- 1.3.6.1.4.1.5504.5.2.2.1.13
		zhoneInvalidIntervals OBJECT-TYPE
			SYNTAX INTEGER (0..96)
			MAX-ACCESS read-only
			STATUS current
			DESCRIPTION
				"The number of intervals in the range from 0 to
				zwValidIntervals for which no data is
				available.  This object will typically be zero
				except in cases where the data for some intervals
				are not available (e.g., in proxy situations)."
			::= { zhoneDs1Entry 13 }


--
		-- 1.3.6.1.4.1.5504.5.2.2.1.14
		zhoneDsxLineLength OBJECT-TYPE
			SYNTAX INTEGER
				{
				dsx0(1),
				dsx133(2),
				dsx266(3),
				dsx399(4),
				dsx533(5),
				dsx655(6)
				}
			MAX-ACCESS read-write
			STATUS current
			DESCRIPTION
				"The length of the dsx wan is in feets. This
				objects provides information for line build out
				circuitry.  The valid range is:
				'dsx0(1)' It is 0 feet for the line build out (LBO) and the default setting.
				'dsx133(2)'It is 133 feets for the LBO.
				'dsx266(3)'It is 266 feets for the LBO.
				'dsx399(4)'It is 399 feets for the LBO.
				'dsx533(5)'It is 533 feets for the LBO.
				'dsx655(6)'It is 655 feets for the LBO.

				This field is not used for E1 platforms.
				"
			DEFVAL { dsx0 }
			::= { zhoneDs1Entry 14 }


--
		-- 1.3.6.1.4.1.5504.5.2.2.1.15
		zhoneLineStatusLastChange OBJECT-TYPE
			SYNTAX TimeStamp
			MAX-ACCESS read-only
			STATUS current
			DESCRIPTION
				"The value of MIB II's sysUpTime object at the
				time this DS1 entered its current line status
				state.  If the current state was entered prior to
				the last re-initialization of the proxy-agent,
				then this object contains a zero value."
			::= { zhoneDs1Entry 15 }


--
		-- 1.3.6.1.4.1.5504.5.2.2.1.16
		zhoneLineStatusChangeTrapEnable OBJECT-TYPE
			SYNTAX INTEGER
				{
				enabled(1),
				disabled(2)
				}
			MAX-ACCESS read-write
			STATUS current
			DESCRIPTION
				"Indicates whether zhoneLineStatusChange traps
				should be generated for this interface.
				"
			DEFVAL { disabled }
			::= { zhoneDs1Entry 16 }


--
		-- 1.3.6.1.4.1.5504.5.2.2.1.17
		zhoneLoopbackStatus OBJECT-TYPE
			SYNTAX INTEGER (1..127)
			MAX-ACCESS read-only
			STATUS current
			DESCRIPTION
				"This variable represents the current state of the
				loopback on the DS1 interface.  It contains
				information about loopbacks established by a
				local manager and remotely from the far end.
				This status is combination of loopbackConfig,
				and sendCode options as this status represents
				the local as well as far loopbacks.
				The various positions are:
				noLoopback(1)
				nearEndLineLoopback(2)
				nearEndOtherLoopback(4)
				nearEndLocalLoopback(8)
				farEndPayloadLoopback(16)
				farEndLineLoopback(32)"
			::= { zhoneDs1Entry 17 }


--
		-- 1.3.6.1.4.1.5504.5.2.2.1.18
		zhoneDs1ChannelNumber OBJECT-TYPE
			SYNTAX INTEGER (0..28)
			MAX-ACCESS read-only
			STATUS current
			DESCRIPTION
				"This variable represents the channel number of
				the DS1/E1 on its parent Ds2/E2 or DS3/E3.  A
				value of 0 indicated this DS1/E1 does not have a
				parent DS3/E3."
			::= { zhoneDs1Entry 18 }


--
		-- 1.3.6.1.4.1.5504.5.2.2.1.19
		zhoneChannelization OBJECT-TYPE
			SYNTAX INTEGER
				{
				disabled(1),
				enabledDs0(2),
				enabledDs1(3)
				}
			MAX-ACCESS read-write
			STATUS current
			DESCRIPTION
				"Indicates whether this ds1/e1 is channelized or
				unchannelized.  The value of enabledDs0 indicates
				that this is a DS1 channelized into DS0s.  The
				value of enabledDs1 indicated that this is a DS2
				channelized into DS1s.  Setting this value will
				cause the creation or deletion of entries in the
				ifTable for the DS0s that are within the DS1.


				TITLE:         AVAILABILITY:
				disabled(1)    (not supported in this release)
				enabledDs0(2)
				enabledDs1(3)  (not supported in this release)

				For BAN disabled"
			DEFVAL { enabledDs0 }
			::= { zhoneDs1Entry 19 }


--
		-- 1.3.6.1.4.1.5504.5.2.2.1.20
		zhoneDs1Mode OBJECT-TYPE
			SYNTAX INTEGER
				{
				other(1),
				dsx(2),
				csu(3)
				}
			MAX-ACCESS read-write
			STATUS current
			DESCRIPTION
				"'other' wan is not in csu or dsx mode.
				'dsx' T1 wan is in dsx mode.
				'csu' T1 wan is in csu mode.

				Default setting is 'csu' for T1 platforms and
				'other' for E1.

				TITLE:      AVAILABILITY:
				other(1)
				dsx(2)
				csu(3)
				BAN E1:other; T1:csu,dsx"
			::= { zhoneDs1Entry 20 }


--
		-- 1.3.6.1.4.1.5504.5.2.2.1.21
		zhoneCsuLineLength OBJECT-TYPE
			SYNTAX INTEGER
				{
				csu00(1),
				csu75(2),
				csu150(3),
				csu225(4)
				}
			MAX-ACCESS read-write
			STATUS current
			DESCRIPTION
				"
				'csu00' it is 0 dB for csu ds1 wan for line build out.
				'csu75' it is -7.5 dB for line build out.
				'csu150' it is -15.0 dB for line build out.
				'csu225' it is -22.5 dB for line build out (LBO).

				This field is not used for E1 platforms."
			DEFVAL { csu00 }
			::= { zhoneDs1Entry 21 }


--
		-- 1.3.6.1.4.1.5504.5.2.2.1.22
		zhoneClockSourceEligibility OBJECT-TYPE
			SYNTAX INTEGER
				{
				notEligible(1),
				eligible(2)
				}
			MAX-ACCESS read-write
			STATUS current
			DESCRIPTION
				"
				The possible values are:

				(1) not-eligibile - this DS1 is not eligible to be negotiated
				   as a possible transmit clock source
				(2) eligible - this DS1 may be used by the DS1 Line resource
				   provider in negotiation as a possible transmit clock source
				   for all DS1s.

				   For BAN DS1, this field is not writeable and will default
				   to eligible. "
			DEFVAL { notEligible }
			::= { zhoneDs1Entry 22 }


		-- 1.3.6.1.4.1.5504.5.2.2.1.23
		zhoneCellScramble OBJECT-TYPE
			SYNTAX TruthValue
			MAX-ACCESS read-write
			STATUS current
			DESCRIPTION
				"This field describes the enabled status of the Ds1 Cell Scramble mode. If this
				field is true(1) then Scramble mode is enabled, if this field is
				false(2) scramble mode is disable.."
			DEFVAL { true }
			::= { zhoneDs1Entry 23 }


		-- 1.3.6.1.4.1.5504.5.2.2.1.24
		zhoneCosetPolynomial OBJECT-TYPE
			SYNTAX TruthValue
			MAX-ACCESS read-write
			STATUS current
			DESCRIPTION
				"This field describes the enabled status of the Coset Polynomial mode. If this
				field is true(1) then Coset Polynomial mode is enabled, if this field is
				false(2) Coset Polynomial mode is disable."
			::= { zhoneDs1Entry 24 }


		-- 1.3.6.1.4.1.5504.5.2.2.1.25
		zhoneDs1ProtocolEmulation OBJECT-TYPE
			SYNTAX INTEGER
				{
				network(1),
				cpe(2)
				}
			MAX-ACCESS read-write
			STATUS current
			DESCRIPTION
				"Indicates whether the device is acting as Network-side
				or CPE with respect to this DS1.   For example,  if
				the system is configured with a PBX on the network
				side of the device, then the device will act as a CPE
				with respect to the DS1.  If the device is on the
				network side of a PBX, then this leaf should be set
				to network, as the PBX would be acting as a CPE."
			DEFVAL { network }
			::= { zhoneDs1Entry 25 }


		-- 1.3.6.1.4.1.5504.5.2.2.1.26
		zhoneDs1SignalType OBJECT-TYPE
			SYNTAX INTEGER
				{
				loopStart(1),
				groundStart(2)
				}
			MAX-ACCESS read-write
			STATUS current
			DESCRIPTION
				"The signaling type of the FXS interfaces
				within this DS1."
			DEFVAL { loopStart }
			::= { zhoneDs1Entry 26 }


		-- 1.3.6.1.4.1.5504.5.2.2.1.27
		zhoneDs1GroupIndex OBJECT-TYPE
			SYNTAX INTEGER (0..2147483647)
			MAX-ACCESS read-write
			STATUS current
			DESCRIPTION
				"The Group index this Ds1 belongs to"
			::= { zhoneDs1Entry 27 }


		-- 1.3.6.1.4.1.5504.5.2.2.1.28
		zhoneDs1LinePower OBJECT-TYPE
			SYNTAX INTEGER
				{
				enabled(1),
				disabled(2)
				}
			MAX-ACCESS read-write
			STATUS current
			DESCRIPTION
				"Enable or disable line power for the DS1 interface."
			DEFVAL { disabled }
			::= { zhoneDs1Entry 28 }


		-- 1.3.6.1.4.1.5504.5.2.2.1.29
		zhoneDs1TimeslotAssignment OBJECT-TYPE
			SYNTAX BITS
				{
				ts0(0),
				ts1(1),
				ts2(2),
				ts3(3),
				ts4(4),
				ts5(5),
				ts6(6),
				ts7(7),
				ts8(8),
				ts9(9),
				ts10(10),
				ts11(11),
				ts12(12),
				ts13(13),
				ts14(14),
				ts15(15),
				ts16(16),
				ts17(17),
				ts18(18),
				ts19(19),
				ts20(20),
				ts21(21),
				ts22(22),
				ts23(23),
				ts24(24),
				ts25(25),
				ts26(26),
				ts27(27),
				ts28(28),
				ts29(29),
				ts30(30),
				ts31(31)
				}
			MAX-ACCESS read-write
			STATUS current
			DESCRIPTION
				"This table entry is a bit field indicating which timeslots
				in a ds1 are used (or assigned).

				  Default for DS1 based card:
				1+1+1+1+1+1+1+1+1+1+1+1+1+1+1+1+1+1+1+1+1+1+1+1+0+0+0+0+0+0+0+0

				  Default for E1 based card:
				1+1+1+1+1+1+1+1+1+1+1+1+1+1+1+1+1+1+1+1+1+1+1+1+1+1+1+1+1+1+1+0."
			::= { zhoneDs1Entry 29 }


		-- 1.3.6.1.4.1.5504.5.2.2.1.30
		zhoneDs1TxClockRecovery OBJECT-TYPE
			SYNTAX INTEGER
				{
				none(1),
				adaptive(2),
				differential(3)
				}
			MAX-ACCESS read-write
			STATUS obsolete
			DESCRIPTION
				"PWE transmit clock recovery method"
			DEFVAL { none }
			::= { zhoneDs1Entry 30 }


		-- 1.3.6.1.4.1.5504.5.2.2.1.31
		zhoneDs1TxClockAdaptiveQuality OBJECT-TYPE
			SYNTAX INTEGER
				{
				stratum1(1),
				stratum3(2),
				stratum3e(3),
				stratum4(4)
				}
			MAX-ACCESS read-write
			STATUS current
			DESCRIPTION
				"Determines sync drift when operating in PWE adaptive
				mode. Values reflect ANSI Standard T1.101 reference
				clock quality."
			DEFVAL { stratum3 }
			::= { zhoneDs1Entry 31 }


		-- 1.3.6.1.4.1.5504.5.2.3
		zhoneDs1CurrentTable OBJECT-TYPE
			SYNTAX SEQUENCE OF ZhoneDs1CurrentEntry
			MAX-ACCESS not-accessible
			STATUS current
			DESCRIPTION
				"The DS1 current table contains various statistics
				being collected for the current 15 minute
				interval.

				Not supported on BAN in this release."
			::= { zhoneDsx 3 }


		-- 1.3.6.1.4.1.5504.5.2.3.1
		zhoneDs1CurrentEntry OBJECT-TYPE
			SYNTAX ZhoneDs1CurrentEntry
			MAX-ACCESS not-accessible
			STATUS current
			DESCRIPTION
				"An entry in the DS1 Current table."
			INDEX { zhoneCurrentIndex }
			::= { zhoneDs1CurrentTable 1 }


		ZhoneDs1CurrentEntry ::=
			SEQUENCE {
				zhoneCurrentIndex
					InterfaceIndex,
				zhoneCurrentESs
					PerfCurrentCount,
				zhoneCurrentSESs
					PerfCurrentCount,
				zhoneCurrentSEFSs
					PerfCurrentCount,
				zhoneCurrentUASs
					PerfCurrentCount,
				zhoneCurrentCSSs
					PerfCurrentCount,
				zhoneCurrentPCVs
					PerfCurrentCount,
				zhoneCurrentLESs
					PerfCurrentCount,
				zhoneCurrentBESs
					PerfCurrentCount,
				zhoneCurrentDMs
					PerfCurrentCount,
				zhoneCurrentLCVs
					PerfCurrentCount
			 }

		-- 1.3.6.1.4.1.5504.5.2.3.1.1
		zhoneCurrentIndex OBJECT-TYPE
			SYNTAX InterfaceIndex
			MAX-ACCESS not-accessible
			STATUS current
			DESCRIPTION
				"The index value which uniquely identifies  the
				DS1 interface to which this entry is applicable.
				The interface identified by a particular value of
				this index is the same interface as identified by
				the same value as a zhLineIndex object
				instance."
			::= { zhoneDs1CurrentEntry 1 }


--
		-- 1.3.6.1.4.1.5504.5.2.3.1.2
		zhoneCurrentESs OBJECT-TYPE
			SYNTAX PerfCurrentCount
			MAX-ACCESS read-only
			STATUS current
			DESCRIPTION
				"The number of Errored Seconds."
			::= { zhoneDs1CurrentEntry 2 }


--
		-- 1.3.6.1.4.1.5504.5.2.3.1.3
		zhoneCurrentSESs OBJECT-TYPE
			SYNTAX PerfCurrentCount
			MAX-ACCESS read-only
			STATUS current
			DESCRIPTION
				"The number of Severely Errored Seconds."
			::= { zhoneDs1CurrentEntry 3 }


--
		-- 1.3.6.1.4.1.5504.5.2.3.1.4
		zhoneCurrentSEFSs OBJECT-TYPE
			SYNTAX PerfCurrentCount
			MAX-ACCESS read-only
			STATUS current
			DESCRIPTION
				"The number of Severely Errored Framing Seconds."
			::= { zhoneDs1CurrentEntry 4 }


--
		-- 1.3.6.1.4.1.5504.5.2.3.1.5
		zhoneCurrentUASs OBJECT-TYPE
			SYNTAX PerfCurrentCount
			MAX-ACCESS read-only
			STATUS current
			DESCRIPTION
				"The number of Unavailable Seconds."
			::= { zhoneDs1CurrentEntry 5 }


--
		-- 1.3.6.1.4.1.5504.5.2.3.1.6
		zhoneCurrentCSSs OBJECT-TYPE
			SYNTAX PerfCurrentCount
			MAX-ACCESS read-only
			STATUS current
			DESCRIPTION
				"The number of Controlled Slip Seconds."
			::= { zhoneDs1CurrentEntry 6 }


--
		-- 1.3.6.1.4.1.5504.5.2.3.1.7
		zhoneCurrentPCVs OBJECT-TYPE
			SYNTAX PerfCurrentCount
			MAX-ACCESS read-only
			STATUS current
			DESCRIPTION
				"The number of Path Coding Violations."
			::= { zhoneDs1CurrentEntry 7 }


--
		-- 1.3.6.1.4.1.5504.5.2.3.1.8
		zhoneCurrentLESs OBJECT-TYPE
			SYNTAX PerfCurrentCount
			MAX-ACCESS read-only
			STATUS current
			DESCRIPTION
				"The number of Line Errored Seconds."
			::= { zhoneDs1CurrentEntry 8 }


--
		-- 1.3.6.1.4.1.5504.5.2.3.1.9
		zhoneCurrentBESs OBJECT-TYPE
			SYNTAX PerfCurrentCount
			MAX-ACCESS read-only
			STATUS current
			DESCRIPTION
				"The number of Bursty Errored Seconds."
			::= { zhoneDs1CurrentEntry 9 }


--
		-- 1.3.6.1.4.1.5504.5.2.3.1.10
		zhoneCurrentDMs OBJECT-TYPE
			SYNTAX PerfCurrentCount
			MAX-ACCESS read-only
			STATUS current
			DESCRIPTION
				"The number of Degraded Minutes."
			::= { zhoneDs1CurrentEntry 10 }


--
		-- 1.3.6.1.4.1.5504.5.2.3.1.11
		zhoneCurrentLCVs OBJECT-TYPE
			SYNTAX PerfCurrentCount
			MAX-ACCESS read-only
			STATUS current
			DESCRIPTION
				"The number of Line Code Violations (LCVs)."
			::= { zhoneDs1CurrentEntry 11 }


		-- 1.3.6.1.4.1.5504.5.2.4
		zhoneDs1IntervalTable OBJECT-TYPE
			SYNTAX SEQUENCE OF ZhoneDs1IntervalEntry
			MAX-ACCESS not-accessible
			STATUS current
			DESCRIPTION
				"The DS1 Interval Table contains various
				statistics collected by each DS1 Interface over
				the previous 24 hours of operation.  The past 24
				hours are broken into 96 completed 15 minute
				intervals.  Each row in this table represents one
				such interval (identified by zwIntervalNumber)
				for one specific instance (identified by
				zwIntervalIndex).

				Not supported on BAN in this release."
			::= { zhoneDsx 4 }


		-- 1.3.6.1.4.1.5504.5.2.4.1
		zhoneDs1IntervalEntry OBJECT-TYPE
			SYNTAX ZhoneDs1IntervalEntry
			MAX-ACCESS not-accessible
			STATUS current
			DESCRIPTION
				"An entry in the DS1 Interval table."
			INDEX { zhoneIntervalIndex, zhoneIntervalNumber }
			::= { zhoneDs1IntervalTable 1 }


		ZhoneDs1IntervalEntry ::=
			SEQUENCE {
				zhoneIntervalIndex
					InterfaceIndex,
				zhoneIntervalNumber
					INTEGER,
				zhoneIntervalESs
					PerfIntervalCount,
				zhoneIntervalSESs
					PerfIntervalCount,
				zhoneIntervalSEFSs
					PerfIntervalCount,
				zhoneIntervalUASs
					PerfIntervalCount,
				zhoneIntervalCSSs
					PerfIntervalCount,
				zhoneIntervalPCVs
					PerfIntervalCount,
				zhoneIntervalLESs
					PerfIntervalCount,
				zhoneIntervalBESs
					PerfIntervalCount,
				zhoneIntervalDMs
					PerfIntervalCount,
				zhoneIntervalLCVs
					PerfIntervalCount,
				zhoneIntervalValidData
					TruthValue
			 }

--
--
		-- 1.3.6.1.4.1.5504.5.2.4.1.1
		zhoneIntervalIndex OBJECT-TYPE
			SYNTAX InterfaceIndex
			MAX-ACCESS not-accessible
			STATUS current
			DESCRIPTION
				"The index value which uniquely identifies the DS1
				interface to which this entry is applicable.  The
				interface identified by a particular value of this
				index is the same interface as identified by the
				same value as a zhLineIndex object instance."
			::= { zhoneDs1IntervalEntry 1 }


--
		-- 1.3.6.1.4.1.5504.5.2.4.1.2
		zhoneIntervalNumber OBJECT-TYPE
			SYNTAX INTEGER (1..96)
			MAX-ACCESS read-only
			STATUS current
			DESCRIPTION
				"A number between 1 and 96, where 1 is the most
				recently completed 15 minute interval and 96 is
				the 15 minutes interval completed 23 hours and 45
				minutes prior to interval 1."
			::= { zhoneDs1IntervalEntry 2 }


--
		-- 1.3.6.1.4.1.5504.5.2.4.1.3
		zhoneIntervalESs OBJECT-TYPE
			SYNTAX PerfIntervalCount
			MAX-ACCESS read-only
			STATUS current
			DESCRIPTION
				"The number of Errored Seconds."
			::= { zhoneDs1IntervalEntry 3 }


--
		-- 1.3.6.1.4.1.5504.5.2.4.1.4
		zhoneIntervalSESs OBJECT-TYPE
			SYNTAX PerfIntervalCount
			MAX-ACCESS read-only
			STATUS current
			DESCRIPTION
				"The number of Severely Errored Seconds."
			::= { zhoneDs1IntervalEntry 4 }


--
		-- 1.3.6.1.4.1.5504.5.2.4.1.5
		zhoneIntervalSEFSs OBJECT-TYPE
			SYNTAX PerfIntervalCount
			MAX-ACCESS read-only
			STATUS current
			DESCRIPTION
				"The number of Severely Errored Framing Seconds."
			::= { zhoneDs1IntervalEntry 5 }


--
		-- 1.3.6.1.4.1.5504.5.2.4.1.6
		zhoneIntervalUASs OBJECT-TYPE
			SYNTAX PerfIntervalCount
			MAX-ACCESS read-only
			STATUS current
			DESCRIPTION
				"The number of Unavailable Seconds.  This object
				may decrease if the occurance of unavailable
				seconds occurs across an inteval boundary."
			::= { zhoneDs1IntervalEntry 6 }


--
		-- 1.3.6.1.4.1.5504.5.2.4.1.7
		zhoneIntervalCSSs OBJECT-TYPE
			SYNTAX PerfIntervalCount
			MAX-ACCESS read-only
			STATUS current
			DESCRIPTION
				"The number of Controlled Slip Seconds."
			::= { zhoneDs1IntervalEntry 7 }


--
		-- 1.3.6.1.4.1.5504.5.2.4.1.8
		zhoneIntervalPCVs OBJECT-TYPE
			SYNTAX PerfIntervalCount
			MAX-ACCESS read-only
			STATUS current
			DESCRIPTION
				"The number of Path Coding Violations."
			::= { zhoneDs1IntervalEntry 8 }


--
		-- 1.3.6.1.4.1.5504.5.2.4.1.9
		zhoneIntervalLESs OBJECT-TYPE
			SYNTAX PerfIntervalCount
			MAX-ACCESS read-only
			STATUS current
			DESCRIPTION
				"The number of Line Errored Seconds."
			::= { zhoneDs1IntervalEntry 9 }


--
		-- 1.3.6.1.4.1.5504.5.2.4.1.10
		zhoneIntervalBESs OBJECT-TYPE
			SYNTAX PerfIntervalCount
			MAX-ACCESS read-only
			STATUS current
			DESCRIPTION
				"The number of Bursty Errored Seconds."
			::= { zhoneDs1IntervalEntry 10 }


--
		-- 1.3.6.1.4.1.5504.5.2.4.1.11
		zhoneIntervalDMs OBJECT-TYPE
			SYNTAX PerfIntervalCount
			MAX-ACCESS read-only
			STATUS current
			DESCRIPTION
				"The number of Degraded Minutes."
			::= { zhoneDs1IntervalEntry 11 }


--
		-- 1.3.6.1.4.1.5504.5.2.4.1.12
		zhoneIntervalLCVs OBJECT-TYPE
			SYNTAX PerfIntervalCount
			MAX-ACCESS read-only
			STATUS current
			DESCRIPTION
				"The number of Line Code Violations."
			::= { zhoneDs1IntervalEntry 12 }


--
		-- 1.3.6.1.4.1.5504.5.2.4.1.13
		zhoneIntervalValidData OBJECT-TYPE
			SYNTAX TruthValue
			MAX-ACCESS read-only
			STATUS current
			DESCRIPTION
				"This variable indicates if the data for this
				interval is valid."
			::= { zhoneDs1IntervalEntry 13 }


		-- 1.3.6.1.4.1.5504.5.2.5
		zhoneDs1TotalTable OBJECT-TYPE
			SYNTAX SEQUENCE OF ZhoneDs1TotalEntry
			MAX-ACCESS not-accessible
			STATUS current
			DESCRIPTION
				"The DS1 Total Table contains the cumulative sum
				of the various statistics for the 24 hour period
				preceding the current interval.

				Not supported on BAN in this release."
			::= { zhoneDsx 5 }


		-- 1.3.6.1.4.1.5504.5.2.5.1
		zhoneDs1TotalEntry OBJECT-TYPE
			SYNTAX ZhoneDs1TotalEntry
			MAX-ACCESS not-accessible
			STATUS current
			DESCRIPTION
				"An entry in the DS1 Total table."
			INDEX { zhoneTotalIndex }
			::= { zhoneDs1TotalTable 1 }


		ZhoneDs1TotalEntry ::=
			SEQUENCE {
				zhoneTotalIndex
					InterfaceIndex,
				zhoneTotalESs
					PerfTotalCount,
				zhoneTotalSESs
					PerfTotalCount,
				zhoneTotalSEFSs
					PerfTotalCount,
				zhoneTotalUASs
					PerfTotalCount,
				zhoneTotalCSSs
					PerfTotalCount,
				zhoneTotalPCVs
					PerfTotalCount,
				zhoneTotalLESs
					PerfTotalCount,
				zhoneTotalBESs
					PerfTotalCount,
				zhoneTotalDMs
					PerfTotalCount,
				zhoneTotalLCVs
					PerfTotalCount
			 }

		-- 1.3.6.1.4.1.5504.5.2.5.1.1
		zhoneTotalIndex OBJECT-TYPE
			SYNTAX InterfaceIndex
			MAX-ACCESS not-accessible
			STATUS current
			DESCRIPTION
				"The index value which uniquely identifies the DS1
				interface to which this entry is applicable.  The
				interface identified by a particular value of this
				index is the same interface as identified by the
				same value as a zhLineIndex object instance."
			::= { zhoneDs1TotalEntry 1 }


--
		-- 1.3.6.1.4.1.5504.5.2.5.1.2
		zhoneTotalESs OBJECT-TYPE
			SYNTAX PerfTotalCount
			MAX-ACCESS read-only
			STATUS current
			DESCRIPTION
				"The sum of Errored Seconds encountered by a DS1
				interface in the previous 24 hour interval.
				Invalid 15 minute intervals count as 0."
			::= { zhoneDs1TotalEntry 2 }


--
		-- 1.3.6.1.4.1.5504.5.2.5.1.3
		zhoneTotalSESs OBJECT-TYPE
			SYNTAX PerfTotalCount
			MAX-ACCESS read-only
			STATUS current
			DESCRIPTION
				"The number of Severely Errored Seconds
				encountered by a DS1 interface in the previous 24
				hour interval.  Invalid 15 minute intervals count
				as 0."
			::= { zhoneDs1TotalEntry 3 }


--
		-- 1.3.6.1.4.1.5504.5.2.5.1.4
		zhoneTotalSEFSs OBJECT-TYPE
			SYNTAX PerfTotalCount
			MAX-ACCESS read-only
			STATUS current
			DESCRIPTION
				"The number of Severely Errored Framing Seconds

				encountered by a DS1 interface in the previous 24
				hour interval.  Invalid 15 minute intervals count
				as 0."
			::= { zhoneDs1TotalEntry 4 }


--
		-- 1.3.6.1.4.1.5504.5.2.5.1.5
		zhoneTotalUASs OBJECT-TYPE
			SYNTAX PerfTotalCount
			MAX-ACCESS read-only
			STATUS current
			DESCRIPTION
				"The number of Unavailable Seconds encountered by
				a DS1 interface in the previous 24 hour interval.
				Invalid 15 minute intervals count as 0."
			::= { zhoneDs1TotalEntry 5 }


--
		-- 1.3.6.1.4.1.5504.5.2.5.1.6
		zhoneTotalCSSs OBJECT-TYPE
			SYNTAX PerfTotalCount
			MAX-ACCESS read-only
			STATUS current
			DESCRIPTION
				"The number of Controlled Slip Seconds encountered
				by a DS1 interface in the previous 24 hour
				interval.  Invalid 15 minute intervals count as
				0."
			::= { zhoneDs1TotalEntry 6 }


--
		-- 1.3.6.1.4.1.5504.5.2.5.1.7
		zhoneTotalPCVs OBJECT-TYPE
			SYNTAX PerfTotalCount
			MAX-ACCESS read-only
			STATUS current
			DESCRIPTION
				"The number of Path Coding Violations encountered
				by a DS1 interface in the previous 24 hour
				interval.  Invalid 15 minute intervals count as
				0."
			::= { zhoneDs1TotalEntry 7 }


--
		-- 1.3.6.1.4.1.5504.5.2.5.1.8
		zhoneTotalLESs OBJECT-TYPE
			SYNTAX PerfTotalCount
			MAX-ACCESS read-only
			STATUS current
			DESCRIPTION
				"The number of Line Errored Seconds encountered by
				a DS1 interface in the previous 24 hour interval.
				Invalid 15 minute intervals count as 0."
			::= { zhoneDs1TotalEntry 8 }


--
		-- 1.3.6.1.4.1.5504.5.2.5.1.9
		zhoneTotalBESs OBJECT-TYPE
			SYNTAX PerfTotalCount
			MAX-ACCESS read-only
			STATUS current
			DESCRIPTION
				"The number of Bursty Errored Seconds (BESs)
				encountered by a DS1 interface in the previous 24
				hour interval. Invalid 15 minute intervals count
				as 0."
			::= { zhoneDs1TotalEntry 9 }


--
		-- 1.3.6.1.4.1.5504.5.2.5.1.10
		zhoneTotalDMs OBJECT-TYPE
			SYNTAX PerfTotalCount
			MAX-ACCESS read-only
			STATUS current
			DESCRIPTION
				"The number of Degraded Minutes (DMs) encountered
				by a DS1 interface in the previous 24 hour
				interval.  Invalid 15 minute intervals count as
				0."
			::= { zhoneDs1TotalEntry 10 }


		-- 1.3.6.1.4.1.5504.5.2.5.1.11
		zhoneTotalLCVs OBJECT-TYPE
			SYNTAX PerfTotalCount
			MAX-ACCESS read-only
			STATUS current
			DESCRIPTION
				"The number of Line Code Violations (LCVs)
				encountered by a DS1 interface in the current 15
				minute interval.  Invalid 15 minute intervals
				count as 0."
			::= { zhoneDs1TotalEntry 11 }


		-- 1.3.6.1.4.1.5504.5.2.6
		zhoneDs1FarEndCurrentTable OBJECT-TYPE
			SYNTAX SEQUENCE OF ZhoneDs1FarEndCurrentEntry
			MAX-ACCESS not-accessible
			STATUS current
			DESCRIPTION
				"The DS1 Far End Current table contains various
				statistics being collected for the current 15
				minute interval.  The statistics are collected
				from the far end messages on the Facilities Data
				Link.  The definitions are the same as described
				for the near-end information.

				Not supported in this release."
			::= { zhoneDsx 6 }


		-- 1.3.6.1.4.1.5504.5.2.6.1
		zhoneDs1FarEndCurrentEntry OBJECT-TYPE
			SYNTAX ZhoneDs1FarEndCurrentEntry
			MAX-ACCESS not-accessible
			STATUS current
			DESCRIPTION
				"An entry in the DS1 Far End Current table."
			INDEX { zhoneFarEndCurrentIndex }
			::= { zhoneDs1FarEndCurrentTable 1 }


		ZhoneDs1FarEndCurrentEntry ::=
			SEQUENCE {
				zhoneFarEndCurrentIndex
					InterfaceIndex,
				zhoneFarEndTimeElapsed
					INTEGER,
				zhoneFarEndValidIntervals
					INTEGER,
				zhoneFarEndCurrentESs
					PerfCurrentCount,
				zhoneFarEndCurrentSESs
					PerfCurrentCount,
				zhoneFarEndCurrentSEFSs
					PerfCurrentCount,
				zhoneFarEndCurrentUASs
					PerfCurrentCount,
				zhoneFarEndCurrentCSSs
					PerfCurrentCount,
				zhoneFarEndCurrentLESs
					PerfCurrentCount,
				zhoneFarEndCurrentPCVs
					PerfCurrentCount,
				zhoneFarEndCurrentBESs
					PerfCurrentCount,
				zhoneFarEndCurrentDMs
					PerfCurrentCount,
				zhoneFarEndInvalidIntervals
					INTEGER
			 }

		-- 1.3.6.1.4.1.5504.5.2.6.1.1
		zhoneFarEndCurrentIndex OBJECT-TYPE
			SYNTAX InterfaceIndex
			MAX-ACCESS not-accessible
			STATUS current
			DESCRIPTION
				"The index value which uniquely identifies the DS1
				interface to which this entry is applicable.  The
				interface identified by a particular value of this
				index is identical to the interface identified by
				the same value of zhLineIndex."
			::= { zhoneDs1FarEndCurrentEntry 1 }


--
		-- 1.3.6.1.4.1.5504.5.2.6.1.2
		zhoneFarEndTimeElapsed OBJECT-TYPE
			SYNTAX INTEGER (0..899)
			MAX-ACCESS read-only
			STATUS current
			DESCRIPTION
				"The number of seconds that have elapsed since the
				beginning of the far end current error-measurement
				period.  If, for some reason, such as an
				adjustment in the system's time-of-day clock, the
				current interval exceeds the maximum value, the
				agent will return the maximum value."
			::= { zhoneDs1FarEndCurrentEntry 2 }


--
		-- 1.3.6.1.4.1.5504.5.2.6.1.3
		zhoneFarEndValidIntervals OBJECT-TYPE
			SYNTAX INTEGER (0..96)
			MAX-ACCESS read-only
			STATUS current
			DESCRIPTION
				"The number of previous far end intervals for
				which data was collected.  The value will be
				96 unless the interface was brought online within
				the last 24 hours, in which case the value will be
				the number of complete 15 minute far end intervals
				since the interface has been online."
			::= { zhoneDs1FarEndCurrentEntry 3 }


--
		-- 1.3.6.1.4.1.5504.5.2.6.1.4
		zhoneFarEndCurrentESs OBJECT-TYPE
			SYNTAX PerfCurrentCount
			MAX-ACCESS read-only
			STATUS current
			DESCRIPTION
				"The number of Far End Errored Seconds."
			::= { zhoneDs1FarEndCurrentEntry 4 }


--
		-- 1.3.6.1.4.1.5504.5.2.6.1.5
		zhoneFarEndCurrentSESs OBJECT-TYPE
			SYNTAX PerfCurrentCount
			MAX-ACCESS read-only
			STATUS current
			DESCRIPTION
				"The number of Far End Severely Errored Seconds."
			::= { zhoneDs1FarEndCurrentEntry 5 }


--
		-- 1.3.6.1.4.1.5504.5.2.6.1.6
		zhoneFarEndCurrentSEFSs OBJECT-TYPE
			SYNTAX PerfCurrentCount
			MAX-ACCESS read-only
			STATUS current
			DESCRIPTION
				"The number of Far End Severely Errored Framing
				Seconds."
			::= { zhoneDs1FarEndCurrentEntry 6 }


--
		-- 1.3.6.1.4.1.5504.5.2.6.1.7
		zhoneFarEndCurrentUASs OBJECT-TYPE
			SYNTAX PerfCurrentCount
			MAX-ACCESS read-only
			STATUS current
			DESCRIPTION
				"The number of Unavailable Seconds."
			::= { zhoneDs1FarEndCurrentEntry 7 }


--
		-- 1.3.6.1.4.1.5504.5.2.6.1.8
		zhoneFarEndCurrentCSSs OBJECT-TYPE
			SYNTAX PerfCurrentCount
			MAX-ACCESS read-only
			STATUS current
			DESCRIPTION
				"The number of Far End Controlled Slip Seconds."
			::= { zhoneDs1FarEndCurrentEntry 8 }


--
		-- 1.3.6.1.4.1.5504.5.2.6.1.9
		zhoneFarEndCurrentLESs OBJECT-TYPE
			SYNTAX PerfCurrentCount
			MAX-ACCESS read-only
			STATUS current
			DESCRIPTION
				"The number of Far End Line Errored Seconds."
			::= { zhoneDs1FarEndCurrentEntry 9 }


--
		-- 1.3.6.1.4.1.5504.5.2.6.1.10
		zhoneFarEndCurrentPCVs OBJECT-TYPE
			SYNTAX PerfCurrentCount
			MAX-ACCESS read-only
			STATUS current
			DESCRIPTION
				"The number of Far End Path Coding Violations."
			::= { zhoneDs1FarEndCurrentEntry 10 }


--
		-- 1.3.6.1.4.1.5504.5.2.6.1.11
		zhoneFarEndCurrentBESs OBJECT-TYPE
			SYNTAX PerfCurrentCount
			MAX-ACCESS read-only
			STATUS current
			DESCRIPTION
				"The number of Far End Bursty Errored Seconds."
			::= { zhoneDs1FarEndCurrentEntry 11 }


--
		-- 1.3.6.1.4.1.5504.5.2.6.1.12
		zhoneFarEndCurrentDMs OBJECT-TYPE
			SYNTAX PerfCurrentCount
			MAX-ACCESS read-only
			STATUS current
			DESCRIPTION
				"The number of Far End Degraded Minutes."
			::= { zhoneDs1FarEndCurrentEntry 12 }


--
		-- 1.3.6.1.4.1.5504.5.2.6.1.13
		zhoneFarEndInvalidIntervals OBJECT-TYPE
			SYNTAX INTEGER (0..96)
			MAX-ACCESS read-only
			STATUS current
			DESCRIPTION
				"The number of intervals in the range from 0 to
				zhFarEndValidIntervals for which no data is
				available.  This object will typically be zero
				except in cases where the data for some intervals
				are not available (e.g., in proxy situations)."
			::= { zhoneDs1FarEndCurrentEntry 13 }


		-- 1.3.6.1.4.1.5504.5.2.7
		zhoneDs1FarEndIntervalTable OBJECT-TYPE
			SYNTAX SEQUENCE OF ZhoneDs1FarEndIntervalEntry
			MAX-ACCESS not-accessible
			STATUS current
			DESCRIPTION
				"The DS1 Far End Interval Table contains various
				statistics collected by each DS1 interface over
				the previous 24 hours of operation.  The past 24
				hours are broken into 96 completed 15 minute
				intervals. Each row in this table represents one
				such interval (identified by
				zwFarEndIntervalNumber) for one specific
				instance (identified by zwFarEndIntervalIndex).

				Not supported in this release."
			::= { zhoneDsx 7 }


		-- 1.3.6.1.4.1.5504.5.2.7.1
		zhoneDs1FarEndIntervalEntry OBJECT-TYPE
			SYNTAX ZhoneDs1FarEndIntervalEntry
			MAX-ACCESS not-accessible
			STATUS current
			DESCRIPTION
				"An entry in the DS1 Far End Interval table."
			INDEX { zhoneFarEndIntervalIndex, zhoneFarEndIntervalNumber }
			::= { zhoneDs1FarEndIntervalTable 1 }


		ZhoneDs1FarEndIntervalEntry ::=
			SEQUENCE {
				zhoneFarEndIntervalIndex
					InterfaceIndex,
				zhoneFarEndIntervalNumber
					INTEGER,
				zhoneFarEndIntervalESs
					PerfIntervalCount,
				zhoneFarEndIntervalSESs
					PerfIntervalCount,
				zhoneFarEndIntervalSEFSs
					PerfIntervalCount,
				zhoneFarEndIntervalUASs
					PerfIntervalCount,
				zhoneFarEndIntervalCSSs
					PerfIntervalCount,
				zhoneFarEndIntervalLESs
					PerfIntervalCount,
				zhoneFarEndIntervalPCVs
					PerfIntervalCount,
				zhoneFarEndIntervalBESs
					PerfIntervalCount,
				zhoneFarEndIntervalDMs
					PerfIntervalCount,
				zhoneFarEndIntervalValidData
					TruthValue
			 }

		-- 1.3.6.1.4.1.5504.5.2.7.1.1
		zhoneFarEndIntervalIndex OBJECT-TYPE
			SYNTAX InterfaceIndex
			MAX-ACCESS not-accessible
			STATUS current
			DESCRIPTION
				"The index value which uniquely identifies the DS1
				interface to which this entry is applicable.  The
				interface identified by a particular value of this
				index is identical to the interface identified by
				the same value of zhLineIndex."
			::= { zhoneDs1FarEndIntervalEntry 1 }


--
		-- 1.3.6.1.4.1.5504.5.2.7.1.2
		zhoneFarEndIntervalNumber OBJECT-TYPE
			SYNTAX INTEGER (1..96)
			MAX-ACCESS read-only
			STATUS current
			DESCRIPTION
				"A number between 1 and 96, where 1 is the most
				recently completed 15 minute interval and 96 is
				the 15 minutes interval completed 23 hours and 45
				minutes prior to interval 1."
			::= { zhoneDs1FarEndIntervalEntry 2 }


--
		-- 1.3.6.1.4.1.5504.5.2.7.1.3
		zhoneFarEndIntervalESs OBJECT-TYPE
			SYNTAX PerfIntervalCount
			MAX-ACCESS read-only
			STATUS current
			DESCRIPTION
				"The number of Far End Errored Seconds."
			::= { zhoneDs1FarEndIntervalEntry 3 }


--
		-- 1.3.6.1.4.1.5504.5.2.7.1.4
		zhoneFarEndIntervalSESs OBJECT-TYPE
			SYNTAX PerfIntervalCount
			MAX-ACCESS read-only
			STATUS current
			DESCRIPTION
				"The number of Far End Severely Errored Seconds."
			::= { zhoneDs1FarEndIntervalEntry 4 }


--
		-- 1.3.6.1.4.1.5504.5.2.7.1.5
		zhoneFarEndIntervalSEFSs OBJECT-TYPE
			SYNTAX PerfIntervalCount
			MAX-ACCESS read-only
			STATUS current
			DESCRIPTION
				"The number of Far End Severely Errored Framing
				Seconds."
			::= { zhoneDs1FarEndIntervalEntry 5 }


--
		-- 1.3.6.1.4.1.5504.5.2.7.1.6
		zhoneFarEndIntervalUASs OBJECT-TYPE
			SYNTAX PerfIntervalCount
			MAX-ACCESS read-only
			STATUS current
			DESCRIPTION
				"The number of Unavailable Seconds."
			::= { zhoneDs1FarEndIntervalEntry 6 }


--
		-- 1.3.6.1.4.1.5504.5.2.7.1.7
		zhoneFarEndIntervalCSSs OBJECT-TYPE
			SYNTAX PerfIntervalCount
			MAX-ACCESS read-only
			STATUS current
			DESCRIPTION
				"The number of Far End Controlled Slip Seconds."
			::= { zhoneDs1FarEndIntervalEntry 7 }


--
		-- 1.3.6.1.4.1.5504.5.2.7.1.8
		zhoneFarEndIntervalLESs OBJECT-TYPE
			SYNTAX PerfIntervalCount
			MAX-ACCESS read-only
			STATUS current
			DESCRIPTION
				"The number of Far End Line Errored Seconds."
			::= { zhoneDs1FarEndIntervalEntry 8 }


--
		-- 1.3.6.1.4.1.5504.5.2.7.1.9
		zhoneFarEndIntervalPCVs OBJECT-TYPE
			SYNTAX PerfIntervalCount
			MAX-ACCESS read-only
			STATUS current
			DESCRIPTION
				"The number of Far End Path Coding Violations."
			::= { zhoneDs1FarEndIntervalEntry 9 }


--
		-- 1.3.6.1.4.1.5504.5.2.7.1.10
		zhoneFarEndIntervalBESs OBJECT-TYPE
			SYNTAX PerfIntervalCount
			MAX-ACCESS read-only
			STATUS current
			DESCRIPTION
				"The number of Far End Bursty Errored Seconds."
			::= { zhoneDs1FarEndIntervalEntry 10 }


--
		-- 1.3.6.1.4.1.5504.5.2.7.1.11
		zhoneFarEndIntervalDMs OBJECT-TYPE
			SYNTAX PerfIntervalCount
			MAX-ACCESS read-only
			STATUS current
			DESCRIPTION
				"The number of Far End Degraded Minutes."
			::= { zhoneDs1FarEndIntervalEntry 11 }


--
		-- 1.3.6.1.4.1.5504.5.2.7.1.12
		zhoneFarEndIntervalValidData OBJECT-TYPE
			SYNTAX TruthValue
			MAX-ACCESS read-only
			STATUS current
			DESCRIPTION
				"This variable indicates if the data for this
				interval is valid."
			::= { zhoneDs1FarEndIntervalEntry 12 }


		-- 1.3.6.1.4.1.5504.5.2.8
		zhoneDs1FarEndTotalTable OBJECT-TYPE
			SYNTAX SEQUENCE OF ZhoneDs1FarEndTotalEntry
			MAX-ACCESS not-accessible
			STATUS current
			DESCRIPTION
				"The DS1 Far End Total Table contains the
				cumulative sum of the various statistics for the
				24 hour period preceding the current interval.

				Not supported in this release."
			::= { zhoneDsx 8 }


		-- 1.3.6.1.4.1.5504.5.2.8.1
		zhoneDs1FarEndTotalEntry OBJECT-TYPE
			SYNTAX ZhoneDs1FarEndTotalEntry
			MAX-ACCESS not-accessible
			STATUS current
			DESCRIPTION
				"An entry in the DS1 Far End Total table."
			INDEX { zhoneFarEndTotalIndex }
			::= { zhoneDs1FarEndTotalTable 1 }


		ZhoneDs1FarEndTotalEntry ::=
			SEQUENCE {
				zhoneFarEndTotalIndex
					InterfaceIndex,
				zhoneFarEndTotalESs
					PerfTotalCount,
				zhoneFarEndTotalSESs
					PerfTotalCount,
				zhoneFarEndTotalSEFSs
					PerfTotalCount,
				zhoneFarEndTotalUASs
					PerfTotalCount,
				zhoneFarEndTotalCSSs
					PerfTotalCount,
				zhoneFarEndTotalLESs
					PerfTotalCount,
				zhoneFarEndTotalPCVs
					PerfTotalCount,
				zhoneFarEndTotalBESs
					PerfTotalCount,
				zhoneFarEndTotalDMs
					PerfTotalCount
			 }

		-- 1.3.6.1.4.1.5504.5.2.8.1.1
		zhoneFarEndTotalIndex OBJECT-TYPE
			SYNTAX InterfaceIndex
			MAX-ACCESS not-accessible
			STATUS current
			DESCRIPTION
				"The index value which uniquely identifies the DS1
				interface to which this entry is applicable.  The
				interface identified by a particular value of this
				index is identical to the interface identified by
				the same value of zhLineIndex."
			::= { zhoneDs1FarEndTotalEntry 1 }


--
		-- 1.3.6.1.4.1.5504.5.2.8.1.2
		zhoneFarEndTotalESs OBJECT-TYPE
			SYNTAX PerfTotalCount
			MAX-ACCESS read-only
			STATUS current
			DESCRIPTION
				"The number of Far End Errored Seconds encountered
				by a DS1 interface in the previous 24 hour
				interval.  Invalid 15 minute intervals count as
				0."
			::= { zhoneDs1FarEndTotalEntry 2 }


--
		-- 1.3.6.1.4.1.5504.5.2.8.1.3
		zhoneFarEndTotalSESs OBJECT-TYPE
			SYNTAX PerfTotalCount
			MAX-ACCESS read-only
			STATUS current
			DESCRIPTION
				"The number of Far End Severely Errored Seconds
				encountered by a DS1 interface in the previous 24
				hour interval.  Invalid 15 minute intervals count
				as 0."
			::= { zhoneDs1FarEndTotalEntry 3 }


--
		-- 1.3.6.1.4.1.5504.5.2.8.1.4
		zhoneFarEndTotalSEFSs OBJECT-TYPE
			SYNTAX PerfTotalCount
			MAX-ACCESS read-only
			STATUS current
			DESCRIPTION
				"The number of Far End Severely Errored Framing
				Seconds encountered by a DS1 interface in the
				previous 24 hour interval. Invalid 15 minute
				intervals count as 0."
			::= { zhoneDs1FarEndTotalEntry 4 }


--
		-- 1.3.6.1.4.1.5504.5.2.8.1.5
		zhoneFarEndTotalUASs OBJECT-TYPE
			SYNTAX PerfTotalCount
			MAX-ACCESS read-only
			STATUS current
			DESCRIPTION
				"The number of Unavailable Seconds encountered by
				a DS1 interface in the previous 24 hour interval.
				Invalid 15 minute intervals count as 0."
			::= { zhoneDs1FarEndTotalEntry 5 }


--
		-- 1.3.6.1.4.1.5504.5.2.8.1.6
		zhoneFarEndTotalCSSs OBJECT-TYPE
			SYNTAX PerfTotalCount
			MAX-ACCESS read-only
			STATUS current
			DESCRIPTION
				"The number of Far End Controlled Slip Seconds
				encountered by a DS1 interface in the previous 24
				hour interval.  Invalid 15 minute intervals count
				as 0."
			::= { zhoneDs1FarEndTotalEntry 6 }


--
		-- 1.3.6.1.4.1.5504.5.2.8.1.7
		zhoneFarEndTotalLESs OBJECT-TYPE
			SYNTAX PerfTotalCount
			MAX-ACCESS read-only
			STATUS current
			DESCRIPTION
				"The number of Far End Line Errored Seconds
				encountered by a DS1 interface in the previous 24
				hour interval.  Invalid 15 minute intervals count
				as 0."
			::= { zhoneDs1FarEndTotalEntry 7 }


		-- 1.3.6.1.4.1.5504.5.2.8.1.8
		zhoneFarEndTotalPCVs OBJECT-TYPE
			SYNTAX PerfTotalCount
			MAX-ACCESS read-only
			STATUS current
			DESCRIPTION
				"The number of Far End Path Coding Violations
				reported via the far end block error count
				encountered by a DS1 interface in the previous 24
				hour interval.  Invalid 15 minute intervals count
				as 0."
			::= { zhoneDs1FarEndTotalEntry 8 }


--
		-- 1.3.6.1.4.1.5504.5.2.8.1.9
		zhoneFarEndTotalBESs OBJECT-TYPE
			SYNTAX PerfTotalCount
			MAX-ACCESS read-only
			STATUS current
			DESCRIPTION
				"The number of Bursty Errored Seconds (BESs)
				encountered by a DS1 interface in the previous 24
				hour interval. Invalid 15 minute intervals count
				as 0."
			::= { zhoneDs1FarEndTotalEntry 9 }


--
		-- 1.3.6.1.4.1.5504.5.2.8.1.10
		zhoneFarEndTotalDMs OBJECT-TYPE
			SYNTAX PerfTotalCount
			MAX-ACCESS read-only
			STATUS current
			DESCRIPTION
				"The number of Degraded Minutes (DMs) encountered
				by a DS1 interface in the previous 24 hour
				interval.  Invalid 15 minute intervals count as
				0."
			::= { zhoneDs1FarEndTotalEntry 10 }


		-- 1.3.6.1.4.1.5504.5.2.9
		zhoneChanMappingTable OBJECT-TYPE
			SYNTAX SEQUENCE OF ZhoneChanMappingEntry
			MAX-ACCESS not-accessible
			STATUS current
			DESCRIPTION
				"The DS1 Channel Mapping table.  This table maps a
				DS1 channel number on a particular DS3 into an
				ifIndex.  In the presence of DS2s, this table can
				be used to map a DS2 channel number on a DS3 into
				an ifIndex, or used to map a DS1 channel number on
				a DS2 onto an ifIndex.

				Not supported in this release."
			::= { zhoneDsx 9 }


		-- 1.3.6.1.4.1.5504.5.2.9.1
		zhoneChanMappingEntry OBJECT-TYPE
			SYNTAX ZhoneChanMappingEntry
			MAX-ACCESS not-accessible
			STATUS current
			DESCRIPTION
				"An entry in the DS1 Channel Mapping table.  There
				is an entry in this table corresponding to each
				ds1 ifEntry within any interface that is
				channelized to the individual ds1 ifEntry level.
				This table is intended to facilitate mapping from
				channelized interface / channel number to DS1
				ifEntry.  (e.g. mapping (DS3 ifIndex, DS1 Channel
				Number) -> ifIndex)
				While this table provides information that can
				also be found in the ifStackTable and
				zhoneWanTable, it provides this same information
				with a single table lookup, rather than by walking
				the ifStackTable to find the various constituent
				ds1 ifTable entries, and testing various
				zhoneWanTable entries to check for the entry
				with the applicable DS1 channel number."
			INDEX { ifIndex, zhoneDs1ChannelNumber }
			::= { zhoneChanMappingTable 1 }


		ZhoneChanMappingEntry ::=
			SEQUENCE {
				zhoneChanMappedIfIndex
					InterfaceIndex
			 }

--
		-- 1.3.6.1.4.1.5504.5.2.9.1.1
		zhoneChanMappedIfIndex OBJECT-TYPE
			SYNTAX InterfaceIndex
			MAX-ACCESS read-only
			STATUS current
			DESCRIPTION
				"This object indicates the ifIndex value assigned
				by the agent for the individual ds1 ifEntry that
				corresponds to the given DS1 channel number
				(specified by the INDEX element
				zwDs1ChannelNumber) of the given channelized
				interface (specified by INDEX element ifIndex)."
			::= { zhoneChanMappingEntry 1 }


		-- 1.3.6.1.4.1.5504.5.2.10
		zhoneDsxTraps OBJECT IDENTIFIER ::= { zhoneDsx 10 }


		-- 1.3.6.1.4.1.5504.5.2.10.0
		zhoneDsxTrapsV2 OBJECT IDENTIFIER ::= { zhoneDsxTraps 0 }


		-- 1.3.6.1.4.1.5504.5.2.10.0.1
		zhoneLineStatusChange NOTIFICATION-TYPE
			OBJECTS { zhoneLineStatus, zhoneLineStatusLastChange, ifAlias }
			STATUS current
			DESCRIPTION
				"A zhoneLineStatusChange trap is not sent when the value of an instance zhoneLineStatus
				changes.  It can be utilizeded by the NMS to trigger polls.  When the line status
				change results from a hihter level line status change (i.e. ds3), then no traps
				for the ds1 are sent.

				Not supported on BAN in this release."
			::= { zhoneDsxTrapsV2 1 }


		-- 1.3.6.1.4.1.5504.5.2.13
		zhoneDs1BertTable OBJECT-TYPE
			SYNTAX SEQUENCE OF ZhoneDs1BertEntry
			MAX-ACCESS not-accessible
			STATUS current
			DESCRIPTION
				"The BERT Table is used to issue Bit Error Rate Tests on
				a particular Ds1."
			::= { zhoneDsx 13 }


		-- 1.3.6.1.4.1.5504.5.2.13.1
		zhoneDs1BertEntry OBJECT-TYPE
			SYNTAX ZhoneDs1BertEntry
			MAX-ACCESS not-accessible
			STATUS current
			DESCRIPTION
				"An entry in the BERT table."
			INDEX { zhoneBertIndex }
			::= { zhoneDs1BertTable 1 }


		ZhoneDs1BertEntry ::=
			SEQUENCE {
				zhoneBertIndex
					Integer32,
				zhoneBertInterfaceIndex
					InterfaceIndex,
				zhoneBertRequest
					INTEGER,
				zhoneBertType
					INTEGER,
				zhoneBertTestDuration
					INTEGER,
				zhoneBertLoopUp
					INTEGER
			 }

		-- 1.3.6.1.4.1.5504.5.2.13.1.1
		zhoneBertIndex OBJECT-TYPE
			SYNTAX Integer32 (1..21)
			MAX-ACCESS not-accessible
			STATUS current
			DESCRIPTION
				"This field is the index field for the BERT test
				channel.  There is only 1 BERT test allowed at a
				time."
			::= { zhoneDs1BertEntry 1 }


		-- 1.3.6.1.4.1.5504.5.2.13.1.2
		zhoneBertInterfaceIndex OBJECT-TYPE
			SYNTAX InterfaceIndex
			MAX-ACCESS read-write
			STATUS current
			DESCRIPTION
				"This field contains the InterfaceIndex of the physical line to
				be tested. If no line is currently being tested this value is 0."
			::= { zhoneDs1BertEntry 2 }


		-- 1.3.6.1.4.1.5504.5.2.13.1.3
		zhoneBertRequest OBJECT-TYPE
			SYNTAX INTEGER
				{
				noOp(1),
				start(2),
				stop(3)
				}
			MAX-ACCESS read-write
			STATUS current
			DESCRIPTION
				"Command request list for the Ds1 BERT test.

				This object corresponds to the list of test operations
				that can be performed.

				The possible values are
				    noOp         (1),  -- used when reading the object
				    start        (2),  -- start test
				    stop         (3),  -- stop an initiated test

				Reading this object will always return the value 'noOp (1)'."
			::= { zhoneDs1BertEntry 3 }


		-- 1.3.6.1.4.1.5504.5.2.13.1.4
		zhoneBertType OBJECT-TYPE
			SYNTAX INTEGER
				{
				qrss(1),
				prbs215(2),
				prbs220(3)
				}
			MAX-ACCESS read-write
			STATUS current
			DESCRIPTION
				"The type of pattern to use for the BERT test on the Ds1.
				Supported patterns are qrss, prbs 2^15, or prbs 2^20."
			DEFVAL { qrss }
			::= { zhoneDs1BertEntry 4 }


		-- 1.3.6.1.4.1.5504.5.2.13.1.5
		zhoneBertTestDuration OBJECT-TYPE
			SYNTAX INTEGER (10..300)
			MAX-ACCESS read-write
			STATUS current
			DESCRIPTION
				"The duration in seconds of the BERT test for the Ds1.
				The valid range for this field is 10-300 seconds."
			::= { zhoneDs1BertEntry 5 }


		-- 1.3.6.1.4.1.5504.5.2.13.1.6
		zhoneBertLoopUp OBJECT-TYPE
			SYNTAX INTEGER
				{
				noloop(1),
				lineloop(2),
				payloadloop(3)
				}
			MAX-ACCESS read-write
			STATUS current
			DESCRIPTION
				"The loop code to be sent to the farend prior to running
				the BERT test for the Ds1."
			::= { zhoneDs1BertEntry 6 }


		-- 1.3.6.1.4.1.5504.5.2.14
		zhoneDs1BertResultsTable OBJECT-TYPE
			SYNTAX SEQUENCE OF ZhoneDs1BertResultsEntry
			MAX-ACCESS not-accessible
			STATUS current
			DESCRIPTION
				"The BERT Results Table is used to retrieve results from a
				Bit Error Rate Test on a particular Ds1."
			::= { zhoneDsx 14 }


		-- 1.3.6.1.4.1.5504.5.2.14.1
		zhoneDs1BertResultsEntry OBJECT-TYPE
			SYNTAX ZhoneDs1BertResultsEntry
			MAX-ACCESS not-accessible
			STATUS current
			DESCRIPTION
				"An entry in the BERT results table."
			INDEX { zhoneBertIndex }
			::= { zhoneDs1BertResultsTable 1 }


		ZhoneDs1BertResultsEntry ::=
			SEQUENCE {
				zhoneBertStatus
					INTEGER,
				zhoneBertElapsedTime
					INTEGER,
				zhoneBertErroredSeconds
					INTEGER,
				zhoneBertOutOfSynchSeconds
					INTEGER,
				zhoneBertErrors
					INTEGER
			 }

		-- 1.3.6.1.4.1.5504.5.2.14.1.1
		zhoneBertStatus OBJECT-TYPE
			SYNTAX INTEGER
				{
				inProgress(1),
				abortInProgress(2),
				complete(3),
				noResults(4),
				aborted(5),
				unsupported(6),
				portNotAdminTest(7),
				failed(8)
				}
			MAX-ACCESS read-only
			STATUS current
			DESCRIPTION
				"The overall BERT operational status.  This field will indicate
				the operation status for the interface indexed by
				zhoneBertInterfaceIndex.


				inProgress (1)        - if the test is currently running.

				abortInProgress (2)   - if a request to stop the test
				                        is still in progress.

				complete (3)          - if the test has been run at least
				                        once since system reset and has
				                        completed.

				noResults (4)         - if the test results are empty, such as
				                        after a system reset.

				aborted (5)           - if the test was aborted by the user before
				                        it could complete.

				unsupported (6)       - if the device does not support BERT.

				portNotAdminTest (7)  - if port not in admin TEST.

				failed (8)            - if BERT failed to complete."
			::= { zhoneDs1BertResultsEntry 1 }


		-- 1.3.6.1.4.1.5504.5.2.14.1.2
		zhoneBertElapsedTime OBJECT-TYPE
			SYNTAX INTEGER (0..300)
			MAX-ACCESS read-only
			STATUS current
			DESCRIPTION
				"Elapsed time of the most recent BERT test."
			::= { zhoneDs1BertResultsEntry 2 }


		-- 1.3.6.1.4.1.5504.5.2.14.1.3
		zhoneBertErroredSeconds OBJECT-TYPE
			SYNTAX INTEGER (0..300)
			MAX-ACCESS read-only
			STATUS current
			DESCRIPTION
				"Number of errored seconds for the most recent BERT test.
				This field is only valid when zhoneBertStatus is complete."
			::= { zhoneDs1BertResultsEntry 3 }


		-- 1.3.6.1.4.1.5504.5.2.14.1.4
		zhoneBertOutOfSynchSeconds OBJECT-TYPE
			SYNTAX INTEGER (0..300)
			MAX-ACCESS read-only
			STATUS current
			DESCRIPTION
				"Number of out of synch seconds for the most recent BERT test.
				This field is only valid when zhoneBertStatus is complete."
			::= { zhoneDs1BertResultsEntry 4 }


		-- 1.3.6.1.4.1.5504.5.2.14.1.5
		zhoneBertErrors OBJECT-TYPE
			SYNTAX INTEGER (0..2147483647)
			MAX-ACCESS read-only
			STATUS current
			DESCRIPTION
				"Number of errors for the most recent BERT test.
				This field is only valid when zhoneBertStatus is complete."
			::= { zhoneDs1BertResultsEntry 5 }



	END

--
-- phyDs1.mib
--
