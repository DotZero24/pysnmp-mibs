--
-- comVoiceV52.mib
-- MIB generated by MG-SOFT Visual MIB Builder Version 3.0 Build 285
-- Tuesday, February 05, 2008 at 02:15:25
--

    ZhoneV52-MIB DEFINITIONS ::= BEGIN

        IMPORTS
            PerfCurrentCount
                FROM PerfHist-TC-MIB
            Integer32, Gauge32, OBJECT-TYPE, MODULE-IDENTITY, OBJECT-IDENTITY,
            NOTIFICATION-TYPE
                FROM SNMPv2-SMI
            TruthValue
                FROM SNMPv2-TC
            zhoneVoice
                FROM Zhone
            ZhoneSlotValue, ZhoneShelfValue, ZhoneAdminString, ZhoneShelfValueOrZero, ZhoneSlotValueOrZero,
            ZhoneRowStatus
                FROM Zhone-TC;


--
-- The general term "access network" refers to the
-- system implemented between the end user and the
-- Local Exchange.  Traditionally this has been the
-- copper distribution plant from the MDF to the
-- subscriber but today encompasses any multiplexing,
-- cross-connect and transmission functions (which
-- may be over various means such as copper, optical
-- fibre, or radio) as well as the "last mile" to
-- the end user.
--
-- In the context of V5, Access Network is used in a
-- more specific sense, describing a system replacing
-- part of the whole of the local line distribution
-- network.  The V5 interface is relevant only between
-- an access network containing active components and
-- a local exchange; it does not apply to a passive
-- copper distribution plant directly connected to the
-- exchange.
--
-- V5 Standards
-- ------------
--
-- The V5 standard specifies interfaces between the
-- access network and the Local Exchange.  Two
-- interfaces to support narrowband services have been
-- specififed, V5.1 and V5.2, both based on 64 Kbit/s
-- channels and 2,048 Mbit/s links.
--
-- V5.2 is a multi-2,048 Mbit/s interface for access
-- networks which additionally may support ISDN PRA
-- user ports and which have traffic concentration
-- capability.
--
--
-- Services
-- --------
-- V5 supports both on-demand services (where the
-- connection is made for each call) such as PSTN and
-- ISDN calls, and leased line service which can
-- either be permanent or semi-permanent.
--
-- The PSTN service supports single customer and PABX
-- access, both with DTMF or line state signaling
-- and with or without supplementary services.  Direct
-- Dialing In (DDI) access is supported with the
-- PABX service.
--
-- ISDN Basic Access support for both the 'S/T'
-- reference point and the NT2 'T' reference point
-- is defined. ISDN PRA is supported with the V5.2
-- interface, either with an NT1 as an integral part
-- of the access network or the NT2 'T' reference
-- point.
--
-- V5 supports semi-permanent leased service (analog
-- or digital).  These are classified as 64Kbit/s
-- bearer channels which pass through a local exchange
-- but which have been provisioned rather than setup on
-- a per call basis.  Permanent leased lines (analog or
-- digital) provided by the access network bypass the
-- local exchange and are outside the scope of the V5
-- interface.
--
-- The V5 services outlined above are supported by
-- combinations of V5 bearer channels, communication
-- and control protocols.  The V5 interface carries
-- 64Kbit/s bearer channels associated with a service
-- transparently.  The V5 communication and control
-- protocols are mapped into carrier paths which are
-- assigned to 64Kbit/s communications channels.
--
--
--
--
--
--
--
--
--
--
--
--
--
--
--
--
--
        -- 1.3.6.1.4.1.5504.4.3.2
        zhoneV52 MODULE-IDENTITY
            LAST-UPDATED "200312091636Z"		-- December 09, 2003 at 16:36 GMT
            ORGANIZATION
                "Zhone Technologies, Inc."
            CONTACT-INFO
                "  Postal:
                           Zhone Technologies, Inc.
                           @ Zhone Way
                           7001 Oakport Street
                           Oakland, CA  94621
                           USA
                Toll-Free: +1 877-ZHONE20 (+1 877-946-6320)
                      Tel: +1-510-777-7000
                      Fax: +1-510-777-7001
                   E-mail: support@zhone.com"
            DESCRIPTION
                "The MIB module to describe objects for V5.2."
            REVISION "200802050138Z"		-- February 05, 2008 at 01:38 GMT
            DESCRIPTION
                "V01.02.09:
                - Added support for south-africa and saudi-arabia
                in National pstn region."
            REVISION "200312091636Z"		-- December 09, 2003 at 16:36 GMT
            DESCRIPTION
                "V01.02.08:
                - Correct the lower range v52IgLocalInterfaceId
                  and v52IgRemoteInterfaceId."
            REVISION "200301311409Z"		-- January 31, 2003 at 14:09 GMT
            DESCRIPTION
                "V01.02.07:
                Add Estonia to v52IgNationalPstnRegion list."
            REVISION "200209101515Z"		-- September 10, 2002 at 15:15 GMT
            DESCRIPTION
                "V01.02.06:
                Add Ireland and Australia to v52IgNationalPstnRegion list."
            REVISION "200204050930Z"		-- April 05, 2002 at 09:30 GMT
            DESCRIPTION
                "V01.02.05:
                Add United Arab Emirates to v52IgNationalPstnRegion list."
            REVISION "200112131430Z"		-- December 13, 2001 at 14:30 GMT
            DESCRIPTION
                "V01.02.04:
                - Add ISDN calls to current, interval and total
                  statistics tables.
                - Change OutboundCallsBlocked to CallsBlocked
                  for current, interval and total statistics tables."
            REVISION "200110241700Z"		-- October 24, 2001 at 17:00 GMT
            DESCRIPTION
                "V01.02.03:
                - Update default values and add read-only restrictions to
                  all MIB variables in v52InterfaceGroupLapvTable."
            REVISION "200109041430Z"		-- September 04, 2001 at 14:30 GMT
            DESCRIPTION
                "V01.02.02:
                - Add v52ProtectionCPathTable and trap notification."
            REVISION "200108011115Z"		-- August 01, 2001 at 11:15 GMT
            DESCRIPTION
                "V01.02.01:
                Add Taiwan to v52IgNationalPstnRegion enum list."
            REVISION "200107231550Z"		-- July 23, 2001 at 15:50 GMT
            DESCRIPTION
                "V01.02.00:
                Update V52 MIB to reflect release 1.2 revisions:

                - Update more MIB variables as supported.
                - Add and update notification traps and their matching
                  MIB variables.
                - Set v52LinkAdminStatus to 'obsolete'.
                - Remove 'unknown' from v52IgSwitchVendor enum.
                - Changed default values for v52IgStartupCheckLinkId and
                  v52IgStartupUnblockUserPorts."
            REVISION "200103091430Z"		-- March 09, 2001 at 14:30 GMT
            DESCRIPTION
                "V01.01.06:
                - Added 'restart' to v52IgAdminStatus.
                - Added additional countries to
                  v52IgNationalPstnRegion.
                - Added a new enum to v52IgSwitchVendor.
                - Added a new block state to v52UserPortBlock.
                - Added v52UserPortOperStatus to
                  v52UserPortEntry.
                - Added v52IgExtensionTable for additional
                  V5.2 interface configuration variables."
            REVISION "200101171317Z"		-- January 17, 2001 at 13:17 GMT
            DESCRIPTION
                "V01.01.05:
                Change the validation for the v52LinkDs1ChannelNumber"
            REVISION "200101091112Z"		-- January 09, 2001 at 11:12 GMT
            DESCRIPTION
                "V01.00.04:
                Reordered ZHONE_KEYWORD_STORAGE_ORDER to agree to the MIB."
            REVISION "200012191433Z"		-- December 19, 2000 at 14:33 GMT
            DESCRIPTION
                "V01.00.03:
                Added 3 new variables to the v52UserPortTable:
                v52UserPortIsdnDsCPathId, v52UserPortIsdnPCPathId,
                v52UserPortIsdnFCPathId.
                Added v52IgProtocolSpecification and
                v52IgPeerStatus to v52InterfaceTable.
                Changed austrilia(6) for austria(6) for
                v52IgNationalPstnRegion."
            REVISION "200011221322Z"		-- November 22, 2000 at 13:22 GMT
            DESCRIPTION
                "V01.00.02:
                Added v52IgSwitchVendor.
                Updated v52UserPortTable index.
                Added reference for v52LinkCheckId and
                v52LinkCheckIdStatus."
            REVISION "200010041053Z"		-- October 04, 2000 at 10:53 GMT
            DESCRIPTION
                "V01.00.01:
                Updated table index structures.
                Updated v52InterfaceGroupTable and v52LinkTable
                according to ETSI V5.2 specifications.
                Added V5.2 notificatoin traps."
            REVISION "200008231058Z"		-- August 23, 2000 at 10:58 GMT
            DESCRIPTION
                "V01.00.00 - Initial Release"
            ::= { zhoneVoice 2 }
-- References:
--
-- Nortel, "An Introduction to V5 Interfaces White
-- Paper"
--
-- ETSI EN 300 347-1 V2.2.2 (1999-12)
-- V interfaces at the digital Local Exchange (LE);
-- V5.2 interface for the support of Access Network
-- (AN); Part 1: V5.2 interface specification
--
-- EN 300 324-1 V1.2.3 (1999-06)
-- V interfaces at the digital Local Exchange (LE);
-- V5.1 interface for the support of Access Network
-- (AN); Part 1: V5.1 interface specification
--
-- Q.824.5
-- SERIES Q: SWITCHING AND SIGNALING Specifications
-- of Signaling System No. 7 - Q3 interface
--



--
-- Node definitions
--

--
-- V5.2 interface dynamically allocates bearer
-- channels to user ports on a per call basis.
-- Permits both protection switching and concentration.
--
-- A fully provisioned V5.2 link of sixteen (16) 2,048
-- Mbit/s would give a maximum of around 480 channels.
-- The concentration factor achievable depends on the
-- number of circuits and the traffic offered and is
-- calculated for a given grade of service.
--
        -- 1.3.6.1.4.1.5504.4.3.2.1
        v52InterfaceGroupTable OBJECT-TYPE
            SYNTAX SEQUENCE OF V52InterfaceGroupEntry
            MAX-ACCESS not-accessible
            STATUS current
            DESCRIPTION
                "V5.2 Interface Group table.

                A V5.2 interface contains 1-16 E1 links.  The protocols
                defined in the ETSI V5.2 specification (ETS 300 347-1)
                are carried across the interface that is located between
                the AN and the LE.  The V5 interface is a logical concept."
            REFERENCE
                "ETSI EN 300 347-1 V2.2.2 (1999-12)
                "
            ::= { zhoneV52 1 }


        -- 1.3.6.1.4.1.5504.4.3.2.1.1
        v52InterfaceGroupEntry OBJECT-TYPE
            SYNTAX V52InterfaceGroupEntry
            MAX-ACCESS not-accessible
            STATUS current
            DESCRIPTION
                "An entry in the v52InterfaceBundleTable"
            INDEX { v52IgNameId }
            ::= { v52InterfaceGroupTable 1 }


        V52InterfaceGroupEntry ::=
            SEQUENCE {
                v52IgNameId
                    ZhoneAdminString,
                v52IgShelf
                    ZhoneShelfValue,
                v52IgSlot
                    ZhoneSlotValue,
                v52IgPeerShelf
                    ZhoneShelfValueOrZero,
                v52IgPeerSlot
                    ZhoneSlotValueOrZero,
                v52IgPeerStatus
                    INTEGER,
                v52IgLocalInterfaceId
                    Integer32,
                v52IgRemoteInterfaceId
                    Integer32,
                v52IgLocalProvVariant
                    Integer32,
                v52IgRemoteProvVariant
                    Integer32,
                v52IgProvVariantRequest
                    INTEGER,
                v52IgProvVariantRequestStatus
                    INTEGER,
                v52IgAdminStatus
                    INTEGER,
                v52IgOperationalStatus
                    INTEGER,
                v52IgOperStatusCause
                    INTEGER,
                v52IgMaxConfiguredCalls
                    Gauge32,
                v52IgCurrActiveCalls
                    Gauge32,
                v52IgPstnLayer3StartAddress
                    Integer32,
                v52IgIsdnEnvFuncStartAddress
                    Integer32,
                v52IgStatsTimeElapsed
                    Integer32,
                v52IgStatsValidIntervals
                    Integer32,
                v52IgStatsInvalidIntervals
                    Integer32,
                v52IgPortAlignmentRequest
                    INTEGER,
                v52IgPortAlignmentStatus
                    INTEGER,
                v52IgNationalPstnRegion
                    INTEGER,
                v52IgSwitchVendor
                    INTEGER,
                v52IgProtocolSpecification
                    INTEGER,
                v52IgRowStatus
                    ZhoneRowStatus
             }

--
        -- 1.3.6.1.4.1.5504.4.3.2.1.1.1
        v52IgNameId OBJECT-TYPE
            SYNTAX ZhoneAdminString
            MAX-ACCESS not-accessible
            STATUS current
            DESCRIPTION
                "The Interface Group name is a system-wide unique
                symbolic name that is used for call routing.  The
                maximum length for this name is 32 characters."
            ::= { v52InterfaceGroupEntry 1 }


--
        -- 1.3.6.1.4.1.5504.4.3.2.1.1.2
        v52IgShelf OBJECT-TYPE
            SYNTAX ZhoneShelfValue
            MAX-ACCESS read-only
            STATUS current
            DESCRIPTION
                "The shelf where this Interface and V5.2
                stack resides.  Range of valid values is
                1-255.  Note 0 is an invalid value."
            ::= { v52InterfaceGroupEntry 2 }


--
        -- 1.3.6.1.4.1.5504.4.3.2.1.1.3
        v52IgSlot OBJECT-TYPE
            SYNTAX ZhoneSlotValue
            MAX-ACCESS read-only
            STATUS current
            DESCRIPTION
                "The shelf where this Interface  and V5.2
                stack resides.  Range of valid values is
                1-17.  Note 0 is an invalid value."
            ::= { v52InterfaceGroupEntry 3 }


--
        -- 1.3.6.1.4.1.5504.4.3.2.1.1.4
        v52IgPeerShelf OBJECT-TYPE
            SYNTAX ZhoneShelfValueOrZero
            MAX-ACCESS read-only
            STATUS current
            DESCRIPTION
                "The shelf where this Redundancy Group's peer
                (or standby) resides.  Peer shelf and peer
                slot define where this peer Interface Group
                and V5.2 stack resides.  Range of valid
                values is 0-255.  A peer shelf value of 0
                represents a no backup configuration."
            ::= { v52InterfaceGroupEntry 4 }


--
        -- 1.3.6.1.4.1.5504.4.3.2.1.1.5
        v52IgPeerSlot OBJECT-TYPE
            SYNTAX ZhoneSlotValueOrZero
            MAX-ACCESS read-only
            STATUS current
            DESCRIPTION
                "The slot where this Interface Group's peer
                (or standby) resides. Peer shelf and peer
                slot define where this Interface Group peer
                and V5.2 stack resides. Range of valid
                values is 0-17. A peer slot value of 0
                represents a no backup configuration."
            ::= { v52InterfaceGroupEntry 5 }


        -- 1.3.6.1.4.1.5504.4.3.2.1.1.6
        v52IgPeerStatus OBJECT-TYPE
            SYNTAX INTEGER
                {
                noStandbyConfigured(1),
                configuredAndAvailable(2),
                configuredAndUnavailable(3)
                }
            MAX-ACCESS read-only
            STATUS current
            DESCRIPTION
                "The status of the peer (or standby) Interface
                Group Valid peer status values are:

                * noStandbyConfigured
                * configuredAndAvailable
                * configuredAndUnavailable"
            ::= { v52InterfaceGroupEntry 6 }


--
        -- 1.3.6.1.4.1.5504.4.3.2.1.1.7
        v52IgLocalInterfaceId OBJECT-TYPE
            SYNTAX Integer32 (0..16777215)
            MAX-ACCESS read-create
            STATUS current
            DESCRIPTION
                "24-bit AN side V5.2 Interface identifier provisioned.
                Valid range is 0..16777215."
            REFERENCE
                "AV5 Application Notes 2.1.4.1 Logical C-Channels"
            DEFVAL { 0 }
            ::= { v52InterfaceGroupEntry 7 }


--
        -- 1.3.6.1.4.1.5504.4.3.2.1.1.8
        v52IgRemoteInterfaceId OBJECT-TYPE
            SYNTAX Integer32 (0..16777215)
            MAX-ACCESS read-only
            STATUS current
            DESCRIPTION
                "24-bit LE side V5.2 Interface identifier provisioned.
                This is read only can only be updated indirectly by
                setting v52IgProvVariantRequest to requestFromLe.

                Valid range is 0..16777215."
            REFERENCE
                "AV5 Application Notes 2.1.4.1 Logical C-Channels"
            ::= { v52InterfaceGroupEntry 8 }


        -- 1.3.6.1.4.1.5504.4.3.2.1.1.9
        v52IgLocalProvVariant OBJECT-TYPE
            SYNTAX Integer32 (0..127)
            MAX-ACCESS read-create
            STATUS current
            DESCRIPTION
                "AN side provisioning variant used to differentiate
                variations in configuration. This is provisioned by the
                user. Valid range is 0..127.  Default is 0."
            REFERENCE
                "AV5 Application Notes 2.1.4.1 Logical C-Channels"
            DEFVAL { 0 }
            ::= { v52InterfaceGroupEntry 9 }


        -- 1.3.6.1.4.1.5504.4.3.2.1.1.10
        v52IgRemoteProvVariant OBJECT-TYPE
            SYNTAX Integer32 (0..127)
            MAX-ACCESS read-only
            STATUS current
            DESCRIPTION
                "LE side provisioning variant used to differentiate
                variations in configuration. This is read only can only be
                updated indirectly by setting v52IgProvVariantRequest to
                requestFromLe.

                Valid range is
                0..127.  Default is 0."
            REFERENCE
                "AV5 Application Notes 2.1.4.1 Logical C-Channels"
            ::= { v52InterfaceGroupEntry 10 }


        -- 1.3.6.1.4.1.5504.4.3.2.1.1.11
        v52IgProvVariantRequest OBJECT-TYPE
            SYNTAX INTEGER
                {
                noRequest(1),
                verifyWithLe(2),
                requestFromLe(3),
                switchLeToLocal(4)
                }
            MAX-ACCESS read-create
            STATUS current
            DESCRIPTION
                "User requests to carry out various actions about
                provisioning variant. Valid values for this variable can
                be:

                * noRequest - this is the default value. Setting the
                  variable to this value explicitly has no effect.
                * verifyWithLe - request to verify if LE is ready for
                  reprovision.
                * requestFromLe - request to get LE Variant ID and
                  Interface ID.
                * switchLeToLocal - request the LE side to change its
                  provisioning variant to be the same as
                  v52IgLocalProvVariant.

                Only requestFromLe set option is currently supported."
            REFERENCE
                "AV5 Application Notes 2.1.4.1 Logical C-Channels"
            DEFVAL { noRequest }
            ::= { v52InterfaceGroupEntry 11 }


        -- 1.3.6.1.4.1.5504.4.3.2.1.1.12
        v52IgProvVariantRequestStatus OBJECT-TYPE
            SYNTAX INTEGER
                {
                verifyWithLeSucceeded(1),
                verifyWithLeFailed(2),
                requestFromLeSucceeded(3),
                requestFromLeFailed(4),
                switchToLocalSucceeded(5),
                switchToLocalFailed(6)
                }
            MAX-ACCESS read-only
            STATUS current
            DESCRIPTION
                "Status result for v52IgProvVariantRequest. When
                v52IgProvVariantRequest has a value of noRequest, the
                value for this variable is invalid.

                Valid values for this variable are:

                * verifyWithLeSucceeded - LE is ready for reprovision with
                  the verifyWithLe request.
                * verifyWithLeFailed - LE is not ready for reprovision
                  with the verifyWithLe request.
                * requestFromLeSucceeded - received Variant ID and
                  Interface ID from LE with the requestFromLe request.
                * requestFromLeFailed - did not receive Variant ID and
                  Interface ID from LE with the requestFromLe request.
                * swithtoLocalSucceeded - LE side has changed its own
                  provisioning variant to be the same as
                  v52IgLocalProvVariant with the switchToLocal request.
                * swithtoLocalFailed - LE side failed to change its own
                  provisioning variant to be the same as
                  v52IgLocalProvVariant with the switchToLocal request."
            REFERENCE
                "AV5 Application Notes 2.1.4.1 Logical C-Channels"
            ::= { v52InterfaceGroupEntry 12 }


--
        -- 1.3.6.1.4.1.5504.4.3.2.1.1.13
        v52IgAdminStatus OBJECT-TYPE
            SYNTAX INTEGER
                {
                inService(1),
                outOfService(2),
                deferredOutOfService(3),
                restart(4)
                }
            MAX-ACCESS read-create
            STATUS current
            DESCRIPTION
                "Interface Admin Status. Valid values are
                inService, outOfService, deferredOutOfService and
                restart. Default value is outOfService.

                * 'deferredOutofService' takes the interface group
                  out of service, but not until all calls are
                  completed.

                * 'restart' causes the v52 interface to shutdown
                  for a period of time and then go through the
                  startup procedure. When restart is complete,
                  the V5.2 interface should go back to the
                  previously configured admin status before it
                  was set to 'restart'. According to ETSI EN
                  300 347-1 V2.2.2, 95 seconds is the minimum time
                  a system has to be shutdown before it can be
                  returned for service."
            DEFVAL { outOfService }
            ::= { v52InterfaceGroupEntry 13 }


--
        -- 1.3.6.1.4.1.5504.4.3.2.1.1.14
        v52IgOperationalStatus OBJECT-TYPE
            SYNTAX INTEGER
                {
                operable(1),
                inoperable(2),
                standby(3),
                degradedService(4),
                inoperableIsInProgress(5),
                inoperableOosInProgress(6)
                }
            MAX-ACCESS read-only
            STATUS current
            DESCRIPTION
                "Interface operational status.  Valid values are
                operable, inoperable, standby, and degradedService.
                Indicates whether it is fully inoperable and
                unable to provide service to the user, or it is
                fully operable and available for use.

                Valid values are operable, inoperable, standby,
                degradedService and the transitional states of
                inoperableIsInProgress and inoperableOosInProgress.
                Depending on the V52 configuration, the transition
                between inService and outOfService can take quite
                some time for an interface group. The transitional
                states give operator a more accurate indication of
                a V52 IG's behavior.

                AdminStatus    OperationalStatus   Description
                -----------    -----------------   -----------
                outOfService   operable            not valid
                outOfService   inoperable          admin out of service
                outOfService   standby             not valid
                inService      operable            normal operations
                inService      inOperable          fault
                inService      standby             normal operations"
            ::= { v52InterfaceGroupEntry 14 }


--
        -- 1.3.6.1.4.1.5504.4.3.2.1.1.15
        v52IgOperStatusCause OBJECT-TYPE
            SYNTAX INTEGER
                {
                other(1),
                localDisable(2),
                remoteOutOfService(3),
                protocolFailure(4)
                }
            MAX-ACCESS read-only
            STATUS current
            DESCRIPTION
                "Cause for Interface operational status.  Valid
                values are other, localDisable, remoteOutOfService,
                and protocolFailure."
            ::= { v52InterfaceGroupEntry 15 }


--
        -- 1.3.6.1.4.1.5504.4.3.2.1.1.16
        v52IgMaxConfiguredCalls OBJECT-TYPE
            SYNTAX Gauge32 (30..480)
            MAX-ACCESS read-only
            STATUS current
            DESCRIPTION
                "Maximum number of active calls.

                Maximum number of active calls is equal to the maximum
                number of links (up to 16) assigned to the IG times
                the maximum number of time slots per E1 link (31)
                less the total number of provisioned C channels on
                these links."
            ::= { v52InterfaceGroupEntry 16 }


--
        -- 1.3.6.1.4.1.5504.4.3.2.1.1.17
        v52IgCurrActiveCalls OBJECT-TYPE
            SYNTAX Gauge32 (0..480)
            MAX-ACCESS read-only
            STATUS current
            DESCRIPTION
                "The number of calls currently active.

                Not supported."
            ::= { v52InterfaceGroupEntry 17 }


--
        -- 1.3.6.1.4.1.5504.4.3.2.1.1.18
        v52IgPstnLayer3StartAddress OBJECT-TYPE
            SYNTAX Integer32 (0..32767)
            MAX-ACCESS read-create
            STATUS current
            DESCRIPTION
                "Starting PSTN layer 3 port address the analogue
                access is assigned to.  Valid range in 0..32767.

                This variable can only be modified when
                v52IgAdminStatus is set to outOfService and
                there are no PSTN user ports attached to the
                interface group."
            ::= { v52InterfaceGroupEntry 18 }


--
        -- 1.3.6.1.4.1.5504.4.3.2.1.1.19
        v52IgIsdnEnvFuncStartAddress OBJECT-TYPE
            SYNTAX Integer32 (0..8175)
            MAX-ACCESS read-create
            STATUS current
            DESCRIPTION
                "The envelope function starting address the ISDN
                primary rate access is assigned to.  Valid range
                is 0..8175.

                This variable can only be modified when
                v52IgAdminStatus is set to outOfService and
                there are no ISDN user ports attached to the
                interface group."
            ::= { v52InterfaceGroupEntry 19 }


--
        -- 1.3.6.1.4.1.5504.4.3.2.1.1.20
        v52IgStatsTimeElapsed OBJECT-TYPE
            SYNTAX Integer32 (0..899)
            MAX-ACCESS read-only
            STATUS current
            DESCRIPTION
                "The number of seconds that have elapsed since
                the beginning of the current collection
                period.  If, for some reason, such as an
                adjustment in the system's time-of-day clock,
                the current interval exceeds the maximum value,
                the agent will return the maximum value.

                Not supported."
            ::= { v52InterfaceGroupEntry 20 }


--
        -- 1.3.6.1.4.1.5504.4.3.2.1.1.21
        v52IgStatsValidIntervals OBJECT-TYPE
            SYNTAX Integer32 (0..96)
            MAX-ACCESS read-only
            STATUS current
            DESCRIPTION
                "The number of previous intervals for which
                data was collected.  The value will typically
                be 96 unless the interface group was brought
                online within the last 24 hours, in which case
                the value will be the number of complete 15 minute
                intervals since the interface has been online.

                In the case where the agent is an SNMP
                transport bridging proxy or SNMP translating
                proxy, it is possible that some intervals
                are unavailable. In this case, this interval
                is the maximum interval number for which
                data is available.

                Not supported."
            ::= { v52InterfaceGroupEntry 21 }


--
        -- 1.3.6.1.4.1.5504.4.3.2.1.1.22
        v52IgStatsInvalidIntervals OBJECT-TYPE
            SYNTAX Integer32 (0..96)
            MAX-ACCESS read-only
            STATUS current
            DESCRIPTION
                "The number of intervals in the range from 0 to
                igStatsValidIntervals for which no data is
                available.  This object will typically be zero
                except in cases where the data for some intervals
                are not available (e.g., in proxy situations).

                Not supported."
            ::= { v52InterfaceGroupEntry 22 }


        -- 1.3.6.1.4.1.5504.4.3.2.1.1.23
        v52IgPortAlignmentRequest OBJECT-TYPE
            SYNTAX INTEGER
                {
                noRequest(1),
                blockAll(2),
                blockIsdn(3),
                blockPstn(4),
                unblockAll(5),
                unblockIsdn(6),
                unblockPstn(7)
                }
            MAX-ACCESS read-create
            STATUS current
            DESCRIPTION
                "Request to block or unblock all the user ports associated
                with the current IG by port type. This is needed to be
                compiliant with the V5.2 requirement for Accelerated Port
                Alignment.

                The status result of this request will be indicated by
                v52IgPortAlignmentStatus and the individual user port
                block status will also be updated.

                Valid values for the variable are:

                * noRequest - this is the default value.
                * blockAll - block all user ports associated with this IG.
                * blockIsdn - block all the isdnBa and isdnPra user ports
                  associated with this IG.
                * blockPstn - block all the pstn user ports associated with
                  this IG.
                * unblockAll - unblock all user ports associated with this
                  IG.
                * unblockIsdn - unblock all the isdnBa and isdnPra user
                  ports associated with this IG.
                * unblockPstn - unblock all the pstn user ports associated
                  with this IG.

                When v52UserPortBlock at the user port level is set to be
                'blockedNotSuitableForGroupUnblocking', the user port will
                not be unblocked by issuing an unblocking request using
                the v52IgPortAlignmentRequest.

                'blockAll' option is currently not supported."
            DEFVAL { noRequest }
            ::= { v52InterfaceGroupEntry 23 }


        -- 1.3.6.1.4.1.5504.4.3.2.1.1.24
        v52IgPortAlignmentStatus OBJECT-TYPE
            SYNTAX INTEGER
                {
                blockAllSucceeded(1),
                blockAllFailed(2),
                blockIsdnSucceded(3),
                blockIsdnFailed(4),
                blockPstnSucceded(5),
                blockPstnFailed(6),
                unblockAllSucceeded(7),
                unblockAllFailed(8),
                unblockIsdnSucceeded(9),
                unblockIsdnFailed(10),
                unblockPstnSucceeded(11),
                unblockPstnFailed(12)
                }
            MAX-ACCESS read-only
            STATUS current
            DESCRIPTION
                "Indicate the status result for user port block/unblock
                request by port type. The values of this variable indicate
                both type of request and its success or fail status.

                The value is invalid when v52IgPortAlignmentRequest is
                noRequest."
            ::= { v52InterfaceGroupEntry 24 }


        -- 1.3.6.1.4.1.5504.4.3.2.1.1.25
        v52IgNationalPstnRegion OBJECT-TYPE
            SYNTAX INTEGER
                {
                etsi(1),
                germany(2),
                uk(3),
                italy(4),
                finland(5),
                austria(6),
                belgium(7),
                china(8),
                france(9),
                hong-kong(10),
                japan(11),
                korea(12),
                netherlands(13),
                new-zealand(14),
                singapore(15),
                spain(16),
                sweden(17),
                switzerland(18),
                mexico(19),
                argentina(20),
                peru(21),
                puerto-rico(22),
                brazil(23),
                malaysia(24),
                taiwan(25),
                united-arab-emirates(26),
                ireland(27),
                australia(28),
                estonia(29),
                south-africa(30),
                saudi-arabia(31)
                }
            MAX-ACCESS read-create
            STATUS current
            DESCRIPTION
                "V5.2's regional and country specific setting for the PSTN
                profile. This setting will dictate the regional signaling
                differences such as ring cadence.

                ETSI is the default value and the list of PSTN regions can
                be extended in the future."
            DEFVAL { etsi }
            ::= { v52InterfaceGroupEntry 25 }


--
        -- 1.3.6.1.4.1.5504.4.3.2.1.1.26
        v52IgSwitchVendor OBJECT-TYPE
            SYNTAX INTEGER
                {
                lucent(2),
                nortel(3),
                alcatel(4),
                ericsson(5),
                nokia(6),
                siemens(7),
                samsung(8)
                }
            MAX-ACCESS read-create
            STATUS current
            DESCRIPTION
                "The switch vendor for the Interface Group. The
                following switch vendors are defined: unknown,
                lucent, nortel, alcatel, ericsson, nokia, siemens,
                samsung.

                Please note that 'unknown(1)' is no longer a valid
                value for this variable."
            DEFVAL { ericsson }
            ::= { v52InterfaceGroupEntry 26 }


--
        -- 1.3.6.1.4.1.5504.4.3.2.1.1.27
        v52IgProtocolSpecification OBJECT-TYPE
            SYNTAX INTEGER
                {
                edition1(1),
                edition2(2)
                }
            MAX-ACCESS read-create
            STATUS current
            DESCRIPTION
                "This variable specifies which variation of the v5.2
                protocol is to be used by this interface group.
                Currently, there are two variations defined according
                to the ETSI specifications:

                * edition1 - refers to V5.2 specification defined in ETSI
                  ETS 300 347-1 ed.1 (1994-09).
                * edition2 - refers to V5.2 specification defined in ETSI
                  EN 300 347-1 V2.2.2 (1999-12)"
            DEFVAL { 2 }
            ::= { v52InterfaceGroupEntry 27 }


        -- 1.3.6.1.4.1.5504.4.3.2.1.1.28
        v52IgRowStatus OBJECT-TYPE
            SYNTAX ZhoneRowStatus
            MAX-ACCESS read-create
            STATUS current
            DESCRIPTION
                "Used to control row creation and deletion.

                A row in this table is created using a single
                SNMP SET request with varbinds for:
                a) v52IgRowStatus set to'CreateAndGo',
                b) the following READ-CREATE object(s):
                   *

                If 'createAndGo' successfully created a new row,
                the RowStatus will be 'active'.  Subsequent to
                successful row creation, the RowStatus can be
                retrieved via an SNMP GET and the returned
                RowStatus value is active.  If the 'createAndGo'
                was unsuccessful an SNMP error will be returned
                and a subsequent GET on the non-existent row
                will also return an SNMP error of noSuchInstance.
                An SNMP SET with the RowStatus value of 'destroy'
                indicates that the agent should remove the row
                from service and then delete it.

                An row object of v52InterfaceGroupEntry can only
                be deleted when there are no v52UserPort associated
                with this IG.

                When an IG is deleted, the associated entries in the
                following tables will be deleted as well.
                - v52InterfaceGroupLapvTable
                - v52LinkTable
                - v52CChannelTable
                - v52CPathTable"
            ::= { v52InterfaceGroupEntry 28 }


        -- 1.3.6.1.4.1.5504.4.3.2.2
        v52InterfaceGroupLapvTable OBJECT-TYPE
            SYNTAX SEQUENCE OF V52InterfaceGroupLapvEntry
            MAX-ACCESS not-accessible
            STATUS current
            DESCRIPTION
                "V5.2 Interface Group LAPV table.

                This table contains the configurable LAPV
                parameters for the interface group.  It augments
                the v52InterfaceGroupTable.  When an
                v52InterfaceGroupEntry is created, a corresponding
                row in the v52InterfaceGroupLapvTable will be
                created. All read-create objects must be provided
                for the SET if the DEFVAL, if one is defined, is
                to be over-ridden."
            ::= { zhoneV52 2 }


        -- 1.3.6.1.4.1.5504.4.3.2.2.1
        v52InterfaceGroupLapvEntry OBJECT-TYPE
            SYNTAX V52InterfaceGroupLapvEntry
            MAX-ACCESS not-accessible
            STATUS current
            DESCRIPTION
                "An augmented entry in the v52InterfaceGroupLapvTable.
                This table augments the v52InterfaceGroupTable."
            AUGMENTS { v52InterfaceGroupEntry }
            ::= { v52InterfaceGroupLapvTable 1 }


        V52InterfaceGroupLapvEntry ::=
            SEQUENCE {
                v52IgLapvMaxOutstandingFrames
                    Integer32,
                v52IgLapvN200
                    Integer32,
                v52IgLapvN201
                    Integer32,
                v52IgLapvT200
                    Integer32,
                v52IgLapvT203
                    Integer32
             }

--
        -- 1.3.6.1.4.1.5504.4.3.2.2.1.1
        v52IgLapvMaxOutstandingFrames OBJECT-TYPE
            SYNTAX Integer32 (1..7)
            UNITS "frames"
            MAX-ACCESS read-create
            STATUS current
            DESCRIPTION
                "Maximum number of outstanding information frames
                at layer 2

                Range of valid values is 1-7.  Default value is 7.

                Currently, the value of this variable cannot be
                changed and it will always be 7."
            DEFVAL { 7 }
            ::= { v52InterfaceGroupLapvEntry 1 }


--
        -- 1.3.6.1.4.1.5504.4.3.2.2.1.2
        v52IgLapvN200 OBJECT-TYPE
            SYNTAX Integer32 (1..10)
            MAX-ACCESS read-create
            STATUS current
            DESCRIPTION
                "The maximum number of retransmissions for a
                frame allowed at layer 2, N200 shall be user
                selectable within the range of 1 to 10, inclusive,
                with a step size of 1 and a default value of 3.

                Currently, the value of this variable cannot be
                changed and it will always be 3."
            DEFVAL { 3 }
            ::= { v52InterfaceGroupLapvEntry 2 }


--
        -- 1.3.6.1.4.1.5504.4.3.2.2.1.3
        v52IgLapvN201 OBJECT-TYPE
            SYNTAX Integer32 (0..260)
            MAX-ACCESS read-create
            STATUS current
            DESCRIPTION
                "The maximum number of octets in the information
                field of an I frame, N201, shall be 260. (This
                SAP is used for operations messages.)  Valid
                range is 0..260.  Default is 260.

                Currently, the value of this variable cannot be
                changed and it will always be 260."
            DEFVAL { 260 }
            ::= { v52InterfaceGroupLapvEntry 3 }


--
        -- 1.3.6.1.4.1.5504.4.3.2.2.1.4
        v52IgLapvT200 OBJECT-TYPE
            SYNTAX Integer32 (100 | 150 | 200 | 250 | 300 | 350 | 400 | 450 | 500 | 550 | 600 | 650 | 700 | 750 | 800 | 850 | 900 | 950 | 1000)
            UNITS "milliseconds"
            MAX-ACCESS read-create
            STATUS current
            DESCRIPTION
                "Maximum layer 2 wait time for an acknowledgment
                of a transmitted frame (T200) For all SAPs, the
                value of T200 shall be user selectable within the
                range of 100 ms to 1000 ms, inclusive, the step
                size shall be 50 ms, and the default value of
                T200 shall be 1000 ms.

                Currently, the value of this variable cannot be
                changed and it will always be 1000 ms."
            DEFVAL { 1000 }
            ::= { v52InterfaceGroupLapvEntry 4 }


--
        -- 1.3.6.1.4.1.5504.4.3.2.2.1.5
        v52IgLapvT203 OBJECT-TYPE
            SYNTAX Integer32 (10 | 20 | 30 | 40 | 50 | 60 | 70 | 80 | 90 | 100 | 110 | 120 | 130 | 140 | 150 | 160 | 170 | 180 | 190 | 200 | 210 | 220 | 230 | 240 | 250 | 260 | 270 | 280 | 290 | 300)
            UNITS "seconds"
            MAX-ACCESS read-create
            STATUS current
            DESCRIPTION
                "Maximum layer 2 idle time before connection
                verification is necessary (T203).For all SAPS,
                the value of T203 shall be user selectable within
                the range of 10 to 300 seconds, inclusive, the
                step size shall be 10 seconds, and the default
                value shall be 10 seconds.

                Currently, the value of this variable cannot be
                changed and it will always be 10 seconds."
            DEFVAL { 10 }
            ::= { v52InterfaceGroupLapvEntry 5 }


        -- 1.3.6.1.4.1.5504.4.3.2.3
        v52LinkTable OBJECT-TYPE
            SYNTAX SEQUENCE OF V52LinkEntry
            MAX-ACCESS not-accessible
            STATUS current
            DESCRIPTION
                "Table of provisioned 2.048 Mbit/s E1 links,

                The term link is a logical concept used to
                describe a communication channel between
                two points.  in V5 there are many kinds of
                links: E1 links, data links, etc.  The
                term link is used to mean E1 link.

                "
            ::= { zhoneV52 3 }


        -- 1.3.6.1.4.1.5504.4.3.2.3.1
        v52LinkEntry OBJECT-TYPE
            SYNTAX V52LinkEntry
            MAX-ACCESS not-accessible
            STATUS current
            DESCRIPTION
                "An entry in the v52LinkTable."
            INDEX { v52IgNameId, v52LinkDsnLgId, v52LinkDs1ChannelNumber }
            ::= { v52LinkTable 1 }


        V52LinkEntry ::=
            SEQUENCE {
                v52LinkDsnLgId
                    Integer32,
                v52LinkDs1ChannelNumber
                    Integer32,
                v52LinkId
                    Integer32,
                v52LinkCheckId
                    INTEGER,
                v52LinkCheckIdStatus
                    INTEGER,
                v52LinkAdminStatus
                    INTEGER,
                v52LinkBlock
                    INTEGER,
                v52LinkBlockStatus
                    INTEGER,
                v52LinkRowStatus
                    ZhoneRowStatus
             }

--
        -- 1.3.6.1.4.1.5504.4.3.2.3.1.1
        v52LinkDsnLgId OBJECT-TYPE
            SYNTAX Integer32 (1..2147483647)
            MAX-ACCESS not-accessible
            STATUS current
            DESCRIPTION
                "The v52LinkDsnLgId object identifies the line group
                entry ID for the E1 line group ID.

                The range for v52LinkDsnLgId is 1..2147483647."
            ::= { v52LinkEntry 1 }


--
        -- 1.3.6.1.4.1.5504.4.3.2.3.1.2
        v52LinkDs1ChannelNumber OBJECT-TYPE
            SYNTAX Integer32 (1..28)
            MAX-ACCESS not-accessible
            STATUS current
            DESCRIPTION
                "Identifies the DS1 for the channelized DS3 or
                physical T1/E1.  The v52LinkDs1ChannelNumber for a card
                with a physical T1 or E1 is 1, otherwise it refers to
                the channel number of the DS3 port which contains the DS1.
                In the later case, the range for v52LinkDS1ChannelNumber is
                1..28."
            ::= { v52LinkEntry 2 }


--
        -- 1.3.6.1.4.1.5504.4.3.2.3.1.3
        v52LinkId OBJECT-TYPE
            SYNTAX Integer32 (0..255)
            MAX-ACCESS read-create
            STATUS current
            DESCRIPTION
                "V5.2 Link identifier.  Provisioned.

                Valid range is 0..255."
            REFERENCE
                "AV5 Application Notes 2.1.4.1 Logical C-Channels"
            ::= { v52LinkEntry 3 }


--
        -- 1.3.6.1.4.1.5504.4.3.2.3.1.4
        v52LinkCheckId OBJECT-TYPE
            SYNTAX INTEGER
                {
                activated(1),
                notActivated(2)
                }
            MAX-ACCESS read-create
            STATUS current
            DESCRIPTION
                "Valid values for this variable are activated and
                notActivated and the default is notActivated.

                Set this variable to 'activated' to request check
                v52LinkId with the LE side link id. When the checkId
                is finished, this value will be 'notActivated'.

                Setting the value to 'notActivated' has no impact.

                A link identification check can successfully be started
                only when the link is operational. This link identification
                procedure can be initiated from either the AN or LE side
                but LE has priority over AN initiated request in case of
                collision of requests from AN and LE, in which case, the
                v52LinkCheckId request will fail.

                It is up to the system management to initiate the link
                identification or not. It can be performed by the system
                management on a timed basis, or be applied after
                re-provisioning."
            REFERENCE
                "Section 16.2.4.3.5 - ETSI EN 300 347-1 V2.2.2 (1999-12)"
            DEFVAL { notActivated }
            ::= { v52LinkEntry 4 }


--
        -- 1.3.6.1.4.1.5504.4.3.2.3.1.5
        v52LinkCheckIdStatus OBJECT-TYPE
            SYNTAX INTEGER
                {
                succeeded(1),
                failed(2),
                rejected(3)
                }
            MAX-ACCESS read-only
            STATUS current
            DESCRIPTION
                "Status result for v52LinkCheckId. Valid values for
                this variable are succeeded, failed and rejected.

                It is the responsibility of the system management to
                take the appropriate action according to the
                v52LinkCheckIdStatus:

                If v52LinkCheckIdStatus is 'rejected', the operator can
                retry the request sometime later.

                If v52LinkCheckIdStatus is 'failed', the operator must
                correctly reprovision the system coordinating with the
                LE provisioning data and restart it."
            REFERENCE
                "Section 16.2.4.3.5 - ETSI EN 300 347-1 V2.2.2 (1999-12)"
            ::= { v52LinkEntry 5 }


        -- 1.3.6.1.4.1.5504.4.3.2.3.1.6
        v52LinkAdminStatus OBJECT-TYPE
            SYNTAX INTEGER
                {
                inService(1),
                outOfService(2)
                }
            MAX-ACCESS read-create
            STATUS obsolete
            DESCRIPTION
                "Link Admin Status.  Valid values are inService
                and outOfService.

                Default is outOfService.

                This variable is obsolete and will no longer be used."
            DEFVAL { outOfService }
            ::= { v52LinkEntry 6 }


--
        -- 1.3.6.1.4.1.5504.4.3.2.3.1.7
        v52LinkBlock OBJECT-TYPE
            SYNTAX INTEGER
                {
                deferredBlocked(1),
                nonDeferredBlocked(2),
                forceBlocked(3),
                unblocked(4)
                }
            MAX-ACCESS read-create
            STATUS current
            DESCRIPTION
                "Link blocking procedure is asymmetrical. AN
                requests link block, LE decides, LE releases
                connection, LE re-establishes semi-perm and
                pre-connected connections.

                An E1 is added in a blocked state and must be
                unblocked by the LE before the E1 becomes
                operational.

                An E1 must be administratively locked or blocked
                by the LE before it can be deleted.

                The default value is unblocked and valid values are:

                * deferredBlocked - wait until there is no active
                  calls on the link.
                * nonDeferredBlocked - disconnect any connection
                  after approval from LE.
                * forceBlocked - This is a forced blocking from AN
                  without LE's approval.
                * unblocked - Unlock the link."
            DEFVAL { unblocked }
            ::= { v52LinkEntry 7 }


--
        -- 1.3.6.1.4.1.5504.4.3.2.3.1.8
        v52LinkBlockStatus OBJECT-TYPE
            SYNTAX INTEGER
                {
                unblocked(1),
                local(2),
                remote(3),
                both(4)
                }
            MAX-ACCESS read-only
            STATUS current
            DESCRIPTION
                "AdminLinkBlock operational status.  Link blocking
                procedure is assymetrical. AN requests link block,
                LE decides, LE releases connection, LE re-establishes
                semi-perm and pre-connected connections.

                Valid values are unblocked, local, remote, and both:

                * local - local is blocked
                * remote - remote is blocked
                * both - both local and remote are blocked
                * unblocked - both local and remote are unblocked"
            ::= { v52LinkEntry 8 }


        -- 1.3.6.1.4.1.5504.4.3.2.3.1.9
        v52LinkRowStatus OBJECT-TYPE
            SYNTAX ZhoneRowStatus
            MAX-ACCESS read-create
            STATUS current
            DESCRIPTION
                "Used to control row creation and deletion.

                A row in this table is created using a single
                SNMP SET request with varbinds for:
                a) v52LinkRowStatus set to'CreateAndGo',
                b) all READ-CREATE object(s)

                If 'createAndGo' successfully created a new row,
                the RowStatus will be 'active'.  Subsequent to
                successful row creation, the RowStatus can be
                retrieved via an SNMP GET and the returned
                RowStatus value is active.  If the 'createAndGo'
                was unsuccessful an SNMP error will be returned
                and a subsequent GET on the non-existent row
                will also return an SNMP error of noSuchInstance.
                An SNMP SET with the RowStatus value of 'destroy'
                indicates that the agent should remove the row
                from service and then delete it.  "
            ::= { v52LinkEntry 9 }


--
-- Physical (timeslots)
--
-- Each 2,048 Mbit/s E1 interface utilizes 32 time-slots
-- as defined in G.703/G.704.  Time slot 0 is used for
-- frame alignment.  Time slot 16 of the first E1 link is
-- utilized by the V5 'control protocol'.
--
        -- 1.3.6.1.4.1.5504.4.3.2.4
        v52CChannelTable OBJECT-TYPE
            SYNTAX SEQUENCE OF V52CChannelEntry
            MAX-ACCESS not-accessible
            STATUS current
            DESCRIPTION
                "Communication Channel (C-channel).  C-paths (see
                v52CPathTable) are carried over C-channels (communications
                channels).  In V5, there are two types of C-channels,
                logical and physical.  Information about logical and
                physical C-channels is included in the provisioning
                data for V5.2 interfaces.  A C-path associated with a
                logical C-channel is protected.  A C-path associated with
                a physical C-channel is not protected.

                In V5.2 only, logical C-channels carry a group of one
                or more C-paths, excluding the C-paths for the protection
                protocol.  A logical C-channel may consist of the C-paths
                for the Control, Link Control, and BCC protocols.  Another
                logical C-channel may consist of the C-path for the PSTN
                protocol.  A third logical C-channel may consist of the
                C-paths for ISDN Ds-type data and ISDN p-type data. A V5.2
                interface may contain up to 44 logical C-channels and each
                logical C-channel on an interface is uniquely identified
                in V5.2 with a 16-bit logical C-channel identifier.

                The goal of the protection protocol is to protect the C-paths
                for the V5 Signaling protocols (ie, BCC, Control, etc)
                as well as the C-paths for ISDN D-channel data. However,
                the protection protocol is designed to protect logical
                C-channels, not C-paths.  Therefore, in order to protect
                a C-path, it must be associated with a logical C-channel.
                This association is made as part of the provisioning variant.

                A physical C-channel consists of a time slot (64kbit/s) on
                an E1 that carries a C-channel (C-channels are used to
                carry signaling traffic).  All physical C-channels are
                restricted to timeslots 16, 15, and 31 in accordance with
                the ETSI specification.

                If logical C-channels are in use, each logical C-channel
                is mapped to one and only one physical C-channel.  This
                restriction is mandated by the role of the protection
                protocol.  The protection protocol, which protects logical
                C-channels, can only protect a single logical C-channel
                per protection switch over.  This implies an implicit
                limitation of one logical C-channel per physical C-channel.

                For a V5.2 interface, the physical C-channels are identified
                by a logical link ID and a timeslot.  Each V5.2 interface can
                support a maximum of 48 physical C-channels (timeslots 16,
                15, and 31 on up to 16 E1 links; 3 * 16 = 48).

                Physical C-channels are not available for bearer connections.
                The physical C-channels are identified at provisioning
                time and when ISDN ports with D-channel signaling are
                added."
            ::= { zhoneV52 4 }


        -- 1.3.6.1.4.1.5504.4.3.2.4.1
        v52CChannelEntry OBJECT-TYPE
            SYNTAX V52CChannelEntry
            MAX-ACCESS not-accessible
            STATUS current
            DESCRIPTION
                "Communication Channel (C-Channel) Entry. Indexed by
                v52IgNameId, v52LinkIndex and v52CChannelTimeSlotIndex.
                Time slots are contained in the Link and in the event
                of the link going out of service, no allocation of
                free timeslots from that link is allowed."
            INDEX { v52IgNameId, v52LinkDsnLgId, v52LinkDs1ChannelNumber, v52CChannelTimeSlotIndex }
            ::= { v52CChannelTable 1 }


        V52CChannelEntry ::=
            SEQUENCE {
                v52CChannelTimeSlotIndex
                    Integer32,
                v52CChannelLogicalChannelId
                    Integer32,
                v52CChannelProtGp
                    INTEGER,
                v52CChannelRole
                    INTEGER,
                v52CChannelStatus
                    INTEGER,
                v52CChannelCurrentLogicalChannelId
                    Integer32,
                v52CChannelRowStatus
                    ZhoneRowStatus,
                v52CChannelStatusCause
                    INTEGER
             }

--
        -- 1.3.6.1.4.1.5504.4.3.2.4.1.1
        v52CChannelTimeSlotIndex OBJECT-TYPE
            SYNTAX Integer32 (15 | 16 | 31)
            MAX-ACCESS not-accessible
            STATUS current
            DESCRIPTION
                "Time Slot Index. A V5 interface contains 31 V5 time slots.
                Time slot 0 is not instantiated, as it is an intrinsic
                part of the 2048 kbit/s link used for framing.

                Valid values can only be 16, 15 and 31 according to the
                ETSI specification."
            ::= { v52CChannelEntry 1 }


--
        -- 1.3.6.1.4.1.5504.4.3.2.4.1.2
        v52CChannelLogicalChannelId OBJECT-TYPE
            SYNTAX Integer32 (0..65535)
            MAX-ACCESS read-create
            STATUS current
            DESCRIPTION
                "Logical C-Channels carry a group of one or more C-Paths,
                excluding the C-Paths used for Protection protocol. A
                V5.2 interface may contain up to 44 logical C-channels
                and each logical C-channel on an interface is uniquely
                identified in V5.2 with a 16 bit logical C-channel
                identifier. Physical C-channels that are provisioned as
                standby channels in a protection group do not have
                logical C-channel identifiers associated with them.

                The logical C-channel identifiers are provisioned, valid
                range is 0..65535."
            DEFVAL { 0 }
            ::= { v52CChannelEntry 2 }


--
        -- 1.3.6.1.4.1.5504.4.3.2.4.1.3
        v52CChannelProtGp OBJECT-TYPE
            SYNTAX INTEGER
                {
                none(1),
                group1(2),
                oneToOneGroup2(3),
                mToNGroup2(4)
                }
            MAX-ACCESS read-create
            STATUS current
            DESCRIPTION
                "C-Channel protection group.  Valid values are
                none, group1, oneToOneGroup2, and mToNgroup2.
                Default value is none.

                oneToOneGroup2 option is currently not supported.

                v52CChanelProtGp can only be modified when the
                v52IgAdminStatus is 'outOfService'."
            DEFVAL { none }
            ::= { v52CChannelEntry 3 }


--
        -- 1.3.6.1.4.1.5504.4.3.2.4.1.4
        v52CChannelRole OBJECT-TYPE
            SYNTAX INTEGER
                {
                active(1),
                standby(2),
                switchToStandby(3)
                }
            MAX-ACCESS read-create
            STATUS current
            DESCRIPTION
                "C-Channel role.   Valid values are:

                * active - the C-Channel is currently active mode.
                * standby - the C-Channel is currently in standby mode.
                * switchToStandby - This value can only be set when the
                  C-Channel is in active mode. When an active channel is
                  set to switchToStandby, one of the standby channels in
                  the same protection group will take over as the new
                  active channel. When this is completed, the channel
                  being switched will become a standby channel in its
                  protection group if it does not fail. If the channel
                  fails, then v52CChannelStatus will indicate a value
                  of failed. 'switchToStandby' is only supported for
                  group2 C-Channels."
            REFERENCE
                "AV5 Application Notes 2.1.4.1 Logical C-Channels"
            DEFVAL { active }
            ::= { v52CChannelEntry 4 }


--
        -- 1.3.6.1.4.1.5504.4.3.2.4.1.5
        v52CChannelStatus OBJECT-TYPE
            SYNTAX INTEGER
                {
                active(1),
                standby(2),
                failed(3)
                }
            MAX-ACCESS read-only
            STATUS current
            DESCRIPTION
                "C-Channel status.  Valid values are active, standby,
                and failed."
            ::= { v52CChannelEntry 5 }


--
        -- 1.3.6.1.4.1.5504.4.3.2.4.1.6
        v52CChannelCurrentLogicalChannelId OBJECT-TYPE
            SYNTAX Integer32 (0..65535)
            MAX-ACCESS read-only
            STATUS current
            DESCRIPTION
                "The value of this variable indicates the current logical
                C-Channel identifier of the physical C-Channel. This is
                useful when a physical C-Channel that was provisioned as
                an active channel fails - if the physical C-Channel was a
                member of a V5.2 protection group the logical C-Channel
                identifier will be assigned to a standby physical
                C-Channel.  This variable is only valid when read in
                conjunction with v52CChannel status as summarized in the
                following table:

                Physical   Channel  Current Logical
                Chan Role  Status   Channel Id
                -----------------------------------------------
                Active     Active   Valid   (prov channel Id)
                Active     Failed   Invalid
                Standby    Standby  Invalid
                Standby    Active   Valid
                Standby    Failed   Invalid"
            ::= { v52CChannelEntry 6 }


        -- 1.3.6.1.4.1.5504.4.3.2.4.1.7
        v52CChannelRowStatus OBJECT-TYPE
            SYNTAX ZhoneRowStatus
            MAX-ACCESS read-create
            STATUS current
            DESCRIPTION
                "Used to control row creation and deletion.

                A row in this table is created using a single
                SNMP SET request with varbinds for:
                a) v52CChannelRowStatus set to'CreateAndGo',
                b) all READ-CREATE object(s)

                If 'createAndGo' successfully created a new row,
                the RowStatus will be 'active'.  Subsequent to
                successful row creation, the RowStatus can be
                retrieved via an SNMP GET and the returned
                RowStatus value is active.  If the 'createAndGo'
                was unsuccessful an SNMP error will be returned
                and a subsequent GET on the non-existent row
                will also return an SNMP error of noSuchInstance.
                An SNMP SET with the RowStatus value of 'destroy'
                indicates that the agent should remove the row
                from service and then delete it.  "
            ::= { v52CChannelEntry 7 }


--
        -- 1.3.6.1.4.1.5504.4.3.2.4.1.8
        v52CChannelStatusCause OBJECT-TYPE
            SYNTAX INTEGER
                {
                other(1),
                switchOverRejected(2),
                switchOverError(3),
                switchOverResetSequenceNumberError(4),
                switchOverAborted(5),
                switchOverRejectedProvisioningError(6),
                switchOverResetSequence(7)
                }
            MAX-ACCESS read-only
            STATUS current
            DESCRIPTION
                "Cause for CChannelStatus. Valid values are

                * other,
                * switchOverRejected
                * switchOverError
                * switchOverResetSequenceNumberError
                * switchOverAborted
                * switchOverRejectedProvisioningError
                * switchOverResetSequence"
            ::= { v52CChannelEntry 8 }


        -- 1.3.6.1.4.1.5504.4.3.2.5
        v52CPathTable OBJECT-TYPE
            SYNTAX SEQUENCE OF V52CPathEntry
            MAX-ACCESS not-accessible
            STATUS current
            DESCRIPTION
                "C-paths consist of a layer 2 data link carrying an
                associated layer 3 signaling protocol.  Layer 3
                signaling is defined by the Control, Link Control,
                PSTN, BCC, and Protection protocols.  Therefore, a
                C-path can exist for the Control protocol, the Link
                Control protocol, the PSTN protocol, the BCC protocol,
                and the Protection protocol.  In addition, ISDN
                D-channel data is also carried over C-paths.  Separate
                C-paths exist for ISDN Ds, p, and f-type data.
                There can only be one of each control, link control, and
                BCC C-Paths whereas multiple PSTN and ISDN C-Paths may
                exist.

                A group of C-Paths are associated with a C-channel.
                The C-path for protection, however, is not carried in
                a C-channel."
            ::= { zhoneV52 5 }


        -- 1.3.6.1.4.1.5504.4.3.2.5.1
        v52CPathEntry OBJECT-TYPE
            SYNTAX V52CPathEntry
            MAX-ACCESS not-accessible
            STATUS current
            DESCRIPTION
                "Entry in the v52CPathTable."
            INDEX { v52IgNameId, v52CPathId }
            ::= { v52CPathTable 1 }


        V52CPathEntry ::=
            SEQUENCE {
                v52CPathId
                    Integer32,
                v52CPathType
                    INTEGER,
                v52CPathLogicalChannelId
                    Integer32,
                v52CPathRowStatus
                    ZhoneRowStatus,
                v52CPathOperStatus
                    INTEGER,
                v52CPathOperStatusCause
                    INTEGER
             }

--
        -- 1.3.6.1.4.1.5504.4.3.2.5.1.1
        v52CPathId OBJECT-TYPE
            SYNTAX Integer32 (1..48)
            MAX-ACCESS not-accessible
            STATUS current
            DESCRIPTION
                "8-bit C-Path identifier. Provisioned.  Valid
                range is 1..48."
            ::= { v52CPathEntry 1 }


--
        -- 1.3.6.1.4.1.5504.4.3.2.5.1.2
        v52CPathType OBJECT-TYPE
            SYNTAX INTEGER
                {
                unknown(1),
                pstn(2),
                ctrl(3),
                bcc(4),
                lctl(5),
                isdnDs(6),
                isdnF(7),
                isdnP(8)
                }
            MAX-ACCESS read-create
            STATUS current
            DESCRIPTION
                "C-path type can be unknown, pstn (PSTN), ctrl
                (Control protocol), bcc (Bearer Channel Connection
                protocol), lctl (Link Control protocol), and the
                following ISDN  path types: Ds-isdn, f-isdn, and
                p-isdn.  Default is unknown."
            DEFVAL { unknown }
            ::= { v52CPathEntry 2 }


--
        -- 1.3.6.1.4.1.5504.4.3.2.5.1.3
        v52CPathLogicalChannelId OBJECT-TYPE
            SYNTAX Integer32 (0..65535)
            MAX-ACCESS read-create
            STATUS current
            DESCRIPTION
                "C-Channel logical Channel ID assigned to this
                C-Path. Provisioned. Valid range is 0..65535."
            DEFVAL { 0 }
            ::= { v52CPathEntry 3 }


        -- 1.3.6.1.4.1.5504.4.3.2.5.1.4
        v52CPathRowStatus OBJECT-TYPE
            SYNTAX ZhoneRowStatus
            MAX-ACCESS read-create
            STATUS current
            DESCRIPTION
                "Used to control row creation and deletion.

                A row in this table is created using a single
                SNMP SET request with varbinds for:
                a) v52CPathRowStatus set to'CreateAndGo',
                b) all READ-CREATE object(s)

                If 'createAndGo' successfully created a new row,
                the RowStatus will be 'active'.  Subsequent to
                successful row creation, the RowStatus can be
                retrieved via an SNMP GET and the returned
                RowStatus value is active.  If the 'createAndGo'
                was unsuccessful an SNMP error will be returned
                and a subsequent GET on the non-existent row
                will also return an SNMP error of noSuchInstance.
                An SNMP SET with the RowStatus value of 'destroy'
                indicates that the agent should remove the row
                from service and then delete it.

                A CPath object can only be deleted when
                v52IgAdminStatus is 'outOfService'."
            ::= { v52CPathEntry 4 }


--
        -- 1.3.6.1.4.1.5504.4.3.2.5.1.5
        v52CPathOperStatus OBJECT-TYPE
            SYNTAX INTEGER
                {
                up(1),
                down(2)
                }
            MAX-ACCESS read-only
            STATUS current
            DESCRIPTION
                "The operational status of this CPath. Valid values are
                'up' and 'down'."
            ::= { v52CPathEntry 5 }


--
        -- 1.3.6.1.4.1.5504.4.3.2.5.1.6
        v52CPathOperStatusCause OBJECT-TYPE
            SYNTAX INTEGER
                {
                establishConfirmationReceived(1),
                establishIndicationReceived(2),
                releaseIndicationReceived(3)
                }
            MAX-ACCESS read-only
            STATUS current
            DESCRIPTION
                "Cause for CPathOperStatus.  Valid values are:

                * establishConfirmationReceived - the data link
                  has been successfully established upon a local
                  request.

                * establishIndicationReceived - the data link
                  has been successfully established upon its
                  peer request.

                * releaseIndicationReceived - the data link has
                  failed because of either Layer 1 failure or
                  no frame exchange with the peer was possible
                  within the given time frame (after T203 timer
                  expiry, followed by T200 timer expiry N200
                 times)."
            ::= { v52CPathEntry 6 }


        -- 1.3.6.1.4.1.5504.4.3.2.6
        v52UserPortTable OBJECT-TYPE
            SYNTAX SEQUENCE OF V52UserPortEntry
            MAX-ACCESS not-accessible
            STATUS current
            DESCRIPTION
                "The User Port Table holds information regarding the
                PSTN and ISDN user ports.  Information regarding the
                provisioning and availability status of the port is
                maintained.  If a user port is busy, information
                regarding the allocation status of Bearer Channels
                to the user port is maintained and tracked by the
                configuration.  If the port is put out of service
                for maintenance, the port is marked unavailable."
            ::= { zhoneV52 6 }


        -- 1.3.6.1.4.1.5504.4.3.2.6.1
        v52UserPortEntry OBJECT-TYPE
            SYNTAX V52UserPortEntry
            MAX-ACCESS not-accessible
            STATUS current
            DESCRIPTION
                "User Port Entry."
            INDEX { v52IgNameId, v52UserPortAddress, v52UserPortType }
            ::= { v52UserPortTable 1 }


        V52UserPortEntry ::=
            SEQUENCE {
                v52UserPortAddress
                    Integer32,
                v52UserPortType
                    INTEGER,
                v52UserPortAdminStatus
                    INTEGER,
                v52UserPortBlock
                    INTEGER,
                v52UserPortBlockStatus
                    INTEGER,
                v52UserPortRegOrLeaseUser
                    INTEGER,
                v52UserPortIsdnDsCPathId
                    Integer32,
                v52UserPortIsdnPCPathId
                    Integer32,
                v52UserPortIsdnFCPathId
                    Integer32,
                v52UserPortRowStatus
                    ZhoneRowStatus,
                v52UserPortOperStatus
                    INTEGER
             }

        -- 1.3.6.1.4.1.5504.4.3.2.6.1.1
        v52UserPortAddress OBJECT-TYPE
            SYNTAX Integer32 (0..32767)
            MAX-ACCESS not-accessible
            STATUS current
            DESCRIPTION
                "User Port Address. If UserPortType is PSTN, valid
                range is 0..32767. If UserPortType is ISDN, valid
                range is 0..8175. Maximum value is 32767.

                The actual address range is further limited by the
                following rules:

                PSTN:
                v52IgPstnLayer3StartAddress <= v52UserPortAddress <
                v52IgPstnLayer3StartAddress + maximum_PSTN_users_allowed_per_IG

                ISDN:
                v52IgIsdnEnvFuncStartAddress <= v52UserPortAddress <
                v52IgIsdnEnvFuncStartAddress + maximum_ISDN_users_allowed_per_IG

                Further, the total number of user ports is restricted by
                the following rule:

                Total_Pstn_User_Ports + 2*Total_Isdn_Bri_User_Ports <=
                Total_User_Ports_Supported_Per_Platform.

                ISDN PRI is not supported by the current release.

                For the current 8 E1 release of Sechtor 100:
                --------------------------------------------
                maximum_PSTN_users_allowed_per_IG is 1920.
                maximum_ISDN_users_allowed_per_IG is 960.
                maximum users supported on the entire Sechtor 100 is 4800.

                The maximum number of PSTN and ISDN user ports supported
                for the 16 E1 release will be updated in the near future."
            ::= { v52UserPortEntry 1 }


        -- 1.3.6.1.4.1.5504.4.3.2.6.1.2
        v52UserPortType OBJECT-TYPE
            SYNTAX INTEGER
                {
                unknown(1),
                pstn(2),
                isdnBa(3),
                isdnPra(4)
                }
            MAX-ACCESS not-accessible
            STATUS current
            DESCRIPTION
                "User Port type.  Valid values are unknown, pstn,
                isdnBa, isdnPra."
            ::= { v52UserPortEntry 2 }


--
        -- 1.3.6.1.4.1.5504.4.3.2.6.1.3
        v52UserPortAdminStatus OBJECT-TYPE
            SYNTAX INTEGER
                {
                inService(1),
                outOfService(2)
                }
            MAX-ACCESS read-create
            STATUS current
            DESCRIPTION
                "UserPort Admin Status.  Valid values are inService
                and outOfService.  Default is outOfService."
            DEFVAL { outOfService }
            ::= { v52UserPortEntry 3 }


--
        -- 1.3.6.1.4.1.5504.4.3.2.6.1.4
        v52UserPortBlock OBJECT-TYPE
            SYNTAX INTEGER
                {
                blocked(1),
                shuttingDown(2),
                unblocked(3),
                blockedNotSuitableForGroupUnblocking(4)
                }
            MAX-ACCESS read-create
            STATUS current
            DESCRIPTION
                "The Q3 interface of the access network can request
                that a port be blocked for non-urgent configuration or
                reconfiguration. If the port is routed through a V5
                interface to a local exchange, then this request can
                only be granted by the local exchange via the V5
                interface. This is intended to avoid interference with
                calls in progress, or calls being set up or cleared down.

                The Q3 interface on the access network can request
                that a port be blocked for urgent configuration or
                reconfiguration. If the port is routed through a V5
                interface to a local exchange, the other side of the
                interface shall be informed of this blocking via the V5
                interface.

                Valid values are:

                * 'blocked' - the user port can be unblocked by both
                  accelerated port alignment (i.e. group unblocking)
                  and sequential port alignment.

                * 'shuttingDown' - same as 'blocked' except active
                  calls will not be blocked until the calls are
                  completed.

                * 'unblocked' - port will be unblocked regardless
                  of its previous port block state.

                * 'blockedNotSuitableForGroupUnblocking' - the user
                  port cannot be unblocked by accelerated port
                  alignment unblocking but can be unblocked by
                  sequential unblocking.

                Default value is blocked."
            DEFVAL { blocked }
            ::= { v52UserPortEntry 4 }


--
        -- 1.3.6.1.4.1.5504.4.3.2.6.1.5
        v52UserPortBlockStatus OBJECT-TYPE
            SYNTAX INTEGER
                {
                unblocked(1),
                localBlocked(2),
                remoteBlocked(3),
                bothBlocked(4)
                }
            MAX-ACCESS read-only
            STATUS current
            DESCRIPTION
                "UserPortBlock operational status.
                Valid values are:

                * localBlocked - local is blocked
                * remoteBlocked - remote is blocked
                * bothBlocked - both local and remote are blocked
                * unblocked - both local and remote are unblocked"
            ::= { v52UserPortEntry 5 }


--
        -- 1.3.6.1.4.1.5504.4.3.2.6.1.6
        v52UserPortRegOrLeaseUser OBJECT-TYPE
            SYNTAX INTEGER
                {
                regular(1),
                permanentLease(2),
                semiPermanentLease(3)
                }
            MAX-ACCESS read-create
            STATUS current
            DESCRIPTION
                "User is a regular, permanent lease, or semi-permanent
                leaseuser.  Valid values are regular, permanentLease,
                semiPermanentLease.  Default is regular."
            DEFVAL { regular }
            ::= { v52UserPortEntry 6 }


--
        -- 1.3.6.1.4.1.5504.4.3.2.6.1.7
        v52UserPortIsdnDsCPathId OBJECT-TYPE
            SYNTAX Integer32 (0..48)
            MAX-ACCESS read-create
            STATUS current
            DESCRIPTION
                "An ISDN user port can carry more than one type of the
                Ds-type, p-type and f-type data. When this user port
                is configured to carry Ds-type data, the value of
                this variable should be configured to be the
                value of the v52CPathID for the isdnDs CPath carrying
                the data.

                A value of 0 indicates the user port is not configured
                to carry Ds-type data."
            DEFVAL { 0 }
            ::= { v52UserPortEntry 7 }


        -- 1.3.6.1.4.1.5504.4.3.2.6.1.8
        v52UserPortIsdnPCPathId OBJECT-TYPE
            SYNTAX Integer32 (0..48)
            MAX-ACCESS read-create
            STATUS current
            DESCRIPTION
                "An ISDN user port can carry more than one type of the
                Ds-type, p-type and f-type data. When this user port
                is configured to carry p-type data, the value of
                this variable should be configured to be the
                value of the v52CPathID for the isdnP CPath carrying
                the data.

                A value of 0 indicates the user port is not configured
                to carry p-type data."
            DEFVAL { 0 }
            ::= { v52UserPortEntry 8 }


        -- 1.3.6.1.4.1.5504.4.3.2.6.1.9
        v52UserPortIsdnFCPathId OBJECT-TYPE
            SYNTAX Integer32 (0..48)
            MAX-ACCESS read-create
            STATUS current
            DESCRIPTION
                "An ISDN user port can carry more than one type of the
                Ds-type, p-type and f-type data. When this user port
                is configured to carry f-type data, the value of
                this variable should be configured to be the
                value of the v52CPathID for the isdnF CPath carrying
                the data.

                A value of 0 indicates the user port is not configured
                to carry f-type data."
            DEFVAL { 0 }
            ::= { v52UserPortEntry 9 }


        -- 1.3.6.1.4.1.5504.4.3.2.6.1.10
        v52UserPortRowStatus OBJECT-TYPE
            SYNTAX ZhoneRowStatus
            MAX-ACCESS read-create
            STATUS current
            DESCRIPTION
                "Used to control row creation and deletion.

                A row in this table is created using a single
                SNMP SET request with varbinds for:
                a) v52UserPortRowStatus set to'CreateAndGo',
                b) the following READ-CREATE object(s):
                   * v52UserPortAddress

                If 'createAndGo' successfully created a new row,
                the RowStatus will be 'active'.  Subsequent to
                successful row creation, the RowStatus can be
                retrieved via an SNMP GET and the returned
                RowStatus value is active.  If the 'createAndGo'
                was unsuccessful an SNMP error will be returned
                and a subsequent GET on the non-existent row
                will also return an SNMP error of noSuchInstance.
                An SNMP SET with the RowStatus value of 'destroy'
                indicates that the agent should remove the row
                from service and then delete it. "
            ::= { v52UserPortEntry 10 }


--
        -- 1.3.6.1.4.1.5504.4.3.2.6.1.11
        v52UserPortOperStatus OBJECT-TYPE
            SYNTAX INTEGER
                {
                inService(1),
                manualOos(2),
                oos(3)
                }
            MAX-ACCESS read-only
            STATUS current
            DESCRIPTION
                "User port operational status. Valid values are inService,
                manualOos and Oos.

                * 'inService' - the user port is ready to carry calls.

                * 'manualOos' - the user port has been manually put into OOS
                  state.

                * 'oos' - the user port is in out of service state even
                  though the port admin state is set to in service."
            ::= { v52UserPortEntry 11 }


        -- 1.3.6.1.4.1.5504.4.3.2.7
        v52StatsCurrentTable OBJECT-TYPE
            SYNTAX SEQUENCE OF V52StatsCurrentEntry
            MAX-ACCESS not-accessible
            STATUS current
            DESCRIPTION
                "The V5.2 Interface Group Statistics Current Table.

                The V5.2 Interface Group Statistics current
                table contains various statistics being collected
                for the current 15 minute interval.

                The maximum number of entries is identical to that
                of the Interface Group Table. The interfaceGroupTable
                is the base table for this augmented table."
            ::= { zhoneV52 7 }


        -- 1.3.6.1.4.1.5504.4.3.2.7.1
        v52StatsCurrentEntry OBJECT-TYPE
            SYNTAX V52StatsCurrentEntry
            MAX-ACCESS not-accessible
            STATUS current
            DESCRIPTION
                "An entry in the v52StatsCurrentTable which
                AUGMENTS the base table v52InterfaceGroupTable.
                There is a 1-to-1 correspondence between rows
                in interfaceGroupTable and rows in this table.
                When a row is created in the base table
                interfaceGroupTable, the corresponding row in
                the augmenting table igStatsCurrentTable must
                also be simultaneously created.  A row in this
                table is created by setting the value of
                igRowStatus to 'CreateAndGo' and setting the
                appropriate values for the columns.  Likewise,
                when a row expires by setting the value of
                igRowStatus to 'destroy' in the interfaceGroupTable
                base table, the same row also expires in this
                augmenting table."
            AUGMENTS { v52InterfaceGroupEntry }
            ::= { v52StatsCurrentTable 1 }


        V52StatsCurrentEntry ::=
            SEQUENCE {
                v52IfCurrentPstnOutboundCalls
                    PerfCurrentCount,
                v52IfCurrentPstnInboundCalls
                    PerfCurrentCount,
                v52IfCurrentCallsBlocked
                    PerfCurrentCount,
                v52IfCurrentV52ProtocolErrors
                    PerfCurrentCount,
                v52IfCurrentLapdSent
                    PerfCurrentCount,
                v52IfCurrentLapdRcvd
                    PerfCurrentCount,
                v52IfCurrentLapdRcvdErrs
                    PerfCurrentCount,
                v52IfCurrentIsdnCalls
                    PerfCurrentCount
             }

--
        -- 1.3.6.1.4.1.5504.4.3.2.7.1.1
        v52IfCurrentPstnOutboundCalls OBJECT-TYPE
            SYNTAX PerfCurrentCount
            MAX-ACCESS read-only
            STATUS current
            DESCRIPTION
                "The number of PSTN outbound calls completed."
            ::= { v52StatsCurrentEntry 1 }


--
        -- 1.3.6.1.4.1.5504.4.3.2.7.1.2
        v52IfCurrentPstnInboundCalls OBJECT-TYPE
            SYNTAX PerfCurrentCount
            MAX-ACCESS read-only
            STATUS current
            DESCRIPTION
                "The number of PSTN inbound calls completed."
            ::= { v52StatsCurrentEntry 2 }


--
        -- 1.3.6.1.4.1.5504.4.3.2.7.1.3
        v52IfCurrentCallsBlocked OBJECT-TYPE
            SYNTAX PerfCurrentCount
            MAX-ACCESS read-only
            STATUS current
            DESCRIPTION
                "The number of calls that were blocked due to no
                available time-slot."
            ::= { v52StatsCurrentEntry 3 }


--
        -- 1.3.6.1.4.1.5504.4.3.2.7.1.4
        v52IfCurrentV52ProtocolErrors OBJECT-TYPE
            SYNTAX PerfCurrentCount
            MAX-ACCESS read-only
            STATUS current
            DESCRIPTION
                "The number of V5.2 Protocol errors."
            ::= { v52StatsCurrentEntry 4 }


--
        -- 1.3.6.1.4.1.5504.4.3.2.7.1.5
        v52IfCurrentLapdSent OBJECT-TYPE
            SYNTAX PerfCurrentCount
            MAX-ACCESS read-only
            STATUS current
            DESCRIPTION
                "The number of LAPD frames sent on all C-Paths
                for this interface group."
            ::= { v52StatsCurrentEntry 5 }


--
        -- 1.3.6.1.4.1.5504.4.3.2.7.1.6
        v52IfCurrentLapdRcvd OBJECT-TYPE
            SYNTAX PerfCurrentCount
            MAX-ACCESS read-only
            STATUS current
            DESCRIPTION
                "The number LAPD frames received on all C-Paths
                for this interface group."
            ::= { v52StatsCurrentEntry 6 }


--
        -- 1.3.6.1.4.1.5504.4.3.2.7.1.7
        v52IfCurrentLapdRcvdErrs OBJECT-TYPE
            SYNTAX PerfCurrentCount
            MAX-ACCESS read-only
            STATUS current
            DESCRIPTION
                "The number LAPD frames received in error on all
                C-Paths for this interface group."
            ::= { v52StatsCurrentEntry 7 }


--
        -- 1.3.6.1.4.1.5504.4.3.2.7.1.8
        v52IfCurrentIsdnCalls OBJECT-TYPE
            SYNTAX PerfCurrentCount
            MAX-ACCESS read-only
            STATUS current
            DESCRIPTION
                "The number of ISDN calls completed."
            ::= { v52StatsCurrentEntry 8 }


        -- 1.3.6.1.4.1.5504.4.3.2.8
        v52StatsIntervalTable OBJECT-TYPE
            SYNTAX SEQUENCE OF V52StatsIntervalEntry
            MAX-ACCESS not-accessible
            STATUS current
            DESCRIPTION
                "V5.2 Interface Group Statistics Interval Table.

                The V5.2 Interface Group Statistics Interval
                Table contains various statistics collected by
                each Interface Group over the previous 6. 12.
                18, or 24 hours of operation.  The past 6, 12,
                18, or 24 hours are broken into 24, 48, 72, or
                96 completed 15 minute intervals.  Each row in
                this table represents one such interval
                (identified by igIntervalNumber) for one
                specific instance (identified by igIntervalIndex)."
            ::= { zhoneV52 8 }


        -- 1.3.6.1.4.1.5504.4.3.2.8.1
        v52StatsIntervalEntry OBJECT-TYPE
            SYNTAX V52StatsIntervalEntry
            MAX-ACCESS not-accessible
            STATUS current
            DESCRIPTION
                "An entry in the igStatsIntervalTable.  Indexed by
                (igNameId, igIntervalNumber)."
            INDEX { v52IgNameId, v52IfIntervalNumber }
            ::= { v52StatsIntervalTable 1 }


        V52StatsIntervalEntry ::=
            SEQUENCE {
                v52IfIntervalNumber
                    Integer32,
                v52IfIntervalPstnOutboundCalls
                    PerfCurrentCount,
                v52IfIntervalPstnInboundCalls
                    PerfCurrentCount,
                v52IfIntervalCallsBlocked
                    PerfCurrentCount,
                v52IfIntervalV52ProtocolErrors
                    PerfCurrentCount,
                v52IfIntervalLapdSent
                    PerfCurrentCount,
                v52IfIntervalLapdRcvd
                    PerfCurrentCount,
                v52IfIntervalLapdRcvdErrs
                    PerfCurrentCount,
                v52IfIntervalIsdnCalls
                    PerfCurrentCount
             }

        -- 1.3.6.1.4.1.5504.4.3.2.8.1.1
        v52IfIntervalNumber OBJECT-TYPE
            SYNTAX Integer32 (1..96)
            MAX-ACCESS not-accessible
            STATUS current
            DESCRIPTION
                "A number between 1 and 96, where 1 is the most
                recently completed 15 minute interval and 96 is
                the 15 minutes interval completed 23 hours and 45
                minutes prior to interval 1."
            ::= { v52StatsIntervalEntry 1 }


--
        -- 1.3.6.1.4.1.5504.4.3.2.8.1.2
        v52IfIntervalPstnOutboundCalls OBJECT-TYPE
            SYNTAX PerfCurrentCount
            MAX-ACCESS read-only
            STATUS current
            DESCRIPTION
                "The number of PSTN outbound calls completed."
            ::= { v52StatsIntervalEntry 2 }


--
        -- 1.3.6.1.4.1.5504.4.3.2.8.1.3
        v52IfIntervalPstnInboundCalls OBJECT-TYPE
            SYNTAX PerfCurrentCount
            MAX-ACCESS read-only
            STATUS current
            DESCRIPTION
                "The number of PSTN inbound calls completed."
            ::= { v52StatsIntervalEntry 3 }


--
        -- 1.3.6.1.4.1.5504.4.3.2.8.1.4
        v52IfIntervalCallsBlocked OBJECT-TYPE
            SYNTAX PerfCurrentCount
            MAX-ACCESS read-only
            STATUS current
            DESCRIPTION
                "The number of calls that were blocked due to no
                available time-slot."
            ::= { v52StatsIntervalEntry 4 }


--
        -- 1.3.6.1.4.1.5504.4.3.2.8.1.5
        v52IfIntervalV52ProtocolErrors OBJECT-TYPE
            SYNTAX PerfCurrentCount
            MAX-ACCESS read-only
            STATUS current
            DESCRIPTION
                "The number of V5.2 Protocol errors."
            ::= { v52StatsIntervalEntry 5 }


--
        -- 1.3.6.1.4.1.5504.4.3.2.8.1.6
        v52IfIntervalLapdSent OBJECT-TYPE
            SYNTAX PerfCurrentCount
            MAX-ACCESS read-only
            STATUS current
            DESCRIPTION
                "The number of LAPD frames sent on all C-Paths
                for this interface group."
            ::= { v52StatsIntervalEntry 6 }


--
        -- 1.3.6.1.4.1.5504.4.3.2.8.1.7
        v52IfIntervalLapdRcvd OBJECT-TYPE
            SYNTAX PerfCurrentCount
            MAX-ACCESS read-only
            STATUS current
            DESCRIPTION
                "The number LAPD frames received on all C-Paths
                for this interface group."
            ::= { v52StatsIntervalEntry 7 }


--
        -- 1.3.6.1.4.1.5504.4.3.2.8.1.8
        v52IfIntervalLapdRcvdErrs OBJECT-TYPE
            SYNTAX PerfCurrentCount
            MAX-ACCESS read-only
            STATUS current
            DESCRIPTION
                "The number LAPD frames received in error on all
                C-Paths for this interface group."
            ::= { v52StatsIntervalEntry 8 }


--
        -- 1.3.6.1.4.1.5504.4.3.2.8.1.9
        v52IfIntervalIsdnCalls OBJECT-TYPE
            SYNTAX PerfCurrentCount
            MAX-ACCESS read-only
            STATUS current
            DESCRIPTION
                "The number of ISDN calls completed."
            ::= { v52StatsIntervalEntry 9 }


        -- 1.3.6.1.4.1.5504.4.3.2.9
        v52StatsTotalTable OBJECT-TYPE
            SYNTAX SEQUENCE OF V52StatsTotalEntry
            MAX-ACCESS not-accessible
            STATUS current
            DESCRIPTION
                "V5.2 Interface Group Statistics Total Table.

                The V5.2 Interface Group Statistics Total
                Table contains the cumulative sum of the
                various statistics for the 24 hour period
                preceding the current interval.

                The maximum number of entries is identical to that
                of the Interface Group Table. The v52InterfaceGroupTable
                is the base table for this augmented table."
            ::= { zhoneV52 9 }


        -- 1.3.6.1.4.1.5504.4.3.2.9.1
        v52StatsTotalEntry OBJECT-TYPE
            SYNTAX V52StatsTotalEntry
            MAX-ACCESS not-accessible
            STATUS current
            DESCRIPTION
                "An entry in the v52StatsTotalTable which
                AUGMENTS the base table interfaceGroupTable.
                There is a 1-to-1 correspondence between rows
                in v52InterfaceGroupTable and rows in this table.
                When a row is created in the base table
                v52InterfaceGroupTable, the corresponding row in
                the augmenting table v52StatsTotalTable must
                also be simultaneously created.  A row in this
                table is created by setting the value of
                v52IgRowStatus to 'CreateAndGo' and setting the
                appropriate values for the columns.  Likewise,
                when a row expires by setting the value of
                v52IgRowStatus to 'destroy' in the v52InterfaceGroupTable
                base table, the same row also expires in this
                augmenting table."
            AUGMENTS { v52InterfaceGroupEntry }
            ::= { v52StatsTotalTable 1 }


        V52StatsTotalEntry ::=
            SEQUENCE {
                v52IfTotalPstnOutboundCalls
                    PerfCurrentCount,
                v52IfTotalPstnInboundCalls
                    PerfCurrentCount,
                v52IfTotalCallsBlocked
                    PerfCurrentCount,
                v52IfTotalV52ProtocolErrors
                    PerfCurrentCount,
                v52ifTotalLapdSent
                    PerfCurrentCount,
                v52IfTotalLapdRcvd
                    PerfCurrentCount,
                v52IfTotalLapdRcvdErrs
                    PerfCurrentCount,
                v52IfTotalIsdnCalls
                    PerfCurrentCount
             }

--
        -- 1.3.6.1.4.1.5504.4.3.2.9.1.1
        v52IfTotalPstnOutboundCalls OBJECT-TYPE
            SYNTAX PerfCurrentCount
            MAX-ACCESS read-only
            STATUS current
            DESCRIPTION
                "The number of PSTN outbound calls completed."
            ::= { v52StatsTotalEntry 1 }


--
        -- 1.3.6.1.4.1.5504.4.3.2.9.1.2
        v52IfTotalPstnInboundCalls OBJECT-TYPE
            SYNTAX PerfCurrentCount
            MAX-ACCESS read-only
            STATUS current
            DESCRIPTION
                "The number of PSTN inbound calls completed."
            ::= { v52StatsTotalEntry 2 }


--
        -- 1.3.6.1.4.1.5504.4.3.2.9.1.3
        v52IfTotalCallsBlocked OBJECT-TYPE
            SYNTAX PerfCurrentCount
            MAX-ACCESS read-only
            STATUS current
            DESCRIPTION
                "The number of calls that were blocked due to no
                available time-slot."
            ::= { v52StatsTotalEntry 3 }


--
        -- 1.3.6.1.4.1.5504.4.3.2.9.1.4
        v52IfTotalV52ProtocolErrors OBJECT-TYPE
            SYNTAX PerfCurrentCount
            MAX-ACCESS read-only
            STATUS current
            DESCRIPTION
                "The number of V5.2 Protocol errors."
            ::= { v52StatsTotalEntry 4 }


--
        -- 1.3.6.1.4.1.5504.4.3.2.9.1.5
        v52ifTotalLapdSent OBJECT-TYPE
            SYNTAX PerfCurrentCount
            MAX-ACCESS read-only
            STATUS current
            DESCRIPTION
                "The number of LAPD frames sent on all C-Paths
                for this interface group."
            ::= { v52StatsTotalEntry 5 }


--
        -- 1.3.6.1.4.1.5504.4.3.2.9.1.6
        v52IfTotalLapdRcvd OBJECT-TYPE
            SYNTAX PerfCurrentCount
            MAX-ACCESS read-only
            STATUS current
            DESCRIPTION
                "The number LAPD frames received on all C-Paths
                for this interface group."
            ::= { v52StatsTotalEntry 6 }


--
        -- 1.3.6.1.4.1.5504.4.3.2.9.1.7
        v52IfTotalLapdRcvdErrs OBJECT-TYPE
            SYNTAX PerfCurrentCount
            MAX-ACCESS read-only
            STATUS current
            DESCRIPTION
                "The number LAPD frames received in error on all
                C-Paths for this interface group."
            ::= { v52StatsTotalEntry 7 }


--
        -- 1.3.6.1.4.1.5504.4.3.2.9.1.8
        v52IfTotalIsdnCalls OBJECT-TYPE
            SYNTAX PerfCurrentCount
            MAX-ACCESS read-only
            STATUS current
            DESCRIPTION
                "The number of ISDN calls completed."
            ::= { v52StatsTotalEntry 8 }


        -- 1.3.6.1.4.1.5504.4.3.2.10
        v52Traps OBJECT-IDENTITY
            STATUS current
            DESCRIPTION
                "All the Zhone trap notifications for V5.2 managed objectes
                will be defined under v52Traps."
            ::= { zhoneV52 10 }


        -- 1.3.6.1.4.1.5504.4.3.2.10.0
        v52TrapsPrefix OBJECT-IDENTITY
            STATUS current
            DESCRIPTION
                "This is the 0 prefix which is required for all v52 traps
                defined in SNMPv2."
            ::= { v52Traps 0 }


        -- 1.3.6.1.4.1.5504.4.3.2.10.0.1
        v52IgProvVariantRequestNotification NOTIFICATION-TYPE
            OBJECTS { v52IgLocalInterfaceId, v52IgRemoteInterfaceId, v52IgLocalProvVariant, v52IgRemoteProvVariant, v52IgProvVariantRequest,
                v52IgProvVariantRequestStatus }
            STATUS current
            DESCRIPTION
                "This is the notification response for a SNMP set on
                v52IgProvVariantRequest.

                This notification is generated only when request is
                initiatated from the AN side. When the AN responds
                to LE's request, the AN just updates
                v52IgRemoteInterfaceId and v52IgRemoteProvVariant."
            ::= { v52TrapsPrefix 1 }


        -- 1.3.6.1.4.1.5504.4.3.2.10.0.2
        v52IgPortAlignmentNotification NOTIFICATION-TYPE
            OBJECTS { v52IgPortAlignmentRequest, v52IgPortAlignmentStatus }
            STATUS current
            DESCRIPTION
                "This is the notification response for a SNMP set on
                v52IgPortAlignmentRequest.

                The v52IgPortAlignmentRequest object indicates the type of
                request initiated by the operator. When the request is
                initiated by LE, v52IgPortAlignmentRequest has a value of
                'noRequest'."
            ::= { v52TrapsPrefix 2 }


        -- 1.3.6.1.4.1.5504.4.3.2.10.0.3
        v52LinkCheckIdNotification NOTIFICATION-TYPE
            OBJECTS { v52LinkCheckId, v52LinkCheckIdStatus }
            STATUS current
            DESCRIPTION
                "This is the notification response for a SNMP set on
                v52LinkCheckId.

                When Check Link ID is initiated by AN, v52LinkCheckId
                has a value of 'activated'. When Check Link ID is
                triggered by LE, v52LinkCheckId has a value of
                'notActivated'."
            ::= { v52TrapsPrefix 3 }


        -- 1.3.6.1.4.1.5504.4.3.2.10.0.4
        v52LinkBlockNotification NOTIFICATION-TYPE
            OBJECTS { v52LinkBlock, v52LinkBlockStatus }
            STATUS current
            DESCRIPTION
                "This is the notification response for a SNMP set on
                v52LinkBlock."
            ::= { v52TrapsPrefix 4 }


        -- 1.3.6.1.4.1.5504.4.3.2.10.0.5
        v52IgOperStatusChange NOTIFICATION-TYPE
            OBJECTS { v52IgAdminStatus, v52IgOperationalStatus, v52IgOperStatusCause }
            STATUS current
            DESCRIPTION
                "A v52IgOperStatusChange notification is sent out whenever
                the value of v52IgOperationalStatus changes."
            ::= { v52TrapsPrefix 5 }


        -- 1.3.6.1.4.1.5504.4.3.2.10.0.6
        v52CChannelStatusChange NOTIFICATION-TYPE
            OBJECTS { v52CChannelRole, v52CChannelStatus, v52CChannelStatusCause }
            STATUS current
            DESCRIPTION
                "A v52CChannelStatusChange notification is sent out whenever
                the value of v52ChannelStatus changes."
            ::= { v52TrapsPrefix 6 }


        -- 1.3.6.1.4.1.5504.4.3.2.10.0.7
        v52CPathOperStatusChange NOTIFICATION-TYPE
            OBJECTS { v52CPathOperStatus, v52CPathOperStatusCause }
            STATUS current
            DESCRIPTION
                "A v52CPathOperStatusChange notification is sent out whenever
                the value of v52CPathOperStatus changes.

                This notificatoin will only be generated for pstn, ctrl, bcc
                and lctl CPath's."
            ::= { v52TrapsPrefix 7 }


        -- 1.3.6.1.4.1.5504.4.3.2.10.0.8
        v52ProtectionCPathOperStatusChange NOTIFICATION-TYPE
            OBJECTS { v52ProtectionCPathOperStatus, v52ProtectionCPathOperStatusCause }
            STATUS current
            DESCRIPTION
                "A v52ProtectionCPathOperStatusChange notification is
                sent out whenever the value of v52ProtectionCPathOperStatus
                changes.

                The protection C-Path is identified by its igNameId and
                C-Path id in the instance OID's in the OBJECTS list."
            ::= { v52TrapsPrefix 8 }


        -- 1.3.6.1.4.1.5504.4.3.2.11
        v52IgExtensionTable OBJECT-TYPE
            SYNTAX SEQUENCE OF V52IgExtensionEntry
            MAX-ACCESS not-accessible
            STATUS current
            DESCRIPTION
                "This is the extension of the v52InterfaceGroupTable for
                extra configuration and monitoring variables for the
                V5.2 interface group."
            ::= { zhoneV52 11 }


        -- 1.3.6.1.4.1.5504.4.3.2.11.1
        v52IgExtensionEntry OBJECT-TYPE
            SYNTAX V52IgExtensionEntry
            MAX-ACCESS not-accessible
            STATUS current
            DESCRIPTION
                "An entry in the v52IgExtensionTable.

                v52IgExtensionEntry is augmented to v52InterfaceGroupEntry.
                Whenever a row is created or destroyed for the
                v52InterfaceGroupEntry, the same row should also be
                created or destroyed for the v52IgExtensionEntry. "
            AUGMENTS { v52InterfaceGroupEntry }
            ::= { v52IgExtensionTable 1 }


        V52IgExtensionEntry ::=
            SEQUENCE {
                v52IgStartupCheckLinkId
                    TruthValue,
                v52IgStartupUnblockUserPorts
                    TruthValue,
                v52IgLinkOutOfServiceTimer
                    Integer32,
                v52IgLinkInServiceTimer
                    Integer32
             }

--
        -- 1.3.6.1.4.1.5504.4.3.2.11.1.1
        v52IgStartupCheckLinkId OBJECT-TYPE
            SYNTAX TruthValue
            MAX-ACCESS read-create
            STATUS current
            DESCRIPTION
                "This variable indicates whether or not Link ID check will
                be performed when a V5.2 interface is starting up.

                The default value is 'false'."
            DEFVAL { false }
            ::= { v52IgExtensionEntry 1 }


--
        -- 1.3.6.1.4.1.5504.4.3.2.11.1.2
        v52IgStartupUnblockUserPorts OBJECT-TYPE
            SYNTAX TruthValue
            MAX-ACCESS read-create
            STATUS current
            DESCRIPTION
                "This variable indicates whether or not user ports will
                be unblocked when a V5.2 interface is starting up.

                The default value is 'false'."
            DEFVAL { false }
            ::= { v52IgExtensionEntry 2 }


--
        -- 1.3.6.1.4.1.5504.4.3.2.11.1.3
        v52IgLinkOutOfServiceTimer OBJECT-TYPE
            SYNTAX Integer32 (50..10000)
            UNITS "milliseconds."
            MAX-ACCESS read-create
            STATUS current
            DESCRIPTION
                "This timer specifies the length of time a Link must
                be in a failed state before the interface declares
                the link failed.  This timer value should always
                exceed the equivalent value on the LE.

                Valid range for the value is 50..10000 milliseconds
                and the default value is 2500 milliseconds.

                "
            DEFVAL { 2500 }
            ::= { v52IgExtensionEntry 3 }


--
        -- 1.3.6.1.4.1.5504.4.3.2.11.1.4
        v52IgLinkInServiceTimer OBJECT-TYPE
            SYNTAX Integer32 (50..10000)
            UNITS "milliseconds"
            MAX-ACCESS read-create
            STATUS current
            DESCRIPTION
                "This timer specifies the length of time a Link must be in a
                framed state before the interface declares the link in
                service.  This timer value should always be less than the
                equivalent value on the LE.

                Valid range for the value is 50..10000 milliseconds and
                the default value is 200 milliseconds."
            DEFVAL { 200 }
            ::= { v52IgExtensionEntry 4 }


        -- 1.3.6.1.4.1.5504.4.3.2.12
        v52ProtectionCPathTable OBJECT-TYPE
            SYNTAX SEQUENCE OF V52ProtectionCPathEntry
            MAX-ACCESS not-accessible
            STATUS current
            DESCRIPTION
                "This table is read-only and is derived from the protection
                group provisioning information from the v52CChannelTable.

                Unlike the C-Paths defined in v52CPathTable, C-Paths for the
                protection protocol are not carried over logical C-Channels.

                For each Interface Group, there will always be two C-Paths
                for protection protcol when an active and a standby CChannel
                are provisioned in protection group 1. The active and
                standby C-Channels for the group 1 protection shall always
                carry the two C-Paths for the protection protocol
                respectively and the protection C-Paths shall not be
                switched by the protection mechanism.

                When an Interface Group has no protection group provisioned
                in the v52CChannelTable, there will be no entries in this
                table for this Interface Group."
            REFERENCE
                "Section 18.1.2, ETSI EN 300 347-1 V2.2.2 (1999-12)"
            ::= { zhoneV52 12 }


        -- 1.3.6.1.4.1.5504.4.3.2.12.1
        v52ProtectionCPathEntry OBJECT-TYPE
            SYNTAX V52ProtectionCPathEntry
            MAX-ACCESS not-accessible
            STATUS current
            DESCRIPTION
                "An entry in the v52ProtectionCPathTable.

                The maximum number of entryies for this table is two."
            INDEX { v52IgNameId, v52ProtectionCPathId }
            ::= { v52ProtectionCPathTable 1 }


        V52ProtectionCPathEntry ::=
            SEQUENCE {
                v52ProtectionCPathId
                    Integer32,
                v52ProtectionCPathOperStatus
                    INTEGER,
                v52ProtectionCPathOperStatusCause
                    INTEGER
             }

        -- 1.3.6.1.4.1.5504.4.3.2.12.1.1
        v52ProtectionCPathId OBJECT-TYPE
            SYNTAX Integer32 (1..2)
            MAX-ACCESS not-accessible
            STATUS current
            DESCRIPTION
                "The valid value range is 1..2.

                v52ProtectionCPathId 1 refers to the C-Path for
                protection running on the provisioned active C-Channel
                in protection group 1.

                v52ProtectionCPathId 2 refers to the C-Path for
                protection running on the provisioned standby C-Channel
                in protection group 1.

                When an Interface Group is provisioned correctly and
                there are one active C-Channel and one standby
                C-Channel provisioned in group 1 protection group for
                that IG, protection C_Paths with ProtectionCPathId 1
                and 2 will be automatically created for that IG."
            ::= { v52ProtectionCPathEntry 1 }


        -- 1.3.6.1.4.1.5504.4.3.2.12.1.2
        v52ProtectionCPathOperStatus OBJECT-TYPE
            SYNTAX INTEGER
                {
                up(1),
                down(2)
                }
            MAX-ACCESS read-only
            STATUS current
            DESCRIPTION
                "This variable indicates the operational status of the
                protection CPath. The valid values are up(1) or down(2)."
            ::= { v52ProtectionCPathEntry 2 }


--
        -- 1.3.6.1.4.1.5504.4.3.2.12.1.3
        v52ProtectionCPathOperStatusCause OBJECT-TYPE
            SYNTAX INTEGER
                {
                establishConfirmationReceived(1),
                establishIndicationReceived(2),
                releaseIndicationReceived(3)
                }
            MAX-ACCESS read-only
            STATUS current
            DESCRIPTION
                "Cause for v52ProtectionCPathOperStatus.
                Valid values are:

                * establishConfirmationReceived - the data link
                  has been successfully established upon a local
                  request.

                * establishIndicationReceived - the data link
                  has been successfully established upon its
                  peer request.

                * releaseIndicationReceived - the data link has
                  failed because of either Layer 1 failure or
                  no frame exchange with the peer was possible
                  within the given time frame (after T203 timer
                  expiry, followed by T200 timer expiry N200
                  times)."
            ::= { v52ProtectionCPathEntry 3 }



    END

--
-- comVoiceV52.mib
--
