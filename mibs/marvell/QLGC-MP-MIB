-- QLGC-MP-MIB.my: QLogic Maintenance Panel MIB
--
-- Copyright (c) 1994-2009 QLogic Corporation.
-- All Rights Reserved

QLGC-MP-MIB DEFINITIONS ::= BEGIN

IMPORTS
    MODULE-IDENTITY, OBJECT-TYPE, OBJECT-IDENTITY, NOTIFICATION-TYPE
    FROM SNMPv2-SMI

    TEXTUAL-CONVENTION
    FROM SNMPv2-TC

    MODULE-COMPLIANCE, OBJECT-GROUP
    FROM SNMPv2-CONF

    qlogicMgmt
    FROM QLOGIC-SMI
    ;

qlgcMaintenancePanelModule MODULE-IDENTITY
    LAST-UPDATED  "200909290000Z" -- September 29, 2009
    ORGANIZATION  "QLogic Corp."
    CONTACT-INFO
    "
    QLogic Customer Service (SNMP)
    Postal: 26650 Aliso Viejo Parkway
            Aliso Viejo, California 92656
            USA
    Tel: +1 952-932-4040

    E-mail: support@qlogic.com
    "
    DESCRIPTION
        "The QLogic maintenance panel MIB module."

    REVISION "200909290000Z" -- September 29, 2009
    DESCRIPTION
       "The syntax and semantics errors reported by the
        smilint program were resolved."

    REVISION   "200703310000Z" -- March 31, 2007
    DESCRIPTION
        "Initial version of this MIB module."

::= { qlogicMgmt 2 }

    qlgcMPNotifications OBJECT IDENTIFIER ::= { qlgcMaintenancePanelModule  0 }
    qlgcMPObjects       OBJECT IDENTIFIER ::= { qlgcMaintenancePanelModule  1 }
    qlgcMPConformance   OBJECT IDENTIFIER ::= { qlgcMaintenancePanelModule  2 }

-- Textual Conventions

MPEpromStatus ::= TEXTUAL-CONVENTION
  STATUS          current
  DESCRIPTION     "Represents the current status of eprom."
  SYNTAX     INTEGER {
                     ok(1),
                     alarm(2)}

------------------------------------------------------------------------

qlgcMPStatus OBJECT IDENTIFIER ::= { qlgcMPObjects 1 }

qlgcMPEpromStatus   OBJECT-TYPE
    SYNTAX          MPEpromStatus
    MAX-ACCESS      read-only
    STATUS          current
    DESCRIPTION
        "The current status of the eprom monitor."

::= { qlgcMPStatus 1 }

------------------------------------------------------------------------

-- Related traps

qlgcMPStatusChange NOTIFICATION-TYPE
    OBJECTS { qlgcMPEpromStatus }
    STATUS  current
    DESCRIPTION
        "The status of the maintenance panel eprom monitor changed."
::= { qlgcMPNotifications 1 }

------------------------------------------------------------------------

-- Conformance Statements

qlgcMPGroups OBJECT IDENTIFIER ::= { qlgcMPConformance 1 }

qlgcMPGroup OBJECT-GROUP
    OBJECTS {
        qlgcMPEpromStatus
    }
    STATUS current
    DESCRIPTION
        "A single point status report on the health of eprom
        located on the maintenance panel."
::= { qlgcMPGroups 1 }

qlgcMPCompliances OBJECT IDENTIFIER ::= { qlgcMPConformance 2 }

qlgcMPComplianceV1 MODULE-COMPLIANCE
    STATUS current
    DESCRIPTION
        "Initial version of compliance statement based on
        initial version of MIB.

        If an implementation can be both a target and an
        initiator, all groups are mandatory."
    MODULE       -- this module
    MANDATORY-GROUPS {
    qlgcMPGroup
    }

::= { qlgcMPCompliances 1 }

END -- QLGC-MP-MIB DEFINITIONS
