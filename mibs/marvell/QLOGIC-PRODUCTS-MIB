-- QLOGIC-PRODUCTS-MIB.my:  QLogic Product Object Identifier Assignments
--
-- Copyright (c) 1994-2013 QLogic Corporation.
-- All Rights Reserved

QLOGIC-PRODUCTS-MIB DEFINITIONS ::= BEGIN

IMPORTS
    MODULE-IDENTITY, OBJECT-IDENTITY
    FROM SNMPv2-SMI

    qlogicModules, qlogicProducts
    FROM QLOGIC-SMI
    ;

qlogicProductsMIB MODULE-IDENTITY
    LAST-UPDATED  "201303290000Z" -- March 29, 2013
    ORGANIZATION  "QLogic Corp."
    CONTACT-INFO
    "
    QLogic Customer Service (SNMP)
    Postal: 26650 Aliso Viejo Parkway
            Aliso Viejo, California 92656
            USA
    Tel: +1 952-932-4040

    E-mail: support@qlogic.com
    "
    DESCRIPTION
        "This module defines the object identifiers that are
        assigned to various hardware platforms, and hence are
        returned as values for sysObjectID"

    REVISION      "201303290000Z" -- March 29, 2013
    DESCRIPTION
        "Added hpStorageWorksSN6000SingleFcSwitch and
         hpStorageWorksSN6000DualFcSwitch systems.
         Changed object name for qlogicProducts 34."

    REVISION      "200909290000Z" -- September 29, 2009
    DESCRIPTION
        "The syntax and semantics errors reported by the
         smilint program were resolved."

    REVISION      "200903030000Z" -- March 03, 2009
    DESCRIPTION
        "Added sanBox3810 system."

    REVISION      "200902170000Z" -- February 17, 2009
    DESCRIPTION
        "Added iSR6140, iSR6142, mpx100, mpx110, iSR6200, mpx200 and mez50 systems."

    REVISION      "200610110000Z" -- October 11, 2006
    DESCRIPTION
        "Renamed EVA-iSCSI to evaISCSI."

    REVISION      "200610060000Z" -- October 6, 2006
    DESCRIPTION
        "Added sanBox6140, EVA-iSCSI."

    REVISION      "200508230000Z" -- August 23, 2005
    DESCRIPTION
        "Initial version of this MIB module."

::= { qlogicModules 1 }

-- OBJECT-IDENTITY will be used for products that can be public knowledge

-- OBJECT IDENTIFIERs are used to mark spaces reserved for products that
-- are in development and thus are not yet public info. Use the name
-- reservedX in which X is the index (reserved1 is "qlogicProducts 1".

sanBox6140 OBJECT-IDENTITY
    STATUS        current
    DESCRIPTION
        "QLogic SANbox 6000 Series Intelligent Storage Router between
        iSCSI and FibreChannel comprising sanBox6140 and sanBox6142."
::= { qlogicProducts 1 }

evaISCSI OBJECT-IDENTITY
    STATUS        current
    DESCRIPTION
        "The HP Storage Works EVA iSCSI Connectivity Option."
::= { qlogicProducts 2 }

reserved3 OBJECT IDENTIFIER ::= { qlogicProducts 3 } -- historical

mpx100 OBJECT-IDENTITY
    STATUS        current
    DESCRIPTION
        "HP StorageWorks mpx100"
::= { qlogicProducts 4 }

iSR6140 OBJECT-IDENTITY
    STATUS        current
    DESCRIPTION
        "QLogic iSR-6140"
::= { qlogicProducts 5 }

iSR6142 OBJECT-IDENTITY
    STATUS        current
    DESCRIPTION
        "QLogic iSR-6142"
::= { qlogicProducts 6 }

mpx110 OBJECT-IDENTITY
    STATUS        current
    DESCRIPTION
        "HP StorageWorks mpx110"
::= { qlogicProducts 7 }

reserved8 OBJECT IDENTIFIER ::= { qlogicProducts 8 } -- unreleased product

sanBox5802 OBJECT-IDENTITY
    STATUS        current
    DESCRIPTION
	"QLogic SANbox 5802 FC Switch."
::= { qlogicProducts 9 }

reserved10 OBJECT IDENTIFIER ::= { qlogicProducts 10 } -- unreleased product

hpStorageWorks820FcSwitch OBJECT-IDENTITY
    STATUS        current
    DESCRIPTION
        "HP StorageWorks 8/20q FC Switch"
::= { qlogicProducts 11 }

reserved12 OBJECT IDENTIFIER ::= { qlogicProducts 12 } -- unreleased product
reserved13 OBJECT IDENTIFIER ::= { qlogicProducts 13 } -- unreleased product

sanBox5800 OBJECT-IDENTITY
    STATUS        current
    DESCRIPTION
        "QLogic SANbox 5800 FC Switch."
::= { qlogicProducts 14 }

reserved15 OBJECT IDENTIFIER ::= { qlogicProducts 15 } -- unreleased product
reserved16 OBJECT IDENTIFIER ::= { qlogicProducts 16 } -- unreleased product

iSR6200 OBJECT-IDENTITY
    STATUS        current
    DESCRIPTION
        "QLogic iSR6200 system, High Availability Intelligent Storage Router"
::= { qlogicProducts 17 }

mpx200 OBJECT-IDENTITY
    STATUS        current
    DESCRIPTION
        "HP StorageWorks MPX200 Multifunction Router"
::= { qlogicProducts 18 }

mez50 OBJECT-IDENTITY
    STATUS        current
    DESCRIPTION
        "HP StorageWorks MEZ50"
::= { qlogicProducts 19 }

sanBox3810 OBJECT-IDENTITY
    STATUS        current
    DESCRIPTION
        "SANbox 3810 FC Switch"
::= { qlogicProducts 20 }

reserved21 OBJECT IDENTIFIER ::= { qlogicProducts 21 } -- unreleased product
reserved22 OBJECT IDENTIFIER ::= { qlogicProducts 22 } -- unreleased product
reserved23 OBJECT IDENTIFIER ::= { qlogicProducts 23 } -- unreleased product

hpStorageWorksSN6000SingleFcSwitch OBJECT-IDENTITY
    STATUS        current
    DESCRIPTION
        "HP StorageWorks SN6000 Stackable Single Power Supply FC Switch"
::= { qlogicProducts 24 }

hpStorageWorksSN6000DualFcSwitch OBJECT-IDENTITY
    STATUS        current
    DESCRIPTION
        "HP StorageWorks SN6000 Stackable Dual Power Supply FC Switch"
::= { qlogicProducts 25 }

reserved26 OBJECT IDENTIFIER ::= { qlogicProducts 26 } -- unreleased product
reserved27 OBJECT IDENTIFIER ::= { qlogicProducts 27 } -- unreleased product
reserved28 OBJECT IDENTIFIER ::= { qlogicProducts 28 } -- unreleased product
reserved29 OBJECT IDENTIFIER ::= { qlogicProducts 29 } -- unreleased product
reserved30 OBJECT IDENTIFIER ::= { qlogicProducts 30 } -- unreleased product
reserved31 OBJECT IDENTIFIER ::= { qlogicProducts 31 } -- unreleased product
reserved32 OBJECT IDENTIFIER ::= { qlogicProducts 32 } -- unreleased product
reserved33 OBJECT IDENTIFIER ::= { qlogicProducts 33 } -- unreleased product

sns2120 OBJECT-IDENTITY
    STATUS        current
    DESCRIPTION
        "SNS2120 FC Switch"
::= { qlogicProducts 34 }

reserved35 OBJECT IDENTIFIER ::= { qlogicProducts 35 } -- unreleased product
reserved36 OBJECT IDENTIFIER ::= { qlogicProducts 36 } -- unreleased product
reserved37 OBJECT IDENTIFIER ::= { qlogicProducts 37 } -- unreleased product
reserved38 OBJECT IDENTIFIER ::= { qlogicProducts 38 } -- unreleased product
reserved39 OBJECT IDENTIFIER ::= { qlogicProducts 39 } -- unreleased product
reserved40 OBJECT IDENTIFIER ::= { qlogicProducts 40 } -- unreleased product
reserved41 OBJECT IDENTIFIER ::= { qlogicProducts 41 } -- unreleased product
reserved42 OBJECT IDENTIFIER ::= { qlogicProducts 42 } -- unreleased product
reserved43 OBJECT IDENTIFIER ::= { qlogicProducts 43 } -- unreleased product

END
