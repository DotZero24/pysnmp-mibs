-- ------------------------------------------------------
-- Seagate Enterprise Array MIB for SNMP traps
--
-- $Revision: 11692 $
--
-- Copyright 2020 Seagate Technology LLC or one of its affiliates
-- All rights reserved. Use is subject to license terms.
--
-- ------------------------------------------------------

SEAGATESYSTEMTRAP-MIB
-- Last edit date: May 14th, 2020
DEFINITIONS ::= BEGIN
  IMPORTS
    enterprises
        FROM RFC1155-SMI
    TRAP-TYPE
        FROM RFC-1215
    connUnitEventId, connUnitEventType, connUnitEventDescr
        FROM FCMGMT-MIB;


    --Textual conventions for this MIB

----------------------------------------------------------------------
    seagateSystems    OBJECT IDENTIFIER ::= { enterprises 347 }


-- Related traps

    seagateEventInfoTrap TRAP-TYPE
        ENTERPRISE seagateSystems
        VARIABLES { connUnitEventId,
                    connUnitEventType,
                    connUnitEventDescr }
        DESCRIPTION
            "An event has been generated by the storage array.
            Recommended severity level (for filtering): info"

        -- Trap annotations are as follows:
        --#TYPE "Informational storage event"
        --#SUMMARY "Informational storage event # %d, type %d, description: %s"
        --#ARGUMENTS {0,1,2}
        --#SEVERITY INFORMATIONAL
        --#TIMEINDEX 6
        ::= 1

    seagateEventWarningTrap TRAP-TYPE
        ENTERPRISE seagateSystems
        VARIABLES { connUnitEventId,
                    connUnitEventType,
                    connUnitEventDescr }
        DESCRIPTION
            "An event has been generated by the storage array.
            Recommended severity level (for filtering): warning"

        -- Trap annotations are as follows:
        --#TYPE "Warning storage event"
        --#SUMMARY "Warning storage event # %d, type %d, description: %s"
        --#ARGUMENTS {0,1,2}
        --#SEVERITY MINOR
        --#TIMEINDEX 6
        ::= 2

    seagateEventErrorTrap TRAP-TYPE
        ENTERPRISE seagateSystems
        VARIABLES { connUnitEventId,
                    connUnitEventType,
                    connUnitEventDescr }
        DESCRIPTION
            "An event has been generated by the storage array.
            Recommended severity level (for filtering): error"

        -- Trap annotations are as follows:
        --#TYPE "Error storage event"
        --#SUMMARY "Error storage event # %d, type %d, description: %s"
        --#ARGUMENTS {0,1,2}
        --#SEVERITY MAJOR
        --#TIMEINDEX 6
        ::= 3

    seagateEventCriticalTrap TRAP-TYPE
        ENTERPRISE seagateSystems
        VARIABLES { connUnitEventId,
                    connUnitEventType,
                    connUnitEventDescr }
        DESCRIPTION
            "An event has been generated by the storage array.
            Recommended severity level (for filtering): critical"

        -- Trap annotations are as follows:
        --#TYPE "Critical storage event"
        --#SUMMARY "Critical storage event # %d, type %d, description: %s"
        --#ARGUMENTS {0,1,2}
        --#SEVERITY CRITICAL
        --#TIMEINDEX 6
        ::= 4

    seagateEventResolvedTrap TRAP-TYPE
        ENTERPRISE seagateSystems
        VARIABLES { connUnitEventId,
                    connUnitEventType,
                    connUnitEventDescr }
        DESCRIPTION
            "An issue has been resolved on the array.
            Recommended severity level (for filtering): resolved"

        -- Trap annotations are as follows:
        --#TYPE "Resolved storage event"
        --#SUMMARY "Resolved storage event # %d, type %d, description: %s"
        --#ARGUMENTS {0,1,2}
        --#SEVERITY INFORMATIONAL
        --#TIMEINDEX 6
        ::= 5

END
