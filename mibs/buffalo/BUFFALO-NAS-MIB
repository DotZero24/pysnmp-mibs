BUFFALO-NAS-MIB DEFINITIONS ::= BEGIN

IMPORTS
    MODULE-IDENTITY, OBJECT-TYPE, NOTIFICATION-TYPE,
    enterprises, Integer32, Unsigned32
        FROM SNMPv2-SMI
    TEXTUAL-CONVENTION, DisplayString, DateAndTime
        FROM SNMPv2-TC
    buffalo FROM BUFFALO-ROOT-MIB;


teraStation		MODULE-IDENTITY
    LAST-UPDATED	"202003090000Z"
    ORGANIZATION	"Buffalo Inc."
    CONTACT-INFO	"URI: http://buffalo.jp/products/catalog/storage/hd_lan_business.html
			 Contact: Network Business Unit
			 Buffalo Inc.
			 3-30-20 Osu, Naka-ku, Nagoya city, Aichi, JAPAN"
    DESCRIPTION		"The MIB for Buffalo NAS.
			 Copyright (c) 2012 Buffalo Inc."
    REVISION		"202003090000Z"
    DESCRIPTION		"revision1 : 20200309"
    ::= { buffalo 27}


teraStationObjects		OBJECT IDENTIFIER
    ::= { teraStation 1 }

teraStationNotifications	OBJECT IDENTIFIER
    ::= { teraStation 2 }

-- ************************************************************************

-- Textual Conventions

-- ************************************************************************

DayOfWeek ::= TEXTUAL-CONVENTION
    STATUS		current
    DESCRIPTION		"Day of the week."
    SYNTAX		INTEGER {
			    sun(1),
			    mon(2),
			    tue(3),
			    wed(4),
			    thu(5),
			    fri(6),
			    sat(7)
			}

LongUTF8String ::= TEXTUAL-CONVENTION
    DISPLAY-HINT	"255t"
    STATUS		current
    DESCRIPTION		"The string is using UTF-8."
    SYNTAX		OCTET STRING (SIZE (1..1024))


-- ************************************************************************

-- Objects

-- ************************************************************************

-- ************************************************************************

-- Backup Task

-- ************************************************************************

nasBackupTable		OBJECT-TYPE
    SYNTAX		SEQUENCE OF NasBackupEntry
    MAX-ACCESS		not-accessible
    STATUS		current
    DESCRIPTION		"The table contains the schedules
			of backup jobs."
    ::= { teraStationObjects 1 }

nasBackupEntry	OBJECT-TYPE
    SYNTAX		NasBackupEntry
    MAX-ACCESS		not-accessible
    STATUS		current
    DESCRIPTION		"An entry for nasBackupTable.
			Contents of the entry are read
			from the file /etc/melco/backupx
			and the entry is made at each file."
    INDEX		{ nasBackupIndex }
    ::= { nasBackupTable 1 }

NasBackupEntry ::= SEQUENCE {
    nasBackupIndex	Integer32,
    nasBackupStatus	INTEGER
}

nasBackupIndex		OBJECT-TYPE
    SYNTAX		Integer32 (1..8)
    MAX-ACCESS		not-accessible
    STATUS		current
    DESCRIPTION		"The index value that uniquely
			identifies nasBackupEntry."
    ::= { nasBackupEntry 1 }

nasBackupStatus		OBJECT-TYPE
    SYNTAX		INTEGER {
			    ready(1),
			    run(2),
			    done(3),
			    error(4)
			}
    MAX-ACCESS		read-only
    STATUS		current
    DESCRIPTION		"The status of a backup job. This
			value is read from the 'status' line
			in the file at /etc/melco/backupx.
			-'ready(1)' means waiting for the
			backup job start.
			-'run(2)' means the backup job is
			running.
			-'done(3)' means the backup job
			succeeded.
			-'error(4)' means the backup job
			failed."
    ::= { nasBackupEntry 3 }

-- ************************************************************************

-- Disk Status

-- ************************************************************************

nasDiskTable		OBJECT-TYPE
    SYNTAX		SEQUENCE OF NasDiskEntry
    MAX-ACCESS		not-accessible
    STATUS		current
    DESCRIPTION		"The table contains information of
			internal drives."
    ::= { teraStationObjects 2 }

nasDiskEntry		OBJECT-TYPE
    SYNTAX		NasDiskEntry
    MAX-ACCESS		not-accessible
    STATUS		current
    DESCRIPTION		"An entry for nasDiskTable.
			Contents of the entry are read from
			the file /etc/melco/diskinfo and
			the entry is made at each 'diskx'
			line."
    INDEX		{ nasDiskIndex }
    ::= { nasDiskTable 1 }

NasDiskEntry ::= SEQUENCE {
    nasDiskIndex	Integer32,
    nasDiskStatus	INTEGER,
    nasDiskCapacity	Integer32,
    nasDiskUsed		Integer32,
    nasDiskSMARTStatus	INTEGER,
    nasDiskSMARTReallocatedSectorCtValue	Integer32,
    nasDiskSMARTReallocatedSectorCtWorst	Integer32,
    nasDiskSMARTReallocatedSectorCtThresh	Integer32,
    nasDiskSMARTReallocatedSectorCtRAW		DisplayString,
    nasDiskSMARTCurrentPendingSectorValue	Integer32,
    nasDiskSMARTCurrentPendingSectorWorst	Integer32,
    nasDiskSMARTCurrentPendingSectorThresh	Integer32,
    nasDiskSMARTCurrentPendingSectorRAW		DisplayString,
    nasDiskSMARTOfflineUncorrectableValue	Integer32,
    nasDiskSMARTOfflineUncorrectableWorst	Integer32,
    nasDiskSMARTOfflineUncorrectableThresh	Integer32,
    nasDiskSMARTOfflineUncorrectableRAW		DisplayString,
    nasSSDSMARTRemainingLifeValue		Integer32,
    nasSSDSMARTRemainingLifeWorst		Integer32,
    nasSSDSMARTRemainingLifeThresh		Integer32,
    nasSSDSMARTBadBlockCountValue		Integer32,
    nasSSDSMARTBadBlockCountWorst		Integer32,
    nasSSDSMARTBadBlockCountThresh		Integer32,
    nasDiskCapacityGiB	Integer32,
    nasDiskCapacityLow	Unsigned32,
    nasDiskCapacityHigh	Unsigned32,
    nasDiskUsedGiB	Integer32,
    nasDiskUsedLow	Unsigned32,
    nasDiskUsedHigh	Unsigned32,
    nasDiskModelName        DisplayString,
    nasDiskSMARTReallocatedSectorCtHealth   Integer32,
    nasDiskSMARTCurrentPendingSectorHealth  Integer32,
    nasDiskSMARTOfflineUncorrectableHealth  Integer32,
    nasDiskSMARTRawReadErrorRateValue       Integer32,
    nasDiskSMARTRawReadErrorRateWorst       Integer32,
    nasDiskSMARTRawReadErrorRateThresh      Integer32,
    nasDiskSMARTRawReadErrorRateRAW         DisplayString,
    nasDiskSMARTRawReadErrorRateHealth      Integer32,
    nasDiskSMARTPowerOnHoursValue           Integer32,
    nasDiskSMARTPowerOnHoursWorst           Integer32,
    nasDiskSMARTPowerOnHoursThresh          Integer32,
    nasDiskSMARTPowerOnHoursRAW             DisplayString,
    nasDiskSMARTPowerOnHoursHealth          Integer32
}

nasDiskIndex		OBJECT-TYPE
    SYNTAX		Integer32
    MAX-ACCESS		not-accessible
    STATUS		current
    DESCRIPTION		"The index value that uniquely
			identifies nasDiskEntry."
    ::= { nasDiskEntry 1 }

nasDiskStatus		OBJECT-TYPE
    SYNTAX		INTEGER {
			    notSupport(-1),
			    normal(1),
			    array1(2),
			    array2(3),
			    standby(4),
			    degrade(5),
			    remove(6),
			    standbyRemoved(7),
			    degradeRemoved(8),
			    removeRemoved(9),
			    array3(10),
			    array4(11),
			    mediaCartridge(12),
			    array5(13),
			    array6(14)
			}
    MAX-ACCESS		read-only
    STATUS		current
    DESCRIPTION		"The status of internal drives. This
			value is read from the 'diskx' line
			in the file at /etc/melco/diskinfo.
			-'notSupport(-1)' means the drive
			slot does not exist.
			-'normal(1)' means the drive is
			being used as a JBOD.
			-'array1(2)' means the drive is
			being used as a part of array 1.
			-'array2(3)' means the drive is
			being used as a part of array 2.
			-'standby(4)' means the drive is
			waiting as a spare drive.
			-'degrade(5)' means the drive has
			degraded and has been removed
			from the array.
			-'remove(6)' means the drive has
			been dismounted by a user.
			-'standbyRemoved(7)' means the
			drive is configured as a spare
			drive and disconnected from the
			TeraStation.
			-'degradeRemoved(8)' means the
			drive has degraded, and has been
			removed from the array and
			disconnected from the TeraStation.
			-'removeRemoved(9)' means the
			drive has been dismounted by
			a user and is disconnected from
			the TeraStation.
			-'array3(10)' means the drive is
			being used as a part of array 3.
			-'array4(11)' means the drive is
			being used as a part of array 4.
			-'mediaCartridge(12)' means the
			drive is configured as a media
			cartridge.
			-'array5(13)' means the drive is
			being used as a part of array 5.
			-'array6(14)' means the drive is
			being used as a part of array 6."
    ::= { nasDiskEntry 2 }

nasDiskCapacity		OBJECT-TYPE
    SYNTAX		Integer32
    MAX-ACCESS		read-only
    STATUS		current
    DESCRIPTION		"The maximum capacity of each
			drive. The unit is in gigabytes to
			show the capacity. The default
			value is '-1'."
    ::= { nasDiskEntry 3 }

nasDiskUsed		OBJECT-TYPE
    SYNTAX		Integer32 (-1..100)
    UNITS			"%"
    MAX-ACCESS		read-only
    STATUS		current
    DESCRIPTION		"The usage of each drive. The
			default value is '-1'."
    ::= { nasDiskEntry 4 }

nasDiskSMARTStatus		OBJECT-TYPE
	SYNTAX		INTEGER {
				unavailable(-2),
				unknown(-1),
				normal(1),
				caution(2),
				fail(3)
			}
    MAX-ACCESS		read-only
    STATUS		current
    DESCRIPTION		"Drive status from S.M.A.R.T."
    ::= { nasDiskEntry 5 }

nasDiskSMARTReallocatedSectorCtValue		OBJECT-TYPE
    SYNTAX		Integer32
    MAX-ACCESS		read-only
    STATUS		current
    DESCRIPTION		"Current value of
			'Reallocated_Sector_Ct'."
    ::= { nasDiskEntry 6 }

nasDiskSMARTReallocatedSectorCtWorst		OBJECT-TYPE
    SYNTAX		Integer32
    MAX-ACCESS		read-only
    STATUS		current
    DESCRIPTION		"Worst value of
			'Reallocated_Sector_Ct'."
    ::= { nasDiskEntry 7 }

nasDiskSMARTReallocatedSectorCtThresh		OBJECT-TYPE
    SYNTAX		Integer32
    MAX-ACCESS		read-only
    STATUS		current
    DESCRIPTION		"Threshold value of
			'Reallocated_Sector_Ct'."
    ::= { nasDiskEntry 8 }

nasDiskSMARTReallocatedSectorCtRAW		OBJECT-TYPE
    SYNTAX		DisplayString
    MAX-ACCESS		read-only
    STATUS		current
    DESCRIPTION		"Raw value of
			'Reallocated_Sector_Ct'."
    ::= { nasDiskEntry 9 }

nasDiskSMARTCurrentPendingSectorValue		OBJECT-TYPE
    SYNTAX		Integer32
    MAX-ACCESS		read-only
    STATUS		current
    DESCRIPTION		"Current value of
			'Current_Pending_Sector'."
    ::= { nasDiskEntry 10 }

nasDiskSMARTCurrentPendingSectorWorst		OBJECT-TYPE
    SYNTAX		Integer32
    MAX-ACCESS		read-only
    STATUS		current
    DESCRIPTION		"Worst value of
			'Current_Pending_Sector'."
    ::= { nasDiskEntry 11 }

nasDiskSMARTCurrentPendingSectorThresh		OBJECT-TYPE
    SYNTAX		Integer32
    MAX-ACCESS		read-only
    STATUS		current
    DESCRIPTION		"Threshold value of
			'Current_Pending_Sector'."
    ::= { nasDiskEntry 12 }

nasDiskSMARTCurrentPendingSectorRAW		OBJECT-TYPE
    SYNTAX		DisplayString
    MAX-ACCESS		read-only
    STATUS		current
    DESCRIPTION		"Raw value of
			'Current_Pending_Sector'."
    ::= { nasDiskEntry 13 }

nasDiskSMARTOfflineUncorrectableValue		OBJECT-TYPE
    SYNTAX		Integer32
    MAX-ACCESS		read-only
    STATUS		current
    DESCRIPTION		"Current value of
			'Offline_Uncorrectable'."
    ::= { nasDiskEntry 14 }

nasDiskSMARTOfflineUncorrectableWorst		OBJECT-TYPE
    SYNTAX		Integer32
    MAX-ACCESS		read-only
    STATUS		current
    DESCRIPTION		"Worst value of
			'Offline_Uncorrectable'."
    ::= { nasDiskEntry 15 }

nasDiskSMARTOfflineUncorrectableThresh		OBJECT-TYPE
    SYNTAX		Integer32
    MAX-ACCESS		read-only
    STATUS		current
    DESCRIPTION		"Threshold value of
			'Offline_Uncorrectable'."
    ::= { nasDiskEntry 16 }

nasDiskSMARTOfflineUncorrectableRAW		OBJECT-TYPE
    SYNTAX		DisplayString
    MAX-ACCESS		read-only
    STATUS		current
    DESCRIPTION		"Raw value of
			'Offline_Uncorrectable'."
    ::= { nasDiskEntry 17 }

nasSSDSMARTRemainingLifeValue			OBJECT-TYPE
    SYNTAX		Integer32
    MAX-ACCESS		read-only
    STATUS		current
    DESCRIPTION		"Percentage of remaining SSD
			lifetime's current value."
    ::= { nasDiskEntry 18 }

nasSSDSMARTRemainingLifeWorst			OBJECT-TYPE
    SYNTAX		Integer32
    MAX-ACCESS		read-only
    STATUS		current
    DESCRIPTION		"Percentage of remaining SSD
			lifetime's worst value."
    ::= { nasDiskEntry 19 }

nasSSDSMARTRemainingLifeThresh		OBJECT-TYPE
    SYNTAX		Integer32
    MAX-ACCESS		read-only
    STATUS		current
    DESCRIPTION		"Percentage of remaining SSD
			lifetime's threshold value."
    ::= { nasDiskEntry 20 }

nasSSDSMARTBadBlockCountValue		OBJECT-TYPE
    SYNTAX		Integer32
    MAX-ACCESS		read-only
    STATUS		current
    DESCRIPTION		"Current value of total bad block
			counts."
    ::= { nasDiskEntry 21 }

nasSSDSMARTBadBlockCountWorst		OBJECT-TYPE
    SYNTAX		Integer32
    MAX-ACCESS		read-only
    STATUS		current
    DESCRIPTION		"Worst value of total bad block
			counts."
    ::= { nasDiskEntry 22 }

nasSSDSMARTBadBlockCountThresh		OBJECT-TYPE
    SYNTAX		Integer32
    MAX-ACCESS		read-only
    STATUS		current
    DESCRIPTION		"Threshold value of total bad
			block counts."
    ::= { nasDiskEntry 23 }

nasDiskCapacityGiB	OBJECT-TYPE
    SYNTAX		Integer32
    MAX-ACCESS		read-only
    STATUS		current
    DESCRIPTION		"The maximum capacity of each drive.
			The unit is in gibibytes to show the
			capacity. The default value is
			'-1'."
    ::= { nasDiskEntry 24 }

nasDiskCapacityLow	OBJECT-TYPE
    SYNTAX		Unsigned32
    MAX-ACCESS		read-only
    STATUS		current
    DESCRIPTION		"The maximum capacity of each drive.
			The unit is in bytes to show the
			capacity. The default value is '0'.
			Together with nasDiskCapacityHigh
			composes 64-bit number."
    ::= { nasDiskEntry 25 }

nasDiskCapacityHigh	OBJECT-TYPE
    SYNTAX		Unsigned32
    MAX-ACCESS		read-only
    STATUS		current
    DESCRIPTION		"The maximum capacity of each drive.
			The unit is in bytes to show the
			capacity. The default value is '0'.
			Together with nasDiskCapacityLow
			composes 64-bit number."
    ::= { nasDiskEntry 26 }

nasDiskUsedGiB		OBJECT-TYPE
    SYNTAX		Integer32
    MAX-ACCESS		read-only
    STATUS		current
    DESCRIPTION		"The usage of each drive in
			gibibytes. The default value is
			'-1'."
    ::= { nasDiskEntry 27 }

nasDiskUsedLow		OBJECT-TYPE
    SYNTAX		Unsigned32
    MAX-ACCESS		read-only
    STATUS		current
    DESCRIPTION		"The usage of each drive in bytes.
			The default value is '0'. Together
			with nasDiskUsedHigh composes 64-bit
			number."
    ::= { nasDiskEntry 28 }

nasDiskUsedHigh		OBJECT-TYPE
    SYNTAX		Unsigned32
    MAX-ACCESS		read-only
    STATUS		current
    DESCRIPTION		"The usage of each drive in bytes.
			The default value is '0'. Together
			with nasDiskUsedLow composes 64-bit
			number."
    ::= { nasDiskEntry 29 }

nasDiskModelName        OBJECT-TYPE
    SYNTAX      DisplayString
    MAX-ACCESS      read-only
    STATUS      current
    DESCRIPTION     "HDD model."
    ::= { nasDiskEntry 30 }

nasDiskSMARTReallocatedSectorCtHealth       OBJECT-TYPE
    SYNTAX      INTEGER {
                unavailable(-2),
                normal(1),
                fail(3)
            }
    MAX-ACCESS      read-only
    STATUS      current
    DESCRIPTION     "ReallocatedSectorCtHealth"
    ::= { nasDiskEntry 31 }

nasDiskSMARTCurrentPendingSectorHealth      OBJECT-TYPE
    SYNTAX      INTEGER {
                unavailable(-2),
                normal(1),
                fail(3)
            }
    MAX-ACCESS      read-only
    STATUS      current
    DESCRIPTION     "CurrentPendingSectorHealth"
    ::= { nasDiskEntry 32 }

nasDiskSMARTOfflineUncorrectableHealth      OBJECT-TYPE
    SYNTAX      INTEGER {
                unavailable(-2),
                normal(1),
                fail(3)
            }
    MAX-ACCESS      read-only
    STATUS      current
    DESCRIPTION     "OfflineUncorrectableHealth"
    ::= { nasDiskEntry 33 }

nasDiskSMARTRawReadErrorRateValue       OBJECT-TYPE
    SYNTAX      Integer32
    MAX-ACCESS      read-only
    STATUS      current
    DESCRIPTION     "RawReadErrorRateValue"
    ::= { nasDiskEntry 34 }

nasDiskSMARTRawReadErrorRateWorst       OBJECT-TYPE
    SYNTAX      Integer32
    MAX-ACCESS      read-only
    STATUS      current
    DESCRIPTION     "RawReadErrorRateWorst"
    ::= { nasDiskEntry 35 }

nasDiskSMARTRawReadErrorRateThresh      OBJECT-TYPE
    SYNTAX      Integer32
    MAX-ACCESS      read-only
    STATUS      current
    DESCRIPTION     "RawReadErrorRateThresh"
    ::= { nasDiskEntry 36 }

nasDiskSMARTRawReadErrorRateRAW     OBJECT-TYPE
    SYNTAX      DisplayString
    MAX-ACCESS      read-only
    STATUS      current
    DESCRIPTION     "RawReadErrorRateRAW."
    ::= { nasDiskEntry 37 }

nasDiskSMARTRawReadErrorRateHealth      OBJECT-TYPE
    SYNTAX      Integer32
    MAX-ACCESS      read-only
    STATUS      current
    DESCRIPTION     "RawReadErrorRateHealth"
    ::= { nasDiskEntry 38 }

nasDiskSMARTPowerOnHoursValue       OBJECT-TYPE
    SYNTAX      Integer32
    MAX-ACCESS      read-only
    STATUS      current
    DESCRIPTION     "PowerOnHoursValue "
    ::= { nasDiskEntry 39 }

nasDiskSMARTPowerOnHoursWorst       OBJECT-TYPE
    SYNTAX      Integer32
    MAX-ACCESS      read-only
    STATUS      current
    DESCRIPTION     "PowerOnHoursWorst"
    ::= { nasDiskEntry 40 }

nasDiskSMARTPowerOnHoursThresh      OBJECT-TYPE
    SYNTAX      Integer32
    MAX-ACCESS      read-only
    STATUS      current
    DESCRIPTION     "PowerOnHoursThresh "
    ::= { nasDiskEntry 41 }

nasDiskSMARTPowerOnHoursRAW     OBJECT-TYPE
    SYNTAX      DisplayString
    MAX-ACCESS      read-only
    STATUS      current
    DESCRIPTION     "Raw value of
            'Offline_Uncorrectable'."
    ::= { nasDiskEntry 42 }

nasDiskSMARTPowerOnHoursHealth      OBJECT-TYPE
    SYNTAX      Integer32
    MAX-ACCESS      read-only
    STATUS      current
    DESCRIPTION     "PowerOnHoursHealth"
    ::= { nasDiskEntry 43 }


-- ************************************************************************

-- Array Status

-- ************************************************************************

nasArrayTable		OBJECT-TYPE
    SYNTAX		SEQUENCE OF NasArrayEntry
    MAX-ACCESS		not-accessible
    STATUS		current
    DESCRIPTION		"The table contains information of
			a RAID array."
    ::= { teraStationObjects 3 }

nasArrayEntry		OBJECT-TYPE
    SYNTAX		NasArrayEntry
    MAX-ACCESS		not-accessible
    STATUS		current
    DESCRIPTION		"An entry for nasArrayTable.
			Contents of the entry are read
			from the file /etc/melco/diskinfo
			and the entry is made at each
			'arrayx' line."
    INDEX		{ nasArrayIndex }
    ::= { nasArrayTable 1 }

NasArrayEntry ::= SEQUENCE {
    nasArrayIndex		Integer32,
    nasArrayStatus		INTEGER,
    nasArrayCapacity		Integer32,
    nasArrayUsed		Integer32,
    nasArrayCapacityGiB		Integer32,
    nasArrayCapacityLow		Unsigned32,
    nasArrayCapacityHigh	Unsigned32,
    nasArrayUsedGiB		Integer32,
    nasArrayUsedLow		Unsigned32,
    nasArrayUsedHigh		Unsigned32
}

nasArrayIndex		OBJECT-TYPE
    SYNTAX		Integer32
    MAX-ACCESS		not-accessible
    STATUS		current
    DESCRIPTION		"The index value that uniquely
			identifies nasArrayEntry."
    ::= { nasArrayEntry 1 }

nasArrayStatus		OBJECT-TYPE
    SYNTAX		INTEGER {
			    notSupport(-1),
			    off(1),
			    raid0(2),
			    raid1(3),
			    raid5(4),
			    raid6(5),
			    raid10(6),
			    raid50(7),
			    raid51(8),
			    raid60(9),
			    raid61(10)
			}
    MAX-ACCESS		read-only
    STATUS		current
    DESCRIPTION		"The status of a RAID array. This
			value is read from the 'arrayx' line
			in the file at /etc/melco/diskinfo.
			-'NotSupport(-1)' means the RAID
			mode is not supported.
			-'off(1)' means the RAID array is
			not configured.
			-'raid0(2)' means the RAID array
			is being used as a RAID 0 array.
			-'raid1(3)' means the RAID array
			is being used as a RAID 1 array.
			-'raid5(4)' means the RAID array
			is being used as a RAID 5 array.
			-'raid6(5)' means the RAID array
			is being used as a RAID 6 array.
			-'raid10(6)' means the RAID array
			is being used as a RAID 10 array.
			-'raid50(7)' means the RAID array
			is being used as a RAID 50 array.
			-'raid51(8)' means the RAID array
			is being used as a RAID 51 array.
			-'raid60(9)' means the RAID array
			is being used as a RAID 60 array.
			-'raid61(10)' means the RAID array
			is being used as a RAID 61 array."
    ::= { nasArrayEntry 2 }

nasArrayCapacity	OBJECT-TYPE
    SYNTAX		Integer32
    MAX-ACCESS		read-only
    STATUS		current
    DESCRIPTION		"The maximum capacity of each
			array. The displayed unit is in
			gigabytes. The defaultvalue is
			'-1'."
    ::= { nasArrayEntry 3 }

nasArrayUsed		OBJECT-TYPE
    SYNTAX		Integer32 (-1..100)
    UNITS			"%"
    MAX-ACCESS		read-only
    STATUS		current
    DESCRIPTION		"The usage of each array. The
			default value is '-1'."
    ::= { nasArrayEntry 4 }

nasArrayCapacityGiB	OBJECT-TYPE
    SYNTAX		Integer32
    MAX-ACCESS		read-only
    STATUS		current
    DESCRIPTION		"The maximum capacity of each array.
			The displayed unit is in gibibytes.
			The default value is '-1'."
    ::= { nasArrayEntry 5 }

nasArrayCapacityLow	OBJECT-TYPE
    SYNTAX		Unsigned32
    MAX-ACCESS		read-only
    STATUS		current
    DESCRIPTION		"The maximum capacity of each array.
			The unit is in bytes to show the
			capacity. The default value is '0'.
			Together with nasArrayCapacityHigh
			composes 64-bit number."
    ::= { nasArrayEntry 6 }

nasArrayCapacityHigh	OBJECT-TYPE
    SYNTAX		Unsigned32
    MAX-ACCESS		read-only
    STATUS		current
    DESCRIPTION		"The maximum capacity of each array.
			The unit is in bytes to show the
			capacity. The default value is '0'.
			Together with nasArrayCapacityLow
			composes 64-bit number."
    ::= { nasArrayEntry 7 }

nasArrayUsedGiB		OBJECT-TYPE
    SYNTAX		Integer32
    MAX-ACCESS		read-only
    STATUS		current
    DESCRIPTION		"The usage of each array in
			gibibytes. The default value is
			'-1'."
    ::= { nasArrayEntry 8 }

nasArrayUsedLow		OBJECT-TYPE
    SYNTAX		Unsigned32
    MAX-ACCESS		read-only
    STATUS		current
    DESCRIPTION		"The usage of each array in bytes.
			The default value is '0'. Together
			with nasArrayUsedHigh composes
			64-bit number."
    ::= { nasArrayEntry 9 }

nasArrayUsedHigh	OBJECT-TYPE
    SYNTAX		Unsigned32
    MAX-ACCESS		read-only
    STATUS		current
    DESCRIPTION		"The usage of each array in bytes.
			The default value is '0'.  Together
			with nasArrayUsedLow composes
			64-bit number."
    ::= { nasArrayEntry 10 }

-- ************************************************************************

-- Errors

-- ************************************************************************

nasErrorTable		OBJECT-TYPE
    SYNTAX		SEQUENCE OF NasErrorEntry
    MAX-ACCESS		not-accessible
    STATUS		current
    DESCRIPTION		"The table contains error events
			that occurred on the TeraStation."
    ::= { teraStationObjects 4 }

nasErrorEntry		OBJECT-TYPE
    SYNTAX		NasErrorEntry
    MAX-ACCESS		not-accessible
    STATUS		current
    DESCRIPTION		"An entry for nasErrorTable.
			Contents of the entry are read
			from the file /tmp/error_status."
    INDEX		{ nasErrorIndex }
    ::= { nasErrorTable 1 }

NasErrorEntry ::= SEQUENCE {
    nasErrorIndex	Integer32,
    nasErrorMsg		DisplayString,
    nasErrorDate	DisplayString,
    nasErrorDateAndTime	DateAndTime
}

nasErrorIndex		OBJECT-TYPE
    SYNTAX		Integer32 (1..99)
    MAX-ACCESS		not-accessible
    STATUS		current
    DESCRIPTION		"The index value that uniquely
			identifies nasErrorEntry."
    ::= { nasErrorEntry 1 }

nasErrorMsg		OBJECT-TYPE
    SYNTAX		DisplayString
    MAX-ACCESS		read-only
    STATUS		current
    DESCRIPTION		"The detail of an error event that
			occurred."
    ::= { nasErrorEntry 2 }

nasErrorDate		OBJECT-TYPE
    SYNTAX		DisplayString
    MAX-ACCESS		read-only
    STATUS		current
    DESCRIPTION		"The date and time on which an
			error event occurred."
    ::= { nasErrorEntry 3 }

nasErrorDateAndTime		OBJECT-TYPE
    SYNTAX		DateAndTime
    MAX-ACCESS		read-only
    STATUS		current
    DESCRIPTION		"The date and time on which an
			error event occurred."
    ::= { nasErrorEntry 4 }

-- ************************************************************************

-- Informations

-- ************************************************************************

nasInformationTable	OBJECT-TYPE
    SYNTAX		SEQUENCE OF NasInformationEntry
    MAX-ACCESS		not-accessible
    STATUS		current
    DESCRIPTION		"The table contains possible
			information events that occurred on
			the TeraStation."
    ::= { teraStationObjects 5 }

nasInformationEntry	OBJECT-TYPE
    SYNTAX		NasInformationEntry
    MAX-ACCESS		not-accessible
    STATUS		current
    DESCRIPTION		"An entry for nasInformationTable.
			Contents of the entry are read
			from the file /tmp/info_status."
    INDEX		{ nasInformationIndex }
    ::= { nasInformationTable 1 }

NasInformationEntry ::= SEQUENCE {
    nasInformationIndex	Integer32,
    nasInformationMsg	DisplayString,
    nasInformationDate	DisplayString,
    nasInformationDateAndTime	DateAndTime
}

nasInformationIndex	OBJECT-TYPE
    SYNTAX		Integer32 (1..99)
    MAX-ACCESS		not-accessible
    STATUS		current
    DESCRIPTION		"The index value that uniquely
			identifies nasInformationTable."
    ::= { nasInformationEntry 1 }

nasInformationMsg	OBJECT-TYPE
    SYNTAX		DisplayString
    MAX-ACCESS		read-only
    STATUS		current
    DESCRIPTION		"The details of an information event
			that occurred."
    ::= { nasInformationEntry 2 }

nasInformationDate	OBJECT-TYPE
    SYNTAX		DisplayString
    MAX-ACCESS		read-only
    STATUS		current
    DESCRIPTION		"The date and time on which an
			information event occurred."
    ::= { nasInformationEntry 3 }

nasInformationDateAndTime	OBJECT-TYPE
    SYNTAX		DateAndTime
    MAX-ACCESS		read-only
    STATUS		current
    DESCRIPTION		"The date and time on which an
			information event occurred."
    ::= { nasInformationEntry 4 }

-- ************************************************************************

-- LVM

-- ************************************************************************

nasLVMParams	OBJECT IDENTIFIER ::= { teraStationObjects 6 }

nasVGTable		OBJECT-TYPE
    SYNTAX		SEQUENCE OF NasVGEntry
    MAX-ACCESS		not-accessible
    STATUS		current
    DESCRIPTION		"The table contains information of
			LVM volumes."
    ::= { nasLVMParams 1 }

nasVGEntry		OBJECT-TYPE
    SYNTAX		NasVGEntry
    MAX-ACCESS		not-accessible
    STATUS		current
    DESCRIPTION		"An entry for nasVGTable."
    INDEX		{ nasVGIndex }
    ::= { nasVGTable 1 }

NasVGEntry ::= SEQUENCE {
    nasVGIndex		Integer32,
    nasVGPESize		Integer32,
    nasVGPETotal	Integer32,
    nasVGPEUsed		Integer32,
    nasLVTable		Integer32,
    nasPVTable		Integer32
}

nasVGIndex		OBJECT-TYPE
    SYNTAX		Integer32
    MAX-ACCESS		not-accessible
    STATUS		current
    DESCRIPTION		"The index value that uniquely
			identifies nasVGEntry."
    ::= { nasVGEntry 1 }

nasVGPESize		OBJECT-TYPE
    SYNTAX		Integer32
    UNITS			"GB"
    MAX-ACCESS		read-only
    STATUS		current
    DESCRIPTION		"Physical extent size."
    ::= { nasVGEntry 2 }

nasVGPETotal		OBJECT-TYPE
    SYNTAX		Integer32
    MAX-ACCESS		read-only
    STATUS		current
    DESCRIPTION		"Total physical extent count."
    ::= { nasVGEntry 3 }

nasVGPEUsed		OBJECT-TYPE
    SYNTAX		Integer32
    MAX-ACCESS		read-only
    STATUS		current
    DESCRIPTION		"Used physical extent count."
    ::= { nasVGEntry 4 }

nasLVTable		OBJECT-TYPE
    SYNTAX		SEQUENCE OF NasLVEntry
    MAX-ACCESS		not-accessible
    STATUS		current
    DESCRIPTION		"The table contains information of
			the logical volume."
    ::= { nasVGEntry 5 }

nasLVEntry		OBJECT-TYPE
    SYNTAX		NasLVEntry
    MAX-ACCESS		not-accessible
    STATUS		current
    DESCRIPTION		"An entry for nasLVTable."
    INDEX		{ nasVGIndex, nasLVIndex }
    ::= { nasLVTable 1 }

NasLVEntry ::= SEQUENCE {
    nasLVIndex		Integer32,
    nasLVName		DisplayString,
    nasLVCapacity	Integer32,
    nasLVUsed		Integer32,
    nasLVCapacityGiB	Integer32,
    nasLVCapacityLow	Unsigned32,
    nasLVCapacityHigh	Unsigned32,
    nasLVUsedGiB	Integer32,
    nasLVUsedLow	Unsigned32,
    nasLVUsedHigh	Unsigned32
}

nasLVIndex		OBJECT-TYPE
    SYNTAX		Integer32 (1..32)
    MAX-ACCESS		not-accessible
    STATUS		current
    DESCRIPTION		"The index value that uniquely
			identifies nasLVEntry."
    ::= { nasLVEntry 1 }

nasLVName		OBJECT-TYPE
    SYNTAX		DisplayString
    MAX-ACCESS		read-only
    STATUS		current
    DESCRIPTION		"Logical volume name."
    ::= { nasLVEntry 2 }

nasLVCapacity		OBJECT-TYPE
    SYNTAX		Integer32
    MAX-ACCESS		read-only
    STATUS		current
    DESCRIPTION		"Logical volume capacity
			in gigabytes."
    ::= { nasLVEntry 3 }

nasLVUsed		OBJECT-TYPE
    SYNTAX		Integer32 (-1..100)
    UNITS			"%"
    MAX-ACCESS		read-only
    STATUS		current
    DESCRIPTION		"Used logical volume."
    ::= { nasLVEntry 4 }

nasLVCapacityGiB	OBJECT-TYPE
    SYNTAX		Integer32
    MAX-ACCESS		read-only
    STATUS		current
    DESCRIPTION         "Logical volume capacity
			in gibibytes."
    ::= { nasLVEntry 5 }

nasLVCapacityLow	OBJECT-TYPE
    SYNTAX		Unsigned32
    MAX-ACCESS		read-only
    STATUS		current
    DESCRIPTION         "Logical volume capacity in bytes.
			Together with nasLVCapacityHigh
			composes 64-bit number."
    ::= { nasLVEntry 6 }

nasLVCapacityHigh	OBJECT-TYPE
    SYNTAX		Unsigned32
    MAX-ACCESS		read-only
    STATUS		current
    DESCRIPTION         "Logical volume capacity in bytes.
			Together with nasLVCapacityLow
			composes 64-bit number."
    ::= { nasLVEntry 7 }

nasLVUsedGiB		OBJECT-TYPE
    SYNTAX		Integer32
    MAX-ACCESS		read-only
    STATUS		current
    DESCRIPTION         "Used logical volume in gibibytes."
    ::= { nasLVEntry 8 }

nasLVUsedLow		OBJECT-TYPE
    SYNTAX		Unsigned32
    MAX-ACCESS		read-only
    STATUS		current
    DESCRIPTION         "Used logical volume in bytes.
			Together with nasLVUsedHigh composes
			64-bit number."
    ::= { nasLVEntry 9 }

nasLVUsedHigh		OBJECT-TYPE
    SYNTAX		Unsigned32
    MAX-ACCESS		read-only
    STATUS		current
    DESCRIPTION         "Used logical volume in bytes.
			Together with nasLVUsedLow composes
			64-bit number."
    ::= { nasLVEntry 10 }

nasPVTable		OBJECT-TYPE
    SYNTAX		SEQUENCE OF NasPVEntry
    MAX-ACCESS		not-accessible
    STATUS		current
    DESCRIPTION		"The table contains information of
			the physical volume."
    ::= { nasVGEntry 6 }

nasPVEntry		OBJECT-TYPE
    SYNTAX		NasPVEntry
    MAX-ACCESS		not-accessible
    STATUS		current
    DESCRIPTION		"An entry for nasPVTable."
    INDEX		{ nasVGIndex, nasPVIndex }
    ::= { nasPVTable 1 }

NasPVEntry ::= SEQUENCE {
    nasPVIndex		Integer32,
    nasPVName		DisplayString
}

nasPVIndex		OBJECT-TYPE
    SYNTAX		Integer32
    MAX-ACCESS		not-accessible
    STATUS		current
    DESCRIPTION		"The index value that uniquely
			identifies nasPVEntry."
    ::= { nasPVEntry 1 }

nasPVName		OBJECT-TYPE
    SYNTAX		DisplayString
    MAX-ACCESS		read-only
    STATUS		current
    DESCRIPTION		"Physical volume name."
    ::= { nasPVEntry 2 }

-- ************************************************************************

-- Failover

-- ************************************************************************
nasFailoverParams	OBJECT IDENTIFIER ::= { teraStationObjects 7 }

nasFailoverRole		OBJECT-TYPE
    SYNTAX		INTEGER {
			    standalone(1),
			    main(2),
			    aloneMain(4),
			    backup(8),
			    aloneBackup(16),
			    maintenanceMain(32),
			    maintenanceBackup(64),
			    emMode(128)
    			}
    MAX-ACCESS		read-only
    STATUS		current
    DESCRIPTION		"The role of the TeraStation in
			failover."
    ::= { nasFailoverParams 1 }

nasFailoverStatus	OBJECT-TYPE
    SYNTAX		INTEGER {
			    idle(0),
			    busy(1),
			    startingMain(2),
			    startingBackup(3),
			    initializing(4),
			    stopping(32)
    			}
    MAX-ACCESS		read-only
    STATUS		current
    DESCRIPTION		"Failover status."
    ::= { nasFailoverParams 2 }

nasFailoverPartner	OBJECT-TYPE
    SYNTAX		IpAddress
    MAX-ACCESS		read-only
    STATUS		current
    DESCRIPTION		"IP address of failover partner."
    ::= { nasFailoverParams 3 }

-- ************************************************************************

-- RPSU

-- ************************************************************************
nasRPSUTable		OBJECT-TYPE
    SYNTAX		SEQUENCE OF NasRpsuEntry
    MAX-ACCESS		not-accessible
    STATUS		current
    DESCRIPTION		"The table contains information of
			the redundant power supply units."
    ::= { teraStationObjects 8 }

nasRPSUEntry		OBJECT-TYPE
    SYNTAX		NasRpsuEntry
    MAX-ACCESS		not-accessible
    STATUS		current
    DESCRIPTION		"An entry for nasRPSUTable.
			Contents of the entry are read
			from miconapl and the entry is
			made at each 'rpsux' line."
    INDEX		{ nasRPSUIndex }
    ::= { nasRPSUTable 1 }

NasRpsuEntry ::= SEQUENCE {
    nasRPSUIndex	Integer32,
    nasRPSUStatus	INTEGER
}

nasRPSUIndex		OBJECT-TYPE
    SYNTAX		Integer32
    MAX-ACCESS		not-accessible
    STATUS		current
    DESCRIPTION		"The index value that uniquely
			identifies nasRPSUEntry."
    ::= { nasRPSUEntry 1 }

nasRPSUStatus		OBJECT-TYPE
    SYNTAX		INTEGER {
			    unknown(-1),
			    fine(1),
			    broken(2)
			}
    MAX-ACCESS		read-only
    STATUS		current
    DESCRIPTION		"The status of the redundant
			power supply unit. This value is
			read from miconapl.
			-'unknown(-1)' means a redundant
			power supply unit is in an unknown
			state.
			-'fine(1)' means a redundant power
			supply unit is working fine.
			-'broken(2)' means a redundant
			power supply unit has failed."
    ::= { nasRPSUEntry 2 }

-- ************************************************************************

-- iSCSI

-- ************************************************************************

nasISCSITable		OBJECT-TYPE
    SYNTAX		SEQUENCE OF NasISCSIEntry
    MAX-ACCESS		not-accessible
    STATUS		current
    DESCRIPTION		"The table contains information of
			the iSCSI (Internet Small Computer
			System Interface)."
    ::= { teraStationObjects 9 }

nasISCSIEntry		OBJECT-TYPE
    SYNTAX		NasISCSIEntry
    MAX-ACCESS		not-accessible
    STATUS		current
    DESCRIPTION		"An entry for nasISCSIParams.
			Contents of the entry are made at
			each 'iSCSIx' line."
    INDEX		{ nasISCSIIndex }
    ::= { nasISCSITable 1 }

NasISCSIEntry ::= SEQUENCE {
    nasISCSIIndex	Integer32,
    nasISCSIName	DisplayString,
    nasISCSIStatus	INTEGER
}

nasISCSIIndex		OBJECT-TYPE
    SYNTAX		Integer32
    MAX-ACCESS		not-accessible
    STATUS		current
    DESCRIPTION		"The index value that uniquely
			identifies nasISCSIEntry."
    ::= { nasISCSIEntry 1 }

nasISCSIName		OBJECT-TYPE
    SYNTAX		DisplayString
    MAX-ACCESS		read-only
    STATUS		current
    DESCRIPTION		"The iSCSI volume name."
    ::= { nasISCSIEntry 2 }

nasISCSIStatus		OBJECT-TYPE
    SYNTAX		INTEGER {
			    unknown (-1),
			    connected (1),
			    standing-by (2)
			}
    MAX-ACCESS		read-only
    STATUS		current
    DESCRIPTION		"The connection status of the iSCSI
			volume.
			-'unknown(-1)' means the iSCSI
			volume is in an unknown state.
			-'connected(1)' means the iSCSI
			volume is connected via the iSCSI
			initiator.
			-'standing-by(2)' means the iSCSI
			volume is disconnected from the
			iSCSI initiator."
    ::= { nasISCSIEntry 3 }

-- ************************************************************************

-- SystemInformation

-- ************************************************************************
nasSystemInformation	OBJECT IDENTIFIER ::= { teraStationObjects 10 }

nasProductName	OBJECT-TYPE
    SYNTAX		OCTET STRING (SIZE (0..255))
    MAX-ACCESS		read-only
    STATUS		current
    DESCRIPTION		"Model name."
    ::= { nasSystemInformation 1 }

nasSerialNumber	OBJECT-TYPE
    SYNTAX		OCTET STRING (SIZE (0..255))
    MAX-ACCESS		read-only
    STATUS		current
    DESCRIPTION		"Serial number."
    ::= { nasSystemInformation 2 }

nasFWVersionMajor	OBJECT-TYPE
    SYNTAX		OCTET STRING (SIZE (0..255))
    MAX-ACCESS		read-only
    STATUS		current
    DESCRIPTION		"Major firmware version."
    ::= { nasSystemInformation 3 }

nasFWVersionMinor	OBJECT-TYPE
    SYNTAX		OCTET STRING (SIZE (0..255))
    MAX-ACCESS		read-only
    STATUS		current
    DESCRIPTION		"Minor firmware version."
    ::= { nasSystemInformation 4 }

nasIsFWUpdateAvailable	OBJECT-TYPE
    SYNTAX		INTEGER {
			    unknown(-1),
			    available(1),
			    unavailable(2),
			    latest(3)
    			}
    MAX-ACCESS		read-only
    STATUS		current
    DESCRIPTION		"Checking whether newer firmware has
			been released."
    ::= { nasSystemInformation 5 }

nasSystemDateAndTime		OBJECT-TYPE
    SYNTAX		DateAndTime
    MAX-ACCESS		read-only
    STATUS		current
    DESCRIPTION		"System date and time."
    ::= { nasSystemInformation 6 }

-- ************************************************************************

-- ServiceStatus

-- ************************************************************************
nasServiceStatus	OBJECT IDENTIFIER ::= { teraStationObjects 11 }

nasServiceStatusSMB	OBJECT-TYPE
    SYNTAX		INTEGER {
			    unknown(-1),
			    on(1),
			    off(2)
    			}
    MAX-ACCESS		read-only
    STATUS		current
    DESCRIPTION		"The SMB setting."
    ::= { nasServiceStatus 1 }

nasServiceStatusDFS	OBJECT-TYPE
    SYNTAX		INTEGER {
			    unknown(-1),
			    on(1),
			    off(2)
    			}
    MAX-ACCESS		read-only
    STATUS		current
    DESCRIPTION		"The DFS setting."
    ::= { nasServiceStatus 2 }

nasServiceStatusAFP	OBJECT-TYPE
    SYNTAX		INTEGER {
			    unknown(-1),
			    on(1),
			    off(2)
    			}
    MAX-ACCESS		read-only
    STATUS		current
    DESCRIPTION		"The AFP setting."
    ::= { nasServiceStatus 3 }

nasServiceStatusFTP	OBJECT-TYPE
    SYNTAX		INTEGER {
			    unknown(-1),
			    on(1),
			    off(2)
    			}
    MAX-ACCESS		read-only
    STATUS		current
    DESCRIPTION		"The FTP setting."
    ::= { nasServiceStatus 4 }

nasServiceStatusSFTP	OBJECT-TYPE
    SYNTAX		INTEGER {
			    unknown(-1),
			    on(1),
			    off(2)
    			}
    MAX-ACCESS		read-only
    STATUS		current
    DESCRIPTION		"The SFTP setting."
    ::= { nasServiceStatus 5 }

nasServiceStatusWebAxs	OBJECT-TYPE
    SYNTAX		INTEGER {
			    unknown(-1),
			    on(1),
			    off(2)
    			}
    MAX-ACCESS		read-only
    STATUS		current
    DESCRIPTION		"The WebAccess setting."
    ::= { nasServiceStatus 6 }

nasServiceStatusNFS	OBJECT-TYPE
    SYNTAX		INTEGER {
			    unknown(-1),
			    on(1),
			    off(2)
    			}
    MAX-ACCESS		read-only
    STATUS		current
    DESCRIPTION		"The NFS setting."
    ::= { nasServiceStatus 7 }

nasServiceStatusRAIDMaintenance	OBJECT-TYPE
    SYNTAX		INTEGER {
			    unknown(-1),
			    on(1),
			    off(2)
    			}
    MAX-ACCESS		read-only
    STATUS		current
    DESCRIPTION		"The RAID scan setting."
    ::= { nasServiceStatus 8 }

nasServiceStatusiSCSI	OBJECT-TYPE
    SYNTAX		INTEGER {
			    unknown(-1),
			    on(1),
			    off(2)
    			}
    MAX-ACCESS		read-only
    STATUS		current
    DESCRIPTION		"The iSCSI setting."
    ::= { nasServiceStatus 9 }

nasServiceStatusDLNAServer	OBJECT-TYPE
    SYNTAX		INTEGER {
			    unknown(-1),
			    on(1),
			    off(2)
    			}
    MAX-ACCESS		read-only
    STATUS		current
    DESCRIPTION		"The DLNA setting."
    ::= { nasServiceStatus 10 }

nasServiceStatusiTunesServer	OBJECT-TYPE
    SYNTAX		INTEGER {
			    unknown(-1),
			    on(1),
			    off(2)
    			}
    MAX-ACCESS		read-only
    STATUS		current
    DESCRIPTION		"The iTunes server setting."
    ::= { nasServiceStatus 11 }

nasServiceStatusSqueezeboxServer	OBJECT-TYPE
    SYNTAX		INTEGER {
			    unknown(-1),
			    on(1),
			    off(2)
    			}
    MAX-ACCESS		read-only
    STATUS		current
    DESCRIPTION		"The Squeezebox server setting."
    ::= { nasServiceStatus 12 }

nasServiceStatusPrintServer	OBJECT-TYPE
    SYNTAX		INTEGER {
			    unknown(-1),
			    on(1),
			    off(2)
    			}
    MAX-ACCESS		read-only
    STATUS		current
    DESCRIPTION		"The print server setting."
    ::= { nasServiceStatus 13 }

nasServiceStatusWebServer	OBJECT-TYPE
    SYNTAX		INTEGER {
			    unknown(-1),
			    on(1),
			    off(2)
    			}
    MAX-ACCESS		read-only
    STATUS		current
    DESCRIPTION		"The web server setting."
    ::= { nasServiceStatus 14 }

nasServiceStatusMySQLServer	OBJECT-TYPE
    SYNTAX		INTEGER {
			    unknown(-1),
			    on(1),
			    off(2)
    			}
    MAX-ACCESS		read-only
    STATUS		current
    DESCRIPTION		"The MySQL server setting."
    ::= { nasServiceStatus 15 }

nasServiceStatusWebAxsSync	OBJECT-TYPE
    SYNTAX		INTEGER {
			    unknown(-1),
			    on(1),
			    off(2)
    			}
    MAX-ACCESS		read-only
    STATUS		current
    DESCRIPTION		"The WebAccess Remote setting."
    ::= { nasServiceStatus 16 }

nasServiceStatusCloudService	OBJECT-TYPE
    SYNTAX		INTEGER {
			    unknown(-1),
			    on(1),
			    off(2)
    			}
    MAX-ACCESS		read-only
    STATUS		current
    DESCRIPTION		"The cloud storage setting."
    ::= { nasServiceStatus 17 }

nasServiceStatusBitTorrent	OBJECT-TYPE
    SYNTAX		INTEGER {
			    unknown(-1),
			    on(1),
			    off(2)
    			}
    MAX-ACCESS		read-only
    STATUS		current
    DESCRIPTION		"The BitTorrent setting."
    ::= { nasServiceStatus 18 }

nasServiceStatusTeraSearch	OBJECT-TYPE
    SYNTAX		INTEGER {
			    unknown(-1),
			    on(1),
			    off(2)
    			}
    MAX-ACCESS		read-only
    STATUS		current
    DESCRIPTION		"The TeraSearch setting."
    ::= { nasServiceStatus 19 }

nasServiceStatusIpCamera	OBJECT-TYPE
    SYNTAX		INTEGER {
			    unknown(-1),
			    on(1),
			    off(2)
    			}
    MAX-ACCESS		read-only
    STATUS		current
    DESCRIPTION		"The surveillance camera setting."
    ::= { nasServiceStatus 20 }

nasServiceStatusVirusScan	OBJECT-TYPE
    SYNTAX		INTEGER {
			    unknown(-1),
			    on(1),
			    off(2)
    			}
    MAX-ACCESS		read-only
    STATUS		current
    DESCRIPTION		"The virus scan setting."
    ::= { nasServiceStatus 21 }

nasServiceStatusSNMP	OBJECT-TYPE
    SYNTAX		INTEGER {
			    unknown(-1),
			    on(1),
			    off(2)
    			}
    MAX-ACCESS		read-only
    STATUS		current
    DESCRIPTION		"The SNMP setting."
    ::= { nasServiceStatus 22 }

nasServiceStatusTimeMachine	OBJECT-TYPE
    SYNTAX		INTEGER {
			    unknown(-1),
			    on(1),
			    off(2)
    			}
    MAX-ACCESS		read-only
    STATUS		current
    DESCRIPTION		"The Time Machine setting."
    ::= { nasServiceStatus 23 }

nasServiceStatusDirectCopy	OBJECT-TYPE
    SYNTAX		INTEGER {
			    unknown(-1),
			    on(1),
			    off(2)
    			}
    MAX-ACCESS		read-only
    STATUS		current
    DESCRIPTION		"The Direct Copy setting."
    ::= { nasServiceStatus 24 }

nasServiceStatusMailNotification	OBJECT-TYPE
    SYNTAX		INTEGER {
			    unknown(-1),
			    on(1),
			    off(2)
    			}
    MAX-ACCESS		read-only
    STATUS		current
    DESCRIPTION		"The email notification setting."
    ::= { nasServiceStatus 25 }

nasServiceStatusWorkingFolder	OBJECT-TYPE
    SYNTAX		INTEGER {
			    unknown(-1),
			    on(1),
			    off(2)
    			}
    MAX-ACCESS		read-only
    STATUS		current
    DESCRIPTION		"The Working Folder setting."
    ::= { nasServiceStatus 26 }

-- ************************************************************************

-- Notifications

-- ************************************************************************

nasErrorOccur		NOTIFICATION-TYPE
    OBJECTS		{ nasErrorMsg, nasErrorDate, nasErrorDateAndTime }
    STATUS		current
    DESCRIPTION		"Trap that is informed when an
			error event occurs. The error code
			will be displayed as 'Exx' (x will
			be numbers)."
    ::= { teraStationNotifications 1 }

nasInformationOccur	NOTIFICATION-TYPE
    OBJECTS		{ nasInformationMsg, nasInformationDate, nasInformationDateAndTime }
    STATUS		current
    DESCRIPTION		"Trap that is informed when an
			information event occurs. The
			information code will be displayed
			as 'Ixx' (x will be numbers)."
    ::= { teraStationNotifications 2 }


END
