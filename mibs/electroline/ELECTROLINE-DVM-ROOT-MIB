--**************************************************************************
--
--    Copyright 2010 Electroline Equipment Inc
--    All Rights Reserved
--
--
--
--**************************************************************************
--    Filename: dvmRoot.mib
--    Author:   Alain Leclerc
--    Creation Date: 2010.05.18
--
--**************************************************************************
--    Description:
--
--		Root MIB of the DVM branch
--
--**************************************************************************
--    Revision History:
--	  2010.05.18	Alain Leclerc		First Draft
--**************************************************************************

ELECTROLINE-DVM-ROOT-MIB DEFINITIONS ::= BEGIN

IMPORTS
    MODULE-IDENTITY,
    OBJECT-TYPE,
    Integer32
        FROM SNMPv2-SMI
    electrolineHardwareProducts
        FROM ELECTROLINE-GLOBAL-REG;

ModulationType ::= TEXTUAL-CONVENTION
       STATUS          current
       DESCRIPTION
           ""
       SYNTAX          INTEGER {
         unknown(-1),
         qam16(0),
         qam64(1),
         qam256(2),
         qam1024(3),
         qam32(4),
         qam128(5),
         qpsk(6)
       }

electrolineDVM MODULE-IDENTITY
    LAST-UPDATED "201005180000Z"
    ORGANIZATION "Electroline Equipment Inc"
    CONTACT-INFO
        "Alain Leclerc"
    DESCRIPTION
        "Electroline DOCSIS HMS Transponder MIBS"
    REVISION      "200303200000Z"
    DESCRIPTION
            "Initial version of this MIB module."
    ::= { electrolineHardwareProducts 3 }


-- /*************
-- * MAIN MENUS *
-- **************/
dvmInventory OBJECT-IDENTITY
	STATUS current
	DESCRIPTION "Sub-tree for device identification"
	::= { electrolineDVM 1 }

dvmConfiguration OBJECT-IDENTITY
	STATUS current
	DESCRIPTION "Sub-tree for DVM Configuration Parameters"
	::= { electrolineDVM 2 }

dvmStatus OBJECT-IDENTITY
	STATUS current
	DESCRIPTION "Sub-tree for DVM Status and troubleshooting information"
	::= { electrolineDVM 3 }

dvmPrivate OBJECT-IDENTITY
	STATUS current
	DESCRIPTION "Sub-tree for private factory MIBS"
	::= { electrolineDVM 4 }

END
