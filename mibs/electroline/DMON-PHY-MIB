DMON-PHY-MIB DEFINITIONS ::= BEGIN

IMPORTS
        MODULE-IDENTITY,
        OBJECT-TYPE,
        IpAddress,
        Unsigned32,
        Integer32,
        Counter32,
        enterprises
                FROM SNMPv2-SMI
        RowStatus,
        DateAndTime,
        TimeInterval,
        StorageType,
        TruthValue
                FROM SNMPv2-TC
        OBJECT-GROUP,
        MODULE-COMPLIANCE
                FROM SNMPv2-CONF
        TenthdB,
        TenthdBmV,
        DocsEqualizerData
                FROM DOCS-IF-MIB
        ModulationType,
        dmonMib
                FROM DMON-MIB;


dmonPhyGroup MODULE-IDENTITY
        LAST-UPDATED    "201111041400Z"
        ORGANIZATION    ""
        CONTACT-INFO
            "
             Postal:
             E-mail: "
        DESCRIPTION
            "
            This is the MIB module for DMON PHY measurement.

            History
              MG - 09/09/2011
                -Updated UNITS from centidBmV to TenthdBmV
                -Updated MER OIDS UNITS from TenthdBmV to TenthdB
              MG - 09/23/2011
                -Change units from billionth to trillionth

              MG - 11/04/2011
                -Added
                  -dmonPhyInfoManagement
                    -dmonPhyInfoMgtHistoryRetention

                -Change UNITS from TenthdBmv to dBmv
                -Change UNITS from TenthdB to dB
            "

        ::= { dmonMib 1 }


--
-- The following group defines the managment of the DMon Phy History Management
--

dmonPhyInfoManagement OBJECT IDENTIFIER ::= { dmonPhyGroup 1 }

dmonPhyInfoMgtHistoryRetention OBJECT-TYPE
     SYNTAX     Unsigned32 (3600..10000000000)
     UNITS      "seconds"
     MAX-ACCESS read-write
     STATUS current
     DESCRIPTION
          "The total amount of seconds that the DMon must retain PHY History in RAM memory.
            Once this OID value is set, it MUST be preserved in non-volatile memory
            and required a reboot to go into effect.
            The DMon MUST retain a Minimum of 3600 seconds of history
         "
     DEFVAL {86400} -- 24Hours
::= { dmonPhyInfoManagement 1 }


dmonPhyInfoTable OBJECT-TYPE
     SYNTAX      SEQUENCE OF DmonPhyInfoEntry
     MAX-ACCESS  not-accessible
     STATUS      current
     DESCRIPTION
            "This table describes the attributes of downstream
             channels (frequency bands)."
     ::= { dmonPhyGroup 2 }

dmonPhyInfoEntry OBJECT-TYPE
     SYNTAX      DmonPhyInfoEntry
     MAX-ACCESS  not-accessible
     STATUS      current
     DESCRIPTION
            "An entry provides a list of attributes for a single
             downstream channel.
             An entry in this table exists for each downstream channel"
     INDEX { dmonPhyChannelIndex }
     ::= { dmonPhyInfoTable 1 }

DmonPhyInfoEntry ::= SEQUENCE {
      dmonPhyChannelIndex                 Integer32,
      dmonPhyChannelLockedtime            DateAndTime,
      dmonPhyChannelFrequency             Integer32,
      dmonPhyChannelModulation            ModulationType,
      dmonPhyChannelPower                 TenthdBmV,
      dmonPhyChannelAnnex                 INTEGER,
      dmonPhyChannelSigQUnerroreds        Counter32,
      dmonPhyChannelSigQCorrecteds        Counter32,
      dmonPhyChannelSigQUncorrectables    Counter32,
      dmonPhyChannelSigQMER               TenthdB,
      dmonPhyChannelSigQPreFECBER         Integer32,
      dmonPhyChannelSigQPostFECBER        Integer32,
      dmonPhyChannelSigQCER               Integer32,
      dmonPhyChannelSigQECR               Integer32,
      dmonPhyChannelInterleave            INTEGER,
      dmonPhyChannelSigQEqualizationData  DocsEqualizerData,
      dmonPhyChannelSigScanId             Integer32,
      dmonPhyChannelPowerMin              TenthdBmV,
      dmonPhyChannelPowerMax              TenthdBmV,
      dmonPhyChannelSigQMERMin            TenthdB,
      dmonPhyChannelSigQMERMax            TenthdB,
      dmonPhyChannelScanMode              INTEGER,
      dmonPhyChannelQAMlocked             TruthValue,
      dmonPhyChannelFEClocked             TruthValue
     }

dmonPhyChannelIndex OBJECT-TYPE
     SYNTAX      Integer32 (1..255)
     MAX-ACCESS  not-accessible
     STATUS      current
     DESCRIPTION
            "The downstream channel index starting from 1."
     ::= { dmonPhyInfoEntry 1 }

dmonPhyChannelLockedtime OBJECT-TYPE
        SYNTAX      DateAndTime
        MAX-ACCESS  read-only
        STATUS      current
        DESCRIPTION
            "The date and time of the reading"
        ::= { dmonPhyInfoEntry 2 }

dmonPhyChannelFrequency OBJECT-TYPE
     SYNTAX      Integer32 (0..1000000000)
     UNITS       "hertz"
     MAX-ACCESS  read-only
     STATUS      current
     DESCRIPTION
            "The center of the downstream frequency associated with
             this channel.  This object will return the current tuner
             frequency."
     ::= { dmonPhyInfoEntry 3 }

dmonPhyChannelModulation OBJECT-TYPE
     SYNTAX      ModulationType
     MAX-ACCESS  read-only
     STATUS      current
     DESCRIPTION
            "The modulation type associated with this downstream
             channel.  If the interface is down, this object either
             returns the most current value, or the value of unknown(1)."
     ::= { dmonPhyInfoEntry 4 }

dmonPhyChannelPower OBJECT-TYPE
     SYNTAX      TenthdBmV
     UNITS       "dBmV"
     MAX-ACCESS  read-only
     STATUS      current
     DESCRIPTION
            "The received power level of the channel.
             If the interface is down, this object either returns
             the most current value or the value of 0.  See the reference
             for recommended and required power levels."
     ::= { dmonPhyInfoEntry 5 }

dmonPhyChannelAnnex OBJECT-TYPE
     SYNTAX      INTEGER {
         unknown(-1),
         annexB(0),
         annexA(1)
     }
     MAX-ACCESS  read-only
     STATUS      current
     DESCRIPTION
            "The value of this object indicates the conformance of
             the implementation to important regional cable standards.
             annexA : Annex A from ITU-T J.83 is used.
                      (equivalent to EN 300 429)
             annexB : Annex B from ITU-T J.83 is used.
             annexC : Annex C from ITU-T J.83 is used."
     ::= { dmonPhyInfoEntry 6 }

dmonPhyChannelSigQUnerroreds OBJECT-TYPE
     SYNTAX      Counter32
     UNITS       "codewords"
     MAX-ACCESS  read-only
     STATUS      current
     DESCRIPTION
            "Codewords received on this channel without error."
     ::= { dmonPhyInfoEntry 7 }

dmonPhyChannelSigQCorrecteds OBJECT-TYPE
     SYNTAX      Counter32
     UNITS       "codewords"
     MAX-ACCESS  read-only
     STATUS      current
     DESCRIPTION
            "Codewords received on this channel with correctable
             errors."
     ::= { dmonPhyInfoEntry 8 }

dmonPhyChannelSigQUncorrectables OBJECT-TYPE
     SYNTAX      Counter32
     UNITS       "codewords"
     MAX-ACCESS  read-only
     STATUS      current
     DESCRIPTION
            "Codewords received on this channel with uncorrectable
             errors."
     ::= { dmonPhyInfoEntry 9 }

dmonPhyChannelSigQMER OBJECT-TYPE
     SYNTAX      TenthdB
     UNITS       "dB"
     MAX-ACCESS  read-only
     STATUS      current
     DESCRIPTION
            "Modulation error ratio of the monitored channel"
     REFERENCE
            "Data-Over-Cable Service Interface Specifications: Physical
             Layer Specification CM-SP-PHYv3.0-I07-080522,
             Section 6.2.22.3"
     ::= { dmonPhyInfoEntry 10 }

dmonPhyChannelSigQPreFECBER OBJECT-TYPE
     SYNTAX      Integer32
     UNITS       "trillionth"
     MAX-ACCESS  read-only
     STATUS      current
     DESCRIPTION
         "Bit-error-rate of the monitored channel before FEC repair"
     ::= { dmonPhyInfoEntry 11 }

dmonPhyChannelSigQPostFECBER OBJECT-TYPE
     SYNTAX      Integer32
     UNITS       "trillionth"
     MAX-ACCESS  read-only
     STATUS      current
     DESCRIPTION
         "Bit-error-rate of the monitored channel after FEC repair"
     ::= { dmonPhyInfoEntry 12 }

dmonPhyChannelSigQCER OBJECT-TYPE
     SYNTAX      Integer32
     UNITS       "trillionth"
     MAX-ACCESS  read-only
     STATUS      current
     DESCRIPTION
         "codeword-error-rate of the monitored channel"
     ::= { dmonPhyInfoEntry 13 }

dmonPhyChannelSigQECR OBJECT-TYPE
     SYNTAX      Integer32
     UNITS       "trillionth"
     MAX-ACCESS  read-only
     STATUS      current
     DESCRIPTION
         "codeword error-corrected-rate of the monitored channel"
     ::= { dmonPhyInfoEntry 14 }

dmonPhyChannelInterleave OBJECT-TYPE
     SYNTAX      INTEGER {
         unknown(1),
         other(2),
         taps8Increment16(3),
         taps16Increment8(4),
         taps32Increment4(5),
         taps64Increment2(6),
         taps128Increment1(7),
         taps12increment17(8),
         taps128Increment2(9),
         taps128Increment3(10),
         taps128Increment4(11),
         taps128Increment5(12),
         taps128Increment6(13),
         taps128Increment7(14),
         taps128Increment8(15)
     }
     MAX-ACCESS  read-only
     STATUS      current
     DESCRIPTION
            "The Forward Error Correction (FEC) interleaving used
             for this downstream channel.
             Values are defined as follows:
             taps8Increment16(3):   protection 5.9/4.1 usec,
                                    latency .22/.15 msec
             taps16Increment8(4):   protection 12/8.2 usec,
                                    latency .48/.33 msec
             taps32Increment4(5):   protection 24/16 usec,
                                    latency .98/.68 msec
             taps64Increment2(6):   protection 47/33 usec,
                                    latency 2/1.4 msec
             taps128Increment1(7):  protection 95/66 usec,
                                    latency 4/2.8 msec
             taps12increment17(8):  protection 18/14 usec,
                                    latency 0.43/0.32 msec

            The value 'taps12increment17' is supported by EuroDOCSIS
            cable systems only, and the others by DOCSIS cable systems.

             If the interface is down, this object either returns
             the configured value (CMTS), the most current value (CM),
             or the value of unknown(1).
             The value of other(2) is returned if the interleave
             is known but not defined in the above list.
             See the associated conformance object for write
             conditions and limitations.  See the reference for the FEC
             configuration described by the setting of this object."

     ::= { dmonPhyInfoEntry 15 }

dmonPhyChannelSigQEqualizationData OBJECT-TYPE
        SYNTAX      DocsEqualizerData
        MAX-ACCESS  read-only
        STATUS      current
        DESCRIPTION
               "This object returns the equalization data for
                the downstream channel."
        ::= { dmonPhyInfoEntry 16 }

dmonPhyChannelSigScanId OBJECT-TYPE
     SYNTAX      Integer32
     MAX-ACCESS  read-only
     STATUS      current
     DESCRIPTION
         "Id generated by the dmon to identify a set of data.  This Id will be send in the scan finish message.
         It will help the CPS to identify the data set."
     ::= { dmonPhyInfoEntry 17 }

dmonPhyChannelPowerMin OBJECT-TYPE
     SYNTAX      TenthdBmV
     UNITS       "dBmV"
     MAX-ACCESS  read-only
     STATUS      current
     DESCRIPTION
            "The min value of the received power level of the channel
             during the dwelling time."
     ::= { dmonPhyInfoEntry 18 }

dmonPhyChannelPowerMax OBJECT-TYPE
     SYNTAX      TenthdBmV
     UNITS       "dBmV"
     MAX-ACCESS  read-only
     STATUS      current
     DESCRIPTION
            "The max value of the received power level of the channel
             during the dwelling time."
     ::= { dmonPhyInfoEntry 19 }

dmonPhyChannelSigQMERMin OBJECT-TYPE
     SYNTAX      TenthdB
     UNITS       "dB"
     MAX-ACCESS  read-only
     STATUS      current
     DESCRIPTION
            "The min value of the modulation error ratio of the monitored channel
       during the dwelling time."
     ::= { dmonPhyInfoEntry 20 }

dmonPhyChannelSigQMERMax OBJECT-TYPE
     SYNTAX      TenthdB
     UNITS       "dB"
     MAX-ACCESS  read-only
     STATUS      current
     DESCRIPTION
            "The max value of the modulation error ratio of the monitored channel
       during the dwelling time."
     ::= { dmonPhyInfoEntry 21 }

dmonPhyChannelScanMode OBJECT-TYPE
     SYNTAX      INTEGER {
         defaultScan (0),
         fastScan (2)
     }
     MAX-ACCESS  read-only
     STATUS      current
     DESCRIPTION
            "The value of this object indicates the result of the
             measurement is from."
     ::= { dmonPhyInfoEntry 22 }

dmonPhyChannelQAMlocked OBJECT-TYPE
        SYNTAX      TruthValue
        MAX-ACCESS  read-only
        STATUS      current
        DESCRIPTION
            "Indicates whether QAM is locked. If not locked, Most of the
       columns in this entry are not valid."
        DEFVAL { false }
     ::= { dmonPhyInfoEntry 23 }

dmonPhyChannelFEClocked OBJECT-TYPE
        SYNTAX      TruthValue
        MAX-ACCESS  read-only
        STATUS      current
        DESCRIPTION
            "Indicates whether FEC is locked. If not locked, post FEC values
       in this entry are not valid."
        DEFVAL { false }
     ::= { dmonPhyInfoEntry 24 }

dmonPhyHistoryInfoTable OBJECT-TYPE
     SYNTAX      SEQUENCE OF DmonPhyHistoryInfoEntry
     MAX-ACCESS  not-accessible
     STATUS      current
     DESCRIPTION
            "This table describes the history attributes of downstream
             channels (frequency bands)."
     ::= { dmonPhyGroup 3 }

dmonPhyHistoryInfoEntry OBJECT-TYPE
     SYNTAX      DmonPhyHistoryInfoEntry
     MAX-ACCESS  not-accessible
     STATUS      current
     DESCRIPTION
            "An entry provides a list of history attributes for a single
             downstream channel.
             An entry in this table exists for each downstream channel"
     INDEX {
             dmonPhyHistoryChannelIndex,
             dmonPhyHistoryIndex
           }
     ::= { dmonPhyHistoryInfoTable 1 }

DmonPhyHistoryInfoEntry ::= SEQUENCE {
        dmonPhyHistoryChannelIndex                  Integer32,
        dmonPhyHistoryIndex                         Integer32,
        dmonPhyHistoryChannelLockedtime             DateAndTime,
        dmonPhyHistoryChannelFrequency              Integer32,
        dmonPhyHistoryChannelModulation             ModulationType,
        dmonPhyHistoryChannelPower                  TenthdBmV,
        dmonPhyHistoryChannelAnnex                  INTEGER,
        dmonPhyHistoryChannelSigQUnerroreds         Counter32,
        dmonPhyHistoryChannelSigQCorrecteds         Counter32,
        dmonPhyHistoryChannelSigQUncorrectables     Counter32,
        dmonPhyHistoryChannelSigQMER                TenthdB,
        dmonPhyHistoryChannelSigQPreFECBER          Integer32,
        dmonPhyHistoryChannelSigQPostFECBER         Integer32,
        dmonPhyHistoryChannelSigQCER                Integer32,
        dmonPhyHistoryChannelSigQECR                Integer32,
        dmonPhyHistoryChannelInterleave             INTEGER,
        dmonPhyHistoryChannelSigQEqualizationData   DocsEqualizerData,
        dmonPhyHistoryChannelSigScanId              Integer32,
        dmonPhyHistoryChannelPowerMin               TenthdBmV,
        dmonPhyHistoryChannelPowerMax               TenthdBmV,
        dmonPhyHistoryChannelSigQMERMin             TenthdB,
        dmonPhyHistoryChannelSigQMERMax             TenthdB,
        dmonPhyHistoryChannelScanMode               INTEGER,
        dmonPhyHistoryChannelQAMlocked              TruthValue,
        dmonPhyHistoryChannelFEClocked              TruthValue
     }

dmonPhyHistoryChannelIndex OBJECT-TYPE
     SYNTAX      Integer32 (1..255)
     MAX-ACCESS  not-accessible
     STATUS      current
     DESCRIPTION
            "The history downstream channel index starting from 1."
     ::= { dmonPhyHistoryInfoEntry 1 }

dmonPhyHistoryIndex OBJECT-TYPE
     SYNTAX      Integer32 (1..9)
     MAX-ACCESS  not-accessible
     STATUS      current
     DESCRIPTION
            "The history index starting from 1."
     ::= { dmonPhyHistoryInfoEntry 2 }

dmonPhyHistoryChannelLockedtime OBJECT-TYPE
        SYNTAX      DateAndTime
        MAX-ACCESS  read-only
        STATUS      current
        DESCRIPTION
            "The history date and time of the reading"
        ::= { dmonPhyHistoryInfoEntry 3 }

dmonPhyHistoryChannelFrequency OBJECT-TYPE
     SYNTAX      Integer32 (0..1000000000)
     UNITS       "hertz"
     MAX-ACCESS  read-only
     STATUS      current
     DESCRIPTION
            "The history center of the downstream frequency associated with
             this channel.  This object will return the current tuner
             frequency."
     ::= { dmonPhyHistoryInfoEntry 4 }

dmonPhyHistoryChannelModulation OBJECT-TYPE
     SYNTAX      ModulationType
     MAX-ACCESS  read-only
     STATUS      current
     DESCRIPTION
            "The history modulation type associated with this downstream
             channel.  If the interface is down, this object either
             returns the most current value, or the value of unknown(1)."
     ::= { dmonPhyHistoryInfoEntry 5 }

dmonPhyHistoryChannelPower OBJECT-TYPE
     SYNTAX      TenthdBmV
     UNITS       "dBmV"
     MAX-ACCESS  read-only
     STATUS      current
     DESCRIPTION
            "The history received power level of the channel.
             If the interface is down, this object either returns
             the most current value or the value of 0.  See the reference
             for recommended and required power levels."
     ::= { dmonPhyHistoryInfoEntry 6 }

dmonPhyHistoryChannelAnnex OBJECT-TYPE
     SYNTAX      INTEGER {
         unknown(-1),
         annexB(0),
         annexA(1)
     }
     MAX-ACCESS  read-only
     STATUS      current
     DESCRIPTION
            "The history value of this object indicates the conformance of
             the implementation to important regional cable standards.
             annexA : Annex A from ITU-T J.83 is used.
                      (equivalent to EN 300 429)
             annexB : Annex B from ITU-T J.83 is used.
             annexC : Annex C from ITU-T J.83 is used."
     ::= { dmonPhyHistoryInfoEntry 7 }

dmonPhyHistoryChannelSigQUnerroreds OBJECT-TYPE
     SYNTAX      Counter32
     UNITS       "codewords"
     MAX-ACCESS  read-only
     STATUS      current
     DESCRIPTION
            "The history codewords received on this channel without error."
     ::= { dmonPhyHistoryInfoEntry 8 }

dmonPhyHistoryChannelSigQCorrecteds OBJECT-TYPE
     SYNTAX      Counter32
     UNITS       "codewords"
     MAX-ACCESS  read-only
     STATUS      current
     DESCRIPTION
            "The history codewords received on this channel with correctable
             errors."
     ::= { dmonPhyHistoryInfoEntry 9 }

dmonPhyHistoryChannelSigQUncorrectables OBJECT-TYPE
     SYNTAX      Counter32
     UNITS       "codewords"
     MAX-ACCESS  read-only
     STATUS      current
     DESCRIPTION
            "The history codewords received on this channel with uncorrectable
             errors."
     ::= { dmonPhyHistoryInfoEntry 10 }

dmonPhyHistoryChannelSigQMER OBJECT-TYPE
     SYNTAX      TenthdB
     UNITS       "dB"
     MAX-ACCESS  read-only
     STATUS      current
     DESCRIPTION
            "The history modulation error ratio of the monitored channel"
     REFERENCE
            "Data-Over-Cable Service Interface Specifications: Physical
             Layer Specification CM-SP-PHYv3.0-I07-080522,
             Section 6.2.22.3"
     ::= { dmonPhyHistoryInfoEntry 11 }

dmonPhyHistoryChannelSigQPreFECBER OBJECT-TYPE
     SYNTAX      Integer32
     UNITS       "trillionth"
     MAX-ACCESS  read-only
     STATUS      current
     DESCRIPTION
         "The history bit-error-rate of the monitored channel before FEC repair"
     ::= { dmonPhyHistoryInfoEntry 12 }

dmonPhyHistoryChannelSigQPostFECBER OBJECT-TYPE
     SYNTAX      Integer32
     UNITS       "trillionth"
     MAX-ACCESS  read-only
     STATUS      current
     DESCRIPTION
         "The history bit-error-rate of the monitored channel after FEC repair"
     ::= { dmonPhyHistoryInfoEntry 13 }

dmonPhyHistoryChannelSigQCER OBJECT-TYPE
     SYNTAX      Integer32
     UNITS       "trillionth"
     MAX-ACCESS  read-only
     STATUS      current
     DESCRIPTION
         "The history codeword-error-rate of the monitored channel"
     ::= { dmonPhyHistoryInfoEntry 14 }

dmonPhyHistoryChannelSigQECR OBJECT-TYPE
     SYNTAX      Integer32
     UNITS       "trillionth"
     MAX-ACCESS  read-only
     STATUS      current
     DESCRIPTION
         "The history codeword error-corrected-rate of the monitored channel"
     ::= { dmonPhyHistoryInfoEntry 15 }

dmonPhyHistoryChannelInterleave OBJECT-TYPE
     SYNTAX      INTEGER {
         unknown(1),
         other(2),
         taps8Increment16(3),
         taps16Increment8(4),
         taps32Increment4(5),
         taps64Increment2(6),
         taps128Increment1(7),
         taps12increment17(8),
         taps128Increment2(9),
         taps128Increment3(10),
         taps128Increment4(11),
         taps128Increment5(12),
         taps128Increment6(13),
         taps128Increment7(14),
         taps128Increment8(15)
     }
     MAX-ACCESS  read-only
     STATUS      current
     DESCRIPTION
            "The history Forward Error Correction (FEC) interleaving used
             for this downstream channel.
             Values are defined as follows:
             taps8Increment16(3):   protection 5.9/4.1 usec,
                                    latency .22/.15 msec
             taps16Increment8(4):   protection 12/8.2 usec,
                                    latency .48/.33 msec
             taps32Increment4(5):   protection 24/16 usec,
                                    latency .98/.68 msec
             taps64Increment2(6):   protection 47/33 usec,
                                    latency 2/1.4 msec
             taps128Increment1(7):  protection 95/66 usec,
                                    latency 4/2.8 msec
             taps12increment17(8):  protection 18/14 usec,
                                    latency 0.43/0.32 msec

            The value 'taps12increment17' is supported by EuroDOCSIS
            cable systems only, and the others by DOCSIS cable systems.

             If the interface is down, this object either returns
             the configured value (CMTS), the most current value (CM),
             or the value of unknown(1).
             The value of other(2) is returned if the interleave
             is known but not defined in the above list.
             See the associated conformance object for write
             conditions and limitations.  See the reference for the FEC
             configuration described by the setting of this object."

     ::= { dmonPhyHistoryInfoEntry 16 }

dmonPhyHistoryChannelSigQEqualizationData OBJECT-TYPE
        SYNTAX      DocsEqualizerData
        MAX-ACCESS  read-only
        STATUS      current
        DESCRIPTION
               "This object returns the hisotry equalization data for
                the downstream channel."
        ::= { dmonPhyHistoryInfoEntry 17 }

dmonPhyHistoryChannelSigScanId OBJECT-TYPE
     SYNTAX      Integer32
     MAX-ACCESS  read-only
     STATUS      current
     DESCRIPTION
         "Id generated by the dmon to identify a set of data.  This Id will be send in the scan finish message.
         It will help the CPS to identify the data set."
     ::= { dmonPhyHistoryInfoEntry 18 }

dmonPhyHistoryChannelPowerMin OBJECT-TYPE
     SYNTAX      TenthdBmV
     UNITS       "dBmV"
     MAX-ACCESS  read-only
     STATUS      current
     DESCRIPTION
            "The min value of the received power level of the channel
             during the dwelling time."
     ::= { dmonPhyHistoryInfoEntry 19 }

dmonPhyHistoryChannelPowerMax OBJECT-TYPE
     SYNTAX      TenthdBmV
     UNITS       "dBmV"
     MAX-ACCESS  read-only
     STATUS      current
     DESCRIPTION
            "The max value of the received power level of the channel
             during the dwelling time."
     ::= { dmonPhyHistoryInfoEntry 20 }

dmonPhyHistoryChannelSigQMERMin OBJECT-TYPE
     SYNTAX      TenthdB
     UNITS       "dB"
     MAX-ACCESS  read-only
     STATUS      current
     DESCRIPTION
            "The min value of the modulation error ratio of the monitored channel
       during the dwelling time."
     ::= { dmonPhyHistoryInfoEntry 21 }

dmonPhyHistoryChannelSigQMERMax OBJECT-TYPE
     SYNTAX      TenthdB
     UNITS       "dB"
     MAX-ACCESS  read-only
     STATUS      current
     DESCRIPTION
            "The max value of the modulation error ratio of the monitored channel
       during the dwelling time."
     ::= { dmonPhyHistoryInfoEntry 22 }

dmonPhyHistoryChannelScanMode OBJECT-TYPE
     SYNTAX      INTEGER {
         defaultScan (0),
         fastScan (2)
     }
     MAX-ACCESS  read-only
     STATUS      current
     DESCRIPTION
            "The value of this object indicates the result of the
             measurement is from."
     ::= { dmonPhyHistoryInfoEntry 23 }

dmonPhyHistoryChannelQAMlocked OBJECT-TYPE
        SYNTAX      TruthValue
        MAX-ACCESS  read-only
        STATUS      current
        DESCRIPTION
            "Indicates whether QAM is locked. If not locked, Most of the
       columns in this entry are not valid."
        DEFVAL { false }
     ::= { dmonPhyHistoryInfoEntry 24 }

dmonPhyHistoryChannelFEClocked OBJECT-TYPE
        SYNTAX      TruthValue
        MAX-ACCESS  read-only
        STATUS      current
        DESCRIPTION
            "Indicates whether FEC is locked. If not locked, post FEC values
       in this entry are not valid."
        DEFVAL { false }
     ::= { dmonPhyHistoryInfoEntry 25 }

END
