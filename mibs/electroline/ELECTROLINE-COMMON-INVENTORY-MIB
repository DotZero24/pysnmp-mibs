--*****************************************************************************
--
--    Copyright 2014 Electroline Equipment Inc.
--    All Rights Reserved
--
--
--*****************************************************************************
--    Filename: ELECTROLINE-COMMON-INVENTORY.mib
--    Author:   Alain Leclerc
--    Creation Date: 2004-01-14
--*****************************************************************************
--    Description:
--
--     SNMPv2 Inventory branch MIB definition for electroline product.
--
--*****************************************************************************
--    Revision History:
--	  2014-01-14	Alain Leclerc		First draft
--*****************************************************************************

ELECTROLINE-COMMON-INVENTORY-MIB DEFINITIONS ::= BEGIN

IMPORTS
    MODULE-IDENTITY,
    OBJECT-TYPE,
    Integer32 	   FROM SNMPv2-SMI
	DateAndTime    FROM SNMPv2-TC
    commonInventory   FROM ELECTROLINE-COMMON-ROOT-MIB;

--*****************************************************************************
-- * GLOBAL INVENTORY DATA
-- *
-- * The following information is used to determine the type of PCB / Assembly
-- * and its revision number.  Additional information required by the DHT
-- * software for proper operation on all board variations is also stored here.
-- *
-- * The values defined for these MIBs are kept in a separate document.
--*****************************************************************************

invHwType OBJECT-TYPE
    SYNTAX   	INTEGER
    MAX-ACCESS  read-only
    STATUS      current
    DESCRIPTION
       "Hardware Model Identification Number. This information is used by the
       software to differentiate the hardware platform on which it is running.
       For example, the HMS022 compatible version and the legacy version of the DHT
       have different hardware types."
    ::= { commonInventory 1 }

invHwMinorRev OBJECT-TYPE
    SYNTAX   	INTEGER
    MAX-ACCESS  read-only
    STATUS      current
    DESCRIPTION
       "Hardware Revision Identification Number, representing the PCB version
       and / or the assembly modification level."
    ::= { commonInventory 2 }

invHwMajorRev OBJECT-TYPE
	SYNTAX 		INTEGER
	MAX-ACCESS	read-only
	STATUS		current
	DESCRIPTION
		"This information is used to represent a family of hardware revisions.
		 Major functional changes will trigger a modification of this value"
	::= { commonInventory 3 }

invHwDrvRev OBJECT-TYPE
    SYNTAX   	INTEGER
    MAX-ACCESS  read-only
    STATUS      current
    DESCRIPTION
       "This information is used to track any changes in the manufacturing process
	    not covered by a PCB/Assembly revision and that have an impact on the drivers.
       "
    ::= { commonInventory 4 }

modelNumber  OBJECT-TYPE
     SYNTAX OCTET STRING (SIZE(0..255))
     ACCESS read-only
     STATUS current
     DESCRIPTION
          "Displays the private electroline model number.
          Displayed in human-readable format."
     ::= { commonInventory 5 }

--*****************************************************************************
-- * MANUFACTURING INVENTORY DATA
-- *
-- * This section contains additional manufacturing process related information
-- * for tracking purposes.
--*****************************************************************************
manufacturingInfo OBJECT-IDENTITY
	STATUS current
	DESCRIPTION "Electroline Private sub-tree to access manufacturing information"
	::= { commonInventory 10 }

mfcDateTime OBJECT-TYPE
	SYNTAX 		DateAndTime
	MAX-ACCESS	read-only
	STATUS		current
	DESCRIPTION
		"Date and time when this unit was tested (in a string format)."
	::= { manufacturingInfo 1 }

mfcTestSwVersion OBJECT-TYPE
	SYNTAX 		OCTET STRING
	MAX-ACCESS	read-only
	STATUS		current
	DESCRIPTION
		"Version of the test station on which this unit was tested."
	::= { manufacturingInfo 2 }
END
