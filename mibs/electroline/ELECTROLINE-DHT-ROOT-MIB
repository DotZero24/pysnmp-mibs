--**************************************************************************
--
--    Copyright 2003 Electroline Equipment Inc
--    All Rights Reserved
--
--
--
--**************************************************************************
--    Filename: dhtRoot.mib
--    Author:   Eric Alarie
--    Creation Date: 2003.03.20
--
--**************************************************************************
--    Description:
--
--		Root MIB of the DHT branch
--
--**************************************************************************
--    Revision History:
--	  2003.03.20	Eric Alarie		First Draft
--**************************************************************************

ELECTROLINE-DHT-ROOT-MIB DEFINITIONS ::= BEGIN

IMPORTS
    MODULE-IDENTITY,
    OBJECT-TYPE,
    Integer32
        FROM SNMPv2-SMI
    electrolineHardwareProducts
        FROM ELECTROLINE-GLOBAL-REG;

electrolineDHT MODULE-IDENTITY
    LAST-UPDATED "200303200000Z"
    ORGANIZATION "Electroline Equipment Inc"
    CONTACT-INFO
        "Eric Alarie"
    DESCRIPTION
        "Electroline DOCSIS HMS Transponder MIBS"
    REVISION      "200303200000Z"
    DESCRIPTION
            "Initial version of this MIB module."
    ::= { electrolineHardwareProducts 2 }


-- /*************
-- * MAIN MENUS *
-- **************/
dhtInventory OBJECT-IDENTITY
	STATUS current
	DESCRIPTION "Sub-tree for device identification"
	::= { electrolineDHT 1 }

dhtConfiguration OBJECT-IDENTITY
	STATUS current
	DESCRIPTION "Sub-tree for DHT Configuration Parameters"
	::= { electrolineDHT 2 }

dhtStatus OBJECT-IDENTITY
	STATUS current
	DESCRIPTION "Sub-tree for DHT Status and troubleshooting information"
	::= { electrolineDHT 3 }

dhtPrivate OBJECT-IDENTITY
	STATUS current
	DESCRIPTION "Sub-tree for private factory MIBS"
	::= { electrolineDHT 4 }

dhtExtensionsMib OBJECT-IDENTITY
	STATUS current
	DESCRIPTION "Sub-tree for DHT Extension Root MIB"
	::= { electrolineDHT 5 }
END
