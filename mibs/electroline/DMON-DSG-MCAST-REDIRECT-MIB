DMON-DSG-MCAST-REDIRECT-MIB DEFINITIONS ::= BEGIN

IMPORTS
        MODULE-IDENTITY,
        OBJECT-TYPE,
        Unsigned32,
        Counter32
                FROM SNMPv2-SMI

        InetAddress ,
        InetPortNumber
                FROM INET-ADDRESS-MIB

        OBJECT-GROUP,
        MODULE-COMPLIANCE
                FROM SNMPv2-CONF
        dmonMib
                FROM DMON-MIB

        dsgIfStdTunnelFilterIndex
                FROM DSG-IF-STD-MIB;

dmonDsgMcastRedirectGroup MODULE-IDENTITY
        LAST-UPDATED    "201111081500Z"
        ORGANIZATION    ""
        CONTACT-INFO
            "
             Postal:
             E-mail: "
        DESCRIPTION
            "
            This is the MIB module for DMON DSG Multicast Stream Redirection.

            History

              11/08/2011 -Maurice Garcia
                -Syntax Error Change
                  -dmonDsgMcastRedirectOperStatus

            "

        ::= { dmonMib 3 }

dmonDsgMcastRedirectInfoTable OBJECT-TYPE
     SYNTAX      SEQUENCE OF DmonDsgMcastRedirectInfoEntry
     MAX-ACCESS  not-accessible
     STATUS      current
     DESCRIPTION
            "This table describes the attributes of DSG Multicast Redirect Object."
     ::= { dmonDsgMcastRedirectGroup 1 }

dmonDsgMcastRedirectInfoEntry OBJECT-TYPE
     SYNTAX      DmonDsgMcastRedirectInfoEntry
     MAX-ACCESS  not-accessible
     STATUS      current
     DESCRIPTION
            "An entry provides a list of attributes "
     INDEX {dsgIfStdTunnelFilterIndex}

     ::= { dmonDsgMcastRedirectInfoTable 1 }

DmonDsgMcastRedirectInfoEntry ::= SEQUENCE {
      dmonDsgMcastRedirectOperStatus    INTEGER ,
      dmonDsgMcastRedirectAdminStatus   INTEGER ,
      dmonDsgMcastRedirectSrcPort       InetPortNumber ,
      dmonDsgMcastRedirectSrcInetAddr   InetAddress ,
      dmonDsgMcastRedirectDestPort      InetPortNumber ,
      dmonDsgMcastRedirectDestInetAddr  InetAddress ,
      dmonDsgMcastRedirectDuration      Integer32 ,
      dmonDsgMcastRedirectPktCounter    Counter32
}

dmonDsgMcastRedirectOperStatus OBJECT-TYPE
    SYNTAX      INTEGER {
         failed(-1) ,
         inActive(0),
         active(1)

    }
    MAX-ACCESS  read-only
    STATUS      current
     DESCRIPTION
            "
             Status
               failed:    Unable to initate redirect traffic
               inActive:  No actice redirect traffic
               active:    Traffic being redirected
            "
     ::= { dmonDsgMcastRedirectInfoEntry 1 }

dmonDsgMcastRedirectAdminStatus OBJECT-TYPE
    SYNTAX      INTEGER {
         stop(0),
         start(1)
    }
    MAX-ACCESS  read-write
    STATUS      current
     DESCRIPTION
            "
              By default the dmonDsgMcastRedirectAdminStatus is set to stop
              Setting the dmonDsgMcastRedirectAdminStatus to start will initiate
              redirect traffic for the duration set by dmonDsgMcastRedirectDuration.
              Upon expiration of the dmonDsgMcastRedirectDuration, this status will
              revert to a stop status

                stop: Stop current traffic redirection
                start: Start traffic redirection
            "
    DEFVAL { 0 }
     ::= { dmonDsgMcastRedirectInfoEntry 2 }

dmonDsgMcastRedirectSrcPort OBJECT-TYPE
    SYNTAX      InetPortNumber
    MAX-ACCESS  read-write
    STATUS      current
     DESCRIPTION
            " Source port of the packets being redirected
              By Default, the DMON MUST use the Source Port of the Multicast Stream
            "
     ::= { dmonDsgMcastRedirectInfoEntry 3 }

dmonDsgMcastRedirectSrcInetAddr OBJECT-TYPE
    SYNTAX      InetAddress
    MAX-ACCESS  read-only
    STATUS      current
    DESCRIPTION
            " Source INET Address of the packets being redirected
              By Default the DMon MUST use the CM INET address
            "
     ::= { dmonDsgMcastRedirectInfoEntry 4 }

dmonDsgMcastRedirectDestPort OBJECT-TYPE
    SYNTAX      InetPortNumber
    MAX-ACCESS  read-write
    STATUS      current
     DESCRIPTION
            " Destination port of the packets being redirected
              By Default, the DMON MUST use the Destination Port of the Multicast Stream
            "
     ::= { dmonDsgMcastRedirectInfoEntry 5 }

dmonDsgMcastRedirectDestInetAddr OBJECT-TYPE
    SYNTAX      InetAddress
    MAX-ACCESS  read-write
    STATUS      current
    DESCRIPTION
            "Destination INET Address of the packets being redirected"
     ::= { dmonDsgMcastRedirectInfoEntry 6 }

dmonDsgMcastRedirectDuration OBJECT-TYPE
    SYNTAX      Integer32
    UNITS       "seconds"
    MAX-ACCESS  read-write
    STATUS      current
    DESCRIPTION
            "Setting this to 0 will redirect the traffic indefinitely"
    DEFVAL { 900 }
     ::= { dmonDsgMcastRedirectInfoEntry 7 }

dmonDsgMcastRedirectPktCounter OBJECT-TYPE
    SYNTAX      Counter32
    UNITS       "packets"
    MAX-ACCESS  read-only
    STATUS      current
    DESCRIPTION
            "Counts the number of packets being redirected"
     ::= { dmonDsgMcastRedirectInfoEntry 8 }

END
