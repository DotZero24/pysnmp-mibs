--**************************************************************************
--
--    Copyright 2012 Electroline Equipment Inc
--    All Rights Reserved
--
--
--
--**************************************************************************
--    Filename		:   ELECTROLINE-DHT-GLOBAL-FIBERNODE.mib
--    Author 		:   Anass El bahri
--    Creation Date :   2012.10.26
--
--**************************************************************************
--    Description:
--
--		This MIB contains all Global Fiber Node Mibs extension
--
--**************************************************************************
--    Revision History:
--	  2012.10.26	Anass El bahri   	First Draft
--	  2012.12.05	Anass El bahri   	Add the control MIBS
--	  2012.12.17	Anass El bahri   	Add comment (official version)
--	  2013.04.29	Anass El bahri   	Add the support of the new version of protocol(4.2)
--	  2013.05.06	Anass El bahri   	Add type of power supply mib
--	  2013.05.07	Anass El bahri   	Add Optical receiver type
--
--**************************************************************************

ELECTROLINE-DHT-GLOBAL-FIBERNODE-MIB DEFINITIONS ::= BEGIN

IMPORTS
    MODULE-IDENTITY,
    OBJECT-TYPE,
    Integer32, Counter32
        FROM SNMPv2-SMI
    DisplayString
        FROM RFC1213-MIB
    TruthValue
        FROM SNMPv2-TC
    dhtExtensionsMibObjects
        FROM ELECTROLINE-DHT-EXTENSIONS-MIB;

dhtGlobalFnIdentMIB MODULE-IDENTITY
    LAST-UPDATED "200412100000Z"
    ORGANIZATION "Electroline Equipment Inc"
    CONTACT-INFO
        "Electroline Equipment Inc.
         E-mail: support@electroline.com
         Telephone:
         	(514) 374-6335
         	(800)-461-3344 (Toll-free - North America)
        "
    DESCRIPTION
        "This set of objects monitor and control a GLOBAL fiber node (VTN-200) that may be present and connected to the ECMM-06.
         This file includes a control object, and status object.
        "
    REVISION      "200412100000Z"
    DESCRIPTION
            "Initial version of this MIB module."
    ::= { dhtExtensionsMibObjects 14 }

--Global Fiber Node Objects

globalFnIdentObjects    OBJECT IDENTIFIER ::= { dhtGlobalFnIdentMIB 1 }

--- ******************
--- * Return lasers
--- ******************

--number of return lazer

globalFnNumberReturnLaser OBJECT-TYPE
     SYNTAX INTEGER (1..8)
     ACCESS read-only
     STATUS current
     DESCRIPTION
		"Number of entries in the return laser table.
 		 A zero entry means the table does not exist and the functional
 		 area is not present in this device."
     ::= { globalFnIdentObjects 1 }

--return laser table

globalFnReturnLaserTable OBJECT-TYPE
    SYNTAX SEQUENCE OF GlobalFnReturnLaserTableEntry
    ACCESS not-accessible
    STATUS current
    DESCRIPTION
		"A table containing information about return lasers in a fiber node"
   	::= { globalFnIdentObjects 2 }

--return lasers entry

globalFnReturnLaserTableEntry OBJECT-TYPE
	SYNTAX GlobalFnReturnLaserTableEntry
    ACCESS not-accessible
    STATUS current
    DESCRIPTION
		"A list of information about each return laser in a fiber node."
	INDEX {globalFnReturnLaserIndex}
    ::= { globalFnReturnLaserTable 1 }

GlobalFnReturnLaserTableEntry ::=
   	SEQUENCE
   	{
		globalFnReturnLaserIndex
				INTEGER,
		globalFnReturnLaserState
				INTEGER,
		globalFnReturnLaserRFLevel
				INTEGER,
		globalFnReturnLaserRFState
				INTEGER,
		globalFnReturnLaserRFControl
				INTEGER,
		globalFnReturnLaserElecAttenuator
				INTEGER,
	}

--return laser index

globalFnReturnLaserIndex OBJECT-TYPE
	SYNTAX INTEGER
	ACCESS read-only
	STATUS current
	DESCRIPTION
		"Index into globalFnRetrunLaserTable.

	 	 a VTN-200 fiber node may have 4 transmitters, numbered 1,2,3,4 in modules 1,2. each module contain two transmitters.
	 	 Module1 can contain RTX1 , RTX2 and Module2 can contain RTX3 , RTX4.
	 	 "
	::= {globalFnReturnLaserTableEntry 1}

--return laser state

globalFnReturnLaserState OBJECT-TYPE
	SYNTAX INTEGER { unavailable(1), available(2) }
	ACCESS read-only
	STATUS current
	DESCRIPTION
		"Report the state of this return transmitter.

		 if the state is available, this return transmitter is plugged in the module.
		 if the state is unavailable, this return transmitter is not plugged in the module.
		 "
	::= {globalFnReturnLaserTableEntry 2}

--return laser RF level

globalFnReturnLaserRFLevel OBJECT-TYPE
	SYNTAX INTEGER
	ACCESS read-only
	STATUS current
	DESCRIPTION
		"Return a laser RF Level. Units in 1 dBmV."
	::= {globalFnReturnLaserTableEntry 3}

--return laser RF control

globalFnReturnLaserRFControl OBJECT-TYPE
	SYNTAX INTEGER  {off(1),on(2)}
	ACCESS read-write
	STATUS current
	DESCRIPTION
		"control the return laser RF path"
	::= {globalFnReturnLaserTableEntry 4}

--return laser electronic attenuator value

globalFnReturnLaserElecAttenuator OBJECT-TYPE
	SYNTAX INTEGER
	ACCESS read-write
	STATUS current
	DESCRIPTION
		"Return a laser electronic attenuator value. Units in 0.5 dB.

	     user can set a return transmitter electronic value by setting this variable.
		"
	::= {globalFnReturnLaserTableEntry 5}

--- ******************
--- * Optical receivers
--- ******************

--number of optical receivers

globalFnNumberOpticalReceiver OBJECT-TYPE
     SYNTAX INTEGER (1..8)
     ACCESS read-only
     STATUS current
     DESCRIPTION
		"Number of entries in the optical receiver table.
 		 A zero entry means the table does not exist and the functional
 	 	 area is not present in the device."
     ::= { globalFnIdentObjects 3 }

-- optical receivers AGC ON/OFF

globalFnOpticalReceiverAGCState OBJECT-TYPE
	SYNTAX INTEGER (0..3)
	ACCESS read-only
	STATUS current
	DESCRIPTION
		"Reports the optical receivers AGC state.

			0 = Optical receiver1 AGC OFF;Optical receiver2 AGC OFF
			1 = Optical receiver1 AGC OFF;Optical receiver2 AGC ON
			2 = Optical receiver1 AGC ON;Optical receiver2 AGC OFF
			3 = Optical receiver1 AGC ON;Optical receiver2 AGC ON."
	::= {globalFnIdentObjects 4}

--Opyical receiver AGC control

globalFnOpticalReceiverAGCControl OBJECT-TYPE
	SYNTAX INTEGER  {frx1-agc-off(1),frx1-agc-on(2),frx2-agc-off(3),frx2-agc-on(4)}
	ACCESS read-write
	STATUS current
	DESCRIPTION
		"control the FRX1 and FRX2 AGC."
	::= {globalFnIdentObjects 5}

--Optical receivers table

globalFnOpticalReceiverTable OBJECT-TYPE
    SYNTAX SEQUENCE OF GlobalFnOpticalReceiverTableEntry
    ACCESS not-accessible
    STATUS current
    DESCRIPTION
		"A table containing information about Optical receivers in a fiber node"
   	::= { globalFnIdentObjects 6 }

--Optical receivers entry

globalFnOpticalReceiverTableEntry OBJECT-TYPE
	SYNTAX GlobalFnOpticalReceiverTableEntry
    ACCESS not-accessible
    STATUS current
    DESCRIPTION
		"A list of information about each optical receiver in a fiber node."
	INDEX {globalFnOpticalReceiverIndex}
    ::= { globalFnOpticalReceiverTable 1 }

GlobalFnOpticalReceiverTableEntry ::=
	SEQUENCE
	{
		globalFnOpticalReceiverIndex
			INTEGER,
		globalFnOpticalReceiverState
			INTEGER,
		globalFnOpticalReceiverType
			DisplayString,
		globalFnOpticalReceiverRFLevel
			INTEGER,
		globalFnOpticalReceiverRFControl
			INTEGER,
		globalFnOpticalReceiverElecAttenuator
			INTEGER,
	}

--Optical receiver index

globalFnOpticalReceiverIndex OBJECT-TYPE
	SYNTAX INTEGER
	ACCESS read-only
	STATUS current
	DESCRIPTION
		"Index into globalFnOpticalReceiverTable.

	 	 a VTN-200 fiber node may have 4 receivers, numbered 1,2,3,4 in modules 1,2. each module contain two receivers.
	 	 Module1 can contain FRX1 , FRX2 and Module2 can contain FRX3 , FRX4."
	::= {globalFnOpticalReceiverTableEntry 1}

--Optical receiver  state

globalFnOpticalReceiverState OBJECT-TYPE
	SYNTAX INTEGER { unavailable(1), available(2) }
	ACCESS read-only
	STATUS current
	DESCRIPTION
		"Report the state of this optical receiver.

		 if the state is available, this optical receiver is plugged in the module.
		 if the state is unavailable, this optical receiver is not plugged in the module.
		 "
	::= {globalFnOpticalReceiverTableEntry 2}

--Optical receiver  type

globalFnOpticalReceiverType OBJECT-TYPE
     SYNTAX DisplayString ( SIZE(0..20) )
     ACCESS read-only
     STATUS optional
     DESCRIPTION
          "Type of optical receiver. Some valid values are: , standard frx,low input frx."
     ::= { globalFnOpticalReceiverTableEntry 3 }

--Optical receiver RF level

globalFnOpticalReceiverRFLevel OBJECT-TYPE
	SYNTAX INTEGER
	ACCESS read-only
	STATUS current
	DESCRIPTION
		"Return an optical receiver RF Level. Units in 1 dBmV."
	::= {globalFnOpticalReceiverTableEntry 4}

--Optical receiver RF control

globalFnOpticalReceiverRFControl OBJECT-TYPE
	SYNTAX INTEGER   { off(1),on(2)}
	ACCESS read-write
	STATUS current
	DESCRIPTION
		"Control the optical receiver RF path"
	::= {globalFnOpticalReceiverTableEntry 5}

--Optical receiver electronic attenuator

globalFnOpticalReceiverElecAttenuator OBJECT-TYPE
	SYNTAX INTEGER
	ACCESS read-write
	STATUS current
	DESCRIPTION
		"Return an optical receiver electronic attenuator value. Units in 0.5 dB.

		 user can set optical receiver electronic value by setting this variable.
		"
	::= {globalFnOpticalReceiverTableEntry 6}

--- ******************
--- * wing switchs
--- ******************

--number of wing switch

globalFnNumberWingSwitch OBJECT-TYPE
     SYNTAX INTEGER ( 0..8 )
     ACCESS read-only
     STATUS current
     DESCRIPTION
		"Number of wing switches in this fiber node
 		 A zero entry means the table does not exist and the functional
 		 area is not present in the device."
     ::= { globalFnIdentObjects 7 }

--wing switch table

globalFnWingSwitchTable OBJECT-TYPE
    SYNTAX SEQUENCE OF GlobalFnWingSwitchTableEntry
    ACCESS not-accessible
    STATUS current
    DESCRIPTION
		" table containing information about wing switches in this fiber node"
   	::= { globalFnIdentObjects 8 }

--wing switch entry

globalFnWingSwitchTableEntry OBJECT-TYPE
	SYNTAX GlobalFnWingSwitchTableEntry
    ACCESS not-accessible
    STATUS current
    DESCRIPTION
		"List of information about each wing switch."
	INDEX {globalFnWingSwitchIndex}
    ::= { globalFnWingSwitchTable 1 }

GlobalFnWingSwitchTableEntry ::=
 	SEQUENCE
 	{
		globalFnWingSwitchIndex
			INTEGER,
		globalFnWingSwitchState
			INTEGER,
		globalFnWingSwitchControl
			INTEGER,
	}

--wing switch index

globalFnWingSwitchIndex OBJECT-TYPE
	SYNTAX INTEGER
	ACCESS read-only
	STATUS current
	DESCRIPTION
		"Index into the dhtGlobalFnWingSwitchTable."
	::= {globalFnWingSwitchTableEntry 1}

--wing switch state

globalFnWingSwitchState OBJECT-TYPE
	SYNTAX INTEGER   {unavailable(0), off(1), sixDb(2), normal(3)}
	ACCESS read-only
	STATUS current
	DESCRIPTION
		"Reports the state of the wing switch.

 	 	 	unavailable(0) indicate that the wing switch is unavailable.
 	 	    off(1) indicate that the wing switch is off.
 	 	    sixDb(2) indicate that the RF level of the node RF port is 6 db.
 	 	    normal(3) indicate that the wing switch is normal.
 	 	"
	::= {globalFnWingSwitchTableEntry 2}

--wing switch control

globalFnWingSwitchControl OBJECT-TYPE
	SYNTAX INTEGER   {off(1), sixDb(2), normal(3)}
	ACCESS read-write
	STATUS current
	DESCRIPTION
		"control the wing switch."
	::= {globalFnWingSwitchTableEntry 3}

--- ******************
--- * RF routers
--- ******************

-- number of Rf router

globalFnNumberRFRouter OBJECT-TYPE
     SYNTAX INTEGER ( 0..8 )
     ACCESS read-only
     STATUS current
     DESCRIPTION
		"Number of RF router in this fiber node
 		 A zero entry means the table does not exist and the functional
 		 area is not present in the device."
     ::= { globalFnIdentObjects 9 }

-- RF router table

globalFnRFRouterTable OBJECT-TYPE

    SYNTAX SEQUENCE OF GlobalFnRFRouterTableEntry
    ACCESS not-accessible
    STATUS current
    DESCRIPTION
		" table containing information about RF routers in this fiber node"
   	::= { globalFnIdentObjects 10 }

-- RF router table

globalRFRouterTableEntry OBJECT-TYPE
	SYNTAX GlobalFnRFRouterTableEntry
    ACCESS not-accessible
    STATUS current
    DESCRIPTION
		"List of information about each RF router."
	INDEX { globalFnRFRouterIndex }
    ::= { globalFnRFRouterTable 1 }

GlobalFnRFRouterTableEntry ::=
 	SEQUENCE
 	{
		globalFnRFRouterIndex
			INTEGER,
		globalFnRFRouterType
			DisplayString,
		globalFnRFRouterDownstreamSwitchState
			INTEGER,
		globalFnRFRouterDownstreamSwitchControl
			INTEGER,
		globalFnRFRouterDownstreamControlTypeState
			INTEGER,
		globalFnRFRouterDownstreamControlTypeSetting
			INTEGER,
		globalFnRFRouterUptreamSwitchState
			INTEGER,
		globalFnRFRouterUptreamSwitchControl
			INTEGER,
		globalFnRFRouterUpstreamControlTypeState
			INTEGER,
		globalFnRFRouterUpstreamControlTypeSetting
			INTEGER,
	}

-- RF router index

globalFnRFRouterIndex OBJECT-TYPE
	SYNTAX INTEGER
	ACCESS read-only
	STATUS current
	DESCRIPTION
		"Index into the dhtGlobalFnRFRouterTable."
	::= {globalRFRouterTableEntry 1}

-- RF router type

globalFnRFRouterType OBJECT-TYPE
	SYNTAX DisplayString  ( SIZE(0..20))
	ACCESS read-only
	STATUS current
	DESCRIPTION
		"RF router type

		0 = Not Present.
		1 = Router Reserved Type1.
		2 = Router Reserved Type2.
		3 = Router Reserved Type3.
		4 = Router Reserved Type4.
		"
	::= {globalRFRouterTableEntry 2}

-- RF router downstream switch state

globalFnRFRouterDownstreamSwitchState OBJECT-TYPE
	SYNTAX INTEGER   {unavailable(0), redundantMode(1), segmentation(2) }
	ACCESS read-only
	STATUS current
	DESCRIPTION
		"Reports the state of the downstream redundant & segmentation switch.

 		 	unavailable(0) indicates that the switch is unavailable.
 		 	redundantMode(1) indicates that the switch is in redundant mode.
 		 	segmentation(2) indicates that the switch is in segmentation mode."
	::= {globalRFRouterTableEntry 3}

--  RF router downstream switch control

globalFnRFRouterDownstreamSwitchControl OBJECT-TYPE
	SYNTAX INTEGER   {redundantMode(1), segmentation(2) }
	ACCESS read-write
	STATUS current
	DESCRIPTION
		"control the downstream switch."
	::= {globalRFRouterTableEntry 4}

-- RF router downstream control type state

globalFnRFRouterDownstreamControlTypeState OBJECT-TYPE
	SYNTAX INTEGER   {remote(0), local(1)}
	ACCESS read-only
	STATUS current
	DESCRIPTION
		"Reports the control mode of the downstream redundant & segmentation switch.

 	     	remote(0) indicates that the switch is in remote mode.
	     	local(1)  indicates that the switch is in local mode."
	::= {globalRFRouterTableEntry 5}

-- RF router downstream control type setting

globalFnRFRouterDownstreamControlTypeSetting OBJECT-TYPE
	SYNTAX INTEGER   {remote(0), local(1)}
	ACCESS read-write
	STATUS current
	DESCRIPTION
		"Control the downstream redundant & segmentation switch mode."
	::= {globalRFRouterTableEntry 6}

-- RF router upstream switch state

globalFnRFRouterUptreamSwitchState OBJECT-TYPE
	SYNTAX INTEGER   {unavailable(0), redundantMode(1), segmentation(2) }
	ACCESS read-only
	STATUS current
	DESCRIPTION
		"Reports the state of the upstream redundant & segmentation switch state.

 		 	unavailable(0) indicates that the switch is unavailable.
 		 	redundantMode(1) indicates that the switch is in redundant mode.
 		 	segmentation(2) indicates that the switch is in segmentation mode."
	::= {globalRFRouterTableEntry 7}

-- RF router upstream switch control

globalFnRFRouterUptreamSwitchControl OBJECT-TYPE
	SYNTAX INTEGER   {redundantMode(1), segmentation(2) }
	ACCESS read-write
	STATUS current
	DESCRIPTION
		"control the upstream switch."
	::= {globalRFRouterTableEntry 8}

-- RF router upstream control type state

globalFnRFRouterUpstreamControlTypeState OBJECT-TYPE
	SYNTAX INTEGER   {remote(0), local(1)}
	ACCESS read-only
	STATUS current
	DESCRIPTION
		"Reports the control mode of the upstream redundant & segmentation switch.

 	     	remote(0) indicates that the switch is in remote mode.
	     	local(1)  indicates that the switch is in local mode."
	::= {globalRFRouterTableEntry 9}


-- RF router upstream control type setting

globalFnRFRouterUpstreamControlTypeSetting OBJECT-TYPE
	SYNTAX INTEGER   {remote(0), local(1)}
	ACCESS read-write
	STATUS current
	DESCRIPTION
		"control the mode of upstream switch."
	::= {globalRFRouterTableEntry 10}


--- ******************
--- * RF ports
--- ******************

--number of rf port

globalFnNumberRFPort OBJECT-TYPE
     SYNTAX INTEGER ( 0..16 )
     ACCESS read-only
     STATUS current
     DESCRIPTION
		"Number of entries in the RF port table.
 		 A zero entry means the table does not exist and the functional
 		 area is not present in the device."
     ::= { globalFnIdentObjects 11 }

-- RF link switch state

globalRFLinkSwitchState OBJECT-TYPE
     SYNTAX INTEGER ( 0..255 )
     ACCESS read-only
     STATUS current
     DESCRIPTION
		"return the RF link switch status

			Bit7 = Optical receiver1 RF ON/OFF State
			Bit6 = Optical receiver2 RF ON/OFF State
			Bit5 = Optical receiver3 RF ON/OFF State
			Bit4 = Optical receiver4 RF ON/OFF State
			Bit3 = Return laser1 RF ON/OFF State
			Bit2 = Return laser2 RF ON/OFF State
			Bit1 = Return laser3 RF ON/OFF State
			Bit0 = Return laser4 RF ON/OFF State

			0 =  RF OFF
			1 =  RF ON
		E.g.  0xA0 = 1010 0000 stand for Optical receiver1 Plug in module1&Optical receiver2 Plug in module1 RF ON, and other RF OFF."
     ::= { globalFnIdentObjects 12 }

--RF reverse link switch state

globalReverseRFLinkSwitchState OBJECT-TYPE
     SYNTAX INTEGER ( 0..7 )
     ACCESS read-only
     STATUS current
     DESCRIPTION
		"return the reverse RF link switch state

			0 = RF Path1 OFF  :RF Path2 OFF   :RF Path3 OFF
			1 = RF Path1 OFF  :RF Path2 OFF   :RF Path3 ON
			2 = RF Path1 OFF  :RF Path2 ON    :RF Path3 OFF
			3 = RF Path1 ON   :RF Path2 OFF   :RF Path3 OFF
			4 = RF Path1 OFF  :RF Path2 ON    :RF Path3 ON
			5 = RF Path1 ON   :RF Path2 ON    :RF Path3 OFF
			6 = RF Path1 ON   :RF Path2 OFF   :RF Path3 ON
			7 = RF Path1 ON   :RF Path2 ON    :RF Path3 ON."
     ::= { globalFnIdentObjects 13 }

--RF reverse link switch control

globalReverseRFLinkSwitchControl OBJECT-TYPE
     SYNTAX INTEGER { path1-off(1),path1-on(2),path2-off(3),path2-on(4),path3-off(5),path3-on(6)}
     ACCESS read-write
     STATUS current
     DESCRIPTION
		"control the reverse link switch path"
     ::= { globalFnIdentObjects 14 }

--RF ports table

globalFnRFPortTable OBJECT-TYPE
    SYNTAX SEQUENCE OF GlobalFnRFPortTableEntry
    ACCESS not-accessible
    STATUS current
    DESCRIPTION
		" table containing information about RF ports in this fiber node"
   	::= { globalFnIdentObjects 15 }

--RF ports table entry

globalFnRFPortTableEntry OBJECT-TYPE
	SYNTAX GlobalFnRFPortTableEntry
    ACCESS not-accessible
    STATUS current
    DESCRIPTION
		"List of information about each RF port."
	INDEX {globalFnRFPortIndex}
    ::= { globalFnRFPortTable 1 }

GlobalFnRFPortTableEntry ::=
 	SEQUENCE
 	{
		globalFnRFPortIndex
			INTEGER,
		globalUpStreamRFLevel
			INTEGER,
		globalFnDownStreamRFLevel
			INTEGER,
	}

--RF port index

globalFnRFPortIndex OBJECT-TYPE
	SYNTAX INTEGER
	ACCESS read-only
	STATUS current
	DESCRIPTION
		"Index into the fnRFPortTable.
 		 This index is application specific.  It can be either the nth port, or a port number.
 		 For example, a node may have 4 ports, numbered 1, 3, 4, 6.  Thus, the indexes could be
 		 .1, .3, .4, .6, OR .1, .2, .3., .4.  In the latter case, the port name is critical."
	::= {globalFnRFPortTableEntry 1}

--RF port upstream RF level

globalUpStreamRFLevel OBJECT-TYPE
     SYNTAX INTEGER
     ACCESS read-only
     STATUS current
     DESCRIPTION
		"Port Reverse RF Level. Units in 1 dBmV."
     ::= { globalFnRFPortTableEntry 2}

--RF port downstream RF level

globalFnDownStreamRFLevel OBJECT-TYPE
     SYNTAX INTEGER
     ACCESS read-only
     STATUS current
     DESCRIPTION
		"Port Forward RF Level. Units in 1 dBmV."
     ::= { globalFnRFPortTableEntry 3}

--- ***********************
--- * electronic attenuator
--- ***********************

-- number of electronic attenuator

globalFnNumberElecAttenuator OBJECT-TYPE
     SYNTAX INTEGER  (0..2)
     ACCESS read-only
     STATUS current
     DESCRIPTION
		"return the number of electronic attenuator in this fiber node."
     ::= { globalFnIdentObjects 16 }

-- electronic attenuator table

globalFnElecAttenuatorTable OBJECT-TYPE
    SYNTAX SEQUENCE OF GlobalFnElecAttenuatorTableEntry
    ACCESS not-accessible
    STATUS current
    DESCRIPTION
		"A table containing information about  electronic attenuator in this fiber node"
   	::= { globalFnIdentObjects 17 }

-- electronic attenuator entry

globalFnElecAttenuatorTableEntry OBJECT-TYPE
	SYNTAX GlobalFnElecAttenuatorTableEntry
    ACCESS not-accessible
    STATUS current
    DESCRIPTION
		"A list of information about each electronic attenuator in this fiber node."
	INDEX {globalFnElecAttenuatorIndex}
    ::= { globalFnElecAttenuatorTable 1 }

GlobalFnElecAttenuatorTableEntry ::=
SEQUENCE
	{
		globalFnElecAttenuatorIndex
			INTEGER,
		globalFnElecAttenuatorValue
			INTEGER,
	}

-- electronic attenuator index

globalFnElecAttenuatorIndex OBJECT-TYPE
	SYNTAX INTEGER
	ACCESS read-only
	STATUS current
	DESCRIPTION
		"Index into the dhtGlobalFnElecAttenuatorTable."
	::= {globalFnElecAttenuatorTableEntry 1}

-- electronic attenuator value

globalFnElecAttenuatorValue OBJECT-TYPE
	SYNTAX 	INTEGER
	ACCESS 	read-write
	STATUS 	current
	DESCRIPTION
		"return the attenuator value.  Units in 0.5 dB.

		 user can set electronic attenuator value by writing this variable.
		 "
	::= {globalFnElecAttenuatorTableEntry 2}

--- ***********************
--- * electronic equaslisers
--- ***********************

-- number of electronic equalizer

globalFnNumberElecEqualizer OBJECT-TYPE
     SYNTAX INTEGER  (0..2)
     ACCESS read-only
     STATUS current
     DESCRIPTION
		"return the number of electronic equalizer in this fiber node."
     ::= { globalFnIdentObjects 18 }

-- electronic equalizer table

globalFnElecEqualizerTable OBJECT-TYPE
    SYNTAX SEQUENCE OF GlobalFnElecEqualizerTableEntry
    ACCESS not-accessible
    STATUS current
    DESCRIPTION
		"A table containing information about electronic equalizer in a fiber node"

   	::= { globalFnIdentObjects 19 }

-- electronic equalizer table

globalFnElecEqualizerTableEntry OBJECT-TYPE
	SYNTAX GlobalFnElecEqualizerTableEntry
    ACCESS not-accessible
    STATUS current
    DESCRIPTION
		"A list of information about each electronic eqalizer in this fiber node."
	INDEX {globalFnElecEqualizerIndex}
    ::= { globalFnElecEqualizerTable 1 }

GlobalFnElecEqualizerTableEntry ::=
SEQUENCE
	{
		globalFnElecEqualizerIndex
			INTEGER,
		globalFnElecEqualizerValue
			INTEGER,
	}

-- electronic equalizer index

globalFnElecEqualizerIndex OBJECT-TYPE
	SYNTAX INTEGER
	ACCESS read-only
	STATUS current
	DESCRIPTION
		"Index into the dhtGlobalFnElecAttenuatorTable."
	::= {globalFnElecEqualizerTableEntry 1}

-- electronic equalizer value

globalFnElecEqualizerValue OBJECT-TYPE
	SYNTAX INTEGER
	ACCESS read-write
	STATUS current
	DESCRIPTION
		"return the equalizer value.  Units in 0.5 dB.

		 user can set electronic equaliser value by writing this variable.
		"
	::= {globalFnElecEqualizerTableEntry 2}

-- optical reveivers AGC offset

globalFnAGCOffsetValue OBJECT-TYPE
	SYNTAX INTEGER
	ACCESS read-write
	STATUS current
	DESCRIPTION
		"return the optical receivers AGC offset value.

		 user can set AGC offset value by writing this variable.
		"
	::= {globalFnIdentObjects 20}

-- optical reveivers AGC RF level

globalFnAGCRfLevel OBJECT-TYPE
	SYNTAX INTEGER
	ACCESS read-write
	STATUS current
	DESCRIPTION
		"return the optical receivers AGC RF level value.

		 user can set AGC RF level by writing this variable.
		"
	::= {globalFnIdentObjects 21}

-- optical reveivers RF level offset

globalFnRfLevelOffsetValue OBJECT-TYPE
	SYNTAX INTEGER
	ACCESS read-write
	STATUS current
	DESCRIPTION
		"return the RF level offset value.

		 user can set RF level offset value by writing this variable.
		"
	::= {globalFnIdentObjects 22}

-- fiber internal temperature

globalFnTemperature OBJECT-TYPE
	SYNTAX INTEGER
	ACCESS read-only
	STATUS current
	DESCRIPTION
		"return the fiber node internal temperature."
	::= {globalFnIdentObjects 23}

-- fiber node reset

globalFnReset OBJECT-TYPE
	SYNTAX INTEGER  { reset(1)}
	ACCESS read-write
	STATUS current
	DESCRIPTION
		"This object is used to reset the VTN-200 by writing 1 to it.
 		Other values written to the object have no effect.
 		Reading the object returns a 1, and has no effect on the unit."
	::= {globalFnIdentObjects 24}

-- reset all RTX and FRX modules

globalFnResetFrxRtx OBJECT-TYPE
	SYNTAX INTEGER  { reset(1)}
	ACCESS read-write
	STATUS current
	DESCRIPTION
		"This object is used to reset all RTX and FRX modules by writing 1 to it.
 		Other values written to the object have no effect.
 		Reading the object returns a 1, and has no effect on the unit."
	::= {globalFnIdentObjects 25}

-- type of power supply

globalFnTypeOfPowerSupply OBJECT-TYPE
	SYNTAX INTEGER  { linePower(1),mainPower(2),not-defined(0)}
	ACCESS read-only
	STATUS current
	DESCRIPTION
		"Report the type of the power supply. "
	::= {globalFnIdentObjects 26}


END
