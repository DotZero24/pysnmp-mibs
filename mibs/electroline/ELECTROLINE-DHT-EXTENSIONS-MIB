--**************************************************************************
--
--    Copyright 2004 Electroline Equipment Inc
--    All Rights Reserved
--
--
--
--**************************************************************************
--    Filename: ELECTROLINE-DHT-EXTENSIONS.mib
--    Author:   Nathaniel Mercure
--    Creation Date: 2004.12.09
--
--**************************************************************************
--    Description:
--
--		Root MIB of the DHT Extensions branch
--
--**************************************************************************
--    Revision History:
--	  2004.12.09	Nathaniel Mercure	First Draft
--	  2004.12.15	Carlene Gardner 	Linguistic revision
--	  2007.12.20	Carlene Gardner 	Update for Enet
--**************************************************************************

ELECTROLINE-DHT-EXTENSIONS-MIB DEFINITIONS ::= BEGIN

IMPORTS
    MODULE-IDENTITY,
    OBJECT-TYPE,
    Integer32
        FROM SNMPv2-SMI
    electrolineDHT
        FROM ELECTROLINE-DHT-ROOT-MIB;



dhtExtensionsMib MODULE-IDENTITY
    LAST-UPDATED "200412090000Z"
    ORGANIZATION "Electroline Equipment Inc"
    CONTACT-INFO
        "Electroline Equipment Inc.
         E-mail: support@electroline.com
         Telephone:
         	(514) 374-6335
         	(800)-461-3344 (Toll-free - North America)
        "
    DESCRIPTION
        "Electroline DHT Extension Root MIB"
    REVISION      "200412090000Z"
    DESCRIPTION
            "Initial version of this MIB module."
    ::= { electrolineDHT 5 }

-- /*****************
-- * Extetions Mibs *
-- *****************/

dhtExtensionsMibObjects OBJECT IDENTIFIER ::= { dhtExtensionsMib 1 }

dhtExtensionsSupported OBJECT-TYPE
     SYNTAX INTEGER
     MAX-ACCESS read-only
     STATUS current
     DESCRIPTION
          "Bit assignment that defines the add-ons which are supported by the current software load
          Bit     Address
           0      Not used
           1      1   Supports HmsExtentions
           2      2   Supports Remote Switch Monitoring
           3      3   Supports Enet Monitoring
           4      4   Future use
           .      .   ....................................
           .      .   ....................................
           .      .   ....................................
           n      n   Future use
          "
     ::= { dhtExtensionsMibObjects 1 }


END
