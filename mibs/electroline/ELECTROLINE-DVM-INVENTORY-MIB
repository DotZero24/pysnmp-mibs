--*****************************************************************************
--
--    Copyright 2010 Electroline Equipment Inc.
--    All Rights Reserved
--
--
--*****************************************************************************
--    Filename: ELECTROLINE-DVM-INVENTORY.mib
--    Author:   Alain Leclerc
--    Creation Date: 2010-09-13
--*****************************************************************************
--    Description:
--
--     SNMPv2 Inventory branch MIB definition for DVM product.
--
--    Note that these MIBs are read-only during normal operation, and are intended
--    for Electroline inventory tracking purpose.
--
--    When the DVM is in factory mode, the value of these MIBS can be configured
--    by the factory programming station.
--    To save the value of these MIBs in non-volatile memory, the
--    factory program must set the "commit" MIB to one (1).
--
--*****************************************************************************
--    Revision History:
--	  2010.09.13	Alain Leclerc	First Draft
--*****************************************************************************

ELECTROLINE-DVM-INVENTORY-MIB DEFINITIONS ::= BEGIN

IMPORTS
    MODULE-IDENTITY,
    OBJECT-TYPE,
    Integer32 	   FROM SNMPv2-SMI
	DateAndTime    FROM SNMPv2-TC
    dvmInventory   FROM ELECTROLINE-DVM-ROOT-MIB;



--*****************************************************************************
-- * GLOBAL INVENTORY DATA
-- *
-- * The following information is used to determine the type of PCB / Assembly
-- * and its revision number.  Additional information required by the DVM
-- * software for proper operation on all board variations is also stored here.
-- *
-- * The values defined for these MIBs are kept in a separate document.
--*****************************************************************************

dvmInvHwType OBJECT-TYPE
    SYNTAX   	INTEGER
    MAX-ACCESS  read-only
    STATUS      current
    DESCRIPTION
       "DVM Hardware Model Identification Number. This information is used by the DVM
       software to differentiate the hardware platform on which it is running."
    ::= { dvmInventory 1 }

dvmInvHwMinorRev OBJECT-TYPE
    SYNTAX   	INTEGER
    MAX-ACCESS  read-only
    STATUS      current
    DESCRIPTION
       "DVM Hardware Revision Identification Number, representing the PCB version
       and / or the assembly modification level."
    ::= { dvmInventory 2 }

dvmInvHwMajorRev OBJECT-TYPE
	SYNTAX 		INTEGER
	MAX-ACCESS	read-only
	STATUS		current
	DESCRIPTION
		"This information is used to represent a family of hardware revisions.
		 Major functional changes will trigger a modification of this value"
	::= { dvmInventory 3 }

dvmInvHwDrvRev OBJECT-TYPE
    SYNTAX   	INTEGER
    MAX-ACCESS  read-only
    STATUS      current
    DESCRIPTION
       "This information is used to track any changes in the manufacturing process
	    not covered by a PCB/Assembly revision and that have an impact on the drivers.
       "
    ::= { dvmInventory 4 }

dvmModelNumber  OBJECT-TYPE
     SYNTAX OCTET STRING (SIZE(0..255))
     ACCESS read-only
     STATUS current
     DESCRIPTION
          "Displays the private electroline model number.
          Displayed in human-readable format."
     ::= { dvmInventory 5 }


--*****************************************************************************
-- * MANUFACTURING INVENTORY DATA
-- *
-- * This section contains additional manufacturing process related information
-- * for tracking purposes.
--*****************************************************************************
dvmManufacturingInfo OBJECT-IDENTITY
	STATUS current
	DESCRIPTION "Electroline Private sub-tree to access manufacturing information"
	::= { dvmInventory 10 }

dvmMfcDateTime OBJECT-TYPE
	SYNTAX 		DateAndTime
	MAX-ACCESS	read-only
	STATUS		current
	DESCRIPTION
		"Date and time when this unit was tested (in a string format)."
	::= { dvmManufacturingInfo 1 }

dvmMfcTestSwVersion OBJECT-TYPE
	SYNTAX 		OCTET STRING
	MAX-ACCESS	read-only
	STATUS		current
	DESCRIPTION
		"Version of the test station with which this DVM was tested."
	::= { dvmManufacturingInfo 2 }
END
