--**************************************************************************
--
--    Copyright 2014 Electroline Equipment Inc
--    All Rights Reserved
--
--
--
--**************************************************************************
--    Filename: ELECTROLINE-COMMON-ROOT.mib
--    Author:   Alain Leclerc
--    Creation Date: 2014.01.14
--
--**************************************************************************
--    Description:
--
--		Root MIB of the electroline common branch
--
--**************************************************************************
--    Revision History:
--	  2014.01.14	Eric Alarie		First Draft
--**************************************************************************

ELECTROLINE-COMMON-ROOT-MIB DEFINITIONS ::= BEGIN

IMPORTS
    MODULE-IDENTITY,
    OBJECT-TYPE,
    Integer32
        FROM SNMPv2-SMI
    electrolineHardwareProducts
        FROM ELECTROLINE-GLOBAL-REG;

electrolineCommon MODULE-IDENTITY
    LAST-UPDATED "201401140000Z"
    ORGANIZATION "Electroline Equipment Inc"
    CONTACT-INFO
        "Alain Leclerc"
    DESCRIPTION
        "Electroline Hardware common MIBS"
    REVISION      "201401140000Z"
    DESCRIPTION
            "Initial version of this MIB module."
    ::= { electrolineHardwareProducts 4 }


-- /*************
-- * MAIN MENUS *
-- **************/
commonInventory OBJECT-IDENTITY
	STATUS current
	DESCRIPTION "Sub-tree for device identification"
	::= { electrolineCommon 1 }

commonConfiguration OBJECT-IDENTITY
	STATUS current
	DESCRIPTION "Sub-tree for DHT Configuration Parameters"
	::= { electrolineCommon 2 }

commonStatus OBJECT-IDENTITY
	STATUS current
	DESCRIPTION "Sub-tree for status and troubleshooting information"
	::= { electrolineCommon 3 }

commonPrivate OBJECT-IDENTITY
	STATUS current
	DESCRIPTION "Sub-tree for private factory MIBS"
	::= { electrolineCommon 4 }
END
