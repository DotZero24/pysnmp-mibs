-- *****************************************************************
-- Senao Enterprise indoor AP/CB Private MIB for EAP and ECB series
--
-- Apr 2008, Adonn Fu
--
-- Copyright (c) 2000-2003 by Senao Networks, Inc.
-- All rights reserved.
-- *****************************************************************

--module definition

SENAO-ENTERPRISE-INDOOR-AP-CB-MIB DEFINITIONS ::= BEGIN

       IMPORTS
       MODULE-IDENTITY, OBJECT-TYPE,
       Counter32, IpAddress, enterprises, TimeTicks
       FROM SNMPv2-SMI
       DisplayString, MacAddress, TruthValue FROM SNMPv2-TC;

-- module OID definition
   senao MODULE-IDENTITY
   LAST-UPDATED "0511250000Z"
   ORGANIZATION "Senao R&D Dept., S/W Division"
   CONTACT-INFO
       "
       Info
       SENAO INTERNATIONAL CO., LTD.
       No.500, Fusing 3 Rd., Hwa-Ya Technical Park,
       Kuei-Shan Hsiang, TAOYUAN County 333, TAIWAN, R.O.C.
       Tel: 886-3-328-9289
       Fax: 886-3-328-9666
       E-mail: info@senao.com.tw
       "
   DESCRIPTION
       "
       The MIB module defines Senao implementation-specific metrics useful in managing
       IEEE 802.11 on Senao devices.
       This is used as a supplement to the standard 802.11 MIB proposed by IEEE.
       "
   ::= { enterprises 14125}

	indoorWirelessDevice OBJECT IDENTIFIER ::= { senao 100 }

	entSystem OBJECT IDENTIFIER ::= { indoorWirelessDevice 1 }
	entLAN OBJECT IDENTIFIER ::= { indoorWirelessDevice 2 }
	entWAN OBJECT IDENTIFIER ::= { indoorWirelessDevice 3 }
	entMacFilter OBJECT IDENTIFIER ::= { indoorWirelessDevice 4}
	entWlan OBJECT IDENTIFIER ::= { indoorWirelessDevice 5}
	entSNMP OBJECT IDENTIFIER ::= { indoorWirelessDevice 6 }

	entWlanCommonInfo OBJECT IDENTIFIER ::= { entWlan 1}

-- objects definition

--	entSystem OBJECT IDENTIFIER ::= { indoorWirelessDevice 1 }
--	entAdminIdleTimeOut OBJECT-TYPE
--		SYNTAX INTEGER (1..1000)
--		MAX-ACCESS read-write
--    	STATUS mandatory
--		DESCRIPTION
--			"Administration idle time out in mins"
--	::= { entSystem 1 }

	entPassword OBJECT-TYPE
		SYNTAX DisplayString  (SIZE (0..32))
		MAX-ACCESS write-only
    	STATUS mandatory
		DESCRIPTION
			"Administration password"
	::= { entSystem 2 }

	entSysModel OBJECT-TYPE
		SYNTAX DisplayString
    	MAX-ACCESS read-only
    	STATUS mandatory
		DESCRIPTION
			"System model"
	::= { entSystem 3 }

	entSysMode OBJECT-TYPE
		SYNTAX INTEGER
		{
			ap-router(0),
			repeater(1),
			ap-bridge(2),
			client-bridge(3),
			client-router(4),
			wds-bridge(5)
		}
    	MAX-ACCESS read-only
    	STATUS mandatory
		DESCRIPTION
			"System mode, 0:AP router, 1:Repeater, 2: AP bridge,
			3: Client bridge, 4: Client router, 5: WDS bridge"
	::= { entSystem 4 }

	entSysUpTime OBJECT-TYPE
		SYNTAX TimeTicks
    	MAX-ACCESS read-only
    	STATUS mandatory
		DESCRIPTION
			"System uptime"
	::= { entSystem 5 }

    entHwVersion OBJECT-TYPE
        SYNTAX DisplayString
        MAX-ACCESS read-only
        STATUS mandatory
        DESCRIPTION
            "The version of the hardware"
    ::= {  entSystem 6 }

    entSN OBJECT-TYPE
        SYNTAX DisplayString
        MAX-ACCESS read-only
        STATUS mandatory
        DESCRIPTION
            "Serial Number"
    ::= {  entSystem 7 }

    entKenelVersion OBJECT-TYPE
        SYNTAX DisplayString
        MAX-ACCESS read-only
        STATUS mandatory
        DESCRIPTION
            "The version of the kernel"
    ::= {  entSystem 8 }

    entAppVersion OBJECT-TYPE
        SYNTAX DisplayString
        MAX-ACCESS read-only
        STATUS mandatory
        DESCRIPTION
            "The version of the system application"
    ::= {  entSystem 9 }

    entReset OBJECT-TYPE
        SYNTAX TruthValue
        MAX-ACCESS write-only
        STATUS mandatory
        DESCRIPTION
            "Setting this attribute TRUE causes the AP rebooted"
    ::= {  entSystem 10 }

     entResetToDefault OBJECT-TYPE
        SYNTAX TruthValue
        MAX-ACCESS write-only
        STATUS mandatory
        DESCRIPTION
            "Setting this attribute TRUE will Reboot the system and change settings to factory default"
    ::= {  entSystem 11 }

    entApplyModules OBJECT-TYPE
        SYNTAX TruthValue
        MAX-ACCESS write-only
        STATUS mandatory
        DESCRIPTION
            "Setting this attribute TRUE will apply the changed modules to reload"
    ::= {  entSystem 12 }

-- entLAN OBJECT IDENTIFIER ::= { indoorWirelessDevice 2 }
	entLANIP OBJECT-TYPE
		SYNTAX IpAddress
		MAX-ACCESS read-write
    	STATUS mandatory
		DESCRIPTION
			"LAN IP address"
	::= { entLAN 1 }

	entLANSubnetMask OBJECT-TYPE
		SYNTAX IpAddress
		MAX-ACCESS read-write
    	STATUS mandatory
		DESCRIPTION
			"LAN subnet mask"
	::= { entLAN 2 }

	entSTPEnable OBJECT-TYPE
		SYNTAX TruthValue
		MAX-ACCESS read-write
    	STATUS mandatory
		DESCRIPTION
			"Set this attribute TRUE will enable 802.1d Spanning Tree."
	::= { entLAN 3 }

	entDHCPEnable OBJECT-TYPE
		SYNTAX TruthValue
		MAX-ACCESS read-write
    	STATUS mandatory
		DESCRIPTION
			"When system mode is not 1(Repeater) and 5(WDS bridge),
			set this attribute TRUE will enable the DHCP server function of device"
	::= { entLAN 4 }

	entIPPoolStart OBJECT-TYPE
		SYNTAX IpAddress
		MAX-ACCESS read-write
    	STATUS mandatory
		DESCRIPTION
			"TWhen system mode is not 1(Repeater) and 5(WDS bridge),
			set the start address of DHCP IP pool"
	::= { entLAN 5 }

	entIPPoolEnd OBJECT-TYPE
		SYNTAX IpAddress
		MAX-ACCESS read-write
    	STATUS mandatory
		DESCRIPTION
			"When system mode is not 1(Repeater) and 5(WDS bridge),
			set the end address of DHCP IP pool"
	::= { entLAN 6 }

	entIPLeaseTime OBJECT-TYPE
	    SYNTAX      INTEGER
	   	{
	   		half-hour(0),
			one-hour(1),
			two-hours(2),
			half-day(3),
			one-day(4),
			two-days(5),
			one-week(6),
			two-weeks(7),
			forever(8)
		}
		MAX-ACCESS read-write
    	STATUS mandatory
		DESCRIPTION
			"When system mode is not 1(Repeater) and 5(WDS bridge),
			the time period client can have the IP address assigned by DHCP server
			0(half hour),
			1(one hour)
			2(two hours),
			3(half day),
			4(one day),
			5(two days),
			6(one week),
			7(two weeks),
			8(forever)
			"
	::= { entLAN 7 }

--	entWAN OBJECT IDENTIFIER ::= { indoorWirelessDevice 3 }
	entRouterEnable OBJECT-TYPE
		SYNTAX TruthValue
		MAX-ACCESS read-write
    	STATUS mandatory
		DESCRIPTION
			"Only When op mode is 0(AP) or (Client bridge),
			can set this attribute. Set TRUE will enable the router."
	::= { entWAN 1 }

--	entMacFilter OBJECT IDENTIFIER ::= { indoorWirelessDevice 4 }
	entLanMacFilteringEnable OBJECT-TYPE
		SYNTAX TruthValue
		MAX-ACCESS read-write
    	STATUS mandatory
		DESCRIPTION
			"Set this attribute TRUE will enable the LAN MAC filtering"
	::= { entMacFilter 1 }

	entLanMacFilteringMode OBJECT-TYPE
		SYNTAX INTEGER
		{
			white-list(0),
			black-list(1)
		}
		MAX-ACCESS read-write
    	STATUS mandatory
		DESCRIPTION
			"The mode of LAN MAC filtering can be 0(white list), 1(black list)"
	::= { entMacFilter 2 }

	entLanMacFilterTable       OBJECT-TYPE
	    SYNTAX          SEQUENCE OF EntLanMacFilterEntry
	    MAX-ACCESS      not-accessible
	    STATUS          current
	    DESCRIPTION
	        "This table provides one row for each LAN MAC filtering.
	        Each row contains the enterprise LAN MAC filtering table
	         for that LAN MAC filtering."
	::= { entMacFilter 3 }

	entLanMacFilterEntry       OBJECT-TYPE
	    SYNTAX          EntLanMacFilterEntry
	    MAX-ACCESS      not-accessible
	    STATUS          current
	    DESCRIPTION     "An entry in the entLanMacFilterTable."
	    INDEX           { entMacAddressIndex }
	::= { entLanMacFilterTable 1 }

 	EntLanMacFilterEntry ::=
	  SEQUENCE {
	  entMacAddressIndex		INTEGER,
	  entMacAddress				MacAddress,
	  entMacFilteringValid		TruthValue,
	  }

 	entMacAddressIndex OBJECT-TYPE
	    SYNTAX      INTEGER
	   	MAX-ACCESS  read-only
	    STATUS      current
	    DESCRIPTION
	        "The auxiliary variable used to identify instances of
	        columnar objects in the LAN MAC Filtering Table"
	::= { entLanMacFilterEntry 1 }

 	entMacAddress OBJECT-TYPE
	    SYNTAX      DisplayString
	   	MAX-ACCESS  read-only
	    STATUS      current
	    DESCRIPTION
	        "MAC address list in the LAN MAC filtering table"
	::= { entLanMacFilterEntry 2 }

 	entMacFilteringValid OBJECT-TYPE
	    SYNTAX      TruthValue
	   	MAX-ACCESS  read-only
	    STATUS      current
	    DESCRIPTION
	        "The validity status of each corresponding MAC address in LAN MAC filtering table"
	::= { entLanMacFilterEntry 3 }

--	entWlan OBJECT IDENTIFIER ::= { indoorWirelessDevice 5}
--	entWlanCommonInfo OBJECT IDENTIFIER ::= { entWlan 1}

	entOpMode OBJECT-TYPE
	    SYNTAX      INTEGER
	   	{
			ap(0),
			client-bridge(1),
			wds-bridge(2),
			repeater(3)
		}
		MAX-ACCESS read-write
    	STATUS mandatory
		DESCRIPTION
			"Set op mode: 0(AP), 1(Client bridge), 2(WDS bridge), 3(Repeater)"
	::= { entWlanCommonInfo 1 }

    entRadio OBJECT-TYPE
	    SYNTAX TruthValue
	    MAX-ACCESS  read-write
	    STATUS  mandatory
	    DESCRIPTION
		    "Set this attribute TRUE will enable the radio"
	::= { entWlanCommonInfo 2 }

	entAPMode OBJECT-TYPE
	    SYNTAX      INTEGER
	   	{
			ap(0),
			wds(1)
		}
		MAX-ACCESS read-write
    	STATUS mandatory
		DESCRIPTION
			"Only when op mode is 0(AP), we can set AP mode: 0(AP), 1(WDS)"
	::= { entWlanCommonInfo 3 }

	entBand OBJECT-TYPE
	    SYNTAX      INTEGER
	   	{
			ieee802dot11-b-g(0),
			ieee802dot11-b(1),
			ieee802dot11-a(2),
			ieee802dot11-g(4),
			ieee802dot11-n(6),
			ieee802dot11-g-n(7),
			ieee802dot11-a-n(8),
			ieee802dot11-b-g-n(9)
		}
		MAX-ACCESS read-write
    	STATUS mandatory
		DESCRIPTION
			"The wireless mode: 0(802.11 b/g),
			1(802.11 b),
			2(802.11 a),
			4(802.11 g),
			6(802.11 n),
			7(802.11 g/n),
			8(802.11 a/n),
			9(802.11 b/g/n)"
	::= { entWlanCommonInfo 4 }

	entESSIDNum OBJECT-TYPE
		SYNTAX INTEGER (1..4)
		MAX-ACCESS read-write
    	STATUS mandatory
		DESCRIPTION
			"Set the Number of multiple ESSID"
	::= { entWlanCommonInfo 5 }

	entChannel OBJECT-TYPE
		SYNTAX INTEGER (1..14)
		MAX-ACCESS read-write
    	STATUS mandatory
		DESCRIPTION
			"The current operating frequency channel"
	::= { entWlanCommonInfo 6 }

	entDataRate OBJECT-TYPE
	    SYNTAX      INTEGER
        {
        	auto(0),
			oneMbps(1),
			twoMbps(2),
			fiveNhalfMbps(5),
			elevenMbps(11),
			sixMbps(6),
			nineMbps(9),
			twelveMbps(12),
			eighteenMbps(18),
			twentytwoMbps(24),
			thirtysixMbps(36),
			fortyeightMbps(48),
			fiftyfourMbps(54)
		}
		MAX-ACCESS read-write
    	STATUS mandatory
		DESCRIPTION
			"This attribute specifies the data rate at which the station may transmit data in Mbps
			0(Auto), 1(1Mbps), 2(2Mbps), 5(5.5Mbps), 11(11Mbps), 6(6Mbps), 9(9Mbps), 12(12Mbps),
			18(18Mbps), 24(24Mbps), 36(36Mbps), 48(48Mbps), 54(54Mbps)"
	::= { entWlanCommonInfo 7 }

	entNDataRate OBJECT-TYPE
		SYNTAX INTEGER
		MAX-ACCESS read-write
    	STATUS mandatory
		DESCRIPTION
			"This attribute specifies the 11n data rate"
	::= { entWlanCommonInfo 8 }

	entTxPower OBJECT-TYPE
		SYNTAX INTEGER
		MAX-ACCESS read-write
    	STATUS mandatory
		DESCRIPTION
			"The transmit power level: 10(%), 25(%), 50(%), 75(%), 90(%), 100(%)"
	::= { entWlanCommonInfo 9 }

	entBeaconInterval OBJECT-TYPE
		SYNTAX INTEGER (20..1024)
		MAX-ACCESS read-write
    	STATUS mandatory
		DESCRIPTION
			"This attribute specifies the number of TU that a station shall use
			for scheduling Beacon transmissions"
	::= { entWlanCommonInfo 10 }

	entDTIMPeriod OBJECT-TYPE
		SYNTAX INTEGER (1..255)
		MAX-ACCESS read-write
    	STATUS mandatory
		DESCRIPTION
			"This attribute specifies the number of beacon intervals"
	::= { entWlanCommonInfo 11 }

	entFragmentationThreshold OBJECT-TYPE
		SYNTAX INTEGER (256..2346)
		MAX-ACCESS read-write
    	STATUS mandatory
		DESCRIPTION
			"This attribute shall specify the current maximum size, in octets,
			of the MPDU that may be delivered to the PHY"
	::= { entWlanCommonInfo 12 }

	entRTSThreshold OBJECT-TYPE
		SYNTAX INTEGER (0..2347)
		MAX-ACCESS read-write
    	STATUS mandatory
		DESCRIPTION
			"This attribute shall indicate the number of octets in an MPDU,
			below which an RTS/CTS handshake shall not be performed."
	::= { entWlanCommonInfo 13 }

	entChannelBandwidth OBJECT-TYPE
		SYNTAX INTEGER (0..1)
		MAX-ACCESS read-write
    	STATUS mandatory
		DESCRIPTION
			"This attribute specifies the channel bandwidth: 0(Auto 20/40 MHZ), 1(20 MHZ)"
	::= { entWlanCommonInfo 14 }

	entPreambleType OBJECT-TYPE
		SYNTAX INTEGER
        {
        	short(1),
			long(2)
		}
		MAX-ACCESS read-write
    	STATUS mandatory
		DESCRIPTION
			"This attribute specifies the preamble type: 1(Short), 2(Long)"
	::= { entWlanCommonInfo 15 }

	entCTSProtection OBJECT-TYPE
		SYNTAX INTEGER
		{
			auto(0),
			always(1),
			none(2)
		}
		MAX-ACCESS read-write
    	STATUS mandatory
		DESCRIPTION
			"This attribute specifies the CTS protection: 0(Auto), 1(Always), 2(None)"
	::= { entWlanCommonInfo 16 }

	entWlanESSIDInfoTable       OBJECT-TYPE
	    SYNTAX          SEQUENCE OF EntWlanESSIDInfoEntry
	    MAX-ACCESS      not-accessible
	    STATUS          current
	    DESCRIPTION
	        "This table provides one row for each ESSID information.
	        Each row contains the enterprise ESSID information Table
	         for that ESSID information."
	::= { entWlan 2 }

	entWlanESSIDInfoEntry       OBJECT-TYPE
	    SYNTAX          EntWlanESSIDInfoEntry
	    MAX-ACCESS      not-accessible
	    STATUS          current
	    DESCRIPTION     "An entry in the entWlanESSIDInfoTable."
	    INDEX           { entWlanESSIDInfoIndex }
	::= { entWlanESSIDInfoTable 1 }

 	EntWlanESSIDInfoEntry ::=
	  SEQUENCE {
	  entWlanESSIDInfoIndex		INTEGER,
	  entESSID				OCTET STRING,
	  entBroadcastESSID		TruthValue,
	  entWMM				TruthValue,
	  entEncryption			INTEGER,
	  entWlanAuthenticationType	INTEGER
	 }

 	entWlanESSIDInfoIndex OBJECT-TYPE
	    SYNTAX      INTEGER
	   	MAX-ACCESS  read-only
	    STATUS      current
	    DESCRIPTION
	        "The auxiliary variable used to identify instances of columnar
	        objects in the ESSID information Table"
	::= { entWlanESSIDInfoEntry 1 }

 	entESSID OBJECT-TYPE
	    SYNTAX      OCTET STRING (SIZE (0..32))
	   	MAX-ACCESS  read-write
	    STATUS      current
	    DESCRIPTION
	        "This attribute reflects the Service Set ID used in
		    the Desired- SSID parameter of the most recent MLME_Scan.request"
	::= { entWlanESSIDInfoEntry 2 }

	entBroadcastESSID OBJECT-TYPE
		SYNTAX TruthValue
		MAX-ACCESS read-write
    	STATUS mandatory
		DESCRIPTION
			"Set this attribute TRUE will enable the hidden SSID"
	::= { entWlanESSIDInfoEntry 3 }

	entWMM OBJECT-TYPE
		SYNTAX TruthValue
		MAX-ACCESS read-write
    	STATUS mandatory
		DESCRIPTION
			"Set this attribute TRUE will enable WMM"
	::= { entWlanESSIDInfoEntry 4 }


 	entEncryption OBJECT-TYPE
	    SYNTAX      INTEGER (0..4)
	   	MAX-ACCESS  read-write
	    STATUS      current
	    DESCRIPTION
	        "The WLAN encryption: 0(none), 1(WEP), 2(TKIP), 3(AES), 4(TKIPAES)"
	::= { entWlanESSIDInfoEntry 5 }

 	entWlanAuthenticationType OBJECT-TYPE
	    SYNTAX      INTEGER (0..8)
	   	MAX-ACCESS  read-write
	    STATUS      current
	    DESCRIPTION
	        "The current authentication algorithms: 0 (openSystem), 1(wepAuto),
	        2(sharedKey), 3(WPAPSK), 4(WPA), 5(WPA2PSK), 6(WPA2), 7(WPA1WPA2),
	        8(WPA1PSKWPA2PSK)"
	::= { entWlanESSIDInfoEntry 6 }

	entWlanWepInfoTable			OBJECT-TYPE
	    SYNTAX          SEQUENCE OF EntWlanWepInfoEntry
	    MAX-ACCESS      not-accessible
	    STATUS          current
	    DESCRIPTION
	        "This table provides one row for each WEP information.
	        Each row contains the enterprise WEP information Table
	         for that WEP information."
	::= { entWlan 3 }

	entWlanWepInfoEntry       OBJECT-TYPE
	    SYNTAX          EntWlanWepInfoEntry
	    MAX-ACCESS      not-accessible
	    STATUS          current
	    DESCRIPTION     "An entry in the entWlanWepInfoTable."
	    INDEX           { entWlanESSIDIndex }
	::= { entWlanWepInfoTable 1 }

 	EntWlanWepInfoEntry ::=
	  SEQUENCE {
	  	entWlanESSIDIndex		INTEGER,
	  	entWlanWepKeyID 		INTEGER,
		entWlanWepKey1Value     OCTET STRING,
		entWlanWepKey2Value     OCTET STRING,
		entWlanWepKey3Value     OCTET STRING,
		entWlanWepKey4Value     OCTET STRING
	  }

 	entWlanESSIDIndex OBJECT-TYPE
	    SYNTAX      INTEGER
	   	MAX-ACCESS  read-only
	    STATUS      current
	    DESCRIPTION
	        "The auxiliary variable used to identify instances of columnar
	        objects in the WEP information Table"
	::= { entWlanWepInfoEntry 1 }

 	entWlanWepKeyID OBJECT-TYPE
	    SYNTAX      INTEGER (1..4)
	   	MAX-ACCESS  read-write
	    STATUS      current
	    DESCRIPTION
	        "This attribute shall indicate the use of the first, second, third, or fourth
	        element of the WEPDefaultKeys array"
	::= { entWlanWepInfoEntry 2 }

 	entWlanWepKey1Value OBJECT-TYPE
	    SYNTAX      OCTET STRING
	   	MAX-ACCESS  read-write
	    STATUS      current
	    DESCRIPTION
	        "Set key1 string. (5 or 13 ASCCI characters, 10 or 26 hex numbers)"
	::= { entWlanWepInfoEntry 3 }

 	entWlanWepKey2Value OBJECT-TYPE
	    SYNTAX      OCTET STRING
	   	MAX-ACCESS  read-write
	    STATUS      current
	    DESCRIPTION
	        "Set key2 string. (5 or 13 ASCCI characters, 10 or 26 hex numbers)"
	::= { entWlanWepInfoEntry 4 }

 	entWlanWepKey3Value OBJECT-TYPE
	    SYNTAX      OCTET STRING
	   	MAX-ACCESS  read-write
	    STATUS      current
	    DESCRIPTION
	        "Set key3 string. (5 or 13 ASCCI characters, 10 or 26 hex numbers)"
	::= { entWlanWepInfoEntry 5 }

 	entWlanWepKey4Value OBJECT-TYPE
	    SYNTAX      OCTET STRING
	   	MAX-ACCESS  read-write
	    STATUS      current
	    DESCRIPTION
	        "Set key4 string. (5 or 13 ASCCI characters, 10 or 26 hex numbers)"
	::= { entWlanWepInfoEntry 6 }

	entWlanWPAInfoTable			OBJECT-TYPE
	    SYNTAX          SEQUENCE OF EntWlanWPAInfoEntry
	    MAX-ACCESS      not-accessible
	    STATUS          current
	    DESCRIPTION
	        "This table provides one row for each WPA information.
	        Each row contains the enterprise WPA information Table
	         for that WPA information."
	::= { entWlan 4 }

	entWlanWPAInfoEntry       OBJECT-TYPE
	    SYNTAX          EntWlanWPAInfoEntry
	    MAX-ACCESS      not-accessible
	    STATUS          current
	    DESCRIPTION     "An entry in the entWlanWPAInfoTable."
	    INDEX           { entWlanWPAESSIDIndex }
	::= { entWlanWPAInfoTable 1 }

 	EntWlanWPAInfoEntry ::=
	  SEQUENCE {
	  entWlanWPAESSIDIndex		INTEGER,
	  entPresharedKey  	DisplayString
	 }

 	entWlanWPAESSIDIndex OBJECT-TYPE
	    SYNTAX      INTEGER
	   	MAX-ACCESS  read-only
	    STATUS      current
	    DESCRIPTION
	        "The auxiliary variable used to identify instances of columnar
	        objects in the WPA information Table"
	::= { entWlanWPAInfoEntry 1 }

 	entPresharedKey OBJECT-TYPE
	    SYNTAX      DisplayString
	   	MAX-ACCESS  write-only
	    STATUS      current
	    DESCRIPTION
	        "The WPA Pre-Shared key. (8~63 ASCII or 64 HEX)"
	::= { entWlanWPAInfoEntry 2 }

	ent802dot1xInfoTable			OBJECT-TYPE
	    SYNTAX          SEQUENCE OF Ent802dot1xInfoEntry
	    MAX-ACCESS      not-accessible
	    STATUS          current
	    DESCRIPTION
	        "This table provides one row for each 802.1x information.
	        Each row contains the enterprise 802.1x information Table
	         for that 802.1x information."
	::= { entWlan 5 }

	ent802dot1xInfoEntry       OBJECT-TYPE
	    SYNTAX          Ent802dot1xInfoEntry
	    MAX-ACCESS      not-accessible
	    STATUS          current
	    DESCRIPTION     "An entry in the ent802dot1xInfoTable."
	    INDEX           { entWlan802dot1xESSIDIndex }
	::= { ent802dot1xInfoTable 1 }

 	Ent802dot1xInfoEntry ::=
	  SEQUENCE {
	  	entWlan802dot1xESSIDIndex		INTEGER,
		entRADIUSServerIPAddress  IpAddress,
		entRADIUSServerPort		INTEGER,
		entRADIUSServerPassword	DisplayString,
		entWlan802dot1xEnable TruthValue
	  }

 	entWlan802dot1xESSIDIndex OBJECT-TYPE
	    SYNTAX      INTEGER
	   	MAX-ACCESS  read-only
	    STATUS      current
	    DESCRIPTION
	        "The auxiliary variable used to identify instances of columnar
	        objects in the 802.1x information Table"
	::= { ent802dot1xInfoEntry 1 }

 	entRADIUSServerIPAddress OBJECT-TYPE
	    SYNTAX      IpAddress
	   	MAX-ACCESS  read-write
	    STATUS      current
	    DESCRIPTION
	        "The address of RADIUS Server"
	::= { ent802dot1xInfoEntry 2 }

 	entRADIUSServerPort OBJECT-TYPE
	    SYNTAX      INTEGER (1..65535)
	   	MAX-ACCESS  read-write
	    STATUS      current
	    DESCRIPTION
	        "The port of RADIUS Server"
	::= { ent802dot1xInfoEntry 3 }

 	entRADIUSServerPassword OBJECT-TYPE
	    SYNTAX      DisplayString
	   	MAX-ACCESS  write-only
	    STATUS      current
	    DESCRIPTION
	        "The password of RADIUS Server"
	::= { ent802dot1xInfoEntry 4 }

 	entWlan802dot1xEnable OBJECT-TYPE
	    SYNTAX      TruthValue
	   	MAX-ACCESS  read-write
	    STATUS      current
	    DESCRIPTION
	        "Set this attribute TRUE will enable 802.1x"
	::= { ent802dot1xInfoEntry 5 }

-- Wlan ClientList table
   	entWlanClientListInfoTable       OBJECT-TYPE
	    SYNTAX          SEQUENCE OF EntWlanClientListInfoEntry
	    MAX-ACCESS      not-accessible
	    STATUS          current
	    DESCRIPTION
	        "This table provides one row for Wlan client list information."
	::= { entWlan 6 }

	entWlanClientListInfoEntry       OBJECT-TYPE
	    SYNTAX          EntWlanClientListInfoEntry
	    MAX-ACCESS      not-accessible
	    STATUS          current
	    DESCRIPTION     "An entry in the entWlanClientListInfoTable."
	    INDEX           { entCLInfoIndex }
	::= { entWlanClientListInfoTable 1 }

 	EntWlanClientListInfoEntry ::=
	  SEQUENCE {
	  entCLInfoIndex		INTEGER,
	  entCLInterface		OCTET STRING,
	  entCLMAC				OCTET STRING,
	  entCLRx				OCTET STRING,
	  entCLTx				OCTET STRING,
	  entCLSignal			INTEGER,
	  entCLConnectedTime	OCTET STRING,
	  entCLIdleTime	 		OCTET STRING
	 }

 	entCLInfoIndex OBJECT-TYPE
	    SYNTAX      INTEGER
	   	MAX-ACCESS  read-only
	    STATUS      current
	    DESCRIPTION
	        "The auxiliary variable used to identify instances of columnar
	        objects in the ClientList information Table"
	::= { entWlanClientListInfoEntry 1 }

 	entCLInterface OBJECT-TYPE
	    SYNTAX      OCTET STRING
	   	MAX-ACCESS  read-write
	    STATUS      current
	    DESCRIPTION
	        "The Client connected SSID"
	::= { entWlanClientListInfoEntry 2 }

	entCLMAC OBJECT-TYPE
		SYNTAX OCTET STRING
		MAX-ACCESS read-write
    	STATUS current
		DESCRIPTION
			"The Client MAC"
	::= { entWlanClientListInfoEntry 3 }

	entCLRx OBJECT-TYPE
		SYNTAX OCTET STRING
		MAX-ACCESS read-write
    	STATUS current
		DESCRIPTION
			"The Rx value"
	::= { entWlanClientListInfoEntry 4 }

 	entCLTx OBJECT-TYPE
	    SYNTAX      OCTET STRING
	   	MAX-ACCESS  read-write
	    STATUS      current
	    DESCRIPTION
	        "The Tx value"
	::= { entWlanClientListInfoEntry 5 }

 	entCLSignal OBJECT-TYPE
	    SYNTAX      INTEGER
	   	MAX-ACCESS  read-write
	    STATUS      current
	    DESCRIPTION
	        "The Client Wlan Signal"
	::= { entWlanClientListInfoEntry 6 }

 	entCLConnectedTime OBJECT-TYPE
	    SYNTAX      OCTET STRING
	   	MAX-ACCESS  read-write
	    STATUS      current
	    DESCRIPTION
	        "The Client connected time"
	::= { entWlanClientListInfoEntry 7 }

 	entCLIdleTime OBJECT-TYPE
	    SYNTAX      OCTET STRING
	   	MAX-ACCESS  read-write
	    STATUS      current
	    DESCRIPTION
	        "The Client idle time"
	::= { entWlanClientListInfoEntry 8 }

-- entSNMP OBJECT IDENTIFIER ::= { indoorWirelessDevice 6 }
    entSNMPStatus OBJECT-TYPE
	    SYNTAX TruthValue
	    MAX-ACCESS  read-write
	    STATUS  mandatory
	    DESCRIPTION
		    "The status of current SNMP agent.0:disable, 1:Enable"
	::= { entSNMP 1 }

    entSNMPVerType OBJECT-TYPE
	    SYNTAX INTEGER
	    {
			all(0),
			v1(1),
			v2c(2),
			v3(3)
		}
	    MAX-ACCESS  read-write
	    STATUS  mandatory
	    DESCRIPTION
		    "The version of current SNMP agent.0:all, 1: v1, 2:v2c, 3:v3"
	::= { entSNMP 2 }

	entSNMPCommunityTable       OBJECT-TYPE
	    SYNTAX          SEQUENCE OF EntSNMPCommunityEntry
	    MAX-ACCESS      not-accessible
	    STATUS          current
	    DESCRIPTION
	        "This table provides one row for each SNMP community.
	        Each row contains the enterprise SNMP community table
	         for that SNMP community."
	::= { entSNMP 3 }

	entSNMPCommunityEntry       OBJECT-TYPE
	    SYNTAX          EntSNMPCommunityEntry
	    MAX-ACCESS      not-accessible
	    STATUS          current
	    DESCRIPTION     "An entry in the entSNMPCommunityTable."
	    INDEX           { entSNMPCommunityIndex }
	::= { entSNMPCommunityTable 1 }

 	EntSNMPCommunityEntry ::=
	  SEQUENCE {
	  entSNMPCommunityIndex         INTEGER,
	  entSNMPCommunityName			DisplayString,
	  entSNMPCommunityType			INTEGER,
	  entSNMPCommunityValid			TruthValue,
	  }

 	entSNMPCommunityIndex OBJECT-TYPE
	    SYNTAX      INTEGER (1..2)
	   	MAX-ACCESS  read-only
	    STATUS      current
	    DESCRIPTION
	        "The auxiliary variable used to identify instances of
	        columnar objects in the SNMP Community Table"
	::= { entSNMPCommunityEntry 1 }

	entSNMPCommunityName OBJECT-TYPE
	    SYNTAX      DisplayString (SIZE (0..32))
	    MAX-ACCESS  read-write
	    STATUS      current
	    DESCRIPTION
	        "The community name used to access SNMP device."
	::= { entSNMPCommunityEntry 2 }

 	entSNMPCommunityType OBJECT-TYPE
	    SYNTAX      INTEGER
	   	{
	   		read(1),
			write(2)
		}
	    MAX-ACCESS  read-only
	    STATUS      current
	    DESCRIPTION
	        "The auxiliary variable used to identify instances of
	        columnar objects in the SNMP Community Table"
	::= { entSNMPCommunityEntry 3 }

 	entSNMPCommunityValid OBJECT-TYPE
	    SYNTAX      TruthValue
	    MAX-ACCESS  read-only
	    STATUS      current
	    DESCRIPTION
	        "Display the validity information of corresponding community index"
	::= { entSNMPCommunityEntry 4 }

	entSNMPTrap OBJECT IDENTIFIER ::= { entSNMP 4 }

    entTrapStatus OBJECT-TYPE
	    SYNTAX TruthValue
	    MAX-ACCESS  read-write
	    STATUS  mandatory
	    DESCRIPTION
		    "The trap status of current SNMP agent.0:disable, 1:Enable"
	::= { entSNMPTrap 1 }

    entTrapVer OBJECT-TYPE
	    SYNTAX INTEGER
	    {
			all(0),
			v1(1),
			v2c(2),
			v3(3)
		}
	    MAX-ACCESS  read-write
	    STATUS  mandatory
	    DESCRIPTION
		    "The trap version of current SNMP agent.0:all, 1: v1, 2:v2c, 3:v3"
	::= { entSNMPTrap 2 }

    entTrapReceiverIPAddress OBJECT-TYPE
	    SYNTAX IpAddress
	    MAX-ACCESS  read-write
	    STATUS  mandatory
	    DESCRIPTION
		    "Specify the IP address(host) to receive the trap report"
	::= { entSNMPTrap 3 }

     entTrapReceiverCommunityName OBJECT-TYPE
	    SYNTAX DisplayString
	    MAX-ACCESS  read-write
	    STATUS  mandatory
	    DESCRIPTION
		    "Specify the community name for  SNMP manager to receive the trap report"
	::= { entSNMPTrap 4 }

 	entTraps OBJECT IDENTIFIER ::= { indoorWirelessDevice 20 }
	entSystemTraps OBJECT IDENTIFIER ::= { entTraps 1 }
	entWanTraps	OBJECT IDENTIFIER ::= { entTraps 2 }

	entSystemTrapsReboot NOTIFICATION-TYPE
		STATUS current
		DESCRIPTION
		"The trap is generated when the system is rebooted."
		::= {entSystemTraps 1}

	entSystemTrapsRestoreToDefault NOTIFICATION-TYPE
		STATUS current
		DESCRIPTION
		"The trap is generated when the default configuration of the system
		is restored."
		::= {entSystemTraps 2}

	entSystemTrapsReloadModules NOTIFICATION-TYPE
		STATUS current
		DESCRIPTION
		"The trap is generated when the system modules are reloaded."
		::= {entSystemTraps 3}

	entWanTrapsLinkDisconnect NOTIFICATION-TYPE
		OBJECTS {ifIndex}
		STATUS current
		DESCRIPTION
		"The trap is generated when the PHY of WAN is disconnected and
		it was connected."
		::= {entWanTraps 1}

	entWanTrapsLinkRecover NOTIFICATION-TYPE
		OBJECTS {ifIndex}
		STATUS current
		DESCRIPTION
		"The trap is generated when the PHY of WAN is connected and
		it was disconnected"
		::= {entWanTraps 2}


END
