QTS-MIB DEFINITIONS ::= BEGIN
   IMPORTS
      enterprises, Counter, TimeTicks
         FROM RFC1155-SMI
      Integer32, Counter32, IpAddress, Unsigned32, Counter64, OBJECT-TYPE
         FROM SNMPv2-SMI
      TRAP-TYPE
         FROM RFC-1215;
      -- From RFC-1213 (MIB-II)
      DisplayString ::= OCTET STRING
    QNAP OBJECT IDENTIFIER ::= { enterprises 55062 }
    QTS OBJECT IDENTIFIER ::= { QNAP 1 }
 -- Frame Relay Multiplexer MIB groups
 -- system
 	system OBJECT IDENTIFIER ::= { QTS 12 }
 -- system Event
  systemEventMsg OBJECT IDENTIFIER ::= { system 1 }
 -- system event
  eventInformMsg OBJECT-TYPE
       SYNTAX DisplayString
       ACCESS read-only
       STATUS current
       DESCRIPTION
            "Information event of NAS system."
      ::= { systemEventMsg 101 }
  eventWarningMsg OBJECT-TYPE
      SYNTAX DisplayString
      ACCESS read-only
      STATUS current
      DESCRIPTION
           "Warning event of NAS system."
      ::= { systemEventMsg 102 }
  eventErrorMsg OBJECT-TYPE
      SYNTAX DisplayString
      ACCESS read-only
      STATUS current
      DESCRIPTION
           "Error event of NAS system."
      ::= { systemEventMsg 103 }
systemTraps OBJECT IDENTIFIER ::= { system 2 }

  eventInform NOTIFICATION-TYPE
      OBJECTS { eventInformMsg }
      STATUS current
      DESCRIPTION
           "Info: %s"
      ::= { systemTraps 1 }
  eventWarning NOTIFICATION-TYPE
      OBJECTS { eventWarningMsg }
      STATUS current
      DESCRIPTION
          "Warn: %s"
      ::= { systemTraps 2 }
  eventError NOTIFICATION-TYPE
      OBJECTS { eventErrorMsg }
      STATUS current
      DESCRIPTION
           "Error: %s"
      ::= { systemTraps 4 }
systemModel OBJECT-TYPE
    SYNTAX DisplayString
    MAX-ACCESS read-only
    STATUS current
    DESCRIPTION
            "System model name"
    ::= { system 3 }

hostname OBJECT-TYPE
    SYNTAX DisplayString
    MAX-ACCESS read-only
    STATUS current
    DESCRIPTION
            "Host name"
    ::= { system 4 }

serialNumber OBJECT-TYPE
    SYNTAX DisplayString (SIZE (0..255))
    MAX-ACCESS read-only
    STATUS current
    DESCRIPTION
            "Enclosure Serial Number."
    ::= { system 5 }

firmwareVersion OBJECT-TYPE
    SYNTAX DisplayString
    MAX-ACCESS read-only
    STATUS current
    DESCRIPTION
            "Firmware Version"
    ::= { system 6 }

firmwareUpgradeAvailable OBJECT-TYPE
    SYNTAX INTEGER
    MAX-ACCESS read-only
    STATUS current
    DESCRIPTION
            "Firmware can upgrade or not"
    ::= { system 7 }

sysFanNumber OBJECT-TYPE
    SYNTAX INTEGER
    MAX-ACCESS read-only
    STATUS current
    DESCRIPTION
            "The number of system fan (regardless of
            their current state) present on this system."
    ::= { system 8 }

systemFanTable OBJECT-TYPE
    SYNTAX SEQUENCE OF SysFanEntryDef
    MAX-ACCESS not-accessible
    STATUS current
    DESCRIPTION
            "A list of interface entries.  The number of
            entries is given by the value of SysFanNumber."
    ::= { system 9 }

sysFanEntry OBJECT-TYPE
    SYNTAX SysFanEntryDef
    MAX-ACCESS not-accessible
    STATUS current
    DESCRIPTION
            "An system fan entry containing objects at the
            subnetwork layer and below for a particular
            interface."
    INDEX { sysFanIndex }
    ::= { systemFanTable 1 }

SysFanEntryDef ::=
    SEQUENCE {
        sysFanIndex
            INTEGER,
        sysFanDescr
            DisplayString,
        sysFanSpeed
            DisplayString
    }

sysFanIndex OBJECT-TYPE
    SYNTAX INTEGER
    MAX-ACCESS read-only
    STATUS current
    DESCRIPTION
            "A unique value for each system fan. Its value
            ranges between 1 and the value of SysFanNumber.  The
            value for each interface must remain constant at
            least from one re-initialization of the entity's
            network management system to the next re-
            initialization."
    ::= { sysFanEntry 1 }

sysFanDescr OBJECT-TYPE
    SYNTAX DisplayString (SIZE (0..255))
    MAX-ACCESS read-only
    STATUS current
    DESCRIPTION
            "A textual string containing information about the
            interface.  This string should include the name of
            the manufacturer, the product name and the version
            of the hardware interface."
    ::= { sysFanEntry 2 }

sysFanSpeed OBJECT-TYPE
    SYNTAX INTEGER
    MAX-ACCESS read-only
    STATUS current
    DESCRIPTION
            "System fan speed."
    ::= { sysFanEntry 3 }
cpuTemperature OBJECT-TYPE
    SYNTAX INTEGER
    MAX-ACCESS read-only
    STATUS current
    DESCRIPTION
        "CPU temperature"
    ::= { system 10 }
systemTemperature OBJECT-TYPE
    SYNTAX INTEGER
    MAX-ACCESS read-only
    STATUS current
    DESCRIPTION
        "System temperature"
    ::= { system 11 }
systemCPU-Usage OBJECT-TYPE
    SYNTAX INTEGER
    MAX-ACCESS read-only
    STATUS current
    DESCRIPTION
        "System CPU usage"
    ::= { system 12 }

systemTotalMem OBJECT-TYPE
    SYNTAX Counter64
    MAX-ACCESS read-only
    STATUS current
    DESCRIPTION
        "System total memory"
    ::= { system 13}
systemFreeMem OBJECT-TYPE
    SYNTAX Counter64
    MAX-ACCESS read-only
    STATUS current
    DESCRIPTION
        "System free memory"
    ::= { system 14 }
systemAvailableMem OBJECT-TYPE
    SYNTAX Counter64
    MAX-ACCESS read-only
    STATUS current
    DESCRIPTION
        "System available memory"
    ::= { system 15 }

systemUsedMemory OBJECT-TYPE
    SYNTAX Counter64
    MAX-ACCESS read-only
    STATUS current
    DESCRIPTION
        "System used memory"
    ::= { system 16 }
systemCacheMemory OBJECT-TYPE
    SYNTAX Counter64
    MAX-ACCESS read-only
    STATUS current
    DESCRIPTION
        "System cached memory"
    ::= { system 17 }
systemBufferMemory OBJECT-TYPE
    SYNTAX Counter64
    MAX-ACCESS read-only
    STATUS current
    DESCRIPTION
        "System buffered memory"
    ::= { system 18 }
sysPowerStatus OBJECT-TYPE
    SYNTAX INTEGER{
                   failed(-1),
                   ok(0)
                   }
    MAX-ACCESS read-only
    STATUS current
    DESCRIPTION
         "System power status."
    ::= { system 19 }
sysUPSStatus OBJECT-TYPE
    SYNTAX INTEGER
    MAX-ACCESS read-only
    STATUS current
    DESCRIPTION
         "System UPS status."
    ::= { system 20 }
sysUptime OBJECT-TYPE
    SYNTAX TimeTicks
    MAX-ACCESS read-only
    STATUS current
    DESCRIPTION
        "The amount of time since this host was last
        initialized.  Note that this is different from
        sysUpTime in the SNMPv2-MIB [RFC1907] because
        sysUpTime is the uptime of the network management
        portion of the system."
    ::= { system 21 }
 -- services
 	services OBJECT IDENTIFIER ::= { QTS 14 }
  nfsV2V3IsEnabled OBJECT-TYPE
    SYNTAX INTEGER{
                   no(0),
                   yes(1)
                   }
    MAX-ACCESS read-only
    STATUS current
    DESCRIPTION
         "NFS V2/V3 enable flag"
    ::= { services 1 }
nfsV4IsEnabled OBJECT-TYPE
    SYNTAX INTEGER{
                   no(0),
                   yes(1)
                   }
    MAX-ACCESS read-only
    STATUS current
    DESCRIPTION
         "NFS V4 enable flag"
    ::= { services 2 }

httpPort OBJECT-TYPE
    SYNTAX INTEGER
    MAX-ACCESS read-only
    STATUS current
    DESCRIPTION
         "HTTP port"
    ::= { services 3 }
httpsPort OBJECT-TYPE
    SYNTAX INTEGER
    MAX-ACCESS read-only
    STATUS current
    DESCRIPTION
         "HTTPs port"
    ::= { services 4 }
sshIsEnabled OBJECT-TYPE
    SYNTAX INTEGER{
                   no(0),
                   yes(1)
                   }
    MAX-ACCESS read-only
    STATUS current
    DESCRIPTION
         "SSH enable flag"
    ::= { services 5 }
sshSFTPEnabled OBJECT-TYPE
    SYNTAX INTEGER{
                   no(0),
                   yes(1)
                   }
    MAX-ACCESS read-only
    STATUS current
    DESCRIPTION
         "SFTP enable flag"
    ::= { services 6 }
sshPortNumber OBJECT-TYPE
    SYNTAX INTEGER
    MAX-ACCESS read-only
    STATUS current
    DESCRIPTION
         "SSH port number"
    ::= { services 7 }
telnetIsEnabled OBJECT-TYPE
    SYNTAX INTEGER{
                   no(0),
                   yes(1)
                   }
    MAX-ACCESS read-only
    STATUS current
    DESCRIPTION
         "Telnet enable flag"
    ::= { services 8 }
telnetPortNumber OBJECT-TYPE
    SYNTAX INTEGER
    MAX-ACCESS read-only
    STATUS current
    DESCRIPTION
         "Telnet port number"
    ::= { services 9 }
ftpEnabled OBJECT-TYPE
    SYNTAX INTEGER{
                   no(0),
                   yes(1)
                   }
    MAX-ACCESS read-only
    STATUS current
    DESCRIPTION
         "FTP enable flag"
    ::= { services 10 }
ftpProtocolStandardEnabled OBJECT-TYPE
    SYNTAX INTEGER{
                   no(0),
                   yes(1)
                   }
    MAX-ACCESS read-only
    STATUS current
    DESCRIPTION
         "FTP standard protocol flag"
    ::= { services 11 }
ftpProtocolSSL-TLSEnabled OBJECT-TYPE
    SYNTAX INTEGER{
                   no(0),
                   yes(1)
                   }
    MAX-ACCESS read-only
    STATUS current
    DESCRIPTION
         "FTP SSL/TLS protocol flag"
    ::= { services 12 }
ftpPortNumber OBJECT-TYPE
    SYNTAX INTEGER
    MAX-ACCESS read-only
    STATUS current
    DESCRIPTION
         "FTP port number"
    ::= { services 13 }
ftpUnicodeSupportEnabled OBJECT-TYPE
    SYNTAX INTEGER{
                   no(0),
                   yes(1)
                   }
    MAX-ACCESS read-only
    STATUS current
    DESCRIPTION
         "FTP support unicode flag"
    ::= { services 14 }
ftpAnnonymousaccessEnabled OBJECT-TYPE
    SYNTAX INTEGER{
                   no(0),
                   yes(1)
                   }
    MAX-ACCESS read-only
    STATUS current
    DESCRIPTION
         "FTP annonymous access flag"
    ::= { services 15 }
ftpMaxConnectionsAllowed OBJECT-TYPE
    SYNTAX INTEGER
    MAX-ACCESS read-only
    STATUS current
    DESCRIPTION
         "FTP max connections"
    ::= { services 16 }
ftpMaxConnectionsPerAccount OBJECT-TYPE
    SYNTAX INTEGER
    MAX-ACCESS read-only
    STATUS current
    DESCRIPTION
         "FTP max connections per account"
    ::= { services 17 }
ftpMaxUploadRate OBJECT-TYPE
    SYNTAX INTEGER{
                   unlimited(0)
                   }
    MAX-ACCESS read-only
    STATUS current
    DESCRIPTION
         "FTP max upload rate (KB/s)"
    ::= { services 18 }
ftpMaxDownloadRate OBJECT-TYPE
    SYNTAX INTEGER{
                   unlimited(0)
                   }
    MAX-ACCESS read-only
    STATUS current
    DESCRIPTION
         "FTP max download rate (KB/s)"
    ::= { services 19 }
END
