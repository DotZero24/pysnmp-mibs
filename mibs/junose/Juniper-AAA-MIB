-- *****************************************************************************
-- Juniper-AAA-MIB
--
-- Juniper Networks Enterprise MIB
--   Authentication/Authorization/Accounting MIB
--
-- Copyright (c) 1999 Redstone Communications, Inc.
-- Copyright (c) 1999-2002 Unisphere Networks, Inc.
-- Copyright (c) 2002-2008 Juniper Networks, Inc.
--   All Rights Reserved.
-- *****************************************************************************

Juniper-AAA-MIB  DEFINITIONS ::= BEGIN

IMPORTS
    MODULE-IDENTITY, OBJECT-TYPE, Integer32, IpAddress, Counter32, Unsigned32,
    Gauge32
        FROM SNMPv2-SMI
    TEXTUAL-CONVENTION, DisplayString, RowStatus, TruthValue
        FROM SNMPv2-TC
    MODULE-COMPLIANCE, OBJECT-GROUP
        FROM SNMPv2-CONF
    juniMibs
        FROM Juniper-MIBs
    JuniName, JuniInterfaceLocationType, JuniInterfaceLocationValue, JuniVrfGroupName, JuniEnable
        FROM Juniper-TC
    juniRouterIndex
        FROM Juniper-ROUTER-MIB
    Ipv6AddressPrefix, Ipv6AddressIfIdentifier, Ipv6Address
        FROM IPV6-TC;

juniAaaMIB  MODULE-IDENTITY
    LAST-UPDATED "200810240916Z"  -- 24-Oct-08 02:46 PM EST
    ORGANIZATION "Juniper Networks, Inc."
    CONTACT-INFO
        "       Juniper Networks, Inc.
        Postal: 10 Technology Park Drive
                Westford, MA  01886-3146
                USA
        Tel:    +1 978 589 5800
        Email:  mib@Juniper.net"
    DESCRIPTION
        "The Authentication, Authorization and Accounting (AAA) MIB for the
        Juniper Networks enterprise."
    -- Revision History
    REVISION    "200810240916Z"  -- 24-Oct-08 02:46 PM EST  - JUNOSe 10.1
    DESCRIPTION
        "Added juniAaaDelegatedIpv6PrefixAsDhcpv6DelegatedPrefix and
        juniAaaFramedIpv6PrefixAsIpv6NdRaPrefix to the juniAaaAssignGeneral object."
    REVISION    "200809041034Z"  -- 04-Sep-08 02:34 AM EST  - JUNOSe 10.0
    DESCRIPTION
        "Modified juniAaaAssignTunnelCallingNumberFormat and
         juniAaaAssignTunnelCallingNumberFormatFallback of juniAaaAssignGeneral
         to include the fixed-adapter-embedded and fixed-adapter-new-field formats.
         Added juniAaaAssignDomainBackupPoolName to the juniAaaAssignDomain object."
    REVISION    "200806110533Z"  -- 11-Jun-08 01:33 AM EDT  - JUNOSe 9.3
    DESCRIPTION
        "Modified juniAaaAssignTunnelCallingNumberFormat of juniAaaAssignGeneral
         to include the SVLAN ID.
         Added juniAaaMonitorIngressTrafficOnly to the juniAaaTimeoutGeneral object."
    REVISION    "200712270944Z"  -- 27-Dec-07 04:44 AM EST  - JUNOSe 9.1
    DESCRIPTION
        "Increased maximum juniAaaIdleTimeout value to 24Hr.
        Added juniAaaAssignDomainTunnelSubscriberAuthentication for enable
        or disable suberscriber to authenticate with configured authentication
        server when there are tunnel configurations under the domain"
    REVISION    "200710040133Z"  -- 03-Oct-07 09:33 PM EDT  - JUNOSe 7.3
    DESCRIPTION
        "Added juniAaaAssignDomainAuthRouterName, juniAaaAssignDomainIpRouterName,
        juniAaaAssignDomainRouterName is deprecated and becomes read-only."
    REVISION    "200707311934Z"  -- 31-Jul-07 01:34 PM EDT  - JUNOSe 8.1
    DESCRIPTION
        "Added juniAaaServiceAcctInterval for the default service
        accounting interval; added juniAaaUserAcctInterval for the
        default user accounting interval; changed juniAaaAcctInterval
        to set both juniAaaServiceAcctInterval, and juniAaaUserAcctInterval;
        get of juniAaaAcctInterval only returns the juniAaaUserAcctInterval
        value"
    REVISION    "200608021834Z"  -- 02-Aug-06 02:34 PM EDT  - JUNOSe 8.1
    DESCRIPTION
        "Added new values to juniAaaAssignTunnelCallingNumberFormat. Added
        juniAaaAssignTunnelCallingNumberFormatFallback "
    REVISION    "200607111305Z"  -- 11-Jul-06 09:05 AM EDT  - JUNOSe 8.1
    DESCRIPTION
    "Added juniAaaAssignQosDownstreamRate."
    REVISION    "200608021333Z"  -- 02-Aug-06 09:33 AM EDT  - JUNOSe 7.3
    DESCRIPTION
        "Added juniAaaAssignDomainTunnelFailoverResync, juniAaaTunnelGroupTunnelFailoverResync.
        Added juniAaaSubscriberInterfaceSummaryTable, juniAaaSubscriberInterfaceSummaryEntry,
        juniAaaSubscriberInterfaceSummaryIndex, juniAaaSubscriberSubInterfaceSummaryIndex,
        juniAaaSubscriberInterfaceSummaryCount, juniAaaSubscriberInterfaceTable,
        juniAaaSubscriberInterfaceEntry, juniAaaSubscriberInterfaceEntry,
        juniAaaSubscriberInterfaceIndex, juniAaaSubscriberSubInterfaceIndex,
        juniAaaSubscriberInterfaceHandle, juniAaaSubscriberInterfaceRowStatus,
        juniAaaSubscriberSlotSummaryTable, juniAaaSubscriberSlotSummaryEntry,
        juniAaaSubscriberSlotSummarySlotIndex, juniAaaSubscriberSlotSummaryCount,
        juniAaaSubscriberSlotTable, juniAaaSubscriberSlotSummaryEntry,
        juniAaaSubscriberSlotIndex, juniAaaSubscriberSlotHandle,
        juniAaaSubscriberSlotRowStatus.
        Added juniAaaAssignDomainTunnelPeerResyncMechanism and
        juniAaaTunnelGroupTunnelPeerResyncMechanism,
        juniAaaTunnelGroupTunnelFailoverResync,
        juniAaaAssignDomainTunnelTxConnectSpeedMethod,
        juniAaaTunnelGroupTunnelTxConnectSpeedMethod,
        juniAaaTunnelTxConnectSpeedMethod."
    REVISION    "200602211554Z"  -- 21-Feb-06 10:54 AM EST - JUNOSe 7.1
    DESCRIPTION
        "Added juniAaaAssignAccountingStatisticsType support.
         Added juniAaaSubscriberExt table support.
         Added l2tp tunnel switch profile support.
         Added juniAaaTunnelSwitchProfile.
         Added IPsec client support."
    REVISION    "200501312201Z"  -- 31-Jan-05 05:01 PM EST  - JUNOSe 7.0
    DESCRIPTION
        "Added juniAaaTunnelGroup support. Added new values to
        juniAaaAssignTunnelCallingNumberFormat."
    REVISION    "200412032212Z"  -- 03-Dec-04 05:12 PM EST  - JUNOSe 6.1
    DESCRIPTION
        "Added juniAaaLocalAuthUser, juniAaaLocalAuthUserDb, and
        juniAaaLocalAuthUserDbAssoc groups to support local authentication
        Added broadcast accounting support: juniAaaAcctBcastServerGroupTable,
        juniAaaAcctBcastServerGroupName, juniAaaOutgoingBcastAcctRequests and
        juniAaaIncomingBcastAcctResponses."
    REVISION    "200405202133Z"  -- 20-May-04 05:33 PM EDT  - JUNOSe 6.0
    DESCRIPTION
        "Added second generation E-series platform support:
            Imported JuniInterfaceLocationType and JuniInterfaceLocationValue
            from Juniper-TC to replace JuniSubscriberLocationType and
            JuniSubscriberLocationValue textual conventions, respectively.
        Increase range for juniAaaSessionTimeout.
        Added support for juniAaaInterfaceAdapterFormat."
    REVISION    "200407261702Z"  -- 26-Jul-04 01:02 PM EDT  - JUNOSe 5.3
    DESCRIPTION
        "Added new states to JuniSubscriberState.  Added realm and domain
        parse direction.  Added juniAaaAuthMethodsTable and
        juniAaaAcctMethodsTable.  Added juniAaaAcctSendImmediateAcctUpdate to
        control the sending of immediate interim accounting updates."
    REVISION    "200305071807Z"  -- 07-May-03 02:07 PM EDT  - JUNOSe 5.1
    DESCRIPTION
        "Added support for juniAaaAssignTunnelCallingNumberFormat.
         Added support for juniAaaInterfaceIdFormat.
         Added support for IPv6."
    REVISION    "200305052025Z"  -- 05-May-03 04:25 PM EDT  - JUNOSe 5.0
    DESCRIPTION
        "Replaced Unisphere names with Juniper names.
         Added juniAaaArssignDomainPoolName.
         Extend range of juniAaaAcctInterval to 24 hours.
         Added support for PPPoE active discovery network (PADN)."
    REVISION    "200304291409Z"  -- 29-Apr-03 10:09 AM EDT  - JUNOSe 4.1
    DESCRIPTION
        "Added protocolTacacaPlus and protoctolEnable to
            JuniAaaAuthenticationMethods.
         Added juniAaaAssignDomainPoolName.
         Added juniAaaAssignDomainTunnelMaxSessions."
    REVISION    "200304251603Z"  -- 25-Apr-03 12:03 PM EDT  - JUNOSe 4.0
    DESCRIPTION
        "Added support for additional AAA objects:
            juniAaaAssignSubscriberLimit,
            juniAaaAcctSendStopOnAaaDeny,
            juniAaaAcctSendStopOnAaaReject,
            juniAaaTunnelIgnoreNasPort,
            juniAaaTunnelIgnoreNasPortType,
            juniAaaTunnelAssignmentIdFormat,
            juniAaaSubscriberPseudoCount,
            juniAaaSubscriberPseudoPeakCount.
         Removed L2F support from juniAaaAssignDomainTunnelType."
    REVISION    "200208011950Z"  -- 01-Aug-02 03:50 PM EDT  - JUNOSe 3.4
    DESCRIPTION
        "Added interface location-relative subscriber management attributes
        under juniAaaSubscribers.  Increase ranges for juniAaaSessionTimeout and
        juniAaaAcctInterval."
    REVISION    "200110051325Z"  -- 05-Oct-01 09:25 AM EDT  - JUNOSe 3.3
    DESCRIPTION
        "Added subscriber management attributes under juniAaaSubscribers,
        capabilities management attributes under juniAaaCapabilities."
    REVISION    "200110031905Z"  -- 03-Oct-01 03:05 PM EDT  - JUNOSe 3.2
    DESCRIPTION
        "Added assignment delimiter attributes:
            juniAaaAssignDomainDelimiters
            juniAaaAssignRealmDelimiters
            juniAaaAssignDomainParseOrder
            juniAaaTunnelClientName
            juniAaaTunnelPassword
            juniAaaTunnelNasPortMethod;
         also, resized:
            juniAaaAssignDomainTunnelHostName
            juniAaaAssignDomainTunnelServerName "
    REVISION    "200103011703Z"  -- 01-Mar-01 12:03 PM EST  - JUNOSe 3.1
    DESCRIPTION
        "Added juniAaaAssignDomainStripDomain"
    REVISION    "200102121954Z"  -- 12-Feb-01 02:54 PM EST  - JUNOSe 3.0
    DESCRIPTION
        "Added parameters to the juniAaaAssignDomainTunnelTable:
            juniAaaAssignDomainTunnelServerName
            juniAaaAssignDomainTunnelClientAddress
         Added juniAaaDupAddrCheck, juniAaaIdleTimeout and juniAaaSessionTimeout
         parameters."
    REVISION    "200005180000Z"  -- 18-May-00               - JUNOSe 2.0
    DESCRIPTION
        "Added ATM traffic shaping parameters to juniAaaAssignDomainTable.
         Added juniAaaAssignDomainTunnelTable.
         Added 'dhcp' as an option for juniAaaAddrAddrPoolDefault;
           use of the value 'none' has been discontinued.
         Added statistics to track the performance of AAA."
    REVISION    "9906010000Z"    --  1-Jun-99               - JUNOSe 1.1
    DESCRIPTION
        "Initial version of this MIB module."
    ::= { juniMibs 20 }


-- +++++++++++++++++++++++++++++++++++++++++++++++++++++++++++++++++++++++++++++
-- Textual conventions
-- +++++++++++++++++++++++++++++++++++++++++++++++++++++++++++++++++++++++++++++
JuniAaaDomainName  ::= TEXTUAL-CONVENTION
    DISPLAY-HINT "63a"
    STATUS      current
    DESCRIPTION
        "The name of an internet domain.  Represents textual information taken
        from the NVT ASCII character set."
    REFERENCE
        "RFC 854: NVT ASCII character set.  See SNMPv2-TC.DisplayString
        DESCRIPTION for a summary."
    SYNTAX      OCTET STRING (SIZE(1..63))

JuniAaaTunnelGroupName  ::= TEXTUAL-CONVENTION
    DISPLAY-HINT "63a"
    STATUS      current
    DESCRIPTION
        "The name of a tunnel group.  Represents textual information taken
        from the NVT ASCII character set."
    REFERENCE
        "RFC 854: NVT ASCII character set.  See SNMPv2-TC.DisplayString
        DESCRIPTION for a summary."
    SYNTAX      OCTET STRING (SIZE(1..63))

JuniAaaTunnelSwitchProfileName  ::= TEXTUAL-CONVENTION
    DISPLAY-HINT "64a"
    STATUS      current
    DESCRIPTION
        "The name of a tunnel switch profile.  Represents textual
         information taken from the NVT ASCII character set."
    REFERENCE
        "RFC 854: NVT ASCII character set.  See SNMPv2-TC.DisplayString
        DESCRIPTION for a summary."
    SYNTAX      OCTET STRING (SIZE(0..64))

JuniAaaAuthenticationMethods  ::= TEXTUAL-CONVENTION
    STATUS      current
    DESCRIPTION
        "The set of configurable authentication choices.  The maximum enumerated
        type will never be greater than 255."
    SYNTAX      INTEGER {
                    protocolRadius(1),
                    protocolNone(4),
                    protocolLine(5),
                    protocolTacacsPlus(6),
                    protocolEnable(7) }

JuniAaaAccountingMethods  ::= TEXTUAL-CONVENTION
    STATUS      current
    DESCRIPTION
        "The set of configurable accounting choices."
    SYNTAX      INTEGER {
                    protocolRadius(1),
                    protocolNone(4) }

JuniAddressAssignType  ::= TEXTUAL-CONVENTION
    STATUS      current
    DESCRIPTION
        "The set of possible AAA address assignment sources."
    SYNTAX      INTEGER {
                    none(0),
                    radius(1),
                    localPool(2),
                    dhcp(3),
                    user(4),
                    application(5),
                    localAuthenticationServer(6),
                    notSet(7) }

JuniSubscriberState  ::= TEXTUAL-CONVENTION
    STATUS      current
    DESCRIPTION
        "The set of possible AAA subscriber states, expressed as a bit map:
            init            Initial state (transient)
            pending         Auth/Acct or Addr Request is pending
            established     Subscriber is authenticated
            deleting        Deletion of subscriber is pending
            tunneling       Subscriber is being tunneled
            tunnelAcct      Tunnel accounting is enabled
            terminated      Subscriber has been terminated
            counted         Subscriber has been counted in statistics
            clientHandleSet Client handle is assigned to user profile
            sentAcctStart   Start accounting record is requested

        More than one state bit can be active simultaneously.  If no bits are
        set, the subscriber is in a transient initial state."
    SYNTAX      BITS {
                    pending(0),
                    established(1),
                    deleting(2),
                    tunneling(3),
                    tunnelAcct(4),
                    terminated(5),
                    counted(6),
                    clientHandleSet(7),
                    sentAcctStart(8) }

JuniSubscriberClientType  ::= TEXTUAL-CONVENTION
    STATUS      current
    DESCRIPTION
        "The set of possible AAA subscriber client types:
            ppp         PPP client
            login       Command line interface or SSH
            ip          IP-based application
            config      Locally configured client identity
            tunnel      Tunnel e.g. L2TP
            other       Unspecified client type "
    SYNTAX      INTEGER {
                    ppp(0),
                    login(1),
                    ip(2),
                    config(3),
                    tunnel(4),
                    other(5) }

JuniSubscriberLocationType  ::= TEXTUAL-CONVENTION
    STATUS      obsolete
    DESCRIPTION
        "Obsolete description of the platform-dependent interpretation of a
        JuniAtmLocationValue object.  This textual convention has been relpaced
        by Juniper-TC.JuniInterfaceLocationType."
    SYNTAX      INTEGER {
                    unknown(0),
                    slotPort(1) }

JuniSubscriberLocationValue  ::= TEXTUAL-CONVENTION
    STATUS      obsolete
    DESCRIPTION
        "Obsolete value of a platform-dependent interface location, represented
        as an OCTET STRING.  A corresponding JuniAtmLocationType object
        identified the mapping of octets to location elements, e.g. 'slot.port'.
        This textual convention has been replaced by
        Juniper-TC.JuniInterfaceLocationValue."
    SYNTAX      OCTET STRING (SIZE(1..16))

JuniSubscriberInterfaceValue  ::= TEXTUAL-CONVENTION
    STATUS      current
    DESCRIPTION
        "Value of the sub-interface, represented as an OCTET STRING."
    SYNTAX      OCTET STRING (SIZE(1..16))

JuniAaaAuthenticationSubscriberTypes  ::= TEXTUAL-CONVENTION
    STATUS      current
    DESCRIPTION
        "The set of authentication subscriber types.  The maximum enumerated
        type will never be greater than 255."
    SYNTAX      INTEGER {
                    ppp(1),
                    atm1483(2),
                    ip(3),
                    tunnel(4),
                    radiusRelay(5),
                    ipsec (6)  }

JuniAaaAccountingSubscriberTypes  ::= TEXTUAL-CONVENTION
    STATUS      current
    DESCRIPTION
        "The set of accounting subscriber types.  The maximum enumerated
        type will never be greater than 255."
    SYNTAX      INTEGER {
                    ppp(1),
                    atm1483(2),
                    ip(3),
                    tunnel(4),
                    radiusRelay(5),
                    ipsec (6)  }


-- +++++++++++++++++++++++++++++++++++++++++++++++++++++++++++++++++++++++++++++
-- Managed object groups
-- +++++++++++++++++++++++++++++++++++++++++++++++++++++++++++++++++++++++++++++
juniAaaObjects                OBJECT IDENTIFIER ::= { juniAaaMIB 1 }

-- Functional groups

juniAaaAssignment             OBJECT IDENTIFIER ::= { juniAaaObjects 1 }
juniAaaAuthentication         OBJECT IDENTIFIER ::= { juniAaaObjects 2 }
juniAaaAccounting             OBJECT IDENTIFIER ::= { juniAaaObjects 3 }
juniAaaAddress                OBJECT IDENTIFIER ::= { juniAaaObjects 4 }
juniAaaStatistics             OBJECT IDENTIFIER ::= { juniAaaObjects 5 }
juniAaaTimeout                OBJECT IDENTIFIER ::= { juniAaaObjects 6 }
juniAaaTunnel                 OBJECT IDENTIFIER ::= { juniAaaObjects 7 }
juniAaaSubscribers            OBJECT IDENTIFIER ::= { juniAaaObjects 8 }
juniAaaCapabilities           OBJECT IDENTIFIER ::= { juniAaaObjects 9 }


-- +++++++++++++++++++++++++++++++++++++++++++++++++++++++++++++++++++++++++++++
-- Managed objects for Assignment functions
-- +++++++++++++++++++++++++++++++++++++++++++++++++++++++++++++++++++++++++++++
juniAaaAssignGeneral          OBJECT IDENTIFIER ::= { juniAaaAssignment 1 }

juniAaaAssignBrasLicense OBJECT-TYPE
    SYNTAX      DisplayString (SIZE(0..16))
    MAX-ACCESS  read-write
    STATUS      current
    DESCRIPTION
        "The license string that determines the system-wide maximum number of
        remote user connections allowed.  A zero-length string (no license)
        prohibits remote user connections."
    ::= { juniAaaAssignGeneral 1 }

juniAaaAssignBrasLicensedUsers OBJECT-TYPE
    SYNTAX      Integer32
    MAX-ACCESS  read-only
    STATUS      current
    DESCRIPTION
        "The system-wide maximum number of remote user connections allowed by
        the currently configured license string."
    ::= { juniAaaAssignGeneral 2 }

juniAaaAssignDomainDelimiters OBJECT-TYPE
    SYNTAX      DisplayString (SIZE(0..8))
    MAX-ACCESS  read-write
    STATUS      current
    DESCRIPTION
        "The list of delimiters used to separate the user's name from the user's
         domain in the username field.  The default is '@'."
    ::= { juniAaaAssignGeneral 3 }

juniAaaAssignRealmDelimiters OBJECT-TYPE
    SYNTAX      DisplayString (SIZE(0..8))
    MAX-ACCESS  read-write
    STATUS      current
    DESCRIPTION
        "The list of delimiters used to separate the user's name from the user's
        realm in the username field.  The realm is treated like the domain in
        the ERX.  The default is none."
    ::= { juniAaaAssignGeneral 4 }

juniAaaAssignDomainParseOrder OBJECT-TYPE
    SYNTAX      INTEGER {
                    domainFirst(1),
                    realmFirst(2) }
    MAX-ACCESS  read-write
    STATUS      current
    DESCRIPTION
        "The order in which the user's name is parsed: either search for domain
        first or realm first in the form (realm/user@domain.com).  The default
        is domain first."
    DEFVAL    { realmFirst }
    ::= { juniAaaAssignGeneral 5 }

juniAaaAssignSubscriberLimit OBJECT-TYPE
    SYNTAX      Integer32 (0..32000)
    UNITS       "users"
    MAX-ACCESS  read-write
    STATUS      current
    DESCRIPTION
        "The maximum number of subscribers permitted in this VR context.  The
        value '0' means no limit."
    ::= { juniAaaAssignGeneral 6 }

juniAaaAssignDomainMaxPadnPerDomain OBJECT-TYPE
    SYNTAX      Unsigned32
    MAX-ACCESS  read-only
    STATUS      current
    DESCRIPTION
        "The maximum number of PPPoE active discovery network (PADN) entries
        permitted in a domain entry."
    ::= { juniAaaAssignGeneral 7 }

juniAaaInterfaceIdFormat OBJECT-TYPE
    SYNTAX      INTEGER {
                    includeSubIntf(1),
                    excludeSubIntf(2) }
    MAX-ACCESS  read-write
    STATUS      current
    DESCRIPTION
        "The interface ID format: include or exclude sub-interface per VR.  The
        sub-interface is included or excluded at the time of the initial AAA
        request for the user and remains for the duration of the login."
    DEFVAL    { includeSubIntf }
    ::= { juniAaaAssignGeneral 8 }

juniAaaAssignTunnelCallingNumberFormat OBJECT-TYPE
    SYNTAX      INTEGER {
                    descriptive(1),
                    fixed(2),
                    descriptiveIncludeAgentCircuitId(3),
                    descriptiveIncludeAgentRemoteId(4),
                    descriptiveIncludeAgentCircuitIdAndAgentRemoteId(5),
                    agentCircuitId(6),
                    agentRemoteId(7),
                    agentCircuitIdIncludeAgentRemoteId(8),
                    fixedIncludeSvlanId(9),
                    fixedAdapterEmbedded(10),
                    fixedAdapterNewField(11),
                    fixedAdapterEmbeddedIncludeSvlanId(12),
                    fixedAdapterNewFieldIncludeSvlanId(13)}
    MAX-ACCESS  read-write
    STATUS      current
    DESCRIPTION
        "The format of the interface identifier passed to L2TP during an
        authentication request. L2TP uses this identifier as the calling-number
        (type 22) attribute value. Note: if selected components of the calling
         number format are not available (i.e. PPPoE Agent Circuit Id and Agent
         Remote Id), then the juniAaaAssignTunnelCallingNumberFallbackFormat will
         be used. Optionally the SVLAN ID inclusion can be enabled"
    DEFVAL    { descriptive }
    ::= { juniAaaAssignGeneral 9 }

juniAaaAssignDomainParseDirection OBJECT-TYPE
    SYNTAX      INTEGER {
                    rightToLeft(1),
                    leftToRight(2) }
    MAX-ACCESS  read-write
    STATUS      current
    DESCRIPTION
        "The direction in which the user's name is parsed: either search
        for domain delimiter from left to right or right to left; first
        delimiter marks boundry. The default is right to left."
    DEFVAL    { rightToLeft }
    ::= { juniAaaAssignGeneral 10 }

juniAaaAssignRealmParseDirection OBJECT-TYPE
    SYNTAX      INTEGER {
                    rightToLeft(1),
                    leftToRight(2) }
    MAX-ACCESS  read-write
    STATUS      current
    DESCRIPTION
        "The direction in which the user's name is parsed: either search
        for realm delimiter from left to right or right to left; first
        delimiter marks boundry. The default is left to right."
    DEFVAL    { leftToRight }
    ::= { juniAaaAssignGeneral 11 }

juniAaaInterfaceAdapterFormat OBJECT-TYPE
    SYNTAX      INTEGER {
                    includeAdapter(1),
                    excludeAdapter(2) }
    MAX-ACCESS  read-write
    STATUS      current
    DESCRIPTION
        "The interface adapter format: include or exclude the adapter if present field
        per VR. The adapter field is included or excluded at the time of the initial
        AAA request for the user and remains for the duration of the login."
    DEFVAL    { includeAdapter }
    ::= { juniAaaAssignGeneral 12 }

juniAaaAssignAccountingStatisticsType OBJECT-TYPE
    SYNTAX      INTEGER {
                    full(0),
                    uptime(1) }
    MAX-ACCESS  read-write
    STATUS      current
    DESCRIPTION
        "The method for collecting AAA acounting statistics. When value is 'full',
         collect a full set of statistics for AAA accounting. When the value is
         'uptime', collect only uptime value for AAA accounting."
    DEFVAL    { full }
    ::= { juniAaaAssignGeneral 13 }

juniAaaAssignQosDownstreamRate OBJECT-TYPE
    SYNTAX      JuniEnable
    MAX-ACCESS  read-write
    STATUS      current
    DESCRIPTION
        "Enables/disables the reporting of the dsl downstream rate information
         to Qos."
    DEFVAL    { disable }
    ::= { juniAaaAssignGeneral 14 }

juniAaaAssignTunnelCallingNumberFormatFallback OBJECT-TYPE
    SYNTAX      INTEGER {
                    descriptive(1),
                    fixed(2),
                    fixedIncludeSvlanId(3),
                    fixedAdapterEmbedded(4),
                    fixedAdapterNewField(5),
                    fixedAdapterEmbeddedIncludeSvlanId(6),
                    fixedAdapterNewFieldIncludeSvlanId(7) }
    MAX-ACCESS  read-write
    STATUS      current
    DESCRIPTION
        "The fallback format of the interface identifier passed to L2TP during an
        authentication request.  L2TP uses this identifier as the calling-number
        (type 22) attribute value."
    DEFVAL    { descriptive }
    ::= { juniAaaAssignGeneral 15 }

juniAaaFramedIpv6PrefixAsIpv6NdRaPrefix OBJECT-TYPE
    SYNTAX      TruthValue
    MAX-ACCESS  read-write
    STATUS      current
    DESCRIPTION
        "Enables/disables the use of framed-ipv6-prefix RADIUS attribute
        for IPv6 ND router advertisement."
    DEFVAL    { false }
    ::= { juniAaaAssignGeneral 16 }

juniAaaDelegatedIpv6PrefixAsDhcpv6DelegatedPrefix OBJECT-TYPE
    SYNTAX      TruthValue
    MAX-ACCESS  read-write
    STATUS      current
    DESCRIPTION
        "Enables/disables the use of delegated-ipv6-prefix RADIUS attribute
        for DHCPv6 prefix delegation."
    DEFVAL    { false }
    ::= { juniAaaAssignGeneral 17 }


juniAaaAssignDomain           OBJECT IDENTIFIER ::= { juniAaaAssignment 2 }

juniAaaAssignDomainTable OBJECT-TYPE
    SYNTAX      SEQUENCE OF JuniAaaAssignDomainEntry
    MAX-ACCESS  not-accessible
    STATUS      current
    DESCRIPTION
        "The entries in this table specify the assignment of a remote access
        user to a virtual router, based on the user's domain."
    ::= { juniAaaAssignDomain 1 }

juniAaaAssignDomainEntry OBJECT-TYPE
    SYNTAX      JuniAaaAssignDomainEntry
    MAX-ACCESS  not-accessible
    STATUS      current
    DESCRIPTION
        "A specification of the virtual router to which users on a specified
        domain should be assigned."
    INDEX     { IMPLIED juniAaaAssignDomainName }
    ::= { juniAaaAssignDomainTable 1 }

JuniAaaAssignDomainEntry ::= SEQUENCE {
    juniAaaAssignDomainName               JuniAaaDomainName,
    juniAaaAssignDomainRowStatus          RowStatus,
    juniAaaAssignDomainRouterName         JuniName,
    juniAaaAssignDomainLoopback           Integer32,
    juniAaaAssignDomainIpHint             TruthValue,
    juniAaaAssignDomainAtmServiceLevel    INTEGER,
    juniAaaAssignDomainAtmPcr             Unsigned32,
    juniAaaAssignDomainAtmScr             Unsigned32,
    juniAaaAssignDomainAtmMbs             Unsigned32,
    juniAaaAssignDomainOverrideUserName   DisplayString,
    juniAaaAssignDomainOverridePassword   OCTET STRING,
    juniAaaAssignDomainStripDomain        TruthValue,
    juniAaaAssignDomainPoolName           DisplayString,
    juniAaaAssignDomainLocalInterface     DisplayString,
    juniAaaAssignDomainIpv6RouterName     JuniName,
    juniAaaAssignDomainIpv6LocalInterface DisplayString,
    juniAaaAssignDomainTunnelGroup        JuniAaaTunnelGroupName,
    juniAaaAssignDomainAuthRouterName     JuniName,
    juniAaaAssignDomainIpRouterName       JuniName,
    juniAaaAssignDomainTunnelSubscriberAuthentication TruthValue,
    juniAaaAssignDomainBackupPoolName     DisplayString }

juniAaaAssignDomainName OBJECT-TYPE
    SYNTAX      JuniAaaDomainName
    MAX-ACCESS  read-only
    STATUS      current
    DESCRIPTION
        "The domain name uniquely identifying this entry."
    ::= { juniAaaAssignDomainEntry 1 }

juniAaaAssignDomainRowStatus OBJECT-TYPE
    SYNTAX      RowStatus
    MAX-ACCESS  read-create
    STATUS      current
    DESCRIPTION
        "Controls creation/deletion of entries in this table.  Only the values
        'createAndGo' and 'destroy' may be SET."
    ::= { juniAaaAssignDomainEntry 2 }

juniAaaAssignDomainRouterName OBJECT-TYPE
    SYNTAX      JuniName
    MAX-ACCESS  read-only
    STATUS      deprecated
    DESCRIPTION
        "This variable is replaced by juniAaaAssignDomainAuthRouterName and
        juniAaaAssignDomainIpRouterName. It returns same value as
        juniAaaAssignDomainAuthRouterName."
    ::= { juniAaaAssignDomainEntry 3 }

juniAaaAssignDomainLoopback OBJECT-TYPE
    SYNTAX      Integer32 (-1..32000)
    MAX-ACCESS  read-create
    STATUS      obsolete
    DESCRIPTION
        "The number of the loopback interface, associated with the specified
        virtual router, whose IP address is used as the source address when
        transmitting IP packets on unnumbered remote access user links.

        For example, if the associated loopback interface for this domain/router
        was configured via the console as 'loopback 2', this object would
        contain the integer value 2.

        A value of -1 indicates the loopback interface is unspecified."
    DEFVAL    { -1 }
    ::= { juniAaaAssignDomainEntry 4 }

juniAaaAssignDomainIpHint OBJECT-TYPE
    SYNTAX      TruthValue
    MAX-ACCESS  read-create
    STATUS      current
    DESCRIPTION
        "Enables/disables the IP hint feature, which causes the system to
        allocate an IP address before going to RADIUS for authentication."
    DEFVAL    { false }
    ::= { juniAaaAssignDomainEntry 5 }

juniAaaAssignDomainAtmServiceLevel OBJECT-TYPE
    SYNTAX      INTEGER {
                    none(0),
                    ubr(1),
                    ubrPcr(2),
                    nrtVbr(3),
                    cbr(4),
                    rtVbr(5) }
    MAX-ACCESS  read-create
    STATUS      current
    DESCRIPTION
        "The Service category for this circuit:
            ubr         Unspecified bit rate (best effort).
            ubrPcr      Unspecified Bit Rate with Peak Cell Rate limit.
            nrtVbr      Non-realtime Variable Bit Rate.
            cbr         Constant bit rate.
            rtVbr       Realtime Variable Bit Rate.

        Set the service level in combination of the traffic attributes
        PCR/SCR/MBS in the following matrix for successfull configurations.

             ServiceLevel     PCR       SCR        MBS
             ------------------------------------------
             ubr              omit      omit       omit
             ubrPcr           must      omit       omit
             nrtVbr           must      must       must
             cbr              must      omit       omit
             rtVbr            must      must       must "
    DEFVAL    { none }
    ::= { juniAaaAssignDomainEntry 6 }

juniAaaAssignDomainAtmPcr OBJECT-TYPE
    SYNTAX      Unsigned32 (0..4294967294)
    UNITS       "kbps"
    MAX-ACCESS  read-create
    STATUS      current
    DESCRIPTION
        "Peak Cell Rate, in kilobits per second (kbps), of this circuit.

        This parameter is only required when juniAaaAssignDomainAtmServiceLevel
        is configured to have one of the following values:
            ubrPcr
            nrtVbr
            cbr "
    DEFVAL    { 0 }
    ::= { juniAaaAssignDomainEntry 7 }

juniAaaAssignDomainAtmScr OBJECT-TYPE
    SYNTAX      Unsigned32 (0..4294967294)
    UNITS       "kbps"
    MAX-ACCESS  read-create
    STATUS      current
    DESCRIPTION
        "Sustained Cell Rate, in kilobits per second (kbps), of this circuit.

        This parameter is only required when juniAaaAssignDomainAtmServiceLevel
        is configured to have one of the following values:
            nrtVbr "
    DEFVAL    { 0 }
    ::= { juniAaaAssignDomainEntry 8 }

juniAaaAssignDomainAtmMbs OBJECT-TYPE
    SYNTAX      Unsigned32 (0..4294967294)
    UNITS       "cells"
    MAX-ACCESS  read-create
    STATUS      current
    DESCRIPTION
        "Maximum Burst Size, in cells, of this circuit.

        This parameter is only required when juniAaaAssugbDomainAtmServiceLevel
        is configured to have one of the following values:
            nrtVbr "
    DEFVAL    { 0 }
    ::= { juniAaaAssignDomainEntry 9 }

juniAaaAssignDomainOverrideUserName OBJECT-TYPE
    SYNTAX      DisplayString (SIZE(0..32))
    MAX-ACCESS  read-create
    STATUS      current
    DESCRIPTION
        "The override user name associated with this entry.  This object is used
        to override the user name of the remote client."
    DEFVAL    { "" }
    ::= { juniAaaAssignDomainEntry 10 }

juniAaaAssignDomainOverridePassword OBJECT-TYPE
    SYNTAX      OCTET STRING (SIZE(0..32))
    MAX-ACCESS  read-create
    STATUS      current
    DESCRIPTION
        "The override password for the user name defined by
        juniAaaAssignDomainOverrideUserName.  This object is used to override
        the password part of the username/password pair of the remote client.
        This value returns a string length of 0 on reads for security reasons."
    DEFVAL    { "" }
    ::= { juniAaaAssignDomainEntry 11 }

juniAaaAssignDomainStripDomain OBJECT-TYPE
    SYNTAX      TruthValue
    MAX-ACCESS  read-create
    STATUS      current
    DESCRIPTION
        "Enables/disables the domain name stripping feature, which causes the
        system to strip the domain name before sending the access-request to
        RADIUS for authentication."
    DEFVAL    { false }
    ::= { juniAaaAssignDomainEntry 12 }

juniAaaAssignDomainPoolName OBJECT-TYPE
    SYNTAX      DisplayString (SIZE(0..16))
    MAX-ACCESS  read-create
    STATUS      current
    DESCRIPTION
        "The name of the local address pool from which to allocate an IP address
        for the subscriber when none is returned from the authentication
        server."
    DEFVAL    { "" }
    ::= { juniAaaAssignDomainEntry 13 }

juniAaaAssignDomainLocalInterface OBJECT-TYPE
    SYNTAX      DisplayString (SIZE(0..64))
    MAX-ACCESS  read-create
    STATUS      current
    DESCRIPTION
        "The local interface, associated with the specified virtual router,
        whose IP address is used as the source address when transmitting
        IP packets on remote access user links."
    DEFVAL    { "" }
    ::= { juniAaaAssignDomainEntry 14 }

juniAaaAssignDomainIpv6RouterName OBJECT-TYPE
    SYNTAX      JuniName
    MAX-ACCESS  read-create
    STATUS      current
    DESCRIPTION
        "The name of the virtual router to which remote access users within this
        domain are assigned for IPv6 interfaces."
    ::= { juniAaaAssignDomainEntry 15 }

juniAaaAssignDomainIpv6LocalInterface OBJECT-TYPE
    SYNTAX      DisplayString (SIZE(0..64))
    MAX-ACCESS  read-create
    STATUS      current
    DESCRIPTION
        "The local interface, associated with the specified virtual router,
        whose IPv6 address is used as the source address when transmitting IPv6
        packets on remote access user links."
    DEFVAL    { "" }
    ::= { juniAaaAssignDomainEntry 16 }

juniAaaAssignDomainTunnelGroup OBJECT-TYPE
    SYNTAX      JuniAaaTunnelGroupName
    MAX-ACCESS  read-create
    STATUS      current
    DESCRIPTION
        "The tunnel group assigned to this domain map.  Non default
        configuration of this object cannot coexist with matching tunnel
        entries in juniAaaAssignDomainTunnelTable. "
    DEFVAL    { "" }
    ::= { juniAaaAssignDomainEntry 17 }

juniAaaAssignDomainAuthRouterName OBJECT-TYPE
    SYNTAX      JuniName
    MAX-ACCESS  read-create
    STATUS      current
    DESCRIPTION
        "The name of the virtual router where remote access users within this
        domain will be authenticated."
    ::= { juniAaaAssignDomainEntry 18 }

juniAaaAssignDomainIpRouterName OBJECT-TYPE
    SYNTAX      JuniName
    MAX-ACCESS  read-create
    STATUS      current
    DESCRIPTION
        "The name of the virtual router to which remote access users within this
        domain are assigned for IP interfaces."
    ::= { juniAaaAssignDomainEntry 19 }

juniAaaAssignDomainTunnelSubscriberAuthentication OBJECT-TYPE
    SYNTAX      TruthValue
    MAX-ACCESS  read-create
    STATUS      current
    DESCRIPTION
        "When there are tunnel configurations under this domain, enable or
        disable subscribers of this domain authenticate with configured
        authentication server."
    DEFVAL    { false }
    ::= { juniAaaAssignDomainEntry 20 }

juniAaaAssignDomainBackupPoolName OBJECT-TYPE
    SYNTAX      DisplayString (SIZE(0..16))
    MAX-ACCESS  read-create
    STATUS      current
    DESCRIPTION
        "The name of the backup local address pool from which to allocate an IP address
        for the subscriber when the primary address pool is 100% allocated"
    DEFVAL    { "" }
    ::= { juniAaaAssignDomainEntry 21 }

juniAaaAssignDomainTunnelTable OBJECT-TYPE
    SYNTAX      SEQUENCE OF JuniAaaAssignDomainTunnelEntry
    MAX-ACCESS  not-accessible
    STATUS      current
    DESCRIPTION
        "The entries in this table specify the tunnels associated with a
        domain."
    ::= { juniAaaAssignDomain 2 }

juniAaaAssignDomainTunnelEntry OBJECT-TYPE
    SYNTAX      JuniAaaAssignDomainTunnelEntry
    MAX-ACCESS  not-accessible
    STATUS      current
    DESCRIPTION
        "A specification of the tunnels associated with a domain."
    INDEX     { juniAaaAssignDomainTunnelName,
                juniAaaAssignDomainTunnelTag }
    ::= { juniAaaAssignDomainTunnelTable 1 }

JuniAaaAssignDomainTunnelEntry ::= SEQUENCE {
    juniAaaAssignDomainTunnelName                 JuniAaaDomainName,
    juniAaaAssignDomainTunnelTag                  Integer32,
    juniAaaAssignDomainTunnelPreference           Integer32,
    juniAaaAssignDomainTunnelType                 INTEGER,
    juniAaaAssignDomainTunnelMedium               INTEGER,
    juniAaaAssignDomainTunnelAddress              DisplayString,
    juniAaaAssignDomainTunnelPassword             DisplayString,
    juniAaaAssignDomainTunnelId                   DisplayString,
    juniAaaAssignDomainTunnelHostName             DisplayString,
    juniAaaAssignDomainTunnelRowStatus            RowStatus,
    juniAaaAssignDomainTunnelServerName           DisplayString,
    juniAaaAssignDomainTunnelClientAddress        DisplayString,
    juniAaaAssignDomainTunnelMaxSessions          Unsigned32,
    juniAaaAssignDomainTunnelReceiveWindowSize    Integer32,
    juniAaaAssignDomainTunnelFailoverResync       INTEGER,
    juniAaaAssignDomainTunnelSwitchProfile        JuniAaaTunnelSwitchProfileName,
    juniAaaAssignDomainTunnelTxConnectSpeedMethod INTEGER }

juniAaaAssignDomainTunnelName OBJECT-TYPE
    SYNTAX      JuniAaaDomainName
    MAX-ACCESS  read-only
    STATUS      current
    DESCRIPTION
        "The domain name associated with this entry."
    ::= { juniAaaAssignDomainTunnelEntry 1 }

juniAaaAssignDomainTunnelTag OBJECT-TYPE
    SYNTAX      Integer32 (1..31)
    MAX-ACCESS  read-only
    STATUS      current
    DESCRIPTION
        "The tunnel tag value associated with this entry."
    ::= { juniAaaAssignDomainTunnelEntry 2 }

juniAaaAssignDomainTunnelPreference OBJECT-TYPE
    SYNTAX      Integer32 (0..2000)
    MAX-ACCESS  read-create
    STATUS      current
    DESCRIPTION
        "The tunnel's preference value associated with this entry.  The value 0
        is the highest preference."
    DEFVAL    { 1000 }
    ::= { juniAaaAssignDomainTunnelEntry 3 }

juniAaaAssignDomainTunnelType OBJECT-TYPE
    SYNTAX      INTEGER {
                    tunnelL2tp(1),
                    tunnelUnknown(2),
                    tunnelL2f(3) }
    MAX-ACCESS  read-create
    STATUS      current
    DESCRIPTION
        "The tunnel type associated with this entry.  Attempts to set this
        object to tunnelUnknown(2) and tunnelL2f(3) will fail (wrongValue)."
    DEFVAL    { tunnelL2tp }
    ::= { juniAaaAssignDomainTunnelEntry 4 }

juniAaaAssignDomainTunnelMedium OBJECT-TYPE
    SYNTAX      INTEGER {
                    tunnelMediumIPv4(1),
                    tunnelMediumUnknown(2) }
    MAX-ACCESS  read-create
    STATUS      current
    DESCRIPTION
        "The tunnel medium associated with this entry.  The medium dictates the
        format of the tunnel address.  Attempts to set this object to
        tunnelMediumUnknown(2) will fail (wrongValue)."
    DEFVAL    { tunnelMediumIPv4 }
    ::= { juniAaaAssignDomainTunnelEntry 5 }

juniAaaAssignDomainTunnelAddress OBJECT-TYPE
    SYNTAX      DisplayString (SIZE(0..32))
    MAX-ACCESS  read-create
    STATUS      current
    DESCRIPTION
        "The tunnel server address associated with this entry.  The
        juniAaaAssignDomainTunnelMedium object defines the format of the
        address.

            MEDIUM               EXAMPLE FORMAT
            tunnelMedium_IPv4    xyz.xyz.xyz.xyz "
    ::= { juniAaaAssignDomainTunnelEntry 6 }

juniAaaAssignDomainTunnelPassword OBJECT-TYPE
    SYNTAX      DisplayString (SIZE(0..32))
    MAX-ACCESS  read-create
    STATUS      current
    DESCRIPTION
        "The tunnel password associated with this entry.  The object returns a
        null length string on reads due to security concerns."
    DEFVAL    { "" }
    ::= { juniAaaAssignDomainTunnelEntry 7 }

juniAaaAssignDomainTunnelId OBJECT-TYPE
    SYNTAX      DisplayString (SIZE(0..32))
    MAX-ACCESS  read-create
    STATUS      current
    DESCRIPTION
        "The tunnel identifier associated with this entry.  The tunnel
        identifier is used to distinguish between multiple tunnels to the same
        juniAaaAssignDomainTunnelAddress."
    DEFVAL    { "" }
    ::= { juniAaaAssignDomainTunnelEntry 8 }

juniAaaAssignDomainTunnelHostName OBJECT-TYPE
    SYNTAX      DisplayString (SIZE(0..64))
    MAX-ACCESS  read-create
    STATUS      current
    DESCRIPTION
        "The tunnel client hostname associated with this entry.  This object is
        analogous to the RADIUS attribute Tunnel-Client-Auth-ID.  When a tunnel
        is established with a peer, this object can be used to distinguish
        groups of tunnels."
    DEFVAL    { "" }
    ::= { juniAaaAssignDomainTunnelEntry 9 }

juniAaaAssignDomainTunnelRowStatus OBJECT-TYPE
    SYNTAX      RowStatus
    MAX-ACCESS  read-create
    STATUS      current
    DESCRIPTION
        "Controls creation/deletion of entries in this table.  Only the values
        'createAndGo' and 'destroy' may be SET."
    ::= { juniAaaAssignDomainTunnelEntry 10 }

juniAaaAssignDomainTunnelServerName OBJECT-TYPE
    SYNTAX      DisplayString (SIZE(0..64))
    MAX-ACCESS  read-create
    STATUS      current
    DESCRIPTION
        "The tunnel server hostname associated with this entry.  This object is
        analogous to the RADIUS attribute Tunnel-Server-Auth-ID.  When a tunnel
        is established with a peer, this object can be used to distinguish
        groups of tunnels."
    DEFVAL    { "" }
    ::= { juniAaaAssignDomainTunnelEntry 11 }

juniAaaAssignDomainTunnelClientAddress OBJECT-TYPE
    SYNTAX      DisplayString (SIZE(0..32))
    MAX-ACCESS  read-create
    STATUS      current
    DESCRIPTION
        "The tunnel client address associated with this entry.  The
        juniAaaAssignDomainTunnelMedium object defines the format of the
        address.

            MEDIUM               EXAMPLE FORMAT
            tunnelMedium_IPv4    xyz.xyz.xyz.xyz "
    ::= { juniAaaAssignDomainTunnelEntry 12 }

juniAaaAssignDomainTunnelMaxSessions OBJECT-TYPE
    SYNTAX      Unsigned32
    MAX-ACCESS  read-create
    STATUS      current
    DESCRIPTION
        "The tunnel's max-session value associated with this entry.  The value 0
        indicates no maximum session value."
    DEFVAL    { 1000 }
    ::= { juniAaaAssignDomainTunnelEntry 13 }

juniAaaAssignDomainTunnelReceiveWindowSize OBJECT-TYPE
    SYNTAX      Integer32 (0 | 4)
    MAX-ACCESS  read-create
    STATUS      current
    DESCRIPTION
        "For an L2TP tunnel this object represents the receive window
        size.  A value of 0 indicates that this object has no effect
        on the tunnel's receive window size."
    DEFVAL    { 0 }
    ::= { juniAaaAssignDomainTunnelEntry 14 }

juniAaaAssignDomainTunnelFailoverResync OBJECT-TYPE
    SYNTAX      INTEGER {
                disable(0),
                failoverProtocol(1),
                silentFailover(2),
                failoverProtocolFallbackToSilentFailover(3),
                notConfigured(4) }
    MAX-ACCESS  read-create
    STATUS      current
    DESCRIPTION
       "For an L2TP tunnel this object represents the failover resync
       mechanism:
       disable(0) - Disable failover resync
       failoverProtocol(1) - Use  the L2TP Failover Protocol
       silentFailover(2) - Use the JUNOSe Silent Failover Mechanism
       failoverProtocolFallbackToSilentFailover(3) - (Default) Use the
       L2TP Failover Protocol and fall back to Silent Failover."
    DEFVAL    { notConfigured }
    ::= { juniAaaAssignDomainTunnelEntry 15 }

juniAaaAssignDomainTunnelSwitchProfile OBJECT-TYPE
    SYNTAX      JuniAaaTunnelSwitchProfileName
    MAX-ACCESS  read-create
    STATUS      current
    DESCRIPTION
        "The name of the L2TP tunnel switch profile to apply in tunnel
         switching scenarios."
    ::= { juniAaaAssignDomainTunnelEntry 16 }

juniAaaAssignDomainTunnelTxConnectSpeedMethod OBJECT-TYPE
    SYNTAX      INTEGER {
                notSet(0),
                staticLayer2(1),
                dynamicLayer2(2),
                qos(3),
                actual(4) }
    MAX-ACCESS  read-create
    STATUS      current
    DESCRIPTION
       "For an L2TP tunnel this object represents the tx connect speed method
       mechanism at the LAC:
       notSet(0)        - this parameter has not been configured
       staticLayer2(1)  - use static layer 2 settings
       dynamicLayer2(2) - use layer 2 settings including dynamic speeds
       qos(3)           - use qos speed
       actual(4)        - minimum of dynamicLayer2 and qos"
    DEFVAL    { notSet }
    ::= { juniAaaAssignDomainTunnelEntry 17 }

juniAaaAssignDomainPadnTable OBJECT-TYPE
    SYNTAX      SEQUENCE OF JuniAaaAssignDomainPadnEntry
    MAX-ACCESS  not-accessible
    STATUS      current
    DESCRIPTION
        "The entries in this table specify the PPPoE active discovery network
        (PADN) parameters associated with a domain."
    ::= { juniAaaAssignDomain 3 }

juniAaaAssignDomainPadnEntry OBJECT-TYPE
    SYNTAX      JuniAaaAssignDomainPadnEntry
    MAX-ACCESS  not-accessible
    STATUS      current
    DESCRIPTION
        "A specification of the PPPoE active discovery network parameters
        associated with a domain."
    INDEX     { juniAaaAssignDomainName,
                juniAaaAssignDomainPadnIpAddress,
                juniAaaAssignDomainPadnIpMask }
    ::= { juniAaaAssignDomainPadnTable 1 }

JuniAaaAssignDomainPadnEntry ::= SEQUENCE {
    juniAaaAssignDomainPadnIpAddress     IpAddress,
    juniAaaAssignDomainPadnIpMask        IpAddress,
    juniAaaAssignDomainPadnRowStatus     RowStatus,
    juniAaaAssignDomainPadnDistance      Integer32 }

juniAaaAssignDomainPadnIpAddress OBJECT-TYPE
    SYNTAX      IpAddress
    MAX-ACCESS  not-accessible
    STATUS      current
    DESCRIPTION
        "The IP address of this entry."
    ::= { juniAaaAssignDomainPadnEntry 1 }

juniAaaAssignDomainPadnIpMask OBJECT-TYPE
    SYNTAX      IpAddress
    MAX-ACCESS  not-accessible
    STATUS      current
    DESCRIPTION
        "The IP mask of this entry."
    ::= { juniAaaAssignDomainPadnEntry 2 }

juniAaaAssignDomainPadnRowStatus OBJECT-TYPE
    SYNTAX      RowStatus
    MAX-ACCESS  read-create
    STATUS      current
    DESCRIPTION
        "Controls creation/deletion of entries in this table.  Only the values
        'createAndGo' and 'destroy' may be SET."
    ::= { juniAaaAssignDomainPadnEntry 3 }

juniAaaAssignDomainPadnDistance OBJECT-TYPE
    SYNTAX      Integer32 (0..255)
    MAX-ACCESS  read-create
    STATUS      current
    DESCRIPTION
        "The administrative distance metric of this entry."
    ::= { juniAaaAssignDomainPadnEntry 4 }

-- +++++++++++++++++++++++++++++++++++++++++++++++++++++++++++++++++++++++++++++
-- Managed objects for Tunnel Groups
-- +++++++++++++++++++++++++++++++++++++++++++++++++++++++++++++++++++++++++++++
juniAaaTunnelGroups         OBJECT IDENTIFIER ::= { juniAaaTunnel 2 }

juniAaaTunnelGroupTable OBJECT-TYPE
    SYNTAX      SEQUENCE OF JuniAaaTunnelGroupEntry
    MAX-ACCESS  not-accessible
    STATUS      current
    DESCRIPTION
        "The entries in this table specify tunnel attributes sufficient tunnel establishment."
    ::= { juniAaaTunnelGroups 1 }

juniAaaTunnelGroupEntry OBJECT-TYPE
    SYNTAX      JuniAaaTunnelGroupEntry
    MAX-ACCESS  not-accessible
    STATUS      current
    DESCRIPTION
        "An entry in the tunnel group table."
    INDEX     { IMPLIED juniAaaTunnelGroupName }
    ::= { juniAaaTunnelGroupTable 1 }

JuniAaaTunnelGroupEntry ::= SEQUENCE {
    juniAaaTunnelGroupName               JuniAaaTunnelGroupName,
    juniAaaTunnelGroupRowStatus          RowStatus }

juniAaaTunnelGroupName OBJECT-TYPE
    SYNTAX      JuniAaaTunnelGroupName
    MAX-ACCESS  read-only
    STATUS      current
    DESCRIPTION
        "The tunnel group name uniquely identifying this entry."
    ::= { juniAaaTunnelGroupEntry 1 }

juniAaaTunnelGroupRowStatus OBJECT-TYPE
    SYNTAX      RowStatus
    MAX-ACCESS  read-create
    STATUS      current
    DESCRIPTION
        "Controls creation/deletion of entries in this table.  Only the values
        'createAndGo' and 'destroy' may be SET."
    ::= { juniAaaTunnelGroupEntry 2 }


juniAaaTunnelGroupTunnelTable OBJECT-TYPE
    SYNTAX      SEQUENCE OF JuniAaaTunnelGroupTunnelEntry
    MAX-ACCESS  not-accessible
    STATUS      current
    DESCRIPTION
        "The entries in this table specify the tunnels associated with a
        tunnel group."
    ::= { juniAaaTunnelGroups 2 }

juniAaaTunnelGroupTunnelEntry OBJECT-TYPE
    SYNTAX      JuniAaaTunnelGroupTunnelEntry
    MAX-ACCESS  not-accessible
    STATUS      current
    DESCRIPTION
        "A specification of the tunnels associated with a tunnel group."
    INDEX     { juniAaaTunnelGroupTunnelName,
                juniAaaTunnelGroupTunnelTag }
    ::= { juniAaaTunnelGroupTunnelTable 1 }

JuniAaaTunnelGroupTunnelEntry ::= SEQUENCE {
    juniAaaTunnelGroupTunnelName                 JuniAaaTunnelGroupName,
    juniAaaTunnelGroupTunnelTag                  Integer32,
    juniAaaTunnelGroupTunnelPreference           Integer32,
    juniAaaTunnelGroupTunnelType                 INTEGER,
    juniAaaTunnelGroupTunnelMedium               INTEGER,
    juniAaaTunnelGroupTunnelAddress              DisplayString,
    juniAaaTunnelGroupTunnelPassword             DisplayString,
    juniAaaTunnelGroupTunnelId                   DisplayString,
    juniAaaTunnelGroupTunnelHostName             DisplayString,
    juniAaaTunnelGroupTunnelRowStatus            RowStatus,
    juniAaaTunnelGroupTunnelServerName           DisplayString,
    juniAaaTunnelGroupTunnelClientAddress        DisplayString,
    juniAaaTunnelGroupTunnelMaxSessions          Integer32,
    juniAaaTunnelGroupTunnelReceiveWindowSize    Integer32,
    juniAaaTunnelGroupTunnelRouterName           JuniName,
    juniAaaTunnelGroupTunnelFailoverResync       INTEGER,
    juniAaaTunnelGroupTunnelSwitchProfile        JuniAaaTunnelSwitchProfileName,
    juniAaaTunnelGroupTunnelTxConnectSpeedMethod INTEGER }

juniAaaTunnelGroupTunnelName OBJECT-TYPE
    SYNTAX      JuniAaaTunnelGroupName
    MAX-ACCESS  read-only
    STATUS      current
    DESCRIPTION
        "The tunnel group name associated with this entry."
    ::= { juniAaaTunnelGroupTunnelEntry 1 }

juniAaaTunnelGroupTunnelTag OBJECT-TYPE
    SYNTAX      Integer32 (1..31)
    MAX-ACCESS  read-only
    STATUS      current
    DESCRIPTION
        "The tunnel tag value associated with this entry."
    ::= { juniAaaTunnelGroupTunnelEntry 2 }

juniAaaTunnelGroupTunnelPreference OBJECT-TYPE
    SYNTAX      Integer32 (0..2000)
    MAX-ACCESS  read-create
    STATUS      current
    DESCRIPTION
        "The tunnel's preference value associated with this entry.  The value 0
        is the highest preference."
    DEFVAL    { 1000 }
    ::= { juniAaaTunnelGroupTunnelEntry 3 }

juniAaaTunnelGroupTunnelType OBJECT-TYPE
    SYNTAX      INTEGER {
                    tunnelL2tp(1) }
    MAX-ACCESS  read-create
    STATUS      current
    DESCRIPTION
        "The tunnel type associated with this entry."
    DEFVAL    { tunnelL2tp }
    ::= { juniAaaTunnelGroupTunnelEntry 4 }

juniAaaTunnelGroupTunnelMedium OBJECT-TYPE
    SYNTAX      INTEGER {
                    tunnelMediumIPv4(1),
                    tunnelMediumUnknown(2) }
    MAX-ACCESS  read-create
    STATUS      current
    DESCRIPTION
        "The tunnel medium associated with this entry.  The medium dictates the
        format of the tunnel address.  Attempts to set this object to
        tunnelMediumUnknown(2) will fail (wrongValue)."
    DEFVAL    { tunnelMediumIPv4 }
    ::= { juniAaaTunnelGroupTunnelEntry 5 }

juniAaaTunnelGroupTunnelAddress OBJECT-TYPE
    SYNTAX      DisplayString (SIZE(0..32))
    MAX-ACCESS  read-create
    STATUS      current
    DESCRIPTION
        "The tunnel server address associated with this entry.  The
        juniAaaTunnelGroupTunnelMedium object defines the format of the
        address.

            MEDIUM               EXAMPLE FORMAT
            tunnelMedium_IPv4    xyz.xyz.xyz.xyz "
    ::= { juniAaaTunnelGroupTunnelEntry 6 }

juniAaaTunnelGroupTunnelPassword OBJECT-TYPE
    SYNTAX      DisplayString (SIZE(0..32))
    MAX-ACCESS  read-create
    STATUS      current
    DESCRIPTION
        "The tunnel password associated with this entry.  The object returns a
        null length string on reads due to security concerns."
    DEFVAL    { "" }
    ::= { juniAaaTunnelGroupTunnelEntry 7 }

juniAaaTunnelGroupTunnelId OBJECT-TYPE
    SYNTAX      DisplayString (SIZE(0..32))
    MAX-ACCESS  read-create
    STATUS      current
    DESCRIPTION
        "The tunnel identifier associated with this entry.  The tunnel
        identifier is used to distinguish between multiple tunnels to the same
        juniAaaTunnelGroupTunnelAddress."
    DEFVAL    { "" }
    ::= { juniAaaTunnelGroupTunnelEntry 8 }

juniAaaTunnelGroupTunnelHostName OBJECT-TYPE
    SYNTAX      DisplayString (SIZE(0..64))
    MAX-ACCESS  read-create
    STATUS      current
    DESCRIPTION
        "The tunnel client hostname associated with this entry.  This object is
        analogous to the RADIUS attribute Tunnel-Client-Auth-ID.  When a tunnel
        is established with a peer, this object can be used to distinguish
        groups of tunnels."
    DEFVAL    { "" }
    ::= { juniAaaTunnelGroupTunnelEntry 9 }

juniAaaTunnelGroupTunnelRowStatus OBJECT-TYPE
    SYNTAX      RowStatus
    MAX-ACCESS  read-create
    STATUS      current
    DESCRIPTION
        "Controls creation/deletion of entries in this table.  Only the values
        'createAndGo' and 'destroy' may be SET."
    ::= { juniAaaTunnelGroupTunnelEntry 10 }

juniAaaTunnelGroupTunnelServerName OBJECT-TYPE
    SYNTAX      DisplayString (SIZE(0..64))
    MAX-ACCESS  read-create
    STATUS      current
    DESCRIPTION
        "The tunnel server hostname associated with this entry.  This object is
        analogous to the RADIUS attribute Tunnel-Server-Auth-ID.  When a tunnel
        is established with a peer, this object can be used to distinguish
        groups of tunnels."
    DEFVAL    { "" }
    ::= { juniAaaTunnelGroupTunnelEntry 11 }

juniAaaTunnelGroupTunnelClientAddress OBJECT-TYPE
    SYNTAX      DisplayString (SIZE(0..32))
    MAX-ACCESS  read-create
    STATUS      current
    DESCRIPTION
        "The tunnel client address associated with this entry.  The
        juniAaaTunnelGroupTunnelMedium object defines the format of the
        address.

            MEDIUM               EXAMPLE FORMAT
            tunnelMedium_IPv4    xyz.xyz.xyz.xyz "
    ::= { juniAaaTunnelGroupTunnelEntry 12 }

juniAaaTunnelGroupTunnelMaxSessions OBJECT-TYPE
    SYNTAX      Integer32
    MAX-ACCESS  read-create
    STATUS      current
    DESCRIPTION
        "The tunnel's max-session value associated with this entry.  The value 0
        indicates no maximum session value."
    DEFVAL    { 1000 }
    ::= { juniAaaTunnelGroupTunnelEntry 13 }

juniAaaTunnelGroupTunnelReceiveWindowSize OBJECT-TYPE
    SYNTAX      Integer32 (0 | 4)
    MAX-ACCESS  read-create
    STATUS      current
    DESCRIPTION
        "For an L2TP tunnel this object represents the receive window
        size.  A value of 0 indicates that this object has no effect
        on the tunnel's receive window size."
    DEFVAL    { 0 }
    ::= { juniAaaTunnelGroupTunnelEntry 14 }

juniAaaTunnelGroupTunnelRouterName OBJECT-TYPE
    SYNTAX      JuniName
    MAX-ACCESS  read-create
    STATUS      current
    DESCRIPTION
        "The name of the virtual router to which remote access users within this
        tunnel are assigned."
    ::= { juniAaaTunnelGroupTunnelEntry 15 }

juniAaaTunnelGroupTunnelFailoverResync OBJECT-TYPE
    SYNTAX      INTEGER {
                disable(0),
                failoverProtocol(1),
                silentFailover(2),
                failoverProtocolFallbackToSilentFailover(3),
                notConfigured(4) }
    MAX-ACCESS  read-create
    STATUS      current
    DESCRIPTION
       "For an L2TP tunnel this object represents the failover resync
       mechanism:
       disable(0) - Disable failover resync
       failoverProtocol(1) - Use  the L2TP Failover Protocol
       silentFailover(2) - Use the JUNOSe Silent Failover Mechanism
       failoverProtocolFallbackToSilentFailover(3) - (Default) Use the
       L2TP Failover Protocol and fall back to Silent Failover."
    DEFVAL    { notConfigured }
    ::= { juniAaaTunnelGroupTunnelEntry 16 }

juniAaaTunnelGroupTunnelSwitchProfile OBJECT-TYPE
    SYNTAX      JuniAaaTunnelSwitchProfileName
    MAX-ACCESS  read-create
    STATUS      current
    DESCRIPTION
        "The name of the L2TP tunnel switch profile to apply in tunnel
         switching scenarios."
    ::= { juniAaaTunnelGroupTunnelEntry 17 }

juniAaaTunnelGroupTunnelTxConnectSpeedMethod OBJECT-TYPE
    SYNTAX      INTEGER {
                notSet(0),
                staticLayer2(1),
                dynamicLayer2(2),
                qos(3),
                actual(4) }
    MAX-ACCESS  read-create
    STATUS      current
    DESCRIPTION
       "For an L2TP tunnel this object represents the tx connect speed method
       mechanism at the LAC:
       notSet(0)        - this parameter has not been configured
       staticLayer2(1)  - use static layer 2 settings
       dynamicLayer2(2) - use layer 2 settings including dynamic speeds
       qos(3)           - use qos speed
       actual(4)        - minimum of dynamicLayer2 and qos"
    DEFVAL    { notSet }
    ::= { juniAaaTunnelGroupTunnelEntry 18 }

-- +++++++++++++++++++++++++++++++++++++++++++++++++++++++++++++++++++++++++++++
-- Managed objects for Authentication functions
-- +++++++++++++++++++++++++++++++++++++++++++++++++++++++++++++++++++++++++++++
juniAaaAuthGeneral            OBJECT IDENTIFIER ::= { juniAaaAuthentication 1 }
juniAaaLocalAuth              OBJECT IDENTIFIER ::= { juniAaaAuthentication 2 }

juniAaaLocalAuthUser          OBJECT IDENTIFIER ::= { juniAaaLocalAuth 1 }
juniAaaLocalAuthUserDb        OBJECT IDENTIFIER ::= { juniAaaLocalAuth 2 }
juniAaaLocalAuthUserDbAssoc   OBJECT IDENTIFIER ::= { juniAaaLocalAuth 3 }

juniAaaAuthMethods OBJECT-TYPE
    SYNTAX       OCTET STRING (SIZE(0..5))
    MAX-ACCESS   read-write
    STATUS       obsolete
    DESCRIPTION
        "The set of authentication protocols configured on this system.  Each
        octet in this object contains one of the values defined in the
        JuniAaaAuthenticationMethods TEXTUAL-CONVENTION.

        The system will sequence through each octet of this object starting at
        octet 1 and attempt to use the corresponding authentication protocol
        defined by JuniAaaAuthenticationMethods.  Note that if the octet is set
        to:
             protocolNone(4)

        Then authentication does not take place.

        If an authentication protocol is configured and attempts to reach the
        authentication server fail, the system will move to the next octet in
        this object and retry the authentication in the form dictated by the
        corresponding authentication protocoltype.  The process of sequencing
        thru each octet will stop if the authentication server is successfully
        contacted, or there are no more configured octets in this object."
     ::= { juniAaaAuthGeneral 1 }

juniAaaAuthMethodsTable OBJECT-TYPE
    SYNTAX       SEQUENCE OF JuniAaaAuthMethodsEntry
    MAX-ACCESS   not-accessible
    STATUS       current
    DESCRIPTION
        "The entries in this table specify the assignment of authentication methods
        for a particular subscriber type."
     ::= { juniAaaAuthGeneral 2 }

juniAaaAuthMethodsEntry OBJECT-TYPE
    SYNTAX      JuniAaaAuthMethodsEntry
    MAX-ACCESS  not-accessible
    STATUS      current
    DESCRIPTION
        "A specification of the authentication methods for a particular
        subscriber type."
    INDEX     { juniAaaAuthMethodsSubscriberType }
    ::= { juniAaaAuthMethodsTable 1 }

JuniAaaAuthMethodsEntry ::= SEQUENCE {
    juniAaaAuthMethodsSubscriberType JuniAaaAuthenticationSubscriberTypes,
    juniAaaAuthMethodsAuthentication OCTET STRING }

juniAaaAuthMethodsSubscriberType OBJECT-TYPE
    SYNTAX      JuniAaaAuthenticationSubscriberTypes
    MAX-ACCESS  read-only
    STATUS      current
    DESCRIPTION
        "The subscriber type."
    ::= { juniAaaAuthMethodsEntry 1 }

juniAaaAuthMethodsAuthentication OBJECT-TYPE
    SYNTAX       OCTET STRING (SIZE(0..5))
    MAX-ACCESS   read-write
    STATUS       current
    DESCRIPTION
        "The set of authentication protocols configured on this system.  Each
        octet in this object contains one of the values defined in the
        JuniAaaAuthenticationMethods TEXTUAL-CONVENTION.

        The system will sequence through each octet of this object starting at
        octet 1 and attempt to use the corresponding authentication protocol
        defined by JuniAaaAuthenticationMethods.  Note that if the octet is set
        to:
             protocolNone(4)

        Then authentication does not take place.

        If an authentication protocol is configured and attempts to reach the
        authentication server fail, the system will move to the next octet in
        this object and retry the authentication in the form dictated by the
        corresponding authentication protocoltype.  The process of sequencing
        thru each octet will stop if the authentication server is successfully
        contacted, or there are no more configured octets in this object."
     ::= { juniAaaAuthMethodsEntry 2 }

juniAaaLocalAuthUserTable     OBJECT-TYPE
    SYNTAX      SEQUENCE OF JuniAaaLocalAuthUserEntry
    MAX-ACCESS  not-accessible
    STATUS      current
    DESCRIPTION
        "This table contains entries for users present in the
        local user databases."
    ::= { juniAaaLocalAuthUser 1 }

juniAaaLocalAuthUserEntry  OBJECT-TYPE
    SYNTAX      JuniAaaLocalAuthUserEntry
    MAX-ACCESS  not-accessible
    STATUS      current
    DESCRIPTION
        "Each entry in this table represents a single user in a local
        user database."
    INDEX     { juniAaaLocalAuthUserDbName, IMPLIED juniAaaLocalAuthUserName }
    ::= { juniAaaLocalAuthUserTable 1 }

JuniAaaLocalAuthUserEntry ::= SEQUENCE {
    juniAaaLocalAuthUserName            DisplayString,
    juniAaaLocalAuthUserRowStatus       RowStatus,
    juniAaaLocalAuthUserPassword        OCTET STRING,
    juniAaaLocalAuthUserEncryption      INTEGER,
    juniAaaLocalAuthUserIpAddress       IpAddress,
    juniAaaLocalAuthUserIpAddressPool   DisplayString,
    juniAaaLocalAuthUserRouterName      JuniName }

juniAaaLocalAuthUserName  OBJECT-TYPE
    SYNTAX      DisplayString (SIZE(1..64))
    MAX-ACCESS  not-accessible
    STATUS      current
    DESCRIPTION
        "The name of the user."
    ::= { juniAaaLocalAuthUserEntry 1 }

juniAaaLocalAuthUserRowStatus  OBJECT-TYPE
    SYNTAX      RowStatus
    MAX-ACCESS  read-create
    STATUS      current
    DESCRIPTION
        "Controls creation/deletion of entries in this table.  Only
        'createAndGo' and 'destroy' enumeration values are supported."
    ::= { juniAaaLocalAuthUserEntry 2 }

juniAaaLocalAuthUserPassword  OBJECT-TYPE
    SYNTAX      OCTET STRING (SIZE(0..32))
    MAX-ACCESS  read-create
    STATUS      current
    DESCRIPTION
        "The password for this user.  If the juniAaaLocalAuthUserEncrypted
        object is not set with this object, the password value is assumed
        to be unencrypted.  When set, any existing password is overwritten.
        Setting a zero length OCTET STRING removes the password.  Reading
        this object always results in a zero length OCTET STRING."
    DEFVAL      { "" }
    ::= { juniAaaLocalAuthUserEntry 3 }

juniAaaLocalAuthUserEncryption  OBJECT-TYPE
    SYNTAX      INTEGER {
                    encryptionNone(0),
                    encryptionSecret(5),
                    encryptionPassword(8) }
    MAX-ACCESS  read-create
    STATUS      current
    DESCRIPTION
        "The encryption type of the password value being set with the
        juniAaaLocalAuthUserPassword object.  Reading this object always
        results in a value of encryptionNone.

        encyptionNone     - The password is unencrypted (i.e. in plain text.)
        encyptionSecret   - The password has been generated using a
                            one-way MD5 encryption mechanism, algorithm 5.
        encyptionPassword - The password has been generated using a
                            two-way encryption mechanism, algorithm 8."
    DEFVAL      { encryptionNone }
    ::= { juniAaaLocalAuthUserEntry 4 }

juniAaaLocalAuthUserIpAddress  OBJECT-TYPE
    SYNTAX      IpAddress
    MAX-ACCESS  read-create
    STATUS      current
    DESCRIPTION
        "The IP address this user is to be assigned, once authenticated.
        This object corresponds to the Framed-IP-Address attribute in RADIUS
        authentication servers."
    DEFVAL      { '00000000'H }  -- 0.0.0.0
    ::= { juniAaaLocalAuthUserEntry 5 }

juniAaaLocalAuthUserIpAddressPool  OBJECT-TYPE
    SYNTAX      DisplayString (SIZE(0..16))
    MAX-ACCESS  read-create
    STATUS      current
    DESCRIPTION
        "The name of the local address pool this user is to be allocated an
        IP address from, once authenticated.  This object corresponds to the
        Framed-Pool attribute in RADIUS authentication servers."
    DEFVAL      { "" }
    ::= { juniAaaLocalAuthUserEntry 6 }

juniAaaLocalAuthUserRouterName  OBJECT-TYPE
    SYNTAX      JuniName
    MAX-ACCESS  read-create
    STATUS      current
    DESCRIPTION
        "The name of the router this user is to be assigned to, once
        authenticated.  This object corresponds to the Unispher-Virtual-Router
        attribute in RADIUS authentication servers."
    DEFVAL      { "" }
    ::= { juniAaaLocalAuthUserEntry 7 }

juniAaaLocalAuthUserDbTable     OBJECT-TYPE
    SYNTAX      SEQUENCE OF JuniAaaLocalAuthUserDbEntry
    MAX-ACCESS  not-accessible
    STATUS      current
    DESCRIPTION
        "This table contains entries for local user databases."
    ::= { juniAaaLocalAuthUserDb 1 }

juniAaaLocalAuthUserDbEntry  OBJECT-TYPE
    SYNTAX      JuniAaaLocalAuthUserDbEntry
    MAX-ACCESS  not-accessible
    STATUS      current
    DESCRIPTION
        "Each entry in this table represents a single local user database."
    INDEX     { IMPLIED juniAaaLocalAuthUserDbName }
    ::= { juniAaaLocalAuthUserDbTable 1 }

JuniAaaLocalAuthUserDbEntry ::= SEQUENCE {
    juniAaaLocalAuthUserDbName          DisplayString,
    juniAaaLocalAuthUserDbRowStatus     RowStatus }

juniAaaLocalAuthUserDbName  OBJECT-TYPE
    SYNTAX      DisplayString (SIZE(1..32))
    MAX-ACCESS  not-accessible
    STATUS      current
    DESCRIPTION
        "The name of this local user database."
    ::= { juniAaaLocalAuthUserDbEntry 1 }

juniAaaLocalAuthUserDbRowStatus  OBJECT-TYPE
    SYNTAX      RowStatus
    MAX-ACCESS  read-create
    STATUS      current
    DESCRIPTION
        "Controls creation/deletion of entries in this table.  Only
        'createAndGo' and 'destroy' enumeration values are supported."
    ::= { juniAaaLocalAuthUserDbEntry 2 }

juniAaaLocalAuthUserDbAssocTable     OBJECT-TYPE
    SYNTAX      SEQUENCE OF JuniAaaLocalAuthUserDbAssocEntry
    MAX-ACCESS  not-accessible
    STATUS      current
    DESCRIPTION
        "This table contains entries that identify the local user
        database that is associated with each virtual router."
    ::= { juniAaaLocalAuthUserDbAssoc 1 }

juniAaaLocalAuthUserDbAssocEntry  OBJECT-TYPE
    SYNTAX      JuniAaaLocalAuthUserDbAssocEntry
    MAX-ACCESS  not-accessible
    STATUS      current
    DESCRIPTION
        "Each entry in this table represents a single association
        between a virtual router and local user database.  The same
        database can be referenced by multiple virtual routers; however,
        a virtual router can reference only one database.  No entries
        are displayed for virtual routers that reference the default
        local user database."
    INDEX     { juniRouterIndex }
    ::= { juniAaaLocalAuthUserDbAssocTable 1 }

JuniAaaLocalAuthUserDbAssocEntry ::= SEQUENCE {
    juniAaaLocalAuthUserDbAssocRowStatus     RowStatus,
    juniAaaLocalAuthUserDbAssocDbName        DisplayString }

juniAaaLocalAuthUserDbAssocRowStatus  OBJECT-TYPE
    SYNTAX      RowStatus
    MAX-ACCESS  read-create
    STATUS      current
    DESCRIPTION
        "Controls creation/deletion of entries in this table.  Only
        'createAndGo' and 'destroy' enumeration values are supported.

        When a virtual router is deleted, its corresponding entries
        in this table will be deleted as well."
    ::= { juniAaaLocalAuthUserDbAssocEntry 1 }

juniAaaLocalAuthUserDbAssocDbName  OBJECT-TYPE
    SYNTAX      DisplayString (SIZE(1..32))
    MAX-ACCESS  read-create
    STATUS      current
    DESCRIPTION
        "The name of local user database associated with this virtual
        router.  Setting the name to the default local user database,
        'default', will delete this entry, as this is the default
        association for all virtual routers."
    ::= { juniAaaLocalAuthUserDbAssocEntry 2 }

-- +++++++++++++++++++++++++++++++++++++++++++++++++++++++++++++++++++++++++++++
-- Managed objects for Accounting functions
-- +++++++++++++++++++++++++++++++++++++++++++++++++++++++++++++++++++++++++++++
juniAaaAcctGeneral            OBJECT IDENTIFIER ::= { juniAaaAccounting 1 }

juniAaaAcctInterval OBJECT-TYPE
    SYNTAX      Integer32 (0|600..86400)
    UNITS       "seconds"
    MAX-ACCESS  read-write
    STATUS      current
    DESCRIPTION
        "The interval that must elapse between generation of accounting reports,
        ranging from 10 minutes to 24 hours, or disabled if set to zero.  The
        set of this object affects both the juniAaaServiceAcctInterval and
        juniAaaUserAcctInterval values; the get of this object returns only the
        juniAaaUserAcctInterval value."
    DEFVAL    { 0 }
    ::= { juniAaaAcctGeneral 1 }

juniAaaAcctDupServerRouterName OBJECT-TYPE
    SYNTAX      JuniName
    MAX-ACCESS  read-write
    STATUS      current
    DESCRIPTION
        "The name of another router on this system to which accounting reports
        should be sent, in addition to or instead of sending accounting reports
        to the accounting service (if any) configured on the current router
        (i.e., the router context within which this object instance exists).

        A zero-length name disables this mechanism."
    DEFVAL    { "" }
    ::= { juniAaaAcctGeneral 2 }

juniAaaAcctMethods OBJECT-TYPE
    SYNTAX      OCTET STRING (SIZE(0..5))
    MAX-ACCESS  read-write
    STATUS      obsolete
    DESCRIPTION
        "The set of accounting protocols configured on this system.  Each octet
        in this object contains one of the values defined in the
        JuniAaaAccountingMethods TEXTUAL CONVENTION.

        The system will sequence through each octet of this object starting at
        octet 1 and attempt to use the corresponding accounting protocol defined
        by JuniAaaAccountingMethods.  Note that if the octet is set to:
             protocolNone(4)

        Then accounting is disabled.

        If an accounting protocol is configured and reports are not successfully
        generated, the system will move to the next octet in this object and
        repeat the attempt to generate an accounting report in the form dictated
        by the corresponding accounting protocol type.  The process of
        sequencing thru each octet will stop if accounting reports are either
        successfully generated, or there are no more configured octets in this
        object."
     ::= { juniAaaAcctGeneral 3 }

juniAaaAcctSendStopOnAaaDeny OBJECT-TYPE
    SYNTAX      TruthValue
    MAX-ACCESS  read-write
    STATUS      current
    DESCRIPTION
        "Enables/disables the accounting stop message sent to the accounting
        server when authentication server grants access, but AAA denies access."
    DEFVAL    { true }
    ::= { juniAaaAcctGeneral 4 }

juniAaaAcctSendStopOnAaaReject OBJECT-TYPE
    SYNTAX      TruthValue
    MAX-ACCESS  read-write
    STATUS      current
    DESCRIPTION
        "Enables/disables the accounting stop message sent to the accounting
        server when authentication server denies access."
    DEFVAL    { false }
    ::= { juniAaaAcctGeneral 5 }

juniAaaAcctSendImmediateAcctUpdate OBJECT-TYPE
    SYNTAX      TruthValue
    MAX-ACCESS  read-write
    STATUS      current
    DESCRIPTION
        "Enables/disables the sending of an accounting update with the client's
         IP address upon receipt of accounting start response."
    DEFVAL    { false }
    ::= { juniAaaAcctGeneral 6 }

juniAaaAcctMethodsTable OBJECT-TYPE
    SYNTAX      SEQUENCE OF JuniAaaAcctMethodsEntry
    MAX-ACCESS  not-accessible
    STATUS      current
    DESCRIPTION
        "The entries in this table specify the assignment of accounting methods
        for a particular subscriber type."
    ::= { juniAaaAcctGeneral 7 }

juniAaaAcctMethodsEntry OBJECT-TYPE
    SYNTAX      JuniAaaAcctMethodsEntry
    MAX-ACCESS  not-accessible
    STATUS      current
    DESCRIPTION
        "A specification of the accounting methods for a particular
        subscriber type."
    INDEX     { juniAaaAcctMethodsSubscriberType }
    ::= { juniAaaAcctMethodsTable 1 }

JuniAaaAcctMethodsEntry ::= SEQUENCE {
    juniAaaAcctMethodsSubscriberType JuniAaaAccountingSubscriberTypes,
    juniAaaAcctMethodsAccounting     OCTET STRING }

juniAaaAcctMethodsSubscriberType OBJECT-TYPE
    SYNTAX      JuniAaaAccountingSubscriberTypes
    MAX-ACCESS  read-only
    STATUS      current
    DESCRIPTION
        "The subscriber type."
    ::= { juniAaaAcctMethodsEntry 1 }

juniAaaAcctMethodsAccounting OBJECT-TYPE
    SYNTAX      OCTET STRING (SIZE(0..5))
    MAX-ACCESS  read-write
    STATUS      current
    DESCRIPTION
        "The set of accounting protocols configured on this system.  Each octet
        in this object contains one of the values defined in the
        JuniAaaAccountingMethods TEXTUAL CONVENTION.

        The system will sequence through each octet of this object starting at
        octet 1 and attempt to use the corresponding accounting protocol defined
        by JuniAaaAccountingMethods.  Note that if the octet is set to:
             protocolNone(4)

        Then accounting is disabled.

        If an accounting protocol is configured and reports are not successfully
        generated, the system will move to the next octet in this object and
        repeat the attempt to generate an accounting report in the form dictated
        by the corresponding accounting protocol type.  The process of
        sequencing thru each octet will stop if accounting reports are either
        successfully generated, or there are no more configured octets in this
        object."
    ::= { juniAaaAcctMethodsEntry 2 }

juniAaaAcctBcastServerGroupName OBJECT-TYPE
    SYNTAX      JuniVrfGroupName
    MAX-ACCESS  read-write
    STATUS      current
    DESCRIPTION
        "The name of a group of other routers on this system to which
        accounting reports should be sent, for every subsriber who
        has this router assigned as an operational router.

        A zero-length name disables this mechanism."
    DEFVAL    { "" }
    ::= { juniAaaAcctGeneral 8 }

juniAaaUserAcctInterval OBJECT-TYPE
    SYNTAX      Integer32 (0|600..86400)
    UNITS       "seconds"
    MAX-ACCESS  read-write
    STATUS      current
    DESCRIPTION
        "The interval that must elapse between generation of user accounting
        reports, ranging from 10 minutes to 24 hours, or disabled if set to zero."
    DEFVAL    { 0 }
    ::= { juniAaaAcctGeneral 9 }

juniAaaServiceAcctInterval OBJECT-TYPE
    SYNTAX      Integer32 (0|600..86400)
    UNITS       "seconds"
    MAX-ACCESS  read-write
    STATUS      current
    DESCRIPTION
        "The interval that must elapse between generation of service accounting
        reports, ranging from 10 minutes to 24 hours, or disabled if set to zero."
    DEFVAL    { 0 }
    ::= { juniAaaAcctGeneral 10 }

-- Global broadcast server group configuration
juniAaaAcctBcastConfig     OBJECT IDENTIFIER ::= { juniAaaAccounting 2 }

juniAaaAcctBcastServerGroupTable OBJECT-TYPE
    SYNTAX      SEQUENCE OF JuniAaaAcctBcastServerGroupEntry
    MAX-ACCESS  not-accessible
    STATUS      current
    DESCRIPTION
        "The entries in this table specify broadcast accounting routers
        of the named group.

        In addition to row status operations if juniAaaAcctBrasServerGroupRouter1,
        juniAaaAcctBrasServerGroupRouter2, juniAaaAcctBrasServerGroupRouter3 and
        juniAaaAcctBrasServerGroupRouter4 are all set zero length strings,
        the entry will be deleted.

        At least one non zero length string router is required to
        successfully create and entry. All non zero length string
        routers have to be unique within the group."
    ::= { juniAaaAcctBcastConfig 1 }

juniAaaAcctBcastServerGroupEntry OBJECT-TYPE
    SYNTAX      JuniAaaAcctBcastServerGroupEntry
    MAX-ACCESS  not-accessible
    STATUS      current
    DESCRIPTION
        "A specification of the accounting servers for a particular
        group."
    INDEX     { juniAaaAcctBcastServerGroup }
    ::= { juniAaaAcctBcastServerGroupTable 1 }

JuniAaaAcctBcastServerGroupEntry ::= SEQUENCE {
    juniAaaAcctBcastServerGroup        JuniVrfGroupName,
    juniAaaAcctBcastServerGroupRouter1 JuniName,
    juniAaaAcctBcastServerGroupRouter2 JuniName,
    juniAaaAcctBcastServerGroupRouter3 JuniName,
    juniAaaAcctBcastServerGroupRouter4 JuniName,
    juniAaaAcctBcastServerGroupRowStatus RowStatus}

juniAaaAcctBcastServerGroup OBJECT-TYPE
    SYNTAX      JuniVrfGroupName
    MAX-ACCESS  not-accessible
    STATUS      current
    DESCRIPTION
        "The group name."
    ::= { juniAaaAcctBcastServerGroupEntry 1 }

juniAaaAcctBcastServerGroupRouter1 OBJECT-TYPE
    SYNTAX      JuniName
    MAX-ACCESS  read-write
    STATUS      current
    DESCRIPTION
        "The name of the first router in the group."
    DEFVAL    { "" }
    ::= { juniAaaAcctBcastServerGroupEntry 2 }

juniAaaAcctBcastServerGroupRouter2 OBJECT-TYPE
    SYNTAX      JuniName
    MAX-ACCESS  read-write
    STATUS      current
    DESCRIPTION
        "The name of the second router in the group."
    DEFVAL    { "" }
    ::= { juniAaaAcctBcastServerGroupEntry 3 }

juniAaaAcctBcastServerGroupRouter3 OBJECT-TYPE
    SYNTAX      JuniName
    MAX-ACCESS  read-write
    STATUS      current
    DESCRIPTION
        "The name of the third router in the group."
    DEFVAL    { "" }
    ::= { juniAaaAcctBcastServerGroupEntry 4 }

juniAaaAcctBcastServerGroupRouter4 OBJECT-TYPE
    SYNTAX      JuniName
    MAX-ACCESS  read-write
    STATUS      current
    DESCRIPTION
        "The name of the third router in the group."
    DEFVAL    { "" }
    ::= { juniAaaAcctBcastServerGroupEntry 5 }

juniAaaAcctBcastServerGroupRowStatus OBJECT-TYPE
    SYNTAX      RowStatus
    MAX-ACCESS  read-write
    STATUS      current
    DESCRIPTION
        "Controls creation/deletion of entries in this table.  Only the values
        'createAndGo' and 'destroy' may be SET.
        In addition to row status operations if
        juniAaaAcctBrasServerGroupRouter1, juniAaaAcctBrasServerGroupRouter2,
        juniAaaAcctBrasServerGroupRouter3 and juniAaaAcctBrasServerGroupRouter4
        are all set zero length strings, the entry will be deleted.

        At least one non zero length string router is required to
        successfully create and entry."
    ::= { juniAaaAcctBcastServerGroupEntry 6 }


-- +++++++++++++++++++++++++++++++++++++++++++++++++++++++++++++++++++++++++++++
-- Managed objects for Address functions
-- +++++++++++++++++++++++++++++++++++++++++++++++++++++++++++++++++++++++++++++
juniAaaAddrGeneral            OBJECT IDENTIFIER ::= { juniAaaAddress 1 }

juniAaaAddrPoolDefault OBJECT-TYPE
    SYNTAX      INTEGER {
                    none(0),
                    local(1),
                    dhcp(2) }
    MAX-ACCESS  read-write
    STATUS      current
    DESCRIPTION
        "Identifies the default source of IP address allocation for remote
        access links:
            none        No address source is specified.  Using this setting
                        allows the remote PPP subscriber (client) to set it's
                        own address.
            local       Use the local address pool named 'default'.
            dhcp        Use DHCP service."
    ::= { juniAaaAddrGeneral 1 }

juniAaaDupAddrCheck OBJECT-TYPE
    SYNTAX      TruthValue
    MAX-ACCESS  read-write
    STATUS      current
    DESCRIPTION
        "Enables/disables the duplicate IP address checking which causes the
        system to check the route table for the PPP user's dynamic IP address
        is provided to PPP (from AAA)."
    ::= { juniAaaAddrGeneral 2 }

juniAaaAddrNameServer         OBJECT IDENTIFIER ::= { juniAaaAddress 2 }

juniAaaAddrDns                OBJECT IDENTIFIER ::= { juniAaaAddrNameServer 1 }
juniAaaAddrWins               OBJECT IDENTIFIER ::= { juniAaaAddrNameServer 2 }

juniAaaAddrDnsPrimary OBJECT-TYPE
    SYNTAX      IpAddress
    MAX-ACCESS  read-write
    STATUS      current
    DESCRIPTION
        "The IP address of the primary DNS server to be used by remote access
        clients.  A value of 0.0.0.0 indicates no server is configured."
    ::= { juniAaaAddrDns 1 }

juniAaaAddrDnsSecondary OBJECT-TYPE
    SYNTAX      IpAddress
    MAX-ACCESS  read-write
    STATUS      current
    DESCRIPTION
        "The IP address of the secondary DNS server to be used by remote access
        clients.  A value of 0.0.0.0 indicates no server is configured."
    ::= { juniAaaAddrDns 2 }

juniAaaAddrIpv6DnsPrimary OBJECT-TYPE
    SYNTAX      Ipv6Address
    MAX-ACCESS  read-write
    STATUS      current
    DESCRIPTION
        "The IPv6 address of the primary IPv6 DNS server to be used by remote
        access clients.  A value of ::0 indicates no server is configured."
    ::= { juniAaaAddrDns 3 }

juniAaaAddrIpv6DnsSecondary OBJECT-TYPE
    SYNTAX      Ipv6Address
    MAX-ACCESS  read-write
    STATUS      current
    DESCRIPTION
        "The IPv6 address of the secondary IPv6 DNS server to be used by remote
        access clients.  A value of ::0 indicates no server is configured."
    ::= { juniAaaAddrDns 4 }

juniAaaAddrWinsPrimary OBJECT-TYPE
    SYNTAX      IpAddress
    MAX-ACCESS  read-write
    STATUS      current
    DESCRIPTION
        "The IP address of the primary WINS server to be used by remote access
        clients.  A value of 0.0.0.0 indicates no server is configured."
    ::= { juniAaaAddrWins 1 }

juniAaaAddrWinsSecondary OBJECT-TYPE
    SYNTAX      IpAddress
    MAX-ACCESS  read-write
    STATUS      current
    DESCRIPTION
        "The IP address of the secondary WINS server to be used by remote access
        clients.  A value of 0.0.0.0 indicates no server is configured."
    ::= { juniAaaAddrWins 2 }


-- +++++++++++++++++++++++++++++++++++++++++++++++++++++++++++++++++++++++++++++
-- Managed objects for Timeout functions
-- +++++++++++++++++++++++++++++++++++++++++++++++++++++++++++++++++++++++++++++
juniAaaTimeoutGeneral         OBJECT IDENTIFIER ::= { juniAaaTimeout 1 }

juniAaaIdleTimeout OBJECT-TYPE
    SYNTAX      Integer32 (0|300..86400)
    UNITS       "seconds"
    MAX-ACCESS  read-write
    STATUS      current
    DESCRIPTION
        "The maximum number of seconds that a user session can be idle before
        system disconnects the user, ranging from 300 to 86400 seconds, 0
        disables idle timeout."
    ::= { juniAaaTimeoutGeneral 1 }

juniAaaSessionTimeout OBJECT-TYPE
    SYNTAX      Integer32 (0|60..31622400)
    UNITS       "seconds"
    MAX-ACCESS  read-write
    STATUS      current
    DESCRIPTION
        "The maximum number of seconds that a user session can be established
        before system disconnects the user, ranging from 60 to 31622400 seconds.
        0 specifies that a default value should be used, according to the rules
        of the implementing interface."
    ::= { juniAaaTimeoutGeneral 2 }

juniAaaMonitorIngressTrafficOnly OBJECT-TYPE
    SYNTAX      JuniEnable
    MAX-ACCESS  read-write
    STATUS      current
    DESCRIPTION
        "Enables/disables the monitoring of ingress traffic. Inactive sessions
        are disconnected after a period, specified in juniAaaIdleTimeout.
        Inactivity is determined by both inbound and outbound traffic. If this
        option is enabled, only ingress traffic is monitored for determining
        session inactivity."
    DEFVAL    { disable }

    ::= { juniAaaTimeoutGeneral 3 }


-- +++++++++++++++++++++++++++++++++++++++++++++++++++++++++++++++++++++++++++++
-- Managed objects for Tunnel functions
-- +++++++++++++++++++++++++++++++++++++++++++++++++++++++++++++++++++++++++++++
juniAaaTunnelGeneral         OBJECT IDENTIFIER ::= { juniAaaTunnel 1 }

juniAaaTunnelClientName OBJECT-TYPE
    SYNTAX      DisplayString (SIZE(0..64))
    MAX-ACCESS  read-write
    STATUS      current
    DESCRIPTION
        "The default tunnel client hostname associated with this virtual router.
        This object is used when no tunnel client name (client auth ID) is
        supplied in the authentication response."
    DEFVAL    { "" }
    ::= { juniAaaTunnelGeneral 1 }

juniAaaTunnelPassword OBJECT-TYPE
    SYNTAX      DisplayString (SIZE(0..32))
    MAX-ACCESS  read-write
    STATUS      current
    DESCRIPTION
        "The default tunnel password associated with this virtual router.
        This object is used when no tunnel password is supplied in the
        authentication response.  The object returns a null length string
        on reads due to security concerns."
    DEFVAL    { "" }
    ::= { juniAaaTunnelGeneral 2 }

juniAaaTunnelNasPortMethod OBJECT-TYPE
    SYNTAX      INTEGER {
                    none(0),
                    ciscoAvp(1) }
    MAX-ACCESS  read-write
    STATUS      current
    DESCRIPTION
        "The default tunnel NAS-port method associated with this virtual router.
        This object is used to specify the LAC's NAS-port method.  This provides
        limit compatiability to Cisco LNS for the NAS-port method AVP."
    DEFVAL    { none }
    ::= { juniAaaTunnelGeneral 3 }

juniAaaTunnelIgnoreNasPort OBJECT-TYPE
    SYNTAX      TruthValue
    MAX-ACCESS  read-write
    STATUS      current
    DESCRIPTION
        "Enables/disables the use of the NAS-port value that is passed in from
        the tunnel application."
    ::= { juniAaaTunnelGeneral 4 }

juniAaaTunnelIgnoreNasPortType OBJECT-TYPE
    SYNTAX      TruthValue
    MAX-ACCESS  read-write
    STATUS      current
    DESCRIPTION
        "Enables/disables the use of the NAS-port-type value that is passed in
        from the tunnel application."
    ::= { juniAaaTunnelGeneral 5 }

juniAaaTunnelAssignmentIdFormat OBJECT-TYPE
    SYNTAX      INTEGER {
                    assignmentId(0),
                    clientServerId(1) }
    MAX-ACCESS  read-write
    STATUS      current
    DESCRIPTION
        "The tunnel assignment ID format for distinguishing tunnel definitions.
        This object is used to specify the tunnel assigment ID format passed to
        the LAC.  The value assignmentId(0) indicates that the original tunnel
        assignment ID value is to be used; clientServerId(1) indicates that the
        concatenated value from client-auth-name, server-auth-name, and
        assignment-id is to be used."
    DEFVAL    { assignmentId }
    ::= { juniAaaTunnelGeneral 6 }

juniAaaTunnelSwitchProfile OBJECT-TYPE
    SYNTAX      JuniAaaTunnelSwitchProfileName
    MAX-ACCESS  read-write
    STATUS      current
    DESCRIPTION
        "The default tunnel switch profile associated with this virtual router.
        This object is used when no tunnel switch profile is supplied in the
        authentication response."
    DEFVAL    { "" }
    ::= { juniAaaTunnelGeneral 7 }

juniAaaTunnelTxConnectSpeedMethod OBJECT-TYPE
    SYNTAX      INTEGER {
                    notSet(0),
                    staticLayer2(1),
                    dynamicLayer2(2),
                    qos(3),
                    actual(4) }
    MAX-ACCESS  read-write
    STATUS      current
    DESCRIPTION
        "The default tunnel tx connect speed method associated with this
        virtual router.  This object is used to specify the LAC's tx connect
        speed method."
    DEFVAL    { notSet }
    ::= { juniAaaTunnelGeneral 8 }

-- +++++++++++++++++++++++++++++++++++++++++++++++++++++++++++++++++++++++++++++
-- Managed objects for Statistics monitoring
-- +++++++++++++++++++++++++++++++++++++++++++++++++++++++++++++++++++++++++++++
juniAaaIncomingInitiateRequests OBJECT-TYPE
    SYNTAX      Counter32
    MAX-ACCESS  read-only
    STATUS      current
    DESCRIPTION
        "The number of AAA incoming initiate requests"
    ::= { juniAaaStatistics 1 }

juniAaaIncomingTerminateRequests OBJECT-TYPE
    SYNTAX      Counter32
    MAX-ACCESS  read-only
    STATUS      current
    DESCRIPTION
        "The number of AAA incomining termination requests"
    ::= { juniAaaStatistics 2 }

juniAaaOutgoingTunnelGrantResponses OBJECT-TYPE
    SYNTAX      Counter32
    MAX-ACCESS  read-only
    STATUS      current
    DESCRIPTION
        "The number of AAA outgoing tunnel grant responses"
    ::= { juniAaaStatistics 3 }

juniAaaOutgoingGrantResponses OBJECT-TYPE
    SYNTAX      Counter32
    MAX-ACCESS  read-only
    STATUS      current
    DESCRIPTION
        "The number of AAA outgoing grant responses"
    ::= { juniAaaStatistics 4 }

juniAaaOutgoingDenyResponses OBJECT-TYPE
    SYNTAX      Counter32
    MAX-ACCESS  read-only
    STATUS      current
    DESCRIPTION
        "The number of AAA outgoing deny responses"
    ::= { juniAaaStatistics 5 }

juniAaaOutgoingErrorResponses OBJECT-TYPE
    SYNTAX      Counter32
    MAX-ACCESS  read-only
    STATUS      current
    DESCRIPTION
        "The number of AAA outgoing error responses"
    ::= { juniAaaStatistics 6 }

juniAaaOutgoingAuthRequests OBJECT-TYPE
    SYNTAX      Counter32
    MAX-ACCESS  read-only
    STATUS      current
    DESCRIPTION
        "The number of AAA outgoing authentication requests"
    ::= { juniAaaStatistics 7 }

juniAaaIncomingAuthResponses OBJECT-TYPE
    SYNTAX      Counter32
    MAX-ACCESS  read-only
    STATUS      current
    DESCRIPTION
        "The number of AAA incoming authentication responses"
    ::= { juniAaaStatistics 8 }

juniAaaOutgoingReAuthRequests OBJECT-TYPE
    SYNTAX      Counter32
    MAX-ACCESS  read-only
    STATUS      current
    DESCRIPTION
        "The number of AAA outgoing re-authentication requests"
    ::= { juniAaaStatistics 9 }

juniAaaIncomingReAuthResponses OBJECT-TYPE
    SYNTAX      Counter32
    MAX-ACCESS  read-only
    STATUS      current
    DESCRIPTION
        "The number of AAA incoming re-authentication responses"
    ::=  { juniAaaStatistics 10 }

juniAaaOutgoingAcctRequests OBJECT-TYPE
    SYNTAX      Counter32
    MAX-ACCESS  read-only
    STATUS      current
    DESCRIPTION
        "The number of AAA outgoing accounting requests"
    ::= { juniAaaStatistics 11 }

juniAaaIncomingAcctResponses OBJECT-TYPE
    SYNTAX      Counter32
    MAX-ACCESS  read-only
    STATUS      current
    DESCRIPTION
        "The number of AAA incoming accounting responses"
    ::= { juniAaaStatistics 12 }

juniAaaOutgoingDupAcctRequests OBJECT-TYPE
    SYNTAX      Counter32
    MAX-ACCESS  read-only
    STATUS      current
    DESCRIPTION
        "The number of AAA outgoing duplicate accounting requests"
    ::= { juniAaaStatistics 13 }

juniAaaIncomingDupAcctResponses OBJECT-TYPE
    SYNTAX      Counter32
    MAX-ACCESS  read-only
    STATUS      current
    DESCRIPTION
        "The number of AAA incoing duplication accounting responses"
    ::= { juniAaaStatistics 14 }

juniAaaOutgoingAddrRequests OBJECT-TYPE
    SYNTAX      Counter32
    MAX-ACCESS  read-only
    STATUS      current
    DESCRIPTION
        "The number of AAA outgoing address requests"
    ::= { juniAaaStatistics 15 }

juniAaaIncomingAddrResponses OBJECT-TYPE
    SYNTAX      Counter32
    MAX-ACCESS  read-only
    STATUS      current
    DESCRIPTION
        "The number of AAA incoming address responses"
    ::= { juniAaaStatistics 16 }

juniAaaOutgoingBcastAcctRequests OBJECT-TYPE
    SYNTAX      Counter32
    MAX-ACCESS  read-only
    STATUS      current
    DESCRIPTION
        "The number of AAA outgoing broadcast accounting requests"
    ::= { juniAaaStatistics 17 }

juniAaaIncomingBcastAcctResponses OBJECT-TYPE
    SYNTAX      Counter32
    MAX-ACCESS  read-only
    STATUS      current
    DESCRIPTION
        "The number of AAA incoing broadcast accounting responses"
    ::= { juniAaaStatistics 18 }




-- +++++++++++++++++++++++++++++++++++++++++++++++++++++++++++++++++++++++++++++
-- Managed objects for Subscriber functions
-- +++++++++++++++++++++++++++++++++++++++++++++++++++++++++++++++++++++++++++++
juniAaaSubscriberMaxCount OBJECT-TYPE
    SYNTAX      Integer32
    MAX-ACCESS  read-only
    STATUS      current
    DESCRIPTION
        "The configuration setting for the maximum number of subscribers.  There
        is a grace number of subscribers above this limit, which when reached
        will cause authentication requests to be denied."
    ::= { juniAaaSubscribers 1 }

juniAaaSubscriberPeakCount OBJECT-TYPE
    SYNTAX      Gauge32
    MAX-ACCESS  read-only
    STATUS      current
    DESCRIPTION
        "The peak number of subscribers.  The peak count includes successfully
        authenticated subscribers as well as those subscribers in the process of
        being authenticated."
    ::= { juniAaaSubscribers 2 }

juniAaaSubscriberCount OBJECT-TYPE
    SYNTAX      Gauge32
    MAX-ACCESS  read-only
    STATUS      current
    DESCRIPTION
        "The current number of subscribers.  The subscriber count includes
        successfully authenticated subscribers as well as those subscribers in
        the process of being authenticated."
    ::= { juniAaaSubscribers 3 }

juniAaaSubscriberTable OBJECT-TYPE
    SYNTAX      SEQUENCE OF JuniAaaSubscriberEntry
    MAX-ACCESS  not-accessible
    STATUS      current
    DESCRIPTION
        "The entries in this table represent subscribers by subscriber handle
        value."
    ::= { juniAaaSubscribers 4 }

juniAaaSubscriberEntry OBJECT-TYPE
    SYNTAX      JuniAaaSubscriberEntry
    MAX-ACCESS  not-accessible
    STATUS      current
    DESCRIPTION
        "A specification of subscribers by subscriber handle."
    INDEX     { juniAaaSubscriberHandle }
    ::= { juniAaaSubscriberTable 1 }

JuniAaaSubscriberEntry ::= SEQUENCE {
    juniAaaSubscriberHandle               Unsigned32,
    juniAaaSubscriberUserName             DisplayString,
    juniAaaSubscriberRouterName           JuniName,
    juniAaaSubscriberRouterIndex          Unsigned32,
    juniAaaSubscriberLoginTime            DisplayString,
    juniAaaSubscriberIpAddress            IpAddress,
    juniAaaSubscriberIpAddressMask        IpAddress,
    juniAaaSubscriberAddrAssignType       JuniAddressAssignType,
    juniAaaSubscriberInterfaceId          DisplayString,
    juniAaaSubscriberState                JuniSubscriberState,
    juniAaaSubscriberClientType           JuniSubscriberClientType,
    juniAaaSubscriberIngressPolicyName    DisplayString,
    juniAaaSubscriberEgressPolicyName     DisplayString,
    juniAaaSubscriberQosProfileName       DisplayString,
    juniAaaSubscriberRowStatus            RowStatus,
    juniAaaSubscriberIpv6RouterIndex      Unsigned32,
    juniAaaSubscriberIpv6AddrIfIdentifier Ipv6AddressIfIdentifier }

juniAaaSubscriberHandle OBJECT-TYPE
    SYNTAX      Unsigned32
    MAX-ACCESS  not-accessible
    STATUS      current
    DESCRIPTION
        "The subscriber handle associated with this subscriber.  A subscriber
        handle is a monotomically increasing integer."
    ::= { juniAaaSubscriberEntry 1 }

juniAaaSubscriberUserName OBJECT-TYPE
    SYNTAX      DisplayString
    MAX-ACCESS  read-only
    STATUS      current
    DESCRIPTION
        "The RADIUS userName associated with this subscriber."
    ::= { juniAaaSubscriberEntry 2 }

juniAaaSubscriberRouterName OBJECT-TYPE
    SYNTAX      JuniName
    MAX-ACCESS  read-only
    STATUS      current
    DESCRIPTION
        "The virtual router assigned to this subscriber."
    ::= { juniAaaSubscriberEntry 3 }

juniAaaSubscriberRouterIndex OBJECT-TYPE
    SYNTAX      Unsigned32
    MAX-ACCESS  read-only
    STATUS      current
    DESCRIPTION
        "The router index that identifies the virtual router associated with
        this subscriber.  The value of this object can be used to index the
        router in the juniRouterTable."
    ::= { juniAaaSubscriberEntry 4 }

juniAaaSubscriberLoginTime OBJECT-TYPE
    SYNTAX      DisplayString
    MAX-ACCESS  read-only
    STATUS      current
    DESCRIPTION
        "The time this subscriber logged in to RADIUS server."
    ::= { juniAaaSubscriberEntry 5 }

juniAaaSubscriberIpAddress OBJECT-TYPE
    SYNTAX      IpAddress
    MAX-ACCESS  read-only
    STATUS      current
    DESCRIPTION
        "The client IP Address assigned to this subscriber."
    ::= { juniAaaSubscriberEntry 6 }

juniAaaSubscriberIpAddressMask OBJECT-TYPE
    SYNTAX      IpAddress
    MAX-ACCESS  read-only
    STATUS      current
    DESCRIPTION
        "The client IP Address Mask assigned to this subscriber."
    ::= { juniAaaSubscriberEntry 7 }

juniAaaSubscriberAddrAssignType OBJECT-TYPE
    SYNTAX      JuniAddressAssignType
    MAX-ACCESS  read-only
    STATUS      current
    DESCRIPTION
        "The address assignment type for this subscriber."
    ::= { juniAaaSubscriberEntry 8 }

juniAaaSubscriberInterfaceId OBJECT-TYPE
    SYNTAX      DisplayString
    MAX-ACCESS  read-only
    STATUS      current
    DESCRIPTION
        "A text string describing the local interface associated with this
        subscriber.  Types/formats/examples for this string include:

        ERX:  <portLocation> == <slot>/<port>;
        E320: <portLocation> == <slot>/<adapter>/<port>;

        ATM Virtual Circuit
        atm <portLocation>:<vpi>.<vci>
        'atm 3/2:0.100'   (ERX)
        'atm 3/0/2:0.100' (E320)

        Ethernet
        { fastEthernet | gigabitEthernet } <portLocation>
        'fastEthernet 3/2'         (ERX)
        'gigabitEthernet 3/2'      (ERX)
        'gigabitEthernet 3/0/2'    (E320)
        'tenGigabitEthernet 3/0/2' (E320)

        Ethernet VLAN
        { fastEthernet | gigabitEthernet } <portLocation>:<vlanID>
        'fastEthernet 3/2:1000'         (ERX)
        'gigabitEthernet 3/2:1000'      (ERX)
        'gigabitEthernet 3/0/2:1000'    (E320)
        'tenGigabitEthernet 3/0/2:1000' (E320)

        Channelized Serial
        serial <portLocation>:<channelSpecifier>[/<channelSpecifier>]*
        'serial 3/2:4'            (ERX T1/E1)
        'serial 3/2:2/4'          (ERX T3/E3)
        'serial 3/2:2/1/1/4'      (ERX OC3/OC12 - channelized DS3)
        'serial 3/2:2/1/1/1/4'    (ERX OC3/OC12 - virtual tributaries)
        'serial 3/0/2:2/1/1/4'    (E320 OC3/OC12 - channelized DS3)
        'serial 3/0/2:2/1/1/1/4'  (E320 OC3/OC12 - virtual tributaries)

        L2TP over IP
        ip:<localIpAddr>:<peerIpAddr>:<localTunnelID>:<peerTunnelID>:
            <localSessionID>:<peerSessionID>:<callSerialNumber>
        'ip:10.10.0.1:20.20.0.2:1234:5678:9abc:def0:6789abcd'
            (Note: tunnelIDs, sessionIDs, and callSerialNumber are in
                   hexadecimal.)

        Other formats may be supported over time."
    ::= { juniAaaSubscriberEntry 9 }

juniAaaSubscriberState OBJECT-TYPE
    SYNTAX      JuniSubscriberState
    MAX-ACCESS  read-only
    STATUS      current
    DESCRIPTION
        "The state of this subscriber."
    ::= { juniAaaSubscriberEntry 10 }

juniAaaSubscriberClientType OBJECT-TYPE
    SYNTAX      JuniSubscriberClientType
    MAX-ACCESS  read-only
    STATUS      current
    DESCRIPTION
        "The client type for this subscriber.  Certain client types (e.g.,
        'other') might be suppressed from representation in this table."
    ::= { juniAaaSubscriberEntry 11 }

juniAaaSubscriberIngressPolicyName OBJECT-TYPE
    SYNTAX      DisplayString
    MAX-ACCESS  read-only
    STATUS      current
    DESCRIPTION
        "The Ingress Policy Name associated with this subscriber."
    ::= { juniAaaSubscriberEntry 12 }

juniAaaSubscriberEgressPolicyName OBJECT-TYPE
    SYNTAX      DisplayString
    MAX-ACCESS  read-only
    STATUS      current
    DESCRIPTION
        "The Egress Policy Name associated with this subscriber."
    ::= { juniAaaSubscriberEntry 13 }

juniAaaSubscriberQosProfileName OBJECT-TYPE
    SYNTAX      DisplayString
    MAX-ACCESS  read-only
    STATUS      current
    DESCRIPTION
        "The QoS Profile Name associated with this subscriber."
    ::= { juniAaaSubscriberEntry 14 }

juniAaaSubscriberRowStatus  OBJECT-TYPE
    SYNTAX      RowStatus
    MAX-ACCESS  read-write
    STATUS      current
    DESCRIPTION
        "Controls the deletion of the subscriber from this table.  Deletion of
        the subscriber is analogous to logging the subscriber out of the
        network.

        Note: only 'destroy' is supported for SNMP SET operations."
    ::= { juniAaaSubscriberEntry 15 }

juniAaaSubscriberIpv6RouterIndex OBJECT-TYPE
    SYNTAX      Unsigned32
    MAX-ACCESS  read-only
    STATUS      current
    DESCRIPTION
        "The router index that identifies the virtual router associated with
        this subscriber's IPv6 interface.  The value of this object can be used
        to index the router in the juniRouterTable."
    ::= { juniAaaSubscriberEntry 16 }

juniAaaSubscriberIpv6AddrIfIdentifier OBJECT-TYPE
    SYNTAX      Ipv6AddressIfIdentifier
    MAX-ACCESS  read-only
    STATUS      current
    DESCRIPTION
        "The client IPv6 Address Interface Identifier assigned to this
        subscriber."
    ::= { juniAaaSubscriberEntry 17 }


-- +++++++++++++++++++++++++++++++++++++++++++++++++++++++++++++++++++++++++++++
-- Subscriber information by virtual router
-- +++++++++++++++++++++++++++++++++++++++++++++++++++++++++++++++++++++++++++++
juniAaaSubscriberRouterSummaryTable OBJECT-TYPE
    SYNTAX      SEQUENCE OF JuniAaaSubscriberRouterSummaryEntry
    MAX-ACCESS  not-accessible
    STATUS      current
    DESCRIPTION
        "The entries in this table report number of subscribers per router."
    ::= { juniAaaSubscribers 5 }

juniAaaSubscriberRouterSummaryEntry OBJECT-TYPE
    SYNTAX      JuniAaaSubscriberRouterSummaryEntry
    MAX-ACCESS  not-accessible
    STATUS      current
    DESCRIPTION
        "A specification of subscribers for a router."
    INDEX     { juniAaaSubscriberRouterSummaryRouterIndex }
    ::= { juniAaaSubscriberRouterSummaryTable 1 }

JuniAaaSubscriberRouterSummaryEntry ::= SEQUENCE {
    juniAaaSubscriberRouterSummaryRouterIndex    Unsigned32,
    juniAaaSubscriberRouterSummaryCount          Gauge32 }

juniAaaSubscriberRouterSummaryRouterIndex OBJECT-TYPE
    SYNTAX      Unsigned32
    MAX-ACCESS  not-accessible
    STATUS      current
    DESCRIPTION
        "The router index of the virtual router.  The value of this object can
        be used to retrieve additional information in the router mib."
    REFERENCE
        "Juniper-ROUTER-MIB"
    ::= { juniAaaSubscriberRouterSummaryEntry 1 }

juniAaaSubscriberRouterSummaryCount OBJECT-TYPE
    SYNTAX      Gauge32
    MAX-ACCESS  read-only
    STATUS      current
    DESCRIPTION
        "The number of subscribers on this router."
    ::= { juniAaaSubscriberRouterSummaryEntry 2 }


juniAaaSubscriberRouterTable OBJECT-TYPE
    SYNTAX      SEQUENCE OF JuniAaaSubscriberRouterEntry
    MAX-ACCESS  not-accessible
    STATUS      current
    DESCRIPTION
        "The entries in this table sort subscribers by router ID."
    ::= { juniAaaSubscribers 6 }

juniAaaSubscriberRouterEntry OBJECT-TYPE
    SYNTAX      JuniAaaSubscriberRouterEntry
    MAX-ACCESS  not-accessible
    STATUS      current
    DESCRIPTION
        "A specification of subscribers by router ID."
    INDEX     { juniAaaSubscriberRouterRouterIndex,
                juniAaaSubscriberRouterHandle }
    ::= { juniAaaSubscriberRouterTable 1 }

JuniAaaSubscriberRouterEntry ::= SEQUENCE {
    juniAaaSubscriberRouterRouterIndex   Unsigned32,
    juniAaaSubscriberRouterHandle        Unsigned32,
    juniAaaSubscriberRouterRowStatus     RowStatus }

juniAaaSubscriberRouterRouterIndex OBJECT-TYPE
    SYNTAX      Unsigned32
    MAX-ACCESS  not-accessible
    STATUS      current
    DESCRIPTION
        "The router index of the virtual router.  The value of this object can
        be used to retrieve additional information in the router MIB."
    REFERENCE
        "Juniper-ROUTER-MIB"
    ::= { juniAaaSubscriberRouterEntry 1 }

juniAaaSubscriberRouterHandle OBJECT-TYPE
    SYNTAX      Unsigned32
    MAX-ACCESS  not-accessible
    STATUS      current
    DESCRIPTION
        "The subscriber handle associated with this subscriber.  A subscriber
        handle is a monotonically increasing integer."
    ::= { juniAaaSubscriberRouterEntry 2 }

juniAaaSubscriberRouterRowStatus  OBJECT-TYPE
    SYNTAX      RowStatus
    MAX-ACCESS  read-only
    STATUS      current
    DESCRIPTION
        "Always has value 'active'."
    ::= { juniAaaSubscriberRouterEntry 3 }


-- +++++++++++++++++++++++++++++++++++++++++++++++++++++++++++++++++++++++++++++
-- Subscriber information by interface location
-- +++++++++++++++++++++++++++++++++++++++++++++++++++++++++++++++++++++++++++++
juniAaaSubscriberLocationType OBJECT-TYPE
    SYNTAX      JuniInterfaceLocationType
    MAX-ACCESS  read-only
    STATUS      current
    DESCRIPTION
        "Describes the interpretation of JuniInterfaceLocationValue object
        values into platform-dependent interface location components, e.g.,
        'slot.port' on an ERX."
    ::= { juniAaaSubscribers 7 }

juniAaaSubscriberLocationSummaryTable OBJECT-TYPE
    SYNTAX      SEQUENCE OF JuniAaaSubscriberLocationSummaryEntry
    MAX-ACCESS  not-accessible
    STATUS      current
    DESCRIPTION
        "The entries in this table report number of subscribers per interface
        location."
    ::= { juniAaaSubscribers 8 }

juniAaaSubscriberLocationSummaryEntry OBJECT-TYPE
    SYNTAX      JuniAaaSubscriberLocationSummaryEntry
    MAX-ACCESS  not-accessible
    STATUS      current
    DESCRIPTION
        "A specification of subscribers on an interface location."
    INDEX     { juniAaaSubscriberLocationSummaryLocationIndex }
    ::= { juniAaaSubscriberLocationSummaryTable 1 }

JuniAaaSubscriberLocationSummaryEntry ::= SEQUENCE {
    juniAaaSubscriberLocationSummaryLocationIndex   JuniInterfaceLocationValue,
    juniAaaSubscriberLocationSummaryCount           Gauge32 }

juniAaaSubscriberLocationSummaryLocationIndex OBJECT-TYPE
    SYNTAX      JuniInterfaceLocationValue
    MAX-ACCESS  not-accessible
    STATUS      current
    DESCRIPTION
        "The value of a platform interface location."
    ::= { juniAaaSubscriberLocationSummaryEntry 1 }

juniAaaSubscriberLocationSummaryCount OBJECT-TYPE
    SYNTAX      Gauge32
    MAX-ACCESS  read-only
    STATUS      current
    DESCRIPTION
        "The number of subscribers associated with this interface location."
    ::= { juniAaaSubscriberLocationSummaryEntry 2 }


juniAaaSubscriberLocationTable OBJECT-TYPE
    SYNTAX      SEQUENCE OF JuniAaaSubscriberLocationEntry
    MAX-ACCESS  not-accessible
    STATUS      current
    DESCRIPTION
        "The entries in this table sort subscribers by interface location."
    ::= { juniAaaSubscribers 9 }

juniAaaSubscriberLocationEntry OBJECT-TYPE
    SYNTAX      JuniAaaSubscriberLocationEntry
    MAX-ACCESS  not-accessible
    STATUS      current
    DESCRIPTION
        "An association of a subscriber to an interface location."
    INDEX     { juniAaaSubscriberLocationLocationIndex,
                juniAaaSubscriberLocationHandle }
    ::= { juniAaaSubscriberLocationTable 1 }

JuniAaaSubscriberLocationEntry ::= SEQUENCE {
    juniAaaSubscriberLocationLocationIndex   JuniInterfaceLocationValue,
    juniAaaSubscriberLocationHandle          Unsigned32,
    juniAaaSubscriberLocationRowStatus       RowStatus }

juniAaaSubscriberLocationLocationIndex OBJECT-TYPE
    SYNTAX      JuniInterfaceLocationValue
    MAX-ACCESS  not-accessible
    STATUS      current
    DESCRIPTION
        "The value of a platform interface location."
    ::= { juniAaaSubscriberLocationEntry 1 }

juniAaaSubscriberLocationHandle OBJECT-TYPE
    SYNTAX      Unsigned32
    MAX-ACCESS  not-accessible
    STATUS      current
    DESCRIPTION
        "The subscriber handle associated with this subscriber.  A subscriber
        handle is a monotonically increasing integer."
    ::= { juniAaaSubscriberLocationEntry 2 }

juniAaaSubscriberLocationRowStatus  OBJECT-TYPE
    SYNTAX      RowStatus
    MAX-ACCESS  read-only
    STATUS      current
    DESCRIPTION
        "Always has value 'active'."
    ::= { juniAaaSubscriberLocationEntry 3 }


-- +++++++++++++++++++++++++++++++++++++++++++++++++++++++++++++++++++++++++++++
-- Pseudo-subscriber information
-- +++++++++++++++++++++++++++++++++++++++++++++++++++++++++++++++++++++++++++++
juniAaaSubscriberPseudoPeakCount OBJECT-TYPE
    SYNTAX      Gauge32
    MAX-ACCESS  read-only
    STATUS      current
    DESCRIPTION
        "The peak number of pseudo-subscribers.  The peak count includes
        successfully authenticated pseudo-subscribers as well as those
        pseudo-subscribers in the process of being authenticated.

        Pseudo-subscribers are those whose identities are locally configured on
        a dynamic link (e.g. an ATM subinterface) via the (imprecisely named)
        Juniper-SUBSCRIBER-MIB.  Some links (e.g. IPoA) provide no link
        protocol with which to query the identity of a remote user.  In such a
        case, a locally configured pseudo-subscriber can be used to conduct AAA
        authentication-based configuration of the dynamic link when it becomes
        active.

        Pseudo-subscribers are understood to be intended more for dynamic
        configuration than for actually identifying the remote user.
        Consequently, the pseudo-subscribers are not reflected in any of the
        subscriber tables defined in this MIB."
    ::= { juniAaaSubscribers 10 }

juniAaaSubscriberPseudoCount OBJECT-TYPE
    SYNTAX      Gauge32
    MAX-ACCESS  read-only
    STATUS      current
    DESCRIPTION
        "The current number of pseudo-subscribers.  The pseudo-subscriber count
        includes successfully authenticated subscribers as well as those
        subscribers in the process of being authenticated.

        Pseudo-subscribers are those whose identities are locally configured on
        a dynamic link (e.g. an ATM subinterface) via the (imprecisely named)
        Juniper-SUBSCRIBER-MIB.  Some links (e.g. IPoA) provide no link
        protocol with which to query the identity of a remote user.  In such a
        case, a locally configured pseudo-subscriber can be used to conduct AAA
        authentication-based configuration of the dynamic link when it becomes
        active.

        Pseudo-subscribers are understood to be intended more for dynamic
        configuration than for actually identifying the remote user.
        Consequently, the pseudo-subscribers are not reflected in any of the
        subscriber tables defined in this MIB."
    ::= { juniAaaSubscribers 11 }


-- +++++++++++++++++++++++++++++++++++++++++++++++++++++++++++++++++++++++++++++
-- IPv6 Address Prefix subscriber information
-- +++++++++++++++++++++++++++++++++++++++++++++++++++++++++++++++++++++++++++++
juniAaaSubscriberIpv6AddrPrefixTable OBJECT-TYPE
    SYNTAX      SEQUENCE OF JuniAaaSubscriberIpv6AddrPrefixEntry
    MAX-ACCESS  not-accessible
    STATUS      current
    DESCRIPTION
        "The entries in this table represent IPv6 Address Prefixes by subscriber
        handle value."
    ::= { juniAaaSubscribers 12 }

juniAaaSubscriberIpv6AddrPrefixEntry OBJECT-TYPE
    SYNTAX      JuniAaaSubscriberIpv6AddrPrefixEntry
    MAX-ACCESS  not-accessible
    STATUS      current
    DESCRIPTION
        "A specification of IPv6 Address Prefixes by subscriber handle."
    INDEX     { juniAaaSubscriberHandle,
                juniAaaSubscriberIpv6AddrPrefix,
                juniAaaSubscriberIpv6AddrPrefixSize }
    ::= { juniAaaSubscriberIpv6AddrPrefixTable 1 }

JuniAaaSubscriberIpv6AddrPrefixEntry ::= SEQUENCE {
    juniAaaSubscriberIpv6AddrPrefix      Ipv6AddressPrefix,
    juniAaaSubscriberIpv6AddrPrefixSize  Integer32 }

juniAaaSubscriberIpv6AddrPrefix OBJECT-TYPE
    SYNTAX      Ipv6AddressPrefix
    MAX-ACCESS  read-only
    STATUS      current
    DESCRIPTION
        "The client IPv6 Address Prefix assigned to this subscriber."
    ::= { juniAaaSubscriberIpv6AddrPrefixEntry 1 }

juniAaaSubscriberIpv6AddrPrefixSize OBJECT-TYPE
    SYNTAX      Integer32 (0..128)
    MAX-ACCESS  read-only
    STATUS      current
    DESCRIPTION
        "The size of the client IPv6 Address Prefix assigned to this
        subscriber."
    ::= { juniAaaSubscriberIpv6AddrPrefixEntry 2 }

juniAaaSubscriberExtTable OBJECT-TYPE
    SYNTAX      SEQUENCE OF JuniAaaSubscriberExtEntry
    MAX-ACCESS  not-accessible
    STATUS      current
    DESCRIPTION
        "The entries in this table represent subscribers extension attributes
         by subscriber handle value."
    ::= { juniAaaSubscribers 13 }

-- +++++++++++++++++++++++++++++++++++++++++++++++++++++++++++++++++++++++++++++
-- Subscriber information by interface
-- +++++++++++++++++++++++++++++++++++++++++++++++++++++++++++++++++++++++++++++

juniAaaSubscriberInterfaceSummaryTable OBJECT-TYPE
    SYNTAX      SEQUENCE OF JuniAaaSubscriberInterfaceSummaryEntry
    MAX-ACCESS  not-accessible
    STATUS      current
    DESCRIPTION
        "The entries in this table report number of subscribers per subscriber
        interface which includes the port type (1 = atm; 2 = ethernet), slot,
        port and sub-interface."
    ::= { juniAaaSubscribers 14 }

juniAaaSubscriberInterfaceSummaryEntry OBJECT-TYPE
    SYNTAX      JuniAaaSubscriberInterfaceSummaryEntry
    MAX-ACCESS  not-accessible
    STATUS      current
    DESCRIPTION
        "A specification of subscribers on an subscriber interface."
    INDEX     { juniAaaSubscriberInterfaceSummaryIndex,
                juniAaaSubscriberSubInterfaceSummaryIndex }
    ::= { juniAaaSubscriberInterfaceSummaryTable 1 }

JuniAaaSubscriberInterfaceSummaryEntry ::= SEQUENCE {
    juniAaaSubscriberInterfaceSummaryIndex     JuniSubscriberInterfaceValue,
    juniAaaSubscriberSubInterfaceSummaryIndex  Integer32,
    juniAaaSubscriberInterfaceSummaryCount     Gauge32 }

juniAaaSubscriberInterfaceSummaryIndex OBJECT-TYPE
    SYNTAX      JuniSubscriberInterfaceValue
    MAX-ACCESS  not-accessible
    STATUS      current
    DESCRIPTION
        "The value of a subscriber interface."
    ::= { juniAaaSubscriberInterfaceSummaryEntry 1 }

juniAaaSubscriberSubInterfaceSummaryIndex OBJECT-TYPE
    SYNTAX      Integer32
    MAX-ACCESS  not-accessible
    STATUS      current
    DESCRIPTION
        "The value of a subscriber sub-interface."
    ::= { juniAaaSubscriberInterfaceSummaryEntry 2 }

juniAaaSubscriberInterfaceSummaryCount OBJECT-TYPE
    SYNTAX      Gauge32
    MAX-ACCESS  read-only
    STATUS      current
    DESCRIPTION
        "The number of subscribers associated with this subscriber interface."
    ::= { juniAaaSubscriberInterfaceSummaryEntry 3 }

juniAaaSubscriberInterfaceTable OBJECT-TYPE
    SYNTAX      SEQUENCE OF JuniAaaSubscriberInterfaceEntry
    MAX-ACCESS  not-accessible
    STATUS      current
    DESCRIPTION
        "The subscriber entries in this table sorted by subscriber interface."
    ::= { juniAaaSubscribers 15 }

juniAaaSubscriberInterfaceEntry OBJECT-TYPE
    SYNTAX      JuniAaaSubscriberInterfaceEntry
    MAX-ACCESS  not-accessible
    STATUS      current
    DESCRIPTION
        "An association of a subscriber to a subscriber interface."
    INDEX     { juniAaaSubscriberInterfaceIndex,
                juniAaaSubscriberSubInterfaceIndex,
                juniAaaSubscriberInterfaceHandle }
    ::= { juniAaaSubscriberInterfaceTable 1 }

JuniAaaSubscriberInterfaceEntry ::= SEQUENCE {
    juniAaaSubscriberInterfaceIndex      JuniSubscriberInterfaceValue,
    juniAaaSubscriberSubInterfaceIndex   Integer32,
    juniAaaSubscriberInterfaceHandle     Unsigned32,
    juniAaaSubscriberInterfaceRowStatus  RowStatus }

juniAaaSubscriberInterfaceIndex OBJECT-TYPE
    SYNTAX      JuniSubscriberInterfaceValue
    MAX-ACCESS  not-accessible
    STATUS      current
    DESCRIPTION
        "The value of a subscriber interface.  This includes the
        port type (1 = ATM; 2 = Ethernet), slot, port, and sub-interface."
    ::= { juniAaaSubscriberInterfaceEntry 1 }

juniAaaSubscriberSubInterfaceIndex OBJECT-TYPE
    SYNTAX      Integer32
    MAX-ACCESS  not-accessible
    STATUS      current
    DESCRIPTION
        "The value of a subscriber sub-interface."
    ::= { juniAaaSubscriberInterfaceEntry 2 }

juniAaaSubscriberInterfaceHandle OBJECT-TYPE
    SYNTAX      Unsigned32
    MAX-ACCESS  not-accessible
    STATUS      current
    DESCRIPTION
        "The subscriber handle associated with this subscriber interface.
        A subscriber handle is a monotonically increasing integer."
    ::= { juniAaaSubscriberInterfaceEntry 3 }

juniAaaSubscriberInterfaceRowStatus  OBJECT-TYPE
    SYNTAX      RowStatus
    MAX-ACCESS  read-only
    STATUS      current
    DESCRIPTION
        "Always has value 'active'."
    ::= { juniAaaSubscriberInterfaceEntry 4 }

-- +++++++++++++++++++++++++++++++++++++++++++++++++++++++++++++++++++++++++++++
-- Subscriber information by slot
-- +++++++++++++++++++++++++++++++++++++++++++++++++++++++++++++++++++++++++++++

juniAaaSubscriberSlotSummaryTable OBJECT-TYPE
    SYNTAX      SEQUENCE OF JuniAaaSubscriberSlotSummaryEntry
    MAX-ACCESS  not-accessible
    STATUS      current
    DESCRIPTION
        "The entries in this table report number of subscribers per slot."
    ::= { juniAaaSubscribers 16 }

juniAaaSubscriberSlotSummaryEntry OBJECT-TYPE
    SYNTAX      JuniAaaSubscriberSlotSummaryEntry
    MAX-ACCESS  not-accessible
    STATUS      current
    DESCRIPTION
        "A specification of subscribers for a slot."
    INDEX     { juniAaaSubscriberSlotSummarySlotIndex }
    ::= { juniAaaSubscriberSlotSummaryTable 1 }

JuniAaaSubscriberSlotSummaryEntry ::= SEQUENCE {
    juniAaaSubscriberSlotSummarySlotIndex    Unsigned32,
    juniAaaSubscriberSlotSummaryCount          Gauge32 }

juniAaaSubscriberSlotSummarySlotIndex OBJECT-TYPE
    SYNTAX      Unsigned32
    MAX-ACCESS  not-accessible
    STATUS      current
    DESCRIPTION
        "The index of the slot."
    ::= { juniAaaSubscriberSlotSummaryEntry 1 }

juniAaaSubscriberSlotSummaryCount OBJECT-TYPE
    SYNTAX      Gauge32
    MAX-ACCESS  read-only
    STATUS      current
    DESCRIPTION
        "The number of subscribers on this slot."
    ::= { juniAaaSubscriberSlotSummaryEntry 2 }

juniAaaSubscriberSlotTable OBJECT-TYPE
    SYNTAX      SEQUENCE OF JuniAaaSubscriberSlotEntry
    MAX-ACCESS  not-accessible
    STATUS      current
    DESCRIPTION
        "The subscriber in this table sorted by slot."
    ::= { juniAaaSubscribers 17 }

juniAaaSubscriberSlotEntry OBJECT-TYPE
    SYNTAX      JuniAaaSubscriberSlotEntry
    MAX-ACCESS  not-accessible
    STATUS      current
    DESCRIPTION
        "A specification of subscribers by slot."
    INDEX     { juniAaaSubscriberSlotIndex,
                juniAaaSubscriberSlotHandle }
    ::= { juniAaaSubscriberSlotTable 1 }

JuniAaaSubscriberSlotEntry ::= SEQUENCE {
    juniAaaSubscriberSlotIndex   Unsigned32,
    juniAaaSubscriberSlotHandle        Unsigned32,
    juniAaaSubscriberSlotRowStatus     RowStatus }

juniAaaSubscriberSlotIndex OBJECT-TYPE
    SYNTAX      Unsigned32
    MAX-ACCESS  not-accessible
    STATUS      current
    DESCRIPTION
        "The index of the slot."
    ::= { juniAaaSubscriberSlotEntry 1 }

juniAaaSubscriberSlotHandle OBJECT-TYPE
    SYNTAX      Unsigned32
    MAX-ACCESS  not-accessible
    STATUS      current
    DESCRIPTION
        "The subscriber handle associated with this slot.  The subscriber
        handle is a monotonically increasing integer."
    ::= { juniAaaSubscriberSlotEntry 2 }

juniAaaSubscriberSlotRowStatus  OBJECT-TYPE
    SYNTAX      RowStatus
    MAX-ACCESS  read-only
    STATUS      current
    DESCRIPTION
        "Always has value 'active'."
    ::= { juniAaaSubscriberSlotEntry 3 }

-- +++++++++++++++++++++++++++++++++++++++++++++++++++++++++++++++++++++++++++++
-- Subscriber information by LAG Interface
-- +++++++++++++++++++++++++++++++++++++++++++++++++++++++++++++++++++++++++++++

juniAaaSubscriberLagInterfaceSummaryTable OBJECT-TYPE
    SYNTAX      SEQUENCE OF JuniAaaSubscriberLagInterfaceSummaryEntry
    MAX-ACCESS  not-accessible
    STATUS      current
    DESCRIPTION
        "The entries in this table report number of subscribers per lag."
    ::= { juniAaaSubscribers 20 }

juniAaaSubscriberLagInterfaceSummaryEntry OBJECT-TYPE
    SYNTAX      JuniAaaSubscriberLagInterfaceSummaryEntry
    MAX-ACCESS  not-accessible
    STATUS      current
    DESCRIPTION
        "A specification of subscribers for a lag."
    INDEX     { juniAaaSubscriberLagInterfaceSummaryLagName }
    ::= { juniAaaSubscriberLagInterfaceSummaryTable 1 }

JuniAaaSubscriberLagInterfaceSummaryEntry ::= SEQUENCE {
    juniAaaSubscriberLagInterfaceSummaryLagName    DisplayString,
    juniAaaSubscriberLagInterfaceSummaryCount           Gauge32 }

juniAaaSubscriberLagInterfaceSummaryLagName OBJECT-TYPE
    SYNTAX      DisplayString (SIZE(0..64))
    MAX-ACCESS  not-accessible
    STATUS      current
    DESCRIPTION
        "The name of the lag."
    ::= { juniAaaSubscriberLagInterfaceSummaryEntry 1 }

juniAaaSubscriberLagInterfaceSummaryCount OBJECT-TYPE
    SYNTAX      Gauge32
    MAX-ACCESS  read-only
    STATUS      current
    DESCRIPTION
        "The number of subscribers on this lag."
    ::= { juniAaaSubscriberLagInterfaceSummaryEntry 2 }

-- +++++++++++++++++++++++++++++++++++++++++++++++++++++++++++++++++++++++++++++
-- Subscriber information by profile
-- +++++++++++++++++++++++++++++++++++++++++++++++++++++++++++++++++++++++++++++

juniAaaSubscriberProfileSummaryTable OBJECT-TYPE
    SYNTAX      SEQUENCE OF JuniAaaSubscriberProfileSummaryEntry
    MAX-ACCESS  not-accessible
    STATUS      current
    DESCRIPTION
        "The entries in this table report number of subscribers per profile."
    ::= { juniAaaSubscribers 18 }

juniAaaSubscriberProfileSummaryEntry OBJECT-TYPE
    SYNTAX      JuniAaaSubscriberProfileSummaryEntry
    MAX-ACCESS  not-accessible
    STATUS      current
    DESCRIPTION
        "A specification of subscribers for a profile."
    INDEX     { juniAaaSubscriberProfileSummaryProfileName }
    ::= { juniAaaSubscriberProfileSummaryTable 1 }

JuniAaaSubscriberProfileSummaryEntry ::= SEQUENCE {
    juniAaaSubscriberProfileSummaryProfileName    DisplayString,
    juniAaaSubscriberProfileSummaryCount          Gauge32 }

juniAaaSubscriberProfileSummaryProfileName OBJECT-TYPE
    SYNTAX      DisplayString (SIZE(1..80))
    MAX-ACCESS  not-accessible
    STATUS      current
    DESCRIPTION
        "The name of the profile."

    ::= { juniAaaSubscriberProfileSummaryEntry 1 }

juniAaaSubscriberProfileSummaryCount OBJECT-TYPE
    SYNTAX      Gauge32
    MAX-ACCESS  read-only
    STATUS      current
    DESCRIPTION
        "The number of subscribers on this profile."
    ::= { juniAaaSubscriberProfileSummaryEntry 2 }


juniAaaSubscriberProfileTable OBJECT-TYPE
    SYNTAX      SEQUENCE OF JuniAaaSubscriberProfileEntry
    MAX-ACCESS  not-accessible
    STATUS      current
    DESCRIPTION
        "The entries in this table sort subscribers by profileName + profileHandle."
    ::= { juniAaaSubscribers 19 }

juniAaaSubscriberProfileEntry OBJECT-TYPE
    SYNTAX      JuniAaaSubscriberProfileEntry
    MAX-ACCESS  not-accessible
    STATUS      current
    DESCRIPTION
        "A specification of subscribers by profile ID."
    INDEX     { juniAaaSubscriberProfileName,
                juniAaaSubscriberProfileHandle }
    ::= { juniAaaSubscriberProfileTable 1 }

JuniAaaSubscriberProfileEntry ::= SEQUENCE {
    juniAaaSubscriberProfileName          DisplayString,
    juniAaaSubscriberProfileHandle        Unsigned32,
    juniAaaSubscriberProfileRowStatus     RowStatus }

juniAaaSubscriberProfileName OBJECT-TYPE
    SYNTAX      DisplayString (SIZE(1..80))
    MAX-ACCESS  not-accessible
    STATUS      current
    DESCRIPTION
        "The DCM profile name associated with this subscriber."

    ::= { juniAaaSubscriberProfileEntry 1 }

juniAaaSubscriberProfileHandle OBJECT-TYPE
    SYNTAX      Unsigned32
    MAX-ACCESS  not-accessible
    STATUS      current
    DESCRIPTION
        "The subscriber handle associated with this subscriber.  A subscriber
        handle is a monotonically increasing integer."
    ::= { juniAaaSubscriberProfileEntry 2 }

juniAaaSubscriberProfileRowStatus  OBJECT-TYPE
    SYNTAX      RowStatus
    MAX-ACCESS  read-only
    STATUS      current
    DESCRIPTION
        "Always has value 'active'."
    ::= { juniAaaSubscriberProfileEntry 3 }

-- +++++++++++++++++++++++++++++++++++++++++++++++++++++++++++++++++++++++++++++
--
-- +++++++++++++++++++++++++++++++++++++++++++++++++++++++++++++++++++++++++++++

juniAaaSubscriberExtEntry OBJECT-TYPE
    SYNTAX      JuniAaaSubscriberExtEntry
    MAX-ACCESS  not-accessible
    STATUS      current
    DESCRIPTION
        "A specification of subscribers extension attributes by subscriber
         handle."
    INDEX     { juniAaaSubscriberHandle }
    ::= { juniAaaSubscriberExtTable 1 }

JuniAaaSubscriberExtEntry ::= SEQUENCE {
    juniAaaSubscriberExtUserName             DisplayString,
    juniAaaSubscriberExtLoginTime            DisplayString,
    juniAaaSubscriberExtIpAddress            IpAddress,
    juniAaaSubscriberExtIpAddressMask        IpAddress,
    juniAaaSubscriberExtAddrAssignType       JuniAddressAssignType,
    juniAaaSubscriberExtState                JuniSubscriberState,
    juniAaaSubscriberExtClientType           JuniSubscriberClientType,
    juniAaaSubscriberExtAcctSessionId        DisplayString,
    juniAaaSubscriberExtClass                DisplayString,
    juniAaaSubscriberExtNasPort              Unsigned32,
    juniAaaSubscriberExtNasPortType          Unsigned32,
    juniAaaSubscriberExtCalledStationId      OCTET STRING,
    juniAaaSubscriberExtCallingStationId     OCTET STRING,
    juniAaaSubscriberExtL2tpTunnelId         Integer32
     }

juniAaaSubscriberExtUserName OBJECT-TYPE
    SYNTAX      DisplayString
    MAX-ACCESS  read-only
    STATUS      current
    DESCRIPTION
        "The user name associated with this subscriber."
    ::= { juniAaaSubscriberExtEntry 1 }

juniAaaSubscriberExtLoginTime OBJECT-TYPE
    SYNTAX      DisplayString
    MAX-ACCESS  read-only
    STATUS      current
    DESCRIPTION
        "The time this subscriber logged in using AAA protocol."
    ::= { juniAaaSubscriberExtEntry 2 }

juniAaaSubscriberExtIpAddress OBJECT-TYPE
    SYNTAX      IpAddress
    MAX-ACCESS  read-only
    STATUS      current
    DESCRIPTION
        "The client IP Address assigned to this subscriber."
    ::= { juniAaaSubscriberExtEntry 3 }

juniAaaSubscriberExtIpAddressMask OBJECT-TYPE
    SYNTAX      IpAddress
    MAX-ACCESS  read-only
    STATUS      current
    DESCRIPTION
        "The client IP Address Mask assigned to this subscriber."
    ::= { juniAaaSubscriberExtEntry 4 }

juniAaaSubscriberExtAddrAssignType OBJECT-TYPE
    SYNTAX      JuniAddressAssignType
    MAX-ACCESS  read-only
    STATUS      current
    DESCRIPTION
        "The address assignment type for this subscriber."
    ::= { juniAaaSubscriberExtEntry 5 }

juniAaaSubscriberExtState OBJECT-TYPE
    SYNTAX      JuniSubscriberState
    MAX-ACCESS  read-only
    STATUS      current
    DESCRIPTION
        "The state of this subscriber."
    ::= { juniAaaSubscriberExtEntry 6 }

juniAaaSubscriberExtClientType OBJECT-TYPE
    SYNTAX      JuniSubscriberClientType
    MAX-ACCESS  read-only
    STATUS      current
    DESCRIPTION
        "The client type for this subscriber.  Certain client types (e.g.,
        'other') might be suppressed from representation in this table."
    ::= { juniAaaSubscriberExtEntry 7 }

juniAaaSubscriberExtAcctSessionId  OBJECT-TYPE
    SYNTAX      DisplayString
    MAX-ACCESS  read-only
    STATUS      current
    DESCRIPTION
        "Account session ID associated with this subscriber. The value
        and encoding of this attribute depends on the way AAA protocol is
        configured. For example it is attribute 44 for RADIUS."
    ::= { juniAaaSubscriberExtEntry 8 }

juniAaaSubscriberExtClass OBJECT-TYPE
    SYNTAX      DisplayString
    MAX-ACCESS  read-only
    STATUS      current
    DESCRIPTION
        "Classification attribute associated with this subscriber. The value
        and encoding of this attribute depends on the way AAA protocol is
        configured. For example it is attribute 25 for RADIUS."
    ::= { juniAaaSubscriberExtEntry 9 }

juniAaaSubscriberExtNasPort OBJECT-TYPE
    SYNTAX      Unsigned32
    MAX-ACCESS  read-only
    STATUS      current
    DESCRIPTION
        "Associated NAS port with this subscriber. The value and encoding of
        this attribute depends on the way AAA protocol is configured. For
        example it is attribute 5 for RADIUS."
    ::= { juniAaaSubscriberExtEntry 10 }

juniAaaSubscriberExtNasPortType OBJECT-TYPE
    SYNTAX      Unsigned32
    MAX-ACCESS  read-only
    STATUS      current
    DESCRIPTION
        "Associated NAS port type attribute associated with this subscriber.
        The value and encoding of this attribute depends on the way AAA protocol
        is configured. For example it is attribute 61 for RADIUS."
    ::= { juniAaaSubscriberExtEntry 11 }

juniAaaSubscriberExtCalledStationId OBJECT-TYPE
    SYNTAX      OCTET STRING (SIZE(0..255))
    MAX-ACCESS  read-only
    STATUS      current
    DESCRIPTION
        "Called ID associated with this subscriber. The value and encoding of
        this attribute depends on the way AAA protocol is configured. For
        example it is attribute 30 for RADIUS."
    ::= { juniAaaSubscriberExtEntry 12 }

juniAaaSubscriberExtCallingStationId OBJECT-TYPE
    SYNTAX      OCTET STRING (SIZE(0..255))
    MAX-ACCESS  read-only
    STATUS      current
    DESCRIPTION
        "Calling ID associated with this subscriber. The value and
        encoding of this attribute depends on the way AAA protocol
        is configured. For example it is attribute 31 for RADIUS."
    ::= { juniAaaSubscriberExtEntry 13 }

juniAaaSubscriberExtL2tpTunnelId OBJECT-TYPE
    SYNTAX      Integer32 (0..65535)
    MAX-ACCESS  read-only
    STATUS      current
    DESCRIPTION
        "L2TP Tunnel ID associated with this subscriber of concerned LNS.
        A value 0 for this attribute indicates the terminated subscriber."
    ::= { juniAaaSubscriberExtEntry 14 }


-- +++++++++++++++++++++++++++++++++++++++++++++++++++++++++++++++++++++++++++++
-- Managed objects for AAA Capabilities
-- +++++++++++++++++++++++++++++++++++++++++++++++++++++++++++++++++++++++++++++
juniAaaAccountingCapability OBJECT-TYPE
    SYNTAX      TruthValue
    MAX-ACCESS  read-only
    STATUS      current
    DESCRIPTION
        "Indicates whether this system supports AAA Accounting.  The value
        true(1) indicate that it does, false(2) indicates that it does not."
    ::= { juniAaaCapabilities 1 }

juniAaaAddressAssignmentCapability OBJECT-TYPE
    SYNTAX      TruthValue
    MAX-ACCESS  read-only
    STATUS      current
    DESCRIPTION
        "Indicates whether this system supports AAA address assignment.  The
        value true(1) indicates that it does, false(2) indicates that it does
        not."
    ::= { juniAaaCapabilities 2 }

juniAaaBrasCapability OBJECT-TYPE
    SYNTAX      TruthValue
    MAX-ACCESS  read-only
    STATUS      current
    DESCRIPTION
        "Indicates whether this system supports AAA BRAS functionality.  The
        value true(1) indicates that it does, false(2) indicates that it does
        not."
    ::= { juniAaaCapabilities 3 }

juniAaaTunnelingCapability OBJECT-TYPE
    SYNTAX      TruthValue
    MAX-ACCESS  read-only
    STATUS      current
    DESCRIPTION
        "Indicates whether this system supports AAA tunneling.  The value
        true(1) indicates that it does, false(2) indicates that it does not."
    ::= { juniAaaCapabilities 4 }


-- +++++++++++++++++++++++++++++++++++++++++++++++++++++++++++++++++++++++++++++
-- Notifications
-- +++++++++++++++++++++++++++++++++++++++++++++++++++++++++++++++++++++++++++++
-- No notifications are defined in this MIB.  Placeholders follow.
-- juniAaaTrapControl      OBJECT IDENTIFIER ::= { juniAaaMIB 2 }
-- juniAaaTraps            OBJECT IDENTIFIER ::= { juniAaaMIB 3 }
-- juniAaaTrapPrefix       OBJECT IDENTIFIER ::= { juniAaaTraps 0 }


-- +++++++++++++++++++++++++++++++++++++++++++++++++++++++++++++++++++++++++++++
-- Conformance information
-- +++++++++++++++++++++++++++++++++++++++++++++++++++++++++++++++++++++++++++++
juniAaaMIBConformance    OBJECT IDENTIFIER ::= { juniAaaMIB 4 }
juniAaaMIBCompliances    OBJECT IDENTIFIER ::= { juniAaaMIBConformance 1 }
juniAaaMIBGroups         OBJECT IDENTIFIER ::= { juniAaaMIBConformance 2 }

--
-- compliance statements
--
juniAaaCompliance  MODULE-COMPLIANCE
    STATUS      obsolete
    DESCRIPTION
        "Obsolete compliance statement for systems supporting AAA.  This
        statement became obsolete when new objects were added."
    MODULE   -- this module
        MANDATORY-GROUPS {
            juniAaaGroup }
    ::= { juniAaaMIBCompliances 1 }                                -- JUNOSe 1.1

juniAaaCompliance2  MODULE-COMPLIANCE
    STATUS      obsolete
    DESCRIPTION
        "Obsolete compliance statement for systems supporting AAA.  This
        statement became obsolete when new objects were added and new groupings
        were defined."
    MODULE   -- this module
        MANDATORY-GROUPS {
            juniAaaGroup2 }
    ::= { juniAaaMIBCompliances 2 }                                -- JUNOSe 2.0

juniAaaCompliance3  MODULE-COMPLIANCE
    STATUS      obsolete
    DESCRIPTION
        "Obsolete compliance statement for systems supporting AAA.  This
        statement became obsolete when the juniAaaAssignDomainStripDomain object
        was added to the B-RAS group."
    MODULE   -- this module
        MANDATORY-GROUPS {
            juniAaaBasicGroup }
        GROUP       juniAaaBrasGroup
            DESCRIPTION
                "This group is mandatory only for those entities that implement
                the AAA B-RAS functionality."
        GROUP       juniAaaTunnelGroup
            DESCRIPTION
                "This group is mandatory only for those entities that implement
                the AAA tunneling functionality."
        GROUP       juniAaaAuthenticationGroup
            DESCRIPTION
                "This group is mandatory only for those entities that implement
                the AAA authentication functionality."
        GROUP       juniAaaAccountingGroup
            DESCRIPTION
                "This group is mandatory only for those entities that implement
                the AAA accounting functionality."
        GROUP       juniAaaAddressGroup
            DESCRIPTION
                "This group is mandatory only for those entities that implement
                the AAA address assignment functionality."
    ::= { juniAaaMIBCompliances 3 }                                -- JUNOSe 3.0

juniAaaCompliance4  MODULE-COMPLIANCE
    STATUS      obsolete
    DESCRIPTION
        "Obsolete compliance statement for systems supporting AAA.  This
        statement became obsolete when new assignment delimiter objects were
        added to the B-RAS group."
    MODULE   -- this module
        MANDATORY-GROUPS {
            juniAaaBasicGroup }
        GROUP       juniAaaBrasGroup2
            DESCRIPTION
                "This group is mandatory only for those entities that implement
                the AAA B-RAS functionality."
        GROUP       juniAaaTunnelGroup
            DESCRIPTION
                "This group is mandatory only for those entities that implement
                the AAA tunneling functionality."
        GROUP       juniAaaAuthenticationGroup
            DESCRIPTION
                "This group is mandatory only for those entities that implement
                the AAA authentication functionality."
        GROUP       juniAaaAccountingGroup
            DESCRIPTION
                "This group is mandatory only for those entities that implement
                the AAA accounting functionality."
        GROUP       juniAaaAddressGroup
            DESCRIPTION
                "This group is mandatory only for those entities that implement
                the AAA address assignment functionality."
    ::= { juniAaaMIBCompliances 4 }                                -- JUNOSe 3.1

juniAaaCompliance5  MODULE-COMPLIANCE
    STATUS      obsolete
    DESCRIPTION
        "Obsolete compliance statement for systems supporting AAA.  This
        statement became obsolete when the subscriber and capabilities groups
        were added."
    MODULE   -- this module
        MANDATORY-GROUPS {
            juniAaaBasicGroup }
        GROUP       juniAaaBrasGroup3
            DESCRIPTION
                "This group is mandatory only for those entities that implement
                the AAA B-RAS functionality."
        GROUP       juniAaaTunnelGroup
            DESCRIPTION
                "This group is mandatory only for those entities that implement
                the AAA tunneling functionality."
        GROUP       juniAaaAuthenticationGroup
            DESCRIPTION
                "This group is mandatory only for those entities that implement
                the AAA authentication functionality."
        GROUP       juniAaaAccountingGroup
            DESCRIPTION
                "This group is mandatory only for those entities that implement
                the AAA accounting functionality."
        GROUP       juniAaaAddressGroup
            DESCRIPTION
                "This group is mandatory only for those entities that implement
                the AAA address assignment functionality."
    ::= { juniAaaMIBCompliances 5 }                                -- JUNOSe 3.2

juniAaaCompliance6  MODULE-COMPLIANCE
    STATUS      obsolete
    DESCRIPTION
        "Obsolete compliance statement for systems supporting AAA.  This
        statement became obsolete when support was added for subscriber
        information by interface location."
    MODULE   -- this module
        MANDATORY-GROUPS {
            juniAaaBasicGroup,
            juniAaaCapabilitiesGroup }
        GROUP       juniAaaBrasGroup3
            DESCRIPTION
                "This group is mandatory only for those entities that implement
                the AAA B-RAS functionality."
        GROUP       juniAaaSubscriberGroup
            DESCRIPTION
                "This group is mandatory only for those entities that implement
                the AAA B-RAS functionality."
        GROUP       juniAaaTunnelGroup
            DESCRIPTION
                "This group is mandatory only for those entities that implement
                the AAA tunneling functionality."
        GROUP       juniAaaAuthenticationGroup
            DESCRIPTION
                "This group is mandatory only for those entities that implement
                the AAA authentication functionality."
        GROUP       juniAaaAccountingGroup
            DESCRIPTION
                "This group is mandatory only for those entities that implement
                the AAA accounting functionality."
        GROUP       juniAaaAddressGroup
            DESCRIPTION
                "This group is mandatory only for those entities that implement
                the AAA address assignment functionality."
    ::= { juniAaaMIBCompliances 6 }                                -- JUNOSe 3.3

juniAaaCompliance7  MODULE-COMPLIANCE
    STATUS      obsolete
    DESCRIPTION
        "Obsolete compliance statement for systems supporting AAA.  This
        statement became obsolete when several new objects were added."
    MODULE   -- this module
        MANDATORY-GROUPS {
            juniAaaBasicGroup,
            juniAaaCapabilitiesGroup }
        GROUP       juniAaaBrasGroup3
            DESCRIPTION
                "This group is mandatory only for those entities that implement
                the AAA B-RAS functionality."
        GROUP       juniAaaSubscriberGroup2
            DESCRIPTION
                "This group is mandatory only for those entities that implement
                the AAA B-RAS functionality."
        GROUP       juniAaaTunnelGroup
            DESCRIPTION
                "This group is mandatory only for those entities that implement
                the AAA tunneling functionality."
        GROUP       juniAaaAuthenticationGroup
            DESCRIPTION
                "This group is mandatory only for those entities that implement
                the AAA authentication functionality."
        GROUP       juniAaaAccountingGroup
            DESCRIPTION
                "This group is mandatory only for those entities that implement
                the AAA accounting functionality."
        GROUP       juniAaaAddressGroup
            DESCRIPTION
                "This group is mandatory only for those entities that implement
                the AAA address assignment functionality."
    ::= { juniAaaMIBCompliances 7 }                                -- JUNOSe 3.4

juniAaaCompliance8  MODULE-COMPLIANCE
    STATUS      obsolete
    DESCRIPTION
        "Obsolete compliance statement for systems supporting AAA.  This
        statement became obsolete when new objects were added to the B-RAS and
        tunnel groups."
    MODULE   -- this module
        MANDATORY-GROUPS {
            juniAaaBasicGroup,
            juniAaaCapabilitiesGroup }
        GROUP       juniAaaBrasGroup4
            DESCRIPTION
                "This group is mandatory only for those entities that implement
                the AAA B-RAS functionality."
        GROUP       juniAaaSubscriberGroup3
            DESCRIPTION
                "This group is mandatory only for those entities that implement
                the AAA B-RAS functionality."
        GROUP       juniAaaTunnelGroup
            DESCRIPTION
                "This group is mandatory only for those entities that implement
                the AAA tunneling functionality."
        GROUP       juniAaaAuthenticationGroup
            DESCRIPTION
                "This group is mandatory only for those entities that implement
                the AAA authentication functionality."
        GROUP       juniAaaAccountingGroup2
            DESCRIPTION
                "This group is mandatory only for those entities that implement
                the AAA accounting functionality."
        GROUP       juniAaaAddressGroup
            DESCRIPTION
                "This group is mandatory only for those entities that implement
                the AAA address assignment functionality."
    ::= { juniAaaMIBCompliances 8 }                                -- JUNOSe 4.0

juniAaaCompliance9  MODULE-COMPLIANCE
    STATUS      obsolete
    DESCRIPTION
        "Obsolete compliance statement for systems supporting AAA.  This
        statement became obsolete when new objects were added to the B-RAS
        group."
    MODULE   -- this module
        MANDATORY-GROUPS {
            juniAaaBasicGroup,
            juniAaaCapabilitiesGroup }
        GROUP       juniAaaBrasGroup5
            DESCRIPTION
                "This group is mandatory only for those entities that implement
                the AAA B-RAS functionality."
        GROUP       juniAaaSubscriberGroup3
            DESCRIPTION
                "This group is mandatory only for those entities that implement
                the AAA B-RAS functionality."
        GROUP       juniAaaTunnelGroup2
            DESCRIPTION
                "This group is mandatory only for those entities that implement
                the AAA tunneling functionality."
        GROUP       juniAaaAuthenticationGroup
            DESCRIPTION
                "This group is mandatory only for those entities that implement
                the AAA authentication functionality."
        GROUP       juniAaaAccountingGroup2
            DESCRIPTION
                "This group is mandatory only for those entities that implement
                the AAA accounting functionality."
        GROUP       juniAaaAddressGroup
            DESCRIPTION
                "This group is mandatory only for those entities that implement
                the AAA address assignment functionality."
    ::= { juniAaaMIBCompliances 9 }                                -- JUNOSe 4.1

juniAaaCompliance10  MODULE-COMPLIANCE
    STATUS      obsolete
    DESCRIPTION
        "Obsolete compliance statement for systems supporting AAA.  This
        statement became obsolete when new objects were added to the B-RAS,
        Subscriber and Address groups."
    MODULE   -- this module
        MANDATORY-GROUPS {
            juniAaaBasicGroup,
            juniAaaCapabilitiesGroup }
        GROUP       juniAaaBrasGroup6
            DESCRIPTION
                "This group is mandatory only for those entities that implement
                the AAA B-RAS functionality."
        GROUP       juniAaaSubscriberGroup3
            DESCRIPTION
                "This group is mandatory only for those entities that implement
                the AAA B-RAS functionality."
        GROUP       juniAaaTunnelGroup2
            DESCRIPTION
                "This group is mandatory only for those entities that implement
                the AAA tunneling functionality."
        GROUP       juniAaaAuthenticationGroup
            DESCRIPTION
                "This group is mandatory only for those entities that implement
                the AAA authentication functionality."
        GROUP       juniAaaAccountingGroup2
            DESCRIPTION
                "This group is mandatory only for those entities that implement
                the AAA accounting functionality."
        GROUP       juniAaaAddressGroup
            DESCRIPTION
                "This group is mandatory only for those entities that implement
                the AAA address assignment functionality."
    ::= { juniAaaMIBCompliances 10 }                               -- JUNOSe 5.0

juniAaaCompliance11  MODULE-COMPLIANCE
    STATUS      obsolete
    DESCRIPTION
        "Obsolete compliance statement for systems supporting AAA."
    MODULE   -- this module
        MANDATORY-GROUPS {
            juniAaaBasicGroup,
            juniAaaCapabilitiesGroup }
        GROUP       juniAaaBrasGroup7
            DESCRIPTION
                "This group is mandatory only for those entities that implement
                the AAA B-RAS functionality."
        GROUP       juniAaaSubscriberGroup4
            DESCRIPTION
                "This group is mandatory only for those entities that implement
                the AAA B-RAS functionality."
        GROUP       juniAaaTunnelGroup2
            DESCRIPTION
                "This group is mandatory only for those entities that implement
                the AAA tunneling functionality."
        GROUP       juniAaaAuthenticationGroup
            DESCRIPTION
                "This group is mandatory only for those entities that implement
                the AAA authentication functionality."
        GROUP       juniAaaAccountingGroup2
            DESCRIPTION
                "This group is mandatory only for those entities that implement
                the AAA accounting functionality."
        GROUP       juniAaaAddressGroup2
            DESCRIPTION
                "This group is mandatory only for those entities that implement
                the AAA address assignment functionality."
    ::= { juniAaaMIBCompliances 11 }                               -- JUNOSe 5.1


juniAaaCompliance12  MODULE-COMPLIANCE
    STATUS      obsolete
    DESCRIPTION
        "Obsolete compliance statement for systems supporting AAA."
    MODULE   -- this module
        MANDATORY-GROUPS {
            juniAaaBasicGroup,
            juniAaaCapabilitiesGroup }
        GROUP       juniAaaBrasGroup8
            DESCRIPTION
                "This group is mandatory only for those entities that implement
                the AAA B-RAS functionality."
        GROUP       juniAaaSubscriberGroup4
            DESCRIPTION
                "This group is mandatory only for those entities that implement
                the AAA B-RAS functionality."
        GROUP       juniAaaTunnelGroup2
            DESCRIPTION
                "This group is mandatory only for those entities that implement
                the AAA tunneling functionality."
        GROUP       juniAaaAuthenticationGroup2
            DESCRIPTION
                "This group is mandatory only for those entities that implement
                the AAA authentication functionality."
        GROUP       juniAaaAccountingGroup3
            DESCRIPTION
                "This group is mandatory only for those entities that implement
                the AAA accounting functionality."
        GROUP       juniAaaAddressGroup2
            DESCRIPTION
                "This group is mandatory only for those entities that implement
                the AAA address assignment functionality."
    ::= { juniAaaMIBCompliances 12 }                               -- JUNOSe 5.3


juniAaaCompliance13  MODULE-COMPLIANCE
    STATUS      obsolete
    DESCRIPTION
        "Obsolete compliance statement for systems supporting AAA."
    MODULE   -- this module
        MANDATORY-GROUPS {
            juniAaaBasicGroup,
            juniAaaCapabilitiesGroup }
        GROUP       juniAaaBrasGroup9
            DESCRIPTION
                "This group is mandatory only for those entities that implement
                the AAA B-RAS functionality."
        GROUP       juniAaaSubscriberGroup4
            DESCRIPTION
                "This group is mandatory only for those entities that implement
                the AAA B-RAS functionality."
        GROUP       juniAaaTunnelGroup3
            DESCRIPTION
                "This group is mandatory only for those entities that implement
                the AAA tunneling functionality."
        GROUP       juniAaaAuthenticationGroup2
            DESCRIPTION
                "This group is mandatory only for those entities that implement
                the AAA authentication functionality."
        GROUP       juniAaaAccountingGroup3
            DESCRIPTION
                "This group is mandatory only for those entities that implement
                the AAA accounting functionality."
        GROUP       juniAaaAddressGroup2
            DESCRIPTION
                "This group is mandatory only for those entities that implement
                the AAA address assignment functionality."
    ::= { juniAaaMIBCompliances 13 }                               -- JUNOSe 6.0

juniAaaCompliance14  MODULE-COMPLIANCE
    STATUS      obsolete
    DESCRIPTION
        "The compliance statement for systems supporting AAA."
    MODULE   -- this module
        MANDATORY-GROUPS {
            juniAaaBasicGroup,
            juniAaaCapabilitiesGroup }
        GROUP       juniAaaBrasGroup9
            DESCRIPTION
                "This group is mandatory only for those entities that implement
                the AAA B-RAS functionality."
        GROUP       juniAaaSubscriberGroup4
            DESCRIPTION
                "This group is mandatory only for those entities that implement
                the AAA B-RAS functionality."
        GROUP       juniAaaTunnelGroup3
            DESCRIPTION
                "This group is mandatory only for those entities that implement
                the AAA tunneling functionality."
        GROUP       juniAaaAuthenticationGroup3
            DESCRIPTION
                "This group is mandatory only for those entities that implement
                the AAA authentication functionality."
        GROUP       juniAaaAccountingGroup4
            DESCRIPTION
                "This group is mandatory only for those entities that implement
                the AAA accounting functionality."
        GROUP       juniAaaAddressGroup2
            DESCRIPTION
                "This group is mandatory only for those entities that implement
                the AAA address assignment functionality."
    ::= { juniAaaMIBCompliances 14 }                               -- JUNOSe 6.1

juniAaaCompliance15  MODULE-COMPLIANCE
    STATUS      obsolete
    DESCRIPTION
        "Obsolete compliance statement for systems supporting AAA."
    MODULE   -- this module
        MANDATORY-GROUPS {
            juniAaaBasicGroup,
            juniAaaCapabilitiesGroup }
        GROUP       juniAaaBrasGroup9
            DESCRIPTION
                "This group is mandatory only for those entities that implement
                the AAA B-RAS functionality."
        GROUP       juniAaaSubscriberGroup4
            DESCRIPTION
                "This group is mandatory only for those entities that implement
                the AAA B-RAS functionality."
        GROUP       juniAaaTunnelGroup4
            DESCRIPTION
                "This group is mandatory only for those entities that implement
                the AAA tunneling functionality."
        GROUP       juniAaaAuthenticationGroup3
            DESCRIPTION
                "This group is mandatory only for those entities that implement
                the AAA authentication functionality."
        GROUP       juniAaaAccountingGroup4
            DESCRIPTION
                "This group is mandatory only for those entities that implement
                the AAA accounting functionality."
        GROUP       juniAaaAddressGroup2
            DESCRIPTION
                "This group is mandatory only for those entities that implement
                the AAA address assignment functionality."
    ::= { juniAaaMIBCompliances 15 }                               -- JUNOSe 7.0

juniAaaCompliance16  MODULE-COMPLIANCE
    STATUS      obsolete
    DESCRIPTION
        "Obsolete compliance statement for systems supporting AAA."
    MODULE   -- this module
        MANDATORY-GROUPS {
            juniAaaBasicGroup,
            juniAaaCapabilitiesGroup }
        GROUP       juniAaaBrasGroup9
            DESCRIPTION
                "This group is mandatory only for those entities that implement
                the AAA B-RAS functionality."
        GROUP       juniAaaSubscriberGroup5
            DESCRIPTION
                "This group is mandatory only for those entities that implement
                the AAA B-RAS functionality."
        GROUP       juniAaaTunnelGroup4
            DESCRIPTION
                "This group is mandatory only for those entities that implement
                the AAA tunneling functionality."
        GROUP       juniAaaAuthenticationGroup3
            DESCRIPTION
                "This group is mandatory only for those entities that implement
                the AAA authentication functionality."
        GROUP       juniAaaAccountingGroup4
            DESCRIPTION
                "This group is mandatory only for those entities that implement
                the AAA accounting functionality."
        GROUP       juniAaaAddressGroup2
            DESCRIPTION
                "This group is mandatory only for those entities that implement
                the AAA address assignment functionality."
    ::= { juniAaaMIBCompliances 16 }                              -- JUNOSe 7.1

juniAaaCompliance17  MODULE-COMPLIANCE
    STATUS      obsolete
    DESCRIPTION
        "Obsolete compliance statement for systems supporting AAA."
    MODULE   -- this module
        MANDATORY-GROUPS {
            juniAaaBasicGroup,
            juniAaaCapabilitiesGroup }
        GROUP       juniAaaBrasGroup10
            DESCRIPTION
                "This group is mandatory only for those entities that implement
                the AAA B-RAS functionality."
        GROUP       juniAaaSubscriberGroup5
            DESCRIPTION
                "This group is mandatory only for those entities that implement
                the AAA B-RAS functionality."
        GROUP       juniAaaTunnelGroup4
            DESCRIPTION
                "This group is mandatory only for those entities that implement
                the AAA tunneling functionality."
        GROUP       juniAaaAuthenticationGroup3
            DESCRIPTION
                "This group is mandatory only for those entities that implement
                the AAA authentication functionality."
        GROUP       juniAaaAccountingGroup4
            DESCRIPTION
                "This group is mandatory only for those entities that implement
                the AAA accounting functionality."
        GROUP       juniAaaAddressGroup2
            DESCRIPTION
                "This group is mandatory only for those entities that implement
                the AAA address assignment functionality."
    ::= { juniAaaMIBCompliances 17 }                              -- JUNOSe 7.1

juniAaaCompliance18  MODULE-COMPLIANCE
    STATUS      obsolete
    DESCRIPTION
        "Obsolete compliance statement for systems supporting AAA."
    MODULE   -- this module
        MANDATORY-GROUPS {
            juniAaaBasicGroup,
            juniAaaCapabilitiesGroup }
        GROUP       juniAaaBrasGroup10
            DESCRIPTION
                "This group is mandatory only for those entities that implement
                the AAA B-RAS functionality."
        GROUP       juniAaaSubscriberGroup5
            DESCRIPTION
                "This group is mandatory only for those entities that implement
                the AAA B-RAS functionality."
        GROUP       juniAaaTunnelGroup5
            DESCRIPTION
                "This group is mandatory only for those entities that implement
                the AAA tunneling functionality."
        GROUP       juniAaaAuthenticationGroup3
            DESCRIPTION
                "This group is mandatory only for those entities that implement
                the AAA authentication functionality."
        GROUP       juniAaaAccountingGroup4
            DESCRIPTION
                "This group is mandatory only for those entities that implement
                the AAA accounting functionality."
        GROUP       juniAaaAddressGroup2
            DESCRIPTION
                "This group is mandatory only for those entities that implement
                the AAA address assignment functionality."
    ::= { juniAaaMIBCompliances 18 }                              -- JUNOSe 7.3

juniAaaCompliance19  MODULE-COMPLIANCE
    STATUS      obsolete
    DESCRIPTION
        "Obsolete compliance statement for systems supporting AAA."
    MODULE   -- this module
        MANDATORY-GROUPS {
            juniAaaBasicGroup,
            juniAaaCapabilitiesGroup }
        GROUP       juniAaaBrasGroup11
            DESCRIPTION
                "This group is mandatory only for those entities that implement
                the AAA B-RAS functionality."
        GROUP       juniAaaSubscriberGroup5
            DESCRIPTION
                "This group is mandatory only for those entities that implement
                the AAA B-RAS functionality."
        GROUP       juniAaaTunnelGroup5
            DESCRIPTION
                "This group is mandatory only for those entities that implement
                the AAA tunneling functionality."
        GROUP       juniAaaAuthenticationGroup3
            DESCRIPTION
                "This group is mandatory only for those entities that implement
                the AAA authentication functionality."
        GROUP       juniAaaAccountingGroup4
            DESCRIPTION
                "This group is mandatory only for those entities that implement
                the AAA accounting functionality."
        GROUP       juniAaaAddressGroup2
            DESCRIPTION
                "This group is mandatory only for those entities that implement
                the AAA address assignment functionality."
    ::= { juniAaaMIBCompliances 19 }                              -- JUNOSe 8.1

juniAaaCompliance20 MODULE-COMPLIANCE
    STATUS      obsolete
    DESCRIPTION
        "Obsolete compliance statement for systems supporting AAA."
    MODULE   -- this module
        MANDATORY-GROUPS {
            juniAaaBasicGroup,
            juniAaaCapabilitiesGroup }
        GROUP       juniAaaBrasGroup11
            DESCRIPTION
                "This group is mandatory only for those entities that implement
                the AAA B-RAS functionality."
        GROUP       juniAaaSubscriberGroup5
            DESCRIPTION
                "This group is mandatory only for those entities that implement
                the AAA B-RAS functionality."
        GROUP       juniAaaTunnelGroup5
            DESCRIPTION
                "This group is mandatory only for those entities that implement
                the AAA tunneling functionality."
        GROUP       juniAaaAuthenticationGroup3
            DESCRIPTION
                "This group is mandatory only for those entities that implement
                the AAA authentication functionality."
        GROUP       juniAaaAccountingGroup5
            DESCRIPTION
                "This group is mandatory only for those entities that implement
                the AAA accounting functionality."
        GROUP       juniAaaAddressGroup2
            DESCRIPTION
                "This group is mandatory only for those entities that implement
                the AAA address assignment functionality."
    ::= { juniAaaMIBCompliances 20 }                              -- JUNOSe 8.1


juniAaaCompliance21 MODULE-COMPLIANCE
    STATUS      obsolete
    DESCRIPTION
        "Obsolete compliance statement for systems supporting AAA. This
        statement became obsolete when the juniAaaMonitorIngressTrafficOnly object
        was added to the B-RAS group."
    MODULE   -- this module
        MANDATORY-GROUPS {
            juniAaaBasicGroup,
            juniAaaCapabilitiesGroup }
        GROUP       juniAaaBrasGroup12
            DESCRIPTION
                "This group is mandatory only for those entities that implement
                the AAA B-RAS functionality."
        GROUP       juniAaaSubscriberGroup5
            DESCRIPTION
                "This group is mandatory only for those entities that implement
                the AAA B-RAS functionality."
        GROUP       juniAaaTunnelGroup5
            DESCRIPTION
                "This group is mandatory only for those entities that implement
                the AAA tunneling functionality."
        GROUP       juniAaaAuthenticationGroup3
            DESCRIPTION
                "This group is mandatory only for those entities that implement
                the AAA authentication functionality."
        GROUP       juniAaaAccountingGroup5
            DESCRIPTION
                "This group is mandatory only for those entities that implement
                the AAA accounting functionality."
        GROUP       juniAaaAddressGroup2
            DESCRIPTION
                "This group is mandatory only for those entities that implement
                the AAA address assignment functionality."
    ::= { juniAaaMIBCompliances 21 }                              -- JUNOSe 9.1


juniAaaCompliance22 MODULE-COMPLIANCE
    STATUS      obsolete
    DESCRIPTION
        "Obsolete compliance statement for systems supporting AAA. This
        statement became obsolete when the juniAaaAssignDomainBackupPoolName
        object was added to the B-RAS group."
    MODULE   -- this module
        MANDATORY-GROUPS {
            juniAaaBasicGroup,
            juniAaaCapabilitiesGroup }
        GROUP       juniAaaBrasGroup13
            DESCRIPTION
                "This group is mandatory only for those entities that implement
                the AAA B-RAS functionality."
        GROUP       juniAaaSubscriberGroup5
            DESCRIPTION
                "This group is mandatory only for those entities that implement
                the AAA B-RAS functionality."
        GROUP       juniAaaTunnelGroup5
            DESCRIPTION
                "This group is mandatory only for those entities that implement
                the AAA tunneling functionality."
        GROUP       juniAaaAuthenticationGroup3
            DESCRIPTION
                "This group is mandatory only for those entities that implement
                the AAA authentication functionality."
        GROUP       juniAaaAccountingGroup5
            DESCRIPTION
                "This group is mandatory only for those entities that implement
                the AAA accounting functionality."
        GROUP       juniAaaAddressGroup2
            DESCRIPTION
                "This group is mandatory only for those entities that implement
                the AAA address assignment functionality."
    ::= { juniAaaMIBCompliances 22 }                              -- JUNOSe 9.3

juniAaaCompliance23 MODULE-COMPLIANCE
    STATUS      obsolete
    DESCRIPTION
        "Obsolete compliance statement for systems supporting AAA. This
        statement became obsolete when juniAaaFramedIpv6PrefixAsIpv6NdRaPrefix
        and juniAaaDelegatedIpv6PrefixAsDhcpv6DelegatedPrefix objects were
        added to the B-RAS group."
    MODULE   -- this module
        MANDATORY-GROUPS {
            juniAaaBasicGroup,
            juniAaaCapabilitiesGroup }
        GROUP       juniAaaBrasGroup14
            DESCRIPTION
                "This group is mandatory only for those entities that implement
                the AAA B-RAS functionality."
        GROUP       juniAaaSubscriberGroup5
            DESCRIPTION
                "This group is mandatory only for those entities that implement
                the AAA B-RAS functionality."
        GROUP       juniAaaTunnelGroup5
            DESCRIPTION
                "This group is mandatory only for those entities that implement
                the AAA tunneling functionality."
        GROUP       juniAaaAuthenticationGroup3
            DESCRIPTION
                "This group is mandatory only for those entities that implement
                the AAA authentication functionality."
        GROUP       juniAaaAccountingGroup5
            DESCRIPTION
                "This group is mandatory only for those entities that implement
                the AAA accounting functionality."
        GROUP       juniAaaAddressGroup2
            DESCRIPTION
                "This group is mandatory only for those entities that implement
                the AAA address assignment functionality."
    ::= { juniAaaMIBCompliances 23 }                              -- JUNOSe 10.0

juniAaaCompliance24 MODULE-COMPLIANCE
    STATUS      current
    DESCRIPTION
        "The compliance statement for systems supporting AAA."
    MODULE   -- this module
        MANDATORY-GROUPS {
            juniAaaBasicGroup,
            juniAaaCapabilitiesGroup }
        GROUP       juniAaaBrasGroup15
            DESCRIPTION
                "This group is mandatory only for those entities that implement
                the AAA B-RAS functionality."
        GROUP       juniAaaSubscriberGroup5
            DESCRIPTION
                "This group is mandatory only for those entities that implement
                the AAA B-RAS functionality."
        GROUP       juniAaaTunnelGroup5
            DESCRIPTION
                "This group is mandatory only for those entities that implement
                the AAA tunneling functionality."
        GROUP       juniAaaAuthenticationGroup3
            DESCRIPTION
                "This group is mandatory only for those entities that implement
                the AAA authentication functionality."
        GROUP       juniAaaAccountingGroup5
            DESCRIPTION
                "This group is mandatory only for those entities that implement
                the AAA accounting functionality."
        GROUP       juniAaaAddressGroup2
            DESCRIPTION
                "This group is mandatory only for those entities that implement
                the AAA address assignment functionality."
    ::= { juniAaaMIBCompliances 24 }                              -- JUNOSe 10.1

--
-- units of conformance
--
juniAaaGroup OBJECT-GROUP
    OBJECTS {
        juniAaaAssignBrasLicense,
        juniAaaAssignBrasLicensedUsers,

        juniAaaAssignDomainName,
        juniAaaAssignDomainRowStatus,
        juniAaaAssignDomainRouterName,
        juniAaaAssignDomainLoopback,

        juniAaaAcctInterval,
        juniAaaAcctDupServerRouterName,

        juniAaaAddrPoolDefault,
        juniAaaAddrDnsPrimary,
        juniAaaAddrDnsSecondary,
        juniAaaAddrWinsPrimary,
        juniAaaAddrWinsSecondary }
    STATUS      obsolete
    DESCRIPTION
        "Obsolete collection of objects providing management of AAA
        functionality in a Juniper product.  This group became obsolete when new
        objects were added."
    ::= { juniAaaMIBGroups 1 }                                     -- JUNOSe 1.1

juniAaaGroup2 OBJECT-GROUP
    OBJECTS {
        juniAaaAssignBrasLicense,
        juniAaaAssignBrasLicensedUsers,
        juniAaaAssignDomainName,
        juniAaaAssignDomainRowStatus,
        juniAaaAssignDomainRouterName,
        juniAaaAssignDomainLoopback,
        juniAaaAssignDomainIpHint,
        juniAaaAssignDomainAtmServiceLevel,
        juniAaaAssignDomainAtmPcr,
        juniAaaAssignDomainAtmScr,
        juniAaaAssignDomainAtmMbs,
        juniAaaAssignDomainOverrideUserName,
        juniAaaAssignDomainOverridePassword,

        juniAaaAcctInterval,
        juniAaaAcctDupServerRouterName,

        juniAaaAddrPoolDefault,
        juniAaaAddrDnsPrimary,
        juniAaaAddrDnsSecondary,
        juniAaaAddrWinsPrimary,
        juniAaaAddrWinsSecondary,
        juniAaaIncomingInitiateRequests,
        juniAaaIncomingTerminateRequests,
        juniAaaOutgoingTunnelGrantResponses,
        juniAaaOutgoingGrantResponses,
        juniAaaOutgoingDenyResponses,
        juniAaaOutgoingErrorResponses,
        juniAaaOutgoingAuthRequests,
        juniAaaIncomingAuthResponses,
        juniAaaOutgoingReAuthRequests,
        juniAaaIncomingReAuthResponses,
        juniAaaOutgoingAcctRequests,
        juniAaaIncomingAcctResponses,
        juniAaaOutgoingDupAcctRequests,
        juniAaaIncomingDupAcctResponses,
        juniAaaOutgoingAddrRequests,
        juniAaaIncomingAddrResponses,

        juniAaaAssignDomainTunnelName,
        juniAaaAssignDomainTunnelTag,
        juniAaaAssignDomainTunnelPreference,
        juniAaaAssignDomainTunnelType,
        juniAaaAssignDomainTunnelMedium,
        juniAaaAssignDomainTunnelAddress,
        juniAaaAssignDomainTunnelPassword,
        juniAaaAssignDomainTunnelId,
        juniAaaAssignDomainTunnelHostName,
        juniAaaAssignDomainTunnelRowStatus }
    STATUS      obsolete
    DESCRIPTION
        "Obsolete collection of objects providing management of AAA
        functionality in a Juniper product.  This group became obsolete when
        new objects were added and new groupings were defined."
    ::= { juniAaaMIBGroups 2 }                                     -- JUNOSe 2.0

juniAaaBasicGroup OBJECT-GROUP
    OBJECTS {
        juniAaaIncomingInitiateRequests,
        juniAaaIncomingTerminateRequests,
        juniAaaOutgoingGrantResponses,
        juniAaaOutgoingDenyResponses,
        juniAaaOutgoingErrorResponses }
    STATUS      current
    DESCRIPTION
        "The basic collection of objects providing management of AAA
        functionality in a Juniper product."
    ::= { juniAaaMIBGroups 3 }                                     -- JUNOSe 3.0

juniAaaBrasGroup OBJECT-GROUP
    OBJECTS {
        juniAaaAssignBrasLicense,
        juniAaaAssignBrasLicensedUsers,
        juniAaaIdleTimeout,
        juniAaaSessionTimeout,

        juniAaaAssignDomainName,
        juniAaaAssignDomainRowStatus,
        juniAaaAssignDomainRouterName,
        juniAaaAssignDomainLoopback,
        juniAaaAssignDomainIpHint,
        juniAaaAssignDomainAtmServiceLevel,
        juniAaaAssignDomainAtmPcr,
        juniAaaAssignDomainAtmScr,
        juniAaaAssignDomainAtmMbs,
        juniAaaAssignDomainOverrideUserName,
        juniAaaAssignDomainOverridePassword }
    STATUS      obsolete
    DESCRIPTION
        "Obsolete collection of objects providing management of AAA B-RAS
        functionality in a Juniper product.  This group became obsolete when the
        juniAaaAssignDomainStripDomain object was added."
    ::= { juniAaaMIBGroups 4 }                                     -- JUNOSe 3.0

juniAaaTunnelGroup OBJECT-GROUP
    OBJECTS {
        juniAaaAssignDomainTunnelName,
        juniAaaAssignDomainTunnelTag,
        juniAaaAssignDomainTunnelPreference,
        juniAaaAssignDomainTunnelType,
        juniAaaAssignDomainTunnelMedium,
        juniAaaAssignDomainTunnelAddress,
        juniAaaAssignDomainTunnelPassword,
        juniAaaAssignDomainTunnelId,
        juniAaaAssignDomainTunnelHostName,
        juniAaaAssignDomainTunnelServerName,
        juniAaaAssignDomainTunnelClientAddress,
        juniAaaAssignDomainTunnelRowStatus,

        juniAaaOutgoingTunnelGrantResponses }
    STATUS      obsolete
    DESCRIPTION
        "Obsolete collection of objects providing management of AAA tunneling
        functionality in a Juniper product.  This group became obsolete when the
        maximum sessions object was added."
    ::= { juniAaaMIBGroups 5 }                                     -- JUNOSe 3.0

juniAaaAuthenticationGroup OBJECT-GROUP
    OBJECTS {
        juniAaaAuthMethods,

        juniAaaOutgoingAuthRequests,
        juniAaaIncomingAuthResponses,
        juniAaaOutgoingReAuthRequests,
        juniAaaIncomingReAuthResponses }
    STATUS      obsolete
    DESCRIPTION
        "Obsolete collection of objects providing management of AAA authentication
        functionality in a Juniper product.  This group became obsolete when the
        authentication methods table was added."
    ::= { juniAaaMIBGroups 6 }                                     -- JUNOSe 3.0

juniAaaAccountingGroup OBJECT-GROUP
    OBJECTS {
        juniAaaAcctInterval,
        juniAaaAcctDupServerRouterName,
        juniAaaAcctMethods,

        juniAaaOutgoingAcctRequests,
        juniAaaIncomingAcctResponses,
        juniAaaOutgoingDupAcctRequests,
        juniAaaIncomingDupAcctResponses }
    STATUS      obsolete
    DESCRIPTION
        "Obsolete collection of objects providing management of AAA accounting
        functionality in a Juniper product.  This group became obsolete when the
        juniAaaAcctSendStopOnAaaDeny object was added."
    ::= { juniAaaMIBGroups 7 }                                     -- JUNOSe 3.0

juniAaaAddressGroup OBJECT-GROUP
    OBJECTS {
        juniAaaAddrPoolDefault,
        juniAaaDupAddrCheck,
        juniAaaAddrDnsPrimary,
        juniAaaAddrDnsSecondary,
        juniAaaAddrWinsPrimary,
        juniAaaAddrWinsSecondary,

        juniAaaOutgoingAddrRequests,
        juniAaaIncomingAddrResponses }
    STATUS      obsolete
    DESCRIPTION
        "Obsolete collection of objects providing management of AAA address
        assignment functionality in a Juniper product.  This group became
        obsolete when IPv6 support was added."
    ::= { juniAaaMIBGroups 8 }                                     -- JUNOSe 3.0

juniAaaBrasGroup2 OBJECT-GROUP
    OBJECTS {
        juniAaaAssignBrasLicense,
        juniAaaAssignBrasLicensedUsers,
        juniAaaIdleTimeout,
        juniAaaSessionTimeout,

        juniAaaAssignDomainName,
        juniAaaAssignDomainRowStatus,
        juniAaaAssignDomainRouterName,
        juniAaaAssignDomainLoopback,
        juniAaaAssignDomainIpHint,
        juniAaaAssignDomainAtmServiceLevel,
        juniAaaAssignDomainAtmPcr,
        juniAaaAssignDomainAtmScr,
        juniAaaAssignDomainAtmMbs,
        juniAaaAssignDomainOverrideUserName,
        juniAaaAssignDomainOverridePassword,
        juniAaaAssignDomainStripDomain }
    STATUS      obsolete
    DESCRIPTION
        "Obsolete collection of objects providing management of AAA B-RAS
        functionality in a Juniper product.  This group became obsolete when new
        assignment delimiter objects were added."
    ::= { juniAaaMIBGroups 9 }                                     -- JUNOSe 3.1

juniAaaBrasGroup3 OBJECT-GROUP
    OBJECTS {
        juniAaaAssignBrasLicense,
        juniAaaAssignBrasLicensedUsers,
        juniAaaAssignDomainDelimiters,
        juniAaaAssignRealmDelimiters,
        juniAaaAssignDomainParseOrder,

        juniAaaIdleTimeout,
        juniAaaSessionTimeout,

        juniAaaTunnelClientName,
        juniAaaTunnelPassword,
        juniAaaTunnelNasPortMethod,

        juniAaaAssignDomainName,
        juniAaaAssignDomainRowStatus,
        juniAaaAssignDomainRouterName,
        juniAaaAssignDomainLoopback,
        juniAaaAssignDomainIpHint,
        juniAaaAssignDomainAtmServiceLevel,
        juniAaaAssignDomainAtmPcr,
        juniAaaAssignDomainAtmScr,
        juniAaaAssignDomainAtmMbs,
        juniAaaAssignDomainOverrideUserName,
        juniAaaAssignDomainOverridePassword,
        juniAaaAssignDomainStripDomain }
    STATUS      obsolete
    DESCRIPTION
        "Obsolete collection of objects providing management of AAA B-RAS
        functionality in a Juniper product.  This group became obsolete when new
        objects were added."
    ::= { juniAaaMIBGroups 10 }                                    -- JUNOSe 3.2

juniAaaSubscriberGroup OBJECT-GROUP
    OBJECTS {
        juniAaaSubscriberMaxCount,
        juniAaaSubscriberPeakCount,
        juniAaaSubscriberCount,

        juniAaaSubscriberUserName,
        juniAaaSubscriberRouterName,
        juniAaaSubscriberRouterIndex,
        juniAaaSubscriberLoginTime,
        juniAaaSubscriberIpAddress,
        juniAaaSubscriberIpAddressMask,
        juniAaaSubscriberAddrAssignType,
        juniAaaSubscriberInterfaceId,
        juniAaaSubscriberState,
        juniAaaSubscriberClientType,
        juniAaaSubscriberIngressPolicyName,
        juniAaaSubscriberEgressPolicyName,
        juniAaaSubscriberQosProfileName,
        juniAaaSubscriberRowStatus,

        juniAaaSubscriberRouterSummaryCount,
        juniAaaSubscriberRouterRowStatus }
    STATUS      obsolete
    DESCRIPTION
        "Obsolete collection of objects providing management of AAA B-RAS
        Subscriber functionality in a Juniper product.  This group became
        obsolete when support was added for monitoring subscriber information by
        interface location."
    ::= { juniAaaMIBGroups 11 }                                    -- JUNOSe 3.3

juniAaaCapabilitiesGroup OBJECT-GROUP
    OBJECTS {
        juniAaaAccountingCapability,
        juniAaaAddressAssignmentCapability,
        juniAaaBrasCapability,
        juniAaaTunnelingCapability }
    STATUS      current
    DESCRIPTION
        "The collection of objects providing management of AAA Capabilities
        functionality in a Juniper product."
    ::= { juniAaaMIBGroups 12 }                                    -- JUNOSe 3.3

juniAaaSubscriberGroup2 OBJECT-GROUP
    OBJECTS {
        juniAaaSubscriberMaxCount,
        juniAaaSubscriberPeakCount,
        juniAaaSubscriberCount,

        juniAaaSubscriberUserName,
        juniAaaSubscriberRouterName,
        juniAaaSubscriberRouterIndex,
        juniAaaSubscriberLoginTime,
        juniAaaSubscriberIpAddress,
        juniAaaSubscriberIpAddressMask,
        juniAaaSubscriberAddrAssignType,
        juniAaaSubscriberInterfaceId,
        juniAaaSubscriberState,
        juniAaaSubscriberClientType,
        juniAaaSubscriberIngressPolicyName,
        juniAaaSubscriberEgressPolicyName,
        juniAaaSubscriberQosProfileName,
        juniAaaSubscriberRowStatus,

        juniAaaSubscriberRouterSummaryCount,
        juniAaaSubscriberRouterRowStatus,

        juniAaaSubscriberLocationType,
        juniAaaSubscriberLocationSummaryCount,
        juniAaaSubscriberLocationRowStatus }
    STATUS      obsolete
    DESCRIPTION
        "Obsolete collection of objects providing management of AAA B-RAS
        Subscriber functionality in a Juniper product.  This group became
        obsolete when the pseudo-subscriber meters were added."
    ::= { juniAaaMIBGroups 13 }                                    -- JUNOSe 3.4

juniAaaAccountingGroup2 OBJECT-GROUP
    OBJECTS {
        juniAaaAcctInterval,
        juniAaaAcctDupServerRouterName,
        juniAaaAcctMethods,
        juniAaaAcctSendStopOnAaaDeny,
        juniAaaAcctSendStopOnAaaReject,
        juniAaaOutgoingAcctRequests,
        juniAaaIncomingAcctResponses,
        juniAaaOutgoingDupAcctRequests,
        juniAaaIncomingDupAcctResponses }
    STATUS      obsolete
    DESCRIPTION
        "Obsolete collection of objects providing management of AAA accounting
        functionality in a Juniper product.  This group became obsolete when the
        accounting methods table was added."
    ::= { juniAaaMIBGroups 14 }                                    -- JUNOSe 4.0

juniAaaBrasGroup4 OBJECT-GROUP
    OBJECTS {
        juniAaaAssignBrasLicense,
        juniAaaAssignBrasLicensedUsers,
        juniAaaAssignDomainDelimiters,
        juniAaaAssignRealmDelimiters,
        juniAaaAssignDomainParseOrder,
        juniAaaAssignSubscriberLimit,

        juniAaaIdleTimeout,
        juniAaaSessionTimeout,

        juniAaaTunnelClientName,
        juniAaaTunnelPassword,
        juniAaaTunnelNasPortMethod,
        juniAaaTunnelIgnoreNasPort,
        juniAaaTunnelIgnoreNasPortType,
        juniAaaTunnelAssignmentIdFormat,

        juniAaaAssignDomainName,
        juniAaaAssignDomainRowStatus,
        juniAaaAssignDomainRouterName,
        juniAaaAssignDomainLoopback,
        juniAaaAssignDomainIpHint,
        juniAaaAssignDomainAtmServiceLevel,
        juniAaaAssignDomainAtmPcr,
        juniAaaAssignDomainAtmScr,
        juniAaaAssignDomainAtmMbs,
        juniAaaAssignDomainOverrideUserName,
        juniAaaAssignDomainOverridePassword,
        juniAaaAssignDomainStripDomain }
    STATUS      obsolete
    DESCRIPTION
        "Obsolete collection of objects providing management of AAA B-RAS
        functionality in a Juniper product.  This group became obsolete when
        assign domain pool name was added."
    ::= { juniAaaMIBGroups 15 }                                    -- JUNOSe 4.0

juniAaaSubscriberGroup3 OBJECT-GROUP
    OBJECTS {
        juniAaaSubscriberMaxCount,
        juniAaaSubscriberPeakCount,
        juniAaaSubscriberCount,

        juniAaaSubscriberUserName,
        juniAaaSubscriberRouterName,
        juniAaaSubscriberRouterIndex,
        juniAaaSubscriberLoginTime,
        juniAaaSubscriberIpAddress,
        juniAaaSubscriberIpAddressMask,
        juniAaaSubscriberAddrAssignType,
        juniAaaSubscriberInterfaceId,
        juniAaaSubscriberState,
        juniAaaSubscriberClientType,
        juniAaaSubscriberIngressPolicyName,
        juniAaaSubscriberEgressPolicyName,
        juniAaaSubscriberQosProfileName,
        juniAaaSubscriberRowStatus,

        juniAaaSubscriberRouterSummaryCount,
        juniAaaSubscriberRouterRowStatus,

        juniAaaSubscriberLocationType,
        juniAaaSubscriberLocationSummaryCount,
        juniAaaSubscriberLocationRowStatus,

        juniAaaSubscriberPseudoPeakCount,
        juniAaaSubscriberPseudoCount }
    STATUS      obsolete
    DESCRIPTION
        "Obsoleted collection of objects providing management of AAA B-RAS
        Subscriber functionality in a Juniper product.  This group became
        obsolete when IPv6 support was added."
    ::= { juniAaaMIBGroups 16 }                                    -- JUNOSe 4.0

juniAaaBrasGroup5 OBJECT-GROUP
    OBJECTS {
        juniAaaAssignBrasLicense,
        juniAaaAssignBrasLicensedUsers,
        juniAaaAssignDomainDelimiters,
        juniAaaAssignRealmDelimiters,
        juniAaaAssignDomainParseOrder,
        juniAaaAssignSubscriberLimit,

        juniAaaIdleTimeout,
        juniAaaSessionTimeout,

        juniAaaTunnelClientName,
        juniAaaTunnelPassword,
        juniAaaTunnelNasPortMethod,
        juniAaaTunnelIgnoreNasPort,
        juniAaaTunnelIgnoreNasPortType,
        juniAaaTunnelAssignmentIdFormat,

        juniAaaAssignDomainName,
        juniAaaAssignDomainRowStatus,
        juniAaaAssignDomainRouterName,
        juniAaaAssignDomainLoopback,
        juniAaaAssignDomainIpHint,
        juniAaaAssignDomainAtmServiceLevel,
        juniAaaAssignDomainAtmPcr,
        juniAaaAssignDomainAtmScr,
        juniAaaAssignDomainAtmMbs,
        juniAaaAssignDomainOverrideUserName,
        juniAaaAssignDomainOverridePassword,
        juniAaaAssignDomainStripDomain,
        juniAaaAssignDomainPoolName }
    STATUS      obsolete
    DESCRIPTION
        "Obsolete collection of objects providing management of AAA B-RAS
        functionality in a Juniper product.  This group became obsolete when
        PADN support was added."
    ::= { juniAaaMIBGroups 17 }                                    -- JUNOSe 4.1

juniAaaTunnelGroup2 OBJECT-GROUP
    OBJECTS {
        juniAaaAssignDomainTunnelName,
        juniAaaAssignDomainTunnelTag,
        juniAaaAssignDomainTunnelPreference,
        juniAaaAssignDomainTunnelType,
        juniAaaAssignDomainTunnelMedium,
        juniAaaAssignDomainTunnelAddress,
        juniAaaAssignDomainTunnelPassword,
        juniAaaAssignDomainTunnelId,
        juniAaaAssignDomainTunnelHostName,
        juniAaaAssignDomainTunnelServerName,
        juniAaaAssignDomainTunnelClientAddress,
        juniAaaAssignDomainTunnelMaxSessions,
        juniAaaAssignDomainTunnelRowStatus,

        juniAaaOutgoingTunnelGrantResponses }
    STATUS      obsolete
    DESCRIPTION
        "Obsolete collection of objects providing management of AAA tunneling
        functionality in a Juniper product."
    ::= { juniAaaMIBGroups 18 }                                    -- JUNOSe 4.1

juniAaaBrasGroup6 OBJECT-GROUP
    OBJECTS {
        juniAaaAssignBrasLicense,
        juniAaaAssignBrasLicensedUsers,
        juniAaaAssignDomainDelimiters,
        juniAaaAssignRealmDelimiters,
        juniAaaAssignDomainParseOrder,
        juniAaaAssignSubscriberLimit,

        juniAaaIdleTimeout,
        juniAaaSessionTimeout,

        juniAaaTunnelClientName,
        juniAaaTunnelPassword,
        juniAaaTunnelNasPortMethod,
        juniAaaTunnelIgnoreNasPort,
        juniAaaTunnelIgnoreNasPortType,
        juniAaaTunnelAssignmentIdFormat,

        juniAaaAssignDomainName,
        juniAaaAssignDomainRowStatus,
        juniAaaAssignDomainRouterName,
        juniAaaAssignDomainIpHint,
        juniAaaAssignDomainAtmServiceLevel,
        juniAaaAssignDomainAtmPcr,
        juniAaaAssignDomainAtmScr,
        juniAaaAssignDomainAtmMbs,
        juniAaaAssignDomainOverrideUserName,
        juniAaaAssignDomainOverridePassword,
        juniAaaAssignDomainStripDomain,
        juniAaaAssignDomainPoolName,
        juniAaaAssignDomainLocalInterface,

        juniAaaAssignDomainMaxPadnPerDomain,
        juniAaaAssignDomainPadnRowStatus,
        juniAaaAssignDomainPadnDistance }
    STATUS      obsolete
    DESCRIPTION
        "Obsolete collection of objects providing management of AAA B-RAS
        functionality in a Juniper product.  This group became obsolete when
        IPv6 support was added."
    ::= { juniAaaMIBGroups 19 }                                    -- JUNOSe 5.0

juniAaaBrasGroup7 OBJECT-GROUP
    OBJECTS {
        juniAaaAssignBrasLicense,
        juniAaaAssignBrasLicensedUsers,
        juniAaaAssignDomainDelimiters,
        juniAaaAssignRealmDelimiters,
        juniAaaAssignDomainParseOrder,
        juniAaaAssignSubscriberLimit,

        juniAaaIdleTimeout,
        juniAaaSessionTimeout,

        juniAaaTunnelClientName,
        juniAaaTunnelPassword,
        juniAaaTunnelNasPortMethod,
        juniAaaTunnelIgnoreNasPort,
        juniAaaTunnelIgnoreNasPortType,
        juniAaaTunnelAssignmentIdFormat,

        juniAaaAssignDomainName,
        juniAaaAssignDomainRowStatus,
        juniAaaAssignDomainRouterName,
        juniAaaAssignDomainIpHint,
        juniAaaAssignDomainAtmServiceLevel,
        juniAaaAssignDomainAtmPcr,
        juniAaaAssignDomainAtmScr,
        juniAaaAssignDomainAtmMbs,
        juniAaaAssignDomainOverrideUserName,
        juniAaaAssignDomainOverridePassword,
        juniAaaAssignDomainStripDomain,
        juniAaaAssignDomainPoolName,
        juniAaaAssignDomainLocalInterface,
        juniAaaAssignDomainIpv6RouterName,
        juniAaaAssignDomainIpv6LocalInterface,

        juniAaaAssignDomainMaxPadnPerDomain,
        juniAaaAssignDomainPadnRowStatus,
        juniAaaAssignDomainPadnDistance,
        juniAaaInterfaceIdFormat,

        juniAaaAssignTunnelCallingNumberFormat,
        juniAaaAssignDomainParseDirection,
        juniAaaAssignRealmParseDirection,
        juniAaaInterfaceAdapterFormat}
    STATUS      obsolete
    DESCRIPTION
        "Obsolete collection of objects providing management of AAA B-RAS
        functionality in a Juniper product."
    ::= { juniAaaMIBGroups 20 }                                    -- JUNOSe 5.1

juniAaaAddressGroup2 OBJECT-GROUP
    OBJECTS {
        juniAaaAddrPoolDefault,
        juniAaaDupAddrCheck,
        juniAaaAddrDnsPrimary,
        juniAaaAddrDnsSecondary,
        juniAaaAddrWinsPrimary,
        juniAaaAddrWinsSecondary,
        juniAaaAddrIpv6DnsPrimary,
        juniAaaAddrIpv6DnsSecondary,

        juniAaaOutgoingAddrRequests,
        juniAaaIncomingAddrResponses }
    STATUS      current
    DESCRIPTION
        "The collection of objects providing management of AAA address
        assignment functionality in a Juniper product."
    ::= { juniAaaMIBGroups 21 }                                    -- JUNOSe 5.1

juniAaaSubscriberGroup4 OBJECT-GROUP
    OBJECTS {
        juniAaaSubscriberMaxCount,
        juniAaaSubscriberPeakCount,
        juniAaaSubscriberCount,

        juniAaaSubscriberUserName,
        juniAaaSubscriberRouterName,
        juniAaaSubscriberRouterIndex,
        juniAaaSubscriberLoginTime,
        juniAaaSubscriberIpAddress,
        juniAaaSubscriberIpAddressMask,
        juniAaaSubscriberAddrAssignType,
        juniAaaSubscriberInterfaceId,
        juniAaaSubscriberState,
        juniAaaSubscriberClientType,
        juniAaaSubscriberIngressPolicyName,
        juniAaaSubscriberEgressPolicyName,
        juniAaaSubscriberQosProfileName,
        juniAaaSubscriberRowStatus,
        juniAaaSubscriberIpv6RouterIndex,
        juniAaaSubscriberIpv6AddrIfIdentifier,
        juniAaaSubscriberIpv6AddrPrefix,
        juniAaaSubscriberIpv6AddrPrefixSize,

        juniAaaSubscriberRouterSummaryCount,
        juniAaaSubscriberRouterRowStatus,

        juniAaaSubscriberLocationType,
        juniAaaSubscriberLocationSummaryCount,
        juniAaaSubscriberLocationRowStatus,

        juniAaaSubscriberPseudoPeakCount,
        juniAaaSubscriberPseudoCount }
    STATUS      obsolete
    DESCRIPTION
        "Obsolete collection of objects providing management of AAA B-RAS Subscriber
        functionality in a Juniper product."
    ::= { juniAaaMIBGroups 22 }                                    -- JUNOSe 5.1

juniAaaSubscriberGroup5 OBJECT-GROUP
    OBJECTS {
        juniAaaSubscriberMaxCount,
        juniAaaSubscriberPeakCount,
        juniAaaSubscriberCount,

        juniAaaSubscriberUserName,
        juniAaaSubscriberRouterName,
        juniAaaSubscriberRouterIndex,
        juniAaaSubscriberLoginTime,
        juniAaaSubscriberIpAddress,
        juniAaaSubscriberIpAddressMask,
        juniAaaSubscriberAddrAssignType,
        juniAaaSubscriberInterfaceId,
        juniAaaSubscriberState,
        juniAaaSubscriberClientType,
        juniAaaSubscriberIngressPolicyName,
        juniAaaSubscriberEgressPolicyName,
        juniAaaSubscriberQosProfileName,
        juniAaaSubscriberRowStatus,
        juniAaaSubscriberIpv6RouterIndex,
        juniAaaSubscriberIpv6AddrIfIdentifier,
        juniAaaSubscriberIpv6AddrPrefix,
        juniAaaSubscriberIpv6AddrPrefixSize,

        juniAaaSubscriberRouterSummaryCount,
        juniAaaSubscriberRouterRowStatus,

        juniAaaSubscriberLocationType,
        juniAaaSubscriberLocationSummaryCount,
        juniAaaSubscriberLocationRowStatus,

        juniAaaSubscriberPseudoPeakCount,
        juniAaaSubscriberPseudoCount,

        juniAaaSubscriberExtUserName,
        juniAaaSubscriberExtLoginTime,
        juniAaaSubscriberExtIpAddress,
        juniAaaSubscriberExtIpAddressMask,
        juniAaaSubscriberExtAddrAssignType,
        juniAaaSubscriberExtState,
        juniAaaSubscriberExtClientType,
        juniAaaSubscriberExtAcctSessionId,
        juniAaaSubscriberExtClass,
        juniAaaSubscriberExtNasPort,
        juniAaaSubscriberExtNasPortType,
        juniAaaSubscriberExtCalledStationId,
        juniAaaSubscriberExtCallingStationId,
        juniAaaSubscriberExtL2tpTunnelId }
    STATUS      current
    DESCRIPTION
        "The collection of objects providing management of AAA B-RAS Subscriber
        functionality in a Juniper product."
    ::= { juniAaaMIBGroups 31 }                                   -- JUNOSe 7.1

juniAaaBrasGroup8 OBJECT-GROUP
    OBJECTS {
        juniAaaAssignBrasLicense,
        juniAaaAssignBrasLicensedUsers,
        juniAaaAssignDomainDelimiters,
        juniAaaAssignRealmDelimiters,
        juniAaaAssignDomainParseOrder,
        juniAaaAssignSubscriberLimit,

        juniAaaIdleTimeout,
        juniAaaSessionTimeout,

        juniAaaTunnelClientName,
        juniAaaTunnelPassword,
        juniAaaTunnelNasPortMethod,
        juniAaaTunnelIgnoreNasPort,
        juniAaaTunnelIgnoreNasPortType,
        juniAaaTunnelAssignmentIdFormat,

        juniAaaAssignDomainName,
        juniAaaAssignDomainRowStatus,
        juniAaaAssignDomainRouterName,
        juniAaaAssignDomainIpHint,
        juniAaaAssignDomainAtmServiceLevel,
        juniAaaAssignDomainAtmPcr,
        juniAaaAssignDomainAtmScr,
        juniAaaAssignDomainAtmMbs,
        juniAaaAssignDomainOverrideUserName,
        juniAaaAssignDomainOverridePassword,
        juniAaaAssignDomainStripDomain,
        juniAaaAssignDomainPoolName,
        juniAaaAssignDomainLocalInterface,
        juniAaaAssignDomainIpv6RouterName,
        juniAaaAssignDomainIpv6LocalInterface,

        juniAaaAssignDomainMaxPadnPerDomain,
        juniAaaAssignDomainPadnRowStatus,
        juniAaaAssignDomainPadnDistance,
        juniAaaInterfaceIdFormat,
        juniAaaAssignTunnelCallingNumberFormat,
        juniAaaAssignDomainParseDirection,
        juniAaaAssignRealmParseDirection }
    STATUS      obsolete
    DESCRIPTION
        "Obsolete collection of objects providing management of AAA B-RAS
        functionality in a Juniper product."
    ::= { juniAaaMIBGroups 23 }                                    -- JUNOSe 5.3

juniAaaBrasGroup9 OBJECT-GROUP
    OBJECTS {
        juniAaaAssignBrasLicense,
        juniAaaAssignBrasLicensedUsers,
        juniAaaAssignDomainDelimiters,
        juniAaaAssignRealmDelimiters,
        juniAaaAssignDomainParseOrder,
        juniAaaAssignSubscriberLimit,

        juniAaaIdleTimeout,
        juniAaaSessionTimeout,

        juniAaaTunnelClientName,
        juniAaaTunnelPassword,
        juniAaaTunnelNasPortMethod,
        juniAaaTunnelIgnoreNasPort,
        juniAaaTunnelIgnoreNasPortType,
        juniAaaTunnelAssignmentIdFormat,

        juniAaaAssignDomainName,
        juniAaaAssignDomainRowStatus,
        juniAaaAssignDomainRouterName,
        juniAaaAssignDomainIpHint,
        juniAaaAssignDomainAtmServiceLevel,
        juniAaaAssignDomainAtmPcr,
        juniAaaAssignDomainAtmScr,
        juniAaaAssignDomainAtmMbs,
        juniAaaAssignDomainOverrideUserName,
        juniAaaAssignDomainOverridePassword,
        juniAaaAssignDomainStripDomain,
        juniAaaAssignDomainPoolName,
        juniAaaAssignDomainLocalInterface,
        juniAaaAssignDomainIpv6RouterName,
        juniAaaAssignDomainIpv6LocalInterface,

        juniAaaAssignDomainMaxPadnPerDomain,
        juniAaaAssignDomainPadnRowStatus,
        juniAaaAssignDomainPadnDistance,
        juniAaaInterfaceIdFormat,
        juniAaaAssignTunnelCallingNumberFormat,
        juniAaaAssignDomainParseDirection,
        juniAaaAssignRealmParseDirection,
        juniAaaInterfaceAdapterFormat}
    STATUS      obsolete
    DESCRIPTION
        "Obsolete  collection of objects providing management of AAA B-RAS
        functionality in a Juniper product."
    ::= { juniAaaMIBGroups 24 }                                    -- JUNOSe 6.0

juniAaaTunnelGroup3 OBJECT-GROUP
    OBJECTS {
        juniAaaAssignDomainTunnelName,
        juniAaaAssignDomainTunnelTag,
        juniAaaAssignDomainTunnelPreference,
        juniAaaAssignDomainTunnelType,
        juniAaaAssignDomainTunnelMedium,
        juniAaaAssignDomainTunnelAddress,
        juniAaaAssignDomainTunnelPassword,
        juniAaaAssignDomainTunnelId,
        juniAaaAssignDomainTunnelHostName,
        juniAaaAssignDomainTunnelServerName,
        juniAaaAssignDomainTunnelClientAddress,
        juniAaaAssignDomainTunnelMaxSessions,
        juniAaaAssignDomainTunnelReceiveWindowSize,
        juniAaaAssignDomainTunnelRowStatus,

        juniAaaOutgoingTunnelGrantResponses }
    STATUS      obsolete
    DESCRIPTION
        "Obsolete collection of objects providing management of AAA tunneling
        functionality in a Juniper product."
    ::= { juniAaaMIBGroups 25 }                                    -- JUNOSe 6.0

juniAaaAccountingGroup3 OBJECT-GROUP
    OBJECTS {
        juniAaaAcctInterval,
        juniAaaAcctDupServerRouterName,
        juniAaaAcctSendStopOnAaaDeny,
        juniAaaAcctSendStopOnAaaReject,
        juniAaaAcctSendImmediateAcctUpdate,
        juniAaaOutgoingAcctRequests,
        juniAaaIncomingAcctResponses,
        juniAaaOutgoingDupAcctRequests,
        juniAaaIncomingDupAcctResponses,
        juniAaaAcctMethodsSubscriberType,
        juniAaaAcctMethodsAccounting }
    STATUS      obsolete
    DESCRIPTION
        "Obsolete collection of objects providing management of AAA accounting
        functionality in a Juniper product."
    ::= { juniAaaMIBGroups 26 }                                    -- JUNOSe 5.3

juniAaaAuthenticationGroup2 OBJECT-GROUP
    OBJECTS {
        juniAaaOutgoingAuthRequests,
        juniAaaIncomingAuthResponses,
        juniAaaOutgoingReAuthRequests,
        juniAaaIncomingReAuthResponses,
        juniAaaAuthMethodsSubscriberType,
        juniAaaAuthMethodsAuthentication }
    STATUS      obsolete
    DESCRIPTION
        "Obsolete collection of objects providing management of AAA authentication
        functionality in a Juniper product."
    ::= { juniAaaMIBGroups 27 }                                     -- JUNOSe 5.3

juniAaaAuthenticationGroup3 OBJECT-GROUP
    OBJECTS {
        juniAaaOutgoingAuthRequests,
        juniAaaIncomingAuthResponses,
        juniAaaOutgoingReAuthRequests,
        juniAaaIncomingReAuthResponses,
        juniAaaAuthMethodsSubscriberType,
        juniAaaAuthMethodsAuthentication,
        juniAaaLocalAuthUserRowStatus,
        juniAaaLocalAuthUserPassword,
        juniAaaLocalAuthUserEncryption,
        juniAaaLocalAuthUserIpAddress,
        juniAaaLocalAuthUserIpAddressPool,
        juniAaaLocalAuthUserRouterName,
        juniAaaLocalAuthUserDbRowStatus,
        juniAaaLocalAuthUserDbAssocRowStatus,
        juniAaaLocalAuthUserDbAssocDbName }
    STATUS      current
    DESCRIPTION
        "The collection of objects providing management of AAA authentication
        functionality in a Juniper product."
    ::= { juniAaaMIBGroups 28 }                                     -- JUNOSe 6.1

juniAaaAccountingGroup4 OBJECT-GROUP
    OBJECTS {
        juniAaaAcctInterval,
        juniAaaAcctDupServerRouterName,
        juniAaaAcctBcastServerGroupName,
        juniAaaAcctBcastServerGroupRouter1,
        juniAaaAcctBcastServerGroupRouter2,
        juniAaaAcctBcastServerGroupRouter3,
        juniAaaAcctBcastServerGroupRouter4,
        juniAaaAcctBcastServerGroupRowStatus,
        juniAaaAcctSendStopOnAaaDeny,
        juniAaaAcctSendStopOnAaaReject,
        juniAaaAcctSendImmediateAcctUpdate,
        juniAaaOutgoingAcctRequests,
        juniAaaIncomingAcctResponses,
        juniAaaOutgoingDupAcctRequests,
        juniAaaIncomingDupAcctResponses,
        juniAaaAcctMethodsSubscriberType,
        juniAaaAcctMethodsAccounting,
        juniAaaOutgoingBcastAcctRequests,
        juniAaaIncomingBcastAcctResponses }
    STATUS      obsolete
    DESCRIPTION
        "The collection of objects providing management of AAA accounting
        functionality in a Juniper product."
    ::= { juniAaaMIBGroups 29 }                                     -- JUNOSe 6.1

juniAaaTunnelGroup4 OBJECT-GROUP
    OBJECTS {
        juniAaaAssignDomainTunnelName,
        juniAaaAssignDomainTunnelTag,
        juniAaaAssignDomainTunnelPreference,
        juniAaaAssignDomainTunnelType,
        juniAaaAssignDomainTunnelMedium,
        juniAaaAssignDomainTunnelAddress,
        juniAaaAssignDomainTunnelPassword,
        juniAaaAssignDomainTunnelId,
        juniAaaAssignDomainTunnelHostName,
        juniAaaAssignDomainTunnelServerName,
        juniAaaAssignDomainTunnelClientAddress,
        juniAaaAssignDomainTunnelMaxSessions,
        juniAaaAssignDomainTunnelReceiveWindowSize,
        juniAaaAssignDomainTunnelSwitchProfile,
        juniAaaAssignDomainTunnelRowStatus,

        juniAaaAssignDomainTunnelGroup,

        juniAaaTunnelGroupTunnelName,
        juniAaaTunnelGroupTunnelTag,
        juniAaaTunnelGroupTunnelPreference,
        juniAaaTunnelGroupTunnelType,
        juniAaaTunnelGroupTunnelMedium,
        juniAaaTunnelGroupTunnelAddress,
        juniAaaTunnelGroupTunnelPassword,
        juniAaaTunnelGroupTunnelId,
        juniAaaTunnelGroupTunnelHostName,
        juniAaaTunnelGroupTunnelRowStatus,
        juniAaaTunnelGroupTunnelServerName,
        juniAaaTunnelGroupTunnelClientAddress,
        juniAaaTunnelGroupTunnelMaxSessions,
        juniAaaTunnelGroupTunnelReceiveWindowSize,
        juniAaaTunnelGroupTunnelRouterName,
        juniAaaTunnelGroupTunnelSwitchProfile,

        juniAaaOutgoingTunnelGrantResponses }
    STATUS      obsolete
    DESCRIPTION
        "Obsolete collection of objects providing management of AAA tunneling
        functionality in a Juniper product."
    ::= { juniAaaMIBGroups 30 }                                    -- JUNOSe 7.0

juniAaaBrasGroup10 OBJECT-GROUP
    OBJECTS {
        juniAaaAssignBrasLicense,
        juniAaaAssignBrasLicensedUsers,
        juniAaaAssignDomainDelimiters,
        juniAaaAssignRealmDelimiters,
        juniAaaAssignDomainParseOrder,
        juniAaaAssignSubscriberLimit,

        juniAaaIdleTimeout,
        juniAaaSessionTimeout,

        juniAaaTunnelClientName,
        juniAaaTunnelPassword,
        juniAaaTunnelNasPortMethod,
        juniAaaTunnelIgnoreNasPort,
        juniAaaTunnelIgnoreNasPortType,
        juniAaaTunnelAssignmentIdFormat,

        juniAaaAssignDomainName,
        juniAaaAssignDomainRowStatus,
        juniAaaAssignDomainRouterName,
        juniAaaAssignDomainIpHint,
        juniAaaAssignDomainAtmServiceLevel,
        juniAaaAssignDomainAtmPcr,
        juniAaaAssignDomainAtmScr,
        juniAaaAssignDomainAtmMbs,
        juniAaaAssignDomainOverrideUserName,
        juniAaaAssignDomainOverridePassword,
        juniAaaAssignDomainStripDomain,
        juniAaaAssignDomainPoolName,
        juniAaaAssignDomainLocalInterface,
        juniAaaAssignDomainIpv6RouterName,
        juniAaaAssignDomainIpv6LocalInterface,
        juniAaaAssignDomainAuthRouterName,
        juniAaaAssignDomainIpRouterName,

        juniAaaAssignDomainMaxPadnPerDomain,
        juniAaaAssignDomainPadnRowStatus,
        juniAaaAssignDomainPadnDistance,
        juniAaaInterfaceIdFormat,
        juniAaaAssignTunnelCallingNumberFormat,
        juniAaaAssignDomainParseDirection,
        juniAaaAssignRealmParseDirection,
        juniAaaInterfaceAdapterFormat,
        juniAaaAssignAccountingStatisticsType,

        juniAaaAssignQosDownstreamRate }
    STATUS      obsolete
    DESCRIPTION
        "Obsolete  collection of objects providing management of AAA B-RAS
        functionality in a Juniper product."
    ::= { juniAaaMIBGroups 32 }                                    -- JUNOSe 7.3


juniAaaTunnelGroup5 OBJECT-GROUP
    OBJECTS {
        juniAaaAssignDomainTunnelName,
        juniAaaAssignDomainTunnelTag,
        juniAaaAssignDomainTunnelPreference,
        juniAaaAssignDomainTunnelType,
        juniAaaAssignDomainTunnelMedium,
        juniAaaAssignDomainTunnelAddress,
        juniAaaAssignDomainTunnelPassword,
        juniAaaAssignDomainTunnelId,
        juniAaaAssignDomainTunnelHostName,
        juniAaaAssignDomainTunnelServerName,
        juniAaaAssignDomainTunnelClientAddress,
        juniAaaAssignDomainTunnelMaxSessions,
        juniAaaAssignDomainTunnelReceiveWindowSize,
        juniAaaAssignDomainTunnelFailoverResync,
        juniAaaAssignDomainTunnelSwitchProfile,
        juniAaaAssignDomainTunnelTxConnectSpeedMethod,
        juniAaaAssignDomainTunnelRowStatus,

        juniAaaAssignDomainTunnelGroup,

        juniAaaTunnelGroupTunnelName,
        juniAaaTunnelGroupTunnelTag,
        juniAaaTunnelGroupTunnelPreference,
        juniAaaTunnelGroupTunnelType,
        juniAaaTunnelGroupTunnelMedium,
        juniAaaTunnelGroupTunnelAddress,
        juniAaaTunnelGroupTunnelPassword,
        juniAaaTunnelGroupTunnelId,
        juniAaaTunnelGroupTunnelHostName,
        juniAaaTunnelGroupTunnelRowStatus,
        juniAaaTunnelGroupTunnelServerName,
        juniAaaTunnelGroupTunnelClientAddress,
        juniAaaTunnelGroupTunnelMaxSessions,
        juniAaaTunnelGroupTunnelReceiveWindowSize,
        juniAaaTunnelGroupTunnelRouterName,
        juniAaaTunnelGroupTunnelFailoverResync,
        juniAaaTunnelGroupTunnelSwitchProfile,
        juniAaaTunnelGroupTunnelTxConnectSpeedMethod,

        juniAaaOutgoingTunnelGrantResponses }
    STATUS      current
    DESCRIPTION
        "The collection of collection of objects providing management of AAA tunneling
        functionality in a Juniper product."
    ::= { juniAaaMIBGroups 33 }                                    -- JUNOSe 7.3


juniAaaBrasGroup11 OBJECT-GROUP
    OBJECTS {
        juniAaaAssignBrasLicense,
        juniAaaAssignBrasLicensedUsers,
        juniAaaAssignDomainDelimiters,
        juniAaaAssignRealmDelimiters,
        juniAaaAssignDomainParseOrder,
        juniAaaAssignSubscriberLimit,

        juniAaaIdleTimeout,
        juniAaaSessionTimeout,

        juniAaaTunnelClientName,
        juniAaaTunnelPassword,
        juniAaaTunnelNasPortMethod,
        juniAaaTunnelIgnoreNasPort,
        juniAaaTunnelIgnoreNasPortType,
        juniAaaTunnelAssignmentIdFormat,

        juniAaaAssignDomainName,
        juniAaaAssignDomainRowStatus,
        juniAaaAssignDomainRouterName,
        juniAaaAssignDomainIpHint,
        juniAaaAssignDomainAtmServiceLevel,
        juniAaaAssignDomainAtmPcr,
        juniAaaAssignDomainAtmScr,
        juniAaaAssignDomainAtmMbs,
        juniAaaAssignDomainOverrideUserName,
        juniAaaAssignDomainOverridePassword,
        juniAaaAssignDomainStripDomain,
        juniAaaAssignDomainPoolName,
        juniAaaAssignDomainLocalInterface,
        juniAaaAssignDomainIpv6RouterName,
        juniAaaAssignDomainIpv6LocalInterface,
        juniAaaAssignDomainAuthRouterName,
        juniAaaAssignDomainIpRouterName,

        juniAaaAssignDomainMaxPadnPerDomain,
        juniAaaAssignDomainPadnRowStatus,
        juniAaaAssignDomainPadnDistance,
        juniAaaInterfaceIdFormat,
        juniAaaAssignTunnelCallingNumberFormat,
        juniAaaAssignDomainParseDirection,
        juniAaaAssignRealmParseDirection,
        juniAaaInterfaceAdapterFormat,
        juniAaaAssignAccountingStatisticsType,
        juniAaaAssignTunnelCallingNumberFormatFallback  }
    STATUS      obsolete
    DESCRIPTION
        "The obsolete collection of objects providing management of AAA B-RAS
        functionality in a Juniper product."
    ::= { juniAaaMIBGroups 34 }                                    -- JUNOSe 8.1

juniAaaAccountingGroup5 OBJECT-GROUP
    OBJECTS {
        juniAaaAcctInterval,
        juniAaaAcctDupServerRouterName,
        juniAaaAcctBcastServerGroupName,
        juniAaaAcctBcastServerGroupRouter1,
        juniAaaAcctBcastServerGroupRouter2,
        juniAaaAcctBcastServerGroupRouter3,
        juniAaaAcctBcastServerGroupRouter4,
        juniAaaAcctBcastServerGroupRowStatus,
        juniAaaAcctSendStopOnAaaDeny,
        juniAaaAcctSendStopOnAaaReject,
        juniAaaAcctSendImmediateAcctUpdate,
        juniAaaOutgoingAcctRequests,
        juniAaaIncomingAcctResponses,
        juniAaaOutgoingDupAcctRequests,
        juniAaaIncomingDupAcctResponses,
        juniAaaAcctMethodsSubscriberType,
        juniAaaAcctMethodsAccounting,
        juniAaaOutgoingBcastAcctRequests,
        juniAaaIncomingBcastAcctResponses,
        juniAaaUserAcctInterval,
        juniAaaServiceAcctInterval }
    STATUS      current
    DESCRIPTION
        "The collection of objects providing management of AAA accounting
        functionality in a Juniper product."
    ::= { juniAaaMIBGroups 35 }                                     -- JUNOSe 9.1

juniAaaBrasGroup12 OBJECT-GROUP
    OBJECTS {
        juniAaaAssignBrasLicense,
        juniAaaAssignBrasLicensedUsers,
        juniAaaAssignDomainDelimiters,
        juniAaaAssignRealmDelimiters,
        juniAaaAssignDomainParseOrder,
        juniAaaAssignSubscriberLimit,

        juniAaaIdleTimeout,
        juniAaaSessionTimeout,

        juniAaaTunnelClientName,
        juniAaaTunnelPassword,
        juniAaaTunnelNasPortMethod,
        juniAaaTunnelIgnoreNasPort,
        juniAaaTunnelIgnoreNasPortType,
        juniAaaTunnelAssignmentIdFormat,

        juniAaaAssignDomainName,
        juniAaaAssignDomainRowStatus,
        juniAaaAssignDomainRouterName,
        juniAaaAssignDomainIpHint,
        juniAaaAssignDomainAtmServiceLevel,
        juniAaaAssignDomainAtmPcr,
        juniAaaAssignDomainAtmScr,
        juniAaaAssignDomainAtmMbs,
        juniAaaAssignDomainOverrideUserName,
        juniAaaAssignDomainOverridePassword,
        juniAaaAssignDomainStripDomain,
        juniAaaAssignDomainPoolName,
        juniAaaAssignDomainLocalInterface,
        juniAaaAssignDomainIpv6RouterName,
        juniAaaAssignDomainIpv6LocalInterface,
        juniAaaAssignDomainAuthRouterName,
        juniAaaAssignDomainIpRouterName,
        juniAaaAssignDomainTunnelSubscriberAuthentication,

        juniAaaAssignDomainMaxPadnPerDomain,
        juniAaaAssignDomainPadnRowStatus,
        juniAaaAssignDomainPadnDistance,
        juniAaaInterfaceIdFormat,
        juniAaaAssignTunnelCallingNumberFormat,
        juniAaaAssignDomainParseDirection,
        juniAaaAssignRealmParseDirection,
        juniAaaInterfaceAdapterFormat,
        juniAaaAssignAccountingStatisticsType,
        juniAaaAssignTunnelCallingNumberFormatFallback  }
    STATUS      obsolete
    DESCRIPTION
        "The obsolete collection of objects providing management of AAA B-RAS
        functionality in a Juniper product."
    ::= { juniAaaMIBGroups 36 }                                    -- JUNOSe 9.1

juniAaaBrasGroup13 OBJECT-GROUP
    OBJECTS {
        juniAaaAssignBrasLicense,
        juniAaaAssignBrasLicensedUsers,
        juniAaaAssignDomainDelimiters,
        juniAaaAssignRealmDelimiters,
        juniAaaAssignDomainParseOrder,
        juniAaaAssignSubscriberLimit,

        juniAaaIdleTimeout,
        juniAaaSessionTimeout,
        juniAaaMonitorIngressTrafficOnly,

        juniAaaTunnelClientName,
        juniAaaTunnelPassword,
        juniAaaTunnelNasPortMethod,
        juniAaaTunnelIgnoreNasPort,
        juniAaaTunnelIgnoreNasPortType,
        juniAaaTunnelAssignmentIdFormat,

        juniAaaAssignDomainName,
        juniAaaAssignDomainRowStatus,
        juniAaaAssignDomainRouterName,
        juniAaaAssignDomainIpHint,
        juniAaaAssignDomainAtmServiceLevel,
        juniAaaAssignDomainAtmPcr,
        juniAaaAssignDomainAtmScr,
        juniAaaAssignDomainAtmMbs,
        juniAaaAssignDomainOverrideUserName,
        juniAaaAssignDomainOverridePassword,
        juniAaaAssignDomainStripDomain,
        juniAaaAssignDomainPoolName,
        juniAaaAssignDomainLocalInterface,
        juniAaaAssignDomainIpv6RouterName,
        juniAaaAssignDomainIpv6LocalInterface,
        juniAaaAssignDomainAuthRouterName,
        juniAaaAssignDomainIpRouterName,
        juniAaaAssignDomainTunnelSubscriberAuthentication,

        juniAaaAssignDomainMaxPadnPerDomain,
        juniAaaAssignDomainPadnRowStatus,
        juniAaaAssignDomainPadnDistance,
        juniAaaInterfaceIdFormat,
        juniAaaAssignTunnelCallingNumberFormat,
        juniAaaAssignDomainParseDirection,
        juniAaaAssignRealmParseDirection,
        juniAaaInterfaceAdapterFormat,
        juniAaaAssignAccountingStatisticsType,
        juniAaaAssignTunnelCallingNumberFormatFallback  }
    STATUS      obsolete
    DESCRIPTION
        "The obsolete collection of objects providing management of AAA B-RAS
        functionality in a Juniper product."
    ::= { juniAaaMIBGroups 37 }                                    -- JUNOSe 9.3

juniAaaBrasGroup14 OBJECT-GROUP
    OBJECTS {
        juniAaaAssignBrasLicense,
        juniAaaAssignBrasLicensedUsers,
        juniAaaAssignDomainDelimiters,
        juniAaaAssignRealmDelimiters,
        juniAaaAssignDomainParseOrder,
        juniAaaAssignSubscriberLimit,

        juniAaaIdleTimeout,
        juniAaaSessionTimeout,
        juniAaaMonitorIngressTrafficOnly,

        juniAaaTunnelClientName,
        juniAaaTunnelPassword,
        juniAaaTunnelNasPortMethod,
        juniAaaTunnelIgnoreNasPort,
        juniAaaTunnelIgnoreNasPortType,
        juniAaaTunnelAssignmentIdFormat,

        juniAaaAssignDomainName,
        juniAaaAssignDomainRowStatus,
        juniAaaAssignDomainRouterName,
        juniAaaAssignDomainIpHint,
        juniAaaAssignDomainAtmServiceLevel,
        juniAaaAssignDomainAtmPcr,
        juniAaaAssignDomainAtmScr,
        juniAaaAssignDomainAtmMbs,
        juniAaaAssignDomainOverrideUserName,
        juniAaaAssignDomainOverridePassword,
        juniAaaAssignDomainStripDomain,
        juniAaaAssignDomainPoolName,
        juniAaaAssignDomainLocalInterface,
        juniAaaAssignDomainIpv6RouterName,
        juniAaaAssignDomainIpv6LocalInterface,
        juniAaaAssignDomainAuthRouterName,
        juniAaaAssignDomainIpRouterName,
        juniAaaAssignDomainTunnelSubscriberAuthentication,
        juniAaaAssignDomainBackupPoolName,

        juniAaaAssignDomainMaxPadnPerDomain,
        juniAaaAssignDomainPadnRowStatus,
        juniAaaAssignDomainPadnDistance,
        juniAaaInterfaceIdFormat,
        juniAaaAssignTunnelCallingNumberFormat,
        juniAaaAssignDomainParseDirection,
        juniAaaAssignRealmParseDirection,
        juniAaaInterfaceAdapterFormat,
        juniAaaAssignAccountingStatisticsType,
        juniAaaAssignTunnelCallingNumberFormatFallback  }
    STATUS      obsolete
    DESCRIPTION
        "The obsolete collection of objects providing management of AAA B-RAS
        functionality in a Juniper product."
    ::= { juniAaaMIBGroups 38 }                                    -- JUNOSe 10.0

juniAaaBrasGroup15 OBJECT-GROUP
    OBJECTS {
        juniAaaAssignBrasLicense,
        juniAaaAssignBrasLicensedUsers,
        juniAaaAssignDomainDelimiters,
        juniAaaAssignRealmDelimiters,
        juniAaaAssignDomainParseOrder,
        juniAaaAssignSubscriberLimit,

        juniAaaIdleTimeout,
        juniAaaSessionTimeout,
        juniAaaMonitorIngressTrafficOnly,

        juniAaaTunnelClientName,
        juniAaaTunnelPassword,
        juniAaaTunnelNasPortMethod,
        juniAaaTunnelIgnoreNasPort,
        juniAaaTunnelIgnoreNasPortType,
        juniAaaTunnelAssignmentIdFormat,

        juniAaaAssignDomainName,
        juniAaaAssignDomainRowStatus,
        juniAaaAssignDomainRouterName,
        juniAaaAssignDomainIpHint,
        juniAaaAssignDomainAtmServiceLevel,
        juniAaaAssignDomainAtmPcr,
        juniAaaAssignDomainAtmScr,
        juniAaaAssignDomainAtmMbs,
        juniAaaAssignDomainOverrideUserName,
        juniAaaAssignDomainOverridePassword,
        juniAaaAssignDomainStripDomain,
        juniAaaAssignDomainPoolName,
        juniAaaAssignDomainLocalInterface,
        juniAaaAssignDomainIpv6RouterName,
        juniAaaAssignDomainIpv6LocalInterface,
        juniAaaAssignDomainAuthRouterName,
        juniAaaAssignDomainIpRouterName,
        juniAaaAssignDomainTunnelSubscriberAuthentication,
        juniAaaAssignDomainBackupPoolName,

        juniAaaAssignDomainMaxPadnPerDomain,
        juniAaaAssignDomainPadnRowStatus,
        juniAaaAssignDomainPadnDistance,
        juniAaaInterfaceIdFormat,
        juniAaaAssignTunnelCallingNumberFormat,
        juniAaaAssignDomainParseDirection,
        juniAaaAssignRealmParseDirection,
        juniAaaInterfaceAdapterFormat,
        juniAaaAssignAccountingStatisticsType,
        juniAaaAssignTunnelCallingNumberFormatFallback,
        juniAaaFramedIpv6PrefixAsIpv6NdRaPrefix,
        juniAaaDelegatedIpv6PrefixAsDhcpv6DelegatedPrefix  }
    STATUS      current
    DESCRIPTION
        "The collection of objects providing management of AAA B-RAS
        functionality in a Juniper product."
    ::= { juniAaaMIBGroups 39 }                                    -- JUNOSe 10.1

END
