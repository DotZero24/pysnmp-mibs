-- Private MIB definition for Trango Systems
-- Access 58xx series wireless broadband Remote Unit P5830S
-- Version: 1.0
-- Date: June 10, 2003
--
-- Copyright 2003: Trango Systems, Inc. All Rights Reserved.
-- Trango Systems, Inc. 15070 Avenue Of Science Suite 200 San Diego CA 92128 USA.
--
-- Reproduction of this document is authorized on condition that the
-- foregoing copyright notice is included.

TRANGOP5830S-RU-MIB DEFINITIONS ::= BEGIN

-- MIB module for enterprise trango wireless broadband
-- of management of P5830S remote unit

    	IMPORTS
            enterprises, IpAddress, Counter
        	FROM RFC1155-SMI
        OBJECT-TYPE
            FROM RFC-1212;

        -- textual conventions

        DisplayString ::=
            OCTET STRING
        -- This data type is used to model textual information taken
        -- from the NVT ASCII character set.  By convention, objects
        -- with this syntax are declared as having
        --
        -- SIZE (0..255)


	-- trango wireless broadband MIB registration id assigned to 5454.
        -- customer needs to change this value based on their OEM value.
	trango	    	OBJECT IDENTIFIER ::= { enterprises 5454 }
	tbw	    	OBJECT IDENTIFIER ::= { trango 1 }
	p5830sru        OBJECT IDENTIFIER ::= { tbw 24 }

	-- modules branched from m5830sap
	rusys   	OBJECT IDENTIFIER ::= { p5830sru 1 }
	rurf    	OBJECT IDENTIFIER ::= { p5830sru 2 }
	mibinfo     	OBJECT IDENTIFIER ::= { p5830sru 5 }

	ruversion	OBJECT IDENTIFIER ::= { rusys 1 }
	ruswitches  	OBJECT IDENTIFIER ::= { rusys 8 }
	rutraffic   	OBJECT IDENTIFIER ::= { rusys 9 }
	ruipconfig  	OBJECT IDENTIFIER ::= { rusys 13 }
	rurftable   	OBJECT IDENTIFIER ::= { rurf 4 }
	ruism       	OBJECT IDENTIFIER ::= { rurf 5 }
	ruunii      	OBJECT IDENTIFIER ::= { rurf 6 }

	-- MIB objects defined below

	-- remote unit system objects
	ruversionHW OBJECT-TYPE
    	    SYNTAX  OCTET STRING (SIZE(2))
            ACCESS  read-only
            STATUS  mandatory
            DESCRIPTION
	       	"Hardware version."
            ::= { ruversion 1 }

	ruversionFW OBJECT-TYPE
            SYNTAX  DisplayString (SIZE (0..80))
            ACCESS  read-only
            STATUS  mandatory
            DESCRIPTION
	       	"Main firmware version.
                 Format: <code version>H<hardware version>D<date>."
            ::= { ruversion 2 }

	ruversionFPGA OBJECT-TYPE
    	    SYNTAX  OCTET STRING (SIZE(4))
            ACCESS  read-only
            STATUS  mandatory
            DESCRIPTION
	       	"FPGA firmware version."
            ::= { ruversion 3 }

	ruversionFWChecksum OBJECT-TYPE
    	    SYNTAX  OCTET STRING (SIZE(4))
            ACCESS  read-only
            STATUS  mandatory
            DESCRIPTION
	       	"Remote unit firmware checksum."
            ::= { ruversion 4 }

	ruversionFPGAChecksum OBJECT-TYPE
    	    SYNTAX  OCTET STRING (SIZE(4))
            ACCESS  read-only
            STATUS  mandatory
            DESCRIPTION
	       	"Remote unit FPGA checksum."
            ::= { ruversion 5 }

	rusysDeviceId OBJECT-TYPE
	    SYNTAX  OCTET STRING (SIZE(6))
	    ACCESS  read-only
	    STATUS  mandatory
	    DESCRIPTION
	        "Remote unit device Id. Each remote unit in a cluster shall have unique ID."
	    ::= { rusys 2 }

	rusysDefOpMode OBJECT-TYPE
	    SYNTAX  INTEGER {
                        on(16),
                        off(0)
                    }
            ACCESS  read-write
	    STATUS  mandatory
	    DESCRIPTION
	        "The operation mode (on or off) the remote unit is on after reboot/power cycle."
	    ::= { rusys 3 }

	rusysCurOpMode OBJECT-TYPE
	    SYNTAX  INTEGER {
                        on(16),
                        off(0)
                    }
	    ACCESS  read-only
	    STATUS  mandatory
	    DESCRIPTION
	        "Remote unit's current operation mode."
	    ::= { rusys 4 }

        rusysActivateOpmode OBJECT-TYPE
            SYNTAX  INTEGER {
                        deactivated(0),
                        activated(1)
                    }
            ACCESS  read-write
            STATUS  mandatory
            DESCRIPTION
                "Engage remote unit to on operation mode."
            DEFVAL { deactivated }
            ::= { rusys 5 }

	rusysReadCommStr OBJECT-TYPE
            SYNTAX  DisplayString (SIZE (0..32))
	    ACCESS  read-write
	    STATUS  mandatory
	    DESCRIPTION
		"SNMP agent read community string. It is used for authenticcation purpose."
 	    ::= { rusys 6 }

	rusysWriteCommStr OBJECT-TYPE
            SYNTAX  DisplayString (SIZE (0..32))
	    ACCESS  read-write
	    STATUS  mandatory
	    DESCRIPTION
	        "SNMP agent write community string. It is used for authentication purpose."
	    ::= { rusys 7 }

	ruswitchesBlockBroadcastMulticast OBJECT-TYPE
	    SYNTAX  INTEGER {
                        passed(0),
                        blocked(1)
                    }
	    ACCESS  read-write
	    STATUS  mandatory
	    DESCRIPTION
		"This switch enables or disables the blocking of Ethernet
                 control packet except ICMP and ARP to reduce the amount
                 of uneccessary overhead introduced to the wireless link."
	    ::= { ruswitches 1 }


	ruswitchesHTTPD OBJECT-TYPE
	    SYNTAX  INTEGER {
                        disabled(0),
                        enabled(1)
                    }
	    ACCESS  read-write
	    STATUS  mandatory
	    DESCRIPTION
		"When it is turned on, then the remote unit is accessible for
                 configuring via web browser (e.g. IE or Nescape)."
	    ::= { ruswitches 5 }

	ruswitchesAutoScanMasterSignal OBJECT-TYPE
	    SYNTAX  INTEGER {
                        disabled(0),
                        enabled(1)
                    }
	    ACCESS  read-write
	    STATUS  mandatory
	    DESCRIPTION
		"This switch enables or disables the auto scan master unit
		 signal operation on the remote unit only."
	    ::= { ruswitches 6 }

	rutrafficEthInOctets OBJECT-TYPE
	    SYNTAX  Counter
	    ACCESS  read-only
	    STATUS  mandatory
	    DESCRIPTION
		"Number of octets of remote unit's payload received on Ethernet port."
            ::= { rutraffic 1 }

	rutrafficEthOutOctets OBJECT-TYPE
	    SYNTAX  Counter
	    ACCESS  read-only
	    STATUS  mandatory
	    DESCRIPTION
		"Number of octets of remote unit's payload transmitted on Ethernet port."
	    ::= { rutraffic 2 }

	rutrafficRfInOctets OBJECT-TYPE
	    SYNTAX  Counter
	    ACCESS  read-only
	    STATUS  mandatory
	    DESCRIPTION
		"Number of octets of remote unit's payload received from RF port."
	    ::= { rutraffic 3 }

	rutrafficRfOutOctets OBJECT-TYPE
	    SYNTAX  Counter
	    ACCESS  read-only
	    STATUS  mandatory
	    DESCRIPTION
		"Number of octets of remote unit's payload transmitted to RF port."
            ::= { rutraffic 4 }

        rusysTemperature OBJECT-TYPE
            SYNTAX  INTEGER (-128..127)
            ACCESS  read-only
            STATUS  mandatory
            DESCRIPTION
                "Current remote unit temperature value (in Celsius)."
            ::= { rusys 10 }

	rusysUpdateFlashAndActivate OBJECT-TYPE
	    SYNTAX  INTEGER {
                        no(0),
                        yes(1)
                    }
	    ACCESS  read-write
	    STATUS  mandatory
	    DESCRIPTION
	        "Save system setting values to Flash and activate the settings."
            DEFVAL  {no}
	    ::= { rusys 11 }

	rusysReboot OBJECT-TYPE
	    SYNTAX  INTEGER {
                        deactivated(0),
                        activated(1)
                    }
	    ACCESS  read-write
	    STATUS  mandatory
	    DESCRIPTION
	        "Reboot the remote unit."
            DEFVAL { deactivated }
	    ::= { rusys 12 }

	ruipconfigIpAddress OBJECT-TYPE
	    SYNTAX  IpAddress
	    ACCESS  read-write
	    STATUS  mandatory
	    DESCRIPTION
	        "New IP address. It will be saved to
                 non-volatile memory and activated in 5 secs."
	    ::= { ruipconfig 1 }

    	ruipconfigSubnet OBJECT-TYPE
	    SYNTAX  IpAddress
	    ACCESS  read-write
	    STATUS  mandatory
	    DESCRIPTION
		"New Subnet mask. It will be saved to
                 non-volatile memory and activated in 5 secs."
	    ::= { ruipconfig 2 }

    	ruipconfigDefaultGateway OBJECT-TYPE
	    SYNTAX  IpAddress
	    ACCESS  read-write
	    STATUS  mandatory
	    DESCRIPTION
		"New Default gateway. It will be saved to
                 non-volatile memory and activated in 5 secs."
	    ::= { ruipconfig 3 }

	-- remote rf objects
	rurfRSSI OBJECT-TYPE
	    SYNTAX  INTEGER (-128..127)
	    ACCESS  read-only
	    STATUS  mandatory
	    DESCRIPTION
		"Remote unit RSSI (in dBm)."
	    ::= { rurf 1 }

	rurftableChannel1 OBJECT-TYPE
	    SYNTAX  INTEGER (5260..5340 | 5736..5836)
	    ACCESS  read-write
	    STATUS  mandatory
	    DESCRIPTION
	        "RF channel 1 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 1 }

	rurftableChannel2 OBJECT-TYPE
	    SYNTAX  INTEGER (5260..5340 | 5736..5836)
	    ACCESS  read-write
	    STATUS  mandatory
	    DESCRIPTION
	        "RF channel 2 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 2 }

	rurftableChannel3 OBJECT-TYPE
	    SYNTAX  INTEGER (5260..5340 | 5736..5836)
            ACCESS  read-write
	    STATUS  mandatory
	    DESCRIPTION
		"RF channel 3 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 3 }

	rurftableChannel4 OBJECT-TYPE
	    SYNTAX  INTEGER (5260..5340 | 5736..5836)
	    ACCESS  read-write
	    STATUS  mandatory
	    DESCRIPTION
		"RF channel 4 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 4 }

	rurftableChannel5 OBJECT-TYPE
	    SYNTAX  INTEGER (5260..5340 | 5736..5836)
	    ACCESS  read-write
	    STATUS  mandatory
	    DESCRIPTION
	 	"RF channel 5 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 5 }

	rurftableChannel6 OBJECT-TYPE
	    SYNTAX  INTEGER (5260..5340 | 5736..5836)
	    ACCESS  read-write
	    STATUS  mandatory
	    DESCRIPTION
	        "RF channel 6 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 6 }

	rurftableChannel7 OBJECT-TYPE
	    SYNTAX  INTEGER (5260..5340 | 5736..5836)
	    ACCESS  read-write
	    STATUS  mandatory
	    DESCRIPTION
	        "RF channel 7 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 7 }

	rurftableChannel8 OBJECT-TYPE
	    SYNTAX  INTEGER (5260..5340 | 5736..5836)
	    ACCESS  read-write
	    STATUS  mandatory
	    DESCRIPTION
		"RF channel 8 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 8 }

	rurftableChannel9 OBJECT-TYPE
	    SYNTAX  INTEGER (5260..5340 | 5736..5836)
	    ACCESS  read-write
	    STATUS  mandatory
	    DESCRIPTION
	        "RF channel 9 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 9 }

	rurftableChannel10 OBJECT-TYPE
	    SYNTAX  INTEGER (5260..5340 | 5736..5836)
	    ACCESS  read-write
	    STATUS  mandatory
	    DESCRIPTION
		"RF channel 10 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 10 }

	rurftableChannel11 OBJECT-TYPE
            SYNTAX  INTEGER (5260..5340 | 5736..5836)
	    ACCESS  read-write
	    STATUS  mandatory
	    DESCRIPTION
		"RF channel 11 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 11 }

	rurftableChannel12 OBJECT-TYPE
	    SYNTAX  INTEGER (5260..5340 | 5736..5836)
	    ACCESS  read-write
	    STATUS  mandatory
	    DESCRIPTION
	   	"RF channel 12 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 12 }

	rurftableChannel13 OBJECT-TYPE
	    SYNTAX  INTEGER (5260..5340 | 5736..5836)
	    ACCESS  read-write
	    STATUS  mandatory
	    DESCRIPTION
		"RF channel 13 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 13 }

	rurftableChannel14 OBJECT-TYPE
	    SYNTAX  INTEGER (5260..5340 | 5736..5836)
	    ACCESS  read-write
	    STATUS  mandatory
	    DESCRIPTION
		"RF channel 14 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 14 }

	rurftableChannel15 OBJECT-TYPE
	    SYNTAX  INTEGER (5260..5340 | 5736..5836)
	    ACCESS  read-write
	    STATUS  mandatory
	    DESCRIPTION
		"RF channel 15 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 15 }

	rurftableChannel16 OBJECT-TYPE
	    SYNTAX  INTEGER (5260..5340 | 5736..5836)
	    ACCESS  read-write
	    STATUS  mandatory
	    DESCRIPTION
		"RF channel 16 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 16 }

	rurftableChannel17 OBJECT-TYPE
	    SYNTAX  INTEGER (5260..5340 | 5736..5836)
	    ACCESS  read-write
	    STATUS  mandatory
	    DESCRIPTION
		"RF channel 17 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 17 }

	rurftableChannel18 OBJECT-TYPE
	    SYNTAX  INTEGER (5260..5340 | 5736..5836)
	    ACCESS  read-write
	    STATUS  mandatory
	    DESCRIPTION
		"RF channel 18 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 18 }

	rurftableChannel19 OBJECT-TYPE
	    SYNTAX  INTEGER (5260..5340 | 5736..5836)
	    ACCESS  read-write
	    STATUS  mandatory
	    DESCRIPTION
		"RF channel 19 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 19 }

	rurftableChannel20 OBJECT-TYPE
	    SYNTAX  INTEGER (5260..5340 | 5736..5836)
	    ACCESS  read-write
	    STATUS  mandatory
	    DESCRIPTION
		"RF channel 20 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 20 }

	rurftableChannel21 OBJECT-TYPE
	    SYNTAX  INTEGER (5260..5340 | 5736..5836)
	    ACCESS  read-write
	    STATUS  mandatory
	    DESCRIPTION
		"RF channel 21 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 21 }

	rurftableChannel22 OBJECT-TYPE
	    SYNTAX  INTEGER (5260..5340 | 5736..5836)
	    ACCESS  read-write
	    STATUS  mandatory
	    DESCRIPTION
		"RF channel 22 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 22 }

	rurftableChannel23 OBJECT-TYPE
	    SYNTAX  INTEGER (5260..5340 | 5736..5836)
	    ACCESS  read-write
	    STATUS  mandatory
	    DESCRIPTION
	    	"RF channel 23 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 23 }

	rurftableChannel24 OBJECT-TYPE
	    SYNTAX  INTEGER (5260..5340 | 5736..5836)
	    ACCESS  read-write
	    STATUS  mandatory
	    DESCRIPTION
		"RF channel 24 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 24 }

	rurftableChannel25 OBJECT-TYPE
	    SYNTAX  INTEGER (5260..5340 | 5736..5836)
	    ACCESS  read-write
	    STATUS  mandatory
	    DESCRIPTION
		"RF channel 25 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 25 }

	rurftableChannel26 OBJECT-TYPE
	    SYNTAX  INTEGER (5260..5340 | 5736..5836)
	    ACCESS  read-write
	    STATUS  mandatory
	    DESCRIPTION
		"RF channel 26 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 26 }

	rurftableChannel27 OBJECT-TYPE
	    SYNTAX  INTEGER (5260..5340 | 5736..5836)
	    ACCESS  read-write
	    STATUS  mandatory
	    DESCRIPTION
		"RF channel 27 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 27 }

	rurftableChannel28 OBJECT-TYPE
	    SYNTAX  INTEGER (5260..5340 | 5736..5836)
	    ACCESS  read-write
	    STATUS  mandatory
	    DESCRIPTION
		"RF channel 28 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 28 }

	rurftableChannel29 OBJECT-TYPE
	    SYNTAX  INTEGER (5260..5340 | 5736..5836)
	    ACCESS  read-write
	    STATUS  mandatory
	    DESCRIPTION
		"RF channel 29 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 29 }

	rurftableChannel30 OBJECT-TYPE
	    SYNTAX  INTEGER (5260..5340 | 5736..5836)
	    ACCESS  read-write
	    STATUS  mandatory
	    DESCRIPTION
		"RF channel 30 frequency (in MHz). It allows you to create your
                 own channel instead of the manufacturing defaults in the remote unit.
                 Keep in mind that channel width is 20MHz, and the frequency
                 specified here is the center frequency.
                 Frequency (5260MHz - 5340MHz) is only applicable to M5830S/P5830S radio."
	    ::= { rurftable 30 }

	ruismTxPowerMax OBJECT-TYPE
            SYNTAX  INTEGER (-128..127)
	    ACCESS  read-only
	    STATUS  mandatory
	    DESCRIPTION
            	"The maximum ISM Tx power value can be set (in dBm)."
            ::= { ruism 1 }

	ruismTxPowerMin OBJECT-TYPE
	    SYNTAX  INTEGER (-128..127)
	    ACCESS  read-only
	    STATUS  mandatory
	    DESCRIPTION
            	"The minimum ISM Tx power value can be set (in dBm)."
            ::= { ruism 2 }

	ruismTxPower OBJECT-TYPE
	    SYNTAX  INTEGER (-128..127)
	    ACCESS  read-write
	    STATUS  mandatory
	    DESCRIPTION
		"ISM RF tx power (in dBm). It specifies the power output
                 of the radio, excluding the antenna gain. Check parameters
                 remoteismTxPowerMax and remoteismTxPowerMin for power setting range."
	    ::= { ruism 3 }

	ruismRxThreshold OBJECT-TYPE
	    SYNTAX  INTEGER (-90 | -85 | -80 | -75 | -70 | -65)
	    ACCESS  read-write
	    STATUS  mandatory
	    DESCRIPTION
		"ISM RF rx threshold (in dBm). It specifies the receiver
	         sensitivity of the remote. By default, the radio's sensitivity is -82dBm.
                 The higher the threshold is, the less sensitive the radio will be.
                 In M5800S, the value -90 represents the rfrxthreshold is disabled."
	    ::= { ruism 4 }

	ruuniiTxPowerMax OBJECT-TYPE
	    SYNTAX  INTEGER (-128..127)
	    ACCESS  read-only
	    STATUS  mandatory
	    DESCRIPTION
            	"This object is only applicable to M5830S/P5830S radio.
                 The maximum UNII Tx power value can be set (in dBm)."
        ::= { ruunii 1 }

	ruuniiTxPowerMin OBJECT-TYPE
	    SYNTAX  INTEGER (-128..127)
	    ACCESS  read-only
	    STATUS  mandatory
	    DESCRIPTION
            	"This object is only applicable to M5830S/P5830S radio.
                 The minimum UNII Tx power value can be set (in dBm)."
            ::= { ruunii 2 }

 	ruuniiTxPower OBJECT-TYPE
	    SYNTAX  INTEGER (-128..127)
	    ACCESS  read-write
	    STATUS  mandatory
	    DESCRIPTION
            	"This object is only applicable to M5830S/P5830S radio.
		 UNII RF tx power (in dBm). It specifies the power output
                 of the radio, excluding the antenna gain. Check parameters
                 apuniiTxPowerMax and apuniiTxPowerMin for power setting range."
	    ::= { ruunii 3 }

	ruuniiRxThreshold OBJECT-TYPE
	    SYNTAX  INTEGER (-90 | -85 | -80 | -75 | -70 | -65)
	    ACCESS  read-write
	    STATUS  mandatory
	    DESCRIPTION
            	"This object is only applicable to M5830S/P5830S radio.
                 UNII RF rx threshold (in dBm). It specifies the receiver
		 sensitivity of the master unit."
	    ::= { ruunii 4 }

	-- MIB version object
	mibinfoVersion OBJECT-TYPE
            SYNTAX  DisplayString (SIZE (0..32))
	    ACCESS  read-only
	    STATUS  mandatory
	    DESCRIPTION
		"Trango remote unit MIB Version."
	    ::= { mibinfo 1 }

-- End of file <trango_P5830S_RU_1p0.mib>
END
