TRANGO-APEX-TRAP-MIB DEFINITIONS ::= BEGIN

IMPORTS
	MODULE-IDENTITY,
	OBJECT-TYPE,
	OBJECT-IDENTITY,
	Unsigned32,
	NOTIFICATION-TYPE,
        apex
                FROM TRANGO-APEX-MIB

	MODULE-COMPLIANCE
		FROM SNMPv2-CONF;

	DisplayString ::= OCTET STRING

-- *******************************************************************
-- ** Trap Information ** trango.twb.apex.trangotrap
-- *******************************************************************

trangotrap		OBJECT IDENTIFIER ::= { apex 6 }

trapReboot		NOTIFICATION-TYPE
	STATUS		current
	DESCRIPTION	"send traps when the system reboots"
	::= { trangotrap 1 }

trapStartUp		NOTIFICATION-TYPE
	STATUS		current
	DESCRIPTION	"send traps when the system starts up"
	::= { trangotrap 2 }

traplock		OBJECT IDENTIFIER ::= { trangotrap 3 }

trapModemLock		NOTIFICATION-TYPE
	STATUS		current
	DESCRIPTION	"send traps when the system lose modem lock"
	::= { traplock 1 }

trapTimingLock		NOTIFICATION-TYPE
	STATUS		current
	DESCRIPTION	"Timing Lock in modem changed"
	::= { traplock 2 }

trapInnerCodeLock	NOTIFICATION-TYPE
	STATUS		current
	DESCRIPTION	"send traps when the system lose Inner Code lock"
	::= { traplock 3 }

trapEqualizerLock	NOTIFICATION-TYPE
	STATUS		current
	DESCRIPTION	"send traps when the system lose Equalizer lock"
	::= { traplock 4 }

trapFrameSyncLock	NOTIFICATION-TYPE
	STATUS		current
	DESCRIPTION	"send traps when the system lose Frame Sync lock"
	::= { traplock 5 }

trapthreshold		OBJECT IDENTIFIER ::= { trangotrap 4 }

trapmse			OBJECT IDENTIFIER ::= { trapthreshold 1 }

trapMSEMinThreshold	NOTIFICATION-TYPE
	STATUS		current
	DESCRIPTION	"send traps when the MSE fall out from the  threshold"
	::= { trapmse 1 }

trapMSEMaxThreshold	NOTIFICATION-TYPE
	STATUS		current
	DESCRIPTION	"send traps when the MSE fall out from the  threshold"
	::= { trapmse 2 }

trapber			OBJECT IDENTIFIER ::= { trapthreshold 2 }

trapBERMinThreshold	NOTIFICATION-TYPE
	STATUS		current
	DESCRIPTION	"send traps when the BER fall out from the  threshold"
	::= { trapber 1 }

trapBERMaxThreshold	NOTIFICATION-TYPE
	STATUS		current
	DESCRIPTION	"send traps when the BER fall out from the  threshold"
	::= { trapber 2 }

trapfer			OBJECT IDENTIFIER ::= { trapthreshold 3 }

trapFERMinThreshold	NOTIFICATION-TYPE
	STATUS		current
	DESCRIPTION	"send traps when the FER fall out from the  threshold"
	::= { trapfer 1 }

trapFERMaxThreshold	NOTIFICATION-TYPE
	STATUS		current
	DESCRIPTION	"send traps when the FER fall out from the  threshold"
	::= { trapfer 2 }

traprssi			OBJECT IDENTIFIER ::= { trapthreshold 4 }

trapRSSIMinThreshold	NOTIFICATION-TYPE
	STATUS		current
	DESCRIPTION	"send traps when the RSSI fall out from the  threshold"
	::= { traprssi 1 }

trapRSSIMaxThreshold	NOTIFICATION-TYPE
	STATUS		current
	DESCRIPTION	"send traps when the RSSI fall out from the  threshold"
	::= { traprssi 2 }

trapidutemp			OBJECT IDENTIFIER ::= { trapthreshold 5 }

trapIDUTempMinThreshold	NOTIFICATION-TYPE
	STATUS		current
	DESCRIPTION	"send traps when the ethernet status exceed threshold"
	::= { trapidutemp 1 }

trapIDUTempMaxThreshold	NOTIFICATION-TYPE
	STATUS		current
	DESCRIPTION	"send traps when the ethernet status exceed threshold"
	::= { trapidutemp 2 }

trapodutemp			OBJECT IDENTIFIER ::= { trapthreshold 6 }

trapODUTempMinThreshold		NOTIFICATION-TYPE
	STATUS		current
	DESCRIPTION	"send traps when the T1 status exceed threshold"
	::= { trapodutemp 1 }

trapODUTempMaxThreshold		NOTIFICATION-TYPE
	STATUS		current
	DESCRIPTION	"send traps when the T1 status exceed threshold"
	::= { trapodutemp 2 }

trapinport			OBJECT IDENTIFIER ::= { trapthreshold 7 }

trapInPortUtilMinThreshold	NOTIFICATION-TYPE
	STATUS		current
	DESCRIPTION	"send traps when the IN port utilization fall below min threshold"
	::= { trapinport 1 }

trapInPortUtilMaxThreshold	NOTIFICATION-TYPE
	STATUS		current
	DESCRIPTION	"send traps when the IN port utilization exceed max threshold"
	::= { trapinport 2 }

trapoutport			OBJECT IDENTIFIER ::= { trapthreshold 8 }

trapOutPortUtilMinThreshold	NOTIFICATION-TYPE
	STATUS		current
	DESCRIPTION	"send traps when the OUT port utilization fall below min threshold"
	::= { trapoutport 1 }

trapOutPortUtilMaxThreshold	NOTIFICATION-TYPE
	STATUS		current
	DESCRIPTION	"send traps when the OUT port utilization exceed max threshold"
	::= { trapoutport 2 }

trapstandby		OBJECT IDENTIFIER ::= { trangotrap 5 }

trapStandbyLinkDown	NOTIFICATION-TYPE
	STATUS		current
	DESCRIPTION	"send traps when Standby link is down"
	::= { trapstandby 1 }

trapStandbyLinkUp	NOTIFICATION-TYPE
	STATUS		current
	DESCRIPTION	"send traps when Standby link is up"
	::= { trapstandby 2 }

trapSwitchover		NOTIFICATION-TYPE
	STATUS		current
	DESCRIPTION	"send traps when backup unit takes over the link"
	::= { trapstandby 3 }

trapeth		OBJECT IDENTIFIER ::= { trangotrap 6 }

trapethstatus		OBJECT IDENTIFIER ::= { trapeth 1 }

trapEth1StatusUpdate	NOTIFICATION-TYPE
	STATUS		current
	DESCRIPTION	"send traps when ethernet port 1 status changed"
	::= { trapethstatus 1 }

trapEth2StatusUpdate	NOTIFICATION-TYPE
	STATUS		current
	DESCRIPTION	"send traps when ethernet port 2 status changed"
	::= { trapethstatus 2 }

trapEth3StatusUpdate	NOTIFICATION-TYPE
	STATUS		current
	DESCRIPTION	"send traps when ethernet port 3 status changed"
	::= { trapethstatus 3 }

trapEth4StatusUpdate	NOTIFICATION-TYPE
	STATUS		current
	DESCRIPTION	"send traps when ethernet port 4 status changed"
	::= { trapethstatus 4 }

trapDownShift		NOTIFICATION-TYPE
	STATUS		current
	DESCRIPTION	"send traps when the system downshift the modulation"
	::= { trangotrap 8 }

trapRapidPortShutdown	NOTIFICATION-TYPE
	STATUS		current
	DESCRIPTION	"send traps when the rapid port shutdown occurs"
	::= { trangotrap 9 }

trapRPSPortUp		NOTIFICATION-TYPE
	STATUS		current
	DESCRIPTION	"send traps when the re-enable ports after RPS port down"
	::= { trangotrap 10 }

END
