TRANGO-APEX-GIGE-MIB DEFINITIONS ::= BEGIN

IMPORTS
	MODULE-IDENTITY,
	OBJECT-TYPE,
	OBJECT-IDENTITY,
	NOTIFICATION-TYPE,
        apex
                FROM TRANGO-APEX-MIB
        DisplayString
		FROM SNMPv2-TC
	MODULE-COMPLIANCE
		FROM SNMPv2-CONF;

-- *******************************************************************
-- ** RF/ODU Information ** trango.twb.apex.rf
-- *******************************************************************

gige			OBJECT IDENTIFIER ::= { apex 4 }

ibm			OBJECT IDENTIFIER ::= { gige 1 }

gigeIBMEnable			OBJECT-TYPE
    	SYNTAX			INTEGER { DISABLED(0), ENABLED(1) }
	MAX-ACCESS		read-write
	STATUS			current
	DESCRIPTION		"Enable/Disable Inband Management feature"
	::= { ibm 1 }

gigeIBMIp			OBJECT-TYPE
    	SYNTAX			IpAddr
	MAX-ACCESS		read-write
	STATUS			current
	DESCRIPTION		"Assign/Display IBM Vlan IP"
	::= { ibm 2 }

gigeIBMVlanID			OBJECT-TYPE
    	SYNTAX			INTEGER
	MAX-ACCESS		read-write
	STATUS			current
	DESCRIPTION		"Assign/Display IBM Vlan ID"
	::= { ibm 3 }

gigeIBMPort			OBJECT-TYPE
    	SYNTAX			INTEGER { COPPER(0), FIBER(1) }
	MAX-ACCESS		read-write
	STATUS			current
	DESCRIPTION		"Assign/Display IBM port"
	::= { ibm 4 }

gigeIBMNetmask			OBJECT-TYPE
    	SYNTAX			IpAddr
	MAX-ACCESS		read-write
	STATUS			current
	DESCRIPTION		"Assign/Display IBM Netmask"
	::= { ibm 5 }

ethEnable			OBJECT IDENTIFIER ::= { gige 2 }

gigeEth1Enable			OBJECT-TYPE
    	SYNTAX			INTEGER { OFF(0), ON(1),  RPSOFF(2) }
	MAX-ACCESS		read-write
	STATUS			current
	DESCRIPTION		"Activate/Deactive link status on Ethernet port 1"
	::= { ethEnable 1 }

gigeEth2Enable			OBJECT-TYPE
    	SYNTAX			INTEGER { OFF(0), ON(1), RPSOFF(2) }
	MAX-ACCESS		read-write
	STATUS			current
	DESCRIPTION		"Activate/Deactive link status on Ethernet port 2"
	::= { ethEnable 2 }

ethStatus			OBJECT IDENTIFIER ::= { gige 3 }

gigeEth1Status			OBJECT-TYPE
    	SYNTAX			INTEGER { OFF(0), ON(1) }
	MAX-ACCESS		read-only
	STATUS			current
	DESCRIPTION		"Show link status on Ethernet port 1"
	::= { ethStatus 1 }

gigeEth2Status			OBJECT-TYPE
    	SYNTAX			INTEGER { OFF(0), ON(1) }
	MAX-ACCESS		read-only
	STATUS			current
	DESCRIPTION		"Show link status on Ethernet port 2"
	::= { ethStatus 2 }

ethSpeed			OBJECT IDENTIFIER ::= { gige 4 }

gigeEth1Speed			OBJECT-TYPE
    	SYNTAX			INTEGER
	MAX-ACCESS		read-write
	STATUS			current
	DESCRIPTION		"Display / set link speed on Ethernet port 1"
	::= { ethSpeed 1 }

gigeEth2Speed			OBJECT-TYPE
    	SYNTAX			INTEGER
	MAX-ACCESS		read-only
	STATUS			current
	DESCRIPTION		"Display link speed on Ethernet port 2"
	::= { ethSpeed 2 }

ethDuplex			OBJECT IDENTIFIER ::= { gige 5 }

gigeEth1Duplex			OBJECT-TYPE
    	SYNTAX			INTEGER { HALF(0), FULL(1) }
	MAX-ACCESS		read-write
	STATUS			current
	DESCRIPTION		"Display / set duplex Ethernet port 1"
	::= { ethDuplex 1 }

gigeEth2Duplex			OBJECT-TYPE
    	SYNTAX			INTEGER { HALF(0), FULL(1) }
	MAX-ACCESS		read-only
	STATUS			current
	DESCRIPTION		"Display duplex Ethernet port 2"
	::= { ethDuplex 2 }

ethPriority			OBJECT IDENTIFIER ::= { gige 6 }

gigeEth1Priority		OBJECT-TYPE
    	SYNTAX			INTEGER
	MAX-ACCESS		read-write
	STATUS			current
	DESCRIPTION		"Display / set Priority for Ethernet port 1"
	::= { ethPriority 1 }

gigeEth2Priority		OBJECT-TYPE
    	SYNTAX			INTEGER
	MAX-ACCESS		read-write
	STATUS			current
	DESCRIPTION		"Display / set Priority for Ethernet port 2"
	::= { ethPriority 2 }

ethMaxRate			OBJECT IDENTIFIER ::= { gige 7 }

gigeEth1MaxRate			OBJECT-TYPE
    	SYNTAX			INTEGER
	MAX-ACCESS		read-write
	STATUS			current
	DESCRIPTION		"Display / set Max Rate for Ethernet port 1"
	::= { ethMaxRate 1 }

gigeEth2MaxRate			OBJECT-TYPE
    	SYNTAX			INTEGER
	MAX-ACCESS		read-write
	STATUS			current
	DESCRIPTION		"Display / set Max Rate for Ethernet port 2"
	::= { ethMaxRate 2 }

ethPauseFrame			OBJECT IDENTIFIER ::= { gige 8 }

gigeEth1PauseFrame		OBJECT-TYPE
    	SYNTAX			INTEGER { OFF(0), ON(1) }
	MAX-ACCESS		read-write
	STATUS			current
	DESCRIPTION		"Display / set Burst Rate for Ethernet port 1"
	::= { ethPauseFrame 1 }

gigeEth2PauseFrame		OBJECT-TYPE
    	SYNTAX			INTEGER { OFF(0), ON(1) }
	MAX-ACCESS		read-write
	STATUS			current
	DESCRIPTION		"Display / set Burst Rate for Ethernet port 2"
	::= { ethPauseFrame 2 }

ethInOctets			OBJECT IDENTIFIER ::= { gige 9 }

gigeEth1InOctets		OBJECT-TYPE
    	SYNTAX			Counter32
	MAX-ACCESS		read-only
	STATUS			current
	DESCRIPTION		"Display number of octet coming in to Ethernet port 1"
	::= { ethInOctets 1 }

gigeEth2InOctets		OBJECT-TYPE
    	SYNTAX			Counter32
	MAX-ACCESS		read-only
	STATUS			current
	DESCRIPTION		"Display number of octet coming in to Ethernet port 2"
	::= { ethInOctets 2 }

ethInUcastPackets		OBJECT IDENTIFIER ::= { gige 10 }

gigeEth1InUcastPackets		OBJECT-TYPE
    	SYNTAX			Counter32
	MAX-ACCESS		read-only
	STATUS			current
	DESCRIPTION		"Display number of Unicast packet coming in to Ethernet port 1"
	::= { ethInUcastPackets 1 }

gigeEth2InUcastPackets		OBJECT-TYPE
    	SYNTAX			Counter32
	MAX-ACCESS		read-only
	STATUS			current
	DESCRIPTION		"Display number of Unicast packet coming in to Ethernet port 2"
	::= { ethInUcastPackets 2 }

ethInNUcastPackets		OBJECT IDENTIFIER ::= { gige 11 }

gigeEth1InNUcastPackets		OBJECT-TYPE
    	SYNTAX			Counter32
	MAX-ACCESS		read-only
	STATUS			current
	DESCRIPTION		"Display number of non-Unicast packet coming in to Ethernet port 1"
	::= { ethInNUcastPackets 1 }

gigeEth2InNUcastPackets		OBJECT-TYPE
    	SYNTAX			Counter32
	MAX-ACCESS		read-only
	STATUS			current
	DESCRIPTION		"Display number of non-Unicast packet coming in to Ethernet port 2"
	::= { ethInNUcastPackets 2 }

ethInTotalPackets		OBJECT IDENTIFIER ::= { gige 12 }

gigeEth1InTotalPackets		OBJECT-TYPE
    	SYNTAX			Counter32
	MAX-ACCESS		read-only
	STATUS			current
	DESCRIPTION		"Display number of Total packet coming in to Ethernet port 1"
	::= { ethInTotalPackets 1 }

gigeEth2InTotalPackets		OBJECT-TYPE
    	SYNTAX			Counter32
	MAX-ACCESS		read-only
	STATUS			current
	DESCRIPTION		"Display number of Total packet coming in to Ethernet port 2"
	::= { ethInTotalPackets 2 }

ethOutOctets			OBJECT IDENTIFIER ::= { gige 13 }

gigeEth1OutOctets		OBJECT-TYPE
    	SYNTAX			Counter32
	MAX-ACCESS		read-only
	STATUS			current
	DESCRIPTION		"Display number of Octets going out from Ethernet port 1"
	::= { ethOutOctets 1 }

gigeEth2OutOctets		OBJECT-TYPE
    	SYNTAX			Counter32
	MAX-ACCESS		read-only
	STATUS			current
	DESCRIPTION		"Display number of Octets going out from Ethernet port 2"
	::= { ethOutOctets 2 }

ethOutUcastPackets			OBJECT IDENTIFIER ::= { gige 14 }

gigeEth1OutUcastPackets		OBJECT-TYPE
    	SYNTAX			Counter32
	MAX-ACCESS		read-only
	STATUS			current
	DESCRIPTION		"Display number of Unicast packets going out from Ethernet port 1"
	::= { ethOutUcastPackets 1 }

gigeEth2OutUcastPackets		OBJECT-TYPE
    	SYNTAX			Counter32
	MAX-ACCESS		read-only
	STATUS			current
	DESCRIPTION		"Display number of Unicast packets going out from Ethernet port 2"
	::= { ethOutUcastPackets 2 }

ethOutNUcastPackets		OBJECT IDENTIFIER ::= { gige 15 }

gigeEth1OutNUcastPackets	OBJECT-TYPE
    	SYNTAX			Counter32
	MAX-ACCESS		read-only
	STATUS			current
	DESCRIPTION		"Display number of non-Unicast packets going out from Ethernet port 1"
	::= { ethOutNUcastPackets 1 }

gigeEth2OutNUcastPackets	OBJECT-TYPE
    	SYNTAX			Counter32
	MAX-ACCESS		read-only
	STATUS			current
	DESCRIPTION		"Display number of non-Unicast packets going out from Ethernet port 2"
	::= { ethOutNUcastPackets 2 }

ethOutTotalPackets		OBJECT IDENTIFIER ::= { gige 16 }

gigeEth1OutTotalPackets		OBJECT-TYPE
    	SYNTAX			Counter32
	MAX-ACCESS		read-only
	STATUS			current
	DESCRIPTION		"Display number of non-Unicast packets going out from Ethernet port 1"
	::= { ethOutTotalPackets 1 }

gigeEth2OutTotalPackets		OBJECT-TYPE
    	SYNTAX			Counter32
	MAX-ACCESS		read-only
	STATUS			current
	DESCRIPTION		"Display number of non-Unicast packets going out from Ethernet port 2"
	::= { ethOutTotalPackets 2 }

ethCRCErrors			OBJECT IDENTIFIER ::= { gige 17 }

gigeEth1CRCErrors		OBJECT-TYPE
    	SYNTAX			Counter32
	MAX-ACCESS		read-only
	STATUS			current
	DESCRIPTION		"Display number of packets with CRC Errors for Ethernet port 1"
	::= { ethCRCErrors 1 }

gigeEth2CRCErrors		OBJECT-TYPE
    	SYNTAX			Counter32
	MAX-ACCESS		read-only
	STATUS			current
	DESCRIPTION		"Display number of packets with CRC Errors for Ethernet port 2"
	::= { ethCRCErrors 2 }

ethCollisionErrors		OBJECT IDENTIFIER ::= { gige 18 }

gigeEth1CollsionErrors		OBJECT-TYPE
    	SYNTAX			Counter32
	MAX-ACCESS		read-only
	STATUS			current
	DESCRIPTION		"Display number of collision errors for Ethernet port 1"
	::= { ethCollisionErrors 1 }

gigeEth2CollsionErrors		OBJECT-TYPE
    	SYNTAX			Counter32
	MAX-ACCESS		read-only
	STATUS			current
	DESCRIPTION		"Display number of collision errors for Ethernet port 2"
	::= { ethCollisionErrors 2 }

ethPriorityQueue		OBJECT IDENTIFIER ::= { gige 19 }

gigeEthPriority0COSQueue	OBJECT-TYPE
    	SYNTAX			INTEGER  { COSQ0(0), COSQ1(1), COSQ2(2), COSQ3(3) }
	MAX-ACCESS		read-write
	STATUS			current
	DESCRIPTION		"Display/Set COS Queue for Priority 0"
	::= { ethPriorityQueue 1 }

gigeEthPriority1COSQueue	OBJECT-TYPE
    	SYNTAX			INTEGER  { COSQ0(0), COSQ1(1), COSQ2(2), COSQ3(3) }
	MAX-ACCESS		read-write
	STATUS			current
	DESCRIPTION		"Display/Set COS Queue for Priority 2"
	::= { ethPriorityQueue 2 }

gigeEthPriority2COSQueue	OBJECT-TYPE
    	SYNTAX			INTEGER  { COSQ0(0), COSQ1(1), COSQ2(2), COSQ3(3) }
	MAX-ACCESS		read-write
	STATUS			current
	DESCRIPTION		"Display/Set COS Queue for Priority 2"
	::= { ethPriorityQueue 3 }

gigeEthPriority3COSQueue	OBJECT-TYPE
    	SYNTAX			INTEGER  { COSQ0(0), COSQ1(1), COSQ2(2), COSQ3(3) }
	MAX-ACCESS		read-write
	STATUS			current
	DESCRIPTION		"Display/Set COS Queue for Priority 3"
	::= { ethPriorityQueue 4 }

gigeEthPriority4COSQueue	OBJECT-TYPE
    	SYNTAX			INTEGER  { COSQ0(0), COSQ1(1), COSQ2(2), COSQ3(3) }
	MAX-ACCESS		read-write
	STATUS			current
	DESCRIPTION		"Display/Set COS Queue for Priority 4"
	::= { ethPriorityQueue 5 }

gigeEthPriority5COSQueue	OBJECT-TYPE
    	SYNTAX			INTEGER  { COSQ0(0), COSQ1(1), COSQ2(2), COSQ3(3) }
	MAX-ACCESS		read-write
	STATUS			current
	DESCRIPTION		"Display/Set COS Queue for Priority 5"
	::= { ethPriorityQueue 6 }

gigeEthPriority6COSQueue	OBJECT-TYPE
    	SYNTAX			INTEGER  { COSQ0(0), COSQ1(1), COSQ2(2), COSQ3(3) }
	MAX-ACCESS		read-write
	STATUS			current
	DESCRIPTION		"Display/Set COS Queue for Priority 6"
	::= { ethPriorityQueue 7 }

gigeEthPriority7COSQueue	OBJECT-TYPE
    	SYNTAX			INTEGER  { COSQ0(0), COSQ1(1), COSQ2(2), COSQ3(3) }
	MAX-ACCESS		read-write
	STATUS			current
	DESCRIPTION		"Display/Set COS Queue for Priority 7"
	::= { ethPriorityQueue 8 }

ethAuto			OBJECT IDENTIFIER ::= { gige 20 }

gigeEth1AutoNegotiate		OBJECT-TYPE
    	SYNTAX			INTEGER { OFF(0), ON(1) }
	MAX-ACCESS		read-write
	STATUS			current
	DESCRIPTION		"Activate/Deactive link status on Ethernet port 1"
	::= { ethAuto 1 }

gigeEth2AutoNegotiate			OBJECT-TYPE
    	SYNTAX			INTEGER { OFF(0), ON(1) }
	MAX-ACCESS		read-write
	STATUS			current
	DESCRIPTION		"Activate/Deactive link status on Ethernet port 2"
	::= { ethAuto 2 }

END
