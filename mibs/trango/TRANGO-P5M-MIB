TRANGO-P5M-MIB DEFINITIONS ::= BEGIN

IMPORTS
	MODULE-IDENTITY,
	OBJECT-TYPE,
	OBJECT-IDENTITY,
	Unsigned32,
	NOTIFICATION-TYPE,
	enterprises
		FROM SNMPv2-SMI

	NOTIFICATION-GROUP,
	MODULE-COMPLIANCE
		FROM SNMPv2-CONF;

--	islModules, islGeneric, islTrango
--		FROM ISL-GLOBAL-REG;

	DisplayString ::= OCTET STRING

-- *******************************************************************
-- * Trango module
-- *******************************************************************
trango		OBJECT IDENTIFIER ::= { enterprises 5454 }
tbw 		OBJECT IDENTIFIER ::= { trango 1 }
trangoModules	OBJECT IDENTIFIER ::= { trango 10 }

trangoP5M MODULE-IDENTITY
	LAST-UPDATED	"200408270000Z"
	ORGANIZATION	"Trango Corporation"
	CONTACT-INFO "
		 Name: 		Trango Systems, Inc.
		 Address:	15070 Avenue of Science
		 Zip:		CA 92128
		 City:		San Diego
		 Country:	U.S.A.
		 Phone:		+1-858-653-3900
		 e-mail:	techsupport@trangobroadband.com
		 This is added by Eclips
		 "
	DESCRIPTION	"The Trango SNMP General MIB Module for Atlas Point to Point P5M"
	REVISION	"200408270000Z"
	DESCRIPTION	"Initial version."
	::= { trangoModules 10 }

-- Trango Atlas Point to Point

p5m		OBJECT IDENTIFIER ::= { tbw 40 }

-- *******************************************************************
-- ** System Information ** islTrango.p5m.sys
-- *******************************************************************
sys		OBJECT IDENTIFIER ::= { p5m 1 }

-- **** Version **** islTrango.p5m.sys.1

ver		OBJECT IDENTIFIER ::= { sys 1  }

verUintType	OBJECT-TYPE
    SYNTAX	INTEGER { mu(1), ru(0) }
    MAX-ACCESS	read-write
    STATUS	current
    DESCRIPTION "MU/RU"
    ::= { ver 1 }

verHW		OBJECT-TYPE
    SYNTAX	OCTET STRING (SIZE(2))
    MAX-ACCESS	read-only
    STATUS	current
    DESCRIPTION "Hardware Version"
    ::= { ver 2 }

verFW		OBJECT-TYPE
    SYNTAX 	DisplayString (SIZE(0..80))
    MAX-ACCESS	read-only
    STATUS	current
    DESCRIPTION "Main firmware version <version code>H<hardware version>D<date code>"
    ::= { ver 3 }

-- verFWChecksum	OBJECT-TYPE
--    SYNTAX	OCTET STRING (SIZE(4))
--    MAX-ACCESS	read-only
--    STATUS	current
--    DESCRIPTION	"Firmware Checksum"
--    ::= { ver 5 }

-- **** MAC Address **** islTrango.p5m.sys.2

sysMAC		OBJECT-TYPE
    SYNTAX	OCTET STRING (SIZE(6))
    MAX-ACCESS	read-only
    STATUS	current
    DESCRIPTION "MAC Address"
    ::= { sys 2 }

-- **** Default Opmode **** islTrango.p5m.sys.3

sysDefaultOpmode	OBJECT-TYPE
    SYNTAX	INTEGER { on(1), off(0) }
    MAX-ACCESS	read-write
    STATUS	current
    DESCRIPTION "Default Opmode"
    ::= { sys 3 }

-- **** Current Opmode **** islTrango.p5m.sys.4

sysCurrentOpmode	OBJECT-TYPE
    SYNTAX	INTEGER { on(1), off(0) }
    MAX-ACCESS	read-only
    STATUS	current
    DESCRIPTION "Current Opmode"
    ::= { sys 4 }

sysActivateOpmode 	OBJECT-TYPE
    SYNTAX	INTEGER { deactivated(0), activated(1) }
    MAX-ACCESS	read-write
    STATUS	current
    DESCRIPTION	"Turn on opmode"
    ::= { sys 5 }

sysReadCommStr OBJECT-TYPE
    SYNTAX	DisplayString (SIZE (0..32))
    MAX-ACCESS  read-write
    STATUS  current
    DESCRIPTION	"SNMP agent read community string. It is used for authentication purpose."
    ::= { sys 6 }

sysWriteCommStr OBJECT-TYPE
    SYNTAX	DisplayString (SIZE (0..32))
    MAX-ACCESS	read-write
    STATUS	current
    DESCRIPTION	"SNMP agent write community string. It is used for authentication purpose."
    ::= { sys 7 }

-- **** Switches **** islTrango.p5m.sys.8

syssw		OBJECT IDENTIFIER ::= { sys 8 }

sysswTftpServerEnable OBJECT-TYPE
    SYNTAX  	INTEGER { disabled(0), enabled(1) }
    MAX-ACCESS  read-write
    STATUS  	current
    DESCRIPTION	"Enable or disable to receive code or fileset download."
    ::= { syssw 1 }

sysswAutoRateShiftingEnable OBJECT-TYPE
    SYNTAX  	INTEGER { disabled(0), enabled(1) }
    MAX-ACCESS  read-write
    STATUS  	current
    DESCRIPTION	"Switch to different speed rate automatically
		 to get the maximum throughput value."
    ::= { syssw 2 }

sysswAutoScanMUSignal OBJECT-TYPE
    SYNTAX  	INTEGER { disabled(0), enabled(1) }
    MAX-ACCESS  read-write
    STATUS	current
    DESCRIPTION	"Remote unit scans to all channel frequencies
		 to listen to its master's heart-beat (RU Only)."
    ::= { syssw 3 }

sysswRSSILEDFlashEnable OBJECT-TYPE
    SYNTAX  	INTEGER { disabled(0),  enabled(1) }
    MAX-ACCESS  read-write
    STATUS  	current
    DESCRIPTION	"Enabling RSSI LED to blink based on its current RSSI value."
    ::= { syssw 4 }

sysswARQEnable OBJECT-TYPE
    SYNTAX  	INTEGER { disabled(0),  enabled(1) }
    MAX-ACCESS  read-write
    STATUS  	current
    DESCRIPTION	"ARQ Enable (MU Only)"
    ::= { syssw 8 }

-- **** Traffic **** islTrango.p5m.sys.9

systraffic	OBJECT IDENTIFIER ::= { sys 9 }

systrafficEthInOctets OBJECT-TYPE
    SYNTAX  	Counter32
    MAX-ACCESS  read-only
    STATUS  	current
    DESCRIPTION	"Number of payload octets received on Ethernet port."
    ::= { systraffic 1 }

systrafficEthOutOctets	OBJECT-TYPE
    SYNTAX  	Counter32
    MAX-ACCESS  read-only
    STATUS  	current
    DESCRIPTION	"Number of payload octets transmitted on Ethernet port."
    ::= { systraffic 2 }

systrafficRfInOctets	OBJECT-TYPE
    SYNTAX  	Counter32
    MAX-ACCESS  read-only
    STATUS  	current
    DESCRIPTION	"Number of octets of remote's payload received from RF port."
    ::= { systraffic 3 }

systrafficRfOutOctets	OBJECT-TYPE
    SYNTAX  	Counter32
    MAX-ACCESS  read-only
    STATUS  	current
    DESCRIPTION	"Number of octets of remote's payload transmitted to RF port."
    ::= { systraffic 4 }

sysReserved1 OBJECT-TYPE
    SYNTAX  	INTEGER { no(0), yes(1) }
    MAX-ACCESS  read-write
    STATUS  	current
    DESCRIPTION "Save system setting values to Flash and activate the settings.
		 Not supported in this release."
    DEFVAL  { no }
    ::= { sys 11 }

sysReboot OBJECT-TYPE
    SYNTAX  	INTEGER { deactivated(0), activated(1) }
    MAX-ACCESS  read-write
    STATUS  	current
    DESCRIPTION "Reboot the master unit."
    DEFVAL { deactivated }
    ::= { sys 12 }

-- **** IPConfig **** islTrango.p5m.sys.13

sysipconfig	OBJECT IDENTIFIER ::= { sys 13 }

sysipconfigIpAddress OBJECT-TYPE
    SYNTAX  	IpAddress
--    MAX-ACCESS  read-only
    MAX-ACCESS  read-write
    STATUS  	current
    DESCRIPTION "IP address"
    ::= { sysipconfig 1 }

sysipconfigSubnet OBJECT-TYPE
    SYNTAX  	IpAddress
--    MAX-ACCESS  read-only
    MAX-ACCESS  read-write
    STATUS	current
    DESCRIPTION	"Subnet mask"
    ::= { sysipconfig 2 }

sysipconfigDefaultGateway OBJECT-TYPE
    SYNTAX  	IpAddress
--    MAX-ACCESS  read-only
    MAX-ACCESS  read-write
    STATUS  	current
    DESCRIPTION	"Default gateway"
    ::= { sysipconfig 3 }

sysipconfigChange OBJECT-TYPE
    SYNTAX  	DisplayString (SIZE(0..80))
    MAX-ACCESS  read-write
    STATUS  	current
    DESCRIPTION	"New IP Address, Subnet Mask and Default Gateway
	xxx.xxx.xxx.xxx xxx.xxx.xxx.xxx xxx.xxx.xxx.xxx"
    ::= { sysipconfig 4 }

-- ************************************************************
sysRemarks OBJECT-TYPE
    SYNTAX	DisplayString (SIZE (0..80))
    MAX-ACCESS	read-write
    STATUS	current
    DESCRIPTION	"Remarks"
    ::= { sys 14 }

-- ************************************************************
sysEncryptEnable OBJECT-TYPE
    SYNTAX  	INTEGER { disabled(0),  enabled(1) }
    MAX-ACCESS  read-write
    STATUS  	current
    DESCRIPTION	"Enable/Disable Encrypt"
    ::= { sys 15 }

sysEncryptKey OBJECT-TYPE
    SYNTAX	Opaque (SIZE (16))
    MAX-ACCESS	read-write
    STATUS	current
    DESCRIPTION	"Encrypt Key"
    ::= { sys 16 }

-- *******************************************************************
-- ** RF islTrango.p5m.rf
-- *******************************************************************
rf	OBJECT IDENTIFIER ::= { p5m 2 }

rfPeerDeviceID	OBJECT-TYPE
    SYNTAX	OCTET STRING (SIZE(4))
    MAX-ACCESS	read-write
    STATUS	current
    DESCRIPTION	"Device ID of Remote Unit"
    ::= { rf 1 }

rfActiveChannel OBJECT-TYPE
    SYNTAX  	INTEGER (1..24)
    MAX-ACCESS  read-write
    STATUS	current
    DESCRIPTION	"It specifies the current active channel number."
    ::= { rf 2 }

rfActivePolarization OBJECT-TYPE
    SYNTAX  	DisplayString (SIZE(1))
    MAX-ACCESS  read-write
    STATUS	current
    DESCRIPTION "It specifies the current polarization."
    ::= { rf 3 }

rfSpeed OBJECT-TYPE
    SYNTAX  	INTEGER (6 | 12 | 18 | 24 | 36 | 48 | 54)
    MAX-ACCESS  read-write
    STATUS	current
    DESCRIPTION	"It specifies the rf speed."
    ::= { rf 4 }

rfTxPower OBJECT-TYPE
    SYNTAX  	INTEGER (-30..40)
    MAX-ACCESS  read-write
    STATUS	current
    DESCRIPTION	"It specifies tx power. And it will be limited by Min/Max by different band"
    ::= { rf 5 }

rfTxMIR 	OBJECT-TYPE
    SYNTAX	INTEGER (100..50000)
    MAX-ACCESS	read-write
    STATUS	current
    DESCRIPTION	"Max Tx Information Rate in Kbps"
    ::= { rf 6 }

rfNumberOfChannel OBJECT-TYPE
    SYNTAX  	INTEGER (1..24)
    MAX-ACCESS  read-only
    STATUS  	current
    DESCRIPTION "number of Channel"
    ::= { rf 7 }

-- **** Channel Table **** islTrango.p5m.rf.5

rfChannelTable OBJECT-TYPE
    SYNTAX  	SEQUENCE OF ChannelTableEntry
    MAX-ACCESS  not-accessible
    STATUS  	current
    DESCRIPTION "Channel Table"
    ::= { rf 8 }

rfChannelTableEntry OBJECT-TYPE
    SYNTAX  	ChannelTableEntry
    MAX-ACCESS  not-accessible
    STATUS  	current
    DESCRIPTION "An entry of Channel Table."
    INDEX { rfChannelTableIndex }
    ::= { rfChannelTable 1 }

ChannelTableEntry ::=
    SEQUENCE {
        rfChannelTableIndex	INTEGER,
	rfChannelFrequency	INTEGER
    }

rfChannelTableIndex OBJECT-TYPE
    SYNTAX	INTEGER (1..24)
    MAX-ACCESS	not-accessible
    STATUS	current
    DESCRIPTION	"index of Channel Table"
    ::= { rfChannelTableEntry 1 }

rfChannelFrequency OBJECT-TYPE
    SYNTAX	INTEGER (5150..5875)
    MAX-ACCESS	read-write
    STATUS	current
    DESCRIPTION	"Frequency (MHz)"
    ::= { rfChannelTableEntry 2 }

-- *******************************************************************
-- *********************** Regulatory ********************************
-- *******************************************************************

rfAreaCode OBJECT-TYPE
    SYNTAX  	INTEGER
    MAX-ACCESS  read-only
    STATUS  	current
    DESCRIPTION "area code which specify band regulatory"
    ::= { rf 9 }

-- *******************************************************************

rfBandTable OBJECT-TYPE
    SYNTAX  	SEQUENCE OF BandTableEntry
    MAX-ACCESS  not-accessible
    STATUS  	current
    DESCRIPTION "4 Band Tables"
    ::= { rf 10 }

rfBandTableEntry OBJECT-TYPE
    SYNTAX  	BandTableEntry
    MAX-ACCESS  not-accessible
    STATUS  	current
    DESCRIPTION "An entry of Band Table."
    INDEX { rfBandTableIndex }
    ::= { rfBandTable 1 }

BandTableEntry ::=
    SEQUENCE {
        rfBandTableIndex	INTEGER,
	rfBandRangeMin		INTEGER,
	rfBandRangeMax		INTEGER,
	rfBandEnable		INTEGER,
	rfBandTxPowerMin	INTEGER,
	rfBandTxPowerMaxCCK	INTEGER,
	rfBandTxPowerMaxBPSK	INTEGER,
	rfBandTxPowerMaxQPSK	INTEGER,
	rfBandTxPowerMax16QAM	INTEGER,
	rfBandTxPowerMax64QAM	INTEGER
    }

rfBandTableIndex OBJECT-TYPE
    SYNTAX	INTEGER (1..4)
    MAX-ACCESS	not-accessible
    STATUS	current
    DESCRIPTION	"index of Band Table"
    ::= { rfBandTableEntry 1 }

rfBandRangeMin OBJECT-TYPE
    SYNTAX	INTEGER
    MAX-ACCESS	read-only
    STATUS	current
    DESCRIPTION	"Min Frequency of Band"
    ::= { rfBandTableEntry 2 }

rfBandRangeMax OBJECT-TYPE
    SYNTAX	INTEGER
    MAX-ACCESS	read-only
    STATUS	current
    DESCRIPTION	"Max Frequency of Band"
    ::= { rfBandTableEntry 3 }

rfBandEnable	OBJECT-TYPE
    SYNTAX	INTEGER { disabled(0),  enabled(1) }
    MAX-ACCESS	read-only
    STATUS	current
    DESCRIPTION	"Band availability"
    ::= { rfBandTableEntry 4 }

rfBandTxPowerMin OBJECT-TYPE
    SYNTAX	INTEGER (-128..127)
    MAX-ACCESS	read-only
    STATUS	current
    DESCRIPTION	"Min Tx Power"
    ::= { rfBandTableEntry 5 }

rfBandTxPowerMaxCCK OBJECT-TYPE
    SYNTAX	INTEGER (-128..127)
    MAX-ACCESS	read-only
    STATUS	current
    DESCRIPTION	"Max Tx Power for CCK"
    ::= { rfBandTableEntry 6 }

rfBandTxPowerMaxBPSK OBJECT-TYPE
    SYNTAX	INTEGER (-128..127)
    MAX-ACCESS	read-only
    STATUS	current
    DESCRIPTION	"Max Tx Power for BPSK"
    ::= { rfBandTableEntry 7 }

rfBandTxPowerMaxQPSK OBJECT-TYPE
    SYNTAX	INTEGER (-128..127)
    MAX-ACCESS	read-only
    STATUS	current
    DESCRIPTION	"Max Tx Power for QPSK"
    ::= { rfBandTableEntry 8 }

rfBandTxPowerMax16QAM OBJECT-TYPE
    SYNTAX	INTEGER (-128..127)
    MAX-ACCESS	read-only
    STATUS	current
    DESCRIPTION	"Max Tx Power for 16 QAM"
    ::= { rfBandTableEntry 9 }

rfBandTxPowerMax64QAM OBJECT-TYPE
    SYNTAX	INTEGER (-128..127)
    MAX-ACCESS	read-only
    STATUS	current
    DESCRIPTION	"Max Tx Power for 64 QAM"
    ::= { rfBandTableEntry 10 }

-- *******************************************************************

rfRSSI 	OBJECT-TYPE
    SYNTAX	INTEGER (-128..127)
    MAX-ACCESS  read-only
    STATUS  	current
    DESCRIPTION	"RSSI (in dBm)."
    ::= { rf 12 }

rfAssociated 	OBJECT-TYPE
    SYNTAX	INTEGER { no(0), yes(1) }
    MAX-ACCESS	read-only
    STATUS	current
    DESCRIPTION "Association Status"
    ::= { rf 13 }

-- *******************************************************************
-- ** RU Management islTrango.p5m.ru (MU Only)
-- *******************************************************************
ru	OBJECT IDENTIFIER ::= { p5m 3 }

ruReserved2 OBJECT-TYPE
    SYNTAX	INTEGER { deactivated(0), activated(1) }
    MAX-ACCESS	read-write
    STATUS	current
    DESCRIPTION	"Perform Power Leveling RU. Not supported in this release."
    ::= { ru 1 }

ruReserved3	OBJECT-TYPE
    SYNTAX	INTEGER { deactivated(0), activated(1) }
    MAX-ACCESS	read-write
    STATUS	current
    DESCRIPTION	"Reboot RU. Not supported in this release."
    ::= { ru 2 }

ruReserved4	OBJECT-TYPE
    SYNTAX	INTEGER ( 0..100 )
    MAX-ACCESS	read-only
    STATUS	current
    DESCRIPTION	"Distance of RU in mile. Not supported in this release."
    ::= { ru 3 }

-- *******************************************************************
-- ** MU/RU Notifications
-- *******************************************************************
trap		OBJECT IDENTIFIER ::= { p5m 4 }
maintenance	OBJECT IDENTIFIER ::= { p5m 5 }
trangoEvents    OBJECT IDENTIFIER ::= { p5m 6 }
trangoEventsV2	OBJECT IDENTIFIER ::= { trangoEvents 0 }

trapTrapDstTable OBJECT-TYPE
    SYNTAX      SEQUENCE OF TrapTrapDstEntry
    MAX-ACCESS  not-accessible
    STATUS      current
    DESCRIPTION "This table allows control of the reporting of traps
                 generated by monitoring the operation of master or remote."
    ::= { trap 1 }

trapTrapDstEntry OBJECT-TYPE
    SYNTAX      TrapTrapDstEntry
    MAX-ACCESS  not-accessible
    STATUS      current
    DESCRIPTION "Allows configuration of the reporting mechanisms for a particular event."
    INDEX { trapTrapDstIndex }
    ::= { trapTrapDstTable 1 }

TrapTrapDstEntry ::= SEQUENCE {
	trapTrapDstIndex      	INTEGER,
	trapTrapDstEnabling   	INTEGER
    }

trapTrapDstIndex OBJECT-TYPE
    SYNTAX      INTEGER (1..2)
    MAX-ACCESS  not-accessible
    STATUS      current
    DESCRIPTION "Event Index."
    ::= { trapTrapDstEntry 1 }

trapTrapDstEnabling OBJECT-TYPE
    SYNTAX  	INTEGER { disabled(0), enabled(1) }
    MAX-ACCESS	read-write
    STATUS      current
    DESCRIPTION "Enabled or Disabled sending trap."
    ::= { trapTrapDstEntry 2 }

trapTrapDstIpAddress OBJECT-TYPE
    SYNTAX      IpAddress
    MAX-ACCESS	read-write
    STATUS      current
    DESCRIPTION "The IP Address of a management station to send traps to."
    ::= { trap 2 }

trapTrapCommStr OBJECT-TYPE
    SYNTAX	DisplayString (SIZE (0..32))
    MAX-ACCESS	read-write
    STATUS      current
    DESCRIPTION "Trap community string."
    ::= { trap 3 }

maintenanceLinkControl OBJECT-TYPE
    SYNTAX	OCTET STRING (SIZE (0..80))
    MAX-ACCESS	read-write
    STATUS      current
    DESCRIPTION "Link Test Summary Data."
    ::= { maintenance 1 }

maintenanceSiteSurveySummary1 OBJECT-TYPE
    SYNTAX	OCTET STRING (SIZE (0..128))
    MAX-ACCESS	read-write
    STATUS      current
    DESCRIPTION "Site Survey Summary Data."
    ::= { maintenance 2 }

maintenanceServiceEnable OBJECT-TYPE
    SYNTAX  	INTEGER { start(1), stop(2), changed(3), boareset(4) }
    MAX-ACCESS  read-write
    STATUS  	current
    DESCRIPTION	"Enable or disable system service."
    ::= { maintenance 3 }

maintenanceSiteSurveySummary2 OBJECT-TYPE
    SYNTAX	OCTET STRING (SIZE (0..128))
    MAX-ACCESS	read-write
    STATUS      current
    DESCRIPTION "Site Survey Summary Data."
    ::= { maintenance 4 }

maintenanceSiteSurveySummary3 OBJECT-TYPE
    SYNTAX	OCTET STRING (SIZE (0..128))
    MAX-ACCESS	read-write
    STATUS      current
    DESCRIPTION "Site Survey Summary Data."
    ::= { maintenance 5 }

maintenanceSiteSurveySummary4 OBJECT-TYPE
    SYNTAX	OCTET STRING (SIZE (0..128))
    MAX-ACCESS	read-write
    STATUS      current
    DESCRIPTION "Site Survey Summary Data."
    ::= { maintenance 6 }

maintenanceSerialNumber OBJECT-TYPE
    SYNTAX	INTEGER
    MAX-ACCESS	read-write
    STATUS      current
    DESCRIPTION "Atlas Board Serial Number."
    ::= { maintenance 7 }

maintenanceUNIIMaxPower OBJECT-TYPE
    SYNTAX	INTEGER
    MAX-ACCESS	read-write
    STATUS      current
    DESCRIPTION "UNII Maximum Power."
    ::= { maintenance 8 }

masterEvent NOTIFICATION-TYPE
    OBJECTS {
	sysCurrentOpmode
    }
    STATUS	current
    DESCRIPTION "This notification signifies that the master unit generated a report."
    ::= { trangoEventsV2 1 }

remoteEvent NOTIFICATION-TYPE
    OBJECTS {
	-- TBD
        sysCurrentOpmode
    }
    STATUS	current
    DESCRIPTION "This notification signifies that the remote unit generated a report."
    ::= { trangoEventsV2 2 }

-- *******************************************************************
-- ** Groups and compliances
-- *******************************************************************
trangoConf      OBJECT IDENTIFIER ::= { p5m 7 }
trangoGroups    OBJECT IDENTIFIER ::= { trangoConf 1 }
trangoCompl     OBJECT IDENTIFIER ::= { trangoConf 2 }

eventReportingGroupV2 NOTIFICATION-GROUP
    NOTIFICATIONS {
	masterEvent,
        remoteEvent
    }
    STATUS	current
    DESCRIPTION "Notification group."
    ::= { trangoGroups 1 }

versionComplV2 MODULE-COMPLIANCE
    STATUS	current
    DESCRIPTION "The implementation requirements for Trango products that support SNMP."
    MODULE		-- this module
    MANDATORY-GROUPS {
	eventReportingGroupV2
    }
    ::= { trangoCompl 1 }

END
