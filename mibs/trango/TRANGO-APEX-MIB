TRANGO-APEX-MIB DEFINITIONS ::= BEGIN

IMPORTS
	MODULE-IDENTITY,
	OBJECT-TYPE,
	OBJECT-IDENTITY,
	Unsigned32,
	NOTIFICATION-TYPE,
	enterprises
		FROM SNMPv2-SMI

	MODULE-COMPLIANCE
		FROM SNMPv2-CONF;

-- *******************************************************************
-- * Trango module
-- *******************************************************************
trango		OBJECT IDENTIFIER ::= { enterprises 5454 }
tbw 		OBJECT IDENTIFIER ::= { trango 1 }
apex		OBJECT IDENTIFIER ::= { tbw 60 }

-- *******************************************************************
-- ** System Information ** trango.twb.baker.sys
-- *******************************************************************
-- sys		OBJECT IDENTIFIER ::= { giga 1 }
-- modem	OBJECT IDENTIFIER ::= { giga 2 }
-- rf		OBJECT IDENTIFIER ::= { giga 3 }
-- gige		OBJECT IDENTIFIER ::= { giga 4 }
-- t1e1		OBJECT IDENTIFIER ::= { giga 5 }
-- trangotrap	OBJECT IDENTIFIER ::= { giga 6 }

END
