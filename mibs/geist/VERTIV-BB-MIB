VERTIV-BB-MIB DEFINITIONS ::= BEGIN

IMPORTS

DisplayString FROM SNMPv2-TC
SnmpAdminString FROM SNMP-FRAMEWORK-MIB
MODULE-IDENTITY, OBJECT-TYPE, OBJECT-IDENTITY, enterprises, Integer32, Gauge32, NOTIFICATION-TYPE FROM SNMPv2-SMI
sysName FROM SNMPv2-MIB;

vertiv MODULE-IDENTITY
	LAST-UPDATED "201809100000Z"
	ORGANIZATION "Vertiv"
	CONTACT-INFO "support@geistglobal.com"
	DESCRIPTION "The MIB for Vertiv Products"
	REVISION "201809100000Z"
	DESCRIPTION "Modified for version 5 compliance"

	REVISION "201209110000Z"
	DESCRIPTION "Original version"
	::= { enterprises 21239 }

blackbird OBJECT IDENTIFIER
	::= { vertiv 5 }
watchdog100 OBJECT IDENTIFIER
	::= { blackbird 1 }

--###########################################################################################--
--deviceInfo--
--###########################################################################################--

deviceInfo OBJECT IDENTIFIER
	::= { watchdog100 1 }

productTitle OBJECT-TYPE
	SYNTAX SnmpAdminString
	MAX-ACCESS read-only
	STATUS current
	DESCRIPTION
		"Product name"
	::= { deviceInfo 1 }

productVersion OBJECT-TYPE
	SYNTAX SnmpAdminString
	MAX-ACCESS read-only
	STATUS current
	DESCRIPTION
		"Product version"
	::= { deviceInfo 2 }

productFriendlyName OBJECT-TYPE
	SYNTAX SnmpAdminString
	MAX-ACCESS read-only
	STATUS current
	DESCRIPTION
		"User-assigned name"
	::= { deviceInfo 3 }

productMacAddress OBJECT-TYPE
	SYNTAX OCTET STRING
	MAX-ACCESS read-only
	STATUS current
	DESCRIPTION
		"Product's unique MAC address"
	::= { deviceInfo 4 }

deviceCount OBJECT-TYPE
	SYNTAX Integer32(0..5)
	MAX-ACCESS read-only
	STATUS current
	DESCRIPTION
		"Total number of devices on unit"
	::= { deviceInfo 6 }

temperatureUnits OBJECT-TYPE
	SYNTAX INTEGER {
			fahrenheit(0),
			celsius(1)
		}
	MAX-ACCESS read-write
	STATUS current
	DESCRIPTION
		"Current units for temperature/dewpoint values:
		0 = Degrees Fahrenheit
		1 = Degrees Celsius"
	::= { deviceInfo 7 }

productModelNumber OBJECT-TYPE
	SYNTAX SnmpAdminString
	MAX-ACCESS read-only
	STATUS current
	DESCRIPTION
		"Product model number (factory-assigned)"
	::= { deviceInfo 8 }

productPartNumber OBJECT-TYPE
	SYNTAX SnmpAdminString
	MAX-ACCESS read-only
	STATUS current
	DESCRIPTION
		"Product part number (factory-assigned)"
	::= { deviceInfo 9 }

productSerialNumber OBJECT-TYPE
	SYNTAX SnmpAdminString
	MAX-ACCESS read-only
	STATUS current
	DESCRIPTION
		"Product serial number (factory-assigned)"
	::= { deviceInfo 10 }

productPlatform OBJECT-TYPE
	SYNTAX SnmpAdminString
	MAX-ACCESS read-only
	STATUS current
	DESCRIPTION
		"Product platform"
	::= { deviceInfo 11 }

--###########################################################################################--
--internalTable--
--###########################################################################################--

internalTable OBJECT-TYPE
	SYNTAX SEQUENCE OF InternalEntry
	MAX-ACCESS  not-accessible
	STATUS current
	DESCRIPTION
		"Internal sensors for units"
	::= { watchdog100 2 }

internalEntry OBJECT-TYPE
	SYNTAX InternalEntry
	MAX-ACCESS  not-accessible
	STATUS current
	DESCRIPTION
		"Entry in the internalTable table: each entry contains an index and other sensor details"
	INDEX { internalIndex }
	::= { internalTable 1 }

InternalEntry ::= SEQUENCE {
	internalIndex				Integer32,
	internalSerial				DisplayString,
	internalLabel				SnmpAdminString,
	internalAvail				Gauge32,
	internalTemp				Integer32,
	internalHumidity				Integer32,
	internalDewPoint				Integer32,
	internalIO1				Integer32,
	internalIO2				Integer32,
	internalIO3				Integer32,
	internalIO4				Integer32,
	internalRelayState				Gauge32
}

internalIndex OBJECT-TYPE
	SYNTAX Integer32(1..100)
	MAX-ACCESS read-only
	STATUS current
	DESCRIPTION
		"Table entry index value"
	::= { internalEntry 1 }

internalSerial OBJECT-TYPE
	SYNTAX DisplayString
	MAX-ACCESS read-only
	STATUS current
	DESCRIPTION
		"Serial Number"
	::= { internalEntry 2 }

internalLabel OBJECT-TYPE
	SYNTAX SnmpAdminString(SIZE (0..25))
	MAX-ACCESS read-write
	STATUS current
	DESCRIPTION
		"User-defined label"
	::= { internalEntry 3 }

internalAvail OBJECT-TYPE
	SYNTAX Gauge32
	MAX-ACCESS read-only
	STATUS current
	DESCRIPTION
		"Device availability. 0 = Unavailable, 1 = Available, 2 = Partially Unavailable"
	::= { internalEntry 4 }

internalTemp OBJECT-TYPE
	SYNTAX Integer32(-40..200)
	UNITS "0.1 Degrees"
	MAX-ACCESS read-only
	STATUS current
	DESCRIPTION
		"Current reading for Temperature in tenths of degrees. Units are given by temperatureUnits field in deviceInfo"
	::= { internalEntry 5 }

internalHumidity OBJECT-TYPE
	SYNTAX Integer32(0..100)
	UNITS "%"
	MAX-ACCESS read-only
	STATUS current
	DESCRIPTION
		"Humidity reading"
	::= { internalEntry 6 }

internalDewPoint OBJECT-TYPE
	SYNTAX Integer32(-40..200)
	UNITS "0.1 Degrees"
	MAX-ACCESS read-only
	STATUS current
	DESCRIPTION
		"Current reading for Dew-point in tenths of degrees. Units are given by temperatureUnits field in deviceInfo"
	::= { internalEntry 7 }

internalIO1 OBJECT-TYPE
	SYNTAX Integer32(0..100)
	MAX-ACCESS read-only
	STATUS current
	DESCRIPTION
		"Current reading for Analog Input 1"
	::= { internalEntry 8 }

internalIO2 OBJECT-TYPE
	SYNTAX Integer32(0..100)
	MAX-ACCESS read-only
	STATUS current
	DESCRIPTION
		"Current reading for Analog Input 2"
	::= { internalEntry 9 }

internalIO3 OBJECT-TYPE
	SYNTAX Integer32(0..100)
	MAX-ACCESS read-only
	STATUS current
	DESCRIPTION
		"Current reading for Analog Input 3"
	::= { internalEntry 10 }

internalIO4 OBJECT-TYPE
	SYNTAX Integer32(0..100)
	MAX-ACCESS read-only
	STATUS current
	DESCRIPTION
		"Current reading for Analog Input 4"
	::= { internalEntry 11 }

internalRelayState OBJECT-TYPE
	SYNTAX Gauge32
	MAX-ACCESS read-only
	STATUS current
	DESCRIPTION
		"Is the relay on?"
	::= { internalEntry 12 }

--###########################################################################################--
--tempSensorTable--
--###########################################################################################--

tempSensorTable OBJECT-TYPE
	SYNTAX SEQUENCE OF TempSensorEntry
	MAX-ACCESS  not-accessible
	STATUS current
	DESCRIPTION
		"Remote Temperature (RT) sensor"
	::= { watchdog100 4 }

tempSensorEntry OBJECT-TYPE
	SYNTAX TempSensorEntry
	MAX-ACCESS  not-accessible
	STATUS current
	DESCRIPTION
		"Entry in the tempSensorTable table: each entry contains an index and other sensor details"
	INDEX { tempSensorIndex }
	::= { tempSensorTable 1 }

TempSensorEntry ::= SEQUENCE {
	tempSensorIndex				Integer32,
	tempSensorSerial				DisplayString,
	tempSensorLabel				SnmpAdminString,
	tempSensorAvail				Gauge32,
	tempSensorTemp				Integer32
}

tempSensorIndex OBJECT-TYPE
	SYNTAX Integer32(1..100)
	MAX-ACCESS not-accessible
	STATUS current
	DESCRIPTION
		"Table entry index value"
	::= { tempSensorEntry 1 }

tempSensorSerial OBJECT-TYPE
	SYNTAX DisplayString
	MAX-ACCESS read-only
	STATUS current
	DESCRIPTION
		"Serial Number"
	::= { tempSensorEntry 2 }

tempSensorLabel OBJECT-TYPE
	SYNTAX SnmpAdminString(SIZE (0..25))
	MAX-ACCESS read-write
	STATUS current
	DESCRIPTION
		"User-defined label"
	::= { tempSensorEntry 3 }

tempSensorAvail OBJECT-TYPE
	SYNTAX Gauge32
	MAX-ACCESS read-only
	STATUS current
	DESCRIPTION
		"Device availability:
		0 = Unavailable
		1 = Available
		2 = Partially Unavailable"
	::= { tempSensorEntry 4 }

tempSensorTemp OBJECT-TYPE
	SYNTAX Integer32(-400..2540)
	UNITS "decidegrees"
	MAX-ACCESS read-only
	STATUS current
	DESCRIPTION
		"Temperature in tenths of a degree. Units are given by temperatureUnits field in deviceInfo."
	::= { tempSensorEntry 5 }

--###########################################################################################--
--airFlowSensorTable--
--###########################################################################################--

airFlowSensorTable OBJECT-TYPE
	SYNTAX SEQUENCE OF AirFlowSensorEntry
	MAX-ACCESS  not-accessible
	STATUS current
	DESCRIPTION
		"Remote Airflow, Humidity, Temperature and Dewpoint (AFHT3) Sensor"
	::= { watchdog100 5 }

airFlowSensorEntry OBJECT-TYPE
	SYNTAX AirFlowSensorEntry
	MAX-ACCESS  not-accessible
	STATUS current
	DESCRIPTION
		"Entry in the airFlowSensorTable table: each entry contains an index and other sensor details"
	INDEX { airFlowSensorIndex }
	::= { airFlowSensorTable 1 }

AirFlowSensorEntry ::= SEQUENCE {
	airFlowSensorIndex				Integer32,
	airFlowSensorSerial				DisplayString,
	airFlowSensorLabel				SnmpAdminString,
	airFlowSensorAvail				Gauge32,
	airFlowSensorTemp				Integer32,
	airFlowSensorFlow				Integer32,
	airFlowSensorHumidity				Integer32,
	airFlowSensorDewPoint				Integer32
}

airFlowSensorIndex OBJECT-TYPE
	SYNTAX Integer32(1..100)
	MAX-ACCESS not-accessible
	STATUS current
	DESCRIPTION
		"Table entry index value"
	::= { airFlowSensorEntry 1 }

airFlowSensorSerial OBJECT-TYPE
	SYNTAX DisplayString
	MAX-ACCESS read-only
	STATUS current
	DESCRIPTION
		"Serial Number"
	::= { airFlowSensorEntry 2 }

airFlowSensorLabel OBJECT-TYPE
	SYNTAX SnmpAdminString(SIZE (0..25))
	MAX-ACCESS read-write
	STATUS current
	DESCRIPTION
		"User-defined label"
	::= { airFlowSensorEntry 3 }

airFlowSensorAvail OBJECT-TYPE
	SYNTAX Gauge32
	MAX-ACCESS read-only
	STATUS current
	DESCRIPTION
		"Device availability:
		0 = Unavailable
		1 = Available
		2 = Partially Unavailable"
	::= { airFlowSensorEntry 4 }

airFlowSensorTemp OBJECT-TYPE
	SYNTAX Integer32(-400..2540)
	UNITS "decidegrees"
	MAX-ACCESS read-only
	STATUS current
	DESCRIPTION
		"Current reading for Temperature in tenths of degrees. Units are given by temperatureUnits field in deviceInfo"
	::= { airFlowSensorEntry 5 }

airFlowSensorFlow OBJECT-TYPE
	SYNTAX Integer32(0..100)
	MAX-ACCESS read-only
	STATUS current
	DESCRIPTION
		" Airflow reading. Still air will be less than 20, while rushing air will be around 100."
	::= { airFlowSensorEntry 6 }

airFlowSensorHumidity OBJECT-TYPE
	SYNTAX Integer32(0..100)
	UNITS "%"
	MAX-ACCESS read-only
	STATUS current
	DESCRIPTION
		"Humidity reading"
	::= { airFlowSensorEntry 7 }

airFlowSensorDewPoint OBJECT-TYPE
	SYNTAX Integer32(-400..2540)
	UNITS "decidegrees"
	MAX-ACCESS read-only
	STATUS current
	DESCRIPTION
		" Dewpoint reading in tenths of a degree. Units are given by temperatureUnits field in deviceInfo."
	::= { airFlowSensorEntry 8 }

--###########################################################################################--
--dewPointSensorTable--
--###########################################################################################--

dewPointSensorTable OBJECT-TYPE
	SYNTAX SEQUENCE OF DewPointSensorEntry
	MAX-ACCESS  not-accessible
	STATUS current
	DESCRIPTION
		"Remote Dew Point sensor"
	::= { watchdog100 6 }

dewPointSensorEntry OBJECT-TYPE
	SYNTAX DewPointSensorEntry
	MAX-ACCESS  not-accessible
	STATUS current
	DESCRIPTION
		"Entry in the dewPointSensorTable table: each entry contains an index and other sensor details"
	INDEX { dewPointSensorIndex }
	::= { dewPointSensorTable 1 }

DewPointSensorEntry ::= SEQUENCE {
	dewPointSensorIndex				Integer32,
	dewPointSensorSerial				DisplayString,
	dewPointSensorName				DisplayString,
	dewPointSensorAvail				Gauge32,
	dewPointSensorTemp				Integer32,
	dewPointSensorHumidity				Integer32,
	dewPointSensorDewPoint				Integer32
}

dewPointSensorIndex OBJECT-TYPE
	SYNTAX Integer32(1..100)
	MAX-ACCESS not-accessible
	STATUS current
	DESCRIPTION
		"Table entry index value"
	::= { dewPointSensorEntry 1 }

dewPointSensorSerial OBJECT-TYPE
	SYNTAX DisplayString
	MAX-ACCESS read-only
	STATUS current
	DESCRIPTION
		"Serial Number"
	::= { dewPointSensorEntry 2 }

dewPointSensorName OBJECT-TYPE
	SYNTAX DisplayString
	MAX-ACCESS read-only
	STATUS current
	DESCRIPTION
		"User-defined label"
	::= { dewPointSensorEntry 3 }

dewPointSensorAvail OBJECT-TYPE
	SYNTAX Gauge32
	MAX-ACCESS read-only
	STATUS current
	DESCRIPTION
		"Device availability:
		0 = Unavailable
		1 = Available
		2 = Partially Unavailable"
	::= { dewPointSensorEntry 4 }

dewPointSensorTemp OBJECT-TYPE
	SYNTAX Integer32(-40..200)
	UNITS "decidegrees"
	MAX-ACCESS read-only
	STATUS current
	DESCRIPTION
		"Current reading for Temperature in tenths of degrees. Units are given by temperatureUnits field in deviceInfo"
	::= { dewPointSensorEntry 5 }

dewPointSensorHumidity OBJECT-TYPE
	SYNTAX Integer32(0..100)
	UNITS "%"
	MAX-ACCESS read-only
	STATUS current
	DESCRIPTION
		"Humidity reading"
	::= { dewPointSensorEntry 6 }

dewPointSensorDewPoint OBJECT-TYPE
	SYNTAX Integer32(-40..200)
	UNITS "decidegrees"
	MAX-ACCESS read-only
	STATUS current
	DESCRIPTION
		"Current reading for Dew-point in tenths of degrees. Units are given by temperatureUnits field in deviceInfo"
	::= { dewPointSensorEntry 7 }

--###########################################################################################--
--ccatSensorTable--
--###########################################################################################--

ccatSensorTable OBJECT-TYPE
	SYNTAX SEQUENCE OF CcatSensorEntry
	MAX-ACCESS  not-accessible
	STATUS current
	DESCRIPTION
		"Remote CCAT sensor"
	::= { watchdog100 7 }

ccatSensorEntry OBJECT-TYPE
	SYNTAX CcatSensorEntry
	MAX-ACCESS  not-accessible
	STATUS current
	DESCRIPTION
		"Entry in the ccatSensorTable table: each entry contains an index and other sensor details"
	INDEX { ccatSensorIndex }
	::= { ccatSensorTable 1 }

CcatSensorEntry ::= SEQUENCE {
	ccatSensorIndex				Integer32,
	ccatSensorSerial				DisplayString,
	ccatSensorName				DisplayString,
	ccatSensorAvail				Gauge32,
	ccatSensorValue				Integer32,
	ccatSensorType				DisplayString,
	ccatSensorDescription				DisplayString
}

ccatSensorIndex OBJECT-TYPE
	SYNTAX Integer32(1..100)
	MAX-ACCESS not-accessible
	STATUS current
	DESCRIPTION
		"Table entry index value"
	::= { ccatSensorEntry 1 }

ccatSensorSerial OBJECT-TYPE
	SYNTAX DisplayString
	MAX-ACCESS read-only
	STATUS current
	DESCRIPTION
		"Serial Number"
	::= { ccatSensorEntry 2 }

ccatSensorName OBJECT-TYPE
	SYNTAX DisplayString
	MAX-ACCESS read-only
	STATUS current
	DESCRIPTION
		"User-defined label"
	::= { ccatSensorEntry 3 }

ccatSensorAvail OBJECT-TYPE
	SYNTAX Gauge32
	MAX-ACCESS read-only
	STATUS current
	DESCRIPTION
		"Device availability:
		0 = Unavailable
		1 = Available
		2 = Partially Unavailable"
	::= { ccatSensorEntry 4 }

ccatSensorValue OBJECT-TYPE
	SYNTAX Integer32(-100..5000)
	MAX-ACCESS read-only
	STATUS current
	DESCRIPTION
		"CCAT sensor reading"
	::= { ccatSensorEntry 5 }

ccatSensorType OBJECT-TYPE
	SYNTAX DisplayString
	MAX-ACCESS read-only
	STATUS current
	DESCRIPTION
		"CCAT sensor type"
	::= { ccatSensorEntry 6 }

ccatSensorDescription OBJECT-TYPE
	SYNTAX DisplayString
	MAX-ACCESS read-only
	STATUS current
	DESCRIPTION
		"CCAT sensor value description"
	::= { ccatSensorEntry 7 }

--###########################################################################################--
--t3hdSensorTable--
--###########################################################################################--

t3hdSensorTable OBJECT-TYPE
	SYNTAX SEQUENCE OF T3hdSensorEntry
	MAX-ACCESS  not-accessible
	STATUS current
	DESCRIPTION
		"Remote Temperature x 3, Humidity and Dewpoint Sensor"
	::= { watchdog100 8 }

t3hdSensorEntry OBJECT-TYPE
	SYNTAX T3hdSensorEntry
	MAX-ACCESS  not-accessible
	STATUS current
	DESCRIPTION
		"Entry in the t3hdSensorTable table: each entry contains an index and other sensor details"
	INDEX { t3hdSensorIndex }
	::= { t3hdSensorTable 1 }

T3hdSensorEntry ::= SEQUENCE {
	t3hdSensorIndex				Integer32,
	t3hdSensorSerial				DisplayString,
	t3hdSensorLabel				SnmpAdminString,
	t3hdSensorAvail				Gauge32,
	t3hdSensorIntLabel				SnmpAdminString,
	t3hdSensorIntTemp				Integer32,
	t3hdSensorIntHumidity				Integer32,
	t3hdSensorIntDewPoint				Integer32,
	t3hdSensorExtAAvail				Gauge32,
	t3hdSensorExtALabel				SnmpAdminString,
	t3hdSensorExtATemp				Integer32,
	t3hdSensorExtBAvail				Gauge32,
	t3hdSensorExtBLabel				SnmpAdminString,
	t3hdSensorExtBTemp				Integer32
}

t3hdSensorIndex OBJECT-TYPE
	SYNTAX Integer32(1..100)
	MAX-ACCESS not-accessible
	STATUS current
	DESCRIPTION
		"Table entry index value"
	::= { t3hdSensorEntry 1 }

t3hdSensorSerial OBJECT-TYPE
	SYNTAX DisplayString
	MAX-ACCESS read-only
	STATUS current
	DESCRIPTION
		"Serial Number"
	::= { t3hdSensorEntry 2 }

t3hdSensorLabel OBJECT-TYPE
	SYNTAX SnmpAdminString(SIZE (0..25))
	MAX-ACCESS read-write
	STATUS current
	DESCRIPTION
		"User-defined label"
	::= { t3hdSensorEntry 3 }

t3hdSensorAvail OBJECT-TYPE
	SYNTAX Gauge32
	MAX-ACCESS read-only
	STATUS current
	DESCRIPTION
		"Device availability:
		0 = Unavailable
		1 = Available
		2 = Partially Unavailable"
	::= { t3hdSensorEntry 4 }

t3hdSensorIntLabel OBJECT-TYPE
	SYNTAX SnmpAdminString(SIZE (0..25))
	MAX-ACCESS read-write
	STATUS current
	DESCRIPTION
		"Internal label (user-defined)"
	::= { t3hdSensorEntry 5 }

t3hdSensorIntTemp OBJECT-TYPE
	SYNTAX Integer32(-400..2540)
	UNITS "decidegrees"
	MAX-ACCESS read-only
	STATUS current
	DESCRIPTION
		"Internal temperature in tenths of a degree. Units are given by temperatureUnits field in deviceInfo."
	::= { t3hdSensorEntry 6 }

t3hdSensorIntHumidity OBJECT-TYPE
	SYNTAX Integer32(0..100)
	UNITS "%"
	MAX-ACCESS read-only
	STATUS current
	DESCRIPTION
		"Internal Humidity"
	::= { t3hdSensorEntry 7 }

t3hdSensorIntDewPoint OBJECT-TYPE
	SYNTAX Integer32(-400..2540)
	UNITS "decidegrees"
	MAX-ACCESS read-only
	STATUS current
	DESCRIPTION
		"Internal dewpoint in tenths of a degree. Units are given by temperatureUnits field in deviceInfo."
	::= { t3hdSensorEntry 8 }

t3hdSensorExtAAvail OBJECT-TYPE
	SYNTAX Gauge32
	MAX-ACCESS read-only
	STATUS current
	DESCRIPTION
		"External A status:
		0 =Unavailable
		1 =Available"
	::= { t3hdSensorEntry 9 }

t3hdSensorExtALabel OBJECT-TYPE
	SYNTAX SnmpAdminString(SIZE (0..25))
	MAX-ACCESS read-write
	STATUS current
	DESCRIPTION
		"External A label (user-defined)"
	::= { t3hdSensorEntry 10 }

t3hdSensorExtATemp OBJECT-TYPE
	SYNTAX Integer32(-400..2540)
	UNITS "decidegrees"
	MAX-ACCESS read-only
	STATUS current
	DESCRIPTION
		" External A temperature in tenths of a degree. Units are given by temperatureUnits field in deviceInfo."
	::= { t3hdSensorEntry 11 }

t3hdSensorExtBAvail OBJECT-TYPE
	SYNTAX Gauge32
	MAX-ACCESS read-only
	STATUS current
	DESCRIPTION
		"External B status:
		0 = Unavailable
		1 = Available"
	::= { t3hdSensorEntry 12 }

t3hdSensorExtBLabel OBJECT-TYPE
	SYNTAX SnmpAdminString(SIZE (0..25))
	MAX-ACCESS read-write
	STATUS current
	DESCRIPTION
		"External B label (user-defined)"
	::= { t3hdSensorEntry 13 }

t3hdSensorExtBTemp OBJECT-TYPE
	SYNTAX Integer32(-400..2540)
	UNITS "decidegrees"
	MAX-ACCESS read-only
	STATUS current
	DESCRIPTION
		"External B temperature in tenths of a degree. Units are given by temperatureUnits field in deviceInfo."
	::= { t3hdSensorEntry 14 }

--###########################################################################################--
--thdSensorTable--
--###########################################################################################--

thdSensorTable OBJECT-TYPE
	SYNTAX SEQUENCE OF ThdSensorEntry
	MAX-ACCESS  not-accessible
	STATUS current
	DESCRIPTION
		"Remote Temperature, Humidity and Dewpoint (THD) Sensor"
	::= { watchdog100 9 }

thdSensorEntry OBJECT-TYPE
	SYNTAX ThdSensorEntry
	MAX-ACCESS  not-accessible
	STATUS current
	DESCRIPTION
		"Entry in the thdSensorTable table: each entry contains an index and other sensor details"
	INDEX { thdSensorIndex }
	::= { thdSensorTable 1 }

ThdSensorEntry ::= SEQUENCE {
	thdSensorIndex				Integer32,
	thdSensorSerial				DisplayString,
	thdSensorLabel				SnmpAdminString,
	thdSensorAvail				Gauge32,
	thdSensorTemp				Integer32,
	thdSensorHumidity				Integer32,
	thdSensorDewPoint				Integer32
}

thdSensorIndex OBJECT-TYPE
	SYNTAX Integer32(1..100)
	MAX-ACCESS not-accessible
	STATUS current
	DESCRIPTION
		"Table entry index value"
	::= { thdSensorEntry 1 }

thdSensorSerial OBJECT-TYPE
	SYNTAX DisplayString
	MAX-ACCESS read-only
	STATUS current
	DESCRIPTION
		"Serial Number"
	::= { thdSensorEntry 2 }

thdSensorLabel OBJECT-TYPE
	SYNTAX SnmpAdminString(SIZE (0..25))
	MAX-ACCESS read-write
	STATUS current
	DESCRIPTION
		"User-defined label"
	::= { thdSensorEntry 3 }

thdSensorAvail OBJECT-TYPE
	SYNTAX Gauge32
	MAX-ACCESS read-only
	STATUS current
	DESCRIPTION
		"Device availability:
		0 = Unavailable
		1 = Available
		2 = Partially Unavailable"
	::= { thdSensorEntry 4 }

thdSensorTemp OBJECT-TYPE
	SYNTAX Integer32(-400..2540)
	UNITS "decidegrees"
	MAX-ACCESS read-only
	STATUS current
	DESCRIPTION
		" Temperature value in tenths of a degree. Units are given by temperatureUnits field in deviceInfo."
	::= { thdSensorEntry 5 }

thdSensorHumidity OBJECT-TYPE
	SYNTAX Integer32(0..100)
	UNITS "%"
	MAX-ACCESS read-only
	STATUS current
	DESCRIPTION
		"Humidity value"
	::= { thdSensorEntry 6 }

thdSensorDewPoint OBJECT-TYPE
	SYNTAX Integer32(-400..2540)
	UNITS "decidegrees"
	MAX-ACCESS read-only
	STATUS current
	DESCRIPTION
		"Dewpoint value in tenths of a degree. Units are given by temperatureUnits field in deviceInfo."
	::= { thdSensorEntry 7 }

--###########################################################################################--
--rpmSensorTable--
--###########################################################################################--

rpmSensorTable OBJECT-TYPE
	SYNTAX SEQUENCE OF RpmSensorEntry
	MAX-ACCESS  not-accessible
	STATUS current
	DESCRIPTION
		"Remote Power Manager Sensor"
	::= { watchdog100 10 }

rpmSensorEntry OBJECT-TYPE
	SYNTAX RpmSensorEntry
	MAX-ACCESS  not-accessible
	STATUS current
	DESCRIPTION
		"Entry in the rpmSensorTable table: each entry contains an index and other sensor details"
	INDEX { rpmSensorIndex }
	::= { rpmSensorTable 1 }

RpmSensorEntry ::= SEQUENCE {
	rpmSensorIndex				Integer32,
	rpmSensorSerial				DisplayString,
	rpmSensorName				DisplayString,
	rpmSensorAvail				Gauge32,
	rpmSensorEnergy				Gauge32,
	rpmSensorVoltage				Gauge32,
	rpmSensorVoltageMax				Gauge32,
	rpmSensorVoltageMin				Gauge32,
	rpmSensorVoltagePeak				Gauge32,
	rpmSensorCurrent				Gauge32,
	rpmSensorRealPower				Gauge32,
	rpmSensorApparentPower				Gauge32,
	rpmSensorPowerFactor				Gauge32,
	rpmSensorOutlet1				Gauge32,
	rpmSensorOutlet2				Gauge32
}

rpmSensorIndex OBJECT-TYPE
	SYNTAX Integer32(1..100)
	MAX-ACCESS not-accessible
	STATUS current
	DESCRIPTION
		"Table entry index value"
	::= { rpmSensorEntry 1 }

rpmSensorSerial OBJECT-TYPE
	SYNTAX DisplayString
	MAX-ACCESS read-only
	STATUS current
	DESCRIPTION
		"Serial Number"
	::= { rpmSensorEntry 2 }

rpmSensorName OBJECT-TYPE
	SYNTAX DisplayString
	MAX-ACCESS read-only
	STATUS current
	DESCRIPTION
		"Friendly Name"
	::= { rpmSensorEntry 3 }

rpmSensorAvail OBJECT-TYPE
	SYNTAX Gauge32
	MAX-ACCESS read-only
	STATUS current
	DESCRIPTION
		"Device availability
		0 = Unavailable
		1 = Available
		2 = Partially Unavailable"
	::= { rpmSensorEntry 4 }

rpmSensorEnergy OBJECT-TYPE
	SYNTAX Gauge32
	UNITS "kWh"
	MAX-ACCESS read-only
	STATUS current
	DESCRIPTION
		"RPM Sensor Accumulated Energy"
	::= { rpmSensorEntry 5 }

rpmSensorVoltage OBJECT-TYPE
	SYNTAX Gauge32
	UNITS "Volts (rms)"
	MAX-ACCESS read-only
	STATUS current
	DESCRIPTION
		"RPM Sensor Voltage"
	::= { rpmSensorEntry 6 }

rpmSensorVoltageMax OBJECT-TYPE
	SYNTAX Gauge32
	UNITS "Volts (rms)"
	MAX-ACCESS read-only
	STATUS current
	DESCRIPTION
		"RPM Sensor Voltage (Max)"
	::= { rpmSensorEntry 7 }

rpmSensorVoltageMin OBJECT-TYPE
	SYNTAX Gauge32
	UNITS "Volts (rms)"
	MAX-ACCESS read-only
	STATUS current
	DESCRIPTION
		"RPM Sensor Voltage (Min)"
	::= { rpmSensorEntry 8 }

rpmSensorVoltagePeak OBJECT-TYPE
	SYNTAX Gauge32
	UNITS "Volts"
	MAX-ACCESS read-only
	STATUS current
	DESCRIPTION
		"RPM Sensor Voltage (Peak)"
	::= { rpmSensorEntry 9 }

rpmSensorCurrent OBJECT-TYPE
	SYNTAX Gauge32
	UNITS "0.1 Amps (rms)"
	MAX-ACCESS read-only
	STATUS current
	DESCRIPTION
		"RPM Sensor Current reading in deciAmps"
	::= { rpmSensorEntry 10 }

rpmSensorRealPower OBJECT-TYPE
	SYNTAX Gauge32
	UNITS "Watts"
	MAX-ACCESS read-only
	STATUS current
	DESCRIPTION
		"RPM Sensor Real Power"
	::= { rpmSensorEntry 11 }

rpmSensorApparentPower OBJECT-TYPE
	SYNTAX Gauge32
	UNITS "Volt-Amps"
	MAX-ACCESS read-only
	STATUS current
	DESCRIPTION
		"RPM Sensor Apparent Power"
	::= { rpmSensorEntry 12 }

rpmSensorPowerFactor OBJECT-TYPE
	SYNTAX Gauge32
	UNITS "%"
	MAX-ACCESS read-only
	STATUS current
	DESCRIPTION
		"RPM Sensor Power Factor"
	::= { rpmSensorEntry 13 }

rpmSensorOutlet1 OBJECT-TYPE
	SYNTAX Gauge32
	MAX-ACCESS read-only
	STATUS current
	DESCRIPTION
		"RPM Sensor Outlet 1 State: 0 = off, 1 = on"
	::= { rpmSensorEntry 14 }

rpmSensorOutlet2 OBJECT-TYPE
	SYNTAX Gauge32
	MAX-ACCESS read-only
	STATUS current
	DESCRIPTION
		"RPM Sensor Outlet 2 State:
		0 = off
		1 = on"
	::= { rpmSensorEntry 15 }

--###########################################################################################--
--a2dSensorTable--
--###########################################################################################--

a2dSensorTable OBJECT-TYPE
	SYNTAX SEQUENCE OF A2dSensorEntry
	MAX-ACCESS  not-accessible
	STATUS current
	DESCRIPTION
		"Analog measurement (A2D) sensor (voltage, current, or dry-contact)"
	::= { watchdog100 11 }

a2dSensorEntry OBJECT-TYPE
	SYNTAX A2dSensorEntry
	MAX-ACCESS  not-accessible
	STATUS current
	DESCRIPTION
		"Entry in the a2dSensorTable table: each entry contains an index and other sensor details"
	INDEX { a2dSensorIndex }
	::= { a2dSensorTable 1 }

A2dSensorEntry ::= SEQUENCE {
	a2dSensorIndex				Integer32,
	a2dSensorSerial				DisplayString,
	a2dSensorLabel				SnmpAdminString,
	a2dSensorAvail				Gauge32,
	a2dSensorValue				Integer32,
	a2dSensorDisplayValue				SnmpAdminString,
	a2dSensorMode				INTEGER,
	a2dSensorUnits				SnmpAdminString,
	a2dSensorMin				Integer32,
	a2dSensorMax				Integer32,
	a2dSensorLowLabel				SnmpAdminString,
	a2dSensorHighLabel				SnmpAdminString,
	a2dSensorAnalogLabel				SnmpAdminString
}

a2dSensorIndex OBJECT-TYPE
	SYNTAX Integer32(1..100)
	MAX-ACCESS not-accessible
	STATUS current
	DESCRIPTION
		"Table entry index value"
	::= { a2dSensorEntry 1 }

a2dSensorSerial OBJECT-TYPE
	SYNTAX DisplayString
	MAX-ACCESS read-only
	STATUS current
	DESCRIPTION
		"Serial Number"
	::= { a2dSensorEntry 2 }

a2dSensorLabel OBJECT-TYPE
	SYNTAX SnmpAdminString(SIZE (0..25))
	MAX-ACCESS read-write
	STATUS current
	DESCRIPTION
		"User-defined label"
	::= { a2dSensorEntry 3 }

a2dSensorAvail OBJECT-TYPE
	SYNTAX Gauge32
	MAX-ACCESS read-only
	STATUS current
	DESCRIPTION
		"Device availability:
		0 = Unavailable
		1 = Available
		2 = Partially Unavailable"
	::= { a2dSensorEntry 4 }

a2dSensorValue OBJECT-TYPE
	SYNTAX Integer32(-1000000..1000000)
	MAX-ACCESS read-only
	STATUS current
	DESCRIPTION
		"Analog measurement value, within either a user-defined or preset range, depending on a2dSensorMode."
	::= { a2dSensorEntry 5 }

a2dSensorDisplayValue OBJECT-TYPE
	SYNTAX SnmpAdminString(SIZE (0..25))
	MAX-ACCESS read-only
	STATUS current
	DESCRIPTION
		" For current/voltage modes, the analog value is given as a string. In binary modes, the value is either a2dSensorLowLabel or a2dSensorHighLabel, based on a2dSensorValue."
	::= { a2dSensorEntry 6 }

a2dSensorMode OBJECT-TYPE
	SYNTAX INTEGER {
			door(1),
			powerFailure(2),
			flood(3),
			wscLeak(4),
			wscFault(5),
			smoke(6),
			ivsNegGnd(7),
			ivsPosGnd(8),
			customVoltage(9),
			customBinary(10),
			customCurrent(11)
			}
	MAX-ACCESS read-write
	STATUS current
	DESCRIPTION
		"Binary modes have two states represented by the values 0 (low) or 1 (high). These correspond to a2dSensorLowLabel and a2dSensorHighLabel. Current and voltage modes provide a scaled value from a2dSensorMin to a2dSensorMax. Analog modes: 1 =Door (binary) 2 =Power failure (binary) 3 =Flood (binary) 4 =Water-sensing cable leak (binary) 5 =Water-sensing cable fault (binary) 6 =Smoke alarm (binary) 7 =Isolated voltage negative ground (voltage) 8 =Isolated voltage positive ground (voltage) 9 =Custom voltage (voltage) 10 =Custom binary (binary) 11 =Custom current (current)"
	::= { a2dSensorEntry 7 }

a2dSensorUnits OBJECT-TYPE
	SYNTAX SnmpAdminString(SIZE (0..7))
	MAX-ACCESS read-write
	STATUS current
	DESCRIPTION
		"The units for the analog value. If a2dSensorMode is customVoltage(9) or customCurrent(11), then this field has a user-defined value. Otherwise, the value is fixed, based on mode."
	::= { a2dSensorEntry 8 }

a2dSensorMin OBJECT-TYPE
	SYNTAX Integer32(-1000000..1000000)
	MAX-ACCESS read-write
	STATUS current
	DESCRIPTION
		"Minimum analog value, given as an integer. The analog measurement is scaled to the range a2dSensorMin to a2dSensorMax. If a2dSensorMode is customVoltage(9) or customCurrent(11), then this field has a user-defined value. Otherwise, the value is fixed, based on mode."
	::= { a2dSensorEntry 9 }

a2dSensorMax OBJECT-TYPE
	SYNTAX Integer32(-1000000..1000000)
	MAX-ACCESS read-write
	STATUS current
	DESCRIPTION
		"Maximum analog value, given as an integer. The analog measurement is scaled to the range a2dSensorMin to a2dSensorMax. If a2dSensorMode is customVoltage(9) or customCurrent(11), then this field has a user-defined value. Otherwise, the value is fixed, based on mode."
	::= { a2dSensorEntry 10 }

a2dSensorLowLabel OBJECT-TYPE
	SYNTAX SnmpAdminString(SIZE (0..25))
	MAX-ACCESS read-write
	STATUS current
	DESCRIPTION
		"Label for 0 (low) binary value. This field is only applicable if a2dSensorMode is one of the binary modes. If a2dSensorMode is customBinary(10), then this field is user-defined. Otherwise, it has a pre-defined value based on the mode."
	::= { a2dSensorEntry 11 }

a2dSensorHighLabel OBJECT-TYPE
	SYNTAX SnmpAdminString(SIZE (0..25))
	MAX-ACCESS read-write
	STATUS current
	DESCRIPTION
		"Label for 1 (high) binary value. The field is only applicable if a2dSensorMode is one of the binary modes. If a2dSensorMode is customBinary(10), then this field is user-defined. Otherwise, it has a pre-defined value based on the mode."
	::= { a2dSensorEntry 12 }

a2dSensorAnalogLabel OBJECT-TYPE
	SYNTAX SnmpAdminString(SIZE (0..25))
	MAX-ACCESS read-write
	STATUS current
	DESCRIPTION
		" Label for the analog measurement"
	::= { a2dSensorEntry 13 }

common OBJECT IDENTIFIER ::= { vertiv 42 }
identity OBJECT IDENTIFIER ::= { common 1 }

wd15 OBJECT-IDENTITY
	STATUS current
	DESCRIPTION
		"Value (OID) used to identify a WD-15 unit"
	::= { identity 31 }

wd100 OBJECT-IDENTITY
	STATUS current
	DESCRIPTION
		"Value (OID) used to identify a WD-100 unit"
	::= { identity 32 }

i02 OBJECT-IDENTITY
	STATUS current
	DESCRIPTION
		"Value (OID) used to identify a GU1 (I-02) unit"
	::= { identity 52 }

--###########################################################################################--
--Notifications--
--###########################################################################################--

trap OBJECT IDENTIFIER ::= { watchdog100 32767 }
trapPrefix OBJECT IDENTIFIER ::= { trap 0 }

trapObj OBJECT IDENTIFIER ::= { trap 1 }

trapSeverity OBJECT-TYPE
	SYNTAX INTEGER {
			none(0),
			warning(1),
			alarm(2)
			}
	MAX-ACCESS  accessible-for-notify
	STATUS current
	DESCRIPTION
		"Indicates the severity of the trap:
		0 = None,
		1 = Warning,
		2 = Alarm"
	::= { trapObj 1 }

trapThreshType OBJECT-TYPE
	SYNTAX INTEGER {
			low(1),
			high(2)
			}
	MAX-ACCESS  accessible-for-notify
	STATUS current
	DESCRIPTION
		"Only sent for threshold alarms.  Identifies the threshold type:
		1 = Low,
		2 = High"
	::= { trapObj 2 }

internalTestNOTIFY NOTIFICATION-TYPE
	STATUS current
	DESCRIPTION
		"Test SNMP Trap"
	::= { trapPrefix 10101 }

--#####deviceInfo#####--

--#####internalTable#####--

internalAvailNOTIFY NOTIFICATION-TYPE
	OBJECTS {
			internalAvail,
			trapSeverity,
			sysName,
			internalLabel
			}
	STATUS current
	DESCRIPTION "Internal device availability trap"
	::= { trapPrefix 10205 }

internalAvailCLEAR NOTIFICATION-TYPE
	OBJECTS {
			internalAvail,
			trapSeverity,
			sysName,
			internalLabel
			}
	STATUS current
	DESCRIPTION "Internal device availability clear trap"
	::= { trapPrefix 20205 }

internalTempNOTIFY NOTIFICATION-TYPE
	OBJECTS {
			internalTemp,
			temperatureUnits,
			trapThreshType,
			trapSeverity,
			sysName,
			internalLabel
			}
	STATUS current
	DESCRIPTION "Internal Temperature Sensor trap"
	::= { trapPrefix 10206 }

internalTempCLEAR NOTIFICATION-TYPE
	OBJECTS {
			internalTemp,
			temperatureUnits,
			trapThreshType,
			trapSeverity,
			sysName,
			internalLabel
			}
	STATUS current
	DESCRIPTION "Internal Temperature Sensor clear trap"
	::= { trapPrefix 20206 }

internalHumidityNOTIFY NOTIFICATION-TYPE
	OBJECTS {
			internalHumidity,
			trapThreshType,
			trapSeverity,
			sysName,
			internalLabel
			}
	STATUS current
	DESCRIPTION "Internal humidity trap"
	::= { trapPrefix 10207 }

internalHumidityCLEAR NOTIFICATION-TYPE
	OBJECTS {
			internalHumidity,
			trapThreshType,
			trapSeverity,
			sysName,
			internalLabel
			}
	STATUS current
	DESCRIPTION "Internal humidity clear trap"
	::= { trapPrefix 20207 }

internalDewPointNOTIFY NOTIFICATION-TYPE
	OBJECTS {
			internalDewPoint,
			temperatureUnits,
			trapThreshType,
			trapSeverity,
			sysName,
			internalLabel
			}
	STATUS current
	DESCRIPTION "Internal Dew Point Sensor trap"
	::= { trapPrefix 10208 }

internalDewPointCLEAR NOTIFICATION-TYPE
	OBJECTS {
			internalDewPoint,
			temperatureUnits,
			trapThreshType,
			trapSeverity,
			sysName,
			internalLabel
			}
	STATUS current
	DESCRIPTION "Internal Dew Point Sensor clear trap"
	::= { trapPrefix 20208 }

internalIO1NOTIFY NOTIFICATION-TYPE
	OBJECTS {
			internalIO1,
			trapThreshType,
			trapSeverity,
			sysName,
			internalLabel
			}
	STATUS current
	DESCRIPTION "Analog1 measurement trap"
	::= { trapPrefix 10209 }

internalIO1CLEAR NOTIFICATION-TYPE
	OBJECTS {
			internalIO1,
			trapThreshType,
			trapSeverity,
			sysName,
			internalLabel
			}
	STATUS current
	DESCRIPTION "Analog1 measurement clear trap"
	::= { trapPrefix 20209 }

internalIO2NOTIFY NOTIFICATION-TYPE
	OBJECTS {
			internalIO2,
			trapThreshType,
			trapSeverity,
			sysName,
			internalLabel
			}
	STATUS current
	DESCRIPTION "Analog2 measurement trap"
	::= { trapPrefix 10210 }

internalIO2CLEAR NOTIFICATION-TYPE
	OBJECTS {
			internalIO2,
			trapThreshType,
			trapSeverity,
			sysName,
			internalLabel
			}
	STATUS current
	DESCRIPTION "Analog2 measurement clear trap"
	::= { trapPrefix 20210 }

internalIO3NOTIFY NOTIFICATION-TYPE
	OBJECTS {
			internalIO3,
			trapThreshType,
			trapSeverity,
			sysName,
			internalLabel
			}
	STATUS current
	DESCRIPTION "Analog3 measurement trap"
	::= { trapPrefix 10211 }

internalIO3CLEAR NOTIFICATION-TYPE
	OBJECTS {
			internalIO3,
			trapThreshType,
			trapSeverity,
			sysName,
			internalLabel
			}
	STATUS current
	DESCRIPTION "Analog3 measurement clear trap"
	::= { trapPrefix 20211 }

internalIO4NOTIFY NOTIFICATION-TYPE
	OBJECTS {
			internalIO4,
			trapThreshType,
			trapSeverity,
			sysName,
			internalLabel
			}
	STATUS current
	DESCRIPTION "Analog4 measurement trap"
	::= { trapPrefix 10212 }

internalIO4CLEAR NOTIFICATION-TYPE
	OBJECTS {
			internalIO4,
			trapThreshType,
			trapSeverity,
			sysName,
			internalLabel
			}
	STATUS current
	DESCRIPTION "Analog4 measurement clear trap"
	::= { trapPrefix 20212 }

--#####tempSensorTable#####--

tempSensorAvailNOTIFY NOTIFICATION-TYPE
	OBJECTS {
			tempSensorAvail,
			trapSeverity,
			sysName,
			tempSensorLabel
			}
	STATUS current
	DESCRIPTION "RT availability trap"
	::= { trapPrefix 10404 }

tempSensorAvailCLEAR NOTIFICATION-TYPE
	OBJECTS {
			tempSensorAvail,
			trapSeverity,
			sysName,
			tempSensorLabel
			}
	STATUS current
	DESCRIPTION "RT availability clear trap"
	::= { trapPrefix 20404 }

tempSensorTempNOTIFY NOTIFICATION-TYPE
	OBJECTS {
			tempSensorTemp,
			temperatureUnits,
			trapThreshType,
			trapSeverity,
			sysName,
			tempSensorLabel
			}
	STATUS current
	DESCRIPTION "RT temperature trap"
	::= { trapPrefix 10405 }

tempSensorTempCLEAR NOTIFICATION-TYPE
	OBJECTS {
			tempSensorTemp,
			temperatureUnits,
			trapThreshType,
			trapSeverity,
			sysName,
			tempSensorLabel
			}
	STATUS current
	DESCRIPTION "RT temperature clear trap"
	::= { trapPrefix 20405 }

--#####airFlowSensorTable#####--

airFlowSensorAvailNOTIFY NOTIFICATION-TYPE
	OBJECTS {
			airFlowSensorAvail,
			trapSeverity,
			sysName,
			airFlowSensorLabel
			}
	STATUS current
	DESCRIPTION "AFHT3 availability trap"
	::= { trapPrefix 10504 }

airFlowSensorAvailCLEAR NOTIFICATION-TYPE
	OBJECTS {
			airFlowSensorAvail,
			trapSeverity,
			sysName,
			airFlowSensorLabel
			}
	STATUS current
	DESCRIPTION "AFHT3 availability clear trap"
	::= { trapPrefix 20504 }

airFlowSensorTempNOTIFY NOTIFICATION-TYPE
	OBJECTS {
			airFlowSensorTemp,
			temperatureUnits,
			trapThreshType,
			trapSeverity,
			sysName,
			airFlowSensorLabel
			}
	STATUS current
	DESCRIPTION "AFHT3 temperature trap"
	::= { trapPrefix 10505 }

airFlowSensorTempCLEAR NOTIFICATION-TYPE
	OBJECTS {
			airFlowSensorTemp,
			temperatureUnits,
			trapThreshType,
			trapSeverity,
			sysName,
			airFlowSensorLabel
			}
	STATUS current
	DESCRIPTION "AFHT3 temperature clear trap"
	::= { trapPrefix 20505 }

airFlowSensorFlowNOTIFY NOTIFICATION-TYPE
	OBJECTS {
			airFlowSensorFlow,
			trapThreshType,
			trapSeverity,
			sysName,
			airFlowSensorLabel
			}
	STATUS current
	DESCRIPTION "AFHT3 airflow trap"
	::= { trapPrefix 10506 }

airFlowSensorFlowCLEAR NOTIFICATION-TYPE
	OBJECTS {
			airFlowSensorFlow,
			trapThreshType,
			trapSeverity,
			sysName,
			airFlowSensorLabel
			}
	STATUS current
	DESCRIPTION "AFHT3 airflow clear trap"
	::= { trapPrefix 20506 }

airFlowSensorHumidityNOTIFY NOTIFICATION-TYPE
	OBJECTS {
			airFlowSensorHumidity,
			trapThreshType,
			trapSeverity,
			sysName,
			airFlowSensorLabel
			}
	STATUS current
	DESCRIPTION "AFHT3 humidity trap"
	::= { trapPrefix 10507 }

airFlowSensorHumidityCLEAR NOTIFICATION-TYPE
	OBJECTS {
			airFlowSensorHumidity,
			trapThreshType,
			trapSeverity,
			sysName,
			airFlowSensorLabel
			}
	STATUS current
	DESCRIPTION "AFHT3 humidity clear trap"
	::= { trapPrefix 20507 }

airFlowSensorDewPointNOTIFY NOTIFICATION-TYPE
	OBJECTS {
			airFlowSensorDewPoint,
			temperatureUnits,
			trapThreshType,
			trapSeverity,
			sysName,
			airFlowSensorLabel
			}
	STATUS current
	DESCRIPTION "AFHT3 dewpoint trap"
	::= { trapPrefix 10508 }

airFlowSensorDewPointCLEAR NOTIFICATION-TYPE
	OBJECTS {
			airFlowSensorDewPoint,
			temperatureUnits,
			trapThreshType,
			trapSeverity,
			sysName,
			airFlowSensorLabel
			}
	STATUS current
	DESCRIPTION "AFHT3 dewpoint clear trap"
	::= { trapPrefix 20508 }

--#####dewPointSensorTable#####--

dewPointSensorAvailNOTIFY NOTIFICATION-TYPE
	OBJECTS {
			dewPointSensorAvail,
			trapSeverity,
			sysName,
			dewPointSensorName
			}
	STATUS current
	DESCRIPTION "Dewpoint available trap"
	::= { trapPrefix 10604 }

dewPointSensorAvailCLEAR NOTIFICATION-TYPE
	OBJECTS {
			dewPointSensorAvail,
			trapSeverity,
			sysName,
			dewPointSensorName
			}
	STATUS current
	DESCRIPTION "Dewpoint available clear trap"
	::= { trapPrefix 20604 }

dewPointSensorTempNOTIFY NOTIFICATION-TYPE
	OBJECTS {
			dewPointSensorTemp,
			temperatureUnits,
			trapThreshType,
			trapSeverity,
			sysName,
			dewPointSensorName
			}
	STATUS current
	DESCRIPTION "Dewpoint temperature trap"
	::= { trapPrefix 10605 }

dewPointSensorTempCLEAR NOTIFICATION-TYPE
	OBJECTS {
			dewPointSensorTemp,
			temperatureUnits,
			trapThreshType,
			trapSeverity,
			sysName,
			dewPointSensorName
			}
	STATUS current
	DESCRIPTION "Dewpoint temperature clear trap"
	::= { trapPrefix 20605 }

dewPointSensorHumidityNOTIFY NOTIFICATION-TYPE
	OBJECTS {
			dewPointSensorHumidity,
			trapThreshType,
			trapSeverity,
			sysName,
			dewPointSensorName
			}
	STATUS current
	DESCRIPTION "Dewpoint humidity trap"
	::= { trapPrefix 10606 }

dewPointSensorHumidityCLEAR NOTIFICATION-TYPE
	OBJECTS {
			dewPointSensorHumidity,
			trapThreshType,
			trapSeverity,
			sysName,
			dewPointSensorName
			}
	STATUS current
	DESCRIPTION "Dewpoint humidity clear trap"
	::= { trapPrefix 20606 }

dewPointSensorDewPointNOTIFY NOTIFICATION-TYPE
	OBJECTS {
			dewPointSensorDewPoint,
			temperatureUnits,
			trapThreshType,
			trapSeverity,
			sysName,
			dewPointSensorName
			}
	STATUS current
	DESCRIPTION "Dewpoint dewpoint trap"
	::= { trapPrefix 10607 }

dewPointSensorDewPointCLEAR NOTIFICATION-TYPE
	OBJECTS {
			dewPointSensorDewPoint,
			temperatureUnits,
			trapThreshType,
			trapSeverity,
			sysName,
			dewPointSensorName
			}
	STATUS current
	DESCRIPTION "Dewpoint dewpoint clear trap"
	::= { trapPrefix 20607 }

--#####ccatSensorTable#####--

ccatSensorAvailNOTIFY NOTIFICATION-TYPE
	OBJECTS {
			ccatSensorAvail,
			trapSeverity,
			sysName,
			ccatSensorName
			}
	STATUS current
	DESCRIPTION "CCAT available trap"
	::= { trapPrefix 10704 }

ccatSensorAvailCLEAR NOTIFICATION-TYPE
	OBJECTS {
			ccatSensorAvail,
			trapSeverity,
			sysName,
			ccatSensorName
			}
	STATUS current
	DESCRIPTION "CCAT available clear trap"
	::= { trapPrefix 20704 }

ccatSensorValueNOTIFY NOTIFICATION-TYPE
	OBJECTS {
			ccatSensorValue,
			trapThreshType,
			trapSeverity,
			sysName,
			ccatSensorType,
			ccatSensorName
			}
	STATUS current
	DESCRIPTION "CCAT measurement trap"
	::= { trapPrefix 10705 }

ccatSensorValueCLEAR NOTIFICATION-TYPE
	OBJECTS {
			ccatSensorValue,
			trapThreshType,
			trapSeverity,
			sysName,
			ccatSensorType,
			ccatSensorName
			}
	STATUS current
	DESCRIPTION "CCAT measurement clear trap"
	::= { trapPrefix 20705 }

--#####t3hdSensorTable#####--

t3hdSensorAvailNOTIFY NOTIFICATION-TYPE
	OBJECTS {
			t3hdSensorAvail,
			trapSeverity,
			sysName,
			t3hdSensorLabel
			}
	STATUS current
	DESCRIPTION "T3HD availability trap"
	::= { trapPrefix 10804 }

t3hdSensorAvailCLEAR NOTIFICATION-TYPE
	OBJECTS {
			t3hdSensorAvail,
			trapSeverity,
			sysName,
			t3hdSensorLabel
			}
	STATUS current
	DESCRIPTION "T3HD availability clear trap"
	::= { trapPrefix 20804 }

t3hdSensorIntTempNOTIFY NOTIFICATION-TYPE
	OBJECTS {
			t3hdSensorIntTemp,
			temperatureUnits,
			trapThreshType,
			trapSeverity,
			sysName,
			t3hdSensorLabel,
			t3hdSensorIntLabel
			}
	STATUS current
	DESCRIPTION "T3HD Internal temperature trap"
	::= { trapPrefix 10806 }

t3hdSensorIntTempCLEAR NOTIFICATION-TYPE
	OBJECTS {
			t3hdSensorIntTemp,
			temperatureUnits,
			trapThreshType,
			trapSeverity,
			sysName,
			t3hdSensorLabel,
			t3hdSensorIntLabel
			}
	STATUS current
	DESCRIPTION "T3HD Internal temperature clear trap"
	::= { trapPrefix 20806 }

t3hdSensorIntHumidityNOTIFY NOTIFICATION-TYPE
	OBJECTS {
			t3hdSensorIntHumidity,
			trapThreshType,
			trapSeverity,
			sysName,
			t3hdSensorLabel,
			t3hdSensorIntLabel
			}
	STATUS current
	DESCRIPTION "T3HD Internal humidity trap"
	::= { trapPrefix 10807 }

t3hdSensorIntHumidityCLEAR NOTIFICATION-TYPE
	OBJECTS {
			t3hdSensorIntHumidity,
			trapThreshType,
			trapSeverity,
			sysName,
			t3hdSensorLabel,
			t3hdSensorIntLabel
			}
	STATUS current
	DESCRIPTION "T3HD Internal humidity clear trap"
	::= { trapPrefix 20807 }

t3hdSensorIntDewPointNOTIFY NOTIFICATION-TYPE
	OBJECTS {
			t3hdSensorIntDewPoint,
			temperatureUnits,
			trapThreshType,
			trapSeverity,
			sysName,
			t3hdSensorLabel,
			t3hdSensorIntLabel
			}
	STATUS current
	DESCRIPTION "T3HD dewpoint trap"
	::= { trapPrefix 10808 }

t3hdSensorIntDewPointCLEAR NOTIFICATION-TYPE
	OBJECTS {
			t3hdSensorIntDewPoint,
			temperatureUnits,
			trapThreshType,
			trapSeverity,
			sysName,
			t3hdSensorLabel,
			t3hdSensorIntLabel
			}
	STATUS current
	DESCRIPTION "T3HD dewpoint clear trap"
	::= { trapPrefix 20808 }

t3hdSensorExtATempNOTIFY NOTIFICATION-TYPE
	OBJECTS {
			t3hdSensorExtATemp,
			temperatureUnits,
			trapThreshType,
			trapSeverity,
			sysName,
			t3hdSensorLabel,
			t3hdSensorExtALabel
			}
	STATUS current
	DESCRIPTION "T3HD External A temperature trap"
	::= { trapPrefix 10811 }

t3hdSensorExtATempCLEAR NOTIFICATION-TYPE
	OBJECTS {
			t3hdSensorExtATemp,
			temperatureUnits,
			trapThreshType,
			trapSeverity,
			sysName,
			t3hdSensorLabel,
			t3hdSensorExtALabel
			}
	STATUS current
	DESCRIPTION "T3HD External A temperature clear trap"
	::= { trapPrefix 20811 }

t3hdSensorExtBTempNOTIFY NOTIFICATION-TYPE
	OBJECTS {
			t3hdSensorExtBTemp,
			temperatureUnits,
			trapThreshType,
			trapSeverity,
			sysName,
			t3hdSensorLabel,
			t3hdSensorExtBLabel
			}
	STATUS current
	DESCRIPTION "T3HD External B temperature trap"
	::= { trapPrefix 10814 }

t3hdSensorExtBTempCLEAR NOTIFICATION-TYPE
	OBJECTS {
			t3hdSensorExtBTemp,
			temperatureUnits,
			trapThreshType,
			trapSeverity,
			sysName,
			t3hdSensorLabel,
			t3hdSensorExtBLabel
			}
	STATUS current
	DESCRIPTION "T3HD External B temperature clear trap"
	::= { trapPrefix 20814 }

--#####thdSensorTable#####--

thdSensorAvailNOTIFY NOTIFICATION-TYPE
	OBJECTS {
			thdSensorAvail,
			trapSeverity,
			sysName,
			thdSensorLabel
			}
	STATUS current
	DESCRIPTION "THD availability trap"
	::= { trapPrefix 10904 }

thdSensorAvailCLEAR NOTIFICATION-TYPE
	OBJECTS {
			thdSensorAvail,
			trapSeverity,
			sysName,
			thdSensorLabel
			}
	STATUS current
	DESCRIPTION "THD availability clear trap"
	::= { trapPrefix 20904 }

thdSensorTempNOTIFY NOTIFICATION-TYPE
	OBJECTS {
			thdSensorTemp,
			temperatureUnits,
			trapThreshType,
			trapSeverity,
			sysName,
			thdSensorLabel
			}
	STATUS current
	DESCRIPTION "THD temperature trap"
	::= { trapPrefix 10905 }

thdSensorTempCLEAR NOTIFICATION-TYPE
	OBJECTS {
			thdSensorTemp,
			temperatureUnits,
			trapThreshType,
			trapSeverity,
			sysName,
			thdSensorLabel
			}
	STATUS current
	DESCRIPTION "THD temperature clear trap"
	::= { trapPrefix 20905 }

thdSensorHumidityNOTIFY NOTIFICATION-TYPE
	OBJECTS {
			thdSensorHumidity,
			trapThreshType,
			trapSeverity,
			sysName,
			thdSensorLabel
			}
	STATUS current
	DESCRIPTION "THD humidity trap"
	::= { trapPrefix 10906 }

thdSensorHumidityCLEAR NOTIFICATION-TYPE
	OBJECTS {
			thdSensorHumidity,
			trapThreshType,
			trapSeverity,
			sysName,
			thdSensorLabel
			}
	STATUS current
	DESCRIPTION "THD humidity clear trap"
	::= { trapPrefix 20906 }

thdSensorDewPointNOTIFY NOTIFICATION-TYPE
	OBJECTS {
			thdSensorDewPoint,
			temperatureUnits,
			trapThreshType,
			trapSeverity,
			sysName,
			thdSensorLabel
			}
	STATUS current
	DESCRIPTION "THD dewpoint trap"
	::= { trapPrefix 10907 }

thdSensorDewPointCLEAR NOTIFICATION-TYPE
	OBJECTS {
			thdSensorDewPoint,
			temperatureUnits,
			trapThreshType,
			trapSeverity,
			sysName,
			thdSensorLabel
			}
	STATUS current
	DESCRIPTION "THD dewpoint clear trap"
	::= { trapPrefix 20907 }

--#####rpmSensorTable#####--

rpmSensorAvailNOTIFY NOTIFICATION-TYPE
	OBJECTS {
			rpmSensorAvail,
			trapSeverity,
			sysName,
			rpmSensorName
			}
	STATUS current
	DESCRIPTION "RPM available trap"
	::= { trapPrefix 11004 }

rpmSensorAvailCLEAR NOTIFICATION-TYPE
	OBJECTS {
			rpmSensorAvail,
			trapSeverity,
			sysName,
			rpmSensorName
			}
	STATUS current
	DESCRIPTION "RPM available clear trap"
	::= { trapPrefix 21004 }

rpmSensorEnergyNOTIFY NOTIFICATION-TYPE
	OBJECTS {
			rpmSensorEnergy,
			trapThreshType,
			trapSeverity,
			sysName,
			rpmSensorName
			}
	STATUS current
	DESCRIPTION "RPM energy trap"
	::= { trapPrefix 11005 }

rpmSensorEnergyCLEAR NOTIFICATION-TYPE
	OBJECTS {
			rpmSensorEnergy,
			trapThreshType,
			trapSeverity,
			sysName,
			rpmSensorName
			}
	STATUS current
	DESCRIPTION "RPM energy clear trap"
	::= { trapPrefix 21005 }

rpmSensorVoltageNOTIFY NOTIFICATION-TYPE
	OBJECTS {
			rpmSensorVoltage,
			trapThreshType,
			trapSeverity,
			sysName,
			rpmSensorName
			}
	STATUS current
	DESCRIPTION "RPM voltage trap"
	::= { trapPrefix 11006 }

rpmSensorVoltageCLEAR NOTIFICATION-TYPE
	OBJECTS {
			rpmSensorVoltage,
			trapThreshType,
			trapSeverity,
			sysName,
			rpmSensorName
			}
	STATUS current
	DESCRIPTION "RPM voltage clear trap"
	::= { trapPrefix 21006 }

rpmSensorVoltageMaxNOTIFY NOTIFICATION-TYPE
	OBJECTS {
			rpmSensorVoltageMax,
			trapThreshType,
			trapSeverity,
			sysName,
			rpmSensorName
			}
	STATUS current
	DESCRIPTION "RPM voltage (max) trap"
	::= { trapPrefix 11007 }

rpmSensorVoltageMaxCLEAR NOTIFICATION-TYPE
	OBJECTS {
			rpmSensorVoltageMax,
			trapThreshType,
			trapSeverity,
			sysName,
			rpmSensorName
			}
	STATUS current
	DESCRIPTION "RPM voltage (max) clear trap"
	::= { trapPrefix 21007 }

rpmSensorVoltageMinNOTIFY NOTIFICATION-TYPE
	OBJECTS {
			rpmSensorVoltageMin,
			trapThreshType,
			trapSeverity,
			sysName,
			rpmSensorName
			}
	STATUS current
	DESCRIPTION "RPM voltage (min) trap"
	::= { trapPrefix 11008 }

rpmSensorVoltageMinCLEAR NOTIFICATION-TYPE
	OBJECTS {
			rpmSensorVoltageMin,
			trapThreshType,
			trapSeverity,
			sysName,
			rpmSensorName
			}
	STATUS current
	DESCRIPTION "RPM voltage (min) clear trap"
	::= { trapPrefix 21008 }

rpmSensorVoltagePeakNOTIFY NOTIFICATION-TYPE
	OBJECTS {
			rpmSensorVoltagePeak,
			trapThreshType,
			trapSeverity,
			sysName,
			rpmSensorName
			}
	STATUS current
	DESCRIPTION "RPM voltage (peak) trap"
	::= { trapPrefix 11009 }

rpmSensorVoltagePeakCLEAR NOTIFICATION-TYPE
	OBJECTS {
			rpmSensorVoltagePeak,
			trapThreshType,
			trapSeverity,
			sysName,
			rpmSensorName
			}
	STATUS current
	DESCRIPTION "RPM voltage (peak) clear trap"
	::= { trapPrefix 21009 }

rpmSensorCurrentNOTIFY NOTIFICATION-TYPE
	OBJECTS {
			rpmSensorCurrent,
			trapThreshType,
			trapSeverity,
			sysName,
			rpmSensorName
			}
	STATUS current
	DESCRIPTION "RPM current trap"
	::= { trapPrefix 11010 }

rpmSensorCurrentCLEAR NOTIFICATION-TYPE
	OBJECTS {
			rpmSensorCurrent,
			trapThreshType,
			trapSeverity,
			sysName,
			rpmSensorName
			}
	STATUS current
	DESCRIPTION "RPM current clear trap"
	::= { trapPrefix 21010 }

rpmSensorRealPowerNOTIFY NOTIFICATION-TYPE
	OBJECTS {
			rpmSensorRealPower,
			trapThreshType,
			trapSeverity,
			sysName,
			rpmSensorName
			}
	STATUS current
	DESCRIPTION "RPM real power trap"
	::= { trapPrefix 11011 }

rpmSensorRealPowerCLEAR NOTIFICATION-TYPE
	OBJECTS {
			rpmSensorRealPower,
			trapThreshType,
			trapSeverity,
			sysName,
			rpmSensorName
			}
	STATUS current
	DESCRIPTION "RPM real power clear trap"
	::= { trapPrefix 21011 }

rpmSensorApparentPowerNOTIFY NOTIFICATION-TYPE
	OBJECTS {
			rpmSensorApparentPower,
			trapThreshType,
			trapSeverity,
			sysName,
			rpmSensorName
			}
	STATUS current
	DESCRIPTION "RPM apparent power trap"
	::= { trapPrefix 11012 }

rpmSensorApparentPowerCLEAR NOTIFICATION-TYPE
	OBJECTS {
			rpmSensorApparentPower,
			trapThreshType,
			trapSeverity,
			sysName,
			rpmSensorName
			}
	STATUS current
	DESCRIPTION "RPM apparent power clear trap"
	::= { trapPrefix 21012 }

rpmSensorPowerFactorNOTIFY NOTIFICATION-TYPE
	OBJECTS {
			rpmSensorPowerFactor,
			trapSeverity,
			trapThreshType,
			sysName,
			rpmSensorName
			}
	STATUS current
	DESCRIPTION "RPM power factor trap"
	::= { trapPrefix 11013 }

rpmSensorPowerFactorCLEAR NOTIFICATION-TYPE
	OBJECTS {
			rpmSensorPowerFactor,
			trapSeverity,
			trapThreshType,
			sysName,
			rpmSensorName
			}
	STATUS current
	DESCRIPTION "RPM power factor clear trap"
	::= { trapPrefix 21013 }

--#####a2dSensorTable#####--

a2dSensorAvailNOTIFY NOTIFICATION-TYPE
	OBJECTS {
			a2dSensorAvail,
			trapSeverity,
			sysName,
			a2dSensorLabel
			}
	STATUS current
	DESCRIPTION "A2D availability trap"
	::= { trapPrefix 11104 }

a2dSensorAvailCLEAR NOTIFICATION-TYPE
	OBJECTS {
			a2dSensorAvail,
			trapSeverity,
			sysName,
			a2dSensorLabel
			}
	STATUS current
	DESCRIPTION "A2D availability clear trap"
	::= { trapPrefix 21104 }

a2dSensorValueNOTIFY NOTIFICATION-TYPE
	OBJECTS {
			a2dSensorValue,
			trapThreshType,
			trapSeverity,
			sysName,
			a2dSensorLabel,
			a2dSensorAnalogLabel,
			a2dSensorDisplayValue
			}
	STATUS current
	DESCRIPTION "A2D measurement trap"
	::= { trapPrefix 11105 }

a2dSensorValueCLEAR NOTIFICATION-TYPE
	OBJECTS {
			a2dSensorValue,
			trapThreshType,
			trapSeverity,
			sysName,
			a2dSensorLabel,
			a2dSensorAnalogLabel,
			a2dSensorDisplayValue
			}
	STATUS current
	DESCRIPTION "A2D measurement clear trap"
	::= { trapPrefix 21105 }

END
