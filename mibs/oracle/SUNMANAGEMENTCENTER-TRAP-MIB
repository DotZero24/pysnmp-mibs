-------------------------------------------------------
-- Copyright 1999 - Sun Microsystems, Inc. All Rights Reserved.
--
--
-------------------------------------------------------
-- Sun Management Center
-------------------------------------------------------
--
-- estrapmib
--     Definitions of the Sun Management Center Trap and Trap Info branches
--     from the enterprises node

SUNMANAGEMENTCENTER-TRAP-MIB DEFINITIONS ::= BEGIN

  IMPORTS

        enterprises, MODULE-IDENTITY, NOTIFICATION-TYPE, OBJECT-TYPE
                FROM SNMPv2-SMI
         OBJECT-GROUP
                FROM SNMPv2-CONF;

traps MODULE-IDENTITY
    LAST-UPDATED "9907201505Z"
    ORGANIZATION "Sun Microsystems Inc."
    CONTACT-INFO
        "        Sun Microsystems Inc.
       Customer Support
            Postal: 901 San Antonio Road
       Palo Alto, CA-94303-4900
    USA
                         Tel: 650-960-1300
                E-mail: service@sun.com"
    DESCRIPTION
        "This mib defines all the traps forwarded by the Sun Management
        Center agent, with their variable bindings. Any outside entity can
        subscribe for these traps."

    REVISION  "9907201505Z"
    DESCRIPTION
        "Rev 1.0  20th July 1999 15:05, Initial version Of MIB."
    ::= { agent 0 }





sun       OBJECT IDENTIFIER ::= { enterprises 42 }
prod      OBJECT IDENTIFIER ::= { sun 2 }
sunsymon  OBJECT IDENTIFIER ::= { prod 12 }
agent     OBJECT IDENTIFIER ::= { sunsymon 2 }
base      OBJECT IDENTIFIER ::= { agent 1 }


trapInfoGroup OBJECT-GROUP
	OBJECTS {  statusOID, refreshOID,  moduleInfo }
	STATUS  current
	DESCRIPTION
		"Varbinds of traps"
	::= { base 3 }


statusChange NOTIFICATION-TYPE
	OBJECTS { statusOID }
	STATUS current
	DESCRIPTION
		"A statusChange trap signifies that the status of an
		object has changed."
	::= { traps 1 }

valueRefresh NOTIFICATION-TYPE
	OBJECTS { refreshOID }
	STATUS current
	DESCRIPTION
		"A valueRefresh trap signifies that the value of an object
		has been manually refreshed."
	::= { traps 2 }

moduleLoaded NOTIFICATION-TYPE
	OBJECTS { moduleInfo }
	STATUS current
	DESCRIPTION
		"A moduleLoaded trap signifies that a module has been loaded."
	::= { traps 4 }

moduleUnloaded NOTIFICATION-TYPE
	OBJECTS { moduleInfo }
	STATUS current
	DESCRIPTION
		"A moduleUnloaded trap signifies that a module has
		been unloaded."
	::= { traps 5 }

statusOID OBJECT-TYPE
	SYNTAX OBJECT IDENTIFIER
	MAX-ACCESS accessible-for-notify
	STATUS current
	DESCRIPTION
		"The identification of the object for which the status
		changed. This occurs as the first trap-specific varbind
		in a statusChangeTrap."
	::= { trapInfoGroup 1 }

refreshOID OBJECT-TYPE
	SYNTAX OBJECT IDENTIFIER
	MAX-ACCESS accessible-for-notify
	STATUS current
	DESCRIPTION
		"The identification of the object for which the value
		was refreshed. This occurs as the first trap-specific
		varbind in a valueRefreshTrap."
	::= { trapInfoGroup 2 }

moduleInfo OBJECT-TYPE
	SYNTAX OCTET STRING
	MAX-ACCESS accessible-for-notify
	STATUS current
	DESCRIPTION
		"The module specification and module version of the
		module that is being loaded or unloaded. This occurs
		as the first trap-specific varbind in a moduleLoaded
		and moduleUnloaded traps."
	::= { trapInfoGroup 5 }

END
