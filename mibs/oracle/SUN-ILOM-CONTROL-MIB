SUN-ILOM-CONTROL-MIB DEFINITIONS ::= BEGIN

IMPORTS
    MODULE-IDENTITY,
    OBJECT-TYPE,
    IpAddress,
    Integer32,
    Unsigned32,
    enterprises         FROM SNMPv2-SMI
    TEXTUAL-CONVENTION,
    RowStatus,
    TruthValue,
    DisplayString,
    DateAndTime         FROM SNMPv2-TC
    OBJECT-GROUP        FROM SNMPv2-CONF
    SnmpAdminString     FROM SNMP-FRAMEWORK-MIB;

    sun                 OBJECT IDENTIFIER ::= { enterprises 42 }
    products            OBJECT IDENTIFIER ::= { sun 2 }
    ilom                OBJECT IDENTIFIER ::= { products 175 }

ilomCtrlMIB MODULE-IDENTITY
    LAST-UPDATED    "201006110000Z" --  June 11, 2010
    ORGANIZATION    "Oracle Corporation"
    CONTACT-INFO    "Oracle Corporation
                     500 Oracle Parkway
                     Redwood Shores, CA 95065
                     U.S.A.

                     http://www.oracle.com"
    DESCRIPTION
        "SUN-ILOM-CONTROL-MIB.mib Version 3.0
         Copyright (c) 2005, 2010, Oracle and/or its affiliates.
         All rights reserved.

         This MIB controls all Sun Integrated Lights Out Management
         devices."

    REVISION
        "201006110000Z" -- June 11, 2010
    DESCRIPTION
        "Add support for the SPARC diagnostic 'HW change' trigger"
    REVISION
        "201006080000Z" -- June 8, 2010
    DESCRIPTION
        "Add ActiveDirectory parameter ilomCtrlActiveDirStrictCredentialErrorEnabled"

    REVISION
        "200903300000Z" -- March 30, 2009
    DESCRIPTION
        "Add LdapSsl optional User Mapping parameters."
    REVISION
        "200903030000Z" -- March 3, 2009
    DESCRIPTION
        "Add ActiveDirectory parameter ilomCtrlActiveDirExpSearchEnabled."
    REVISION
        "200805150000Z" -- May 15, 2008
    DESCRIPTION
        "Version 3.0
         Released with ILOM version 3.0
            Added alert event class/type filtering
            Added Telemetry Harness Daemon (THD)
            Added dns-locator objects and certificate params for ActiveDirectory
            Added ilomCtrlLdapSsl
            Unify POST knobs for Volume and Enterprise Products
            Added BackupAndRestore configuration XML file support
            Added DNS configuration support
            Added factory to ILOMCtrlResetToDefaultsAction
            Added 'other' values to several TCs
            Added ilomCtrlSPARCHostHypervisorVersion
            Added ilomCtrlSPARCHostSysFwVersion
            Added ilomCtrlSPARCHostSendBreakAction
            Added sideband management support"
    REVISION
        "200804110000Z" -- April 11, 2008
    DESCRIPTION
        "Add destinationport for use with trap type alerts.
         Remove range from ilomCtrlEventLogRecordID."
    REVISION
        "200702200000Z" -- February 20, 2007
    DESCRIPTION
        "Version 2.0"
    REVISION
        "200612150000Z" -- December 15, 2006
    DESCRIPTION
        "Version: 1.1
         Released with ILOM version 1.1.5"
    REVISION
        "200512190000Z" -- December 19, 2005
    DESCRIPTION
        "Version: 0.7
         Initial Release"

    ::= { ilom 102 }

    ilomCtrlClients           OBJECT IDENTIFIER ::= { ilomCtrlMIB 1 }
    ilomCtrlServices          OBJECT IDENTIFIER ::= { ilomCtrlMIB 2 }
    ilomCtrlNetwork           OBJECT IDENTIFIER ::= { ilomCtrlMIB 3 }
    ilomCtrlUsers             OBJECT IDENTIFIER ::= { ilomCtrlMIB 4 }
    ilomCtrlSessions          OBJECT IDENTIFIER ::= { ilomCtrlMIB 5 }
    ilomCtrlFirmwareMgmt      OBJECT IDENTIFIER ::= { ilomCtrlMIB 6 }
    ilomCtrlLogs              OBJECT IDENTIFIER ::= { ilomCtrlMIB 7 }
    ilomCtrlAlerts            OBJECT IDENTIFIER ::= { ilomCtrlMIB 8 }
    ilomCtrlClock             OBJECT IDENTIFIER ::= { ilomCtrlMIB 9 }
    ilomCtrlSerial            OBJECT IDENTIFIER ::= { ilomCtrlMIB 10 }
    ilomCtrlPowerReset        OBJECT IDENTIFIER ::= { ilomCtrlMIB 11 }
    ilomCtrlRedundancy        OBJECT IDENTIFIER ::= { ilomCtrlMIB 12 }
    ilomCtrlPolicy            OBJECT IDENTIFIER ::= { ilomCtrlMIB 13 }
    ilomCtrlConfigMgmt        OBJECT IDENTIFIER ::= { ilomCtrlMIB 14 }
    ilomCtrlSPARC             OBJECT IDENTIFIER ::= { ilomCtrlMIB 15 }
    ilomCtrlIdentification    OBJECT IDENTIFIER ::= { ilomCtrlMIB 16 }
    ilomCtrlThd               OBJECT IDENTIFIER ::= { ilomCtrlMIB 17 }
    ilomCtrlConformances      OBJECT IDENTIFIER ::= { ilomCtrlMIB 18 }

    ilomCtrlNtp               OBJECT IDENTIFIER ::= { ilomCtrlClients 1 }
    ilomCtrlLdap              OBJECT IDENTIFIER ::= { ilomCtrlClients 2 }
    ilomCtrlRadius            OBJECT IDENTIFIER ::= { ilomCtrlClients 3 }
    ilomCtrlRemoteSyslog      OBJECT IDENTIFIER ::= { ilomCtrlClients 4 }
    ilomCtrlActiveDirectory   OBJECT IDENTIFIER ::= { ilomCtrlClients 5 }
    ilomCtrlSMTP              OBJECT IDENTIFIER ::= { ilomCtrlClients 6 }
    ilomCtrlLdapSsl           OBJECT IDENTIFIER ::= { ilomCtrlClients 7 }
    ilomCtrlDNS               OBJECT IDENTIFIER ::= { ilomCtrlClients 8 }

    ilomCtrlHttp              OBJECT IDENTIFIER ::= { ilomCtrlServices 1 }
    ilomCtrlHttps             OBJECT IDENTIFIER ::= { ilomCtrlServices 2 }
    ilomCtrlSsh               OBJECT IDENTIFIER ::= { ilomCtrlServices 3 }
    ilomCtrlSingleSignon      OBJECT IDENTIFIER ::= { ilomCtrlServices 4 }

    ilomCtrlEventLog          OBJECT IDENTIFIER ::= { ilomCtrlLogs 1 }

    ilomCtrlPowerControl      OBJECT IDENTIFIER ::= { ilomCtrlPowerReset 1 }
    ilomCtrlResetControl      OBJECT IDENTIFIER ::= { ilomCtrlPowerReset 2 }

    ilomCtrlBackupAndRestore  OBJECT IDENTIFIER ::= { ilomCtrlConfigMgmt 2 }

    ilomCtrlSPARCDiags        OBJECT IDENTIFIER ::= { ilomCtrlSPARC 1 }
    ilomCtrlSPARCHostControl  OBJECT IDENTIFIER ::= { ilomCtrlSPARC 2 }
    ilomCtrlSPARCBootMode     OBJECT IDENTIFIER ::= { ilomCtrlSPARC 3 }
    ilomCtrlSPARCKeySwitch    OBJECT IDENTIFIER ::= { ilomCtrlSPARC 4 }

    ilomCtrlCompliances       OBJECT IDENTIFIER ::= { ilomCtrlConformances 1 }
    ilomCtrlGroups            OBJECT IDENTIFIER ::= { ilomCtrlConformances 2 }

-- ***************************************************************************
-- *                      Textual Conventions                                *
-- ***************************************************************************
ILOMCtrlTargetIndex ::= TEXTUAL-CONVENTION
    STATUS current
    DESCRIPTION
        "A string that is short enough to be used properly as an
         index without overflowing the maximum number of subOIDs."
    SYNTAX OCTET STRING (SIZE (0..110))

ILOMCtrlModTargetIndex ::= TEXTUAL-CONVENTION
    STATUS current
    DESCRIPTION
        "A string that is short enough to be used properly along
         with ILOMCtrlInstanceTargetIndex as a pair of indexes
         without overflowing the maximum number of subOIDs."
    SYNTAX OCTET STRING (SIZE (0..12))

ILOMCtrlInstanceTargetIndex ::= TEXTUAL-CONVENTION
    STATUS current
    DESCRIPTION
        "A string that is short enough to be used properly along
         with ILOMCtrlModTargetIndex as a pair of indexes
         without overflowing the maximum number of subOIDs."
    SYNTAX OCTET STRING (SIZE (0..100))

ILOMCtrlSessionsConnectionType ::= TEXTUAL-CONVENTION
    STATUS current
    DESCRIPTION
        "An enumerated value which describes possible connection
         types by which a user can be log in."
    SYNTAX INTEGER {
        shell(1),
        web(2),
        other(3),
        snmp(4)
    }

ILOMCtrlLocalUserUsername ::= TEXTUAL-CONVENTION
   STATUS       current
   DESCRIPTION
     "A local user username.
      This must start with an alphabetical letter
      and may contain alphabetical letters, digits,
      hyphens and underscores.
      This can not be 'password'.
      This can not contain spaces."
   SYNTAX OCTET STRING (SIZE (4..16))

ILOMCtrlLocalUserPassword ::= TEXTUAL-CONVENTION
   STATUS       current
   DESCRIPTION
     "A local user password."
   SYNTAX OCTET STRING (SIZE (8..16))

ILOMCtrlUserRole ::= TEXTUAL-CONVENTION
    STATUS deprecated
    DESCRIPTION
        "An enumerated value which describes possible privilege
         levels (also known as roles) a user can have.
         ***NOTE: this textual-convention is deprecated and replaced
         by ILOMCtrlUserRoles."
    SYNTAX INTEGER {
        administrator(1),
        operator(2),
        none(3),
        other(4)
    }

-- While deprecated, the use of ILOMCtrlUserRole will result in the
-- following transformations:
--
--      ILOMCtrlUserRole    ILOMCtrlUserRoles
--      ----------------    -----------------
--      administrator(1)    "Administrator"
--
--      operator(2)         "Operator"
--
--      none(3)             ""
--
--      other(4)            <Unknown>

ILOMCtrlUserRoles ::= TEXTUAL-CONVENTION
    STATUS current
    DESCRIPTION
        "A set of role-IDs which describe the possible privilege
         levels (also known as roles) for a user.  This property
         supports the legacy roles of 'Administrator' or
         'Operator', or any of the individual role ID combinations
         of 'a', 'u', 'c', 'r', 'o' and 's' (like 'aucro') where
         a-admin, u-user, c-console, r-reset, s-service and o-readOnly."
    SYNTAX OCTET STRING (SIZE (0..13))

ILOMCtrlLocalUserAuthCLIMode ::= TEXTUAL-CONVENTION
    STATUS current
    DESCRIPTION
        "An enumerated value which describes the possible CLI modes.
         The 'default' mode corresponds to the ILOM DMTF CLP.  The
         'alom' mode corresponds to the ALOM CMT."
    SYNTAX INTEGER {
        default(1),
        alom(2)
    }

ILOMCtrlPowerAction ::= TEXTUAL-CONVENTION
    STATUS current
    DESCRIPTION
        "An enumerated value which describes possible actions
         that can applied to a power control target."
    SYNTAX INTEGER {
        powerOn(1),
        powerOff(2),
        powerCycle(3),
        powerSoft(4)
    }

ILOMCtrlResetAction ::= TEXTUAL-CONVENTION
    STATUS current
    DESCRIPTION
        "An enumerated value which describes possible actions
         that can applied to a reset control target."
    SYNTAX INTEGER {
        reset(1),
        resetNonMaskableInterrupt(2),
        force(3)
    }

ILOMCtrlNetworkIpDiscovery ::= TEXTUAL-CONVENTION
    STATUS current
    DESCRIPTION
        "An enumerated value which determines whether the IP settings
         should static or dynamic (DHCP)."
    SYNTAX INTEGER {
        static(1),
        dynamic(2),
        other(3)
    }

ILOMCtrlEventLogType ::= TEXTUAL-CONVENTION
    STATUS current
    DESCRIPTION
        "An enumerated value which describes the possible event log type."
    SYNTAX INTEGER {
        log(1),
        action(2),
        fault(3),
        state(4),
        repair(5),
        other(6)
    }

ILOMCtrlEventLogClass ::= TEXTUAL-CONVENTION
    STATUS current
    DESCRIPTION
        "An enumerated value which describes the possible event log class."
    SYNTAX INTEGER {
        audit(1),
        ipmi(2),
        chassis(3),
        fma(4),
        system(5),
        pcm(6),
        other(7)
    }

ILOMCtrlEventSeverity ::= TEXTUAL-CONVENTION
    STATUS current
    DESCRIPTION
        "An enumerated value which describes the possible event severities."
    SYNTAX INTEGER {
        disable(1),
        critical(2),
        major(3),
        minor(4),
        down(5),
        other(6)
    }

ILOMCtrlAlertType ::= TEXTUAL-CONVENTION
    STATUS current
    DESCRIPTION
        "An enumerated value which describes the possible alert notification types."
    SYNTAX INTEGER {
        email(1),
        snmptrap(2),
        ipmipet(3)
    }

ILOMCtrlAlertSNMPVersion ::= TEXTUAL-CONVENTION
    STATUS current
    DESCRIPTION
        "An enumeration of the possible SNMP versions for traps generated
         by configuring alert rules."
    SYNTAX INTEGER {
        v1(1),
        v2c(2),
        v3(3)
    }

ILOMCtrlBaudRate ::= TEXTUAL-CONVENTION
    STATUS current
    DESCRIPTION
        "An enumerated value which describes the possible baud rates for serial ports."
    SYNTAX INTEGER {
        baud9600(1),
        baud19200(2),
        baud38400(3),
        baud57600(4),
        baud115200(5)
    }

ILOMCtrlFlowControl ::= TEXTUAL-CONVENTION
    STATUS current
    DESCRIPTION
        "An enumerated value which describes the possible flowcontrol settings for serial ports."
    SYNTAX INTEGER {
        unknown(1),
        hardware(2),
        software(3),
        none(4)
    }

ILOMCtrlFirmwareUpdateStatus ::= TEXTUAL-CONVENTION
    STATUS current
    DESCRIPTION
        "An enumerated value which contains all the possible status values during
         a firmware update."
    SYNTAX INTEGER {
        tftpError(1),
        imageVerificationFailed(2),
        inProgress(3),
        success(4),
        other(5)
    }

ILOMCtrlFirmwareUpdateAction ::= TEXTUAL-CONVENTION
    STATUS current
    DESCRIPTION
        "An enumerated value which contains all the possible firmware management
         actions."
    SYNTAX INTEGER {
        clearProperties(1),
        initiate(2)
    }

ILOMCtrlResetToDefaultsAction ::= TEXTUAL-CONVENTION
    STATUS current
    DESCRIPTION
        "An enumerated value indicating possible actions for resetting the
         SP back to factory defaults."
    SYNTAX INTEGER {
        none(1),
        all(2),
        factory(3)
    }

ILOMCtrlRedundancyStatus ::= TEXTUAL-CONVENTION
    STATUS current
    DESCRIPTION
        "An enumerated value which contains all the possible states a device
         can have in a redundant configuration."
    SYNTAX INTEGER {
        initializing(1),
        active(2),
        standby(3),
        standAlone(4),
        other(5)
    }

ILOMCtrlRedundancyAction ::= TEXTUAL-CONVENTION
    STATUS current
    DESCRIPTION
        "Setting the redundancy action to initiateFailover will cause the
         current SC to switch mastership. i.e., it will initiate actions to
         become master if it is standby or to become standby if it is master.

         No action is taken if the SC is initializing or running in
         standalone mode."
    SYNTAX INTEGER {
        ready(1),
        initiateFailover(2)
    }

ILOMCtrlSPARCDiagsLevel ::= TEXTUAL-CONVENTION
    STATUS deprecated
    DESCRIPTION
        "An enumerated value which contains all the possible states for
         embedded diagnostics for the host.  The min value is the same as
         the 'enabled' value on some platforms and the max value is the same
         as the 'extended' value.
         ***NOTE: this textual-convention is deprecated and replaced with
         ILOMCtrlSPARCDiagsLevelAdv."
    SYNTAX INTEGER {
        min(1),
        max(2),
        advsettings(3)
    }

ILOMCtrlSPARCDiagsLevelAdv ::= TEXTUAL-CONVENTION
    STATUS current
    DESCRIPTION
        "An enumerated value which contains all the possible states for
         embedded diagnostics for the host.  The min value is the same as
         the 'enabled' value on some platforms and the max value is the same
         as the 'extended' value."
    SYNTAX INTEGER {
        init(1),
        minimum(2),
        normal(3),
        maximum(4),
        other(5)
    }

ILOMCtrlSPARCDiagsTrigger ::= TEXTUAL-CONVENTION
    STATUS current
    DESCRIPTION
        "An enumerated value which contains all the possible states for
         the trigger for embedded diagnostics on the host. x64 platforms with
         embedded diagnostics only support 'all-resets' and 'none' as
         possible states."
    SYNTAX INTEGER {
        allResets(1),
        none(2),
        userReset(3),
        powerOnReset(4),
        errorTest(5),
        userResetandpowerOnReset(6),
        userResetanderrorTest(7),
        userTestandpowerOnReset(8),
        hwChange(9),
        hwChangeandpowerOnReset(10),
        hwChangeanderrorTest(11)
    }

ILOMCtrlSPARCDiagsMode ::= TEXTUAL-CONVENTION
    STATUS current
    DESCRIPTION
        "An enumerated value which contains all the possible OPS modes specified
         to POST."
    SYNTAX INTEGER {
        off(1),
        normal(2),
        service(3),
        unknown(4)
    }

ILOMCtrlSPARCDiagsVerbosity ::= TEXTUAL-CONVENTION
    STATUS deprecated
    DESCRIPTION
        "An enumerated value which contains all the possible states for
         the verbosity level for embedded diagnostics on the host.
         ***NOTE: this textual-convention is deprecated and replaced with
         ILOMCtrlSPARCDiagsVerbosityAdv."
    SYNTAX INTEGER {
        min(1),
        max(2),
        advsettings(3)
    }

ILOMCtrlSPARCDiagsVerbosityAdv ::= TEXTUAL-CONVENTION
    STATUS current
    DESCRIPTION
        "An enumerated value which contains all the possible states for
         the verbosity level for embedded diagnostics on the host."
    SYNTAX INTEGER {
        none(1),
        minimum(2),
        normal(3),
        maximum(4),
        debug(5)
    }

ILOMCtrlSPARCHostAutoRestartPolicy ::= TEXTUAL-CONVENTION
    STATUS current
    DESCRIPTION
        "An enumerated value which contains all the possible actions
         to perform when the SP determines that the host has hung."
    SYNTAX INTEGER {
        none(1),
        reset(2),
        dumpcore(3)
}

ILOMCtrlSPARCHostBootRestart ::= TEXTUAL-CONVENTION
    STATUS current
    DESCRIPTION
        "An enumerated value which contains all the possible actions
         to perform when the boot timer expires."
    SYNTAX INTEGER {
        none(1),
        reset(2)
}

ILOMCtrlSPARCHostBootFailRecovery ::= TEXTUAL-CONVENTION
    STATUS current
    DESCRIPTION
        "An enumerated value which contains all the possible actions
         to perform when the max boot failures allowed is reached."
    SYNTAX INTEGER {
        none(1),
        powercycle(2),
        poweroff(3)
}

ILOMCtrlSPARCHostSendBreakAction ::= TEXTUAL-CONVENTION
    STATUS current
    DESCRIPTION
        "Send Break Action to Host."
    SYNTAX INTEGER {
        nop(1),
        break(2),
        dumpcore(3)
}

ILOMCtrlSPARCHostIoReconfigurePolicy ::= TEXTUAL-CONVENTION
    STATUS current
    DESCRIPTION
        "An enumerated value which contains all the possible states
        for the host IO reconfiguration policy that is applied at next
        host power-on."
    SYNTAX INTEGER {
        false(1),
        nextboot(2),
        true(3)
}


ILOMCtrlSPARCBootModeState ::= TEXTUAL-CONVENTION
    STATUS current
    DESCRIPTION
        "An enumerated value which contains all the possible states for
         the boot mode state."
    SYNTAX INTEGER {
        normal(1),
        resetNvram(2)
    }

ILOMCtrlSPARCKeySwitchState ::= TEXTUAL-CONVENTION
    STATUS current
    DESCRIPTION
        "An enumerated value which contains all the possible states for
         the key switch."
    SYNTAX INTEGER {
        normal(1),
        standby(2),
        diag(3),
        locked(4)
    }

ILOMCtrlSPARCDiagsAction ::= TEXTUAL-CONVENTION
    STATUS current
    DESCRIPTION
        "An action to take to control POST running on the host."
    SYNTAX INTEGER {
        stop(1),
        start(2)
    }

ILOMCtrlSshKeyGenType ::= TEXTUAL-CONVENTION
    STATUS current
    DESCRIPTION
        "An enumerated value which contains all the possible key types for
         ssh."
    SYNTAX INTEGER {
        none(1),
        rsa(2),
        dsa(3)
    }

ILOMCtrlThdAction ::= TEXTUAL-CONVENTION
    STATUS current
    DESCRIPTION
        "An enumerated value which contains all the possible control actions
         for a THD module."
    SYNTAX INTEGER {
        suspend(1),
        resume(2),
        nop(3)
    }

ILOMCtrlBackupAndRestoreAction ::= TEXTUAL-CONVENTION
    STATUS current
    DESCRIPTION
        "An action to start Backup or Restore operation."
    SYNTAX INTEGER {
        backup(1),
        restore(2)
    }


-- ***************************************************************************
-- *                            ilomCtrlNtp                                  *
-- ***************************************************************************

-- This section provides the properties for configuring the NTP protocol
-- settings.

ilomCtrlDeviceNTPServerOneIP OBJECT-TYPE
    SYNTAX IpAddress
    MAX-ACCESS read-write
    STATUS current
    DESCRIPTION
        "The IP address of the first NTP server used by the device.
         This property is ignored if NTP is not enabled."
    ::= { ilomCtrlNtp 1 }

ilomCtrlDeviceNTPServerTwoIP OBJECT-TYPE
    SYNTAX IpAddress
    MAX-ACCESS read-write
    STATUS current
    DESCRIPTION
        "The IP address of the second NTP server used by the device.
         This property is ignored if NTP is not enabled."
    ::= { ilomCtrlNtp 2 }


-- ***************************************************************************
-- *                             ilomCtrlLdap                                *
-- ***************************************************************************

-- This section provides properties for configuring the embedded LDAP
-- client.

ilomCtrlLdapEnabled OBJECT-TYPE
    SYNTAX TruthValue
    MAX-ACCESS read-write
    STATUS current
    DESCRIPTION
        "Specifies whether or not the LDAP client is enabled."
    ::= { ilomCtrlLdap 1 }

ilomCtrlLdapServerIP OBJECT-TYPE
    SYNTAX IpAddress
    MAX-ACCESS read-write
    STATUS current
    DESCRIPTION
        "The IP address of the LDAP server used as a name service for
         user accounts."
    ::= { ilomCtrlLdap 2 }

ilomCtrlLdapPortNumber OBJECT-TYPE
    SYNTAX Integer32 (0..65535)
    MAX-ACCESS read-write
    STATUS current
    DESCRIPTION
        "Specifies the port number for the LDAP client."
    ::= { ilomCtrlLdap 3 }

ilomCtrlLdapBindDn OBJECT-TYPE
    SYNTAX SnmpAdminString
    MAX-ACCESS read-write
    STATUS current
    DESCRIPTION
        "The distinguished name (DN) for the read-only proxy user used to bind
         to the LDAP server. Example: cn=proxyuser,ou=people,dc=sun,dc=com"
    ::= { ilomCtrlLdap 4 }

ilomCtrlLdapBindPassword OBJECT-TYPE
    SYNTAX SnmpAdminString
    MAX-ACCESS read-write
    STATUS current
    DESCRIPTION
        "The password of a read-only proxy user which is used to bind
         to the LDAP server.  This property is essentially write-only.
         The write-only access level is no longer supported as of SNMPv2.
         This property must return a null value when read."
    ::= { ilomCtrlLdap 5 }

ilomCtrlLdapSearchBase OBJECT-TYPE
    SYNTAX SnmpAdminString
    MAX-ACCESS read-write
    STATUS current
    DESCRIPTION
        "A search base in the LDAP database below which to find users.
         Example: ou=people,dc=sun,dc=com"
    ::= { ilomCtrlLdap 6 }

ilomCtrlLdapDefaultRole OBJECT-TYPE
    SYNTAX ILOMCtrlUserRole
    MAX-ACCESS read-write
    STATUS deprecated
    DESCRIPTION
        "Specifies the role that a user authenticated via LDAP should have.
         ***NOTE: this object is deprecated and replaced by
         ilomCtrlLdapDefaultRoles."
    ::= { ilomCtrlLdap 7 }

ilomCtrlLdapDefaultRoles OBJECT-TYPE
    SYNTAX ILOMCtrlUserRoles
    MAX-ACCESS read-write
    STATUS current
    DESCRIPTION
        "Specifies the role that a user authenticated via LDAP should have.
         This property supports the legacy roles of 'Administrator' or
         'Operator', or any of the individual role ID combinations
         of 'a', 'u', 'c', 'r', 'o' and 's' (like 'aucro') where
         a-admin, u-user, c-console, r-reset, s-service and o-readOnly."
    ::= { ilomCtrlLdap 8 }


-- ***************************************************************************
-- *                             ilomCtrlRadius                              *
-- ***************************************************************************

-- This section provides properties for configuring the embedded RADIUS
-- client.

ilomCtrlRadiusEnabled OBJECT-TYPE
    SYNTAX TruthValue
    MAX-ACCESS read-write
    STATUS current
    DESCRIPTION
        "Specifies whether or not the RADIUS client is enabled."
    ::= { ilomCtrlRadius 1 }

ilomCtrlRadiusServerIP OBJECT-TYPE
    SYNTAX IpAddress
    MAX-ACCESS read-write
    STATUS current
    DESCRIPTION
        "The IP address of the RADIUS server used as a name service for
         user accounts."
    ::= { ilomCtrlRadius 2 }

ilomCtrlRadiusPortNumber OBJECT-TYPE
    SYNTAX Integer32 (0..65535)
    MAX-ACCESS read-write
    STATUS current
    DESCRIPTION
        "Specifies the port number for the RADIUS client."
    ::= { ilomCtrlRadius 3 }

ilomCtrlRadiusSecret OBJECT-TYPE
    SYNTAX SnmpAdminString
    MAX-ACCESS read-write
    STATUS current
    DESCRIPTION
        "The shared secret encryption key that is used to encypt traffic between
         the RADIUS client and server."
    ::= { ilomCtrlRadius 4 }

ilomCtrlRadiusDefaultRole OBJECT-TYPE
    SYNTAX ILOMCtrlUserRole
    MAX-ACCESS read-write
    STATUS deprecated
    DESCRIPTION
        "Specifies the role that a user authenticated via RADIUS should have.
         ***NOTE: this object is deprecated and replaced by ILOMCtrlUserRoles."
    ::= { ilomCtrlRadius 5 }

ilomCtrlRadiusDefaultRoles OBJECT-TYPE
    SYNTAX ILOMCtrlUserRoles
    MAX-ACCESS read-write
    STATUS current
    DESCRIPTION
        "Specifies the role that a user authenticated via RADIUS should have.
         This property supports the legacy roles of 'Administrator' or
         'Operator', or any of the individual role ID combinations
         of 'a', 'u', 'c', 'r', 'o' and 's' (like 'aucro') where
         a-admin, u-user, c-console, r-reset, s-service and o-readOnly."
    ::= { ilomCtrlRadius 6 }


-- ***************************************************************************
-- *                      ilomCtrlRemoteSyslog                               *
-- ***************************************************************************

-- This section provides properties for configuring remote syslog destinations
-- to which log entries will be forwarded.

ilomCtrlRemoteSyslogDest1 OBJECT-TYPE
    SYNTAX IpAddress
    MAX-ACCESS read-write
    STATUS current
    DESCRIPTION
        "The IP address of the first remote syslog destination (log host)."
    ::= { ilomCtrlRemoteSyslog 1 }

ilomCtrlRemoteSyslogDest2 OBJECT-TYPE
    SYNTAX IpAddress
    MAX-ACCESS read-write
    STATUS current
    DESCRIPTION
        "The IP address of the second remote syslog destination (log host)."
    ::= { ilomCtrlRemoteSyslog 2 }


-- ***************************************************************************
-- *                             ilomCtrlHttp                                *
-- ***************************************************************************

-- This section provides properties for configuring the embedded Web server
-- on the device.

ilomCtrlHttpEnabled OBJECT-TYPE
    SYNTAX TruthValue
    MAX-ACCESS read-write
    STATUS current
    DESCRIPTION
        "Specifies whether or not the embedded web server should be
         running and listening on the HTTP port."
    ::= { ilomCtrlHttp 1 }

ilomCtrlHttpPortNumber OBJECT-TYPE
    SYNTAX Integer32 (0..65535)
    MAX-ACCESS read-write
    STATUS current
    DESCRIPTION
        "Specifies the port number that the embedded web server should
         listen to for HTTP requests."
    ::= { ilomCtrlHttp 2 }

ilomCtrlHttpSecureRedirect OBJECT-TYPE
    SYNTAX TruthValue
    MAX-ACCESS read-write
    STATUS current
    DESCRIPTION
        "Specifies whether or not the embedded web server should
         redirect HTTP connections to HTTPS."
    ::= { ilomCtrlHttp 3 }


-- ***************************************************************************
-- *                             ilomCtrlHttps                               *
-- ***************************************************************************

-- This section provides properties for configuring the embedded Web server
-- on the device.

ilomCtrlHttpsEnabled OBJECT-TYPE
    SYNTAX TruthValue
    MAX-ACCESS read-write
    STATUS current
    DESCRIPTION
        "Specifies whether or not the embedded web server should be
         running and listening on the HTTPS port."
    ::= { ilomCtrlHttps 1 }

ilomCtrlHttpsPortNumber OBJECT-TYPE
    SYNTAX Integer32 (0..65535)
    MAX-ACCESS read-write
    STATUS current
    DESCRIPTION
        "Specifies the port number that the embedded web server should
         listen to for HTTPS requests."
    ::= { ilomCtrlHttps 2 }


-- ***************************************************************************
-- *                             ilomCtrlSsh                                 *
-- ***************************************************************************

-- This section provides properties for viewing the secure shell settings
-- for the device.

ilomCtrlSshRsaKeyFingerprint OBJECT-TYPE
    SYNTAX SnmpAdminString
    MAX-ACCESS read-only
    STATUS current
    DESCRIPTION
        "The fingerprint of the RSA key used for the SSH protocol."
    ::= { ilomCtrlSsh 1 }

ilomCtrlSshRsaKeyLength OBJECT-TYPE
    SYNTAX Integer32 (0..65535)
    MAX-ACCESS read-only
    STATUS current
    DESCRIPTION
        "The length of the RSA key used for the SSH protocol."
    ::= { ilomCtrlSsh 2 }

ilomCtrlSshDsaKeyFingerprint OBJECT-TYPE
    SYNTAX SnmpAdminString
    MAX-ACCESS read-only
    STATUS current
    DESCRIPTION
        "The fingerprint of the DSA key used for the SSH protocol."
    ::= { ilomCtrlSsh 3 }

ilomCtrlSshDsaKeyLength OBJECT-TYPE
    SYNTAX Integer32 (0..65535)
    MAX-ACCESS read-only
    STATUS current
    DESCRIPTION
        "The length of the DSA key used for the SSH protocol."
    ::= { ilomCtrlSsh 4 }

ilomCtrlSshGenerateNewKeyAction OBJECT-TYPE
    SYNTAX TruthValue
    MAX-ACCESS read-write
    STATUS current
    DESCRIPTION
        "This property is used to initiate a new public key generation."
    ::= { ilomCtrlSsh 5 }

ilomCtrlSshGenerateNewKeyType OBJECT-TYPE
    SYNTAX ILOMCtrlSshKeyGenType
    MAX-ACCESS read-write
    STATUS current
    DESCRIPTION
        "SSH new key type. The possible type are rsa(2), dsa(3)."
    ::= { ilomCtrlSsh 6 }

ilomCtrlSshRestartSshdAction OBJECT-TYPE
    SYNTAX TruthValue
    MAX-ACCESS read-write
    STATUS current
    DESCRIPTION
        "This property is used to initiate sshd restart."
    ::= { ilomCtrlSsh 7 }

ilomCtrlSshEnabled OBJECT-TYPE
    SYNTAX TruthValue
    MAX-ACCESS read-write
    STATUS current
    DESCRIPTION
        "Speicfies whether or not the SSHD is enabled."
    ::= { ilomCtrlSsh 8 }


-- ***************************************************************************
-- *                          ilomCtrlSingleSignon                           *
-- ***************************************************************************

-- This section provides a property for controlling the single sign-on
-- authentication behavior of the device.

ilomCtrlSingleSignonEnabled OBJECT-TYPE
    SYNTAX TruthValue
    MAX-ACCESS read-write
    STATUS current
    DESCRIPTION
        "Specified whether single sign-on authentication should be
         enabled on the device.  Single sign-on allows tokens to be passed
         around so that it is not necessary to re-enter passwords between
         different applications.  This would allow single sign-on between
         the SC web interface and the SP web interface, between the SC
         command-line interface and the SP command-line interface, and
         between the SC and SP interfaces and the Java Remote Console
         application."
    ::= { ilomCtrlSingleSignon 1 }


-- ***************************************************************************
-- *                      ilomCtrlNetwork                                    *
-- ***************************************************************************

-- This section provides properties for configuring the network for
-- the system controller and/or service processor(s).

ilomCtrlNetworkTable OBJECT-TYPE
    SYNTAX SEQUENCE OF ILOMCtrlNetworkEntry
    MAX-ACCESS not-accessible
    STATUS current
    DESCRIPTION
        "A table listing all targets whose networks can be controlled."
    ::= { ilomCtrlNetwork 1 }

ilomCtrlNetworkEntry OBJECT-TYPE
    SYNTAX ILOMCtrlNetworkEntry
    MAX-ACCESS not-accessible
    STATUS current
    DESCRIPTION
        "An entry for a target which can be reset."
    INDEX { ilomCtrlNetworkTarget }
    ::= { ilomCtrlNetworkTable 1 }

ILOMCtrlNetworkEntry ::= SEQUENCE {
        ilomCtrlNetworkTarget                   SnmpAdminString,
        ilomCtrlNetworkMacAddress               SnmpAdminString,
        ilomCtrlNetworkIpDiscovery              ILOMCtrlNetworkIpDiscovery,
        ilomCtrlNetworkIpAddress                IpAddress,
        ilomCtrlNetworkIpGateway                IpAddress,
        ilomCtrlNetworkIpNetmask                IpAddress,
        ilomCtrlNetworkPendingIpDiscovery       ILOMCtrlNetworkIpDiscovery,
        ilomCtrlNetworkPendingIpAddress         IpAddress,
        ilomCtrlNetworkPendingIpGateway         IpAddress,
        ilomCtrlNetworkPendingIpNetmask         IpAddress,
        ilomCtrlNetworkCommitPending            TruthValue,
        ilomCtrlNetworkOutOfBandMacAddress      SnmpAdminString,
        ilomCtrlNetworkSidebandMacAddress       SnmpAdminString,
        ilomCtrlNetworkPendingManagementPort    SnmpAdminString,
        ilomCtrlNetworkManagementPort           SnmpAdminString,
        ilomCtrlNetworkDHCPServerAddr           IpAddress,
        ilomCtrlNetworkState                    TruthValue
    }

ilomCtrlNetworkTarget OBJECT-TYPE
    SYNTAX SnmpAdminString
    MAX-ACCESS not-accessible
    STATUS current
    DESCRIPTION
        "This is the nomenclature name for a target which has a configurable
         network.  On some systems, there are multiple targets which have
         networks.  On a traditional, non-blade system, this table will contain
         only one row for the network configuration of the service processor,
         which has a nomenclature name of '/SP'.  On blade systems, this table
         will contain multiple rows.  There will be a row for '/SC' which
         allows for configuration of the system controller's network settings.
         In addition, there will be rows for each blade's service processor.
         For example, a blade's service processor nomenclature takes the form of
         '/CH/BL0/SP', '/CH/BL1/SP' and so on.  This will allow for the
         configuration of the service processors from the system controller.
         In the case of redundant system controllers, the floating master IP
         addressed can be configured using a name of /MASTERSC."
    ::= { ilomCtrlNetworkEntry 1 }

ilomCtrlNetworkMacAddress OBJECT-TYPE
    SYNTAX SnmpAdminString
    MAX-ACCESS read-only
    STATUS current
    DESCRIPTION
        "Specifies the MAC address of the service processor or system controller."
    ::= { ilomCtrlNetworkEntry 2 }

ilomCtrlNetworkIpDiscovery OBJECT-TYPE
    SYNTAX ILOMCtrlNetworkIpDiscovery
    MAX-ACCESS read-only
    STATUS current
    DESCRIPTION
        "Specifies whether the current target is configured to have static
         IP settings or whether these settings are retrieved dynamically from DHCP."
    ::= { ilomCtrlNetworkEntry 3 }

ilomCtrlNetworkIpAddress OBJECT-TYPE
    SYNTAX IpAddress
    MAX-ACCESS read-only
    STATUS current
    DESCRIPTION
        "Indicates the current IP address for the given target."
    ::= { ilomCtrlNetworkEntry 4 }

ilomCtrlNetworkIpGateway OBJECT-TYPE
    SYNTAX IpAddress
    MAX-ACCESS read-only
    STATUS current
    DESCRIPTION
        "Indicates the current IP gateway for the given target."
    ::= { ilomCtrlNetworkEntry 5 }

ilomCtrlNetworkIpNetmask OBJECT-TYPE
    SYNTAX IpAddress
    MAX-ACCESS read-only
    STATUS current
    DESCRIPTION
        "Indicates the current IP netmask for the given target."
    ::= { ilomCtrlNetworkEntry 6 }

ilomCtrlNetworkPendingIpDiscovery OBJECT-TYPE
    SYNTAX ILOMCtrlNetworkIpDiscovery
    MAX-ACCESS read-write
    STATUS current
    DESCRIPTION
        "This property is used to set the pending value for the mode of
         IP discovery for the given target.  The possible values are static(1)
         or dynamic(2).  Static values can be specified by setting the other
         pending properties in this table: ilomCtrlNetworkPendingIpAddress,
         ilomCtrlNetworkPendingIpGateway, and ilomCtrlNetworkPendingIpNetmask.
         If dynamic is specified, the other pending properties should
         not be set.  This property does not take effect until the
         ilomCtrlNetworkCommitPending property is set to true for the
         given row."
    ::= { ilomCtrlNetworkEntry 7 }

ilomCtrlNetworkPendingIpAddress OBJECT-TYPE
    SYNTAX IpAddress
    MAX-ACCESS read-write
    STATUS current
    DESCRIPTION
        "This property is used to set the pending IP address for the given
         target.  This property does not take effect until the
         ilomCtrlNetworkCommitPending property is set to true for the
         given row."
    ::= { ilomCtrlNetworkEntry 8 }

ilomCtrlNetworkPendingIpGateway OBJECT-TYPE
    SYNTAX IpAddress
    MAX-ACCESS read-write
    STATUS current
    DESCRIPTION
        "This property is used to set the pending IP gateway for the given
         target.  This property does not take effect until the
         ilomCtrlNetworkCommitPending property is set to true for the
         given row."
    ::= { ilomCtrlNetworkEntry 9 }

ilomCtrlNetworkPendingIpNetmask OBJECT-TYPE
    SYNTAX IpAddress
    MAX-ACCESS read-write
    STATUS current
    DESCRIPTION
        "This property is used to set the pending IP netmask for the given
         target.  This property does not take effect until the
         ilomCtrlNetworkCommitPending property is set to true for the
         given row."
    ::= { ilomCtrlNetworkEntry 10 }

ilomCtrlNetworkCommitPending OBJECT-TYPE
    SYNTAX TruthValue
    MAX-ACCESS read-write
    STATUS current
    DESCRIPTION
        "This property is used to commit pending properties for the given row.
         Settings this property to true(1) will cause the network to be
         reconfigured according to the values specified in the other pending
         properties."
    ::= { ilomCtrlNetworkEntry 11 }

ilomCtrlNetworkOutOfBandMacAddress OBJECT-TYPE
    SYNTAX SnmpAdminString
    MAX-ACCESS read-only
    STATUS current
    DESCRIPTION
        "Specifies the MAC address of the out of band management interface (where applicable)"
    ::= { ilomCtrlNetworkEntry 12 }

ilomCtrlNetworkSidebandMacAddress OBJECT-TYPE
    SYNTAX SnmpAdminString
    MAX-ACCESS read-only
    STATUS current
    DESCRIPTION
        "Specifies the MAC address of the sideband management interface (where applicable)"
    ::= { ilomCtrlNetworkEntry 13 }

ilomCtrlNetworkPendingManagementPort OBJECT-TYPE
    SYNTAX SnmpAdminString
    MAX-ACCESS read-write
    STATUS current
    DESCRIPTION
         "This property is used to set the pending management port
         for the giventarget.  This property does not take effect until the
         ilomCtrlNetworkCommitPending property is set to true for the
         given row."
    ::= { ilomCtrlNetworkEntry 14 }

ilomCtrlNetworkManagementPort OBJECT-TYPE
    SYNTAX SnmpAdminString
    MAX-ACCESS read-write
    STATUS current
    DESCRIPTION
        "Indicates the current managment port for the given target"
    ::= { ilomCtrlNetworkEntry 15 }

ilomCtrlNetworkDHCPServerAddr OBJECT-TYPE
    SYNTAX IpAddress
    MAX-ACCESS read-only
    STATUS current
    DESCRIPTION
        "The address of the DHCP server for this row."
    ::= { ilomCtrlNetworkEntry 16 }

ilomCtrlNetworkState OBJECT-TYPE
    SYNTAX TruthValue
    MAX-ACCESS read-write
    STATUS current
    DESCRIPTION
        "Specifies whether or not the row is enabled."
    ::= { ilomCtrlNetworkEntry 17 }


-- ***************************************************************************
-- *                           ilomCtrlUsers                                  *
-- ***************************************************************************

-- This section provides properties for creating and removing local
-- users on the device and setting their password.

-- While deprecated, the use of ilomCtrlLocalUserAuthTable will work as
-- before, with the Role to Roles transformation noted above.
-- All users shown in either ilomCtrlLocalUserAuthTable or
-- ilomCtrlLocalUserTable will be shown in both.
-- Where Roles for a user in the latter do not match one of the defined
-- Role mappings, other(4) will be shown.

ilomCtrlLocalUserAuthTable OBJECT-TYPE
    SYNTAX SEQUENCE OF ILOMCtrlLocalUserAuthEntry
    MAX-ACCESS not-accessible
    STATUS deprecated
    DESCRIPTION
        "This table provides a listing of the current local users on a
         system along with their password state.
         ***NOTE: this table is deprecated and replaced with
         ilomCtrlLocalUserTable."
    ::= { ilomCtrlUsers 1 }

ilomCtrlLocalUserAuthEntry OBJECT-TYPE
    SYNTAX ILOMCtrlLocalUserAuthEntry
    MAX-ACCESS not-accessible
    STATUS  deprecated
    DESCRIPTION
        "An entry containing objects for a local user in the database.
         ***NOTE: this object is deprecated and replaced with
         ilomCtrlLocalUserEntry."
    INDEX { ilomCtrlLocalUserAuthUsername }
    ::= { ilomCtrlLocalUserAuthTable 1 }

ILOMCtrlLocalUserAuthEntry ::= SEQUENCE {
        ilomCtrlLocalUserAuthUsername           SnmpAdminString,
        ilomCtrlLocalUserAuthPassword           SnmpAdminString,
        ilomCtrlLocalUserAuthRole               ILOMCtrlUserRole,
        ilomCtrlLocalUserAuthRowStatus          RowStatus,
        ilomCtrlLocalUserAuthCLIMode            ILOMCtrlLocalUserAuthCLIMode
    }

ilomCtrlLocalUserAuthUsername OBJECT-TYPE
    SYNTAX SnmpAdminString
    MAX-ACCESS not-accessible
    STATUS deprecated
    DESCRIPTION
        "The username of a local user on the device.
         ***NOTE: this object is deprecated and replaced with
         ilomCtrlLocalUserUsername."
    ::= { ilomCtrlLocalUserAuthEntry 1 }

ilomCtrlLocalUserAuthPassword OBJECT-TYPE
    SYNTAX SnmpAdminString
    MAX-ACCESS read-create
    STATUS deprecated
    DESCRIPTION
        "The password of a local user on the device.  This
         property is essentially write-only.  The write-only
         access level is no longer supported as of SNMPv2.
         This property must return a null value when read.
         ***NOTE: this object is deprecated and replaced with
         ilomCtrlLocalUserPassword."
    ::= { ilomCtrlLocalUserAuthEntry 2 }

ilomCtrlLocalUserAuthRole OBJECT-TYPE
    SYNTAX ILOMCtrlUserRole
    MAX-ACCESS read-write
    STATUS deprecated
    DESCRIPTION
        "Specifies whether a user's password is assigned or unassigned.
         ***NOTE: this object is deprecated and replaced with
         ilomCtrlLocalUserRoles."
    ::= { ilomCtrlLocalUserAuthEntry 3 }

ilomCtrlLocalUserAuthRowStatus OBJECT-TYPE
    SYNTAX RowStatus
    MAX-ACCESS read-create
    STATUS deprecated
    DESCRIPTION
        "This object is used to create a new row or to delete
         an existing row in the table.  This property can be set
         to either createAndWait(5) or destroy(6), to create and remove
         a user respectively.
         ***NOTE: this object is deprecated and replaced with
         ilomCtrlLocalUserRowStatus."
    ::= { ilomCtrlLocalUserAuthEntry 4 }

ilomCtrlLocalUserAuthCLIMode OBJECT-TYPE
    SYNTAX ILOMCtrlLocalUserAuthCLIMode
    MAX-ACCESS read-write
    STATUS deprecated
    DESCRIPTION
        "Allows the CLI mode to be configured on a per-user basis.  The CLI mode
         determines which shell the user will interact with.  If the 'default'
         mode is select, the user will see the DMTF CLP after logging in via
         ssh or the console.  If the 'alom' mode is selected, the user will see
         the ALOM CMT shell after logging in via ssh or the console.
         ***NOTE: this object is deprecated and replaced with
         ilomCtrlLocalUserCLIMode."
    ::= { ilomCtrlLocalUserAuthEntry 5 }

ilomCtrlLocalUserTable OBJECT-TYPE
    SYNTAX SEQUENCE OF ILOMCtrlLocalUserEntry
    MAX-ACCESS not-accessible
    STATUS current
    DESCRIPTION
        "This table provides a listing of the current local users on a
         system along with their password state."
    ::= { ilomCtrlUsers 2 }

ilomCtrlLocalUserEntry OBJECT-TYPE
    SYNTAX ILOMCtrlLocalUserEntry
    MAX-ACCESS not-accessible
    STATUS current
    DESCRIPTION
        "An entry containing objects for a local user in the database."
    INDEX { ilomCtrlLocalUserUsername }
    ::= { ilomCtrlLocalUserTable 1 }

ILOMCtrlLocalUserEntry ::= SEQUENCE {
        ilomCtrlLocalUserUsername           ILOMCtrlLocalUserUsername,
        ilomCtrlLocalUserPassword           ILOMCtrlLocalUserPassword,
        ilomCtrlLocalUserRoles              ILOMCtrlUserRoles,
        ilomCtrlLocalUserRowStatus          RowStatus,
        ilomCtrlLocalUserCLIMode            ILOMCtrlLocalUserAuthCLIMode
    }

ilomCtrlLocalUserUsername OBJECT-TYPE
    SYNTAX ILOMCtrlLocalUserUsername
    MAX-ACCESS not-accessible
    STATUS current
    DESCRIPTION
        "The username of a local user on the device."
    ::= { ilomCtrlLocalUserEntry 1 }

ilomCtrlLocalUserPassword OBJECT-TYPE
    SYNTAX ILOMCtrlLocalUserPassword
    MAX-ACCESS read-create
    STATUS current
    DESCRIPTION
        "The password of a local user on the device.  This
         property is essentially write-only.  The write-only
         access level is no longer supported as of SNMPv2.
         This property must return a null value when read."
    ::= { ilomCtrlLocalUserEntry 2 }

ilomCtrlLocalUserRoles OBJECT-TYPE
    SYNTAX ILOMCtrlUserRoles
    MAX-ACCESS read-write
    STATUS current
    DESCRIPTION
        "Specifies the role that is associated with a user.  The roles can
         be assigned for the legacy roles of 'Administrator' or 'Operator', or
         any of the individual role IDs of 'a', 'u', 'c', 'r', 'o' and 's'.
         The role IDs can be joined together 'aucros' where a-admin, u-user,
         c-console, r-reset, s-service and o-readOnly."
    ::= { ilomCtrlLocalUserEntry 3 }

ilomCtrlLocalUserRowStatus OBJECT-TYPE
    SYNTAX RowStatus
    MAX-ACCESS read-create
    STATUS current
    DESCRIPTION
        "This object is used to create a new row or to delete
         an existing row in the table.  This property can be set
         to either createAndWait(5) or destroy(6), to create and remove
         a user respectively."
    ::= { ilomCtrlLocalUserEntry 4 }

ilomCtrlLocalUserCLIMode OBJECT-TYPE
    SYNTAX ILOMCtrlLocalUserAuthCLIMode
    MAX-ACCESS read-write
    STATUS current
    DESCRIPTION
        "Allows the CLI mode to be configured on a per-user basis.  The CLI mode
         determines which shell the user will interact with.  If the 'default'
         mode is select, the user will see the DMTF CLP after logging in via
         ssh or the console.  If the 'alom' mode is selected, the user will see
         the ALOM CMT shell after logging in via ssh or the console."
    ::= { ilomCtrlLocalUserEntry 5 }

-- ***************************************************************************
-- *                      ilomCtrlSessions                                   *
-- ***************************************************************************

-- This section provides properties for retriving a list of current active
-- active sessions.

ilomCtrlSessionsTable OBJECT-TYPE
    SYNTAX SEQUENCE OF ILOMCtrlSessionsEntry
    MAX-ACCESS not-accessible
    STATUS current
    DESCRIPTION
        "A table listing the current user sessions."
    ::= { ilomCtrlSessions 1 }

ilomCtrlSessionsEntry OBJECT-TYPE
    SYNTAX ILOMCtrlSessionsEntry
    MAX-ACCESS not-accessible
    STATUS current
    DESCRIPTION
        "An entry for a current session."
    INDEX { ilomCtrlSessionsId }
    ::= { ilomCtrlSessionsTable 1 }

ILOMCtrlSessionsEntry ::= SEQUENCE {
        ilomCtrlSessionsId                      Integer32,
        ilomCtrlSessionsUsername                SnmpAdminString,
        ilomCtrlSessionsConnectionType          ILOMCtrlSessionsConnectionType,
        ilomCtrlSessionsLoginTime               DateAndTime
    }

ilomCtrlSessionsId OBJECT-TYPE
    SYNTAX Integer32 (0..65535)
    MAX-ACCESS not-accessible
    STATUS current
    DESCRIPTION
        "The instance number of a given logged-in user.  This
         property is necessary since the same user can be logged
         in multiple times."
    ::= { ilomCtrlSessionsEntry 1 }

ilomCtrlSessionsUsername OBJECT-TYPE
    SYNTAX SnmpAdminString
    MAX-ACCESS read-only
    STATUS current
    DESCRIPTION
        "The username of the user associated with the session."
    ::= { ilomCtrlSessionsEntry 2 }

ilomCtrlSessionsConnectionType OBJECT-TYPE
    SYNTAX ILOMCtrlSessionsConnectionType
    MAX-ACCESS read-only
    STATUS current
    DESCRIPTION
        "The type of connection that the given user is using to
         access the device."
    ::= { ilomCtrlSessionsEntry 3 }

ilomCtrlSessionsLoginTime OBJECT-TYPE
    SYNTAX DateAndTime
    MAX-ACCESS read-only
    STATUS current
    DESCRIPTION
        "The date and time that the logged into the device."
    ::= { ilomCtrlSessionsEntry 4 }


-- ***************************************************************************
-- *                         ilomCtrlFirmwareMgmt                            *
-- ***************************************************************************

-- These properties are used to manage the firmware on the device.  The firmware
-- image itself is not tranferred via SNMP.  Instead, the MIB can be used to
-- initiate the transfer of the image via TFTP.

ilomCtrlFirmwareMgmtVersion OBJECT-TYPE
    SYNTAX SnmpAdminString
    MAX-ACCESS read-only
    STATUS current
    DESCRIPTION
        "The version of the current firmware image."
    ::= { ilomCtrlFirmwareMgmt 1 }

ilomCtrlFirmwareBuildNumber OBJECT-TYPE
    SYNTAX Integer32 (0..65535)
    MAX-ACCESS read-only
    STATUS current
    DESCRIPTION
        "The build number of the current firmware image."
    ::= { ilomCtrlFirmwareMgmt 2 }

ilomCtrlFirmwareBuildDate OBJECT-TYPE
    SYNTAX SnmpAdminString
    MAX-ACCESS read-only
    STATUS current
    DESCRIPTION
        "The build date and time of the current firmware image."
    ::= { ilomCtrlFirmwareMgmt 3 }

ilomCtrlFirmwareTFTPServerIP OBJECT-TYPE
    SYNTAX IpAddress
    MAX-ACCESS read-write
    STATUS current
    DESCRIPTION
        "The IP address of the TFTP server which will be used to download the
         the firmware image."
    ::= { ilomCtrlFirmwareMgmt 4 }

ilomCtrlFirmwareTFTPFileName OBJECT-TYPE
    SYNTAX SnmpAdminString
    MAX-ACCESS read-write
    STATUS current
    DESCRIPTION
        "The relative path of the new firmware image file on the TFTP server."
    ::= { ilomCtrlFirmwareMgmt 5 }

ilomCtrlFirmwarePreserveConfig OBJECT-TYPE
    SYNTAX TruthValue
    MAX-ACCESS read-write
    STATUS current
    DESCRIPTION
        "This property determines whether the previous configuration of the device
         should be preserved after a firmware update.  The configuration data includes
         all users information, configuration of clients and services, and any logs.
         The default value of this property is true."
    ::= { ilomCtrlFirmwareMgmt 6 }

ilomCtrlFirmwareMgmtStatus OBJECT-TYPE
    SYNTAX ILOMCtrlFirmwareUpdateStatus
    MAX-ACCESS read-only
    STATUS current
    DESCRIPTION
        "This property indicates the status of a firmware update.  If a TFTP error
         occurred while attempting to upload a new firmware image, the value of
         this property will be tftpError(1).  If the image was uploaded correctly but
         it did not pass verification, the value of this property will be
         imageVerificationFailed(2).  Otherwise, the status will indicate that the
         update is inProgress(3) or is a success(4).  A firmware update could take
         as long as 20 minutes.  During this time, no other operations should be
         performed on the device.  Upon success, the device will be reset."
    ::= { ilomCtrlFirmwareMgmt 7 }

ilomCtrlFirmwareMgmtAction OBJECT-TYPE
    SYNTAX ILOMCtrlFirmwareUpdateAction
    MAX-ACCESS read-write
    STATUS current
    DESCRIPTION
        "This property is used to initiate a firmware update using the values
         of the other firmware management properties as parameters.  It can
         also clear the values of those parameters.   To initiate a firmware
         update, set the value of this property to initate(2).  To clear the
         values of the writeable firmware management properties, set this
         propery to clearProperties(1).  Before initiating a firmware update,
         the ilomCtrlFirmwareTFTPServerIP, ilomCtrlFirmwareTFTPFileName,
         and ilomCtrlFirmwarePreserveConfig properties must be set.  After
         intiating a firmware update, the ilomCtrlFirmwareMgmtStatus
         property can be used to determine if the operation was successful.
         This is effectively a write-only property."
    ::= { ilomCtrlFirmwareMgmt 8 }

ilomCtrlFirmwareMgmtFilesystemVersion OBJECT-TYPE
    SYNTAX SnmpAdminString
    MAX-ACCESS read-only
    STATUS current
    DESCRIPTION
        "The version of the current file system."
    ::= { ilomCtrlFirmwareMgmt 9 }

ilomCtrlFirmwareDelayBIOS OBJECT-TYPE
    SYNTAX TruthValue
    MAX-ACCESS read-write
    STATUS current
    DESCRIPTION
      "On servers that support a BIOS, this property is used to postpone the
       BIOS upgrade until the next server poweroff. Setting this property to
       'false' will cause the server to be forced off if a BIOS upgrade is
       necessary.
       The default value of this property is false."
    ::= { ilomCtrlFirmwareMgmt 10 }


-- ***************************************************************************
-- *                      ilomCtrlEventLog                                   *
-- ***************************************************************************

-- This section provides the ability to view the event logs which are stored
-- on the device.

ilomCtrlEventLogTable OBJECT-TYPE
    SYNTAX SEQUENCE OF ILOMCtrlEventLogEntry
    MAX-ACCESS not-accessible
    STATUS current
    DESCRIPTION
        "This table provides a list of the current entries in the
         event log."
    ::= { ilomCtrlEventLog 1 }

ilomCtrlEventLogEntry OBJECT-TYPE
    SYNTAX ILOMCtrlEventLogEntry
    MAX-ACCESS not-accessible
    STATUS current
    DESCRIPTION
        "An entry in the event logs table."
    INDEX { ilomCtrlEventLogRecordID }
    ::= { ilomCtrlEventLogTable 1 }

ILOMCtrlEventLogEntry ::= SEQUENCE {
        ilomCtrlEventLogRecordID                Unsigned32,
        ilomCtrlEventLogType                    ILOMCtrlEventLogType,
        ilomCtrlEventLogTimestamp               DateAndTime,
        ilomCtrlEventLogClass                   ILOMCtrlEventLogClass,
        ilomCtrlEventLogSeverity                ILOMCtrlEventSeverity,
        ilomCtrlEventLogDescription             SnmpAdminString
    }

ilomCtrlEventLogRecordID OBJECT-TYPE
    SYNTAX Unsigned32
    MAX-ACCESS not-accessible
    STATUS current
    DESCRIPTION
        "The record number for a given the event log entry."
    ::= { ilomCtrlEventLogEntry 1 }

ilomCtrlEventLogType OBJECT-TYPE
    SYNTAX ILOMCtrlEventLogType
    MAX-ACCESS read-only
    STATUS current
    DESCRIPTION
        "An integer representing the type of event."
    ::= { ilomCtrlEventLogEntry 2 }

ilomCtrlEventLogTimestamp OBJECT-TYPE
    SYNTAX DateAndTime
    MAX-ACCESS read-only
    STATUS current
    DESCRIPTION
        "The date and time that the event log entry was recorded."
    ::= { ilomCtrlEventLogEntry 3 }

ilomCtrlEventLogClass OBJECT-TYPE
    SYNTAX ILOMCtrlEventLogClass
    MAX-ACCESS read-only
    STATUS current
    DESCRIPTION
        "An integer representing the class of event."
    ::= { ilomCtrlEventLogEntry 4 }

ilomCtrlEventLogSeverity OBJECT-TYPE
    SYNTAX ILOMCtrlEventSeverity
    MAX-ACCESS read-only
    STATUS current
    DESCRIPTION
        "The event severity corresponding to the given log entry."
    ::= { ilomCtrlEventLogEntry 5 }

ilomCtrlEventLogDescription OBJECT-TYPE
    SYNTAX SnmpAdminString
    MAX-ACCESS read-only
    STATUS current
    DESCRIPTION
        "A textual description of the event."
    ::= { ilomCtrlEventLogEntry 6 }


ilomCtrlEventLogClear OBJECT-TYPE
    SYNTAX TruthValue
    MAX-ACCESS read-write
    STATUS current
    DESCRIPTION
        "When set to 'true' clears the event log."
    ::= { ilomCtrlEventLog 2 }

-- ***************************************************************************
-- *                         ilomCtrlAlerts                                  *
-- ***************************************************************************

-- This section provides the ability to configure alerts, such as e-mail
-- notifications, snmp traps, or remote syslog.

ilomCtrlAlertsTable OBJECT-TYPE
    SYNTAX SEQUENCE OF ILOMCtrlAlertsEntry
    MAX-ACCESS not-accessible
    STATUS current
    DESCRIPTION
        "This table is used to view and add alert rules."
    ::= { ilomCtrlAlerts 1 }

ilomCtrlAlertsEntry OBJECT-TYPE
    SYNTAX ILOMCtrlAlertsEntry
    MAX-ACCESS not-accessible
    STATUS current
    DESCRIPTION
        "An entry containing objects for an alert rule."
    INDEX { ilomCtrlAlertID }
    ::= { ilomCtrlAlertsTable 1 }

ILOMCtrlAlertsEntry ::= SEQUENCE {
        ilomCtrlAlertID                         Integer32,
        ilomCtrlAlertSeverity                   ILOMCtrlEventSeverity,
        ilomCtrlAlertType                       ILOMCtrlAlertType,
        ilomCtrlAlertDestinationIP              IpAddress,
        ilomCtrlAlertDestinationEmail           SnmpAdminString,
        ilomCtrlAlertSNMPVersion                ILOMCtrlAlertSNMPVersion,
        ilomCtrlAlertSNMPCommunityOrUsername    SnmpAdminString,
        ilomCtrlAlertDestinationPort            Integer32,
        ilomCtrlAlertEmailEventClassFilter      SnmpAdminString,
        ilomCtrlAlertEmailEventTypeFilter       SnmpAdminString,
        ilomCtrlAlertEmailCustomSender          SnmpAdminString,
        ilomCtrlAlertEmailMessagePrefix         SnmpAdminString
    }

ilomCtrlAlertID OBJECT-TYPE
    SYNTAX Integer32 (0..65535)
    MAX-ACCESS not-accessible
    STATUS current
    DESCRIPTION
        "An integer ID associated with a given alert rule."
    ::= { ilomCtrlAlertsEntry 1 }

ilomCtrlAlertSeverity OBJECT-TYPE
    SYNTAX ILOMCtrlEventSeverity
    MAX-ACCESS read-write
    STATUS current
    DESCRIPTION
        "This property specifies the mininum event severity which should
         trigger an alert, for a given class."
    ::= { ilomCtrlAlertsEntry 2 }

ilomCtrlAlertType OBJECT-TYPE
    SYNTAX ILOMCtrlAlertType
    MAX-ACCESS read-write
    STATUS current
    DESCRIPTION
        "This property specifies the type of notification for a given alert.
         If the type is snmptrap(2) or ipmipet(3), the ilomCtrlAlertDestinationIP
         must be specified. If the type is email(1), the ilomCtrlAlertDestinationEmail
         must be specified."
    ::= { ilomCtrlAlertsEntry 3 }

ilomCtrlAlertDestinationIP OBJECT-TYPE
    SYNTAX IpAddress
    MAX-ACCESS read-write
    STATUS current
    DESCRIPTION
        "This property species the IP address to send alert notifications when
         the alert type is snmptrap(2), ipmipet(3), or remotesyslog(4)."
    ::= { ilomCtrlAlertsEntry 4}

ilomCtrlAlertDestinationEmail OBJECT-TYPE
    SYNTAX SnmpAdminString
    MAX-ACCESS read-write
    STATUS current
    DESCRIPTION
        "This property species the email address to send alert notifications when
         the alert type is email(1)."
    ::= { ilomCtrlAlertsEntry 5}

ilomCtrlAlertSNMPVersion OBJECT-TYPE
    SYNTAX ILOMCtrlAlertSNMPVersion
    MAX-ACCESS read-write
    STATUS current
    DESCRIPTION
        "The version of SNMP trap that should be used for the given
         alert rule."
    ::= { ilomCtrlAlertsEntry 6 }

ilomCtrlAlertSNMPCommunityOrUsername OBJECT-TYPE
    SYNTAX SnmpAdminString
    MAX-ACCESS read-write
    STATUS current
    DESCRIPTION
        "This string specifies the community string to be used when the
         ilomCtrlAlertSNMPVersion property is set to 'v1' or 'v2c'.
         Alternatively, this string specifies the SNMP username to use
         when the ilomCtrlAlertSNMPVersion is set to 'v3'."
    ::= { ilomCtrlAlertsEntry 7 }

ilomCtrlAlertDestinationPort OBJECT-TYPE
    SYNTAX Integer32 (0..65535)
    MAX-ACCESS read-write
    STATUS current
    DESCRIPTION
        "Destination port for SNMP traps, 0 maps to the default"
    ::= { ilomCtrlAlertsEntry 8 }

ilomCtrlAlertEmailEventClassFilter OBJECT-TYPE
    SYNTAX SnmpAdminString
    MAX-ACCESS read-write
    STATUS current
    DESCRIPTION
        "A class name or 'all' to filter emailed alerts on."
    ::= { ilomCtrlAlertsEntry 9 }

ilomCtrlAlertEmailEventTypeFilter OBJECT-TYPE
    SYNTAX SnmpAdminString
    MAX-ACCESS read-write
    STATUS current
    DESCRIPTION
        "A type name or 'all' to filter emailed alerts on."
    ::= { ilomCtrlAlertsEntry 10 }

ilomCtrlAlertEmailCustomSender OBJECT-TYPE
    SYNTAX SnmpAdminString (SIZE (0..80))
    MAX-ACCESS read-write
    STATUS current
    DESCRIPTION
        "An optional format to identify the sender or the 'from' address.
         Customizing this string allows the user to specify the exact contents
         (up to 80 chars) of the 'from' field in the email message. Either one
         of the substitution strings '<IPADDRESS>' or '<HOSTNAME>' can be used
         as needed. By default, this parameter is an empty string, which
         results in the standard ILOM formatted originator for the
         alerts. e.g., ilom-sp@sp1302.dev.sun.com, sun-ilom@[<IPADDRESS>],
         or ilom-alert@<HOSTNAME>.abc.com"
   DEFVAL { "" }
    ::= { ilomCtrlAlertsEntry 11 }

ilomCtrlAlertEmailMessagePrefix OBJECT-TYPE
    SYNTAX SnmpAdminString (SIZE (0..80))
    MAX-ACCESS read-write
    STATUS current
    DESCRIPTION
        "An optional string that can be added to the beginning of
         the message body.  The prefix size can be up to 80
         characters."
   DEFVAL { "" }
    ::= { ilomCtrlAlertsEntry 12 }


-- ***************************************************************************
-- *                         ilomCtrlClock                                   *
-- ***************************************************************************

ilomCtrlDateAndTime OBJECT-TYPE
    SYNTAX DateAndTime
    MAX-ACCESS read-write
    STATUS current
    DESCRIPTION
        "The date and time of the device."
    ::= { ilomCtrlClock 1 }

ilomCtrlNTPEnabled OBJECT-TYPE
    SYNTAX TruthValue
    MAX-ACCESS read-write
    STATUS current
    DESCRIPTION
        "Specifies whether or not Network Time Protocol is enabled."
    ::= { ilomCtrlClock 2 }

ilomCtrlTimezone  OBJECT-TYPE
    SYNTAX SnmpAdminString
    MAX-ACCESS read-write
    STATUS current
    DESCRIPTION
        "The configured timezone string."
    ::= { ilomCtrlClock 3 }

-- ***************************************************************************
-- *                         ilomCtrlSerial                                  *
-- ***************************************************************************

ilomCtrlSerialInternalPortPresent OBJECT-TYPE
    SYNTAX TruthValue
    MAX-ACCESS read-only
    STATUS current
    DESCRIPTION
        "Indicates whether the given device has an internal serial port that
         is configurable.  The internal serial port is the connection between
         the host server and the service processor that allows the SP to
         access the host serial console."
    ::= { ilomCtrlSerial 1 }

ilomCtrlSerialInternalPortBaudRate OBJECT-TYPE
    SYNTAX ILOMCtrlBaudRate
    MAX-ACCESS read-write
    STATUS current
    DESCRIPTION
        "Specifies the current baud rate setting for the internal serial port.
         This is only readable/settable if ilomCtrlSerialInternalPortPresent
         is true."
    ::= { ilomCtrlSerial 2 }

ilomCtrlSerialExternalPortPresent OBJECT-TYPE
    SYNTAX TruthValue
    MAX-ACCESS read-only
    STATUS current
    DESCRIPTION
        "Indicates whether the given device has an external serial port that
         is configurable."
    ::= { ilomCtrlSerial 3 }

ilomCtrlSerialExternalPortBaudRate OBJECT-TYPE
    SYNTAX ILOMCtrlBaudRate
    MAX-ACCESS read-write
    STATUS current
    DESCRIPTION
        "Specifies the current baud rate setting for the external serial port.
         This is only readable/settable if ilomCtrlSerialExternalPortPresent
         is true."
    ::= { ilomCtrlSerial 4 }

ilomCtrlSerialExternalPortFlowControl OBJECT-TYPE
    SYNTAX ILOMCtrlFlowControl
    MAX-ACCESS read-only
    STATUS current
    DESCRIPTION
        "Specifies the current flowcontrol setting for the external serial port.
         This is only readable/settable if ilomCtrlSerialExternalPortPresent
         is true."
    ::= { ilomCtrlSerial 5 }


-- ***************************************************************************
-- *                         ilomCtrlPowerControl                            *
-- ***************************************************************************

-- This section provides properties for controlling the power for a given
-- target.  In some systems, such as blade systems, there are multiple
-- targets to control.

ilomCtrlPowerTable OBJECT-TYPE
    SYNTAX SEQUENCE OF ILOMCtrlPowerEntry
    MAX-ACCESS not-accessible
    STATUS current
    DESCRIPTION
        "A table listing all targets whose power can be controlled."
    ::= { ilomCtrlPowerControl 1 }

ilomCtrlPowerEntry OBJECT-TYPE
    SYNTAX ILOMCtrlPowerEntry
    MAX-ACCESS not-accessible
    STATUS current
    DESCRIPTION
        "An entry for a power-controllable target."
    INDEX { ilomCtrlPowerTarget }
    ::= { ilomCtrlPowerTable 1 }

ILOMCtrlPowerEntry ::= SEQUENCE {
        ilomCtrlPowerTarget                     SnmpAdminString,
        ilomCtrlPowerAction                     ILOMCtrlPowerAction
    }

ilomCtrlPowerTarget OBJECT-TYPE
    SYNTAX SnmpAdminString
    MAX-ACCESS not-accessible
    STATUS current
    DESCRIPTION
        "This is the nomenclature name for a target which supports
         power control.  On some systems, there are multiple targets
         which support power control.  On a traditional, non-blade system,
         this table will contain only one row.  The nomenclature name for
         a traditional server is '/SYS'.  On blade systems, this table
         will contain multiple rows.  There will be a row for '/CH' which
         allows for power control of the entire chassis.  In addition,
         there will be rows for each blade.  Blade nomenclature
         takes the form of '/CH/BL0/SYS', '/CH/BL1/SYS', and so on."
    ::= { ilomCtrlPowerEntry 1 }

ilomCtrlPowerAction OBJECT-TYPE
    SYNTAX ILOMCtrlPowerAction
    MAX-ACCESS read-write
    STATUS current
    DESCRIPTION
        "The action to apply to the given power control target.  The
         possible actions are powerOn(1), powerOff(2), powerCycle(3),
         and powerSoft(4).
         When this value is read, it returns a null value."
    ::= { ilomCtrlPowerEntry 2 }


-- ***************************************************************************
-- *                         ilomCtrlResetControl                            *
-- ***************************************************************************

-- This section provides properties for performing a reset of a given
-- target.  In some systems, such as blade systems, there are multiple
-- targets to control.

ilomCtrlResetTable OBJECT-TYPE
    SYNTAX SEQUENCE OF ILOMCtrlResetEntry
    MAX-ACCESS not-accessible
    STATUS current
    DESCRIPTION
        "A table listing all targets which can be reset."
    ::= { ilomCtrlResetControl 1 }

ilomCtrlResetEntry OBJECT-TYPE
    SYNTAX ILOMCtrlResetEntry
    MAX-ACCESS not-accessible
    STATUS current
    DESCRIPTION
        "An entry for a target which can be reset."
    INDEX { ilomCtrlResetTarget }
    ::= { ilomCtrlResetTable 1 }

ILOMCtrlResetEntry ::= SEQUENCE {
        ilomCtrlResetTarget                     SnmpAdminString,
        ilomCtrlResetAction                     ILOMCtrlResetAction
    }

ilomCtrlResetTarget OBJECT-TYPE
    SYNTAX SnmpAdminString
    MAX-ACCESS not-accessible
    STATUS current
    DESCRIPTION
        "This is the nomenclature name for a target which supports
         reset capabilities.  On some systems, there are multiple targets
         which support reset.  On most systems, only system controllers
         and service processors support reset.  On a traditional, non-blade
         system, this table will contain only one row, representing its
         service processor.  The nomenclature name for a traditional server's
         service processor is '/SP'.  On blade systems, this table
         will contain multiple rows.  There will be a row for '/SC' which
         allows for reset of the system controller.  In addition,
         there will be rows for each blade's service processor.  For example,
         a blade's service processor nomenclature takes the form of
         '/CH/BL0/SP', '/CH/BL1/SP' and so on."
    ::= { ilomCtrlResetEntry 1 }

ilomCtrlResetAction OBJECT-TYPE
    SYNTAX ILOMCtrlResetAction
    MAX-ACCESS read-write
    STATUS current
    DESCRIPTION
        "The action to apply to the given reset control target.  The
         possible actions are reset(1), which is a normal reset,
         resetNonMaskableInterrupt(2) which is a forced reset, and
         force(3) which is a forced reset for platforms that do not
         support NMI.
         When this value is read, it returns a null value."
    ::= { ilomCtrlResetEntry 2 }


-- ***************************************************************************
-- *                         ilomCtrlRedundancy                              *
-- ***************************************************************************

-- This section provides properties for the redundancy features of the device.
-- The redundancy features allow two system controllers to be configured in
-- a highly available environment.  This section does not apply to service
-- processors.

ilomCtrlRedundancyStatus OBJECT-TYPE
    SYNTAX ILOMCtrlRedundancyStatus
    MAX-ACCESS read-only
    STATUS current
    DESCRIPTION
        "This property indicates the status of the device in a redundant
         configuration.  It may be active(2) or standby(3) when configured
         as a redundant pair or standAlone(4) if it does not have a peer.
         In addition, it may be in a state called initializing(1) if
         it is in a transitional state."
    ::= { ilomCtrlRedundancy 1 }

ilomCtrlRedundancyAction OBJECT-TYPE
    SYNTAX ILOMCtrlRedundancyAction
    MAX-ACCESS read-write
    STATUS current
    DESCRIPTION
        "This action is used to promote or demote this device from active
         or standy status."
    ::= { ilomCtrlRedundancy 2 }

ilomCtrlRedundancyFRUName OBJECT-TYPE
    SYNTAX DisplayString
    MAX-ACCESS read-only
    STATUS current
    DESCRIPTION
        "FRU Name of the CMM on which this agent is running."
    ::= { ilomCtrlRedundancy 3 }

-- ***************************************************************************
-- *                      ilomCtrlPolicy
-- ***************************************************************************

-- This section defines a table for administering policies.

ilomCtrlPolicyTable OBJECT-TYPE
    SYNTAX SEQUENCE OF ILOMCtrlPolicyEntry
    MAX-ACCESS not-accessible
    STATUS current
    DESCRIPTION
        "A table listing all policies that can be administered."
    ::= { ilomCtrlPolicy 1 }

ilomCtrlPolicyEntry OBJECT-TYPE
    SYNTAX ILOMCtrlPolicyEntry
    MAX-ACCESS not-accessible
    STATUS current
    DESCRIPTION
        "An entry for a policy which can be enabled or disabled."
    INDEX { ilomCtrlPolicyId }
    ::= { ilomCtrlPolicyTable 1 }

ILOMCtrlPolicyEntry ::= SEQUENCE {
        ilomCtrlPolicyId                Integer32,
        ilomCtrlPolicyShortStr          DisplayString,
        ilomCtrlPolicyLongStr           DisplayString,
        ilomCtrlPolicyEnabled           TruthValue
    }

ilomCtrlPolicyId OBJECT-TYPE
    SYNTAX Integer32 (0..65535)
    MAX-ACCESS not-accessible
    STATUS current
    DESCRIPTION
        "An integer identifier of the policy."
    ::= { ilomCtrlPolicyEntry 1 }

ilomCtrlPolicyShortStr OBJECT-TYPE
    SYNTAX DisplayString
    MAX-ACCESS read-only
    STATUS current
    DESCRIPTION
        "A short description of the policy."
    ::= { ilomCtrlPolicyEntry 2 }

ilomCtrlPolicyLongStr OBJECT-TYPE
    SYNTAX DisplayString
    MAX-ACCESS read-only
    STATUS current
    DESCRIPTION
        "A verbose description of the policy."
    ::= { ilomCtrlPolicyEntry 3 }

ilomCtrlPolicyEnabled OBJECT-TYPE
    SYNTAX TruthValue
    MAX-ACCESS read-write
    STATUS current
    DESCRIPTION
        "Indicates the status of the policy."
    ::= { ilomCtrlPolicyEntry 4 }


-- ***************************************************************************
-- *                      ilomCtrlConfigMgmt
-- ***************************************************************************

-- This section includes properties related to Configuration management.

ilomCtrlResetToDefaultsAction OBJECT-TYPE
    SYNTAX ILOMCtrlResetToDefaultsAction
    MAX-ACCESS read-write
    STATUS current
    DESCRIPTION
        "This property is used to initiate the action of restoring the
         configuration on the SP to the original factory default state."
    ::= { ilomCtrlConfigMgmt 1 }


-- ***************************************************************************
-- *                      ilomCtrlBackupAndRestore
-- ***************************************************************************

-- This section includes properties related to BackupAndRestore operation.

ilomCtrlBackupAndRestoreTargetURI OBJECT-TYPE
    SYNTAX SnmpAdminString
    MAX-ACCESS read-write
    STATUS current
    DESCRIPTION
        "This property is used to set target destination of configuration xml
         file during backup and restore.
         The syntax is {protocol}://[user:passwword]@]host[/][path/][file]
         for example tftp://10.8.136.154/remotedir/config_backup.xml
         currently, the supported protocols are: scp, tftp.
         for certain protocol which needs password field, please use
         ilomCtrlBackupAndRestoreProtocolPassword to set password."
    ::= { ilomCtrlBackupAndRestore 1 }

ilomCtrlBackupAndRestorePassphrase OBJECT-TYPE
    SYNTAX SnmpAdminString
    MAX-ACCESS read-write
    STATUS current
    DESCRIPTION
        "This property is used to set passphrase for encrypt/decrypt
         sensitive data during backup and restore.
         For snmpget, it returns null as value. "
    ::= { ilomCtrlBackupAndRestore 2 }

ilomCtrlBackupAndRestoreAction OBJECT-TYPE
    SYNTAX ILOMCtrlBackupAndRestoreAction
    MAX-ACCESS read-write
    STATUS current
    DESCRIPTION
        "This property is used to issue a action,
         either backup or restore. "
    ::= { ilomCtrlBackupAndRestore 3 }

ilomCtrlBackupAndRestoreActionStatus OBJECT-TYPE
    SYNTAX SnmpAdminString
    MAX-ACCESS read-only
    STATUS current
    DESCRIPTION
        "This property is used to monitor the current status of
         backup/restore. "
    ::= { ilomCtrlBackupAndRestore 4 }


-- ***************************************************************************
-- *                      ilomCtrlSPARCDiags
-- ***************************************************************************

-- This section defines properties for configuring SPARC-specific diagnostics.

ilomCtrlSPARCDiagsLevel OBJECT-TYPE
    SYNTAX ILOMCtrlSPARCDiagsLevel
    MAX-ACCESS read-write
    STATUS deprecated
    DESCRIPTION
        "Indicates the level of embedded diagnostics that should be run
         on the host during a boot.
         ***NOTE: this object is deprecated and replaced with these:
            ilomCtrlSPARCDiagsPowerOnLevel,
            ilomCtrlSPARCDiagsUserResetLevel,
            ilomCtrlSPARCDiagsErrorResetLevel
         While deprecated, this object will display advsettings(3), unless:
            - all 3 of the above are currently set to init(1),
              in which case this object will display min(1)
            - all 3 of the above are currently set to maximum(3),
              in which case this object will display max(2)."
    ::= { ilomCtrlSPARCDiags 1 }

ilomCtrlSPARCDiagsTrigger OBJECT-TYPE
    SYNTAX ILOMCtrlSPARCDiagsTrigger
    MAX-ACCESS read-write
    STATUS current
    DESCRIPTION
        "Indicates the triggers of embedded diagnostics for the host."
    ::= { ilomCtrlSPARCDiags 2 }

ilomCtrlSPARCDiagsVerbosity OBJECT-TYPE
    SYNTAX ILOMCtrlSPARCDiagsVerbosity
    MAX-ACCESS read-write
    STATUS deprecated
    DESCRIPTION
        "Indicates the verbosity level of embedded diagnostics that should
         be run on the host during a boot.
         ***NOTE: this object is deprecated and replaced with these:
            ilomCtrlSPARCDiagsPowerOnVerbosity,
            ilomCtrlSPARCDiagsUserResetVerbosity,
            ilomCtrlSPARCDiagsErrorResetVerbosity.
         While deprecated, this object will display advsettings(3), unless:
            - all 3 of the above are currently set to minimum(1),
              in which case this object will display min(1)
            - all 3 of the above are currently set to maximum(3),
              in which case this object will display max(2)."
    ::= { ilomCtrlSPARCDiags 3 }

ilomCtrlSPARCDiagsMode OBJECT-TYPE
    SYNTAX ILOMCtrlSPARCDiagsMode
    MAX-ACCESS read-write
    STATUS current
    DESCRIPTION
        "Indicates the modes for POST.  POST will stop at the mode
         specified by this property."
    ::= { ilomCtrlSPARCDiags 4 }

ilomCtrlSPARCDiagsPowerOnLevel OBJECT-TYPE
    SYNTAX ILOMCtrlSPARCDiagsLevelAdv
    MAX-ACCESS read-write
    STATUS current
    DESCRIPTION
        "Indicates the level of embedded diagnostics that should be run
         on the host during a boot for the power-on-reset trigger."
    ::= { ilomCtrlSPARCDiags 5 }

ilomCtrlSPARCDiagsUserResetLevel OBJECT-TYPE
    SYNTAX ILOMCtrlSPARCDiagsLevelAdv
    MAX-ACCESS read-write
    STATUS current
    DESCRIPTION
        "Indicates the level of embedded diagnostics that should be run
         on the host during a boot for the user-reset trigger."
    ::= { ilomCtrlSPARCDiags 6 }

ilomCtrlSPARCDiagsErrorResetLevel OBJECT-TYPE
    SYNTAX ILOMCtrlSPARCDiagsLevelAdv
    MAX-ACCESS read-write
    STATUS current
    DESCRIPTION
        "Indicates the level of embedded diagnostics that should be run
         on the host during a boot for the error-reset trigger."
    ::= { ilomCtrlSPARCDiags 7 }

ilomCtrlSPARCDiagsPowerOnVerbosity OBJECT-TYPE
    SYNTAX ILOMCtrlSPARCDiagsVerbosityAdv
    MAX-ACCESS read-write
    STATUS current
    DESCRIPTION
        "Indicates the verbosity level of embedded diagnostics that should
         be run on the host during a boot for power-on-reset trigger."
    ::= { ilomCtrlSPARCDiags 8 }

ilomCtrlSPARCDiagsUserResetVerbosity OBJECT-TYPE
    SYNTAX ILOMCtrlSPARCDiagsVerbosityAdv
    MAX-ACCESS read-write
    STATUS current
    DESCRIPTION
        "Indicates the verbosity level of embedded diagnostics that should
         be run on the host during a boot for user-reset trigger."
    ::= { ilomCtrlSPARCDiags 9 }

ilomCtrlSPARCDiagsErrorResetVerbosity OBJECT-TYPE
    SYNTAX ILOMCtrlSPARCDiagsVerbosityAdv
    MAX-ACCESS read-write
    STATUS current
    DESCRIPTION
        "Indicates the verbosity level of embedded diagnostics that should
         be run on the host during a boot for error-reset trigger."
    ::= { ilomCtrlSPARCDiags 10 }

ilomCtrlSPARCDiagsStatus OBJECT-TYPE
    SYNTAX Integer32 (0..100)
    MAX-ACCESS read-only
    STATUS current
    DESCRIPTION
        "Indicates the progress of POST diagnostics on the host, expressed
         as a percentage."
    ::= { ilomCtrlSPARCDiags 11 }

ilomCtrlSPARCDiagsAction OBJECT-TYPE
    SYNTAX ILOMCtrlSPARCDiagsAction
    MAX-ACCESS read-write
    STATUS current
    DESCRIPTION
        "An action to take to control POST running on the host."
    ::= { ilomCtrlSPARCDiags 12 }

ilomCtrlSPARCDiagsHwChangeLevel OBJECT-TYPE
    SYNTAX ILOMCtrlSPARCDiagsLevelAdv
    MAX-ACCESS read-write
    STATUS current
    DESCRIPTION
        "Indicates the level of embedded diagnostics that should be run
         on the host during a boot for the hw-change trigger."
    ::= { ilomCtrlSPARCDiags 13 }

ilomCtrlSPARCDiagsHwChangeVerbosity OBJECT-TYPE
    SYNTAX ILOMCtrlSPARCDiagsVerbosityAdv
    MAX-ACCESS read-write
    STATUS current
    DESCRIPTION
        "Indicates the verbosity level of embedded diagnostics that should
         be run on the host during a boot for hw-change trigger."
    ::= { ilomCtrlSPARCDiags 14 }

-- ***************************************************************************
-- *                      ilomCtrlSPARCHostControl
-- ***************************************************************************

-- This section defines properties used to control SPARC-specific host software.

ilomCtrlSPARCHostMACAddress OBJECT-TYPE
    SYNTAX SnmpAdminString
    MAX-ACCESS read-only
    STATUS current
    DESCRIPTION
        "Displays the starting MAC address for the host."
    ::= { ilomCtrlSPARCHostControl 1 }

ilomCtrlSPARCHostOBPVersion OBJECT-TYPE
    SYNTAX SnmpAdminString
    MAX-ACCESS read-only
    STATUS current
    DESCRIPTION
        "Displays the version string for OBP."
    ::= { ilomCtrlSPARCHostControl 3 }

ilomCtrlSPARCHostPOSTVersion OBJECT-TYPE
    SYNTAX SnmpAdminString
    MAX-ACCESS read-only
    STATUS current
    DESCRIPTION
        "Displays the version string for POST."
    ::= { ilomCtrlSPARCHostControl 4 }

ilomCtrlSPARCHostAutoRunOnError OBJECT-TYPE
    SYNTAX TruthValue
    MAX-ACCESS read-write
    STATUS current
    DESCRIPTION
        "This option determines whether the host should continue to boot in the event
         of a non-fatal POST error."
    ::= { ilomCtrlSPARCHostControl 6 }

ilomCtrlSPARCHostPOSTStatus OBJECT-TYPE
    SYNTAX SnmpAdminString
    MAX-ACCESS read-only
    STATUS current
    DESCRIPTION
        "A string that describes the status of POST.
         ***NOTE: OS Boot status is ilomCtrlSPARCHostOSBootStatus."
    ::= { ilomCtrlSPARCHostControl 7 }

ilomCtrlSPARCHostAutoRestartPolicy OBJECT-TYPE
    SYNTAX ILOMCtrlSPARCHostAutoRestartPolicy
    MAX-ACCESS read-write
    STATUS current
    DESCRIPTION
        "This determines what action the SP should take when it discovers that
         the host is hung."
    ::= { ilomCtrlSPARCHostControl 8 }

ilomCtrlSPARCHostOSBootStatus OBJECT-TYPE
    SYNTAX SnmpAdminString
    MAX-ACCESS read-only
    STATUS current
    DESCRIPTION
        "A string that describes the boot status of host OS."
    ::= { ilomCtrlSPARCHostControl 9 }

ilomCtrlSPARCHostBootTimeout OBJECT-TYPE
    SYNTAX Integer32 (0..36000)
    MAX-ACCESS read-write
    STATUS current
    DESCRIPTION
        "This is the boot timer time out value."
    ::= { ilomCtrlSPARCHostControl 10 }

ilomCtrlSPARCHostBootRestart OBJECT-TYPE
    SYNTAX ILOMCtrlSPARCHostBootRestart
    MAX-ACCESS read-write
    STATUS current
    DESCRIPTION
        "This determines what action the SP should take when
         the boot timer expires."
    ::= { ilomCtrlSPARCHostControl 11 }

ilomCtrlSPARCHostMaxBootFail OBJECT-TYPE
    SYNTAX Integer32 (0..10000)
    MAX-ACCESS read-write
    STATUS current
    DESCRIPTION
        "This is the number of max boot failures allowed."
    ::= { ilomCtrlSPARCHostControl 12 }

ilomCtrlSPARCHostBootFailRecovery OBJECT-TYPE
    SYNTAX ILOMCtrlSPARCHostBootFailRecovery
    MAX-ACCESS read-write
    STATUS current
    DESCRIPTION
        "This determines what action the SP should take when
         the max boot failures are reached."
    ::= { ilomCtrlSPARCHostControl 13 }

ilomCtrlSPARCHostHypervisorVersion OBJECT-TYPE
    SYNTAX SnmpAdminString
    MAX-ACCESS read-only
    STATUS current
    DESCRIPTION
        "Displays the version string for Hypervisor."
    ::= { ilomCtrlSPARCHostControl 14 }

ilomCtrlSPARCHostSysFwVersion OBJECT-TYPE
    SYNTAX SnmpAdminString
    MAX-ACCESS read-only
    STATUS current
    DESCRIPTION
        "Displays the version string for SysFw."
    ::= { ilomCtrlSPARCHostControl 15 }

ilomCtrlSPARCHostSendBreakAction OBJECT-TYPE
    SYNTAX ILOMCtrlSPARCHostSendBreakAction
    MAX-ACCESS read-write
    STATUS current
    DESCRIPTION
        "Send Break Action to Host"
    ::= { ilomCtrlSPARCHostControl 16 }

ilomCtrlSPARCHostIoReconfigurePolicy OBJECT-TYPE
    SYNTAX ILOMCtrlSPARCHostIoReconfigurePolicy
    MAX-ACCESS read-write
    STATUS current
    DESCRIPTION
        "This determines the host IO reconfiguration policy to apply on
        next host power-on."
    ::= { ilomCtrlSPARCHostControl 17 }

ilomCtrlSPARCHostGMVersion OBJECT-TYPE
    SYNTAX SnmpAdminString
    MAX-ACCESS read-only
    STATUS current
    DESCRIPTION
        "Displays the version string for Guest Manager."
    ::= { ilomCtrlSPARCHostControl 18 }

-- ***************************************************************************
-- *                      ilomCtrlSPARCBootMode
-- ***************************************************************************

-- This section defines properties for configuring SPARC-specific boot mode
-- features.

ilomCtrlSPARCBootModeState OBJECT-TYPE
    SYNTAX ILOMCtrlSPARCBootModeState
    MAX-ACCESS read-write
    STATUS current
    DESCRIPTION
        "Configures the boot mode state for the host.  Specifying 'normal'
         means that the host retains current NVRAM variable settings.
         Specifying 'resetNvram' means that all NVRAM settings will be
         reset to their default values."
    ::= { ilomCtrlSPARCBootMode 1 }

ilomCtrlSPARCBootModeScript OBJECT-TYPE
    SYNTAX SnmpAdminString (SIZE (0..255))
    MAX-ACCESS read-write
    STATUS current
    DESCRIPTION
        "Specifies the script to run when host boots."
    ::= { ilomCtrlSPARCBootMode 2 }

ilomCtrlSPARCBootModeExpires OBJECT-TYPE
    SYNTAX DateAndTime
    MAX-ACCESS read-only
    STATUS current
    DESCRIPTION
        "Displays the date and time for when the boot mode configuration should
         expire."
    ::= { ilomCtrlSPARCBootMode 3 }

ilomCtrlSPARCBootModeLDOMConfig OBJECT-TYPE
    SYNTAX SnmpAdminString (SIZE (0..255))
    MAX-ACCESS read-write
    STATUS current
    DESCRIPTION
        "This string refers to the config name value that must either be
         'default' or match a named LDOM configuration downloaded to
         the service processor using the LDOM Manager."
    ::= { ilomCtrlSPARCBootMode 4 }


-- ***************************************************************************
-- *                      ilomCtrlSPARCKeySwitch
-- ***************************************************************************

-- This section defines properties for controlling the virtual key switch.

ilomCtrlSPARCKeySwitchState OBJECT-TYPE
    SYNTAX ILOMCtrlSPARCKeySwitchState
    MAX-ACCESS read-write
    STATUS current
    DESCRIPTION
        "Specifies the current state of the virtual key switch."
    ::= { ilomCtrlSPARCKeySwitch 1 }


-- ***************************************************************************
-- *                      ilomCtrlIdentification
-- ***************************************************************************

-- This section defines miscellaneous configuration parameters for the
-- service processor.

ilomCtrlSystemIdentifier OBJECT-TYPE
    SYNTAX SnmpAdminString
    MAX-ACCESS read-write
    STATUS current
    DESCRIPTION
        "This string, which is often the host name of the server
         associated with ILOM, will be sent out in the varbind
         for all traps that ILOM generates."
    ::= { ilomCtrlIdentification 1 }

ilomCtrlHostName OBJECT-TYPE
    SYNTAX SnmpAdminString
    MAX-ACCESS read-write
    STATUS current
    DESCRIPTION
        "This string is the hostname for ILOM."
    ::= { ilomCtrlIdentification 2 }

-- ***************************************************************************
-- *                      ilomCtrlActiveDirectory
-- ***************************************************************************

-- This section defines properties for configuring the Active Directory client.

ilomCtrlActiveDirectoryEnabled OBJECT-TYPE
    SYNTAX TruthValue
    MAX-ACCESS read-write
    STATUS current
    DESCRIPTION
        "Specifies whether or not the Active Directory client is enabled."
    ::= { ilomCtrlActiveDirectory 1 }

ilomCtrlActiveDirectoryIP OBJECT-TYPE
    SYNTAX IpAddress
    MAX-ACCESS read-write
    STATUS current
    DESCRIPTION
        "The IP address of the Active Directory server used as a name service for
         user accounts."
    ::= { ilomCtrlActiveDirectory 2 }

ilomCtrlActiveDirectoryPortNumber OBJECT-TYPE
    SYNTAX Integer32 (0..65535)
    MAX-ACCESS read-write
    STATUS current
    DESCRIPTION
        "Specifies the port number for the Active Directory client.  Specifying 0 as
         the port means auto-select while specifying 1-65535 configures the actual port."
    ::= { ilomCtrlActiveDirectory 3 }

ilomCtrlActiveDirectoryDefaultRole OBJECT-TYPE
    SYNTAX ILOMCtrlUserRole
    MAX-ACCESS read-write
    STATUS deprecated
    DESCRIPTION
        "Specifies the role that a user authenticated via Active Directory should have.
         Setting this property to 'Administrator' or 'Operator' will cause the
         Active Directory client to ignore the schema stored on the AD server.
         Setting this to 'none' clears the value and indicates that the native
         Active Directory schema should be used.
         ***NOTE: this object is deprecated and replaced with
         ilomCtrlActiveDirectoryDefaultRoles."
    ::= { ilomCtrlActiveDirectory 4 }

ilomCtrlActiveDirectoryCertFileURI OBJECT-TYPE
    SYNTAX SnmpAdminString
    MAX-ACCESS read-write
    STATUS current
    DESCRIPTION
        "This is the URI of a certificate file needed when Strict Cert Mode is
         enabled.  Setting the URI causes the tranfer of the file, making the
         certificate available immediately for certificate authentication."
    ::= { ilomCtrlActiveDirectory 5 }

ilomCtrlActiveDirectoryTimeout OBJECT-TYPE
    SYNTAX Integer32 (1..20)
    MAX-ACCESS read-write
    STATUS current
    DESCRIPTION
        "Specifies the number of seconds to wait before timing out if the
         Active Directory Server is not responding."
    ::= { ilomCtrlActiveDirectory 6 }

ilomCtrlActiveDirectoryStrictCertEnabled OBJECT-TYPE
    SYNTAX TruthValue
    MAX-ACCESS read-write
    STATUS current
    DESCRIPTION
        "Specifies whether or not the Strict Cert Mode is enabled for
         the Active Directory Client.  If enabled, the Active Directory
         certificate must be uploaded to the SP so that certificate
         validation can be performed when communicating with the
         Active Directory server."
    ::= { ilomCtrlActiveDirectory 7 }

ilomCtrlActiveDirectoryCertFileStatus OBJECT-TYPE
    SYNTAX DisplayString
    MAX-ACCESS read-only
    STATUS current
    DESCRIPTION
        "A string indicating the status of the certificate file.
         This is useful in determining whether a certificate file
         is present or not."
    ::= { ilomCtrlActiveDirectory 8 }

ilomCtrlActiveDirUserDomainTable OBJECT-TYPE
    SYNTAX SEQUENCE OF ILOMCtrlActiveDirUserDomainEntry
    MAX-ACCESS not-accessible
    STATUS current
    DESCRIPTION
        "This table is used to configure domain information required for
         configuring the Active Directory client."
    ::= { ilomCtrlActiveDirectory 9 }

ilomCtrlActiveDirUserDomainEntry OBJECT-TYPE
    SYNTAX ILOMCtrlActiveDirUserDomainEntry
    MAX-ACCESS not-accessible
    STATUS current
    DESCRIPTION
        "An entry for an Active Directory user domain."
    INDEX { ilomCtrlActiveDirUserDomainId }
    ::= { ilomCtrlActiveDirUserDomainTable 1 }

ILOMCtrlActiveDirUserDomainEntry ::= SEQUENCE {
        ilomCtrlActiveDirUserDomainId           Integer32,
        ilomCtrlActiveDirUserDomain             SnmpAdminString
    }

ilomCtrlActiveDirUserDomainId OBJECT-TYPE
    SYNTAX Integer32 (1..5)
    MAX-ACCESS not-accessible
    STATUS current
    DESCRIPTION
        "An integer identifier of the Active Directory domain."
    ::= { ilomCtrlActiveDirUserDomainEntry 1 }

ilomCtrlActiveDirUserDomain OBJECT-TYPE
    SYNTAX SnmpAdminString
    MAX-ACCESS read-write
    STATUS current
    DESCRIPTION
        "This string should match exactly with an authentication domain
         on the Active Directory server.  This string should contain
         a substitution string '<USERNAME>' which will be replaced with the
         user's login name during authentication.  Either the principle
         or distinguished name format is allowed."
    ::= { ilomCtrlActiveDirUserDomainEntry 2 }

ilomCtrlActiveDirAdminGroupsTable OBJECT-TYPE
    SYNTAX SEQUENCE OF ILOMCtrlActiveDirAdminGroupsEntry
    MAX-ACCESS not-accessible
    STATUS current
    DESCRIPTION
        "This table is used to configure admin group information required for
         configuring the Active Directory client."
    ::= { ilomCtrlActiveDirectory 10 }

ilomCtrlActiveDirAdminGroupsEntry OBJECT-TYPE
    SYNTAX ILOMCtrlActiveDirAdminGroupsEntry
    MAX-ACCESS not-accessible
    STATUS current
    DESCRIPTION
        "An entry for an Active Directory admin group."
    INDEX { ilomCtrlActiveDirAdminGroupId }
    ::= { ilomCtrlActiveDirAdminGroupsTable 1 }

ILOMCtrlActiveDirAdminGroupsEntry ::= SEQUENCE {
        ilomCtrlActiveDirAdminGroupId           Integer32,
        ilomCtrlActiveDirAdminGroupName         SnmpAdminString
    }

ilomCtrlActiveDirAdminGroupId OBJECT-TYPE
    SYNTAX Integer32 (1..5)
    MAX-ACCESS not-accessible
    STATUS current
    DESCRIPTION
        "An integer identifier of the Active Directory admin group entry."
    ::= { ilomCtrlActiveDirAdminGroupsEntry 1 }

ilomCtrlActiveDirAdminGroupName OBJECT-TYPE
    SYNTAX SnmpAdminString
    MAX-ACCESS read-write
    STATUS current
    DESCRIPTION
        "This string should contain a distinguished name that exactly matches
         one of the group names on the ActiveDirectory server.  Any user belonging
         to one of these groups in this table will be assigned the ILOM role
         of Administrator."
    ::= { ilomCtrlActiveDirAdminGroupsEntry 2 }

ilomCtrlActiveDirOperatorGroupsTable OBJECT-TYPE
    SYNTAX SEQUENCE OF ILOMCtrlActiveDirOperatorGroupsEntry
    MAX-ACCESS not-accessible
    STATUS current
    DESCRIPTION
        "This table is used to configure operator group information required for
         configuring the Active Directory client."
    ::= { ilomCtrlActiveDirectory 11 }

ilomCtrlActiveDirOperatorGroupsEntry OBJECT-TYPE
    SYNTAX ILOMCtrlActiveDirOperatorGroupsEntry
    MAX-ACCESS not-accessible
    STATUS current
    DESCRIPTION
        "An entry for an Active Directory operator group."
    INDEX { ilomCtrlActiveDirOperatorGroupId }
    ::= { ilomCtrlActiveDirOperatorGroupsTable 1 }

ILOMCtrlActiveDirOperatorGroupsEntry ::= SEQUENCE {
        ilomCtrlActiveDirOperatorGroupId                Integer32,
        ilomCtrlActiveDirOperatorGroupName              SnmpAdminString
    }

ilomCtrlActiveDirOperatorGroupId OBJECT-TYPE
    SYNTAX Integer32 (1..5)
    MAX-ACCESS not-accessible
    STATUS current
    DESCRIPTION
        "An integer identifier of the Active Directory operator group entry."
    ::= { ilomCtrlActiveDirOperatorGroupsEntry 1 }

ilomCtrlActiveDirOperatorGroupName OBJECT-TYPE
    SYNTAX SnmpAdminString
    MAX-ACCESS read-write
    STATUS current
    DESCRIPTION
        "This string should contain a distinguished name that exactly matches
         one of the group names on the ActiveDirectory server.  Any user belonging
         to one of these groups in this table will be assigned the ILOM role
         of Operator."
    ::= { ilomCtrlActiveDirOperatorGroupsEntry 2 }

ilomCtrlActiveDirAlternateServerTable OBJECT-TYPE
    SYNTAX SEQUENCE OF ILOMCtrlActiveDirAlternateServerEntry
    MAX-ACCESS not-accessible
    STATUS current
    DESCRIPTION
        "This table is used to view and configure alternate server information
         for the Active Directory client."
    ::= { ilomCtrlActiveDirectory 12 }

ilomCtrlActiveDirAlternateServerEntry OBJECT-TYPE
    SYNTAX ILOMCtrlActiveDirAlternateServerEntry
    MAX-ACCESS not-accessible
    STATUS current
    DESCRIPTION
        "An entry for an Active Directory alternate server."
    INDEX { ilomCtrlActiveDirAlternateServerId }
    ::= { ilomCtrlActiveDirAlternateServerTable 1 }

ILOMCtrlActiveDirAlternateServerEntry ::= SEQUENCE {
        ilomCtrlActiveDirAlternateServerId              Integer32,
        ilomCtrlActiveDirAlternateServerIp              IpAddress,
        ilomCtrlActiveDirAlternateServerPort            Integer32,
        ilomCtrlActiveDirAlternateServerCertStatus      DisplayString,
        ilomCtrlActiveDirAlternateServerCertURI         SnmpAdminString,
        ilomCtrlActiveDirAlternateServerCertClear       TruthValue,
        ilomCtrlActiveDirAlternateServerCertVersion     DisplayString,
        ilomCtrlActiveDirAlternateServerCertSerialNo    DisplayString,
        ilomCtrlActiveDirAlternateServerCertIssuer      DisplayString,
        ilomCtrlActiveDirAlternateServerCertSubject     DisplayString,
        ilomCtrlActiveDirAlternateServerCertValidBegin  DisplayString,
        ilomCtrlActiveDirAlternateServerCertValidEnd    DisplayString
    }

ilomCtrlActiveDirAlternateServerId OBJECT-TYPE
    SYNTAX Integer32 (1..5)
    MAX-ACCESS not-accessible
    STATUS current
    DESCRIPTION
        "An integer identifier of the Active Directory alternate server table."
    ::= { ilomCtrlActiveDirAlternateServerEntry 1 }

ilomCtrlActiveDirAlternateServerIp OBJECT-TYPE
    SYNTAX IpAddress
    MAX-ACCESS read-write
    STATUS current
    DESCRIPTION
        "The IP address of the Active Directory alternate server
        used as a name service for user accounts."
    ::= { ilomCtrlActiveDirAlternateServerEntry 2 }

ilomCtrlActiveDirAlternateServerPort OBJECT-TYPE
    SYNTAX Integer32 (0..65535)
    MAX-ACCESS read-write
    STATUS current
    DESCRIPTION
        "Specifies the port number for the Active Directory alternate server.
         Specifying 0 as the port indicates that auto-select will use the
         well known port number.  Specifying 1-65535 is used to explicitly
         set the port number."
    ::= { ilomCtrlActiveDirAlternateServerEntry 3 }

ilomCtrlActiveDirAlternateServerCertStatus OBJECT-TYPE
    SYNTAX DisplayString
    MAX-ACCESS read-only
    STATUS current
    DESCRIPTION
        "A string indicating the status of the certificate file.
         This is useful in determining whether a certificate file
         is present or not."
    ::= { ilomCtrlActiveDirAlternateServerEntry 4 }

ilomCtrlActiveDirAlternateServerCertURI OBJECT-TYPE
    SYNTAX SnmpAdminString
    MAX-ACCESS read-write
    STATUS current
    DESCRIPTION
        "This is the URI of a certificate file needed when Strict Cert Mode is
         enabled.  Setting the URI causes the tranfer of the file, making the
         certificate available immediately for certificate authentication.
         Additionally, either 'remove' or 'restore' are supported for direct
         certificate manipulation."
    ::= { ilomCtrlActiveDirAlternateServerEntry 5 }

ilomCtrlActiveDirAlternateServerCertClear OBJECT-TYPE
    SYNTAX TruthValue
    MAX-ACCESS read-write
    STATUS current
    DESCRIPTION
        "A variable that will clear the certificate info associated
         with the server when it is set to true."
    ::= { ilomCtrlActiveDirAlternateServerEntry 6 }

ilomCtrlActiveDirAlternateServerCertVersion OBJECT-TYPE
    SYNTAX DisplayString
    MAX-ACCESS read-only
    STATUS current
    DESCRIPTION
        "A string indicating the certificate version of the
         alternate server certificate file."
    ::= { ilomCtrlActiveDirAlternateServerEntry 7 }

ilomCtrlActiveDirAlternateServerCertSerialNo OBJECT-TYPE
    SYNTAX DisplayString
    MAX-ACCESS read-only
    STATUS current
    DESCRIPTION
        "A string showing the serial number of the alternate server
         certificate file."
    ::= { ilomCtrlActiveDirAlternateServerEntry 8 }

ilomCtrlActiveDirAlternateServerCertIssuer OBJECT-TYPE
    SYNTAX DisplayString
    MAX-ACCESS read-only
    STATUS current
    DESCRIPTION
        "A string showing the issuer of the alternate server
         certificate file."
    ::= { ilomCtrlActiveDirAlternateServerEntry 9 }

ilomCtrlActiveDirAlternateServerCertSubject OBJECT-TYPE
    SYNTAX DisplayString
    MAX-ACCESS read-only
    STATUS current
    DESCRIPTION
        "A string showing the subject of the alternate server
         certificate file."
    ::= { ilomCtrlActiveDirAlternateServerEntry 10 }

ilomCtrlActiveDirAlternateServerCertValidBegin OBJECT-TYPE
    SYNTAX DisplayString
    MAX-ACCESS read-only
    STATUS current
    DESCRIPTION
        "A string showing the valid start date of the alternate server
         certificate file."
    ::= { ilomCtrlActiveDirAlternateServerEntry 11 }

ilomCtrlActiveDirAlternateServerCertValidEnd OBJECT-TYPE
    SYNTAX DisplayString
    MAX-ACCESS read-only
    STATUS current
    DESCRIPTION
        "A string showing the valid end date of the alternate server
         certificate file."
    ::= { ilomCtrlActiveDirAlternateServerEntry 12 }

ilomCtrlActiveDirectoryLogDetail OBJECT-TYPE
    SYNTAX INTEGER  {
               none(1),     -- no messages logged
               high(2),     -- high messages only
               medium(3),   -- high + medium
               low(4),      -- high + medium + low
               trace(5)     -- high + medium + low + trace
           }
    MAX-ACCESS read-write
    STATUS current
    DESCRIPTION
        "Controls the amount of messages sent to the event log.  The
         high priority has the least number of messages going to the log,
         while the lowest priority 'trace' has the most messages logged.
         When this object is set to 'none', no messages are logged."
    ::= { ilomCtrlActiveDirectory 13 }

ilomCtrlActiveDirectoryDefaultRoles OBJECT-TYPE
    SYNTAX ILOMCtrlUserRoles
    MAX-ACCESS read-write
    STATUS current
    DESCRIPTION
        "Specifies the role that a user authenticated via Active Directory should have.
         Setting this property to legacy roles of 'Administrator' or 'Operator', or
         any of the individual role IDs of 'a', 'u', 'c', 'r', 'o' and 's'  will cause
         the Active Directory client to ignore the schema stored on the AD server.
         Setting this to 'none' clears the value and indicates that the native
         Active Directory schema should be used.  The role IDs can be joined
         together 'aucros' where a-admin, u-user, c-console, r-reset,
         s-service and o-readOnly."
    ::= { ilomCtrlActiveDirectory 14 }

ilomCtrlActiveDirCustomGroupsTable OBJECT-TYPE
    SYNTAX SEQUENCE OF ILOMCtrlActiveDirCustomGroupsEntry
    MAX-ACCESS not-accessible
    STATUS current
    DESCRIPTION
        "This table is used to configure custom group information required for
         configuring the Active Directory client."
    ::= { ilomCtrlActiveDirectory 15 }

ilomCtrlActiveDirCustomGroupsEntry OBJECT-TYPE
    SYNTAX ILOMCtrlActiveDirCustomGroupsEntry
    MAX-ACCESS not-accessible
    STATUS current
    DESCRIPTION
        "An entry for an Active Directory custom group."
    INDEX { ilomCtrlActiveDirCustomGroupId }
    ::= { ilomCtrlActiveDirCustomGroupsTable 1 }

ILOMCtrlActiveDirCustomGroupsEntry ::= SEQUENCE {
        ilomCtrlActiveDirCustomGroupId                Integer32,
        ilomCtrlActiveDirCustomGroupName              SnmpAdminString,
        ilomCtrlActiveDirCustomGroupRoles             ILOMCtrlUserRoles
    }

ilomCtrlActiveDirCustomGroupId OBJECT-TYPE
    SYNTAX Integer32 (1..5)
    MAX-ACCESS not-accessible
    STATUS current
    DESCRIPTION
        "An integer identifier of the Active Directory custom group entry."
    ::= { ilomCtrlActiveDirCustomGroupsEntry 1 }

ilomCtrlActiveDirCustomGroupName OBJECT-TYPE
    SYNTAX SnmpAdminString
    MAX-ACCESS read-write
    STATUS current
    DESCRIPTION
        "This string should contain a distinguished name that exactly matches
         one of the group names on the ActiveDirectory server.  Any user belonging
         to one of these groups in this table will be assigned the ILOM role
         based on the entry's configuration for roles."
    ::= { ilomCtrlActiveDirCustomGroupsEntry 2 }

ilomCtrlActiveDirCustomGroupRoles OBJECT-TYPE
    SYNTAX ILOMCtrlUserRoles
    MAX-ACCESS read-write
    STATUS current
    DESCRIPTION
        "Specifies the role that a user authenticated via Active Directory should have.
         Setting this property to legacy roles of 'Administrator' or 'Operator', or
         any of the individual role IDs of 'a', 'u', 'c', 'r', 'o' and 's' will cause
         the Active Directory client to ignore the schema stored on the AD server.
         Setting this to 'none' clears the value and indicates that the native
         Active Directory schema should be used. The role IDs can be joined
         together 'aucros' where  a-admin, u-user, c-console, r-reset,
         s-service and o-readOnly."
    ::= { ilomCtrlActiveDirCustomGroupsEntry 3 }

ilomCtrlActiveDirectoryCertClear OBJECT-TYPE
    SYNTAX TruthValue
    MAX-ACCESS read-write
    STATUS current
    DESCRIPTION
        "A variable that will clear the certificate info associated
         with the server when it is set to true."
    ::= { ilomCtrlActiveDirectory 16 }

ilomCtrlActiveDirectoryCertVersion OBJECT-TYPE
    SYNTAX DisplayString
    MAX-ACCESS read-only
    STATUS current
    DESCRIPTION
        "A string indicating the certificate version of the
         certificate file."
    ::= { ilomCtrlActiveDirectory 17 }

ilomCtrlActiveDirectoryCertSerialNo OBJECT-TYPE
    SYNTAX DisplayString
    MAX-ACCESS read-only
    STATUS current
    DESCRIPTION
        "A string showing the serial number of the certificate file."
    ::= { ilomCtrlActiveDirectory 18 }

ilomCtrlActiveDirectoryCertIssuer OBJECT-TYPE
    SYNTAX DisplayString
    MAX-ACCESS read-only
    STATUS current
    DESCRIPTION
        "A string showing the issuer of the certificate file."
    ::= { ilomCtrlActiveDirectory 19 }

ilomCtrlActiveDirectoryCertSubject OBJECT-TYPE
    SYNTAX DisplayString
    MAX-ACCESS read-only
    STATUS current
    DESCRIPTION
        "A string showing the subject of the certificate file."
    ::= { ilomCtrlActiveDirectory 20 }

ilomCtrlActiveDirectoryCertValidBegin OBJECT-TYPE
    SYNTAX DisplayString
    MAX-ACCESS read-only
    STATUS current
    DESCRIPTION
        "A string showing the valid start date of the certificate file."
    ::= { ilomCtrlActiveDirectory 21 }

ilomCtrlActiveDirectoryCertValidEnd OBJECT-TYPE
    SYNTAX DisplayString
    MAX-ACCESS read-only
    STATUS current
    DESCRIPTION
        "A string showing the valid end date of the certificate file."
    ::= { ilomCtrlActiveDirectory 22 }

ilomCtrlActiveDirDnsLocatorEnabled OBJECT-TYPE
    SYNTAX TruthValue
    MAX-ACCESS read-write
    STATUS current
    DESCRIPTION
        "Specifies whether or not the Active Directory DNS Locator
         functionality is enabled."
    ::= { ilomCtrlActiveDirectory 23 }

ilomCtrlActiveDirDnsLocatorQueryTable OBJECT-TYPE
    SYNTAX SEQUENCE OF ILOMCtrlActiveDirDnsLocatorQueryEntry
    MAX-ACCESS not-accessible
    STATUS current
    DESCRIPTION
        "This table is used to configure DNS Locator search queries
         used to locate the Active Directory server."
    ::= { ilomCtrlActiveDirectory 24 }

ilomCtrlActiveDirDnsLocatorQueryEntry OBJECT-TYPE
    SYNTAX ILOMCtrlActiveDirDnsLocatorQueryEntry
    MAX-ACCESS not-accessible
    STATUS current
    DESCRIPTION
        "An entry for an Active Directory DNS Locator search query."
    INDEX { ilomCtrlActiveDirDnsLocatorQueryId }
    ::= { ilomCtrlActiveDirDnsLocatorQueryTable 1 }

ILOMCtrlActiveDirDnsLocatorQueryEntry ::= SEQUENCE {
        ilomCtrlActiveDirDnsLocatorQueryId       Integer32,
        ilomCtrlActiveDirDnsLocatorQueryService  SnmpAdminString
    }

ilomCtrlActiveDirDnsLocatorQueryId OBJECT-TYPE
    SYNTAX Integer32 (1..5)
    MAX-ACCESS not-accessible
    STATUS current
    DESCRIPTION
        "An integer identifier of the Active Directory DNS Locator Query entry."
    ::= { ilomCtrlActiveDirDnsLocatorQueryEntry 1 }

ilomCtrlActiveDirDnsLocatorQueryService OBJECT-TYPE
    SYNTAX SnmpAdminString
    MAX-ACCESS read-write
    STATUS current
    DESCRIPTION
        "This string should contain the service name that will be used to
         perform the DNS query.  The name may contain '<DOMAIN>' as a
         substitution marker, being replaced by the domain information
         associated for the user at the time of authentication.  Also, the
         optional '<PORT: >' (ie <PORT:636> for standard LDAP/SSL port 636)
         can be used to override any learned port information if necessary."
    ::= { ilomCtrlActiveDirDnsLocatorQueryEntry 2 }

ilomCtrlActiveDirExpSearchEnabled OBJECT-TYPE
    SYNTAX TruthValue
    MAX-ACCESS read-write
    STATUS current
    DESCRIPTION
        "Specifies whether or not the Active Directory expanded search
         query functionality is enabled."
    ::= { ilomCtrlActiveDirectory 25 }

ilomCtrlActiveDirStrictCredentialErrorEnabled OBJECT-TYPE
    SYNTAX TruthValue
    MAX-ACCESS read-write
    STATUS current
    DESCRIPTION
        "Specifies whether or not user credential errors for Active Directory
         cause the user credentials to be completely errored out, or if the
         credential validation is attempted using any alternate server. When
         the parameter is true, the first user credential violation takes effect,
         but when the mode is false, the same user credentionals can be
         presented to other servers for authentication."
    ::= { ilomCtrlActiveDirectory 26 }

-- ***************************************************************************
-- *                      ilomCtrlSMTP
-- ***************************************************************************

-- This section provides properties for configuring the embedded SMTP
-- client.

ilomCtrlSMTPEnabled OBJECT-TYPE
    SYNTAX TruthValue
    MAX-ACCESS read-write
    STATUS current
    DESCRIPTION
        "Specifies whether or not the SMTP client is enabled."
    ::= { ilomCtrlSMTP 1 }

ilomCtrlSMTPServerIP OBJECT-TYPE
    SYNTAX IpAddress
    MAX-ACCESS read-write
    STATUS current
    DESCRIPTION
        "The IP address of the SMTP server used as a name service for
         user accounts."
    ::= { ilomCtrlSMTP 2 }

ilomCtrlSMTPPortNumber OBJECT-TYPE
    SYNTAX Integer32 (0..65535)
    MAX-ACCESS read-write
    STATUS current
    DESCRIPTION
        "Specifies the port number for the SMTP client."
    ::= { ilomCtrlSMTP 3 }

ilomCtrlSMTPCustomSender OBJECT-TYPE
    SYNTAX SnmpAdminString (SIZE (0..80))
    MAX-ACCESS read-write
    STATUS current
    DESCRIPTION
        "An optional format to identify the sender or the 'from' address.
         Customizing this string allows the user to specify the exact contents
         (up to 80 chars) of the 'from' field in the email message. Either one
         of the substitution strings '<IPADDRESS>' or '<HOSTNAME>' can be used
         as needed. e.g., ilom-sp@sp1302.dev.sun.com, sun-ilom@[<IPADDRESS>],
         or ilom-alert@<HOSTNAME>.abc.com.  By default, this parameter is an
         empty string.  The 'from' field is formatted by either: 1) alert-rule
         custom-sender, 2) smtp custom-sender, or 3) the standard ILOM originator."
   DEFVAL { "" }
    ::= { ilomCtrlSMTP 4 }

-- ***************************************************************************
-- *                      ilomCtrlThd
-- ***************************************************************************

-- This section provides Telemetry Harness Daemon (THD) status and control,
-- as well as status and control for THD modules.

ilomCtrlThdState OBJECT-TYPE
    SYNTAX SnmpAdminString
    MAX-ACCESS read-only
    STATUS current
    DESCRIPTION
        "The state of the THD daemon."
    ::= { ilomCtrlThd 1 }

ilomCtrlThdAction OBJECT-TYPE
    SYNTAX ILOMCtrlThdAction
    MAX-ACCESS read-write
    STATUS current
    DESCRIPTION
        "Control action for THD daemon, either suspend or resume."
    ::= { ilomCtrlThd 2 }

ilomCtrlThdModulesTable OBJECT-TYPE
    SYNTAX SEQUENCE OF ILOMCtrlThdModulesEntry
    MAX-ACCESS not-accessible
    STATUS current
    DESCRIPTION
        "A table listing the currently loaded THD modules."
    ::= { ilomCtrlThd 3 }

ilomCtrlThdModulesEntry OBJECT-TYPE
    SYNTAX ILOMCtrlThdModulesEntry
    MAX-ACCESS not-accessible
    STATUS current
    DESCRIPTION
        "An entry for a currently loaded THD module."
    INDEX { ilomCtrlThdModuleName }
    ::= { ilomCtrlThdModulesTable 1 }

ILOMCtrlThdModulesEntry ::= SEQUENCE {
        ilomCtrlThdModuleName       ILOMCtrlTargetIndex,
        ilomCtrlThdModuleDesc       SnmpAdminString,
        ilomCtrlThdModuleState      SnmpAdminString,
        ilomCtrlThdModuleAction     ILOMCtrlThdAction
    }

ilomCtrlThdModuleName OBJECT-TYPE
    SYNTAX ILOMCtrlTargetIndex
    MAX-ACCESS not-accessible
    STATUS current
    DESCRIPTION
        "The name of the THD module."
    ::= { ilomCtrlThdModulesEntry 1 }

ilomCtrlThdModuleDesc OBJECT-TYPE
    SYNTAX SnmpAdminString
    MAX-ACCESS read-only
    STATUS current
    DESCRIPTION
        "The description of the THD module."
    ::= { ilomCtrlThdModulesEntry 2 }

ilomCtrlThdModuleState OBJECT-TYPE
    SYNTAX SnmpAdminString
    MAX-ACCESS read-only
    STATUS current
    DESCRIPTION
        "The state of the THD module."
    ::= { ilomCtrlThdModulesEntry 3 }

ilomCtrlThdModuleAction OBJECT-TYPE
    SYNTAX ILOMCtrlThdAction
    MAX-ACCESS read-write
    STATUS current
    DESCRIPTION
        "The control action for the THD module."
    ::= { ilomCtrlThdModulesEntry 4 }

ilomCtrlThdInstanceTable OBJECT-TYPE
    SYNTAX SEQUENCE OF ILOMCtrlThdInstanceEntry
    MAX-ACCESS not-accessible
    STATUS current
    DESCRIPTION
        "A table listing instances of currently loaded THD modules."
    ::= { ilomCtrlThd 4 }

ilomCtrlThdInstanceEntry OBJECT-TYPE
    SYNTAX ILOMCtrlThdInstanceEntry
    MAX-ACCESS not-accessible
    STATUS current
    DESCRIPTION
        "An entry for a currently loaded THD module."
    INDEX { ilomCtrlThdModName, ilomCtrlThdInstanceName }
    ::= { ilomCtrlThdInstanceTable 1 }

ILOMCtrlThdInstanceEntry ::= SEQUENCE {
        ilomCtrlThdModName          ILOMCtrlModTargetIndex,
        ilomCtrlThdInstanceName     ILOMCtrlInstanceTargetIndex,
        ilomCtrlThdInstanceState    SnmpAdminString,
        ilomCtrlThdInstanceAction   ILOMCtrlThdAction
    }

ilomCtrlThdModName OBJECT-TYPE
    SYNTAX ILOMCtrlModTargetIndex
    MAX-ACCESS not-accessible
    STATUS current
    DESCRIPTION
        "The name of the THD class of the instance."
    ::= { ilomCtrlThdInstanceEntry 1 }

ilomCtrlThdInstanceName OBJECT-TYPE
    SYNTAX ILOMCtrlInstanceTargetIndex
    MAX-ACCESS not-accessible
    STATUS current
    DESCRIPTION
        "The name of the instance."
    ::= { ilomCtrlThdInstanceEntry 2 }

ilomCtrlThdInstanceState OBJECT-TYPE
    SYNTAX SnmpAdminString
    MAX-ACCESS read-only
    STATUS current
    DESCRIPTION
        "The state of the instance."
    ::= { ilomCtrlThdInstanceEntry 3 }

ilomCtrlThdInstanceAction OBJECT-TYPE
    SYNTAX ILOMCtrlThdAction
    MAX-ACCESS read-write
    STATUS current
    DESCRIPTION
        "The control action for instance."
    ::= { ilomCtrlThdInstanceEntry 4 }

-- ***************************************************************************
-- *                      ilomCtrlLdapSsl
-- * This section defines properties for configuring the Ldap/ssl client.
-- ***************************************************************************
ilomCtrlLdapSslGlobalObj  OBJECT IDENTIFIER ::= { ilomCtrlLdapSsl 1 }

ilomCtrlLdapSslEnabled OBJECT-TYPE
    SYNTAX TruthValue
    MAX-ACCESS read-write
    STATUS current
    DESCRIPTION
        "Specifies whether or not the LDAP/SSL client is enabled."
    ::= { ilomCtrlLdapSslGlobalObj 1 }

ilomCtrlLdapSslIP OBJECT-TYPE
    SYNTAX IpAddress
    MAX-ACCESS read-write
    STATUS current
    DESCRIPTION
        "The IP address of the LDAP/SSL server used as a directory service for
         user accounts."
    ::= { ilomCtrlLdapSslGlobalObj 2 }

ilomCtrlLdapSslPortNumber OBJECT-TYPE
    SYNTAX Integer32 (0..65535)
    MAX-ACCESS read-write
    STATUS current
    DESCRIPTION
        "Specifies the port number for the LDAP/SSL client.  Specifying 0 as
         the port means auto-select while specifying 1-65535 configures the
         actual port value."
    ::= { ilomCtrlLdapSslGlobalObj 3 }

ilomCtrlLdapSslDefaultRole OBJECT-TYPE
    SYNTAX ILOMCtrlUserRole
    MAX-ACCESS read-write
    STATUS current
    DESCRIPTION
        "Specifies the role that a user authenticated via LDAP/SSL should have.
         Setting this property to 'Administrator' or 'Operator' will cause the
         LDAP/SSL client to ignore the schema stored on the server.  The user
         will be granted the corresponding access level.  Setting this to an
         empty string, or 'none' clears the value and indicates that the native
         LDAP/SSL schema should be used."
    ::= { ilomCtrlLdapSslGlobalObj 4 }

ilomCtrlLdapSslCertFileURI OBJECT-TYPE
    SYNTAX SnmpAdminString
    MAX-ACCESS read-write
    STATUS current
    DESCRIPTION
        "The tftp URI of the LDAP/SSL server's certificate file that should
         be uploaded in order to perform certificate validation.  Setting
         the URI causes the tranfer of the specified file, making the
         certificate available immediately for certificate authentication.
         The server certificate file is needed when Strict Cert Mode
         is enabled.  Additionally, either 'remove' or 'restore' are
         supported for direct certificate manipulation."
    ::= { ilomCtrlLdapSslGlobalObj 5 }

ilomCtrlLdapSslTimeout OBJECT-TYPE
    SYNTAX Integer32 (1..20)
    MAX-ACCESS read-write
    STATUS current
    DESCRIPTION
        "Specifies the number of seconds to wait before timing out if the
         LDAP/SSL Server is not responding."
    ::= { ilomCtrlLdapSslGlobalObj 6 }

ilomCtrlLdapSslStrictCertEnabled OBJECT-TYPE
    SYNTAX TruthValue
    MAX-ACCESS read-write
    STATUS current
    DESCRIPTION
        "Specifies whether or not the Strict Cert Mode is enabled for
         the LDAP/SSL Client.  If enabled, the LDAP/SSL server's
         certificate must be uploaded to the SP so that certificate
         validation can be performed when communicating with the
         LDAP/SSL server."
    ::= { ilomCtrlLdapSslGlobalObj 7 }

ilomCtrlLdapSslCertFileStatus OBJECT-TYPE
    SYNTAX DisplayString
    MAX-ACCESS read-only
    STATUS current
    DESCRIPTION
        "A string indicating the status of the certificate file.
         This is useful in determining whether a certificate file
         is present or not."
    ::= { ilomCtrlLdapSslGlobalObj 8 }

ilomCtrlLdapSslLogDetail OBJECT-TYPE
    SYNTAX INTEGER  {
               none(1),     -- no messages logged
               high(2),     -- high messages only
               medium(3),   -- high + medium
               low(4),      -- high + medium + low
               trace(5)     -- high + medium + low + trace
           }
    MAX-ACCESS read-write
    STATUS current
    DESCRIPTION
        "Controls the amount of messages sent to the event log.  The
         high priority has the least number of messages going to the log,
         while the lowest priority 'trace' has the most messages logged.
         When this object is set to 'none', no messages are logged."
    ::= { ilomCtrlLdapSslGlobalObj 9 }

ilomCtrlLdapSslDefaultRoles OBJECT-TYPE
    SYNTAX ILOMCtrlUserRoles
    MAX-ACCESS read-write
    STATUS current
    DESCRIPTION
        "Specifies the role that a user authenticated via LDAP/SSL should have.
         Setting this property to legacy roles of 'Administrator' or 'Operator', or
         any of the individual role IDs of 'a', 'u', 'c', 'r', 'o' and 's'  will cause
         the LDAP/SSL client to ignore the schema stored on the LDAP server.
         Setting this to 'none' clears the value and indicates that the native
         LDAP/SSL schema should be used.  The role IDs can be joined
         together 'aucros' where a-admin, u-user, c-console, r-reset,
         s-service and o-readOnly."
    ::= { ilomCtrlLdapSslGlobalObj 10 }

ilomCtrlLdapSslCertFileClear OBJECT-TYPE
    SYNTAX TruthValue
    MAX-ACCESS read-write
    STATUS current
    DESCRIPTION
        "A variable that will clear the certificate info associated
         with the server when it is set to true."
    ::= { ilomCtrlLdapSslGlobalObj 11 }

ilomCtrlLdapSslCertFileVersion OBJECT-TYPE
    SYNTAX DisplayString
    MAX-ACCESS read-only
    STATUS current
    DESCRIPTION
        "A string indicating the certificate version of the
         certificate file."
    ::= { ilomCtrlLdapSslGlobalObj 12 }

ilomCtrlLdapSslCertFileSerialNo OBJECT-TYPE
    SYNTAX DisplayString
    MAX-ACCESS read-only
    STATUS current
    DESCRIPTION
        "A string showing the serial number of the certificate file."
    ::= { ilomCtrlLdapSslGlobalObj 13 }

ilomCtrlLdapSslCertFileIssuer OBJECT-TYPE
    SYNTAX DisplayString
    MAX-ACCESS read-only
    STATUS current
    DESCRIPTION
        "A string showing the issuer of the certificate file."
    ::= { ilomCtrlLdapSslGlobalObj 14 }

ilomCtrlLdapSslCertFileSubject OBJECT-TYPE
    SYNTAX DisplayString
    MAX-ACCESS read-only
    STATUS current
    DESCRIPTION
        "A string showing the subject of the certificate file."
    ::= { ilomCtrlLdapSslGlobalObj 15 }

ilomCtrlLdapSslCertFileValidBegin OBJECT-TYPE
    SYNTAX DisplayString
    MAX-ACCESS read-only
    STATUS current
    DESCRIPTION
        "A string showing the valid start date of the certificate file."
    ::= { ilomCtrlLdapSslGlobalObj 16 }

ilomCtrlLdapSslCertFileValidEnd OBJECT-TYPE
    SYNTAX DisplayString
    MAX-ACCESS read-only
    STATUS current
    DESCRIPTION
        "A string showing the valid end date of the certificate file."
    ::= { ilomCtrlLdapSslGlobalObj 17 }

ilomCtrlLdapSslOptUsrMappingEnabled OBJECT-TYPE
    SYNTAX TruthValue
    MAX-ACCESS read-write
    STATUS current
    DESCRIPTION
        "Specifies whether or not the optional UserMapping feature is enabled. When
         this feature is enabled, a typical Manager style ldap bind is done first
         using the specified credentials for the bindDn and bindPw. Then, the
         user's login name is used as part of the search/filter criteria defined
         in the attribute-info to obtain the user's official Distinguished Name."
    ::= { ilomCtrlLdapSslGlobalObj 18 }

ilomCtrlLdapSslOptUsrMappingAttrInfo OBJECT-TYPE
    SYNTAX SnmpAdminString (SIZE (0..80))
    MAX-ACCESS read-write
    STATUS current
    DESCRIPTION
        "The attribute information used to lookup the user login name to
         the user's Distinguished Name (DN). Typically, it looks very much
         like a standard LDAP query or filter. The <USERNAME> prefix will
         be replaced with the login name as part of the query
           eg: (&(objectclass=person)(uid=<USERNAME>))."
    ::= { ilomCtrlLdapSslGlobalObj 19 }

ilomCtrlLdapSslOptUsrMappingBindDn OBJECT-TYPE
    SYNTAX SnmpAdminString (SIZE (0..80))
    MAX-ACCESS read-write
    STATUS current
    DESCRIPTION
        "The Distinguished Name used for the manager style ldap bind so
         that user lookups can be done."
    ::= { ilomCtrlLdapSslGlobalObj 20 }

ilomCtrlLdapSslOptUsrMappingBindPw OBJECT-TYPE
    SYNTAX SnmpAdminString (SIZE (0..32))
    MAX-ACCESS read-write
    STATUS current
    DESCRIPTION
        "The password string used for the manager style ldap bind."
    ::= { ilomCtrlLdapSslGlobalObj 21 }

ilomCtrlLdapSslOptUsrMappingSearchBase OBJECT-TYPE
    SYNTAX SnmpAdminString (SIZE (0..80))
    MAX-ACCESS read-write
    STATUS current
    DESCRIPTION
        "The search based used to attempt the user name look up as defined
         in the attribute information above."
    ::= { ilomCtrlLdapSslGlobalObj 22 }

--
-- Domain Table
--
ilomCtrlLdapSslUserDomainTable OBJECT-TYPE
    SYNTAX SEQUENCE OF ILOMCtrlLdapSslUserDomainEntry
    MAX-ACCESS not-accessible
    STATUS current
    DESCRIPTION
        "This table is used to configure domain information required for
         configuring the LDAP/SSL client."
    ::= { ilomCtrlLdapSsl 2 }

ilomCtrlLdapSslUserDomainEntry OBJECT-TYPE
    SYNTAX ILOMCtrlLdapSslUserDomainEntry
    MAX-ACCESS not-accessible
    STATUS current
    DESCRIPTION
        "An entry for an LDAP/SSL user domain."
    INDEX { ilomCtrlLdapSslUserDomainId }
    ::= { ilomCtrlLdapSslUserDomainTable 1 }

ILOMCtrlLdapSslUserDomainEntry ::= SEQUENCE {
        ilomCtrlLdapSslUserDomainId           Integer32,
        ilomCtrlLdapSslUserDomain             SnmpAdminString
    }

ilomCtrlLdapSslUserDomainId OBJECT-TYPE
    SYNTAX Integer32 (1..5)
    MAX-ACCESS not-accessible
    STATUS current
    DESCRIPTION
        "An integer identifier of the LDAP/SSL domain."
    ::= { ilomCtrlLdapSslUserDomainEntry 1 }

ilomCtrlLdapSslUserDomain OBJECT-TYPE
    SYNTAX SnmpAdminString
    MAX-ACCESS read-write
    STATUS current
    DESCRIPTION
        "This string should match exactly with an authentication domain
         on the LDAP/SSL server.  This string should contain
         a substitution string '<USERNAME>' which will be replaced with the
         user's login name during authentication.  Either the principle
         or distinguished name format is allowed."
    ::= { ilomCtrlLdapSslUserDomainEntry 2 }

--
-- Admin Group Table
--
ilomCtrlLdapSslAdminGroupsTable OBJECT-TYPE
    SYNTAX SEQUENCE OF ILOMCtrlLdapSslAdminGroupsEntry
    MAX-ACCESS not-accessible
    STATUS current
    DESCRIPTION
        "This table is used to configure Admin Group information required for
         configuring the LDAP/SSL client."
    ::= { ilomCtrlLdapSsl 3 }

ilomCtrlLdapSslAdminGroupsEntry OBJECT-TYPE
    SYNTAX ILOMCtrlLdapSslAdminGroupsEntry
    MAX-ACCESS not-accessible
    STATUS current
    DESCRIPTION
        "An entry for an LDAP/SSL Admin Group."
    INDEX { ilomCtrlLdapSslAdminGroupId }
    ::= { ilomCtrlLdapSslAdminGroupsTable 1 }

ILOMCtrlLdapSslAdminGroupsEntry ::= SEQUENCE {
        ilomCtrlLdapSslAdminGroupId           Integer32,
        ilomCtrlLdapSslAdminGroupName         SnmpAdminString
    }

ilomCtrlLdapSslAdminGroupId OBJECT-TYPE
    SYNTAX Integer32 (1..5)
    MAX-ACCESS not-accessible
    STATUS current
    DESCRIPTION
        "An integer identifier of the LDAP/SSL AdminGroup entry."
    ::= { ilomCtrlLdapSslAdminGroupsEntry 1 }

ilomCtrlLdapSslAdminGroupName OBJECT-TYPE
    SYNTAX SnmpAdminString
    MAX-ACCESS read-write
    STATUS current
    DESCRIPTION
        "This string should contain a distinguished name that exactly matches
         one of the group names on the LDAP/SSL server.  Any user belonging
         to one of these groups in this table will be assigned the ILOM role
         of Administrator."
    ::= { ilomCtrlLdapSslAdminGroupsEntry 2 }

--
-- Operator Group Table
--
ilomCtrlLdapSslOperatorGroupsTable OBJECT-TYPE
    SYNTAX SEQUENCE OF ILOMCtrlLdapSslOperatorGroupsEntry
    MAX-ACCESS not-accessible
    STATUS current
    DESCRIPTION
        "This table is used to configure Operator Group information required for
         configuring the LDAP/SSL client."
    ::= { ilomCtrlLdapSsl 4 }

ilomCtrlLdapSslOperatorGroupsEntry OBJECT-TYPE
    SYNTAX ILOMCtrlLdapSslOperatorGroupsEntry
    MAX-ACCESS not-accessible
    STATUS current
    DESCRIPTION
        "An entry for an LDAP/SSL Operator Group."
    INDEX { ilomCtrlLdapSslOperatorGroupId }
    ::= { ilomCtrlLdapSslOperatorGroupsTable 1 }

ILOMCtrlLdapSslOperatorGroupsEntry ::= SEQUENCE {
        ilomCtrlLdapSslOperatorGroupId                Integer32,
        ilomCtrlLdapSslOperatorGroupName              SnmpAdminString
    }

ilomCtrlLdapSslOperatorGroupId OBJECT-TYPE
    SYNTAX Integer32 (1..5)
    MAX-ACCESS not-accessible
    STATUS current
    DESCRIPTION
        "An integer identifier of the LDAP/SSL Operator Group entry."
    ::= { ilomCtrlLdapSslOperatorGroupsEntry 1 }

ilomCtrlLdapSslOperatorGroupName OBJECT-TYPE
    SYNTAX SnmpAdminString
    MAX-ACCESS read-write
    STATUS current
    DESCRIPTION
        "This string should contain a distinguished name that exactly matches
         one of the group names on the LDAP/SSL server.  Any user belonging
         to one of these groups in this table will be assigned the ILOM role
         of Operator."
    ::= { ilomCtrlLdapSslOperatorGroupsEntry 2 }

--
-- Alternate Server Table
--
ilomCtrlLdapSslAlternateServerTable OBJECT-TYPE
    SYNTAX SEQUENCE OF ILOMCtrlLdapSslAlternateServerEntry
    MAX-ACCESS not-accessible
    STATUS current
    DESCRIPTION
        "This table is used to view and configure alternate server information
         for the LDAP/SSL client."
    ::= { ilomCtrlLdapSsl 5 }

ilomCtrlLdapSslAlternateServerEntry OBJECT-TYPE
    SYNTAX ILOMCtrlLdapSslAlternateServerEntry
    MAX-ACCESS not-accessible
    STATUS current
    DESCRIPTION
        "An entry for an LDAP/SSL alternate server table."
    INDEX { ilomCtrlLdapSslAlternateServerId }
    ::= { ilomCtrlLdapSslAlternateServerTable 1 }

ILOMCtrlLdapSslAlternateServerEntry ::= SEQUENCE {
        ilomCtrlLdapSslAlternateServerId              Integer32,
        ilomCtrlLdapSslAlternateServerIp              IpAddress,
        ilomCtrlLdapSslAlternateServerPort            Integer32,
        ilomCtrlLdapSslAlternateServerCertStatus      DisplayString,
        ilomCtrlLdapSslAlternateServerCertURI         SnmpAdminString,
        ilomCtrlLdapSslAlternateServerCertClear       TruthValue,
        ilomCtrlLdapSslAlternateServerCertVersion     DisplayString,
        ilomCtrlLdapSslAlternateServerCertSerialNo    DisplayString,
        ilomCtrlLdapSslAlternateServerCertIssuer      DisplayString,
        ilomCtrlLdapSslAlternateServerCertSubject     DisplayString,
        ilomCtrlLdapSslAlternateServerCertValidBegin  DisplayString,
        ilomCtrlLdapSslAlternateServerCertValidEnd    DisplayString
    }

ilomCtrlLdapSslAlternateServerId OBJECT-TYPE
    SYNTAX Integer32 (1..5)
    MAX-ACCESS not-accessible
    STATUS current
    DESCRIPTION
        "An integer identifier of the LDAP/SSL alternate server table."
    ::= { ilomCtrlLdapSslAlternateServerEntry 1 }

ilomCtrlLdapSslAlternateServerIp OBJECT-TYPE
    SYNTAX IpAddress
    MAX-ACCESS read-write
    STATUS current
    DESCRIPTION
        "The IP address of the LDAP/SSL alternate server
        used as directory server for user accounts."
    ::= { ilomCtrlLdapSslAlternateServerEntry 2 }

ilomCtrlLdapSslAlternateServerPort OBJECT-TYPE
    SYNTAX Integer32 (0..65535)
    MAX-ACCESS read-write
    STATUS current
    DESCRIPTION
        "Specifies the port number for the LDAP/SSL alternate server.
         Specifying 0 as the port indicates that auto-select will use the
         well known port number.  Specifying 1-65535 is used to explicitly
         set the port number."
    ::= { ilomCtrlLdapSslAlternateServerEntry 3 }

ilomCtrlLdapSslAlternateServerCertStatus OBJECT-TYPE
    SYNTAX DisplayString
    MAX-ACCESS read-only
    STATUS current
    DESCRIPTION
        "A string indicating the status of the certificate file.
         This is useful in determining whether a certificate file
         is present or not."
    ::= { ilomCtrlLdapSslAlternateServerEntry 4 }

ilomCtrlLdapSslAlternateServerCertURI OBJECT-TYPE
    SYNTAX SnmpAdminString
    MAX-ACCESS read-write
    STATUS current
    DESCRIPTION
        "This is the URI of a certificate file needed when Strict Cert Mode is
         enabled.  Setting the URI causes the tranfer of the file, making the
         certificate available immediately for certificate authentication.
         Additionally, either 'remove' or 'restore' are supported for direct
         certificate manipulation."
    ::= { ilomCtrlLdapSslAlternateServerEntry 5 }

ilomCtrlLdapSslAlternateServerCertClear OBJECT-TYPE
    SYNTAX TruthValue
    MAX-ACCESS read-write
    STATUS current
    DESCRIPTION
        "A variable that will clear the certificate info associated
         with the server when it is set to true."
    ::= { ilomCtrlLdapSslAlternateServerEntry 6 }

ilomCtrlLdapSslAlternateServerCertVersion OBJECT-TYPE
    SYNTAX DisplayString
    MAX-ACCESS read-only
    STATUS current
    DESCRIPTION
        "A string indicating the certificate version of the
         alternate server certificate file."
    ::= { ilomCtrlLdapSslAlternateServerEntry 7 }

ilomCtrlLdapSslAlternateServerCertSerialNo OBJECT-TYPE
    SYNTAX DisplayString
    MAX-ACCESS read-only
    STATUS current
    DESCRIPTION
        "A string showing the serial number of the alternate server
         certificate file."
    ::= { ilomCtrlLdapSslAlternateServerEntry 8 }

ilomCtrlLdapSslAlternateServerCertIssuer OBJECT-TYPE
    SYNTAX DisplayString
    MAX-ACCESS read-only
    STATUS current
    DESCRIPTION
        "A string showing the issuer of the alternate server
         certificate file."
    ::= { ilomCtrlLdapSslAlternateServerEntry 9 }

ilomCtrlLdapSslAlternateServerCertSubject OBJECT-TYPE
    SYNTAX DisplayString
    MAX-ACCESS read-only
    STATUS current
    DESCRIPTION
        "A string showing the subject of the alternate server
         certificate file."
    ::= { ilomCtrlLdapSslAlternateServerEntry 10 }

ilomCtrlLdapSslAlternateServerCertValidBegin OBJECT-TYPE
    SYNTAX DisplayString
    MAX-ACCESS read-only
    STATUS current
    DESCRIPTION
        "A string showing the valid start date of the alternate server
         certificate file."
    ::= { ilomCtrlLdapSslAlternateServerEntry 11 }

ilomCtrlLdapSslAlternateServerCertValidEnd OBJECT-TYPE
    SYNTAX DisplayString
    MAX-ACCESS read-only
    STATUS current
    DESCRIPTION
        "A string showing the valid end date of the alternate server
         certificate file."
    ::= { ilomCtrlLdapSslAlternateServerEntry 12 }

--
-- Custom Group Table
--
ilomCtrlLdapSslCustomGroupsTable OBJECT-TYPE
    SYNTAX SEQUENCE OF ILOMCtrlLdapSslCustomGroupsEntry
    MAX-ACCESS not-accessible
    STATUS current
    DESCRIPTION
        "This table is used to configure custom group information required for
         configuring the LDAP/SSL client."
    ::= { ilomCtrlLdapSsl 6 }

ilomCtrlLdapSslCustomGroupsEntry OBJECT-TYPE
    SYNTAX ILOMCtrlLdapSslCustomGroupsEntry
    MAX-ACCESS not-accessible
    STATUS current
    DESCRIPTION
        "An entry for an LDAP/SSLcustom group."
    INDEX { ilomCtrlLdapSslCustomGroupId }
    ::= { ilomCtrlLdapSslCustomGroupsTable 1 }

ILOMCtrlLdapSslCustomGroupsEntry ::= SEQUENCE {
        ilomCtrlLdapSslCustomGroupId                Integer32,
        ilomCtrlLdapSslCustomGroupName              SnmpAdminString,
        ilomCtrlLdapSslCustomGroupRoles             ILOMCtrlUserRoles
    }

ilomCtrlLdapSslCustomGroupId OBJECT-TYPE
    SYNTAX Integer32 (1..5)
    MAX-ACCESS not-accessible
    STATUS current
    DESCRIPTION
        "An integer identifier of the LDAP/SSL custom group entry."
    ::= { ilomCtrlLdapSslCustomGroupsEntry 1 }

ilomCtrlLdapSslCustomGroupName OBJECT-TYPE
    SYNTAX SnmpAdminString
    MAX-ACCESS read-write
    STATUS current
    DESCRIPTION
        "This string should contain a distinguished name that exactly matches
         one of the group names on the LDAP/SSL server.  Any user belonging
         to one of these groups in this table will be assigned the ILOM role
         based on the entry's configuration for roles."
    ::= { ilomCtrlLdapSslCustomGroupsEntry 2 }

ilomCtrlLdapSslCustomGroupRoles OBJECT-TYPE
    SYNTAX ILOMCtrlUserRoles
    MAX-ACCESS read-write
    STATUS current
    DESCRIPTION
        "Specifies the role that a user authenticated via LDAP/SSL should have.
         Setting this property to legacy roles of 'Administrator' or 'Operator', or
         any of the individual role IDs of 'a', 'u', 'c', 'r', 'o' and 's' will cause
         the LDAP/SSL client to ignore the schema stored on the LDAP/SSL server.
         Setting this to 'none' clears the value and indicates that the native
         LDAP/SSL schema should be used. The role IDs can be joined
         together 'aucros' where  a-admin, u-user, c-console, r-reset,
         s-service and o-readOnly."
    ::= { ilomCtrlLdapSslCustomGroupsEntry 3 }

-- ***************************************************************************
-- *                      ilomCtrlDNS
-- ***************************************************************************

-- This section provides properties for configuring the DNS nameserver and
-- searchpath.

ilomCtrlDNSNameServers OBJECT-TYPE
   SYNTAX SnmpAdminString
   MAX-ACCESS read-write
   STATUS current
   DESCRIPTION
       "Specifies the nameserver for DNS."
   ::= { ilomCtrlDNS 1 }

ilomCtrlDNSSearchPath OBJECT-TYPE
   SYNTAX SnmpAdminString
   MAX-ACCESS read-write
   STATUS current
   DESCRIPTION
        "Specifies the searchpath for DNS."
   ::= { ilomCtrlDNS 2 }

ilomCtrlDNSdhcpAutoDns OBJECT-TYPE
   SYNTAX TruthValue
   MAX-ACCESS read-write
   STATUS current
   DESCRIPTION
        "Specifies whether or not DHCP autodns is enabled."
   ::= { ilomCtrlDNS 3 }

ilomCtrlDNSTimeout OBJECT-TYPE
   SYNTAX Integer32 (1..10)
   MAX-ACCESS read-write
   STATUS current
   DESCRIPTION
        "Specifies the number of seconds to wait before timing out if
         the server does not respond."
   DEFVAL { 5 }
   ::= { ilomCtrlDNS 4 }

ilomCtrlDNSRetries OBJECT-TYPE
   SYNTAX Integer32 (0..4)
   MAX-ACCESS read-write
   STATUS current
   DESCRIPTION
        "Specifies the number of times a request is attempted again, after
         a timeout."
   DEFVAL { 1 }
   ::= { ilomCtrlDNS 5 }
--
-- Object Groups
--

ilomCtrlObjectsGroup OBJECT-GROUP
    OBJECTS {
        ilomCtrlDeviceNTPServerOneIP,
        ilomCtrlDeviceNTPServerTwoIP,
        ilomCtrlLdapEnabled,
        ilomCtrlLdapServerIP,
        ilomCtrlLdapPortNumber,
        ilomCtrlLdapBindDn,
        ilomCtrlLdapBindPassword,
        ilomCtrlLdapSearchBase,
        ilomCtrlLdapDefaultRoles,
        ilomCtrlRadiusEnabled,
        ilomCtrlRadiusServerIP,
        ilomCtrlRadiusPortNumber,
        ilomCtrlRadiusSecret,
        ilomCtrlRadiusDefaultRoles,
        ilomCtrlRemoteSyslogDest1,
        ilomCtrlRemoteSyslogDest2,
        ilomCtrlActiveDirectoryEnabled,
        ilomCtrlActiveDirectoryIP,
        ilomCtrlActiveDirectoryPortNumber,
        ilomCtrlActiveDirectoryCertFileURI,
        ilomCtrlActiveDirectoryTimeout,
        ilomCtrlActiveDirectoryStrictCertEnabled,
        ilomCtrlActiveDirectoryCertFileStatus,
        ilomCtrlActiveDirUserDomain,
        ilomCtrlActiveDirAdminGroupName,
        ilomCtrlActiveDirOperatorGroupName,
        ilomCtrlActiveDirCustomGroupName,
        ilomCtrlActiveDirCustomGroupRoles,
        ilomCtrlActiveDirAlternateServerIp,
        ilomCtrlActiveDirAlternateServerPort,
        ilomCtrlActiveDirAlternateServerCertStatus,
        ilomCtrlActiveDirAlternateServerCertURI,
        ilomCtrlActiveDirAlternateServerCertClear,
        ilomCtrlActiveDirAlternateServerCertVersion,
        ilomCtrlActiveDirAlternateServerCertSerialNo,
        ilomCtrlActiveDirAlternateServerCertIssuer,
        ilomCtrlActiveDirAlternateServerCertSubject,
        ilomCtrlActiveDirAlternateServerCertValidBegin,
        ilomCtrlActiveDirAlternateServerCertValidEnd,
        ilomCtrlActiveDirectoryLogDetail,
        ilomCtrlActiveDirectoryDefaultRoles,
        ilomCtrlActiveDirectoryCertClear,
        ilomCtrlActiveDirectoryCertVersion,
        ilomCtrlActiveDirectoryCertSerialNo,
        ilomCtrlActiveDirectoryCertIssuer,
        ilomCtrlActiveDirectoryCertSubject,
        ilomCtrlActiveDirectoryCertValidBegin,
        ilomCtrlActiveDirectoryCertValidEnd,
        ilomCtrlActiveDirDnsLocatorEnabled,
        ilomCtrlActiveDirDnsLocatorQueryService,
        ilomCtrlActiveDirExpSearchEnabled,
        ilomCtrlActiveDirStrictCredentialErrorEnabled,
        ilomCtrlSMTPEnabled,
        ilomCtrlSMTPServerIP,
        ilomCtrlSMTPPortNumber,
        ilomCtrlSMTPCustomSender,
        ilomCtrlLdapSslEnabled,
        ilomCtrlLdapSslIP,
        ilomCtrlLdapSslPortNumber,
        ilomCtrlLdapSslDefaultRole,
        ilomCtrlLdapSslCertFileURI,
        ilomCtrlLdapSslTimeout,
        ilomCtrlLdapSslStrictCertEnabled,
        ilomCtrlLdapSslCertFileStatus,
        ilomCtrlLdapSslLogDetail,
        ilomCtrlLdapSslDefaultRoles,
        ilomCtrlLdapSslCertFileClear,
        ilomCtrlLdapSslCertFileVersion,
        ilomCtrlLdapSslCertFileSerialNo,
        ilomCtrlLdapSslCertFileIssuer,
        ilomCtrlLdapSslCertFileSubject,
        ilomCtrlLdapSslCertFileValidBegin,
        ilomCtrlLdapSslCertFileValidEnd,
        ilomCtrlLdapSslOptUsrMappingEnabled,
        ilomCtrlLdapSslOptUsrMappingAttrInfo,
        ilomCtrlLdapSslOptUsrMappingBindDn,
        ilomCtrlLdapSslOptUsrMappingBindPw,
        ilomCtrlLdapSslOptUsrMappingSearchBase,
        ilomCtrlLdapSslUserDomain,
        ilomCtrlLdapSslAdminGroupName,
        ilomCtrlLdapSslOperatorGroupName,
        ilomCtrlLdapSslCustomGroupName,
        ilomCtrlLdapSslCustomGroupRoles,
        ilomCtrlLdapSslAlternateServerIp,
        ilomCtrlLdapSslAlternateServerPort,
        ilomCtrlLdapSslAlternateServerCertStatus,
        ilomCtrlLdapSslAlternateServerCertURI,
        ilomCtrlLdapSslAlternateServerCertClear,
        ilomCtrlLdapSslAlternateServerCertVersion,
        ilomCtrlLdapSslAlternateServerCertSerialNo,
        ilomCtrlLdapSslAlternateServerCertIssuer,
        ilomCtrlLdapSslAlternateServerCertSubject,
        ilomCtrlLdapSslAlternateServerCertValidBegin,
        ilomCtrlLdapSslAlternateServerCertValidEnd,
        ilomCtrlHttpEnabled,
        ilomCtrlHttpPortNumber,
        ilomCtrlHttpSecureRedirect,
        ilomCtrlHttpsEnabled,
        ilomCtrlHttpsPortNumber,
        ilomCtrlSshRsaKeyFingerprint,
        ilomCtrlSshRsaKeyLength,
        ilomCtrlSshDsaKeyFingerprint,
        ilomCtrlSshDsaKeyLength,
        ilomCtrlSshGenerateNewKeyAction,
        ilomCtrlSshGenerateNewKeyType,
        ilomCtrlSshRestartSshdAction,
        ilomCtrlSshEnabled,
        ilomCtrlSingleSignonEnabled,
        ilomCtrlNetworkMacAddress,
        ilomCtrlNetworkIpDiscovery,
        ilomCtrlNetworkIpAddress,
        ilomCtrlNetworkIpGateway,
        ilomCtrlNetworkIpNetmask,
        ilomCtrlNetworkPendingIpDiscovery,
        ilomCtrlNetworkPendingIpAddress,
        ilomCtrlNetworkPendingIpGateway,
        ilomCtrlNetworkPendingIpNetmask,
        ilomCtrlNetworkCommitPending,
        ilomCtrlNetworkDHCPServerAddr,
        ilomCtrlNetworkPendingManagementPort,
        ilomCtrlNetworkManagementPort,
        ilomCtrlNetworkOutOfBandMacAddress,
        ilomCtrlNetworkSidebandMacAddress,
        ilomCtrlNetworkState,
        ilomCtrlLocalUserPassword,
        ilomCtrlLocalUserRoles,
        ilomCtrlLocalUserRowStatus,
        ilomCtrlLocalUserCLIMode,
        ilomCtrlSessionsUsername,
        ilomCtrlSessionsConnectionType,
        ilomCtrlSessionsLoginTime,
        ilomCtrlFirmwareMgmtVersion,
        ilomCtrlFirmwareBuildNumber,
        ilomCtrlFirmwareBuildDate,
        ilomCtrlFirmwareTFTPServerIP,
        ilomCtrlFirmwareTFTPFileName,
        ilomCtrlFirmwarePreserveConfig,
        ilomCtrlFirmwareMgmtStatus,
        ilomCtrlFirmwareMgmtAction,
        ilomCtrlFirmwareMgmtFilesystemVersion,
        ilomCtrlFirmwareDelayBIOS,
        ilomCtrlEventLogType,
        ilomCtrlEventLogTimestamp,
        ilomCtrlEventLogClass,
        ilomCtrlEventLogSeverity,
        ilomCtrlEventLogDescription,
        ilomCtrlEventLogClear,
        ilomCtrlAlertSeverity,
        ilomCtrlAlertType,
        ilomCtrlAlertDestinationIP,
        ilomCtrlAlertDestinationPort,
        ilomCtrlAlertDestinationEmail,
        ilomCtrlAlertSNMPVersion,
        ilomCtrlAlertSNMPCommunityOrUsername,
        ilomCtrlAlertEmailEventClassFilter,
        ilomCtrlAlertEmailEventTypeFilter,
        ilomCtrlAlertEmailCustomSender,
        ilomCtrlAlertEmailMessagePrefix,
        ilomCtrlDateAndTime,
        ilomCtrlNTPEnabled,
        ilomCtrlTimezone,
        ilomCtrlSerialInternalPortPresent,
        ilomCtrlSerialInternalPortBaudRate,
        ilomCtrlSerialExternalPortPresent,
        ilomCtrlSerialExternalPortBaudRate,
        ilomCtrlSerialExternalPortFlowControl,
        ilomCtrlPowerAction,
        ilomCtrlResetAction,
        ilomCtrlRedundancyStatus,
        ilomCtrlRedundancyAction,
        ilomCtrlRedundancyFRUName,
        ilomCtrlPolicyShortStr,
        ilomCtrlPolicyLongStr,
        ilomCtrlPolicyEnabled,
        ilomCtrlResetToDefaultsAction,
        ilomCtrlSPARCDiagsTrigger,
        ilomCtrlSPARCDiagsMode,
        ilomCtrlSPARCDiagsPowerOnLevel,
        ilomCtrlSPARCDiagsUserResetLevel,
        ilomCtrlSPARCDiagsErrorResetLevel,
        ilomCtrlSPARCDiagsPowerOnVerbosity,
        ilomCtrlSPARCDiagsUserResetVerbosity,
        ilomCtrlSPARCDiagsErrorResetVerbosity,
        ilomCtrlSPARCDiagsStatus,
        ilomCtrlSPARCDiagsAction,
        ilomCtrlSPARCDiagsHwChangeLevel,
        ilomCtrlSPARCDiagsHwChangeVerbosity,
        ilomCtrlSPARCHostMACAddress,
        ilomCtrlSPARCHostOBPVersion,
        ilomCtrlSPARCHostPOSTVersion,
        ilomCtrlSPARCHostAutoRunOnError,
        ilomCtrlSPARCHostPOSTStatus,
        ilomCtrlSPARCHostAutoRestartPolicy,
        ilomCtrlSPARCHostIoReconfigurePolicy,
        ilomCtrlSPARCHostOSBootStatus,
        ilomCtrlSPARCHostBootTimeout,
        ilomCtrlSPARCHostBootRestart,
        ilomCtrlSPARCHostMaxBootFail,
        ilomCtrlSPARCHostBootFailRecovery,
        ilomCtrlSPARCHostHypervisorVersion,
        ilomCtrlSPARCHostSysFwVersion,
        ilomCtrlSPARCHostGMVersion,
        ilomCtrlSPARCHostSendBreakAction,
        ilomCtrlSPARCBootModeState,
        ilomCtrlSPARCBootModeScript,
        ilomCtrlSPARCBootModeExpires,
        ilomCtrlSPARCBootModeLDOMConfig,
        ilomCtrlSPARCKeySwitchState,
        ilomCtrlSystemIdentifier,
        ilomCtrlHostName,
        ilomCtrlThdState,
        ilomCtrlThdAction,
        ilomCtrlThdModuleDesc,
        ilomCtrlThdModuleState,
        ilomCtrlThdModuleAction,
        ilomCtrlThdInstanceState,
        ilomCtrlThdInstanceAction,
        ilomCtrlBackupAndRestoreTargetURI,
        ilomCtrlBackupAndRestorePassphrase,
        ilomCtrlBackupAndRestoreAction,
        ilomCtrlBackupAndRestoreActionStatus,
        ilomCtrlDNSNameServers,
        ilomCtrlDNSSearchPath,
        ilomCtrlDNSdhcpAutoDns,
        ilomCtrlDNSTimeout,
        ilomCtrlDNSRetries
    }
    STATUS current
    DESCRIPTION
        "The group of current objects."
    ::= { ilomCtrlGroups 2 }

ilomCtrlDeprecatedObjectsGroup OBJECT-GROUP
    OBJECTS {
        ilomCtrlLdapDefaultRole,
        ilomCtrlRadiusDefaultRole,
        ilomCtrlLocalUserAuthPassword,
        ilomCtrlLocalUserAuthRole,
        ilomCtrlLocalUserAuthRowStatus,
        ilomCtrlLocalUserAuthCLIMode,
        ilomCtrlSPARCDiagsLevel,
        ilomCtrlSPARCDiagsVerbosity,
        ilomCtrlActiveDirectoryDefaultRole
    }
    STATUS deprecated
    DESCRIPTION
        "The objects that have been deprecated."
    ::= { ilomCtrlGroups 1 }

END
