------------------------------------------------------------------------------
--
--  File         : maipuGtsMIB.mib
--  Description  : Maipu Generic Traffic Shaping MIB file.
--  Version      : 1.00
--  Date         : December 26, 2009
-- 	Copyright    : 2009 by Maipu Communication Technology Co., LTD.
--					All rights reserved.
--
-- $Id:
--
------------------------------------------------------------------------------

------------------------------------------------------------------------------
MAIPU-GTS-MIB DEFINITIONS ::= BEGIN


IMPORTS
        MODULE-IDENTITY, OBJECT-TYPE, NOTIFICATION-TYPE, enterprises, Counter32, Gauge32,
          Integer32, Unsigned32, TimeTicks,IpAddress,Counter64
            FROM SNMPv2-SMI
        TEXTUAL-CONVENTION, TruthValue, MacAddress,
          RowStatus, DisplayString, DateAndTime
            FROM SNMPv2-TC
        MODULE-COMPLIANCE, OBJECT-GROUP
            FROM SNMPv2-CONF
        mpMgmt
            FROM MAIPU-SMI;


maipu               	OBJECT IDENTIFIER ::= { enterprises 5651 }
mpMgmt2             	OBJECT IDENTIFIER ::= { maipu 6 }
mpRouterTech        	OBJECT IDENTIFIER ::= { mpMgmt2 2 }
mpRtQoSv2           	OBJECT IDENTIFIER ::= { mpRouterTech 3 }


maipuGtsMIB         	MODULE-IDENTITY
                    		LAST-UPDATED 	"0912291622Z"
                    		ORGANIZATION 	"Maipu Communication Technology Co., LTD."
                    		CONTACT-INFO
                    			""
                    		DESCRIPTION
                      			"Maipu Generic Traffic Shaping MIB"
                    		::= { mpRtQoSv2  5 }

-- Textual Conventions
Unsigned64 ::= TEXTUAL-CONVENTION
    STATUS          current
    DESCRIPTION
        "An unsigned 64 bit integer. We use SYNTAX Counter64 for the encoding rules, such as rate
        in bps."
    SYNTAX          Counter64

------------------------------------------------------------------------------
maipuGtsMIBObjects  	OBJECT IDENTIFIER ::= { maipuGtsMIB 1 }


------------------------------------------------------------------------------
mpGtsConfigs        	OBJECT IDENTIFIER ::= { maipuGtsMIBObjects 1 }

mpGtsInterfaceCfgTable	OBJECT-TYPE
                    		SYNTAX  SEQUENCE OF  MpGtsInterfaceCfgEntry
                    		MAX-ACCESS  not-accessible
                    		STATUS  current
                    		DESCRIPTION
                    			"A table of traffic shaping configuration entries for main and
                    			sub interface. Traffic Shaping is a method of traffic control.
                    			It allows a set of traffic shapings to be configured and applied
                    			to packets flowing out of an interface to shape network traffic."
                    		::= { mpGtsConfigs 1 }

mpGtsInterfaceCfgEntry	OBJECT-TYPE
                    		SYNTAX  MpGtsInterfaceCfgEntry
                    		MAX-ACCESS  not-accessible
                    		STATUS  current
                    		DESCRIPTION
                    			"A collection of traffic-shape configuration objects on this
                    			interface. Entries in the mpGtsInterfaceCfgTable is created and
                    			deleted via the traffic-shape command line interface."
                    		INDEX  { ifIndex,   mpGtsIFCfgRowIndex }
                    		::= { mpGtsInterfaceCfgTable 1 }

MpGtsInterfaceCfgEntry	::= SEQUENCE {
                    			mpGtsIFCfgRowIndex   Integer32,
                    			mpGtsIFCfgType   INTEGER,
                    			mpGtsIFCfgAclName   DisplayString,
                    			mpGtsIFCfgRate64   Unsigned64,
                    			mpGtsIFCfgBurstSize   Unsigned32,
                    			mpGtsIFCfgExtBurstSize   Unsigned32,
                    			mpGtsIFCfgQueueLimit   Unsigned32
                    	             }


mpGtsIFCfgRowIndex	OBJECT-TYPE
                    		SYNTAX  Integer32(1..2147483647)
                    		MAX-ACCESS  not-accessible
                    		STATUS  current
                    		DESCRIPTION
                    			"An arbitrary index for traffic shaping objects. It will increase
                    			as the list is traversed, but may skip."
                    		::= { mpGtsInterfaceCfgEntry 1 }

mpGtsIFCfgType	OBJECT-TYPE
                    		SYNTAX  INTEGER {
                    			          all(1),
                    			          accessList(2)
                    			        }
                    		MAX-ACCESS  read-only
                    		STATUS  current
                    		DESCRIPTION
                    			"The type of traffic shaping."
                    		::= { mpGtsInterfaceCfgEntry 2 }

mpGtsIFCfgAclName	OBJECT-TYPE
                    		SYNTAX  DisplayString(SIZE(0..255))
                    		MAX-ACCESS  read-only
                    		STATUS  current
                    		DESCRIPTION
                    			"Access list name. This field only makes sense when mpGtsIFCfgType
                    			is accessList(2)."
                    		::= { mpGtsInterfaceCfgEntry 3 }

mpGtsIFCfgRate64	OBJECT-TYPE
                    		SYNTAX  Unsigned64
                    		UNITS  "bits/second"
                    		MAX-ACCESS  read-only
                    		STATUS  current
                    		DESCRIPTION
                    			"The comitted traffic-shaping rate, in bits/second.  This is the
                    			sustained rate permitted by the traffic shaping."
                    		::= { mpGtsInterfaceCfgEntry 4 }

mpGtsIFCfgBurstSize	OBJECT-TYPE
                    		SYNTAX  Unsigned32
                    		UNITS  "bits"
                    		MAX-ACCESS  read-only
                    		STATUS  current
                    		DESCRIPTION
                    			"The amount of traffic, in bits, in excess of the committed rate
                    			that will be instantaneously permitted by traffic-shaping feature."
                    		::= { mpGtsInterfaceCfgEntry 5 }

mpGtsIFCfgExtBurstSize	OBJECT-TYPE
                    		SYNTAX  Unsigned32
                    		UNITS  "bits"
                    		MAX-ACCESS  read-only
                    		STATUS  current
                    		DESCRIPTION
                    			"The amount of traffic, in bits, in excess of the burst limit,
                    			which may be conditionally permitted by traffic-shaping feature."
                    		::= { mpGtsInterfaceCfgEntry 6 }

mpGtsIFCfgQueueLimit	OBJECT-TYPE
                    		SYNTAX  Unsigned32
                    		UNITS  "packets"
                    		MAX-ACCESS  read-only
                    		STATUS  current
                    		DESCRIPTION
                    			"Maximum allowed queue size for the queue."
                    		::= { mpGtsInterfaceCfgEntry 7 }


------------------------------------------------------------------------------
mpGtsFrameRelayVCCfgTable	OBJECT-TYPE
                    		SYNTAX  SEQUENCE OF  MpGtsFrameRelayVCCfgEntry
                    		MAX-ACCESS  not-accessible
                    		STATUS  current
                    		DESCRIPTION
                    			"A table of traffic shaping configuration entries for Frame Relay
                    			VC. Traffic Shaping is a method of traffic control.  It allows a
                    			set of traffic shapings to be configured and applied to packets
                    			flowing out of an interface to shape network traffic."
                    		::= { mpGtsConfigs 2 }

mpGtsFrameRelayVCCfgEntry	OBJECT-TYPE
                    		SYNTAX  MpGtsFrameRelayVCCfgEntry
                    		MAX-ACCESS  not-accessible
                    		STATUS  current
                    		DESCRIPTION
                    			"A collection of traffic-shape configuration objects on this Frame
                    			Relay VC. Entries in the mpGtsFrameRelayVCCfgTable is created and
                    			deleted via the traffic-shape command line interface."
                    		INDEX  { ifIndex,   mpGtsFRCfgDLCI,   mpGtsFRCfgRowIndex }
                    		::= { mpGtsFrameRelayVCCfgTable 1 }

MpGtsFrameRelayVCCfgEntry	::= SEQUENCE {
                    			mpGtsFRCfgDLCI         Unsigned32,
                    			mpGtsFRCfgRowIndex     Integer32,
                    			mpGtsFRCfgType         INTEGER,
                    			mpGtsFRCfgAclName      DisplayString,
                    			mpGtsFRCfgRate64       Unsigned64,
                    			mpGtsFRCfgBurstSize    Unsigned32,
                    			mpGtsFRCfgExtBurstSize   Unsigned32,
                    			mpGtsFRCfgQueueLimit   Unsigned32
                    	             }


mpGtsFRCfgDLCI      	OBJECT-TYPE
                    		SYNTAX  Unsigned32(0..1007)
                    		MAX-ACCESS  not-accessible
                    		STATUS  current
                    		DESCRIPTION
                    			"DLCI for the FRVC to which the Traffic Shaping objectis attached."
                    		::= { mpGtsFrameRelayVCCfgEntry 1 }


mpGtsFRCfgRowIndex  	OBJECT-TYPE
                    		SYNTAX  Integer32(1..2147483647)
                    		MAX-ACCESS  not-accessible
                    		STATUS  current
                    		DESCRIPTION
                    			"An arbitrary index for traffic shaping objects. It will increase
                    			as the list is traversed, but may skip."
                    		::= { mpGtsFrameRelayVCCfgEntry 2 }

mpGtsFRCfgType      	OBJECT-TYPE
                    		SYNTAX  INTEGER {
                    			          all(1),
                    			          accessList(2)
                    			        }
                    		MAX-ACCESS  read-only
                    		STATUS  current
                    		DESCRIPTION
                    			"The type of traffic shaping."
                    		::= { mpGtsFrameRelayVCCfgEntry 3 }

mpGtsFRCfgAclName   	OBJECT-TYPE
                    		SYNTAX  DisplayString(SIZE(0..255))
                    		MAX-ACCESS  read-only
                    		STATUS  current
                    		DESCRIPTION
                    			"Access list name. This field only makes sense when
                    			mpGtsFRCfgType is accessList(2)."
                    		::= { mpGtsFrameRelayVCCfgEntry 4 }

mpGtsFRCfgRate64      	OBJECT-TYPE
                    		SYNTAX  Unsigned64
                    		UNITS  "bits/second"
                    		MAX-ACCESS  read-only
                    		STATUS  current
                    		DESCRIPTION
                    			"The comitted traffic-shaping rate, in bits/second.  This is the
                    			sustained rate permitted by the traffic shaping."
                    		::= { mpGtsFrameRelayVCCfgEntry 5 }

mpGtsFRCfgBurstSize 	OBJECT-TYPE
                    		SYNTAX  Unsigned32
                    		UNITS  "bits"
                    		MAX-ACCESS  read-only
                    		STATUS  current
                    		DESCRIPTION
                    			"The amount of traffic, in bits, in excess of the committed rate
                    			that will be instantaneously permitted by traffic-shaping feature."
                    		::= { mpGtsFrameRelayVCCfgEntry 6 }

mpGtsFRCfgExtBurstSize	OBJECT-TYPE
                    		SYNTAX  Unsigned32
                    		UNITS  "bits"
                    		MAX-ACCESS  read-only
                    		STATUS  current
                    		DESCRIPTION
                    			"The amount of traffic, in bits, in excess of the burst limit,
                    			which may be conditionally permitted by traffic-shaping feature."
                    		::= { mpGtsFrameRelayVCCfgEntry 7 }

mpGtsFRCfgQueueLimit	OBJECT-TYPE
                    		SYNTAX  Unsigned32
                    		UNITS  "packets"
                    		MAX-ACCESS  read-only
                    		STATUS  current
                    		DESCRIPTION
                    			"Maximum allowed queue size for the queue."
                    		::= { mpGtsFrameRelayVCCfgEntry 8 }


------------------------------------------------------------------------------
mpGtsATMPVCCfgTable 	OBJECT-TYPE
                    		SYNTAX  SEQUENCE OF  MpGtsATMPVCCfgEntry
                    		MAX-ACCESS  not-accessible
                    		STATUS  current
                    		DESCRIPTION
                    			"A table of traffic shaping configuration entries for ATM PVC.
                    			Rate Limit is a method of traffic control.  It allows a set of
                    			traffic shapings to be configured and applied to packets flowing out
                    			of an interface to shape network traffic."
                    		::= { mpGtsConfigs 3 }

mpGtsATMPVCCfgEntry 	OBJECT-TYPE
                    		SYNTAX  MpGtsATMPVCCfgEntry
                    		MAX-ACCESS  not-accessible
                    		STATUS  current
                    		DESCRIPTION
                    			"A collection of traffic-shape configuration objects on this ATM
                    			PVC. Entries in the mpGtsATMPVCCfgTable is created and deleted
                    			via the traffic-shape command line interface."
                    		INDEX  { ifIndex,   mpGtsATMCfgVPI,   mpGtsATMCfgVCI,   mpGtsATMCfgRowIndex }
                    		::= { mpGtsATMPVCCfgTable 1 }

MpGtsATMPVCCfgEntry 	::= SEQUENCE {
                    			mpGtsATMCfgVPI         Unsigned32,
                    			mpGtsATMCfgVCI         Unsigned32,
                    			mpGtsATMCfgRowIndex    Integer32,
                    			mpGtsATMCfgType        INTEGER,
                    			mpGtsATMCfgAclName     DisplayString,
                    			mpGtsATMCfgRate64      Unsigned64,
                    			mpGtsATMCfgBurstSize   Unsigned32,
                    			mpGtsATMCfgExtBurstSize   Unsigned32,
                    			mpGtsATMCfgQueueLimit   Unsigned32
                    	             }


mpGtsATMCfgVPI      	OBJECT-TYPE
                    		SYNTAX  Unsigned32(0..4095)
                    		MAX-ACCESS  not-accessible
                    		STATUS  current
                    		DESCRIPTION
                    			"VPI for the ATMVC to which the Traffic Shaping objectis attached."
                    		::= { mpGtsATMPVCCfgEntry 1 }

mpGtsATMCfgVCI      	OBJECT-TYPE
                    		SYNTAX  Unsigned32(0..65535)
                    		MAX-ACCESS  not-accessible
                    		STATUS  current
                    		DESCRIPTION
                    			"VCI for the ATMVC to which the Traffic Shaping objectis attached."
                    		::= { mpGtsATMPVCCfgEntry 2 }


mpGtsATMCfgRowIndex 	OBJECT-TYPE
                    		SYNTAX  Integer32(1..2147483647)
                    		MAX-ACCESS  not-accessible
                    		STATUS  current
                    		DESCRIPTION
                    			"An arbitrary index for traffic shaping objects. It will increase
                    			as the list is traversed, but may skip."
                    		::= { mpGtsATMPVCCfgEntry 3 }

mpGtsATMCfgType     	OBJECT-TYPE
                    		SYNTAX  INTEGER {
                    			          all(1),
                    			          accessList(2)
                    			        }
                    		MAX-ACCESS  read-only
                    		STATUS  current
                    		DESCRIPTION
                    			"The type of traffic shaping."
                    		::= { mpGtsATMPVCCfgEntry 4 }

mpGtsATMCfgAclName  	OBJECT-TYPE
                    		SYNTAX  DisplayString(SIZE(0..255))
                    		MAX-ACCESS  read-only
                    		STATUS  current
                    		DESCRIPTION
                    			"Access list name.This field only makes sense when
                    			mpGtsATMCfgType is accessList(2)."
                    		::= { mpGtsATMPVCCfgEntry 5 }

mpGtsATMCfgRate64     	OBJECT-TYPE
                    		SYNTAX  Unsigned64
                    		UNITS	"bits/second"
                    		MAX-ACCESS  read-only
                    		STATUS  current
                    		DESCRIPTION
                    			"The comitted traffic-shaping rate, in bits/second.  This is the
                    			sustained rate permitted by the traffic shaping."
                    		::= { mpGtsATMPVCCfgEntry 6 }

mpGtsATMCfgBurstSize	OBJECT-TYPE
                    		SYNTAX  Unsigned32
                    		UNITS  "bits"
                    		MAX-ACCESS  read-only
                    		STATUS  current
                    		DESCRIPTION
                    			"The amount of traffic, in bits, in excess of the committed rate
                    			that will be instantaneously permitted by traffic-shaping feature."
                    		::= { mpGtsATMPVCCfgEntry 7 }

mpGtsATMCfgExtBurstSize	OBJECT-TYPE
                    		SYNTAX  Unsigned32
                    		UNITS  "bits"
                    		MAX-ACCESS  read-only
                    		STATUS  current
                    		DESCRIPTION
                    			"The amount of traffic, in bits, in excess of the burst limit,
                    			which may be conditionally permitted by traffic-shaping feature."
                    		::= { mpGtsATMPVCCfgEntry 8 }

mpGtsATMCfgQueueLimit	OBJECT-TYPE
                    		SYNTAX  Unsigned32
                    		UNITS  "packets"
                    		MAX-ACCESS  read-only
                    		STATUS  current
                    		DESCRIPTION
                    			"Maximum allowed queue size for the queue."
                    		::= { mpGtsATMPVCCfgEntry 9 }



------------------------------------------------------------------------------
mpGtsStats          	OBJECT IDENTIFIER ::= { maipuGtsMIBObjects 2 }

mpGtsInterfaceStatTable	OBJECT-TYPE
                    		SYNTAX  SEQUENCE OF  MpGtsInterfaceStatEntry
                    		MAX-ACCESS  not-accessible
                    		STATUS  current
                    		DESCRIPTION
                    			"A table of traffic shaping statistics entries."
                    		::= { mpGtsStats 1 }

mpGtsInterfaceStatEntry	OBJECT-TYPE
                    		SYNTAX  MpGtsInterfaceStatEntry
                    		MAX-ACCESS  not-accessible
                    		STATUS  current
                    		DESCRIPTION
                    			"A collection of traffic-shape statistical objects on this interface.
                    			Entries are created and deleted via the traffic-shape command line
                    			interface."
                    		INDEX  { ifIndex,  mpGtsIFCfgRowIndex }
                    		::= { mpGtsInterfaceStatTable 1 }

MpGtsInterfaceStatEntry	::= SEQUENCE {
                    			mpGtsIFStatSentByte64   Counter64,
                    			mpGtsIFStatSentPkt64   Counter64,
                    			mpGtsIFStatDelayedByte64   Counter64,
                    			mpGtsIFStatDelayedPkt64   Counter64,
								mpGtsIFStatDropByte64   Counter64,
                    			mpGtsIFStatDropPkt64   Counter64,
                    			mpGtsIFStatActive   TruthValue,
                    			mpGtsIFStatCurrentQSize   Gauge32
                    	             }


mpGtsIFStatSentByte64	OBJECT-TYPE
                    		SYNTAX  Counter64
                    		UNITS  "Octets"
                    		MAX-ACCESS  read-only
                    		STATUS  current
                    		DESCRIPTION
                    			"This object represents the 64 bits counter of octets that have
                    			been sent."
                    		::= { mpGtsInterfaceStatEntry 1 }

mpGtsIFStatSentPkt64	OBJECT-TYPE
                    		SYNTAX  Counter64
                    		UNITS  "Packets"
                    		MAX-ACCESS  read-only
                    		STATUS  current
                    		DESCRIPTION
                    			"This object represents the 64 bits counter of packets that have
                    			been sent."
                    		::= { mpGtsInterfaceStatEntry 2 }

mpGtsIFStatDelayedByte64	OBJECT-TYPE
                    		SYNTAX  Counter64
                    		UNITS  "Octets"
                    		MAX-ACCESS  read-only
                    		STATUS  current
                    		DESCRIPTION
                    			"This object represents the 64 bits counter of octets that have
                    			been delayed."
                    		::= { mpGtsInterfaceStatEntry 3 }

mpGtsIFStatDelayedPkt64	OBJECT-TYPE
                    		SYNTAX  Counter64
                    		UNITS  "Packets"
                    		MAX-ACCESS  read-only
                    		STATUS  current
                    		DESCRIPTION
                    			"This object represents the 64 bits counter of packets that have
                    			been delayed."
                    		::= { mpGtsInterfaceStatEntry 4 }

mpGtsIFStatDropByte64	OBJECT-TYPE
                    		SYNTAX  Counter64
                    		UNITS  "Octets"
                    		MAX-ACCESS  read-only
                    		STATUS  current
                    		DESCRIPTION
                    			"This object represents the 64 bits counter of octets that have
                    			been dropped during shaping."
                    		::= { mpGtsInterfaceStatEntry 5 }

mpGtsIFStatDropPkt64	OBJECT-TYPE
                    		SYNTAX  Counter64
                    		UNITS  "Packets"
                    		MAX-ACCESS  read-only
                    		STATUS  current
                    		DESCRIPTION
                    			"This object represents the 64 bits counter of packets that have
                    			been dropped during shaping."
                    		::= { mpGtsInterfaceStatEntry 6 }

mpGtsIFStatActive	OBJECT-TYPE
                    		SYNTAX  TruthValue
                    		MAX-ACCESS  read-only
                    		STATUS  current
                    		DESCRIPTION
                    			"This object indicates the current traffic-shaping state. When
                    			traffic-shaping is enabled and the traffic rate exceeds the shape
                    			rate, traffic-shaping is considered to be active.  Otherwise, it
                    			is considered inactive."
                    		::= { mpGtsInterfaceStatEntry 7 }

mpGtsIFStatCurrentQSize	OBJECT-TYPE
                    		SYNTAX  Gauge32
                    		UNITS  "Packets"
                    		MAX-ACCESS  read-only
                    		STATUS  current
                    		DESCRIPTION
                    			"This object indicates the current traffic-shaping queue depth in
                    			packets."
                    		::= { mpGtsInterfaceStatEntry 8 }



------------------------------------------------------------------------------
mpGtsFrameRelayVCStatTable	OBJECT-TYPE
                    		SYNTAX  SEQUENCE OF  MpGtsFrameRelayVCStatEntry
                    		MAX-ACCESS  not-accessible
                    		STATUS  current
                    		DESCRIPTION
                    			"A table of traffic shaping statistics entries for Frame Relay VC."
                    		::= { mpGtsStats 2 }

mpGtsFrameRelayVCStatEntry	OBJECT-TYPE
                    		SYNTAX  MpGtsFrameRelayVCStatEntry
                    		MAX-ACCESS  not-accessible
                    		STATUS  current
                    		DESCRIPTION
                    			"A collection of traffic-shape statistical objects on this Frame Relay
                    			VC. Entries are created and deleted via the traffic-shape command
                    			line interface."
                    		INDEX  { ifIndex,   mpGtsFRCfgDLCI,   mpGtsFRCfgRowIndex }
                    		::= { mpGtsFrameRelayVCStatTable 1 }

MpGtsFrameRelayVCStatEntry	::= SEQUENCE {
                    			mpGtsFRStatSentByte64   Counter64,
                    			mpGtsFRStatSentPkt64   Counter64,
                    			mpGtsFRStatDelayedByte64   Counter64,
                    			mpGtsFRStatDelayedPkt64   Counter64,
								mpGtsFRStatDropByte64   Counter64,
                    			mpGtsFRStatDropPkt64   Counter64,
                    			mpGtsFRStatActive   TruthValue,
                    			mpGtsFRStatCurrentQSize   Gauge32
                    	             }


mpGtsFRStatSentByte64	OBJECT-TYPE
                    		SYNTAX  Counter64
                    		UNITS  "Octets"
                    		MAX-ACCESS  read-only
                    		STATUS  current
                    		DESCRIPTION
                    			"This object represents the 64 bits counter of octets that have
                    			been sent."
                    		::= { mpGtsFrameRelayVCStatEntry 1 }

mpGtsFRStatSentPkt64	OBJECT-TYPE
                    		SYNTAX  Counter64
                    		UNITS  "Packets"
                    		MAX-ACCESS  read-only
                    		STATUS  current
                    		DESCRIPTION
                    			"This object represents the 64 bits counter of packets that have
                    			been sent."
                    		::= { mpGtsFrameRelayVCStatEntry 2 }

mpGtsFRStatDelayedByte64	OBJECT-TYPE
                    		SYNTAX  Counter64
                    		UNITS  "Octets"
                    		MAX-ACCESS  read-only
                    		STATUS  current
                    		DESCRIPTION
                    			"This object represents the 64 bits counter of octets that have
                    			been delayed."
                    		::= { mpGtsFrameRelayVCStatEntry 3 }

mpGtsFRStatDelayedPkt64	OBJECT-TYPE
                    		SYNTAX  Counter64
                    		UNITS  "Packets"
                    		MAX-ACCESS  read-only
                    		STATUS  current
                    		DESCRIPTION
                    			"This object represents the 64 bits counter of packets that have
                    			been delayed."
                    		::= { mpGtsFrameRelayVCStatEntry 4 }

mpGtsFRStatDropByte64	OBJECT-TYPE
                    		SYNTAX  Counter64
                    		UNITS  "Octets"
                    		MAX-ACCESS  read-only
                    		STATUS  current
                    		DESCRIPTION
                    			"This object represents the 64 bits counter of octets that have
                    			been dropped during shaping."
                    		::= { mpGtsFrameRelayVCStatEntry 5 }

mpGtsFRStatDropPkt64	OBJECT-TYPE
                    		SYNTAX  Counter64
                    		UNITS  "Packets"
                    		MAX-ACCESS  read-only
                    		STATUS  current
                    		DESCRIPTION
                    			"This object represents the 64 bits counter of packets that have
                    			been dropped during shaping."
                    		::= { mpGtsFrameRelayVCStatEntry 6 }

mpGtsFRStatActive	OBJECT-TYPE
                    		SYNTAX  TruthValue
                    		MAX-ACCESS  read-only
                    		STATUS  current
                    		DESCRIPTION
                    			"This object indicates the current traffic-shaping state. When
                    			traffic-shaping is enabled and the traffic rate exceeds the shape
                    			rate, traffic-shaping is considered to be active.  Otherwise, it
                    			is considered inactive."
                    		::= { mpGtsFrameRelayVCStatEntry 7 }

mpGtsFRStatCurrentQSize	OBJECT-TYPE
                    		SYNTAX  Gauge32
                    		UNITS  "Packets"
                    		MAX-ACCESS  read-only
                    		STATUS  current
                    		DESCRIPTION
                    			"This object indicates the current traffic-shaping queue depth in
                    			packets."
                    		::= { mpGtsFrameRelayVCStatEntry 8 }


------------------------------------------------------------------------------
mpGtsATMPVCStatTable	OBJECT-TYPE
                    		SYNTAX  SEQUENCE OF  MpGtsATMPVCStatEntry
                    		MAX-ACCESS  not-accessible
                    		STATUS  current
                    		DESCRIPTION
                    			"A table of traffic shaping statistics entries for ATM PVC."
                    		::= { mpGtsStats 3 }

mpGtsATMPVCStatEntry	OBJECT-TYPE
                    		SYNTAX  MpGtsATMPVCStatEntry
                    		MAX-ACCESS  not-accessible
                    		STATUS  current
                    		DESCRIPTION
                    			"A collection of traffic-shape statistical objects on this ATM PVC.
                    			Entries are created and deleted via the traffic-shape command line
                    			interface."
                    		INDEX  { ifIndex,   mpGtsATMCfgVPI,   mpGtsATMCfgVCI,   mpGtsATMCfgRowIndex }
                    		::= { mpGtsATMPVCStatTable 1 }

MpGtsATMPVCStatEntry	::= SEQUENCE {
                    			mpGtsATMStatSentByte64   Counter64,
                    			mpGtsATMStatSentPkt64   Counter64,
                    			mpGtsATMStatDelayedByte64   Counter64,
                    			mpGtsATMStatDelayedPkt64   Counter64,
								mpGtsATMStatDropByte64   Counter64,
                    			mpGtsATMStatDropPkt64   Counter64,
                    			mpGtsATMStatActive   TruthValue,
                    			mpGtsATMStatCurrentQSize   Gauge32
                    	             }


mpGtsATMStatSentByte64	OBJECT-TYPE
                    		SYNTAX  Counter64
                    		UNITS  "Octets"
                    		MAX-ACCESS  read-only
                    		STATUS  current
                    		DESCRIPTION
                    			"This object represents the 64 bits counter of octets that have
                    			been sent."
                    		::= { mpGtsATMPVCStatEntry 1 }

mpGtsATMStatSentPkt64	OBJECT-TYPE
                    		SYNTAX  Counter64
                    		UNITS  "Packets"
                    		MAX-ACCESS  read-only
                    		STATUS  current
                    		DESCRIPTION
                    			"This object represents the 64 bits counter of packets that have
                    			been sent."
                    		::= { mpGtsATMPVCStatEntry 2 }

mpGtsATMStatDelayedByte64	OBJECT-TYPE
                    		SYNTAX  Counter64
                    		UNITS  "Octets"
                    		MAX-ACCESS  read-only
                    		STATUS  current
                    		DESCRIPTION
                    			"This object represents the 64 bits counter of octets that have
                    			been delayed."
                    		::= { mpGtsATMPVCStatEntry 3 }

mpGtsATMStatDelayedPkt64	OBJECT-TYPE
                    		SYNTAX  Counter64
                    		UNITS  "Packets"
                    		MAX-ACCESS  read-only
                    		STATUS  current
                    		DESCRIPTION
                    			"This object represents the 64 bits counter of packets that have
                    			been delayed."
                    		::= { mpGtsATMPVCStatEntry 4 }

mpGtsATMStatDropByte64	OBJECT-TYPE
                    		SYNTAX  Counter64
                    		UNITS  "Octets"
                    		MAX-ACCESS  read-only
                    		STATUS  current
                    		DESCRIPTION
                    			"This object represents the 64 bits counter of octets that have
                    			been dropped during shaping."
                    		::= { mpGtsATMPVCStatEntry 5 }

mpGtsATMStatDropPkt64	OBJECT-TYPE
                    		SYNTAX  Counter64
                    		UNITS  "Packets"
                    		MAX-ACCESS  read-only
                    		STATUS  current
                    		DESCRIPTION
                    			"This object represents the 64 bits counter of packets that have
                    			been dropped during shaping."
                    		::= { mpGtsATMPVCStatEntry 6 }

mpGtsATMStatActive	OBJECT-TYPE
                    		SYNTAX  TruthValue
                    		MAX-ACCESS  read-only
                    		STATUS  current
                    		DESCRIPTION
                    			"This object indicates the current traffic-shaping state. When
                    			traffic-shaping is enabled and the traffic rate exceeds the shape
                    			rate, traffic-shaping is considered to be active.  Otherwise, it
                    			is considered inactive."
                    		::= { mpGtsATMPVCStatEntry 7 }

mpGtsATMStatCurrentQSize	OBJECT-TYPE
                    		SYNTAX  Gauge32
                    		UNITS  "Packets"
                    		MAX-ACCESS  read-only
                    		STATUS  current
                    		DESCRIPTION
                    			"This object indicates the current traffic-shaping queue depth in
                    			packets."
                    		::= { mpGtsATMPVCStatEntry 8 }


END
------------------------------------------------------------------------------
-- ============================================================================
-- $Log: maipuGtsMIB.mib,v $
--
--
-- ============================================================================
