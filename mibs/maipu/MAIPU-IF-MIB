-- *****************************************************************
-- MAIPU-INTERFACE.mib:  Maipu enterprise device interface MIB file
--
-- Copyright (c)  by Maipu DataComm Inc.
-- All rights reserved.
--
-- *****************************************************************
--

MAIPU-IF-MIB DEFINITIONS ::= BEGIN

IMPORTS
    DisplayString  , RowStatus			FROM SNMPv2-TC
    MODULE-IDENTITY, OBJECT-TYPE, Unsigned32,
    IpAddress, NOTIFICATION-TYPE        FROM SNMPv2-SMI
    snmpTraps                           FROM SNMPv2-MIB
    ifIndex, ifDescr, ifType			FROM RFC1213-MIB
    mpMgmt                              FROM MAIPU-SMI;

mpIfMib MODULE-IDENTITY
    LAST-UPDATED "0102090000Z"
    ORGANIZATION "Maipu DataComm"
    CONTACT-INFO
	"   Maipu DataComm
		Customer Service

		Postal: Consulate Drive
			Chengdu, Sichuan  610041
			China  "

    DESCRIPTION
		"The assignments for Maipu router's MIB of inteface infomation!"
    ::= {mpMgmt 2 }

ethConfTable OBJECT-TYPE
    SYNTAX SEQUENCE OF EthConfEntry
    MAX-ACCESS not-accessible
    STATUS current
    DESCRIPTION
		"以太网口的配置表."
    ::= { mpIfMib 1 }

ethConfEntry OBJECT-TYPE
    SYNTAX EthConfEntry
    MAX-ACCESS not-accessible
    STATUS current
    DESCRIPTION
		"以太网口配置表条目."
    INDEX { ethConfIfIndex }
    ::= { ethConfTable 1 }

EthConfEntry ::=
    SEQUENCE {
		ethConfIfIndex
				INTEGER,
		ethMtu
				INTEGER,
		ethDescription
				DisplayString,
		ethUcastAddr
				IpAddress,
		ethUcastMask
				IpAddress,
		ethUcastUnnumber
				INTEGER,
		ethBcastAddr
				IpAddress,
		ethMetric
				INTEGER,
		ethDuplex
				INTEGER,
		ethRate
				INTEGER
			}

ethConfIfIndex OBJECT-TYPE
	SYNTAX	INTEGER
	MAX-ACCESS	read-only
	STATUS	current
	DESCRIPTION
		"以太网口配置表索引,应与ifIndex相同."
	::= { ethConfEntry 1 }

ethMtu	OBJECT-TYPE
	SYNTAX	INTEGER (64..18000)
	MAX-ACCESS	read-write
	STATUS	current
	DESCRIPTION
		"以太网口上最大传输单元."
	DEFVAL { 1500 }
	::= { ethConfEntry 2 }

ethDescription	OBJECT-TYPE
	SYNTAX	DisplayString
	MAX-ACCESS	read-write
	STATUS	current
	DESCRIPTION
		"以太网口上的功能描述."
	::= { ethConfEntry 3 }

ethUcastAddr	OBJECT-TYPE
	SYNTAX	IpAddress
	MAX-ACCESS	read-write
	STATUS	current
	DESCRIPTION
		"以太网口IP地址."
	::= { ethConfEntry 4 }

ethUcastMask	OBJECT-TYPE
	SYNTAX	IpAddress
	MAX-ACCESS	read-write
	STATUS	current
	DESCRIPTION
		"以太网口IP地址掩码."
	::= { ethConfEntry 5 }

ethUcastUnnumber	OBJECT-TYPE
	SYNTAX	INTEGER
	MAX-ACCESS	read-write
	STATUS	current
	DESCRIPTION
		"使某一有效接口上的IP无编号处理有效.0表示不使用无编号,
		 正整数表示与ifIndex相应的接口."
	::= { ethConfEntry 6 }

ethBcastAddr	OBJECT-TYPE
	SYNTAX	IpAddress
	MAX-ACCESS	read-write
	STATUS	current
	DESCRIPTION
		"以太网口广播地址."
	::= { ethConfEntry 7 }

ethMetric	OBJECT-TYPE
	SYNTAX	INTEGER (0..255)
	MAX-ACCESS	read-write
	STATUS	current
	DESCRIPTION
		"网络以太网口管理尺度."
	DEFVAL { 0 }
	::= { ethConfEntry 8 }

ethDuplex	OBJECT-TYPE
	SYNTAX	INTEGER {
				half(1),
				full(2),
				auto(3)
					}
	MAX-ACCESS	read-write
	STATUS	current
	DESCRIPTION
		"以太网口的工作模式."
	::= { ethConfEntry 9 }

ethRate	OBJECT-TYPE
	SYNTAX	INTEGER
	MAX-ACCESS	read-write
	STATUS	current
	DESCRIPTION
		"以太网口的速率.可取值10或100,当取值为0时,指自动配置."
	::= { ethConfEntry 10 }

-- *****************************
secondaryTable	OBJECT-TYPE
	SYNTAX	SEQUENCE OF SecondaryEntry
	MAX-ACCESS	not-accessible
	STATUS	current
	DESCRIPTION
		"辅助地址表."
	::= { mpIfMib 2 }

secondaryEntry	OBJECT-TYPE
	SYNTAX	SecondaryEntry
	MAX-ACCESS	not-accessible
	STATUS	current
	DESCRIPTION
		"辅助地址表条目."
	INDEX { secondaryIfIndex, secondaryIp }
	::= { secondaryTable 1 }

SecondaryEntry ::=
	SEQUENCE {
		secondaryIfIndex
			INTEGER,
		secondaryIp
			IpAddress,
		secondaryMask
			IpAddress,
		secondaryStatus
			RowStatus
		}

secondaryIfIndex	OBJECT-TYPE
	SYNTAX	INTEGER
	MAX-ACCESS	read-create
	STATUS	current
	DESCRIPTION
		"指示这一个辅助地址是在哪个接口上的,只有以太网口才有辅助地址."
	::= { secondaryEntry 1 }

secondaryIp	OBJECT-TYPE
	SYNTAX	IpAddress
	MAX-ACCESS	read-create
	STATUS	current
	DESCRIPTION
		"辅助地址Ip."
	::= { secondaryEntry 2 }

secondaryMask	OBJECT-TYPE
	SYNTAX	IpAddress
	MAX-ACCESS	read-create
	STATUS	current
	DESCRIPTION
		"辅助地址掩码."
	::= { secondaryEntry 3 }

secondaryStatus	OBJECT-TYPE
	SYNTAX	RowStatus
	MAX-ACCESS	read-create
	STATUS	current
	DESCRIPTION
		"辅助地址表的行状态,用于增加,删除或修改一行的内容."
	::= { secondaryEntry 4 }

-- *********************************
serialConfTable OBJECT-TYPE
    SYNTAX SEQUENCE OF SerialConfEntry
    MAX-ACCESS not-accessible
    STATUS current
    DESCRIPTION
		"串口的配置表."
    ::= { mpIfMib 3 }

serialConfEntry OBJECT-TYPE
    SYNTAX SerialConfEntry
    MAX-ACCESS not-accessible
    STATUS current
    DESCRIPTION
		"串口配置表条目."
    INDEX { serialConfIndex }
    ::= { serialConfTable 1 }

SerialConfEntry ::=
    SEQUENCE {
		serialConfIndex
				INTEGER,
		serialMtu
				INTEGER,
		serialDescription
				DisplayString,
		serialUcastAddr
				IpAddress,
		serialUcastMask
				IpAddress,
		serialUnnumber
				INTEGER,
		serialBcastAddr
				IpAddress,
		serialMetric
				INTEGER,
		serialClockSpeed
				INTEGER,
		serialClockLine
				INTEGER,
		serialClockInvert
				INTEGER,
		serialNrziEncode
				INTEGER,
		serialIdleMode
				INTEGER,
		serialSpeed
				INTEGER,
		serialDataBits
				INTEGER,
		serialStopBits
				INTEGER,
		serialParity
				INTEGER,
		serialFlowCtl
				INTEGER,
		serialMru
				INTEGER,
		serialStartCharacter
				INTEGER,
		serialStopCharacter
				INTEGER,
		serialEncapsulation
				INTEGER,
		serialPhyLayer
				INTEGER,
		serialIpTcpHeadCompress
				INTEGER,
		serialBackup
				INTEGER,
		serialBackupIf
				INTEGER,
		serialBackupAct
				Unsigned32,
		serialBackupDeact
				Unsigned32,
		serialQos
				INTEGER,
		serialQosList
				INTEGER,
		serialTxHigh
				INTEGER,
		serialTxMedium
				INTEGER,
		serialTxNormal
				INTEGER,
		serialTxLow
				INTEGER,
		serialTbds
				INTEGER
			}

serialConfIndex OBJECT-TYPE
	SYNTAX	INTEGER
	MAX-ACCESS	read-only
	STATUS	current
	DESCRIPTION
		"串口配置表索引,应与ifIndex相同."
	::= { serialConfEntry 1 }

serialMtu	OBJECT-TYPE
	SYNTAX	INTEGER (64..18000)
	MAX-ACCESS	read-write
	STATUS	current
	DESCRIPTION
		"串口上最大传输单元."
	DEFVAL { 1500 }
	::= { serialConfEntry 2 }

serialDescription	OBJECT-TYPE
	SYNTAX	DisplayString
	MAX-ACCESS	read-write
	STATUS	current
	DESCRIPTION
		"串口上的功能描述."
	::= { serialConfEntry 3 }

serialUcastAddr	OBJECT-TYPE
	SYNTAX	IpAddress
	MAX-ACCESS	read-write
	STATUS	current
	DESCRIPTION
		"串口IP地址."
	::= { serialConfEntry 4 }

serialUcastMask	OBJECT-TYPE
	SYNTAX	IpAddress
	MAX-ACCESS	read-write
	STATUS	current
	DESCRIPTION
		"串口IP地址掩码."
	::= { serialConfEntry 5 }

serialUnnumber	OBJECT-TYPE
	SYNTAX	INTEGER
	MAX-ACCESS	read-write
	STATUS	current
	DESCRIPTION
		"使某一有效串口上的IP无编号处理有效.0表示不使用无编号,
		 正整数表示与ifIndex相应的接口."
	::= { serialConfEntry 6 }

serialBcastAddr	OBJECT-TYPE
	SYNTAX	IpAddress
	MAX-ACCESS	read-write
	STATUS	current
	DESCRIPTION
		"串口广播地址."
	::= { serialConfEntry 7 }

serialMetric	OBJECT-TYPE
	SYNTAX	INTEGER (0..255)
	MAX-ACCESS	read-write
	STATUS	current
	DESCRIPTION
		"网络串口管理尺度."
	DEFVAL { 0 }
	::= { serialConfEntry 8 }

serialClockSpeed	OBJECT-TYPE
	SYNTAX	INTEGER
	MAX-ACCESS	read-write
	STATUS	current
	DESCRIPTION
		"同步串口时钟频率.只对应于DCE方式.当接口为V.24时,
		 最高时钟速率为200kbps,当接口为V.35时,最高时钟速率为8Mbps."
	::= { serialConfEntry 9 }

serialClockLine	OBJECT-TYPE
	SYNTAX	INTEGER {
				normal(1),
				multiplex(2)
					}
	MAX-ACCESS	read-write
	STATUS	current
	DESCRIPTION
		"同步串口时钟复用,只对应于DTE方式. 1：分别使用TxC和RxC
		 作为发送和接收时钟；2：仅用TxC作为发送和接收时钟。"
	DEFVAL { normal }
	::= { serialConfEntry 10 }

serialClockInvert	OBJECT-TYPE
	SYNTAX	INTEGER {
				restore(1),
				invert(2)
					}
	MAX-ACCESS	read-write
	STATUS	current
	DESCRIPTION
		"同步串口时钟翻转.只对应于DTE方式."
	DEFVAL { restore }
	::= { serialConfEntry 11 }

serialNrziEncode	OBJECT-TYPE
	SYNTAX	INTEGER {
				nrz(1),
				nrzi(2)
					}
	MAX-ACCESS	read-write
	STATUS	current
	DESCRIPTION
		"串口编码方式. 1：NRZ编码；2：NRZI编码。"
	DEFVAL { nrz }
	::= { serialConfEntry 12 }

serialIdleMode	OBJECT-TYPE
	SYNTAX	INTEGER {
				marks(1),
				flags(2)
					}
	MAX-ACCESS	read-write
	STATUS	current
	DESCRIPTION
		"串口上发送的空闲字符类型. 1：FF； 2：7E"
	DEFVAL { marks }
	::= { serialConfEntry 13 }

serialSpeed	OBJECT-TYPE
	SYNTAX	INTEGER
	MAX-ACCESS	read-write
	STATUS	current
	DESCRIPTION
		"异步串口传输速率."
	DEFVAL { 115200 }
	::= { serialConfEntry 14 }

serialDataBits	OBJECT-TYPE
	SYNTAX	INTEGER (5..8)
	MAX-ACCESS	read-write
	STATUS	current
	DESCRIPTION
		"异步串口数据位."
	DEFVAL { 8 }
	::= { serialConfEntry 15 }

serialStopBits	OBJECT-TYPE
	SYNTAX	INTEGER (1..2)
	MAX-ACCESS	read-write
	STATUS	current
	DESCRIPTION
		"异步串口停止位."
	DEFVAL { 1 }
	::= { serialConfEntry 16 }

serialParity	OBJECT-TYPE
	SYNTAX	INTEGER {
				none(1),
				odd(2),
				even(3),
				space(4),
				mark(5)
					}
	MAX-ACCESS	read-write
	STATUS	current
	DESCRIPTION
		"异步串口奇偶校验."
	DEFVAL { none }
	::= { serialConfEntry 17 }

serialFlowCtl	OBJECT-TYPE
	SYNTAX	INTEGER {
				none(1),
				software(2),
				hardware(3)
					}
	MAX-ACCESS	read-write
	STATUS	current
	DESCRIPTION
		"异步串口流控方式."
	DEFVAL { none }
	::= { serialConfEntry 18 }

serialMru	OBJECT-TYPE
	SYNTAX	INTEGER (128..4096)
	MAX-ACCESS	read-write
	STATUS	current
	DESCRIPTION
		"异步串口最大接收单元大小."
	DEFVAL { 1500}
	::= { serialConfEntry 19 }

serialStartCharacter	OBJECT-TYPE
	SYNTAX	INTEGER (0..255)
	MAX-ACCESS	read-write
	STATUS	current
	DESCRIPTION
		"异步串口上的起始字符."
	::= { serialConfEntry 20 }

serialStopCharacter	OBJECT-TYPE
	SYNTAX	INTEGER (0..255)
	MAX-ACCESS	read-write
	STATUS	current
	DESCRIPTION
		"异步串口上的结束字符."
	::= { serialConfEntry 21 }

serialEncapsulation	OBJECT-TYPE
	SYNTAX	INTEGER {
				slip(1),
				ppp(2),
				frame-relay(3),
				x25(4),
				lapb(5),
				hdlc(6),
				sdlcPri(7),
				sdlcSec(8),
				sdlc(9),
				trans(10)
					}
	MAX-ACCESS	read-write
	STATUS	current
	DESCRIPTION
		"接口封装协议类型."
	DEFVAL { hdlc }
	::= { serialConfEntry 22 }

serialPhyLayer	OBJECT-TYPE
	SYNTAX	INTEGER {
				syn(1),
				asyn(2)
					}
	MAX-ACCESS	read-write
	STATUS	current
	DESCRIPTION
		"接口物理层实现模式."
	DEFVAL { syn }
	::= { serialConfEntry 23 }

serialIpTcpHeadCompress	OBJECT-TYPE
	SYNTAX	INTEGER {
				noCompress(1),
				compress(2),
				compressRx(3)
					}
	MAX-ACCESS	read-write
	STATUS	current
	DESCRIPTION
		"接口上是否发送压缩报头的IP包."
	DEFVAL { noCompress }
	::= { serialConfEntry 24 }

serialBackup	OBJECT-TYPE
	SYNTAX	INTEGER {
				primary(1),
				backup(2),
				none(3)
					}
	MAX-ACCESS	read-write
	STATUS	current
	DESCRIPTION
		"接口的备份情况."
	::= { serialConfEntry 25 }

serialBackupIf	OBJECT-TYPE
	SYNTAX	INTEGER
	MAX-ACCESS	read-write
	STATUS	current
	DESCRIPTION
		"配置接口的备份口的索引."
	::= { serialConfEntry 26 }

serialBackupAct	OBJECT-TYPE
	SYNTAX	Unsigned32 (0..4294967294)
	MAX-ACCESS	read-write
	STATUS	current
	DESCRIPTION
		"主口断开后启用备份口的延迟时间.该值为空表示不启用备份口."
	::= { serialConfEntry 27 }

serialBackupDeact	OBJECT-TYPE
	SYNTAX	Unsigned32 (0..4294967294)
	MAX-ACCESS	read-write
	STATUS	current
	DESCRIPTION
		"主口恢复后启用主口的延迟时间.该值为空表示不断开备份口."
	::= { serialConfEntry 28 }

serialQos	OBJECT-TYPE
	SYNTAX	INTEGER {
				fifo(1),
				wfq(2),
				pq(3)
					}
	MAX-ACCESS	read-write
	STATUS	current
	DESCRIPTION
		"接口上的QoS排队方式."
	DEFVAL { fifo }
	::= { serialConfEntry 29 }

serialQosList	OBJECT-TYPE
	SYNTAX	INTEGER (1..16)
	MAX-ACCESS	read-write
	STATUS	current
	DESCRIPTION
		"接口上的QoS排队方式所使用的weight-list/priority-list的列表号."
	::= { serialConfEntry 30 }

serialTxHigh	OBJECT-TYPE
	SYNTAX	INTEGER (2..500)
	MAX-ACCESS	read-write
	STATUS	current
	DESCRIPTION
		"接口上的高优先级队列深度."
	DEFVAL { 50 }
	::= { serialConfEntry 31 }

serialTxMedium	OBJECT-TYPE
	SYNTAX	INTEGER (2..500)
	MAX-ACCESS	read-write
	STATUS	current
	DESCRIPTION
		"接口上的中优先级队列深度."
	DEFVAL { 50 }
	::= { serialConfEntry 32 }

serialTxNormal	OBJECT-TYPE
	SYNTAX	INTEGER (2..500)
	MAX-ACCESS	read-write
	STATUS	current
	DESCRIPTION
		"接口上的较低优先级队列深度."
	DEFVAL { 50 }
	::= { serialConfEntry 33 }

serialTxLow	OBJECT-TYPE
	SYNTAX	INTEGER (2..500)
	MAX-ACCESS	read-write
	STATUS	current
	DESCRIPTION
		"接口上的低优先级队列深度."
	DEFVAL { 50 }
	::= { serialConfEntry 34 }

serialTbds	OBJECT-TYPE
	SYNTAX	INTEGER (2..16)
	MAX-ACCESS	read-write
	STATUS	current
	DESCRIPTION
		"接口上的缓冲区大小."
	DEFVAL { 16 }
	::= { serialConfEntry 35 }

-- *****************************
-- subIfTable { mpIfMib 4 }
-- *****************************

-- *****************************
terminalTable	OBJECT-TYPE
	SYNTAX	SEQUENCE OF TerminalEntry
	MAX-ACCESS	not-accessible
	STATUS	current
	DESCRIPTION
		"终端信息表."
	::= { mpIfMib 5 }

terminalEntry	OBJECT-TYPE
	SYNTAX	TerminalEntry
	MAX-ACCESS	not-accessible
	STATUS	current
	DESCRIPTION
		"终端信息表入口."
	INDEX	{ termIndex }
	::= { terminalTable 1 }

TerminalEntry ::=
	SEQUENCE {
		termIndex	INTEGER,
		termStatus	INTEGER,
		termSpeed	INTEGER,
		termDatabits	INTEGER,
		termStopbits	INTEGER,
		termParity	INTEGER,
		termFlowCtrl	INTEGER,
		termLineOn	INTEGER,
		termRxBuf	INTEGER,
		termTxBuf	INTEGER,
		termPrint	INTEGER,
		termAutoLink	INTEGER,
		termAutoLinkNo	INTEGER,
		termRxDelay	INTEGER,
		termEscChar	OCTET STRING,
		termLocalHost	IpAddress,
		termTxBytes	INTEGER,
		termRxBytes	INTEGER,
		termRowStatus	RowStatus
			}

termIndex	OBJECT-TYPE
	SYNTAX	INTEGER
	MAX-ACCESS	read-write
	STATUS	current
	DESCRIPTION
		"终端号."
	::= { terminalEntry 1 }

termStatus	OBJECT-TYPE
	SYNTAX	INTEGER {
				disable(1),
				enable(2)
					}
	MAX-ACCESS	read-write
	STATUS	current
	DESCRIPTION
		"终端状态."
	::= { terminalEntry 2 }

termSpeed	OBJECT-TYPE
	SYNTAX	INTEGER
	MAX-ACCESS	read-write
	STATUS	current
	DESCRIPTION
		"终端速率."
	::= { terminalEntry 3 }

termDatabits	OBJECT-TYPE
	SYNTAX	INTEGER (5..8)
	MAX-ACCESS	read-write
	STATUS	current
	DESCRIPTION
		"终端数据位."
	::= { terminalEntry 4 }

termStopbits	OBJECT-TYPE
	SYNTAX	INTEGER (1..2)
	MAX-ACCESS	read-write
	STATUS	current
	DESCRIPTION
		"终端停止位."
	::= { terminalEntry 5 }

termParity	OBJECT-TYPE
	SYNTAX	INTEGER {
				even(1),
				mark(2),
				none(3),
				odd(4),
				space(5)
					}
	MAX-ACCESS	read-write
	STATUS	current
	DESCRIPTION
		"终端奇偶校验."
	::= { terminalEntry 6 }

termFlowCtrl	OBJECT-TYPE
	SYNTAX	INTEGER {
				hard(1),
				soft(2),
				none(3)
					}
	MAX-ACCESS	read-write
	STATUS	current
	DESCRIPTION
		"终端流控."
	::= { terminalEntry 7 }

termLineOn	OBJECT-TYPE
	SYNTAX	INTEGER {
				cts(1),
				dcd(2),
				dsr(3)
				}
	MAX-ACCESS	read-write
	STATUS	current
	DESCRIPTION
		"终端线路tx－on."
	::= { terminalEntry 8 }

termRxBuf	OBJECT-TYPE
	SYNTAX	INTEGER (32..8192)
	MAX-ACCESS	read-write
	STATUS	current
	DESCRIPTION
		"终端接收buf大小."
	::= { terminalEntry 9 }

termTxBuf	OBJECT-TYPE
	SYNTAX	INTEGER (32..8192)
	MAX-ACCESS	read-write
	STATUS	current
	DESCRIPTION
		"终端发送buf大小."
	::= { terminalEntry 10 }

termPrint	OBJECT-TYPE
	SYNTAX	INTEGER {
				off(1),
				on(2)
					}
	MAX-ACCESS	read-write
	STATUS	current
	DESCRIPTION
		"终端是否打印帮助信息."
	::= { terminalEntry 11 }

termAutoLink	OBJECT-TYPE
	SYNTAX	INTEGER {
				off(1),
				on(2)
					}
	MAX-ACCESS	read-write
	STATUS	current
	DESCRIPTION
		"终端是否自动建链."
	::= { terminalEntry 12 }

termAutoLinkNo	OBJECT-TYPE
	SYNTAX	INTEGER (0..9)
	MAX-ACCESS	read-write
	STATUS	current
	DESCRIPTION
		"终端自动建链业务号."
	::= { terminalEntry 13 }

termRxDelay	OBJECT-TYPE
	SYNTAX	INTEGER {
				off(1),
				on(2)
					}
	MAX-ACCESS	read-write
	STATUS	current
	DESCRIPTION
		"终端是否接收延迟."
	::= { terminalEntry 14 }

termEscChar	OBJECT-TYPE
	SYNTAX	OCTET STRING
	MAX-ACCESS	read-write
	STATUS	current
	DESCRIPTION
		"终端切换字符，最多四个字符，每个0～31，如^G=7."
	::= { terminalEntry 15 }

termLocalHost	OBJECT-TYPE
	SYNTAX	IpAddress
	MAX-ACCESS	read-write
	STATUS	current
	DESCRIPTION
		"终端本地ip地址."
	::= { terminalEntry 16 }

termTxBytes	OBJECT-TYPE
	SYNTAX	INTEGER
	MAX-ACCESS	read-only
	STATUS	current
	DESCRIPTION
		"终端统计终端发送数据字节数."
	::= { terminalEntry 17 }

termRxBytes	OBJECT-TYPE
	SYNTAX	INTEGER
	MAX-ACCESS	read-only
	STATUS	current
	DESCRIPTION
		"终端统计终端接收数据字节数."
	::= { terminalEntry 18 }

termRowStatus	OBJECT-TYPE
	SYNTAX	RowStatus
	MAX-ACCESS	read-create
	STATUS	current
	DESCRIPTION
		"终端表行状态."
	::= { terminalEntry 19 }

-- *****************************
terminalHostTable	OBJECT-TYPE
	SYNTAX	SEQUENCE OF TerminalHostEntry
	MAX-ACCESS	not-accessible
	STATUS	current
	DESCRIPTION
		"终端的远端业务信息表."
	::= { mpIfMib 6 }

terminalHostEntry	OBJECT-TYPE
	SYNTAX	TerminalHostEntry
	MAX-ACCESS	not-accessible
	STATUS	current
	DESCRIPTION
		"终端的远端业务信息表入口."
	INDEX	{ termHostIndex, termHostNo }
	::= { terminalHostTable 1 }

TerminalHostEntry ::=
	SEQUENCE {
		termHostIndex	INTEGER,
		termHostNo	INTEGER,
		termHostName	DisplayString,
		termHostIp	IpAddress,
		termHostPort	INTEGER,
		termHostType	INTEGER,
		termHostTelnetType	DisplayString,
		termHostStauts	INTEGER,
		termHostFixtermType	INTEGER,
		termHostFixtermAuth	INTEGER,
		termHostFixtermChars	OCTET STRING,
		termHostRloginUser		INTEGER,
		termHostRloginLocal		DisplayString,
		termHostRloginRemote	DisplayString,
		termHostRowStatus	RowStatus
			}

termHostIndex	OBJECT-TYPE
	SYNTAX	INTEGER
	MAX-ACCESS	read-only
	STATUS	current
	DESCRIPTION
		"终端号."
	::= { terminalHostEntry 1 }

termHostNo	OBJECT-TYPE
	SYNTAX	INTEGER (0..9)
	MAX-ACCESS	read-only
	STATUS	current
	DESCRIPTION
		"终端的远端业务编号."
	::= { terminalHostEntry 2 }

termHostName	OBJECT-TYPE
	SYNTAX	DisplayString (SIZE(0..40))
	MAX-ACCESS	read-write
	STATUS	current
	DESCRIPTION
		"终端的远端业务名称."
	::= { terminalHostEntry 3 }

termHostIp	OBJECT-TYPE
	SYNTAX	IpAddress
	MAX-ACCESS	read-write
	STATUS	current
	DESCRIPTION
		"终端的远端业务IP地址."
	::= { terminalHostEntry 4 }

termHostPort	OBJECT-TYPE
	SYNTAX	INTEGER
	MAX-ACCESS	read-write
	STATUS	current
	DESCRIPTION
		"终端的远端业务TCP端口号."
	::= { terminalHostEntry 5 }

termHostType	OBJECT-TYPE
	SYNTAX	INTEGER {
				telnet(1),
				rlogin(2),
				fixterm(3)
					}
	MAX-ACCESS	read-write
	STATUS	current
	DESCRIPTION
		"终端的远端业务类型."
	::= { terminalHostEntry 6 }

termHostTelnetType	OBJECT-TYPE
	SYNTAX	DisplayString (SIZE(0..10))
	MAX-ACCESS	read-write
	STATUS	current
	DESCRIPTION
		"终端的远端业务:telnet业务类型."
	::= { terminalHostEntry 7 }

termHostStauts	OBJECT-TYPE
	SYNTAX	INTEGER {
				standby(1),
				connect(2),
				disconnet(3)
					}
	MAX-ACCESS	read-write
	STATUS	current
	DESCRIPTION
		"终端的远端业务工作状态."
	::= { terminalHostEntry 8 }

termHostFixtermType	OBJECT-TYPE
	SYNTAX	INTEGER {
				client(1),
				server(2)
					}
	MAX-ACCESS	read-write
	STATUS	current
	DESCRIPTION
		"终端的远端业务:fixterm类型."
	::= { terminalHostEntry 9 }

termHostFixtermAuth	OBJECT-TYPE
	SYNTAX	INTEGER {
				authentic(1),
				non-authentic(2)
					}
	MAX-ACCESS	read-write
	STATUS	current
	DESCRIPTION
		"终端的远端业务:fixterm认证类型."
	::= { terminalHostEntry 10 }

termHostFixtermChars	OBJECT-TYPE
	SYNTAX	OCTET STRING
	MAX-ACCESS	read-write
	STATUS	current
	DESCRIPTION
		"终端的远端业务:fixterm自动刷屏字符."
	::= { terminalHostEntry 11 }

termHostRloginUser	OBJECT-TYPE
	SYNTAX	INTEGER {
				off(1),
				on(2)
					}
	MAX-ACCESS	read-write
	STATUS	current
	DESCRIPTION
		"终端的远端业务:rlogin是否允许配置远端用户名."
	::= { terminalHostEntry 12 }

termHostRloginLocal	OBJECT-TYPE
	SYNTAX	DisplayString (SIZE(0..40))
	MAX-ACCESS	read-write
	STATUS	current
	DESCRIPTION
		"终端的远端业务:rlogin本地用户名."
	::= { terminalHostEntry 13 }

termHostRloginRemote	OBJECT-TYPE
	SYNTAX	DisplayString (SIZE(0..40))
	MAX-ACCESS	read-write
	STATUS	current
	DESCRIPTION
		"终端的远端业务:rlogin远端用户名."
	::= { terminalHostEntry 14 }

termHostRowStatus	OBJECT-TYPE
	SYNTAX	RowStatus
	MAX-ACCESS	read-create
	STATUS	current
	DESCRIPTION
		"终端业务表的行状态"
	::= { terminalHostEntry 15 }

-- *****************************
lineConfTable	OBJECT-TYPE
	SYNTAX	SEQUENCE OF LineConfEntry
	MAX-ACCESS	not-accessible
	STATUS	current
	DESCRIPTION
		"终端的远端业务信息表."
	::= { mpIfMib 7 }

lineConfEntry	OBJECT-TYPE
	SYNTAX	LineConfEntry
	MAX-ACCESS	not-accessible
	STATUS	current
	DESCRIPTION
		"终端的远端业务信息表入口."
	INDEX	{ lineConfNo }
	::= { lineConfTable 1 }

LineConfEntry ::=
	SEQUENCE {
		lineConfNo	INTEGER,
		lineConfMode	INTEGER,
		lineConfRowStatus	RowStatus
			}

lineConfNo	OBJECT-TYPE
	SYNTAX	INTEGER
	MAX-ACCESS	read-only
	STATUS	current
	DESCRIPTION
		"line号."
	::= { lineConfEntry 1 }

lineConfMode	OBJECT-TYPE
	SYNTAX	INTEGER {
				interface(1),
				terminal(2),
				free(3)
					}
	MAX-ACCESS	read-write
	STATUS	current
	DESCRIPTION
		"line类型."
	::= { lineConfEntry 2 }

lineConfRowStatus	OBJECT-TYPE
	SYNTAX	RowStatus
	MAX-ACCESS	read-create
	STATUS	current
	DESCRIPTION
		"line表行状态."
	::= { lineConfEntry 3 }

-- *****************************
bridgeConfTable	OBJECT-TYPE
	SYNTAX	SEQUENCE OF BridgeConfEntry
	MAX-ACCESS	not-accessible
	STATUS	current
	DESCRIPTION
		"桥配置表."
	::= { mpIfMib 8 }

bridgeConfEntry	OBJECT-TYPE
	SYNTAX	BridgeConfEntry
	MAX-ACCESS	not-accessible
	STATUS	current
	DESCRIPTION
		"桥配置表入口."
	INDEX	{ bridgeConfIfIndex }
	::= { bridgeConfTable 1 }

BridgeConfEntry ::=
	SEQUENCE {
		bridgeConfIfIndex	INTEGER,
		bridgeConfBriNo		INTEGER,
		bridgeConfRowStatus	RowStatus
			}

bridgeConfIfIndex	OBJECT-TYPE
	SYNTAX	INTEGER
	MAX-ACCESS	read-only
	STATUS	current
	DESCRIPTION
		"配置桥的接口索引."
	::= { bridgeConfEntry 1 }

bridgeConfBriNo	OBJECT-TYPE
	SYNTAX	INTEGER (1..10)
	MAX-ACCESS	read-write
	STATUS	current
	DESCRIPTION
		"桥号."
	::= { bridgeConfEntry 2 }

bridgeConfRowStatus	OBJECT-TYPE
	SYNTAX	RowStatus
	MAX-ACCESS	read-create
	STATUS	current
	DESCRIPTION
		"桥配置表行状态."
	::= { bridgeConfEntry 3 }

END
