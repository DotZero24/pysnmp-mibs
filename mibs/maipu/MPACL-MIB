------------------------------------------------------------------------------
--
--  File         : mpAcl.mib
--  Description  :
--  Version      :
--  Date         : March 20, 2006
-- 	Copyright    : 2006 by maipu (sichuan) communication technology co.,ltd.
--					All rights reserved.
--
-- $Id:
--
------------------------------------------------------------------------------

------------------------------------------------------------------------------
MPACL-MIB DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress,
	RowStatus, DisplayString, DateAndTime
                                                 FROM SNMPv2-TC
        MODULE-COMPLIANCE, OBJECT-GROUP
        	FROM SNMPv2-CONF
        mpMgmt
        	FROM MAIPU-SMI
        ObjectName, ObjectSyntax, NetworkAddress
                FROM RFC1155-SMI;



mpAclMib            	MODULE-IDENTITY
                    		LAST-UPDATED 	"0603201716Z"
                    		ORGANIZATION 	"四川迈普数据通信股份有限公司,
                    		             	 Maipu (Sichuan) Communication Technology Co. LTD."
                    		CONTACT-INFO
                    			"编 写 人：huyq
                    			 联系地址：四川省 成都市 高新区 九兴大道16号
                    			 邮    编：610041
                    			 电    话：
                    			 传    真：
                    			 电子邮件："
                    		DESCRIPTION
                      			""
                    		::= { mpMgmt  30 }




------------------------------------------------------------------------------
mpAclConf           	OBJECT IDENTIFIER ::= { mpAclMib 5 }

mpAclStdTable       	OBJECT-TYPE
                    		SYNTAX  SEQUENCE OF  MpAclStdEntry
                    		MAX-ACCESS  not-accessible
                    		STATUS  current
                    		DESCRIPTION
                    			"标准ACL的配置表."
                    		::= { mpAclConf 10 }

mpAclStdEntry       	OBJECT-TYPE
                    		SYNTAX  MpAclStdEntry
                    		MAX-ACCESS  not-accessible
                    		STATUS  current
                    		DESCRIPTION
                    			"标准ACL的配置表."
                    		INDEX  { aclStdName, aclStdSequence }
                    		::= { mpAclStdTable 1 }

MpAclStdEntry       	::= SEQUENCE {
                    			aclStdName             DisplayString,
                    			aclStdSequence         INTEGER,
                    			aclStdType             INTEGER,
                    			aclStdSrcAddr          IpAddress,
                    			aclStdSrcWildcard      IpAddress,
                    			aclStdLogEnable        INTEGER,
--                    			aclStdAuditEnable      INTEGER,
                    			aclStdTimeRngName      DisplayString,
                    			aclStdRemark           DisplayString,
                    			aclStdMatchPkts        Counter64,
--                    			aclStdMatchBytes       Counter64,
                    			aclStdRowStatus        RowStatus
                    	             }


aclStdName          	OBJECT-TYPE
                    		SYNTAX  DisplayString(SIZE(1..31))
                    		MAX-ACCESS  read-create
                    		STATUS  current
                    		DESCRIPTION
                    			"访问列表名称或编号."
                    		::= { mpAclStdEntry 1 }

aclStdSequence      	OBJECT-TYPE
                    		SYNTAX  INTEGER(1..2147483647)
                    		MAX-ACCESS  read-create
                    		STATUS  current
                    		DESCRIPTION
                    			"规则的序号."
                    		::= { mpAclStdEntry 2 }

aclStdType          	OBJECT-TYPE
                    		SYNTAX  INTEGER {
                    			         permit(1),
                    			          deny(2),
                    			          remark(3)
                    			        }
                    		MAX-ACCESS  read-write
                    		STATUS  current
                    		DESCRIPTION
                    			"规则的类型，该字段必须指定."
                    		::= { mpAclStdEntry 3 }

aclStdSrcAddr       	OBJECT-TYPE
                    		SYNTAX  IpAddress
                    		MAX-ACCESS  read-write
                    		STATUS  current
                    		DESCRIPTION
                    			"源IP地址，该字段必须指定."
                    		::= { mpAclStdEntry 4 }

aclStdSrcWildcard   	OBJECT-TYPE
                    		SYNTAX  IpAddress
                    		MAX-ACCESS  read-write
                    		STATUS  current
                    		DESCRIPTION
                    			"源IP地址通配符。当是host的时候，该值为0;是any的时候，该值为0xffffffff。该字段必须指定."
                    		::= { mpAclStdEntry 5 }

aclStdLogEnable     	OBJECT-TYPE
                    		SYNTAX  INTEGER {
                    			         disable(1),
                    			          enable(2)
                    			        }
                    		MAX-ACCESS  read-write
                    		STATUS  current
                    		DESCRIPTION
                    			"是否进行日志记录,缺省为disable."
                    		::= { mpAclStdEntry 6 }

-- 更新7500、3700、2700、MP5、PM3特殊出厂版本：注释掉不用的配置项  by zhaoym 2007.12.12
--aclStdAuditEnable   	OBJECT-TYPE
--                    		SYNTAX  INTEGER {
--                    			         disable(1),
--                    			          enable(2)
--                    			        }
--                    		MAX-ACCESS  read-write
--                    		STATUS  current
--                    		DESCRIPTION
--                    			"是否进行审计,缺省为disable."
--                    		::= { mpAclStdEntry 7 }

aclStdTimeRngName   	OBJECT-TYPE
                    		SYNTAX  DisplayString(SIZE(0..31))
                    		MAX-ACCESS  read-write
                    		STATUS  current
                    		DESCRIPTION
                    			"时间域名称，缺省为空."
                    		::= { mpAclStdEntry 8 }

aclStdRemark        	OBJECT-TYPE
                    		SYNTAX  DisplayString(SIZE(0..99))
                    		MAX-ACCESS  read-write
                    		STATUS  current
                    		DESCRIPTION
                    			"规则的注释，仅当aclStdType为remark(3)时该字段有意义."
                    		::= { mpAclStdEntry 9 }

aclStdMatchPkts     	OBJECT-TYPE
                    		SYNTAX  Counter64
                    		MAX-ACCESS  read-only
                    		STATUS  current
                    		DESCRIPTION
                    			"与该规则相匹配的报文数统计值."
                    		::= { mpAclStdEntry 10 }
-- 更新7500、3700、2700、MP5、PM3特殊出厂版本：注释掉不用的配置项  by zhaoym 2007.12.12
--aclStdMatchBytes    	OBJECT-TYPE
--                   		SYNTAX  Counter64
--                    		MAX-ACCESS  read-only
--                    		STATUS  current
--                    		DESCRIPTION
--                    			"与该规则相匹配的字节数统计值."
--                    		::= { mpAclStdEntry 11 }

aclStdRowStatus     	OBJECT-TYPE
                    		SYNTAX  RowStatus
                    		MAX-ACCESS  read-create
                    		STATUS  current
                    		DESCRIPTION
                    			"标准ACL的配置表的行状态."
                    		::= { mpAclStdEntry 12 }

mpAclExtTable       	OBJECT-TYPE
                    		SYNTAX  SEQUENCE OF  MpAclExtEntry
                    		MAX-ACCESS  not-accessible
                    		STATUS  current
                    		DESCRIPTION
                    			"扩展ACL的配置表."
                    		::= { mpAclConf 20 }

mpAclExtEntry       	OBJECT-TYPE
                    		SYNTAX  MpAclExtEntry
                    		MAX-ACCESS  not-accessible
                    		STATUS  current
                    		DESCRIPTION
                    			"扩展ACL的配置表."
                    		INDEX  { aclExtName, aclExtSequence }
                    		::= { mpAclExtTable 1 }

MpAclExtEntry       	::= SEQUENCE {
                    			aclExtName             DisplayString,
                    			aclExtSequence         INTEGER,
                    			aclExtType             INTEGER,
                    			aclExtProtocol         INTEGER,
                    			aclExtSrcAddr          IpAddress,
                    			aclExtSrcWildcard      IpAddress,
                    			aclExtDestAddr         IpAddress,
                    			aclExtDestWildcard     IpAddress,
                    			aclExtPrecedence       INTEGER,
                    			aclExtTos              INTEGER,
                    			aclExtIcmpMsgType      INTEGER,
                    			aclExtIcmpMsgCode      INTEGER,
                    			aclExtIgmpMsgType      INTEGER,
                    			aclExtTUSrcPortType    INTEGER,
                    			aclExtTUSrcPort        INTEGER,
                    			aclExtTUSrcEndPort     INTEGER,
                    			aclExtTUDestPortType   INTEGER,
                    			aclExtTUDestPort       INTEGER,
                    			aclExtTUDestEndPort    INTEGER,
                    			aclExtTcpFlag          INTEGER,
                    			aclExtLogEnable        INTEGER,
--                    			aclExtAuditEnable      INTEGER,
                    			aclExtTimeRngName      DisplayString,
                    			aclExtReflectName      DisplayString,
                    			aclExtReflectTimeOut   INTEGER,
                    			aclExtEvaluateName     DisplayString,
                    			aclExtRemark           DisplayString,
                    			aclExtMatchPkts        Counter64,
--                    			aclExtMatchBytes       Counter64,
                    			aclExtRowStatus        RowStatus
                    	             }


aclExtName          	OBJECT-TYPE
                    		SYNTAX  DisplayString(SIZE(1..31))
                    		MAX-ACCESS  read-create
                    		STATUS  current
                    		DESCRIPTION
                    			"访问列表名称或编号."
                    		::= { mpAclExtEntry 1 }

aclExtSequence      	OBJECT-TYPE
                    		SYNTAX  INTEGER(1..2147483647)
                    		MAX-ACCESS  read-create
                    		STATUS  current
                    		DESCRIPTION
                    			"规则的序号."
                    		::= { mpAclExtEntry 2 }

aclExtType          	OBJECT-TYPE
                    		SYNTAX  INTEGER {
                    			         permit(1),
                    			          deny(2),
                    			          remark(3),
                    			          evaluate(4)
                    			        }
                    		MAX-ACCESS  read-write
                    		STATUS  current
                    		DESCRIPTION
                    			"规则的类型，该字段必须指定."
                    		::= { mpAclExtEntry 3 }

aclExtProtocol      	OBJECT-TYPE
                    		SYNTAX  INTEGER(0..255)
                    		MAX-ACCESS  read-write
                    		STATUS  current
                    		DESCRIPTION
                    			"IP协议类型，该字段必须指定."
                    		::= { mpAclExtEntry 4 }

aclExtSrcAddr       	OBJECT-TYPE
                    		SYNTAX  IpAddress
                    		MAX-ACCESS  read-write
                    		STATUS  current
                    		DESCRIPTION
                    			"源IP地址，该字段必须指定."
                    		::= { mpAclExtEntry 5 }

aclExtSrcWildcard   	OBJECT-TYPE
                    		SYNTAX  IpAddress
                    		MAX-ACCESS  read-write
                    		STATUS  current
                    		DESCRIPTION
                    			"源IP地址通配符。当是host的时候，该值为0;是any的时候，该值为0xffffffff。该字段必须指定."
                    		::= { mpAclExtEntry 6 }

aclExtDestAddr      	OBJECT-TYPE
                    		SYNTAX  IpAddress
                    		MAX-ACCESS  read-write
                    		STATUS  current
                    		DESCRIPTION
                    			"目的IP地址，该字段必须指定."
                    		::= { mpAclExtEntry 7 }

aclExtDestWildcard  	OBJECT-TYPE
                    		SYNTAX  IpAddress
                    		MAX-ACCESS  read-write
                    		STATUS  current
                    		DESCRIPTION
                    			"目的IP地址通配符。当是host的时候，该值为0;是any的时候，该值为0xffffffff。该字段必须指定."
                    		::= { mpAclExtEntry 8 }

aclExtPrecedence    	OBJECT-TYPE
                    		SYNTAX  INTEGER(-1..7)
                    		MAX-ACCESS  read-write
                    		STATUS  current
                    		DESCRIPTION
                    			"IP优先级。routine - 0,  priority - 1, immediate - 2, flash - 3, flash-voeride - 4, critical - 5, internet - 6, network - 7, -1表示不关心."
                    		::= { mpAclExtEntry 9 }

aclExtTos           	OBJECT-TYPE
                    		SYNTAX  INTEGER(-1..15)
                    		MAX-ACCESS  read-write
                    		STATUS  current
                    		DESCRIPTION
                    			"IP TOS。 normal - 0,  min-monetary-cost - 1, max-reliability - 2,  max-throughput - 4,  min-delay - 8, -1表示不关心."
                    		::= { mpAclExtEntry 10 }

aclExtIcmpMsgType   	OBJECT-TYPE
                    		SYNTAX  INTEGER(-1..255)
                    		MAX-ACCESS  read-write
                    		STATUS  current
                    		DESCRIPTION
                    			"ICMP类型, -1表示不关心."
                    		::= { mpAclExtEntry 11 }

aclExtIcmpMsgCode   	OBJECT-TYPE
                    		SYNTAX  INTEGER(-1..255)
                    		MAX-ACCESS  read-write
                    		STATUS  current
                    		DESCRIPTION
                    			"ICMP代码, -1表示不关心."
                    		::= { mpAclExtEntry 12 }

aclExtIgmpMsgType   	OBJECT-TYPE
                    		SYNTAX  INTEGER(-1..15)
                    		MAX-ACCESS  read-write
                    		STATUS  current
                    		DESCRIPTION
                    			"IGMP类型, -1表示不关心."
                    		::= { mpAclExtEntry 13 }

aclExtTUSrcPortType 	OBJECT-TYPE
                    		SYNTAX  INTEGER {
                    			         no-care(0),
                    			          eq(1),
                    			          gt(2),
                    			          lt(3),
                    			          neq(4),
                    			          range(5),
                    			          wildcard(6)
                    			        }
                    		MAX-ACCESS  read-write
                    		STATUS  current
                    		DESCRIPTION
                    			"TCP或UDP源端口类型，0表示不关心源端口."
                    		::= { mpAclExtEntry 14 }

aclExtTUSrcPort     	OBJECT-TYPE
                    		SYNTAX  INTEGER(0..65535)
                    		MAX-ACCESS  read-write
                    		STATUS  current
                    		DESCRIPTION
                    			"源端口号。当类型是range时，这是起始端口号."
                    		::= { mpAclExtEntry 15 }

aclExtTUSrcEndPort  	OBJECT-TYPE
                    		SYNTAX  INTEGER(0..65535)
                    		MAX-ACCESS  read-write
                    		STATUS  current
                    		DESCRIPTION
                    			"当类型是range时，这是终止端口号；当类型是wildcard时，这是端口的wildcard值."
                    		::= { mpAclExtEntry 16 }

aclExtTUDestPortType	OBJECT-TYPE
                    		SYNTAX  INTEGER {
                    			         no-care(0),
                    			          eq(1),
                    			          gt(2),
                    			          lt(3),
                    			          neq(4),
                    			          range(5),
                    			          wildcard(6)
                    			        }
                    		MAX-ACCESS  read-write
                    		STATUS  current
                    		DESCRIPTION
                    			"TCP或UDP目的端口类型， 0表示不关心目的端口."
                    		::= { mpAclExtEntry 17 }

aclExtTUDestPort    	OBJECT-TYPE
                    		SYNTAX  INTEGER(0..65535)
                    		MAX-ACCESS  read-write
                    		STATUS  current
                    		DESCRIPTION
                    			"目的端口号。当类型是range时，这是起始端口号."
                    		::= { mpAclExtEntry 18 }

aclExtTUDestEndPort 	OBJECT-TYPE
                    		SYNTAX  INTEGER(0..65535)
                    		MAX-ACCESS  read-write
                    		STATUS  current
                    		DESCRIPTION
                    			"当类型是range时，这是终止端口号；当类型是wildcard时，这是端口的wildcard值."
                    		::= { mpAclExtEntry 19 }

aclExtTcpFlag       	OBJECT-TYPE
                    		SYNTAX  INTEGER(-1..63)
                    		MAX-ACCESS  read-write
                    		STATUS  current
                    		DESCRIPTION
                    			"TCP标志。FIN - 0x01,SYN - 0x02,RST - 0x04,SH - 0x08,ACK - 0x10,URG - 0x20,ESTABLISHED - 0x14, -1表示不关心."
                    		::= { mpAclExtEntry 20 }

aclExtLogEnable     	OBJECT-TYPE
                    		SYNTAX  INTEGER {
                    			         disable(1),
                    			          enable(2)
                    			        }
                    		MAX-ACCESS  read-write
                    		STATUS  current
                    		DESCRIPTION
                    			"是否进行日志记录,缺省为disable."
                    		::= { mpAclExtEntry 21 }

-- 更新7500、3700、2700、MP5、PM3特殊出厂版本：注释掉不用的配置项  by zhaoym 2007.12.12
--aclExtAuditEnable   	OBJECT-TYPE
--                    		SYNTAX  INTEGER {
--                    			         disable(1),
--                    			          enable(2)
--                    			        }
--                    		MAX-ACCESS  read-write
--                    		STATUS  current
--                    		DESCRIPTION
--                    			"是否进行审计,缺省为disable."
--                    		::= { mpAclExtEntry 22 }

aclExtTimeRngName   	OBJECT-TYPE
                    		SYNTAX  DisplayString(SIZE(0..31))
                    		MAX-ACCESS  read-write
                    		STATUS  current
                    		DESCRIPTION
                    			"时间域的名称，缺省为空."
                    		::= { mpAclExtEntry 23 }

aclExtReflectName   	OBJECT-TYPE
                    		SYNTAX  DisplayString(SIZE(0..31))
                    		MAX-ACCESS  read-write
                    		STATUS  current
                    		DESCRIPTION
                    			"自反访问列表的名称，缺省为空."
                    		::= { mpAclExtEntry 24 }

aclExtReflectTimeOut	OBJECT-TYPE
                    		SYNTAX  INTEGER(0..2147483647)
                    		MAX-ACCESS  read-write
                    		STATUS  current
                    		DESCRIPTION
                    			"自反访问列表超时时间，单位为秒，缺省为0,表示使用全局的超时时间。仅当aclExtReflectName非空时该字段才有效.0表示不关心该字段."
                    		::= { mpAclExtEntry 25 }

aclExtEvaluateName  	OBJECT-TYPE
                    		SYNTAX  DisplayString(SIZE(0..31))
                    		MAX-ACCESS  read-write
                    		STATUS  current
                    		DESCRIPTION
                    			"evaluate访问列表的名称，缺省为空."
                    		::= { mpAclExtEntry 26 }

aclExtRemark        	OBJECT-TYPE
                    		SYNTAX  DisplayString(SIZE(0..99))
                    		MAX-ACCESS  read-write
                    		STATUS  current
                    		DESCRIPTION
                    			"规则的注释，仅当aclExtType为remark(3)时该字段有意义."
                    		::= { mpAclExtEntry 27 }


aclExtMatchPkts     	OBJECT-TYPE
                   		SYNTAX  Counter64
                   		MAX-ACCESS  read-only
                    		STATUS  current
                    		DESCRIPTION
                    			"与该规则相匹配的报文数统计值."
                    		::= { mpAclExtEntry 28 }

-- 更新7500、3700、2700、MP5、PM3特殊出厂版本：注释掉不用的配置项  by zhaoym 2007.12.12
--aclExtMatchBytes    	OBJECT-TYPE
--                    		SYNTAX  Counter64
--                    		MAX-ACCESS  read-only
--                   		STATUS  current
--                    		DESCRIPTION
--                    			"与该规则相匹配的字节数统计值."
--                    		::= { mpAclExtEntry 29 }

aclExtRowStatus     	OBJECT-TYPE
                    		SYNTAX  RowStatus
                    		MAX-ACCESS  read-create
                    		STATUS  current
                    		DESCRIPTION
                    			"扩展ACL的配置表的行状态."
                    		::= { mpAclExtEntry 30 }



END
------------------------------------------------------------------------------
-- ============================================================================
-- $Log: mpAcl.mib,v $
-- Revision 1.1  2010/06/21 11:18:46  liyh
-- first commit
--
--
--
-- ============================================================================
