-- *****************************************************************
-- MAIPU-FILE.mib:  Maipu enterprise device file MIB file
--
-- version 1.0.0.0, Augest 1, 2001 huanglulu
--
-- Copyright (c)  by Maipu DataComm Inc.
-- All rights reserved.
--
-- *****************************************************************
--

MPFILE-MIB DEFINITIONS ::= BEGIN

IMPORTS
    DisplayString					FROM SNMPv2-TC
    MODULE-IDENTITY, OBJECT-TYPE,
    IpAddress						FROM SNMPv2-SMI
    mpMgmt			        		FROM MAIPU-SMI;

mpFileMib MODULE-IDENTITY
    LAST-UPDATED "0108010000Z"
    ORGANIZATION "Maipu DataComm"
    CONTACT-INFO
        "	Maipu DataComm
		Customer Service

		Postal: Consulate Drive
			Chengdu, Sichuan  5148299
			China

	        Tel: 86-028-5148299

		E-mail: office@maipu.com"
    DESCRIPTION
        "The assignments for Maipu router's MIB of device file infomation!"
    ::= { mpMgmt 3 }

mpSoftVersion	OBJECT-TYPE
	SYNTAX	DisplayString (SIZE(1..20))
	MAX-ACCESS	read-only
	STATUS	current
	DESCRIPTION
	  "The Software Version of the product."
	::= { mpFileMib 1 }

mpFileTable	OBJECT-TYPE
	SYNTAX	SEQUENCE OF MpFileEntry
	MAX-ACCESS	not-accessible
	STATUS	current
	DESCRIPTION
	  "The ftp command table."
	::= { mpFileMib 2 }

mpFileEntry	OBJECT-TYPE
	SYNTAX	MpFileEntry
	MAX-ACCESS	not-accessible
	STATUS	current
	DESCRIPTION
	  "The file command table entry."
	INDEX { mpFileCommand }
	::= { mpFileTable 1 }

MpFileEntry ::=
	SEQUENCE {
		mpFileCommand
			INTEGER,
		mpFileName
			DisplayString,
		mpFileSize
			INTEGER,
		mpFileConfigType
			INTEGER,
		mpFileTransMode
			INTEGER,
		mpFileServerIP
			IpAddress,
		mpFileUser
			DisplayString,
		mpFilePassword
			OCTET STRING,
		mpFileEncrypt
			INTEGER
				}

mpFileCommand	OBJECT-TYPE
	SYNTAX	INTEGER {
				backup(1),
				restore(2),
				update(3),
				reboot(4)
					}
	MAX-ACCESS	read-write
	STATUS	current
	DESCRIPTION
		"Send command to do with a file."
	::= { mpFileEntry 1 }

mpFileName	OBJECT-TYPE
	SYNTAX	DisplayString(SIZE(1..255))
	MAX-ACCESS	read-write
	STATUS	current
	DESCRIPTION
	  	"Filename for the command."
	::= { mpFileEntry 2 }

mpFileSize	OBJECT-TYPE
	SYNTAX	INTEGER
	MAX-ACCESS	read-write
	STATUS	current
	DESCRIPTION
		"File size."
	::= { mpFileEntry 3 }

mpFileConfigType	OBJECT-TYPE
	SYNTAX	INTEGER {
				other(1),
				running(2),
				startup(3)
					}
	MAX-ACCESS	read-write
	STATUS	current
	DESCRIPTION
		"Backup file as running-config or startup-config."
	::= { mpFileEntry 4 }

mpFileTransMode	OBJECT-TYPE
	SYNTAX	INTEGER {
				ftp(1),
				tftp(2),
				rcp(3)
					}
	MAX-ACCESS	read-write
	STATUS	current
	DESCRIPTION
		"File transfer mode."
	::= { mpFileEntry 5 }

mpFileServerIP	OBJECT-TYPE
	SYNTAX	IpAddress
	MAX-ACCESS	read-write
	STATUS	current
	DESCRIPTION
	  	"FTP or TFTP or RCP Server IP address."
	::= { mpFileEntry 6 }

mpFileUser	OBJECT-TYPE
	SYNTAX	DisplayString(SIZE(1..255))
	MAX-ACCESS	read-write
	STATUS	current
	DESCRIPTION
		"User name."
	::= { mpFileEntry 7 }

mpFilePassword	OBJECT-TYPE
	SYNTAX	OCTET STRING(SIZE(0..255))
	MAX-ACCESS	read-write
	STATUS	current
	DESCRIPTION
		"User password."
	::= { mpFileEntry 8 }

mpFileEncrypt	OBJECT-TYPE
	SYNTAX	INTEGER {
				none(1)
					}
	MAX-ACCESS	read-write
	STATUS	current
	DESCRIPTION
		"File encryption type."
	::= { mpFileEntry 9 }


-- *************************
-- 2002.9.19 做路由器的命令
-- *************************

mpRtrCommand	OBJECT IDENTIFIER ::= { mpFileMib 3 }

mpRtrCommWrite OBJECT-TYPE
    SYNTAX INTEGER {
    			noop(1),
    			write(2)
    				}
    MAX-ACCESS read-write
    STATUS current
    DESCRIPTION
        "路由器的write命令。"
    ::= { mpRtrCommand 1 }

mpRtrCommBackup OBJECT-TYPE
    SYNTAX INTEGER (0..255)
    MAX-ACCESS read-write
    STATUS current
    DESCRIPTION
        "路由器的Write Backup命令。"
    ::= { mpRtrCommand 2 }

END
