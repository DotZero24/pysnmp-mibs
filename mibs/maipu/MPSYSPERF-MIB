------------------------------------------------------------------------------
--
--  File         : mpSysPerMib.mib
--  Description  :
--  Version      :
--  Date         : July 31, 2007
-- 	Copyright    : 2007 by maipu (sichuan) communication technology co.,ltd.
--					All rights reserved.
--
-- $Id:
--
------------------------------------------------------------------------------

------------------------------------------------------------------------------
MPSYSPERF-MIB DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress,
	RowStatus, DisplayString, DateAndTime
                                                 FROM SNMPv2-TC
        MODULE-COMPLIANCE, OBJECT-GROUP
        	FROM SNMPv2-CONF
        mpMgmt
        	FROM MAIPU-SMI
        ObjectName, ObjectSyntax, NetworkAddress
                FROM RFC1155-SMI;



mpSysPerfMib        	MODULE-IDENTITY
                    		LAST-UPDATED 	"0707311414Z"
                    		ORGANIZATION 	"Maipu (Sichuan) Communication Technology Co. LTD."
                    		CONTACT-INFO
                    			"yangtian
                    			 Maipu (Sichuan) Communication Technology Co. LTD.
                    			 610041"
                    		DESCRIPTION
                      			" The system performance MIB of Maipu device"
                    		::= { mpMgmt  901 }



mpSysRamUsage       	OBJECT-TYPE
                    		SYNTAX  INTEGER(0..100)
                    		MAX-ACCESS  read-only
                    		STATUS  current
                    		DESCRIPTION
                    			"The usage of system RAM."
                    		::= { mpSysPerfMib 1 }

mpSysCpuUsage       	OBJECT-TYPE
                    		SYNTAX  INTEGER(0..100)
                    		MAX-ACCESS  read-only
                    		STATUS  current
                    		DESCRIPTION
                    			"The usage of system CPU."
                    		::= { mpSysPerfMib 2 }

mpSysCpuPeakLoad    	OBJECT-TYPE
                    		SYNTAX  INTEGER(0..100)
                    		MAX-ACCESS  read-only
                    		STATUS  current
                    		DESCRIPTION
                    			"The peak load of CPU in last 5 minutes."
                    		::= { mpSysPerfMib 3 }



END
------------------------------------------------------------------------------
-- ============================================================================
-- $Log: mpSysPerfMib.mib,v $
-- Revision 1.1  2010/06/21 11:18:46  liyh
-- first commit
--
-- Revision 1.1  2008/07/04 06:39:00  yangtian
-- ROUTER-11636
-- 提交系统能力MIB
--
--
--
-- ============================================================================
