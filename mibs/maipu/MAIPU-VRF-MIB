------------------------------------------------------------------------------
--
--  File         : mVrfMib.mi2
--  Description  : 关于路由转发表配置的MIB库。源于tmsL3Mib库。
--  Version      : 1.0
--  Date         : 2004.5.27
-- 	Copyright    : 2004 by maipu (sichuan) communication technology co.,ltd.
--					All rights reserved.
--
-- $Id: mVrfMib.mi2,v 1.1 2004/08/26 06:29:12 yaohui Exp $
--
------------------------------------------------------------------------------

    MAIPU-VRF-MIB DEFINITIONS ::= BEGIN

    IMPORTS
        MODULE-IDENTITY, OBJECT-TYPE,
        Integer32, Counter64 ,Counter32,IpAddress
        	FROM SNMPv2-SMI
        DisplayString, TruthValue ,RowStatus
        	FROM SNMPv2-TC
        MODULE-COMPLIANCE, OBJECT-GROUP
        	FROM SNMPv2-CONF
        mpMgmt
        	FROM MAIPU-SMI;

    mVrfMib MODULE-IDENTITY
        LAST-UPDATED    "0405271003Z"
        ORGANIZATION    "Maipu (Sichuan ) Communication Technology Co.,Ltd"
        CONTACT-INFO    "Maipu (Sichuan ) Communication Technology Co.,Ltd
                         E-mail: maipu2@sc.cninfo.net"
        DESCRIPTION     "Maipu Switch Enterprise MIB definition."
        REVISION        "0405271003Z"
		DESCRIPTION     "Initial MIB creation."

        ::= { mpMgmt 89 }

mVrfMibObjects OBJECT IDENTIFIER ::= { mVrfMib 1 }

------------------------------------------------------------------------------
--  Textual Conventions (i.e., these do not affect object encoding):
------------------------------------------------------------------------------


------------------------------------------------------------------------------
--  define groups in SYS-IF-MIB
------------------------------------------------------------------------------
    mVrfGlobal           OBJECT IDENTIFIER ::= { mVrfMibObjects 1 }
    mVrfConfiguration1        OBJECT IDENTIFIER ::= { mVrfMibObjects 2 }
    mVrfConfiguration2	        OBJECT IDENTIFIER ::= { mVrfMibObjects 3 }

------------------------------------------------------------------------------
--  mIfGlobal - Global information Group
------------------------------------------------------------------------------


------------------------------------------------------------------------------
--  mVrfConfiguration1 -  Vrf Configuration information Group
------------------------------------------------------------------------------
    mVrfConfiguration1Table OBJECT-TYPE
	    SYNTAX     	SEQUENCE OF SysVrfConfiguration1Entry
	    MAX-ACCESS 	not-accessible
	    STATUS     	current
	    DESCRIPTION
	    	"The table containing information of the designed unit."
	    ::= { mVrfConfiguration1 1 }

	mVrfConfiguration1Entry OBJECT-TYPE
	    SYNTAX     	SysVrfConfiguration1Entry
	    MAX-ACCESS 	not-accessible
	    STATUS     	current
	    DESCRIPTION
	    	"Information about the status of one management domain."
	    INDEX { mVrfConfiguration1NameIndex }
	    ::= { mVrfConfiguration1Table 1 }

	SysVrfConfiguration1Entry ::= SEQUENCE {
	    mVrfConfiguration1Name          	    DisplayString,
	    mVrfConfiguration1RouteDistinguisher	DisplayString,
	    mVrfConfiguration1Description	        DisplayString
	}

	mVrfConfiguration1Name OBJECT-TYPE
        SYNTAX 		DisplayString (SIZE (0..32))
        MAX-ACCESS 	not-accessible
        STATUS 		current
        DESCRIPTION
            "VRF名称"
        ::= { mVrfConfiguration1Entry 1 }

	mVrfConfiguration1RouteDistinguisher OBJECT-TYPE
        SYNTAX 		DisplayString (SIZE (0..27))
        MAX-ACCESS 	read-create
        STATUS 		current
        DESCRIPTION
            " "
        ::= { mVrfConfiguration1Entry 2 }

	mVrfConfiguration1Description OBJECT-TYPE
	    SYNTAX  	DisplayString (SIZE (0..50))
	    MAX-ACCESS 	read-create
	    STATUS 		current
	    DESCRIPTION
	       	"VRF配置描述"
	    ::= { mVrfConfiguration1Entry 3 }


------------------------------------------------------------------------------
--  mVrfConfiguration2 -  Vrf Configuration information Group
------------------------------------------------------------------------------
    mVrfConfiguration2Table OBJECT-TYPE
	    SYNTAX     	SEQUENCE OF SysVrfConfiguration2Entry
	    MAX-ACCESS 	not-accessible
	    STATUS     	current
	    DESCRIPTION
	    	"The table containing information of the designed unit."
	    ::= { mVrfConfiguration2 1 }

	mVrfConfiguration2Entry OBJECT-TYPE
	    SYNTAX     	SysVrfConfiguration2Entry
	    MAX-ACCESS 	not-accessible
	    STATUS     	current
	    DESCRIPTION
	    	"Information about the status of one management domain."
	    INDEX { mVrfConfiguration2Name, mVrfConfiguration2Type, mVrfConfiguration2RouteDistinguisher}
	    ::= { mVrfConfiguration2Table 1 }

	SysVrfConfiguration2Entry ::= SEQUENCE {
	    mVrfConfiguration2Name	     	    DisplayString,
        mVrfConfiguration2Type              INTEGER,
	    mVrfConfiguration2RouteDistinguisher	DisplayString
	}

    mVrfConfiguration2Name OBJECT-TYPE
        SYNTAX 		DisplayString (SIZE (0..32))
        MAX-ACCESS 	not-accessible
        STATUS 		current
        DESCRIPTION
            "VRF名称"
        ::= { mVrfConfiguration2Entry 1 }

    mVrfConfiguration2Type OBJECT-TYPE
	    SYNTAX  	INTEGER
        			{
        				import(1),
        				export(2),
						both(3)
        			}
	    MAX-ACCESS 	read-create
	    STATUS 		current
	    DESCRIPTION
	       	"VRF类型"
	    ::= { mVrfConfiguration1Entry 3 }

	mVrfConfiguration2RouteDistinguisher OBJECT-TYPE
        SYNTAX 		DisplayString (SIZE (0..27))
        MAX-ACCESS 	read-create
        STATUS 		current
        DESCRIPTION
            " "
        ::= { mVrfConfiguration2Entry 3 }


END


-- ============================================================================
-- $Log: mVrfMib.mi2,v $
-- Revision 1.1  2004/08/26 06:29:12  yaohui
-- add files
--
-- Revision 1.1  2004/06/24 07:48:39  liudf
-- #VRSP-3897: Support VRF
--
-- Revision 1.1  2004/5/27 10:30:00  zhaoying
-- resolve compile problem #3151
--
-- ============================================================================
