--*****************************************************************
-- MAIPU-SYSTEM-MIB
--
-- lvjian 2006-10-25
--
-- *****************************************************************
--




MAIPU-SYSTEM-MIB DEFINITIONS ::= BEGIN

IMPORTS
        MODULE-IDENTITY, OBJECT-TYPE, NOTIFICATION-TYPE, enterprises, Counter32, Gauge32,
          Integer32, Unsigned32, TimeTicks,IpAddress,Counter64
            FROM SNMPv2-SMI
        TEXTUAL-CONVENTION, TruthValue, MacAddress,
          RowStatus, DisplayString, DateAndTime
            FROM SNMPv2-TC
        MODULE-COMPLIANCE, OBJECT-GROUP
            FROM SNMPv2-CONF
        mpMgmt
            FROM MAIPU-SMI;

mpSystemMib 							OBJECT IDENTIFIER ::= {mpMgmt 600}


mpSysInfoMib							OBJECT IDENTIFIER ::= {mpSystemMib 1}
mpSysMpuMib								OBJECT IDENTIFIER ::= {mpSystemMib 2}
mpSysUnitMib							OBJECT IDENTIFIER ::= {mpSystemMib 3}
mpSysSiuMib								OBJECT IDENTIFIER ::= {mpSystemMib 4}
mpSysSubSlotMib							OBJECT IDENTIFIER ::= {mpSystemMib 5}
mpSysPortMib    						OBJECT IDENTIFIER ::= {mpSystemMib 6}
mpSysPowerMib 							OBJECT IDENTIFIER ::= {mpSystemMib 7}
mpSysFanCardMib 						OBJECT IDENTIFIER ::= {mpSystemMib 8}
mpSysCpuMib 							OBJECT IDENTIFIER ::= {mpSystemMib 9}
mpSysMemoryMib 							OBJECT IDENTIFIER ::= {mpSystemMib 10}
mpSysWorkModMib                         OBJECT IDENTIFIER ::= {mpSystemMib 11}





--mpuInfoTable MPU卡信息表

mpuInfoTable    OBJECT-TYPE
    SYNTAX  SEQUENCE OF mpuInfoEntry
    ACCESS  not-accessible
    STATUS  current
    DESCRIPTION
            "MPU卡信息表。"
    ::= {mpSysMpuMib 1}

mpuInfoEntry  OBJECT-TYPE
    SYNTAX  mpuInfoEntry
    ACCESS  not-accessible
    STATUS  current
    DESCRIPTION
            "MPU卡信息表条目。"
    INDEX   {mpuIndex}
    ::= {mpuInfoTable 1}

mpuIndex  OBJECT-TYPE
    SYNTAX  INTEGER
    ACCESS  read-only
    STATUS  current
    DESCRIPTION
            "MPU卡索引，即插槽号绝对值。"
    ::= {mpuInfoEntry 1}

mpuType  OBJECT-TYPE
    SYNTAX  INTEGER
    ACCESS  read-only
    STATUS  current
    DESCRIPTION
            "MPU卡类型。"
    ::= {mpuInfoEntry 2}

mpuDescription  OBJECT-TYPE
    SYNTAX  DISPLASTRING(SIZE (0..128))
    ACCESS  read-write
    STATUS  current
    DESCRIPTION
            "MPU卡描述，最大长度128个字节。"
    ::= {mpuInfoEntry 3}

mpuSerialNumber  OBJECT-TYPE
    SYNTAX  DISPLASTRING(SIZE (0..31))
    ACCESS  read-only
    STATUS  current
    DESCRIPTION
            "MPU卡序列号，最大长度32个字节。"
    ::= {mpuInfoEntry 4}

mpuSoftwareVersion  OBJECT-TYPE
    SYNTAX  DISPLASTRING(SIZE (0..31))
    ACCESS  read-only
    STATUS  current
    DESCRIPTION
            "MPU卡软件版本。最大长度32个字节。"
    ::= {mpuInfoEntry 5}

mpuHardwareVersion  OBJECT-TYPE
    SYNTAX  DISPLASTRING(SIZE (0..255))
    ACCESS  read-only
    STATUS  current
    DESCRIPTION
            "MPU卡硬件版本，最大长度255个字节。"
    ::= {mpuInfoEntry 6}

mpuFPGAVersion  OBJECT-TYPE
    SYNTAX  DISPLASTRING(SIZE (0..255))
    ACCESS  read-only
    STATUS  current
    DESCRIPTION
            "MPU卡FPGA版本，最大长度255个字节。"
    ::= {mpuInfoEntry 7}


mpuMonitorVersion  OBJECT-TYPE
    SYNTAX  DISPLASTRING(SIZE (0..31))
    ACCESS  read-only
    STATUS  current
    DESCRIPTION
            "MPU卡Monitor版本，最大长度32个字节。"
    ::= {mpuInfoEntry 8}

mpuCMMSoftwareVersion  OBJECT-TYPE
    SYNTAX  DISPLASTRING(SIZE (0..31))
    ACCESS  read-only
    STATUS  current
    DESCRIPTION
            "MPU卡CMM软件版本，最大长度32个字节。"
    ::= {mpuInfoEntry 9}

mpuCMMHardwareVersion  OBJECT-TYPE
    SYNTAX  DISPLASTRING(SIZE (0..31))
    ACCESS  read-only
    STATUS  current
    DESCRIPTION
            "MPU卡CMM硬件版本，最大长度32个字节。"
    ::= {mpuInfoEntry 10}

mpuCMMMonitorVersion  OBJECT-TYPE
    SYNTAX  DISPLASTRING(SIZE (0..31))
    ACCESS  read-only
    STATUS  current
    DESCRIPTION
            "MPU卡CMMMonitor版本，最大长度32个字节。"
    ::= {mpuInfoEntry 11}

mpuFlashTotalBytes  OBJECT-TYPE
    SYNTAX  Gauge32
    ACCESS  read-only
    STATUS  current
    DESCRIPTION
            "MPU卡flash总字节数(单位字节)。"
    ::= {mpuInfoEntry 12}

mpuFlashLeftBytes  OBJECT-TYPE
    SYNTAX  Gauge32
    ACCESS  read-only
    STATUS  current
    DESCRIPTION
            "MPU卡flash剩余字节数(单位字节)。"
    ::= {mpuInfoEntry 13}

mpuWorkingMode OBJECT-TYPE
    SYNTAX  INTEGER{
    				master(1),
    				slave(2),
    				doubleRouter(3)
    				}
    ACCESS  read-only
    STATUS  current
    DESCRIPTION
            "MPU卡工作模式。(1主卡 2从卡 3双路由器)"
    ::= {mpuInfoEntry 14}

mpuOnlineStatus OBJECT-TYPE
    SYNTAX  INTEGER{
    				online(1),
    				offline(2)
    				}
    ACCESS  read-only
    STATUS  current
    DESCRIPTION
            "MPU卡物理在线状态。(1在线 2不在线)"
    ::= {mpuInfoEntry 15}

mpuWorkingStatus  OBJECT-TYPE
    SYNTAX  INTEGER{
    				on(1),
    				off(2)
    				}
    ACCESS  read-only
    STATUS  current
    DESCRIPTION
            "MPU卡工作状态。(1 工作，2未工作)"
    ::= {mpuInfoEntry 16}

mpuPowerStatus OBJECT-TYPE
    SYNTAX  INTEGER{
    				on(1),
    				off(2)
    				}
    ACCESS  read-only
    STATUS  current
    DESCRIPTION
            "MPU卡加电状态。(1已加电 2未加电)"
    ::= {mpuInfoEntry 17}

mpuSynchronizationStatus OBJECT-TYPE
    SYNTAX  INTEGER{
    				batchSync(1),
    				realtimeSync(2),
    				noSlave(3),
    				abnormal(4)
    				}
    ACCESS  read-only
    STATUS  current
    DESCRIPTION
            "MPU卡同步状态。(1完全同步(批量同步) 2实时同步 3从卡空缺 4异常)"
    ::= {mpuInfoEntry 18}

mpuCFStatus OBJECT-TYPE
    SYNTAX  INTEGER{
    				online(1),
    				offline(2)
    				}
    ACCESS  read-only
    STATUS  current
    DESCRIPTION
            "MPUCF卡在位状态。(1在位2不在位)"
    ::= {mpuInfoEntry 19}

mpuTemperature  OBJECT-TYPE
    SYNTAX  INTEGER
    ACCESS  read-only
    STATUS  current
    DESCRIPTION
            "MPU卡温度。(单位 摄氏度)"
    ::= {mpuInfoEntry 20}

mpuSubSlotNumber OBJECT-TYPE
    SYNTAX  INTEGER
    ACCESS  read-only
    STATUS  current
    DESCRIPTION
            "MPU卡上的子槽位数。"
    ::= {mpuInfoEntry 21}

--mpuInfoTable end

-- unitInfoTable LPU与SFU信息表

unitInfoTable    OBJECT-TYPE
    SYNTAX  SEQUENCE OF unitInfoEntry
    ACCESS  not-accessible
    STATUS  current
    DESCRIPTION
            "LPU与SFU信息表。"
    ::= {mpSysUnitMib 1}

unitInfoEntry  OBJECT-TYPE
    SYNTAX  unitInfoEntry
    ACCESS  not-accessible
    STATUS  current
    DESCRIPTION
            "LPU与SFU信息表条目。"
    INDEX   {unitIndex}
    ::= {unitInfoTable 1}

unitIndex  OBJECT-TYPE
    SYNTAX  INTEGER
    ACCESS  read-only
    STATUS  current
    DESCRIPTION
            "LPU或SFU卡索引，即插槽号绝对值。"
    ::= {unitInfoEntry 1}

unitType  OBJECT-TYPE
    SYNTAX  INTEGER
    ACCESS  read-only
    STATUS  current
    DESCRIPTION
            "lpu或sfu卡类型。629477376 sfu-a,629547009 sfu-b,591949824 sfu-c,591953921 sfu-d,629227544 24GET(四代),629227800 24GEF(四代),612451120 24GET+24GEF(四代),629227568 48GET(四代),629227824 48GEF(四代),629354754 2XGE(四代),629354756 4XGE(四代),629354760 8XGE(四代),591481112 24GEFHC,591480856 24GETHC,592206616 16GET8CGEH,591481136 48GEFHC,591480880 48GETHC,592210714 24GEF2XGEH,591630336 NTA"
    ::= {unitInfoEntry 2}

unitDescription  OBJECT-TYPE
    SYNTAX  DISPLASTRING(SIZE (0..128))
    ACCESS  read-write
    STATUS  current
    DESCRIPTION
            "lpu或sfu卡描述，最大长度128个字节。"
    ::= {unitInfoEntry 3}

unitSerialNumber  OBJECT-TYPE
    SYNTAX  DISPLASTRING(SIZE (0..31))
    ACCESS  read-only
    STATUS  current
    DESCRIPTION
            "lpu或sfu卡序列号，最大长度32个字节。"
    ::= {unitInfoEntry 4}

unitSoftwareVersion  OBJECT-TYPE
    SYNTAX  DISPLASTRING(SIZE (0..31))
    ACCESS  read-only
    STATUS  current
    DESCRIPTION
            "lpu或sfu卡软件版本。最大长度32个字节。"
    ::= {unitInfoEntry 5}

unitHardwareVersion  OBJECT-TYPE
    SYNTAX  DISPLASTRING(SIZE (0..255))
    ACCESS  read-only
    STATUS  current
    DESCRIPTION
            "lpu或sfu卡硬件版本，最大长度255个字节。"
    ::= {unitInfoEntry 6}

unitFPGAVersion  OBJECT-TYPE
    SYNTAX  DISPLASTRING(SIZE (0..255))
    ACCESS  read-only
    STATUS  current
    DESCRIPTION
            "lpu或sfu卡FPGA版本，最大长度255个字节。"
    ::= {unitInfoEntry 7}

unitCMMSoftwareVersion  OBJECT-TYPE
    SYNTAX  DISPLASTRING(SIZE (0..31))
    ACCESS  read-only
    STATUS  current
    DESCRIPTION
            "lpu或sfu卡CMM软件版本，最大长度32个字节。"
    ::= {unitInfoEntry 8}

unitCMMHardwareVersion  OBJECT-TYPE
    SYNTAX  DISPLASTRING(SIZE (0..31))
    ACCESS  read-only
    STATUS  current
    DESCRIPTION
            "lpu或sfu卡CMM更件版本，最大长度32个字节。"
    ::= {unitInfoEntry 9}

unitCMMMonitorVersion  OBJECT-TYPE
    SYNTAX  DISPLASTRING(SIZE (0..31))
    ACCESS  read-only
    STATUS  current
    DESCRIPTION
            "LPU或SFU卡CMMMonitor版本，最大长度32个字节。"
    ::= {unitInfoEntry 10}

unitOnlineStatus OBJECT-TYPE
    SYNTAX  INTEGER{
    				online(1),
    				offline(2)
    				}
    ACCESS  read-only
    STATUS  current
    DESCRIPTION
            "lpu或sfu卡在线状态。(1在线 2不在线)"
    ::= {unitInfoEntry 11}

unitWorkingStatus  OBJECT-TYPE
    SYNTAX  INTEGER{
    				on(1),
    				off(2)
    				}
    ACCESS  read-only
    STATUS  current
    DESCRIPTION
            "lpu或sfu卡工作状态。(1 工作，2未工作)"
    ::= {unitInfoEntry 12}

unitPowerStatus OBJECT-TYPE
    SYNTAX  INTEGER{
    				on(1),
    				off(2)
    				}
    ACCESS  read-only
    STATUS  current
    DESCRIPTION
            "lpu或sfu卡加电状态。(1已加电 2未加电)"
    ::= {unitInfoEntry 13}


-- lpuInfoTable end

-- siuInfoTable SIU信息表

siuInfoTable    OBJECT-TYPE
    SYNTAX  SEQUENCE OF siuInfoEntry
    ACCESS  not-accessible
    STATUS  current
    DESCRIPTION
            "siu信息表。"
    ::= {mpSysSiuMib 1}

siuInfoEntry  OBJECT-TYPE
    SYNTAX  siuInfoEntry
    ACCESS  not-accessible
    STATUS  current
    DESCRIPTION
            "siu信息表条目。"
    INDEX   {siuIndex}
    ::= {siuInfoTable 1}

siuIndex  OBJECT-TYPE
    SYNTAX  INTEGER
    ACCESS  read-only
    STATUS  current
    DESCRIPTION
            "siu卡索引，即插槽号绝对值。"
    ::= {siuInfoEntry 1}

siuDescription  OBJECT-TYPE
    SYNTAX  DISPLASTRING(SIZE (0..128))
    ACCESS  read-write
    STATUS  current
    DESCRIPTION
            "siu卡描述，最大长度128个字节。"
    ::= {siuInfoEntry 2}

siuSerialNumber  OBJECT-TYPE
    SYNTAX  DISPLASTRING(SIZE (0..31))
    ACCESS  read-only
    STATUS  current
    DESCRIPTION
            "siu卡序列号，最大长度32个字节。"
    ::= {siuInfoEntry 3}

siuCMMSoftwareVersion  OBJECT-TYPE
    SYNTAX  DISPLASTRING(SIZE (0..31))
    ACCESS  read-only
    STATUS  current
    DESCRIPTION
            "siu卡软件版本。最大长度32个字节。"
    ::= {siuInfoEntry 4}

siuCMMHardwareVersion  OBJECT-TYPE
    SYNTAX  DISPLASTRING(SIZE (0..31))
    ACCESS  read-only
    STATUS  current
    DESCRIPTION
            "siu卡硬件版本，最大长度32个字节。"
    ::= {siuInfoEntry 5}

siuCMMMonitorVersion  OBJECT-TYPE
    SYNTAX  DISPLASTRING(SIZE (0..31))
    ACCESS  read-only
    STATUS  current
    DESCRIPTION
            "SIU卡Monitor版本，最大长度32个字节。"
    ::= {siuInfoEntry 6}

siuWorkingStatus  OBJECT-TYPE
    SYNTAX  INTEGER{
    				on(1),
    				off(2)
    				}
    ACCESS  read-only
    STATUS  current
    DESCRIPTION
            "siu卡工作状态。(1 工作，2未工作)"
    ::= {siuInfoEntry 7}

siuAlarmStatus  OBJECT-TYPE
    SYNTAX  TruthValue
    ACCESS  read-only
    STATUS  current
    DESCRIPTION
            "电源告警状态。(1 有告警, 2 无告警)"
    ::= {siuInfoEntry 8}


-- siuInfoTable end



-- subSlotTable  接口属性表

subSlotTable    OBJECT-TYPE
    SYNTAX  SEQUENCE OF subSlotEntry
    ACCESS  not-accessible
    STATUS  current
    DESCRIPTION
            "端口属性表。"
    ::= {mpSysSubSlotMib 1}

subSlotEntry  OBJECT-TYPE
    SYNTAX  subSlotEntry
    ACCESS  not-accessible
    STATUS  current
    DESCRIPTION
            "端口属性表条目。"
    INDEX   {subSlotParentIndex,subSlotIndex}
    ::= {subSlotTable 1}

subSlotParentIndex  OBJECT-TYPE
    SYNTAX  INTEGER
    ACCESS  read-only
    STATUS  current
    DESCRIPTION
            "子插槽所在的父插槽号。"
    ::= {subSlotEntry 1}

subSlotIndex  OBJECT-TYPE
    SYNTAX  INTEGER
    ACCESS  read-only
    STATUS  current
    DESCRIPTION
            "子插槽号。"
    ::= {subSlotEntry 2}

subSlotCardType  OBJECT-TYPE
    SYNTAX  INTEGER
    ACCESS  read-only
    STATUS  current
    DESCRIPTION
            "子插槽上插的板卡类型。"
    ::= {subSlotEntry 3}

subSlotPortNumber  OBJECT-TYPE
    SYNTAX  INTEGER
    ACCESS  read-only
    STATUS  current
    DESCRIPTION
            "子插槽上的端口数目"
    ::= {subSlotEntry 4}

subSlotOnlineStatus OBJECT-TYPE
    SYNTAX  INTEGER{
    				online(1),
    				offline(2)
    				}
    ACCESS  read-only
    STATUS  current
    DESCRIPTION
            "子插槽物理在线状态。(1在线 2不在线)"
    ::= {subSlotEntry 5}

-- subSlotTable  end


-- portInfoTable  端口信息表

portInfoTable    OBJECT-TYPE
    SYNTAX  SEQUENCE OF portInfoEntry
    ACCESS  not-accessible
    STATUS  current
    DESCRIPTION
            "端口属性表。"
    ::= {mpSysPortMib 1}

portInfoEntry  OBJECT-TYPE
    SYNTAX  portInfoEntry
    ACCESS  not-accessible
    STATUS  current
    DESCRIPTION
            "端口属性表条目。"
    INDEX   {portSlotIndex,portSubSlotIndex,portIndex}
    ::= {portInfoTable 1}

portSlotIndex  OBJECT-TYPE
    SYNTAX  INTEGER
    ACCESS  read-only
    STATUS  current
    DESCRIPTION
            "端口所在板卡的索引，即插槽号绝对值。"
    ::= {portInfoEntry 1}

portSubSlotIndex  OBJECT-TYPE
    SYNTAX  INTEGER
    ACCESS  read-only
    STATUS  current
    DESCRIPTION
            "端口所在子插槽板卡的索引。"
    ::= {portInfoEntry 2}

portIndex  OBJECT-TYPE
    SYNTAX  INTEGER
    ACCESS  read-only
    STATUS  current
    DESCRIPTION
            "端口索引。"
    ::= {portInfoEntry 3}

portType  OBJECT-TYPE
    SYNTAX  INTEGER{
    				copper(1),
    				fiber(2)
    				}
    ACCESS  read-only
    STATUS  current
    DESCRIPTION
            "端口类型。1 电口 2光口"
    ::= {portInfoEntry 4}

portLinkStatus  OBJECT-TYPE
    SYNTAX  INTEGER{
    				up(1),
    				down(2),
    				loop(3)
    				}
    ACCESS  read-only
    STATUS  current
    DESCRIPTION
            "端口状态。(1 up 2 down 3 loop)"
    ::= {portInfoEntry 5}

portOnlineStatus OBJECT-TYPE
    SYNTAX  INTEGER{
    				online(1),
    				offline(2)
    				}
    ACCESS  read-only
    STATUS  current
    DESCRIPTION
            "端口物理在线状态。(1在线 2不在线)"
    ::= {portInfoEntry 6}

-- portInfoTable  end


-- powerInfoTable   电源表

powerInfoTable    OBJECT-TYPE
    SYNTAX  SEQUENCE OF powerInfoEntry
    ACCESS  not-accessible
    STATUS  current
    DESCRIPTION
            "电源表。"
    ::= {mpSysPowerMib 1}

powerInfoEntry  OBJECT-TYPE
    SYNTAX  powerInfoEntry
    ACCESS  not-accessible
    STATUS  current
    DESCRIPTION
            "电源表条目。"
    INDEX   {powerIndex}
    ::= {powerInfoTable 1}

powerIndex  OBJECT-TYPE
    SYNTAX  INTEGER
    ACCESS  read-only
    STATUS  current
    DESCRIPTION
            "电源索引，即插槽号绝对值。"
    ::= {powerInfoEntry 1}

powerType  OBJECT-TYPE
    SYNTAX  INTEGER{
            alternating-non-intelligent(1),
            direct-non-intelligent(2),
            alternating-intelligent(3),
            direct-intelligent(4)
            }
    ACCESS  read-only
    STATUS  current
    DESCRIPTION
            "电源类型。 (1交流非智能 2直流非智能 3交流智能 4直流智能)"
    ::= {powerInfoEntry 2}

powerDescription  OBJECT-TYPE
    SYNTAX  DISPLASTRING(SIZE (0..128))
    ACCESS  read-write
    STATUS  current
    DESCRIPTION
            "电源描述，最大长度128个字节"
    ::= {powerInfoEntry 3}

powerSerialNumber  OBJECT-TYPE
    SYNTAX  DISPLASTRING(SIZE (0..31))
    ACCESS  read-only
    STATUS  current
    DESCRIPTION
            "电源序列号，最大长度32个字节。"
    ::= {powerInfoEntry 4}

powerCMMSoftwareVersion  OBJECT-TYPE
    SYNTAX  DISPLASTRING(SIZE (0..31))
    ACCESS  read-only
    STATUS  current
    DESCRIPTION
            "电源CMM软件版本，最大长度32个字节。"
    ::= {powerInfoEntry 5}

powerCMMHardwareVersion  OBJECT-TYPE
    SYNTAX  DISPLASTRING(SIZE (0..31))
    ACCESS  read-only
    STATUS  current
    DESCRIPTION
            "电源CMM硬件版本，最大长度32个字节。"
    ::= {powerInfoEntry 6}

powerCMMMonitorVersion  OBJECT-TYPE
    SYNTAX  DISPLASTRING(SIZE (0..31))
    ACCESS  read-only
    STATUS  current
    DESCRIPTION
            "电源Monitor版本，最大长度32个字节。"
    ::= {powerInfoEntry 7}

powerOnlineStatus  OBJECT-TYPE
    SYNTAX  INTEGER{
    				online(1),
            offline(2)
            }
    ACCESS  read-only
    STATUS  current
    DESCRIPTION
            "电源物理在线状态。(1 在线, 2 不在线)"
    ::= {powerInfoEntry 8}

powerWorkingStatus  OBJECT-TYPE
    SYNTAX  INTEGER{
    				on(1),
            off(2)
            }
    ACCESS  read-only
    STATUS  current
    DESCRIPTION
            "电源工作状态。(1 工作, 2 未工作)"
    ::= {powerInfoEntry 9}

powerAlarmStatus  OBJECT-TYPE
    SYNTAX  INTEGER{
						normal(1),
						alarm(2)
            }
    ACCESS  read-only
    STATUS  current
    DESCRIPTION
            "电源告警状态。(1 正常, 2 告警)"
    ::= {powerInfoEntry 10}

powerVoltageInput  OBJECT-TYPE
    SYNTAX  INTEGER
    UNITS   "mV"
    ACCESS  read-only
    STATUS  current
    DESCRIPTION
            "电源输入电压。(单位：mv)"
    ::= {powerInfoEntry 11}

powerVoltageOutput  OBJECT-TYPE
    SYNTAX  INTEGER
    UNITS   "mV"
    ACCESS  read-only
    STATUS  current
    DESCRIPTION
            "电源输出电压。(单位：mv)"
    ::= {powerInfoEntry 12}

powerCurrentInput  OBJECT-TYPE
    SYNTAX  INTEGER
    UNITS   "mA"
    ACCESS  read-only
    STATUS  current
    DESCRIPTION
            "电源输出电流。(单位：mA)"
    ::= {powerInfoEntry 13}

powerCurrentOutput OBJECT-TYPE
    SYNTAX  INTEGER
		UNITS   "mA"
    ACCESS  read-only
    STATUS  current
    DESCRIPTION
            "电源输出电流。(单位：mA)"
    ::= {powerInfoEntry 14}

-- powerInfoTable end


-- fanCardInfoTable   风扇卡表

fanCardInfoTable    OBJECT-TYPE
    SYNTAX  SEQUENCE OF fanCardInfoEntry
    ACCESS  not-accessible
    STATUS  current
    DESCRIPTION
            "风扇卡表。"
    ::= {mpSysFanCardMib 1}

fanCardInfoEntry  OBJECT-TYPE
    SYNTAX  fanCardInfoEntry
    ACCESS  not-accessible
    STATUS  current
    DESCRIPTION
            "风扇卡表条目。"
    INDEX   {fanCardIndex}
    ::= {fanCardInfoTable 1}

fanCardIndex  OBJECT-TYPE
    SYNTAX  INTEGER
    ACCESS  read-only
    STATUS  current
    DESCRIPTION
            "风扇卡索引，即插槽号绝对值。"
    ::= {fanCardInfoEntry 1}

fanCardDescription  OBJECT-TYPE
    SYNTAX  DISPLASTRING(SIZE (0..128))
    ACCESS  read-write
    STATUS  current
    DESCRIPTION
            "风扇卡描述，最大长度128个字节"
    ::= {fanCardInfoEntry 2}

fanCardSerialNumber  OBJECT-TYPE
    SYNTAX  DISPLASTRING(SIZE (0..31))
    ACCESS  read-only
    STATUS  current
    DESCRIPTION
            "风扇卡序列号，最大长度32个字节。"
    ::= {fanCardInfoEntry 3}

fanCardCMMSoftwareVersion  OBJECT-TYPE
    SYNTAX  DISPLASTRING(SIZE (0..31))
    ACCESS  read-only
    STATUS  current
    DESCRIPTION
            "风扇卡CMM软件版本，最大长度32个字节。"
    ::= {fanCardInfoEntry 4}

fanCardCMMHardwareVersion  OBJECT-TYPE
    SYNTAX  DISPLASTRING(SIZE (0..31))
    ACCESS  read-only
    STATUS  current
    DESCRIPTION
            "风扇卡CMM硬件版本，最大长度32个字节。"
    ::= {fanCardInfoEntry 5}

fanCardCMMMonitorVersion  OBJECT-TYPE
    SYNTAX  DISPLASTRING(SIZE (0..31))
    ACCESS  read-only
    STATUS  current
    DESCRIPTION
            "风扇卡CMMMonitor版本，最大长度32个字节。"
    ::= {fanCardInfoEntry 6}

fanCardOnlineStatus  OBJECT-TYPE
    SYNTAX  INTEGER{
    				online(1),
            offline(2)
            }
    ACCESS  read-only
    STATUS  current
    DESCRIPTION
            "风扇卡物理在线状态。(1 在线, 2 不在线)"
    ::= {fanCardInfoEntry 7}

fanCardWorkingStatus  OBJECT-TYPE
    SYNTAX  INTEGER{
    				on(1),
            off(2)
            }
    ACCESS  read-only
    STATUS  current
    DESCRIPTION
            "风扇卡工作状态。(1 工作, 2 未工作)"
    ::= {fanCardInfoEntry 8}

fanCardAlarmStatus  OBJECT-TYPE
    SYNTAX  INTEGER{
						normal(1),
						alarm(2)
            }
    ACCESS  read-only
    STATUS  current
    DESCRIPTION
            "风扇卡告警状态。(1 正常, 2 告警)"
    ::= {fanCardInfoEntry 9}

fanCardGrps  OBJECT-TYPE
    SYNTAX  INTEGER
    ACCESS  read-only
    STATUS  current
    DESCRIPTION
            "风扇卡的风扇组数。"
    ::= {fanCardInfoEntry 10}

fanCardNumPerGrp  OBJECT-TYPE
    SYNTAX  INTEGER
    ACCESS  read-only
    STATUS  current
    DESCRIPTION
            "风扇卡每组风扇的个数。"
    ::= {fanCardInfoEntry 11}


-- fanCardInfoTable  end

-- fanInfoTable   风扇表

fanInfoTable    OBJECT-TYPE
    SYNTAX  SEQUENCE OF fanInfoEntry
    ACCESS  not-accessible
    STATUS  current
    DESCRIPTION
            "风扇表。"
    ::= {mpSysFanCardMib 2}

fanInfoEntry  OBJECT-TYPE
    SYNTAX  fanInfoEntry
    ACCESS  not-accessible
    STATUS  current
    DESCRIPTION
            "风扇表条目。"
    INDEX   {fanCardIndex,fanIndex}
    ::= {fanInfoTable 1}

fanCardIndex  OBJECT-TYPE
    SYNTAX  INTEGER
    ACCESS  read-only
    STATUS  current
    DESCRIPTION
            "风扇所在风扇卡索引，即插槽号绝对值。"
    ::= {fanInfoEntry 1}

fanIndex  OBJECT-TYPE
    SYNTAX  INTEGER
    ACCESS  read-only
    STATUS  current
    DESCRIPTION
            "风扇索引，从第0组第0个风扇开始。"
    ::= {fanInfoEntry 2}


fanStatus  OBJECT-TYPE
    SYNTAX  INTEGER
    ACCESS  read-only
    STATUS  current
    DESCRIPTION
            "风扇状态息，1 OK,2 FAIL"
    ::= {fanInfoEntry 3}

fanSpeed  OBJECT-TYPE
    SYNTAX  INTEGER
    ACCESS  read-only
    STATUS  current
    DESCRIPTION
            "风扇速度，0代表最低速,7代表最高速。"
    ::= {fanInfoEntry 4}



-- fanInfoTable  end



-- cpuUtilizationTable  CPU利用率表

cpuUtilizationTable    OBJECT-TYPE
    SYNTAX  SEQUENCE OF cpuUtilizationEntry
    ACCESS  not-accessible
    STATUS  current
    DESCRIPTION
            "CPU利用率表。"
    ::= {mpSysCpuMib 1}

cpuUtilizationEntry  OBJECT-TYPE
    SYNTAX  cpuUtilizationEntry
    ACCESS  not-accessible
    STATUS  current
    DESCRIPTION
            "CPU利用率表条目。"
    INDEX   {cpuIndex,cpuCoreId}
    ::= {cpuUtilizationTable 1}

cpuIndex  OBJECT-TYPE
    SYNTAX  INTEGER
    ACCESS  read-only
    STATUS  current
    DESCRIPTION
            "CPU索引。"
    ::= {cpuUtilizationEntry 1}

cpuCoreId  OBJECT-TYPE
    SYNTAX  INTEGER
    ACCESS  read-only
    STATUS  current
    DESCRIPTION
            "CPU内核索引。"
    ::= {cpuUtilizationEntry 2}

cpuCoreUtilization   OBJECT-TYPE
    SYNTAX  Gauge32 (0..100)
    UNITS   "%"
    ACCESS  read-only
    STATUS  current
    DESCRIPTION
            "CPU内核利用率。(单位%)"
    ::= {cpuUtilizationEntry 3}

-- cpuUtilizationTable  end


-- cpuTemperatureTable  CPU温度表

cpuTemperatureTable    OBJECT-TYPE
    SYNTAX  SEQUENCE OF cpuTemperatureEntry
    ACCESS  not-accessible
    STATUS  current
    DESCRIPTION
            "CPU利用率表。"
    ::= {mpSysCpuMib 2}

cpuTemperatureEntry  OBJECT-TYPE
    SYNTAX  cpuTemperatureEntry
    ACCESS  not-accessible
    STATUS  current
    DESCRIPTION
            "CPU利用率表条目。"
    INDEX   {cpuIndex}
    ::= {cpuTemperatureTable 1}

cpuIndex  OBJECT-TYPE
    SYNTAX  INTEGER
    ACCESS  read-only
    STATUS  current
    DESCRIPTION
            "CPU索引。"
    ::= {cpuTemperatureEntry 1}

cpuTemperature  OBJECT-TYPE
    SYNTAX  INTEGER
    UNITS   "'C"
    ACCESS  read-only
    STATUS  current
    DESCRIPTION
            "CPU温度。(单位 摄氏度)"
    ::= {cpuTemperatureEntry 2}

-- cpuTempTable  end


-- memoryTable  内存表

memoryTable    OBJECT-TYPE
    SYNTAX  SEQUENCE OF memoryEntry
    ACCESS  not-accessible
    STATUS  current
    DESCRIPTION
            "内存表。"
    ::= {mpSysMemoryMib 1}

memoryEntry  OBJECT-TYPE
    SYNTAX  memoryEntry
    ACCESS  not-accessible
    STATUS  current
    DESCRIPTION
            "内存表条目。"
    INDEX   {memIndex}
    ::= {memoryTable 1}

memIndex  OBJECT-TYPE
    SYNTAX  INTEGER
    ACCESS  read-only
    STATUS  current
    DESCRIPTION
            "内存索引。"
    ::= {memoryEntry 1}


memBytesFree  OBJECT-TYPE
    SYNTAX  INTEGER
    ACCESS  read-only
    STATUS  current
    DESCRIPTION
            "空闲内存字节数。"
    ::= {memoryEntry 2}

memBlocksFree  OBJECT-TYPE
    SYNTAX  INTEGER
    ACCESS  read-only
    STATUS  current
    DESCRIPTION
            "空闲内存块数。"
    ::= {memoryEntry 3}

memAvgBlockSizeFree  OBJECT-TYPE
    SYNTAX  INTEGER
    ACCESS  read-only
    STATUS  current
    DESCRIPTION
            "空闲的内存块平均大小。"
    ::= {memoryEntry 4}

memMaxBlockSizeFree  OBJECT-TYPE
    SYNTAX  INTEGER
    ACCESS  read-only
    STATUS  current
    DESCRIPTION
            "最大空闲内存块。"
    ::= {memoryEntry 5}

memBytesAlloc  OBJECT-TYPE
    SYNTAX  INTEGER
    ACCESS  read-only
    STATUS  current
    DESCRIPTION
            "已分配内存字节数。"
    ::= {memoryEntry 6}

memBlocksAlloc  OBJECT-TYPE
    SYNTAX  INTEGER
    ACCESS  read-only
    STATUS  current
    DESCRIPTION
            "已分配内存块数。"
    ::= {memoryEntry 7}

memAvgBlockSizeAlloc  OBJECT-TYPE
    SYNTAX  INTEGER
    ACCESS  read-only
    STATUS  current
    DESCRIPTION
            "已分配的平均内存块大小。"
    ::= {memoryEntry 8}

memTotalBytes  OBJECT-TYPE
    SYNTAX  INTEGER
    ACCESS  read-only
    STATUS  current
    DESCRIPTION
            "内存总数。"
    ::= {memoryEntry 9}

memUtilization  OBJECT-TYPE
    SYNTAX  INTEGER(0..100)
    UNITS   "%"
    ACCESS  read-only
    STATUS  current
    DESCRIPTION
            "内存使用率。(单位%)"
    ::= {memoryEntry 10}

-- memoryTable  end


--mpSysInfo 系统信息

sysVoltage  OBJECT-TYPE
    SYNTAX  INTEGER
    UNITS   "mV"
    ACCESS  read-only
    STATUS  current
    DESCRIPTION
            "系统电压。(单位mV)"
    ::= {mpSysInfoMib 1}

sysCurrent  OBJECT-TYPE
    SYNTAX  INTEGER
    UNITS   "mA"
    ACCESS  read-only
    STATUS  current
    DESCRIPTION
            "系统电流。(单位mA)"
    ::= {mpSysInfoMib 2}



--mpSysInfo end



--mpSysWorkMod 系统工作模式

SysWorkMod  OBJECT-TYPE
    SYNTAX  INTEGER {
				   modeInvalid(1),
				   modeBigTable(2),
                              modeSmallTable(3),
                              modeBh01Standard(4),
                              modeBh01Mix(5)
            }


    ACCESS  read-only
    STATUS  current
    DESCRIPTION
            "系统当前工作模式。(1系统工作模式还没确定 2带TCAM的4代板卡 3不带TCAM的4代板卡 4全是3代板卡 5 三、四代板卡混合)"
    ::= {mpSysWorkModMib 1}



--mpSysWorkMod end


END
