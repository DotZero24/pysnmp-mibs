------------------------------------------------------------------------------
--
--  File         : sys.mi2
--  Description  :
--  Version      :
--  Date         : March 3, 2003
-- 	Copyright    : 2003 by maipu (sichuan) communication technology co.,ltd.
--					All rights reserved.
--
-- $Id:
--
------------------------------------------------------------------------------

------------------------------------------------------------------------------
MAIPU-POLICYROUTE-MIB DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress,
	RowStatus, DisplayString, DateAndTime
                                                 FROM SNMPv2-TC
        MODULE-COMPLIANCE, OBJECT-GROUP
        	FROM SNMPv2-CONF
        mpMgmt
        	FROM MAIPU-SMI
        ObjectName, ObjectSyntax, NetworkAddress
                FROM RFC1155-SMI;


routeMib            	OBJECT IDENTIFIER ::= { mpMgmt 81 }



policyRoute         	MODULE-IDENTITY
                    		LAST-UPDATED 	"0703071024Z"
                    		ORGANIZATION 	"四川迈普数据通信股份有限公司,
                    		             	 Maipu (Sichuan) Communication Technology Co. LTD."
                    		CONTACT-INFO
                    			"编 写 人:  ???
                    			 联系地址：四川省 成都市 高新区 九兴大道16号
                    			 邮    编：    610041
                    			 电    话：
                    			 传    真：
                    			 电子邮件： ????"
                    		DESCRIPTION
                      			""
                    		::= { routeMib  6 }

------------------------------------------------------------------------------
-- Textual Conventions
------------------------------------------------------------------------------
EnabledStatus ::= TEXTUAL-CONVENTION
    STATUS      current
    DESCRIPTION
        "A simple status value for the object."
    SYNTAX      INTEGER {
	enabled(1), disabled(2) }

------------------------------------------------------------------------------


policyRouteLocal    	OBJECT-TYPE
                    		SYNTAX  DisplayString(SIZE(0..31))
                    		MAX-ACCESS  read-write
                    		STATUS  current
                    		DESCRIPTION
                    			"The name of Route-Map used for local policy route."
                    		::= { policyRoute 1 }

policyRouteTable    	OBJECT-TYPE
                    		SYNTAX  SEQUENCE OF   PolicyRouteEntry
                    		MAX-ACCESS  not-accessible
                    		STATUS  current
                    		DESCRIPTION
                    			"Policy route used for packet forwarding"
                    		::= { policyRoute 2 }

policyRouteEntry    	OBJECT-TYPE
                    		SYNTAX  PolicyRouteEntry
                    		MAX-ACCESS  not-accessible
                    		STATUS  current
                    		DESCRIPTION
                    			"Policy route used for packet forwarding"
                    		INDEX  { policyRouteIfindex }
                    		::= { policyRouteTable 1 }

PolicyRouteEntry    	::= SEQUENCE {
                    			policyRouteIfindex     Unsigned32,
                    			policyRouteRoutemap    DisplayString,
                    			policyRouteCache       EnabledStatus,
                    			policyRouteRowStatus   RowStatus
                    	             }


policyRouteIfindex  	OBJECT-TYPE
                    		SYNTAX  Unsigned32
                    		MAX-ACCESS  not-accessible
                    		STATUS  current
                    		DESCRIPTION
                    			"The interface configured PBR."
                    		::= { policyRouteEntry 1 }

policyRouteRoutemap 	OBJECT-TYPE
                    		SYNTAX  DisplayString(SIZE(0..31))
                    		MAX-ACCESS  read-write
                    		STATUS  current
                    		DESCRIPTION
                    			"PBR used Route-Map."
                    		::= { policyRouteEntry 2 }

policyRouteCache    	OBJECT-TYPE
                    		SYNTAX  EnabledStatus
                    		MAX-ACCESS  read-write
                    		STATUS  current
                    		DESCRIPTION
                    			"PBR cache."
                    		::= { policyRouteEntry 3 }

policyRouteRowStatus	OBJECT-TYPE
                    		SYNTAX  RowStatus
                    		MAX-ACCESS  read-create
                    		STATUS  current
                    		DESCRIPTION
                    			""
                    		::= { policyRouteEntry 4 }



END
------------------------------------------------------------------------------
-- ============================================================================
-- $Log: policyRoute.mib,v $
-- Revision 1.1  2010/06/21 11:18:46  liyh
-- first commit
--
-- Revision 1.1.2.2  2007/04/20 03:12:59  linmao
-- MYPOWER-4050: fix bug of local policy MIB
--
-- Revision 1.1.2.1  2007/03/14 03:33:36  linmao
-- MYPOWER-3981: PBR support SNMP
--
--
--
-- ============================================================================
