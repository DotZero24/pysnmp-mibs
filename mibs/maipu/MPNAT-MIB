MPNAT-MIB DEFINITIONS ::= BEGIN

IMPORTS
        MODULE-IDENTITY, OBJECT-TYPE, NOTIFICATION-TYPE, enterprises, Counter32, Gauge32,
          Integer32, Unsigned32, TimeTicks,IpAddress,Counter64
            FROM SNMPv2-SMI
        TEXTUAL-CONVENTION, TruthValue, MacAddress,
          RowStatus, DisplayString, DateAndTime
            FROM SNMPv2-TC
        MODULE-COMPLIANCE, OBJECT-GROUP
            FROM SNMPv2-CONF
        mpMgmt
            FROM MAIPU-SMI;

mpNatMib  OBJECT IDENTIFIER ::= {mpMgmt 18}

natConf  OBJECT IDENTIFIER ::= {mpNatMib 1}

natCommIfTable  OBJECT-TYPE
    SYNTAX  SEQUENCE OF NatCommIfEntry
    ACCESS  not-accessible
    STATUS  current
    DESCRIPTION
            "地址转换协议接口配置表."
    ::= {natConf 1}

natCommIfEntry  OBJECT-TYPE
    SYNTAX  natCommIfEntry
    ACCESS  not-accessible
    STATUS  current
    DESCRIPTION
            "地址转换协议接口配置表条目."
    INDEX   {natCommIfIndex}
    ::= {natCommIfTable 1}

natCommIfIndex  OBJECT-TYPE
    SYNTAX  INTEGER
    ACCESS  read-create
    STATUS  current
    DESCRIPTION
            "指定地址转换的接口的接口索引."
    ::= {natCommIfEntry 1}

natCommIfFlag  OBJECT-TYPE
    SYNTAX  INTEGER {
	inside(1),
	outside(2)
            }
    ACCESS  read-create
    STATUS  current
    DESCRIPTION
            "指定地址转换的接口的标记,是与内部还是外部相连."
    ::= {natCommIfEntry 2}

natCommIfStatus  OBJECT-TYPE
    SYNTAX  RowStatus
    ACCESS  read-write
    STATUS  current
    DESCRIPTION
            "指定地址转换接口配置表的行状态,用于增加,删除或修改一行的内容."
    ::= {natCommIfEntry 3}

natInSrcTable  OBJECT-TYPE
    SYNTAX  SEQUENCE OF NatInSrcEntry
    ACCESS  not-accessible
    STATUS  current
    DESCRIPTION
            "地址转换的内部源地址表."
    ::= {natConf 2}

natInSrcEntry  OBJECT-TYPE
    SYNTAX  natInSrcEntry
    ACCESS  not-accessible
    STATUS  current
    DESCRIPTION
            "地址转换的内部源地址表条目."
    INDEX   {natInSrcAclName}
    ::= {natInSrcTable 1}

natInSrcAclName  OBJECT-TYPE
    SYNTAX  OCTET STRING(SIZE(0..255))
    ACCESS  read-create
    STATUS  current
    DESCRIPTION
            "指定地址转换使用的访问列表的编号或名称."
    ::= {natInSrcEntry 1}

natInSrcType  OBJECT-TYPE
    SYNTAX  INTEGER {
		source(1),
		destination(2)
            }
    ACCESS  read-create
    STATUS  current
    DESCRIPTION
            "指定地址转换使用的类型."
    ::= {natInSrcEntry 2}

natInSrcPoolName  OBJECT-TYPE
    SYNTAX  OCTET STRING(SIZE(0..255))
    ACCESS  read-create
    STATUS  current
    DESCRIPTION
            "指定地址转换使用的地址池."
    ::= {natInSrcEntry 3}

natInSrcIfName  OBJECT-TYPE
    SYNTAX  OCTET STRING(SIZE(0..255))
    ACCESS  read-create
    STATUS  current
    DESCRIPTION
            "指定地址转换使用的接口名."
    ::= {natInSrcEntry 4}

natInSrcOverload  OBJECT-TYPE
    SYNTAX  INTEGER {
		nooverload(1),
		overload(2)
            }
    ACCESS  read-create
    STATUS  current
    DESCRIPTION
            "指定地址转换使用的负载使能."
    ::= {natInSrcEntry 5}

natInOutType  OBJECT-TYPE
    SYNTAX  INTEGER {
		inside(1),
		outside(2)
            }
    ACCESS  read-create
    STATUS  current
    DESCRIPTION
            "指定地址转换使用的外部源转换."
    ::= {natInSrcEntry 6}

natVrfName  OBJECT-TYPE
    SYNTAX  OCTET STRING(SIZE(0..255))
    ACCESS  read-create
    STATUS  current
    DESCRIPTION
            "指定地址转换的VRF."
    ::= {natInSrcEntry 7}

natInSrcStatus  OBJECT-TYPE
    SYNTAX  RowStatus
    ACCESS  read-write
    STATUS  current
    DESCRIPTION
            "指定地址转换表的行状态."
    ::= {natInSrcEntry 8}

natInSrcStaticTable  OBJECT-TYPE
    SYNTAX  SEQUENCE OF NatInSrcStaticEntry
    ACCESS  not-accessible
    STATUS  current
    DESCRIPTION
            "地址转换的静态内部源地址."
    ::= {natConf 3}

natInSrcStaticEntry  OBJECT-TYPE
    SYNTAX  natInSrcStaticEntry
    ACCESS  not-accessible
    STATUS  current
    DESCRIPTION
            "地址转换的静态内部源地址表条目."
    INDEX   {natInSrcStaticProto, natInSrcStaticLocalIp, natInSrcStaticGlobalIp, natInSrcStaticNetmask, natInSrcStaticLocalPort, natInSrcStaticGlobalPort, natInOutType}
    ::= {natInSrcStaticTable 1}

natInSrcStaticProto  OBJECT-TYPE
    SYNTAX  INTEGER {
		none(1),
		tcp(2),
		udp(3)
            }
    ACCESS  read-create
    STATUS  current
    DESCRIPTION
            "静态指定地址转换表的协议类型."
    ::= {natInSrcStaticEntry 1}

natInSrcStaticLocalIp  OBJECT-TYPE
    SYNTAX  IpAddress
    ACCESS  read-create
    STATUS  current
    DESCRIPTION
            "静态指定地址转换表的本地IP."
    ::= {natInSrcStaticEntry 2}

natInSrcStaticGlobalIp  OBJECT-TYPE
    SYNTAX  IpAddress
    ACCESS  read-create
    STATUS  current
    DESCRIPTION
            "静态指定地址转换表的全局IP."
    ::= {natInSrcStaticEntry 3}

natInSrcStaticNetmask  OBJECT-TYPE
    SYNTAX  IpAddress
    ACCESS  read-create
    STATUS  current
    DESCRIPTION
            "静态指定网络地址转换的地址掩码. （静态主机地址转换时，掩码必须为0.0.0.0或者255.255.255.255）"
    ::= {natInSrcStaticEntry 4}

natInSrcStaticLocalPort  OBJECT-TYPE
    SYNTAX  INTEGER (0..65535)
    ACCESS  read-create
    STATUS  current
    DESCRIPTION
            "静态指定地址转换表的本地端口 (当协议为tcp/udp时，端口必定大于0；若无协议，则端口为0)."
    ::= {natInSrcStaticEntry 5}

natInSrcStaticGlobalPort  OBJECT-TYPE
    SYNTAX  INTEGER(0..65535)
    ACCESS  read-create
    STATUS  current
    DESCRIPTION
            "静态指定地址转换表的全局端口."
    ::= {natInSrcStaticEntry 6}

natInOutType  OBJECT-TYPE
    SYNTAX  INTEGER(0..65535)
    ACCESS  read-create
    STATUS  current
    DESCRIPTION
            "静态指定地址转换的方向."
    ::= {natInSrcStaticEntry 7}

natVrfName  OBJECT-TYPE
    SYNTAX  OCTET STRING(SIZE(0..255))
    ACCESS  read-create
    STATUS  current
    DESCRIPTION
            "指定地址转换的VRF."
    ::= {natInSrcStaticEntry 8}

natInSrcStaticStatus  OBJECT-TYPE
    SYNTAX  RowStatus
    ACCESS  read-write
    STATUS  current
    DESCRIPTION
            "静态指定地址转换表的行状态."
    ::= {natInSrcStaticEntry 9}

natPoolTable  OBJECT-TYPE
    SYNTAX  SEQUENCE OF NatPoolEntry
    ACCESS  not-accessible
    STATUS  current
    DESCRIPTION
            "地址转换的地址池."
    ::= {natConf 4}

natPoolEntry  OBJECT-TYPE
    SYNTAX  natPoolEntry
    ACCESS  not-accessible
    STATUS  current
    DESCRIPTION
            "地址转换的地址池表条目."
    INDEX   {natPoolName}
    ::= {natPoolTable 1}

natPoolName  OBJECT-TYPE
    SYNTAX  OCTET STRING(SIZE(0..255))
    ACCESS  read-create
    STATUS  current
    DESCRIPTION
            "地址转换的地址池名."
    ::= {natPoolEntry 1}

natPoolStartIp  OBJECT-TYPE
    SYNTAX  IpAddress
    ACCESS  read-create
    STATUS  current
    DESCRIPTION
            "地址转换的开始IP."
    ::= {natPoolEntry 2}

natPoolEndIp  OBJECT-TYPE
    SYNTAX  IpAddress
    ACCESS  read-create
    STATUS  current
    DESCRIPTION
            "地址转换的结束IP."
    ::= {natPoolEntry 3}

natPoolNetmask  OBJECT-TYPE
    SYNTAX  IpAddress
    ACCESS  read-create
    STATUS  current
    DESCRIPTION
            "地址转换的掩码。开始IP和结束IP必须在同一网段."
    ::= {natPoolEntry 4}

natPoolType  OBJECT-TYPE
    SYNTAX  INTEGER {
		generic(1),
		rotary(2)
            }
    ACCESS  read-create
    STATUS  current
    DESCRIPTION
            "地址转换是否环回."
    ::= {natPoolEntry 5}

natPoolStatus  OBJECT-TYPE
    SYNTAX  RowStatus
    ACCESS  read-write
    STATUS  current
    DESCRIPTION
            "地址转换的地址池表的行状态."
    ::= {natPoolEntry 6}

natTranslation  OBJECT IDENTIFIER ::= {natConf 5}

natTransIcmpError  OBJECT-TYPE
    SYNTAX  INTEGER (0..2147483647)
    ACCESS  read-write
    STATUS  current
    DESCRIPTION
            "当配置为0时表示never."
    ::= {natTranslation 1}

natTransIcmpTimeout  OBJECT-TYPE
    SYNTAX  INTEGER (0..2147483647)
    ACCESS  read-write
    STATUS  current
    DESCRIPTION
            "当配置为0时表示never."
    ::= {natTranslation 2}

natTransTcpTimeout  OBJECT-TYPE
    SYNTAX  INTEGER (0..2147483647)
    ACCESS  read-write
    STATUS  current
    DESCRIPTION
            "当配置为0时表示never."
    ::= {natTranslation 3}

natTransUdpTimeout  OBJECT-TYPE
    SYNTAX  INTEGER (0..2147483647)
    ACCESS  read-write
    STATUS  current
    DESCRIPTION
            "当配置为0时表示never."
    ::= {natTranslation 4}

natTransDnsTimeout  OBJECT-TYPE
    SYNTAX  INTEGER (0..2147483647)
    ACCESS  read-write
    STATUS  current
    DESCRIPTION
            "当配置为0时表示never."
    ::= {natTranslation 5}

natTransFinRstTimeout  OBJECT-TYPE
    SYNTAX  INTEGER (0..2147483647)
    ACCESS  read-write
    STATUS  current
    DESCRIPTION
            "当配置为0时表示never."
    ::= {natTranslation 6}

natTransSynTimeout  OBJECT-TYPE
    SYNTAX  INTEGER (0..2147483647)
    ACCESS  read-write
    STATUS  current
    DESCRIPTION
            "当配置为0时表示never."
    ::= {natTranslation 7}

natTransTimeout  OBJECT-TYPE
    SYNTAX  INTEGER (0..2147483647)
    ACCESS  read-write
    STATUS  current
    DESCRIPTION
            "当配置为0时表示never."
    ::= {natTranslation 8}

natTransMaxEntry  OBJECT-TYPE
    SYNTAX  INTEGER (8000..150000)
    ACCESS  read-write
    STATUS  current
    DESCRIPTION
            "可配置的最大值取决于内存大小,小于64M为23000,小于128M为53000,大于或等于256以上为150000."
    ::= {natTranslation 9}

natTransMaxHashsize  OBJECT-TYPE
    SYNTAX  INTEGER (997..7993)
    ACCESS  read-write
    STATUS  current
    DESCRIPTION
            "."
    ::= {natTranslation 10}

natTransMaxHashChange  OBJECT-TYPE
    SYNTAX  INTEGER {
		value1(1),
		value2(2)
            }
    ACCESS  read-write
    STATUS  current
    DESCRIPTION
            "."
    ::= {natTranslation 11}

natTransMaxIcmpEntry  OBJECT-TYPE
    SYNTAX  INTEGER (50..5000)
    ACCESS  read-write
    STATUS  current
    DESCRIPTION
            "可配置的最大值取决于内存大小,小于64M为500,小于128M为2500,大于或等于256以上为5000."
    ::= {natTranslation 12}

natStat  OBJECT IDENTIFIER ::= {mpNatMib 2}

natCommStat  OBJECT IDENTIFIER ::= {natStat 1}

natCommStatTotalTransStatic  OBJECT-TYPE
    SYNTAX  Counter32
    ACCESS  read-only
    STATUS  current
    DESCRIPTION
            "."
    ::= {natCommStat 1}

natCommStatTotalTransDyna  OBJECT-TYPE
    SYNTAX  Counter32
    ACCESS  read-only
    STATUS  current
    DESCRIPTION
            "."
    ::= {natCommStat 2}

natCommStatTotalTransFree  OBJECT-TYPE
    SYNTAX  Counter32
    ACCESS  read-only
    STATUS  current
    DESCRIPTION
            "."
    ::= {natCommStat 3}

natCommStatNoMemery  OBJECT-TYPE
    SYNTAX  Counter32
    ACCESS  read-only
    STATUS  current
    DESCRIPTION
            "."
    ::= {natCommStat 4}

natCommStatExecDrops  OBJECT-TYPE
    SYNTAX  Counter32
    ACCESS  read-only
    STATUS  current
    DESCRIPTION
            "."
    ::= {natCommStat 5}

natCommStatOverKills  OBJECT-TYPE
    SYNTAX  Counter32
    ACCESS  read-only
    STATUS  current
    DESCRIPTION
            "."
    ::= {natCommStat 6}

natCommStatCurrHash  OBJECT-TYPE
    SYNTAX  Counter32
    ACCESS  read-only
    STATUS  current
    DESCRIPTION
            "."
    ::= {natCommStat 7}

natCommStatTransMode  OBJECT-TYPE
    SYNTAX  INTEGER
    ACCESS  read-only
    STATUS  current
    DESCRIPTION
            "."
    ::= {natCommStat 8}

natCommStatHits  OBJECT-TYPE
    SYNTAX  Counter32
    ACCESS  read-only
    STATUS  current
    DESCRIPTION
            "."
    ::= {natCommStat 9}

natCommStatMisses  OBJECT-TYPE
    SYNTAX  Counter32
    ACCESS  read-only
    STATUS  current
    DESCRIPTION
            "."
    ::= {natCommStat 10}

natCommStatExpTrans  OBJECT-TYPE
    SYNTAX  Counter32
    ACCESS  read-only
    STATUS  current
    DESCRIPTION
            "."
    ::= {natCommStat 11}

natCommStatFragTotals  OBJECT-TYPE
    SYNTAX  Counter32
    ACCESS  read-only
    STATUS  current
    DESCRIPTION
            "."
    ::= {natCommStat 12}

natCommStatFragHadexisteds  OBJECT-TYPE
    SYNTAX  Counter32
    ACCESS  read-only
    STATUS  current
    DESCRIPTION
            "."
    ::= {natCommStat 13}

natCommStatFragNomemorys  OBJECT-TYPE
    SYNTAX  Counter32
    ACCESS  read-only
    STATUS  current
    DESCRIPTION
            "."
    ::= {natCommStat 14}

natCommStatFragHits  OBJECT-TYPE
    SYNTAX  Counter32
    ACCESS  read-only
    STATUS  current
    DESCRIPTION
            "."
    ::= {natCommStat 15}

natCommStatFragExpireds  OBJECT-TYPE
    SYNTAX  Counter32
    ACCESS  read-only
    STATUS  current
    DESCRIPTION
            "."
    ::= {natCommStat 16}

natCommStatFragNews  OBJECT-TYPE
    SYNTAX  Counter32
    ACCESS  read-only
    STATUS  current
    DESCRIPTION
            "."
    ::= {natCommStat 17}

natCommStatFtpTotals  OBJECT-TYPE
    SYNTAX  Counter32
    ACCESS  read-only
    STATUS  current
    DESCRIPTION
            "."
    ::= {natCommStat 18}

natCommStatFtpHits  OBJECT-TYPE
    SYNTAX  Counter32
    ACCESS  read-only
    STATUS  current
    DESCRIPTION
            "."
    ::= {natCommStat 19}

natCommStatFtpNomemorys  OBJECT-TYPE
    SYNTAX  Counter32
    ACCESS  read-only
    STATUS  current
    DESCRIPTION
            "."
    ::= {natCommStat 20}

natFrequency  OBJECT-TYPE
    SYNTAX  INTEGER (1..60)
    ACCESS  read-write
    STATUS  current
    DESCRIPTION
            "."
    ::= {mpNatMib 3}

natRedirect  OBJECT-TYPE
    SYNTAX  INTEGER
    ACCESS  read-write
    STATUS  current
    DESCRIPTION
            "."
    ::= {mpNatMib 4}
END
