------------------------------------------------------------------------------
--
--  File         : maipuQueueMIB.mib
--  Description  : MIB for FIFO, Priority, Custom, and Fair Queuing
--  Version      : 1.00
--  Date         : December 26, 2009
-- 	Copyright    : 2009 by Maipu Communication Technology Co., LTD.
--					All rights reserved.
--
-- $Id:
--
------------------------------------------------------------------------------

------------------------------------------------------------------------------
MAIPU-QUEUE-MIB DEFINITIONS ::= BEGIN


IMPORTS
        MODULE-IDENTITY, OBJECT-TYPE, NOTIFICATION-TYPE, enterprises, Counter32, Gauge32,
          Integer32, Unsigned32, TimeTicks,IpAddress,Counter64
            FROM SNMPv2-SMI
        TEXTUAL-CONVENTION, TruthValue, MacAddress,
          RowStatus, DisplayString, DateAndTime
            FROM SNMPv2-TC
        MODULE-COMPLIANCE, OBJECT-GROUP
            FROM SNMPv2-CONF
        mpMgmt
            FROM MAIPU-SMI;


maipu               	OBJECT IDENTIFIER ::= { enterprises 5651 }
mpMgmt2             	OBJECT IDENTIFIER ::= { maipu 6 }
mpRouterTech        	OBJECT IDENTIFIER ::= { mpMgmt2 2 }
mpRtQoSv2           	OBJECT IDENTIFIER ::= { mpRouterTech 3 }



maipuQueueMIB       	MODULE-IDENTITY
                    		LAST-UPDATED 	"0912261525Z"
                    		ORGANIZATION 	"Maipu Communication Technology Co., LTD."
                    		CONTACT-INFO
                    			""
                    		DESCRIPTION
                      			"MIB for FIFO, Priority, Custom, and Fair Queuing"
                    		::= { mpRtQoSv2  3 }




------------------------------------------------------------------------------
maipuQueueObjects   	OBJECT IDENTIFIER ::= { maipuQueueMIB 1 }


------------------------------------------------------------------------------
mpQueueConfig       	OBJECT IDENTIFIER ::= { maipuQueueObjects 1 }

mpQInterfaceCfgTable	OBJECT-TYPE
                    		SYNTAX  SEQUENCE OF   MpQInterfaceCfgEntry
                    		MAX-ACCESS  not-accessible
                    		STATUS  current
                    		DESCRIPTION
                    			"This table contains objects that describe the queuing on a main
                    			or sub interface."
                    		::= { mpQueueConfig 1 }

mpQInterfaceCfgEntry	OBJECT-TYPE
                    		SYNTAX  MpQInterfaceCfgEntry
                    		MAX-ACCESS  not-accessible
                    		STATUS  current
                    		DESCRIPTION
                    			"A list of queuing attributes for a main or sub interface."
                    		INDEX  { ifIndex }
                    		::= { mpQInterfaceCfgTable 1 }

MpQInterfaceCfgEntry	::= SEQUENCE {
                    			mpQIFCfgQType          INTEGER,
                    			mpQIFCfgQueues         Integer32
                    	             }


mpQIFCfgQType       	OBJECT-TYPE
                    		SYNTAX  INTEGER {
                    			          fifo(1),
                    			          priority(2),
                    			          custom(3),
                    			          weightedFair(4)
                    			        }
                    		MAX-ACCESS  read-only
                    		STATUS  current
                    		DESCRIPTION
                    			"The type of queueing used on the interface."
                    		::= { mpQInterfaceCfgEntry 1 }

mpQIFCfgQueues      	OBJECT-TYPE
                    		SYNTAX  Integer32
                    		MAX-ACCESS  read-only
                    		STATUS  current
                    		DESCRIPTION
                    			"The number of queues in the queue set."
                    		::= { mpQInterfaceCfgEntry 2 }

------------------------------------------------------------------------------
mpQFrameRelayVCCfgTable	OBJECT-TYPE
                    		SYNTAX  SEQUENCE OF   MpQFrameRelayVCCfgEntry
                    		MAX-ACCESS  not-accessible
                    		STATUS  current
                    		DESCRIPTION
                    			"This table contains objects that describe the queuing on a Frame
                    			Relay VC."
                    		::= { mpQueueConfig 2 }

mpQFrameRelayVCCfgEntry	OBJECT-TYPE
                    		SYNTAX  MpQFrameRelayVCCfgEntry
                    		MAX-ACCESS  not-accessible
                    		STATUS  current
                    		DESCRIPTION
                    			"A list of queuing attributes for a Frame Relay VC."
                    		INDEX  { ifIndex,  mpQFRCfgDLCI }
                    		::= { mpQFrameRelayVCCfgTable 1 }

MpQFrameRelayVCCfgEntry	::= SEQUENCE {
								mpQFRCfgDLCI           Unsigned32,
                    			mpQFRCfgQType          INTEGER,
                    			mpQFRCfgQueues         Integer32
                    	             }

mpQFRCfgDLCI        	OBJECT-TYPE
                    		SYNTAX  Unsigned32(0..1007)
                    		MAX-ACCESS  not-accessible
                    		STATUS  current
                    		DESCRIPTION
                    			"DLCI for the Frame Relay VC."
                    		::= { mpQFrameRelayVCCfgEntry 1 }

mpQFRCfgQType       	OBJECT-TYPE
                    		SYNTAX  INTEGER {
                    			          fifo(1),
                    			          priority(2),
                    			          custom(3),
                    			          weightedFair(4)
                    			        }
                    		MAX-ACCESS  read-only
                    		STATUS  current
                    		DESCRIPTION
                    			"The type of queueing used on the Frame Relay VC."
                    		::= { mpQFrameRelayVCCfgEntry 2 }

mpQFRCfgQueues      	OBJECT-TYPE
                    		SYNTAX  Integer32
                    		MAX-ACCESS  read-only
                    		STATUS  current
                    		DESCRIPTION
                    			"The number of queues in the queue set."
                    		::= { mpQFrameRelayVCCfgEntry 3 }


------------------------------------------------------------------------------
mpQATMPVCCfgTable	OBJECT-TYPE
                    		SYNTAX  SEQUENCE OF   MpQATMPVCCfgEntry
                    		MAX-ACCESS  not-accessible
                    		STATUS  current
                    		DESCRIPTION
                    			"This table contains objects that describe the queuing on an ATM
                    			PVC."
                    		::= { mpQueueConfig 3 }

mpQATMPVCCfgEntry	OBJECT-TYPE
                    		SYNTAX  MpQATMPVCCfgEntry
                    		MAX-ACCESS  not-accessible
                    		STATUS  current
                    		DESCRIPTION
                    			"A list of queuing attributes for an ATM PVC."
                    		INDEX  { ifIndex,  mpQATMCfgVPI,  mpQATMCfgVCI }
                    		::= { mpQATMPVCCfgTable 1 }

MpQATMPVCCfgEntry	::= SEQUENCE {
								mpQATMCfgVPI			Unsigned32,
								mpQATMCfgVCI			Unsigned32,
                    			mpQATMCfgQType          INTEGER,
                    			mpQATMCfgQueues         Integer32
                    	             }


mpQATMCfgVPI     	OBJECT-TYPE
                    		SYNTAX  Unsigned32(0..4095)
                    		MAX-ACCESS  not-accessible
                    		STATUS  current
                    		DESCRIPTION
                    			"VPI for the ATM PVC."
                    		::= { mpQATMPVCCfgEntry 1 }

mpQATMCfgVCI     	OBJECT-TYPE
                    		SYNTAX  Unsigned32(0..65535)
                    		MAX-ACCESS  not-accessible
                    		STATUS  current
                    		DESCRIPTION
                    			"VCI for the ATM PVC."
                    		::= { mpQATMPVCCfgEntry 2 }

mpQATMCfgQType       	OBJECT-TYPE
                    		SYNTAX  INTEGER {
                    			          fifo(1),
                    			          priority(2),
                    			          custom(3),
                    			          weightedFair(4)
                    			        }
                    		MAX-ACCESS  read-only
                    		STATUS  current
                    		DESCRIPTION
                    			"The type of queueing used on the ATM PVC."
                    		::= { mpQATMPVCCfgEntry 3 }

mpQATMCfgQueues      	OBJECT-TYPE
                    		SYNTAX  Integer32
                    		MAX-ACCESS  read-only
                    		STATUS  current
                    		DESCRIPTION
                    			"The number of queues in the queue set."
                    		::= { mpQATMPVCCfgEntry 4 }


------------------------------------------------------------------------------
mpQueueStats        	OBJECT IDENTIFIER ::= { maipuQueueObjects 2 }

mpQInterfaceStatTable	OBJECT-TYPE
                    		SYNTAX  SEQUENCE OF   MpQInterfaceStatEntry
                    		MAX-ACCESS  not-accessible
                    		STATUS  current
                    		DESCRIPTION
                    			"This table contains statistical objects that for the queues of a
                    			main or sub interface."
                    		::= { mpQueueStats 1 }

mpQInterfaceStatEntry	OBJECT-TYPE
                    		SYNTAX  MpQInterfaceStatEntry
                    		MAX-ACCESS  not-accessible
                    		STATUS  current
                    		DESCRIPTION
                    			"A list of queuing attributes for a main or sub interface."
                    		INDEX  { ifIndex,  mpQIFstatQNumber }
                    		::= { mpQInterfaceStatTable 1 }

MpQInterfaceStatEntry	::= SEQUENCE {
                    			mpQIFstatQNumber       Integer32,
                    			mpQIFstatDepthUnit     INTEGER,
                    			mpQIFstatCurrentDepth   Gauge32,
                    			mpQIFstatMaxDepth      Integer32,
                    			mpQIFstatTransmitPkt64   Counter64,
                    			mpQIFstatDiscardPkt64   Counter64
                    	             }


mpQIFstatQNumber    	OBJECT-TYPE
                    		SYNTAX  Integer32(0..2147483647)
                    		MAX-ACCESS  not-accessible
                    		STATUS  current
                    		DESCRIPTION
                    			"The number of the queue within the queue set."
                    		::= { mpQInterfaceStatEntry 1 }

mpQIFstatDepthUnit  	OBJECT-TYPE
                    		SYNTAX  INTEGER {
                    			          packets(1),
                    			          bytes(2),
                    			          cells(3),
                    			          ms(4),
                    			          us(5)
                    			        }
                    		MAX-ACCESS  read-only
                    		STATUS  current
                    		DESCRIPTION
                    			"Represents the unit type to measure the depth of the queue."
                    		::= { mpQInterfaceStatEntry 2 }

mpQIFstatCurrentDepth	OBJECT-TYPE
                    		SYNTAX  Gauge32
                    		MAX-ACCESS  read-only
                    		STATUS  current
                    		DESCRIPTION
                    			"The current depth of the queue."
                    		::= { mpQInterfaceStatEntry 3 }

mpQIFstatMaxDepth   	OBJECT-TYPE
                    		SYNTAX  Integer32
                    		MAX-ACCESS  read-only
                    		STATUS  current
                    		DESCRIPTION
                    			"The maximum depth of the queue."
                    		::= { mpQInterfaceStatEntry 4 }

mpQIFstatTransmitPkt64	OBJECT-TYPE
                    		SYNTAX  Counter64
                    		UNITS  "packets"
                    		MAX-ACCESS  read-only
                    		STATUS  current
                    		DESCRIPTION
                    			"The number of packets transmitted from this queue."
                    		::= { mpQInterfaceStatEntry 5 }

mpQIFstatDiscardPkt64	OBJECT-TYPE
                    		SYNTAX  Counter64
                    		UNITS  "packets"
                    		MAX-ACCESS  read-only
                    		STATUS  current
                    		DESCRIPTION
                    			"The number of packets discarded from this queue by reason of
                    			enqueue at a time that QCurrentDepth >= QMaxDepth."
                    		::= { mpQInterfaceStatEntry 6 }


------------------------------------------------------------------------------
mpQFrameRelayVCStatTable	OBJECT-TYPE
                    		SYNTAX  SEQUENCE OF   MpQFrameRelayVCStatEntry
                    		MAX-ACCESS  not-accessible
                    		STATUS  current
                    		DESCRIPTION
                    			"This table contains statistical objects that for the queues of a
                    			Frame Relay VC."
                    		::= { mpQueueStats 2 }

mpQFrameRelayVCStatEntry	OBJECT-TYPE
                    		SYNTAX  MpQFrameRelayVCStatEntry
                    		MAX-ACCESS  not-accessible
                    		STATUS  current
                    		DESCRIPTION
                    			"A list of queuing attributes for a Frame Relay VC."
                    		INDEX  { ifIndex,  mpQFRCfgDLCI,  mpQFRstatQNumber }
                    		::= { mpQFrameRelayVCStatTable 1 }

MpQFrameRelayVCStatEntry	::= SEQUENCE {
                    			mpQFRstatQNumber       Integer32,
                    			mpQFRstatDepthUnit     INTEGER,
                    			mpQFRstatCurrentDepth   Gauge32,
                    			mpQFRstatMaxDepth      Integer32,
                    			mpQFRstatTransmitPkt64   Counter64,
                    			mpQFRstatDiscardPkt64   Counter64
                    	             }


mpQFRstatQNumber    	OBJECT-TYPE
                    		SYNTAX  Integer32(0..2147483647)
                    		MAX-ACCESS  not-accessible
                    		STATUS  current
                    		DESCRIPTION
                    			"The number of the queue within the queue set."
                    		::= { mpQFrameRelayVCStatEntry 1 }

mpQFRstatDepthUnit  	OBJECT-TYPE
                    		SYNTAX  INTEGER {
                    			          packets(1),
                    			          bytes(2),
                    			          cells(3),
                    			          ms(4),
                    			          us(5)
                    			        }
                    		MAX-ACCESS  read-only
                    		STATUS  current
                    		DESCRIPTION
                    			"Represents the unit type to measure the depth of the queue."
                    		::= { mpQFrameRelayVCStatEntry 2 }

mpQFRstatCurrentDepth	OBJECT-TYPE
                    		SYNTAX  Gauge32
                    		MAX-ACCESS  read-only
                    		STATUS  current
                    		DESCRIPTION
                    			"The current depth of the queue."
                    		::= { mpQFrameRelayVCStatEntry 3 }

mpQFRstatMaxDepth   	OBJECT-TYPE
                    		SYNTAX  Integer32
                    		MAX-ACCESS  read-only
                    		STATUS  current
                    		DESCRIPTION
                    			"The maximum depth of the queue."
                    		::= { mpQFrameRelayVCStatEntry 4 }

mpQFRstatTransmitPkt64	OBJECT-TYPE
                    		SYNTAX  Counter64
                    		UNITS  "packets"
                    		MAX-ACCESS  read-only
                    		STATUS  current
                    		DESCRIPTION
                    			"The number of packets transmitted from this queue."
                    		::= { mpQFrameRelayVCStatEntry 5 }

mpQFRstatDiscardPkt64	OBJECT-TYPE
                    		SYNTAX  Counter64
                    		UNITS  "packets"
                    		MAX-ACCESS  read-only
                    		STATUS  current
                    		DESCRIPTION
                    			"The number of packets discarded from this queue by reason of
                    			enqueue at a time that QCurrentDepth >= QMaxDepth."
                    		::= { mpQFrameRelayVCStatEntry 6 }


------------------------------------------------------------------------------
mpQATMPVCStatTable	OBJECT-TYPE
                    		SYNTAX  SEQUENCE OF   MpQATMPVCStatEntry
                    		MAX-ACCESS  not-accessible
                    		STATUS  current
                    		DESCRIPTION
                    			"This table contains statistical objects that for the queues of
                    			an ATM PVC."
                    		::= { mpQueueStats 3 }

mpQATMPVCStatEntry	OBJECT-TYPE
                    		SYNTAX  MpQATMPVCStatEntry
                    		MAX-ACCESS  not-accessible
                    		STATUS  current
                    		DESCRIPTION
                    			"A list of queuing attributes for an ATM PVC."
                    		INDEX  { ifIndex,  mpQATMCfgVPI,  mpQATMCfgVCI,  mpQATMstatQNumber }
                    		::= { mpQATMPVCStatTable 1 }

MpQATMPVCStatEntry	::= SEQUENCE {
                    			mpQATMstatQNumber       Integer32,
                    			mpQATMstatDepthUnit     INTEGER,
                    			mpQATMstatCurrentDepth   Gauge32,
                    			mpQATMstatMaxDepth      Integer32,
                    			mpQATMstatTransmitPkt64   Counter64,
                    			mpQATMstatDiscardPkt64   Counter64
                    	             }


mpQATMstatQNumber    	OBJECT-TYPE
                    		SYNTAX  Integer32(0..2147483647)
                    		MAX-ACCESS  not-accessible
                    		STATUS  current
                    		DESCRIPTION
                    			"The number of the queue within the queue set."
                    		::= { mpQATMPVCStatEntry 1 }

mpQATMstatDepthUnit  	OBJECT-TYPE
                    		SYNTAX  INTEGER {
                    			          packets(1),
                    			          bytes(2),
                    			          cells(3),
                    			          ms(4),
                    			          us(5)
                    			        }
                    		MAX-ACCESS  read-only
                    		STATUS  current
                    		DESCRIPTION
                    			"Represents the unit type to measure the depth of the queue."
                    		::= { mpQATMPVCStatEntry 2 }

mpQATMstatCurrentDepth	OBJECT-TYPE
                    		SYNTAX  Gauge32
                    		MAX-ACCESS  read-only
                    		STATUS  current
                    		DESCRIPTION
                    			"The current depth of the queue."
                    		::= { mpQATMPVCStatEntry 3 }

mpQATMstatMaxDepth   	OBJECT-TYPE
                    		SYNTAX  Integer32
                    		MAX-ACCESS  read-only
                    		STATUS  current
                    		DESCRIPTION
                    			"The maximum depth of the queue."
                    		::= { mpQATMPVCStatEntry 4 }

mpQATMstatTransmitPkt64	OBJECT-TYPE
                    		SYNTAX  Counter64
                    		UNITS  "packets"
                    		MAX-ACCESS  read-only
                    		STATUS  current
                    		DESCRIPTION
                    			"The number of packets transmitted from this queue."
                    		::= { mpQATMPVCStatEntry 5 }

mpQATMstatDiscardPkt64	OBJECT-TYPE
                    		SYNTAX  Counter64
                    		UNITS  "packets"
                    		MAX-ACCESS  read-only
                    		STATUS  current
                    		DESCRIPTION
                    			"The number of packets discarded from this queue by reason of
                    			enqueue at a time that QCurrentDepth >= QMaxDepth."
                    		::= { mpQATMPVCStatEntry 6 }


END
------------------------------------------------------------------------------
-- ============================================================================
-- $Log: maipuQueueMIB.mib,v $
--
--
-- ============================================================================
