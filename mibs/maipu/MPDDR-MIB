-- *****************************************************************
-- MAIPU-DDR.mib:  Maipu enterprise device DDR MIB file
--
--version 1.0.0.0, Feb 27, 2001 Huanglulu
--version 1.0.0.1, Sep 14, 2002 Huanglulu
--
-- Copyright (c)  by Maipu DataComm Inc.
-- All rights reserved.
--
-- *****************************************************************
--

MPDDR-MIB DEFINITIONS ::= BEGIN

IMPORTS
    RowStatus							FROM SNMPv2-TC
    IpAddress,
    MODULE-IDENTITY, OBJECT-TYPE        FROM SNMPv2-SMI
    mpMgmt                              FROM MAIPU-SMI;

mpDdrMib MODULE-IDENTITY
    LAST-UPDATED "0102270000Z"
    ORGANIZATION "Maipu DataComm"
    CONTACT-INFO
	"   Maipu DataComm
		Customer Service

		Postal: Consulate Drive
			Chengdu, Sichuan  610041
			China

		Tel: 86-028-5161006

		E-mail: office@maipu.com"
    DESCRIPTION
		"The assignments for Maipu router's MIB of DDR infomation!"
    ::= {mpMgmt 19 }


--//********** ddr configuration *********//
ddrConfTable OBJECT-TYPE
    SYNTAX SEQUENCE OF DdrConfEntry
    MAX-ACCESS not-accessible
    STATUS current
    DESCRIPTION
		"DDR的配置表."
    ::= { mpDdrMib 1 }

ddrConfEntry OBJECT-TYPE
    SYNTAX DdrConfEntry
    MAX-ACCESS not-accessible
    STATUS current
    DESCRIPTION
		"DDR配置表条目."
    INDEX { ddrConfIfIndex }
    ::= { ddrConfTable 1 }

DdrConfEntry ::=
	SEQUENCE {
		ddrConfIfIndex			INTEGER,
		ddrConfHoldQueue		INTEGER,
		ddrConfRotaryGroup		INTEGER,
		ddrConfPriority			INTEGER,
		ddrConfWait				INTEGER,
		ddrConfFastIdle			INTEGER,
		ddrConfIdleTimeout		INTEGER,
		ddrConfEnableTimeout	INTEGER,
		ddrConfDialerGroup		INTEGER,
		ddrConfCallbackSecure	INTEGER,
		ddrConfCallbackTime		INTEGER,
		ddrConfDialerRemoteName	OCTET STRING,
		ddrConfDialerRotor		INTEGER,
		ddrDialerType			INTEGER,
		ddrDialerLoadThreshold	INTEGER,
		ddrConfStatus			RowStatus,
		ddrDialerThreshDecision	INTEGER,
		ddrDialerPool			INTEGER
				}

ddrConfIfIndex	OBJECT-TYPE
	SYNTAX	INTEGER
	MAX-ACCESS	read-create
	STATUS	current
	DESCRIPTION
		"DDR配置所在接口的接口索引."
	::= { ddrConfEntry 1 }

ddrConfHoldQueue	OBJECT-TYPE
	SYNTAX	INTEGER (0..101)
	MAX-ACCESS	read-create
	STATUS	current
	DESCRIPTION
		"DDR缓存interesting数据包个数."
	DEFVAL { 0 }
	::= { ddrConfEntry 2 }

ddrConfRotaryGroup	OBJECT-TYPE
	SYNTAX	INTEGER (0..256)
	MAX-ACCESS	read-create
	STATUS	current
	DESCRIPTION
		"配置接口所属于的拨号器接口."
	::= { ddrConfEntry 3 }

ddrConfPriority	OBJECT-TYPE
	SYNTAX	INTEGER (0..256)
	MAX-ACCESS	read-create
	STATUS	current
	DESCRIPTION
		"优先级."
	::= { ddrConfEntry 4 }

ddrConfWait	OBJECT-TYPE
	SYNTAX	INTEGER (0..2147484)
	MAX-ACCESS	read-create
	STATUS	current
	DESCRIPTION
		"等待呼叫建立时间."
	DEFVAL { 60 }
	::= { ddrConfEntry 5 }

ddrConfFastIdle	OBJECT-TYPE
	SYNTAX	INTEGER (0..2147484)
	MAX-ACCESS	read-create
	STATUS	current
	DESCRIPTION
		"线路在切断当前呼叫以让位给正在等待使用该线路的另一个
		 呼叫之前,线路所允许保持的空闲时间.."
	DEFVAL { 20 }
	::= { ddrConfEntry 6 }

ddrConfIdleTimeout	OBJECT-TYPE
	SYNTAX	INTEGER (0..2147484)
	MAX-ACCESS	read-create
	STATUS	current
	DESCRIPTION
		"线路在被切断前可以保持的空闲时间."
	DEFVAL { 120 }
	::= { ddrConfEntry 7 }

ddrConfEnableTimeout	OBJECT-TYPE
	SYNTAX	INTEGER (0..2147484)
	MAX-ACCESS	read-create
	STATUS	current
	DESCRIPTION
		"一个呼叫完成或失败后,可以再次进行下一次呼叫的间隔时间."
	DEFVAL { 15 }
	::= { ddrConfEntry 8 }

ddrConfDialerGroup	OBJECT-TYPE
	SYNTAX	INTEGER (0..11)
	MAX-ACCESS	read-create
	STATUS	current
	DESCRIPTION
		"配置接口为属于一个特定的拨号组."
	::= { ddrConfEntry 9 }

ddrConfCallbackSecure	OBJECT-TYPE
	SYNTAX	INTEGER {
				disable(1),
				enable(2)
					}
	MAX-ACCESS	read-create
	STATUS	current
	DESCRIPTION
		"启动DDR回拨安全."
	::= { ddrConfEntry 10 }

ddrConfCallbackTime	OBJECT-TYPE
	SYNTAX	INTEGER (0..2147484)
	MAX-ACCESS	read-create
	STATUS	current
	DESCRIPTION
		"DDR回拨等待时间."
	::= { ddrConfEntry 11 }

ddrConfDialerRemoteName	OBJECT-TYPE
	SYNTAX	OCTET STRING (SIZE(0..34))
	MAX-ACCESS	read-create
	STATUS	current
	DESCRIPTION
		"配置远程主机名."
	::= { ddrConfEntry 12 }

ddrConfDialerRotor	OBJECT-TYPE
	SYNTAX	INTEGER {
				enable(1),
				disable(2),
				best(3),
				priority(4)
					}
	MAX-ACCESS	read-create
	STATUS	current
	DESCRIPTION
		"配置DDR拨转子."
	::= { ddrConfEntry 13 }

ddrDialerType	OBJECT-TYPE
	SYNTAX	INTEGER {
				noInBand(1),
				inBand(2)
					}
	MAX-ACCESS	read-create
	STATUS	current
	DESCRIPTION
		"拨号器类型."
	::= { ddrConfEntry 14 }

ddrDialerLoadThreshold	OBJECT-TYPE
	SYNTAX	INTEGER (0..256)
	MAX-ACCESS	read-create
	STATUS	current
	DESCRIPTION
		""
	::= { ddrConfEntry 15 }

ddrConfStatus	OBJECT-TYPE
	SYNTAX	RowStatus
	MAX-ACCESS	read-create
	STATUS	current
	DESCRIPTION
		"DDR配置表的行状态,用于增加,删除或修改一行的内容."
	::= { ddrConfEntry 16 }

ddrDialerThreshDecision	OBJECT-TYPE
	SYNTAX	INTEGER {
				outbount(1),
				inbound(2),
				either(3)
					}
	MAX-ACCESS	read-create
	STATUS	current
	DESCRIPTION
		""
	DEFVAL { 1 }
	::= { ddrConfEntry 17 }

ddrDialerPool	OBJECT-TYPE
	SYNTAX	INTEGER (0..256)
	MAX-ACCESS	read-create
	STATUS	current
	DESCRIPTION
		""
	::= { ddrConfEntry 18 }


--//********** dialerPool *********//
ddrDialerPoolTable	OBJECT-TYPE
	SYNTAX	SEQUENCE OF DdrDialerPoolEntry
	MAX-ACCESS	not-accessible
	STATUS	current
	DESCRIPTION
		""
	::= { mpDdrMib 7 }

ddrDialerPoolEntry	OBJECT-TYPE
	SYNTAX	DdrDialerPoolEntry
	MAX-ACCESS	not-accessible
	STATUS	current
	DESCRIPTION
		""
	INDEX { ddrDialerPoolIfIndex, ddrDialerPoolMember }
	::= { ddrDialerPoolTable 1 }

DdrDialerPoolEntry ::=
	SEQUENCE {
		ddrDialerPoolIfIndex
			INTEGER,
		ddrDialerPoolMember
			INTEGER,
		ddrDialerPoolStatus
			RowStatus,
		ddrDialerPoolMemPri
			INTEGER
				}

ddrDialerPoolIfIndex	OBJECT-TYPE
	SYNTAX	INTEGER
	MAX-ACCESS	read-create
	STATUS	current
	DESCRIPTION
		"."
	::= { ddrDialerPoolEntry 1 }

ddrDialerPoolMember	OBJECT-TYPE
	SYNTAX	INTEGER (1..255)
	MAX-ACCESS	read-create
	STATUS	current
	DESCRIPTION
		"."
	::= { ddrDialerPoolEntry 2 }

ddrDialerPoolStatus	OBJECT-TYPE
	SYNTAX	RowStatus
	MAX-ACCESS	read-create
	STATUS	current
	DESCRIPTION
		"行状态,用于增加,删除或修改一行的内容."
	::= { ddrDialerPoolEntry 3 }

ddrDialerPoolMemPri	OBJECT-TYPE
	SYNTAX	INTEGER (1..256)
	MAX-ACCESS	read-create
	STATUS	current
	DESCRIPTION
		"."
	::= { ddrDialerPoolEntry 4 }

--//********** dialerList *********//
ddrDialerListTable	OBJECT-TYPE
	SYNTAX	SEQUENCE OF DdrDialerListEntry
	MAX-ACCESS	not-accessible
	STATUS	current
	DESCRIPTION
		"DDR拨号列表."
	::= { mpDdrMib 2 }

ddrDialerListEntry	OBJECT-TYPE
	SYNTAX	DdrDialerListEntry
	MAX-ACCESS	not-accessible
	STATUS	current
	DESCRIPTION
		"DDR拨号列表条目."
	INDEX { ddrDialerListNum }
	::= { ddrDialerListTable 1 }

DdrDialerListEntry ::=
	SEQUENCE {
		ddrDialerListNum
			INTEGER,
		ddrDialerListProtocol
			INTEGER,
		ddrDialerListMode
			INTEGER,
		ddrDialerListAccess
			INTEGER,
		ddrDialerListStatus
			RowStatus
				}

ddrDialerListNum	OBJECT-TYPE
	SYNTAX	INTEGER (1..10)
	MAX-ACCESS	read-create
	STATUS	current
	DESCRIPTION
		"DDR拨号列表编号."
	::= { ddrDialerListEntry 1 }

ddrDialerListProtocol	OBJECT-TYPE
	SYNTAX	INTEGER {
				ip(1)
					}
	MAX-ACCESS	read-create
	STATUS	current
	DESCRIPTION
		"DDR拨号列表采用的协议方式."
	DEFVAL { ip }
	::= { ddrDialerListEntry 2 }

ddrDialerListMode	OBJECT-TYPE
	SYNTAX	INTEGER {
				permit(1),
				deny(2),
				other(3),
				accessList(4)
					}
	MAX-ACCESS	read-create
	STATUS	current
	DESCRIPTION
		"DDR拨号列表的限制方式."
	DEFVAL { 0 }
	::= { ddrDialerListEntry 3 }

ddrDialerListAccess	OBJECT-TYPE
	SYNTAX	INTEGER (1..2000)
	MAX-ACCESS	read-create
	STATUS	current
	DESCRIPTION
		"DDR拨号列表如果采用访问列表的列表号."
	::= { ddrDialerListEntry 4 }

ddrDialerListStatus	OBJECT-TYPE
	SYNTAX	RowStatus
	MAX-ACCESS	read-create
	STATUS	current
	DESCRIPTION
		"DDR拨号列表的行状态,用于增加,删除或修改一行的内容."
	::= { ddrDialerListEntry 5 }

--//********* dialerMap *********//
ddrDialerMapTable	OBJECT-TYPE
	SYNTAX	SEQUENCE OF DdrDialerMapEntry
	MAX-ACCESS	not-accessible
	STATUS	current
	DESCRIPTION
		"DDR拨号映射表."
	::= { mpDdrMib 3 }

ddrDialerMapEntry	OBJECT-TYPE
	SYNTAX	DdrDialerMapEntry
	MAX-ACCESS	not-accessible
	STATUS	current
	DESCRIPTION
		"DDR拨号映射表条目."
	INDEX { ddrDialerMapIndex, ddrDialerMapIfIndex }
	::= { ddrDialerMapTable 1 }

DdrDialerMapEntry ::=
	SEQUENCE {
		ddrDialerMapIndex
			INTEGER,
		ddrDialerMapIfIndex
			INTEGER,
		ddrDialerMapProtocol
			INTEGER,
		ddrDialerMapIpAddr
			IpAddress,
		ddrDialerMapHostName
			OCTET STRING,
		ddrDialerMapString
			OCTET STRING,
		ddrDialerMapBroadcast
			INTEGER,
		ddrDialerMapClassName
			OCTET STRING,
		ddrDialerMapStatus
			RowStatus
				}

ddrDialerMapIndex	OBJECT-TYPE
	SYNTAX	INTEGER
	MAX-ACCESS	read-only
	STATUS	current
	DESCRIPTION
		"DDR拨号映射表索引."
	::= { ddrDialerMapEntry 1 }

ddrDialerMapIfIndex	OBJECT-TYPE
	SYNTAX	INTEGER
	MAX-ACCESS	read-create
	STATUS	current
	DESCRIPTION
		"DDR拨号映射表所在的接口的接口索引."
	::= { ddrDialerMapEntry 2 }

ddrDialerMapProtocol	OBJECT-TYPE
	SYNTAX	INTEGER {
				ip(1)
					}
	MAX-ACCESS	read-create
	STATUS	current
	DESCRIPTION
		"DDR拨号映射的协议方式."
	::= { ddrDialerMapEntry 3 }

ddrDialerMapIpAddr	OBJECT-TYPE
	SYNTAX	IpAddress
	MAX-ACCESS	read-create
	STATUS	current
	DESCRIPTION
		"DDR拨号映射的远端IP地址."
	::= { ddrDialerMapEntry 4 }

ddrDialerMapHostName	OBJECT-TYPE
	SYNTAX	OCTET STRING
	MAX-ACCESS	read-create
	STATUS	current
	DESCRIPTION
		"DDR拨号映射的远端系统名称."
	::= { ddrDialerMapEntry 5 }

ddrDialerMapString	OBJECT-TYPE
	SYNTAX	OCTET STRING (SIZE(0..31))
	MAX-ACCESS	read-create
	STATUS	current
	DESCRIPTION
		"DDR拨号映射的远端电话号码(用于发出呼叫)."
	::= { ddrDialerMapEntry 6 }

ddrDialerMapBroadcast	OBJECT-TYPE
	SYNTAX	INTEGER {
				disable(1),
				enable(2)
					}
	MAX-ACCESS	read-create
	STATUS	current
	DESCRIPTION
		"."
	::= { ddrDialerMapEntry 7 }

ddrDialerMapClassName	OBJECT-TYPE
	SYNTAX	OCTET STRING
	MAX-ACCESS	read-create
	STATUS	current
	DESCRIPTION
		"."
	::= { ddrDialerMapEntry 8 }

ddrDialerMapStatus	OBJECT-TYPE
	SYNTAX	RowStatus
	MAX-ACCESS	read-create
	STATUS	current
	DESCRIPTION
		"DDR拨号映射表的行状态,用于增加,删除或修改一行的内容."
	::= { ddrDialerMapEntry 9 }


--//********* dialerMapClass *********//
ddrDialerMapClassTable	OBJECT-TYPE
	SYNTAX	SEQUENCE OF DdrDialerMapClassEntry
	MAX-ACCESS	not-accessible
	STATUS	current
	DESCRIPTION
		"DDR拨号映射类表."
	::= { mpDdrMib 4 }

ddrDialerMapClassEntry	OBJECT-TYPE
	SYNTAX	DdrDialerMapClassEntry
	MAX-ACCESS	not-accessible
	STATUS	current
	DESCRIPTION
		"DDR拨号映射类表条目."
	INDEX { ddrDialerMapClassName }
	::= { ddrDialerMapClassTable 1 }

DdrDialerClassMapEntry ::=
	SEQUENCE {
		ddrDialerMapClassName	OCTET STRING,
		ddrDialerCallBackServer	INTEGER,
		ddrDialerWaitCarrier	INTEGER,
		ddrDialerFastIlde		INTEGER,
		ddrDialerIdle			INTEGER,
		ddrDialerEnale			INTEGER,
		ddrDialerMapClassStatus	RowStatus
			}

ddrDialerMapClassName	OBJECT-TYPE
	SYNTAX	OCTET STRING
	MAX-ACCESS	read-write
	STATUS	current
	DESCRIPTION
		"DDR拨号影射类模式."
	::= { ddrDialerMapClassEntry 1 }

ddrDialerCallBackServer	OBJECT-TYPE
	SYNTAX	INTEGER {
				disable(1),
				username(2),
				dialString(3)
					}
	MAX-ACCESS	read-write
	STATUS	current
	DESCRIPTION
		"配置DDR映射类的回拨服务器."
	::= { ddrDialerMapClassEntry 2 }

ddrDialerWaitCarrier	OBJECT-TYPE
	SYNTAX	INTEGER (1..2147483)
	MAX-ACCESS	read-write
	STATUS	current
	DESCRIPTION
		"配置等待载波时间."
	::= { ddrDialerMapClassEntry 3 }

ddrDialerFastIlde	OBJECT-TYPE
	SYNTAX	INTEGER (1..2147483)
	MAX-ACCESS	read-write
	STATUS	current
	DESCRIPTION
		"配置快速定时器超时时间."
	::= { ddrDialerMapClassEntry 4 }

ddrDialerIdle	OBJECT-TYPE
	SYNTAX	INTEGER (1..2147483)
	MAX-ACCESS	read-write
	STATUS	current
	DESCRIPTION
		"配置空闲定时器超时时间."
	::= { ddrDialerMapClassEntry 5 }

ddrDialerEnale	OBJECT-TYPE
	SYNTAX	INTEGER (1..2147483)
	MAX-ACCESS	read-write
	STATUS	current
	DESCRIPTION
		"配置enable定时器超时时间."
	::= { ddrDialerMapClassEntry 6 }

ddrDialerMapClassStatus	OBJECT-TYPE
	SYNTAX	RowStatus
	MAX-ACCESS	 read-create
	STATUS	current
	DESCRIPTION
		"DDR拨号映射类表的行状态,用于增加,删除或修改一行的内容."
	::= {ddrDialerMapClassEntry 7 }


--//********* dialerStat *********//
ddrDialerStatTable	OBJECT-TYPE
	SYNTAX	SEQUENCE OF DdrDialerStatEntry
	MAX-ACCESS	not-accessible
	STATUS	current
	DESCRIPTION
		"DDR拨号统计表."
	::= { mpDdrMib 5 }

ddrDialerStatEntry	OBJECT-TYPE
	SYNTAX	DdrDialerStatEntry
	MAX-ACCESS	not-accessible
	STATUS	current
	DESCRIPTION
		"DDR拨号统计表条目."
	INDEX { ddrDialerStatIfIndex }
	::= { ddrDialerStatTable 1 }

DdrDialerStatEntry ::=
	SEQUENCE {
		ddrDialerStatIfIndex		INTEGER,
		ddrDialerType	 			INTEGER,
		ddrDialerState	 			INTEGER,
		ddrDialerTimeLeft			INTEGER,
		ddrDialerReason				INTEGER,
		ddrDialerReasonIpSrc		IpAddress,
		ddrDialerReasonIpDest		IpAddress,
		ddrDialerBoundTo			INTEGER,
		ddrDialerConnectTime		OCTET STRING,
		ddrDialerConnectTo			OCTET STRING,
		ddrDialerPeerName			OCTET STRING
			}

ddrDialerStatIfIndex	OBJECT-TYPE
	SYNTAX	INTEGER
	MAX-ACCESS	read-only
	STATUS	current
	DESCRIPTION
		"接口索引."
	::= { ddrDialerStatEntry 1 }

ddrDialerType	OBJECT-TYPE
	SYNTAX	INTEGER {
				none(1),
				isdn(2),
				inBand-async(3),
				inBand-sync(4),
				bChannel(5),
				dialer-profile(6),
				unknownType(7)
					}
	MAX-ACCESS	read-only
	STATUS	current
	DESCRIPTION
		"拨号类型"
	::= { ddrDialerStatEntry 2 }

ddrDialerState	OBJECT-TYPE
	SYNTAX	INTEGER {
				waitCallback(1),
				shutdown(2),
				enabling(3),
				idle(4),
				callPending(5),
				physicalUp(6),
				multilinkMem(7),
				linkLayerUp(8)
					}
	MAX-ACCESS	read-only
	STATUS	current
	DESCRIPTION
		"拨号状态."
	::= { ddrDialerStatEntry 3 }

ddrDialerTimeLeft	OBJECT-TYPE
	SYNTAX	INTEGER
	MAX-ACCESS	read-only
	STATUS	current
	DESCRIPTION
		"拨号剩余时间."
	::= { ddrDialerStatEntry 4 }

ddrDialerReason	OBJECT-TYPE
	SYNTAX	INTEGER {
				ip(1),
				callbackReturn(2),
				multilinkBundle(3)
					}
	MAX-ACCESS	read-only
	STATUS	current
	DESCRIPTION
		"拨号原因."
	::= { ddrDialerStatEntry 5 }

ddrDialerReasonIpSrc	OBJECT-TYPE
	SYNTAX	IpAddress
	MAX-ACCESS	read-only
	STATUS	current
	DESCRIPTION
		"拨号源地址."
	::= { ddrDialerStatEntry 6 }

ddrDialerReasonIpDest	OBJECT-TYPE
	SYNTAX	IpAddress
	MAX-ACCESS	read-only
	STATUS	current
	DESCRIPTION
		"拨号目的IP."
	::= { ddrDialerStatEntry 7 }

ddrDialerBoundTo	OBJECT-TYPE
	SYNTAX	INTEGER
	MAX-ACCESS	read-only
	STATUS	current
	DESCRIPTION
		"逻辑接口索引."
	::= { ddrDialerStatEntry 8 }

ddrDialerConnectTime	OBJECT-TYPE
	SYNTAX	OCTET STRING
	MAX-ACCESS	read-only
	STATUS	current
	DESCRIPTION
		"当前连接呼叫的时间."
	::= { ddrDialerStatEntry 9 }

ddrDialerConnectTo	OBJECT-TYPE
	SYNTAX	OCTET STRING
	MAX-ACCESS	read-only
	STATUS	current
	DESCRIPTION
		"当前连接目的主机名."
	::= { ddrDialerStatEntry 10 }

ddrDialerPeerName	OBJECT-TYPE
	SYNTAX	OCTET STRING
	MAX-ACCESS	read-only
	STATUS	current
	DESCRIPTION
		"."
	::= { ddrDialerStatEntry 11 }


--******* multilink configure *********
multilinkConfTable	OBJECT-TYPE
	SYNTAX	SEQUENCE OF multilinkConfEntry
	MAX-ACCESS	not-accessible
	STATUS	current
	DESCRIPTION
		"DDR拨号多链路配置表."
	::= { mpDdrMib 6 }

multilinkConfEntry	OBJECT-TYPE
	SYNTAX	MultilinkConfEntry
	MAX-ACCESS	not-accessible
	STATUS	current
	DESCRIPTION
		"DDR拨号多链路配置表条目."
	INDEX { multilinkConfIfIndex }
	::= { multilinkConfTable 1 }

MultilinkConfEntry    ::=
	SEQUENCE {
		multilinkConfIfIndex	    INTEGER,
		multilinkConfMultilinkGroup	INTEGER,
		multilinkConfStatus		RowStatus
			}

multilinkConfIfIndex	OBJECT-TYPE
	SYNTAX	INTEGER
	MAX-ACCESS	read-write
	STATUS	current
	DESCRIPTION
		"multilink配置所在接口的接口索引."
	::= { multilinkConfEntry 1 }

multilinkConfMultilinkGroup	OBJECT-TYPE
	SYNTAX	INTEGER (0..255)
	MAX-ACCESS	read-write
	STATUS	current
	DESCRIPTION
		"物理接口所关联的multilink接口的单元号."
	::= { multilinkConfEntry 2 }

multilinkConfStatus	OBJECT-TYPE
	SYNTAX	RowStatus
	MAX-ACCESS	 read-create
	STATUS	current
	DESCRIPTION
		"DDR拨号多链路配置表的行状态,用于增加,删除或修改一行的内容."
	::= {multilinkConfEntry 3 }

--******* Dialer information *********
ddrDialerInfoTable	OBJECT-TYPE
	SYNTAX	SEQUENCE OF DdrDialerInfoEntry
	MAX-ACCESS	not-accessible
	STATUS	current
	DESCRIPTION
		"."
	::= { mpDdrMib 8 }

ddrDialerInfoEntry	OBJECT-TYPE
	SYNTAX	DdrDialerInfoEntry
	MAX-ACCESS	not-accessible
	STATUS	current
	DESCRIPTION
		"."
	INDEX { ddrDialerInfoIndex, ddrDialerInfoIfIndex }
	::= { ddrDialerInfoTable 1 }

DdrDialerInfoEntry    ::=
	SEQUENCE {
		ddrDialerInfoIndex			INTEGER,
		ddrDialerInfoIfIndex		INTEGER,
		ddrDialerInfoDialString		OCTET STRING,
		ddrDialerInfoSuccess		INTEGER,
		ddrDialerInfoFailure		INTEGER,
		ddrDialerInfoLastCalled  	OCTET STRING,
		ddrDialerInfoLastStatus  	INTEGER
			}

ddrDialerInfoIndex	OBJECT-TYPE
	SYNTAX	INTEGER
	MAX-ACCESS	read-only
	STATUS	current
	DESCRIPTION
		""
	::= { ddrDialerInfoEntry 1 }

ddrDialerInfoIfIndex	OBJECT-TYPE
	SYNTAX	INTEGER
	MAX-ACCESS	read-only
	STATUS	current
	DESCRIPTION
		"接口索引."
	::= { ddrDialerInfoEntry 2 }

ddrDialerInfoDialString	OBJECT-TYPE
	SYNTAX	OCTET STRING
	MAX-ACCESS	 read-only
	STATUS	current
	DESCRIPTION
		"拨号串."
	::= {ddrDialerInfoEntry 3 }

ddrDialerInfoSuccess	OBJECT-TYPE
	SYNTAX	INTEGER
	MAX-ACCESS	read-only
	STATUS	current
	DESCRIPTION
		"成功次数"
	::= { ddrDialerInfoEntry 4 }

ddrDialerInfoFailure	OBJECT-TYPE
	SYNTAX	INTEGER
	MAX-ACCESS	read-only
	STATUS	current
	DESCRIPTION
		"失败次数."
	::= { ddrDialerInfoEntry 5 }

ddrDialerInfoLastCalled	OBJECT-TYPE
	SYNTAX	OCTET STRING
	MAX-ACCESS	 read-only
	STATUS	current
	DESCRIPTION
		"上一次拨号内容."
	::= {ddrDialerInfoEntry 6 }

ddrDialerInfoLastStatus	OBJECT-TYPE
	SYNTAX	INTEGER {
				success(1),
				failer(2)
					}
	MAX-ACCESS	read-only
	STATUS	current
	DESCRIPTION
		"上一次拨号状态."
	::= { ddrDialerInfoEntry 7 }

END
