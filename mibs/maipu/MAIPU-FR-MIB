-- *****************************************************************
-- MAIPU-FRAMERELAY.mib:  Maipu enterprise device Frame-Relay MIB file
--
--version 1.0.0.0, Feb 15, 2001 Huanglulu
--
-- Copyright (c)  by Maipu DataComm Inc.
-- All rights reserved.
--
-- *****************************************************************
--

MAIPU-FR-MIB DEFINITIONS ::= BEGIN

IMPORTS
    RowStatus, DisplayString				FROM SNMPv2-TC
    MODULE-IDENTITY, OBJECT-TYPE,
    IpAddress, OBJECT-IDENTITY, Counter32 	FROM SNMPv2-SMI
    mpMgmt                             		FROM MAIPU-SMI;

mpFrMib MODULE-IDENTITY
    LAST-UPDATED "0102160000Z"
    ORGANIZATION "Maipu DataComm"
    CONTACT-INFO
	"   Maipu DataComm
		Customer Service

		Postal: Consulate Drive
			Chengdu, Sichuan  610041
			China

		Tel: 86-028-5161006

		E-mail: office@maipu.com"
    DESCRIPTION
		"The assignments for Maipu router's MIB of Frame-Relay infomation!"
    ::= {mpMgmt 6 }

frIfMib	OBJECT-IDENTITY
	STATUS	current
	DESCRIPTION
		"接口上的帧中继协议."
	::= { mpFrMib 1 }

frPvcMib	OBJECT-IDENTITY
	STATUS	current
	DESCRIPTION
		"接口上的帧中继PVC."
	::= { mpFrMib 2 }

--frMapMib	OBJECT-IDENTITY
--	STATUS	current
--	DESCRIPTION
--		"接口上的帧中继地址映射."
--	::= { mpFrMib 3 }

--//***********if configure********//
frConfTable OBJECT-TYPE
    SYNTAX SEQUENCE OF FrConfEntry
    MAX-ACCESS not-accessible
    STATUS current
    DESCRIPTION
		"帧中继协议的接口配置表."
    ::= { frIfMib 1 }

frConfEntry OBJECT-TYPE
    SYNTAX FrConfEntry
    MAX-ACCESS not-accessible
    STATUS current
    DESCRIPTION
		"帧中继协议的接口配置表条目."
    INDEX { frConfIfIndex }
    ::= { frConfTable 1 }

FrConfEntry ::=
    SEQUENCE {
		frConfIfIndex
			INTEGER,
		frConfIfType
			INTEGER,
		frConfIfStatus
			RowStatus
		}

frConfIfIndex	OBJECT-TYPE
	SYNTAX	INTEGER
	MAX-ACCESS	read-only
	STATUS	current
	DESCRIPTION
		"配置帧中继协议的接口的接口索引,与ifIndex相同."
	::= { frConfEntry 1 }

frConfIfType	OBJECT-TYPE
	SYNTAX	INTEGER {
				dte(1),
				dce(2),
				nni(3)
					}
	MAX-ACCESS	read-create
	STATUS	current
	DESCRIPTION
		"帧中继接口的工作方式."
	DEFVAL { dte }
	::= { frConfEntry 2 }

frConfIfStatus	OBJECT-TYPE
	SYNTAX	RowStatus
	MAX-ACCESS	read-create
	STATUS	current
	DESCRIPTION
		"帧中继接口配置表行状态."
	::= { frConfEntry 3 }

--//***********frLmi configuration********//
frLmiConfTable OBJECT-TYPE
    SYNTAX SEQUENCE OF FrLmiConfEntry
    MAX-ACCESS not-accessible
    STATUS current
    DESCRIPTION
		"帧中继LMI协议接口配置表."
    ::= { frIfMib 2 }

frLmiConfEntry OBJECT-TYPE
    SYNTAX FrLmiConfEntry
    MAX-ACCESS not-accessible
    STATUS current
    DESCRIPTION
		"帧中继LMI协议的接口配置表条目."
    INDEX { frLmiConfIfIndex }
    ::= { frLmiConfTable 1 }

FrLmiConfEntry ::=
    SEQUENCE {
		frLmiConfIfIndex
			INTEGER,
		frLmiType
			INTEGER,
		frLmiN391Dte
			INTEGER,
		frLmiN392Dte
			INTEGER,
		frLmiN393Dte
			INTEGER,
		frLmiN392Dce
			INTEGER,
		frLmiN393Dce
			INTEGER,
		frLmiT392Dce
			INTEGER,
		frLmiKeepalive
			INTEGER,
		frLmiConfStatus
			RowStatus
		}

frLmiConfIfIndex	OBJECT-TYPE
	SYNTAX	INTEGER
	MAX-ACCESS	read-only
	STATUS	current
	DESCRIPTION
		"帧中继lmi协议的接口索引,与ifIndex相同."
	::= { frLmiConfEntry 1 }

frLmiType		OBJECT-TYPE
	SYNTAX	INTEGER {
				ansi(1),
				q933a(2),
				lmi(3)
					}
	MAX-ACCESS	read-create
	STATUS	current
	DESCRIPTION
		"帧中继lmi方式."
	DEFVAL { ansi }
	::= { frLmiConfEntry 2 }

frLmiN391Dte	OBJECT-TYPE
	SYNTAX	INTEGER (1..255)
	MAX-ACCESS	read-create
	STATUS	current
	DESCRIPTION
		"请求PVC状态的计数器."
	::= { frLmiConfEntry 3 }

frLmiN392Dte	OBJECT-TYPE
	SYNTAX	INTEGER (1..10)
	MAX-ACCESS	read-create
	STATUS	current
	DESCRIPTION
		"DTE错误阈值."
	::= { frLmiConfEntry 4 }

frLmiN393Dte	OBJECT-TYPE
	SYNTAX	INTEGER (1..10)
	MAX-ACCESS	read-create
	STATUS	current
	DESCRIPTION
		"DTE事件计数器.这个值不能小于frN392Dte."
	::= { frLmiConfEntry 5 }

frLmiN392Dce	OBJECT-TYPE
	SYNTAX	INTEGER (1..10)
	MAX-ACCESS	read-create
	STATUS	current
	DESCRIPTION
		"DCE错误阈值."
	::= { frLmiConfEntry 6 }

frLmiN393Dce	OBJECT-TYPE
	SYNTAX	INTEGER (1..10)
	MAX-ACCESS	read-create
	STATUS	current
	DESCRIPTION
		"DCE事件计数器.这个值不能小于frN392Dce."
	::= { frLmiConfEntry 7 }

frLmiT392Dce	OBJECT-TYPE
	SYNTAX	INTEGER (5..30)
	MAX-ACCESS	read-create
	STATUS	current
	DESCRIPTION
		"DCE轮询定时器."
	::= { frLmiConfEntry 8 }

frLmiKeepalive	OBJECT-TYPE
	SYNTAX	INTEGER (0..32767)
	MAX-ACCESS	read-create
	STATUS	current
	DESCRIPTION
		"发送保活帧的间隔时间,为0则表示不发送保活帧."
	::= { frLmiConfEntry 9 }

frLmiConfStatus	OBJECT-TYPE
	SYNTAX	RowStatus
	MAX-ACCESS	read-create
	STATUS	current
	DESCRIPTION
		"帧中继LMI协议行状态."
	::= { frLmiConfEntry 10 }

--//***********frLmi statistics*****************
frLmiStatTable	OBJECT-TYPE
    SYNTAX SEQUENCE OF FrLmiStatEntry
    MAX-ACCESS not-accessible
    STATUS current
    DESCRIPTION
		"帧中继LMI协议的统计表."
    ::= { frIfMib 3 }

frLmiStatEntry OBJECT-TYPE
    SYNTAX FrLmiStatEntry
    MAX-ACCESS not-accessible
    STATUS current
    DESCRIPTION
		"帧中继LMI协议统计表条目."
    INDEX { frLmiStatIfIndex }
    ::= { frLmiStatTable 1 }

FrLmiStatEntry ::=
    SEQUENCE {
    		frLmiStatIfIndex
    			INTEGER,
		frLmiStEnqSent
			Counter32,
		frLmiStMsgRecv
			Counter32,
		frLmiStTimeout
			Counter32,
		frLmiStEnqRecv
			Counter32,
		frLmiStMsgSent
			Counter32,
		frLmiStEnqTimeout
			Counter32
				}

frLmiStatIfIndex	OBJECT-TYPE
	SYNTAX	INTEGER
	MAX-ACCESS	read-only
	STATUS	current
	DESCRIPTION
		"帧中继LMI协议统计表的索引,用ifIndex值."
	::= { frLmiStatEntry 1 }

frLmiStEnqSent		OBJECT-TYPE
	SYNTAX	Counter32
	MAX-ACCESS	read-only
	STATUS	current
	DESCRIPTION
		"发送的状态请求报文的数目"
	::= { frLmiStatEntry 2 }

frLmiStMsgRecv	OBJECT-TYPE
	SYNTAX	Counter32
	MAX-ACCESS	read-only
	STATUS	current
	DESCRIPTION
		"收到的状态相应报文的数目"
	::= { frLmiStatEntry 3 }

frLmiStTimeout		OBJECT-TYPE
	SYNTAX	Counter32
	MAX-ACCESS	read-only
	STATUS	current
	DESCRIPTION
		"状态请求报文超时的数目"
	::= { frLmiStatEntry 4 }

frLmiStEnqRecv	OBJECT-TYPE
	SYNTAX	Counter32
	MAX-ACCESS	read-only
	STATUS	current
	DESCRIPTION
		"收到的状态请求报文的数目"
	::= { frLmiStatEntry 5 }

frLmiStMsgSent	OBJECT-TYPE
	SYNTAX	Counter32
	MAX-ACCESS	read-only
	STATUS	current
	DESCRIPTION
		"发送的状态相应报文的数目"
	::= { frLmiStatEntry 6 }

frLmiStEnqTimeout		OBJECT-TYPE
	SYNTAX	Counter32
	MAX-ACCESS	read-only
	STATUS	current
	DESCRIPTION
		"状态相应报文超时的数目"
	::= { frLmiStatEntry 7 }

--//************frInarp configuration*****************
frInarpConfTable	OBJECT-TYPE
	SYNTAX	SEQUENCE OF FrInarpConfEntry
	MAX-ACCESS	not-accessible
	STATUS	current
	DESCRIPTION
		"帧中继InArp协议配置表."
	::= { frIfMib 4 }

frInarpConfEntry	OBJECT-TYPE
	SYNTAX	FrInarpConfEntry
	MAX-ACCESS	not-accessible
	STATUS	current
	DESCRIPTION
		"帧中继InArp协议配置表条目."
	INDEX { frInarpConfIfIndex }
	::= { frInarpConfTable 1 }

FrInarpConfEntry ::=
	SEQUENCE {
		frInarpConfIfIndex
			INTEGER,
		frInarpEnable
			INTEGER,
		frInarpInterval
			INTEGER,
		frInarpUpdate
			INTEGER,
		frInarpStatus
			RowStatus
				}

frInarpConfIfIndex	OBJECT-TYPE
	SYNTAX	INTEGER
	MAX-ACCESS	read-only
	STATUS	current
	DESCRIPTION
		"配置InArp协议的接口的索引,与ifIndex相同."
	::= { frInarpConfEntry 1 }

frInarpEnable	OBJECT-TYPE
	SYNTAX	INTEGER {
				enable(1),
				disable(2)
				}
	MAX-ACCESS	read-create
	STATUS	current
	DESCRIPTION
		"是否在接口上启用InARP协议."
	DEFVAL { disable }
	::= { frInarpConfEntry 2 }

frInarpInterval	OBJECT-TYPE
	SYNTAX	INTEGER (15..300)
	MAX-ACCESS	read-create
	STATUS	current
	DESCRIPTION
		"发送InARP请求的时间间隔."
	::= { frInarpConfEntry 3 }

frInarpUpdate	OBJECT-TYPE
	SYNTAX	INTEGER {
				disable(1),
				enable(2)
				}
	MAX-ACCESS	read-only
	STATUS	current
	DESCRIPTION
		"是否周期性的更新动态地址映射."
	DEFVAL { disable }
	::= { frInarpConfEntry 4 }

frInarpStatus	OBJECT-TYPE
	SYNTAX	RowStatus
	MAX-ACCESS	read-create
	STATUS	current
	DESCRIPTION
		"帧中继Inarp协议配置表行状态."
	::= { frInarpConfEntry 5 }

--//************frInarp statistics*****************
frInarpStatTable	OBJECT-TYPE
	SYNTAX	SEQUENCE OF FrInarpStatEntry
	MAX-ACCESS	not-accessible
	STATUS	current
	DESCRIPTION
		"帧中继InArp协议统计表."
	::= { frIfMib 5 }

frInarpStatEntry	OBJECT-TYPE
	SYNTAX	FrInarpStatEntry
	MAX-ACCESS	not-accessible
	STATUS	current
	DESCRIPTION
		"帧中继InArp协议统计表条目."
	INDEX { frInarpConfIfIndex }
	::= { frInarpStatTable 1 }

FrInarpStatEntry ::=
		SEQUENCE {
		frInarpStatIfIndex
			INTEGER,
		frInarpReqSent
			Counter32,
		frInarpReqRecv
			Counter32,
		frInarpReplySent
			Counter32,
		frInarpReplyRecv
			Counter32
				}

frInarpStatIfIndex	OBJECT-TYPE
	SYNTAX	INTEGER
	MAX-ACCESS	read-only
	STATUS	current
	DESCRIPTION
		"InArp统计表的索引,用接口的索引值,与ifIndex相同."
	::= { frInarpStatEntry 1 }

frInarpReqSent	OBJECT-TYPE
	SYNTAX	Counter32
	MAX-ACCESS	read-only
	STATUS	current
	DESCRIPTION
		"发送的InArp请求数."
	::= { frInarpStatEntry 2 }

frInarpReqRecv	OBJECT-TYPE
	SYNTAX	Counter32
	MAX-ACCESS	read-only
	STATUS	current
	DESCRIPTION
		"接收的InArp请求数."
	::= { frInarpStatEntry 3 }

frInarpReplySent	OBJECT-TYPE
	SYNTAX	Counter32
	MAX-ACCESS	read-only
	STATUS	current
	DESCRIPTION
		"发送的InArp应答数."
	::= { frInarpStatEntry 4 }

frInarpReplyRecv	OBJECT-TYPE
	SYNTAX	Counter32
	MAX-ACCESS	read-only
	STATUS	current
	DESCRIPTION
		"接收的InArp应答数."
	::= { frInarpStatEntry 5 }

--//*******fr pvc configuration**************
frPvcConfTable	OBJECT-TYPE
	SYNTAX	SEQUENCE OF FrPvcConfEntry
	MAX-ACCESS	not-accessible
	STATUS	current
	DESCRIPTION
		"接口上的PVC配置表."
	::= { frPvcMib 1 }

frPvcConfEntry		OBJECT-TYPE
	SYNTAX	FrPvcConfEntry
	MAX-ACCESS	not-accessible
	STATUS	current
	DESCRIPTION
		"接口上的数据链路标识表条目."
	INDEX { frPvcConfIfIndex, frPvcConfDlci }
	::= { frPvcConfTable 1 }

FrPvcConfEntry ::=
	SEQUENCE {
		frPvcConfIfIndex
			INTEGER,
		frPvcConfDlci
			INTEGER,
		frPvcIntf
			DisplayString,
		frPvcUsage
			INTEGER,
		frPvcStatus
			INTEGER,
		frPvcEncType
			INTEGER,
		frPvcMapIp
			IpAddress,
		frPvcMapType
			INTEGER,
		frPvcRouteOutIntf
			DisplayString,
		frPvcRouteOutDlci
			INTEGER,
		frPvcRouteStatus
			INTEGER,
		frPvcBroadcast
			INTEGER,
		frPvcNoInarpIp
			INTEGER,
		frPvcGetFromDce
			INTEGER,
		frPvcConfTableStatus
			RowStatus
				}

frPvcConfIfIndex	OBJECT-TYPE
	SYNTAX	INTEGER
	MAX-ACCESS	read-only
	STATUS	current
	DESCRIPTION
		"接口索引,与ifIndex相同."
	::= { frPvcConfEntry 1 }

frPvcConfDlci	OBJECT-TYPE
	SYNTAX	INTEGER (16..1007)
	MAX-ACCESS	read-create
	STATUS	current
	DESCRIPTION
		"接口上的数据链路标识dlci."
	::= { frPvcConfEntry 2 }

frPvcIntf	OBJECT-TYPE
	SYNTAX	DisplayString(SIZE(1..255))
	MAX-ACCESS	read-create
	STATUS	current
	DESCRIPTION
		"PVC的接口名字."
	::= { frPvcConfEntry 3 }

frPvcUsage	OBJECT-TYPE
	SYNTAX	INTEGER {
				local(1),
				switched(2)
				}
	MAX-ACCESS	read-create
	STATUS	current
	DESCRIPTION
		"PVC的用途."
	DEFVAL { local }
	::= { frPvcConfEntry 4 }

frPvcStatus	OBJECT-TYPE
	SYNTAX	INTEGER{
				inActive(1),
				active(2),
				static(3),
				deleted(4),
				defined(5)
					}
	MAX-ACCESS	read-only
	STATUS	current
	DESCRIPTION
		"PVC的状态."
	::= { frPvcConfEntry 5 }

frPvcEncType	OBJECT-TYPE
	SYNTAX	INTEGER {
				ietf(1),
				cisco(2)
				}
	MAX-ACCESS	read-create
	STATUS	current
	DESCRIPTION
		"PVC的封装类型."
	DEFVAL { ietf }
	::= { frPvcConfEntry 6 }

frPvcMapIp	OBJECT-TYPE
	SYNTAX	IpAddress
	MAX-ACCESS	read-create
	STATUS	current
	DESCRIPTION
		"PVC映射的IP地址."
	::= { frPvcConfEntry 7 }

frPvcMapType	OBJECT-TYPE
	SYNTAX	INTEGER {
				static(1),
				dynamic(2)
				}
	MAX-ACCESS	read-create
	STATUS	current
	DESCRIPTION
		"PVC地址映射的类型."
	DEFVAL {static}
	::= { frPvcConfEntry 8 }

frPvcRouteOutIntf	OBJECT-TYPE
	SYNTAX	DisplayString (SIZE(1..255))
	MAX-ACCESS	read-create
	STATUS	current
	DESCRIPTION
		"PVC路由的输出接口."
	::= { frPvcConfEntry 9 }

frPvcRouteOutDlci	OBJECT-TYPE
	SYNTAX	INTEGER
	MAX-ACCESS	read-create
	STATUS	current
	DESCRIPTION
		"PVC路由的输出DLCI."
	::= { frPvcConfEntry 10 }

frPvcRouteStatus	OBJECT-TYPE
	SYNTAX	INTEGER {
				inactive(1),
				active(2),
				static(3)
				}
	MAX-ACCESS	read-only
	STATUS	current
	DESCRIPTION
		"PVC路由的状态."
	::= { frPvcConfEntry 11 }

frPvcBroadcast	OBJECT-TYPE
	SYNTAX	INTEGER {
				disable(1),
				enable(2)
				}
	MAX-ACCESS	read-create
	STATUS	current
	DESCRIPTION
		"PVC是否支持广播."
	DEFVAL {disable }
	::= { frPvcConfEntry 12 }

frPvcNoInarpIp		OBJECT-TYPE
	SYNTAX	INTEGER {
				disable(1),
				enable(2)
				}
	MAX-ACCESS	read-create
	STATUS	current
	DESCRIPTION
		"PVC是否支持InARP协议."
	DEFVAL {disable }
	::= { frPvcConfEntry 13 }

frPvcGetFromDce		OBJECT-TYPE
	SYNTAX	INTEGER {
				false(1),
				true(2)
				}
	MAX-ACCESS	read-create
	STATUS	current
	DESCRIPTION
		"PVC是否从DCE自动获取的."
	DEFVAL {false }
	::= { frPvcConfEntry 14 }

frPvcConfTableStatus	OBJECT-TYPE
	SYNTAX	RowStatus
	MAX-ACCESS	read-create
	STATUS	current
	DESCRIPTION
		"接口上的数据链路标识表的行状态,用于增加,删除或修改一行的内容."
	::= { frPvcConfEntry 15 }

--//**********fr pvc statistics**********
frPvcStaticTable	OBJECT-TYPE
	SYNTAX	SEQUENCE OF FrPvcStaticEntry
	MAX-ACCESS	not-accessible
	STATUS	current
	DESCRIPTION
		"接口上的PVC统计表."
	::= { frPvcMib 2 }

frPvcStaticEntry	OBJECT-TYPE
	SYNTAX	FrPvcStaticEntry
	MAX-ACCESS	not-accessible
	STATUS	current
	DESCRIPTION
		"接口上的PVC统计表条目."
	INDEX { frPvcStatIfIndex, frPvcStatDlci }
	::= { frPvcStaticTable 1 }

FrPvcStaticEntry ::=
	SEQUENCE {
		frPvcStatIfIndex
			INTEGER,
		frPvcStatDlci
			INTEGER,
		frPvcStatInPkts
			Counter32,
		frPvcStatOutPkts
			Counter32,
		frPvcStatInBytes
			Counter32,
		frPvcStatOutBytes
			Counter32,
		frPvcStatDroppedPkts
			Counter32,
		frPvcStatInFecnPkts
			Counter32,
		frPvcStatOutFecnPkts
			Counter32,
		frPvcStatInBecnPkts
			Counter32,
		frPvcStatOutBecnPkts
			Counter32,
		frPvcStatInDePkts
			Counter32,
		frPvcStatOutDePkts
			Counter32,
		frPvcSwitchPkts
			Counter32
				}

frPvcStatIfIndex	OBJECT-TYPE
	SYNTAX	INTEGER
	MAX-ACCESS	read-only
	STATUS	current
	DESCRIPTION
		"PVC统计表的接口索引,与ifIndex相同."
	::= { frPvcStaticEntry 1 }

frPvcStatDlci	OBJECT-TYPE
	SYNTAX	INTEGER (16..1007)
	MAX-ACCESS	read-only
	STATUS	current
	DESCRIPTION
		"PVC的dlci值."
	::= { frPvcStaticEntry 2 }

frPvcStatInPkts	OBJECT-TYPE
	SYNTAX	Counter32
	MAX-ACCESS	read-only
	STATUS	current
	DESCRIPTION
		"PVC输入分组的数目。"
	::= { frPvcStaticEntry 3 }

frPvcStatOutPkts	OBJECT-TYPE
	SYNTAX	Counter32
	MAX-ACCESS	read-only
	STATUS	current
	DESCRIPTION
		"PVC输出分组的数目。"
	::= { frPvcStaticEntry 4 }

frPvcStatInBytes	OBJECT-TYPE
	SYNTAX	Counter32
	MAX-ACCESS	read-only
	STATUS	current
	DESCRIPTION
		"PVC输入数据的比特数。"
	::= { frPvcStaticEntry 5 }

frPvcStatOutBytes	OBJECT-TYPE
	SYNTAX	Counter32
	MAX-ACCESS	read-only
	STATUS	current
	DESCRIPTION
		"PVC输出数据的比特数。"
	::= { frPvcStaticEntry 6 }

frPvcStatDroppedPkts	OBJECT-TYPE
	SYNTAX	Counter32
	MAX-ACCESS	read-only
	STATUS	current
	DESCRIPTION
		"PVC丢弃的分组数目。"
	::= { frPvcStaticEntry 7 }

frPvcStatInFecnPkts	OBJECT-TYPE
	SYNTAX	Counter32
	MAX-ACCESS	read-only
	STATUS	current
	DESCRIPTION
		"PVC输入的FECN置位的分组数目。"
	::= { frPvcStaticEntry 8 }

frPvcStatOutFecnPkts	OBJECT-TYPE
	SYNTAX	Counter32
	MAX-ACCESS	read-only
	STATUS	current
	DESCRIPTION
		"PVC输出的FECN置位的分组数目。"
	::= { frPvcStaticEntry 9 }

frPvcStatInBecnPkts	OBJECT-TYPE
	SYNTAX	Counter32
	MAX-ACCESS	read-only
	STATUS	current
	DESCRIPTION
		"PVC输入的BECN置位的分组数目。"
	::= { frPvcStaticEntry 10 }

frPvcStatOutBecnPkts	OBJECT-TYPE
	SYNTAX	Counter32
	MAX-ACCESS	read-only
	STATUS	current
	DESCRIPTION
		"PVC输出的BECN置位的分组数目。"
	::= { frPvcStaticEntry 11 }

frPvcStatInDePkts	OBJECT-TYPE
	SYNTAX	Counter32
	MAX-ACCESS	read-only
	STATUS	current
	DESCRIPTION
		"PVC输入的DE置位的分组数目。"
	::= { frPvcStaticEntry 12 }

frPvcStatOutDePkts	OBJECT-TYPE
	SYNTAX	Counter32
	MAX-ACCESS	read-only
	STATUS	current
	DESCRIPTION
		"PVC输出的DE置位的分组数目。"
	::= { frPvcStaticEntry 13 }

frPvcSwitchPkts	OBJECT-TYPE
	SYNTAX	Counter32
	MAX-ACCESS	read-only
	STATUS	current
	DESCRIPTION
		"PVC交换的分组数目。"
	::= { frPvcStaticEntry 14 }

END
