------------------------------------------------------------------------------
--
--  File         : sys.mi2
--  Description  :
--  Version      :
--  Date         : March 3, 2003
-- 	Copyright    : 2003 by maipu (sichuan) communication technology co.,ltd.
--					All rights reserved.
--
-- $Id:
--
------------------------------------------------------------------------------

------------------------------------------------------------------------------
MPPORT-CAPABILITY DEFINITIONS ::= BEGIN


IMPORTS
        MODULE-IDENTITY, OBJECT-TYPE, NOTIFICATION-TYPE, enterprises, Counter32, Gauge32,
        Integer32, Unsigned32, TimeTicks,IpAddress,Counter64
        	                                    FROM SNMPv2-SMI
        TEXTUAL-CONVENTION, TruthValue, MacAddress,
	RowStatus, DisplayString, DateAndTime
                                                 FROM SNMPv2-TC
        MODULE-COMPLIANCE, OBJECT-GROUP
        	FROM SNMPv2-CONF
        mpMgmt
        	FROM MAIPU-SMI
        ObjectName, ObjectSyntax, NetworkAddress
                FROM RFC1155-SMI;


maipu               	OBJECT IDENTIFIER ::= { enterprises 5651 }
mpMgmt2             	OBJECT IDENTIFIER ::= { maipu 6 }
mpSwitchTech        	OBJECT IDENTIFIER ::= { mpMgmt2 3 }
mpSwPort            	OBJECT IDENTIFIER ::= { mpSwitchTech 1 }
mpPortConformance   	OBJECT IDENTIFIER ::= { mpSwPort 13 }

mpPortCapability    	MODULE-IDENTITY
                    		LAST-UPDATED 	"1012271112Z"
                    		ORGANIZATION 	"四川迈普数据通信股份有限公司,
                    		             	 Maipu (Sichuan) Communication Technology Co. LTD."
                    		CONTACT-INFO
                    			"编 写 人:  ???
                    			 联系地址：四川省 成都市 高新区 九兴大道16号
                    			 邮    编：    610041
                    			 电    话：
                    			 传    真：
                    			 电子邮件： ????"
                    		DESCRIPTION
                      			"Subtree for maipu port capability mib."
                    		::= { mpPortConformance  3 }



mpPortArlMode       	OBJECT-TYPE
                    		SYNTAX  INTEGER {
                    			         svl(1),
                    			          ivl(2)
                    			        }
                    		MAX-ACCESS  read-only
                    		STATUS  current
                    		DESCRIPTION
                    			"If device is in svl mode,then read mpSwitchTech.mpSwPort.mprSwArlTable to get mac entries.
                           If device is in ivl mode,then read mpSwitchTech.mpSwPort.mprSwIvlArlTable to get mac entries."
                    		::= { mpPortCapability 1 }

mpPortSwArea        	OBJECT-TYPE
                    		SYNTAX  TruthValue
                    		MAX-ACCESS  read-only
                    		STATUS  current
                    		DESCRIPTION
                    			"If device has swarea limit,then dot1qVlanStatic field dot1qVlanIndex high bits than 12 bit indicate swarea number and low 12 bits indicate vlan id.
                    			 If device has no swarea limit,then dot1qVlanStatic field dot1qVlanIndex is standard meaning indicate vlan id."
                    		::= { mpPortCapability 2 }



END
------------------------------------------------------------------------------
-- ============================================================================
-- $Log: mpPortCapability.mib,v $
-- Revision 1.1  2010/12/28 00:57:21  yanxq
-- add mprSwIvlArlTable #ROUTER-16526
--
--
--
-- ============================================================================
