------------------------------------------------------------------------------
--
--  File         : sys.mi2
--  Description  :
--  Version      :
--  Date         : March 3, 2003
-- 	Copyright    : 2003 by maipu (sichuan) communication technology co.,ltd.
--					All rights reserved.
--
-- $Id:
--
------------------------------------------------------------------------------

------------------------------------------------------------------------------
MAIPU-NTP-MIB DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress,
	RowStatus, DisplayString, DateAndTime
                                                 FROM SNMPv2-TC
        MODULE-COMPLIANCE, OBJECT-GROUP
        	FROM SNMPv2-CONF
        mpMgmt
        	FROM MAIPU-SMI
        ObjectName, ObjectSyntax, NetworkAddress
                FROM RFC1155-SMI;



ntpMib              	MODULE-IDENTITY
                    		LAST-UPDATED 	"0808051413Z"
                    		ORGANIZATION 	"四川迈普数据通信股份有限公司,
                    		             	 Maipu (Sichuan) Communication Technology Co. LTD."
                    		CONTACT-INFO
                    			"编 写 人:  ???
                    			 联系地址：四川省 成都市 高新区 九兴大道16号
                    			 邮    编：    610041
                    			 电    话：
                    			 传    真：
                    			 电子邮件： ????"
                    		DESCRIPTION
                      			""
                    		::= { mpMgmt  97 }

------------------------------------------------------------------------------
-- Textual Conventions
------------------------------------------------------------------------------
EnabledStatus ::= TEXTUAL-CONVENTION
    STATUS      current
    DESCRIPTION
        "A simple status value for the object."
    SYNTAX      INTEGER {
	enabled(1), disabled(2) }

------------------------------------------------------------------------------


ntpAuthenticationCntl	OBJECT-TYPE
                    		SYNTAX  EnabledStatus
                    		MAX-ACCESS  read-write
                    		STATUS  current
                    		DESCRIPTION
                    			"Indicates whether the NTP authenticate enabled or not. 'Enabled' results in need authenticate ; 'disabled',need not authenticate."
                    		::= { ntpMib 1 }

ntpMasterCntl       	OBJECT-TYPE
                    		SYNTAX  EnabledStatus
                    		MAX-ACCESS  read-write
                    		STATUS  current
                    		DESCRIPTION
                    			"Indicates whether the NTP act as a master or not. 'Enabled' results in act as master and provide clock resource only, can not be synchronized by anyone else; 'disabled'results in can be synchronized and synchronize others."
                    		::= { ntpMib 2 }

ntpMasterStratum    	OBJECT-TYPE
                    		SYNTAX  INTEGER(2..15)
                    		MAX-ACCESS  read-write
                    		STATUS  current
                    		DESCRIPTION
                    			"The ntp master's stratum number"
                    		::= { ntpMib 3 }

ntpSynStatus        	OBJECT-TYPE
                    		SYNTAX  INTEGER {
                    			         synchronized  (1),
                    			          unsynchronized (2)
                    			        }
                    		MAX-ACCESS  read-only
                    		STATUS  current
                    		DESCRIPTION
                    			"Indicates the synchronization status of the local clock ."
                    		::= { ntpMib 4 }

ntpSynTime          	OBJECT-TYPE
                    		SYNTAX  DisplayString(SIZE(0..255))
                    		MAX-ACCESS  read-only
                    		STATUS  current
                    		DESCRIPTION
                    			"This is the local time, in timestamp format, when the local clock was last updated. If the local clock has never been synchronized,the value is zero."
                    		::= { ntpMib 5 }

ntpAuthenticationKeyTable	OBJECT-TYPE
                    		SYNTAX  SEQUENCE OF   NtpAuthenticationKeyEntry
                    		MAX-ACCESS  not-accessible
                    		STATUS  current
                    		DESCRIPTION
                    			"config the authentication-key list"
                    		::= { ntpMib 20 }

ntpAuthenticationKeyEntry	OBJECT-TYPE
                    		SYNTAX  NtpAuthenticationKeyEntry
                    		MAX-ACCESS  not-accessible
                    		STATUS  current
                    		DESCRIPTION
                    			"config the authentication-key list"
                    		INDEX  { ntpAuthKeyNum }
                    		::= { ntpAuthenticationKeyTable 1 }

NtpAuthenticationKeyEntry	::= SEQUENCE {
                    			ntpAuthKeyNum          Unsigned32,
                    			ntpAuthStr             DisplayString,
                    			ntpAuthKeyRowStatus    RowStatus
                    	             }


ntpAuthKeyNum       	OBJECT-TYPE
                    		SYNTAX  Unsigned32
                    		MAX-ACCESS  not-accessible
                    		STATUS  current
                    		DESCRIPTION
                    			"Key ID for authentication string"
                    		::= { ntpAuthenticationKeyEntry 1 }

ntpAuthStr          	OBJECT-TYPE
                    		SYNTAX  DisplayString(SIZE(0..20))
                    		MAX-ACCESS  read-create
                    		STATUS  current
                    		DESCRIPTION
                    			"It auhentication string used to encrypt the packet"
                    		::= { ntpAuthenticationKeyEntry 2 }

ntpAuthKeyRowStatus 	OBJECT-TYPE
                    		SYNTAX  RowStatus
                    		MAX-ACCESS  read-create
                    		STATUS  current
                    		DESCRIPTION
                    			""
                    		::= { ntpAuthenticationKeyEntry 3 }

ntpTrustKeyTable    	OBJECT-TYPE
                    		SYNTAX  SEQUENCE OF   NtpTrustKeyEntry
                    		MAX-ACCESS  not-accessible
                    		STATUS  current
                    		DESCRIPTION
                    			""
                    		::= { ntpMib 21 }

ntpTrustKeyEntry    	OBJECT-TYPE
                    		SYNTAX  NtpTrustKeyEntry
                    		MAX-ACCESS  not-accessible
                    		STATUS  current
                    		DESCRIPTION
                    			""
                    		INDEX  { ntpTrustKeyNum }
                    		::= { ntpTrustKeyTable 1 }

NtpTrustKeyEntry    	::= SEQUENCE {
                    			ntpTrustKeyNum         Unsigned32,
                    			ntpTrustkeyRowStatus   RowStatus
                    	             }


ntpTrustKeyNum      	OBJECT-TYPE
                    		SYNTAX  Unsigned32
                    		MAX-ACCESS  not-accessible
                    		STATUS  current
                    		DESCRIPTION
                    			"It provide misconfiguration of authentication key ID"
                    		::= { ntpTrustKeyEntry 1 }

ntpTrustkeyRowStatus	OBJECT-TYPE
                    		SYNTAX  RowStatus
                    		MAX-ACCESS  read-create
                    		STATUS  current
                    		DESCRIPTION
                    			""
                    		::= { ntpTrustKeyEntry 2 }

ntpServerTable      	OBJECT-TYPE
                    		SYNTAX  SEQUENCE OF   NtpServerEntry
                    		MAX-ACCESS  not-accessible
                    		STATUS  current
                    		DESCRIPTION
                    			""
                    		::= { ntpMib 22 }

ntpServerEntry      	OBJECT-TYPE
                    		SYNTAX  NtpServerEntry
                    		MAX-ACCESS  not-accessible
                    		STATUS  current
                    		DESCRIPTION
                    			""
                    		INDEX  { ntpServerAddr, ntpServerVRF }
                    		::= { ntpServerTable 1 }

NtpServerEntry      	::= SEQUENCE {
                    			ntpServerAddr          IpAddress,
                    			ntpServerVRF           DisplayString,
                    			ntpServerKeyNum        Unsigned32,
                    			ntpServerVersion       INTEGER,
                    			ntpServerRowStatus     RowStatus
                    	             }


ntpServerAddr       	OBJECT-TYPE
                    		SYNTAX  IpAddress
                    		MAX-ACCESS  not-accessible
                    		STATUS  current
                    		DESCRIPTION
                    			""
                    		::= { ntpServerEntry 1 }

ntpServerVRF        	OBJECT-TYPE
                    		SYNTAX  DisplayString(SIZE(1..31))
                    		MAX-ACCESS  not-accessible
                    		STATUS  current
                    		DESCRIPTION
                    			""
                    		::= { ntpServerEntry 2 }

ntpServerKeyNum     	OBJECT-TYPE
                    		SYNTAX  Unsigned32
                    		MAX-ACCESS  read-create
                    		STATUS  current
                    		DESCRIPTION
                    			""
                    		::= { ntpServerEntry 3 }

ntpServerVersion    	OBJECT-TYPE
                    		SYNTAX  INTEGER {
                    			         ver1(1),
                    			          ver2(2),
                    			          ver3(3),
                    			          ver4(4)
                    			        }
                    		MAX-ACCESS  read-create
                    		STATUS  current
                    		DESCRIPTION
                    			"This value identifies the particular version of the NTP supported by this node."
                    		::= { ntpServerEntry 4 }

ntpServerRowStatus  	OBJECT-TYPE
                    		SYNTAX  RowStatus
                    		MAX-ACCESS  read-create
                    		STATUS  current
                    		DESCRIPTION
                    			""
                    		::= { ntpServerEntry 5 }



END
------------------------------------------------------------------------------
-- ============================================================================
-- $Log: ntpMib.mib,v $
-- Revision 1.1  2010/06/21 11:18:46  liyh
-- first commit
--
-- Revision 1.1.6.1  2010/01/04 11:49:15  shenjie
-- router-13939,平台变更合入到RM7B
--
-- Revision 1.1.2.1  2008/10/28 12:49:37  shenjie
-- VRSP-7878,NTP支持lpu向mpu同步时间,shenjie
--
--
--
-- ============================================================================
