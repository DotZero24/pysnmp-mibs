-- *****************************************************************
-- MAIPU-MODEM.mib:  Maipu enterprise device modem MIB file
--
--version 1.0.0.0, Feb 20, 2001 Huanglulu
--version 1.0.0.1, Sep 13, 2002 Huanglulu
--
-- Copyright (c)  by Maipu DataComm Inc.
-- All rights reserved.
--
-- *****************************************************************
--

MAIPU-MODEM-MIB DEFINITIONS ::= BEGIN

IMPORTS
    RowStatus							FROM SNMPv2-TC
    MODULE-IDENTITY, OBJECT-TYPE        FROM SNMPv2-SMI
    mpMgmt                              FROM MAIPU-SMI;

mpModemMib MODULE-IDENTITY
    LAST-UPDATED "0102200000Z"
    ORGANIZATION "Maipu DataComm"
    CONTACT-INFO
	"   Maipu DataComm
		Customer Service

		Postal: Consulate Drive
			Chengdu, Sichuan  610041
			China

		Tel: 86-028-5161006

		E-mail: office@maipu.com"
    DESCRIPTION
		"The assignments for Maipu router's MIB of modem infomation!"
    ::= {mpMgmt 15 }

modemConfTable OBJECT-TYPE
    SYNTAX SEQUENCE OF ModemConfEntry
    MAX-ACCESS not-accessible
    STATUS current
    DESCRIPTION
		"modem的配置表."
    ::= { mpModemMib 1 }

modemConfEntry OBJECT-TYPE
    SYNTAX ModemConfEntry
    MAX-ACCESS not-accessible
    STATUS current
    DESCRIPTION
		"modem配置表条目."
    INDEX { modemIfIndex }
    ::= { modemConfTable 1 }

ModemConfEntry ::=
	SEQUENCE {
		modemIfIndex
			INTEGER,
		modemLocation
			INTEGER,
		modemActive
			INTEGER,
		modemLine
			INTEGER,
		modemParty
			INTEGER,
		modemAsyncMode
			INTEGER,
		modemClockMode
			INTEGER,
		modemClockRate
			INTEGER,
		modemStatus
			INTEGER
				}

modemIfIndex	OBJECT-TYPE
	SYNTAX	INTEGER
	MAX-ACCESS	read-only
	STATUS	current
	DESCRIPTION
		"modem配置表的索引,对应于接口索引,与ifIndex相同."
	::= { modemConfEntry 1 }

modemLocation	OBJECT-TYPE
	SYNTAX	INTEGER {
				inner(1),
				outer(2),
				noOuter(3)
					}
	MAX-ACCESS	read-write
	STATUS	current
	DESCRIPTION
		"内置modem或允许外置modem."
	::= { modemConfEntry 2 }

modemActive	OBJECT-TYPE
	SYNTAX	INTEGER {
				enable(1),
				disable(2)
					}
	MAX-ACCESS	read-create
	STATUS	current
	DESCRIPTION
		"是否启动modem."
	::= { modemConfEntry 3 }

modemLine	OBJECT-TYPE
	SYNTAX	INTEGER {
				leased(1),
				nonLeased(2)
					}
	MAX-ACCESS	read-create
	STATUS	current
	DESCRIPTION
		"modem是否使用专线."
	DEFVAL { nonLeased }
	::= { modemConfEntry 4 }

modemParty	OBJECT-TYPE
	SYNTAX	INTEGER {
				originate(1),
				answer(2),
				none(3)
					}
	MAX-ACCESS	read-create
	STATUS	current
	DESCRIPTION
		"配置modem成为主叫/被叫."
	DEFVAL { none }
	::= { modemConfEntry 5 }

modemAsyncMode	OBJECT-TYPE
	SYNTAX	INTEGER {
				buffer(1),
				direct(2),
				errorCorrect(3)
					}
	MAX-ACCESS	read-create
	STATUS	current
	DESCRIPTION
		"配置modem异步模式."
	::= { modemConfEntry 6 }


modemClockMode	OBJECT-TYPE
	SYNTAX	INTEGER {
				internal(1),
				external(2),
				slave(3)
					}
	MAX-ACCESS	read-create
	STATUS	current
	DESCRIPTION
		"modem使用的时钟模式."
	::= { modemConfEntry 7 }

modemClockRate	OBJECT-TYPE
	SYNTAX	INTEGER
	MAX-ACCESS	read-create
	STATUS	current
	DESCRIPTION
		"modem使用的时钟速率."
	::= { modemConfEntry 8 }

modemStatus	OBJECT-TYPE
	SYNTAX	INTEGER {
				unconfig(1),
				idle(2),
				atMode(3),
				dialout(4),
				answer(5),
				connect(6),
				config(7),
				hangUp(8)
					}
	MAX-ACCESS	read-only
	STATUS	current
	DESCRIPTION
		"modem的状态."
	::= { modemConfEntry 9 }


--//*************
modemDialerTable	OBJECT-TYPE
	SYNTAX	SEQUENCE OF ModemDialerEntry
	MAX-ACCESS	not-accessible
	STATUS	current
	DESCRIPTION
		"modem拨号配置表."
	::= { mpModemMib 2 }

modemDialerEntry	OBJECT-TYPE
	SYNTAX	ModemDialerEntry
	MAX-ACCESS	not-accessible
	STATUS	current
	DESCRIPTION
		"modem拨号配置表条目."
	INDEX { modemDialerIfIndex, modemDialerString }
	::= { modemDialerTable 1 }

ModemDialerEntry ::=
	SEQUENCE {
		modemDialerIfIndex
			INTEGER,
		modemDialerString
			OCTET STRING,
		modemDialerStatus
			RowStatus
				}

modemDialerIfIndex	OBJECT-TYPE
	SYNTAX	INTEGER
	MAX-ACCESS	read-create
	STATUS	current
	DESCRIPTION
		"modem拨号配置表的索引,对应于接口索引,与ifIndex相同."
	::= { modemDialerEntry 1 }

modemDialerString	OBJECT-TYPE
	SYNTAX	OCTET STRING
	MAX-ACCESS	read-create
	STATUS	current
	DESCRIPTION
		"modem拨号使用的号码."
	::= { modemDialerEntry 2 }

modemDialerStatus	OBJECT-TYPE
	SYNTAX	RowStatus
	MAX-ACCESS	read-create
	STATUS	current
	DESCRIPTION
		"modem拨号配置表行状态,用于增加,删除或修改一行的内容."
	::= { modemDialerEntry 3 }

--//*************
modemScriptTable	OBJECT-TYPE
	SYNTAX	SEQUENCE OF ModemScriptEntry
	MAX-ACCESS	not-accessible
	STATUS	current
	DESCRIPTION
		"modem脚本配置表."
	::= { mpModemMib 3 }

modemScriptEntry	OBJECT-TYPE
	SYNTAX	ModemScriptEntry
	MAX-ACCESS	not-accessible
	STATUS	current
	DESCRIPTION
		"modem脚本配置表条目."
	INDEX { modemScriptName }
	::= { modemScriptTable 1 }

ModemScriptEntry ::=
	SEQUENCE {
		modemScriptName
			OCTET STRING,
		modemScriptString
			OCTET STRING,
		modemScriptStatus
			RowStatus
				}

modemScriptName	OBJECT-TYPE
	SYNTAX	OCTET STRING
	MAX-ACCESS	read-create
	STATUS	current
	DESCRIPTION
		"modem脚本名."
	::= { modemScriptEntry 1 }

modemScriptString	OBJECT-TYPE
	SYNTAX	OCTET STRING
	MAX-ACCESS	read-create
	STATUS	current
	DESCRIPTION
		"modem脚本."
	::= { modemScriptEntry 2 }

modemScriptStatus	OBJECT-TYPE
	SYNTAX	RowStatus
	MAX-ACCESS	read-create
	STATUS	current
	DESCRIPTION
		"modem脚本配置表行状态,用于增加,删除或修改一行的内容."
	::= { modemScriptEntry 3 }

END
