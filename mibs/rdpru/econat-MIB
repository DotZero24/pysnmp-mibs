econat-MIB DEFINITIONS ::= BEGIN

IMPORTS
        enterprises
                FROM SNMPv2-SMI
        OBJECT-TYPE
                FROM RFC-1212

        DisplayString
                FROM RFC-1213
dot1dBridge, dot1dBasePortEntry, dot1dBasePort
		FROM BRIDGE-MIB;

rdp	       OBJECT IDENTIFIER ::= {enterprises 45555}
econat     OBJECT IDENTIFIER ::= {rdp 1}
counters   OBJECT IDENTIFIER ::= {econat 2}
poolsinfo  OBJECT IDENTIFIER ::= {counters 61}
poolid     OBJECT IDENTIFIER ::= {poolsinfo 0}


econatGaddrAlloc OBJECT-TYPE
  SYNTAX  DisplayString
  ACCESS  read-only
  STATUS  mandatory
  DESCRIPTION
          "Counts of allocating global ip"
  ::= {counters 1}

econatGaddrFree OBJECT-TYPE
  SYNTAX  DisplayString
  ACCESS  read-only
  STATUS  mandatory
  DESCRIPTION
          "Counts of freeing global ip"
  ::= {counters 2}

econatPortBlockAlloc OBJECT-TYPE
  SYNTAX  DisplayString
  ACCESS  read-only
  STATUS  mandatory
  DESCRIPTION
          "Counts of port block allocating in already allocated global addres"
  ::= {counters 3}

econatPortBlockFree OBJECT-TYPE
  SYNTAX  DisplayString
  ACCESS  read-only
  STATUS  mandatory
  DESCRIPTION
          "Counts of freeing port blocks"
  ::= {counters 4}

econatPortAlloc OBJECT-TYPE
  SYNTAX  DisplayString
  ACCESS  read-only
  STATUS  mandatory
  DESCRIPTION
          "Counts of allocating port in already allocated block or global address"
  ::= {counters 5}

econatPortFree OBJECT-TYPE
  SYNTAX  DisplayString
  ACCESS  read-only
  STATUS  mandatory
  DESCRIPTION
          "Counts of freeing ports"
  ::= {counters 6}

econatSessionAlloc OBJECT-TYPE
  SYNTAX  DisplayString
  ACCESS  read-only
  STATUS  mandatory
  DESCRIPTION
          "Counts of successful session creating"
  ::= {counters 7}

econatSessionFree OBJECT-TYPE
  SYNTAX  DisplayString
  ACCESS  read-only
  STATUS  mandatory
  DESCRIPTION
          "Counts of successful session freeing"
  ::= {counters 8}

econatSessionAllocErrorEgress OBJECT-TYPE
  SYNTAX  DisplayString
  ACCESS  read-only
  STATUS  mandatory
  DESCRIPTION
          "Counts of failed tries of allocating either block or port on egress"
  ::= {counters 9}

econatSessionAllocErrorIngress OBJECT-TYPE
  SYNTAX  DisplayString
  ACCESS  read-only
  STATUS  mandatory
  DESCRIPTION
          "Counts of failed tries of allocating either block or port on ingress"
  ::= {counters 10}

econatTranslationAllocError OBJECT-TYPE
  SYNTAX  DisplayString
  ACCESS  read-only
  STATUS  mandatory
  DESCRIPTION
          "Counts of failed tries of allocating entry in translation table"
  ::= {counters 11}

econatSessionFreeError OBJECT-TYPE
  SYNTAX  DisplayString
  ACCESS  read-only
  STATUS  mandatory
  DESCRIPTION
          "Counts of failed tries of freeing sessions"
  ::= {counters 12}

econatLoggedMessages OBJECT-TYPE
  SYNTAX  DisplayString
  ACCESS  read-only
  STATUS  mandatory
  DESCRIPTION
          "Counts of logged (but not sent yet) connlog messages"
  ::= {counters 13}

econatDroppedMessages OBJECT-TYPE
  SYNTAX  DisplayString
  ACCESS  read-only
  STATUS  mandatory
  DESCRIPTION
          "Counts of failed tries of logging connlog messages"
  ::= {counters 14}

econatAvgEgressRxQueue OBJECT-TYPE
  SYNTAX  DisplayString
  ACCESS  read-only
  STATUS  mandatory
  DESCRIPTION
          "Average length of egress rx queue"
  ::= {counters 15}

econatAvgIngressRxQueue OBJECT-TYPE
  SYNTAX  DisplayString
  ACCESS  read-only
  STATUS  mandatory
  DESCRIPTION
          "Average length of ingress rx queue"
  ::= {counters 16}


econatEgressRxQueueVoid OBJECT-TYPE
  SYNTAX  DisplayString
  ACCESS  read-only
  STATUS  mandatory
  DESCRIPTION
          "Counts of main cycles when we didn't get rx egress packets from queue at all"
  ::= {counters 17}


econatEgressRxQueueMedium OBJECT-TYPE
  SYNTAX  DisplayString
  ACCESS  read-only
  STATUS  mandatory
  DESCRIPTION
          "Counts of main cycles when we get rx egress packets from queue less than we could"
  ::= {counters 18}


econatEgressRxQueueOverflow OBJECT-TYPE
  SYNTAX  DisplayString
  ACCESS  read-only
  STATUS  mandatory
  DESCRIPTION
          "Counts of main cycles when we get all rx egress packets from queue"
  ::= {counters 19}


econatIngressRxQueueVoid OBJECT-TYPE
  SYNTAX  DisplayString
  ACCESS  read-only
  STATUS  mandatory
  DESCRIPTION
          "Counts of main cycles when we didn't get rx ingress packets from queue at all"
  ::= {counters 20}


econatIngressRxQueueMedium OBJECT-TYPE
  SYNTAX  DisplayString
  ACCESS  read-only
  STATUS  mandatory
  DESCRIPTION
          "Counts of main cycles when we get rx ingress packets from queue less than we could"
  ::= {counters 21}


econatIngressRxQueueOverflow OBJECT-TYPE
  SYNTAX  DisplayString
  ACCESS  read-only
  STATUS  mandatory
  DESCRIPTION
          "Counts of main cycles when we get all rx ingress packets from queue"
  ::= {counters 22}


econatDispFreeMbufs0 OBJECT-TYPE
  SYNTAX  DisplayString
  ACCESS  read-only
  STATUS  mandatory
  DESCRIPTION
          "Counts of free membufs of dataplane mempool on socket 0"
  ::= {counters 23}


econatDispFreeMbufs1 OBJECT-TYPE
  SYNTAX  DisplayString
  ACCESS  read-only
  STATUS  mandatory
  DESCRIPTION
          "Counts of free membufs of dataplane mempool on socket 1"
  ::= {counters 24}


econatAvgConnRequestsPerBurst OBJECT-TYPE
  SYNTAX  DisplayString
  ACCESS  read-only
  STATUS  mandatory
  DESCRIPTION
          "Counts of average connection requests per burst"
  ::= {counters 25}


econatAvgConnRequestsPerNonEmptyBurst OBJECT-TYPE
  SYNTAX  DisplayString
  ACCESS  read-only
  STATUS  mandatory
  DESCRIPTION
          "Counts of average connection requests per non empty burst"
  ::= {counters 26}


econatConnRingVoid OBJECT-TYPE
  SYNTAX  DisplayString
  ACCESS  read-only
  STATUS  mandatory
  DESCRIPTION
          "Counts of main cycles when we didn't processed requests at all on both (urgent/lazy) connrings"
  ::= {counters 27}


econatConnRingMedium OBJECT-TYPE
  SYNTAX  DisplayString
  ACCESS  read-only
  STATUS  mandatory
  DESCRIPTION
          "Counts of main cycles when we processed requests on both (urgent/lazy) connrings less than we could"
  ::= {counters 28}


econatConnRingPostponed OBJECT-TYPE
  SYNTAX  DisplayString
  ACCESS  read-only
  STATUS  mandatory
  DESCRIPTION
          "Counts of main cycles when we have postponed some packets in lazy connring. Urgent connring is processing first, cause has more priority"
  ::= {counters 29}


econatConnRingOverflow OBJECT-TYPE
  SYNTAX  DisplayString
  ACCESS  read-only
  STATUS  mandatory
  DESCRIPTION
          "Counts of failed tries of putting packets to both (urgent/lazy) connrings - conring is full"
  ::= {counters 30}


econatRacePrevented1 OBJECT-TYPE
  SYNTAX  DisplayString
  ACCESS  read-only
  STATUS  mandatory
  DESCRIPTION
          "Incremented when we detect data corruption from another threads. No panic, it's a standard situation"
  ::= {counters 32}


econatRacePrevented2 OBJECT-TYPE
  SYNTAX  DisplayString
  ACCESS  read-only
  STATUS  mandatory
  DESCRIPTION
          "Incremented when we detect data corruption from another threads. No panic, it's a standard situation"
  ::= {counters 33}


econatRacePrevented3 OBJECT-TYPE
  SYNTAX  DisplayString
  ACCESS  read-only
  STATUS  mandatory
  DESCRIPTION
          "Incremented when we detect data corruption from another threads. No panic, it's a standard situation"
  ::= {counters 34}


econatIpDropUnknownProto OBJECT-TYPE
  SYNTAX  DisplayString
  ACCESS  read-only
  STATUS  mandatory
  DESCRIPTION
          "Counts of dropped packets with unknown prototype
		  It's not UDP/TCP/ICMP/GRE/RDP/IPv4/IPv6/ESP/AH/L2TP"
  ::= {counters 40}


econatIpPassUnknownProto OBJECT-TYPE
  SYNTAX  DisplayString
  ACCESS  read-only
  STATUS  mandatory
  DESCRIPTION
          "Counts of passed packets with unknown prototype
		  It's not UDP/TCP/ICMP/GRE/RDP/IPv4/IPv6/ESP/AH/L2TP"
  ::= {counters 41}


econatIpDropOpaqueProto OBJECT-TYPE
  SYNTAX  DisplayString
  ACCESS  read-only
  STATUS  mandatory
  DESCRIPTION
          "Counts of dropped packets with next prototypes:
		  RDP/IPv4/IPv6/ESP/AH/L2TP"
  ::= {counters 42}


econatIpPassOpaqueProto OBJECT-TYPE
  SYNTAX  DisplayString
  ACCESS  read-only
  STATUS  mandatory
  DESCRIPTION
          "Counts of passed packets with next prototypes:
		  RDP/IPv4/IPv6/ESP/AH/L2TP"
  ::= {counters 43}


econatTranslatedOpaque OBJECT-TYPE
  SYNTAX  DisplayString
  ACCESS  read-only
  STATUS  mandatory
  DESCRIPTION
          "Counts of translated packets with next prototypes:
		  RDP/IPv4/IPv6/ESP/AH/L2TP"
  ::= {counters 44}


econatInOpaqueError OBJECT-TYPE
  SYNTAX  DisplayString
  ACCESS  read-only
  STATUS  mandatory
  DESCRIPTION
          "Counts of error in packets with next prototypes:
		  RDP/IPv4/IPv6/ESP/AH/L2TP"
  ::= {counters 45}


econatEgressOpaqueNoPool OBJECT-TYPE
  SYNTAX  DisplayString
  ACCESS  read-only
  STATUS  mandatory
  DESCRIPTION
          "Counts of failed tries of finding pool for packet on egress with next prototypes:
		  RDP/IPv4/IPv6/ESP/AH/L2TP"
  ::= {counters 46}


econatIngressOpaqueNoPool OBJECT-TYPE
  SYNTAX  DisplayString
  ACCESS  read-only
  STATUS  mandatory
  DESCRIPTION
          "Counts of failed tries of finding pool for packet on ingress with next prototypes:
		  RDP/IPv4/IPv6/ESP/AH/L2TP"
  ::= {counters 47}


econatSessionAllocNoPoolEgress OBJECT-TYPE
  SYNTAX  DisplayString
  ACCESS  read-only
  STATUS  mandatory
  DESCRIPTION
          "Counts of moments when we didn't find pool for egress packet"
  ::= {counters 50}


econatSessionAllocNoPoolIngress OBJECT-TYPE
  SYNTAX  DisplayString
  ACCESS  read-only
  STATUS  mandatory
  DESCRIPTION
          "Counts of moments when we didn't find pool for ingress packet"
  ::= {counters 51}


econatAvgEgressConnRequests OBJECT-TYPE
  SYNTAX  DisplayString
  ACCESS  read-only
  STATUS  mandatory
  DESCRIPTION
          "Counts of period average connection requests on egress"
  ::= {counters 55}


econatAvgIngressConnRequests OBJECT-TYPE
  SYNTAX  DisplayString
  ACCESS  read-only
  STATUS  mandatory
  DESCRIPTION
          "Counts of period average connection requests on ingress"
  ::= {counters 56}

econatAvgEgressConnsCreated OBJECT-TYPE
  SYNTAX  DisplayString
  ACCESS  read-only
  STATUS  mandatory
  DESCRIPTION
          "Counts of period average connection created on egress"
  ::= {counters 57}


econatAvgIngressConnsCreated OBJECT-TYPE
  SYNTAX  DisplayString
  ACCESS  read-only
  STATUS  mandatory
  DESCRIPTION
          "Counts of period average connection created on ingress"
  ::= {counters 58}


econatUsedNaptPortBlocks OBJECT-TYPE
  SYNTAX  DisplayString
  ACCESS  read-only
  STATUS  mandatory
  DESCRIPTION
          "Counts of used napt port blocks"
  ::= {counters 59}


econatUsedNaptPorts OBJECT-TYPE
  SYNTAX  DisplayString
  ACCESS  read-only
  STATUS  mandatory
  DESCRIPTION
          "Counts of used napt ports"
  ::= {counters 60}


econatNaptTotalAddresses OBJECT-TYPE
  SYNTAX  DisplayString
  ACCESS  read-only
  STATUS  mandatory
  DESCRIPTION
          "Total amount of napt addresses of current pool"
  ::= {poolid 3}


econatNaptUsedAddress OBJECT-TYPE
  SYNTAX  DisplayString
  ACCESS  read-only
  STATUS  mandatory
  DESCRIPTION
          "Amount of used napt addresses of current pool"
  ::= {poolid 4}


econatNaptUnusedAddresses OBJECT-TYPE
  SYNTAX  DisplayString
  ACCESS  read-only
  STATUS  mandatory
  DESCRIPTION
          "Amount of unused napt addresses of current pool"
  ::= {poolid 5}


econatNaptTotalPortsTcp OBJECT-TYPE
  SYNTAX  DisplayString
  ACCESS  read-only
  STATUS  mandatory
  DESCRIPTION
          "Total amount of napt TCP ports of current pool"
  ::= {poolid 6}


econatNaptTotalPortsUdp OBJECT-TYPE
  SYNTAX  DisplayString
  ACCESS  read-only
  STATUS  mandatory
  DESCRIPTION
          "Total amount of napt UDP ports of current pool"
  ::= {poolid 7}


econatNaptTotalPortsIcmp OBJECT-TYPE
  SYNTAX  DisplayString
  ACCESS  read-only
  STATUS  mandatory
  DESCRIPTION
          "Total amount of napt ICMP ports of current pool"
  ::= {poolid 8}


econatNaptUsedPortsTcp OBJECT-TYPE
  SYNTAX  DisplayString
  ACCESS  read-only
  STATUS  mandatory
  DESCRIPTION
          "Amount of used napt TCP ports of current pool"
  ::= {poolid 9}


econatNaptUsedPortsUdp OBJECT-TYPE
  SYNTAX  DisplayString
  ACCESS  read-only
  STATUS  mandatory
  DESCRIPTION
          "Amount of used napt UDP ports of current pool"
  ::= {poolid 10}


econatNaptUsedPortsIcmp OBJECT-TYPE
  SYNTAX  DisplayString
  ACCESS  read-only
  STATUS  mandatory
  DESCRIPTION
          "Amount of used napt ICMP ports of current pool"
  ::= {poolid 11}


econatBnatTotalAddresses OBJECT-TYPE
  SYNTAX  DisplayString
  ACCESS  read-only
  STATUS  mandatory
  DESCRIPTION
          "Total amount of bnat total addresses of current pool"
  ::= {poolid 12}


econatBnatStaticAddresses OBJECT-TYPE
  SYNTAX  DisplayString
  ACCESS  read-only
  STATUS  mandatory
  DESCRIPTION
          "Amount of bnat static addresses of current pool"
  ::= {poolid 13}


econatBnatUsedAddresses OBJECT-TYPE
  SYNTAX  DisplayString
  ACCESS  read-only
  STATUS  mandatory
  DESCRIPTION
          "Amount of used bnat addresses of current pool"
  ::= {poolid 14}


econatBnatUnusedAddresses OBJECT-TYPE
  SYNTAX  DisplayString
  ACCESS  read-only
  STATUS  mandatory
  DESCRIPTION
          "Amount of unused bnat addresses of current pool"
  ::= {poolid 15}


econatBnatConnectionsTcpIngress OBJECT-TYPE
  SYNTAX  DisplayString
  ACCESS  read-only
  STATUS  mandatory
  DESCRIPTION
          "Counts of bnat TCP connections on ingress"
  ::= {poolid 16}


econatBnatConnectionsUdpIngress OBJECT-TYPE
  SYNTAX  DisplayString
  ACCESS  read-only
  STATUS  mandatory
  DESCRIPTION
          "Counts of bnat UDP connections on ingress"
  ::= {poolid 17}


econatBnatConnectionsIcmpIngress OBJECT-TYPE
  SYNTAX  DisplayString
  ACCESS  read-only
  STATUS  mandatory
  DESCRIPTION
          "Counts of bnat ICMP connections on ingress"
  ::= {poolid 18}


econatBnatConnectionsOtherIngress OBJECT-TYPE
  SYNTAX  DisplayString
  ACCESS  read-only
  STATUS  mandatory
  DESCRIPTION
          "Counts of bnat connections on ingress where protocol is:
		  RDP/IPv4/IPv6/ESP/AH/L2TP"
  ::= {poolid 19}


econatBnatConnectionsTcpEgress OBJECT-TYPE
  SYNTAX  DisplayString
  ACCESS  read-only
  STATUS  mandatory
  DESCRIPTION
          "Counts of bnat TCP connections on egress"
  ::= {poolid 20}


econatBnatConnectionsUdpEgress OBJECT-TYPE
  SYNTAX  DisplayString
  ACCESS  read-only
  STATUS  mandatory
  DESCRIPTION
          "Counts of bnat UDP connections on egress"
  ::= {poolid 21}


econatBnatConnectionsIcmpEgress OBJECT-TYPE
  SYNTAX  DisplayString
  ACCESS  read-only
  STATUS  mandatory
  DESCRIPTION
          "Counts of bnat ICMP connections on egress"
  ::= {poolid 22}


econatBnatConnectionsOtherEgress OBJECT-TYPE
  SYNTAX  DisplayString
  ACCESS  read-only
  STATUS  mandatory
  DESCRIPTION
          "Counts of bnat connections on egress where protocol is:
		  RDP/IPv4/IPv6/ESP/AH/L2TP"
  ::= {poolid 23}


econatBnatConnectionsTcp OBJECT-TYPE
  SYNTAX  DisplayString
  ACCESS  read-only
  STATUS  mandatory
  DESCRIPTION
          "Counts of bnat TCP connections (inress+egress)"
  ::= {poolid 24}


econatBnatConnectionsUdp OBJECT-TYPE
  SYNTAX  DisplayString
  ACCESS  read-only
  STATUS  mandatory
  DESCRIPTION
          "Counts of bnat UDP connections (inress+egress)"
  ::= {poolid 25}


econatBnatConnectionsIcmp OBJECT-TYPE
  SYNTAX  DisplayString
  ACCESS  read-only
  STATUS  mandatory
  DESCRIPTION
          "Counts of bnat ICMP connections (inress+egress)"
  ::= {poolid 26}


econatBnatConnectionsOther OBJECT-TYPE
  SYNTAX  DisplayString
  ACCESS  read-only
  STATUS  mandatory
  DESCRIPTION
          "Counts of bnat connections (ingress+egress) where protocol is:
		  RDP/IPv4/IPv6/ESP/AH/L2TP"
  ::= {poolid 27}


econatTcpSessions OBJECT-TYPE
  SYNTAX  DisplayString
  ACCESS  read-only
  STATUS  mandatory
  DESCRIPTION
          "Counts of TCP sessions"
  ::= {counters 62}


econatAproxSessionLimit OBJECT-TYPE
  SYNTAX  DisplayString
  ACCESS  read-only
  STATUS  mandatory
  DESCRIPTION
          "Approximate session limit"
  ::= {counters 63}


econatUdpSessions OBJECT-TYPE
  SYNTAX  DisplayString
  ACCESS  read-only
  STATUS  mandatory
  DESCRIPTION
          "Counts of UDP sessions"
  ::= {counters 64}


econatAproxSessionLimit2 OBJECT-TYPE
  SYNTAX  DisplayString
  ACCESS  read-only
  STATUS  mandatory
  DESCRIPTION
          "Approximate session limit"
  ::= {counters 65}


econatIcmpSessions OBJECT-TYPE
  SYNTAX  DisplayString
  ACCESS  read-only
  STATUS  mandatory
  DESCRIPTION
          "Counts of ICMP sessions"
  ::= {counters 66}


econatAproxSessionLimit3 OBJECT-TYPE
  SYNTAX  DisplayString
  ACCESS  read-only
  STATUS  mandatory
  DESCRIPTION
          "Approximate session limit"
  ::= {counters 67}


econatDpCpuBurst OBJECT-TYPE
  SYNTAX  DisplayString
  ACCESS  read-only
  STATUS  mandatory
  DESCRIPTION
          "CPU load"
  ::= {counters 105}


econatDpTotalMemory OBJECT-TYPE
  SYNTAX  DisplayString
  ACCESS  read-only
  STATUS  mandatory
  DESCRIPTION
          "Total amount of memory in econat software"
  ::= {counters 106}


econatDpFreeMemory OBJECT-TYPE
  SYNTAX  DisplayString
  ACCESS  read-only
  STATUS  mandatory
  DESCRIPTION
          "Free amount of memory in econat software"
  ::= {counters 107}


econatCpTotalMemory OBJECT-TYPE
  SYNTAX  DisplayString
  ACCESS  read-only
  STATUS  mandatory
  DESCRIPTION
          "Total amount of memory in econat platform"
  ::= {counters 108}


econatCpFreeMemory OBJECT-TYPE
  SYNTAX  DisplayString
  ACCESS  read-only
  STATUS  mandatory
  DESCRIPTION
          "Free amount of memory in econat platform"
  ::= {counters 109}


econatDpCpuSocket0 OBJECT-TYPE
  SYNTAX  DisplayString
  ACCESS  read-only
  STATUS  mandatory
  DESCRIPTION
          "CPU0 load"
  ::= {counters 110}


econatDpCpuSocket1 OBJECT-TYPE
  SYNTAX  DisplayString
  ACCESS  read-only
  STATUS  mandatory
  DESCRIPTION
          "CPU1 load"
  ::= {counters 111}


econatAvgEgressRxQueueSocket0 OBJECT-TYPE
  SYNTAX  DisplayString
  ACCESS  read-only
  STATUS  mandatory
  DESCRIPTION
          "Average length of egress rx queue on socket 0"
  ::= {counters 112}


econatAvgIngressRxQueueSocket0 OBJECT-TYPE
  SYNTAX  DisplayString
  ACCESS  read-only
  STATUS  mandatory
  DESCRIPTION
          "Average length of ingress rx queue on socket 0"
  ::= {counters 113}


econatAvgEgressRxQueueSocket1 OBJECT-TYPE
  SYNTAX  DisplayString
  ACCESS  read-only
  STATUS  mandatory
  DESCRIPTION
          "Average length of egress rx queue on socket 1"
  ::= {counters 114}


econatAvgIngressRxQueueSocket1 OBJECT-TYPE
  SYNTAX  DisplayString
  ACCESS  read-only
  STATUS  mandatory
  DESCRIPTION
          "Average length of ingress rx queue on socket 1"
  ::= {counters 115}


econatAvgEgressRxQueueSocketBoth OBJECT-TYPE
  SYNTAX  DisplayString
  ACCESS  read-only
  STATUS  mandatory
  DESCRIPTION
          "Average length of egress rx queue on both sockets"
  ::= {counters 116}


econatAvgIngressRxQueueSocketBoth OBJECT-TYPE
  SYNTAX  DisplayString
  ACCESS  read-only
  STATUS  mandatory
  DESCRIPTION
          "Average length of ingress rx queue on both sockets"
  ::= {counters 117}


econatFreeLoggingMbufs OBJECT-TYPE
  SYNTAX  DisplayString
  ACCESS  read-only
  STATUS  mandatory
  DESCRIPTION
          "Counts of free logging membufs"
  ::= {counters 120}


econatCntReconfigs OBJECT-TYPE
  SYNTAX  DisplayString
  ACCESS  read-only
  STATUS  mandatory
  DESCRIPTION
          "Counts of successful tries of reconfigure econat"
  ::= {counters 121}


econatDroppedClonedMessages OBJECT-TYPE
  SYNTAX  DisplayString
  ACCESS  read-only
  STATUS  mandatory
  DESCRIPTION
          "Counts of failed tries of copying logging packet if counts of logging server >1. Usual due to logging membuf is overflow"
  ::= {counters 125}


econatDroppedLoggerMbufs OBJECT-TYPE
  SYNTAX  DisplayString
  ACCESS  read-only
  STATUS  mandatory
  DESCRIPTION
          "Counts of failed tries of preparing logging packet due to logging membuf is overflow"
  ::= {counters 126}


econatRolledQueues OBJECT-TYPE
  SYNTAX  DisplayString
  ACCESS  read-only
  STATUS  mandatory
  DESCRIPTION
          "Counts of rolling queues"
  ::= {counters 127}


econatAlgSessionAlloc  OBJECT-TYPE
  SYNTAX  DisplayString
  ACCESS  read-only
  STATUS  mandatory
  DESCRIPTION
          "Counts of allocating alg sessions"
  ::= {counters 130}


econatAlgSessionFree  OBJECT-TYPE
  SYNTAX  DisplayString
  ACCESS  read-only
  STATUS  mandatory
  DESCRIPTION
          "Counts of freeing alg sessions"
  ::= {counters 131}


econatAlgSessionAllocError  OBJECT-TYPE
  SYNTAX  DisplayString
  ACCESS  read-only
  STATUS  mandatory
  DESCRIPTION
          "Counts of failed tries of allocating alg session"
  ::= {counters 132}


econatAlgSessionFreeError  OBJECT-TYPE
  SYNTAX  DisplayString
  ACCESS  read-only
  STATUS  mandatory
  DESCRIPTION
          "Counts of failed tries of freeing alg sessions"
  ::= {counters 133}


econatAlgTranslationAlloc  OBJECT-TYPE
  SYNTAX  DisplayString
  ACCESS  read-only
  STATUS  mandatory
  DESCRIPTION
          "Counts of allocating translation for alg"
  ::= {counters 134}


econatAlgTranslationAllocError  OBJECT-TYPE
  SYNTAX  DisplayString
  ACCESS  read-only
  STATUS  mandatory
  DESCRIPTION
          "Counts of failed tries of allocating translation for alg"
  ::= {counters 135}

econatAlgTranslationFree  OBJECT-TYPE
  SYNTAX  DisplayString
  ACCESS  read-only
  STATUS  mandatory
  DESCRIPTION
          "Counts of freeing translation for alg"
  ::= {counters 136}


econatAlgTranslationFreeError  OBJECT-TYPE
  SYNTAX  DisplayString
  ACCESS  read-only
  STATUS  mandatory
  DESCRIPTION
          "Counts of failed tries of freeing translation for alg"
  ::= {counters 137}

econatTcpStateEstablished  OBJECT-TYPE
  SYNTAX  DisplayString
  ACCESS  read-only
  STATUS  mandatory
  DESCRIPTION
          "Counts of created TCP connections"
  ::= {counters 150}


econatTcpStateCloseTimeout  OBJECT-TYPE
  SYNTAX  DisplayString
  ACCESS  read-only
  STATUS  mandatory
  DESCRIPTION
          "Counts of TCP sessions that have been closed by timeout"
  ::= {counters 151}


econatUdpStateEstablished  OBJECT-TYPE
  SYNTAX  DisplayString
  ACCESS  read-only
  STATUS  mandatory
  DESCRIPTION
          "Counts of created UDP connections"
  ::= {counters 152}


econatUdpStateCloseTimeout  OBJECT-TYPE
  SYNTAX  DisplayString
  ACCESS  read-only
  STATUS  mandatory
  DESCRIPTION
          "Counts of UDP sessions that have been closed by timeout"
  ::= {counters 153}


econatIcmpStateEstablished  OBJECT-TYPE
  SYNTAX  DisplayString
  ACCESS  read-only
  STATUS  mandatory
  DESCRIPTION
          "Counts of created ICMP connections"
  ::= {counters 154}


econatIcmpStateCloseTimeout  OBJECT-TYPE
  SYNTAX  DisplayString
  ACCESS  read-only
  STATUS  mandatory
  DESCRIPTION
          "Counts of ICMP sessions that have been closed by timeout"
  ::= {counters 155}


econatGreStateEstablished  OBJECT-TYPE
  SYNTAX  DisplayString
  ACCESS  read-only
  STATUS  mandatory
  DESCRIPTION
          "Counts of created GRE connections"
  ::= {counters 156}


econatGreStateCloseTimeout  OBJECT-TYPE
  SYNTAX  DisplayString
  ACCESS  read-only
  STATUS  mandatory
  DESCRIPTION
          "Counts of GRE sessions that have been closed by timeout"
  ::= {counters 157}



econatOpaqueStateEstablished  OBJECT-TYPE
  SYNTAX  DisplayString
  ACCESS  read-only
  STATUS  mandatory
  DESCRIPTION
          "Counts of created Opaque connections"
  ::= {counters 158}


econatOpaqueStateCloseTimeout  OBJECT-TYPE
  SYNTAX  DisplayString
  ACCESS  read-only
  STATUS  mandatory
  DESCRIPTION
          "Counts of Opaque sessions that have been closed by timeout"
  ::= {counters 159}

econatSessTcpAlloc  OBJECT-TYPE
  SYNTAX  DisplayString
  ACCESS  read-only
  STATUS  mandatory
  DESCRIPTION
          "Counts of allocating TCP sessions"
  ::= {counters 160}


econatSessTcpFree  OBJECT-TYPE
  SYNTAX  DisplayString
  ACCESS  read-only
  STATUS  mandatory
  DESCRIPTION
          "Counts of freeing TCP sessions"
  ::= {counters 161}


econatSessUdpAlloc  OBJECT-TYPE
  SYNTAX  DisplayString
  ACCESS  read-only
  STATUS  mandatory
  DESCRIPTION
          "Counts of allocating UDP sessions"
  ::= {counters 162}


econatSessUdpFree  OBJECT-TYPE
  SYNTAX  DisplayString
  ACCESS  read-only
  STATUS  mandatory
  DESCRIPTION
          "Counts of freeing UDP sessions"
  ::= {counters 163}


econatSessIcmpAlloc  OBJECT-TYPE
  SYNTAX  DisplayString
  ACCESS  read-only
  STATUS  mandatory
  DESCRIPTION
          "Counts of allocating ICMP sessions"
  ::= {counters 164}


econatSessIcmpFree  OBJECT-TYPE
  SYNTAX  DisplayString
  ACCESS  read-only
  STATUS  mandatory
  DESCRIPTION
          "Counts of freeing ICMP sessions"
  ::= {counters 165}


econatSessionAllocPerSec  OBJECT-TYPE
  SYNTAX  DisplayString
  ACCESS  read-only
  STATUS  mandatory
  DESCRIPTION
          "Counts of allocating session per second"
  ::= {counters 170}


econatSessionFreePerSec  OBJECT-TYPE
  SYNTAX  DisplayString
  ACCESS  read-only
  STATUS  mandatory
  DESCRIPTION
          "Counts of freeing session per second"
  ::= {counters 171}


econatNaptGaddrAllocPerSec  OBJECT-TYPE
  SYNTAX  DisplayString
  ACCESS  read-only
  STATUS  mandatory
  DESCRIPTION
          "Counts of allocating napt global addresses per second"
  ::= {counters 172}


econatNaptGaddrFreePerSec  OBJECT-TYPE
  SYNTAX  DisplayString
  ACCESS  read-only
  STATUS  mandatory
  DESCRIPTION
          "Counts of freeing napt global addresses per second"
  ::= {counters 173}


econatSessionAllocNoPoolEgressPerSec  OBJECT-TYPE
  SYNTAX  DisplayString
  ACCESS  read-only
  STATUS  mandatory
  DESCRIPTION
          "Counts of moments when we didn't find pool for egress packet"
  ::= {counters 174}


econatSessionAllocNoPoolIngressPerSec  OBJECT-TYPE
  SYNTAX  DisplayString
  ACCESS  read-only
  STATUS  mandatory
  DESCRIPTION
          "Counts of moments when we didn't find pool for ingress packet"
  ::= {counters 175}


econatSessTcpAllocPerSec  OBJECT-TYPE
  SYNTAX  DisplayString
  ACCESS  read-only
  STATUS  mandatory
  DESCRIPTION
          "Counts of allocating TCP session per second"
  ::= {counters 180}


econatTcpStateEstablishedPerSec  OBJECT-TYPE
  SYNTAX  DisplayString
  ACCESS  read-only
  STATUS  mandatory
  DESCRIPTION
          "Counts of creating TCP connections per second"
  ::= {counters 181}


econatSessUdpAllocPerSec  OBJECT-TYPE
  SYNTAX  DisplayString
  ACCESS  read-only
  STATUS  mandatory
  DESCRIPTION
          "Counts of allocating UDP session per second"
  ::= {counters 182}


econatUdpStateEstablishedPerSec  OBJECT-TYPE
  SYNTAX  DisplayString
  ACCESS  read-only
  STATUS  mandatory
  DESCRIPTION
          "Counts of creating UDP connections per second"
  ::= {counters 183}


econatTranslatedTcpPerSec  OBJECT-TYPE
  SYNTAX  DisplayString
  ACCESS  read-only
  STATUS  mandatory
  DESCRIPTION
          "Counts of translating TCP packets per second"
  ::= {counters 184}


econatTranslatedUdpPerSec  OBJECT-TYPE
  SYNTAX  DisplayString
  ACCESS  read-only
  STATUS  mandatory
  DESCRIPTION
          "Counts of translating UDP packets per second"
  ::= {counters 185}


econatInJumbo OBJECT-TYPE
  SYNTAX  DisplayString
  ACCESS  read-only
  STATUS  mandatory
  DESCRIPTION
          "Counts of in jumbo frames"
  ::= {counters 200}


econatOutJumbo OBJECT-TYPE
  SYNTAX  DisplayString
  ACCESS  read-only
  STATUS  mandatory
  DESCRIPTION
          "Counts of out jumbo frames"
  ::= {counters 201}


econatSessionEarlyFreeIngress OBJECT-TYPE
  SYNTAX  DisplayString
  ACCESS  read-only
  STATUS  mandatory
  DESCRIPTION
          "Free session on ingress due to TCP RST or FIN packet"
  ::= {counters 300}


econatSessionEarlyFreeEgress OBJECT-TYPE
  SYNTAX  DisplayString
  ACCESS  read-only
  STATUS  mandatory
  DESCRIPTION
          "Free session on egress due to TCP RST or FIN packet"
  ::= {counters 301}


econatSessionAllocNaptOtherErrorEgress OBJECT-TYPE
  SYNTAX  DisplayString
  ACCESS  read-only
  STATUS  mandatory
  DESCRIPTION
          "Counts of failed tries of allocating Other napt port or block on egress"
  ::= {counters 320}


econatSessionAllocNaptTcpErrorEgress OBJECT-TYPE
  SYNTAX  DisplayString
  ACCESS  read-only
  STATUS  mandatory
  DESCRIPTION
          "Counts of failed tries of allocating TCP napt port or block on egress"
  ::= {counters 321}


econatSessionAllocNaptUdpErrorEgress OBJECT-TYPE
  SYNTAX  DisplayString
  ACCESS  read-only
  STATUS  mandatory
  DESCRIPTION
          "Counts of failed tries of allocating UDP napt port or block on egress"
  ::= {counters 322}


econatSessionAllocNaptIcmpErrorEgress OBJECT-TYPE
  SYNTAX  DisplayString
  ACCESS  read-only
  STATUS  mandatory
  DESCRIPTION
          "Counts of failed tries of allocating ICMP napt port or block on egress"
  ::= {counters 323}


econatSessionAllocNaptPptpgreErrorEgress OBJECT-TYPE
  SYNTAX  DisplayString
  ACCESS  read-only
  STATUS  mandatory
  DESCRIPTION
          "Counts of failed tries of allocating PPTP napt port or block on egress"
  ::= {counters 324}


econatSessionAllocNaptL4otherErrorEgress OBJECT-TYPE
  SYNTAX  DisplayString
  ACCESS  read-only
  STATUS  mandatory
  DESCRIPTION
          "Counts of failed tries of allocating Opaque napt port or block on egress"
  ::= {counters 325}


econatDroppedPacketCauseL2mtu OBJECT-TYPE
  SYNTAX  DisplayString
  ACCESS  read-only
  STATUS  mandatory
  DESCRIPTION
          "Counts of dropped rx packets due to l2 mtu"
  ::= {counters 326}


econatSessionAllocBnatOtherErrorEgress OBJECT-TYPE
  SYNTAX  DisplayString
  ACCESS  read-only
  STATUS  mandatory
  DESCRIPTION
          "Counts of failed tries of allocating Other bnat session on egress"
  ::= {counters 340}


econatSessionAllocBnatTcpErrorEgress OBJECT-TYPE
  SYNTAX  DisplayString
  ACCESS  read-only
  STATUS  mandatory
  DESCRIPTION
          "Counts of failed tries of allocating TCP bnat session on egress"
  ::= {counters 341}


econatSessionAllocBnatUdpErrorEgress OBJECT-TYPE
  SYNTAX  DisplayString
  ACCESS  read-only
  STATUS  mandatory
  DESCRIPTION
          "Counts of failed tries of allocating UDP bnat session on egress"
  ::= {counters 342}


econatSessionAllocBnatIcmpErrorEgress OBJECT-TYPE
  SYNTAX  DisplayString
  ACCESS  read-only
  STATUS  mandatory
  DESCRIPTION
          "Counts of failed tries of allocating ICMP bnat session on egress"
  ::= {counters 343}


econatSessionAllocBnatPptpgreErrorEgress OBJECT-TYPE
  SYNTAX  DisplayString
  ACCESS  read-only
  STATUS  mandatory
  DESCRIPTION
          "Counts of failed tries of allocating PPTP bnat session on egress"
  ::= {counters 344}


econatSessionAllocBnatL4otherErrorEgress OBJECT-TYPE
  SYNTAX  DisplayString
  ACCESS  read-only
  STATUS  mandatory
  DESCRIPTION
          "Counts of failed tries of allocating Opaque bnat session on egress"
  ::= {counters 345}


econatNaptGaddrAllocError OBJECT-TYPE
  SYNTAX  DisplayString
  ACCESS  read-only
  STATUS  mandatory
  DESCRIPTION
          "Counts of failed tries of allocating global address on napt"
  ::= {counters 360}


econatBnatGaddrAllocError OBJECT-TYPE
  SYNTAX  DisplayString
  ACCESS  read-only
  STATUS  mandatory
  DESCRIPTION
          "Counts of failed tries of allocating global address on bnat"
  ::= {counters 361}


econatBnatPortAllocErrLimitReached OBJECT-TYPE
  SYNTAX  DisplayString
  ACCESS  read-only
  STATUS  mandatory
  DESCRIPTION
          "Counts of failed tries of allocating port on bnat due to per user limit exceeded"
  ::= {counters 370}


econatBnatPortAllocErrIngressDisabled OBJECT-TYPE
  SYNTAX  DisplayString
  ACCESS  read-only
  STATUS  mandatory
  DESCRIPTION
          "Counts of failed tries of allocating bnat port on ingress due to allow_external_connect is disabled"
  ::= {counters 371}


econatBnatPortAllocErrIngressInactiveClient OBJECT-TYPE
  SYNTAX  DisplayString
  ACCESS  read-only
  STATUS  mandatory
  DESCRIPTION
          "Counts of failed tries of allocating bnat port on ingress cause no egress translations from client"
  ::= {counters 372}


econatBnatPortAllocErrIngressNoClient OBJECT-TYPE
  SYNTAX  DisplayString
  ACCESS  read-only
  STATUS  mandatory
  DESCRIPTION
          "Counts of failed tries of allocating bnat port on ingress cause no association current white ip <-> grey ip"
  ::= {counters 373}


econatBnatPortAllocErrMappingCreation OBJECT-TYPE
  SYNTAX  DisplayString
  ACCESS  read-only
  STATUS  mandatory
  DESCRIPTION
          "Counts of failed tries of bnat mapping creation"
  ::= {counters 374}


econatBnatPortFreeErrNoMapping OBJECT-TYPE
  SYNTAX  DisplayString
  ACCESS  read-only
  STATUS  mandatory
  DESCRIPTION
          "Counts of failed tries of delete bnat mapping, cause it's not exists"
  ::= {counters 375}


econatBnatPortFreeErrAlreadyZero OBJECT-TYPE
  SYNTAX  DisplayString
  ACCESS  read-only
  STATUS  mandatory
  DESCRIPTION
          "Counts of failed tries of freeing bnat port, couse it's already is zero"
  ::= {counters 376}


econatAllocatedLoggerMbufs OBJECT-TYPE
  SYNTAX  DisplayString
  ACCESS  read-only
  STATUS  mandatory
  DESCRIPTION
          "Counts of allocating mbuf for logging"
  ::= {counters 380}


econatAllocatedArpMbufs OBJECT-TYPE
  SYNTAX  DisplayString
  ACCESS  read-only
  STATUS  mandatory
  DESCRIPTION
          "Counts of allocating mbuf for ARP"
  ::= {counters 381}


econatAllocatedLldpMbufs OBJECT-TYPE
  SYNTAX  DisplayString
  ACCESS  read-only
  STATUS  mandatory
  DESCRIPTION
          "Counts of allocating mbuf for LLDP"
  ::= {counters 382}


econatSentLoggerMbufs OBJECT-TYPE
  SYNTAX  DisplayString
  ACCESS  read-only
  STATUS  mandatory
  DESCRIPTION
          "Counts of sent logger mbufs"
  ::= {counters 385}


econatSysloggerNoMbufs OBJECT-TYPE
  SYNTAX  DisplayString
  ACCESS  read-only
  STATUS  mandatory
  DESCRIPTION
          "Syslogger mbufs has exceeded"
  ::= {counters 387}


econatUrllogMsgsEnqueued OBJECT-TYPE
  SYNTAX  DisplayString
  ACCESS  read-only
  STATUS  mandatory
  DESCRIPTION
          "Counts of isuccessful enqueue url logging message"
  ::= {counters 390}


econatUrllogMsgsNotEnqueued OBJECT-TYPE
  SYNTAX  DisplayString
  ACCESS  read-only
  STATUS  mandatory
  DESCRIPTION
          "Counts of fail enqueue url logging message"
  ::= {counters 391}


econatRaceNoEgressPayload OBJECT-TYPE
  SYNTAX  DisplayString
  ACCESS  read-only
  STATUS  mandatory
  DESCRIPTION
          "Race condition in egress translations"
  ::= {counters 395}


econatRaceNoIngressPayload OBJECT-TYPE
  SYNTAX  DisplayString
  ACCESS  read-only
  STATUS  mandatory
  DESCRIPTION
          "Race condition in ingress translations"
  ::= {counters 396}


econatAlgEnqueued OBJECT-TYPE
  SYNTAX  DisplayString
  ACCESS  read-only
  STATUS  mandatory
  DESCRIPTION
          "Counts of enqueued alg packets"
  ::= {counters 397}


econatAlgRingOverflows OBJECT-TYPE
  SYNTAX  DisplayString
  ACCESS  read-only
  STATUS  mandatory
  DESCRIPTION
          "Counts of failed tries of putting alg packet to queue due to full ring"
  ::= {counters 398}


econatAlgHashOverflows OBJECT-TYPE
  SYNTAX  DisplayString
  ACCESS  read-only
  STATUS  mandatory
  DESCRIPTION
          "Counts of failed tries of alg packet processing due to alg memory is exceeded"
  ::= {counters 399}


econatAlgFtpPatchDng OBJECT-TYPE
  SYNTAX  DisplayString
  ACCESS  read-only
  STATUS  mandatory
  DESCRIPTION
          "Counts of failed tries of ftp alg packet patching due to memory problem"
  ::= {counters 400}


econatAlgSipPatchDng OBJECT-TYPE
  SYNTAX  DisplayString
  ACCESS  read-only
  STATUS  mandatory
  DESCRIPTION
          "Counts of failed tries of sip alg packet patching due to memory problem"
  ::= {counters 401}


econatAlgRtspPatchDng OBJECT-TYPE
  SYNTAX  DisplayString
  ACCESS  read-only
  STATUS  mandatory
  DESCRIPTION
          "Counts of failed tries of rtsp alg packet patching due to memory problem"
  ::= {counters 402}


econatRteHashOverflow OBJECT-TYPE
  SYNTAX  DisplayString
  ACCESS  read-only
  STATUS  mandatory
  DESCRIPTION
          "Counts of failed tries of allocating memory from one of the hashes due to it's full"
  ::= {counters 403}


econatPsuStateChanges OBJECT-TYPE
  SYNTAX  DisplayString
  ACCESS  read-only
  STATUS  mandatory
  DESCRIPTION
          "Counts of changing PSU state"
  ::= {counters 404}


econatHairpinProcess OBJECT-TYPE
  SYNTAX  DisplayString
  ACCESS  read-only
  STATUS  mandatory
  DESCRIPTION
          "Counts of tries of hairpin processing"
  ::= {counters 405}


econatHairpinRefused OBJECT-TYPE
  SYNTAX  DisplayString
  ACCESS  read-only
  STATUS  mandatory
  DESCRIPTION
          "Counts of refusing hairpin"
  ::= {counters 406}


econatPpFailedSanitycheck OBJECT-TYPE
  SYNTAX  DisplayString
  ACCESS  read-only
  STATUS  mandatory
  DESCRIPTION
          "Counts of failed packet validation"
  ::= {counters 407}


econatPpCantccHairpin OBJECT-TYPE
  SYNTAX  DisplayString
  ACCESS  read-only
  STATUS  mandatory
  DESCRIPTION
          "Counts of failed tries of creating hairpin connection"
  ::= {counters 408}


econatPpCantccReconfig OBJECT-TYPE
  SYNTAX  DisplayString
  ACCESS  read-only
  STATUS  mandatory
  DESCRIPTION
          "Counts of failed tries of creating translation due to reconfiguration"
  ::= {counters 409}


econatPpTranslationBug OBJECT-TYPE
  SYNTAX  DisplayString
  ACCESS  read-only
  STATUS  mandatory
  DESCRIPTION
          "Counts of creating translation bug. Call support"
  ::= {counters 410}


econatPpHairpinRefused OBJECT-TYPE
  SYNTAX  DisplayString
  ACCESS  read-only
  STATUS  mandatory
  DESCRIPTION
          "Refused hairpin (debug counter)"
  ::= {counters 411}


econatPpHairpinRefusedIngress OBJECT-TYPE
  SYNTAX  DisplayString
  ACCESS  read-only
  STATUS  mandatory
  DESCRIPTION
          "Refuse to do hairpin, no flag (debug counter)"
  ::= {counters 412}


econatPpInvalidFlowDrop OBJECT-TYPE
  SYNTAX  DisplayString
  ACCESS  read-only
  STATUS  mandatory
  DESCRIPTION
          "Counts of dropping packet due to invalid flow"
  ::= {counters 413}


econatNaptPortAlloc OBJECT-TYPE
  SYNTAX  DisplayString
  ACCESS  read-only
  STATUS  mandatory
  DESCRIPTION
          "Counts of allocating of napt port"
  ::= {counters 430}


econatNaptPortFree OBJECT-TYPE
  SYNTAX  DisplayString
  ACCESS  read-only
  STATUS  mandatory
  DESCRIPTION
          "Counts of freeing of napt port"
  ::= {counters 431}


econatBnatGaddrAlloc OBJECT-TYPE
  SYNTAX  DisplayString
  ACCESS  read-only
  STATUS  mandatory
  DESCRIPTION
          "Counts of allocating bnat global address"
  ::= {counters 432}


econatBnatGaddrFree OBJECT-TYPE
  SYNTAX  DisplayString
  ACCESS  read-only
  STATUS  mandatory
  DESCRIPTION
          "Counts of freeing bnat global address"
  ::= {counters 433}


econatBnatPortAlloc OBJECT-TYPE
  SYNTAX  DisplayString
  ACCESS  read-only
  STATUS  mandatory
  DESCRIPTION
          "Counts of allocating bnat port"
  ::= {counters 434}


econatBnatPortFree OBJECT-TYPE
  SYNTAX  DisplayString
  ACCESS  read-only
  STATUS  mandatory
  DESCRIPTION
          "Counts of freeing bnat port"
  ::= {counters 435}


econatBrasDroppedAccess OBJECT-TYPE
  SYNTAX  DisplayString
  ACCESS  read-only
  STATUS  mandatory
  DESCRIPTION
          "Counts of packets dropped by BRAS"
  ::= {counters 500}


econatBrasDroppedPolicer OBJECT-TYPE
  SYNTAX  DisplayString
  ACCESS  read-only
  STATUS  mandatory
  DESCRIPTION
          "Counts of packets dropped by BRAS policer"
  ::= {counters 501}


econatBrasRedirected OBJECT-TYPE
  SYNTAX  DisplayString
  ACCESS  read-only
  STATUS  mandatory
  DESCRIPTION
          "Counts of packets redirected by BRAS"
  ::= {counters 502}


econatDpiBannedEgressTcp OBJECT-TYPE
  SYNTAX  DisplayString
  ACCESS  read-only
  STATUS  mandatory
  DESCRIPTION
          "Counts of tcp sessions banned by DPI on egress"
  ::= {counters 600}


econatDpiBannedIngressTcp OBJECT-TYPE
  SYNTAX  DisplayString
  ACCESS  read-only
  STATUS  mandatory
  DESCRIPTION
          "Counts of tcp sessions banned by DPI on ingress"
  ::= {counters 601}


econatDpiBannedEgressUdp OBJECT-TYPE
  SYNTAX  DisplayString
  ACCESS  read-only
  STATUS  mandatory
  DESCRIPTION
          "Counts of UDP sessions (means econat sessions) banned by DPI on egress (bittorent)"
  ::= {counters 602}


econatDpiBannedIngressUdp OBJECT-TYPE
  SYNTAX  DisplayString
  ACCESS  read-only
  STATUS  mandatory
  DESCRIPTION
          "Counts of UDP sessions (means econat sessions) banned by DPI on ingress (bittorent)"
  ::= {counters 603}


econatDpiRKNLastLoad OBJECT-TYPE
  SYNTAX  DisplayString
  ACCESS  read-only
  STATUS  mandatory
  DESCRIPTION
          "Timestamp of last successful download of Roskomnadzor database"
  ::= {counters 605}


econatDpiRKNLastParse OBJECT-TYPE
  SYNTAX  DisplayString
  ACCESS  read-only
  STATUS  mandatory
  DESCRIPTION
          "Timestamp of last successful parsing of Roskomnadzor database"
  ::= {counters 606}


econatDpiNoHostBufs OBJECT-TYPE
  SYNTAX  DisplayString
  ACCESS  read-only
  STATUS  mandatory
  DESCRIPTION
          "Counts of failed allocating memory for host_mbuf due its exceeded"
  ::= {counters 620}


econatDpiNoPathBufs OBJECT-TYPE
  SYNTAX  DisplayString
  ACCESS  read-only
  STATUS  mandatory
  DESCRIPTION
          "Counts of failed allocating memory for path_mbuf due its exceeded"
  ::= {counters 621}


econatDpiNoStateBufs OBJECT-TYPE
  SYNTAX  DisplayString
  ACCESS  read-only
  STATUS  mandatory
  DESCRIPTION
          "Counts of failed allocating memory for state_mbuf due its exceeded"
  ::= {counters 622}


econatTableHash8Ext1 OBJECT-TYPE
  SYNTAX  DisplayString
  ACCESS  read-only
  STATUS  mandatory
  DESCRIPTION
          "Debug hash counter"
  ::= {counters 700}


econatTableHash8Ext2 OBJECT-TYPE
  SYNTAX  DisplayString
  ACCESS  read-only
  STATUS  mandatory
  DESCRIPTION
          "Debug hash counter"
  ::= {counters 701}


econatTableHash8Ext4 OBJECT-TYPE
  SYNTAX  DisplayString
  ACCESS  read-only
  STATUS  mandatory
  DESCRIPTION
          "Debug hash counter"
  ::= {counters 702}


econatTableHash8Ext8 OBJECT-TYPE
  SYNTAX  DisplayString
  ACCESS  read-only
  STATUS  mandatory
  DESCRIPTION
          "Debug hash counter"
  ::= {counters 703}


econatTableHash8Ext16 OBJECT-TYPE
  SYNTAX  DisplayString
  ACCESS  read-only
  STATUS  mandatory
  DESCRIPTION
          "Debug hash counter"
  ::= {counters 704}


econatTableHash8Overflow OBJECT-TYPE
  SYNTAX  DisplayString
  ACCESS  read-only
  STATUS  mandatory
  DESCRIPTION
          "Debug hash counter"
  ::= {counters 705}


econatTableHash12Ext1 OBJECT-TYPE
  SYNTAX  DisplayString
  ACCESS  read-only
  STATUS  mandatory
  DESCRIPTION
          "Debug hash counter"
  ::= {counters 706}


econatTableHash12Ext2 OBJECT-TYPE
  SYNTAX  DisplayString
  ACCESS  read-only
  STATUS  mandatory
  DESCRIPTION
          "Debug hash counter"
  ::= {counters 707}


econatTableHash12Ext4 OBJECT-TYPE
  SYNTAX  DisplayString
  ACCESS  read-only
  STATUS  mandatory
  DESCRIPTION
          "Debug hash counter"
  ::= {counters 708}


econatTableHash12Ext8 OBJECT-TYPE
  SYNTAX  DisplayString
  ACCESS  read-only
  STATUS  mandatory
  DESCRIPTION
          "Debug hash counter"
  ::= {counters 709}


econatTableHash12Ext16 OBJECT-TYPE
  SYNTAX  DisplayString
  ACCESS  read-only
  STATUS  mandatory
  DESCRIPTION
          "Debug hash counter"
  ::= {counters 710}


econatTableHash12Overflow OBJECT-TYPE
  SYNTAX  DisplayString
  ACCESS  read-only
  STATUS  mandatory
  DESCRIPTION
          "Debug hash counter"
  ::= {counters 711}


econatTransPerUserLimitExceeded OBJECT-TYPE
  SYNTAX  DisplayString
  ACCESS  read-only
  STATUS  mandatory
  DESCRIPTION
          "Per user connection limit was exceeded"
  ::= {counters 712}

END
