PACKETFRONT-SMI DEFINITIONS ::= BEGIN
--
-- This is the PacketFront Management Information Base SMI definitions
-- to be used together with PacketFront products.
--
-- Copyright (c) 2007,2008,2009 PacketFront Systems AB

IMPORTS
  MODULE-IDENTITY,
  OBJECT-IDENTITY,
  enterprises
    FROM SNMPv2-SMI;

--
-- PacketFront Enterprise SMI
--
packetfront MODULE-IDENTITY
    LAST-UPDATED "200903231039Z"
    ORGANIZATION "PacketFront Systems AB"
    CONTACT-INFO
        "PacketFront Systems AB
         Customer Service

         Mail : Isafjordsgatan 35
                SE-164 28 Kista
                Sweden

         Tel  : +46 8 5090 1500

         E-mail: snmp@packetfront.com
         Web   : http://www.packetfront.com"
    DESCRIPTION
        "The PacketFront management information base SMI definitions"

    REVISION "200903231039Z"
    DESCRIPTION
        "Updated telephone number in contact-info"
    REVISION "200801171405Z"
    DESCRIPTION
        "Correct warnings in imports"
    REVISION "200705111228Z"
    DESCRIPTION
        "Created from PACKETFRONT-MIB.mib"

    ::= { enterprises 9303 }  -- assigned by IANA

--
-- Product information
--
pfProduct	OBJECT-IDENTITY
		STATUS current
		DESCRIPTION
		"The product group from which sysObjectID values are set."
		::= { packetfront 1 }

--
-- Configuration
--
pfConfig	OBJECT-IDENTITY
		STATUS current
		DESCRIPTION
		"The configuration subtree"
		::= { packetfront 2 }

ipdConfig       OBJECT-IDENTITY
                STATUS current
                DESCRIPTION
                "The configuration subtree"
                ::= { pfConfig 1 }

--
-- Experimental
--
pfExperiment	OBJECT-IDENTITY
		STATUS current
		DESCRIPTION
		"The root object for experimental objects.
		Experimental objects are used during
		development before a permanent assignment
		to the packetfront mib has been determined.

		Objects in this tree will come and go. No guarantees for
		their existance or accuracy is ever provided."
        	::= { packetfront 3 }


--
-- Management
--
pfMgmt		OBJECT-IDENTITY
		STATUS current
                DESCRIPTION
		"The root object for all PacketFront management objects"
                ::= { packetfront 4 }


pfModules	OBJECT-IDENTITY
		STATUS current
		DESCRIPTION
		"pfModules provides a root object identifier from which the
		MODULE-IDENTITY values may be assigned"
		::= { packetfront 5 }


END
