PACKETFRONT-PRODUCTS-MIB DEFINITIONS ::= BEGIN
--
-- PacketFront Product Object identifier Assignments
--
-- Copyright (c) 2002 PacketFront Sweden AB
-- Copyright (c) 2007-2010 PacketFront Systems AB
-- All rights reserved
--

IMPORTS
        MODULE-IDENTITY,
        OBJECT-IDENTITY
        FROM SNMPv2-SMI

        pfProduct,
        pfModules
        FROM PACKETFRONT-SMI;

--
-- PacketFront products
--
pfProductsMIB MODULE-IDENTITY
    LAST-UPDATED "201005171410Z"
    ORGANIZATION "PacketFront Systems AB"
    CONTACT-INFO
        "PacketFront Systems AB
         Customer Service

         Mail : Isafjordsgatan 35
                SE-164 28 Kista
                Sweden

         Tel  : +46 8 5090 1500

         E-mail: snmp@packetfront.com
         Web   : http://www.packetfront.com"
    DESCRIPTION
        "The PacketFront management information base describing product
         families and the products within those families"

    REVISION "201005171410Z"
    DESCRIPTION
	"Added mediastar (MS) product group, updated DRG group"
    REVISION "200904141229Z"
    DESCRIPTION
	"Added service engine (SE) product group"
    REVISION "200903231053Z"
    DESCRIPTION
	"Updated telephone information in contact-info"
    REVISION "200705141238Z"
    DESCRIPTION
	"Generation from PACKETFRONT-MIB"
    REVISION "200601251330Z"
    DESCRIPTION
        "Updated to reflect PacketFronts new corporate address"
    REVISION "200410201434Z"
    DESCRIPTION
        "Added the ASR10K platorm"
    REVISION "200311040001Z"
    DESCRIPTION
        "Added the IPD1116C platform"

    ::= { pfModules 2 }

--
-- Product groups
--
asr	OBJECT-IDENTITY
	STATUS current
	DESCRIPTION
		"The Access Switching Router (ASR) product group"
	::= { pfProduct 1 }

ipd	OBJECT-IDENTITY
	STATUS current
	DESCRIPTION
		"The IP DSLAM (IPD) product group"
	::= { pfProduct 2 }

drg	OBJECT-IDENTITY
	STATUS current
	DESCRIPTION
		"The Digital Residential Gateway (DRG) product group"
	::= { pfProduct 3 }

se	OBJECT-IDENTITY
	STATUS current
	DESCRIPTION
		"The Service Engine (SE) product group"
	::= { pfProduct 4 }

ms	OBJECT-IDENTITY
	STATUS current
	DESCRIPTION
		"The MetroStar (MS) product group"
	::= { pfProduct 5 }


-- ASR4000 products

asr4108C	OBJECT IDENTIFIER ::= { asr  1 }
asr4116C	OBJECT IDENTIFIER ::= { asr  2 }
asr4124C	OBJECT IDENTIFIER ::= { asr  3 }
asr4208FM	OBJECT IDENTIFIER ::= { asr  4 }
asr4216FM	OBJECT IDENTIFIER ::= { asr  5 }
asr4224FM	OBJECT IDENTIFIER ::= { asr  6 }
asr4308FV	OBJECT IDENTIFIER ::= { asr  7 }
asr4316FV	OBJECT IDENTIFIER ::= { asr  8 }
asr4324FV	OBJECT IDENTIFIER ::= { asr  9 }
asr4408SFV	OBJECT IDENTIFIER ::= { asr 10 }
asr4416SFV	OBJECT IDENTIFIER ::= { asr 11 }
asr4424SFV	OBJECT IDENTIFIER ::= { asr 12 }
asr4508SFM	OBJECT IDENTIFIER ::= { asr 13 }
asr4516SFM	OBJECT IDENTIFIER ::= { asr 14 }
asr4524SFM	OBJECT IDENTIFIER ::= { asr 15 }
asr4608SFS	OBJECT IDENTIFIER ::= { asr 16 }
asr4616SFS	OBJECT IDENTIFIER ::= { asr 17 }
asr4624SFS	OBJECT IDENTIFIER ::= { asr 18 }
asr3108VDSL	OBJECT IDENTIFIER ::= { asr 19 }
asr3116VDSL	OBJECT IDENTIFIER ::= { asr 20 }
asr3124VDSL	OBJECT IDENTIFIER ::= { asr 21 }
asr3208VDSL	OBJECT IDENTIFIER ::= { asr 22 }
asr3216VDSL	OBJECT IDENTIFIER ::= { asr 23 }
asr3224VDSL	OBJECT IDENTIFIER ::= { asr 24 }
asr3308VDSL	OBJECT IDENTIFIER ::= { asr 25 }
asr3316VDSL	OBJECT IDENTIFIER ::= { asr 26 }
asr3324VDSL	OBJECT IDENTIFIER ::= { asr 27 }
asr4708SFL	OBJECT IDENTIFIER ::= { asr 28 }
asr4716SFL	OBJECT IDENTIFIER ::= { asr 29 }
asr4724SFL	OBJECT IDENTIFIER ::= { asr 30 }
asr4108Cco	OBJECT IDENTIFIER ::= { asr 31 }
asr4116Cco	OBJECT IDENTIFIER ::= { asr 32 }
asr4124Cco	OBJECT IDENTIFIER ::= { asr 33 }
asr4208FMco	OBJECT IDENTIFIER ::= { asr 34 }
asr4216FMco	OBJECT IDENTIFIER ::= { asr 35 }
asr4224FMco	OBJECT IDENTIFIER ::= { asr 36 }
asr4308FVco	OBJECT IDENTIFIER ::= { asr 37 }
asr4316FVco	OBJECT IDENTIFIER ::= { asr 38 }
asr4324FVco	OBJECT IDENTIFIER ::= { asr 39 }
asr4508SFMco	OBJECT IDENTIFIER ::= { asr 40 }
asr4516SFMco	OBJECT IDENTIFIER ::= { asr 41 }
asr4524SFMco	OBJECT IDENTIFIER ::= { asr 42 }
asr4608SFSco	OBJECT IDENTIFIER ::= { asr 43 }
asr4616SFSco	OBJECT IDENTIFIER ::= { asr 44 }
asr4624SFSco	OBJECT IDENTIFIER ::= { asr 45 }
asr4708SFLco	OBJECT IDENTIFIER ::= { asr 46 }
asr4716SFLco	OBJECT IDENTIFIER ::= { asr 47 }
asr4724SFLco	OBJECT IDENTIFIER ::= { asr 48 }

-- ASR 10k products
asr10132co	OBJECT IDENTIFIER ::= { asr 49 }

-- ASR 5k products
asr5124Cacco	OBJECT IDENTIFIER ::= { asr 50 }
asr5124Cdcco	OBJECT IDENTIFIER ::= { asr 51 }
asr5224FMacco	OBJECT IDENTIFIER ::= { asr 52 }
asr5224FMdcco	OBJECT IDENTIFIER ::= { asr 53 }
asr5624FSacco	OBJECT IDENTIFIER ::= { asr 54 }
asr5624FSdcco	OBJECT IDENTIFIER ::= { asr 55 }
asr5724FLacco	OBJECT IDENTIFIER ::= { asr 56 }
asr5724FLdcco	OBJECT IDENTIFIER ::= { asr 57 }

-- IPD products
ipd1116C	OBJECT IDENTIFIER ::= { ipd 1 }

-- DRG products
drg100		OBJECT IDENTIFIER ::= { drg 1 }		-- DRG100, DRG22; 1xWAN, 1xLAN copper only, software bridge, 1x/2x FXS
drg340		OBJECT IDENTIFIER ::= { drg 2 }		-- DRG340/540; 1xWAN fiber/copper, 4xLAN copper only, 2xFXS
drg560		OBJECT IDENTIFIER ::= { drg 3 }		-- DRG560; 1xWAN fiber/copper, 8xLAN copper only
drg580		OBJECT IDENTIFIER ::= { drg 4 }		-- DRG580; 1xWAN fiber/copper, 8xLAN copper only, 2x FXS
evm01		OBJECT IDENTIFIER ::= { drg 5 }		-- eVoIP platform; 1xWAN MII, 2x/4x FXS
drg600Access	OBJECT IDENTIFIER ::= {	drg 6 }		-- DRG600-Access; 1xWAN fiber/copper; 6xLAN copper only
drg600Telephony	OBJECT IDENTIFIER ::= {	drg 7 }		-- DRG600-Telephony; 1xWAN, 2xFXS
drg600Wifi	OBJECT IDENTIFIER ::= {	drg 8 }		-- DRG600-WiFi; 1xWAN; 1xLAN; WiFi Router
drg615		OBJECT IDENTIFIER ::= {	drg 7 }		-- DRG615; 1xGPON; 4xLAN
drg635		OBJECT IDENTIFIER ::= {	drg 8 }		-- DRG635; 1xGPON; 4xLAN; CATV
drg701		OBJECT IDENTIFIER ::= {	drg 9 }		-- DRG700; 1x100/1000M copper WAN; 4x1000M LAN
drg702		OBJECT IDENTIFIER ::= {	drg 10 }	-- DRG700; 1x100/1000M copper WAN; 4x1000M LAN; 2xFXS
drg703		OBJECT IDENTIFIER ::= {	drg 11 }	-- DRG700; 1x100/1000M copper WAN; 4x1000M LAN; 2xFXS, IEEE802.11bgn
drg711		OBJECT IDENTIFIER ::= {	drg 12 }	-- DRG700; 1x100/1000M fiber WAN; 4x1000M LAN;
drg712		OBJECT IDENTIFIER ::= {	drg 13 }	-- DRG700; 1x100/1000M fiber WAN; 4x1000M LAN; CATV
drg714		OBJECT IDENTIFIER ::= {	drg 14 }	-- DRG700; 1x100/1000M fiber WAN; 4x1000M LAN; 2xFXS, CATV
drg716		OBJECT IDENTIFIER ::= {	drg 15 }	-- DRG700; 1x100/1000M fiber WAN; 4x1000M LAN; 2xFXS, IEEE802.11bgn, CATV
drg718		OBJECT IDENTIFIER ::= {	drg 16 }	-- DRG700; 1x100/1000M fiber WAN; 4x1000M LAN; 2xFXS
drg719		OBJECT IDENTIFIER ::= {	drg 17 }	-- DRG700; 1x100/1000M fiber WAN; 4x1000M LAN; 2xFXS, IEEE802.11bgn

-- MetroStar products
ms2016ac	OBJECT IDENTIFIER ::= { ms  1 }
ms2016dc	OBJECT IDENTIFIER ::= { ms  2 }
ms3028ac	OBJECT IDENTIFIER ::= { ms  3 }
ms3028dc	OBJECT IDENTIFIER ::= { ms  4 }
ms3128ac	OBJECT IDENTIFIER ::= { ms  5 }
ms3128dc	OBJECT IDENTIFIER ::= { ms  6 }

END
