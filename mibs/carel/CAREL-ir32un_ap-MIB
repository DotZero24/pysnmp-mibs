--
-- CAREL-ir32un_ap.MIB
-- MIB generated by CAREL
-- Friday, 14 March 2003
--

    CAREL-ir32un_ap-MIB DEFINITIONS ::= BEGIN

		IMPORTS
			OBJECT-GROUP
				FROM SNMPv2-CONF
			sysContact, sysName, sysLocation
				FROM SNMPv2-MIB
			enterprises, MODULE-IDENTITY
				FROM SNMPv2-SMI;

        ir32un_apMIB MODULE-IDENTITY
      		LAST-UPDATED  "200303141724Z"		-- March 14, 2003 at 17:24 GMT
      		ORGANIZATION  "CAREL SpA"
      		CONTACT-INFO
                "
                        Simone Ravazzolo
                        Carel SpA
                        Via dell'Industria, 11
                        35020 Brugine (PD) Italy
                        Tel: +39 049 9716611
                        E-mail: simone.ravazzolo@carel.com
                "
      		DESCRIPTION
                "This is the MIB module for the ir32un_ap device."
			::= { instruments 1 }


--
-- Node definitions
--

		-- 1.3.6.1.4.1.9839
		carel OBJECT IDENTIFIER ::= { enterprises 9839 }

		-- 1.3.6.1.4.1.9839.1
		systm OBJECT IDENTIFIER ::= { carel 1 }

		-- 1.3.6.1.4.1.9839.1.1
		agentRelease OBJECT-TYPE
			SYNTAX Integer32
			UNITS "N/A"
			MAX-ACCESS read-only
			STATUS current
			DESCRIPTION "Release of the Agent."
		::= { systm 1 }

		-- 1.3.6.1.4.1.9839.1.2
		agentCode OBJECT-TYPE
			SYNTAX Integer32
			UNITS "N/A"
			MAX-ACCESS read-only
			STATUS current
			DESCRIPTION "Code of the Agent. 1=WebGate"
		::= { systm 2 }

		-- 1.3.6.1.4.1.9839.2
		instruments OBJECT IDENTIFIER ::= { carel 2 }

		-- 1.3.6.1.4.1.9839.2.0
		webGateInfo OBJECT IDENTIFIER ::= { instruments 0 }

		-- 1.3.6.1.4.1.9839.2.0.1
		agentParameters OBJECT IDENTIFIER ::= { webGateInfo 1 }

		-- 1.3.6.1.4.1.9839.2.0.1.1
		netSize OBJECT-TYPE
			SYNTAX Integer32 (1..16)
			UNITS "N/A"
			MAX-ACCESS read-write
			STATUS current
			DESCRIPTION "Network size. It corresponds to the number of units connected to the WebGate. "
		::= { agentParameters 1 }

		-- 1.3.6.1.4.1.9839.2.0.1.2
		baudRate OBJECT-TYPE
			SYNTAX Integer32 (1200 | 2400 |4800 |9600 | 19200)
			UNITS "N/A"
			MAX-ACCESS read-write
			STATUS current
			DESCRIPTION "Baudrate of the Carel network. "
		::= { agentParameters 2 }

		-- 1.3.6.1.4.1.9839.2.0.2
		unitTypeGroup OBJECT IDENTIFIER ::= { webGateInfo 2 }

		-- 1.3.6.1.4.1.9839.2.0.2.1
		unit1-Type OBJECT-TYPE
			SYNTAX DisplayString
			UNITS "N/A"
			MAX-ACCESS read-only
			STATUS current
			DESCRIPTION "Type of the unit having serial address 1. "
			::= { unitTypeGroup 1 }

		-- ... You will have how many unitX-Type objects as the value of netSize is

		-- 1.3.6.1.4.1.9839.2.0.3
		unitCodeGroup OBJECT IDENTIFIER ::= { webGateInfo 3 }

		-- 1.3.6.1.4.1.9839.2.0.3.1
		unit1-Code OBJECT-TYPE
			SYNTAX Integer32
			UNITS "N/A"
			MAX-ACCESS read-only
			STATUS current
			DESCRIPTION "Code of the unit having serial address 1. "
			::= { unitCodeGroup 1 }

		-- ... You will have how many unitX-Code objects as the value of netSize is

		-- 1.3.6.1.4.1.9839.2.0.4
		unitSoftwareReleaseGroup OBJECT IDENTIFIER ::= { webGateInfo 4 }

		-- 1.3.6.1.4.1.9839.2.0.3.1
		unit1-SoftwareRelease OBJECT-TYPE
			SYNTAX Integer32
			UNITS "N/A"
			MAX-ACCESS read-only
			STATUS current
			DESCRIPTION "Software release of the unit having serial address 1. "
			::= { unitSoftwareReleaseGroup 1 }

		-- ... You will have how many unitX-SoftwareRelease objects as the value of netSize is

		-- 1.3.6.1.4.1.9839.2.0.5
		unitMinSoftwareReleaseGroup OBJECT IDENTIFIER ::= { webGateInfo 5 }

		-- 1.3.6.1.4.1.9839.2.0.5.1
		unit1-MinSoftwareRelease OBJECT-TYPE
			SYNTAX Integer32
			UNITS "N/A"
			MAX-ACCESS read-only
			STATUS current
			DESCRIPTION "Minimum software release of the unit having serial address 1. "
			::= { unitMinSoftwareReleaseGroup 1 }

		-- ... You will have how many unitX-MinSoftwareRelease objects as the value of netSize is

		-- 1.3.6.1.4.1.9839.2.0.6
		unitMaxSoftwareReleaseGroup OBJECT IDENTIFIER ::= { webGateInfo 6 }

		-- 1.3.6.1.4.1.9839.2.0.6.1
		unit1-MaxSoftwareRelease OBJECT-TYPE
			SYNTAX Integer32
			UNITS "N/A"
			MAX-ACCESS read-only
			STATUS current
			DESCRIPTION "Maximum software release of the unit having serial address 1. "
			::= { unitMaxSoftwareReleaseGroup 1 }

		-- ... You will have how many unitX-MaxSoftwareRelease objects as the value of netSize is

		-- 1.3.6.1.4.1.9839.2.0.7
		unitNoAnswerCounterGroup OBJECT IDENTIFIER ::= { webGateInfo 7 }

		-- 1.3.6.1.4.1.9839.2.0.7.1
		unit1-NoAnswerCounter OBJECT-TYPE
			SYNTAX Integer32
			UNITS "N/A"
			MAX-ACCESS read-only
			STATUS current
			DESCRIPTION "No answer counter of the unit having serial address 1. "
			::= { unitNoAnswerCounterGroup 1 }

		-- ... You will have how many unitX-NoAnswerCounter objects as the value of netSize is

		-- 1.3.6.1.4.1.9839.2.0.8
		unitErrorChecksumCounterGroup OBJECT IDENTIFIER ::= { webGateInfo 8 }

		-- 1.3.6.1.4.1.9839.2.0.8.1
		unit1-ErrorChecksumCounter OBJECT-TYPE
			SYNTAX Integer32
			UNITS "N/A"
			MAX-ACCESS read-only
			STATUS current
			DESCRIPTION "Error checksum counter of the unit having serial address 1. "
			::= { unitErrorChecksumCounterGroup 1 }

		-- ... You will have how many unitX-ErrorChecksumCounter objects as the value of netSize is

		-- 1.3.6.1.4.1.9839.2.0.9
		unitTimeoutCounterGroup OBJECT IDENTIFIER ::= { webGateInfo 9 }

		-- 1.3.6.1.4.1.9839.2.0.9.1
		unit1-TimeoutCounter OBJECT-TYPE
			SYNTAX Integer32
			UNITS "N/A"
			MAX-ACCESS read-only
			STATUS current
			DESCRIPTION "Timeout counter of the unit having serial address 1. "
			::= { unitTimeoutCounterGroup 1 }

		-- ... You will have how many unitX-TimeoutCounter objects as the value of netSize is

		-- 1.3.6.1.4.1.9839.2.0.10
		unitOnLineStatusGroup OBJECT IDENTIFIER ::= { webGateInfo 10 }

		-- 1.3.6.1.4.1.9839.2.0.10.1
		unit1-OnLineStatus OBJECT-TYPE
			SYNTAX Integer32
			UNITS "N/A"
			MAX-ACCESS read-only
			STATUS current
			DESCRIPTION "On line status of the unit having serial address 1. "
			::= { unitOnLineStatusGroup 1 }

		-- ... You will have how many unitX-OnLineStatus objects as the value of netSize is

		-- 1.3.6.1.4.1.9839.2.1
        -- ir32un_apMIB OBJECT IDENTIFIER ::= { instruments 1 }

        -- 1.3.6.1.4.1.9839.2.1.1
        digitalObjects OBJECT IDENTIFIER ::= { ir32un_apMIB 1 }

        -- 1.3.6.1.4.1.9839.2.1.1.1
        stato_id_1 OBJECT-TYPE
                    SYNTAX Integer32 (0..1)
                    UNITS "N/A"
                    MAX-ACCESS read-only
                    STATUS current
                    DESCRIPTION "Digital input 1"
                    ::= { digitalObjects 1 }

        -- 1.3.6.1.4.1.9839.2.1.1.2
        stato_id_2 OBJECT-TYPE
                    SYNTAX Integer32 (0..1)
                    UNITS "N/A"
                    MAX-ACCESS read-only
                    STATUS current
                    DESCRIPTION "Digital input 2"
                    ::= { digitalObjects 2 }

        -- 1.3.6.1.4.1.9839.2.1.1.3
        stato_ud_1 OBJECT-TYPE
                    SYNTAX Integer32 (0..1)
                    UNITS "N/A"
                    MAX-ACCESS read-only
                    STATUS current
                    DESCRIPTION "Out 1"
                    ::= { digitalObjects 3 }

        -- 1.3.6.1.4.1.9839.2.1.1.4
        stato_ud_2 OBJECT-TYPE
                    SYNTAX Integer32 (0..1)
                    UNITS "N/A"
                    MAX-ACCESS read-only
                    STATUS current
                    DESCRIPTION "Out 2"
                    ::= { digitalObjects 4 }

        -- 1.3.6.1.4.1.9839.2.1.1.5
        stato_ud_3 OBJECT-TYPE
                    SYNTAX Integer32 (0..1)
                    UNITS "N/A"
                    MAX-ACCESS read-only
                    STATUS current
                    DESCRIPTION "Out 3"
                    ::= { digitalObjects 5 }

        -- 1.3.6.1.4.1.9839.2.1.1.6
        stato_ud_4 OBJECT-TYPE
                    SYNTAX Integer32 (0..1)
                    UNITS "N/A"
                    MAX-ACCESS read-only
                    STATUS current
                    DESCRIPTION "Out 4"
                    ::= { digitalObjects 6 }

        -- 1.3.6.1.4.1.9839.2.1.1.8
        all_sonda_0 OBJECT-TYPE
                    SYNTAX Integer32 (0..1)
                    UNITS "N/A"
                    MAX-ACCESS read-only
                    STATUS current
                    DESCRIPTION "Probe 1 error"
                    ::= { digitalObjects 8 }

        -- 1.3.6.1.4.1.9839.2.1.1.9
        all_sonda_1 OBJECT-TYPE
                    SYNTAX Integer32 (0..1)
                    UNITS "N/A"
                    MAX-ACCESS read-only
                    STATUS current
                    DESCRIPTION "Probe 2 error"
                    ::= { digitalObjects 9 }

        -- 1.3.6.1.4.1.9839.2.1.1.10
        all_eeprom OBJECT-TYPE
                    SYNTAX Integer32 (0..1)
                    UNITS "N/A"
                    MAX-ACCESS read-only
                    STATUS current
                    DESCRIPTION "Eeprom memory error"
                    ::= { digitalObjects 10 }

        -- 1.3.6.1.4.1.9839.2.1.1.11
        all_id_1 OBJECT-TYPE
                    SYNTAX Integer32 (0..1)
                    UNITS "N/A"
                    MAX-ACCESS read-only
                    STATUS current
                    DESCRIPTION "Alarm from digital input 1"
                    ::= { digitalObjects 11 }

        -- 1.3.6.1.4.1.9839.2.1.1.12
        all_alta_temp OBJECT-TYPE
                    SYNTAX Integer32 (0..1)
                    UNITS "N/A"
                    MAX-ACCESS read-only
                    STATUS current
                    DESCRIPTION "High pressure alarm"
                    ::= { digitalObjects 12 }

        -- 1.3.6.1.4.1.9839.2.1.1.13
        all_bassa_temp OBJECT-TYPE
                    SYNTAX Integer32 (0..1)
                    UNITS "N/A"
                    MAX-ACCESS read-only
                    STATUS current
                    DESCRIPTION "Low pressure alarm"
                    ::= { digitalObjects 13 }

        -- 1.3.6.1.4.1.9839.2.1.1.14
        prop_prop_int OBJECT-TYPE
                    SYNTAX Integer32 (0..1)
                    UNITS "N/A"
                    MAX-ACCESS read-write
                    STATUS current
                    DESCRIPTION "Type of regulation"
                    DEFVAL { 0 }
                    ::= { digitalObjects 14 }

        -- 1.3.6.1.4.1.9839.2.1.1.15
        tipo_sonda OBJECT-TYPE
                    SYNTAX Integer32 (0..1)
                    UNITS "N/A"
                    MAX-ACCESS read-write
                    STATUS current
                    DESCRIPTION "Sensor type"
                    DEFVAL { 0 }
                    ::= { digitalObjects 15 }

        -- 1.3.6.1.4.1.9839.2.1.1.16
        celsius_farhan OBJECT-TYPE
                    SYNTAX Integer32 (0..1)
                    UNITS "N/A"
                    MAX-ACCESS read-write
                    STATUS current
                    DESCRIPTION "Temperature unit of measure: °C or °F"
                    DEFVAL { 0 }
                    ::= { digitalObjects 16 }

        -- 1.3.6.1.4.1.9839.2.1.1.17
        modo_speciale OBJECT-TYPE
                    SYNTAX Integer32 (0..1)
                    UNITS "N/A"
                    MAX-ACCESS read-write
                    STATUS current
                    DESCRIPTION "“Special” mode of operation"
                    DEFVAL { 0 }
                    ::= { digitalObjects 17 }

        -- 1.3.6.1.4.1.9839.2.1.1.18
        tipo_out_grad4 OBJECT-TYPE
                    SYNTAX Integer32 (0..1)
                    UNITS "N/A"
                    MAX-ACCESS read-write
                    STATUS current
                    DESCRIPTION "OUT4: Type of output"
                    ::= { digitalObjects 18 }

        -- 1.3.6.1.4.1.9839.2.1.1.19
        tipo_out_grad3 OBJECT-TYPE
                    SYNTAX Integer32 (0..1)
                    UNITS "N/A"
                    MAX-ACCESS read-write
                    STATUS current
                    DESCRIPTION "OUT3: Type of output"
                    ::= { digitalObjects 19 }

        -- 1.3.6.1.4.1.9839.2.1.1.20
        tipo_out_grad2 OBJECT-TYPE
                    SYNTAX Integer32 (0..1)
                    UNITS "N/A"
                    MAX-ACCESS read-write
                    STATUS current
                    DESCRIPTION "OUT2: Type of output"
                    ::= { digitalObjects 20 }

        -- 1.3.6.1.4.1.9839.2.1.1.21
        tipo_out_grad1 OBJECT-TYPE
                    SYNTAX Integer32 (0..1)
                    UNITS "N/A"
                    MAX-ACCESS read-write
                    STATUS current
                    DESCRIPTION "OUT1: Type of output"
                    ::= { digitalObjects 21 }



        -- 1.3.6.1.4.1.9839.2.1.2
        analogObjects OBJECT IDENTIFIER ::= { ir32un_apMIB 2 }

        -- 1.3.6.1.4.1.9839.2.1.2.1
        ing_sonda_0 OBJECT-TYPE
                    SYNTAX Integer32 (-32767..32767)
                    UNITS "bar x10"
                    MAX-ACCESS read-only
                    STATUS current
                    DESCRIPTION "Probe 1"
                    ::= { analogObjects 1 }

        -- 1.3.6.1.4.1.9839.2.1.2.3
        set_point1 OBJECT-TYPE
                    SYNTAX Integer32 (-32767..32767)
                    UNITS "N/A"
                    MAX-ACCESS read-write
                    STATUS current
                    DESCRIPTION "Main set-point"
                    DEFVAL { 200 }
                    ::= { analogObjects 3 }

        -- 1.3.6.1.4.1.9839.2.1.2.4
        set_point2 OBJECT-TYPE
                    SYNTAX Integer32 (-32767..32767)
                    UNITS "N/A"
                    MAX-ACCESS read-write
                    STATUS current
                    DESCRIPTION "Second set-point"
                    DEFVAL { 400 }
                    ::= { analogObjects 4 }

        -- 1.3.6.1.4.1.9839.2.1.2.5
        differenziale1 OBJECT-TYPE
                    SYNTAX Integer32 (1..999)
                    UNITS "bar x10"
                    MAX-ACCESS read-write
                    STATUS current
                    DESCRIPTION "Differential St1"
                    DEFVAL { 20 }
                    ::= { analogObjects 5 }

        -- 1.3.6.1.4.1.9839.2.1.2.6
        differenziale2 OBJECT-TYPE
                    SYNTAX Integer32 (1..999)
                    UNITS "bar x10"
                    MAX-ACCESS read-write
                    STATUS current
                    DESCRIPTION "Differential St2"
                    DEFVAL { 20 }
                    ::= { analogObjects 6 }

        -- 1.3.6.1.4.1.9839.2.1.2.7
        zona_morta OBJECT-TYPE
                    SYNTAX Integer32 (0..999)
                    UNITS "bar x10"
                    MAX-ACCESS read-write
                    STATUS current
                    DESCRIPTION "Dead zone"
                    DEFVAL { 20 }
                    ::= { analogObjects 7 }

        -- 1.3.6.1.4.1.9839.2.1.2.8
        offset_sonda OBJECT-TYPE
                    SYNTAX Integer32 (-990..999)
                    UNITS "bar x10"
                    MAX-ACCESS read-write
                    STATUS current
                    DESCRIPTION "Inlet probe calibration"
                    DEFVAL { 0 }
                    ::= { analogObjects 8 }

        -- 1.3.6.1.4.1.9839.2.1.2.9
        sog_bassa_temp OBJECT-TYPE
                    SYNTAX Integer32 (-990..32767)
                    UNITS "bar x10"
                    MAX-ACCESS read-write
                    STATUS current
                    DESCRIPTION "Low pressure set"
                    ::= { analogObjects 9 }

        -- 1.3.6.1.4.1.9839.2.1.2.10
        sog_alta_temp OBJECT-TYPE
                    SYNTAX Integer32 (-32767..9990)
                    UNITS "bar x10"
                    MAX-ACCESS read-write
                    STATUS current
                    DESCRIPTION "High pressure set"
                    ::= { analogObjects 10 }

        -- 1.3.6.1.4.1.9839.2.1.2.11
        differenz_all OBJECT-TYPE
                    SYNTAX Integer32 (-990..990)
                    UNITS "bar x10"
                    MAX-ACCESS read-write
                    STATUS current
                    DESCRIPTION "Alarm differential (absolute value)"
                    DEFVAL { 20 }
                    ::= { analogObjects 11 }

        -- 1.3.6.1.4.1.9839.2.1.2.12
        tempo_di_pwm OBJECT-TYPE
                    SYNTAX Integer32 (2..9990)
                    UNITS "sec-0.2 x10"
                    MAX-ACCESS read-write
                    STATUS current
                    DESCRIPTION "PWM cycle time"
                    DEFVAL { 200 }
                    ::= { analogObjects 12 }

        -- 1.3.6.1.4.1.9839.2.1.2.13
        val_minimo_av OBJECT-TYPE
                    SYNTAX Integer32 (-990..32767)
                    UNITS "N/A"
                    MAX-ACCESS read-write
                    STATUS current
                    DESCRIPTION "Minimum value of voltage and current inputs"
                    DEFVAL { 0 }
                    ::= { analogObjects 13 }

        -- 1.3.6.1.4.1.9839.2.1.2.14
        val_massimo_av OBJECT-TYPE
                    SYNTAX Integer32 (-32767..9990)
                    UNITS "N/A"
                    MAX-ACCESS read-write
                    STATUS current
                    DESCRIPTION "Maximum value of voltage and current inputs"
                    DEFVAL { 1000 }
                    ::= { analogObjects 14 }

        -- 1.3.6.1.4.1.9839.2.1.2.15
        set1_min_ok OBJECT-TYPE
                    SYNTAX Integer32 (-990..32767)
                    UNITS "bar x10"
                    MAX-ACCESS read-write
                    STATUS current
                    DESCRIPTION "Minimum value of St1"
                    ::= { analogObjects 15 }

        -- 1.3.6.1.4.1.9839.2.1.2.16
        set1_max_ok OBJECT-TYPE
                    SYNTAX Integer32 (-32767..9990)
                    UNITS "bar x10"
                    MAX-ACCESS read-write
                    STATUS current
                    DESCRIPTION "Maximum value of St1"
                    ::= { analogObjects 16 }

        -- 1.3.6.1.4.1.9839.2.1.2.17
        set2_min_ok OBJECT-TYPE
                    SYNTAX Integer32 (-990..32767)
                    UNITS "bar x10"
                    MAX-ACCESS read-write
                    STATUS current
                    DESCRIPTION "Minimum value of St2"
                    ::= { analogObjects 17 }

        -- 1.3.6.1.4.1.9839.2.1.2.18
        set2_max_ok OBJECT-TYPE
                    SYNTAX Integer32 (-32767..9990)
                    UNITS "bar x10"
                    MAX-ACCESS read-write
                    STATUS current
                    DESCRIPTION "Maximum value of St2"
                    ::= { analogObjects 18 }

        -- 1.3.6.1.4.1.9839.2.1.2.19
        autorita OBJECT-TYPE
                    SYNTAX Integer32 (-20..20)
                    UNITS "N/A"
                    MAX-ACCESS read-write
                    STATUS current
                    DESCRIPTION "Authority"
                    DEFVAL { 5 }
                    ::= { analogObjects 19 }



        -- 1.3.6.1.4.1.9839.2.1.3
        integerObjects OBJECT IDENTIFIER ::= { ir32un_apMIB 3 }

        -- 1.3.6.1.4.1.9839.2.1.3.1
        modo_funz_c0 OBJECT-TYPE
                    SYNTAX Integer32 (1..9)
                    UNITS "N/A"
                    MAX-ACCESS read-write
                    STATUS current
                    DESCRIPTION "Mode of operation"
                    DEFVAL { 2 }
                    ::= { integerObjects 1 }

        -- 1.3.6.1.4.1.9839.2.1.3.2
        rit_2ins_c6 OBJECT-TYPE
                    SYNTAX Integer32 (0..999)
                    UNITS "sec"
                    MAX-ACCESS read-write
                    STATUS current
                    DESCRIPTION "Delay between energizations of different outputs"
                    DEFVAL { 5 }
                    ::= { integerObjects 2 }

        -- 1.3.6.1.4.1.9839.2.1.3.3
        tmin_2out_c7 OBJECT-TYPE
                    SYNTAX Integer32 (0..15)
                    UNITS "min"
                    MAX-ACCESS read-write
                    STATUS current
                    DESCRIPTION "Minimum time between 2 sucess. energ. output"
                    DEFVAL { 0 }
                    ::= { integerObjects 3 }

        -- 1.3.6.1.4.1.9839.2.1.3.4
        tmin_off_out_c8 OBJECT-TYPE
                    SYNTAX Integer32 (0..15)
                    UNITS "min"
                    MAX-ACCESS read-write
                    STATUS current
                    DESCRIPTION "Minimum disenergization time-interval"
                    DEFVAL { 0 }
                    ::= { integerObjects 4 }

        -- 1.3.6.1.4.1.9839.2.1.3.5
        tmin_on_c9 OBJECT-TYPE
                    SYNTAX Integer32 (0..15)
                    UNITS "min"
                    MAX-ACCESS read-write
                    STATUS current
                    DESCRIPTION "Minimum energization time-interval"
                    DEFVAL { 0 }
                    ::= { integerObjects 5 }

        -- 1.3.6.1.4.1.9839.2.1.3.6
        sicur_sonde OBJECT-TYPE
                    SYNTAX Integer32 (0..3)
                    UNITS "N/A"
                    MAX-ACCESS read-write
                    STATUS current
                    DESCRIPTION "Outputs status in the event of sensor alarm"
                    DEFVAL { 0 }
                    ::= { integerObjects 6 }

        -- 1.3.6.1.4.1.9839.2.1.3.7
        rotazione OBJECT-TYPE
                    SYNTAX Integer32 (0..7)
                    UNITS "N/A"
                    MAX-ACCESS read-write
                    STATUS current
                    DESCRIPTION "Rotation"
                    DEFVAL { 0 }
                    ::= { integerObjects 7 }

        -- 1.3.6.1.4.1.9839.2.1.3.8
        velocita_sonda OBJECT-TYPE
                    SYNTAX Integer32 (1..14)
                    UNITS "N/A"
                    MAX-ACCESS read-write
                    STATUS current
                    DESCRIPTION "Sensor response"
                    DEFVAL { 5 }
                    ::= { integerObjects 8 }

        -- 1.3.6.1.4.1.9839.2.1.3.9
        presenza_sonda OBJECT-TYPE
                    SYNTAX Integer32 (0..4)
                    UNITS "N/A"
                    MAX-ACCESS read-write
                    STATUS current
                    DESCRIPTION "Use of the second sensor"
                    DEFVAL { 0 }
                    ::= { integerObjects 9 }

        -- 1.3.6.1.4.1.9839.2.1.3.10
        tempo_allarme OBJECT-TYPE
                    SYNTAX Integer32 (120..60)
                    UNITS "min"
                    MAX-ACCESS read-write
                    STATUS current
                    DESCRIPTION "Delayed alarm"
                    ::= { integerObjects 10 }

        -- 1.3.6.1.4.1.9839.2.1.3.11
        gestione_id1 OBJECT-TYPE
                    SYNTAX Integer32 (0..4)
                    UNITS "N/A"
                    MAX-ACCESS read-write
                    STATUS current
                    DESCRIPTION "Digital input 1 management"
                    DEFVAL { 0 }
                    ::= { integerObjects 11 }

        -- 1.3.6.1.4.1.9839.2.1.3.12
        gestione_id2 OBJECT-TYPE
                    SYNTAX Integer32 (0..4)
                    UNITS "N/A"
                    MAX-ACCESS read-write
                    STATUS current
                    DESCRIPTION "Digital input 2 management"
                    DEFVAL { 0 }
                    ::= { integerObjects 12 }

        -- 1.3.6.1.4.1.9839.2.1.3.13
        sicur_all_id OBJECT-TYPE
                    SYNTAX Integer32 (0..3)
                    UNITS "N/A"
                    MAX-ACCESS read-write
                    STATUS current
                    DESCRIPTION "Outputs status in the event of alarm via dig. input"
                    DEFVAL { 0 }
                    ::= { integerObjects 13 }

        -- 1.3.6.1.4.1.9839.2.1.3.14
        set_gradino1 OBJECT-TYPE
                    SYNTAX Integer32 (0..15)
                    UNITS "N/A"
                    MAX-ACCESS read-write
                    STATUS current
                    DESCRIPTION "OUT1: Dependence"
                    ::= { integerObjects 14 }

        -- 1.3.6.1.4.1.9839.2.1.3.15
        offset_grad1 OBJECT-TYPE
                    SYNTAX Integer32 (-100..100)
                    UNITS "N/A"
                    MAX-ACCESS read-write
                    STATUS current
                    DESCRIPTION "OUT1: Energization"
                    ::= { integerObjects 15 }

        -- 1.3.6.1.4.1.9839.2.1.3.16
        diff_gradino1 OBJECT-TYPE
                    SYNTAX Integer32 (-100..100)
                    UNITS "N/A"
                    MAX-ACCESS read-write
                    STATUS current
                    DESCRIPTION "OUT1: Differential / Logic"
                    ::= { integerObjects 16 }

        -- 1.3.6.1.4.1.9839.2.1.3.17
        set_gradino2 OBJECT-TYPE
                    SYNTAX Integer32 (0..15)
                    UNITS "N/A"
                    MAX-ACCESS read-write
                    STATUS current
                    DESCRIPTION "OUT2: Dependence"
                    ::= { integerObjects 17 }

        -- 1.3.6.1.4.1.9839.2.1.3.18
        offset_grad2 OBJECT-TYPE
                    SYNTAX Integer32 (-100..100)
                    UNITS "N/A"
                    MAX-ACCESS read-write
                    STATUS current
                    DESCRIPTION "OUT2: Energization"
                    ::= { integerObjects 18 }

        -- 1.3.6.1.4.1.9839.2.1.3.19
        diff_gradino2 OBJECT-TYPE
                    SYNTAX Integer32 (-100..100)
                    UNITS "N/A"
                    MAX-ACCESS read-write
                    STATUS current
                    DESCRIPTION "OUT2: Differential / Logic"
                    ::= { integerObjects 19 }

        -- 1.3.6.1.4.1.9839.2.1.3.20
        set_gradino3 OBJECT-TYPE
                    SYNTAX Integer32 (0..15)
                    UNITS "N/A"
                    MAX-ACCESS read-write
                    STATUS current
                    DESCRIPTION "OUT3: Dependence"
                    ::= { integerObjects 20 }

        -- 1.3.6.1.4.1.9839.2.1.3.21
        offset_grad3 OBJECT-TYPE
                    SYNTAX Integer32 (-100..100)
                    UNITS "N/A"
                    MAX-ACCESS read-write
                    STATUS current
                    DESCRIPTION "OUT3: Energization"
                    ::= { integerObjects 21 }

        -- 1.3.6.1.4.1.9839.2.1.3.22
        diff_gradino3 OBJECT-TYPE
                    SYNTAX Integer32 (-100..100)
                    UNITS "N/A"
                    MAX-ACCESS read-write
                    STATUS current
                    DESCRIPTION "OUT3: Differential / Logic"
                    ::= { integerObjects 22 }

        -- 1.3.6.1.4.1.9839.2.1.3.23
        set_gradino4 OBJECT-TYPE
                    SYNTAX Integer32 (0..15)
                    UNITS "N/A"
                    MAX-ACCESS read-write
                    STATUS current
                    DESCRIPTION "OUT4: Dependence"
                    ::= { integerObjects 23 }

        -- 1.3.6.1.4.1.9839.2.1.3.24
        offset_grad4 OBJECT-TYPE
                    SYNTAX Integer32 (-100..100)
                    UNITS "N/A"
                    MAX-ACCESS read-write
                    STATUS current
                    DESCRIPTION "OUT4: Energization"
                    ::= { integerObjects 24 }

        -- 1.3.6.1.4.1.9839.2.1.3.25
        diff_gradino4 OBJECT-TYPE
                    SYNTAX Integer32 (-100..100)
                    UNITS "N/A"
                    MAX-ACCESS read-write
                    STATUS current
                    DESCRIPTION "OUT4: Differential / Logic"
                    ::= { integerObjects 25 }

        -- 1.3.6.1.4.1.9839.2.1.3.26
        tast_telecom OBJECT-TYPE
                    SYNTAX Integer32 (0..4)
                    UNITS "N/A"
                    MAX-ACCESS read-write
                    STATUS current
                    DESCRIPTION "Operating keypad and/or remote control"
                    DEFVAL { 4 }
                    ::= { integerObjects 26 }

        -- 1.3.6.1.4.1.9839.2.1.3.27
        codice_telecom OBJECT-TYPE
                    SYNTAX Integer32 (0..120)
                    UNITS "N/A"
                    MAX-ACCESS read-write
                    STATUS current
                    DESCRIPTION "Operating the remote control"
                    DEFVAL { 0 }
                    ::= { integerObjects 27 }



	END

--
-- CAREL-ir32un_ap.MIB
--
