--
-- UNCDZ.MIB
-- MIB generated by CAREL
-- Thursday, 12 August 2004
--

    UNCDZ-MIB DEFINITIONS ::= BEGIN

		IMPORTS
			OBJECT-GROUP
				FROM SNMPv2-CONF
			sysContact, sysName, sysLocation
				FROM SNMPv2-MIB
			enterprises, MODULE-IDENTITY, OBJECT-TYPE, Integer32
				FROM SNMPv2-SMI;

        uncdz-MIB MODULE-IDENTITY
      		LAST-UPDATED  "200408121552Z"		-- August 12, 2004 at 15:52 GMT
      		ORGANIZATION  "CAREL SpA"
      		CONTACT-INFO
                "
                        Simone Ravazzolo
                        Carel SpA
                        Via dell'Industria, 11
                        35020 Brugine (PD) Italy
                        Tel: +39 049 9716611
                        E-mail: simone.ravazzolo@carel.com
                "
      		DESCRIPTION
                "This is the MIB module for the UNIFLAIR UNCDZ device."
      		REVISION  "200408121552Z"		-- August 12, 2004 at 15:52 GMT
      		DESCRIPTION
                "This is the original version of the MIB."
			::= { instruments 1 }


--
-- Node definitions
--

		-- 1.3.6.1.4.1.9839
		carel OBJECT IDENTIFIER ::= { enterprises 9839 }

		-- 1.3.6.1.4.1.9839.1
		systm OBJECT IDENTIFIER ::= { carel 1 }

		-- 1.3.6.1.4.1.9839.1.1
		agentRelease OBJECT-TYPE
			SYNTAX Integer32
			UNITS "N/A"
			MAX-ACCESS read-only
			STATUS current
			DESCRIPTION "Release of the Agent."
		::= { systm 1 }

		-- 1.3.6.1.4.1.9839.1.2
		agentCode OBJECT-TYPE
			SYNTAX Integer32
			UNITS "N/A"
			MAX-ACCESS read-only
			STATUS current
   			DESCRIPTION "Code of the Agent. 2=pCOWeb."
		::= { systm 2 }

		-- 1.3.6.1.4.1.9839.2
		instruments OBJECT IDENTIFIER ::= { carel 2 }

		-- 1.3.6.1.4.1.9839.2.0
 		pCOWebInfo OBJECT IDENTIFIER ::= { instruments 0 }


		-- 1.3.6.1.4.1.9839.2.0.10
		pCOStatusgroup OBJECT IDENTIFIER ::= { pCOWebInfo 10 }

		-- 1.3.6.1.4.1.9839.2.0.10.1
		pCOId1-Status OBJECT-TYPE
			SYNTAX Integer32
			UNITS "N/A"
			MAX-ACCESS read-only
			STATUS current
			DESCRIPTION "Status of pCOId1. 0=Offline, 1=Init, 2=Online"
			::= { pCOStatusgroup 1 }

		-- ... You will have how many pCOIdX-Status objects as the pCOs connected to pCOWeb.

		-- 1.3.6.1.4.1.9839.2.0.11
		pCOErrorsNumbergroup OBJECT IDENTIFIER ::= { pCOWebInfo 11 }

		-- 1.3.6.1.4.1.9839.2.0.11.1
		pCOId1-ErrorsNumber OBJECT-TYPE
			SYNTAX Integer32
			UNITS "N/A"
			MAX-ACCESS read-only
			STATUS current
			DESCRIPTION "Number of Communication Errors from pCOId1 to pCOWeb."
			::= { pCOErrorsNumbergroup 1 }

		-- ... You will have how many pCOIdX-ErrorsNumber objects as the pCOs connected to pCOWeb.

	-- 1.3.6.1.4.1.9839.2.1.1
	digitalObjects OBJECT IDENTIFIER ::= { uncdz-MIB 1 }

        -- 1.3.6.1.4.1.9839.2.1.1.1
        vent-on OBJECT-TYPE
                    SYNTAX Integer32
                    UNITS "N/A"
                    MAX-ACCESS read-only
                    STATUS current
                    DESCRIPTION "System On (Fan)"
                    ::= { digitalObjects 1 }

        -- 1.3.6.1.4.1.9839.2.1.1.2
        compressore1 OBJECT-TYPE
                    SYNTAX Integer32
                    UNITS "N/A"
                    MAX-ACCESS read-only
                    STATUS current
                    DESCRIPTION "Compressor 1"
                    ::= { digitalObjects 2 }

        -- 1.3.6.1.4.1.9839.2.1.1.3
        compressore2 OBJECT-TYPE
                    SYNTAX Integer32
                    UNITS "N/A"
                    MAX-ACCESS read-only
                    STATUS current
                    DESCRIPTION "Compressor 2"
                    ::= { digitalObjects 3 }

        -- 1.3.6.1.4.1.9839.2.1.1.4
        compressore3 OBJECT-TYPE
                    SYNTAX Integer32
                    UNITS "N/A"
                    MAX-ACCESS read-only
                    STATUS current
                    DESCRIPTION "Compressor 3"
                    ::= { digitalObjects 4 }

        -- 1.3.6.1.4.1.9839.2.1.1.5
        compressore4 OBJECT-TYPE
                    SYNTAX Integer32
                    UNITS "N/A"
                    MAX-ACCESS read-only
                    STATUS current
                    DESCRIPTION "Compressor 4"
                    ::= { digitalObjects 5 }

        -- 1.3.6.1.4.1.9839.2.1.1.6
        out-h1 OBJECT-TYPE
                    SYNTAX Integer32
                    UNITS "N/A"
                    MAX-ACCESS read-only
                    STATUS current
                    DESCRIPTION "Heating 1"
                    ::= { digitalObjects 6 }

        -- 1.3.6.1.4.1.9839.2.1.1.7
        out-h2 OBJECT-TYPE
                    SYNTAX Integer32
                    UNITS "N/A"
                    MAX-ACCESS read-only
                    STATUS current
                    DESCRIPTION "Heating 2"
                    ::= { digitalObjects 7 }

        -- 1.3.6.1.4.1.9839.2.1.1.8
        out-h3 OBJECT-TYPE
                    SYNTAX Integer32
                    UNITS "N/A"
                    MAX-ACCESS read-only
                    STATUS current
                    DESCRIPTION "Heating 3"
                    ::= { digitalObjects 8 }

        -- 1.3.6.1.4.1.9839.2.1.1.9
        gas-caldo-on OBJECT-TYPE
                    SYNTAX Integer32
                    UNITS "N/A"
                    MAX-ACCESS read-only
                    STATUS current
                    DESCRIPTION "Hot Gas Coil"
                    ::= { digitalObjects 9 }

        -- 1.3.6.1.4.1.9839.2.1.1.10
        on-deum OBJECT-TYPE
                    SYNTAX Integer32
                    UNITS "N/A"
                    MAX-ACCESS read-only
                    STATUS current
                    DESCRIPTION "Dehumidification"
                    ::= { digitalObjects 10 }

        -- 1.3.6.1.4.1.9839.2.1.1.11
        power OBJECT-TYPE
                    SYNTAX Integer32
                    UNITS "N/A"
                    MAX-ACCESS read-only
                    STATUS current
                    DESCRIPTION "Humidification"
                    ::= { digitalObjects 11 }

        -- 1.3.6.1.4.1.9839.2.1.1.12
        mal-access OBJECT-TYPE
                    SYNTAX Integer32
                    UNITS "N/A"
                    MAX-ACCESS read-only
                    STATUS current
                    DESCRIPTION "Tampering Alarm"
                    ::= { digitalObjects 12 }

        -- 1.3.6.1.4.1.9839.2.1.1.13
        mal-ata OBJECT-TYPE
                    SYNTAX Integer32
                    UNITS "N/A"
                    MAX-ACCESS read-only
                    STATUS current
                    DESCRIPTION "Alarm: Room High Temperature"
                    ::= { digitalObjects 13 }

        -- 1.3.6.1.4.1.9839.2.1.1.14
        mal-bta OBJECT-TYPE
                    SYNTAX Integer32
                    UNITS "N/A"
                    MAX-ACCESS read-only
                    STATUS current
                    DESCRIPTION "Alarm: Room Low Temperature"
                    ::= { digitalObjects 14 }

        -- 1.3.6.1.4.1.9839.2.1.1.15
        mal-aua OBJECT-TYPE
                    SYNTAX Integer32
                    UNITS "N/A"
                    MAX-ACCESS read-only
                    STATUS current
                    DESCRIPTION "Alarm: Room High Humidity"
                    ::= { digitalObjects 15 }

        -- 1.3.6.1.4.1.9839.2.1.1.16
        mal-bua OBJECT-TYPE
                    SYNTAX Integer32
                    UNITS "N/A"
                    MAX-ACCESS read-only
                    STATUS current
                    DESCRIPTION "Alarm: Room Low Humidity"
                    ::= { digitalObjects 16 }

        -- 1.3.6.1.4.1.9839.2.1.1.17
        mal-eap OBJECT-TYPE
                    SYNTAX Integer32
                    UNITS "N/A"
                    MAX-ACCESS read-only
                    STATUS current
                    DESCRIPTION "Alarm: Room High/Low Temp./Humid.(Ext. Devices)"
                    ::= { digitalObjects 17 }

        -- 1.3.6.1.4.1.9839.2.1.1.18
        mal-filter OBJECT-TYPE
                    SYNTAX Integer32
                    UNITS "N/A"
                    MAX-ACCESS read-only
                    STATUS current
                    DESCRIPTION "Alarm: Clogged Filter"
                    ::= { digitalObjects 18 }

        -- 1.3.6.1.4.1.9839.2.1.1.19
        mal-flood OBJECT-TYPE
                    SYNTAX Integer32
                    UNITS "N/A"
                    MAX-ACCESS read-only
                    STATUS current
                    DESCRIPTION "Alarm: Water Leakage Detected"
                    ::= { digitalObjects 19 }

        -- 1.3.6.1.4.1.9839.2.1.1.20
        mal-flux OBJECT-TYPE
                    SYNTAX Integer32
                    UNITS "N/A"
                    MAX-ACCESS read-only
                    STATUS current
                    DESCRIPTION "Alarm: Loss of Air Flow"
                    ::= { digitalObjects 20 }

        -- 1.3.6.1.4.1.9839.2.1.1.21
        mal-heater OBJECT-TYPE
                    SYNTAX Integer32
                    UNITS "N/A"
                    MAX-ACCESS read-only
                    STATUS current
                    DESCRIPTION "Alarm: Heater Overheating"
                    ::= { digitalObjects 21 }

        -- 1.3.6.1.4.1.9839.2.1.1.22
        mal-hp1 OBJECT-TYPE
                    SYNTAX Integer32
                    UNITS "N/A"
                    MAX-ACCESS read-only
                    STATUS current
                    DESCRIPTION "Alarm: High Pressure 1"
                    ::= { digitalObjects 22 }

        -- 1.3.6.1.4.1.9839.2.1.1.23
        mal-hp2 OBJECT-TYPE
                    SYNTAX Integer32
                    UNITS "N/A"
                    MAX-ACCESS read-only
                    STATUS current
                    DESCRIPTION "Alarm: High Pressure 2"
                    ::= { digitalObjects 23 }

        -- 1.3.6.1.4.1.9839.2.1.1.24
        mal-lp1 OBJECT-TYPE
                    SYNTAX Integer32
                    UNITS "N/A"
                    MAX-ACCESS read-only
                    STATUS current
                    DESCRIPTION "Alarm: Low Pressure 1"
                    ::= { digitalObjects 24 }

        -- 1.3.6.1.4.1.9839.2.1.1.25
        mal-lp2 OBJECT-TYPE
                    SYNTAX Integer32
                    UNITS "N/A"
                    MAX-ACCESS read-only
                    STATUS current
                    DESCRIPTION "Alarm: Low Pressure 2"
                    ::= { digitalObjects 25 }

        -- 1.3.6.1.4.1.9839.2.1.1.26
        mal-phase OBJECT-TYPE
                    SYNTAX Integer32
                    UNITS "N/A"
                    MAX-ACCESS read-only
                    STATUS current
                    DESCRIPTION "Alarm: Wrong phase sequence"
                    ::= { digitalObjects 26 }

        -- 1.3.6.1.4.1.9839.2.1.1.27
        mal-smoke OBJECT-TYPE
                    SYNTAX Integer32
                    UNITS "N/A"
                    MAX-ACCESS read-only
                    STATUS current
                    DESCRIPTION "Alarm: SMOKE-FIRE DETECTED"
                    ::= { digitalObjects 27 }

        -- 1.3.6.1.4.1.9839.2.1.1.28
        mal-lan OBJECT-TYPE
                    SYNTAX Integer32
                    UNITS "N/A"
                    MAX-ACCESS read-only
                    STATUS current
                    DESCRIPTION "Alarm: Interrupted LAN"
                    ::= { digitalObjects 28 }

        -- 1.3.6.1.4.1.9839.2.1.1.29
        mal-hcurr OBJECT-TYPE
                    SYNTAX Integer32
                    UNITS "N/A"
                    MAX-ACCESS read-only
                    STATUS current
                    DESCRIPTION "Humidifier Alarm: High Current"
                    ::= { digitalObjects 29 }

        -- 1.3.6.1.4.1.9839.2.1.1.30
        mal-nopower OBJECT-TYPE
                    SYNTAX Integer32
                    UNITS "N/A"
                    MAX-ACCESS read-only
                    STATUS current
                    DESCRIPTION "Humidifier Alarm: Power Loss"
                    ::= { digitalObjects 30 }

        -- 1.3.6.1.4.1.9839.2.1.1.31
        mal-nowater OBJECT-TYPE
                    SYNTAX Integer32
                    UNITS "N/A"
                    MAX-ACCESS read-only
                    STATUS current
                    DESCRIPTION "Humidifier Alarm: Water Loss"
                    ::= { digitalObjects 31 }

        -- 1.3.6.1.4.1.9839.2.1.1.32
        mal-cw-dh OBJECT-TYPE
                    SYNTAX Integer32
                    UNITS "N/A"
                    MAX-ACCESS read-only
                    STATUS current
                    DESCRIPTION "Alarm: Chilled Water Temp. too High for Dehumidification"
                    ::= { digitalObjects 32 }

        -- 1.3.6.1.4.1.9839.2.1.1.33
        mal-tc-cw OBJECT-TYPE
                    SYNTAX Integer32
                    UNITS "N/A"
                    MAX-ACCESS read-only
                    STATUS current
                    DESCRIPTION "Alarm: CW Valve Failure or Water Flow too Low"
                    ::= { digitalObjects 33 }

        -- 1.3.6.1.4.1.9839.2.1.1.34
        mal-wflow OBJECT-TYPE
                    SYNTAX Integer32
                    UNITS "N/A"
                    MAX-ACCESS read-only
                    STATUS current
                    DESCRIPTION "Alarm: Loss of Water flow"
                    ::= { digitalObjects 34 }

        -- 1.3.6.1.4.1.9839.2.1.1.35
        mal-wht OBJECT-TYPE
                    SYNTAX Integer32
                    UNITS "N/A"
                    MAX-ACCESS read-only
                    STATUS current
                    DESCRIPTION "Alarm: High chilled water temp."
                    ::= { digitalObjects 35 }

        -- 1.3.6.1.4.1.9839.2.1.1.36
        mal-sonda-ta OBJECT-TYPE
                    SYNTAX Integer32
                    UNITS "N/A"
                    MAX-ACCESS read-only
                    STATUS current
                    DESCRIPTION "Alarm: Room air Sensor Failure/Disconnected"
                    ::= { digitalObjects 36 }

        -- 1.3.6.1.4.1.9839.2.1.1.37
        mal-sonda-tac OBJECT-TYPE
                    SYNTAX Integer32
                    UNITS "N/A"
                    MAX-ACCESS read-only
                    STATUS current
                    DESCRIPTION "Alarm: Hot water Sensor Failure/Disconnected"
                    ::= { digitalObjects 37 }

        -- 1.3.6.1.4.1.9839.2.1.1.38
        mal-sonda-tc OBJECT-TYPE
                    SYNTAX Integer32
                    UNITS "N/A"
                    MAX-ACCESS read-only
                    STATUS current
                    DESCRIPTION "Alarm: Condensing water Sensor Failure/Disconnect."
                    ::= { digitalObjects 38 }

        -- 1.3.6.1.4.1.9839.2.1.1.39
        mal-sonda-te OBJECT-TYPE
                    SYNTAX Integer32
                    UNITS "N/A"
                    MAX-ACCESS read-only
                    STATUS current
                    DESCRIPTION "Alarm: Outdoor temp. Sensor Failure/Disconnected"
                    ::= { digitalObjects 39 }

        -- 1.3.6.1.4.1.9839.2.1.1.40
        mal-sonda-tm OBJECT-TYPE
                    SYNTAX Integer32
                    UNITS "N/A"
                    MAX-ACCESS read-only
                    STATUS current
                    DESCRIPTION "Alarm: Delivery temp. Sensor Failure/Disconnected"
                    ::= { digitalObjects 40 }

        -- 1.3.6.1.4.1.9839.2.1.1.41
        mal-sonda-ua OBJECT-TYPE
                    SYNTAX Integer32
                    UNITS "N/A"
                    MAX-ACCESS read-only
                    STATUS current
                    DESCRIPTION "Alarm: Rel. Humidity Sensor Failure/Disconnected"
                    ::= { digitalObjects 41 }

        -- 1.3.6.1.4.1.9839.2.1.1.42
        mal-ore-compr1 OBJECT-TYPE
                    SYNTAX Integer32
                    UNITS "N/A"
                    MAX-ACCESS read-only
                    STATUS current
                    DESCRIPTION "Service Alarm: Compressor 1 hour counter threshold"
                    ::= { digitalObjects 42 }

        -- 1.3.6.1.4.1.9839.2.1.1.43
        mal-ore-compr2 OBJECT-TYPE
                    SYNTAX Integer32
                    UNITS "N/A"
                    MAX-ACCESS read-only
                    STATUS current
                    DESCRIPTION "Service Alarm: Compressor 2 hour counter threshold"
                    ::= { digitalObjects 43 }

        -- 1.3.6.1.4.1.9839.2.1.1.44
        mal-ore-compr3 OBJECT-TYPE
                    SYNTAX Integer32
                    UNITS "N/A"
                    MAX-ACCESS read-only
                    STATUS current
                    DESCRIPTION "Service Alarm: Compressor 3 hour counter threshold"
                    ::= { digitalObjects 44 }

        -- 1.3.6.1.4.1.9839.2.1.1.45
        mal-ore-compr4 OBJECT-TYPE
                    SYNTAX Integer32
                    UNITS "N/A"
                    MAX-ACCESS read-only
                    STATUS current
                    DESCRIPTION "Service Alarm: Compressor 4 hour counter threshold"
                    ::= { digitalObjects 45 }

        -- 1.3.6.1.4.1.9839.2.1.1.46
        mal-ore-filtro OBJECT-TYPE
                    SYNTAX Integer32
                    UNITS "N/A"
                    MAX-ACCESS read-only
                    STATUS current
                    DESCRIPTION "Service Alarm: Air Filter hour counter threshold"
                    ::= { digitalObjects 46 }

        -- 1.3.6.1.4.1.9839.2.1.1.47
        mal-ore-risc1 OBJECT-TYPE
                    SYNTAX Integer32
                    UNITS "N/A"
                    MAX-ACCESS read-only
                    STATUS current
                    DESCRIPTION "Service Alarm: Heater 1 hour counter threshold"
                    ::= { digitalObjects 47 }

        -- 1.3.6.1.4.1.9839.2.1.1.48
        mal-ore-risc2 OBJECT-TYPE
                    SYNTAX Integer32
                    UNITS "N/A"
                    MAX-ACCESS read-only
                    STATUS current
                    DESCRIPTION "Service Alarm: Heater 2 hour counter threshold"
                    ::= { digitalObjects 48 }

        -- 1.3.6.1.4.1.9839.2.1.1.49
        mal-ore-umid OBJECT-TYPE
                    SYNTAX Integer32
                    UNITS "N/A"
                    MAX-ACCESS read-only
                    STATUS current
                    DESCRIPTION "Service Alarm: Humidifier hour counter threshold"
                    ::= { digitalObjects 49 }

        -- 1.3.6.1.4.1.9839.2.1.1.50
        mal-ore-unit OBJECT-TYPE
                    SYNTAX Integer32
                    UNITS "N/A"
                    MAX-ACCESS read-only
                    STATUS current
                    DESCRIPTION "Service Alarm: Unit hour counter threshold"
                    ::= { digitalObjects 50 }

        -- 1.3.6.1.4.1.9839.2.1.1.51
        glb-al OBJECT-TYPE
                    SYNTAX Integer32
                    UNITS "N/A"
                    MAX-ACCESS read-only
                    STATUS current
                    DESCRIPTION "General Alarm"
                    ::= { digitalObjects 51 }

        -- 1.3.6.1.4.1.9839.2.1.1.52
        or-al-2lev OBJECT-TYPE
                    SYNTAX Integer32
                    UNITS "N/A"
                    MAX-ACCESS read-only
                    STATUS current
                    DESCRIPTION "2nd Level Alarm"
                    ::= { digitalObjects 52 }

        -- 1.3.6.1.4.1.9839.2.1.1.53
        range-t-ext OBJECT-TYPE
                    SYNTAX Integer32
                    UNITS "N/A"
                    MAX-ACCESS read-only
                    STATUS current
                    DESCRIPTION "Outdoor Temp. Sensor Fitted"
                    ::= { digitalObjects 53 }

        -- 1.3.6.1.4.1.9839.2.1.1.54
        range-t-circ OBJECT-TYPE
                    SYNTAX Integer32
                    UNITS "N/A"
                    MAX-ACCESS read-only
                    STATUS current
                    DESCRIPTION "Closed Circuit (or Chilled) Water Temperature Sensor Fitted"
                    ::= { digitalObjects 54 }

        -- 1.3.6.1.4.1.9839.2.1.1.55
        range-t-man OBJECT-TYPE
                    SYNTAX Integer32
                    UNITS "N/A"
                    MAX-ACCESS read-only
                    STATUS current
                    DESCRIPTION "Delivery Temp. Sensor Fitted"
                    ::= { digitalObjects 55 }

        -- 1.3.6.1.4.1.9839.2.1.1.56
        range-t-ac OBJECT-TYPE
                    SYNTAX Integer32
                    UNITS "N/A"
                    MAX-ACCESS read-only
                    STATUS current
                    DESCRIPTION "Hot water temp. Sensor Fitted"
                    ::= { digitalObjects 56 }

        -- 1.3.6.1.4.1.9839.2.1.1.57
        umid-al OBJECT-TYPE
                    SYNTAX Integer32
                    UNITS "N/A"
                    MAX-ACCESS read-only
                    STATUS current
                    DESCRIPTION "Humidifier general alarm"
                    ::= { digitalObjects 57 }

        -- 1.3.6.1.4.1.9839.2.1.1.58
        range-u-amb OBJECT-TYPE
                    SYNTAX Integer32
                    UNITS "N/A"
                    MAX-ACCESS read-only
                    STATUS current
                    DESCRIPTION "Relative Humidity Sensor Fitted"
                    ::= { digitalObjects 58 }

        -- 1.3.6.1.4.1.9839.2.1.1.60
        k-syson OBJECT-TYPE
                    SYNTAX Integer32 (0..1)
                    UNITS "N/A"
                    MAX-ACCESS read-write
                    STATUS current
                    DESCRIPTION "Unit Remote Switch-On/Off Control"
                    ::= { digitalObjects 60 }

        -- 1.3.6.1.4.1.9839.2.1.1.61
        xs-res-al OBJECT-TYPE
                    SYNTAX Integer32 (0..1)
                    UNITS "N/A"
                    MAX-ACCESS read-write
                    STATUS current
                    DESCRIPTION "Buzzer and Alarm Remote Reset Control"
                    ::= { digitalObjects 61 }

        -- 1.3.6.1.4.1.9839.2.1.1.63
        sleep-mode OBJECT-TYPE
                    SYNTAX Integer32 (0..1)
                    UNITS "N/A"
                    MAX-ACCESS read-write
                    STATUS current
                    DESCRIPTION "Set Back Mode (Sleep Mode)"
                    ::= { digitalObjects 63 }

        -- 1.3.6.1.4.1.9839.2.1.1.64
        test-sm OBJECT-TYPE
                    SYNTAX Integer32 (0..1)
                    UNITS "N/A"
                    MAX-ACCESS read-write
                    STATUS current
                    DESCRIPTION "Set Back mode: Cyclical Start of Fan"
                    ::= { digitalObjects 64 }

        -- 1.3.6.1.4.1.9839.2.1.1.65
        ab-mediath OBJECT-TYPE
                    SYNTAX Integer32 (0..1)
                    UNITS "N/A"
                    MAX-ACCESS read-write
                    STATUS current
                    DESCRIPTION "Usage of T+ H Values: Local (0) / Mean (1)"
                    ::= { digitalObjects 65 }

        -- 1.3.6.1.4.1.9839.2.1.1.66
        ustdby1-2 OBJECT-TYPE
                    SYNTAX Integer32 (0..1)
                    UNITS "N/A"
                    MAX-ACCESS read-write
                    STATUS current
                    DESCRIPTION "No. Of Stand-by Units: one (0) / two (1)"
                    ::= { digitalObjects 66 }

        -- 1.3.6.1.4.1.9839.2.1.1.67
        emerg OBJECT-TYPE
                    SYNTAX Integer32
                    UNITS "N/A"
                    MAX-ACCESS read-only
                    STATUS current
                    DESCRIPTION "Unit in Emergency operation"
                    ::= { digitalObjects 67 }


        -- 1.3.6.1.4.1.9839.2.1.2
        analogObjects OBJECT IDENTIFIER ::= { uncdz-MIB 2 }

        -- 1.3.6.1.4.1.9839.2.1.2.1
        temp-amb OBJECT-TYPE
                    SYNTAX Integer32
                    UNITS "N/A"
                    MAX-ACCESS read-only
                    STATUS current
                    DESCRIPTION "Room Temperature"
                    ::= { analogObjects 1 }

        -- 1.3.6.1.4.1.9839.2.1.2.2
        temp-ext OBJECT-TYPE
                    SYNTAX Integer32
                    UNITS "deg.C x 10"
                    MAX-ACCESS read-only
                    STATUS current
                    DESCRIPTION "Outdoor Temperature"
                    ::= { analogObjects 2 }

        -- 1.3.6.1.4.1.9839.2.1.2.3
        temp-mand OBJECT-TYPE
                    SYNTAX Integer32
                    UNITS "deg.C x 10"
                    MAX-ACCESS read-only
                    STATUS current
                    DESCRIPTION "Delivery Air Temperature"
                    ::= { analogObjects 3 }

        -- 1.3.6.1.4.1.9839.2.1.2.4
        temp-circ OBJECT-TYPE
                    SYNTAX Integer32
                    UNITS "deg.C x 10"
                    MAX-ACCESS read-only
                    STATUS current
                    DESCRIPTION "Closed Circuit (or Chilled) Water Temperature"
                    ::= { analogObjects 4 }

        -- 1.3.6.1.4.1.9839.2.1.2.5
        temp-ac OBJECT-TYPE
                    SYNTAX Integer32
                    UNITS "deg.C x 10"
                    MAX-ACCESS read-only
                    STATUS current
                    DESCRIPTION "Hot Water Temperature"
                    ::= { analogObjects 5 }

        -- 1.3.6.1.4.1.9839.2.1.2.6
        umid-amb OBJECT-TYPE
                    SYNTAX Integer32
                    UNITS "rH% x 10"
                    MAX-ACCESS read-only
                    STATUS current
                    DESCRIPTION "Room Relative Humidity"
                    ::= { analogObjects 6 }

        -- 1.3.6.1.4.1.9839.2.1.2.7
        t-set OBJECT-TYPE
                    SYNTAX Integer32 (-32767..32767)
                    UNITS "deg.C x 10"
                    MAX-ACCESS read-write
                    STATUS current
                    DESCRIPTION "Cooling Set Point"
                    ::= { analogObjects 7 }

        -- 1.3.6.1.4.1.9839.2.1.2.8
        t-diff OBJECT-TYPE
                    SYNTAX Integer32 (-32767..32767)
                    UNITS "deg.C x 10"
                    MAX-ACCESS read-write
                    STATUS current
                    DESCRIPTION "Cooling Prop.Band"
                    ::= { analogObjects 8 }

        -- 1.3.6.1.4.1.9839.2.1.2.9
        t-set-c OBJECT-TYPE
                    SYNTAX Integer32 (-32767..32767)
                    UNITS "deg.C x 10"
                    MAX-ACCESS read-write
                    STATUS current
                    DESCRIPTION "Heating Set point"
                    ::= { analogObjects 9 }

        -- 1.3.6.1.4.1.9839.2.1.2.10
        t-diff-c OBJECT-TYPE
                    SYNTAX Integer32 (-32767..32767)
                    UNITS "deg.C x 10"
                    MAX-ACCESS read-write
                    STATUS current
                    DESCRIPTION "Heating Prop.Band"
                    ::= { analogObjects 10 }

        -- 1.3.6.1.4.1.9839.2.1.2.11
        ht-set OBJECT-TYPE
                    SYNTAX Integer32 (-32767..32767)
                    UNITS "deg.C"
                    MAX-ACCESS read-write
                    STATUS current
                    DESCRIPTION "Room High Temp. Alarm Threshold"
                    ::= { analogObjects 11 }

        -- 1.3.6.1.4.1.9839.2.1.2.12
        lt-set OBJECT-TYPE
                    SYNTAX Integer32 (-32767..32767)
                    UNITS "deg.C"
                    MAX-ACCESS read-write
                    STATUS current
                    DESCRIPTION "Room Low Temp. Alarm Threshold"
                    ::= { analogObjects 12 }

        -- 1.3.6.1.4.1.9839.2.1.2.13
        t-set-sm OBJECT-TYPE
                    SYNTAX Integer32 (-32767..32767)
                    UNITS "N/A"
                    MAX-ACCESS read-write
                    STATUS current
                    DESCRIPTION "Setback Mode: Cooling Set Point"
                    ::= { analogObjects 13 }

        -- 1.3.6.1.4.1.9839.2.1.2.14
        t-set-c-sm OBJECT-TYPE
                    SYNTAX Integer32 (-32767..32767)
                    UNITS "N/A"
                    MAX-ACCESS read-write
                    STATUS current
                    DESCRIPTION "Setback Mode: Heating Set Point"
                    ::= { analogObjects 14 }

        -- 1.3.6.1.4.1.9839.2.1.2.15
        t-cw-dh OBJECT-TYPE
                    SYNTAX Integer32 (-32767..32767)
                    UNITS "N/A"
                    MAX-ACCESS read-write
                    STATUS current
                    DESCRIPTION "CW Set Point to Start Dehumidification Cycle"
                    ::= { analogObjects 15 }

        -- 1.3.6.1.4.1.9839.2.1.2.16
        htset-cw OBJECT-TYPE
                    SYNTAX Integer32 (-32767..32767)
                    UNITS "N/A"
                    MAX-ACCESS read-write
                    STATUS current
                    DESCRIPTION "CW High Temperature Alarm Threshold"
                    ::= { analogObjects 16 }

        -- 1.3.6.1.4.1.9839.2.1.2.17
        t-set-cw OBJECT-TYPE
                    SYNTAX Integer32 (-32767..32767)
                    UNITS "N/A"
                    MAX-ACCESS read-write
                    STATUS current
                    DESCRIPTION "CW Set Point to Start CW Operating Mode (TC only)"
                    ::= { analogObjects 17 }

        -- 1.3.6.1.4.1.9839.2.1.2.18
        t-rc-es OBJECT-TYPE
                    SYNTAX Integer32 (-32767..32767)
                    UNITS "N/A"
                    MAX-ACCESS read-write
                    STATUS current
                    DESCRIPTION "Rad-cooler Set Point  in E.S.  Mode (ES Only)"
                    ::= { analogObjects 18 }

        -- 1.3.6.1.4.1.9839.2.1.2.19
        t-rc-est OBJECT-TYPE
                    SYNTAX Integer32 (-32767..32767)
                    UNITS "N/A"
                    MAX-ACCESS read-write
                    STATUS current
                    DESCRIPTION "Rad-cooler Set Point  in DX  Mode (ES Only)"
                    ::= { analogObjects 19 }

        -- 1.3.6.1.4.1.9839.2.1.2.20
        rampa-valv OBJECT-TYPE
                    SYNTAX Integer32
                    UNITS "N/A"
                    MAX-ACCESS read-only
                    STATUS current
                    DESCRIPTION "0-10V Ramp 1 Value (CW Valve Ramp)"
                    ::= { analogObjects 20 }

        -- 1.3.6.1.4.1.9839.2.1.2.21
        anaout2 OBJECT-TYPE
                    SYNTAX Integer32
                    UNITS "N/A"
                    MAX-ACCESS read-only
                    STATUS current
                    DESCRIPTION "0-10V Ramp 2 Value (HW Valve/Rad Cooler Ramp)"
                    ::= { analogObjects 21 }

        -- 1.3.6.1.4.1.9839.2.1.2.22
        steam-production OBJECT-TYPE
                    SYNTAX Integer32
                    UNITS "kg/h x 10"
                    MAX-ACCESS read-only
                    STATUS current
                    DESCRIPTION "Humidifier: steam capacity"
                    ::= { analogObjects 22 }

        -- 1.3.6.1.4.1.9839.2.1.2.23
        t-set-lm OBJECT-TYPE
                    SYNTAX Integer32 (-32767..32767)
                    UNITS "deg.C"
                    MAX-ACCESS read-write
                    STATUS current
                    DESCRIPTION "Delivery Air Temperature Limit Set Point "
                    ::= { analogObjects 23 }

        -- 1.3.6.1.4.1.9839.2.1.2.24
        delta-lm OBJECT-TYPE
                    SYNTAX Integer32 (-32767..32767)
                    UNITS "deg.C x 10"
                    MAX-ACCESS read-write
                    STATUS current
                    DESCRIPTION "T+H Values: Mean/Local Diff. (aut. Changeover)"
                    ::= { analogObjects 24 }




        -- 1.3.6.1.4.1.9839.2.1.3
        integerObjects OBJECT IDENTIFIER ::= { uncdz-MIB 3 }

        -- 1.3.6.1.4.1.9839.2.1.3.1
        ore-filtro OBJECT-TYPE
                    SYNTAX Integer32
                    UNITS "h"
                    MAX-ACCESS read-only
                    STATUS current
                    DESCRIPTION "Air Filter Working Houres"
                    ::= { integerObjects 1 }

        -- 1.3.6.1.4.1.9839.2.1.3.2
        ore-unit OBJECT-TYPE
                    SYNTAX Integer32
                    UNITS "h"
                    MAX-ACCESS read-only
                    STATUS current
                    DESCRIPTION "Unit Working Houres"
                    ::= { integerObjects 2 }

        -- 1.3.6.1.4.1.9839.2.1.3.3
        ore-compr1 OBJECT-TYPE
                    SYNTAX Integer32
                    UNITS "h"
                    MAX-ACCESS read-only
                    STATUS current
                    DESCRIPTION "Compressor 1 Working Houres"
                    ::= { integerObjects 3 }

        -- 1.3.6.1.4.1.9839.2.1.3.4
        ore-compr2 OBJECT-TYPE
                    SYNTAX Integer32
                    UNITS "h"
                    MAX-ACCESS read-only
                    STATUS current
                    DESCRIPTION "Compressor 2 Working Houres"
                    ::= { integerObjects 4 }

        -- 1.3.6.1.4.1.9839.2.1.3.5
        ore-compr3 OBJECT-TYPE
                    SYNTAX Integer32
                    UNITS "h"
                    MAX-ACCESS read-only
                    STATUS current
                    DESCRIPTION "Compressor 3 Working Houres"
                    ::= { integerObjects 5 }

        -- 1.3.6.1.4.1.9839.2.1.3.6
        ore-compr4 OBJECT-TYPE
                    SYNTAX Integer32
                    UNITS "h"
                    MAX-ACCESS read-only
                    STATUS current
                    DESCRIPTION "Compressor 4 Working Houres"
                    ::= { integerObjects 6 }

        -- 1.3.6.1.4.1.9839.2.1.3.7
        ore-heat1 OBJECT-TYPE
                    SYNTAX Integer32
                    UNITS "h"
                    MAX-ACCESS read-only
                    STATUS current
                    DESCRIPTION "Heater 1 Working Houres"
                    ::= { integerObjects 7 }

        -- 1.3.6.1.4.1.9839.2.1.3.8
        ore-heat2 OBJECT-TYPE
                    SYNTAX Integer32
                    UNITS "h"
                    MAX-ACCESS read-only
                    STATUS current
                    DESCRIPTION "Heater 2 Working Houres"
                    ::= { integerObjects 8 }

        -- 1.3.6.1.4.1.9839.2.1.3.9
        ore-umid OBJECT-TYPE
                    SYNTAX Integer32
                    UNITS "h"
                    MAX-ACCESS read-only
                    STATUS current
                    DESCRIPTION "Humidifier Working Houres"
                    ::= { integerObjects 9 }

        -- 1.3.6.1.4.1.9839.2.1.3.12
        hdiff OBJECT-TYPE
                    SYNTAX Integer32 (-32767..32767)
                    UNITS "rH%"
                    MAX-ACCESS read-write
                    STATUS current
                    DESCRIPTION "Dehumidification Proportional Band"
                    ::= { integerObjects 12 }

        -- 1.3.6.1.4.1.9839.2.1.3.13
        hu-diff OBJECT-TYPE
                    SYNTAX Integer32 (-32767..32767)
                    UNITS "rH%"
                    MAX-ACCESS read-write
                    STATUS current
                    DESCRIPTION "Humidification Proportional Band"
                    ::= { integerObjects 13 }

        -- 1.3.6.1.4.1.9839.2.1.3.14
        hh-set OBJECT-TYPE
                    SYNTAX Integer32 (-32767..32767)
                    UNITS "rH%"
                    MAX-ACCESS read-write
                    STATUS current
                    DESCRIPTION "High Relative Humidity Alarm Threshold"
                    ::= { integerObjects 14 }

        -- 1.3.6.1.4.1.9839.2.1.3.15
        lh-set OBJECT-TYPE
                    SYNTAX Integer32 (-32767..32767)
                    UNITS "rH%"
                    MAX-ACCESS read-write
                    STATUS current
                    DESCRIPTION "Low Relative Humidity Alarm Threshold"
                    ::= { integerObjects 15 }

        -- 1.3.6.1.4.1.9839.2.1.3.16
        hset OBJECT-TYPE
                    SYNTAX Integer32 (-32767..32767)
                    UNITS "rH%"
                    MAX-ACCESS read-write
                    STATUS current
                    DESCRIPTION "Dehumidification Set Point"
                    ::= { integerObjects 16 }

        -- 1.3.6.1.4.1.9839.2.1.3.17
        hset-sm OBJECT-TYPE
                    SYNTAX Integer32 (-32767..32767)
                    UNITS "rH%"
                    MAX-ACCESS read-write
                    STATUS current
                    DESCRIPTION "Setback Mode: Dehumidification Set Point"
                    ::= { integerObjects 17 }

        -- 1.3.6.1.4.1.9839.2.1.3.18
        hu-set OBJECT-TYPE
                    SYNTAX Integer32 (-32767..32767)
                    UNITS "rH%"
                    MAX-ACCESS read-write
                    STATUS current
                    DESCRIPTION "Humidification Set Point"
                    ::= { integerObjects 18 }

        -- 1.3.6.1.4.1.9839.2.1.3.19
        hu-set-sm OBJECT-TYPE
                    SYNTAX Integer32 (-32767..32767)
                    UNITS "rH%"
                    MAX-ACCESS read-write
                    STATUS current
                    DESCRIPTION "Setback Mode: Humidification Set Point"
                    ::= { integerObjects 19 }

        -- 1.3.6.1.4.1.9839.2.1.3.20
        restart-delay OBJECT-TYPE
                    SYNTAX Integer32 (-32767..32767)
                    UNITS "sec"
                    MAX-ACCESS read-write
                    STATUS current
                    DESCRIPTION "Restart Delay"
                    ::= { integerObjects 20 }

        -- 1.3.6.1.4.1.9839.2.1.3.21
        regul-delay OBJECT-TYPE
                    SYNTAX Integer32 (-32767..32767)
                    UNITS "sec"
                    MAX-ACCESS read-write
                    STATUS current
                    DESCRIPTION "Regulation Start Transitory "
                    ::= { integerObjects 21 }

        -- 1.3.6.1.4.1.9839.2.1.3.22
        time-lowp OBJECT-TYPE
                    SYNTAX Integer32 (-32767..32767)
                    UNITS "sec"
                    MAX-ACCESS read-write
                    STATUS current
                    DESCRIPTION "Low Pressure Delay"
                    ::= { integerObjects 22 }

        -- 1.3.6.1.4.1.9839.2.1.3.23
        alarm-delay OBJECT-TYPE
                    SYNTAX Integer32 (-32767..32767)
                    UNITS "m"
                    MAX-ACCESS read-write
                    STATUS current
                    DESCRIPTION "Room T+H Alarm Delay"
                    ::= { integerObjects 23 }

        -- 1.3.6.1.4.1.9839.2.1.3.24
        exc-time OBJECT-TYPE
                    SYNTAX Integer32 (-32767..32767)
                    UNITS "m"
                    MAX-ACCESS read-write
                    STATUS current
                    DESCRIPTION "Anti-Hunting Constant of Room Regulation "
                    ::= { integerObjects 24 }

        -- 1.3.6.1.4.1.9839.2.1.3.25
        t-std-by OBJECT-TYPE
                    SYNTAX Integer32 (-32767..32767)
                    UNITS "h"
                    MAX-ACCESS read-write
                    STATUS current
                    DESCRIPTION "Stand-by Cycle Base Time"
                    ::= { integerObjects 25 }

        -- 1.3.6.1.4.1.9839.2.1.3.27
        lan-unit OBJECT-TYPE
                    SYNTAX Integer32 (-32767..32767)
                    UNITS "n"
                    MAX-ACCESS read-write
                    STATUS current
                    DESCRIPTION "Total of units connected in LAN"
                    ::= { integerObjects 27 }

        -- 1.3.6.1.4.1.9839.2.1.3.28
        ciclo-sm OBJECT-TYPE
                    SYNTAX Integer32 (-32767..32767)
                    UNITS "m"
                    MAX-ACCESS read-write
                    STATUS current
                    DESCRIPTION "Set Back Mode: Fan Cyclical Start Interval"
                    ::= { integerObjects 28 }





	END

--
-- UNCDZ.MIB
--
