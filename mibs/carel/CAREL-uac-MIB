--
-- CAREL-uac.MIB
-- MIB generated by CAREL
-- Friday, 14 March 2003
--

    CAREL-uac-MIB DEFINITIONS ::= BEGIN

		IMPORTS
			OBJECT-GROUP
				FROM SNMPv2-CONF
			sysContact, sysName, sysLocation
				FROM SNMPv2-MIB
			enterprises, MODULE-IDENTITY
				FROM SNMPv2-SMI;

        uacMIB MODULE-IDENTITY
      		LAST-UPDATED  "200303141725Z"		-- March 14, 2003 at 17:25 GMT
      		ORGANIZATION  "CAREL SpA"
      		CONTACT-INFO
                "
                        Simone Ravazzolo
                        Carel SpA
                        Via dell'Industria, 11
                        35020 Brugine (PD) Italy
                        Tel: +39 049 9716611
                        E-mail: simone.ravazzolo@carel.com
                "
      		DESCRIPTION
                "This is the MIB module for the uac device."
			::= { instruments 1 }


--
-- Node definitions
--

		-- 1.3.6.1.4.1.9839
		carel OBJECT IDENTIFIER ::= { enterprises 9839 }

		-- 1.3.6.1.4.1.9839.1
		systm OBJECT IDENTIFIER ::= { carel 1 }

		-- 1.3.6.1.4.1.9839.1.1
		agentRelease OBJECT-TYPE
			SYNTAX Integer32
			UNITS "N/A"
			MAX-ACCESS read-only
			STATUS current
			DESCRIPTION "Release of the Agent."
		::= { systm 1 }

		-- 1.3.6.1.4.1.9839.1.2
		agentCode OBJECT-TYPE
			SYNTAX Integer32
			UNITS "N/A"
			MAX-ACCESS read-only
			STATUS current
			DESCRIPTION "Code of the Agent. 1=WebGate"
		::= { systm 2 }

		-- 1.3.6.1.4.1.9839.2
		instruments OBJECT IDENTIFIER ::= { carel 2 }

		-- 1.3.6.1.4.1.9839.2.0
		webGateInfo OBJECT IDENTIFIER ::= { instruments 0 }

		-- 1.3.6.1.4.1.9839.2.0.1
		agentParameters OBJECT IDENTIFIER ::= { webGateInfo 1 }

		-- 1.3.6.1.4.1.9839.2.0.1.1
		netSize OBJECT-TYPE
			SYNTAX Integer32 (1..16)
			UNITS "N/A"
			MAX-ACCESS read-write
			STATUS current
			DESCRIPTION "Network size. It corresponds to the number of units connected to the WebGate. "
		::= { agentParameters 1 }

		-- 1.3.6.1.4.1.9839.2.0.1.2
		baudRate OBJECT-TYPE
			SYNTAX Integer32 (1200 | 2400 |4800 |9600 | 19200)
			UNITS "N/A"
			MAX-ACCESS read-write
			STATUS current
			DESCRIPTION "Baudrate of the Carel network. "
		::= { agentParameters 2 }

		-- 1.3.6.1.4.1.9839.2.0.2
		unitTypeGroup OBJECT IDENTIFIER ::= { webGateInfo 2 }

		-- 1.3.6.1.4.1.9839.2.0.2.1
		unit1-Type OBJECT-TYPE
			SYNTAX DisplayString
			UNITS "N/A"
			MAX-ACCESS read-only
			STATUS current
			DESCRIPTION "Type of the unit having serial address 1. "
			::= { unitTypeGroup 1 }

		-- ... You will have how many unitX-Type objects as the value of netSize is

		-- 1.3.6.1.4.1.9839.2.0.3
		unitCodeGroup OBJECT IDENTIFIER ::= { webGateInfo 3 }

		-- 1.3.6.1.4.1.9839.2.0.3.1
		unit1-Code OBJECT-TYPE
			SYNTAX Integer32
			UNITS "N/A"
			MAX-ACCESS read-only
			STATUS current
			DESCRIPTION "Code of the unit having serial address 1. "
			::= { unitCodeGroup 1 }

		-- ... You will have how many unitX-Code objects as the value of netSize is

		-- 1.3.6.1.4.1.9839.2.0.4
		unitSoftwareReleaseGroup OBJECT IDENTIFIER ::= { webGateInfo 4 }

		-- 1.3.6.1.4.1.9839.2.0.3.1
		unit1-SoftwareRelease OBJECT-TYPE
			SYNTAX Integer32
			UNITS "N/A"
			MAX-ACCESS read-only
			STATUS current
			DESCRIPTION "Software release of the unit having serial address 1. "
			::= { unitSoftwareReleaseGroup 1 }

		-- ... You will have how many unitX-SoftwareRelease objects as the value of netSize is

		-- 1.3.6.1.4.1.9839.2.0.5
		unitMinSoftwareReleaseGroup OBJECT IDENTIFIER ::= { webGateInfo 5 }

		-- 1.3.6.1.4.1.9839.2.0.5.1
		unit1-MinSoftwareRelease OBJECT-TYPE
			SYNTAX Integer32
			UNITS "N/A"
			MAX-ACCESS read-only
			STATUS current
			DESCRIPTION "Minimum software release of the unit having serial address 1. "
			::= { unitMinSoftwareReleaseGroup 1 }

		-- ... You will have how many unitX-MinSoftwareRelease objects as the value of netSize is

		-- 1.3.6.1.4.1.9839.2.0.6
		unitMaxSoftwareReleaseGroup OBJECT IDENTIFIER ::= { webGateInfo 6 }

		-- 1.3.6.1.4.1.9839.2.0.6.1
		unit1-MaxSoftwareRelease OBJECT-TYPE
			SYNTAX Integer32
			UNITS "N/A"
			MAX-ACCESS read-only
			STATUS current
			DESCRIPTION "Maximum software release of the unit having serial address 1. "
			::= { unitMaxSoftwareReleaseGroup 1 }

		-- ... You will have how many unitX-MaxSoftwareRelease objects as the value of netSize is

		-- 1.3.6.1.4.1.9839.2.0.7
		unitNoAnswerCounterGroup OBJECT IDENTIFIER ::= { webGateInfo 7 }

		-- 1.3.6.1.4.1.9839.2.0.7.1
		unit1-NoAnswerCounter OBJECT-TYPE
			SYNTAX Integer32
			UNITS "N/A"
			MAX-ACCESS read-only
			STATUS current
			DESCRIPTION "No answer counter of the unit having serial address 1. "
			::= { unitNoAnswerCounterGroup 1 }

		-- ... You will have how many unitX-NoAnswerCounter objects as the value of netSize is

		-- 1.3.6.1.4.1.9839.2.0.8
		unitErrorChecksumCounterGroup OBJECT IDENTIFIER ::= { webGateInfo 8 }

		-- 1.3.6.1.4.1.9839.2.0.8.1
		unit1-ErrorChecksumCounter OBJECT-TYPE
			SYNTAX Integer32
			UNITS "N/A"
			MAX-ACCESS read-only
			STATUS current
			DESCRIPTION "Error checksum counter of the unit having serial address 1. "
			::= { unitErrorChecksumCounterGroup 1 }

		-- ... You will have how many unitX-ErrorChecksumCounter objects as the value of netSize is

		-- 1.3.6.1.4.1.9839.2.0.9
		unitTimeoutCounterGroup OBJECT IDENTIFIER ::= { webGateInfo 9 }

		-- 1.3.6.1.4.1.9839.2.0.9.1
		unit1-TimeoutCounter OBJECT-TYPE
			SYNTAX Integer32
			UNITS "N/A"
			MAX-ACCESS read-only
			STATUS current
			DESCRIPTION "Timeout counter of the unit having serial address 1. "
			::= { unitTimeoutCounterGroup 1 }

		-- ... You will have how many unitX-TimeoutCounter objects as the value of netSize is

		-- 1.3.6.1.4.1.9839.2.0.10
		unitOnLineStatusGroup OBJECT IDENTIFIER ::= { webGateInfo 10 }

		-- 1.3.6.1.4.1.9839.2.0.10.1
		unit1-OnLineStatus OBJECT-TYPE
			SYNTAX Integer32
			UNITS "N/A"
			MAX-ACCESS read-only
			STATUS current
			DESCRIPTION "On line status of the unit having serial address 1. "
			::= { unitOnLineStatusGroup 1 }

		-- ... You will have how many unitX-OnLineStatus objects as the value of netSize is

		-- 1.3.6.1.4.1.9839.2.1
        uacMIB OBJECT IDENTIFIER ::= { instruments 1 }

        -- 1.3.6.1.4.1.9839.2.1.1
        digitalObjects OBJECT IDENTIFIER ::= { uacMIB 1 }

        -- 1.3.6.1.4.1.9839.2.1.1.3
        al_eeprom OBJECT-TYPE
                    SYNTAX Integer32 (0..1)
                    UNITS "N/A"
                    MAX-ACCESS read-only
                    STATUS current
                    DESCRIPTION "eeprom error"
                    ::= { digitalObjects 3 }

        -- 1.3.6.1.4.1.9839.2.1.1.4
        al_b1_ko OBJECT-TYPE
                    SYNTAX Integer32 (0..1)
                    UNITS "N/A"
                    MAX-ACCESS read-only
                    STATUS current
                    DESCRIPTION "Control sensor faulty or not connected"
                    ::= { digitalObjects 4 }

        -- 1.3.6.1.4.1.9839.2.1.1.5
        al_b2_ko OBJECT-TYPE
                    SYNTAX Integer32 (0..1)
                    UNITS "N/A"
                    MAX-ACCESS read-only
                    STATUS current
                    DESCRIPTION "Evaporator sensor faulty or not connected"
                    ::= { digitalObjects 5 }

        -- 1.3.6.1.4.1.9839.2.1.1.6
        al_b3_ko OBJECT-TYPE
                    SYNTAX Integer32 (0..1)
                    UNITS "N/A"
                    MAX-ACCESS read-only
                    STATUS current
                    DESCRIPTION "Humidity probe faulty or not connected"
                    ::= { digitalObjects 6 }

        -- 1.3.6.1.4.1.9839.2.1.1.7
        al_b4_ko OBJECT-TYPE
                    SYNTAX Integer32 (0..1)
                    UNITS "N/A"
                    MAX-ACCESS read-only
                    STATUS current
                    DESCRIPTION "Supply sensor faulty or not connected"
                    ::= { digitalObjects 7 }

        -- 1.3.6.1.4.1.9839.2.1.1.8
        al_clock OBJECT-TYPE
                    SYNTAX Integer32 (0..1)
                    UNITS "N/A"
                    MAX-ACCESS read-only
                    STATUS current
                    DESCRIPTION "clock board faulty or not connected"
                    ::= { digitalObjects 8 }

        -- 1.3.6.1.4.1.9839.2.1.1.9
        al_hp_ckt1 OBJECT-TYPE
                    SYNTAX Integer32 (0..1)
                    UNITS "N/A"
                    MAX-ACCESS read-only
                    STATUS current
                    DESCRIPTION "high pressure on circuit 1"
                    ::= { digitalObjects 9 }

        -- 1.3.6.1.4.1.9839.2.1.1.10
        al_hp_ckt2 OBJECT-TYPE
                    SYNTAX Integer32 (0..1)
                    UNITS "N/A"
                    MAX-ACCESS read-only
                    STATUS current
                    DESCRIPTION "high pressure on circuit 2"
                    ::= { digitalObjects 10 }

        -- 1.3.6.1.4.1.9839.2.1.1.11
        al_lp_ckt1 OBJECT-TYPE
                    SYNTAX Integer32 (0..1)
                    UNITS "N/A"
                    MAX-ACCESS read-only
                    STATUS current
                    DESCRIPTION "low pressure on circuit 1"
                    ::= { digitalObjects 11 }

        -- 1.3.6.1.4.1.9839.2.1.1.12
        al_lp_ckt2 OBJECT-TYPE
                    SYNTAX Integer32 (0..1)
                    UNITS "N/A"
                    MAX-ACCESS read-only
                    STATUS current
                    DESCRIPTION "low pressure on circuit 2"
                    ::= { digitalObjects 12 }

        -- 1.3.6.1.4.1.9839.2.1.1.13
        al_flow_sw OBJECT-TYPE
                    SYNTAX Integer32 (0..1)
                    UNITS "N/A"
                    MAX-ACCESS read-only
                    STATUS current
                    DESCRIPTION "Air flow alarm"
                    ::= { digitalObjects 13 }

        -- 1.3.6.1.4.1.9839.2.1.1.14
        al_clogged_fl OBJECT-TYPE
                    SYNTAX Integer32 (0..1)
                    UNITS "N/A"
                    MAX-ACCESS read-only
                    STATUS current
                    DESCRIPTION "clogged filter"
                    ::= { digitalObjects 14 }

        -- 1.3.6.1.4.1.9839.2.1.1.15
        al_heaters_ol OBJECT-TYPE
                    SYNTAX Integer32 (0..1)
                    UNITS "N/A"
                    MAX-ACCESS read-only
                    STATUS current
                    DESCRIPTION "Resistors overheat"
                    ::= { digitalObjects 15 }

        -- 1.3.6.1.4.1.9839.2.1.1.16
        al_fan_ol OBJECT-TYPE
                    SYNTAX Integer32 (0..1)
                    UNITS "N/A"
                    MAX-ACCESS read-only
                    STATUS current
                    DESCRIPTION "Fan overheat"
                    ::= { digitalObjects 16 }

        -- 1.3.6.1.4.1.9839.2.1.1.17
        al_comp_ol OBJECT-TYPE
                    SYNTAX Integer32 (0..1)
                    UNITS "N/A"
                    MAX-ACCESS read-only
                    STATUS current
                    DESCRIPTION "Compressor overheat"
                    ::= { digitalObjects 17 }

        -- 1.3.6.1.4.1.9839.2.1.1.18
        al_freecool OBJECT-TYPE
                    SYNTAX Integer32 (0..1)
                    UNITS "N/A"
                    MAX-ACCESS read-only
                    STATUS current
                    DESCRIPTION "Cooling alarm"
                    ::= { digitalObjects 18 }

        -- 1.3.6.1.4.1.9839.2.1.1.19
        al_humidif OBJECT-TYPE
                    SYNTAX Integer32 (0..1)
                    UNITS "N/A"
                    MAX-ACCESS read-only
                    STATUS current
                    DESCRIPTION "Humidifier alarm"
                    ::= { digitalObjects 19 }

        -- 1.3.6.1.4.1.9839.2.1.1.20
        al_room_lt OBJECT-TYPE
                    SYNTAX Integer32 (0..1)
                    UNITS "N/A"
                    MAX-ACCESS read-only
                    STATUS current
                    DESCRIPTION "room low temperature"
                    ::= { digitalObjects 20 }

        -- 1.3.6.1.4.1.9839.2.1.1.21
        al_room_ht OBJECT-TYPE
                    SYNTAX Integer32 (0..1)
                    UNITS "N/A"
                    MAX-ACCESS read-only
                    STATUS current
                    DESCRIPTION "room high temperature"
                    ::= { digitalObjects 21 }

        -- 1.3.6.1.4.1.9839.2.1.1.22
        al_room_lh OBJECT-TYPE
                    SYNTAX Integer32 (0..1)
                    UNITS "N/A"
                    MAX-ACCESS read-only
                    STATUS current
                    DESCRIPTION "room low humidity"
                    ::= { digitalObjects 22 }

        -- 1.3.6.1.4.1.9839.2.1.1.23
        al_room_hh OBJECT-TYPE
                    SYNTAX Integer32 (0..1)
                    UNITS "N/A"
                    MAX-ACCESS read-only
                    STATUS current
                    DESCRIPTION "room high humidity"
                    ::= { digitalObjects 23 }

        -- 1.3.6.1.4.1.9839.2.1.1.24
        al_generic_ext OBJECT-TYPE
                    SYNTAX Integer32 (0..1)
                    UNITS "N/A"
                    MAX-ACCESS read-only
                    STATUS current
                    DESCRIPTION "External alarm"
                    ::= { digitalObjects 24 }

        -- 1.3.6.1.4.1.9839.2.1.1.25
        al_fan_maint OBJECT-TYPE
                    SYNTAX Integer32 (0..1)
                    UNITS "N/A"
                    MAX-ACCESS read-only
                    STATUS current
                    DESCRIPTION "fan maintenance"
                    ::= { digitalObjects 25 }

        -- 1.3.6.1.4.1.9839.2.1.1.26
        al_filter_maint OBJECT-TYPE
                    SYNTAX Integer32 (0..1)
                    UNITS "N/A"
                    MAX-ACCESS read-only
                    STATUS current
                    DESCRIPTION "air filter maintenance"
                    ::= { digitalObjects 26 }

        -- 1.3.6.1.4.1.9839.2.1.1.27
        al_comp1_maint OBJECT-TYPE
                    SYNTAX Integer32 (0..1)
                    UNITS "N/A"
                    MAX-ACCESS read-only
                    STATUS current
                    DESCRIPTION "compressor n°1 maintenance"
                    ::= { digitalObjects 27 }

        -- 1.3.6.1.4.1.9839.2.1.1.28
        al_comp2_maint OBJECT-TYPE
                    SYNTAX Integer32 (0..1)
                    UNITS "N/A"
                    MAX-ACCESS read-only
                    STATUS current
                    DESCRIPTION "compressor n°2 maintenance"
                    ::= { digitalObjects 28 }

        -- 1.3.6.1.4.1.9839.2.1.1.29
        al_low_c_ee OBJECT-TYPE
                    SYNTAX Integer32 (0..1)
                    UNITS "N/A"
                    MAX-ACCESS read-only
                    STATUS current
                    DESCRIPTION "low voltage while eeprom writing"
                    ::= { digitalObjects 29 }

        -- 1.3.6.1.4.1.9839.2.1.1.30
        al_volt_lack OBJECT-TYPE
                    SYNTAX Integer32 (0..1)
                    UNITS "N/A"
                    MAX-ACCESS read-only
                    STATUS current
                    DESCRIPTION "No shelter mains"
                    ::= { digitalObjects 30 }

        -- 1.3.6.1.4.1.9839.2.1.1.31
        al_smoke_fire OBJECT-TYPE
                    SYNTAX Integer32 (0..1)
                    UNITS "N/A"
                    MAX-ACCESS read-only
                    STATUS current
                    DESCRIPTION "Smoke/Fire alarm"
                    ::= { digitalObjects 31 }

        -- 1.3.6.1.4.1.9839.2.1.1.33
        unit_status OBJECT-TYPE
                    SYNTAX Integer32 (0..1)
                    UNITS "N/A"
                    MAX-ACCESS read-only
                    STATUS current
                    DESCRIPTION "On status"
                    ::= { digitalObjects 33 }

        -- 1.3.6.1.4.1.9839.2.1.1.34
        comp1_status OBJECT-TYPE
                    SYNTAX Integer32 (0..1)
                    UNITS "N/A"
                    MAX-ACCESS read-only
                    STATUS current
                    DESCRIPTION "Compressor 1"
                    ::= { digitalObjects 34 }

        -- 1.3.6.1.4.1.9839.2.1.1.35
        comp2_status OBJECT-TYPE
                    SYNTAX Integer32 (0..1)
                    UNITS "N/A"
                    MAX-ACCESS read-only
                    STATUS current
                    DESCRIPTION "Compressor 2"
                    ::= { digitalObjects 35 }

        -- 1.3.6.1.4.1.9839.2.1.1.36
        heater1_status OBJECT-TYPE
                    SYNTAX Integer32 (0..1)
                    UNITS "N/A"
                    MAX-ACCESS read-write
                    STATUS current
                    DESCRIPTION "Heater 1"
                    ::= { digitalObjects 36 }

        -- 1.3.6.1.4.1.9839.2.1.1.37
        heater2_status OBJECT-TYPE
                    SYNTAX Integer32 (0..1)
                    UNITS "N/A"
                    MAX-ACCESS read-write
                    STATUS current
                    DESCRIPTION "Heater 2"
                    ::= { digitalObjects 37 }

        -- 1.3.6.1.4.1.9839.2.1.1.38
        fan_status OBJECT-TYPE
                    SYNTAX Integer32 (0..1)
                    UNITS "N/A"
                    MAX-ACCESS read-only
                    STATUS current
                    DESCRIPTION "Fan status"
                    ::= { digitalObjects 38 }

        -- 1.3.6.1.4.1.9839.2.1.1.39
        deshum_status OBJECT-TYPE
                    SYNTAX Integer32 (0..1)
                    UNITS "N/A"
                    MAX-ACCESS read-only
                    STATUS current
                    DESCRIPTION "Dehumidifier"
                    ::= { digitalObjects 39 }

        -- 1.3.6.1.4.1.9839.2.1.1.41
        humid_on OBJECT-TYPE
                    SYNTAX Integer32 (0..1)
                    UNITS "N/A"
                    MAX-ACCESS read-write
                    STATUS current
                    DESCRIPTION "with HA=4,5 humidifier status"
                    ::= { digitalObjects 41 }

        -- 1.3.6.1.4.1.9839.2.1.1.45
        al_fan1_ol OBJECT-TYPE
                    SYNTAX Integer32 (0..1)
                    UNITS "N/A"
                    MAX-ACCESS read-only
                    STATUS current
                    DESCRIPTION "Fan overheat 1"
                    ::= { digitalObjects 45 }

        -- 1.3.6.1.4.1.9839.2.1.1.46
        al_fan2_ol OBJECT-TYPE
                    SYNTAX Integer32 (0..1)
                    UNITS "N/A"
                    MAX-ACCESS read-only
                    STATUS current
                    DESCRIPTION "Fan overheat 2"
                    ::= { digitalObjects 46 }

        -- 1.3.6.1.4.1.9839.2.1.1.49
        on_off OBJECT-TYPE
                    SYNTAX Integer32 (0..1)
                    UNITS "N/A"
                    MAX-ACCESS read-write
                    STATUS current
                    DESCRIPTION "On/off command (like press on/off key)"
                    ::= { digitalObjects 49 }

        -- 1.3.6.1.4.1.9839.2.1.1.50
        measunit OBJECT-TYPE
                    SYNTAX Integer32 (0..1)
                    UNITS "flag"
                    MAX-ACCESS read-write
                    STATUS current
                    DESCRIPTION "Measure unit (celsius/Fahrenheit)"
                    DEFVAL { 0 }
                    ::= { digitalObjects 50 }



        -- 1.3.6.1.4.1.9839.2.1.2
        analogObjects OBJECT IDENTIFIER ::= { uacMIB 2 }

        -- 1.3.6.1.4.1.9839.2.1.2.1
        probeb3_rp OBJECT-TYPE
                    SYNTAX Integer32 (-32767..32767)
                    UNITS "%RH x10"
                    MAX-ACCESS read-write
                    STATUS current
                    DESCRIPTION "Reading probe B3"
                    ::= { analogObjects 1 }

        -- 1.3.6.1.4.1.9839.2.1.2.2
        probeb1_rn OBJECT-TYPE
                    SYNTAX Integer32 (-32767..32767)
                    UNITS "°C x10"
                    MAX-ACCESS read-only
                    STATUS current
                    DESCRIPTION "Room temper. B1"
                    ::= { analogObjects 2 }

        -- 1.3.6.1.4.1.9839.2.1.2.3
        probeb2_ro OBJECT-TYPE
                    SYNTAX Integer32 (-32767..32767)
                    UNITS "°C x10"
                    MAX-ACCESS read-write
                    STATUS current
                    DESCRIPTION "Reading probe B2"
                    ::= { analogObjects 3 }

        -- 1.3.6.1.4.1.9839.2.1.2.4
        probeb4_rr OBJECT-TYPE
                    SYNTAX Integer32 (-32767..32767)
                    UNITS "°C x10"
                    MAX-ACCESS read-write
                    STATUS current
                    DESCRIPTION "Reading probe B4"
                    ::= { analogObjects 4 }

        -- 1.3.6.1.4.1.9839.2.1.2.5
        real_setp OBJECT-TYPE
                    SYNTAX Integer32 (-32767..32767)
                    UNITS "°C x10"
                    MAX-ACCESS read-write
                    STATUS current
                    DESCRIPTION "Set point"
                    DEFVAL { 200 }
                    ::= { analogObjects 5 }

        -- 1.3.6.1.4.1.9839.2.1.2.11
        sum_setp_r1 OBJECT-TYPE
                    SYNTAX Integer32 (-32767..32767)
                    UNITS "°C x10"
                    MAX-ACCESS read-write
                    STATUS current
                    DESCRIPTION "Temperature set point (cooling)"
                    DEFVAL { 200 }
                    ::= { analogObjects 11 }

        -- 1.3.6.1.4.1.9839.2.1.2.12
        win_setp_r9 OBJECT-TYPE
                    SYNTAX Integer32 (-32767..32767)
                    UNITS "°C x10"
                    MAX-ACCESS read-write
                    STATUS current
                    DESCRIPTION "Temperature set point (heating)"
                    DEFVAL { 180 }
                    ::= { analogObjects 12 }

        -- 1.3.6.1.4.1.9839.2.1.2.13
        min_setp_t_ra OBJECT-TYPE
                    SYNTAX Integer32 (-40..32767)
                    UNITS "°C x10"
                    MAX-ACCESS read-write
                    STATUS current
                    DESCRIPTION "Minimum temperature set point"
                    DEFVAL { 0 }
                    ::= { analogObjects 13 }

        -- 1.3.6.1.4.1.9839.2.1.2.14
        max_setp_t_rb OBJECT-TYPE
                    SYNTAX Integer32 (-32767..1400)
                    UNITS "°C x10"
                    MAX-ACCESS read-write
                    STATUS current
                    DESCRIPTION "Maximum temperature set point"
                    DEFVAL { 500 }
                    ::= { analogObjects 14 }

        -- 1.3.6.1.4.1.9839.2.1.2.15
        sum_diff_r2 OBJECT-TYPE
                    SYNTAX Integer32 (1..198)
                    UNITS "°C x10"
                    MAX-ACCESS read-write
                    STATUS current
                    DESCRIPTION "Cooling differential"
                    DEFVAL { 30 }
                    ::= { analogObjects 15 }

        -- 1.3.6.1.4.1.9839.2.1.2.16
        win_diff_r3 OBJECT-TYPE
                    SYNTAX Integer32 (1..198)
                    UNITS "°C x10"
                    MAX-ACCESS read-write
                    STATUS current
                    DESCRIPTION "Heating differential"
                    DEFVAL { 20 }
                    ::= { analogObjects 16 }

        -- 1.3.6.1.4.1.9839.2.1.2.17
        n_zone_r4 OBJECT-TYPE
                    SYNTAX Integer32 (1..360)
                    UNITS "°C x10"
                    MAX-ACCESS read-write
                    STATUS current
                    DESCRIPTION "Temperature dead zone"
                    DEFVAL { 10 }
                    ::= { analogObjects 17 }

        -- 1.3.6.1.4.1.9839.2.1.2.18
        hum_setp_r5 OBJECT-TYPE
                    SYNTAX Integer32 (-32767..32767)
                    UNITS "%RH x10"
                    MAX-ACCESS read-write
                    STATUS current
                    DESCRIPTION "Humidity Set Point"
                    DEFVAL { 500 }
                    ::= { analogObjects 18 }

        -- 1.3.6.1.4.1.9839.2.1.2.19
        min_setp_h_rc OBJECT-TYPE
                    SYNTAX Integer32 (0..32767)
                    UNITS "%RH x10"
                    MAX-ACCESS read-write
                    STATUS current
                    DESCRIPTION "Minimum humidity set point"
                    DEFVAL { 0 }
                    ::= { analogObjects 19 }

        -- 1.3.6.1.4.1.9839.2.1.2.20
        max_setp_h_rd OBJECT-TYPE
                    SYNTAX Integer32 (-32767..1000)
                    UNITS "%RH x10"
                    MAX-ACCESS read-write
                    STATUS current
                    DESCRIPTION "Maximum humidity set point"
                    DEFVAL { 1000 }
                    ::= { analogObjects 20 }

        -- 1.3.6.1.4.1.9839.2.1.2.21
        diff_hum_r6 OBJECT-TYPE
                    SYNTAX Integer32 (10..200)
                    UNITS "%RH x10"
                    MAX-ACCESS read-write
                    STATUS current
                    DESCRIPTION "Humidification differential"
                    DEFVAL { 40 }
                    ::= { analogObjects 21 }

        -- 1.3.6.1.4.1.9839.2.1.2.22
        diff_dehum_r7 OBJECT-TYPE
                    SYNTAX Integer32 (10..200)
                    UNITS "%RH x10"
                    MAX-ACCESS read-write
                    STATUS current
                    DESCRIPTION "Dehumidification differential"
                    DEFVAL { 30 }
                    ::= { analogObjects 22 }

        -- 1.3.6.1.4.1.9839.2.1.2.23
        n_zone_h_r8 OBJECT-TYPE
                    SYNTAX Integer32 (0..200)
                    UNITS "%RH x10"
                    MAX-ACCESS read-write
                    STATUS current
                    DESCRIPTION "Humidity control dead zone"
                    DEFVAL { 20 }
                    ::= { analogObjects 23 }

        -- 1.3.6.1.4.1.9839.2.1.2.24
        authority_rg OBJECT-TYPE
                    SYNTAX Integer32 (-20..20)
                    UNITS "N/A"
                    MAX-ACCESS read-write
                    STATUS current
                    DESCRIPTION "rG Authority for compensation"
                    DEFVAL { 5 }
                    ::= { analogObjects 24 }

        -- 1.3.6.1.4.1.9839.2.1.2.25
        s_setp_b2_rh OBJECT-TYPE
                    SYNTAX Integer32 (-40..1400)
                    UNITS "°C x10"
                    MAX-ACCESS read-write
                    STATUS current
                    DESCRIPTION "Cooling set point compensation"
                    DEFVAL { 250 }
                    ::= { analogObjects 25 }

        -- 1.3.6.1.4.1.9839.2.1.2.26
        w_setp_b2_ri OBJECT-TYPE
                    SYNTAX Integer32 (-40..1400)
                    UNITS "°C x10"
                    MAX-ACCESS read-write
                    STATUS current
                    DESCRIPTION "Heating set point compensation"
                    DEFVAL { 100 }
                    ::= { analogObjects 26 }

        -- 1.3.6.1.4.1.9839.2.1.2.27
        diff_freec_rl OBJECT-TYPE
                    SYNTAX Integer32 (0..540)
                    UNITS "°C x10"
                    MAX-ACCESS read-write
                    STATUS current
                    DESCRIPTION "Free cooling differential(only for shelters)"
                    DEFVAL { 90 }
                    ::= { analogObjects 27 }

        -- 1.3.6.1.4.1.9839.2.1.2.28
        min_t_freec_rn OBJECT-TYPE
                    SYNTAX Integer32 (-40..860)
                    UNITS "°C x10"
                    MAX-ACCESS read-only
                    STATUS current
                    DESCRIPTION "Lower supply temperature limit during free cooling"
                    DEFVAL { 50 }
                    ::= { analogObjects 28 }

        -- 1.3.6.1.4.1.9839.2.1.2.29
        delta_p6 OBJECT-TYPE
                    SYNTAX Integer32 (0..900)
                    UNITS "°C x10"
                    MAX-ACCESS read-write
                    STATUS current
                    DESCRIPTION "Delta from effective set point for low temperature alarm"
                    DEFVAL { 100 }
                    ::= { analogObjects 29 }

        -- 1.3.6.1.4.1.9839.2.1.2.30
        delta_p7 OBJECT-TYPE
                    SYNTAX Integer32 (0..900)
                    UNITS "°C x10"
                    MAX-ACCESS read-write
                    STATUS current
                    DESCRIPTION "Delta from effective set point for high temperature alarm"
                    DEFVAL { 100 }
                    ::= { analogObjects 30 }

        -- 1.3.6.1.4.1.9839.2.1.2.31
        delta_p8 OBJECT-TYPE
                    SYNTAX Integer32 (0..500)
                    UNITS "%RH x10"
                    MAX-ACCESS read-write
                    STATUS current
                    DESCRIPTION "Delta from set point for low humidity alarm"
                    DEFVAL { 200 }
                    ::= { analogObjects 31 }

        -- 1.3.6.1.4.1.9839.2.1.2.32
        delta_p9 OBJECT-TYPE
                    SYNTAX Integer32 (0..500)
                    UNITS "%RH x10"
                    MAX-ACCESS read-write
                    STATUS current
                    DESCRIPTION "Delta from set point for high humidity alarm"
                    DEFVAL { 200 }
                    ::= { analogObjects 32 }

        -- 1.3.6.1.4.1.9839.2.1.2.33
        diff_pd OBJECT-TYPE
                    SYNTAX Integer32 (0..360)
                    UNITS "°C x10"
                    MAX-ACCESS read-write
                    STATUS current
                    DESCRIPTION "Return supply temp. difference for supply temp ala"
                    DEFVAL { 30 }
                    ::= { analogObjects 33 }

        -- 1.3.6.1.4.1.9839.2.1.2.34
        min_fan_s_f5 OBJECT-TYPE
                    SYNTAX Integer32 (0..32767)
                    UNITS "°C x10"
                    MAX-ACCESS read-write
                    STATUS current
                    DESCRIPTION "% reg. band for min speed or temp./pressure for min speed in condens."
                    DEFVAL { 200 }
                    ::= { analogObjects 34 }

        -- 1.3.6.1.4.1.9839.2.1.2.35
        max_fan_s_f6 OBJECT-TYPE
                    SYNTAX Integer32 (-32767..1580)
                    UNITS "°C x10"
                    MAX-ACCESS read-write
                    STATUS current
                    DESCRIPTION "% reg. band for max speed or temp./pressure for max speed in condens."
                    DEFVAL { 1000 }
                    ::= { analogObjects 35 }

        -- 1.3.6.1.4.1.9839.2.1.2.36
        probeconvl OBJECT-TYPE
                    SYNTAX Integer32 (0..32767)
                    UNITS "%RH/bar x10"
                    MAX-ACCESS read-write
                    STATUS current
                    DESCRIPTION "Minimun value of humidity/pressure at 0mA, 4mA or 0Vdc"
                    DEFVAL { 0 }
                    ::= { analogObjects 36 }

        -- 1.3.6.1.4.1.9839.2.1.2.37
        probeconvh OBJECT-TYPE
                    SYNTAX Integer32 (-32767..1000)
                    UNITS "%RH/bar x10"
                    MAX-ACCESS read-write
                    STATUS current
                    DESCRIPTION "maximun value of humidity/pressure at 20mA or 1Vdc"
                    DEFVAL { 1000 }
                    ::= { analogObjects 37 }

        -- 1.3.6.1.4.1.9839.2.1.2.38
        calibrazione_sonda_b1 OBJECT-TYPE
                    SYNTAX Integer32 (-108..108)
                    UNITS "°C x10"
                    MAX-ACCESS read-write
                    STATUS current
                    DESCRIPTION "Calibration probe B1"
                    DEFVAL { 0 }
                    ::= { analogObjects 38 }

        -- 1.3.6.1.4.1.9839.2.1.2.39
        calibrazione_sonda_b2 OBJECT-TYPE
                    SYNTAX Integer32 (-108..108)
                    UNITS "°C x10"
                    MAX-ACCESS read-write
                    STATUS current
                    DESCRIPTION "Calibration probe B2"
                    DEFVAL { 0 }
                    ::= { analogObjects 39 }

        -- 1.3.6.1.4.1.9839.2.1.2.40
        calibrazione_sonda_b3 OBJECT-TYPE
                    SYNTAX Integer32 (-100..100)
                    UNITS "%RH/bar x10"
                    MAX-ACCESS read-write
                    STATUS current
                    DESCRIPTION "Calibration probe B3"
                    DEFVAL { 0 }
                    ::= { analogObjects 40 }

        -- 1.3.6.1.4.1.9839.2.1.2.41
        calibrazione_sonda_b4 OBJECT-TYPE
                    SYNTAX Integer32 (-108..108)
                    UNITS "°C x10"
                    MAX-ACCESS read-write
                    STATUS current
                    DESCRIPTION "Calibration probe B4"
                    DEFVAL { 0 }
                    ::= { analogObjects 41 }



        -- 1.3.6.1.4.1.9839.2.1.3
        integerObjects OBJECT IDENTIFIER ::= { uacMIB 3 }

        -- 1.3.6.1.4.1.9839.2.1.3.11
        fan_h_count_fa OBJECT-TYPE
                    SYNTAX Integer32 (0..30000)
                    UNITS "hours"
                    MAX-ACCESS read-write
                    STATUS current
                    DESCRIPTION "Supply fan hour counter"
                    DEFVAL { 0 }
                    ::= { integerObjects 11 }

        -- 1.3.6.1.4.1.9839.2.1.3.12
        filt_h_count_fc OBJECT-TYPE
                    SYNTAX Integer32 (0..30000)
                    UNITS "hours"
                    MAX-ACCESS read-write
                    STATUS current
                    DESCRIPTION "Filter hour counter"
                    DEFVAL { 0 }
                    ::= { integerObjects 12 }

        -- 1.3.6.1.4.1.9839.2.1.3.13
        cmp1_h_count_c9 OBJECT-TYPE
                    SYNTAX Integer32 (0..30000)
                    UNITS "hours"
                    MAX-ACCESS read-write
                    STATUS current
                    DESCRIPTION "compressor 1 hour counter"
                    DEFVAL { 0 }
                    ::= { integerObjects 13 }

        -- 1.3.6.1.4.1.9839.2.1.3.14
        cmp2_h_count_ca OBJECT-TYPE
                    SYNTAX Integer32 (0..30000)
                    UNITS "hours"
                    MAX-ACCESS read-write
                    STATUS current
                    DESCRIPTION "compressor 2 hour counter"
                    DEFVAL { 0 }
                    ::= { integerObjects 14 }

        -- 1.3.6.1.4.1.9839.2.1.3.15
        en_fan_hc_f9 OBJECT-TYPE
                    SYNTAX Integer32 (0..30000)
                    UNITS "hours"
                    MAX-ACCESS read-write
                    STATUS current
                    DESCRIPTION "Supply fan hour counter threshold"
                    DEFVAL { 0 }
                    ::= { integerObjects 15 }

        -- 1.3.6.1.4.1.9839.2.1.3.16
        en_filt_hc_fb OBJECT-TYPE
                    SYNTAX Integer32 (0..30000)
                    UNITS "hours"
                    MAX-ACCESS read-write
                    STATUS current
                    DESCRIPTION "Filter hour counter threshold"
                    DEFVAL { 0 }
                    ::= { integerObjects 16 }

        -- 1.3.6.1.4.1.9839.2.1.3.17
        en_cmps_hc_c8 OBJECT-TYPE
                    SYNTAX Integer32 (0..30000)
                    UNITS "hours"
                    MAX-ACCESS read-write
                    STATUS current
                    DESCRIPTION "compressor hour counter threshold"
                    DEFVAL { 0 }
                    ::= { integerObjects 17 }

        -- 1.3.6.1.4.1.9839.2.1.3.18
        unit_model_h1 OBJECT-TYPE
                    SYNTAX Integer32 (0..3)
                    UNITS "flag"
                    MAX-ACCESS read-write
                    STATUS current
                    DESCRIPTION "Machine model"
                    DEFVAL { 0 }
                    ::= { integerObjects 18 }

        -- 1.3.6.1.4.1.9839.2.1.3.19
        cool_mode_h5 OBJECT-TYPE
                    SYNTAX Integer32 (1..5)
                    UNITS "flag"
                    MAX-ACCESS read-write
                    STATUS current
                    DESCRIPTION "Operating mode of the 2 “cool” outputs"
                    DEFVAL { 1 }
                    ::= { integerObjects 19 }

        -- 1.3.6.1.4.1.9839.2.1.3.20
        heat_mode_h6 OBJECT-TYPE
                    SYNTAX Integer32 (0..4)
                    UNITS "flag"
                    MAX-ACCESS read-write
                    STATUS current
                    DESCRIPTION "Operating mode of the 2 “heat” outputs"
                    DEFVAL { 1 }
                    ::= { integerObjects 20 }

        -- 1.3.6.1.4.1.9839.2.1.3.21
        en_humidif_h8 OBJECT-TYPE
                    SYNTAX Integer32 (0..1)
                    UNITS "flag"
                    MAX-ACCESS read-write
                    STATUS current
                    DESCRIPTION "Presence of humidifier"
                    DEFVAL { 0 }
                    ::= { integerObjects 21 }

        -- 1.3.6.1.4.1.9839.2.1.3.22
        tempo_di_escursione_valvola_3 OBJECT-TYPE
                    SYNTAX Integer32 (0..600)
                    UNITS "sec"
                    MAX-ACCESS read-write
                    STATUS current
                    DESCRIPTION "3P valve or damper excursion time"
                    DEFVAL { 150 }
                    ::= { integerObjects 22 }

        -- 1.3.6.1.4.1.9839.2.1.3.23
        prop_pi_re OBJECT-TYPE
                    SYNTAX Integer32 (0..1)
                    UNITS "flag"
                    MAX-ACCESS read-write
                    STATUS current
                    DESCRIPTION "Type of temperature regulation"
                    DEFVAL { 0 }
                    ::= { integerObjects 23 }

        -- 1.3.6.1.4.1.9839.2.1.3.24
        pi_time_rf OBJECT-TYPE
                    SYNTAX Integer32 (10..3600)
                    UNITS "sec"
                    MAX-ACCESS read-write
                    STATUS current
                    DESCRIPTION "Integration time for P+I action"
                    DEFVAL { 600 }
                    ::= { integerObjects 24 }

        -- 1.3.6.1.4.1.9839.2.1.3.25
        conf_humid_h9 OBJECT-TYPE
                    SYNTAX Integer32 (0..9)
                    UNITS "flags"
                    MAX-ACCESS read-write
                    STATUS current
                    DESCRIPTION "Type of dehumidification"
                    DEFVAL { 0 }
                    ::= { integerObjects 25 }

        -- 1.3.6.1.4.1.9839.2.1.3.26
        conf_b2_hc OBJECT-TYPE
                    SYNTAX Integer32 (0..3)
                    UNITS "flag"
                    MAX-ACCESS read-write
                    STATUS current
                    DESCRIPTION "Function of probe B2"
                    DEFVAL { 0 }
                    ::= { integerObjects 26 }

        -- 1.3.6.1.4.1.9839.2.1.3.27
        conf_b3_hd OBJECT-TYPE
                    SYNTAX Integer32 (0..1)
                    UNITS "flag"
                    MAX-ACCESS read-write
                    STATUS current
                    DESCRIPTION "Function of probe B3"
                    DEFVAL { 0 }
                    ::= { integerObjects 27 }

        -- 1.3.6.1.4.1.9839.2.1.3.28
        conf_anout2_hb OBJECT-TYPE
                    SYNTAX Integer32 (0..2)
                    UNITS "flag"
                    MAX-ACCESS read-write
                    STATUS current
                    DESCRIPTION "Function of output Y2"
                    DEFVAL { 0 }
                    ::= { integerObjects 28 }

        -- 1.3.6.1.4.1.9839.2.1.3.29
        id_on_off_he OBJECT-TYPE
                    SYNTAX Integer32 (0..1)
                    UNITS "flag"
                    MAX-ACCESS read-write
                    STATUS current
                    DESCRIPTION "ON/OFF digital input"
                    DEFVAL { 0 }
                    ::= { integerObjects 29 }

        -- 1.3.6.1.4.1.9839.2.1.3.30
        al_out_lgk_hf OBJECT-TYPE
                    SYNTAX Integer32 (0..3)
                    UNITS "flag"
                    MAX-ACCESS read-write
                    STATUS current
                    DESCRIPTION "Alarm relay logic"
                    DEFVAL { 0 }
                    ::= { integerObjects 30 }

        -- 1.3.6.1.4.1.9839.2.1.3.31
        conf_deshum_ha OBJECT-TYPE
                    SYNTAX Integer32 (0..7)
                    UNITS "flag"
                    MAX-ACCESS read-write
                    STATUS current
                    DESCRIPTION "Function of the dehumidificat./humidif. Relay"
                    DEFVAL { 0 }
                    ::= { integerObjects 31 }

        -- 1.3.6.1.4.1.9839.2.1.3.32
        conf_id_al_pb OBJECT-TYPE
                    SYNTAX Integer32 (0..6)
                    UNITS "flag"
                    MAX-ACCESS read-write
                    STATUS current
                    DESCRIPTION "Type of management of generic alarm input ID5"
                    DEFVAL { 1 }
                    ::= { integerObjects 32 }

        -- 1.3.6.1.4.1.9839.2.1.3.33
        un_rot_num_h2 OBJECT-TYPE
                    SYNTAX Integer32 (0..6)
                    UNITS "flag"
                    MAX-ACCESS read-write
                    STATUS current
                    DESCRIPTION "N. of machines in rotation"
                    DEFVAL { 0 }
                    ::= { integerObjects 33 }

        -- 1.3.6.1.4.1.9839.2.1.3.34
        un_rot_adr_h3 OBJECT-TYPE
                    SYNTAX Integer32 (1..6)
                    UNITS "N/A"
                    MAX-ACCESS read-write
                    STATUS current
                    DESCRIPTION "Address of unit in rotation"
                    DEFVAL { 1 }
                    ::= { integerObjects 34 }

        -- 1.3.6.1.4.1.9839.2.1.3.35
        rot_time_h4 OBJECT-TYPE
                    SYNTAX Integer32 (0..250)
                    UNITS "hours"
                    MAX-ACCESS read-write
                    STATUS current
                    DESCRIPTION "Rotation time between a series of units"
                    DEFVAL { 0 }
                    ::= { integerObjects 35 }

        -- 1.3.6.1.4.1.9839.2.1.3.36
        presenza_sonda_1 OBJECT-TYPE
                    SYNTAX Integer32 (0..1)
                    UNITS "flag"
                    MAX-ACCESS read-write
                    STATUS current
                    DESCRIPTION "Presence external air probe B2"
                    DEFVAL { 0 }
                    ::= { integerObjects 36 }

        -- 1.3.6.1.4.1.9839.2.1.3.37
        tipo_sonda_2 OBJECT-TYPE
                    SYNTAX Integer32 (0..2)
                    UNITS "flag"
                    MAX-ACCESS read-write
                    STATUS current
                    DESCRIPTION "Type of humidity/press./temp. probe B3"
                    DEFVAL { 0 }
                    ::= { integerObjects 37 }

        -- 1.3.6.1.4.1.9839.2.1.3.38
        presenza_sonda_3 OBJECT-TYPE
                    SYNTAX Integer32 (0..1)
                    UNITS "flag"
                    MAX-ACCESS read-write
                    STATUS current
                    DESCRIPTION "Presence supply air B4"
                    DEFVAL { 0 }
                    ::= { integerObjects 38 }

        -- 1.3.6.1.4.1.9839.2.1.3.39
        filtro_digitale OBJECT-TYPE
                    SYNTAX Integer32 (1..15)
                    UNITS "°C"
                    MAX-ACCESS read-write
                    STATUS current
                    DESCRIPTION "Digital filter"
                    DEFVAL { 4 }
                    ::= { integerObjects 39 }

        -- 1.3.6.1.4.1.9839.2.1.3.40
        limitazione_ingresso OBJECT-TYPE
                    SYNTAX Integer32 (1..15)
                    UNITS "N/A"
                    MAX-ACCESS read-write
                    STATUS current
                    DESCRIPTION "Input limit"
                    DEFVAL { 8 }
                    ::= { integerObjects 40 }

        -- 1.3.6.1.4.1.9839.2.1.3.41
        keyb_lockup_hi OBJECT-TYPE
                    SYNTAX Integer32 (-32767..32767)
                    UNITS "N/A"
                    MAX-ACCESS read-write
                    STATUS current
                    DESCRIPTION "inibit parameter modifications"
                    ::= { integerObjects 41 }

        -- 1.3.6.1.4.1.9839.2.1.3.42
        param_set_hl OBJECT-TYPE
                    SYNTAX Integer32 (0..3)
                    UNITS "flag"
                    MAX-ACCESS read-write
                    STATUS current
                    DESCRIPTION "Parameter sets"
                    DEFVAL { 0 }
                    ::= { integerObjects 42 }

        -- 1.3.6.1.4.1.9839.2.1.3.43
        display_cfg_hn OBJECT-TYPE
                    SYNTAX Integer32 (0..2)
                    UNITS "flag"
                    MAX-ACCESS read-write
                    STATUS current
                    DESCRIPTION "Select data shown on display"
                    DEFVAL { 0 }
                    ::= { integerObjects 43 }

        -- 1.3.6.1.4.1.9839.2.1.3.44
        buzzer_cfg_p4 OBJECT-TYPE
                    SYNTAX Integer32 (0..15)
                    UNITS "min"
                    MAX-ACCESS read-write
                    STATUS current
                    DESCRIPTION "P4 Buzzer activation"
                    DEFVAL { 0 }
                    ::= { integerObjects 44 }

        -- 1.3.6.1.4.1.9839.2.1.3.45
        alm_reset_p5 OBJECT-TYPE
                    SYNTAX Integer32 (1..5)
                    UNITS "flag"
                    MAX-ACCESS read-write
                    STATUS current
                    DESCRIPTION "Reset alarms"
                    DEFVAL { 1 }
                    ::= { integerObjects 45 }

        -- 1.3.6.1.4.1.9839.2.1.3.48
        user_pw_hh OBJECT-TYPE
                    SYNTAX Integer32 (0..200)
                    UNITS "N/A"
                    MAX-ACCESS read-write
                    STATUS current
                    DESCRIPTION "USER password"
                    DEFVAL { 22 }
                    ::= { integerObjects 48 }

        -- 1.3.6.1.4.1.9839.2.1.3.49
        sw_release_hr OBJECT-TYPE
                    SYNTAX Integer32 (-32767..32767)
                    UNITS "N/A"
                    MAX-ACCESS read-only
                    STATUS current
                    DESCRIPTION "Software version"
                    DEFVAL { 13 }
                    ::= { integerObjects 49 }

        -- 1.3.6.1.4.1.9839.2.1.3.50
        fan_config_f1 OBJECT-TYPE
                    SYNTAX Integer32 (0..2)
                    UNITS "flag"
                    MAX-ACCESS read-write
                    STATUS current
                    DESCRIPTION "Fan operating mode"
                    DEFVAL { 1 }
                    ::= { integerObjects 50 }

        -- 1.3.6.1.4.1.9839.2.1.3.51
        min_volt_f2 OBJECT-TYPE
                    SYNTAX Integer32 (0..32767)
                    UNITS "step"
                    MAX-ACCESS read-write
                    STATUS current
                    DESCRIPTION "Minimum triac voltage threshold"
                    DEFVAL { 35 }
                    ::= { integerObjects 51 }

        -- 1.3.6.1.4.1.9839.2.1.3.52
        max_volt_f3 OBJECT-TYPE
                    SYNTAX Integer32 (-32767..100)
                    UNITS "step"
                    MAX-ACCESS read-write
                    STATUS current
                    DESCRIPTION "Maximum triac voltage threshold"
                    DEFVAL { 75 }
                    ::= { integerObjects 52 }

        -- 1.3.6.1.4.1.9839.2.1.3.53
        triac_durat_f4 OBJECT-TYPE
                    SYNTAX Integer32 (0..15)
                    UNITS "ms"
                    MAX-ACCESS read-write
                    STATUS current
                    DESCRIPTION "Duration of triac impulse"
                    DEFVAL { 2 }
                    ::= { integerObjects 53 }

        -- 1.3.6.1.4.1.9839.2.1.3.54
        min_out_val_f7 OBJECT-TYPE
                    SYNTAX Integer32 (0..32767)
                    UNITS "%"
                    MAX-ACCESS read-write
                    STATUS current
                    DESCRIPTION "Minimum output value"
                    DEFVAL { 10 }
                    ::= { integerObjects 54 }

        -- 1.3.6.1.4.1.9839.2.1.3.55
        max_out_val_f8 OBJECT-TYPE
                    SYNTAX Integer32 (-32767..100)
                    UNITS "%"
                    MAX-ACCESS read-write
                    STATUS current
                    DESCRIPTION "Maximum output value"
                    DEFVAL { 100 }
                    ::= { integerObjects 55 }

        -- 1.3.6.1.4.1.9839.2.1.3.56
        min_on_time_c1 OBJECT-TYPE
                    SYNTAX Integer32 (0..300)
                    UNITS "sec"
                    MAX-ACCESS read-write
                    STATUS current
                    DESCRIPTION "Minimum ON time"
                    DEFVAL { 60 }
                    ::= { integerObjects 56 }

        -- 1.3.6.1.4.1.9839.2.1.3.57
        min_off_time_c2 OBJECT-TYPE
                    SYNTAX Integer32 (0..900)
                    UNITS "sec"
                    MAX-ACCESS read-write
                    STATUS current
                    DESCRIPTION "Minimum OFF time"
                    DEFVAL { 60 }
                    ::= { integerObjects 57 }

        -- 1.3.6.1.4.1.9839.2.1.3.58
        t_betw_2_on_c3 OBJECT-TYPE
                    SYNTAX Integer32 (0..900)
                    UNITS "sec"
                    MAX-ACCESS read-write
                    STATUS current
                    DESCRIPTION "Minimum time between two start-ups"
                    DEFVAL { 360 }
                    ::= { integerObjects 58 }

        -- 1.3.6.1.4.1.9839.2.1.3.59
        t_comp_2_on_c4 OBJECT-TYPE
                    SYNTAX Integer32 (0..300)
                    UNITS "sec"
                    MAX-ACCESS read-write
                    STATUS current
                    DESCRIPTION "ON delay between the 2 compressors"
                    DEFVAL { 30 }
                    ::= { integerObjects 59 }

        -- 1.3.6.1.4.1.9839.2.1.3.60
        t_comp_2_off_c5 OBJECT-TYPE
                    SYNTAX Integer32 (0..300)
                    UNITS "sec"
                    MAX-ACCESS read-write
                    STATUS current
                    DESCRIPTION "OFF delay between the 2 compressors"
                    DEFVAL { 0 }
                    ::= { integerObjects 60 }

        -- 1.3.6.1.4.1.9839.2.1.3.61
        t_comp_fan_c7 OBJECT-TYPE
                    SYNTAX Integer32 (0..300)
                    UNITS "sec"
                    MAX-ACCESS read-write
                    STATUS current
                    DESCRIPTION "Comp. ON delay from supply fan start-up"
                    DEFVAL { 20 }
                    ::= { integerObjects 61 }

        -- 1.3.6.1.4.1.9839.2.1.3.62
        off_fan_d_fd OBJECT-TYPE
                    SYNTAX Integer32 (0..900)
                    UNITS "sec"
                    MAX-ACCESS read-write
                    STATUS current
                    DESCRIPTION "Supply fan off delay"
                    DEFVAL { 20 }
                    ::= { integerObjects 62 }

        -- 1.3.6.1.4.1.9839.2.1.3.63
        on_dalay_hg OBJECT-TYPE
                    SYNTAX Integer32 (0..300)
                    UNITS "sec"
                    MAX-ACCESS read-write
                    STATUS current
                    DESCRIPTION "Delay on start-up"
                    DEFVAL { 0 }
                    ::= { integerObjects 63 }

        -- 1.3.6.1.4.1.9839.2.1.3.64
        en_rotat_c6 OBJECT-TYPE
                    SYNTAX Integer32 (0..1)
                    UNITS "flag"
                    MAX-ACCESS read-write
                    STATUS current
                    DESCRIPTION "Compressor rotation"
                    DEFVAL { 0 }
                    ::= { integerObjects 64 }

        -- 1.3.6.1.4.1.9839.2.1.3.65
        d_flow_s_p1 OBJECT-TYPE
                    SYNTAX Integer32 (0..250)
                    UNITS "sec"
                    MAX-ACCESS read-write
                    STATUS current
                    DESCRIPTION "Flow alarm delay from fan start-up"
                    DEFVAL { 20 }
                    ::= { integerObjects 65 }

        -- 1.3.6.1.4.1.9839.2.1.3.66
        d_flow_run_p2 OBJECT-TYPE
                    SYNTAX Integer32 (0..90)
                    UNITS "sec"
                    MAX-ACCESS read-write
                    STATUS current
                    DESCRIPTION "Flow alarm delay during operation"
                    DEFVAL { 5 }
                    ::= { integerObjects 66 }

        -- 1.3.6.1.4.1.9839.2.1.3.67
        lp_delay_p3 OBJECT-TYPE
                    SYNTAX Integer32 (0..250)
                    UNITS "sec"
                    MAX-ACCESS read-write
                    STATUS current
                    DESCRIPTION "Low pressure alarm delay from compress. Start-up"
                    DEFVAL { 40 }
                    ::= { integerObjects 67 }

        -- 1.3.6.1.4.1.9839.2.1.3.68
        al_prb_delay_pa OBJECT-TYPE
                    SYNTAX Integer32 (0..150)
                    UNITS "min"
                    MAX-ACCESS read-write
                    STATUS current
                    DESCRIPTION "Alarm delay high/low temperature/humidity on start-up"
                    DEFVAL { 20 }
                    ::= { integerObjects 68 }

        -- 1.3.6.1.4.1.9839.2.1.3.69
        al_gen_delay_pc OBJECT-TYPE
                    SYNTAX Integer32 (0..250)
                    UNITS "sec"
                    MAX-ACCESS read-write
                    STATUS current
                    DESCRIPTION "Generic alarm delay"
                    DEFVAL { 60 }
                    ::= { integerObjects 69 }

        -- 1.3.6.1.4.1.9839.2.1.3.70
        t_slot_cfg_rt OBJECT-TYPE
                    SYNTAX Integer32 (0..2)
                    UNITS "flag"
                    MAX-ACCESS read-write
                    STATUS current
                    DESCRIPTION "Time band setting"
                    DEFVAL { 0 }
                    ::= { integerObjects 70 }

        -- 1.3.6.1.4.1.9839.2.1.3.71
        fan_time_fe OBJECT-TYPE
                    SYNTAX Integer32 (0..60)
                    UNITS "sec"
                    MAX-ACCESS read-write
                    STATUS current
                    DESCRIPTION "Fan pick-up time in condensation"
                    DEFVAL { 4 }
                    ::= { integerObjects 71 }

        -- 1.3.6.1.4.1.9839.2.1.3.72
        abilitazione_allarme_fumo OBJECT-TYPE
                    SYNTAX Integer32 (0..1)
                    UNITS "flag"
                    MAX-ACCESS read-write
                    STATUS current
                    DESCRIPTION "Input selection"
                    DEFVAL { 0 }
                    ::= { integerObjects 72 }

        -- 1.3.6.1.4.1.9839.2.1.3.73
        abilitazione_allarme_cf OBJECT-TYPE
                    SYNTAX Integer32 (0..1)
                    UNITS "flag"
                    MAX-ACCESS read-write
                    STATUS current
                    DESCRIPTION "Water flow alarm enable"
                    DEFVAL { 0 }
                    ::= { integerObjects 73 }

        -- 1.3.6.1.4.1.9839.2.1.3.74
        abilitazione_allarme_ht OBJECT-TYPE
                    SYNTAX Integer32 (0..1)
                    UNITS "flag"
                    MAX-ACCESS read-write
                    STATUS current
                    DESCRIPTION "high temperature pre-alarm enable"
                    DEFVAL { 0 }
                    ::= { integerObjects 74 }



	END

--
-- CAREL-uac.MIB
--
