--
-- CAREL-rtop_pco.MIB
-- MIB generated by CAREL
-- Friday, 14 March 2003
--

    CAREL-rtop_pco-MIB DEFINITIONS ::= BEGIN

		IMPORTS
			OBJECT-GROUP
				FROM SNMPv2-CONF
			sysContact, sysName, sysLocation
				FROM SNMPv2-MIB
			enterprises, MODULE-IDENTITY
				FROM SNMPv2-SMI;

        rtop_pcoMIB MODULE-IDENTITY
      		LAST-UPDATED  "200303141725Z"		-- March 14, 2003 at 17:25 GMT
      		ORGANIZATION  "CAREL SpA"
      		CONTACT-INFO
                "
                        Simone Ravazzolo
                        Carel SpA
                        Via dell'Industria, 11
                        35020 Brugine (PD) Italy
                        Tel: +39 049 9716611
                        E-mail: simone.ravazzolo@carel.com
                "
      		DESCRIPTION
                "This is the MIB module for the rtop_pco device."
			::= { instruments 1 }


--
-- Node definitions
--

		-- 1.3.6.1.4.1.9839
		carel OBJECT IDENTIFIER ::= { enterprises 9839 }

		-- 1.3.6.1.4.1.9839.1
		systm OBJECT IDENTIFIER ::= { carel 1 }

		-- 1.3.6.1.4.1.9839.1.1
		agentRelease OBJECT-TYPE
			SYNTAX Integer32
			UNITS "N/A"
			MAX-ACCESS read-only
			STATUS current
			DESCRIPTION "Release of the Agent."
		::= { systm 1 }

		-- 1.3.6.1.4.1.9839.1.2
		agentCode OBJECT-TYPE
			SYNTAX Integer32
			UNITS "N/A"
			MAX-ACCESS read-only
			STATUS current
			DESCRIPTION "Code of the Agent. 1=WebGate"
		::= { systm 2 }

		-- 1.3.6.1.4.1.9839.2
		instruments OBJECT IDENTIFIER ::= { carel 2 }

		-- 1.3.6.1.4.1.9839.2.0
		webGateInfo OBJECT IDENTIFIER ::= { instruments 0 }

		-- 1.3.6.1.4.1.9839.2.0.1
		agentParameters OBJECT IDENTIFIER ::= { webGateInfo 1 }

		-- 1.3.6.1.4.1.9839.2.0.1.1
		netSize OBJECT-TYPE
			SYNTAX Integer32 (1..16)
			UNITS "N/A"
			MAX-ACCESS read-write
			STATUS current
			DESCRIPTION "Network size. It corresponds to the number of units connected to the WebGate. "
		::= { agentParameters 1 }

		-- 1.3.6.1.4.1.9839.2.0.1.2
		baudRate OBJECT-TYPE
			SYNTAX Integer32 (1200 | 2400 |4800 |9600 | 19200)
			UNITS "N/A"
			MAX-ACCESS read-write
			STATUS current
			DESCRIPTION "Baudrate of the Carel network. "
		::= { agentParameters 2 }

		-- 1.3.6.1.4.1.9839.2.0.2
		unitTypeGroup OBJECT IDENTIFIER ::= { webGateInfo 2 }

		-- 1.3.6.1.4.1.9839.2.0.2.1
		unit1-Type OBJECT-TYPE
			SYNTAX DisplayString
			UNITS "N/A"
			MAX-ACCESS read-only
			STATUS current
			DESCRIPTION "Type of the unit having serial address 1. "
			::= { unitTypeGroup 1 }

		-- ... You will have how many unitX-Type objects as the value of netSize is

		-- 1.3.6.1.4.1.9839.2.0.3
		unitCodeGroup OBJECT IDENTIFIER ::= { webGateInfo 3 }

		-- 1.3.6.1.4.1.9839.2.0.3.1
		unit1-Code OBJECT-TYPE
			SYNTAX Integer32
			UNITS "N/A"
			MAX-ACCESS read-only
			STATUS current
			DESCRIPTION "Code of the unit having serial address 1. "
			::= { unitCodeGroup 1 }

		-- ... You will have how many unitX-Code objects as the value of netSize is

		-- 1.3.6.1.4.1.9839.2.0.4
		unitSoftwareReleaseGroup OBJECT IDENTIFIER ::= { webGateInfo 4 }

		-- 1.3.6.1.4.1.9839.2.0.3.1
		unit1-SoftwareRelease OBJECT-TYPE
			SYNTAX Integer32
			UNITS "N/A"
			MAX-ACCESS read-only
			STATUS current
			DESCRIPTION "Software release of the unit having serial address 1. "
			::= { unitSoftwareReleaseGroup 1 }

		-- ... You will have how many unitX-SoftwareRelease objects as the value of netSize is

		-- 1.3.6.1.4.1.9839.2.0.5
		unitMinSoftwareReleaseGroup OBJECT IDENTIFIER ::= { webGateInfo 5 }

		-- 1.3.6.1.4.1.9839.2.0.5.1
		unit1-MinSoftwareRelease OBJECT-TYPE
			SYNTAX Integer32
			UNITS "N/A"
			MAX-ACCESS read-only
			STATUS current
			DESCRIPTION "Minimum software release of the unit having serial address 1. "
			::= { unitMinSoftwareReleaseGroup 1 }

		-- ... You will have how many unitX-MinSoftwareRelease objects as the value of netSize is

		-- 1.3.6.1.4.1.9839.2.0.6
		unitMaxSoftwareReleaseGroup OBJECT IDENTIFIER ::= { webGateInfo 6 }

		-- 1.3.6.1.4.1.9839.2.0.6.1
		unit1-MaxSoftwareRelease OBJECT-TYPE
			SYNTAX Integer32
			UNITS "N/A"
			MAX-ACCESS read-only
			STATUS current
			DESCRIPTION "Maximum software release of the unit having serial address 1. "
			::= { unitMaxSoftwareReleaseGroup 1 }

		-- ... You will have how many unitX-MaxSoftwareRelease objects as the value of netSize is

		-- 1.3.6.1.4.1.9839.2.0.7
		unitNoAnswerCounterGroup OBJECT IDENTIFIER ::= { webGateInfo 7 }

		-- 1.3.6.1.4.1.9839.2.0.7.1
		unit1-NoAnswerCounter OBJECT-TYPE
			SYNTAX Integer32
			UNITS "N/A"
			MAX-ACCESS read-only
			STATUS current
			DESCRIPTION "No answer counter of the unit having serial address 1. "
			::= { unitNoAnswerCounterGroup 1 }

		-- ... You will have how many unitX-NoAnswerCounter objects as the value of netSize is

		-- 1.3.6.1.4.1.9839.2.0.8
		unitErrorChecksumCounterGroup OBJECT IDENTIFIER ::= { webGateInfo 8 }

		-- 1.3.6.1.4.1.9839.2.0.8.1
		unit1-ErrorChecksumCounter OBJECT-TYPE
			SYNTAX Integer32
			UNITS "N/A"
			MAX-ACCESS read-only
			STATUS current
			DESCRIPTION "Error checksum counter of the unit having serial address 1. "
			::= { unitErrorChecksumCounterGroup 1 }

		-- ... You will have how many unitX-ErrorChecksumCounter objects as the value of netSize is

		-- 1.3.6.1.4.1.9839.2.0.9
		unitTimeoutCounterGroup OBJECT IDENTIFIER ::= { webGateInfo 9 }

		-- 1.3.6.1.4.1.9839.2.0.9.1
		unit1-TimeoutCounter OBJECT-TYPE
			SYNTAX Integer32
			UNITS "N/A"
			MAX-ACCESS read-only
			STATUS current
			DESCRIPTION "Timeout counter of the unit having serial address 1. "
			::= { unitTimeoutCounterGroup 1 }

		-- ... You will have how many unitX-TimeoutCounter objects as the value of netSize is

		-- 1.3.6.1.4.1.9839.2.0.10
		unitOnLineStatusGroup OBJECT IDENTIFIER ::= { webGateInfo 10 }

		-- 1.3.6.1.4.1.9839.2.0.10.1
		unit1-OnLineStatus OBJECT-TYPE
			SYNTAX Integer32
			UNITS "N/A"
			MAX-ACCESS read-only
			STATUS current
			DESCRIPTION "On line status of the unit having serial address 1. "
			::= { unitOnLineStatusGroup 1 }

		-- ... You will have how many unitX-OnLineStatus objects as the value of netSize is

		-- 1.3.6.1.4.1.9839.2.1
        -- rtop_pcoMIB OBJECT IDENTIFIER ::= { instruments 1 }

        -- 1.3.6.1.4.1.9839.2.1.1
        digitalObjects OBJECT IDENTIFIER ::= { rtop_pcoMIB 1 }

        -- 1.3.6.1.4.1.9839.2.1.1.8
        start_stop OBJECT-TYPE
                    SYNTAX Integer32 (0..1)
                    UNITS "N/A"
                    MAX-ACCESS read-write
                    STATUS current
                    DESCRIPTION "Remote ON / OFF"
                    DEFVAL { 0 }
                    ::= { digitalObjects 8 }

        -- 1.3.6.1.4.1.9839.2.1.1.15
        ventilatore_p OBJECT-TYPE
                    SYNTAX Integer32 (0..1)
                    UNITS "N/A"
                    MAX-ACCESS read-only
                    STATUS current
                    DESCRIPTION "Main fan"
                    ::= { digitalObjects 15 }

        -- 1.3.6.1.4.1.9839.2.1.1.16
        cont_avv_a1 OBJECT-TYPE
                    SYNTAX Integer32 (0..1)
                    UNITS "N/A"
                    MAX-ACCESS read-only
                    STATUS current
                    DESCRIPTION "Compressor 1"
                    ::= { digitalObjects 16 }

        -- 1.3.6.1.4.1.9839.2.1.1.17
        cont_avv_a2 OBJECT-TYPE
                    SYNTAX Integer32 (0..1)
                    UNITS "N/A"
                    MAX-ACCESS read-only
                    STATUS current
                    DESCRIPTION "Compressor 2"
                    ::= { digitalObjects 17 }

        -- 1.3.6.1.4.1.9839.2.1.1.20
        resistenza1 OBJECT-TYPE
                    SYNTAX Integer32 (0..1)
                    UNITS "N/A"
                    MAX-ACCESS read-only
                    STATUS current
                    DESCRIPTION "Heater n.1"
                    ::= { digitalObjects 20 }

        -- 1.3.6.1.4.1.9839.2.1.1.21
        resistenza2 OBJECT-TYPE
                    SYNTAX Integer32 (0..1)
                    UNITS "N/A"
                    MAX-ACCESS read-only
                    STATUS current
                    DESCRIPTION "Heater n.2"
                    ::= { digitalObjects 21 }

        -- 1.3.6.1.4.1.9839.2.1.1.22
        umidifica OBJECT-TYPE
                    SYNTAX Integer32 (0..1)
                    UNITS "N/A"
                    MAX-ACCESS read-only
                    STATUS current
                    DESCRIPTION "Humidification"
                    ::= { digitalObjects 22 }

        -- 1.3.6.1.4.1.9839.2.1.1.23
        ventilatore1 OBJECT-TYPE
                    SYNTAX Integer32 (0..1)
                    UNITS "N/A"
                    MAX-ACCESS read-only
                    STATUS current
                    DESCRIPTION "Fan n.1"
                    ::= { digitalObjects 23 }

        -- 1.3.6.1.4.1.9839.2.1.1.24
        ventilatore2 OBJECT-TYPE
                    SYNTAX Integer32 (0..1)
                    UNITS "N/A"
                    MAX-ACCESS read-only
                    STATUS current
                    DESCRIPTION "Fan n.2"
                    ::= { digitalObjects 24 }

        -- 1.3.6.1.4.1.9839.2.1.1.26
        glb_al OBJECT-TYPE
                    SYNTAX Integer32 (0..1)
                    UNITS "N/A"
                    MAX-ACCESS read-only
                    STATUS current
                    DESCRIPTION "General alarm"
                    ::= { digitalObjects 26 }

        -- 1.3.6.1.4.1.9839.2.1.1.27
        mask_term1 OBJECT-TYPE
                    SYNTAX Integer32 (0..1)
                    UNITS "N/A"
                    MAX-ACCESS read-only
                    STATUS current
                    DESCRIPTION "Compressor n°1 overload alarm"
                    ::= { digitalObjects 27 }

        -- 1.3.6.1.4.1.9839.2.1.1.28
        mask_term2 OBJECT-TYPE
                    SYNTAX Integer32 (0..1)
                    UNITS "N/A"
                    MAX-ACCESS read-only
                    STATUS current
                    DESCRIPTION "Compressor n°2 overload alarm"
                    ::= { digitalObjects 28 }

        -- 1.3.6.1.4.1.9839.2.1.1.29
        mask_press_h1 OBJECT-TYPE
                    SYNTAX Integer32 (0..1)
                    UNITS "N/A"
                    MAX-ACCESS read-only
                    STATUS current
                    DESCRIPTION "Alarm: high pressure pressostat circuit n°1"
                    ::= { digitalObjects 29 }

        -- 1.3.6.1.4.1.9839.2.1.1.30
        mask_press_h2 OBJECT-TYPE
                    SYNTAX Integer32 (0..1)
                    UNITS "N/A"
                    MAX-ACCESS read-only
                    STATUS current
                    DESCRIPTION "Alarm: high pressure pressostat circuit n°2"
                    ::= { digitalObjects 30 }

        -- 1.3.6.1.4.1.9839.2.1.1.31
        mask_antigelo OBJECT-TYPE
                    SYNTAX Integer32 (0..1)
                    UNITS "N/A"
                    MAX-ACCESS read-only
                    STATUS current
                    DESCRIPTION "Antifreeze alarm"
                    ::= { digitalObjects 31 }

        -- 1.3.6.1.4.1.9839.2.1.1.32
        mask_q14 OBJECT-TYPE
                    SYNTAX Integer32 (0..1)
                    UNITS "N/A"
                    MAX-ACCESS read-only
                    STATUS current
                    DESCRIPTION "Data acquisition failure - eeprom"
                    ::= { digitalObjects 32 }

        -- 1.3.6.1.4.1.9839.2.1.1.33
        mask_q15 OBJECT-TYPE
                    SYNTAX Integer32 (0..1)
                    UNITS "N/A"
                    MAX-ACCESS read-only
                    STATUS current
                    DESCRIPTION "Clock board faulty"
                    DEFVAL { 0 }
                    ::= { digitalObjects 33 }

        -- 1.3.6.1.4.1.9839.2.1.1.34
        mask_q3 OBJECT-TYPE
                    SYNTAX Integer32 (0..1)
                    UNITS "N/A"
                    MAX-ACCESS read-only
                    STATUS current
                    DESCRIPTION "Inlet air high temperature alarm"
                    ::= { digitalObjects 34 }

        -- 1.3.6.1.4.1.9839.2.1.1.35
        mask_q4 OBJECT-TYPE
                    SYNTAX Integer32 (0..1)
                    UNITS "N/A"
                    MAX-ACCESS read-only
                    STATUS current
                    DESCRIPTION "Inlet air low temperature alarm"
                    ::= { digitalObjects 35 }

        -- 1.3.6.1.4.1.9839.2.1.1.36
        mask_q5 OBJECT-TYPE
                    SYNTAX Integer32 (0..1)
                    UNITS "N/A"
                    MAX-ACCESS read-only
                    STATUS current
                    DESCRIPTION "Maintenance compressor n°1"
                    ::= { digitalObjects 36 }

        -- 1.3.6.1.4.1.9839.2.1.1.37
        mask_q6 OBJECT-TYPE
                    SYNTAX Integer32 (0..1)
                    UNITS "N/A"
                    MAX-ACCESS read-only
                    STATUS current
                    DESCRIPTION "Maintenance compressor n°2"
                    ::= { digitalObjects 37 }

        -- 1.3.6.1.4.1.9839.2.1.1.38
        bassa_press1 OBJECT-TYPE
                    SYNTAX Integer32 (0..1)
                    UNITS "N/A"
                    MAX-ACCESS read-only
                    STATUS current
                    DESCRIPTION "Alarm: low pressure pressostat circuit n°1"
                    ::= { digitalObjects 38 }

        -- 1.3.6.1.4.1.9839.2.1.1.39
        bassa_press2 OBJECT-TYPE
                    SYNTAX Integer32 (0..1)
                    UNITS "N/A"
                    MAX-ACCESS read-only
                    STATUS current
                    DESCRIPTION "Alarm: low pressure pressostat circuit n°2"
                    ::= { digitalObjects 39 }

        -- 1.3.6.1.4.1.9839.2.1.1.40
        mask_interbl OBJECT-TYPE
                    SYNTAX Integer32 (0..1)
                    UNITS "N/A"
                    MAX-ACCESS read-only
                    STATUS current
                    DESCRIPTION "Generic lock alarm"
                    ::= { digitalObjects 40 }

        -- 1.3.6.1.4.1.9839.2.1.1.41
        mask_defrost1 OBJECT-TYPE
                    SYNTAX Integer32 (0..1)
                    UNITS "N/A"
                    MAX-ACCESS read-only
                    STATUS current
                    DESCRIPTION "Circuit n°1 defrost probe alarm"
                    ::= { digitalObjects 41 }

        -- 1.3.6.1.4.1.9839.2.1.1.42
        mask_defrost2 OBJECT-TYPE
                    SYNTAX Integer32 (0..1)
                    UNITS "N/A"
                    MAX-ACCESS read-only
                    STATUS current
                    DESCRIPTION "Circuit n°2 defrost probe alarm"
                    ::= { digitalObjects 42 }

        -- 1.3.6.1.4.1.9839.2.1.1.43
        mask_filtro OBJECT-TYPE
                    SYNTAX Integer32 (0..1)
                    UNITS "N/A"
                    MAX-ACCESS read-only
                    STATUS current
                    DESCRIPTION "Clogged filter alarm"
                    ::= { digitalObjects 43 }

        -- 1.3.6.1.4.1.9839.2.1.1.44
        mask_term_res OBJECT-TYPE
                    SYNTAX Integer32 (0..1)
                    UNITS "N/A"
                    MAX-ACCESS read-only
                    STATUS current
                    DESCRIPTION "Heaters overload alarm"
                    ::= { digitalObjects 44 }

        -- 1.3.6.1.4.1.9839.2.1.1.45
        en_pompacalore OBJECT-TYPE
                    SYNTAX Integer32 (0..1)
                    UNITS "N/A"
                    MAX-ACCESS read-write
                    STATUS current
                    DESCRIPTION "Enabling of functioning as heatpump"
                    DEFVAL { 0 }
                    ::= { digitalObjects 45 }

        -- 1.3.6.1.4.1.9839.2.1.1.46
        en_orologio OBJECT-TYPE
                    SYNTAX Integer32 (0..1)
                    UNITS "N/A"
                    MAX-ACCESS read-write
                    STATUS current
                    DESCRIPTION "Enabling of clock board"
                    DEFVAL { 0 }
                    ::= { digitalObjects 46 }

        -- 1.3.6.1.4.1.9839.2.1.1.47
        en_umidita OBJECT-TYPE
                    SYNTAX Integer32 (0..1)
                    UNITS "N/A"
                    MAX-ACCESS read-write
                    STATUS current
                    DESCRIPTION "Enabling of humidity function"
                    DEFVAL { 0 }
                    ::= { digitalObjects 47 }

        -- 1.3.6.1.4.1.9839.2.1.1.48
        en_mandata OBJECT-TYPE
                    SYNTAX Integer32 (0..1)
                    UNITS "N/A"
                    MAX-ACCESS read-write
                    STATUS current
                    DESCRIPTION "Enabling of outlet air temperature probe"
                    DEFVAL { 0 }
                    ::= { digitalObjects 48 }

        -- 1.3.6.1.4.1.9839.2.1.1.50
        en_supervisore OBJECT-TYPE
                    SYNTAX Integer32 (0..1)
                    UNITS "N/A"
                    MAX-ACCESS read-write
                    STATUS current
                    DESCRIPTION "Enabling of supervisory serial board"
                    DEFVAL { 0 }
                    ::= { digitalObjects 50 }

        -- 1.3.6.1.4.1.9839.2.1.1.51
        en_stampante OBJECT-TYPE
                    SYNTAX Integer32 (0..1)
                    UNITS "N/A"
                    MAX-ACCESS read-write
                    STATUS current
                    DESCRIPTION "Enabling of printer"
                    DEFVAL { 0 }
                    ::= { digitalObjects 51 }

        -- 1.3.6.1.4.1.9839.2.1.1.52
        en_freecool OBJECT-TYPE
                    SYNTAX Integer32 (0..1)
                    UNITS "N/A"
                    MAX-ACCESS read-write
                    STATUS current
                    DESCRIPTION "Enabling of summer freecooling"
                    DEFVAL { 0 }
                    ::= { digitalObjects 52 }

        -- 1.3.6.1.4.1.9839.2.1.1.53
        en_freeheat OBJECT-TYPE
                    SYNTAX Integer32 (0..1)
                    UNITS "N/A"
                    MAX-ACCESS read-write
                    STATUS current
                    DESCRIPTION "Enabling of winter freeheating"
                    DEFVAL { 1 }
                    ::= { digitalObjects 53 }

        -- 1.3.6.1.4.1.9839.2.1.1.55
        en_compensazio OBJECT-TYPE
                    SYNTAX Integer32 (0..1)
                    UNITS "N/A"
                    MAX-ACCESS read-write
                    STATUS current
                    DESCRIPTION "Enabling of compensation"
                    DEFVAL { 0 }
                    ::= { digitalObjects 55 }

        -- 1.3.6.1.4.1.9839.2.1.1.56
        off_ventp_defr OBJECT-TYPE
                    SYNTAX Integer32 (0..1)
                    UNITS "N/A"
                    MAX-ACCESS read-write
                    STATUS current
                    DESCRIPTION "Enabling of main fan OFF during defrost"
                    DEFVAL { 1 }
                    ::= { digitalObjects 56 }

        -- 1.3.6.1.4.1.9839.2.1.1.57
        en_sbrin_cont OBJECT-TYPE
                    SYNTAX Integer32 (0..1)
                    UNITS "N/A"
                    MAX-ACCESS read-write
                    STATUS current
                    DESCRIPTION "Enabling of simultaneous defrost"
                    DEFVAL { 0 }
                    ::= { digitalObjects 57 }

        -- 1.3.6.1.4.1.9839.2.1.1.58
        autostart OBJECT-TYPE
                    SYNTAX Integer32 (0..1)
                    UNITS "N/A"
                    MAX-ACCESS read-write
                    STATUS current
                    DESCRIPTION "Enabling of automatic restart"
                    DEFVAL { 1 }
                    ::= { digitalObjects 58 }

        -- 1.3.6.1.4.1.9839.2.1.1.59
        en_remoto OBJECT-TYPE
                    SYNTAX Integer32 (0..1)
                    UNITS "N/A"
                    MAX-ACCESS read-write
                    STATUS current
                    DESCRIPTION "Enabling of remote ON / OFF"
                    DEFVAL { 0 }
                    ::= { digitalObjects 59 }

        -- 1.3.6.1.4.1.9839.2.1.1.64
        abil_rotaz OBJECT-TYPE
                    SYNTAX Integer32 (0..1)
                    UNITS "N/A"
                    MAX-ACCESS read-write
                    STATUS current
                    DESCRIPTION "Enabling of compressors rotation"
                    DEFVAL { 1 }
                    ::= { digitalObjects 64 }

        -- 1.3.6.1.4.1.9839.2.1.1.65
        sys_on OBJECT-TYPE
                    SYNTAX Integer32 (0..1)
                    UNITS "N/A"
                    MAX-ACCESS read-write
                    STATUS current
                    DESCRIPTION "Unit ON / OFF"
                    ::= { digitalObjects 65 }

        -- 1.3.6.1.4.1.9839.2.1.1.74
        syson1 OBJECT-TYPE
                    SYNTAX Integer32 (0..1)
                    UNITS "N/A"
                    MAX-ACCESS read-write
                    STATUS current
                    DESCRIPTION "Visualisation machine state"
                    ::= { digitalObjects 74 }

        -- 1.3.6.1.4.1.9839.2.1.1.75
        en_binati OBJECT-TYPE
                    SYNTAX Integer32 (0..1)
                    UNITS "N/A"
                    MAX-ACCESS read-write
                    STATUS current
                    DESCRIPTION "Enabling of fans shared"
                    DEFVAL { 0 }
                    ::= { digitalObjects 75 }

        -- 1.3.6.1.4.1.9839.2.1.1.76
        en_sond_text OBJECT-TYPE
                    SYNTAX Integer32 (0..1)
                    UNITS "N/A"
                    MAX-ACCESS read-write
                    STATUS current
                    DESCRIPTION "Enabling of external air temperature probe"
                    DEFVAL { 0 }
                    ::= { digitalObjects 76 }

        -- 1.3.6.1.4.1.9839.2.1.1.77
        en_sond_uext OBJECT-TYPE
                    SYNTAX Integer32 (0..1)
                    UNITS "N/A"
                    MAX-ACCESS read-write
                    STATUS current
                    DESCRIPTION "Enabling of external humidity probe"
                    DEFVAL { 0 }
                    ::= { digitalObjects 77 }

        -- 1.3.6.1.4.1.9839.2.1.1.78
        en_sond_def1 OBJECT-TYPE
                    SYNTAX Integer32 (0..1)
                    UNITS "N/A"
                    MAX-ACCESS read-write
                    STATUS current
                    DESCRIPTION "Enabling of Defrost / Condens.1 probe"
                    DEFVAL { 0 }
                    ::= { digitalObjects 78 }

        -- 1.3.6.1.4.1.9839.2.1.1.79
        en_sond_def2 OBJECT-TYPE
                    SYNTAX Integer32 (0..1)
                    UNITS "N/A"
                    MAX-ACCESS read-write
                    STATUS current
                    DESCRIPTION "Enabling of Defrost / Condens.2 probe"
                    DEFVAL { 0 }
                    ::= { digitalObjects 79 }

        -- 1.3.6.1.4.1.9839.2.1.1.86
        tipo_cont OBJECT-TYPE
                    SYNTAX Integer32 (0..1)
                    UNITS "N/A"
                    MAX-ACCESS read-write
                    STATUS current
                    DESCRIPTION "Control type: Temp or Enthalpy"
                    DEFVAL { 1 }
                    ::= { digitalObjects 86 }



        -- 1.3.6.1.4.1.9839.2.1.2
        analogObjects OBJECT IDENTIFIER ::= { rtop_pcoMIB 2 }

        -- 1.3.6.1.4.1.9839.2.1.2.1
        temp_aria_amb OBJECT-TYPE
                    SYNTAX Integer32 (0..999990)
                    UNITS "°C x10"
                    MAX-ACCESS read-only
                    STATUS current
                    DESCRIPTION "Recirculated air temperature"
                    DEFVAL { 0 }
                    ::= { analogObjects 1 }

        -- 1.3.6.1.4.1.9839.2.1.2.2
        temp_aria_est OBJECT-TYPE
                    SYNTAX Integer32 (-32767..32767)
                    UNITS "°C x10"
                    MAX-ACCESS read-only
                    STATUS current
                    DESCRIPTION "External air temperature"
                    DEFVAL { 0 }
                    ::= { analogObjects 2 }

        -- 1.3.6.1.4.1.9839.2.1.2.5
        umid_ambiente OBJECT-TYPE
                    SYNTAX Integer32 (-32767..32767)
                    UNITS "°C x10"
                    MAX-ACCESS read-only
                    STATUS current
                    DESCRIPTION "Recirculated air relative humidity"
                    ::= { analogObjects 5 }

        -- 1.3.6.1.4.1.9839.2.1.2.6
        umid_esterna OBJECT-TYPE
                    SYNTAX Integer32 (30..130)
                    UNITS "°C x10"
                    MAX-ACCESS read-only
                    STATUS current
                    DESCRIPTION "External air relative humidity"
                    DEFVAL { 0 }
                    ::= { analogObjects 6 }

        -- 1.3.6.1.4.1.9839.2.1.2.15
        set_temp_ariae OBJECT-TYPE
                    SYNTAX Integer32 (-32767..32767)
                    UNITS "N/A"
                    MAX-ACCESS read-write
                    STATUS current
                    DESCRIPTION "Summer Temp. Setpoint"
                    ::= { analogObjects 15 }

        -- 1.3.6.1.4.1.9839.2.1.2.16
        set_temp_ariai OBJECT-TYPE
                    SYNTAX Integer32 (-32767..32767)
                    UNITS "N/A"
                    MAX-ACCESS read-write
                    STATUS current
                    DESCRIPTION "Winter Temp. Setpoint"
                    ::= { analogObjects 16 }

        -- 1.3.6.1.4.1.9839.2.1.2.17
        set_umid_est OBJECT-TYPE
                    SYNTAX Integer32 (-32767..32767)
                    UNITS "N/A"
                    MAX-ACCESS read-write
                    STATUS current
                    DESCRIPTION "Summer Humid.Setpoint"
                    ::= { analogObjects 17 }

        -- 1.3.6.1.4.1.9839.2.1.2.18
        set_umid_inv OBJECT-TYPE
                    SYNTAX Integer32 (-32767..32767)
                    UNITS "N/A"
                    MAX-ACCESS read-write
                    STATUS current
                    DESCRIPTION "Winter Humid.Setpoint"
                    ::= { analogObjects 18 }

        -- 1.3.6.1.4.1.9839.2.1.2.19
        lim_sup_temp OBJECT-TYPE
                    SYNTAX Integer32 (-9990..9990)
                    UNITS "°C x10"
                    MAX-ACCESS read-write
                    STATUS current
                    DESCRIPTION "Temperature set-point selection higher limit"
                    DEFVAL { 350 }
                    ::= { analogObjects 19 }

        -- 1.3.6.1.4.1.9839.2.1.2.20
        lim_inf_temp OBJECT-TYPE
                    SYNTAX Integer32 (-9990..9990)
                    UNITS "°C x10"
                    MAX-ACCESS read-write
                    STATUS current
                    DESCRIPTION "Temperature set-point selection lower limit"
                    DEFVAL { 50 }
                    ::= { analogObjects 20 }

        -- 1.3.6.1.4.1.9839.2.1.2.21
        banda_temp_e OBJECT-TYPE
                    SYNTAX Integer32 (0..150)
                    UNITS "°C x10"
                    MAX-ACCESS read-write
                    STATUS current
                    DESCRIPTION "Summer temperature differential"
                    DEFVAL { 30 }
                    ::= { analogObjects 21 }

        -- 1.3.6.1.4.1.9839.2.1.2.22
        banda_temp_i OBJECT-TYPE
                    SYNTAX Integer32 (0..150)
                    UNITS "°C x10"
                    MAX-ACCESS read-write
                    STATUS current
                    DESCRIPTION "Winter temperature differential"
                    DEFVAL { 30 }
                    ::= { analogObjects 22 }

        -- 1.3.6.1.4.1.9839.2.1.2.23
        lim_sup_umid OBJECT-TYPE
                    SYNTAX Integer32 (-9990..9990)
                    UNITS "% x10"
                    MAX-ACCESS read-write
                    STATUS current
                    DESCRIPTION "Humidity set point selection higher limit"
                    DEFVAL { 800 }
                    ::= { analogObjects 23 }

        -- 1.3.6.1.4.1.9839.2.1.2.24
        lim_inf_umid OBJECT-TYPE
                    SYNTAX Integer32 (-9990..9990)
                    UNITS "% x10"
                    MAX-ACCESS read-write
                    STATUS current
                    DESCRIPTION "Humidity set point selection lower limit"
                    DEFVAL { 250 }
                    ::= { analogObjects 24 }

        -- 1.3.6.1.4.1.9839.2.1.2.25
        diff_umid_e OBJECT-TYPE
                    SYNTAX Integer32 (0..2000)
                    UNITS "% x10"
                    MAX-ACCESS read-write
                    STATUS current
                    DESCRIPTION "Summer humidity differential"
                    DEFVAL { 50 }
                    ::= { analogObjects 25 }

        -- 1.3.6.1.4.1.9839.2.1.2.26
        diff_umid_i OBJECT-TYPE
                    SYNTAX Integer32 (0..2000)
                    UNITS "% x10"
                    MAX-ACCESS read-write
                    STATUS current
                    DESCRIPTION "Winter humidity differential"
                    DEFVAL { 50 }
                    ::= { analogObjects 26 }

        -- 1.3.6.1.4.1.9839.2.1.2.28
        offset_fcool OBJECT-TYPE
                    SYNTAX Integer32 (-9990..9990)
                    UNITS "°C x10"
                    MAX-ACCESS read-write
                    STATUS current
                    DESCRIPTION "Summer freecooling valve: Offset"
                    DEFVAL { -20 }
                    ::= { analogObjects 28 }

        -- 1.3.6.1.4.1.9839.2.1.2.29
        diff_fcool OBJECT-TYPE
                    SYNTAX Integer32 (-9990..9990)
                    UNITS "°C x10"
                    MAX-ACCESS read-write
                    STATUS current
                    DESCRIPTION "Summer freecooling valve: Differential"
                    DEFVAL { 20 }
                    ::= { analogObjects 29 }

        -- 1.3.6.1.4.1.9839.2.1.2.30
        offset_fheat OBJECT-TYPE
                    SYNTAX Integer32 (-9990..9990)
                    UNITS "°C x10"
                    MAX-ACCESS read-write
                    STATUS current
                    DESCRIPTION "Winter freecooling valve: Offset"
                    DEFVAL { 20 }
                    ::= { analogObjects 30 }

        -- 1.3.6.1.4.1.9839.2.1.2.31
        diff_fheat OBJECT-TYPE
                    SYNTAX Integer32 (-9990..9990)
                    UNITS "°C x10"
                    MAX-ACCESS read-write
                    STATUS current
                    DESCRIPTION "Winter freecooling valve: Differential"
                    DEFVAL { 20 }
                    ::= { analogObjects 31 }

        -- 1.3.6.1.4.1.9839.2.1.2.32
        set_mandata OBJECT-TYPE
                    SYNTAX Integer32 (-9990..9990)
                    UNITS "°C x10"
                    MAX-ACCESS read-write
                    STATUS current
                    DESCRIPTION "Minimun outlet air temperature control set-point"
                    DEFVAL { 150 }
                    ::= { analogObjects 32 }

        -- 1.3.6.1.4.1.9839.2.1.2.33
        ban_mandata OBJECT-TYPE
                    SYNTAX Integer32 (-9990..9990)
                    UNITS "°C x10"
                    MAX-ACCESS read-write
                    STATUS current
                    DESCRIPTION "Minimun outlet air temperature control differential"
                    DEFVAL { 30 }
                    ::= { analogObjects 33 }

        -- 1.3.6.1.4.1.9839.2.1.2.34
        set_esterno OBJECT-TYPE
                    SYNTAX Integer32 (-9990..9990)
                    UNITS "°C x10"
                    MAX-ACCESS read-write
                    STATUS current
                    DESCRIPTION "Summer compensation control set-point"
                    DEFVAL { 300 }
                    ::= { analogObjects 34 }

        -- 1.3.6.1.4.1.9839.2.1.2.35
        diff_esterno_e OBJECT-TYPE
                    SYNTAX Integer32 (-9990..9990)
                    UNITS "°C x10"
                    MAX-ACCESS read-write
                    STATUS current
                    DESCRIPTION "Summer compensation control differential"
                    DEFVAL { 300 }
                    ::= { analogObjects 35 }

        -- 1.3.6.1.4.1.9839.2.1.2.36
        max_comp_e OBJECT-TYPE
                    SYNTAX Integer32 (0..9990)
                    UNITS "°C x10"
                    MAX-ACCESS read-write
                    STATUS current
                    DESCRIPTION "Maximun summer compensation"
                    DEFVAL { 50 }
                    ::= { analogObjects 36 }

        -- 1.3.6.1.4.1.9839.2.1.2.37
        set_min OBJECT-TYPE
                    SYNTAX Integer32 (-500..500)
                    UNITS "°C x10"
                    MAX-ACCESS read-write
                    STATUS current
                    DESCRIPTION "Defrost starting Set"
                    DEFVAL { -20 }
                    ::= { analogObjects 37 }

        -- 1.3.6.1.4.1.9839.2.1.2.38
        set_stop OBJECT-TYPE
                    SYNTAX Integer32 (-500..500)
                    UNITS "°C x10"
                    MAX-ACCESS read-write
                    STATUS current
                    DESCRIPTION "Defrost stop Set"
                    DEFVAL { 140 }
                    ::= { analogObjects 38 }

        -- 1.3.6.1.4.1.9839.2.1.2.39
        zona_morta OBJECT-TYPE
                    SYNTAX Integer32 (0..30)
                    UNITS "°C x10"
                    MAX-ACCESS read-write
                    STATUS current
                    DESCRIPTION "Temperature regulation dead zone"
                    DEFVAL { 0 }
                    ::= { analogObjects 39 }

        -- 1.3.6.1.4.1.9839.2.1.2.40
        zona_morta_u OBJECT-TYPE
                    SYNTAX Integer32 (0..30)
                    UNITS "% x10"
                    MAX-ACCESS read-write
                    STATUS current
                    DESCRIPTION "Humidity regulation dead zone"
                    DEFVAL { 0 }
                    ::= { analogObjects 40 }

        -- 1.3.6.1.4.1.9839.2.1.2.41
        sg_alta_in_e OBJECT-TYPE
                    SYNTAX Integer32 (-9990..9990)
                    UNITS "°C x10"
                    MAX-ACCESS read-write
                    STATUS current
                    DESCRIPTION "Summer recirculated air temperature high threshold"
                    DEFVAL { 320 }
                    ::= { analogObjects 41 }

        -- 1.3.6.1.4.1.9839.2.1.2.42
        sg_bassa_in_e OBJECT-TYPE
                    SYNTAX Integer32 (-9990..9990)
                    UNITS "°C x10"
                    MAX-ACCESS read-write
                    STATUS current
                    DESCRIPTION "Summer recirculated air temperature low threshold"
                    DEFVAL { 200 }
                    ::= { analogObjects 42 }

        -- 1.3.6.1.4.1.9839.2.1.2.43
        sg_alta_in_i OBJECT-TYPE
                    SYNTAX Integer32 (-9990..9990)
                    UNITS "°C x10"
                    MAX-ACCESS read-write
                    STATUS current
                    DESCRIPTION "Winter recirculated air temperature high threshold"
                    DEFVAL { 260 }
                    ::= { analogObjects 43 }

        -- 1.3.6.1.4.1.9839.2.1.2.44
        sg_bassa_in_i OBJECT-TYPE
                    SYNTAX Integer32 (-9990..9990)
                    UNITS "°C x10"
                    MAX-ACCESS read-write
                    STATUS current
                    DESCRIPTION "Winter recirculated air temperature low threshold"
                    DEFVAL { 170 }
                    ::= { analogObjects 44 }

        -- 1.3.6.1.4.1.9839.2.1.2.48
        tar_defrost1 OBJECT-TYPE
                    SYNTAX Integer32 (-990..990)
                    UNITS "°C x10"
                    MAX-ACCESS read-write
                    STATUS current
                    DESCRIPTION "Defrost 1 temperature calibration"
                    DEFVAL { 0 }
                    ::= { analogObjects 48 }

        -- 1.3.6.1.4.1.9839.2.1.2.49
        tar_defrost2 OBJECT-TYPE
                    SYNTAX Integer32 (-990..990)
                    UNITS "°C x10"
                    MAX-ACCESS read-write
                    STATUS current
                    DESCRIPTION "Defrost 2 temperature calibration"
                    DEFVAL { 0 }
                    ::= { analogObjects 49 }

        -- 1.3.6.1.4.1.9839.2.1.2.52
        offset_res OBJECT-TYPE
                    SYNTAX Integer32 (-9990..9990)
                    UNITS "°C x10"
                    MAX-ACCESS read-write
                    STATUS current
                    DESCRIPTION "Heaters regulation Offset"
                    DEFVAL { -20 }
                    ::= { analogObjects 52 }

        -- 1.3.6.1.4.1.9839.2.1.2.53
        differ_res OBJECT-TYPE
                    SYNTAX Integer32 (-9990..9990)
                    UNITS "°C x10"
                    MAX-ACCESS read-write
                    STATUS current
                    DESCRIPTION "Heaters regulation differential"
                    DEFVAL { 20 }
                    ::= { analogObjects 53 }

        -- 1.3.6.1.4.1.9839.2.1.2.54
        tar_umid_amb OBJECT-TYPE
                    SYNTAX Integer32 (20..130)
                    UNITS "°C x10"
                    MAX-ACCESS read-write
                    STATUS current
                    DESCRIPTION "Recirculated air humidity calibration"
                    DEFVAL { 0 }
                    ::= { analogObjects 54 }

        -- 1.3.6.1.4.1.9839.2.1.2.62
        offset_valv OBJECT-TYPE
                    SYNTAX Integer32 (-9990..9990)
                    UNITS "°C x10"
                    MAX-ACCESS read-write
                    STATUS current
                    DESCRIPTION "Heating valve Offset"
                    DEFVAL { -20 }
                    ::= { analogObjects 62 }

        -- 1.3.6.1.4.1.9839.2.1.2.63
        diff_valv OBJECT-TYPE
                    SYNTAX Integer32 (-9990..9990)
                    UNITS "°C x10"
                    MAX-ACCESS read-write
                    STATUS current
                    DESCRIPTION "Heating valve differential"
                    DEFVAL { 20 }
                    ::= { analogObjects 63 }

        -- 1.3.6.1.4.1.9839.2.1.2.64
        set_esternoi OBJECT-TYPE
                    SYNTAX Integer32 (-9990..9990)
                    UNITS "°C x10"
                    MAX-ACCESS read-write
                    STATUS current
                    DESCRIPTION "External temperature set-point for Winter compensation"
                    DEFVAL { 50 }
                    ::= { analogObjects 64 }

        -- 1.3.6.1.4.1.9839.2.1.2.66
        max_comp_i OBJECT-TYPE
                    SYNTAX Integer32 (0..9990)
                    UNITS "°C x10"
                    MAX-ACCESS read-write
                    STATUS current
                    DESCRIPTION "Maximun Winter compensation"
                    DEFVAL { 50 }
                    ::= { analogObjects 66 }

        -- 1.3.6.1.4.1.9839.2.1.2.67
        set_vent1 OBJECT-TYPE
                    SYNTAX Integer32 (0..9990)
                    UNITS "°C x10"
                    MAX-ACCESS read-write
                    STATUS current
                    DESCRIPTION "Set-point fan 1: condensing control"
                    DEFVAL { 500 }
                    ::= { analogObjects 67 }

        -- 1.3.6.1.4.1.9839.2.1.2.68
        set_vent2 OBJECT-TYPE
                    SYNTAX Integer32 (0..9990)
                    UNITS "°C x10"
                    MAX-ACCESS read-write
                    STATUS current
                    DESCRIPTION "Set-point fan 2: condensing control"
                    DEFVAL { 400 }
                    ::= { analogObjects 68 }

        -- 1.3.6.1.4.1.9839.2.1.2.69
        diff_vent1 OBJECT-TYPE
                    SYNTAX Integer32 (0..9990)
                    UNITS "°C x10"
                    MAX-ACCESS read-write
                    STATUS current
                    DESCRIPTION "Diferential fan 1: condensing control"
                    DEFVAL { 50 }
                    ::= { analogObjects 69 }

        -- 1.3.6.1.4.1.9839.2.1.2.70
        diff_vent2 OBJECT-TYPE
                    SYNTAX Integer32 (0..9990)
                    UNITS "°C x10"
                    MAX-ACCESS read-write
                    STATUS current
                    DESCRIPTION "Diferential fan 2: condensing control"
                    DEFVAL { 50 }
                    ::= { analogObjects 70 }



        -- 1.3.6.1.4.1.9839.2.1.3
        integerObjects OBJECT IDENTIFIER ::= { rtop_pcoMIB 3 }

        -- 1.3.6.1.4.1.9839.2.1.3.10
        ore_comp1 OBJECT-TYPE
                    SYNTAX Integer32 (1..15)
                    UNITS "N/A"
                    MAX-ACCESS read-write
                    STATUS current
                    DESCRIPTION "Working hours compressorn.1"
                    DEFVAL { 10000 }
                    ::= { integerObjects 10 }

        -- 1.3.6.1.4.1.9839.2.1.3.11
        ore_comp2 OBJECT-TYPE
                    SYNTAX Integer32 (1..15)
                    UNITS "N/A"
                    MAX-ACCESS read-write
                    STATUS current
                    DESCRIPTION "Working hours compressorn.2"
                    DEFVAL { 10000 }
                    ::= { integerObjects 11 }

        -- 1.3.6.1.4.1.9839.2.1.3.19
        rit_all_ht_in OBJECT-TYPE
                    SYNTAX Integer32 (0..999)
                    UNITS "sec"
                    MAX-ACCESS read-write
                    STATUS current
                    DESCRIPTION "Recirculated air High / Low temperature alarm delay"
                    DEFVAL { 30 }
                    ::= { integerObjects 19 }

        -- 1.3.6.1.4.1.9839.2.1.3.20
        rit_all_press OBJECT-TYPE
                    SYNTAX Integer32 (-32767..32767)
                    UNITS "sec"
                    MAX-ACCESS read-write
                    STATUS current
                    DESCRIPTION "Low pressure alarm delay"
                    DEFVAL { 120 }
                    ::= { integerObjects 20 }

        -- 1.3.6.1.4.1.9839.2.1.3.23
        n_comp_deum OBJECT-TYPE
                    SYNTAX Integer32 (0..2)
                    UNITS "N/A"
                    MAX-ACCESS read-write
                    STATUS current
                    DESCRIPTION "Number of dehumidifying compessor"
                    DEFVAL { 1 }
                    ::= { integerObjects 23 }

        -- 1.3.6.1.4.1.9839.2.1.3.24
        rit_stop_ventp OBJECT-TYPE
                    SYNTAX Integer32 (0..999)
                    UNITS "sec"
                    MAX-ACCESS read-write
                    STATUS current
                    DESCRIPTION "Main fan OFF delay"
                    DEFVAL { 20 }
                    ::= { integerObjects 24 }

        -- 1.3.6.1.4.1.9839.2.1.3.25
        rit_part_comp OBJECT-TYPE
                    SYNTAX Integer32 (0..999)
                    UNITS "sec"
                    MAX-ACCESS read-write
                    STATUS current
                    DESCRIPTION "Compressor start-up delay"
                    DEFVAL { 60 }
                    ::= { integerObjects 25 }

        -- 1.3.6.1.4.1.9839.2.1.3.26
        rit_interbl OBJECT-TYPE
                    SYNTAX Integer32 (0..999)
                    UNITS "sec"
                    MAX-ACCESS read-write
                    STATUS current
                    DESCRIPTION "Interblock alarm delay time"
                    DEFVAL { 0 }
                    ::= { integerObjects 26 }

        -- 1.3.6.1.4.1.9839.2.1.3.27
        min_sp_comp OBJECT-TYPE
                    SYNTAX Integer32 (0..9999)
                    UNITS "sec"
                    MAX-ACCESS read-write
                    STATUS current
                    DESCRIPTION "Minimun compressor OFF time"
                    DEFVAL { 180 }
                    ::= { integerObjects 27 }

        -- 1.3.6.1.4.1.9839.2.1.3.28
        new_pass_ut OBJECT-TYPE
                    SYNTAX Integer32 (0..32000)
                    UNITS "N/A"
                    MAX-ACCESS read-write
                    STATUS current
                    DESCRIPTION "New user password"
                    DEFVAL { 1234 }
                    ::= { integerObjects 28 }

        -- 1.3.6.1.4.1.9839.2.1.3.30
        new_pass_cos OBJECT-TYPE
                    SYNTAX Integer32 (0..32000)
                    UNITS "N/A"
                    MAX-ACCESS read-write
                    STATUS current
                    DESCRIPTION "New manifacturer password"
                    DEFVAL { 1234 }
                    ::= { integerObjects 30 }

        -- 1.3.6.1.4.1.9839.2.1.3.31
        min_stes_comp OBJECT-TYPE
                    SYNTAX Integer32 (0..9999)
                    UNITS "sec"
                    MAX-ACCESS read-write
                    STATUS current
                    DESCRIPTION "Minimun time between 2 atart-ups of same compressor"
                    DEFVAL { 360 }
                    ::= { integerObjects 31 }

        -- 1.3.6.1.4.1.9839.2.1.3.32
        min_tra_comp OBJECT-TYPE
                    SYNTAX Integer32 (0..9999)
                    UNITS "sec"
                    MAX-ACCESS read-write
                    STATUS current
                    DESCRIPTION "Minimun time between 2 atart-ups of different compressor"
                    DEFVAL { 10 }
                    ::= { integerObjects 32 }

        -- 1.3.6.1.4.1.9839.2.1.3.33
        min_acc_comp OBJECT-TYPE
                    SYNTAX Integer32 (0..9999)
                    UNITS "sec"
                    MAX-ACCESS read-write
                    STATUS current
                    DESCRIPTION "Minimun compressor ON time"
                    DEFVAL { 60 }
                    ::= { integerObjects 33 }

        -- 1.3.6.1.4.1.9839.2.1.3.35
        tempo_max OBJECT-TYPE
                    SYNTAX Integer32 (-32767..32767)
                    UNITS "N/A"
                    MAX-ACCESS read-write
                    STATUS current
                    DESCRIPTION "Maximun duration of defrost"
                    DEFVAL { 1 }
                    ::= { integerObjects 35 }

        -- 1.3.6.1.4.1.9839.2.1.3.36
        min_apertura OBJECT-TYPE
                    SYNTAX Integer32 (0..99)
                    UNITS "%"
                    MAX-ACCESS read-write
                    STATUS current
                    DESCRIPTION "Minimun opening per cent of damper"
                    DEFVAL { 25 }
                    ::= { integerObjects 36 }

        -- 1.3.6.1.4.1.9839.2.1.3.37
        sgl_macchina OBJECT-TYPE
                    SYNTAX Integer32 (0..32000)
                    UNITS "N/A"
                    MAX-ACCESS read-write
                    STATUS current
                    DESCRIPTION "Machine working hours alarm threshold"
                    DEFVAL { 20000 }
                    ::= { integerObjects 37 }

        -- 1.3.6.1.4.1.9839.2.1.3.41
        n_res OBJECT-TYPE
                    SYNTAX Integer32 (0..2)
                    UNITS "N/A"
                    MAX-ACCESS read-write
                    STATUS current
                    DESCRIPTION "Number of heaters"
                    DEFVAL { 0 }
                    ::= { integerObjects 41 }

        -- 1.3.6.1.4.1.9839.2.1.3.42
        tempo_integra OBJECT-TYPE
                    SYNTAX Integer32 (0..9999)
                    UNITS "N/A"
                    MAX-ACCESS read-write
                    STATUS current
                    DESCRIPTION "Integration time for Prop.+ Integr. regulation"
                    DEFVAL { 600 }
                    ::= { integerObjects 42 }



	END

--
-- CAREL-rtop_pco.MIB
--
