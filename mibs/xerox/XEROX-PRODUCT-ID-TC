XEROX-PRODUCT-ID-TC DEFINITIONS ::= BEGIN

-- Module:  XCMI Product Identifier Textual Conventions MIB
--

--
--

IMPORTS
    MODULE-IDENTITY, OBJECT-IDENTITY
            FROM SNMPv2-SMI             -- IETF RFC 1442/1902/2578
    xeroxCommonMIB
            FROM XEROX-COMMON-MIB;

xcmPidTC MODULE-IDENTITY
    LAST-UPDATED "1304100000Z"  -- April 10, 2013 /* VersionUpdate */
    ORGANIZATION "Xerox Corporation -
        Xerox Common Management Interface (XCMI) Working Group"
    CONTACT-INFO "
                      XCMI Editors
        E-Mail:       xcmi.editors@xerox.com

        --
        --
        "

-- /* VersionUpdate */
    DESCRIPTION "
        XCMI Product ID Module,
        Version 6.038.pub

        Copyright (C) 1997-2013 Xerox Corporation. All Rights Reserved."
    ::= { xeroxCommonMIB 62 }
        -- ::= {1.3.6.1.4.1.253.8.62}

xcmPidProductIdentifiers OBJECT-IDENTITY
    STATUS      current
    DESCRIPTION
        "The root of all identifiers defined in this module."
    ::= { xcmPidTC 1 }
        -- ::= {1.3.6.1.4.1.253.8.62.1}

----------------------------------------------------------------
-- Document Centre Systems
----------------------------------------------------------------

xcmPidDocuCentreSystems OBJECT-IDENTITY
    STATUS      current
    DESCRIPTION
        "Document Centre Systems product line identifier
                 (not a complete product identifier)."
    ::= { xcmPidProductIdentifiers 1 }
        -- ::= {1.3.6.1.4.1.253.8.62.1.1}

-- Document Centre/System 20

xcmPidDCS20 OBJECT-IDENTITY
    STATUS      current
    DESCRIPTION
        "Document Centre/System 20 product type identifier
                 (not a complete product identifier)."
    ::= { xcmPidDocuCentreSystems 1 }


        -- ::= {1.3.6.1.4.1.253.8.62.1.1.1}

xcmPidDCS20M1 OBJECT-IDENTITY
    STATUS      current
    DESCRIPTION
        "Document Centre/System 20 launch configuration model
                 identifier (not a complete product identifier)."
    ::= { xcmPidDCS20 1 }
        -- ::= {1.3.6.1.4.1.253.8.62.1.1.1.1}
            -- => SAP PID string = "111"

xcmPidDCS20M1V1 OBJECT-IDENTITY
    STATUS      current
    DESCRIPTION
        "Document Centre/System 20 launch configuration version,
                 and complete product identifier."
    ::= { xcmPidDCS20M1 1 }
        -- ::= {1.3.6.1.4.1.253.8.62.1.1.1.1.1}

-- Document Centre/System 35

xcmPidDCS35 OBJECT-IDENTITY
    STATUS      current
    DESCRIPTION
        "Document Centre/System 35 product type identifier
                 (not a complete product identifier)."
    ::= { xcmPidDocuCentreSystems 2 }
        -- ::= {1.3.6.1.4.1.253.8.62.1.1.2}

xcmPidDCS35M1 OBJECT-IDENTITY
    STATUS      current
    DESCRIPTION
        "Document Centre/System 35 launch configuration model
                 identifier (not a complete product identifier)."
    ::= { xcmPidDCS35 1 }
        -- ::= {1.3.6.1.4.1.253.8.62.1.1.2.1}
            -- => SAP PID string = "121"

xcmPidDCS35M1V1 OBJECT-IDENTITY
    STATUS      current
    DESCRIPTION
        "Document Centre/System 35 launch configuration version,
                 and complete product identifier."
    ::= { xcmPidDCS35M1 1 }
        -- ::= {1.3.6.1.4.1.253.8.62.1.1.2.1.1}

--
--

-- Document Centre 220  (20 ppm)

xcmPidDC220 OBJECT-IDENTITY
    STATUS      current
    DESCRIPTION
        "Document Centre 220 product type identifier
                 (not a complete product identifier)."
    ::= { xcmPidDocuCentreSystems 8 }
        -- ::= {1.3.6.1.4.1.253.8.62.1.1.8}

xcmPidDC220ST OBJECT-IDENTITY
    STATUS      current
    DESCRIPTION
        "Document Centre 220ST multi-function system
                 model identifier (not a complete product identifier)."
    ::= { xcmPidDC220 1 }
        -- ::= {1.3.6.1.4.1.253.8.62.1.1.8.1}
            -- => SAP PID string = "181"

xcmPidDC220STV3 OBJECT-IDENTITY
    STATUS      current
    DESCRIPTION
        "Document Centre 220ST multi-function system
                 second post-launch configuration version, and
                 complete product identifier."
    ::= { xcmPidDC220ST 3 }
        -- ::= {1.3.6.1.4.1.253.8.62.1.1.8.1.3}

xcmPidDC220STV4 OBJECT-IDENTITY
    STATUS      current
    DESCRIPTION
        "Document Centre 220ST multi-function system
                 third post-launch configuration version, and
                 complete product identifier."
    ::= { xcmPidDC220ST 4 }
        -- ::= {1.3.6.1.4.1.253.8.62.1.1.8.1.4}

-- Document Centre 230  (30 ppm)

xcmPidDC230 OBJECT-IDENTITY
    STATUS      current
    DESCRIPTION
        "Document Centre 230 product type identifier
                 (not a complete product identifier)."
    ::= { xcmPidDocuCentreSystems 3 }
        -- ::= {1.3.6.1.4.1.253.8.62.1.1.3}

xcmPidDC230ST OBJECT-IDENTITY
    STATUS      current
    DESCRIPTION


        "Document Centre 230ST multi-function system
                 model identifier (not a complete product identifier)."
    ::= { xcmPidDC230 1 }
        -- ::= {1.3.6.1.4.1.253.8.62.1.1.3.1}
            -- => SAP PID string = "131"

xcmPidDC230STV1 OBJECT-IDENTITY
    STATUS      current
    DESCRIPTION
        "Document Centre 230ST multi-function system
                 launch configuration version, and
                 complete product identifier."
    ::= { xcmPidDC230ST 1 }
        -- ::= {1.3.6.1.4.1.253.8.62.1.1.3.1.1}

xcmPidDC230STV2 OBJECT-IDENTITY
    STATUS      current
    DESCRIPTION
        "Document Centre 230ST multi-function system
                 first post-launch configuration version, and
                 complete product identifier."
    ::= { xcmPidDC230ST 2 }
        -- ::= {1.3.6.1.4.1.253.8.62.1.1.3.1.2}

xcmPidDC230STV3 OBJECT-IDENTITY
    STATUS      current
    DESCRIPTION
        "Document Centre 230ST multi-function system
                 second post-launch configuration version, and
                 complete product identifier."
    ::= { xcmPidDC230ST 3 }
        -- ::= {1.3.6.1.4.1.253.8.62.1.1.3.1.3}

xcmPidDC230STV4 OBJECT-IDENTITY
    STATUS      current
    DESCRIPTION
        "Document Centre 230ST multi-function system
                 third post-launch configuration version, and
                 complete product identifier."
    ::= { xcmPidDC230ST 4 }
        -- ::= {1.3.6.1.4.1.253.8.62.1.1.3.1.4}

xcmPidDC230STV5 OBJECT-IDENTITY
    STATUS      current
    DESCRIPTION
        "Document Centre 230ST multi-function system
                 fourth post-launch configuration version, and
                 complete product identifier."
    ::= { xcmPidDC230ST 5 }
        -- ::= {1.3.6.1.4.1.253.8.62.1.1.3.1.5}

xcmPidDC230LP OBJECT-IDENTITY
    STATUS      current


    DESCRIPTION
        "Document Centre 230LP laser printer
                 model identifier (not a complete product identifier)."
    ::= { xcmPidDC230 2 }
        -- ::= {1.3.6.1.4.1.253.8.62.1.1.3.2}
            -- => SAP PID string = "132"

xcmPidDC230LPV1 OBJECT-IDENTITY
    STATUS      current
    DESCRIPTION
        "Document Centre 230LP laser printer
                 launch configuration version, and
                 complete product identifier."
    ::= { xcmPidDC230LP 1 }
        -- ::= {1.3.6.1.4.1.253.8.62.1.1.3.2.1}

xcmPidDC230LPV2 OBJECT-IDENTITY
    STATUS      current
    DESCRIPTION
        "Document Centre 230LP laser printer
                 first post-launch configuration version, and
                 complete product identifier."
    ::= { xcmPidDC230LP 2 }
        -- ::= {1.3.6.1.4.1.253.8.62.1.1.3.2.2}

xcmPidDC230LPV3 OBJECT-IDENTITY
    STATUS      current
    DESCRIPTION
        "Document Centre 230LP laser printer
                 second post-launch configuration version, and
                 complete product identifier."
    ::= { xcmPidDC230LP 3 }
        -- ::= {1.3.6.1.4.1.253.8.62.1.1.3.2.3}

xcmPidDC230LPV4 OBJECT-IDENTITY
    STATUS      current
    DESCRIPTION
        "Document Centre 230LP laser printer
                 third post-launch configuration version, and
                 complete product identifier."
    ::= { xcmPidDC230LP 4 }
        -- ::= {1.3.6.1.4.1.253.8.62.1.1.3.2.4}

xcmPidDC230LPV5 OBJECT-IDENTITY
    STATUS      current
    DESCRIPTION
        "Document Centre 230LP laser printer
                 fourth post-launch configuration version, and
                 complete product identifier."
    ::= { xcmPidDC230LP 5 }
        -- ::= {1.3.6.1.4.1.253.8.62.1.1.3.2.5}

-- Document Centre 230 Intel upgrade (30 ppm)


xcmPidDC230i OBJECT-IDENTITY
    STATUS      current
    DESCRIPTION
        "Document Centre 230i multi-function system
                 model identifier (not a complete product identifier)."
    ::= { xcmPidDocuCentreSystems 22 }
        -- ::= {1.3.6.1.4.1.253.8.62.1.1.22}

xcmPidDC230iST OBJECT-IDENTITY
    STATUS      current
    DESCRIPTION
        "Document Centre 230iST multi-function system
                 model identifier (not a complete product identifier)."
    ::= { xcmPidDC230i 1 }
        -- ::= {1.3.6.1.4.1.253.8.62.1.1.22.1}
            -- => SAP PID string = "1F1"

xcmPidDC230iSTV1 OBJECT-IDENTITY
    STATUS      current
    DESCRIPTION
        "Document Centre 230iST multi-function system
                 launch configuration version, and
                 complete product identifier."
    ::= { xcmPidDC230iST 1 }
        -- ::= {1.3.6.1.4.1.253.8.62.1.1.22.1.1}

xcmPidDC230iSTV2 OBJECT-IDENTITY
    STATUS      current
    DESCRIPTION
        "Document Centre 230iST multi-function system
                 first post-launch configuration version, and
                 complete product identifier."
    ::= { xcmPidDC230iST 2 }
        -- ::= {1.3.6.1.4.1.253.8.62.1.1.22.1.2}

--
--


-- Document Centre 240  (40 ppm)

xcmPidDC240 OBJECT-IDENTITY
    STATUS      current
    DESCRIPTION
        "Document Centre 240 product type identifier
                 (not a complete product identifier)."
    ::= { xcmPidDocuCentreSystems 5 }
        -- ::= {1.3.6.1.4.1.253.8.62.1.1.5}

xcmPidDC240ST OBJECT-IDENTITY
    STATUS      current
    DESCRIPTION
        "Document Centre 240ST multi-function system
                 model identifier (not a complete product identifier)."
    ::= { xcmPidDC240 1 }
        -- ::= {1.3.6.1.4.1.253.8.62.1.1.5.1}
            -- => SAP PID string = "151"

xcmPidDC240STV1 OBJECT-IDENTITY
    STATUS      current
    DESCRIPTION
        "Document Centre 240ST multi-function system launch
          configuration version, and complete product identifier."
    ::= { xcmPidDC240ST 1 }
        -- ::= {1.3.6.1.4.1.253.8.62.1.1.5.1.1}

xcmPidDC240STV2 OBJECT-IDENTITY
    STATUS      current
    DESCRIPTION
        "Document Centre 240ST multi-function system
                 first post-launch configuration version, and
                 complete product identifier."
    ::= { xcmPidDC240ST 2 }
        -- ::= {1.3.6.1.4.1.253.8.62.1.1.5.1.2}

xcmPidDC240STV3 OBJECT-IDENTITY
    STATUS      current
    DESCRIPTION
        "Document Centre 240ST multi-function system
                 second post-launch configuration version, and
                 complete product identifier."
    ::= { xcmPidDC240ST 3 }
        -- ::= {1.3.6.1.4.1.253.8.62.1.1.5.1.3}

-- Document Centre 255  (55 ppm)

xcmPidDC255 OBJECT-IDENTITY
    STATUS      current
    DESCRIPTION
        "Document Centre 255 product type identifier
                 (not a complete product identifier)."


    ::= { xcmPidDocuCentreSystems 7 }
        -- ::= {1.3.6.1.4.1.253.8.62.1.1.7}

xcmPidDC255ST OBJECT-IDENTITY
    STATUS      current
    DESCRIPTION
        "Document Centre 255ST multi-function system
                 model identifier (not a complete product identifier)."
    ::= { xcmPidDC255 1 }
        -- ::= {1.3.6.1.4.1.253.8.62.1.1.7.1}
            -- => SAP PID string = "171"

xcmPidDC255STV1 OBJECT-IDENTITY
    STATUS      current
    DESCRIPTION
        "Document Centre 255ST multi-function system launch
          configuration version, and complete product identifier."
    ::= { xcmPidDC255ST 1 }
        -- ::= {1.3.6.1.4.1.253.8.62.1.1.7.1.1}

xcmPidDC255STV2 OBJECT-IDENTITY
    STATUS      current
    DESCRIPTION
        "Document Centre 255ST multi-function system
                 first post-launch configuration version, and
                 complete product identifier."
    ::= { xcmPidDC255ST 2 }
        -- ::= {1.3.6.1.4.1.253.8.62.1.1.7.1.2}

xcmPidDC255STV3 OBJECT-IDENTITY
    STATUS      current
    DESCRIPTION
        "Document Centre 255ST multi-function system
                 second post-launch configuration version, and
                 complete product identifier."
    ::= { xcmPidDC255ST 3 }
        -- ::= {1.3.6.1.4.1.253.8.62.1.1.7.1.3}

xcmPidDC255LP OBJECT-IDENTITY
    STATUS      current
    DESCRIPTION
        "Document Centre 255LP laser printer
                 model identifier (not a complete product identifier)."
    ::= { xcmPidDC255 2 }
        -- ::= {1.3.6.1.4.1.253.8.62.1.1.7.2}
            -- => SAP PID string = "172"

xcmPidDC255LPV1 OBJECT-IDENTITY
    STATUS      current
    DESCRIPTION
        "Document Centre 255LP laser printer launch configuration
                 version, and complete product identifier."
    ::= { xcmPidDC255LP 1 }


        -- ::= {1.3.6.1.4.1.253.8.62.1.1.7.2.1}

xcmPidDC255LPV2 OBJECT-IDENTITY
    STATUS      current
    DESCRIPTION
        "Document Centre 255LP laser printer
                 first post-launch configuration version, and
                 complete product identifier."
    ::= { xcmPidDC255LP 2 }
        -- ::= {1.3.6.1.4.1.253.8.62.1.1.7.2.2}

xcmPidDC255LPV3 OBJECT-IDENTITY
    STATUS      current
    DESCRIPTION
        "Document Centre 255LP laser printer
                 second post-launch configuration version, and
                 complete product identifier."
    ::= { xcmPidDC255LP 3 }
        -- ::= {1.3.6.1.4.1.253.8.62.1.1.7.2.3}

-- Document Centre 265  (65 ppm)

xcmPidDC265 OBJECT-IDENTITY
    STATUS      current
    DESCRIPTION
        "Document Centre 265 product type identifier
                 (not a complete product identifier)."
    ::= { xcmPidDocuCentreSystems 4 }
        -- ::= {1.3.6.1.4.1.253.8.62.1.1.4}

xcmPidDC265ST OBJECT-IDENTITY
    STATUS      current
    DESCRIPTION
        "Document Centre 265ST multi-function system
                 model identifier (not a complete product identifier)."
    ::= { xcmPidDC265 1 }
        -- ::= {1.3.6.1.4.1.253.8.62.1.1.4.1}
            -- => SAP PID string = "141"

xcmPidDC265STV1 OBJECT-IDENTITY
    STATUS      current
    DESCRIPTION
        "Document Centre 265ST multi-function system launch
          configuration version, and complete product identifier."
    ::= { xcmPidDC265ST 1 }
        -- ::= {1.3.6.1.4.1.253.8.62.1.1.4.1.1}

xcmPidDC265STV2 OBJECT-IDENTITY
    STATUS      current
    DESCRIPTION
        "Document Centre 265ST multi-function system
                 first post-launch configuration version, and
                 complete product identifier."


    ::= { xcmPidDC265ST 2 }
        -- ::= {1.3.6.1.4.1.253.8.62.1.1.4.1.2}

xcmPidDC265STV3 OBJECT-IDENTITY
    STATUS      current
    DESCRIPTION
        "Document Centre 265ST multi-function system
                 second post-launch configuration version, and
                 complete product identifier."
    ::= { xcmPidDC265ST 3 }
        -- ::= {1.3.6.1.4.1.253.8.62.1.1.4.1.3}

xcmPidDC265LP OBJECT-IDENTITY
    STATUS      current
    DESCRIPTION
        "Document Centre 265LP laser printer
                 model identifier (not a complete product identifier)."
    ::= { xcmPidDC265 2 }
        -- ::= {1.3.6.1.4.1.253.8.62.1.1.4.2}
            -- => SAP PID string = "142"

xcmPidDC265LPV1 OBJECT-IDENTITY
    STATUS      current
    DESCRIPTION
        "Document Centre 265LP laser printer launch configuration
                 version, and complete product identifier."
    ::= { xcmPidDC265LP 1 }
        -- ::= {1.3.6.1.4.1.253.8.62.1.1.4.2.1}

xcmPidDC265LPV2 OBJECT-IDENTITY
    STATUS      current
    DESCRIPTION
        "Document Centre 265LP laser printer
                 first post-launch configuration version, and
                 complete product identifier."
    ::= { xcmPidDC265LP 2 }
        -- ::= {1.3.6.1.4.1.253.8.62.1.1.4.2.2}

xcmPidDC265LPV3 OBJECT-IDENTITY
    STATUS      current
    DESCRIPTION
        "Document Centre 265LP laser printer
                 second post-launch configuration version, and
                 complete product identifier."
    ::= { xcmPidDC265LP 3 }
        -- ::= {1.3.6.1.4.1.253.8.62.1.1.4.2.3}

--
--

-- Document Centre 332  (32 ppm)

xcmPidDC332 OBJECT-IDENTITY
    STATUS      current
    DESCRIPTION
        "Document Centre 332 product type identifier
                 (not a complete product identifier)."
    ::= { xcmPidDocuCentreSystems 9 }
        -- ::= {1.3.6.1.4.1.253.8.62.1.1.9}

xcmPidDC332ST OBJECT-IDENTITY
    STATUS      current
    DESCRIPTION
        "Document Centre 332ST multi-function system
                 model identifier (not a complete product identifier)."
    ::= { xcmPidDC332 1 }
        -- ::= {1.3.6.1.4.1.253.8.62.1.1.9.1}
            -- => SAP PID string = "191"


xcmPidDC332STV1 OBJECT-IDENTITY
    STATUS      current
    DESCRIPTION
        "Document Centre 332ST multi-function system
                 launch configuration version, and
                 complete product identifier."
    ::= { xcmPidDC332ST 1 }
        -- ::= {1.3.6.1.4.1.253.8.62.1.1.9.1.1}

xcmPidDC332STV2 OBJECT-IDENTITY
    STATUS      current
    DESCRIPTION
        "Document Centre 332ST multi-function system
                 first post-launch configuration version, and
                 complete product identifier."
    ::= { xcmPidDC332ST 2 }
        -- ::= {1.3.6.1.4.1.253.8.62.1.1.9.1.2}

--
--

-- Document Centre 340  (40 ppm)

xcmPidDC340 OBJECT-IDENTITY
    STATUS      current
    DESCRIPTION
        "Document Centre 340 product type identifier
                 (not a complete product identifier)."
    ::= { xcmPidDocuCentreSystems 6 }
        -- ::= {1.3.6.1.4.1.253.8.62.1.1.6}

xcmPidDC340ST OBJECT-IDENTITY
    STATUS      current
    DESCRIPTION
        "Document Centre 340ST multi-function system
                 model identifier (not a complete product identifier)."
    ::= { xcmPidDC340 1 }
        -- ::= {1.3.6.1.4.1.253.8.62.1.1.6.1}
            -- => SAP PID string = "161"

xcmPidDC340STV1 OBJECT-IDENTITY
    STATUS      current
    DESCRIPTION
        "Document Centre 340ST multi-function system
                 launch configuration version, and
                 complete product identifier."
    ::= { xcmPidDC340ST 1 }
        -- ::= {1.3.6.1.4.1.253.8.62.1.1.6.1.1}

xcmPidDC340STV2 OBJECT-IDENTITY
    STATUS      current
    DESCRIPTION
        "Document Centre 340ST multi-function system
                 first post-launch configuration version, and
                 complete product identifier."
    ::= { xcmPidDC340ST 2 }


        -- ::= {1.3.6.1.4.1.253.8.62.1.1.6.1.2}

--
--

-- Document Centre 420  (20 ppm)

xcmPidDC420 OBJECT-IDENTITY
    STATUS      current
    DESCRIPTION
        "Document Centre 420 product type identifier
                 (not a complete product identifier)."
    ::= { xcmPidDocuCentreSystems 19 }
        -- ::= {1.3.6.1.4.1.253.8.62.1.1.19}

xcmPidDC420ST OBJECT-IDENTITY
    STATUS      current
    DESCRIPTION
        "Document Centre 420ST multi-function system
                 model identifier (not a complete product identifier)."
    ::= { xcmPidDC420 1 }
        -- ::= {1.3.6.1.4.1.253.8.62.1.1.19.1}
            -- => SAP PID string = "1C1"

xcmPidDC420STV1 OBJECT-IDENTITY
    STATUS      current
    DESCRIPTION
        "Document Centre 420ST multi-function system
                 launch configuration version, and
                 complete product identifier."
    ::= { xcmPidDC420ST 1 }
        -- ::= {1.3.6.1.4.1.253.8.62.1.1.19.1.1}

xcmPidDC420STV2 OBJECT-IDENTITY
    STATUS      current
    DESCRIPTION
        "Document Centre 420ST multi-function system
                 first post-launch configuration version, and
                 complete product identifier."
    ::= { xcmPidDC420ST 2 }
        -- ::= {1.3.6.1.4.1.253.8.62.1.1.19.1.2}

--
--

-- Document Centre 426

xcmPidDC426 OBJECT-IDENTITY
    STATUS      current
    DESCRIPTION
        "Document Centre 426 multi-function system
                 model identifier (not a complete product identifier)."
    ::= { xcmPidDC420 2 }
        -- ::= {1.3.6.1.4.1.253.8.62.1.1.19.2}
            -- => SAP PID string = "1C2"
            -- => USB PID string = 1730 = 0x6C2

xcmPidDC426V1 OBJECT-IDENTITY
    STATUS      current
    DESCRIPTION
        "Document Centre 426 multi-function system
                 launch configuration version, and
                 complete product identifier."
    ::= { xcmPidDC426 1 }
        -- ::= {1.3.6.1.4.1.253.8.62.1.1.19.2.1}

-- Document Centre 432  (32 ppm)

xcmPidDC432 OBJECT-IDENTITY
    STATUS      current
    DESCRIPTION
        "Document Centre 432 product type identifier
                 (not a complete product identifier)."
    ::= { xcmPidDocuCentreSystems 20 }
        -- ::= {1.3.6.1.4.1.253.8.62.1.1.20}

xcmPidDC432ST OBJECT-IDENTITY
    STATUS      current
    DESCRIPTION
        "Document Centre 432ST multi-function system
                 model identifier (not a complete product identifier)."
    ::= { xcmPidDC432 1 }
        -- ::= {1.3.6.1.4.1.253.8.62.1.1.20.1}
            -- => SAP PID string = "1D1"

xcmPidDC432STV1 OBJECT-IDENTITY
    STATUS      current
    DESCRIPTION
        "Document Centre 432ST multi-function system
                 launch configuration version, and
                 complete product identifier."
    ::= { xcmPidDC432ST 1 }
        -- ::= {1.3.6.1.4.1.253.8.62.1.1.20.1.1}


xcmPidDC432STV2 OBJECT-IDENTITY
    STATUS      current
    DESCRIPTION
        "Document Centre 432ST multi-function system
                 first post-launch configuration version, and
                 complete product identifier."
    ::= { xcmPidDC432ST 2 }
        -- ::= {1.3.6.1.4.1.253.8.62.1.1.20.1.2}

xcmPidDC432STV3 OBJECT-IDENTITY
    STATUS      current
    DESCRIPTION
        "Document Centre 432ST multi-function system
                 second post-launch configuration version, and
                 complete product identifier."
    ::= { xcmPidDC432ST 3 }
        -- ::= {1.3.6.1.4.1.253.8.62.1.1.20.1.3}

xcmPidDC432STV4 OBJECT-IDENTITY
    STATUS      current
    DESCRIPTION
        "Document Centre 432ST multi-function system
                 third post-launch configuration version, and
                 complete product identifier."
    ::= { xcmPidDC432ST 4 }
        -- ::= {1.3.6.1.4.1.253.8.62.1.1.20.1.4}

xcmPidDC432STV5 OBJECT-IDENTITY
    STATUS      current
    DESCRIPTION
        "Document Centre 432ST multi-function system
                 fourth post-launch configuration version, and
                 complete product identifier."
    ::= { xcmPidDC432ST 5 }
        -- ::= {1.3.6.1.4.1.253.8.62.1.1.20.1.5}

-- Document Centre 430

xcmPidDC430 OBJECT-IDENTITY
    STATUS      current
    DESCRIPTION
        "Document Centre 430 multi-function system
                 model identifier (not a complete product identifier)."
    ::= { xcmPidDC432 2 }
        -- ::= {1.3.6.1.4.1.253.8.62.1.1.20.2}
            -- => SAP PID string = "1D2"
            -- => USB PID string = 1766 = 0x6E6

xcmPidDC430V1 OBJECT-IDENTITY
    STATUS      current
    DESCRIPTION
        "Document Centre 430 multi-function system


                 launch configuration version, and
                 complete product identifier."
    ::= { xcmPidDC430 1 }
        -- ::= {1.3.6.1.4.1.253.8.62.1.1.20.2.1}

-- Document Centre 440  (40 ppm)

xcmPidDC440 OBJECT-IDENTITY
    STATUS      current
    DESCRIPTION
        "Document Centre 440 product type identifier
                 (not a complete product identifier)."
    ::= { xcmPidDocuCentreSystems 21 }
        -- ::= {1.3.6.1.4.1.253.8.62.1.1.21}

xcmPidDC440ST OBJECT-IDENTITY
    STATUS      current
    DESCRIPTION
        "Document Centre 440ST multi-function system
                 model identifier (not a complete product identifier)."
    ::= { xcmPidDC440 1 }
        -- ::= {1.3.6.1.4.1.253.8.62.1.1.21.1}
            -- => SAP PID string = "1E1"

xcmPidDC440STV1 OBJECT-IDENTITY
    STATUS      current
    DESCRIPTION
        "Document Centre 440ST multi-function system
                 launch configuration version, and
                 complete product identifier."
    ::= { xcmPidDC440ST 1 }
        -- ::= {1.3.6.1.4.1.253.8.62.1.1.21.1.1}

xcmPidDC440STV2 OBJECT-IDENTITY
    STATUS      current
    DESCRIPTION
        "Document Centre 440ST multi-function system
                 first post-launch configuration version, and
                 complete product identifier."
    ::= { xcmPidDC440ST 2 }
        -- ::= {1.3.6.1.4.1.253.8.62.1.1.21.1.2}

xcmPidDC440STV3 OBJECT-IDENTITY
    STATUS      current
    DESCRIPTION
        "Document Centre 440ST multi-function system
                 second post-launch configuration version, and
                 complete product identifier."
    ::= { xcmPidDC440ST 3 }
        -- ::= {1.3.6.1.4.1.253.8.62.1.1.21.1.3}

--
--

-- Document Centre 4XX  (XX = 60, 70)

xcmPidDC4XX OBJECT-IDENTITY
    STATUS      current
    DESCRIPTION
        "Document Centre 4XX product type identifier
                 (not a complete product identifier)."
    ::= { xcmPidDocuCentreSystems 17 }
        -- ::= {1.3.6.1.4.1.253.8.62.1.1.17}

xcmPidDC460 OBJECT-IDENTITY
    STATUS      current
    DESCRIPTION
        "Document Centre 460 multi-functional system
                 model identifier (not a complete product identifier)."
    ::= { xcmPidDC4XX 2 }
        -- ::= {1.3.6.1.4.1.253.8.62.1.1.17.2}
            -- => SAP PID string = "1A2"

xcmPidDC460V1 OBJECT-IDENTITY
    STATUS      current
    DESCRIPTION
        "Document Centre 460 multi-functional system launch
                configuration version, and complete product identifier."
    ::= { xcmPidDC460 1 }
        -- ::= {1.3.6.1.4.1.253.8.62.1.1.17.2.1}

--
--

xcmPidDC470 OBJECT-IDENTITY
    STATUS      current
    DESCRIPTION
        "Document Centre 470 multi-functional system
                 model identifier (not a complete product identifier)."
    ::= { xcmPidDC4XX 4 }
        -- ::= {1.3.6.1.4.1.253.8.62.1.1.17.4}
            -- => SAP PID string = "1A4"

xcmPidDC470V1 OBJECT-IDENTITY
    STATUS      current
    DESCRIPTION
        "Document Centre 470 multi-functional system launch
                configuration version, and complete product identifier."
    ::= { xcmPidDC470 1 }
        -- ::= {1.3.6.1.4.1.253.8.62.1.1.17.4.1}

--
--

xcmPidDC4YY OBJECT-IDENTITY
    STATUS      current
    DESCRIPTION
        "Document Centre 4YY product type identifier
                 (not a complete product identifier)."
    ::= { xcmPidDocuCentreSystems 23 }
        -- ::= {1.3.6.1.4.1.253.8.62.1.1.23}

xcmPidDC480 OBJECT-IDENTITY
    STATUS      current
    DESCRIPTION
        "Document Centre 480 multi-functional system
                 model identifier (not a complete product identifier)."
    ::= { xcmPidDC4YY 1 }
        -- ::= {1.3.6.1.4.1.253.8.62.1.1.23.1}
            -- => SAP PID string = "1G1"

xcmPidDC480V1 OBJECT-IDENTITY
    STATUS      current
    DESCRIPTION
        "Document Centre 480 multi-functional system, UNUSED
                version, and complete product identifier."


    ::= { xcmPidDC480 1 }
        -- ::= {1.3.6.1.4.1.253.8.62.1.1.23.1.1}

--
--

-- Document Centre 425

xcmPidDC425 OBJECT-IDENTITY
    STATUS      current
    DESCRIPTION
        "Document Centre 425 product type identifier
                 (not a complete product identifier)."
    ::= { xcmPidDocuCentreSystems 24 }
        -- ::= {1.3.6.1.4.1.253.8.62.1.1.24}

xcmPidDC425ST OBJECT-IDENTITY


    STATUS      current
    DESCRIPTION
        "Document Centre 425ST multi-functional system
                 model identifier (not a complete product identifier)."
    ::= { xcmPidDC425 1 }
        -- ::= {1.3.6.1.4.1.253.8.62.1.1.24.1}
            -- => SAP PID string = "1H1"

xcmPidDC425STV1 OBJECT-IDENTITY
    STATUS      current
    DESCRIPTION
        "Document Centre 425ST multi-functional system launch
                configuration version, and complete product identifier."
    ::= { xcmPidDC425ST 1 }
        -- ::= {1.3.6.1.4.1.253.8.62.1.1.24.1.1}

--
--

-- Document Centre 555, 55 ppm

xcmPidDC555 OBJECT-IDENTITY
    STATUS      current
    DESCRIPTION
        "Document Centre 555 product type identifier
                 (not a complete product identifier)."
    ::= { xcmPidDocuCentreSystems 27 }
        -- ::= {1.3.6.1.4.1.253.8.62.1.1.27}

xcmPidDC555ST OBJECT-IDENTITY
    STATUS      current
    DESCRIPTION
        "Document Centre 555ST multi-functional system
                 model identifier (not a complete product identifier)."
    ::= { xcmPidDC555 1 }
        -- ::= {1.3.6.1.4.1.253.8.62.1.1.27.1}
            -- => SAP PID string = "1K1"

xcmPidDC555STV1 OBJECT-IDENTITY
    STATUS      current
    DESCRIPTION
        "Document Centre 555ST multi-functional system ECE pre-launch
                configuration version, and complete product identifier."
    ::= { xcmPidDC555ST 1 }
        -- ::= {1.3.6.1.4.1.253.8.62.1.1.27.1.1}

xcmPidDC555STV2 OBJECT-IDENTITY
    STATUS      current
    DESCRIPTION
        "Document Centre 555ST multi-functional system,
                 launch configuration version, and
                 complete product identifier."
    ::= { xcmPidDC555ST 2 }


        -- ::= {1.3.6.1.4.1.253.8.62.1.1.27.1.2}

--
--


-- Document Centre 535, 35 ppm.

xcmPidDC535 OBJECT-IDENTITY
    STATUS  current
    DESCRIPTION
        "Document Centre 535 product type identifier


                 (not a complete product identifier)."
    ::= { xcmPidDocuCentreSystems 30 }
        -- ::= {1.3.6.1.4.1.253.8.62.1.1.30 }

xcmPidDC535ST OBJECT-IDENTITY
    STATUS  current
    DESCRIPTION
        "Document Centre 535 multi-function system model identifier
                 (not a complete product identifier)."
    ::= { xcmPidDC535 1 }
        -- ::= {1.3.6.1.4.1.253.8.62.1.1.30.1}
            -- => SAP PID string = "1N1"

xcmPidDC535STV1 OBJECT-IDENTITY
    STATUS  current
    DESCRIPTION
        "Document Centre 535 multi-function system
                 ECE pre-launch configuration version, and
                 complete product identifier."
    ::= { xcmPidDC535ST 1 }
        -- ::= {1.3.6.1.4.1.253.8.62.1.1.30.1.1}

xcmPidDC535STV2 OBJECT-IDENTITY
    STATUS  current
    DESCRIPTION
        "Document Centre 535 multi-function system
                 launch configuration version, and
                 complete product identifier."
    ::= { xcmPidDC535ST 2 }
        -- ::= {1.3.6.1.4.1.253.8.62.1.1.30.1.2}

-- Document Centre 545, 45 ppm.

xcmPidDC545 OBJECT-IDENTITY
    STATUS  current
    DESCRIPTION
        "Document Centre 545 product type identifier
                 (not a complete product identifier)."
    ::= { xcmPidDocuCentreSystems 31 }
        -- ::= {1.3.6.1.4.1.253.8.62.1.1.31}

xcmPidDC545ST OBJECT-IDENTITY
    STATUS  current
    DESCRIPTION
        "Document Centre 545 multi-function system model identifier
                 (not a complete product identifier)."
    ::= { xcmPidDC545 1 }
        -- ::= {1.3.6.1.4.1.253.8.62.1.1.31.1}
            -- => SAP PID string = "1O1"

xcmPidDC545STV1 OBJECT-IDENTITY
    STATUS  current
    DESCRIPTION
        "Document Centre 545 multi-function system


                 ECE pre-launch configuration version, and
                 complete product identifier."
    ::= { xcmPidDC545ST 1 }
        -- ::= {1.3.6.1.4.1.253.8.62.1.1.31.1.1}

xcmPidDC545STV2 OBJECT-IDENTITY
    STATUS  current
    DESCRIPTION
        "Document Centre 545 multi-function system
                 launch configuration version, and
                 complete product identifier."
    ::= { xcmPidDC545ST 2 }
        -- ::= {1.3.6.1.4.1.253.8.62.1.1.31.1.2}

--
--

----------------------------------------------------------------
-- Xerographic WorkCentre and WorkCentrePro MF Devices
----------------------------------------------------------------

xcmPidWorkCentreMFSystems OBJECT-IDENTITY
    STATUS      current
    DESCRIPTION
        "WorkCentre and WorkCentrePro Systems product line identifier
                 (not a complete product identifier)."
    ::= { xcmPidProductIdentifiers 20 }
        -- ::= {1.3.6.1.4.1.253.8.62.1.20}

-- WorkCentrePro Series

xcmPidWCPro OBJECT-IDENTITY
    STATUS      current
    DESCRIPTION
        "WorkCentrePro System product line identifier
                 (not a complete product identifier)."
    ::= { xcmPidWorkCentreMFSystems 1 }
        -- ::= {1.3.6.1.4.1.253.8.62.1.20.1 }

-- WorkCentrePro32C 32 ppm/16 ppm color

xcmPidWCP32C OBJECT-IDENTITY
    STATUS      current
    DESCRIPTION
        "WorkCentrePro32C multi-function system identifier
                 (not a complete product identifier)."
    ::= { xcmPidWCPro 1 }
        -- ::= {1.3.6.1.4.1.253.8.62.1.20.1.1 }
            -- => SAP PID string = "D11"

xcmPidWCP32CV1 OBJECT-IDENTITY


    STATUS      current
    DESCRIPTION
        "WorkCentrePro32C multi-function system,
                 launch configuration version #1, and
                 complete product identifier."
    ::= { xcmPidWCP32C 1 }
        -- ::= {1.3.6.1.4.1.253.8.62.1.20.1.1.1}

xcmPidWCP32CV2 OBJECT-IDENTITY
    STATUS      current
    DESCRIPTION
        "WorkCentrePro32C multi-function system,
                 launch configuration version #2, and
                 complete product identifier."
    ::= { xcmPidWCP32C 2 }
        -- ::= {1.3.6.1.4.1.253.8.62.1.20.1.1.2}

-- WorkCentrePro35 35 ppm

xcmPidWCP35 OBJECT-IDENTITY
    STATUS      current
    DESCRIPTION
        "WorkCentrePro35 multi-function system identifier
                 (not a complete product identifier)."
    ::= { xcmPidWCPro 2 }
        -- ::= {1.3.6.1.4.1.253.8.62.1.20.1.2 }
            -- => SAP PID string = "D12"

xcmPidWCP35V1 OBJECT-IDENTITY
    STATUS      current
    DESCRIPTION
        "WorkCentrePro35 multi-function system,
                 launch configuration version #1, and
                 complete product identifier."
    ::= { xcmPidWCP35 1 }
        -- ::= {1.3.6.1.4.1.253.8.62.1.20.1.2.1}

xcmPidWCP35V2 OBJECT-IDENTITY
    STATUS      current
    DESCRIPTION
        "WorkCentrePro35 multi-function system,
                 launch configuration version #2, and
                 complete product identifier."
    ::= { xcmPidWCP35 2 }
        -- ::= {1.3.6.1.4.1.253.8.62.1.20.1.2.2}

-- WorkCentrePro40C 40 ppm/22 ppm color

xcmPidWCP40C OBJECT-IDENTITY
    STATUS      current


    DESCRIPTION
        "WorkCentrePro40C multi-function system identifier
                 (not a complete product identifier)."
    ::= { xcmPidWCPro 3 }
        -- ::= {1.3.6.1.4.1.253.8.62.1.20.1.3 }
            -- => SAP PID string = "D13"

xcmPidWCP40CV1 OBJECT-IDENTITY
    STATUS      current
    DESCRIPTION
        "WorkCentrePro40C multi-function system,
                 launch configuration version #1, and
                 complete product identifier."
    ::= { xcmPidWCP40C 1 }
        -- ::= {1.3.6.1.4.1.253.8.62.1.20.1.3.1}

xcmPidWCP40CV2 OBJECT-IDENTITY
    STATUS      current
    DESCRIPTION
        "WorkCentrePro40C multi-function system,
                 launch configuration version #2, and
                 complete product identifier."
    ::= { xcmPidWCP40C 2 }
        -- ::= {1.3.6.1.4.1.253.8.62.1.20.1.3.2}

-- WorkCentrePro45 45 ppm.

xcmPidWCP45 OBJECT-IDENTITY
    STATUS      current
    DESCRIPTION
     "WorkCentrePro45 multi-function system identifier
      (not a complete product identifier)."
    ::= { xcmPidWCPro 4 }
        -- ::= {1.3.6.1.4.1.253.8.62.1.20.1.4 }
            -- => SAP PID string = "D14"

xcmPidWCP45V1 OBJECT-IDENTITY
    STATUS      current
    DESCRIPTION
        "WorkCentrePro45 multi-function system,
                 launch configuration version #1, and
                 complete product identifier."
    ::= { xcmPidWCP45 1 }
        -- ::= {1.3.6.1.4.1.253.8.62.1.20.1.4.1}

xcmPidWCP45V2 OBJECT-IDENTITY
    STATUS      current
    DESCRIPTION
        "WorkCentrePro45 multi-function system,
                 launch configuration version #2, and
                 complete product identifier."
    ::= { xcmPidWCP45 2 }


        -- ::= {1.3.6.1.4.1.253.8.62.1.20.1.4.2}

-- WorkCentrePro55  55 ppm.

xcmPidWCP55 OBJECT-IDENTITY
    STATUS      current
    DESCRIPTION
        "WorkCentrePro55 multi-function system identifier
                 (not a complete product identifier)."
    ::= { xcmPidWCPro 5 }
        -- ::= {1.3.6.1.4.1.253.8.62.1.20.1.5 }
            -- => SAP PID string = "D15"

xcmPidWCP55V1 OBJECT-IDENTITY
    STATUS      current
    DESCRIPTION
        "WorkCentrePro55 multi-function system,
                 launch configuration version #1, and
                 complete product identifier."
    ::= { xcmPidWCP55 1 }
        -- ::= {1.3.6.1.4.1.253.8.62.1.20.1.5.1}

xcmPidWCP55V2 OBJECT-IDENTITY
    STATUS      current
    DESCRIPTION
        "WorkCentrePro55 multi-function system,
                 launch configuration version #2, and
                 complete product identifier."
    ::= { xcmPidWCP55 2 }
        -- ::= {1.3.6.1.4.1.253.8.62.1.20.1.5.2}

--
--

-- WorkCentre Pro 165


xcmPidWCP165 OBJECT-IDENTITY
    STATUS      current
    DESCRIPTION
        "WorkCentre Pro 165 multi-function system identifier
                 (not a complete product identifier)."
    ::= { xcmPidWCPro 9 }
        -- ::= {1.3.6.1.4.1.253.8.62.1.20.1.9 }
            -- => SAP PID string = "D19"

xcmPidWCP165V1 OBJECT-IDENTITY
    STATUS      current
    DESCRIPTION
        "WorkCentre Pro 165 multi-function system,
                 launch configuration version #1, and
                 complete product identifier."
    ::= { xcmPidWCP165 1 }
        -- ::= {1.3.6.1.4.1.253.8.62.1.20.1.9.1}

-- WorkCentre Pro 175

xcmPidWCP175 OBJECT-IDENTITY
    STATUS      current
    DESCRIPTION
        "WorkCentre Pro 175 multi-function system identifier
                 (not a complete product identifier)."
    ::= { xcmPidWCPro 17 }
        -- ::= {1.3.6.1.4.1.253.8.62.1.20.1.17 }
            -- => SAP PID string = "D1A"

xcmPidWCP175V1 OBJECT-IDENTITY
    STATUS      current
    DESCRIPTION
        "WorkCentre Pro 175 multi-function system,
                 launch configuration version #1, and
                 complete product identifier."
    ::= { xcmPidWCP175 1 }
        -- ::= {1.3.6.1.4.1.253.8.62.1.20.1.17.1}

-- WorkCentre 265

xcmPidWC265 OBJECT-IDENTITY
    STATUS      current
    DESCRIPTION
        "WorkCentre 265 multi-function system identifier
                 (not a complete product identifier)."
    ::= { xcmPidWCPro 22 }
        -- ::= {1.3.6.1.4.1.253.8.62.1.20.1.22 }
            -- => SAP PID string = "D1F"


            -- => USB PID string = 16899 = 0x4203

xcmPidWC265V1 OBJECT-IDENTITY
    STATUS      current
    DESCRIPTION
        "WorkCentre 265 multi-function system,
                 launch configuration version #1, and
                 complete product identifier."
    ::= { xcmPidWC265 1 }
        -- ::= {1.3.6.1.4.1.253.8.62.1.20.1.22.1 }

-- WorkCentre 275
--

xcmPidWC275 OBJECT-IDENTITY
    STATUS      current
    DESCRIPTION
        "WorkCentre 275 multi-function system identifier
                 (not a complete product identifier)."
    ::= { xcmPidWCPro 23 }
        -- ::= {1.3.6.1.4.1.253.8.62.1.20.1.23 }
            -- => SAP PID string = "D1G"
            -- => USB PID string = 16900 = 0x4204

xcmPidWC275V1 OBJECT-IDENTITY
    STATUS      current
    DESCRIPTION
        "WorkCentre 275 multi-function system,
                 launch configuration version #1, and
                 complete product identifier."
    ::= { xcmPidWC275 1 }
        -- ::= {1.3.6.1.4.1.253.8.62.1.20.1.23.1 }

-- WorkCentre Pro 265

xcmPidWCP265 OBJECT-IDENTITY
    STATUS      current
    DESCRIPTION
        "WorkCentre Pro 265 multi-function system identifier
                 (not a complete product identifier)."
    ::= { xcmPidWCPro 24 }
        -- ::= {1.3.6.1.4.1.253.8.62.1.20.1.24 }
            -- => SAP PID string = "D1H"
            -- => USB PID string = 16901 = 0x4205

xcmPidWCP265V1 OBJECT-IDENTITY
    STATUS      current
    DESCRIPTION
        "WorkCentre Pro 265 multi-function system,
                 launch configuration version #1, and
                 complete product identifier."


    ::= { xcmPidWCP265 1 }
        -- ::= {1.3.6.1.4.1.253.8.62.1.20.1.24.1 }

-- WorkCentre Pro 275

xcmPidWCP275 OBJECT-IDENTITY
    STATUS      current
    DESCRIPTION
        "WorkCentre Pro 275 multi-function system identifier
                 (not a complete product identifier)."
    ::= { xcmPidWCPro 25 }
        -- ::= {1.3.6.1.4.1.253.8.62.1.20.1.25 }
            -- => SAP PID string = "D1I"
            -- => USB PID string = 16902 = 0x4206

xcmPidWCP275V1 OBJECT-IDENTITY
    STATUS      current
    DESCRIPTION
        "WorkCentre Pro 275 multi-function system,
                 launch configuration version #1, and
                 complete product identifier."
    ::= { xcmPidWCP275 1 }
        -- ::= {1.3.6.1.4.1.253.8.62.1.20.1.25.1 }

-- WorkCentre+PostScript 265
--

xcmPidWCPS265 OBJECT-IDENTITY
    STATUS      current
    DESCRIPTION
        "WorkCentre + PostScript 265 multi-function system identifier
                 (not a complete product identifier)."
    ::= { xcmPidWCPro 26 }
        -- ::= {1.3.6.1.4.1.253.8.62.1.20.1.26 }
            -- => SAP PID string = "D1J"
            -- => USB PID string = 16903 = 0x4207

xcmPidWCPS265V1 OBJECT-IDENTITY
    STATUS      current
    DESCRIPTION
        "WorkCentre + PostScript 265 multi-function system,
                 launch configuration version #1, and
                 complete product identifier."
    ::= { xcmPidWCPS265 1 }
        -- ::= {1.3.6.1.4.1.253.8.62.1.20.1.26.1 }

-- WorkCentre+PostScript 275
--


xcmPidWCPS275 OBJECT-IDENTITY
    STATUS      current
    DESCRIPTION
        "WorkCentre + PostScript 275 multi-function system identifier
                 (not a complete product identifier)."
    ::= { xcmPidWCPro 27 }
        -- ::= {1.3.6.1.4.1.253.8.62.1.20.1.27 }
            -- => SAP PID string = "D1K"
            -- => USB PID string = 16904 = 0x4208

xcmPidWCPS275V1 OBJECT-IDENTITY
    STATUS      current
    DESCRIPTION
        "WorkCentre + PostScript 275 multi-function system,
                 launch configuration version #1, and
                 complete product identifier."
    ::= { xcmPidWCPS275 1 }
        -- ::= {1.3.6.1.4.1.253.8.62.1.20.1.27.1 }

--
-- Patriot / Lexington branding is "WorkCentre" however
--     the functionality is the same as WorkCentre Pro.

xcmPidWC7655 OBJECT-IDENTITY
    STATUS      current
    DESCRIPTION
        "WorkCentre 7655 multi-function system identifier
                 (not a complete product identifier)."
    ::= { xcmPidWCPro 28 }
        -- ::= {1.3.6.1.4.1.253.8.62.1.20.1.28 }
            -- => SAP PID string = "D1L"
            -- => USB PID string = 16905 = 0x4209
            -- => Compatible ID = XR_PS_Office_Color

xcmPidWC7655V1 OBJECT-IDENTITY
    STATUS      current
    DESCRIPTION
        "WorkCentre 7655 system identifier
         launch configuration version #1, and
         complete product identifier."
    ::= { xcmPidWC7655 1 }
        -- ::= {1.3.6.1.4.1.253.8.62.1.20.1.28.1 }

--
-- Patriot / Lexington branding is "WorkCentre" however
--     the functionality is the same as WorkCentre Pro.

xcmPidWC7665 OBJECT-IDENTITY
    STATUS      current
    DESCRIPTION


        "WorkCentre 7665 system identifier
                 (not a complete product identifier)."
    ::= { xcmPidWCPro 29 }
        -- ::= {1.3.6.1.4.1.253.8.62.1.20.1.29 }
            -- => SAP PID string = "D1M"
            -- => USB PID string = 16906 = 0x420A
            -- => Compatible ID = XR_PS_Office_Color

xcmPidWC7665V1 OBJECT-IDENTITY
    STATUS      current
    DESCRIPTION
        "WorkCentre 7665 system identifier
         launch configuration version #1, and
         complete product identifier."
    ::= { xcmPidWC7665 1 }
        -- ::= {1.3.6.1.4.1.253.8.62.1.20.1.29.1 }

--
-- Patriot / Lexington branding is "WorkCentre" however
--     the functionality is the same as WorkCentre Pro.

xcmPidWC7675 OBJECT-IDENTITY
    STATUS      current
    DESCRIPTION
        "WorkCentre 7675 system identifier
                 (not a complete product identifier)."
    ::= { xcmPidWCPro 36 }
        -- ::= {1.3.6.1.4.1.253.8.62.1.20.1.36 }
            -- => SAP PID string = "D1S"
            -- => USB PID string = 16912 = 0x4210
            -- => Compatible ID = XR_PS_Office_Color

xcmPidWC7675V1 OBJECT-IDENTITY
    STATUS      current
    DESCRIPTION
        "WorkCentre 7675 system identifier
         launch configuration version #1, and
         complete product identifier."
    ::= { xcmPidWC7675 1 }
        -- ::= {1.3.6.1.4.1.253.8.62.1.20.1.36.1 }

--
--

--
--

--
--

--
--

--
--

-- WorkCentre Pro C2128 (Copeland 28ppm / 21ppm color)

xcmPidWCPC2128 OBJECT-IDENTITY
    STATUS      current
    DESCRIPTION
        "WorkCentre Pro C2128 multi-function system
                 identifier (not a complete product identifier)."
    ::= { xcmPidWCPro 19 }
        -- ::= {1.3.6.1.4.1.253.8.62.1.20.1.19}
            -- => SAP PID string = "D1C"
            -- => USB PID string = 16896 = 0x4200

xcmPidWCPC2128V1 OBJECT-IDENTITY
    STATUS      current
    DESCRIPTION
        "WorkCentre Pro C2128 multi-function system launch configuration
                 and version #1, and complete product identifier."
    ::= { xcmPidWCPC2128 1 }
        -- ::= {1.3.6.1.4.1.253.8.62.1.20.1.19.1}

-- WorkCentre Pro C2636 (Copeland 36ppm / 26ppm color)

xcmPidWCPC2636 OBJECT-IDENTITY
    STATUS      current
    DESCRIPTION
        "WorkCentre Pro C2636 multi-function system
                 identifier (not a complete product identifier)."
    ::= { xcmPidWCPro 20 }


        -- ::= {1.3.6.1.4.1.253.8.62.1.20.1.20}
            -- => SAP PID string = "D1D"
            -- => USB PID string = 16897 = 0x4201

xcmPidWCPC2636V1 OBJECT-IDENTITY
    STATUS      current
    DESCRIPTION
        "WorkCentre Pro C2636 multi-function system launch configuration
                 and version #1, and complete product identifier."
    ::= { xcmPidWCPC2636 1 }
        -- ::= {1.3.6.1.4.1.253.8.62.1.20.1.20.1}

-- WorkCentre Pro C3545 (Copeland 45ppm / 35ppm color)

xcmPidWCPC3545 OBJECT-IDENTITY
    STATUS      current
    DESCRIPTION
        "WorkCentre Pro C3545 multi-function system
                 identifier (not a complete product identifier)."
    ::= { xcmPidWCPro 21 }
        -- ::= {1.3.6.1.4.1.253.8.62.1.20.1.21}
            -- => SAP PID string = "D1E"
            -- => USB PID string = 16898 = 0x4202

xcmPidWCPC3545V1 OBJECT-IDENTITY
    STATUS      current
    DESCRIPTION
        "WorkCentre Pro C3545 multi-function system launch configuration
                 and version #1, and complete product identifier."
    ::= { xcmPidWCPC3545 1 }
        -- ::= {1.3.6.1.4.1.253.8.62.1.20.1.21.1}

--
--

--
-- WorkCentre MultiFunction Series

xcmPidWCMF OBJECT-IDENTITY
    STATUS      current
    DESCRIPTION
        "WorkCentre System identifier
                 (not a complete product identifier)."
    ::= { xcmPidWorkCentreMFSystems 2 }
        -- ::= {1.3.6.1.4.1.253.8.62.1.20.2 }

----------------------------------------------------------------
----------------------------------------------------------------


xcmPidWCMF3 OBJECT-IDENTITY
    STATUS      current
    DESCRIPTION
        "WorkCentrePro System product line identifier
                 (not a complete product identifier)."
    ::= { xcmPidWorkCentreMFSystems 3 }
        -- ::= {1.3.6.1.4.1.253.8.62.1.20.3 }

--
--

xcmPidWCM35 OBJECT-IDENTITY
    STATUS      current
    DESCRIPTION
        "WorkCentre M35 multi-function system identifier
                (not a complete product identifier)."
    ::= { xcmPidWCMF 2 }
        -- ::= {1.3.6.1.4.1.253.8.62.1.20.2.2 }


            -- => SAP PID string = "D22"

xcmPidWCM35V1 OBJECT-IDENTITY
    STATUS      current
    DESCRIPTION
        "WorkCentre M35 multi-function system,
                 launch configuration version #1, and
                 complete product identifier."
    ::= { xcmPidWCM35 1 }
        -- ::= {1.3.6.1.4.1.253.8.62.1.20.2.2.1}

xcmPidWCM35V2 OBJECT-IDENTITY
    STATUS      current
    DESCRIPTION
        "WorkCentre M35 multi-function system,
                 launch configuration version #2, and
                 complete product identifier."
    ::= { xcmPidWCM35 2 }
        -- ::= {1.3.6.1.4.1.253.8.62.1.20.2.2.2}

xcmPidWCM45 OBJECT-IDENTITY
    STATUS      current
    DESCRIPTION
        "WorkCentre M45 multi-function system identifier
                (not a complete product identifier)."
    ::= { xcmPidWCMF 3 }
        -- ::= {1.3.6.1.4.1.253.8.62.1.20.2.3 }
            -- => SAP PID string = "D23"

xcmPidWCM45V1 OBJECT-IDENTITY
    STATUS      current
    DESCRIPTION
        "WorkCentre M45 multi-function system,
                 launch configuration version #1, and
                 complete product identifier."
    ::= { xcmPidWCM45 1 }
        -- ::= {1.3.6.1.4.1.253.8.62.1.20.2.3.1}

xcmPidWCM45V2 OBJECT-IDENTITY
    STATUS      current
    DESCRIPTION
        "WorkCentre M45 multi-function system,
                 launch configuration version #2, and
                 complete product identifier."
    ::= { xcmPidWCM45 2 }
        -- ::= {1.3.6.1.4.1.253.8.62.1.20.2.3.2}

xcmPidWCM55 OBJECT-IDENTITY
    STATUS      current
    DESCRIPTION
        "WorkCentre M55 multi-function system identifier
                (not a complete product identifier)."
    ::= { xcmPidWCMF 4 }
        -- ::= {1.3.6.1.4.1.253.8.62.1.20.2.4 }


            -- => SAP PID string = "D24"

xcmPidWCM55V1 OBJECT-IDENTITY
    STATUS      current
    DESCRIPTION
        "WorkCentre M55 multi-function system,
                 launch configuration version #1, and
                 complete product identifier."
    ::= { xcmPidWCM55 1 }
        -- ::= {1.3.6.1.4.1.253.8.62.1.20.2.4.1}

xcmPidWCM55V2 OBJECT-IDENTITY
    STATUS      current
    DESCRIPTION
        "WorkCentre M55 multi-function system,
                 launch configuration version #2, and
                 complete product identifier."
    ::= { xcmPidWCM55 2 }
        -- ::= {1.3.6.1.4.1.253.8.62.1.20.2.4.2}

-- WorkCentre M165

xcmPidWCM165 OBJECT-IDENTITY
    STATUS      current
    DESCRIPTION
        "WorkCentre  M165 multi-function system identifier
                 (not a complete product identifier)."
    ::= { xcmPidWCMF 5 }
        -- ::= {1.3.6.1.4.1.253.8.62.1.20.2.5 }
            -- => SAP PID string = "D25"

xcmPidWCM165V1 OBJECT-IDENTITY
    STATUS      current
    DESCRIPTION
        "WorkCentre  M165 multi-function system,
                 launch configuration version #1, and
                 complete product identifier."
    ::= { xcmPidWCM165 1 }
        -- ::= {1.3.6.1.4.1.253.8.62.1.20.2.5.1}

-- WorkCentre  M175

xcmPidWCM175 OBJECT-IDENTITY
    STATUS      current
    DESCRIPTION
        "WorkCentre  M175 multi-function system identifier
                 (not a complete product identifier)."
    ::= { xcmPidWCMF 6 }
        -- ::= {1.3.6.1.4.1.253.8.62.1.20.2.6 }
            -- => SAP PID string = "D26"


xcmPidWCM175V1 OBJECT-IDENTITY
    STATUS      current
    DESCRIPTION
        "WorkCentre  M175 multi-function system,
                 launch configuration version #1, and
                 complete product identifier."
    ::= { xcmPidWCM175 1 }
        -- ::= {1.3.6.1.4.1.253.8.62.1.20.2.6.1}

--
--

-- WorkCentre M35 with PostScript

xcmPidWCMPS35 OBJECT-IDENTITY


    STATUS      current
    DESCRIPTION
        "WorkCentre  M35 PostScript multi-function system identifier
                 (not a complete product identifier)."
    ::= { xcmPidWCMF 9 }
        -- ::= {1.3.6.1.4.1.253.8.62.1.20.2.9 }
            -- => SAP PID string = "D29"
            -- => USB PID string = 16929 = 0x4221

xcmPidWCMPS35V1 OBJECT-IDENTITY
    STATUS      current
    DESCRIPTION
        "WorkCentre  M35 PostScript multi-function system,
                 launch configuration version #1, and
                 complete product identifier."
    ::= { xcmPidWCMPS35 1 }
        -- ::= {1.3.6.1.4.1.253.8.62.1.20.2.9.1}

-- WorkCentre M45 with PostScript

xcmPidWCMPS45 OBJECT-IDENTITY
    STATUS      current
    DESCRIPTION
        "WorkCentre  M45 PostScript multi-function system identifier
                 (not a complete product identifier)."
    ::= { xcmPidWCMF 17 }
        -- ::= {1.3.6.1.4.1.253.8.62.1.20.2.17 }
            -- => SAP PID string = "D2A"
            -- => USB PID string = 16930 = 0x4222

xcmPidWCMPS45V1 OBJECT-IDENTITY
    STATUS      current
    DESCRIPTION
        "WorkCentre  M45 PostScript multi-function system,
                 launch configuration version #1, and
                 complete product identifier."
    ::= { xcmPidWCMPS45 1 }
        -- ::= {1.3.6.1.4.1.253.8.62.1.20.2.17.1}

-- WorkCentre M55 with PostScript

xcmPidWCMPS55 OBJECT-IDENTITY
    STATUS      current
    DESCRIPTION
        "WorkCentre  M55 PostScript multi-function system identifier
                 (not a complete product identifier)."
    ::= { xcmPidWCMF 18 }
        -- ::= {1.3.6.1.4.1.253.8.62.1.20.2.18 }
            -- => SAP PID string = "D2B"
            -- => USB PID string = 16931 = 0x4223


xcmPidWCMPS55V1 OBJECT-IDENTITY
    STATUS      current
    DESCRIPTION
        "WorkCentre  M55 PostScript multi-function system,
                 launch configuration version #1, and
                 complete product identifier."
    ::= { xcmPidWCMPS55 1 }
        -- ::= {1.3.6.1.4.1.253.8.62.1.20.2.18.1}

-- WorkCentre M165 with PostScript

xcmPidWCMPS165 OBJECT-IDENTITY
    STATUS      current
    DESCRIPTION
        "WorkCentre  M165 PostScript multi-function system identifier
                 (not a complete product identifier)."
    ::= { xcmPidWCMF 19 }
        -- ::= {1.3.6.1.4.1.253.8.62.1.20.2.19 }
            -- => SAP PID string = "D2C"
            -- => USB PID string = 16932 = 0x4224

xcmPidWCMPS165V1 OBJECT-IDENTITY
    STATUS      current
    DESCRIPTION
        "WorkCentre  M165 PostScript multi-function system,
                 launch configuration version #1, and
                 complete product identifier."
    ::= { xcmPidWCMPS165 1 }
        -- ::= {1.3.6.1.4.1.253.8.62.1.20.2.19.1}

-- WorkCentre M175 with PostScript

xcmPidWCMPS175 OBJECT-IDENTITY
    STATUS      current
    DESCRIPTION
        "WorkCentre  M175 PostScript multi-function system identifier
                 (not a complete product identifier)."
    ::= { xcmPidWCMF 20 }
        -- ::= {1.3.6.1.4.1.253.8.62.1.20.2.20 }
            -- => SAP PID string = "D2D"
            -- => USB PID string = 16933 = 0x4225

xcmPidWCMPS175V1 OBJECT-IDENTITY
    STATUS      current
    DESCRIPTION
        "WorkCentre  M175 PostScript multi-function system,
                 launch configuration version #1, and


                 complete product identifier."
    ::= { xcmPidWCMPS175 1 }
        -- ::= {1.3.6.1.4.1.253.8.62.1.20.2.20.1}

-- WorkCentre + PostScript 232

xcmPidWCPS232 OBJECT-IDENTITY
    STATUS      current
    DESCRIPTION
        "WorkCentre + PostScript 232 multi-function system identifier
                 (not a complete product identifier)."
    ::= { xcmPidWCMF 26 }
        -- ::= {1.3.6.1.4.1.253.8.62.1.20.2.26}
            -- => SAP PID string = "D2J"
            -- => USB PID string = 16939 = 0x422B

xcmPidWCPS232V1 OBJECT-IDENTITY
    STATUS      current
    DESCRIPTION
        "WorkCentre + PostScript 232 multi-function system,
                 launch configuration version #1, and
                 complete product identifier."
    ::= { xcmPidWCPS232 1 }
        -- ::= {1.3.6.1.4.1.253.8.62.1.20.2.26.1}

-- WorkCentre + PostScript 238

xcmPidWCPS238 OBJECT-IDENTITY
    STATUS      current
    DESCRIPTION
        "WorkCentre + PostScript 238 multi-function system identifier
                 (not a complete product identifier)."
    ::= { xcmPidWCMF 27 }
        -- ::= {1.3.6.1.4.1.253.8.62.1.20.2.27}
            -- => SAP PID string = "D2K"
            -- => USB PID string = 16940 = 0x422C

xcmPidWCPS238V1 OBJECT-IDENTITY
    STATUS      current
    DESCRIPTION
        "WorkCentre + PostScript 238 multi-function system,
                 launch configuration version #1, and
                 complete product identifier."
    ::= { xcmPidWCPS238 1 }
        -- ::= {1.3.6.1.4.1.253.8.62.1.20.2.27.1}

-- WorkCentre + PostScript 245


xcmPidWCPS245 OBJECT-IDENTITY
    STATUS      current
    DESCRIPTION
        "WorkCentre + PostScript 245 multi-function system identifier
                 (not a complete product identifier)."
    ::= { xcmPidWCMF 28 }
        -- ::= {1.3.6.1.4.1.253.8.62.1.20.2.28}
            -- => SAP PID string = "D2L"
            -- => USB PID string = 16941 = 0x422D

xcmPidWCPS245V1 OBJECT-IDENTITY
    STATUS      current
    DESCRIPTION
        "WorkCentre + PostScript 245 multi-function system,
                 launch configuration version #1, and
                 complete product identifier."
    ::= { xcmPidWCPS245 1 }
        -- ::= {1.3.6.1.4.1.253.8.62.1.20.2.28.1}

-- WorkCentre + PostScript 255

xcmPidWCPS255 OBJECT-IDENTITY
    STATUS      current
    DESCRIPTION
        "WorkCentre + PostScript 255 multi-function system identifier
                 (not a complete product identifier)."
    ::= { xcmPidWCMF 29 }
        -- ::= {1.3.6.1.4.1.253.8.62.1.20.2.29}
            -- => SAP PID string = "D2M"
            -- => USB PID string = 16942 = 0x422E

xcmPidWCPS255V1 OBJECT-IDENTITY
    STATUS      current
    DESCRIPTION
        "WorkCentre + PostScript 255 multi-function system,
                 launch configuration version #1, and
                 complete product identifier."
    ::= { xcmPidWCPS255 1 }
        -- ::= {1.3.6.1.4.1.253.8.62.1.20.2.29.1}

-- WorkCentre Pro 232

xcmPidWCP232 OBJECT-IDENTITY
    STATUS      current
    DESCRIPTION
        "WorkCentre Pro 232 multi-function system identifier
                 (not a complete product identifier)."
    ::= { xcmPidWCMF 30 }


        -- ::= {1.3.6.1.4.1.253.8.62.1.20.2.30}
            -- => SAP PID string = "D2N"
            -- => USB PID string = 16943 = 0x422F

xcmPidWCP232V1 OBJECT-IDENTITY
    STATUS      current
    DESCRIPTION
        "WorkCentre Pro 232 multi-function system,
                 launch configuration version #1, and
                 complete product identifier."
    ::= { xcmPidWCP232 1 }
        -- ::= {1.3.6.1.4.1.253.8.62.1.20.2.30.1}

-- WorkCentre Pro 238

xcmPidWCP238 OBJECT-IDENTITY
    STATUS      current
    DESCRIPTION
        "WorkCentre Pro 238 multi-function system identifier
                 (not a complete product identifier)."
    ::= { xcmPidWCMF 31 }
        -- ::= {1.3.6.1.4.1.253.8.62.1.20.2.31}
            -- => SAP PID string = "D2O"
            -- => USB PID string = 16944 = 0x4230

xcmPidWCP238V1 OBJECT-IDENTITY
    STATUS      current
    DESCRIPTION
        "WorkCentre Pro 238 multi-function system,
                 launch configuration version #1, and
                 complete product identifier."
    ::= { xcmPidWCP238 1 }
        -- ::= {1.3.6.1.4.1.253.8.62.1.20.2.31.1}

-- WorkCentre Pro 245

xcmPidWCP245 OBJECT-IDENTITY
    STATUS      current
    DESCRIPTION
        "WorkCentre Pro 245 multi-function system identifier
                 (not a complete product identifier)."
    ::= { xcmPidWCMF 32 }
        -- ::= {1.3.6.1.4.1.253.8.62.1.20.2.32}
            -- => SAP PID string = "D2P"
            -- => USB PID string = 16945 = 0x4231

xcmPidWCP245V1 OBJECT-IDENTITY
    STATUS      current
    DESCRIPTION
        "WorkCentre Pro 245 multi-function system,


                 launch configuration version #1, and
                 complete product identifier."
    ::= { xcmPidWCP245 1 }
        -- ::= {1.3.6.1.4.1.253.8.62.1.20.2.32.1}

-- WorkCentre Pro 255

xcmPidWCP255 OBJECT-IDENTITY
    STATUS      current
    DESCRIPTION
        "WorkCentre Pro 255 multi-function system identifier
                 (not a complete product identifier)."
    ::= { xcmPidWCMF 33 }
        -- ::= {1.3.6.1.4.1.253.8.62.1.20.2.33}
            -- => SAP PID string = "D2Q"
            -- => USB PID string = 16946 = 0x4232

xcmPidWCP255V1 OBJECT-IDENTITY
    STATUS      current
    DESCRIPTION
        "WorkCentre Pro 255 multi-function system,
                 launch configuration version #1, and
                 complete product identifier."
    ::= { xcmPidWCP255 1 }
        -- ::= {1.3.6.1.4.1.253.8.62.1.20.2.33.1}

-- WorkCentre 232

xcmPidWC232 OBJECT-IDENTITY
    STATUS      current
    DESCRIPTION
        "WorkCentre 232 multi-function system identifier
                 (not a complete product identifier)."
    ::= { xcmPidWCMF 34 }
        -- ::= {1.3.6.1.4.1.253.8.62.1.20.2.34}
            -- => SAP PID string = "D2R"
            -- => USB PID string = 16947 = 0x4233

xcmPidWC232V1 OBJECT-IDENTITY
    STATUS      current
    DESCRIPTION
        "WorkCentre 232 multi-function system,
                 launch configuration version #1, and
                 complete product identifier."
    ::= { xcmPidWC232 1 }
        -- ::= {1.3.6.1.4.1.253.8.62.1.20.2.34.1}

-- WorkCentre 238


xcmPidWC238 OBJECT-IDENTITY
    STATUS      current
    DESCRIPTION
        "WorkCentre 238 multi-function system identifier
                 (not a complete product identifier)."
    ::= { xcmPidWCMF 35 }
        -- ::= {1.3.6.1.4.1.253.8.62.1.20.2.35}
            -- => SAP PID string = "D2S"
            -- => USB PID string = 16948 = 0x4234

xcmPidWC238V1 OBJECT-IDENTITY
    STATUS      current
    DESCRIPTION
        "WorkCentre 238 multi-function system,
                 launch configuration version #1, and
                 complete product identifier."
    ::= { xcmPidWC238 1 }
        -- ::= {1.3.6.1.4.1.253.8.62.1.20.2.35.1}

-- WorkCentre 245

xcmPidWC245 OBJECT-IDENTITY
    STATUS      current
    DESCRIPTION
        "WorkCentre 245 multi-function system identifier
                 (not a complete product identifier)."
    ::= { xcmPidWCMF 36 }
        -- ::= {1.3.6.1.4.1.253.8.62.1.20.2.36}
            -- => SAP PID string = "D2T"
            -- => USB PID number = 16949 = 0x4235

xcmPidWC245V1 OBJECT-IDENTITY
    STATUS      current
    DESCRIPTION
        "WorkCentre 245 multi-function system,
                 launch configuration version #1, and
                 complete product identifier."
    ::= { xcmPidWC245 1 }
        -- ::= {1.3.6.1.4.1.253.8.62.1.20.2.36.1}

-- WorkCentre 255

xcmPidWC255 OBJECT-IDENTITY
    STATUS      current
    DESCRIPTION
        "WorkCentre 255 multi-function system identifier
                 (not a complete product identifier)."
    ::= { xcmPidWCMF 37 }
        -- ::= {1.3.6.1.4.1.253.8.62.1.20.2.37}


            -- => SAP PID string = "D2U"
            -- => USB PID string = 16950 = 0x4236

xcmPidWC255V1 OBJECT-IDENTITY
    STATUS      current
    DESCRIPTION
        "WorkCentre 255 multi-function system,
                 launch configuration version #1, and
                 complete product identifier."
    ::= { xcmPidWC255 1 }
        -- ::= {1.3.6.1.4.1.253.8.62.1.20.2.37.1}

--

-- WorkCentre M128
--      FX developed mono multi-function machine for
--      XC market (28ppm)
--



xcmPidWCMF28 OBJECT-IDENTITY
    STATUS      current
    DESCRIPTION
        "Xerox WorkCentre M128 multi-function system identifier
                 (not a complete product identifier)."
    ::= { xcmPidWCMF 23 }
        -- ::= {1.3.6.1.4.1.253.8.62.1.20.2.23}
            -- => SAP PID string = "D2G"
            -- => USB PID string = 16936 = 0x4228

xcmPidWCMFM28 OBJECT-IDENTITY
    STATUS      current
    DESCRIPTION
        "Xerox WorkCentre M128 multi-function system,
                 launch configuration version #1, and
                 complete product identifier."
    ::= { xcmPidWCMF28 1 }
        -- ::= {1.3.6.1.4.1.253.8.62.1.20.2.23.1}

--
--

--

-- WorkCentre 5135

xcmPidWorkCentre5135 OBJECT-IDENTITY
    STATUS      current
    DESCRIPTION
        "Xerox WorkCentre 5135 model identifier
                 (not a complete product identifier)."
    ::= { xcmPidWCMF 40 }
        -- ::= {1.3.6.1.4.1.253.8.62.1.20.2.40}
            -- => SAP PID string = "D2X"
            -- => USB PID string = 16953 = 0x4239
--
-- PNP PID Generation PLEASE NOTE:
--   The following assumes the IEEE 1284 Device ID contains the
--   following attributes:
--      MFG:Xerox MDL:WorkCentre 5135
--   The following PNP IDs were generated using these
--   parameters (manufacturer / model ):
--     -mf "Xerox" -mo "WorkCentre 5135"
--   The generated PNP PID is only valid for those parameters
--      WorkCentre 5135      XeroxWorkCentre_51352AA4

xcmPidWorkCentre5135C1 OBJECT-IDENTITY
    STATUS      current
    DESCRIPTION
        "Xerox WorkCentre 5135 model and configuration 1 identifier
           (not a complete product identifier)."
    ::= { xcmPidWorkCentre5135 1 }
        -- ::= {1.3.6.1.4.1.253.8.62.1.20.2.40.1}

-- WorkCentre Model 5135 Configuration One Version One

xcmPidWorkCentre5135C1V1 OBJECT-IDENTITY
    STATUS      current
    DESCRIPTION
        "Xerox WorkCentre 5135 launch model, configuration 1,
           version 1.  A complete product identifier."
    ::= { xcmPidWorkCentre5135C1 1 }
        -- ::= {1.3.6.1.4.1.253.8.62.1.20.2.40.1.1}

xcmPidWorkCentre5135C1V2 OBJECT-IDENTITY
    STATUS      current
    DESCRIPTION


        "Xerox WorkCentre 5135 launch model, configuration 1,
           version 2.  A complete product identifier."
    ::= { xcmPidWorkCentre5135C1 2 }
        -- ::= {1.3.6.1.4.1.253.8.62.1.20.2.40.1.2}

-- WorkCentre 5150

xcmPidWorkCentre5150 OBJECT-IDENTITY
    STATUS      current
    DESCRIPTION
        "Xerox WorkCentre 5150 model identifier
                 (not a complete product identifier)."
    ::= { xcmPidWCMF 41 }
        -- ::= {1.3.6.1.4.1.253.8.62.1.20.2.41}
            -- => SAP PID string = "D2Y"
            -- => USB PID string = 16954 = 0x423A
--
-- PNP PID Generation PLEASE NOTE:
--   The following assumes the IEEE 1284 Device ID contains the
--   following attributes:
--      MFG:Xerox MDL:WorkCentre 5150
--   The following PNP IDs were generated using these
--   parameters (manufacturer / model ):
--     -mf "Xerox" -mo "WorkCentre 5150"
--   The generated PNP PID is only valid for those parameters
--      WorkCentre 5150      XeroxWorkCentre_51508967

xcmPidWorkCentre5150C1 OBJECT-IDENTITY
    STATUS      current
    DESCRIPTION
        "Xerox WorkCentre 5150 model and configuration 1 identifier
           (not a complete product identifier)."
    ::= { xcmPidWorkCentre5150 1 }
        -- ::= {1.3.6.1.4.1.253.8.62.1.20.2.41.1}

-- WorkCentre Model 5150 Configuration One Version One

xcmPidWorkCentre5150C1V1 OBJECT-IDENTITY
    STATUS      current
    DESCRIPTION
        "Xerox WorkCentre 5150 launch model, configuration 1,
           version 1.  A complete product identifier."
    ::= { xcmPidWorkCentre5150C1 1 }
        -- ::= {1.3.6.1.4.1.253.8.62.1.20.2.41.1.1}

xcmPidWorkCentre5150C1V2 OBJECT-IDENTITY
    STATUS      current
    DESCRIPTION
        "Xerox WorkCentre 5150 launch model, configuration 1,
           version 2.  A complete product identifier."
    ::= { xcmPidWorkCentre5150C1 2 }
        -- ::= {1.3.6.1.4.1.253.8.62.1.20.2.41.1.2}


--
--

--

-- WorkCentre 5632

xcmPidWC5632 OBJECT-IDENTITY
    STATUS      current
    DESCRIPTION
        "WorkCentre 5632 multi-function system identifier
                 (not a complete product identifier)."
    ::= { xcmPidWCMF3 35 }


        -- ::= {1.3.6.1.4.1.253.8.62.1.20.3.35}
            -- => SAP PID string = "D3S"
            -- => USB PID string = 16984 = 0x4258
            -- => Compatible ID = XR_PS_Office_Mono

--
-- PNP PID Generation PLEASE NOTE:
--   The following assumes the IEEE 1284 Device ID contains the
--   following attributes:
--      MFG:Xerox MDL:WorkCentre 5632
--   The following PNP IDs were generated using these
--   parameters (manufacturer / model ):
--     -mf "Xerox" -mo "WorkCentre 5632"
--   The generated PNP PID is only valid for those parameters
--      WorkCentre 5632      XeroxWorkCentre_56322954

xcmPidWC5632V1 OBJECT-IDENTITY
    STATUS      current
    DESCRIPTION
        "WorkCentre 5632 multi-function system,
                 launch configuration version #1, and
                 complete product identifier."
    ::= { xcmPidWC5632 1 }
        -- ::= {1.3.6.1.4.1.253.8.62.1.20.3.35.1}

--
--

--
--

-- WorkCentre 5638

xcmPidWC5638 OBJECT-IDENTITY
    STATUS      current
    DESCRIPTION
        "WorkCentre 5638 multi-function system identifier
                 (not a complete product identifier)."
    ::= { xcmPidWCMF3 37 }
        -- ::= {1.3.6.1.4.1.253.8.62.1.20.3.37}
            -- => SAP PID string = "D3U"
            -- => USB PID string = 16986 = 0x425A
            -- => Compatible ID = XR_PS_Office_Mono

--
-- PNP PID Generation PLEASE NOTE:
--   The following assumes the IEEE 1284 Device ID contains the
--   following attributes:
--      MFG:Xerox MDL:WorkCentre 5638
--   The following PNP IDs were generated using these
--   parameters (manufacturer / model ):
--     -mf "Xerox" -mo "WorkCentre 5638"
--   The generated PNP PID is only valid for those parameters
--      WorkCentre 5638      XeroxWorkCentre_56382ED4

xcmPidWC5638V1 OBJECT-IDENTITY
    STATUS      current
    DESCRIPTION
        "WorkCentre 5638 multi-function system,
                 launch configuration version #1, and
                 complete product identifier."
    ::= { xcmPidWC5638 1 }
        -- ::= {1.3.6.1.4.1.253.8.62.1.20.3.37.1}

--
--

-- WorkCentre 5645

xcmPidWC5645 OBJECT-IDENTITY
    STATUS      current
    DESCRIPTION
        "WorkCentre 5645 multi-function system identifier
                 (not a complete product identifier)."
    ::= { xcmPidWCMF3 38 }
        -- ::= {1.3.6.1.4.1.253.8.62.1.20.3.38}
            -- => SAP PID string = "D3V"
            -- => USB PID string = 16987 = 0x425B
            -- => Compatible ID = XR_PS_Office_Mono

--
-- PNP PID Generation PLEASE NOTE:
--   The following assumes the IEEE 1284 Device ID contains the
--   following attributes:
--      MFG:Xerox MDL:WorkCentre 5645
--   The following PNP IDs were generated using these
--   parameters (manufacturer / model ):
--     -mf "Xerox" -mo "WorkCentre 5645"
--   The generated PNP PID is only valid for those parameters
--      WorkCentre 5645      XeroxWorkCentre_5645DB17

xcmPidWC5645V1 OBJECT-IDENTITY
    STATUS      current
    DESCRIPTION
        "WorkCentre 5645 multi-function system,
                 launch configuration version #1, and
                 complete product identifier."
    ::= { xcmPidWC5645 1 }
        -- ::= {1.3.6.1.4.1.253.8.62.1.20.3.38.1}

--


--

-- WorkCentre 5655

xcmPidWC5655 OBJECT-IDENTITY
    STATUS      current
    DESCRIPTION
        "WorkCentre 5655 multi-function system identifier
                 (not a complete product identifier)."
    ::= { xcmPidWCMF3 39 }
        -- ::= {1.3.6.1.4.1.253.8.62.1.20.3.39}
            -- => SAP PID string = "D3W"
            -- => USB PID string = 16988 = 0x425C
            -- => Compatible ID = XR_PS_Office_Mono

--
-- PNP PID Generation PLEASE NOTE:
--   The following assumes the IEEE 1284 Device ID contains the
--   following attributes:
--      MFG:Xerox MDL:WorkCentre 5655
--   The following PNP IDs were generated using these
--   parameters (manufacturer / model ):
--     -mf "Xerox" -mo "WorkCentre 5655"
--   The generated PNP PID is only valid for those parameters
--      WorkCentre 5655      XeroxWorkCentre_56554B16

xcmPidWC5655V1 OBJECT-IDENTITY
    STATUS      current
    DESCRIPTION
        "WorkCentre 5655 multi-function system,
                 launch configuration version #1, and
                 complete product identifier."
    ::= { xcmPidWC5655 1 }
        -- ::= {1.3.6.1.4.1.253.8.62.1.20.3.39.1}

--
--


-- WorkCentre 5665

xcmPidWC5665 OBJECT-IDENTITY
    STATUS      current
    DESCRIPTION
        "WorkCentre 5665 multi-function system identifier
                 (not a complete product identifier)."
    ::= { xcmPidWCMF3 40 }
        -- ::= {1.3.6.1.4.1.253.8.62.1.20.3.40}
            -- => SAP PID string = "D3X"
            -- => USB PID string = 16989 = 0x425D
            -- => Compatible ID = XR_PS_Office_Mono

--
-- PNP PID Generation PLEASE NOTE:
--   The following assumes the IEEE 1284 Device ID contains the
--   following attributes:
--      MFG:Xerox MDL:WorkCentre 5665
--   The following PNP IDs were generated using these
--   parameters (manufacturer / model ):
--     -mf "Xerox" -mo "WorkCentre 5665"
--   The generated PNP PID is only valid for those parameters
--      WorkCentre 5665      XeroxWorkCentre_5665BB16

xcmPidWC5665V1 OBJECT-IDENTITY
    STATUS      current
    DESCRIPTION
        "WorkCentre 5665 multi-function system,
                 launch configuration version #1, and
                 complete product identifier."
    ::= { xcmPidWC5665 1 }
        -- ::= {1.3.6.1.4.1.253.8.62.1.20.3.40.1}

--
--


-- WorkCentre 5675

xcmPidWC5675 OBJECT-IDENTITY
    STATUS      current
    DESCRIPTION
        "WorkCentre 5675 multi-function system identifier
                 (not a complete product identifier)."
    ::= { xcmPidWCMF3 41 }
        -- ::= {1.3.6.1.4.1.253.8.62.1.20.3.41}
            -- => SAP PID string = "D3Y"
            -- => USB PID string = 16990 = 0x425E
            -- => Compatible ID = XR_PS_Office_Mono

--
-- PNP PID Generation PLEASE NOTE:
--   The following assumes the IEEE 1284 Device ID contains the
--   following attributes:
--      MFG:Xerox MDL:WorkCentre 5675
--   The following PNP IDs were generated using these
--   parameters (manufacturer / model ):
--     -mf "Xerox" -mo "WorkCentre 5675"
--   The generated PNP PID is only valid for those parameters
--      WorkCentre 5675      XeroxWorkCentre_56752B17

xcmPidWC5675V1 OBJECT-IDENTITY
    STATUS      current
    DESCRIPTION
        "WorkCentre 5675 multi-function system,
                 launch configuration version #1, and
                 complete product identifier."
    ::= { xcmPidWC5675 1 }
        -- ::= {1.3.6.1.4.1.253.8.62.1.20.3.41.1}

--
--


--

----------------------------------------------------------------
----------------------------------------------------------------



xcmPidWCMF4 OBJECT-IDENTITY
    STATUS      current
    DESCRIPTION
        "Xerox WorkCentre System product line identifier
                 (not a complete product identifier)."
    ::= { xcmPidWorkCentreMFSystems 4 }
        -- ::= {1.3.6.1.4.1.253.8.62.1.20.4 }

--
--

-- WorkCentre 5687

xcmPidWC5687 OBJECT-IDENTITY
    STATUS      current
    DESCRIPTION
        "Xerox WorkCentre 5687 multi-function system identifier
                 (not a complete product identifier)."
    ::= { xcmPidWCMF4 9 }
        -- ::= {1.3.6.1.4.1.253.8.62.1.20.4.9}
            -- => SAP PID string = "D49"


            -- => USB PID string = 17001 = 0x4269
            -- => Compatible ID = XR_PS_Office_Mono

--
-- PNP PID Generation PLEASE NOTE:
--   The following assumes the IEEE 1284 Device ID contains the
--   following attributes:
--      MFG:Xerox MDL:WorkCentre 5687
--   The following PNP IDs were generated using these
--   parameters (manufacturer / model ):
--     -mf "Xerox" -mo "WorkCentre 5687"
--   The generated PNP PID is only valid for those parameters
--      WorkCentre 5687      XeroxWorkCentre_56871A93

xcmPidWC5687V1 OBJECT-IDENTITY
    STATUS      current
    DESCRIPTION
        "Xerox WorkCentre 5687 multi-function system,
                 launch configuration version #1, and
                 complete product identifier."
    ::= { xcmPidWC5687 1 }
        -- ::= {1.3.6.1.4.1.253.8.62.1.20.4.9.1}

--
--

-- WorkCentre 5030

xcmPidWC5030 OBJECT-IDENTITY
    STATUS      current
    DESCRIPTION
        "Xerox WorkCentre 5030 multi-function system identifier
                 (not a complete product identifier)."
    ::= { xcmPidWCMF4 17 }
        -- ::= {1.3.6.1.4.1.253.8.62.1.20.4.17}
            -- => SAP PID string = "D4A"


            -- => USB PID string = 17002 = 0x426A

--
-- PNP PID Generation PLEASE NOTE:
--   The following assumes the IEEE 1284 Device ID contains the
--   following attributes:
--      MFG:Xerox MDL:WorkCentre 5030
--   The following PNP IDs were generated using these
--   parameters (manufacturer / model ):
--     -mf "Xerox" -mo "WorkCentre 5030"
--   The generated PNP PID is only valid for those parameters
--      WorkCentre 5030      XeroxWorkCentre_5030E935

xcmPidWC5030V1 OBJECT-IDENTITY
    STATUS      current
    DESCRIPTION
        "Xerox WorkCentre 5030 multi-function system,
                 launch configuration version #1, and
                 complete product identifier."
    ::= { xcmPidWC5030 1 }
        -- ::= {1.3.6.1.4.1.253.8.62.1.20.4.17.1}

xcmPidWC5030V2 OBJECT-IDENTITY
    STATUS      current
    DESCRIPTION
        "Xerox WorkCentre 5030 multi-function system,
                 launch configuration version #2, and
                 complete product identifier."
    ::= { xcmPidWC5030 2 }
        -- ::= {1.3.6.1.4.1.253.8.62.1.20.4.17.2}

-- WorkCentre 5050

xcmPidWC5050 OBJECT-IDENTITY
    STATUS      current
    DESCRIPTION
        "Xerox WorkCentre 5050 multi-function system identifier
                 (not a complete product identifier)."
    ::= { xcmPidWCMF4 18 }
        -- ::= {1.3.6.1.4.1.253.8.62.1.20.4.18}
            -- => SAP PID string = "D4B"
            -- => USB PID string = 17003 = 0x426B

--
-- PNP PID Generation PLEASE NOTE:
--   The following assumes the IEEE 1284 Device ID contains the
--   following attributes:
--      MFG:Xerox MDL:WorkCentre 5050
--   The following PNP IDs were generated using these
--   parameters (manufacturer / model ):
--     -mf "Xerox" -mo "WorkCentre 5050"


--   The generated PNP PID is only valid for those parameters
--      WorkCentre 5050      XeroxWorkCentre_50504936

xcmPidWC5050V1 OBJECT-IDENTITY
    STATUS      current
    DESCRIPTION
        "Xerox WorkCentre 5050 multi-function system,
                 launch configuration version #1, and
                 complete product identifier."
    ::= { xcmPidWC5050 1 }
        -- ::= {1.3.6.1.4.1.253.8.62.1.20.4.18.1}

xcmPidWC5050V2 OBJECT-IDENTITY
    STATUS      current
    DESCRIPTION
        "Xerox WorkCentre 5050 multi-function system,
                 launch configuration version #2, and
                 complete product identifier."
    ::= { xcmPidWC5050 2 }
        -- ::= {1.3.6.1.4.1.253.8.62.1.20.4.18.2}

--
--


--
--

----------------------------------------------------------------
----------------------------------------------------------------


xcmPidWCMF5 OBJECT-IDENTITY
    STATUS      current
    DESCRIPTION
        "Xerox WorkCentre System product line identifier
                 (not a complete product identifier)."
    ::= { xcmPidWorkCentreMFSystems 5 }
        -- ::= {1.3.6.1.4.1.253.8.62.1.20.5 }

--
--

-- WorkCentre 6400


xcmPidWC6400 OBJECT-IDENTITY
    STATUS      current
    DESCRIPTION
        "Xerox WorkCentre 6400 model identifier
           (not a complete product identifier)."
    ::= { xcmPidWCMF5 5 }
        -- ::= {1.3.6.1.4.1.253.8.62.1.20.5.5}
            -- => SAP PID string = "D55"
            -- => USB PID string = 17033 = 0x4289

xcmPidWC6400S OBJECT-IDENTITY
    STATUS      current
    DESCRIPTION
        "Xerox WorkCentre 6400S
           model and configuration identifier
           (not a complete product identifier)."
    ::= { xcmPidWC6400 1 }
        -- ::= {1.3.6.1.4.1.253.8.62.1.20.5.5.1}
--
-- PNP PID Generation PLEASE NOTE:
--   The following assumes the IEEE 1284 Device ID contains the
--   following attributes:
--    MFG:Xerox MDL:WorkCentre 6400S
--   The following PNP ID was generated using these
--   parameters (manufacturer and model):
--     -mf "Xerox" -mo "WorkCentre 6400S"


--   The generated PNP PID is only valid for those parameters
            -- => PnP ID XeroxWorkCentre_64001ADC

      -- => Compatible ID = XR_PS_Office_Color

xcmPidWC6400Sv1 OBJECT-IDENTITY
    STATUS      current
    DESCRIPTION
        "Xerox WorkCentre 6400S
            launch model, configuration, version 1.
            A complete product identifier."
    ::= { xcmPidWC6400S 1 }
        -- ::= {1.3.6.1.4.1.253.8.62.1.20.5.5.1.1}

xcmPidWC6400Sv2 OBJECT-IDENTITY
    STATUS      current
    DESCRIPTION
        "Xerox WorkCentre 6400S
            launch model, configuration, version 2.
            A complete product identifier."
    ::= { xcmPidWC6400S 2 }
        -- ::= {1.3.6.1.4.1.253.8.62.1.20.5.5.1.2}

xcmPidWC6400X OBJECT-IDENTITY
    STATUS      current
    DESCRIPTION
        "Xerox WorkCentre 6400X
           model and configuration identifier
           (not a complete product identifier)."
    ::= { xcmPidWC6400 2 }
        -- ::= {1.3.6.1.4.1.253.8.62.1.20.5.5.2}
--
-- PNP PID Generation PLEASE NOTE:
--   The following assumes the IEEE 1284 Device ID contains the
--   following attributes:
--    MFG:Xerox MDL:WorkCentre 6400X
--   The following PNP ID was generated using these
--   parameters (manufacturer and model):
--     -mf "Xerox" -mo "WorkCentre 6400X"
--   The generated PNP PID is only valid for those parameters
            -- => PnP ID XeroxWorkCentre_6400DD9D

      -- => Compatible ID = XR_PS_Office_Color

xcmPidWC6400Xv1 OBJECT-IDENTITY
    STATUS      current
    DESCRIPTION
        "Xerox WorkCentre 6400X
            launch model, configuration, version 1.
            A complete product identifier."
    ::= { xcmPidWC6400X 1 }
        -- ::= {1.3.6.1.4.1.253.8.62.1.20.5.5.2.1}

xcmPidWC6400Xv2 OBJECT-IDENTITY


    STATUS      current
    DESCRIPTION
        "Xerox WorkCentre 6400X
            launch model, configuration, version 2.
            A complete product identifier."
    ::= { xcmPidWC6400X 2 }
        -- ::= {1.3.6.1.4.1.253.8.62.1.20.5.5.2.2}

xcmPidWC6400XF OBJECT-IDENTITY
    STATUS      current
    DESCRIPTION
        "Xerox WorkCentre 6400XF
           model and configuration identifier
           (not a complete product identifier)."
    ::= { xcmPidWC6400 3 }
        -- ::= {1.3.6.1.4.1.253.8.62.1.20.5.5.3}
--
-- PNP PID Generation PLEASE NOTE:
--   The following assumes the IEEE 1284 Device ID contains the
--   following attributes:
--    MFG:Xerox MDL:WorkCentre 6400XF
--   The following PNP ID was generated using these
--   parameters (manufacturer and model):
--     -mf "Xerox" -mo "WorkCentre 6400XF"
--   The generated PNP PID is only valid for those parameters
            -- => PnP ID XeroxWorkCentre_64005B9D

xcmPidWC6400XFv1 OBJECT-IDENTITY
    STATUS      current
    DESCRIPTION
        "Xerox WorkCentre 6400XF
            launch model, configuration, version 1.
            A complete product identifier."
    ::= { xcmPidWC6400XF 1 }
        -- ::= {1.3.6.1.4.1.253.8.62.1.20.5.5.3.1}

xcmPidWC6400XFv2 OBJECT-IDENTITY
    STATUS      current
    DESCRIPTION
        "Xerox WorkCentre 6400XF
            launch model, configuration, version 2.
            A complete product identifier."
    ::= { xcmPidWC6400XF 2 }
        -- ::= {1.3.6.1.4.1.253.8.62.1.20.5.5.3.2}

--
--

--
--

--


--
--

-- WorkCentre 5735

xcmPidWorkCentre5735 OBJECT-IDENTITY
    STATUS      current
    DESCRIPTION
        "Xerox WorkCentre 5735 model identifier
                 (not a complete product identifier)."
    ::= { xcmPidWCMF5 29 }
        -- ::= {1.3.6.1.4.1.253.8.62.1.20.5.29}
            -- => SAP PID string = "D5M"
            -- => USB PID string = 17050 = 0x429A
--
-- PNP PID Generation PLEASE NOTE:
--   The following assumes the IEEE 1284 Device ID contains the
--   following attributes:
--      MFG:Xerox MDL:WorkCentre 5735
--   The following PNP IDs were generated using these
--   parameters (manufacturer / model ):
--     -mf "Xerox" -mo "WorkCentre 5735"
--   The generated PNP PID is only valid for those parameters
--      WorkCentre 5735      XeroxWorkCentre_57352B46

xcmPidWorkCentre5735C1 OBJECT-IDENTITY
    STATUS      current
    DESCRIPTION
        "Xerox WorkCentre 5735 model and configuration 1 identifier
           (not a complete product identifier)."
    ::= { xcmPidWorkCentre5735 1 }
        -- ::= {1.3.6.1.4.1.253.8.62.1.20.5.29.1}

-- WorkCentre Model 5735 Configuration One Version One

xcmPidWorkCentre5735C1V1 OBJECT-IDENTITY
    STATUS      current
    DESCRIPTION
        "Xerox WorkCentre 5735 launch model, configuration 1,
           version 1.  A complete product identifier."
    ::= { xcmPidWorkCentre5735C1 1 }
        -- ::= {1.3.6.1.4.1.253.8.62.1.20.5.29.1.1}

-- WorkCentre 5740

xcmPidWorkCentre5740 OBJECT-IDENTITY


    STATUS      current
    DESCRIPTION
        "Xerox WorkCentre 5740 model identifier
                 (not a complete product identifier)."
    ::= { xcmPidWCMF5 30 }
        -- ::= {1.3.6.1.4.1.253.8.62.1.20.5.30}
            -- => SAP PID string = "D5N"
            -- => USB PID string = 17051 = 0x429B
--
-- PNP PID Generation PLEASE NOTE:
--   The following assumes the IEEE 1284 Device ID contains the
--   following attributes:
--      MFG:Xerox MDL:WorkCentre 5740
--   The following PNP IDs were generated using these
--   parameters (manufacturer / model ):
--     -mf "Xerox" -mo "WorkCentre 5740"
--   The generated PNP PID is only valid for those parameters
--      WorkCentre 5740      XeroxWorkCentre_57401884

xcmPidWorkCentre5740C1 OBJECT-IDENTITY
    STATUS      current
    DESCRIPTION
        "Xerox WorkCentre 5740 model and configuration 1 identifier
           (not a complete product identifier)."
    ::= { xcmPidWorkCentre5740 1 }
        -- ::= {1.3.6.1.4.1.253.8.62.1.20.5.30.1}

-- WorkCentre Model 5740 Configuration One Version One

xcmPidWorkCentre5740C1V1 OBJECT-IDENTITY
    STATUS      current
    DESCRIPTION
        "Xerox WorkCentre 5740 launch model, configuration 1,
           version 1.  A complete product identifier."
    ::= { xcmPidWorkCentre5740C1 1 }
        -- ::= {1.3.6.1.4.1.253.8.62.1.20.5.30.1.1}

-- WorkCentre 5745

xcmPidWorkCentre5745 OBJECT-IDENTITY
    STATUS      current
    DESCRIPTION
        "Xerox WorkCentre 5745 model identifier
                 (not a complete product identifier)."
    ::= { xcmPidWCMF5 31 }
        -- ::= {1.3.6.1.4.1.253.8.62.1.20.5.31}
            -- => SAP PID string = "D5O"
            -- => USB PID string = 17052 = 0x429C
--
-- PNP PID Generation PLEASE NOTE:


--   The following assumes the IEEE 1284 Device ID contains the
--   following attributes:
--      MFG:Xerox MDL:WorkCentre 5745
--   The following PNP IDs were generated using these
--   parameters (manufacturer / model ):
--     -mf "Xerox" -mo "WorkCentre 5745"
--   The generated PNP PID is only valid for those parameters
--      WorkCentre 5745      XeroxWorkCentre_57451B44

xcmPidWorkCentre5745C1 OBJECT-IDENTITY
    STATUS      current
    DESCRIPTION
        "Xerox WorkCentre 5745 model and configuration 1 identifier
           (not a complete product identifier)."
    ::= { xcmPidWorkCentre5745 1 }
        -- ::= {1.3.6.1.4.1.253.8.62.1.20.5.31.1}

-- WorkCentre Model 5745 Configuration One Version One

xcmPidWorkCentre5745C1V1 OBJECT-IDENTITY
    STATUS      current
    DESCRIPTION
        "Xerox WorkCentre 5745 launch model, configuration 1,
           version 1.  A complete product identifier."
    ::= { xcmPidWorkCentre5745C1 1 }
        -- ::= {1.3.6.1.4.1.253.8.62.1.20.5.31.1.1}

-- WorkCentre 5755

xcmPidWorkCentre5755 OBJECT-IDENTITY
    STATUS      current
    DESCRIPTION
        "Xerox WorkCentre 5755 model identifier
                 (not a complete product identifier)."
    ::= { xcmPidWCMF5 32 }
        -- ::= {1.3.6.1.4.1.253.8.62.1.20.5.32}
            -- => SAP PID string = "D5P"
            -- => USB PID string = 17053 = 0x429D
--
-- PNP PID Generation PLEASE NOTE:
--   The following assumes the IEEE 1284 Device ID contains the
--   following attributes:
--      MFG:Xerox MDL:WorkCentre 5755
--   The following PNP IDs were generated using these
--   parameters (manufacturer / model ):
--     -mf "Xerox" -mo "WorkCentre 5755"
--   The generated PNP PID is only valid for those parameters
--      WorkCentre 5755      XeroxWorkCentre_57558B45

xcmPidWorkCentre5755C1 OBJECT-IDENTITY


    STATUS      current
    DESCRIPTION
        "Xerox WorkCentre 5755 model and configuration 1 identifier
           (not a complete product identifier)."
    ::= { xcmPidWorkCentre5755 1 }
        -- ::= {1.3.6.1.4.1.253.8.62.1.20.5.32.1}

-- WorkCentre Model 5755 Configuration One Version One

xcmPidWorkCentre5755C1V1 OBJECT-IDENTITY
    STATUS      current
    DESCRIPTION
        "Xerox WorkCentre 5755 launch model, configuration 1,
           version 1.  A complete product identifier."
    ::= { xcmPidWorkCentre5755C1 1 }
        -- ::= {1.3.6.1.4.1.253.8.62.1.20.5.32.1.1}

-- WorkCentre 5765

xcmPidWorkCentre5765 OBJECT-IDENTITY
    STATUS      current
    DESCRIPTION
        "Xerox WorkCentre 5765 model identifier
                 (not a complete product identifier)."
    ::= { xcmPidWCMF5 33 }
        -- ::= {1.3.6.1.4.1.253.8.62.1.20.5.33}
            -- => SAP PID string = "D5Q"
            -- => USB PID string = 17054 = 0x429E
--
-- PNP PID Generation PLEASE NOTE:
--   The following assumes the IEEE 1284 Device ID contains the
--   following attributes:
--      MFG:Xerox MDL:WorkCentre 5765
--   The following PNP IDs were generated using these
--   parameters (manufacturer / model ):
--     -mf "Xerox" -mo "WorkCentre 5765"
--   The generated PNP PID is only valid for those parameters
--      WorkCentre 5765      XeroxWorkCentre_57657B45

xcmPidWorkCentre5765C1 OBJECT-IDENTITY
    STATUS      current
    DESCRIPTION
        "Xerox WorkCentre 5765 model and configuration 1 identifier
           (not a complete product identifier)."
    ::= { xcmPidWorkCentre5765 1 }
        -- ::= {1.3.6.1.4.1.253.8.62.1.20.5.33.1}

-- WorkCentre Model 5765 Configuration One Version One

xcmPidWorkCentre5765C1V1 OBJECT-IDENTITY


    STATUS      current
    DESCRIPTION
        "Xerox WorkCentre 5765 launch model, configuration 1,
           version 1.  A complete product identifier."
    ::= { xcmPidWorkCentre5765C1 1 }
        -- ::= {1.3.6.1.4.1.253.8.62.1.20.5.33.1.1}

-- WorkCentre 5775

xcmPidWorkCentre5775 OBJECT-IDENTITY
    STATUS      current
    DESCRIPTION
        "Xerox WorkCentre 5775 model identifier
                 (not a complete product identifier)."
    ::= { xcmPidWCMF5 34 }
        -- ::= {1.3.6.1.4.1.253.8.62.1.20.5.34}
            -- => SAP PID string = "D5R"
            -- => USB PID string = 17055 = 0x429F
--
-- PNP PID Generation PLEASE NOTE:
--   The following assumes the IEEE 1284 Device ID contains the
--   following attributes:
--      MFG:Xerox MDL:WorkCentre 5775
--   The following PNP IDs were generated using these
--   parameters (manufacturer / model ):
--     -mf "Xerox" -mo "WorkCentre 5775"
--   The generated PNP PID is only valid for those parameters
--      WorkCentre 5775      XeroxWorkCentre_5775EB44

xcmPidWorkCentre5775C1 OBJECT-IDENTITY
    STATUS      current
    DESCRIPTION
        "Xerox WorkCentre 5775 model and configuration 1 identifier
           (not a complete product identifier)."
    ::= { xcmPidWorkCentre5775 1 }
        -- ::= {1.3.6.1.4.1.253.8.62.1.20.5.34.1}

-- WorkCentre Model 5775 Configuration One Version One

xcmPidWorkCentre5775C1V1 OBJECT-IDENTITY
    STATUS      current
    DESCRIPTION
        "Xerox WorkCentre 5775 launch model, configuration 1,
           version 1.  A complete product identifier."
    ::= { xcmPidWorkCentre5775C1 1 }
        -- ::= {1.3.6.1.4.1.253.8.62.1.20.5.34.1.1}

-- WorkCentre 5790



xcmPidWorkCentre5790 OBJECT-IDENTITY
    STATUS      current
    DESCRIPTION
        "Xerox WorkCentre 5790 model identifier
                 (not a complete product identifier)."
    ::= { xcmPidWCMF5 35 }
        -- ::= {1.3.6.1.4.1.253.8.62.1.20.5.35}
            -- => SAP PID string = "D5S"
            -- => USB PID string = 17056 = 0x42A0
--
-- PNP PID Generation PLEASE NOTE:
--   The following assumes the IEEE 1284 Device ID contains the
--   following attributes:
--      MFG:Xerox MDL:WorkCentre 5790
--   The following PNP IDs were generated using these
--   parameters (manufacturer / model ):
--     -mf "Xerox" -mo "WorkCentre 5790"
--   The generated PNP PID is only valid for those parameters
--      WorkCentre 5790      XeroxWorkCentre_57908880

xcmPidWorkCentre5790C1 OBJECT-IDENTITY
    STATUS      current
    DESCRIPTION
        "Xerox WorkCentre 5790 model and configuration 1 identifier
           (not a complete product identifier)."
    ::= { xcmPidWorkCentre5790 1 }
        -- ::= {1.3.6.1.4.1.253.8.62.1.20.5.35.1}

-- WorkCentre Model 5790 Configuration One Version One
xcmPidWorkCentre5790C1V1 OBJECT-IDENTITY
    STATUS      current
    DESCRIPTION
        "Xerox WorkCentre 5790 launch model, configuration 1,
           version 1.  A complete product identifier."
    ::= { xcmPidWorkCentre5790C1 1 }
        -- ::= {1.3.6.1.4.1.253.8.62.1.20.5.35.1.1}

--
--

----------------------------------------------------------------
----------------------------------------------------------------

xcmPidWCMF6 OBJECT-IDENTITY
    STATUS      current
    DESCRIPTION
        "Xerox WorkCentre System product line identifier
                 (not a complete product identifier)."
    ::= { xcmPidWorkCentreMFSystems 6 }
        -- ::= {1.3.6.1.4.1.253.8.62.1.20.6 }

--
--


-- WorkCentre 3045B

xcmPidWorkCentre3045B OBJECT-IDENTITY
    STATUS      current
    DESCRIPTION
        "Xerox WorkCentre 3045B model identifier
                 (not a complete product identifier)."
    ::= { xcmPidWCMF6 7 }
        -- ::= {1.3.6.1.4.1.253.8.62.1.20.6.7}
            -- => SAP PID string = "D67"
            -- => USB PID string = 17071 = 0x42AF
            -- => PnP-X WiFi ID = VEN_0109&DEV_42AF
            -- => PnP ID = XeroxWorkCentre_3045B793
--
-- PNP PID Generation PLEASE NOTE:
--   The following assumes the IEEE 1284 Device ID contains the
--   following attributes:
--      MFG:Xerox MDL:WorkCentre 3045B
--   The following PNP IDs were generated using these
--   parameters (manufacturer / model ):
--     -mf "Xerox" -mo "WorkCentre 3045B"
--   The generated PNP PID is only valid for those parameters
--      WorkCentre 3045B      XeroxWorkCentre_3045B793

-- WorkCentre Model 3045B Configuration One

xcmPidWorkCentre3045BC1 OBJECT-IDENTITY
    STATUS      current
    DESCRIPTION
        "Xerox WorkCentre 3045B model and configuration 1 identifier
           (not a complete product identifier)."
    ::= { xcmPidWorkCentre3045B 1 }
        -- ::= {1.3.6.1.4.1.253.8.62.1.20.6.7.1}

-- WorkCentre Model 3045B Configuration One Version One

xcmPidWorkCentre3045BC1V1 OBJECT-IDENTITY
    STATUS      current
    DESCRIPTION
        "Xerox WorkCentre 3045B launch model, configuration 1,
           version 1.  A complete product identifier."
    ::= { xcmPidWorkCentre3045BC1 1 }
        -- ::= {1.3.6.1.4.1.253.8.62.1.20.6.7.1.1}

--
--

-- WorkCentre 3045NI

xcmPidWorkCentre3045NI OBJECT-IDENTITY
    STATUS      current
    DESCRIPTION


        "Xerox WorkCentre 3045NI model identifier
                 (not a complete product identifier)."
    ::= { xcmPidWCMF6 9 }
        -- ::= {1.3.6.1.4.1.253.8.62.1.20.6.9}
            -- => SAP PID string = "D69"
            -- => USB PID string = 17073 = 0x42B1
            -- => PnP-X WiFi ID = VEN_0109&DEV_42B1
            -- => PnP ID = XeroxWorkCentre_30459B33
--
-- PNP PID Generation PLEASE NOTE:
--   The following assumes the IEEE 1284 Device ID contains the
--   following attributes:
--      MFG:Xerox MDL:WorkCentre 3045NI
--   The following PNP IDs were generated using these
--   parameters (manufacturer / model ):
--     -mf "Xerox" -mo "WorkCentre 3045NI"
--   The generated PNP PID is only valid for those parameters
--      WorkCentre 3045NI      XeroxWorkCentre_30459B33

-- WorkCentre Model 3045NI Configuration One

xcmPidWorkCentre3045NIC1 OBJECT-IDENTITY
    STATUS      current
    DESCRIPTION
        "Xerox WorkCentre 3045NI model and configuration 1 identifier
           (not a complete product identifier)."
    ::= { xcmPidWorkCentre3045NI 1 }
        -- ::= {1.3.6.1.4.1.253.8.62.1.20.6.9.1}

-- WorkCentre Model 3045NI Configuration One Version One

xcmPidWorkCentre3045NIC1V1 OBJECT-IDENTITY
    STATUS      current
    DESCRIPTION
        "Xerox WorkCentre 3045NI launch model, configuration 1,
           version 1.  A complete product identifier."
    ::= { xcmPidWorkCentre3045NIC1 1 }
        -- ::= {1.3.6.1.4.1.253.8.62.1.20.6.9.1.1}

--
--


xcmPidWorkCentre6605 OBJECT-IDENTITY
    STATUS      current
    DESCRIPTION
        "Xerox WorkCentre 6605 model identifier
           (not a complete product identifier)."
    ::= { xcmPidWCMF6 34 }
        -- ::= {1.3.6.1.4.1.253.8.62.1.20.6.34}
            -- => SAP PID string = "D6R"
            -- => USB PID string = 17091 = 0x42C3
            -- => PnP-X WiFi ID = VEN_0109&DEV_42C3


            -- => PnP ID = XeroxWorkCentre_66055F15
            -- => Compatible ID = XR_PS_Basic_Color

-- PNP PID Generation PLEASE NOTE:
--   The following assumes the IEEE 1284 Device ID contains
--   attributes corresponding to manufacturer and model name.
--
--   The following PNP IDs were generated using these
--   parameters (manufacturer and model):
--     -mf "Xerox" -mo "WorkCentre 6605"
--   The generated PNP PIDs are only valid for those parameters
       -- => WorkCentre 6605        XeroxWorkCentre_66055F15

-- WorkCentre 6605 Configuration 1

xcmPidWorkCentre6605NC1 OBJECT-IDENTITY
    STATUS      current
    DESCRIPTION
        "Xerox WorkCentre 6605
           model and configuration 1 identifier
           (not a complete product identifier)."
    ::= { xcmPidWorkCentre6605 1 }
        -- ::= {1.3.6.1.4.1.253.8.62.1.20.6.34.1}

-- PNP PID Generation PLEASE NOTE:
--   The following assumes the IEEE 1284 Device ID contains
--   attributes corresponding to manufacturer and model name.
--
--   The following PNP IDs were generated using these
--   parameters (manufacturer and model):
--     -mf "Xerox" -mo "WorkCentre 6605N"
--   The generated PNP PIDs are only valid for those parameters
       -- => WorkCentre 6605N        XeroxWorkCentre_6605FB1E

-- WorkCentre 6605 Configuration 1 Version 1

xcmPidWorkCentre6605NC1V1 OBJECT-IDENTITY
    STATUS      current
    DESCRIPTION
        "Xerox WorkCentre 6605
            launch model, configuration 1, version 1.
            A complete product identifier."
    ::= { xcmPidWorkCentre6605NC1 1 }
        -- ::= {1.3.6.1.4.1.253.8.62.1.20.6.34.1.1}

-- WorkCentre 6605 Configuration 2

xcmPidWorkCentre6605DNC2 OBJECT-IDENTITY
    STATUS      current
    DESCRIPTION
        "Xerox WorkCentre 6605
           model and configuration 2 identifier
           (not a complete product identifier)."
    ::= { xcmPidWorkCentre6605 2 }


        -- ::= {1.3.6.1.4.1.253.8.62.1.20.6.34.2}

-- PNP PID Generation PLEASE NOTE:
--   The following assumes the IEEE 1284 Device ID contains
--   attributes corresponding to manufacturer and model name.
--
--   The following PNP IDs were generated using these
--   parameters (manufacturer and model):
--     -mf "Xerox" -mo "WorkCentre 6605DN"
--   The generated PNP PIDs are only valid for those parameters
       -- => WorkCentre 6605DN        XeroxWorkCentre_66059CFD

-- WorkCentre 6605 Configuration 2 Version 1

xcmPidWorkCentre6605DNC2V1 OBJECT-IDENTITY
    STATUS      current
    DESCRIPTION
        "Xerox WorkCentre 6605
            launch model, configuration 2, version 1.
            A complete product identifier."
    ::= { xcmPidWorkCentre6605DNC2 1 }
        -- ::= {1.3.6.1.4.1.253.8.62.1.20.6.34.2.1}

--
--

----------------------------------------------------------------
----------------------------------------------------------------

xcmPidWCMF7 OBJECT-IDENTITY
    STATUS      current
    DESCRIPTION
        "Xerox WorkCentre System product line identifier
                 (not a complete product identifier)."
    ::= { xcmPidWorkCentreMFSystems 7 }
        -- ::= {1.3.6.1.4.1.253.8.62.1.20.7}

--
--

--
--

--
--

--
--


--
--

----------------------------------------------------------------
-- Desktop DocuPrint Printers
----------------------------------------------------------------

xcmPidDesktopDocuPrintPrinters OBJECT-IDENTITY
    STATUS      current
    DESCRIPTION
        "Desktop DocuPrint Printers product line identifier
                 (not a complete product identifier)."
    ::= { xcmPidProductIdentifiers 2 }
        -- ::= {1.3.6.1.4.1.253.8.62.1.2}

--
--

-- Desktop DocuPrint 4517

xcmPid4517 OBJECT-IDENTITY
    STATUS      current
    DESCRIPTION
        "Desktop DocuPrint 4517 product type identifier
                 (not a complete product identifier)."
    ::= { xcmPidDesktopDocuPrintPrinters 2 }
        -- ::= {1.3.6.1.4.1.253.8.62.1.2.2}

xcmPid4517PlusM1 OBJECT-IDENTITY
    STATUS      current
    DESCRIPTION
        "Desktop DocuPrint 4517+ launch configuration model identifier
                 (not a complete product identifier)."
    ::= { xcmPid4517 1 }
        -- ::= {1.3.6.1.4.1.253.8.62.1.2.2.1}
            -- => SAP PID string = "221"

xcmPid4517PlusM1V1 OBJECT-IDENTITY
    STATUS      current
    DESCRIPTION
        "Desktop DocuPrint 4517+ launch configuration model and version,
                 and complete product identifier."
    ::= { xcmPid4517PlusM1 1 }
        -- ::= {1.3.6.1.4.1.253.8.62.1.2.2.1.1}


-- Desktop DocuPrint N17

xcmPidDocuPrintN17 OBJECT-IDENTITY
    STATUS      current
    DESCRIPTION
        "Desktop DocuPrint N17 launch configuration model
                 identifier (not a complete product identifier)."
    ::= { xcmPid4517 2 }
        -- ::= {1.3.6.1.4.1.253.8.62.1.2.2.2}
            -- => SAP PID string = "222"

xcmPidDocuPrintN17V1 OBJECT-IDENTITY
    STATUS      current
    DESCRIPTION
        "Desktop DocuPrint N17 launch configuration model and
                 version, and complete product identifier."
    ::= { xcmPidDocuPrintN17 1 }
        -- ::= {1.3.6.1.4.1.253.8.62.1.2.2.2.1}

--
--

-- Desktop DocuPrint C55

xcmPidDocuPrintC55 OBJECT-IDENTITY
    STATUS      current
    DESCRIPTION
        "Desktop DocuPrint C55 product type identifier
                 (not a complete product identifier)."
    ::= { xcmPidDesktopDocuPrintPrinters 3 }
        -- ::= {1.3.6.1.4.1.253.8.62.1.2.3}

xcmPidDocuPrintC55M1 OBJECT-IDENTITY
    STATUS      current
    DESCRIPTION
        "Desktop DocuPrint C55 launch configuration model identifier
                 (not a complete product identifier)."
    ::= { xcmPidDocuPrintC55 1 }
        -- ::= {1.3.6.1.4.1.253.8.62.1.2.3.1}
            -- => SAP PID string = "231"

xcmPidDocuPrintC55M1V1 OBJECT-IDENTITY
    STATUS      current


    DESCRIPTION
        "Desktop DocuPrint C55 launch configuration model and version,
                 and complete product identifier."
    ::= { xcmPidDocuPrintC55M1 1 }
        -- ::= {1.3.6.1.4.1.253.8.62.1.2.3.1.1}

xcmPidDocuPrintC55M1V2 OBJECT-IDENTITY
    STATUS      current
    DESCRIPTION
        "Desktop DocuPrint C55 launch configuration model
                 post-launch configuration version,
                 and complete product identifier."
    ::= { xcmPidDocuPrintC55M1 2 }
        -- ::= {1.3.6.1.4.1.253.8.62.1.2.3.1.2}

-- Desktop DocuPrint NC60

xcmPidDocuPrintNC60 OBJECT-IDENTITY
    STATUS      current
    DESCRIPTION
        "Desktop DocuPrint NC60 launch configuration model identifier
                 (not a complete product identifier)."
    ::= { xcmPidDocuPrintC55 2 }
        -- ::= {1.3.6.1.4.1.253.8.62.1.2.3.2}
            -- => SAP PID string = "232"

xcmPidDocuPrintNC60V1 OBJECT-IDENTITY
    STATUS      current
    DESCRIPTION
        "Desktop DocuPrint NC60 launch configuration model and version,
                 and complete product identifier."
    ::= { xcmPidDocuPrintNC60 1 }
        -- ::= {1.3.6.1.4.1.253.8.62.1.2.3.2.1}

--
--

-- Desktop DocuPrint P1210

xcmPidP1210 OBJECT-IDENTITY
    STATUS      current
    DESCRIPTION
        "Desktop DocuPrint P1210 product type identifier
                 (not a complete product identifier)."


    ::= { xcmPidDesktopDocuPrintPrinters 4 }
        -- ::= {1.3.6.1.4.1.253.8.62.1.2.4}

xcmPidP1210M1 OBJECT-IDENTITY
    STATUS      current
    DESCRIPTION
        "Desktop DocuPrint P1210 launch configuration model identifier
                 (not a complete product identifier)."
    ::= { xcmPidP1210 1 }
        -- ::= {1.3.6.1.4.1.253.8.62.1.2.4.1}
            -- => SAP PID string = "241"

xcmPidP1210M1V1 OBJECT-IDENTITY
    STATUS      current
    DESCRIPTION
        "Desktop DocuPrint P1210 launch configuration model and version,
                 and complete product identifier."
    ::= { xcmPidP1210M1 1 }
        -- ::= {1.3.6.1.4.1.253.8.62.1.2.4.1.1}

-- Desktop Xerox Phaser 3400

xcmPidP3400 OBJECT-IDENTITY
    STATUS      current
    DESCRIPTION
        "Xerox Phaser 3400 product type identifier
                 (not a complete product identifier)."
    ::= { xcmPidDesktopDocuPrintPrinters 5 }
        -- ::= {1.3.6.1.4.1.253.8.62.1.2.5}

xcmPidP3400M1 OBJECT-IDENTITY
    STATUS      current
    DESCRIPTION
        "Xerox Phaser 3400 launch configuration model identifier
                 (not a complete product identifier)."
    ::= { xcmPidP3400 1 }
        -- ::= {1.3.6.1.4.1.253.8.62.1.2.5.1}
            -- => SAP PID string = "251"

xcmPidP3400M1V1 OBJECT-IDENTITY
    STATUS      current
    DESCRIPTION
        "Xerox Phaser 3400 launch configuration model and version,
                 and complete product identifier."
    ::= { xcmPidP3400M1 1 }
        -- ::= {1.3.6.1.4.1.253.8.62.1.2.5.1.1}

----------------------------------------------------------------
-- WorkGroup & MidRange DocuPrint Printers
----------------------------------------------------------------

xcmPidWorkGroupDocuPrintPrinters OBJECT-IDENTITY
    STATUS      current


    DESCRIPTION
        "WorkGroup & MidRange DocuPrint Printers product line identifier
                 (not a complete product identifier)."
    ::= { xcmPidProductIdentifiers 3 }
        -- ::= {1.3.6.1.4.1.253.8.62.1.3}

--
--

-- WorkGroup DocuPrint Nnn

xcmPidDocuPrintNnn OBJECT-IDENTITY
    STATUS      current
    DESCRIPTION
        "WorkGroup DocuPrint Nnn product type identifier
                 (not a complete product identifier)."
    ::= { xcmPidWorkGroupDocuPrintPrinters 2 }
        -- ::= {1.3.6.1.4.1.253.8.62.1.3.2}

xcmPidDocuPrintN32 OBJECT-IDENTITY
    STATUS      current
    DESCRIPTION


        "WorkGroup DocuPrint N32 model identifier
                 (not a complete product identifier)."
    ::= { xcmPidDocuPrintNnn 1 }
        -- ::= {1.3.6.1.4.1.253.8.62.1.3.2.1}
            -- => SAP PID string = "321"

xcmPidDocuPrintN32V1 OBJECT-IDENTITY
    STATUS      current
    DESCRIPTION
        "WorkGroup DocuPrint N32 launch configuration version,
                 and complete product identifier."
    ::= { xcmPidDocuPrintN32 1 }
        -- ::= {1.3.6.1.4.1.253.8.62.1.3.2.1.1}

xcmPidDocuPrintN32V2 OBJECT-IDENTITY
    STATUS      current
    DESCRIPTION
        "WorkGroup DocuPrint N32 post-launch configuration version,
                 and complete product identifier."
    ::= { xcmPidDocuPrintN32 2 }
        -- ::= {1.3.6.1.4.1.253.8.62.1.3.2.1.2}

xcmPidDocuPrintN24 OBJECT-IDENTITY
    STATUS      current
    DESCRIPTION
        "WorkGroup DocuPrint N24 model identifier
                 (not a complete product identifier)."
    ::= { xcmPidDocuPrintNnn 2 }
        -- ::= {1.3.6.1.4.1.253.8.62.1.3.2.2}
            -- => SAP PID string = "322"

xcmPidDocuPrintN24V1 OBJECT-IDENTITY
    STATUS      current
    DESCRIPTION
        "WorkGroup DocuPrint N24 launch configuration version,
                 and complete product identifier."
    ::= { xcmPidDocuPrintN24 1 }
        -- ::= {1.3.6.1.4.1.253.8.62.1.3.2.2.1}

xcmPidDocuPrintN24V2 OBJECT-IDENTITY
    STATUS      current
    DESCRIPTION
        "WorkGroup DocuPrint N24 post-launch configuration version,
                 and complete product identifier."
    ::= { xcmPidDocuPrintN24 2 }
        -- ::= {1.3.6.1.4.1.253.8.62.1.3.2.2.2}

xcmPidDocuPrintN40 OBJECT-IDENTITY
    STATUS      current
    DESCRIPTION
        "WorkGroup DocuPrint N40 model identifier
                 (not a complete product identifier)."


    ::= { xcmPidDocuPrintNnn 3 }
        -- ::= {1.3.6.1.4.1.253.8.62.1.3.2.3}
            -- => SAP PID string = "323"

xcmPidDocuPrintN40V1 OBJECT-IDENTITY
    STATUS      current
    DESCRIPTION
        "WorkGroup DocuPrint N40 launch configuration version,
                 and complete product identifier."
    ::= { xcmPidDocuPrintN40 1 }
        -- ::= {1.3.6.1.4.1.253.8.62.1.3.2.3.1}

--   DP N24: {1.3.6.1.4.1.279.253.62.1.3.2.5.1}, "325"
--   DP N32: {1.3.6.1.4.1.279.253.62.1.3.2.4.1}, "324"
--   DP N40: {1.3.6.1.4.1.279.253.62.1.3.2.6.1}, "326"

xcmPidDocuPrintN2025 OBJECT-IDENTITY
    STATUS      current
    DESCRIPTION
        "WorkGroup DocuPrint N2025 model identifier
                 (not a complete product identifier)."
    ::= { xcmPidDocuPrintNnn 17 }
        -- ::= {1.3.6.1.4.1.253.8.62.1.3.2.17}
            -- => SAP PID string = "32A"

xcmPidDocuPrintN2025V1 OBJECT-IDENTITY
    STATUS      current
    DESCRIPTION
        "WorkGroup DocuPrint N2025 launch configuration version,
                 and complete product identifier."
    ::= { xcmPidDocuPrintN2025 1 }
        -- ::= {1.3.6.1.4.1.253.8.62.1.3.2.17.1}

xcmPidDocuPrintN2025V2 OBJECT-IDENTITY
    STATUS      current
    DESCRIPTION
        "WorkGroup DocuPrint N2025 first post-launch
                 configuration version, and complete
                 product identifier."
    ::= { xcmPidDocuPrintN2025 2 }
        -- ::= {1.3.6.1.4.1.253.8.62.1.3.2.17.2}

xcmPidDocuPrintN2125 OBJECT-IDENTITY
    STATUS      current
    DESCRIPTION
        "WorkGroup DocuPrint N2125 model identifier
                 (not a complete product identifier)."
    ::= { xcmPidDocuPrintNnn 18 }
        -- ::= {1.3.6.1.4.1.253.8.62.1.3.2.18}
            -- => SAP PID string = "32B"


xcmPidDocuPrintN2125V1 OBJECT-IDENTITY
    STATUS      current
    DESCRIPTION
        "WorkGroup DocuPrint N2125 launch configuration version,
                 and complete product identifier."
    ::= { xcmPidDocuPrintN2125 1 }
        -- ::= {1.3.6.1.4.1.253.8.62.1.3.2.18.1}

--
--

xcmPidDocuPrintN2425 OBJECT-IDENTITY
    STATUS      current
    DESCRIPTION
        "WorkGroup DocuPrint N2425 model identifier
                 (not a complete product identifier)."
    ::= { xcmPidDocuPrintNnn 19 }
        -- ::= {1.3.6.1.4.1.253.8.62.1.3.2.19}
            -- => SAP PID string = "32C"

xcmPidDocuPrintN2425V1 OBJECT-IDENTITY
    STATUS      current
    DESCRIPTION
        "WorkGroup DocuPrint N2425 launch configuration version,
                 and complete product identifier."
    ::= { xcmPidDocuPrintN2425 1 }
        -- ::= {1.3.6.1.4.1.253.8.62.1.3.2.19.1}

xcmPidDocuPrintN2825 OBJECT-IDENTITY
    STATUS      current
    DESCRIPTION
        "WorkGroup DocuPrint N2825 model identifier
                 (not a complete product identifier)."
    ::= { xcmPidDocuPrintNnn 20 }
        -- ::= {1.3.6.1.4.1.253.8.62.1.3.2.20}
            -- => SAP PID string = "32D"

xcmPidDocuPrintN2825V1 OBJECT-IDENTITY


    STATUS      current
    DESCRIPTION
        "WorkGroup DocuPrint N2825 launch configuration version,
                 and complete product identifier."
    ::= { xcmPidDocuPrintN2825 1 }
        -- ::= {1.3.6.1.4.1.253.8.62.1.3.2.20.1}

--
--

xcmPidDocuPrintN3225 OBJECT-IDENTITY
    STATUS      current
    DESCRIPTION
        "WorkGroup DocuPrint N3225 model identifier
                 (not a complete product identifier)."
    ::= { xcmPidDocuPrintNnn 21 }
        -- ::= {1.3.6.1.4.1.253.8.62.1.3.2.21}
            -- => SAP PID string = "32E"

xcmPidDocuPrintN3225V1 OBJECT-IDENTITY
    STATUS      current
    DESCRIPTION
        "WorkGroup DocuPrint N3225 launch configuration version,
                 and complete product identifier."
    ::= { xcmPidDocuPrintN3225 1 }
        -- ::= {1.3.6.1.4.1.253.8.62.1.3.2.21.1}

--
--

xcmPidDocuPrintN4025 OBJECT-IDENTITY
    STATUS      current
    DESCRIPTION
        "WorkGroup DocuPrint N4025 model identifier
                 (not a complete product identifier)."
    ::= { xcmPidDocuPrintNnn 22 }
        -- ::= {1.3.6.1.4.1.253.8.62.1.3.2.22}
            -- => SAP PID string = "32F"

xcmPidDocuPrintN4025V1 OBJECT-IDENTITY
    STATUS      current
    DESCRIPTION
        "WorkGroup DocuPrint N4025 launch configuration version,
                 and complete product identifier."
    ::= { xcmPidDocuPrintN4025 1 }
        -- ::= {1.3.6.1.4.1.253.8.62.1.3.2.22.1}

xcmPidDocuPrintN4025V2 OBJECT-IDENTITY
    STATUS      current
    DESCRIPTION
        "WorkGroup DocuPrint N4025 first post-launch
                 configuration version, and complete
                 product identifier."
    ::= { xcmPidDocuPrintN4025 2 }
        -- ::= {1.3.6.1.4.1.253.8.62.1.3.2.22.2}

xcmPidDocuPrintAyame35 OBJECT-IDENTITY
    STATUS      current           -- actually deprecated
    DESCRIPTION
        "WorkGroup DocuPrint Ayame35 model identifier
                 (not a complete product identifier)."
    ::= { xcmPidDocuPrintNnn 35 }
        -- ::= {1.3.6.1.4.1.253.8.62.1.3.2.35}
            -- => SAP PID string = "32S"

xcmPidDocuPrintAyame35V1 OBJECT-IDENTITY
    STATUS      current           -- actually deprecated
    DESCRIPTION
        "WorkGroup DocuPrint Ayame35 launch configuration version,
                 and complete product identifier."
    ::= { xcmPidDocuPrintAyame35 1 }
        -- ::= {1.3.6.1.4.1.253.8.62.1.3.2.35.1}

xcmPidDocuPrintN4525 OBJECT-IDENTITY
    STATUS      current
    DESCRIPTION
        "WorkGroup DocuPrint N4525 model identifier


                 (not a complete product identifier)."
    ::= { xcmPidDocuPrintNnn 36 }
        -- ::= {1.3.6.1.4.1.253.8.62.1.3.2.36}
            -- => SAP PID string = "32T"

xcmPidDocuPrintN4525V1 OBJECT-IDENTITY
    STATUS      current
    DESCRIPTION
        "WorkGroup DocuPrint N4525 launch configuration version,
                 and complete product identifier."
    ::= { xcmPidDocuPrintN4525 1 }
        -- ::= {1.3.6.1.4.1.253.8.62.1.3.2.36.1}

xcmPidPhaser5400 OBJECT-IDENTITY
    STATUS      current
    DESCRIPTION
        "WorkGroup Phaser 5400 model identifier
                 (not a complete product identifier)."
    ::= { xcmPidDocuPrintNnn 37 }
        -- ::= {1.3.6.1.4.1.253.8.62.1.3.2.37}
            -- => SAP PID string = "32U"

xcmPidPhaser5400V1 OBJECT-IDENTITY
    STATUS      current
    DESCRIPTION
        "WorkGroup Phaser 5400 launch configuration version,
                 and complete product identifier."
    ::= { xcmPidPhaser5400 1 }
        -- ::= {1.3.6.1.4.1.253.8.62.1.3.2.37.1}

--
--

-- WorkGroup DocuPrint NCnn Color Laser Printers

xcmPidDocuPrintNCnn OBJECT-IDENTITY
    STATUS      current
    DESCRIPTION
        "WorkGroup DocuPrint NCnn Color Laser Printers product type
                 identifier (not a complete product identifier)."
    ::= { xcmPidWorkGroupDocuPrintPrinters 3 }
        -- ::= {1.3.6.1.4.1.253.8.62.1.3.3}

xcmPidDocuPrintNC70 OBJECT-IDENTITY
    STATUS      current
    DESCRIPTION
        "WorkGroup DocuPrint NC70 Color Laser Printer
                 model identifier (not a complete product identifier)."
    ::= { xcmPidDocuPrintNCnn 1 }
        -- ::= {1.3.6.1.4.1.253.8.62.1.3.3.1}
            -- => SAP PID string = "331"

xcmPidDocuPrintNC70V1 OBJECT-IDENTITY
    STATUS      current
    DESCRIPTION
        "WorkGroup DocuPrint NC70 Color Laser Printer
                 launch configuration version,
                 and complete product identifier."
    ::= { xcmPidDocuPrintNC70 1 }
        -- ::= {1.3.6.1.4.1.253.8.62.1.3.3.1.1}

xcmPidDocuPrintNC80 OBJECT-IDENTITY
    STATUS      current
    DESCRIPTION
        "WorkGroup DocuPrint NC80 Color Laser Printer
                 model identifier (not a complete product identifier)."
    ::= { xcmPidDocuPrintNCnn 2 }
        -- ::= {1.3.6.1.4.1.253.8.62.1.3.3.2}
            -- => SAP PID string = "332"

xcmPidDocuPrintNC80V1 OBJECT-IDENTITY
    STATUS      current
    DESCRIPTION
        "WorkGroup DocuPrint NC80 Color Laser Printer
                 launch configuration version,
                 and complete product identifier."
    ::= { xcmPidDocuPrintNC80 1 }
        -- ::= {1.3.6.1.4.1.253.8.62.1.3.3.2.1}

--
--

xcmPidXeroxPhaserPrinters OBJECT-IDENTITY
    STATUS      current
    DESCRIPTION
        "Xerox Phaser Printers product line identifier
                 (not a complete product identifier)."
    ::= { xcmPidProductIdentifiers 19 }
        -- ::= {1.3.6.1.4.1.253.8.62.1.19}

--     Xerox Phaser 3yyy = PLP Family

xcmPidPhaser3yyyFamily OBJECT-IDENTITY
    STATUS      current
    DESCRIPTION
        "Xerox Phaser 3yyy Family product line identifier
         (not a complete product identifier)."
    ::= { xcmPidXeroxPhaserPrinters 1 }
        -- ::= {1.3.6.1.4.1.253.8.62.1.19.1}

-- Phaser 3450 Family, 25 ppm monochrome Laser printer
-- 3450B is the Base configuration
-- 3450D adds: Duplex
-- 3450DN adds: Network connection


xcmPidPhaser3450 OBJECT-IDENTITY
    STATUS      current
    DESCRIPTION
      "Xerox Phaser 3450 Laser Printer model identifier
       (not a complete product identifier)."
    ::= { xcmPidPhaser3yyyFamily 1 }
        -- ::= {1.3.6.1.4.1.253.8.62.1.19.1.1}
            -- => SAP PID string = "C11"
            -- => USB PID string = 15589 = 0x3CE5

xcmPidPhaser3450D OBJECT-IDENTITY
    STATUS      current
    DESCRIPTION
        "Xerox Phaser 3450D Laser Printer launch configuration model,
                  version, and complete product identifier."
    ::= { xcmPidPhaser3450 2 }
        -- ::= {1.3.6.1.4.1.253.8.62.1.19.1.1.2}

xcmPidPhaser3450DN OBJECT-IDENTITY
    STATUS      current
    DESCRIPTION
        "Xerox Phaser 3450DN Laser Printer launch configuration model,
                  version, and complete product identifier."
    ::= { xcmPidPhaser3450 3 }
        -- ::= {1.3.6.1.4.1.253.8.62.1.19.1.1.3}

xcmPidPhaser3450B OBJECT-IDENTITY
    STATUS      current
    DESCRIPTION
        "Xerox Phaser 3450B Laser Printer launch configuration model,
                  version, and complete product identifier."
    ::= { xcmPidPhaser3450 4 }
        -- ::= {1.3.6.1.4.1.253.8.62.1.19.1.1.4}

-- Phaser 3500, 38 ppm, Letter Size, monochrome Laser printer
-- xcmPIDPhaser3500b -  base configuration
-- xcmPIDPhaser3500n -  base configuration + optional Network Card
-- Note: There is no Phaser 3500N model or configuration

xcmPidPhaser3500 OBJECT-IDENTITY
    STATUS      current
    DESCRIPTION
        "Xerox Phaser 3500 Laser Printer model identifier
                 (not a complete product identifier)."
    ::= { xcmPidPhaser3yyyFamily 2 }
        -- ::= {1.3.6.1.4.1.253.8.62.1.19.1.2}
            -- => SAP PID string = "C12"
            -- => USB PID string = 15590 = 0x3CE6

xcmPidPhaser3500b OBJECT-IDENTITY
    STATUS      current
    DESCRIPTION


        "Xerox Phaser 3500b (Base) Laser Printer launch
   configuration model, version, and complete product identifier."
    ::= { xcmPidPhaser3500 1 }
        -- ::= {1.3.6.1.4.1.253.8.62.1.19.1.2.1}

xcmPidPhaser3500n OBJECT-IDENTITY
    STATUS      current
    DESCRIPTION
        "Xerox Phaser 3500n (Base+Network Card) Laser Printer launch
   configuration model, version, and complete product identifier."
    ::= { xcmPidPhaser3500 2 }
        -- ::= {1.3.6.1.4.1.253.8.62.1.19.1.2.2}

-- Phaser 3150, 22 ppm, Letter Size, monochrome Laser printer
-- xcmPIDPhaser3150b -  base configuration
-- xcmPIDPhaser3150n -  base configuration + optional Network Card
-- Note: There is no Phaser 3150N model or configuration

xcmPidPhaser3150 OBJECT-IDENTITY
    STATUS      current
    DESCRIPTION
        "Xerox Phaser 3150 Laser Printer model identifier
                 (not a complete product identifier)."
    ::= { xcmPidPhaser3yyyFamily 3 }
        -- ::= {1.3.6.1.4.1.253.8.62.1.19.1.3}
            -- => SAP PID string = "C13"
            -- => USB PID string = 15591 = 0x3CE7

xcmPidPhaser3150b OBJECT-IDENTITY
    STATUS      current
    DESCRIPTION
        "Xerox Phaser 3150b (Base) Laser Printer launch
   configuration model, version, and complete product identifier."
    ::= { xcmPidPhaser3150 1 }
        -- ::= {1.3.6.1.4.1.253.8.62.1.19.1.3.1}

xcmPidPhaser3150n OBJECT-IDENTITY
    STATUS      current
    DESCRIPTION
        "Xerox Phaser 3150n (Base+Network Card) Laser Printer launch
   configuration model, version, and complete product identifier."
    ::= { xcmPidPhaser3150 2 }
        -- ::= {1.3.6.1.4.1.253.8.62.1.19.1.3.2}

-- Phaser 3428  28ppm A4 monochrome

xcmPidPhaser3428 OBJECT-IDENTITY
    STATUS      current
    DESCRIPTION
        "Xerox Phaser 3428 Laser Printer model identifier
                 (not a complete product identifier)."
    ::= { xcmPidPhaser3yyyFamily 4 }


        -- ::= {1.3.6.1.4.1.253.8.62.1.19.1.4}
            -- => SAP PID string = "C14"
            -- => USB PID string = 15592 = 0x3CE8

xcmPidPhaser3428v1 OBJECT-IDENTITY
    STATUS      current
    DESCRIPTION
        "Xerox Phaser 3428 Laser Printer launch configuration model,
                  version 1, and complete product identifier."
    ::= { xcmPidPhaser3428 1 }
        -- ::= {1.3.6.1.4.1.253.8.62.1.19.1.4.1}

-- Phaser 3124

xcmPidPhaser3124 OBJECT-IDENTITY
    STATUS      current
    DESCRIPTION
        "Xerox Phaser 3124 Laser Printer model identifier
                 (not a complete product identifier)."
    ::= { xcmPidPhaser3yyyFamily 5 }
        -- ::= {1.3.6.1.4.1.253.8.62.1.19.1.5}
            -- => SAP PID string = "C15"
            -- => USB PID string = 15593 = 0x3CE9

xcmPidPhaser3124v1 OBJECT-IDENTITY
    STATUS      current
    DESCRIPTION
        "Xerox Phaser 3124 Laser Printer launch configuration model,
                  version 1, and complete product identifier."
    ::= { xcmPidPhaser3124 1 }
        -- ::= {1.3.6.1.4.1.253.8.62.1.19.1.5.1}

-- Phaser 3125

xcmPidPhaser3125 OBJECT-IDENTITY
    STATUS      current
    DESCRIPTION
        "Xerox Phaser 3125 Laser Printer model identifier
                 (not a complete product identifier)."
    ::= { xcmPidPhaser3yyyFamily 6 }
        -- ::= {1.3.6.1.4.1.253.8.62.1.19.1.6}
            -- => SAP PID string = "C16"
            -- => USB PID string = 15594 = 0x3CEA

xcmPidPhaser3125v1 OBJECT-IDENTITY
    STATUS      current
    DESCRIPTION
        "Xerox Phaser 3125 Laser Printer launch configuration model,
                  version 1, and complete product identifier."
    ::= { xcmPidPhaser3125 1 }
        -- ::= {1.3.6.1.4.1.253.8.62.1.19.1.6.1}


-- Phaser 3250

xcmPidPhaser3250 OBJECT-IDENTITY
    STATUS      current
    DESCRIPTION
        "Xerox Phaser 3250 Laser Printer model identifier
                 (not a complete product identifier)."
    ::= { xcmPidPhaser3yyyFamily 8 }
        -- ::= {1.3.6.1.4.1.253.8.62.1.19.1.8}
            -- => SAP PID string = "C18"
            -- => USB PID string = 15596 = 0x3CEC

xcmPidPhaser3250v1 OBJECT-IDENTITY
    STATUS      current
    DESCRIPTION
        "Xerox Phaser 3250 Printer launch configuration model,
                version 1, and complete product identifier."
    ::= { xcmPidPhaser3250 1 }
        -- ::= {1.3.6.1.4.1.253.8.62.1.19.1.8.1}

-- Phaser 3600

xcmPidPhaser3600 OBJECT-IDENTITY
    STATUS      current
    DESCRIPTION
        "Xerox Phaser 3600 model identifier
                 (not a complete product identifier)."
    ::= { xcmPidPhaser3yyyFamily 9 }
        -- ::= {1.3.6.1.4.1.253.8.62.1.19.1.9}
            -- => SAP PID string = "C19"
            -- => USB PID string = 15597 = 0x3CED

xcmPidPhaser3600v1 OBJECT-IDENTITY
    STATUS      current
    DESCRIPTION
        "Xerox Phaser 3600 launch configuration model,
                version 1, and complete product identifier."
    ::= { xcmPidPhaser3600 1 }
        -- ::= {1.3.6.1.4.1.253.8.62.1.19.1.9.1}

-- Phaser 3100MFP

xcmPidPhaser3100MFP OBJECT-IDENTITY
    STATUS      current
    DESCRIPTION
        "Xerox Phaser 3100 4-in-1  model identifier
                 (not a complete product identifier)."
    ::= { xcmPidPhaser3yyyFamily 17 }
        -- ::= {1.3.6.1.4.1.253.8.62.1.19.1.17}
            -- => SAP PID string = "C1A"


            -- => USB PID string = 15598 = 0x3CEE

xcmPidPhaser3100MFPv1 OBJECT-IDENTITY
    STATUS      current
    DESCRIPTION
        "Xerox Phaser 3100MFP launch configuration model,
                version 1, and complete product identifier."
    ::= { xcmPidPhaser3100MFP 1 }
        -- ::= {1.3.6.1.4.1.253.8.62.1.19.1.17.1}

-- Phaser 3100

xcmPidPhaser3100 OBJECT-IDENTITY
    STATUS      current
    DESCRIPTION
        "Xerox Phaser 3100 3-in-1 model identifier
                 (not a complete product identifier)."
    ::= { xcmPidPhaser3yyyFamily 18 }
        -- ::= {1.3.6.1.4.1.253.8.62.1.19.1.18}
            -- => SAP PID string = "C1B"
            -- => USB PID string = 15599 = 0x3CEF

xcmPidPhaser3100v1 OBJECT-IDENTITY
    STATUS      current
    DESCRIPTION
        "Xerox Phaser 3100 launch configuration model,
                version 1, and complete product identifier."
    ::= { xcmPidPhaser3100 1 }
        -- ::= {1.3.6.1.4.1.253.8.62.1.19.1.18.1}

-- Phaser 3435

xcmPidPhaser3435 OBJECT-IDENTITY
    STATUS      current
    DESCRIPTION
        "Xerox Phaser 3435 35ppm A4 model identifier
                 (not a complete product identifier)."
    ::= { xcmPidPhaser3yyyFamily 19 }
        -- ::= {1.3.6.1.4.1.253.8.62.1.19.1.19}
            -- => SAP PID string = "C1C"
            -- => USB PID string = 15600 = 0x3CF0

xcmPidPhaser3435v1 OBJECT-IDENTITY
    STATUS      current
    DESCRIPTION
        "Xerox Phaser 3435 launch configuration model,
                version 1, and complete product identifier."
    ::= { xcmPidPhaser3435 1 }
        -- ::= {1.3.6.1.4.1.253.8.62.1.19.1.19.1}

-- Phaser 3300MFP



xcmPidPhaser3300MFP OBJECT-IDENTITY
    STATUS      current
    DESCRIPTION
        "Xerox Phaser 3300MFP model identifier
           (not a complete product identifier)."
    ::= { xcmPidPhaser3yyyFamily 20 }
        -- ::= {1.3.6.1.4.1.253.8.62.1.19.1.20}
            -- => SAP PID string = "C1D"
            -- => USB PID string = 15601 = 0x3CF1
            -- => PnP ID PS   XeroxPhaser_3300MFP_9B8F
            -- => PnP ID PCL  XeroxPhaser_3300MFP_91D6
            -- => PnP ID PCL6 XeroxPhaser_3300MFP_8890

xcmPidPhaser3300MFPc1 OBJECT-IDENTITY
    STATUS      current
    DESCRIPTION
        "Xerox Phaser 3300MFP
           model and configuration identifier
           (not a complete product identifier)."
    ::= { xcmPidPhaser3300MFP 1 }
        -- ::= {1.3.6.1.4.1.253.8.62.1.19.1.20.1}

xcmPidPhaser3300MFPc1v1 OBJECT-IDENTITY
    STATUS      current
    DESCRIPTION
        "Xerox Phaser 3300MFP
            launch model, configuration, version 1.
            A complete product identifier."
    ::= { xcmPidPhaser3300MFPc1 1 }
        -- ::= {1.3.6.1.4.1.253.8.62.1.19.1.20.1.1}

--
--

-- Phaser 3010

xcmPidPhaser3010 OBJECT-IDENTITY
    STATUS      current
    DESCRIPTION
        "Xerox Phaser 3010 model identifier
                 (not a complete product identifier)."
    ::= { xcmPidPhaser3yyyFamily 26 }
        -- ::= {1.3.6.1.4.1.253.8.62.1.19.1.26}
            -- => SAP PID string = "C1J"
            -- => USB PID string = 15607 = 0x3CF7
            -- => PnP-X WiFi ID = VEN_0109&DEV_3CF7


            -- => PnP ID = XeroxPhaser_3010853C
--
-- PNP PID Generation PLEASE NOTE:
--   The following assumes the IEEE 1284 Device ID contains the
--   following attributes:
--      MFG:Xerox MDL:Phaser 3010
--   The following PNP IDs were generated using these
--   parameters (manufacturer / model ):
--     -mf "Xerox" -mo "Phaser 3010"
--   The generated PNP PID is only valid for those parameters
--      Phaser 3010      XeroxPhaser_3010853C

-- Phaser Model 3010 Configuration One

xcmPidPhaser3010C1 OBJECT-IDENTITY
    STATUS      current
    DESCRIPTION
        "Xerox Phaser 3010 model and configuration 1 identifier
           (not a complete product identifier)."
    ::= { xcmPidPhaser3010 1 }
        -- ::= {1.3.6.1.4.1.253.8.62.1.19.1.26.1}

-- Phaser Model 3010 Configuration One Version One

xcmPidPhaser3010C1V1 OBJECT-IDENTITY
    STATUS      current
    DESCRIPTION
        "Xerox Phaser 3010 launch model, configuration 1,
           version 1.  A complete product identifier."
    ::= { xcmPidPhaser3010C1 1 }
        -- ::= {1.3.6.1.4.1.253.8.62.1.19.1.26.1.1}

--
--

-- Phaser 3040

xcmPidPhaser3040 OBJECT-IDENTITY
    STATUS      current
    DESCRIPTION
        "Xerox Phaser 3040 model identifier
                 (not a complete product identifier)."
    ::= { xcmPidPhaser3yyyFamily 28 }
        -- ::= {1.3.6.1.4.1.253.8.62.1.19.1.28}
            -- => SAP PID string = "C1L"
            -- => USB PID string = 15609 = 0x3CF9
            -- => PnP-X WiFi ID = VEN_0109&DEV_3CF9
            -- => PnP ID = XeroxPhaser_3040D73F
--
-- PNP PID Generation PLEASE NOTE:
--   The following assumes the IEEE 1284 Device ID contains the
--   following attributes:
--      MFG:Xerox MDL:Phaser 3040
--   The following PNP IDs were generated using these


--   parameters (manufacturer / model ):
--     -mf "Xerox" -mo "Phaser 3040"
--   The generated PNP PID is only valid for those parameters
--      Phaser 3040      XeroxPhaser_3040D73F

-- Phaser Model 3040 Configuration One

xcmPidPhaser3040C1 OBJECT-IDENTITY
    STATUS      current
    DESCRIPTION
        "Xerox Phaser 3040 model and configuration 1 identifier
           (not a complete product identifier)."
    ::= { xcmPidPhaser3040 1 }
        -- ::= {1.3.6.1.4.1.253.8.62.1.19.1.28.1}

-- Phaser Model 3040 Configuration One Version One

xcmPidPhaser3040C1V1 OBJECT-IDENTITY
    STATUS      current
    DESCRIPTION
        "Xerox Phaser 3040 launch model, configuration 1,
           version 1.  A complete product identifier."
    ::= { xcmPidPhaser3040C1 1 }
        -- ::= {1.3.6.1.4.1.253.8.62.1.19.1.28.1.1}

--
--

--     Xerox Phaser 4yyy = Monochrome, A4 Family

xcmPidPhaser4yyyFamily OBJECT-IDENTITY
    STATUS      current
    DESCRIPTION
        "Xerox Phaser 4yyy Family product line identifier
                 (not a complete product identifier)."
    ::= { xcmPidXeroxPhaserPrinters 2 }
        -- ::= {1.3.6.1.4.1.253.8.62.1.19.2}

-- Phaser 4400 Family, 26 ppm Laser printer
-- 4400B is the Base configuration


-- 4400N  adds: built-in 10/100 Ethernet
-- 4400DT adds: 550 Sheet Feeder
--              Duplex
-- 4400DX adds: Hard Disk
--              +32 MB RAM

xcmPidPhaser4400 OBJECT-IDENTITY
    STATUS      current
    DESCRIPTION
        "Xerox Phaser 4400 Laser Printer model identifier
                 (not a complete product identifier)."
    ::= { xcmPidPhaser4yyyFamily 1 }
        -- ::= {1.3.6.1.4.1.253.8.62.1.19.2.1}
            -- => SAP PID string = "C21"

xcmPidPhaser4400N OBJECT-IDENTITY
    STATUS      current
    DESCRIPTION
        "Xerox Phaser 4400N Laser Printer launch configuration model,
                  version, and complete product identifier."
    ::= { xcmPidPhaser4400 1 }
        -- ::= {1.3.6.1.4.1.253.8.62.1.19.2.1.1}

xcmPidPhaser4400DT OBJECT-IDENTITY
    STATUS      current
    DESCRIPTION
        "Xerox Phaser 4400DT Laser Printer launch configuration model,
                  version, and complete product identifier."
    ::= { xcmPidPhaser4400 2 }
        -- ::= {1.3.6.1.4.1.253.8.62.1.19.2.1.2}

xcmPidPhaser4400DX OBJECT-IDENTITY
    STATUS      current
    DESCRIPTION
        "Xerox Phaser 4400DX Laser Printer launch configuration model,
                  version, and complete product identifier."
    ::= { xcmPidPhaser4400 3 }
        -- ::= {1.3.6.1.4.1.253.8.62.1.19.2.1.3}

xcmPidPhaser4400B OBJECT-IDENTITY
    STATUS      current
    DESCRIPTION
        "Xerox Phaser 4400B Laser Printer launch configuration model,
                  version, and complete product identifier."
    ::= { xcmPidPhaser4400 4 }
        -- ::= {1.3.6.1.4.1.253.8.62.1.19.2.1.4}

-- Phaser 4500 Family (Carmel), 35-ppm A4 Monochrome Laser Printer
-- 4500B is the base configuration (no network, 16MB)
-- 4500N: built-in 10/100 Ethernet + (True 1200 X 1200 Print Quality)
-- 4500DT: 4500N + 550 Sheet Feeder and Auto Duplexer
-- 4500DX: 4500DT + Hard Disk + Offset Output Tray


xcmPidPhaser4500 OBJECT-IDENTITY
    STATUS      current
    DESCRIPTION
        "Xerox Phaser 4500 Laser Printer model identifier
                 (not a complete product identifier)."
    ::= { xcmPidPhaser4yyyFamily 2 }
        -- ::= {1.3.6.1.4.1.253.8.62.1.19.2.2}
            -- => SAP PID string = "C22"
            -- => USB PID string = 15626 = 0x3D0A

xcmPidPhaser4500N OBJECT-IDENTITY
    STATUS      current
    DESCRIPTION
        "Xerox Phaser 4500N Laser Printer launch configuration model,
                  version, and complete product identifier."
    ::= { xcmPidPhaser4500 1 }
        -- ::= {1.3.6.1.4.1.253.8.62.1.19.2.2.1}

xcmPidPhaser4500DT OBJECT-IDENTITY
    STATUS      current
    DESCRIPTION
        "Xerox Phaser 4500DT Laser Printer launch configuration model,
                  version, and complete product identifier."
    ::= { xcmPidPhaser4500 2 }
        -- ::= {1.3.6.1.4.1.253.8.62.1.19.2.2.2}

xcmPidPhaser4500DX OBJECT-IDENTITY
    STATUS      current
    DESCRIPTION
        "Xerox Phaser 4500DX Laser Printer launch configuration model,
                  version, and complete product identifier."
    ::= { xcmPidPhaser4500 3 }
        -- ::= {1.3.6.1.4.1.253.8.62.1.19.2.2.3}

xcmPidPhaser4500B OBJECT-IDENTITY
    STATUS      current
    DESCRIPTION
        "Xerox Phaser 4500B Laser Printer launch configuration model,
                  version, and complete product identifier."
    ::= { xcmPidPhaser4500 4 }
        -- ::= {1.3.6.1.4.1.253.8.62.1.19.2.2.4}

-- Phaser 4510 Family  45-ppm Letter Monochrome Laser Printer
-- 4510B is the base configuration (no network)
-- 4510N: built-in 10/100 Ethernet + (256MB)
-- 4510DT: 4500N + more memory
-- 4510DX: 4500DT + Hard Disk + Extra Tray(550 Sheets)

xcmPidPhaser4510 OBJECT-IDENTITY
    STATUS      current
    DESCRIPTION


        "Xerox Phaser 4510 Laser Printer model identifier
                 (not a complete product identifier)."
    ::= { xcmPidPhaser4yyyFamily 3 }
        -- ::= {1.3.6.1.4.1.253.8.62.1.19.2.3}
            -- => SAP PID string = "C23"
            -- => USB PID string = 15627 = 0x3D0B

xcmPidPhaser4510B OBJECT-IDENTITY
    STATUS      current
    DESCRIPTION
        "Xerox Phaser 4510B Laser Printer launch configuration model,
                  version, and complete product identifier."
    ::= { xcmPidPhaser4510 1 }
        -- ::= {1.3.6.1.4.1.253.8.62.1.19.2.3.1}

xcmPidPhaser4510N OBJECT-IDENTITY
    STATUS      current
    DESCRIPTION
        "Xerox Phaser 4510N Laser Printer launch configuration model,
                  version, and complete product identifier."
    ::= { xcmPidPhaser4510 2 }
        -- ::= {1.3.6.1.4.1.253.8.62.1.19.2.3.2}

xcmPidPhaser4510DT OBJECT-IDENTITY
    STATUS      current
    DESCRIPTION
        "Xerox Phaser 4510DT Laser Printer launch configuration model,
                  version, and complete product identifier."
    ::= { xcmPidPhaser4510 3 }
        -- ::= {1.3.6.1.4.1.253.8.62.1.19.2.3.3}

xcmPidPhaser4510DX OBJECT-IDENTITY
    STATUS      current
    DESCRIPTION
        "Xerox Phaser 4510DX Laser Printer launch configuration model,
                  version, and complete product identifier."
    ::= { xcmPidPhaser4510 4 }
        -- ::= {1.3.6.1.4.1.253.8.62.1.19.2.3.4}

--
--
--     Xerox Phaser 5yyy = Monochrome, A3 Family

xcmPidPhaser5yyyFamily OBJECT-IDENTITY
    STATUS      current
    DESCRIPTION
        "Xerox Phaser 5yyy Family product line identifier
                 (not a complete product identifier)."
    ::= { xcmPidXeroxPhaserPrinters 3 }
        -- ::= {1.3.6.1.4.1.253.8.62.1.19.3}

--
-- Phaser 5500 Family


-- 5500B: Base configuration (No Network, 64MB RAM)
-- 5500N:  5500B +  built-in 10/100 Ethernet
-- 5500DN: 5500N +  Auto Duplex
-- 5500DT: 5500DN +  Auxillary Trays
-- 5500DX: 5500DT + 64MB, Finisher, Internal HD

xcmPidPhaser5500 OBJECT-IDENTITY
    STATUS      current
    DESCRIPTION
        "Xerox Phaser 5500 Laser Printer model identifier
                 (not a complete product identifier)."
    ::= { xcmPidPhaser5yyyFamily 1 }
        -- ::= {1.3.6.1.4.1.253.8.62.1.19.3.1}
            -- => SAP PID string = "C31"
            -- => USB PID string = 15661 = 0x3D2D

xcmPidPhaser5500B OBJECT-IDENTITY
    STATUS      current
    DESCRIPTION
        "Xerox Phaser 5500B Laser Printer launch configuration model,
                  version, and complete product identifier."
    ::= { xcmPidPhaser5500 1 }
        -- ::= {1.3.6.1.4.1.253.8.62.1.19.3.1.1}

xcmPidPhaser5500N OBJECT-IDENTITY
    STATUS      current
    DESCRIPTION
        "Xerox Phaser 5500N Laser Printer launch configuration model,
                  version, and complete product identifier."
    ::= { xcmPidPhaser5500 2 }
        -- ::= {1.3.6.1.4.1.253.8.62.1.19.3.1.2}

xcmPidPhaser5500DN OBJECT-IDENTITY
    STATUS      current
    DESCRIPTION
        "Xerox Phaser 5500DN Laser Printer launch configuration model,
                  version, and complete product identifier."
    ::= { xcmPidPhaser5500 3 }
        -- ::= {1.3.6.1.4.1.253.8.62.1.19.3.1.3}

xcmPidPhaser5500DT OBJECT-IDENTITY
    STATUS      current
    DESCRIPTION
        "Xerox Phaser 5500DT Laser Printer launch configuration model,
                  version, and complete product identifier."
    ::= { xcmPidPhaser5500 4 }
        -- ::= {1.3.6.1.4.1.253.8.62.1.19.3.1.4}

xcmPidPhaser5500DX OBJECT-IDENTITY
    STATUS      current
    DESCRIPTION
        "Xerox Phaser 5500DX Laser Printer launch configuration model,
                  version, and complete product identifier."


    ::= { xcmPidPhaser5500 5 }
        -- ::= {1.3.6.1.4.1.253.8.62.1.19.3.1.5}

-- Phaser 5550
-- 5550B: Base configuration (No Network)
-- 5550N:  5550B + Networked 256MB
-- 5550DN: 5550N + Duplex
-- 5550DT: 5550DN +  Auxillary Trays

xcmPidPhaser5550 OBJECT-IDENTITY
    STATUS      current
    DESCRIPTION
        "Xerox Phaser 5550 Laser Printer model identifier
                 (not a complete product identifier)."
    ::= { xcmPidPhaser5yyyFamily 2 }
        -- ::= {1.3.6.1.4.1.253.8.62.1.19.3.2}
            -- => SAP PID string = "C32"
            -- => USB PID string = 15662 = 0x3D2E

xcmPidPhaser5550B OBJECT-IDENTITY
    STATUS      current
    DESCRIPTION
        "Xerox Phaser 5550B Laser Printer launch configuration model,
                  version, and complete product identifier."
    ::= { xcmPidPhaser5550 1 }
        -- ::= {1.3.6.1.4.1.253.8.62.1.19.3.2.1}

xcmPidPhaser5550N OBJECT-IDENTITY
    STATUS      current
    DESCRIPTION
        "Xerox Phaser 5550N Laser Printer launch configuration model,
                  version, and complete product identifier."
    ::= { xcmPidPhaser5550 2 }
        -- ::= {1.3.6.1.4.1.253.8.62.1.19.3.2.2}

xcmPidPhaser5550DN OBJECT-IDENTITY
    STATUS      current
    DESCRIPTION
        "Xerox Phaser 5550DN Laser Printer launch configuration model,
                  version, and complete product identifier."
    ::= { xcmPidPhaser5550 3 }
        -- ::= {1.3.6.1.4.1.253.8.62.1.19.3.2.3}

xcmPidPhaser5550DT OBJECT-IDENTITY
    STATUS      current
    DESCRIPTION
        "Xerox Phaser 5550DT Laser Printer launch configuration model,
                  version, and complete product identifier."
    ::= { xcmPidPhaser5550 4 }
        -- ::= {1.3.6.1.4.1.253.8.62.1.19.3.2.4}


-- Phaser 5335

xcmPidPhaser5335 OBJECT-IDENTITY
    STATUS      current
    DESCRIPTION
        "Xerox Phaser 5335 Laser Printer model identifier
                 (not a complete product identifier)."
    ::= { xcmPidPhaser5yyyFamily 3 }
        -- ::= {1.3.6.1.4.1.253.8.62.1.19.3.3}
            -- => SAP PID string = "C33"
            -- => USB PID string = 15663 = 0x3D2F

xcmPidPhaser5335v1 OBJECT-IDENTITY
    STATUS      current
    DESCRIPTION
        "Xerox Phaser 5335 Laser Printer launch configuration model,
                  version, and complete product identifier."
    ::= { xcmPidPhaser5335 1 }
        -- ::= {1.3.6.1.4.1.253.8.62.1.19.3.3.1}

--
--     Xerox Phaser 6yyy = Color, A4 Family
--
--

xcmPidPhaser6yyyFamily OBJECT-IDENTITY
    STATUS      current
    DESCRIPTION
        "Xerox Phaser 6yyy Family product line identifier
                 (not a complete product identifier)."
    ::= { xcmPidXeroxPhaserPrinters 4 }
        -- ::= {1.3.6.1.4.1.253.8.62.1.19.4}

--
-- Phaser 6100 Family (Gingko), 21/5 ppm 4 Pass Color Laser Printer
-- 6100: Base configuration (No Network, 32MB RAM, Duplex)
-- 6100n: 6100 + Optional 10/100 Ethernet Network Card

xcmPidPhaser6100 OBJECT-IDENTITY
    STATUS      current
    DESCRIPTION
        "Xerox Phaser 6100 Laser Printer model identifier
                 (not a complete product identifier)."
    ::= { xcmPidPhaser6yyyFamily 2 }
        -- ::= {1.3.6.1.4.1.253.8.62.1.19.4.2}
            -- => SAP PID string = "C42"
            -- => USB PID string = 15698 = 0x3D52

xcmPidPhaser6100n OBJECT-IDENTITY
    STATUS      current
    DESCRIPTION


        "Xerox Phaser 6100n Laser Printer,
                  launch configuration model,
                  version, and complete product identifier."
    ::= { xcmPidPhaser6100 1 }
        -- ::= {1.3.6.1.4.1.253.8.62.1.19.4.2.1}

-- Phaser 6200 Family, 16/16 ppm Color Laser printer
-- 6200B is the Base configuration (no network, 64MB)
-- 6200N adds: built-in 10/100 Ethernet
-- 6200DP: 6200N + 64MB (128 total) and Auto Duplex
-- 6200DX: 6200DP + 128MB (256 total), 2-500 Sheet Input Tray
--         and a cart

xcmPidPhaser6200 OBJECT-IDENTITY
    STATUS      current
    DESCRIPTION
        "Xerox Phaser 6200 Laser Printer model identifier
                 (not a complete product identifier)."
    ::= { xcmPidPhaser6yyyFamily 1 }
        -- ::= {1.3.6.1.4.1.253.8.62.1.19.4.1}
            -- => SAP PID string = "C41"
            -- => USB PID string = 15697 = 0x3D51

xcmPidPhaser6200B OBJECT-IDENTITY
    STATUS      current
    DESCRIPTION
        "Xerox Phaser 6200B Laser Printer launch configuration model,
                  version, and complete product identifier."
    ::= { xcmPidPhaser6200 1 }
        -- ::= {1.3.6.1.4.1.253.8.62.1.19.4.1.1}

xcmPidPhaser6200N OBJECT-IDENTITY
    STATUS      current
    DESCRIPTION
        "Xerox Phaser 6200N Laser Printer launch configuration model,
                  version, and complete product identifier."
    ::= { xcmPidPhaser6200 2 }
        -- ::= {1.3.6.1.4.1.253.8.62.1.19.4.1.2}

xcmPidPhaser6200DP OBJECT-IDENTITY
    STATUS      current
    DESCRIPTION
        "Xerox Phaser 6200DP Laser Printer launch configuration model,
                  version, and complete product identifier."
    ::= { xcmPidPhaser6200 3 }
        -- ::= {1.3.6.1.4.1.253.8.62.1.19.4.1.3}

xcmPidPhaser6200DX OBJECT-IDENTITY
    STATUS      current
    DESCRIPTION
        "Xerox Phaser 6200DX Laser Printer launch configuration model,
                  version, and complete product identifier."


    ::= { xcmPidPhaser6200 4 }
        -- ::= {1.3.6.1.4.1.253.8.62.1.19.4.1.4}

-- Phaser 6250 Family, 26-ppm Single Pass A4 Color Laser Printer
-- 6250B is the Base configuration (No Network, 128MB RAM)
-- 6250N adds: Built-in 10/100 Ethernet, 256MB RAM, Pipeline performance
-- 6250DP: 6250N + Auto Duplex, Photomode
-- 6250DT: 6250DP + Single Auxiliary Tray + 256 (512MB total)
-- 6250DX: 6250DT + Internal HD

xcmPidPhaser6250 OBJECT-IDENTITY
    STATUS      current
    DESCRIPTION
        "Xerox Phaser 6250 Laser Printer model identifier
                 (not a complete product identifier)."
    ::= { xcmPidPhaser6yyyFamily 3 }
        -- ::= {1.3.6.1.4.1.253.8.62.1.19.4.3}
            -- => SAP PID string = "C43"
            -- => USB PID string = 15699 = 0x3D53

xcmPidPhaser6250B OBJECT-IDENTITY
    STATUS      current
    DESCRIPTION
        "Xerox Phaser 6250B Laser Printer,
                  the Base configuration (No Network, 128MB RAM)
                  launch configuration model,
                  version, and complete product identifier."
    ::= { xcmPidPhaser6250 1 }
        -- ::= {1.3.6.1.4.1.253.8.62.1.19.4.3.1}

xcmPidPhaser6250N OBJECT-IDENTITY
    STATUS      current
    DESCRIPTION
        "Xerox Phaser 6250N Laser Printer
                  adds: Built-in 10/100 Ethernet, 256MB RAM,
    Pipeline performance
                  launch configuration model,
                  version, and complete product identifier."
    ::= { xcmPidPhaser6250 2 }
        -- ::= {1.3.6.1.4.1.253.8.62.1.19.4.3.2}

xcmPidPhaser6250DP OBJECT-IDENTITY
    STATUS      current
    DESCRIPTION
        "Xerox Phaser 6250DP Laser Printer
                  6250N + Auto Duplex, Photomode
                  launch configuration model,
                  version, and complete product identifier."
    ::= { xcmPidPhaser6250 3 }
        -- ::= {1.3.6.1.4.1.253.8.62.1.19.4.3.3}

xcmPidPhaser6250DT OBJECT-IDENTITY
    STATUS      current


    DESCRIPTION
        "Xerox Phaser 6250DT Laser Printer
                  6250DP + Single Auxiliary Tray + 256 (512MB total)
                  launch configuration model,
                  version, and complete product identifier."
    ::= { xcmPidPhaser6250 5 }
        -- ::= {1.3.6.1.4.1.253.8.62.1.19.4.3.5}

xcmPidPhaser6250DX OBJECT-IDENTITY
    STATUS      current
    DESCRIPTION
        "Xerox Phaser 6250DX Laser Printer
                  6250DT + Internal HD
                  launch configuration model,
                  version, and complete product identifier."
    ::= { xcmPidPhaser6250 4 }
        -- ::= {1.3.6.1.4.1.253.8.62.1.19.4.3.4}

--
-- Phaser 6300/6350, 26/36-ppm Single Pass A4 Color Laser Printers
-- 6300N is the Base configuration for the 6300
--       (Built-in 10/100 Ethernet, 128MB RAM, 26ppm B&W/36ppm color)
-- 6300DN: 6300N + Auto Duplex
-- 6350DP is the Base configuration for the 6350
--       (Built-in 10/100 Ethernet, 256MB RAM, 36/36ppm)
-- 6350DT: 6300DP + Single Auxiliary Tray + 256MB (512MB total)
-- 6350DX: 6300DT + Internal HD

xcmPidPhaser6300 OBJECT-IDENTITY
    STATUS      current
    DESCRIPTION
        "Xerox Phaser 6300 Laser Printer model identifier
                 (not a complete product identifier)."
    ::= { xcmPidPhaser6yyyFamily 4 }
        -- ::= {1.3.6.1.4.1.253.8.62.1.19.4.4}
            -- => SAP PID string = "C44"
            -- => USB PID string = 15700 = 0x3D54

xcmPidPhaser6300B OBJECT-IDENTITY
    STATUS      current
    DESCRIPTION
        "Xerox Phaser 6300B Laser Printer
                  launch configuration model,
                  version, and complete product identifier."
    ::= { xcmPidPhaser6300 1 }
        -- ::= {1.3.6.1.4.1.253.8.62.1.19.4.4.1}

xcmPidPhaser6300N OBJECT-IDENTITY
    STATUS      current
    DESCRIPTION
        "Xerox Phaser 6300N Laser Printer
                  the Base configuration (Built-in 10/100 Ethernet, 128M


                  26ppm B&W/36ppm Color) launch configuration model,
                  version, and complete product identifier."
    ::= { xcmPidPhaser6300 2 }
        -- ::= {1.3.6.1.4.1.253.8.62.1.19.4.4.2}

xcmPidPhaser6300DN OBJECT-IDENTITY
    STATUS      current
    DESCRIPTION
        "Xerox Phaser 6300DN Laser Printer
                  6300N + Auto Duplex
                  launch configuration model,
                  version, and complete product identifier."
    ::= { xcmPidPhaser6300 3 }
        -- ::= {1.3.6.1.4.1.253.8.62.1.19.4.4.3}

xcmPidPhaser6350 OBJECT-IDENTITY
    STATUS      current
    DESCRIPTION
        "Xerox Phaser 6350 Series Laser Printer model identifier
                 (not a complete product identifier)."
    ::= { xcmPidPhaser6yyyFamily 6 }
        -- ::= {1.3.6.1.4.1.253.8.62.1.19.4.6}
            -- => SAP PID string = "C46"
            -- => USB PID string = 15702 = 0x3D56

xcmPidPhaser6350DP OBJECT-IDENTITY
    STATUS      current
    DESCRIPTION
        "Xerox Phaser 6350DP Laser Printer
                  6300DN + Photomode + 128MB (256MB total) + 36ppm B&W
                  launch configuration model,
                  version, and complete product identifier."
    ::= { xcmPidPhaser6350 1 }
        -- ::= {1.3.6.1.4.1.253.8.62.1.19.4.6.1}

xcmPidPhaser6350DT OBJECT-IDENTITY
    STATUS      current
    DESCRIPTION
        "Xerox Phaser 6350DT Laser Printer
                  6350DP + Single Auxiliary Tray + 256MB (512MB total)
                  launch configuration model,
                  version, and complete product identifier."
    ::= { xcmPidPhaser6350 2 }
        -- ::= {1.3.6.1.4.1.253.8.62.1.19.4.6.2}

xcmPidPhaser6350DX OBJECT-IDENTITY
    STATUS      current
    DESCRIPTION
        "Xerox Phaser 6350DX Laser Printer
                  6350DT + Internal HD
                  launch configuration model,
                  version, and complete product identifier."
    ::= { xcmPidPhaser6350 3 }
        -- ::= {1.3.6.1.4.1.253.8.62.1.19.4.6.3}


--
--

-- Phaser 6120
-- xcmPIDPhaser6120b -  base configuration
-- xcmPIDPhaser6120n -  base configuration + optional Network Card

xcmPidPhaser6120 OBJECT-IDENTITY
    STATUS      current
    DESCRIPTION
        "Xerox Phaser 6120 Laser Printer model identifier
                 (not a complete product identifier)."
    ::= { xcmPidPhaser6yyyFamily 7 }


        -- ::= {1.3.6.1.4.1.253.8.62.1.19.4.7}
            -- => SAP PID string = "C47"
            -- => USB PID string = 15703 = 0x3D57

xcmPidPhaser6120b OBJECT-IDENTITY
    STATUS      current
    DESCRIPTION
        "Xerox Phaser 6120b (Base) Laser Printer launch
   configuration model, version, and complete product identifier."
    ::= { xcmPidPhaser6120 1 }
        -- ::= {1.3.6.1.4.1.253.8.62.1.19.4.7.1}

xcmPidPhaser6120n OBJECT-IDENTITY
    STATUS      current
    DESCRIPTION
        "Xerox Phaser 6120n (Base+Network Card) Laser Printer launch
   configuration model, version, and complete product identifier."
    ::= { xcmPidPhaser6120 2 }
        -- ::= {1.3.6.1.4.1.253.8.62.1.19.4.7.2}

--
-- Phaser 6360, 42 letter / 40-ppm Single Pass A4 Color Laser Printers
-- 6360N:  Networked 256 MB
-- 6360DN: 6360N + Duplex
-- 6360DT: 6360DN + single auxiliary tray / 550 sheets + 256 MB
-- 6360DX: 6360DT + two auxiliary trays / 550 sheets +  256 MB +
--                  hard drive

xcmPidPhaser6360 OBJECT-IDENTITY
    STATUS      current
    DESCRIPTION
        "Xerox Phaser 6360 Color Laser Printer model identifier
                 (not a complete product identifier)."
    ::= { xcmPidPhaser6yyyFamily 8 }
        -- ::= {1.3.6.1.4.1.253.8.62.1.19.4.8}
            -- => SAP PID string = "C48"
            -- => USB PID string = 15704 = 0x3D58

xcmPidPhaser6360N OBJECT-IDENTITY
    STATUS      current
    DESCRIPTION
        "Xerox Phaser 6360N Color Laser Printer
                  launch configuration model,
                  version, and complete product identifier."
    ::= { xcmPidPhaser6360 1 }
        -- ::= {1.3.6.1.4.1.253.8.62.1.19.4.8.1}

xcmPidPhaser6360DN OBJECT-IDENTITY
    STATUS      current
    DESCRIPTION
        "Xerox Phaser 6360DN Color Laser Printer
                  launch configuration model,
                  version, and complete product identifier."


    ::= { xcmPidPhaser6360 2 }
        -- ::= {1.3.6.1.4.1.253.8.62.1.19.4.8.2}

xcmPidPhaser6360DT OBJECT-IDENTITY
    STATUS      current
    DESCRIPTION
        "Xerox Phaser 6360DT Color Laser Printer
                  launch configuration model,
                  version, and complete product identifier."
    ::= { xcmPidPhaser6360 3 }
        -- ::= {1.3.6.1.4.1.253.8.62.1.19.4.8.3}

xcmPidPhaser6360DX OBJECT-IDENTITY
    STATUS      current
    DESCRIPTION
        "Xerox Phaser 6360DX Color Laser Printer
                  launch configuration model,
                  version, and complete product identifier."
    ::= { xcmPidPhaser6360 4 }
        -- ::= {1.3.6.1.4.1.253.8.62.1.19.4.8.4}

-- Phaser 6180  Phaser Color Printers
-- 6180N:  Networked 128 MB
-- 6180DN: 6180N + Duplex

xcmPidPhaser6180 OBJECT-IDENTITY
    STATUS      current
    DESCRIPTION
        "Xerox Phaser 6180 Color Printer model identifier
                 (not a complete product identifier)."
    ::= { xcmPidPhaser6yyyFamily 9 }
        -- ::= {1.3.6.1.4.1.253.8.62.1.19.4.9}
            -- => SAP PID string = "C49"
            -- => USB PID string = 15705 = 0x3D59

xcmPidPhaser6180N OBJECT-IDENTITY
    STATUS      current
    DESCRIPTION
        "Xerox Phaser 6180N Color Printer
                  launch configuration model,
                  version, and complete product identifier."
    ::= { xcmPidPhaser6180 1 }
        -- ::= {1.3.6.1.4.1.253.8.62.1.19.4.9.1}

xcmPidPhaser6180DN OBJECT-IDENTITY
    STATUS      current
    DESCRIPTION
        "Xerox Phaser 6180DN Color Printer
                  launch configuration model,
                  version, and complete product identifier."
    ::= { xcmPidPhaser6180 2 }


        -- ::= {1.3.6.1.4.1.253.8.62.1.19.4.9.2}

-- Phaser 6110N  Phaser Printer

xcmPidPhaser6110N OBJECT-IDENTITY
    STATUS      current
    DESCRIPTION
        "Xerox Phaser 6110N Printer model identifier
                 (not a complete product identifier)."
    ::= { xcmPidPhaser6yyyFamily 17 }
        -- ::= {1.3.6.1.4.1.253.8.62.1.19.4.17}
            -- => SAP PID string = "C4A"
            -- => USB PID string = 15706 = 0x3D5A

xcmPidPhaser6110Nv1 OBJECT-IDENTITY
    STATUS      current
    DESCRIPTION
        "Xerox Phaser 6110N Version 1 Printer
                  launch configuration model,
                  version, and complete product identifier."
    ::= { xcmPidPhaser6110N 1 }
        -- ::= {1.3.6.1.4.1.253.8.62.1.19.4.17.1}

-- Phaser 6115MFP  Phaser Color Printers
-- 6115B:  Base: MFP with Networking
-- 6115BD: Base + Duplex

xcmPidPhaser6115 OBJECT-IDENTITY
    STATUS      current
    DESCRIPTION
        "Xerox Phaser 6115 model identifier
                 (not a complete product identifier)."
    ::= { xcmPidPhaser6yyyFamily 18 }
        -- ::= {1.3.6.1.4.1.253.8.62.1.19.4.18}
            -- => SAP PID string = "C4B"
            -- => USB PID string = 15707 = 0x3D5B

xcmPidPhaser6115N OBJECT-IDENTITY
    STATUS      current
    DESCRIPTION
        "Xerox Phaser 6115 Base launch configuration model,
                  version, and complete product identifier."
    ::= { xcmPidPhaser6115 1 }
        -- ::= {1.3.6.1.4.1.253.8.62.1.19.4.18.1}

xcmPidPhaser6115DN OBJECT-IDENTITY
    STATUS      current
    DESCRIPTION
        "Xerox Phaser 6115 Base + Duplex launch configuration
            model, version, and complete product identifier."
    ::= { xcmPidPhaser6115 2 }
        -- ::= {1.3.6.1.4.1.253.8.62.1.19.4.18.2}


-- Phaser 6110MFP3  Phaser Printer

xcmPidPhaser6110MFP3 OBJECT-IDENTITY
    STATUS      current
    DESCRIPTION
        "Xerox Phaser 6110MFP3 Printer model identifier
                 (not a complete product identifier)."
    ::= { xcmPidPhaser6yyyFamily 19 }
        -- ::= {1.3.6.1.4.1.253.8.62.1.19.4.19}
            -- => SAP PID string = "C4C"
            -- => USB PID string = 15708 = 0x3D5C

xcmPidPhaser6110MFP3v1 OBJECT-IDENTITY
    STATUS      current
    DESCRIPTION
        "Xerox Phaser 6110MFP3 Version 1 Printer
                  launch configuration model,
                  version, and complete product identifier."
    ::= { xcmPidPhaser6110MFP3 1 }
        -- ::= {1.3.6.1.4.1.253.8.62.1.19.4.19.1}

-- Phaser 6110MFP4  Phaser Printer

xcmPidPhaser6110MFP4 OBJECT-IDENTITY
    STATUS      current
    DESCRIPTION
        "Xerox Phaser 6110MFP4 Printer model identifier
                 (not a complete product identifier)."
    ::= { xcmPidPhaser6yyyFamily 20 }
        -- ::= {1.3.6.1.4.1.253.8.62.1.19.4.20}
            -- => SAP PID string = "C4D"
            -- => USB PID string = 15709 = 0x3D5D

xcmPidPhaser6110MFP4v1 OBJECT-IDENTITY
    STATUS      current
    DESCRIPTION
        "Xerox Phaser 6110MFP4 Version 1 Printer
                  launch configuration model,
                  version, and complete product identifier."
    ::= { xcmPidPhaser6110MFP4 1 }
        -- ::= {1.3.6.1.4.1.253.8.62.1.19.4.20.1}

-- Phaser 6180MFP


xcmPidPhaser6180MFP OBJECT-IDENTITY
    STATUS      current
    DESCRIPTION
        "Xerox Phaser 6180 Printer model identifier
                 (not a complete product identifier)."
    ::= { xcmPidPhaser6yyyFamily 21 }
        -- ::= {1.3.6.1.4.1.253.8.62.1.19.4.21}
            -- => SAP PID string = "C4E"
            -- => USB PID string = 15710 = 0x3D5E

xcmPidPhaser6180MFPN OBJECT-IDENTITY
    STATUS      current
    DESCRIPTION
        "Xerox Phaser 6180 Printer (Network + 128MB RAM)
                  launch configuration model,
                  version, and complete product identifier."
    ::= { xcmPidPhaser6180MFP 1 }
        -- ::= {1.3.6.1.4.1.253.8.62.1.19.4.21.1}

xcmPidPhaser6180MFPDN OBJECT-IDENTITY
    STATUS      current
    DESCRIPTION
        "Xerox Phaser 6180 Printer (Network + 128MB RAM + Duplex)
                  launch configuration model,
                  version, and complete product identifier."
    ::= { xcmPidPhaser6180MFP 2 }
        -- ::= {1.3.6.1.4.1.253.8.62.1.19.4.21.2}


-- Phaser 6130


xcmPidPhaser6130 OBJECT-IDENTITY
    STATUS      current
    DESCRIPTION
        "Xerox Phaser 6130 model identifier
                 (not a complete product identifier)."
    ::= { xcmPidPhaser6yyyFamily 23 }
        -- ::= {1.3.6.1.4.1.253.8.62.1.19.4.23}
            -- => SAP PID string = "C4G"
            -- => USB PID string = 15712 = 0x3D60

xcmPidPhaser6130N OBJECT-IDENTITY
    STATUS      current
    DESCRIPTION


        "Xerox Phaser Color Printer 6130N
                  launch configuration model,
                  version, and complete product identifier."
    ::= { xcmPidPhaser6130 1 }
        -- ::= {1.3.6.1.4.1.253.8.62.1.19.4.23.1}

-- Phaser 6125


xcmPidPhaser6125 OBJECT-IDENTITY
    STATUS      current
    DESCRIPTION
        "Xerox Phaser 6125 model identifier
                 (not a complete product identifier)."
    ::= { xcmPidPhaser6yyyFamily 24 }
        -- ::= {1.3.6.1.4.1.253.8.62.1.19.4.24}
            -- => SAP PID string = "C4H"
            -- => USB PID string = 15713 = 0x3D61

xcmPidPhaser6125N OBJECT-IDENTITY
    STATUS      current
    DESCRIPTION
        "Xerox Phaser Color Printer 6125N
                  launch configuration model,
                  version, and complete product identifier."
    ::= { xcmPidPhaser6125 1 }
        -- ::= {1.3.6.1.4.1.253.8.62.1.19.4.24.1}

-- Xerox Phaser 6280  Phaser Color Printers
-- Xerox Phaser 6280N:  Networked + 128MB RAM
-- Xerox Phaser 6280DN: 6280N + Duplex
-- Xerox Phaser 6280DT: 6280DN + additional tray(s) + RAM


xcmPidPhaser6280 OBJECT-IDENTITY
    STATUS      current
    DESCRIPTION
        "Xerox Phaser 6280 Color Printer model identifier
                 (not a complete product identifier)."
    ::= { xcmPidPhaser6yyyFamily 25 }
        -- ::= {1.3.6.1.4.1.253.8.62.1.19.4.25}
            -- => SAP PID string = "C4I"
            -- => USB PID string = 15714 = 0x3D62

xcmPidPhaser6280N OBJECT-IDENTITY
    STATUS      current
    DESCRIPTION
        "Xerox Phaser 6280N Color Printer
           model and configuration identifier


           (not a complete product identifier)."
    ::= { xcmPidPhaser6280 1 }
        -- ::= {1.3.6.1.4.1.253.8.62.1.19.4.25.1}

xcmPidPhaser6280Nv1 OBJECT-IDENTITY
    STATUS      current
    DESCRIPTION
        "Xerox Phaser 6280N Color Printer
            launch model, configuration, version 1.
            A complete product identifier."
    ::= { xcmPidPhaser6280N 1 }
        -- ::= {1.3.6.1.4.1.253.8.62.1.19.4.25.1.1}

xcmPidPhaser6280DN OBJECT-IDENTITY
    STATUS      current
    DESCRIPTION
        "Xerox Phaser 6280DN Color Printer
           model and configuration identifier
           (not a complete product identifier)."
    ::= { xcmPidPhaser6280 2 }
        -- ::= {1.3.6.1.4.1.253.8.62.1.19.4.25.2}

xcmPidPhaser6280DNv1 OBJECT-IDENTITY
    STATUS      current
    DESCRIPTION
        "Xerox Phaser 6280DN Color Printer
            launch model, configuration, version 1.
            A complete product identifier."
    ::= { xcmPidPhaser6280DN 1 }
        -- ::= {1.3.6.1.4.1.253.8.62.1.19.4.25.2.1}

xcmPidPhaser6280DT OBJECT-IDENTITY
    STATUS      current
    DESCRIPTION
        "Xerox Phaser 6280DT Color Printer
           model and configuration identifier
           (not a complete product identifier)."
    ::= { xcmPidPhaser6280 3 }
        -- ::= {1.3.6.1.4.1.253.8.62.1.19.4.25.3}

xcmPidPhaser6280DTv1 OBJECT-IDENTITY
    STATUS      current
    DESCRIPTION
        "Xerox Phaser 6280DT Color Printer
            launch model, configuration, version 1.
            A complete product identifier."
    ::= { xcmPidPhaser6280DT 1 }
        -- ::= {1.3.6.1.4.1.253.8.62.1.19.4.25.3.1}

--
--


xcmPidPhaser6700 OBJECT-IDENTITY
    STATUS      current
    DESCRIPTION
        "Xerox Phaser 6700  model identifier
           (not a complete product identifier)."
    ::= { xcmPidPhaser6yyyFamily 30 }


        -- ::= {1.3.6.1.4.1.253.8.62.1.19.4.30}
            -- => SAP PID string = "C4N"
            -- => USB PID string = 15719 = 0x3D67

-- PNP PID Generation PLEASE NOTE:
--   The following assumes the IEEE 1284 Device ID contains
--   attributes corresponding to manufacturer and model name.
--
--   The following PNP IDs were generated using these
--   parameters (manufacturer and model):
--     -mf "Xerox" -mo "Phaser 6700N"
--     -mf "Xerox" -mo "Phaser 6700DN"
--     -mf "Xerox" -mo "Phaser 6700DT"
--     -mf "Xerox" -mo "Phaser 6700DX"
--   The generated PNP PIDs are only valid for those parameters
       -- => Phaser 6700N XeroxPhaser_6700NF19A
       -- => Phaser 6700DN XeroxPhaser_6700DNFFF7
       -- => Phaser 6700DT XeroxPhaser_6700DT3476
       -- => Phaser 6700DX XeroxPhaser_6700DX3176

-- Phaser 6700 Base Configuration 1 "N"
-- Phaser 6700 Networking / 1GB RAM

xcmPidPhaser6700C1 OBJECT-IDENTITY
    STATUS      current
    DESCRIPTION
        "Xerox Phaser 6700
           model and configuration 1 identifier
           (not a complete product identifier)."
    ::= { xcmPidPhaser6700 1 }
        -- ::= {1.3.6.1.4.1.253.8.62.1.19.4.30.1}

xcmPidPhaser6700C1V1 OBJECT-IDENTITY
    STATUS      current
    DESCRIPTION
        "Xerox Phaser 6700
            launch model, configuration 1, version 1.
            A complete product identifier."
    ::= { xcmPidPhaser6700C1 1 }
        -- ::= {1.3.6.1.4.1.253.8.62.1.19.4.30.1.1}

-- Phaser 6700 Configuration 2 "DN"
-- Phaser 6700 Networking / 1GB RAM / Duplex

xcmPidPhaser6700C2 OBJECT-IDENTITY
    STATUS      current
    DESCRIPTION
        "Xerox Phaser 6700
           model and configuration 2 identifier
           (not a complete product identifier)."
    ::= { xcmPidPhaser6700 2 }
        -- ::= {1.3.6.1.4.1.253.8.62.1.19.4.30.2}

xcmPidPhaser6700C2V1 OBJECT-IDENTITY


    STATUS      current
    DESCRIPTION
        "Xerox Phaser 6700
            launch model, configuration 2, version 1.
            A complete product identifier."
    ::= { xcmPidPhaser6700C2 1 }
        -- ::= {1.3.6.1.4.1.253.8.62.1.19.4.30.2.1}

-- Phaser 6700 Configuration 3 "DT"
-- Phaser 6700 Networking / 1GB RAM / Duplex / Two 550 Sheet Trays

xcmPidPhaser6700C3 OBJECT-IDENTITY
    STATUS      current
    DESCRIPTION
        "Xerox Phaser 6700
           model and configuration 3 identifier
           (not a complete product identifier)."
    ::= { xcmPidPhaser6700 3 }
        -- ::= {1.3.6.1.4.1.253.8.62.1.19.4.30.3}

xcmPidPhaser6700C3V1 OBJECT-IDENTITY
    STATUS      current
    DESCRIPTION
        "Xerox Phaser 6700
            launch model, configuration 3, version 1.
            A complete product identifier."
    ::= { xcmPidPhaser6700C3 1 }
        -- ::= {1.3.6.1.4.1.253.8.62.1.19.4.30.3.1}

-- Phaser 6700 Configuration 4 "DX"
-- Phaser 6700 Networking / Duplex / 1 GB RAM / Two 550 Sheet Trays
-- Phaser 6700 Hard Drive
xcmPidPhaser6700C4 OBJECT-IDENTITY
    STATUS      current
    DESCRIPTION
        "Xerox Phaser 6700
           model and configuration 4 identifier
           (not a complete product identifier)."
    ::= { xcmPidPhaser6700 4 }
        -- ::= {1.3.6.1.4.1.253.8.62.1.19.4.30.4}

xcmPidPhaser6700C4V1 OBJECT-IDENTITY
    STATUS      current
    DESCRIPTION
        "Xerox Phaser 6700
            launch model, configuration 4, version 1.
            A complete product identifier."
    ::= { xcmPidPhaser6700C4 1 }
        -- ::= {1.3.6.1.4.1.253.8.62.1.19.4.30.4.1}

--
--


xcmPidWorkCentre6015B OBJECT-IDENTITY
    STATUS      current
    DESCRIPTION
        "Xerox WorkCentre 6015B  model identifier
           (not a complete product identifier)."
    ::= { xcmPidPhaser6yyyFamily 32 }
        -- ::= {1.3.6.1.4.1.253.8.62.1.19.4.32}
            -- => SAP PID string = "C4P"
            -- => USB PID string = 15721 = 0x3D69
            -- => PnP-X WiFi ID = VEN_0109&DEV_3D69
            -- => PnP ID = XeroxWorkCentre_6015B64F

-- PNP PID Generation PLEASE NOTE:
--   The following assumes the IEEE 1284 Device ID contains
--   attributes corresponding to manufacturer and model name.
--
--   The following PNP IDs were generated using these
--   parameters (manufacturer and model):
--     -mf "Xerox" -mo "WorkCentre 6015B"
--   The generated PNP PIDs are only valid for those parameters
       -- => WorkCentre 6015B XeroxWorkCentre_6015B64F

-- WorkCentre 6015B Configuration 1

xcmPidWorkCentre6015BC1 OBJECT-IDENTITY
    STATUS      current
    DESCRIPTION
        "Xerox WorkCentre 6015B
           model and configuration 1 identifier
           (not a complete product identifier)."
    ::= { xcmPidWorkCentre6015B 1 }
        -- ::= {1.3.6.1.4.1.253.8.62.1.19.4.32.1}

-- WorkCentre 6015B Configuration 1 Version 1


xcmPidWorkCentre6015BC1V1 OBJECT-IDENTITY
    STATUS      current
    DESCRIPTION
        "Xerox WorkCentre 6015B
            launch model, configuration 1, version 1.
            A complete product identifier."
    ::= { xcmPidWorkCentre6015BC1 1 }
        -- ::= {1.3.6.1.4.1.253.8.62.1.19.4.32.1.1}


xcmPidPhaser6500 OBJECT-IDENTITY
    STATUS      current
    DESCRIPTION
        "Xerox Phaser 6500  model identifier
           (not a complete product identifier)."
    ::= { xcmPidPhaser6yyyFamily 33 }
        -- ::= {1.3.6.1.4.1.253.8.62.1.19.4.33}
            -- => SAP PID string = "C4Q"
            -- => USB PID string = 15722 = 0x3D6A

-- PNP PID Generation PLEASE NOTE:
--   The following assumes the IEEE 1284 Device ID contains
--   attributes corresponding to manufacturer and model name.
--
--   The following PNP IDs were generated using these
--   parameters (manufacturer and model):
--     -mf "Xerox" -mo "Phaser 6500"
--   The generated PNP PIDs are only valid for those parameters
       -- => Phaser 6500 XeroxPhaser_65001BAC

-- Phaser 6500 Base Configuration 1 "N"

xcmPidPhaser6500C1 OBJECT-IDENTITY
    STATUS      current
    DESCRIPTION
        "Xerox Phaser 6500
           model and configuration 1 identifier
           (not a complete product identifier)."
    ::= { xcmPidPhaser6500 1 }
        -- ::= {1.3.6.1.4.1.253.8.62.1.19.4.33.1}

xcmPidPhaser6500C1V1 OBJECT-IDENTITY
    STATUS      current
    DESCRIPTION
        "Xerox Phaser 6500
            launch model, configuration 1, version 1.
            A complete product identifier."
    ::= { xcmPidPhaser6500C1 1 }
        -- ::= {1.3.6.1.4.1.253.8.62.1.19.4.33.1.1}


-- Phaser 6500 Configuration 2 "DN"

xcmPidPhaser6500C2 OBJECT-IDENTITY
    STATUS      current
    DESCRIPTION
        "Xerox Phaser 6500
           model and configuration 2 identifier
           (not a complete product identifier)."
    ::= { xcmPidPhaser6500 2 }
        -- ::= {1.3.6.1.4.1.253.8.62.1.19.4.33.2}

xcmPidPhaser6500C2V1 OBJECT-IDENTITY
    STATUS      current
    DESCRIPTION
        "Xerox Phaser 6500
            launch model, configuration 2, version 1.
            A complete product identifier."
    ::= { xcmPidPhaser6500C2 1 }
        -- ::= {1.3.6.1.4.1.253.8.62.1.19.4.33.2.1}


xcmPidWorkCentre6505 OBJECT-IDENTITY
    STATUS      current
    DESCRIPTION
        "Xerox WorkCentre 6505  model identifier
           (not a complete product identifier)."
    ::= { xcmPidPhaser6yyyFamily 34 }
        -- ::= {1.3.6.1.4.1.253.8.62.1.19.4.34}
            -- => SAP PID string = "C4R"
            -- => USB PID string = 15723 = 0x3D6B

-- PNP PID Generation PLEASE NOTE:
--   The following assumes the IEEE 1284 Device ID contains
--   attributes corresponding to manufacturer and model name.
--
--   The following PNP IDs were generated using these
--   parameters (manufacturer and model):
--     -mf "Xerox" -mo "WorkCentre 6505"
--   The generated PNP PIDs are only valid for those parameters
       -- => WorkCentre 6505 XeroxWorkCentre_65055FE5

-- WorkCentre 6505 Base Configuration 1 "N"

xcmPidWorkCentre6505C1 OBJECT-IDENTITY
    STATUS      current
    DESCRIPTION
        "Xerox WorkCentre 6505
           model and configuration 1 identifier
           (not a complete product identifier)."
    ::= { xcmPidWorkCentre6505 1 }
        -- ::= {1.3.6.1.4.1.253.8.62.1.19.4.34.1}


xcmPidWorkCentre6505C1V1 OBJECT-IDENTITY
    STATUS      current
    DESCRIPTION
        "Xerox WorkCentre 6505
            launch model, configuration 1, version 1.
            A complete product identifier."
    ::= { xcmPidWorkCentre6505C1 1 }
        -- ::= {1.3.6.1.4.1.253.8.62.1.19.4.34.1.1}

-- WorkCentre 6505 Configuration 2 "D"

xcmPidWorkCentre6505C2 OBJECT-IDENTITY
    STATUS      current
    DESCRIPTION
        "Xerox WorkCentre 6505
           model and configuration 2 identifier
           (not a complete product identifier)."
    ::= { xcmPidWorkCentre6505 2 }
        -- ::= {1.3.6.1.4.1.253.8.62.1.19.4.34.2}

xcmPidWorkCentre6505C2V1 OBJECT-IDENTITY
    STATUS      current
    DESCRIPTION
        "Xerox WorkCentre 6505
            launch model, configuration 2, version 1.
            A complete product identifier."
    ::= { xcmPidWorkCentre6505C2 1 }
        -- ::= {1.3.6.1.4.1.253.8.62.1.19.4.34.2.1}


xcmPidPhaser6000 OBJECT-IDENTITY
    STATUS      current
    DESCRIPTION
        "Xerox Phaser 6000  model identifier
           (not a complete product identifier)."
    ::= { xcmPidPhaser6yyyFamily 35 }
        -- ::= {1.3.6.1.4.1.253.8.62.1.19.4.35}
            -- => SAP PID string = "C4S"
            -- => USB PID string = 15724 = 0x3D6C

-- PNP PID Generation PLEASE NOTE:
--   The following assumes the IEEE 1284 Device ID contains
--   attributes corresponding to manufacturer and model name.
--
--   The following PNP IDs were generated using these
--   parameters (manufacturer and model):
--     -mf "Xerox" -mo "Phaser 6000"
--   The generated PNP PIDs are only valid for those parameters
       -- => Phaser 6000 XeroxPhaser_60001ABC


-- Phaser 6000 Base Configuration

xcmPidPhaser6000C1 OBJECT-IDENTITY
    STATUS      current
    DESCRIPTION
        "Xerox Phaser 6000
           model and configuration 1 identifier
           (not a complete product identifier)."
    ::= { xcmPidPhaser6000 1 }
        -- ::= {1.3.6.1.4.1.253.8.62.1.19.4.35.1}

xcmPidPhaser6000C1V1 OBJECT-IDENTITY
    STATUS      current
    DESCRIPTION
        "Xerox Phaser 6000
            launch model, configuration 1, version 1.
            A complete product identifier."
    ::= { xcmPidPhaser6000C1 1 }
        -- ::= {1.3.6.1.4.1.253.8.62.1.19.4.35.1.1}


xcmPidWorkCentre6015 OBJECT-IDENTITY
    STATUS      current
    DESCRIPTION
        "Xerox WorkCentre 6015 model identifier
           (not a complete product identifier)."
    ::= { xcmPidPhaser6yyyFamily 36 }
        -- ::= {1.3.6.1.4.1.253.8.62.1.19.4.36}
            -- => SAP PID string = "C4T"
            -- => USB PID string = 15725 = 0x3D6D
            -- => PnP-X WiFi ID = VEN_0109&DEV_3D6D
            -- => PnP ID = XeroxWorkCentre_6015CEF4

-- PNP PID Generation PLEASE NOTE:
--   The following assumes the IEEE 1284 Device ID contains
--   attributes corresponding to manufacturer and model name.
--
--   The following PNP IDs were generated using these
--   parameters (manufacturer and model):
--     -mf "Xerox" -mo "WorkCentre 6015"
--   The generated PNP PIDs are only valid for those parameters
       -- => WorkCentre 6015 XeroxWorkCentre_6015CEF4

-- WorkCentre 6015 Configuration 1

xcmPidWorkCentre6015C1 OBJECT-IDENTITY
    STATUS      current
    DESCRIPTION
        "Xerox WorkCentre 6015
           model and configuration 1 identifier
           (not a complete product identifier)."


    ::= { xcmPidWorkCentre6015 1 }
        -- ::= {1.3.6.1.4.1.253.8.62.1.19.4.36.1}

-- WorkCentre 6015 Configuration 1 Version 1

xcmPidWorkCentre6015C1V1 OBJECT-IDENTITY
    STATUS      current
    DESCRIPTION
        "Xerox WorkCentre 6015
            launch model, configuration 1, version 1.
            A complete product identifier."
    ::= { xcmPidWorkCentre6015C1 1 }
        -- ::= {1.3.6.1.4.1.253.8.62.1.19.4.36.1.1}

-- WorkCentre 6015 Configuration 2

xcmPidWorkCentre6015C2 OBJECT-IDENTITY
    STATUS      current
    DESCRIPTION
        "Xerox WorkCentre 6015
           model and configuration 2 identifier
           (not a complete product identifier)."
    ::= { xcmPidWorkCentre6015 2 }
        -- ::= {1.3.6.1.4.1.253.8.62.1.19.4.36.2}

-- WorkCentre 6015 Configuration 2 Version 1

xcmPidWorkCentre6015C2V1 OBJECT-IDENTITY
    STATUS      current
    DESCRIPTION
        "Xerox WorkCentre 6015
            launch model, configuration 2, version 1.
            A complete product identifier."
    ::= { xcmPidWorkCentre6015C2 1 }
        -- ::= {1.3.6.1.4.1.253.8.62.1.19.4.36.2.1}



xcmPidPhaser6600 OBJECT-IDENTITY
    STATUS      current
    DESCRIPTION
        "Xerox Phaser 6600 model identifier
           (not a complete product identifier)."
    ::= { xcmPidPhaser6yyyFamily 37 }
        -- ::= {1.3.6.1.4.1.253.8.62.1.19.4.37}
            -- => SAP PID string = "C4U"
            -- => USB PID string = 15726 = 0x3D6E
            -- => PnP-X WiFi ID = VEN_0109&DEV_3D6E
            -- => PnP ID = XeroxPhaser_66001B5C
            -- => Compatible ID = XR_PS_Basic_Color


-- PNP PID Generation PLEASE NOTE:
--   The following assumes the IEEE 1284 Device ID contains
--   attributes corresponding to manufacturer and model name.
--
--   The following PNP IDs were generated using these
--   parameters (manufacturer and model):
--     -mf "Xerox" -mo "Phaser 6600"
--   The generated PNP PIDs are only valid for those parameters
       -- => Phaser 6600       XeroxPhaser_66001B5C

-- Phaser 6600 Configuration 1

xcmPidPhaser6600NC1 OBJECT-IDENTITY
    STATUS      current
    DESCRIPTION
        "Xerox Phaser 6600
           model and configuration 1 identifier
           (not a complete product identifier)."
    ::= { xcmPidPhaser6600 1 }
        -- ::= {1.3.6.1.4.1.253.8.62.1.19.4.37.1}

-- PNP PID Generation PLEASE NOTE:
--   The following assumes the IEEE 1284 Device ID contains
--   attributes corresponding to manufacturer and model name.
--
--   The following PNP IDs were generated using these
--   parameters (manufacturer and model):
--     -mf "Xerox" -mo "Phaser 6600N"
--   The generated PNP PIDs are only valid for those parameters
       -- => Phaser 6600N      XeroxPhaser_6600N0D9B

-- Phaser 6600 Configuration 1 Version 1

xcmPidPhaser6600NC1V1 OBJECT-IDENTITY
    STATUS      current
    DESCRIPTION
        "Xerox Phaser 6600
            launch model, configuration 1, version 1.
            A complete product identifier."
    ::= { xcmPidPhaser6600NC1 1 }
        -- ::= {1.3.6.1.4.1.253.8.62.1.19.4.37.1.1}

-- Phaser 6600 Configuration 2

xcmPidPhaser6600DNC2 OBJECT-IDENTITY
    STATUS      current
    DESCRIPTION
        "Xerox Phaser 6600
           model and configuration 2 identifier
           (not a complete product identifier)."
    ::= { xcmPidPhaser6600 2 }
        -- ::= {1.3.6.1.4.1.253.8.62.1.19.4.37.2}


-- PNP PID Generation PLEASE NOTE:
--   The following assumes the IEEE 1284 Device ID contains
--   attributes corresponding to manufacturer and model name.
--
--   The following PNP IDs were generated using these
--   parameters (manufacturer and model):
--     -mf "Xerox" -mo "Phaser 6600DN"
--   The generated PNP PIDs are only valid for those parameters
       -- => Phaser 6600DN      XeroxPhaser_6600DN3FCA

-- Phaser 6600 Configuration 2 Version 1

xcmPidPhaser6600DNC2V1 OBJECT-IDENTITY
    STATUS      current
    DESCRIPTION
        "Xerox Phaser 6600
            launch model, configuration 2, version 1.
            A complete product identifier."
    ::= { xcmPidPhaser6600DNC2 1 }
        -- ::= {1.3.6.1.4.1.253.8.62.1.19.4.37.2.1}

--     Xerox Phaser 7yyy = Color, A3 Family

xcmPidPhaser7yyyFamily OBJECT-IDENTITY
    STATUS      current
    DESCRIPTION
        "Xerox Phaser 7yyy Family product line identifier
                 (not a complete product identifier)."
    ::= { xcmPidXeroxPhaserPrinters 5 }
        -- ::= {1.3.6.1.4.1.253.8.62.1.19.5}

-- Phaser 7300 Family, 30/37 ppm Color Laser printer
-- 7300B is the Base configuration (no network, 128)
-- 7300N  adds: built-in 10/100 Ethernet
-- 7300DN: 7300N + Auto Duplex
-- 7300DT: 7300N + 128 (256 total), 550 Sheet Feeder,
--         Auto Duplex and a hard disk
-- 7300DX: 7300DT + 128 (384 total), 2-550 Sheet Feeder
--         (3 Auxiliary Trays Total)

xcmPidPhaser7300 OBJECT-IDENTITY
    STATUS      current
    DESCRIPTION
        "Xerox Phaser 7300 Laser Printer model identifier
                 (not a complete product identifier)."
    ::= { xcmPidPhaser7yyyFamily 1 }
        -- ::= {1.3.6.1.4.1.253.8.62.1.19.5.1}
            -- => SAP PID string = "C51"

xcmPidPhaser7300DN OBJECT-IDENTITY
    STATUS      current


    DESCRIPTION
        "Xerox Phaser 7300DN Laser Printer launch configuration model,
                  version, and complete product identifier."
    ::= { xcmPidPhaser7300 1 }
        -- ::= {1.3.6.1.4.1.253.8.62.1.19.5.1.1}

xcmPidPhaser7300N OBJECT-IDENTITY
    STATUS      current
    DESCRIPTION
        "Xerox Phaser 7300N Laser Printer launch configuration model,
                  version, and complete product identifier."
    ::= { xcmPidPhaser7300 2 }
        -- ::= {1.3.6.1.4.1.253.8.62.1.19.5.1.2}

xcmPidPhaser7300DT OBJECT-IDENTITY
    STATUS      current
    DESCRIPTION
        "Xerox Phaser 7300DT Laser Printer launch configuration model,
                  version, and complete product identifier."
    ::= { xcmPidPhaser7300 3 }
        -- ::= {1.3.6.1.4.1.253.8.62.1.19.5.1.3}

xcmPidPhaser7300DX OBJECT-IDENTITY
    STATUS      current
    DESCRIPTION
        "Xerox Phaser 7300DX Laser Printer launch configuration model,
                  version, and complete product identifier."
    ::= { xcmPidPhaser7300 4 }
        -- ::= {1.3.6.1.4.1.253.8.62.1.19.5.1.4}

xcmPidPhaser7300B OBJECT-IDENTITY
    STATUS      current
    DESCRIPTION
        "Xerox Phaser 7300B Laser Printer launch configuration model,
                  version, and complete product identifier."
    ::= { xcmPidPhaser7300 5 }
        -- ::= {1.3.6.1.4.1.253.8.62.1.19.5.1.5}

-- Phaser 7400 Family, 36/40 ppm Color Laser printer
-- 7400N:   256MB + built-in 10/100 Ethernet
-- 7400DN:  7400N + Auto Duplex + 550 Sheet Feeder
--          (1 additional 550 Sheet Feeder)
-- 7400DT:  7400N + 256 (512 total)  + 2x550 Sheet Feeders,
--          and a hard disk (3 additional 550 Sheet Feeders)
-- 7400DX:  7400DT + 550 Sheet Feeder (4 additional 550 Sheet Feeders)
-- 7400DXF: 7400DX + Finisher
--

xcmPidPhaser7400 OBJECT-IDENTITY
    STATUS      current
    DESCRIPTION


        "Xerox Phaser 7400 Laser Printer model identifier
                 (not a complete product identifier)."
    ::= { xcmPidPhaser7yyyFamily 2 }
        -- ::= {1.3.6.1.4.1.253.8.62.1.19.5.2}
            -- => SAP PID string = "C52"
            -- => USB PID string = 15734 = 0x3D76

xcmPidPhaser7400B OBJECT-IDENTITY
    STATUS      current
    DESCRIPTION
        "Xerox Phaser 7400B Laser Printer launch configuration model,
                  version, and complete product identifier."
    ::= { xcmPidPhaser7400 1 }
        -- ::= {1.3.6.1.4.1.253.8.62.1.19.5.2.1}

xcmPidPhaser7400N OBJECT-IDENTITY
    STATUS      current
    DESCRIPTION
        "Xerox Phaser 7400N Laser Printer launch configuration model,
                  version, and complete product identifier."
    ::= { xcmPidPhaser7400 2 }
        -- ::= {1.3.6.1.4.1.253.8.62.1.19.5.2.2}

xcmPidPhaser7400DN OBJECT-IDENTITY
    STATUS      current
    DESCRIPTION
        "Xerox Phaser 7400DN Laser Printer launch configuration model,
                  version, and complete product identifier."
    ::= { xcmPidPhaser7400 3 }
        -- ::= {1.3.6.1.4.1.253.8.62.1.19.5.2.3}

xcmPidPhaser7400DT OBJECT-IDENTITY
    STATUS      current
    DESCRIPTION
        "Xerox Phaser 7400DT Laser Printer launch configuration model,
                  version, and complete product identifier."
    ::= { xcmPidPhaser7400 4 }
        -- ::= {1.3.6.1.4.1.253.8.62.1.19.5.2.4}

xcmPidPhaser7400DX OBJECT-IDENTITY
    STATUS      current
    DESCRIPTION
        "Xerox Phaser 7400DX Laser Printer launch configuration model,
                  version, and complete product identifier."
    ::= { xcmPidPhaser7400 5 }
        -- ::= {1.3.6.1.4.1.253.8.62.1.19.5.2.5}

xcmPidPhaser7400DXF OBJECT-IDENTITY
    STATUS      current
    DESCRIPTION
        "Xerox Phaser 7400DXF Laser Printer launch configuration model,
                  version, and complete product identifier."
    ::= { xcmPidPhaser7400 6 }
        -- ::= {1.3.6.1.4.1.253.8.62.1.19.5.2.6}


-- Phaser 7750 Family, 35/35 ppm Color Laser Printer
-- 7750B is the base configuration (no network, 128MB)
-- 7750DN: built-in 10/100 Ethernet, 256MB, Auto Duplex & Hard Drive, Ph
-- 7750GX: 7750DN + Lower Tray, 512MB and 128SDRAM
-- 7750DXF: 7750GX + Hi Cap feeder + Finisher

xcmPidPhaser7750 OBJECT-IDENTITY
    STATUS      current
    DESCRIPTION
        "Xerox Phaser 7750 Laser Printer model identifier
                 (not a complete product identifier)."
    ::= { xcmPidPhaser7yyyFamily 3 }
        -- ::= {1.3.6.1.4.1.253.8.62.1.19.5.3}
            -- => SAP PID string = "C53"

xcmPidPhaser7750B OBJECT-IDENTITY
    STATUS      current
    DESCRIPTION
        "Xerox Phaser 7750B Laser Printer launch configuration model,
                  version, and complete product identifier."
    ::= { xcmPidPhaser7750 1 }
        -- ::= {1.3.6.1.4.1.253.8.62.1.19.5.3.1}

xcmPidPhaser7750DN OBJECT-IDENTITY
    STATUS      current
    DESCRIPTION
        "Xerox Phaser 7750DN Laser Printer launch configuration model,
                  version, and complete product identifier."
    ::= { xcmPidPhaser7750 2 }
        -- ::= {1.3.6.1.4.1.253.8.62.1.19.5.3.2}

xcmPidPhaser7750GX OBJECT-IDENTITY
    STATUS      current
    DESCRIPTION
        "Xerox Phaser 7750GX Laser Printer launch configuration model,
                  version, and complete product identifier."
    ::= { xcmPidPhaser7750 3 }
        -- ::= {1.3.6.1.4.1.253.8.62.1.19.5.3.3}

xcmPidPhaser7750DXF OBJECT-IDENTITY
    STATUS      current
    DESCRIPTION
        "Xerox Phaser 7750DXF Laser Printer launch configuration model,
                  version, and complete product identifier."
    ::= { xcmPidPhaser7750 4 }
        -- ::= {1.3.6.1.4.1.253.8.62.1.19.5.3.4}

-- Phaser 7760 Family, 35/35 ppm Color Laser Printer
-- 7760B is the base configuration (no network, 128MB)


-- 7760DN: built-in 10/100 Ethernet, 256MB, Auto Duplex & Hard Drive, Ph
-- 7760GX: 7760DN + Lower Tray, 512MB and 128SDRAM
-- 7760DXF: 7760GX + Hi Cap feeder

xcmPidPhaser7760 OBJECT-IDENTITY
    STATUS      current
    DESCRIPTION
        "Xerox Phaser 7760 Laser Printer model identifier
                 (not a complete product identifier)."
    ::= { xcmPidPhaser7yyyFamily 4 }
        -- ::= {1.3.6.1.4.1.253.8.62.1.19.5.4}
            -- => SAP PID string = "C54"
            -- => USB PID string = 15736 = 0x3D78

xcmPidPhaser7760B OBJECT-IDENTITY
    STATUS      current
    DESCRIPTION
        "Xerox Phaser 7760B Laser Printer launch configuration model,
                  version, and complete product identifier."
    ::= { xcmPidPhaser7760 1 }
        -- ::= {1.3.6.1.4.1.253.8.62.1.19.5.4.1}

xcmPidPhaser7760DN OBJECT-IDENTITY
    STATUS      current
    DESCRIPTION
        "Xerox Phaser 7760DN Laser Printer launch configuration model,
                  version, and complete product identifier."
    ::= { xcmPidPhaser7760 2 }
        -- ::= {1.3.6.1.4.1.253.8.62.1.19.5.4.2}

xcmPidPhaser7760GX OBJECT-IDENTITY
    STATUS      current
    DESCRIPTION
        "Xerox Phaser 7760GX Laser Printer launch configuration model,
                  version, and complete product identifier."
    ::= { xcmPidPhaser7760 3 }
        -- ::= {1.3.6.1.4.1.253.8.62.1.19.5.4.3}

xcmPidPhaser7760DX OBJECT-IDENTITY
    STATUS      current
    DESCRIPTION
        "Xerox Phaser 7760DX Laser Printer launch configuration model,
                  version, and complete product identifier."
    ::= { xcmPidPhaser7760 4 }
        -- ::= {1.3.6.1.4.1.253.8.62.1.19.5.4.4}

--
--


--
-- Phaser 7800
-- 7800N:   Base + 512MB + built-in 10/100 Ethernet + Hard Drive
-- 7800DN:  7800N + Duplexer
-- 7800GX:  7800DN + 2 Universal Trays
-- 7800DX:  7800DN + 1 Universal Tray + 2 High-Capacity Trays

xcmPidPhaser7800 OBJECT-IDENTITY
    STATUS      current
    DESCRIPTION
        "Xerox Phaser 7800 Laser Printer model identifier
                 (not a complete product identifier)."
    ::= { xcmPidPhaser7yyyFamily 6 }
        -- ::= {1.3.6.1.4.1.253.8.62.1.19.5.6}
            -- => SAP PID string = "C56"
            -- => USB PID string = 15738 = 0x3D7A

xcmPidPhaser7800NC1 OBJECT-IDENTITY
    STATUS      current
    DESCRIPTION
        "Xerox Phaser 7800N Laser Printer
           model and configuration identifier
           (not a complete product identifier)."
    ::= { xcmPidPhaser7800 1 }
        -- ::= {1.3.6.1.4.1.253.8.62.1.19.5.6.1}


--
-- PNP PID Generation PLEASE NOTE:
--   The following assumes the IEEE 1284 Device ID contains the
--   following attributes:
--        MFG:Xerox MDL:Phaser 7800N
--   The following PNP ID was generated using these
--   parameters (manufacturer and model):
--     -mf "Xerox" -mo "Phaser 7800N"
--   The generated PNP PID is only valid for those parameters
            -- => PNP ID XeroxPhaser_7800N47A5

xcmPidPhaser7800NC1V1 OBJECT-IDENTITY
    STATUS      current
    DESCRIPTION
        "Xerox Phaser 7800N Laser Printer
            launch model, configuration, version 1.
            A complete product identifier."
    ::= { xcmPidPhaser7800NC1 1 }
        -- ::= {1.3.6.1.4.1.253.8.62.1.19.5.6.1.1}

xcmPidPhaser7800DNC1 OBJECT-IDENTITY
    STATUS      current
    DESCRIPTION
        "Xerox Phaser 7800DN Laser Printer
           model and configuration identifier
           (not a complete product identifier)."
    ::= { xcmPidPhaser7800 2 }
        -- ::= {1.3.6.1.4.1.253.8.62.1.19.5.6.2}
--
-- PNP PID Generation PLEASE NOTE:
--   The following assumes the IEEE 1284 Device ID contains the
--   following attributes:
--       MFG:Xerox MDL:Phaser 7800DN
--   The following PNP ID was generated using these
--   parameters (manufacturer and model):
--     -mf "Xerox" -mo "Phaser 7800DN"
--   The generated PNP PID is only valid for those parameters
            -- => PNP ID XeroxPhaser_7800DNEF01

xcmPidPhaser7800DNC1V1 OBJECT-IDENTITY
    STATUS      current
    DESCRIPTION
        "Xerox Phaser 7800DN Laser Printer
            launch model, configuration, version 1.
            A complete product identifier."
    ::= { xcmPidPhaser7800DNC1 1 }
        -- ::= {1.3.6.1.4.1.253.8.62.1.19.5.6.2.1}

xcmPidPhaser7800GXC1 OBJECT-IDENTITY
    STATUS      current
    DESCRIPTION
        "Xerox Phaser 7800GX Laser Printer
           model and configuration identifier
           (not a complete product identifier)."


    ::= { xcmPidPhaser7800 3 }
        -- ::= {1.3.6.1.4.1.253.8.62.1.19.5.6.3}
--
-- PNP PID Generation PLEASE NOTE:
--   The following assumes the IEEE 1284 Device ID contains the
--   following attributes:
--    MFG:Xerox MDL:Phaser 7800GX
--   The following PNP ID was generated using these
--   parameters (manufacturer and model):
--     -mf "Xerox" -mo "Phaser 7800GX"
--   The generated PNP PID is only valid for those parameters
            -- => PNP ID      XeroxPhaser_7800GXD180

xcmPidPhaser7800GXC1V1 OBJECT-IDENTITY
    STATUS      current
    DESCRIPTION
        "Xerox Phaser 7800GX Laser Printer
            launch model, configuration, version 1.
            A complete product identifier."
    ::= { xcmPidPhaser7800GXC1 1 }
        -- ::= {1.3.6.1.4.1.253.8.62.1.19.5.6.3.1}

xcmPidPhaser7800DXC1 OBJECT-IDENTITY
    STATUS      current
    DESCRIPTION
        "Xerox Phaser 7800DX Laser Printer
           model and configuration identifier
           (not a complete product identifier)."
    ::= { xcmPidPhaser7800 4 }
        -- ::= {1.3.6.1.4.1.253.8.62.1.19.5.6.4}
--
-- PNP PID Generation PLEASE NOTE:
--   The following assumes the IEEE 1284 Device ID contains the
--   following attributes:
--    MFG:Xerox MDL:Phaser 7800DX
--   The following PNP ID was generated using these
--   parameters (manufacturer and model):
--     -mf "Xerox" -mo "Phaser 7800DX"
--   The generated PNP PID is only valid for those parameters
            -- => PNP ID XeroxPhaser_7800DX2180

xcmPidPhaser7800DXC1V1 OBJECT-IDENTITY
    STATUS      current
    DESCRIPTION
        "Xerox Phaser 7800DX Laser Printer
            launch model, configuration, version 1.
            A complete product identifier."
    ::= { xcmPidPhaser7800DXC1 1 }
        -- ::= {1.3.6.1.4.1.253.8.62.1.19.5.6.4.1}



xcmPidPhaser7100 OBJECT-IDENTITY
    STATUS      current
    DESCRIPTION
        "Xerox Phaser 7100 Printer model identifier
                 (not a complete product identifier)."
    ::= { xcmPidPhaser7yyyFamily 7 }
        -- ::= {1.3.6.1.4.1.253.8.62.1.19.5.7}
            -- => SAP PID string = "C57"
            -- => USB PID string = 15739 = 0x3D7B
            -- => PnP-X WiFi ID = VEN_0109&DEV_3D7B
            -- => Compatible ID = XR_PS_Office_Color
--
-- PNP PID Generation PLEASE NOTE:
--   The following assumes the IEEE 1284 Device ID contains the
--   following attributes:
--        MFG:Xerox MDL:Phaser 7100N
--   The following PNP ID was generated using these
--   parameters (manufacturer and model):
--     -mf "Xerox" -mo "Phaser 7100N"
--   The generated PNP PID is only valid for those parameters
            -- => PNP ID  XeroxPhaser_7100ND9A6

xcmPidPhaser7100NC1 OBJECT-IDENTITY
    STATUS      current
    DESCRIPTION
        "Xerox Phaser 7100N Printer
           model and configuration identifier
           (not a complete product identifier)."
    ::= { xcmPidPhaser7100 1 }
        -- ::= {1.3.6.1.4.1.253.8.62.1.19.5.7.1}

xcmPidPhaser7100NC1V1 OBJECT-IDENTITY
    STATUS      current
    DESCRIPTION
        "Xerox Phaser 70xxN Printer
            launch model, configuration, version 1.
            A complete product identifier."
    ::= { xcmPidPhaser7100NC1 1 }
        -- ::= {1.3.6.1.4.1.253.8.62.1.19.5.7.1.1}

xcmPidPhaser7100DNC1 OBJECT-IDENTITY
    STATUS      current
    DESCRIPTION
        "Xerox Phaser 70xxDN Printer
           model and configuration identifier
           (not a complete product identifier)."
    ::= { xcmPidPhaser7100 2 }
        -- ::= {1.3.6.1.4.1.253.8.62.1.19.5.7.2}
--
-- PNP PID Generation PLEASE NOTE:
--   The following assumes the IEEE 1284 Device ID contains the
--   following attributes:
--        MFG:Xerox MDL:Phaser 7100DN


--   The following PNP ID was generated using these
--   parameters (manufacturer and model):
--     -mf "Xerox" -mo "Phaser 7100DN"
--   The generated PNP PID is only valid for those parameters
            -- => PNP ID  XeroxPhaser_7100DNEEDF

xcmPidPhaser7100DNC1V1 OBJECT-IDENTITY
    STATUS      current
    DESCRIPTION
        "Xerox Phaser 7100DN Printer
            launch model, configuration, version 1.
            A complete product identifier."
    ::= { xcmPidPhaser7100DNC1 1 }
        -- ::= {1.3.6.1.4.1.253.8.62.1.19.5.7.2.1}

--     Xerox Phaser 8yyy = Color, OSI Family

xcmPidPhaser8yyyFamily OBJECT-IDENTITY
    STATUS      current
    DESCRIPTION
        "Xerox Phaser 8yyy Family product line identifier
                 (not a complete product identifier)."
    ::= { xcmPidXeroxPhaserPrinters 6 }
        -- ::= {1.3.6.1.4.1.253.8.62.1.19.6}

-- Phaser 8400 Family, 16/20 ppm Solid Ink Color printer
-- 8400B is the Base configuration (no network, 64MB)
-- 8840BD: 8400B + Pipelining and Auto Duplex
-- 8400N:  8400B + built-in 10/100 Ethernet
-- 8400DP: 8400N + 64MB (128 total), pipelining and Auto Duplex
-- 8400DX: 8400DP + Hard disk, High cap feeder and Job collation.

xcmPidPhaser8400 OBJECT-IDENTITY
    STATUS      current
    DESCRIPTION
        "Xerox Phaser 8400 Laser Printer model identifier
                 (not a complete product identifier)."
    ::= { xcmPidPhaser8yyyFamily 1 }
        -- ::= {1.3.6.1.4.1.253.8.62.1.19.6.1}
            -- => SAP PID string = "C61"
            -- => USB PID string = 65521 = 0xFEC5
            -- Note that the USB PID of 14017 is not used.

xcmPidPhaser8400B OBJECT-IDENTITY
    STATUS      current
    DESCRIPTION
        "Xerox Phaser 8400B Laser Printer launch configuration model,
                  and complete product identifier. The 8400B is not
                  network connected so this SNMP id is not used."
    ::= { xcmPidPhaser8400 1 }


        -- ::= {1.3.6.1.4.1.253.8.62.1.19.6.1.1}

xcmPidPhaser8400N OBJECT-IDENTITY
    STATUS      current
    DESCRIPTION
        "Xerox Phaser 8400N Laser Printer launch configuration model,
                  and complete product identifier."
    ::= { xcmPidPhaser8400 2 }
        -- ::= {1.3.6.1.4.1.253.8.62.1.19.6.1.2}

xcmPidPhaser8400DP OBJECT-IDENTITY
    STATUS      current
    DESCRIPTION
        "Xerox Phaser 8400DP Laser Printer launch configuration model,
                  and complete product identifier."
    ::= { xcmPidPhaser8400 3 }
        -- ::= {1.3.6.1.4.1.253.8.62.1.19.6.1.3}

xcmPidPhaser8400DX OBJECT-IDENTITY
    STATUS      current
    DESCRIPTION
        "Xerox Phaser 8400DX Laser Printer launch configuration model,
                  and complete product identifier."
    ::= { xcmPidPhaser8400 4 }
        -- ::= {1.3.6.1.4.1.253.8.62.1.19.6.1.4}

xcmPidPhaser8400BD OBJECT-IDENTITY
    STATUS      current
    DESCRIPTION
        "Xerox Phaser 8400BD Laser Printer launch configuration model,
                  This is not network connected so the SNMP id is not
                  used."
    ::= { xcmPidPhaser8400 5 }
        -- ::= {1.3.6.1.4.1.253.8.62.1.19.6.1.5}

--
--

-- Phaser 8560 Family
-- Phaser 8560, Copy/Print/Scan/Fax, 30/30ppm

xcmPidPhaser8560 OBJECT-IDENTITY
    STATUS      current
    DESCRIPTION
        "Xerox Phaser 8560 launch configuration
                 model identifier (not a complete product identifier)."
    ::= { xcmPidPhaser8yyyFamily 7 }
        -- ::= {1.3.6.1.4.1.253.8.62.1.19.6.7}
            -- => SAP PID string = "C67"
            -- => USB PID string = 15775 = 0x3D9F

xcmPidPhaser8560v1 OBJECT-IDENTITY
    STATUS      current
    DESCRIPTION
        "Xerox Phaser 8560 Copy/Print/Scan/Fax, 30/30ppm
         complete product identifier."
    ::= { xcmPidPhaser8560 1 }
        -- ::= {1.3.6.1.4.1.253.8.62.1.19.6.7.1}

--
--

-- Phaser 8560 Printer Family
-- 8560N is the Base configuration for the 8560


--        (30ppm, Built-in 10/100 Ethernet, 256MB)
-- 8560DN: 8560N + Auto Duplex
-- 8560DT: 8560DN + 1 additional paper tray
-- 8560DX: 8560DT + +256MB +
--         1 additional paper tray + Hard disk
-- 8560PP: Page Pack configuration of 8560

xcmPidPhaser8560p OBJECT-IDENTITY
    STATUS      current
    DESCRIPTION
        "Xerox Phaser 8560 Color Printer model identifier
                 (not a complete product identifier)."
    ::= { xcmPidPhaser8yyyFamily 9 }
        -- ::= {1.3.6.1.4.1.253.8.62.1.19.6.9}
            -- => SAP PID string = "C69"
            -- => USB PID string = 15777 = 0x3DA1

xcmPidPhaser8560N OBJECT-IDENTITY
    STATUS      current
    DESCRIPTION
        "Xerox Phaser 8560N Color Printer launch configuration
              model, and complete product identifier."
    ::= { xcmPidPhaser8560p 1 }
        -- ::= {1.3.6.1.4.1.253.8.62.1.19.6.9.1}

xcmPidPhaser8560DN OBJECT-IDENTITY
    STATUS      current
    DESCRIPTION
        "Xerox Phaser 8560DN Color Printer launch configuration
              model, and complete product identifier."
    ::= { xcmPidPhaser8560p 2 }
        -- ::= {1.3.6.1.4.1.253.8.62.1.19.6.9.2}

xcmPidPhaser8560DT OBJECT-IDENTITY
    STATUS      current
    DESCRIPTION
        "Xerox Phaser 8560DT Color Printer launch configuration
              model, and complete product identifier."
    ::= { xcmPidPhaser8560p 3 }
        -- ::= {1.3.6.1.4.1.253.8.62.1.19.6.9.3}

xcmPidPhaser8560DX OBJECT-IDENTITY
    STATUS      current
    DESCRIPTION
        "Xerox Phaser 8560DX Color Printer launch configuration
              model, and complete product identifier."
    ::= { xcmPidPhaser8560p 4 }
        -- ::= {1.3.6.1.4.1.253.8.62.1.19.6.9.4}

xcmPidPhaser8560PP OBJECT-IDENTITY
    STATUS      current
    DESCRIPTION
        "Xerox Phaser 8560PP Printer launch configuration
              model, and complete product identifier."


    ::= { xcmPidPhaser8560p 6 }
        -- ::= {1.3.6.1.4.1.253.8.62.1.19.6.9.5}

-- Phaser 8860 Printer
-- 8860 is the base configuration

xcmPidPhaser8860 OBJECT-IDENTITY
    STATUS      current
    DESCRIPTION
        "Xerox Phaser 8860 Color Printer model identifier
                 (not a complete product identifier)."
    ::= { xcmPidPhaser8yyyFamily 17 }
        -- ::= {1.3.6.1.4.1.253.8.62.1.19.6.17}
            -- => SAP PID string = "C6A"
            -- => USB PID string = 15778 = 0x3DA2

xcmPidPhaser8860v1 OBJECT-IDENTITY
    STATUS      current
    DESCRIPTION
        "Xerox Phaser 8860N Color Printer launch configuration
              model, and complete product identifier."
    ::= { xcmPidPhaser8860 1 }
        -- ::= {1.3.6.1.4.1.253.8.62.1.19.6.17.1}

-- Phaser 8860 Multi-Function Printer (print/copy/scan/fax)
-- 8860MFP is the base configuration

xcmPidPhaser8860MFP OBJECT-IDENTITY
    STATUS      current
    DESCRIPTION
        "Xerox Phaser 8860MFP model identifier
                 (not a complete product identifier)."
    ::= { xcmPidPhaser8yyyFamily 18 }
        -- ::= {1.3.6.1.4.1.253.8.62.1.19.6.18}
            -- => SAP PID string = "C6B"
            -- => USB PID string = 15779 = 0x3DA3

xcmPidPhaser8860MFPv1 OBJECT-IDENTITY
    STATUS      current
    DESCRIPTION
        "Xerox Phaser 8860MFP MFD launch configuration
              model, and complete product identifier."
    ::= { xcmPidPhaser8860MFP 1 }
        -- ::= {1.3.6.1.4.1.253.8.62.1.19.6.18.1}

--
--


xcmPidP3200MFP OBJECT-IDENTITY
    STATUS      current
    DESCRIPTION
        "Xerox Phaser 3200 MFP system identifier
                 (not a complete product identifier)."
    ::= { xcmPidPhaser8yyyFamily 19 }
        -- ::= {1.3.6.1.4.1.253.8.62.1.19.6.19}
            -- => SAP PID string = "C6C"
            -- => USB PID string = 15780 = 0x3DA4

xcmPidP3200MFPv1 OBJECT-IDENTITY
    STATUS      current
    DESCRIPTION
        "Xerox Phaser 3200 MFP system identifier
         launch configuration version #1, and
         complete product identifier."
    ::= { xcmPidP3200MFP 1 }
        -- ::= {1.3.6.1.4.1.253.8.62.1.19.6.19.1}

------------------------------------------------------------------
--     Xerox Phaser 9yyy = Phaser Print Servers
------------------------------------------------------------------

xcmPidPhaser9yyyFamily OBJECT-IDENTITY
    STATUS      current
    DESCRIPTION
        "Xerox Phaser 9yyy Family product line identifier
                 (not a complete product identifier)."
    ::= { xcmPidXeroxPhaserPrinters 9 }
        -- ::= {1.3.6.1.4.1.253.8.62.1.19.9}

--
--

----------------------------------------------------------------
-- MidRange Color Printers
----------------------------------------------------------------

xcmPidMidRangeColorPrinters OBJECT-IDENTITY
    STATUS      current
    DESCRIPTION
        "MidRange Color Printers product line identifier
                 (not a complete product identifier)."
    ::= { xcmPidProductIdentifiers 4 }
        -- ::= {1.3.6.1.4.1.253.8.62.1.4}

--
--

-- MidRange Color Printer Document Centre ColorSeries 50

xcmPidDCColorSeries50 OBJECT-IDENTITY
    STATUS      current
    DESCRIPTION
        "Document Centre ColorSeries 50 mid-range color printer product
                 type identifier (not a complete product identifier)."
    ::= { xcmPidMidRangeColorPrinters 2 }
        -- ::= {1.3.6.1.4.1.253.8.62.1.4.2}

xcmPidDCColorSeries50M1 OBJECT-IDENTITY
    STATUS      current
    DESCRIPTION
        "Document Centre ColorSeries 50 mid-range color printer
                 launch configuration model identifier
                 (not a complete product identifier)."
    ::= { xcmPidDCColorSeries50 1 }
        -- ::= {1.3.6.1.4.1.253.8.62.1.4.2.1}
            -- => SAP PID string = "421"

xcmPidDCColorSeries50M1V1 OBJECT-IDENTITY
    STATUS      current
    DESCRIPTION
        "Document Centre ColorSeries 50 mid-range color printer
                 launch configuration version,
                 and complete product identifier."
    ::= { xcmPidDCColorSeries50M1 1 }
        -- ::= {1.3.6.1.4.1.253.8.62.1.4.2.1.1}

--
--

----------------------------------------------------------------
-- DocuColor 2000 Series


----------------------------------------------------------------

xcmPidDocuColor2000Series OBJECT-IDENTITY
    STATUS      current
    DESCRIPTION
        "DocuColor 2000 Family product line identifier
                 (not a complete product identifier)."
    ::= { xcmPidProductIdentifiers 17 }
        -- ::= {1.3.6.1.4.1.253.8.62.1.17}

--
--

--
--

--
--

--
--

----------------------------------------------------------------
-- DocuColor 3000 Series
----------------------------------------------------------------

xcmPidDocuColor3000series OBJECT-IDENTITY
    STATUS      current
    DESCRIPTION
        "Xerox DocuColor 3000 Digital Press product type
 identifier (not a complete product identifier)."
    ::= { xcmPidDocuColor2000Series 7 }
        -- ::= {1.3.6.1.4.1.253.8.62.1.17.7}

--
--


--
--

xcmPidDocuColor240SPLASH OBJECT-IDENTITY
    STATUS      current
    DESCRIPTION
        "Xerox DocuColor 240 with the Fiery Controller
         and DFE launch configuration model identifier
         (not a complete product identifier)."
    ::= { xcmPidDocuColor3000series 8 }
        -- ::= {1.3.6.1.4.1.253.8.62.1.17.7.8}
            -- => SAP PID string = "A78"
            -- => USB PID string = 13220 = 0x33A4

xcmPidDocuColor240SPLASHv1 OBJECT-IDENTITY
    STATUS      current
    DESCRIPTION
        "Xerox DocuColor 240 with the Fiery Controller
         and DFE configuration model and version, and complete
         product identifier."
    ::= { xcmPidDocuColor240SPLASH 1 }
        -- ::= {1.3.6.1.4.1.253.8.62.1.17.7.8.1}

--
--

xcmPidDocuColor250SPLASH OBJECT-IDENTITY
    STATUS      current
    DESCRIPTION
        "Xerox DocuColor 250 with the Fiery Controller
         and DFE launch configuration model identifier
         (not a complete product identifier)."
    ::= { xcmPidDocuColor3000series 9 }
        -- ::= {1.3.6.1.4.1.253.8.62.1.17.7.9}
            -- => SAP PID string = "A79"
            -- => USB PID string = 13221 = 0x33A5

xcmPidDocuColor250SPLASHv1 OBJECT-IDENTITY
    STATUS      current
    DESCRIPTION
        "Xerox DocuColor 250 with the Fiery Controller
         and DFE configuration model and version, and complete
         product identifier."
    ::= { xcmPidDocuColor250SPLASH 1 }
        -- ::= {1.3.6.1.4.1.253.8.62.1.17.7.9.1}

--


--

xcmPidDocuColor242EFI OBJECT-IDENTITY
    STATUS      current
    DESCRIPTION
        "Xerox DocuColor 242 with the EFI Fiery Controller
         launch configuration model identifier
         (not a complete product identifier)."
    ::= { xcmPidDocuColor3000series 17 }
        -- ::= {1.3.6.1.4.1.253.8.62.1.17.7.17}
            -- => SAP PID string = "A7A"
            -- => USB PID string = 13222 = 0x33A6

xcmPidDocuColor242EFIv1 OBJECT-IDENTITY
    STATUS      current
    DESCRIPTION
        "Xerox DocuColor 242 with the EFI Fiery Controller
         configuration model and version, and complete
         product identifier."
    ::= { xcmPidDocuColor242EFI 1 }
        -- ::= {1.3.6.1.4.1.253.8.62.1.17.7.17.1}
--
--

xcmPidDocuColor242 OBJECT-IDENTITY
    STATUS      current
    DESCRIPTION
        "Xerox DocuColor 242 with the Fiery Color Server
         launch configuration model identifier
         (not a complete product identifier)."
    ::= { xcmPidDocuColor3000series 18 }
        -- ::= {1.3.6.1.4.1.253.8.62.1.17.7.18}
            -- => SAP PID string = "A7B"
            -- => USB PID string = 13223 = 0x33A7

xcmPidDocuColor242v1 OBJECT-IDENTITY
    STATUS      current
    DESCRIPTION
        "Xerox DocuColor 242 with the Fiery Color Server
         configuration model and version, and complete
         product identifier."
    ::= { xcmPidDocuColor242 1 }
        -- ::= {1.3.6.1.4.1.253.8.62.1.17.7.18.1}

--
--

xcmPidDocuColor252EFI OBJECT-IDENTITY


    STATUS      current
    DESCRIPTION
        "Xerox DocuColor 252 with the EFI Fiery Controller
         launch configuration model identifier
         (not a complete product identifier)."
    ::= { xcmPidDocuColor3000series 19 }
        -- ::= {1.3.6.1.4.1.253.8.62.1.17.7.19}
            -- => SAP PID string = "A7C"
            -- => USB PID string = 13224 = 0x33A8

xcmPidDocuColor252EFIv1 OBJECT-IDENTITY
    STATUS      current
    DESCRIPTION
        "Xerox DocuColor 252 with the EFI Fiery Controller
         configuration model and version, and complete
         product identifier."
    ::= { xcmPidDocuColor252EFI 1 }
        -- ::= {1.3.6.1.4.1.253.8.62.1.17.7.19.1}
--
--

xcmPidDocuColor252 OBJECT-IDENTITY
    STATUS      current
    DESCRIPTION
        "Xerox DocuColor 252 with the Fiery Color Server
         launch configuration model identifier
         (not a complete product identifier)."
    ::= { xcmPidDocuColor3000series 20 }
        -- ::= {1.3.6.1.4.1.253.8.62.1.17.7.20}
            -- => SAP PID string = "A7D"
            -- => USB PID string = 13225 = 0x33A9

xcmPidDocuColor252v1 OBJECT-IDENTITY
    STATUS      current
    DESCRIPTION
        "Xerox DocuColor 252 with the Fiery Color Server
         configuration model and version, and complete
         product identifier."
    ::= { xcmPidDocuColor252 1 }
        -- ::= {1.3.6.1.4.1.253.8.62.1.17.7.20.1}

--
--

xcmPidDocuColor260EFI OBJECT-IDENTITY
    STATUS      current
    DESCRIPTION
        "Xerox DocuColor 260 with the EFI Fiery Controller
         launch configuration model identifier
         (not a complete product identifier)."


    ::= { xcmPidDocuColor3000series 21 }
        -- ::= {1.3.6.1.4.1.253.8.62.1.17.7.21}
            -- => SAP PID string = "A7E"
            -- => USB PID string = 13226 = 0x33AA

xcmPidDocuColor260EFIv1 OBJECT-IDENTITY
    STATUS      current
    DESCRIPTION
        "Xerox DocuColor 260 with the EFI Fiery Controller
         configuration model and version, and complete
         product identifier."
    ::= { xcmPidDocuColor260EFI 1 }
        -- ::= {1.3.6.1.4.1.253.8.62.1.17.7.21.1}
--
--

xcmPidDocuColor260 OBJECT-IDENTITY
    STATUS      current
    DESCRIPTION
        "Xerox DocuColor 260 with the Fiery Color Server
         launch configuration model identifier
         (not a complete product identifier)."
    ::= { xcmPidDocuColor3000series 22 }
        -- ::= {1.3.6.1.4.1.253.8.62.1.17.7.22}
            -- => SAP PID string = "A7F"
            -- => USB PID string = 13227 = 0x33AB

xcmPidDocuColor260v1 OBJECT-IDENTITY
    STATUS      current
    DESCRIPTION
        "Xerox DocuColor 260 with the Fiery Color Server
         configuration model and version, and complete
         product identifier."
    ::= { xcmPidDocuColor260 1 }
        -- ::= {1.3.6.1.4.1.253.8.62.1.17.7.22.1}

--

xcmPidDocuColor242C OBJECT-IDENTITY
    STATUS      current
    DESCRIPTION
        "Xerox DocuColor 242 with the Creo Spire Color Server
         launch configuration model identifier
         (not a complete product identifier)."
    ::= { xcmPidDocuColor3000series 23 }
        -- ::= {1.3.6.1.4.1.253.8.62.1.17.7.23}
            -- => SAP PID string = "A7G"
            -- => USB PID string = 13228 = 0x33AC

xcmPidDocuColor242Cv1 OBJECT-IDENTITY


    STATUS      current
    DESCRIPTION
        "Xerox DocuColor 242 with the Creo Spire Color Server
         configuration model and version, and complete
         product identifier."
    ::= { xcmPidDocuColor242C 1 }
        -- ::= {1.3.6.1.4.1.253.8.62.1.17.7.23.1}

--

xcmPidDocuColor242S OBJECT-IDENTITY
    STATUS      current
    DESCRIPTION
        "Xerox DocuColor 242 Splash
         launch configuration model identifier
         (not a complete product identifier)."
    ::= { xcmPidDocuColor3000series 24 }
        -- ::= {1.3.6.1.4.1.253.8.62.1.17.7.24}
            -- => SAP PID string = "A7H"
            -- => USB PID string = 13229 = 0x33AD

xcmPidDocuColor242Sv1 OBJECT-IDENTITY
    STATUS      current
    DESCRIPTION
        "Xerox DocuColor 242 Splash
         configuration model and version, and complete
         product identifier."
    ::= { xcmPidDocuColor242S 1 }
        -- ::= {1.3.6.1.4.1.253.8.62.1.17.7.24.1}

--

xcmPidDocuColor252C OBJECT-IDENTITY
    STATUS      current
    DESCRIPTION
        "Xerox DocuColor 252 with the Creo Spire Color Server
         launch configuration model identifier
         (not a complete product identifier)."
    ::= { xcmPidDocuColor3000series 25 }
        -- ::= {1.3.6.1.4.1.253.8.62.1.17.7.25}
            -- => SAP PID string = "A7I"
            -- => USB PID string = 13230 = 0x33AE

xcmPidDocuColor252Cv1 OBJECT-IDENTITY
    STATUS      current
    DESCRIPTION
        "Xerox DocuColor 252 with the Creo Spire Color Server
         configuration model and version, and complete
         product identifier."
    ::= { xcmPidDocuColor252C 1 }


        -- ::= {1.3.6.1.4.1.253.8.62.1.17.7.25.1}

--

xcmPidDocuColor252S OBJECT-IDENTITY
    STATUS      current
    DESCRIPTION
        "Xerox DocuColor 252 Splash
         launch configuration model identifier
         (not a complete product identifier)."
    ::= { xcmPidDocuColor3000series 26 }
        -- ::= {1.3.6.1.4.1.253.8.62.1.17.7.26}
            -- => SAP PID string = "A7J"
            -- => USB PID string = 13231 = 0x33AF

xcmPidDocuColor252Sv1 OBJECT-IDENTITY
    STATUS      current
    DESCRIPTION
        "Xerox DocuColor 252 Splash
         configuration model and version, and complete
         product identifier."
    ::= { xcmPidDocuColor252S 1 }
        -- ::= {1.3.6.1.4.1.253.8.62.1.17.7.26.1}

--

xcmPidDocuColor260C OBJECT-IDENTITY
    STATUS      current
    DESCRIPTION
        "Xerox DocuColor 260 with the Creo Spire Color Server
         launch configuration model identifier
         (not a complete product identifier)."
    ::= { xcmPidDocuColor3000series 27 }
        -- ::= {1.3.6.1.4.1.253.8.62.1.17.7.27}
            -- => SAP PID string = "A7K"
            -- => USB PID string = 13232 = 0x33B0

xcmPidDocuColor260Cv1 OBJECT-IDENTITY
    STATUS      current
    DESCRIPTION
        "Xerox DocuColor 260 with the Creo Spire Color Server
         configuration model and version, and complete
         product identifier."
    ::= { xcmPidDocuColor260C 1 }
        -- ::= {1.3.6.1.4.1.253.8.62.1.17.7.27.1}

--


xcmPidDocuColor260S OBJECT-IDENTITY
    STATUS      current
    DESCRIPTION
        "Xerox DocuColor 260 Splash
         launch configuration model identifier
         (not a complete product identifier)."
    ::= { xcmPidDocuColor3000series 28 }
        -- ::= {1.3.6.1.4.1.253.8.62.1.17.7.28}
            -- => SAP PID string = "A7L"
            -- => USB PID string = 13233 = 0x33B1

xcmPidDocuColor260Sv1 OBJECT-IDENTITY
    STATUS      current
    DESCRIPTION
        "Xerox DocuColor 260 Splash
         configuration model and version, and complete
         product identifier."
    ::= { xcmPidDocuColor260S 1 }
        -- ::= {1.3.6.1.4.1.253.8.62.1.17.7.28.1}

--
--

----------------------------------------------------------------
-- DocuPrint NPS (Network Printing Systems) Printers
----------------------------------------------------------------

xcmPidDocuPrintNPS OBJECT-IDENTITY
    STATUS      current
    DESCRIPTION
        "DocuPrint NPS (Network Printing Systems) product line
                 identifier (not a complete product identifier)."
    ::= { xcmPidProductIdentifiers 9 }
        -- ::= {1.3.6.1.4.1.253.8.62.1.9}

-- DocuPrint NPS DP4050 Printer

xcmPidDP4050NPS OBJECT-IDENTITY
    STATUS      current
    DESCRIPTION
        "DocuPrint NPS DP4050 product type identifier
                 (not a complete product identifier)."
    ::= { xcmPidDocuPrintNPS 1 }
        -- ::= {1.3.6.1.4.1.253.8.62.1.9.1}

xcmPidDP4050NPSM1 OBJECT-IDENTITY
    STATUS      current
    DESCRIPTION
        "DocuPrint NPS DP4050 launch configuration model identifier
                 (not a complete product identifier)."
    ::= { xcmPidDP4050NPS 1 }
        -- ::= {1.3.6.1.4.1.253.8.62.1.9.1.1}
            -- => SAP PID string = "911"

xcmPidDP4050NPSM1V1 OBJECT-IDENTITY
    STATUS      current
    DESCRIPTION
        "DocuPrint NPS DP4050 launch configuration version,
                 and complete product identifier."
    ::= { xcmPidDP4050NPSM1 1 }


        -- ::= {1.3.6.1.4.1.253.8.62.1.9.1.1.1}

-- DocuPrint NPS DP4090 Printer

xcmPidDP4090NPS OBJECT-IDENTITY
    STATUS      current
    DESCRIPTION
        "DocuPrint NPS DP4090 product type identifier
                 (not a complete product identifier)."
    ::= { xcmPidDocuPrintNPS 2 }
        -- ::= {1.3.6.1.4.1.253.8.62.1.9.2}

xcmPidDP4090NPSM1 OBJECT-IDENTITY
    STATUS      current
    DESCRIPTION
        "DocuPrint NPS DP4090 launch configuration model identifier
                 (not a complete product identifier)."
    ::= { xcmPidDP4090NPS 1 }
        -- ::= {1.3.6.1.4.1.253.8.62.1.9.2.1}
            -- => SAP PID string = "921"

xcmPidDP4090NPSM1V1 OBJECT-IDENTITY
    STATUS      current
    DESCRIPTION
        "DocuPrint NPS DP4090 launch configuration version,
                 and complete product identifier."
    ::= { xcmPidDP4090NPSM1 1 }
        -- ::= {1.3.6.1.4.1.253.8.62.1.9.2.1.1}

-- DocuPrint NPS DP4850 Printer

xcmPidDP4850NPS OBJECT-IDENTITY
    STATUS      current
    DESCRIPTION
        "DocuPrint NPS DP4850 product type identifier
                 (not a complete product identifier)."
    ::= { xcmPidDocuPrintNPS 3 }
        -- ::= {1.3.6.1.4.1.253.8.62.1.9.3}

xcmPidDP4850NPSM1 OBJECT-IDENTITY
    STATUS      current
    DESCRIPTION
        "DocuPrint NPS DP4850 launch configuration model identifier
                 (not a complete product identifier)."
    ::= { xcmPidDP4850NPS 1 }
        -- ::= {1.3.6.1.4.1.253.8.62.1.9.3.1}
            -- => SAP PID string = "931"

xcmPidDP4850NPSM1V1 OBJECT-IDENTITY
    STATUS      current
    DESCRIPTION
        "DocuPrint NPS DP4850 launch configuration version,


                 and complete product identifier."
    ::= { xcmPidDP4850NPSM1 1 }
        -- ::= {1.3.6.1.4.1.253.8.62.1.9.3.1.1}

-- DocuPrint NPS DP4890 Printer

xcmPidDP4890NPS OBJECT-IDENTITY
    STATUS      current
    DESCRIPTION
        "DocuPrint NPS DP4890 product type identifier
                 (not a complete product identifier)."
    ::= { xcmPidDocuPrintNPS 4 }
        -- ::= {1.3.6.1.4.1.253.8.62.1.9.4}

xcmPidDP4890NPSM1 OBJECT-IDENTITY
    STATUS      current
    DESCRIPTION
        "DocuPrint NPS DP4890 launch configuration model identifier
                 (not a complete product identifier)."
    ::= { xcmPidDP4890NPS 1 }
        -- ::= {1.3.6.1.4.1.253.8.62.1.9.4.1}
            -- => SAP PID string = "941"

xcmPidDP4890NPSM1V1 OBJECT-IDENTITY
    STATUS      current
    DESCRIPTION
        "DocuPrint NPS DP4890 launch configuration version,
                 and complete product identifier."
    ::= { xcmPidDP4890NPSM1 1 }
        -- ::= {1.3.6.1.4.1.253.8.62.1.9.4.1.1}

-- DocuPrint NPS DP4635 Printer

xcmPidDP4635NPS OBJECT-IDENTITY
    STATUS      current
    DESCRIPTION
        "DocuPrint NPS DP4635 product type identifier
                 (not a complete product identifier)."
    ::= { xcmPidDocuPrintNPS 5 }
        -- ::= {1.3.6.1.4.1.253.8.62.1.9.5}

xcmPidDP4635NPSM1 OBJECT-IDENTITY
    STATUS      current
    DESCRIPTION
        "DocuPrint NPS DP4635 launch configuration model identifier
                 (not a complete product identifier)."
    ::= { xcmPidDP4635NPS 1 }
        -- ::= {1.3.6.1.4.1.253.8.62.1.9.5.1}
            -- => SAP PID string = "951"

xcmPidDP4635NPSM1V1 OBJECT-IDENTITY
    STATUS      current


    DESCRIPTION
        "DocuPrint NPS DP4635 launch configuration version,
                 and complete product identifier."
    ::= { xcmPidDP4635NPSM1 1 }
        -- ::= {1.3.6.1.4.1.253.8.62.1.9.5.1.1}

-- DocuPrint NPS DP4635 Micr Printer

xcmPidDP4635NPSMicr OBJECT-IDENTITY
    STATUS      current
    DESCRIPTION
        "DocuPrint NPS DP4635 Micr launch configuration model identifier
                 (not a complete product identifier)."
    ::= { xcmPidDP4635NPS 2 }
        -- ::= {1.3.6.1.4.1.253.8.62.1.9.5.2}
            -- => SAP PID string = "952"

xcmPidDP4635NPSMicrV1 OBJECT-IDENTITY
    STATUS      current
    DESCRIPTION
        "DocuPrint NPS DP4635 Micr launch configuration version,
                 and complete product identifier."
    ::= { xcmPidDP4635NPSMicr 1 }
        -- ::= {1.3.6.1.4.1.253.8.62.1.9.5.2.1}

-- DocuPrint NPS DP180 Printer

xcmPidDP180NPS OBJECT-IDENTITY
    STATUS      current
    DESCRIPTION
        "DocuPrint NPS DP180 product type identifier
                 (not a complete product identifier)."
    ::= { xcmPidDocuPrintNPS 6 }
        -- ::= {1.3.6.1.4.1.253.8.62.1.9.6}

xcmPidDP180NPSM1 OBJECT-IDENTITY
    STATUS      current
    DESCRIPTION
        "DocuPrint NPS DP180 launch configuration model identifier
                 (not a complete product identifier)."
    ::= { xcmPidDP180NPS 1 }
        -- ::= {1.3.6.1.4.1.253.8.62.1.9.6.1}
            -- => SAP PID string = "961"

xcmPidDP180NPSM1V1 OBJECT-IDENTITY
    STATUS      current
    DESCRIPTION
        "DocuPrint NPS DP180 launch configuration version,
                 and complete product identifier."
    ::= { xcmPidDP180NPSM1 1 }
        -- ::= {1.3.6.1.4.1.253.8.62.1.9.6.1.1}

-- DocuPrint NPS DP180 Micr Printer


xcmPidDP180NPSMicr OBJECT-IDENTITY
    STATUS      current
    DESCRIPTION
        "DocuPrint NPS DP180 Micr launch configuration model identifier
                 (not a complete product identifier)."
    ::= { xcmPidDP180NPS 2 }
        -- ::= {1.3.6.1.4.1.253.8.62.1.9.6.2}
            -- => SAP PID string = "962"

xcmPidDP180NPSMicrV1 OBJECT-IDENTITY
    STATUS      current
    DESCRIPTION
        "DocuPrint NPS DP180 Micr launch configuration version,
                 and complete product identifier."
    ::= { xcmPidDP180NPSMicr 1 }
        -- ::= {1.3.6.1.4.1.253.8.62.1.9.6.2.1}

-- DocuPrint NPS DP96 Printer

xcmPidDP96NPS OBJECT-IDENTITY
    STATUS      current
    DESCRIPTION
        "DocuPrint NPS DP96 product type identifier
                 (not a complete product identifier)."
    ::= { xcmPidDocuPrintNPS 7 }
        -- ::= {1.3.6.1.4.1.253.8.62.1.9.7}

xcmPidDP96NPSM1 OBJECT-IDENTITY
    STATUS      current
    DESCRIPTION
        "DocuPrint NPS DP96 launch configuration model identifier
                 (not a complete product identifier)."
    ::= { xcmPidDP96NPS 1 }
        -- ::= {1.3.6.1.4.1.253.8.62.1.9.7.1}
            -- => SAP PID string = "971"

xcmPidDP96NPSM1V1 OBJECT-IDENTITY
    STATUS      current
    DESCRIPTION
        "DocuPrint NPS DP96 launch configuration version,
                 and complete product identifier."
    ::= { xcmPidDP96NPSM1 1 }
        -- ::= {1.3.6.1.4.1.253.8.62.1.9.7.1.1}

-- DocuPrint NPS DP96 Micr Printer

xcmPidDP96NPSMicr OBJECT-IDENTITY
    STATUS      current
    DESCRIPTION
        "DocuPrint NPS DP96 Micr launch configuration model identifier
                 (not a complete product identifier)."
    ::= { xcmPidDP96NPS 2 }


        -- ::= {1.3.6.1.4.1.253.8.62.1.9.7.2}
            -- => SAP PID string = "972"

xcmPidDP96NPSMicrV1 OBJECT-IDENTITY
    STATUS      current
    DESCRIPTION
        "DocuPrint NPS DP96 Micr launch configuration version,
                 and complete product identifier."
    ::= { xcmPidDP96NPSMicr 1 }
        -- ::= {1.3.6.1.4.1.253.8.62.1.9.7.2.1}

-- DocuPrint NPS DP92c Printer

xcmPidDP92cNPS OBJECT-IDENTITY
    STATUS      current
    DESCRIPTION
        "DocuPrint NPS DP92c product type identifier
                 (not a complete product identifier)."
    ::= { xcmPidDocuPrintNPS 8 }
        -- ::= {1.3.6.1.4.1.253.8.62.1.9.8}

xcmPidDP92cNPSM1 OBJECT-IDENTITY
    STATUS      current
    DESCRIPTION
        "DocuPrint NPS DP92c launch configuration model identifier
                 (not a complete product identifier)."
    ::= { xcmPidDP92cNPS 1 }
        -- ::= {1.3.6.1.4.1.253.8.62.1.9.8.1}
            -- => SAP PID string = "981"

xcmPidDP92cNPSM1V1 OBJECT-IDENTITY
    STATUS      current
    DESCRIPTION
        "DocuPrint NPS DP92c launch configuration version,
                 and complete product identifier."
    ::= { xcmPidDP92cNPSM1 1 }
        -- ::= {1.3.6.1.4.1.253.8.62.1.9.8.1.1}

-- DocuPrint NPS DP155 Printer

xcmPidDP155NPS OBJECT-IDENTITY
    STATUS      current
    DESCRIPTION
        "DocuPrint NPS DP155 product type identifier
                 (not a complete product identifier)."
    ::= { xcmPidDocuPrintNPS 9 }
        -- ::= {1.3.6.1.4.1.253.8.62.1.9.9}

xcmPidDP155NPSM1 OBJECT-IDENTITY
    STATUS      current
    DESCRIPTION
        "DocuPrint NPS DP155 launch configuration model identifier
                 (not a complete product identifier)."
    ::= { xcmPidDP155NPS 1 }


        -- ::= {1.3.6.1.4.1.253.8.62.1.9.9.1}
            -- => SAP PID string = "991"

xcmPidDP155NPSM1V1 OBJECT-IDENTITY
    STATUS      current
    DESCRIPTION
        "DocuPrint NPS DP155 launch configuration version,
                 and complete product identifier."
    ::= { xcmPidDP155NPSM1 1 }
        -- ::= {1.3.6.1.4.1.253.8.62.1.9.9.1.1}

-- DocuPrint NPS DP155 Micr Printer

xcmPidDP155NPSMicr OBJECT-IDENTITY
    STATUS      current
    DESCRIPTION
        "DocuPrint NPS DP155 Micr launch configuration model identifier
                 (not a complete product identifier)."
    ::= { xcmPidDP155NPS 2 }
        -- ::= {1.3.6.1.4.1.253.8.62.1.9.9.2}
            -- => SAP PID string = "992"

xcmPidDP155NPSMicrV1 OBJECT-IDENTITY
    STATUS      current
    DESCRIPTION
        "DocuPrint NPS DP155 Micr launch configuration version,
                 and complete product identifier."
    ::= { xcmPidDP155NPSMicr 1 }
        -- ::= {1.3.6.1.4.1.253.8.62.1.9.9.2.1}

-- DocuPrint NPS DP115 Printer

xcmPidDP115NPS OBJECT-IDENTITY
    STATUS      current
    DESCRIPTION
        "DocuPrint NPS DP115 product type identifier
                 (not a complete product identifier)."
    ::= { xcmPidDocuPrintNPS 17 }
        -- ::= {1.3.6.1.4.1.253.8.62.1.9.17}

xcmPidDP115NPSM1 OBJECT-IDENTITY
    STATUS      current
    DESCRIPTION
        "DocuPrint NPS DP115 launch configuration model identifier
                 (not a complete product identifier)."
    ::= { xcmPidDP115NPS 1 }
        -- ::= {1.3.6.1.4.1.253.8.62.1.9.17.1}
            -- => SAP PID string = "9A1"

xcmPidDP115NPSM1V1 OBJECT-IDENTITY
    STATUS      current
    DESCRIPTION
        "DocuPrint NPS DP115 launch configuration version,
                 and complete product identifier."


    ::= { xcmPidDP115NPSM1 1 }
        -- ::= {1.3.6.1.4.1.253.8.62.1.9.17.1.1}

-- DocuPrint NPS DP115 Micr Printer

xcmPidDP115NPSMicr OBJECT-IDENTITY
    STATUS      current
    DESCRIPTION
        "DocuPrint NPS DP115 Micr launch configuration model identifier
                 (not a complete product identifier)."
    ::= { xcmPidDP115NPS 2 }
        -- ::= {1.3.6.1.4.1.253.8.62.1.9.17.2}
            -- => SAP PID string = "9A2"

xcmPidDP115NPSMicrV1 OBJECT-IDENTITY
    STATUS      current
    DESCRIPTION
        "DocuPrint NPS DP115 Micr launch configuration version,
                 and complete product identifier."
    ::= { xcmPidDP115NPSMicr 1 }
        -- ::= {1.3.6.1.4.1.253.8.62.1.9.17.2.1}

-- DocuPrint NPS DP100 Printer

xcmPidDP100NPS OBJECT-IDENTITY
    STATUS      current
    DESCRIPTION
        "DocuPrint NPS DP100 product type identifier
                 (not a complete product identifier)."
    ::= { xcmPidDocuPrintNPS 18 }
        -- ::= {1.3.6.1.4.1.253.8.62.1.9.18}

xcmPidDP100NPSM1 OBJECT-IDENTITY
    STATUS      current
    DESCRIPTION
        "DocuPrint NPS DP100 launch configuration model identifier
                 (not a complete product identifier)."
    ::= { xcmPidDP100NPS 1 }
        -- ::= {1.3.6.1.4.1.253.8.62.1.9.18.1}
            -- => SAP PID string = "9B1"

xcmPidDP100NPSM1V1 OBJECT-IDENTITY
    STATUS      current
    DESCRIPTION
        "DocuPrint NPS DP100 launch configuration version,
                 and complete product identifier."
    ::= { xcmPidDP100NPSM1 1 }
        -- ::= {1.3.6.1.4.1.253.8.62.1.9.18.1.1}

-- DocuPrint NPS DP100 Micr Printer

xcmPidDP100NPSMicr OBJECT-IDENTITY
    STATUS      current
    DESCRIPTION


        "DocuPrint NPS DP100 Micr launch configuration model identifier
                 (not a complete product identifier)."
    ::= { xcmPidDP100NPS 2 }
        -- ::= {1.3.6.1.4.1.253.8.62.1.9.18.2}
            -- => SAP PID string = "9B2"

xcmPidDP100NPSMicrV1 OBJECT-IDENTITY
    STATUS      current
    DESCRIPTION
        "DocuPrint NPS DP100 Micr launch configuration version,
                 and complete product identifier."
    ::= { xcmPidDP100NPSMicr 1 }
        -- ::= {1.3.6.1.4.1.253.8.62.1.9.18.2.1}

-- DocuColor 2045 and 2060 NPS/IPS

xcmPidDC2000FamilyNPS OBJECT-IDENTITY
    STATUS      current
    DESCRIPTION
        "DocuColor 2000 NPS Family product line identifier
                 (not a complete product identifier)."
    ::= { xcmPidDocuPrintNPS 19 }
        -- ::= {1.3.6.1.4.1.253.8.62.1.9.19}

xcmPidDocuColor2045NPS OBJECT-IDENTITY
    STATUS      current
    DESCRIPTION
     "Xerox DocuColor 2045 NPS/IPS product identifier
       (not a complete product identifier)."
    ::= { xcmPidDC2000FamilyNPS 1 }
        -- ::= {1.3.6.1.4.1.253.8.62.1.9.19.1}
            -- => SAP PID string = "9C1"

xcmPidDocuColor2045NPSV1 OBJECT-IDENTITY
    STATUS      current
    DESCRIPTION
        "Xerox DocuColor 2045 NPS/IPS launch configuration
                 version, and complete product identifier."
    ::= { xcmPidDocuColor2045NPS 1 }
        -- ::= {1.3.6.1.4.1.253.8.62.1.9.19.1.1}

xcmPidDocuColor2060NPS OBJECT-IDENTITY
    STATUS      current
    DESCRIPTION
        "Xerox DocuColor 2060 NPS/IPS product type identifier
                 (not a complete product identifier)."
    ::= { xcmPidDC2000FamilyNPS 2 }
        -- ::= {1.3.6.1.4.1.253.8.62.1.9.19.2}
            -- => SAP PID string = "9C2"

xcmPidDocuColor2060NPSV1 OBJECT-IDENTITY
    STATUS      current
    DESCRIPTION
        "Xerox DocuColor 2060 NPS/IPS launch configuration


                 version, and complete product identifier."
    ::= { xcmPidDocuColor2060NPS 1 }
        -- ::= {1.3.6.1.4.1.253.8.62.1.9.19.2.1}

xcmPidDocuColor5252NPS OBJECT-IDENTITY
    STATUS      current
    DESCRIPTION
        "Xerox DocuColor 5252 NPS/IPS product type identifier
                 (not a complete product identifier)."
    ::= { xcmPidDC2000FamilyNPS 3 }
        -- ::= {1.3.6.1.4.1.253.8.62.1.9.19.3}
            -- => SAP PID string = "9C3"

xcmPidDocuColor5252NPSV1 OBJECT-IDENTITY
    STATUS      current
    DESCRIPTION
        "Xerox DocuColor 5252 NPS/IPS launch configuration
                 version, and complete product identifier."
    ::= { xcmPidDocuColor5252NPS 1 }
        -- ::= {1.3.6.1.4.1.253.8.62.1.9.19.3.1}

------------------------------------------------------
--
-- DocuColor 6000 NPS/IPS Family per Nick Briggs
-- No USB connectivity
------------------------------------------------------

xcmPidDC6000FamilyNPS OBJECT-IDENTITY
    STATUS      current
    DESCRIPTION
        "DocuColor 6000 NPS Family product line identifier
                 (not a complete product identifier)."
    ::= { xcmPidDocuPrintNPS 20 }
        -- ::= {1.3.6.1.4.1.253.8.62.1.9.20}

xcmPidDocuColor6060NPS OBJECT-IDENTITY
    STATUS      current
    DESCRIPTION
        "Xerox DocuColor 6060 NPS/IPS product type identifier
                 (not a complete product identifier)."
    ::= { xcmPidDC6000FamilyNPS 1 }
        -- ::= {1.3.6.1.4.1.253.8.62.1.9.20.1}
            -- => SAP PID string = "9D1"

xcmPidDocuColor6060NPSV1 OBJECT-IDENTITY
    STATUS      current
    DESCRIPTION
        "Xerox DocuColor 6060 NPS/IPS launch configuration
                 version, and complete product identifier."
    ::= { xcmPidDocuColor6060NPS 1 }
        -- ::= {1.3.6.1.4.1.253.8.62.1.9.20.1.1}

--
--

----------------------------------------------------------------
-- DocuPrint EPS Printers
----------------------------------------------------------------

xcmPidDocuPrintEPS OBJECT-IDENTITY
    STATUS      current
    DESCRIPTION
        "DocuPrint EPS product line
                 identifier (not a complete product identifier)."
    ::= { xcmPidProductIdentifiers 18 }
        -- ::= {1.3.6.1.4.1.253.8.62.1.18}

-- DocuPrint DP180 EPS Printer

xcmPidDP180EPS OBJECT-IDENTITY
    STATUS      current           -- actually deprecated
    DESCRIPTION
        "DocuPrint DP180 EPS product type identifier
                 (not a complete product identifier)."
    ::= { xcmPidDocuPrintEPS 1 }
        -- ::= {1.3.6.1.4.1.253.8.62.1.18.1}

xcmPidDP180EPSM1 OBJECT-IDENTITY
    STATUS      current           -- actually deprecated
    DESCRIPTION
        "DocuPrint DP180 EPS launch configuration model identifier
                 (not a complete product identifier)."
    ::= { xcmPidDP180EPS 1 }
        -- ::= {1.3.6.1.4.1.253.8.62.1.18.1.1}
            -- => SAP PID string = "B11"


xcmPidDP180EPSM1V1 OBJECT-IDENTITY
    STATUS      current           -- actually deprecated
    DESCRIPTION
        "DocuPrint DP180 EPS launch configuration version,
                 and complete product identifier."
    ::= { xcmPidDP180EPSM1 1 }
        -- ::= {1.3.6.1.4.1.253.8.62.1.18.1.1.1}

-- DocuPrint 2000 Series EPS Printers

xcmPidDP2000EPS OBJECT-IDENTITY
    STATUS      current
    DESCRIPTION
        "DocuPrint 2000 Series EPS product type identifier
                 (not a complete product identifier)."
    ::= { xcmPidDocuPrintEPS 2 }
        -- ::= {1.3.6.1.4.1.253.8.62.1.18.2}

xcmPidDP2000S100EPS OBJECT-IDENTITY
    STATUS      current
    DESCRIPTION
     "DocuPrint 2000 Series 100 EPS launch configuration
      model identifier (not a complete product identifier)."
    ::= { xcmPidDP2000EPS 1 }
        -- ::= {1.3.6.1.4.1.253.8.62.1.18.2.1}
            -- => SAP PID string = "B21"

xcmPidDP2000S100EPSV1 OBJECT-IDENTITY
    STATUS      current
    DESCRIPTION
        "DocuPrint 2000 Series 100 EPS launch configuration
                 version and complete product identifier."
    ::= { xcmPidDP2000S100EPS 1 }
        -- ::= {1.3.6.1.4.1.253.8.62.1.18.2.1.1}

xcmPidDP2000S115EPS OBJECT-IDENTITY
    STATUS      current
    DESCRIPTION
        "DocuPrint 2000 Series 115 EPS launch configuration
                 model identifier
                 (not a complete product identifier)."
    ::= { xcmPidDP2000EPS 2 }
        -- ::= {1.3.6.1.4.1.253.8.62.1.18.2.2}
            -- => SAP PID string = "B22"

xcmPidDP2000S115EPSV1 OBJECT-IDENTITY
    STATUS      current
    DESCRIPTION
        "DocuPrint 2000 Series 115 EPS launch configuration
                 version and complete product identifier."
    ::= { xcmPidDP2000S115EPS 1 }
        -- ::= {1.3.6.1.4.1.253.8.62.1.18.2.2.1}


xcmPidDP2000S135EPS OBJECT-IDENTITY
    STATUS      current
    DESCRIPTION
        "DocuPrint 2000 Series 135 EPS launch configuration
                 model identifier
                 (not a complete product identifier)."
    ::= { xcmPidDP2000EPS 3 }
        -- ::= {1.3.6.1.4.1.253.8.62.1.18.2.3}
            -- => SAP PID string = "B23"

xcmPidDP2000S135EPSV1 OBJECT-IDENTITY
    STATUS      current
    DESCRIPTION
        "DocuPrint 2000 Series 135 EPS launch configuration
                 version and complete product identifier."
    ::= { xcmPidDP2000S135EPS 1 }
        -- ::= {1.3.6.1.4.1.253.8.62.1.18.2.3.1}

xcmPidDP2000S155EPS OBJECT-IDENTITY
    STATUS      current
    DESCRIPTION
     "DocuPrint 2000 Series 155 EPS launch configuration
       model identifier (not a complete product identifier)."
    ::= { xcmPidDP2000EPS 4 }
        -- ::= {1.3.6.1.4.1.253.8.62.1.18.2.4}
            -- => SAP PID string = "B24"

xcmPidDP2000S155EPSV1 OBJECT-IDENTITY
    STATUS      current
    DESCRIPTION
        "DocuPrint 2000 Series 155 EPS launch configuration
                 version and complete product identifier."
    ::= { xcmPidDP2000S155EPS 1 }
        -- ::= {1.3.6.1.4.1.253.8.62.1.18.2.4.1}

xcmPidDP2000S180EPS OBJECT-IDENTITY
    STATUS      current
    DESCRIPTION
        "DocuPrint 2000 Series 180 EPS launch configuration
                 model identifier
                 (not a complete product identifier)."
    ::= { xcmPidDP2000EPS 5 }
        -- ::= {1.3.6.1.4.1.253.8.62.1.18.2.5}
            -- => SAP PID string = "B25"

xcmPidDP2000S180EPSV1 OBJECT-IDENTITY
    STATUS      current
    DESCRIPTION
        "DocuPrint 2000 Series 180 EPS launch configuration
                 version and complete product identifier."
    ::= { xcmPidDP2000S180EPS 1 }
        -- ::= {1.3.6.1.4.1.253.8.62.1.18.2.5.1}


-- DocuPrint 2000 Series EPS MICR Printers

xcmPidDP2000S100EPSMX OBJECT-IDENTITY
    STATUS      current
    DESCRIPTION
        "DocuPrint 2000 Series 100 EPS MX launch configuration
                 model identifier
                 (not a complete product identifier)."
    ::= { xcmPidDP2000EPS 8 }
        -- ::= {1.3.6.1.4.1.253.8.62.1.18.2.8}
            -- => SAP PID string = "B28"

xcmPidDP2000S100EPSMXV1 OBJECT-IDENTITY
    STATUS      current
    DESCRIPTION
        "DocuPrint 2000 Series 100 EPS MX launch configuration
                 version and complete product identifier."
    ::= { xcmPidDP2000S100EPSMX 1 }
        -- ::= {1.3.6.1.4.1.253.8.62.1.18.2.8.1}

xcmPidDP2000S115EPSMX OBJECT-IDENTITY
    STATUS      current
    DESCRIPTION
        "DocuPrint 2000 Series 115 EPS MX launch configuration
                 model identifier
                 (not a complete product identifier)."
    ::= { xcmPidDP2000EPS 9 }
        -- ::= {1.3.6.1.4.1.253.8.62.1.18.2.9}
            -- => SAP PID string = "B29"

xcmPidDP2000S115EPSMXV1 OBJECT-IDENTITY
    STATUS      current
    DESCRIPTION
        "DocuPrint 2000 Series 115 EPS MX launch configuration
                 version and complete product identifier."
    ::= { xcmPidDP2000S115EPSMX 1 }
        -- ::= {1.3.6.1.4.1.253.8.62.1.18.2.9.1}

xcmPidDP2000S135EPSMX OBJECT-IDENTITY
    STATUS      current
    DESCRIPTION
        "DocuPrint 2000 Series 135 EPS MX launch configuration
                 model identifier
                 (not a complete product identifier)."
    ::= { xcmPidDP2000EPS 17 }
        -- ::= {1.3.6.1.4.1.253.8.62.1.18.2.17}
            -- => SAP PID string = "B2A"

xcmPidDP2000S135EPSMXV1 OBJECT-IDENTITY
    STATUS      current
    DESCRIPTION
        "DocuPrint 2000 Series 135 EPS MX launch configuration
                 version and complete product identifier."


    ::= { xcmPidDP2000S135EPSMX 1 }
        -- ::= {1.3.6.1.4.1.253.8.62.1.18.2.17.1}

xcmPidDP2000S155EPSMX OBJECT-IDENTITY
    STATUS      current
    DESCRIPTION
        "DocuPrint 2000 Series 155 EPS MX launch configuration
                 model identifier
                 (not a complete product identifier)."
    ::= { xcmPidDP2000EPS 18 }
        -- ::= {1.3.6.1.4.1.253.8.62.1.18.2.18}
            -- => SAP PID string = "B2B"

xcmPidDP2000S155EPSMXV1 OBJECT-IDENTITY
    STATUS      current
    DESCRIPTION
        "DocuPrint 2000 Series 155 EPS MX launch configuration
                 version and complete product identifier."
    ::= { xcmPidDP2000S155EPSMX 1 }
        -- ::= {1.3.6.1.4.1.253.8.62.1.18.2.18.1}

xcmPidDP2000S180EPSMX OBJECT-IDENTITY
    STATUS      current
    DESCRIPTION
        "DocuPrint 2000 Series 180 EPS MX launch configuration
                 model identifier
                 (not a complete product identifier)."
    ::= { xcmPidDP2000EPS 19 }
        -- ::= {1.3.6.1.4.1.253.8.62.1.18.2.19}
            -- => SAP PID string = "B2C"

xcmPidDP2000S180EPSMXV1 OBJECT-IDENTITY
    STATUS      current
    DESCRIPTION
        "DocuPrint 2000 Series 180 EPS MX launch configuration
                 version and complete product identifier."
    ::= { xcmPidDP2000S180EPSMX 1 }
        -- ::= {1.3.6.1.4.1.253.8.62.1.18.2.19.1}

-- DocuPrint 6075

xcmPidDP2000S6075 OBJECT-IDENTITY
    STATUS      current
    DESCRIPTION
        "DocuPrint 6075 launch configuration model identifier
                 (not a complete product identifier)."
    ::= { xcmPidDP2000EPS 6 }
        -- ::= {1.3.6.1.4.1.253.8.62.1.18.2.6}
            -- => SAP PID string = "B26"

xcmPidDP2000S6075V1 OBJECT-IDENTITY
    STATUS      current
    DESCRIPTION
        "DocuPrint 6075 launch configuration


                 version and complete product identifier."
    ::= { xcmPidDP2000S6075 1 }
        -- ::= {1.3.6.1.4.1.253.8.62.1.18.2.6.1}

-- DocuPrint 6090

xcmPidDP2000S6090 OBJECT-IDENTITY
    STATUS      current
    DESCRIPTION
        "DocuPrint 6090 launch configuration model identifier
                 (not a complete product identifier)."
    ::= { xcmPidDP2000EPS 7 }
        -- ::= {1.3.6.1.4.1.253.8.62.1.18.2.7}
            -- => SAP PID string = "B27"

xcmPidDP2000S6090V1 OBJECT-IDENTITY
    STATUS      current
    DESCRIPTION
        "DocuPrint 6090 launch configuration
                 version and complete product identifier."
    ::= { xcmPidDP2000S6090 1 }
        -- ::= {1.3.6.1.4.1.253.8.62.1.18.2.7.1}

-- DocuPrint DP180 Micr EPS Printer

xcmPidDP180EPSMicr OBJECT-IDENTITY
    STATUS      current           -- actually deprecated
    DESCRIPTION
     "DocuPrint DP180 Micr EPS launch model identifier
                 (not a complete product identifier)."
    ::= { xcmPidDP180EPS 2 }
        -- ::= {1.3.6.1.4.1.253.8.62.1.18.1.2}
            -- => SAP PID string = "B12"

xcmPidDP180EPSMicrV1 OBJECT-IDENTITY
    STATUS      current           -- actually deprecated
    DESCRIPTION
        "DocuPrint DP180 Micr EPS launch configuration version,
                 and complete product identifier."
    ::= { xcmPidDP180EPSMicr 1 }
        -- ::= {1.3.6.1.4.1.253.8.62.1.18.1.2.1}

--
--

----------------------------------------------------------------
-- DocuTechs
----------------------------------------------------------------

xcmPidDocuTechs OBJECT-IDENTITY
    STATUS      current
    DESCRIPTION
        "DocuTech product line identifier
                 (not a complete product identifier)."
    ::= { xcmPidProductIdentifiers 5 }
        -- ::= {1.3.6.1.4.1.253.8.62.1.5}

--
--

-- DocuTech 6100 (DocuSP 6100)


xcmPidDocuTech6100 OBJECT-IDENTITY
    STATUS      current
    DESCRIPTION
        "DocuTech 6100 product type identifier
                 (not a complete product identifier)."
    ::= { xcmPidDocuTechs 4 }
        -- ::= {1.3.6.1.4.1.253.8.62.1.5.4}

xcmPidDocuTech6100M1 OBJECT-IDENTITY
    STATUS      current
    DESCRIPTION
        "DocuTech 6100 launch configuration model identifier
                 (not a complete product identifier)."
    ::= { xcmPidDocuTech6100 1 }
        -- ::= {1.3.6.1.4.1.253.8.62.1.5.4.1}
            -- => SAP PID string = "541"

xcmPidDocuTech6100M1V1 OBJECT-IDENTITY
    STATUS      current
    DESCRIPTION
        "DocuTech 6100 launch configuration version,
                 and complete product identifier."
    ::= { xcmPidDocuTech6100M1 1 }
        -- ::= {1.3.6.1.4.1.253.8.62.1.5.4.1.1}

xcmPidDocuTech6100M1V2 OBJECT-IDENTITY
    STATUS      current
    DESCRIPTION
        "DocuTech 6100 launch configuration version,
                 and complete product identifier."
    ::= { xcmPidDocuTech6100M1 2 }
        -- ::= {1.3.6.1.4.1.253.8.62.1.5.4.1.2}

-- DocuTech 6115 (DocuSP 6115)

xcmPidDocuTech6115 OBJECT-IDENTITY
    STATUS      current
    DESCRIPTION
        "DocuTech 6115 product type identifier
                 (not a complete product identifier)."
    ::= { xcmPidDocuTechs 5 }
        -- ::= {1.3.6.1.4.1.253.8.62.1.5.5}

xcmPidDocuTech6115M1 OBJECT-IDENTITY
    STATUS      current
    DESCRIPTION
        "DocuTech 6115 launch configuration model identifier
                 (not a complete product identifier)."
    ::= { xcmPidDocuTech6115 1 }
        -- ::= {1.3.6.1.4.1.253.8.62.1.5.5.1}
            -- => SAP PID string = "551"

xcmPidDocuTech6115M1V1 OBJECT-IDENTITY


    STATUS      current
    DESCRIPTION
        "DocuTech 6115 launch configuration version,
                 and complete product identifier."
    ::= { xcmPidDocuTech6115M1 1 }
        -- ::= {1.3.6.1.4.1.253.8.62.1.5.5.1.1}

xcmPidDocuTech6115M1V2 OBJECT-IDENTITY
    STATUS      current
    DESCRIPTION
        "DocuTech 6115 launch configuration version,
                 and complete product identifier."
    ::= { xcmPidDocuTech6115M1 2 }
        -- ::= {1.3.6.1.4.1.253.8.62.1.5.5.1.2}

-- DocuTech 6135 (DocuSP 6135)

xcmPidDocuTech6135 OBJECT-IDENTITY
    STATUS      current
    DESCRIPTION
        "DocuTech 6135 product type identifier
                 (not a complete product identifier)."
    ::= { xcmPidDocuTechs 2 }
        -- ::= {1.3.6.1.4.1.253.8.62.1.5.2}

xcmPidDocuTech6135M1 OBJECT-IDENTITY
    STATUS      current
    DESCRIPTION
        "DocuTech 6135 launch configuration model identifier
                 (not a complete product identifier)."
    ::= { xcmPidDocuTech6135 1 }
        -- ::= {1.3.6.1.4.1.253.8.62.1.5.2.1}
            -- => SAP PID string = "521"

xcmPidDocuTech6135M1V1 OBJECT-IDENTITY
    STATUS      current
    DESCRIPTION
        "DocuTech 6135 launch configuration version,
                 and complete product identifier."
    ::= { xcmPidDocuTech6135M1 1 }
        -- ::= {1.3.6.1.4.1.253.8.62.1.5.2.1.1}

xcmPidDocuTech6135M1V2 OBJECT-IDENTITY
    STATUS      current
    DESCRIPTION
        "DocuTech 6135 launch configuration version,
                 and complete product identifier."
    ::= { xcmPidDocuTech6135M1 2 }
        -- ::= {1.3.6.1.4.1.253.8.62.1.5.2.1.2}

-- DocuTech 6155 (DocuSP 6155)

xcmPidDocuTech6155 OBJECT-IDENTITY
    STATUS      current


    DESCRIPTION
        "DocuTech 6155 product type identifier
                 (not a complete product identifier)."
    ::= { xcmPidDocuTechs 6 }
        -- ::= {1.3.6.1.4.1.253.8.62.1.5.6}

xcmPidDocuTech6155M1 OBJECT-IDENTITY
    STATUS      current
    DESCRIPTION
        "DocuTech 6155 launch configuration model identifier
                 (not a complete product identifier)."
    ::= { xcmPidDocuTech6155 1 }
        -- ::= {1.3.6.1.4.1.253.8.62.1.5.6.1}
            -- => SAP PID string = "561"

xcmPidDocuTech6155M1V1 OBJECT-IDENTITY
    STATUS      current
    DESCRIPTION
        "DocuTech 6155 launch configuration version,
                 and complete product identifier."
    ::= { xcmPidDocuTech6155M1 1 }
        -- ::= {1.3.6.1.4.1.253.8.62.1.5.6.1.1}

xcmPidDocuTech6155M1V2 OBJECT-IDENTITY
    STATUS      current
    DESCRIPTION
        "DocuTech 6155 launch configuration version,
                 and complete product identifier."
    ::= { xcmPidDocuTech6155M1 2 }
        -- ::= {1.3.6.1.4.1.253.8.62.1.5.6.1.2}

-- DocuTech 6180 (DocuSP 6180)

xcmPidDocuTech6180 OBJECT-IDENTITY
    STATUS      current
    DESCRIPTION
        "DocuTech 6180 product type identifier
                 (not a complete product identifier)."
    ::= { xcmPidDocuTechs 3 }
        -- ::= {1.3.6.1.4.1.253.8.62.1.5.3}

xcmPidDocuTech6180M1 OBJECT-IDENTITY
    STATUS      current
    DESCRIPTION
        "DocuTech 6180 launch configuration model identifier
                 (not a complete product identifier)."
    ::= { xcmPidDocuTech6180 1 }
        -- ::= {1.3.6.1.4.1.253.8.62.1.5.3.1}
            -- => SAP PID string = "531"

xcmPidDocuTech6180M1V1 OBJECT-IDENTITY
    STATUS      current
    DESCRIPTION
        "DocuTech 6180 launch configuration version,


                 and complete product identifier."
    ::= { xcmPidDocuTech6180M1 1 }
        -- ::= {1.3.6.1.4.1.253.8.62.1.5.3.1.1}

xcmPidDocuTech6180M1V2 OBJECT-IDENTITY
    STATUS      current
    DESCRIPTION
        "DocuTech 6180 launch configuration version,
                 and complete product identifier."
    ::= { xcmPidDocuTech6180M1 2 }
        -- ::= {1.3.6.1.4.1.253.8.62.1.5.3.1.2}

-- DocuTech 6075 (DocuSP 6075)

xcmPidDocuTech6075 OBJECT-IDENTITY
    STATUS      current
    DESCRIPTION
        "DocuTech 6075 product type identifier
                 (not a complete product identifier)."
    ::= { xcmPidDocuTechs 7 }
        -- ::= {1.3.6.1.4.1.253.8.62.1.5.7}

xcmPidDocuTech6075M1 OBJECT-IDENTITY
    STATUS      current
    DESCRIPTION
        "DocuTech 6075 launch configuration model identifier
                 (not a complete product identifier)."
    ::= { xcmPidDocuTech6075 1 }
        -- ::= {1.3.6.1.4.1.253.8.62.1.5.7.1}
            -- => SAP PID string = "571"

xcmPidDocuTech6075M1V1 OBJECT-IDENTITY
    STATUS      current
    DESCRIPTION
        "DocuTech 6075 launch configuration version,
                 and complete product identifier."
    ::= { xcmPidDocuTech6075M1 1 }
        -- ::= {1.3.6.1.4.1.253.8.62.1.5.7.1.1}

-- DocuTech 6090 (DocuSP 6090)

xcmPidDocuTech6090 OBJECT-IDENTITY
    STATUS      current
    DESCRIPTION
        "DocuTech 6090 product type identifier
                 (not a complete product identifier)."
    ::= { xcmPidDocuTechs 8 }
        -- ::= {1.3.6.1.4.1.253.8.62.1.5.8}

xcmPidDocuTech6090M1 OBJECT-IDENTITY
    STATUS      current
    DESCRIPTION
        "DocuTech 6090 launch configuration model identifier
                 (not a complete product identifier)."


    ::= { xcmPidDocuTech6090 1 }
        -- ::= {1.3.6.1.4.1.253.8.62.1.5.8.1}
            -- => SAP PID string = "581"

xcmPidDocuTech6090M1V1 OBJECT-IDENTITY
    STATUS      current
    DESCRIPTION
        "DocuTech 6090 launch configuration version,
                 and complete product identifier."
    ::= { xcmPidDocuTech6090M1 1 }
        -- ::= {1.3.6.1.4.1.253.8.62.1.5.8.1.1}

--
--


----------------------------------------------------------------
-- updated Xerox Nuvera Product Line PID name
--    OLD = xcmPidNuvera
--    NEW = xcmPidNuveraProductLine
--
--    NOTE: Reset of branch definition remains the same
--    5/1/2012 by TSilver
----------------------------------------------------------------


xcmPidNuveraProductLine OBJECT-IDENTITY
    STATUS      current
    DESCRIPTION
        "Nuvera product line identifier
                 (not a complete product identifier)."
    ::= { xcmPidProductIdentifiers 23 }
        -- ::= {1.3.6.1.4.1.253.8.62.1.23}

--
--
--
--

xcmPidNuveraEAProductionSystemFamily OBJECT-IDENTITY
    STATUS      current
    DESCRIPTION
        "Xerox Nuvera EA Production System family
         identifier (not a complete product identifier)."
    ::= { xcmPidNuveraProductLine 17 }
        -- ::= {1.3.6.1.4.1.253.8.62.1.23.17}

xcmPidNuvera100x120x144x157EAPS OBJECT-IDENTITY
    STATUS      current
    DESCRIPTION
        "Xerox Nuvera 100x120x144x157 EAPS system model
         identifier (not a complete product identifier)."
    ::= { xcmPidNuveraEAProductionSystemFamily 1 }
        -- ::= {1.3.6.1.4.1.253.8.62.1.23.17.1}

--
--
xcmPidNuvera100x120x144x157EAPSEmbeddedFFPS OBJECT-IDENTITY
    STATUS      current
    DESCRIPTION
         "Xerox Nuvera 100x120x144x157 EAPS with an
         embedded FreeFlow Print Server (FFPS) DFE
         system configuration model identifier
         (not a complete product identifier)."
    ::= { xcmPidNuvera100x120x144x157EAPS 1 }
        -- ::= {1.3.6.1.4.1.253.8.62.1.23.17.1.1}

xcmPidNuvera100x120x144x157EAPSEmbeddedFFPSV1 OBJECT-IDENTITY
    STATUS      current
    DESCRIPTION
         "Xerox Nuvera 100x120x144x157 EAPS with an
         embedded FreeFlow Print Server (FFPS) DFE
         device launch configuration version and
         complete product identifier."
    ::= { xcmPidNuvera100x120x144x157EAPSEmbeddedFFPS 1 }
        -- ::= {1.3.6.1.4.1.253.8.62.1.23.17.1.1.1}

xcmPidNuveraEAPerfectingProductionSystemFamily OBJECT-IDENTITY
    STATUS      current
    DESCRIPTION
        "Xerox Nuvera EA Perfecting Production System
         family identifier (not a complete product identifier)."
    ::= { xcmPidNuveraProductLine 18 }


        -- ::= {1.3.6.1.4.1.253.8.62.1.23.18}

xcmPidNuvera200x288x314EAPPS OBJECT-IDENTITY
    STATUS      current
    DESCRIPTION
        "Xerox Nuvera 200x288x314 EAPPS system model
         identifier (not a complete product identifier)."
    ::= { xcmPidNuveraEAPerfectingProductionSystemFamily 1 }
        -- ::= {1.3.6.1.4.1.253.8.62.1.23.18.1}

--
--
xcmPidNuvera200x288x314EAPPSEmbeddedFFPS OBJECT-IDENTITY
    STATUS      current
    DESCRIPTION
         "Xerox Nuvera 200x288x314 EAPPS with an
         embedded FreeFlow Print Server (FFPS) DFE
         system configuration model identifier
         (not a complete product identifier)."
    ::= { xcmPidNuvera200x288x314EAPPS 1 }
        -- ::= {1.3.6.1.4.1.253.8.62.1.23.18.1.1}

-- CB Fix

xcmPidNuvera200x288x314EAPPSEmbeddedFFPSv1 OBJECT-IDENTITY
    STATUS      current
    DESCRIPTION
         "Xerox Nuvera 200x288x314 EAPPS with an
         embedded FreeFlow Print Server (FFPS) DFE
         device launch configuration version and
         complete product identifier."
    ::= { xcmPidNuvera200x288x314EAPPSEmbeddedFFPS 1 }
        -- ::= {1.3.6.1.4.1.253.8.62.1.23.18.1.1.1}

xcmPidNuveraMXProductionSystemFamily OBJECT-IDENTITY
    STATUS      current
    DESCRIPTION
        "Xerox Nuvera MX Production System family identifier
         (not a complete product identifier)."
    ::= { xcmPidNuveraProductLine 19 }
        -- ::= {1.3.6.1.4.1.253.8.62.1.23.19}

xcmPidNuvera100x120x144MXPS OBJECT-IDENTITY
    STATUS      current
    DESCRIPTION
        "Xerox Nuvera 100x120x144 MXPS system model
         identifier (not a complete product identifier)."
    ::= { xcmPidNuveraMXProductionSystemFamily 1 }
        -- ::= {1.3.6.1.4.1.253.8.62.1.23.19.1}

--
--


xcmPidNuvera100x120x144MXPSEmbeddedFFPS OBJECT-IDENTITY
    STATUS      current
    DESCRIPTION
         "Xerox Nuvera 100x120x144 MXPS with an
         embedded FreeFlow Print Server (FFPS) DFE
         system configuration model identifier
         (not a complete product identifier)."
    ::= { xcmPidNuvera100x120x144MXPS 1 }
        -- ::= {1.3.6.1.4.1.253.8.62.1.23.19.1.1}

xcmPidNuvera100x120x144MXPSEmbeddedFFPSV1 OBJECT-IDENTITY
    STATUS      current
    DESCRIPTION
         "Xerox Nuvera 100x120x144 MXPS with an
         embedded FreeFlow Print Server (FFPS) DFE
         device launch configuration version and
         complete product identifier."
    ::= { xcmPidNuvera100x120x144MXPSEmbeddedFFPS 1 }
        -- ::= {1.3.6.1.4.1.253.8.62.1.23.19.1.1.1}

xcmPidNuveraMXPerfectingProductionSystemFamily OBJECT-IDENTITY
    STATUS      current
    DESCRIPTION
        "Xerox Nuvera MX Perfecting Production System
         family identifier (not a complete product identifier)."
    ::= { xcmPidNuveraProductLine 20 }
        -- ::= {1.3.6.1.4.1.253.8.62.1.23.20}

xcmPidNuvera200x288MXPPS OBJECT-IDENTITY
    STATUS      current
    DESCRIPTION
        "Xerox Nuvera 200x288 MXPPS system model
         identifier (not a complete product identifier)."
    ::= { xcmPidNuveraMXPerfectingProductionSystemFamily 1 }
        -- ::= {1.3.6.1.4.1.253.8.62.1.23.20.1}

--
--
xcmPidNuvera200x288MXPPSEmbeddedFFPS OBJECT-IDENTITY
    STATUS      current
    DESCRIPTION
         "Xerox Nuvera 200x288 MXPPS with an
         embedded FreeFlow Print Server (FFPS) DFE
         system configuration model identifier
         (not a complete product identifier)."
    ::= { xcmPidNuvera200x288MXPPS 1 }
        -- ::= {1.3.6.1.4.1.253.8.62.1.23.20.1.1}

xcmPidNuvera200x288MXPPSEmbeddedFFPSV1 OBJECT-IDENTITY
    STATUS      current
    DESCRIPTION
         "Xerox Nuvera 200x288 MXPPS with an
         embedded FreeFlow Print Server (FFPS) DFE


         device launch configuration version and
         complete product identifier."
    ::= { xcmPidNuvera200x288MXPPSEmbeddedFFPS 1 }
        -- ::= {1.3.6.1.4.1.253.8.62.1.23.20.1.1.1}


-------------------------------------------------------
-- DocuTech Highlight Color EPS
-------------------------------------------------------


xcmPidDocuTechHiColorEPS OBJECT-IDENTITY
    STATUS      current
    DESCRIPTION
        "DocuTech Highlight Color EPS product type identifier
                 (not a complete product identifier)."
 ::= { xcmPidDocuTechs 19 }
        -- ::= {1.3.6.1.4.1.253.8.62.1.5.19}

--
--

-------------------------------------------------------
-- DocuSP-DFE B/W
-------------------------------------------------------


xcmPidDocuSPDFE OBJECT-IDENTITY
    STATUS      current
    DESCRIPTION
        "DocuSP-DFE B/W Copier / Printer product type identifier
                 (not a complete product identifier)."
 ::= { xcmPidDocuTechs 20 }


        -- ::= {1.3.6.1.4.1.253.8.62.1.5.20}

--
--

-------------------------------------------------------
-- DocuSP-DFE Color
-------------------------------------------------------


xcmPidDocuSPDFEColor OBJECT-IDENTITY
    STATUS      current
    DESCRIPTION
        "DocuSP-DFE Color Copier / Printer product type identifier
                 (not a complete product identifier)."
 ::= { xcmPidDocuTechs 21 }
        -- ::= {1.3.6.1.4.1.253.8.62.1.5.21}

--
--

-------------------------------------------------------
-------------------------------------------------------

xcmPidDocuSPTEAK OBJECT-IDENTITY
    STATUS      current
    DESCRIPTION
        "Xerox 41xx Copier / Printer with Free Flow
          Print Server product type identifier
                 (not a complete product identifier)."


 ::= { xcmPidDocuTechs 22 }
        -- ::= {1.3.6.1.4.1.253.8.62.1.5.22}

--
--

--
--

xcmPidXeroxWideFormat OBJECT-IDENTITY
    STATUS      current
    DESCRIPTION
        "Xerox Wide Format Printers product line identifier
                 (not a complete product identifier)."
    ::= { xcmPidProductIdentifiers 22 }
        -- ::= {1.3.6.1.4.1.253.8.62.1.22}

--
--


xcmPidColorQube OBJECT-IDENTITY
    STATUS      current
    DESCRIPTION
        "ColorQube product line identifier
                 (not a complete product identifier)."
    ::= { xcmPidProductIdentifiers 24 }
        -- ::= {1.3.6.1.4.1.253.8.62.1.24}

-- ColorQube 9200 Family

xcmPidColorQube9200 OBJECT-IDENTITY
    STATUS      current
    DESCRIPTION
        "Xerox ColorQube 9200 family identifier
           (not a complete product identifier)."
    ::= { xcmPidColorQube 1 }
        -- ::= {1.3.6.1.4.1.253.8.62.1.24.1}



-- ColorQube 9200 Family  9201 Model

xcmPidColorQube9201 OBJECT-IDENTITY
    STATUS      current


    DESCRIPTION
        "Xerox ColorQube 9201 model identifier
           (not a complete product identifier)."
    ::= { xcmPidColorQube9200 1 }
        -- ::= {1.3.6.1.4.1.253.8.62.1.24.1.1}
            -- => SAP PID string = "H11"
            -- => USB PID string = 22069 = 0x5635
            -- => Compatible ID = XR_PS_Office_Color
--
-- PLEASE NOTE:
-- The MODEL NAME used for the PNP ID   "ColorQube 9201"
-- The generated PNP PID are only valid for that MODEL NAME
--
            -- => PNP ID ColorQube 9201  XeroxColorQube_92018FFA

-- ColorQube Model 9201 Configuration One
--      Common Board Controller (CBC)

xcmPidColorQube9201C1 OBJECT-IDENTITY
    STATUS      current
    DESCRIPTION
        "Xerox ColorQube 9201
           model and configuration 1 identifier
           (not a complete product identifier)."
    ::= { xcmPidColorQube9201 1 }
        -- ::= {1.3.6.1.4.1.253.8.62.1.24.1.1.1}

xcmPidColorQube9201C1V1 OBJECT-IDENTITY
    STATUS      current
    DESCRIPTION
        "Xerox ColorQube 9201
            launch model, configuration 1, version 1.
            A complete product identifier."
    ::= { xcmPidColorQube9201C1 1 }
        -- ::= {1.3.6.1.4.1.253.8.62.1.24.1.1.1.1}

xcmPidColorQube9201C1V2 OBJECT-IDENTITY
    STATUS      current
    DESCRIPTION
        "Xerox ColorQube 9201
            launch model, configuration 1, version 2.
            A complete product identifier."
    ::= { xcmPidColorQube9201C1 2 }
        -- ::= {1.3.6.1.4.1.253.8.62.1.24.1.1.1.2}

xcmPidColorQube9201C1V3 OBJECT-IDENTITY
    STATUS      current
    DESCRIPTION
        "Xerox ColorQube 9201
            launch model, configuration 1, version 3.
            A complete product identifier."
    ::= { xcmPidColorQube9201C1 3 }
        -- ::= {1.3.6.1.4.1.253.8.62.1.24.1.1.1.3}


-- ColorQube Model 9201 Configuration Two
--      Single Board Controller (SBC)

xcmPidColorQube9201C2 OBJECT-IDENTITY
    STATUS      current
    DESCRIPTION
        "Xerox ColorQube 9201
           model and configuration 2 identifier
           (not a complete product identifier)."
    ::= { xcmPidColorQube9201 2 }
        -- ::= {1.3.6.1.4.1.253.8.62.1.24.1.1.2}

xcmPidColorQube9201C2V1 OBJECT-IDENTITY
    STATUS      current
    DESCRIPTION
        "Xerox ColorQube 9201
            launch model, configuration 2, version 1.
            A complete product identifier."
    ::= { xcmPidColorQube9201C2 1 }
        -- ::= {1.3.6.1.4.1.253.8.62.1.24.1.1.2.1}

xcmPidColorQube9201C2V2 OBJECT-IDENTITY
    STATUS      current
    DESCRIPTION
        "Xerox ColorQube 9201
            launch model, configuration 2, version 2.
            A complete product identifier."
    ::= { xcmPidColorQube9201C2 2 }
        -- ::= {1.3.6.1.4.1.253.8.62.1.24.1.1.2.2}



-- ColorQube 9200 Family  9202 Model

xcmPidColorQube9202 OBJECT-IDENTITY
    STATUS      current
    DESCRIPTION
        "Xerox ColorQube 9202 model identifier
           (not a complete product identifier)."
    ::= { xcmPidColorQube9200 2 }
        -- ::= {1.3.6.1.4.1.253.8.62.1.24.1.2}
            -- => SAP PID string = "H12"
            -- => USB PID string = 22070 = 0x5636
            -- => Compatible ID = XR_PS_Office_Color
--
-- PLEASE NOTE:
-- The MODEL NAME used for the PNP ID   "ColorQube 9202"
-- The generated PNP PID are only valid for that MODEL NAME


--
            -- => PNP ID ColorQube 9202  XeroxColorQube_92028EBA

-- ColorQube Model 9202 Configuration One
--      Common Board Controller (CBC)

xcmPidColorQube9202C1 OBJECT-IDENTITY
    STATUS      current
    DESCRIPTION
        "Xerox ColorQube 9202
           model and configuration 1 identifier
           (not a complete product identifier)."
    ::= { xcmPidColorQube9202 1 }
        -- ::= {1.3.6.1.4.1.253.8.62.1.24.1.2.1}

xcmPidColorQube9202C1V1 OBJECT-IDENTITY
    STATUS      current
    DESCRIPTION
        "Xerox ColorQube 9202
            launch model, configuration 1, version 1.
            A complete product identifier."
    ::= { xcmPidColorQube9202C1 1 }
        -- ::= {1.3.6.1.4.1.253.8.62.1.24.1.2.1.1}

xcmPidColorQube9202C1V2 OBJECT-IDENTITY
    STATUS      current
    DESCRIPTION
        "Xerox ColorQube 9202
            launch model, configuration 1, version 2.
            A complete product identifier."
    ::= { xcmPidColorQube9202C1 2 }
        -- ::= {1.3.6.1.4.1.253.8.62.1.24.1.2.1.2}

xcmPidColorQube9202C1V3 OBJECT-IDENTITY
    STATUS      current
    DESCRIPTION
        "Xerox ColorQube 9202
            launch model, configuration 1, version 3.
            A complete product identifier."
    ::= { xcmPidColorQube9202C1 3 }
        -- ::= {1.3.6.1.4.1.253.8.62.1.24.1.2.1.3}

-- ColorQube Model 9202 Configuration Two
--      Single Board Controller (SBC)

xcmPidColorQube9202C2 OBJECT-IDENTITY
    STATUS      current
    DESCRIPTION
        "Xerox ColorQube 9202
           model and configuration 2 identifier
           (not a complete product identifier)."
    ::= { xcmPidColorQube9202 2 }
        -- ::= {1.3.6.1.4.1.253.8.62.1.24.1.2.2}


xcmPidColorQube9202C2V1 OBJECT-IDENTITY
    STATUS      current
    DESCRIPTION
        "Xerox ColorQube 9202
            launch model, configuration 2, version 1.
            A complete product identifier."
    ::= { xcmPidColorQube9202C2 1 }
        -- ::= {1.3.6.1.4.1.253.8.62.1.24.1.2.2.1}

xcmPidColorQube9202C2V2 OBJECT-IDENTITY
    STATUS      current
    DESCRIPTION
        "Xerox ColorQube 9202
            launch model, configuration 2, version 2.
            A complete product identifier."
    ::= { xcmPidColorQube9202C2 2 }
        -- ::= {1.3.6.1.4.1.253.8.62.1.24.1.2.2.2}



-- ColorQube 9200 Family  9203 Model

xcmPidColorQube9203 OBJECT-IDENTITY
    STATUS      current
    DESCRIPTION
        "Xerox ColorQube 9203 model identifier
           (not a complete product identifier)."
    ::= { xcmPidColorQube9200 3 }
        -- ::= {1.3.6.1.4.1.253.8.62.1.24.1.3}
            -- => SAP PID string = "H13"
            -- => USB PID string = 22071 = 0x5637
            -- => Compatible ID = XR_PS_Office_Color
--
-- PLEASE NOTE:
-- The MODEL NAME used for the PNP ID   "ColorQube 9203"
-- The generated PNP PID are only valid for that MODEL NAME
--
            -- => PNP ID ColorQube 9203 XeroxColorQube_92034E7B

-- ColorQube Model 9203 Configuration One
--      Common Board Controller (CBC)

xcmPidColorQube9203C1 OBJECT-IDENTITY
    STATUS      current
    DESCRIPTION
        "Xerox ColorQube 9203
           model and configuration 1 identifier
           (not a complete product identifier)."


    ::= { xcmPidColorQube9203 1 }
        -- ::= {1.3.6.1.4.1.253.8.62.1.24.1.3.1}

xcmPidColorQube9203C1V1 OBJECT-IDENTITY
    STATUS      current
    DESCRIPTION
        "Xerox ColorQube 9203
            launch model, configuration 1, version 1.
            A complete product identifier."
    ::= { xcmPidColorQube9203C1 1 }
        -- ::= {1.3.6.1.4.1.253.8.62.1.24.1.3.1.1}

xcmPidColorQube9203C1V2 OBJECT-IDENTITY
    STATUS      current
    DESCRIPTION
        "Xerox ColorQube 9203
            launch model, configuration 1, version 2.
            A complete product identifier."
    ::= { xcmPidColorQube9203C1 2 }
        -- ::= {1.3.6.1.4.1.253.8.62.1.24.1.3.1.2}

xcmPidColorQube9203C1V3 OBJECT-IDENTITY
    STATUS      current
    DESCRIPTION
        "Xerox ColorQube 9203
            launch model, configuration 1, version 3.
            A complete product identifier."
    ::= { xcmPidColorQube9203C1 3 }
        -- ::= {1.3.6.1.4.1.253.8.62.1.24.1.3.1.3}

-- ColorQube Model 9203 Configuration Two
--      Single Board Controller (SBC)

xcmPidColorQube9203C2 OBJECT-IDENTITY
    STATUS      current
    DESCRIPTION
        "Xerox ColorQube 9203
           model and configuration 2 identifier
           (not a complete product identifier)."
    ::= { xcmPidColorQube9203 2 }
        -- ::= {1.3.6.1.4.1.253.8.62.1.24.1.3.2}

xcmPidColorQube9203C2V1 OBJECT-IDENTITY
    STATUS      current
    DESCRIPTION
        "Xerox ColorQube 9203
            launch model, configuration 2, version 1.
            A complete product identifier."
    ::= { xcmPidColorQube9203C2 1 }
        -- ::= {1.3.6.1.4.1.253.8.62.1.24.1.3.2.1}

xcmPidColorQube9203C2V2 OBJECT-IDENTITY
    STATUS      current
    DESCRIPTION


        "Xerox ColorQube 9203
            launch model, configuration 2, version 2.
            A complete product identifier."
    ::= { xcmPidColorQube9203C2 2 }
        -- ::= {1.3.6.1.4.1.253.8.62.1.24.1.3.2.2}

--
--

-- ColorQube 8x00 Family

xcmPidColorQube8x00 OBJECT-IDENTITY


    STATUS      current
    DESCRIPTION
        "Xerox ColorQube 8x00 family identifier
           (not a complete product identifier)."
    ::= { xcmPidColorQube 3 }
        -- ::= {1.3.6.1.4.1.253.8.62.1.24.3}


-- ColorQube 8x00 Family  8700 Model

xcmPidColorQube8700 OBJECT-IDENTITY
    STATUS      current
    DESCRIPTION
        "Xerox ColorQube 8700 model identifier
           (not a complete product identifier)."
    ::= { xcmPidColorQube8x00 1 }
        -- ::= {1.3.6.1.4.1.253.8.62.1.24.3.1}
            -- => SAP PID string = "H31"
            -- => USB PID string = 22141 = 0x567d

xcmPidColorQube8700S OBJECT-IDENTITY
    STATUS      current
    DESCRIPTION
        "Xerox ColorQube 8700
           model and S configuration identifier
           (not a complete product identifier)."
    ::= { xcmPidColorQube8700 1 }
        -- ::= {1.3.6.1.4.1.253.8.62.1.24.3.1.1}
--
-- PLEASE NOTE:
-- The MODEL NAME used for the PNP ID   "ColorQube 8700S"
-- The generated PNP PID are only valid for that MODEL NAME
--
   -- => PNP ID ColorQube 8700S  XeroxColorQube_8700SE273

   -- => Compatible ID = XR_XPS_Office_Color

xcmPidColorQube8700Sv1 OBJECT-IDENTITY
    STATUS      current
    DESCRIPTION
        "Xerox ColorQube 8700
            launch model, S configuration, version 1.
            A complete product identifier."
    ::= { xcmPidColorQube8700S 1 }
        -- ::= {1.3.6.1.4.1.253.8.62.1.24.3.1.1.1}

xcmPidColorQube8700X OBJECT-IDENTITY
    STATUS      current
    DESCRIPTION
        "Xerox ColorQube 8700
           model and X configuration identifier


           (not a complete product identifier)."
    ::= { xcmPidColorQube8700 2 }
        -- ::= {1.3.6.1.4.1.253.8.62.1.24.3.1.2}
--
-- PLEASE NOTE:
-- The MODEL NAME used for the PNP ID   "ColorQube 8700X"
-- The generated PNP PID are only valid for that MODEL NAME
--
   -- => PNP ID ColorQube 8700X  XeroxColorQube_8700X2532

   -- => Compatible ID = XR_XPS_Office_Color

xcmPidColorQube8700Xv1 OBJECT-IDENTITY
    STATUS      current
    DESCRIPTION
        "Xerox ColorQube 8700
            launch model, X configuration, version 1.
            A complete product identifier."
    ::= { xcmPidColorQube8700X 1 }
        -- ::= {1.3.6.1.4.1.253.8.62.1.24.3.1.2.1}

xcmPidColorQube8700XF OBJECT-IDENTITY
    STATUS      current
    DESCRIPTION
        "Xerox ColorQube 8700
           model and XF configuration identifier
           (not a complete product identifier)."
    ::= { xcmPidColorQube8700 3 }
        -- ::= {1.3.6.1.4.1.253.8.62.1.24.3.1.3}
--
-- PLEASE NOTE:
-- The MODEL NAME used for the PNP ID   "ColorQube 8700XF"
-- The generated PNP PID are only valid for that MODEL NAME
--
    -- => PNP ID ColorQube 8700XF  XeroxColorQube_8700X2725

xcmPidColorQube8700XFv1 OBJECT-IDENTITY
    STATUS      current
    DESCRIPTION
        "Xerox ColorQube 8700
            launch model, XF configuration, version 1.
            A complete product identifier."
    ::= { xcmPidColorQube8700XF 1 }
        -- ::= {1.3.6.1.4.1.253.8.62.1.24.3.1.3.1}


-- ColorQube 8x00 Family  8900 Model

xcmPidColorQube8900 OBJECT-IDENTITY
    STATUS      current
    DESCRIPTION


        "Xerox ColorQube 8900 model identifier
           (not a complete product identifier)."
    ::= { xcmPidColorQube8x00 2 }
        -- ::= {1.3.6.1.4.1.253.8.62.1.24.3.2}
            -- => SAP PID string = "H32"
            -- => USB PID string = 22142 = 0x567e

xcmPidColorQube8900X OBJECT-IDENTITY
    STATUS      current
    DESCRIPTION
        "Xerox ColorQube 8900
           model and X configuration identifier
           (not a complete product identifier)."
    ::= { xcmPidColorQube8900 2 }
        -- ::= {1.3.6.1.4.1.253.8.62.1.24.3.2.2}
--
-- PLEASE NOTE:
-- The MODEL NAME used for the PNP ID   "ColorQube 8900X"
-- The generated PNP PID are only valid for that MODEL NAME
--
     -- => PNP ID ColorQube 8900X  XeroxColorQube_8900XCD30

xcmPidColorQube8900Xv1 OBJECT-IDENTITY
    STATUS      current
    DESCRIPTION
        "Xerox ColorQube 8900
            launch model, X configuration, version 1.
            A complete product identifier."
    ::= { xcmPidColorQube8900X 1 }
        -- ::= {1.3.6.1.4.1.253.8.62.1.24.3.2.2.1}

--

xcmPidColorQube8900S OBJECT-IDENTITY
    STATUS      current
    DESCRIPTION
        "Xerox ColorQube 8900
           model and S configuration identifier
           (not a complete product identifier)."
    ::= { xcmPidColorQube8900 3 }
        -- ::= {1.3.6.1.4.1.253.8.62.1.24.3.2.3}

-- PLEASE NOTE:
-- The MODEL NAME used for the PNP ID   "ColorQube 8900S"
-- The generated PNP PID are only valid for that MODEL NAME
--
     -- => PnP ID ColorQube 8900S  XeroxColorQube_8900S0A71

xcmPidColorQube8900Sv1 OBJECT-IDENTITY
    STATUS      current
    DESCRIPTION
        "Xerox ColorQube 8900


            launch model, S configuration, version 1.
            A complete product identifier."
    ::= { xcmPidColorQube8900S 1 }
        -- ::= {1.3.6.1.4.1.253.8.62.1.24.3.2.3.1}

-- ColorQube 9300 Family

xcmPidColorQube9300 OBJECT-IDENTITY
    STATUS      current
    DESCRIPTION
        "Xerox ColorQube 9300 family identifier
           (not a complete product identifier)."
    ::= { xcmPidColorQube 4 }
        -- ::= {1.3.6.1.4.1.253.8.62.1.24.4}

-- ColorQube Model 9301

xcmPidColorQube9301 OBJECT-IDENTITY
    STATUS      current
    DESCRIPTION
        "Xerox ColorQube 9301 model identifier
           (not a complete product identifier)."
    ::= { xcmPidColorQube9300 1 }
        -- ::= {1.3.6.1.4.1.253.8.62.1.24.4.1}
            -- => SAP PID string = "H41"
            -- => USB PID string = 22177 = 0x56A1
            -- => Compatible ID = XR_XPS_Office_Color
--
-- PLEASE NOTE:
-- The MODEL NAME used for the PNP ID   "ColorQube 9301"
-- The generated PNP PID are only valid for that MODEL NAME
--
            -- => PNP ID ColorQube 9301  XeroxColorQube_93014FAB

xcmPidColorQube9301C1 OBJECT-IDENTITY
    STATUS      current
    DESCRIPTION
        "Xerox ColorQube 9301
           model and configuration 1 identifier
           (not a complete product identifier)."
    ::= { xcmPidColorQube9301 1 }
        -- ::= {1.3.6.1.4.1.253.8.62.1.24.4.1.1}

xcmPidColorQube9301C1V1 OBJECT-IDENTITY
    STATUS      current
    DESCRIPTION
        "Xerox ColorQube 9301
            launch model, configuration 1, version 1.
            A complete product identifier."
    ::= { xcmPidColorQube9301C1 1 }
        -- ::= {1.3.6.1.4.1.253.8.62.1.24.4.1.1.1}



xcmPidColorQube9301C1V2 OBJECT-IDENTITY
    STATUS      current
    DESCRIPTION
        "Xerox ColorQube 9301
            launch model, configuration 1, version 2.
            A complete product identifier."
    ::= { xcmPidColorQube9301C1 2 }
        -- ::= {1.3.6.1.4.1.253.8.62.1.24.4.1.1.2}

-- ColorQube Model 9302

xcmPidColorQube9302 OBJECT-IDENTITY
    STATUS      current
    DESCRIPTION
        "Xerox ColorQube 9302 model identifier
           (not a complete product identifier)."
    ::= { xcmPidColorQube9300 2 }
        -- ::= {1.3.6.1.4.1.253.8.62.1.24.4.2}
            -- => SAP PID string = "H42"
            -- => USB PID string = 22178 = 0x56A2
            -- => Compatible ID = XR_XPS_Office_Color
--
-- PLEASE NOTE:
-- The MODEL NAME used for the PNP ID   "ColorQube 9302"
-- The generated PNP PID are only valid for that MODEL NAME
--
            -- => PNP ID ColorQube 9302  XeroxColorQube_93024EEB

xcmPidColorQube9302C1 OBJECT-IDENTITY
    STATUS      current
    DESCRIPTION
        "Xerox ColorQube 9302
           model and configuration 1 identifier
           (not a complete product identifier)."
    ::= { xcmPidColorQube9302 1 }
        -- ::= {1.3.6.1.4.1.253.8.62.1.24.4.2.1}

xcmPidColorQube9302C1V1 OBJECT-IDENTITY
    STATUS      current
    DESCRIPTION
        "Xerox ColorQube 9302
            launch model, configuration 1, version 1.
            A complete product identifier."
    ::= { xcmPidColorQube9302C1 1 }
        -- ::= {1.3.6.1.4.1.253.8.62.1.24.4.2.1.1}


xcmPidColorQube9302C1V2 OBJECT-IDENTITY
    STATUS      current
    DESCRIPTION


        "Xerox ColorQube 9302
            launch model, configuration 1, version 2.
            A complete product identifier."
    ::= { xcmPidColorQube9302C1 2 }
        -- ::= {1.3.6.1.4.1.253.8.62.1.24.4.2.1.2}

-- ColorQube Model 9303

xcmPidColorQube9303 OBJECT-IDENTITY
    STATUS      current
    DESCRIPTION
        "Xerox ColorQube 9303 model identifier
           (not a complete product identifier)."
    ::= { xcmPidColorQube9300 3 }
        -- ::= {1.3.6.1.4.1.253.8.62.1.24.4.3}
            -- => SAP PID string = "H43"
            -- => USB PID string = 22179 = 0x56A3
            -- => Compatible ID = XR_XPS_Office_Color
--
-- PLEASE NOTE:
-- The MODEL NAME used for the PNP ID   "ColorQube 9303"
-- The generated PNP PID are only valid for that MODEL NAME
--
            -- => PNP ID ColorQube 9303 XeroxColorQube_93038E2A

xcmPidColorQube9303C1 OBJECT-IDENTITY
    STATUS      current
    DESCRIPTION
        "Xerox ColorQube 9303
           model and configuration 1 identifier
           (not a complete product identifier)."
    ::= { xcmPidColorQube9303 1 }
        -- ::= {1.3.6.1.4.1.253.8.62.1.24.4.3.1}

xcmPidColorQube9303C1V1 OBJECT-IDENTITY
    STATUS      current
    DESCRIPTION
        "Xerox ColorQube 9303
            launch model, configuration 1, version 1.
            A complete product identifier."
    ::= { xcmPidColorQube9303C1 1 }
        -- ::= {1.3.6.1.4.1.253.8.62.1.24.4.3.1.1}


xcmPidColorQube9303C1V2 OBJECT-IDENTITY
    STATUS      current
    DESCRIPTION
        "Xerox ColorQube 9303
            launch model, configuration 1, version 2.
            A complete product identifier."
    ::= { xcmPidColorQube9303C1 2 }
        -- ::= {1.3.6.1.4.1.253.8.62.1.24.4.3.1.2}


--
--

----------------------------------------------------------------
-- Arc for FX Requested PIDs
----------------------------------------------------------------

xcmPidFXSystems OBJECT-IDENTITY
    STATUS      current
    DESCRIPTION
        "Fuji Xerox Systems product line identifier
                 (not a complete product identifier)."
    ::= { xcmPidProductIdentifiers 30 }
        -- ::= {1.3.6.1.4.1.253.8.62.1.30}


--
--

----------------------------------------------------------------
-- Xerox Entry-level Production Color PIDs
----------------------------------------------------------------


--
--

----------------------------------------------------------------
-- Xerox Entry-level Production Color PIDs
----------------------------------------------------------------

xcmPidEPCProductLine OBJECT-IDENTITY
    STATUS      current
    DESCRIPTION
        "Xerox Entry-level Production Color product line
         identifier (not a complete product identifier)."
    ::= { xcmPidProductIdentifiers 31 }
        -- ::= {1.3.6.1.4.1.253.8.62.1.31}

--
--

----------------------------------------------------------------
-- Xerox Light Production Monochrome PIDs
----------------------------------------------------------------

xcmPidLPMProductLine OBJECT-IDENTITY
    STATUS      current
    DESCRIPTION
        "Xerox Light Production Monochrome product line
         identifier (not a complete product identifier)."
    ::= { xcmPidProductIdentifiers 32 }
        -- ::= {1.3.6.1.4.1.253.8.62.1.32}

--
--

----------------------------------------------------------------
-- Xerox Digital Printing Press PIDs
----------------------------------------------------------------

xcmPidDigitalPrintingPressProductLine OBJECT-IDENTITY
    STATUS      current
    DESCRIPTION
        "Xerox Digital Printing Press product line
         identifier (not a complete product identifier)."
    ::= { xcmPidProductIdentifiers 33 }
        -- ::= {1.3.6.1.4.1.253.8.62.1.33}


--
--

----------------------------------------------------------------
-- Dedicated Print Servers / External NICs
-- (dedicated and local to target printer)
----------------------------------------------------------------

xcmPidDedPrintServers OBJECT-IDENTITY
    STATUS      current
    DESCRIPTION
        "Dedicated print servers product line identifier
                 (not a complete product identifier)."
    ::= { xcmPidProductIdentifiers 8 }
        -- ::= {1.3.6.1.4.1.253.8.62.1.8}

--
--

xcmPidPhaserPrintServer OBJECT-IDENTITY
    STATUS      current
    DESCRIPTION
        "Xerox Fast Port dedicated print server product type identifier
                 (not a complete product identifier)."
    ::= { xcmPidDedPrintServers 2 }
        -- ::= {1.3.6.1.4.1.253.8.62.1.8.2}

-- Phaser EX7750 Family, 35/35 ppm Color Laser Printer
-- with EFI Fiery Network Controller
-- EX7750 is the Base configuration (no network, 64MB)

xcmPidPhaserEX7750 OBJECT-IDENTITY
    STATUS      current
    DESCRIPTION
        "Xerox Phaser Fiery model identifier
                 (not a complete product identifier)."
    ::= { xcmPidPhaserPrintServer 1 }
        -- ::= {1.3.6.1.4.1.253.8.62.1.8.2.1}
            -- => SAP PID string = "821"
            -- => USB PID string = 10441 = 0x28C9

xcmPidPhaserEX7750GX OBJECT-IDENTITY
    STATUS      current
    DESCRIPTION
        "Xerox Phaser EX7750 Controller with Phaser 7750GX
         Printer configuration."
    ::= { xcmPidPhaserEX7750 1 }
        -- ::= {1.3.6.1.4.1.253.8.62.1.8.2.1.1}

xcmPidPhaserEX7750DXF OBJECT-IDENTITY
    STATUS      current
    DESCRIPTION
        "Xerox Phaser EX7750 Controller with Phaser 7750DXF
         Printer configuration."
    ::= { xcmPidPhaserEX7750 2 }
        -- ::= {1.3.6.1.4.1.253.8.62.1.8.2.1.2}
END
