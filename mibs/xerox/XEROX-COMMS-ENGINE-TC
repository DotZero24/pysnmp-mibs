XEROX-COMMS-ENGINE-TC DEFINITIONS ::= BEGIN

--  Module: Communications Engine TC
--  File:   50commtc.mib
--  Date:   17 September 2001 - Version 5.10.pub

--  Textual Conventions companion to the Comms Engine MIB

IMPORTS
    MODULE-IDENTITY,
        OBJECT-TYPE
            FROM SNMPv2-SMI             -- IETF RFC 1442/1902/2578
    TEXTUAL-CONVENTION
            FROM SNMPv2-TC              -- IETF RFC 1443/1903/2579
    xeroxCommonMIB
            FROM XEROX-COMMON-MIB;

xcmCommsEngineTC MODULE-IDENTITY
    LAST-UPDATED "0209170000Z" -- 17 September 2002
    ORGANIZATION "Xerox Corporation - XCMI Working Group"
    CONTACT-INFO
        "           XCMI Editors
        Email:      coherence@crt.xerox.com
        "
    DESCRIPTION
        "Version:   5.10.pub

        The TC module for textual conventions, enumerated types, OIDs,
        and other volatile elements of the companion Communications
        Engine MIB, which supports detailed protocol stack graphing,
        and active management of communications protocol stacks,
        communications end system applications, communications
        intermediate systems, and communications gateways for network
        accessible host systems.

        Copyright (C) 1995-2002 Xerox Corporation. All Rights Reserved."
    ::= { xeroxCommonMIB 60 }

--
--          The Comms Engine TC
--
--          Textual Conventions


XcmCommsMgmtCommandRequest ::= TEXTUAL-CONVENTION
    STATUS      current
    DESCRIPTION
        "A write to this object by an (authorized) management station
        SHALL invokes a command for this protocol entity.
        A read of this object SHALL return the command currently in
        progress or last completed.
        It is mandatory that a conforming management agent ensure that
        the contents of this object remain 'in bounds' - an undefined
        value SHALL be replaced by 'none' - ie, although rejected with
        error in the SetResponse PDU, this object SHALL NOT contain any
        such undefined value.  At system initialization, this object
        SHALL contain 'none'.

      * 'none' - NO action(s) SHALL be taken, except agent SHALL clear
        '...CommandData' and set '...CommandStatus' to 'noError'.
      * 'test' or 'manage' - the associated '...CommandData' object
        SHALL be specified in the same SetRequest PDU.
      * all other commands - the associated '...CommandData' object
        MAY be specified in the same SetRequest PDU.
      * 'disable' - this protocol SHALL transition immediately (ie,
        without attempting graceful quiesce) to the 'inoperative' state.
      * 'enable', 'resetWarm', 'resetCold', or 'resetFactory' - the
        final state SHALL be either 'closed' or 'opened'.
      * 'test' - this protocol SHALL transition immediately to the
        'testing' state; otherwise, it is a local matter (ie, protocol
        specific) how this command is processed; however, the associated
        '...CommandData' object SHALL be specified.
      * 'enable' - it is a local matter (ie, protocol specific) whether
        the final state SHALL be 'closed' or 'opened'; however, if
        'closed' results, an 'open' SHALL yield 'opened'.
      * 'close', 'recover', or 'open' - this protocol SHALL make a 'best
        effort' to make an orderly transition to the requested final
        state.
      * 'quiesce' - this protocol SHALL make a 'best effort' to make a
        graceful transition to the 'closed' state.
      * 'resetCounters' - all comms counters SHALL be reset to zero.
      * 'resetWarm' - a comms 'warm restart' SHALL be performed.
      * 'resetCold' - a comms 'cold restart' SHALL be performed (ie, a
        power cycle reset).
      * 'resetFactory' - all factory defaults SHALL be restored, and a
        comms 'cold restart' SHALL be performed (ie, a power cycle
        reset).
      * 'flushInput' - all comms input (in progress or internally
        queued) SHALL be gracefully flushed
      * 'flushOutput' - all comms output (in progress or internally
        queued) SHALL be gracefully flushed
      * 'flushInOut' - all comms input and output output (in progress
        or internally queued) SHALL be gracefully flushed
      * 'manage' - it is a local matter (ie, product specific) how this
        command is processed; however, the associated '...CommandData'
        object SHALL be specified.

        Note:   All of the POSIX and XCMI comms level operations are


        taken from the POSIX System Admin std (IEEE 1387.4) and aligned
        with the high-end XCMI System Admin MIB."
    REFERENCE
        "See:   'dot5Commands' in IEEE 802.5 Token Ring MIB (RFC 1748).
        Compare:    'ifOperStatus' (current) and 'ifAdminStatus'
        (desired) in the Interfaces Group of IETF MIB-II (RFC 1213);
        'RowStatus' textual convention in IETF SMIv2 (RFC 1902/2578)."
    SYNTAX      INTEGER {
        none(1),
        disable(2),                     -- to 'inoperative' state
        test(3),                        -- to 'testing' state
        enable(4),                      -- to 'closed' (or 'opened')
        close(5),                       -- to 'closed' from 'opened'
        recover(6),                     -- to 'opened' from 'recovering'
        open(7),                        -- to 'opened' from 'closed'
        quiesce(8),                     -- to 'closed' gracefully
        resetCounters(9),               -- zero all protocol counters
        resetWarm(10),                  -- warm start - current defaults
        resetCold(11),                  -- cold start - current defaults
        resetFactory(12),               -- cold start - factory defaults
        flushInput(13),                 -- flush all input
        flushOutput(14),                -- flush all output
        flushInOut(15),                 -- flush all input and output
        manage(16),                     -- manage command, any state
        --  POSIX - Communications level operations (on host system)
        commsCreate(1701),              -- 'pdcreate' (create comms)
        commsDelete(1702),              -- 'pddelete' (delete comms)
        commsList(1703),                -- 'pdls' (list svc attributes)
        commsSet(1704),                 -- 'pdset' (set svc attributes)
        commsClean(1705),               -- 'pdclean' (remove all paths)
        commsDisable(1706),             -- 'pddisable' (stop new paths)
        commsEnable(1707),              -- 'pdenable' (allow new paths)
        commsPause(1708),               -- 'pdpause' (pause comms)
        commsResume(1709),              -- 'pdresume' (resume comms)
        commsShutdown(1710),            -- 'pdshutdown' (end comms)
        --  XCMI - Communications level extensions (on host system)
        commsManage(2701),              -- manage comms object(s)
        commsRestart(2702),             -- restart comms
        commsInstall(2721),             -- install comms object(s)
        commsUpgrade(2722),             -- upgrade comms object(s)
        commsBackup(2723),              -- backup comms object(s)
        commsRestore(2724),             -- restore comms object(s)
        commsConfigure(2725),           -- configure comms object(s)
        commsDiagnose(2726),            -- diagnose comms object(s)
        commsResetCounters(2731),       -- reset comms counters
        commsResetWarm(2732),           -- warm reset (no power cycle)
        commsResetCold(2733),           -- cold reset (w/ power cycle)
        commsResetFactory(2734),        -- factory defaults reset
        commsLogin(2741),               -- login w/ authentication
        commsLogout(2742)               -- logout w/ authentication
    }


XcmCommsMgmtCommandData ::= TEXTUAL-CONVENTION
    STATUS      current
    DESCRIPTION
        "A write to this object specifies:  a) a 'test' command subtype
        and any accompanying 'test' protocol specific data; or b) a
        'manage' command subtype and any accompanying 'manage' protocol
        specific data; or c) protocol specific data accompanying any
        other command.
        A read of this object SHALL return the data (if any) which
        accompanied the current or last completed command.
        Note:   Conforming implementations are STRONGLY encouraged to
        consider support of encrypted password writes in this object."
    REFERENCE
        "See:   Appropriate standards for protocol specific tests"
    SYNTAX      OCTET STRING (SIZE (0..255))

XcmCommsMgmtState ::= TEXTUAL-CONVENTION
    STATUS      current
    DESCRIPTION
        "A relatively generic description of the current state of
        this communications entity.

        Usage:  It is desirable that the implementor report the states
        of all stack layers corresponding to conceptual rows in the
        'xcmCommsStackTable' accurately.  The use of the value 'unknown'
        SHOULD NOT be the general case, unless the host system has NO
        local instrumentation of the stack layers (such as the DMTF DMI,
        Desktop Management Interface) - when ANY local instrumentation
        of the stack layers is available, the implementor SHOULD
        accurately report stack layer states."
    SYNTAX      INTEGER {
        other(1),
        unknown(2),
        inoperative(3),                 -- permanent inactive state
        testing(4),                     -- local or remote tests active
        closed(5),                      -- active but closed state
        closing(6),                     -- transition to closed state
        opening(7),                     -- transition to opened state
        recovering(8),                  -- recovery to opened state
        opened(9)                       -- active and opened state
    }

XcmCommsMgmtConditions ::= TEXTUAL-CONVENTION
    STATUS      current
    DESCRIPTION
        "A relatively generic description of the current conditions of
        this communications entity.

        The definition of 'conditions' is partially entity specific
        and is NOT completely amenable to generalization.  However, a
        base set of values (which MAY be extended for each entity type)
        is given below:

              1 : disableInProgress                  (normally NOT used)


              2 : testInProgress                              (optional)
              4 : enableInProgress
              8 : closeInProgress
             16 : recoverInProgress                           (optional)
             32 : openInProgress
             64 : quiesceInProgress                           (optional)
            128 : resetCountersInProgress            (normally NOT used)
            256 : resetWarmInProgress                 (current defaults)
            512 : resetColdInProgress                 (current defaults)
           1024 : resetFactoryInProgress              (factory defaults)
           2048 : manageInProgress                            (optional)
           4096 : incomingTestInProgress                      (optional)
           8192 : outgoingTestInProgress                      (optional)
          16384 : incomingAuthorizeInProgress                 (optional)
          32768 : outgoingAuthorizeInProgress                 (optional)
          65536 : incomingFlowControlInProgress               (optional)
         131072 : outgoingFlowControlInProgress               (optional)

        The above basic 'conditions' remember the original intent of the
        current command, when it results in several state transitions
        before arriving at the 'final' state.  They augment the state
        info available from a variable of type 'XcmCommsMgmtState',
        by graphing the 'progress' of a command through the states.

        Usage:  It is desirable that the implementor report 'conditions'
        of all stack layers corresponding to conceptual rows in the
        'xcmCommsStackTable' accurately.  'Conditions' occur within or
        across 'states' in a finite state machine (FSM) implementation
        of a communications entity.  They represent both transient and
        long term constraints and circumstances."
    SYNTAX      INTEGER (0..2147483647)  -- biggest int = 2**31-1

XcmCommsStackPosition ::= TEXTUAL-CONVENTION
    STATUS      current
    DESCRIPTION
        "A relatively generic description of the current
        position of this protocol entity (ie, this layer) in a protocol
        stack.

        Composed of one or more of the following position descriptors,
        arithmetically added together:

        bottom      :  1
        middle      :  2
        top         :  4
        lowerMux    :  8
        upperMux    : 16

        Usage:  A conceptual row in 'xcmCommsStackTable', which occupies
        a 'bottom' position in a protocol stack AND has a corresponding
        row in the 'xcmCommsStackXrefTable', SHOULD have valid
        references in 'xcmCommsStackXrefIfIndex' (to IETF MIB-II) and
        'xcmCommsStackXrefHrCommDevIndex' (to IETF Host Resources MIB).


        Usage:  A conceptual row in 'xcmCommsStackTable' which occupies
        a 'lowerMux' and/or an 'upperMux' position in a protocol stack
        SHALL have one (or two) valid corresponding conceptual
        rows in the 'xcmCommsMuxTable', as the conventionally used
        'xcmStack[Lower|Upper]StackIndex' objects take on zero values
        for multiplexors (thus breaking the graph of the stack layers,
        without the use of the 'xcmCommsMuxTable').

        Note:   In many real open systems which are internet attached,
        IETF IP (connectionless mode) network layer has a position of:
        a)  'middle' - neither top nor bottom;
        b)  'lowerMux' - above both OSI LLC (ISO 8802-2) and OSI CONP
            (CCITT X.25 over LAPB) datalinks; and
        c)  'upperMux' - below both IETF TCP (connection mode) and
            IETF UDP (connectionless mode) transports."
    SYNTAX      INTEGER {
        bottom(1),                      -- simple bottom layer
        middle(2),                      -- simple middle layer
        top(4),                         -- simple top    layer
        bottomAndTop(5),                -- dumb interface
        lowerMux(8),                    -- NOT used stand-alone
        bottomLowerMux(9),              -- bottom and lowerMux
        middleLowerMux(10),             -- middle and lowerMux
        topLowerMux(12),                -- top    and lowerMux
        upperMux(16),                   -- NOT used stand-alone
        bottomUpperMux(17),             -- bottom and upperMux
        middleUpperMux(18),             -- middle and upperMux
        topUpperMux(20),                -- top    and upperMux
        bottomBothMux(25),              -- bottom, lowerMux, upperMux
        middleBothMux(26),              -- middle, lowerMux, upperMux
        topBothMux(28)                  -- top,    lowerMux, upperMux
    }

XcmCommsStackExtPurpose ::= TEXTUAL-CONVENTION
    STATUS      current
    DESCRIPTION
        "A relatively generic description of the current
        purpose of this stack layer/sublayer during normal operation.

        Usage:  Please note that 'layerInterWorkingUnit' would correctly
        describe:  a datalink MAC sublayer bridge (eg, IEEE 802.1D); a
        network layer relay (X.25 backbone switch); a network layer
        gateway (eg, X.25 <--> Telex IWU); or a transport layer gateway
        (eg, OSI COTP over X.25 <--> OSI COTP over OSI CLNP).
        Also note that 'systemInterWorkingUnit' would correctly describe
        an application layer gateway (eg, X/Open XDPA <--> Novell NDPS,
        for print services based on DPA, ISO 10175)."
    SYNTAX      INTEGER {
        other(1),
        unknown(2),
        layerOther(11),                 -- eg, ARP (routing protocol)
        layerDataTransfer(12),          -- non-application layer
        layerManagement(13),            -- eg, OSI TLMI (transport mgmt)


        layerSecurity(14),              -- eg, OSI TLSP (transport sec)
        layerInterWorkingUnit(15),      -- lower layer relay or gateway
        systemOther(16),
        systemDataTransfer(17),         -- application layer program
        systemManagement(18),           -- eg, IETF SNMP
        systemSecurity(19),             -- eg, CCITT X.800 series
        systemInterWorkingUnit(20)      -- application layer gateway
    }

XcmCommsStackExtRole ::= TEXTUAL-CONVENTION
    STATUS      current
    DESCRIPTION
        "A relatively generic description of the current
        role of this stack layer/sublayer during normal operation.

        Usage:  The values 'peer', 'primary', and 'secondary' are
        standard roles for non-application layer protocols.  The value
        'multicaster' indicates a role of multicast host (ie, all remote
        systems would play roles of 'secondary').  The values 'client'
        and 'server', which are analogous to 'primary' and 'secondary',
        are normally used to refer to application layer protocols, along
        with 'peer' (eg, IBM SNA APPC applications)."
    SYNTAX      INTEGER {
        other(1),
        unknown(2),
        peer(11),                       -- association peer (balanced)
        primary(12),                    -- association initiator
        secondary(13),                  -- association responder
        multicaster(14),                -- association multicaster
        client(15),                     -- analogous to primary
        server(16)                      -- analogous to secondary
    }

XcmCommsStackExtSuite ::= TEXTUAL-CONVENTION
    STATUS      current
    DESCRIPTION
        "The current protocol suite of this protocol entity
        (stack layer or sublayer)."
    SYNTAX      INTEGER {
        other(1),
        unknown(2),
        osilan(11),                     -- OSI LAN (ISO/IEEE 802.x)
        osiman(12),                     -- OSI MAN (ISO/IEEE 802.6)
        osiwan(13),                     -- OSI WAN (ISO/CCITT)
        internet(14),                   -- Internet Protocol Suite
        ibmsna(15),                     -- IBM SNA
        ibmbisync(16),                  -- IBM Bisync
        decnet(17),                     -- DEC DECnet
        appletalk(18),                  -- Apple AppleTalk
        netware(19),                    -- Novell NetWare
        vines(20),                      -- Banyan Vines
        lantastic(21),                  -- Lantastic
        lanserver(22),                  -- IBM LAN Server
        lanmanager(23),                 -- Microsoft LAN Manager


        ntas(24),                       -- Microsoft NT/AS
        netbios(25),                    -- NetBIOS Generic
        netbeui(26),                    -- NetBEUI Generic
        serial(27),                     -- Serial Ports
        parallel(28),                   -- Parallel Ports
        directPrint(29),                -- Direct Print Serial/Parallel
        usb(30)                         -- Universal Serial Bus Ports
    }

XcmCommsStackExtSuiteVersion ::= TEXTUAL-CONVENTION
    STATUS      current
    DESCRIPTION
        "The current protocol suite version of this protocol entity
        (stack layer or sublayer).

        Usage:  The following enumeration is used to unambiguously
        identify a specific protocol suite version (or generic version),
        without resort to textual strings.

        Note:   The following enumeration values are composed of two
        N-digit elements (left-to-right):
        a)  First, the two-digit enumeration value of the protocol suite
            (from 'XcmCommsStackExtSuite'); and
        b)  Second, a unique four-digit identifier."
    SYNTAX      INTEGER {
        other(1),
        unknown(2),
        osilanVersions(110101),         -- OSI LAN (ISO/IEEE 802.x)
        osimanVersions(120101),         -- OSI MAN (ISO/IEEE 802.6)
        osiwanVersions(130101),         -- OSI WAN (ISO/CCITT)
        internetVersions(140101),       -- Internet Protocol Suite
        ibmsnaVersions(150101),         -- IBM SNA
        ibmbisyncVersions(160101),      -- IBM Bisync
        decnetVersions(170101),         -- DEC DECnet

        appletalkVersions(180101),      -- Apple AppleTalk
        appletalkPhase1(181999),        -- Apple AppleTalk Phase 1
        appletalkPhase2(182999),        -- Apple AppleTalk Phase 2

        netwareVersions(190101),        -- Novell NetWare
        netware2x(192999),              -- Novell NetWare 2.x
        netware3x(193999),              -- Novell NetWare 3.x
        netware4x(194999),              -- Novell NetWare 4.x

        vinesVersions(200101),          -- Banyan Vines
        lantasticVersions(210101),      -- Lantastic
        lanserverVersions(220101),      -- IBM LAN Server
        lanmanagerVersions(230101),     -- Microsoft LAN Manager
        ntasVersions(240101),           -- Microsoft NTAS
        netbiosVersions(250101),        -- NetBIOS Generic
        netbeuiVersions(260101),        -- NetBEUI Generic
        serialVersions(270101),         -- Serial Ports
        parallelVersions(280101),       -- Parallel Ports
        directPrintVersions(290101),    -- Direct Print Serial/Parallel


        usbVersions(300101)             -- Universal Serial Bus Ports
    }

XcmCommsStackExtLayer ::= TEXTUAL-CONVENTION
    STATUS      current
    DESCRIPTION
        "The closest approximate layer in the OSI Reference Model
        (CCITT X.200 | ISO 7498) to the current behavior
        of this stack layer or sublayer.

        Usage:  Note that this value MAY NOT be strictly
        accurate.  A number of legacy proprietary protocol suites use
        unusual and irregular names for their protocols (eg, frequent
        assignment of relatively simplistic transport protocols to the
        OSI Reference Model session layer in some protocol suites).

        Note:   The following enumeration values are biased by ten (10),
        for ease of use, from the original OSI Reference Model."
    SYNTAX      INTEGER {
        other(1),
        unknown(2),
        physical(11),
        datalink(12),
        network(13),
        transport(14),
        session(15),
        presentation(16),
        application(17)
    }

XcmCommsStackExtProtocol ::= TEXTUAL-CONVENTION
    STATUS      current
    DESCRIPTION
        "The specific protocol (within a given protocol suite) currently
        configured for this stack layer or sublayer.

        Usage:  The following enumeration is used to unambiguously
        identify a specific protocol (within a given protocol suite),
        without resort to textual strings.

        Note:   The following enumeration values are composed of three
        two-digit elements (left-to-right):
        a)  First, the two-digit enumeration value of the protocol suite
            (from 'XcmCommsStackExtSuite');
        b)  Second, the two-digit enumeration value of the OSI Reference
            Model layer (from 'XcmCommsStackExtLayer'); and
        c)  Third, a unique two-digit identifier."
    SYNTAX      INTEGER {
        other(1),
        unknown(2),

        osilanSuite(110101),            -- OSI LAN (ISO/IEEE 802.x)
            --  PMD (Physical Medium Dependent)
        osilan8023PMD(111103),          -- OSI LAN 802.3 PMD (physical)


        osilan8024PMD(111104),          -- OSI LAN 802.4 PMD (physical)
        osilan8025PMD(111105),          -- OSI LAN 802.5 PMD (physical)
        osilanFDDIPMD(111107),          -- OSI LAN FDDI PMD (physical)
        osilan80211PMD(111108),         -- OSI LAN 802.11 PMD (physical)
            --  PHY (Physical Medium Independent)
        osilan8023PHY(111113),          -- OSI LAN 802.3 PHY (physical)
        osilan8024PHY(111114),          -- OSI LAN 802.4 PHY (physical)
        osilan8025PHY(111115),          -- OSI LAN 802.5 PHY (physical)
        osilanFDDIPHY(111117),          -- OSI LAN FDDI PHY (physical)
            --  MAC (Medium Access Control)
        osilan80211PHY(111118),         -- OSI LAN 802.11 PHY (physical)
        osilan8023MAC(111203),          -- OSI LAN 802.3 MAC (datalink)
        osilan8024MAC(111204),          -- OSI LAN 802.4 MAC (datalink)
        osilan8025MAC(111205),          -- OSI LAN 802.5 MAC (datalink)
        osilanFDDIMAC(111207),          -- OSI LAN FDDI MAC (datalink)
        osilan80211MAC(111208),         -- OSI LAN 802.11 MAC (datalink)
            --  SMT (Station Management)
        osilan8025SMT(111215),          -- OSI LAN 802.5 SMT (datalink)
        osilanFDDISMT(111217),          -- OSI LAN FDDI SMT (datalink)
        osilan80211SMT(111218),         -- OSI LAN 802.11 SMT (datalink)
            --  LLC (Logical Link Control)
        osilan8022LLC(111221),          -- OSI LAN 802.2 LLC
            --  LLC SNAP (Subnetwork Address Protocol)
        osilan8022LLCSNAP(111222),      -- OSI LAN 802.2 LLC SNAP
            --  LMMP (LAN/MAN Management Protocol)
        osilan8021BLMMP(111232),        -- OSI LAN 802.1B LMMP (mgmt)
            --  BRG (Bridge)
        osilan8021DBRG(111234),         -- OSI LAN 802.1D BRG (bridge)
            --  SDE (Secure Data Exchange)
        osilan80210SDE(111241),         -- OSI LAN 802.10 SDE (security)

        osimanSuite(120101),            -- OSI MAN (ISO/IEEE 802.6)
        osiman8026PMD(121106),          -- OSI MAN 802.6 PMD (physical)
        osiman8026PHY(121116),          -- OSI MAN 802.6 PHY (physical)
        osiman8026MAC(121206),          -- OSI MAN 802.6 MAC (datalink)
        osiman8026SMT(121216),          -- OSI MAN 802.6 SMT (datalink)

        osiwanSuite(130101),            -- OSI WAN (ISO/CCITT)
        osiwanHdlcABM(131201),          -- OSI WAN HDLC ABM
        osiwanHdlcARM(131202),          -- OSI WAN HDLC ARM
        osiwanHdlcNRM(131203),          -- OSI WAN HDLC NRM
        osiwanHdlcABME(131211),         -- OSI WAN HDLC ABME
        osiwanHdlcARME(131212),         -- OSI WAN HDLC ARME
        osiwanHdlcNRME(131213),         -- OSI WAN HDLC NRME
        osiwanHdlcLAPB(131221),         -- OSI WAN HDLC LAPB (X.25)
        osiwanHdlcLAPD(131224),         -- OSI WAN HDLC LAPD (ISDN)
        osiwanFax(131241),              -- OSI WAN Fax (facsimile)
        osiwanPSTN(131251),             -- OSI WAN PSTN (analog phone)
        osiwanISDN(131261),             -- OSI WAN ISDN (digital phone)
        osiwanCLNP(131301),             -- OSI WAN CLNP (ISO 8473)
        osiwanCONP(131302),             -- OSI WAN CONP (CCITT X.25)
        osiwanESIS(131303),             -- OSI WAN ESIS (routing)
        osiwanISIS(131304),             -- OSI WAN ISIS (routing)
        osiwanCLTP(131401),             -- OSI WAN CLTP (ISO 8602)


        osiwanCOTP(131402),             -- OSI WAN COTP (CCITT X.224)
        osiwanCLSP(131501),             -- OSI WAN CLSP (ISO 9548)
        osiwanCOSP(131502),             -- OSI WAN COSP (CCITT X.225)
        osiwanCLPP(131601),             -- OSI WAN CLPP (ISO 9576)
        osiwanCOPP(131602),             -- OSI WAN COPP (CCITT X.226)
        osiwanACSE(131701),             -- OSI WAN ACSE (CCITT X.227)
        osiwanRTSE(131702),             -- OSI WAN RTSE (CCITT X.228)
        osiwanROSE(131703),             -- OSI WAN ROSE (CCITT X.229)
        osiwanCCR(131704),              -- OSI WAN CCR (ISO 9805)
        osiwanDPA(131713),              -- OSI WAN DPA (ISO 10175)
        osiwanFTAM(131714),             -- OSI WAN FTAM (ISO 8571)
        osiwanVT(131716),               -- OSI WAN VT (ISO 9041)
        osiwanMHS(131740),              -- OSI WAN MHS (CCITT X.400)
        osiwanDS(131750),               -- OSI WAN DS (CCITT X.500)
        osiwanDAP(131751),              -- OSI WAN DAP (CCITT X.500)
        osiwanDSP(131752),              -- OSI WAN DSP (CCITT X.500)
        osiwanMgmt(131770),             -- OSI WAN Mgmt (CCITT X.700)
        osiwanCMIP(131771),             -- OSI WAN CMIP (CCITT X.711)
        osiwanSec(131780),              -- OSI WAN Sec (CCITT X.800)

        internetSuite(140101),          -- Internet Protocol Suite
        internetSLIP(141201),           -- Internet SLIP (datalink)
        internetPPP(141202),            -- Internet PPP (datalink)
        internetIP(141301),             -- Internet IP (network)
        internetICMP(141302),           -- Internet ICMP (network)
        internetARP(141303),            -- Internet ARP (routing)
        internetDHCP(141304),           -- Internet DHCP (routing/boot)
        internetBOOTP(141305),          -- Internet BOOTP (routing/boot)
        internetRARP(141306),           -- Internet RARP (routing/boot)
        internetIPv6(141310),           -- Internet IPv6 (network)
        internetUDP(141401),            -- Internet UDP (CL transport)
        internetTCP(141402),            -- Internet TCP (CO transport)
        internetPing(141404),           -- Internet Ping (echo)
        internetSSL3(141405),           -- Internet SSL3 (security)
        internetTLS(141406),            -- Internet TLS (security)
        internetRaw(141501),            -- Internet Raw Print (printing)
        internetIPP(141502),            -- Internet IPP (printing)
        internetLPR(141503),            -- Internet LPR (printing)
        internetFTP(141504),            -- Internet FTP (filing)
        internetSMTP(141505),           -- Internet SMTP (email)
        internetTelnet(141506),         -- Internet Telnet (terminal)
        internetDNS(141507),            -- Internet DNS (directory)
        internetTFTP(141508),           -- Internet TFTP (filing)
        internetHTTP(141509),           -- Internet HTTP (WWW)
        internetSNMP(141510),           -- Internet SNMP (mgmt)
        internetSNMPv1(141511),         -- Internet SNMP V1 (mgmt)
        internetSNMPv2(141512),         -- Internet SNMP V2 (mgmt)
        internetSNMPv3(141513),         -- Internet SNMP V3 (mgmt)
        internetPOP3(141514),           -- Internet POP3 (email access)
        internetIMAP4(141515),          -- Internet IMAP4 (email access)
        internetFax(141516),            -- Internet Fax (internet fax)
        internetWINS(141519),           -- Internet WINS (directory)
        internetSunOncSuite(141520),    -- Internet Sun ONC Suite
        internetSunOncNIS(141521),      -- Internet Sun ONC NIS


        internetSunOncPlusNIS(141522),  -- Internet Sun ONC+ NIS+
        internetSunOncRPC(141523),      -- Internet Sun ONC RPC (NIS)
        internetSunOncPlusRPC(141524),  -- Internet Sun ONC+ RPC (NIS+)
        internetSunTiRPC(141525),       -- Internet Sun Trans Indep RPC
        internetOsfDceSuite(141530),    -- Internet OSF DCE Suite
        internetOsfDceCDS(141531),      -- Internet OSF DCE CDS (dir)
        internetOsfDceRPC(141532),      -- Internet OSF DCE RPC (w/ CDS)
        internetOsfDceKerberos(141533), -- Internet OSF DCE Kerberos
        internetOsfDmeSuite(141540),    -- Internet OSF DME Suite (mgmt)
        internetLDAP(141551),           -- Internet LDAP (directory)
                                        -- mappings over 'internetTCP'
                                        -- and 'osiwanCOTP' (RFC 1777)
                                        -- to 'osiwanDS' (OSI directory)
        internetCLDAP(141552),          -- Internet CLDAP (directory)
                                        -- mappings over 'internetUDP'
                                        -- and 'osiwanCLTP' (RFC 1798)
                                        -- to 'osiwanDS' (OSI directory)
        internetSalutation(141561),     -- Internet Salutation
        internetUpnpSuite(141570),      -- MS UPnP Suite (plug-and-play)
        internetUpnpSSDP(141571),       -- MS UPnP SSDP (discovery)
        internetUpnpGENA(141572),       -- MS UPnP GENA (notification)
        internetSLP(141591),            -- Internet SLP (discovery)
        internetSLPv1(141592),          -- Internet SLPv1 (discovery)
        internetSLPv2(141593),          -- Internet SLPv2 (discovery)

        ibmsnaSuite(150101),            -- IBM SNA
            --  SDLC (WAN Synchronous Datalink Control)
        ibmsnaSDLC(151201),             -- IBM SNA SDLC (datalink)
            --  DLC (LAN Datalink Control)
        ibmsnaDLC(151211),              -- IBM SNA DLC (datalink)
            --  DLS (LAN Datalink Switching)
        ibmsnaDLS(151221),              -- IBM SNA DLS (datalink)
            --  PC (Path Control)
        ibmsnaPC(151301),               -- IBM SNA PC (network)
            --  TC (Transmission Control)
        ibmsnaTC(151401),               -- IBM SNA TC (transport)
            --  DFC (Data Flow Control)
        ibmsnaDFC(151501),              -- IBM SNA DFC (session)
            --  CSC (Common Session Control)
        ibmsnaCSC(151502),              -- IBM SNA CSC (session)
            --  PUNS (Physical Unit Network Services)
        ibmsnaPUNS(151503),             -- IBM SNA PU NS (session)
            --  LUNS (Logical Unit Network Services)
        ibmsnaLUNS(151504),             -- IBM SNA LU NS (session)
            --  PS (Presentation Services)
        ibmsnaPS(151601),               -- IBM SNA PS (presentation)
            --  3270 PS (3270 Presentation Services)
        ibmsna3270PS(151602),           -- IBM SNA 3270 PS
            --  5250 PS (5250 Presentation Services)
        ibmsna5250PS(151603),           -- IBM SNA 5250 PS
            --  RJE (Remote Job Entry)
        ibmsnaRJE(151604),              -- IBM SNA RJE
            --  APPC (Advanced Program-to-Program Communication)
        ibmsnaAPPC(151605),             -- IBM SNA APPC


        ibmbisyncSuite(160101),         -- IBM Bisync
            --  DLC (Datalink Control)
        ibmbisyncDLC(161201),           -- IBM BiSync DLC (datalink)
            --  PS (Presentation Services)
        ibmbisyncPS(161601),            -- IBM BiSync PS (presentation)
            --  3270 PS (3270 Presentation Services)
        ibmbisync3270PS(161602),        -- IBM BiSync 3270 PS
            --  5250 PS (5250 Presentation Services)
        ibmbisync5250PS(161603),        -- IBM BiSync 5250 PS
            --  RJE (Remote Job Entry)
        ibmbisyncRJE(161604),           -- IBM BiSync RJE

        decnetSuite(170101),            -- DEC DECnet

        appletalkSuite(180101),         -- Apple AppleTalk
        appletalkLLAP(181201),          -- AppleTalk LocalTalk LAP
        appletalkELAP(181202),          -- AppleTalk EtherTalk LAP
        appletalkTLAP(181203),          -- AppleTalk TokenTalk LAP
        appletalkDDP(181301),           -- AppleTalk DDP (CL network)
        appletalkAARP(181303),          -- AppleTalk AARP (routing)
        appletalkATP(181401),           -- AppleTalk ATP (CL transport)
        appletalkADSP(181402),          -- AppleTalk ADSP (CO transport)
        appletalkRTMP(181403),          -- AppleTalk RTMP (routing)
        appletalkAEP(181404),           -- AppleTalk AEP (echo)
        appletalkASP(181501),           -- AppleTalk ASP (CO session)
        appletalkZIP(181502),           -- AppleTalk ZIP (directory)
        appletalkPAP(181503),           -- AppleTalk PAP (printing)
        appletalkNBP(181507),           -- AppleTalk NBP (directory)
        appletalkSNMP(181510),          -- AppleTalk SNMP (mgmt)
        appletalkSNMPv1(181511),        -- AppleTalk SNMP V1 (mgmt)
        appletalkSNMPv2(181512),        -- AppleTalk SNMP V2 (mgmt)
        appletalkSNMPv3(181513),        -- AppleTalk SNMP V2 (mgmt)
        appletalkAFP(181601),           -- AppleTalk AFP (filing)

        netwareSuite(190101),           -- Novell NetWare
        netwareIPX(191301),             -- NetWare IPX (CL network)
        netwareSPX(191402),             -- NetWare SPX (CO transport)
        netwareRIP(191403),             -- NetWare RIP (routing)
        netwareEcho(191404),            -- NetWare Echo (echo)
        netwareNCP(191501),             -- NetWare NCP (core protocols)
        netwareNetbios(191502),         -- NetWare NetBIOS (emulation)
        netwarePServer(191503),         -- NetWare PServer (printing)
        netwareFServer(191504),         -- NetWare FServer (filing)
        netwareMHS(191505),             -- NetWare MHS (email)
        netwareBindery(191507),         -- NetWare Bindery (directory)
        netwareNDS(191508),             -- NetWare NDS (directory)
        netwareRPrinter(191509),        -- NetWare RPrinter (printing)
        netwareSNMP(191510),            -- NetWare SNMP (mgmt)
        netwareSNMPv1(191511),          -- NetWare SNMP V1 (mgmt)
        netwareSNMPv2(191512),          -- NetWare SNMP V2 (mgmt)
        netwareSNMPv3(191513),          -- NetWare SNMP V2 (mgmt)
        netwareSAP(191591),             -- NetWare SAP (discovery)


        vinesSuite(200101),             -- Banyan Vines
        vinesVIP(201301),               -- Vines VIP (CL network)
        vinesVICP(201302),              -- Vines VICP (network)
        vinesVARP(201303),              -- Vines VARP (routing)
        vinesIP(201311),                -- Vines IP (CL network)
        vinesICMP(201312),              -- Vines ICMP (network)
        vinesARP(201313),               -- Vines ARP (routing)
        vinesVRTP(201314),              -- Vines VRTP (routing)
        vinesVIPC(201401),              -- Vines VIPC (CL transport)
        vinesVSPP(201402),              -- Vines VSPP (CO transport)
        vinesUDP(201411),               -- Vines UDP (CL transport)
        vinesTCP(201412),               -- Vines TCP (CO transport)
        vinesNetRPC(201501),            -- Vines NetRPC (transactions)
        vinesSocket(201502),            -- Vines Socket (CL/CO session)
        vinesNetbios(201503),           -- Vines NetBIOS (emulation)
        vinesPrint(201701),             -- Vines Print (printing)
        vinesFiling(201702),            -- Vines Filing (filing)
        vinesMail(201703),              -- Vines Mail (email)
        vinesStreetTalk(201704),        -- Vines StreetTalk (directory)

        lantasticSuite(210101),         -- Lantastic

        lanserverSuite(220101),         -- IBM LAN Server

        lanmanagerSuite(230101),        -- Microsoft LAN Manager

        ntasSuite(240101),              -- Microsoft NTAS

        netbiosSuite(250101),           -- NetBIOS Generic
        netbiosNBP(251501),             -- NetBIOS NBP (core session)
        netbiosSNMP(251510),            -- NetBIOS SNMP (mgmt)
        netbiosSNMPv1(251511),          -- NetBIOS SNMP V1 (mgmt)
        netbiosSNMPv2(251512),          -- NetBIOS SNMP V2 (mgmt)
        netbiosSNMPv3(251513),          -- NetBIOS SNMP V3 (mgmt)
        netbiosIntEndNode(251520),      -- NetBIOS over TCP End Node
        netbiosIntNameServer(251521),   -- NetBIOS over TCP Name Server
        netbiosIntDistServer(251522),   -- NetBIOS over TCP Dist Server
        netbiosSAP(251591),             -- NetBIOS SAP (discovery)
        netbiosSMB(251701),             -- NetBIOS SMB (Server Msg Blk)
        netbiosPClient(251702),         -- NetBIOS Printing Client
        netbiosPServer(251703),         -- NetBIOS Printing Server
        netbiosFClient(251704),         -- NetBIOS Filing Client
        netbiosFServer(251705),         -- NetBIOS Filing Server

        netbeuiSuite(260101),           -- NetBEUI Generic
        netbeuiDatalink(261201),        -- NetBEUI Datalink (no routing)
        netbeuiLLC(261221),             -- NetBEUI LLC (ISO/IEEE 802.2)
        netbeuiDLC(261231),             -- NetBEUI DLC (IBM SNA DLC)

        serialSuite(270101),            -- Serial Ports
        --  see 'directPrintSuite' for datalink print protocols

        parallelSuite(280101),          -- Parallel Ports


        --  see 'directPrintSuite' for datalink print protocols

        directPrintSuite(290101),       -- Direct Print Serial/Parallel

        usbSuite(300101)                -- Universal Serial Bus Ports
        --  see 'directPrintSuite' for datalink print protocols
    }

XcmCommsAddressExtForm ::= TEXTUAL-CONVENTION
    STATUS      current
    DESCRIPTION
        "The current address form of this protocol entity."
    SYNTAX      INTEGER {
        other(1),
        unknown(2),
        postal(11),                     -- Public Postal Service
        voice(12),                      -- Voice Switching
        telex(13),                      -- Telex Switching
        fax(14),                        -- Fax Switching
        packet(15),                     -- Packet Switching
        email(16),                      -- Electronic Mail Service
        fullName(17),                   -- Full Distinguished Name
        relName(18)                     -- Relative Distinguished Name
    }

XcmCommsAddressExtScope ::= TEXTUAL-CONVENTION
    STATUS      current
    DESCRIPTION
        "The current address scope of this protocol entity."
    SYNTAX      INTEGER {
        other(1),
        unknown(2),
        subnet(11),                     -- one subnetwork
        region(12),                     -- group of subnetworks
        network(13),                    -- one internet, RPOA, ADMD, etc
        universe(14)                    -- all internet, RPOA, ADMD, etc
    }

XcmCommsAddressExtFanout ::= TEXTUAL-CONVENTION
    STATUS      current
    DESCRIPTION
        "The current address fan out of this protocol entity."
    SYNTAX      INTEGER {
        other(1),
        unknown(2),
        --  Address Data  --
        unicast(11),                    -- one destination
        multicast(12),                  -- group of destinations
        broadcast(13),                  -- all network destinations
        universe(14),                   -- all networks and destinations
        --  Address Mask  --
        unicastMask(15),                -- one destination
        multicastMask(16),              -- group of destinations
        broadcastMask(17),              -- all network destinations


        universeMask(18)                -- all networks and destinations
    }

XcmCommsEngineGroupSupport ::= TEXTUAL-CONVENTION
    STATUS      current
    DESCRIPTION
        "The terse conformance statement of ALL mandatory, conditionally
        mandatory, and optional XCMI Comms Engine MIB object groups
        supported by this management agent implementation (ie, version)
        on this host system, specified in a bit-mask.

        The current set of values (which MAY be extended in the future)
        is given below:

              1 : commsEngineGroup            -- 2**0
              2 : commsEngineExtGroup         -- 2**1
              4 : commsStackGroup             -- 2**2
              8 : commsStackExtGroup          -- 2**3
             16 : commsStackXrefGroup         -- 2**4
             32 : commsMuxGroup               -- 2**5
             64 : commsMuxExtGroup            -- 2**6
            128 : commsAddressGroup           -- 2**7
            256 : commsAddressExtGroup        -- 2**8
            512 : commsTrafficGroup           -- 2**9
           1024 : commsAccessGroup            -- 2**10
           2048 : commsMgmtGroup              -- 2**11

        Usage:  Conforming management agents SHALL accurately
        report their support for XCMI Comms Engine MIB object groups."
    SYNTAX      INTEGER (0..2147483647)  -- biggest int = 2**31-1

--
--          The Comms Engine TC Dummy Group (DO NOT USE)
--
--          DO NOT USE - Present to suppress compiler warnings ONLY!
--
--          Note:  The following objects have 'odd' use of case in their
--          names (ie, 'xCm...'), in order to make obvious their related
--          textual conventions

xCmCommsEngineDummy OBJECT IDENTIFIER ::= { xcmCommsEngineTC 999 }

xCmCommsMgmtCommandRequest OBJECT-TYPE
    SYNTAX      XcmCommsMgmtCommandRequest
    MAX-ACCESS  not-accessible
    STATUS      current
    DESCRIPTION "Dummy - DO NOT USE"
    ::= { xCmCommsEngineDummy 1 }

xCmCommsMgmtCommandData OBJECT-TYPE
    SYNTAX      XcmCommsMgmtCommandData
    MAX-ACCESS  not-accessible
    STATUS      current
    DESCRIPTION "Dummy - DO NOT USE"


    ::= { xCmCommsEngineDummy 2 }

xCmCommsMgmtState OBJECT-TYPE
    SYNTAX      XcmCommsMgmtState
    MAX-ACCESS  not-accessible
    STATUS      current
    DESCRIPTION "Dummy - DO NOT USE"
    ::= { xCmCommsEngineDummy 3 }

xCmCommsMgmtConditions OBJECT-TYPE
    SYNTAX      XcmCommsMgmtConditions
    MAX-ACCESS  not-accessible
    STATUS      current
    DESCRIPTION "Dummy - DO NOT USE"
    ::= { xCmCommsEngineDummy 4 }

xCmCommsStackPosition OBJECT-TYPE
    SYNTAX      XcmCommsStackPosition
    MAX-ACCESS  not-accessible
    STATUS      current
    DESCRIPTION "Dummy - DO NOT USE"
    ::= { xCmCommsEngineDummy 5 }

xCmCommsStackExtPurpose OBJECT-TYPE
    SYNTAX      XcmCommsStackExtPurpose
    MAX-ACCESS  not-accessible
    STATUS      current
    DESCRIPTION "Dummy - DO NOT USE"
    ::= { xCmCommsEngineDummy 6 }

xCmCommsStackExtRole OBJECT-TYPE
    SYNTAX      XcmCommsStackExtRole
    MAX-ACCESS  not-accessible
    STATUS      current
    DESCRIPTION "Dummy - DO NOT USE"
    ::= { xCmCommsEngineDummy 7 }

xCmCommsStackExtSuite OBJECT-TYPE
    SYNTAX      XcmCommsStackExtSuite
    MAX-ACCESS  not-accessible
    STATUS      current
    DESCRIPTION "Dummy - DO NOT USE"
    ::= { xCmCommsEngineDummy 8 }

xCmCommsStackExtSuiteVersion OBJECT-TYPE
    SYNTAX      XcmCommsStackExtSuiteVersion
    MAX-ACCESS  not-accessible
    STATUS      current
    DESCRIPTION "Dummy - DO NOT USE"
    ::= { xCmCommsEngineDummy 9 }

xCmCommsStackExtLayer OBJECT-TYPE
    SYNTAX      XcmCommsStackExtLayer
    MAX-ACCESS  not-accessible


    STATUS      current
    DESCRIPTION "Dummy - DO NOT USE"
    ::= { xCmCommsEngineDummy 10 }

xCmCommsStackExtProtocol OBJECT-TYPE
    SYNTAX      XcmCommsStackExtProtocol
    MAX-ACCESS  not-accessible
    STATUS      current
    DESCRIPTION "Dummy - DO NOT USE"
    ::= { xCmCommsEngineDummy 11 }

xCmCommsAddressExtForm OBJECT-TYPE
    SYNTAX      XcmCommsAddressExtForm
    MAX-ACCESS  not-accessible
    STATUS      current
    DESCRIPTION "Dummy - DO NOT USE"
    ::= { xCmCommsEngineDummy 12 }

xCmCommsAddressExtScope OBJECT-TYPE
    SYNTAX      XcmCommsAddressExtScope
    MAX-ACCESS  not-accessible
    STATUS      current
    DESCRIPTION "Dummy - DO NOT USE"
    ::= { xCmCommsEngineDummy 13 }

xCmCommsAddressExtFanout OBJECT-TYPE
    SYNTAX      XcmCommsAddressExtFanout
    MAX-ACCESS  not-accessible
    STATUS      current
    DESCRIPTION "Dummy - DO NOT USE"
    ::= { xCmCommsEngineDummy 14 }

xCmCommsEngineGroupSupport OBJECT-TYPE
    SYNTAX      XcmCommsEngineGroupSupport
    MAX-ACCESS  not-accessible
    STATUS      current
    DESCRIPTION "Dummy - DO NOT USE"
    ::= { xCmCommsEngineDummy 15 }

END
