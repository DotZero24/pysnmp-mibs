XEROX-COMMS-CONFIG-TC DEFINITIONS ::= BEGIN

--  Module: Communications Configuration TC
--  File:   52conftc.mib
--  Date:   02 May 2012 - Version 6.002.pub VersionUpdate

--  Textual Conventions companion to the Comms Config MIB
--  Contains the REGISTRY of XCMI Standard NetBIOS Listen Ports

IMPORTS
    MODULE-IDENTITY, OBJECT-IDENTITY,
        OBJECT-TYPE
            FROM SNMPv2-SMI             -- IETF RFC 1442/1902/2578
    TEXTUAL-CONVENTION
            FROM SNMPv2-TC              -- IETF RFC 1443/1903/2579
    xeroxCommonMIB
            FROM XEROX-COMMON-MIB;

xcmCommsConfigTC MODULE-IDENTITY
    LAST-UPDATED "1110120000Z" -- 12 October 2011
    ORGANIZATION "Xerox Corporation - XCMI Working Group"
    CONTACT-INFO
        "           XCMI Editors
        Email:      coherence@crt.xerox.com
        "
    DESCRIPTION
        "Version:   6.001.pub

        The TC module for textual conventions, enumerated types, OIDs,
        and other volatile elements of the companion Communications
        Config MIB, which supports active configuration discovery of
        communications end system applications, communications
        intermediate systems, and communications gateways for network
        accessible host systems.

        Copyright (C) 1996-2007 Xerox Corporation. All Rights Reserved."
    ::= { xeroxCommonMIB 63 }

--
--          The Comms Config TC
--
--          Textual Conventions

--
--          SNMP over NetBIOS Transport Domain and Transport Address
--
--          For use with SNMPv1/v2 protocols over the NetBIOS.


--
--          See section 2.0 'Definitions' of SNMPv2 Transport Mappings
--          (RFC 1449/1906) for information on SNMP mappings over other
--          network/transport protocols from other protocol suites.

xcmSnmpNetbiosDomain OBJECT-IDENTITY
    STATUS      current
    DESCRIPTION
        "The SNMP over NetBIOS transport domain.  The corresponding
        transport address is of type 'XcmSnmpNetbiosAddress'."
    ::= { xcmCommsConfigTC 3 }

XcmSnmpNetbiosAddress ::= TEXTUAL-CONVENTION
    STATUS      current
    DESCRIPTION
        "The canonical NetBIOS transport address.  The corresponding
        SNMP over NetBIOS transport domain is 'xcmSnmpNetbiosDomain'.

        The canonical NetBIOS transport address
        (registered as a NetBIOS session layer name via 'AddName'):

            Octets      Contents        Encoding
            ------      --------        --------
              1-12      MAC-address     ASCII hexadecimal (uppercase)
                        [IEEE 802.x]        ('0'-'9', 'A'-'F')
             13-14      XCMI-reserved   ASCII decimal zeros
                        [XCMI future]       ('0' - 0x30)
             15-16      NetBIOS-port    binary network-byte order
                        [XCMI std port]     (high-order byte first)
        "
    SYNTAX  OCTET STRING (SIZE (16))

xcmSnmpIPHostnameDomain OBJECT-IDENTITY
    STATUS      current
    DESCRIPTION
        "The transport domain for SNMP over UDP when
         using host name instead of IP address.  The corresponding
         transport address is of type 'XcmSnmpIPHostnameAddress'."
    ::= { xcmCommsConfigTC 5 }

XcmSnmpIPHostnameAddress ::= TEXTUAL-CONVENTION
    STATUS      current
    DESCRIPTION
        "The transport address.  The corresponding
        transport domain is 'xcmSnmpIPHostnameDomain'.

            Octets      Contents            Encoding
            ------      --------            --------
              1         Host Name Length    unsigned char 0-255
              2-n       FQDN
              n+1, n+2  UDP Port                                "

    SYNTAX  OCTET STRING (SIZE (255))


--
--          REGISTRY of XCMI Standard NetBIOS Ports
--          (used with XCMI standard SNMP over NetBIOS mapping)
--
--          Entity                      Listen Port
--          ------                      -----------
--          SNMP management agent       161 (decimal)
--          SNMP management station     162 (decimal)

--
--          Comms Options Types and Syntaxes
--
--          Implementation of these options is optional for all systems,
--          and useful for ones which implement stack layer graphing
--          (via the Stack and Mux Groups) and ALSO for ones which do
--          NOT implement stack layer graphing (eg, low cost systems).

XcmCommsConfigGroupSupport ::= TEXTUAL-CONVENTION
    STATUS      current
    DESCRIPTION
        "The terse conformance statement of ALL mandatory, conditionally
        mandatory, and optional XCMI Comms Config MIB object groups
        supported by this management agent implementation (ie, version)
        on this host system, specified in a bit-mask.

        The current set of values (which MAY be extended in the future)
        is given below:

              1 : commsConfigGroup            -- 2**0
              2 : commsOptionGroup            -- 2**1
              4 : commsDirRecordGroup         -- 2**2
              8 : commsDirAttributeGroup      -- 2**3
             16 : commsDirStringGroup         -- 2**4
             32 : commsProtocolGroup          -- 2**5

        Usage:  Conforming management agents SHALL accurately
        report their support for XCMI Comms Config MIB object groups."
    SYNTAX      INTEGER (0..2147483647)  -- biggest int = 2**31-1

XcmCommsDirRecordType ::= TEXTUAL-CONVENTION
    STATUS      current
    DESCRIPTION
        "The type of the directory record specified
        in this conceptual row in the 'xcmCommsDirRecordTable'.

        Usage:  Directory records of type 'recordXxxGroup' SHALL
        contain only 'xxxIndex' directory attributes (ie, pointers to
        individual 'recordXxx' directory records)."
    SYNTAX      INTEGER {
        other(1),                       -- see key attribute type/index
        unknown(2),                     -- NOT valid as record type
        top(10),                        -- top (root of directory)
        recordService(100),             -- individual service record


        recordServiceGroup(101),        -- group of service records
        recordAccount(200),             -- individual account record
        recordAccountGroup(201),        -- group of account records
        recordDepartment(300),          -- individual department record
        recordDepartmentGroup(301),     -- group of department records
        recordMailbox(400),             -- individual mailbox record
        recordMailboxGroup(401),        -- group of mailboxe records
        recordResource(500),            -- individual resource record
        recordResourceGroup(501),       -- group of resource records
        recordSpeedDial(600),           -- individual speed dial record
        recordSpeedDialGroup(601),      -- group of speed dial records
        recordUser(700),                -- individual user
        recordUserGroup(701),           -- group of users
        recordButtonDial(800),          -- individual button dial record
        recordButtonDialGroup(801),     -- group of button dial records
        recordRepository(900),          -- individual repository
        recordRepositoryGroup(901)      -- group of repositories
    }

XcmCommsDirAttributeType ::= TEXTUAL-CONVENTION
    STATUS      current
    DESCRIPTION
        "A directory attribute type, used to identify this
        integer-valued directory attribute, which MAY have a matching
        string-valued directory attribute in 'xcmCommsDirStringTable'.

        Usage:   When directory attribute type indicates integer-valued,
        the value of 'xcmCommsDirAttributeValue' SHALL be the
        actual value of this directory attribute.

        Usage:   When directory attribute type indicates string-valued,
        the value of 'xcmCommsDirAttributeValue' SHALL be zero,
        EXCEPT for a directory attribute type of 'protocolTyped...',
        when the protocol type SHALL be specified as the integer value.
        The actual string-valued attribute SHALL be specified in
        an exactly matching row of 'xcmCommsDirStringTable'.

        Usage:  Matching directory attributes (string-valued)
        SHALL be specified in an exactly matching row of
        'xcmCommsDirStringTable'.  Matching rows have EXACTLY the SAME
        values of 'xcmCommsDirRecordType', 'xcmCommsDirRecordIndex',
        'xcmCommsDirAttributeType', and 'xcmCommsDirAttributeIndex'.

        Usage:  Parallel directory attributes (peers of this one)
        SHALL be specified in parallel (NOT matching) rows of
        'xcmCommsDirAttributeTable' (integer-valued attributes) or
        'xcmCommsDirStringTable' (string-valued attributes).  Parallel
        rows have EXACTLY the SAME values of 'xcmCommsDirRecordType',
        'xcmCommsDirRecordIndex', and 'xcmCommsDirAttributeIndex',
        but MUST have a DIFFERENT value of 'xcmCommsDirAttributeType'.

        Usage:   When directory attribute type is 'protocolTyped...' the
        particular protocol layer SHALL be specified by placing a
        a value from the enumeration 'XcmCommsStackExtProtocol' in


        'xcmCommsDirAttributeValue' for this row."
    REFERENCE
        "See:   'xcmCommsDirAttributeType' in the XCMI Comms Config MIB
                'XcmCommsStackExtProtocol' in the XCMI Comms Engine TC."
    SYNTAX      INTEGER {
        --  WARNING - this enumeration is work-in-progress - do NOT use
        other(1),
        unknown(2),
        --  Structural directory attributes (integer-valued)
        --
        parentRecordType(10),           -- (xcmCommsDirRecordType)
        parentRecordIndex(11),          -- (xcmCommsDirRecordIndex)
        parentGroupRecordType(12),      -- (xcmCommsDirRecordType)
        parentGroupRecordIndex(13),     -- (xcmCommsDirRecordIndex)
        peerRecordType(20),             -- (xcmCommsDirRecordType)
        peerRecordIndex(21),            -- (xcmCommsDirRecordIndex)
        peerGroupRecordType(22),        -- (xcmCommsDirRecordType)
        peerGroupRecordIndex(23),       -- (xcmCommsDirRecordIndex)
        childRecordType(30),            -- (xcmCommsDirRecordType)
        childRecordIndex(31),           -- (xcmCommsDirRecordIndex)
        childGroupRecordType(32),       -- (xcmCommsDirRecordType)
        childGroupRecordIndex(33),      -- (xcmCommsDirRecordIndex)
        --  Service directory attributes (integer-valued)
        --
        serviceIndex(100),              -- (xcmCommsDirRecordIndex)
        serviceGroupIndex(101),         -- (xcmCommsDirRecordIndex)
        servicePosixRights(102),        -- (XcmSecPosixRights)
        servicePosixVerbs(103),         -- (XcmSecPosixVerbs)
        serviceType(110),               -- (XcmSvcMonServiceType)
        serviceSkill(111),              -- (XcmSecUserSkill)
        serviceScope(112),              -- (XcmSecAccountScope)
        servicePhysicalDeviceIndex(120),-- (hrDeviceIndex)
        serviceLogicalDeviceIndex(121), -- (hrDeviceIndex)
        serviceExternalDeviceIndex(122),-- (hrDeviceIndex)
        serviceSWRunIndex(123),         -- (hrSWRunIndex)
        serviceSWInstalledIndex(124),   -- (hrSWInstalledIndex)
        serviceStorageIndex(125),       -- (hrStorageIndex)
        servicePriority(130),           -- (xcmSvcMonServicePriority)
        --  Service lifetime usage and limits (integer-valued)
        --  ('serviceLifetimeUsage' SHALL have subtype per
        --  the 'XcmGenMessageMapStringLabel' syntax in XCMI General TC)
        --  specified in 'xcmCommsDirStringValue')
        --  ('serviceLifetimeUsage' MAY have units class/type specified
        --  in parallel '...[UnitClass|Unit]' rows)
        serviceLifetimeUsage(140),          -- (deviceLifetimeUsage)
        serviceLifetimeUnitClass(141),      -- (xcmHrDevDetailUnitClass)
        serviceLifetimeUnit(142),           -- (xcmHrDevDetailUnit)
        serviceLifetimeLimit(143),          -- (deviceMaximumLifetime...
        --  Service lifetime errors and warnings (integer-valued)
        --  ('serviceLifetime[Error|Warning]Count' MAY have subtype per
        --  the 'XcmGenMessageMapStringLabel' syntax in XCMI General TC,
        --  specified in 'xcmCommsDirStringValue')
        serviceLifetimeErrorCount(144),     -- (deviceLifetimeErrorCount
        serviceLifetimeErrorLimit(145),     -- (deviceLifetimeErrorLimit


        serviceLifetimeWarningCount(146),   -- (deviceLifetimeWarning...
        serviceLifetimeWarningLimit(147),   -- (deviceLifetimeWarning...
        --  Service directory attributes (string-valued)
        --
        serviceName(150),               -- (...Utf8String)
        serviceFullName(151),           -- (...Utf8String)
        serviceCode(152),               -- (...Utf8String)
        servicePassword(153),           -- (...Utf8String)
        servicePasscode(154),           -- (...Utf8String)
        serviceAlias(155),              -- (...Utf8String)
        serviceLoginDate(156),          -- (DateAndTime)
        serviceLogoutDate(157),         -- (DateAndTime)
        serviceDescription(160),        -- (...Utf8String)
        serviceLocation(161),           -- (...Utf8String)
        serviceTypeOID(162),            -- (...Utf8String) - string OID
        serviceProductID(163),          -- (ProductID) - see '93pidtc'
        serviceLanguageConfigured(170), -- (...Utf8String) - RFC 1766
        serviceLanguageSupported(171),  -- (...Utf8String) - RFC 1766
        serviceCharsetConfigured(172),  -- (...Utf8String) - IANA name
        serviceCharsetSupported(173),   -- (...Utf8String) - IANA name
        serviceTree(180),               -- (...Utf8String)
        serviceContext(181),            -- (...Utf8String)
        serviceVolume(182),             -- (...Utf8String)
        servicePath(183),               -- (...Utf8String)
        --  Account directory attributes (integer-valued)
        --
        accountIndex(200),              -- (xcmCommsDirRecordIndex)
        accountGroupIndex(201),         -- (xcmCommsDirRecordIndex)
        accountPosixRights(202),        -- (XcmSecPosixRights)
        accountPosixVerbs(203),         -- (XcmSecPosixVerbs)
        accountRole(210),               -- (XcmSecUserRole)
        accountSkill(211),              -- (XcmSecUserSkill)
        accountScope(212),              -- (XcmSecAccountScope)
        --  Account lifetime usage and limits (integer-valued)
        --  ('accountLifetimeUsage' SHALL have subtype per
        --  the 'XcmGenMessageMapStringLabel' syntax in XCMI General TC)
        --  specified in 'xcmCommsDirStringValue')
        --  ('accountLifetimeUsage' MAY have units class/type specified
        --  in parallel '...[UnitClass|Unit]' rows)
        accountLifetimeUsage(240),          -- (deviceLifetimeUsage)
        accountLifetimeUnitClass(241),      -- (xcmHrDevDetailUnitClass)
        accountLifetimeUnit(242),           -- (xcmHrDevDetailUnit)
        accountLifetimeLimit(243),          -- (deviceMaximumLifetime...
        --  Account lifetime errors and warnings (integer-valued)
        --  ('accountLifetime[Error|Warning]Count' MAY have subtype per
        --  the 'XcmGenMessageMapStringLabel' syntax in XCMI General TC,
        --  specified in 'xcmCommsDirStringValue')
        accountLifetimeErrorCount(244),     -- (deviceLifetimeErrorCount
        accountLifetimeErrorLimit(245),     -- (deviceLifetimeErrorLimit
        accountLifetimeWarningCount(246),   -- (deviceLifetimeWarning...
        accountLifetimeWarningLimit(247),   -- (deviceLifetimeWarning...
        --  Account directory attributes (string-valued)
        --
        accountName(250),               -- (...Utf8String)


        accountFullName(251),           -- (...Utf8String)
        accountCode(252),               -- (...Utf8String)
        accountPassword(253),           -- (...Utf8String)
        accountPasscode(254),           -- (...Utf8String)
        accountAlias(255),              -- (...Utf8String)
        accountLoginDate(256),          -- (DateAndTime)
        accountLogoutDate(257),         -- (DateAndTime)
        accountDescription(260),        -- (...Utf8String)
        accountLocation(261),           -- (...Utf8String)
        --  Department directory attributes (integer-valued)
        --
        departmentIndex(300),           -- (xcmCommsDirRecordIndex)
        departmentGroupIndex(301),      -- (xcmCommsDirRecordIndex)
        --  Department directory attributes (string-valued)
        --
        departmentName(350),            -- (...Utf8String)
        departmentFullName(351),        -- (...Utf8String)
        departmentCode(352),            -- (...Utf8String)
        departmentDescription(360),     -- (...Utf8String)
        departmentLocation(361),        -- (...Utf8String)
        --  Mailbox directory attributes (integer-valued)
        --
        mailboxIndex(400),              -- (xcmCommsDirRecordIndex)
        mailboxGroupIndex(401),         -- (xcmCommsDirRecordIndex)
        --  Mailbox directory attributes (string-valued)
        --
        mailboxName(450),               -- (...Utf8String)
        mailboxFullName(451),           -- (...Utf8String)
        mailboxCode(452),               -- (...Utf8String)
        mailboxDescription(460),        -- (...Utf8String)
        mailboxLocation(461),           -- (...Utf8String)
        --  Resource directory attributes (integer-valued)
        --
        resourceIndex(500),             -- (xcmCommsDirRecordIndex)
        resourceGroupIndex(501),        -- (xcmCommsDirRecordIndex)
        resourcePosixRights(502),       -- (XcmSecPosixRights)
        resourcePosixVerbs(503),        -- (XcmSecPosixVerbs)
        resourceType(510),              -- (XcmRsrcType)
        resourceSkill(511),             -- (XcmSecUserSkill)
        resourceScope(512),             -- (XcmSecAccountScope)
        --  Resource lifetime usage and limits (integer-valued)
        --  ('resourceLifetimeUsage' SHALL have subtype per
        --  the 'XcmGenMessageMapStringLabel' syntax in XCMI General TC)
        --  specified in 'xcmCommsDirStringValue')
        --  ('resourceLifetimeUsage' MAY have units class/type specified
        --  in parallel '...[UnitClass|Unit]' rows)
        resourceLifetimeUsage(540),         -- (deviceLifetimeUsage)
        resourceLifetimeUnitClass(541),     -- (xcmHrDevDetailUnitClass)
        resourceLifetimeUnit(542),          -- (xcmHrDevDetailUnit)
        resourceLifetimeLimit(543),         -- (deviceMaximumLifetime...
        --  Resource lifetime errors and warnings (integer-valued)
        --  ('resourceLifetime[Error|Warning]Count' MAY have subtype per
        --  the 'XcmGenMessageMapStringLabel' syntax in XCMI General TC,
        --  specified in 'xcmCommsDirStringValue')


        resourceLifetimeErrorCount(544),    -- (deviceLifetimeErrorCount
        resourceLifetimeErrorLimit(545),    -- (deviceLifetimeErrorLimit
        resourceLifetimeWarningCount(546),  -- (deviceLifetimeWarning...
        resourceLifetimeWarningLimit(547),  -- (deviceLifetimeWarning...
        --  Resource directory attributes (string-valued)
        --
        resourceName(550),              -- (...Utf8String)
        resourceFullName(551),          -- (...Utf8String)
        resourceCode(552),              -- (...Utf8String)
        resourcePassword(553),          -- (...Utf8String)
        resourcePasscode(554),          -- (...Utf8String)
        resourceAlias(555),             -- (...Utf8String)
        resourceLoginDate(556),         -- (DateAndTime)
        resourceLogoutDate(557),        -- (DateAndTime)
        resourceDescription(560),       -- (...Utf8String)
        resourceLocation(561),          -- (...Utf8String)
        --  Speed Dial directory attributes (integer-valued)
        --
        speedDialIndex(600),            -- (xcmCommsDirRecordIndex)
        speedDialGroupIndex(601),       -- (xcmCommsDirRecordIndex)
        --  Speed Dial directory attributes (string-valued)
        --
        speedDialName(650),             -- (...Utf8String)
        speedDialFullName(651),         -- (...Utf8String)
        speedDialCode(652),             -- (...Utf8String)
        speedDialDescription(660),      -- (...Utf8String)
        speedDialLocation(661),         -- (...Utf8String)
        --  User directory attributes (integer-valued)
        --
        userIndex(700),                 -- (xcmCommsDirRecordIndex)
        userGroupIndex(701),            -- (xcmCommsDirRecordIndex)
        userPosixRights(702),           -- (XcmSecPosixRights)
        userPosixVerbs(703),            -- (XcmSecPosixVerbs)
        userRole(710),                  -- (XcmSecUserRole)
        userSkill(711),                 -- (XcmSecUserSkill)
        userScope(712),                 -- (XcmSecAccountScope)
        --  User lifetime usage and limits (integer-valued)
        --  ('userLifetimeUsage' SHALL have subtype per
        --  the 'XcmGenMessageMapStringLabel' syntax in XCMI General TC)
        --  specified in 'xcmCommsDirStringValue')
        --  ('userLifetimeUsage' MAY have units class/type specified
        --  in parallel '...[UnitClass|Unit]' rows)
        userLifetimeUsage(740),             -- (deviceLifetimeUsage)
        userLifetimeUnitClass(741),         -- (xcmHrDevDetailUnitClass)
        userLifetimeUnit(742),              -- (xcmHrDevDetailUnit)
        userLifetimeLimit(743),             -- (deviceMaximumLifetime...
        --  User lifetime errors and warnings (integer-valued)
        --  ('userLifetime[Error|Warning]Count' MAY have subtype per
        --  the 'XcmGenMessageMapStringLabel' syntax in XCMI General TC,
        --  specified in 'xcmCommsDirStringValue')
        userLifetimeErrorCount(744),        -- (deviceLifetimeErrorCount
        userLifetimeErrorLimit(745),        -- (deviceLifetimeErrorLimit
        userLifetimeWarningCount(746),      -- (deviceLifetimeWarning...
        userLifetimeWarningLimit(747),      -- (deviceLifetimeWarning...


        --  User directory attributes (string-valued)
        --
        userName(750),                  -- (...Utf8String)
        userFullName(751),              -- (...Utf8String)
        userCode(752),                  -- (...Utf8String)
        userPassword(753),              -- (...Utf8String)
        userPasscode(754),              -- (...Utf8String)
        userAlias(755),                 -- (...Utf8String)
        userLoginDate(756),             -- (DateAndTime)
        userLogoutDate(757),            -- (DateAndTime)
        userDescription(760),           -- (...Utf8String)
        userLocation(761),              -- (...Utf8String)
        --  Button Dial directory attributes (integer-valued)
        --
        buttonDialIndex(800),           -- (xcmCommsDirRecordIndex)
        buttonDialGroupIndex(801),      -- (xcmCommsDirRecordIndex)
        --  Button Dial directory attributes (string-valued)
        --
        buttonDialName(850),            -- (...Utf8String)
        buttonDialFullName(851),        -- (...Utf8String)
        buttonDialCode(852),            -- (...Utf8String)
        buttonDialDescription(860),     -- (...Utf8String)
        buttonDialLocation(861),        -- (...Utf8String)
        --  Repository directory attributes (integer-valued)
        --
        repositoryIndex(900),           -- (xcmCommsDirRecordIndex)
        repositoryGroupIndex(901),      -- (xcmCommsDirRecordIndex)
        repositoryPosixRights(902),     -- (XcmSecPosixRights)
        repositoryPosixVerbs(903),      -- (XcmSecPosixVerbs)
        repositorySkill(911),           -- (XcmSecUserSkill)
        repositoryScope(912),           -- (XcmSecAccountScope)
        --  Repository directory attributes (string-valued)
        --
        repositoryName(950),            -- (...Utf8String)
        repositoryFullName(951),        -- (...Utf8String)
        repositoryCode(952),            -- (...Utf8String)
        repositoryPassword(953),        -- (...Utf8String)
        repositoryPasscode(954),        -- (...Utf8String)
        repositoryAlias(955),           -- (...Utf8String)
        repositoryLoginDate(956),       -- (DateAndTime)
        repositoryLogoutDate(957),      -- (DateAndTime)
        repositoryDescription(960),     -- (...Utf8String)
        repositoryLocation(961),        -- (...Utf8String)
        --  Protocol directory attributes (integer-valued)
        --
        --  Conformance:  'protocolType' attributes SHALL
        --  have protocol type in 'xcmCommsDirAttributeValue' (integer),
        --  as an enumerated type from 'XcmCommsStackExtProtocol'
        --  defined in the XCMI Comms Engine MIB.
        --  Other 'protocolXxx' (integer) attributes SHALL have
        --  protocol type in a parallel 'protocolType' base row.
        --
        protocolType(1000),             -- (XcmCommsStackExtProtocol)
        protocolPurpose(1001),          -- (XcmCommsStackExtPurpose)


        protocolRole(1002),             -- (XcmCommsStackExtRole)
        protocolSuite(1003),            -- (XcmCommsStackExtSuite)
        protocolLayer(1004),            -- (XcmCommsStackExtLayer)
        protocolDeviceIndex(1010),      -- (hrDeviceIndex)
        protocolInterfaceIndex(1011),   -- (ifIndex)
        protocolPriority(1030),         -- (xcmSvcMonServicePriority)
        protocolConnectorType(1510),    -- (xcmCOOsilanConnectorType)
        protocolConnectorAdaptive(1511),-- (TruthValue)
        protocolSignalType(1512),       -- (xcmCOOsilanSignalType)
        protocolSignalAdaptive(1513),   -- (TruthValue)
        protocolCableType(1514),        -- (xcmCOOsilanCableType)
        protocolCableAdaptive(1515),    -- (TruthValue)
        protocolFrameType(1520),        -- (xcmCOOsilanFrameType)
        protocolFrameAdaptive(1521),    -- (TruthValue)
        protocolMinFrameSize(1522),     -- (Ordinal32)
        protocolMaxFrameSize(1523),     -- (Ordinal32)
        protocolSpeed(1530),            -- (ifSpeed)
        protocolSpeedAdaptive(1531),    -- (TruthValue)
        protocolMinSpeed(1532),         -- (ifSpeed)
        protocolMaxSpeed(1533),         -- (ifSpeed)
        protocolBidirectional(1534),    -- (TruthValue)
        protocolDirection(1535),        -- (xcmCOOsiwanDirection)
        protocolFlowControl(1536),      -- (TruthValue)
        protocolMaxConnections(1537),   -- (Cardinal32)
        protocolInputTimeout(1540),     -- (Cardinal32) - seconds
        protocolInputFlowWindow(1541),  -- (Ordinal32)
        protocolInputPrime(1542),       -- (TruthValue)
        protocolMinInputChars(1543),    -- (Cardinal32)
        protocolMaxInputChars(1544),    -- (Cardinal32)
        protocolOutputTimeout(1550),    -- (Cardinal32) - seconds
        protocolOutputFlowWindow(1551), -- (Ordinal32)
        protocolOutputPrime(1552),      -- (TruthValue)
        protocolMinOutputChars(1553),   -- (Cardinal32)
        protocolMaxOutputChars(1554),   -- (Cardinal32)
        protocolMaxRetries(1560),       -- (Cardinal32)
        protocolRetryInterval(1561),    -- (Cardinal32) - seconds
        protocolPollInterval(1562),     -- (Cardinal32) - seconds
        protocolListen(1570),           -- (TruthValue)
        protocolListenSocket(1571),     -- (Ordinal32)
        protocolListenInterval(1572),   -- (Cardinal32) - seconds
        protocolSpool(1580),            -- (TruthValue)
        protocolMaxSpool(1581),         -- (Cardinal32)
        protocolJobTimeout(1582),       -- (Cardinal32) - seconds
        protocolAutoSwitch(1583),       -- (xcmCODirectPrintProtocol)
        protocolBinaryPS(1584),         -- (TruthValue)
        protocolDefaultPDL(1585),       -- (XcmPrtInterpreterLangFamily)
        protocolSendStartTime(1590),    -- (XcmHrDevCalendarTimeOfDay)
        protocolSendEndTime(1591),      -- (XcmHrDevCalendarTimeOfDay)
        protocolReceiveStartTime(1592), -- (XcmHrDevCalendarTimeOfDay)
        protocolReceiveEndTime(1593),   -- (XcmHrDevCalendarTimeOfDay)
        protocolSendLineNumber(1600),   -- (xcmCOOsiwanLineNumber)
        protocolSendCoverSheet(1601),   -- (TruthValue)
        protocolSendHeader(1602),       -- (TruthValue)
        protocolSendConfirmPrint(1603), -- (TruthValue)


        protocolSendManual(1604),       -- (TruthValue)
        protocolSendSecurity(1605),     -- (TruthValue)
        protocolSendStoreTime(1606),    -- (Cardinal32) - seconds
        protocolSendResolution(1610),   -- (Cardinal32) - dots/inch
        protocolSendErrorCorrection(1611),      -- (TruthValue)
        protocolReceiveLineNumber(1620),-- (xcmCOOsiwanLineNumber)
        protocolReceiveCoverSheet(1621),-- (TruthValue)
        protocolReceiveFooter(1622),    -- (TruthValue)
        protocolReceiveToMemory(1623),  -- (TruthValue)
        protocolReceiveManual(1624),    -- (TruthValue)
        protocolReceiveSecurity(1625),  -- (TruthValue)
        protocolReceiveAutoReduce(1626),-- (TruthValue)
        protocolReceiveOverflow(1627),  -- (TruthValue)
        protocolReceiveCollate(1628),   -- (TruthValue)
        protocolReceiveResolution(1630),-- (Cardinal32) - dots/inch
        protocolReceiveErrorCorrection(1631),   -- (TruthValue)
        --  Protocol directory attributes (string-valued)
        --
        --  Conformance:  'protocolTypedXxx' attributes SHALL
        --  have protocol type in 'xcmCommsDirAttributeValue' (integer),
        --  as an enumerated type from 'XcmCommsStackExtProtocol'
        --  defined in the XCMI Comms Engine MIB.
        --
        protocolTypedName(2000),                -- (...Utf8String)
        protocolTypedFullName(2001),            -- (...Utf8String)
        protocolTypedPassword(2002),            -- (...Utf8String)
        protocolTypedHostName(2003),            -- (...Utf8String)
        protocolTypedQueueName(2004),           -- (...Utf8String)
        protocolTypedServerName(2005),          -- (...Utf8String)
        protocolTypedDescription(2006),         -- (...Utf8String)
        protocolTypedLocation(2007),            -- (...Utf8String)
        protocolTypedAddress(2010),             -- (...Utf8String)
        protocolTypedBroadcastAddress(2011),    -- (...Utf8String)
        protocolTypedListenAddress(2012),       -- (...Utf8String)
        protocolTypedMulticastAddress(2013),    -- (...Utf8String)
        protocolTypedConfirmAddress(2014),      -- (...Utf8String)
        protocolTypedConfirmURL(2015),          -- (...Utf8String)
        protocolTypedAcceptAddress(2020),       -- (...Utf8String)
        protocolTypedAcceptSubnet(2021),        -- (...Utf8String)
        protocolTypedRejectAddress(2022),       -- (...Utf8String)
        protocolTypedRejectSubnet(2023),        -- (...Utf8String)
        protocolTypedURC(2030),                 -- (...Utf8String)
        protocolTypedURI(2031),                 -- (...Utf8String)
        protocolTypedURL(2032),                 -- (...Utf8String)
        protocolTypedURN(2033),                 -- (...Utf8String)
        protocolTypedDeviceName(2040),          -- (...Utf8String)
        reserved(3000)
    }


XcmCommsLDAPAttributeType ::= TEXTUAL-CONVENTION
    STATUS      current
    DESCRIPTION
        "The type of LDAP attribute stored in this communications,
        device, or service detail conceptual row.

        Usage:  Conforming XCMI management stations and agents SHALL
        encode LDAP attributes as UTF-8 strings (like SLPv2, RFC 2608).
        - Integers SHALL be encoded as (signed) decimal strings.
        - Booleans SHALL be encoded as 'true' or 'false' strings.
        - Binary data (e.g., 'userCertificate') SHALL be stored
        in SLPv2 opaque encoding (leading '\FF' and escaped octets)."
    REFERENCE
        "See:   'xcmCOInternetLDAPAttributeStr'
                in XCMI Comms Config TC.
        See:    'systemDirectoryLDAPObjectClass' and
                'systemDirectoryLDAPAttribute' in XCMI Svc Mon TC.
        See:    Section 5 'Service Attributes' in
                Service Location Protocol v2 (RFC 2608).
        See:    Section 9 'Attribute Types' in
                COSINE and Internet X.500 Schema (RFC 1274).
        See:    Section 5 'Attribute Types' in
                Summary of X.500:1996 User Schema for LDAPv3 (RFC 2256).
        See:    Section 9.1 'Attribute Types' in
                Definition of inetOrgPerson LDAP Class (RFC 2798)."
    SYNTAX      INTEGER {
        other(1),
        unknown(2),

        --  ITU-T X.520 Directory Attributes
        --  (see section 5 'Attribute Types' in RFC 2256)
        --  (LDAP Attribute OIDs are '2.5.4.x', where x = attrType)
        --  (see section 7.7 'person', 7.8 'organizationalPerson', and
        --  7.11 'residentialPerson' in RFC 2256)
        commonName(3),                  -- 'cn' - common name string
        surname(4),                     -- 'sn' - family name string
        serialNumber(5),                -- device serial number string
        country(6),                     -- 'c' - country (ISO 3166)
        city(7),                        -- 'l' - locality or region
        state(8),                       -- 'st' - state or province
        streetAddress(9),               -- 'street' - physical address
        org(10),                        -- 'o' - organization name
        orgUnit(11),                    -- 'ou' - organization unit
        title(12),                      -- organizational title
                                        -- see 'userClass' and
                                        -- 'personalTitle'
        description(13),                -- description of object
        searchGuide(14),                -- search guide - OBSOLETE
        businessCategory(15),           -- business type of organization
        postalAddress(16),              -- postal delivery address
        postalCode(17),                 -- postal code (aka ZIP code)
        postOfficeBox(18),              -- post office box
        office(19),                     -- 'physicalDeliveryOfficeName'
        telephoneNumber(20),            -- ITU-T E.164 format (RFC 2806)


        telexNumber(21),                -- ITU-T Telex number
        teletexTerminal(22),            -- ITU-T Teletex terminal id
        faxNumber(23),                  -- ITU-T T.series Fax (RFC 2806)
        x121Address(24),                -- ITU-T X.121 address
        isdnNumber(25),                 -- 'internationalISDNNumber'
        registeredAddress(26),          -- for telegrams and expedited
        destinationIndicator(27),       -- for telegram service
        preferredDeliveryMethod(28),    -- preference for delivery
        presentationAddress(29),        -- ISO OSI presentation address
        supportedContext(30),           -- ISO OSI application contexts
        member(31),                     -- member distinguished name
        owner(32),                      -- owner distinguished name
        role(33),                       -- 'roleOccupant' - role DN
        seeAlso(34),                    -- see also distinguished name
        userPassword(35),               -- user password (MUST encrypt)
        userCertificate(36),            -- user certificate or URL
        caCertificate(37),              -- CA certificate or URL
        authorityRevocationList(38),    -- authority rev list or URL
        certificateRevocationList(39),  -- certificate rev list or URL
        crossCertificatePair(40),       -- cross certificate pair
        name(41),                       -- base type - NOT used
        givenName(42),                  -- first name string
        initials(43),                   -- initials (without surname)
        generationQualifier(44),        -- generation (e.g., "IInd")
        x500UniqueIdentifier(45),       -- X.500 unique id (see 'uid')
        dnQualifier(46),                -- relative DN qualifier
        enhancedSearchGuide(47),        -- X.500 client search filters
        protocolInformation(48),        -- additional ISO OSI address
        distinguishedName(49),          -- base type - NOT used
        uniqueMember(50),               -- X.500 unique member (???)
        houseIdentifier(51),            -- building id within location
        supportedAlgorithms(52),        -- ISO OSI supported algorithms
        deltaRevocationList(53),        -- delta rev list or URL
        dmdName(54),                    -- mgmt domain admin authority

        --  Selected COSINE and Internet X.500 Attributes
        --  (see section 9.1.3 'Attributes from RFC 1274' in RFC 2798)
        --  (see Section 8.3.2 'Pilot Person' in RFC 1274)
        --  ('pilotPerson' derived from X.521 'person')
        --  (names below follow RFC 2798 changes to RFC 1274)
        uid(101),                       -- 'userid' in RFC 1274
                                        -- (system login name)
        textEncodedORAddress(102),      -- X.400 O/R address
                                        -- (historic)
        mail(103),                      -- 'rfc822Mailbox' in RFC 1274
                                        -- (RFC 2822/822 format)
        info(104),                      -- general info
        favoriteDrink(105),             -- favorite beverage of person
        roomNumber(106),                -- room number
        photo(107),                     -- ITU-T T.4 G3 Fax (per X.420)
        userClass(108),                 -- see 'title'
        host(109),                      -- host computer
        manager(110),                   -- manager of an object
        documentIdentifier(111),        -- document unique id


        documentTitle(112),             -- document title
        documentVersion(113),           -- document version number
        documentAuthor(114),            -- document author
        documentLocation(115),          -- document location
        homePhone(116),                 -- 'homeTelephoneNumber'
                                        -- in RFC 1274 (E.164 format)
        secretary(117),                 -- secretary of a person
        otherMailbox(118),              -- other than X.400 and RFC 822
        domainComponent(121),           -- component of a DNS name
        associatedDomain(127),          -- associated DNS domain
        associatedName(128),            -- associated DNS name
        homePostalAddress(129),         -- home postal address
        personalTitle(130),             -- personal title - see 'title'
        mobile(131),                    -- 'mobileTelephoneNumber'
                                        -- in RFC 1274 (E.164 format)
        pager(132),                     -- 'pagerTelephoneNumber'
                                        -- in RFC 1274 (E.164 format)
        friendlyCountry(133),           -- friendly (readable) country
        uniqueIdentifier(134),          -- unique id for an object
        orgStatus(135),                 -- 'organizationalStatus'
        buildingName(138),              -- building name of org or unit
        personalSignature(143),         -- ITU-T T.4 G3 Fax (per X.420)
        audio(145),                     -- audio data
                                        -- (historic)
        documentPublisher(146),         -- document publisher

        --  'inetOrgPerson' Object Class Attributes
        --  (see section 9.1 'Attribute Types' in RFC 2798)
        --  ('inetOrgPerson' derived from X.521 'organizationalPerson')
        carLicense(201),                -- vehicle license plate
        departmentNumber(202),          -- dept id within organization
        displayName(203),               -- preferred name of person
        employeeNumber(204),            -- employee number w/in org
        employeeType(205),              -- employee type w/in org
        jpegPhoto(206),                 -- JPEG photo
                                        -- (historic)
        preferredLanguage(207),         -- preferred language (RFC 3066)
        userSMIMECertificate(208),      -- signed message for S/MIME
        userPKCS12(209),                -- PKCS #12 for personal id info

        --  URI Attributes
        --  (see definition of 'labeledURI' in RFC 2079)
        --  ('labeledURI' is MAY in 'inetOrgPerson' class in RFC 2798)
        labeledURI(300)                 -- URI (RFC 2396/2732 format)
    }

--
--          Special Comms Option Types
--

xcmCOSpecialTypes OBJECT-IDENTITY
    STATUS      current
    DESCRIPTION
        "The root of all special comms option types defined in


        the Comms Config TC."
    ::= { xcmCommsConfigTC 4 }

xcmCOSpecialLabel OBJECT-IDENTITY
--  SYNTAX      stringLocalization
    STATUS      current
    DESCRIPTION
        "Human-readable name for the following configuration subtree,
        specified in 'xcmCommsOptionsValueString'.

        Usage:  To label tree vertices (eg, for client GUI)."
    ::= { xcmCOSpecialTypes 1 }

xcmCOSpecialImport OBJECT-IDENTITY
--  SYNTAX      integerIndex
    STATUS      current
    DESCRIPTION
        "The 'xcmCommsOptionIndex' of an 'imported' configuration
        subtree, specified in 'xcmCommsOptionValueInteger'.

        Usage:  To import a section of common config from elsewhere.
        All comms configuration options in the 'imported' subtree SHALL
        be 'imported' and THEN any dependent options found via the
        current 'xcmCommsOptionFamilyIndex' chain SHALL be treated as
        though they logically 'followed' the 'imported' configuration
        subtree.

        Usage:  This row SHALL be logically 're-typed' by inheritance
        from the first imported row (eg, 'xcmCOOsilanEthernet'), but
        ONLY for the 'scoping' of dependent options which are found via
        the current 'xcmCommsOptionFamilyIndex' chain (eg, a dependent
        option for 'xcmCOOsilanEthernetFrameOverride').

        Usage:  The pointer specified in 'xcmCommsOptionValueInteger'
        SHALL be used to evaluate the 'imported' configuration substree
        and THEN any 'local' options SHALL be evaluated from the current
        'xcmCommsOptionFamilyIndex' chain.

        Usage:  As would normally be true of any option, this row SHALL
        NOT affect the 'scoping' of independent options found via the
        current 'xcmCommsOptionNextIndex' chain (eg, the next protocol
        within a given protocol suite configuration subtree)."
    ::= { xcmCOSpecialTypes 2 }

xcmCOSpecialRemark OBJECT-IDENTITY
--  SYNTAX      stringLocalization
    STATUS      current
    DESCRIPTION
        "Human-readable remark for the following configuration subtree,
        specified in 'xcmCommsOptionsValueString'.

        Usage:  To comment tree vertices (eg, for client GUI)."
    ::= { xcmCOSpecialTypes 3 }


xcmCOSpecialAddress OBJECT-IDENTITY
--  SYNTAX      stringLocalization
    STATUS      current
    DESCRIPTION
        "Human-readable canonical address for the protocol specified in
        'xcmCommsOptionValueOID' (eg, 'xcmCOInternetIP') is specified
        in 'xcmCommsOptionsValueString' (eg, '19.242.128.21').

        Usage:  'Overloads' protocol types to yield protocol addresses."
    ::= { xcmCOSpecialTypes 4 }

xcmCOSpecialState OBJECT-IDENTITY
--  SYNTAX      XcmCommsMmgtState
    STATUS      current
    DESCRIPTION
        "The current state of the communications protocol specified
        in 'xcmCommsOptionValueOID' (eg, 'xcmCOInternetIP') is specified
        in 'xcmCommsOptionsValueInteger' (eg, 'opened(9)').

        Usage:  'Overloads' protocol types to yield protocol entity
        states."
    REFERENCE
        "See:   'XcmCommsMgmtState' in XCMI Comms Engine TC."
    ::= { xcmCOSpecialTypes 5 }

xcmCOSpecialConditions OBJECT-IDENTITY
--  SYNTAX      XcmCommsMmgtConditions
    STATUS      current
    DESCRIPTION
        "The current conditions of the communications protocol specified
        in 'xcmCommsOptionValueOID' (eg, 'xcmCOInternetIP') is specified
        in 'xcmCommsOptionsValueInteger' (eg, 'openInProgress').

        Usage:  'Overloads' protocol types to yield protocol entity
        conditions."
    REFERENCE
        "See:   'XcmCommsMgmtConditions' in XCMI Comms Engine TC."
    ::= { xcmCOSpecialTypes 6 }

xcmCOSpecialName OBJECT-IDENTITY
--  SYNTAX      stringLocalization
    STATUS      current
    DESCRIPTION
        "Human-readable directory name for the directory specified in
        'xcmCommsOptionValueOID' (eg, 'xcmCOInternetDNS') is specified
        in 'xcmCommsOptionsValueString' (eg, 'showstopper.sample.com').

        Usage:  'Overloads' directory types to yield directory names."
    ::= { xcmCOSpecialTypes 7 }

xcmCOSpecialSupportedInteger OBJECT-IDENTITY
--  SYNTAX      integerNumber
    STATUS      current


    DESCRIPTION
        "Integer-encoded supported value for the option specified in
        'xcmCommsOptionValueOID' (eg, 'xcmCOOsilanFrameType') is found
        in 'xcmCommsOptionsValueInteger' (eg, 'mac(3)').

        Usage:  'Overloads' option types to yield options supported."
    ::= { xcmCOSpecialTypes 8 }

xcmCOSpecialSupportedString OBJECT-IDENTITY
--  SYNTAX      stringLocalization
    STATUS      current
    DESCRIPTION
        "String-encoded supported value for the option specified in
        'xcmCommsOptionValueOID' (eg, 'xcmCOAppletalkNBPType') is found
        in 'xcmCommsOptionsValueString' (eg, 'LaserPrinter').

        Usage:  'Overloads' option types to yield options supported."
    ::= { xcmCOSpecialTypes 9 }

xcmCOSpecialAcceptAddress OBJECT-IDENTITY
--  SYNTAX      stringLocalization
    STATUS      current
    DESCRIPTION
        "Human-readable 'accept' address for the protocol specified in
        'xcmCommsOptionValueOID' (eg, 'xcmCOInternetIP') is specified
        in 'xcmCommsOptionsValueString' (eg, '19.242.128.21').

        Usage:  'Overloads' protocol types to yield protocol specific
        addresses of remote entities at this protocol layer,
        from which incoming datagrams and/or connections SHALL
        be accepted.

        Usage:  Address format is the protocol specific canonical
        format defined for this protocol type as defined elsewhere in
        this XCMI Comms Config TC."
    ::= { xcmCOSpecialTypes 10 }

xcmCOSpecialAcceptSubnet OBJECT-IDENTITY
--  SYNTAX      stringLocalization
    STATUS      current
    DESCRIPTION
        "Human-readable 'accept' subnet for the protocol specified in
        'xcmCommsOptionValueOID' (eg, 'xcmCOInternetIP') is specified
        in 'xcmCommsOptionsValueString' (eg, '19.242.255.255' as might
        be specified in an 'xcmCOInternetIPSubnetMask' comms option).

        Usage:  'Overloads' protocol types to yield protocol specific
        subnet masks of remote entities at this protocol layer,
        from which incoming datagrams and/or connections SHALL
        be accepted.

        Usage:  Subnet mask format is the protocol specific canonical
        format defined for this protocol type as defined elsewhere in
        this XCMI Comms Config TC."


    ::= { xcmCOSpecialTypes 11 }

xcmCOSpecialRejectAddress OBJECT-IDENTITY
--  SYNTAX      stringLocalization
    STATUS      current
    DESCRIPTION
        "Human-readable 'reject' address for the protocol specified in
        'xcmCommsOptionValueOID' (eg, 'xcmCOInternetIP') is specified
        in 'xcmCommsOptionsValueString' (eg, '19.242.128.21').

        Usage:  'Overloads' protocol types to yield protocol specific
        addresses of remote entities at this protocol layer,
        from which incoming datagrams and/or connections SHALL
        be rejected.

        Usage:  Address format is the protocol specific canonical
        format defined for this protocol type as defined elsewhere in
        this XCMI Comms Config TC."
    ::= { xcmCOSpecialTypes 12 }

xcmCOSpecialRejectSubnet OBJECT-IDENTITY
--  SYNTAX      stringLocalization
    STATUS      current
    DESCRIPTION
        "Human-readable 'reject' subnet for the protocol specified in
        'xcmCommsOptionValueOID' (eg, 'xcmCOInternetIP') is specified
        in 'xcmCommsOptionsValueString' (eg, '19.242.255.255' as might
        be specified in an 'xcmCOInternetIPSubnetMask' comms option).

        Usage:  'Overloads' protocol types to yield protocol specific
        subnet masks of remote entities at this protocol layer,
        from which incoming datagrams and/or connections SHALL
        be rejected.

        Usage:  Subnet mask format is the protocol specific canonical
        format defined for this protocol type as defined elsewhere in
        this XCMI Comms Config TC."
    ::= { xcmCOSpecialTypes 13 }

xcmCOSpecialMaxRequestRetries OBJECT-IDENTITY
--  SYNTAX      Cardinal32 - retries
    STATUS      current
    DESCRIPTION
        "The maximum request retries for the communications protocol
        specified in 'xcmCommsOptionValueOID' (eg, 'xcmCOInternetDNS')
        is specified in 'xcmCommsOptionsValueInteger' (eg, '4' retries).

        Usage:  A value of zero indicates that the request SHALL ONLY be
        attempted once (no retries) before being considered a failure.

        Usage:  'Overloads' protocol types to yield protocol request
        retry limits."
    ::= { xcmCOSpecialTypes 14 }


xcmCOSpecialRequestTimeout OBJECT-IDENTITY
--  SYNTAX      Cardinal32 - seconds
    STATUS      current
    DESCRIPTION
        "The request timeout for the communications protocol
        specified in 'xcmCommsOptionValueOID' (eg, 'xcmCOInternetDNS')
        is specified in 'xcmCommsOptionsValueInteger' (eg, '3' seconds).

        Usage:  A value of zero indicates that the request timeout is a
        local system default (and NOT reported/configured).

        Usage:  'Overloads' protocol types to yield protocol request
        timeout limits."
    ::= { xcmCOSpecialTypes 15 }

xcmCOSpecialSecurity OBJECT-IDENTITY
--  SYNTAX      TruthValue - protocol enable/disable
    STATUS      current
    DESCRIPTION
        "The security protocol (datalink, network, transport layer, etc)
        specified in 'xcmCommsOptionValueOID' (eg, 'xcmCOInternetTLS')
        is enabled and disabled by 'xcmCommsOptionsValueInteger'.

        Usage:  'Overloads' protocol types to configure security for
        datalink, network, transport, and application layer protocols."
    ::= { xcmCOSpecialTypes 16 }

--
--          OSI LAN Protocol Suite
--

xcmCOOsilanSuite
    OBJECT IDENTIFIER ::= { xcmCommsConfigTC 11 }
    -- integerTruthValue

xcmCOOsilanPhysicals
    OBJECT IDENTIFIER ::= { xcmCOOsilanSuite 1100 }
    -- integerTruthValue
xcmCOOsilanConnectorType        -- OSI LAN Connector Type
    OBJECT IDENTIFIER ::= { xcmCOOsilanPhysicals 1 }
    -- integerEnum (1=none, 2=other, 3=rj11, 4=rj45, 5=db9,
    -- 6=bnc, 7=aui, 8=sma, 9=rg48)
xcmCOOsilanConnectorOverride    -- OSI LAN Connector Type Override
    OBJECT IDENTIFIER ::= { xcmCOOsilanConnectorType 1 }
    -- integerEnum (see 'xcmCOOsilanConnectorType' above)
xcmCOOsilanConnectorDetected    -- OSI LAN Connector Type Detected
    OBJECT IDENTIFIER ::= { xcmCOOsilanConnectorType 2 }
    -- integerEnum (see 'xcmCOOsilanConnectorType' above)
xcmCOOsilanConnectorAdaptive    -- OSI LAN Connector Type Adaptive
    OBJECT IDENTIFIER ::= { xcmCOOsilanConnectorType 3 }
    -- integerTruthValue
xcmCOOsilanSignalType           -- OSI LAN Signal Type
    OBJECT IDENTIFIER ::= { xcmCOOsilanPhysicals 2 }


    -- integerEnum
    -- (1=none,
    --  2=other,
    --  3=10baseT, 4=10base2, 5=10base5, 6=10baseFL, - Standard Ethernet
    --
    --  7=100base-TX (HalfDuplex),                   - Fast Ethernet
    --       (This is used for fast ethernet half duplex.
    --         It can be used for 100base-T, 100base-T2, 100base-T4,
    --                            100base-TX, 100base-FX, etc.)
    --
    --  8=100base-TX (FullDuplex),                   - Fast Ethernet
    --      (This is used for fast ethernet full duplex.
    --        It can be used for 100base-T, 100base-T2, 100base-T4,
    --                           100base-TX, 100base-FX, etc.)
    --
    --  9=4mbTokenRing, 10=16mbTokenRing,            - Token Ring
    --  11=100mbTokenRing,                           - Fast Token Ring
    --  12=10baseT (HalfDuplex),
    --  13=10baseT (FullDuplex),
    --
    --  14=1000base-TX (HalfDuplex),                 - 1 Gigabit Etherne
    --         (This is used for gibabit ethernet half duplex.
    --           It can be used for 1000base-T, 1000base-TX, etc.)
    --
    --  15=1000base-TX (FullDuplex)                  - 1 Gigabit Etherne
    --         (This is used for gibabit ethernet full duplex.
    --           It can be used for 1000base-T, 1000base-TX, etc.)
    --
    -- )
    --
    -- This object identifies the values to be used in
    -- SignalOverride and SignalDetected. It does not
    -- specify a row to be returned in the Comms Option Group
    --
    -- This object identifies the values to be used in
    -- SignalOverride and SignalDetected. It does not
    -- specify a row to be returned in the Comms Option Group
xcmCOOsilanSignalOverride       -- OSI LAN Signal Type Override
    OBJECT IDENTIFIER ::= { xcmCOOsilanSignalType 1 }
    -- integerEnum (see 'xcmCOOsilanSignalType' above)
    -- This is the requested signal type
    -- If SignalAdaptive is true 1=none should be the returned
    -- because SignalDetected will return the value being used
    -- This should be implemented as R/W in the Comms Option Group
xcmCOOsilanSignalDetected       -- OSI LAN Signal Type Detected
    OBJECT IDENTIFIER ::= { xcmCOOsilanSignalType 2 }
    -- integerEnum (see 'xcmCOOsilanSignalType' above)
    -- This is signal type in use
    -- This should be implemented as R/O in the Comms Option Group
xcmCOOsilanSignalAdaptive       -- OSI LAN Signal Type Adaptive
    OBJECT IDENTIFIER ::= { xcmCOOsilanSignalType 3 }
    -- integerTruthValue
    -- If true is selected "autodetect" signal type has been selected
    -- If false is selected the SignalOverride value has been selected


    -- This should be implemented as R/W in the Comms Option Group
xcmCOOsilanSignalSupport        -- OSI LAN Signal Type Support
    OBJECT IDENTIFIER ::= { xcmCOOsilanSignalType 4 }
    -- integerEnum (list of 'xcmCOOsilanSignalType' above)
xcmCOOsilanSignalCapability        -- OSI LAN Signal Type Capability
    OBJECT IDENTIFIER ::= { xcmCOOsilanSignalType 5 }
    -- This bit-mask defines the signal types supported by the device.
    -- The current set of values (which MAY be extended in the future)
    -- is given below
    --        1  10 MB simplex                2**0
    --        2  10 MB duplex                 2**1
    --        4  100 MB simplex               2**2
    --        8  100 MB duplex                2**3
    --       16  1 GB simplex                 2**4
    --       32  1 GB duplex                  2**5
    -- Usage:  The set of supported signal types is specified by
    -- adding together the various signals.  For example, the value
    -- 63 indicates that all the signal types are supported and the
    -- value 3 indicates that 10 MB simplex and 10 MB duplex are
    -- supported.
    --      SYNTAX INTEGER (0..2147483647)
    --          biggest int = 2**31-1
xcmCOOsilanCableType            -- OSI LAN Cable Type
    OBJECT IDENTIFIER ::= { xcmCOOsilanPhysicals 3 }
    -- integerEnum (1=none, 2=other,
    -- 3=utp, 4=stp, 5=ftp,                         - Twisted Pair
    -- 6=thinCoax, 7=thickCoax,                     - Coax
    -- 8=fiber)                                     - Fiber
xcmCOOsilanCableOverride        -- OSI LAN Cable Type Override
    OBJECT IDENTIFIER ::= { xcmCOOsilanCableType 1 }
    -- integerEnum (see 'xcmCOOsilanCableType' above)
xcmCOOsilanCableDetected        -- OSI LAN Cable Type Detected
    OBJECT IDENTIFIER ::= { xcmCOOsilanCableType 2 }
    -- integerEnum (see 'xcmCOOsilanCableType' above)
xcmCOOsilanCableAdaptive        -- OSI LAN Cable Type Adaptive
    OBJECT IDENTIFIER ::= { xcmCOOsilanCableType 3 }
    -- integerTruthValue
xcmCOOsilanCableSupport         -- OSI LAN Cable Type Support
    OBJECT IDENTIFIER ::= { xcmCOOsilanCableType 4 }
    -- integerEnum (list of 'xcmCOOsilanCableType' above)

xcmCOOsilanDatalinks
    OBJECT IDENTIFIER ::= { xcmCOOsilanSuite 1200 }
    -- integerTruthValue (w/ chain of 'xcmCOOsilan...')
xcmCOOsilanFrameType            -- OSI LAN Frame Type
    OBJECT IDENTIFIER ::= { xcmCOOsilanSuite 1201 }
    -- integerEnum (1=llc, 2=snap, 3=mac, 4=ethernetII, 5=adaptive)
    -- (Ethernet [IEEE 802.3] supports all five of above frame types)
    -- (ALL others [IEEE 802.x] support ONLY llc, snap, or adaptive)
    -- ('adaptive' obsoleted by 'xcmCOOsilanFrameTypeAdaptive' below)
xcmCOOsilanFrameOverride        -- OSI LAN Frame Type Override
    OBJECT IDENTIFIER ::= { xcmCOOsilanFrameType 1 }
    -- integerEnum (see 'xcmCOOsilanFrameType' above)
xcmCOOsilanFrameDetected        -- OSI LAN Frame Type Detected


    OBJECT IDENTIFIER ::= { xcmCOOsilanFrameType 2 }
    -- integerEnum (see 'xcmCOOsilanFrameType' above)
xcmCOOsilanFrameAdaptive        -- OSI LAN Frame Type Adaptive
    OBJECT IDENTIFIER ::= { xcmCOOsilanFrameType 3 }
    -- integerTruthValue
    -- (obsoletes 'adaptive' in 'xcmCOOsilanFrameType' above)
xcmCOOsilanEthernet             -- OSI LAN Ethernet (IEEE 802.3)
    OBJECT IDENTIFIER ::= { xcmCOOsilanSuite 1203 }
    -- integerTruthValue
xcmCOOsilanTokenBus             -- OSI LAN Token Bus (IEEE 802.4)
    OBJECT IDENTIFIER ::= { xcmCOOsilanSuite 1204 }
    -- integerTruthValue
xcmCOOsilanTokenRing            -- OSI LAN Token Ring (IEEE 802.5)
    OBJECT IDENTIFIER ::= { xcmCOOsilanSuite 1205 }
    -- integerTruthValue
xcmCOOsilanFDDI                 -- OSI LAN FDDI
    OBJECT IDENTIFIER ::= { xcmCOOsilanSuite 1207 }
    -- integerTruthValue

xcmCOOsilanEthernetType         -- OSI LAN Ethernet Adapter Type
    OBJECT IDENTIFIER ::= { xcmCOOsilanEthernet 1 }
    -- integerEnum (1=none, 2=other,
    -- 3=integral,                      - adapter on system board
    -- 4=isa,                           - adapter on ISA interface
    -- 5=eisa,                          - adapter on EISA interface
    -- 6=pci,                           - adapter on PCI interface
    -- 7=pcmcia)                        - adapter on PCMCIA interface
xcmCOOsilanEthernetDevice
    OBJECT IDENTIFIER ::= { xcmCOOsilanEthernet 2 }
    -- integerNumber ('hrDeviceIndex' in IETF HR MIB, or 0=unknown)
xcmCOOsilanEthernetDeviceName
    OBJECT IDENTIFIER ::= { xcmCOOsilanEthernetDevice 1 }
    -- stringLocalization ('xcmHrDevInfoName' in HRX, eg, '/dev/elan1')
xcmCOOsilanEthernetSpeed
    OBJECT IDENTIFIER ::= { xcmCOOsilanEthernet 3 }
    -- integerNumber (as in 'ifSpeed' in IETF MIB-II)
xcmCOOsilanEthernetSpeedOverride
    OBJECT IDENTIFIER ::= { xcmCOOsilanEthernetSpeed 1 }
    -- integerNumber (see 'xcmCOOsilanEthernetSpeed' above)
xcmCOOsilanEthernetSpeedDetected
    OBJECT IDENTIFIER ::= { xcmCOOsilanEthernetSpeed 2 }
    -- integerNumber (see 'xcmCOOsilanEthernetSpeed' above)
xcmCOOsilanEthernetSpeedAdaptive
    OBJECT IDENTIFIER ::= { xcmCOOsilanEthernetSpeed 3 }
    -- integerTruthValue
xcmCOOsilanEthernetSpeedSupport
    OBJECT IDENTIFIER ::= { xcmCOOsilanEthernetSpeed 4 }
    -- integerNumber (as in 'ifSpeed' in IETF MIB-II, list of speeds)
xcmCOOsilanEthernetMinSpeed
    OBJECT IDENTIFIER ::= { xcmCOOsilanEthernetSpeed 5 }
    -- integerNumber (as in 'ifSpeed' in IETF MIB-II)
xcmCOOsilanEthernetMaxSpeed
    OBJECT IDENTIFIER ::= { xcmCOOsilanEthernetSpeed 6 }
    -- integerNumber (as in 'ifSpeed' in IETF MIB-II)


xcmCOOsilanEthernetMaxFrameSize
    OBJECT IDENTIFIER ::= { xcmCOOsilanEthernet 4 }
    -- integerNumber (as in 'ifMtu' in IETF MIB-II)
xcmCOOsilanEthernetInterface
    OBJECT IDENTIFIER ::= { xcmCOOsilanEthernet 5 }
    -- integerNumber ('ifIndex' in IETF MIB-II, or 0=unknown)
xcmCOOsilanEthernetMACAddress
    OBJECT IDENTIFIER ::= { xcmCOOsilanEthernet 6 }
    -- stringLocalization (hex format, MAC address)
    -- ([12 octets] - ASCII hex of IEEE 802.x MAC address)
    -- (MAC address in 'ifPhysAddress' in IETF MIB-II)

xcmCOOsilanTokenRingType        -- OSI LAN Token Ring Adapter Type
    OBJECT IDENTIFIER ::= { xcmCOOsilanTokenRing 1 }
    -- integerEnum (1=none, 2=other,
    -- 3=integral,                      - adapter on system board
    -- 4=isa,                           - adapter on ISA interface
    -- 5=eisa,                          - adapter on EISA interface
    -- 6=pci,                           - adapter on PCI interface
    -- 7=pcmcia)                        - adapter on PCMCIA interface
xcmCOOsilanTokenRingDevice
    OBJECT IDENTIFIER ::= { xcmCOOsilanTokenRing 2 }
    -- integerNumber ('hrDeviceIndex' in IETF HR MIB, or 0=unknown)
xcmCOOsilanTokenRingDeviceName
    OBJECT IDENTIFIER ::= { xcmCOOsilanTokenRingDevice 1 }
    -- stringLocalization ('xcmHrDevInfoName' in HRX, eg, '/dev/trlan1')
xcmCOOsilanTokenRingSpeed
    OBJECT IDENTIFIER ::= { xcmCOOsilanTokenRing 3 }
    -- integerNumber (as in 'ifSpeed' in IETF MIB-II)
xcmCOOsilanTokenRingSpeedOverride
    OBJECT IDENTIFIER ::= { xcmCOOsilanTokenRingSpeed 1 }
    -- integerNumber (see 'xcmCOOsilanTokenRingSpeed' above)
xcmCOOsilanTokenRingSpeedDetected
    OBJECT IDENTIFIER ::= { xcmCOOsilanTokenRingSpeed 2 }
    -- integerNumber (see 'xcmCOOsilanTokenRingSpeed' above)
xcmCOOsilanTokenRingSpeedAdaptive
    OBJECT IDENTIFIER ::= { xcmCOOsilanTokenRingSpeed 3 }
    -- integerTruthValue
xcmCOOsilanTokenRingSpeedSupport
    OBJECT IDENTIFIER ::= { xcmCOOsilanTokenRingSpeed 4 }
    -- integerNumber (as in 'ifSpeed' in IETF MIB-II, list of speeds)
xcmCOOsilanTokenRingMinSpeed
    OBJECT IDENTIFIER ::= { xcmCOOsilanTokenRingSpeed 5 }
    -- integerNumber (as in 'ifSpeed' in IETF MIB-II)
xcmCOOsilanTokenRingMaxSpeed
    OBJECT IDENTIFIER ::= { xcmCOOsilanTokenRingSpeed 6 }
    -- integerNumber (as in 'ifSpeed' in IETF MIB-II)
xcmCOOsilanTokenRingMaxFrameSize
    OBJECT IDENTIFIER ::= { xcmCOOsilanTokenRing 4 }
    -- integerNumber (as in 'ifMtu' in IETF MIB-II)
xcmCOOsilanTokenRingInterface
    OBJECT IDENTIFIER ::= { xcmCOOsilanTokenRing 5 }
    -- integerNumber ('ifIndex' in IETF MIB-II, or 0=unknown)
xcmCOOsilanTokenRingMACAddress


    OBJECT IDENTIFIER ::= { xcmCOOsilanTokenRing 6 }
    -- stringLocalization (hex format, MAC address)
    -- ([12 octets] - ASCII hex of IEEE 802.x MAC address)
    -- ('burned in' MAC address, MAY be 'ifPhysAddress' in IETF MIB-II)
    -- See: 'xcmCOOsilanTokenRingMACOverride' below
xcmCOOsilanTokenRingSSR         -- OSI LAN Token Ring Source Stn Route
    OBJECT IDENTIFIER ::= { xcmCOOsilanTokenRing 11 }
    -- integerTruthValue (true=enableSSR, false=disableSSR)
    -- See: IBM Token Ring Network Architecture Reference, SC30-3374-01,
    --      page 2-3 'Source Routing', page 2-8 'Broadcast Terminology',
    --      and page 3-8 'Routing Information Field'
    -- See: 'xcmCOOsilanTokenRing[AllRoute|SingleRR|Adaptive]' below
xcmCOOsilanTokenRingSSRAllRoute -- OSI LAN Token Ring All Route Request
    OBJECT IDENTIFIER ::= { xcmCOOsilanTokenRing 12 }
    -- integerTruthValue (true=allRouteReq, false=singleRouteReq)
    -- (true specifies send broadcast requests, when SSR is enabled)
    -- (false specifies send unicast requests, when SSR is enabled)
xcmCOOsilanTokenRingSSRSingleRR -- OSI LAN Token Ring Single Route Resp
    OBJECT IDENTIFIER ::= { xcmCOOsilanTokenRing 13 }
    -- integerTruthValue (true=singleRouteResp, false=allRouteResp)
    -- (true specifies send unicast responses, when SSR is enabled)
    -- (false specifies send broadcast responses, when SSR is enabled)
xcmCOOsilanTokenRingSSRAdaptive -- OSI LAN Token Ring Adaptive
    OBJECT IDENTIFIER ::= { xcmCOOsilanTokenRing 14 }
    -- integerTruthValue (true=adaptive, false=static)
    -- (true specifies sniff local subnetwork, when SSR is enabled)
    -- (false specifies use 'xcmCOOsilanTokenRing[AllRoute|SingleRR]')
xcmCOOsilanTokenRingMACOverride -- OSI LAN Token Ring MAC Override
    OBJECT IDENTIFIER ::= { xcmCOOsilanTokenRing 21 }
    -- stringLocalization (hex format, MAC address)
    -- ([12 octets] - ASCII hex of IEEE 802.x MAC address)
    -- (specifies the local MAC address of this token ring station)
    -- (MAY be used to override 'burned in' hardware address in
    -- 'xcmCOOsilanTokenRingMACAddress' and FORCE 'ifPhysAddress')
    -- See: 'xcmCOOsilanTokenRingMACAddress' above

--
--          OSI WAN Protocol Suite
--

xcmCOOsiwanSuite
    OBJECT IDENTIFIER ::= { xcmCommsConfigTC 13 }
    -- integerTruthValue

xcmCOOsiwanPhysicals
    OBJECT IDENTIFIER ::= { xcmCOOsiwanSuite 1100 }
    -- integerTruthValue
xcmCOOsiwanConnectorType        -- OSI WAN Connector Type
    OBJECT IDENTIFIER ::= { xcmCOOsiwanPhysicals 1 }
    -- integerEnum (1=none, 2=other, 3=rj11, 4=rj45)
xcmCOOsiwanConnectorOverride    -- OSI WAN Connector Type Override
    OBJECT IDENTIFIER ::= { xcmCOOsiwanConnectorType 1 }
    -- integerEnum (see 'xcmCOOsiwanConnectorType' above)
xcmCOOsiwanConnectorDetected    -- OSI WAN Connector Type Detected


    OBJECT IDENTIFIER ::= { xcmCOOsiwanConnectorType 2 }
    -- integerEnum (see 'xcmCOOsiwanConnectorType' above)
xcmCOOsiwanConnectorAdaptive    -- OSI WAN Connector Type Adaptive
    OBJECT IDENTIFIER ::= { xcmCOOsiwanConnectorType 3 }
    -- integerTruthValue
xcmCOOsiwanSignalType           -- OSI WAN Signal Type
    OBJECT IDENTIFIER ::= { xcmCOOsiwanPhysicals 2 }
    -- integerEnum (1=none, 2=other, 3=tone, 4=pulse)
xcmCOOsiwanSignalOverride       -- OSI WAN Signal Type Override
    OBJECT IDENTIFIER ::= { xcmCOOsiwanSignalType 1 }
    -- integerEnum (see 'xcmCOOsiwanSignalType' above)
xcmCOOsiwanSignalDetected       -- OSI WAN Signal Type Detected
    OBJECT IDENTIFIER ::= { xcmCOOsiwanSignalType 2 }
    -- integerEnum (see 'xcmCOOsiwanSignalType' above)
xcmCOOsiwanSignalAdaptive       -- OSI WAN Signal Type Adaptive
    OBJECT IDENTIFIER ::= { xcmCOOsiwanSignalType 3 }
    -- integerTruthValue
xcmCOOsiwanSignalSupport        -- OSI WAN Signal Type Support
    OBJECT IDENTIFIER ::= { xcmCOOsiwanSignalType 4 }
    -- integerEnum (list of 'xcmCOOsiwanSignalType' above)
xcmCOOsiwanLineNumber           -- OSI WAN Line Number
    OBJECT IDENTIFIER ::= { xcmCOOsiwanPhysicals 4 }
    -- integerNumber (1=default or 1..n)
xcmCOOsiwanSendManual           -- OSI WAN Receive Manual
    OBJECT IDENTIFIER ::= { xcmCOOsiwanPhysicals 5 }
    -- integerTruthValue (true=sendManual, false=sendAuto)
xcmCOOsiwanReceiveManual        -- OSI WAN Receive Manual
    OBJECT IDENTIFIER ::= { xcmCOOsiwanPhysicals 6 }
    -- integerTruthValue (true=receiveManual, false=receiveAuto)
xcmCOOsiwanRingsBeforeAnswer    -- OSI WAN Rings Before Answer
    OBJECT IDENTIFIER ::= { xcmCOOsiwanPhysicals 7 }
    -- integerNumber (1..n)
xcmCOOsiwanErrorCorrection      -- OSI WAN Error Correction
    OBJECT IDENTIFIER ::= { xcmCOOsiwanPhysicals 8 }
    -- integerTruthValue
xcmCOOsiwanDirection            -- OSI WAN Direction
    OBJECT IDENTIFIER ::= { xcmCOOsiwanPhysicals 9 }
    -- integerEnum (1=sendAndReceive, 2=sendOnly, 3=receiveOnly)
xcmCOOsiwanSendStartTime        -- OSI WAN Send Start Time
    OBJECT IDENTIFIER ::= { xcmCOOsiwanPhysicals 10 }
    -- integerNumber (XcmHrDevCalendarTimeOfDay in XCMI HRX TC)
xcmCOOsiwanSendEndTime          -- OSI WAN Send End Time
    OBJECT IDENTIFIER ::= { xcmCOOsiwanPhysicals 11 }
    -- integerNumber (XcmHrDevCalendarTimeOfDay in XCMI HRX TC)
xcmCOOsiwanReceiveStartTime     -- OSI WAN Receive Start Time
    OBJECT IDENTIFIER ::= { xcmCOOsiwanPhysicals 12 }
    -- integerNumber (XcmHrDevCalendarTimeOfDay in XCMI HRX TC)
xcmCOOsiwanReceiveEndTime       -- OSI WAN Receive End Time
    OBJECT IDENTIFIER ::= { xcmCOOsiwanPhysicals 13 }
    -- integerNumber (XcmHrDevCalendarTimeOfDay in XCMI HRX TC)
xcmCOOsiwanRingerVolume         -- OSI WAN Ringer Volume
    OBJECT IDENTIFIER ::= { xcmCOOsiwanPhysicals 20 }
    -- integerNumber (0=off, or 1..100)
xcmCOOsiwanMonitorVolume        -- OSI WAN Monitor Volume


    OBJECT IDENTIFIER ::= { xcmCOOsiwanPhysicals 21 }
    -- integerNumber (0=off, or 1..100)
xcmCOOsiwanAlarmVolume          -- OSI WAN Alarm Volume
    OBJECT IDENTIFIER ::= { xcmCOOsiwanPhysicals 22 }
    -- integerNumber (0=off, or 1..100)
xcmCOOsiwanKeyboardVolume       -- OSI WAN Keyboard Volume
    OBJECT IDENTIFIER ::= { xcmCOOsiwanPhysicals 23 }
    -- integerNumber (0=off, or 1..100)

xcmCOOsiwanDatalinks
    OBJECT IDENTIFIER ::= { xcmCOOsiwanSuite 1200 }
    -- integerTruthValue (w/ chain of 'xcmCOOsiwan...')
xcmCOOsiwanFax                  -- CCITT Fax (facsimile)
    OBJECT IDENTIFIER ::= { xcmCOOsiwanSuite 1241 }
    -- integerTruthValue
xcmCOOsiwanPSTN                 -- CCITT PSTN (analog telephone)
    OBJECT IDENTIFIER ::= { xcmCOOsiwanSuite 1251 }
    -- integerTruthValue
xcmCOOsiwanISDN                 -- CCITT ISDN (digital telephone)
    OBJECT IDENTIFIER ::= { xcmCOOsiwanSuite 1261 }
    -- integerTruthValue

xcmCOOsiwanFaxAddress
    OBJECT IDENTIFIER ::= { xcmCOOsiwanFax 1 }
    -- stringLocalization
xcmCOOsiwanFaxDevice
    OBJECT IDENTIFIER ::= { xcmCOOsiwanFax 2 }
    -- integerNumber ('hrDeviceIndex' in IETF HR MIB, or 0=unknown)
xcmCOOsiwanFaxDeviceName
    OBJECT IDENTIFIER ::= { xcmCOOsiwanFaxDevice 1 }
    -- stringLocalization ('xcmHrDevInfoName' in HRX, eg, '/dev/lpr1')
xcmCOOsiwanFaxSpeed
    OBJECT IDENTIFIER ::= { xcmCOOsiwanFax 3 }
    -- integerNumber (as in 'ifSpeed' in IETF MIB-II)
xcmCOOsiwanFaxSpeedOverride
    OBJECT IDENTIFIER ::= { xcmCOOsiwanFaxSpeed 1 }
    -- integerNumber (see 'xcmCOOsiwanFaxSpeed' above)
xcmCOOsiwanFaxSpeedDetected
    OBJECT IDENTIFIER ::= { xcmCOOsiwanFaxSpeed 2 }
    -- integerNumber (see 'xcmCOOsiwanFaxSpeed' above)
xcmCOOsiwanFaxSpeedAdaptive
    OBJECT IDENTIFIER ::= { xcmCOOsiwanFaxSpeed 3 }
    -- integerTruthValue
xcmCOOsiwanFaxSpeedSupport
    OBJECT IDENTIFIER ::= { xcmCOOsiwanFaxSpeed 4 }
    -- integerNumber (as in 'ifSpeed' in IETF MIB-II, list of speeds)
xcmCOOsiwanFaxMinSpeed
    OBJECT IDENTIFIER ::= { xcmCOOsiwanFaxSpeed 5 }
    -- integerNumber (as in 'ifSpeed' in IETF MIB-II)
xcmCOOsiwanFaxMaxSpeed
    OBJECT IDENTIFIER ::= { xcmCOOsiwanFaxSpeed 6 }
    -- integerNumber (as in 'ifSpeed' in IETF MIB-II)
xcmCOOsiwanFaxInterface
    OBJECT IDENTIFIER ::= { xcmCOOsiwanFax 5 }


    -- integerNumber ('ifIndex' in IETF MIB-II, or 0=unknown)
xcmCOOsiwanFaxAcceptAddress     -- CCITT Fax Accept Address (list)
    OBJECT IDENTIFIER ::= { xcmCOOsiwanFax 11 }
    -- stringLocalization (used for both send and receive)
xcmCOOsiwanFaxRejectAddress     -- CCITT Fax Reject Address (list)
    OBJECT IDENTIFIER ::= { xcmCOOsiwanFax 12 }
    -- stringLocalization (used for both send and receive)
xcmCOOsiwanFaxSendCoverSheet    -- CCITT Fax Send Add Cover Sheet
    OBJECT IDENTIFIER ::= { xcmCOOsiwanFax 20 }
    -- integerTruthValue
xcmCOOsiwanFaxSendHeader        -- CCITT Fax Send Add Header
    OBJECT IDENTIFIER ::= { xcmCOOsiwanFax 21 }
    -- integerTruthValue
xcmCOOsiwanFaxSendManual        -- CCITT Fax Send Manual
    OBJECT IDENTIFIER ::= { xcmCOOsiwanFax 22 }
    -- integerTruthValue (true=sendManual, false=sendAuto)
xcmCOOsiwanFaxSendSecurity      -- CCITT Fax Send Security
    OBJECT IDENTIFIER ::= { xcmCOOsiwanFax 23 }
    -- integerTruthValue (true=checkRemoteAddress, false=noSecurity)
xcmCOOsiwanFaxMaxRetries        -- CCITT Fax Send Max Retries
    OBJECT IDENTIFIER ::= { xcmCOOsiwanFax 24 }
    -- integerNumber (0=immediate, or 1..n)
xcmCOOsiwanFaxRetryInterval     -- CCITT Fax Send Retry Interval
    OBJECT IDENTIFIER ::= { xcmCOOsiwanFax 25 }
    -- integerNumber (seconds, 0=none, or 1..n)
xcmCOOsiwanFaxSendStoreTime     -- CCITT Fax Send Store For Later Time
    OBJECT IDENTIFIER ::= { xcmCOOsiwanFax 26 }
    -- integerNumber (seconds, 0=discard, or 1..n)
xcmCOOsiwanFaxMaxOriginalLength -- CCITT Fax Send Max Original Length
    OBJECT IDENTIFIER ::= { xcmCOOsiwanFax 27 }
    -- integerNumber (millimeters, 0=infinite, or 1..n)
xcmCOOsiwanFaxReceiveCoverSheet -- CCITT Fax Receive Add Cover Sheet
    OBJECT IDENTIFIER ::= { xcmCOOsiwanFax 30 }
    -- integerTruthValue
xcmCOOsiwanFaxReceiveFooter     -- CCITT Fax Receive Print Footer
    OBJECT IDENTIFIER ::= { xcmCOOsiwanFax 31 }
    -- integerTruthValue
xcmCOOsiwanFaxReceiveToMemory   -- CCITT Fax Receive To Memory
    OBJECT IDENTIFIER ::= { xcmCOOsiwanFax 32 }
    -- integerTruthValue (true=receiveToMemory, false=rejectReceive)
xcmCOOsiwanFaxReceiveManual     -- CCITT Fax Receive Manual
    OBJECT IDENTIFIER ::= { xcmCOOsiwanFax 33 }
    -- integerTruthValue (true=receiveManual, false=receiveAuto)
xcmCOOsiwanFaxReceiveSecurity   -- CCITT Fax Receive Security
    OBJECT IDENTIFIER ::= { xcmCOOsiwanFax 34 }
    -- integerTruthValue (true=checkRemoteAddress, false=noSecurity)
xcmCOOsiwanFaxReceiveAutoReduce -- CCITT Fax Receive Auto Reduce To Fit
    OBJECT IDENTIFIER ::= { xcmCOOsiwanFax 35 }
    -- integerTruthValue (true=autoReduce, false=noAutoReduce)
xcmCOOsiwanFaxReceiveOverflow   -- CCITT Fax Receive Overflow To Next
    OBJECT IDENTIFIER ::= { xcmCOOsiwanFax 36 }
    -- integerTruthValue
xcmCOOsiwanFaxReceiveCollate    -- CCITT Fax Receive Collate
    OBJECT IDENTIFIER ::= { xcmCOOsiwanFax 37 }


    -- integerTruthValue

xcmCOOsiwanFaxG3                -- CCITT Fax G3 Mode
    OBJECT IDENTIFIER ::= { xcmCOOsiwanFax 40 }
    -- integerTruthValue (true=enableG3, false=disableG3)

xcmCOOsiwanFaxG4                -- CCITT Fax G4 Mode
    OBJECT IDENTIFIER ::= { xcmCOOsiwanFax 41 }
    -- integerTruthValue (true=enableG4, false=disableG4)

xcmCOOsiwanFaxLineSwitching     -- CCITT Fax Line Switching
    OBJECT IDENTIFIER ::= { xcmCOOsiwanFax 42 }
    -- integerTruthValue (enable/disable internal/external line switch)

xcmCOOsiwanFaxMaxSpeedDial      -- CCITT Fax Max Speed Dial Entries
    OBJECT IDENTIFIER ::= { xcmCOOsiwanFax 43 }
    -- integerNumber (fax max speed dial entries)
    -- (see - 'XcmCommsDirRecordType' in XCMI TC, especially
    -- 'recordSpeedDial' and 'recordSpeedDialGroup' records)
    -- (see - 'XcmCommsDirAttributeType' in XCMI CC TC, especially
    -- 'service...' and 'speedDial...' attributes)

xcmCOOsiwanPSTNAddress          -- CCITT PSTN (analog telephone)
    OBJECT IDENTIFIER ::= { xcmCOOsiwanPSTN 1 }
    -- stringLocalization

xcmCOOsiwanISDNAddress          -- CCITT ISDN (digital telephone)
    OBJECT IDENTIFIER ::= { xcmCOOsiwanISDN 1 }
    -- stringLocalization

xcmCOOsiwanTransports
    OBJECT IDENTIFIER ::= { xcmCOOsiwanSuite 1400 }
    -- integerTruthValue

xcmCOOsiwanApplications
    OBJECT IDENTIFIER ::= { xcmCOOsiwanSuite 1700 }
    -- integerTruthValue
xcmCOOsiwanDPA                          -- ISO 10175 (printing)
    OBJECT IDENTIFIER ::= { xcmCOOsiwanSuite 1713 }
    -- integerTruthValue
xcmCOOsiwanFTAM                         -- ISO 8571 (filing)
    OBJECT IDENTIFIER ::= { xcmCOOsiwanSuite 1714 }
    -- integerTruthValue
xcmCOOsiwanVT                           -- ISO 9041 (terminal)
    OBJECT IDENTIFIER ::= { xcmCOOsiwanSuite 1716 }
    -- integerTruthValue
xcmCOOsiwanMHS                          -- CCITT X.400 (email)
    OBJECT IDENTIFIER ::= { xcmCOOsiwanSuite 1740 }
    -- integerTruthValue
xcmCOOsiwanDS                           -- CCITT X.500 (directory)
    OBJECT IDENTIFIER ::= { xcmCOOsiwanSuite 1750 }
    -- integerTruthValue
xcmCOOsiwanDAP                          -- CCITT X.500 DAP (access)
    OBJECT IDENTIFIER ::= { xcmCOOsiwanSuite 1751 }


    -- integerTruthValue
xcmCOOsiwanDSP                          -- CCITT X.500 DSP (backbones)
    OBJECT IDENTIFIER ::= { xcmCOOsiwanSuite 1752 }
    -- integerTruthValue
xcmCOOsiwanMgmt                         -- CCITT X.700 (system mgmt)
    OBJECT IDENTIFIER ::= { xcmCOOsiwanSuite 1770 }
    -- integerTruthValue
xcmCOOsiwanCMIP                         -- CCITT X.710/X.711 CMIP (mgmt)
    OBJECT IDENTIFIER ::= { xcmCOOsiwanSuite 1771 }
    -- integerTruthValue
xcmCOOsiwanSecurity                     -- CCITT X.800 (system security)
    OBJECT IDENTIFIER ::= { xcmCOOsiwanSuite 1780 }
    -- integerTruthValue

--
--          Internet Protocol Suite
--

xcmCOInternetSuite
    OBJECT IDENTIFIER ::= { xcmCommsConfigTC 14 }
    -- integerTruthValue

xcmCOInternetDatalinks
    OBJECT IDENTIFIER ::= { xcmCOInternetSuite 1200 }
    -- integerTruthValue (w/ chain of 'xcmCOOsilan...')
    -- (obsoletes 'xcmCOInternetIPDatalinks')
xcmCOInternetSLIP               -- SLIP (serial datalink)
    OBJECT IDENTIFIER ::= { xcmCOInternetSuite 1201 }
    -- integerTruthValue
xcmCOInternetPPP                -- PPP (serial datalink)
    OBJECT IDENTIFIER ::= { xcmCOInternetSuite 1202 }
    -- integerTruthValue

xcmCOInternetTransports
    OBJECT IDENTIFIER ::= { xcmCOInternetSuite 1400 }
    -- integerTruthValue
xcmCOInternetIP                 -- IP (CL network)
    OBJECT IDENTIFIER ::= { xcmCOInternetSuite 1301 }
    -- integerTruthValue
xcmCOInternetICMP               -- ICMP (layer management - network)
    OBJECT IDENTIFIER ::= { xcmCOInternetSuite 1302 }
    -- integerTruthValue
xcmCOInternetARP                -- ARP (routing)
    OBJECT IDENTIFIER ::= { xcmCOInternetSuite 1303 }
    -- integerTruthValue
xcmCOInternetDHCP               -- DHCP (routing/boot)
    OBJECT IDENTIFIER ::= { xcmCOInternetSuite 1304 }
    -- integerTruthValue
xcmCOInternetBOOTP              -- BOOTP (routing/boot)
    OBJECT IDENTIFIER ::= { xcmCOInternetSuite 1305 }
    -- integerTruthValue

xcmCOInternetBOOTPBroadcastEnabled
   OBJECT IDENTIFIER ::= { xcmCOInternetBOOTP 1}


    -- integerTruthValue (true=enableBOOTPBroadcast,
    --                    false=disableBOOTPBroadcast)

xcmCOInternetRARP               -- RARP (routing/boot)
    OBJECT IDENTIFIER ::= { xcmCOInternetSuite 1306 }
    -- integerTruthValue
xcmCOInternetIPv6               -- IPv6 (CL Network, RFC 2460)
    OBJECT IDENTIFIER ::= { xcmCOInternetSuite 1310 }
    -- integerTruthValue
xcmCOInternetUDP                -- UDP (CL transport)
    OBJECT IDENTIFIER ::= { xcmCOInternetSuite 1401 }
    -- integerTruthValue
xcmCOInternetTCP                -- TCP (CO transport)
    OBJECT IDENTIFIER ::= { xcmCOInternetSuite 1402 }
    -- integerTruthValue
xcmCOInternetPing               -- Ping (echo)
    OBJECT IDENTIFIER ::= { xcmCOInternetSuite 1404 }
    -- integerTruthValue
xcmCOInternetSSL3               -- SSL3 (security)
    OBJECT IDENTIFIER ::= { xcmCOInternetSuite 1405 }
    -- integerTruthValue
    -- (Netscape Secure Sockets Layer v3)
xcmCOInternetTLS                -- TLS (security)
    OBJECT IDENTIFIER ::= { xcmCOInternetSuite 1406 }
    -- integerTruthValue
    -- (see RFC 2246, TLS Protocol v1.0, January 1999)

xcmCOInternetICMPv6               -- ICMPv6 (RFC 2463)
    OBJECT IDENTIFIER ::= { xcmCOInternetSuite 1410 }
    -- integerTruthValue

xcmCOInternetSSL3Port               -- SSL3 port number
    OBJECT IDENTIFIER ::= { xcmCOInternetSSL3 1 }
    -- integerNumber

xcmCOInternetSSL3CipherStrength        -- SSL3 Cipher Strength
    OBJECT IDENTIFIER ::= { xcmCOInternetSSL3 2 }
    -- Cipher encryption strength used to control the set of
    --  supported ciphers when using SSL (e.g. to enforce
    --  128-bit or higher encryption keys).
    -- integerNumber
    -- 0=custom, 40, 56, 128, 168, 256, etc.
    -- (e.g. 40 enforces all encryption keys 40-bit or higher,
    --  128 enforces all encryption keys 128-bit or higher)
    -- 0=custom allows choice of specific encryption keys

xcmCOInternetIPAddress          -- IP Node Address
    OBJECT IDENTIFIER ::= { xcmCOInternetIP 1 }
    -- stringLocalization (IPv4 - dotted decimal 'a.b.c.d')
    -- (IPv4 - decimal values [1-3 octets] of four 8-bit components)
    -- (eg, '13.226.19.10')

xcmCOInternetIPv6Address          -- IPv6 Node Address
    OBJECT IDENTIFIER ::= { xcmCOInternetIPv6 1 }


    -- (IPv6 - eight hex values [0-4 octets] of 16-bit components
    --  optionally followed by '/' and prefix length [1-3 octets] -
    --  ASCII decimal of 1-octet prefix length)
    -- (eg, 'FEDC:BA98:7654:3210/64')
    -- (see section 2.2 'Textual Representation of Addresses' and
    --  section 2.3 'Text Representation of Address Prefixes' in
    -- RFC 2373, IPv6 Addressing Architecture)
    -- (see section 2 'Literal IPv6 Address Format in URL Syntax' in
    -- RFC 2732, Format for Literal IPv6 Addresses in URLs)

xcmCOInternetIPSocketAddress    -- IP Socket Address
    OBJECT IDENTIFIER ::= { xcmCOInternetIPAddress 1 }
    -- stringLocalization (IPv4 - dotted decimal 'a.b.c.d:socket')
    -- (note - in IPv4 ONLY, a dot '.' MAY also be used before 'socket'
    -- and such use of dot was recommended in XCMI v4.0 and earlier)
    -- (see 'xcmCOInternetIPAddress' for references)

xcmCOInternetIPv6SocketAddress    -- IPv6 Socket Address
    OBJECT IDENTIFIER ::= { xcmCOInternetIPv6Address 1 }
    -- stringLocalization (IPv6 - hex w/ colons '[x1:...:x8/ppp]:socket'
    -- ('socket' [1-5 octets] - ASCII decimal of 2-octet socket)
    -- (see 'xcmCOInternetIPv6Address' for references)

xcmCOInternetIPv6ManuallyAssignedAddress
    OBJECT IDENTIFIER ::= { xcmCOInternetIPv6Address 2 }
    -- stringLocalization (IPv6 - hex w/ colons '[x1:...:x8/yyy]')
    -- (see 'xcmCOInternetIPv6Address' for references)
    -- Indicates an address that was manually configured, e.g., by user
    -- configuration.

xcmCOInternetIPv6DHCPv6AssignedAddress
    OBJECT IDENTIFIER ::= { xcmCOInternetIPv6Address 3 }
    -- stringLocalization (IPv6 - hex w/ colons '[x1:...:x8/yyy]')
    -- (see 'xcmCOInternetIPv6Address' for references)
    -- Indicates an address that was assigned to this system by
    -- a DHCPv6 server.

xcmCOInternetIPv6LinkLocalAddress
    OBJECT IDENTIFIER ::= { xcmCOInternetIPv6Address 4 }
    -- stringLocalization (IPv6 - hex w/ colons '[x1:...:x8/yyy]')
    -- (see 'xcmCOInternetIPv6Address' for references)
    -- Indicates the address created with the link local prefix fe80
    -- and the EUI-64 interface id by IPv6 stateless auto-configuration.

xcmCOInternetIPv6StatelessAddress
    OBJECT IDENTIFIER ::= { xcmCOInternetIPv6Address 5 }
    -- stringLocalization (IPv6 - hex w/ colons '[x1:...:x8/yyy]')
    -- (see 'xcmCOInternetIPv6Address' for references)
    -- Indicates an address created by IPv6 stateless auto-configuration

xcmCOInternetIPv6RandomAddress
    OBJECT IDENTIFIER ::= { xcmCOInternetIPv6Address 6 }
    -- stringLocalization (IPv6 - hex w/ colons '[x1:...:x8/yyy]')
    -- (see 'xcmCOInternetIPv6Address' for references)


    -- Indicates an address chosen by the system at random, e.g.,
    -- an RFC 3041 privacy address.

xcmCOInternetIPv6AutomaticAddressing
    OBJECT IDENTIFIER ::= { xcmCOInternetIPv6Address 7 }
    -- integerTruthValue

xcmCOInternetIPv6EUI64InterfaceId
    OBJECT IDENTIFIER ::= { xcmCOInternetIPv6 2 }
    -- stringLocalization (IPv6 - hex w/ colons '[x1:...:x8]')
    -- The EUI-64 Interface Identifier generated
    -- automatically by the device from the Ethernet
    -- MAC (physical/link layer) address.

xcmCOInternetIPv6RouterAdvertisementAddressPrefix
    OBJECT IDENTIFIER ::= { xcmCOInternetIPv6 3 }
    -- stringLocalization
    -- (IPv6 - eight hex values [0-4 octets] of 16-bit components
    --  optionally followed by '/' and prefix length [1-3 octets] -
    --  ASCII decimal of 1-octet prefix length)
    -- (eg, 'FEDC:BA98:7654:3210:FEDC:BA98:7654:3210/64')
    -- The IPv6 address prefix values received from
    -- Router Advertisements when a router is present on the local
    -- network per RFC 2462.

xcmCOInternetIPv6DefaultGateway         -- IPv6 Default Gateway
    OBJECT IDENTIFIER ::= { xcmCOInternetIPv6 4 }
    -- stringLocalization (IPv6 - hex w/ colons '[x1:...:x8/yyy]')
    -- (see 'xcmCOInternetIPv6Address' for references)

xcmCOInternetIPv6HostName               -- System Hostname
    OBJECT IDENTIFIER ::= { xcmCOInternetIPv6 5 }
    -- stringLocalization
    -- The HostName used for IPv4 and IPv6 will be one and the same.

xcmCOInternetIPSubnetMask       -- IP Subnet Mask
    OBJECT IDENTIFIER ::= { xcmCOInternetIP 2 }
    -- stringLocalization (IPv4 - dotted decimal 'a.b.c.d')
    -- (see 'xcmCOInternetIPAddress' for references)

xcmCOInternetIPAddressViaRARP   -- IP Address Via RARP (dynamic)
    OBJECT IDENTIFIER ::= { xcmCOInternetIP 3 }
    -- integerTruthValue (true=enableRARP, false=disableRARP)
    -- (if false, then use 'xcmCOInternetIPAddress' value)
    -- (obsoleted by 'xcmCOInternetIPAddressSource')

xcmCOInternetIPDefaultGateway   -- IP Default Gateway
    OBJECT IDENTIFIER ::= { xcmCOInternetIP 4 }
    -- stringLocalization (IPv4 - dotted decimal 'a.b.c.d')
    -- (see 'xcmCOInternetIPAddress' for references)


xcmCOInternetIPAddressSource    -- IP Address Source (static/dynamic)
    OBJECT IDENTIFIER ::= { xcmCOInternetIP 5 }
    -- integerEnum (1=none, 2=other,
    -- 3=static, 4=viaRARP, 5=viaBOOTP, 6=viaDHCP,
    -- 7=viaDHCPAutoIP,
    -- 8=viaAutoIPv6,
    --  (see 'IPv6 Sateless Address Autoconfig', RFC 2462, Dec 1998)
    -- 9=viaAutoIPv4)
    --  (see 'draft-ietf-zeroconf-ipv4-linklocal-17.txt', Jul 2004
    --  and Automatic Private IP Addressing)
    --  (Obsoletes 'xcmCOInternetIPAddressViaRARP')
xcmCOInternetIPDatalinks        -- IP Datalinks
    OBJECT IDENTIFIER ::= { xcmCOInternetIP 12 }
    -- integerTruthValue (w/ chain of 'xcmCOOsilan...')
    -- (obsoleted by 'xcmCOInternetDatalinks')
xcmCOInternetIPHostName         -- IP Host Name
    OBJECT IDENTIFIER ::= { xcmCOInternetIP 50 }
    -- stringLocalization
xcmCOInternetIPAutoIPAddress -- Computed AutoIP Address
OBJECT IDENTIFIER ::= { xcmCOInternetIP 51 }
-- stringLocalization (IPv4 - dotted decimal '1.b.c.d')
-- <or>
-- stringLocalization (IPv6 - hex w/ colons '[x1:...:x8]')
-- (IPv4 - decimal values [1-3 octets] or four 8-bit components)
-- (eg, '13.226.19.10')
-- (IPv6 - eight hex values [0-4 octets] of 16-bit components)
-- (eg, 'FEDC:BA98:7654:3210:FEDC:BA98:7654:3210')
-- (see section 2.2 'Textual Representation of Addresses' in
-- RFC 2373, IPv6 Addressing Architecture)
-- (see section 2 'Literal IPv6 Address Format in URL Syntax' in
-- RFC 2732, Format for Literal IPv6 Addresses in URLs)
xcmCOInternetIPAutoEnable          -- Enable auto IP Address
    OBJECT IDENTIFIER ::= { xcmCOInternetIP 60 }
    -- integerTruthValue (true=enabled, false=disabled)

xcmCOInternetIPBcastCache
   OBJECT IDENTIFIER ::= { xcmCOInternetIP 61 }
   -- The upper level enumeration for the network address
   -- caching for the walkup installation protocol
xcmCOInternetIPInstall
   OBJECT IDENTIFIER ::= { xcmCOInternetIP 62 }
   -- The upper level enumeration for the walkup
   -- installation protocol for device selection

xcmCOInternetIPSec
    OBJECT IDENTIFIER ::= { xcmCOInternetIP 70 }
    -- integerTruthValue (true=enableIPSec, false=disableIPSec)

-- Network Address Caching (xcmCOInternetIPBcastCache)
xcmCOInternetIPBCacheEnabled     -- Network Address Cache Allowed
    OBJECT IDENTIFIER ::= { xcmCOInternetIPBcastCache 1 }
    -- integerTruthValue
    -- (true=enable network addess caching,


    --  false=disable caching)

xcmCOInternetIPBCacheAddress1    -- Network Address Cache 1
    OBJECT IDENTIFIER ::= { xcmCOInternetIPBcastCache 2 }
    -- stringLocalization
    -- The formatting for this string is the
    -- per xcmCOInternetIPAutoIPAddress
xcmCOInternetIPBCacheAddress2    -- Network Address Cache 2
    OBJECT IDENTIFIER ::= { xcmCOInternetIPBcastCache 3 }
    -- stringLocalization
    -- The formatting for this string is the
    -- per xcmCOInternetIPAutoIPAddress
xcmCOInternetIPBCacheAddress3    -- Network Address Cache 3
    OBJECT IDENTIFIER ::= { xcmCOInternetIPBcastCache 4 }
    -- stringLocalization
    -- The formatting for this string is the
    -- per xcmCOInternetIPAutoIPAddress
xcmCOInternetIPBCacheAddress4    -- Network Address Cache 4
    OBJECT IDENTIFIER ::= { xcmCOInternetIPBcastCache 5 }
    -- stringLocalization
    -- The formatting for this string is the
    -- per xcmCOInternetIPAutoIPAddress

-- Installation Protocol for device selection (xcmCOInternetIPInstall)
xcmCOInternetIPInstallSelect       -- Printer selected for installation
   OBJECT IDENTIFIER ::= { xcmCOInternetIPInstall 1 }
   -- integerTruthValue
   -- (true=selected for installation, false=not selected)
xcmCOInternetIPAllSubnetsLocal     -- Local-only Installation Subnets
   OBJECT IDENTIFIER ::= { xcmCOInternetIPInstall 2 }
   -- integerTruthValue
   -- (true=Only local subnet allowed,
   --  false=Remote subnets allowed)

--
--  DHCP Configuration
--
xcmCOInternetDHCPClassID        -- DHCP Class ID (option to server)
    OBJECT IDENTIFIER ::= { xcmCOInternetDHCP 1 }
    -- stringLocalization (dotted decimal 'ProductID' OR label of Pid)
xcmCOInternetDHCPLeaseTime      -- DHCP Lease Time (option to server)
    OBJECT IDENTIFIER ::= { xcmCOInternetDHCP 2 }
    -- integerNumber (seconds, -1=infinite, 0=none, or 1..n)
xcmCOInternetDHCPRequestTimeout -- DHCP Request Timeout (for replies)
    OBJECT IDENTIFIER ::= { xcmCOInternetDHCP 3 }
    -- integerNumber (seconds, 0=none, or 1..n)

xcmCOInternetDHCPServer -- DHCP Server
    OBJECT IDENTIFIER ::= { xcmCOInternetDHCP 4 }
    -- stringLocalization
    -- The server that provided the IP Address for this
    -- device. The formatting for this string is the
    -- per xcmCOInternetIPAutoIPAddress


--
--  DHCP Options
--
--  Final arc of each of the following DHCP option get/set flags is the
--  option code as defined in IETF DHCP Options (RFC 2132, March 1997)
--
--  DHCP options named 'xxxGet' are legal for read by client
--  DHCP options named 'xxxSet' are legal for write/read by client
--
xcmCOInternetDHCPOptionGet      -- DHCP Option Get (read by client)
    OBJECT IDENTIFIER ::= { xcmCOInternetDHCP 10 }
    -- integerTruthValue
xcmCOInternetDHCPOptionSet      -- DHCP Option Set (write by client)
    OBJECT IDENTIFIER ::= { xcmCOInternetDHCP 11 }
    -- integerTruthValue
--
--  DHCP Options - BOOTP Vendor Extensions in RFC 1497 (RFC 2132, pg 5)
--
xcmCODHCPGetSubnetMask          -- single subnet mask
    OBJECT IDENTIFIER ::= { xcmCOInternetDHCPOptionGet 1 }
    -- integerTruthValue
xcmCODHCPGetSubnetTimeOffset    -- single subnet time offset
    OBJECT IDENTIFIER ::= { xcmCOInternetDHCPOptionGet 2 }
    -- integerTruthValue
xcmCODHCPGetRouter              -- list routers
    OBJECT IDENTIFIER ::= { xcmCOInternetDHCPOptionGet 3 }
    -- integerTruthValue
xcmCODHCPGetTPTimeServer        -- list RFC 868 time servers
    OBJECT IDENTIFIER ::= { xcmCOInternetDHCPOptionGet 4 }
    -- integerTruthValue
xcmCODHCPGetIEN116NameServer    -- list IEN 116 name servers
    OBJECT IDENTIFIER ::= { xcmCOInternetDHCPOptionGet 5 }
    -- integerTruthValue
xcmCODHCPGetDNSNameServer       -- list DNS name servers
    OBJECT IDENTIFIER ::= { xcmCOInternetDHCPOptionGet 6 }
    -- integerTruthValue
xcmCODHCPGetLogServer           -- list MIT-LCS UDP log servers
    OBJECT IDENTIFIER ::= { xcmCOInternetDHCPOptionGet 7 }
    -- integerTruthValue
xcmCODHCPGetCookieServer        -- list RFC 865 cookie servers
    OBJECT IDENTIFIER ::= { xcmCOInternetDHCPOptionGet 8 }
    -- integerTruthValue
xcmCODHCPGetLPRServer           -- list LPR servers
    OBJECT IDENTIFIER ::= { xcmCOInternetDHCPOptionGet 9 }
    -- integerTruthValue
xcmCODHCPGetImpressServer       -- list Imagen Impress servers
    OBJECT IDENTIFIER ::= { xcmCOInternetDHCPOptionGet 10 }
    -- integerTruthValue
xcmCODHCPGetResourceLocServer   -- list RFC 887 RLP servers
    OBJECT IDENTIFIER ::= { xcmCOInternetDHCPOptionGet 11 }
    -- integerTruthValue
xcmCODHCPGetHostName            -- single client host name
    OBJECT IDENTIFIER ::= { xcmCOInternetDHCPOptionGet 12 }


    -- integerTruthValue
xcmCODHCPGetBootFileSize        -- size in 512-octet blocks
    OBJECT IDENTIFIER ::= { xcmCOInternetDHCPOptionGet 13 }
    -- integerTruthValue
xcmCODHCPGetMeritDumpFile       -- single core dump file path
    OBJECT IDENTIFIER ::= { xcmCOInternetDHCPOptionGet 14 }
    -- integerTruthValue
xcmCODHCPGetDNSDomainName       -- single DNS domain name
    OBJECT IDENTIFIER ::= { xcmCOInternetDHCPOptionGet 15 }
    -- integerTruthValue
xcmCODHCPGetSwapServer          -- single client swap server
    OBJECT IDENTIFIER ::= { xcmCOInternetDHCPOptionGet 16 }
    -- integerTruthValue
xcmCODHCPGetRootPath            -- single client root path
    OBJECT IDENTIFIER ::= { xcmCOInternetDHCPOptionGet 17 }
    -- integerTruthValue
xcmCODHCPGetExtensionsPath      -- single client extensions path
    OBJECT IDENTIFIER ::= { xcmCOInternetDHCPOptionGet 18 }
    -- integerTruthValue
--
--  DHCP Options - IP Layer Parameters per Host (RFC 2132, pg 11)
--
xcmCODHCPGetIPForwarding        -- single IP forwarding enable
    OBJECT IDENTIFIER ::= { xcmCOInternetDHCPOptionGet 19 }
    -- integerTruthValue
xcmCODHCPGetNLSourceRouting     -- non-local source route enable
    OBJECT IDENTIFIER ::= { xcmCOInternetDHCPOptionGet 20 }
    -- integerTruthValue
xcmCODHCPGetNLPolicyFilter      -- list nl source route filters
    OBJECT IDENTIFIER ::= { xcmCOInternetDHCPOptionGet 21 }
    -- integerTruthValue
xcmCODHCPGetMaxIPDatagramSize   -- single max IP datagram size
    OBJECT IDENTIFIER ::= { xcmCOInternetDHCPOptionGet 22 }
    -- integerTruthValue
xcmCODHCPGetIPDefaultTTL        -- single IP default TTL
    OBJECT IDENTIFIER ::= { xcmCOInternetDHCPOptionGet 23 }
    -- integerTruthValue
xcmCODHCPGetPathMTUAgeTimeout   -- single Path MTU age timeout
    OBJECT IDENTIFIER ::= { xcmCOInternetDHCPOptionGet 24 }
    -- integerTruthValue
xcmCODHCPGetPathMTUPlateau      -- list Path MTU sizes
    OBJECT IDENTIFIER ::= { xcmCOInternetDHCPOptionGet 25 }
    -- integerTruthValue
--
--  DHCP Options - IP Layer Parameters per Interface (RFC 2132, pg 13
--
xcmCODHCPGetInterfaceMTUSize    -- single interface MTU size
    OBJECT IDENTIFIER ::= { xcmCOInternetDHCPOptionGet 26 }
    -- integerTruthValue
xcmCODHCPGetAllSubnetsLocal     -- single subnets local enable
    OBJECT IDENTIFIER ::= { xcmCOInternetDHCPOptionGet 27 }
    -- integerTruthValue
xcmCODHCPGetBroadcastAddress    -- single IP broadcast address
    OBJECT IDENTIFIER ::= { xcmCOInternetDHCPOptionGet 28 }


    -- integerTruthValue
xcmCODHCPGetMaskDiscovery       -- single mask discovery enable
    OBJECT IDENTIFIER ::= { xcmCOInternetDHCPOptionGet 29 }
    -- integerTruthValue
xcmCODHCPGetMaskSupplier        -- single mask response enable
    OBJECT IDENTIFIER ::= { xcmCOInternetDHCPOptionGet 30 }
    -- integerTruthValue
xcmCODHCPGetRouterDiscovery     -- single router discover enable
    OBJECT IDENTIFIER ::= { xcmCOInternetDHCPOptionGet 31 }
    -- integerTruthValue
xcmCODHCPGetRouterSolAddress    -- single router solicit address
    OBJECT IDENTIFIER ::= { xcmCOInternetDHCPOptionGet 32 }
    -- integerTruthValue
xcmCODHCPGetStaticRoute         -- list static routes
    OBJECT IDENTIFIER ::= { xcmCOInternetDHCPOptionGet 33 }
    -- integerTruthValue
--
--  DHCP Options - Link Layer Parameters per Interface (RFC 2132, pg 16)
--
xcmCODHCPGetARPTrailer          -- single ARP trailer enable
    OBJECT IDENTIFIER ::= { xcmCOInternetDHCPOptionGet 34 }
    -- integerTruthValue
xcmCODHCPGetARPCacheTimeout     -- single ARP cache timeout
    OBJECT IDENTIFIER ::= { xcmCOInternetDHCPOptionGet 35 }
    -- integerTruthValue
xcmCODHCPGetEthernetFrameIEEE   -- single IEEE 802.3 enable
    OBJECT IDENTIFIER ::= { xcmCOInternetDHCPOptionGet 36 }
    -- integerTruthValue
--
--  DHCP Options - TCP Layer Parameters per Interface (RFC 2132, pg 17)
--
xcmCODHCPGetTCPDefaultTTL       -- single TCP default TTL
    OBJECT IDENTIFIER ::= { xcmCOInternetDHCPOptionGet 37 }
    -- integerTruthValue
xcmCODHCPGetTCPKeepInterval     -- single TCP keepalive interval
    OBJECT IDENTIFIER ::= { xcmCOInternetDHCPOptionGet 38 }
    -- integerTruthValue
xcmCODHCPGetTCPKeepGarbage      -- single TCP KA garbage enable
    OBJECT IDENTIFIER ::= { xcmCOInternetDHCPOptionGet 39 }
    -- integerTruthValue
--
--  DHCP Options - Application and Service Parameters (RFC 2132, pg 18)
--
xcmCODHCPGetNISDomainName       -- single NIS domain name
    OBJECT IDENTIFIER ::= { xcmCOInternetDHCPOptionGet 40 }
    -- integerTruthValue
xcmCODHCPGetNISNameServer       -- list NIS name servers
    OBJECT IDENTIFIER ::= { xcmCOInternetDHCPOptionGet 41 }
    -- integerTruthValue
xcmCODHCPGetNTPTimeServer       -- list NTP time servers
    OBJECT IDENTIFIER ::= { xcmCOInternetDHCPOptionGet 42 }
    -- integerTruthValue
xcmCODHCPGetVendorSpecific      -- any vendor specific info
    OBJECT IDENTIFIER ::= { xcmCOInternetDHCPOptionGet 43 }


    -- integerTruthValue
xcmCODHCPGetNetbiosNameServer   -- list NetBIOS name servers
    OBJECT IDENTIFIER ::= { xcmCOInternetDHCPOptionGet 44 }
    -- integerTruthValue
xcmCODHCPGetNetbiosDistServer   -- list NetBIOS dg dist servers
    OBJECT IDENTIFIER ::= { xcmCOInternetDHCPOptionGet 45 }
    -- integerTruthValue
xcmCODHCPGetNetbiosNodeType     -- single NetBIOS node type
    OBJECT IDENTIFIER ::= { xcmCOInternetDHCPOptionGet 46 }
    -- integerTruthValue
xcmCODHCPGetNetbiosScope        -- single NetBIOS scope
    OBJECT IDENTIFIER ::= { xcmCOInternetDHCPOptionGet 47 }
    -- integerTruthValue
xcmCODHCPGetXWindowFontServer   -- list X Window font servers
    OBJECT IDENTIFIER ::= { xcmCOInternetDHCPOptionGet 48 }
    -- integerTruthValue
xcmCODHCPGetXWindowDisplayMgr   -- list X Window display mgrs
    OBJECT IDENTIFIER ::= { xcmCOInternetDHCPOptionGet 49 }
    -- integerTruthValue
xcmCODHCPGetNISPlusDomainName   -- single NIS+ domain name
    OBJECT IDENTIFIER ::= { xcmCOInternetDHCPOptionGet 64 }
    -- integerTruthValue
xcmCODHCPGetNISPlusNameServer   -- list NIS+ name servers
    OBJECT IDENTIFIER ::= { xcmCOInternetDHCPOptionGet 65 }
    -- integerTruthValue
xcmCODHCPGetMobileIPHomeAgent   -- list Mobile IP home agents
    OBJECT IDENTIFIER ::= { xcmCOInternetDHCPOptionGet 68 }
    -- integerTruthValue
xcmCODHCPGetSMTPMailServer      -- list SMTP mail servers
    OBJECT IDENTIFIER ::= { xcmCOInternetDHCPOptionGet 69 }
    -- integerTruthValue
xcmCODHCPGetPOP3MailServer      -- list POP3 mail servers
    OBJECT IDENTIFIER ::= { xcmCOInternetDHCPOptionGet 70 }
    -- integerTruthValue
xcmCODHCPGetNNTPNewsServer      -- list NNTP news servers
    OBJECT IDENTIFIER ::= { xcmCOInternetDHCPOptionGet 71 }
    -- integerTruthValue
xcmCODHCPGetWWWServer           -- list WWW servers
    OBJECT IDENTIFIER ::= { xcmCOInternetDHCPOptionGet 72 }
    -- integerTruthValue
xcmCODHCPGetFingerServer        -- list Finger servers
    OBJECT IDENTIFIER ::= { xcmCOInternetDHCPOptionGet 73 }
    -- integerTruthValue
xcmCODHCPGetIRCServer           -- list IRC chat servers
    OBJECT IDENTIFIER ::= { xcmCOInternetDHCPOptionGet 74 }
    -- integerTruthValue
xcmCODHCPGetStreetTalkServer    -- list StreetTalk name servers
    OBJECT IDENTIFIER ::= { xcmCOInternetDHCPOptionGet 75 }
    -- integerTruthValue
xcmCODHCPGetStreetTalkDAServer  -- list StreetTalk DA servers
    OBJECT IDENTIFIER ::= { xcmCOInternetDHCPOptionGet 76 }
    -- integerTruthValue
--
--  DHCP Options - DHCP Extensions (RFC 2132, pg 25)


--
xcmCODHCPSetIPAddressRequest    -- single client IP address
    OBJECT IDENTIFIER ::= { xcmCOInternetDHCPOptionSet 50 }
    -- integerTruthValue
xcmCODHCPSetIPAddressLeaseTime  -- single IP address lease time
    OBJECT IDENTIFIER ::= { xcmCOInternetDHCPOptionSet 51 }
    -- integerTruthValue
xcmCODHCPSetOptionOverload      -- single option overload type
    OBJECT IDENTIFIER ::= { xcmCOInternetDHCPOptionSet 52 }
    -- integerTruthValue
xcmCODHCPGetMessageType         -- single DHCP message type
    OBJECT IDENTIFIER ::= { xcmCOInternetDHCPOptionGet 53 }
    -- integerTruthValue
xcmCODHCPGetServerID            -- single DHCP server identifier
    OBJECT IDENTIFIER ::= { xcmCOInternetDHCPOptionGet 54 }
    -- integerTruthValue
xcmCODHCPGetParameterRequest    -- list DHCP parameter requests
    OBJECT IDENTIFIER ::= { xcmCOInternetDHCPOptionGet 55 }
    -- integerTruthValue
xcmCODHCPGetErrorMessage        -- single DHCP error message
    OBJECT IDENTIFIER ::= { xcmCOInternetDHCPOptionGet 56 }
    -- integerTruthValue
xcmCODHCPGetMaxMessageSize      -- single max DHCP message size
    OBJECT IDENTIFIER ::= { xcmCOInternetDHCPOptionGet 57 }
    -- integerTruthValue
xcmCODHCPGetRenewT1Interval     -- single renewing T1 interval
    OBJECT IDENTIFIER ::= { xcmCOInternetDHCPOptionGet 58 }
    -- integerTruthValue
xcmCODHCPGetRebindT2Interval    -- single rebind T2 interval
    OBJECT IDENTIFIER ::= { xcmCOInternetDHCPOptionGet 59 }
    -- integerTruthValue
xcmCODHCPSetClassID             -- single class identifier
    OBJECT IDENTIFIER ::= { xcmCOInternetDHCPOptionSet 60 }
    -- integerTruthValue
xcmCODHCPSetClientID            -- single client identifier
    OBJECT IDENTIFIER ::= { xcmCOInternetDHCPOptionSet 61 }
    -- integerTruthValue
xcmCODHCPGetTFTPServerName      -- single TFTP server name
    OBJECT IDENTIFIER ::= { xcmCOInternetDHCPOptionGet 66 }
    -- stringLocalization (the name used by the device)
xcmCODHCPGetBootFileName        -- single boot filename
    OBJECT IDENTIFIER ::= { xcmCOInternetDHCPOptionGet 67 }
    -- stringLocalization (the name used by the device)
--
--  DHCP Options - Novell NetWare Directory Services (RFC 2241, pg 18)
--
xcmCODHCPGetNDSNameServer       -- list NetWare NDS name servers
    OBJECT IDENTIFIER ::= { xcmCOInternetDHCPOptionGet 85 }
    -- integerTruthValue
xcmCODHCPGetNDSTreeName         -- single NetWare NDS tree name
    OBJECT IDENTIFIER ::= { xcmCOInternetDHCPOptionGet 86 }
    -- integerTruthValue
xcmCODHCPGetNDSContext          -- single NetWare NDS context
    OBJECT IDENTIFIER ::= { xcmCOInternetDHCPOptionGet 87 }


    -- integerTruthValue

xcmCOInternetUDPAddress         -- UDP Address
    OBJECT IDENTIFIER ::= { xcmCOInternetUDP 1 }
    -- stringLocalization (IPv4 - dotted decimal 'a.b.c.d:socket')
    -- (note - in IPv4 ONLY, a dot '.' MAY also be used before 'socket'
    -- and such use of dot was recommended in XCMI v4.0 and earlier)
    -- (see 'xcmCOInternetIPAddress' for references)

xcmCOInternetUDPPort            -- UDP Port
    OBJECT IDENTIFIER ::= { xcmCOInternetUDP 2 }
    -- stringLocalization (ASCII decimal format, 'socket')

xcmCOInternetTCPAddress         -- TCP Address
    OBJECT IDENTIFIER ::= { xcmCOInternetTCP 1 }
    -- stringLocalization (IPv4 - dotted decimal 'a.b.c.d:socket')
    -- (note - in IPv4 ONLY, a dot '.' MAY also be used before 'socket'
    -- and such use of dot was recommended in XCMI v4.0 and earlier)
    -- (see 'xcmCOInternetIPAddress' for references)

xcmCOInternetTCPPort            -- TCP Port
    OBJECT IDENTIFIER ::= { xcmCOInternetTCP 2 }
    -- stringLocalization (ASCII decimal format, 'socket')

xcmCOInternetTCPMaxSegmentSize -- TCP Default Max Segment Size
    OBJECT IDENTIFIER ::= { xcmCOInternetTCP 3 }
    -- integerNumber

xcmCOInternetApplications
    OBJECT IDENTIFIER ::= { xcmCOInternetSuite 1700 }
    -- integerTruthValue

xcmCOInternetRaw                -- Raw Print (printing)
    OBJECT IDENTIFIER ::= { xcmCOInternetSuite 1501 }
    -- integerTruthValue
xcmCOInternetIPP                -- IPP (printing)
    OBJECT IDENTIFIER ::= { xcmCOInternetSuite 1502 }
    -- integerTruthValue
xcmCOInternetLPR                -- LPR (printing)
    OBJECT IDENTIFIER ::= { xcmCOInternetSuite 1503 }
    -- integerTruthValue

xcmCOInternetFTP                -- FTP (filing)
    OBJECT IDENTIFIER ::= { xcmCOInternetSuite 1504 }
    -- integerTruthValue
xcmCOInternetFTPPassiveMode -- FTP passive mode
    OBJECT IDENTIFIER ::= { xcmCOInternetFTP 1 }
    -- integerTruthValue

xcmCOInternetSMTP               -- SMTP (email)
    OBJECT IDENTIFIER ::= { xcmCOInternetSuite 1505 }
    -- integerTruthValue
    -- (see RFC 821 / STD 10, 'Simple Mail Transfer Protocol', Aug 1982)


    -- (see RFC 1869 / STD 10, 'SMTP Service Extensions', November 1995)
xcmCOInternetTelnet             -- Telnet (virtual terminal)
    OBJECT IDENTIFIER ::= { xcmCOInternetSuite 1506 }
    -- integerTruthValue
xcmCOInternetDNS                -- DNS (directory)
    OBJECT IDENTIFIER ::= { xcmCOInternetSuite 1507 }
    -- integerTruthValue
xcmCOInternetTFTP               -- TFTP (filing)
    OBJECT IDENTIFIER ::= { xcmCOInternetSuite 1508 }
    -- integerTruthValue
xcmCOInternetHTTP               -- HTTP (World Wide Web - WWW)
    OBJECT IDENTIFIER ::= { xcmCOInternetSuite 1509 }
    -- integerTruthValue

xcmCOInternetSNMP               -- SNMP (network mgmt)
    OBJECT IDENTIFIER ::= { xcmCOInternetSuite 1510 }
    -- integerTruthValue
xcmCOInternetSNMPv1             -- SNMPv1 (network mgmt)
    OBJECT IDENTIFIER ::= { xcmCOInternetSuite 1511 }
    -- integerTruthValue
    -- (obsoleted by 'xcmCOInternetSNMPVersion')
xcmCOInternetSNMPv2             -- SNMPv2 (network mgmt)
    OBJECT IDENTIFIER ::= { xcmCOInternetSuite 1512 }
    -- integerTruthValue
    -- (obsoleted by 'xcmCOInternetSNMPVersion')
xcmCOInternetSNMPv3             -- SNMPv3 (network mgmt)
    OBJECT IDENTIFIER ::= { xcmCOInternetSuite 1513 }
    -- integerTruthValue
    -- (obsoleted by 'xcmCOInternetSNMPVersion')
xcmCOInternetSNMPVersion        -- SNMP Version (network mgmt)
    OBJECT IDENTIFIER ::= { xcmCOInternetSNMP 1 }
    -- integerEnum (from 'XcmGenSNMPVersion' in XCMI General TC)
    -- (obsoletes 'xcmCOInternetSNMP[v1|v2|v3]')

xcmCOInternetSNMPAdminAddress   -- SNMP Admin Address
    OBJECT IDENTIFIER ::= { xcmCOInternetSNMP 2 }
    -- integerTruthValue(8) & stringLocalization(13)
    -- The SNMP Administrator Accept Address
    -- i.e. the Host Access List for SNMP

xcmCOInternetPOP3               -- Internet POP3 (email access)
    OBJECT IDENTIFIER ::= { xcmCOInternetSuite 1514 }
    -- integerTruthValue
    -- (see RFC 1939 / STD 53, 'Post Office Protocol v3', May 1996)
    -- (see RFC 1957, 'Implementations of POP3', June 1996)
    -- (see RFC 2384, 'POP URL Scheme', August 1998)
    -- (see RFC 2449, 'POP3 Extension Mechanism, November 1998)

xcmCOInternetIMAP4              -- Internet IMAP4 (email access)
    OBJECT IDENTIFIER ::= { xcmCOInternetSuite 1515 }
    -- integerTruthValue
    -- (see RFC 2060, 'Internet Msg Access Protocol v4', December 1996)
    -- (see RFC 2192, 'IMAP URL Scheme', September 1997)
    -- (see RFC 2683, 'IMAP4 Implementations', September 1999)


xcmCOInternetFax                -- Internet Fax (facsimile over email)
    OBJECT IDENTIFIER ::= { xcmCOInternetSuite 1516 }
    -- integerTruthValue
    -- (see RFC 2305, 'Simple Fax Using Internet Mail', March 1998)
    -- (see RFC 2532, 'Extended Fax Using Internet Mail', March 1999)

xcmCOInternetNTP                -- NTP (RFC 4330)
    OBJECT IDENTIFIER ::= { xcmCOInternetSuite 1517}
     -- integerTruthValue

xcmCOInternetSFTP                -- SFTP (filing)
    OBJECT IDENTIFIER ::= { xcmCOInternetSuite 1518}
 -- integerTruthValue

xcmCOInternetWINS               -- Microsoft WINS (directory)
    OBJECT IDENTIFIER ::= { xcmCOInternetSuite 1519 }
    -- integerTruthValue

xcmCOInternetSunOncSuite        -- Sun ONC Suite (distributed computing)
    OBJECT IDENTIFIER ::= { xcmCOInternetSuite 1520 }
    -- integerTruthValue
xcmCOInternetSunOncNIS          -- Sun ONC NIS (directory)
    OBJECT IDENTIFIER ::= { xcmCOInternetSuite 1521 }
    -- integerTruthValue
xcmCOInternetSunOncPlusNIS      -- Sun ONC+ NIS+ (directory)
    OBJECT IDENTIFIER ::= { xcmCOInternetSuite 1522 }
    -- integerTruthValue
xcmCOInternetSunOncRPC          -- Sun ONC RPC (w/ NIS)
    OBJECT IDENTIFIER ::= { xcmCOInternetSuite 1523 }
    -- integerTruthValue
xcmCOInternetSunOncPlusRPC      -- Sun ONC+ RPC (w/ NIS+)
    OBJECT IDENTIFIER ::= { xcmCOInternetSuite 1524 }
    -- integerTruthValue
xcmCOInternetSunTiRPC           -- Sun TI RPC (transactions)
    OBJECT IDENTIFIER ::= { xcmCOInternetSuite 1525 }
    -- integerTruthValue

xcmCOInternetHTTPS               -- HTTPS (World Wide Web - WWW)
    OBJECT IDENTIFIER ::= { xcmCOInternetSuite 1526 }
    -- integerTruthValue

xcmCOInternetOsfDceSuite        -- OSF DCE Suite (distributed computing)
    OBJECT IDENTIFIER ::= { xcmCOInternetSuite 1530 }
    -- integerTruthValue
xcmCOInternetOsfDceCDS          -- OSF DCE CDS (directory)
    OBJECT IDENTIFIER ::= { xcmCOInternetSuite 1531 }
    -- integerTruthValue
xcmCOInternetOsfDceRPC          -- OSF DCE RPC (w/ CDS)
    OBJECT IDENTIFIER ::= { xcmCOInternetSuite 1532 }
    -- integerTruthValue
xcmCOInternetOsfDceKerberos     -- OSF DCE Kerberos (security tickets)
    OBJECT IDENTIFIER ::= { xcmCOInternetSuite 1533 }
    -- integerTruthValue


xcmCOInternetOsfDmeSuite        -- OSF DME Suite (distributed mgmt)
    OBJECT IDENTIFIER ::= { xcmCOInternetSuite 1540 }
    -- integerTruthValue

xcmCOInternetLDAP               -- LDAP (to X.500 directory, RFC 1777)
    OBJECT IDENTIFIER ::= { xcmCOInternetSuite 1551 }
    -- integerTruthValue
xcmCOInternetCLDAP              -- CLDAP (to X.500 directory, RFC 1798)
    OBJECT IDENTIFIER ::= { xcmCOInternetSuite 1552 }
    -- integerTruthValue

xcmCOInternetSalutation         -- Salutation (FX/IBM consortium)
    OBJECT IDENTIFIER ::= { xcmCOInternetSuite 1561 }
    -- integerTruthValue

xcmCOInternetUpnpSuite          -- MS UPnP Suite (plug-and-play)
    OBJECT IDENTIFIER ::= { xcmCOInternetSuite 1570 }
    -- integerTruthValue
xcmCOInternetUpnpSSDP           -- MS UPnP SSDP (discovery)
    OBJECT IDENTIFIER ::= { xcmCOInternetSuite 1571 }
    -- integerTruthValue
xcmCOInternetUpnpGENA           -- MS UPnP GENA (notification)
    OBJECT IDENTIFIER ::= { xcmCOInternetSuite 1572 }
    -- integerTruthValue

xcmCOInternetSLP                -- SLP (discovery)
    OBJECT IDENTIFIER ::= { xcmCOInternetSuite 1591 }
    -- integerTruthValue
xcmCOInternetSLPv1              -- SLPv1 (discovery)
    OBJECT IDENTIFIER ::= { xcmCOInternetSuite 1592 }
    -- integerTruthValue
    -- (obsoleted by 'xcmCOInternetSLPVersion')
xcmCOInternetSLPv2              -- SLPv2 (discovery)
    OBJECT IDENTIFIER ::= { xcmCOInternetSuite 1593 }
    -- integerTruthValue
    -- (obsoleted by 'xcmCOInternetSLPVersion')

--
--          Web Services on Devices Protocol Suite
--

xcmCOInternetWSDSuite           -- Web Services on Devices
    OBJECT IDENTIFIER ::= { xcmCOInternetSuite 1595 }
        -- integerTruthValue

xcmCOInternetWSDiscovery        -- WS-Discovery Protocol
    OBJECT IDENTIFIER ::= { xcmCOInternetWSDSuite 1 }
    -- integerTruthValue

xcmCOInternetWSXResourcePort    -- Xerox WS-XResource Port Number
    OBJECT IDENTIFIER ::= { xcmCOInternetWSDSuite 2 }
    -- integerNumber
    -- Xerox Resource Service Listening Port Number


xcmCOInternetWSDiscoveryMulticast  -- WS-Discovery Multicast
    OBJECT IDENTIFIER ::= { xcmCOInternetWSDiscovery 1 }
    -- integerTruthValue

xcmCOInternetWSDiscoveryPort    -- WS-Discovery Port Number
    OBJECT IDENTIFIER ::= { xcmCOInternetWSDiscovery 2 }
        -- integerNumber
    -- Web Services Discovery Listening Port Number

xcmCOInternetWSPrintPort       -- Microsoft WS-Print Port Number
    OBJECT IDENTIFIER ::= { xcmCOInternetWSDSuite 3 }
    -- integerNumber
    -- Print Service Listening Port Number

xcmCOInternetWSScanPort        -- Microsoft WS-Scan Port Number
    OBJECT IDENTIFIER ::= { xcmCOInternetWSDSuite 4 }
    -- integerNumber
    -- Scan Service Listening Port Number

xcmCOInternetWSTransferPort       -- WS-Transfer Port
    OBJECT IDENTIFIER ::= { xcmCOInternetWSDSuite 5 }
    -- integerNumber
    -- Web Services Transfer Listening Port Number

xcmCOInternetDeallocateAllDynamicResources
-- Configuration mechanism.  Used to release all resources
-- that have been dynamically allocated to the system.
-- Helps prevent stale records.
-- If enabled, on shutdown:
--       if DHCP is enabled, send DHCPRELEASE to DHCP server
--       if DDNS is enabled, delete resource records being
--          maintained by the device
    OBJECT IDENTIFIER ::= { xcmCOInternetSuite  1600}
    -- integerTruthValue
    -- (true=enable, false=disable)

xcmCOInternetDHCPv6               -- DHCPv6
    OBJECT IDENTIFIER ::= { xcmCOInternetSuite 1800 }
-- integerTruthValue
-- DHCPv6
    -- RFC 3315, Dynamic Host Configuration Protocol for IPv6 (DHCPv6)

xcmCOInternetDHCPv6ConfigState    -- DHCPv6 configuration
    OBJECT IDENTIFIER ::= { xcmCOInternetDHCPv6 1 }
-- integerEnum (1=Use DHCPv6 as directed by a router,
-- 2=Always enable DHCP for address assignment,
-- 3=Always enable DHCP for other configuration data,
-- 4=Never use DHCPv6)

xcmCOInternetDNSv6                -- DNS (directory)
    OBJECT IDENTIFIER ::= { xcmCOInternetSuite 1801 }
-- integerTruthValue
-- DNS over IPv6


xcmCOInternetDNSv6DomainName      -- DNS Domain Name (directory)
    OBJECT IDENTIFIER ::= { xcmCOInternetDNSv6 1 }
-- stringLocalization
-- The domain name for this system for DNS over IPv6.

xcmCOInternetDNSv6ServerAddress   -- DNS Server Address (directory)
OBJECT IDENTIFIER ::= { xcmCOInternetDNSv6 2 }
-- stringLocalization (IPv6 - hex w/ colons '[x1:...:x8/yyy]')
-- (see 'xcmCOInternetIPv6Address' for references)

xcmCOInternetDNSv6DynamicUpdate   -- DNS Dynamic Update (directory)
OBJECT IDENTIFIER ::= { xcmCOInternetDNSv6 3 }
-- integerTruthValue
-- (true=enableDynamicUpdate, false=disableDynamicUpdate)
-- (see RFC 2136 'Dynamic Updates in DNS', April 1997)

xcmCOInternetDNSv6ResolutionPolicy    -- Resolution Policy
    OBJECT IDENTIFIER ::= { xcmCOInternetDNSv6 4 }
-- Used to choose address when hostname DNS query
-- returns both IPv4 and IPv6 addresses
-- integerEnum (1=prefer IPv4 address,
-- 2=prefer IPv6 address)

xcmCOInternetIPv6DeallocateAllDynamicResources
-- Configuration mechanism.  Used to release all resources
    -- that have been dynamically allocated to the system.
-- Helps prevent stale records.
-- If enabled, on shutdown:
--       if DHCPv6 is enabled, send DHCPRELEASE to DHCPv6 server
--       if DDNSv6 is enabled, delete resource records being
--          maintained by the device
OBJECT IDENTIFIER ::= { xcmCOInternetSuite 1802}
-- integerTruthValue
-- (true=enable, false=disable)

xcmCOInternetSLPVersion         -- SLP Version (discovery)
    OBJECT IDENTIFIER ::= { xcmCOInternetSLP 1 }
    -- integerEnum (1=none, 2=other,
    -- 3=SLPv1,                                     - RFC 2165
    -- 4=SLPv2)                                     - RFC 2608
    -- (obsoletes 'xcmCOInternetSLP[v1|v2]')

xcmCOInternetRawHostName        -- Raw Host Name
    OBJECT IDENTIFIER ::= { xcmCOInternetRaw 1 }
    -- stringLocalization

xcmCOInternetRawHostAddress     -- Raw Host Address
    OBJECT IDENTIFIER ::= { xcmCOInternetRaw 2 }
    -- stringLocalization (IPv4 - dotted decimal 'a.b.c.d')
    -- (see 'xcmCOInternetIPAddress' for references)


xcmCOInternetRawListenSocket    -- Raw Listen Socket
    OBJECT IDENTIFIER ::= { xcmCOInternetRaw 3 }
    -- integerNumber (9100=default or 1..n)
    -- (see Internet Assigned Numbers, RFC 1700, and IANA registry)
xcmCOInternetRawMaxClients      -- Raw Max Clients (concurrently)
    OBJECT IDENTIFIER ::= { xcmCOInternetRaw 4 }
    -- integerNumber (0..n)
xcmCOInternetRawAcceptAddress   -- Raw Accept Address (list)
    OBJECT IDENTIFIER ::= { xcmCOInternetRaw 11 }
    -- integerTruthValue (w/ chain of 'xcmCOInternetIPAddress')
xcmCOInternetRawAcceptSubnet    -- Raw Accept Subnet (list)
    OBJECT IDENTIFIER ::= { xcmCOInternetRaw 12 }
    -- integerTruthValue (w/ chain of 'xcmCOInternetIPSubnetMask')
xcmCOInternetRawRejectAddress   -- Raw Reject Address (list)
    OBJECT IDENTIFIER ::= { xcmCOInternetRaw 21 }
    -- integerTruthValue (w/ chain of 'xcmCOInternetIPAddress')
xcmCOInternetRawRejectSubnet    -- Raw Reject Subnet (list)
    OBJECT IDENTIFIER ::= { xcmCOInternetRaw 22 }
    -- integerTruthValue (w/ chain of 'xcmCOInternetIPSubnetMask')
xcmCOInternetRawSpool           -- Raw Spool (printing)
    OBJECT IDENTIFIER ::= { xcmCOInternetRaw 31 }
    -- integerEnum (1=none, 2=other, 3=disk, 4=ram)
xcmCOInternetRawMaxSpool        -- Raw Max Spool (printing)
    OBJECT IDENTIFIER ::= { xcmCOInternetRaw 32 }
    -- integerNumber (spool area size in bytes, 0..n)
xcmCOInternetRawJobTimeout      -- Raw Job Timeout (printing)
    OBJECT IDENTIFIER ::= { xcmCOInternetRaw 40 }
    -- integerNumber (seconds, 0=infinite or 1..n)
xcmCOInternetRawAutoSwitch      -- Raw Auto Switch (printing)
    OBJECT IDENTIFIER ::= { xcmCOInternetRaw 41 }
    -- integerEnum (see 'xcmCODirectPrintProtocol' below)
xcmCOInternetRawBinaryPS        -- Raw Binary PS (printing)
    OBJECT IDENTIFIER ::= { xcmCOInternetRaw 42 }
    -- integerTruthValue (true=enableBinaryPS, false=disableBinaryPS)
    -- (interpret all PostScript jobs as binary - ignore control chars)
    -- (PostScript per job submission protocol or 'xxxDefaultPDL' below)
xcmCOInternetRawDefaultPDL      -- Raw Default PDL (printing)
    OBJECT IDENTIFIER ::= { xcmCOInternetRaw 43 }
    -- integerEnum ('XcmPrtInterpreterLangFamily' in XCMI Prt Ext TC)
    -- (fixed PDL if 'xxxAutoSwitch' is 'none' or 'other')
    -- (default PDL if 'xxxAutoSwitch' is 'autoSwitch')
    -- (ignored if 'xxxAutoSwitch' is 'ps...' or 'hp...')
    -- See: 'prtInterpreterLangFamily' in IETF Printer MIB (RFC 1759)
    -- See: 'prtChannelDefaultPageDescLangIndex' (default PDL via value
    --      of 'prtInterpreterIndex') in IETF Printer MIB (RFC 1759)
xcmCOInternetRawBidirectional      --
    OBJECT IDENTIFIER ::= { xcmCOInternetRaw 44 }
    -- integerTruthValue (true=enabled, false=disabled)

xcmCOInternetIPPHostName        -- IPP Host Name
    OBJECT IDENTIFIER ::= { xcmCOInternetIPP 1 }
    -- stringLocalization


xcmCOInternetIPPHostAddress     -- IPP Host Address
    OBJECT IDENTIFIER ::= { xcmCOInternetIPP 2 }
    -- stringLocalization (IPv4 - dotted decimal 'a.b.c.d')
    -- (see 'xcmCOInternetIPAddress' for references)

xcmCOInternetIPPListenSocket    -- IPP Listen Socket
    OBJECT IDENTIFIER ::= { xcmCOInternetIPP 3 }
    -- integerNumber (631=default or 1..n)
    -- (see Internet Assigned Numbers, RFC 1700, and IANA registry)
xcmCOInternetIPPMaxClients      -- IPP Max Clients (concurrently)
    OBJECT IDENTIFIER ::= { xcmCOInternetIPP 4 }
    -- integerNumber (0..n)
xcmCOInternetIPPVersionString   -- IPP Version String
    OBJECT IDENTIFIER ::= { xcmCOInternetIPP 9 }
    -- stringLocalization (eg, '1.1' for IPP/1.1, RFC 2910/2911)
xcmCOInternetIPPAcceptAddress   -- IPP Accept Address (list)
    OBJECT IDENTIFIER ::= { xcmCOInternetIPP 11 }
    -- integerTruthValue (w/ chain of 'xcmCOInternetIPAddress')
xcmCOInternetIPPAcceptSubnet    -- IPP Accept Subnet (list)
    OBJECT IDENTIFIER ::= { xcmCOInternetIPP 12 }
    -- integerTruthValue (w/ chain of 'xcmCOInternetIPSubnetMask')
xcmCOInternetIPPRejectAddress   -- IPP Reject Address (list)
    OBJECT IDENTIFIER ::= { xcmCOInternetIPP 21 }
    -- integerTruthValue (w/ chain of 'xcmCOInternetIPAddress')
xcmCOInternetIPPRejectSubnet    -- IPP Reject Subnet (list)
    OBJECT IDENTIFIER ::= { xcmCOInternetIPP 22 }
    -- integerTruthValue (w/ chain of 'xcmCOInternetIPSubnetMask')
xcmCOInternetIPPSpool           -- IPP Spool (printing)
    OBJECT IDENTIFIER ::= { xcmCOInternetIPP 31 }
    -- integerEnum (1=none, 2=other, 3=disk, 4=ram)
xcmCOInternetIPPMaxSpool        -- IPP Max Spool (printing)
    OBJECT IDENTIFIER ::= { xcmCOInternetIPP 32 }
    -- integerNumber (spool area size in bytes, 0..n)
xcmCOInternetIPPJobTimeout      -- IPP Job Timeout (printing)
    OBJECT IDENTIFIER ::= { xcmCOInternetIPP 40 }
    -- integerNumber (seconds, 0=infinite or 1..n)
xcmCOInternetIPPAutoSwitch      -- IPP Auto Switch (printing)
    OBJECT IDENTIFIER ::= { xcmCOInternetIPP 41 }
    -- integerEnum (see 'xcmCODirectPrintProtocol' below)
xcmCOInternetIPPBinaryPS        -- IPP Binary PS (printing)
    OBJECT IDENTIFIER ::= { xcmCOInternetIPP 42 }
    -- integerTruthValue (true=enableBinaryPS, false=disableBinaryPS)
    -- (interpret all PostScript jobs as binary - ignore control chars)
    -- (PostScript per job submission protocol or 'xxxDefaultPDL' below)
xcmCOInternetIPPDefaultPDL      -- IPP Default PDL (printing)
    OBJECT IDENTIFIER ::= { xcmCOInternetIPP 43 }
    -- integerEnum ('XcmPrtInterpreterLangFamily' in XCMI Prt Ext TC)
    -- (fixed PDL if 'xxxAutoSwitch' is 'none' or 'other')
    -- (default PDL if 'xxxAutoSwitch' is 'autoSwitch')
    -- (ignored if 'xxxAutoSwitch' is 'ps...' or 'hp...')
    -- See: 'prtInterpreterLangFamily' in IETF Printer MIB (RFC 1759)
    -- See: 'prtChannelDefaultPageDescLangIndex' (default PDL via value
    --      of 'prtInterpreterIndex') in IETF Printer MIB (RFC 1759)


xcmCOInternetIPPAuthScheme   -- IPP Authentication Scheme
    OBJECT IDENTIFIER ::= { xcmCOInternetIPP 50 }
    -- integerEnum (Basic(2), Digest(3))
    -- The IPP Authentication Scheme selected by the user

xcmCOInternetLPRHostName        -- LPR Host Name
    OBJECT IDENTIFIER ::= { xcmCOInternetLPR 1 }
    -- stringLocalization

xcmCOInternetLPRHostAddress     -- LPR Host Address
    OBJECT IDENTIFIER ::= { xcmCOInternetLPR 2 }
    -- stringLocalization (IPv4 - dotted decimal 'a.b.c.d')
    -- (see 'xcmCOInternetIPAddress' for references)

xcmCOInternetLPRListenSocket    -- LPR Listen Socket (RFC 1179)
    OBJECT IDENTIFIER ::= { xcmCOInternetLPR 3 }
    -- integerNumber (515=default or 1..n)
    -- (see Internet Assigned Numbers, RFC 1700, and IANA registry)
xcmCOInternetLPRMaxClients      -- LPR Max Clients (concurrently)
    OBJECT IDENTIFIER ::= { xcmCOInternetLPR 4 }
    -- integerNumber (0..n)
xcmCOInternetLPRAcceptAddress   -- LPR Accept Address (list)
    OBJECT IDENTIFIER ::= { xcmCOInternetLPR 11 }
    -- integerTruthValue (w/ chain of 'xcmCOInternetIPAddress')
xcmCOInternetLPRAcceptSubnet    -- LPR Accept Subnet (list)
    OBJECT IDENTIFIER ::= { xcmCOInternetLPR 12 }
    -- integerTruthValue (w/ chain of 'xcmCOInternetIPSubnetMask')
xcmCOInternetLPRRejectAddress   -- LPR Reject Address (list)
    OBJECT IDENTIFIER ::= { xcmCOInternetLPR 21 }
    -- integerTruthValue (w/ chain of 'xcmCOInternetIPAddress')
xcmCOInternetLPRRejectSubnet    -- LPR Reject Subnet (list)
    OBJECT IDENTIFIER ::= { xcmCOInternetLPR 22 }
    -- integerTruthValue (w/ chain of 'xcmCOInternetIPSubnetMask')
xcmCOInternetLPRSpool           -- LPR Spool (printing)
    OBJECT IDENTIFIER ::= { xcmCOInternetLPR 31 }
    -- integerEnum (1=none, 2=other, 3=disk, 4=ram)
xcmCOInternetLPRMaxSpool        -- LPR Max Spool (printing)
    OBJECT IDENTIFIER ::= { xcmCOInternetLPR 32 }
    -- integerNumber (spool area size in bytes, 0..n)
xcmCOInternetLPRJobTimeout      -- LPR Job Timeout (printing)
    OBJECT IDENTIFIER ::= { xcmCOInternetLPR 40 }
    -- integerNumber (seconds, 0=infinite or 1..n)
xcmCOInternetLPRAutoSwitch      -- LPR Auto Switch (printing)
    OBJECT IDENTIFIER ::= { xcmCOInternetLPR 41 }
    -- integerEnum (see 'xcmCODirectPrintProtocol' below)
xcmCOInternetLPRBinaryPS        -- LPR Binary PS (printing)
    OBJECT IDENTIFIER ::= { xcmCOInternetLPR 42 }
    -- integerTruthValue (true=enableBinaryPS, false=disableBinaryPS)
    -- (interpret all PostScript jobs as binary - ignore control chars)
    -- (PostScript per job submission protocol or 'xxxDefaultPDL' below)
xcmCOInternetLPRDefaultPDL      -- LPR Default PDL (printing)
    OBJECT IDENTIFIER ::= { xcmCOInternetLPR 43 }
    -- integerEnum ('XcmPrtInterpreterLangFamily' in XCMI Prt Ext TC)


    -- (fixed PDL if 'xxxAutoSwitch' is 'none' or 'other')
    -- (default PDL if 'xxxAutoSwitch' is 'autoSwitch')
    -- (ignored if 'xxxAutoSwitch' is 'ps...' or 'hp...')
    -- See: 'prtInterpreterLangFamily' in IETF Printer MIB (RFC 1759)
    -- See: 'prtChannelDefaultPageDescLangIndex' (default PDL via value
    --      of 'prtInterpreterIndex') in IETF Printer MIB (RFC 1759)

xcmCOInternetSMTPHostName       -- SMTP Host Name
    OBJECT IDENTIFIER ::= { xcmCOInternetSMTP 1 }
    -- stringLocalization

xcmCOInternetSMTPHostAddress    -- SMTP Host Address
    OBJECT IDENTIFIER ::= { xcmCOInternetSMTP 2 }
    -- stringLocalization (IPv4 - dotted decimal 'a.b.c.d')
    -- (see 'xcmCOInternetIPAddress' for references)

xcmCOInternetSMTPListenSocket   -- SMTP Listen Socket
    OBJECT IDENTIFIER ::= { xcmCOInternetSMTP 3 }
    -- integerNumber (25=default or 1..n)
    -- (see Internet Assigned Numbers, RFC 1700, and IANA registry)
xcmCOInternetSMTPMaxClients     -- SMTP Max Clients (concurrently)
    OBJECT IDENTIFIER ::= { xcmCOInternetSMTP 4 }
    -- integerNumber (0..n)
xcmCOInternetSMTPAcceptAddress  -- SMTP Accept Address (list)
    OBJECT IDENTIFIER ::= { xcmCOInternetSMTP 11 }
    -- integerTruthValue (w/ chain of 'xcmCOInternetIPAddress')
xcmCOInternetSMTPAcceptSubnet   -- SMTP Accept Subnet (list)
    OBJECT IDENTIFIER ::= { xcmCOInternetSMTP 12 }
    -- integerTruthValue (w/ chain of 'xcmCOInternetIPSubnetMask')
xcmCOInternetSMTPRejectAddress  -- SMTP Reject Address (list)
    OBJECT IDENTIFIER ::= { xcmCOInternetSMTP 21 }
    -- integerTruthValue (w/ chain of 'xcmCOInternetIPAddress')
xcmCOInternetSMTPRejectSubnet   -- SMTP Reject Subnet (list)
    OBJECT IDENTIFIER ::= { xcmCOInternetSMTP 22 }
    -- integerTruthValue (w/ chain of 'xcmCOInternetIPSubnetMask')
xcmCOInternetSMTPSpool          -- SMTP Spool (printing)
    OBJECT IDENTIFIER ::= { xcmCOInternetSMTP 31 }
    -- integerEnum (1=none, 2=other, 3=disk, 4=ram)
xcmCOInternetSMTPMaxSpool       -- SMTP Max Spool (printing)
    OBJECT IDENTIFIER ::= { xcmCOInternetSMTP 32 }
    -- integerNumber (spool area size in bytes, 0..n)
xcmCOInternetSMTPJobTimeout     -- SMTP Job Timeout (printing)
    OBJECT IDENTIFIER ::= { xcmCOInternetSMTP 40 }
    -- integerNumber (seconds, 0=infinite or 1..n)
xcmCOInternetSMTPAutoSwitch     -- SMTP Auto Switch (printing)
    OBJECT IDENTIFIER ::= { xcmCOInternetSMTP 41 }
    -- integerEnum (see 'xcmCODirectPrintProtocol' below)
xcmCOInternetSMTPBinaryPS       -- SMTP Binary PS (printing)
    OBJECT IDENTIFIER ::= { xcmCOInternetSMTP 42 }
    -- integerTruthValue (true=enableBinaryPS, false=disableBinaryPS)
    -- (interpret all PostScript jobs as binary - ignore control chars)
    -- (PostScript per job submission protocol or 'xxxDefaultPDL' below)
xcmCOInternetSMTPDefaultPDL     -- SMTP Default PDL (printing)
    OBJECT IDENTIFIER ::= { xcmCOInternetSMTP 43 }


    -- integerEnum ('XcmPrtInterpreterLangFamily' in XCMI Prt Ext TC)
    -- (fixed PDL if 'xxxAutoSwitch' is 'none' or 'other')
    -- (default PDL if 'xxxAutoSwitch' is 'autoSwitch')
    -- (ignored if 'xxxAutoSwitch' is 'ps...' or 'hp...')
    -- See: 'prtInterpreterLangFamily' in IETF Printer MIB (RFC 1759)
    -- See: 'prtChannelDefaultPageDescLangIndex' (default PDL via value
    --      of 'prtInterpreterIndex') in IETF Printer MIB (RFC 1759)
xcmCOInternetSMTPSubject        -- SMTP Subject (default)
    OBJECT IDENTIFIER ::= { xcmCOInternetSMTP 44 }
    -- stringLocalization
    -- (default subject field for outgoing SMTP message)
xcmCOInternetSMTPSignatureLine  -- SMTP Signature Line (default)
    OBJECT IDENTIFIER ::= { xcmCOInternetSMTP 45 }
    -- stringLocalization
    -- (default signature line for outgoing SMTP message)
xcmCOInternetSMTPUserName       -- SMTP User Name (for login to MTA)
    OBJECT IDENTIFIER ::= { xcmCOInternetSMTP 47 }
    -- stringLocalization
    -- (default user name for login to remote MTA)
xcmCOInternetSMTPPassword       -- SMTP Password (for login to MTA)
    OBJECT IDENTIFIER ::= { xcmCOInternetSMTP 48 }
    -- stringLocalization (SHALL be encrypted)
    -- (default password for login to remote MTA)
xcmCOInternetSMTPMaxInputText   -- SMTP Max Text Body Size (incoming)
    OBJECT IDENTIFIER ::= { xcmCOInternetSMTP 50 }
    -- integerNumber (bytes, 0=none, or 1..n)
    -- (max text body size for incoming SMTP message)
    -- (value of zero indicates incoming text body is NOT allowed)
xcmCOInternetSMTPMaxInputAttach -- SMTP Max Attachment Size (incoming)
    OBJECT IDENTIFIER ::= { xcmCOInternetSMTP 51 }
    -- integerNumber (bytes, 0=none, or 1..n)
    -- (max attachment size for incoming SMTP message)
    -- (value of zero indicates incoming attachment is NOT allowed)
xcmCOInternetSMTPMaxOutputText  -- SMTP Max Text Body Size (outgoing)
    OBJECT IDENTIFIER ::= { xcmCOInternetSMTP 52 }
    -- integerNumber (bytes, 0=none, or 1..n)
    -- (max text body size for outgoing SMTP message)
    -- (value of zero indicates outgoing text body is NOT allowed)
xcmCOInternetSMTPMaxOutputAttach -- SMTP Max Attachment Size (outgoing)
    OBJECT IDENTIFIER ::= { xcmCOInternetSMTP 53 }
    -- integerNumber (bytes, 0=none, or 1..n)
    -- (max attachment size for outgoing SMTP message)
    -- (value of zero indicates outgoing attachment is NOT allowed)
xcmCOInternetSMTPConfirmRequest -- SMTP Confirm Outgoing Email
    OBJECT IDENTIFIER ::= { xcmCOInternetSMTP 54 }
    -- integerTruthValue (true=enableDSN, false=disableDSN)
xcmCOInternetSMTPConfirmReply   -- SMTP Confirm Incoming Email
    OBJECT IDENTIFIER ::= { xcmCOInternetSMTP 55 }
    -- integerTruthValue (true=enableDSN, false=disableDSN)
xcmCOInternetSMTPConfirmTimeout -- SMTP Confirm Outgoing Timeout
    OBJECT IDENTIFIER ::= { xcmCOInternetSMTP 56 }
    -- integerNumber (seconds, 0=none, or 1..n)
xcmCOInternetSMTPFeatureReply   -- SMTP Feature Report in Confirm Reply
    OBJECT IDENTIFIER ::= { xcmCOInternetSMTP 57 }


    -- integerTruthValue (true=enableReport, false=disableReport)
xcmCOInternetSMTPMailAddress    -- SMTP Mail Address
    OBJECT IDENTIFIER ::= { xcmCOInternetSMTP 58 }
    -- stringLocalization (RFC 822 format - 'user@hostname')
    -- (see RFC 822, 'Format of Internet Mail Messages', August, 1982)
xcmCOInternetSMTPMaxInFragments -- SMTP Max Fragments (incoming)
    OBJECT IDENTIFIER ::= { xcmCOInternetSMTP 59 }
    -- integerNumber (0=none, or 2..n)
    -- (max fragments for incoming SMTP message)
    -- (zero indicates incoming fragments are NOT allowed)
xcmCOInternetSMTPMaxOutFragments -- SMTP Max Fragments (outgoing)
    OBJECT IDENTIFIER ::= { xcmCOInternetSMTP 60 }
    -- integerNumber (0=none, or 2..n)
    -- (max fragments for outgoing SMTP message)
    -- (zero indicates outgoing fragments are NOT allowed)
xcmCOInternetSMTPMaxInAttachments -- SMTP Max Attachments (incoming)
    OBJECT IDENTIFIER ::= { xcmCOInternetSMTP 61 }
    -- integerNumber (0=none, or 1..n)
    -- (max attachments for incoming SMTP message)
    -- (zero indicates incoming attachments are NOT allowed)
xcmCOInternetSMTPMaxOutAttachments -- SMTP Max Attachments (outgoing)
    OBJECT IDENTIFIER ::= { xcmCOInternetSMTP 62 }
    -- integerNumber (0=none, or 1..n)
    -- (max attachments for outgoing SMTP message)
    -- (zero indicates outgoing attachments are NOT allowed)
xcmCOInternetSMTPMaxInputSize   -- SMTP Max Message Size (incoming)
    OBJECT IDENTIFIER ::= { xcmCOInternetSMTP 63 }
    -- integerNumber (bytes, 0=none, or 1..n)
    -- (max size in bytes for incoming SMTP message)
    -- (zero indicates incoming messages are NOT allowed)
xcmCOInternetSMTPMaxOutputSize  -- SMTP Max Message Size (outgoing)
    OBJECT IDENTIFIER ::= { xcmCOInternetSMTP 64 }
    -- integerNumber (bytes, 0=none, or 1..n)
    -- (max size in bytes for outgoing SMTP message)
    -- (zero indicates outgoing messages are NOT allowed)
xcmCOInternetSMTPReversePath  -- SMTP Reverse Path
    OBJECT IDENTIFIER ::= { xcmCOInternetSMTP 65 }
    -- stringLocalization (RFC 822 format - 'user@hostname')
    -- The reverse source routing list for SMTP mail.
xcmCOInternetSMTPAutoServer -- Automatic SMTP Server detection
   OBJECT IDENTIFIER ::= { xcmCOInternetSMTP 70 }
   -- integerTruthValue
   -- (true=enable automatic SMTP Server Detection,
   --  false=disable auto detection)

xcmCOInternetDNSDomainName      -- DNS Domain Name (directory)
    OBJECT IDENTIFIER ::= { xcmCOInternetDNS 1 }
    -- stringLocalization
xcmCOInternetDNSLanguage        -- DNS Language (directory)
    OBJECT IDENTIFIER ::= { xcmCOInternetDNS 3 }
    -- stringLocalization (language tag, per RFC 2277)
    -- (default is unknown language, per RFC 2277)
xcmCOInternetDNSCharset         -- DNS Charset (directory)


    OBJECT IDENTIFIER ::= { xcmCOInternetDNS 4 }
    -- integerEnum (see 'CodedCharSet' in IETF Printer MIB)
    -- (default '106' UTF-8, per RFC 2277 and RFC 2279)
xcmCOInternetDNSServerName      -- DNS Server Name (directory)
    OBJECT IDENTIFIER ::= { xcmCOInternetDNS 5 }
    -- stringLocalization

xcmCOInternetDNSServerAddress   -- DNS Server Address (directory)
    OBJECT IDENTIFIER ::= { xcmCOInternetDNS 6 }
    -- stringLocalization (IPv4 - dotted decimal 'a.b.c.d')
    -- (see 'xcmCOInternetIPAddress' for references)

xcmCOInternetDNSServerResolvedAddress   -- DNS Server Address (directory
    OBJECT IDENTIFIER ::= { xcmCOInternetDNS 7 }
    -- stringLocalization
    -- address used by resolver (address may have been manually entered
    -- or returned by DHCP server)
    -- can be either IPv4 or IPv6 address
    -- (IPv4 - dotted decimal 'a.b.c.d')
    -- (see 'xcmCOInternetIPAddress' for references)
    -- (IPv6 - hex w/ colons '[x1:...:x8/yyy]')
    -- (see 'xcmCOInternetIPv6Address' for references)

xcmCOInternetDNSServerTimeout   -- DNS Server Timeout
    OBJECT IDENTIFIER ::= { xcmCOInternetDNS 8 }
    -- integerNumber
    -- value in seconds

xcmCOInternetDNSAppendDomainName   -- DNS Append Domain Name
    OBJECT IDENTIFIER ::= { xcmCOInternetDNS 9 }
    -- integerTruthValue
    -- (true=append domain name to hostname to resolve
    --  unqualified hostnames)

xcmCOInternetDNSAppendParentDomains  -- DNS Append Parent Domains
    OBJECT IDENTIFIER ::= { xcmCOInternetDNS 10 }
    -- integerTruthValue
    -- (true=append parent domains to hostname to resolve
    --  unqualified hostnames)

xcmCOInternetDNSDomainNameList   -- DNS Domain Name List
    OBJECT IDENTIFIER ::= { xcmCOInternetDNS 11 }
    -- stringLocalization
    -- Search list for hostname lookup
    -- Prioritized list of domain names used to resolve
    --  unqualified hostnames.
    -- Linux limits the list to six domains with a total
    --  of 256 characters.

xcmCOInternetDNSDynamicUpdate   -- DNS Dynamic Update (directory)
    OBJECT IDENTIFIER ::= { xcmCOInternetDNS 13 }
    -- integerTruthValue
    -- (true=enableDynamicUpdate, false=disableDynamicUpdate)
    -- (see RFC 2136 'Dynamic Updates in DNS', April 1997)


xcmCOInternetDNSUpdatePolicy    -- DNS Update Policy (directory)
    OBJECT IDENTIFIER ::= { xcmCOInternetDNS 14 }
    -- integerEnum
    -- (1=lastUpdateWins, 2=firstUpdateWins)
    -- (see RFC 2136 'Dynamic Updates in DNS', April 1997)
xcmCOInternetDNSMulticastEnable  -- DNS Multicast Enable
    OBJECT IDENTIFIER ::= { xcmCOInternetDNS 30 }
    -- integerTruthValue (true=enableMDNS, false=disableMDNS)
    -- (use of link local multicast DNS extensions)
    -- (see 'draft-ietf-dnsext-mdns-03.txt', July 2001)
    -- (see 'draft-guttman-dhc-mdns-enable-01.txt', July 2001)
xcmCOInternetIOSDiscoveryEnable -- IOS Discovery Enable
    OBJECT IDENTIFIER ::= { xcmCOInternetDNS 31 }
    -- integerTruthValue (true=enableIOSDiscovery,
    --                    false=disableIOSDiscovery)
    -- (Apple IOS discovery advertisement)

xcmCOInternetHTTPAddressURL     -- HTTP Universal Resource Locator (WWW)
    OBJECT IDENTIFIER ::= { xcmCOInternetHTTP 1 }
    -- stringLocalization
xcmCOInternetHTTPAddressURI     -- HTTP Universal Resource ID (WWW)
    OBJECT IDENTIFIER ::= { xcmCOInternetHTTP 2 }
    -- stringLocalization
xcmCOInternetHTTPAddressURN     -- HTTP Universal Resource Name (WWW)
    OBJECT IDENTIFIER ::= { xcmCOInternetHTTP 3 }
    -- stringLocalization
xcmCOInternetHTTPVersionString  -- HTTP Version String
    OBJECT IDENTIFIER ::= { xcmCOInternetHTTP 9 }
    -- stringLocalization (eg, '1.1' for HTTP/1.1, RFC 2616)
xcmCOInternetHTTPListenSocket   -- HTTP Listen Socket
    OBJECT IDENTIFIER ::= { xcmCOInternetHTTP 11 }
    -- integerNumber (80=default or 1..n)
    -- (see Internet Assigned Numbers, RFC 1700, and IANA registry)
xcmCOInternetHTTPMaxClients     -- HTTP Max Clients (concurrently)
    OBJECT IDENTIFIER ::= { xcmCOInternetHTTP 12 }
    -- integerNumber (0..n)
xcmCOInternetHTTPClientTimeout  -- HTTP Client Timeout (concurrently)
    OBJECT IDENTIFIER ::= { xcmCOInternetHTTP 13 }
    -- integerNumber (seconds, 0=infinite or 1..n)
xcmCOInternetHTTPStatusRefresh  -- HTTP Status Refresh Delay
    OBJECT IDENTIFIER ::= { xcmCOInternetHTTP 14 }
    -- integerNumber (seconds, 0=infinite or 1..n)
    -- The refresh delay used by CWIS when updating status

xcmCOInternetHTTPAdminAddress  -- HTTP Admin Address
    OBJECT IDENTIFIER ::= { xcmCOInternetHTTP 15 }
    -- integerTruthValue(8) & stringLocalization(13)
    -- The HTTP Administrator Accept Address
    -- i.e. the Host Access List for HTTP/CWIS

xcmCOInternetHTTPKeyUsrAddress  -- HTTP Key User Address
    OBJECT IDENTIFIER ::= { xcmCOInternetHTTP 16 }
    -- integerTruthValue(8) & stringLocalization(13)


    -- The HTTP Key User Accept Address
    -- i.e. the Host Access List for HTTP/CWIS

xcmCOInternetHTTPProxy   -- HTTP Proxy enabled/disabled
    OBJECT IDENTIFIER ::= { xcmCOInternetHTTP 20 }

xcmCOInternetHTTPInfoFwd  -- HTTP Information Forwarding
    OBJECT IDENTIFIER ::= { xcmCOInternetHTTP 25 }
    -- integerTruthValue
    -- (true=Information Forwarding to Xerox enabled,
    --  false=Information Forwarding disabled)
    -- When enabled information about model, install date, etc.
    -- can be sent to Xerox.
xcmCOInternetHTTPProxyIPAddress  -- HTTP Proxy IP address
    OBJECT IDENTIFIER ::= { xcmCOInternetHTTPProxy 1 }

xcmCOInternetHTTPProxyHostName  -- HTTP Proxy Host Name
    OBJECT IDENTIFIER ::= { xcmCOInternetHTTPProxy 2 }

xcmCOInternetHTTPProxyPortNumber   -- HTTP Proxy Port Number
    OBJECT IDENTIFIER ::= { xcmCOInternetHTTPProxy 3 }

xcmCOInternetHTTPProxyExceptions   -- HTTP Proxy Exceptions
    OBJECT IDENTIFIER ::= { xcmCOInternetHTTPProxy 4 }
    --  stringLocalization
    --  Used to specify a list of addresses that do not require
    --    the use of proxy.
    --  Semicolons are used to separate entries.
    --  Address lists that are longer than 255 characters require
    --    multiple rows to be predefined in the CommsOption table.
    --  The rows are related using the NextIndex, PreviousIndex
    --    and FamilyIndex.
    --  The FamilyIndex from the first
    --    xcmCOInternetHTTPProxyExceptions node shall indicate the
    --    next node.
    --  The final node shall be identified using NextIndex
    --     and FamilyIndex equal to zero.
    --  It is the responsibility of the management tool to "get"
    --     all rows and concatenate them for display.
    --  It is the responsibility of the management tool to break
    --     up the string into segments that are less than 255 to
    --     "set" the rows.

xcmCOInternetHTTPProxyServer      -- HTTP Proxy Server IP Address
                                  --    or Host Name
    OBJECT IDENTIFIER ::= { xcmCOInternetHTTPProxy 5 }
    -- stringLocalization
    -- The IP address or Host Name of the HTTP Proxy server.

xcmCOInternetHTTPProxyUserName   -- HTTP Proxy User Name (for login)
    OBJECT IDENTIFIER ::= { xcmCOInternetHTTPProxy 6 }
    -- stringLocalization
    -- (default user name for login to HTTP Proxy )


xcmCOInternetHTTPProxyPassword  -- HTTP Proxy Password (for login)
    OBJECT IDENTIFIER ::= { xcmCOInternetHTTPProxy 7 }
    -- stringLocalization (SHALL be encrypted)
    -- (default password for login to HTTP Proxy )

xcmCOInternetHTTPProxyAutoDetect  -- HTTP Proxy Auto Detect
    OBJECT IDENTIFIER ::= { xcmCOInternetHTTPProxy 8 }
    -- integerTruthValue
    -- (true=automatically check for and retrieve proxy server
    --    if no valid proxy server is defined,
    --  false=do not automatically check for valid proxy server)

xcmCOInternetHTTPProxyShareSettings -- HTTP Proxy Shared Settings
    OBJECT IDENTIFIER::= { xcmCOInternetHTTPProxy 9 }
    -- integerTruthValue
    -- Used to share the same Proxy settings for HTTP and HTTPS

xcmCOInternetHTTPProxyAuthValid -- HTTP Proxy Authentication Valid
    OBJECT IDENTIFIER::= { xcmCOInternetHTTPProxy 10 }
    -- integerTruthValue
    -- Used to determine if authentication is used for HTTP

xcmCOInternetPOP3HostName       -- POP3 Host Name
    OBJECT IDENTIFIER ::= { xcmCOInternetPOP3 1 }
    -- stringLocalization

xcmCOInternetPOP3HostAddress    -- POP3 Host Address
    OBJECT IDENTIFIER ::= { xcmCOInternetPOP3 2 }
    -- stringLocalization (IPv4 - dotted decimal 'a.b.c.d')
    -- (see 'xcmCOInternetIPAddress' for references)

xcmCOInternetPOP3PollInterval   -- POP3 Poll Interval
    OBJECT IDENTIFIER ::= { xcmCOInternetPOP3 4 }
    -- integerNumber (seconds, 0=immediate or 1..n)
    -- (0=immediate - poll as frequently as application wishes)
    -- (1..n=interval in seconds - SHOULD NOT be less than 3 seconds)
    -- (max_int=poll once every 68 years - ie, disable polling)
xcmCOInternetPOP3Subject        -- POP3 Subject (default)
    OBJECT IDENTIFIER ::= { xcmCOInternetPOP3 44 }
    -- stringLocalization
    -- (default subject field for outgoing POP3 message)
xcmCOInternetPOP3SignatureLine  -- POP3 Signature Line (default)
    OBJECT IDENTIFIER ::= { xcmCOInternetPOP3 45 }
    -- stringLocalization
    -- (default signature line for outgoing POP3 message)
xcmCOInternetPOP3UserName       -- POP3 User Name (for login to MTA)
    OBJECT IDENTIFIER ::= { xcmCOInternetPOP3 47 }
    -- stringLocalization
    -- (default user name for login to remote MTA)
xcmCOInternetPOP3Password       -- POP3 Password (for login to MTA)
    OBJECT IDENTIFIER ::= { xcmCOInternetPOP3 48 }
    -- stringLocalization (SHALL be encrypted)
    -- (default password for login to remote MTA)


xcmCOInternetPOP3MaxInputText   -- POP3 Max Text Body Size (incoming)
    OBJECT IDENTIFIER ::= { xcmCOInternetPOP3 50 }
    -- integerNumber (bytes, 0=none, or 1..n)
    -- (max text body size for incoming POP3 message)
    -- (value of zero indicates incoming text body is NOT allowed)
xcmCOInternetPOP3MaxInputAttach -- POP3 Max Attachment Size (incoming)
    OBJECT IDENTIFIER ::= { xcmCOInternetPOP3 51 }
    -- integerNumber (bytes, 0=none, or 1..n)
    -- (max attachment size for incoming POP3 message)
    -- (value of zero indicates incoming attachment is NOT allowed)
xcmCOInternetPOP3MaxOutputText  -- POP3 Max Text Body Size (outgoing)
    OBJECT IDENTIFIER ::= { xcmCOInternetPOP3 52 }
    -- integerNumber (bytes, 0=none, or 1..n)
    -- (max text body size for outgoing POP3 message)
    -- (value of zero indicates outgoing text body is NOT allowed)
xcmCOInternetPOP3MaxOutputAttach -- POP3 Max Attachment Size (outgoing)
    OBJECT IDENTIFIER ::= { xcmCOInternetPOP3 53 }
    -- integerNumber (bytes, 0=none, or 1..n)
    -- (max attachment size for outgoing POP3 message)
    -- (value of zero indicates outgoing attachment is NOT allowed)
xcmCOInternetPOP3ConfirmRequest -- POP3 Confirm Outgoing Email
    OBJECT IDENTIFIER ::= { xcmCOInternetPOP3 54 }
    -- integerTruthValue (true=enableMDN, false=disableMDN)
xcmCOInternetPOP3ConfirmReply   -- POP3 Confirm Incoming Email
    OBJECT IDENTIFIER ::= { xcmCOInternetPOP3 55 }
    -- integerTruthValue (true=enableMDN, false=disableMDN)
xcmCOInternetPOP3ConfirmTimeout -- POP3 Confirm Outgoing Timeout
    OBJECT IDENTIFIER ::= { xcmCOInternetPOP3 56 }
    -- integerNumber (seconds, 0=none, or 1..n)
xcmCOInternetPOP3FeatureReply   -- POP3 Feature Report in Confirm Reply
    OBJECT IDENTIFIER ::= { xcmCOInternetPOP3 57 }
    -- integerTruthValue (true=enableReport, false=disableReport)
xcmCOInternetPOP3MailAddress    -- POP3 Mail Address
    OBJECT IDENTIFIER ::= { xcmCOInternetPOP3 58 }
    -- stringLocalization (RFC 822 format - 'user@hostname')
    -- (see RFC 822, 'Format of Internet Mail Messages', August, 1982)
xcmCOInternetPOP3MaxInFragments -- POP3 Max Fragments (incoming)
    OBJECT IDENTIFIER ::= { xcmCOInternetPOP3 59 }
    -- integerNumber (0=none, or 2..n)
    -- (max fragments for incoming POP3 message)
    -- (zero indicates incoming fragments are NOT allowed)
xcmCOInternetPOP3MaxOutFragments -- POP3 Max Fragments (outgoing)
    OBJECT IDENTIFIER ::= { xcmCOInternetPOP3 60 }
    -- integerNumber (0=none, or 2..n)
    -- (max fragments for outgoing POP3 message)
    -- (zero indicates outgoing fragments are NOT allowed)
xcmCOInternetPOP3MaxInAttachments -- POP3 Max Attachments (incoming)
    OBJECT IDENTIFIER ::= { xcmCOInternetPOP3 61 }
    -- integerNumber (0=none, or 1..n)
    -- (max attachments for incoming POP3 message)
    -- (zero indicates incoming attachments are NOT allowed)
xcmCOInternetPOP3MaxOutAttachments -- POP3 Max Attachments (outgoing)
    OBJECT IDENTIFIER ::= { xcmCOInternetPOP3 62 }
    -- integerNumber (0=none, or 1..n)


    -- (max attachments for outgoing POP3 message)
    -- (zero indicates outgoing attachments are NOT allowed)
xcmCOInternetPOP3MaxInputSize   -- POP3 Max Message Size (incoming)
    OBJECT IDENTIFIER ::= { xcmCOInternetPOP3 63 }
    -- integerNumber (bytes, 0=none, or 1..n)
    -- (max size in bytes for incoming POP3 message)
    -- (zero indicates incoming messages are NOT allowed)
xcmCOInternetPOP3MaxOutputSize  -- POP3 Max Message Size (outgoing)
    OBJECT IDENTIFIER ::= { xcmCOInternetPOP3 64 }
    -- integerNumber (bytes, 0=none, or 1..n)
    -- (max size in bytes for outgoing POP3 message)
    -- (zero indicates outgoing messages are NOT allowed)

xcmCOInternetIMAP4HostName      -- IMAP4 Host Name
    OBJECT IDENTIFIER ::= { xcmCOInternetIMAP4 1 }
    -- stringLocalization

xcmCOInternetIMAP4HostAddress   -- IMAP4 Host Address
    OBJECT IDENTIFIER ::= { xcmCOInternetIMAP4 2 }
    -- stringLocalization (IPv4 - dotted decimal 'a.b.c.d')
    -- (see 'xcmCOInternetIPAddress' for references)

xcmCOInternetIMAP4PollInterval  -- IMAP4 Poll Interval
    OBJECT IDENTIFIER ::= { xcmCOInternetIMAP4 4 }
    -- integerNumber (seconds, 0=immediate or 1..n)
    -- (0=immediate - poll as frequently as application wishes)
    -- (1..n=interval in seconds - SHOULD NOT be less than 3 seconds)
    -- (max_int=poll once every 68 years - ie, disable polling)
xcmCOInternetIMAP4Subject       -- IMAP4 Subject (default)
    OBJECT IDENTIFIER ::= { xcmCOInternetIMAP4 44 }
    -- stringLocalization
    -- (default subject field for outgoing IMAP4 message)
xcmCOInternetIMAP4SignatureLine -- IMAP4 Signature Line (default)
    OBJECT IDENTIFIER ::= { xcmCOInternetIMAP4 45 }
    -- stringLocalization
    -- (default signature line for outgoing IMAP4 message)
xcmCOInternetIMAP4UserName      -- IMAP4 User Name (for login to MTA)
    OBJECT IDENTIFIER ::= { xcmCOInternetIMAP4 47 }
    -- stringLocalization
    -- (default user name for login to remote MTA)
xcmCOInternetIMAP4Password      -- IMAP4 Password (for login to MTA)
    OBJECT IDENTIFIER ::= { xcmCOInternetIMAP4 48 }
    -- stringLocalization (SHALL be encrypted)
    -- (default password for login to remote MTA)
xcmCOInternetIMAP4MaxInputText  -- IMAP4 Max Text Body Size (incoming)
    OBJECT IDENTIFIER ::= { xcmCOInternetIMAP4 50 }
    -- integerNumber (bytes, 0=none, or 1..n)
    -- (max text body size for incoming IMAP4 message)
    -- (value of zero indicates incoming text body is NOT allowed)
xcmCOInternetIMAP4MaxInputAttach -- IMAP4 Max Attachment Size (incoming)
    OBJECT IDENTIFIER ::= { xcmCOInternetIMAP4 51 }
    -- integerNumber (bytes, 0=none, or 1..n)
    -- (max attachment size for incoming IMAP4 message)


    -- (value of zero indicates incoming attachment is NOT allowed)
xcmCOInternetIMAP4MaxOutputText -- IMAP4 Max Text Body Size (outgoing)
    OBJECT IDENTIFIER ::= { xcmCOInternetIMAP4 52 }
    -- integerNumber (bytes, 0=none, or 1..n)
    -- (max text body size for outgoing IMAP4 message)
    -- (value of zero indicates outgoing text body is NOT allowed)
xcmCOInternetIMAP4MaxOutputAttach -- IMAP4 Max Attach Size (outgoing)
    OBJECT IDENTIFIER ::= { xcmCOInternetIMAP4 53 }
    -- integerNumber (bytes, 0=none, or 1..n)
    -- (max attachment size for outgoing IMAP4 message)
    -- (value of zero indicates outgoing attachment is NOT allowed)
xcmCOInternetIMAP4ConfirmRequest -- IMAP4 Confirm Outgoing Email
    OBJECT IDENTIFIER ::= { xcmCOInternetIMAP4 54 }
    -- integerTruthValue (true=enableMDN, false=disableMDN)
xcmCOInternetIMAP4ConfirmReply  -- IMAP4 Confirm Incoming Email
    OBJECT IDENTIFIER ::= { xcmCOInternetIMAP4 55 }
    -- integerTruthValue (true=enableMDN, false=disableMDN)
xcmCOInternetIMAP4ConfirmTimeout -- IMAP4 Confirm Outgoing Timeout
    OBJECT IDENTIFIER ::= { xcmCOInternetIMAP4 56 }
    -- integerNumber (seconds, 0=none, or 1..n)
xcmCOInternetIMAP4FeatureReply  -- IMAP4 Feature Report in Confirm Reply
    OBJECT IDENTIFIER ::= { xcmCOInternetIMAP4 57 }
    -- integerTruthValue (true=enableReport, false=disableReport)
xcmCOInternetIMAP4MailAddress   -- IMAP4 Mail Address
    OBJECT IDENTIFIER ::= { xcmCOInternetIMAP4 58 }
    -- stringLocalization (RFC 822 format - 'user@hostname')
    -- (see RFC 822, 'Format of Internet Mail Messages', August, 1982)
xcmCOInternetIMAP4MaxInFragments -- IMAP4 Max Fragments (incoming)
    OBJECT IDENTIFIER ::= { xcmCOInternetIMAP4 59 }
    -- integerNumber (0=none, or 2..n)
    -- (max fragments for incoming IMAP4 message)
    -- (zero indicates incoming fragments are NOT allowed)
xcmCOInternetIMAP4MaxOutFragments -- IMAP4 Max Fragments (outgoing)
    OBJECT IDENTIFIER ::= { xcmCOInternetIMAP4 60 }
    -- integerNumber (0=none, or 2..n)
    -- (max fragments for outgoing IMAP4 message)
    -- (zero indicates outgoing fragments are NOT allowed)
xcmCOInternetIMAP4MaxInAttachments -- IMAP4 Max Attachments (incoming)
    OBJECT IDENTIFIER ::= { xcmCOInternetIMAP4 61 }
    -- integerNumber (0=none, or 1..n)
    -- (max attachments for incoming IMAP4 message)
    -- (zero indicates incoming attachments are NOT allowed)
xcmCOInternetIMAP4MaxOutAttachments -- IMAP4 Max Attachments (outgoing)
    OBJECT IDENTIFIER ::= { xcmCOInternetIMAP4 62 }
    -- integerNumber (0=none, or 1..n)
    -- (max attachments for outgoing IMAP4 message)
    -- (zero indicates outgoing attachments are NOT allowed)
xcmCOInternetIMAP4MaxInputSize   -- IMAP4 Max Message Size (incoming)
    OBJECT IDENTIFIER ::= { xcmCOInternetIMAP4 63 }
    -- integerNumber (bytes, 0=none, or 1..n)
    -- (max size in bytes for incoming IMAP4 message)
    -- (zero indicates incoming messages are NOT allowed)
xcmCOInternetIMAP4MaxOutputSize  -- IMAP4 Max Message Size (outgoing)
    OBJECT IDENTIFIER ::= { xcmCOInternetIMAP4 64 }


    -- integerNumber (bytes, 0=none, or 1..n)
    -- (max size in bytes for outgoing IMAP4 message)
    -- (zero indicates outgoing messages are NOT allowed)

xcmCOInternetNTPHostName        -- NTP Server hostname
    OBJECT IDENTIFIER ::= { xcmCOInternetNTP 1 }
    -- stringLocalization

xcmCOInternetNTPHostAddress    -- NTP Server IP address
    OBJECT IDENTIFIER ::= { xcmCOInternetNTP 2 }
    -- stringLocalization (IPv4 dotted decimal 'a.b.c.d')

xcmCOInternetNTPv6HostAddress   -- NTP Server IPv6 address
    OBJECT IDENTIFIER ::= { xcmCOInternetNTP 3 }
    -- stringLocalization (IPv6 - hex w/ colons '[x1:...:x8/yyy]')
    -- (see 'xcmCOInternetIPv6Address' for references)

xcmCOInternetNTPPort            -- NTP Port number
    OBJECT IDENTIFIER ::= { xcmCOInternetNTP 4 }
    -- integerNumber (1..999)

xcmCOInternetNTPGMTOffset       -- NTP GMT offset
    OBJECT IDENTIFIER ::= { xcmCOInternetNTP 5 }
    -- integerNumber (-720..+780 minutes)

xcmCOInternetNTPPollInterval    -- NTP Polling interval
    OBJECT IDENTIFIER ::= { xcmCOInternetNTP 6 }
    -- integerNumber (1..1440 minutes)

xcmCOInternetNTPSkewTime        -- NTP Skew time
    OBJECT IDENTIFIER ::= { xcmCOInternetNTP 7 }
    -- integerNumber (1..300 minutes)

xcmCOInternetWINSDomainName     -- WINS Domain Name (directory)
    OBJECT IDENTIFIER ::= { xcmCOInternetWINS 1 }
    -- stringLocalization
xcmCOInternetWINSLanguage       -- WINS Language (directory)
    OBJECT IDENTIFIER ::= { xcmCOInternetWINS 3 }
    -- stringLocalization (language tag, per RFC 2277)
    -- (default is unknown language, per RFC 2277)
xcmCOInternetWINSCharset        -- WINS Charset (directory)
    OBJECT IDENTIFIER ::= { xcmCOInternetWINS 4 }
    -- integerEnum (see 'CodedCharSet' in IETF Printer MIB)
    -- (default '106' UTF-8, per RFC 2277 and RFC 2279)
xcmCOInternetWINSServerName     -- WINS Server Name (directory)
    OBJECT IDENTIFIER ::= { xcmCOInternetWINS 5 }
    -- stringLocalization

xcmCOInternetWINSServerAddress  -- WINS Server Address (directory)
    OBJECT IDENTIFIER ::= { xcmCOInternetWINS 6 }
    -- stringLocalization (IPv4 - dotted decimal 'a.b.c.d')
    -- (see 'xcmCOInternetIPAddress' for references)


xcmCOInternetWINSServerSocket   -- WINS Server Socket (directory)
    OBJECT IDENTIFIER ::= { xcmCOInternetWINS 7 }
    -- integerNumber (1512=default or 1..n)
    -- (see Internet Assigned Numbers, RFC 1700, and IANA registry)

xcmCOInternetLDAPLanguage       -- LDAP Language (directory)
    OBJECT IDENTIFIER ::= { xcmCOInternetLDAP 3 }
    -- stringLocalization (language tag, per RFC 2277)
    -- (default is unknown language, per RFC 2277)
xcmCOInternetLDAPCharset        -- LDAP Charset (directory)
    OBJECT IDENTIFIER ::= { xcmCOInternetLDAP 4 }
    -- integerEnum (see 'CodedCharSet' in IETF Printer MIB)
    -- (default '106' UTF-8, per RFC 2271, RFC 2277, RFC 2279)
xcmCOInternetLDAPServerName     -- LDAP Server Name (directory)
    OBJECT IDENTIFIER ::= { xcmCOInternetLDAP 5 }
    -- stringLocalization

xcmCOInternetLDAPServerAddress  -- LDAP Server Address (directory)
    OBJECT IDENTIFIER ::= { xcmCOInternetLDAP 6 }
    -- stringLocalization (IPv4 - dotted decimal 'a.b.c.d')
    -- (see 'xcmCOInternetIPAddress' for references)

xcmCOInternetLDAPServerSocket   -- LDAP Server Socket (directory)
    OBJECT IDENTIFIER ::= { xcmCOInternetLDAP 7 }
    -- integerNumber (389=default or 1..n)
    -- (see Internet Assigned Numbers, RFC 1700, and IANA registry)
xcmCOInternetLDAPPollInterval   -- LDAP Poll Interval (directory)
    OBJECT IDENTIFIER ::= { xcmCOInternetLDAP 8 }
    -- integerNumber (seconds, 0=immediate or 1..n)
    -- (0=immediate - poll as frequently as application wishes)
    -- (1..n=interval in seconds - SHOULD NOT be less than 3 seconds)
    -- (max_int=poll once every 68 years - ie, disable polling)
xcmCOInternetLDAPBindDN         -- LDAP Bind User Name (directory)
    OBJECT IDENTIFIER ::= { xcmCOInternetLDAP 11 }
    -- stringLocalization
xcmCOInternetLDAPBindPassword   -- LDAP Bind Password (directory)
    OBJECT IDENTIFIER ::= { xcmCOInternetLDAP 12 }
    -- stringLocalization (SHALL be encrypted)
xcmCOInternetLDAPBaseDN         -- LDAP Base Dist Name (directory)
    OBJECT IDENTIFIER ::= { xcmCOInternetLDAP 13 }
    -- stringLocalization
xcmCOInternetLDAPPrinterName    -- LDAP Printer Name (directory)
    OBJECT IDENTIFIER ::= { xcmCOInternetLDAP 21 }
    -- stringLocalization
xcmCOInternetLDAPPrinterClass   -- LDAP Printer Object Class (directory)
    OBJECT IDENTIFIER ::= { xcmCOInternetLDAP 22 }
    -- stringLocalization
xcmCOInternetLDAPAttributeName  -- LDAP Attribute Name (directory)
    OBJECT IDENTIFIER ::= { xcmCOInternetLDAP 31 }
    -- stringLocalization (name of attribute)
xcmCOInternetLDAPAttributeType  -- LDAP Attribute Type (directory)
    OBJECT IDENTIFIER ::= { xcmCOInternetLDAP 32 }
    -- stringLocalization (data type of attribute)


xcmCOInternetLDAPAttributeInt   -- LDAP Attribute Integer (directory)
    OBJECT IDENTIFIER ::= { xcmCOInternetLDAP 33 }
    -- integerNumber (according to type above)
xcmCOInternetLDAPAttributeStr   -- LDAP Attribute String (directory)
    OBJECT IDENTIFIER ::= { xcmCOInternetLDAP 34 }
    -- stringLocalization (according to type) - value per SLPv2
    -- integerEnum (XcmCommsLDAPAttributeType) - name and data type
    -- (see 'XcmCommsLDAPAttributeType' for string encoding rules)
xcmCOInternetLDAPMaxSearchResult -- LDAP Max Search Result (directory)
    OBJECT IDENTIFIER ::= { xcmCOInternetLDAP 35 }
    -- integerNumber (0..n)
    -- (max search results - matching entries)
xcmCOInternetLDAPSearchTimeout  -- LDAP Search Timeout (directory)
    OBJECT IDENTIFIER ::= { xcmCOInternetLDAP 36 }
    -- integerNumber (seconds, 0=infinite or 1..n)

xcmCOInternetSSDPCacheTimeout   -- MS UPnP SSDP Cache Timeout
    OBJECT IDENTIFIER ::= { xcmCOInternetUpnpSSDP 1 }
    -- integerNumber (seconds, 0=none, or 1..n)
    -- (max time to cache service advertisements)
    -- (SHOULD default to 1800 seconds, per MS UPnP architecure specs)
    -- (device SHOULD renew advertisement every CacheTimeout/4 seconds)
xcmCOInternetSSDPTimeToLive     -- MS UPnP SSDP Time To Live
    OBJECT IDENTIFIER ::= { xcmCOInternetUpnpSSDP 2 }
    -- integerNumber (hops, 0=none, or 1..n)
    -- (max hop count for SSDP messages)
    -- (SHOULD default to 1 hop - link local only, per MS Win/ME)
xcmCOInternetSSDPServerVersion  -- MS UPnP SSDP Server Version
    OBJECT IDENTIFIER ::= { xcmCOInternetUpnpSSDP 3 }
    -- stringLocalization (versions of OS, UPnP, and specific product)
    -- (format 'OS/ver UPnP/ver ProductName/ver')
    -- (eg, 'Linux/8.0 UPnP/1.0 DocuCentre/470')

xcmCOInternetSLPLanguage        -- SLP Language (discovery)
    OBJECT IDENTIFIER ::= { xcmCOInternetSLP 3 }
    -- stringLocalization (language tag, per RFC 2277)
    -- (default is unknown language, per RFC 2277)
xcmCOInternetSLPCharset         -- SLP Charset (discovery)
    OBJECT IDENTIFIER ::= { xcmCOInternetSLP 4 }
    -- integerEnum (see 'CodedCharSet' in IETF Printer MIB)
    -- (default '106' UTF-8, per RFC 2271, RFC 2277, RFC 2279)
xcmCOInternetSLPServerName      -- SLP Server Name (discovery)
    OBJECT IDENTIFIER ::= { xcmCOInternetSLP 5 }
    -- stringLocalization (see Directory Agent in IETF SLP)

xcmCOInternetSLPServerAddress   -- SLP Server Address (discovery)
    OBJECT IDENTIFIER ::= { xcmCOInternetSLP 6 }
    -- stringLocalization (IPv4 - dotted decimal 'a.b.c.d')
    -- (see 'xcmCOInternetIPAddress' for references)

xcmCOInternetSLPServerSocket    -- SLP Server Socket (discovery)
    OBJECT IDENTIFIER ::= { xcmCOInternetSLP 7 }
    -- integerNumber (427=default or 1..n)
    -- (see Internet Assigned Numbers, RFC 1700, and IANA registry)


xcmCOInternetSLPPollInterval    -- SLP Poll Interval (discovery)
    OBJECT IDENTIFIER ::= { xcmCOInternetSLP 8 }
    -- integerNumber (seconds, 0=immediate or 1..n)
    -- (0=immediate - poll as frequently as application wishes)
    -- (1..n=interval in seconds - SHOULD NOT be less than 3 seconds)
    -- (max_int=poll once every 68 years - ie, disable polling)
    -- (obsoleted by 'xcmCOInternetSLPDAFindActiveWait')

--  SLPv2 (section 13, RFC 2608) and SLPv1 (section 22.2, RFC 2165)
xcmCOInternetSLPMaxMulticastTime -- SLP Max Multicast Complete Time
    OBJECT IDENTIFIER ::= { xcmCOInternetSLP 10 }
    -- integerNumber (seconds, 0=none, or 1..n)
    -- (max time to wait for a complete multicast query response)
    -- (SHOULD default to 15 seconds, per SLPv2 RFC 2608)
    -- (see SLPv2 RFC 2608 CONFIG_MAX_MC)
    -- (see SLPv1 RFC 2165 CONFIG_INTERVAL_3)
    -- (compare SLPv1 RFC 2165 CONFIG_INTERVAL_7)
xcmCOInternetSLPDAFindStartWait  -- SLP DA Find Start Wait
    OBJECT IDENTIFIER ::= { xcmCOInternetSLP 11 }
    -- integerNumber (seconds, 0=none, or 1..n)
    -- (interval to wait before starting DA discovery after SA reboot)
    -- (SHOULD default to 3 seconds, per SLPv2 RFC 2608)
    -- (see SLPv2 RFC 2608 CONFIG_START_WAIT)
    -- (see SLPv1 RFC 2165 CONFIG_INTERVAL_4)
xcmCOInternetSLPInitialRetryWait -- SLP Initial Request Retry Wait
    OBJECT IDENTIFIER ::= { xcmCOInternetSLP 12 }
    -- integerNumber (seconds, 0=none, or 1..n)
    -- (interval to wait before initial retry of multicast or unicast)
    -- (SHOULD default to 2 seconds, per SLPv2 RFC 2608)
    -- (see SLPv2 RFC 2608 CONFIG_RETRY)
    -- (see SLPv1 RFC 2165 CONFIG_INTERVAL_2)
    -- (compare SLPv1 RFC 2165 CONFIG_INTERVAL_5)
    -- (compare SLPv1 RFC 2165 CONFIG_INTERVAL_6)
xcmCOInternetSLPMaxUnicastTime   -- SLP Max Unicast Complete Time
    OBJECT IDENTIFIER ::= { xcmCOInternetSLP 13 }
    -- integerNumber (seconds, 0=none, or 1..n)
    -- (max time to wait for a complete unicast query response)
    -- (SHOULD default to 15 seconds, per SLPv2 RFC 2608)
    -- (see SLPv2 RFC 2608 CONFIG_RETRY_MAX)
    -- (see SLPv1 RFC 2165 CONFIG_INTERVAL_8)
    -- (compare SLPv1 RFC 2165 CONFIG_INTERVAL_8)
xcmCOInternetSLPDAHeartbeatTime  -- SLP DA Heartbeat Time
    OBJECT IDENTIFIER ::= { xcmCOInternetSLP 14 }
    -- integerNumber (seconds, 0=none, or 1..n)
    -- (interval to wait before DA multicast/broadcast DAAdvert)
    -- (SHOULD default to 10800 seconds [3 hours], per SLPv2 RFC 2608)
    -- (see SLPv2 RFC 2608 CONFIG_DA_BEAT)
    -- (see SLPv1 RFC 2165 CONFIG_INTERVAL_9)
xcmCOInternetSLPDAFindActiveWait -- SLP DA Find Active Retry Wait
    OBJECT IDENTIFIER ::= { xcmCOInternetSLP 15 }
    -- integerNumber (seconds, 0=none, or 1..n)
    -- (interval to wait before retry of active DA discovery)
    -- (SHOULD default to 900 seconds [15 minutes], per SLPv2 RFC 2608)
    -- (see SLPv2 RFC 2608 CONFIG_DA_FIND)


    -- (no SLPv1 RFC 2165 equivalent configuration)
    -- (obsoletes 'xcmCOInternetSLPPollInterval' above)
xcmCOInternetSLPRegPassiveWait   -- SLP Register After Passive Find Wait
    OBJECT IDENTIFIER ::= { xcmCOInternetSLP 16 }
    -- integerNumber (seconds, 0=none, or 1..n)
    -- (interval to wait before registration after passive DA discovery)
    -- (SHOULD default to 1-3 seconds, per SLPv2 RFC 2608)
    -- (see SLPv2 RFC 2608 CONFIG_REG_PASSIVE)
    -- (see SLPv1 RFC 2165 CONFIG_INTERVAL_10)
xcmCOInternetSLPRegActiveWait    -- SLP Register After Active Find Wait
    OBJECT IDENTIFIER ::= { xcmCOInternetSLP 17 }
    -- integerNumber (seconds, 0=none, or 1..n)
    -- (interval to wait before registration after active DA discovery)
    -- (SHOULD default to 1-3 seconds, per SLPv2 RFC 2608)
    -- (see SLPv2 RFC 2608 CONFIG_REG_ACTIVE)
    -- (see SLPv1 RFC 2165 CONFIG_INTERVAL_11)
xcmCOInternetSLPCloseConnWait    -- SLP Close Idle Connection Wait
    OBJECT IDENTIFIER ::= { xcmCOInternetSLP 18 }
    -- integerNumber (seconds, 0=none, or 1..n)
    -- (interval to wait before DAs and SAs close idle connection)
    -- (SHOULD default to 300 seconds [5 minutes], per SLPv2 RFC 2608)
    -- (see SLPv2 RFC 2608 CONFIG_CLOSE_CONN)
    -- (see SLPv1 RFC 2165 CONFIG_INTERVAL_12)
xcmCOInternetSLPCacheReplyTime   -- SLPv1 Cache Reply by XID Time
    OBJECT IDENTIFIER ::= { xcmCOInternetSLP 20 }
    -- integerNumber (seconds, 0=none, or 1..n)
    -- (max time to cache responses by XID before discarding)
    -- (SHOULD default to 60 seconds, per SLPv1 RFC 2165)
    -- (see SLPv1 RFC 2165 CONFIG_INTERVAL_0)
xcmCOInternetSLPMaxRegLifetime   -- SLPv1 Max Registration Lifetime
    OBJECT IDENTIFIER ::= { xcmCOInternetSLP 21 }
    -- integerNumber (seconds, 0=none, or 1..n)
    -- (max lifetime of registrations before expiration)
    -- (SHOULD default to 10800 seconds, per SLPv1 RFC 2165)
    -- (see SLPv1 RFC 2165 CONFIG_INTERVAL_1)
xcmCOInternetSLPDAFindRetryWait  -- SLP DA Find Retry Wait
    OBJECT IDENTIFIER ::= { xcmCOInternetSLP 22 }
    -- integerNumber (seconds, 0=none, or 1..n)
    -- (interval to wait before retransmit DA discovery)
    -- (SHOULD default to 3 seconds, per SLPv1 RFC 2165)
    -- (compare SLPv2 RFC 2608 CONFIG_RETRY)
    -- (see SLPv1 RFC 2165 CONFIG_INTERVAL_5)
xcmCOInternetSLPMaxDARequestTime -- SLP Max DA Request Time
    OBJECT IDENTIFIER ::= { xcmCOInternetSLP 23 }
    -- integerNumber (seconds, 0=none, or 1..n)
    -- (interval to wait before DA request timeout)
    -- (SHOULD default to 5 seconds, per SLPv1 RFC 2165)
    -- (compare SLPv2 RFC 2608 CONFIG_RETRY)
    -- (see SLPv1 RFC 2165 CONFIG_INTERVAL_6)
xcmCOInternetSLPMulticastEnable  -- SLP Multicast Enable
    OBJECT IDENTIFIER ::= { xcmCOInternetSLP 30 }
    -- integerTruthValue (true=useMulticast, false=useBroadcast)
    -- (use of multicast [scalable] versus broadcast [non-scalable])
    -- (SHOULD default to 'true', per SLPv1 RFC 2165)


    -- (SHOULD default to 'true', per SLPv2 RFC 2608)
xcmCOInternetSLPMulticastRadius  -- SLP Multicast Radius (hop count)
    OBJECT IDENTIFIER ::= { xcmCOInternetSLP 31 }
    -- integerNumber (0..255)
    -- (multicast/broadcast radius)
    -- (SHOULD default to 32, per SLPv1 RFC 2165)
    -- (range '0..32' for SLPv1 RFC 2165)
    -- (range '0..255' for SLPv2 RFC 2608)
xcmCOInternetSLPPathMTUSize      -- SLP Path MTU Size
    OBJECT IDENTIFIER ::= { xcmCOInternetSLP 32 }
    -- integerNumber (0..n)
    -- (path max transmission unit size in bytes)
    -- (SHOULD default to 1400, per SLPv1 RFC 2165)
xcmCOInternetSLPScopeName        -- SLP Scope Name
    OBJECT IDENTIFIER ::= { xcmCOInternetSLP 40 }
    -- stringLocalization
    -- (configured scope name)
    -- (SHOULD default to 'DEFAULT', per SLPv2 RFC 2608)
xcmCOInternetSLPScopeKey         -- SLP Scope Key
    OBJECT IDENTIFIER ::= { xcmCOInternetSLP 41 }
    -- stringLocalization (SHALL be encrypted)
    -- (configured protected scope key)
    -- (see section 22, SLPv1 RFC 2165)
xcmCOInternetSLPAttributesEnable  -- SLP Attributes Enable
    OBJECT IDENTIFIER ::= { xcmCOInternetSLP 50 }
    -- integerTruthValue
    -- (true=enable SLP Attributes support,
    --  false=disable SLP Attributes support)

xcmCOInternetOsfDceKerberosRealm -- OSF DCE Kerberos Realm (security)
    OBJECT IDENTIFIER ::= { xcmCOInternetOsfDceKerberos 1 }
    -- stringLocalization

--
--          AppleTalk Protocol Suite
--

xcmCOAppletalkSuite
    OBJECT IDENTIFIER ::= { xcmCommsConfigTC 18 }
    -- integerTruthValue

xcmCOAppletalkDatalinks
    OBJECT IDENTIFIER ::= { xcmCOAppletalkSuite 1200 }
    -- integerTruthValue (w/ chain of 'xcmCOOsilan...')
    -- (obsoletes 'xcmCOAppletalkDDPDatalinks')
xcmCOAppletalkLLAP              -- LocalTalk LAP (datalink)
    OBJECT IDENTIFIER ::= { xcmCOAppletalkSuite 1201 }
    -- integerTruthValue
xcmCOAppletalkELAP              -- EtherTalk LAP (datalink)
    OBJECT IDENTIFIER ::= { xcmCOAppletalkSuite 1202 }
    -- integerTruthValue
xcmCOAppletalkTLAP              -- TokenTalk LAP (datalink)
    OBJECT IDENTIFIER ::= { xcmCOAppletalkSuite 1203 }


    -- integerTruthValue
xcmCOAppletalkPhase             -- AppleTalk Phase (datalink)
    OBJECT IDENTIFIER ::= { xcmCOAppletalkSuite 1211 }
    -- integerEnum (1=phase1, 2=phase2)

xcmCOAppletalkTransports
    OBJECT IDENTIFIER ::= { xcmCOAppletalkSuite 1400 }
    -- integerTruthValue
xcmCOAppletalkDDP               -- DDP (CL network)
    OBJECT IDENTIFIER ::= { xcmCOAppletalkSuite 1301 }
    -- integerTruthValue
xcmCOAppletalkAARP              -- AARP (routing)
    OBJECT IDENTIFIER ::= { xcmCOAppletalkSuite 1303 }
    -- integerTruthValue
xcmCOAppletalkATP               -- ATP (CL transport)
    OBJECT IDENTIFIER ::= { xcmCOAppletalkSuite 1401 }
    -- integerTruthValue
xcmCOAppletalkADSP              -- ADSP (CO transport)
    OBJECT IDENTIFIER ::= { xcmCOAppletalkSuite 1402 }
    -- integerTruthValue
xcmCOAppletalkRTMP              -- RTMP (routing)
    OBJECT IDENTIFIER ::= { xcmCOAppletalkSuite 1403 }
    -- integerTruthValue
xcmCOAppletalkAEP               -- AEP (echo)
    OBJECT IDENTIFIER ::= { xcmCOAppletalkSuite 1404 }
    -- integerTruthValue
xcmCOAppletalkNBP               -- NBP (directory)
    OBJECT IDENTIFIER ::= { xcmCOAppletalkSuite 1405 }
    -- integerTruthValue

xcmCOAppletalkDDPAddress        -- DDP Node Address
    OBJECT IDENTIFIER ::= { xcmCOAppletalkDDP 1 }
    -- stringLocalization (dotted hex format, 'network.node')
    -- ('network' [4 octets] - ASCII hex of 2-octet AppleTalk network)
    -- ('node'    [2 octets] - ASCII hex of 1-octet AppleTalk node)
xcmCOAppletalkDDPSocketAddress  -- DDP Socket Address
    OBJECT IDENTIFIER ::= { xcmCOAppletalkDDPAddress 1 }
    -- stringLocalization (dotted hex format, 'network.node.socket')
    -- ('network' [4 octets] - ASCII hex of 2-octet AppleTalk network)
    -- ('node'    [2 octets] - ASCII hex of 1-octet AppleTalk node)
    -- ('socket'  [2 octets] - ASCII hex of 1-octet AppleTalk socket)
xcmCOAppletalkDDPDatalinks      -- DDP Datalinks
    OBJECT IDENTIFIER ::= { xcmCOAppletalkDDP 12 }
    -- integerTruthValue (w/ chain of 'xcmCOOsilan...')
    -- (obsoleted by 'xcmCOAppletalkDatalinks')

xcmCOAppletalkNBPHostName       -- NBP Host Name (directory)
    OBJECT IDENTIFIER ::= { xcmCOAppletalkNBP 1 }
    -- stringLocalization (AppleTalk name is 'Object:Type@Zone')
    -- (restricted to 'AppleASCII' chars, per Apple 'Inside Macintosh')
xcmCOAppletalkNBPLanguage       -- NBP Language (directory)
    OBJECT IDENTIFIER ::= { xcmCOAppletalkNBP 3 }
    -- stringLocalization (language tag, per RFC 2277)
    -- (default is unknown language, per RFC 2277)


xcmCOAppletalkNBPCharset        -- NBP Charset (directory)
    OBJECT IDENTIFIER ::= { xcmCOAppletalkNBP 4 }
    -- integerEnum (see 'CodedCharSet' in IETF Printer MIB)
    -- (default '106' UTF-8, per RFC 2277, RFC 2279)
    -- (restricted to 'AppleASCII' chars, per Apple 'Inside Macintosh')
xcmCOAppletalkNBPObject         -- NBP Object (directory)
    OBJECT IDENTIFIER ::= { xcmCOAppletalkNBP 11 }
    -- stringLocalization
    -- (restricted to 'AppleASCII' chars, per Apple 'Inside Macintosh')
xcmCOAppletalkNBPType           -- NBP Type (directory)
    OBJECT IDENTIFIER ::= { xcmCOAppletalkNBP 12 }
    -- stringLocalization ('LaserWriter'=default)
    -- (restricted to 'AppleASCII' chars, per Apple 'Inside Macintosh')
xcmCOAppletalkNBPZone           -- NBP Zone (directory)
    OBJECT IDENTIFIER ::= { xcmCOAppletalkNBP 13 }
    -- stringLocalization
    -- (restricted to 'AppleASCII' chars, per Apple 'Inside Macintosh')
xcmCOAppletalkNBPNetwork        -- NBP Network (directory)
    OBJECT IDENTIFIER ::= { xcmCOAppletalkNBP 21 }
    -- integerNumber (0..65534)
xcmCOAppletalkNBPNode           -- NBP Node (directory)
    OBJECT IDENTIFIER ::= { xcmCOAppletalkNBP 22 }
    -- integerNumber (0..254)
xcmCOAppletalkNBPSocket         -- NBP Socket (directory)
    OBJECT IDENTIFIER ::= { xcmCOAppletalkNBP 23 }
    -- integerNumber (0..254)
xcmCOAppletalkNBPZoneToNetworks -- NBP Zone to Networks (directory)
    OBJECT IDENTIFIER ::= { xcmCOAppletalkNBP 31 }
    -- stringLocalization (dotted string 'zone.netFirst.netLast')

xcmCOAppletalkApplications
    OBJECT IDENTIFIER ::= { xcmCOAppletalkSuite 1700 }
    -- integerTruthValue
xcmCOAppletalkASP               -- ASP (CO session)
    OBJECT IDENTIFIER ::= { xcmCOAppletalkSuite 1501 }
    -- integerTruthValue
xcmCOAppletalkZIP               -- ZIP (directory)
    OBJECT IDENTIFIER ::= { xcmCOAppletalkSuite 1502 }
    -- integerTruthValue
xcmCOAppletalkPAP               -- PAP (printing)
    OBJECT IDENTIFIER ::= { xcmCOAppletalkSuite 1503 }
    -- integerTruthValue

xcmCOAppletalkSNMP              -- SNMP (network mgmt)
    OBJECT IDENTIFIER ::= { xcmCOAppletalkSuite 1510 }
    -- integerTruthValue
xcmCOAppletalkSNMPv1            -- SNMPv1 (network mgmt)
    OBJECT IDENTIFIER ::= { xcmCOAppletalkSuite 1511 }
    -- integerTruthValue
xcmCOAppletalkSNMPv2            -- SNMPv2 (network mgmt)
    OBJECT IDENTIFIER ::= { xcmCOAppletalkSuite 1512 }
    -- integerTruthValue
xcmCOAppletalkSNMPv3            -- SNMPv3 (network mgmt)
    OBJECT IDENTIFIER ::= { xcmCOAppletalkSuite 1513 }


    -- integerTruthValue

xcmCOAppletalkAFP               -- AFP (filing)
    OBJECT IDENTIFIER ::= { xcmCOAppletalkSuite 1601 }
    -- integerTruthValue
xcmCOAppletalkPS                -- PostScript (printing)
    OBJECT IDENTIFIER ::= { xcmCOAppletalkSuite 1602 }
    -- integerTruthValue

xcmCOAppletalkPAPHostName       -- PAP Host Name
    OBJECT IDENTIFIER ::= { xcmCOAppletalkPAP 1 }
    -- stringLocalization (AppleTalk name is 'Object:Type@Zone')
xcmCOAppletalkPAPHostAddress    -- PAP Host Address
    OBJECT IDENTIFIER ::= { xcmCOAppletalkPAP 2 }
    -- stringLocalization (dotted hex format, 'network.node.socket')
xcmCOAppletalkPAPListenSocket   -- PAP Listen Socket
    OBJECT IDENTIFIER ::= { xcmCOAppletalkPAP 3 }
    -- integerNumber (140=default or 3..255)
xcmCOAppletalkPAPMaxClients     -- PAP Max Clients (concurrently)
    OBJECT IDENTIFIER ::= { xcmCOAppletalkPAP 4 }
    -- integerNumber (0..n)
xcmCOAppletalkPAPMaxPrinters    -- PAP Max Printers (printing)
    OBJECT IDENTIFIER ::= { xcmCOAppletalkPAP 5 }
    -- integerNumber (1=default or 1..n)
xcmCOAppletalkPAPObject         -- PAP Object (printing)
    OBJECT IDENTIFIER ::= { xcmCOAppletalkPAP 11 }
    -- stringLocalization
    -- (restricted to 'AppleASCII' chars, per Apple 'Inside Macintosh')
xcmCOAppletalkPAPType           -- PAP Type (printing)
    OBJECT IDENTIFIER ::= { xcmCOAppletalkPAP 12 }
    -- stringLocalization ('LaserWriter'=default)
    -- (restricted to 'AppleASCII' chars, per Apple 'Inside Macintosh')
xcmCOAppletalkPAPZone           -- PAP Zone (printing)
    OBJECT IDENTIFIER ::= { xcmCOAppletalkPAP 13 }
    -- stringLocalization
    -- (restricted to 'AppleASCII' chars, per Apple 'Inside Macintosh')
xcmCOAppletalkPAPNetwork        -- PAP Network (printing)
    OBJECT IDENTIFIER ::= { xcmCOAppletalkPAP 21 }
    -- integerNumber (0..65534)
xcmCOAppletalkPAPNode           -- PAP Node (printing)
    OBJECT IDENTIFIER ::= { xcmCOAppletalkPAP 22 }
    -- integerNumber (0..254)
xcmCOAppletalkPAPSpool          -- PAP Spool (printing)
    OBJECT IDENTIFIER ::= { xcmCOAppletalkPAP 31 }
    -- integerEnum (1=none, 2=other, 3=disk, 4=ram)
xcmCOAppletalkPAPMaxSpool       -- PAP Max Spool (printing)
    OBJECT IDENTIFIER ::= { xcmCOAppletalkPAP 32 }
    -- integerNumber (spool area size in bytes, 0..n)
xcmCOAppletalkPAPJobTimeout     -- PAP Job Timeout (printing)
    OBJECT IDENTIFIER ::= { xcmCOAppletalkPAP 40 }
    -- integerNumber (seconds, 0=infinite or 1..n)
xcmCOAppletalkPAPAutoSwitch     -- PAP Auto Switch (printing)
    OBJECT IDENTIFIER ::= { xcmCOAppletalkPAP 41 }
    -- integerEnum (see 'xcmCODirectPrintProtocol' below)


xcmCOAppletalkPAPBinaryPS       -- PAP Binary PS (printing)
    OBJECT IDENTIFIER ::= { xcmCOAppletalkPAP 42 }
    -- integerTruthValue (true=enableBinaryPS, false=disableBinaryPS)
    -- (interpret all PostScript jobs as binary - ignore control chars)
    -- (PostScript per job submission protocol or 'xxxDefaultPDL' below)
xcmCOAppletalkPAPDefaultPDL     -- PAP Default PDL (printing)
    OBJECT IDENTIFIER ::= { xcmCOAppletalkPAP 43 }
    -- integerEnum ('XcmPrtInterpreterLangFamily' in XCMI Prt Ext TC)
    -- (fixed PDL if 'xxxAutoSwitch' is 'none' or 'other')
    -- (default PDL if 'xxxAutoSwitch' is 'autoSwitch')
    -- (ignored if 'xxxAutoSwitch' is 'ps...' or 'hp...')
    -- See: 'prtInterpreterLangFamily' in IETF Printer MIB (RFC 1759)
    -- See: 'prtChannelDefaultPageDescLangIndex' (default PDL via value
    --      of 'prtInterpreterIndex') in IETF Printer MIB (RFC 1759)

--
--          NetWare Protocol Suite
--

xcmCONetwareSuite
    OBJECT IDENTIFIER ::= { xcmCommsConfigTC 19 }
    -- integerTruthValue

xcmCONetwareDatalinks
    OBJECT IDENTIFIER ::= { xcmCONetwareSuite 1200 }
    -- integerTruthValue (w/ chain of 'xcmCOOsilan...')
    -- (obsoletes 'xcmCONetwareIPXDatalinks')

xcmCONetwareTransports
    OBJECT IDENTIFIER ::= { xcmCONetwareSuite 1400 }
    -- integerTruthValue
xcmCONetwareIPX                 -- IPX (CL network)
    OBJECT IDENTIFIER ::= { xcmCONetwareSuite 1301 }
    -- integerTruthValue
xcmCONetwareIP                -- IP Network Layer.
OBJECT IDENTIFIER  ::= {xcmCONetwareSuite 1302}
    -- integerTruthValue (true=Netware communicating via IP,
    -- false=Netware not communicating via IP)
xcmCONetwareSPX                 -- SPX (CO transport)
    OBJECT IDENTIFIER ::= { xcmCONetwareSuite 1402 }
    -- integerTruthValue
xcmCONetwareRIP                 -- RIP (routing)
    OBJECT IDENTIFIER ::= { xcmCONetwareSuite 1403 }
    -- integerTruthValue
xcmCONetwareEcho                -- Echo (echo)
    OBJECT IDENTIFIER ::= { xcmCONetwareSuite 1404 }
    -- integerTruthValue

xcmCONetwareIPXAddress          -- IPX Node Address
    OBJECT IDENTIFIER ::= { xcmCONetwareIPX 1 }
    -- stringLocalization (dotted hex format, 'network.node')
    -- ('network' [8 octets] - unique network ID, '0' means 'local net')
    -- ('node'    [12 octets] - ASCII hex of IEEE 802.x MAC address)
xcmCONetwareIPXSocketAddress    -- IPX Socket Address


    OBJECT IDENTIFIER ::= { xcmCONetwareIPXAddress 1 }
    -- stringLocalization (dotted hex format, 'network.node.socket')
    -- ('network' [8 octets] - unique network ID, '0' means 'local net')
    -- ('node'    [12 octets] - ASCII hex of IEEE 802.x MAC address)
    -- ('socket'  [4 octets] - ASCII hex of 2-octet NetWare socket)
xcmCONetwareIPXDatalinks        -- IPX Datalinks
    OBJECT IDENTIFIER ::= { xcmCONetwareIPX 12 }
    -- integerTruthValue (w/ chain of 'xcmCOOsilan...')
    -- (obsoleted by 'xcmCONetwareDatalinks')

xcmCONetwareApplications
    OBJECT IDENTIFIER ::= { xcmCONetwareSuite 1700 }
    -- integerTruthValue
xcmCONetwareNCP                 -- NCP (core protocols)
    OBJECT IDENTIFIER ::= { xcmCONetwareSuite 1501 }
    -- integerTruthValue
xcmCONetwareNetbios             -- NetBIOS Emulation
    OBJECT IDENTIFIER ::= { xcmCONetwareSuite 1502 }
    -- integerTruthValue
xcmCONetwarePServer             -- PServer (printing)
    OBJECT IDENTIFIER ::= { xcmCONetwareSuite 1503 }
    -- integerTruthValue
xcmCONetwareFServer             -- FServer (filing)
    OBJECT IDENTIFIER ::= { xcmCONetwareSuite 1504 }
    -- integerTruthValue
xcmCONetwareMHS                 -- MHS (email)
    OBJECT IDENTIFIER ::= { xcmCONetwareSuite 1505 }
    -- integerTruthValue
xcmCONetwareBindery             -- Bindery (directory)
    OBJECT IDENTIFIER ::= { xcmCONetwareSuite 1507 }
    -- integerTruthValue
xcmCONetwareNDS                 -- NDS (directory)
    OBJECT IDENTIFIER ::= { xcmCONetwareSuite 1508 }
    -- integerTruthValue
xcmCONetwareRPrinter            -- RPrinter (printing)
    OBJECT IDENTIFIER ::= { xcmCONetwareSuite 1509 }
    -- integerTruthValue

xcmCONetwareSNMP                -- SNMP (network mgmt)
    OBJECT IDENTIFIER ::= { xcmCONetwareSuite 1510 }
    -- integerTruthValue
xcmCONetwareSNMPv1              -- SNMPv1 (network mgmt)
    OBJECT IDENTIFIER ::= { xcmCONetwareSuite 1511 }
    -- integerTruthValue
xcmCONetwareSNMPv2              -- SNMPv2 (network mgmt)
    OBJECT IDENTIFIER ::= { xcmCONetwareSuite 1512 }
    -- integerTruthValue
xcmCONetwareSNMPv3              -- SNMPv3 (network mgmt)
    OBJECT IDENTIFIER ::= { xcmCONetwareSuite 1513 }
    -- integerTruthValue

xcmCONetwareSAP                 -- SAP (discovery)
    OBJECT IDENTIFIER ::= { xcmCONetwareSuite 1591 }
    -- integerTruthValue


xcmCONetwareNDSIP                 -- Netware over IP
    OBJECT IDENTIFIER ::= { xcmCONetwareSuite 1600 }
    -- integerTruthValue
    -- (true = enabled; false= disabled )

xcmCONetwareNDSIPHostname
    -- Novell server hostname used to find tree & context for filing
    OBJECT IDENTIFIER ::= { xcmCONetwareNDSIP 1 }
    -- stringLocalization

xcmCONetwareNDSIPAddress
    -- Novell server IP address used to find tree & context for filing
    OBJECT IDENTIFIER ::= { xcmCONetwareNDSIP 2 }
    -- stringLocalization (IPv4 - dotted decimal 'a.b.c.d')
    -- <or>
    -- stringLocalization (IPv6 - hex w/ colons '[x1:...:x8]')
    -- (IPv4 - decimal values [1-3 octets] of four 8-bit components)
    -- (eg, '13.226.19.10')
    -- (IPv6 - eight hex values [0-4 octets] of 16-bit components)

xcmCONetwareNDSIPUseHostname          -- to choose Hostname or IPAddress
    OBJECT IDENTIFIER ::= { xcmCONetwareNDSIP 3 }
    -- integerTruthValue
    -- (true = Hostname; false= IPAddress )

xcmCONetwarePServerName         -- PServer Name (printing)
    OBJECT IDENTIFIER ::= { xcmCONetwarePServer 1 }
    -- stringLocalization
    -- (compare with 'xcmCONetware[RPrinter|SAPUnit]Name')
xcmCONetwarePServerPassword     -- PServer Password (printing)
    OBJECT IDENTIFIER ::= { xcmCONetwarePServer 2 }
    -- stringLocalization (SHALL be encrypted)
xcmCONetwarePServerQueueName    -- PServer Queue Name (printing)
    OBJECT IDENTIFIER ::= { xcmCONetwarePServer 3 }
    -- stringLocalization
xcmCONetwarePServerPollInterval -- PServer Poll Interval (printing)
    OBJECT IDENTIFIER ::= { xcmCONetwarePServer 4 }
    -- integerNumber (seconds, 0=immediate or 1..n)
    -- (0=immediate - poll as frequently as application wishes)
    -- (1..n=interval in seconds - SHOULD NOT be less than 3 seconds)
    -- (max_int=poll once every 68 years - ie, disable polling)
xcmCONetwarePServerFindFServer  -- PServer Find FServer (printing)
    OBJECT IDENTIFIER ::= { xcmCONetwarePServer 5 }
    -- integerTruthValue (true=enableFind, false=disableFind)
xcmCONetwarePServerMaxFServers  -- PServer Max FServers (printing)
    OBJECT IDENTIFIER ::= { xcmCONetwarePServer 6 }
    -- integerNumber (1..n)
xcmCONetwarePServerNotify       -- PServer Notify (printing)
    OBJECT IDENTIFIER ::= { xcmCONetwarePServer 7 }
    -- integerTruthValue (true=enableNotify, false=disableNotify)
xcmCONetwarePServerNotifyLocale -- PServer Notify Locale (printing)
    OBJECT IDENTIFIER ::= { xcmCONetwarePServerNotify 1 }
    -- integerNumber (0=default, or 'xcmGenLocalizationIndex' of locale)


    -- (used to override 'xcmGenFixedLocalizationIndex' for this CPU)
xcmCONetwarePServerMaxPrinters  -- PServer Max Printers (printing)
    OBJECT IDENTIFIER ::= { xcmCONetwarePServer 8 }
    -- integerNumber (1=default or 1..n)
xcmCONetwarePServerSuspendPoll
-- Enable/Disable of a different job polling interval when
--   EnergyStarSuspend Mode is Enabled.
OBJECT IDENTIFIER ::= { xcmCONetwarePServer 9 }
-- integerTruthValue (true=enabled, false=disabled)
xcmCONetwarePServerSuspendPollInterval
-- Pserver Poll Interval when EnergyStarSuspend Mode AND
--   xcmCONetwarePServerSuspendPoll arexe Enabled. Ignore if
--   EnergyStarSuspend Mode OR xcmCONetwarePServerSuspendPoll
--   are Disabled.
OBJECT IDENTIFIER ::= { xcmCONetwarePServer 10 }
-- integerNumber

xcmCONetwarePServerSpool        -- PServer Spool (printing)
    OBJECT IDENTIFIER ::= { xcmCONetwarePServer 31 }
    -- integerEnum (1=none, 2=other, 3=disk, 4=ram)
xcmCONetwarePServerMaxSpool     -- PServer Max Spool (printing)
    OBJECT IDENTIFIER ::= { xcmCONetwarePServer 32 }
    -- integerNumber (spool area size in bytes, 0..n)
xcmCONetwarePServerJobTimeout   -- PServer Job Timeout (printing)
    OBJECT IDENTIFIER ::= { xcmCONetwarePServer 40 }
    -- integerNumber (seconds, 0=infinite or 1..n)
xcmCONetwarePServerAutoSwitch   -- PServer Auto Switch (printing)
    OBJECT IDENTIFIER ::= { xcmCONetwarePServer 41 }
    -- integerEnum (see 'xcmCODirectPrintProtocol' below)
xcmCONetwarePServerBinaryPS     -- PServer Binary PS (printing)
    OBJECT IDENTIFIER ::= { xcmCONetwarePServer 42 }
    -- integerTruthValue (true=enableBinaryPS, false=disableBinaryPS)
    -- (interpret all PostScript jobs as binary - ignore control chars)
    -- (PostScript per job submission protocol or 'xxxDefaultPDL' below)
xcmCONetwarePServerDefaultPDL   -- PServer Default PDL (printing)
    OBJECT IDENTIFIER ::= { xcmCONetwarePServer 43 }
    -- integerEnum ('XcmPrtInterpreterLangFamily' in XCMI Prt Ext TC)
    -- (fixed PDL if 'xxxAutoSwitch' is 'none' or 'other')
    -- (default PDL if 'xxxAutoSwitch' is 'autoSwitch')
    -- (ignored if 'xxxAutoSwitch' is 'ps...' or 'hp...')
    -- See: 'prtInterpreterLangFamily' in IETF Printer MIB (RFC 1759)
    -- See: 'prtChannelDefaultPageDescLangIndex' (default PDL via value
    --      of 'prtInterpreterIndex') in IETF Printer MIB (RFC 1759)
xcmCONetwarePServerConfigTimeout -- PServer Configuration Timeout
    OBJECT IDENTIFIER ::= { xcmCONetwarePServer 50 }
    -- integerNumber (seconds, 0=infinite or 1..n)
    -- The amount of timeout automatic Print Server configuration
    -- is allowed to run before timing out.

xcmCONetwareRPrinterName        -- RPrinter PServer Name (printing)
    OBJECT IDENTIFIER ::= { xcmCONetwareRPrinter 1 }
    -- stringLocalization
    -- (compare with 'xcmCONetware[PServer|SAPUnit]Name')
xcmCONetwareRPrinterNumber      -- RPrinter Printer Number (printing)


    OBJECT IDENTIFIER ::= { xcmCONetwareRPrinter 2 }
    -- integerNumber (1..n)
xcmCONetwareRPrinterPollInterval -- RPrinter Poll Interval (printing)
    OBJECT IDENTIFIER ::= { xcmCONetwareRPrinter 3 }
    -- integerNumber (seconds, 0=immediate or 1..n)
    -- (0=immediate - poll as frequently as application wishes)
    -- (1..n=interval in seconds - SHOULD NOT be less than 3 seconds)
    -- (max_int=poll once every 68 years - ie, disable polling)
xcmCONetwareRPrinterJobTimeout  -- RPrinter Job Timeout (printing)
    OBJECT IDENTIFIER ::= { xcmCONetwareRPrinter 40 }
    -- integerNumber (seconds, 0=infinite or 1..n)
xcmCONetwareRPrinterAutoSwitch  -- RPrinter Auto Switch (printing)
    OBJECT IDENTIFIER ::= { xcmCONetwareRPrinter 41 }
    -- integerEnum (see 'xcmCODirectPrintProtocol' below)
xcmCONetwareRPrinterBinaryPS    -- RPrinter Binary PS (printing)
    OBJECT IDENTIFIER ::= { xcmCONetwareRPrinter 42 }
    -- integerTruthValue (true=enableBinaryPS, false=disableBinaryPS)
    -- (interpret all PostScript jobs as binary - ignore control chars)
    -- (PostScript per job submission protocol or 'xxxDefaultPDL' below)
xcmCONetwareRPrinterDefaultPDL  -- RPrinter Default PDL (printing)
    OBJECT IDENTIFIER ::= { xcmCONetwareRPrinter 43 }
    -- integerEnum ('XcmPrtInterpreterLangFamily' in XCMI Prt Ext TC)
    -- (fixed PDL if 'xxxAutoSwitch' is 'none' or 'other')
    -- (default PDL if 'xxxAutoSwitch' is 'autoSwitch')
    -- (ignored if 'xxxAutoSwitch' is 'ps...' or 'hp...')
    -- See: 'prtInterpreterLangFamily' in IETF Printer MIB (RFC 1759)
    -- See: 'prtChannelDefaultPageDescLangIndex' (default PDL via value
    --      of 'prtInterpreterIndex') in IETF Printer MIB (RFC 1759)

xcmCONetwareFServerName         -- FServer Name (filing)
    OBJECT IDENTIFIER ::= { xcmCONetwareFServer 1 }
    -- stringLocalization
xcmCONetwareFServerPassword     -- FServer Password (filing)
    OBJECT IDENTIFIER ::= { xcmCONetwareFServer 2 }
    -- stringLocalization (SHALL be encrypted)
xcmCONetwareFServerAddress      -- FServer Address (filing)
    OBJECT IDENTIFIER ::= { xcmCONetwareFServer 3 }
    -- stringLocalization (dotted hex format, 'network.node')

xcmCONetwareBinderyLanguage     -- Bindery Language (directory)
    OBJECT IDENTIFIER ::= { xcmCONetwareBindery 3 }
    -- stringLocalization (language tag, per RFC 2277)
    -- (default is unknown language, per RFC 2277)
xcmCONetwareBinderyCharset      -- Bindery Charset (directory)
    OBJECT IDENTIFIER ::= { xcmCONetwareBindery 4 }
    -- integerEnum (see 'CodedCharSet' in IETF Printer MIB)
    -- (default '106' UTF-8, per NetWare Bindery, RFC 2277, RFC 2279)

xcmCONetwareNDSTreeName         -- NDS Tree Name (directory)
    OBJECT IDENTIFIER ::= { xcmCONetwareNDS 1 }
    -- stringLocalization
xcmCONetwareNDSContext          -- NDS Context (directory)
    OBJECT IDENTIFIER ::= { xcmCONetwareNDS 2 }
    -- stringLocalization


xcmCONetwareNDSLanguage         -- NDS Language (directory)
    OBJECT IDENTIFIER ::= { xcmCONetwareNDS 3 }
    -- stringLocalization (language tag, per RFC 2277)
    -- (default is unknown language, per RFC 2277)
xcmCONetwareNDSCharset          -- NDS Charset (directory)
    OBJECT IDENTIFIER ::= { xcmCONetwareNDS 4 }
    -- integerEnum (see 'CodedCharSet' in IETF Printer MIB)
    -- (default '106' UTF-8, per NetWare NDS, RFC 2277, RFC 2279)

xcmCONetwareSAPInterval         -- SAP Interval (discovery)
    OBJECT IDENTIFIER ::= { xcmCONetwareSAP 1 }
    -- integerNumber (seconds, 0=none, or 1..n)
xcmCONetwareSAPNumber           -- SAP Number (discovery)
    OBJECT IDENTIFIER ::= { xcmCONetwareSAP 2 }
    -- integerNumber (CAUTION - Novell assigned - 0=none, or 1..n)
    -- (used with any format, including legacy ones)
xcmCONetwareSAPValueString      -- SAP Value String (discovery)
    OBJECT IDENTIFIER ::= { xcmCONetwareSAP 3 }
    -- stringLocalization
    -- (used with any format, including legacy ones)
xcmCONetwareSAPUnitName         -- SAP Unit Name (discovery)
    OBJECT IDENTIFIER ::= { xcmCONetwareSAP 4 }
    -- stringLocalization
    -- (used with any format, including legacy ones)
    -- (compare with 'xcmCONetware[PServer|RPrinter]Name')
xcmCONetwareSAPFormatID         -- SAP Format ID (discovery)
    OBJECT IDENTIFIER ::= { xcmCONetwareSAP 5 }
    -- stringLocalization
    -- (used ONLY with XC and FX XCMI/FXCMI standard formats)
xcmCONetwareSAPSuspend
-- Enable/Disable of a different SAP interval when
-- EnergyStarSuspend Mode is Enabled.
OBJECT IDENTIFIER ::= { xcmCONetwareSAP 6 }
-- integerTruthValue (true=enabled, false=disabled)
xcmCONetwareSAPSuspendInterval
-- SAP Interval when EnergyStarSuspend Mode AND xcmCONetwareSAPSuspend
-- are Enabled. Ignore if EnergyStarSuspend Mode OR
-- xcmCONetwareSAPSuspend are Disabled.
OBJECT IDENTIFIER ::= { xcmCONetwareSAP 7 }
-- integerNumber

--
--          Vines Protocol Suite
--

xcmCOVinesSuite
    OBJECT IDENTIFIER ::= { xcmCommsConfigTC 20 }
    -- integerTruthValue

xcmCOVinesDatalinks
    OBJECT IDENTIFIER ::= { xcmCOVinesSuite 1200 }
    -- integerTruthValue (w/ chain of 'xcmCOOsilan...')

xcmCOVinesTransports


    OBJECT IDENTIFIER ::= { xcmCOVinesSuite 1400 }
    -- integerTruthValue
xcmCOVinesVIP                   -- VIP (CL network)
    OBJECT IDENTIFIER ::= { xcmCOVinesSuite 1301 }
    -- integerTruthValue
xcmCOVinesVICP                  -- VICP (layer management - network)
    OBJECT IDENTIFIER ::= { xcmCOVinesSuite 1302 }
    -- integerTruthValue
xcmCOVinesVARP                  -- VARP (routing)
    OBJECT IDENTIFIER ::= { xcmCOVinesSuite 1303 }
    -- integerTruthValue
xcmCOVinesIP                    -- IP (CL network)
    OBJECT IDENTIFIER ::= { xcmCOVinesSuite 1311 }
    -- integerTruthValue
xcmCOVinesICMP                  -- ICMP (layer management - network)
    OBJECT IDENTIFIER ::= { xcmCOVinesSuite 1312 }
    -- integerTruthValue
xcmCOVinesARP                   -- ARP (routing)
    OBJECT IDENTIFIER ::= { xcmCOVinesSuite 1313 }
    -- integerTruthValue
xcmCOVinesVRTP                  -- VRTP (routing)
    OBJECT IDENTIFIER ::= { xcmCOVinesSuite 1314 }
    -- integerTruthValue
xcmCOVinesVIPC                  -- VIPC (CL transport)
    OBJECT IDENTIFIER ::= { xcmCOVinesSuite 1401 }
    -- integerTruthValue
xcmCOVinesVSPP                  -- VSPP (CO transport)
    OBJECT IDENTIFIER ::= { xcmCOVinesSuite 1402 }
    -- integerTruthValue
xcmCOVinesUDP                   -- UDP (CL transport)
    OBJECT IDENTIFIER ::= { xcmCOVinesSuite 1411 }
    -- integerTruthValue
xcmCOVinesTCP                   -- TCP (CO transport)
    OBJECT IDENTIFIER ::= { xcmCOVinesSuite 1412 }
    -- integerTruthValue

xcmCOVinesApplications
    OBJECT IDENTIFIER ::= { xcmCOVinesSuite 1700 }
    -- integerTruthValue
xcmCOVinesNetRPC                -- NetRPC (transactions)
    OBJECT IDENTIFIER ::= { xcmCOVinesSuite 1501 }
    -- integerTruthValue
xcmCOVinesSocket                -- Socket (CL/CO session)
    OBJECT IDENTIFIER ::= { xcmCOVinesSuite 1502 }
    -- integerTruthValue
xcmCOVinesNetbios               -- NetBIOS (emulation)
    OBJECT IDENTIFIER ::= { xcmCOVinesSuite 1503 }
    -- integerTruthValue
xcmCOVinesPrint                 -- Print (printing)
    OBJECT IDENTIFIER ::= { xcmCOVinesSuite 1701 }
    -- integerTruthValue
xcmCOVinesFiling                -- Filing (filing)
    OBJECT IDENTIFIER ::= { xcmCOVinesSuite 1702 }
    -- integerTruthValue


xcmCOVinesMail                  -- Mail (email)
    OBJECT IDENTIFIER ::= { xcmCOVinesSuite 1703 }
    -- integerTruthValue
xcmCOVinesStreetTalk            -- StreetTalk (directory)
    OBJECT IDENTIFIER ::= { xcmCOVinesSuite 1704 }
    -- integerTruthValue

xcmCOVinesPrintName             -- Print Name to Server (printing)
    OBJECT IDENTIFIER ::= { xcmCOVinesPrint 1 }
    -- stringLocalization
xcmCOVinesPrintPassword         -- Print Password to Server (printing)
    OBJECT IDENTIFIER ::= { xcmCOVinesPrint 2 }
    -- stringLocalization (SHALL be encrypted)
xcmCOVinesPrintPollInterval     -- Print Poll Interval (printing)
    OBJECT IDENTIFIER ::= { xcmCOVinesPrint 4 }
    -- integerNumber (seconds, 0=immediate or 1..n)
    -- (0=immediate - poll as frequently as application wishes)
    -- (1..n=interval in seconds - SHOULD NOT be less than 3 seconds)
    -- (max_int=poll once every 68 years - ie, disable polling)
xcmCOVinesPrintMaxServers       -- Print Max Servers (printing)
    OBJECT IDENTIFIER ::= { xcmCOVinesPrint 5 }
    -- integerNumber (0=infinite, or 1..n)
xcmCOVinesPrintServerName       -- Print Server Name (printing)
    OBJECT IDENTIFIER ::= { xcmCOVinesPrint 6 }
    -- stringLocalization
xcmCOVinesPrintSpool            -- Print Spool (printing)
    OBJECT IDENTIFIER ::= { xcmCOVinesPrint 31 }
    -- integerEnum (1=none, 2=other, 3=disk, 4=ram)
xcmCOVinesPrintMaxSpool         -- Print Max Spool (printing)
    OBJECT IDENTIFIER ::= { xcmCOVinesPrint 32 }
    -- integerNumber (spool area size in bytes, 0..n)
xcmCOVinesPrintJobTimeout       -- Print Job Timeout (printing)
    OBJECT IDENTIFIER ::= { xcmCOVinesPrint 40 }
    -- integerNumber (seconds, 0=infinite or 1..n)
xcmCOVinesPrintAutoSwitch       -- Print Auto Switch (printing)
    OBJECT IDENTIFIER ::= { xcmCOVinesPrint 41 }
    -- integerEnum (see 'xcmCODirectPrintProtocol' below)
xcmCOVinesPrintBinaryPS         -- Print Binary PS (printing)
    OBJECT IDENTIFIER ::= { xcmCOVinesPrint 42 }
    -- integerTruthValue (true=enableBinaryPS, false=disableBinaryPS)
    -- (interpret all PostScript jobs as binary - ignore control chars)
    -- (PostScript per job submission protocol or 'xxxDefaultPDL' below)
xcmCOVinesPrintDefaultPDL       -- Print Default PDL (printing)
    OBJECT IDENTIFIER ::= { xcmCOVinesPrint 43 }
    -- integerEnum ('XcmPrtInterpreterLangFamily' in XCMI Prt Ext TC)
    -- (fixed PDL if 'xxxAutoSwitch' is 'none' or 'other')
    -- (default PDL if 'xxxAutoSwitch' is 'autoSwitch')
    -- (ignored if 'xxxAutoSwitch' is 'ps...' or 'hp...')
    -- See: 'prtInterpreterLangFamily' in IETF Printer MIB (RFC 1759)
    -- See: 'prtChannelDefaultPageDescLangIndex' (default PDL via value
    --      of 'prtInterpreterIndex') in IETF Printer MIB (RFC 1759)

xcmCOVinesStreetTalkLanguage    -- StreetTalk Language (directory)
    OBJECT IDENTIFIER ::= { xcmCOVinesStreetTalk 3 }


    -- stringLocalization (language tag, per RFC 2277)
    -- (default is unknown language, per RFC 2277)
xcmCOVinesStreetTalkCharset     -- StreetTalk Charset (directory)
    OBJECT IDENTIFIER ::= { xcmCOVinesStreetTalk 4 }
    -- integerEnum (see 'CodedCharSet' in IETF Printer MIB)
    -- (default '106' UTF-8, per Vines StreetTalk, RFC 2277, RFC 2279)

--
--          NetBIOS Protocol Suite
--

xcmCONetbiosSuite
    OBJECT IDENTIFIER ::= { xcmCommsConfigTC 25 }
    -- integerTruthValue

xcmCONetbiosDatalinks
    OBJECT IDENTIFIER ::= { xcmCONetbiosSuite 1200 }
    -- integerTruthValue (w/ chain of 'xcmCOOsilan...')

xcmCONetbiosTransports
    OBJECT IDENTIFIER ::= { xcmCONetbiosSuite 1400 }
    -- integerTruthValue

xcmCONetbiosNBP                 -- NBP (NetBIOS Protocol)
    OBJECT IDENTIFIER ::= { xcmCONetbiosSuite 1501 }
    -- integerTruthValue

xcmCONetbiosSNMP                -- SNMP (network mgmt)
    OBJECT IDENTIFIER ::= { xcmCONetbiosSuite 1510 }
    -- integerTruthValue
xcmCONetbiosSNMPv1              -- SNMPv1 (network mgmt)
    OBJECT IDENTIFIER ::= { xcmCONetbiosSuite 1511 }
    -- integerTruthValue
xcmCONetbiosSNMPv2              -- SNMPv2 (network mgmt)
    OBJECT IDENTIFIER ::= { xcmCONetbiosSuite 1512 }
    -- integerTruthValue
xcmCONetbiosSNMPv3              -- SNMPv3 (network mgmt)
    OBJECT IDENTIFIER ::= { xcmCONetbiosSuite 1513 }
    -- integerTruthValue

xcmCONetbiosIntEndNode           -- NetBIOS over TCP End Node
    OBJECT IDENTIFIER ::= { xcmCONetbiosSuite 1520 }
    -- integerTruthValue
    -- See: RFC 1001/1002 (NetBIOS over TCP) and RFC 2132 (DHCP Options)
xcmCONetbiosIntNameServer        -- NetBIOS over TCP Name Server
    OBJECT IDENTIFIER ::= { xcmCONetbiosSuite 1521 }
    -- integerTruthValue
    -- See: RFC 1001/1002 (NetBIOS over TCP) and RFC 2132 (DHCP Options)
xcmCONetbiosIntDistServer        -- NetBIOS over TCP Dist Server
    OBJECT IDENTIFIER ::= { xcmCONetbiosSuite 1522 }
    -- integerTruthValue
    -- See: RFC 1001/1002 (NetBIOS over TCP) and RFC 2132 (DHCP Options)


xcmCONetbiosSAP                 -- SAP (discovery)
    OBJECT IDENTIFIER ::= { xcmCONetbiosSuite 1591 }
    -- integerTruthValue

xcmCONetbiosApplications
    OBJECT IDENTIFIER ::= { xcmCONetbiosSuite 1700 }
    -- integerTruthValue
xcmCONetbiosSMB                 -- SMB (Server Message Block)
    OBJECT IDENTIFIER ::= { xcmCONetbiosSuite 1701 }
    -- integerTruthValue
xcmCONetbiosSMBPClient          -- SMB Printing Client
    OBJECT IDENTIFIER ::= { xcmCONetbiosSuite 1702 }
    -- integerTruthValue
xcmCONetbiosSMBPServer          -- SMB Printing Server
    OBJECT IDENTIFIER ::= { xcmCONetbiosSuite 1703 }
    -- integerTruthValue
xcmCONetbiosSMBFClient          -- SMB Filing Client
    OBJECT IDENTIFIER ::= { xcmCONetbiosSuite 1704 }
    -- integerTruthValue
xcmCONetbiosSMBFServer          -- SMB Filing Server
    OBJECT IDENTIFIER ::= { xcmCONetbiosSuite 1705 }
    -- integerTruthValue
xcmCONetbiosSMBDomain          -- SMB Domain
    OBJECT IDENTIFIER ::= { xcmCONetbiosSuite 1706 }

xcmCONetbiosNBPName             -- NBP Name (directory)
    OBJECT IDENTIFIER ::= { xcmCONetbiosNBP 1 }
    -- often used for 'SMB Host Name' value
    -- stringLocalization (hostname)
xcmCONetbiosNBPGroupName        -- NBP Group Name (directory)
    OBJECT IDENTIFIER ::= { xcmCONetbiosNBP 2 }
    -- often used for 'Workgroup' value
    -- stringLocalization (groupname)
xcmCONetbiosNBPPassword         -- NBP Password (directory)
    OBJECT IDENTIFIER ::= { xcmCONetbiosNBP 3 }
    -- stringLocalization (SHALL be encrypted)
xcmCONetbiosNBPService          -- NBP Service (directory)
    OBJECT IDENTIFIER ::= { xcmCONetbiosNBP 4 }
    -- often used for 'Share Name' value
    -- stringLocalization (servicename)
xcmCONetbiosNBPRemark           -- NBP Node Remark (directory)
    OBJECT IDENTIFIER ::= { xcmCONetbiosNBP 5 }
    -- often used for 'SMB Host Name Comment' value
    -- stringLocalization (hostname comment)
xcmCONetbiosNBPServiceRemark    -- NBP Service Remark (directory)
    OBJECT IDENTIFIER ::= { xcmCONetbiosNBP 6 }
    -- often used for 'Share Name Comment' value
    -- stringLocalization (sharename comment)
xcmCONetbiosNBPIPCRemark        -- NBP IPC Remark (directory)
    OBJECT IDENTIFIER ::= { xcmCONetbiosNBP 7 }
    -- stringLocalization (IPC$ comment - transport, address, type)
xcmCONetbiosNBPLanguage         -- NetBIOS Language (directory)
    OBJECT IDENTIFIER ::= { xcmCONetbiosNBP 8 }


    -- stringLocalization (language tag, per RFC 2277)
    -- (default is unknown language, per RFC 2277)
xcmCONetbiosNBPCharset          -- NetBIOS Charset (directory)
    OBJECT IDENTIFIER ::= { xcmCONetbiosNBP 9 }
    -- integerEnum (see 'CodedCharSet' in IETF Printer MIB)
    -- (default '106' UTF-8, per RFC 2277, RFC 2279)
xcmCONetbiosNBPOverNetbeui      -- NetBIOS over NetBEUI (native)
    OBJECT IDENTIFIER ::= { xcmCONetbiosNBP 11 }
    -- integerTruthValue
xcmCONetbiosNBPOverInternet     -- NetBIOS over TCP (RFC 1001/1002)
    OBJECT IDENTIFIER ::= { xcmCONetbiosNBP 12 }
    -- integerTruthValue
xcmCONetbiosNBPOverNetware      -- NetBIOS over IPX (Netware)
    OBJECT IDENTIFIER ::= { xcmCONetbiosNBP 13 }
    -- integerTruthValue

xcmCONetbiosIntEndNodeAddress    -- NetBIOS over TCP End Node Address
    OBJECT IDENTIFIER ::= { xcmCONetbiosIntEndNode 1 }
    -- stringLocalization (dotted decimal format, 'a.b.c.d')
    -- ('a' to 'd' [1-3 octets] - ASCII decimal of 1-octet components)
    -- See: RFC 1001/1002 (NetBIOS over TCP) and RFC 2132 (DHCP Options)
xcmCONetbiosIntEndNodeSource     -- NetBIOS over TCP End Node Source
    OBJECT IDENTIFIER ::= { xcmCONetbiosIntEndNode 2 }
    -- integerEnum (1=none, 2=other,
    -- 3=static, 4=reserved, 5=viaBOOTP, 6=viaDHCP)

xcmCONetbiosIntNodeType         -- NetBIOS over TCP Node Type
    OBJECT IDENTIFIER ::= { xcmCONetbiosIntEndNode 3 }
    -- integerEnum (1=none, 2=other,
    -- 3=broadcast, 4=pointToPoint, 5=mixedMode)
    -- See: RFC 1001/1002 (NetBIOS over TCP) and RFC 2132 (DHCP Options)
xcmCONetbiosIntNodeTypeSource   -- NetBIOS over TCP Node Type Source
    OBJECT IDENTIFIER ::= { xcmCONetbiosIntEndNode 4 }
    -- integerEnum (1=none, 2=other,
    -- 3=static, 4=reserved, 5=viaBOOTP, 6=viaDHCP)

xcmCONetbiosIntNodeScope         -- NetBIOS over TCP Node Scope
    OBJECT IDENTIFIER ::= { xcmCONetbiosIntEndNode 5 }
    -- stringLocalization (must be valid DNS name)
    -- See: RFC 1001/1002 (NetBIOS over TCP) and RFC 2132 (DHCP Options)
xcmCONetbiosIntNodeScopeSource   -- NetBIOS over TCP Node Scope Source
    OBJECT IDENTIFIER ::= { xcmCONetbiosIntEndNode 6 }
    -- integerEnum (1=none, 2=other,
    -- 3=static, 4=reserved, 5=viaBOOTP, 6=viaDHCP)

xcmCONetbiosIntNameServerAddress -- NetBIOS over TCP Name Server Address
    OBJECT IDENTIFIER ::= { xcmCONetbiosIntNameServer 1 }
    -- stringLocalization (dotted decimal format, 'a.b.c.d')
    -- ('a' to 'd' [1-3 octets] - ASCII decimal of 1-octet components)
    -- See: RFC 1001/1002 (NetBIOS over TCP) and RFC 2132 (DHCP Options)
xcmCONetbiosIntNameServerSource  -- NetBIOS over TCP Name Server Source
    OBJECT IDENTIFIER ::= { xcmCONetbiosIntNameServer 2 }
    -- integerEnum (1=none, 2=other,
    -- 3=static, 4=reserved, 5=viaBOOTP, 6=viaDHCP)


xcmCONetbiosIntDistServerAddress -- NetBIOS over TCP Dist Server Address
    OBJECT IDENTIFIER ::= { xcmCONetbiosIntDistServer 1 }
    -- stringLocalization (dotted decimal format, 'a.b.c.d')
    -- ('a' to 'd' [1-3 octets] - ASCII decimal of 1-octet components)
    -- See: RFC 1001/1002 (NetBIOS over TCP) and RFC 2132 (DHCP Options)
xcmCONetbiosIntDistServerSource  -- NetBIOS over TCP Dist Server Source
    OBJECT IDENTIFIER ::= { xcmCONetbiosIntDistServer 2 }
    -- integerEnum (1=none, 2=other,
    -- 3=static, 4=reserved, 5=viaBOOTP, 6=viaDHCP)

xcmCONetbiosSAPInterval         -- SAP Interval (discovery)
    OBJECT IDENTIFIER ::= { xcmCONetbiosSAP 1 }
    -- integerNumber (seconds, 0=none, or 1..n)

xcmCONetbiosSMBPClientMaxConns  -- Print Client Max Conns (concurrently)
    OBJECT IDENTIFIER ::= { xcmCONetbiosSMBPClient 4 }
    -- integerNumber (0..n)
xcmCONetbiosSMBPClientSpool     -- Print Client Spool (printing)
    OBJECT IDENTIFIER ::= { xcmCONetbiosSMBPClient 31 }
    -- integerEnum (1=none, 2=other, 3=disk, 4=ram)
xcmCONetbiosSMBPClientMaxSpool  -- Print Client Max Spool (printing)
    OBJECT IDENTIFIER ::= { xcmCONetbiosSMBPClient 32 }
    -- integerNumber (spool area size in bytes, 0..n)
xcmCONetbiosSMBPClientJobTimeout -- Print Client Job Timeout (printing)
    OBJECT IDENTIFIER ::= { xcmCONetbiosSMBPClient 40 }
    -- integerNumber (seconds, 0=infinite or 1..n)
xcmCONetbiosSMBPClientAutoSwitch -- Print Client Auto Switch (printing)
    OBJECT IDENTIFIER ::= { xcmCONetbiosSMBPClient 41 }
    -- integerEnum (see 'xcmCODirectPrintProtocol' below)
xcmCONetbiosSMBPClientBinaryPS   -- Print Client Binary PS (printing)
    OBJECT IDENTIFIER ::= { xcmCONetbiosSMBPClient 42 }
    -- integerTruthValue (true=enableBinaryPS, false=disableBinaryPS)
    -- (interpret all PostScript jobs as binary - ignore control chars)
    -- (PostScript per job submission protocol or 'xxxDefaultPDL' below)
xcmCONetbiosSMBPClientDefaultPDL -- Print Client Default PDL (printing)
    OBJECT IDENTIFIER ::= { xcmCONetbiosSMBPClient 43 }
    -- integerEnum ('XcmPrtInterpreterLangFamily' in XCMI Prt Ext TC)
    -- (fixed PDL if 'xxxAutoSwitch' is 'none' or 'other')
    -- (default PDL if 'xxxAutoSwitch' is 'autoSwitch')
    -- (ignored if 'xxxAutoSwitch' is 'ps...' or 'hp...')
    -- See: 'prtInterpreterLangFamily' in IETF Printer MIB (RFC 1759)
    -- See: 'prtChannelDefaultPageDescLangIndex' (default PDL via value
    --      of 'prtInterpreterIndex') in IETF Printer MIB (RFC 1759)

xcmCONetbiosSMBPServerMaxConns  -- Print Server Max Conns (concurrently)
    OBJECT IDENTIFIER ::= { xcmCONetbiosSMBPServer 4 }
    -- integerNumber (0..n)
xcmCONetbiosSMBPServerSpool     -- Print Server Spool (printing)
    OBJECT IDENTIFIER ::= { xcmCONetbiosSMBPServer 31 }
    -- integerEnum (1=none, 2=other, 3=disk, 4=ram)
xcmCONetbiosSMBPServerMaxSpool  -- Print Server Max Spool (printing)
    OBJECT IDENTIFIER ::= { xcmCONetbiosSMBPServer 32 }
    -- integerNumber (spool area size in bytes, 0..n)


xcmCONetbiosSMBPServerJobTimeout -- Print Server Job Timeout (printing)
    OBJECT IDENTIFIER ::= { xcmCONetbiosSMBPServer 40 }
    -- integerNumber (seconds, 0=infinite or 1..n)
xcmCONetbiosSMBPServerAutoSwitch -- Print Server Auto Switch (printing)
    OBJECT IDENTIFIER ::= { xcmCONetbiosSMBPServer 41 }
    -- integerEnum (see 'xcmCODirectPrintProtocol' below)
xcmCONetbiosSMBPServerBinaryPS   -- Print Server Binary PS (printing)
    OBJECT IDENTIFIER ::= { xcmCONetbiosSMBPServer 42 }
    -- integerTruthValue (true=enableBinaryPS, false=disableBinaryPS)
    -- (interpret all PostScript jobs as binary - ignore control chars)
    -- (PostScript per job submission protocol or 'xxxDefaultPDL' below)
xcmCONetbiosSMBPServerDefaultPDL -- Print Server Default PDL (printing)
    OBJECT IDENTIFIER ::= { xcmCONetbiosSMBPServer 43 }
    -- integerEnum ('XcmPrtInterpreterLangFamily' in XCMI Prt Ext TC)
    -- (fixed PDL if 'xxxAutoSwitch' is 'none' or 'other')
    -- (default PDL if 'xxxAutoSwitch' is 'autoSwitch')
    -- (ignored if 'xxxAutoSwitch' is 'ps...' or 'hp...')
    -- See: 'prtInterpreterLangFamily' in IETF Printer MIB (RFC 1759)
    -- See: 'prtChannelDefaultPageDescLangIndex' (default PDL via value
    --      of 'prtInterpreterIndex') in IETF Printer MIB (RFC 1759)

xcmCONetbiosSMBFServerName      -- SMB Filing Server Name
    OBJECT IDENTIFIER ::= { xcmCONetbiosSMBFServer 1 }
    -- stringLocalization

--
--          NetBEUI Protocol Suite
--

xcmCONetbeuiSuite
    OBJECT IDENTIFIER ::= { xcmCommsConfigTC 26 }
    -- integerTruthValue

xcmCONetbeuiDatalinks
    OBJECT IDENTIFIER ::= { xcmCONetbeuiSuite 1200 }
    -- integerTruthValue (w/ chain of 'xcmCOOsilan...')
xcmCONetbeuiLLC                 -- NetBEUI LLC (ISO/IEEE 802.2)
    OBJECT IDENTIFIER ::= { xcmCONetbeuiSuite 1201 }
    -- integerTruthValue
xcmCONetbeuiDLC                 -- NetBEUI DLC (IBM SNA DLC)
    OBJECT IDENTIFIER ::= { xcmCONetbeuiSuite 1202 }
    -- integerTruthValue

--
--          Serial Protocol Suite
--

xcmCOSerialSuite
    OBJECT IDENTIFIER ::= { xcmCommsConfigTC 27 }
    -- integerTruthValue

xcmCOSerialPhysical
    OBJECT IDENTIFIER ::= { xcmCOSerialSuite 1100 }
    -- integerTruthValue


xcmCOSerialSignalType
    OBJECT IDENTIFIER ::= { xcmCOSerialSuite 1101 }
    -- integerEnum (1=none, 2=other, 3=rs232, 4=rs422, 5=v35)
xcmCOSerialSignalOverride       -- Serial Signal Type Override
    OBJECT IDENTIFIER ::= { xcmCOSerialSignalType 1 }
    -- integerEnum (see 'xcmCOSerialSignalType' above)
xcmCOSerialSignalDetected       -- Serial Signal Type Detected
    OBJECT IDENTIFIER ::= { xcmCOSerialSignalType 2 }
    -- integerEnum (see 'xcmCOSerialSignalType' above)
xcmCOSerialSignalAdaptive       -- Serial Signal Type Adaptive
    OBJECT IDENTIFIER ::= { xcmCOSerialSignalType 3 }
    -- integerTruthValue
xcmCOSerialSignalSupport        -- OSI LAN Signal Type Support
    OBJECT IDENTIFIER ::= { xcmCOSerialSignalType 4 }
    -- integerEnum (list of 'xcmCOSerialSignalType' above)
xcmCOSerialDevice
    OBJECT IDENTIFIER ::= { xcmCOSerialSuite 1102 }
    -- integerNumber ('hrDeviceIndex' in IETF HR MIB, or 0=unknown)
xcmCOSerialDeviceName
    OBJECT IDENTIFIER ::= { xcmCOSerialDevice 1 }
    -- stringLocalization ('xcmHrDevInfoName' in HRX, eg, '/dev/com1')
xcmCOSerialSpeed
    OBJECT IDENTIFIER ::= { xcmCOSerialSuite 1103 }
    -- integerNumber (as in 'ifSpeed' in IETF MIB-II)
xcmCOSerialSpeedOverride
    OBJECT IDENTIFIER ::= { xcmCOSerialSpeed 1 }
    -- integerNumber (see 'xcmCOSerialSpeed' above)
xcmCOSerialSpeedDetected
    OBJECT IDENTIFIER ::= { xcmCOSerialSpeed 2 }
    -- integerNumber (see 'xcmCOSerialSpeed' above)
xcmCOSerialSpeedAdaptive
    OBJECT IDENTIFIER ::= { xcmCOSerialSpeed 3 }
    -- integerTruthValue
xcmCOSerialSpeedSupport
    OBJECT IDENTIFIER ::= { xcmCOSerialSpeed 4 }
    -- integerNumber (as in 'ifSpeed' in IETF MIB-II, list of speeds)
xcmCOSerialMinSpeed
    OBJECT IDENTIFIER ::= { xcmCOSerialSpeed 5 }
    -- integerNumber (as in 'ifSpeed' in IETF MIB-II)
xcmCOSerialMaxSpeed
    OBJECT IDENTIFIER ::= { xcmCOSerialSpeed 6 }
    -- integerNumber (as in 'ifSpeed' in IETF MIB-II)
xcmCOSerialBidirectional
    OBJECT IDENTIFIER ::= { xcmCOSerialSuite 1104 }
    -- integerTruthValue
xcmCOSerialInputTimeout         -- POSIX.1 'VTIME' * 10 (in 'termios.h')
    OBJECT IDENTIFIER ::= { xcmCOSerialSuite 1105 }
    -- integerNumber (seconds, 0=infinite or 1..n)
xcmCOSerialOutputTimeout
    OBJECT IDENTIFIER ::= { xcmCOSerialSuite 1106 }
    -- integerNumber (seconds, 0=infinite or 1..n)
xcmCOSerialConnectorType
    OBJECT IDENTIFIER ::= { xcmCOSerialSuite 1107 }
    -- integerEnum (1=none, 2=other, 3=db9, 4=db25, 5=v35, 6=rj11)


xcmCOSerialConnectorOverride    -- Serial Connector Type Override
    OBJECT IDENTIFIER ::= { xcmCOSerialConnectorType 1 }
    -- integerEnum (see 'xcmCOSerialConnectorType' above)
xcmCOSerialConnectorDetected    -- Serial Connector Type Detected
    OBJECT IDENTIFIER ::= { xcmCOSerialConnectorType 2 }
    -- integerEnum (see 'xcmCOSerialConnectorType' above)
xcmCOSerialConnectorAdaptive    -- Serial Connector Type Adaptive
    OBJECT IDENTIFIER ::= { xcmCOSerialConnectorType 3 }
    -- integerTruthValue
xcmCOSerialMinInputChars        -- POSIX.1 'VMIN' (in 'termios.h')
    OBJECT IDENTIFIER ::= { xcmCOSerialSuite 1108 }
    -- integerNumber (0=infinite or 1..n)
xcmCOSerialMaxInputChars        -- POSIX.1 'nbyte' (in 'read()')
    OBJECT IDENTIFIER ::= { xcmCOSerialSuite 1109 }
    -- integerNumber (0=infinite or 1..n)
xcmCOSerialParity
    OBJECT IDENTIFIER ::= { xcmCOSerialSuite 1111 }
    -- integerEnum (1=none, 2=odd, 3=even, 4=mark, 5=space)
xcmCOSerialDataBits
    OBJECT IDENTIFIER ::= { xcmCOSerialSuite 1112 }
    -- integerNumber (0=default or 5..8)
xcmCOSerialFlowControl
    OBJECT IDENTIFIER ::= { xcmCOSerialSuite 1113 }
    -- integerEnum (1=none, 2=xonXoff, 3=rtsCts, 4=dtrDsr,
    -- 5=robustXonXoff)
xcmCOSerialStartBits
    OBJECT IDENTIFIER ::= { xcmCOSerialSuite 1114 }
    -- integerEnum (0=default or 1=1 bit, 2=1.5 bits)
xcmCOSerialStopBits
    OBJECT IDENTIFIER ::= { xcmCOSerialSuite 1115 }
    -- integerEnum (0=default or 1=1 bit, 2=2 bits, 3=1.5 bits)
xcmCOSerialInputPrime
    OBJECT IDENTIFIER ::= { xcmCOSerialSuite 1116 }
    -- integerTruthValue
xcmCOSerialDTR                  -- Data Terminal Ready
    OBJECT IDENTIFIER ::= { xcmCOSerialSuite 1121 }
    -- integerEnum (1=fixedHigh, 2=fixedLow, 3=activeHigh, 4=activeLow)
xcmCOSerialDSR                  -- Data Set Ready
    OBJECT IDENTIFIER ::= { xcmCOSerialSuite 1122 }
    -- integerEnum (1=fixedHigh, 2=fixedLow, 3=activeHigh, 4=activeLow)
xcmCOSerialCTS                  -- Clear To Send
    OBJECT IDENTIFIER ::= { xcmCOSerialSuite 1123 }
    -- integerEnum (1=fixedHigh, 2=fixedLow, 3=activeHigh, 4=activeLow)
xcmCOSerialRTS                  -- Request To Send
    OBJECT IDENTIFIER ::= { xcmCOSerialSuite 1124 }
    -- integerEnum (1=fixedHigh, 2=fixedLow, 3=activeHigh, 4=activeLow)

xcmCOSerialDatalinks
    OBJECT IDENTIFIER ::= { xcmCOSerialSuite 1200 }
    -- integerTruthValue

xcmCOSerialProtocol
    OBJECT IDENTIFIER ::= { xcmCOSerialDatalinks 1 }
    -- integerEnum (see 'xcmCODirectPrintProtocol' below)


--
--          Parallel Protocol Suite
--

xcmCOParallelSuite
    OBJECT IDENTIFIER ::= { xcmCommsConfigTC 28 }
    -- integerTruthValue

xcmCOParallelPhysical
    OBJECT IDENTIFIER ::= { xcmCOParallelSuite 1100 }
    -- integerTruthValue
xcmCOParallelSignalType
    OBJECT IDENTIFIER ::= { xcmCOParallelSuite 1101 }
    -- integerEnum (1=none, 2=other, 3=centronics, 4=ecp, 5=epp)
xcmCOParallelSignalOverride     -- Parallel Signal Type Override
    OBJECT IDENTIFIER ::= { xcmCOParallelSignalType 1 }
    -- integerEnum (see 'xcmCOParallelSignalType' above)
xcmCOParallelSignalDetected     -- Parallel Signal Type Detected
    OBJECT IDENTIFIER ::= { xcmCOParallelSignalType 2 }
    -- integerEnum (see 'xcmCOParallelSignalType' above)
xcmCOParallelSignalAdaptive     -- Parallel Signal Type Adaptive
    OBJECT IDENTIFIER ::= { xcmCOParallelSignalType 3 }
    -- integerTruthValue
xcmCOParallelSignalSupport      -- OSI LAN Signal Type Support
    OBJECT IDENTIFIER ::= { xcmCOParallelSignalType 4 }
    -- integerEnum (list of 'xcmCOParallelSignalType' above)
xcmCOParallelDevice
    OBJECT IDENTIFIER ::= { xcmCOParallelSuite 1102 }
    -- integerNumber ('hrDeviceIndex' in IETF HR MIB, or 0=unknown)
xcmCOParallelDeviceName
    OBJECT IDENTIFIER ::= { xcmCOParallelDevice 1 }
    -- stringLocalization ('xcmHrDevInfoName' in HRX, eg, '/dev/lpr1')
xcmCOParallelDeviceID           -- IEEE 1284 Device Identifier
    OBJECT IDENTIFIER ::= { xcmCOParallelDevice 2 }
    -- stringLocalization (set of capabilities as 'key:value(,value)')
    -- (keys and values MUST be US-ASCII)
    -- (spaces, tabs, formfeeds and line breaks are allowed and ignored)
    -- (values are delimited by a comma)
    -- (capabilites are delimited by a semicolon)
    -- (REQUIRED capabilities for all systems are:
    -- - MANUFACTURER (or abbreviation MFG)
    -- - COMMAND SET (or abbreviation CMD)
    -- - MODEL (or abbreviation MDL)
    -- (OPTIONAL capabilities for all systems include:
    -- - COMMENT
    -- - ACTIVE COMMAND SET
    -- (eg, 'MANUFACTURER: Xerox; COMMAND SET:PCL, PJL, PS; MODEL: ...')
    -- (see section 7.6 of IEEE 1284-2000)
xcmCOParallelSpeed
    OBJECT IDENTIFIER ::= { xcmCOParallelSuite 1103 }
    -- integerNumber (as in 'ifSpeed' in IETF MIB-II)
xcmCOParallelSpeedOverride
    OBJECT IDENTIFIER ::= { xcmCOParallelSpeed 1 }


    -- integerNumber (see 'xcmCOParallelSpeed' above)
xcmCOParallelSpeedDetected
    OBJECT IDENTIFIER ::= { xcmCOParallelSpeed 2 }
    -- integerNumber (see 'xcmCOParallelSpeed' above)
xcmCOParallelSpeedAdaptive
    OBJECT IDENTIFIER ::= { xcmCOParallelSpeed 3 }
    -- integerTruthValue
xcmCOParallelSpeedSupport
    OBJECT IDENTIFIER ::= { xcmCOParallelSpeed 4 }
    -- integerNumber (as in 'ifSpeed' in IETF MIB-II, list of speeds)
xcmCOParallelMinSpeed
    OBJECT IDENTIFIER ::= { xcmCOParallelSpeed 5 }
    -- integerNumber (as in 'ifSpeed' in IETF MIB-II)
xcmCOParallelMaxSpeed
    OBJECT IDENTIFIER ::= { xcmCOParallelSpeed 6 }
    -- integerNumber (as in 'ifSpeed' in IETF MIB-II)
xcmCOParallelBidirectional
    OBJECT IDENTIFIER ::= { xcmCOParallelSuite 1104 }
    -- integerTruthValue
xcmCOParallelInputTimeout       -- POSIX.1 'VTIME' * 10 (in 'termios.h')
    OBJECT IDENTIFIER ::= { xcmCOParallelSuite 1105 }
    -- integerNumber (seconds, 0=infinite or 1..n)
xcmCOParallelOutputTimeout
    OBJECT IDENTIFIER ::= { xcmCOParallelSuite 1106 }
    -- integerNumber (seconds, 0=infinite or 1..n)
xcmCOParallelConnectorType
    OBJECT IDENTIFIER ::= { xcmCOParallelSuite 1107 }
    -- integerEnum (1=none, 2=other, 3=centronics, 4=db25)
xcmCOParallelConnectorOverride  -- Parallel Connector Type Override
    OBJECT IDENTIFIER ::= { xcmCOParallelConnectorType 1 }
    -- integerEnum (see 'xcmCOParallelConnectorType' above)
xcmCOParallelConnectorDetected  -- Parallel Connector Type Detected
    OBJECT IDENTIFIER ::= { xcmCOParallelConnectorType 2 }
    -- integerEnum (see 'xcmCOParallelConnectorType' above)
xcmCOParallelConnectorAdaptive  -- Parallel Connector Type Adaptive
    OBJECT IDENTIFIER ::= { xcmCOParallelConnectorType 3 }
    -- integerTruthValue
xcmCOParallelMinInputChars      -- POSIX.1 'VMIN' (in 'termios.h')
    OBJECT IDENTIFIER ::= { xcmCOParallelSuite 1108 }
    -- integerNumber (0=infinite or 1..n)
xcmCOParallelMaxInputChars      -- POSIX.1 'nbyte' (in 'read()')
    OBJECT IDENTIFIER ::= { xcmCOParallelSuite 1109 }
    -- integerNumber (0=infinite or 1..n)
xcmCOParallelParity
    OBJECT IDENTIFIER ::= { xcmCOParallelSuite 1111 }
    -- integerEnum (1=none, 2=odd, 3=even, 4=mark, 5=space)
xcmCOParallelDataBits
    OBJECT IDENTIFIER ::= { xcmCOParallelSuite 1112 }
    -- integerNumber (0=default or 7..8)
xcmCOParallelFlowControl
    OBJECT IDENTIFIER ::= { xcmCOParallelSuite 1113 }
    -- integerEnum (1=none, 2=xonXoff)
xcmCOParallelInputPrime
    OBJECT IDENTIFIER ::= { xcmCOParallelSuite 1116 }


    -- integerTruthValue
xcmCOParallelHandshake
    OBJECT IDENTIFIER ::= { xcmCOParallelSuite 1117 }
    -- integerEnum (1=none, 2=ackBusy, 3=ackBusyAck, 4=busyAck)
xcmCOParallelDataStrobe
    OBJECT IDENTIFIER ::= { xcmCOParallelSuite 1118 }
    -- integerNumber (microseconds, 0=none, or 1..n)

xcmCOParallelDatalinks
    OBJECT IDENTIFIER ::= { xcmCOParallelSuite 1200 }
    -- integerTruthValue

xcmCOParallelProtocol
    OBJECT IDENTIFIER ::= { xcmCOParallelDatalinks 1 }
    -- integerEnum (see 'xcmCODirectPrintProtocol' below)

--
--          Direct Print Protocol Suite (Serial/Parallel)
--

xcmCODirectPrintSuite
    OBJECT IDENTIFIER ::= { xcmCommsConfigTC 29 }
    -- integerTruthValue

xcmCODirectPrintPhysical
    OBJECT IDENTIFIER ::= { xcmCODirectPrintSuite 1100 }
    -- integerTruthValue

xcmCODirectPrintDatalinks
    OBJECT IDENTIFIER ::= { xcmCODirectPrintSuite 1200 }
    -- integerTruthValue

xcmCODirectPrintProtocol
    OBJECT IDENTIFIER ::= { xcmCODirectPrintDatalinks 1 }
    -- integerEnum
    -- Generic datastream encoding and interpreter modes
    -- See: Vendor datastream encoding and interpreter language specs
    -- (1=none,                 - no sense - binary datastream
    --  2=other,                - other sensing mode or fixed encoding
    --  3=autoSwitch,           - sense both encoding and interpreter
    -- Adobe datastream modes (default to PostScript languages)
    -- See: Adobe "Serial and Parallel Binary Communications Protocols"
    -- See: Adobe PostScript and PDF interpreter language specs
    -- 11=psAutoSwitch,         - sense encoding, PS languages default
    -- 12=psRaw,                - fixed Raw encoding, PS default
    -- 13=psStandard,           - fixed Standard encoding, PS default
    -- 14=psBCP,                - fixed BCP encoding, PS default
    -- 15=psTBCP,               - fixed TBCP encoding, PS default
    -- 16=psAutoSwitchBCP,      - sense PS, default to BCP encoding
    -- 17=psAutoSwitchTBCP,     - sense PS, default to TBCP encoding
    -- 18=psAutoSwitchRaw,      - sense PS, default to Raw encoding
    -- 19=psAutoSwitchStandard  - sense PS, default to Standard encoding
    -- HP datastream modes (default to HP languages)
    -- See: HP PCL, PJL, and GL interpreter language specs


    -- 21=hpAutoSwitch,         - sense encoding, HP languages default
    -- 22=hpText,               - fixed Text encoding, HP default
    -- 23=hpPCL,                - fixed PCL encoding, HP default
    -- 24=hpPJL,                - fixed PJL encoding, HP default
    -- 25=hpGL,                 - fixed GL encoding, HP default
    -- 26=hpAutoSwitchText,     - sense HP, default to Text encoding
    -- 27=hpAutoSwitchPCL,      - sense HP, default to PCL encoding
    -- 28=hpAutoSwitchPJL,      - sense HP, default to PJL encoding
    -- 29=hpAutoSwitchGL)       - sense HP, default to GL encoding

--
--          USB Protocol Suite
--

xcmCOUsbSuite
    OBJECT IDENTIFIER ::= { xcmCommsConfigTC 30 }
    -- integerTruthValue

xcmCOUsbPhysical
    OBJECT IDENTIFIER ::= { xcmCOUsbSuite 1100 }
xcmCOUsbDevice
    OBJECT IDENTIFIER ::= { xcmCOUsbSuite 1102 }
    -- integerNumber ('hrDeviceIndex' in IETF HR MIB, or 0=unknown)
xcmCOUsbDeviceName
    OBJECT IDENTIFIER ::= { xcmCOUsbDevice 1 }
    -- stringLocalization ('xcmHrDevInfoName' in HRX, eg, '/dev/com1')
xcmCOUsbSpeed
    OBJECT IDENTIFIER ::= { xcmCOUsbSuite 1103 }
    -- integerNumber (as in 'ifSpeed' in IETF MIB-II)
xcmCOUsbSpeedOverride
    OBJECT IDENTIFIER ::= { xcmCOUsbSpeed 1 }
    -- integerNumber (see 'xcmCOUsbSpeed' above)
xcmCOUsbSpeedDetected
    OBJECT IDENTIFIER ::= { xcmCOUsbSpeed 2 }
    -- integerNumber (see 'xcmCOUsbSpeed' above)
xcmCOUsbSpeedAdaptive
    OBJECT IDENTIFIER ::= { xcmCOUsbSpeed 3 }
    -- integerTruthValue
xcmCOUsbSpeedSupport
    OBJECT IDENTIFIER ::= { xcmCOUsbSpeed 4 }
    -- integerNumber (as in 'ifSpeed' in IETF MIB-II, list of speeds)
xcmCOUsbMinSpeed
    OBJECT IDENTIFIER ::= { xcmCOUsbSpeed 5 }
    -- integerNumber (as in 'ifSpeed' in IETF MIB-II)
xcmCOUsbMaxSpeed
    OBJECT IDENTIFIER ::= { xcmCOUsbSpeed 6 }
    -- integerNumber (as in 'ifSpeed' in IETF MIB-II)
xcmCOUsbBidirectional
    OBJECT IDENTIFIER ::= { xcmCOUsbSuite 1104 }
    -- integerTruthValue
xcmCOUsbInputTimeout            -- POSIX.1 'VTIME' * 10 (in 'termios.h')
    OBJECT IDENTIFIER ::= { xcmCOUsbSuite 1105 }
    -- integerNumber (seconds, 0=infinite or 1..n)
xcmCOUsbOutputTimeout


    OBJECT IDENTIFIER ::= { xcmCOUsbSuite 1106 }
    -- integerNumber (seconds, 0=infinite or 1..n)
xcmCOUsbMinInputChars           -- POSIX.1 'VMIN' (in 'termios.h')
    OBJECT IDENTIFIER ::= { xcmCOUsbSuite 1108 }
    -- integerNumber (0=infinite or 1..n)
xcmCOUsbMaxInputChars           -- POSIX.1 'nbyte' (in 'read()')
    OBJECT IDENTIFIER ::= { xcmCOUsbSuite 1109 }
    -- integerNumber (0=infinite or 1..n)

xcmCOUsbDatalinks
    OBJECT IDENTIFIER ::= { xcmCOUsbSuite 1200 }
    -- integerTruthValue

xcmCOUsbProtocol
    OBJECT IDENTIFIER ::= { xcmCOUsbDatalinks 1 }
    -- integerEnum (see 'xcmCODirectPrintProtocol' below)

--
--          The Comms Config TC Dummy Group (DO NOT USE)
--
--          DO NOT USE - Present to suppress compiler warnings ONLY!
--
--          Note:  The following objects have 'odd' use of case in their
--          names (ie, 'xCm...'), in order to make obvious their related
--          textual conventions

xCmCommsConfigDummy OBJECT IDENTIFIER ::= { xcmCommsConfigTC 999 }

xCmSnmpNetbiosAddress OBJECT-TYPE
    SYNTAX      XcmSnmpNetbiosAddress
    MAX-ACCESS  not-accessible
    STATUS      current
    DESCRIPTION "Dummy - DO NOT USE"
    ::= { xCmCommsConfigDummy 1 }

xCmCommsConfigGroupSupport OBJECT-TYPE
    SYNTAX      XcmCommsConfigGroupSupport
    MAX-ACCESS  not-accessible
    STATUS      current
    DESCRIPTION "Dummy - DO NOT USE"
    ::= { xCmCommsConfigDummy 2 }

xCmCommsDirRecordType OBJECT-TYPE
    SYNTAX      XcmCommsDirRecordType
    MAX-ACCESS  not-accessible
    STATUS      current
    DESCRIPTION "Dummy - DO NOT USE"
    ::= { xCmCommsConfigDummy 3 }

xCmCommsDirAttributeType OBJECT-TYPE
    SYNTAX      XcmCommsDirAttributeType
    MAX-ACCESS  not-accessible
    STATUS      current
    DESCRIPTION "Dummy - DO NOT USE"


    ::= { xCmCommsConfigDummy 4 }

xCmCommsLDAPAttributeType OBJECT-TYPE
    SYNTAX      XcmCommsLDAPAttributeType
    MAX-ACCESS  not-accessible
    STATUS      current
    DESCRIPTION "Dummy - DO NOT USE"
    ::= { xCmCommsConfigDummy 5 }

xCmSnmpIPHostnameAddress OBJECT-TYPE
    SYNTAX      XcmSnmpIPHostnameAddress
    MAX-ACCESS  not-accessible
    STATUS      current
    DESCRIPTION "Dummy - DO NOT USE"
    ::= { xCmCommsConfigDummy 6 }
END
