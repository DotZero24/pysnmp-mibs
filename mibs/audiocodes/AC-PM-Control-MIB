AC-PM-Control-MIB DEFINITIONS ::= BEGIN


    IMPORTS


        OBJECT-TYPE,
        MODULE-IDENTITY                             FROM SNMPv2-SMI
        TAddress,
        DisplayString,
        DateAndTime, TEXTUAL-CONVENTION             FROM SNMPv2-TC
        IpAddress                                   FROM RFC1155-SMI
        Unsigned32,
		Integer32,
        enterprises                                 FROM SNMPv2-SMI
		SnmpAdminString								FROM SNMP-FRAMEWORK-MIB
		audioCodes,
		acRegistrations,
		acGeneric,
		acProducts,acBoardMibs,acPerformance		FROM AUDIOCODES-TYPES-MIB;


acPMControl  MODULE-IDENTITY
    LAST-UPDATED "200908250451Z"          --Tuesday, August 25, 2009
    ORGANIZATION "AudioCodes Ltd"
    CONTACT-INFO
    "Postal: Support
			 AudioCodes LTD
             1 Hayarden Street
             Airport City
			 Lod, ISRAEL 70151
     Tel:    972-3-9764000
     Fax:    972-3-9764040
     Email:  support@audiocodes.com
     Web:    www.audiocodes.com"


    DESCRIPTION
    "The AC-PM-Control MIB offers performance monitoring
For the Control related elements in Audiocodes' devices.
The Configuration sub-tree is for configuring the interval
Period length for the entire AC-PM-Control MIB, and the
different tables' thresholds.
The Data sub-tree presents the tables of monitored
elements.

Note  - for the entire MIB the value (-1) means the value
Asked for is either not supported or currently not relevant
(this is for when values asked for are for intervals not yet
recorded."



    ::= {acPerformance 8}








     acPMControlConfiguration OBJECT IDENTIFIER ::= {acPMControl 1}


     acPMControlConfigurationPeriodLength OBJECT-TYPE
       SYNTAX Unsigned32 (0..894780)
       MAX-ACCESS read-write
       STATUS current
       DESCRIPTION
           "Length of monitoring intervals for entire MIB.
Time is in minutes.
Access: Instant."
       ::= {acPMControlConfiguration 1}



     acPMControlConfigurationResetTotalCounters OBJECT-TYPE
       SYNTAX INTEGER {
                  resetCountersDone(1)
,
                  resetTotalCounters(2)

                  }
       MAX-ACCESS read-write
       STATUS current
       DESCRIPTION
           "Total-Counters Reset.  To reset the total counters, set the
value of this object to resetTotalCounters(2).
Access: Instant."
       ::= {acPMControlConfiguration 2}



     acPMCPConnectionAttributes OBJECT IDENTIFIER ::= {acPMControlConfiguration 32}


     acPMCPConnectionAttributesLifetimeHighThreshold OBJECT-TYPE
       SYNTAX Unsigned32 (0..2147483647)
       MAX-ACCESS read-write
       STATUS current
       DESCRIPTION
           "High threshold.
Access: Instant."
       ::= {acPMCPConnectionAttributes 1}



     acPMCPConnectionAttributesLifetimeLowThreshold OBJECT-TYPE
       SYNTAX Unsigned32 (0..2147483647)
       MAX-ACCESS read-write
       STATUS current
       DESCRIPTION
           "Low threshold.
Access: Instant."
       ::= {acPMCPConnectionAttributes 2}



     acPMCPConnectionAttributesStateHighThreshold OBJECT-TYPE
       SYNTAX Unsigned32 (0..2147483647)
       MAX-ACCESS read-write
       STATUS current
       DESCRIPTION
           "High threshold.
Access: Instant."
       ::= {acPMCPConnectionAttributes 3}



     acPMCPConnectionAttributesStateLowThreshold OBJECT-TYPE
       SYNTAX Unsigned32 (0..2147483647)
       MAX-ACCESS read-write
       STATUS current
       DESCRIPTION
           "Low threshold.
Access: Instant."
       ::= {acPMCPConnectionAttributes 4}



     acPMCPConnectionAttributesCommandCounterHighThreshold OBJECT-TYPE
       SYNTAX Unsigned32 (0..2147483647)
       MAX-ACCESS read-write
       STATUS current
       DESCRIPTION
           "High threshold.
Access: Instant."
       ::= {acPMCPConnectionAttributes 5}



     acPMCPConnectionAttributesCommandCounterLowThreshold OBJECT-TYPE
       SYNTAX Unsigned32 (0..2147483647)
       MAX-ACCESS read-write
       STATUS current
       DESCRIPTION
           "Low threshold.
Access: Instant."
       ::= {acPMCPConnectionAttributes 6}



     acPMCPConnectionAttributesRetransmissionCountHighThreshold OBJECT-TYPE
       SYNTAX Unsigned32 (0..2147483647)
       MAX-ACCESS read-write
       STATUS current
       DESCRIPTION
           "High threshold.
Access: Instant."
       ::= {acPMCPConnectionAttributes 7}



     acPMCPConnectionAttributesRetransmissionCountLowThreshold OBJECT-TYPE
       SYNTAX Unsigned32 (0..2147483647)
       MAX-ACCESS read-write
       STATUS current
       DESCRIPTION
           "Low threshold.
Access: Instant."
       ::= {acPMCPConnectionAttributes 8}



     acPMCPConnectionAttributesActiveContextCountHighThreshold OBJECT-TYPE
       SYNTAX Unsigned32 (0..2147483647)
       MAX-ACCESS read-write
       STATUS current
       DESCRIPTION
           "High threshold.
Access: Instant."
       ::= {acPMCPConnectionAttributes 9}



     acPMCPConnectionAttributesActiveContextCountLowThreshold OBJECT-TYPE
       SYNTAX Unsigned32 (0..2147483647)
       MAX-ACCESS read-write
       STATUS current
       DESCRIPTION
           "Low threshold.
Access: Instant."
       ::= {acPMCPConnectionAttributes 10}



     acPMCPConnectionAttributesCommandSuccessCountHighThreshold OBJECT-TYPE
       SYNTAX Unsigned32 (0..2147483647)
       MAX-ACCESS read-write
       STATUS obsolete
       DESCRIPTION
           "High threshold.
Access: Instant."
       ::= {acPMCPConnectionAttributes 11}



     acPMCPConnectionAttributesCommandSuccessCountLowThreshold OBJECT-TYPE
       SYNTAX Unsigned32 (0..2147483647)
       MAX-ACCESS read-write
       STATUS obsolete
       DESCRIPTION
           "Low threshold.
Access: Instant."
       ::= {acPMCPConnectionAttributes 12}



     acPMCPConnectionAttributesCommandFailureCountHighThreshold OBJECT-TYPE
       SYNTAX Unsigned32 (0..2147483647)
       MAX-ACCESS read-write
       STATUS obsolete
       DESCRIPTION
           "High threshold.
Access: Instant."
       ::= {acPMCPConnectionAttributes 13}



     acPMCPConnectionAttributesCommandFailureCountLowThreshold OBJECT-TYPE
       SYNTAX Unsigned32 (0..2147483647)
       MAX-ACCESS read-write
       STATUS obsolete
       DESCRIPTION
           "Low threshold.
Access: Instant."
       ::= {acPMCPConnectionAttributes 14}



     acPMCPConnectionAttributesCommandProcessTimeHighThreshold OBJECT-TYPE
       SYNTAX Unsigned32 (0..2147483647)
       MAX-ACCESS read-write
       STATUS current
       DESCRIPTION
           "High threshold.
Access: Instant."
       ::= {acPMCPConnectionAttributes 15}



     acPMCPConnectionAttributesCommandProcessTimeLowThreshold OBJECT-TYPE
       SYNTAX Unsigned32 (0..2147483647)
       MAX-ACCESS read-write
       STATUS current
       DESCRIPTION
           "Low threshold.
Access: Instant."
       ::= {acPMCPConnectionAttributes 16}



     acPMCPConnectionAttributesTransactionProcessTimerHighThreshold OBJECT-TYPE
       SYNTAX Unsigned32 (0..2147483647)
       MAX-ACCESS read-write
       STATUS current
       DESCRIPTION
           "High threshold.
Access: Instant."
       ::= {acPMCPConnectionAttributes 17}



     acPMCPConnectionAttributesTransactionProcessTimerLowThreshold OBJECT-TYPE
       SYNTAX Unsigned32 (0..2147483647)
       MAX-ACCESS read-write
       STATUS current
       DESCRIPTION
           "Low threshold.
Access: Instant."
       ::= {acPMCPConnectionAttributes 18}



     acPMMegacoAttributes OBJECT IDENTIFIER ::= {acPMControlConfiguration 33}


     acPMMegacoAttributesServiceChangeCountHighThreshold OBJECT-TYPE
       SYNTAX Unsigned32 (0..2147483647)
       MAX-ACCESS read-write
       STATUS current
       DESCRIPTION
           "High threshold.
Access: Instant."
       ::= {acPMMegacoAttributes 1}



     acPMMegacoAttributesServiceChangeCountLowThreshold OBJECT-TYPE
       SYNTAX Unsigned32 (0..2147483647)
       MAX-ACCESS read-write
       STATUS current
       DESCRIPTION
           "Low threshold.
Access: Instant."
       ::= {acPMMegacoAttributes 2}



     acPMMegacoAttributesCmdSuccessCountHighThreshold OBJECT-TYPE
       SYNTAX Unsigned32 (0..2147483647)
       MAX-ACCESS read-write
       STATUS obsolete
       DESCRIPTION
           "High threshold.
Access: Instant."
       ::= {acPMMegacoAttributes 3}



     acPMMegacoAttributesCmdSuccessCountLowThreshold OBJECT-TYPE
       SYNTAX Unsigned32 (0..2147483647)
       MAX-ACCESS read-write
       STATUS obsolete
       DESCRIPTION
           "Low threshold.
Access: Instant."
       ::= {acPMMegacoAttributes 4}



     acPMMegacoAttributesCmdFailureCountHighThreshold OBJECT-TYPE
       SYNTAX Unsigned32 (0..2147483647)
       MAX-ACCESS read-write
       STATUS obsolete
       DESCRIPTION
           "High threshold.
Access: Instant."
       ::= {acPMMegacoAttributes 5}



     acPMMegacoAttributesCmdFailureCountLowThreshold OBJECT-TYPE
       SYNTAX Unsigned32 (0..2147483647)
       MAX-ACCESS read-write
       STATUS obsolete
       DESCRIPTION
           "Low threshold.
Access: Instant."
       ::= {acPMMegacoAttributes 6}



     acPMSipAttributes OBJECT IDENTIFIER ::= {acPMControlConfiguration 34}


     acPMSipAttributesCallDurationHighThreshold OBJECT-TYPE
       SYNTAX Unsigned32 (0..2147483647)
       MAX-ACCESS read-write
       STATUS current
       DESCRIPTION
           "Low threshold.
Access: Instant."
       ::= {acPMSipAttributes 1}



     acPMSipAttributesCallDurationLowThreshold OBJECT-TYPE
       SYNTAX Unsigned32 (0..2147483647)
       MAX-ACCESS read-write
       STATUS current
       DESCRIPTION
           "Low threshold.
Access: Instant."
       ::= {acPMSipAttributes 2}



     acPMControlData OBJECT IDENTIFIER ::= {acPMControl 2}


     acPMControlDataAcPMControlTimeFromStartOfInterval OBJECT-TYPE
       SYNTAX Unsigned32 (0..2147483647)
       MAX-ACCESS read-only
       STATUS current
       DESCRIPTION
           "The time in seconds since the start of the current interval.
MIB specific."
       ::= {acPMControlData 1}



     acPMCPConnection OBJECT IDENTIFIER ::= {acPMControlData 31}


     -- ****************************************
     -- acPMCPConnectionLifetime table declaration
     -- ****************************************
     acPMCPConnectionLifetimeTable OBJECT-TYPE
       SYNTAX SEQUENCE OF AcPMCPConnectionLifetimeEntry
       MAX-ACCESS not-accessible
       STATUS current
       DESCRIPTION
           "Connection lifetime in seconds."
       ::= {acPMCPConnection 1}



     -- ****************************************
     -- acPMCPConnectionLifetime table entry
     -- ****************************************
     acPMCPConnectionLifetimeEntry OBJECT-TYPE
       SYNTAX AcPMCPConnectionLifetimeEntry
       MAX-ACCESS not-accessible
       STATUS current
       DESCRIPTION
           ""
       INDEX {acPMCPConnectionLifetimeInterval}
       ::= {acPMCPConnectionLifetimeTable 1}



     -- ****************************************
     -- acPMCPConnectionLifetime TABLE
     -- ****************************************
     AcPMCPConnectionLifetimeEntry ::= SEQUENCE {
       acPMCPConnectionLifetimeInterval                Unsigned32,
       acPMCPConnectionLifetimeVal                     Gauge32,
       acPMCPConnectionLifetimeAverage                 Integer32,
       acPMCPConnectionLifetimeMax                     Integer32,
       acPMCPConnectionLifetimeMin                     Integer32,
       acPMCPConnectionLifetimeVolume                  Counter32,
       acPMCPConnectionLifetimeTimeBelowLowThreshold   Integer32,
       acPMCPConnectionLifetimeTimeBetweenThresholds   Integer32,
       acPMCPConnectionLifetimeTimeAboveHighThreshold  Integer32,
       acPMCPConnectionLifetimeFullDayAverage          Integer32,
       acPMCPConnectionLifetimeTotal                   Integer32
     }



     acPMCPConnectionLifetimeInterval OBJECT-TYPE
       SYNTAX Unsigned32 (0..4)
       MAX-ACCESS not-accessible
       STATUS current
       DESCRIPTION
           "Interval index.
0 - current period (incomplete monitoring - mid period).
1 - Last full period.
2 - One before last
3 - Two before last
4 - Three before last."
       ::= {acPMCPConnectionLifetimeEntry 1}



     acPMCPConnectionLifetimeVal OBJECT-TYPE
       SYNTAX Gauge32
       MAX-ACCESS read-only
       STATUS current
       DESCRIPTION
           "Value of gauge or counter."
       ::= {acPMCPConnectionLifetimeEntry 2}



     acPMCPConnectionLifetimeAverage OBJECT-TYPE
       SYNTAX Integer32 (-1..2147483647)
       MAX-ACCESS read-only
       STATUS current
       DESCRIPTION
           "Average value with in the period time."
       ::= {acPMCPConnectionLifetimeEntry 3}



     acPMCPConnectionLifetimeMax OBJECT-TYPE
       SYNTAX Integer32 (-1..2147483647)
       MAX-ACCESS read-only
       STATUS current
       DESCRIPTION
           "Maximum value with in the period time."
       ::= {acPMCPConnectionLifetimeEntry 4}



     acPMCPConnectionLifetimeMin OBJECT-TYPE
       SYNTAX Integer32 (-1..2147483647)
       MAX-ACCESS read-only
       STATUS current
       DESCRIPTION
           "Minimum value with in the period time."
       ::= {acPMCPConnectionLifetimeEntry 5}



     acPMCPConnectionLifetimeVolume OBJECT-TYPE
       SYNTAX Counter32
       MAX-ACCESS read-only
       STATUS current
       DESCRIPTION
           "Activity volume."
       ::= {acPMCPConnectionLifetimeEntry 6}



     acPMCPConnectionLifetimeTimeBelowLowThreshold OBJECT-TYPE
       SYNTAX Integer32 (-1..100)
       MAX-ACCESS read-only
       STATUS current
       DESCRIPTION
           "Percent of interval time for which gauge is below what was determined
as the low threshold."
       ::= {acPMCPConnectionLifetimeEntry 7}



     acPMCPConnectionLifetimeTimeBetweenThresholds OBJECT-TYPE
       SYNTAX Integer32 (-1..100)
       MAX-ACCESS read-only
       STATUS current
       DESCRIPTION
           "Percent of interval time for which gauge is above what was determined
as the high threshold."
       ::= {acPMCPConnectionLifetimeEntry 8}



     acPMCPConnectionLifetimeTimeAboveHighThreshold OBJECT-TYPE
       SYNTAX Integer32 (-1..100)
       MAX-ACCESS read-only
       STATUS current
       DESCRIPTION
           "Percent of interval time for which gauge is between what were
determined as the low and high thresholds."
       ::= {acPMCPConnectionLifetimeEntry 9}



     acPMCPConnectionLifetimeFullDayAverage OBJECT-TYPE
       SYNTAX Integer32 (-1..2147483647)
       MAX-ACCESS read-only
       STATUS current
       DESCRIPTION
           "The average of full 24 hours."
       ::= {acPMCPConnectionLifetimeEntry 10}



     acPMCPConnectionLifetimeTotal OBJECT-TYPE
       SYNTAX Integer32 (-1..2147483647)
       MAX-ACCESS read-only
       STATUS current
       DESCRIPTION
           "Total since last reset."
       ::= {acPMCPConnectionLifetimeEntry 11}



     -- ****************************************
     -- acPMCPConnectionState table declaration
     -- ****************************************
     acPMCPConnectionStateTable OBJECT-TYPE
       SYNTAX SEQUENCE OF AcPMCPConnectionStateEntry
       MAX-ACCESS not-accessible
       STATUS current
       DESCRIPTION
           "MGC connection activity indicator."
       ::= {acPMCPConnection 2}



     -- ****************************************
     -- acPMCPConnectionState table entry
     -- ****************************************
     acPMCPConnectionStateEntry OBJECT-TYPE
       SYNTAX AcPMCPConnectionStateEntry
       MAX-ACCESS not-accessible
       STATUS current
       DESCRIPTION
           ""
       INDEX {acPMCPConnectionStateInterval}
       ::= {acPMCPConnectionStateTable 1}



     -- ****************************************
     -- acPMCPConnectionState TABLE
     -- ****************************************
     AcPMCPConnectionStateEntry ::= SEQUENCE {
       acPMCPConnectionStateInterval                   Unsigned32,
       acPMCPConnectionStateChanges                    Gauge32,
       acPMCPConnectionStateActiveTime                 Integer32
     }



     acPMCPConnectionStateInterval OBJECT-TYPE
       SYNTAX Unsigned32 (0..2)
       MAX-ACCESS not-accessible
       STATUS current
       DESCRIPTION
           "Interval index.
0 - current period (incomplete monitoring - mid period).
1 - Last full period.
2 - One before last."
       ::= {acPMCPConnectionStateEntry 1}



     acPMCPConnectionStateChanges OBJECT-TYPE
       SYNTAX Gauge32
       MAX-ACCESS read-only
       STATUS current
       DESCRIPTION
           "Activity volume."
       ::= {acPMCPConnectionStateEntry 2}



     acPMCPConnectionStateActiveTime OBJECT-TYPE
       SYNTAX Integer32 (-1..100)
       MAX-ACCESS read-only
       STATUS current
       DESCRIPTION
           "Percent of interval time for which gauge is between what were
determined as the low and high thresholds."
       ::= {acPMCPConnectionStateEntry 3}



     -- ****************************************
     -- acPMCPCommandCounter table declaration
     -- ****************************************
     acPMCPCommandCounterTable OBJECT-TYPE
       SYNTAX SEQUENCE OF AcPMCPCommandCounterEntry
       MAX-ACCESS not-accessible
       STATUS current
       DESCRIPTION
           "MGC command/response counters. Index: 0=sent commands, 1=received commands"
       ::= {acPMCPConnection 3}



     -- ****************************************
     -- acPMCPCommandCounter table entry
     -- ****************************************
     acPMCPCommandCounterEntry OBJECT-TYPE
       SYNTAX AcPMCPCommandCounterEntry
       MAX-ACCESS not-accessible
       STATUS current
       DESCRIPTION
           ""
       INDEX {acPMCPCommandCounterDirection,acPMCPCommandCounterInterval}
       ::= {acPMCPCommandCounterTable 1}



     -- ****************************************
     -- acPMCPCommandCounter TABLE
     -- ****************************************
     AcPMCPCommandCounterEntry ::= SEQUENCE {
       acPMCPCommandCounterDirection                   INTEGER,
       acPMCPCommandCounterInterval                    Unsigned32,
       acPMCPCommandCounterVal                         Counter32,
       acPMCPCommandCounterTotal                       Integer32
     }



     acPMCPCommandCounterDirection OBJECT-TYPE
       SYNTAX INTEGER {
                  tx(0)
,
                  rx(1)

                  }
       MAX-ACCESS not-accessible
       STATUS current
       DESCRIPTION
           "Direction index.
 0 - transmit
 1 - receive."
       ::= {acPMCPCommandCounterEntry 1}



     acPMCPCommandCounterInterval OBJECT-TYPE
       SYNTAX Unsigned32 (0..2)
       MAX-ACCESS not-accessible
       STATUS current
       DESCRIPTION
           "Interval index.
0 - current period (incomplete monitoring - mid period).
1 - Last full period.
2 - One before last."
       ::= {acPMCPCommandCounterEntry 2}



     acPMCPCommandCounterVal OBJECT-TYPE
       SYNTAX Counter32
       MAX-ACCESS read-only
       STATUS current
       DESCRIPTION
           "Value of gauge or counter."
       ::= {acPMCPCommandCounterEntry 3}



     acPMCPCommandCounterTotal OBJECT-TYPE
       SYNTAX Integer32 (-1..2147483647)
       MAX-ACCESS read-only
       STATUS current
       DESCRIPTION
           "Total since last reset."
       ::= {acPMCPCommandCounterEntry 4}



     -- ****************************************
     -- acPMCPRetransmissionCount table declaration
     -- ****************************************
     acPMCPRetransmissionCountTable OBJECT-TYPE
       SYNTAX SEQUENCE OF AcPMCPRetransmissionCountEntry
       MAX-ACCESS not-accessible
       STATUS current
       DESCRIPTION
           "Number of transaction retransmissions.
The first direction (tx(0)) counts the transactions sent from the board,
while the second direction (rx(1)) counts the incoming retransmissions."
       ::= {acPMCPConnection 4}



     -- ****************************************
     -- acPMCPRetransmissionCount table entry
     -- ****************************************
     acPMCPRetransmissionCountEntry OBJECT-TYPE
       SYNTAX AcPMCPRetransmissionCountEntry
       MAX-ACCESS not-accessible
       STATUS current
       DESCRIPTION
           ""
       INDEX {acPMCPRetransmissionCountDirection,acPMCPRetransmissionCountInterval}
       ::= {acPMCPRetransmissionCountTable 1}



     -- ****************************************
     -- acPMCPRetransmissionCount TABLE
     -- ****************************************
     AcPMCPRetransmissionCountEntry ::= SEQUENCE {
       acPMCPRetransmissionCountDirection              INTEGER,
       acPMCPRetransmissionCountInterval               Unsigned32,
       acPMCPRetransmissionCountVal                    Gauge32,
       acPMCPRetransmissionCountTotal                  Integer32
     }



     acPMCPRetransmissionCountDirection OBJECT-TYPE
       SYNTAX INTEGER {
                  tx(0)
,
                  rx(1)

                  }
       MAX-ACCESS not-accessible
       STATUS current
       DESCRIPTION
           "Direction index.
 0 - transmit
 1 - receive."
       ::= {acPMCPRetransmissionCountEntry 1}



     acPMCPRetransmissionCountInterval OBJECT-TYPE
       SYNTAX Unsigned32 (0..2)
       MAX-ACCESS not-accessible
       STATUS current
       DESCRIPTION
           "Interval index.
0 - current period (incomplete monitoring - mid period).
1 - Last full period.
2 - One before last."
       ::= {acPMCPRetransmissionCountEntry 2}



     acPMCPRetransmissionCountVal OBJECT-TYPE
       SYNTAX Gauge32
       MAX-ACCESS read-only
       STATUS current
       DESCRIPTION
           "Value of gauge or counter."
       ::= {acPMCPRetransmissionCountEntry 3}



     acPMCPRetransmissionCountTotal OBJECT-TYPE
       SYNTAX Integer32 (-1..2147483647)
       MAX-ACCESS read-only
       STATUS current
       DESCRIPTION
           "Total since last reset."
       ::= {acPMCPRetransmissionCountEntry 4}



     -- ****************************************
     -- acPMActiveContextCount table declaration
     -- ****************************************
     acPMActiveContextCountTable OBJECT-TYPE
       SYNTAX SEQUENCE OF AcPMActiveContextCountEntry
       MAX-ACCESS not-accessible
       STATUS current
       DESCRIPTION
           "Number of active contexts"
       ::= {acPMCPConnection 5}



     -- ****************************************
     -- acPMActiveContextCount table entry
     -- ****************************************
     acPMActiveContextCountEntry OBJECT-TYPE
       SYNTAX AcPMActiveContextCountEntry
       MAX-ACCESS not-accessible
       STATUS current
       DESCRIPTION
           ""
       INDEX {acPMActiveContextCountInterval}
       ::= {acPMActiveContextCountTable 1}



     -- ****************************************
     -- acPMActiveContextCount TABLE
     -- ****************************************
     AcPMActiveContextCountEntry ::= SEQUENCE {
       acPMActiveContextCountInterval                  Unsigned32,
       acPMActiveContextCountVal                       Gauge32,
       acPMActiveContextCountAverage                   Integer32,
       acPMActiveContextCountMax                       Integer32,
       acPMActiveContextCountMin                       Integer32,
       acPMActiveContextCountVolume                    Counter32,
       acPMActiveContextCountTimeBelowLowThreshold     Integer32,
       acPMActiveContextCountTimeBetweenThresholds     Integer32,
       acPMActiveContextCountTimeAboveHighThreshold    Integer32,
       acPMActiveContextCountFullDayAverage            Integer32,
       acPMActiveContextCountTotal                     Integer32
     }



     acPMActiveContextCountInterval OBJECT-TYPE
       SYNTAX Unsigned32 (0..2)
       MAX-ACCESS not-accessible
       STATUS current
       DESCRIPTION
           "Interval index.
0 - current period (incomplete monitoring - mid period).
1 - Last full period.
2 - One before last."
       ::= {acPMActiveContextCountEntry 1}



     acPMActiveContextCountVal OBJECT-TYPE
       SYNTAX Gauge32
       MAX-ACCESS read-only
       STATUS current
       DESCRIPTION
           "Value of gauge or counter."
       ::= {acPMActiveContextCountEntry 2}



     acPMActiveContextCountAverage OBJECT-TYPE
       SYNTAX Integer32 (-1..2147483647)
       MAX-ACCESS read-only
       STATUS current
       DESCRIPTION
           "Average value with in the period time."
       ::= {acPMActiveContextCountEntry 3}



     acPMActiveContextCountMax OBJECT-TYPE
       SYNTAX Integer32 (-1..2147483647)
       MAX-ACCESS read-only
       STATUS current
       DESCRIPTION
           "Maximum value with in the period time."
       ::= {acPMActiveContextCountEntry 4}



     acPMActiveContextCountMin OBJECT-TYPE
       SYNTAX Integer32 (-1..2147483647)
       MAX-ACCESS read-only
       STATUS current
       DESCRIPTION
           "Minimum value with in the period time."
       ::= {acPMActiveContextCountEntry 5}



     acPMActiveContextCountVolume OBJECT-TYPE
       SYNTAX Counter32
       MAX-ACCESS read-only
       STATUS current
       DESCRIPTION
           "Activity volume."
       ::= {acPMActiveContextCountEntry 6}



     acPMActiveContextCountTimeBelowLowThreshold OBJECT-TYPE
       SYNTAX Integer32 (-1..100)
       MAX-ACCESS read-only
       STATUS current
       DESCRIPTION
           "Percent of interval time for which gauge is below what was determined
as the low threshold."
       ::= {acPMActiveContextCountEntry 7}



     acPMActiveContextCountTimeBetweenThresholds OBJECT-TYPE
       SYNTAX Integer32 (-1..100)
       MAX-ACCESS read-only
       STATUS current
       DESCRIPTION
           "Percent of interval time for which gauge is above what was determined
as the high threshold."
       ::= {acPMActiveContextCountEntry 8}



     acPMActiveContextCountTimeAboveHighThreshold OBJECT-TYPE
       SYNTAX Integer32 (-1..100)
       MAX-ACCESS read-only
       STATUS current
       DESCRIPTION
           "Percent of interval time for which gauge is between what were
determined as the low and high thresholds."
       ::= {acPMActiveContextCountEntry 9}



     acPMActiveContextCountFullDayAverage OBJECT-TYPE
       SYNTAX Integer32 (-1..2147483647)
       MAX-ACCESS read-only
       STATUS current
       DESCRIPTION
           "The average of full 24 hours."
       ::= {acPMActiveContextCountEntry 10}



     acPMActiveContextCountTotal OBJECT-TYPE
       SYNTAX Integer32 (-1..2147483647)
       MAX-ACCESS read-only
       STATUS current
       DESCRIPTION
           "Total since last reset."
       ::= {acPMActiveContextCountEntry 11}



     -- ****************************************
     -- acPMCPCommandSuccessCount table declaration
     -- ****************************************
     acPMCPCommandSuccessCountTable OBJECT-TYPE
       SYNTAX SEQUENCE OF AcPMCPCommandSuccessCountEntry
       MAX-ACCESS not-accessible
       STATUS obsolete
       DESCRIPTION
           "Number of successful commands, per command type. Index: 0=add, 1=move, 2=modify, 3=subtract, 4=SC, 5=AuditValue, 6=AuditCapabilities, 7=Notify"
       ::= {acPMCPConnection 6}



     -- ****************************************
     -- acPMCPCommandSuccessCount table entry
     -- ****************************************
     acPMCPCommandSuccessCountEntry OBJECT-TYPE
       SYNTAX AcPMCPCommandSuccessCountEntry
       MAX-ACCESS not-accessible
       STATUS obsolete
       DESCRIPTION
           ""
       INDEX {acPMCPCommandSuccessCountCommandType,acPMCPCommandSuccessCountInterval}
       ::= {acPMCPCommandSuccessCountTable 1}



     -- ****************************************
     -- acPMCPCommandSuccessCount TABLE
     -- ****************************************
     AcPMCPCommandSuccessCountEntry ::= SEQUENCE {
       acPMCPCommandSuccessCountCommandType            INTEGER,
       acPMCPCommandSuccessCountInterval               Unsigned32,
       acPMCPCommandSuccessCountVal                    Gauge32,
       acPMCPCommandSuccessCountTotal                  Integer32
     }



     acPMCPCommandSuccessCountCommandType OBJECT-TYPE
       SYNTAX INTEGER {
                  add(0)
,
                  move(1)
,
                  modify(2)
,
                  subtract(3)
,
                  sc(4)
,
                  auditValue(5)
,
                  auditCapabilities(6)
,
                  notify(7)

                  }
       MAX-ACCESS not-accessible
       STATUS obsolete
       DESCRIPTION
           "Command type:
 0=add, 1=move, 2=modify, 3=subtract, 4=SC, 5=AuditValue, 6=AuditCapabilities,
7=Notify."
       ::= {acPMCPCommandSuccessCountEntry 1}



     acPMCPCommandSuccessCountInterval OBJECT-TYPE
       SYNTAX Unsigned32 (0..2)
       MAX-ACCESS not-accessible
       STATUS obsolete
       DESCRIPTION
           "Interval index.
0 - current period (incomplete monitoring - mid period).
1 - Last full period.
2 - One before last."
       ::= {acPMCPCommandSuccessCountEntry 2}



     acPMCPCommandSuccessCountVal OBJECT-TYPE
       SYNTAX Gauge32
       MAX-ACCESS read-only
       STATUS obsolete
       DESCRIPTION
           "Value of gauge or counter."
       ::= {acPMCPCommandSuccessCountEntry 3}



     acPMCPCommandSuccessCountTotal OBJECT-TYPE
       SYNTAX Integer32 (-1..2147483647)
       MAX-ACCESS read-only
       STATUS obsolete
       DESCRIPTION
           "Total since last reset."
       ::= {acPMCPCommandSuccessCountEntry 4}



     -- ****************************************
     -- acPMCPCommandFailureCount table declaration
     -- ****************************************
     acPMCPCommandFailureCountTable OBJECT-TYPE
       SYNTAX SEQUENCE OF AcPMCPCommandFailureCountEntry
       MAX-ACCESS not-accessible
       STATUS obsolete
       DESCRIPTION
           "Number of failing commands, per command type. Index: 0=add, 1=move, 2=modify, 3=subtract, 4=SC, 5=AuditValue, 6=AuditCapabilities, 7=Notify"
       ::= {acPMCPConnection 7}



     -- ****************************************
     -- acPMCPCommandFailureCount table entry
     -- ****************************************
     acPMCPCommandFailureCountEntry OBJECT-TYPE
       SYNTAX AcPMCPCommandFailureCountEntry
       MAX-ACCESS not-accessible
       STATUS obsolete
       DESCRIPTION
           ""
       INDEX {acPMCPCommandFailureCountCommandType,acPMCPCommandFailureCountInterval}
       ::= {acPMCPCommandFailureCountTable 1}



     -- ****************************************
     -- acPMCPCommandFailureCount TABLE
     -- ****************************************
     AcPMCPCommandFailureCountEntry ::= SEQUENCE {
       acPMCPCommandFailureCountCommandType            INTEGER,
       acPMCPCommandFailureCountInterval               Unsigned32,
       acPMCPCommandFailureCountVal                    Gauge32,
       acPMCPCommandFailureCountTotal                  Integer32
     }



     acPMCPCommandFailureCountCommandType OBJECT-TYPE
       SYNTAX INTEGER {
                  add(0)
,
                  move(1)
,
                  modify(2)
,
                  subtract(3)
,
                  sc(4)
,
                  auditValue(5)
,
                  auditCapabilities(6)
,
                  notify(7)

                  }
       MAX-ACCESS not-accessible
       STATUS obsolete
       DESCRIPTION
           "Command type:
 0=add, 1=move, 2=modify, 3=subtract, 4=SC, 5=AuditValue, 6=AuditCapabilities,
7=Notify."
       ::= {acPMCPCommandFailureCountEntry 1}



     acPMCPCommandFailureCountInterval OBJECT-TYPE
       SYNTAX Unsigned32 (0..2)
       MAX-ACCESS not-accessible
       STATUS obsolete
       DESCRIPTION
           "Interval index.
0 - current period (incomplete monitoring - mid period).
1 - Last full period.
2 - One before last."
       ::= {acPMCPCommandFailureCountEntry 2}



     acPMCPCommandFailureCountVal OBJECT-TYPE
       SYNTAX Gauge32
       MAX-ACCESS read-only
       STATUS obsolete
       DESCRIPTION
           "Value of gauge or counter."
       ::= {acPMCPCommandFailureCountEntry 3}



     acPMCPCommandFailureCountTotal OBJECT-TYPE
       SYNTAX Integer32 (-1..2147483647)
       MAX-ACCESS read-only
       STATUS current
       DESCRIPTION
           "Total since last reset."
       ::= {acPMCPCommandFailureCountEntry 4}



     -- ****************************************
     -- acPMcpCmdProcessTime table declaration
     -- ****************************************
     acPMcpCmdProcessTimeTable OBJECT-TYPE
       SYNTAX SEQUENCE OF AcPMcpCmdProcessTimeEntry
       MAX-ACCESS not-accessible
       STATUS current
       DESCRIPTION
           "Processing time (in Microseconds), per command type."
       ::= {acPMCPConnection 8}



     -- ****************************************
     -- acPMcpCmdProcessTime table entry
     -- ****************************************
     acPMcpCmdProcessTimeEntry OBJECT-TYPE
       SYNTAX AcPMcpCmdProcessTimeEntry
       MAX-ACCESS not-accessible
       STATUS current
       DESCRIPTION
           ""
       INDEX {acPMcpCmdProcessTimeInterval}
       ::= {acPMcpCmdProcessTimeTable 1}



     -- ****************************************
     -- acPMcpCmdProcessTime TABLE
     -- ****************************************
     AcPMcpCmdProcessTimeEntry ::= SEQUENCE {
       acPMcpCmdProcessTimeInterval                    Unsigned32,
       acPMcpCmdProcessTimeVal                         Gauge32,
       acPMcpCmdProcessTimeAverage                     Integer32,
       acPMcpCmdProcessTimeMax                         Integer32,
       acPMcpCmdProcessTimeMin                         Integer32,
       acPMcpCmdProcessTimeVolume                      Counter32,
       acPMcpCmdProcessTimeTimeBelowLowThreshold       Integer32,
       acPMcpCmdProcessTimeTimeBetweenThresholds       Integer32,
       acPMcpCmdProcessTimeTimeAboveHighThreshold      Integer32,
       acPMcpCmdProcessTimeFullDayAverage              Integer32,
       acPMcpCmdProcessTimeTotal                       Integer32
     }



     acPMcpCmdProcessTimeInterval OBJECT-TYPE
       SYNTAX Unsigned32 (0..2)
       MAX-ACCESS not-accessible
       STATUS current
       DESCRIPTION
           "Interval index.
0 - current period (incomplete monitoring - mid period).
1 - Last full period.
2 - One before last."
       ::= {acPMcpCmdProcessTimeEntry 1}



     acPMcpCmdProcessTimeVal OBJECT-TYPE
       SYNTAX Gauge32
       MAX-ACCESS read-only
       STATUS current
       DESCRIPTION
           "Value of gauge or counter."
       ::= {acPMcpCmdProcessTimeEntry 2}



     acPMcpCmdProcessTimeAverage OBJECT-TYPE
       SYNTAX Integer32 (-1..2147483647)
       MAX-ACCESS read-only
       STATUS current
       DESCRIPTION
           "Average value with in the period time."
       ::= {acPMcpCmdProcessTimeEntry 3}



     acPMcpCmdProcessTimeMax OBJECT-TYPE
       SYNTAX Integer32 (-1..2147483647)
       MAX-ACCESS read-only
       STATUS current
       DESCRIPTION
           "Maximum value with in the period time."
       ::= {acPMcpCmdProcessTimeEntry 4}



     acPMcpCmdProcessTimeMin OBJECT-TYPE
       SYNTAX Integer32 (-1..2147483647)
       MAX-ACCESS read-only
       STATUS current
       DESCRIPTION
           "Minimum value with in the period time."
       ::= {acPMcpCmdProcessTimeEntry 5}



     acPMcpCmdProcessTimeVolume OBJECT-TYPE
       SYNTAX Counter32
       MAX-ACCESS read-only
       STATUS current
       DESCRIPTION
           "Activity volume."
       ::= {acPMcpCmdProcessTimeEntry 6}



     acPMcpCmdProcessTimeTimeBelowLowThreshold OBJECT-TYPE
       SYNTAX Integer32 (-1..100)
       MAX-ACCESS read-only
       STATUS current
       DESCRIPTION
           "Percent of interval time for which gauge is below what was determined
as the low threshold."
       ::= {acPMcpCmdProcessTimeEntry 7}



     acPMcpCmdProcessTimeTimeBetweenThresholds OBJECT-TYPE
       SYNTAX Integer32 (-1..100)
       MAX-ACCESS read-only
       STATUS current
       DESCRIPTION
           "Percent of interval time for which gauge is above what was determined
as the high threshold."
       ::= {acPMcpCmdProcessTimeEntry 8}



     acPMcpCmdProcessTimeTimeAboveHighThreshold OBJECT-TYPE
       SYNTAX Integer32 (-1..100)
       MAX-ACCESS read-only
       STATUS current
       DESCRIPTION
           "Percent of interval time for which gauge is between what were
determined as the low and high thresholds."
       ::= {acPMcpCmdProcessTimeEntry 9}



     acPMcpCmdProcessTimeFullDayAverage OBJECT-TYPE
       SYNTAX Integer32 (-1..2147483647)
       MAX-ACCESS read-only
       STATUS current
       DESCRIPTION
           "The average of full 24 hours."
       ::= {acPMcpCmdProcessTimeEntry 10}



     acPMcpCmdProcessTimeTotal OBJECT-TYPE
       SYNTAX Integer32 (-1..2147483647)
       MAX-ACCESS read-only
       STATUS current
       DESCRIPTION
           "Total since last reset."
       ::= {acPMcpCmdProcessTimeEntry 11}



     -- ****************************************
     -- acPMcpTransactionProcessTimer table declaration
     -- ****************************************
     acPMcpTransactionProcessTimerTable OBJECT-TYPE
       SYNTAX SEQUENCE OF AcPMcpTransactionProcessTimerEntry
       MAX-ACCESS not-accessible
       STATUS current
       DESCRIPTION
           "Processing time (in Microseconds), For transaction request."
       ::= {acPMCPConnection 9}



     -- ****************************************
     -- acPMcpTransactionProcessTimer table entry
     -- ****************************************
     acPMcpTransactionProcessTimerEntry OBJECT-TYPE
       SYNTAX AcPMcpTransactionProcessTimerEntry
       MAX-ACCESS not-accessible
       STATUS current
       DESCRIPTION
           ""
       INDEX {acPMcpTransactionProcessTimerInterval}
       ::= {acPMcpTransactionProcessTimerTable 1}



     -- ****************************************
     -- acPMcpTransactionProcessTimer TABLE
     -- ****************************************
     AcPMcpTransactionProcessTimerEntry ::= SEQUENCE {
       acPMcpTransactionProcessTimerInterval           Unsigned32,
       acPMcpTransactionProcessTimerVal                Gauge32,
       acPMcpTransactionProcessTimerAverage            Integer32,
       acPMcpTransactionProcessTimerMax                Integer32,
       acPMcpTransactionProcessTimerMin                Integer32,
       acPMcpTransactionProcessTimerVolume             Counter32,
       acPMcpTransactionProcessTimerTimeBelowLowThreshold
                                                       Integer32,
       acPMcpTransactionProcessTimerTimeBetweenThresholds
                                                       Integer32,
       acPMcpTransactionProcessTimerTimeAboveHighThreshold
                                                       Integer32,
       acPMcpTransactionProcessTimerFullDayAverage     Integer32,
       acPMcpTransactionProcessTimerTotal              Integer32
     }



     acPMcpTransactionProcessTimerInterval OBJECT-TYPE
       SYNTAX Unsigned32 (0..2)
       MAX-ACCESS not-accessible
       STATUS current
       DESCRIPTION
           "Interval index.
0 - current period (incomplete monitoring - mid period).
1 - Last full period.
2 - One before last."
       ::= {acPMcpTransactionProcessTimerEntry 1}



     acPMcpTransactionProcessTimerVal OBJECT-TYPE
       SYNTAX Gauge32
       MAX-ACCESS read-only
       STATUS current
       DESCRIPTION
           "Value of gauge or counter."
       ::= {acPMcpTransactionProcessTimerEntry 2}



     acPMcpTransactionProcessTimerAverage OBJECT-TYPE
       SYNTAX Integer32 (-1..2147483647)
       MAX-ACCESS read-only
       STATUS current
       DESCRIPTION
           "Average value with in the period time."
       ::= {acPMcpTransactionProcessTimerEntry 3}



     acPMcpTransactionProcessTimerMax OBJECT-TYPE
       SYNTAX Integer32 (-1..2147483647)
       MAX-ACCESS read-only
       STATUS current
       DESCRIPTION
           "Maximum value with in the period time."
       ::= {acPMcpTransactionProcessTimerEntry 4}



     acPMcpTransactionProcessTimerMin OBJECT-TYPE
       SYNTAX Integer32 (-1..2147483647)
       MAX-ACCESS read-only
       STATUS current
       DESCRIPTION
           "Minimum value with in the period time."
       ::= {acPMcpTransactionProcessTimerEntry 5}



     acPMcpTransactionProcessTimerVolume OBJECT-TYPE
       SYNTAX Counter32
       MAX-ACCESS read-only
       STATUS current
       DESCRIPTION
           "Activity volume."
       ::= {acPMcpTransactionProcessTimerEntry 6}



     acPMcpTransactionProcessTimerTimeBelowLowThreshold OBJECT-TYPE
       SYNTAX Integer32 (-1..100)
       MAX-ACCESS read-only
       STATUS current
       DESCRIPTION
           "Percent of interval time for which gauge is below what was determined
as the low threshold."
       ::= {acPMcpTransactionProcessTimerEntry 7}



     acPMcpTransactionProcessTimerTimeBetweenThresholds OBJECT-TYPE
       SYNTAX Integer32 (-1..100)
       MAX-ACCESS read-only
       STATUS current
       DESCRIPTION
           "Percent of interval time for which gauge is above what was determined
as the high threshold."
       ::= {acPMcpTransactionProcessTimerEntry 8}



     acPMcpTransactionProcessTimerTimeAboveHighThreshold OBJECT-TYPE
       SYNTAX Integer32 (-1..100)
       MAX-ACCESS read-only
       STATUS current
       DESCRIPTION
           "Percent of interval time for which gauge is between what were
determined as the low and high thresholds."
       ::= {acPMcpTransactionProcessTimerEntry 9}



     acPMcpTransactionProcessTimerFullDayAverage OBJECT-TYPE
       SYNTAX Integer32 (-1..2147483647)
       MAX-ACCESS read-only
       STATUS current
       DESCRIPTION
           "The average of full 24 hours."
       ::= {acPMcpTransactionProcessTimerEntry 10}



     acPMcpTransactionProcessTimerTotal OBJECT-TYPE
       SYNTAX Integer32 (-1..2147483647)
       MAX-ACCESS read-only
       STATUS current
       DESCRIPTION
           "Total since last reset."
       ::= {acPMcpTransactionProcessTimerEntry 11}



     -- ****************************************
     -- acPMCPCallAttemptsPerSec table declaration
     -- ****************************************
     acPMCPCallAttemptsPerSecTable OBJECT-TYPE
       SYNTAX SEQUENCE OF AcPMCPCallAttemptsPerSecEntry
       MAX-ACCESS not-accessible
       STATUS current
       DESCRIPTION
           "Number of Call attempts (successful and unsuccessful)  for second"
       ::= {acPMCPConnection 10}



     -- ****************************************
     -- acPMCPCallAttemptsPerSec table entry
     -- ****************************************
     acPMCPCallAttemptsPerSecEntry OBJECT-TYPE
       SYNTAX AcPMCPCallAttemptsPerSecEntry
       MAX-ACCESS not-accessible
       STATUS current
       DESCRIPTION
           ""
       INDEX {acPMCPCallAttemptsPerSecInterval}
       ::= {acPMCPCallAttemptsPerSecTable 1}



     -- ****************************************
     -- acPMCPCallAttemptsPerSec TABLE
     -- ****************************************
     AcPMCPCallAttemptsPerSecEntry ::= SEQUENCE {
       acPMCPCallAttemptsPerSecInterval                Unsigned32,
       acPMCPCallAttemptsPerSecVal                     Gauge32,
       acPMCPCallAttemptsPerSecAverage                 Integer32,
       acPMCPCallAttemptsPerSecMax                     Integer32,
       acPMCPCallAttemptsPerSecMin                     Integer32,
       acPMCPCallAttemptsPerSecVolume                  Counter32
     }



     acPMCPCallAttemptsPerSecInterval OBJECT-TYPE
       SYNTAX Unsigned32 (0..2)
       MAX-ACCESS not-accessible
       STATUS current
       DESCRIPTION
           "Interval index.
0 - current period (incomplete monitoring - mid period).
1 - Last full period.
2 - One before last."
       ::= {acPMCPCallAttemptsPerSecEntry 1}



     acPMCPCallAttemptsPerSecVal OBJECT-TYPE
       SYNTAX Gauge32
       MAX-ACCESS read-only
       STATUS current
       DESCRIPTION
           "Value of gauge or counter."
       ::= {acPMCPCallAttemptsPerSecEntry 2}



     acPMCPCallAttemptsPerSecAverage OBJECT-TYPE
       SYNTAX Integer32 (-1..2147483647)
       MAX-ACCESS read-only
       STATUS current
       DESCRIPTION
           "Average value with in the period time."
       ::= {acPMCPCallAttemptsPerSecEntry 3}



     acPMCPCallAttemptsPerSecMax OBJECT-TYPE
       SYNTAX Integer32 (-1..2147483647)
       MAX-ACCESS read-only
       STATUS current
       DESCRIPTION
           "Maximum value with in the period time."
       ::= {acPMCPCallAttemptsPerSecEntry 4}



     acPMCPCallAttemptsPerSecMin OBJECT-TYPE
       SYNTAX Integer32 (-1..2147483647)
       MAX-ACCESS read-only
       STATUS current
       DESCRIPTION
           "Minimum value with in the period time."
       ::= {acPMCPCallAttemptsPerSecEntry 5}



     acPMCPCallAttemptsPerSecVolume OBJECT-TYPE
       SYNTAX Counter32
       MAX-ACCESS read-only
       STATUS current
       DESCRIPTION
           "Activity volume."
       ::= {acPMCPCallAttemptsPerSecEntry 6}



     acPMMegaco OBJECT IDENTIFIER ::= {acPMControlData 41}


     -- ****************************************
     -- acPMMegacoServiceChangeCount table declaration
     -- ****************************************
     acPMMegacoServiceChangeCountTable OBJECT-TYPE
       SYNTAX SEQUENCE OF AcPMMegacoServiceChangeCountEntry
       MAX-ACCESS not-accessible
       STATUS current
       DESCRIPTION
           "Number of service changes, per method. Index: 0=FailOver, 1=Forced, 2=Graceful, 3=Restart, 4=Disconnected, 5=Handoff"
       ::= {acPMMegaco 1}



     -- ****************************************
     -- acPMMegacoServiceChangeCount table entry
     -- ****************************************
     acPMMegacoServiceChangeCountEntry OBJECT-TYPE
       SYNTAX AcPMMegacoServiceChangeCountEntry
       MAX-ACCESS not-accessible
       STATUS current
       DESCRIPTION
           ""
       INDEX {acPMMegacoServiceChangeCountMethod,acPMMegacoServiceChangeCountInterval}
       ::= {acPMMegacoServiceChangeCountTable 1}



     -- ****************************************
     -- acPMMegacoServiceChangeCount TABLE
     -- ****************************************
     AcPMMegacoServiceChangeCountEntry ::= SEQUENCE {
       acPMMegacoServiceChangeCountMethod              INTEGER,
       acPMMegacoServiceChangeCountInterval            Unsigned32,
       acPMMegacoServiceChangeCountVal                 Gauge32
     }



     acPMMegacoServiceChangeCountMethod OBJECT-TYPE
       SYNTAX INTEGER {
                  failOver(0)
,
                  forced(1)
,
                  graceful(2)
,
                  restart(3)
,
                  disconnected(4)
,
                  handoff(5)

                  }
       MAX-ACCESS not-accessible
       STATUS current
       DESCRIPTION
           "Method:
0=FailOver, 1=Forced, 2=Graceful, 3=Restart, 4=Disconnected,
5=Handoff."
       ::= {acPMMegacoServiceChangeCountEntry 1}



     acPMMegacoServiceChangeCountInterval OBJECT-TYPE
       SYNTAX Unsigned32 (0..2)
       MAX-ACCESS not-accessible
       STATUS current
       DESCRIPTION
           "Interval index.
0 - current period (incomplete monitoring - mid period).
1 - Last full period.
2 - One before last."
       ::= {acPMMegacoServiceChangeCountEntry 2}



     acPMMegacoServiceChangeCountVal OBJECT-TYPE
       SYNTAX Gauge32
       MAX-ACCESS read-only
       STATUS current
       DESCRIPTION
           "Value of gauge or counter."
       ::= {acPMMegacoServiceChangeCountEntry 3}



     -- ****************************************
     -- acPMCPCmdSuccessCount table declaration
     -- ****************************************
     acPMCPCmdSuccessCountTable OBJECT-TYPE
       SYNTAX SEQUENCE OF AcPMCPCmdSuccessCountEntry
       MAX-ACCESS not-accessible
       STATUS current
       DESCRIPTION
           "Number of successful commands, per command type. Index: 0=add, 1=move, 2=modify, 3=subtract, 4=SC, 5=AuditValue, 6=AuditCapabilities, 7=Notify"
       ::= {acPMMegaco 2}



     -- ****************************************
     -- acPMCPCmdSuccessCount table entry
     -- ****************************************
     acPMCPCmdSuccessCountEntry OBJECT-TYPE
       SYNTAX AcPMCPCmdSuccessCountEntry
       MAX-ACCESS not-accessible
       STATUS current
       DESCRIPTION
           ""
       INDEX {acPMCPCmdSuccessCountCommandType,acPMCPCmdSuccessCountInterval}
       ::= {acPMCPCmdSuccessCountTable 1}



     -- ****************************************
     -- acPMCPCmdSuccessCount TABLE
     -- ****************************************
     AcPMCPCmdSuccessCountEntry ::= SEQUENCE {
       acPMCPCmdSuccessCountCommandType                INTEGER,
       acPMCPCmdSuccessCountInterval                   Unsigned32,
       acPMCPCmdSuccessCountVal                        Gauge32,
       acPMCPCmdSuccessCountTotal                      Integer32
     }



     acPMCPCmdSuccessCountCommandType OBJECT-TYPE
       SYNTAX INTEGER {
                  add(0)
,
                  move(1)
,
                  modify(2)
,
                  subtract(3)
,
                  sc(4)
,
                  auditValue(5)
,
                  auditCapabilities(6)
,
                  notify(7)

                  }
       MAX-ACCESS not-accessible
       STATUS current
       DESCRIPTION
           "Command type:
 0=add, 1=move, 2=modify, 3=subtract, 4=SC, 5=AuditValue, 6=AuditCapabilities,
7=Notify."
       ::= {acPMCPCmdSuccessCountEntry 1}



     acPMCPCmdSuccessCountInterval OBJECT-TYPE
       SYNTAX Unsigned32 (0..2)
       MAX-ACCESS not-accessible
       STATUS current
       DESCRIPTION
           "Interval index.
0 - current period (incomplete monitoring - mid period).
1 - Last full period.
2 - One before last."
       ::= {acPMCPCmdSuccessCountEntry 2}



     acPMCPCmdSuccessCountVal OBJECT-TYPE
       SYNTAX Gauge32
       MAX-ACCESS read-only
       STATUS current
       DESCRIPTION
           "Value of gauge or counter."
       ::= {acPMCPCmdSuccessCountEntry 3}



     acPMCPCmdSuccessCountTotal OBJECT-TYPE
       SYNTAX Integer32 (-1..2147483647)
       MAX-ACCESS read-only
       STATUS current
       DESCRIPTION
           "Total since last reset."
       ::= {acPMCPCmdSuccessCountEntry 4}



     -- ****************************************
     -- acPMCPCmdFailureCount table declaration
     -- ****************************************
     acPMCPCmdFailureCountTable OBJECT-TYPE
       SYNTAX SEQUENCE OF AcPMCPCmdFailureCountEntry
       MAX-ACCESS not-accessible
       STATUS current
       DESCRIPTION
           "Number of failing commands, per command type. Index: 0=add, 1=move, 2=modify, 3=subtract, 4=SC, 5=AuditValue, 6=AuditCapabilities, 7=Notify"
       ::= {acPMMegaco 3}



     -- ****************************************
     -- acPMCPCmdFailureCount table entry
     -- ****************************************
     acPMCPCmdFailureCountEntry OBJECT-TYPE
       SYNTAX AcPMCPCmdFailureCountEntry
       MAX-ACCESS not-accessible
       STATUS current
       DESCRIPTION
           ""
       INDEX {acPMCPCmdFailureCountCommandType,acPMCPCmdFailureCountInterval}
       ::= {acPMCPCmdFailureCountTable 1}



     -- ****************************************
     -- acPMCPCmdFailureCount TABLE
     -- ****************************************
     AcPMCPCmdFailureCountEntry ::= SEQUENCE {
       acPMCPCmdFailureCountCommandType                INTEGER,
       acPMCPCmdFailureCountInterval                   Unsigned32,
       acPMCPCmdFailureCountVal                        Gauge32,
       acPMCPCmdFailureCountTotal                      Integer32
     }



     acPMCPCmdFailureCountCommandType OBJECT-TYPE
       SYNTAX INTEGER {
                  add(0)
,
                  move(1)
,
                  modify(2)
,
                  subtract(3)
,
                  sc(4)
,
                  auditValue(5)
,
                  auditCapabilities(6)
,
                  notify(7)

                  }
       MAX-ACCESS not-accessible
       STATUS current
       DESCRIPTION
           "Command type:
 0=add, 1=move, 2=modify, 3=subtract, 4=SC, 5=AuditValue, 6=AuditCapabilities,
7=Notify."
       ::= {acPMCPCmdFailureCountEntry 1}



     acPMCPCmdFailureCountInterval OBJECT-TYPE
       SYNTAX Unsigned32 (0..2)
       MAX-ACCESS not-accessible
       STATUS current
       DESCRIPTION
           "Interval index.
0 - current period (incomplete monitoring - mid period).
1 - Last full period.
2 - One before last."
       ::= {acPMCPCmdFailureCountEntry 2}



     acPMCPCmdFailureCountVal OBJECT-TYPE
       SYNTAX Gauge32
       MAX-ACCESS read-only
       STATUS current
       DESCRIPTION
           "Value of gauge or counter."
       ::= {acPMCPCmdFailureCountEntry 3}



     acPMCPCmdFailureCountTotal OBJECT-TYPE
       SYNTAX Integer32 (-1..2147483647)
       MAX-ACCESS read-only
       STATUS current
       DESCRIPTION
           "Total since last reset."
       ::= {acPMCPCmdFailureCountEntry 4}



     -- ****************************************
     -- acPMcpUMTSHandOverCount table declaration
     -- ****************************************
     acPMcpUMTSHandOverCountTable OBJECT-TYPE
       SYNTAX SEQUENCE OF AcPMcpUMTSHandOverCountEntry
       MAX-ACCESS not-accessible
       STATUS current
       DESCRIPTION
           "Number of active channels per trunk (index: trunk number)."
       ::= {acPMMegaco 4}



     -- ****************************************
     -- acPMcpUMTSHandOverCount table entry
     -- ****************************************
     acPMcpUMTSHandOverCountEntry OBJECT-TYPE
       SYNTAX AcPMcpUMTSHandOverCountEntry
       MAX-ACCESS not-accessible
       STATUS current
       DESCRIPTION
           ""
       INDEX {acPMcpUMTSHandOverCountInterval}
       ::= {acPMcpUMTSHandOverCountTable 1}



     -- ****************************************
     -- acPMcpUMTSHandOverCount TABLE
     -- ****************************************
     AcPMcpUMTSHandOverCountEntry ::= SEQUENCE {
       acPMcpUMTSHandOverCountInterval                 Unsigned32,
       acPMcpUMTSHandOverCountVal                      Gauge32
     }



     acPMcpUMTSHandOverCountInterval OBJECT-TYPE
       SYNTAX Unsigned32 (0..2)
       MAX-ACCESS not-accessible
       STATUS current
       DESCRIPTION
           "Interval index.
0 - current period (incomplete monitoring - mid period).
1 - Last full period.
2 - One before last."
       ::= {acPMcpUMTSHandOverCountEntry 1}



     acPMcpUMTSHandOverCountVal OBJECT-TYPE
       SYNTAX Gauge32
       MAX-ACCESS read-only
       STATUS current
       DESCRIPTION
           "Value of gauge or counter."
       ::= {acPMcpUMTSHandOverCountEntry 2}



     -- ****************************************
     -- acPMMegacoAddFailureCount table declaration
     -- ****************************************
     acPMMegacoAddFailureCountTable OBJECT-TYPE
       SYNTAX SEQUENCE OF AcPMMegacoAddFailureCountEntry
       MAX-ACCESS not-accessible
       STATUS current
       DESCRIPTION
           "Number of Megaco failures for Add"
       ::= {acPMMegaco 5}



     -- ****************************************
     -- acPMMegacoAddFailureCount table entry
     -- ****************************************
     acPMMegacoAddFailureCountEntry OBJECT-TYPE
       SYNTAX AcPMMegacoAddFailureCountEntry
       MAX-ACCESS not-accessible
       STATUS current
       DESCRIPTION
           ""
       INDEX {acPMMegacoAddFailureCountInterval}
       ::= {acPMMegacoAddFailureCountTable 1}



     -- ****************************************
     -- acPMMegacoAddFailureCount TABLE
     -- ****************************************
     AcPMMegacoAddFailureCountEntry ::= SEQUENCE {
       acPMMegacoAddFailureCountInterval               Unsigned32,
       acPMMegacoAddFailureCountVal                    Gauge32
     }



     acPMMegacoAddFailureCountInterval OBJECT-TYPE
       SYNTAX Unsigned32 (0..2)
       MAX-ACCESS not-accessible
       STATUS current
       DESCRIPTION
           "Interval index.
0 - current period (incomplete monitoring - mid period).
1 - Last full period.
2 - One before last."
       ::= {acPMMegacoAddFailureCountEntry 1}



     acPMMegacoAddFailureCountVal OBJECT-TYPE
       SYNTAX Gauge32
       MAX-ACCESS read-only
       STATUS current
       DESCRIPTION
           "Value of gauge or counter."
       ::= {acPMMegacoAddFailureCountEntry 2}



     -- ****************************************
     -- acPMMegacoModifyFailureCount table declaration
     -- ****************************************
     acPMMegacoModifyFailureCountTable OBJECT-TYPE
       SYNTAX SEQUENCE OF AcPMMegacoModifyFailureCountEntry
       MAX-ACCESS not-accessible
       STATUS current
       DESCRIPTION
           "Number of Megaco failures for Modify "
       ::= {acPMMegaco 6}



     -- ****************************************
     -- acPMMegacoModifyFailureCount table entry
     -- ****************************************
     acPMMegacoModifyFailureCountEntry OBJECT-TYPE
       SYNTAX AcPMMegacoModifyFailureCountEntry
       MAX-ACCESS not-accessible
       STATUS current
       DESCRIPTION
           ""
       INDEX {acPMMegacoModifyFailureCountInterval}
       ::= {acPMMegacoModifyFailureCountTable 1}



     -- ****************************************
     -- acPMMegacoModifyFailureCount TABLE
     -- ****************************************
     AcPMMegacoModifyFailureCountEntry ::= SEQUENCE {
       acPMMegacoModifyFailureCountInterval            Unsigned32,
       acPMMegacoModifyFailureCountVal                 Gauge32
     }



     acPMMegacoModifyFailureCountInterval OBJECT-TYPE
       SYNTAX Unsigned32 (0..2)
       MAX-ACCESS not-accessible
       STATUS current
       DESCRIPTION
           "Interval index.
0 - current period (incomplete monitoring - mid period).
1 - Last full period.
2 - One before last."
       ::= {acPMMegacoModifyFailureCountEntry 1}



     acPMMegacoModifyFailureCountVal OBJECT-TYPE
       SYNTAX Gauge32
       MAX-ACCESS read-only
       STATUS current
       DESCRIPTION
           "Value of gauge or counter."
       ::= {acPMMegacoModifyFailureCountEntry 2}



     -- ****************************************
     -- acPMMegacoSuccessfulAddWithLoopback table declaration
     -- ****************************************
     acPMMegacoSuccessfulAddWithLoopbackTable OBJECT-TYPE
       SYNTAX SEQUENCE OF AcPMMegacoSuccessfulAddWithLoopbackEntry
       MAX-ACCESS not-accessible
       STATUS current
       DESCRIPTION
           "Number of successful Megaco Add commands with  loopback."
       ::= {acPMMegaco 7}



     -- ****************************************
     -- acPMMegacoSuccessfulAddWithLoopback table entry
     -- ****************************************
     acPMMegacoSuccessfulAddWithLoopbackEntry OBJECT-TYPE
       SYNTAX AcPMMegacoSuccessfulAddWithLoopbackEntry
       MAX-ACCESS not-accessible
       STATUS current
       DESCRIPTION
           ""
       INDEX {acPMMegacoSuccessfulAddWithLoopbackInterval}
       ::= {acPMMegacoSuccessfulAddWithLoopbackTable 1}



     -- ****************************************
     -- acPMMegacoSuccessfulAddWithLoopback TABLE
     -- ****************************************
     AcPMMegacoSuccessfulAddWithLoopbackEntry ::= SEQUENCE {
       acPMMegacoSuccessfulAddWithLoopbackInterval     Unsigned32,
       acPMMegacoSuccessfulAddWithLoopbackVal          Gauge32
     }



     acPMMegacoSuccessfulAddWithLoopbackInterval OBJECT-TYPE
       SYNTAX Unsigned32 (0..2)
       MAX-ACCESS not-accessible
       STATUS current
       DESCRIPTION
           "Interval index.
0 - current period (incomplete monitoring - mid period).
1 - Last full period.
2 - One before last."
       ::= {acPMMegacoSuccessfulAddWithLoopbackEntry 1}



     acPMMegacoSuccessfulAddWithLoopbackVal OBJECT-TYPE
       SYNTAX Gauge32
       MAX-ACCESS read-only
       STATUS current
       DESCRIPTION
           "Value of gauge or counter."
       ::= {acPMMegacoSuccessfulAddWithLoopbackEntry 2}



     -- ****************************************
     -- acPMMegacoFailedAddWithLoopback table declaration
     -- ****************************************
     acPMMegacoFailedAddWithLoopbackTable OBJECT-TYPE
       SYNTAX SEQUENCE OF AcPMMegacoFailedAddWithLoopbackEntry
       MAX-ACCESS not-accessible
       STATUS current
       DESCRIPTION
           "Number of failed  Megaco Add commands with  loopback."
       ::= {acPMMegaco 8}



     -- ****************************************
     -- acPMMegacoFailedAddWithLoopback table entry
     -- ****************************************
     acPMMegacoFailedAddWithLoopbackEntry OBJECT-TYPE
       SYNTAX AcPMMegacoFailedAddWithLoopbackEntry
       MAX-ACCESS not-accessible
       STATUS current
       DESCRIPTION
           ""
       INDEX {acPMMegacoFailedAddWithLoopbackInterval}
       ::= {acPMMegacoFailedAddWithLoopbackTable 1}



     -- ****************************************
     -- acPMMegacoFailedAddWithLoopback TABLE
     -- ****************************************
     AcPMMegacoFailedAddWithLoopbackEntry ::= SEQUENCE {
       acPMMegacoFailedAddWithLoopbackInterval         Unsigned32,
       acPMMegacoFailedAddWithLoopbackVal              Gauge32
     }



     acPMMegacoFailedAddWithLoopbackInterval OBJECT-TYPE
       SYNTAX Unsigned32 (0..2)
       MAX-ACCESS not-accessible
       STATUS current
       DESCRIPTION
           "Interval index.
0 - current period (incomplete monitoring - mid period).
1 - Last full period.
2 - One before last."
       ::= {acPMMegacoFailedAddWithLoopbackEntry 1}



     acPMMegacoFailedAddWithLoopbackVal OBJECT-TYPE
       SYNTAX Gauge32
       MAX-ACCESS read-only
       STATUS current
       DESCRIPTION
           "Value of gauge or counter."
       ::= {acPMMegacoFailedAddWithLoopbackEntry 2}



     -- ****************************************
     -- acPMMegacoOutgoingCommandSuccessCount table declaration
     -- ****************************************
     acPMMegacoOutgoingCommandSuccessCountTable OBJECT-TYPE
       SYNTAX SEQUENCE OF AcPMMegacoOutgoingCommandSuccessCountEntry
       MAX-ACCESS not-accessible
       STATUS current
       DESCRIPTION
           "Number of successful Megaco outgoing commands."
       ::= {acPMMegaco 9}



     -- ****************************************
     -- acPMMegacoOutgoingCommandSuccessCount table entry
     -- ****************************************
     acPMMegacoOutgoingCommandSuccessCountEntry OBJECT-TYPE
       SYNTAX AcPMMegacoOutgoingCommandSuccessCountEntry
       MAX-ACCESS not-accessible
       STATUS current
       DESCRIPTION
           ""
       INDEX {acPMMegacoOutgoingCommandSuccessCountInterval}
       ::= {acPMMegacoOutgoingCommandSuccessCountTable 1}



     -- ****************************************
     -- acPMMegacoOutgoingCommandSuccessCount TABLE
     -- ****************************************
     AcPMMegacoOutgoingCommandSuccessCountEntry ::= SEQUENCE {
       acPMMegacoOutgoingCommandSuccessCountInterval   Unsigned32,
       acPMMegacoOutgoingCommandSuccessCountVal        Gauge32
     }



     acPMMegacoOutgoingCommandSuccessCountInterval OBJECT-TYPE
       SYNTAX Unsigned32 (0..2)
       MAX-ACCESS not-accessible
       STATUS current
       DESCRIPTION
           "Interval index.
0 - current period (incomplete monitoring - mid period).
1 - Last full period.
2 - One before last."
       ::= {acPMMegacoOutgoingCommandSuccessCountEntry 1}



     acPMMegacoOutgoingCommandSuccessCountVal OBJECT-TYPE
       SYNTAX Gauge32
       MAX-ACCESS read-only
       STATUS current
       DESCRIPTION
           "Value of gauge or counter."
       ::= {acPMMegacoOutgoingCommandSuccessCountEntry 2}



     -- ****************************************
     -- acPMMegacoOutgoingCommandFailureCount table declaration
     -- ****************************************
     acPMMegacoOutgoingCommandFailureCountTable OBJECT-TYPE
       SYNTAX SEQUENCE OF AcPMMegacoOutgoingCommandFailureCountEntry
       MAX-ACCESS not-accessible
       STATUS current
       DESCRIPTION
           "Number of failed  Megaco  outgoing commands ."
       ::= {acPMMegaco 10}



     -- ****************************************
     -- acPMMegacoOutgoingCommandFailureCount table entry
     -- ****************************************
     acPMMegacoOutgoingCommandFailureCountEntry OBJECT-TYPE
       SYNTAX AcPMMegacoOutgoingCommandFailureCountEntry
       MAX-ACCESS not-accessible
       STATUS current
       DESCRIPTION
           ""
       INDEX {acPMMegacoOutgoingCommandFailureCountInterval}
       ::= {acPMMegacoOutgoingCommandFailureCountTable 1}



     -- ****************************************
     -- acPMMegacoOutgoingCommandFailureCount TABLE
     -- ****************************************
     AcPMMegacoOutgoingCommandFailureCountEntry ::= SEQUENCE {
       acPMMegacoOutgoingCommandFailureCountInterval   Unsigned32,
       acPMMegacoOutgoingCommandFailureCountVal        Gauge32
     }



     acPMMegacoOutgoingCommandFailureCountInterval OBJECT-TYPE
       SYNTAX Unsigned32 (0..2)
       MAX-ACCESS not-accessible
       STATUS current
       DESCRIPTION
           "Interval index.
0 - current period (incomplete monitoring - mid period).
1 - Last full period.
2 - One before last."
       ::= {acPMMegacoOutgoingCommandFailureCountEntry 1}



     acPMMegacoOutgoingCommandFailureCountVal OBJECT-TYPE
       SYNTAX Gauge32
       MAX-ACCESS read-only
       STATUS current
       DESCRIPTION
           "Value of gauge or counter."
       ::= {acPMMegacoOutgoingCommandFailureCountEntry 2}



     acPMMGCP OBJECT IDENTIFIER ::= {acPMControlData 51}


     -- ****************************************
     -- acPMMGCPRsipReasonCount table declaration
     -- ****************************************
     acPMMGCPRsipReasonCountTable OBJECT-TYPE
       SYNTAX SEQUENCE OF AcPMMGCPRsipReasonCountEntry
       MAX-ACCESS not-accessible
       STATUS current
       DESCRIPTION
           "Number of RSIPs, per reason code."
       ::= {acPMMGCP 1}



     -- ****************************************
     -- acPMMGCPRsipReasonCount table entry
     -- ****************************************
     acPMMGCPRsipReasonCountEntry OBJECT-TYPE
       SYNTAX AcPMMGCPRsipReasonCountEntry
       MAX-ACCESS not-accessible
       STATUS current
       DESCRIPTION
           ""
       INDEX {acPMMGCPRsipReasonCountReasonCode,acPMMGCPRsipReasonCountInterval}
       ::= {acPMMGCPRsipReasonCountTable 1}



     -- ****************************************
     -- acPMMGCPRsipReasonCount TABLE
     -- ****************************************
     AcPMMGCPRsipReasonCountEntry ::= SEQUENCE {
       acPMMGCPRsipReasonCountReasonCode               INTEGER,
       acPMMGCPRsipReasonCountInterval                 Unsigned32,
       acPMMGCPRsipReasonCountVal                      Counter32
     }



     acPMMGCPRsipReasonCountReasonCode OBJECT-TYPE
       SYNTAX INTEGER {
                  restart(0)
,
                  forced(1)
,
                  disconnected(2)
,
                  keepAlive(3)
,
                  graceful(4)
,
                  cancelGraceful(5)
,
                  resetBoard(6)
,
                  nonVoice(7)

                  }
       MAX-ACCESS not-accessible
       STATUS current
       DESCRIPTION
           "Reason code. Index: 0=Restart, 1=Forced, 2=Disconnected, 3=KeepAlive,
4=Graceful, 5=CancelGraceful, 6=ResetBoard, 7=NonVoice."
       ::= {acPMMGCPRsipReasonCountEntry 1}



     acPMMGCPRsipReasonCountInterval OBJECT-TYPE
       SYNTAX Unsigned32 (0..2)
       MAX-ACCESS not-accessible
       STATUS current
       DESCRIPTION
           "Interval index.
0 - current period (incomplete monitoring - mid period).
1 - Last full period.
2 - One before last."
       ::= {acPMMGCPRsipReasonCountEntry 2}



     acPMMGCPRsipReasonCountVal OBJECT-TYPE
       SYNTAX Counter32
       MAX-ACCESS read-only
       STATUS current
       DESCRIPTION
           "Value of gauge or counter."
       ::= {acPMMGCPRsipReasonCountEntry 3}



     -- ****************************************
     -- acPMMGCPGeneratedDLCX table declaration
     -- ****************************************
     acPMMGCPGeneratedDLCXTable OBJECT-TYPE
       SYNTAX SEQUENCE OF AcPMMGCPGeneratedDLCXEntry
       MAX-ACCESS not-accessible
       STATUS current
       DESCRIPTION
           "This parameter counts the number of gateway-generated DLCX commands (as opposed to DLCX commands received from the call-agent)."
       ::= {acPMMGCP 2}



     -- ****************************************
     -- acPMMGCPGeneratedDLCX table entry
     -- ****************************************
     acPMMGCPGeneratedDLCXEntry OBJECT-TYPE
       SYNTAX AcPMMGCPGeneratedDLCXEntry
       MAX-ACCESS not-accessible
       STATUS current
       DESCRIPTION
           ""
       INDEX {acPMMGCPGeneratedDLCXInterval}
       ::= {acPMMGCPGeneratedDLCXTable 1}



     -- ****************************************
     -- acPMMGCPGeneratedDLCX TABLE
     -- ****************************************
     AcPMMGCPGeneratedDLCXEntry ::= SEQUENCE {
       acPMMGCPGeneratedDLCXInterval                   Unsigned32,
       acPMMGCPGeneratedDLCXVal                        Counter32
     }



     acPMMGCPGeneratedDLCXInterval OBJECT-TYPE
       SYNTAX Unsigned32 (0..2)
       MAX-ACCESS not-accessible
       STATUS current
       DESCRIPTION
           "Interval index.
0 - current period (incomplete monitoring - mid period).
1 - Last full period.
2 - One before last."
       ::= {acPMMGCPGeneratedDLCXEntry 1}



     acPMMGCPGeneratedDLCXVal OBJECT-TYPE
       SYNTAX Counter32
       MAX-ACCESS read-only
       STATUS current
       DESCRIPTION
           "Value of gauge or counter."
       ::= {acPMMGCPGeneratedDLCXEntry 2}



     -- ****************************************
     -- acPMMGCPCommandSuccessCount table declaration
     -- ****************************************
     acPMMGCPCommandSuccessCountTable OBJECT-TYPE
       SYNTAX SEQUENCE OF AcPMMGCPCommandSuccessCountEntry
       MAX-ACCESS not-accessible
       STATUS current
       DESCRIPTION
           "Number of successful commands, per command type. Index: EPCF (0),CRCX (1),MDCX (2),DLCX (3),RQNT (4),NTFY (5),AUEP(6),AUCX (7),RSIP(8)."
       ::= {acPMMGCP 3}



     -- ****************************************
     -- acPMMGCPCommandSuccessCount table entry
     -- ****************************************
     acPMMGCPCommandSuccessCountEntry OBJECT-TYPE
       SYNTAX AcPMMGCPCommandSuccessCountEntry
       MAX-ACCESS not-accessible
       STATUS current
       DESCRIPTION
           ""
       INDEX {acPMMGCPCommandSuccessCountCommandType,acPMMGCPCommandSuccessCountInterval}
       ::= {acPMMGCPCommandSuccessCountTable 1}



     -- ****************************************
     -- acPMMGCPCommandSuccessCount TABLE
     -- ****************************************
     AcPMMGCPCommandSuccessCountEntry ::= SEQUENCE {
       acPMMGCPCommandSuccessCountCommandType          INTEGER,
       acPMMGCPCommandSuccessCountInterval             Unsigned32,
       acPMMGCPCommandSuccessCountVal                  Gauge32,
       acPMMGCPCommandSuccessCountTotal                Integer32
     }



     acPMMGCPCommandSuccessCountCommandType OBJECT-TYPE
       SYNTAX INTEGER {
                  add(0)
,
                  move(1)
,
                  modify(2)
,
                  subtract(3)
,
                  sc(4)
,
                  auditValue(5)
,
                  auditCapabilities(6)
,
                  notify(7)

                  }
       MAX-ACCESS not-accessible
       STATUS current
       DESCRIPTION
           "Command type:EPCF (0),CRCX (1),MDCX (2),DLCX (3),RQNT (4),NTFY
(5),AUEP(6),AUCX (7),RSIP(8)."
       ::= {acPMMGCPCommandSuccessCountEntry 1}



     acPMMGCPCommandSuccessCountInterval OBJECT-TYPE
       SYNTAX Unsigned32 (0..2)
       MAX-ACCESS not-accessible
       STATUS current
       DESCRIPTION
           "Interval index.
0 - current period (incomplete monitoring - mid period).
1 - Last full period.
2 - One before last."
       ::= {acPMMGCPCommandSuccessCountEntry 2}



     acPMMGCPCommandSuccessCountVal OBJECT-TYPE
       SYNTAX Gauge32
       MAX-ACCESS read-only
       STATUS current
       DESCRIPTION
           "Value of gauge or counter."
       ::= {acPMMGCPCommandSuccessCountEntry 3}



     acPMMGCPCommandSuccessCountTotal OBJECT-TYPE
       SYNTAX Integer32 (-1..2147483647)
       MAX-ACCESS read-only
       STATUS current
       DESCRIPTION
           "Total since last reset."
       ::= {acPMMGCPCommandSuccessCountEntry 4}



     -- ****************************************
     -- acPMMGCPCommandFailureCount table declaration
     -- ****************************************
     acPMMGCPCommandFailureCountTable OBJECT-TYPE
       SYNTAX SEQUENCE OF AcPMMGCPCommandFailureCountEntry
       MAX-ACCESS not-accessible
       STATUS current
       DESCRIPTION
           "Number of failing commands, per command type. Index: EPCF (0),CRCX (1),MDCX (2),DLCX (3),RQNT (4),NTFY (5),AUEP(6),AUCX (7),RSIP(8)."
       ::= {acPMMGCP 4}



     -- ****************************************
     -- acPMMGCPCommandFailureCount table entry
     -- ****************************************
     acPMMGCPCommandFailureCountEntry OBJECT-TYPE
       SYNTAX AcPMMGCPCommandFailureCountEntry
       MAX-ACCESS not-accessible
       STATUS current
       DESCRIPTION
           ""
       INDEX {acPMMGCPCommandFailureCountCommandType,acPMMGCPCommandFailureCountInterval}
       ::= {acPMMGCPCommandFailureCountTable 1}



     -- ****************************************
     -- acPMMGCPCommandFailureCount TABLE
     -- ****************************************
     AcPMMGCPCommandFailureCountEntry ::= SEQUENCE {
       acPMMGCPCommandFailureCountCommandType          INTEGER,
       acPMMGCPCommandFailureCountInterval             Unsigned32,
       acPMMGCPCommandFailureCountVal                  Gauge32,
       acPMMGCPCommandFailureCountTotal                Integer32
     }



     acPMMGCPCommandFailureCountCommandType OBJECT-TYPE
       SYNTAX INTEGER {
                  add(0)
,
                  move(1)
,
                  modify(2)
,
                  subtract(3)
,
                  sc(4)
,
                  auditValue(5)
,
                  auditCapabilities(6)
,
                  notify(7)

                  }
       MAX-ACCESS not-accessible
       STATUS current
       DESCRIPTION
           "Command type:EPCF (0),CRCX (1),MDCX (2),DLCX (3),RQNT (4),NTFY
(5),AUEP(6),AUCX (7),RSIP(8)."
       ::= {acPMMGCPCommandFailureCountEntry 1}



     acPMMGCPCommandFailureCountInterval OBJECT-TYPE
       SYNTAX Unsigned32 (0..2)
       MAX-ACCESS not-accessible
       STATUS current
       DESCRIPTION
           "Interval index.
0 - current period (incomplete monitoring - mid period).
1 - Last full period.
2 - One before last."
       ::= {acPMMGCPCommandFailureCountEntry 2}



     acPMMGCPCommandFailureCountVal OBJECT-TYPE
       SYNTAX Gauge32
       MAX-ACCESS read-only
       STATUS current
       DESCRIPTION
           "Value of gauge or counter."
       ::= {acPMMGCPCommandFailureCountEntry 3}



     acPMMGCPCommandFailureCountTotal OBJECT-TYPE
       SYNTAX Integer32 (-1..2147483647)
       MAX-ACCESS read-only
       STATUS current
       DESCRIPTION
           "Total since last reset."
       ::= {acPMMGCPCommandFailureCountEntry 4}



     -- ****************************************
     -- acPMMGCPLoopbackCRCX table declaration
     -- ****************************************
     acPMMGCPLoopbackCRCXTable OBJECT-TYPE
       SYNTAX SEQUENCE OF AcPMMGCPLoopbackCRCXEntry
       MAX-ACCESS not-accessible
       STATUS current
       DESCRIPTION
           ""
       ::= {acPMMGCP 5}



     -- ****************************************
     -- acPMMGCPLoopbackCRCX table entry
     -- ****************************************
     acPMMGCPLoopbackCRCXEntry OBJECT-TYPE
       SYNTAX AcPMMGCPLoopbackCRCXEntry
       MAX-ACCESS not-accessible
       STATUS current
       DESCRIPTION
           ""
       INDEX {acPMMGCPLoopbackCRCXInterval}
       ::= {acPMMGCPLoopbackCRCXTable 1}



     -- ****************************************
     -- acPMMGCPLoopbackCRCX TABLE
     -- ****************************************
     AcPMMGCPLoopbackCRCXEntry ::= SEQUENCE {
       acPMMGCPLoopbackCRCXInterval                    Unsigned32,
       acPMMGCPLoopbackCRCXVal                         Counter32
     }



     acPMMGCPLoopbackCRCXInterval OBJECT-TYPE
       SYNTAX Unsigned32 (0..2)
       MAX-ACCESS not-accessible
       STATUS current
       DESCRIPTION
           "Interval index.
0 - current period (incomplete monitoring - mid period).
1 - Last full period.
2 - One before last."
       ::= {acPMMGCPLoopbackCRCXEntry 1}



     acPMMGCPLoopbackCRCXVal OBJECT-TYPE
       SYNTAX Counter32
       MAX-ACCESS read-only
       STATUS current
       DESCRIPTION
           "Value of gauge or counter."
       ::= {acPMMGCPLoopbackCRCXEntry 2}



     -- ****************************************
     -- acPMMGCPFailedLoopbackCRCX table declaration
     -- ****************************************
     acPMMGCPFailedLoopbackCRCXTable OBJECT-TYPE
       SYNTAX SEQUENCE OF AcPMMGCPFailedLoopbackCRCXEntry
       MAX-ACCESS not-accessible
       STATUS current
       DESCRIPTION
           ""
       ::= {acPMMGCP 6}



     -- ****************************************
     -- acPMMGCPFailedLoopbackCRCX table entry
     -- ****************************************
     acPMMGCPFailedLoopbackCRCXEntry OBJECT-TYPE
       SYNTAX AcPMMGCPFailedLoopbackCRCXEntry
       MAX-ACCESS not-accessible
       STATUS current
       DESCRIPTION
           ""
       INDEX {acPMMGCPFailedLoopbackCRCXInterval}
       ::= {acPMMGCPFailedLoopbackCRCXTable 1}



     -- ****************************************
     -- acPMMGCPFailedLoopbackCRCX TABLE
     -- ****************************************
     AcPMMGCPFailedLoopbackCRCXEntry ::= SEQUENCE {
       acPMMGCPFailedLoopbackCRCXInterval              Unsigned32,
       acPMMGCPFailedLoopbackCRCXVal                   Counter32
     }



     acPMMGCPFailedLoopbackCRCXInterval OBJECT-TYPE
       SYNTAX Unsigned32 (0..2)
       MAX-ACCESS not-accessible
       STATUS current
       DESCRIPTION
           "Interval index.
0 - current period (incomplete monitoring - mid period).
1 - Last full period.
2 - One before last."
       ::= {acPMMGCPFailedLoopbackCRCXEntry 1}



     acPMMGCPFailedLoopbackCRCXVal OBJECT-TYPE
       SYNTAX Counter32
       MAX-ACCESS read-only
       STATUS current
       DESCRIPTION
           "Value of gauge or counter."
       ::= {acPMMGCPFailedLoopbackCRCXEntry 2}



     -- ****************************************
     -- acPMMGCPGeneratedNTFY table declaration
     -- ****************************************
     acPMMGCPGeneratedNTFYTable OBJECT-TYPE
       SYNTAX SEQUENCE OF AcPMMGCPGeneratedNTFYEntry
       MAX-ACCESS not-accessible
       STATUS current
       DESCRIPTION
           ""
       ::= {acPMMGCP 7}



     -- ****************************************
     -- acPMMGCPGeneratedNTFY table entry
     -- ****************************************
     acPMMGCPGeneratedNTFYEntry OBJECT-TYPE
       SYNTAX AcPMMGCPGeneratedNTFYEntry
       MAX-ACCESS not-accessible
       STATUS current
       DESCRIPTION
           ""
       INDEX {acPMMGCPGeneratedNTFYInterval}
       ::= {acPMMGCPGeneratedNTFYTable 1}



     -- ****************************************
     -- acPMMGCPGeneratedNTFY TABLE
     -- ****************************************
     AcPMMGCPGeneratedNTFYEntry ::= SEQUENCE {
       acPMMGCPGeneratedNTFYInterval                   Unsigned32,
       acPMMGCPGeneratedNTFYVal                        Counter32
     }



     acPMMGCPGeneratedNTFYInterval OBJECT-TYPE
       SYNTAX Unsigned32 (0..2)
       MAX-ACCESS not-accessible
       STATUS current
       DESCRIPTION
           "Interval index.
0 - current period (incomplete monitoring - mid period).
1 - Last full period.
2 - One before last."
       ::= {acPMMGCPGeneratedNTFYEntry 1}



     acPMMGCPGeneratedNTFYVal OBJECT-TYPE
       SYNTAX Counter32
       MAX-ACCESS read-only
       STATUS current
       DESCRIPTION
           "Value of gauge or counter."
       ::= {acPMMGCPGeneratedNTFYEntry 2}



     -- ****************************************
     -- acPMMGCPFailedNTFYResponses table declaration
     -- ****************************************
     acPMMGCPFailedNTFYResponsesTable OBJECT-TYPE
       SYNTAX SEQUENCE OF AcPMMGCPFailedNTFYResponsesEntry
       MAX-ACCESS not-accessible
       STATUS current
       DESCRIPTION
           ""
       ::= {acPMMGCP 8}



     -- ****************************************
     -- acPMMGCPFailedNTFYResponses table entry
     -- ****************************************
     acPMMGCPFailedNTFYResponsesEntry OBJECT-TYPE
       SYNTAX AcPMMGCPFailedNTFYResponsesEntry
       MAX-ACCESS not-accessible
       STATUS current
       DESCRIPTION
           ""
       INDEX {acPMMGCPFailedNTFYResponsesInterval}
       ::= {acPMMGCPFailedNTFYResponsesTable 1}



     -- ****************************************
     -- acPMMGCPFailedNTFYResponses TABLE
     -- ****************************************
     AcPMMGCPFailedNTFYResponsesEntry ::= SEQUENCE {
       acPMMGCPFailedNTFYResponsesInterval             Unsigned32,
       acPMMGCPFailedNTFYResponsesVal                  Counter32
     }



     acPMMGCPFailedNTFYResponsesInterval OBJECT-TYPE
       SYNTAX Unsigned32 (0..2)
       MAX-ACCESS not-accessible
       STATUS current
       DESCRIPTION
           "Interval index.
0 - current period (incomplete monitoring - mid period).
1 - Last full period.
2 - One before last."
       ::= {acPMMGCPFailedNTFYResponsesEntry 1}



     acPMMGCPFailedNTFYResponsesVal OBJECT-TYPE
       SYNTAX Counter32
       MAX-ACCESS read-only
       STATUS current
       DESCRIPTION
           "Value of gauge or counter."
       ::= {acPMMGCPFailedNTFYResponsesEntry 2}



     -- ****************************************
     -- acPMMGCPFailedRSIPResponses table declaration
     -- ****************************************
     acPMMGCPFailedRSIPResponsesTable OBJECT-TYPE
       SYNTAX SEQUENCE OF AcPMMGCPFailedRSIPResponsesEntry
       MAX-ACCESS not-accessible
       STATUS current
       DESCRIPTION
           ""
       ::= {acPMMGCP 9}



     -- ****************************************
     -- acPMMGCPFailedRSIPResponses table entry
     -- ****************************************
     acPMMGCPFailedRSIPResponsesEntry OBJECT-TYPE
       SYNTAX AcPMMGCPFailedRSIPResponsesEntry
       MAX-ACCESS not-accessible
       STATUS current
       DESCRIPTION
           ""
       INDEX {acPMMGCPFailedRSIPResponsesInterval}
       ::= {acPMMGCPFailedRSIPResponsesTable 1}



     -- ****************************************
     -- acPMMGCPFailedRSIPResponses TABLE
     -- ****************************************
     AcPMMGCPFailedRSIPResponsesEntry ::= SEQUENCE {
       acPMMGCPFailedRSIPResponsesInterval             Unsigned32,
       acPMMGCPFailedRSIPResponsesVal                  Counter32
     }



     acPMMGCPFailedRSIPResponsesInterval OBJECT-TYPE
       SYNTAX Unsigned32 (0..2)
       MAX-ACCESS not-accessible
       STATUS current
       DESCRIPTION
           "Interval index.
0 - current period (incomplete monitoring - mid period).
1 - Last full period.
2 - One before last."
       ::= {acPMMGCPFailedRSIPResponsesEntry 1}



     acPMMGCPFailedRSIPResponsesVal OBJECT-TYPE
       SYNTAX Counter32
       MAX-ACCESS read-only
       STATUS current
       DESCRIPTION
           "Value of gauge or counter."
       ::= {acPMMGCPFailedRSIPResponsesEntry 2}



     -- ****************************************
     -- acPMMGCPFailedCRCXResponses table declaration
     -- ****************************************
     acPMMGCPFailedCRCXResponsesTable OBJECT-TYPE
       SYNTAX SEQUENCE OF AcPMMGCPFailedCRCXResponsesEntry
       MAX-ACCESS not-accessible
       STATUS current
       DESCRIPTION
           "Number of failed responses to CRCX commands, per reason code."
       ::= {acPMMGCP 10}



     -- ****************************************
     -- acPMMGCPFailedCRCXResponses table entry
     -- ****************************************
     acPMMGCPFailedCRCXResponsesEntry OBJECT-TYPE
       SYNTAX AcPMMGCPFailedCRCXResponsesEntry
       MAX-ACCESS not-accessible
       STATUS current
       DESCRIPTION
           ""
       INDEX {acPMMGCPFailedCRCXResponsesReasonCode,acPMMGCPFailedCRCXResponsesInterval}
       ::= {acPMMGCPFailedCRCXResponsesTable 1}



     -- ****************************************
     -- acPMMGCPFailedCRCXResponses TABLE
     -- ****************************************
     AcPMMGCPFailedCRCXResponsesEntry ::= SEQUENCE {
       acPMMGCPFailedCRCXResponsesReasonCode           INTEGER,
       acPMMGCPFailedCRCXResponsesInterval             Unsigned32,
       acPMMGCPFailedCRCXResponsesVal                  Counter32
     }



     acPMMGCPFailedCRCXResponsesReasonCode OBJECT-TYPE
       SYNTAX INTEGER {
                  reasoncode-400(0)
,
                  reasoncode-401(1)
,
                  reasoncode-402(2)
,
                  reasoncode-403(3)
,
                  reasoncode-404(4)
,
                  reasoncode-405(5)
,
                  reasoncode-406(6)
,
                  reasoncode-407(7)
,
                  reasoncode-409(8)
,
                  reasoncode-410(9)
,
                  reasoncode-500(10)
,
                  reasoncode-501(11)
,
                  reasoncode-502(12)
,
                  reasoncode-503(13)
,
                  reasoncode-504(14)
,
                  reasoncode-505(15)
,
                  reasoncode-506(16)
,
                  reasoncode-507(17)
,
                  reasoncode-508(18)
,
                  reasoncode-509(19)
,
                  reasoncode-510(20)
,
                  reasoncode-511(21)
,
                  reasoncode-512(22)
,
                  reasoncode-513(23)
,
                  reasoncode-514(24)
,
                  reasoncode-515(25)
,
                  reasoncode-516(26)
,
                  reasoncode-517(27)
,
                  reasoncode-518(28)
,
                  reasoncode-519(29)
,
                  reasoncode-520(30)
,
                  reasoncode-521(31)
,
                  reasoncode-522(32)
,
                  reasoncode-523(33)
,
                  reasoncode-524(34)
,
                  reasoncode-525(35)
,
                  reasoncode-526(36)
,
                  reasoncode-527(37)
,
                  reasoncode-528(38)
,
                  reasoncode-529(39)
,
                  reasoncode-530(40)
,
                  reasoncode-531(41)
,
                  reasoncode-532(42)
,
                  reasoncode-533(43)
,
                  reasoncode-534(44)
,
                  reasoncode-535(45)
,
                  reasoncode-536(46)
,
                  reasoncode-537(47)
,
                  reasoncode-538(48)
,
                  reasoncode-539(49)
,
                  reasoncode-540(50)
,
                  reasoncode-541(51)

                  }
       MAX-ACCESS not-accessible
       STATUS current
       DESCRIPTION
           "Reason code Index. The Numbers at the values are as in the RFC."
       ::= {acPMMGCPFailedCRCXResponsesEntry 1}



     acPMMGCPFailedCRCXResponsesInterval OBJECT-TYPE
       SYNTAX Unsigned32 (0..2)
       MAX-ACCESS not-accessible
       STATUS current
       DESCRIPTION
           "Interval index.
0 - current period (incomplete monitoring - mid period).
1 - Last full period.
2 - One before last."
       ::= {acPMMGCPFailedCRCXResponsesEntry 2}



     acPMMGCPFailedCRCXResponsesVal OBJECT-TYPE
       SYNTAX Counter32
       MAX-ACCESS read-only
       STATUS current
       DESCRIPTION
           "Value of gauge or counter."
       ::= {acPMMGCPFailedCRCXResponsesEntry 3}



     -- ****************************************
     -- acPMMGCPFailedMDCXResponses table declaration
     -- ****************************************
     acPMMGCPFailedMDCXResponsesTable OBJECT-TYPE
       SYNTAX SEQUENCE OF AcPMMGCPFailedMDCXResponsesEntry
       MAX-ACCESS not-accessible
       STATUS current
       DESCRIPTION
           "Number of failed responses to CRCX commands, per reason code."
       ::= {acPMMGCP 11}



     -- ****************************************
     -- acPMMGCPFailedMDCXResponses table entry
     -- ****************************************
     acPMMGCPFailedMDCXResponsesEntry OBJECT-TYPE
       SYNTAX AcPMMGCPFailedMDCXResponsesEntry
       MAX-ACCESS not-accessible
       STATUS current
       DESCRIPTION
           ""
       INDEX {acPMMGCPFailedMDCXResponsesReasonCode,acPMMGCPFailedMDCXResponsesInterval}
       ::= {acPMMGCPFailedMDCXResponsesTable 1}



     -- ****************************************
     -- acPMMGCPFailedMDCXResponses TABLE
     -- ****************************************
     AcPMMGCPFailedMDCXResponsesEntry ::= SEQUENCE {
       acPMMGCPFailedMDCXResponsesReasonCode           INTEGER,
       acPMMGCPFailedMDCXResponsesInterval             Unsigned32,
       acPMMGCPFailedMDCXResponsesVal                  Counter32
     }



     acPMMGCPFailedMDCXResponsesReasonCode OBJECT-TYPE
       SYNTAX INTEGER {
                  reasoncode-400(0)
,
                  reasoncode-401(1)
,
                  reasoncode-402(2)
,
                  reasoncode-403(3)
,
                  reasoncode-404(4)
,
                  reasoncode-405(5)
,
                  reasoncode-406(6)
,
                  reasoncode-407(7)
,
                  reasoncode-409(8)
,
                  reasoncode-410(9)
,
                  reasoncode-500(10)
,
                  reasoncode-501(11)
,
                  reasoncode-502(12)
,
                  reasoncode-503(13)
,
                  reasoncode-504(14)
,
                  reasoncode-505(15)
,
                  reasoncode-506(16)
,
                  reasoncode-507(17)
,
                  reasoncode-508(18)
,
                  reasoncode-509(19)
,
                  reasoncode-510(20)
,
                  reasoncode-511(21)
,
                  reasoncode-512(22)
,
                  reasoncode-513(23)
,
                  reasoncode-514(24)
,
                  reasoncode-515(25)
,
                  reasoncode-516(26)
,
                  reasoncode-517(27)
,
                  reasoncode-518(28)
,
                  reasoncode-519(29)
,
                  reasoncode-520(30)
,
                  reasoncode-521(31)
,
                  reasoncode-522(32)
,
                  reasoncode-523(33)
,
                  reasoncode-524(34)
,
                  reasoncode-525(35)
,
                  reasoncode-526(36)
,
                  reasoncode-527(37)
,
                  reasoncode-528(38)
,
                  reasoncode-529(39)
,
                  reasoncode-530(40)
,
                  reasoncode-531(41)
,
                  reasoncode-532(42)
,
                  reasoncode-533(43)
,
                  reasoncode-534(44)
,
                  reasoncode-535(45)
,
                  reasoncode-536(46)
,
                  reasoncode-537(47)
,
                  reasoncode-538(48)
,
                  reasoncode-539(49)
,
                  reasoncode-540(50)
,
                  reasoncode-541(51)

                  }
       MAX-ACCESS not-accessible
       STATUS current
       DESCRIPTION
           "Reason code Index. The Numbers at the values are as in the RFC."
       ::= {acPMMGCPFailedMDCXResponsesEntry 1}



     acPMMGCPFailedMDCXResponsesInterval OBJECT-TYPE
       SYNTAX Unsigned32 (0..2)
       MAX-ACCESS not-accessible
       STATUS current
       DESCRIPTION
           "Interval index.
0 - current period (incomplete monitoring - mid period).
1 - Last full period.
2 - One before last."
       ::= {acPMMGCPFailedMDCXResponsesEntry 2}



     acPMMGCPFailedMDCXResponsesVal OBJECT-TYPE
       SYNTAX Counter32
       MAX-ACCESS read-only
       STATUS current
       DESCRIPTION
           "Value of gauge or counter."
       ::= {acPMMGCPFailedMDCXResponsesEntry 3}



     -- ****************************************
     -- acPMMGCPGeneratedDLCXPerReasonCode table declaration
     -- ****************************************
     acPMMGCPGeneratedDLCXPerReasonCodeTable OBJECT-TYPE
       SYNTAX SEQUENCE OF AcPMMGCPGeneratedDLCXPerReasonCodeEntry
       MAX-ACCESS not-accessible
       STATUS current
       DESCRIPTION
           "Number of gateway-generated DLCX commands per reason code. when you choose 0 its 900(ENDPOINT_MALFUNCTIONING) and so on."
       ::= {acPMMGCP 12}



     -- ****************************************
     -- acPMMGCPGeneratedDLCXPerReasonCode table entry
     -- ****************************************
     acPMMGCPGeneratedDLCXPerReasonCodeEntry OBJECT-TYPE
       SYNTAX AcPMMGCPGeneratedDLCXPerReasonCodeEntry
       MAX-ACCESS not-accessible
       STATUS current
       DESCRIPTION
           ""
       INDEX {acPMMGCPGeneratedDLCXPerReasonCodeReasonCode,acPMMGCPGeneratedDLCXPerReasonCodeInterval}
       ::= {acPMMGCPGeneratedDLCXPerReasonCodeTable 1}



     -- ****************************************
     -- acPMMGCPGeneratedDLCXPerReasonCode TABLE
     -- ****************************************
     AcPMMGCPGeneratedDLCXPerReasonCodeEntry ::= SEQUENCE {
       acPMMGCPGeneratedDLCXPerReasonCodeReasonCode    INTEGER,
       acPMMGCPGeneratedDLCXPerReasonCodeInterval      Unsigned32,
       acPMMGCPGeneratedDLCXPerReasonCodeVal           Counter32
     }



     acPMMGCPGeneratedDLCXPerReasonCodeReasonCode OBJECT-TYPE
       SYNTAX INTEGER {
                  eNDPOINT-MALFUNCTIONING-900(0)
,
                  eNDPOINT-TAKEN-OUT-OF-SERVICE-901(1)
,
                  lOSS-OF-LOWER-LAYER-CONNECTIVITY-902(2)
,
                  qOS-RESOURCE-RESERVATION-WAS-LOST-903(3)
,
                  mANUAL-INTERVENTION-904(4)
,
                  fACILITY-FAILURE-905(5)

                  }
       MAX-ACCESS not-accessible
       STATUS current
       DESCRIPTION
           "Reason code Index. The Numbers at the values are as in the RFC."
       ::= {acPMMGCPGeneratedDLCXPerReasonCodeEntry 1}



     acPMMGCPGeneratedDLCXPerReasonCodeInterval OBJECT-TYPE
       SYNTAX Unsigned32 (0..2)
       MAX-ACCESS not-accessible
       STATUS current
       DESCRIPTION
           "Interval index.
0 - current period (incomplete monitoring - mid period).
1 - Last full period.
2 - One before last."
       ::= {acPMMGCPGeneratedDLCXPerReasonCodeEntry 2}



     acPMMGCPGeneratedDLCXPerReasonCodeVal OBJECT-TYPE
       SYNTAX Counter32
       MAX-ACCESS read-only
       STATUS current
       DESCRIPTION
           "Value of gauge or counter."
       ::= {acPMMGCPGeneratedDLCXPerReasonCodeEntry 3}



     acPMSIP OBJECT IDENTIFIER ::= {acPMControlData 52}


     -- ****************************************
     -- acPMSIPAttemptedCalls table declaration
     -- ****************************************
     acPMSIPAttemptedCallsTable OBJECT-TYPE
       SYNTAX SEQUENCE OF AcPMSIPAttemptedCallsEntry
       MAX-ACCESS not-accessible
       STATUS current
       DESCRIPTION
           "Number of attempted calls (Index 0 for TEL2IP and Index 1 for IP2TEL)"
       ::= {acPMSIP 1}



     -- ****************************************
     -- acPMSIPAttemptedCalls table entry
     -- ****************************************
     acPMSIPAttemptedCallsEntry OBJECT-TYPE
       SYNTAX AcPMSIPAttemptedCallsEntry
       MAX-ACCESS not-accessible
       STATUS current
       DESCRIPTION
           ""
       INDEX {acPMSIPAttemptedCallsDirection,acPMSIPAttemptedCallsInterval}
       ::= {acPMSIPAttemptedCallsTable 1}



     -- ****************************************
     -- acPMSIPAttemptedCalls TABLE
     -- ****************************************
     AcPMSIPAttemptedCallsEntry ::= SEQUENCE {
       acPMSIPAttemptedCallsDirection                  INTEGER,
       acPMSIPAttemptedCallsInterval                   Unsigned32,
       acPMSIPAttemptedCallsVal                        Counter32
     }



     acPMSIPAttemptedCallsDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPAttemptedCallsEntry 1}



     acPMSIPAttemptedCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPAttemptedCallsEntry 2}



     acPMSIPAttemptedCallsVal OBJECT-TYPE
       SYNTAX Counter32
       MAX-ACCESS read-only
       STATUS current
       DESCRIPTION
           "Value of gauge or counter."
       ::= {acPMSIPAttemptedCallsEntry 3}



     -- ****************************************
     -- acPMSIPCallDuration table declaration
     -- ****************************************
     acPMSIPCallDurationTable OBJECT-TYPE
       SYNTAX SEQUENCE OF AcPMSIPCallDurationEntry
       MAX-ACCESS not-accessible
       STATUS current
       DESCRIPTION
           "Call Duration (Index 0 for Tel2IP and Index 1 for IP2Tel);The Total preprty gives the sum of all calls duration, while the Value property is for the last call only"
       ::= {acPMSIP 2}



     -- ****************************************
     -- acPMSIPCallDuration table entry
     -- ****************************************
     acPMSIPCallDurationEntry OBJECT-TYPE
       SYNTAX AcPMSIPCallDurationEntry
       MAX-ACCESS not-accessible
       STATUS current
       DESCRIPTION
           ""
       INDEX {acPMSIPCallDurationDirection,acPMSIPCallDurationInterval}
       ::= {acPMSIPCallDurationTable 1}



     -- ****************************************
     -- acPMSIPCallDuration TABLE
     -- ****************************************
     AcPMSIPCallDurationEntry ::= SEQUENCE {
       acPMSIPCallDurationDirection                    INTEGER,
       acPMSIPCallDurationInterval                     Unsigned32,
       acPMSIPCallDurationVal                          Gauge32,
       acPMSIPCallDurationAverage                      Integer32,
       acPMSIPCallDurationMax                          Integer32,
       acPMSIPCallDurationMin                          Integer32,
       acPMSIPCallDurationVolume                       Counter32,
       acPMSIPCallDurationTimeBelowLowThreshold        Integer32,
       acPMSIPCallDurationTimeBetweenThresholds        Integer32,
       acPMSIPCallDurationTimeAboveHighThreshold       Integer32,
       acPMSIPCallDurationFullDayAverage               Integer32,
       acPMSIPCallDurationTotal                        Integer32
     }



     acPMSIPCallDurationDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPCallDurationEntry 1}



     acPMSIPCallDurationInterval OBJECT-TYPE
       SYNTAX Unsigned32 (0..2)
       MAX-ACCESS not-accessible
       STATUS current
       DESCRIPTION
           "Interval index.
0 - current period (incomplete monitoring - mid period).
1 - Last full period.
2 - One before last."
       ::= {acPMSIPCallDurationEntry 2}



     acPMSIPCallDurationVal OBJECT-TYPE
       SYNTAX Gauge32
       MAX-ACCESS read-only
       STATUS current
       DESCRIPTION
           "Value of gauge or counter."
       ::= {acPMSIPCallDurationEntry 3}



     acPMSIPCallDurationAverage OBJECT-TYPE
       SYNTAX Integer32 (-1..2147483647)
       MAX-ACCESS read-only
       STATUS current
       DESCRIPTION
           "Average value with in the period time."
       ::= {acPMSIPCallDurationEntry 4}



     acPMSIPCallDurationMax OBJECT-TYPE
       SYNTAX Integer32 (-1..2147483647)
       MAX-ACCESS read-only
       STATUS current
       DESCRIPTION
           "Maximum value with in the period time."
       ::= {acPMSIPCallDurationEntry 5}



     acPMSIPCallDurationMin OBJECT-TYPE
       SYNTAX Integer32 (-1..2147483647)
       MAX-ACCESS read-only
       STATUS current
       DESCRIPTION
           "Minimum value with in the period time."
       ::= {acPMSIPCallDurationEntry 6}



     acPMSIPCallDurationVolume OBJECT-TYPE
       SYNTAX Counter32
       MAX-ACCESS read-only
       STATUS current
       DESCRIPTION
           "Activity volume."
       ::= {acPMSIPCallDurationEntry 7}



     acPMSIPCallDurationTimeBelowLowThreshold OBJECT-TYPE
       SYNTAX Integer32 (-1..100)
       MAX-ACCESS read-only
       STATUS current
       DESCRIPTION
           "Percent of interval time for which gauge is below what was determined
as the low threshold."
       ::= {acPMSIPCallDurationEntry 8}



     acPMSIPCallDurationTimeBetweenThresholds OBJECT-TYPE
       SYNTAX Integer32 (-1..100)
       MAX-ACCESS read-only
       STATUS current
       DESCRIPTION
           "Percent of interval time for which gauge is above what was determined
as the high threshold."
       ::= {acPMSIPCallDurationEntry 9}



     acPMSIPCallDurationTimeAboveHighThreshold OBJECT-TYPE
       SYNTAX Integer32 (-1..100)
       MAX-ACCESS read-only
       STATUS current
       DESCRIPTION
           "Percent of interval time for which gauge is between what were
determined as the low and high thresholds."
       ::= {acPMSIPCallDurationEntry 10}



     acPMSIPCallDurationFullDayAverage OBJECT-TYPE
       SYNTAX Integer32 (-1..2147483647)
       MAX-ACCESS read-only
       STATUS current
       DESCRIPTION
           "The average of full 24 hours."
       ::= {acPMSIPCallDurationEntry 11}



     acPMSIPCallDurationTotal OBJECT-TYPE
       SYNTAX Integer32 (-1..2147483647)
       MAX-ACCESS read-only
       STATUS current
       DESCRIPTION
           "Total since last reset."
       ::= {acPMSIPCallDurationEntry 12}



     -- ****************************************
     -- acPMSIPNoMatchCalls table declaration
     -- ****************************************
     acPMSIPNoMatchCallsTable OBJECT-TYPE
       SYNTAX SEQUENCE OF AcPMSIPNoMatchCallsEntry
       MAX-ACCESS not-accessible
       STATUS current
       DESCRIPTION
           "Number of no match calls (Index 0 for TEL2IP and Index 1 for IP2TEL)"
       ::= {acPMSIP 3}



     -- ****************************************
     -- acPMSIPNoMatchCalls table entry
     -- ****************************************
     acPMSIPNoMatchCallsEntry OBJECT-TYPE
       SYNTAX AcPMSIPNoMatchCallsEntry
       MAX-ACCESS not-accessible
       STATUS current
       DESCRIPTION
           ""
       INDEX {acPMSIPNoMatchCallsDirection,acPMSIPNoMatchCallsInterval}
       ::= {acPMSIPNoMatchCallsTable 1}



     -- ****************************************
     -- acPMSIPNoMatchCalls TABLE
     -- ****************************************
     AcPMSIPNoMatchCallsEntry ::= SEQUENCE {
       acPMSIPNoMatchCallsDirection                    INTEGER,
       acPMSIPNoMatchCallsInterval                     Unsigned32,
       acPMSIPNoMatchCallsVal                          Counter32
     }



     acPMSIPNoMatchCallsDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPNoMatchCallsEntry 1}



     acPMSIPNoMatchCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPNoMatchCallsEntry 2}



     acPMSIPNoMatchCallsVal OBJECT-TYPE
       SYNTAX Counter32
       MAX-ACCESS read-only
       STATUS current
       DESCRIPTION
           "Value of gauge or counter."
       ::= {acPMSIPNoMatchCallsEntry 3}



     -- ****************************************
     -- acPMSIPBusyCalls table declaration
     -- ****************************************
     acPMSIPBusyCallsTable OBJECT-TYPE
       SYNTAX SEQUENCE OF AcPMSIPBusyCallsEntry
       MAX-ACCESS not-accessible
       STATUS current
       DESCRIPTION
           "Number of busy calls (Index 0 for TEL2IP and Index 1 for IP2TEL)"
       ::= {acPMSIP 4}



     -- ****************************************
     -- acPMSIPBusyCalls table entry
     -- ****************************************
     acPMSIPBusyCallsEntry OBJECT-TYPE
       SYNTAX AcPMSIPBusyCallsEntry
       MAX-ACCESS not-accessible
       STATUS current
       DESCRIPTION
           ""
       INDEX {acPMSIPBusyCallsDirection,acPMSIPBusyCallsInterval}
       ::= {acPMSIPBusyCallsTable 1}



     -- ****************************************
     -- acPMSIPBusyCalls TABLE
     -- ****************************************
     AcPMSIPBusyCallsEntry ::= SEQUENCE {
       acPMSIPBusyCallsDirection                       INTEGER,
       acPMSIPBusyCallsInterval                        Unsigned32,
       acPMSIPBusyCallsVal                             Counter32
     }



     acPMSIPBusyCallsDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPBusyCallsEntry 1}



     acPMSIPBusyCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPBusyCallsEntry 2}



     acPMSIPBusyCallsVal OBJECT-TYPE
       SYNTAX Counter32
       MAX-ACCESS read-only
       STATUS current
       DESCRIPTION
           "Value of gauge or counter."
       ::= {acPMSIPBusyCallsEntry 3}



     -- ****************************************
     -- acPMSIPNoAnswerCalls table declaration
     -- ****************************************
     acPMSIPNoAnswerCallsTable OBJECT-TYPE
       SYNTAX SEQUENCE OF AcPMSIPNoAnswerCallsEntry
       MAX-ACCESS not-accessible
       STATUS current
       DESCRIPTION
           "Number of no answer calls (Index 0 for TEL2IP and Index 1 for IP2TEL)"
       ::= {acPMSIP 5}



     -- ****************************************
     -- acPMSIPNoAnswerCalls table entry
     -- ****************************************
     acPMSIPNoAnswerCallsEntry OBJECT-TYPE
       SYNTAX AcPMSIPNoAnswerCallsEntry
       MAX-ACCESS not-accessible
       STATUS current
       DESCRIPTION
           ""
       INDEX {acPMSIPNoAnswerCallsDirection,acPMSIPNoAnswerCallsInterval}
       ::= {acPMSIPNoAnswerCallsTable 1}



     -- ****************************************
     -- acPMSIPNoAnswerCalls TABLE
     -- ****************************************
     AcPMSIPNoAnswerCallsEntry ::= SEQUENCE {
       acPMSIPNoAnswerCallsDirection                   INTEGER,
       acPMSIPNoAnswerCallsInterval                    Unsigned32,
       acPMSIPNoAnswerCallsVal                         Counter32
     }



     acPMSIPNoAnswerCallsDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPNoAnswerCallsEntry 1}



     acPMSIPNoAnswerCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPNoAnswerCallsEntry 2}



     acPMSIPNoAnswerCallsVal OBJECT-TYPE
       SYNTAX Counter32
       MAX-ACCESS read-only
       STATUS current
       DESCRIPTION
           "Value of gauge or counter."
       ::= {acPMSIPNoAnswerCallsEntry 3}



     -- ****************************************
     -- acPMSIPNoRouteCalls table declaration
     -- ****************************************
     acPMSIPNoRouteCallsTable OBJECT-TYPE
       SYNTAX SEQUENCE OF AcPMSIPNoRouteCallsEntry
       MAX-ACCESS not-accessible
       STATUS current
       DESCRIPTION
           "Number of no route calls (Index 0 for TEL2IP and Index 1 for IP2TEL)"
       ::= {acPMSIP 6}



     -- ****************************************
     -- acPMSIPNoRouteCalls table entry
     -- ****************************************
     acPMSIPNoRouteCallsEntry OBJECT-TYPE
       SYNTAX AcPMSIPNoRouteCallsEntry
       MAX-ACCESS not-accessible
       STATUS current
       DESCRIPTION
           ""
       INDEX {acPMSIPNoRouteCallsDirection,acPMSIPNoRouteCallsInterval}
       ::= {acPMSIPNoRouteCallsTable 1}



     -- ****************************************
     -- acPMSIPNoRouteCalls TABLE
     -- ****************************************
     AcPMSIPNoRouteCallsEntry ::= SEQUENCE {
       acPMSIPNoRouteCallsDirection                    INTEGER,
       acPMSIPNoRouteCallsInterval                     Unsigned32,
       acPMSIPNoRouteCallsVal                          Counter32
     }



     acPMSIPNoRouteCallsDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPNoRouteCallsEntry 1}



     acPMSIPNoRouteCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPNoRouteCallsEntry 2}



     acPMSIPNoRouteCallsVal OBJECT-TYPE
       SYNTAX Counter32
       MAX-ACCESS read-only
       STATUS current
       DESCRIPTION
           "Value of gauge or counter."
       ::= {acPMSIPNoRouteCallsEntry 3}



     -- ****************************************
     -- acPMSIPFailCalls table declaration
     -- ****************************************
     acPMSIPFailCallsTable OBJECT-TYPE
       SYNTAX SEQUENCE OF AcPMSIPFailCallsEntry
       MAX-ACCESS not-accessible
       STATUS current
       DESCRIPTION
           "Number of calls that failed because of other reasons (Index 0 for TEL2IP and Index 1 for IP2TEL)"
       ::= {acPMSIP 7}



     -- ****************************************
     -- acPMSIPFailCalls table entry
     -- ****************************************
     acPMSIPFailCallsEntry OBJECT-TYPE
       SYNTAX AcPMSIPFailCallsEntry
       MAX-ACCESS not-accessible
       STATUS current
       DESCRIPTION
           ""
       INDEX {acPMSIPFailCallsDirection,acPMSIPFailCallsInterval}
       ::= {acPMSIPFailCallsTable 1}



     -- ****************************************
     -- acPMSIPFailCalls TABLE
     -- ****************************************
     AcPMSIPFailCallsEntry ::= SEQUENCE {
       acPMSIPFailCallsDirection                       INTEGER,
       acPMSIPFailCallsInterval                        Unsigned32,
       acPMSIPFailCallsVal                             Counter32
     }



     acPMSIPFailCallsDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPFailCallsEntry 1}



     acPMSIPFailCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPFailCallsEntry 2}



     acPMSIPFailCallsVal OBJECT-TYPE
       SYNTAX Counter32
       MAX-ACCESS read-only
       STATUS current
       DESCRIPTION
           "Value of gauge or counter."
       ::= {acPMSIPFailCallsEntry 3}



     -- ****************************************
     -- acPMSIPEstablishedCalls table declaration
     -- ****************************************
     acPMSIPEstablishedCallsTable OBJECT-TYPE
       SYNTAX SEQUENCE OF AcPMSIPEstablishedCallsEntry
       MAX-ACCESS not-accessible
       STATUS current
       DESCRIPTION
           "Number of established calls (Index 0 for TEL2IP and Index 1 for IP2TEL)"
       ::= {acPMSIP 8}



     -- ****************************************
     -- acPMSIPEstablishedCalls table entry
     -- ****************************************
     acPMSIPEstablishedCallsEntry OBJECT-TYPE
       SYNTAX AcPMSIPEstablishedCallsEntry
       MAX-ACCESS not-accessible
       STATUS current
       DESCRIPTION
           ""
       INDEX {acPMSIPEstablishedCallsDirection,acPMSIPEstablishedCallsInterval}
       ::= {acPMSIPEstablishedCallsTable 1}



     -- ****************************************
     -- acPMSIPEstablishedCalls TABLE
     -- ****************************************
     AcPMSIPEstablishedCallsEntry ::= SEQUENCE {
       acPMSIPEstablishedCallsDirection                INTEGER,
       acPMSIPEstablishedCallsInterval                 Unsigned32,
       acPMSIPEstablishedCallsVal                      Counter32
     }



     acPMSIPEstablishedCallsDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPEstablishedCallsEntry 1}



     acPMSIPEstablishedCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPEstablishedCallsEntry 2}



     acPMSIPEstablishedCallsVal OBJECT-TYPE
       SYNTAX Counter32
       MAX-ACCESS read-only
       STATUS current
       DESCRIPTION
           "Value of gauge or counter."
       ::= {acPMSIPEstablishedCallsEntry 3}



     -- ****************************************
     -- acPMSIPFaxAttemptedCalls table declaration
     -- ****************************************
     acPMSIPFaxAttemptedCallsTable OBJECT-TYPE
       SYNTAX SEQUENCE OF AcPMSIPFaxAttemptedCallsEntry
       MAX-ACCESS not-accessible
       STATUS current
       DESCRIPTION
           "Number of attempted fax calls (Index 0 for TEL2IP and Index 1 for IP2TEL)"
       ::= {acPMSIP 9}



     -- ****************************************
     -- acPMSIPFaxAttemptedCalls table entry
     -- ****************************************
     acPMSIPFaxAttemptedCallsEntry OBJECT-TYPE
       SYNTAX AcPMSIPFaxAttemptedCallsEntry
       MAX-ACCESS not-accessible
       STATUS current
       DESCRIPTION
           ""
       INDEX {acPMSIPFaxAttemptedCallsDirection,acPMSIPFaxAttemptedCallsInterval}
       ::= {acPMSIPFaxAttemptedCallsTable 1}



     -- ****************************************
     -- acPMSIPFaxAttemptedCalls TABLE
     -- ****************************************
     AcPMSIPFaxAttemptedCallsEntry ::= SEQUENCE {
       acPMSIPFaxAttemptedCallsDirection               INTEGER,
       acPMSIPFaxAttemptedCallsInterval                Unsigned32,
       acPMSIPFaxAttemptedCallsVal                     Counter32
     }



     acPMSIPFaxAttemptedCallsDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPFaxAttemptedCallsEntry 1}



     acPMSIPFaxAttemptedCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPFaxAttemptedCallsEntry 2}



     acPMSIPFaxAttemptedCallsVal OBJECT-TYPE
       SYNTAX Counter32
       MAX-ACCESS read-only
       STATUS current
       DESCRIPTION
           "Value of gauge or counter."
       ::= {acPMSIPFaxAttemptedCallsEntry 3}



     -- ****************************************
     -- acPMSIPFaxSuccessCalls table declaration
     -- ****************************************
     acPMSIPFaxSuccessCallsTable OBJECT-TYPE
       SYNTAX SEQUENCE OF AcPMSIPFaxSuccessCallsEntry
       MAX-ACCESS not-accessible
       STATUS current
       DESCRIPTION
           "Number of success fax calls (Index 0 for TEL2IP and Index 1 for IP2TEL)"
       ::= {acPMSIP 10}



     -- ****************************************
     -- acPMSIPFaxSuccessCalls table entry
     -- ****************************************
     acPMSIPFaxSuccessCallsEntry OBJECT-TYPE
       SYNTAX AcPMSIPFaxSuccessCallsEntry
       MAX-ACCESS not-accessible
       STATUS current
       DESCRIPTION
           ""
       INDEX {acPMSIPFaxSuccessCallsDirection,acPMSIPFaxSuccessCallsInterval}
       ::= {acPMSIPFaxSuccessCallsTable 1}



     -- ****************************************
     -- acPMSIPFaxSuccessCalls TABLE
     -- ****************************************
     AcPMSIPFaxSuccessCallsEntry ::= SEQUENCE {
       acPMSIPFaxSuccessCallsDirection                 INTEGER,
       acPMSIPFaxSuccessCallsInterval                  Unsigned32,
       acPMSIPFaxSuccessCallsVal                       Counter32
     }



     acPMSIPFaxSuccessCallsDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPFaxSuccessCallsEntry 1}



     acPMSIPFaxSuccessCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPFaxSuccessCallsEntry 2}



     acPMSIPFaxSuccessCallsVal OBJECT-TYPE
       SYNTAX Counter32
       MAX-ACCESS read-only
       STATUS current
       DESCRIPTION
           "Value of gauge or counter."
       ::= {acPMSIPFaxSuccessCallsEntry 3}



     -- ****************************************
     -- acPMSIPForwardedCalls table declaration
     -- ****************************************
     acPMSIPForwardedCallsTable OBJECT-TYPE
       SYNTAX SEQUENCE OF AcPMSIPForwardedCallsEntry
       MAX-ACCESS not-accessible
       STATUS current
       DESCRIPTION
           "Number of calls released due to forwarding (Index 0 for TEL2IP and Index 1 for IP2TEL)"
       ::= {acPMSIP 11}



     -- ****************************************
     -- acPMSIPForwardedCalls table entry
     -- ****************************************
     acPMSIPForwardedCallsEntry OBJECT-TYPE
       SYNTAX AcPMSIPForwardedCallsEntry
       MAX-ACCESS not-accessible
       STATUS current
       DESCRIPTION
           ""
       INDEX {acPMSIPForwardedCallsDirection,acPMSIPForwardedCallsInterval}
       ::= {acPMSIPForwardedCallsTable 1}



     -- ****************************************
     -- acPMSIPForwardedCalls TABLE
     -- ****************************************
     AcPMSIPForwardedCallsEntry ::= SEQUENCE {
       acPMSIPForwardedCallsDirection                  INTEGER,
       acPMSIPForwardedCallsInterval                   Unsigned32,
       acPMSIPForwardedCallsVal                        Counter32
     }



     acPMSIPForwardedCallsDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPForwardedCallsEntry 1}



     acPMSIPForwardedCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPForwardedCallsEntry 2}



     acPMSIPForwardedCallsVal OBJECT-TYPE
       SYNTAX Counter32
       MAX-ACCESS read-only
       STATUS current
       DESCRIPTION
           "Value of gauge or counter."
       ::= {acPMSIPForwardedCallsEntry 3}



     -- ****************************************
     -- acPMSIPNoResourcesCalls table declaration
     -- ****************************************
     acPMSIPNoResourcesCallsTable OBJECT-TYPE
       SYNTAX SEQUENCE OF AcPMSIPNoResourcesCallsEntry
       MAX-ACCESS not-accessible
       STATUS current
       DESCRIPTION
           "Number of calls released because of no resources (Index 0 for TEL2IP and Index 1 for IP2TEL)"
       ::= {acPMSIP 12}



     -- ****************************************
     -- acPMSIPNoResourcesCalls table entry
     -- ****************************************
     acPMSIPNoResourcesCallsEntry OBJECT-TYPE
       SYNTAX AcPMSIPNoResourcesCallsEntry
       MAX-ACCESS not-accessible
       STATUS current
       DESCRIPTION
           ""
       INDEX {acPMSIPNoResourcesCallsDirection,acPMSIPNoResourcesCallsInterval}
       ::= {acPMSIPNoResourcesCallsTable 1}



     -- ****************************************
     -- acPMSIPNoResourcesCalls TABLE
     -- ****************************************
     AcPMSIPNoResourcesCallsEntry ::= SEQUENCE {
       acPMSIPNoResourcesCallsDirection                INTEGER,
       acPMSIPNoResourcesCallsInterval                 Unsigned32,
       acPMSIPNoResourcesCallsVal                      Counter32
     }



     acPMSIPNoResourcesCallsDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPNoResourcesCallsEntry 1}



     acPMSIPNoResourcesCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPNoResourcesCallsEntry 2}



     acPMSIPNoResourcesCallsVal OBJECT-TYPE
       SYNTAX Counter32
       MAX-ACCESS read-only
       STATUS current
       DESCRIPTION
           "Value of gauge or counter."
       ::= {acPMSIPNoResourcesCallsEntry 3}



     -- ****************************************
     -- acPMSIPTel2IPTrunkEstablishedCalls table declaration
     -- ****************************************
     acPMSIPTel2IPTrunkEstablishedCallsTable OBJECT-TYPE
       SYNTAX SEQUENCE OF AcPMSIPTel2IPTrunkEstablishedCallsEntry
       MAX-ACCESS not-accessible
       STATUS current
       DESCRIPTION
           "Number of Tel2IP established calls per trunk."
       ::= {acPMSIP 13}



     -- ****************************************
     -- acPMSIPTel2IPTrunkEstablishedCalls table entry
     -- ****************************************
     acPMSIPTel2IPTrunkEstablishedCallsEntry OBJECT-TYPE
       SYNTAX AcPMSIPTel2IPTrunkEstablishedCallsEntry
       MAX-ACCESS not-accessible
       STATUS current
       DESCRIPTION
           ""
       INDEX {acPMSIPTel2IPTrunkEstablishedCallsTrunkNum,acPMSIPTel2IPTrunkEstablishedCallsInterval}
       ::= {acPMSIPTel2IPTrunkEstablishedCallsTable 1}



     -- ****************************************
     -- acPMSIPTel2IPTrunkEstablishedCalls TABLE
     -- ****************************************
     AcPMSIPTel2IPTrunkEstablishedCallsEntry ::= SEQUENCE {
       acPMSIPTel2IPTrunkEstablishedCallsTrunkNum      Unsigned32,
       acPMSIPTel2IPTrunkEstablishedCallsInterval      Unsigned32,
       acPMSIPTel2IPTrunkEstablishedCallsVal           Counter32
     }



     acPMSIPTel2IPTrunkEstablishedCallsTrunkNum OBJECT-TYPE
       SYNTAX Unsigned32 (0..83)
       MAX-ACCESS not-accessible
       STATUS current
       DESCRIPTION
           "Trunk number.
0 is the first trunk."
       ::= {acPMSIPTel2IPTrunkEstablishedCallsEntry 1}



     acPMSIPTel2IPTrunkEstablishedCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPTel2IPTrunkEstablishedCallsEntry 2}



     acPMSIPTel2IPTrunkEstablishedCallsVal OBJECT-TYPE
       SYNTAX Counter32
       MAX-ACCESS read-only
       STATUS current
       DESCRIPTION
           "Value of gauge or counter."
       ::= {acPMSIPTel2IPTrunkEstablishedCallsEntry 3}



     -- ****************************************
     -- acPMSIPIP2TelTrunkEstablishedCalls table declaration
     -- ****************************************
     acPMSIPIP2TelTrunkEstablishedCallsTable OBJECT-TYPE
       SYNTAX SEQUENCE OF AcPMSIPIP2TelTrunkEstablishedCallsEntry
       MAX-ACCESS not-accessible
       STATUS current
       DESCRIPTION
           "Number of IP2Tel established calls per trunk."
       ::= {acPMSIP 14}



     -- ****************************************
     -- acPMSIPIP2TelTrunkEstablishedCalls table entry
     -- ****************************************
     acPMSIPIP2TelTrunkEstablishedCallsEntry OBJECT-TYPE
       SYNTAX AcPMSIPIP2TelTrunkEstablishedCallsEntry
       MAX-ACCESS not-accessible
       STATUS current
       DESCRIPTION
           ""
       INDEX {acPMSIPIP2TelTrunkEstablishedCallsTrunkNum,acPMSIPIP2TelTrunkEstablishedCallsInterval}
       ::= {acPMSIPIP2TelTrunkEstablishedCallsTable 1}



     -- ****************************************
     -- acPMSIPIP2TelTrunkEstablishedCalls TABLE
     -- ****************************************
     AcPMSIPIP2TelTrunkEstablishedCallsEntry ::= SEQUENCE {
       acPMSIPIP2TelTrunkEstablishedCallsTrunkNum      Unsigned32,
       acPMSIPIP2TelTrunkEstablishedCallsInterval      Unsigned32,
       acPMSIPIP2TelTrunkEstablishedCallsVal           Counter32
     }



     acPMSIPIP2TelTrunkEstablishedCallsTrunkNum OBJECT-TYPE
       SYNTAX Unsigned32 (0..83)
       MAX-ACCESS not-accessible
       STATUS current
       DESCRIPTION
           "Trunk number.
0 is the first trunk."
       ::= {acPMSIPIP2TelTrunkEstablishedCallsEntry 1}



     acPMSIPIP2TelTrunkEstablishedCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPIP2TelTrunkEstablishedCallsEntry 2}



     acPMSIPIP2TelTrunkEstablishedCallsVal OBJECT-TYPE
       SYNTAX Counter32
       MAX-ACCESS read-only
       STATUS current
       DESCRIPTION
           "Value of gauge or counter."
       ::= {acPMSIPIP2TelTrunkEstablishedCallsEntry 3}



     -- ****************************************
     -- acPMSIPTel2IPTrunkGroupEstablishedCalls table declaration
     -- ****************************************
     acPMSIPTel2IPTrunkGroupEstablishedCallsTable OBJECT-TYPE
       SYNTAX SEQUENCE OF AcPMSIPTel2IPTrunkGroupEstablishedCallsEntry
       MAX-ACCESS not-accessible
       STATUS current
       DESCRIPTION
           "Number of Tel2IP established calls per trunk group."
       ::= {acPMSIP 15}



     -- ****************************************
     -- acPMSIPTel2IPTrunkGroupEstablishedCalls table entry
     -- ****************************************
     acPMSIPTel2IPTrunkGroupEstablishedCallsEntry OBJECT-TYPE
       SYNTAX AcPMSIPTel2IPTrunkGroupEstablishedCallsEntry
       MAX-ACCESS not-accessible
       STATUS current
       DESCRIPTION
           ""
       INDEX {acPMSIPTel2IPTrunkGroupEstablishedCallsGroupNum,acPMSIPTel2IPTrunkGroupEstablishedCallsInterval}
       ::= {acPMSIPTel2IPTrunkGroupEstablishedCallsTable 1}



     -- ****************************************
     -- acPMSIPTel2IPTrunkGroupEstablishedCalls TABLE
     -- ****************************************
     AcPMSIPTel2IPTrunkGroupEstablishedCallsEntry ::= SEQUENCE {
       acPMSIPTel2IPTrunkGroupEstablishedCallsGroupNum Unsigned32,
       acPMSIPTel2IPTrunkGroupEstablishedCallsInterval Unsigned32,
       acPMSIPTel2IPTrunkGroupEstablishedCallsVal      Counter32
     }



     acPMSIPTel2IPTrunkGroupEstablishedCallsGroupNum OBJECT-TYPE
       SYNTAX Unsigned32 (0..83)
       MAX-ACCESS not-accessible
       STATUS current
       DESCRIPTION
           "Trunk Group number.
0 is the first trunk group."
       ::= {acPMSIPTel2IPTrunkGroupEstablishedCallsEntry 1}



     acPMSIPTel2IPTrunkGroupEstablishedCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPTel2IPTrunkGroupEstablishedCallsEntry 2}



     acPMSIPTel2IPTrunkGroupEstablishedCallsVal OBJECT-TYPE
       SYNTAX Counter32
       MAX-ACCESS read-only
       STATUS current
       DESCRIPTION
           "Value of gauge or counter."
       ::= {acPMSIPTel2IPTrunkGroupEstablishedCallsEntry 3}



     -- ****************************************
     -- acPMSIPIP2TelTrunkGroupEstablishedCalls table declaration
     -- ****************************************
     acPMSIPIP2TelTrunkGroupEstablishedCallsTable OBJECT-TYPE
       SYNTAX SEQUENCE OF AcPMSIPIP2TelTrunkGroupEstablishedCallsEntry
       MAX-ACCESS not-accessible
       STATUS current
       DESCRIPTION
           "Number of IP2Tel established calls per trunk group."
       ::= {acPMSIP 16}



     -- ****************************************
     -- acPMSIPIP2TelTrunkGroupEstablishedCalls table entry
     -- ****************************************
     acPMSIPIP2TelTrunkGroupEstablishedCallsEntry OBJECT-TYPE
       SYNTAX AcPMSIPIP2TelTrunkGroupEstablishedCallsEntry
       MAX-ACCESS not-accessible
       STATUS current
       DESCRIPTION
           ""
       INDEX {acPMSIPIP2TelTrunkGroupEstablishedCallsGroupNum,acPMSIPIP2TelTrunkGroupEstablishedCallsInterval}
       ::= {acPMSIPIP2TelTrunkGroupEstablishedCallsTable 1}



     -- ****************************************
     -- acPMSIPIP2TelTrunkGroupEstablishedCalls TABLE
     -- ****************************************
     AcPMSIPIP2TelTrunkGroupEstablishedCallsEntry ::= SEQUENCE {
       acPMSIPIP2TelTrunkGroupEstablishedCallsGroupNum Unsigned32,
       acPMSIPIP2TelTrunkGroupEstablishedCallsInterval Unsigned32,
       acPMSIPIP2TelTrunkGroupEstablishedCallsVal      Counter32
     }



     acPMSIPIP2TelTrunkGroupEstablishedCallsGroupNum OBJECT-TYPE
       SYNTAX Unsigned32 (0..83)
       MAX-ACCESS not-accessible
       STATUS current
       DESCRIPTION
           "Trunk Group number.
0 is the first trunk group."
       ::= {acPMSIPIP2TelTrunkGroupEstablishedCallsEntry 1}



     acPMSIPIP2TelTrunkGroupEstablishedCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPIP2TelTrunkGroupEstablishedCallsEntry 2}



     acPMSIPIP2TelTrunkGroupEstablishedCallsVal OBJECT-TYPE
       SYNTAX Counter32
       MAX-ACCESS read-only
       STATUS current
       DESCRIPTION
           "Value of gauge or counter."
       ::= {acPMSIPIP2TelTrunkGroupEstablishedCallsEntry 3}





END
