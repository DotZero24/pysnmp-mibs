--
-- CRESTRON-MONITOR-MIB.my
-- MIB generated by MG-SOFT Visual MIB Builder Version 5.0  Build 250
-- Wednesday, June 23, 2004 at 11:42:40
--

	CRESTRON-MONITOR-MIB DEFINITIONS ::= BEGIN
 
		IMPORTS
			crestronCommon, Digital			
				FROM CRESTRON-ROOT-MIB			
			OBJECT-GROUP, NOTIFICATION-GROUP			
				FROM SNMPv2-CONF			
			Integer32, Counter32, OBJECT-TYPE, MODULE-IDENTITY, NOTIFICATION-TYPE			
				FROM SNMPv2-SMI			
			DisplayString, RowStatus, StorageType			
				FROM SNMPv2-TC;
	
	
-- A mib for monitoring other mib variables and generating traps if certain conditions are met.
		-- 1.3.6.1.4.1.3212.1.2
		crestronMonitor MODULE-IDENTITY 
			LAST-UPDATED "200308181217Z"		-- August 18, 2003 at 12:17 GMT
			ORGANIZATION 
				"Crestron Electronics, Inc."
			CONTACT-INFO 
				"Contact-info."
			DESCRIPTION 
				"Description."
			REVISION "200308181219Z"		-- August 18, 2003 at 12:19 GMT
			DESCRIPTION 
				"Just an example."
			::= { crestronCommon 2 }

		
	
	
--
-- Node definitions
--
	
		-- 1.3.6.1.4.1.3212.1.2.1
		crestronMonMIBVersion OBJECT-TYPE
			SYNTAX Integer32
			MAX-ACCESS read-only
			STATUS current
			DESCRIPTION
				"Description."
			::= { crestronMonitor 1 }

		
		-- 1.3.6.1.4.1.3212.1.2.2
		crestronMonAdmin OBJECT IDENTIFIER ::= { crestronMonitor 2 }

		
		-- 1.3.6.1.4.1.3212.1.2.3
		crestronMonNotifications OBJECT IDENTIFIER ::= { crestronMonitor 3 }

		
		-- 1.3.6.1.4.1.3212.1.2.3.1
		crestronMonTrapMsg OBJECT-TYPE
			SYNTAX DisplayString
			MAX-ACCESS accessible-for-notify
			STATUS current
			DESCRIPTION
				"Description."
			::= { crestronMonNotifications 1 }

		
		-- 1.3.6.1.4.1.3212.1.2.3.2
		crestronMonTrap NOTIFICATION-TYPE
			OBJECTS { crestronMonTrapMsg }
			STATUS current
			DESCRIPTION 
				"Description."
			::= { crestronMonNotifications 2 }

		
		-- 1.3.6.1.4.1.3212.1.2.4
		crestronMonObjects OBJECT IDENTIFIER ::= { crestronMonitor 4 }

		
		-- 1.3.6.1.4.1.3212.1.2.4.4
		crestronMonProbes OBJECT IDENTIFIER ::= { crestronMonObjects 4 }

		
		-- 1.3.6.1.4.1.3212.1.2.4.4.1
		crestronMonProbesCnt OBJECT-TYPE
			SYNTAX Counter32
			MAX-ACCESS read-only
			STATUS current
			DESCRIPTION
				"Description."
			::= { crestronMonProbes 1 }

		
		-- 1.3.6.1.4.1.3212.1.2.4.4.2
		crestronMonProbesTable OBJECT-TYPE
			SYNTAX SEQUENCE OF CrestronMonProbesEntry
			MAX-ACCESS not-accessible
			STATUS current
			DESCRIPTION
				"Description."
			::= { crestronMonProbes 2 }

		
		-- 1.3.6.1.4.1.3212.1.2.4.4.2.1
		crestronMonProbesEntry OBJECT-TYPE
			SYNTAX CrestronMonProbesEntry
			MAX-ACCESS not-accessible
			STATUS current
			DESCRIPTION
				"Description."
			INDEX { crestronMonProbeOid }
			::= { crestronMonProbesTable 1 }

		
		CrestronMonProbesEntry ::=
			SEQUENCE { 
				crestronMonProbeOid
					OBJECT IDENTIFIER,
				crestronMonProbeOidLen
					Integer32,
				crestronMonProbeDesc
					DisplayString,
				crestronMonProbeStringVal
					DisplayString,
				crestronMonProbeNumVal
					Integer32,
				crestronMonProbeMatched
					Digital,
				crestronMonProbeComparator
					DisplayString,
				crestronMonProbeStorageType
					StorageType,
				crestronMonProbeRowStatus
					RowStatus
			 }

		-- 1.3.6.1.4.1.3212.1.2.4.4.2.1.1
		crestronMonProbeOid OBJECT-TYPE
			SYNTAX OBJECT IDENTIFIER
			MAX-ACCESS read-write
			STATUS current
			DESCRIPTION
				"Object ID whose value is being monitored."
			::= { crestronMonProbesEntry 1 }

		
		-- 1.3.6.1.4.1.3212.1.2.4.4.2.1.2
		crestronMonProbeOidLen OBJECT-TYPE
			SYNTAX Integer32
			MAX-ACCESS read-write
			STATUS current
			DESCRIPTION
				"Description."
			::= { crestronMonProbesEntry 2 }

		
		-- 1.3.6.1.4.1.3212.1.2.4.4.2.1.3
		crestronMonProbeDesc OBJECT-TYPE
			SYNTAX DisplayString
			MAX-ACCESS read-write
			STATUS current
			DESCRIPTION
				"A short explanation of what this probe is monitoring."
			::= { crestronMonProbesEntry 3 }

		
		-- 1.3.6.1.4.1.3212.1.2.4.4.2.1.4
		crestronMonProbeStringVal OBJECT-TYPE
			SYNTAX DisplayString
			MAX-ACCESS read-write
			STATUS current
			DESCRIPTION
				"Description."
			::= { crestronMonProbesEntry 4 }

		
		-- 1.3.6.1.4.1.3212.1.2.4.4.2.1.5
		crestronMonProbeNumVal OBJECT-TYPE
			SYNTAX Integer32
			MAX-ACCESS read-write
			STATUS current
			DESCRIPTION
				"Description."
			::= { crestronMonProbesEntry 5 }

		
		-- 1.3.6.1.4.1.3212.1.2.4.4.2.1.6
		crestronMonProbeMatched OBJECT-TYPE
			SYNTAX Digital
			MAX-ACCESS read-only
			STATUS current
			DESCRIPTION
				"Description."
			::= { crestronMonProbesEntry 6 }

		
		-- 1.3.6.1.4.1.3212.1.2.4.4.2.1.7
		crestronMonProbeComparator OBJECT-TYPE
			SYNTAX DisplayString
			MAX-ACCESS read-write
			STATUS current
			DESCRIPTION
				"Description."
			::= { crestronMonProbesEntry 7 }

		
		-- 1.3.6.1.4.1.3212.1.2.4.4.2.1.8
		crestronMonProbeStorageType OBJECT-TYPE
			SYNTAX StorageType
			MAX-ACCESS read-write
			STATUS current
			DESCRIPTION
				"Whether or not to save this entry to permanent storage."
			::= { crestronMonProbesEntry 8 }

		
		-- 1.3.6.1.4.1.3212.1.2.4.4.2.1.9
		crestronMonProbeRowStatus OBJECT-TYPE
			SYNTAX RowStatus
			MAX-ACCESS read-write
			STATUS current
			DESCRIPTION
				"Whether or not this probe is active.  Write this after all the other row variables have been set, otherwise you may get undesired traps."
			::= { crestronMonProbesEntry 9 }

		
		-- 1.3.6.1.4.1.3212.1.2.5
		crestronMonConformance OBJECT IDENTIFIER ::= { crestronMonitor 5 }

		
		-- 1.3.6.1.4.1.3212.1.2.5.1
		crestronMonCompliances OBJECT IDENTIFIER ::= { crestronMonConformance 1 }

		
		-- 1.3.6.1.4.1.3212.1.2.5.2
		crestronMonGroups OBJECT IDENTIFIER ::= { crestronMonConformance 2 }

		
-- Have to create this for SMIv2 but is not used yet.
		-- 1.3.6.1.4.1.3212.1.2.5.2.1
		crestronMonAllObjects OBJECT-GROUP
			OBJECTS { crestronMonMIBVersion, crestronMonTrapMsg, crestronMonProbesCnt, crestronMonProbeOid, crestronMonProbeStorageType, 
				crestronMonProbeRowStatus, crestronMonProbeDesc, crestronMonProbeOidLen, crestronMonProbeStringVal, crestronMonProbeNumVal, 
				crestronMonProbeMatched, crestronMonProbeComparator }
			STATUS current
			DESCRIPTION 
				"Description."
			::= { crestronMonGroups 1 }

		
		-- 1.3.6.1.4.1.3212.1.2.5.2.6
		crestronMonAllTraps NOTIFICATION-GROUP
			NOTIFICATIONS { crestronMonTrap }
			STATUS current
			DESCRIPTION 
				"Description."
			::= { crestronMonGroups 6 }

		
	
	END

--
-- CRESTRON-MONITOR-MIB.my
--
