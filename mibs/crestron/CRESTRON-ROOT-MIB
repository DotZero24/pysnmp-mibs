--
-- CRESTRON-ROOT-MIB.my
-- MIB generated by MG-SOFT Visual MIB Builder Version 6.0  Build 88
-- Wednesday, May 18, 2005 at 19:42:01
--

	CRESTRON-ROOT-MIB DEFINITIONS ::= BEGIN

		IMPORTS
			OBJECT-GROUP
				FROM SNMPv2-CONF
			enterprises, Integer32, OBJECT-TYPE, MODULE-IDENTITY
				FROM SNMPv2-SMI
			TEXTUAL-CONVENTION
				FROM SNMPv2-TC;


		-- 1.3.6.1.4.1.3212
		crestron MODULE-IDENTITY
			LAST-UPDATED "200308181523Z"		-- August 18, 2003 at 15:23 GMT
			ORGANIZATION
				"Crestron Electronics, Inc."
			CONTACT-INFO
				"Your contact info"
			DESCRIPTION
				"Enter the description for this MIB module."
			::= { enterprises 3212 }



--
-- Textual conventions
--

		TcpPort ::= TEXTUAL-CONVENTION
			STATUS current
			DESCRIPTION
				"Description."
			SYNTAX Integer32 (0..65535)

		UdpPort ::= TEXTUAL-CONVENTION
			STATUS current
			DESCRIPTION
				"Description."
			SYNTAX Integer32 (0..65535)

		Digital ::= TEXTUAL-CONVENTION
			STATUS current
			DESCRIPTION
				"Description."
			SYNTAX INTEGER
				{
				off(0),
				on(1)
				}


--
-- Node definitions
--

		-- 1.3.6.1.4.1.3212.1
		crestronAdmin OBJECT IDENTIFIER ::= { crestron 1 }


		-- 1.3.6.1.4.1.3212.2
		crestronNotifications OBJECT IDENTIFIER ::= { crestron 2 }


		-- 1.3.6.1.4.1.3212.3
		crestronObjects OBJECT IDENTIFIER ::= { crestron 3 }


		-- 1.3.6.1.4.1.3212.3.1
		crestronRootMIBVersion OBJECT-TYPE
			SYNTAX Integer32
			MAX-ACCESS read-only
			STATUS current
			DESCRIPTION
				"Description."
			::= { crestronObjects 1 }


		-- 1.3.6.1.4.1.3212.5
		crestronConformance OBJECT IDENTIFIER ::= { crestron 5 }


		-- 1.3.6.1.4.1.3212.5.2
		crestronCompliances OBJECT IDENTIFIER ::= { crestronConformance 2 }


		-- 1.3.6.1.4.1.3212.5.3
		crestronGroups OBJECT IDENTIFIER ::= { crestronConformance 3 }


		-- 1.3.6.1.4.1.3212.5.3.1
		crestronRootAllObjects OBJECT-GROUP
			OBJECTS { crestronRootMIBVersion }
			STATUS current
			DESCRIPTION
				"Description."
			::= { crestronGroups 1 }


-- MIBs common to all Crestron products.
		-- 1.3.6.1.4.1.3212.6
		crestronCommon OBJECT IDENTIFIER ::= { crestron 6 }


-- Crestron MIBs that are common to all control systems.
		-- 1.3.6.1.4.1.3212.7
		crestronControl OBJECT IDENTIFIER ::= { crestron 7 }


-- Crestron MIBs common to all touchpanels.
		-- 1.3.6.1.4.1.3212.8
		crestronTouch OBJECT IDENTIFIER ::= { crestron 8 }



	END

--
-- CRESTRON-ROOT-MIB.my
--
