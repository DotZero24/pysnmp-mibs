--
-- CRESTRON-SYSTEM-MIB.my
-- MIB generated by MG-SOFT Visual MIB Builder Version 5.0  Build 250
-- Thursday, June 10, 2004 at 12:18:20
--

	CRESTRON-SYSTEM-MIB DEFINITIONS ::= BEGIN
 
		IMPORTS
			crestronCommon			
				FROM CRESTRON-ROOT-MIB			
			OBJECT-GROUP, NOTIFICATION-GROUP			
				FROM SNMPv2-CONF			
			Integer32, Counter32, OBJECT-TYPE, MODULE-IDENTITY, NOTIFICATION-TYPE			
				FROM SNMPv2-SMI			
			DisplayString			
				FROM SNMPv2-TC;
	
	
-- Information common to all Crestron control systems
		-- 1.3.6.1.4.1.3212.1.1
		crestronSystem MODULE-IDENTITY 
			LAST-UPDATED "200308181217Z"		-- August 18, 2003 at 12:17 GMT
			ORGANIZATION 
				"Crestron Electronics, Inc."
			CONTACT-INFO 
				"Contact-info."
			DESCRIPTION 
				"Description."
			REVISION "200308181219Z"		-- August 18, 2003 at 12:19 GMT
			DESCRIPTION 
				"Just an example."
			::= { crestronCommon 1 }

		
	
	
--
-- Node definitions
--
	
		-- 1.3.6.1.4.1.3212.1.1.1
		crestronSysMIBVersion OBJECT-TYPE
			SYNTAX Integer32
			MAX-ACCESS read-only
			STATUS current
			DESCRIPTION
				"Description."
			::= { crestronSystem 1 }

		
		-- 1.3.6.1.4.1.3212.1.1.2
		crestronSysAdmin OBJECT IDENTIFIER ::= { crestronSystem 2 }

		
		-- 1.3.6.1.4.1.3212.1.1.3
		crestronSysNotifications OBJECT IDENTIFIER ::= { crestronSystem 3 }

		
		-- 1.3.6.1.4.1.3212.1.1.3.1
		crestronSysTrapMsg OBJECT-TYPE
			SYNTAX DisplayString
			MAX-ACCESS accessible-for-notify
			STATUS current
			DESCRIPTION
				"Description."
			::= { crestronSysNotifications 1 }

		
		-- 1.3.6.1.4.1.3212.1.1.3.2
		crestronSysTrap NOTIFICATION-TYPE
			OBJECTS { crestronSysTrapMsg }
			STATUS current
			DESCRIPTION 
				"Description."
			::= { crestronSysNotifications 2 }

		
		-- 1.3.6.1.4.1.3212.1.1.4
		crestronSysObjects OBJECT IDENTIFIER ::= { crestronSystem 4 }

		
		-- 1.3.6.1.4.1.3212.1.1.4.2
		crestronSysErrors OBJECT IDENTIFIER ::= { crestronSysObjects 2 }

		
		-- 1.3.6.1.4.1.3212.1.1.4.4
		crestronSysInterfaces OBJECT IDENTIFIER ::= { crestronSysObjects 4 }

		
		-- 1.3.6.1.4.1.3212.1.1.4.4.1
		crestronSysInterfacesCount OBJECT-TYPE
			SYNTAX Counter32
			MAX-ACCESS read-only
			STATUS current
			DESCRIPTION
				"Description."
			::= { crestronSysInterfaces 1 }

		
		-- 1.3.6.1.4.1.3212.1.1.4.4.2
		crestronSysInterfacesTable OBJECT-TYPE
			SYNTAX SEQUENCE OF CrestronSysInterfacesEntry
			MAX-ACCESS not-accessible
			STATUS current
			DESCRIPTION
				"Description."
			::= { crestronSysInterfaces 2 }

		
		-- 1.3.6.1.4.1.3212.1.1.4.4.2.1
		crestronSysInterfacesEntry OBJECT-TYPE
			SYNTAX CrestronSysInterfacesEntry
			MAX-ACCESS not-accessible
			STATUS current
			DESCRIPTION
				"Description."
			INDEX { crestronSysInterfacesId }
			::= { crestronSysInterfacesTable 1 }

		
		CrestronSysInterfacesEntry ::=
			SEQUENCE { 
				crestronSysInterfacesId
					Integer32,
				crestronSysInterfacesRxOverruns
					Integer32,
				crestronSysInterfacesTxAllocFailed
					Integer32,
				crestronSysInterfacesTxAllocTimeoput
					Integer32
			 }

		-- 1.3.6.1.4.1.3212.1.1.4.4.2.1.1
		crestronSysInterfacesId OBJECT-TYPE
			SYNTAX Integer32 (1..65535)
			MAX-ACCESS read-write
			STATUS current
			DESCRIPTION
				"Description."
			::= { crestronSysInterfacesEntry 1 }

		
		-- 1.3.6.1.4.1.3212.1.1.4.4.2.1.2
		crestronSysInterfacesRxOverruns OBJECT-TYPE
			SYNTAX Integer32
			MAX-ACCESS read-write
			STATUS current
			DESCRIPTION
				"Description."
			::= { crestronSysInterfacesEntry 2 }

		
		-- 1.3.6.1.4.1.3212.1.1.4.4.2.1.3
		crestronSysInterfacesTxAllocFailed OBJECT-TYPE
			SYNTAX Integer32
			MAX-ACCESS read-write
			STATUS current
			DESCRIPTION
				"Description."
			::= { crestronSysInterfacesEntry 3 }

		
		-- 1.3.6.1.4.1.3212.1.1.4.4.2.1.4
		crestronSysInterfacesTxAllocTimeoput OBJECT-TYPE
			SYNTAX Integer32
			MAX-ACCESS read-write
			STATUS current
			DESCRIPTION
				"Description."
			::= { crestronSysInterfacesEntry 4 }

		
		-- 1.3.6.1.4.1.3212.1.1.5
		crestronSysConformance OBJECT IDENTIFIER ::= { crestronSystem 5 }

		
		-- 1.3.6.1.4.1.3212.1.1.5.1
		crestronSysCompliances OBJECT IDENTIFIER ::= { crestronSysConformance 1 }

		
		-- 1.3.6.1.4.1.3212.1.1.5.2
		crestronSysGroups OBJECT IDENTIFIER ::= { crestronSysConformance 2 }

		
-- Have to create this for SMIv2 but is not used yet.
		-- 1.3.6.1.4.1.3212.1.1.5.2.1
		crestronSystemAllObjects OBJECT-GROUP
			OBJECTS { crestronSysMIBVersion, crestronSysTrapMsg, crestronSysInterfacesCount, crestronSysInterfacesId, crestronSysInterfacesRxOverruns, 
				crestronSysInterfacesTxAllocFailed, crestronSysInterfacesTxAllocTimeoput }
			STATUS current
			DESCRIPTION 
				"Description."
			::= { crestronSysGroups 1 }

		
		-- 1.3.6.1.4.1.3212.1.1.5.2.6
		crestronSystemAllTraps NOTIFICATION-GROUP
			NOTIFICATIONS { crestronSysTrap }
			STATUS current
			DESCRIPTION 
				"Description."
			::= { crestronSysGroups 6 }

		
	
	END

--
-- CRESTRON-SYSTEM-MIB.my
--
