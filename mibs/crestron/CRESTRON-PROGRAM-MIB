--
-- CRESTRON-PROGRAM-MIB.my
-- MIB generated by MG-SOFT Visual MIB Builder Version 6.0  Build 88
-- Saturday, March 03, 2007 at 08:23:58
--

	CRESTRON-PROGRAM-MIB DEFINITIONS ::= BEGIN
 
		IMPORTS
			crestronControl			
				FROM CRESTRON-ROOT-MIB			
			OBJECT-GROUP, NOTIFICATION-GROUP			
				FROM SNMPv2-CONF			
			Integer32, OBJECT-TYPE, MODULE-IDENTITY, NOTIFICATION-TYPE			
				FROM SNMPv2-SMI			
			DisplayString, TEXTUAL-CONVENTION			
				FROM SNMPv2-TC;
	
	
-- Things about a running control system program.  This is different enough to not be covered by the HOST-RESOURCES-MIB. 
		-- 1.3.6.1.4.1.3212.2.2
		crestronProgram MODULE-IDENTITY 
			LAST-UPDATED "200308181217Z"		-- August 18, 2003 at 12:17 GMT
			ORGANIZATION 
				"Crestron Electronics, Inc."
			CONTACT-INFO 
				"Contact-info."
			DESCRIPTION 
				"Description."
			REVISION "200308181219Z"		-- August 18, 2003 at 12:19 GMT
			DESCRIPTION 
				"Just an example."
			::= { crestronControl 2 }

		
	
--
-- Textual conventions
--
	
		ProgramState ::= TEXTUAL-CONVENTION
			STATUS current
			DESCRIPTION 
				"Description."
			REFERENCE 
				"0 : unknown
				1 : deleted
				2 : initialized
				3 : running
				4 : paused
				5 : stopped
				6 : failed"
			SYNTAX Integer32 (0..6)

	
--
-- Node definitions
--
	
		-- 1.3.6.1.4.1.3212.2.2.1
		crestronProgAdmin OBJECT IDENTIFIER ::= { crestronProgram 1 }

		
		-- 1.3.6.1.4.1.3212.2.2.2
		crestronProgNotifications OBJECT IDENTIFIER ::= { crestronProgram 2 }

		
		-- 1.3.6.1.4.1.3212.2.2.2.1
		crestronProgStateChangeTrap NOTIFICATION-TYPE
			OBJECTS { crestronProgLabel, crestronProgUptime }
			STATUS current
			DESCRIPTION 
				"Description."
			::= { crestronProgNotifications 1 }

		
		-- 1.3.6.1.4.1.3212.2.2.3
		crestronProgObjects OBJECT IDENTIFIER ::= { crestronProgram 3 }

		
		-- 1.3.6.1.4.1.3212.2.2.3.1
		crestronProgMIBVersion OBJECT-TYPE
			SYNTAX Integer32
			MAX-ACCESS read-only
			STATUS current
			DESCRIPTION
				"Description."
			::= { crestronProgObjects 1 }

		
		-- 1.3.6.1.4.1.3212.2.2.3.2
		crestronProgInfo OBJECT IDENTIFIER ::= { crestronProgObjects 2 }

		
-- How long the current program has been running.
		-- 1.3.6.1.4.1.3212.2.2.3.2.1
		crestronProgUptime OBJECT-TYPE
			SYNTAX Integer32
			MAX-ACCESS read-only
			STATUS current
			DESCRIPTION
				"Description."
			::= { crestronProgInfo 1 }

		
-- A meaningful name for the current running program.
		-- 1.3.6.1.4.1.3212.2.2.3.2.2
		crestronProgLabel OBJECT-TYPE
			SYNTAX DisplayString
			MAX-ACCESS read-only
			STATUS current
			DESCRIPTION
				"Description."
			::= { crestronProgInfo 2 }

		
		-- 1.3.6.1.4.1.3212.2.2.3.2.3
		crestronProgSymbolCnt OBJECT-TYPE
			SYNTAX Integer32
			MAX-ACCESS read-only
			STATUS current
			DESCRIPTION
				"Description."
			::= { crestronProgInfo 3 }

		
		-- 1.3.6.1.4.1.3212.2.2.3.2.4
		crestronProgFilename OBJECT-TYPE
			SYNTAX DisplayString
			MAX-ACCESS read-only
			STATUS current
			DESCRIPTION
				"Description."
			::= { crestronProgInfo 4 }

		
		-- 1.3.6.1.4.1.3212.2.2.3.2.5
		crestronProgCompiledOn OBJECT-TYPE
			SYNTAX DisplayString
			MAX-ACCESS read-only
			STATUS current
			DESCRIPTION
				"Description."
			::= { crestronProgInfo 5 }

		
		-- 1.3.6.1.4.1.3212.2.2.3.2.6
		crestronProgState OBJECT-TYPE
			SYNTAX ProgramState
			MAX-ACCESS read-write
			STATUS current
			DESCRIPTION
				"Description."
			::= { crestronProgInfo 6 }

		
		-- 1.3.6.1.4.1.3212.2.2.5
		crestronProgConformance OBJECT IDENTIFIER ::= { crestronProgram 5 }

		
		-- 1.3.6.1.4.1.3212.2.2.5.1
		crestronProgCompliances OBJECT IDENTIFIER ::= { crestronProgConformance 1 }

		
		-- 1.3.6.1.4.1.3212.2.2.5.2
		crestronProgGroups OBJECT IDENTIFIER ::= { crestronProgConformance 2 }

		
-- Have to create this for SMIv2 but is not used yet.
		-- 1.3.6.1.4.1.3212.2.2.5.2.1
		crestronProgAllObjects OBJECT-GROUP
			OBJECTS { crestronProgMIBVersion, crestronProgUptime, crestronProgLabel, crestronProgSymbolCnt, crestronProgFilename, 
				crestronProgCompiledOn, crestronProgState }
			STATUS current
			DESCRIPTION 
				"Description."
			::= { crestronProgGroups 1 }

		
		-- 1.3.6.1.4.1.3212.2.2.5.2.2
		crestronProgAllTraps NOTIFICATION-GROUP
			NOTIFICATIONS { crestronProgStateChangeTrap }
			STATUS current
			DESCRIPTION 
				"Description."
			::= { crestronProgGroups 2 }

		
	
	END

--
-- CRESTRON-PROGRAM-MIB.my
--
