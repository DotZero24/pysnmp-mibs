--
-- CRESTRON-PRODUCTS-MIB.my
-- MIB generated by MG-SOFT Visual MIB Builder Version 6.0  Build 88
-- Wednesday, May 18, 2005 at 20:00:49
--

	CRESTRON-PRODUCTS-MIB DEFINITIONS ::= BEGIN
 
		IMPORTS
			crestron			
				FROM CRESTRON-ROOT-MIB			
			MODULE-IDENTITY, OBJECT-IDENTITY			
				FROM SNMPv2-SMI;
	
	
		-- 1.3.6.1.4.1.3212.9
		crestronProducts MODULE-IDENTITY 
			LAST-UPDATED "200505181925Z"		-- May 18, 2005 at 19:25 GMT
			ORGANIZATION 
				"Organization."
			CONTACT-INFO 
				"Contact-info."
			DESCRIPTION 
				"The purpose of this MIB is solely to list the products which support SNMP.  
				hrProcessorFrwID will hold a value from this MIB to indicate which specific product is present."
			::= { crestron 9 }

		
	
	
--
-- Node definitions
--
	
		-- 1.3.6.1.4.1.3212.9.1
		crestronProductPRO2 OBJECT-IDENTITY
			STATUS current
			DESCRIPTION 
				"A 2-series control system product."
			::= { crestronProducts 1 }

		
		-- 1.3.6.1.4.1.3212.9.2
		crestronProductQMRMC OBJECT-IDENTITY
			STATUS current
			DESCRIPTION 
				"Description."
			::= { crestronProducts 2 }

		
		-- 1.3.6.1.4.1.3212.9.3
		crestronProductQMRMCRX OBJECT-IDENTITY
			STATUS current
			DESCRIPTION 
				"Description."
			::= { crestronProducts 3 }

		
		-- 1.3.6.1.4.1.3212.9.4
		crestronProductDVP4 OBJECT-IDENTITY
			STATUS current
			DESCRIPTION 
				"Description."
			::= { crestronProducts 4 }

		
		-- 1.3.6.1.4.1.3212.9.5
		crestronProductMP2 OBJECT-IDENTITY
			STATUS current
			DESCRIPTION 
				"Description."
			::= { crestronProducts 5 }

		
		-- 1.3.6.1.4.1.3212.9.6
		crestronProductPollAcc OBJECT-IDENTITY
			STATUS current
			DESCRIPTION 
				"Description."
			::= { crestronProducts 6 }

		
	
	END

--
-- CRESTRON-PRODUCTS-MIB.my
--
