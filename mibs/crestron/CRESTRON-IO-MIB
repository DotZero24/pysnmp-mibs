--
-- CRESTRON-IO-MIB.my
-- MIB generated by MG-SOFT Visual MIB Builder Version 5.0  Build 250
-- Thursday, June 10, 2004 at 10:22:51
--

--  CRESTRON-IO-MIB.my
-- MIB generated by MG-SOFT Visual MIB Builder Version 5.0  Build 250
-- Tuesday, May 04, 2004 at 10:32:45
--

	CRESTRON-IO-MIB DEFINITIONS ::= BEGIN

		IMPORTS
			crestronControl, Digital
				FROM CRESTRON-ROOT-MIB
			OBJECT-GROUP, NOTIFICATION-GROUP
				FROM SNMPv2-CONF
			Integer32, OBJECT-TYPE, MODULE-IDENTITY, NOTIFICATION-TYPE
				FROM SNMPv2-SMI
			DisplayString, TEXTUAL-CONVENTION
				FROM SNMPv2-TC;


--  1.3.6.1.4.1.3212.1.1
-- August 18, 2003 at 16:21 GMT
		-- 1.3.6.1.4.1.3212.7.1
		crestronIo MODULE-IDENTITY
			LAST-UPDATED "200308181621Z"		-- August 18, 2003 at 16:21 GMT
			ORGANIZATION
				"Crestron Electronics, Inc."
			CONTACT-INFO
				"Crestron Electronics, Inc.
				15 Volvo Dr.
				Rockleigh NJ 07647
				Phone: (201) 767-3400
				Fax: (201) 767-1905"
			DESCRIPTION
				"A generic MIB for control systems based on analog, digital, and string inputs and outputs."
			::= { crestronControl 1 }



--
-- Textual conventions
--

--  Textual conventions
--
		IoId ::= TEXTUAL-CONVENTION
			STATUS current
			DESCRIPTION
				"Description."
			SYNTAX INTEGER (1..65535)

		Comparator ::= TEXTUAL-CONVENTION
			STATUS current
			DESCRIPTION
				"Description."
			SYNTAX INTEGER
				{
				equals(1),
				greaterThan(2),
				lessThan(3),
				greaterThanOrEqualTo(4),
				lessThanOrEqualTo(5),
				notEqualTo(6)
				}


--
-- Node definitions
--

		-- 1.3.6.1.4.1.3212.7.1.1
		crestronIoAdmin OBJECT IDENTIFIER ::= { crestronIo 1 }


		-- 1.3.6.1.4.1.3212.7.1.2
		crestronIoNotifications OBJECT IDENTIFIER ::= { crestronIo 2 }


--  1.3.6.1.4.1.3212.1.1.4.1
		-- 1.3.6.1.4.1.3212.7.1.2.1
		crestronIoTrap NOTIFICATION-TYPE
			STATUS current
			DESCRIPTION
				"Description."
			::= { crestronIoNotifications 1 }


--  1.3.6.1.4.1.3212.1.1.5.1
		-- 1.3.6.1.4.1.3212.7.1.2.2
		crestronIoDigitalTrapData OBJECT-TYPE
			SYNTAX Digital
			MAX-ACCESS accessible-for-notify
			STATUS current
			DESCRIPTION
				"Description."
			::= { crestronIoNotifications 2 }


--  1.3.6.1.4.1.3212.1.1.5.2
		-- 1.3.6.1.4.1.3212.7.1.2.3
		crestronIoAnalogTrapData OBJECT-TYPE
			SYNTAX Integer32
			MAX-ACCESS accessible-for-notify
			STATUS current
			DESCRIPTION
				"Description."
			::= { crestronIoNotifications 3 }


--  1.3.6.1.4.1.3212.1.1.5.3
		-- 1.3.6.1.4.1.3212.7.1.2.4
		crestronIoSerialTrapData OBJECT-TYPE
			SYNTAX OCTET STRING
			MAX-ACCESS accessible-for-notify
			STATUS current
			DESCRIPTION
				"Description."
			::= { crestronIoNotifications 4 }


		-- 1.3.6.1.4.1.3212.7.1.3
		crestronIoObjects OBJECT IDENTIFIER ::= { crestronIo 3 }


--  Node definitions
--
-- 1.3.6.1.4.1.3212.1.1.1
		-- 1.3.6.1.4.1.3212.7.1.3.1
		crestronIoVersion OBJECT-TYPE
			SYNTAX Integer32
			MAX-ACCESS read-only
			STATUS current
			DESCRIPTION
				"Version number for this MIB."
			::= { crestronIoObjects 1 }


--  1.3.6.1.4.1.3212.1.1.6
		-- 1.3.6.1.4.1.3212.7.1.3.2
		crestronIoDigital OBJECT IDENTIFIER ::= { crestronIoObjects 2 }


--  1.3.6.1.4.1.3212.1.1.6.1
		-- 1.3.6.1.4.1.3212.7.1.3.2.1
		crestronIoDigitalReadWrite OBJECT IDENTIFIER ::= { crestronIoDigital 1 }


--  1.3.6.1.4.1.3212.1.1.6.1.1
		-- 1.3.6.1.4.1.3212.7.1.3.2.1.1
		crestronIoDigitalReadWriteTable OBJECT-TYPE
			SYNTAX SEQUENCE OF CrestronIoDigitalReadWriteEntry
			MAX-ACCESS not-accessible
			STATUS current
			DESCRIPTION
				"Description."
			::= { crestronIoDigitalReadWrite 1 }


--  1.3.6.1.4.1.3212.1.1.6.1.1.1
		-- 1.3.6.1.4.1.3212.7.1.3.2.1.1.1
		crestronIoDigitalReadWriteEntry OBJECT-TYPE
			SYNTAX CrestronIoDigitalReadWriteEntry
			MAX-ACCESS not-accessible
			STATUS current
			DESCRIPTION
				"Description."
			INDEX { crestronIoDigitalReadWriteIoId }
			::= { crestronIoDigitalReadWriteTable 1 }


		CrestronIoDigitalReadWriteEntry ::=
			SEQUENCE {
				crestronIoDigitalReadWriteIoId
					IoId,
				crestronIoDigitalReadWriteIoText
					DisplayString,
				crestronIoDigitalReadWriteValue
					Integer32,
				crestronIoDigitalReadWrite0Text
					DisplayString,
				crestronIoDigitalReadWrite1Text
					DisplayString
			 }

--  1.3.6.1.4.1.3212.1.1.6.1.1.1.1
		-- 1.3.6.1.4.1.3212.7.1.3.2.1.1.1.1
		crestronIoDigitalReadWriteIoId OBJECT-TYPE
			SYNTAX IoId
			MAX-ACCESS read-only
			STATUS current
			DESCRIPTION
				"Description."
			::= { crestronIoDigitalReadWriteEntry 1 }


--  1.3.6.1.4.1.3212.1.1.6.1.1.1.2
		-- 1.3.6.1.4.1.3212.7.1.3.2.1.1.1.2
		crestronIoDigitalReadWriteIoText OBJECT-TYPE
			SYNTAX DisplayString
			MAX-ACCESS read-only
			STATUS current
			DESCRIPTION
				"Description."
			::= { crestronIoDigitalReadWriteEntry 2 }


--  1.3.6.1.4.1.3212.1.1.6.1.1.1.3
		-- 1.3.6.1.4.1.3212.7.1.3.2.1.1.1.3
		crestronIoDigitalReadWriteValue OBJECT-TYPE
			SYNTAX Integer32 (0..1)
			MAX-ACCESS read-write
			STATUS current
			DESCRIPTION
				"Description."
			::= { crestronIoDigitalReadWriteEntry 3 }


--  1.3.6.1.4.1.3212.1.1.6.1.1.1.4
		-- 1.3.6.1.4.1.3212.7.1.3.2.1.1.1.4
		crestronIoDigitalReadWrite0Text OBJECT-TYPE
			SYNTAX DisplayString
			MAX-ACCESS read-only
			STATUS current
			DESCRIPTION
				"Description."
			::= { crestronIoDigitalReadWriteEntry 4 }


--  1.3.6.1.4.1.3212.1.1.6.1.1.1.5
		-- 1.3.6.1.4.1.3212.7.1.3.2.1.1.1.5
		crestronIoDigitalReadWrite1Text OBJECT-TYPE
			SYNTAX DisplayString
			MAX-ACCESS read-only
			STATUS current
			DESCRIPTION
				"Description."
			::= { crestronIoDigitalReadWriteEntry 5 }


--  1.3.6.1.4.1.3212.1.1.6.2
		-- 1.3.6.1.4.1.3212.7.1.3.2.2
		crestronIoDigitalReadOnly OBJECT IDENTIFIER ::= { crestronIoDigital 2 }


--  1.3.6.1.4.1.3212.1.1.6.2.1
		-- 1.3.6.1.4.1.3212.7.1.3.2.2.1
		crestronIoDigitalReadOnlyTable OBJECT-TYPE
			SYNTAX SEQUENCE OF CrestronIoDigitalReadOnlyEntry
			MAX-ACCESS not-accessible
			STATUS current
			DESCRIPTION
				"Description."
			::= { crestronIoDigitalReadOnly 1 }


--  1.3.6.1.4.1.3212.1.1.6.2.1.1
		-- 1.3.6.1.4.1.3212.7.1.3.2.2.1.1
		crestronIoDigitalReadOnlyEntry OBJECT-TYPE
			SYNTAX CrestronIoDigitalReadOnlyEntry
			MAX-ACCESS not-accessible
			STATUS current
			DESCRIPTION
				"Description."
			INDEX { crestronIoDigitalReadOnlyIoId }
			::= { crestronIoDigitalReadOnlyTable 1 }


		CrestronIoDigitalReadOnlyEntry ::=
			SEQUENCE {
				crestronIoDigitalReadOnlyIoId
					IoId,
				crestronIoDigitalReadOnlyIoText
					DisplayString,
				crestronIoDigitalReadOnlyValue
					Integer32,
				crestronIoDigitalReadOnly0Text
					DisplayString,
				crestronIoDigitalReadOnly1Text
					DisplayString
			 }

--  1.3.6.1.4.1.3212.1.1.6.2.1.1.1
		-- 1.3.6.1.4.1.3212.7.1.3.2.2.1.1.1
		crestronIoDigitalReadOnlyIoId OBJECT-TYPE
			SYNTAX IoId
			MAX-ACCESS read-only
			STATUS current
			DESCRIPTION
				"Description."
			::= { crestronIoDigitalReadOnlyEntry 1 }


--  1.3.6.1.4.1.3212.1.1.6.2.1.1.2
		-- 1.3.6.1.4.1.3212.7.1.3.2.2.1.1.2
		crestronIoDigitalReadOnlyIoText OBJECT-TYPE
			SYNTAX DisplayString
			MAX-ACCESS read-only
			STATUS current
			DESCRIPTION
				"Description."
			::= { crestronIoDigitalReadOnlyEntry 2 }


--  1.3.6.1.4.1.3212.1.1.6.2.1.1.3
		-- 1.3.6.1.4.1.3212.7.1.3.2.2.1.1.3
		crestronIoDigitalReadOnlyValue OBJECT-TYPE
			SYNTAX Integer32 (0..1)
			MAX-ACCESS read-only
			STATUS current
			DESCRIPTION
				"Description."
			::= { crestronIoDigitalReadOnlyEntry 3 }


--  1.3.6.1.4.1.3212.1.1.6.2.1.1.4
		-- 1.3.6.1.4.1.3212.7.1.3.2.2.1.1.4
		crestronIoDigitalReadOnly0Text OBJECT-TYPE
			SYNTAX DisplayString
			MAX-ACCESS read-only
			STATUS current
			DESCRIPTION
				"Description."
			::= { crestronIoDigitalReadOnlyEntry 4 }


--  1.3.6.1.4.1.3212.1.1.6.2.1.1.5
		-- 1.3.6.1.4.1.3212.7.1.3.2.2.1.1.5
		crestronIoDigitalReadOnly1Text OBJECT-TYPE
			SYNTAX DisplayString
			MAX-ACCESS read-only
			STATUS current
			DESCRIPTION
				"Description."
			::= { crestronIoDigitalReadOnlyEntry 5 }


--  1.3.6.1.4.1.3212.1.1.7
		-- 1.3.6.1.4.1.3212.7.1.3.3
		crestronIoAnalog OBJECT IDENTIFIER ::= { crestronIoObjects 3 }


--  1.3.6.1.4.1.3212.1.1.7.1
		-- 1.3.6.1.4.1.3212.7.1.3.3.1
		crestronIoAnalogReadWrite OBJECT IDENTIFIER ::= { crestronIoAnalog 1 }


--  1.3.6.1.4.1.3212.1.1.7.1.1
		-- 1.3.6.1.4.1.3212.7.1.3.3.1.1
		crestronIoAnalogReadWriteTable OBJECT-TYPE
			SYNTAX SEQUENCE OF CrestronIoAnalogReadWriteEntry
			MAX-ACCESS not-accessible
			STATUS current
			DESCRIPTION
				"Description."
			::= { crestronIoAnalogReadWrite 1 }


--  1.3.6.1.4.1.3212.1.1.7.1.1.1
		-- 1.3.6.1.4.1.3212.7.1.3.3.1.1.1
		crestronIoAnalogReadWriteEntry OBJECT-TYPE
			SYNTAX CrestronIoAnalogReadWriteEntry
			MAX-ACCESS not-accessible
			STATUS current
			DESCRIPTION
				"Description."
			INDEX { crestronIoAnalogReadWriteIoId }
			::= { crestronIoAnalogReadWriteTable 1 }


		CrestronIoAnalogReadWriteEntry ::=
			SEQUENCE {
				crestronIoAnalogReadWriteIoId
					IoId,
				crestronIoAnalogReadWriteText
					DisplayString,
				crestronIoAnalogReadWriteValue
					Integer32
			 }

--  1.3.6.1.4.1.3212.1.1.7.1.1.1.1
		-- 1.3.6.1.4.1.3212.7.1.3.3.1.1.1.1
		crestronIoAnalogReadWriteIoId OBJECT-TYPE
			SYNTAX IoId
			MAX-ACCESS read-only
			STATUS current
			DESCRIPTION
				"Description."
			::= { crestronIoAnalogReadWriteEntry 1 }


--  1.3.6.1.4.1.3212.1.1.7.1.1.1.2
		-- 1.3.6.1.4.1.3212.7.1.3.3.1.1.1.2
		crestronIoAnalogReadWriteText OBJECT-TYPE
			SYNTAX DisplayString
			MAX-ACCESS read-only
			STATUS current
			DESCRIPTION
				"Description."
			::= { crestronIoAnalogReadWriteEntry 2 }


--  1.3.6.1.4.1.3212.1.1.7.1.1.1.3
		-- 1.3.6.1.4.1.3212.7.1.3.3.1.1.1.3
		crestronIoAnalogReadWriteValue OBJECT-TYPE
			SYNTAX Integer32
			MAX-ACCESS read-write
			STATUS current
			DESCRIPTION
				"Description."
			::= { crestronIoAnalogReadWriteEntry 3 }


--  1.3.6.1.4.1.3212.1.1.7.2
		-- 1.3.6.1.4.1.3212.7.1.3.3.2
		crestronIoAnalogReadOnly OBJECT IDENTIFIER ::= { crestronIoAnalog 2 }


--  1.3.6.1.4.1.3212.1.1.7.2.1
		-- 1.3.6.1.4.1.3212.7.1.3.3.2.1
		crestronIoAnalogReadOnlyTable OBJECT-TYPE
			SYNTAX SEQUENCE OF CrestronIoAnalogReadOnlyEntry
			MAX-ACCESS not-accessible
			STATUS current
			DESCRIPTION
				"Description."
			::= { crestronIoAnalogReadOnly 1 }


--  1.3.6.1.4.1.3212.1.1.7.2.1.1
		-- 1.3.6.1.4.1.3212.7.1.3.3.2.1.1
		crestronIoAnalogReadOnlyEntry OBJECT-TYPE
			SYNTAX CrestronIoAnalogReadOnlyEntry
			MAX-ACCESS not-accessible
			STATUS current
			DESCRIPTION
				"Description."
			INDEX { crestronIoAnalogReadOnlyIoId }
			::= { crestronIoAnalogReadOnlyTable 1 }


		CrestronIoAnalogReadOnlyEntry ::=
			SEQUENCE {
				crestronIoAnalogReadOnlyIoId
					IoId,
				crestronIoAnalogReadOnlyText
					DisplayString,
				crestronIoAnalogReadOnlyValue
					Integer32
			 }

--  1.3.6.1.4.1.3212.1.1.7.2.1.1.1
		-- 1.3.6.1.4.1.3212.7.1.3.3.2.1.1.1
		crestronIoAnalogReadOnlyIoId OBJECT-TYPE
			SYNTAX IoId
			MAX-ACCESS read-only
			STATUS current
			DESCRIPTION
				"Description."
			::= { crestronIoAnalogReadOnlyEntry 1 }


--  1.3.6.1.4.1.3212.1.1.7.2.1.1.2
		-- 1.3.6.1.4.1.3212.7.1.3.3.2.1.1.2
		crestronIoAnalogReadOnlyText OBJECT-TYPE
			SYNTAX DisplayString
			MAX-ACCESS read-only
			STATUS current
			DESCRIPTION
				"Description."
			::= { crestronIoAnalogReadOnlyEntry 2 }


--  1.3.6.1.4.1.3212.1.1.7.2.1.1.3
		-- 1.3.6.1.4.1.3212.7.1.3.3.2.1.1.3
		crestronIoAnalogReadOnlyValue OBJECT-TYPE
			SYNTAX Integer32
			MAX-ACCESS read-only
			STATUS current
			DESCRIPTION
				"Description."
			::= { crestronIoAnalogReadOnlyEntry 3 }


--  Maps integer values to meaningful strings.
-- 1.3.6.1.4.1.3212.1.1.7.3
		-- 1.3.6.1.4.1.3212.7.1.3.3.3
		crestronValue OBJECT IDENTIFIER ::= { crestronIoAnalog 3 }


--  1.3.6.1.4.1.3212.1.1.7.3.1
		-- 1.3.6.1.4.1.3212.7.1.3.3.3.1
		crestronValueTable OBJECT-TYPE
			SYNTAX SEQUENCE OF CrestronValueEntry
			MAX-ACCESS not-accessible
			STATUS current
			DESCRIPTION
				"Description."
			::= { crestronValue 1 }


--  1.3.6.1.4.1.3212.1.1.7.3.1.1
		-- 1.3.6.1.4.1.3212.7.1.3.3.3.1.1
		crestronValueEntry OBJECT-TYPE
			SYNTAX CrestronValueEntry
			MAX-ACCESS not-accessible
			STATUS current
			DESCRIPTION
				"Description."
			INDEX { crestronValueIoId }
			::= { crestronValueTable 1 }


		CrestronValueEntry ::=
			SEQUENCE {
				crestronValueIoId
					Integer32,
				crestronValueValue
					Integer32,
				crestronValueText
					DisplayString
			 }

--  1.3.6.1.4.1.3212.1.1.7.3.1.1.1
		-- 1.3.6.1.4.1.3212.7.1.3.3.3.1.1.1
		crestronValueIoId OBJECT-TYPE
			SYNTAX Integer32 (1..65535)
			MAX-ACCESS read-only
			STATUS current
			DESCRIPTION
				"Description."
			::= { crestronValueEntry 1 }


--  1.3.6.1.4.1.3212.1.1.7.3.1.1.2
		-- 1.3.6.1.4.1.3212.7.1.3.3.3.1.1.2
		crestronValueValue OBJECT-TYPE
			SYNTAX Integer32
			MAX-ACCESS read-only
			STATUS current
			DESCRIPTION
				"Description."
			::= { crestronValueEntry 2 }


--  1.3.6.1.4.1.3212.1.1.7.3.1.1.3
		-- 1.3.6.1.4.1.3212.7.1.3.3.3.1.1.3
		crestronValueText OBJECT-TYPE
			SYNTAX DisplayString
			MAX-ACCESS read-only
			STATUS current
			DESCRIPTION
				"Description."
			::= { crestronValueEntry 3 }


--  1.3.6.1.4.1.3212.1.1.8
		-- 1.3.6.1.4.1.3212.7.1.3.4
		crestronIoSerial OBJECT IDENTIFIER ::= { crestronIoObjects 4 }


--  1.3.6.1.4.1.3212.1.1.8.1
		-- 1.3.6.1.4.1.3212.7.1.3.4.1
		crestronIoSerialReadWrite OBJECT IDENTIFIER ::= { crestronIoSerial 1 }


--  1.3.6.1.4.1.3212.1.1.8.1.1
		-- 1.3.6.1.4.1.3212.7.1.3.4.1.1
		crestronIoSerialReadWriteTable OBJECT-TYPE
			SYNTAX SEQUENCE OF CrestronIoSerialReadWriteEntry
			MAX-ACCESS not-accessible
			STATUS current
			DESCRIPTION
				"Description."
			::= { crestronIoSerialReadWrite 1 }


--  1.3.6.1.4.1.3212.1.1.8.1.1.1
		-- 1.3.6.1.4.1.3212.7.1.3.4.1.1.1
		crestronIoSerialReadWriteEntry OBJECT-TYPE
			SYNTAX CrestronIoSerialReadWriteEntry
			MAX-ACCESS not-accessible
			STATUS current
			DESCRIPTION
				"Description."
			INDEX { crestronIoSerialReadWriteIoId }
			::= { crestronIoSerialReadWriteTable 1 }


		CrestronIoSerialReadWriteEntry ::=
			SEQUENCE {
				crestronIoSerialReadWriteIoId
					IoId,
				crestronIoSerialReadWriteIoText
					DisplayString,
				crestronIoSerialReadWriteValue
					OCTET STRING
			 }

--  1.3.6.1.4.1.3212.1.1.8.1.1.1.1
		-- 1.3.6.1.4.1.3212.7.1.3.4.1.1.1.1
		crestronIoSerialReadWriteIoId OBJECT-TYPE
			SYNTAX IoId
			MAX-ACCESS read-only
			STATUS current
			DESCRIPTION
				"Description."
			::= { crestronIoSerialReadWriteEntry 1 }


--  1.3.6.1.4.1.3212.1.1.8.1.1.1.2
		-- 1.3.6.1.4.1.3212.7.1.3.4.1.1.1.2
		crestronIoSerialReadWriteIoText OBJECT-TYPE
			SYNTAX DisplayString
			MAX-ACCESS read-only
			STATUS current
			DESCRIPTION
				"Description."
			::= { crestronIoSerialReadWriteEntry 2 }


--  1.3.6.1.4.1.3212.1.1.8.1.1.1.3
		-- 1.3.6.1.4.1.3212.7.1.3.4.1.1.1.3
		crestronIoSerialReadWriteValue OBJECT-TYPE
			SYNTAX OCTET STRING
			MAX-ACCESS read-write
			STATUS current
			DESCRIPTION
				"Description."
			::= { crestronIoSerialReadWriteEntry 3 }


--  1.3.6.1.4.1.3212.1.1.8.2
		-- 1.3.6.1.4.1.3212.7.1.3.4.2
		crestronIoSerialReadOnly OBJECT IDENTIFIER ::= { crestronIoSerial 2 }


--  1.3.6.1.4.1.3212.1.1.8.2.1
		-- 1.3.6.1.4.1.3212.7.1.3.4.2.1
		crestronIoSerialReadOnlyTable OBJECT-TYPE
			SYNTAX SEQUENCE OF CrestronIoSerialReadOnlyEntry
			MAX-ACCESS not-accessible
			STATUS current
			DESCRIPTION
				"Description."
			::= { crestronIoSerialReadOnly 1 }


--  1.3.6.1.4.1.3212.1.1.8.2.1.1
		-- 1.3.6.1.4.1.3212.7.1.3.4.2.1.1
		crestronIoSerialReadOnlyEntry OBJECT-TYPE
			SYNTAX CrestronIoSerialReadOnlyEntry
			MAX-ACCESS not-accessible
			STATUS current
			DESCRIPTION
				"Description."
			INDEX { crestronIoSerialReadOnlyIoId }
			::= { crestronIoSerialReadOnlyTable 1 }


		CrestronIoSerialReadOnlyEntry ::=
			SEQUENCE {
				crestronIoSerialReadOnlyIoId
					IoId,
				crestronIoSerialReadOnlyIoText
					DisplayString,
				crestronIoSerialReadOnlyValue
					OCTET STRING
			 }

--  1.3.6.1.4.1.3212.1.1.8.2.1.1.1
		-- 1.3.6.1.4.1.3212.7.1.3.4.2.1.1.1
		crestronIoSerialReadOnlyIoId OBJECT-TYPE
			SYNTAX IoId
			MAX-ACCESS read-only
			STATUS current
			DESCRIPTION
				"Description."
			::= { crestronIoSerialReadOnlyEntry 1 }


--  1.3.6.1.4.1.3212.1.1.8.2.1.1.2
		-- 1.3.6.1.4.1.3212.7.1.3.4.2.1.1.2
		crestronIoSerialReadOnlyIoText OBJECT-TYPE
			SYNTAX DisplayString
			MAX-ACCESS read-only
			STATUS current
			DESCRIPTION
				"Description."
			::= { crestronIoSerialReadOnlyEntry 2 }


--  1.3.6.1.4.1.3212.1.1.8.2.1.1.3
		-- 1.3.6.1.4.1.3212.7.1.3.4.2.1.1.3
		crestronIoSerialReadOnlyValue OBJECT-TYPE
			SYNTAX OCTET STRING
			MAX-ACCESS read-only
			STATUS current
			DESCRIPTION
				"Description."
			::= { crestronIoSerialReadOnlyEntry 3 }


		-- 1.3.6.1.4.1.3212.7.1.5
		crestronIoConformance OBJECT IDENTIFIER ::= { crestronIo 5 }


		-- 1.3.6.1.4.1.3212.7.1.5.1
		crestronIoCompliances OBJECT IDENTIFIER ::= { crestronIoConformance 1 }


		-- 1.3.6.1.4.1.3212.7.1.5.2
		crestronIoGroups OBJECT IDENTIFIER ::= { crestronIoConformance 2 }


--  1.3.6.1.4.1.3212.1.1.2.4
		-- 1.3.6.1.4.1.3212.7.1.5.2.1
		crestronIoInputObjects OBJECT-GROUP
			OBJECTS { crestronIoAnalogReadWriteIoId, crestronIoAnalogReadWriteValue, crestronIoDigitalReadWriteIoId, crestronIoDigitalReadWriteValue, crestronIoAnalogReadWriteText,
				crestronIoDigitalReadWriteIoText, crestronIoDigitalReadWrite0Text, crestronIoDigitalReadWrite1Text, crestronIoSerialReadWriteIoId, crestronIoSerialReadWriteIoText,
				crestronIoSerialReadWriteValue }
			STATUS current
			DESCRIPTION
				"Description."
			::= { crestronIoGroups 1 }


--  1.3.6.1.4.1.3212.1.1.2.5
		-- 1.3.6.1.4.1.3212.7.1.5.2.2
		crestronIoOutputObjects OBJECT-GROUP
			OBJECTS { crestronIoAnalogReadOnlyIoId, crestronIoAnalogReadOnlyValue, crestronIoDigitalReadOnlyIoId, crestronIoDigitalReadOnlyValue, crestronIoAnalogReadOnlyText,
				crestronIoDigitalReadWriteIoText, crestronIoDigitalReadWrite0Text, crestronIoDigitalReadWrite1Text, crestronIoDigitalReadOnly1Text, crestronIoDigitalReadOnly0Text,
				crestronIoDigitalReadOnlyIoText, crestronIoSerialReadOnlyIoId, crestronIoSerialReadOnlyIoText, crestronIoSerialReadOnlyValue }
			STATUS current
			DESCRIPTION
				"Description."
			::= { crestronIoGroups 2 }


--  1.3.6.1.4.1.3212.1.1.2.7
		-- 1.3.6.1.4.1.3212.7.1.5.2.3
		crestronIoMiscObjects OBJECT-GROUP
			OBJECTS { crestronIoVersion, crestronValueIoId, crestronValueValue, crestronValueText, crestronIoDigitalTrapData,
				crestronIoAnalogTrapData, crestronIoSerialTrapData }
			STATUS current
			DESCRIPTION
				"Description."
			::= { crestronIoGroups 3 }


--  1.3.6.1.4.1.3212.1.1.3.1
		-- 1.3.6.1.4.1.3212.7.1.5.2.4
		crestronIoTrapObjects NOTIFICATION-GROUP
			NOTIFICATIONS { crestronIoTrap }
			STATUS current
			DESCRIPTION
				"Description."
			::= { crestronIoGroups 4 }



	END

--
-- CRESTRON-IO-MIB.my
--
