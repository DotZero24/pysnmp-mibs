RUGGEDCOM-SERIAL-MIB DEFINITIONS ::= BEGIN

IMPORTS
    MODULE-IDENTITY, OBJECT-IDENTITY,
    OBJECT-TYPE, IpAddress,
    Integer32                			FROM SNMPv2-SMI
    OBJECT-GROUP			       	    FROM SNMPv2-CONF
    TEXTUAL-CONVENTION					FROM SNMPv2-TC
	PortList							FROM Q-BRIDGE-MIB
   	ruggedcomMgmt                   	FROM RUGGEDCOM-MIB
	InterfaceIndex				        FROM IF-MIB;

rcSerial MODULE-IDENTITY
    LAST-UPDATED "201101111000Z"      -- Jan 11, 10:00 EST 2011
    ORGANIZATION "RuggedCom"
    CONTACT-INFO
       "Postal: RuggedCom Inc.
                300 Applewood Crescent
                Concord, Ontario,
                L4K 5C7 Canada
        Tel:    1-905-856-5288
        E-Mail: support@ruggedcom.com"

    DESCRIPTION
        "RuggedCom MIB for Managing Proprietary Settings for Serial Ports and
        Serial Protocols on RuggedCom Serial Server Devices."

	REVISION	"201101111000Z"      -- Jan 11, 10:00 EST 2011
    DESCRIPTION
        "The initial version of RuggedCom MIB for Serial Ports and Serial Protocols."

    ::= { ruggedcomMgmt 6 }

-- ---------------------------------------------------------------------- --
-- Textual Conventions
-- ---------------------------------------------------------------------- --

-- Copied from P-BRIDGE-MIB to avoid compilation of that mib
-- as ROS does not support P-BRIDGE-MIB

EnabledStatus ::= TEXTUAL-CONVENTION
    STATUS      current
    DESCRIPTION
        "A simple status value for the object."
    SYNTAX	INTEGER {
    			enabled(1),
    			disabled(2)
    		}

RcFlowControl ::= TEXTUAL-CONVENTION
	STATUS	current
	DESCRIPTION
		"FlowControl setting for serial port."
	SYNTAX	INTEGER	{
				none(1),
				xonXoff(2)
			}

RcSerProtocol	::= TEXTUAL-CONVENTION
	STATUS	current
	DESCRIPTION
		"Serial Protocols permitted for RuggedCom Serial Device Servers."
	SYNTAX  INTEGER  {
     			noProtocol(1),
     			rawSock(2),
     			modbusServer(3),
     			modbusClient(4),
     			itcsWIN(5),
     			itcsTIN(6),
     			microlok(7),
     			dnp(8),
     			dnpRawSock(9),
     			mirrorBits(10),
     			preemptRawSock(11),
     			telnetComport(12)
     		}

RcTransport ::= TEXTUAL-CONVENTION
	STATUS	current
	DESCRIPTION
		"Transport protocol used for IP traffic."
	SYNTAX	INTEGER {
				udp(1),
				tcp(2)
			}

RcCallDir ::= TEXTUAL-CONVENTION
	STATUS	current
	DESCRIPTION
		"Call Direction options for a RuggedCom Serial Server device."
	SYNTAX	INTEGER {
				in(0),
				out(1),
				both(2)
			}

RcSerPortType ::= TEXTUAL-CONVENTION
	STATUS	current
	DESCRIPTION
		"Serial Port Type for RuggedCom Serial Server device."
	SYNTAX	INTEGER	{
				none(0),
				rs232(1),
				rs485(2),
				rs422(3),
				tpc(4),
				fiber(5)
			}

-- ---------------------------------------------------------------------- --
--  rcSerial subtrees
-- ---------------------------------------------------------------------- --

rcSerialPortParams OBJECT-IDENTITY
    STATUS      current
    DESCRIPTION
        "The main subtree for managing Global Serial Port parameters."
    ::= { rcSerial  1 }

rcMbServer		OBJECT-IDENTITY
	STATUS		current
	DESCRIPTION
	    "The main subtree for managing the  Modbus Protocol Server settings
	    on RuggedCom serial Devices."
	::= { rcSerial 2 }

rcMbClient	OBJECT-IDENTITY
	STATUS	current
	DESCRIPTION
		"The main subtree for managing the Modbus Protocol Client Settings on
		RuggedCom serial devices."
	::= { rcSerial 3 }

rcRawSock	OBJECT-IDENTITY
	STATUS	current
	DESCRIPTION
		"The main subtree for managing the Raw Socket Protocol Settings on
		RuggedCom serial devices."
	::= { rcSerial 4 }

rcPreemptRS	OBJECT-IDENTITY
	STATUS	current
	DESCRIPTION
		"The main subtree for managing the Preemptive Raw Socket Protocol
		settings on RuggedCom serial devices."
	::= { rcSerial 5 }

rcTinAndWin	OBJECT-IDENTITY
	STATUS			current
	DESCRIPTION
		"The main subtree for managing the TIN and WIN protocol settings on
		RuggedCom serial devices."
	::= { rcSerial	6 }

rcMicrolok	OBJECT-IDENTITY
	STATUS			current
	DESCRIPTION
		"The main subtree for managing the Microlok protocol settings on
		RuggedCom serial devices."
	::= { rcSerial 7 }

rcDnp	OBJECT-IDENTITY
	STATUS			current
	DESCRIPTION
		"Tha main subtree for managing the Dnp protocol settings on
		RuggedCom serial devices."
	::= { rcSerial 8 }

rcDnpRs OBJECT-IDENTITY
	STATUS			current
	DESCRIPTION
		"Tha main subtree for managing the Dnp over Raw Socket protocol
		settings on RuggedCom serial devices."
	::= { rcSerial 9 }

rcMirrorBits	OBJECT-IDENTITY
	STATUS			current
	DESCRIPTION
		"Tha main subtree for managing the Mirrored Bit protocol settings on
		RuggedCom serial devices."
	::= { rcSerial 10 }

rcTelnetComport	 OBJECT-IDENTITY
	STATUS			current
	DESCRIPTION
		"Tha main subtree for managing the TelnetPortComport protocol settings on
		RuggedCom serial devices."
	::= { rcSerial 11 }

rcConnStats OBJECT-IDENTITY
	STATUS	 current
	DESCRIPTION
		"The main subtree for the information about Connection Statistics for
		RuggedCom serial devices."
	::= { rcSerial 15 }

rcSerDeviceCmnd OBJECT-IDENTITY
    STATUS	current
    DESCRIPTION
    	"The main subtree for serial port control commands"
	::= { rcSerial 16}


-- ---------------------------------------------------------------------- --
-- ---------------------------------------------------------------------- --
rcSerialConformance	OBJECT IDENTIFIER ::= { rcSerial 18 }
-- rcSerialCompliances  OBJECT IDENTIFIER ::= { rcSerialConformance 1 }
rcSerialGroups		OBJECT IDENTIFIER ::= { rcSerialConformance 2 }


-- ---------------------------------------------------------------------- --
-- Serial Port configuration
-- ---------------------------------------------------------------------- --

rcSerialPortTable OBJECT-TYPE
	SYNTAX SEQUENCE OF RcSerialPortEntry
	MAX-ACCESS			not-accessible
	STATUS				current
	DESCRIPTION
	    "A list of port entries. The number of entries might be
	    retreived as the value of object 'rs232Number' from RFC1659."
	::= { rcSerialPortParams 1 }

rcSerialPortEntry OBJECT-TYPE
	SYNTAX				RcSerialPortEntry
	MAX-ACCESS			not-accessible
	STATUS				current
	DESCRIPTION
	    "Status and configuration parameters for a port."
        INDEX {
                rcSerialPortNumber
        }
	::= { rcSerialPortTable 1 }

RcSerialPortEntry ::= SEQUENCE {
		rcSerialPortNumber  Integer32,
		rcSerialPortIfIndex InterfaceIndex,
		rcSerialProtocol	RcSerProtocol,
		rcSerialPortType	RcSerPortType,
		rcSerialForceHD		INTEGER,
		rcSerialTurnAround	Integer32,
		rcSerialPostTxDelay Integer32,
		rcSerialHoldTime	Integer32,
		rcSerialDscp		Integer32,
		rcSerialRxtoTxDelay	Integer32
	}

rcSerialPortNumber	OBJECT-TYPE
	SYNTAX			Integer32 (1..65535)
    MAX-ACCESS  	not-accessible
    STATUS      	current
    DESCRIPTION
		"The physical Serial Port Number of the device  for which this Entry
		contains configuration settings."
	::= { rcSerialPortEntry 1 }

rcSerialPortIfIndex OBJECT-TYPE
	SYNTAX			InterfaceIndex
    MAX-ACCESS  	read-only
    STATUS      	current
    DESCRIPTION
		"The value of ifIndex for the port. This value is same as
		'rs232PortIndex' which is the index  used for 'rs232PortTable'
		in RS-232-MIB."
    ::= { rcSerialPortEntry 2 }

rcSerialProtocol	OBJECT-TYPE
	SYNTAX			RcSerProtocol
    MAX-ACCESS  	read-write
    STATUS      	current
    DESCRIPTION
		"A Serial Protocol supported on the Serial Port represented
		by this entry."
    ::= { rcSerialPortEntry 3 }

rcSerialPortType	OBJECT-TYPE
	SYNTAX			RcSerPortType
    MAX-ACCESS  	read-write
    STATUS      	current
    DESCRIPTION
		"A Serial Port Type supported on the Serial Port represented
		by this entry."
    ::= { rcSerialPortEntry 4 }

rcSerialForceHD OBJECT-TYPE
    SYNTAX  INTEGER {
	    		on(1),
	    		off(2),
	    		notApplicable(3)
    		}
    MAX-ACCESS  read-write
    STATUS      current
    DESCRIPTION
		"Enables forcing half duplex mode of operation on the Serial Port.

		While sending data out of the serial port all received data are ignored.
		This mode of operation is available only on ports that operate in full
		duplex mode"
    ::= { rcSerialPortEntry 5 }

rcSerialTurnAround OBJECT-TYPE
	SYNTAX      Integer32(0..1000 )
	UNITS		"milliseconds"
	MAX-ACCESS  read-write
	STATUS      current
	DESCRIPTION
		"The amount of delay between the transmission of individual messages
		out of the serial port.

		For 'rcSerialProtocol' object value modbusServer(3) this value must be non-zero.
		It represents delay between sending a brodcast message and the next poll
		out of serial port, because RTUs do not reply to a broadcast, so enough
		time must be ensured to process it."
        ::= { rcSerialPortEntry 6 }

rcSerialPostTxDelay OBJECT-TYPE
	SYNTAX      Integer32(0..15 )
	UNITS		"bits"
	MAX-ACCESS  read-write
	STATUS      current
	DESCRIPTION
		"The number of bits needed to generate required delay with configured
		baudrate('rs232PortOutSpeed') after the last bit of the packet was
		sent out before serial UART starts listening to the RX line .

		This value is relevant for RS485 interface only with 'rs232PortType'
		equals other(1)."
        ::= { rcSerialPortEntry 7 }

rcSerialHoldTime OBJECT-TYPE
	SYNTAX      Integer32(0..15000)
	UNITS		"milliseconds"
	MAX-ACCESS  read-write
	STATUS      current
	DESCRIPTION
		"The maximum amount of time in ms that serial packet can be held in the
		queue before being sent to the serial line.

		Time is measured from the moment the packet is received from the IP
		layer."
        ::= { rcSerialPortEntry 8 }

rcSerialDscp OBJECT-TYPE
	SYNTAX      Integer32(0..63)
	MAX-ACCESS  read-write
	STATUS      current
	DESCRIPTION
		"The value of DS byte to be set in the IP header.

		DS byte setting is supported in the egress direction only."
        ::= { rcSerialPortEntry 9 }

rcSerialRxtoTxDelay OBJECT-TYPE
	SYNTAX      Integer32(0..1000)
	UNITS		"milliseconds"
	MAX-ACCESS  read-write
	STATUS      current
	DESCRIPTION
		"The minimum amount of time in ms that the transmission of a new
		message should delay after the last message is received through the
		serial port.

		This parameter is useful, especially for the half duplex transmission
		mode, such as two-wire 	RS485 serial protocol.
		It ensures that the connected device gets enough time to turn off
		its transmitter and to turn on its receiver, so that it can receive
		next message without a single bit loss."
        ::= { rcSerialPortEntry 10 }

-- ---------------------------------------------------------------------- --
-- Modbus Server configuration
-- ---------------------------------------------------------------------- --
rcMbServerTable OBJECT-TYPE
	SYNTAX SEQUENCE OF  RcMbServerEntry
	MAX-ACCESS			not-accessible
	STATUS				current
	DESCRIPTION
	    "This table provides configuration options for the ports when
	    'rcSerialProtocol'equals modbusServer(3)."
	::= { rcMbServer 1 }

rcMbServerEntry OBJECT-TYPE
	SYNTAX		RcMbServerEntry
	MAX-ACCESS	not-accessible
	STATUS		current
	DESCRIPTION
	    "List of all the configuration options for a port for which
	    'rcSerialProtocol' equals modbusServer(3)."
	INDEX { rcMbServerPort }
	::= { rcMbServerTable 1 }

RcMbServerEntry ::=	SEQUENCE {
	    rcMbServerPort			Integer32,
	    rcMbServerRespTimer		Integer32,
	    rcMbServerAuxTcpPort	Integer32,
	    rcMbServerSendExcep 	EnabledStatus,
	    rcMbServerLinkStats		EnabledStatus
	}

rcMbServerPort OBJECT-TYPE
	SYNTAX		Integer32 (1..65535)
	MAX-ACCESS	not-accessible
	STATUS		current
	DESCRIPTION
		"The physical Serial Port Number for which this Entry contains the
		Modbus Server Protocol configuration settings."
	::= { rcMbServerEntry 1 }

rcMbServerRespTimer OBJECT-TYPE
	SYNTAX		Integer32(50..10000)
	UNITS		"milliseconds"
	MAX-ACCESS	read-write
	STATUS		current
	DESCRIPTION
		"The allowable time to wait for the RTU to start to respond."
	::= { rcMbServerEntry 2 }

rcMbServerAuxTcpPort	 OBJECT-TYPE
	SYNTAX		Integer32(1024..65535)
	MAX-ACCESS	read-write
	STATUS		current
	DESCRIPTION
		"The alternative TCP port number where a 'rcMbServerPort' may listen
		to incoming TCP conncetions.

		Note:TCP Modbus Server always listens on TCP port 502.
		So this parameter allows the RuggedCom serial device to accept
		TCP Modbus Protocol connections request on both TCP ports."
	::= { rcMbServerEntry 3 }

rcMbServerSendExcep OBJECT-TYPE
	SYNTAX		EnabledStatus
	MAX-ACCESS	read-write
	STATUS		current
	DESCRIPTION
		"Allows the RuggedCom Serial Devices to enable or disable sending TCP
		Modbus exception back to the master if response has not been
		received from the RTU within expected time."
	::= { rcMbServerEntry 4 }

rcMbServerLinkStats	OBJECT-TYPE
	SYNTAX		EnabledStatus
	MAX-ACCESS	read-write
	STATUS		current
	DESCRIPTION
		"Enables links statistics collection."
	::= { rcMbServerEntry 5 }

-- ---------------------------------------------------------------------- --
-- Modbus Client configuration
-- ---------------------------------------------------------------------- --
rcMbClientIPPort	OBJECT-TYPE
	SYNTAX			Integer32(1..65535)
	MAX-ACCESS		read-write
	STATUS			current
	DESCRIPTION
		"A remote port number to which protocol	connection manager sends TCP
		connection requests."
	::= { rcMbClient 1}

rcMbClientFwdExcp	OBJECT-TYPE
	SYNTAX			EnabledStatus
	MAX-ACCESS		read-write
	STATUS			current
	DESCRIPTION
		"Enables forwarding exception messages to the Master as exception
		codes 10 (no path) or 11 (no response).

		When the Master polls for an unconfigured RTU or the remote Modbus
		Server receives a poll for an RTU which is not configured or is timing
		out, it returns an exception message.

		This object should be set to 'disabled(2)' if Master does not support
		exceptions but recognizes failure by time-out when waiting for
		response."
	::= { rcMbClient 2}

rcMbClientLinkStats		OBJECT-TYPE
	SYNTAX				EnabledStatus
	MAX-ACCESS			read-write
	STATUS				current
	DESCRIPTION
		"Enables link statistics collection."
	::= { rcMbClient 3}

rcMbClientDscp	OBJECT-TYPE
	SYNTAX		Integer32(0..63)
	MAX-ACCESS	read-write
	STATUS		current
	DESCRIPTION
		"The value of DS byte to be set in the IP header.

		DS byte setting is supported in the egress direction only."
	::= { rcMbClient 4}

-- ---------------------------------------------------------------------- --
-- RawSocket configuration
-- ---------------------------------------------------------------------- --
rcRawSockTable OBJECT-TYPE
	SYNTAX SEQUENCE OF RcRawSockEntry
	MAX-ACCESS	not-accessible
	STATUS		current
	DESCRIPTION
	    "This table represents the entries for ports configured for Raw Socket
	    serial protocol on RuggedCom serial devices."
	::= { rcRawSock 1 }

rcRawSockEntry 	OBJECT-TYPE
	SYNTAX		RcRawSockEntry
	MAX-ACCESS	not-accessible
	STATUS		current
	DESCRIPTION
	    "List of all the configuration options available for a port configured
	    for Raw Socket serial protocol on Ruggedcom serial devices."
	INDEX { rcRawSockPort }
	::= { rcRawSockTable 1 }

RcRawSockEntry ::= SEQUENCE {
	    rcRawSockPort			Integer32,
	    rcRawSockPackChar		Integer32,
	    rcRawSockPackTimer		Integer32,
	    rcRawSockPackSize 		Integer32,
	    rcRawSockFlowControl	RcFlowControl,
	    rcRawSockTransport		RcTransport,
	    rcRawSockCallDir		RcCallDir,
	    rcRawSockMaxConn		Integer32,
	    rcRawSockLocPort		Integer32,
	    rcRawSockRemPort		Integer32,
	    rcRawSockIpAdd			IpAddress,
	    rcRawSockLinkStats		EnabledStatus
	}

rcRawSockPort	OBJECT-TYPE
	SYNTAX		Integer32 (1..65535)
	MAX-ACCESS	not-accessible
	STATUS		current
	DESCRIPTION
		"The physical Serial Port Number for which this Entry contains
		the Raw Socket serial protocol configuration settings."
	::= { rcRawSockEntry 1 }

rcRawSockPackChar OBJECT-TYPE
	SYNTAX		Integer32(0..256)
	MAX-ACCESS	read-write
	STATUS		current
	DESCRIPTION
		"The character that can be used to force forwarding of accumulated
		data to the network.

		If a packetization character is not configured - object is set to the
		value of '256', accumulated data will be forwarded based upon the
		paketization timeout parameter which is the value set for object
		rcRawSockPackTimer."
	::= { rcRawSockEntry 2 }

rcRawSockPackTimer OBJECT-TYPE
	SYNTAX		Integer32(3..1000)
	UNITS		"milliseconds"
	MAX-ACCESS	read-write
	STATUS		current
	DESCRIPTION
		"The delay in ms from the last received character until when data is
		forwarded."
	::= { rcRawSockEntry 3 }

rcRawSockPackSize OBJECT-TYPE
	SYNTAX		Integer32(64..1401)
	UNITS		"bytes"
	MAX-ACCESS	read-write
	STATUS		current
	DESCRIPTION
		"The maximum number of bytes received from serial port to be
		forwarded."
	::= { rcRawSockEntry 4 }

rcRawSockFlowControl	OBJECT-TYPE
	SYNTAX		RcFlowControl
	MAX-ACCESS	read-write
	STATUS		current
	DESCRIPTION
		"The type of FlowControl to be used on the port."
	::= { rcRawSockEntry 5 }

rcRawSockTransport	OBJECT-TYPE
	SYNTAX			RcTransport
	MAX-ACCESS		read-write
	STATUS			current
	DESCRIPTION
		"A transport protocol used for IP traffic for protocol on this port."
	::= { rcRawSockEntry 6 }

rcRawSockCallDir	OBJECT-TYPE
	SYNTAX			RcCallDir
	MAX-ACCESS		read-write
	STATUS			current
	DESCRIPTION
		"Defines following:
		- whether to accept an incoming connection 'in(0)'			or
		- to place an outgoing connection 'out(1)'  or
		- to place an outgoing connection and wait for incomming 'both(2)'

		Note: This parameter is applicable only for TCP transport."
	::= { rcRawSockEntry 7 }

rcRawSockMaxConn	OBJECT-TYPE
	SYNTAX			Integer32(1..64)
	MAX-ACCESS		read-write
	STATUS			current
	DESCRIPTION
		"The maximum number of allowed incoming TCP connections."
	::= { rcRawSockEntry 8 }

rcRawSockLocPort	OBJECT-TYPE
	SYNTAX			Integer32(1..65535)
	MAX-ACCESS		read-write
	STATUS			current
	DESCRIPTION
		"The local IP port to listen to an incoming TCP connection or UDP
		datagrams."
	::= { rcRawSockEntry 9 }

rcRawSockRemPort	OBJECT-TYPE
	SYNTAX			Integer32(1..65535)
	MAX-ACCESS		read-write
	STATUS			current
	DESCRIPTION
		"The remote IP port to use when placing an outgoing connection."
	::= { rcRawSockEntry 10 }

rcRawSockIpAdd	OBJECT-TYPE
	SYNTAX		IpAddress
	MAX-ACCESS	read-write
	STATUS		current
	DESCRIPTION
		"Defines the IpAddress based on the following:
		- For outgoing TCP connection (client) 'rcRawSockCallDir' is 'out(2)'
		  this is the remote IP address to communicate with.
		- For incoming TCP connection (server), 'rcRawSockCallDir' is
		  'out(2)' or 'both(3)' this is the local interface IP address to
		  listen to the local port for connection request.
		- For both, outgoing and incoming connections enabled
		  (client or server), 'rcRawSockCallDir' is 'both(3)' this is the
		  remote IP address where to place an outgoing TCP connection request
		  or from which to accept calls.
		- For UDP transport address of interface to listen to UDP datagrams."
	::= { rcRawSockEntry 11 }

rcRawSockLinkStats	OBJECT-TYPE
	SYNTAX			EnabledStatus
	MAX-ACCESS		read-write
	STATUS			current
	DESCRIPTION
		"Enables links statistics collection for RawSocket on this port."
	::= { rcRawSockEntry 12 }

-- ---------------------------------------------------------------------- --
-- Preemptiv RawSocket
-- ---------------------------------------------------------------------- --
rcPreemptRSTable OBJECT-TYPE
	SYNTAX SEQUENCE OF RcPreemptRSEntry
	MAX-ACCESS	not-accessible
	STATUS		current
	DESCRIPTION
	    "This Table defines the configuration options available for ports
	    configured for PreEmptive Raw Socket serial protocol."
	::= { rcPreemptRS 1 }

rcPreemptRSEntry OBJECT-TYPE
	SYNTAX		RcPreemptRSEntry
	MAX-ACCESS	not-accessible
	STATUS		current
	DESCRIPTION
	    "A list of port entries with configuration options for ports configured
	    for PreEmptive Raw Socket protocol."
	INDEX { rcPreemptRSPort }
	::= { rcPreemptRSTable 1 }

RcPreemptRSEntry ::=	SEQUENCE {
	    rcPreemptRSPort				Integer32,
	    rcPreemptRSPackChar	  		Integer32,
	    rcPreemptRSPackTimer	  	Integer32,
	    rcPreemptRSPackSize 	  	Integer32,
	    rcPreemptRSFlowControl  	RcFlowControl,
	    rcPreemptRSLocPort	  		Integer32,
	    rcPreemptRSRemPort	  		Integer32,
	    rcPreemptRSIpAdd			IpAddress,
	    rcPreemptRSLinkStats		EnabledStatus,
	    rcPreemptRSDynPackChar  	Integer32,
	    rcPreemptRSDynPackTimer 	Integer32,
	    rcPreemptRSDynTimeout		Integer32
	}

rcPreemptRSPort	OBJECT-TYPE
	SYNTAX		Integer32(1..65535)
	MAX-ACCESS	not-accessible
	STATUS		current
	DESCRIPTION
		"The physical Serial Port Number for which 	this Entry contains
		the Preemptive Raw Socket serial protocol configuration settings."
	::= { rcPreemptRSEntry 1 }

rcPreemptRSPackChar	OBJECT-TYPE
	SYNTAX			Integer32(0..256)
	MAX-ACCESS		read-write
	STATUS			current
	DESCRIPTION
		"The character that can be used to force forwarding of accumulated
		data to the network.

		If a packetization character is not configured - object is set to the
		value of '256', accumulated data will be forwarded based upon the
		paketization timeout parameter which is the value set for object
		rcPreemptRSPackTimer."
	::= { rcPreemptRSEntry 2 }

rcPreemptRSPackTimer OBJECT-TYPE
	SYNTAX			Integer32(3..1000)
	UNITS			"milliseconds"
	MAX-ACCESS		read-write
	STATUS			current
	DESCRIPTION
		"The delay in milliseconds from the last received character until
		when data is forwarded."
	::= { rcPreemptRSEntry 3 }

rcPreemptRSPackSize	OBJECT-TYPE
	SYNTAX		Integer32(64..1400)
	UNITS		"bytes"
	MAX-ACCESS	read-write
	STATUS		current
	DESCRIPTION
		"The Maximum number of bytes received from serial port to be packed
		in one IP packet."
	::= { rcPreemptRSEntry 4 }

rcPreemptRSFlowControl	OBJECT-TYPE
	SYNTAX		RcFlowControl
	MAX-ACCESS	read-write
	STATUS		current
	DESCRIPTION
		"The type of FlowControl to be used on the port."
	::= { rcPreemptRSEntry 5 }

rcPreemptRSLocPort	OBJECT-TYPE
	SYNTAX			Integer32(1..65535)
	MAX-ACCESS		read-write
	STATUS			current
	DESCRIPTION
		"The local IP port to listen to an incoming TCP connection or UDP
		datagrams."
	::= { rcPreemptRSEntry 6 }

rcPreemptRSRemPort	OBJECT-TYPE
	SYNTAX			Integer32(1..65535)
	MAX-ACCESS		read-write
	STATUS			current
	DESCRIPTION
		"The remote TCP port to use when placing an outgoing connection."
	::= { rcPreemptRSEntry 7 }

rcPreemptRSIpAdd	OBJECT-TYPE
	SYNTAX			IpAddress
	MAX-ACCESS		read-write
	STATUS			current
	DESCRIPTION
		"Defines the IpAddress based on the following:
		- For outgoing TCP connection (client) 'rcRawSockCallDir' is 'out(2)'
		  this is the remote IP address to communicate with.
		- For incoming TCP connection (server), 'rcRawSockCallDir' is
		  'out(2)' or 'both(3)' this is the local interface IP address to
		  listen to the local port for connection request.
		- For both, outgoing and incoming connections enabled
		  (client or server), 'rcRawSockCallDir' is 'both(3)' this is the
		  remote IP address where to place an outgoing TCP connection request
		  or from which to accept calls."
	::= { rcPreemptRSEntry 8 }

rcPreemptRSLinkStats		OBJECT-TYPE
	SYNTAX		EnabledStatus
	MAX-ACCESS	read-write
	STATUS		current
	DESCRIPTION
		"Enables links statistics collection."
	::= { rcPreemptRSEntry 9 }

rcPreemptRSDynPackChar	OBJECT-TYPE
	SYNTAX		Integer32(0..256)
	MAX-ACCESS	read-write
	STATUS		current
	DESCRIPTION
		"The character that can be used to force forwarding of accumulated data
		to the network for connection to dynamic master.

		If a packetization character is not configured, accumulated data will
		be forwarded based upon the packetization timeout parameter
		'rcPreemptRSDynPackTimer'."
	::= { rcPreemptRSEntry 10 }

rcPreemptRSDynPackTimer OBJECT-TYPE
	SYNTAX		Integer32(3..1000)
	UNITS 		"milliseconds"
	MAX-ACCESS	read-write
	STATUS		current
	DESCRIPTION
		"The delay in milliseconds from the last received character until when
		data is forwarded to the dynamic master."
	::= { rcPreemptRSEntry 11 }

rcPreemptRSDynTimeout	  OBJECT-TYPE
	SYNTAX		Integer32(10..3600)
	UNITS		"seconds"
	MAX-ACCESS	read-write
	STATUS		current
	DESCRIPTION
		"The time in seconds that is allowed to dynamic master to be idle
		before it's connection is closed.
		The protocol listens to the socket open to dymamic master, and if
		no data are received within this time, conneciton will be closed."
	::= { rcPreemptRSEntry 12 }

-- ---------------------------------------------------------------------- --
-- TIN and WIN protocols configuraiton
-- ---------------------------------------------------------------------- --

rcTinAndWinTinMode	OBJECT-TYPE
	SYNTAX			INTEGER {
						tin1(1),
						tin2(2)
					}
	MAX-ACCESS		read-write
	STATUS			current
	DESCRIPTION
		"The TIN Protocol running mode"
	::= { rcTinAndWin 1}

rcTinAndWinTinTrans	OBJECT-TYPE
	SYNTAX			RcTransport
	MAX-ACCESS		read-write
	STATUS			current
	DESCRIPTION
		"A transport protocol used for IP traffic for TIN protocol."
	::= { rcTinAndWin 2}

rcTinAndWinWinTrans	OBJECT-TYPE
	SYNTAX			RcTransport
	MAX-ACCESS		read-write
	STATUS			current
	DESCRIPTION
		"A transport protocol used for IP traffic for WIN protocol."
	::= { rcTinAndWin 3}

rcTinAndWinTinIpPort	OBJECT-TYPE
	SYNTAX			Integer32(1024..65535)
	MAX-ACCESS		read-write
	STATUS			current
	DESCRIPTION
		"A local port number on which TIN protocol listens to connections or
		UDP	datagrams."
	::= { rcTinAndWin 4}

rcTinAndWinWinIpPort	OBJECT-TYPE
	SYNTAX			Integer32(1024..65535)
	MAX-ACCESS		read-write
	STATUS			current
	DESCRIPTION
		"A local port number on which WIN protocol listens to connections or
		UDP	datagrams."
	::= { rcTinAndWin 5}

rcTinAndWinMsgAgingTime	OBJECT-TYPE
	SYNTAX			Integer32(0..3600)
	UNITS			"seconds"
	MAX-ACCESS		read-write
	STATUS			current
	DESCRIPTION
		"Aging time for TIN mode2 messages.

		The feature is disabled if the value of this object is '0'.

		When the feature is enabled, any TIN mode2 message received will be
		stored in an internal table. So if the same message is received
		within the time window specified by this parameter, the new message is
		considered duplicate, and thus discarded."
	::= { rcTinAndWin 6}

rcTinAndWinAddrAgingTime	OBJECT-TYPE
	SYNTAX			Integer32(1..1000)
	UNITS			"milliseconds"
	MAX-ACCESS		read-write
	STATUS			current
	DESCRIPTION
		"The time of communication inactivity in milliseconds after which a
		learned TIN address is removed from the dynamic device address table.

		Entries in Link Statistics Table with the aged	address will be kept
		until statistics is cleared."
	::= { rcTinAndWin 7}

rcTinAndWinBroadCastAddr	OBJECT-TYPE
	SYNTAX	INTEGER {
			static(1),
			dynamic(2),
			staticAndDynamic(3)
		}
	MAX-ACCESS		read-write
	STATUS			current
	DESCRIPTION
		"The device address table in which addresses will be found for broadcast
		messages."
	::= { rcTinAndWin 8}

rcTinAndWinUniAddr	OBJECT-TYPE
	SYNTAX	INTEGER {
			static(1),
			dynamic(2),
			staticAndDynamic(3)
		}
	MAX-ACCESS		read-write
	STATUS			current
	DESCRIPTION
		"The device address table in which addresses will be found for unicast
		messages."
	::= { rcTinAndWin 9}

rcTinAndWinLinkStats 	OBJECT-TYPE
	SYNTAX				EnabledStatus
	MAX-ACCESS			read-write
	STATUS				current
	DESCRIPTION
		"Enables links statistics collection for TIN and WIN protocols."
     ::= { rcTinAndWin 10}

rcTinAndWinWinDscp	OBJECT-TYPE
	SYNTAX			Integer32(0..63)
	MAX-ACCESS		read-write
	STATUS			current
	DESCRIPTION
		"The value of DS byte to be set in the IP header.

		DS byte setting is supported in the egress direction only."
	::= { rcTinAndWin 11}

rcTinAndWinTinDscp	OBJECT-TYPE
	SYNTAX			Integer32(0..63)
	MAX-ACCESS		read-write
	STATUS			current
	DESCRIPTION
		"The value of DS byte to be set in the IP header.

		DS byte setting is supported in the egress direction only."
	::= { rcTinAndWin 12}


-- ---------------------------------------------------------------------- --
-- Microlok protocol configuration
-- ---------------------------------------------------------------------- --
rcMicrolokTransport	OBJECT-TYPE
	SYNTAX			RcTransport
	MAX-ACCESS		read-write
	STATUS			current
	DESCRIPTION
		"A transport protocol used for IP traffic for Microloc protocol."
	::= {rcMicrolok 1}

rcMicrolokIpPort	OBJECT-TYPE
	SYNTAX			Integer32(1024..65535)
	MAX-ACCESS		read-write
	STATUS			current
	DESCRIPTION
		"A local port number on which Microloc protocol listens to connections
		or UDP	datagrams."
	::= {rcMicrolok  2}

rcMicrolokLinkStats	OBJECT-TYPE
	SYNTAX			EnabledStatus
	MAX-ACCESS		read-write
	STATUS			current
	DESCRIPTION
		"Enables links statistics collection."
	::= {rcMicrolok  3}

rcMicrolokDscp		OBJECT-TYPE
	SYNTAX			Integer32(0..63)
	MAX-ACCESS		read-write
	STATUS			current
	DESCRIPTION
		"The value of DS byte to be set in the IP header.

		DS byte setting is supported in the egress direction only."
	::= {rcMicrolok  4}

-- ---------------------------------------------------------------------- --
-- DNP protocol configuration
-- ---------------------------------------------------------------------- --

rcDnpTransport		OBJECT-TYPE
	SYNTAX			RcTransport
	MAX-ACCESS		read-write
	STATUS			current
	DESCRIPTION
		"A transport protocol used for IP traffic for DNP protocol."
	::= {rcDnp	1}

rcDnpIpPort	    	OBJECT-TYPE
	SYNTAX			Integer32(1024..65535)
	MAX-ACCESS		read-write
	STATUS			current
	DESCRIPTION
		"A local port number on which DNP protocol listens to connections or
		UDP	datagrams."
	::= { rcDnp 2 }

rcDnpLearning		OBJECT-TYPE
	SYNTAX			IpAddress
	MAX-ACCESS		read-write
	STATUS			current
	DESCRIPTION
		"Enable or disable address learning.

		Learning can be disabled, or enabled on management IP interface, or
		enabled on the interface with specific IP address. If learning is
		enabled and remote address is not known, UDP broadcast message will be
		sent and source addresses will be learned on devices that run DNP
		protocol. If local address is not known, message will be sent to all
		serial ports running DNP protocol. Local addresses will be learned from
		local responses. If TCP transport is configured, connection will be
		established to the devices with the corresponding IP address."
	::= { rcDnp 3 }

rcDnpAgingTimer		OBJECT-TYPE
	SYNTAX			Integer32
	MAX-ACCESS		read-write
	STATUS			current
	DESCRIPTION
		"The time of communication inactivity after which a learned DNP address
		is removed from the device address table.

		Entries in Link Statistics Table with the aged address will be kept
		until statistics is	cleared."
	::= { rcDnp 4 }

rcDnpLinkStats		OBJECT-TYPE
	SYNTAX			Integer32
	MAX-ACCESS		read-write
	STATUS			current
	DESCRIPTION
		"Enables links statistics collection."
	::= { rcDnp 5 }

rcDnpDscp			OBJECT-TYPE
	SYNTAX			Integer32(0..63)
	MAX-ACCESS		read-write
	STATUS			current
	DESCRIPTION
		"The value of DS byte to be set in the IP header.

		DS byte setting is supported in the egress direction only."
	::= { rcDnp 6 }

-- ---------------------------------------------------------------------- --
-- DNP over RawSocket configuration
-- ---------------------------------------------------------------------- --


rcDnpRsTable OBJECT-TYPE
	SYNTAX SEQUENCE OF	RcDnpRsEntry
	MAX-ACCESS		not-accessible
	STATUS			current
	DESCRIPTION
	    "This table represents the set of parameters provide the ability to
	    configure DNP over RawSocket protocol settings for serial ports.
	    If no ports appear, then the DNP over RawSocket protocol must first be
	    assigned to port(s)"
	::= { rcDnpRs 1}

rcDnpRsEntry 		OBJECT-TYPE
	SYNTAX			RcDnpRsEntry
	MAX-ACCESS		not-accessible
	STATUS			current
	DESCRIPTION
	    "List of ports with configuration parameters for DNP over RawSocket
	    serial protocol ."
	INDEX { rcDnpRsPort }
	::= { rcDnpRsTable 1 }

RcDnpRsEntry::=	SEQUENCE {
	    rcDnpRsPort			Integer32,
	    rcDnpRsCalllDir		RcCallDir,
	    rcDnpRsTransport	RcTransport,
	    rcDnpRsMaxConns     Integer32,
	    rcDnpRsLocPort		Integer32,
	    rcDnpRsRemPort		Integer32,
	    rcDnpRsIpAdd		IpAddress,
	    rcDnpRsLinkStats	EnabledStatus
		}

rcDnpRsPort			OBJECT-TYPE
	SYNTAX			Integer32(1..65535)
	MAX-ACCESS		not-accessible
	STATUS			current
	DESCRIPTION
		"The physical Serial Port Number for which this Entry contains DNP over
		Raw Socket serial protocol configuration settings."
 	::= { rcDnpRsEntry 1 }

rcDnpRsCalllDir 	OBJECT-TYPE
	SYNTAX			RcCallDir
	MAX-ACCESS		read-write
	STATUS			current
	DESCRIPTION
		"Defines following:
		- whether to accept an incoming connection 'in(0)'			or
		- to place an outgoing connection 'out(1)'  or
		- to place an outgoing connection and wait for incomming 'both(2)'

		Note: This parameter is applicable only for TCP transport."
	::= { rcDnpRsEntry 2 }

rcDnpRsTransport	OBJECT-TYPE
	SYNTAX			RcTransport
	MAX-ACCESS		read-write
	STATUS			current
	DESCRIPTION
		"A transport protocol used for IP traffic for DNPRS on this port."
	::= { rcDnpRsEntry 3 }

rcDnpRsMaxConns 	OBJECT-TYPE
	SYNTAX			Integer32(1..64)
	MAX-ACCESS		read-write
	STATUS			current
	DESCRIPTION
		"The maximum number of allowed incoming TCP connections."
	::= { rcDnpRsEntry 4 }

rcDnpRsLocPort		OBJECT-TYPE
	SYNTAX			Integer32(1024..65535)
	MAX-ACCESS		read-write
	STATUS			current
	DESCRIPTION
		"The local IP port to listen to an incoming TCP connection or UDP
		datagrams."
	::= { rcDnpRsEntry 5 }

rcDnpRsRemPort		OBJECT-TYPE
	SYNTAX			Integer32(1024..65535)
	MAX-ACCESS		read-write
	STATUS			current
	DESCRIPTION
		"The remote TCP port to use when placing an outgoing connection."
	::= { rcDnpRsEntry 6 }

rcDnpRsIpAdd		OBJECT-TYPE
	SYNTAX			IpAddress
	MAX-ACCESS		read-write
	STATUS			current
	DESCRIPTION
		"Defines the IpAddress based on the following:
		- For outgoing TCP connection (client) 'rcRawSockCallDir' is 'out(2)'
		  this is the remote IP address to communicate with.
		- For incoming TCP connection (server), 'rcRawSockCallDir' is
		  'out(2)' or 'both(3)' this is the local interface IP address to
		  listen to the local port for connection request.
		- For both, outgoing and incoming connections enabled
		  (client or server), 'rcRawSockCallDir' is 'both(3)' this is the
		  remote IP address where to place an outgoing TCP connection request
		  or from which to accept calls.
		- For UDP transport address of interface to listen to UDP datagrams."
	::= { rcDnpRsEntry 7 }

rcDnpRsLinkStats	OBJECT-TYPE
	SYNTAX			EnabledStatus
	MAX-ACCESS		read-write
	STATUS			current
	DESCRIPTION
		"Enables links statistics collection."
	::= { rcDnpRsEntry 8 }

-- ---------------------------------------------------------------------- --
-- ---------------------------------------------------------------------- --
rcMirrBitsTable OBJECT-TYPE
	SYNTAX SEQUENCE OF	RcMirrBitsEntry
	MAX-ACCESS		not-accessible
	STATUS			current
	DESCRIPTION
	    "This table presents the list of ports with configuration options for
	    configuring the Mirrirod Bits serial protocol on RuggedCom serial
	    devices"
	::= { rcMirrorBits 1}

rcMirrBitsEntry	OBJECT-TYPE
	SYNTAX			RcMirrBitsEntry
	MAX-ACCESS		not-accessible
	STATUS			current
	DESCRIPTION
	    "List of configuration options for all the ports configured for
	    Mirrored Bits serial protocol."
	INDEX { rcMirrBitsPort }
	::= { rcMirrBitsTable 1 }

RcMirrBitsEntry::=
	SEQUENCE {
	    rcMirrBitsPort		Integer32,
	    rcMirrBitsTransport RcTransport,
	    rcMirrBitsLocPort	Integer32,
	    rcMirrBitsRemPort	Integer32,
	    rcMirrBitsIpAdd	  	IpAddress,
	    rcMirrBitsLinkStats EnabledStatus
	}

rcMirrBitsPort OBJECT-TYPE
	SYNTAX			Integer32(1..65535)
	MAX-ACCESS		not-accessible
	STATUS			current
	DESCRIPTION
		"The physical Serial Port Number for which this Entry contains the
		Mirrored Bits serial protocol configuration settings."
	::= { rcMirrBitsEntry 1 }

rcMirrBitsTransport OBJECT-TYPE
	SYNTAX			RcTransport
	MAX-ACCESS		read-write
	STATUS			current
	DESCRIPTION
		"A transport protocol used for IP traffic for MorroredBits on this
		port.

		This object is always set to the value of 'udp(2)'."
	::= { rcMirrBitsEntry 2 }

rcMirrBitsLocPort 	OBJECT-TYPE
	SYNTAX			Integer32(1024..65535)
	MAX-ACCESS		read-write
	STATUS			current
	DESCRIPTION
		"The local IP port to listen to UDP	datagrams."
	::= { rcMirrBitsEntry 3 }

rcMirrBitsRemPort	OBJECT-TYPE
	SYNTAX			Integer32(1024..65535)
	MAX-ACCESS		read-write
	STATUS			current
	DESCRIPTION
		"The Remote port to which protocol on this port can exchange UDP
		datagrams."
	::= { rcMirrBitsEntry 4 }

rcMirrBitsIpAdd		OBJECT-TYPE
	SYNTAX			IpAddress
	MAX-ACCESS		read-write
	STATUS			current
	DESCRIPTION
		"The IP Address of interface to listen to UDP datagrams."
	::= { rcMirrBitsEntry 5 }

rcMirrBitsLinkStats	OBJECT-TYPE
	SYNTAX			EnabledStatus
	MAX-ACCESS		read-write
	STATUS			current
	DESCRIPTION
		"Enables links statistics collection."
	::= { rcMirrBitsEntry 6 }

-- ---------------------------------------------------------------------- --
-- ---------------------------------------------------------------------- --
rcTelnetComportTable OBJECT-TYPE
	SYNTAX SEQUENCE OF	RcTelnetComportEntry
	MAX-ACCESS		not-accessible
	STATUS			current
	DESCRIPTION
	    "This table provides a list of port entries configured for TelnetPort
	    Comport  serial protocolwith configuration options."
	::= { rcTelnetComport 1 }

rcTelnetComportEntry 	OBJECT-TYPE
	SYNTAX			RcTelnetComportEntry
	MAX-ACCESS		not-accessible
	STATUS			current
	DESCRIPTION
	    "List of ports with configuration options for TelnetPortComports serial
	    protocol."
	INDEX { rcTelnetComportPort }
	::= { rcTelnetComportTable 1 }

RcTelnetComportEntry ::=
	SEQUENCE {
	    rcTelnetComportPort			Integer32,
	    rcTelnetComportPackChar		Integer32,
	    rcTelnetComportPackTimer	Integer32,
	    rcTelnetComportPackSize 	Integer32,
	    rcTelnetComportFlowControl 	RcFlowControl,
	    rcTelnetComportCallDir		RcCallDir,
	    rcTelnetComportLocPort	  	Integer32,
	    rcTelnetComportRemPort	  	Integer32,
	    rcTelnetComportIpAdd		IpAddress,
	    rcTelnetComportLinkStats	EnabledStatus
	}

rcTelnetComportPort	OBJECT-TYPE
	SYNTAX			Integer32(1..65535)
	MAX-ACCESS		not-accessible
	STATUS			current
	DESCRIPTION
		"Thephysical Serial Port Number for which this Entry contains the
		TelnetPortComport serial protocol configuration settings."
	::= { rcTelnetComportEntry 1 }

rcTelnetComportPackChar OBJECT-TYPE
	SYNTAX			Integer32(0..255)
	MAX-ACCESS		read-write
	STATUS			current
	DESCRIPTION
		"The character that can be used to force forwarding of accumulated
		data to the network.

		If a packetization character is not configured - object is set to the
		value of '256', accumulated data will be forwarded based upon the
		paketization timeout parameter which is the value set for object
		rcTelnetComportPackTimer."
	::= { rcTelnetComportEntry 2 }

rcTelnetComportPackTimer OBJECT-TYPE
	SYNTAX			Integer32(3..1000)
	UNITS			"milliseconds"
	MAX-ACCESS		read-write
	STATUS			current
	DESCRIPTION
		"The delay from the last received character until when data is
		forwarded."
	::= { rcTelnetComportEntry 3 }

rcTelnetComportPackSize OBJECT-TYPE
	SYNTAX			Integer32(64..1400)
	UNITS			"bytes"
	MAX-ACCESS		read-write
	STATUS			current
	DESCRIPTION
		"The maximum number of bytes received from serial port to be packed
		in one IP packet."
	::= { rcTelnetComportEntry 4 }

rcTelnetComportFlowControl OBJECT-TYPE
	SYNTAX			RcFlowControl
	MAX-ACCESS  	read-write
	STATUS			current
	DESCRIPTION
		"The type of FlowControl to be used on the port."
    ::= { rcTelnetComportEntry 5 }

rcTelnetComportCallDir	OBJECT-TYPE
	SYNTAX			RcCallDir
	MAX-ACCESS		read-write
	STATUS			current
	DESCRIPTION
		"Defines following:
		- whether to accept an incoming connection 'in(0)'			or
		- to place an outgoing connection 'out(1)'  or
		- to place an outgoing connection and wait for incomming 'both(2)'.

		This protocol support only TCP transport."
	::= { rcTelnetComportEntry 6 }

rcTelnetComportLocPort	OBJECT-TYPE
	SYNTAX			Integer32(1024..65535)
	MAX-ACCESS		read-write
	STATUS			current
	DESCRIPTION
		"The local IP port to listen to an incoming TCP connection."
	::= { rcTelnetComportEntry 7 }

rcTelnetComportRemPort	OBJECT-TYPE
	SYNTAX			Integer32(1024..65535)
	MAX-ACCESS		read-write
	STATUS			current
	DESCRIPTION
		"The remote TCP port to use when placing an outgoing connection."
	::= { rcTelnetComportEntry 8 }

rcTelnetComportIpAdd	OBJECT-TYPE
	SYNTAX			IpAddress
	MAX-ACCESS		read-write
	STATUS			current
	DESCRIPTION
		"Defines the IpAddress based on the following:
		- For outgoing TCP connection (client) 'rcRawSockCallDir' is 'out(2)'
		  this is the remote IP address to communicate with.
		- For incoming TCP connection (server), 'rcRawSockCallDir' is
		  'out(2)' or 'both(3)' this is the local interface IP address to
		  listen to the local port for connection request.
		- For both, outgoing and incoming connections enabled
		  (client or server), 'rcRawSockCallDir' is 'both(3)' this is the
		  remote IP address where to place an outgoing TCP connection request
		  or from which to accept calls."
	::= { rcTelnetComportEntry 9 }

rcTelnetComportLinkStats	OBJECT-TYPE
	SYNTAX			EnabledStatus
	MAX-ACCESS		read-write
	STATUS			current
	DESCRIPTION
		"Enables links statistics collection."
		::= { rcTelnetComportEntry 10 }

-- ---------------------------------------------------------------------- --
-- Connection Statistics table
-- ---------------------------------------------------------------------- --

rcConnStatsTable	OBJECT-TYPE
	SYNTAX SEQUENCE OF RcConnStatsEntry
	MAX-ACCESS		not-accessible
	STATUS			current
	DESCRIPTION
 	"This table provides the statictics information for all active TCP
 	connections on the RuggedCom serial device."
 	::= { rcConnStats 1 }

rcConnStatsEntry OBJECT-TYPE
	SYNTAX		RcConnStatsEntry
	MAX-ACCESS	not-accessible
	STATUS		current
	DESCRIPTION
	"List of parameters providing the statictics information for all active TCP
 	connections on the RuggedCom serial device."
	INDEX {
		rcConnStatsRemIp,
		rcConnStatsRemPort,
		rcConnStatsLocPort
	}
	::= { rcConnStatsTable 1 }

RcConnStatsEntry ::= SEQUENCE {
 		rcConnStatsRemIp	IpAddress,
 		rcConnStatsRemPort	Integer32,
 		rcConnStatsLocPort  Integer32,
 		rcConnStatsRxPkts   Integer32,
 		rcConnStatsTxPkts 	Integer32
 	}

rcConnStatsRemIp 	OBJECT-TYPE
	SYNTAX			IpAddress
	MAX-ACCESS		not-accessible
	STATUS			current
	DESCRIPTION
		"The remote IP address of the TCP connection."
	::= { rcConnStatsEntry 1 }

rcConnStatsRemPort	OBJECT-TYPE
	SYNTAX			Integer32(1024..65535)
	MAX-ACCESS		not-accessible
	STATUS			current
	DESCRIPTION
		"The remote port number of the connection."
	::= { rcConnStatsEntry 2 }

rcConnStatsLocPort	OBJECT-TYPE
	SYNTAX			Integer32(1024..65535)
	MAX-ACCESS		not-accessible
	STATUS			current
	DESCRIPTION
		"The local port number of the connection."
	::= { rcConnStatsEntry 3 }

rcConnStatsRxPkts	OBJECT-TYPE
	SYNTAX			Integer32
	MAX-ACCESS		read-only
	STATUS			current
	DESCRIPTION
		"The number of received packets."
	::= { rcConnStatsEntry 4 }

rcConnStatsTxPkts  	OBJECT-TYPE
	SYNTAX			Integer32
	MAX-ACCESS		read-only
	STATUS			current
	DESCRIPTION
		"The number of transmitted packets."
	::= { rcConnStatsEntry 5 }

-- ---------------------------------------------------------------------- --
-- SerialDevice Commands
-- ---------------------------------------------------------------------- --

rcSerDeviceCmndResetPort OBJECT-TYPE
    SYNTAX      	PortList
    MAX-ACCESS  	read-write
    STATUS      	current
    DESCRIPTION
        "The list of ports for which Reset should be performed on the
        RuggedCom Serial devices.

        A read attempt for this object always returns an empty list of ports."
    ::= { rcSerDeviceCmnd 1}

rcSerDeviceCmndClearStats	OBJECT-TYPE
	SYNTAX      	PortList
    MAX-ACCESS  	read-write
    STATUS      	current
    DESCRIPTION
        "The list of ports for which Clearing statistics command should be
        performed on the RuggedCom Serial devices.

        A read attempt for this object always returns an empty list of ports."
    ::= { rcSerDeviceCmnd 2}

-- ---------------------------------------------------------------------- --
--
-- ---------------------------------------------------------------------- --
rcSerialPortParamsGroup OBJECT-GROUP
	OBJECTS	{
		rcSerialPortIfIndex,
		rcSerialProtocol,
		rcSerialPortType,
		rcSerialForceHD,
		rcSerialTurnAround,
		rcSerialPostTxDelay,
		rcSerialHoldTime,
		rcSerialDscp,
		rcSerialRxtoTxDelay
	}
	STATUS      current
    DESCRIPTION
		"Objects related to global settings for RuggedCom serial devices."
    ::= { rcSerialGroups 1 }

rcSerialMbServerGroup OBJECT-GROUP
	OBJECTS	{
		rcMbServerRespTimer,
	    rcMbServerAuxTcpPort,
	    rcMbServerSendExcep,
	    rcMbServerLinkStats
	}
	STATUS      current
    DESCRIPTION
		"Objects related to settings ModBus Server protocol for RuggedCom serial
		devices."
    ::= { rcSerialGroups 2 }

rcSerialMbClientGroup OBJECT-GROUP
	OBJECTS	{
		rcMbClientIPPort,
		rcMbClientFwdExcp,
		rcMbClientLinkStats,
		rcMbClientDscp
	}
	STATUS      current
    DESCRIPTION
		"Objects related to settings ModBus client protocol for RuggedCom serial
		devices."
    ::= { rcSerialGroups 3 }

rcSerialRawSocketGroup OBJECT-GROUP
	OBJECTS {
		rcRawSockPackChar,
	    rcRawSockPackTimer,
	    rcRawSockPackSize,
	    rcRawSockFlowControl,
	    rcRawSockTransport,
	    rcRawSockCallDir,
	    rcRawSockMaxConn,
	    rcRawSockLocPort,
	    rcRawSockRemPort,
	    rcRawSockIpAdd,
	    rcRawSockLinkStats
	}
	STATUS      current
    DESCRIPTION
		"Objects related to settings for raw Socket protocol on RuggedCom serial
		devices."
    ::= { rcSerialGroups 4 }

rcSerialPreEmpRawSockGroup OBJECT-GROUP
	OBJECTS {
	    rcPreemptRSPackChar,
	    rcPreemptRSPackTimer,
	    rcPreemptRSPackSize,
	    rcPreemptRSFlowControl,
	    rcPreemptRSLocPort,
	    rcPreemptRSRemPort,
	    rcPreemptRSIpAdd,
	    rcPreemptRSLinkStats,
	    rcPreemptRSDynPackChar,
	    rcPreemptRSDynPackTimer,
	    rcPreemptRSDynTimeout
	}
	STATUS      current
    DESCRIPTION
		"Objects related to settings for Preemptive Raw Socket serial protocol
		on RuggedCom serial devices."
    ::= { rcSerialGroups 5 }

rcSerialTinAndWinGroup OBJECT-GROUP
	OBJECTS	{
		rcTinAndWinTinMode,
		rcTinAndWinTinTrans,
		rcTinAndWinWinTrans,
		rcTinAndWinTinIpPort,
		rcTinAndWinWinIpPort,
		rcTinAndWinMsgAgingTime,
		rcTinAndWinAddrAgingTime,
		rcTinAndWinBroadCastAddr,
		rcTinAndWinUniAddr,
		rcTinAndWinLinkStats,
		rcTinAndWinWinDscp,
		rcTinAndWinTinDscp
	}
	STATUS      current
    DESCRIPTION
		"Objects related to settings for Tin and Win protocols on RuggedCom
		serial devices."
    ::= { rcSerialGroups 6 }

rcSerialMicrolokGroup	OBJECT-GROUP
	OBJECTS	{
		rcMicrolokTransport,
		rcMicrolokIpPort,
		rcMicrolokLinkStats,
		rcMicrolokDscp
	}
	STATUS      current
    DESCRIPTION
		"Objects related to settings for Microlok protocols on RuggedCom
		serial devices."
    ::= { rcSerialGroups 7 }

rcSerialDnpGroup	OBJECT-GROUP
	OBJECTS	{
		rcDnpTransport,
		rcDnpIpPort,
		rcDnpLearning,
		rcDnpAgingTimer,
		rcDnpLinkStats,
		rcDnpDscp
	}
	STATUS      current
    DESCRIPTION
		"Objects related to settings for Dnp protocols on RuggedCom
		serial devices."
    ::= { rcSerialGroups 8 }

rcSerialDnpRsGroup	OBJECT-GROUP
	OBJECTS	{
	   	rcDnpRsCalllDir,
	    rcDnpRsTransport,
	    rcDnpRsMaxConns,
	    rcDnpRsLocPort,
	    rcDnpRsRemPort,
	    rcDnpRsIpAdd,
	    rcDnpRsLinkStats
	}
	STATUS      current
    DESCRIPTION
		"Objects related to settings for Dnp over Raw Socket protocol on
		RuggedCom serial devices."
    ::= { rcSerialGroups 9 }

rcSerialMirrBitsGroup	OBJECT-GROUP
	OBJECTS	{
	    rcMirrBitsTransport,
	    rcMirrBitsLocPort,
	    rcMirrBitsRemPort,
	    rcMirrBitsIpAdd,
	    rcMirrBitsLinkStats
	}
	STATUS      current
    DESCRIPTION
		"Objects related to settings for Mirrored Bits protocol on
		RuggedCom serial devices."
    ::= { rcSerialGroups 10 }

rcSerialTelnetComportGroup	OBJECT-GROUP
	OBJECTS	{
		rcTelnetComportPackChar,
	    rcTelnetComportPackTimer,
	    rcTelnetComportPackSize,
	    rcTelnetComportFlowControl,
	    rcTelnetComportCallDir,
	    rcTelnetComportLocPort,
	    rcTelnetComportRemPort,
	    rcTelnetComportIpAdd,
	    rcTelnetComportLinkStats
	}
	STATUS      current
    DESCRIPTION
		"Objects related to settings for TelnetPortComport protocol on
		RuggedCom serial devices."
    ::= { rcSerialGroups 11 }

rcSerialConnStatsGroup	OBJECT-GROUP
	OBJECTS	{
		rcConnStatsRxPkts,
 		rcConnStatsTxPkts
	}
	STATUS      current
    DESCRIPTION
		"Objects related to Connection Statistics from Serial protocol on RuggedCom
		serial devices."
    ::= { rcSerialGroups 15 }

rcSerialCommandsGroup	OBJECT-GROUP
	OBJECTS	{
		rcSerDeviceCmndResetPort,
		rcSerDeviceCmndClearStats
	}
	STATUS      current
    DESCRIPTION
		"Objects related to Serial Port Commands on RuggedCom serial devices."
    ::= { rcSerialGroups 16 }

END
