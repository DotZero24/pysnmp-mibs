RUGGEDCOM-MC30-MIB DEFINITIONS ::= BEGIN
IMPORTS
    MODULE-IDENTITY                 FROM SNMPv2-SMI
    AGENT-CAPABILITIES              FROM SNMPv2-CONF
    ruggedcomProducts, ruggedcomAgentCapabilities
                                    FROM RUGGEDCOM-MIB;

ruggedcomMC30Module MODULE-IDENTITY
    LAST-UPDATED "201105011700Z"      -- May 1, 17:00 EST 2011
    ORGANIZATION "RuggedCom - Industrial Strength Networks"
    CONTACT-INFO
       "Postal: RuggedCom Inc.
                300 Applewood Crescent
                Concord, Ontario,
                L4K 5C7 Canada
        Tel:    1-905-856-5288
        E-Mail: support@ruggedcom.com"
    DESCRIPTION
        "The MIB module that describes the management of RuggedMediaConverter30
        devices."

    REVISION "201105011700Z"      -- May 1, 17:00 EST 2011
    DESCRIPTION
        "Obsolete all AGENT-CAPABILITIES statemenst from this MIB."

    REVISION "200905151700Z"      -- May 15, 17:00 EST 2009;
    DESCRIPTION
        "Added ruggedcomMC30Agents041 statement.
        VARIATION for sysName changed.
        rcSysStsObjectsGroup1 is supported from RUGGEDCOM-SYS-INFO-MIB."

    REVISION "200803071100Z"      -- Mar 7, 11:00 EST 2008;
    DESCRIPTION
        "Fixed typos in AGENT-CAPABILITIES.
        Added ruggedcomMC30Agents04 statement.
        Supports updated RUGGEDCOM-TRAPS-MIB and RUGGEDCOM-SYS-INFO-MIB."


    REVISION "200611021100Z"      -- November 2, 11:00 EST 2006;
    DESCRIPTION
        "Fixed typos in AGENT-CAPABILITIES."

    REVISION "200609090900Z"      -- September 9, 09:00 EST 2006;
    DESCRIPTION
        "Created ruggedcomMC30Agents03 cgent capabilities.
        Added support for SNMPV3 (RFC 3411, RFC 3414, RFC 3415) and
        RUGGEDCOM-SYS-INFO-MIB.
        Updated CONTACT-INFO."

    REVISION "200406281000Z"      -- June 28, 10:00 EST 2004;
    DESCRIPTION
        "The intial MIB module that describes the management of
        RuggedMediaConverter30 devices."
    ::= { ruggedcomProducts 3 }

-- ---------------------------------------------------------------------- --
-- Branches commented out are reserved for possible future implementation
-- ---------------------------------------------------------------------- --
-- mc30Objects  OBJECT IDENTIFIER ::= { ruggedcomMC30Module 1 }
-- mc30Tables OBJECT IDENTIFIER ::= { ruggedcomMC30Module 2 }
-- mc30Conformance  OBJECT IDENTIFIER ::= { ruggedcomMC30Module 3 }
-- mc30Compliances  OBJECT IDENTIFIER ::= { mc30Conformance 1 }
-- mc30Groups OBJECT IDENTIFIER ::= { mc30Conformance 2 }

-- ---------------------------------------------------------------------- --
--  Rugged MC30 Agent Capabilities
-- ---------------------------------------------------------------------- --

ruggedcomMC30Agents  AGENT-CAPABILITIES
    PRODUCT-RELEASE "Rugged Media Converter RMC30 Agent capabilities version
                     1.0.0. "
    STATUS          obsolete
    DESCRIPTION
        "The Rugged Media Converter 30 Agent."

-- ---------------------------------------------------------------------- --
    SUPPORTS RUGGEDCOM-TRAPS-MIB
        INCLUDES    { ruggedcomGenericTrapGroup }
-- ---------------------------------------------------------------------- --
    SUPPORTS SNMPv2-MIB
    -- rfc1907.txt

        INCLUDES     { snmpGroup, snmpCommunityGroup, snmpSetGroup,
                       systemGroup, snmpBasicNotificationsGroup }

        VARIATION   sysContact
            DESCRIPTION
                "The string of up to 49 characters is supported for this
                 object."

        VARIATION   sysName
            DESCRIPTION
                "The string of up to 19 characters is supported for this
                object."

        VARIATION   sysLocation
            DESCRIPTION
                "The string of up to 49 characters is supported for this
                object."

        VARIATION   sysORIndex
            DESCRIPTION
                "Only one sysOREntry is created by Rugged Server Agent.
                Dynamic configuration of MIB modules is not supported."

    ::= { ruggedcomAgentCapabilities 3 }

-- ---------------------------------------------------------------------- --
--  Rugged MC30 Agent Capabilities
-- ---------------------------------------------------------------------- --

ruggedcomMC30Agents03  AGENT-CAPABILITIES
    PRODUCT-RELEASE "Rugged Media Converter RMC30 Agent capabilities version
                     3.0.0. "
    STATUS          obsolete
    DESCRIPTION
        "The Rugged Media Converter 30 Agent."

-- ---------------------------------------------------------------------- --
    SUPPORTS RUGGEDCOM-TRAPS-MIB
        INCLUDES    { ruggedcomGenericTrapGroup }

-- ---------------------------------------------------------------------- --
    SUPPORTS RUGGEDCOM-SYS-INFO-MIB
        INCLUDES    { rcSysErrObjectsGroup,
					  rcSysStsObjectsGroup,
					  rcSysStsObjectsTemperatureGroup,
					  rcSysInfoDeviceInfoGroup }

-- ---------------------------------------------------------------------- --
    SUPPORTS SNMPv2-MIB
    -- rfc1907.txt

        INCLUDES     { snmpGroup, snmpCommunityGroup, snmpSetGroup,
                       systemGroup, snmpBasicNotificationsGroup }

        VARIATION   sysContact
            DESCRIPTION
                "The string of up to 49 characters is supported for this
                 object."

        VARIATION   sysName
            DESCRIPTION
                "The string of up to 19 characters is supported for this
                object."

        VARIATION   sysLocation
            DESCRIPTION
                "The string of up to 49 characters is supported for this
                object."

        VARIATION   sysORIndex
            DESCRIPTION
                "Only one sysOREntry is created by Rugged Server Agent.
                Dynamic configuration of MIB modules is not supported."

-- ---------------------------------------------------------------------- --
    SUPPORTS SNMP-FRAMEWORK-MIB
    -- rfc3411.txt

        INCLUDES    { snmpEngineGroup }
-- ---------------------------------------------------------------------- --
    SUPPORTS SNMP-USER-BASED-SM-MIB
    -- rfc3414.txt

        INCLUDES    { usmMIBBasicGroup }

-- ---------------------------------------------------------------------- --
    SUPPORTS SNMP-VIEW-BASED-ACM-MIB
    -- rfc3415.txt

        INCLUDES    { vacmBasicGroup }

        VARIATION   vacmAccessContextMatch
            ACCESS  read-only
            DESCRIPTION
                "Write access is not implemented per RFC 3415 compliance
                statement."

        VARIATION   vacmAccessStorageType
            ACCESS  read-only
            DESCRIPTION
                "Write access is not implemented per RFC 3415 compliance
                statement.  The value of this object is always
                'nonVolatile(3)'."

        VARIATION   vacmAccessStatus
            ACCESS  read-only
            DESCRIPTION
                "Write access is not implemented per RFC 3415 compliance
                statement.  The value of this object is always 'active(1)'."

        VARIATION   vacmViewTreeFamilyMask
            ACCESS  read-only
            DESCRIPTION
                "Write access is not implemented per RFC 3415 compliance
                statement."

        VARIATION   vacmViewTreeFamilyType
            ACCESS  read-only
            DESCRIPTION
                "Write access is not implemented per RFC 3415 compliance
                statement."

        VARIATION   vacmViewTreeFamilyStorageType
            ACCESS  read-only
            DESCRIPTION
                "Write access is not implemented per RFC 3415 compliance
                statement.  The value of this object is always 'permanent(4)'."

        VARIATION   vacmViewTreeFamilyStatus
            ACCESS  read-only
            DESCRIPTION
                "Write access is not implemented per RFC 3415 compliance
                statement.  The value of this object is always 'active(1)'."

-- ---------------------------------------------------------------------- --

    ::= { ruggedcomAgentCapabilities 6 }

-- ---------------------------------------------------------------------- --
--  Rugged MC30 Agent Capabilities
-- ---------------------------------------------------------------------- --

ruggedcomMC30Agents04  AGENT-CAPABILITIES
    PRODUCT-RELEASE "Rugged Media Converter RMC30 Agent capabilities version
                     4.0.0. "
    STATUS          obsolete
    DESCRIPTION
        "The Rugged Media Converter 30 Agent."

-- ---------------------------------------------------------------------- --
    SUPPORTS RUGGEDCOM-TRAPS-MIB
        INCLUDES    { ruggedcomNotificationsGroup}

-- ---------------------------------------------------------------------- --
    SUPPORTS RUGGEDCOM-SYS-INFO-MIB
        INCLUDES    { rcSysErrObjectsGroup,
					  rcSysStsObjectsGroup,
					  rcSysStsObjectsTemperatureGroup,
					  rcSysInfoDeviceInfoGroup,
					  rcSysDeviceCommGroup }

-- ---------------------------------------------------------------------- --
    SUPPORTS SNMPv2-MIB
    -- rfc1907.txt

        INCLUDES     { snmpGroup, snmpCommunityGroup, snmpSetGroup,
                       systemGroup, snmpBasicNotificationsGroup }

        VARIATION   sysContact
            DESCRIPTION
                "The string of up to 49 characters is supported for this
                 object."

        VARIATION   sysName
            DESCRIPTION
                "The string of up to 19 characters is supported for this
                object."

        VARIATION   sysLocation
            DESCRIPTION
                "The string of up to 49 characters is supported for this
                object."

        VARIATION   sysORIndex
            DESCRIPTION
                "Only one sysOREntry is created by Rugged Server Agent.
                Dynamic configuration of MIB modules is not supported."

-- ---------------------------------------------------------------------- --
    SUPPORTS SNMP-FRAMEWORK-MIB
    -- rfc3411.txt

        INCLUDES    { snmpEngineGroup }
-- ---------------------------------------------------------------------- --
    SUPPORTS SNMP-USER-BASED-SM-MIB
    -- rfc3414.txt

        INCLUDES    { usmMIBBasicGroup }

-- ---------------------------------------------------------------------- --
    SUPPORTS SNMP-VIEW-BASED-ACM-MIB
    -- rfc3415.txt

        INCLUDES    { vacmBasicGroup }

        VARIATION   vacmAccessContextMatch
            ACCESS  read-only
            DESCRIPTION
                "Write access is not implemented per RFC 3415 compliance
                statement."

        VARIATION   vacmAccessStorageType
            ACCESS  read-only
            DESCRIPTION
                "Write access is not implemented per RFC 3415 compliance
                statement.  The value of this object is always
                'nonVolatile(3)'."

        VARIATION   vacmAccessStatus
            ACCESS  read-only
            DESCRIPTION
                "Write access is not implemented per RFC 3415 compliance
                statement.  The value of this object is always 'active(1)'."

        VARIATION   vacmViewTreeFamilyMask
            ACCESS  read-only
            DESCRIPTION
                "Write access is not implemented per RFC 3415 compliance
                statement."

        VARIATION   vacmViewTreeFamilyType
            ACCESS  read-only
            DESCRIPTION
                "Write access is not implemented per RFC 3415 compliance
                statement."

        VARIATION   vacmViewTreeFamilyStorageType
            ACCESS  read-only
            DESCRIPTION
                "Write access is not implemented per RFC 3415 compliance
                statement.  The value of this object is always 'permanent(4)'."

        VARIATION   vacmViewTreeFamilyStatus
            ACCESS  read-only
            DESCRIPTION
                "Write access is not implemented per RFC 3415 compliance
                statement.  The value of this object is always 'active(1)'."

-- ---------------------------------------------------------------------- --

    ::= { ruggedcomAgentCapabilities 11 }

-- ---------------------------------------------------------------------- --
--  Rugged MC30 Agent Capabilities
-- ---------------------------------------------------------------------- --

ruggedcomMC30Agents041  AGENT-CAPABILITIES
    PRODUCT-RELEASE "Rugged Media Converter RMC30 Agent capabilities version
                     4.1.0. "
    STATUS          obsolete
    DESCRIPTION
        "The Rugged Media Converter 30 Agent."

-- ---------------------------------------------------------------------- --
    SUPPORTS RUGGEDCOM-TRAPS-MIB
        INCLUDES    { ruggedcomNotificationsGroup}

-- ---------------------------------------------------------------------- --
    SUPPORTS RUGGEDCOM-SYS-INFO-MIB
        INCLUDES    { rcSysErrObjectsGroup,
					  rcSysStsObjectsGroup1,
					  rcSysStsObjectsTemperatureGroup,
					  rcSysInfoDeviceInfoGroup,
					  rcSysDeviceCommGroup }

-- ---------------------------------------------------------------------- --
    SUPPORTS SNMPv2-MIB
    -- rfc1907.txt

        INCLUDES     { snmpGroup, snmpCommunityGroup, snmpSetGroup,
                       systemGroup, snmpBasicNotificationsGroup }

        VARIATION   sysContact
            DESCRIPTION
                "The string of up to 49 characters is supported for this
                 object."

        VARIATION   sysName
            DESCRIPTION
                "The string of up to 24 characters is supported for this
                object."

        VARIATION   sysLocation
            DESCRIPTION
                "The string of up to 49 characters is supported for this
                object."

        VARIATION   sysORIndex
            DESCRIPTION
                "Only one sysOREntry is created by Rugged Server Agent.
                Dynamic configuration of MIB modules is not supported."

-- ---------------------------------------------------------------------- --
    SUPPORTS SNMP-FRAMEWORK-MIB
    -- rfc3411.txt

        INCLUDES    { snmpEngineGroup }
-- ---------------------------------------------------------------------- --
    SUPPORTS SNMP-USER-BASED-SM-MIB
    -- rfc3414.txt

        INCLUDES    { usmMIBBasicGroup }

-- ---------------------------------------------------------------------- --
    SUPPORTS SNMP-VIEW-BASED-ACM-MIB
    -- rfc3415.txt

        INCLUDES    { vacmBasicGroup }

        VARIATION   vacmAccessContextMatch
            ACCESS  read-only
            DESCRIPTION
                "Write access is not implemented per RFC 3415 compliance
                statement."

        VARIATION   vacmAccessStorageType
            ACCESS  read-only
            DESCRIPTION
                "Write access is not implemented per RFC 3415 compliance
                statement.  The value of this object is always
                'nonVolatile(3)'."

        VARIATION   vacmAccessStatus
            ACCESS  read-only
            DESCRIPTION
                "Write access is not implemented per RFC 3415 compliance
                statement.  The value of this object is always 'active(1)'."

        VARIATION   vacmViewTreeFamilyMask
            ACCESS  read-only
            DESCRIPTION
                "Write access is not implemented per RFC 3415 compliance
                statement."

        VARIATION   vacmViewTreeFamilyType
            ACCESS  read-only
            DESCRIPTION
                "Write access is not implemented per RFC 3415 compliance
                statement."

        VARIATION   vacmViewTreeFamilyStorageType
            ACCESS  read-only
            DESCRIPTION
                "Write access is not implemented per RFC 3415 compliance
                statement.  The value of this object is always 'permanent(4)'."

        VARIATION   vacmViewTreeFamilyStatus
            ACCESS  read-only
            DESCRIPTION
                "Write access is not implemented per RFC 3415 compliance
                statement.  The value of this object is always 'active(1)'."

-- ---------------------------------------------------------------------- --

    ::= { ruggedcomMC30Agents04 1 }
END
