RUGGEDCOM-TIMECONFIG-MIB DEFINITIONS ::= BEGIN

IMPORTS
    MODULE-IDENTITY,
    OBJECT-TYPE, Integer32, Unsigned32				FROM SNMPv2-SMI
    TEXTUAL-CONVENTION, TruthValue, DateAndTime,
    DisplayString									FROM SNMPv2-TC
    OBJECT-GROUP			       	    			FROM SNMPv2-CONF
    ruggedcomMgmt									FROM RUGGEDCOM-MIB;

rcTimeConfig	MODULE-IDENTITY
    LAST-UPDATED "201509281300Z"      -- Sep 28, 13:00 EST 2015
    ORGANIZATION "Siemens Canada Ltd."
    CONTACT-INFO
       "Postal: RuggedCom Inc.
                300 Applewood Crescent
                Concord, Ontario,
                L4K 5C7 Canada
        Tel:    1-905-856-5288
        E-Mail: support@ruggedcom.com"
    DESCRIPTION
        "Siemens - RuggedCom prorietary to configure and monitor time and date module."

	REVISION    "201509281300Z"      -- Sep 28, 13:00 EST 2015
    DESCRIPTION
        "Initial version of Siemens - RuggedCom prorietary MIB to control and
        monitor time and date module."

    ::= { ruggedcomMgmt 11 }

--=====================================================================
-- Textual Conventions
--=====================================================================
RcTimeSyncStatus ::= TEXTUAL-CONVENTION
    STATUS       current
    DESCRIPTION
        "The status of a TimeSync (GPS/IRIGB) module."
	SYNTAX		INTEGER {
					notPresent(1),
					disabled(2),
					locked(3),
					searching(4),
					aquiring(5),
					holdover(6),
					parity(7),		-- IRIGB specific
					decoder(8),
					shortckt(9),	-- GPS specific
					cfgfailure(10)
				}
-- ---------------------------------------------------------- --
-- rcTimeConfig subtrees
-- ---------------------------------------------------------- --
rcTimeConfigBase		OBJECT IDENTIFIER ::= { rcTimeConfig 1 }
rcTimeConfigConformance	OBJECT IDENTIFIER ::= { rcTimeConfig 3 }
rcTimeConfigGroups 		OBJECT IDENTIFIER ::= { rcTimeConfigConformance 2 }

-- -------------------------------------------------------------
-- Base subtree
-- -------------------------------------------------------------
rcTimeSource		 OBJECT-TYPE
    SYNTAX		INTEGER {
					localclk(6),
					irigb(2),
					ieee1588(4),
					ntp(5),
					gps(3)
				}
    MAX-ACCESS  read-write
    STATUS      current
    DESCRIPTION
         "A time source that is driving the local clock."
    ::= { rcTimeConfigBase 1}

rcTimeAndDate	 OBJECT-TYPE
    SYNTAX		DateAndTime
    MAX-ACCESS  read-write
    STATUS      current
    DESCRIPTION
         "This parameter allows for both the viewing and setting
          of the local time and date in DateAndTime format.

          DateAndTime is a standard Textual Convention which is
          defined in the SNMPv2-TC"
    ::= { rcTimeConfigBase 2}

rcDSTOfst	 OBJECT-TYPE
    SYNTAX		Unsigned32(0..86399)
    UNITS       "seconds"
    MAX-ACCESS  read-write
    STATUS      current
    DESCRIPTION
         "This parameter specifies the amount of time to be shifted
         forward/backward when DST begins and ends.

         For example for most part of USA and Canada, DST time shift
         is 1 hour (01:00:00) forward when DST begins and 1 hour backward
         when DST ends."
    ::= { rcTimeConfigBase 3}

rcCurrentUTCOfst	 OBJECT-TYPE
    SYNTAX		Unsigned32(0..1000)
    UNITS       "seconds"
    MAX-ACCESS  read-write
    STATUS      current
    DESCRIPTION
         "Current UTC offset parameter allows user to adjust the difference
         between UTC and TAI."
    ::= { rcTimeConfigBase 4}

rcLeapSecPending	 OBJECT-TYPE
    SYNTAX		TruthValue
    MAX-ACCESS  read-write
    STATUS      current
    DESCRIPTION
         "This parameter allows user to manage the leap second event. A leap
         second is a second added to Coordinated "
    ::= { rcTimeConfigBase 5}

rcDSTRule		 OBJECT-TYPE
    SYNTAX		DisplayString (SIZE (0..32))
    MAX-ACCESS  read-write
    STATUS      current
    DESCRIPTION
         "This parameter specifies a rule for time and date when the transition
         between Standard and Daylight Saving Time occurs.

         Format: mm.n.d/HH:MM:SS mm.n.d/HH:MM:SS
         mm - Month of the year (01 - January, 12 - December)
    	 n - nth d-day in the month (1 - 1st d-day, 5 - 5th/last d-day)
         d - day of the week (0 - Sunday, 6 - Saturday)
   		 HH - hour of the day (0 - 24)
   		 MM - minute of the hour (0 - 59)
   		 SS - second of the minute (0 - 59)

		 Example: The following rule applies in most part of USA and Canada:
		 03.2.0/02:00:00 11.1.0/02:00:00
		 DST begins on March's 2nd Sunday at 2:00am
		 DST ends on November's 1st Sunday at 2:00am. "

    ::= { rcTimeConfigBase 6}
-- ---------------------------------------------------------------------- --
--  Conformance Groups
-- ---------------------------------------------------------------------- --
rcTimeConfigBaseGroup OBJECT-GROUP
	OBJECTS		{
					rcTimeSource,
					rcTimeAndDate,
					rcDSTOfst,
					rcCurrentUTCOfst,
					rcLeapSecPending,
					rcDSTRule
				}
	STATUS     current
    DESCRIPTION
        "A group of objects providing ability to monitor and configure Time and Date status."
    ::= { rcTimeConfigGroups 1 }

END
