-- ------------------------------------------------------------------------
-- automationSystem.mib
--
-- SIEMENS AG
-- Industry Sector
--
-- general object definitions to identify
-- an Industry Automation Division system
--
-- Copyright (c) 2005-2013 Siemens AG
-- All rights reserved.
-- ------------------------------------------------------------------------

AUTOMATION-SYSTEM-MIB           DEFINITIONS ::= BEGIN

IMPORTS
    automationMgmt              FROM AUTOMATION-SMI
    AutomationSerialNumberTC,
    AutomationVersionNumberTC,
    AutomationTriggerTC,
    AutomationOrderNumberTC,
    AutomationFunctionStringTC,
    AutomationLocationStringTC  FROM AUTOMATION-TC
    DisplayString,
    DateAndTime                 FROM SNMPv2-TC
    Counter32,
    IpAddress,
    Unsigned32,
    Integer32,
    OBJECT-TYPE,
    NOTIFICATION-TYPE,
    MODULE-IDENTITY             FROM SNMPv2-SMI
    MODULE-COMPLIANCE,
    OBJECT-GROUP,
    NOTIFICATION-GROUP          FROM SNMPv2-CONF;

automationSystemMIB             MODULE-IDENTITY
  LAST-UPDATED                  "201308270000Z"
  ORGANIZATION                  "Siemens AG"
  CONTACT-INFO                  "
                                Siemens AG
                                Industry Sector
                                I IA AS CTO SYA
                                SNMP Automation Registration Authority

                                Postal: Gleiwitzer Strasse 555
                                        Nuremberg-Moorenbrunn
                                        D-90475
                                Tel:    +49 911 895 0
                                E-mail: automation-mib.industry@siemens.com
                                "
  DESCRIPTION                   "
                                Definition of generic management objects
                                which describe a general I IA product.
                                "

  REVISION                      "201308270000Z"
  DESCRIPTION                   "
                                Assignment of snmp-path for 'automationSwDate' was
                                adjusted.
                                "

  REVISION                      "201306250000Z"
  DESCRIPTION                   "
                                Added automationSwUser, automationSwDate,
                                automationConfigId, automationConfigUser,
                                automationConfigDate.
                                IpAddress objects are deprecated."

  REVISION                      "201207010000Z"
  DESCRIPTION                   "time shift added."

  REVISION                      "201206010000Z"
  DESCRIPTION                   "Bugfixes and corrections according to SPH V1.2."

  REVISION                      "200903100000Z"
  DESCRIPTION                   "geographical coordinates added."

  REVISION                      "200811100000Z"
  DESCRIPTION                   "Update the contact information."

  REVISION                      "200804290000Z"
  DESCRIPTION                   "Bugfixes, no changes regarding content."

  REVISION                      "200501120000Z"
  DESCRIPTION                   "Initial Version of the MIB module."
  ::= { automationMgmt 2 }

-- ------------------------------------------------------------------------
-- groups of mib module
-- ------------------------------------------------------------------------
automationSystemObjects         OBJECT IDENTIFIER ::= { automationSystemMIB 1 }
automationSystemNotifications   OBJECT IDENTIFIER ::= { automationSystemMIB 2 }
automationSystemConformance     OBJECT IDENTIFIER ::= { automationSystemMIB 3 }

-- ------------------------------------------------------------------------
-- system identification
-- ------------------------------------------------------------------------
automationSystemIdent           OBJECT IDENTIFIER
    ::= { automationSystemObjects 1 }

automationManufacturerId        OBJECT-TYPE
    SYNTAX                      Unsigned32 (0..65535)
    MAX-ACCESS                  read-only
    STATUS                      current
    DESCRIPTION                 "
                                A code which identifies the vendor of the
                                component (e. g. the specific department
                                or OEM).
                                "
    ::= { automationSystemIdent 1 }

automationOrderNumber           OBJECT-TYPE
    SYNTAX                      AutomationOrderNumberTC
    MAX-ACCESS                  read-only
    STATUS                      current
    DESCRIPTION                 "The type / order number of the system."
    ::= { automationSystemIdent 2 }

automationSerialNumber          OBJECT-TYPE
    SYNTAX                      AutomationSerialNumberTC
    MAX-ACCESS                  read-only
    STATUS                      current
    DESCRIPTION                 "The serial number of the system."
    ::= { automationSystemIdent 3 }

automationHwRevision            OBJECT-TYPE
    SYNTAX                      AutomationVersionNumberTC
    MAX-ACCESS                  read-only
    STATUS                      current
    DESCRIPTION                 "The hardware version of the system."
    ::= { automationSystemIdent 4 }

automationSwRevision            OBJECT-TYPE
    SYNTAX                      AutomationVersionNumberTC
    MAX-ACCESS                  read-only
    STATUS                      current
    DESCRIPTION                 "The firmware version of the system."
    ::= { automationSystemIdent 5 }

automationRevisionCounter       OBJECT-TYPE
    SYNTAX                      Counter32
    MAX-ACCESS                  read-only
    STATUS                      current
    DESCRIPTION                 "
                                This value will be incremented every time
                                one of the other values of
                                automationIM0Group or automationIM1Group
                                (cp. conformance statements) changes.
                                The counter starts with 1
                                (default configuration).
                                "
    ::= { automationSystemIdent 6 }

automationRevisionDate          OBJECT-TYPE
    SYNTAX                      DateAndTime
    MAX-ACCESS                  read-only
    STATUS                      current
    DESCRIPTION                 "
                                The time of the last change of the value of
                                automationRevisionCounter. The value starts
                                with the date of the default configuration.
                                If a system doesn't support an absolute time
                                it must not support the value
                                (cp. conformance statements).

                                If the system supports the ENTITY-MIB the
                                value of this entry correlates to
                                entLastChangeTime.
                                "
    ::= { automationSystemIdent 7 }

automationFunctionTag           OBJECT-TYPE
    SYNTAX                      AutomationFunctionStringTC
    MAX-ACCESS                  read-only
    STATUS                      current
    DESCRIPTION                 "
                                A code which describes the function of the
                                component within the plant. This value will
                                be set by the engineering system. It is
                                comparable to the 'sysName'of MIB-II
                                but from the automation point of view.
                                "
    DEFVAL                      {""}
    ::= { automationSystemIdent 8 }

automationLocationTag           OBJECT-TYPE
    SYNTAX                      AutomationLocationStringTC
    MAX-ACCESS                  read-only
    STATUS                      current
    DESCRIPTION                 "
                                A code which describes the location where
                                the component is installed within the plant.
                                This value will be set by the engineering
                                system. It is comparable to the
                                'sysLocation' of MIB-II but from the
                                automation point of view.
                                "
    DEFVAL                      {""}
    ::= { automationSystemIdent 9 }

automationGeoLatitude           OBJECT-TYPE
    SYNTAX                      DisplayString
    MAX-ACCESS                  read-write
    STATUS                      current
    DESCRIPTION                 "
                                geographical latitude of the equipment site
                                shown in one of the following formats:
                                - DD.DDDDDD^
                                - DD^MM.MMMM'
                                - DD^MM'SS.SS.
                                a leading '+' sign or the trailing letter 'N'
                                indicates northern latitude,
                                a leading '-' sign or the trailing letter 'S'
                                indicates southern latitude.
                                The geodesic reference system is WGS84.
                                Only so many shall be written for fractional
                                digits until the desired precision is
                                represented.
                                Examples:  49.025^, 49^01.5224',
                                           49^01'31.343 N,
                                          +49^01'31.343
                                        or 49^01'31.343
                                "
    ::= { automationSystemIdent 10 }

automationGeoLongitude          OBJECT-TYPE
    SYNTAX                      DisplayString
    MAX-ACCESS                  read-write
    STATUS                      current
    DESCRIPTION                 "
                                geographical longitude of the equipment site
                                shown in one of the following formats:
                                - DDD.DDDDD^
                                - DDD^MM.MMMM'
                                - DDD^MM'SS.SS
                                a leading '+' sign or the trailing letter
                                'O' or 'E' indicates eastern longitude,
                                a leading '-' sign or the trailing letter 'W'
                                indicates western longitude,
                                The geodesic reference system is WGS84.
                                Only so many shall be written for fractional
                                digits until the desired precision is
                                represented.
                                Examples:  8.3498^,
                                           8^20.986',
                                           8^20'59.2 E,
                                          +8^20'59.2
                                        or 8^20'59.2
                                "
    ::= { automationSystemIdent 11 }

automationGeoHeight             OBJECT-TYPE
    SYNTAX                      DisplayString
    MAX-ACCESS                  read-write
    STATUS                      current
    DESCRIPTION                 "
                                geographical height of the equipment site
                                in the following format:
                                - dddddd m (high-order zeros are suppressed)
                                a leading sign '-' indicates a height
                                                   below zero.
                                The geodesic reference system is WGS84.
                                Examples: 158 m, - 20 m
                                "
     ::= { automationSystemIdent 12 }

automationTimeZoneOffsetHours   OBJECT-TYPE
    SYNTAX                      Integer32 (-23..23)
    MAX-ACCESS                  read-write
    STATUS                      current
    DESCRIPTION                 "
                                The offset hours of the time zone group's
                                time zone from UTC.
                                "
     ::= { automationSystemIdent 13 }

automationTimeZoneOffsetMinutes OBJECT-TYPE
    SYNTAX                      Integer32 (-59..59)
    MAX-ACCESS                  read-write
    STATUS                      current
    DESCRIPTION                 "
                                The offset minutes of the time zone group's
                                time zone from UTC.
                                "
     ::= { automationSystemIdent 14 }

automationSwUser                OBJECT-TYPE
    SYNTAX                      DisplayString
    MAX-ACCESS                  read-only
    STATUS                      current
    DESCRIPTION                 "
                                The name of the user who made the last
                                firmware update.
                                The value 'unknown' shall be
                                given, if the user is not known.
                                "
    ::= { automationSystemIdent 15 }

automationSwDate                OBJECT-TYPE
    SYNTAX                      DateAndTime
    MAX-ACCESS                  read-only
    STATUS                      current
    DESCRIPTION                 "
                                The time of the last firmware update.
                                The value starts with the date of the
                                default configuration.
                                If a system doesn't support an absolute time
                                it must not support the value.
                                "
    ::= { automationSystemIdent 16 }

-- ------------------------------------------------------------------------
-- system status
-- ------------------------------------------------------------------------
automationSystemStatus          OBJECT IDENTIFIER
    ::= { automationSystemObjects 2 }

automationOperState             OBJECT-TYPE
    SYNTAX                      INTEGER {
                                ok(0),
                                maintenanceRequired(1),
                                maintenanceDemanded(2),
                                fault(3)
                                }
    MAX-ACCESS                  read-only
    STATUS                      current
    DESCRIPTION                 "
                                General operational status of the component.
                                ok(0) indicates that the component works,
                                    no errors.
                                maintenanceRequired(1) indicates, that at
                                    the moment there aren't any problems
                                    but maintenace is required e. g.
                                    because a service interval has expired
                                    or the component determined a software
                                    update and so on.
                                maintenanceDemanded(2) indicates,
                                    that the component works, but there are
                                    problems which could lead to fault
                                    situations.
                                fault(3) indicates a failure condition on
                                    the component.
                                    If a fault-LED is available (on front panel),
                                    the fault-LED indication shall be synchronized
                                    with the fault value of automationOperState.
                                    If the automationOperState signals a fault,
                                    the fault-LED must be lit (ON).
                                    In all other states of automationOperState
                                    the fault-LED is off.
                                "
    ::= { automationSystemStatus 1 }

automationApplicationOperState  OBJECT-TYPE
    SYNTAX                      INTEGER {
                                noControl(1),
                                run(2),
                                stop(3)
                                }
    MAX-ACCESS                  read-only
    STATUS                      current
    DESCRIPTION                 "
                                Operating status of the application within the
                                automation system.
                                This status indicates whether the device
                                context is part of an automation system that is
                                in operation (run or stop) or not (no_control).
                                "
    ::= { automationSystemStatus 2 }
-- ------------------------------------------------------------------------
-- system generics
-- ------------------------------------------------------------------------
automationSystemGeneric         OBJECT IDENTIFIER
    ::= { automationSystemObjects 3 }

automationSystemRestart         OBJECT-TYPE
    SYNTAX                      INTEGER {
                                noOperation(0),
                                coldstart(1),
                                warmstart(2),
                                restartBasicDefaults(3),
                                restartCompleteDefaults(4)
                                }
    MAX-ACCESS                  read-write
    STATUS                      current
    DESCRIPTION                 "
                                Restart the system. Setting the value to 1
                                causes a coldstart, a value of 2 causes a
                                warmstart. The different behaviour of
                                coldstart and warmstart depends on the
                                component and is described in the user
                                manual of the component.

                                If a warmstart is triggered by the values
                                of 3 or 4 the settings of the component will
                                be reseted to factory defaults. The value of
                                3 means that only the basic parameters will
                                be reseted, the value of 4 causes a complete
                                reset. Which parameters are affected by this
                                action is described in the components
                                manual.

                                If write access is not allowed, no matter what reason
                                (e.g. an active PROFINET configuration), write requests
                                must be rejected with error 'noSuchName' (SNMPv1 agents) or
                                'notWriteable' (SNMPv2 and SNMPv3 agents) respectively.
                                "
    ::= { automationSystemGeneric 1 }

automationPowerUpCount          OBJECT-TYPE
    SYNTAX                      Counter32
    MAX-ACCESS                  read-only
    STATUS                      current
    DESCRIPTION                 "Number of system starts."
    ::= { automationSystemGeneric 3 }

automationResetCounters         OBJECT-TYPE
    SYNTAX                      AutomationTriggerTC
    MAX-ACCESS                  read-write
    STATUS                      current
    DESCRIPTION                 "
                                Reset all statistic counters of the
                                component. On write access only a value of
                                set(1) will be accepted (and causes a reset
                                of the counters of the system), all other
                                values will be rejected.

                                If write access is not allowed, no matter what reason
                                (e.g. an active PROFINET configuration), write requests
                                must be rejected with error 'noSuchName' (SNMPv1 agents) or
                                'notWriteable' (SNMPv2 and SNMPv3 agents) respectively.
                                "
    ::= { automationSystemGeneric 4 }

automationConfigId              OBJECT-TYPE
    SYNTAX                      OCTET STRING(SIZE(64))
    MAX-ACCESS                  read-only
    STATUS                      current
    DESCRIPTION                 "
                                Signature of all configuration parameter
                                values.
                                The special value of all bytes 0x00 denotes the
                                situation of a temporarily not available
                                signature, what might happen during a
                                configuration download while the signature
                                is under construction.
                                If the ConfigId cannot be built, no matter what reason
                                (e.g. incompatibilities between parameter layout and
                                build algorithm, out of resources, ...), get requestes
                                must be responded with error 'noSuchInstance'.
                                "
    ::= { automationSystemGeneric 5 }

automationConfigUser            OBJECT-TYPE
    SYNTAX                      DisplayString
    MAX-ACCESS                  read-only
    STATUS                      current
    DESCRIPTION                 "
                                The name of the user who made the last
                                change to any parameter of the configuration
                                parameter set. The value 'unknown' shall be
                                given, if the user is not known.
                                "
    ::= { automationSystemGeneric 6 }

automationConfigDate            OBJECT-TYPE
    SYNTAX                      DateAndTime
    MAX-ACCESS                  read-only
    STATUS                      current
    DESCRIPTION                 "
                                The time of the last change to a parameter
                                of the configuration parameter set.
                                The value starts with the date of the
                                default configuration.
                                If a system doesn't support an absolute time
                                it must not support the value
                                (cp. conformance statements).
                                "
    ::= { automationSystemGeneric 7 }


-- ------------------------------------------------------------------------
-- agent configuration of the system
--
-- Note that if write access is not allowed, no matter what reason (e.g. an active
-- PROFINET configuration), write requests must be rejected with error 'noSuchName'
-- (SNMPv1 agents) or 'notWriteable' (SNMPv2 and SNMPv3 agents) respectively.
--
-- ------------------------------------------------------------------------
automationSystemIp              OBJECT IDENTIFIER
    ::= { automationSystemObjects 4 }

-- ------------------------------------------------------------------------
-- The objects of this branch have been deprecated in favor of the IP
-- version neutral ip address objects of the ipMIB of RFC 4293
-- ------------------------------------------------------------------------

automationSystemIpAddress       OBJECT-TYPE
    SYNTAX                      IpAddress
    MAX-ACCESS                  read-write
    STATUS                      deprecated
    DESCRIPTION                 "
                                This object contains the IP address of the
                                system (which is used to connect to the SNMP
                                agent, the web entity etc.). If the
                                component features an outbandport, this
                                object contains the inband IP address.

                                "
    DEFVAL                      { '0000'H }
    ::= { automationSystemIp 1 }

automationSystemIpSubnetMask    OBJECT-TYPE
    SYNTAX                      IpAddress
    MAX-ACCESS                  read-write
    STATUS                      deprecated
    DESCRIPTION                 "
                                This object contains the subnet mask of
                                the system (which is used to connect to
                                the SNMP agent, the webentity etc.).
                                If the component features an outbandport,
                                this object contains the inband subnet mask.
                                "
    DEFVAL                      { '0000'H }
    ::= { automationSystemIp 2 }

automationSystemIpGateway       OBJECT-TYPE
    SYNTAX                      IpAddress
    MAX-ACCESS                  read-write
    STATUS                      deprecated
    DESCRIPTION                 "
                                The default gateway of the system.

                                "
    DEFVAL                      { '0000'H }
    ::= { automationSystemIp 3 }

automationSystemOutbandIp       OBJECT-TYPE
    SYNTAX                      IpAddress
    MAX-ACCESS                  read-write
    STATUS                      deprecated
    DESCRIPTION                 "
                                If the system features an outband port, this
                                object contains its IP address.
                                "
    DEFVAL                      { '0000'H }
    ::= { automationSystemIp 4 }

automationSystemOutbandSubnetMask   OBJECT-TYPE
    SYNTAX                      IpAddress
    MAX-ACCESS                  read-write
    STATUS                      deprecated
    DESCRIPTION                 "
                                If the system features an outband port,
                                this object contains its subnet mask.
                                "
    DEFVAL                      { '0000'H }
    ::= { automationSystemIp 5 }

-- ------------------------------------------------------------------------
-- general event definitions
-- ------------------------------------------------------------------------
automationSystemNotificationsV2 OBJECT IDENTIFIER
    ::= { automationSystemNotifications 0 }

automationOperStateChanged      NOTIFICATION-TYPE
    OBJECTS                     { automationOperState }
    STATUS                      current
    DESCRIPTION                 "The system triggers this event in case the
                                value of automationOperState changed."
    ::= { automationSystemNotificationsV2 1 }

automationRevisionChanged       NOTIFICATION-TYPE
    STATUS                      current
    DESCRIPTION                 "
                                The system triggers this event in case the
                                configuration changed (e. g. the hardware
                                configuration, a firmware update or IP
                                parameter).
                                "
    ::= { automationSystemNotificationsV2 2 }

-- ------------------------------------------------------------------------
-- conformance statements
-- ------------------------------------------------------------------------

--
-- MIB groupings
--
automationSystemGroups          OBJECT IDENTIFIER
    ::= { automationSystemConformance 1 }

automationIM0Group              OBJECT-GROUP
    OBJECTS                     {
                                automationManufacturerId,
                                automationOrderNumber,
                                automationSerialNumber,
                                automationHwRevision,
                                automationSwRevision,
                                automationRevisionCounter
                                }
    STATUS                      current
    DESCRIPTION                 "
                                This group collects the named parameters
                                according to the referenced guideline.
                                "
    REFERENCE                   "
                                I&M parameters are described in the
                                PROFIBUS Guideline, Profile Guidelines
                                Part 1:

                                Identification & Maintenance Functions,
                                Version 1.2, October 2009
                                "
    ::= { automationSystemGroups 1 }

automationIM1Group              OBJECT-GROUP
    OBJECTS                     {
                                automationFunctionTag,
                                automationLocationTag
                                }
    STATUS                      current
    DESCRIPTION                 "
                                This group collects the named parameters
                                according to the referenced guideline.
                                "
    REFERENCE                   "
                                I&M parameters are described in the
                                PROFIBUS Guideline, Profile Guidelines
                                Part 1:
                                Identification & Maintenance Functions,
                                Version 1.2, October 2009
                                "
    ::= { automationSystemGroups 2 }

automationIM2Group              OBJECT-GROUP
    OBJECTS                     { automationRevisionDate }
    STATUS                      current
    DESCRIPTION                 "
                                This group collects the named parameters
                                according to the referenced guideline.
                                The revision date is only available if
                                the system supports an absolute time,
                                therefore this group must be only
                                supported if the absolute time is
                                available.
                                "
    REFERENCE                   "
                                I&M parameters are described in the
                                PROFIBUS Guideline, Profile Guidelines
                                Part 1:
                                Identification & Maintenance Functions,
                                Version 1.2, October 2009
                                "
    ::= { automationSystemGroups 3 }

automationStatusGroup           OBJECT-GROUP
    OBJECTS                     { automationOperState,
                                  automationApplicationOperState
                                }
    STATUS                      current
    DESCRIPTION                 "Generic status information."
    ::= { automationSystemGroups 4 }

automationRemoteRestartGroup    OBJECT-GROUP
    OBJECTS                     {
                                automationSystemRestart,
                                automationPowerUpCount
                                }
    STATUS                      current
    DESCRIPTION                 "Allows restart via SNMP."
    ::= { automationSystemGroups 5 }

automationResetCounterGroup     OBJECT-GROUP
    OBJECTS                     { automationResetCounters }
    STATUS                      current
    DESCRIPTION                 "Allows reset of all counters."
    ::= { automationSystemGroups 6 }

automationIpGroup               OBJECT-GROUP
    OBJECTS                     {
                                automationSystemIpAddress,
                                automationSystemIpSubnetMask,
                                automationSystemIpGateway
                                }
    STATUS                      deprecated
    DESCRIPTION                 "IP configuration of the agent."
    ::= { automationSystemGroups 7 }

automationOutbandGroup          OBJECT-GROUP
    OBJECTS                     {
                                automationSystemOutbandIp,
                                automationSystemOutbandSubnetMask
                                }
    STATUS                      deprecated
    DESCRIPTION                 "Configuration of the outband port."
    ::= { automationSystemGroups 8 }

automationStatusEvents          NOTIFICATION-GROUP
    NOTIFICATIONS               { automationOperStateChanged }
    STATUS                      current
    DESCRIPTION                 "Notifications about status changes."
    ::= { automationSystemGroups 9 }

automationConfigurationEvents   NOTIFICATION-GROUP
    NOTIFICATIONS               { automationRevisionChanged }
    STATUS                      current
    DESCRIPTION                 "Notifications about configuration changes."
    ::= { automationSystemGroups 10 }

automationGeoLocation           OBJECT-GROUP
    OBJECTS                     {
                                automationGeoLatitude,
                                automationGeoLongitude,
                                automationGeoHeight
                                }
    STATUS                      current
    DESCRIPTION                 "
                                This group collects the named parameters
                                according to the geographical coordinates.
                                "

    ::= { automationSystemGroups 11 }

automationGeoLocationTimeShift  OBJECT-GROUP
    OBJECTS                     {
                                automationGeoLatitude,
                                automationGeoLongitude,
                                automationGeoHeight,
                                automationTimeZoneOffsetHours,
                                automationTimeZoneOffsetMinutes
                                }
    STATUS                      current
    DESCRIPTION                 "
                                This group collects the named parameters
                                according to the geographical coordinates
                                and the location dependent time shift.
                                "
    ::= { automationSystemGroups 12 }

automationConfigIdGroup         OBJECT-GROUP
    OBJECTS                     {
                                automationConfigId,
                                automationConfigUser,
                                automationConfigDate
                                }
    STATUS                      current
    DESCRIPTION                 "
                                This group collects the named parameters
                                for the suppport of a config signature.
                                "
    ::= { automationSystemGroups 13 }

automationSwDownloadGroup       OBJECT-GROUP
    OBJECTS                     {
                                automationSwUser,
                                automationSwDate
                                }
    STATUS                      current
    DESCRIPTION                 "
                                This group collects the named parameters
                                for a firmware download.
                                "
    ::= { automationSystemGroups 14 }

--
--  compliance specifications
--
automationSystemCompliances     OBJECT IDENTIFIER
    ::= { automationSystemConformance 2 }

automationSystemBasicCompliance MODULE-COMPLIANCE
    STATUS                      current
    DESCRIPTION                 "Minimum implementation requirements for all
                                Industry Automation Division systems
                                with SNMP support."
    MODULE                      -- compliance to the containing MIB module
    MANDATORY-GROUPS            { automationIM0Group }
    GROUP                       automationIM1Group
    DESCRIPTION                 "Required if the system provides I&M 1."
    GROUP                       automationIM2Group
    DESCRIPTION                 "Required if the system provides I&M 2."
    GROUP                       automationStatusGroup
    DESCRIPTION                 "Required if the system provides a
                                collective status information."
    GROUP                       automationResetCounterGroup
    DESCRIPTION                 "
                                Required for systems which provide a
                                reset of all their counters.
                                "
    ::= { automationSystemCompliances 1 }

automationSystemExtCompliance   MODULE-COMPLIANCE
    STATUS                      deprecated
    DESCRIPTION                 "Extended requirements for
                                Industry Automation Division systems."
    MODULE                      -- compliance to the containing MIB module
    MANDATORY-GROUPS            { automationIM0Group }
    GROUP                       automationIM1Group
    DESCRIPTION                 "Required if the system provides I&M 1."
    GROUP                       automationIM2Group
    DESCRIPTION                 "Required if the system provides I&M 2."
    GROUP                       automationIpGroup
    DESCRIPTION                 "Required if the system allows configuring of
                                the IP parameters via SNMP and no other MIBs
                                are implemented which support management of
                                this parameters."
    GROUP                       automationOutbandGroup
    DESCRIPTION                 "Required if the system provides an outband
                                port and management of this port is allowed
                                via SNMP and no other MIBs are implemented
                                which support management of the outband
                                port."
    GROUP                       automationRemoteRestartGroup
    DESCRIPTION                 "Required if restart of the system via
                                SNMP allowed."
    GROUP                       automationStatusGroup
    DESCRIPTION                 "Required if the system provides a
                                collective status information."
    GROUP                       automationResetCounterGroup
    DESCRIPTION                 "Required for systems which provide a
                                reset of all their counters."
    GROUP                       automationConfigurationEvents
    DESCRIPTION                 "Required for systems which provide
                                notifications."
    GROUP                       automationStatusEvents
    DESCRIPTION                 "Required for systems which provide
                                notifications."
    GROUP                       automationGeoLocation
    DESCRIPTION                 "Required for systems which provide
                                geographical coordinates."
    GROUP                       automationGeoLocationTimeShift
    DESCRIPTION                 "Required for systems which provide
                                geographical coordinates and time shift."
    ::= { automationSystemCompliances 2 }

automationSystemExtCompliance2  MODULE-COMPLIANCE
    STATUS                      current
    DESCRIPTION                 "Extended requirements for
                                Industry Automation Division systems."
    MODULE                      -- compliance to the containing MIB module
    MANDATORY-GROUPS            { automationIM0Group }
    GROUP                       automationIM1Group
    DESCRIPTION                 "Required if the system provides I&M 1."
    GROUP                       automationIM2Group
    DESCRIPTION                 "Required if the system provides I&M 2."
    GROUP                       automationRemoteRestartGroup
    DESCRIPTION                 "Required if restart of the system via
                                SNMP allowed."
    GROUP                       automationStatusGroup
    DESCRIPTION                 "Required if the system provides a
                                collective status information."
    GROUP                       automationResetCounterGroup
    DESCRIPTION                 "Required for systems which provide a
                                reset of all their counters."
    GROUP                       automationConfigurationEvents
    DESCRIPTION                 "Required for systems which provide
                                notifications."
    GROUP                       automationStatusEvents
    DESCRIPTION                 "Required for systems which provide
                                notifications."
    GROUP                       automationGeoLocation
    DESCRIPTION                 "Required for systems which provide
                                geographical coordinates."
    GROUP                       automationGeoLocationTimeShift
    DESCRIPTION                 "Required for systems which provide
                                geographical coordinates and time shift."
    GROUP                       automationConfigIdGroup
    DESCRIPTION                 "Required for systems which provide
                                configuration signatures."
    GROUP                       automationSwDownloadGroup
    DESCRIPTION                 "Required for systems which support
                                firmware download."
    ::= { automationSystemCompliances 3 }

END
