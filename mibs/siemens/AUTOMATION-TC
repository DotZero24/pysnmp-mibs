-- ----------------------------------------------------------------------
-- automationTc.mib
--
-- SIEMENS AG
-- Industry Sector
--
-- general textual conventions
--
-- Copyright (c) 2005-2013 Siemens AG
-- All rights reserved.
-- ----------------------------------------------------------------------

AUTOMATION-TC                   DEFINITIONS ::= BEGIN

IMPORTS
  automationModules             FROM AUTOMATION-SMI
  MODULE-IDENTITY               FROM SNMPv2-SMI
  TEXTUAL-CONVENTION            FROM SNMPv2-TC;

automationTcModule              MODULE-IDENTITY
  LAST-UPDATED                  "201306300000Z"
  ORGANIZATION                  "Siemens AG"
  CONTACT-INFO                  "
                                Siemens AG
                                Industry Sector
                                I IA AS CTO SYA
                                SNMP Automation Registration Authority

                                Postal: Gleiwitzer Strasse 555
                                        Nuremberg-Moorenbrunn
                                        D-90475
                                Tel:    +49 911 895 0
                                E-mail: automation-mib.industry@siemens.com
                                "
  DESCRIPTION                   "Definition of general TEXTUAL CONVENTIONS
                                for Siemens Industry Sector."

  REVISION                      "201306300000Z"
  DESCRIPTION                   "correction of DISPLAY-HINTs."

  REVISION                      "201209190000Z"
  DESCRIPTION                   "correction of length for AutomationVersionNumberTC."

  REVISION                      "201207270000Z"
  DESCRIPTION                   "Bugfixes and corrections according to SPH V1.2.
                                 Update contact information"

  REVISION                      "200811100000Z"
  DESCRIPTION                   "Update the contact information."

  REVISION                      "200804290000Z"
  DESCRIPTION                   "textual convention for
                                AutomationLocationString and
                                AutomationFunctionString added according
                                IEC61158-6-10."

  REVISION                      "200501120000Z"
  DESCRIPTION                   "Initial Version of the MIB module."
  ::= { automationModules 1 }

AutomationOrderNumberTC         ::= TEXTUAL-CONVENTION
  DISPLAY-HINT                  "1a"
  STATUS                        current
  DESCRIPTION                   "The format of type identification / order
                                numbers of Siemens I IA products."
  SYNTAX                        OCTET STRING (SIZE (16..32))

AutomationSerialNumberTC        ::= TEXTUAL-CONVENTION
  DISPLAY-HINT                  "1a"
  STATUS                        current
  DESCRIPTION                   "The format of serial numbers of
                                Siemens I IA products."
  SYNTAX                        OCTET STRING (SIZE (32))

AutomationVersionNumberTC       ::= TEXTUAL-CONVENTION
  DISPLAY-HINT                  "1a"
  STATUS                        current
  DESCRIPTION                   "The version format of Siemens I IA in a
                                simplified OSLO form :
                                [RCSTBPVKD][0-9]{1,2}\.[0-9]{1,2}\.[0-9]{1,2}
                                "
  SYNTAX                        OCTET STRING (SIZE (0..32))

AutomationMacAddressTC          ::= TEXTUAL-CONVENTION
  DISPLAY-HINT                  "1x:"
  STATUS                        current
  DESCRIPTION                   "
                                A six octet string (48-bit), using the
                                hexadecimal representation, in canonical
                                order specified by IEEE Std 802
                                (Overview and Architecture,
                                formerly IEEE Std 802.1a).

                                Shorter MAC address values than 48 bits, if
                                used, are represented by setting their
                                unused upper octets to all 0's, i.e.,
                                the 16-bit address AAFF shall be
                                represented as 00000000AAFF.
                                "
  SYNTAX                        OCTET STRING (SIZE (6))

AutomationIpAddressTC           ::= TEXTUAL-CONVENTION
  DISPLAY-HINT                  "1a"
  STATUS                        current
  DESCRIPTION                   "
                                An octet string which represents either an
                                IPv4 address or an IPv6 address or
                                a DNS compliant name.
                                "
  SYNTAX                        OCTET STRING

AutomationStatusTC              ::= TEXTUAL-CONVENTION
  STATUS                        current
  DESCRIPTION                   "A uniform representation of status values."
  SYNTAX                        INTEGER { invalid(0), enable(1), disable(2) }

AutomationTriggerTC             ::= TEXTUAL-CONVENTION
  STATUS                        current
  DESCRIPTION                   "A uniform representation of trigger values"
  SYNTAX                        INTEGER { trigger(1), notTriggered(2) }

AutomationFunctionStringTC      ::= TEXTUAL-CONVENTION
  DISPLAY-HINT                  "32a"
  STATUS                        current
  DESCRIPTION                   "
                                The format of function tags according
                                IEC 61158-6-10, chapter 6.2.6.13 IM_Tag_Function.
                                The value shall be filled with blanks
                                if it is shorter than 32.
                                Non-printable characters and
                                control sequences are not allowed.
                                Adopted from DisplayString;
                                see description in SNMPv2-TC for additional
                                information.
                                "
  SYNTAX                        OCTET STRING (SIZE (32))

AutomationLocationStringTC      ::= TEXTUAL-CONVENTION
  DISPLAY-HINT                  "22a"
  STATUS                        current
  DESCRIPTION                   "
                                The format of function tags according
                                IEC 61158-6-10, chapter 6.2.6.14 IM_Tag_Location.
                                The value shall be filled with blanks
                                if it is shorter than 22.
                                Non-printable characters and
                                control sequences are not allowed.
                                Adopted from DisplayString;
                                see description in SNMPv2-TC for additional
                                information.
                                "
  SYNTAX                        OCTET STRING (SIZE (22))

END
