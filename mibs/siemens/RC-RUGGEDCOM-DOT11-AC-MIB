RC-RUGGEDCOM-DOT11-AC-MIB DEFINITIONS ::= BEGIN

IMPORTS
    MODULE-IDENTITY				    FROM SNMPv2-SMI
    AGENT-CAPABILITIES              FROM SNMPv2-CONF
    ruggedcomAgentCapability        FROM RUGGEDCOM-MIB;

ruggedcomRcDot11ACModule MODULE-IDENTITY
    LAST-UPDATED "201206011700Z"      -- Jun 01, 17:00 EST 2012;
    ORGANIZATION "RuggedCom - Industrial Strength Networks"
    CONTACT-INFO
       "Postal: RuggedCom Inc.
                300 Applewood Crescent
                Concord, Ontario,
                L4K 5C7 Canada
        Tel:    1-905-856-5288
        E-Mail: support@ruggedcom.com"
    DESCRIPTION
        "The capabilities description for RUGGEDCOM-DOT11-MIB."

	REVISION    "201206011700Z"      -- Jun 01, 17:00 EST 2012;
    DESCRIPTION
        "Fixed typing errors."

	REVISION    "201102221700Z"      -- Feb 22, 17:00 EST 2011;
    DESCRIPTION
        "Initial version of this MIB module."

    ::= { ruggedcomAgentCapability 16 }

-- ---------------------------------------------------------------------- --
--  RUGGEDCOM DOT11 MIB Agent Capabilities
-- ---------------------------------------------------------------------- --
ruggedcomRcDot11AC   	AGENT-CAPABILITIES
    PRODUCT-RELEASE "ROS-CF52"
    STATUS          current
    DESCRIPTION
        "RUGGEDCOM-DOT11-MIB Agent Capabilities."

    SUPPORTS RUGGEDCOM-STP-MIB

        INCLUDES    { rcRstpBaseStpTxHoldCountGroup,
        			  rcRstpBaseGroup,
        			  rcRstpNotifyGroup }

-- ---------------------------------------------------------------------- --
    ::= { ruggedcomRcDot11ACModule 1 }

END
