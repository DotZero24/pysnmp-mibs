RUGGEDCOM-SYS-INFO-MIB DEFINITIONS ::= BEGIN

IMPORTS
    MODULE-IDENTITY, OBJECT-IDENTITY,
    OBJECT-TYPE, Integer32	        	FROM SNMPv2-SMI
    TEXTUAL-CONVENTION, TruthValue,
    DisplayString			        	FROM SNMPv2-TC
    OBJECT-GROUP						FROM SNMPv2-CONF
    ruggedcomMgmt						FROM RUGGEDCOM-MIB;

rcSysInfo MODULE-IDENTITY
    LAST-UPDATED "201711021000Z"      -- Nov. 02, 10:00 EST 2017
    ORGANIZATION "Siemens Canada Ltd., Process Industries and Drives"
    CONTACT-INFO
       "Postal: Siemens Canad Ltd.
                300 Applewood Crescent
                Concord, Ontario,
                L4K 5C7 Canada
        Tel:    1-905-856-5288
        E-Mail: support.canada.automation@siemens.com"

	DESCRIPTION
        "RuggedCom system information MIB."

	REVISION    "201711021000Z"      -- Nov. 02, 10:00 EST 2017
    DESCRIPTION
        "Added new object rcDeviceErrSystem."

	REVISION    "201709201100Z"      -- Sept. 20, 11:00 EST 2017
    DESCRIPTION
        "Updated DESCRIPTION of objects rcDeviceErrRadiusServerUnreachable and
		 rcDeviceErrTacacsServerUnreachable."

	REVISION    "201702151000Z"      -- Feb 15, 10:00 EST 2017
    DESCRIPTION
        "Updated ORGANIZATION and CONTACT-INFO. Updated DESCRIPTION of
        object rcDeviceErrNtpServerUnreachable."

	REVISION    "201410081700Z"      -- Oct 08, 17:00 EST 2014
    DESCRIPTION
        "Added new board IDs in RcMainBoard TEXTUAL-CONVENTION."

	REVISION    "201208301700Z"      -- Aug 30, 17:00 EST 2012
    DESCRIPTION
        "Added new objects: rcDeviceStsKeysDflt and rcDeviceInfoMinBootSwVer
         related to the device security in the group
         rcSysDeviceSecurityGroup01."

	REVISION    "201206011700Z"      -- Jun 01, 17:00 EST 2012

    DESCRIPTION
        "Added new objects rcDeviceStsPwdsWeak related to the device
        security in the group rcSysDeviceSecurityGroup."

    REVISION "201104051000Z"         -- Apr 05, 10:00 EST 2011
    DESCRIPTION
        "Extended RcHardwareStatus textual convention. Added
         'notConnected(4)' value."

    REVISION "201009161300Z"         -- Sep 16, 13:00 EST 2010
    DESCRIPTION
        "Added Fan Bank Module hardware status elements.
         Added new objects:
        	rcDeviceStsFanBank1 and rcDeviceStsFanBank2
         Added new types related to module Slot and state change."

    REVISION "200905171300Z"         -- May 17, 13:00 EST 2009
    DESCRIPTION
        "Fixed description for object rcDeviceCommClearSyslog.
         Added new object:
        	rcDeviceCommClearLogs
         Removed statement about mandatory groups from groups descriptions."


    REVISION "200812171300Z"         -- Dec 17, 13:00 EST 2008
    DESCRIPTION
        "Fixed mistyped object name for rcDeviceStsErrorAlarm in
         rcSysStsObjectsGroup objects list.
         Added new object:
        	rcDeviceCommIdentify."

    REVISION 	"200810091000Z"      -- Oct 09, 10:00 EST 2008
    DESCRIPTION
        "Added new objects:
        	rcDeviceStsErrorAlarm,
        	rcDeviceStsFailSafeRelay,
        	rcDeviceStsNoOfActiveAlarms."

    REVISION 	"200809121400Z"      -- Sep 12, 14:00 EST 2008
    DESCRIPTION
        "Adde new enumeration labels for rcDeviceInfoMainBoardType
        for new hardware platform support."

    REVISION 	"200802151400Z"      -- Feb 15, 14:00 EST 2008
    DESCRIPTION
        "Removed '_' characters from enumeration labels.
        Added new objects:
           rcDeviceInfoPendingBootSwVersion
           rcDeviceInfoPendingMainSwVersion
           rcDeviceInfoCfgRevision
		   rcDeviceCommReset
           rcDeviceCommLoadDefaultCfg,
		   rcDeviceCommClearAlarms,
		   rcDeviceCommClearSyslog
        "

    REVISION 	"200609061400Z"      -- Sept 6, 14:00 EST 2006
    DESCRIPTION
        "The initial version of RuggedCom system information MIB."
    ::= { ruggedcomMgmt 2 }

RcHardwareStatus ::= TEXTUAL-CONVENTION
    STATUS       current
    DESCRIPTION
		"A status of a hardware module in the RuggedCom device."
    SYNTAX  	INTEGER {
					notPresent(1),		-- the module is not present
					functional(2),	    -- the module is present and functional
					notFunctional(3),   -- the module is present, but not
										-- functional
					notConnected(4)		-- the module is present, but not connected
			    }

RcFanStatus ::= TEXTUAL-CONVENTION
    STATUS       current
    DESCRIPTION
		"The status of a fan-bank."
    SYNTAX  	INTEGER {
					notPresent(1),	-- this bank is not present
					failed(2),		-- this bank has failed due to a mechanical
									-- or sensor problem
					standby(3),	    -- the fan system is active, but this bank
									-- is designated as a backup and not
					off(4),			-- currently spinning this bank is off
					on(5)			-- this bank is currently spinning
			    }

RcHotswapModuleSlot ::= TEXTUAL-CONVENTION
    STATUS       current
    DESCRIPTION
		"A physical slot holding the hotswapable module (ROX 2 specific).
		 As the value 0 is forbidden in SNMP enumerations, this value is the
		 value 1 higher than some other ROX 2 slot values"
    SYNTAX  	INTEGER {
					pm1(1),
					lm1(2),
					lm2(3),
					lm3(4),
					cm(5),
					sm(6),
					lm4(7),
					lm5(8),
					lm6(9),
					pm2(10),
					main(11), -- The backplane is not hotswapable
					em(12)    -- This is a logical slot not a physical one,
							  -- not hotswapable
			    }

RcHotswapModuleState ::= TEXTUAL-CONVENTION
    STATUS       current
    DESCRIPTION
		"A status of a hardware module in the RuggedCom device."
    SYNTAX  	INTEGER {
					empty(1),		-- the module is not present
					disabled(2),	-- the module is present, but has been
									-- disabled by configuration.
					resetting(3),   -- the module is present and is on its way
									-- to either operating or failed.
					operating(4),   -- the module is present and has reached
									-- the operating state
					failed(5),		-- the module is present, but cannot be
					unknown(255)    -- booted unknown status
			    }



RcMainBoard ::= TEXTUAL-CONVENTION
    STATUS       current
    DESCRIPTION
		"A main board type code. This textual convention will be updated
		any time when new main board type is developed."
    SYNTAX  	INTEGER {
							rsMCPU2(1),			-- RSMCPU, otherwise known as
												-- 40-00-0026 Rev A1
							rs400revB2(2),
							rmc30(3),
							rs900revB1F(4),		-- RS900 with 6 copper,
												-- 2 fiber and 1 optional port
							rs900revB1noF(5),	-- RS900 with 8 copper and 1
												-- optional port
							rs1600M(6),			-- RS1600 Modular, obsolete
							rs400revC1(7),
							rsG2100(8),
							rs900G(9),
							rsG2200(10),
							rs969(11),
							rs900v2F(12),		-- RS900 88E6095 based with
												-- 6 copper, 2 fiber and
							rs900v2noF(13),		-- 1 optional port RS900
												-- 88E6095 based with 8 copper
												-- and 1 optional port
							rs416(15),
							rsRMC30Ksz80001(16),
							rs930(17),
							rs969v2(18),
							rs910(19),
							rs920(20),
							rs940G(21),
							rsi80x(22),
							rsG2300(23),
							rs416v2(24),
							rsg2288(25),
							rp110(26),
							rs900GP(27),
							rs900M(28),
							rs950G(29),
							rs900v3F(30),
							rs900v3noF(31),
							rsg2100v2(32),
							rsG2488(61),
							rsG2488v2(62),
							rsG2488v3(63),
							rmc8388A(64),
							rmc8388B(65),
							rmc8388C(66),
							rsG920P(67),
							rsl910(68),
							rsg9xxc(70),
							rsg9xxr(71),
							rst2228(129),
							rst916(130),
							rsMCPU(255),	    -- RSMCPU, otherwise known
												-- as 40-00-0008 Rev B1
							rx1000(256),
							rx1100(257),
							rx1500(258),
							rx1501(259),
							rx1510(260),
							rx1511(261),
							rx1512(262),
							rx5000(263),
							mx5000(264),
							rx1400(265)
			    }


rcSysInfoConformance OBJECT IDENTIFIER ::= { rcSysInfo 5 }
-- rcSysInfoCompliances  OBJECT IDENTIFIER ::= { rcSysInfoConformance 1 }
rcSysInfoGroups OBJECT IDENTIFIER ::= { rcSysInfoConformance 2 }

-- ---------------------------------------------------------------------- --
--  SysInfo subtrees
-- ---------------------------------------------------------------------- --


rcDeviceError OBJECT-IDENTITY
    STATUS      current
    DESCRIPTION
        "The main subtree for various errors detected in RuggedCom devices."
    ::= { rcSysInfo  1 }

rcDeviceStatus OBJECT-IDENTITY
    STATUS      current
    DESCRIPTION
        "The main subtree for various status information detected in
        RuggedCom devices."
    ::= { rcSysInfo  2 }

rcDeviceInfo OBJECT-IDENTITY
    STATUS      current
    DESCRIPTION
        "The main subtree for RuggedCom devices manufacturing information."
    ::= { rcSysInfo  3 }

rcDeviceCommands OBJECT-IDENTITY
    STATUS      current
    DESCRIPTION
        "The main subtree for device control commands."
    ::= { rcSysInfo  4 }

-- ---------------------------------------------------------------------- --
--  Device errors objects
-- ---------------------------------------------------------------------- --

rcDeviceErrBootupError OBJECT-TYPE
    SYNTAX  	DisplayString
    MAX-ACCESS  read-only
    STATUS      obsolete
    DESCRIPTION
         "The error discovered during bootup process.
         If there was no error during device bootup, zero length string
         will be retreived."
    ::= { rcDeviceError 1}

rcDeviceErrWatchdogReset OBJECT-TYPE
    SYNTAX  	TruthValue
    MAX-ACCESS  read-only
    STATUS      obsolete
    DESCRIPTION
         "Indicates whether the last device reboot was caused by wachdog."
    ::= { rcDeviceError 2}

rcDeviceErrConfigurationFailure OBJECT-TYPE
    SYNTAX  	TruthValue
    MAX-ACCESS  read-only
    STATUS      obsolete
    DESCRIPTION
         "Indicates whether errors were detected while applying configuration
         settings from configuration file.
         Configuration is updated from the configureation file at bootup time
         when file is loaded from nonvolatile memory, or when new file is
         downloaded to the device.
         Whenever the value of this object changes from false(2) to true(1),
         the device will generate genericTrap notification."
    REFERENCE
    	"genericTrap notification is defined in ruggedcomTrapsModule."
    ::= { rcDeviceError 3}

rcDeviceErrCrashLogCreated OBJECT-TYPE
    SYNTAX  	TruthValue
    MAX-ACCESS  read-only
    STATUS      obsolete
    DESCRIPTION
         "Indicates whether the device error that caused creation of an
         entry in crashlog.txt file was detected.
         Whenever the value of this object changes from false(2) to true(1),
         the device will generate genericTrap notification."
    REFERENCE
    	"genericTrap notification is defined in ruggedcomTrapsModule."
    ::= { rcDeviceError 4}

rcDeviceErrStackOverflow OBJECT-TYPE
    SYNTAX  	TruthValue
    MAX-ACCESS  read-only
    STATUS      obsolete
    DESCRIPTION
         "Indicates whether the stack of any of the system tasks is used
         over the system threshold.
         Whenever the value of this object changes from false(2) to true(1),
         the device will generate genericTrap notification."
    REFERENCE
    	"genericTrap notification is defined in ruggedcomTrapsModule."
    ::= { rcDeviceError 5}

rcDeviceErrHeapError OBJECT-TYPE
    SYNTAX  	TruthValue
    MAX-ACCESS  read-only
    STATUS      obsolete
    DESCRIPTION
         "Indicates whether the system memory corruption was detected.
         Whenever the value of this object changes from false(2) to true(1),
         the device will generate genericTrap notification."
    REFERENCE
    	"genericTrap notification is defined in ruggedcomTrapsModule."
    ::= { rcDeviceError 6}

rcDeviceErrDateAndTimeSetFailed OBJECT-TYPE
    SYNTAX  	TruthValue
    MAX-ACCESS  read-only
    STATUS      obsolete
    DESCRIPTION
         "Indicates whether the date and time setting in the device falied.
         Whenever the value of this object changes from false(2) to true(1),
         the device will generate genericTrap notification."
    REFERENCE
    	"genericTrap notification is defined in ruggedcomTrapsModule."
    ::= { rcDeviceError 7}

rcDeviceErrNtpServerUnreachable OBJECT-TYPE
    SYNTAX  	TruthValue
    MAX-ACCESS  read-only
    STATUS      current
    DESCRIPTION
         "Indicates whether any of NTP servers (if required) can be reached.
         The value of this object is 'true' if both servers become unreachable.
         Whenever the value of this object changes, the device will generate
		 the ntpServiceAvailableChange notification."
    REFERENCE
    	"ntpServiceAvailableChange notification is defined in RUGGEDCOM-NTP-MIB file."
    ::= { rcDeviceError 8 }

rcDeviceErrBootPTftpTrFailed OBJECT-TYPE
    SYNTAX  	TruthValue
    MAX-ACCESS  read-only
    STATUS      current
    DESCRIPTION
         "Indicates whether the the file was transfered properly after
         obtaining IP address from the BootP server.
         Whenever the value of this object changes from false(2) to true(1),
         the device will generate genericTrap notification."
    REFERENCE
    	"genericTrap notification is defined in ruggedcomTrapsModule."
    ::= { rcDeviceError 9 }

rcDeviceErrRadiusServerUnreachable OBJECT-TYPE
    SYNTAX  	TruthValue
    MAX-ACCESS  read-only
    STATUS      current
    DESCRIPTION
         "Indicates whether the RADIUS server (if required) can be reached.
         Whenever the value of this object changes, the device will generate
		 the radiusServiceAvailableChange notification."
    REFERENCE
    	"radiusServiceAvailableChange notification is defined in ruggedcomTrapsModule."
    ::= { rcDeviceError 10 }

rcDeviceErrTacacsServerUnreachable OBJECT-TYPE
    SYNTAX  	TruthValue
    MAX-ACCESS  read-only
    STATUS      current
    DESCRIPTION
         "Indicates whether the TACACS+ server (if required) can be reached.
         Whenever the value of this object changes, the device will generate
		 the tacacsServiceAvailableChange notification."
    REFERENCE
    	"tacacsServiceAvailableChange notification is defined in ruggedcomTrapsModule."
    ::= { rcDeviceError 11 }


rcDeviceErrSystem OBJECT-TYPE
	SYNTAX  BITS {
               errCrashLog(0),
               errWatchdogRst(1),
               errBootupErr(2),
               errCfgFailure(3),
               errStackOvfl(4),
               errHeapErr(5),
               errRealTimeClk(6),
               errRxBuffersLow(7),
			   errClockManager_OutOfResources(8),
			   errClockManager_PrimarySourceFailed(9),
			   errFpgaCompatibility(10),
			   }
	MAX-ACCESS read-only
	STATUS      current
	DESCRIPTION
		"Indicated whether a device failure occured. Whenever the value of this object
		changes, the device will generate the deviceErrTrap notification."
	REFERENCE
		"deviceErrTrap notification is defined in ruggedcomTrapsModule."
	::= {rcDeviceError 12 }


-- ---------------------------------------------------------------------- --
--  Device Status information objects
-- ---------------------------------------------------------------------- --

rcDeviceStsCpuUsage OBJECT-TYPE
    SYNTAX  	Integer32
    UNITS      "tenths of percent"
    MAX-ACCESS  read-only
    STATUS      current
    DESCRIPTION
         "The percentage in tenths of percent of available CPU cycles used
         for device operation as measured over the last second when
         object was retreived."
    ::= { rcDeviceStatus 1 }

rcDeviceStsAvailableRam OBJECT-TYPE
    SYNTAX  	Integer32
    MAX-ACCESS  read-only
    STATUS      current
    DESCRIPTION
         "The total number of bytes of RAM still available in the system
         control CPU."
    ::= { rcDeviceStatus 2 }

rcDeviceStsTemperature OBJECT-TYPE
    SYNTAX  	Integer32
    UNITS      "Celsius degrees"
    MAX-ACCESS  read-only
    STATUS      current
    DESCRIPTION
         "The temperature measured in the device."
    ::= { rcDeviceStatus 3 }

rcDeviceStsPowerSupply1 OBJECT-TYPE
    SYNTAX  	RcHardwareStatus
    MAX-ACCESS  read-only
    STATUS      current
    DESCRIPTION
         "Indicates the status of Power Supply Module 1.
         Whenever the value of this object changes from functional(2) to
         notFunctional(3), or from notFunctionl(3) to functional(2),
         the device will generate powerSupplyTrap notification."
    REFERENCE
    	"powerSupplyTrap notification is defined in ruggedcomTrapsModule."
    ::= { rcDeviceStatus 4 }

rcDeviceStsPowerSupply2 OBJECT-TYPE
    SYNTAX  	RcHardwareStatus
    MAX-ACCESS  read-only
    STATUS      current
    DESCRIPTION
         "Indicates the status of Power Supply Module 2.
         Whenever the value of this object changes from functional(2) to
         notFunctional(3), or from notFunctionl(3) to functional(2),
         the device will generate powerSupplyTrap notification."
    REFERENCE
    	"powerSupplyTrap notification is defined in ruggedcomTrapsModule."
    ::= { rcDeviceStatus 5 }

rcDeviceStsCpuUsagePercent OBJECT-TYPE
    SYNTAX  	Integer32
    UNITS      "percent"
    MAX-ACCESS  read-only
    STATUS      current
    DESCRIPTION
         "The percentage of available CPU cycles used for device operation
         as measured over the last second when object was retreived."
    ::= { rcDeviceStatus 6 }


rcDeviceStsFailSafeRelay OBJECT-TYPE
    SYNTAX  	INTEGER {
					energized(1),
					deEnergized(2)
			    }
    MAX-ACCESS  read-only
    STATUS      current
    DESCRIPTION
         "Indicates status of fail safe relay in the device.
         Fail safe relay is deEnergized(2) if there is at least one active
         alarm recorded in the device."
    ::= { rcDeviceStatus 7 }


rcDeviceStsErrorAlarm OBJECT-TYPE
    SYNTAX  	TruthValue
    MAX-ACCESS  read-only
    STATUS      current
    DESCRIPTION
         "Indicates that at least one alarm of level ERROR, ALERT or CRITICAL
         is active in the device."
    ::= { rcDeviceStatus 8 }


rcDeviceStsNoOfActiveAlarms OBJECT-TYPE
    SYNTAX  	Integer32
    MAX-ACCESS  read-only
    STATUS      current
    DESCRIPTION
         "Number of active alarms currently recorded in device."
    ::= { rcDeviceStatus 9 }

rcDeviceStsFanBank1 OBJECT-TYPE
    SYNTAX  	RcFanStatus
    MAX-ACCESS  read-only
    STATUS      current
    DESCRIPTION
         "Indicates the status of Fan Bank Module 1."
    REFERENCE
    	"fanBankTrap notification is defined in ruggedcomTrapsModule."
    ::= { rcDeviceStatus 10 }

rcDeviceStsFanBank2 OBJECT-TYPE
    SYNTAX  	RcFanStatus
    MAX-ACCESS  read-only
    STATUS      current
    DESCRIPTION
         "Indicates the status of Fan Bank Module 2."
    REFERENCE
    	"fanBankTrap notification is defined in ruggedcomTrapsModule."
    ::= { rcDeviceStatus 11 }

rcDeviceStsPwdsWeak OBJECT-TYPE
    SYNTAX  	BITS {
				     adminPwd(0),
				     operPwd(1),
				     guestPwd(2)
			    }
    MAX-ACCESS  read-only
    STATUS      current
    DESCRIPTION
         "Indicates if any of passwords is configured as 'weak'.
         Change in the value of the bit in this object from '0' to  '1'
         will generate weakPasswordTrap."
    REFERENCE
    	"weakPasswordTrap notification is defined in ruggedcomTrapsModule."
    ::= { rcDeviceStatus 12 }

rcDeviceStsKeysDflt OBJECT-TYPE
    SYNTAX  	BITS {
					sshDfltKeys(0),
					sslDfltKeys(1)
			    }
    MAX-ACCESS  read-only
    STATUS      current
    DESCRIPTION
         "Indicates if any of secure services uses default keys and/or
         certificates. Customer is advised to update keys for secure
         services if defaults are used.
         Change in the value of the bit in this object from '0' to  '1'
         will generate defaultKeysTrap notification."
    REFERENCE
    	"defaultKeysTrap notification is defined in ruggedcomTrapsModule."
    ::= { rcDeviceStatus 13 }

-- ---------------------------------------------------------------------- --
--  General System Information objects
-- ---------------------------------------------------------------------- --

rcDeviceInfoSerialNumber OBJECT-TYPE
    SYNTAX  	DisplayString
    MAX-ACCESS  read-only
    STATUS      current
    DESCRIPTION
         "The manufacturing serial number of the device."
    ::= { rcDeviceInfo 1 }

rcDeviceInfoBootSwVersion OBJECT-TYPE
    SYNTAX  	DisplayString
    MAX-ACCESS  read-only
    STATUS      current
    DESCRIPTION
         "The version and the build date of the boot loader software."
    ::= { rcDeviceInfo 2 }

rcDeviceInfoMainSwVersion OBJECT-TYPE
    SYNTAX  	DisplayString
    MAX-ACCESS  read-only
    STATUS      current
    DESCRIPTION
         "The version and the build date of the main operating system
         software."
    ::= { rcDeviceInfo 3 }

rcDeviceInfoMainBoardType OBJECT-TYPE
    SYNTAX  	RcMainBoard
    MAX-ACCESS  read-only
    STATUS      current
    DESCRIPTION
         "The identification code of the device main board."
    ::= { rcDeviceInfo 4 }

rcDeviceInfoTotalRam OBJECT-TYPE
    SYNTAX  	Integer32
    MAX-ACCESS  read-only
    STATUS      current
    DESCRIPTION
         "The total number of bytes of RAM in the system control CPU."
    ::= { rcDeviceInfo 5 }

rcDeviceInfoPendingBootSwVersion OBJECT-TYPE
    SYNTAX  	DisplayString
    MAX-ACCESS  read-only
    STATUS      current
    DESCRIPTION
         "The version and the build date of the boot loader software
         that has been loaded to the device and is pending reboot.
         Whenever the value of this object changes from zero-length string
         to any string of non-zero length, the device will generate
         swUpgradeTrap notification."
    REFERENCE
    	"swUpgradeTrap notification is defined in ruggedcomTrapsModule."
    ::= { rcDeviceInfo 6 }

rcDeviceInfoPendingMainSwVersion OBJECT-TYPE
    SYNTAX  	DisplayString
    MAX-ACCESS  read-only
    STATUS      current
    DESCRIPTION
         "The version and the build date of the main operating system
         software that has been loaded to the device and is pending reboot.
         Whenever the value of this object changes from zero-length string
         to any string of non-zero length, the device will generate
         swUpgradeTrap notification."
    REFERENCE
    	"swUpgradeTrap notification is defined in ruggedcomTrapsModule."
    ::= { rcDeviceInfo 7 }

rcDeviceInfoCfgRevision OBJECT-TYPE
    SYNTAX  	Integer32
    MAX-ACCESS  read-only
    STATUS      current
    DESCRIPTION
         "The configuration file revision.
         The revision number will be updated whenever file is saved to the
         flash memory. This number is recorded in config.csv at the time file
         is uploaded from the device.
         Whenever the value of this object changes the device will generate
         cfgChangeTrap notification."
    REFERENCE
    	"cfgChangeTrap notification is defined in ruggedcomTrapsModule."
    ::= { rcDeviceInfo 8 }

rcDeviceInfoMinBootSwVer OBJECT-TYPE
    SYNTAX  	DisplayString
    MAX-ACCESS  read-only
    STATUS      current
    DESCRIPTION
         "The minimum version of the boot loader software required by
         ROS device. If this version is not newer than the version
         retreived as a value of object rcDeviceInfoBootSwVersion, trap
         bootVersionMismatchTrap will be generated."

    REFERENCE
    	"bootVersionMismatchTrap notification is defined in
    	ruggedcomTrapsModule."
    ::= { rcDeviceInfo 9 }

-- ---------------------------------------------------------------------- --
--  Device control commands objects
-- ---------------------------------------------------------------------- --

rcDeviceCommReset OBJECT-TYPE
    SYNTAX  	TruthValue
    MAX-ACCESS  read-write
    STATUS      current
    DESCRIPTION
         "Setting the value of this object to 'true(1)' will cause device
          to reboot.
          As a result of Read request the agent will return value 'false(2)'."
    ::= { rcDeviceCommands 1}

rcDeviceCommLoadDefaultCfg OBJECT-TYPE
    SYNTAX  	TruthValue
    MAX-ACCESS  read-write
    STATUS      current
    DESCRIPTION
         "Setting the value of this object to 'true(1)' will force device
          to load default configuration to all tables.
          As a result of Read request the agent will return value 'false(2)'."
    ::= { rcDeviceCommands 2}

rcDeviceCommClearAlarms OBJECT-TYPE
    SYNTAX  	TruthValue
    MAX-ACCESS  read-write
    STATUS      current
    DESCRIPTION
         "Setting the value of this object to 'true(1)' will cause device
         to clear all alarms.
         As a result of Read request the agent will return value 'false(2)'."
    ::= { rcDeviceCommands 3}

rcDeviceCommClearSyslog OBJECT-TYPE
    SYNTAX  	TruthValue
    MAX-ACCESS  read-write
    STATUS      current
    DESCRIPTION
         "Setting the value of this object to 'true(1)' will cause device
         to clear syslog.txt file.
         As a result of Read request the agent will return value 'false(2)'."
    ::= { rcDeviceCommands 4}

rcDeviceCommClearLogs OBJECT-TYPE
    SYNTAX  	TruthValue
    MAX-ACCESS  read-write
    STATUS      current
    DESCRIPTION
         "Setting the value of this object to 'true(1)' will cause device
         to clear syslog.txt and crashlog.txt files.
         As a result of Read request the agent will return value 'false(2)'."
    ::= { rcDeviceCommands 5}

rcDeviceCommIdentify OBJECT-TYPE
    SYNTAX  	Integer32 (0..300)
    MAX-ACCESS  read-write
    STATUS      current
    DESCRIPTION
         "Time Period in seconds for which the device should continue flashing
         the LEDs when possible so that device is visually recognized.
         Setting this value to any value greater than 0 will start LED flash
         timer on the device.Setting the value to 0 will stop the LED flash
         timer. On Read request agent always sends back the existing Timeout
         value for LED flash Timer."
    ::= { rcDeviceCommands 6 }


-- ---------------------------------------------------------------------- --
--  Object Groups
-- ---------------------------------------------------------------------- --

rcSysErrObjectsGroup OBJECT-GROUP
    OBJECTS     {
					rcDeviceErrBootupError,
					rcDeviceErrWatchdogReset,
					rcDeviceErrConfigurationFailure,
					rcDeviceErrCrashLogCreated,
					rcDeviceErrStackOverflow,
					rcDeviceErrHeapError,
					rcDeviceErrDateAndTimeSetFailed,
					rcDeviceErrNtpServerUnreachable,
					rcDeviceErrBootPTftpTrFailed,
					rcDeviceErrRadiusServerUnreachable,
					rcDeviceErrTacacsServerUnreachable
                }
    STATUS      obsolete
    DESCRIPTION
        "A group of objects providing information about irregularities
        in the device."
    ::= { rcSysInfoGroups 1 }

rcSysStsObjectsGroup OBJECT-GROUP
    OBJECTS     {
					rcDeviceStsCpuUsage,
					rcDeviceStsCpuUsagePercent,
					rcDeviceStsAvailableRam
				}
    STATUS      obsolete
    DESCRIPTION
        "A group of objects providing information device resources."
    ::= { rcSysInfoGroups 2 }


rcSysStsObjectsTemperatureGroup OBJECT-GROUP
    OBJECTS     {
					rcDeviceStsTemperature
				}
    STATUS      current
    DESCRIPTION
        "This group is created to allow MIBs for products that do not have
        temperature sensore installed to exclude rcDeviceStsTemperature
        object."
    ::= { rcSysInfoGroups 3 }

rcSysStsPowerSupplyGroup OBJECT-GROUP
    OBJECTS     {
					rcDeviceStsPowerSupply1,
					rcDeviceStsPowerSupply2
                }
    STATUS      current
    DESCRIPTION
        "A group of objects providing information about power supply modules
        in the device. This group is mandatory for products with redundant
        power supply."
    ::= { rcSysInfoGroups 4 }

rcSysInfoDeviceInfoGroup  OBJECT-GROUP
    OBJECTS     {
					rcDeviceInfoMainBoardType,
					rcDeviceInfoTotalRam,
					rcDeviceInfoBootSwVersion,
					rcDeviceInfoMainSwVersion,
					rcDeviceInfoPendingBootSwVersion,
					rcDeviceInfoPendingMainSwVersion,
					rcDeviceInfoCfgRevision,
					rcDeviceInfoSerialNumber
                }
    STATUS      current
    DESCRIPTION
        "A group of object providing manufacturer's information about
        product's main board hardware, software, identification."
    ::= { rcSysInfoGroups 5 }

rcSysDeviceCommGroup  OBJECT-GROUP
    OBJECTS     {
					rcDeviceCommReset,
					rcDeviceCommLoadDefaultCfg,
					rcDeviceCommClearAlarms,
					rcDeviceCommClearSyslog,
                    rcDeviceCommClearLogs
                }
    STATUS      current
    DESCRIPTION
        "A group of object providing device control commands."
    ::= { rcSysInfoGroups 6 }

rcSysDeviceCommIdentifyGroup  OBJECT-GROUP
    OBJECTS     {
					rcDeviceCommIdentify
                }
    STATUS      current
    DESCRIPTION
        "A group of object providing device control commands for
        visual recognisation of the device (LED flashing)."
    ::= { rcSysInfoGroups 7 }



rcSysStsObjectsGroup1 OBJECT-GROUP
    OBJECTS     {
					rcDeviceStsCpuUsage,
					rcDeviceStsCpuUsagePercent,
					rcDeviceStsAvailableRam,
					rcDeviceStsErrorAlarm,
					rcDeviceStsFailSafeRelay,
					rcDeviceStsNoOfActiveAlarms
				}
    STATUS      current
    DESCRIPTION
        "A group of objects providing information about device resources."
    ::= { rcSysInfoGroups 8 }


rcSysStsFanBankGroup OBJECT-GROUP
    OBJECTS     {
					rcDeviceStsFanBank1,
					rcDeviceStsFanBank2
                }
    STATUS      current
    DESCRIPTION
        "A group of objects providing information about fan bank modules
        in the device. This group is mandatory for products with redundant
        fan banks."
    ::= { rcSysInfoGroups 9 }


rcSysDeviceSecurityGroup  OBJECT-GROUP
    OBJECTS     {
					rcDeviceStsPwdsWeak
                }
    STATUS      current
    DESCRIPTION
        "A group of object providing device control commands."
    ::= { rcSysInfoGroups 10 }

rcSysDeviceSecurityGroup01  OBJECT-GROUP
    OBJECTS     {
					rcDeviceStsPwdsWeak,
					rcDeviceStsKeysDflt,
					rcDeviceInfoMinBootSwVer
                }
    STATUS      current
    DESCRIPTION
        "A group of object providing device control commands."
    ::= { rcSysInfoGroups 11 }

rcSysErrObjectsGroup1 OBJECT-GROUP
    OBJECTS     {
					rcDeviceErrSystem
                }
    STATUS      current
    DESCRIPTION
        "A group of objects providing information about device system errors."
    ::= { rcSysInfoGroups 12 }

END
