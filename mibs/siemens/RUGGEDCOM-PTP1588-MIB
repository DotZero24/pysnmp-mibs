RUGGEDCOM-PTP1588-MIB DEFINITIONS ::= BEGIN

IMPORTS
    MODULE-IDENTITY,
    OBJECT-TYPE, Integer32, NOTIFICATION-TYPE,
    IpAddress										FROM SNMPv2-SMI
    TEXTUAL-CONVENTION, TruthValue				  	FROM SNMPv2-TC
    OBJECT-GROUP			       	    			FROM SNMPv2-CONF
    DisplayString									FROM SNMPv2-TC
    PortList   										FROM Q-BRIDGE-MIB
    ruggedcomMgmt									FROM RUGGEDCOM-MIB;

rcPTP1588 	MODULE-IDENTITY
    LAST-UPDATED "202307071600Z"      -- July 7, 16:00 EST 2023
    ORGANIZATION "Siemens Canada Ltd."
    CONTACT-INFO
       "Postal: RuggedCom Inc.
                300 Applewood Crescent
                Concord, Ontario,
                L4K 5C7 Canada
        Tel:    1-905-856-5288
        E-Mail: support@ruggedcom.com"
    DESCRIPTION
        "Siemens - RuggedCom proprietary to control and monitor PTP1588 module."

	REVISION    "201509231300Z"      -- Sep 23, 13:00 EST 2015
    DESCRIPTION
        "Initial version of Siemens - RuggedCom proprietary MIB to control and
        monitor PTP1588 module."

	REVISION    "202206171300Z"      -- June 17, 13:00 EST 2022
    DESCRIPTION
       "Add the following objects to the list to display the PTP clock parameters
        and mib object to enable PTP globally.
			rcPTP1588ClkAnnounceInt
			rcPTP1588ClkAnnounceRcTout
			rcPTP1588ClkSyncInt
			rcPTP1588ClkDelayMech
			rcPTP1588GlobleEnable
			rcPTP1588ClkProfileId
			rcPTP1588ClkNetProtocol
			rcPTP1588ClkVlanId
			rcPTP1588ClkPriority"

	REVISION    "202207201215Z"      -- July 17, 12:15 EST 2022
    DESCRIPTION
       "Added the following object to the list to display the PTP clock parameters.
			rcPTP1588ClkDomainNumber"

	REVISION    "202207251000Z"      -- Ju1y 25, 10:00 EST 2022
    DESCRIPTION
       "Added the following objects to the list to display the Global PTP parameters.
			rcPTP1588GlobalP2PRequestInterval
			rcPTP1588GlobalE2ERequestInterval
			rcPTP1588Global1Step"

	REVISION    "202305011700Z"      -- May 1, 17:00 EST 2023
    DESCRIPTION
       "Added the following objects to the list to display the Boundry Clock PTP parameters.
		rcPTP1588BClkPorts
		rcPTP1588BClkGroupName
        rcPTP1588BClkProfileId
        rcPTP1588BClkDomainNumber
        rcPTP1588BClkTransportProtocol
        rcPTP1588BClkPathDelayMech
        rcPTP1588BClkPTPPortType
        rcPTP1588BClkSyncInt
        rcPTP1588BClkAnnounceInt
        rcPTP1588BClkAnnounceRcTout
        rcPTP1588BClkAutoReg
        rcPTP1588BClkMasterIP
        rcPTP1588BClkBackUpIP
        rcPTP1588BClkGMIdentity
        rcPTP1588BClkVlanId
        rcPTP1588BClkPriority"

	REVISION    "202307071600Z"      -- July 7, 16:00 EST 2023
    DESCRIPTION
       "Added the following object to the list to display the Ordinary Clock PTP Clock Accuracy.
		rcPTP1588ClkAccuracy"


    ::= { ruggedcomMgmt 12 }

--=====================================================================
-- Textual Conventions
--=====================================================================

-- ---------------------------------------------------------- --
-- rcPTP1588 sub-trees
-- ---------------------------------------------------------- --
rcPTP1588Base				OBJECT IDENTIFIER ::= { rcPTP1588 1 }
rcPTP1588Conformance 		OBJECT IDENTIFIER ::= { rcPTP1588 3 }
rcPTP1588Groups 			OBJECT IDENTIFIER ::= { rcPTP1588Conformance 2 }
rcPTP1588BCTables			OBJECT IDENTIFIER ::= { rcPTP1588 4 }

-- -------------------------------------------------------------
-- Base sub-tree
-- -------------------------------------------------------------
rcPTP1588ClkType		 OBJECT-TYPE
    SYNTAX	INTEGER {
						ordinaryClock(2),
						p2ptc(3),
						boundaryClock(4),
						e2etc(5),
						ocp2ptc(6),
						oce2etc(7),
						transparentClock(8),
						ocAndTc(9)
					}
    MAX-ACCESS  read-write
    STATUS      current
    DESCRIPTION
         "PTP1588 Clock Type."
    ::= { rcPTP1588Base 1}

rcPTP1588EthPorts		 OBJECT-TYPE
    SYNTAX		PortList
    MAX-ACCESS  read-write
    STATUS      current
    DESCRIPTION
         "Selects which Ethernet ports will take part in PTP
          (Precision Time Protocol) message exchanges."
    ::= { rcPTP1588Base 2}

rcPTP1588StartUpWait	 OBJECT-TYPE
    SYNTAX		Integer32(0..3600)
    MAX-ACCESS  read-write
    STATUS      current
    DESCRIPTION
         "This parameter in seconds provides the ability to bootstrap the PTP
         network in an orderly fashion."
    ::= { rcPTP1588Base 3}

rcPTP1588NetClass		 OBJECT-TYPE
    SYNTAX		INTEGER {
					netclass1588(1),
					nonnetclass1588(2)
				}
    MAX-ACCESS  read-write
    STATUS      current
    DESCRIPTION
         "This parameter indicates all devices in the timing plane are IEEE1588 aware
          (IEEE1588 network) or whether the timing plane includes non-IEEE1588 devices
           as well (non-IEEE1588 network)."
    ::= { rcPTP1588Base 4}

rcPTP1588SlaveEthPort	 OBJECT-TYPE
    SYNTAX		PortList
    MAX-ACCESS  read-write
    STATUS      current
    DESCRIPTION
         "Selects the Ethernet port which will act as the Slave port when the device is
          configured as a Boundary Clock."
    ::= { rcPTP1588Base 5}

rcPTP1588SlaveDomain	 OBJECT-TYPE
    SYNTAX		Integer32(0..127)
    MAX-ACCESS  read-write
    STATUS      current
    DESCRIPTION
         "Selects the PTP (Precision Time Protocol) domain number for the Slave Clock. A
          PTP domain is a logical grouping of PTP clocks that synchronize to each other
          using the PTP protocol."
    ::= { rcPTP1588Base 6}

rcPTP1588SlaveAutoReg	 OBJECT-TYPE
    SYNTAX		TruthValue
    MAX-ACCESS  read-write
    STATUS      current
    DESCRIPTION
         "This parameter is specific to unicast transport. This parameter allows user to
          auto register the slave clock to unicast master as specified by the 'Master IP
          Address' attribute."
    ::= { rcPTP1588Base 7}

rcPTP1588SlaveMasteIP	 OBJECT-TYPE
    SYNTAX		IpAddress
    MAX-ACCESS  read-write
    STATUS      current
    DESCRIPTION
         "This parameter is specific to unicast transport and represents the IP address of
          the unicast PTP (Precision Time Protocol) master clock."
    ::= { rcPTP1588Base 8}

rcPTP1588SlaveBackUpIP	 OBJECT-TYPE
    SYNTAX		IpAddress
    MAX-ACCESS  read-write
    STATUS      current
    DESCRIPTION
         "This parameter is specific to unicast transport and represents the IP address of the
          unicast backup PTP (Precision Time Protocol) master clock."
    ::= { rcPTP1588Base 9}

rcPTP1588ServoStatus	 OBJECT-TYPE
    SYNTAX		DisplayString
    MAX-ACCESS  read-only
    STATUS      current
    DESCRIPTION
         "It Shows the status of clock servo.
          Clock servo mechanism is use to discipline the system clock.
          The lock status represents clock accuracy is with in the desired limits.
          User might see system alarm before convergence of clock servo"
    ::= { rcPTP1588Base 10}

rcPTP1588SlaveFeqAdj	 OBJECT-TYPE
    SYNTAX		Integer32
    MAX-ACCESS  read-only
    STATUS      current
    DESCRIPTION
         "This parameter shows the current amount of discipline applied to the
		 local frequency reference (TCXO), i.e. the amount of correction on this
		 system required to syntonize to the current reference"
    ::= { rcPTP1588Base 11}

rcPTP1588E2EDelay	 OBJECT-TYPE
    SYNTAX		Integer32
    MAX-ACCESS  read-only
    STATUS      current
    DESCRIPTION
         "This parameter shows measured E2E (also called request-response)
		 delay between master and slave clocks"
    ::= { rcPTP1588Base 12}

rcPTP1588GlobalEnable OBJECT-TYPE
    SYNTAX TruthValue
    MAX-ACCESS read-write
    STATUS current
    DESCRIPTION
         "True if PTP is enabled globally."
    DEFVAL { false }
    ::= { rcPTP1588Base 13 }

rcPTP1588GlobalP2PRequestInterval OBJECT-TYPE
    SYNTAX INTEGER {
			value1Sec		(1),
			value2Sec		(2),
			value4Sec		(3),
			value8Sec		(4),
			value16Sec		(5),
			value32Sec		(6)
    }
    MAX-ACCESS read-write
    STATUS current
    DESCRIPTION
         "The PTP (Precision Time Protocol) Announce interval (mean time interval
		 between successive Announce messages) in seconds.
         Interpretation placed on the value:
         1: Announce value is 1 Second.
         2: Announce value is 2 Second.
         3: Announce value is 4 Second.
         4: Announce value is 8 Second.
         5: Announce value is 16 Second.
         6: Announce value is 32 Second."
    DEFVAL { 1 }
    ::= { rcPTP1588Base 14 }

rcPTP1588GlobalE2ERequestInterval OBJECT-TYPE
    SYNTAX INTEGER {
			value1Sec		(1),
			value2Sec		(2),
			value4Sec		(3),
			value8Sec		(4),
			value16Sec		(5),
			value32Sec		(6)
    }
    MAX-ACCESS read-write
    STATUS current
    DESCRIPTION
         "The PTP (Precision Time Protocol) Announce interval (mean time interval
		 between successive Announce messages) in seconds.
         Interpretation placed on the value:
         1: Announce value is 1 Second.
         2: Announce value is 2 Second.
         3: Announce value is 4 Second.
         4: Announce value is 8 Second.
         5: Announce value is 16 Second.
         6: Announce value is 32 Second."
    REFERENCE "IEEE Std 1588-2008 7.7.2.2 and 8.2.5.4.1"
    DEFVAL { 1 }
    ::= { rcPTP1588Base 15 }

rcPTP1588Global1Step OBJECT-TYPE
    SYNTAX TruthValue
    MAX-ACCESS read-write
    STATUS current
    DESCRIPTION
         "True if PTP is enabled globally."
    DEFVAL { false }
    ::= { rcPTP1588Base 16 }

rcPTP1588ClkAnnounceInt OBJECT-TYPE
    SYNTAX INTEGER {
			value1Sec		(1),
			value2Sec		(2),
			value4Sec		(3),
			value8Sec		(4),
			value16Sec		(5),
			value32Sec		(6)
    }
    MAX-ACCESS read-write
    STATUS current
    DESCRIPTION
         "The PTP (Precision Time Protocol) Announce interval (mean time interval
		 between successive Announce messages) in seconds.
         Interpretation placed on the value:
         1: Announce value is 1 Second.
         2: Announce value is 2 Second.
         3: Announce value is 4 Second.
         4: Announce value is 8 Second.
         5: Announce value is 16 Second.
         6: Announce value is 32 Second."
    REFERENCE "IEEE Std 1588-2008 7.7.2.2 and 8.2.5.4.1"
    DEFVAL { 1 }
    ::= { rcPTP1588Base 17 }

rcPTP1588ClkAnnounceRcTout OBJECT-TYPE
    SYNTAX Integer32(2..4)
    MAX-ACCESS read-write
    STATUS current
    DESCRIPTION
         "The AnnounceReceiptTimeout, an integral multiple of announceInterval."
    DEFVAL { 3 }
    ::= { rcPTP1588Base 18 }

rcPTP1588ClkSyncInt OBJECT-TYPE
    SYNTAX INTEGER {
			value125millSec		(1),
			value250millSec		(2),
			value500millSec		(3),
			value1Sec			(4),
			value2Sec			(5)
    }
    MAX-ACCESS read-write
    STATUS current
    DESCRIPTION
         "The PTP (Precision Time Protocol) Sync interval (mean time interval
		  between successive Sync messages).
		  Interpretation placed on the value:
         1: Sync interval value is 125 Millisecond.
         2: Sync interval value is 250 Millisecond.
         3: Sync interval value is 500 Millisecond.
         4: Sync interval value is 1 Second.
         5: Sync interval value is 2 Second."
    DEFVAL { 0 }
    ::= { rcPTP1588Base 19 }

rcPTP1588ClkDelayMech OBJECT-TYPE
    SYNTAX INTEGER {
			e2e			(1),
			p2p			(2),
	        disabled	(254)
		   }
    MAX-ACCESS 	read-write
    STATUS 	current
    DESCRIPTION
      "The propagation delay measuring option used by the port. For IEEE C37.238 compliant implementations this value shall be 2 (p2p)."
    REFERENCE "IEEE Std 1588-2008 8.2.5.4.4 and Table 9"
    DEFVAL  { 2 }
    ::= { rcPTP1588Base 20 }

rcPTP1588ClkProfileId OBJECT-TYPE
    SYNTAX INTEGER {
                    defaultP2PProfile   (0),
                    powerProfile        (1),
                    ieee8021as		    (2),
                    lxi	     			(3),
                    telecom 			(4),
                    utilityProfile      (5),
                    defaultE2EProfile   (6),
                    customProfile       (7),
                    powerProfileV2      (8)

                   }
    MAX-ACCESS	read-write
    STATUS	current
    DESCRIPTION
      "Indicates the PTP Profile in use."
    DEFVAL { 1 }
    ::= { rcPTP1588Base 21 }

rcPTP1588ClkDomainNumber OBJECT-TYPE
    SYNTAX Unsigned32(0..254)
    MAX-ACCESS read-write
    STATUS current
    DESCRIPTION
         "Selects the PTP (Precision Time Protocol) domain number. A PTP domain is a
		  logical grouping of PTP clocks that synchronize to each other using the PTP
		  protocol."
    DEFVAL { 0 }
    ::= { rcPTP1588Base 22 }

rcPTP1588ClkNetProtocol OBJECT-TYPE
    SYNTAX INTEGER {
				  ieee8023   (1),
                  udpIpv4    (2)
	           }
    MAX-ACCESS 	read-write
    STATUS 	current
    DESCRIPTION
       "Indicates Network Protocol in use. For IEEE C37.238 compliant implementations this value shall be 1 (ieee8023)."
    DEFVAL 	{ 1 }
    ::= { rcPTP1588Base 23 }

rcPTP1588ClkVlanId OBJECT-TYPE
    SYNTAX	Integer32(-2..4094)
    MAX-ACCESS 	read-write
    STATUS	current
    DESCRIPTION
      "Indicates VLAN ID in use.
		-2 = PVID
		-1 = Priority tagged
		0  = Untagged
		1 to 4094 = VID set"
    DEFVAL 	{ -2 }
    ::= { rcPTP1588Base 24 }

rcPTP1588ClkPriority OBJECT-TYPE
    SYNTAX	Unsigned32(0..7)
    MAX-ACCESS 	read-write
    STATUS	current
    DESCRIPTION
      "Indicates VLAN tag Priority in use."
    DEFVAL 	{ 4 }
    ::= { rcPTP1588Base 25 }

rcPTP1588ClkAccuracy OBJECT-TYPE
    SYNTAX   INTEGER {
                timeAccurateTo50ns(0),
                timeAccurateTo100ns(1),
                timeAccurateTo250ns(2),
                timeAccurateTo1us(3),
                timeAccurateTo2to5us(4),
                timeAccurateTo10us(5),
                timeAccurateTo25us(6),
                timeAccurateTo100us(7),
                timeAccurateTo250us(8),
                timeAccurateTo1ms(9),
                timeAccurateTo2to5ms(10),
                timeAccurateTo10ms(11),
                timeAccurateTo25ms(12),
                timeAccurateTo100ms(13),
                timeAccurateTo250ms(14)
                }
    MAX-ACCESS 	read-write
    STATUS	current
    DESCRIPTION
      "This parameter allows the user to configure the desired clock accuracy. This
		represents the instantaneous value of the time offset between master and slave
		clocks. The system will generate an alarm if the time offset from the master
		exceeds the desired accuracy. This mib object is supported only for OC and
		OC+TC clock type."
    DEFVAL 	{ 3 }
    ::= { rcPTP1588Base 26 }
-- ---------------------------------------------------------------------- --
rcPTP1588BClkTable OBJECT-TYPE
    SYNTAX      SEQUENCE OF RcPTP1588BClkEntry
    MAX-ACCESS  not-accessible
    STATUS      current
    DESCRIPTION
        "A table containing configuration information for
        Boundry Clock Parameters"
    ::= { rcPTP1588BCTables 1 }

rcPTP1588BClkEntry OBJECT-TYPE
    SYNTAX      RcPTP1588BClkEntry
    MAX-ACCESS  not-accessible
    STATUS      current
    DESCRIPTION
        "Static information for a Boundry Clock Parameters configured into the
        device by (local or network) management."
    INDEX {
			rcPTP1588BClkPorts
        }
    ::= { rcPTP1588BClkTable 1 }

RcPTP1588BClkEntry ::=
    SEQUENCE {
        rcPTP1588BClkPorts
            PortList,
		rcPTP1588BClkGroupName
            DisplayString,
        rcPTP1588BClkProfileId
			INTEGER,
        rcPTP1588BClkDomainNumber
			Unsigned32,
        rcPTP1588BClkTransportProtocol
			INTEGER,
        rcPTP1588BClkPathDelayMech
			INTEGER,
        rcPTP1588BClkPTPPortType
			INTEGER,
        rcPTP1588BClkSyncInt
			INTEGER,
        rcPTP1588BClkAnnounceInt
			INTEGER,
        rcPTP1588BClkAnnounceRcTout
			Integer32,
        rcPTP1588BClkAutoReg
			TruthValue,
        rcPTP1588BClkMasterIP
			IpAddress,
        rcPTP1588BClkBackUpIP
			IpAddress,
        rcPTP1588BClkGMIdentity
			Integer32,
        rcPTP1588BClkVlanId
			Integer32,
        rcPTP1588BClkPriority
			Unsigned32,
    }

rcPTP1588BClkPorts OBJECT-TYPE
    SYNTAX      PortList
    MAX-ACCESS  read-write
    STATUS      current
    DESCRIPTION
        "The set of ports"
    ::= { rcPTP1588BClkEntry 1 }

rcPTP1588BClkGroupName OBJECT-TYPE
    SYNTAX      DisplayString
    MAX-ACCESS  read-write
    STATUS      current
    DESCRIPTION
        "Name assigned to the port group"
    ::= { rcPTP1588BClkEntry 2 }

rcPTP1588BClkProfileId	 OBJECT-TYPE
    SYNTAX INTEGER {
                    defaultP2PProfile   (0),
                    powerProfile        (1),
                    ieee8021as    (2),
                    lxi     (3),
                    telecom (4),
                    utilityProfile      (5),
                    defaultE2EProfile   (6),
                    customProfile       (7),
                    powerProfileV2      (8)

                   }
    MAX-ACCESS read-write
    STATUS current
    DESCRIPTION
      "Indicates the PTP Profile in use."
    ::= { rcPTP1588BClkEntry 3}

rcPTP1588BClkDomainNumber OBJECT-TYPE
    SYNTAX Unsigned32(0..254)
    MAX-ACCESS read-write
    STATUS current
    DESCRIPTION
         "Selects the PTP (Precision Time Protocol) domain number. A PTP domain is a
		  logical grouping of PTP clocks that synchronize to each other using the PTP
		  protocol."
    ::= { rcPTP1588BClkEntry 4 }

rcPTP1588BClkTransportProtocol OBJECT-TYPE
    SYNTAX INTEGER {
					layer2multicast		(1),
					layer3multicast		(2),
					layer3unicast		(3)
			}
    MAX-ACCESS 	read-write
    STATUS 	current
    DESCRIPTION
       "Indicates Transport Protocol in use."
    ::= { rcPTP1588BClkEntry 5 }

rcPTP1588BClkPathDelayMech OBJECT-TYPE
    SYNTAX INTEGER {
					end2end		(1),
					peer2peer	(2),
					disabled	(3)
			}
    MAX-ACCESS 	read-write
    STATUS 	current
    DESCRIPTION
      "The propagation delay measuring option used by the port."
    ::= { rcPTP1588BClkEntry 6 }

rcPTP1588BClkPTPPortType OBJECT-TYPE
    SYNTAX INTEGER {
					auto		(1),
					slaveonly	(2),
					masteronly	(3)
			}
    MAX-ACCESS 	read-write
    STATUS 	current
    DESCRIPTION
      "Selects the PTP (Precision Time Protocol) Port Type. "
    ::= { rcPTP1588BClkEntry 7 }

rcPTP1588BClkSyncInt OBJECT-TYPE
    SYNTAX INTEGER {
					value125millSec		(1),
					value250millSec		(2),
					value500millSec		(3),
					value1Sec			(4),
					value2Sec			(5)
			}
    MAX-ACCESS read-write
    STATUS current
    DESCRIPTION
         "The PTP (Precision Time Protocol) Sync interval (mean time interval
		  between successive Sync messages).
		  Interpretation placed on the value:
         1: Sync interval value is 125 Millisecond.
         2: Sync interval value is 250 Millisecond.
         3: Sync interval value is 500 Millisecond.
         4: Sync interval value is 1 Second.
         5: Sync interval value is 2 Second."
    ::= { rcPTP1588BClkEntry 8 }

rcPTP1588BClkAnnounceInt OBJECT-TYPE
    SYNTAX INTEGER {
					value1Sec		(1),
					value2Sec		(2),
					value4Sec		(3),
					value8Sec		(4),
					value16Sec		(5),
					value32Sec		(6)
			}
    MAX-ACCESS read-write
    STATUS current
    DESCRIPTION
         "The PTP (Precision Time Protocol) Announce interval (mean time interval
		 between successive Announce messages) in seconds.
         Interpretation placed on the value:
         1: Announce value is 1 Second.
         2: Announce value is 2 Second.
         3: Announce value is 4 Second.
         4: Announce value is 8 Second.
         5: Announce value is 16 Second.
         6: Announce value is 32 Second."
    ::= { rcPTP1588BClkEntry 9 }

rcPTP1588BClkAnnounceRcTout OBJECT-TYPE
    SYNTAX Integer32(2..4)
    MAX-ACCESS read-write
    STATUS current
    DESCRIPTION
         "The AnnounceReceiptTimeout, an integral multiple of announceInterval."
    ::= { rcPTP1588BClkEntry 10 }

rcPTP1588BClkAutoReg	 OBJECT-TYPE
    SYNTAX		TruthValue
    MAX-ACCESS  read-write
    STATUS      current
    DESCRIPTION
         "This parameter is specific to unicast transport. This parameter allows user to
          auto register the slave clock to unicast master as specified by the 'Master IP
          Address' attribute."
    ::= { rcPTP1588BClkEntry 11 }

rcPTP1588BClkMasterIP	 OBJECT-TYPE
    SYNTAX		IpAddress
    MAX-ACCESS  read-write
    STATUS      current
    DESCRIPTION
         "This parameter is specific to unicast transport and represents the IP address of
          the unicast PTP (Precision Time Protocol) master clock."
    ::= { rcPTP1588BClkEntry 12 }

rcPTP1588BClkBackUpIP	 OBJECT-TYPE
    SYNTAX		IpAddress
    MAX-ACCESS  read-write
    STATUS      current
    DESCRIPTION
         "This parameter is specific to unicast transport and represents the IP address of the
          unicast backup PTP (Precision Time Protocol) master clock."
    ::= { rcPTP1588BClkEntry 13 }

rcPTP1588BClkGMIdentity OBJECT-TYPE
    SYNTAX	Integer32
    MAX-ACCESS	read-write
    STATUS	current
    DESCRIPTION
      "Grandmaster Identity received in GRANDMASTER_ID TLV."
    ::= { rcPTP1588BClkEntry 14 }

rcPTP1588BClkVlanId OBJECT-TYPE
    SYNTAX	Integer32(-2..4094)
    MAX-ACCESS 	read-write
    STATUS	current
    DESCRIPTION
      "Indicates VLAN ID in use.
		-2 = PVID
		-1 = Priority tagged
		0  = Untagged
		1 to 4094 = VID set"
    ::= { rcPTP1588BClkEntry 15 }

rcPTP1588BClkPriority OBJECT-TYPE
    SYNTAX	Unsigned32(0..7)
    MAX-ACCESS 	read-write
    STATUS	current
    DESCRIPTION
      "Indicates VLAN tag Priority in use."
    ::= { rcPTP1588BClkEntry 16 }
-- ---------------------------------------------------------------------- --
--  Conformance Groups
-- ---------------------------------------------------------------------- --
rcPTP1588BaseGroup OBJECT-GROUP
	OBJECTS		{
					rcPTP1588ClkType,
					rcPTP1588EthPorts,
					rcPTP1588StartUpWait,
					rcPTP1588NetClass,
					rcPTP1588SlaveEthPort,
					rcPTP1588SlaveDomain,
					rcPTP1588SlaveAutoReg,
					rcPTP1588SlaveMasteIP,
					rcPTP1588SlaveBackUpIP,
					rcPTP1588ServoStatus,
					rcPTP1588SlaveFeqAdj,
					rcPTP1588E2EDelay,
					rcPTP1588GlobalEnable,
					rcPTP1588GlobalP2PRequestInterval,
					rcPTP1588GlobalE2ERequestInterval,
					rcPTP1588Global1Step,
					rcPTP1588ClkAnnounceInt,
					rcPTP1588ClkAnnounceRcTout,
					rcPTP1588ClkSyncInt,
					rcPTP1588ClkDelayMech,
					rcPTP1588ClkProfileId,
					rcPTP1588ClkDomainNumber,
					rcPTP1588ClkNetProtocol,
					rcPTP1588ClkVlanId,
					rcPTP1588ClkPriority,
					rcPTP1588ClkAccuracy
				}
	STATUS     current
    DESCRIPTION
        "A group of objects providing ability to monitor and configure PTP1588 clocks status."
    ::= { rcPTP1588Groups 1 }

rcPTP1588BCTablesGroup OBJECT-GROUP
	OBJECTS		{
					rcPTP1588BClkPorts,
					rcPTP1588BClkGroupName,
					rcPTP1588BClkProfileId,
					rcPTP1588BClkDomainNumber,
					rcPTP1588BClkNetProtocol,
					rcPTP1588BClkPathDelayMech,
					rcPTP1588BClkPTPPortType,
					rcPTP1588BClkSyncInt,
					rcPTP1588BClkAnnounceInt,
					rcPTP1588BClkAnnounceRcTout,
					rcPTP1588BClkAutoReg,
					rcPTP1588BClkMasterIP,
					rcPTP1588BClkBackUpIP,
					rcPTP1588BClkGMIdentity,
					rcPTP1588BClkVlanId,
					rcPTP1588BClkPriority
				}
	STATUS     current
    DESCRIPTION
        "A group of objects providing ability to monitor and configure PTP1588 Boundary clocks parameters."
    ::= { rcPTP1588Groups 2 }
END
