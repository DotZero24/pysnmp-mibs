Wellfleet-DOT1QTAG-CONFIG-MIB DEFINITIONS ::= BEGIN

-- First created by Rahul Mehta 07/25/97 for 802.1q VLAN tagging in the router.

    IMPORTS

	OBJECT-TYPE
	  FROM RFC-1212
	DisplayString
	  FROM RFC1213-MIB
	wfDot1qTagConfigGroup
	  FROM Wellfleet-COMMON-MIB;

wfDot1qTagConfig OBJECT IDENTIFIER ::= { wfDot1qTagConfigGroup 1 }

wfDot1qTagConfigTable OBJECT-TYPE
	SYNTAX  SEQUENCE OF WfDot1qTagConfigEntry
	ACCESS  not-accessible
	STATUS  mandatory
	DESCRIPTION
		"A table that contains the global read-write
		802.1q VLAN tagging attributes on a per circuit
		basis. Here circuit number is the Local VLAN Id."
	::= { wfDot1qTagConfig 1 }

wfDot1qTagConfigEntry OBJECT-TYPE
	SYNTAX  WfDot1qTagConfigEntry
	ACCESS  not-accessible
	STATUS  mandatory
	DESCRIPTION
		"A list of information maintained for each circuit."
	INDEX   {wfDot1qTagCfgPhysicalPortId,
		     wfDot1qTagCfgLocalVlanId }
	::= { wfDot1qTagConfigTable 1 }

WfDot1qTagConfigEntry ::= SEQUENCE {
	wfDot1qTagCfgDelete
		INTEGER,
	wfDot1qTagCfgDisable
		INTEGER,
	wfDot1qTagCfgVlanName
		DisplayString,
	wfDot1qTagCfgLocalVlanId
		 INTEGER,
	wfDot1qTagCfgGlobalVlanId
		INTEGER,
	wfDot1qTagCfgVirtualPortType
		INTEGER,
	wfDot1qTagCfgPhysicalPortId
		INTEGER,
	wfDot1qTagCfgProtocolType
		INTEGER
}

wfDot1qTagCfgDelete OBJECT-TYPE
	SYNTAX  INTEGER {
			create(1),
			delete(2)
	}
	ACCESS   read-write
	STATUS   mandatory
	DESCRIPTION
		"Creation and deletion flag for this record. When set to 2
		it will cause this entry to be deleted from the MIB"
	DEFVAL   { create }
	::= { wfDot1qTagConfigEntry 1 }

wfDot1qTagCfgDisable OBJECT-TYPE
	SYNTAX  INTEGER {
			enabled(1),
			disabled(2)
	}
	ACCESS  read-write
	STATUS  mandatory
	DESCRIPTION
		"Enable/Disable parameter. A disabled interface will
		never be selected as the active interface for a circuit."
	DEFVAL  { enabled }
	::= { wfDot1qTagConfigEntry 2 }

wfDot1qTagCfgVlanName OBJECT-TYPE
	SYNTAX  DisplayString
	ACCESS  read-write
	STATUS  mandatory
	DESCRIPTION
		"The name for the VLAN circuit.
		NOTE: For SM purposes only. This a dummy cfg. parameter."
	::= { wfDot1qTagConfigEntry 3 }

wfDot1qTagCfgLocalVlanId OBJECT-TYPE
	SYNTAX  INTEGER(1..1023)
	ACCESS  read-only
	STATUS  mandatory
	DESCRIPTION
		"The index of the circuit on which Dot1qTag related
		attributes are set. Uniquely identifies the group
		within a Box. Here it is same as the Circuit Number."
	::= { wfDot1qTagConfigEntry 4 }

wfDot1qTagCfgGlobalVlanId OBJECT-TYPE
	SYNTAX  INTEGER(1..4095)
	ACCESS  read-write
	STATUS  mandatory
	DESCRIPTION
		"Uniquely identifies the group within the enterprise.
		 Global VLAN ID is a 12 bit unique number."
	::= { wfDot1qTagConfigEntry 5 }

wfDot1qTagCfgVirtualPortType OBJECT-TYPE
	SYNTAX  INTEGER {
			tagged(1)
	}
	ACCESS  read-write
	STATUS  mandatory
	DESCRIPTION
		"The Virtual Port Type."
	DEFVAL  { tagged }
	::= { wfDot1qTagConfigEntry 6 }

wfDot1qTagCfgPhysicalPortId OBJECT-TYPE
	SYNTAX  INTEGER
	ACCESS  read-only
	STATUS  mandatory
	DESCRIPTION
		"The physical port id which is same as the line number."
	::= { wfDot1qTagConfigEntry 7 }

wfDot1qTagCfgProtocolType OBJECT-TYPE
	SYNTAX  INTEGER(1514..65535)
	ACCESS  read-write
	STATUS  mandatory
	DESCRIPTION
		"The IEEE802.1q protocol type value.
		NOTE: With the initial release of the software, the
		Tag Protocol Identifier (TPID) field in 802.1 tag will
		contain Bay Networks' propietary value of 8100 (Hex).
		This value will be specified by the IEEE in the
		forthcoming revisions of the 802.1Q standard, Bay
		Networks will support the standard value."
	DEFVAL	{ 33024 }
	::= { wfDot1qTagConfigEntry 8 }

END  -- Wellfleet-DOT1QTAG-CONFIG-MIB
