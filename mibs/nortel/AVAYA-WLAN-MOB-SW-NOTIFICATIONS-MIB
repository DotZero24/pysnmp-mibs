AVAYA-WLAN-MOB-SW-NOTIFICATIONS-MIB DEFINITIONS ::= BEGIN

IMPORTS
    MODULE-IDENTITY, OBJECT-TYPE, NOTIFICATION-TYPE,
    Unsigned32, Integer32, Gauge32
        FROM SNMPv2-SMI
    MacAddress
        FROM SNMPv2-TC
    TEXTUAL-CONVENTION
        FROM SNMPv2-TC
    SnmpAdminString
        FROM SNMP-FRAMEWORK-MIB
    InetAddressType, InetAddress
        FROM INET-ADDRESS-MIB
    AvWlanMobVlanRole, AvWlanMobVlanState,
    AvWlanSwitchNotifAuxLimitsMap
        FROM AVAYA-WLAN-TC-MIB
    avayaWlanMibs
        FROM SYNOPTICS-ROOT-MIB;

avayaWlanMobSwitchNotificationsMib MODULE-IDENTITY
    LAST-UPDATED "201112150000Z" -- 15 Dec 2011
    ORGANIZATION "Avaya, Inc"
    CONTACT-INFO "Avaya, Inc"
    DESCRIPTION
        "AVAYA WLAN Mobility Switch Notifications MIB

        Copyright 2011 Avaya, Inc.
        All rights reserved.
        This Avaya SNMP Management Information Base Specification
        (Specification) embodies Avaya's confidential and proprietary
        intellectual property.  Avaya retains all title and ownership
        in the Specification, including any revisions.

        This Specification is supplied 'AS IS,' and Avaya makes no warranty,
        either express or implied, as to the use, operation, condition, or
        performance of the Specification."

    REVISION "201112150000Z" -- 15 Dec 2011
    DESCRIPTION  "v1:  Initial version."

    ::= { avayaWlanMibs 19 }

avWlanMobSwNotifications
    OBJECT IDENTIFIER ::= { avayaWlanMobSwitchNotificationsMib 0 }
avWlanMobSwNotificationObjects
    OBJECT IDENTIFIER ::= { avayaWlanMobSwitchNotificationsMib 1 }

-- ============================================================================
-- avWlanMobSwNotificationAuxObjects
-- ============================================================================

avWlanMobSwNotificationAuxObjects
    OBJECT IDENTIFIER ::= { avWlanMobSwNotificationObjects 1 }

avWlanNotifAuxMobilityControllerInetAddressType  OBJECT-TYPE
    SYNTAX       InetAddressType
    MAX-ACCESS   accessible-for-notify
    STATUS       current
    DESCRIPTION
        "The type of address contained in a corresponding instance of
         avWlanNotifAuxMobilityControllerInetAddress."
    ::= { avWlanMobSwNotificationAuxObjects 1 }

avWlanNotifAuxMobilityControllerInetAddress  OBJECT-TYPE
    SYNTAX       InetAddress
    MAX-ACCESS   accessible-for-notify
    STATUS       current
    DESCRIPTION
        "This object identifies a controller network address."
    ::= { avWlanMobSwNotificationAuxObjects 2 }

avWlanNotifAuxNumberOfVlanEntries OBJECT-TYPE
    SYNTAX       Unsigned32
    MAX-ACCESS   accessible-for-notify
    STATUS       current
    DESCRIPTION
        "This object identifies the number of Mobility VLAN entries
         that were successfully downloaded by the WSP."
    ::= { avWlanMobSwNotificationAuxObjects 3 }

avWlanNotifAuxMSTDownloadEntries  OBJECT-TYPE
    SYNTAX       Unsigned32
    MAX-ACCESS   accessible-for-notify
    STATUS       current
    DESCRIPTION
        "This object identifies the number of Mobility switches
         that were successfully downloaded by the WSP."
    ::= { avWlanMobSwNotificationAuxObjects 4 }

avWlanNotifAuxPeerDeviceInetAddressType  OBJECT-TYPE
    SYNTAX       InetAddressType
    MAX-ACCESS   accessible-for-notify
    STATUS       current
    DESCRIPTION
        "The type of address contained in a corresponding instance of
         avWlanNotifAuxPeerDeviceInetAddress."
    ::= { avWlanMobSwNotificationAuxObjects 5 }

avWlanNotifAuxPeerDeviceInetAddress  OBJECT-TYPE
    SYNTAX       InetAddress
    MAX-ACCESS   accessible-for-notify
    STATUS       current
    DESCRIPTION
        "This object identifies the IP address of any peer device connected
        to the WSP."
    ::= { avWlanMobSwNotificationAuxObjects 6 }

avWlanNotifAuxPeerDeviceAddress  OBJECT-TYPE
    SYNTAX       MacAddress
    MAX-ACCESS   accessible-for-notify
    STATUS       current
    DESCRIPTION
        "This object specifies the MAC address of the peer device."
    ::= { avWlanMobSwNotificationAuxObjects 7 }

avWlanNotifAuxPeerDeviceType OBJECT-TYPE
    SYNTAX       INTEGER {
                     accessPoint(1),
                     mobilitySwitch(2)
                 }
    MAX-ACCESS   accessible-for-notify
    STATUS       current
    DESCRIPTION
        "This object specifies the peer device type."
    ::= { avWlanMobSwNotificationAuxObjects 8 }

avWlanNotifAuxConnectionFailureReason  OBJECT-TYPE
    SYNTAX       INTEGER {
                     kaLoss(1),
                     controlPlane(2),
                     peerReset(3)
                 }
    MAX-ACCESS   accessible-for-notify
    STATUS       current
    DESCRIPTION
        "This object indicate the reason for connection failure with
        the peer device. The peer device is either a Access Point or
        Wireless Switching Point. The supported values are:

           kaLoss       - loss of keep alive packets between the peers.
           controlPlane - connection closed by the controller
           peerReset    - peer device closed the connection "
    ::= { avWlanMobSwNotificationAuxObjects 9 }

avWlanNotifAuxMobilityVlanName OBJECT-TYPE
    SYNTAX       SnmpAdminString (SIZE (1..32))
    MAX-ACCESS   accessible-for-notify
    STATUS       current
    DESCRIPTION
        "This object specifies the name of the mobility VLAN."
    ::= { avWlanMobSwNotificationAuxObjects 10 }

avWlanNotifAuxVlanServerInetAddressType OBJECT-TYPE
    SYNTAX       InetAddressType
    MAX-ACCESS   accessible-for-notify
    STATUS       current
    DESCRIPTION
        "The type of address contained in a corresponding instance of
        avWlanNotifAuxVlanServerInetAddress."
    ::= { avWlanMobSwNotificationAuxObjects 11 }

avWlanNotifAuxVlanServerInetAddress OBJECT-TYPE
    SYNTAX       InetAddress
    MAX-ACCESS   accessible-for-notify
    STATUS       current
    DESCRIPTION
        "This object identifies the IP address of VLAN server."
    ::= { avWlanMobSwNotificationAuxObjects 12 }

avWlanNotifAuxVlanServerAddress  OBJECT-TYPE
    SYNTAX       MacAddress
    MAX-ACCESS   accessible-for-notify
    STATUS       current
    DESCRIPTION
        "This object specifies the MAC address of the VLAN server."
    ::= { avWlanMobSwNotificationAuxObjects 13 }

avWlanNotifAuxMobilityVlanSelfGenerationNumber OBJECT-TYPE
    SYNTAX       Unsigned32
    MAX-ACCESS   accessible-for-notify
    STATUS       current
    DESCRIPTION
        "This object identifies the self generation number associated with
        the mobility VLAN in the WSP device. This number will be
        received by the WSP during a MVT download."
    ::= { avWlanMobSwNotificationAuxObjects 14 }

avWlanNotifAuxMobilityVlanPeerGenerationNumber OBJECT-TYPE
    SYNTAX       Unsigned32
    MAX-ACCESS   accessible-for-notify
    STATUS       current
    DESCRIPTION
        "This object identifies the peer generation number for each
        mobility VLAN received from the WSP (during VLAN advertisements)."
    ::= { avWlanMobSwNotificationAuxObjects 15 }

avWlanNotifAuxOldVlanRole OBJECT-TYPE
    SYNTAX       AvWlanMobVlanRole
    MAX-ACCESS   accessible-for-notify
    STATUS       current
    DESCRIPTION
        "This object specifies the old role of the mobility VLAN."
    ::= { avWlanMobSwNotificationAuxObjects 16 }

avWlanNotifAuxNewVlanRole OBJECT-TYPE
    SYNTAX       AvWlanMobVlanRole
    MAX-ACCESS   accessible-for-notify
    STATUS       current
    DESCRIPTION
        "This object specifies the new role of the mobility VLAN."
    ::= { avWlanMobSwNotificationAuxObjects 17 }

avWlanNotifAuxRoleChangeReason OBJECT-TYPE
    SYNTAX       INTEGER {
                     administrator(1),
                     clientRoam(2)
                 }
    MAX-ACCESS   accessible-for-notify
    STATUS       current
    DESCRIPTION
        "This object specifies the reason for change in mobility VLAN role
        by this WSP. The following values are supported:
           administrator - role change due to admin configuration
           clientRoam    - role change due to client roaming.
        "
    ::= { avWlanMobSwNotificationAuxObjects 18 }

avWlanNotifAuxOldState OBJECT-TYPE
    SYNTAX       AvWlanMobVlanState
    MAX-ACCESS   accessible-for-notify
    STATUS       current
    DESCRIPTION
        "This object specifies the old state of the mobility vlan MAP."
    ::= { avWlanMobSwNotificationAuxObjects 19 }

avWlanNotifAuxNewState OBJECT-TYPE
    SYNTAX       AvWlanMobVlanState
    MAX-ACCESS   accessible-for-notify
    STATUS       current
    DESCRIPTION
        "This object specifies the new state of the mobility vlan MAP."
    ::= { avWlanMobSwNotificationAuxObjects 20 }

avWlanNotifAuxStateChangeReason OBJECT-TYPE
    SYNTAX       INTEGER {
                     mobVlanDeleted(1),
                     mobVlanCreated(2),
                     localVlanDeleted(3)
                 }
    MAX-ACCESS   accessible-for-notify
    STATUS       current
    DESCRIPTION
        "This object specifies the reason for change in mobility VLAN
        state in this WSP device. The following values are supported:
           mobVlanDeleted    - state change due to deletion of mobility VLAN
           mobVlanCreated    - state change due to creation of mobility VLAN
           localVlanDeleted  - state change due to deletion of local VLAN
        "
    ::= { avWlanMobSwNotificationAuxObjects 21 }

avWlanNotifAuxVlanState OBJECT-TYPE
    SYNTAX       AvWlanMobVlanState
    MAX-ACCESS   accessible-for-notify
    STATUS       current
    DESCRIPTION
        "This object specifies the current state of the mobility VLAN."
    ::= { avWlanMobSwNotificationAuxObjects 22 }

avWlanNotifAuxRemoveReason OBJECT-TYPE
    SYNTAX       INTEGER {
                     administrator(1),
                     lvidDeletion(2)
                 }
    MAX-ACCESS   accessible-for-notify
    STATUS       current
    DESCRIPTION
        "This object specifies the reason for removal of mobility VLAN
        in this WSP. The following values are supported:
           administrator - removed due to admin configuration
           clientRoam    - removed due to deletion of lvid.
        "
    ::= { avWlanMobSwNotificationAuxObjects 23 }

avWlanNotifAuxControlFrameType OBJECT-TYPE
    SYNTAX       INTEGER {
                     igmpReport(1),
                     igmpLeave(2)
                 }
    MAX-ACCESS   accessible-for-notify
    STATUS       current
    DESCRIPTION
        "This object specifies the IGMP control frame type."
    ::= { avWlanMobSwNotificationAuxObjects 24 }

avWlanNotifAuxInetAddressType OBJECT-TYPE
    SYNTAX       InetAddressType
    MAX-ACCESS   accessible-for-notify
    STATUS       current
    DESCRIPTION
        "The type of address contained in a corresponding instance of
        avWlanNotifAuxInetAddress."
    ::= { avWlanMobSwNotificationAuxObjects 25 }

avWlanNotifAuxInetAddress  OBJECT-TYPE
    SYNTAX       InetAddress
    MAX-ACCESS   accessible-for-notify
    STATUS       current
    DESCRIPTION
        "This object identifies the source IP in the IGMP control frame."
    ::= { avWlanMobSwNotificationAuxObjects 26 }

avWlanSwitchNotifAuxAuxLimitsReached OBJECT-TYPE
    SYNTAX       AvWlanSwitchNotifAuxLimitsMap
    MAX-ACCESS   accessible-for-notify
    STATUS       current
    DESCRIPTION
        "This objects is included in the avWlanSwitchLimitsReached notification to
        indicate which limits have been reached."
    ::= { avWlanMobSwNotificationAuxObjects 27 }

-- ============================================================================
-- avWlanSwitchNotifications
-- ============================================================================

avWlanSwitchNotifications
    OBJECT IDENTIFIER ::= { avWlanMobSwNotifications 1 }

avWlanSwitchMCPConnectionEstablished NOTIFICATION-TYPE
    OBJECTS { avWlanNotifAuxMobilityControllerInetAddressType,
              avWlanNotifAuxMobilityControllerInetAddress}
    STATUS       current
    DESCRIPTION
        "A avWlanSwitchMCPConnectionEstablished trap signifies that the SNMP entity,
        acting in an agent role,  MCP client successfully established
        connection with the MCP server in Wireless Controller.
        The Trap is Enabled by default."
    ::= { avWlanSwitchNotifications 1 }

avWlanSwitchMCPLostConnection NOTIFICATION-TYPE
    OBJECTS { avWlanNotifAuxMobilityControllerInetAddressType,
              avWlanNotifAuxMobilityControllerInetAddress}
    STATUS       current
    DESCRIPTION
        "A avWlanSwitchMCPLostConnection trap signifies that the SNMP entity,
        acting in an agent role, MCP client lost connection with the MCP server
        in Wireless Controller.
        The Trap is Enabled by default."
    ::= { avWlanSwitchNotifications 2 }

avWlanSwitchMVTDownload NOTIFICATION-TYPE
    OBJECTS { avWlanNotifAuxMobilityControllerInetAddressType,
              avWlanNotifAuxMobilityControllerInetAddress,
              avWlanNotifAuxNumberOfVlanEntries }
    STATUS       current
    DESCRIPTION
        "A avWlanSwitchMVTDownload trap signifies that the SNMP entity,
         acting in an agent role, has received Mobility Vlan Table download
         from the Mobility controller. Mobility Switch receives MVT when it
         registers with the Mobility Controller. Controller address and number
         of entries in the table is passed as parameter.
         The Trap is Enabled by default."
    ::= { avWlanSwitchNotifications 3 }

avWlanSwitchMSTDownload NOTIFICATION-TYPE
    OBJECTS { avWlanNotifAuxMobilityControllerInetAddressType,
              avWlanNotifAuxMobilityControllerInetAddress,
              avWlanNotifAuxMSTDownloadEntries }
    STATUS       current
    DESCRIPTION
        "A avWlanSwitchMSTDownload trap signifies that the SNMP entity,
         acting in an agent role, has received Mobility Switch Table download
         from the Mobility Controller. Mobility Switch receives MST when it
         registers with the Mobility controller. Controller address and number
         of entries in the table is passed as parameter.
         The Trap is Enabled by default."
    ::= { avWlanSwitchNotifications 4 }

avWlanSwitchPeerDeviceConnectionEstablished NOTIFICATION-TYPE
    OBJECTS { avWlanNotifAuxPeerDeviceInetAddressType,
              avWlanNotifAuxPeerDeviceInetAddress,
              avWlanNotifAuxPeerDeviceAddress,
              avWlanNotifAuxPeerDeviceType }
    STATUS       current
    DESCRIPTION
        "A avWlanSwitchPeerDeviceConnectionEstablished trap signifies that the SNMP entity,
         acting in an agent role, has established connection to the peer device.
         Peer switch IP, MAC address and device type is passed as parameter.
         The Trap is Enabled by default."
    ::= { avWlanSwitchNotifications 5 }

avWlanSwitchPeerDeviceLostConnection NOTIFICATION-TYPE
    OBJECTS { avWlanNotifAuxPeerDeviceInetAddressType,
              avWlanNotifAuxPeerDeviceInetAddress,
              avWlanNotifAuxPeerDeviceAddress,
              avWlanNotifAuxPeerDeviceType,
              avWlanNotifAuxConnectionFailureReason }
    STATUS       current
    DESCRIPTION
        "A avWlanSwitchPeerDeviceLostConnection trap signifies that the SNMP entity,
         acting in an agent role, has lost connection to the peer device.
         Peer switch IP, MAC, device type and failure reason are  passed as parameter.
         The Trap is Enabled by default."
    ::= { avWlanSwitchNotifications 6 }

avWlanSwitchVlanServerElected NOTIFICATION-TYPE
    OBJECTS { avWlanNotifAuxMobilityVlanName,
              avWlanNotifAuxVlanServerInetAddressType,
              avWlanNotifAuxVlanServerInetAddress,
              avWlanNotifAuxVlanServerAddress }
    STATUS       current
    DESCRIPTION
        "A avWlanSwitchVlanServerElected trap signifies that the SNMP entity,
         acting in an agent role, has elected vlan server for a mobility vlan.
         Mobility vlan name, vlan server IP and MAC address is passed as parameter.
         The Trap is Disabled by default."
    ::= { avWlanSwitchNotifications 7 }

avWlanSwitchLostConnectionToVlanServer NOTIFICATION-TYPE
    OBJECTS { avWlanNotifAuxMobilityVlanName,
              avWlanNotifAuxVlanServerInetAddressType,
              avWlanNotifAuxVlanServerInetAddress,
              avWlanNotifAuxVlanServerAddress }
    STATUS       current
    DESCRIPTION
        "A avWlanSwitchLostConnectionToVlanServer trap signifies that the SNMP entity,
         acting in an agent role, has lost connection to vlan server and there are no
         other alternative vlan servers for the mobility vlan.
         Mobility vlan name, vlan server IP and MAC address is passed as parameter.
         The trap is Enabled by default."
    ::= { avWlanSwitchNotifications 8 }

avWlanSwitchVlanGenNumberMismatch NOTIFICATION-TYPE
    OBJECTS { avWlanNotifAuxMobilityVlanName,
              avWlanNotifAuxMobilityVlanSelfGenerationNumber,
              avWlanNotifAuxMobilityVlanPeerGenerationNumber }
    STATUS        current
    DESCRIPTION
        "A avWlanSwitchVlanGenNumberMismatch trap signifies that the SNMP entity,
         acting in an agent role, has detected change in the generation number.
         Mobility switches advertise the generation numbers for the mapped
         mobility vlans in the mobility domain. Generation numbers are used to
         detect stale mobility vlans. The mobility vlan name, mobility switch
         generation number and the peer switch generation number is passed as parameter.
         This is enabled by default."
    ::= { avWlanSwitchNotifications 9 }


avWlanSwitchVlanRoleChanged NOTIFICATION-TYPE
    OBJECTS { avWlanNotifAuxMobilityVlanName,
              avWlanNotifAuxOldVlanRole,
              avWlanNotifAuxNewVlanRole,
              avWlanNotifAuxRoleChangeReason }
    STATUS    current
    DESCRIPTION
        "A avWlanSwitchVlanRoleChanged trap signifies that the SNMP entity,
         acting in an agent role, has changed the role of the mobility vlan.
         Mobility vlan name, old and new role, reason for the role change
         is passed as parameter.
         The trap is Disabled by default."
    ::= { avWlanSwitchNotifications 10 }

avWlanSwitchVlanMapStateChanged NOTIFICATION-TYPE
    OBJECTS { avWlanNotifAuxMobilityVlanName,
              avWlanNotifAuxOldState,
              avWlanNotifAuxNewState,
              avWlanNotifAuxStateChangeReason }
    STATUS       current
    DESCRIPTION
        "A avWlanSwitchVlanMapStateChanged trap signifies that the SNMP entity,
         acting in an agent role, has changed the state of the mobility vlan map.
         A vlan map is the association between mobility vlan name and the local
         static vlan.  The state is Active as long as Mobility vlan name and the
         local static vlan are active.
         Deletion of mobility vlan or the local static vlan results in a
         InActive state for a vlan map. Vlan map will become Active if the
         mobility vlan is created before the next MVT download. Mobility vlan name,
         old, new state and the reason is passed as parameter.
         The trap is Disabled by default."
    ::= { avWlanSwitchNotifications 11 }

avWlanSwitchVlanMapRemoved NOTIFICATION-TYPE
    OBJECTS { avWlanNotifAuxMobilityVlanName,
              avWlanNotifAuxVlanState,
              avWlanNotifAuxRemoveReason }
    STATUS       current
    DESCRIPTION
        "A avWlanSwitchVlanMapRemoved trap signifies that the SNMP entity,
        acting in an agent role, has deleted the mobility vlan map.
        InActive maps are deleted when the mobility vlan is not present in
        the MVT download. Active maps are deleted either from the config or
        when the lvid to which mobility vlan is mapped is deleted. Mobility
        vlan name, vlan state and reason for removal is passed as parameter.
        The trap is Enabled by default."
    ::= { avWlanSwitchNotifications 12 }

avWlanSwitchVlanTrackAffected NOTIFICATION-TYPE
    OBJECTS { avWlanNotifAuxMobilityVlanName }
    STATUS       current
    DESCRIPTION
        "A avWlanSwitchVlanTrackAffected trap signifies that the SNMP entity,
         acting in an agent role, has detected a mobility vlan in server role has no ports
         active in its track list. Mobility vlan name is passed as parameter.
         The trap is Disabled by default."
    ::= { avWlanSwitchNotifications 13 }

avWlanSwitchIgmpSnoopingEnabled NOTIFICATION-TYPE
    OBJECTS { avWlanNotifAuxMobilityVlanName }
    STATUS       current
    DESCRIPTION
        "A avWlanSwitchIgmpSnoopingEnabled trap signifies that the SNMP entity,
         acting in an agent role, has successfully enabled IGMP snooping on a mobility vlan.
         local vlan identifier which is mapped to mobility vlan is passed as parameter.
         The trap is Disabled by default."
    ::= { avWlanSwitchNotifications 14 }

avWlanSwitchIgmpSnoopingDisabled NOTIFICATION-TYPE
    OBJECTS { avWlanNotifAuxMobilityVlanName }
    STATUS       current
    DESCRIPTION
        "A avWlanSwitchIgmpSnoopingDisabled trap signifies that the SNMP entity,
        acting in an agent role, has successfully disabled IGMP snooping
        on a mobility vlan. Mobility vlan name is passed as parameter. The trap is
	Disabled by default."
    ::= { avWlanSwitchNotifications 15 }

avWlanSwitchIgmpControlFrameReceived NOTIFICATION-TYPE
    OBJECTS { avWlanNotifAuxMobilityVlanName,
              avWlanNotifAuxControlFrameType,
              avWlanNotifAuxPeerDeviceType,
              avWlanNotifAuxInetAddressType,
              avWlanNotifAuxInetAddress }
    STATUS       current
    DESCRIPTION
        "A avWlanSwitchIgmpControlFrameReceived trap signifies that the SNMP entity,
         acting in an agent role, has snooped IGMP control frame on a mobility vlan.
         Mobility vlan name, Frame Type, device type and IGMP source IP
         are passed as parameters. The trap is Disabled by default."
    ::= { avWlanSwitchNotifications 16 }

avWlanSwitchLimitsReached NOTIFICATION-TYPE
    OBJECTS { avWlanSwitchNotifAuxAuxLimitsReached }
    STATUS       current
    DESCRIPTION
        "This trap signifies that the SNMP entity, acting in an agent role,
        has detected some switch limits being reached.
        The bit mask avWlanSwitchNotifAuxLimitsReached is send in the trap
        to indicate the parameter for which limits are reached.
        This trap is enabled by default."
    ::= { avWlanSwitchNotifications 17 }

END
