Wellfleet-CSMACD-MIB DEFINITIONS ::= BEGIN

-- Created by mdl2asn version 3.1
-- Creation date: Wed Aug 30 16:39:16 EDT 1995


    IMPORTS

      Counter, Gauge, TimeTicks
        FROM RFC1155-SMI
      OBJECT-TYPE
        FROM RFC-1212
      wfLine, wfCSMACDAutoNegGroup
        FROM Wellfleet-COMMON-MIB;


    wfCSMACDTable OBJECT-TYPE
        SYNTAX	SEQUENCE OF WfCSMACDEntry
        ACCESS	not-accessible
        STATUS	mandatory
        DESCRIPTION
                "CSMA/CD line record"
        ::= { wfLine 1 }

    wfCSMACDEntry OBJECT-TYPE
        SYNTAX	WfCSMACDEntry
        ACCESS	not-accessible
        STATUS	mandatory
        DESCRIPTION
                "An entry in the csmacd table"
        INDEX	{ wfCSMACDSlot,
    		  wfCSMACDConnector }
        ::= { wfCSMACDTable 1 }

    WfCSMACDEntry ::= SEQUENCE {
    	    wfCSMACDDelete
    		INTEGER,
    	    wfCSMACDEnable
    		INTEGER,
    	    wfCSMACDState
    		INTEGER,
    	    wfCSMACDSlot
    		INTEGER,
    	    wfCSMACDConnector
    		INTEGER,
    	    wfCSMACDCct
    		INTEGER,
    	    wfCSMACDBofl
    		INTEGER,
    	    wfCSMACDBoflTmo
    		INTEGER,
    	    wfCSMACDMtu
    		INTEGER,
    	    wfCSMACDMadr
    		OCTET STRING,
    	    wfCSMACDOctetsRxOk
    		Counter,
    	    wfCSMACDFramesRxOk
    		Counter,
    	    wfCSMACDOctetsTxOk
    		Counter,
    	    wfCSMACDFramesTxOk
    		Counter,
    	    wfCSMACDDeferredTx
    		Counter,
    	    wfCSMACDLateCollnTx
    		Counter,
    	    wfCSMACDExcessvCollnTx
    		Counter,
    	    wfCSMACDBablErrorTx
    		Counter,
    	    wfCSMACDBufErrorTx
    		Counter,
    	    wfCSMACDLcarTx
    		Counter,
    	    wfCSMACDUfloTx
    		Counter,
    	    wfCSMACDFcsErrorRx
    		Counter,
    	    wfCSMACDAlignErrorRx
    		Counter,
    	    wfCSMACDLackRescErrorRx
    		Counter,
    	    wfCSMACDTooLongErrorRx
    		Counter,
    	    wfCSMACDOfloRx
    		Counter,
    	    wfCSMACDMerr
    		Counter,
    	    wfCSMACDCerr
    		Counter,
    	    wfCSMACDHardwareFilter
    		INTEGER,
    	    wfCSMACDTxQueueLength
    		INTEGER,
    	    wfCSMACDRxQueueLength
    		INTEGER,
    	    wfCSMACDTxClipFrames
    		Counter,
    	    wfCSMACDRxReplenMisses
    		Counter,
    	    wfCSMACDCfgTxQueueLength
    		INTEGER,
    	    wfCSMACDCfgRxQueueLength
    		INTEGER,
    	    wfCSMACDAlignmentMode
    		INTEGER,
    	    wfCSMACDUnAlignedFrames
    		Counter,
    	    wfCSMACDLineNumber
    		INTEGER,
    	    wfCSMACDLateCollnRx
    		Counter,
    	    wfCSMACDModule
    		INTEGER,
    	    wfCSMACDActualConnector
    		INTEGER,
    	    wfCSMACDLastChange
    		TimeTicks,
    	    wfCSMACDOutQLen
    		Gauge,
    	    wfCSMACDIntProcessings
    		Counter,
    	    wfCSMACDTxProcessings
    		Counter,
    	    wfCSMACDRxProcessings
    		Counter,
    	    wfCSMACDTxCmplProcessings
    		Counter,
    	    wfCSMACDTxQueueReductions
    		Counter,
    	    wfCSMACDSingleCollisionFrames
    		Counter,
    	    wfCSMACDMultipleCollisionFrames
    		Counter,
    	    wfCSMACDInternalMacTxErrors
    		Counter,
    	    wfCSMACDLineCapability
    		INTEGER,
    	    wfCSMACDEtherChipSet
    		OBJECT IDENTIFIER,
    	    wfCSMACDRxSymbolErrors
    		Counter,
    	    wfCSMACDInternalMacRxErrors
    		Counter,
    	    wfCSMACDConfigurableSpeed
    		INTEGER,
    	    wfCSMACDRxFlushes
    		Counter,
    	    wfCSMACDTxDeadlocks
    		Counter,
            wfCSMACDBoflRetries
                INTEGER,
            wfCSMACDBoflTmoDivisor
                INTEGER,
    	    wfCSMACDTurboBoflDebug
    		INTEGER,
    	    wfCSMACDIfIndex
    		INTEGER,
	    wfCSMACDTxFlowControlPauseFrames
		Counter,
	    wfCSMACDRxFlowControlPauseFrames
		Counter,
	    wfCSMACDRxUnsupportedOpcodes
		Counter,
	    wfCSMACDFlowControlEnable
		INTEGER,
	    wfCSMACDTxFlowControlPauseTime
		INTEGER,
	    wfCSMACDTxFlowControlPauseZeroEnable
		INTEGER,
	    wfCSMACDDsqmsLineSpeed
		INTEGER
        }

    wfCSMACDDelete OBJECT-TYPE
        SYNTAX	INTEGER {
    		    create(1),
    		    delete(2)
    		}
        ACCESS	read-write
        STATUS	mandatory
        DESCRIPTION
                "create/delete parameter, dflt = created"
        DEFVAL	{ create }
        ::= { wfCSMACDEntry 1 }

    wfCSMACDEnable OBJECT-TYPE
        SYNTAX	INTEGER {
    		    enable(1),
    		    disable(2)
    		}
        ACCESS	read-write
        STATUS	mandatory
        DESCRIPTION
                "enable/disable parameter, dflt = enabled"
        DEFVAL	{ enable }
        ::= { wfCSMACDEntry 2 }

    wfCSMACDState OBJECT-TYPE
        SYNTAX	INTEGER {
    		    up(1),
    		    down(2),
    		    init(3),
    		    notpresent(4)
    		}
        ACCESS	read-only
        STATUS	mandatory
        DESCRIPTION
                "line driver state variable, Not Present, Init, Down, Up"
        DEFVAL	{ notpresent }
        ::= { wfCSMACDEntry 3 }

    wfCSMACDSlot OBJECT-TYPE
        SYNTAX	INTEGER(1..14)
        ACCESS	read-only
        STATUS	mandatory
        DESCRIPTION
                "instance ID Slot, filled in by driver"
        ::= { wfCSMACDEntry 4 }

    wfCSMACDConnector OBJECT-TYPE
        SYNTAX	INTEGER(1..44)
        ACCESS	read-only
        STATUS	mandatory
        DESCRIPTION
                "instance ID Connector, filled in by driver. For the ASN
                this attribute is an encoded value and is equal to
                'module'*10 + 'connector'. Where 'module' is defined in
                attribute 42 and 'connector' is defined in attribute 43
                of this table. For non-ASN platforms this attribute is
                the physical connector number on the slot."
        ::= { wfCSMACDEntry 5 }

    wfCSMACDCct OBJECT-TYPE
        SYNTAX	INTEGER(1..1023)
        ACCESS	read-write
        STATUS	mandatory
        DESCRIPTION
                "cct number for this line instance"
        ::= { wfCSMACDEntry 6 }

    wfCSMACDBofl OBJECT-TYPE
        SYNTAX	INTEGER {
    		    enable(1),
    		    disable(2)
    		}
        ACCESS	read-write
        STATUS	mandatory
        DESCRIPTION
                "bofl parameter, dflt = enabled"
        DEFVAL	{ enable }
        ::= { wfCSMACDEntry 7 }

    wfCSMACDBoflTmo OBJECT-TYPE
        SYNTAX	INTEGER(0..60)
        ACCESS	read-write
        STATUS	mandatory
        DESCRIPTION
                "bofl parameter, dflt = 5. A value of zero has a special meaning.
                 When bofl tmo is zero, the line is killed as soon as the link down
		 down condition is determined."
        DEFVAL	{ 5 }
        ::= { wfCSMACDEntry 8 }

    wfCSMACDMtu OBJECT-TYPE
        SYNTAX	INTEGER {
    		    default(1518)
    		}
        ACCESS	read-only
        STATUS	mandatory
        DESCRIPTION
                "mtu parameter, fixed"
        DEFVAL	{ default }
        ::= { wfCSMACDEntry 9 }

    wfCSMACDMadr OBJECT-TYPE
        SYNTAX	OCTET STRING
        ACCESS	read-only
        STATUS	mandatory
        DESCRIPTION
                "line MAC address, fixed - line driver fills in"
        ::= { wfCSMACDEntry 10 }

    wfCSMACDOctetsRxOk OBJECT-TYPE
        SYNTAX	Counter
        ACCESS	read-only
        STATUS	mandatory
        DESCRIPTION
                "Number of octets received without error"
        ::= { wfCSMACDEntry 11 }

    wfCSMACDFramesRxOk OBJECT-TYPE
        SYNTAX	Counter
        ACCESS	read-only
        STATUS	mandatory
        DESCRIPTION
                "Number of frames received without error"
        ::= { wfCSMACDEntry 12 }

    wfCSMACDOctetsTxOk OBJECT-TYPE
        SYNTAX	Counter
        ACCESS	read-only
        STATUS	mandatory
        DESCRIPTION
                "Number of octets transmitted without error"
        ::= { wfCSMACDEntry 13 }

    wfCSMACDFramesTxOk OBJECT-TYPE
        SYNTAX	Counter
        ACCESS	read-only
        STATUS	mandatory
        DESCRIPTION
                "Number of frames transmitted without error"
        ::= { wfCSMACDEntry 14 }

    wfCSMACDDeferredTx OBJECT-TYPE
        SYNTAX	Counter
        ACCESS	read-only
        STATUS	mandatory
        DESCRIPTION
                "Number of deferred transmissions"
        ::= { wfCSMACDEntry 15 }

    wfCSMACDLateCollnTx OBJECT-TYPE
        SYNTAX	Counter
        ACCESS	read-only
        STATUS	mandatory
        DESCRIPTION
                "Number of late collisions"
        ::= { wfCSMACDEntry 16 }

    wfCSMACDExcessvCollnTx OBJECT-TYPE
        SYNTAX	Counter
        ACCESS	read-only
        STATUS	mandatory
        DESCRIPTION
                "Number of excessive collisions"
        ::= { wfCSMACDEntry 17 }

    wfCSMACDBablErrorTx OBJECT-TYPE
        SYNTAX	Counter
        ACCESS	read-only
        STATUS	mandatory
        DESCRIPTION
                "Number of frames transmitted larger than the MTU size
                 in wfCSMACDMtu"
        ::= { wfCSMACDEntry 18 }

    wfCSMACDBufErrorTx OBJECT-TYPE
        SYNTAX	Counter
        ACCESS	read-only
        STATUS	mandatory
        DESCRIPTION
                "Number of internal buffer errors"
        ::= { wfCSMACDEntry 19 }

    wfCSMACDLcarTx OBJECT-TYPE
        SYNTAX	Counter
        ACCESS	read-only
        STATUS	mandatory
        DESCRIPTION
                "Number of loss of carrier errors"
        ::= { wfCSMACDEntry 20 }

    wfCSMACDUfloTx OBJECT-TYPE
        SYNTAX	Counter
        ACCESS	read-only
        STATUS	mandatory
        DESCRIPTION
                "Number of transmitter underflow errors"
        ::= { wfCSMACDEntry 21 }

    wfCSMACDFcsErrorRx OBJECT-TYPE
        SYNTAX	Counter
        ACCESS	read-only
        STATUS	mandatory
        DESCRIPTION
                "Number of receiver checksum errors"
        ::= { wfCSMACDEntry 22 }

    wfCSMACDAlignErrorRx OBJECT-TYPE
        SYNTAX	Counter
        ACCESS	read-only
        STATUS	mandatory
        DESCRIPTION
                "Number of receiver alignment errors"
        ::= { wfCSMACDEntry 23 }

    wfCSMACDLackRescErrorRx OBJECT-TYPE
        SYNTAX	Counter
        ACCESS	read-only
        STATUS	mandatory
        DESCRIPTION
                "Number of receiver lack of resource errors"
        ::= { wfCSMACDEntry 24 }

    wfCSMACDTooLongErrorRx OBJECT-TYPE
        SYNTAX	Counter
        ACCESS	read-only
        STATUS	mandatory
        DESCRIPTION
                "Number of frames received exceeding the MTU size
                 in wfCSMACDMtu."
        ::= { wfCSMACDEntry 25 }

    wfCSMACDOfloRx OBJECT-TYPE
        SYNTAX	Counter
        ACCESS	read-only
        STATUS	mandatory
        DESCRIPTION
                "Number of receiver overflow errors"
        ::= { wfCSMACDEntry 26 }

    wfCSMACDMerr OBJECT-TYPE
        SYNTAX	Counter
        ACCESS	read-only
        STATUS	mandatory
        DESCRIPTION
                "Number of internal memory errors"
        ::= { wfCSMACDEntry 27 }

    wfCSMACDCerr OBJECT-TYPE
        SYNTAX	Counter
        ACCESS	read-only
        STATUS	mandatory
        DESCRIPTION
                "Number of collision errors"
        ::= { wfCSMACDEntry 28 }

    wfCSMACDHardwareFilter OBJECT-TYPE
        SYNTAX	INTEGER {
    		    enable(1),
    		    disable(2)
    		}
        ACCESS	read-write
        STATUS	mandatory
        DESCRIPTION
                "Hardware filtering parameter."
        DEFVAL	{ disable }
        ::= { wfCSMACDEntry 29 }

    wfCSMACDTxQueueLength OBJECT-TYPE
        SYNTAX	INTEGER
        ACCESS	read-only
        STATUS	mandatory
        DESCRIPTION
                "Current Transmit Queue Length"
        ::= { wfCSMACDEntry 30 }

    wfCSMACDRxQueueLength OBJECT-TYPE
        SYNTAX	INTEGER
        ACCESS	read-only
        STATUS	mandatory
        DESCRIPTION
                "Current Receive Queue Length"
        ::= { wfCSMACDEntry 31 }

    wfCSMACDTxClipFrames OBJECT-TYPE
        SYNTAX	Counter
        ACCESS	read-only
        STATUS	mandatory
        DESCRIPTION
                "Number of frames clipped in driver's transmit routine due to transmit
                congestion."
        ::= { wfCSMACDEntry 32 }

    wfCSMACDRxReplenMisses OBJECT-TYPE
        SYNTAX	Counter
        ACCESS	read-only
        STATUS	mandatory
        DESCRIPTION
                "Number of packet buffer misses while attempting to replenish driver
                receive ring."
        ::= { wfCSMACDEntry 33 }

    wfCSMACDCfgTxQueueLength OBJECT-TYPE
        SYNTAX	INTEGER(0..255)
        ACCESS	read-write
        STATUS	mandatory
        DESCRIPTION
                "Configured Transmit Queue Length. Values other than zero over-ride
                the router selected values. A value of zero has a special meaning.
                Zero causes router based default values to be used. Values larger
                than the compiled ring size are truncated to the compiled ring
                size."
        ::= { wfCSMACDEntry 34 }

    wfCSMACDCfgRxQueueLength OBJECT-TYPE
        SYNTAX	INTEGER(0..255)
        ACCESS	read-write
        STATUS	mandatory
        DESCRIPTION
                "Configured Receive Queue Length. Values other than zero over-ride
                the router selected values. A value of zero has a special meaning.
                Zero causes router based default values to be used. Values larger
                than the compiled ring size are truncated to the compiled ring
                size."
        ::= { wfCSMACDEntry 35 }

    wfCSMACDAlignmentMode OBJECT-TYPE
        SYNTAX	INTEGER {
    		    all(1),
    		    bytes(2),
    		    disabled(3)
    		}
        ACCESS	read-write
        STATUS	mandatory
        DESCRIPTION
                "Enables special frame re-alignment in the Line Driver. Only needed when
                4 ethernet interfaces are configured on a single slot.  Only needed if
                experiencing transmit underflow errors (wfCSMACDUfloTx).  When this
                attribute is set to DISABLED,  non-optimally aligned frames are transmitted
                as is.  When this attribute is set to ALL (1),  all non-optimally aligned
                frames are re-aligned before transmission.  When this attribute is set to
                ALIGN_OVER_128_BYTES (2), all non-optimally aligned frames over 128 bytes
                in length are re-aligned before transmission and frames up to and including
                128 bytes in length are transmitted as is."
        DEFVAL	{ disabled }
        ::= { wfCSMACDEntry 36 }

    wfCSMACDUnAlignedFrames OBJECT-TYPE
        SYNTAX	Counter
        ACCESS	read-only
        STATUS	mandatory
        DESCRIPTION
                "Number of non-optimally aligned frames queued to the driver for transmit.
                This statistic does not indicate that any frames have been dropped. If
                the ethernet I/O board is not a Quad Ethernet Link Module (QENET) or if it
                is a QENET and none of the four ethernet interfaces are experiencing
                transmit underflow errors (wfCSMACDUfloTx),  then this statistic should be
                ignored.

                If, however, this interface or other interfaces on the QENET are
                experiencing transmit underflow errors,  the underflows are preventable
                by setting the wfCSMACDAlignmentMode attribute to 1.  See explanation of
                that attribute for more information.

                This attribute means that these frames are candidates for re-alignment.
                It does not, by itself, indicate that re-alignment is necessary."
        ::= { wfCSMACDEntry 37 }

    wfCSMACDLineNumber OBJECT-TYPE
        SYNTAX	INTEGER
        ACCESS	read-write
        STATUS	mandatory
        DESCRIPTION
                "Logical line number associated with this driver entity."
        ::= { wfCSMACDEntry 38 }

    wfCSMACDLateCollnRx OBJECT-TYPE
        SYNTAX	Counter
        ACCESS	read-only
        STATUS	mandatory
        DESCRIPTION
                "Number of late collisions - found in QUICC Ethernet Rx Buffer Descriptors"
        ::= { wfCSMACDEntry 39 }

    wfCSMACDModule OBJECT-TYPE
        SYNTAX	INTEGER {
    		    one(1),
    		    two(2),
    		    three(3),
    		    four(4)
    		}
        ACCESS	read-only
        STATUS	mandatory
        DESCRIPTION
                "Module number for ASN platform, filled in by driver. For non-ASN
                platforms this attribute will not be used."
        ::= { wfCSMACDEntry 40 }

    wfCSMACDActualConnector OBJECT-TYPE
        SYNTAX	INTEGER {
    		    one(1),
    		    two(2),
    		    three(3),
    		    four(4)
    		}
        ACCESS	read-only
        STATUS	mandatory
        DESCRIPTION
                "Actual connector number for ASN platform, filled in by
                driver. For non-ASN platforms this attribute will not be used."
        ::= { wfCSMACDEntry 41 }

    wfCSMACDLastChange OBJECT-TYPE
        SYNTAX	TimeTicks
        ACCESS	read-only
        STATUS	mandatory
        DESCRIPTION
                "The value of SysUpTime at the time the interface entered it's current
                operational state (UP state).  SysUpTime is defined as the time (in
                hundredths of a second) since the network management portion of the
                system was last re-initialized.  Usually the time since boot."
        ::= { wfCSMACDEntry 42 }

    wfCSMACDOutQLen OBJECT-TYPE
        SYNTAX	Gauge
        ACCESS	read-only
        STATUS	mandatory
        DESCRIPTION
                "The instantaneous current length of the output packet queue (in packets)."
        ::= { wfCSMACDEntry 43 }

    wfCSMACDIntProcessings OBJECT-TYPE
        SYNTAX	Counter
        ACCESS	read-only
        STATUS	mandatory
        DESCRIPTION
                "counts the number of times the interrupt service routine
                has been called"
        ::= { wfCSMACDEntry 44 }

    wfCSMACDTxProcessings OBJECT-TYPE
        SYNTAX	Counter
        ACCESS	read-only
        STATUS	mandatory
        DESCRIPTION
                "Counts the number of times the transmit routine
                has been called"
        ::= { wfCSMACDEntry 45 }

    wfCSMACDRxProcessings OBJECT-TYPE
        SYNTAX	Counter
        ACCESS	read-only
        STATUS	mandatory
        DESCRIPTION
                "Counts the number of times RINT processing takes place
                in the interrupt service routine."
        ::= { wfCSMACDEntry 46 }

    wfCSMACDTxCmplProcessings OBJECT-TYPE
        SYNTAX	Counter
        ACCESS	read-only
        STATUS	mandatory
        DESCRIPTION
                "Counts the number of times the transmit complete
                processing takes place"
        ::= { wfCSMACDEntry 47 }

    wfCSMACDTxQueueReductions OBJECT-TYPE
        SYNTAX	Counter
        ACCESS	read-only
        STATUS	mandatory
        DESCRIPTION
                "Counts the number of times the transmit queue
                has been shrinked in size due to the number of
                tx clips exceeding the treshold"
        ::= { wfCSMACDEntry 48 }

    wfCSMACDSingleCollisionFrames OBJECT-TYPE
        SYNTAX	Counter
        ACCESS	read-only
        STATUS	mandatory
        DESCRIPTION
                "A count of successfully transmitted frames on a particular interface
                for which transmission is inhibited by exactly one collision."
        ::= { wfCSMACDEntry 49 }

    wfCSMACDMultipleCollisionFrames OBJECT-TYPE
        SYNTAX	Counter
        ACCESS	read-only
        STATUS	mandatory
        DESCRIPTION
                "A count of successfully transmitted frames on a particular interface
                for which transmission is inhibited by more than one collision."
        ::= { wfCSMACDEntry 50 }

    wfCSMACDInternalMacTxErrors OBJECT-TYPE
        SYNTAX	Counter
        ACCESS	read-only
        STATUS	mandatory
        DESCRIPTION
                "A count of frames for which transmission on a particular interface fails
                due to an internal MAC sublayer transmit error.  A frame is only counted
                by an instance of this object if it is not counted by the corresponding
                instance of either the LateCollisions object, the ExcessiveCollisions
                object, or the CarrierSenseErrors object."
        ::= { wfCSMACDEntry 51 }

    wfCSMACDLineCapability OBJECT-TYPE
        SYNTAX	INTEGER {
    		    tenbaset(1),
    		    tenbasetduplex(2),
    		    hundredbasetx(3),
    		    hundredbasetxduplex(4),
    		    hundredbaset4(5),
    		    tenbasetduplexcongctrl(6),
    		    hundredbasetxduplexcongctrl(7),
		    gigabitduplex(8),
		    gigabitduplexflowctrl(9)
    		}
        ACCESS	read-only
        STATUS	mandatory
        DESCRIPTION
                "If NWay is configured, this attribute contains a value that uniquely
                identifies the single capability that was agreed upon by the local and
                remote interfaces.  If NWay is not configured, this attribute describes
                the speed and duplex setting that was configured for this interface."
        DEFVAL	{ tenbaset }
        ::= { wfCSMACDEntry 52 }

    wfCSMACDEtherChipSet OBJECT-TYPE
        SYNTAX	OBJECT IDENTIFIER
        ACCESS	read-only
        STATUS	mandatory
        DESCRIPTION
                "This object contains an OBJECT IDENTIFIER which identifies the chipset used
                to realize the interface.  This object usually identifies the Medium Access
                Control (MAC) chip."
        ::= { wfCSMACDEntry 53 }

    wfCSMACDRxSymbolErrors OBJECT-TYPE
        SYNTAX	Counter
        ACCESS	read-only
        STATUS	mandatory
        DESCRIPTION
                "A count of frames received on a particular interface with one or more
                100Mb symbol errors detected."
        ::= { wfCSMACDEntry 54 }

    wfCSMACDInternalMacRxErrors OBJECT-TYPE
        SYNTAX	Counter
        ACCESS	read-only
        STATUS	mandatory
        DESCRIPTION
                "A count of frames for which reception on a particular interface fails
                due to an internal MAC sublayer receive error.  A frame is only counted
                by an instance of this object if it is not counted by the corresponding
                instance of either the FrameTooLongs object, the AlignmentErrors object,
                or the FCSErrors object."
        ::= { wfCSMACDEntry 55 }

    wfCSMACDConfigurableSpeed OBJECT-TYPE
        SYNTAX	INTEGER {
    		    enabled(1),
    		    disabled(2)
    		}
        ACCESS	read-only
        STATUS	mandatory
        DESCRIPTION
                "This attribute will be enabled(1) if the interface supports different
                speed configurations.  If configurable speeds are not supported on the
                interface, this attribute will be disabled(2).  Creation of
                wfCSMACDAutoNegEntry records for 10/100BaseT is valid only if this
		attribute is enabled. For Gigabit Ethernet the latter statement is not
		true"
        DEFVAL	{ disabled }
        ::= { wfCSMACDEntry 56 }

    wfCSMACDRxFlushes OBJECT-TYPE
        SYNTAX	Counter
        ACCESS	read-only
        STATUS	mandatory
        DESCRIPTION
                "This attribute describes the number of times the hardware
                has entered a state which required a flush of the RX FIFO."
        ::= { wfCSMACDEntry 57 }

    wfCSMACDTxDeadlocks OBJECT-TYPE
        SYNTAX	Counter
        ACCESS	read-only
        STATUS	mandatory
        DESCRIPTION
                "This attribute describes the number of times the hardware
                has entered a Tx Deadlock condition, and the software
                intervenes to free up the lock."
        ::= { wfCSMACDEntry 58 }

    wfCSMACDBoflRetries OBJECT-TYPE
        SYNTAX  INTEGER(1..60)
        ACCESS  read-write
        STATUS  mandatory
        DESCRIPTION
                "bofl retries, dflt = 5"
        DEFVAL  { 5 }
        ::= { wfCSMACDEntry 59 }

    wfCSMACDBoflTmoDivisor OBJECT-TYPE
        SYNTAX  INTEGER(1..100)
        ACCESS  read-write
        STATUS  mandatory
        DESCRIPTION
                "bofl tmo divisorr, dflt = 1"
        DEFVAL  { 1 }
        ::= { wfCSMACDEntry 60 }

    wfCSMACDTurboBoflDebug OBJECT-TYPE
        SYNTAX	INTEGER
        ACCESS	read-write
        STATUS	mandatory
        DESCRIPTION
                "Special Turbo-BOFL debug mechanism to be used by Engineering
		 and Manufacturing only.
		 31-24 : TMO - period of breath (amount of time between
						 successive breaths of life)
		 23-16 : Number of packets per breath.
		 15-0  : Packet length in bytes - 22 bytes minimum.
		 All bits set to zero will disable this attribute."

        DEFVAL	{ 0 }
        ::= { wfCSMACDEntry 61 }

    wfCSMACDIfIndex OBJECT-TYPE
        SYNTAX  INTEGER
        ACCESS  read-only
        STATUS  mandatory
        DESCRIPTION
                "IfTable Index for this line instance,
                 filled in by driver. For the BAC it is not the same
                 as the circuit number."
        ::= { wfCSMACDEntry 62 }

     wfCSMACDTxFlowControlPauseFrames OBJECT-TYPE
        SYNTAX  Counter
        ACCESS  read-only
        STATUS  mandatory
        DESCRIPTION
                "This attribute indicates the number of Flow Control
                 Pause frames transmitted."
        ::= { wfCSMACDEntry 63 }

     wfCSMACDRxFlowControlPauseFrames OBJECT-TYPE
        SYNTAX  Counter
        ACCESS  read-only
        STATUS  mandatory
        DESCRIPTION
                "This attribute indicates the number of Flow Control
                 Pause frames received."
        ::= { wfCSMACDEntry 64 }

     wfCSMACDRxUnsupportedOpcodes OBJECT-TYPE
        SYNTAX  Counter
        ACCESS  read-only
        STATUS  mandatory
        DESCRIPTION
                "This attribute indicates the number of Control
                 frames received that were not pause frames."
        ::= { wfCSMACDEntry 65 }

     wfCSMACDFlowControlEnable  OBJECT-TYPE
        SYNTAX  INTEGER {
                    enabled(1),
                    disabled(2)
                }
        ACCESS  read-write
        STATUS  mandatory
        DESCRIPTION
                "Flow control enable/disable parameter, dflt = enabled"
        DEFVAL  { enabled }
        ::= { wfCSMACDEntry 66 }

     wfCSMACDTxFlowControlPauseTime  OBJECT-TYPE
        SYNTAX  INTEGER(32..65535)
        ACCESS  read-write
        STATUS  mandatory
        DESCRIPTION
                "This attribute indicates flow control pause time in slots."
        DEFVAL	{ 65535 }
        ::= { wfCSMACDEntry 67 }

     wfCSMACDTxFlowControlPauseZeroEnable  OBJECT-TYPE
        SYNTAX  INTEGER {
                    enabled(1),
                    disabled(2)
                }
        ACCESS  read-write
        STATUS  mandatory
        DESCRIPTION
                "Tx Pause 0 frame generation enable/disable parameter, dflt = enabled."
        DEFVAL  { enabled }
        ::= { wfCSMACDEntry 68 }

     wfCSMACDDsqmsLineSpeed OBJECT-TYPE
        SYNTAX  INTEGER(1..100000000)
        ACCESS  read-write
        STATUS  mandatory
        DESCRIPTION
                "User-selected line speed for DSQMS client"
        DEFVAL  { 1250000 }
        ::= { wfCSMACDEntry 69 }



    wfCSMACDAutoNegTable OBJECT-TYPE
        SYNTAX	SEQUENCE OF WfCSMACDAutoNegEntry
        ACCESS	not-accessible
        STATUS	mandatory
        DESCRIPTION
                "CSMA/CD Auto Negotiation (NWay) record"
        ::= { wfCSMACDAutoNegGroup 1 }

    wfCSMACDAutoNegEntry OBJECT-TYPE
        SYNTAX	WfCSMACDAutoNegEntry
        ACCESS	not-accessible
        STATUS	mandatory
        DESCRIPTION
                "An entry in the csmacd table"
        INDEX	{ wfCSMACDAutoNegSlot,
    		  wfCSMACDAutoNegConnector }
        ::= { wfCSMACDAutoNegTable 1 }

    WfCSMACDAutoNegEntry ::= SEQUENCE {
    	    wfCSMACDAutoNegDelete
    		INTEGER,
    	    wfCSMACDAutoNegSlot
    		INTEGER,
    	    wfCSMACDAutoNegConnector
    		INTEGER,
    	    wfCSMACDAutoNegSpeedSelect
    		INTEGER,
    	    wfCSMACDAutoNegRemoteSignaling
    		INTEGER,
    	    wfCSMACDAutoNegState
    		INTEGER,
    	    wfCSMACDAutoNegRestartAutoConfig
    		INTEGER,
    	    wfCSMACDAutoNegLocalCapability
    		Gauge,
    	    wfCSMACDAutoNegAdvertisedCapability
    		Gauge,
    	    wfCSMACDAutoNegReceivedCapability
    		Gauge
        }

    wfCSMACDAutoNegDelete OBJECT-TYPE
        SYNTAX	INTEGER {
    		    create(1),
    		    delete(2)
    		}
        ACCESS	read-write
        STATUS	mandatory
        DESCRIPTION
                "create/delete parameter, dflt = created"
        DEFVAL	{ create }
        ::= { wfCSMACDAutoNegEntry 1 }

    wfCSMACDAutoNegSlot OBJECT-TYPE
        SYNTAX	INTEGER(1..14)
        ACCESS	read-only
        STATUS	mandatory
        DESCRIPTION
                "instance ID Slot, filled in by driver"
        ::= { wfCSMACDAutoNegEntry 2 }

    wfCSMACDAutoNegConnector OBJECT-TYPE
        SYNTAX	INTEGER(1..44)
        ACCESS	read-only
        STATUS	mandatory
        DESCRIPTION
                "instance ID Connector, filled in by driver. For the ASN
                this attribute is an encoded value and is equal to
                'module'*10 + 'connector'. Where 'module' is defined in
                attribute 42 and 'connector' is defined in attribute 43
                of this table. For non-ASN platforms this attribute is
                the physical connector number on the slot."
        ::= { wfCSMACDAutoNegEntry 3 }

    wfCSMACDAutoNegSpeedSelect OBJECT-TYPE
        SYNTAX	INTEGER {
    		    nway(1),
    		    tenbaset(2),
    		    tenbasetduplex(3),
    		    hundredbasetx(4),
    		    hundredbasetxduplex(5),
    		    hundredbaset4(6),
    		    macloopback(7),
    		    phyloopback(8),
    		    twisterloopback(9),
    		    tenbasetduplexcongctrl(10),
    		    hundredbasetxduplexcongctrl(11),
		    gigabitduplex(12),
		    gigabitduplexflowctrl(13)
    		}
        ACCESS	read-write
        STATUS	mandatory
        DESCRIPTION
                "This value indicates the configured speed of the local interface.
                This parameter allows configuration of a specific speed and duplex
                setting, or allows configuration/enabling of Auto Negotiation/NWay.
                Selecting a specific speed (i.e. a value other than 1) implicitly
                disables Auto Negotiation/NWay."
        DEFVAL	{ hundredbasetx }
        ::= { wfCSMACDAutoNegEntry 4 }

    wfCSMACDAutoNegRemoteSignaling OBJECT-TYPE
        SYNTAX	INTEGER {
    		    detected(1),
    		    notdetected(2)
    		}
        ACCESS	read-only
        STATUS	mandatory
        DESCRIPTION
                "This value indicates whether the remote end of the link is operating
                Auto Negotiation signaling or not.  It shall take the value detected if,
                during the previous link negotiation, FLP bursts were received from the
                remote end.
                NOTE: This parameter is only valid if SpeedSelect is configured for NWay."
        DEFVAL	{ notdetected }
        ::= { wfCSMACDAutoNegEntry 5 }

    wfCSMACDAutoNegState OBJECT-TYPE
        SYNTAX	INTEGER {
    		    disabled(1),
    		    configuring(2),
    		    complete(3),
    		    paralleldetectfail(4)
    		}
        ACCESS	read-only
        STATUS	mandatory
        DESCRIPTION
                "This value indicates whether Auto Negotiation signaling is in progress
                or has completed.
                NOTE: This parameter is only valid if SpeedSelect is configured for NWay."
        DEFVAL	{ disabled }
        ::= { wfCSMACDAutoNegEntry 6 }

    wfCSMACDAutoNegRestartAutoConfig OBJECT-TYPE
        SYNTAX	INTEGER
        ACCESS	read-write
        STATUS	mandatory
        DESCRIPTION
                "Writing any value to this attribute forces Auto Negotiation to begin link
                re-negotiation. This action has no effect if Auto Negotiation signaling
                is disabled.
                NOTE: This parameter is only valid if SpeedSelect is configured for NWay."
        ::= { wfCSMACDAutoNegEntry 7 }

    wfCSMACDAutoNegLocalCapability OBJECT-TYPE
        SYNTAX	Gauge
        ACCESS	read-only
        STATUS	mandatory
        DESCRIPTION
                "This is a GAUGE because this attribute is 32-bit unsigned, non-increasing
                A value that uniquely identifies the set of capabilities of the LOCAL Auto
                Negotiation entity. The value is a sum which initially takes the value zero.
                Then, for each capability of the LOCAL interface, 2 raised to the power
                noted below is added to the sum. For example, a LOCAL interface which has
                the capability to support only 100Base-TX would have a value of 128 (2**7).
                In contrast, a LOCAL interface which supports both 100Base-TX and 100Base-TX
                Full Duplex would cause this object to have a value of 384 ((2**7) + (2**8)).

                The powers of 2 assigned to the capabilities are these:

                         Power   Capability
     			  0	  Pause
			  1       ASM_DIR
                          5       10Base-T
                          6       10Base-T  Full Duplex
                          7      100Base-TX
                          8      100Base-TX Full Duplex
                          9      100Base-T4
			 14	 1000Base-X
			 15	 1000Base-X Full Duplex

                NOTE: This parameter is only valid if SpeedSelect is configured for NWay."
        ::= { wfCSMACDAutoNegEntry 8 }

    wfCSMACDAutoNegAdvertisedCapability OBJECT-TYPE
        SYNTAX	Gauge
        ACCESS	read-write
        STATUS	mandatory
        DESCRIPTION
                "This is a GAUGE because this attribute is 32-bit unsigned, non-increasing
                A successful set operation will result in immediate link re-negotiation if
                AutoNegAdminState is enabled.  A value that uniquely identifies the set of
                capabilities advertised by the local Auto Negotiation entity. The value is
                a sum which initially takes the value zero. Then, for each capability of
                the ADVERTISED interface, 2 raised to the power noted below is added to the
                sum. For example, a ADVERTISED interface which has the capability to support
                only 100Base-TX would have a value of 128 (2**7). In contrast, an ADVERTISED
                interface which supports both 100Base-TX and 100Base-TX Full Duplex would
                cause this object to have a value of 384 ((2**7) + (2**8)).

                The powers of 2 assigned to the capabilities are these:

                         Power   Capability
     			  0	  Pause
			  1       ASM_DIR
                          5       10Base-T
                          6       10Base-T  Full Duplex
                          7      100Base-TX
                          8      100Base-TX Full Duplex
                          9      100Base-T4
			 14	 1000Base-X
			 15	 1000Base-X Full Duplex

                NOTE: This parameter is only valid if SpeedSelect is configured for NWay."
        ::= { wfCSMACDAutoNegEntry 9 }

    wfCSMACDAutoNegReceivedCapability OBJECT-TYPE
        SYNTAX	Gauge
        ACCESS	read-only
        STATUS	mandatory
        DESCRIPTION
                "This is a GAUGE because this attribute is 32-bit unsigned, non-increasing
                A value that uniquely identifies the set of capabilities of the REMOTE Auto
                Negotiation entity. The value is a sum which initially takes the value zero.
                Then, for each capability of the REMOTE interface, 2 raised to the power
                noted below is added to the sum. For example, a REMOTE interface which has
                the capability to support only 100Base-TX would have a value of 128 (2**7).
                In contrast, a REMOTE interface which supports both 100Base-TX and 100Base-TX
                Full Duplex would cause this object to have a value of 384 ((2**7) + (2**8)).

                The powers of 2 assigned to the capabilities are these:

                         Power   Capability
     			  0	  Pause
			  1       ASM_DIR
                          5       10Base-T
                          6       10Base-T  Full Duplex
                          7      100Base-TX
                          8      100Base-TX Full Duplex
                          9      100Base-T4
			 14	 1000Base-X
			 15	 1000Base-X Full Duplex

                NOTE: This parameter is only valid if SpeedSelect is configured for NWay."
        ::= { wfCSMACDAutoNegEntry 10 }

    END  -- Wellfleet-CSMACD-MIB
