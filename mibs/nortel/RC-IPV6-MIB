RC-IPV6-MIB DEFINITIONS ::= BEGIN

IMPORTS
    MODULE-IDENTITY, OBJECT-TYPE, Integer32, Counter32, IpAddress, Gauge32, Unsigned32
        FROM SNMPv2-SMI
    DisplayString, TruthValue, MacAddress, RowStatus, TimeStamp, TEXTUAL-CONVENTION,
    RowPointer, DateAndTime, StorageType
        FROM SNMPv2-TC
    MODULE-COMPLIANCE, OBJECT-GROUP
        FROM SNMPv2-CONF
    InterfaceIndex, InterfaceIndexOrZero
        FROM IF-MIB
    PhysAddress
        FROM RFC1213-MIB
    InetAddressType, InetAddress, InetPortNumber
        FROM INET-ADDRESS-MIB
    Ipv6AddressIfIdentifier, Ipv6Address, Ipv6IfIndex
        FROM IPV6-TC
    rcIpv6, rcIp, IdList, EnableValue, RcVlanIdOrNone
        FROM RAPID-CITY
    SnmpAdminString
        FROM SNMP-FRAMEWORK-MIB
    VrfIdentifier
        FROM RC-VRF-MIB
    ipv6RouteEntry
        FROM IPV6-MIB
    tunnelInetConfigEntry
        FROM TUNNEL-MIB
    IpIsisPlsbNodeNickName
        FROM RC-IP-MIB;

rcIpv6Mib MODULE-IDENTITY
       LAST-UPDATED     "202005060000Z"
       ORGANIZATION     "Bay Networks, Rapid-City Group"
       CONTACT-INFO     "Yu-Ten Lee
          Postal:        Nortel Networks, Inc.
			 4655 Great America Pkwy.
			 Santa Clara, CA 95052-8185

			 Tel:           408-495-2560
                         Fax:           408-495-6680
                         E-mail:        ylee@nortelnetworks.com"

       DESCRIPTION      "Enterprise MIB for the Accelar product family."

       REVISION "202005060000Z" -- 6 May 2019
       DESCRIPTION "Version 82: Add rcIpv6AddressName
	   			Requested by Deb Fitzgerald (Prem)"

       REVISION "202003120000Z" -- 12 March 2020
       DESCRIPTION "Version 81: Add rcIpv6StaticRouteName
				Requested by Deborah Fitzgerald (Prem)"

       REVISION "201910090000Z" -- 09 October 2019
       DESCRIPTION "Version 80: Add the following based on VOSS 8.1 mibs MRT syntax check -
	                        * rcIpv6StaticRouteBfdTable
				(Prem)"

       REVISION "201906190000Z" -- 19 Jun 2019
       DESCRIPTION "Version 79: Add rcIpv6InterfaceBfdVrfId and rcIpv6InterfaceBfdVrfName
	                        to rcIpv6InterfaceBfdTable.
	   			Requested by Vinay (commit 4a2f8e58) (Prem)"

       REVISION "201906060000Z" -- 06 Jun 2019
       DESCRIPTION "Version 78: Add rcIpv6AddressIfType under rcIpv6AddressTable.
	   			Requested by Andrew Chillar (NLS) (Prem)"

       REVISION "201810300000Z" -- 30 Oct. 2018
       DESCRIPTION "Version 77:  Add rcIpv6RouteExtensionLayer3VirtualInterface and update DESCRIPTION
	   			 for rcIpv6RouteExtensionSrcVrfId.
				 Requested by Bianca Neagu (Prem)"

       REVISION "201808280000Z" -- 28 Aug. 2018
       DESCRIPTION "Version 76:  added rcIpv6RouteExtensionSrcVrfId"

       REVISION "201807120000Z" -- 12 July 2018
       DESCRIPTION "Version 75: Changed the type for rcIpv6FhsSnoopNotificationEntryCount
                                from INTEGER to Integer32, as it is not an enumeration.
                                (azmeu)"

       REVISION "201807100000Z" -- 10 July 2018
       DESCRIPTION "Version 74: Change range from Integer32 (1..16777215) to
	   			Integer32 (0..16777215) for objects:
	   			rcIpv6IsisInFilterIsid and rcIpv6IsisInFilterNickNameIsid"

       REVISION "201804030000Z" -- 03 Apr 2018
       DESCRIPTION "Version 73: Changed the range of -
	   			rcIpv6IsisInFilterPolicyName,
				rcIpv6IsisInFilterNickNamePolicyName,
				rcIpv6IsisInFilterIsidPolicyName,
				rcIpv6IsisInFilterNickNameIsidPolicyName,
				rcIpv6IsisInFilterIsidListPolicyName,
				rcIpv6IsisInFilterNickNameIsidListPolicyName
				to include 0 because it is optional parameter
				Requested by Ada Mladin/Bianca-Elena Neagu (Prem)"

       REVISION "201804020000Z" -- 02 Apr 2018
       DESCRIPTION "Version 72: Add the following -
	   			rcIpv6IsisGenInFilter
				rcIpv6IsisInFilterNickNameTableSize
				rcIpv6IsisInFilterIsidTableSize
				rcIpv6IsisInFilterNickNameIsidTableSize
				rcIpv6IsisInFilterIsidListTableSize
				rcIpv6IsisInFilterNickNameIsidListTableSize
				rcIpv6IsisInFilterApply
				rcIpv6IsisInFilterDefault
				rcIpv6IsisInFilterPolicyName
				rcIpv6IsisInFilterObjects
				rcIpv6IsisInFilterNickNameTable
				rcIpv6IsisInFilterIsidTable
				rcIpv6IsisInFilterNickNameIsidTable
				rcIpv6IsisInFilterIsidListTable
				rcIpv6IsisInFilterNickNameIsidListTable
				Requested by Ada Mladin (Prem)."

       REVISION "201702010000Z" -- 01 Feb 2017
       DESCRIPTION "Version 71: Corrected MIB compiler error."

       REVISION "201606160000Z" -- 16 June 2016
       DESCRIPTION "Version 70: Added - rcIpv6InterfaceIpsecEnable to
	                        rcIpv6InterfaceTable"

       REVISION "201602050000Z" -- 05 Feb 2016
       DESCRIPTION "Version 69: Added - rcIpv6RouteExtensionPathType"

       REVISION "201510190000Z" -- 19 October 2015
       DESCRIPTION "Version 68: Added -
	   			    rcIpv6FhsSnoopTable,
				    rcIpv6FhsSnoopNotificationObjects,
				    rcIpv6FhsSnoopNotificationEntryType and
				    rcIpv6FhsSnoopNotificationEntryCount
	                        Requested by Shivanand - submit 25855 (prempa)"

       REVISION "201509040000Z" -- 04 Sept 2015
       DESCRIPTION "Version 67: Corrected the OID(24->23, 25->24)for objects
	   			rcIpv6SourceRouteEnable and
	                        rcIpv6IcmpMulticastRequestEnable (malok)"
       REVISION "201509010000Z" -- 01 Sept 2015
       DESCRIPTION "Version 66: Added rcIpv6SourceRouteEnable and
	                        rcIpv6IcmpMulticastRequestEnable (malok)"

       REVISION "201507210000Z" -- 21 July 2015
       DESCRIPTION "Version 65: Added rcIpv6NetToPhysicalCvid.
	   			Requested by Zuyan (Prem)"

       REVISION "201507070000Z" -- 07 July 2015
       DESCRIPTION "Version 64: Added rcIpv6AlternativeRouteEnable.
	   			Requested by Sebastian Costache (Prem)"

       REVISION "201506290000Z" -- 29 June 2015
       DESCRIPTION "Version 63: Added ripng to rcIpv6RoutePreProtocol.
	   			Requested by Hemadri Mhaskar (Prem) for RIPng"

       REVISION "201506160000Z" -- 16 June 2015
       DESCRIPTION "Version 62: Added ebgp and ibgp to rcIpv6RoutePreProtocol.
	   			Requested by Osamu (Prem) for BGP+"

       REVISION "201504220000Z" -- 22 April 2015
       DESCRIPTION "Version 61: Added rcIpv6RoutePrefTableSize
	                              rcIpv6RoutePrefTable"

       REVISION "201501260000Z" -- 26 January 2015
       DESCRIPTION "Version 60: Added rcIpv6AddressValidLifetime and rcIpv6AddressPrefLifetime to rcIpv6AddressTable"

       REVISION "201412110000Z" -- 11 December 2014
       DESCRIPTION "Version 59: Added rcIpv6RouteExtensionTable to replace
	   			rcIpv6RouteTable. Reverted the rcIpv6RouteTable
				back to the original definition (as defined
				in MRT version 49 - 30 May 2014) because this
				was the version that was published in one
				of the Stackables release."

       REVISION "201412090000Z" -- 9 December 2014
       DESCRIPTION "Version 58: Change rcIpv6MLDHostCacheTable indexes order."

       REVISION "201412040000Z" -- 4 December 2014
       DESCRIPTION "Version 57: Added rcTunnelXInetConfigTable to augment tunnelInetConfigTable.
                                Added rcIpv6ClearGlobalIcmpStats to rcIpv6Scalars.
                                Make rcIpv6DefaultRoutersTable and rcIpv6MLDHostCacheTable indexes not-accessible (conformance with SMIv2)."

       REVISION "201411260000Z" -- 26 November 2014
       DESCRIPTION "Version 56: Added the following scalars: rcIpv6Autoconfig, rcIpv6IcmpAddrUnreach,
                                rcIpv6IcmpPortUnreach, rcIpv6SlowPathToCpu;
                                Added another field to rcIpv6InterfaceTable: rcIpv6InterfaceProcessRedirect;
                                Added two more tables: rcIpv6DefaultRoutersTable, rcIpv6MLDHostCacheTable;
                                Imported ipv6RouteEntry from IPV6-MIB as a temporary fix due to compile error;"

       REVISION "201411050000Z" -- 5 November 2014
       DESCRIPTION "Version 55: Added rcIpv6RouteProtocol.
				Requested by Amit Choudhary on Nov 5 2014 (Prem)"

       REVISION "201410150000Z" -- 15 October 2014
       DESCRIPTION "Version 54: Removed rcIpv6RouteDest, rcIpv6RoutePfxLength
	   			and rcIpv6RouteIndex from rcIpv6RouteTable
				because they are not needed anymore.
				Request based on the VSP9000 Federal (Prem)"

       REVISION "201409190000Z" -- 19 September 2014
       DESCRIPTION "Version 53: Change the rcIpv6RouteTable INDEX to AUGMENTS { ipv6RouteEntry }"

       REVISION "201409170000Z" -- 17 September 2014
       DESCRIPTION "Version 52: Removed range of rcIpv6ConfDhcpIfIndex."

       REVISION "201408060000Z" -- 06 August 2014
       DESCRIPTION "Version 51: Added rcIpv6NetToPhysicalBMac under rcIpv6NetToPhysicalTable."

       REVISION "201407040000Z" -- 04 July 2014
       DESCRIPTION "Version 50: Updated rcIpv6InterfaceType from read-only to read-create and added value loopback(4) to rcIpv6InterfaceType."

       REVISION "201405300000Z" -- 30 May 2014
       DESCRIPTION "Version 49: Added rcIpv6RouteTable."

       REVISION "201401070000Z" -- 07 January 2014
       DESCRIPTION "Version 48: Change description for rcIpv6IcmpErrorInterval."

       REVISION "201308230000Z" -- 23 August 2013
       DESCRIPTION "Version 47: Added EnableValue at IMPORTS section."

       REVISION "201304160000Z" -- 16 April 2013
       DESCRIPTION "Version 46: Changed default value for rcIpv6InterfaceRetransmitTime.
                                Correct syntax error (missing comma) in RcIpv6InterfaceEntry."

       REVISION "201210240000Z" -- 24 Oct 2012
       DESCRIPTION "Version 45: Added rcIpv6InterfaceBfdEnable and
	                        rcIpv6InterfaceBfdTable"

       REVISION "201201090000Z" -- 09 Jan 2012
       DESCRIPTION "Version 44: Added rcIpv6RouteStaticGlobalAdminEnabled
	                        Modified rcIpv6IcmpAnycastEchoReply and
				rcIpv6IcmpMulticastEchoReply to fix the conflict"

       REVISION "201112010000Z" -- 01 Dec 2011
       DESCRIPTION "Version 43: Added rcIpv6InterfaceRsmltEnable"

       REVISION "201111080000Z" -- 08 November 2011
       DESCRIPTION "Version 42: Added rcIpv6DCacheIfType and
	                        rcIpv6DCacheIfData. Modified the syntax
				of rcIpv6DCacheIfIndex to Unsigned32.
				Modified the OID for rcIpv6DCachePmtu
				and rcIpv6DCachePmtuAge."

       REVISION "201110200000Z" -- 20 October 2011
       DESCRIPTION "Version 41: Added rcIpv6InterfaceForwardingEnabled,
                                Added rcIpv6InterfaceReversePathCheckEnable,
                                      rcIpv6InterfaceReversePathCheckMode,
                                      which was missing in table SEQUENCE.
                                      Change read-write to read-create
                                      for objects in rcIpv6InterfaceTable."

       REVISION "201110180000Z" -- 18 October 2011
       DESCRIPTION "Version 40: Added rcIpv6InterfaceReversePathCheckEnable,
	                        rcIpv6InterfaceReversePathCheckMode"


       REVISION "201109280000Z" -- 28 September 2011
       DESCRIPTION "Version 39: Added rcIpv6IcmpAnycastEchoReply and
	                        rcIpv6IcmpMulticastEchoReply"

       REVISION "201108040000Z" -- 04 August 2011
       DESCRIPTION "Version 38: Remove rcIpv6InterfaceReachableTimer,
                                update range for rcIpv6InterfaceReachableTime"

       REVISION "201107270000Z" -- 27 July 2011
       DESCRIPTION "Version 37: Added rcIpv6InterfaceReachableTimer"

       REVISION "201107220000Z" -- 22 July 2011
       DESCRIPTION "Version 36: Added rcIpv6RouteStaticClear,
                                      rcIpv6InterfaceClearIcmpStats,
                                      rcIpv6InterfaceClearGeneralStats,
                                      rcIpv6InterfaceClearNeighborCache,
                                      rcIpv6InterfaceClearDestinationCache,
                                      rcIpv6DestinationCacheTable"

       REVISION "201106240000Z" -- 24 June 2011
       DESCRIPTION "Version 35: Added rcIpv6InterfaceCurHopLimit
	                              rcIpv6RouterAdvertRetransmitTime
			        Deprecated: rcIpv6InterfaceRetransmitTime.
				            rcIpv6RouterAdvertRetransmitTimer.
				Correct Syntax: rcIpv6RouterAdvertLinkMTU,
				                rcIpv6InterfaceReachableTime,
						rcIpv6InterfaceRetransmitTimer.
				Change rcIpv6RouterAdvertReachableTime to read-write"

       REVISION "201105260000Z" -- 26 May 2011
       DESCRIPTION "Version 34: Added rcIpv6InterfaceRetransmitTimer"

       REVISION "201102040000Z" -- 04 Feb 2011
       DESCRIPTION "Version 33: Correct the synatx rcIpv6ConfDhcpIfIndex,
	                        rcIpv6PrefixUseDefaultVal and
				rcIpv6RouterAdvertUseDefaultVal based on
				the intial release"

       REVISION "201101060000Z" -- 06 January 2011
       DESCRIPTION "Version 32: Added rcIpv6InterfaceMacOffset,
	            rcIpv6PrefixValidLifetime and rcIpv6PrefixPreferredLifetime.
		    Added enum value web(5) to rcIpv6RadiusServUsedBy.
		    Increased the size of rcIpv6RsmltOperVrfName,
		    rcIpv6RsmltPeerVrfName and rcIpv6RsmltEdgePeerVrfName."

       REVISION "201011120000Z" -- 02 November 2010
       DESCRIPTION "Version 31: Corrected the SYNTAX for the following -
	                        rcIpv6MgmtPortStaticRoutePrefixLength
				rcIpv6MgmtPortStaticRouteDistance
				rcIpv6MgmtPortStaticRoutePreference."

       REVISION "201011020000Z" -- 02 November 2010
       DESCRIPTION "Version 30: Added rcIpv6MgmtPortStaticRouteTable."

       REVISION "201008250000Z" -- 25 August 2010
       DESCRIPTION "Version 29: Added rcIpv6ClearDhcpCounters."

       REVISION "200910220000Z" -- 22 October 2009
       DESCRIPTION "Version 28: Modified rcIpv6InterfaceDescr."

       REVISION "200909150000Z" -- 15 September 2009
       DESCRIPTION "Version 27: Updated rcIpv6IcmpErrorQuota,rcIpv6PrefixValidLife,rcIpv6PrefixPreferredLife
                                Added rcIpv6RsmltOperTable,rcIpv6RsmltPeerTable,rcIpv6RsmltEdgePeerTable."

       REVISION "200907200000Z" -- 20 July 2009
       DESCRIPTION "Version 26: Expand range of rcIpv6ConfDhcpIfIndex."

       REVISION "200903120000Z" -- 12 March 2009
       DESCRIPTION "Version 25: Added table ''rcIpv6RadiusServTable."


       REVISION "200901270000Z" -- 27 January 2009
       DESCRIPTION "Version 24: Added tables 'rcIpv6ConfDhcpRelayTable' and 'rcIpv6DhcpForwardTable '."

       REVISION "200809160000Z" -- 16 September 2008
       DESCRIPTION "Version 23: Added MIB objects for Ipv6 prefix list"

       REVISION "200806300000Z" -- 30 June 2008
       DESCRIPTION "Version 22: rcIpv6InterfaceIdentifier
                                rcIpv6InterfaceIdentifierLength
                                rcIpv6InterfaceDescr
                                rcIpv6InterfaceVlanId
                                rcIpv6InterfaceReasmMaxSize
                                rcIpv6InterfaceAdminStatus
                                rcIpv6InterfaceReachableTime
                                rcIpv6InterfaceRetransmitTime
                                rcIpv6InterfaceMulticastAdminStatus
                                rcIpv6AddressType
                                rcIpv6AddressPrefixLength
                                rcIpv6PrefixUseDefaultVal
                                rcIpv6PrefixValidLife
                                rcIpv6PrefixPreferredLife
                                rcIpv6PrefixAtValidLife
                                rcIpv6PrefixAtPreferredLife
                                rcIpv6PrefixInfinite
                                rcIpv6PrefixOnLinkFlag
                                rcIpv6PrefixAutoFlag
                                rcIpv6PrefixAddressEui
                                rcIpv6PrefixNoAdvertise
                                rcIpv6StaticRouteDistance
                                rcIpv6StaticRoutePreference
                                rcIpv6StaticRouteEnable
                                rcIpv6NetToPhysicalPhysAddress
                                rcIpv6NetToPhysicalType
                                Change MAX-ACCESS of above objects from read-write to read-create."

       REVISION "200803140000Z" -- 14 March 2008
       DESCRIPTION "Version 21: Added new TC 'Ipv6NextHdr'."

       REVISION "200802290000Z" -- 29 Feb 2008
       DESCRIPTION "Version 20:  Fix range of rcIpv6InterfaceReasmMaxSize."

       REVISION "200801150000Z" -- 15 Jan 2008
       DESCRIPTION "Version 19:  Changed rcIpv6NetToPhysicalInterface to read=create."

       REVISION "200709040000Z" -- 04 Sep 2007
       DESCRIPTION "Version 17:  Added objects to enable/disable IPv6 globally."

       REVISION "200706270000Z" -- 27 Jun 2007
       DESCRIPTION "Version 16: Remove status option for rcIpv6StaticRouteStatus:
			reachableInRtmButNotBestRoute"

       REVISION "200706250000Z" -- 25 June 2006
       DESCRIPTION "Version 15: Added rcIpv6IcmpErrorQuota"

       REVISION "200705310000Z" -- 31 May 2007
       DESCRIPTION "Version 14: Added a status option for rcIpv6StaticRouteStatus:
			reachableInRtmButNotBestRoute"

       REVISION "200604100000Z" -- 10 Apr 2006
       DESCRIPTION "Version 13: Updated rcIpv6InterfaceReasmMaxSize"

       REVISION "200603210000Z" -- 21 Mar 2006
       DESCRIPTION "Version 12: Removed  rcIpv6StaticRouteLocalNextHop"

       REVISION "200603160000Z" -- 16 Mar 2006
       DESCRIPTION "Version 11: Updated rcIpv6StaticRouteStatus"

       REVISION "200602090000Z" -- 09 Feb 2006
       DESCRIPTION "Version 10: Updated rcIpv6PrefixUseDefaultVal & rcIpv6RouterAdvertUseDefaultVal"

       REVISION "200512060000Z" -- 06 DEC 2005
       DESCRIPTION "Version 9: Added rcIpv6IcmpNetUnreach and rcIpv6IcmpRedirectMsg mibs"

       REVISION "200512050000Z" -- 05 DEC 2005
       DESCRIPTION "Version 8: Added rcIpv6InterfaceType in rcIpv6InterfaceTable"

       REVISION "200511280000Z" -- 28 Nov 2005
       DESCRIPTION "Version 7: Updated MAX-ACCESS for RowStatus from read-write to read-create"

       REVISION "200511230000Z" -- 23 Nov 2005
       DESCRIPTION "Version 6: Changed range + MAX-ACCESS fields for some ipv6 objects"

       REVISION "200511210000Z" -- 21 Nov 2005
       DESCRIPTION "Version 5: Removed rcIpv6InterfaceType from rcIpv6InterfaceTable"

       REVISION "200511080000Z" -- 08 Nov 2005
       DESCRIPTION "Version 4: Changed syntax of rcIpv6RouterAdvertLinkMTU to Unsigned32"

       REVISION "200509200000Z" -- 20 Sep 2005
       DESCRIPTION "Version 3: Complete overhaul by Padma's team"

       REVISION "200407200000Z" -- 20 July 2004
       DESCRIPTION "Version 2: Added version info"

       REVISION "200401010000Z" -- Unknown
       DESCRIPTION "Version 1: Initial version by Ally Li"

       ::= { rcIpv6 1 }

-- -------------------------------------------------
-- Textual convention from ietf-draft-2011-update-11
-- -------------------------------------------------

IpAddressOriginTC ::= TEXTUAL-CONVENTION
    STATUS     current
    DESCRIPTION
           "The origin of the address.

            manual(2) indicates that the address was manually configured
            to a specified address, e.g. by user configuration.

            dhcp(4) indicates an address that was assigned to this
            system by a DHCP server.

            linklayer(5) indicates an address created by IPv6 stateless
            auto-configuration.

            random(6) indicates an address chosen by the system at
            random, e.g. an IPv4 address within 169.254/16, or an RFC
            3041 privacy address."
    SYNTAX     INTEGER {
        other(1),
        manual(2),
        dhcp(4),
        linklayer(5),
        random(6)
    }

IpAddressStatusTC ::= TEXTUAL-CONVENTION
    STATUS     current
    DESCRIPTION
           "The status of an address.  Most of the states correspond to
            states from the IPv6 Stateless Address Autoconfiguration
            protocol [5].

            The preferred(1) state indicates that this is a valid
            address that can appear as the destination or source address
            of a packet.

            The deprecated(2) state indicates that this is a valid but
            deprecated address that should no longer be used as a source
            address in new communications, but packets addressed to such
            an address are processed as expected.

            The invalid(3) state indicates that this isn't a valid
            address and it shouldn't appear as the destination or source
            address of a packet.

            The inaccessible(4) state indicates that the address is not
            accessible because the interface to which this address is
            assigned is not operational.

            The unknown(5) state indicates that the status can not be
            determined for some reason.

            The tentative(6) state indicates the uniqueness of the
            address on the link is being verified.  Addresses in this
            state should not be used for general communication and
            should only be used to determine the uniqueness of the
            address.

            The duplicate(7) state indicates the address has been
            determined to be non-unique on the link and so must not be
            used.

            In the absence of other information, an IPv4 address is
            always preferred(1)."
    REFERENCE "RFC 2462"
    SYNTAX     INTEGER {
        preferred(1),
        deprecated(2),
        invalid(3),
        inaccessible(4),
        unknown(5),
        tentative(6),
        duplicate(7)
    }

-- Textual convention from ietf-draft-2011-update-11

Ipv6NextHdr ::= TEXTUAL-CONVENTION
   STATUS       current
   DESCRIPTION  "The ipv6 next header to look for."
   SYNTAX       INTEGER {
                  hop-by-hop(0),   -- hop-by-hop
                  icmpv4(1),       -- icmpv4
                  igmpv4(2),       -- igmpv4
                  ipInIp(4),       -- ip in ip encapsulation
                  tcp(6),          -- tcp
                  egp(8),          -- egp
                  udp(17),         -- udp
                  ipv6(41),        -- ipv6
                  routing(43),     -- routing extension hdr
                  frag(44),        -- fragmentation extension hdr
                  rsvp(46),        -- rsvp
                  ipsecESP(50),    -- ipsecESP
                  ipsecAh(51),     -- ipsecAh
                  icmpv6(58),      -- icmpv6
                  noNxtHdr(59),    -- not next hdr
                  destOptions(60), -- destination options extension hdr
                  undefined(255)   -- not provisioned
                 }


rcIpv6Notifications		OBJECT IDENTIFIER ::= { rcIpv6Mib 0 }
rcIpv6Objects		OBJECT IDENTIFIER ::= { rcIpv6Mib 1 }

rcIpv6Scalars		OBJECT IDENTIFIER ::= { rcIpv6Objects 1 }

-- IPv6 ICMP rate limiting
rcIpv6IcmpErrorInterval OBJECT-TYPE
        SYNTAX        INTEGER (0..2147483647)
        MAX-ACCESS    read-write
        STATUS        current
        DESCRIPTION   "The rate limit interval (in milliseconds) at which
                      ICMP error messages can be sent out.
                      A value of zero means no rate limit."
        DEFVAL        { 1000 }
        ::= { rcIpv6Scalars 1 }

-- IPv6 Multicast Admin Status
rcIpv6MulticastAdminStatus OBJECT-TYPE
        SYNTAX        TruthValue
        MAX-ACCESS    read-write
        STATUS        current
        DESCRIPTION   "This indicates the global admin status for
                       multicast."
        DEFVAL        { false }
        ::= { rcIpv6Scalars 2 }

rcIpv6IcmpNetUnreach OBJECT-TYPE
        SYNTAX        TruthValue
        MAX-ACCESS    read-write
        STATUS        current
        DESCRIPTION   "Used to set the icmp net unreach feature enable/disable."
        DEFVAL        { false }
        ::= { rcIpv6Scalars 3 }

rcIpv6IcmpRedirectMsg OBJECT-TYPE
        SYNTAX       TruthValue
        MAX-ACCESS   read-write
        STATUS       current
        DESCRIPTION  "used to set the icmp redirect feature enable/disable."
        DEFVAL        { false }
        ::= { rcIpv6Scalars 4 }

rcIpv6IcmpErrorQuota OBJECT-TYPE
        SYNTAX        INTEGER (0..2000000)
        MAX-ACCESS    read-write
        STATUS        current
        DESCRIPTION   "The number of ICMP error messages that can
                      be sent out during ICMP error interval.
                      A value of zero means not be send any."
        DEFVAL        { 50 }
        ::= { rcIpv6Scalars 5 }

rcIpv6GlobalAdminEnabled OBJECT-TYPE
        SYNTAX        TruthValue
        MAX-ACCESS    read-write
        STATUS        current
        DESCRIPTION   "Indicates whether IPv6 has been administratively
                       enabled."
        DEFVAL        { true }
        ::= { rcIpv6Scalars 6 }

rcIpv6GlobalOperEnabled OBJECT-TYPE
        SYNTAX        TruthValue
        MAX-ACCESS    read-write
        STATUS        current
        DESCRIPTION   "Indicates whether IPv6 is currently enabled."
        DEFVAL        { true }
        ::= { rcIpv6Scalars 7 }

rcIpv6PrefixListTableSize OBJECT-TYPE
        SYNTAX        Unsigned32
        MAX-ACCESS    read-only
        STATUS        current
        DESCRIPTION   "Size of Ipv6 Prefix List Table"
        ::= { rcIpv6Scalars 8 }

rcIpv6ClearDhcpCounters OBJECT-TYPE
        SYNTAX        INTEGER {
                           clear(1)
                      }
        MAX-ACCESS    read-write
        STATUS        current
        DESCRIPTION   "Setting this object will clear IPv6 DHCP counters."
        ::= { rcIpv6Scalars 9 }

-- IPv6 Clear Static Routes
rcIpv6RouteStaticClear OBJECT-TYPE
       SYNTAX          TruthValue
       MAX-ACCESS      read-write
       STATUS          current
       DESCRIPTION     "Clear all IPv6 static routes."
       DEFVAL          { false }
       ::= { rcIpv6Scalars 10 }

-- IPv6 Static Routes Global Admin Status
rcIpv6RouteStaticGlobalAdminEnabled OBJECT-TYPE
        SYNTAX        TruthValue
        MAX-ACCESS    read-write
        STATUS        current
        DESCRIPTION   "Used to globally enable/disable all IPv6 static routes."
        DEFVAL        { true }
        ::= { rcIpv6Scalars 11 }

rcIpv6IcmpAnycastEchoReply OBJECT-TYPE
       SYNTAX          TruthValue
       MAX-ACCESS      read-write
       STATUS          current
       DESCRIPTION     "Used to enable/disable icmp echo reply msg
	                for anycast addresses."
       DEFVAL          { false }
       ::= { rcIpv6Scalars 12 }

rcIpv6IcmpMulticastEchoReply OBJECT-TYPE
       SYNTAX          TruthValue
       MAX-ACCESS      read-write
       STATUS          current
       DESCRIPTION     "Used to enable/disable icmp echo reply msg
	                for multicast addresses."
       DEFVAL          { false }
       ::= { rcIpv6Scalars 13 }

rcIpv6Autoconfig OBJECT-TYPE
       SYNTAX          TruthValue
       MAX-ACCESS      read-write
       STATUS          current
       DESCRIPTION     "Used to enable / disable IPv6 autoconfiguration
                        from router advertisements"
       DEFVAL          { false }
       ::= { rcIpv6Scalars 14 }

rcIpv6IcmpAddrUnreach OBJECT-TYPE
       SYNTAX          TruthValue
       MAX-ACCESS      read-write
       STATUS          current
       DESCRIPTION     "Used to enable / disable address unreachable message"
       DEFVAL          { false }
       ::= { rcIpv6Scalars 15 }

rcIpv6IcmpPortUnreach OBJECT-TYPE
       SYNTAX          TruthValue
       MAX-ACCESS      read-write
       STATUS          current
       DESCRIPTION     "Used to enable / disable port unreachable message"
       DEFVAL          { false }
       ::= { rcIpv6Scalars 16 }

rcIpv6SlowPathToCpu OBJECT-TYPE
       SYNTAX          TruthValue
       MAX-ACCESS      read-write
       STATUS          current
       DESCRIPTION     "Used to enable / disable slow-path-to-cpu"
       DEFVAL          { false }
       ::= { rcIpv6Scalars 17 }


rcIpv6ClearGlobalIcmpStats OBJECT-TYPE
       SYNTAX          INTEGER {
                           clear(1)
                       }
       MAX-ACCESS      read-write
       STATUS          current
       DESCRIPTION     "Setting this object will clear global IPv6 ICMP statistics"
       ::= { rcIpv6Scalars 18 }

rcIpv6EcmpEnable OBJECT-TYPE
        SYNTAX        TruthValue
        MAX-ACCESS    read-write
        STATUS        current
        DESCRIPTION   "Used to globally enable/disable equal-cost
	    	       multi-path feature."
        DEFVAL        { false }
        ::= { rcIpv6Scalars 19 }

rcIpv6EcmpMaxPath OBJECT-TYPE
        SYNTAX        Unsigned32 (1..8)
        MAX-ACCESS    read-write
        STATUS        current
        DESCRIPTION   "Used to globally set the maximum number of
	    	       paths that can be equal cost."
        ::= { rcIpv6Scalars 20 }

rcIpv6RoutePrefTableSize OBJECT-TYPE
        SYNTAX        Integer32
        MAX-ACCESS    read-only
        STATUS        current
        DESCRIPTION   "table size of the rcIpv6RoutePrefTable"
        ::= { rcIpv6Scalars 21 }

rcIpv6AlternativeRouteEnable OBJECT-TYPE
        SYNTAX        TruthValue
        MAX-ACCESS    read-write
        STATUS        current
        DESCRIPTION   "Used to globally enable/disable alterative-route"
	DEFVAL        { true }
        ::= { rcIpv6Scalars 22 }

rcIpv6SourceRouteEnable OBJECT-TYPE
       SYNTAX	      TruthValue
       MAX-ACCESS     read-write
       STATUS	      current
       DESCRIPTION    "Used to globally enable/disable ipv6 source routing feature."
       DEFVAL         { false }
       ::= { rcIpv6Scalars 23 }

rcIpv6IcmpMulticastRequestEnable OBJECT-TYPE
       SYNTAX	      TruthValue
       MAX-ACCESS     read-write
       STATUS         current
       DESCRIPTION    "Used to globally enable/disable
	              ipv6 icmp echo multicast request feature."
       DEFVAL         { true }
       ::= { rcIpv6Scalars 24 }

rcIpv6IsisGenInFilter  OBJECT IDENTIFIER ::= {rcIpv6Scalars 25}

rcIpv6IsisInFilterNickNameTableSize OBJECT-TYPE
        SYNTAX        Integer32
        MAX-ACCESS    read-only
        STATUS        current
        DESCRIPTION   "Ipv6 Isis In Filter Nick Name table size"
        ::= { rcIpv6IsisGenInFilter 1 }

rcIpv6IsisInFilterIsidTableSize OBJECT-TYPE
        SYNTAX        Integer32
        MAX-ACCESS    read-only
        STATUS        current
        DESCRIPTION   "Ipv6 Isis In Filter Isid table size"
        ::= { rcIpv6IsisGenInFilter 2 }

rcIpv6IsisInFilterNickNameIsidTableSize OBJECT-TYPE
        SYNTAX        Integer32
        MAX-ACCESS    read-only
        STATUS        current
        DESCRIPTION   "Ipv6 Isis In Filter Nick Name Isid table size"
        ::= { rcIpv6IsisGenInFilter 3 }

rcIpv6IsisInFilterIsidListTableSize OBJECT-TYPE
        SYNTAX        Integer32
        MAX-ACCESS    read-only
        STATUS        current
        DESCRIPTION   "Ipv6 Isis In Filter Isid List table size"
        ::= { rcIpv6IsisGenInFilter 4 }

rcIpv6IsisInFilterNickNameIsidListTableSize OBJECT-TYPE
        SYNTAX        Integer32
        MAX-ACCESS    read-only
        STATUS        current
        DESCRIPTION   "Ipv6 Isis In Filter Nick Name Isid List table size"
        ::= { rcIpv6IsisGenInFilter 5 }

rcIpv6IsisInFilterApply OBJECT-TYPE
        SYNTAX        INTEGER  {
                   		noAction(1),
                    		apply(2)
                                }
        MAX-ACCESS    read-write
        STATUS        current
        DESCRIPTION   "Used to Apply the Ipv6 Isis Accept filters.
                       When the value is set to apply, all the elements in
                       the in the various Ipv6 Isis In Filter Tables will be
                       applied as well as rcIpv6IsisInFilterDefault. This may
                       be a disruptive operation to traffic.
                       The get will always return noAction."
	DEFVAL        { noAction }
        ::= { rcIpv6IsisGenInFilter 6 }

rcIpv6IsisInFilterDefault OBJECT IDENTIFIER ::= { rcIpv6Scalars 26 }

rcIpv6IsisInFilterPolicyName OBJECT-TYPE
        SYNTAX        DisplayString (SIZE(0..64))
        MAX-ACCESS    read-write
        STATUS        current
        DESCRIPTION   "Route Map name"
        ::= { rcIpv6IsisInFilterDefault 1 }

-- IPv6 Interface Table
rcIpv6InterfaceTable OBJECT-TYPE
        SYNTAX          SEQUENCE OF RcIpv6InterfaceEntry
        MAX-ACCESS      not-accessible
        STATUS          current
        DESCRIPTION     "This table contains list of IPv6 interfaces and
             per-interface IPv6-specific information."
        ::= { rcIpv6Objects 2 }

rcIpv6InterfaceEntry OBJECT-TYPE
        SYNTAX          RcIpv6InterfaceEntry
        MAX-ACCESS      not-accessible
        STATUS          current
        DESCRIPTION     "An entry of ipv6 interface In Table containing
                         per-interface information."
        INDEX           { rcIpv6InterfaceIfIndex }
        ::= { rcIpv6InterfaceTable 1 }

RcIpv6InterfaceEntry ::=
        SEQUENCE {
                  rcIpv6InterfaceIfIndex                InterfaceIndex,
                  rcIpv6InterfaceIdentifier             Ipv6AddressIfIdentifier,
                  rcIpv6InterfaceIdentifierLength       INTEGER,
                  rcIpv6InterfaceDescr                  DisplayString,
                  rcIpv6InterfaceVlanId                 INTEGER,
                  rcIpv6InterfaceType                   INTEGER,
                  rcIpv6InterfaceReasmMaxSize           INTEGER,
                  rcIpv6InterfacePhysAddress            PhysAddress,
                  rcIpv6InterfaceAdminStatus            TruthValue,
                  rcIpv6InterfaceOperStatus             INTEGER,
                  rcIpv6InterfaceReachableTime          INTEGER,
                  rcIpv6InterfaceRetransmitTime         INTEGER,
                  rcIpv6InterfaceMulticastAdminStatus   TruthValue,
                  rcIpv6InterfaceRowStatus                   RowStatus,
                  rcIpv6InterfaceDhcpEnabled               TruthValue,
                  rcIpv6InterfaceMacOffset              Integer32,
                  rcIpv6InterfaceRetransmitTimer        Unsigned32,
		  rcIpv6InterfaceCurHopLimit            Integer32,
                  rcIpv6InterfaceClearIcmpStats         TruthValue,
                  rcIpv6InterfaceClearGeneralStats      TruthValue,
                  rcIpv6InterfaceClearNeighborCache     TruthValue,
                  rcIpv6InterfaceClearDestinationCache  TruthValue,
                  rcIpv6InterfaceReversePathCheckEnable TruthValue,
                  rcIpv6InterfaceReversePathCheckMode   INTEGER,
                  rcIpv6InterfaceForwardingEnabled      TruthValue,
		  rcIpv6InterfaceRsmltEnable            TruthValue,
		  rcIpv6InterfaceBfdEnable         	TruthValue,
                  rcIpv6InterfaceProcessRedirect        TruthValue,
		  rcIpv6InterfaceIpsecEnable            TruthValue
                 }

rcIpv6InterfaceIfIndex OBJECT-TYPE
        SYNTAX        InterfaceIndex
        MAX-ACCESS    not-accessible
        STATUS        current
        DESCRIPTION   "An unique value to identify a physical interface
                               or a logical interface (VLAN).
                       For the brouter port it is the ifindex of the
                       port and in the case of the vlan it is the
                       ifindex of the vlan."
        ::= { rcIpv6InterfaceEntry 1 }

rcIpv6InterfaceIdentifier OBJECT-TYPE
        SYNTAX        Ipv6AddressIfIdentifier
        MAX-ACCESS    read-create
        STATUS        current
        DESCRIPTION   "IPv6 address
                       interface identifiers. This is a binary string
                       of up to 8 octets in network byte-order."
        ::= { rcIpv6InterfaceEntry 2 }

rcIpv6InterfaceIdentifierLength OBJECT-TYPE
        SYNTAX        INTEGER (0..64)
        UNITS         "bits"
        MAX-ACCESS    read-create
        STATUS        current
        DESCRIPTION
                      "The length of the Interface Identifier in bits."
        ::= { rcIpv6InterfaceEntry 3 }

rcIpv6InterfaceDescr OBJECT-TYPE
        SYNTAX        DisplayString (SIZE (0..255))
        MAX-ACCESS    read-create
        STATUS        current
        DESCRIPTION   "A textual string containing information about the
                      interface. This string may be set by network management system."
        ::= { rcIpv6InterfaceEntry 4 }

rcIpv6InterfaceVlanId OBJECT-TYPE
        SYNTAX        INTEGER (1..4094)
        MAX-ACCESS    read-create
        STATUS        current
        DESCRIPTION   "A value that uniquely identifies the Virtual LAN
                      associated with this entry. This value corresponds
                      to the lower 12 bits in the IEEE 802.1Q VLAN Tag."
        ::= { rcIpv6InterfaceEntry 5 }

rcIpv6InterfaceType OBJECT-TYPE
        SYNTAX        INTEGER {
                      ethernet(1),
                      pointToPoint(2),
                      pointToMultipoint(3),
                      loopback(4)
                      }
        MAX-ACCESS    read-create
        STATUS        current
        DESCRIPTION   "The interface type. Only ethernet and loopback values are configurable."
        ::= { rcIpv6InterfaceEntry 6 }

rcIpv6InterfaceReasmMaxSize    OBJECT-TYPE
        SYNTAX        INTEGER (1280..9600)
        MAX-ACCESS    read-create
        STATUS        current
        DESCRIPTION   "MTU for this IPv6 interface, this value should
                       be same for all the ip addresses defined on
                       this interface."
        DEFVAL        { 1500 }
        ::= { rcIpv6InterfaceEntry 7 }

rcIpv6InterfacePhysAddress    OBJECT-TYPE
        SYNTAX        PhysAddress
        MAX-ACCESS    read-only
        STATUS        current
        DESCRIPTION   "The media-dependent `physical' address, for the
                       ethernet media it is the MAC address"
        ::= { rcIpv6InterfaceEntry 8 }

rcIpv6InterfaceAdminStatus OBJECT-TYPE
        SYNTAX        TruthValue
        MAX-ACCESS    read-create
        STATUS        current
        DESCRIPTION   "The indication of whether IPv6 is enabled (up)
             or disabled (down) on this interface. This object does not
             affect the state of the interface itself, only its
             connection to an IPv6 stack."
        DEFVAL        { false }
        ::= { rcIpv6InterfaceEntry 9 }

rcIpv6InterfaceOperStatus OBJECT-TYPE
        SYNTAX        INTEGER {
                        up(1),
                        down(2)
                      }
        MAX-ACCESS    read-only
        STATUS        current
        DESCRIPTION   "Operating status of the interface."
        ::= { rcIpv6InterfaceEntry 10 }

rcIpv6InterfaceReachableTime  OBJECT-TYPE
    SYNTAX     INTEGER (1..3600000)
    MAX-ACCESS read-create
    STATUS     current
    DESCRIPTION
           "The time (in milliseconds) a neighbor is considered
            reachable after receiving a reachability confirmation.
            REFERENCE  RFC2461, Section 6.3.2"
    DEFVAL        { 30000 }
        ::= { rcIpv6InterfaceEntry 11 }

rcIpv6InterfaceRetransmitTime OBJECT-TYPE
    SYNTAX     INTEGER (0..3600000)
    MAX-ACCESS read-create
    STATUS     deprecated
    DESCRIPTION
           "The time (in milliseconds) between retransmissions of
            Neighbor Solicitation messages to a neighbor when
            resolving the address or when probing the reachability
            of a neighbor. REFERENCE RFC2461, Section 6.3.2"
    DEFVAL        { 1000 }
        ::= { rcIpv6InterfaceEntry 12 }

rcIpv6InterfaceMulticastAdminStatus OBJECT-TYPE
        SYNTAX        TruthValue
        MAX-ACCESS    read-create
        STATUS        current
        DESCRIPTION   "This indicates the admin status for multicast
                       for this interface."
        DEFVAL        { false }
        ::= { rcIpv6InterfaceEntry 13 }

rcIpv6InterfaceRowStatus OBJECT-TYPE
        SYNTAX        RowStatus
        MAX-ACCESS    read-create
        STATUS        current
        DESCRIPTION   "Row status for create/delete."
        ::= { rcIpv6InterfaceEntry 14 }

rcIpv6InterfaceDhcpEnabled  OBJECT-TYPE
        SYNTAX        TruthValue
        MAX-ACCESS    read-create
        STATUS        current
        DESCRIPTION   "Enable or disable DHCP on the specified
                      interface."
        DEFVAL        {false}
        ::= { rcIpv6InterfaceEntry 15 }

rcIpv6InterfaceMacOffset OBJECT-TYPE
        SYNTAX        Integer32 (0..65535)
        MAX-ACCESS    read-create
        STATUS        current
        DESCRIPTION   "Used to request a particular MAC for an IPv6 VLAN. Analogous to
                       rcIpAdEntMacOffset in rcIpAddrTable.
                       The system has 512 mac addresses of which 0-507 are reserved for
                       Boardwalk box. 508-511 is reserved for MG. One can either
                       mention a mac offset while configuring IPv6 on a vlan or it can
                       be alloted by the system within the above range."
        ::= { rcIpv6InterfaceEntry 16 }

rcIpv6InterfaceRetransmitTimer OBJECT-TYPE
       SYNTAX     	Unsigned32 (1..4294967295)
       MAX-ACCESS    	read-create
       STATUS        	current
       DESCRIPTION   	"The time (in milliseconds) between retransmissions of
	                Neighbor Solicitation messages to a neighbor when
			resolving the address or when probing the reachability
			of a neighbor. REFERENCE RFC2461, Section 6.3.2"
       DEFVAL        	{ 1000 }
       ::= { rcIpv6InterfaceEntry 17 }

rcIpv6InterfaceCurHopLimit OBJECT-TYPE
        SYNTAX        Integer32 (1..255)
        MAX-ACCESS    read-create
        STATUS        current
        DESCRIPTION
           "The default value to be placed in the current hop limit
            field in router advertisements sent from this interface.
            The value should be set to the current diameter of the
            Internet.

            The default should be set to the value specified in the IANA
            web pages (www.iana.org) at the time of implementation.
            REFERENCE RFC2461 Section 6.2.1"

        DEFVAL        { 30 }
        ::= {  rcIpv6InterfaceEntry 18 }

--
-- 19 is available
--

rcIpv6InterfaceClearIcmpStats  OBJECT-TYPE
       SYNTAX         TruthValue
       MAX-ACCESS     read-create
       STATUS         current
       DESCRIPTION    "Clear ICMP statistics for an interface"
       DEFVAL             {false}
       ::= { rcIpv6InterfaceEntry 20 }

rcIpv6InterfaceClearGeneralStats  OBJECT-TYPE
       SYNTAX         TruthValue
       MAX-ACCESS     read-create
       STATUS         current
       DESCRIPTION    "Clear general statistics for an interface"
       DEFVAL             {false}
       ::= { rcIpv6InterfaceEntry 21 }

rcIpv6InterfaceClearNeighborCache  OBJECT-TYPE
       SYNTAX         TruthValue
       MAX-ACCESS     read-create
       STATUS         current
       DESCRIPTION    "Clear Neighbor Cache for an interface"
       DEFVAL             {false}
       ::= { rcIpv6InterfaceEntry 22 }

rcIpv6InterfaceClearDestinationCache  OBJECT-TYPE
       SYNTAX         TruthValue
       MAX-ACCESS     read-create
       STATUS         current
       DESCRIPTION    "Clear Destination Cache for an interface"
       DEFVAL             {false}
       ::= { rcIpv6InterfaceEntry 23 }

rcIpv6InterfaceReversePathCheckEnable OBJECT-TYPE
        SYNTAX        TruthValue
        MAX-ACCESS    read-create
        STATUS        current
        DESCRIPTION   "Used to indicate whether this interface should
                      perform Reverse Path Check"
        DEFVAL        { false }
        ::= { rcIpv6InterfaceEntry 24 }

rcIpv6InterfaceReversePathCheckMode OBJECT-TYPE
        SYNTAX   INTEGER    {
                    existonly (1),
                    strict (2)
                  }
        MAX-ACCESS    read-create
        STATUS        current
        DESCRIPTION   "Reverse Path Checking mode."
        DEFVAL        { existonly }
        ::= { rcIpv6InterfaceEntry 25 }

rcIpv6InterfaceForwardingEnabled OBJECT-TYPE
        SYNTAX        TruthValue
        MAX-ACCESS    read-create
        STATUS        current
        DESCRIPTION   "Used to indicate whether this interface should
                      perform forwarding"
        DEFVAL        { true }
        ::= { rcIpv6InterfaceEntry 26}

rcIpv6InterfaceRsmltEnable OBJECT-TYPE
        SYNTAX        TruthValue
        MAX-ACCESS    read-create
        STATUS        current
        DESCRIPTION   "Used to indicate whether this interface has
                      rsmlt enabled or not"
        DEFVAL        { false }
        ::= { rcIpv6InterfaceEntry 27 }

rcIpv6InterfaceBfdEnable OBJECT-TYPE
        SYNTAX        TruthValue
        MAX-ACCESS    read-create
        STATUS        current
        DESCRIPTION   "Used to indicate whether this interface has
                      BFD enabled or not"
        DEFVAL        { false }
        ::= { rcIpv6InterfaceEntry 28 }

rcIpv6InterfaceProcessRedirect OBJECT-TYPE
        SYNTAX        TruthValue
        MAX-ACCESS    read-create
        STATUS        current
        DESCRIPTION   "Used to indicate whether this interface has
                      ProcessRedirect enabled or not"
        DEFVAL        { false }
        ::= { rcIpv6InterfaceEntry 29 }

rcIpv6InterfaceIpsecEnable OBJECT-TYPE
        SYNTAX        TruthValue
        MAX-ACCESS    read-create
        STATUS        current
        DESCRIPTION   "Used to indicate whether this interface has
                      IPSec enabled or disabled"
        DEFVAL        { false }
        ::= { rcIpv6InterfaceEntry 30 }


-- End of IPv6 Interface Table
-- IPv6 Address Table

rcIpv6AddressTable OBJECT-TYPE
    SYNTAX     SEQUENCE OF RcIpv6AddressEntry
    MAX-ACCESS not-accessible
    STATUS     current
    DESCRIPTION
           "This table contains addressing information relevant
            to the entity's interfaces.

            This table does not contain multicast address
            information. Tables for such information should be
            contained in multicast specific MIBs such as RFC3019.

            While this table is writable the user will note that several
            objects, such as rcIpv6AddressOrigin, are not. The
            intention in allowing a user to write to this table is to
            allow them to add or remove any entry that isn't permanent.
            The user should be  allowed to modify objects and entries
            when that would not cause inconsistencies within the table.
            Allowing write access to objects such as rcIpv6AddressOrigin
            could allow a user to insert an entry and then label it
            incorrectly."
    ::= { rcIpv6Objects 3 }


rcIpv6AddressEntry OBJECT-TYPE
    SYNTAX     RcIpv6AddressEntry
    MAX-ACCESS not-accessible
    STATUS     current
    DESCRIPTION
           "An address mapping for a particular interface. Note that
            when an address is added to an interface the resulted
            prefix is added to that interface."
    INDEX { rcIpv6AddressIfIndex, rcIpv6AddressAddr }
    ::= { rcIpv6AddressTable 1 }

RcIpv6AddressEntry ::= SEQUENCE {
        rcIpv6AddressIfIndex         InterfaceIndex,
        rcIpv6AddressAddr            Ipv6Address,
        rcIpv6AddressType            INTEGER,
        rcIpv6AddressPrefixLength    INTEGER,
        rcIpv6AddressPrefix          RowPointer,
        rcIpv6AddressOrigin          IpAddressOriginTC,
        rcIpv6AddressStatus          IpAddressStatusTC,
        rcIpv6AddressCreated         TimeStamp,
        rcIpv6AddressLastChanged     TimeStamp,
        rcIpv6AddressRowStatus       RowStatus,
        rcIpv6AddressValidLifetime   Unsigned32,
        rcIpv6AddressPrefLifetime    Unsigned32,
        rcIpv6AddressIfType          INTEGER,
        rcIpv6AddressName            DisplayString
    }

rcIpv6AddressIfIndex OBJECT-TYPE
    SYNTAX     InterfaceIndex
    MAX-ACCESS not-accessible
    STATUS     current
    DESCRIPTION
           "The index value which uniquely identifies the interface to
            which this entry is applicable.  The interface identified by
            a particular value of this index is the same interface as
            identified by the same value of the IfIndex field in the
            rcIpv6InterfaceIfIndex."
    ::= { rcIpv6AddressEntry 1 }

rcIpv6AddressAddr OBJECT-TYPE
    SYNTAX     Ipv6Address
    MAX-ACCESS not-accessible
    STATUS     current
    DESCRIPTION
           "The IPv6 address to which this entry's addressing
            information pertains. This is one of the ipv6 addresses that
            this interface(identified by the rcIpv6AddressIfIndex) has.

            Implementors need to be aware that if the size of
            ipAddressAddr exceeds 116 octets then OIDS of instances of
            columns in this row will have more than 128 sub-identifiers
            and cannot be accessed using SNMPv1, SNMPv2c or SNMPv3."
    ::= { rcIpv6AddressEntry 2 }

rcIpv6AddressType OBJECT-TYPE
    SYNTAX     INTEGER {
                 unicast(1),
                 anycast(2)
    }
    MAX-ACCESS read-create
    STATUS     current
    DESCRIPTION
           "The type of address.  It is either unicast or anycast
            IPv6 addresses (RFC3513).  "
    DEFVAL { unicast }
    ::= { rcIpv6AddressEntry 3 }

rcIpv6AddressPrefixLength OBJECT-TYPE
    SYNTAX     INTEGER (0..128)
    MAX-ACCESS read-create
    STATUS     current
    DESCRIPTION
           "Prefix Length value for this address. Cannot be changed
            after the creation. This field MUST be provided in order
            to create an entry in this table."
    ::= { rcIpv6AddressEntry 4 }

rcIpv6AddressPrefix OBJECT-TYPE
    SYNTAX     RowPointer
    MAX-ACCESS read-only
    STATUS     current
    DESCRIPTION
           "A pointer to the row in the prefix table to which this
            address belongs.  May be { 0 0 } if there is no such row."
    ::= { rcIpv6AddressEntry 5 }

rcIpv6AddressOrigin OBJECT-TYPE
    SYNTAX     IpAddressOriginTC
    MAX-ACCESS read-only
    STATUS     current
    DESCRIPTION
           "The origin of the address. The origin of the address, one
            of: other(1),manual(2), dhcp(4),linklayer(5), random(6)"
    ::= { rcIpv6AddressEntry 6 }

rcIpv6AddressStatus OBJECT-TYPE
    SYNTAX     IpAddressStatusTC
    MAX-ACCESS read-only
    STATUS     current
    DESCRIPTION
           "The status of the address, describing if the address can be
            used for communication. It will One of: preferred(1),
            deprecated(2),invalid(3),inaccessible(4),unknown(5),
            tentative(6), duplicate(7)"
    DEFVAL { preferred }
    ::= { rcIpv6AddressEntry 7 }

rcIpv6AddressCreated OBJECT-TYPE
    SYNTAX     TimeStamp
    MAX-ACCESS read-only
    STATUS     current
    DESCRIPTION "The value of sysUpTime at the time this entry was
            created.  If this entry was created prior to the last re-
            initialization of the local network management subsystem,
            then this object contains a zero value."
    ::= { rcIpv6AddressEntry 8 }

rcIpv6AddressLastChanged OBJECT-TYPE
    SYNTAX     TimeStamp
    MAX-ACCESS read-only
    STATUS     current
    DESCRIPTION
           "The value of sysUpTime at the time this entry was last
            updated.  If this entry was updated prior to the last re-
            initialization of the local network management subsystem,
            then this object contains a zero value."
    ::= { rcIpv6AddressEntry 9 }

rcIpv6AddressRowStatus OBJECT-TYPE
    SYNTAX     RowStatus
    MAX-ACCESS read-create
    STATUS     current
    DESCRIPTION "The status of this conceptual row.
            The RowStatus TC requires that this DESCRIPTION clause
            states under which circumstances other objects in this row
            can be modified.  The value of this object has no effect on
            whether other objects in this conceptual row can be
            modified.
            A conceptual row can not be made active until the
            rcIpv6AddressIfIndex has been set to a valid index. Only
            createAndGo and Delete vlaues are supported. "
    ::= { rcIpv6AddressEntry 10 }

rcIpv6AddressValidLifetime OBJECT-TYPE
    SYNTAX      Unsigned32  (0..4294967295)
    MAX-ACCESS  read-only
    STATUS      current
    DESCRIPTION "Valid lifetime in seconds, indicates
                 how long this address is valid.
                 A result of 4294967295 means infinite"
   ::= { rcIpv6AddressEntry 11 }

rcIpv6AddressPrefLifetime OBJECT-TYPE
    SYNTAX      Unsigned32  (0..4294967295)
    MAX-ACCESS  read-only
    STATUS      current
    DESCRIPTION "Preferred lifetime in seconds, indicates
                 how long this address is in use and not deprecated.
                 A result of 4294967295 means infinite"
   ::= { rcIpv6AddressEntry 12 }

rcIpv6AddressIfType   OBJECT-TYPE
    SYNTAX      INTEGER {
                    circuitLessIP(1),
                    brouterPort(2),
                    vlan(3),
		    mgmtOob(4),
		    mgmtClip(5),
		    mgmtVlan(6)
                }
    MAX-ACCESS  read-only
    STATUS      current
    DESCRIPTION "The address entry IfType indicates the type of the
     		 interface. In the case of circuit-less-IP there is
                 no association with any ports. In other words, it can
                 be thought of as a virtual interface. The value
                 'brouter port' indicates this interface is associated
                 with a specific physical port. The value 'vlan'
                 indicates a logical port that contains one or physical
                 ports/MLT ports. The value 'mgmtOob' is for the out of
		 band mgmt port.  The value 'mgmtClip' is for the
		 designated management clip. The value 'mgmtVlan' is for
		 the designated management vlan."
    ::= { rcIpv6AddressEntry 13 }

rcIpv6AddressName OBJECT-TYPE
    SYNTAX      DisplayString (SIZE (0..64))
    MAX-ACCESS  read-create
    STATUS      current
    DESCRIPTION "The administratively assignmed name for this address."
    ::= { rcIpv6AddressEntry 14 }


-- Neighbor Discovery Prefix Table

rcIpv6PrefixTable  OBJECT-TYPE
        SYNTAX          SEQUENCE OF RcIpv6PrefixEntry
        MAX-ACCESS      not-accessible
        STATUS          current
        DESCRIPTION     "This table allows the user to
            determine the source of an IP address or set of
            IP addresses and allows other tables to
            share the information via pointer rather than by copying.

            For example when the node configures both a unicast and
            anycast address for a prefix the ipAddressPrefix objects for
            those addresses will point to a single row in this table.


            This table primarily provides support for IPv6 prefixes and
            several of the objects are less meaningful for IPv4.  The
            table continues to allow IPv4 addresses to allow future
            flexibility.  In order to promote a common configuration
            this document includes suggestions for default values for
            IPv4 prefixes.  Each of these values may be overridden if an
            object is meaningful to the node.


            All prefixes used by this entity should be included in this
            table independent of how the entity learned the prefix.
            (This table isn't limited to prefixes learned from router
            advertisements.)  "
        ::= { rcIpv6Objects 4 }

rcIpv6PrefixEntry OBJECT-TYPE
        SYNTAX          RcIpv6PrefixEntry
        MAX-ACCESS      not-accessible
        STATUS          current
        DESCRIPTION     "An entry of ipv6 prefix In the Table."
        INDEX           { rcIpv6PrefixIfIndex,
                          rcIpv6PrefixAddr,
                          rcIpv6PrefixLength }
        ::= { rcIpv6PrefixTable 1 }

RcIpv6PrefixEntry ::=
        SEQUENCE {
                  rcIpv6PrefixIfIndex         InterfaceIndex,
                  rcIpv6PrefixAddr            Ipv6Address,
                  rcIpv6PrefixLength          INTEGER,
                  rcIpv6PrefixVlanId          INTEGER,
                  rcIpv6PrefixUseDefaultVal   INTEGER,
                  rcIpv6PrefixValidLife       Integer32,
                  rcIpv6PrefixPreferredLife   Integer32,
                  rcIpv6PrefixAtValidLife     DateAndTime,
                  rcIpv6PrefixAtPreferredLife DateAndTime,
                  rcIpv6PrefixInfinite        TruthValue,
                  rcIpv6PrefixOnLinkFlag      TruthValue,
                  rcIpv6PrefixAutoFlag        TruthValue,
                  rcIpv6PrefixAddressEui      INTEGER,
                  rcIpv6PrefixNoAdvertise     TruthValue,
                  rcIpv6PrefixRowStatus       RowStatus,
                  rcIpv6PrefixValidLifetime   Unsigned32,
                  rcIpv6PrefixPreferredLifetime Unsigned32
                 }

rcIpv6PrefixIfIndex OBJECT-TYPE
        SYNTAX        InterfaceIndex
        MAX-ACCESS    not-accessible
        STATUS        current
        DESCRIPTION   "An unique value to identify an ipv6 interface.
                       For the brouter port it is the ifindex of the
                       port and in the case of the vlan it is the
                       ifindex of the vlan."
        ::= { rcIpv6PrefixEntry 1 }

rcIpv6PrefixAddr OBJECT-TYPE
        SYNTAX        Ipv6Address
        MAX-ACCESS    not-accessible
        STATUS        current
        DESCRIPTION   "Prefix to create an ipv6 address in ipv6 interface
                       table."
        ::= { rcIpv6PrefixEntry 2 }

rcIpv6PrefixLength OBJECT-TYPE
        SYNTAX        INTEGER (0..128)
        MAX-ACCESS    not-accessible
        STATUS        current
        DESCRIPTION   "Mask to create an ipv6 prefix entry
                       either will be advertised or suppressed"
        ::= { rcIpv6PrefixEntry 3 }

rcIpv6PrefixVlanId OBJECT-TYPE
        SYNTAX        INTEGER (1..4094)
        MAX-ACCESS    read-only
        STATUS        current
        DESCRIPTION   "A value that uniquely identifies the Virtual LAN
                      associated with this entry. This value corresponds
                      to the lower 12 bits in the IEEE 802.1Q VLAN Tag."
        ::= { rcIpv6PrefixEntry 4 }


rcIpv6PrefixUseDefaultVal   OBJECT-TYPE
       SYNTAX        INTEGER {
                         none(1),
                         valid-life(2),
                         preferred-life(3),
                         infinite(4),
                         no-advertise(5)
                      }
        MAX-ACCESS    read-create
        STATUS        current
        DESCRIPTION   "Select one of the value to set/use it's value
                      to default value. This is a bitmask field,
                      setting all the bits means that all the options
                      will be reverted to default values."
        ::= { rcIpv6PrefixEntry 5 }

rcIpv6PrefixValidLife OBJECT-TYPE
        SYNTAX        Integer32(0..3600000)
        MAX-ACCESS    read-create
        STATUS        current
        DESCRIPTION   "Valid lifetime in seconds, indicates
                      how long this prefix advertised in
                      the nbr advertisement is valid."
        DEFVAL        { 2592000 }
        ::= { rcIpv6PrefixEntry 6 }

rcIpv6PrefixPreferredLife OBJECT-TYPE
        SYNTAX        Integer32(0..3600000)
        MAX-ACCESS    read-create
        STATUS        current
        DESCRIPTION   "Preferred lifetime in seconds, indicates
                      how long this prefix advertised in
                      advertisemt for this prefix."
        DEFVAL        { 604800 }
        ::= { rcIpv6PrefixEntry 7 }

rcIpv6PrefixAtValidLife OBJECT-TYPE
        SYNTAX        DateAndTime
        MAX-ACCESS    read-create
        STATUS        current
        DESCRIPTION   "Is the date and time, upon reaching this
                      value the prefix will be expired,
                      if configured this option will
                      be included in the neighbor advertisement
                      for this prefix."
        ::= { rcIpv6PrefixEntry 8 }

rcIpv6PrefixAtPreferredLife OBJECT-TYPE
        SYNTAX        DateAndTime
        MAX-ACCESS    read-create
        STATUS        current
        DESCRIPTION   "Is the date and time, upon reaching this
                      value the prefix will be expired,
                      if configured this option will be
                      included in the neighbor advertisement
                      for this prefix."
        ::= { rcIpv6PrefixEntry 9 }

rcIpv6PrefixInfinite OBJECT-TYPE
        SYNTAX        TruthValue
        MAX-ACCESS    read-create
        STATUS        current
        DESCRIPTION   "if set the prefix's valid lifetime will
                      not exprie."
        DEFVAL        { false }
        ::= { rcIpv6PrefixEntry 10 }

rcIpv6PrefixOnLinkFlag OBJECT-TYPE
        SYNTAX        TruthValue
        MAX-ACCESS    read-create
        STATUS        current
        DESCRIPTION   "if set then this prefix can be used
                      for onlink determination. This value
                      be placed in the L-bit field in the prefix
                      information option. It is a 1 bit flag. "
        DEFVAL        { true }
        ::= { rcIpv6PrefixEntry 11 }

rcIpv6PrefixAutoFlag OBJECT-TYPE
        SYNTAX        TruthValue
        MAX-ACCESS    read-create
        STATUS        current
        DESCRIPTION   "if set then this prefix can be used
                      for autonomous address config. This value
                      be placed in the auto-flag field in the prefix
                      information option. It is a 1 bit flag. "
        DEFVAL        { true }
        ::= { rcIpv6PrefixEntry 12 }

rcIpv6PrefixAddressEui OBJECT-TYPE
        SYNTAX     INTEGER {
                            eui-not-used(1),
                            eui-used-with-ul-complement(2),
                            eui-used-without-ul-complement(3)
                       }
        MAX-ACCESS    read-create
        STATUS        current
        DESCRIPTION   "Use an EUI-64 interface ID in the low-order
                       64bits of the address when not specified in the address field.
                       If enabled use EUI, otherwise use EUI-64 and complement U/L
                       (Universal/Local bit). This operation should
                       be allowed for both global and link local
                       addresses. Once the entry is  create cannot modify this field.
                       This will be valid to use only when the PrefixLength is 64 or less"
        DEFVAL        { eui-not-used }
        ::= { rcIpv6PrefixEntry 13 }

rcIpv6PrefixNoAdvertise OBJECT-TYPE
        SYNTAX        TruthValue
        MAX-ACCESS    read-create
        STATUS        current
        DESCRIPTION   "if set then this prefix can not be included
                      in the neighbor advertisement."
        DEFVAL        { false }
        ::= { rcIpv6PrefixEntry 14 }

rcIpv6PrefixRowStatus OBJECT-TYPE
        SYNTAX        RowStatus
        MAX-ACCESS    read-create
        STATUS        current
        DESCRIPTION   "Row status for create/delete."
        ::= { rcIpv6PrefixEntry 15 }

rcIpv6PrefixValidLifetime OBJECT-TYPE
        SYNTAX        Unsigned32 (0..4294967295)
        MAX-ACCESS    read-create
        STATUS        current
        DESCRIPTION   "Valid lifetime in seconds, indicates
                      how long this prefix advertised in
                      the nbr advertisement is valid.
                      Value of 4294967295 represents infinity."
        DEFVAL        { 2592000 }
        ::= { rcIpv6PrefixEntry 16 }

rcIpv6PrefixPreferredLifetime OBJECT-TYPE
        SYNTAX        Unsigned32 (0..4294967295)
        MAX-ACCESS    read-create
        STATUS        current
        DESCRIPTION   "Preferred lifetime in seconds, indicates
                      how long this prefix advertised in
                      advertisemt for this prefix.
                      Value of 4294967295 represents infinity."
        DEFVAL        { 604800 }
        ::= { rcIpv6PrefixEntry 17 }

-- IPV6 Neighbor Discovery Route Advertisement Table

rcIpv6RouterAdvertTable  OBJECT-TYPE
        SYNTAX          SEQUENCE OF  RcIpv6RouterAdvertEntry
        MAX-ACCESS      not-accessible
        STATUS          current
        DESCRIPTION     "The table containing information
               used to construct router advertisements."
        ::= { rcIpv6Objects 5 }

rcIpv6RouterAdvertEntry OBJECT-TYPE
        SYNTAX          RcIpv6RouterAdvertEntry
        MAX-ACCESS      not-accessible
        STATUS          current
        DESCRIPTION
           "An entry containing information used to construct
            router advertisements."
        INDEX  { rcIpv6RouterAdvertIfIndex }
        ::= { rcIpv6RouterAdvertTable 1 }

RcIpv6RouterAdvertEntry ::=
        SEQUENCE {
                rcIpv6RouterAdvertIfIndex       InterfaceIndex,
                rcIpv6RouterAdvertSendAdverts   TruthValue,
                rcIpv6RouterAdvertUseDefaultVal INTEGER,
                rcIpv6RouterAdvertMaxInterval   INTEGER,
                rcIpv6RouterAdvertMinInterval   INTEGER,
                rcIpv6RouterAdvertReachableTime INTEGER,
                rcIpv6RouterAdvertRetransmitTimer  INTEGER,
                rcIpv6RouterAdvertDefaultLifeTime  INTEGER,
                rcIpv6RouterAdvertCurHopLimit      INTEGER,
                rcIpv6RouterAdvertManagedFlag      TruthValue,
                rcIpv6RouterAdvertOtherConfigFlag  TruthValue,
                rcIpv6RouterAdvertDadNsNum         INTEGER,
                rcIpv6RouterAdvertLinkMTU          Unsigned32,
		rcIpv6RouterAdvertRetransmitTime   Unsigned32
                 }

rcIpv6RouterAdvertIfIndex OBJECT-TYPE
        SYNTAX        InterfaceIndex
        MAX-ACCESS    not-accessible
        STATUS        current
        DESCRIPTION   "An unique value to identify an ipv6 interface.
                       For the brouter port it is the ifindex of the
                       port and in the case of the vlan it is the
                       ifindex of the vlan."
        ::= {  rcIpv6RouterAdvertEntry 1 }

rcIpv6RouterAdvertSendAdverts OBJECT-TYPE
    SYNTAX     TruthValue
    MAX-ACCESS read-write
    STATUS     current
    DESCRIPTION
           "A flag indicating whether or not the router sends periodic
            router advertisements and responds to router solicitations
            on this interface. REFERENCE RFC2461 Section 6.2.1"
    DEFVAL { false }
        ::= {  rcIpv6RouterAdvertEntry 2 }

rcIpv6RouterAdvertUseDefaultVal   OBJECT-TYPE
       SYNTAX        INTEGER {
                      none(1),
                      send-advertisement(2),
                      max-interval(3),
                      min-interval(4),
                      default-life-time(5),
                      hop-limit(6),
                      managed-flag(7),
                      other-config-flag(8),
                      dad-ns-num(9),
		      linkMtu(10),
                      reachableTime(11),
		      retransmitTime(12)
                  }
        MAX-ACCESS    read-write
        STATUS        current
        DESCRIPTION   "Select one of the value to set/use it's
                       value to default value, or set all the bits
                       to indicate all the options will be set to
                       their default value."
        ::= {  rcIpv6RouterAdvertEntry 3 }

rcIpv6RouterAdvertMaxInterval OBJECT-TYPE
        SYNTAX        INTEGER (4..1800)
        MAX-ACCESS    read-write
        STATUS        current
        DESCRIPTION   "Configure the max interval (in seconds)
                      at which the transmission of route
                      advertisments can occur on this interface.
                      This must be no less than 4 seconds and
                      no greater than 1800."
         DEFVAL        { 600 }
        ::= {  rcIpv6RouterAdvertEntry 4 }

 rcIpv6RouterAdvertMinInterval OBJECT-TYPE
        SYNTAX        INTEGER (3..1350)
        MAX-ACCESS    read-write
        STATUS        current
        DESCRIPTION   "Configure the min interval (in seconds)
                      at which the transmission of route
                      advertisments can occur on this interface.
                      This must be no less than 3 seconds and
                      no greater than .75* max-interval."
        DEFVAL        { 200 }
        ::= {  rcIpv6RouterAdvertEntry 5 }

 rcIpv6RouterAdvertReachableTime OBJECT-TYPE
        SYNTAX        INTEGER (0..36000000)
        MAX-ACCESS    read-write
        STATUS        current
        DESCRIPTION   "The value (in milliseconds) to be placed                               in the router advertisement message
                      sent by the router. The value zero means
                      unspecified (by this router). Used to
                      configure the amount of time that a remote
                      IPv6 node is considered reachable after
                      some reachability confirmation event has
                      occured.
                      REFERENCE RFC2461 Section 6.2.1"
        ::= {  rcIpv6RouterAdvertEntry 6 }

rcIpv6RouterAdvertRetransmitTimer OBJECT-TYPE
        SYNTAX        INTEGER (0..36000000)
        MAX-ACCESS    read-only
        STATUS        deprecated
        DESCRIPTION   "The value (in milliseconds) to be placed                               in the retransmit timer field in router
                      advertisement message sent from this
                      interface. The value zero means
                      unspecified (by this router). Used to
                      configure the amount of time that router
                      should wait for the transmit to occur.
                      REFERENCE RFC2461 Section 6.2.1"
        ::= {  rcIpv6RouterAdvertEntry 7 }

rcIpv6RouterAdvertDefaultLifeTime OBJECT-TYPE
        SYNTAX        INTEGER (0|4..9000)
        MAX-ACCESS    read-write
        STATUS        current
        DESCRIPTION
           "The value to be placed in the router lifetime field of
            router advertisements sent from this interface.  This value
            MUST be either 0 or between rcIpv6RouterAdvertMaxInterval and
            9000 seconds.


            A value of zero indicates that the router is not to be used
            as a default router.

            The default is 3 * rcIpv6RouterAdvertMaxInterval.
            REFERENCE RFC2461 Section 6.2.1"
        DEFVAL        { 1800 }
        ::= {  rcIpv6RouterAdvertEntry 8 }

rcIpv6RouterAdvertCurHopLimit OBJECT-TYPE
        SYNTAX        INTEGER (0..255)
        MAX-ACCESS    read-write
        STATUS        current
        DESCRIPTION
           "The default value to be placed in the current hop limit
            field in router advertisements sent from this interface.
            The value should be set to the current diameter of the
            Internet.

            A value of zero in the router advertisement indicates that
            the advertisement isn't specifying a value for curHopLimit.

            The default should be set to the value specified in the IANA
            web pages (www.iana.org) at the time of implementation.
            REFERENCE RFC2461 Section 6.2.1"

        DEFVAL        { 30 }
        ::= {  rcIpv6RouterAdvertEntry 9 }

rcIpv6RouterAdvertManagedFlag OBJECT-TYPE
        SYNTAX        TruthValue
        MAX-ACCESS    read-write
        STATUS        current
        DESCRIPTION   "if true then the M-bit(Managed address
                      configureation)  in the router
                      adverisement will be set.
                      REFERENCE RFC2461 Section 6.2.1"
        DEFVAL        { false }
        ::= {  rcIpv6RouterAdvertEntry 10 }

rcIpv6RouterAdvertOtherConfigFlag OBJECT-TYPE
        SYNTAX        TruthValue
        MAX-ACCESS    read-write
        STATUS        current
        DESCRIPTION   "if true then the O-bit (Other stateful
                      Configuration) in the router
                      adverisement will be set. REFERENCE
                      RFC2461 Section 6.2.1"
        DEFVAL        { false }
        ::= {  rcIpv6RouterAdvertEntry 11 }

rcIpv6RouterAdvertDadNsNum OBJECT-TYPE
        SYNTAX        INTEGER (0..600)
        MAX-ACCESS    read-write
        STATUS        current
        DESCRIPTION   "The number of neighbor solicitation
                      messages for DAD (Duplicate address
                      detection). A value 0 is used to disable
                      DAD process on this interface. A value 1
                      is used to send one advertisment without
                      any retransmissions."
        ::= {  rcIpv6RouterAdvertEntry 12 }

rcIpv6RouterAdvertLinkMTU OBJECT-TYPE
    SYNTAX     Unsigned32 (0 | 1280..1500 | 1850 | 9500)
    MAX-ACCESS read-only
    STATUS     current
    DESCRIPTION
           "The value to be placed in MTU options sent by the
            router on this interface.  A value of zero
            indicates that no MTU options are sent. REFERENCE
            RFC2461 Section 6.2.1"
    ::= { rcIpv6RouterAdvertEntry 13 }

rcIpv6RouterAdvertRetransmitTime OBJECT-TYPE
        SYNTAX        Unsigned32 (0..4294967295)
        MAX-ACCESS    read-write
        STATUS        current
        DESCRIPTION   "The value (in milliseconds) to be placed                               in the retransmit timer field in router
                      advertisement message sent from this
                      interface. The value zero means
                      unspecified (by this router). Used to
                      configure the amount of time that router
                      should wait for the transmit to occur.
                      REFERENCE RFC2461 Section 6.2.1.
           	      Use this object to replace
		      rcIpv6RouterAdvertRetransmitTimer"
        ::= {  rcIpv6RouterAdvertEntry 14 }

-- IPV6 Static Route Table

rcIpv6StaticRouteTable OBJECT-TYPE
        SYNTAX          SEQUENCE OF RcIpv6StaticRouteEntry
        MAX-ACCESS      not-accessible
        STATUS          current
        DESCRIPTION     "This table contains list of routes that are
                         created by the user to destination networks."
        ::= { rcIpv6Objects 6 }

rcIpv6StaticRouteEntry OBJECT-TYPE
        SYNTAX          RcIpv6StaticRouteEntry
        MAX-ACCESS      not-accessible
        STATUS          current
        DESCRIPTION     "An entry in the static route table for IPv6
                         can be created for a destination with a specific
                         prefix length; multiple entries to the same
                         destination are created either by specifying the
                         next-hop or interfaceIndex or both to reach the destination.
                         However if the nexthop Ipv6 address is a link-local
                         address then IfIndex must be supplied."
        INDEX           { rcIpv6StaticRouteDest,
                          rcIpv6StaticRoutePrefixLength,
                          rcIpv6StaticRouteNextHop,
                          rcIpv6StaticRouteIfIndex }
        ::= { rcIpv6StaticRouteTable 1 }

RcIpv6StaticRouteEntry ::=
        SEQUENCE {
                  rcIpv6StaticRouteDest                  Ipv6Address,
                  rcIpv6StaticRoutePrefixLength          INTEGER,
                  rcIpv6StaticRouteNextHop               Ipv6Address,
                  rcIpv6StaticRouteIfIndex               InterfaceIndex,
                  rcIpv6StaticRouteDistance              INTEGER,
                  rcIpv6StaticRouteEnable                TruthValue,
                  rcIpv6StaticRouteStatus                INTEGER,
                  rcIpv6StaticRoutePreference            INTEGER,
                  rcIpv6StaticRouteRowStatus             RowStatus,
		  rcIpv6StaticRouteName			 DisplayString
                 }

rcIpv6StaticRouteDest OBJECT-TYPE
        SYNTAX        Ipv6Address
        MAX-ACCESS    not-accessible
        STATUS        current
        DESCRIPTION   "The destination IPv6 address of this route.
                The values for the index objects rcIpv6StaticRouteDest and
                rcIpv6StaticRoutePrefixLength must be consistent.  When
                the value of rcIpv6StaticRouteDest (excluding the zone
                index, if one is present) is x, then the bitwise
                logical-AND of x with the value of the mask formed from
                the corresponding index object
                rcIpv6StaticRoutePrefixLength MUST be equal to x. If
                not, then the index pair is not consistent and an
                inconsistentName error must be returned on SET or
                CREATE requests."

        ::= { rcIpv6StaticRouteEntry 1 }

rcIpv6StaticRoutePrefixLength OBJECT-TYPE
        SYNTAX        INTEGER (0..128)
        MAX-ACCESS    not-accessible
        STATUS        current
        DESCRIPTION   "Indicates the number of leading one bits which
                form the mask to be logical-ANDed with the destination
                address before being compared to the value in the
                rcIpv6StaticRouteDestAddr field."
        ::= { rcIpv6StaticRouteEntry 2 }

rcIpv6StaticRouteNextHop OBJECT-TYPE
        SYNTAX        Ipv6Address
        MAX-ACCESS    not-accessible
        STATUS        current
        DESCRIPTION   "Next hop IPv6 address for this destination.
                On remote routes, the address of the next system en
                route.  For non-remote routes, a zero length string. "
        ::= { rcIpv6StaticRouteEntry 3 }

rcIpv6StaticRouteIfIndex OBJECT-TYPE
        SYNTAX        InterfaceIndex
        MAX-ACCESS    not-accessible
        STATUS        current
        DESCRIPTION   "The ifIndex value which identifies the local
                interface through which the next hop of this route
                should be reached.  A value of 0 is valid and
                represents the scenario where no interface is specified."
        ::= { rcIpv6StaticRouteEntry 4 }

rcIpv6StaticRouteDistance OBJECT-TYPE
        SYNTAX        INTEGER (1..65535 )
        MAX-ACCESS    read-create
        STATUS        current
        DESCRIPTION   "cost/distance to reach the destination for this
                      node."
        DEFVAL        { 1 }
        ::= { rcIpv6StaticRouteEntry 5 }

rcIpv6StaticRouteStatus OBJECT-TYPE
       SYNTAX          INTEGER {
                         notReachable(1),
                         tryToResolve(2),
                         reachableNotInRtm(3),
                         reachableInRtm(4)
                       }
        MAX-ACCESS      read-only
        STATUS        	current
        DESCRIPTION   	"Used to indicate the current status of entry in routing table.
			 1. notReachable means the route is unreachable via
				the specified next hop.
			 2. tryToResolve means the route's nexthop address
				requires resolution by sending neighbour solicit message.
			 3. reachableNotInRtm means the route is reachable via the
				 specified next hop. It's the alternative route.
			 4. reachableInRtm means the route is reachable via the specified
			         next hop and best route. "
        ::= { rcIpv6StaticRouteEntry 6 }

rcIpv6StaticRoutePreference OBJECT-TYPE
        SYNTAX        INTEGER (1..255)
        MAX-ACCESS    read-create
        STATUS        current
        DESCRIPTION   "Used to indicate the route preference of this
                      entry.  If there are more than one route that can
                      be used to forward IP traffic, the route that has
                      a highest preference will be used instead of a
                      lower preference one. The higher the number,
                      the higher the preference."
        DEFVAL        { 5 }
        ::= { rcIpv6StaticRouteEntry 7 }

rcIpv6StaticRouteEnable OBJECT-TYPE
        SYNTAX         	TruthValue
        MAX-ACCESS     	read-create
        STATUS         	current
        DESCRIPTION    	"Used to enable/disable this entry."
	    DEFVAL        { true }
        ::= { rcIpv6StaticRouteEntry 8 }

rcIpv6StaticRouteRowStatus OBJECT-TYPE
        SYNTAX        RowStatus
        MAX-ACCESS    read-create
        STATUS        current
        DESCRIPTION   "Row status for create/delete."
        ::= { rcIpv6StaticRouteEntry 9 }

rcIpv6StaticRouteName OBJECT-TYPE
        SYNTAX        DisplayString (SIZE (0..64))
        MAX-ACCESS    read-create
        STATUS        current
        DESCRIPTION   "An administratively-assigned name for this static route"
        ::= { rcIpv6StaticRouteEntry 10 }

-- IPV6 Management Port Static Route Table

rcIpv6MgmtPortStaticRouteTable OBJECT-TYPE
        SYNTAX          SEQUENCE OF RcIpv6MgmtPortStaticRouteEntry
        MAX-ACCESS      not-accessible
        STATUS          current
        DESCRIPTION     "This table contains list of routes that are
                         created by the user to destination networks
			 on the management port."
        ::= { rcIpv6Objects 12 }

rcIpv6MgmtPortStaticRouteEntry OBJECT-TYPE
        SYNTAX          RcIpv6MgmtPortStaticRouteEntry
        MAX-ACCESS      not-accessible
        STATUS          current
        DESCRIPTION     "An entry in the static route table for IPv6
                         can be created for a destination with a specific
                         prefix length; multiple entries to the same
                         destination are created either by specifying the
                         next-hop or interfaceIndex or both to reach the destination.
                         However if the nexthop Ipv6 address is a link-local
                         address then IfIndex must be supplied."
        INDEX           { rcIpv6MgmtPortStaticRouteIfIndex,
			  rcIpv6MgmtPortStaticRouteDest,
                          rcIpv6MgmtPortStaticRoutePrefixLength,
                          rcIpv6MgmtPortStaticRouteNextHop }
        ::= { rcIpv6MgmtPortStaticRouteTable 1 }

RcIpv6MgmtPortStaticRouteEntry ::=
        SEQUENCE {
                  rcIpv6MgmtPortStaticRouteIfIndex	InterfaceIndex,
                  rcIpv6MgmtPortStaticRouteDest		Ipv6Address,
                  rcIpv6MgmtPortStaticRoutePrefixLength	Integer32,
                  rcIpv6MgmtPortStaticRouteNextHop	Ipv6Address,
                  rcIpv6MgmtPortStaticRouteDistance	Integer32,
                  rcIpv6MgmtPortStaticRouteEnable	TruthValue,
                  rcIpv6MgmtPortStaticRouteStatus	INTEGER,
                  rcIpv6MgmtPortStaticRoutePreference	Integer32,
                  rcIpv6MgmtPortStaticRouteRowStatus	RowStatus
                 }

rcIpv6MgmtPortStaticRouteIfIndex OBJECT-TYPE
        SYNTAX        InterfaceIndex
        MAX-ACCESS    not-accessible
        STATUS        current
        DESCRIPTION   "The ifIndex value which identifies the local
                interface through which the next hop of this route
                should be reached.  A value of 0 is valid and
                represents the scenario where no interface is specified."
        ::= { rcIpv6MgmtPortStaticRouteEntry 1 }

rcIpv6MgmtPortStaticRouteDest OBJECT-TYPE
        SYNTAX        Ipv6Address
        MAX-ACCESS    not-accessible
        STATUS        current
        DESCRIPTION   "The destination IPv6 address of this route.
                The values for the index objects rcIpv6StaticRouteDest and
                rcIpv6StaticRoutePrefixLength must be consistent.  When
                the value of rcIpv6StaticRouteDest (excluding the zone
                index, if one is present) is x, then the bitwise
                logical-AND of x with the value of the mask formed from
                the corresponding index object
                rcIpv6StaticRoutePrefixLength MUST be equal to x. If
                not, then the index pair is not consistent and an
                inconsistentName error must be returned on SET or
                CREATE requests."

        ::= { rcIpv6MgmtPortStaticRouteEntry 2 }

rcIpv6MgmtPortStaticRoutePrefixLength OBJECT-TYPE
        SYNTAX        Integer32 (0..128)
        MAX-ACCESS    not-accessible
        STATUS        current
        DESCRIPTION   "Indicates the number of leading one bits which
                form the mask to be logical-ANDed with the destination
                address before being compared to the value in the
                rcIpv6MgmtPortStaticRouteDestAddr field."
        ::= { rcIpv6MgmtPortStaticRouteEntry 3 }

rcIpv6MgmtPortStaticRouteNextHop OBJECT-TYPE
        SYNTAX        Ipv6Address
        MAX-ACCESS    not-accessible
        STATUS        current
        DESCRIPTION   "Next hop IPv6 address for this destination.
                On remote routes, the address of the next system en
                route.  For non-remote routes, a zero length string. "
        ::= { rcIpv6MgmtPortStaticRouteEntry 4 }

rcIpv6MgmtPortStaticRouteDistance OBJECT-TYPE
        SYNTAX        Integer32 (1..65535 )
        MAX-ACCESS    read-create
        STATUS        current
        DESCRIPTION   "cost/distance to reach the destination for this
                      node."
        DEFVAL        { 1 }
        ::= { rcIpv6MgmtPortStaticRouteEntry 5 }

rcIpv6MgmtPortStaticRouteStatus OBJECT-TYPE
       SYNTAX          INTEGER {
                         notReachable(1),
                         tryToResolve(2),
                         reachableNotInRtm(3),
                         reachableInRtm(4)
                       }
        MAX-ACCESS      read-only
        STATUS        	current
        DESCRIPTION   	"(1)notReachable means the route is not reachable and no
                            neighbor request entry is built to resolved the next-hop.
                            It happens when there is no route or neighbor to reach
                            the static route's next-hop.
                         (2)tryToResolve means the route is not reachable but a
                            neighbor request entry is built to resolved the next-hop.
                            It happens when there is a local equivelent route in system to
                            reach the next-hop but the neighor is not learnt yet
                         (3)reachableNotInRtm means the static route is
                            reachable but it is not in RTM. It happens when the static
                            route is reachable, but it is not the best among alternative
                            static route.
                         (4)reachableInRtm means the static route is reachable
                            and it is in RTM. It happens when the static
                            route is reachable, and it is the best among alternative
                            static route to be added into RTM. "
        ::= { rcIpv6MgmtPortStaticRouteEntry 6 }

rcIpv6MgmtPortStaticRoutePreference OBJECT-TYPE
        SYNTAX        Integer32 (1..255)
        MAX-ACCESS    read-create
        STATUS        current
        DESCRIPTION   "Used to indicate the route preference of this
                      entry.  If there are more than one route that can
                      be used to forward IP traffic, the route that has
                      a highest preference will be used instead of a
                      lower preference one. The higher the number,
                      the higher the preference."
        DEFVAL        { 5 }
        ::= { rcIpv6MgmtPortStaticRouteEntry 7 }

rcIpv6MgmtPortStaticRouteEnable OBJECT-TYPE
        SYNTAX         	TruthValue
        MAX-ACCESS     	read-create
        STATUS         	current
        DESCRIPTION    	"Used to enable/disable this entry."
	    DEFVAL        { true }
        ::= { rcIpv6MgmtPortStaticRouteEntry 8 }


rcIpv6MgmtPortStaticRouteRowStatus OBJECT-TYPE
        SYNTAX        RowStatus
        MAX-ACCESS    read-create
        STATUS        current
        DESCRIPTION   "Row status for create/delete."
        ::= { rcIpv6MgmtPortStaticRouteEntry 9 }

--
-- the Internet Address Translation table
--

rcIpv6NetToPhysicalTable OBJECT-TYPE
    SYNTAX     SEQUENCE OF RcIpv6NetToPhysicalEntry
    MAX-ACCESS not-accessible
    STATUS     current
    DESCRIPTION
           "The IP Address Translation table used for mapping from IP
            addresses to physical addresses.

            The Address Translation tables contain the IP address to
            'physical' address equivalences.  Some interfaces do not use
            translation tables for determining address equivalences
            (e.g., DDN-X.25 has an algorithmic method); if all
            interfaces are of this type, then the Address Translation
            table is empty, i.e., has zero entries.

            While many protocols may be used to populate this table, ARP
            [10] and Neighbor Discovery [4] are the most likely
            options."
    REFERENCE "RFC0826 and RFC2461"
    ::= { rcIpv6Objects 7 }

rcIpv6NetToPhysicalEntry OBJECT-TYPE
    SYNTAX     RcIpv6NetToPhysicalEntry
    MAX-ACCESS not-accessible
    STATUS     current
    DESCRIPTION
           "Each entry contains one IP address to `physical' address
            equivalence."
    INDEX       { rcIpv6NetToPhysicalIfIndex,
                  rcIpv6NetToPhysicalNetAddress }
    ::= { rcIpv6NetToPhysicalTable 1 }

RcIpv6NetToPhysicalEntry ::= SEQUENCE {
        rcIpv6NetToPhysicalIfIndex         InterfaceIndex,
        rcIpv6NetToPhysicalNetAddress      Ipv6Address,
        rcIpv6NetToPhysicalPhysAddress     PhysAddress,
        rcIpv6NetToPhysicalInterface       Integer32,
        rcIpv6NetToPhysicalLastUpdated     TimeStamp,
        rcIpv6NetToPhysicalType            INTEGER,
        rcIpv6NetToPhysicalState           INTEGER,
        rcIpv6NetToPhysicalRowStatus       RowStatus,
	rcIpv6NetToPhysicalBMac            MacAddress,
	rcIpv6NetToPhysicalCvid            Integer32
    }

rcIpv6NetToPhysicalIfIndex OBJECT-TYPE
    SYNTAX     InterfaceIndex
    MAX-ACCESS not-accessible
    STATUS     current
    DESCRIPTION
           "The index value which uniquely identifies the interface to
            which this entry is applicable.  The interface identified by
            a particular value of this index is the same interface as
            identified by the same value of the IfIndex field in the
            rcIpv6InterfaceIfIndex."
    ::= { rcIpv6NetToPhysicalEntry 1 }

rcIpv6NetToPhysicalNetAddress OBJECT-TYPE
    SYNTAX     Ipv6Address
    MAX-ACCESS not-accessible
    STATUS     current
    DESCRIPTION
           "The IP Address corresponding to the media-dependent
            `physical' address.  The address type of this object is
            specified in rcIpv6NetToPhysicalAddressType.


            Implementors need to be aware that if the size of
            rcIpv6NetToPhysicalNetAddress exceeds 115 octets then OIDS of
            instances of columns in this row will have more than 128
            sub-identifiers and cannot be accessed using SNMPv1, SNMPv2c
            or SNMPv3."
    ::= { rcIpv6NetToPhysicalEntry 2 }

rcIpv6NetToPhysicalPhysAddress OBJECT-TYPE
    SYNTAX     PhysAddress (SIZE(0..65535))
    MAX-ACCESS read-create
    STATUS     current
    DESCRIPTION
           "The media-dependent `physical' address.

            As the entries in this table are typically not persistent
            when this object is written the entity SHOULD NOT save the
            change to non-volatile storage. In the ethernet case
            it is a MAC address."
    ::= { rcIpv6NetToPhysicalEntry 3 }

rcIpv6NetToPhysicalInterface            OBJECT-TYPE
    SYNTAX     Integer32
    MAX-ACCESS read-create
    STATUS     current
    DESCRIPTION
           "The field represents either a physical port id or the MLT
            port id. This entry is associated either with
            a port or with a MLT in a VLAN/Brouter port. If the value is
            0 then the interface is CP port."
    ::= { rcIpv6NetToPhysicalEntry 4 }

rcIpv6NetToPhysicalLastUpdated OBJECT-TYPE
    SYNTAX     TimeStamp
    MAX-ACCESS read-only
    STATUS     current
    DESCRIPTION
           "The value of sysUpTime at the time this entry was last
            updated.  If this entry was updated prior to the last re-
            initialization of the local network management subsystem,
            then this object contains a zero value."
    ::= { rcIpv6NetToPhysicalEntry 5 }

rcIpv6NetToPhysicalType OBJECT-TYPE
    SYNTAX     INTEGER {
                other(1),        -- none of the following
                dynamic(2),
                static(3),
                local(4)         -- local interface
            }
    MAX-ACCESS read-create
    STATUS     current
    DESCRIPTION
           "The type of mapping.

            The 'dynamic(2)' type indicates that the IP address to
            physical addresses mapping has been dynamically resolved
            using e.g. IPv4 ARP or the IPv6 Neighbor Discovery protocol.

            The 'static(3)' type indicates that the mapping has been
            statically configured.  Both of these refer to entries that
            provide mappings for other entities addresses.

            The 'local(4)' type indicates that the mapping is provided
            for an entity's own interface address.

            As the entries in this table are typically not persistent
            when this object is written the entity SHOULD NOT save the
            change to non-volatile storage."
    DEFVAL { static }
    ::= { rcIpv6NetToPhysicalEntry 6 }

rcIpv6NetToPhysicalState OBJECT-TYPE
    SYNTAX     INTEGER {
                     reachable(1), -- confirmed reachability

                     stale(2),     -- unconfirmed reachability

                     delay(3),     -- waiting for reachability
                                   -- confirmation before entering
                                   -- the probe state

                     probe(4),     -- actively probing

                     invalid(5),   -- an invalidated mapping

                     unknown(6),   -- state can not be determined
                                   -- for some reason.

                     incomplete(7) -- address resolution is being performed.
                    }
    MAX-ACCESS read-only
    STATUS     current
    DESCRIPTION
           "The Neighbor Unreachability Detection [4] state for the
            interface when the address mapping in this entry is used.
            If Neighbor Unreachability Detection is not in use (eg. for
            IPv4), this object is always unknown(6).
            REFERENCE RFC2461"
    ::= { rcIpv6NetToPhysicalEntry 8 }

rcIpv6NetToPhysicalRowStatus OBJECT-TYPE
    SYNTAX     RowStatus
    MAX-ACCESS read-create
    STATUS     current
    DESCRIPTION
           "The status of this conceptual row.

            The RowStatus TC requires that this DESCRIPTION clause
            states under which circumstances other objects in this row
            can be modified.  The value of this object has no effect on
            whether other objects in this conceptual row can be
            modified.

            A conceptual row can not be made active until the
            rcIpv6NetToPhysicalPhysAddress object has been set.
            Note that if the rcIpv6NetToPhysicalType is set to
'invalid' the
            managed node may delete the entry independent of the state
            of this object. Only createandGo and Delete operations are
            supported"
    ::= { rcIpv6NetToPhysicalEntry 9 }

rcIpv6NetToPhysicalBMac OBJECT-TYPE
    SYNTAX          MacAddress
    MAX-ACCESS      read-only
    STATUS          current
    DESCRIPTION
           "If the rcIpv6NetToPhysicalEntry is learned from a
           SPBM network, instead of using port to track where the
           rcIpv6NetToPhysicalNetAddress come from, the backbone
           MAC address is used to track that."
    ::= { rcIpv6NetToPhysicalEntry 10 }

rcIpv6NetToPhysicalCvid OBJECT-TYPE
        SYNTAX        Integer32 (1..4096)
        MAX-ACCESS    read-only
        STATUS        current
        DESCRIPTION   "Used to identify customer vid of the switched uni port
                      of this entry is associated with. 4095 is not used. 4096
                      is reserved for untagged case."
    ::= { rcIpv6NetToPhysicalEntry 11 }

rcIpv6PrefixListTable OBJECT-TYPE
        SYNTAX          SEQUENCE OF RcIpv6PrefixListEntry
        MAX-ACCESS      not-accessible
        STATUS          current
        DESCRIPTION     "IPv6 Prefix List table"
        ::= { rcIpv6Objects 8 }

rcIpv6PrefixListEntry OBJECT-TYPE
        SYNTAX          RcIpv6PrefixListEntry
        MAX-ACCESS      not-accessible
        STATUS          current
        DESCRIPTION     "An entry of Ipv6 Prefix List Table."
        INDEX           { rcIpv6PrefixListId,
                          rcIpv6PrefixListPrefix,
                          rcIpv6PrefixListPrefixMaskLen }
        ::= { rcIpv6PrefixListTable 1 }

RcIpv6PrefixListEntry ::=
        SEQUENCE {
                rcIpv6PrefixListId               Unsigned32,
                rcIpv6PrefixListPrefix           Ipv6Address,
                rcIpv6PrefixListPrefixMaskLen    Unsigned32,
                rcIpv6PrefixListMaskLenFrom      Unsigned32,
                rcIpv6PrefixListMaskLenUpto      Unsigned32,
                rcIpv6PrefixListName             SnmpAdminString,
                rcIpv6PrefixListRowStatus        RowStatus
        }

rcIpv6PrefixListId OBJECT-TYPE
        SYNTAX        Unsigned32 (0..2147483647)
        MAX-ACCESS    not-accessible
        STATUS        current
        DESCRIPTION   "Id of an IPv6 Prefix List"
        ::= { rcIpv6PrefixListEntry 1 }

rcIpv6PrefixListPrefix OBJECT-TYPE
        SYNTAX        Ipv6Address
        MAX-ACCESS    not-accessible
        STATUS        current
        DESCRIPTION   "Is a member of a specific ipv6 prefix list.
                       Adding the prefix to the given ipv6 prefix list"
        ::= { rcIpv6PrefixListEntry 2 }

rcIpv6PrefixListPrefixMaskLen OBJECT-TYPE
        SYNTAX        Unsigned32 (0..128)
        MAX-ACCESS    not-accessible
        STATUS        current
        DESCRIPTION   "Mask length of the ipv6 prefix added to the prefix list"
        ::= { rcIpv6PrefixListEntry 3 }

rcIpv6PrefixListMaskLenFrom OBJECT-TYPE
        SYNTAX        Unsigned32 (0..128)
        MAX-ACCESS    read-create
        STATUS        current
        DESCRIPTION   "Lower bound of mask length of the ipv6 prefix added
                       to the prefix list"
        ::= { rcIpv6PrefixListEntry 4 }

rcIpv6PrefixListMaskLenUpto OBJECT-TYPE
        SYNTAX        Unsigned32 (0..128)
        MAX-ACCESS    read-create
        STATUS        current
        DESCRIPTION   "Higher bound of mask length of the ipv6 prefix added
                       to the prefix list"
        ::= { rcIpv6PrefixListEntry 5 }

rcIpv6PrefixListName OBJECT-TYPE
        SYNTAX        SnmpAdminString (SIZE(1..64))
        MAX-ACCESS    read-create
        STATUS        current
        DESCRIPTION   "Name of the Ipv6 prefix list"
        ::= { rcIpv6PrefixListEntry 6 }

rcIpv6PrefixListRowStatus OBJECT-TYPE
        SYNTAX        RowStatus
        MAX-ACCESS    read-create
        STATUS        current
        DESCRIPTION   "Used to create/delete entries in the ipv6 prefix list table"
        ::= { rcIpv6PrefixListEntry 7 }

--BEGIN OF DHCP RELAY FOR IPV6

rcIpv6ConfDhcpRelayTable OBJECT-TYPE
        SYNTAX             SEQUENCE OF RcIpv6ConfDhcpRelayEntry
        MAX-ACCESS     not-accessible
        STATUS              current
        DESCRIPTION     "DHCP Relay for Ipv6 configuration table"
    ::= { rcIpv6Objects  9 }

rcIpv6ConfDhcpRelayEntry OBJECT-TYPE
        SYNTAX        	RcIpv6ConfDhcpRelayEntry
        MAX-ACCESS   not-accessible
        STATUS        	current
        DESCRIPTION  	"Used to configure DHCP on a particular L3 interface.  An
		entry is created automatically when the variable
		rcIpv6InterfaceDhcpEnabled is set to TRUE.
	      	Once created this entry will only be deleted if the
                 	rcIpv6ConfDhcpRowStatus is set to 'destroy(6)'.  In
	      	which case, the rcIpv6InterfaceDhcpEnabled is automatically
	      	reset to the FALSE setting."
        INDEX         	{ rcIpv6ConfDhcpIfIndex }
        ::= { rcIpv6ConfDhcpRelayTable 1 }

RcIpv6ConfDhcpRelayEntry ::=
        SEQUENCE {
                rcIpv6ConfDhcpIfIndex                 InterfaceIndex,
                rcIpv6ConfDhcpMaxHop    	      Unsigned32,
                rcIpv6ConfDhcpRemoteIdEnabled  TruthValue,
                rcIpv6ConfDhcpNumRequests       Counter32,
                rcIpv6ConfDhcpNumReplies	      Counter32,
                rcIpv6ConfDhcpRowStatus 	      RowStatus
        }

rcIpv6ConfDhcpIfIndex OBJECT-TYPE
        SYNTAX        	InterfaceIndex
        MAX-ACCESS      not-accessible
        STATUS        	current
        DESCRIPTION  	"Interface number.  The number can represent either
		a physical or logical(VLAN) interface."
        ::= { rcIpv6ConfDhcpRelayEntry 1 }

rcIpv6ConfDhcpMaxHop OBJECT-TYPE
        SYNTAX        	Unsigned32  (1..32)
        MAX-ACCESS   read-create
        STATUS        	current
        DESCRIPTION  	"Used to indicate the maximum number of hops a
		DHCP packet can take from the source device to
		the destination device (i.e., DHCP client to
		DHCP server)."
        DEFVAL        	{ 32 }
        ::= { rcIpv6ConfDhcpRelayEntry 2 }

rcIpv6ConfDhcpRemoteIdEnabled OBJECT-TYPE
        SYNTAX        	TruthValue
        MAX-ACCESS   read-create
        STATUS        	current
        DESCRIPTION  	"Used to indicate if remote-id option is enabled."
        DEFVAL	{ false }
        ::= { rcIpv6ConfDhcpRelayEntry 3 }

rcIpv6ConfDhcpNumRequests OBJECT-TYPE
        SYNTAX        	Counter32
        MAX-ACCESS   read-only
        STATUS        	current
        DESCRIPTION  	"The total number of DHCP requests seen on this interface."
        ::= { rcIpv6ConfDhcpRelayEntry 4 }

rcIpv6ConfDhcpNumReplies OBJECT-TYPE
        SYNTAX           	Counter32
        MAX-ACCESS   read-only
        STATUS        	current
        DESCRIPTION  	"The total number of DHCP replies seen on this interface."
        ::= { rcIpv6ConfDhcpRelayEntry 5 }

rcIpv6ConfDhcpRowStatus OBJECT-TYPE
        SYNTAX        	RowStatus
        MAX-ACCESS   read-create
        STATUS        	current
        DESCRIPTION   "An entry is created automatically when the variable
                      	rcIpv6InterfaceDhcpEnabled is set to TRUE.
                      	Once created this entry will only be deleted if the
                      	rcIpv6ConfDhcpRowStatus is set to 'destroy(6)',  In
                      	which case, the rcIpv6InterfaceDhcpEnabled is automatically
                      	reset to the FALSE setting."
        ::= { rcIpv6ConfDhcpRelayEntry 6 }

rcIpv6DhcpForwardTable OBJECT-TYPE
        SYNTAX	  SEQUENCE OF RcIpv6DhcpForwardEntry
        MAX-ACCESS     not-accessible
        STATUS        	  current
        DESCRIPTION     "DHCP Relay forwarding table."
    ::= { rcIpv6Objects  10 }

rcIpv6DhcpForwardEntry OBJECT-TYPE
        SYNTAX        	RcIpv6DhcpForwardEntry
        MAX-ACCESS  	not-accessible
        STATUS        	current
        DESCRIPTION   "An entry used represents a DHCP Relayed message forwarding directive."
        INDEX         	{ rcIpv6DhcpForwardAgentAddr, rcIpv6DhcpForwardServerAddr }
        ::= { rcIpv6DhcpForwardTable 1 }

RcIpv6DhcpForwardEntry ::=
        SEQUENCE {
                rcIpv6DhcpForwardAgentAddr   Ipv6Address,
                rcIpv6DhcpForwardServerAddr  Ipv6Address,
                rcIpv6DhcpForwardEnabled      TruthValue,
                rcIpv6DhcpForwardRowStatus   RowStatus
        }

rcIpv6DhcpForwardAgentAddr OBJECT-TYPE
        SYNTAX        	Ipv6Address
        MAX-ACCESS   not-accessible
        STATUS        	current
        DESCRIPTION   "The IP address configured on an interface
                      	(i.e., a locally configured IP address)."
        ::= { rcIpv6DhcpForwardEntry 1 }

rcIpv6DhcpForwardServerAddr OBJECT-TYPE
        SYNTAX        	Ipv6Address
        MAX-ACCESS   not-accessible
        STATUS        	current
        DESCRIPTION   "The IP address of the DHCP server.  If this
	              	IP address corresponds to a local interface address, the DHCP packet is multicast out
       	      	the interface the IP address is assigned to.otherwise,the DHCP packet is sent via unicast to the remote device."
        ::= { rcIpv6DhcpForwardEntry 2 }

rcIpv6DhcpForwardEnabled OBJECT-TYPE
        SYNTAX        	TruthValue
        MAX-ACCESS   read-create
        STATUS        	current
        DESCRIPTION  	"Used to indicate whether the entry should be used."
        DEFVAL        	{ true }
        ::= { rcIpv6DhcpForwardEntry 3 }

rcIpv6DhcpForwardRowStatus OBJECT-TYPE
        SYNTAX        	RowStatus
        MAX-ACCESS   read-create
        STATUS        	current
        DESCRIPTION  	"Row status of this entry."
        ::= { rcIpv6DhcpForwardEntry 4 }

--END OF DHCP RELAY FOR IPV6

-- BEGIN OF IPV6 DESTINATION CACHE SECTION

rcIpv6DestinationCacheTable OBJECT-TYPE
        SYNTAX          SEQUENCE OF RcIpv6DestinationCacheEntry
        MAX-ACCESS      not-accessible
        STATUS          current
        DESCRIPTION     "Ipv6 Destination Cache table"
    ::= { rcIpv6Objects  13 }

rcIpv6DestinationCacheEntry OBJECT-TYPE
        SYNTAX          RcIpv6DestinationCacheEntry
        MAX-ACCESS      not-accessible
        STATUS          current
        DESCRIPTION     "Used to display Destination Cache"
        INDEX           { rcIpv6DCacheDestAddr, rcIpv6DCacheIfIndex }
        ::= { rcIpv6DestinationCacheTable 1 }

RcIpv6DestinationCacheEntry ::=
        SEQUENCE {
                rcIpv6DCacheDestAddr              Ipv6Address,
                rcIpv6DCacheIfIndex               Unsigned32,
                rcIpv6DCacheNextHop               Ipv6Address,
                rcIpv6DCacheIfType                INTEGER,
                rcIpv6DCacheIfData                DisplayString,
                rcIpv6DCachePmtu                  Integer32,
                rcIpv6DCachePmtuAge               Counter32
        }

rcIpv6DCacheDestAddr OBJECT-TYPE
        SYNTAX          Ipv6Address
        MAX-ACCESS      not-accessible
        STATUS          current
        DESCRIPTION     "IPv6 Destination Address from the
                         Destination Cache."
        ::= { rcIpv6DestinationCacheEntry 1 }

rcIpv6DCacheIfIndex OBJECT-TYPE
        SYNTAX          Unsigned32
        MAX-ACCESS      not-accessible
        STATUS          current
        DESCRIPTION     "The last 16 bits of this object's value are
	                 interpreted as InterfaceIndex (it can represent
			 either a physical, or a VLAN, or a tunnel
			 interface); the first 16 bits are ignored when
			 the object's value is interpreted."
        ::= { rcIpv6DestinationCacheEntry 2 }

rcIpv6DCacheNextHop OBJECT-TYPE
        SYNTAX          Ipv6Address
        MAX-ACCESS      read-only
        STATUS          current
        DESCRIPTION     "Ipv6 Next Hop for a Destination Cache entry."
        ::= { rcIpv6DestinationCacheEntry 3 }

rcIpv6DCacheIfType OBJECT-TYPE
        SYNTAX          INTEGER {real(1), virtual(2)}
        MAX-ACCESS      read-only
        STATUS          current
        DESCRIPTION     "Interface type; it can be a real (i.e.
	                 VLAN, brouter, tunnel) or a virtual
			 circuit (i.e. VRRP, RSMLT)."
        ::= { rcIpv6DestinationCacheEntry 4 }

rcIpv6DCacheIfData OBJECT-TYPE
        SYNTAX        DisplayString (SIZE (0..20))
        MAX-ACCESS    read-only
        STATUS        current
        DESCRIPTION   "Used to display additional information about
	               virtual circuits (i.e. if it is a VRRP or
		       RSMLT circuit, the vrId if it is a VRRP circuit);
		       no information is displayed for real circuits."
        ::= { rcIpv6DestinationCacheEntry 5 }

rcIpv6DCachePmtu OBJECT-TYPE
        SYNTAX        Integer32
        MAX-ACCESS    read-only
        STATUS        current
        DESCRIPTION   "Path MTU for the entry."
        ::= { rcIpv6DestinationCacheEntry 6 }

rcIpv6DCachePmtuAge OBJECT-TYPE
        SYNTAX        Counter32
        MAX-ACCESS    read-only
        STATUS        current
        DESCRIPTION   "Indicates how much time (in seconds) has passed
	               since the PMTU was updated the last time."
        ::= { rcIpv6DestinationCacheEntry 7 }

--END OF IPv6 DESTINATION CACHE SECTION


-- IPv6 Radius Serv Table

rcIpv6RadiusServTable OBJECT-TYPE
        SYNTAX        SEQUENCE OF RcIpv6RadiusServEntry
        MAX-ACCESS    not-accessible
        STATUS        current
        DESCRIPTION   "The RADIUS table (0 to 10 entries).  This
                      table lists the information of the RADIUS server."
        ::= { rcIpv6Objects 11}

rcIpv6RadiusServEntry OBJECT-TYPE
        SYNTAX        RcIpv6RadiusServEntry
        MAX-ACCESS    not-accessible
        STATUS        current
        DESCRIPTION   "A RADIUS server table entry."
        INDEX         { rcIpv6RadiusServAddress,
                        rcIpv6RadiusServUsedBy }
        ::= { rcIpv6RadiusServTable 1 }

RcIpv6RadiusServEntry ::=
        SEQUENCE {
                rcIpv6RadiusServAddress          Ipv6Address,
                rcIpv6RadiusServUsedBy            INTEGER,
                rcIpv6RadiusServPriority            Unsigned32,
                rcIpv6RadiusServTimeOut             Unsigned32,
                rcIpv6RadiusServEnable              TruthValue,
                rcIpv6RadiusServMaxRetries          Unsigned32,
                rcIpv6RadiusServUdpPort             Unsigned32,
                rcIpv6RadiusServSecretKey           SnmpAdminString,
                rcIpv6RadiusServAccessRequests      Counter32,
                rcIpv6RadiusServAccessAccepts       Counter32,
                rcIpv6RadiusServAccessRejects       Counter32,
                rcIpv6RadiusServBadResponses        Counter32,
                rcIpv6RadiusServPendingRequests     Counter32,
                rcIpv6RadiusServClientRetries       Counter32,
                rcIpv6RadiusServAcctEnable          TruthValue,
                rcIpv6RadiusServAcctUdpPort         Unsigned32,
                rcIpv6RadiusServAcctOnRequests      Counter32,
                rcIpv6RadiusServAcctOffRequests     Counter32,
                rcIpv6RadiusServAcctStartRequests   Counter32,
                rcIpv6RadiusServAcctStopRequests    Counter32,
                rcIpv6RadiusServAcctInterimRequests Counter32,
                rcIpv6RadiusServAcctBadResponses    Counter32,
                rcIpv6RadiusServAcctPendingRequests Counter32,
                rcIpv6RadiusServAcctClientRetries   Counter32,
                rcIpv6RadiusServNasIpAddress        Ipv6Address,
                rcIpv6RadiusServRoundTripTime       SnmpAdminString,
                rcIpv6RadiusServAccessChallanges    Counter32,
                rcIpv6RadiusServSourceIpAddr        Ipv6Address,
                rcIpv6RadiusServRowStatus           RowStatus
        }

rcIpv6RadiusServAddress OBJECT-TYPE
        SYNTAX        Ipv6Address
        MAX-ACCESS    not-accessible
        STATUS        current
        DESCRIPTION   "Server IP address of the RADIUS authentication server
                       referred to in this table entry."
        ::= { rcIpv6RadiusServEntry 1 }

rcIpv6RadiusServUsedBy OBJECT-TYPE
        SYNTAX        INTEGER {
                         cli(1),
                         igap(2),
                         snmp(3),
                         eap(4),
			 web(5)
                      }
        MAX-ACCESS    not-accessible
        STATUS        current
        DESCRIPTION   "cli(1): for cli login, igap(2): for igap,snmp(3):
                       for snmp login, eap(4) for EAP PAE Authenticator,
		       web(5) for EDM."
        ::= { rcIpv6RadiusServEntry 2 }

rcIpv6RadiusServPriority OBJECT-TYPE
        SYNTAX        Unsigned32 (1..10)
        MAX-ACCESS    read-create
        STATUS        current
        DESCRIPTION   "Server priority, used to control which server to choose
                       first to send authentication."
        DEFVAL        { 10 }
        ::= { rcIpv6RadiusServEntry 3 }

rcIpv6RadiusServTimeOut OBJECT-TYPE
        SYNTAX        Unsigned32 (1..20)
        MAX-ACCESS    read-create
        STATUS        current
        DESCRIPTION   "The time interval in seconds before the client
                       retransmit the packet."
        DEFVAL        { 3 }
        ::= { rcIpv6RadiusServEntry 4 }

rcIpv6RadiusServEnable  OBJECT-TYPE
        SYNTAX        TruthValue
        MAX-ACCESS    read-create
        STATUS        current
        DESCRIPTION   "Enable or disable this server."
        DEFVAL        { true }
        ::= { rcIpv6RadiusServEntry 5 }

rcIpv6RadiusServMaxRetries OBJECT-TYPE
        SYNTAX        Unsigned32 (0..6)
        MAX-ACCESS    read-create
        STATUS        current
        DESCRIPTION   "Maximum number of retransmissions."
        DEFVAL        { 1 }
        ::= { rcIpv6RadiusServEntry 6 }

rcIpv6RadiusServUdpPort OBJECT-TYPE
        SYNTAX        Unsigned32 (1..65536)
        MAX-ACCESS    read-create
        STATUS        current
        DESCRIPTION   "The UDP port the client is using to send requests
                       to this server."
        DEFVAL        { 1812 }
        ::= { rcIpv6RadiusServEntry 7 }

rcIpv6RadiusServSecretKey OBJECT-TYPE
        SYNTAX        SnmpAdminString (SIZE (0..32))
        MAX-ACCESS    read-create
        STATUS        current
        DESCRIPTION   "The identifier of the RADIUS authentication client."
        ::= { rcIpv6RadiusServEntry 8 }

rcIpv6RadiusServAccessRequests OBJECT-TYPE
        SYNTAX          Counter32
        MAX-ACCESS      read-only
        STATUS          current
        DESCRIPTION     "The number of RADIUS access-response packets sent to
                         this server. This does not include retransmissions."
        ::= { rcIpv6RadiusServEntry 9 }

rcIpv6RadiusServAccessAccepts OBJECT-TYPE
        SYNTAX          Counter32
        MAX-ACCESS      read-only
        STATUS          current
        DESCRIPTION     "The number of RADIUS access-accept packets (valid or
                         invalid) received from this server."
        ::= { rcIpv6RadiusServEntry 10 }

rcIpv6RadiusServAccessRejects OBJECT-TYPE
        SYNTAX          Counter32
        MAX-ACCESS      read-only
        STATUS          current
        DESCRIPTION     "The number of RADIUS access-reject packets (valid or
                         invalid) received from this server."
        ::= { rcIpv6RadiusServEntry 11 }

rcIpv6RadiusServBadResponses OBJECT-TYPE
        SYNTAX          Counter32
        MAX-ACCESS      read-only
        STATUS          current
        DESCRIPTION     "The number of RADIUS invalid access-response packets
                         received from this server."
        ::= { rcIpv6RadiusServEntry 12 }

rcIpv6RadiusServPendingRequests OBJECT-TYPE
        SYNTAX          Counter32
        MAX-ACCESS      read-only
        STATUS          current
        DESCRIPTION     "The number of RADIUS access-request packets destined
                         for this server that have not yet timed out or
                         received a response. This variable is incremented
                         when an access-request is sent and decremented due
                         to receipt of an access-accept, access-reject, a
                         timeout or retransmission."
        ::= { rcIpv6RadiusServEntry 13 }

rcIpv6RadiusServClientRetries OBJECT-TYPE
        SYNTAX          Counter32
        MAX-ACCESS      read-only
        STATUS          current
        DESCRIPTION     "The number of authentication retransmission to
                         this server."
        ::= { rcIpv6RadiusServEntry 14}

rcIpv6RadiusServAcctEnable OBJECT-TYPE
        SYNTAX        TruthValue
        MAX-ACCESS    read-create
        STATUS        current
        DESCRIPTION   "Enable or disable Radius Accounting on this server."
        DEFVAL        { true }
        ::= { rcIpv6RadiusServEntry 15 }

rcIpv6RadiusServAcctUdpPort OBJECT-TYPE
        SYNTAX        Unsigned32 (1..65536)
        MAX-ACCESS    read-create
        STATUS        current
        DESCRIPTION   "The UDP port the client used to send accounting
                       requests to this server."
        DEFVAL        { 1813 }
        ::= { rcIpv6RadiusServEntry 16 }

rcIpv6RadiusServAcctOnRequests OBJECT-TYPE
        SYNTAX          Counter32
        MAX-ACCESS      read-only
        STATUS          current
        DESCRIPTION     "The number of RADIUS accounting-on packets sent to
                         this server. This does not include retransmissions."
        ::= { rcIpv6RadiusServEntry 17 }

rcIpv6RadiusServAcctOffRequests OBJECT-TYPE
        SYNTAX          Counter32
        MAX-ACCESS      read-only
        STATUS          current
        DESCRIPTION     "The number of RADIUS accounting-off packets sent to
                         this server. This does not include retransmissions."
        ::= { rcIpv6RadiusServEntry 18 }

rcIpv6RadiusServAcctStartRequests OBJECT-TYPE
        SYNTAX          Counter32
        MAX-ACCESS      read-only
        STATUS          current
        DESCRIPTION     "The number of RADIUS accounting-start packets sent to
                         this server. This does not include retransmissions."
        ::= { rcIpv6RadiusServEntry 19 }

rcIpv6RadiusServAcctStopRequests OBJECT-TYPE
        SYNTAX          Counter32
        MAX-ACCESS      read-only
        STATUS          current
        DESCRIPTION     "The number of RADIUS accounting-stop packets sent to
                         this server. This does not include retransmissions."
        ::= { rcIpv6RadiusServEntry 20 }

rcIpv6RadiusServAcctInterimRequests OBJECT-TYPE
        SYNTAX          Counter32
        MAX-ACCESS      read-only
        STATUS          current
        DESCRIPTION     "The number of RADIUS accounting-interim packets sent to
                         this server. This does not include retransmissions."
        ::= { rcIpv6RadiusServEntry 21 }

rcIpv6RadiusServAcctBadResponses OBJECT-TYPE
        SYNTAX          Counter32
        MAX-ACCESS      read-only
        STATUS          current
        DESCRIPTION     "The number of Invalid responses received from this
                         server."
        ::= { rcIpv6RadiusServEntry 22 }

rcIpv6RadiusServAcctPendingRequests OBJECT-TYPE
        SYNTAX          Counter32
        MAX-ACCESS      read-only
        STATUS          current
        DESCRIPTION     "The number of RADIUS accounting packets that are waiting
                         be sent to this server. This variable is incremented
                         whenever any accounting-request is sent to this server and
                         decremented when an acknowledgement is received or timeout
                         occurs."
        ::= { rcIpv6RadiusServEntry 23 }

rcIpv6RadiusServAcctClientRetries OBJECT-TYPE
        SYNTAX          Counter32
        MAX-ACCESS      read-only
        STATUS          current
        DESCRIPTION     "The number of RADIUS accounting packets retransmitted
                         to this server."
        ::= { rcIpv6RadiusServEntry 24 }

rcIpv6RadiusServNasIpAddress OBJECT-TYPE
        SYNTAX          Ipv6Address
        MAX-ACCESS      read-only
        STATUS          current
        DESCRIPTION     "RADIUS Client NAS Identifier for this server."
        ::= { rcIpv6RadiusServEntry 25 }

rcIpv6RadiusServRoundTripTime OBJECT-TYPE
        SYNTAX          SnmpAdminString (SIZE(0..20))
        MAX-ACCESS      read-only
        STATUS          current
        DESCRIPTION     "Time different between the instance when
                         a RADIUS request is sent and the
                         corresponding response is received."
        ::= { rcIpv6RadiusServEntry 26 }

rcIpv6RadiusServAccessChallanges OBJECT-TYPE
        SYNTAX          Counter32
        MAX-ACCESS      read-only
        STATUS          current
        DESCRIPTION     "The number of RADIUS access-challanges packets
                         sent to this server. This does not include
                         retransmission."
        ::= { rcIpv6RadiusServEntry 27 }

rcIpv6RadiusServSourceIpAddr OBJECT-TYPE
        SYNTAX          Ipv6Address
        MAX-ACCESS      read-create
        STATUS          current
        DESCRIPTION     "source IP address RADIUS packets."
        ::= { rcIpv6RadiusServEntry 28 }

rcIpv6RadiusServRowStatus OBJECT-TYPE
        SYNTAX        RowStatus
        MAX-ACCESS    read-create
        STATUS        current
        DESCRIPTION   "Used to create/delete entries."
        ::= { rcIpv6RadiusServEntry 29 }

-- IPv6 BFD Table

rcIpv6InterfaceBfdTable OBJECT-TYPE
        SYNTAX	      SEQUENCE OF RcIpv6InterfaceBfdEntry
        MAX-ACCESS    not-accessible
        STATUS	      current
        DESCRIPTION   "BFD configuration table"
        ::= { rcIpv6Objects 14 }

rcIpv6InterfaceBfdEntry OBJECT-TYPE
        SYNTAX	      RcIpv6InterfaceBfdEntry
        MAX-ACCESS    not-accessible
        STATUS	      current
        DESCRIPTION   "Used to configure BFD on a particular interface. An
                       entry is created automatically when the variable
                       rcIpv6InterfaceBfdEnable is set to TRUE and deleted when
                       rcIpv6InterfaceBfdEnable is set to FALSE."
        INDEX	      { rcIpv6InterfaceBfdIfIndex }
        ::= { rcIpv6InterfaceBfdTable 1 }

RcIpv6InterfaceBfdEntry ::= SEQUENCE {
                rcIpv6InterfaceBfdIfIndex	      InterfaceIndex,
                rcIpv6InterfaceBfdMinRxInterval  	Integer32,
                rcIpv6InterfaceBfdTxInterval	    	Integer32,
                rcIpv6InterfaceBfdMultiplier	    	Integer32,
                rcIpv6InterfaceBfdHoldOffInterval  	Unsigned32,
                rcIpv6InterfaceBfdStaticFlag       EnableValue,
                rcIpv6InterfaceBfdVrfId                 VrfIdentifier,
                rcIpv6InterfaceBfdVrfName               DisplayString
        }

rcIpv6InterfaceBfdIfIndex OBJECT-TYPE
        SYNTAX        InterfaceIndex
        MAX-ACCESS    not-accessible
        STATUS        current
        DESCRIPTION   "Interface number.  The number can represent either
                       a physical or logical(VLAN) interface."
        ::= { rcIpv6InterfaceBfdEntry 1 }

rcIpv6InterfaceBfdMinRxInterval OBJECT-TYPE
        SYNTAX        Integer32 (100..65535)
        MAX-ACCESS    read-write
        STATUS        current
        DESCRIPTION   "the min rx interval in milliseconds"
        DEFVAL        { 200 }
        ::= { rcIpv6InterfaceBfdEntry 2 }

rcIpv6InterfaceBfdTxInterval	  OBJECT-TYPE
        SYNTAX        Integer32 (100..65535)
        MAX-ACCESS    read-write
        STATUS        current
        DESCRIPTION   "the desired tx interval in milliseconds"
        DEFVAL        { 200 }
        ::= { rcIpv6InterfaceBfdEntry 3 }

rcIpv6InterfaceBfdMultiplier	  OBJECT-TYPE
        SYNTAX        Integer32 (1..20)
        MAX-ACCESS    read-write
        STATUS        current
        DESCRIPTION   "the multiplier BFD wait before rx timeout"
        DEFVAL        { 3 }
        ::= { rcIpv6InterfaceBfdEntry 4 }

rcIpv6InterfaceBfdHoldOffInterval    OBJECT-TYPE
        SYNTAX        Unsigned32 (0..65535)
        MAX-ACCESS    read-write
        STATUS        current
        DESCRIPTION
                "This object specifies the hold off timer interval, in
                seconds. 0 means that hold off timer is disabled."
        DEFVAL        { 0 }
        ::= { rcIpv6InterfaceBfdEntry 6 }

rcIpv6InterfaceBfdStaticFlag  OBJECT-TYPE
        SYNTAX        EnableValue
        MAX-ACCESS    read-write
        STATUS        current
        DESCRIPTION
                "This object specifies the static-flag for bfd. When
                disabled, the static route will go down, when bfd is
		    disabled."
       DEFVAL        { enable }
       ::= { rcIpv6InterfaceBfdEntry 7}

rcIpv6InterfaceBfdVrfId OBJECT-TYPE
        SYNTAX        VrfIdentifier
        MAX-ACCESS    read-write
        STATUS        current
        DESCRIPTION   "Indicates the Virtual Router to which the IPv6 BFD
                       instance belongs."
        ::= { rcIpv6InterfaceBfdEntry 8 }

rcIpv6InterfaceBfdVrfName OBJECT-TYPE
        SYNTAX         DisplayString (SIZE (0..32))
	MAX-ACCESS     read-only
	STATUS         current
	DESCRIPTION    "The Name of the Virtual Router to which the IPv6 BFD
	                    instance belongs."
	::= { rcIpv6InterfaceBfdEntry 9 }

-- IPv6 Route Table

rcIpv6RouteTable OBJECT-TYPE
        SYNTAX          SEQUENCE OF RcIpv6RouteEntry
        MAX-ACCESS      not-accessible
        STATUS          current
        DESCRIPTION     "This entity's IPV6 Routing table."
	::= { rcIpv6Objects  15 }

rcIpv6RouteEntry OBJECT-TYPE
	SYNTAX  	RcIpv6RouteEntry
        MAX-ACCESS  	not-accessible
        STATUS  	current
        DESCRIPTION	"A route to a particular destination."
        INDEX           { rcIpv6RouteDest,
			  rcIpv6RoutePfxLength,
			  rcIpv6RouteIndex }
    	::= { rcIpv6RouteTable 1 }

RcIpv6RouteEntry ::=
	SEQUENCE {
		   rcIpv6RouteDest		Ipv6Address,
               	   rcIpv6RoutePfxLength 	INTEGER,
               	   rcIpv6RouteIndex		Unsigned32,
		   rcIpv6RouteNextHopId         DisplayString
		 }

rcIpv6RouteDest OBJECT-TYPE
 	SYNTAX     Ipv6Address
     	MAX-ACCESS not-accessible
     	STATUS     current
   	DESCRIPTION
       	       "The destination IPv6 address of this route.
       		This object may not take a Multicast address
       		value."
     	::= { rcIpv6RouteEntry 1 }

rcIpv6RoutePfxLength OBJECT-TYPE
     	SYNTAX     INTEGER(0..128)
     	UNITS      "bits"
     	MAX-ACCESS not-accessible
     	STATUS     current
     	DESCRIPTION
       		"Indicates the prefix length of the destination
       		address."
     	::= { rcIpv6RouteEntry 2 }

rcIpv6RouteIndex OBJECT-TYPE
     	SYNTAX     Unsigned32
     	MAX-ACCESS not-accessible
     	STATUS     current
     	DESCRIPTION
       		"The value which uniquely identifies the route
       		among the routes to the same network layer
       		destination.  The way this value is chosen is
       		implementation specific but it must be unique for
       		rcIpv6RouteDest/rcIpv6RoutePfxLength pair and remain
       		constant for the life of the route."
     	::= { rcIpv6RouteEntry 3 }

rcIpv6RouteNextHopId OBJECT-TYPE
      	SYNTAX          DisplayString (SIZE (255))
        MAX-ACCESS      read-only
        STATUS          current
        DESCRIPTION     "Identifier of the next-hop, hostname or mac adress."
    	::= { rcIpv6RouteEntry 4 }

-- End of IPv6 Route Table

-- IPv6 Default Routers Table

rcIpv6DefaultRoutersTable OBJECT-TYPE
        SYNTAX          SEQUENCE OF RcIpv6DefaultRoutersEntry
        MAX-ACCESS      not-accessible
        STATUS          current
        DESCRIPTION     "IPv6 Default Routers Table."
        ::= { rcIpv6Objects  16 }

rcIpv6DefaultRoutersEntry OBJECT-TYPE
        SYNTAX          RcIpv6DefaultRoutersEntry
        MAX-ACCESS      not-accessible
        STATUS          current
        DESCRIPTION     "The entry for the IPv6 Default Routers Table."
        INDEX           { rcIpv6DefaultRoutersAddress, rcIpv6DefaultRoutersIfIndex }
        ::= { rcIpv6DefaultRoutersTable 1 }

RcIpv6DefaultRoutersEntry ::=
        SEQUENCE {
            rcIpv6DefaultRoutersAddress         Ipv6Address,
            rcIpv6DefaultRoutersIfIndex         Unsigned32,
            rcIpv6DefaultRoutersLifetime        Integer32,
            rcIpv6DefaultRoutersActive          TruthValue
        }

rcIpv6DefaultRoutersAddress OBJECT-TYPE
        SYNTAX          Ipv6Address
        MAX-ACCESS      not-accessible
        STATUS          current
        DESCRIPTION     "Learned Router Address for an IPv6 Default Routers Entry."
        ::= { rcIpv6DefaultRoutersEntry 1 }

rcIpv6DefaultRoutersIfIndex OBJECT-TYPE
        SYNTAX          Unsigned32
        MAX-ACCESS      not-accessible
        STATUS          current
        DESCRIPTION     "Interface number for an IPv6 Default Routers Entry."
        ::= { rcIpv6DefaultRoutersEntry 2 }

rcIpv6DefaultRoutersLifetime OBJECT-TYPE
        SYNTAX          Integer32
        MAX-ACCESS      read-only
        STATUS          current
        DESCRIPTION     "Remaining Router Lifetime for an IPv6 Default Routers Entry."
        ::= { rcIpv6DefaultRoutersEntry 3 }

rcIpv6DefaultRoutersActive OBJECT-TYPE
        SYNTAX          TruthValue
        MAX-ACCESS      read-only
        STATUS          current
        DESCRIPTION     "See if a default router is active for an IPv6 Default Routers Entry."
        ::= { rcIpv6DefaultRoutersEntry 4 }

-- End of IPv6 Default Router Table

-- IPv6 MLD Host Cache Table

rcIpv6MLDHostCacheTable OBJECT-TYPE
        SYNTAX          SEQUENCE OF RcIpv6MLDHostCacheEntry
        MAX-ACCESS      not-accessible
        STATUS          current
        DESCRIPTION     "IPv6 MLD Host Cache Table."
        ::= { rcIpv6Objects  17 }

rcIpv6MLDHostCacheEntry OBJECT-TYPE
        SYNTAX          RcIpv6MLDHostCacheEntry
        MAX-ACCESS      not-accessible
        STATUS          current
        DESCRIPTION     "The entry for the IPv6 MLD Host Cache Table."
        INDEX           { rcIpv6MLDHostCacheIfIndex, rcIpv6MLDHostCacheGrpAddress }
        ::= { rcIpv6MLDHostCacheTable 1 }

RcIpv6MLDHostCacheEntry ::=
        SEQUENCE {
            rcIpv6MLDHostCacheIfIndex                   Unsigned32,
            rcIpv6MLDHostCacheGrpAddress                Ipv6Address,
            rcIpv6MLDHostCacheGrpLocallyRegistered      Integer32,
            rcIpv6MLDHostCacheGrpLastReporter           Ipv6Address,
            rcIpv6MLDHostCacheGrpUpTime                 Unsigned32,
            rcIpv6MLDHostCacheGrpExpiryTime             Unsigned32,
            rcIpv6MLDHostCacheGrpFilterMode             Unsigned32
        }

rcIpv6MLDHostCacheIfIndex OBJECT-TYPE
        SYNTAX          Unsigned32
        MAX-ACCESS      not-accessible
        STATUS          current
        DESCRIPTION     "Interface number for an IPv6 MLD Host Cache Entry."
        ::= { rcIpv6MLDHostCacheEntry 1 }

rcIpv6MLDHostCacheGrpAddress OBJECT-TYPE
        SYNTAX          Ipv6Address
        MAX-ACCESS      not-accessible
        STATUS          current
        DESCRIPTION     "Group Address for an IPv6 MLD Host Cache Entry."
        ::= { rcIpv6MLDHostCacheEntry 2 }

rcIpv6MLDHostCacheGrpLocallyRegistered OBJECT-TYPE
        SYNTAX          Integer32
        MAX-ACCESS      read-only
        STATUS          current
        DESCRIPTION     "Group Locally Registered for an IPv6 MLD Host Cache Entry."
        ::= { rcIpv6MLDHostCacheEntry 3 }

rcIpv6MLDHostCacheGrpLastReporter OBJECT-TYPE
        SYNTAX          Ipv6Address
        MAX-ACCESS      read-only
        STATUS          current
        DESCRIPTION     "Group Last Reporter Address for an IPv6 MLD Host Cache Entry."
        ::= { rcIpv6MLDHostCacheEntry 4 }

rcIpv6MLDHostCacheGrpUpTime OBJECT-TYPE
        SYNTAX          Unsigned32
        MAX-ACCESS      read-only
        STATUS          current
        DESCRIPTION     "Group Uptime for an IPv6 MLD Host Cache Entry."
        ::= { rcIpv6MLDHostCacheEntry 5 }

rcIpv6MLDHostCacheGrpExpiryTime OBJECT-TYPE
        SYNTAX          Unsigned32
        MAX-ACCESS      read-only
        STATUS          current
        DESCRIPTION     "Group Expiry Time for an IPv6 MLD Host Cache Entry."
        ::= { rcIpv6MLDHostCacheEntry 6 }

rcIpv6MLDHostCacheGrpFilterMode OBJECT-TYPE
        SYNTAX          Unsigned32
        MAX-ACCESS      read-only
        STATUS          current
        DESCRIPTION     "Group Filter Mode for an IPv6 MLD Host Cache Entry."
        ::= { rcIpv6MLDHostCacheEntry 7 }

-- End of IPv6 MLD Host Cache Table

-- IPv6 RSMLT

rcIpRsmlt OBJECT IDENTIFIER       ::= { rcIp 26 }

rcIpv6RsmltOperTable OBJECT-TYPE
        SYNTAX          SEQUENCE OF RcIpv6RsmltOperEntry
        MAX-ACCESS      not-accessible
        STATUS          current
        DESCRIPTION     "Route Smlt Table"
    ::= { rcIpRsmlt 5 }

rcIpv6RsmltOperEntry OBJECT-TYPE
        SYNTAX        	RcIpv6RsmltOperEntry
        MAX-ACCESS      not-accessible
        STATUS        	current
        DESCRIPTION   	"A local IPv6 RSMLT entry"
        INDEX         	{ rcIpv6RsmltOperIfIndex,
                          rcIpv6RsmltOperIpv6Addr,
                          rcIpv6RsmltOperIpv6PrefixLength }
        ::= { rcIpv6RsmltOperTable 1 }

RcIpv6RsmltOperEntry ::=
        SEQUENCE {
                rcIpv6RsmltOperIfIndex                 InterfaceIndex,
                rcIpv6RsmltOperIpv6Addr                Ipv6Address,
                rcIpv6RsmltOperIpv6PrefixLength        Integer32,
                rcIpv6RsmltOperAdminStatus             TruthValue,
                rcIpv6RsmltOperHoldDownTimer           Integer32,
                rcIpv6RsmltOperHoldDownTimeRemaining   Integer32,
                rcIpv6RsmltOperHoldUpTimer             Integer32,
                rcIpv6RsmltOperHoldUpTimeRemaining     Integer32,
                rcIpv6RsmltOperOperStatus              INTEGER,
                rcIpv6RsmltOperSmltId                  IdList,
                rcIpv6RsmltOperSltId                   IdList,
                rcIpv6RsmltOperVlanId                  Integer32,
                rcIpv6RsmltOperMacAddr                 MacAddress,
                rcIpv6RsmltOperVrfId                   VrfIdentifier,
                rcIpv6RsmltOperVrfName                 SnmpAdminString
        }

rcIpv6RsmltOperIfIndex OBJECT-TYPE
        SYNTAX        InterfaceIndex
        MAX-ACCESS    not-accessible
        STATUS        current
        DESCRIPTION   "Route Smlt Oper IfIndex."
        ::= { rcIpv6RsmltOperEntry 1 }

rcIpv6RsmltOperIpv6Addr OBJECT-TYPE
        SYNTAX         Ipv6Address
        MAX-ACCESS     not-accessible
        STATUS         current
        DESCRIPTION    "IPv6 Interface with RSMLT on."
        ::= { rcIpv6RsmltOperEntry  2 }

rcIpv6RsmltOperIpv6PrefixLength OBJECT-TYPE
        SYNTAX        Integer32 (0..128)
        MAX-ACCESS    not-accessible
        STATUS        current
        DESCRIPTION   "IPv6 Prefix Length."
        ::= { rcIpv6RsmltOperEntry  3 }

rcIpv6RsmltOperAdminStatus OBJECT-TYPE
        SYNTAX        TruthValue
        MAX-ACCESS    read-write
        STATUS        current
        DESCRIPTION   "is a enable/disable flag."
        DEFVAL        { false }
        ::= { rcIpv6RsmltOperEntry 4 }

rcIpv6RsmltOperHoldDownTimer OBJECT-TYPE
        SYNTAX        Integer32 (0..3600)
        MAX-ACCESS    read-write
        STATUS        current
        DESCRIPTION   "Timer value, the range of value is from 0 to 3600."
        DEFVAL        { 0 }
        ::= { rcIpv6RsmltOperEntry 5 }

rcIpv6RsmltOperHoldDownTimeRemaining OBJECT-TYPE
        SYNTAX        Integer32 (0..3600)
        MAX-ACCESS    read-only
        STATUS        current
        DESCRIPTION   "The time value that indicate how much time
                       remaining of HoldDownTimer."
        DEFVAL        { 0 }
        ::= { rcIpv6RsmltOperEntry  6 }

rcIpv6RsmltOperHoldUpTimer OBJECT-TYPE
        SYNTAX        Integer32 (0..3600 | 9999)
        MAX-ACCESS    read-write
        STATUS        current
        DESCRIPTION   "The range of value 0 to 3600 or 9999. 9999 means
                       infinity."
        DEFVAL        { 0 }
        ::= { rcIpv6RsmltOperEntry  7 }

rcIpv6RsmltOperHoldUpTimeRemaining OBJECT-TYPE
        SYNTAX        Integer32 (0..3600 | 9999)
        MAX-ACCESS    read-only
        STATUS        current
        DESCRIPTION   "The time value that indicate how much time
                       remaining of HoldUpTimer."
        DEFVAL        { 0 }
        ::= { rcIpv6RsmltOperEntry  8 }

rcIpv6RsmltOperOperStatus OBJECT-TYPE
        SYNTAX        INTEGER {
                        up(1),
                        down(2)
                      }
        MAX-ACCESS    read-only
        STATUS        current
        DESCRIPTION   "The operation status of Rsmlt, up or down."
        DEFVAL        { down }
        ::= { rcIpv6RsmltOperEntry  9 }

rcIpv6RsmltOperSmltId OBJECT-TYPE
        SYNTAX        IdList
        MAX-ACCESS    read-only
        STATUS        current
        DESCRIPTION   "The id range for SMLT is 1-32."
        ::= { rcIpv6RsmltOperEntry  10 }

rcIpv6RsmltOperSltId OBJECT-TYPE
        SYNTAX        IdList
        MAX-ACCESS    read-only
        STATUS        current
        DESCRIPTION   "The id range for SLT is 1-512."
        ::= { rcIpv6RsmltOperEntry  11 }

rcIpv6RsmltOperVlanId OBJECT-TYPE
        SYNTAX        Integer32 (1..4093)
        MAX-ACCESS    read-only
        STATUS        current
        DESCRIPTION   "Vlan id."
        ::= { rcIpv6RsmltOperEntry  12 }

rcIpv6RsmltOperMacAddr OBJECT-TYPE
        SYNTAX        MacAddress
        MAX-ACCESS    read-only
        STATUS        current
        DESCRIPTION   "Mac Address."
        ::= { rcIpv6RsmltOperEntry  13 }

rcIpv6RsmltOperVrfId OBJECT-TYPE
        SYNTAX        VrfIdentifier
        MAX-ACCESS    read-only
        STATUS        current
        DESCRIPTION   "Indicates the Virtual Router to which the RSMLT
                       Oper instance belongs."
        ::= { rcIpv6RsmltOperEntry  14 }

rcIpv6RsmltOperVrfName OBJECT-TYPE
        SYNTAX        SnmpAdminString (SIZE (0..64))
        MAX-ACCESS    read-only
        STATUS        current
        DESCRIPTION   "Name of the Virtual Router to which the RSMLT Oper
                       instance belongs."
        ::= { rcIpv6RsmltOperEntry  15 }


-- Route IPv6 Smlt Peer Table

rcIpv6RsmltPeerTable OBJECT-TYPE
        SYNTAX          SEQUENCE OF RcIpv6RsmltPeerEntry
        MAX-ACCESS      not-accessible
        STATUS          current
        DESCRIPTION     "Route Smlt Peer Table"
    ::= { rcIpRsmlt 6 }

rcIpv6RsmltPeerEntry OBJECT-TYPE
        SYNTAX        	RcIpv6RsmltPeerEntry
        MAX-ACCESS       not-accessible
        STATUS        	current
        DESCRIPTION   	"An entry of Ip As Path Access List Table."
        INDEX         	{ rcIpv6RsmltPeerIfIndex,
                          rcIpv6RsmltPeerIpv6Addr,
                          rcIpv6RsmltPeerIpv6PrefixLength }
        ::= { rcIpv6RsmltPeerTable 1 }

RcIpv6RsmltPeerEntry ::=
        SEQUENCE {
                rcIpv6RsmltPeerIfIndex                 InterfaceIndex,
                rcIpv6RsmltPeerIpv6Addr                Ipv6Address,
                rcIpv6RsmltPeerIpv6PrefixLength        Integer32,
                rcIpv6RsmltPeerAdminStatus             TruthValue,
                rcIpv6RsmltPeerHoldDownTimer           Integer32,
                rcIpv6RsmltPeerHoldDownTimeRemaining   Integer32,
                rcIpv6RsmltPeerHoldUpTimer             Integer32,
                rcIpv6RsmltPeerHoldUpTimeRemaining     Integer32,
                rcIpv6RsmltPeerOperStatus              INTEGER,
                rcIpv6RsmltPeerSmltId                  IdList,
                rcIpv6RsmltPeerSltId                   IdList,
                rcIpv6RsmltPeerVlanId                  Integer32,
                rcIpv6RsmltPeerMacAddr                 MacAddress,
                rcIpv6RsmltPeerVrfId                   VrfIdentifier,
                rcIpv6RsmltPeerVrfName                 SnmpAdminString
        }

rcIpv6RsmltPeerIfIndex OBJECT-TYPE
        SYNTAX        InterfaceIndex
        MAX-ACCESS    not-accessible
        STATUS        current
        DESCRIPTION   "Route Smlt Oper IfIndex."
        ::= { rcIpv6RsmltPeerEntry 1 }

rcIpv6RsmltPeerIpv6Addr OBJECT-TYPE
        SYNTAX        Ipv6Address
        MAX-ACCESS    not-accessible
        STATUS        current
        DESCRIPTION   "IP Interface with RSMLT on."
        ::= { rcIpv6RsmltPeerEntry  2 }

rcIpv6RsmltPeerIpv6PrefixLength OBJECT-TYPE
        SYNTAX        Integer32 (0..128)
        MAX-ACCESS    not-accessible
        STATUS        current
        DESCRIPTION   "IPv6 Prefix Length"
        ::= { rcIpv6RsmltPeerEntry 3 }

rcIpv6RsmltPeerAdminStatus OBJECT-TYPE
        SYNTAX        TruthValue
        MAX-ACCESS    read-only
        STATUS        current
        DESCRIPTION   "is a enable/disable flag."
        ::= { rcIpv6RsmltPeerEntry 4 }

rcIpv6RsmltPeerHoldDownTimer OBJECT-TYPE
        SYNTAX        Integer32 (0..3600)
        MAX-ACCESS    read-only
        STATUS        current
        DESCRIPTION   "Timer value, the range of value is from 0 to 3600."
        DEFVAL        { 0 }
        ::= { rcIpv6RsmltPeerEntry 5 }

rcIpv6RsmltPeerHoldDownTimeRemaining OBJECT-TYPE
        SYNTAX        Integer32 (0..3600)
        MAX-ACCESS    read-only
        STATUS        current
        DESCRIPTION   "The time value that indicate how much time
                       remaining of HoldDownTimer."
        DEFVAL        { 0 }
        ::= { rcIpv6RsmltPeerEntry  6 }

rcIpv6RsmltPeerHoldUpTimer OBJECT-TYPE
        SYNTAX        Integer32 (0..3600 | 9999)
        MAX-ACCESS    read-only
        STATUS        current
        DESCRIPTION   "The range of value 0 to 3600 or 9999. 9999 means
                       infinity."
        DEFVAL        { 0 }
        ::= { rcIpv6RsmltPeerEntry  7 }

rcIpv6RsmltPeerHoldUpTimeRemaining OBJECT-TYPE
        SYNTAX        Integer32 (0..3600 | 9999)
        MAX-ACCESS    read-only
        STATUS        current
        DESCRIPTION   "The time value that indicate how much time
                       remaining of HoldUpTimer."
        DEFVAL        { 0 }
        ::= { rcIpv6RsmltPeerEntry  8 }

rcIpv6RsmltPeerOperStatus OBJECT-TYPE
        SYNTAX        INTEGER {
                        up(1),
                        down(2)
                      }
        MAX-ACCESS    read-only
        STATUS        current
        DESCRIPTION   "The operation status of Rsmlt, up or down."
        DEFVAL        { down }
        ::= { rcIpv6RsmltPeerEntry  9 }

rcIpv6RsmltPeerSmltId OBJECT-TYPE
        SYNTAX        IdList
        MAX-ACCESS    read-only
        STATUS        current
        DESCRIPTION   "The id range for SMLT is 1-32."
        ::= { rcIpv6RsmltPeerEntry  10 }

rcIpv6RsmltPeerSltId OBJECT-TYPE
        SYNTAX        IdList
        MAX-ACCESS    read-only
        STATUS        current
        DESCRIPTION   "The id range for SLT is 1-512."
        ::= { rcIpv6RsmltPeerEntry  11 }

rcIpv6RsmltPeerVlanId OBJECT-TYPE
        SYNTAX        Integer32 (1..4093)
        MAX-ACCESS    read-only
        STATUS        current
        DESCRIPTION   "Vlan id."
        ::= { rcIpv6RsmltPeerEntry  12 }

rcIpv6RsmltPeerMacAddr OBJECT-TYPE
        SYNTAX        MacAddress
        MAX-ACCESS    read-only
        STATUS        current
        DESCRIPTION   "Mac Address."
        ::= { rcIpv6RsmltPeerEntry  13 }

rcIpv6RsmltPeerVrfId OBJECT-TYPE
        SYNTAX        VrfIdentifier
        MAX-ACCESS    read-only
        STATUS        current
        DESCRIPTION   "Indicates the Virtual Router to which the RSMLT Peer
                       instance belongs."
        ::= { rcIpv6RsmltPeerEntry  14 }

rcIpv6RsmltPeerVrfName OBJECT-TYPE
        SYNTAX        SnmpAdminString (SIZE (0..64))
        MAX-ACCESS    read-only
        STATUS        current
        DESCRIPTION   "Name of the Virtual Router to which the RSMLT Peer
                       instance belongs."
        ::= { rcIpv6RsmltPeerEntry 15 }


-- IPv6 RSMLT Edge Peer table

rcIpv6RsmltEdgePeerTable OBJECT-TYPE
        SYNTAX        SEQUENCE OF RcIpv6RsmltEdgePeerEntry
        MAX-ACCESS    not-accessible
        STATUS        current
        DESCRIPTION   "RSMLT Edge Support Peer Info table. This
                      table consists of the RSMLT Peers for which
                      the switch will act as a PeerForwarder."
        ::= { rcIpRsmlt 7 }

rcIpv6RsmltEdgePeerEntry OBJECT-TYPE
        SYNTAX        RcIpv6RsmltEdgePeerEntry
        MAX-ACCESS    not-accessible
        STATUS        current
        DESCRIPTION   "RSMLT Edge Support Peer Info Entry"
        INDEX         { rcIpv6RsmltEdgePeerVlanId,
                        rcIpv6RsmltEdgePeerIpv6Address,
                        rcIpv6RsmltEdgePeerIpv6PrefixLength }
        ::= { rcIpv6RsmltEdgePeerTable 1 }

RcIpv6RsmltEdgePeerEntry ::=
	SEQUENCE {
                rcIpv6RsmltEdgePeerVlanId           Integer32,
                rcIpv6RsmltEdgePeerIpv6Address      Ipv6Address,
                rcIpv6RsmltEdgePeerIpv6PrefixLength Integer32,
                rcIpv6RsmltEdgePeerMacAddress       MacAddress,
                rcIpv6RsmltEdgePeerVrfId            VrfIdentifier,
                rcIpv6RsmltEdgePeerVrfName          SnmpAdminString,
                rcIpv6RsmltEdgePeerIsRaPrefix       TruthValue,
                rcIpv6RsmltEdgePeerConfType         Integer32,
                rcIpv6RsmltEdgePeerNoAdvertise      TruthValue,
                rcIpv6RsmltEdgePeerOspf6Advertise   TruthValue,
                rcIpv6RsmltEdgePeerPrefCandidate    TruthValue,
                rcIpv6RsmltEdgePeerPfxValidLife     Integer32,
                rcIpv6RsmltEdgePeerPfxPrefLife      Integer32,
                rcIpv6RsmltEdgePeerPfxOnLinkFlag    TruthValue,
                rcIpv6RsmltEdgePeerPfxAutoFlag      TruthValue
        }

rcIpv6RsmltEdgePeerVlanId  OBJECT-TYPE
        SYNTAX        Integer32 (1..4094)
        MAX-ACCESS    not-accessible
        STATUS        current
        DESCRIPTION   "A value that uniquely identifies the Virtual LAN
                      associated with this entry."
        ::= { rcIpv6RsmltEdgePeerEntry 1}

rcIpv6RsmltEdgePeerIpv6Address OBJECT-TYPE
        SYNTAX        Ipv6Address
        MAX-ACCESS    not-accessible
        STATUS        current
        DESCRIPTION   "IP address of the Peer RSMLT Interface."
        ::= { rcIpv6RsmltEdgePeerEntry 2}

rcIpv6RsmltEdgePeerIpv6PrefixLength OBJECT-TYPE
        SYNTAX        Integer32 (0..128)
        MAX-ACCESS    not-accessible
        STATUS        current
        DESCRIPTION   "If set then this prefix can be used
                       for address autoconfig,
                       passed opaquely to Infinity"
        ::= { rcIpv6RsmltEdgePeerEntry 3 }

rcIpv6RsmltEdgePeerMacAddress OBJECT-TYPE
        SYNTAX        MacAddress
        MAX-ACCESS    read-only
        STATUS        current
        DESCRIPTION   "The MAC address of the Peer RSMLT interface."
        ::= { rcIpv6RsmltEdgePeerEntry 4 }

rcIpv6RsmltEdgePeerVrfId OBJECT-TYPE
        SYNTAX        VrfIdentifier
        MAX-ACCESS    read-only
        STATUS        current
        DESCRIPTION   "Indicates the Virtual Router to which the RSMLT Edge Peer
                       instance belongs."
        ::= { rcIpv6RsmltEdgePeerEntry 5 }

rcIpv6RsmltEdgePeerVrfName OBJECT-TYPE
        SYNTAX        SnmpAdminString (SIZE (0..64))
        MAX-ACCESS    read-only
        STATUS        current
        DESCRIPTION   "Name of the Virtual Router to which the RSMLT Edge Peer
                       instance belongs."
        ::= { rcIpv6RsmltEdgePeerEntry 6 }

rcIpv6RsmltEdgePeerIsRaPrefix OBJECT-TYPE
        SYNTAX        TruthValue
        MAX-ACCESS    read-only
        STATUS        current
        DESCRIPTION   "True if this is a Router Advertisement prefix, False if
                       this is a global address."
        ::= { rcIpv6RsmltEdgePeerEntry 7 }

rcIpv6RsmltEdgePeerConfType OBJECT-TYPE
        SYNTAX        Integer32 (0..128)
        MAX-ACCESS    read-only
        STATUS        current
        DESCRIPTION   "Type of configured address, passed opaquely to Infinity "
        ::= { rcIpv6RsmltEdgePeerEntry 8 }

rcIpv6RsmltEdgePeerNoAdvertise OBJECT-TYPE
        SYNTAX        TruthValue
        MAX-ACCESS    read-only
        STATUS        current
        DESCRIPTION   "True if advertisement of this prefix is disabled,
                       passed opaquely to Infinity"
        ::= { rcIpv6RsmltEdgePeerEntry 9 }

rcIpv6RsmltEdgePeerOspf6Advertise OBJECT-TYPE
        SYNTAX        TruthValue
        MAX-ACCESS    read-only
        STATUS        current
        DESCRIPTION   "True if OSPFv3 advertisement of this prefix is enabled,
                       passed opaquely to Infinity"
        ::= { rcIpv6RsmltEdgePeerEntry 10 }

rcIpv6RsmltEdgePeerPrefCandidate OBJECT-TYPE
        SYNTAX        TruthValue
        MAX-ACCESS    read-only
        STATUS        current
        DESCRIPTION   "True if address is considered for preferred selection,
                       passed opaquely to Infinity"
        ::= { rcIpv6RsmltEdgePeerEntry 11 }

rcIpv6RsmltEdgePeerPfxValidLife OBJECT-TYPE
        SYNTAX        Integer32
        MAX-ACCESS    read-only
        STATUS        current
        DESCRIPTION   "Valid lifetime in seconds,
                       passed opaquely to Infinity"
        ::= { rcIpv6RsmltEdgePeerEntry 12 }

rcIpv6RsmltEdgePeerPfxPrefLife OBJECT-TYPE
        SYNTAX        Integer32
        MAX-ACCESS    read-only
        STATUS        current
        DESCRIPTION   "Preferred lifetime in seconds,
                       passed opaquely to Infinity"
        ::= { rcIpv6RsmltEdgePeerEntry 13 }

rcIpv6RsmltEdgePeerPfxOnLinkFlag OBJECT-TYPE
        SYNTAX        TruthValue
        MAX-ACCESS    read-only
        STATUS        current
        DESCRIPTION   "If set then this prefix can be used
                       for onlink determination,
                       passed opaquely to Infinity"
        ::= { rcIpv6RsmltEdgePeerEntry 14 }

rcIpv6RsmltEdgePeerPfxAutoFlag OBJECT-TYPE
        SYNTAX        TruthValue
        MAX-ACCESS    read-only
        STATUS        current
        DESCRIPTION   "If set then this prefix can be used
                       for address autoconfig,
                       passed opaquely to Infinity"
        ::= { rcIpv6RsmltEdgePeerEntry 15 }


--------------------------------------------------------------
--
-- rcTunnelXInetConfigTable
--
--------------------------------------------------------------

rcTunnelXInetConfigTable  OBJECT-TYPE
    SYNTAX      SEQUENCE OF RcTunnelXInetConfigEntry
    MAX-ACCESS  not-accessible
    STATUS      current
    DESCRIPTION
            "A table that containing information on configured tunnels."
    ::= { rcIpv6Objects 18 }

rcTunnelXInetConfigEntry OBJECT-TYPE
        SYNTAX        RcTunnelXInetConfigEntry
        MAX-ACCESS    not-accessible
        STATUS        current
        DESCRIPTION
            "An entry containing additional tunnel information. This
             object augments tunnelInetConfigEntry."
        AUGMENTS { tunnelInetConfigEntry }
        ::= { rcTunnelXInetConfigTable 1 }

RcTunnelXInetConfigEntry ::=
	SEQUENCE {
        	rcTunnelXInetConfigStatus INTEGER,
        	rcTunnelXInetConfigMode   INTEGER
	}

rcTunnelXInetConfigStatus OBJECT-TYPE
        SYNTAX        INTEGER {
                        inactive(1),
                        active(2)
                      }
        MAX-ACCESS    read-create
        STATUS        current
        DESCRIPTION
           "Indicates the tunnel status"
        DEFVAL { inactive }
        ::= { rcTunnelXInetConfigEntry 1 }

rcTunnelXInetConfigMode OBJECT-TYPE
        SYNTAX     INTEGER {
                     management(1),
                     data(2)
                   }
        MAX-ACCESS read-create
        STATUS     current
        DESCRIPTION
           "Indicates the tunnel mode"
        DEFVAL { management }
        ::= { rcTunnelXInetConfigEntry 2 }


-- IPv6 Route Extension Table
rcIpv6RouteExtensionTable OBJECT-TYPE
        SYNTAX          SEQUENCE OF RcIpv6RouteExtensionEntry
        MAX-ACCESS      not-accessible
        STATUS          current
        DESCRIPTION     "This entity's IPV6 Routing table."
	    ::= { rcIpv6Objects  19 }

rcIpv6RouteExtensionEntry OBJECT-TYPE
	SYNTAX  	RcIpv6RouteExtensionEntry
        MAX-ACCESS  	not-accessible
        STATUS  	current
        DESCRIPTION	"A route to a particular destination."
        AUGMENTS {
                     ipv6RouteEntry
        }
    	::= { rcIpv6RouteExtensionTable 1 }

RcIpv6RouteExtensionEntry ::=
	SEQUENCE {
		      rcIpv6RouteExtensionNextHopId         DisplayString,
		      rcIpv6RouteExtensionProtocol          INTEGER,
 		      rcIpv6RouteExtensionPathType          INTEGER,
                      rcIpv6RouteExtensionSrcVrfId          VrfIdentifier,
		      rcIpv6RouteExtensionLayer3VirtualInterface Integer32
		 }

rcIpv6RouteExtensionNextHopId OBJECT-TYPE
      	SYNTAX          DisplayString (SIZE (255))
        MAX-ACCESS      read-only
        STATUS          current
        DESCRIPTION     "Identifier of the next-hop, hostname or mac adress."
    	::= { rcIpv6RouteExtensionEntry 1 }

rcIpv6RouteExtensionProtocol OBJECT-TYPE
        SYNTAX     INTEGER {
       		 other(1),   -- none of the following

                	     -- non-protocol information,
                    	     -- e.g., manually configured
       		 local(2),   -- entries

       		 netmgmt(3), -- static route

                	     -- obtained via Neighbor
                    	     -- Discovery protocol,
       		 ndisc(4),   -- e.g., result of Redirect

                	     -- the following are all
                    	     -- dynamic routing protocols
       		 rip(5),     -- RIPng
      		 ospf(6),    -- Open Shortest Path First
       		 bgp(7),     -- Border Gateway Protocol
        	 idrp(8),    -- InterDomain Routing Protocol
       		 igrp(9),    -- InterGateway Routing Protocol
    	         isis(10)    -- ISIS Protocol
        }
        MAX-ACCESS	 read-only
        STATUS    	 current
        DESCRIPTION	 "The routing mechanism via which this route was learned."
        ::= { rcIpv6RouteExtensionEntry 2 }

rcIpv6RouteExtensionPathType OBJECT-TYPE
        SYNTAX     INTEGER {
                  b(1),      -- Best non-ECMP path
                  be(2),     -- Best ECMP path
                  a(3),      -- Alternate non-ECMP path
                  ae(4)      -- Alternate ECMP path
        }
        MAX-ACCESS      read-only
        STATUS          current
        DESCRIPTION     "Indicates IPv6 route path type: best, alternative, ECMP."
        ::= { rcIpv6RouteExtensionEntry  3 }

rcIpv6RouteExtensionSrcVrfId OBJECT-TYPE
        SYNTAX          VrfIdentifier
        MAX-ACCESS      read-only
        STATUS          current
        DESCRIPTION     "srcVrfId of the next-hop address. If the route is an ISIS route,
	    		 advertised under an ISID that i snot locally configured, on any VRF,
			 srcVrfId will be 1023"
    ::= { rcIpv6RouteExtensionEntry 4 }

rcIpv6RouteExtensionLayer3VirtualInterface OBJECT-TYPE
        SYNTAX          Integer32
        MAX-ACCESS      read-only
        STATUS          current
        DESCRIPTION     "Identifier of the Layer 3 Virtual Interface - SPB I-SID.
	                 0 denotes GlobalRouter and 1 denotes not applicable to route"
    ::= { rcIpv6RouteExtensionEntry 5 }



-- Ipv6 Route Pref Table

rcIpv6RoutePrefTable OBJECT-TYPE
        SYNTAX          SEQUENCE OF RcIpv6RoutePrefEntry
        MAX-ACCESS      not-accessible
        STATUS          current
        DESCRIPTION     "IPv6 Route Pref table. This table and
			 rcIpNewRoutePrefTable is designed
	                 to obsolete the rcIpRoutePrefTable"
        ::= { rcIpv6Objects 20 }

rcIpv6RoutePrefEntry OBJECT-TYPE
        SYNTAX          RcIpv6RoutePrefEntry
        MAX-ACCESS      not-accessible
        STATUS          current
        DESCRIPTION     "An entry of Ipv6 Route Pref Table."
        INDEX           { rcIpv6RoutePrefDefaultValue }
        ::= { rcIpv6RoutePrefTable 1 }

RcIpv6RoutePrefEntry ::=
        SEQUENCE {
		rcIpv6RoutePrefDefaultValue     Integer32,
                rcIpv6RoutePrefProtocol         INTEGER,
                rcIpv6RoutePrefConfiguredValue  Integer32
        }

rcIpv6RoutePrefDefaultValue OBJECT-TYPE
        SYNTAX        Integer32 (0..255)
        MAX-ACCESS    not-accessible
        STATUS        current
        DESCRIPTION   "Shows the default preference value for the given
                       protocol."
        ::= { rcIpv6RoutePrefEntry 1 }

rcIpv6RoutePrefProtocol OBJECT-TYPE
        SYNTAX        INTEGER {
	                  local(1),
		       	  static(2),
                          ospfv3Intra(3),
                          ospfv3Inter(4),
                          ospfv3External1(5),
                          ospfv3External2(6),
			  spbmLevel1(7),
			  ebgp(8),
			  ibgp(9),
			  ripng(10)
                      }
        MAX-ACCESS    read-only
        STATUS        current
        DESCRIPTION   "Protocol name"
        ::= { rcIpv6RoutePrefEntry 2 }

rcIpv6RoutePrefConfiguredValue OBJECT-TYPE
        SYNTAX        Integer32 (0..255)
        MAX-ACCESS    read-write
        STATUS        current
        DESCRIPTION   "This value is configurable by the user"
        ::= { rcIpv6RoutePrefEntry 3 }

--
--IPv6 FHS Snooping Table
--
rcIpv6FhsSnoopTable   OBJECT-TYPE
	SYNTAX	      SEQUENCE OF RcIpv6FhsSnoopEntry
	MAX-ACCESS    not-accessible
	STATUS	      current
	DESCRIPTION   "This table contains the entries which are
                       snooped by different methods."
	::= { rcIpv6Objects 21 }

rcIpv6FhsSnoopEntry OBJECT-TYPE
	SYNTAX	      RcIpv6FhsSnoopEntry
	MAX-ACCESS    not-accessible
	STATUS	      current
	DESCRIPTION   "An entry containing a learned DHCPv6 binding."
	INDEX         { rcIpv6FhsSnoopVlanId, rcIpv6FhsSnoopIpv6Address }
	::= { rcIpv6FhsSnoopTable 1 }

RcIpv6FhsSnoopEntry ::=
	SEQUENCE {
		rcIpv6FhsSnoopVlanId			RcVlanIdOrNone,
		rcIpv6FhsSnoopIpv6Address		Ipv6Address,
		rcIpv6FhsSnoopMacAddress		MacAddress,
		rcIpv6FhsSnoopInterfaceIndex		InterfaceIndex,
		rcIpv6FhsSnoopEntryType			INTEGER,
		rcIpv6FhsSnoopEntrySource 		INTEGER,
		rcIpv6FhsSnoopValidTime			Unsigned32,
		rcIpv6FhsSnoopTimeToExpiry		Unsigned32,
		rcIpv6FhsSnoopRowStatus			RowStatus
	}

rcIpv6FhsSnoopVlanId OBJECT-TYPE
	SYNTAX	      RcVlanIdOrNone
	MAX-ACCESS    not-accessible
	STATUS	      current
	DESCRIPTION   "The VLAN to which the snooped entry belongs."
	::= { rcIpv6FhsSnoopEntry 1 }

rcIpv6FhsSnoopIpv6Address OBJECT-TYPE
	SYNTAX        Ipv6Address
	MAX-ACCESS    not-accessible
	STATUS        current
	DESCRIPTION   "The IPv6 address assigned to this IPv6 host."
	::= { rcIpv6FhsSnoopEntry 2 }

rcIpv6FhsSnoopMacAddress OBJECT-TYPE
	SYNTAX        MacAddress
	MAX-ACCESS    read-create
	STATUS        current
	DESCRIPTION   "The MAC address of the snooped entry."
	::= { rcIpv6FhsSnoopEntry 3 }

rcIpv6FhsSnoopInterfaceIndex OBJECT-TYPE
	SYNTAX        InterfaceIndex
	MAX-ACCESS    read-create
	STATUS        current
	DESCRIPTION   "The interface on which the entry is learnt."
	::= { rcIpv6FhsSnoopEntry 4 }

rcIpv6FhsSnoopEntryType OBJECT-TYPE
	SYNTAX	      INTEGER {
			  static(1),
			  dynamic(2)
		      }
	MAX-ACCESS    read-only
	STATUS        current
	DESCRIPTION   "Indicates the type of entry - static (1)
	    	       or dynamic (2). "
	::= { rcIpv6FhsSnoopEntry 5 }

rcIpv6FhsSnoopEntrySource OBJECT-TYPE
	SYNTAX	      INTEGER {
			  static(1),
			  dhcp(2)
		      }
	MAX-ACCESS    read-only
	STATUS        current
	DESCRIPTION   "Indicates the method entry was learnt
	    	       from - static (1) or dhcp (2)."
	::= { rcIpv6FhsSnoopEntry 6 }

rcIpv6FhsSnoopValidTime OBJECT-TYPE
	SYNTAX        Unsigned32
	UNITS         "seconds"
	MAX-ACCESS    read-create
	STATUS        current
	DESCRIPTION   "The valid time for the snooped entry."
	::= { rcIpv6FhsSnoopEntry 7 }

rcIpv6FhsSnoopTimeToExpiry OBJECT-TYPE
	SYNTAX        Unsigned32
	UNITS         "seconds"
	MAX-ACCESS    read-only
	STATUS        current
	DESCRIPTION   "The time to expiry of the snooped entry."
	::= { rcIpv6FhsSnoopEntry 8 }

rcIpv6FhsSnoopRowStatus OBJECT-TYPE
	SYNTAX        RowStatus
	MAX-ACCESS    read-create
	STATUS        current
	DESCRIPTION   "Row status to create/delete snooped entries."
	 ::= { rcIpv6FhsSnoopEntry 9}

--
-- Notifications objects
--
rcIpv6FhsSnoopNotificationObjects OBJECT IDENTIFIER ::= { rcIpv6Objects 22 }


rcIpv6FhsSnoopNotificationEntryType OBJECT-TYPE
	SYNTAX	      INTEGER {
			  static (1),
			  dynamic (2)
		      }
	MAX-ACCESS    accessible-for-notify
	STATUS        current
	DESCRIPTION   "This value indicates type of binding entry. static (1)
		      entries are created by administrator manually whereas
		      dynamic (2) entries are learnt through snooping."
	::= { rcIpv6FhsSnoopNotificationObjects 1 }

rcIpv6FhsSnoopNotificationEntryCount OBJECT-TYPE
	SYNTAX	      Integer32
	MAX-ACCESS    accessible-for-notify
	STATUS        current
	DESCRIPTION   "This value indicates current number of binding
	    	       entries of type rcIpv6FhsSnoopingNotificationEntryType"
	::= { rcIpv6FhsSnoopNotificationObjects 2 }

rcIpv6IsisInFilterObjects OBJECT IDENTIFIER ::= { rcIpv6Objects 23 }

-- IPv6 Isis In Filter Nick Name Table
rcIpv6IsisInFilterNickNameTable OBJECT-TYPE
        SYNTAX          SEQUENCE OF RcIpv6IsisInFilterNickNameEntry
        MAX-ACCESS      not-accessible
        STATUS          current
        DESCRIPTION     "IPv6 Isis In Filter Nick Name table"
        ::= { rcIpv6IsisInFilterObjects 1 }

rcIpv6IsisInFilterNickNameEntry OBJECT-TYPE
        SYNTAX          RcIpv6IsisInFilterNickNameEntry
        MAX-ACCESS      not-accessible
        STATUS          current
        DESCRIPTION     "An entry of Ipv6 Isis In Filter Nick Name Table."
        INDEX           { rcIpv6IsisInFilterNickNameAdvertisingRtr }
        ::= { rcIpv6IsisInFilterNickNameTable 1 }

RcIpv6IsisInFilterNickNameEntry ::=
        SEQUENCE {
               rcIpv6IsisInFilterNickNameAdvertisingRtr  IpIsisPlsbNodeNickName,
               rcIpv6IsisInFilterNickNameEnable          TruthValue,
               rcIpv6IsisInFilterNickNamePolicyName      DisplayString,
               rcIpv6IsisInFilterNickNameRowStatus       RowStatus
        }

rcIpv6IsisInFilterNickNameAdvertisingRtr OBJECT-TYPE
        SYNTAX        IpIsisPlsbNodeNickName
        MAX-ACCESS    not-accessible
        STATUS        current
        DESCRIPTION   "NickName used to filter by"
        ::= { rcIpv6IsisInFilterNickNameEntry 1 }

rcIpv6IsisInFilterNickNameEnable OBJECT-TYPE
        SYNTAX        TruthValue
        MAX-ACCESS    read-create
        STATUS        current
        DESCRIPTION   "Enables or disables the Nick Name entry.  The value
                       must be enabled to filter."
        DEFVAL        { false }
        ::= { rcIpv6IsisInFilterNickNameEntry 2 }

rcIpv6IsisInFilterNickNamePolicyName OBJECT-TYPE
        SYNTAX        DisplayString (SIZE(0..64))
        MAX-ACCESS    read-create
        STATUS        current
        DESCRIPTION   "Route Map name used"
        ::= { rcIpv6IsisInFilterNickNameEntry 3 }

rcIpv6IsisInFilterNickNameRowStatus OBJECT-TYPE
        SYNTAX        RowStatus
        MAX-ACCESS    read-create
        STATUS        current
        DESCRIPTION   "Ipv6 Isis In Filter Nick Name Table Row Status"
        ::= { rcIpv6IsisInFilterNickNameEntry 4 }

-- IPv6 Isis In Filter ISID Table
rcIpv6IsisInFilterIsidTable OBJECT-TYPE
        SYNTAX          SEQUENCE OF RcIpv6IsisInFilterIsidEntry
        MAX-ACCESS      not-accessible
        STATUS          current
        DESCRIPTION     "IPv6 Isis In Filter Isid Isid table"
        ::= {  rcIpv6IsisInFilterObjects 2 }

rcIpv6IsisInFilterIsidEntry OBJECT-TYPE
        SYNTAX          RcIpv6IsisInFilterIsidEntry
        MAX-ACCESS      not-accessible
        STATUS          current
        DESCRIPTION     "An entry of Ipv6 Isis In Filter Table."
        INDEX           { rcIpv6IsisInFilterIsid }
        ::= { rcIpv6IsisInFilterIsidTable 1 }

RcIpv6IsisInFilterIsidEntry ::=
        SEQUENCE {
                rcIpv6IsisInFilterIsid                Integer32,
                rcIpv6IsisInFilterIsidEnable          TruthValue,
                rcIpv6IsisInFilterIsidPolicyName      DisplayString,
                rcIpv6IsisInFilterIsidRowStatus       RowStatus
        }

rcIpv6IsisInFilterIsid OBJECT-TYPE
        SYNTAX        Integer32 (0..16777215)
        MAX-ACCESS    not-accessible
        STATUS        current
        DESCRIPTION   "Isid value used to filter by"
        ::= { rcIpv6IsisInFilterIsidEntry 1 }

rcIpv6IsisInFilterIsidEnable OBJECT-TYPE
        SYNTAX        TruthValue
        MAX-ACCESS    read-create
        STATUS        current
        DESCRIPTION   "Enables or disables the Isid entry.  The value
                       must be enabled to filter."
        DEFVAL        { false }
        ::= { rcIpv6IsisInFilterIsidEntry 2 }

rcIpv6IsisInFilterIsidPolicyName OBJECT-TYPE
        SYNTAX        DisplayString (SIZE(0..64))
        MAX-ACCESS    read-create
        STATUS        current
        DESCRIPTION   "Route Map name used"
        ::= { rcIpv6IsisInFilterIsidEntry 3 }

rcIpv6IsisInFilterIsidRowStatus OBJECT-TYPE
        SYNTAX        RowStatus
        MAX-ACCESS    read-create
        STATUS        current
        DESCRIPTION   "IPv6 Isis In Filter Isid Table Row Status"
        ::= { rcIpv6IsisInFilterIsidEntry 4 }

-- IPv6 Isis In Filter NickName ISID Table

rcIpv6IsisInFilterNickNameIsidTable OBJECT-TYPE
        SYNTAX          SEQUENCE OF RcIpv6IsisInFilterNickNameIsidEntry
        MAX-ACCESS      not-accessible
        STATUS          current
        DESCRIPTION     "IPv6 Isis In Filter Nick Name Isid table"
        ::= { rcIpv6IsisInFilterObjects 3 }

rcIpv6IsisInFilterNickNameIsidEntry OBJECT-TYPE
        SYNTAX          RcIpv6IsisInFilterNickNameIsidEntry
        MAX-ACCESS      not-accessible
        STATUS          current
        DESCRIPTION     "An entry of IPv6 Isis In Filter Nick Name Isid Table."
        INDEX           { rcIpv6IsisInFilterNickNameIsidAdvertisingRtr,
                          rcIpv6IsisInFilterNickNameIsid }
        ::= { rcIpv6IsisInFilterNickNameIsidTable 1 }

RcIpv6IsisInFilterNickNameIsidEntry ::=
        SEQUENCE {
             rcIpv6IsisInFilterNickNameIsidAdvertisingRtr  IpIsisPlsbNodeNickName,
             rcIpv6IsisInFilterNickNameIsid                Integer32,
             rcIpv6IsisInFilterNickNameIsidEnable          TruthValue,
             rcIpv6IsisInFilterNickNameIsidPolicyName      DisplayString,
             rcIpv6IsisInFilterNickNameIsidRowStatus       RowStatus
        }

rcIpv6IsisInFilterNickNameIsidAdvertisingRtr OBJECT-TYPE
        SYNTAX        IpIsisPlsbNodeNickName
        MAX-ACCESS    not-accessible
        STATUS        current
        DESCRIPTION   "Nick Name used to filter by"
        ::= { rcIpv6IsisInFilterNickNameIsidEntry 1 }

rcIpv6IsisInFilterNickNameIsid OBJECT-TYPE
        SYNTAX        Integer32 (0..16777215)
        MAX-ACCESS    not-accessible
        STATUS        current
        DESCRIPTION   "Isid used to filter by"
        ::= { rcIpv6IsisInFilterNickNameIsidEntry 2 }

rcIpv6IsisInFilterNickNameIsidEnable OBJECT-TYPE
        SYNTAX        TruthValue
        MAX-ACCESS    read-create
        STATUS        current
        DESCRIPTION   ""
        DEFVAL        { false }
        ::= { rcIpv6IsisInFilterNickNameIsidEntry 3 }

rcIpv6IsisInFilterNickNameIsidPolicyName OBJECT-TYPE
        SYNTAX        DisplayString (SIZE(0..64))
        MAX-ACCESS    read-create
        STATUS        current
        DESCRIPTION   "Route Map name used"
        ::= { rcIpv6IsisInFilterNickNameIsidEntry 4 }

rcIpv6IsisInFilterNickNameIsidRowStatus OBJECT-TYPE
        SYNTAX        RowStatus
        MAX-ACCESS    read-create
        STATUS        current
        DESCRIPTION   "IPv6 Isis In Filter Nick Name Isid Table Row Status"
        ::= { rcIpv6IsisInFilterNickNameIsidEntry 5 }


-- IPv6 Isis In Filter ISID List Table
rcIpv6IsisInFilterIsidListTable OBJECT-TYPE
        SYNTAX          SEQUENCE OF RcIpv6IsisInFilterIsidListEntry
        MAX-ACCESS      not-accessible
        STATUS          current
        DESCRIPTION     "IPv6 Isis In Filter Isid List table"
        ::= { rcIpv6IsisInFilterObjects 4 }

rcIpv6IsisInFilterIsidListEntry OBJECT-TYPE
        SYNTAX          RcIpv6IsisInFilterIsidListEntry
        MAX-ACCESS      not-accessible
        STATUS          current
        DESCRIPTION     "An entry of IPv6 Isis In Filter Table."
        INDEX           { rcIpv6IsisInFilterIsidListName }
        ::= { rcIpv6IsisInFilterIsidListTable 1 }

RcIpv6IsisInFilterIsidListEntry ::=
        SEQUENCE {
               rcIpv6IsisInFilterIsidListName            DisplayString,
               rcIpv6IsisInFilterIsidListEnable          TruthValue,
               rcIpv6IsisInFilterIsidListPolicyName      DisplayString,
               rcIpv6IsisInFilterIsidListRowStatus       RowStatus
}

rcIpv6IsisInFilterIsidListName OBJECT-TYPE
        SYNTAX        DisplayString(SIZE (1..32))
        MAX-ACCESS    not-accessible
        STATUS        current
        DESCRIPTION   "Name of Isid List"
        ::= { rcIpv6IsisInFilterIsidListEntry 1 }

rcIpv6IsisInFilterIsidListEnable OBJECT-TYPE
        SYNTAX        TruthValue
        MAX-ACCESS    read-create
        STATUS        current
        DESCRIPTION   "Enables or disables the Isid List entry.  The value
                       must be enabled to filter."
        DEFVAL        { false }
        ::= { rcIpv6IsisInFilterIsidListEntry 2 }

rcIpv6IsisInFilterIsidListPolicyName OBJECT-TYPE
        SYNTAX        DisplayString (SIZE(0..64))
        MAX-ACCESS    read-create
        STATUS        current
        DESCRIPTION   "Route Map name"
        ::= { rcIpv6IsisInFilterIsidListEntry 3 }

rcIpv6IsisInFilterIsidListRowStatus OBJECT-TYPE
        SYNTAX        RowStatus
        MAX-ACCESS    read-create
        STATUS        current
        DESCRIPTION   "IPv6 Isis In Filter Isid List Table Row Status"
        ::= { rcIpv6IsisInFilterIsidListEntry 4 }

-- IPv6 Isis In Filter Nick Name ISID List Table
rcIpv6IsisInFilterNickNameIsidListTable OBJECT-TYPE
        SYNTAX          SEQUENCE OF RcIpv6IsisInFilterNickNameIsidListEntry
        MAX-ACCESS      not-accessible
        STATUS          current
        DESCRIPTION     "IPv6 Isis In Filter Nick Name Isid List table"
        ::= { rcIpv6IsisInFilterObjects 5 }

rcIpv6IsisInFilterNickNameIsidListEntry OBJECT-TYPE
        SYNTAX          RcIpv6IsisInFilterNickNameIsidListEntry
        MAX-ACCESS      not-accessible
        STATUS          current
        DESCRIPTION     "An entry of IPv6 Isis In Filter Nick Name Isid ListTable"
        INDEX           { rcIpv6IsisInFilterNickNameIsidListAdvertisingRtr,
                          rcIpv6IsisInFilterNickNameIsidListName }
        ::= { rcIpv6IsisInFilterNickNameIsidListTable 1 }

RcIpv6IsisInFilterNickNameIsidListEntry ::=
        SEQUENCE {
          rcIpv6IsisInFilterNickNameIsidListAdvertisingRtr IpIsisPlsbNodeNickName,
          rcIpv6IsisInFilterNickNameIsidListName            DisplayString,
          rcIpv6IsisInFilterNickNameIsidListEnable          TruthValue,
          rcIpv6IsisInFilterNickNameIsidListPolicyName      DisplayString,
          rcIpv6IsisInFilterNickNameIsidListRowStatus       RowStatus
        }

rcIpv6IsisInFilterNickNameIsidListAdvertisingRtr OBJECT-TYPE
        SYNTAX        IpIsisPlsbNodeNickName
        MAX-ACCESS    not-accessible
        STATUS        current
        DESCRIPTION   "Nick Name used to filter by"
        ::= { rcIpv6IsisInFilterNickNameIsidListEntry 1 }

rcIpv6IsisInFilterNickNameIsidListName OBJECT-TYPE
        SYNTAX        DisplayString(SIZE (1..32))
        MAX-ACCESS    not-accessible
        STATUS        current
        DESCRIPTION   "Name of Isid List used to filter"
        ::= { rcIpv6IsisInFilterNickNameIsidListEntry 2 }

rcIpv6IsisInFilterNickNameIsidListEnable OBJECT-TYPE
        SYNTAX        TruthValue
        MAX-ACCESS    read-create
        STATUS        current
        DESCRIPTION   "Enables or disables the Nick Name Isid List entry.
                       The value must be enabled to filter."
        DEFVAL        { false }
        ::= { rcIpv6IsisInFilterNickNameIsidListEntry 3 }

rcIpv6IsisInFilterNickNameIsidListPolicyName OBJECT-TYPE
        SYNTAX        DisplayString (SIZE(0..64))
        MAX-ACCESS    read-create
        STATUS        current
        DESCRIPTION   "Route Map name"
        ::= { rcIpv6IsisInFilterNickNameIsidListEntry 4 }

rcIpv6IsisInFilterNickNameIsidListRowStatus OBJECT-TYPE
        SYNTAX        RowStatus
        MAX-ACCESS    read-create
        STATUS        current
        DESCRIPTION   "IPv6 Isis In Filter Nick Name Isid List Table Row Status"
        ::= { rcIpv6IsisInFilterNickNameIsidListEntry 5 }

-- Start of IPv6 Static route BFD Table

rcIpv6StaticRouteBfdTable OBJECT-TYPE
        SYNTAX          SEQUENCE OF RcIpv6StaticRouteBfdEntry
        MAX-ACCESS      not-accessible
        STATUS          current
        DESCRIPTION     "This table is used to hold next hop addresses on which BFD is enabled."
        ::= { rcIpv6Objects 24  }

rcIpv6StaticRouteBfdEntry OBJECT-TYPE
        SYNTAX          RcIpv6StaticRouteBfdEntry
        MAX-ACCESS      not-accessible
        STATUS          current
        DESCRIPTION     "An IPv6 address of the next hop of the BFD session."
        INDEX           {rcIpv6StaticRouteBfdIfIndex,
                         rcIpv6StaticRouteBfdNextHop}
        ::= { rcIpv6StaticRouteBfdTable 1 }

RcIpv6StaticRouteBfdEntry ::=
        SEQUENCE {
                rcIpv6StaticRouteBfdIfIndex        InterfaceIndexOrZero,
                rcIpv6StaticRouteBfdNextHop        Ipv6Address,
                rcIpv6StaticRouteBfdRowStatus      RowStatus,
                rcIpv6StaticRouteBfdVrfId          VrfIdentifier,
                rcIpv6StaticRouteBfdVrfName        DisplayString
        }

rcIpv6StaticRouteBfdIfIndex OBJECT-TYPE
        SYNTAX        InterfaceIndexOrZero
        MAX-ACCESS    not-accessible
        STATUS        current
        DESCRIPTION   "The IfIndex value which identifies the local
                interface through which the next hop of this route
                should be reached."
        ::= { rcIpv6StaticRouteBfdEntry 1 }

rcIpv6StaticRouteBfdNextHop OBJECT-TYPE
        SYNTAX          Ipv6Address
        MAX-ACCESS      not-accessible
        STATUS          current
        DESCRIPTION     "The IPv6 address of the next hop of the BFD session."
        ::= { rcIpv6StaticRouteBfdEntry 2 }

rcIpv6StaticRouteBfdRowStatus OBJECT-TYPE
        SYNTAX          RowStatus
        MAX-ACCESS      read-create
        STATUS          current
        DESCRIPTION     "Used to create/delete entries"
        ::= { rcIpv6StaticRouteBfdEntry 3 }

rcIpv6StaticRouteBfdVrfId  OBJECT-TYPE
        SYNTAX        VrfIdentifier
        MAX-ACCESS    read-create
        STATUS        current
        DESCRIPTION   "Indicates the Virtual Router to which the IPv6 static route BFD
                           instance belongs."
        ::= { rcIpv6StaticRouteBfdEntry 4 }

rcIpv6StaticRouteBfdVrfName OBJECT-TYPE
        SYNTAX         DisplayString (SIZE (0..32))
        MAX-ACCESS     read-only
        STATUS         current
        DESCRIPTION    "The Name of the Virtual Router to which the IPv6 static route BFD
                           instance belongs."
        ::= { rcIpv6StaticRouteBfdEntry 5 }

 --End of Static Route Bfd Table.

END
