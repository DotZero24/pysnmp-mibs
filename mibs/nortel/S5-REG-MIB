S5-REG-MIB DEFINITIONS ::= BEGIN

IMPORTS
    MODULE-IDENTITY
        FROM SNMPv2-SMI
    s5reg
        FROM S5-ROOT-MIB;

s5RegMib MODULE-IDENTITY
       LAST-UPDATED    "201612090000Z"
       ORGANIZATION    "Avaya"
       CONTACT-INFO    "Avaya"
       DESCRIPTION
           "S5000 Registration MIB

            Copyright 1996 - 2014 Avaya, Inc.
            All rights reserved.
            This Avaya SNMP Management Information Base Specification
            (Specification) embodies Avaya' confidential and
            proprietary intellectual property. Avaya retains all
            title and ownership in the Specification, including any
            revisions.

            This Specification is supplied 'AS IS,' and Avaya makes
            no warranty, either express or implied, as to the use,
            operation, condition, or performance of the Specification."

       REVISION "201612090000Z" -- 9 December 2016
       DESCRIPTION "Version 248:  Added registrations for ERS5928 MTS UPWR model."

       REVISION "201607210000Z" -- 21 July 2016
       DESCRIPTION "Version 247:  Added registrations for ERS 36XX models."

       REVISION "201505050000Z" -- 5 May 2015
       DESCRIPTION "Version 246:  Added registrations for ERS 3550T and ERS 3550T-PWR+ models."

       REVISION "201407290000Z" -- 29 July 2014
       DESCRIPTION "Version 245:  Added registrations for ERS 5900 and ERS 4900 product families.
                                  They replace former X710 and X610."

       REVISION "201403210000Z" -- 21 March 2014
       DESCRIPTION "Version 244:  Added registrations for ERS X710 and ERS X610 product families."

       REVISION "201402130000Z" -- 13 February 2014
       DESCRIPTION "Version 243:  Added s5ChasComBrdGbic-DIRECT, s5ChasComBrdGbic-40G-SR4,
                                  s5ChasComBrdGbic-40G-LR, s5ChasComBrdGbic-40G-ER;
                                  added support for VSP7024XT and VSP7000 MDAs"

       REVISION "201308260000Z" -- 26 August 2013
       DESCRIPTION "Version 242:  Added registrations for ERS3549GTS and ERS3549GTS-PWR+ models."

       REVISION "201301240000Z" -- 24 January 2013
       DESCRIPTION "Version 241:  Added registrations for 3526T and 3526T-PWR+ models."

       REVISION "201110100000Z" -- 10 Oct 2011
       DESCRIPTION "Version 240:  Added additional registrations for 35xx"

       REVISION "201107290000Z" -- 29 July 2011
       DESCRIPTION "Version 239:  Added s5ChasComBrdVSP7024XLS-7008XLS and
                                  s5ChasComBrdVSP7024XLS-7008XLT."

       REVISION "201106290000Z" -- 29 June 2011
       DESCRIPTION "Version 238:  Rename registrations for 47xx into 48xx."

       REVISION "201104280000Z" -- 28 Apr 2011
       DESCRIPTION "Version 237:  Added support for VSP7024XLS."

       REVISION "201103080000Z" -- 08 Mar 2011
       DESCRIPTION "Version 236:  Fix registrations for 45xx and 47xx"

       REVISION "201101250000Z" -- 25 Jan 2011
       DESCRIPTION "Version 235:  Added additional registrations for 45xx"

       REVISION "201008270000Z" -- 27 Aug 2010
       DESCRIPTION "Version 234:  Added registrations for 45xx and 47xx"

       REVISION "200910130000Z" -- 13 Oct 2009
       DESCRIPTION "Version 233:  Added s5ChasComBrdGbic-EX."

       REVISION "200906090000Z" -- 09 Jun 2009
       DESCRIPTION "Version 232:  Added regs for WC8180."

       REVISION "200905280000Z" -- 28 May 2009
       DESCRIPTION "Version 231:  Fixup HW CPLD OIDs."

       REVISION "200904150000Z" -- 15 Apr 2009
       DESCRIPTION "Version 230:  Added secondary flash registrations for ESU."

       REVISION "200903300000Z" -- 30 Mar 2009
       DESCRIPTION "Version 229:  Added CPU, Board1 and Board2 sensors for ESU.
                                  Added HW CPLD Store for ESU"

       REVISION "200812160000Z" -- 16 Dec 2008
       DESCRIPTION "Version 228:  Changed ers64xx to ers66xx."

       REVISION "200811210000Z" -- 21 Nov 2008
       DESCRIPTION "Version 227:  Added additional regs for 56xx pwr supplies."

       REVISION "200810290000Z" -- 29 Oct 2008
       DESCRIPTION "Version 226:  Added registrations for ERS64xx."

       REVISION "200810140000Z" -- 14 Oct 2008
       DESCRIPTION "Version 225:  Added registrations for ERS4524-GT-PWR."

       REVISION "200805220000Z" -- 22 May 2008
       DESCRIPTION "Version 224:  Added additional registrations for ERS56xx."

       REVISION "200711210000Z" -- 21 Nov 2007
       DESCRIPTION "Version 223:  Added registrations for new GBIC types."

       REVISION "200710160000Z" -- 16 Oct 2007
       DESCRIPTION "Version 222:  Added registrations for ESU1860/1880."

       REVISION "200706040000Z" -- 04 June 2007
       DESCRIPTION "Version 221:  Added registrations for ERS56xx."

       REVISION "200705080000Z" -- 08 May 2007
       DESCRIPTION "Version 220:  Added registrations for USB."

       REVISION "200702220000Z" -- 22 Feb 2007
       DESCRIPTION "Version 219:  Added additional Botany Bay definitions."

       REVISION "200609120000Z" -- 12 Sept 2006
       DESCRIPTION "Version 218:  Corrected ERS25xx definitions."

       REVISION "200609010000Z" -- 01 Sept 2006
       DESCRIPTION "Version 217:  Added ERS25xx definitions."

       REVISION "200607060000Z" -- 06 July 2006
       DESCRIPTION "Version 216:  Fix botany bay definitions."

       REVISION "200605250000Z" -- 25 May 2006
       DESCRIPTION "Version 215:  Add PoL storage types."

       REVISION "200604120000Z" -- 12 April 2006
       DESCRIPTION "Version 214:  Fix typo."

       REVISION "200604060000Z" -- 06 April 2006
       DESCRIPTION "Version 213:  Added Botany Bay definitions."

       REVISION "200511040000Z" -- 04 November 2005
       DESCRIPTION "Version 212:  Added various BES definitions."

       REVISION "200504250000Z" -- 25 April 2005
       DESCRIPTION "v211:  added s5ChasComBrdGbic-DWDM, s5ChasComBrdGbic-10G-SR,
                           s5ChasComBrdGbic-10G-LR, s5ChasComBrdGbic-10G-ER, and
                           s5ChasComBrdGbic-10G-LX4."

       REVISION "200410190000Z" -- 19 October 2004
       DESCRIPTION "v210:  added support for 2270 WLAN Security Switch Crypto Accelerator"

       REVISION "200410130000Z" -- 13 Oct 2004
       DESCRIPTION "v209:  added support for Outrigger and Dragline."

       REVISION "200410120000Z" -- 12 October 2004
       DESCRIPTION "v208:  fixed typo & added support for 2270 WLAN Security Switch"

       REVISION "200408310002Z" -- 31 August 2004
       DESCRIPTION "v207:  fix OID conflicts"

       REVISION "200408310001Z" -- 31 August 2004
       DESCRIPTION "v206:  fix typo"

       REVISION "200408310000Z" -- 31 August 2004
       DESCRIPTION "v205:  added support for Baystack 470 24T/48T
                           PWR switches"

       REVISION "200407200000Z" -- 20 July 2004
       DESCRIPTION "v204:  Added version info"

       REVISION "200305050000Z" -- 05 May 2003
       DESCRIPTION "v199:  Conversion to SMIv2"

       ::= { s5reg 4 }


-- Registrations for Chassis Types
-- (values for object s5ChasType)
s5ChasTypeVal OBJECT IDENTIFIER ::= { s5reg 1 }

-- Unknown or unavailable chassis type
s5ChasTypeUnknown
    OBJECT IDENTIFIER ::= { s5ChasTypeVal 1 }

-- The chassis type for the 3000
s5ChasTypeM3000Orig
    OBJECT IDENTIFIER ::= { s5ChasTypeVal 2 }

-- The chassis type for the 3030
s5ChasTypeM3030
    OBJECT IDENTIFIER ::= { s5ChasTypeVal 3 }

-- The original chassis for the 5000
s5ChasTypeM5000
    OBJECT IDENTIFIER ::= { s5ChasTypeVal 12 }

-- The chassis type for EtherCell
s5ChasTypeM1032x
    OBJECT IDENTIFIER ::= { s5ChasTypeVal 16 }

-- The chassis type for the 5005
s5ChasTypeM5005
    OBJECT IDENTIFIER ::= { s5ChasTypeVal 17 }

-- The chassis types for Distributed 5000
s5ChasType5DN000
    OBJECT IDENTIFIER ::= { s5ChasTypeVal 24 }
-- Model 5DN002 Hub 1.5U with 2 MDA Slots
s5ChasType5DN002Unit-1U2
    OBJECT IDENTIFIER ::= { s5ChasType5DN000 1 }
-- Model 5DN003 Hub 2.5U with 3 MDA Slots
s5ChasType5DN003Unit-2U3
    OBJECT IDENTIFIER ::= { s5ChasType5DN000 2 }
-- Model 5DN001-08 D-Day Hub 1.5U fixed config RJ-45
s5ChasType5DN001-08Unit-2U0
    OBJECT IDENTIFIER ::= { s5ChasType5DN000 3 }

-- The chassis types for BayStack Ethernet
s5ChasTypeNBayStack
    OBJECT IDENTIFIER ::= { s5ChasTypeVal 25 }
s5ChasTypeNBayStackUnit-12Port
    OBJECT IDENTIFIER ::= { s5ChasTypeNBayStack 1 }
s5ChasTypeNBayStackUnit-24Port
    OBJECT IDENTIFIER ::= { s5ChasTypeNBayStack 2}

-- The chassis types for the BayStack 100BASE-T Hub Stack
s5ChasTypeBayStack100Hub
    OBJECT IDENTIFIER ::= { s5ChasTypeVal 27 }
s5ChasTypeBayStack100Unit-12Port
    OBJECT IDENTIFIER ::= { s5ChasTypeBayStack100Hub 1 }

-- The chassis type for the 3000 Fast Ethernet
s5ChasTypeM3000
    OBJECT IDENTIFIER ::= { s5ChasTypeVal 28 }

-- Orion switch chassis type
s5ChasTypeXedia
    OBJECT IDENTIFIER ::= { s5ChasTypeVal 29 }

-- Unused Chassis type
s5ChasTypeNotUsed
    OBJECT IDENTIFIER ::= { s5ChasTypeVal 30 }

-- Chassis types for 28200 Ethernet Switch
s5ChasType28200
    OBJECT IDENTIFIER ::= { s5ChasTypeVal 31 }
-- Model 28200 Ethernet Switch with 4 - MDA slots
s5ChasType28200Unit-4slot
    OBJECT IDENTIFIER ::= { s5ChasType28200 1 }

-- Chassis types for Centillion
s5ChasTypeCent-sixSlot
    OBJECT IDENTIFIER ::= { s5ChasTypeVal 32 }
s5ChasTypeCent-twelveSlot
    OBJECT IDENTIFIER ::= { s5ChasTypeVal 33 }
s5ChasTypeCent-singleSlot
    OBJECT IDENTIFIER ::= { s5ChasTypeVal 34 }

-- Chassis type for Bay Stack 301
s5ChasTypeBayStack301
    OBJECT IDENTIFIER ::= { s5ChasTypeVal 35 }

-- Chassis type for Bay Stack Token Ring
s5ChasTypeBayStackTr
    OBJECT IDENTIFIER ::= { s5ChasTypeVal 36 }
s5ChasTypeBayStackTrUnit-24-port
    OBJECT IDENTIFIER ::= { s5ChasTypeBayStackTr 1 }

-- Chassis type for FVC Multimedia switch
s5ChasTypeFVC10625
    OBJECT IDENTIFIER ::= { s5ChasTypeVal 37 }

-- Chassis type for Switch Node
s5ChasTypeSwitchNode
    OBJECT IDENTIFIER ::= { s5ChasTypeVal 38 }

-- Chassis types for BayStack302
s5ChasTypeBayStack302
    OBJECT IDENTIFIER ::= { s5ChasTypeVal 39 }
s5ChasTypeBayStack302-ethSwitch
    OBJECT IDENTIFIER ::= { s5ChasTypeBayStack302 1 }

-- Chassis types for BayStack350
s5ChasTypeBayStack350
    OBJECT IDENTIFIER ::= { s5ChasTypeVal 40 }
s5ChasTypeBayStack350-ethSwitch
    OBJECT IDENTIFIER ::= { s5ChasTypeBayStack350 1 }

-- The chassis types for BayStack150 Ethernet
s5ChasTypeBayStack150
    OBJECT IDENTIFIER ::= { s5ChasTypeVal 41 }
s5ChasTypeBayStack150MasterUnit-24Port
    OBJECT IDENTIFIER ::= { s5ChasTypeBayStack150 1 }
s5ChasTypeBayStack150MasterUnit-12Port
    OBJECT IDENTIFIER ::= { s5ChasTypeBayStack150 2 }
s5ChasTypeBayStack150SlaveUnit-24Port
    OBJECT IDENTIFIER ::= { s5ChasTypeBayStack150 3 }
s5ChasTypeBayStack150SlaveUnit-12Port
    OBJECT IDENTIFIER ::= { s5ChasTypeBayStack150 4 }

--The chassis type for C50N switch
s5ChasTypeC50N
    OBJECT IDENTIFIER ::= { s5ChasTypeVal 42 }
--The chassis type for C50T switch
s5ChasTypeC50T
    OBJECT IDENTIFIER ::= { s5ChasTypeVal 43 }

-- Chassis type for BayStacks 303 and 304
s5ChasTypeBayStack303-304
    OBJECT IDENTIFIER ::= { s5ChasTypeVal 44 }

-- The chassis types for BayStack200 Ethernet
s5ChasTypeBayStack200
    OBJECT IDENTIFIER ::= { s5ChasTypeVal 45 }
s5ChasTypeBayStack200NMMHostUnit-12TxPort
    OBJECT IDENTIFIER ::= { s5ChasTypeBayStack200 1 }
s5ChasTypeBayStack200NMMHostUnit-12Tx1FxPort
    OBJECT IDENTIFIER ::= { s5ChasTypeBayStack200 2 }
s5ChasTypeBayStack200HostUnit-24Port
    OBJECT IDENTIFIER ::= { s5ChasTypeBayStack200 3 }
s5ChasTypeBayStack200HostUnit-12Port
    OBJECT IDENTIFIER ::= { s5ChasTypeBayStack200 4 }

-- The chassis types for BayStack250 10/100BASE-T Hub
s5ChasTypeBayStack250
    OBJECT IDENTIFIER ::= { s5ChasTypeVal 46 }
s5ChasTypeBayStack250NMMHostUnit-12TxPort
    OBJECT IDENTIFIER ::= { s5ChasTypeBayStack250 1 }
s5ChasTypeBayStack250HostUnit-24Port
    OBJECT IDENTIFIER ::= { s5ChasTypeBayStack250 2 }
s5ChasTypeBayStack250HostUnit-12Port
    OBJECT IDENTIFIER ::= { s5ChasTypeBayStack250 3 }
s5ChasTypeBayStack250NMMHostUnit-24Port
    OBJECT IDENTIFIER ::= { s5ChasTypeBayStack250 4 }
s5ChasTypeBayStack254HostUnit-12Port
    OBJECT IDENTIFIER ::= { s5ChasTypeBayStack250 5 }
s5ChasTypeBayStack255HostUnit-24Port
    OBJECT IDENTIFIER ::= { s5ChasTypeBayStack250 6 }

-- The chassis types for stackProbes RMON probes

s5ChasTypeStackProbe
    OBJECT IDENTIFIER ::= { s5ChasTypeVal 47 }

s5ChasTypeStackProbeOgp -- OGP Probes
    OBJECT IDENTIFIER ::= { s5ChasTypeStackProbe 1 }

s5ChasTypeStackProbeOgpEth -- OGP Ethernet
    OBJECT IDENTIFIER ::= { s5ChasTypeStackProbeOgp 1 }
s5ChasTypeStackProbeOgpEth-1Port
    OBJECT IDENTIFIER ::= { s5ChasTypeStackProbeOgpEth 1 }
s5ChasTypeStackProbeOgpEth-2Port
    OBJECT IDENTIFIER ::= { s5ChasTypeStackProbeOgpEth 2 }
s5ChasTypeStackProbeOgpEth-4Port
    OBJECT IDENTIFIER ::= { s5ChasTypeStackProbeOgpEth 4 }

s5ChasTypeStackProbeOgpTr -- OGP Token Ring
    OBJECT IDENTIFIER ::= { s5ChasTypeStackProbeOgp 2 }
s5ChasTypeStackProbeOgpTr-1Port
    OBJECT IDENTIFIER ::= { s5ChasTypeStackProbeOgpTr 1 }
s5ChasTypeStackProbeOgpTr-2Port
    OBJECT IDENTIFIER ::= { s5ChasTypeStackProbeOgpTr 2 }

s5ChasTypeStackProbeOgpFddi -- OGP FDDI
    OBJECT IDENTIFIER ::= { s5ChasTypeStackProbeOgp 3 }
s5ChasTypeStackProbeOgpFddiSas
    OBJECT IDENTIFIER ::= { s5ChasTypeStackProbeOgpFddi 1 }
s5ChasTypeStackProbeOgpFddiDas
    OBJECT IDENTIFIER ::= { s5ChasTypeStackProbeOgpFddi 2 }

s5ChasTypeStackProbeOgpFeth --OGP Fast-Ethernet
    OBJECT IDENTIFIER ::= { s5ChasTypeStackProbeOgp 4 }
s5ChasTypeStackProbeOgpFeth-1Port
    OBJECT IDENTIFIER ::= { s5ChasTypeStackProbeOgpFeth 1 }
s5ChasTypeStackProbeOgpFeth-2Port
    OBJECT IDENTIFIER ::= { s5ChasTypeStackProbeOgpFeth 2 }

s5ChasTypeStackProbe1000 -- Series 1000 Probes (Pocket Probes)
    OBJECT IDENTIFIER ::= { s5ChasTypeStackProbe 2 }
s5ChasTypeStackProbe1000Eth
    OBJECT IDENTIFIER ::= { s5ChasTypeStackProbe1000 1 }
s5ChasTypeStackProbe1000Eth-1Port
    OBJECT IDENTIFIER ::= { s5ChasTypeStackProbe1000Eth 1 }
s5ChasTypeStackProbe1000Feth
    OBJECT IDENTIFIER ::= { s5ChasTypeStackProbe1000 2 }
s5ChasTypeStackProbe1000Feth-1Port
    OBJECT IDENTIFIER ::= { s5ChasTypeStackProbe1000Feth 1 }

s5ChasTypeStackProbe2000 -- Series 2000 Probes
    OBJECT IDENTIFIER ::= { s5ChasTypeStackProbe 3 }
s5ChasTypeStackProbe2000Eth
    OBJECT IDENTIFIER ::= { s5ChasTypeStackProbe2000 1 }
s5ChasTypeStackProbe2000Eth-1Port
    OBJECT IDENTIFIER ::= { s5ChasTypeStackProbe2000Eth 1 }
s5ChasTypeStackProbe2000Eth-2Port
    OBJECT IDENTIFIER ::= { s5ChasTypeStackProbe2000Eth 2 }
s5ChasTypeStackProbe2000Eth-4Port
    OBJECT IDENTIFIER ::= { s5ChasTypeStackProbe2000Eth 4 }
s5ChasTypeStackProbe2000Fddi
    OBJECT IDENTIFIER ::= { s5ChasTypeStackProbe2000 2 }
s5ChasTypeStackProbe2000FddiSas
    OBJECT IDENTIFIER ::= { s5ChasTypeStackProbe2000Fddi 1 }
s5ChasTypeStackProbe2000FddiDas
    OBJECT IDENTIFIER ::= { s5ChasTypeStackProbe2000Fddi 2 }

s5ChasTypeStackProbe3000 -- Series 3000 Probes
    OBJECT IDENTIFIER ::= { s5ChasTypeStackProbe 4 }
s5ChasTypeStackProbe3000Geth
    OBJECT IDENTIFIER ::= { s5ChasTypeStackProbe3000 1 }
s5ChasTypeStackProbe3000Geth-1Port
    OBJECT IDENTIFIER ::= { s5ChasTypeStackProbe3000Geth 1 }

-- The chassis types for BayStack 450
s5ChasTypeBayStack450
    OBJECT IDENTIFIER ::= { s5ChasTypeVal 48 }
s5ChasTypeBayStack450-12TxPort
    OBJECT IDENTIFIER ::= { s5ChasTypeBayStack450 1 }
s5ChasTypeBayStack450-24TxPort
    OBJECT IDENTIFIER ::= { s5ChasTypeBayStack450 2 }

-- The chassis types for BayStack 303-24T
s5ChasTypeBayStack303-24T
    OBJECT IDENTIFIER ::= { s5ChasTypeVal 49 }

-- The chassis types for Accelar 8010
s5ChasTypeAccelar8010
    OBJECT IDENTIFIER ::= { s5ChasTypeVal 58 }

-- The chassis types for Accelar 8006
s5ChasTypeAccelar8006
    OBJECT IDENTIFIER ::= { s5ChasTypeVal 59 }

-- The chassis types for BayStack 670
s5ChasTypeBayStack670
    OBJECT IDENTIFIER ::= { s5ChasTypeVal 60 }

-- The chassis types for Business Policy Switch 2000
s5ChasTypeBPS2000
    OBJECT IDENTIFIER ::= { s5ChasTypeVal 64 }
s5ChasTypeBPS2000-24TxPort
    OBJECT IDENTIFIER ::= { s5ChasTypeBPS2000 1 }

-- The chassis types for BayStack 3580
s5ChasTypeBayStack3580
    OBJECT IDENTIFIER ::= { s5ChasTypeVal 67 }
s5ChasTypeBayStack3580-16F
    OBJECT IDENTIFIER ::= {s5ChasTypeBayStack3580 1 }

-- The chassis types for BayStack 420
s5ChasTypeBayStack420
    OBJECT IDENTIFIER ::= { s5ChasTypeVal 69 }
s5ChasTypeBayStack420-24TxPort
    OBJECT IDENTIFIER ::= { s5ChasTypeBayStack420 1 }

-- The chassis types for OPTera Metro 1200 Ethernet Service Module
s5ChasTypeMetro1200ESM
    OBJECT IDENTIFIER ::= { s5ChasTypeVal 70 }
s5ChasTypeMetro1200ESM-12TxPort
    OBJECT IDENTIFIER ::= { s5ChasTypeMetro1200ESM 1 }

-- The chassis types for BayStack380
s5ChasTypeBayStack380
    OBJECT IDENTIFIER ::= { s5ChasTypeVal 71 }
s5ChasTypeBayStack380-24TxPort
    OBJECT IDENTIFIER ::= { s5ChasTypeBayStack380 1 }

-- The chassis types for BayStack470
s5ChasTypeBayStack470
    OBJECT IDENTIFIER ::= { s5ChasTypeVal 72 }
s5ChasTypeBayStack470-48TxPort
    OBJECT IDENTIFIER ::= { s5ChasTypeBayStack470 1 }

-- The chassis types for OPTera Metro 1450 Ethernet Service Module
s5ChasTypeMetro1450ESM
    OBJECT IDENTIFIER ::= { s5ChasTypeVal 73 }
s5ChasTypeMetro1450ESM-12TxPort2Gbic
    OBJECT IDENTIFIER ::= { s5ChasTypeMetro1450ESM 1 }

-- The chassis types for OPTera Metro 1400 Ethernet Service Module
s5ChasTypeMetro1400ESM
    OBJECT IDENTIFIER ::= { s5ChasTypeVal 74 }
s5ChasTypeMetro1400ESM-12TxPort2Gbic
    OBJECT IDENTIFIER ::= { s5ChasTypeMetro1400ESM 1 }

-- The chassis types for BayStack 460-24T-PWR
s5ChasTypeBayStack460-24T-PWR
    OBJECT IDENTIFIER ::= { s5ChasTypeVal 75 }
s5ChasTypeBayStack460-24T-PWR-24TxPort
    OBJECT IDENTIFIER ::= { s5ChasTypeBayStack460-24T-PWR 1 }

-- The chassis types for BayStack 10 Power Supply Unit
s5ChasTypeBayStack10
    OBJECT IDENTIFIER ::= { s5ChasTypeVal 76 }
s5ChasTypeBayStack10-powerSupplyUnit
    OBJECT IDENTIFIER ::= { s5ChasTypeBayStack10 1 }

-- The chassis types for BayStack380-24F
s5ChasTypeBayStack380-24F
    OBJECT IDENTIFIER ::= { s5ChasTypeVal 77 }
s5ChasTypeBayStack380-24F-20MiniGbic4Gbic
    OBJECT IDENTIFIER ::= { s5ChasTypeBayStack380-24F 1 }

-- The chassis types for BayStack 5510-24T
s5ChasTypeBayStack5510-24T
    OBJECT IDENTIFIER ::= { s5ChasTypeVal 78 }
s5ChasTypeBayStack5510-24T-24TxPort
    OBJECT IDENTIFIER ::= { s5ChasTypeBayStack5510-24T 1 }

-- The chassis types for BayStack 5510-48T
s5ChasTypeBayStack5510-48T
    OBJECT IDENTIFIER ::= { s5ChasTypeVal 79 }
s5ChasTypeBayStack5510-48T-48TxPort
    OBJECT IDENTIFIER ::= { s5ChasTypeBayStack5510-48T 1 }

-- The chassis types for BayStack470 24-port version
s5ChasTypeBayStack470-24T
    OBJECT IDENTIFIER ::= { s5ChasTypeVal 80 }
s5ChasTypeBayStack470-24TxPort
    OBJECT IDENTIFIER ::= { s5ChasTypeBayStack470-24T 1 }

-- The chassis types for Nortel Networks Wireless LAN Access Point 2220
s5ChasTypeWLANAccessPoint2220
    OBJECT IDENTIFIER ::= { s5ChasTypeVal 81 }
s5ChasTypeWLANAccessPoint2220-wirelessAP
    OBJECT IDENTIFIER ::= { s5ChasTypeWLANAccessPoint2220 1 }

-- The chassis types for Nortel Networks Wireless LAN Security Switch 2250
s5ChasTypeWLANSecuritySwitch2250
    OBJECT IDENTIFIER ::= { s5ChasTypeVal 82 }
s5ChasTypeWLANSecuritySwitch2250-securitySwitch
    OBJECT IDENTIFIER ::= { s5ChasTypeWLANSecuritySwitch2250 1 }

-- The chassis types for BayStack 425
s5ChasTypeBayStack425
    OBJECT IDENTIFIER ::= { s5ChasTypeVal 83 }
s5ChasTypeBayStack425-24
    OBJECT IDENTIFIER ::= { s5ChasTypeBayStack425 1 }
s5ChasTypeBayStack425-48
    OBJECT IDENTIFIER ::= { s5ChasTypeBayStack425 2 }

-- The chassis types for Nortel Networks Wireless LAN Access Point 2221
s5ChasTypeWLANAccessPoint2221
    OBJECT IDENTIFIER ::= { s5ChasTypeVal 84 }
s5ChasTypeWLANAccessPoint2221-wirelessAP
    OBJECT IDENTIFIER ::= { s5ChasTypeWLANAccessPoint2221 1 }

-- The chassis types for BayStack 5520-24T-PWR and 5520-48T-PWR
s5ChasTypeBayStack5520
    OBJECT IDENTIFIER ::= { s5ChasTypeVal 85 }
s5ChasTypeBayStack5520-24T-PWR-24TxPort
    OBJECT IDENTIFIER ::= { s5ChasTypeBayStack5520 1 }
s5ChasTypeBayStack5520-48T-PWR-48TxPort
    OBJECT IDENTIFIER ::= { s5ChasTypeBayStack5520 2 }

-- The chassis types for BayStack 325
s5ChasTypeBayStack325
    OBJECT IDENTIFIER ::= { s5ChasTypeVal 86 }
s5ChasTypeBayStack325-24T
    OBJECT IDENTIFIER ::= { s5ChasTypeBayStack325 1 }
s5ChasTypeBayStack325-24G
    OBJECT IDENTIFIER ::= { s5ChasTypeBayStack325 2 }

-- The chassis types for Nortel Networks Wireless LAN Access Point 2225
s5ChasTypeWLANAccessPoint2225
    OBJECT IDENTIFIER ::= { s5ChasTypeVal 87 }
s5ChasTypeWLANAccessPoint2225-wirelessAP
    OBJECT IDENTIFIER ::= { s5ChasTypeWLANAccessPoint2225 1 }

-- The chassis types for BayStack470 24-port PWR version
s5ChasTypeBayStack470-24T-PWR
    OBJECT IDENTIFIER ::= { s5ChasTypeVal 88 }
s5ChasTypeBayStack470-24TxPort-PWR
    OBJECT IDENTIFIER ::= { s5ChasTypeBayStack470-24T-PWR 1 }

-- The chassis types for BayStack470 48-port PWR version
s5ChasTypeBayStack470-48T-PWR
    OBJECT IDENTIFIER ::= { s5ChasTypeVal 89 }
s5ChasTypeBayStack470-48TxPort-PWR
    OBJECT IDENTIFIER ::= { s5ChasTypeBayStack470-48T-PWR 1 }

-- The chassis types for Nortel Networks Wireless LAN Security Switch 2270
s5ChasTypeWLANSecuritySwitch2270
    OBJECT IDENTIFIER ::= { s5ChasTypeVal 90 }
s5ChasTypeWLANSecuritySwitch2270-securitySwitch
    OBJECT IDENTIFIER ::= { s5ChasTypeWLANSecuritySwitch2270 1 }

-- The chassis types for Ethernet Routing Switch 5530
s5ChasTypeEthernetRoutingSwitch5530
    OBJECT IDENTIFIER ::= { s5ChasTypeVal 91 }
s5ChasTypeEthernetRoutingSwitch5530-24TFD
    OBJECT IDENTIFIER ::= { s5ChasTypeEthernetRoutingSwitch5530 1 }

-- The chassis types for Ethernet Switch 3510
s5ChasTypeEthernetSwitch3510
    OBJECT IDENTIFIER ::= { s5ChasTypeVal 92 }
s5ChasTypeEthernetSwitch3510-24T
    OBJECT IDENTIFIER ::= { s5ChasTypeEthernetSwitch3510 1 }

-- The chassis types for SMB GIG BES 1010
s5ChasTypeBES1010
    OBJECT IDENTIFIER ::= { s5ChasTypeVal 93 }
s5ChasTypeBES1010-24T
    OBJECT IDENTIFIER ::= { s5ChasTypeBES1010 1 }
s5ChasTypeBES1010-48T
    OBJECT IDENTIFIER ::= { s5ChasTypeBES1010 2 }

-- The chassis types for SMB GIG BES 1020
s5ChasTypeBES1020
    OBJECT IDENTIFIER ::= { s5ChasTypeVal 94 }
s5ChasTypeBES1020-24T-PWR
    OBJECT IDENTIFIER ::= { s5ChasTypeBES1020 1 }
s5ChasTypeBES1020-48T-PWR
    OBJECT IDENTIFIER ::= { s5ChasTypeBES1020 2 }

-- The chassis types for SMB GIG BES 2010
s5ChasTypeBES2010
    OBJECT IDENTIFIER ::= { s5ChasTypeVal 95 }
s5ChasTypeBES2010-24T
    OBJECT IDENTIFIER ::= { s5ChasTypeBES2010 1 }
s5ChasTypeBES2010-48T
    OBJECT IDENTIFIER ::= { s5ChasTypeBES2010 2 }

-- The chassis types for SMB GIG BES 2020
s5ChasTypeBES2020
    OBJECT IDENTIFIER ::= { s5ChasTypeVal 96 }
s5ChasTypeBES2020-24T-PWR
    OBJECT IDENTIFIER ::= { s5ChasTypeBES2020 1 }
s5ChasTypeBES2020-48T-PWR
    OBJECT IDENTIFIER ::= { s5ChasTypeBES2020 2 }

-- The chassis types for SMB FE BES 110
s5ChasTypeBES110
    OBJECT IDENTIFIER ::= { s5ChasTypeVal 97 }
s5ChasTypeBES110-24T
    OBJECT IDENTIFIER ::= { s5ChasTypeBES110 1 }
s5ChasTypeBES110-48T
    OBJECT IDENTIFIER ::= { s5ChasTypeBES110 2 }

-- The chassis types for SMB FE BES 120
s5ChasTypeBES120
    OBJECT IDENTIFIER ::= { s5ChasTypeVal 98 }
s5ChasTypeBES120-24T-PWR
    OBJECT IDENTIFIER ::= { s5ChasTypeBES120 1 }
s5ChasTypeBES120-48T-PWR
    OBJECT IDENTIFIER ::= { s5ChasTypeBES120 2 }

-- The chassis types for SMB FE BES 210
s5ChasTypeBES210
    OBJECT IDENTIFIER ::= { s5ChasTypeVal 99 }
s5ChasTypeBES210-24T
    OBJECT IDENTIFIER ::= { s5ChasTypeBES210 1 }
s5ChasTypeBES210-48T
    OBJECT IDENTIFIER ::= { s5ChasTypeBES210 2 }

-- The chassis types for SMB FE BES 220
s5ChasTypeBES220
    OBJECT IDENTIFIER ::= { s5ChasTypeVal 100 }
s5ChasTypeBES220-24T-PWR
    OBJECT IDENTIFIER ::= { s5ChasTypeBES220 1 }
s5ChasTypeBES220-48T-PWR
    OBJECT IDENTIFIER ::= { s5ChasTypeBES220 2 }

-- The chassis types for ERS 45xx (Botany Bay)
s5ChasTypeERS45xx
    OBJECT IDENTIFIER ::= { s5ChasTypeVal 101 }
s5ChasTypeERS4548GT
    OBJECT IDENTIFIER ::= { s5ChasTypeERS45xx 1 }
s5ChasTypeERS4548GT-PWR
    OBJECT IDENTIFIER ::= { s5ChasTypeERS45xx 2 }
s5ChasTypeERS4550T
    OBJECT IDENTIFIER ::= { s5ChasTypeERS45xx 3 }
s5ChasTypeERS4550T-PWR
    OBJECT IDENTIFIER ::= { s5ChasTypeERS45xx 4 }
s5ChasTypeERS4526FX
    OBJECT IDENTIFIER ::= { s5ChasTypeERS45xx 5 }
s5ChasTypeERS4526GTX-PWR
    OBJECT IDENTIFIER ::= { s5ChasTypeERS45xx 6 }
s5ChasTypeERS4526GTX
    OBJECT IDENTIFIER ::= { s5ChasTypeERS45xx 7 }
s5ChasTypeERS4524GT
    OBJECT IDENTIFIER ::= { s5ChasTypeERS45xx 8 }
s5ChasTypeERS4526T-PWR
    OBJECT IDENTIFIER ::= { s5ChasTypeERS45xx 9 }
s5ChasTypeERS4526T
    OBJECT IDENTIFIER ::= { s5ChasTypeERS45xx 10 }
s5ChasTypeERS4524GT-PWR
    OBJECT IDENTIFIER ::= { s5ChasTypeERS45xx 11 }
s5ChasTypeERS4526T-PWR-PLUS
    OBJECT IDENTIFIER ::= { s5ChasTypeERS45xx 12 }
s5ChasTypeERS4550T-PWR-PLUS
    OBJECT IDENTIFIER ::= { s5ChasTypeERS45xx 13 }

-- The chassis types for ERS 25xx
s5ChasTypeERS25xx
    OBJECT IDENTIFIER ::= { s5ChasTypeVal 102 }
s5ChasTypeERS2500-26T
    OBJECT IDENTIFIER ::= { s5ChasTypeERS25xx 1 }
s5ChasTypeERS2500-26T-PWR
    OBJECT IDENTIFIER ::= { s5ChasTypeERS25xx 2 }
s5ChasTypeERS2500-50T
    OBJECT IDENTIFIER ::= { s5ChasTypeERS25xx 3 }
s5ChasTypeERS2500-50T-PWR
    OBJECT IDENTIFIER ::= { s5ChasTypeERS25xx 4 }

-- The chassis types for ERS 56xx
s5ChasTypeERS56xx
    OBJECT IDENTIFIER ::= { s5ChasTypeVal 103 }
s5ChasTypeERS5698-TFD-PWR
    OBJECT IDENTIFIER ::= { s5ChasTypeERS56xx 1 }
s5ChasTypeERS5698-TFD
    OBJECT IDENTIFIER ::= { s5ChasTypeERS56xx 2 }
s5ChasTypeERS5650-TD-PWR
    OBJECT IDENTIFIER ::= { s5ChasTypeERS56xx 3 }
s5ChasTypeERS5650-TD
    OBJECT IDENTIFIER ::= { s5ChasTypeERS56xx 4 }
s5ChasTypeERS5632-FD
    OBJECT IDENTIFIER ::= { s5ChasTypeERS56xx 5 }

-- The chassis types for ESU1860
s5ChasTypeESU1860
    OBJECT IDENTIFIER ::= { s5ChasTypeVal 104 }
s5ChasTypeESU1860S
    OBJECT IDENTIFIER ::= { s5ChasTypeESU1860 1 }
s5ChasTypeESU1860B
    OBJECT IDENTIFIER ::= { s5ChasTypeESU1860 2 }
s5ChasTypeESU1860T
    OBJECT IDENTIFIER ::= { s5ChasTypeESU1860 3 }
s5ChasTypeESU1860V
    OBJECT IDENTIFIER ::= { s5ChasTypeESU1860 4 }

-- The chassis types for ESU1880
s5ChasTypeESU1880
    OBJECT IDENTIFIER ::= { s5ChasTypeVal 105 }
s5ChasTypeESU1880S
    OBJECT IDENTIFIER ::= { s5ChasTypeESU1880 1 }

-- The chassis types for ERS 66xx
s5ChasTypeERS66xx
    OBJECT IDENTIFIER ::= { s5ChasTypeVal 106 }
s5ChasTypeERS642-XSGT
    OBJECT IDENTIFIER ::= { s5ChasTypeERS66xx 1 }
s5ChasTypeERS6632-XTS
    OBJECT IDENTIFIER ::= { s5ChasTypeERS66xx 2 }

-- The chassis types for WC 8xxx
s5ChasTypeWC8xxx
    OBJECT IDENTIFIER ::= { s5ChasTypeVal 107 }
s5ChasTypeWC8180
    OBJECT IDENTIFIER ::= { s5ChasTypeWC8xxx 1 }

-- The chassis types for ERS 48xx
s5ChasTypeERS48xx
    OBJECT IDENTIFIER ::= { s5ChasTypeVal 108 }
s5ChasTypeERS4826GTS-PWR-PLUS
    OBJECT IDENTIFIER ::= { s5ChasTypeERS48xx 1 }
s5ChasTypeERS4850GTS-PWR-PLUS
    OBJECT IDENTIFIER ::= { s5ChasTypeERS48xx 2 }
s5ChasTypeERS4826GTS
    OBJECT IDENTIFIER ::= { s5ChasTypeERS48xx 3 }
s5ChasTypeERS4850GTS
    OBJECT IDENTIFIER ::= { s5ChasTypeERS48xx 4 }

-- The chassis types for VSP 7xxx
s5ChasTypeVSP7xxx
    OBJECT IDENTIFIER ::= { s5ChasTypeVal 109 }
s5ChasTypeVSP7024XLS
    OBJECT IDENTIFIER ::= { s5ChasTypeVSP7xxx 1 }

-- The chassis types for ERS 35xx
s5ChasTypeERS35xx
    OBJECT IDENTIFIER ::= { s5ChasTypeVal 110 }
s5ChasTypeERS3510GT
    OBJECT IDENTIFIER ::= { s5ChasTypeERS35xx 1 }
s5ChasTypeERS3510GT-PWR-PLUS
    OBJECT IDENTIFIER ::= { s5ChasTypeERS35xx 2 }
s5ChasTypeERS3524GT
    OBJECT IDENTIFIER ::= { s5ChasTypeERS35xx 3 }
s5ChasTypeERS3524GT-PWR-PLUS
    OBJECT IDENTIFIER ::= { s5ChasTypeERS35xx 4 }
s5ChasTypeERS3526GT
    OBJECT IDENTIFIER ::= { s5ChasTypeERS35xx 5 }
s5ChasTypeERS3526GT-PWR-PLUS
    OBJECT IDENTIFIER ::= { s5ChasTypeERS35xx 6 }
s5ChasTypeERS3526T
    OBJECT IDENTIFIER ::= { s5ChasTypeERS35xx 7 }
s5ChasTypeERS3526T-PWR-PLUS
    OBJECT IDENTIFIER ::= { s5ChasTypeERS35xx 8 }
s5ChasTypeERS3549GTS
    OBJECT IDENTIFIER ::= { s5ChasTypeERS35xx 9 }
s5ChasTypeERS3549GTS-PWR-PLUS
    OBJECT IDENTIFIER ::= { s5ChasTypeERS35xx 10 }
s5ChasTypeERS3550T
    OBJECT IDENTIFIER ::= { s5ChasTypeERS35xx 11 }
s5ChasTypeERS3550T-PWR-PLUS
    OBJECT IDENTIFIER ::= { s5ChasTypeERS35xx 12 }

-- The chassis types for ERS 5900
s5ChasTypeERS59xx
    OBJECT IDENTIFIER ::= { s5ChasTypeVal 111 }
s5ChasTypeERS5928GTS
    OBJECT IDENTIFIER ::= { s5ChasTypeERS59xx 1 }
s5ChasTypeERS5928GTS-PWR-PLUS
    OBJECT IDENTIFIER ::= { s5ChasTypeERS59xx 2 }
s5ChasTypeERS5952GTS
    OBJECT IDENTIFIER ::= { s5ChasTypeERS59xx 3 }
s5ChasTypeERS5952GTS-PWR-PLUS
    OBJECT IDENTIFIER ::= { s5ChasTypeERS59xx 4 }
s5ChasTypeERS5928GTS-UPWR
    OBJECT IDENTIFIER ::= { s5ChasTypeERS59xx 5 }
s5ChasTypeERS59100GTS
    OBJECT IDENTIFIER ::= { s5ChasTypeERS59xx 6 }
s5ChasTypeERS59100GTS-PWR-PLUS
    OBJECT IDENTIFIER ::= { s5ChasTypeERS59xx 7 }
s5ChasTypeERS5928MTS-UPWR
    OBJECT IDENTIFIER ::= { s5ChasTypeERS59xx 8 }

-- The chassis types for ERS 4900
s5ChasTypeERS49xx
    OBJECT IDENTIFIER ::= { s5ChasTypeVal 112 }
s5ChasTypeERS4926GTS
    OBJECT IDENTIFIER ::= { s5ChasTypeERS49xx 1 }
s5ChasTypeERS4926GTS-PWR-PLUS
    OBJECT IDENTIFIER ::= { s5ChasTypeERS49xx 2 }
s5ChasTypeERS4950GTS
    OBJECT IDENTIFIER ::= { s5ChasTypeERS49xx 3 }
s5ChasTypeERS4950GTS-PWR-PLUS
    OBJECT IDENTIFIER ::= { s5ChasTypeERS49xx 4 }

-- The chassis types for ERS 3600
s5ChasTypeERS36xx
    OBJECT IDENTIFIER ::= { s5ChasTypeVal 113 }
s5ChasTypeERS3626GTS
    OBJECT IDENTIFIER ::= { s5ChasTypeERS36xx 1 }
s5ChasTypeERS3626GTS-PWR-PLUS
    OBJECT IDENTIFIER ::= { s5ChasTypeERS36xx 2 }
s5ChasTypeERS3650GTS
    OBJECT IDENTIFIER ::= { s5ChasTypeERS36xx 3 }
s5ChasTypeERS3650GTS-PWR-PLUS
    OBJECT IDENTIFIER ::= { s5ChasTypeERS36xx 4 }

-- Registrations for Chassis Group Types
-- (values for object s5ChasGrpType)
s5ChasGrpTypeVal OBJECT IDENTIFIER ::= { s5reg 2 }

-- Supervisor group
s5ChasGrpSup OBJECT IDENTIFIER ::= { s5ChasGrpTypeVal 1 }

-- Backplane group
s5ChasGrpBkpl OBJECT IDENTIFIER ::= { s5ChasGrpTypeVal 2 }

-- Board (or slots) group
s5ChasGrpBrd OBJECT IDENTIFIER ::= { s5ChasGrpTypeVal 3 }

-- Power supply group
s5ChasGrpPwr OBJECT IDENTIFIER ::= { s5ChasGrpTypeVal 4 }

-- Chassis level temperature sensor group
s5ChasGrpTmpSnr
    OBJECT IDENTIFIER ::= { s5ChasGrpTypeVal 5 }

-- Chassis level fan group
s5ChasGrpFan OBJECT IDENTIFIER ::= { s5ChasGrpTypeVal 6 }

-- Chassis level clock group
s5ChasGrpClk OBJECT IDENTIFIER ::= { s5ChasGrpTypeVal 7 }

-- Virtual chassis unit group
s5ChasGrpUnit OBJECT IDENTIFIER ::= { s5ChasGrpTypeVal 8 }

-- Registrations for Chassis Components and Sub-components
-- (values for object s5ChasComType)
s5ChasComTypeVal
    OBJECT IDENTIFIER ::= { s5reg 3 }

-- Backplanes
s5ChasComBkpl OBJECT IDENTIFIER ::= { s5ChasComTypeVal 1 }

-- Model 5000 Lower Backplane
s5ChasComBkplM5000low
    OBJECT IDENTIFIER ::= { s5ChasComBkpl 1 }
-- Model 5000(920-209) Ethernet/Token Ring/CMB Backplane
s5ChasComBkplM5000lowCmbEthTok
    OBJECT IDENTIFIER ::= { s5ChasComBkplM5000low 4 }

-- Model 5000(920-???) Ethernet/CMB Backplane
s5ChasComBkplM5000lowCmbEth
    OBJECT IDENTIFIER ::= { s5ChasComBkplM5000low 5 }

-- Model 5000 Middle Left Backplane
s5ChasComBkplM5000midLeft
    OBJECT IDENTIFIER ::= { s5ChasComBkpl 2 }

-- Model 5000(920-241) Full Size FDDI Backplane
s5ChasComBkplM5000midLeftFddiFull
    OBJECT IDENTIFIER ::= { s5ChasComBkplM5000midLeft 0 }

-- Model 5000 Middle Right Backplane
s5ChasComBkplM5000midRight
    OBJECT IDENTIFIER ::= { s5ChasComBkpl 3 }

-- Model 5000 Upper Left Backplane
s5ChasComBkplM5000highLeft
    OBJECT IDENTIFIER ::= { s5ChasComBkpl 4 }

-- Model 5000 Upper Right Backplane
s5ChasComBkplM5000highRight
    OBJECT IDENTIFIER ::= { s5ChasComBkpl 5 }

-- Centillion Backplane
s5ChasComBkplCentATM
    OBJECT IDENTIFIER ::= { s5ChasComBkpl 6 }

-- BH/Catapult Backplane
s5ChasComBkpl2x65000BH
    OBJECT IDENTIFIER ::= { s5ChasComBkpl 7 }
s5ChasComBkpl1x125000BH
    OBJECT IDENTIFIER ::= { s5ChasComBkpl 8 }

-- C50N/C50T Backplane
s5ChasComBkplC50
    OBJECT IDENTIFIER ::= { s5ChasComBkpl 9 }

-- Backplanes (NEW names)
s5ChasComMBkpl OBJECT IDENTIFIER ::= { s5ChasComTypeVal 7 }

s5ChasComM5000Bkpl -- 5000 Chassis
    OBJECT IDENTIFIER ::= { s5ChasComMBkpl 12 }

s5ChasComM5005Bkpl -- 5005 Chassis
    OBJECT IDENTIFIER ::= { s5ChasComMBkpl 17 }

s5ChasComM5Dx000Bkpl -- Distributed 5000 Hub Backplane
    OBJECT IDENTIFIER ::= { s5ChasComMBkpl 24 }
s5ChasComM5DN000BkplEth3
    OBJECT IDENTIFIER ::= { s5ChasComM5Dx000Bkpl 1 }

s5ChasComMNBayStackBkpl -- BayStack Ethernet Stack
    OBJECT IDENTIFIER ::= { s5ChasComMBkpl 25 }
s5ChasComMNBayStackBkplEth3
    OBJECT IDENTIFIER ::= { s5ChasComMNBayStackBkpl 1 }

s5ChasComBayStack100Bkpl -- BayStack 100BASE-T Hub Stack
    OBJECT IDENTIFIER ::= { s5ChasComMBkpl 27 }

s5ChasComM3000Bkpl -- 3000 Chassis Backplane
    OBJECT IDENTIFIER ::= { s5ChasComMBkpl 28 }

s5ChasCom28200Bkpl -- 28200 Backplane
    OBJECT IDENTIFIER ::= { s5ChasComMBkpl 30 }

s5ChasComMBayStackTrBkpl -- BayStack Token Ring Hub Backplane
    OBJECT IDENTIFIER ::= { s5ChasComMBkpl 36 }
s5ChasComMBayStackTrBkplTr1 -- BayStack Token Ring Stack
    OBJECT IDENTIFIER ::= { s5ChasComMBayStackTrBkpl 1 }

s5ChasComM3030Bkpl -- 3030 Chassis Backplane
    OBJECT IDENTIFIER ::= { s5ChasComMBkpl 39 }

s5ChasComSwitchNodeBkpl -- Switch Node Backplane
    OBJECT IDENTIFIER ::= { s5ChasComMBkpl 40 }

s5ChasComBayStack150Bkpl -- BayStack150 Ethernet Stack
    OBJECT IDENTIFIER ::= { s5ChasComMBkpl 41 }
s5ChasComBayStack150BkplEth
    OBJECT IDENTIFIER ::= { s5ChasComBayStack150Bkpl 1 }

s5ChasComMBayStack303-304Bkpl -- BayStack 303/304 Backplane
    OBJECT IDENTIFIER ::= { s5ChasComMBkpl 42 }

s5ChasComBayStack200Bkpl -- BayStack200 Ethernet Stack
    OBJECT IDENTIFIER ::= { s5ChasComMBkpl 43 }
s5ChasComBayStack200BkplEth
    OBJECT IDENTIFIER ::= { s5ChasComBayStack200Bkpl 1 }

s5ChasComBayStack250Bkpl -- BayStack250 Ethernet Stack
    OBJECT IDENTIFIER ::= { s5ChasComMBkpl 44 }
s5ChasComBayStack250BkplEth10 -- 10Mb Bkpl
    OBJECT IDENTIFIER ::= { s5ChasComBayStack250Bkpl 1 }
s5ChasComBayStack250BkplEth100 -- 100Mb Bkpl
    OBJECT IDENTIFIER ::= { s5ChasComBayStack250Bkpl 2 }

s5ChasComMAccelar8010Bkpl -- Accelar 8010 Chassis Backplane
    OBJECT IDENTIFIER ::= { s5ChasComMBkpl 45 }

--- Model 3000 Ethernet Backplane
s5ChasComM3000EthBkpl
    OBJECT IDENTIFIER ::= { s5ChasComM3000Bkpl 2 }
s5ChasComM3000-1Bkpl -- Model 3000-1 Ethernet Backplane
    OBJECT IDENTIFIER ::= { s5ChasComM3000EthBkpl 0 }
s5ChasComM3000NBkpl -- Model 3000N Multi-Segment Ethernet Backplane
    OBJECT IDENTIFIER ::= { s5ChasComM3000EthBkpl 7 }

--- Model 3000 Ethernet/Token Ring Backplane
s5ChasComM3000EthTokBkpl
    OBJECT IDENTIFIER ::= { s5ChasComM3000Bkpl 3 }
s5ChasComM3000-4Bkpl -- Model 3000-4 Enet/Token Ring Backplane
    OBJECT IDENTIFIER ::= { s5ChasComM3000EthTokBkpl 4 }
s5ChasComM3000NTBkpl -- Model 3000NT Multi-Segment Enet/TR Backplane
    OBJECT IDENTIFIER ::= { s5ChasComM3000EthTokBkpl 5 }

--- Model 3000 Ethernet/FDDI Backplane
s5ChasComM3000EthFddiBkpl
    OBJECT IDENTIFIER ::= { s5ChasComM3000Bkpl 4 }

--- Model 3000 Ethernet/Token Ring/FDDI Backplane
s5ChasComM3000EthTokFddiBkpl
    OBJECT IDENTIFIER ::= { s5ChasComM3000Bkpl 5 }
s5ChasComM3000-5Bkpl -- Model 3000-5 Enet/Token Ring/FDDI Backplane
    OBJECT IDENTIFIER ::= { s5ChasComM3000EthTokFddiBkpl 2 }
s5ChasComM3000SBkpl -- Model 3000S Multi-Segment Enet/TR/FDDI Backplane
    OBJECT IDENTIFIER ::= { s5ChasComM3000EthTokFddiBkpl 6 }

--- Model 3000 Ethernet/Token Ring Backplane with Redundant Power
s5ChasComM3000EthTokRedBkpl
    OBJECT IDENTIFIER ::= { s5ChasComM3000Bkpl 6 }
s5ChasComM3000-4RBkpl -- Model 3000-4R Multi-Segment Enet/TR Backplane
    OBJECT IDENTIFIER ::= { s5ChasComM3000EthTokRedBkpl 1 }
s5ChasComM3000NTRBkpl -- Model 3000NTR Multi-Segment Ethernet/TR Backplane
    OBJECT IDENTIFIER ::= { s5ChasComM3000EthTokRedBkpl 9 }

--- Model 3000 Ethernet/Token Ring/FDDI Backplane with Redundant Power
s5ChasComM3000EthTokFddiRedBkpl
    OBJECT IDENTIFIER ::= { s5ChasComM3000Bkpl 7 }
s5ChasComM3000-5RBkpl -- Model 3000-5R Multi-Segment Enet/TR/FDDI Backplane

    OBJECT IDENTIFIER ::= { s5ChasComM3000EthTokFddiRedBkpl 3 }
s5ChasComM3000SRBkpl -- Model 3000SR Multi-Segment Enet/TR/FDDI Backplane
    OBJECT IDENTIFIER ::= { s5ChasComM3000EthTokFddiRedBkpl 8 }

--- Model 3000 Token Ring Backplane
s5ChasComM3000TokBkpl
    OBJECT IDENTIFIER ::= { s5ChasComM3000Bkpl 8 }

--- Model 3000CT Multi-Segment Ethernet/Token Ring/Fast Ethernet Backplane
s5ChasComM3000CTBkpl
    OBJECT IDENTIFIER ::= { s5ChasComM3000Bkpl 9 }

--- Model 3000C Multi-Segment Ethernet/Fast Ethernet Backplane
s5ChasComM3000CBkpl
    OBJECT IDENTIFIER ::= { s5ChasComM3000Bkpl 10 }

--- Model 3000CTR Multi-Segment Ethernet/Token Ring/Fast Ethernet Backplane

--- with Redundant Power
s5ChasComM3000CTRBkpl
    OBJECT IDENTIFIER ::= { s5ChasComM3000Bkpl 11 }

--- Model 3030 Ethernet Backplane
s5ChasComM3030EthBkpl
    OBJECT IDENTIFIER ::= { s5ChasComM3030Bkpl 1 }

--- Model 3030C Ethernet/Token Ring Backplane
s5ChasComM3030EthTrBkpl
    OBJECT IDENTIFIER ::= { s5ChasComM3030Bkpl 5 }

-- Model 5000 Lower Backplane
s5ChasComM5000BkplLow
    OBJECT IDENTIFIER ::= { s5ChasComM5000Bkpl 1 }
-- Model 5000(920-209) Ethernet/Token Ring/CMB Backplane
s5ChasComM5000BkplLowCmbEthTok
    OBJECT IDENTIFIER ::= { s5ChasComM5000BkplLow 4 }

-- Model 5000(920-303) Ethernet/CMB Backplane
s5ChasComM5000BkplLowCmbEth
    OBJECT IDENTIFIER ::= { s5ChasComM5000BkplLow 5 }

-- Model 5000 Middle Left Backplane
s5ChasComM5000BkplMidLeft
    OBJECT IDENTIFIER ::= { s5ChasComM5000Bkpl 2 }

-- Model 5000(920-241) Full Size FDDI Backplane
s5ChasComM5000BkplMidLeftFddiFull
    OBJECT IDENTIFIER ::= { s5ChasComM5000BkplMidLeft 0 }

-- Model 5000 Full Size 100Mbps Ethernet Backplane
s5ChasComM5000BkplMidLeftEth100MbsFull
    OBJECT IDENTIFIER ::= { s5ChasComM5000BkplMidLeft 4 }

-- Model 5000 8 slots Size 100Mbps Ethernet Backplane
s5ChasComM5000BkplMidLeftEth100Mbs
    OBJECT IDENTIFIER ::= { s5ChasComM5000BkplMidLeft 7 }

-- Model 5000 Middle Right Backplane
s5ChasComM5000BkplMidRight
    OBJECT IDENTIFIER ::= { s5ChasComM5000Bkpl 3 }

-- Model 5000 6 slot Size FDDI Backplane
s5ChasComBkplM5000midRightFddi
    OBJECT IDENTIFIER ::= { s5ChasComBkplM5000midRight 0 }

-- Model 5000 Upper Left Backplane
s5ChasComM5000BkplHighLeft
    OBJECT IDENTIFIER ::= { s5ChasComM5000Bkpl 4 }
-- Model 5000 100MBps Ethernet Backplane
s5ChasComM5000BkplHighLeftEth100Mbs
    OBJECT IDENTIFIER ::= { s5ChasComM5000BkplHighLeft 4 }
-- Model 5000 Switched Packet Bus (GPB) Backplane
s5ChasComM5000BkplHighLeftSwitchedPktBusFull
    OBJECT IDENTIFIER ::= { s5ChasComM5000BkplHighLeft 5 }
-- Model 5000 ATM 16 Port Backplane
s5ChasComM5000BkplHighLeftAtm16
    OBJECT IDENTIFIER ::= { s5ChasComM5000BkplHighLeft 8 }
-- Model 5000 ATM 64 Port Backplane
s5ChasComM5000BkplHighLeftAtm64
    OBJECT IDENTIFIER ::= { s5ChasComM5000BkplHighLeft 9 }

-- Model 5000 Upper Right Backplane
s5ChasComM5000BkplHighRight
    OBJECT IDENTIFIER ::= { s5ChasComM5000Bkpl 5 }

-- Model 5005 Lower Backplane
s5ChasComM5005BkplLow
    OBJECT IDENTIFIER ::= { s5ChasComM5005Bkpl 1 }
-- Model 5005(920-305) Ethernet/Token Ring/CMB Backplane
s5ChasComM5005BkplLowCmbEthTok
    OBJECT IDENTIFIER ::= { s5ChasComM5005BkplLow 4 }

-- Model 5005(920-316) Ethernet/CMB Backplane
s5ChasComM5005BkplLowCmbEth
    OBJECT IDENTIFIER ::= { s5ChasComM5005BkplLow 5 }

-- Model 5005 Middle Backplane
s5ChasComM5005BkplMidLeft
    OBJECT IDENTIFIER ::= { s5ChasComM5005Bkpl 2 }
-- Model 5005 Fddi Backplane
s5ChasComM5005BkplMidLeftFddi
    OBJECT IDENTIFIER ::= { s5ChasComM5005BkplMidLeft 1 }

-- Model 5005 100 Mbps Backplane
s5ChasComM5005BkplMidLeftEth100Mbs
    OBJECT IDENTIFIER ::= { s5ChasComM5005BkplMidLeft 5 }

-- Model 5005 Upper Backplane
s5ChasComM5005BkplHighLeft
    OBJECT IDENTIFIER ::= { s5ChasComM5005Bkpl 4 }
-- Model 5005 Switched Packet Bus (GPB) Backplane
s5ChasComM5005BkplHighLeftSwitchedPktBus
    OBJECT IDENTIFIER ::= { s5ChasComM5005BkplHighLeft 6 }

-- Power supplies
s5ChasComPwr OBJECT IDENTIFIER ::= { s5ChasComTypeVal 2 }

-- Model 5000 950 Watt AC Chassis Power Supply with
-- internal fan and temperature sensor
s5ChasComPwrM5000-950A
    OBJECT IDENTIFIER ::= { s5ChasComPwr 0 }
s5ChasComPwrM5000-950AFan -- Internal Fan
    OBJECT IDENTIFIER ::= { s5ChasComPwrM5000-950A 1 }
s5ChasComPwrM5000-950ATmpSnr -- Internal Temerature Sensor
    OBJECT IDENTIFIER ::= { s5ChasComPwrM5000-950A 2 }

-- Model 5000 (721-018) 950 Watt AC Chassis Power Supply with
-- internal fan and temperature sensor
s5ChasComPwrM5000-950
    OBJECT IDENTIFIER ::= { s5ChasComPwr 1 }
s5ChasComPwrM5000-950Fan -- Internal Fan
    OBJECT IDENTIFIER ::= { s5ChasComPwrM5000-950 1 }
s5ChasComPwrM5000-950TmpSnr -- Internal Temerature Sensor
    OBJECT IDENTIFIER ::= { s5ChasComPwrM5000-950 2 }

-- Centillion AC Chassis Power Supply
s5ChasComPwrCent OBJECT IDENTIFIER ::= { s5ChasComPwr 2 }
--Centillion 50N Chassis Power Supply
s5ChasComPwrCent50N OBJECT IDENTIFIER ::= { s5ChasComPwr 3 }
--Centillion 50T Chassis Power Supply
s5ChasComPwrCent50T OBJECT IDENTIFIER ::= { s5ChasComPwr 4 }

-- Power supplies (NEW names)
s5ChasComMPwr OBJECT IDENTIFIER ::= { s5ChasComTypeVal 8 }

s5ChasComM5000Pwr -- 5000 Chassis
    OBJECT IDENTIFIER ::= { s5ChasComMPwr 12 }

s5ChasComM5005Pwr -- 5005 Chassis
    OBJECT IDENTIFIER ::= { s5ChasComMPwr 17 }

s5ChasComM1032xPwr -- 1032x Chassis
    OBJECT IDENTIFIER ::= { s5ChasComMPwr 16 }

s5ChasComM5DN000Pwr -- Distributed 5000 Chassis
    OBJECT IDENTIFIER ::= { s5ChasComMPwr 24 }

s5ChasComMNBayStackPwr -- BayStack Ethernet Hub Power Supply
    OBJECT IDENTIFIER ::= { s5ChasComMPwr 25 }

s5ChasComMBayStack100Pwr -- BayStack 100BASE-T Power Supply
    OBJECT IDENTIFIER ::= { s5ChasComMPwr 27 }

s5ChasComM3000Pwr -- 3000 Chassis Power Supply
    OBJECT IDENTIFIER ::= { s5ChasComMPwr 28 }

s5ChasComMBayStackTrPwr -- BayStack Token Ring Hub Power Supply
    OBJECT IDENTIFIER ::= { s5ChasComMPwr 36 }

s5ChasComM28200Pwr -- 28200 Chassis Power Supplies
    OBJECT IDENTIFIER ::= { s5ChasComMPwr 30 }

s5ChasComMBayStack301Pwr -- BayStack 301 Chassis Power Supplies
    OBJECT IDENTIFIER ::= { s5ChasComMPwr 31 }

s5ChasComSwitchNodePwr -- Switch Node Chassis Power Supply
    OBJECT IDENTIFIER ::= { s5ChasComMPwr 32 }

s5ChasComBayStack150Pwr -- BayStack150 Ethernet Hub Power Supply
    OBJECT IDENTIFIER ::= { s5ChasComMPwr 41 }

s5ChasComMBayStack303-304Pwr -- BayStack 303/304 Chassis Power Supply
    OBJECT IDENTIFIER ::= { s5ChasComMPwr 42 }

s5ChasComBayStack200Pwr -- BayStack200 Ethernet Hub Power Supply
    OBJECT IDENTIFIER ::= { s5ChasComMPwr 43 }

s5ChasComBayStack250Pwr -- BayStack250 Ethernet Hub Power Supply
    OBJECT IDENTIFIER ::= { s5ChasComMPwr 44 }

s5ChasComMAccelar8001Pwr -- Accelar 8010 Chassis AC Power Supply
    OBJECT IDENTIFIER ::= { s5ChasComMPwr 45 }

s5ChasComMAccelar8002Pwr -- Accelar 8010 Chassis DC Power Supply
    OBJECT IDENTIFIER ::= { s5ChasComMPwr 46 }

-- BPS 2000 24 port Switch Power Supply
s5ChasComBPS2000Pwr
    OBJECT IDENTIFIER ::= { s5ChasComMPwr 47 }
s5ChasComBPS2000Pwr-Main -- Unit Power Supply
    OBJECT IDENTIFIER ::= { s5ChasComBPS2000Pwr 1 }
s5ChasComBPS2000Pwr-RedundFeed -- Redundant Power Supply Feed
    OBJECT IDENTIFIER ::= { s5ChasComBPS2000Pwr 2 }

-- BayStack450 Switch Family Power Supply (includes BayStack 350 and 410)
s5ChasComBayStack450Pwr
    OBJECT IDENTIFIER ::= { s5ChasComMPwr 48 }
s5ChasComBayStack450Pwr-Main -- Unit Power Supply
    OBJECT IDENTIFIER ::= { s5ChasComBayStack450Pwr 1 }
s5ChasComBayStack450Pwr-RedundFeed -- Redundant Power Supply Feed
    OBJECT IDENTIFIER ::= { s5ChasComBayStack450Pwr 2 }

-- BayStack3580 Gigabit Switch Power Supply
s5ChasComBayStack3580Pwr
    OBJECT IDENTIFIER ::= { s5ChasComMPwr 49 }
s5ChasComBayStack3580Pwr-Main -- Unit Power Supply
    OBJECT IDENTIFIER ::= { s5ChasComBayStack3580Pwr 1 }
s5ChasComBayStack3580Pwr-RedundFeed -- Redundant Power Supply Feed
    OBJECT IDENTIFIER ::= {s5ChasComBayStack3580Pwr 2 }

-- BayStack420 24 Port Switch Power Supply
s5ChasComBayStack420Pwr
    OBJECT IDENTIFIER ::= { s5ChasComMPwr 50 }

-- Metro1200ESM 12 Port Switch Power Supply
s5ChasComMetro1200ESMPwr
    OBJECT IDENTIFIER ::= { s5ChasComMPwr 51 }
s5ChasComMetro1200ESMPwr-Main -- Unit Power Supply
    OBJECT IDENTIFIER ::= { s5ChasComMetro1200ESMPwr 1 }
s5ChasComMetro1200ESMPwr-RedundFeed -- Redundant Power Supply Feed
    OBJECT IDENTIFIER ::= { s5ChasComMetro1200ESMPwr 2 }

-- BayStack380 24 Port 10/100/1000 Switch Power Supply
s5ChasComBayStack380Pwr
    OBJECT IDENTIFIER ::= { s5ChasComMPwr 52 }
s5ChasComBayStack380Pwr-Main -- Unit Power Supply
    OBJECT IDENTIFIER ::= { s5ChasComBayStack380Pwr 1 }
s5ChasComBayStack380Pwr-RedundFeed -- Redundant Power Supply Feed
    OBJECT IDENTIFIER ::= { s5ChasComBayStack380Pwr 2 }

-- BayStack470 48 Port Switch Power Supply
s5ChasComBayStack470Pwr
    OBJECT IDENTIFIER ::= { s5ChasComMPwr 53 }
s5ChasComBayStack470Pwr-Main -- Unit Power Supply
    OBJECT IDENTIFIER ::= { s5ChasComBayStack470Pwr 1 }
s5ChasComBayStack470Pwr-RedundFeed -- Redundant Power Supply Feed
    OBJECT IDENTIFIER ::= { s5ChasComBayStack470Pwr 2 }

-- Metro1450ESM 12 Port + 2 GBIC Switch Power Supply
s5ChasComMetro1450ESMPwr
    OBJECT IDENTIFIER ::= { s5ChasComMPwr 54 }
s5ChasComMetro1450ESMPwr-Main -- Unit Power Supply
    OBJECT IDENTIFIER ::= { s5ChasComMetro1450ESMPwr 1 }
s5ChasComMetro1450ESMPwr-RedundFeed -- Redundant Power Supply Feed
    OBJECT IDENTIFIER ::= { s5ChasComMetro1450ESMPwr 2 }

-- Metro1400ESM 12 Port + 2 GBIC Switch Power Supply
s5ChasComMetro1400ESMPwr
    OBJECT IDENTIFIER ::= { s5ChasComMPwr 55 }
s5ChasComMetro1400ESMPwr-Main -- Unit Power Supply
    OBJECT IDENTIFIER ::= { s5ChasComMetro1400ESMPwr 1 }
s5ChasComMetro1400ESMPwr-RedundFeed -- Redundant Power Supply Feed
    OBJECT IDENTIFIER ::= { s5ChasComMetro1400ESMPwr 2 }

-- BayStack460-24T-PWR 24 Port Switch Power Supply
s5ChasComBayStack460-24T-PWRPwr
    OBJECT IDENTIFIER ::= { s5ChasComMPwr 56 }
s5ChasComBayStack460-24T-PWRPwr-Main -- Unit Power Supply
    OBJECT IDENTIFIER ::= { s5ChasComBayStack460-24T-PWRPwr 1 }
s5ChasComBayStack460-24T-PWRPwr-RedundFeed -- Redundant Power Supply Feed
    OBJECT IDENTIFIER ::= { s5ChasComBayStack460-24T-PWRPwr 2 }

-- BayStack380-24F 20 Mini-Gbic + 4 Gbic Port 1000 Switch Power Supply
s5ChasComBayStack380-24FPwr
    OBJECT IDENTIFIER ::= { s5ChasComMPwr 57 }
s5ChasComBayStack380-24FPwr-Main -- Unit Power Supply
    OBJECT IDENTIFIER ::= { s5ChasComBayStack380-24FPwr 1 }
s5ChasComBayStack380-24FPwr-RedundFeed -- Redundant Power Supply Feed
    OBJECT IDENTIFIER ::= { s5ChasComBayStack380-24FPwr 2 }

-- BayStack5510-24T 24 Port Switch Power Supply
s5ChasComBayStack5510-24TPwr
    OBJECT IDENTIFIER ::= { s5ChasComMPwr 58 }
s5ChasComBayStack5510-24TPwr-Main -- Unit Power Supply
    OBJECT IDENTIFIER ::= { s5ChasComBayStack5510-24TPwr 1 }
s5ChasComBayStack5510-24TPwr-RedundFeed -- Redundant Power Supply Feed
    OBJECT IDENTIFIER ::= { s5ChasComBayStack5510-24TPwr 2 }

-- BayStack5510-48T 48 Port Switch Power Supply
s5ChasComBayStack5510-48TPwr
    OBJECT IDENTIFIER ::= { s5ChasComMPwr 59 }
s5ChasComBayStack5510-48TPwr-Main -- Unit Power Supply
    OBJECT IDENTIFIER ::= { s5ChasComBayStack5510-48TPwr 1 }
s5ChasComBayStack5510-48TPwr-RedundFeed -- Redundant Power Supply Feed
    OBJECT IDENTIFIER ::= { s5ChasComBayStack5510-48TPwr 2 }

-- BayStack470 24 Port Switch Power Supply
s5ChasComBayStack470-24TPwr
    OBJECT IDENTIFIER ::= { s5ChasComMPwr 60 }
s5ChasComBayStack470-24TPwr-Main -- Unit Power Supply
    OBJECT IDENTIFIER ::= { s5ChasComBayStack470-24TPwr 1 }
s5ChasComBayStack470-24TPwr-RedundFeed -- Redundant Power Supply Feed
    OBJECT IDENTIFIER ::= { s5ChasComBayStack470-24TPwr 2 }

-- Nortel Networks Wireless LAN Access Point 2220 Power Supply
s5ChasComWLANAccessPoint2220Pwr
    OBJECT IDENTIFIER ::= { s5ChasComMPwr 61 }
s5ChasComWLANAccessPoint2220Pwr-Main -- Unit Power Supply
    OBJECT IDENTIFIER ::= { s5ChasComWLANAccessPoint2220Pwr 1 }

-- Nortel Networks Wireless LAN Security Switch 2250 Power Supply
s5ChasComWLANSecuritySwitch2250Pwr
    OBJECT IDENTIFIER ::= { s5ChasComMPwr 62 }
s5ChasComWLANSecuritySwitch2250Pwr-Main -- Unit Power Supply
    OBJECT IDENTIFIER ::= { s5ChasComWLANSecuritySwitch2250Pwr 1 }

-- BayStack 425 Switch Power Supply
s5ChasComBayStack425Pwr
    OBJECT IDENTIFIER ::= { s5ChasComMPwr 63 }
s5ChasComBayStack425PwrMain -- Unit Power Supply
    OBJECT IDENTIFIER ::= { s5ChasComBayStack425Pwr 1 }
s5ChasComBayStack425PwrRedundFeed -- Redundant Power Supply Feed
    OBJECT IDENTIFIER ::= { s5ChasComBayStack425Pwr 2 }

-- Nortel Networks Wireless LAN Access Point 2221 Power Supply
s5ChasComWLANAccessPoint2221Pwr
    OBJECT IDENTIFIER ::= { s5ChasComMPwr 64 }
s5ChasComWLANAccessPoint2221Pwr-Main -- Unit Power Supply
    OBJECT IDENTIFIER ::= { s5ChasComWLANAccessPoint2221Pwr 1 }

-- BayStack5520-24T-PWR 24 Port Switch Power Supply
s5ChasComBayStack5520-24T-PWRPwr
    OBJECT IDENTIFIER ::= { s5ChasComMPwr 65 }
s5ChasComBayStack5520-24T-PWRPwr-Main -- Unit Power Supply
    OBJECT IDENTIFIER ::= { s5ChasComBayStack5520-24T-PWRPwr 1 }
s5ChasComBayStack5520-24T-PWRPwr-RedundFeed -- Redundant Power Supply Feed
    OBJECT IDENTIFIER ::= { s5ChasComBayStack5520-24T-PWRPwr 2 }

-- BayStack5520-48T-PWR 48 Port Switch Power Supply
s5ChasComBayStack5520-48T-PWRPwr
    OBJECT IDENTIFIER ::= { s5ChasComMPwr 66 }
s5ChasComBayStack5520-48T-PWRPwr-Main -- Unit Power Supply
    OBJECT IDENTIFIER ::= { s5ChasComBayStack5520-48T-PWRPwr 1 }
s5ChasComBayStack5520-48T-PWRPwr-RedundFeed -- Redundant Power Supply Feed
    OBJECT IDENTIFIER ::= { s5ChasComBayStack5520-48T-PWRPwr 2 }

-- BayStack 325 Switch Power Supply
s5ChasComBayStack325Pwr
    OBJECT IDENTIFIER ::= { s5ChasComMPwr 67 }
s5ChasComBayStack325PwrMain -- Unit Power Supply
    OBJECT IDENTIFIER ::= { s5ChasComBayStack325Pwr 1 }
s5ChasComBayStack325PwrRedundFeed -- Redundant Power Supply Feed
    OBJECT IDENTIFIER ::= { s5ChasComBayStack325Pwr 2 }

-- Nortel Networks Wireless LAN Access Point 2225 Power Supply
s5ChasComWLANAccessPoint2225Pwr
    OBJECT IDENTIFIER ::= { s5ChasComMPwr 68 }
s5ChasComWLANAccessPoint2225Pwr-Main -- Unit Power Supply
    OBJECT IDENTIFIER ::= { s5ChasComWLANAccessPoint2225Pwr 1 }

-- BayStack470 24 Port PWR Switch Power Supply
s5ChasComBayStack470-24T-PWRPwr
    OBJECT IDENTIFIER ::= { s5ChasComMPwr 69 }
s5ChasComBayStack470-24T-PWRPwr-Main -- Unit Power Supply
    OBJECT IDENTIFIER ::= { s5ChasComBayStack470-24T-PWRPwr 1 }
s5ChasComBayStack470-24T-PWRPwr-RedundFeed -- Redundant Power Supply Feed
    OBJECT IDENTIFIER ::= { s5ChasComBayStack470-24T-PWRPwr 2 }

-- BayStack470 48 Port PWR Switch Power Supply
s5ChasComBayStack470-48T-PWRPwr
    OBJECT IDENTIFIER ::= { s5ChasComMPwr 70 }
s5ChasComBayStack470-48T-PWRPwr-Main -- Unit Power Supply
    OBJECT IDENTIFIER ::= { s5ChasComBayStack470-48T-PWRPwr 1 }
s5ChasComBayStack470-48T-PWRPwr-RedundFeed -- Redundant Power Supply Feed
    OBJECT IDENTIFIER ::= { s5ChasComBayStack470-48T-PWRPwr 2 }

-- Nortel Networks Wireless LAN Security Switch 2270 Power Supply
s5ChasComWLANSecuritySwitch2270Pwr
    OBJECT IDENTIFIER ::= { s5ChasComMPwr 71 }
s5ChasComWLANSecuritySwitch2270Pwr-Main -- Unit Power Supply
    OBJECT IDENTIFIER ::= { s5ChasComWLANSecuritySwitch2270Pwr 1 }

-- Ethernet Routing Switch 5530-24TFD Power Supply
s5ChasComEthernetRoutingSwitch5530-24TFDPwr
    OBJECT IDENTIFIER ::= { s5ChasComMPwr 72 }
s5ChasComEthernetRoutingSwitch5530-24TFDPwr-Main -- Unit Power Supply
    OBJECT IDENTIFIER ::= { s5ChasComEthernetRoutingSwitch5530-24TFDPwr 1 }
s5ChasComEthernetRoutingSwitch5530-24TFDPwr-RedundFeed -- Redundant Power Supply Feed
    OBJECT IDENTIFIER ::= { s5ChasComEthernetRoutingSwitch5530-24TFDPwr 2 }

-- Ethernet Switch 3510-24T Power Supply
s5ChasComEthernetSwitch3510-24TPwr
    OBJECT IDENTIFIER ::= { s5ChasComMPwr 73 }
s5ChasComEthernetSwitch3510-24TPwr-Main -- Unit Power Supply
    OBJECT IDENTIFIER ::= { s5ChasComEthernetSwitch3510-24TPwr 1 }
s5ChasComEthernetSwitch3510-24TPwr-RedundFeed -- Redundant Power Supply Feed
    OBJECT IDENTIFIER ::= { s5ChasComEthernetSwitch3510-24TPwr 2 }

-- SMB GIG BES 1010 24T Power Supply
s5ChasComBES1010-24TPwr
    OBJECT IDENTIFIER ::= { s5ChasComMPwr 74 }
s5ChasComBES1010-24TPwr-Main -- Unit Power Supply
    OBJECT IDENTIFIER ::= { s5ChasComBES1010-24TPwr 1 }
s5ChasComBES1010-24TPwr-RedundFeed -- Redundant Power Supply Feed
    OBJECT IDENTIFIER ::= { s5ChasComBES1010-24TPwr 2 }

-- SMB GIG BES 1010 48T Power Supply
s5ChasComBES1010-48TPwr
    OBJECT IDENTIFIER ::= { s5ChasComMPwr 75 }
s5ChasComBES1010-48TPwr-Main -- Unit Power Supply
    OBJECT IDENTIFIER ::= { s5ChasComBES1010-48TPwr 1 }
s5ChasComBES1010-48TPwr-RedundFeed -- Redundant Power Supply Feed
    OBJECT IDENTIFIER ::= { s5ChasComBES1010-48TPwr 2 }

-- SMB GIG BES 1020 24T PWR Power Supply
s5ChasComBES1020-24T-PWRPwr
    OBJECT IDENTIFIER ::= { s5ChasComMPwr 76 }
s5ChasComBES1020-24T-PWRPwr-Main -- Unit Power Supply
    OBJECT IDENTIFIER ::= { s5ChasComBES1020-24T-PWRPwr 1 }
s5ChasComBES1020-24T-PWRPwr-RedundFeed -- Redundant Power Supply Feed
    OBJECT IDENTIFIER ::= { s5ChasComBES1020-24T-PWRPwr 2 }

-- SMB GIG BES 1020 48T PWR Power Supply
s5ChasComBES1020-48T-PWRPwr
    OBJECT IDENTIFIER ::= { s5ChasComMPwr 77 }
s5ChasComBES1020-48T-PWRPwr-Main -- Unit Power Supply
    OBJECT IDENTIFIER ::= { s5ChasComBES1020-48T-PWRPwr 1 }
s5ChasComBES1020-48T-PWRPwr-RedundFeed -- Redundant Power Supply Feed
    OBJECT IDENTIFIER ::= { s5ChasComBES1020-48T-PWRPwr 2 }

-- SMB GIG BES 2010 24T Power Supply
s5ChasComBES2010-24TPwr
    OBJECT IDENTIFIER ::= { s5ChasComMPwr 78 }
s5ChasComBES2010-24TPwr-Main -- Unit Power Supply
    OBJECT IDENTIFIER ::= { s5ChasComBES2010-24TPwr 1 }
s5ChasComBES2010-24TPwr-RedundFeed -- Redundant Power Supply Feed
    OBJECT IDENTIFIER ::= { s5ChasComBES2010-24TPwr 2 }

-- SMB GIG BES 2010 48T Power Supply
s5ChasComBES2010-48TPwr
    OBJECT IDENTIFIER ::= { s5ChasComMPwr 79 }
s5ChasComBES2010-48TPwr-Main -- Unit Power Supply
    OBJECT IDENTIFIER ::= { s5ChasComBES2010-48TPwr 1 }
s5ChasComBES2010-48TPwr-RedundFeed -- Redundant Power Supply Feed
    OBJECT IDENTIFIER ::= { s5ChasComBES2010-48TPwr 2 }

-- SMB GIG BES 2020 24T PWR Power Supply
s5ChasComBES2020-24T-PWRPwr
    OBJECT IDENTIFIER ::= { s5ChasComMPwr 80 }
s5ChasComBES2020-24T-PWRPwr-Main -- Unit Power Supply
    OBJECT IDENTIFIER ::= { s5ChasComBES2020-24T-PWRPwr 1 }
s5ChasComBES2020-24T-PWRPwr-RedundFeed -- Redundant Power Supply Feed
    OBJECT IDENTIFIER ::= { s5ChasComBES2020-24T-PWRPwr 2 }

-- SMB GIG BES 2020 48T PWR Power Supply
s5ChasComBES2020-48T-PWRPwr
    OBJECT IDENTIFIER ::= { s5ChasComMPwr 81 }
s5ChasComBES2020-48T-PWRPwr-Main -- Unit Power Supply
    OBJECT IDENTIFIER ::= { s5ChasComBES2020-48T-PWRPwr 1 }
s5ChasComBES2020-48T-PWRPwr-RedundFeed -- Redundant Power Supply Feed
    OBJECT IDENTIFIER ::= { s5ChasComBES2020-48T-PWRPwr 2 }

-- SMB FE BES 110 24T Power Supply
s5ChasComBES110-24TPwr
    OBJECT IDENTIFIER ::= { s5ChasComMPwr 82 }
s5ChasComBES110-24TPwr-Main -- Unit Power Supply
    OBJECT IDENTIFIER ::= { s5ChasComBES110-24TPwr 1 }
s5ChasComBES110-24TPwr-RedundFeed -- Redundant Power Supply Feed
    OBJECT IDENTIFIER ::= { s5ChasComBES110-24TPwr 2 }

-- SMB FE BES 110 48T Power Supply
s5ChasComBES110-48TPwr
    OBJECT IDENTIFIER ::= { s5ChasComMPwr 83 }
s5ChasComBES110-48TPwr-Main -- Unit Power Supply
    OBJECT IDENTIFIER ::= { s5ChasComBES110-48TPwr 1 }
s5ChasComBES110-48TPwr-RedundFeed -- Redundant Power Supply Feed
    OBJECT IDENTIFIER ::= { s5ChasComBES110-48TPwr 2 }

-- SMB FE BES 120 24T PWR Power Supply
s5ChasComBES120-24T-PWRPwr
    OBJECT IDENTIFIER ::= { s5ChasComMPwr 84 }
s5ChasComBES120-24T-PWRPwr-Main -- Unit Power Supply
    OBJECT IDENTIFIER ::= { s5ChasComBES120-24T-PWRPwr 1 }
s5ChasComBES120-24T-PWRPwr-RedundFeed -- Redundant Power Supply Feed
    OBJECT IDENTIFIER ::= { s5ChasComBES120-24T-PWRPwr 2 }

-- SMB FE BES 120 48T PWR Power Supply
s5ChasComBES120-48T-PWRPwr
    OBJECT IDENTIFIER ::= { s5ChasComMPwr 85 }
s5ChasComBES120-48T-PWRPwr-Main -- Unit Power Supply
    OBJECT IDENTIFIER ::= { s5ChasComBES120-48T-PWRPwr 1 }
s5ChasComBES120-48T-PWRPwr-RedundFeed -- Redundant Power Supply Feed
    OBJECT IDENTIFIER ::= { s5ChasComBES120-48T-PWRPwr 2 }

-- SMB FE BES 210 24T Power Supply
s5ChasComBES210-24TPwr
    OBJECT IDENTIFIER ::= { s5ChasComMPwr 86 }
s5ChasComBES210-24TPwr-Main -- Unit Power Supply
    OBJECT IDENTIFIER ::= { s5ChasComBES210-24TPwr 1 }
s5ChasComBES210-24TPwr-RedundFeed -- Redundant Power Supply Feed
    OBJECT IDENTIFIER ::= { s5ChasComBES210-24TPwr 2 }

-- SMB FE BES 210 48T Power Supply
s5ChasComBES210-48TPwr
    OBJECT IDENTIFIER ::= { s5ChasComMPwr 87 }
s5ChasComBES210-48TPwr-Main -- Unit Power Supply
    OBJECT IDENTIFIER ::= { s5ChasComBES210-48TPwr 1 }
s5ChasComBES210-48TPwr-RedundFeed -- Redundant Power Supply Feed
    OBJECT IDENTIFIER ::= { s5ChasComBES210-48TPwr 2 }

-- SMB FE BES 220 24T PWR Power Supply
s5ChasComBES220-24T-PWRPwr
    OBJECT IDENTIFIER ::= { s5ChasComMPwr 88 }
s5ChasComBES220-24T-PWRPwr-Main -- Unit Power Supply
    OBJECT IDENTIFIER ::= { s5ChasComBES220-24T-PWRPwr 1 }
s5ChasComBES220-24T-PWRPwr-RedundFeed -- Redundant Power Supply Feed
    OBJECT IDENTIFIER ::= { s5ChasComBES220-24T-PWRPwr 2 }

-- SMB FE BES 220 48T PWR Power Supply
s5ChasComBES220-48T-PWRPwr
    OBJECT IDENTIFIER ::= { s5ChasComMPwr 89 }
s5ChasComBES220-48T-PWRPwr-Main -- Unit Power Supply
    OBJECT IDENTIFIER ::= { s5ChasComBES220-48T-PWRPwr 1 }
s5ChasComBES220-48T-PWRPwr-RedundFeed -- Redundant Power Supply Feed
    OBJECT IDENTIFIER ::= { s5ChasComBES220-48T-PWRPwr 2 }

-- ERS 4548GT Power Supply (Botany Bay)
s5ChasComERS4548GTPwr
    OBJECT IDENTIFIER ::= { s5ChasComMPwr 90 }
s5ChasComERS4548GTPwr-Main -- Unit Power Supply
    OBJECT IDENTIFIER ::= { s5ChasComERS4548GTPwr 1 }
s5ChasComERS4548GTPwr-RedundFeed -- Redundant Power Supply Feed
    OBJECT IDENTIFIER ::= { s5ChasComERS4548GTPwr 2 }

-- ERS 4548GT-PWR Power Supply (Botany Bay)
s5ChasComERS4548GT-PWRPwr
    OBJECT IDENTIFIER ::= { s5ChasComMPwr 91 }
s5ChasComERS4548GT-PWRPwr-Main -- Unit Power Supply
    OBJECT IDENTIFIER ::= { s5ChasComERS4548GT-PWRPwr 1 }
s5ChasComERS4548GT-PWRPwr-RedundFeed -- Redundant Power Supply Feed
    OBJECT IDENTIFIER ::= { s5ChasComERS4548GT-PWRPwr 2 }

-- ERS 4550T Power Supply (Botany Bay)
s5ChasComERS4550TPwr
    OBJECT IDENTIFIER ::= { s5ChasComMPwr 92 }
s5ChasComERS4550TPwr-Main -- Unit Power Supply
    OBJECT IDENTIFIER ::= { s5ChasComERS4550TPwr 1 }
s5ChasComERS4550TPwr-RedundFeed -- Redundant Power Supply Feed
    OBJECT IDENTIFIER ::= { s5ChasComERS4550TPwr 2 }

-- ERS 4550T-PWR Power Supply (Botany Bay)
s5ChasComERS4550T-PWRPwr
    OBJECT IDENTIFIER ::= { s5ChasComMPwr 93 }
s5ChasComERS4550T-PWRPwr-Main -- Unit Power Supply
    OBJECT IDENTIFIER ::= { s5ChasComERS4550T-PWRPwr 1 }
s5ChasComERS4550T-PWRPwr-RedundFeed -- Redundant Power Supply Feed
    OBJECT IDENTIFIER ::= { s5ChasComERS4550T-PWRPwr 2 }

-- ERS 4526FX Power Supply (Botany Bay)
s5ChasComERS4526FXPwr
    OBJECT IDENTIFIER ::= { s5ChasComMPwr 94 }
s5ChasComERS4526FXPwr-Main -- Unit Power Supply
    OBJECT IDENTIFIER ::= { s5ChasComERS4526FXPwr 1 }
s5ChasComERS4526FXPwr-RedundFeed -- Redundant Power Supply Feed
    OBJECT IDENTIFIER ::= { s5ChasComERS4526FXPwr 2 }

-- ERS 2500-26T Power Supply
s5ChasComERS2500-26TPwr
    OBJECT IDENTIFIER ::= { s5ChasComMPwr 95 }
s5ChasComERS2500-26TPwr-Main -- Unit Power Supply
    OBJECT IDENTIFIER ::= { s5ChasComERS2500-26TPwr 1 }
s5ChasComERS2500-26TPwr-RedundFeed -- Redundant Power Supply Feed
    OBJECT IDENTIFIER ::= { s5ChasComERS2500-26TPwr 2 }

-- ERS 2500-26T-PWR Power Supply
s5ChasComERS2500-26T-PWRPwr
    OBJECT IDENTIFIER ::= { s5ChasComMPwr 96 }
s5ChasComERS2500-26T-PWRPwr-Main -- Unit Power Supply
    OBJECT IDENTIFIER ::= { s5ChasComERS2500-26T-PWRPwr 1 }
s5ChasComERS2500-26T-PWRPwr-RedundFeed -- Redundant Power Supply Feed
    OBJECT IDENTIFIER ::= { s5ChasComERS2500-26T-PWRPwr 2 }

-- ERS 2500-50T Power Supply
s5ChasComERS2500-50TPwr
    OBJECT IDENTIFIER ::= { s5ChasComMPwr 97 }
s5ChasComERS2500-50TPwr-Main -- Unit Power Supply
    OBJECT IDENTIFIER ::= { s5ChasComERS2500-50TPwr 1 }
s5ChasComERS2500-50TPwr-RedundFeed -- Redundant Power Supply Feed
    OBJECT IDENTIFIER ::= { s5ChasComERS2500-50TPwr 2 }

-- ERS 2500-50T-PWR Power Supply
s5ChasComERS2500-50T-PWRPwr
    OBJECT IDENTIFIER ::= { s5ChasComMPwr 98 }
s5ChasComERS2500-50T-PWRPwr-Main -- Unit Power Supply
    OBJECT IDENTIFIER ::= { s5ChasComERS2500-50T-PWRPwr 1 }
s5ChasComERS2500-50T-PWRPwr-RedundFeed -- Redundant Power Supply Feed
    OBJECT IDENTIFIER ::= { s5ChasComERS2500-50T-PWRPwr 2 }

-- ERS 4526GTX-PWR Power Supply (Botany Bay)
s5ChasComERS4526GTX-PWRPwr
    OBJECT IDENTIFIER ::= { s5ChasComMPwr 99 }
s5ChasComERS4526GTX-PWRPwr-Main -- Unit Power Supply
    OBJECT IDENTIFIER ::= { s5ChasComERS4526GTX-PWRPwr 1 }
s5ChasComERS4526GTX-PWRPwr-RedundFeed -- Redundant Power Supply Feed
    OBJECT IDENTIFIER ::= { s5ChasComERS4526GTX-PWRPwr 2 }

-- ERS 4526GTX Power Supply (Botany Bay)
s5ChasComERS4526GTXPwr
    OBJECT IDENTIFIER ::= { s5ChasComMPwr 100 }
s5ChasComERS4526GTXPwr-Main -- Unit Power Supply
    OBJECT IDENTIFIER ::= { s5ChasComERS4526GTXPwr 1 }
s5ChasComERS4526GTXPwr-RedundFeed -- Redundant Power Supply Feed
    OBJECT IDENTIFIER ::= { s5ChasComERS4526GTXPwr 2 }

-- ERS 4524GT Power Supply (Botany Bay)
s5ChasComERS4524GTPwr
    OBJECT IDENTIFIER ::= { s5ChasComMPwr 101 }
s5ChasComERS4524GTPwr-Main -- Unit Power Supply
    OBJECT IDENTIFIER ::= { s5ChasComERS4524GTPwr 1 }
s5ChasComERS4524GTPwr-RedundFeed -- Redundant Power Supply Feed
    OBJECT IDENTIFIER ::= { s5ChasComERS4524GTPwr 2 }

-- ERS 4526T Power Supply (Botany Bay)
s5ChasComERS4526TPwr
    OBJECT IDENTIFIER ::= { s5ChasComMPwr 102 }
s5ChasComERS4526TPwr-Main -- Unit Power Supply
    OBJECT IDENTIFIER ::= { s5ChasComERS4526TPwr 1 }
s5ChasComERS4526TPwr-RedundFeed -- Redundant Power Supply Feed
    OBJECT IDENTIFIER ::= { s5ChasComERS4526TPwr 2 }

-- ERS 4526T-PWR Power Supply (Botany Bay)
s5ChasComERS4526T-PWRPwr
    OBJECT IDENTIFIER ::= { s5ChasComMPwr 103 }
s5ChasComERS4526T-PWRPwr-Main -- Unit Power Supply
    OBJECT IDENTIFIER ::= { s5ChasComERS4526T-PWRPwr 1 }
s5ChasComERS4526T-PWRPwr-RedundFeed -- Redundant Power Supply Feed
    OBJECT IDENTIFIER ::= { s5ChasComERS4526T-PWRPwr 2 }

-- ERS 5698-TFD-PWR Power Supply (Botany Bay)
s5ChasComERS5698-TFD-PWRPwr
    OBJECT IDENTIFIER ::= { s5ChasComMPwr 104 }
s5ChasComERS5698-TFD-PWRPwr-Main -- Unit Power Supply
    OBJECT IDENTIFIER ::= { s5ChasComERS5698-TFD-PWRPwr 1 }
s5ChasComERS5698-TFD-PWRPwr-RedundFeed -- Redundant Power Supply Feed
    OBJECT IDENTIFIER ::= { s5ChasComERS5698-TFD-PWRPwr 2 }
s5ChasComERS5698-TFD-PWRPwr-None -- No Power Supply installed
    OBJECT IDENTIFIER ::= { s5ChasComERS5698-TFD-PWRPwr 3 }
s5ChasComERS5698-TFD-PWRPwr-AC-DC-12V-300W -- AC-DC-12V-300W Power Supply
    OBJECT IDENTIFIER ::= { s5ChasComERS5698-TFD-PWRPwr 4 }
s5ChasComERS5698-TFD-PWRPwr-DC-DC-12V-300W -- DC-DC-12V-300W Power Supply
    OBJECT IDENTIFIER ::= { s5ChasComERS5698-TFD-PWRPwr 5 }
s5ChasComERS5698-TFD-PWRPwr-AC-DC-48V-600W -- AC-DC-48V-600W Power Supply
    OBJECT IDENTIFIER ::= { s5ChasComERS5698-TFD-PWRPwr 6 }
s5ChasComERS5698-TFD-PWRPwr-DC-DC-48V-600W -- DC-DC-48V-600W Power Supply
    OBJECT IDENTIFIER ::= { s5ChasComERS5698-TFD-PWRPwr 7 }
s5ChasComERS5698-TFD-PWRPwr-AC-DC-48V-1000W -- AC-DC-48V-1000W Power Supply
    OBJECT IDENTIFIER ::= { s5ChasComERS5698-TFD-PWRPwr 8 }
s5ChasComERS5698-TFD-PWRPwr-DC-DC-48V-1000W -- DC-DC-48V-1000W Power Supply
    OBJECT IDENTIFIER ::= { s5ChasComERS5698-TFD-PWRPwr 9 }

-- ERS 5698-TFD Power Supply (Botany Bay)
s5ChasComERS5698-TFDPwr
    OBJECT IDENTIFIER ::= { s5ChasComMPwr 105 }
s5ChasComERS5698-TFDPwr-Main -- Unit Power Supply
    OBJECT IDENTIFIER ::= { s5ChasComERS5698-TFDPwr 1 }
s5ChasComERS5698-TFDPwr-RedundFeed -- Redundant Power Supply Feed
    OBJECT IDENTIFIER ::= { s5ChasComERS5698-TFDPwr 2 }
s5ChasComERS5698-TFDPwr-None -- No Power Supply installed
    OBJECT IDENTIFIER ::= { s5ChasComERS5698-TFDPwr 3 }
s5ChasComERS5698-TFDPwr-AC-DC-12V-300W -- AC-DC-12V-300W Power Supply
    OBJECT IDENTIFIER ::= { s5ChasComERS5698-TFDPwr 4 }
s5ChasComERS5698-TFDPwr-DC-DC-12V-300W -- DC-DC-12V-300W Power Supply
    OBJECT IDENTIFIER ::= { s5ChasComERS5698-TFDPwr 5 }
s5ChasComERS5698-TFDPwr-AC-DC-48V-600W -- AC-DC-48V-600W Power Supply
    OBJECT IDENTIFIER ::= { s5ChasComERS5698-TFDPwr 6 }
s5ChasComERS5698-TFDPwr-DC-DC-48V-600W -- DC-DC-48V-600W Power Supply
    OBJECT IDENTIFIER ::= { s5ChasComERS5698-TFDPwr 7 }
s5ChasComERS5698-TFDPwr-AC-DC-48V-1000W -- AC-DC-48V-1000W Power Supply
    OBJECT IDENTIFIER ::= { s5ChasComERS5698-TFDPwr 8 }
s5ChasComERS5698-TFDPwr-DC-DC-48V-1000W -- DC-DC-48V-1000W Power Supply
    OBJECT IDENTIFIER ::= { s5ChasComERS5698-TFDPwr 9 }

-- ERS 5650-TD-PWR Power Supply (Botany Bay)
s5ChasComERS5650-TD-PWRPwr
    OBJECT IDENTIFIER ::= { s5ChasComMPwr 106 }
s5ChasComERS5650-TD-PWRPwr-Main -- Unit Power Supply
    OBJECT IDENTIFIER ::= { s5ChasComERS5650-TD-PWRPwr 1 }
s5ChasComERS5650-TD-PWRPwr-RedundFeed -- Redundant Power Supply Feed
    OBJECT IDENTIFIER ::= { s5ChasComERS5650-TD-PWRPwr 2 }
s5ChasComERS5650-TD-PWRPwr-None -- No Power Supply installed
    OBJECT IDENTIFIER ::= { s5ChasComERS5650-TD-PWRPwr 3 }
s5ChasComERS5650-TD-PWRPwr-AC-DC-12V-300W -- AC-DC-12V-300W Power Supply
    OBJECT IDENTIFIER ::= { s5ChasComERS5650-TD-PWRPwr 4 }
s5ChasComERS5650-TD-PWRPwr-DC-DC-12V-300W -- DC-DC-12V-300W Power Supply
    OBJECT IDENTIFIER ::= { s5ChasComERS5650-TD-PWRPwr 5 }
s5ChasComERS5650-TD-PWRPwr-AC-DC-48V-600W -- AC-DC-48V-600W Power Supply
    OBJECT IDENTIFIER ::= { s5ChasComERS5650-TD-PWRPwr 6 }
s5ChasComERS5650-TD-PWRPwr-DC-DC-48V-600W -- DC-DC-48V-600W Power Supply
    OBJECT IDENTIFIER ::= { s5ChasComERS5650-TD-PWRPwr 7 }
s5ChasComERS5650-TD-PWRPwr-AC-DC-48V-1000W -- AC-DC-48V-1000W Power Supply
    OBJECT IDENTIFIER ::= { s5ChasComERS5650-TD-PWRPwr 8 }
s5ChasComERS5650-TD-PWRPwr-DC-DC-48V-1000W -- DC-DC-48V-1000W Power Supply
    OBJECT IDENTIFIER ::= { s5ChasComERS5650-TD-PWRPwr 9 }

-- ERS 5650-TD Power Supply (Botany Bay)
s5ChasComERS5650-TDPwr
    OBJECT IDENTIFIER ::= { s5ChasComMPwr 107 }
s5ChasComERS5650-TDPwr-Main -- Unit Power Supply
    OBJECT IDENTIFIER ::= { s5ChasComERS5650-TDPwr 1 }
s5ChasComERS5650-TDPwr-RedundFeed -- Redundant Power Supply Feed
    OBJECT IDENTIFIER ::= { s5ChasComERS5650-TDPwr 2 }
s5ChasComERS5650-TDPwr-None -- No Power Supply installed
    OBJECT IDENTIFIER ::= { s5ChasComERS5650-TDPwr 3 }
s5ChasComERS5650-TDPwr-AC-DC-12V-300W -- AC-DC-12V-300W Power Supply
    OBJECT IDENTIFIER ::= { s5ChasComERS5650-TDPwr 4 }
s5ChasComERS5650-TDPwr-DC-DC-12V-300W -- DC-DC-12V-300W Power Supply
    OBJECT IDENTIFIER ::= { s5ChasComERS5650-TDPwr 5 }
s5ChasComERS5650-TDPwr-AC-DC-48V-600W -- AC-DC-48V-600W Power Supply
    OBJECT IDENTIFIER ::= { s5ChasComERS5650-TDPwr 6 }
s5ChasComERS5650-TDPwr-DC-DC-48V-600W -- DC-DC-48V-600W Power Supply
    OBJECT IDENTIFIER ::= { s5ChasComERS5650-TDPwr 7 }
s5ChasComERS5650-TDPwr-AC-DC-48V-1000W -- AC-DC-48V-1000W Power Supply
    OBJECT IDENTIFIER ::= { s5ChasComERS5650-TDPwr 8 }
s5ChasComERS5650-TDPwr-DC-DC-48V-1000W -- DC-DC-48V-1000W Power Supply
    OBJECT IDENTIFIER ::= { s5ChasComERS5650-TDPwr 9 }

-- ERS 5632-FD Power Supply (Botany Bay)
s5ChasComERS5632-FDPwr
    OBJECT IDENTIFIER ::= { s5ChasComMPwr 108 }
s5ChasComERS5632-FDPwr-Main -- Unit Power Supply
    OBJECT IDENTIFIER ::= { s5ChasComERS5632-FDPwr 1 }
s5ChasComERS5632-FDPwr-RedundFeed -- Redundant Power Supply Feed
    OBJECT IDENTIFIER ::= { s5ChasComERS5632-FDPwr 2 }
s5ChasComERS5632-FDPwr-None -- No Power Supply installed
    OBJECT IDENTIFIER ::= { s5ChasComERS5632-FDPwr 3 }
s5ChasComERS5632-FDPwr-AC-DC-12V-300W -- AC-DC-12V-300W Power Supply
    OBJECT IDENTIFIER ::= { s5ChasComERS5632-FDPwr 4 }
s5ChasComERS5632-FDPwr-DC-DC-12V-300W -- DC-DC-12V-300W Power Supply
    OBJECT IDENTIFIER ::= { s5ChasComERS5632-FDPwr 5 }
s5ChasComERS5632-FDPwr-AC-DC-48V-600W -- AC-DC-48V-600W Power Supply
    OBJECT IDENTIFIER ::= { s5ChasComERS5632-FDPwr 6 }
s5ChasComERS5632-FDPwr-DC-DC-48V-600W -- DC-DC-48V-600W Power Supply
    OBJECT IDENTIFIER ::= { s5ChasComERS5632-FDPwr 7 }
s5ChasComERS5632-FDPwr-AC-DC-48V-1000W -- AC-DC-48V-1000W Power Supply
    OBJECT IDENTIFIER ::= { s5ChasComERS5632-FDPwr 8 }
s5ChasComERS5632-FDPwr-DC-DC-48V-1000W -- DC-DC-48V-1000W Power Supply
    OBJECT IDENTIFIER ::= { s5ChasComERS5632-FDPwr 9 }

-- ESU1860S Power Supply
s5ChasComESU1860SPwr
    OBJECT IDENTIFIER ::= { s5ChasComMPwr 109 }
s5ChasComESU1860SPwr-Main-DC -- Unit Power Supply DC
    OBJECT IDENTIFIER ::= { s5ChasComESU1860SPwr 1 }
s5ChasComESU1860SPwr-Main-AC -- Unit Power Supply AC
    OBJECT IDENTIFIER ::= { s5ChasComESU1860SPwr 2 }
s5ChasComESU1860SPwr-RedundFeed-DC -- Redundant Power Supply Feed DC
    OBJECT IDENTIFIER ::= { s5ChasComESU1860SPwr 3 }
s5ChasComESU1860SPwr-RedundFeed-AC -- Redundant Power Supply Feed AC
    OBJECT IDENTIFIER ::= { s5ChasComESU1860SPwr 4 }


-- ESU1860B Power Supply
s5ChasComESU1860BPwr
    OBJECT IDENTIFIER ::= { s5ChasComMPwr 110 }
s5ChasComESU1860BPwr-Main-DC -- Unit Power Supply DC
    OBJECT IDENTIFIER ::= { s5ChasComESU1860BPwr 1 }
s5ChasComESU1860BPwr-Main-AC -- Unit Power Supply AC
    OBJECT IDENTIFIER ::= { s5ChasComESU1860BPwr 2 }
s5ChasComESU1860BPwr-RedundFeed-DC -- Redundant Power Supply Feed DC
    OBJECT IDENTIFIER ::= { s5ChasComESU1860BPwr 3 }
s5ChasComESU1860BPwr-RedundFeed-AC -- Redundant Power Supply Feed AC
    OBJECT IDENTIFIER ::= { s5ChasComESU1860BPwr 4 }


-- ESU1860T Power Supply
s5ChasComESU1860TPwr
    OBJECT IDENTIFIER ::= { s5ChasComMPwr 111 }
s5ChasComESU1860TPwr-Main-DC -- Unit Power Supply DC
    OBJECT IDENTIFIER ::= { s5ChasComESU1860TPwr 1 }
s5ChasComESU1860TPwr-Main-AC -- Unit Power Supply AC
    OBJECT IDENTIFIER ::= { s5ChasComESU1860TPwr 2 }
s5ChasComESU1860TPwr-RedundFeed-DC -- Redundant Power Supply Feed DC
    OBJECT IDENTIFIER ::= { s5ChasComESU1860TPwr 3 }
s5ChasComESU1860TPwr-RedundFeed-AC -- Redundant Power Supply Feed AC
    OBJECT IDENTIFIER ::= { s5ChasComESU1860TPwr 4 }

-- ESU1860V Power Supply
s5ChasComESU1860VPwr
    OBJECT IDENTIFIER ::= { s5ChasComMPwr 112 }
s5ChasComESU1860VPwr-Main-DC -- Unit Power Supply DC
    OBJECT IDENTIFIER ::= { s5ChasComESU1860VPwr 1 }
s5ChasComESU1860VPwr-Main-AC -- Unit Power Supply AC
    OBJECT IDENTIFIER ::= { s5ChasComESU1860VPwr 2 }
s5ChasComESU1860VPwr-RedundFeed-DC -- Redundant Power Supply Feed DC
    OBJECT IDENTIFIER ::= { s5ChasComESU1860VPwr 3 }
s5ChasComESU1860VPwr-RedundFeed-AC -- Redundant Power Supply Feed AC
    OBJECT IDENTIFIER ::= { s5ChasComESU1860VPwr 4 }

-- ESU1880S Power Supply
s5ChasComESU1880SPwr
    OBJECT IDENTIFIER ::= { s5ChasComMPwr 113 }
s5ChasComESU1880SPwr-Main-DC -- Unit Power Supply DC
    OBJECT IDENTIFIER ::= { s5ChasComESU1880SPwr 1 }
s5ChasComESU1880SPwr-Main-AC -- Unit Power Supply AC
    OBJECT IDENTIFIER ::= { s5ChasComESU1880SPwr 2 }
s5ChasComESU1880SPwr-RedundFeed-DC -- Redundant Power Supply Feed DC
    OBJECT IDENTIFIER ::= { s5ChasComESU1880SPwr 3 }
s5ChasComESU1880SPwr-RedundFeed-AC -- Redundant Power Supply Feed AC
    OBJECT IDENTIFIER ::= { s5ChasComESU1880SPwr 4 }

-- ERS 4524GT-PWR Power Supply (Botany Bay)
s5ChasComERS4524GT-PWRPwr
    OBJECT IDENTIFIER ::= { s5ChasComMPwr 114 }
s5ChasComERS4524GT-PWRPwr-Main -- Unit Power Supply
    OBJECT IDENTIFIER ::= { s5ChasComERS4524GT-PWRPwr 1 }
s5ChasComERS4524GT-PWRPwr-RedundFeed -- Redundant Power Supply Feed
    OBJECT IDENTIFIER ::= { s5ChasComERS4524GT-PWRPwr 2 }

-- ERS 6628XSGT Power Supply (Botany Bay)
s5ChasComERS6628XSGTPwr
    OBJECT IDENTIFIER ::= { s5ChasComMPwr 115 }
s5ChasComERS6628XSGTPwr-Main -- Unit Power Supply
    OBJECT IDENTIFIER ::= { s5ChasComERS6628XSGTPwr 1 }
s5ChasComERS6628XSGTPwr-RedundFeed -- Redundant Power Supply Feed
    OBJECT IDENTIFIER ::= { s5ChasComERS6628XSGTPwr 2 }

-- ERS 6632XSGT Power Supply (Botany Bay)
s5ChasComERS6632XTSPwr
    OBJECT IDENTIFIER ::= { s5ChasComMPwr 116 }
s5ChasComERS6632XTSPwr-Main -- Unit Power Supply
    OBJECT IDENTIFIER ::= { s5ChasComERS6632XTSPwr 1 }
s5ChasComERS6632XTSPwr-RedundFeed -- Redundant Power Supply Feed
    OBJECT IDENTIFIER ::= { s5ChasComERS6632XTSPwr 2 }

-- WC 8xxx Power Supply (Bonaire)
s5ChasComWC8180Pwr
    OBJECT IDENTIFIER ::= { s5ChasComMPwr 117 }
s5ChasComWC8180Pwr-Main -- Unit Power Supply
    OBJECT IDENTIFIER ::= { s5ChasComWC8180Pwr 1 }
s5ChasComWC8180Pwr-RedundFeed -- Redundant Power Supply Feed
    OBJECT IDENTIFIER ::= { s5ChasComWC8180Pwr 2 }

-- ERS 4526T-PWR+ Power Supply (Botany Bay)
s5ChasComERS4526T-PWR-PLUSPwr
    OBJECT IDENTIFIER ::= { s5ChasComMPwr 118 }
s5ChasComERS4526T-PWR-PLUSPwr-Main -- Unit Power Supply
    OBJECT IDENTIFIER ::= { s5ChasComERS4526T-PWR-PLUSPwr 1 }
s5ChasComERS4526T-PWR-PLUSPwr-RedundFeed -- Redundant Power Supply Feed
    OBJECT IDENTIFIER ::= { s5ChasComERS4526T-PWR-PLUSPwr 2 }

-- ERS 4550T-PWR+ Power Supply (Botany Bay)
s5ChasComERS4550T-PWR-PLUSPwr
    OBJECT IDENTIFIER ::= { s5ChasComMPwr 119 }
s5ChasComERS4550T-PWR-PLUSPwr-Main -- Unit Power Supply
    OBJECT IDENTIFIER ::= { s5ChasComERS4550T-PWR-PLUSPwr 1 }
s5ChasComERS4550T-PWR-PLUSPwr-RedundFeed -- Redundant Power Supply Feed
    OBJECT IDENTIFIER ::= { s5ChasComERS4550T-PWR-PLUSPwr 2 }

-- ERS 4826GTS-PWR+ Power Supply
s5ChasComERS4826GTS-PWR-PLUSPwr
    OBJECT IDENTIFIER ::= { s5ChasComMPwr 120 }
s5ChasComERS4826GTS-PWR-PLUSPwr-Main -- Unit Power Supply
    OBJECT IDENTIFIER ::= { s5ChasComERS4826GTS-PWR-PLUSPwr 1 }
s5ChasComERS4826GTS-PWR-PLUSPwr-RedundFeed -- Redundant Power Supply Feed
    OBJECT IDENTIFIER ::= { s5ChasComERS4826GTS-PWR-PLUSPwr 2 }

-- ERS 4850GTS-PWR+ Power Supply
s5ChasComERS4850GTS-PWR-PLUSPwr
    OBJECT IDENTIFIER ::= { s5ChasComMPwr 121 }
s5ChasComERS4850GTS-PWR-PLUSPwr-Main -- Unit Power Supply
    OBJECT IDENTIFIER ::= { s5ChasComERS4850GTS-PWR-PLUSPwr 1 }
s5ChasComERS4850GTS-PWR-PLUSPwr-RedundFeed -- Redundant Power Supply Feed
    OBJECT IDENTIFIER ::= { s5ChasComERS4850GTS-PWR-PLUSPwr 2 }

-- ERS 4826GTS Power Supply
s5ChasComERS4826GTSPwr
    OBJECT IDENTIFIER ::= { s5ChasComMPwr 122 }
s5ChasComERS4826GTSPwr-Main -- Unit Power Supply
    OBJECT IDENTIFIER ::= { s5ChasComERS4826GTSPwr 1 }
s5ChasComERS4826GTSPwr-RedundFeed -- Redundant Power Supply Feed
    OBJECT IDENTIFIER ::= { s5ChasComERS4826GTSPwr 2 }

-- ERS 4850GTS Power Supply
s5ChasComERS4850GTSPwr
    OBJECT IDENTIFIER ::= { s5ChasComMPwr 123 }
s5ChasComERS4850GTSPwr-Main -- Unit Power Supply
    OBJECT IDENTIFIER ::= { s5ChasComERS4850GTSPwr 1 }
s5ChasComERS4850GTSPwr-RedundFeed -- Redundant Power Supply Feed
    OBJECT IDENTIFIER ::= { s5ChasComERS4850GTSPwr 2 }

-- VSP 7024XLS Power Supply
s5ChasComVSP7024XLSPwr
    OBJECT IDENTIFIER ::= { s5ChasComMPwr 124 }
s5ChasComVSP7024XLSPwr-Main -- Unit Power Supply
    OBJECT IDENTIFIER ::= { s5ChasComVSP7024XLSPwr 1 }
s5ChasComVSP7024XLSPwr-RedundFeed -- Redundant Power Supply Feed
    OBJECT IDENTIFIER ::= { s5ChasComVSP7024XLSPwr 2 }

-- ERS 3510GT Power Supply
s5ChasComERS3510GTPwr
    OBJECT IDENTIFIER ::= { s5ChasComMPwr 125 }
s5ChasComERS3510GTPwr-Main -- Unit Power Supply
    OBJECT IDENTIFIER ::= { s5ChasComERS3510GTPwr 1 }
s5ChasComERS3510GTPwr-RedundFeed -- Redundant Power Supply Feed
    OBJECT IDENTIFIER ::= { s5ChasComERS3510GTPwr 2 }

-- ERS 3510GT-PWR+ Power Supply
s5ChasComERS3510GT-PWR-PLUSPwr
    OBJECT IDENTIFIER ::= { s5ChasComMPwr 126 }
s5ChasComERS3510GT-PWR-PLUSPwr-Main -- Unit Power Supply
    OBJECT IDENTIFIER ::= { s5ChasComERS3510GT-PWR-PLUSPwr 1 }
s5ChasComERS3510GT-PWR-PLUSPwr-RedundFeed -- Redundant Power Supply Feed
    OBJECT IDENTIFIER ::= { s5ChasComERS3510GT-PWR-PLUSPwr 2 }

-- ERS 3524GT Power Supply
s5ChasComERS3524GTPwr
    OBJECT IDENTIFIER ::= { s5ChasComMPwr 127 }
s5ChasComERS3524GTPwr-Main -- Unit Power Supply
    OBJECT IDENTIFIER ::= { s5ChasComERS3524GTPwr 1 }
s5ChasComERS3524GTPwr-RedundFeed -- Redundant Power Supply Feed
    OBJECT IDENTIFIER ::= { s5ChasComERS3524GTPwr 2 }

-- ERS 3524GT-PWR+ Power Supply
s5ChasComERS3524GT-PWR-PLUSPwr
    OBJECT IDENTIFIER ::= { s5ChasComMPwr 128 }
s5ChasComERS3524GT-PWR-PLUSPwr-Main -- Unit Power Supply
    OBJECT IDENTIFIER ::= { s5ChasComERS3524GT-PWR-PLUSPwr 1 }
s5ChasComERS3524GT-PWR-PLUSPwr-RedundFeed -- Redundant Power Supply Feed
    OBJECT IDENTIFIER ::= { s5ChasComERS3524GT-PWR-PLUSPwr 2 }

-- ERS 3526GT Power Supply
s5ChasComERS3526GTPwr
    OBJECT IDENTIFIER ::= { s5ChasComMPwr 129 }
s5ChasComERS3526GTPwr-Main -- Unit Power Supply
    OBJECT IDENTIFIER ::= { s5ChasComERS3526GTPwr 1 }
s5ChasComERS3526GTPwr-RedundFeed -- Redundant Power Supply Feed
    OBJECT IDENTIFIER ::= { s5ChasComERS3526GTPwr 2 }

-- ERS 3526GT-PWR+ Power Supply
s5ChasComERS3526GT-PWR-PLUSPwr
    OBJECT IDENTIFIER ::= { s5ChasComMPwr 130 }
s5ChasComERS3526GT-PWR-PLUSPwr-Main -- Unit Power Supply
    OBJECT IDENTIFIER ::= { s5ChasComERS3526GT-PWR-PLUSPwr 1 }
s5ChasComERS3526GT-PWR-PLUSPwr-RedundFeed -- Redundant Power Supply Feed
    OBJECT IDENTIFIER ::= { s5ChasComERS3526GT-PWR-PLUSPwr 2 }

-- ERS 3526T Power Supply
s5ChasComERS3526TPwr
    OBJECT IDENTIFIER ::= { s5ChasComMPwr 131 }
s5ChasComERS3526TPwr-Main -- Unit Power Supply
    OBJECT IDENTIFIER ::= { s5ChasComERS3526TPwr 1 }
s5ChasComERS3526TPwr-RedundFeed -- Redundant Power Supply Feed
    OBJECT IDENTIFIER ::= { s5ChasComERS3526TPwr 2 }

-- ERS 3526T-PWR+ Power Supply
s5ChasComERS3526T-PWR-PLUSPwr
    OBJECT IDENTIFIER ::= { s5ChasComMPwr 132 }
s5ChasComERS3526T-PWR-PLUSPwr-Main -- Unit Power Supply
    OBJECT IDENTIFIER ::= { s5ChasComERS3526T-PWR-PLUSPwr 1 }
s5ChasComERS3526T-PWR-PLUSPwr-RedundFeed -- Redundant Power Supply Feed
    OBJECT IDENTIFIER ::= { s5ChasComERS3526T-PWR-PLUSPwr 2 }

-- ERS 3549GTS Power Supply
s5ChasComERS3549GTSPwr
    OBJECT IDENTIFIER ::= { s5ChasComMPwr 133 }
s5ChasComERS3549GTSPwr-Main -- Unit Power Supply
    OBJECT IDENTIFIER ::= { s5ChasComERS3549GTSPwr 1 }

-- ERS 3549GTS-PWR+ Power Supply
s5ChasComERS3549GTS-PWR-PLUSPwr
    OBJECT IDENTIFIER ::= { s5ChasComMPwr 134 }
s5ChasComERS3549GTS-PWR-PLUSPwr-Main -- Unit Power Supply
    OBJECT IDENTIFIER ::= { s5ChasComERS3549GTS-PWR-PLUSPwr 1 }

-- VSP 7024XT Power Supply
s5ChasComVSP7024XTPwr
    OBJECT IDENTIFIER ::= { s5ChasComMPwr 135 }
s5ChasComVSP7024XTPwr-Main -- Unit Power Supply
    OBJECT IDENTIFIER ::= { s5ChasComVSP7024XTPwr 1 }
s5ChasComVSP7024XTPwr-RedundFeed -- Redundant Power Supply Feed
    OBJECT IDENTIFIER ::= { s5ChasComVSP7024XTPwr 2 }

-- ERS 5900 Power Supply

-- ERS 5928GTS Power Supply
s5ChasComERS5928GTSPwr
    OBJECT IDENTIFIER ::= { s5ChasComMPwr 136 }
s5ChasComERS5928GTSPwr-Main -- Unit Power Supply
    OBJECT IDENTIFIER ::= { s5ChasComERS5928GTSPwr 1 }
s5ChasComERS5928GTSPwr-RedundFeed -- Redundant Power Supply Feed
    OBJECT IDENTIFIER ::= { s5ChasComERS5928GTSPwr 2 }

-- ERS 5928GTS-PWR+ Power Supply
s5ChasComERS5928GTS-PWR-PLUSPwr
    OBJECT IDENTIFIER ::= { s5ChasComMPwr 137 }
s5ChasComERS5928GTS-PWR-PLUSPwr-Main -- Unit Power Supply
    OBJECT IDENTIFIER ::= { s5ChasComERS5928GTS-PWR-PLUSPwr 1 }
s5ChasComERS5928GTS-PWR-PLUSPwr-RedundFeed -- Redundant Power Supply Feed
    OBJECT IDENTIFIER ::= { s5ChasComERS5928GTS-PWR-PLUSPwr 2 }

-- ERS 5952GTS Power Supply
s5ChasComERS5952GTSPwr
    OBJECT IDENTIFIER ::= { s5ChasComMPwr 138 }
s5ChasComERS5952GTSPwr-Main -- Unit Power Supply
    OBJECT IDENTIFIER ::= { s5ChasComERS5952GTSPwr 1 }
s5ChasComERS5952GTSPwr-RedundFeed -- Redundant Power Supply Feed
    OBJECT IDENTIFIER ::= { s5ChasComERS5952GTSPwr 2 }

-- ERS 5952GTS-PWR+ Power Supply
s5ChasComERS5952GTS-PWR-PLUSPwr
    OBJECT IDENTIFIER ::= { s5ChasComMPwr 139 }
s5ChasComERS5952GTS-PWR-PLUSPwr-Main -- Unit Power Supply
    OBJECT IDENTIFIER ::= { s5ChasComERS5952GTS-PWR-PLUSPwr 1 }
s5ChasComERS5952GTS-PWR-PLUSPwr-RedundFeed -- Redundant Power Supply Feed
    OBJECT IDENTIFIER ::= { s5ChasComERS5952GTS-PWR-PLUSPwr 2 }

-- ERS 5928GTS-uPWR Power Supply
s5ChasComERS5928GTS-UPWRPwr
    OBJECT IDENTIFIER ::= { s5ChasComMPwr 140 }
s5ChasComERS5928GTS-UPWRPwr-Main -- Unit Power Supply
    OBJECT IDENTIFIER ::= { s5ChasComERS5928GTS-UPWRPwr 1 }
s5ChasComERS5928GTS-UPWRPwr-RedundFeed -- Redundant Power Supply Feed
    OBJECT IDENTIFIER ::= { s5ChasComERS5928GTS-UPWRPwr 2 }

-- ERS 59100GTS Power Supply
s5ChasComERS59100GTSPwr
    OBJECT IDENTIFIER ::= { s5ChasComMPwr 141 }
s5ChasComERS59100GTSPwr-Main -- Unit Power Supply
    OBJECT IDENTIFIER ::= { s5ChasComERS59100GTSPwr 1 }
s5ChasComERS59100GTSPwr-RedundFeed -- Redundant Power Supply Feed
    OBJECT IDENTIFIER ::= { s5ChasComERS59100GTSPwr 2 }

-- ERS 59100GTS-PWR+ Power Supply
s5ChasComERS59100GTS-PWR-PLUSPwr
    OBJECT IDENTIFIER ::= { s5ChasComMPwr 142 }
s5ChasComERS59100GTS-PWR-PLUSPwr-Main -- Unit Power Supply
    OBJECT IDENTIFIER ::= { s5ChasComERS59100GTS-PWR-PLUSPwr 1 }
s5ChasComERS59100GTS-PWR-PLUSPwr-RedundFeed -- Redundant Power Supply Feed
    OBJECT IDENTIFIER ::= { s5ChasComERS59100GTS-PWR-PLUSPwr 2 }

-- ERS 4900 Power Supply

-- ERS 4926GTS Power Supply
s5ChasComERS4926GTSPwr
    OBJECT IDENTIFIER ::= { s5ChasComMPwr 143 }
s5ChasComERS4926GTSPwr-Main -- Unit Power Supply
    OBJECT IDENTIFIER ::= { s5ChasComERS4926GTSPwr 1 }
s5ChasComERS4926GTSPwr-RedundFeed -- Redundant Power Supply Feed
    OBJECT IDENTIFIER ::= { s5ChasComERS4926GTSPwr 2 }

-- ERS 4926GTS-PWR+ Power Supply
s5ChasComERS4926GTS-PWR-PLUSPwr
    OBJECT IDENTIFIER ::= { s5ChasComMPwr 144 }
s5ChasComERS4926GTS-PWR-PLUSPwr-Main -- Unit Power Supply
    OBJECT IDENTIFIER ::= { s5ChasComERS4926GTS-PWR-PLUSPwr 1 }
s5ChasComERS4926GTS-PWR-PLUSPwr-RedundFeed -- Redundant Power Supply Feed
    OBJECT IDENTIFIER ::= { s5ChasComERS4926GTS-PWR-PLUSPwr 2 }

-- ERS 4950GTS Power Supply
s5ChasComERS4950GTSPwr
    OBJECT IDENTIFIER ::= { s5ChasComMPwr 145 }
s5ChasComERS4950GTSPwr-Main -- Unit Power Supply
    OBJECT IDENTIFIER ::= { s5ChasComERS4950GTSPwr 1 }
s5ChasComERS4950GTSPwr-RedundFeed -- Redundant Power Supply Feed
    OBJECT IDENTIFIER ::= { s5ChasComERS4950GTSPwr 2 }

-- ERS 4950GTS-PWR+ Power Supply
s5ChasComERS4950GTS-PWR-PLUSPwr
    OBJECT IDENTIFIER ::= { s5ChasComMPwr 146 }
s5ChasComERS4950GTS-PWR-PLUSPwr-Main -- Unit Power Supply
    OBJECT IDENTIFIER ::= { s5ChasComERS4950GTS-PWR-PLUSPwr 1 }
s5ChasComERS4950GTS-PWR-PLUSPwr-RedundFeed -- Redundant Power Supply Feed
    OBJECT IDENTIFIER ::= { s5ChasComERS4950GTS-PWR-PLUSPwr 2 }

-- ERS 3550T Power Supply
s5ChasComERS3550TPwr
    OBJECT IDENTIFIER ::= { s5ChasComMPwr 147 }
s5ChasComERS3550TPwr-Main -- Unit Power Supply
    OBJECT IDENTIFIER ::= { s5ChasComERS3550TPwr 1 }

-- ERS 3550T-PWR+ Power Supply
s5ChasComERS3550T-PWR-PLUSPwr
    OBJECT IDENTIFIER ::= { s5ChasComMPwr 148 }
s5ChasComERS3550T-PWR-PLUSPwr-Main -- Unit Power Supply
    OBJECT IDENTIFIER ::= { s5ChasComERS3550T-PWR-PLUSPwr 1 }

-- ERS 3626GTS Power Supply
s5ChasComERS3626GTSPwr
    OBJECT IDENTIFIER ::= { s5ChasComMPwr 149 }
s5ChasComERS3626GTSPwr-Main -- Unit Power Supply
    OBJECT IDENTIFIER ::= { s5ChasComERS3626GTSPwr 1 }

-- ERS 3626GTS-PWR+ Power Supply
s5ChasComERS3626GTS-PWR-PLUSPwr
    OBJECT IDENTIFIER ::= { s5ChasComMPwr 150 }
s5ChasComERS3626GTS-PWR-PLUSPwr-Main -- Unit Power Supply
    OBJECT IDENTIFIER ::= { s5ChasComERS3626GTS-PWR-PLUSPwr 1 }

-- ERS 3650GTS Power Supply
s5ChasComERS3650GTSPwr
    OBJECT IDENTIFIER ::= { s5ChasComMPwr 151 }
s5ChasComERS3650GTSPwr-Main -- Unit Power Supply
    OBJECT IDENTIFIER ::= { s5ChasComERS3650GTSPwr 1 }

-- ERS 3650GTS-PWR+ Power Supply
s5ChasComERS3650GTS-PWR-PLUSPwr
    OBJECT IDENTIFIER ::= { s5ChasComMPwr 152 }
s5ChasComERS3650GTS-PWR-PLUSPwr-Main -- Unit Power Supply
    OBJECT IDENTIFIER ::= { s5ChasComERS3650GTS-PWR-PLUSPwr 1 }

-- ERS 5928MTS-uPWR Power Supply
s5ChasComERS5928MTS-UPWRPwr
    OBJECT IDENTIFIER ::= { s5ChasComMPwr 153 }
s5ChasComERS5928MTS-UPWRPwr-Main -- Unit Power Supply
    OBJECT IDENTIFIER ::= { s5ChasComERS5928MTS-UPWRPwr 1 }
s5ChasComERS5928MTS-UPWRPwr-RedundFeed -- Redundant Power Supply Feed
    OBJECT IDENTIFIER ::= { s5ChasComERS5928MTS-UPWRPwr 2 }

-- Model 5000 (721-018) 950 Watt AC Chassis Power Supply with
-- internal fan and temperature sensor (but returning a differnt ID)
s5ChasComM5000Pwr-950A
    OBJECT IDENTIFIER ::= { s5ChasComM5000Pwr 0 }

-- Model 5000 (721-018) 950 Watt AC Chassis Power Supply with
-- internal fan and temperature sensor
s5ChasComM5000Pwr-950
    OBJECT IDENTIFIER ::= { s5ChasComM5000Pwr 1 }

-- Model 5000 1400 Watt DC Chassis Power Supply
s5ChasComM5000Pwr-1400WDC
    OBJECT IDENTIFIER ::= { s5ChasComM5000Pwr 3 }

-- Model 5005 (721-029) 600 Watt AC Chassis Power Supply with
-- internal fan and temperature sensor
s5ChasComM5005Pwr-600
    OBJECT IDENTIFIER ::= { s5ChasComM5005Pwr 1 }

-- Model 5005 900 Watt AC Chassis Power Supply
s5ChasComM5005Pwr-900WAC
    OBJECT IDENTIFIER ::= { s5ChasComM5005Pwr 2 }

-- Model 5005 900 Watt DC Chassis Power Supply
s5ChasComM5005Pwr-900WDC
    OBJECT IDENTIFIER ::= { s5ChasComM5005Pwr 3 }

-- Model 1032x (721-???) ??? Watt AC Chassis Power Supply
s5ChasComM1032xPwr-A
    OBJECT IDENTIFIER ::= { s5ChasComM1032xPwr 1 }

-- Stackable Redundant Power Supply Feed
s5ChasCom5DN000Pwr-RedundFeed
    OBJECT IDENTIFIER ::= { s5ChasComM5DN000Pwr 1 }

-- Model 5DN002 Hub 50W AC Chassis Power Supply
s5ChasComM5DN002Pwr-50W
    OBJECT IDENTIFIER ::= { s5ChasComM5DN000Pwr 2 }

-- Model 5DN003 Hub 110W AC Chassis Power Supply
s5ChasComM5DN003Pwr-110W
    OBJECT IDENTIFIER ::= { s5ChasComM5DN000Pwr 3 }

-- Stackable Redundant Power Supply Feed
s5ChasComMNBayStackPwr-RedundFeed
    OBJECT IDENTIFIER ::= { s5ChasComMNBayStackPwr 1 }

-- BayStack Ethernet Hub 50W AC Chassis Power Supply
s5ChasComMNBayStackPwr-50W
    OBJECT IDENTIFIER ::= { s5ChasComMNBayStackPwr 2 }

-- BayStack 100BASE-T Hub 110W AC Chassis Power Supply
s5ChasComMBayStack100Pwr-110W
    OBJECT IDENTIFIER ::= { s5ChasComMBayStack100Pwr 2 }

-- BayStack 100BASE-T Hub Redundant Power Supply Feed
s5ChasComMBayStack100Pwr-RedundFeed
    OBJECT IDENTIFIER ::= { s5ChasComMBayStack100Pwr 1 }

-- Model 3001 360 Watt Power Supply Module
s5ChasComM3000360Pwr
    OBJECT IDENTIFIER ::= { s5ChasComM3000Pwr 1 }

-- Model 3002/3002DC 460 Watt Power Supply Module
s5ChasComM3000460Pwr
    OBJECT IDENTIFIER ::= { s5ChasComM3000Pwr 2 }

-- Model 3003 460 Watt DC/DC Power Supply Module
s5ChasComM3003-460Pwr
    OBJECT IDENTIFIER ::= { s5ChasComM3000Pwr 3 }

-- Stackable Redundant Power supply Feed
s5ChasComMBayStackTrPwr-RedundFeed
    OBJECT IDENTIFIER ::= { s5ChasComMBayStackTrPwr 1 }

-- Module BayStack TR (721-048-A) 150W AC/DC Chassis PowerSupply
s5ChasComMBayStackTrPwr-150W
    OBJECT IDENTIFIER ::= { s5ChasComMBayStackTrPwr 2 }

-- Model 28200 Ethernet Switch 182W AC Chassis Power Supply
s5ChasComM28200Pwr-182W
    OBJECT IDENTIFIER ::= { s5ChasComM28200Pwr 2 }
-- Model 28200 Ethernet Switch Redundant Power Supply Feed
s5ChasComM28200Pwr-RedundFeed
    OBJECT IDENTIFIER ::= { s5ChasComM28200Pwr 1 }

-- BayStack 301 Internal Power Supply
s5ChasComMBayStack301IntPwr
    OBJECT IDENTIFIER ::= { s5ChasComMBayStack301Pwr 1 }
-- BayStack 301 External Power Supply
s5ChasComMBayStack301ExtPwr
    OBJECT IDENTIFIER ::= { s5ChasComMBayStack301Pwr 2 }

-- BayStack150 Ethernet Hub Chassis Power Supply
s5ChasComBayStack150MasterPwr -- Master Unit Power Supply
    OBJECT IDENTIFIER ::= { s5ChasComBayStack150Pwr 1 }
s5ChasComBayStack150SlavePwr -- Slave unit Power Supply
    OBJECT IDENTIFIER ::= { s5ChasComBayStack150Pwr 2 }

-- BayStack200 Ethernet Hub Chassis Power Supply
s5ChasComBayStack200MasterPwr -- Master Unit Power Supply
    OBJECT IDENTIFIER ::= { s5ChasComBayStack200Pwr 1 }

-- BayStack250 Ethernet Hub Chassis Power Supply
s5ChasComBayStack250MasterPwr -- Master Unit Power Supply
    OBJECT IDENTIFIER ::= { s5ChasComBayStack250Pwr 1 }
s5ChasComBayStack250SlavePwr -- Slave Unit Power Supply
    OBJECT IDENTIFIER ::= { s5ChasComBayStack250Pwr 2 }





-- Chassis level Temperature Sensors
s5ChasComTmpSnr OBJECT IDENTIFIER ::= { s5ChasComTypeVal 3 }

-- Model 5000 Chassis temperature sensor
s5ChasComTmpSnrM5000
    OBJECT IDENTIFIER ::= { s5ChasComTmpSnr 1 }

-- OPTera Metro 1200 Ethernet Service Module Chassis temperature sensor
s5ChasComTmpSnrMetro1200ESM
    OBJECT IDENTIFIER ::= { s5ChasComTmpSnr 2 }

-- OPTera Metro 1450 Ethernet Service Module Chassis temperature sensor
s5ChasComTmpSnrMetro1450ESM
    OBJECT IDENTIFIER ::= { s5ChasComTmpSnr 3 }

-- OPTera Metro 1400 Ethernet Service Module Chassis temperature sensor
s5ChasComTmpSnrMetro1400ESM
    OBJECT IDENTIFIER ::= { s5ChasComTmpSnr 4 }

-- BayStack 460-24T-PWR Chassis temperature sensor
s5ChasComTmpSnrBayStack460-24T-PWR
    OBJECT IDENTIFIER ::= { s5ChasComTmpSnr 5 }

-- BayStack 5510-24T Chassis temperature sensor
s5ChasComTmpSnrBayStack5510-24T
    OBJECT IDENTIFIER ::= { s5ChasComTmpSnr 6 }

-- BayStack 5510-48T Chassis temperature sensor
s5ChasComTmpSnrBayStack5510-48T
    OBJECT IDENTIFIER ::= { s5ChasComTmpSnr 7 }

-- BayStack 425 Chassis temperature sensor
s5ChasComTmpSnrBayStack425
    OBJECT IDENTIFIER ::= { s5ChasComTmpSnr 8 }

-- BayStack 5520-24T-PWR and 5520-48T-PWR Chassis temperature sensor
s5ChasComTmpSnrBayStack5520-24T-PWR
    OBJECT IDENTIFIER ::= { s5ChasComTmpSnr 9 }
s5ChasComTmpSnrBayStack5520-48T-PWR
    OBJECT IDENTIFIER ::= { s5ChasComTmpSnr 10 }

-- BayStack 325 Chassis temperature sensor
s5ChasComTmpSnrBayStack325
    OBJECT IDENTIFIER ::= { s5ChasComTmpSnr 11 }

-- Chassis level Temperature Sensors (NEW names)
s5ChasComMTmpSnr OBJECT IDENTIFIER ::= { s5ChasComTypeVal 9 }
s5ChasComM5000TmpSnr -- 5000 Chassis
    OBJECT IDENTIFIER ::= { s5ChasComMTmpSnr 12 }
s5ChasComM5005TmpSnr -- 5005 Chassis
    OBJECT IDENTIFIER ::= { s5ChasComMTmpSnr 17 }

-- Model 5000 (900-???) Chassis temperature sensor
s5ChasComM5000TmpSnrA
    OBJECT IDENTIFIER ::= { s5ChasComM5000TmpSnr 1 }

-- Model 5005 (900-???) Chassis temperature sensor
s5ChasComM5005TmpSnrA
    OBJECT IDENTIFIER ::= { s5ChasComM5005TmpSnr 1 }

-- Model ESU1860S Chassis temperature sensor
s5ChasComESU1860STmpSnr
    OBJECT IDENTIFIER ::= { s5ChasComMTmpSnr 18 }

-- Model ESU1860S CPU temperature sensor
s5ChasComESU1860STmpSnrCPU
    OBJECT IDENTIFIER ::= { s5ChasComESU1860STmpSnr 1 }

-- Model ESU1860S Board1 temperature sensor
s5ChasComESU1860STmpSnrBoard1
    OBJECT IDENTIFIER ::= { s5ChasComESU1860STmpSnr 2 }

-- Model ESU1860S Board2 temperature sensor
s5ChasComESU1860STmpSnrBoard2
    OBJECT IDENTIFIER ::= { s5ChasComESU1860STmpSnr 3 }

-- Model ESU1860B Chassis temperature sensor
s5ChasComESU1860BTmpSnr
    OBJECT IDENTIFIER ::= { s5ChasComMTmpSnr 19 }

-- Model ESU1860B CPU temperature sensor
s5ChasComESU1860BTmpSnrCPU
    OBJECT IDENTIFIER ::= { s5ChasComESU1860BTmpSnr 1 }

-- Model ESU1860B Board1 temperature sensor
s5ChasComESU1860BTmpSnrBoard1
    OBJECT IDENTIFIER ::= { s5ChasComESU1860BTmpSnr 2 }

-- Model ESU1860B Board2 temperature sensor
s5ChasComESU1860BTmpSnrBoard2
    OBJECT IDENTIFIER ::= { s5ChasComESU1860BTmpSnr 3 }

-- Model ESU1860T Chassis temperature sensor
s5ChasComESU1860TTmpSnr
    OBJECT IDENTIFIER ::= { s5ChasComMTmpSnr 20 }

-- Model ESU1860T CPU temperature sensor
s5ChasComESU1860TTmpSnrCPU
    OBJECT IDENTIFIER ::= { s5ChasComESU1860TTmpSnr 1 }

-- Model ESU1860T Board1 temperature sensor
s5ChasComESU1860TTmpSnrBoard1
    OBJECT IDENTIFIER ::= { s5ChasComESU1860TTmpSnr 2 }

-- Model ESU1860T Board2 temperature sensor
s5ChasComESU1860TTmpSnrBoard2
    OBJECT IDENTIFIER ::= { s5ChasComESU1860TTmpSnr 3 }

-- Model ESU1860V Chassis temperature sensor
s5ChasComESU1860VTmpSnr
    OBJECT IDENTIFIER ::= { s5ChasComMTmpSnr 21 }

-- Model ESU1860V CPU temperature sensor
s5ChasComESU1860VTmpSnrCPU
    OBJECT IDENTIFIER ::= { s5ChasComESU1860VTmpSnr 1 }

-- Model ESU1860V Board1 temperature sensor
s5ChasComESU1860VTmpSnrBoard1
    OBJECT IDENTIFIER ::= { s5ChasComESU1860VTmpSnr 2 }

-- Model ESU1860V Board2 temperature sensor
s5ChasComESU1860VTmpSnrBoard2
    OBJECT IDENTIFIER ::= { s5ChasComESU1860VTmpSnr 3 }

-- Model ESU1880S Chassis temperature sensor
s5ChasComESU1880STmpSnr
    OBJECT IDENTIFIER ::= { s5ChasComMTmpSnr 22 }

-- Model ESU1880S CPU temperature sensor
s5ChasComESU1880STmpSnrCPU
    OBJECT IDENTIFIER ::= { s5ChasComESU1880STmpSnr 1 }

-- Model ESU1880S Board1 temperature sensor
s5ChasComESU1880STmpSnrBoard1
    OBJECT IDENTIFIER ::= { s5ChasComESU1880STmpSnr 2 }

-- Model ESU1880S Board2 temperature sensor
s5ChasComESU1880STmpSnrBoard2
    OBJECT IDENTIFIER ::= { s5ChasComESU1880STmpSnr 3 }

-- Chassis level Fans
s5ChasComFan OBJECT IDENTIFIER ::= { s5ChasComTypeVal 4 }

-- Model 5000 (900-003) Chassis fan
s5ChasComFanM5000
    OBJECT IDENTIFIER ::= { s5ChasComFan 1 }

-- Centillion Chassis fan
s5ChasComFanCent OBJECT IDENTIFIER ::= { s5ChasComFan 2 }
--Centillion 50N Chassis Power Supply
s5ChasComCent50NFan OBJECT IDENTIFIER ::= { s5ChasComFan 3 }
--Centillion 50T Chassis Power Supply
s5ChasComCent50TFan OBJECT IDENTIFIER ::= { s5ChasComFan 4 }

-- Chassis level Fans (NEW names)
s5ChasComMFan OBJECT IDENTIFIER ::= { s5ChasComTypeVal 10 }

s5ChasComM5000Fan -- 5000 Chassis
    OBJECT IDENTIFIER ::= { s5ChasComMFan 12 }

s5ChasComM5005Fan -- 5005 Chassis
    OBJECT IDENTIFIER ::= { s5ChasComMFan 17 }

s5ChasComM1032xFan -- 1032x Chassis
    OBJECT IDENTIFIER ::= { s5ChasComMFan 16 }

s5ChasComM5DN000Fan -- Distributed 5000 Chassis
    OBJECT IDENTIFIER ::= { s5ChasComMFan 24 }

s5ChasComMNBayStackFan -- BayStack Ethernet Hub Fan
    OBJECT IDENTIFIER ::= { s5ChasComMFan 25 }

s5ChasComMBayStack100Fan -- BayStack 100BASE-T Hub Fan
    OBJECT IDENTIFIER ::= { s5ChasComMFan 27 }

s5ChasComM3000Fan -- 3000 Chassis Fan
    OBJECT IDENTIFIER ::= { s5ChasComMFan 28 }

s5ChasComM28200Fan --Model 28200 Ethernet Switch Chassis Level Fan
    OBJECT IDENTIFIER ::= { s5ChasComMFan 30 }

s5ChasComMBayStack301Fan -- Bay Stack 301 Chassis Level Fan
    OBJECT IDENTIFIER ::= { s5ChasComMFan 31 }

s5ChasComSwitchNodeFan -- Switch Node Chassis Fan
    OBJECT IDENTIFIER ::= { s5ChasComMFan 32 }

s5ChasComMBayStackTrFan -- BayStack Token Ring hub Fan
    OBJECT IDENTIFIER ::= { s5ChasComMFan 36 }

s5ChasComBayStack150Fan -- BayStack150 Ethernet Hub Fan
    OBJECT IDENTIFIER ::= { s5ChasComMFan 41 }

s5ChasComMBayStack303-304Fan -- Bay Stack 303/304 Chassis Level Fan
    OBJECT IDENTIFIER ::= { s5ChasComMFan 42 }

s5ChasComBayStack200Fan -- BayStack200 Ethernet Hub Fan
    OBJECT IDENTIFIER ::= { s5ChasComMFan 43 }

s5ChasComBayStack250Fan -- BayStack250 Ethernet Hub Fan
    OBJECT IDENTIFIER ::= { s5ChasComMFan 44 }

s5ChasComMAccelar8010Fan -- Accelar 8010 Chassis Fan
    OBJECT IDENTIFIER ::= { s5ChasComMFan 45 }

s5ChasComBPS2000Fan -- BPS 2000 Ethernet Switch Fan
    OBJECT IDENTIFIER ::= { s5ChasComMFan 47 }
s5ChasComBPS2000UnitFan
    OBJECT IDENTIFIER ::= { s5ChasComBPS2000Fan 1 }

-- BayStack450 Switch Family Fan (includes BayStack 350 and 410)
s5ChasComBayStack450Fan
    OBJECT IDENTIFIER ::= { s5ChasComMFan 48 }
s5ChasComBayStack450UnitFan
    OBJECT IDENTIFIER ::= { s5ChasComBayStack450Fan 1 }
s5ChasComBayStack450RedundPwrFan
    OBJECT IDENTIFIER ::= { s5ChasComBayStack450Fan 2 }

-- BayStack3580 Gigabit Switch Fan
s5ChasComBayStack3580Fan
    OBJECT IDENTIFIER ::= { s5ChasComMFan 49 }
s5ChasComBayStack3580UnitFan
    OBJECT IDENTIFIER ::= { s5ChasComBayStack3580Fan 1 }

-- BayStack420 Ethernet Switch Fan
s5ChasComBayStack420Fan
    OBJECT IDENTIFIER ::= { s5ChasComMFan 50 }

-- OPTera Metro 1200 Ethernet Service Module Ethernet Switch Fan
s5ChasComMetro1200ESMFan
    OBJECT IDENTIFIER ::= { s5ChasComMFan 51 }
s5ChasComMetro1200ESMUnitFan
    OBJECT IDENTIFIER ::= { s5ChasComMetro1200ESMFan 1 }

-- BayStack380 Ethernet Switch Fan
s5ChasComBayStack380Fan
    OBJECT IDENTIFIER ::= { s5ChasComMFan 52 }
s5ChasComBayStack380UnitFan
    OBJECT IDENTIFIER ::= { s5ChasComBayStack380Fan 1 }

-- BayStack470 Ethernet Switch Fan
s5ChasComBayStack470Fan
    OBJECT IDENTIFIER ::= { s5ChasComMFan 53 }
s5ChasComBayStack470UnitFan
    OBJECT IDENTIFIER ::= { s5ChasComBayStack470Fan 1 }

-- OPTera Metro 1450 Ethernet Service Module Ethernet Switch Fan
s5ChasComMetro1450ESMFan
    OBJECT IDENTIFIER ::= { s5ChasComMFan 54 }
s5ChasComMetro1450ESMUnitFan
    OBJECT IDENTIFIER ::= { s5ChasComMetro1450ESMFan 1 }

-- OPTera Metro 1400 Ethernet Service Module Ethernet Switch Fan
s5ChasComMetro1400ESMFan
    OBJECT IDENTIFIER ::= { s5ChasComMFan 55 }
s5ChasComMetro1400ESMUnitFan
    OBJECT IDENTIFIER ::= { s5ChasComMetro1400ESMFan 1 }

-- BayStack 460-24T-PWR Ethernet Switch Fan
s5ChasComBayStack460-24T-PWRFan
    OBJECT IDENTIFIER ::= { s5ChasComMFan 56 }
s5ChasComBayStack460-24T-PWRUnitFan
    OBJECT IDENTIFIER ::= { s5ChasComBayStack460-24T-PWRFan 1 }

-- BayStack380-24F Ethernet Switch Fan
s5ChasComBayStack380-24F-Fan
    OBJECT IDENTIFIER ::= { s5ChasComMFan 57 }
s5ChasComBayStack380-24FUnitFan
    OBJECT IDENTIFIER ::= { s5ChasComBayStack380-24F-Fan 1 }

-- BayStack 5510-24T Ethernet Switch Fan
s5ChasComBayStack5510-24TFan
    OBJECT IDENTIFIER ::= { s5ChasComMFan 58 }
s5ChasComBayStack5510-24TUnitFan
    OBJECT IDENTIFIER ::= { s5ChasComBayStack5510-24TFan 1 }

-- BayStack 5510-48T Ethernet Switch Fan
s5ChasComBayStack5510-48TFan
    OBJECT IDENTIFIER ::= { s5ChasComMFan 59 }
s5ChasComBayStack5510-48TUnitFan
    OBJECT IDENTIFIER ::= { s5ChasComBayStack5510-48TFan 1 }

-- BayStack470-24T Ethernet Switch Fan
s5ChasComBayStack470-24TFan
    OBJECT IDENTIFIER ::= { s5ChasComMFan 60 }
s5ChasComBayStack470-24TUnitFan
    OBJECT IDENTIFIER ::= { s5ChasComBayStack470-24TFan 1 }

-- Nortel Networks Wireless LAN Access Point 2220 Fan
s5ChasComWLANAccessPoint2220Fan
    OBJECT IDENTIFIER ::= { s5ChasComMFan 61 }
s5ChasComWLANAccessPoint2220UnitFan
    OBJECT IDENTIFIER ::= { s5ChasComWLANAccessPoint2220Fan 1 }

-- Nortel Networks Wireless LAN Security Switch 2250 Fan
s5ChasComWLANSecuritySwitch2250Fan
    OBJECT IDENTIFIER ::= { s5ChasComMFan 62 }
s5ChasComWLANSecuritySwitch2250UnitFan
    OBJECT IDENTIFIER ::= { s5ChasComWLANSecuritySwitch2250Fan 1 }

-- BayStack 425 Ethernet Switch Fan
s5ChasComBayStack425Fan
    OBJECT IDENTIFIER ::= { s5ChasComMFan 63 }
s5ChasComBayStack425UnitFan
    OBJECT IDENTIFIER ::= { s5ChasComBayStack425Fan 1 }

-- Nortel Networks Wireless LAN Access Point 2221 Fan
s5ChasComWLANAccessPoint2221Fan
    OBJECT IDENTIFIER ::= { s5ChasComMFan 64 }
s5ChasComWLANAccessPoint2221UnitFan
    OBJECT IDENTIFIER ::= { s5ChasComWLANAccessPoint2221Fan 1 }

-- BayStack 5520-24T-PWR Ethernet Switch Fan
s5ChasComBayStack5520-24T-PWRFan
    OBJECT IDENTIFIER ::= { s5ChasComMFan 65 }
s5ChasComBayStack5520-24T-PWRUnitFan
    OBJECT IDENTIFIER ::= { s5ChasComBayStack5520-24T-PWRFan 1 }

-- BayStack 5520-48T-PWR Ethernet Switch Fan
s5ChasComBayStack5520-48T-PWRFan
    OBJECT IDENTIFIER ::= { s5ChasComMFan 66 }
s5ChasComBayStack5520-48T-PWRUnitFan
    OBJECT IDENTIFIER ::= { s5ChasComBayStack5520-48T-PWRFan 1 }

-- BayStack 325 Ethernet Switch Fan
s5ChasComBayStack325Fan
    OBJECT IDENTIFIER ::= { s5ChasComMFan 67 }
s5ChasComBayStack325UnitFan
    OBJECT IDENTIFIER ::= { s5ChasComBayStack325Fan 1 }

-- Nortel Networks Wireless LAN Access Point 2225 Fan
s5ChasComWLANAccessPoint2225Fan
    OBJECT IDENTIFIER ::= { s5ChasComMFan 68 }
s5ChasComWLANAccessPoint2225UnitFan
    OBJECT IDENTIFIER ::= { s5ChasComWLANAccessPoint2225Fan 1 }

-- BayStack470-24T PWR Ethernet Switch Fan
s5ChasComBayStack470-24T-PWRFan
    OBJECT IDENTIFIER ::= { s5ChasComMFan 69 }
s5ChasComBayStack470-24T-PWRUnitFan
    OBJECT IDENTIFIER ::= { s5ChasComBayStack470-24T-PWRFan 1 }

-- BayStack470-48T PWR Ethernet Switch Fan
s5ChasComBayStack470-48T-PWRFan
    OBJECT IDENTIFIER ::= { s5ChasComMFan 70 }
s5ChasComBayStack470-48T-PWRUnitFan
    OBJECT IDENTIFIER ::= { s5ChasComBayStack470-48T-PWRFan 1 }

-- Nortel Networks Wireless LAN Security Switch 2270 Fan
s5ChasComWLANSecuritySwitch2270Fan
    OBJECT IDENTIFIER ::= { s5ChasComMFan 71 }
s5ChasComWLANSecuritySwitch2270UnitFan
    OBJECT IDENTIFIER ::= { s5ChasComWLANSecuritySwitch2270Fan 1 }

-- Ethernet Routing Switch 5530-24TFD Switch Fan
s5ChasComEthernetRoutingSwitch5530-24TFDFan
    OBJECT IDENTIFIER ::= { s5ChasComMFan 72 }
s5ChasComEthernetRoutingSwitch5530-24TFDUnitFan
    OBJECT IDENTIFIER ::= { s5ChasComEthernetRoutingSwitch5530-24TFDFan 1 }

-- Ethernet Switch 3510-24T Switch Fan
s5ChasComEthernetSwitch3510-24TFan
    OBJECT IDENTIFIER ::= { s5ChasComMFan 73 }
s5ChasComEthernetSwitch3510-24TUnitFan
    OBJECT IDENTIFIER ::= { s5ChasComEthernetSwitch3510-24TFan 1 }

-- SMB GIG BES 1010 24T Switch Fan
s5ChasComBES1010-24TFan
    OBJECT IDENTIFIER ::= { s5ChasComMFan 74 }
s5ChasComBES1010-24TUnitFan
    OBJECT IDENTIFIER ::= { s5ChasComBES1010-24TFan 1 }

-- SMB GIG BES 1010 48T Switch Fan
s5ChasComBES1010-48TFan
    OBJECT IDENTIFIER ::= { s5ChasComMFan 75 }
s5ChasComBES1010-48TUnitFan
    OBJECT IDENTIFIER ::= { s5ChasComBES1010-48TFan 1 }

-- SMB GIG BES 1020 24T PWR Switch Fan
s5ChasComBES1020-24T-PWRFan
    OBJECT IDENTIFIER ::= { s5ChasComMFan 76 }
s5ChasComBES1020-24T-PWRUnitFan
    OBJECT IDENTIFIER ::= { s5ChasComBES1020-24T-PWRFan 1 }

-- SMB GIG BES 1020 48T PWR Switch Fan
s5ChasComBES1020-48T-PWRFan
    OBJECT IDENTIFIER ::= { s5ChasComMFan 77 }
s5ChasComBES1020-48T-PWRUnitFan
    OBJECT IDENTIFIER ::= { s5ChasComBES1020-48T-PWRFan 1 }

-- SMB GIG BES 2010 24T Switch Fan
s5ChasComBES2010-24TFan
    OBJECT IDENTIFIER ::= { s5ChasComMFan 78 }
s5ChasComBES2010-24TUnitFan
    OBJECT IDENTIFIER ::= { s5ChasComBES2010-24TFan 1 }

-- SMB GIG BES 2010 48T Switch Fan
s5ChasComBES2010-48TFan
    OBJECT IDENTIFIER ::= { s5ChasComMFan 79 }
s5ChasComBES2010-48TUnitFan
    OBJECT IDENTIFIER ::= { s5ChasComBES2010-48TFan 1 }

-- SMB GIG BES 2020 24T PWR Switch Fan
s5ChasComBES2020-24T-PWRFan
    OBJECT IDENTIFIER ::= { s5ChasComMFan 80 }
s5ChasComBES2020-24T-PWRUnitFan
    OBJECT IDENTIFIER ::= { s5ChasComBES2020-24T-PWRFan 1 }

-- SMB GIG BES 2020 48T PWR Switch Fan
s5ChasComBES2020-48T-PWRFan
    OBJECT IDENTIFIER ::= { s5ChasComMFan 81 }
s5ChasComBES2020-48T-PWRUnitFan
    OBJECT IDENTIFIER ::= { s5ChasComBES2020-48T-PWRFan 1 }

-- SMB FE BES 110 24T Switch Fan
s5ChasComBES110-24TFan
    OBJECT IDENTIFIER ::= { s5ChasComMFan 82 }
s5ChasComBES110-24TUnitFan
    OBJECT IDENTIFIER ::= { s5ChasComBES110-24TFan 1 }

-- SMB FE BES 110 48T Switch Fan
s5ChasComBES110-48TFan
    OBJECT IDENTIFIER ::= { s5ChasComMFan 83 }
s5ChasComBES110-48TUnitFan
    OBJECT IDENTIFIER ::= { s5ChasComBES110-48TFan 1 }

-- SMB FE BES 120 24T PWR Switch Fan
s5ChasComBES120-24T-PWRFan
    OBJECT IDENTIFIER ::= { s5ChasComMFan 84 }
s5ChasComBES120-24T-PWRUnitFan
    OBJECT IDENTIFIER ::= { s5ChasComBES120-24T-PWRFan 1 }

-- SMB FE BES 120 48T PWR Switch Fan
s5ChasComBES120-48T-PWRFan
    OBJECT IDENTIFIER ::= { s5ChasComMFan 85 }
s5ChasComBES120-48T-PWRUnitFan
    OBJECT IDENTIFIER ::= { s5ChasComBES120-48T-PWRFan 1 }

-- SMB FE BES 210 24T Switch Fan
s5ChasComBES210-24TFan
    OBJECT IDENTIFIER ::= { s5ChasComMFan 86 }
s5ChasComBES210-24TUnitFan
    OBJECT IDENTIFIER ::= { s5ChasComBES210-24TFan 1 }

-- SMB FE BES 210 48T Switch Fan
s5ChasComBES210-48TFan
    OBJECT IDENTIFIER ::= { s5ChasComMFan 87 }
s5ChasComBES210-48TUnitFan
    OBJECT IDENTIFIER ::= { s5ChasComBES210-48TFan 1 }

-- SMB FE BES 220 24T PWR Switch Fan
s5ChasComBES220-24T-PWRFan
    OBJECT IDENTIFIER ::= { s5ChasComMFan 88 }
s5ChasComBES220-24T-PWRUnitFan
    OBJECT IDENTIFIER ::= { s5ChasComBES220-24T-PWRFan 1 }

-- SMB FE BES 220 48T PWR Switch Fan
s5ChasComBES220-48T-PWRFan
    OBJECT IDENTIFIER ::= { s5ChasComMFan 89 }
s5ChasComBES220-48T-PWRUnitFan
    OBJECT IDENTIFIER ::= { s5ChasComBES220-48T-PWRFan 1 }

-- ERS4548GT Switch Fan
s5ChasComERS4548GTFan
    OBJECT IDENTIFIER ::= { s5ChasComMFan 90 }
s5ChasComERS4548GTUnitFan
    OBJECT IDENTIFIER ::= { s5ChasComERS4548GTFan 1 }

-- ERS4548GT-PWR Switch Fan
s5ChasComERS4548GT-PWRFan
    OBJECT IDENTIFIER ::= { s5ChasComMFan 91 }
s5ChasComERS4548GT-PWRUnitFan
    OBJECT IDENTIFIER ::= { s5ChasComERS4548GT-PWRFan 1 }

-- ERS4550T Switch Fan
s5ChasComERS4550TFan
    OBJECT IDENTIFIER ::= { s5ChasComMFan 92 }
s5ChasComERS4550TUnitFan
    OBJECT IDENTIFIER ::= { s5ChasComERS4550TFan 1 }

-- ERS4550T-PWR Switch Fan
s5ChasComERS4550T-PWRFan
    OBJECT IDENTIFIER ::= { s5ChasComMFan 93 }
s5ChasComERS4550T-PWRUnitFan
    OBJECT IDENTIFIER ::= { s5ChasComERS4550T-PWRFan 1 }

-- ERS4526FX Switch Fan
s5ChasComERS4526FXFan
    OBJECT IDENTIFIER ::= { s5ChasComMFan 94 }
s5ChasComERS4526FXUnitFan
    OBJECT IDENTIFIER ::= { s5ChasComERS4526FXFan 1 }

-- ERS2500-26T Switch Fan
s5ChasComERS2500-26TFan
    OBJECT IDENTIFIER ::= { s5ChasComMFan 95 }
s5ChasComERS2500-26TUnitFan
    OBJECT IDENTIFIER ::= { s5ChasComERS2500-26TFan 1 }

-- ERS2500-26T-PWR Switch Fan
s5ChasComERS2500-26T-PWRFan
    OBJECT IDENTIFIER ::= { s5ChasComMFan 96 }
s5ChasComERS2500-26T-PWRUnitFan
    OBJECT IDENTIFIER ::= { s5ChasComERS2500-26T-PWRFan 1 }

-- ERS2500-50T Switch Fan
s5ChasComERS2500-50TFan
    OBJECT IDENTIFIER ::= { s5ChasComMFan 97 }
s5ChasComERS2500-50TUnitFan
    OBJECT IDENTIFIER ::= { s5ChasComERS2500-50TFan 1 }

-- ERS2500-50T-PWR Switch Fan
s5ChasComERS2500-50T-PWRFan
    OBJECT IDENTIFIER ::= { s5ChasComMFan 98 }
s5ChasComERS2500-50T-PWRUnitFan
    OBJECT IDENTIFIER ::= { s5ChasComERS2500-50T-PWRFan 1 }

-- ERS4526GTX-PWR Switch Fan
s5ChasComERS4526GTX-PWRFan
    OBJECT IDENTIFIER ::= { s5ChasComMFan 99 }
s5ChasComERS4526GTX-PWRUnitFan
    OBJECT IDENTIFIER ::= { s5ChasComERS4526GTX-PWRFan 1 }

-- ERS4526GTX Switch Fan
s5ChasComERS4526GTXFan
    OBJECT IDENTIFIER ::= { s5ChasComMFan 100 }
s5ChasComERS4526GTXUnitFan
    OBJECT IDENTIFIER ::= { s5ChasComERS4526GTXFan 1 }

-- ERS4524GT Switch Fan
s5ChasComERS4524GTFan
    OBJECT IDENTIFIER ::= { s5ChasComMFan 101 }
s5ChasComERS4524GTUnitFan
    OBJECT IDENTIFIER ::= { s5ChasComERS4524GTFan 1 }

-- ERS4526T Switch Fan
s5ChasComERS4526TFan
    OBJECT IDENTIFIER ::= { s5ChasComMFan 102 }
s5ChasComERS4526TUnitFan
    OBJECT IDENTIFIER ::= { s5ChasComERS4526TFan 1 }

-- ERS4526T-PWR Switch Fan
s5ChasComERS4526T-PWRFan
    OBJECT IDENTIFIER ::= { s5ChasComMFan 103 }
s5ChasComERS4526T-PWRUnitFan
    OBJECT IDENTIFIER ::= { s5ChasComERS4526T-PWRFan 1 }

-- ERS5698-TFD-PWR Switch Fan
s5ChasComERS5698-TFD-PWRFan
    OBJECT IDENTIFIER ::= { s5ChasComMFan 104 }
s5ChasComERS5698-TFD-PWRUnitFan
    OBJECT IDENTIFIER ::= { s5ChasComERS5698-TFD-PWRFan 1 }

-- ERS5698-TFD Switch Fan
s5ChasComERS5698-TFDFan
    OBJECT IDENTIFIER ::= { s5ChasComMFan 105 }
s5ChasComERS5698-TFDUnitFan
    OBJECT IDENTIFIER ::= { s5ChasComERS5698-TFDFan 1 }

-- ERS5650-TD-PWR Switch Fan
s5ChasComERS5650-TD-PWRFan
    OBJECT IDENTIFIER ::= { s5ChasComMFan 106 }
s5ChasComERS5650-TD-PWRUnitFan
    OBJECT IDENTIFIER ::= { s5ChasComERS5650-TD-PWRFan 1 }

-- ERS5650-TD Switch Fan
s5ChasComERS5650-TDFan
    OBJECT IDENTIFIER ::= { s5ChasComMFan 107 }
s5ChasComERS5650-TDUnitFan
    OBJECT IDENTIFIER ::= { s5ChasComERS5650-TDFan 1 }

-- ERS5632-FD Switch Fan
s5ChasComERS5632-FDFan
    OBJECT IDENTIFIER ::= { s5ChasComMFan 108 }
s5ChasComERS5632-FDUnitFan
    OBJECT IDENTIFIER ::= { s5ChasComERS5632-FDFan 1 }

-- ESU1860S Switch Fan
s5ChasComESU1860SFan
    OBJECT IDENTIFIER ::= { s5ChasComMFan 109 }
s5ChasComESU1860SUnitFan
    OBJECT IDENTIFIER ::= { s5ChasComESU1860SFan 1 }

-- ESU1860B Switch Fan
s5ChasComESU1860BFan
    OBJECT IDENTIFIER ::= { s5ChasComMFan 110 }
s5ChasComESU1860BUnitFan
    OBJECT IDENTIFIER ::= { s5ChasComESU1860BFan 1 }

-- ESU1860T Switch Fan
s5ChasComESU1860TFan
    OBJECT IDENTIFIER ::= { s5ChasComMFan 111 }
s5ChasComESU1860TUnitFan
    OBJECT IDENTIFIER ::= { s5ChasComESU1860TFan 1 }

-- ESU1860V Switch Fan
s5ChasComESU1860VFan
    OBJECT IDENTIFIER ::= { s5ChasComMFan 112 }
s5ChasComESU1860VUnitFan
    OBJECT IDENTIFIER ::= { s5ChasComESU1860VFan 1 }

-- ESU1880S Switch Fan
s5ChasComESU1880SFan
    OBJECT IDENTIFIER ::= { s5ChasComMFan 113 }
s5ChasComESU1880SUnitFan
    OBJECT IDENTIFIER ::= { s5ChasComESU1880SFan 1 }

-- ERS4524GT-PWR Switch Fan
s5ChasComERS4524GT-PWRFan
    OBJECT IDENTIFIER ::= { s5ChasComMFan 114 }
s5ChasComERS4524GT-PWRUnitFan
    OBJECT IDENTIFIER ::= { s5ChasComERS4524GT-PWRFan 1 }

-- ERS6628XSGT Switch Fan
s5ChasComERS6628XSGTFan
    OBJECT IDENTIFIER ::= { s5ChasComMFan 115 }
s5ChasComERS6628XSGTUnitFan
    OBJECT IDENTIFIER ::= { s5ChasComERS6628XSGTFan 1 }

-- ERS6632XTS Switch Fan
s5ChasComERS6632XTSFan
    OBJECT IDENTIFIER ::= { s5ChasComMFan 116 }
s5ChasComERS6632XTSUnitFan
    OBJECT IDENTIFIER ::= { s5ChasComERS6632XTSFan 1 }

-- WC8180 Switch Fan
s5ChasComWC8180Fan
    OBJECT IDENTIFIER ::= { s5ChasComMFan 117 }
s5ChasComWC8180UnitFan
    OBJECT IDENTIFIER ::= { s5ChasComWC8180Fan 1 }

-- ERS4526T-PWR+ Switch Fan
s5ChasComERS4526T-PWR-PLUSFan
    OBJECT IDENTIFIER ::= { s5ChasComMFan 118 }
s5ChasComERS4526T-PWR-PLUSUnitFan
    OBJECT IDENTIFIER ::= { s5ChasComERS4526T-PWR-PLUSFan 1 }

-- ERS4550T-PWR+ Switch Fan
s5ChasComERS4550T-PWR-PLUSFan
    OBJECT IDENTIFIER ::= { s5ChasComMFan 119 }
s5ChasComERS4550T-PWR-PLUSUnitFan
    OBJECT IDENTIFIER ::= { s5ChasComERS4550T-PWR-PLUSFan 1 }

-- ERS4826GTS-PWR+ Switch Fan
s5ChasComERS4826GTS-PWR-PLUSFan
    OBJECT IDENTIFIER ::= { s5ChasComMFan 120 }
s5ChasComERS4826GTS-PWR-PLUSUnitFan
    OBJECT IDENTIFIER ::= { s5ChasComERS4826GTS-PWR-PLUSFan 1 }

-- ERS4850GTS-PWR+ Switch Fan
s5ChasComERS4850GTS-PWR-PLUSFan
    OBJECT IDENTIFIER ::= { s5ChasComMFan 121 }
s5ChasComERS4850GTS-PWR-PLUSUnitFan
    OBJECT IDENTIFIER ::= { s5ChasComERS4850GTS-PWR-PLUSFan 1 }

-- ERS4826GTS Switch Fan
s5ChasComERS4826GTSFan
    OBJECT IDENTIFIER ::= { s5ChasComMFan 122 }
s5ChasComERS4826GTSUnitFan
    OBJECT IDENTIFIER ::= { s5ChasComERS4826GTSFan 1 }

-- ERS4850GTS Switch Fan
s5ChasComERS4850GTSFan
    OBJECT IDENTIFIER ::= { s5ChasComMFan 123 }
s5ChasComERS4850GTSUnitFan
    OBJECT IDENTIFIER ::= { s5ChasComERS4850GTSFan 1 }

-- VSP7024XLS Switch Fan
s5ChasComVSP7024XLSFan
    OBJECT IDENTIFIER ::= { s5ChasComMFan 124 }
s5ChasComVSP7024XLSUnitFan
    OBJECT IDENTIFIER ::= { s5ChasComVSP7024XLSFan 1 }

-- ERS3510GT Switch Fan
s5ChasComERS3510GTFan
    OBJECT IDENTIFIER ::= { s5ChasComMFan 125 }
s5ChasComERS3510GTUnitFan
    OBJECT IDENTIFIER ::= { s5ChasComERS3510GTFan 1 }

-- ERS3510GT-PWR+ Switch Fan
s5ChasComERS3510GT-PWR-PLUSFan
    OBJECT IDENTIFIER ::= { s5ChasComMFan 126 }
s5ChasComERS3510GT-PWR-PLUSUnitFan
    OBJECT IDENTIFIER ::= { s5ChasComERS3510GT-PWR-PLUSFan 1 }

-- ERS3524GT Switch Fan
s5ChasComERS3524GTFan
    OBJECT IDENTIFIER ::= { s5ChasComMFan 127 }
s5ChasComERS3524GTUnitFan
    OBJECT IDENTIFIER ::= { s5ChasComERS3524GTFan 1 }

-- ERS3524GT-PWR+ Switch Fan
s5ChasComERS3524GT-PWR-PLUSFan
    OBJECT IDENTIFIER ::= { s5ChasComMFan 128 }
s5ChasComERS3524GT-PWR-PLUSUnitFan
    OBJECT IDENTIFIER ::= { s5ChasComERS3524GT-PWR-PLUSFan 1 }

-- ERS3526GT Switch Fan
s5ChasComERS3526GTFan
    OBJECT IDENTIFIER ::= { s5ChasComMFan 129 }
s5ChasComERS3526GTUnitFan
    OBJECT IDENTIFIER ::= { s5ChasComERS3526GTFan 1 }

-- ERS3526GT-PWR+ Switch Fan
s5ChasComERS3526GT-PWR-PLUSFan
    OBJECT IDENTIFIER ::= { s5ChasComMFan 130 }
s5ChasComERS3526GT-PWR-PLUSUnitFan
    OBJECT IDENTIFIER ::= { s5ChasComERS3526GT-PWR-PLUSFan 1 }

-- ERS3526T Switch Fan
s5ChasComERS3526TFan
    OBJECT IDENTIFIER ::= { s5ChasComMFan 131 }
s5ChasComERS3526TUnitFan
    OBJECT IDENTIFIER ::= { s5ChasComERS3526TFan 1 }

-- ERS3526T-PWR+ Switch Fan
s5ChasComERS3526T-PWR-PLUSFan
    OBJECT IDENTIFIER ::= { s5ChasComMFan 132 }
s5ChasComERS3526T-PWR-PLUSUnitFan
    OBJECT IDENTIFIER ::= { s5ChasComERS3526T-PWR-PLUSFan 1 }

-- ERS3549GTS Switch Fan
s5ChasComERS3549GTSFan
    OBJECT IDENTIFIER ::= { s5ChasComMFan 133 }
s5ChasComERS3549GTSUnitFan1
    OBJECT IDENTIFIER ::= { s5ChasComERS3549GTSFan 1 }
s5ChasComERS3549GTSUnitFan2
    OBJECT IDENTIFIER ::= { s5ChasComERS3549GTSFan 2 }

-- ERS3549GTS-PWR+ Switch Fan
s5ChasComERS3549GTS-PWR-PLUSFan
    OBJECT IDENTIFIER ::= { s5ChasComMFan 134 }
s5ChasComERS3549GTS-PWR-PLUSUnitFan1
    OBJECT IDENTIFIER ::= { s5ChasComERS3549GTS-PWR-PLUSFan 1 }
s5ChasComERS3549GTS-PWR-PLUSUnitFan2
    OBJECT IDENTIFIER ::= { s5ChasComERS3549GTS-PWR-PLUSFan 2 }
s5ChasComERS3549GTS-PWR-PLUSUnitFan3
    OBJECT IDENTIFIER ::= { s5ChasComERS3549GTS-PWR-PLUSFan 3 }
s5ChasComERS3549GTS-PWR-PLUSUnitFan4
    OBJECT IDENTIFIER ::= { s5ChasComERS3549GTS-PWR-PLUSFan 4 }

-- VSP7024XT Switch Fan
s5ChasComVSP7024XTFan
    OBJECT IDENTIFIER ::= { s5ChasComMFan 135 }
s5ChasComVSP7024XTUnitFan
    OBJECT IDENTIFIER ::= { s5ChasComVSP7024XTFan 1 }

-- ERS 5928GTS Switch Fan
s5ChasComERS5928GTSFan
    OBJECT IDENTIFIER ::= { s5ChasComMFan 136 }
s5ChasComERS5928GTSUnitFan
    OBJECT IDENTIFIER ::= { s5ChasComERS5928GTSFan 1 }

-- ERS 5928GTS-PWR+ Switch Fan
s5ChasComERS5928GTS-PWR-PLUSFan
    OBJECT IDENTIFIER ::= { s5ChasComMFan 137 }
s5ChasComERS5928GTS-PWR-PLUSUnitFan
    OBJECT IDENTIFIER ::= { s5ChasComERS5928GTS-PWR-PLUSFan 1 }

-- ERS 5952GTS Switch Fan
s5ChasComERS5952GTSFan
    OBJECT IDENTIFIER ::= { s5ChasComMFan 138 }
s5ChasComERS5952GTSUnitFan
    OBJECT IDENTIFIER ::= { s5ChasComERS5952GTSFan 1 }

-- ERS 5952GTS-PWR+ Switch Fan
s5ChasComERS5952GTS-PWR-PLUSFan
    OBJECT IDENTIFIER ::= { s5ChasComMFan 139 }
s5ChasComERS5952GTS-PWR-PLUSUnitFan
    OBJECT IDENTIFIER ::= { s5ChasComERS5952GTS-PWR-PLUSFan 1 }

-- ERS 5928GTS-uPWR Switch Fan
s5ChasComERS5928GTS-UPWRFan
    OBJECT IDENTIFIER ::= { s5ChasComMFan 140 }
s5ChasComERS5928GTS-UPWRUnitFan
    OBJECT IDENTIFIER ::= { s5ChasComERS5928GTS-UPWRFan 1 }

-- ERS 59100GTS Switch Fan
s5ChasComERS59100GTSFan
    OBJECT IDENTIFIER ::= { s5ChasComMFan 141 }
s5ChasComERS59100GTSUnitFan
    OBJECT IDENTIFIER ::= { s5ChasComERS59100GTSFan 1 }

-- ERS 59100GTS-PWR+ Switch Fan
s5ChasComERS59100GTS-PWR-PLUSFan
    OBJECT IDENTIFIER ::= { s5ChasComMFan 142 }
s5ChasComERS59100GTS-PWR-PLUSUnitFan
    OBJECT IDENTIFIER ::= { s5ChasComERS59100GTS-PWR-PLUSFan 1 }

-- ERS 4926GTS Switch Fan
s5ChasComERS4926GTSFan
    OBJECT IDENTIFIER ::= { s5ChasComMFan 143 }
s5ChasComERS4926GTSUnitFan
    OBJECT IDENTIFIER ::= { s5ChasComERS4926GTSFan 1 }

-- ERS 4926GTS-PWR+ Switch Fan
s5ChasComERS4926GTS-PWR-PLUSFan
    OBJECT IDENTIFIER ::= { s5ChasComMFan 144 }
s5ChasComERS4926GTS-PWR-PLUSUnitFan
    OBJECT IDENTIFIER ::= { s5ChasComERS4926GTS-PWR-PLUSFan 1 }

-- ERS 4950GTS Switch Fan
s5ChasComERS4950GTSFan
    OBJECT IDENTIFIER ::= { s5ChasComMFan 145 }
s5ChasComERS4950GTSUnitFan
    OBJECT IDENTIFIER ::= { s5ChasComERS4950GTSFan 1 }

-- ERS 4950GTS-PWR+ Switch Fan
s5ChasComERS4950GTS-PWR-PLUSFan
    OBJECT IDENTIFIER ::= { s5ChasComMFan 146 }
s5ChasComERS4950GTS-PWR-PLUSUnitFan
    OBJECT IDENTIFIER ::= { s5ChasComERS4950GTS-PWR-PLUSFan 1 }

-- ERS3550T Switch Fan
s5ChasComERS3550TFan
    OBJECT IDENTIFIER ::= { s5ChasComMFan 147 }
s5ChasComERS3550TUnitFan1
    OBJECT IDENTIFIER ::= { s5ChasComERS3550TFan 1 }
s5ChasComERS3550TUnitFan2
    OBJECT IDENTIFIER ::= { s5ChasComERS3550TFan 2 }

-- ERS3550T-PWR+ Switch Fan
s5ChasComERS3550T-PWR-PLUSFan
    OBJECT IDENTIFIER ::= { s5ChasComMFan 148 }
s5ChasComERS3550T-PWR-PLUSUnitFan1
    OBJECT IDENTIFIER ::= { s5ChasComERS3550T-PWR-PLUSFan 1 }
s5ChasComERS3550T-PWR-PLUSUnitFan2
    OBJECT IDENTIFIER ::= { s5ChasComERS3550T-PWR-PLUSFan 2 }
s5ChasComERS3550T-PWR-PLUSUnitFan3
    OBJECT IDENTIFIER ::= { s5ChasComERS3550T-PWR-PLUSFan 3 }
s5ChasComERS3550T-PWR-PLUSUnitFan4
    OBJECT IDENTIFIER ::= { s5ChasComERS3550T-PWR-PLUSFan 4 }

-- ERS3626GTS Switch Fan
s5ChasComERS3626GTSFan
    OBJECT IDENTIFIER ::= { s5ChasComMFan 149 }
s5ChasComERS3626GTSUnitFan1
    OBJECT IDENTIFIER ::= { s5ChasComERS3626GTSFan 1 }

-- ERS3626GTSPWR+ Switch Fan
s5ChasComERS3626GTS-PWR-PLUSFan
    OBJECT IDENTIFIER ::= { s5ChasComMFan 150 }
s5ChasComERS3626GTS-PWR-PLUSUnitFan1
    OBJECT IDENTIFIER ::= { s5ChasComERS3626GTS-PWR-PLUSFan 1 }
s5ChasComERS3626GTS-PWR-PLUSUnitFan2
    OBJECT IDENTIFIER ::= { s5ChasComERS3626GTS-PWR-PLUSFan 2 }
s5ChasComERS3626GTS-PWR-PLUSUnitFan3
    OBJECT IDENTIFIER ::= { s5ChasComERS3626GTS-PWR-PLUSFan 3 }

-- ERS3650GTS Switch Fan
s5ChasComERS3650GTSFan
    OBJECT IDENTIFIER ::= { s5ChasComMFan 151 }
s5ChasComERS3650GTSUnitFan1
    OBJECT IDENTIFIER ::= { s5ChasComERS3650GTSFan 1 }

-- ERS3650GTSPWR+ Switch Fan
s5ChasComERS3650GTS-PWR-PLUSFan
    OBJECT IDENTIFIER ::= { s5ChasComMFan 152 }
s5ChasComERS3650GTS-PWR-PLUSUnitFan1
    OBJECT IDENTIFIER ::= { s5ChasComERS3650GTS-PWR-PLUSFan 1 }
s5ChasComERS3650GTS-PWR-PLUSUnitFan2
    OBJECT IDENTIFIER ::= { s5ChasComERS3650GTS-PWR-PLUSFan 2 }
s5ChasComERS3650GTS-PWR-PLUSUnitFan3
    OBJECT IDENTIFIER ::= { s5ChasComERS3650GTS-PWR-PLUSFan 3 }
s5ChasComERS3650GTS-PWR-PLUSUnitFan4
    OBJECT IDENTIFIER ::= { s5ChasComERS3650GTS-PWR-PLUSFan 4 }

-- ERS 5928MTS-uPWR Switch Fan
s5ChasComERS5928MTS-UPWRFan
    OBJECT IDENTIFIER ::= { s5ChasComMFan 153 }
s5ChasComERS5928MTS-UPWRUnitFan
    OBJECT IDENTIFIER ::= { s5ChasComERS5928MTS-UPWRFan 1 }

-- Model 5000 (900-003) Chassis fan
s5ChasComM5000FanA
    OBJECT IDENTIFIER ::= { s5ChasComM5000Fan 1 }

-- Model 5000 (900-003) Chassis fan (real return code)
s5ChasComM5000FanAA
    OBJECT IDENTIFIER ::= { s5ChasComM5000Fan 2 }

-- Model 5005 Chassis fan
s5ChasComM5005FanA
    OBJECT IDENTIFIER ::= { s5ChasComM5005Fan 1 }

-- Model 1032x Chassis fan
s5ChasComM1032xFanA
    OBJECT IDENTIFIER ::= { s5ChasComM1032xFan 1 }

-- Model 3000 Chassis Fan
s5ChasComM3000FanA
    OBJECT IDENTIFIER ::= { s5ChasComM3000Fan 1 }

-- Model 5DN002 Hub 2.5 inch Fan
s5ChasComM5DN002Fan-1U
    OBJECT IDENTIFIER ::= { s5ChasComM5DN000Fan 1 }

-- Model 5DN003 Hub 3.5 inch Fan
s5ChasComM5DN003Fan-2U
    OBJECT IDENTIFIER ::= { s5ChasComM5DN000Fan 2 }

-- BayStack Ethernet Hub Fan
s5ChasComMNBayStackFanA
    OBJECT IDENTIFIER ::= { s5ChasComMNBayStackFan 1 }

-- BayStack 100BASE-T Hub Fan
s5ChasComMBayStack100FanA
    OBJECT IDENTIFIER ::= { s5ChasComMBayStack100Fan 1 }

-- BayStack Token Hub Fan Type A
s5ChasComMBayStackTrFanA
    OBJECT IDENTIFIER ::= { s5ChasComMBayStackTrFan 1 }
-- Model 28200 Ethernet Switch Fan
s5ChasComM28200FanA
    OBJECT IDENTIFIER ::= { s5ChasComM28200Fan 1 }
-- BayStack 301 Fan A
s5ChasComMBayStack301FanA
    OBJECT IDENTIFIER ::= { s5ChasComMBayStack301Fan 1 }

-- BayStack150 Ethernet Master Hub Fan
s5ChasComBayStack150MasterFan
    OBJECT IDENTIFIER ::= { s5ChasComBayStack150Fan 1 }

-- BayStack200 Ethernet Master Hub Fan
s5ChasComBayStack200MasterFan
    OBJECT IDENTIFIER ::= { s5ChasComBayStack200Fan 1 }

-- BayStack250 10/100 Ethernet Master Hub Fan
s5ChasComBayStack250MasterFan
    OBJECT IDENTIFIER ::= { s5ChasComBayStack250Fan 1 }
-- BayStack250 10/100 Ethernet Slave Hub Fan
s5ChasComBayStack250SlaveFan
    OBJECT IDENTIFIER ::= { s5ChasComBayStack250Fan 2 }



-- Chassis level Backplane Clocks
s5ChasComClk OBJECT IDENTIFIER ::= { s5ChasComTypeVal 5 }

-- Model 5000 Backplane Clock
s5ChasComClkM5000
    OBJECT IDENTIFIER ::= { s5ChasComClk 1 }

-- Chassis level Backplane Clocks (NEW names)
s5ChasComMClk OBJECT IDENTIFIER ::= { s5ChasComTypeVal 11 }
s5ChasComM5000Clk -- 5000 Chassis
    OBJECT IDENTIFIER ::= { s5ChasComMClk 12 }
s5ChasComM5005Clk -- 5005 Chassis
    OBJECT IDENTIFIER ::= { s5ChasComMClk 17 }
s5ChasComMAccelar8010Clk -- Accelar 8010 Chassis
    OBJECT IDENTIFIER ::= { s5ChasComMClk 18 }

-- Model 5000 (900-???) Backplane Clock
s5ChasComM5000ClkA
    OBJECT IDENTIFIER ::= { s5ChasComM5000Clk 1 }

-- Model 5005 (900-???) Backplane Clock
s5ChasComM5005ClkA
    OBJECT IDENTIFIER ::= { s5ChasComM5005Clk 1 }

-- Supervisor Module and Boards in Slots
s5ChasComMod OBJECT IDENTIFIER ::= { s5ChasComTypeVal 6 }

-- Model 331X Ethernet Network Management Module
s5ChasComM331X
    OBJECT IDENTIFIER ::= { s5ChasComMod 1 }
s5ChasComMDA331X
    OBJECT IDENTIFIER ::= { s5ChasComM331X 255 }

-- Model 3302 Shielded Twisted Pair (STP) Host Module
s5ChasComM3302
    OBJECT IDENTIFIER ::= { s5ChasComMod 2 }
s5ChasComMDA3302
    OBJECT IDENTIFIER ::= { s5ChasComM3302 255 }

-- Model 33XX Ethernet Local Bridge
s5ChasComM33XX
    OBJECT IDENTIFIER ::= { s5ChasComMod 3 }
s5ChasComMDA3324-ST -- Model 3324-ST Ethernet Local Bridge with FOIRL FiberPort
    OBJECT IDENTIFIER ::= { s5ChasComM33XX 0 }
s5ChasComMDA3323 -- Model 3323 Ethernet Local Bridge with AUI Port
    OBJECT IDENTIFIER ::= { s5ChasComM33XX 3 }

-- Model 3304-ST FOIRL Fiber Optic Host Module
s5ChasComM3304
    OBJECT IDENTIFIER ::= { s5ChasComMod 4 }
s5ChasComMDA3304
    OBJECT IDENTIFIER ::= { s5ChasComM3304 255 }

-- Model 3305 Unshielded Twisted Pair (UTP) Host Module
s5ChasComM3305
    OBJECT IDENTIFIER ::= { s5ChasComMod 5 }
s5ChasComMDA3305
    OBJECT IDENTIFIER ::= { s5ChasComM3305 255 }

-- Model 333X Ethernet Retiming Unit
s5ChasComM333X
    OBJECT IDENTIFIER ::= { s5ChasComMod 6 }
s5ChasComMDA3334-ST -- Model 3334-ST Ethernet Retiming Unit with FOIRL
    OBJECT IDENTIFIER ::= { s5ChasComM333X 0 }
s5ChasComMDA3333 -- Model 3333 Ethernet Retiming Unit with AUI
    OBJECT IDENTIFIER ::= { s5ChasComM333X 3 }

-- Model 3307 10BASE-T 50 Pin Host Module
s5ChasComM3307
    OBJECT IDENTIFIER ::= { s5ChasComMod 7 }
s5ChasComMDA3307
    OBJECT IDENTIFIER ::= { s5ChasComM3307 255 }

-- Model 3308 10BASE-T Host Module
s5ChasComM3308
    OBJECT IDENTIFIER ::= { s5ChasComMod 8 }
s5ChasComMDA3308
    OBJECT IDENTIFIER ::= { s5ChasComM3308 255 }

-- Model 3301 Thin Net Host Module
s5ChasComM3301
    OBJECT IDENTIFIER ::= { s5ChasComMod 9 }
s5ChasComMDA3301
    OBJECT IDENTIFIER ::= { s5ChasComM3301 255 }

-- Model 3904 FDDI fiber host module
s5ChasComM3904
    OBJECT IDENTIFIER ::= { s5ChasComMod 10 }
s5ChasComMDA3904
    OBJECT IDENTIFIER ::= { s5ChasComM3904 85 }
s5ChasComMDA3904-2SM
    OBJECT IDENTIFIER ::= { s5ChasComM3904 90 }
s5ChasComMDA3904-4SM
    OBJECT IDENTIFIER ::= { s5ChasComM3904 170 }

-- Model 3902 FDDI STP host module
s5ChasComM3902
    OBJECT IDENTIFIER ::= { s5ChasComMod 11 }
s5ChasComMDA3902
    OBJECT IDENTIFIER ::= { s5ChasComM3902 255 }

-- Model 3910S Network Management Module
s5ChasComM3910S
    OBJECT IDENTIFIER ::= { s5ChasComMod 12 }
s5ChasComMDA3910S -- Model 3910 Super NMM
    OBJECT IDENTIFIER ::= { s5ChasComM3910S 80 }
s5ChasComMDA3910S-SM -- Model 3910S-SM FDDI Single Mode Fiber NMM
    OBJECT IDENTIFIER ::= { s5ChasComM3910S 160 }

-- Model 331XS Ethernet Network Management Module
s5ChasComM331XS
    OBJECT IDENTIFIER ::= { s5ChasComMod 14 }
s5ChasComMDA3314S -- Model 3314S Ethernet NMM with ST FORIL Fiber Port
    OBJECT IDENTIFIER ::= { s5ChasComM331XS 0 }
s5ChasComMDA3313S -- Model 3313S Ethernet NMM with AUI Port
    OBJECT IDENTIFIER ::= { s5ChasComM331XS 3 }

-- Model 3100R Summing Module
s5ChasComM3100R
    OBJECT IDENTIFIER ::= { s5ChasComMod 15 }
s5ChasComMDA3100R
    OBJECT IDENTIFIER ::= { s5ChasComM3100R 255 }

-- Model 3502 Shielded Twisted Pair Token Ring Host Module
s5ChasComM3502
    OBJECT IDENTIFIER ::= { s5ChasComMod 16 }
s5ChasComMDA3502
    OBJECT IDENTIFIER ::= { s5ChasComM3502 255 }

-- Model 3502A Shielded Twisted Pair Token Ring Host Module
s5ChasComM3502A
    OBJECT IDENTIFIER ::= { s5ChasComMod 17 }
s5ChasComMDA3502A
    OBJECT IDENTIFIER ::= { s5ChasComM3502A 255 }

-- Model 353X Repeater Module
s5ChasComM353X
    OBJECT IDENTIFIER ::= { s5ChasComMod 18 }
s5ChasComMDA3532 -- Model 3532 Shielded Twisted Pair Repeater Module
    OBJECT IDENTIFIER ::= { s5ChasComM353X 2 }
s5ChasComMDA3534 -- Model 3534 FOIRL Fiber Repeater Module
    OBJECT IDENTIFIER ::= { s5ChasComM353X 4 }

-- Model 3040 Network Control Engine
s5ChasComM3040
    OBJECT IDENTIFIER ::= { s5ChasComMod 19 }
s5ChasComMDA3040
    OBJECT IDENTIFIER ::= { s5ChasComM3040 255 }

-- Model 3505 Unshielded Twisted Pair Token Ring Host Module
s5ChasComM3505
    OBJECT IDENTIFIER ::= { s5ChasComMod 20 }
s5ChasComMDA3505
    OBJECT IDENTIFIER ::= { s5ChasComM3505 255 }

-- Model 3505A Unshielded Twisted Pair Token Ring Host Module
s5ChasComM3505A
    OBJECT IDENTIFIER ::= { s5ChasComMod 21 }
s5ChasComMDA3505A
    OBJECT IDENTIFIER ::= { s5ChasComM3505A 255 }

-- Model 355X FOIRL Fiber Ring-In/Ring-Out Module
s5ChasComM355X
    OBJECT IDENTIFIER ::= { s5ChasComMod 22 }
s5ChasComMDA3552 -- Model 3552 STP Ring-In/Ring-Out Module
    OBJECT IDENTIFIER ::= { s5ChasComM355X 2 }
s5ChasComMDA3554 -- Model 3554 FOIRL Fiber Ring-In/Ring-Out Module
    OBJECT IDENTIFIER ::= { s5ChasComM355X 4 }

-- Model 3040S Network Control Engine
s5ChasComM3040S
    OBJECT IDENTIFIER ::= { s5ChasComMod 23 }
s5ChasComMDA3040S
    OBJECT IDENTIFIER ::= { s5ChasComM3040S 255 }

-- Model 351X Token Ring Network Management Module
s5ChasComM351X
    OBJECT IDENTIFIER ::= { s5ChasComMod 24 }
s5ChasComMDA3512 -- Model 3512 Token Ring NMM with STP RI/RO
    OBJECT IDENTIFIER ::= { s5ChasComM351X 2 }
s5ChasComMDA3513 -- Model 3513 Token Ring NMM with STP Repeater
    OBJECT IDENTIFIER ::= { s5ChasComM351X 3 }
s5ChasComMDA3514 -- Model 3514 Token Ring NMM with Fiber RI/RO
    OBJECT IDENTIFIER ::= { s5ChasComM351X 4 }

-- Model 33XXS Ethernet High Speed Local Bridge
s5ChasComM33XXS
    OBJECT IDENTIFIER ::= { s5ChasComMod 25 }
s5ChasComMDA3324S -- Model 3324S Ethernet High Speed Local Bridge with FOIRLFiber Port
    OBJECT IDENTIFIER ::= { s5ChasComM33XXS 0 }
s5ChasComMDA3323S -- Model 3323S Ethernet High Speed Local Bridge with AUI
    OBJECT IDENTIFIER ::= { s5ChasComM33XXS 3 }

-- Model 3386 Ethernet Remote Router
s5ChasComM338X
    OBJECT IDENTIFIER ::= { s5ChasComMod 26 }
s5ChasComMDA3384 -- Model 3384 Ethernet Local Router with FOIRL Fiber Port
    OBJECT IDENTIFIER ::= { s5ChasComM338X 0 }
s5ChasComMDA3383 -- Model 3383 Ethernet Local Router with AUI Port
    OBJECT IDENTIFIER ::= { s5ChasComM338X 3 }
s5ChasComMDA3386 -- Model 3386 Ethernet Remote Router with Universal Port
    OBJECT IDENTIFIER ::= { s5ChasComM338X 4 }

-- Model 3328 EtherSwitch Module
s5ChasComM3328
    OBJECT IDENTIFIER ::= { s5ChasComMod 27 }
s5ChasComMDA3328
    OBJECT IDENTIFIER ::= { s5ChasComM3328 255 }

-- Model 3395 Ethernet terminal server
s5ChasComM3395
    OBJECT IDENTIFIER ::= { s5ChasComMod 28 }
s5ChasComMDA3395
    OBJECT IDENTIFIER ::= { s5ChasComM3395 255 }

-- Model 3394 Ethernet LocalTalk Router/Repeater
s5ChasComM3394
    OBJECT IDENTIFIER ::= { s5ChasComMod 29 }
s5ChasComMDA3394
    OBJECT IDENTIFIER ::= { s5ChasComM3394 255 }

-- Model 3522 Token Ring Bridge
s5ChasComM3522
    OBJECT IDENTIFIER ::= { s5ChasComMod 30 }
s5ChasComMDA3522
    OBJECT IDENTIFIER ::= { s5ChasComM3522 255 }

-- Model 3395A Ethernet terminal server
s5ChasComM3395A
    OBJECT IDENTIFIER ::= { s5ChasComMod 31 }
s5ChasComMDA3395A
    OBJECT IDENTIFIER ::= { s5ChasComM3395A 255 }

-- Model 3800 Multi Media Router Module
s5ChasComM3800
    OBJECT IDENTIFIER ::= { s5ChasComMod 32 }
s5ChasComMDA3803 -- Model 3803 Ethernet Media Adapter
    OBJECT IDENTIFIER ::= { s5ChasComM3800 0 }
s5ChasComMDA3805 -- Model 3805 Token Ring Media Adapter
    OBJECT IDENTIFIER ::= { s5ChasComM3800 1 }
s5ChasComMDA3809 -- Model 3809 FDDI Media Adapter
    OBJECT IDENTIFIER ::= { s5ChasComM3800 2 }
s5ChasComMDA3806 -- Model 3806 Serial WAN Media Adapter
    OBJECT IDENTIFIER ::= { s5ChasComM3800 3 }
s5ChasComMDA3800 -- Model 3800 Multi Media Router Module
    OBJECT IDENTIFIER ::= { s5ChasComM3800 255 }

-- Model 3368 10BASE-T LattisSecure Host Module
s5ChasComM3368
    OBJECT IDENTIFIER ::= { s5ChasComMod 36 }
s5ChasComMDA3368
    OBJECT IDENTIFIER ::= { s5ChasComM3368 255 }

-- Model 3307A 10BASE-T with Amp Connector Host Module
s5ChasComM3307A
    OBJECT IDENTIFIER ::= { s5ChasComMod 37 }
s5ChasComMDA3307A
    OBJECT IDENTIFIER ::= { s5ChasComM3307A 255 }

-- Model 3308A 10BASE-T Host Module
s5ChasComM3308A
    OBJECT IDENTIFIER ::= { s5ChasComMod 38 }
s5ChasComMDA3308A
    OBJECT IDENTIFIER ::= { s5ChasComM3308A 255 }

-- Model 3301-75 Ohms Thin Net Host Module
s5ChasComM3301-75
    OBJECT IDENTIFIER ::= { s5ChasComMod 41 }
s5ChasComMDA3301-75
    OBJECT IDENTIFIER ::= { s5ChasComM3301-75 255 }

-- Model 3301-93 Ohms Thin Net Host Module
s5ChasComM3301-93
    OBJECT IDENTIFIER ::= { s5ChasComMod 42 }
s5ChasComMDA3301-93
    OBJECT IDENTIFIER ::= { s5ChasComM3301-93 255 }

-- Model 3502B Unshielded Twisted Pair Token Ring Host Module
s5ChasComM3502B
    OBJECT IDENTIFIER ::= { s5ChasComMod 45 }
s5ChasComMDA3502B
    OBJECT IDENTIFIER ::= { s5ChasComM3502B 255 }

-- Model 3505B Unshielded Twisted Pair Token Ring Host Module
s5ChasComM3505B
    OBJECT IDENTIFIER ::= { s5ChasComMod 46 }
s5ChasComMDA3505B
    OBJECT IDENTIFIER ::= { s5ChasComM3505B 255 }

-- Model 3307HD 10BASE-T 50 Pin 24 Port Host Module
s5ChasComM3307HD
    OBJECT IDENTIFIER ::= { s5ChasComMod 47 }
s5ChasComMDA3307HD
    OBJECT IDENTIFIER ::= { s5ChasComM3307HD 255 }

-- Model 3356 Ethernet Remote Bridge
s5ChasComM3356
    OBJECT IDENTIFIER ::= { s5ChasComMod 56 }
s5ChasSubComMDA3356X21 -- Model 3356-X.21(barrier) Enet Remote Bridge
    OBJECT IDENTIFIER ::= { s5ChasComM3356 1 }
s5ChasSubComMDA3356X21U -- Model 3356-X.21(unbarrier) Enet Remote Bridge
    OBJECT IDENTIFIER ::= { s5ChasComM3356 2 }
s5ChasSubComMDA3356RS232 -- Model 3356-RS232 Ethernet Remote Bridge
    OBJECT IDENTIFIER ::= { s5ChasComM3356 3 }
s5ChasSubComMDA3356RS449 -- Model 3356-RS449 Ethernet Remote Bridge
    OBJECT IDENTIFIER ::= { s5ChasComM3356 4 }
s5ChasSubComMDA3356V35 -- Model 3356-V.35 Ethernet Remote Bridge
    OBJECT IDENTIFIER ::= { s5ChasComM3356 5 }
s5ChasSubComMDA3356G703 -- Model 3356G703 Ethernet Remote Bridge
    OBJECT IDENTIFIER ::= { s5ChasComM3356 6 }
s5ChasSubComMDA3356T1 -- Model 3356-T1 Ethernet Remote Bridge
    OBJECT IDENTIFIER ::= { s5ChasComM3356 7 }
s5ChasSubComMDA3356 -- Model 3356 Ethernet Remote Bridge
    OBJECT IDENTIFIER ::= { s5ChasComM3356 255 }

-- Model 3902A FDDI SDDI host module
s5ChasComM3902A
    OBJECT IDENTIFIER ::= { s5ChasComMod 63 }
s5ChasComMDA3902A
    OBJECT IDENTIFIER ::= { s5ChasComM3902A 255 }

-- Model 3910S-SD FDDI SDDI Network Management Module
s5ChasComM3910S-SD
    OBJECT IDENTIFIER ::= { s5ChasComMod 67 }
s5ChasComMDA3910S-SD
    OBJECT IDENTIFIER ::= { s5ChasComM3910S-SD 255 }

-- Model 3313A Ethernet Network Management Module with AUI Port
s5ChasComM3313A
    OBJECT IDENTIFIER ::= { s5ChasComMod 68 }
s5ChasComMDA3313A
    OBJECT IDENTIFIER ::= { s5ChasComM3313A 255 }

-- Model 3314A Ethernet Network Management Module with 10BASE-FL Port
s5ChasComM3314A
    OBJECT IDENTIFIER ::= { s5ChasComMod 69 }
s5ChasComMDA3314A
    OBJECT IDENTIFIER ::= { s5ChasComM3314A 255 }

-- Model 3304A FOIRL Fiber Optic Host Module
s5ChasComM3304A
    OBJECT IDENTIFIER ::= { s5ChasComMod 70 }
s5ChasComMDA3304A
    OBJECT IDENTIFIER ::= { s5ChasComM3304A 255 }

-- Model 3910SA FDDI Network Management Module
s5ChasComM3910SA
    OBJECT IDENTIFIER ::= { s5ChasComMod 71 }
s5ChasComMDA3910SA -- Model 3910SA FDDI NMM
    OBJECT IDENTIFIER ::= { s5ChasComM3910SA 80 }
s5ChasComMDA3910SA-SM -- Model 3910SA-SM FDDI NMM
    OBJECT IDENTIFIER ::= { s5ChasComM3910SA 160 }

-- Model 3905 UTP FDDI Host Module
s5ChasComM3905
    OBJECT IDENTIFIER ::= { s5ChasComMod 73 }
s5ChasComMDA3905
    OBJECT IDENTIFIER ::= { s5ChasComM3905 0 }

-- Model 3486 LattisEngine/486
s5ChasComM3486
    OBJECT IDENTIFIER ::= { s5ChasComMod 82 }
s5ChasComMDA3486
    OBJECT IDENTIFIER ::= { s5ChasComM3486 255 }

-- Model 3504-ST Token Ring Fiber Host Module
s5ChasComM3504-ST
    OBJECT IDENTIFIER ::= { s5ChasComMod 83 }
s5ChasComMDA3504-ST
    OBJECT IDENTIFIER ::= { s5ChasComM3504-ST 255 }

-- Model 3517SA Token Ring Network Management Module
s5ChasComM3517SA
    OBJECT IDENTIFIER ::= { s5ChasComMod 101 }
s5ChasComMDA3517SA
    OBJECT IDENTIFIER ::= { s5ChasComM3517SA 255 }

-- Model 3308B 10BASE-T Host Module
s5ChasComM3308B
    OBJECT IDENTIFIER ::= { s5ChasComMod 102 }
s5ChasComMDA3308B
    OBJECT IDENTIFIER ::= { s5ChasComM3308B 255 }

-- Model 3313SA Ethernet Network Management Module with AUI Port
s5ChasComM3313SA
    OBJECT IDENTIFIER ::= { s5ChasComMod 105 }
s5ChasComMDA3313SA
    OBJECT IDENTIFIER ::= { s5ChasComM3313SA 255 }

-- Model 3314SA Ethernet Network Management Module with 10BASE-FL Port
s5ChasComM3314SA
    OBJECT IDENTIFIER ::= { s5ChasComMod 106 }
s5ChasComMDA3314SA
    OBJECT IDENTIFIER ::= { s5ChasComM3314SA 255 }

-- Model 3174 Communications Controller Module
s5ChasComM3174
    OBJECT IDENTIFIER ::= { s5ChasComMod 107 }
s5ChasComMDA3174
    OBJECT IDENTIFIER ::= { s5ChasComM3174 255 }

-- Model 3522A Token Ring Bridge
s5ChasComM3522A
    OBJECT IDENTIFIER ::= { s5ChasComMod 108 }
s5ChasComMDA3522A
    OBJECT IDENTIFIER ::= { s5ChasComM3522A 255 }

-- Model 3299-C Terminal Multiplexor Adapter Module
s5ChasComM3299-C
    OBJECT IDENTIFIER ::= { s5ChasComMod 116 }
s5ChasComMDA3299-C
    OBJECT IDENTIFIER ::= { s5ChasComM3299-C 255 }

-- Model 3299-U UTP Terminal Multiplexor Adapter Module
s5ChasComM3299-U
    OBJECT IDENTIFIER ::= { s5ChasComMod 117 }
s5ChasComMDA3299-U
    OBJECT IDENTIFIER ::= { s5ChasComM3299-U 255 }

-- Model 3299-F Fiber Optic Terminal Adapter Module
s5ChasComM3299-F
    OBJECT IDENTIFIER ::= { s5ChasComMod 119 }
s5ChasComMDA3299-F
    OBJECT IDENTIFIER ::= { s5ChasComM3299-F 255 }

-- Model 3410 Fast Ethernet Network Management Module
s5ChasComM3410
    OBJECT IDENTIFIER ::= { s5ChasComMod 120 }
s5ChasComM3410Store -- Storage areas
    OBJECT IDENTIFIER ::= { s5ChasComM3410 0 }
s5ChasComM3410StoreBoot -- EPROM Boot Firmware
    OBJECT IDENTIFIER ::= { s5ChasComM3410Store 1 }
s5ChasComM3410StoreFlash -- FLASH Agent Image
    OBJECT IDENTIFIER ::= { s5ChasComM3410Store 2 }
s5ChasComM3410StoreDram -- DRAM Agent Image
    OBJECT IDENTIFIER ::= { s5ChasComM3410Store 3 }

-- Model 3405 Fast Ethernet Host Module with 12 100Base-TX Ports
s5ChasComM3405Tx12
    OBJECT IDENTIFIER ::= { s5ChasComMod 121 }
s5ChasComM3405Tx12Store -- Storage areas
    OBJECT IDENTIFIER ::= { s5ChasComM3405Tx12 0 }
s5ChasComM3405Tx12StoreRom -- ROM Host Firmware
    OBJECT IDENTIFIER ::= { s5ChasComM3405Tx12Store 1 }

-- Model 3475-FX Fast Ethernet Host Module with 11 100Base-TX Ports
-- and 1 100Base-FX Port
s5ChasComM3475FxTx11
    OBJECT IDENTIFIER ::= { s5ChasComMod 122 }
s5ChasComM3475FxTx11Store -- Storage areas
    OBJECT IDENTIFIER ::= { s5ChasComM3475FxTx11 0 }
s5ChasComM3475FxTx11StoreRom -- ROM HostFirmware
    OBJECT IDENTIFIER ::= { s5ChasComM3475FxTx11Store 1 }

-- Model 3308S Desktop Switching Host Module with 22 10Base-TX Ports
-- and 2 10/100 Ethernet Ports
s5ChasComM3308S
    OBJECT IDENTIFIER ::= { s5ChasComMod 130 }
s5ChasComM3308SStore -- Storage areas
    OBJECT IDENTIFIER ::= { s5ChasComM3308S 0 }
s5ChasComM3308SStoreDram -- DRAM
    OBJECT IDENTIFIER ::= { s5ChasComM3308SStore 1 }
s5ChasComM3308SStoreFlash1 -- FLASH Agent Image
    OBJECT IDENTIFIER ::= { s5ChasComM3308SStore 2 }
s5ChasComM3308SStoreFlash2 -- FLASH Agent Image
    OBJECT IDENTIFIER ::= { s5ChasComM3308SStore 3 }
s5ChasComM3308SStoreFlash3 -- FLASH Host Firmware
    OBJECT IDENTIFIER ::= { s5ChasComM3308SStore 4 }
s5ChasComM3308SStoreFlash4 -- FLASH Boot
    OBJECT IDENTIFIER ::= { s5ChasComM3308SStore 5 }

-- OpenBay Eversys S3000 Application Server Module
s5ChasComM3000ASM
    OBJECT IDENTIFIER ::= { s5ChasComMod 200 }
s5ChasComMDA3000ASM
    OBJECT IDENTIFIER ::= { s5ChasComM3000ASM 255 }

-- Model 5110 Supervisory Module
s5ChasComSupM5110
    OBJECT IDENTIFIER ::= { s5ChasComMod 258 }
s5ChasComSupM5110Store -- Storage areas
    OBJECT IDENTIFIER ::= { s5ChasComSupM5110 0 }
s5ChasComSupM5110StoreDram -- DRAM
    OBJECT IDENTIFIER ::= { s5ChasComSupM5110Store 1 }
s5ChasComSupM5110StoreFlash -- FLASH
    OBJECT IDENTIFIER ::= { s5ChasComSupM5110Store 2 }
s5ChasComSupM5110StoreNvram -- NVRAM
    OBJECT IDENTIFIER ::= { s5ChasComSupM5110Store 3 }
s5ChasComSupM5110StoreChaEeProm -- Chassis EEProm
    OBJECT IDENTIFIER ::= { s5ChasComSupM5110Store 4 }

-- Model 5304P Ethernet Host Module
s5ChasComBrdM5304P
    OBJECT IDENTIFIER ::= { s5ChasComMod 259 }
s5ChasComBrdM5304PStore -- Storage areas
    OBJECT IDENTIFIER ::= { s5ChasComBrdM5304P 0 }
s5ChasComBrdM5304PStore8051Rom -- 8051 Firmware
    OBJECT IDENTIFIER ::= { s5ChasComBrdM5304PStore 1 }
s5ChasComBrdM5304PStoreDspRom -- DSP Frimware
    OBJECT IDENTIFIER ::= { s5ChasComBrdM5304PStore 2 }

-- Model 5308 Ethernet Host Module
s5ChasComBrdM5308
    OBJECT IDENTIFIER ::= { s5ChasComMod 260 }
s5ChasComBrdM5308Store -- Storage areas
    OBJECT IDENTIFIER ::= { s5ChasComBrdM5308 0 }
s5ChasComBrdM5308Store8051Rom -- 8051 Firmware
    OBJECT IDENTIFIER ::= { s5ChasComBrdM5308Store 1 }
s5ChasComBrdM5308StoreDspRom -- DSP Frimware
    OBJECT IDENTIFIER ::= { s5ChasComBrdM5308Store 2 }

-- Model 5308-AF Ethernet Host Module
s5ChasComBrdM5308AF
    OBJECT IDENTIFIER ::= { s5ChasComMod 261 }
s5ChasComBrdM5308AFStore -- Storage areas
    OBJECT IDENTIFIER ::= { s5ChasComBrdM5308AF 0 }
s5ChasComBrdM5308AFStore8051Rom -- 8051 Firmware
    OBJECT IDENTIFIER ::= { s5ChasComBrdM5308AFStore 1 }
s5ChasComBrdM5308AFStoreDspRom -- DSP Frimware
    OBJECT IDENTIFIER ::= { s5ChasComBrdM5308AFStore 2 }

-- Model 5378-F Ethernet Host Module
s5ChasComBrdM5378F
    OBJECT IDENTIFIER ::= { s5ChasComMod 262 }
s5ChasComBrdM5378FStore -- Storage areas
    OBJECT IDENTIFIER ::= { s5ChasComBrdM5378F 0 }
s5ChasComBrdM5378FStore8051Rom -- 8051 Firmware
    OBJECT IDENTIFIER ::= { s5ChasComBrdM5378FStore 1 }
s5ChasComBrdM5378FStoreDspRom -- DSP Frimware
    OBJECT IDENTIFIER ::= { s5ChasComBrdM5378FStore 2 }

-- Model 5502 Token Ring Host Module
s5ChasComBrdM5502
    OBJECT IDENTIFIER ::= { s5ChasComMod 263 }
s5ChasComBrdM5502Store -- Storage areas
    OBJECT IDENTIFIER ::= { s5ChasComBrdM5502 0 }
s5ChasComBrdM5502Store8051Rom -- 8051 Firmware
    OBJECT IDENTIFIER ::= { s5ChasComBrdM5502Store 1 }

-- Model 5505P Token Ring Host Module
s5ChasComBrdM5505P
    OBJECT IDENTIFIER ::= { s5ChasComMod 264 }
s5ChasComBrdM5505PStore -- Storage areas
    OBJECT IDENTIFIER ::= { s5ChasComBrdM5505P 0 }
s5ChasComBrdM5505PStore8051Rom -- 8051 Firmware
    OBJECT IDENTIFIER ::= { s5ChasComBrdM5505PStore 1 }

-- Model 5575-F Token Ring Host Module
s5ChasComBrdM5575F
    OBJECT IDENTIFIER ::= { s5ChasComMod 265 }
s5ChasComBrdM5575FStore -- Storage areas
    OBJECT IDENTIFIER ::= { s5ChasComBrdM5575F 0 }
s5ChasComBrdM5575FStore8051Rom -- 8051 Firmware
    OBJECT IDENTIFIER ::= { s5ChasComBrdM5575FStore 1 }

-- Model 5902 FDDI Host Module
s5ChasComBrdM5902
    OBJECT IDENTIFIER ::= { s5ChasComMod 266 }
s5ChasComBrdM5902Store -- Storage areas
    OBJECT IDENTIFIER ::= { s5ChasComBrdM5902 0 }
s5ChasComBrdM5902StoreDram -- DRAM
    OBJECT IDENTIFIER ::= { s5ChasComBrdM5902Store 1 }
s5ChasComBrdM5902StoreFlash -- FLASH
    OBJECT IDENTIFIER ::= { s5ChasComBrdM5902Store 2 }
s5ChasComBrdM5902StoreNvram -- NVRAM
    OBJECT IDENTIFIER ::= { s5ChasComBrdM5902Store 3 }

-- Model 5904 FDDI Host Module
s5ChasComBrdM5904
    OBJECT IDENTIFIER ::= { s5ChasComMod 267 }
s5ChasComBrdM5904Store -- Storage areas
    OBJECT IDENTIFIER ::= { s5ChasComBrdM5904 0 }
s5ChasComBrdM5904StoreDram -- DRAM
    OBJECT IDENTIFIER ::= { s5ChasComBrdM5904Store 1 }
s5ChasComBrdM5904StoreFlash -- FLASH
    OBJECT IDENTIFIER ::= { s5ChasComBrdM5904Store 2 }
s5ChasComBrdM5904StoreNvram -- NVRAM
    OBJECT IDENTIFIER ::= { s5ChasComBrdM5904Store 3 }

-- Model 5904-2SM FDDI Host Module
s5ChasComBrdM59042SM
    OBJECT IDENTIFIER ::= { s5ChasComMod 268 }
s5ChasComBrdM59042SMStore -- Storage areas
    OBJECT IDENTIFIER ::= { s5ChasComBrdM59042SM 0 }
s5ChasComBrdM59042SMStoreDram -- DRAM
    OBJECT IDENTIFIER ::= { s5ChasComBrdM59042SMStore 1 }
s5ChasComBrdM59042SMStoreFlash -- FLASH
    OBJECT IDENTIFIER ::= { s5ChasComBrdM59042SMStore 2 }
s5ChasComBrdM59042SMStoreNvram -- NVRAM
    OBJECT IDENTIFIER ::= { s5ChasComBrdM59042SMStore 3 }

-- Model 5310 Ethernet Network Management Module
s5ChasComBrdM5310
    OBJECT IDENTIFIER ::= { s5ChasComMod 269 }
s5ChasComBrdM5310Store -- Storage areas
    OBJECT IDENTIFIER ::= { s5ChasComBrdM5310 0 }
s5ChasComBrdM5310StoreBoot -- EPROM Boot Firmware
    OBJECT IDENTIFIER ::= { s5ChasComBrdM5310 1 }
s5ChasComBrdM5310StoreFlash -- FLASH Agent image
    OBJECT IDENTIFIER ::= { s5ChasComBrdM5310Store 2 }
s5ChasComBrdM5310StoreDram -- DRAM Agent image
    OBJECT IDENTIFIER ::= { s5ChasComBrdM5310Store 3 }

-- Model 5510 Token Ring Network Management Module
s5ChasComBrdM5510
    OBJECT IDENTIFIER ::= { s5ChasComMod 270 }
s5ChasComBrdM5510Store -- Storage areas
    OBJECT IDENTIFIER ::= { s5ChasComBrdM5510 0 }
s5ChasComBrdM5510StoreBoot -- EPROM Boot Firmware
    OBJECT IDENTIFIER ::= { s5ChasComBrdM5510Store 1 }
s5ChasComBrdM5510StoreFlash -- FLASH Agent image
    OBJECT IDENTIFIER ::= { s5ChasComBrdM5510Store 2 }
s5ChasComBrdM5510StoreDram -- DRAM Agent image
    OBJECT IDENTIFIER ::= { s5ChasComBrdM5510Store 3 }

-- Model 5910S FDDI Network Management Module
s5ChasComBrdM5910S
    OBJECT IDENTIFIER ::= { s5ChasComMod 271 }
s5ChasComBrdM5910SStore -- Storage areas
    OBJECT IDENTIFIER ::= { s5ChasComBrdM5910S 0 }
s5ChasComBrdM5910SStoreDram -- DRAM Agent image
    OBJECT IDENTIFIER ::= { s5ChasComBrdM5910SStore 1 }
s5ChasComBrdM5910SStoreFlash -- FLASH Agent image
    OBJECT IDENTIFIER ::= { s5ChasComBrdM5910SStore 2 }
s5ChasComBrdM5910SStoreNvram -- NVRAM
    OBJECT IDENTIFIER ::= { s5ChasComBrdM5910SStore 3 }

-- Model 5910S-SM FDDI Network Management Module
s5ChasComBrdM5910SSM
    OBJECT IDENTIFIER ::= { s5ChasComMod 272 }
s5ChasComBrdM5910SSMStore -- Storage areas
    OBJECT IDENTIFIER ::= { s5ChasComBrdM5910SSM 0 }
s5ChasComBrdM5910SSMStoreDram -- DRAM Agent image
    OBJECT IDENTIFIER ::= { s5ChasComBrdM5910SSMStore 1 }
s5ChasComBrdM5910SSMStoreFlash -- FLASH Agent image
    OBJECT IDENTIFIER ::= { s5ChasComBrdM5910SSMStore 2 }
s5ChasComBrdM5910SSMStoreNvram -- NVRAM
    OBJECT IDENTIFIER ::= { s5ChasComBrdM5910SSMStore 3 }

-- Model 5311 Ethernet Data Collection Engine
s5ChasComBrdSubM5311
    OBJECT IDENTIFIER ::= { s5ChasComMod 273 }

-- Model 5511 Token Ring Data Collection Engine
s5ChasComBrdSubM5511
    OBJECT IDENTIFIER ::= { s5ChasComMod 274 }

-- Model 5905 FDDI Host Module
s5ChasComBrdM5905
    OBJECT IDENTIFIER ::= { s5ChasComMod 275 }
s5ChasComBrdM5905Store -- Storage areas
    OBJECT IDENTIFIER ::= { s5ChasComBrdM5905 0 }
s5ChasComBrdM5905StoreDram -- DRAM
    OBJECT IDENTIFIER ::= { s5ChasComBrdM5905Store 1 }
s5ChasComBrdM5905StoreFlash -- FLASH
    OBJECT IDENTIFIER ::= { s5ChasComBrdM5905Store 2 }
s5ChasComBrdM5905StoreNvram -- NVRAM
    OBJECT IDENTIFIER ::= { s5ChasComBrdM5905Store 3 }

-- Model 5574-C Token Ring Cluster Repeater/Host Module
s5ChasComBrdM5575C
    OBJECT IDENTIFIER ::= { s5ChasComMod 276 }
s5ChasComBrdM5575CStore -- Storage areas
    OBJECT IDENTIFIER ::= { s5ChasComBrdM5575C 0 }
s5ChasComBrdM5575CStore8051Rom -- 8051 Firmware
    OBJECT IDENTIFIER ::= { s5ChasComBrdM5575CStore 1 }

-- Model 559 Token Ring De-jitterizer/FPU Submodule
s5ChasComBrdM559
    OBJECT IDENTIFIER ::= { s5ChasComMod 277 }

-- Model 5390 Communications Server Module
s5ChasComBrdM5390
    OBJECT IDENTIFIER ::= { s5ChasComMod 278 }
s5ChasComBrdM5390Store -- Storage areas
    OBJECT IDENTIFIER ::= { s5ChasComBrdM5390 0 }
s5ChasComBrdM5390StoreDram -- DRAM
    OBJECT IDENTIFIER ::= { s5ChasComBrdM5390Store 1 }
s5ChasComBrdM5390StoreFlash -- FLASH
    OBJECT IDENTIFIER ::= { s5ChasComBrdM5390Store 2 }
s5ChasComBrdM5390StoreNvram -- NVRAM
    OBJECT IDENTIFIER ::= { s5ChasComBrdM5390Store 3 }

-- Model 5307 Ethernet Telco Host Module
s5ChasComBrdM5307
    OBJECT IDENTIFIER ::= { s5ChasComMod 279 }
s5ChasComBrdM5307Store -- Storage areas
    OBJECT IDENTIFIER ::= { s5ChasComBrdM5307 0 }
s5ChasComBrdM5307Store8051Rom -- 8051 Firmware
    OBJECT IDENTIFIER ::= { s5ChasComBrdM5307Store 1 }
s5ChasComBrdM5307StoreDspRom -- DSP Firmware
    OBJECT IDENTIFIER ::= { s5ChasComBrdM5307Store 2 }

-- Model 5308 Ethernet Host Module (Cost Reduced)
s5ChasComBrdMCR5308
    OBJECT IDENTIFIER ::= { s5ChasComMod 280 }
s5ChasComBrdMCR5308Store -- Storage areas
    OBJECT IDENTIFIER ::= { s5ChasComBrdMCR5308 0 }
s5ChasComBrdMCR5308Store8051Rom -- 8051 Firmware
    OBJECT IDENTIFIER ::= { s5ChasComBrdMCR5308Store 1 }
s5ChasComBrdMCR5308StoreDspRom -- DSP Firmware
    OBJECT IDENTIFIER ::= { s5ChasComBrdMCR5308Store 2 }

-- Model 5378-F Ethernet Cluster Host Module (Cost Reduced)
s5ChasComBrdMCR5378F
    OBJECT IDENTIFIER ::= { s5ChasComMod 281 }
s5ChasComBrdMCR5378FStore -- Storage areas
    OBJECT IDENTIFIER ::= { s5ChasComBrdMCR5378F 0 }
s5ChasComBrdMCR5378FStore8051Rom -- 8051 Firmware
    OBJECT IDENTIFIER ::= { s5ChasComBrdMCR5378FStore 1 }
s5ChasComBrdMCR5378FStoreDspRom -- DSP Firmware
    OBJECT IDENTIFIER ::= { s5ChasComBrdMCR5378FStore 2 }

-- Model 5505 Token Ring STP/UTP Host Module
s5ChasComBrdM5505
    OBJECT IDENTIFIER ::= { s5ChasComMod 282 }
s5ChasComBrdM5505Store -- Storage areas
    OBJECT IDENTIFIER ::= { s5ChasComBrdM5505 0 }
s5ChasComBrdM5505Store8051Rom -- 8051 Firmware
    OBJECT IDENTIFIER ::= { s5ChasComBrdM5505Store 1 }

-- Model 5115 Supervisory Module
s5ChasComSupM5115
    OBJECT IDENTIFIER ::= { s5ChasComMod 284 }
s5ChasComSupM5115Store -- Storage areas
    OBJECT IDENTIFIER ::= { s5ChasComSupM5115 0 }
s5ChasComSupM5115StoreDram -- DRAM
    OBJECT IDENTIFIER ::= { s5ChasComSupM5115Store 1 }
s5ChasComSupM5115StoreFlash -- FLASH
    OBJECT IDENTIFIER ::= { s5ChasComSupM5115Store 2 }
s5ChasComSupM5115StoreNvram -- NVRAM
    OBJECT IDENTIFIER ::= { s5ChasComSupM5115Store 3 }
s5ChasComSupM5115StoreChaEeProm -- Chassis EEProm
    OBJECT IDENTIFIER ::= { s5ChasComSupM5115Store 4 }

-- Model 5740 ATM Switch Control Module
s5ChasComBrdM5740
    OBJECT IDENTIFIER ::= { s5ChasComMod 285 }
s5ChasComBrdM5740Store -- Storage areas
    OBJECT IDENTIFIER ::= { s5ChasComBrdM5740 0 }
s5ChasComBrdM5740Store8051Rom -- 8051 firmware
    OBJECT IDENTIFIER ::= { s5ChasComBrdM5740Store 1 }
s5ChasComBrdM5740StoreBoot -- EPROM boot firmware
    OBJECT IDENTIFIER ::= { s5ChasComBrdM5740Store 2 }
s5ChasComBrdM5740StoreDram -- SRAM
    OBJECT IDENTIFIER ::= { s5ChasComBrdM5740Store 3 }
s5ChasComBrdM5740StoreNvram -- NVRAM
    OBJECT IDENTIFIER ::= { s5ChasComBrdM5740Store 4 }
s5ChasComBrdM5740StoreDisk1 -- disk drive #1
    OBJECT IDENTIFIER ::= { s5ChasComBrdM5740Store 5 }
s5ChasComBrdM5740StoreDisk2 -- disk drive #2
    OBJECT IDENTIFIER ::= { s5ChasComBrdM5740Store 6 }

-- Model 5720 ATM 12 Port Switch Fabric Module
s5ChasComBrdM5720
    OBJECT IDENTIFIER ::= { s5ChasComMod 287 }
s5ChasComBrdM5720Store -- Storage areas
    OBJECT IDENTIFIER ::= { s5ChasComBrdM5720 0 }
s5ChasComBrdM5720Store8051Rom -- 8051 firmware
    OBJECT IDENTIFIER ::= { s5ChasComBrdM5720Store 1 }
s5ChasComBrdM5720StoreEprom -- EPROM
    OBJECT IDENTIFIER ::= { s5ChasComBrdM5720Store 2 }
s5ChasComBrdM5720StoreSram -- SRAM
    OBJECT IDENTIFIER ::= { s5ChasComBrdM5720Store 3 }

-- Model 5700 ATM MDA Host Board
s5ChasComBrdM5700
    OBJECT IDENTIFIER ::= { s5ChasComMod 288 }
s5ChasComBrdM5700Store -- Storage areas
    OBJECT IDENTIFIER ::= { s5ChasComBrdM5700 0 }
s5ChasComBrdM5700Store8051Rom -- 8051 firmware
    OBJECT IDENTIFIER ::= { s5ChasComBrdM5700Store 1 }
s5ChasComBrdM5700StoreEprom -- EPROM
    OBJECT IDENTIFIER ::= { s5ChasComBrdM5700Store 2 }
s5ChasComBrdM5700StoreSram -- SRAM
    OBJECT IDENTIFIER ::= { s5ChasComBrdM5700Store 3 }

-- Model 5700-17 ATM 155M SONET OC-3C SMF-SC MDA
s5ChasComBrdSubM5700-17
    OBJECT IDENTIFIER ::= { s5ChasComMod 289 }

-- Model 5700-24 ATM 100M TAXI MMF-MIC MDA
s5ChasComBrdSubM5700-24
    OBJECT IDENTIFIER ::= { s5ChasComMod 290 }

-- Model 5700-14 ATM 155M SONET OC-3C MMF-ST MDA
s5ChasComBrdSubM5700-14
    OBJECT IDENTIFIER ::= { s5ChasComMod 291 }

-- Model 5700-31 ATM 45M B3ZS 75BNC-MDA
s5ChasComBrdSubM5700-31
    OBJECT IDENTIFIER ::= { s5ChasComMod 292 }

-- Model 5700-15 ATM 155M SONET OC-3C CAT5-RJ45 MDA
s5ChasComBrdSubM5700-15
    OBJECT IDENTIFIER ::= { s5ChasComMod 293 }

-- Model 5715 ATM 155M SONET OC-3C 8 CAT5-RJ-45 Host Board
s5ChasComBrdM5715
    OBJECT IDENTIFIER ::= { s5ChasComMod 294 }
s5ChasComBrdM5715Store -- Storage areas
    OBJECT IDENTIFIER ::= { s5ChasComBrdM5715 0 }
s5ChasComBrdM5715Store8051Rom -- 8051 firmware
    OBJECT IDENTIFIER ::= { s5ChasComBrdM5715Store 1 }
s5ChasComBrdM5715StoreEprom -- EPROM
    OBJECT IDENTIFIER ::= { s5ChasComBrdM5715Store 2 }
s5ChasComBrdM5715StoreSram -- SRAM
    OBJECT IDENTIFIER ::= { s5ChasComBrdM5715Store 3 }

-- Model 5714 ATM 155M SONET OC-3C 8 MMF-ST Host Board
s5ChasComBrdM5714
    OBJECT IDENTIFIER ::= { s5ChasComMod 295 }
s5ChasComBrdM5714Store -- Storage areas
    OBJECT IDENTIFIER ::= { s5ChasComBrdM5714 0 }
s5ChasComBrdM5714Store8051Rom -- 8051 firmware
    OBJECT IDENTIFIER ::= { s5ChasComBrdM5714Store 1 }
s5ChasComBrdM5714StoreEprom -- EPROM
    OBJECT IDENTIFIER ::= { s5ChasComBrdM5714Store 2 }
s5ChasComBrdM5714StoreSram -- SRAM
    OBJECT IDENTIFIER ::= { s5ChasComBrdM5714Store 3 }

-- Model 5328 ATM Ethernet Switch 24 Port 10BaseT Host
s5ChasComBrdM5328
    OBJECT IDENTIFIER ::= { s5ChasComMod 296 }
s5ChasComBrdM5328Store -- Storage areas
    OBJECT IDENTIFIER ::= { s5ChasComBrdM5328 0 }
s5ChasComBrdM5328Store8051Rom -- 8051 firmware
    OBJECT IDENTIFIER ::= { s5ChasComBrdM5328Store 1 }
s5ChasComBrdM5328StoreEprom -- EPROM
    OBJECT IDENTIFIER ::= { s5ChasComBrdM5328Store 2 }
s5ChasComBrdM5328StoreSram -- SRAM
    OBJECT IDENTIFIER ::= { s5ChasComBrdM5328Store 3 }

-- Model 5324 ATM Ethernet Switch 10 Port 10BaseF Host
s5ChasComBrdM5324
    OBJECT IDENTIFIER ::= { s5ChasComMod 297 }
s5ChasComBrdM5324Store -- Storage areas
    OBJECT IDENTIFIER ::= { s5ChasComBrdM5324 0 }
s5ChasComBrdM5324Store8051Rom -- 8051 firmware
    OBJECT IDENTIFIER ::= { s5ChasComBrdM5324Store 1 }
s5ChasComBrdM5324StoreEprom -- EPROM
    OBJECT IDENTIFIER ::= { s5ChasComBrdM5324Store 2 }
s5ChasComBrdM5324StoreSram -- SRAM
    OBJECT IDENTIFIER ::= { s5ChasComBrdM5324Store 3 }

-- Model 10328-F EtherCell Concentrator
s5ChasComBrdM10328F
    OBJECT IDENTIFIER ::= { s5ChasComMod 298 }
s5ChasComBrdM10328FStore -- Storage areas
    OBJECT IDENTIFIER ::= { s5ChasComBrdM10328F 0 }
s5ChasComBrdM10328FStoreSram -- SRAM
    OBJECT IDENTIFIER ::= { s5ChasComBrdM10328FStore 1 }
s5ChasComBrdM10328FStoreDram -- DRAM
    OBJECT IDENTIFIER ::= { s5ChasComBrdM10328FStore 2 }
s5ChasComBrdM10328FStoreNvram -- NVRAM
    OBJECT IDENTIFIER ::= { s5ChasComBrdM10328FStore 3 }
s5ChasComBrdM10328FStoreEprom -- EPROM
    OBJECT IDENTIFIER ::= { s5ChasComBrdM10328FStore 4 }
s5ChasComBrdM10328FStoreFlash -- FLASH
    OBJECT IDENTIFIER ::= { s5ChasComBrdM10328FStore 5 }

-- Model 10328-SM EtherCEll Concentrator
s5ChasComBrdM10328SM OBJECT IDENTIFIER ::= { s5ChasComMod 301 }
s5ChasComBrdM10328SMStore -- Storage areas
    OBJECT IDENTIFIER ::= { s5ChasComBrdM10328SM 0 }
s5ChasComBrdM10328SMStoreSram -- SRAM
    OBJECT IDENTIFIER ::= { s5ChasComBrdM10328SMStore 1 }
s5ChasComBrdM10328SMStoreDram -- DRAM
    OBJECT IDENTIFIER ::= { s5ChasComBrdM10328SMStore 2 }
s5ChasComBrdM10328SMStoreNvram -- NVRAM
    OBJECT IDENTIFIER ::= { s5ChasComBrdM10328SMStore 3 }
s5ChasComBrdM10328SMStoreEprom -- EPROM
    OBJECT IDENTIFIER ::= { s5ChasComBrdM10328SMStore 4 }
s5ChasComBrdM10328SMStoreFlash -- FLASH
    OBJECT IDENTIFIER ::= { s5ChasComBrdM10328SMStore 5 }

-- Model 10324-F EtherCEll Concentrator
s5ChasComBrdM10324F OBJECT IDENTIFIER ::= { s5ChasComMod 302 }
s5ChasComBrdM10324FStore -- Storage areas
    OBJECT IDENTIFIER ::= { s5ChasComBrdM10324F 0 }
s5ChasComBrdM10324FStoreSram -- SRAM
    OBJECT IDENTIFIER ::= { s5ChasComBrdM10324FStore 1 }
s5ChasComBrdM10324FStoreDram -- DRAM
    OBJECT IDENTIFIER ::= { s5ChasComBrdM10324FStore 2 }
s5ChasComBrdM10324FStoreNvram -- NVRAM
    OBJECT IDENTIFIER ::= { s5ChasComBrdM10324FStore 3 }
s5ChasComBrdM10324FStoreEprom -- EPROM
    OBJECT IDENTIFIER ::= { s5ChasComBrdM10324FStore 4 }
s5ChasComBrdM10324FStoreFlash -- FLASH
    OBJECT IDENTIFIER ::= { s5ChasComBrdM10324FStore 5 }

-- Model 5308P Ethernet Host Module
s5ChasComBrdM5308P OBJECT IDENTIFIER ::= { s5ChasComMod 306 }
s5ChasComBrdM5308PStore -- Storage areas
    OBJECT IDENTIFIER ::= { s5ChasComBrdM5308P 0 }
s5ChasComBrdM5308PStore8051Rom -- 8051 Firmware
    OBJECT IDENTIFIER ::= { s5ChasComBrdM5308PStore 1 }

-- Model 5310A Ethernet Network Management Mother Board Module for 5310A/5310SA
s5ChasComBrdM5310ASA OBJECT IDENTIFIER ::= { s5ChasComMod 317 }
s5ChasComBrdM5310ASAStore -- Storage areas
    OBJECT IDENTIFIER ::= { s5ChasComBrdM5310ASA 0 }
s5ChasComBrdM5310ASAStoreBoot -- EPROM Boot Firmware
    OBJECT IDENTIFIER ::= { s5ChasComBrdM5310ASAStore 1 }
s5ChasComBrdM5310ASAStoreFlash -- FLASH Agent Image
    OBJECT IDENTIFIER ::= { s5ChasComBrdM5310ASAStore 2 }
s5ChasComBrdM5310ASAStoreDram -- DRAM Agent Image
    OBJECT IDENTIFIER ::= { s5ChasComBrdM5310ASAStore 3 }

-- Ethernet Management Communications Engine Submodule
s5ChasComBrdSubMMCE OBJECT IDENTIFIER ::= { s5ChasComMod 318 }

-- (Not an external product) 920-370 5740 ATM Backplane Interface
s5ChasComBrdSubM5740AtmBkplIntf
    OBJECT IDENTIFIER ::= { s5ChasComMod 319 }

-- Model 5DN002 Hub 2-Slot Conectivity Motherboard
s5ChasComM5DN002m
    OBJECT IDENTIFIER ::= { s5ChasComMod 342 }
s5ChasComM5DN002mStore -- Storage areas
    OBJECT IDENTIFIER ::= { s5ChasComM5DN002m 0 }
s5ChasComM5DN002mStoreFlash -- FLASH Agent image
    OBJECT IDENTIFIER ::= { s5ChasComM5DN002mStore 1 }
s5ChasComM5DN002mStoreBoot -- Boot Agent Image
    OBJECT IDENTIFIER ::= { s5ChasComM5DN002mStore 2 }

-- Model 5DN003 Hub 3-Slot Conectivity Motherboard
s5ChasComM5DN003m
    OBJECT IDENTIFIER ::= { s5ChasComMod 343 }
s5ChasComM5DN003mStore -- Storage areas
    OBJECT IDENTIFIER ::= { s5ChasComM5DN003m 0 }
s5ChasComM5DN003mStoreFlash -- FLASH Agent image
    OBJECT IDENTIFIER ::= { s5ChasComM5DN003mStore 1 }
s5ChasComM5DN003mStoreBoot -- Boot Agent Image
    OBJECT IDENTIFIER ::= { s5ChasComM5DN003mStore 2 }

-- Model 5DN308P D-Day Hub 12-port RJ-45 10Base-T Module
s5ChasComM5DN308P
    OBJECT IDENTIFIER ::= { s5ChasComMod 344 }

-- Model 5DN304P D-Day Hub 3-port 10Base-FL Fiber Module
s5ChasComM5DN304P
    OBJECT IDENTIFIER ::= { s5ChasComMod 345 }

-- Model 5DN378P-F D-Day Hub 10Base-FL/10Base-T Module
s5ChasComM5DN378P-F
    OBJECT IDENTIFIER ::= { s5ChasComMod 346 }

-- Model 5DN307P D-Day Hub 12-port Telco 10Base-T Module
s5ChasComM5DN307P
    OBJECT IDENTIFIER ::= { s5ChasComMod 347 }

-- Model 5DN310 Ethernet Network Management Module
s5ChasComM5DN310
    OBJECT IDENTIFIER ::= { s5ChasComMod 348 }
s5ChasComM5DN310Store -- Storage areas
    OBJECT IDENTIFIER ::= { s5ChasComM5DN310 0 }
s5ChasComM5DN310StoreBoot -- EPROM Boot Firmware
    OBJECT IDENTIFIER ::= { s5ChasComM5DN310Store 1 }
s5ChasComM5DN310StoreFlash -- FLASH Agent image
    OBJECT IDENTIFIER ::= { s5ChasComM5DN310Store 2 }
s5ChasComM5DN310StoreDram -- DRAM Agent image
    OBJECT IDENTIFIER ::= { s5ChasComM5DN310Store 3 }

-- Model N11 Data Collection Module
s5ChasComMN11
    OBJECT IDENTIFIER ::= { s5ChasComMod 349 }
s5ChasComMN11Store -- Storage areas
    OBJECT IDENTIFIER ::= { s5ChasComMN11 0 }
s5ChasComMN11StoreFlash -- FLASH N11 image
    OBJECT IDENTIFIER ::= { s5ChasComMN11Store 1 }
s5ChasComMN11StoreDram -- DRAM N11 image
    OBJECT IDENTIFIER ::= { s5ChasComMN11Store 2 }

-- BayStack Ethernet Hub 12-Port RJ-45 10Base-T mother board
s5ChasComMNBayStackm1
    OBJECT IDENTIFIER ::= { s5ChasComMod 350}
s5ChasComMNBayStackm1Store -- Storage areas
    OBJECT IDENTIFIER ::= { s5ChasComMNBayStackm1 0 }
s5ChasComMNBayStackm1StoreRom -- ROM Host Firmware
    OBJECT IDENTIFIER ::= { s5ChasComMNBayStackm1Store 1 }

-- BayStack Ethernet Hub 24-Port RJ-45 10Base-T mother board
s5ChasComMNBayStackm2
    OBJECT IDENTIFIER ::= { s5ChasComMod 351}
s5ChasComMNBayStackm2Store -- Storage areas
    OBJECT IDENTIFIER ::= { s5ChasComMNBayStackm2 0 }
s5ChasComMNBayStackm2StoreRom -- ROM Host Firmware
    OBJECT IDENTIFIER ::= { s5ChasComMNBayStackm2Store 1 }

-- BayStack Ethernet Hub AUI Media Adapter
s5ChasComMNBayStackAui
    OBJECT IDENTIFIER ::= { s5ChasComMod 352 }

-- BayStack Ethernet Hub 10Base-2 Media Adapter
s5ChasComMNBayStackThin
    OBJECT IDENTIFIER ::= { s5ChasComMod 353 }

-- BayStack Ethernet Hub 10Base-FL Media Adapter
s5ChasComMNBayStackFL
    OBJECT IDENTIFIER ::= { s5ChasComMod 354 }

-- BayStack Ethernet Hub Standard Ethernet Network Management Module
s5ChasComMNBayStackStdNmm
    OBJECT IDENTIFIER ::= { s5ChasComMod 355 }
s5ChasComMNBayStackStdNmmStore -- Storage areas
    OBJECT IDENTIFIER ::= { s5ChasComMNBayStackStdNmm 0 }
s5ChasComMNBayStackStdnmmStoreBoot -- EPROM Boot Firmware
    OBJECT IDENTIFIER ::= { s5ChasComMNBayStackStdNmmStore 1 }
s5ChasComMNBayStackStdNmmStoreFlash -- FLASH Agent image
    OBJECT IDENTIFIER ::= { s5ChasComMNBayStackStdNmmStore 2 }
s5ChasComMNBayStackStdNmmStoreDram -- DRAM Agent image
    OBJECT IDENTIFIER ::= { s5ChasComMNBayStackStdNmmStore 3 }

-- BayStack Ethernet Hub Advanced Ethernet Network Management Module
s5ChasComMNBayStackAdvNmm
    OBJECT IDENTIFIER ::= { s5ChasComMod 356 }
s5ChasComMNBayStackAdvNmmStore -- Storage areas
    OBJECT IDENTIFIER ::= { s5ChasComMNBayStackAdvNmm 0 }
s5ChasComMNBayStackAdvNmmStoreBoot -- EPROM Boot Firmware
    OBJECT IDENTIFIER ::= { s5ChasComMNBayStackAdvNmmStore 1 }
s5ChasComMNBayStackAdvNmmStoreFlash -- FLASH Agent image
    OBJECT IDENTIFIER ::= { s5ChasComMNBayStackAdvNmmStore 2 }
s5ChasComMNBayStackAdvNmmStoreDram -- DRAM Agent image
    OBJECT IDENTIFIER ::= { s5ChasComMNBayStackAdvNmmStore 3 }

-- Model BayStack Ethernet Hub 10Base-T Media Adapter
s5ChasComMF-10BaseT
    OBJECT IDENTIFIER ::= { s5ChasComMod 357 }

-- Model 58000 1/100 Ethernet Switch Management Module
s5ChasComBrdM58000
    OBJECT IDENTIFIER ::= { s5ChasComMod 359 }
s5ChasComBrdM58000Store -- Storage areas
    OBJECT IDENTIFIER ::= { s5ChasComBrdM58000 0 }
s5ChasComBrdM58000StoreBoot -- EPROM Boot Firmware
    OBJECT IDENTIFIER ::= { s5ChasComBrdM58000Store 1 }
s5ChasComBrdM58000StoreFlash -- FLASH Switch Image
    OBJECT IDENTIFIER ::= { s5ChasComBrdM58000Store 2 }

-- Model 58000-14 2 Port 100BASE-F MDA with SC connectors
s5ChasComBrdSubM5800014
    OBJECT IDENTIFIER ::= { s5ChasComMod 360 }

-- Model 58000-15 2 Port 100BASE-T MDA with RJ45 connectors
s5ChasComBrdSubM5800015
    OBJECT IDENTIFIER ::= { s5ChasComMod 361 }

-- Model 58000-16 2 Port 100BASE-T/100BASE-F MDA with one RJ45 and SC connector
s5ChasComBrdSubM5800016
    OBJECT IDENTIFIER ::= { s5ChasComMod 362 }

-- Model 58000 MDA expansion module for model 58000 Ethernet Switch
s5ChasComBrdSubM58000MdaExp
    OBJECT IDENTIFIER ::= { s5ChasComMod 363 }

-- Model 5DN378P-A D-Day Hub 10Base-AUI/10Base-T Module
s5ChasComM5DN378P-A
    OBJECT IDENTIFIER ::= { s5ChasComMod 364 }

-- Mother Board for BayStack 12 Port 100BAST-T Hub
s5ChasComMBayStack100m1
    OBJECT IDENTIFIER ::= { s5ChasComMod 365 }
s5ChasComMBayStack100m1Store -- Storage areas
    OBJECT IDENTIFIER ::= { s5ChasComMBayStack100m1 0 }
s5ChasComMBayStack100m1StoreRom -- ROM Host Firmware
    OBJECT IDENTIFIER ::= { s5ChasComMBayStack100m1Store 1 }

-- Advanced NMM for BayStack 100BAST-T Hub
s5ChasComMBayStack100Nmm
    OBJECT IDENTIFIER ::= { s5ChasComMod 366 }
s5ChasComMBayStack100NmmStore -- Storage areas
    OBJECT IDENTIFIER ::= { s5ChasComMBayStack100Nmm 0 }
s5ChasComMBayStack100NmmStoreBoot -- EPROM Boot Firmware
    OBJECT IDENTIFIER ::= { s5ChasComMBayStack100NmmStore 1 }
s5ChasComMBayStack100NmmStoreFlash -- FLASH Agent image
    OBJECT IDENTIFIER ::= { s5ChasComMBayStack100NmmStore 2 }
s5ChasComMBayStack100NmmStoreDram -- DRAM Agent image
    OBJECT IDENTIFIER ::= { s5ChasComMBayStack100NmmStore 3 }

-- 100BASE-FX MDA with SC connector for BayStack 100BASE-T Hub
s5ChasComMBayStack100-FxMda
    OBJECT IDENTIFIER ::= { s5ChasComMod 368 }

-- 100BASE-TX MDA with RJ/45 connector for BayStack 100BASE-T Hub
s5ChasComMBayStack100-TxMda
    OBJECT IDENTIFIER ::= { s5ChasComMod 369 }

-- 12 port 100BASE-TX expansion module for BayStack 100BASE-T Hub
s5ChasComMBayStack100-Tx12
    OBJECT IDENTIFIER ::= { s5ChasComMod 371 }

-- D5000 Model 5DN301P 4 port ThinNet module with BNC coax connectors
s5ChasComM5DN301P
    OBJECT IDENTIFIER ::= { s5ChasComMod 372 }

--5000 Model 5307PS-HD Ethernet Host Module (36 Ports with Telco & BaySecure)
s5ChasComBrdM5307PS-HD
    OBJECT IDENTIFIER ::= {s5ChasComMod 373}
s5ChasComBrdM5307PS-HDStore
    OBJECT IDENTIFIER ::= {s5ChasComBrdM5307PS-HD 0}
s5ChasComBrdM5307PS-HDStore8051Rom
    OBJECT IDENTIFIER ::= {s5ChasComBrdM5307PS-HDStore 1}

--5000 Model 5300P Ethernet Host Module with 4 MDA sockets
s5ChasComBrdM5300P
    OBJECT IDENTIFIER ::= {s5ChasComMod 374}
s5ChasComBrdM5300PStore
    OBJECT IDENTIFIER ::= {s5ChasComBrdM5300P 0}
s5ChasComBrdM5300PStore8051Rom
    OBJECT IDENTIFIER ::= {s5ChasComBrdM5300PStore 1}

-- BH/Catapult Modules
s5ChasComMod-5328mEther16PC10BT
    OBJECT IDENTIFIER ::= { s5ChasComMod 375 }
s5ChasComMod-5724mATM4PMMFiber
    OBJECT IDENTIFIER ::= { s5ChasComMod 376 }
s5ChasComMod-5724MmATMMCP4PMMFiber
    OBJECT IDENTIFIER ::= { s5ChasComMod 377 }

s5ChasComMod-5328MmEtherMCP8PC10BT
    OBJECT IDENTIFIER ::= { s5ChasComMod 378 }
s5ChasComMod-5328FXmEther12P2FXP
    OBJECT IDENTIFIER ::= { s5ChasComMod 379 }
-- 5000BH Model 5324 12 port 10Base-FL Ethernet Switching Host
s5ChasComMod-5324mEther12PFL
    OBJECT IDENTIFIER ::= { s5ChasComMod 380 }

s5ChasComMod-5525mTR8PCopper
    OBJECT IDENTIFIER ::= { s5ChasComMod 381 }
s5ChasComMod-5525MmTRMCP4PCopper
    OBJECT IDENTIFIER ::= { s5ChasComMod 382 }
s5ChasComMod-5524mTR8PFiber
    OBJECT IDENTIFIER ::= { s5ChasComMod 383 }
s5ChasComMod-5524MmTR4PFiber
    OBJECT IDENTIFIER ::= { s5ChasComMod 384 }
s5ChasComMod-5924mFDDI1P
    OBJECT IDENTIFIER ::= { s5ChasComMod 385 }
s5ChasComMod-5824mEther4PFX
    OBJECT IDENTIFIER ::= { s5ChasComMod 386 }
s5ChasComMod-5828FmEther2PTX2PFX
    OBJECT IDENTIFIER ::= { s5ChasComMod 387 }
s5ChasComMod-5824MmEtherMCP2PFX
    OBJECT IDENTIFIER ::= { s5ChasComMod 388 }
s5ChasComMod-5724SMmATM4PSMFiber
    OBJECT IDENTIFIER ::= { s5ChasComMod 389 }
s5ChasComMod-5725mATM4PCopper
    OBJECT IDENTIFIER ::= { s5ChasComMod 390 }
s5ChasComMod-5721DS3mATM2P
    OBJECT IDENTIFIER ::= { s5ChasComMod 391 }
s5ChasComMod-5721E3mATM2P
    OBJECT IDENTIFIER ::= { s5ChasComMod 392 }
-- 5380 Ethernet Router Base Module with connections for 4 Enet backplanes and 2 Net Modules
s5ChasComMod-5380E4Bkp2N
    OBJECT IDENTIFIER ::= { s5ChasComMod 395 }
-- 5580 Token Ring Router Base Module with connections for 4 TR backplanes and 2 Net Modules
s5ChasComMod-5380TR4Bkp2N
    OBJECT IDENTIFIER ::= { s5ChasComMod 396 }

-- 5000 Router Dual Ethernet Net Module with 2 AUI/10BASE-T ports
s5ChasComMod-5000ENetD10-T
    OBJECT IDENTIFIER ::= { s5ChasComMod 397 }
-- 5000 Router 100BASE-T Net Module with Single MII/100BASE-TX port
s5ChasComMod-5000ENetS100-T
    OBJECT IDENTIFIER ::= { s5ChasComMod 398 }
-- 5000 Router Dual Token Ring Net Module with 2 Token Ring DB-9 ports
s5ChasComMod-5000TRNetD-DB9
    OBJECT IDENTIFIER ::= { s5ChasComMod 399 }
-- 5000 Router Multi Mode FDDI Net Module with one DAS port with MIC connectors
s5ChasComMod-5000MMFibNetD-DASMIC
    OBJECT IDENTIFIER ::= { s5ChasComMod 400 }
-- 5000 Router Single Mode FDDI Net Module with one DAS port with MIC connectors
s5ChasComMod-5000SMFibNetS-DASMIC
    OBJECT IDENTIFIER ::= { s5ChasComMod 401 }
-- 5000 Router Single/Multi Mode FDDI Net Module with one DAS port with MIC connectors
s5ChasComMod-5000SMMMFibNetS-DASMIC
    OBJECT IDENTIFIER ::= { s5ChasComMod 402 }
-- 5000 Router Multi/Single Mode FDDI Net Module with one DAS port with MIC connectors
s5ChasComMod-5000MMSMFibNetS-DASMIC
    OBJECT IDENTIFIER ::= { s5ChasComMod 403 }
-- 5000 Router Dual Sync Net Module with 2 Sync WAN ports through two 44-pin connectors
s5ChasComMod-5000SynNetD-WAN44
    OBJECT IDENTIFIER ::= { s5ChasComMod 404 }
-- 5000 Router Quad BRI Net Module with four 8 pin modular ISDN BRI ports
s5ChasComMod-5000SynNetQ-ISDNBRI8
    OBJECT IDENTIFIER ::= { s5ChasComMod 405 }
-- 5000 Router MCE1 Net Module with one Multi-Channel 75/120 Ohm E1 port
s5ChasComMod-5000MCE1NetQ-75120
    OBJECT IDENTIFIER ::= { s5ChasComMod 406 }
-- 5000 Router MCT1 Net Module with one Multi-Channel RJ-48C T1 port
s5ChasComMod-5000MCT1NetQ-RJ48C
    OBJECT IDENTIFIER ::= { s5ChasComMod 407 }
-- 5000 Router Quad Sync Net Module with four 50 pin connectors
s5ChasComMod-5000SynNet4-50Pin
    OBJECT IDENTIFIER ::= { s5ChasComMod 408 }
-- 5000 Router Compression Co-Processor Module, occupying 1 net module location
s5ChasComMod-5000Co-Processor
    OBJECT IDENTIFIER ::= { s5ChasComMod 409 }
-- 5000 Router Multi Mode 155M OC3 ATM Net Module with one SC port
s5ChasComMod-5000ATMNet1-MMOC3
    OBJECT IDENTIFIER ::= { s5ChasComMod 410 }
-- 5000 Router Single Mode 155M OC3 ATM Net Module with one SC port
s5ChasComMod-5000ATMNet1-SMOC3
    OBJECT IDENTIFIER ::= { s5ChasComMod 411 }
-- 5000 Router DS3 ATM Net Module with one DS3 ATM port
s5ChasComMod-5000ATMNet1-DS3
    OBJECT IDENTIFIER ::= { s5ChasComMod 412 }
-- 5000 Router E3 ATM Net Module with one E3 ATM port
s5ChasComMod-5000ATMNet1-E3
    OBJECT IDENTIFIER ::= { s5ChasComMod 413 }
-- Model 58000-109 2 port FDDI MDA with MIC Connectors
s5ChasComBrdSubM58000Fddi
    OBJECT IDENTIFIER ::= { s5ChasComMod 414 }

-- Model 28200 10/100 Ethernet Switch Mother board and Backplane
s5ChasComBrdM28200
    OBJECT IDENTIFIER ::= { s5ChasComMod 415 }
s5ChasComBrdM28200Store -- Storage Areas
    OBJECT IDENTIFIER ::= { s5ChasComBrdM28200 0 }
s5ChasComBrdM28200StoreBoot -- EPROM Boot Firmware
    OBJECT IDENTIFIER ::= { s5ChasComBrdM28200Store 1 }
s5ChasComBrdM28200StoreFlash -- Flash Switch Image
    OBJECT IDENTIFIER ::= { s5ChasComBrdM28200Store 2 }
s5ChasComBrdM28200StoreDram -- DRAM Switch Image
    OBJECT IDENTIFIER ::= { s5ChasComBrdM28200Store 3 }

-- Model 28200-15 8 port 10 Base-T MDA with RJ45 Connectors
s5ChasComBrdSubM2820015
    OBJECT IDENTIFIER ::= { s5ChasComMod 416 }

-- Model 28200-14 4 port 10 Base-FL MDA with ST Connectors
s5ChasComBrdSubM2820014
    OBJECT IDENTIFIER ::= { s5ChasComMod 417 }

-- Model 28200-105 2 port 100 Base-TX MDA with RJ45 Connectors
s5ChasComBrdSubM28200105
    OBJECT IDENTIFIER ::= { s5ChasComMod 418 }

-- Model 28200-104 2 port 100 Base-FX MDA with SC Connectors
s5ChasComBrdSubM28200104
    OBJECT IDENTIFIER ::= { s5ChasComMod 419 }

-- Model 28200-106 2 port MDA with one100 Base-TX RJ45 port
-- and one 100Base-FX SC port
s5ChasComBrdSubM28200106
    OBJECT IDENTIFIER ::= { s5ChasComMod 420 }

-- Model 28200-EXP 2 port expansion MDA for Bay Networks
-- proprietary trunk connection.
s5ChasComBrdSubM28200Exp
    OBJECT IDENTIFIER ::= { s5ChasComMod 421 }

-- Model 28200-724 Single port ATM 155Mb MMF OC3 MDA with MIC connectors
s5ChasComBrdSubM28200Atm
    OBJECT IDENTIFIER ::= { s5ChasComMod 422 }

-- Model 28200-109 2 port FDDI MDA
-- with MIC Connectors
s5ChasComBrdSubM28200Fddi
    OBJECT IDENTIFIER ::= { s5ChasComMod 423 }

-- Model 28200-N11 10Mb Data Collection Module
s5ChasComBrdSubM28200N11
    OBJECT IDENTIFIER ::= { s5ChasComMod 424 }

-- Model 28200-N111 10/100Mb Data Collection Module
s5ChasComBrdSubM28200N111
    OBJECT IDENTIFIER ::= { s5ChasComMod 425 }

-- Centillion Component Modules
s5ChasComMod-c100mTR4PC
    OBJECT IDENTIFIER ::= { s5ChasComMod 426 }
s5ChasComMod-c100mTRMCP4PC
    OBJECT IDENTIFIER ::= { s5ChasComMod 427 }
s5ChasComMod-c100mATM
    OBJECT IDENTIFIER ::= { s5ChasComMod 428 }
s5ChasComMod-c100mTRFiber
    OBJECT IDENTIFIER ::= { s5ChasComMod 429 }
s5ChasComMod-c100mTRMCPFiber
    OBJECT IDENTIFIER ::= { s5ChasComMod 430 }
s5ChasComMod-c100mEther16PC10BT
    OBJECT IDENTIFIER ::= { s5ChasComMod 431 }
s5ChasComMod-c100mEtherMCP8PC10BT
    OBJECT IDENTIFIER ::= { s5ChasComMod 432 }
s5ChasComMod-c100mATM2PSMFiber
    OBJECT IDENTIFIER ::= { s5ChasComMod 433 }
s5ChasComMod-c100mATM2PCopper
    OBJECT IDENTIFIER ::= { s5ChasComMod 434 }
s5ChasComMod-c100mATM4PMMFiber
    OBJECT IDENTIFIER ::= { s5ChasComMod 435 }
s5ChasComMod-c100mATM4PSMFiber
    OBJECT IDENTIFIER ::= { s5ChasComMod 436 }
s5ChasComMod-c100mATM4PCopper
    OBJECT IDENTIFIER ::= { s5ChasComMod 437 }
s5ChasComMod-c100mATMMCP2PSMFiber
    OBJECT IDENTIFIER ::= { s5ChasComMod 438 }
s5ChasComMod-c100mATMMCP2PMMFiber
    OBJECT IDENTIFIER ::= { s5ChasComMod 439 }
s5ChasComMod-c100mATMMCP2PCopper
    OBJECT IDENTIFIER ::= { s5ChasComMod 440 }
s5ChasComMod-c100mATMMCP4PSMFiber
    OBJECT IDENTIFIER ::= { s5ChasComMod 441 }
s5ChasComMod-c100mATMMCP4PMMFiber
    OBJECT IDENTIFIER ::= { s5ChasComMod 442 }
s5ChasComMod-c100mATMMCP4PCopper
    OBJECT IDENTIFIER ::= { s5ChasComMod 443 }
s5ChasComMod-c100mATM2PC
    OBJECT IDENTIFIER ::= { s5ChasComMod 444 }
s5ChasComMod-c100mATM4PC
    OBJECT IDENTIFIER ::= { s5ChasComMod 445 }
s5ChasComMod-c100mATMMCP2PC
    OBJECT IDENTIFIER ::= { s5ChasComMod 446 }
s5ChasComMod-c100mATMMCP4PC
    OBJECT IDENTIFIER ::= { s5ChasComMod 447 }

--5300P Model Dummy OID No Media Adapter Fitted
s5ChasComBrdSubDummy
    OBJECT IDENTIFIER ::= { s5ChasComMod 448 }
--5300P Model 5300-T 10BASE-T Media Adapter
s5ChasComBrdSub5300-T
    OBJECT IDENTIFIER ::= { s5ChasComMod 449 }
--5300P Model 5300-A AUI Media Adapter (Female)
s5ChasComBrdSub5300-A
    OBJECT IDENTIFIER ::= { s5ChasComMod 450 }
--5300P Model 5300-D Male AUI Media Adapter
s5ChasComBrdSub5300-D
    OBJECT IDENTIFIER ::= { s5ChasComMod 451 }
--5300P Model 5300-F 10BASE-F Media Adapter
s5ChasComBrdSub5300-F
    OBJECT IDENTIFIER ::= { s5ChasComMod 452 }
--5300P Model 5300-S Single Mode Fiber Media Adapter
s5ChasComBrdSub5300-S
    OBJECT IDENTIFIER ::= { s5ChasComMod 453 }
--5300P Model 5300-2 10BASE-2 Thinnet Media Adapter
s5ChasComBrdSub5300-2
    OBJECT IDENTIFIER ::= { s5ChasComMod 454 }

-- BayStack Token Ring Hub 24 port Motherboard
s5ChasComMBayStackTrm1
    OBJECT IDENTIFIER ::= { s5ChasComMod 456 }
s5ChasComMBayStackTrm1Store -- Storage areas
    OBJECT IDENTIFIER ::= { s5ChasComMBayStackTrm1 0 }
s5ChasComMBayStackTrm1StoreFlash -- FLASH Agent Image
    OBJECT IDENTIFIER ::= { s5ChasComMBayStackTrm1Store 1 }
s5ChasComMBayStackTrm1StoreBoot -- BOOT Agent Image
    OBJECT IDENTIFIER ::= { s5ChasComMBayStackTrm1Store 2 }

-- BayStack Token Ring Network Management Module
s5ChasComMBayStackTrNmm
    OBJECT IDENTIFIER ::= { s5ChasComMod 457 }
s5ChasComMBayStackTrNmmStore -- storage areas
    OBJECT IDENTIFIER ::= { s5ChasComMBayStackTrNmm 0 }
s5ChasComMBayStackTrNmmStoreBoot -- EPROM Boot Firmware
    OBJECT IDENTIFIER ::= { s5ChasComMBayStackTrNmmStore 1 }
s5ChasComMBayStackTrNmmStoreFlash -- FLASH Agent image
    OBJECT IDENTIFIER ::= { s5ChasComMBayStackTrNmmStore 2 }
s5ChasComMBayStackTrNmmStoreDram -- DRAM Agent image
    OBJECT IDENTIFIER ::= { s5ChasComMBayStackTrNmmStore 3 }

-- BayStack Token Ring Hub Fiber MDA module
s5ChasComMBayStackTrMDAFiber
    OBJECT IDENTIFIER ::= { s5ChasComMod 458 }

-- BayStack Token Ring Hub Copper MDA module
s5ChasComMBayStackTrMDACopper
    OBJECT IDENTIFIER ::= { s5ChasComMod 459 }

-- BayStack Token Ring Hub DCM module
s5ChasComMBayStackTrDCM
    OBJECT IDENTIFIER ::= { s5ChasComMod 460 }

-- BayStack Token Ring Hub Multi-Ring module
s5ChasComMBayStackTrMRM
    OBJECT IDENTIFIER ::= { s5ChasComMod 461 }

-- BayStack Ethernet Hub 24-port Telco 10Base-T motherboard
s5ChasComMNBayStackm3
    OBJECT IDENTIFIER ::= { s5ChasComMod 462 }
s5ChasComMNBayStackm3Store -- Storage areas
    OBJECT IDENTIFIER ::= { s5ChasComMNBayStackm3 0 }
s5ChasComMNBayStackm3StoreRom -- ROM Host Firmware
    OBJECT IDENTIFIER ::= { s5ChasComMNBayStackm3Store 1 }

-- BayStack Ethernet Hub 8 port 10Base-2 motherboard
s5ChasComMNBayStackm4
    OBJECT IDENTIFIER ::= { s5ChasComMod 463 }
s5ChasComMNBayStackm4Store -- Storage areas
    OBJECT IDENTIFIER ::= { s5ChasComMNBayStackm4 0 }
s5ChasComMNBayStackm4StoreRom -- ROM Host Firmware
    OBJECT IDENTIFIER ::= { s5ChasComMNBayStackm4Store 1 }

-- BayStack Ethernet Hub Redundant Link Capable 10Base-FL Media Adapter
s5ChasComMNBayStackRedFL
    OBJECT IDENTIFIER ::= { s5ChasComMod 464 }

-- BayStack Ethernet Hub Single Mode Fiber Media Adapter
s5ChasComMNBayStackSMFL
    OBJECT IDENTIFIER ::= {s5ChasComMod 465 }

-- BayStack Ethernet Hub Redundant-Link Capable Single Mode Fiber Media Adapter
s5ChasComMNBayStackSMRedFL
    OBJECT IDENTIFIER ::= {s5ChasComMod 466 }

--5000 Model 5308S Ethernet Host Module with BaySecure
s5ChasComBrdM5308S
    OBJECT IDENTIFIER ::= {s5ChasComMod 467}
s5ChasComBrdM5308SStore
    OBJECT IDENTIFIER ::= {s5ChasComBrdM5308S 0}
s5ChasComBrdM5308SStore8051Rom
    OBJECT IDENTIFIER ::= {s5ChasComBrdM5308SStore 1}

--5000 Model 5307S Ethernet Host Module with BaySecure
s5ChasComBrdM5307S
    OBJECT IDENTIFIER ::= {s5ChasComMod 468}
s5ChasComBrdM5307SStore
    OBJECT IDENTIFIER ::= {s5ChasComBrdM5307S 0}
s5ChasComBrdM5307SStore8051Rom
    OBJECT IDENTIFIER ::= {s5ChasComBrdM5307SStore 1}

--5000 Model 5308PS Ethernet Host Module with BaySecure
s5ChasComBrdM5308PS
    OBJECT IDENTIFIER ::= {s5ChasComMod 469}
s5ChasComBrdM5308PSStore
    OBJECT IDENTIFIER ::= {s5ChasComBrdM5308PS 0}
s5ChasComBrdM5308PSStore8051Rom
    OBJECT IDENTIFIER ::= {s5ChasComBrdM5308PSStore 1}

--5000 Model 5307PS Ethernet Host Module with BaySecure
s5ChasComBrdM5307PS
    OBJECT IDENTIFIER ::= {s5ChasComMod 470}
s5ChasComBrdM5307PSStore
    OBJECT IDENTIFIER ::= {s5ChasComBrdM5307PS 0}
s5ChasComBrdM5307PSStore8051Rom
    OBJECT IDENTIFIER ::= {s5ChasComBrdM5307PSStore 1}

-- Model 5DN308PS D5000 Ethernet Host MDA with BaySecure
s5ChasComM5DN308PS
    OBJECT IDENTIFIER ::= { s5ChasComMod 471 }

-- Model 5DN307PS D5000 Ethernet Host MDA with BaySecure
s5ChasComM5DN307PS
    OBJECT IDENTIFIER ::= { s5ChasComMod 472 }

-- Model 5DN378P-SM D5000 Ethernet Host MDA with BaySecure
s5ChasComM5DN378P-SM
    OBJECT IDENTIFIER ::= { s5ChasComMod 473 }

-- BayStack Ethernet Hub 6 port 10BaseFL motherboard
s5ChasComMNBayStackm5
    OBJECT IDENTIFIER ::= {s5ChasComMod 477}
s5ChasComMNBayStackm5Store -- Storage areas
    OBJECT IDENTIFIER ::= {s5ChasComMNBayStackm5 0 }
s5ChasComMNBayStackm5StoreRom -- ROM Host Firmware
    OBJECT IDENTIFIER ::= {s5ChasComMNBayStackm5Store 1 }

-- BayStack 301 Ethernet Switch
s5ChasComMBayStack301
    OBJECT IDENTIFIER ::= { s5ChasComMod 478 }
s5ChasComMBayStack301Store
    OBJECT IDENTIFIER ::= { s5ChasComMBayStack301 0 }
s5ChasComMBayStack301MaxRAM
    OBJECT IDENTIFIER ::= { s5ChasComMBayStack301Store 1 }
s5ChasComMBayStack301InstalledRAM
    OBJECT IDENTIFIER ::= { s5ChasComMBayStack301Store 2 }
s5ChasComMBayStack301Flash
    OBJECT IDENTIFIER ::= { s5ChasComMBayStack301Store 3 }

-- Model 5DN003A Hub 3-Slot Connectivity Motherboard
-- with Temperature Sensor
s5ChasComM5DN003Am
    OBJECT IDENTIFIER ::= { s5ChasComMod 485 }
s5ChasComM5DN003AmStore -- Storage areas
    OBJECT IDENTIFIER ::= { s5ChasComM5DN003Am 0 }
s5ChasComM5DN003AmStoreFlash -- FLASH Agent image
    OBJECT IDENTIFIER ::= { s5ChasComM5DN003AmStore 1 }
s5ChasComM5DN003AmStoreBoot -- Boot Agent Image
    OBJECT IDENTIFIER ::= { s5ChasComM5DN003AmStore 2 }

-- Model 5DN002A Hub 2-Slot Connectivity Motherboard
-- with Temperature Sensor
s5ChasComM5DN002Am
    OBJECT IDENTIFIER ::= { s5ChasComMod 486 }
s5ChasComM5DN002AmStore -- Storage areas
    OBJECT IDENTIFIER ::= { s5ChasComM5DN002Am 0 }
s5ChasComM5DN002AmStoreFlash -- FLASH Agent image
    OBJECT IDENTIFIER ::= { s5ChasComM5DN002AmStore 1 }
s5ChasComM5DN002AmStoreBoot -- Boot Agent Image
    OBJECT IDENTIFIER ::= { s5ChasComM5DN002AmStore 2 }

-- 5000 Model 5405 Fast Ethernet Host Module
s5ChasComBrdM5405
    OBJECT IDENTIFIER ::= { s5ChasComMod 500 }
s5ChasComBrdM5405Store -- Storage areas
    OBJECT IDENTIFIER ::= { s5ChasComBrdM5405 0 }
s5ChasComBrdM5405StoreBoot -- EPROM Boot Firmware
    OBJECT IDENTIFIER ::= { s5ChasComBrdM5405Store 1 }
s5ChasComBrdM5405StoreFlash -- FLASH Host Firmware Image
    OBJECT IDENTIFIER ::= { s5ChasComBrdM5405Store 2 }
s5ChasComBrdM5405StoreDram -- DRAM Host Image
    OBJECT IDENTIFIER ::= { s5ChasComBrdM5405Store 3 }

-- 5000 Model 5475-FX Fast Ethernet Host Module
s5ChasComBrdM5475FX
    OBJECT IDENTIFIER ::= { s5ChasComMod 501 }
s5ChasComBrdM5475FXStore -- Storage areas
    OBJECT IDENTIFIER ::= { s5ChasComBrdM5475FX 0 }
s5ChasComBrdM5475FXStoreBoot -- EPROM Boot Firmware
    OBJECT IDENTIFIER ::= { s5ChasComBrdM5475FXStore 1 }
s5ChasComBrdM5475FXStoreFlash -- FLASH Host Firmware Image
    OBJECT IDENTIFIER ::= { s5ChasComBrdM5475FXStore 2 }
s5ChasComBrdM5475FXStoreDram -- DRAM Host Image
    OBJECT IDENTIFIER ::= { s5ChasComBrdM5475FXStore 3 }

s5ChasComMod-c100mEther12P2FXP
    OBJECT IDENTIFIER ::= { s5ChasComMod 507}
s5ChasComMod-c100mEther14P2TXP
    OBJECT IDENTIFIER ::= { s5ChasComMod 508}

--Model 5605P Fast Ethernet Host Module
s5ChasComBrdM5605P
    OBJECT IDENTIFIER ::= { s5ChasComMod 510 }
s5ChasComBrdM5605PStore -- Storage areas
    OBJECT IDENTIFIER ::= { s5ChasComBrdM5605P 0 }
s5ChasComBrdM5605PStoreBoot -- Boot Firmware
    OBJECT IDENTIFIER ::= { s5ChasComBrdM5605PStore 1 }
s5ChasComBrdM5605PStoreFlash -- Flash Host Firmware
    OBJECT IDENTIFIER ::= { s5ChasComBrdM5605PStore 2 }
s5ChasComBrdM5605PStoreDram -- DRAM Host Firmware
    OBJECT IDENTIFIER ::= { s5ChasComBrdM5605PStore 3 }

-- Model 5675P-FX Fast Ethernet Host Module
s5ChasComBrdM5675PFX
    OBJECT IDENTIFIER ::= { s5ChasComMod 511 }
s5ChasComBrdM5675PFXStore -- Storage areas
    OBJECT IDENTIFIER ::= { s5ChasComBrdM5675PFX 0 }
s5ChasComBrdM5675PFXStoreBoot -- Boot Firmware
    OBJECT IDENTIFIER ::= { s5ChasComBrdM5675PFXStore 1 }
s5ChasComBrdM5675PFXStoreFlash -- Flash Host Firmware
    OBJECT IDENTIFIER ::= { s5ChasComBrdM5675PFXStore 2 }
s5ChasComBrdM5675PFXStoreDram -- DRAM Host Firmware
    OBJECT IDENTIFIER ::= { s5ChasComBrdM5675PFXStore 3 }

-- Model 5616 Fast Ethernet Network Management Module
s5ChasComBrdM5616
    OBJECT IDENTIFIER ::= { s5ChasComMod 512 }
s5ChasComBrdM5616Store -- Storage areas
    OBJECT IDENTIFIER ::= { s5ChasComBrdM5616 0 }
s5ChasComBrdM5616StoreBoot -- FLASH Boot Firmware
    OBJECT IDENTIFIER ::= { s5ChasComBrdM5616 1 }
s5ChasComBrdM5616StoreFlash -- FLASH Agent image
    OBJECT IDENTIFIER ::= { s5ChasComBrdM5616Store 2 }
s5ChasComBrdM5616StoreDram -- DRAM Agent image
    OBJECT IDENTIFIER ::= { s5ChasComBrdM5616Store 3 }

-- Model 5316 Ethernet Network Management Module
s5ChasComBrdM5316
    OBJECT IDENTIFIER ::= { s5ChasComMod 513 }
s5ChasComBrdM5316Store -- Storage areas
    OBJECT IDENTIFIER ::= { s5ChasComBrdM5316 0 }
s5ChasComBrdM5316StoreBoot -- FLASH Boot Firmware
    OBJECT IDENTIFIER ::= { s5ChasComBrdM5316 1 }
s5ChasComBrdM5316StoreFlash -- FLASH Agent image
    OBJECT IDENTIFIER ::= { s5ChasComBrdM5316Store 2 }
s5ChasComBrdM5316StoreDram -- DRAM Agent image
    OBJECT IDENTIFIER ::= { s5ChasComBrdM5316Store 3 }

-- 100Base-FX MDA for 3308S Desktop Switching Host
s5ChasComM3308S-FxMda
    OBJECT IDENTIFIER ::= { s5ChasComMod 514 }

-- BayStack302T Board (or slots) group
s5ChasComBrdBayStack302T
    OBJECT IDENTIFIER ::= { s5ChasComMod 515 }
s5ChasComBrdBayStack302TStore -- Storage areas
    OBJECT IDENTIFIER ::= { s5ChasComBrdBayStack302T 0 }
s5ChasComBrdBayStack302TFlash -- FLASH image storage
    OBJECT IDENTIFIER ::= { s5ChasComBrdBayStack302TStore 1 }
s5ChasComBrdBayStack302TDram -- DRAM image storage
    OBJECT IDENTIFIER ::= { s5ChasComBrdBayStack302TStore 2 }

-- BayStack302F Board (or slots) group
s5ChasComBrdBayStack302F
    OBJECT IDENTIFIER ::= { s5ChasComMod 516 }
s5ChasComBrdBayStack302FStore -- Storage areas
    OBJECT IDENTIFIER ::= { s5ChasComBrdBayStack302F 0 }
s5ChasComBrdBayStack302FFlash -- FLASH image storage
    OBJECT IDENTIFIER ::= { s5ChasComBrdBayStack302FStore 1 }
s5ChasComBrdBayStack302FDram -- DRAM image storage
    OBJECT IDENTIFIER ::= { s5ChasComBrdBayStack302FStore 2 }

--C100 8Port 10 Base FL switching Module
s5ChasComMod-c100mEther8P10FL
    OBJECT IDENTIFIER ::= { s5ChasComMod 517}

--C100 14 port 12x10BT/2x100BT Fiber
s5ChasComMod-c100mEther12P2BTP
    OBJECT IDENTIFIER ::= { s5ChasComMod 518}

--C100 4 port 100BT Enet slave card
s5ChasComMod-c100mEther4P100BT
    OBJECT IDENTIFIER ::= { s5ChasComMod 519}

-- 5000BH Model 5425 4 port 100 Base TX Ethernet Switching Host Module
s5ChasComMod-5425mEther4PC100BT
    OBJECT IDENTIFIER ::= { s5ChasComMod 520 }

--C100 8/2 ethernet combo card (8 port 10BT, 2 port 100TX)
s5ChasComMod-c100mEther8P2TXP
    OBJECT IDENTIFIER ::= { s5ChasComMod 527 }

-- BayStack350 Switch Board (or slots) group
s5ChasComBrdBayStack350T
    OBJECT IDENTIFIER ::= { s5ChasComMod 528 }
s5ChasComBrdBayStack350TStore -- Storage areas
    OBJECT IDENTIFIER ::= { s5ChasComBrdBayStack350T 0 }
s5ChasComBrdBayStack350TFlash -- Flash image storage
    OBJECT IDENTIFIER ::= { s5ChasComBrdBayStack350TStore 1 }
s5ChasComBrdBayStack350TBootFW -- Boot Firmware storage
    OBJECT IDENTIFIER ::= { s5ChasComBrdBayStack350TStore 2 }
s5ChasComBrdBayStack350TDram -- DRAM storage
    OBJECT IDENTIFIER ::= { s5ChasComBrdBayStack350TStore 3 }

s5ChasComBrdBayStack350F
    OBJECT IDENTIFIER ::= { s5ChasComMod 529 }
s5ChasComBrdBayStack350FStore -- Storage areas
    OBJECT IDENTIFIER ::= { s5ChasComBrdBayStack350F 0 }
s5ChasComBrdBayStack350FFlash -- Flash image storage
    OBJECT IDENTIFIER ::= { s5ChasComBrdBayStack350FStore 1 }
s5ChasComBrdBayStack350FBootFW -- Boot Firmware storage
    OBJECT IDENTIFIER ::= { s5ChasComBrdBayStack350FStore 2 }
s5ChasComBrdBayStack350FDram -- DRAM storage
    OBJECT IDENTIFIER ::= { s5ChasComBrdBayStack350FStore 3 }

s5ChasComBrdBayStack350FHD
    OBJECT IDENTIFIER ::= { s5ChasComMod 530 }
s5ChasComBrdBayStack350FHDStore -- Storage areas
    OBJECT IDENTIFIER ::= { s5ChasComBrdBayStack350FHD 0 }
s5ChasComBrdBayStack350FHDFlash -- Flash image storage
    OBJECT IDENTIFIER ::= { s5ChasComBrdBayStack350FHDStore 1 }
s5ChasComBrdBayStack350FHDBootFW -- Boot Firmware storage
    OBJECT IDENTIFIER ::= { s5ChasComBrdBayStack350FHDStore 2 }
s5ChasComBrdBayStack350FHDDram -- DRAM storage
    OBJECT IDENTIFIER ::= { s5ChasComBrdBayStack350FHDStore 3 }

s5ChasComBrdBayStack350THD
    OBJECT IDENTIFIER ::= { s5ChasComMod 531 }
s5ChasComBrdBayStack350THDStore -- Storage areas
    OBJECT IDENTIFIER ::= { s5ChasComBrdBayStack350THD 0 }
s5ChasComBrdBayStack350THDFlash -- Flash image storage
    OBJECT IDENTIFIER ::= { s5ChasComBrdBayStack350THDStore 1 }
s5ChasComBrdBayStack350THDBootFW -- Boot Firmware storage
    OBJECT IDENTIFIER ::= { s5ChasComBrdBayStack350THDStore 2 }
s5ChasComBrdBayStack350THDDram -- DRAM storage
    OBJECT IDENTIFIER ::= { s5ChasComBrdBayStack350THDStore 3 }

-- 5000BH module 5724M/SM 4 port SMF ATM MCP
s5ChasComMod-5724M-SMmATMMCP4PSMFiber
    OBJECT IDENTIFIER ::= { s5ChasComMod 533 }

-- Switch Node Component Modules
-- Switch Node 16 Port 10BASET Switch Net Module
s5ChasComMod-SwNode10t16
    OBJECT IDENTIFIER ::= { s5ChasComMod 534 }

-- Switch Node 2 port 100BASET Switch Net Module
s5ChasComMod-SwNode100tx2
    OBJECT IDENTIFIER ::= { s5ChasComMod 535 }

-- Switch Node 8 port 10 Meg Fiber Switch Net Module
s5ChasComMod-SwNode10f8
    OBJECT IDENTIFIER ::= { s5ChasComMod 536 }

-- Switch Node 16 port 100BASET Switch Net Module
s5ChasComMod-SwNode100tx16
    OBJECT IDENTIFIER ::= { s5ChasComMod 537 }

-- Switch Node 3 port 100 Meg Fiber Switch Net Module
s5ChasComMod-SwNode100fx3
    OBJECT IDENTIFIER ::= { s5ChasComMod 541 }

-- Switch Node DCM module
s5ChasComDCMX220SwNode
    OBJECT IDENTIFIER ::= { s5ChasComMod 542 }

-- C100 16 port 4x4 100 Base TX Ethernet Bank Switching Host Module
s5ChasComMod-c100mEther4x4P100BT
    OBJECT IDENTIFIER ::= { s5ChasComMod 544 }

-- C100 4 port 100FX Ethernet Switching Host Module
s5ChasComMod-c100mEther4P100FX
    OBJECT IDENTIFIER ::= { s5ChasComMod 545 }

s5ChasComBrdBayStack150 -- BayStack150 24 port Master Unit Repeater Brd
    OBJECT IDENTIFIER ::= { s5ChasComMod 546 }

s5ChasComBrdBayStack152 -- BayStack150 12 port Master Unit Repeater Brd
    OBJECT IDENTIFIER ::= { s5ChasComMod 547 }

s5ChasComBrdBayStack151 -- BayStack150 24 port Slave Unit Repeater Brd
    OBJECT IDENTIFIER ::= { s5ChasComMod 548 }

s5ChasComBrdBayStack153 -- BayStack150 12 port Slave Unit Repeater Brd
    OBJECT IDENTIFIER ::= { s5ChasComMod 549 }

s5ChasComBrdBayStack150NMM -- BayStack150 NMM in the Master unit
    OBJECT IDENTIFIER ::= { s5ChasComMod 550 }
s5ChasComBrdBayStack150NMMStore -- storage areas
    OBJECT IDENTIFIER ::= { s5ChasComBrdBayStack150NMM 0 }
s5ChasComBrdBayStack150NMMStoreBoot -- EPROM Boot Firmware
    OBJECT IDENTIFIER ::= { s5ChasComBrdBayStack150NMMStore 1 }
s5ChasComBrdBayStack150NMMStoreFlash -- FLASH Agent image
    OBJECT IDENTIFIER ::= { s5ChasComBrdBayStack150NMMStore 2 }
s5ChasComBrdBayStack150NMMStoreDram -- DRAM Agent image
    OBJECT IDENTIFIER ::= { s5ChasComBrdBayStack150NMMStore 3 }

-- BayStack150 Expansion Module on NMM
s5ChasComBrdBayStack150NMMExpMod
    OBJECT IDENTIFIER ::= { s5ChasComMod 551 }

-- C100 ATMSpeed MDA Switch Host Module
s5ChasComMod-C100ATMMDAhost
    OBJECT IDENTIFIER ::= { s5ChasComMod 552 }
-- C100 ATMSpeed MDA MCP Module
s5ChasComMod-C100ATMMDAMcp
    OBJECT IDENTIFIER ::= { s5ChasComMod 553 }
-- 5720 ATM MDA switch host module
s5ChasComMod-5720ATMMDAhost
    OBJECT IDENTIFIER ::= { s5ChasComMod 554 }
-- 5720M ATM MDA MCP module
s5ChasComMod-5720MATMMDAMcp
    OBJECT IDENTIFIER ::= { s5ChasComMod 555 }
-- 5720-14 Multimode fiber MDA
s5ChasComMod-5720-14MultiModeMda
    OBJECT IDENTIFIER ::= { s5ChasComMod 556 }
-- 5720-15 Unshielded twisted pair MDA
s5ChasComMod-5720-15UTPMda
    OBJECT IDENTIFIER ::= { s5ChasComMod 557 }
-- 5720-17 Singlemode Fiber MDA
s5ChasComMod-5720-17SingleModeMda
    OBJECT IDENTIFIER ::= { s5ChasComMod 558 }
-- 5720-31 DS3 MDA 980-714-B
s5ChasComMod-5720-31DS3Mda
    OBJECT IDENTIFIER ::= { s5ChasComMod 559 }
-- 5720-41 E3 MDA 980-797-A
s5ChasComMod-5720-41E3Mda
    OBJECT IDENTIFIER ::= { s5ChasComMod 560 }

-- Switch Node CPU Module
s5ChasComMod-SwNodeCPU
    OBJECT IDENTIFIER ::= { s5ChasComMod 561 }

-- 8 Port UTP TokenSpeed MCP for the C100
s5ChasComMod-c1008PUTPTRMcp
    OBJECT IDENTIFIER ::= { s5ChasComMod 562 }
-- 8 Port UTP TokenSpeed Switch Host Module for the C100
s5ChasComMod-c1008PUTPTR
    OBJECT IDENTIFIER ::= { s5ChasComMod 563 }

-- Model 5328-HD Ethernet 24 Port 10Base-T Switch Host Module
s5ChasComBrdM5328-HD
    OBJECT IDENTIFIER ::= { s5ChasComMod 564 }
s5ChasComBrdM5328-HDStore -- storage areas
    OBJECT IDENTIFIER ::= { s5ChasComBrdM5328-HD 0 }
s5ChasComBrdM5328-HDStoreFlash -- FLASH Agent image
    OBJECT IDENTIFIER ::= { s5ChasComBrdM5328-HDStore 1 }
s5ChasComBrdM5328-HDStoreDram -- DRAM Agent image
    OBJECT IDENTIFIER ::= { s5ChasComBrdM5328-HDStore 2 }

-- 5000BH Model 5625 24 port 10/100 Ethernet Copper Switch Host
s5ChasComBrdM5625
    OBJECT IDENTIFIER ::= { s5ChasComMod 565 }

-- Model 5455 Ethernet 16 port 4 * 4 100BASE-TX Bank Switch Net Module
s5ChasComBrdM5455
    OBJECT IDENTIFIER ::= { s5ChasComMod 568 }
s5ChasComBrdM5455Store -- storage areas
    OBJECT IDENTIFIER ::= { s5ChasComBrdM5455 0 }
s5ChasComBrdM5455StoreFlash -- FLASH Agent image
    OBJECT IDENTIFIER ::= { s5ChasComBrdM5455Store 1 }
s5ChasComBrdM5455StoreDram -- DRAM Agent image
    OBJECT IDENTIFIER ::= { s5ChasComBrdM5455Store 2 }

-- Model 5611-DCM Data Collection Module for 5616SA
s5ChasComM5611-DCM
    OBJECT IDENTIFIER ::= { s5ChasComMod 569 }
s5ChasComM5611-DCMStore -- Storage areas
    OBJECT IDENTIFIER ::= { s5ChasComM5611-DCM 0 }
s5ChasComM5611-DCMStoreFlash -- FLASH image
    OBJECT IDENTIFIER ::= { s5ChasComM5611-DCMStore 1 }
s5ChasComM5611-DCMStoreDram -- DRAM image
    OBJECT IDENTIFIER ::= { s5ChasComM5611-DCMStore 2 }

s5ChasComBrdBayStack202 -- BayStack200 12Tx port Host Unit Repeater Brd
    OBJECT IDENTIFIER ::= { s5ChasComMod 570 }

s5ChasComBrdBayStack203 -- BayStack200 12Tx 1Fx port Host Unit Repeater Brd

    OBJECT IDENTIFIER ::= { s5ChasComMod 571 }

s5ChasComBrdBayStack204 -- BayStack200 24 port Host Unit Repeater Brd
    OBJECT IDENTIFIER ::= { s5ChasComMod 572 }

s5ChasComBrdBayStack205 -- BayStack200 12 port Host Unit Repeater Brd
    OBJECT IDENTIFIER ::= { s5ChasComMod 573 }

s5ChasComBrdBayStack200NMM -- BayStack200 NMM in the NMM Host Unit
    OBJECT IDENTIFIER ::= { s5ChasComMod 574 }
s5ChasComBrdBayStack200NMMStore -- storage areas
    OBJECT IDENTIFIER ::= { s5ChasComBrdBayStack200NMM 0 }
s5ChasComBrdBayStack200NMMStoreFlash -- FLASH Agent image
    OBJECT IDENTIFIER ::= { s5ChasComBrdBayStack200NMMStore 1 }
s5ChasComBrdBayStack200NMMStoreDram -- DRAM Agent image
    OBJECT IDENTIFIER ::= { s5ChasComBrdBayStack200NMMStore 2 }

-- BayStack 303 24+1 10BASE-T/100BASE-T Switch with 1 MDA
s5ChasComMBayStack303
    OBJECT IDENTIFIER ::= { s5ChasComMod 575 }

-- BayStack 304 12+1 10BASE-T/100BASE-T Switch with 1 MDA
s5ChasComMBayStack304
    OBJECT IDENTIFIER ::= { s5ChasComMod 576 }

-- BayStack 303A 24+1 10BASE-T/100BASE-T Switch with 1 MDA
s5ChasComMBayStack303A
    OBJECT IDENTIFIER ::= { s5ChasComMod 577 }

-- BayStack 304A 12+1 10BASE-T/100BASE-T Switch with 1 MDA
s5ChasComMBayStack304A
    OBJECT IDENTIFIER ::= { s5ChasComMod 578 }

-- Model MFX-1 100BASE-FX MDA for BayStack 303 and 304
s5ChasComMBayStack303-304FxMda
    OBJECT IDENTIFIER ::= { s5ChasComMod 579 }

-- Model MTX-1 10/100 MDA for BayStack 303 and 304
s5ChasComMBayStack303-304TxMda
    OBJECT IDENTIFIER ::= { s5ChasComMod 580 }

-- Model 5665 10/100 Ethernet Switch Host Module
s5ChasComBrdM5665
    OBJECT IDENTIFIER ::= { s5ChasComMod 581 }
s5ChasComBrdM5665Store -- Storage areas
    OBJECT IDENTIFIER ::= { s5ChasComBrdM5665 0 }
s5ChasComBrdM5665StoreFlash -- Flash Host Firmware
    OBJECT IDENTIFIER ::= { s5ChasComBrdM5665Store 1 }
s5ChasComBrdM5665StoreDram -- DRAM Host Firmware
    OBJECT IDENTIFIER ::= { s5ChasComBrdM5665Store 2 }

-- Model 5660-FX 100Base-FX Up-link Segment Switch NMM Module
-- with "S", "C", and "N" bus connections.
s5ChasComBrdM5660FX
    OBJECT IDENTIFIER ::= { s5ChasComMod 583 }
s5ChasComBrdM5660FXStore -- Storage areas
    OBJECT IDENTIFIER ::= { s5ChasComBrdM5660FX 0 }
s5ChasComBrdM5660FXStoreFlash -- Flash Agent Firmware
    OBJECT IDENTIFIER ::= { s5ChasComBrdM5660FXStore 1 }
s5ChasComBrdM5660FXStoreDram -- DRAM Agent Firmware
    OBJECT IDENTIFIER ::= { s5ChasComBrdM5660FXStore 2 }

-- Model 5620-FX 10/100Base-FX Up-link Segment Switch NMM Module
-- with "C" and "N" bus connections.
s5ChasComBrdM5620FX
    OBJECT IDENTIFIER ::= { s5ChasComMod 584 }
s5ChasComBrdM5620FXStore -- Storage areas
    OBJECT IDENTIFIER ::= { s5ChasComBrdM5620FX 0 }
s5ChasComBrdM5620FXStoreFlash -- Flash Agent Firmware
    OBJECT IDENTIFIER ::= { s5ChasComBrdM5620FXStore 1 }
s5ChasComBrdM5620FXStoreDram -- DRAM Agent Firmware
    OBJECT IDENTIFIER ::= { s5ChasComBrdM5620FXStore 2 }

s5ChasComBrdBayStack250 -- BayStack250 12 port NMM Host Unit Repeater Brd
    OBJECT IDENTIFIER ::= { s5ChasComMod 595 }

s5ChasComBrdBayStack251 -- BayStack250 12 port Host Unit Repeater Brd
    OBJECT IDENTIFIER ::= { s5ChasComMod 596 }

s5ChasComBrdBayStack252 -- BayStack250 24 port Host Unit Repeater Brd
    OBJECT IDENTIFIER ::= { s5ChasComMod 597 }

s5ChasComBrdBayStack250NMM -- BayStack250 NMM in the NMM Host Unit
    OBJECT IDENTIFIER ::= { s5ChasComMod 598 }
s5ChasComBrdBayStack250NMMStore -- storage areas
    OBJECT IDENTIFIER ::= { s5ChasComBrdBayStack250NMM 0 }
s5ChasComBrdBayStack250NMMStoreFlash -- FLASH Agent image
    OBJECT IDENTIFIER ::= { s5ChasComBrdBayStack250NMMStore 1 }
s5ChasComBrdBayStack250NMMStoreDram -- DRAM Agent image
    OBJECT IDENTIFIER ::= { s5ChasComBrdBayStack250NMMStore 2 }
s5ChasComBrdBayStack250NMMStoreBoot -- EPROM Boot Firmware
    OBJECT IDENTIFIER ::= { s5ChasComBrdBayStack250NMMStore 3 }

--C100 24 Port 10BASE-T Switch Host Module with 2 Telco Connectors
s5ChasComMod-c100mEther24P10BT
    OBJECT IDENTIFIER ::= { s5ChasComMod 631 }

-- C100 Multimode fiber MDA
s5ChasComMod-C100ATMMultiModeMda
    OBJECT IDENTIFIER ::= { s5ChasComMod 632 }
-- C100 Unshielded twisted pair MDA
s5ChasComMod-C100ATMUTPMda
    OBJECT IDENTIFIER ::= { s5ChasComMod 633 }
-- C100 Singlemode Fiber MDA
s5ChasComMod-C100ATMSingleModeMda
    OBJECT IDENTIFIER ::= { s5ChasComMod 634 }
-- C100 DS3 MDA
s5ChasComMod-C100ATMDS3Mda
    OBJECT IDENTIFIER ::= { s5ChasComMod 635 }
-- C100 E3 MDA
s5ChasComMod-C100ATME3Mda
    OBJECT IDENTIFIER ::= { s5ChasComMod 636 }

-- 5000BH Token Ring 24 Port Host
s5ChasComBrdTR24PC
    OBJECT IDENTIFIER ::= { s5ChasComMod 637 }

-- C100 Token Ring 16 Port Host
s5ChasComBrd-C100TR16PC
    OBJECT IDENTIFIER ::= { s5ChasComMod 638 }

-- 5000BH 57622M-SM 1 Port 622 Mbps 0C12-C ATM SMF MCP Module
s5ChasComBrd57622M-SM
    OBJECT IDENTIFIER ::= { s5ChasComMod 645 }

-- 5000BH 57622M-MM 1 Port 622 Mbps 0C12-C ATM MMF MCP Module
s5ChasComBrd57622M-MM
    OBJECT IDENTIFIER ::= { s5ChasComMod 646 }

-- 5000BH 57622-MM 1 Port 622 Mbps 0C12-C ATM MMF Switch Host
s5ChasComBrd57622-MM
    OBJECT IDENTIFIER ::= { s5ChasComMod 647 }

-- C100 1 Port 622 Mbps 0C12-C ATM SMF MCP Module
s5ChasComBrd-C100ATMMCP1PSM
    OBJECT IDENTIFIER ::= { s5ChasComMod 648 }

-- C100 1 Port 622 Mbps 0C12-C ATM MMF MCP Module
s5ChasComBrd-C100ATMMCP1PMM
    OBJECT IDENTIFIER ::= { s5ChasComMod 649 }

-- C100 1 Port 622 Mbps 0C12-C ATM MMF Switch Host
s5ChasComBrd-C100ATM1PMM
    OBJECT IDENTIFIER ::= { s5ChasComMod 650 }

s5ChasComBrdBayStack450-24T -- BayStack450-24T
    OBJECT IDENTIFIER ::= { s5ChasComMod 653 }
s5ChasComBrdBayStack450-24TStore -- storage areas
    OBJECT IDENTIFIER ::= { s5ChasComBrdBayStack450-24T 0 }
s5ChasComBrdBayStack450-24TStoreFlash -- FLASH image storage
    OBJECT IDENTIFIER ::= { s5ChasComBrdBayStack450-24TStore 1 }
s5ChasComBrdBayStack450-24TStoreBootFW -- Boot Firmware storage
    OBJECT IDENTIFIER ::= { s5ChasComBrdBayStack450-24TStore 2 }
s5ChasComBrdBayStack450-24TStoreDram -- DRAM storage
    OBJECT IDENTIFIER ::= { s5ChasComBrdBayStack450-24TStore 3 }

s5ChasComBrdBayStack450-12T -- BayStack450-12T
    OBJECT IDENTIFIER ::= { s5ChasComMod 654 }
s5ChasComBrdBayStack450-12TStore -- storage areas
    OBJECT IDENTIFIER ::= { s5ChasComBrdBayStack450-12T 0 }
s5ChasComBrdBayStack450-12TStoreFlash -- FLASH image storage
    OBJECT IDENTIFIER ::= { s5ChasComBrdBayStack450-12TStore 1 }
s5ChasComBrdBayStack450-12TStoreBootFW -- Boot Firmware storage
    OBJECT IDENTIFIER ::= { s5ChasComBrdBayStack450-12TStore 2 }
s5ChasComBrdBayStack450-12TStoreDram -- DRAM storage
    OBJECT IDENTIFIER ::= { s5ChasComBrdBayStack450-12TStore 3 }

s5ChasComBrdBayStack410-24T -- BayStack410-24T
    OBJECT IDENTIFIER ::= { s5ChasComMod 655 }

s5ChasComBrdBayStack450-1SX -- 1 port 1000Base-SX MDA
    OBJECT IDENTIFIER ::= { s5ChasComMod 656 }

s5ChasComBrdBayStack450-1SR -- 1 port 1000Base-SX MDA with LinkSafe
    OBJECT IDENTIFIER ::= { s5ChasComMod 657 }

s5ChasComBrdBayStack400-4TX -- 4 port 10/100 autosense MDA with RJ/45 connectors
    OBJECT IDENTIFIER ::= { s5ChasComMod 658 }

s5ChasComBrdBayStack400-2FX -- 2 port 100Base-FX MDA with SC connectors
    OBJECT IDENTIFIER ::= { s5ChasComMod 659 }

s5ChasComBrdBayStack400-ST1 -- Stacking MDA
    OBJECT IDENTIFIER ::= { s5ChasComMod 660 }

s5ChasComBrdBayStack400-ST2 -- Dual ring stacking MDA
    OBJECT IDENTIFIER ::= { s5ChasComMod 661 }

s5ChasComBrdBayStack450-1LX -- 1 port 1000Base-LX MDA
    OBJECT IDENTIFIER ::= { s5ChasComMod 662 }

s5ChasComBrdBayStack450-1LR -- 1 port 1000Base-LX MDA with LinkSafe
    OBJECT IDENTIFIER ::= { s5ChasComMod 663 }

s5ChasComBrdBayStack450-2SX -- 2 port 1000Base-SX MDA
    OBJECT IDENTIFIER ::= { s5ChasComMod 664 }

s5ChasComBrdBayStack450-2LX -- 2 port 1000Base-LX MDA
    OBJECT IDENTIFIER ::= { s5ChasComMod 665 }

s5ChasComBrdBayStack450-OC3 -- 2 port 155 Mbps OC3 Multi Mode ATM MDA
    OBJECT IDENTIFIER ::= { s5ChasComMod 666 }

-- BayStack 450-24TQP Chameleon 200 or 201 designated as "QP" to
-- differentiate from BayStack 450-24T Chameleon 100
s5ChasComBrdBayStack450-24TQP -- quad phy
    OBJECT IDENTIFIER ::= { s5ChasComMod 667 }

s5ChasComBrdBPS2000-24T -- BPS 2000-24T
    OBJECT IDENTIFIER ::= { s5ChasComMod 668 }
s5ChasComBrdBPS2000-24TStore -- storage areas
    OBJECT IDENTIFIER ::= { s5ChasComBrdBPS2000-24T 0 }
s5ChasComBrdBPS2000-24TStoreFlash -- FLASH image storage
    OBJECT IDENTIFIER ::= { s5ChasComBrdBPS2000-24TStore 1 }
s5ChasComBrdBPS2000-24TStoreBootFW -- Boot Firmware storage
    OBJECT IDENTIFIER ::= { s5ChasComBrdBPS2000-24TStore 2 }
s5ChasComBrdBPS2000-24TStoreDram -- DRAM storage
    OBJECT IDENTIFIER ::= { s5ChasComBrdBPS2000-24TStore 3 }

-- 5000BH Model 5424 24 Port 100BaseFx Host
s5ChasComBrd5424
    OBJECT IDENTIFIER ::= { s5ChasComMod 669 }

-- BayStack 525 Token Ring Switch
s5ChasComBrdBayStack525
    OBJECT IDENTIFIER ::= { s5ChasComMod 670 }

-- BayStack 350-24T (Non-Stackable) Chameleon 100
s5ChasComBrdBayStack350-24T -- BayStack350-24T
    OBJECT IDENTIFIER ::= { s5ChasComMod 671 }
s5ChasComBrdBayStack350-24TStore -- storage areas
    OBJECT IDENTIFIER ::= { s5ChasComBrdBayStack350-24T 0 }
s5ChasComBrdBayStack350-24TStoreFlash -- FLASH image storage
    OBJECT IDENTIFIER ::= { s5ChasComBrdBayStack350-24TStore 1 }
s5ChasComBrdBayStack350-24TStoreBootFW -- Boot Firmware storage
    OBJECT IDENTIFIER ::= { s5ChasComBrdBayStack350-24TStore 2 }
s5ChasComBrdBayStack350-24TStoreDram -- DRAM storage
    OBJECT IDENTIFIER ::= { s5ChasComBrdBayStack350-24TStore 3 }

-- BayStack 350-12T (Non-Stackable) Chameleon 100
s5ChasComBrdBayStack350-12T -- BayStack350-12T
    OBJECT IDENTIFIER ::= { s5ChasComMod 672 }
s5ChasComBrdBayStack350-12TStore -- storage areas
    OBJECT IDENTIFIER ::= { s5ChasComBrdBayStack350-12T 0 }
s5ChasComBrdBayStack350-12TStoreFlash -- FLASH image storage
    OBJECT IDENTIFIER ::= { s5ChasComBrdBayStack350-12TStore 1 }
s5ChasComBrdBayStack350-12TStoreBootFW -- Boot Firmware storage
    OBJECT IDENTIFIER ::= { s5ChasComBrdBayStack350-12TStore 2 }
s5ChasComBrdBayStack350-12TStoreDram -- DRAM storage
    OBJECT IDENTIFIER ::= { s5ChasComBrdBayStack350-12TStore 3 }

-- BayStack250 24 port NMM Host Unit Repeater Brd
s5ChasComBrdBayStack253
    OBJECT IDENTIFIER ::= { s5ChasComMod 673 }

-- BayStack 450-12TQP Chameleon 200 or 201 designated as "QP" to
-- differentiate from BayStack 450-12T Chameleon 100
s5ChasComBrdBayStack450-12TQP -- quad phy
    OBJECT IDENTIFIER ::= { s5ChasComMod 674 }

-- BayStack 350-24TQP (Non-Stackable) Chameleon 200 or 201
-- The official product name is BayStack 350-24T. Registered here as "QP"
-- to avoid naming conflict with Chameleon 100 BayStack 350-24T
s5ChasComBrdBayStack350-24TQP -- BayStack350-24TQP
    OBJECT IDENTIFIER ::= { s5ChasComMod 675 }
s5ChasComBrdBayStack350-24TQPStore -- storage areas
    OBJECT IDENTIFIER ::= { s5ChasComBrdBayStack350-24TQP 0 }
s5ChasComBrdBayStack350-24TQPStoreFlash -- FLASH image storage
    OBJECT IDENTIFIER ::= { s5ChasComBrdBayStack350-24TQPStore 1 }
s5ChasComBrdBayStack350-24TQPStoreBootFW -- Boot Firmware storage
    OBJECT IDENTIFIER ::= { s5ChasComBrdBayStack350-24TQPStore 2 }
s5ChasComBrdBayStack350-24TQPStoreDram -- DRAM storage
    OBJECT IDENTIFIER ::= { s5ChasComBrdBayStack350-24TQPStore 3 }

-- BayStack 350-12TQP (Non-Stackable) Chameleon 200 or 201
-- The official product name is BayStack 350-12T. Registered here as "QP"
-- to avoid naming conflict with Chameleon 100 BayStack 350-12T
s5ChasComBrdBayStack350-12TQP -- BayStack350-12TQP
    OBJECT IDENTIFIER ::= { s5ChasComMod 676 }
s5ChasComBrdBayStack350-12TQPStore -- storage areas
    OBJECT IDENTIFIER ::= { s5ChasComBrdBayStack350-12TQP 0 }
s5ChasComBrdBayStack350-12TQPStoreFlash -- FLASH image storage
    OBJECT IDENTIFIER ::= { s5ChasComBrdBayStack350-12TQPStore 1 }
s5ChasComBrdBayStack350-12TQPStoreBootFW -- Boot Firmware storage
    OBJECT IDENTIFIER ::= { s5ChasComBrdBayStack350-12TQPStore 2 }
s5ChasComBrdBayStack350-12TQPStoreDram -- DRAM storage
    OBJECT IDENTIFIER ::= { s5ChasComBrdBayStack350-12TQPStore 3 }

-- BayStack 450-12F "Firefly" 12 Fiber Ports + MDA Slot
s5ChasComBrdBayStack450-12F -- BayStack450-12F
    OBJECT IDENTIFIER ::= { s5ChasComMod 681 }
s5ChasComBrdBayStack450-12FStore -- storage areas
    OBJECT IDENTIFIER ::= { s5ChasComBrdBayStack450-12F 0 }
s5ChasComBrdBayStack450-12FStoreFlash -- FLASH image storage
    OBJECT IDENTIFIER ::= { s5ChasComBrdBayStack450-12FStore 1 }
s5ChasComBrdBayStack450-12FStoreBootFW -- Boot Firmware storage
    OBJECT IDENTIFIER ::= { s5ChasComBrdBayStack450-12FStore 2 }
s5ChasComBrdBayStack450-12FStoreDram -- DRAM storage
    OBJECT IDENTIFIER ::= { s5ChasComBrdBayStack450-12FStore 3 }

s5ChasComBrdBayStack400-4FX -- 4 port 100Base-FX MDA with MT-RJ connectors
    OBJECT IDENTIFIER ::= { s5ChasComMod 682 }

-- BayStack 303-24T 24+1 10BASE-T/100BASE-T Switch with 2 MDA
s5ChasComMBayStack303-24T
    OBJECT IDENTIFIER ::= { s5ChasComMod 691 }

-- BayStack 253 10/100 Hub 100Base-FX Media Adapter
s5ChasComBrdBayStack-100FxMda
    OBJECT IDENTIFIER ::= { s5ChasComMod 692 }

-- Accelar 8010 chassis 32 port 10/100 switch host module with MDA slot
s5ChasComBrdAccelar8132TX
    OBJECT IDENTIFIER ::= { s5ChasComMod 693 }

-- Accelar 8010 chassis 48 port 10/100 switch host module
s5ChasComBrdAccelar8148TX
    OBJECT IDENTIFIER ::= { s5ChasComMod 694 }

-- BayStack250 12 port Slave Unit Repeater Brd
s5ChasComBrdBayStack254
    OBJECT IDENTIFIER ::= { s5ChasComMod 695 }

-- BayStack250 24 port Slave Unit Repeater Brd
s5ChasComBrdBayStack255
    OBJECT IDENTIFIER ::= { s5ChasComMod 696 }

-- 1 port 100Base-FX MDA for BayStack 25x 10/100 Hub
s5ChasComBrdBayStack25x-100FxMda
    OBJECT IDENTIFIER ::= { s5ChasComMod 697 }

-- 5000BH Model 5625HD 24-port 10/100 Ethernet Copper Switch Host
s5ChasComBrdM5625HD
    OBJECT IDENTIFIER ::= { s5ChasComMod 701 }

-- 5000BH Model 5424HD 24-port 100BaseFX Switch Host
s5ChasComBrdM5424HD
    OBJECT IDENTIFIER ::= { s5ChasComMod 702 }

-- C50/C100 20-port 10/100 Ethernet Copper Switch Host
s5ChasComMod-C100mEther20PC
    OBJECT IDENTIFIER ::= { s5ChasComMod 703 }

-- C50/C100 16-port 100BaseFX Switch Host
s5ChasComMod-C100mEther16P100FX
    OBJECT IDENTIFIER ::= { s5ChasComMod 704 }

s5ChasComBrdBayStack670 -- BayStack670 11 Mb/s wireless access point
    OBJECT IDENTIFIER ::= { s5ChasComMod 705 }
s5ChasComBrdBayStack670Store -- storage areas
    OBJECT IDENTIFIER ::= { s5ChasComBrdBayStack670 0 }
s5ChasComBrdBayStack670StoreFlash -- FLASH image storage
    OBJECT IDENTIFIER ::= { s5ChasComBrdBayStack670Store 1 }

-- 500xBH Model 5420 3-port GBIC Ethernet Switch Module
s5ChasComBrdM5420
    OBJECT IDENTIFIER ::= { s5ChasComMod 706 }

-- C50/C100 3-port EtherSpeedII GBIC Switch Module
s5ChasComMod-C100mEther3PGBIC
    OBJECT IDENTIFIER ::= { s5ChasComMod 707 }

s5ChasComBrdBPS2000-4TX -- 4 port 10/100 MDA
    OBJECT IDENTIFIER ::= { s5ChasComMod 708 }

s5ChasComBrdBPS2000-4FX -- 4 port 100Base-FX MDA
    OBJECT IDENTIFIER ::= { s5ChasComMod 709 }

s5ChasComBrdBPS2000-2FX -- 2 port 100Base-FX MDA
    OBJECT IDENTIFIER ::= { s5ChasComMod 710 }

s5ChasComBrdBayStack3580-16F -- BayStack3580-16F
    OBJECT IDENTIFIER ::= { s5ChasComMod 711 }
s5ChasComBrdBayStack3580-16FStore -- storage areas
    OBJECT IDENTIFIER ::= { s5ChasComBrdBayStack3580-16F 0 }
s5ChasComBrdBayStack3580-16FStoreFlash -- FLASH image storage
    OBJECT IDENTIFIER ::= { s5ChasComBrdBayStack3580-16FStore 1 }
s5ChasComBrdBayStack3580-16FStoreBootFW -- Boot Firmware storage
    OBJECT IDENTIFIER ::= { s5ChasComBrdBayStack3580-16FStore 2 }
s5ChasComBrdBayStack3580-16FStoreDram -- DRAM storage
    OBJECT IDENTIFIER ::= { s5ChasComBrdBayStack3580-16FStore 3 }

-- BayStack 450 ATM MDAs. There is also an s5ChasComBrdBayStack450-OC3
-- defined above as:
--

s5ChasComBrdBayStack450-OC3S -- 2 port 155 Mbps OC3 Single Mode ATM MDA
    OBJECT IDENTIFIER ::= { s5ChasComMod 717 }

s5ChasComBrdBayStack450-OC12 -- 2 port 622 Mbps OC12 Multi Mode ATM MDA
    OBJECT IDENTIFIER ::= { s5ChasComMod 718 }

s5ChasComBrdBayStack450-OC12S -- 2 port 622 Mbps OC12 Single Mode ATM MDA
    OBJECT IDENTIFIER ::= { s5ChasComMod 719 }

-- BayStack 420-24T 24-Port 10/100 Ethernet Switch
s5ChasComBrdBayStack420-24T -- BayStack420-24T
    OBJECT IDENTIFIER ::= { s5ChasComMod 720 }
s5ChasComBrdBayStack420-24TStore -- storage areas
    OBJECT IDENTIFIER ::= { s5ChasComBrdBayStack420-24T 0 }
s5ChasComBrdBayStack420-24TStoreFlash -- FLASH image storage
    OBJECT IDENTIFIER ::= { s5ChasComBrdBayStack420-24TStore 1 }
s5ChasComBrdBayStack420-24TStoreBootFW -- Boot Firmware storage
    OBJECT IDENTIFIER ::= { s5ChasComBrdBayStack420-24TStore 2 }
s5ChasComBrdBayStack420-24TStoreDram -- DRAM storage
    OBJECT IDENTIFIER ::= { s5ChasComBrdBayStack420-24TStore 3 }

-- BayStack 450 and BPS2000 1 port 1 Phy packet bus II GBIC MDA.
-- BayStack 450 and BPS2000 single port single Phy GBIC MDA
s5ChasComBrdBayStack450-GBIC
    OBJECT IDENTIFIER ::= { s5ChasComMod 721 }
s5ChasComBrdBayStack450-GBICno -- No Transceiver present
    OBJECT IDENTIFIER ::= { s5ChasComBrdBayStack450-GBIC 1 }
s5ChasComBrdBayStack450-GBICun -- Unsupported Transceiver
    OBJECT IDENTIFIER ::= { s5ChasComBrdBayStack450-GBIC 2 }
s5ChasComBrdBayStack450-GBICsx -- Short Distance
    OBJECT IDENTIFIER ::= { s5ChasComBrdBayStack450-GBIC 3 }
s5ChasComBrdBayStack450-GBIClx -- Long Distance
    OBJECT IDENTIFIER ::= { s5ChasComBrdBayStack450-GBIC 4 }
s5ChasComBrdBayStack450-GBICzx -- 50 Kilometers
    OBJECT IDENTIFIER ::= { s5ChasComBrdBayStack450-GBIC 5 }
s5ChasComBrdBayStack450-GBICxd -- 70 Kilometers
    OBJECT IDENTIFIER ::= { s5ChasComBrdBayStack450-GBIC 6 }
s5ChasComBrdBayStack450-GBICbt -- Copper GBIC
    OBJECT IDENTIFIER ::= { s5ChasComBrdBayStack450-GBIC 7 }

-- OPTera Metro 1200 Ethernet Service Module
s5ChasComBrdMetro1200ESM-12T
    OBJECT IDENTIFIER ::= { s5ChasComMod 722 }
s5ChasComBrdMetro1200ESM-12TStore -- storage areas
    OBJECT IDENTIFIER ::= { s5ChasComBrdMetro1200ESM-12T 0 }
s5ChasComBrdMetro1200ESM-12TStoreFlash -- FLASH image storage
    OBJECT IDENTIFIER ::= { s5ChasComBrdMetro1200ESM-12TStore 1 }
s5ChasComBrdMetro1200ESM-12TStoreBootFW -- Boot Firmware storage
    OBJECT IDENTIFIER ::= { s5ChasComBrdMetro1200ESM-12TStore 2 }
s5ChasComBrdMetro1200ESM-12TStoreDram -- DRAM storage
    OBJECT IDENTIFIER ::= { s5ChasComBrdMetro1200ESM-12TStore 3 }

-- BayStack380 10/100/1000 Ethernet Switch
s5ChasComBrdBayStack380-24T
    OBJECT IDENTIFIER ::= { s5ChasComMod 723 }
s5ChasComBrdBayStack380-24TStore -- storage areas
    OBJECT IDENTIFIER ::= { s5ChasComBrdBayStack380-24T 0 }
s5ChasComBrdBayStack380-24TStoreFlash -- FLASH image storage
    OBJECT IDENTIFIER ::= { s5ChasComBrdBayStack380-24TStore 1 }
s5ChasComBrdBayStack380-24TStoreBootFW -- Boot Firmware storage
    OBJECT IDENTIFIER ::= { s5ChasComBrdBayStack380-24TStore 2 }
s5ChasComBrdBayStack380-24TStoreDram -- DRAM storage
    OBJECT IDENTIFIER ::= { s5ChasComBrdBayStack380-24TStore 3 }

-- BPS2000 Talon MDAs
s5ChasComBrdTalonMDA
    OBJECT IDENTIFIER ::= { s5ChasComMod 724 }
s5ChasComBrdTalonMDA-1GT -- BPS2000 Talon 1GT MDA
    OBJECT IDENTIFIER ::= { s5ChasComBrdTalonMDA 1 }
s5ChasComBrdTalonMDA-2GT -- BPS2000 Talon 2GT MDA
    OBJECT IDENTIFIER ::= { s5ChasComBrdTalonMDA 2 }
s5ChasComBrdTalonMDA-2GE -- BPS2000 Talon GBIC MDA
    OBJECT IDENTIFIER ::= { s5ChasComBrdTalonMDA 3 }

-- BPS2000 Talon GBIC MDA GBIC definitions
s5ChasComBrdTalonMDA-2GE-NO-NO -- GBICS: NONE NONE
    OBJECT IDENTIFIER ::= { s5ChasComBrdTalonMDA-2GE 1 1 }
s5ChasComBrdTalonMDA-2GE-NO-UN -- GBICS: NONE UNSUPPORTED
    OBJECT IDENTIFIER ::= { s5ChasComBrdTalonMDA-2GE 1 2 }
s5ChasComBrdTalonMDA-2GE-NO-SX -- GBICS: NONE SX
    OBJECT IDENTIFIER ::= { s5ChasComBrdTalonMDA-2GE 1 3 }
s5ChasComBrdTalonMDA-2GE-NO-LX -- GBICS: NONE LX
    OBJECT IDENTIFIER ::= { s5ChasComBrdTalonMDA-2GE 1 4 }
s5ChasComBrdTalonMDA-2GE-NO-ZX -- GBICS: NONE ZX
    OBJECT IDENTIFIER ::= { s5ChasComBrdTalonMDA-2GE 1 5 }
s5ChasComBrdTalonMDA-2GE-NO-XD -- GBICS: NONE XD
    OBJECT IDENTIFIER ::= { s5ChasComBrdTalonMDA-2GE 1 6 }
s5ChasComBrdTalonMDA-2GE-UN-NO -- GBICS: UNSUPPORTED NONE
    OBJECT IDENTIFIER ::= { s5ChasComBrdTalonMDA-2GE 2 1 }
s5ChasComBrdTalonMDA-2GE-UN-UN -- GBICS: UNSUPPORTED UNSUPPORTED
    OBJECT IDENTIFIER ::= { s5ChasComBrdTalonMDA-2GE 2 2 }
s5ChasComBrdTalonMDA-2GE-UN-SX -- GBICS: UNSUPPORTED SX
    OBJECT IDENTIFIER ::= { s5ChasComBrdTalonMDA-2GE 2 3 }
s5ChasComBrdTalonMDA-2GE-UN-LX -- GBICS: UNSUPPORTED LX
    OBJECT IDENTIFIER ::= { s5ChasComBrdTalonMDA-2GE 2 4 }
s5ChasComBrdTalonMDA-2GE-UN-ZX -- GBICS: UNSUPPORTED ZX
    OBJECT IDENTIFIER ::= { s5ChasComBrdTalonMDA-2GE 2 5 }
s5ChasComBrdTalonMDA-2GE-UN-XD -- GBICS: UNSUPPORTED XD
    OBJECT IDENTIFIER ::= { s5ChasComBrdTalonMDA-2GE 2 6 }
s5ChasComBrdTalonMDA-2GE-SX-NO -- GBICS: SX NONE
    OBJECT IDENTIFIER ::= { s5ChasComBrdTalonMDA-2GE 3 1 }
s5ChasComBrdTalonMDA-2GE-SX-UN -- GBICS: SX UNSUPPORTED
    OBJECT IDENTIFIER ::= { s5ChasComBrdTalonMDA-2GE 3 2 }
s5ChasComBrdTalonMDA-2GE-SX-SX -- GBICS: SX SX
    OBJECT IDENTIFIER ::= { s5ChasComBrdTalonMDA-2GE 3 3 }
s5ChasComBrdTalonMDA-2GE-SX-LX -- GBICS: SX LX
    OBJECT IDENTIFIER ::= { s5ChasComBrdTalonMDA-2GE 3 4 }
s5ChasComBrdTalonMDA-2GE-SX-ZX -- GBICS: SX ZX
    OBJECT IDENTIFIER ::= { s5ChasComBrdTalonMDA-2GE 3 5 }
s5ChasComBrdTalonMDA-2GE-SX-XD -- GBICS: SX XD
    OBJECT IDENTIFIER ::= { s5ChasComBrdTalonMDA-2GE 3 6 }
s5ChasComBrdTalonMDA-2GE-LX-NO -- GBICS: LX NONE
    OBJECT IDENTIFIER ::= { s5ChasComBrdTalonMDA-2GE 4 1 }
s5ChasComBrdTalonMDA-2GE-LX-UN -- GBICS: LX UNSUPPORTED
    OBJECT IDENTIFIER ::= { s5ChasComBrdTalonMDA-2GE 4 2 }
s5ChasComBrdTalonMDA-2GE-LX-SX -- GBICS: LX SX
    OBJECT IDENTIFIER ::= { s5ChasComBrdTalonMDA-2GE 4 3 }
s5ChasComBrdTalonMDA-2GE-LX-LX -- GBICS: LX LX
    OBJECT IDENTIFIER ::= { s5ChasComBrdTalonMDA-2GE 4 4 }
s5ChasComBrdTalonMDA-2GE-LX-ZX -- GBICS: LX ZX
    OBJECT IDENTIFIER ::= { s5ChasComBrdTalonMDA-2GE 4 5 }
s5ChasComBrdTalonMDA-2GE-LX-XD -- GBICS: LX XD
    OBJECT IDENTIFIER ::= { s5ChasComBrdTalonMDA-2GE 4 6 }
s5ChasComBrdTalonMDA-2GE-ZX-NO -- GBICS: ZX NONE
    OBJECT IDENTIFIER ::= { s5ChasComBrdTalonMDA-2GE 5 1 }
s5ChasComBrdTalonMDA-2GE-ZX-UN -- GBICS: ZX UNSUPPORTED
    OBJECT IDENTIFIER ::= { s5ChasComBrdTalonMDA-2GE 5 2 }
s5ChasComBrdTalonMDA-2GE-ZX-SX -- GBICS: ZX SX
    OBJECT IDENTIFIER ::= { s5ChasComBrdTalonMDA-2GE 5 3 }
s5ChasComBrdTalonMDA-2GE-ZX-LX -- GBICS: ZX LX
    OBJECT IDENTIFIER ::= { s5ChasComBrdTalonMDA-2GE 5 4 }
s5ChasComBrdTalonMDA-2GE-ZX-ZX -- GBICS: ZX ZX
    OBJECT IDENTIFIER ::= { s5ChasComBrdTalonMDA-2GE 5 5 }
s5ChasComBrdTalonMDA-2GE-ZX-XD -- GBICS: ZX XD
    OBJECT IDENTIFIER ::= { s5ChasComBrdTalonMDA-2GE 5 6 }
s5ChasComBrdTalonMDA-2GE-XD-NO -- GBICS: XD NONE
    OBJECT IDENTIFIER ::= { s5ChasComBrdTalonMDA-2GE 6 1 }
s5ChasComBrdTalonMDA-2GE-XD-UN -- GBICS: XD UNSUPPORTED
    OBJECT IDENTIFIER ::= { s5ChasComBrdTalonMDA-2GE 6 2 }
s5ChasComBrdTalonMDA-2GE-XD-SX -- GBICS: XD SX
    OBJECT IDENTIFIER ::= { s5ChasComBrdTalonMDA-2GE 6 3 }
s5ChasComBrdTalonMDA-2GE-XD-LX -- GBICS: XD LX
    OBJECT IDENTIFIER ::= { s5ChasComBrdTalonMDA-2GE 6 4 }
s5ChasComBrdTalonMDA-2GE-XD-ZX -- GBICS: XD ZX
    OBJECT IDENTIFIER ::= { s5ChasComBrdTalonMDA-2GE 6 5 }
s5ChasComBrdTalonMDA-2GE-XD-XD -- GBICS: XD XD
    OBJECT IDENTIFIER ::= { s5ChasComBrdTalonMDA-2GE 6 6 }

-- 4 port 100Base-FX Single-Mode MDA
s5ChasComBrdBPS2000-4FX-SM
    OBJECT IDENTIFIER ::= { s5ChasComMod 725 }

-- BayStack470 10/100 48 Port Ethernet Switch
s5ChasComBrdBayStack470-48T
    OBJECT IDENTIFIER ::= { s5ChasComMod 726 }
s5ChasComBrdBayStack470-48TStore -- storage areas
    OBJECT IDENTIFIER ::= { s5ChasComBrdBayStack470-48T 0 }
s5ChasComBrdBayStack470-48TStoreFlash -- FLASH image storage
    OBJECT IDENTIFIER ::= { s5ChasComBrdBayStack470-48TStore 1 }
s5ChasComBrdBayStack470-48TStoreBootFW -- Boot Firmware storage
    OBJECT IDENTIFIER ::= { s5ChasComBrdBayStack470-48TStore 2 }
s5ChasComBrdBayStack470-48TStoreDram -- DRAM storage
    OBJECT IDENTIFIER ::= { s5ChasComBrdBayStack470-48TStore 3 }

-- GBIC registrations
s5ChasComBrdGbic OBJECT IDENTIFIER ::= { s5ChasComMod 727 }
s5ChasComBrdGbic-None        OBJECT IDENTIFIER ::= { s5ChasComBrdGbic 1 }
s5ChasComBrdGbic-Unsupported OBJECT IDENTIFIER ::= { s5ChasComBrdGbic 2 }
s5ChasComBrdGbic-SX          OBJECT IDENTIFIER ::= { s5ChasComBrdGbic 3 }
s5ChasComBrdGbic-LX          OBJECT IDENTIFIER ::= { s5ChasComBrdGbic 4 }
s5ChasComBrdGbic-ZX          OBJECT IDENTIFIER ::= { s5ChasComBrdGbic 5 }
s5ChasComBrdGbic-XD          OBJECT IDENTIFIER ::= { s5ChasComBrdGbic 6 }
s5ChasComBrdGbic-TX          OBJECT IDENTIFIER ::= { s5ChasComBrdGbic 7 }
s5ChasComBrdGbic-CWDM        OBJECT IDENTIFIER ::= { s5ChasComBrdGbic 8 }
s5ChasComBrdGbic-DWDM        OBJECT IDENTIFIER ::= { s5ChasComBrdGbic 9 }
s5ChasComBrdGbic-10G-SR      OBJECT IDENTIFIER ::= { s5ChasComBrdGbic 10 }
s5ChasComBrdGbic-10G-LR      OBJECT IDENTIFIER ::= { s5ChasComBrdGbic 11 }
s5ChasComBrdGbic-10G-ER      OBJECT IDENTIFIER ::= { s5ChasComBrdGbic 12 }
s5ChasComBrdGbic-10G-LX4     OBJECT IDENTIFIER ::= { s5ChasComBrdGbic 13 }
s5ChasComBrdGbic-10G-ZR      OBJECT IDENTIFIER ::= { s5ChasComBrdGbic 14 }
s5ChasComBrdGbic-10G-LRM     OBJECT IDENTIFIER ::= { s5ChasComBrdGbic 15 }
s5ChasComBrdGbic-T1          OBJECT IDENTIFIER ::= { s5ChasComBrdGbic 16 }
s5ChasComBrdGbic-EX          OBJECT IDENTIFIER ::= { s5ChasComBrdGbic 17 }
s5ChasComBrdGbic-DIRECT      OBJECT IDENTIFIER ::= { s5ChasComBrdGbic 18 }
s5ChasComBrdGbic-40G-SR4     OBJECT IDENTIFIER ::= { s5ChasComBrdGbic 19 }
s5ChasComBrdGbic-40G-LR      OBJECT IDENTIFIER ::= { s5ChasComBrdGbic 20 }
s5ChasComBrdGbic-40G-ER      OBJECT IDENTIFIER ::= { s5ChasComBrdGbic 21 }

-- OPTera Metro 1450 Ethernet Service Module
s5ChasComBrdMetro1450ESM-12T2GBIC
    OBJECT IDENTIFIER ::= { s5ChasComMod 728 }
s5ChasComBrdMetro1450ESM-12T2GBICStore -- storage areas
    OBJECT IDENTIFIER ::= { s5ChasComBrdMetro1450ESM-12T2GBIC 0 }
s5ChasComBrdMetro1450ESM-12T2GBICStoreFlash -- FLASH image storage
    OBJECT IDENTIFIER ::= { s5ChasComBrdMetro1450ESM-12T2GBICStore 1 }
s5ChasComBrdMetro1450ESM-12T2GBICStoreBootFW -- Boot Firmware storage
    OBJECT IDENTIFIER ::= { s5ChasComBrdMetro1450ESM-12T2GBICStore 2 }
s5ChasComBrdMetro1450ESM-12T2GBICStoreDram -- DRAM storage
    OBJECT IDENTIFIER ::= { s5ChasComBrdMetro1450ESM-12T2GBICStore 3 }

-- OPTera Metro 1400 Ethernet Service Module
s5ChasComBrdMetro1400ESM-12T2GBIC
    OBJECT IDENTIFIER ::= { s5ChasComMod 729 }
s5ChasComBrdMetro1400ESM-12T2GBICStore -- storage areas
    OBJECT IDENTIFIER ::= { s5ChasComBrdMetro1400ESM-12T2GBIC 0 }
s5ChasComBrdMetro1400ESM-12T2GBICStoreFlash -- FLASH image storage
    OBJECT IDENTIFIER ::= { s5ChasComBrdMetro1400ESM-12T2GBICStore 1 }
s5ChasComBrdMetro1400ESM-12T2GBICStoreBootFW -- Boot Firmware storage
    OBJECT IDENTIFIER ::= { s5ChasComBrdMetro1400ESM-12T2GBICStore 2 }
s5ChasComBrdMetro1400ESM-12T2GBICStoreDram -- DRAM storage
    OBJECT IDENTIFIER ::= { s5ChasComBrdMetro1400ESM-12T2GBICStore 3 }

-- BayStack 460-24T-PWR
s5ChasComBrdBayStack460-24T-PWR-24T
    OBJECT IDENTIFIER ::= { s5ChasComMod 730 }
s5ChasComBrdBayStack460-24T-PWR-24TStore -- storage areas
    OBJECT IDENTIFIER ::= { s5ChasComBrdBayStack460-24T-PWR-24T 0 }
s5ChasComBrdBayStack460-24T-PWR-24TStoreFlash -- FLASH image storage
    OBJECT IDENTIFIER ::= { s5ChasComBrdBayStack460-24T-PWR-24TStore 1 }
s5ChasComBrdBayStack460-24T-PWR-24TStoreBootFW -- Boot Firmware storage
    OBJECT IDENTIFIER ::= { s5ChasComBrdBayStack460-24T-PWR-24TStore 2 }
s5ChasComBrdBayStack460-24T-PWR-24TStoreDram -- DRAM storage
    OBJECT IDENTIFIER ::= { s5ChasComBrdBayStack460-24T-PWR-24TStore 3 }
s5ChasComBrdBayStack460-24T-PWR-24TStorePoLFlash -- PoL Flash image storage
    OBJECT IDENTIFIER ::= { s5ChasComBrdBayStack460-24T-PWR-24TStore 4 }

-- BayStack380-24F 1000 Ethernet Switch
s5ChasComBrdBayStack380-24F
    OBJECT IDENTIFIER ::= { s5ChasComMod 731 }
s5ChasComBrdBayStack380-24FStore -- storage areas
    OBJECT IDENTIFIER ::= { s5ChasComBrdBayStack380-24F 0 }
s5ChasComBrdBayStack380-24FStoreFlash -- FLASH image storage
    OBJECT IDENTIFIER ::= { s5ChasComBrdBayStack380-24FStore 1 }
s5ChasComBrdBayStack380-24FStoreBootFW -- Boot Firmware storage
    OBJECT IDENTIFIER ::= { s5ChasComBrdBayStack380-24FStore 2 }
s5ChasComBrdBayStack380-24FStoreDram -- DRAM storage
    OBJECT IDENTIFIER ::= { s5ChasComBrdBayStack380-24FStore 3 }

-- BayStack 5510-24T
s5ChasComBrdBayStack5510-24T
    OBJECT IDENTIFIER ::= { s5ChasComMod 732 }
s5ChasComBrdBayStack5510-24TStore -- storage areas
    OBJECT IDENTIFIER ::= { s5ChasComBrdBayStack5510-24T 0 }
s5ChasComBrdBayStack5510-24TStoreFlash -- FLASH image storage
    OBJECT IDENTIFIER ::= { s5ChasComBrdBayStack5510-24TStore 1 }
s5ChasComBrdBayStack5510-24TStoreBootFW -- Boot Firmware storage
    OBJECT IDENTIFIER ::= { s5ChasComBrdBayStack5510-24TStore 2 }
s5ChasComBrdBayStack5510-24TStoreDram -- DRAM storage
    OBJECT IDENTIFIER ::= { s5ChasComBrdBayStack5510-24TStore 3 }

-- BayStack 5510-48T
s5ChasComBrdBayStack5510-48T
    OBJECT IDENTIFIER ::= { s5ChasComMod 733 }
s5ChasComBrdBayStack5510-48TStore -- storage areas
    OBJECT IDENTIFIER ::= { s5ChasComBrdBayStack5510-48T 0 }
s5ChasComBrdBayStack5510-48TStoreFlash -- FLASH image storage
    OBJECT IDENTIFIER ::= { s5ChasComBrdBayStack5510-48TStore 1 }
s5ChasComBrdBayStack5510-48TStoreBootFW -- Boot Firmware storage
    OBJECT IDENTIFIER ::= { s5ChasComBrdBayStack5510-48TStore 2 }
s5ChasComBrdBayStack5510-48TStoreDram -- DRAM storage
    OBJECT IDENTIFIER ::= { s5ChasComBrdBayStack5510-48TStore 3 }

-- BayStack470 10/100 24 Port Ethernet Switch
s5ChasComBrdBayStack470-24T
    OBJECT IDENTIFIER ::= { s5ChasComMod 734 }
s5ChasComBrdBayStack470-24TStore -- storage areas
    OBJECT IDENTIFIER ::= { s5ChasComBrdBayStack470-24T 0 }
s5ChasComBrdBayStack470-24TStoreFlash -- FLASH image storage
    OBJECT IDENTIFIER ::= { s5ChasComBrdBayStack470-24TStore 1 }
s5ChasComBrdBayStack470-24TStoreBootFW -- Boot Firmware storage
    OBJECT IDENTIFIER ::= { s5ChasComBrdBayStack470-24TStore 2 }
s5ChasComBrdBayStack470-24TStoreDram -- DRAM storage
    OBJECT IDENTIFIER ::= { s5ChasComBrdBayStack470-24TStore 3 }

-- Nortel Networks Wireless LAN Access Point 2220
s5ChasComBrdWLANAccessPoint2220
    OBJECT IDENTIFIER ::= { s5ChasComMod 735 }
s5ChasComBrdWLANAccessPoint2220Store -- storage areas
    OBJECT IDENTIFIER ::= { s5ChasComBrdWLANAccessPoint2220 0 }
s5ChasComBrdWLANAccessPoint2220StoreFlash -- FLASH image storage
    OBJECT IDENTIFIER ::= { s5ChasComBrdWLANAccessPoint2220Store 1 }
s5ChasComBrdWLANAccessPoint2220StoreBootFW -- Boot Firmware storage
    OBJECT IDENTIFIER ::= { s5ChasComBrdWLANAccessPoint2220Store 2 }
s5ChasComBrdWLANAccessPoint2220StoreDram -- DRAM storage
    OBJECT IDENTIFIER ::= { s5ChasComBrdWLANAccessPoint2220Store 3 }

-- Nortel Networks Wireless LAN Security Switch 2250
s5ChasComBrdWLANSecuritySwitch2250
    OBJECT IDENTIFIER ::= { s5ChasComMod 736 }
s5ChasComBrdWLANSecuritySwitch2250Store -- storage areas
    OBJECT IDENTIFIER ::= { s5ChasComBrdWLANSecuritySwitch2250 0 }
s5ChasComBrdWLANSecuritySwitch2250StoreFlash -- FLASH image storage
    OBJECT IDENTIFIER ::= { s5ChasComBrdWLANSecuritySwitch2250Store 1 }
s5ChasComBrdWLANSecuritySwitch2250StoreBootFW -- Boot Firmware storage
    OBJECT IDENTIFIER ::= { s5ChasComBrdWLANSecuritySwitch2250Store 2 }
s5ChasComBrdWLANSecuritySwitch2250StoreDram -- DRAM storage
    OBJECT IDENTIFIER ::= { s5ChasComBrdWLANSecuritySwitch2250Store 3 }

-- BayStack 425
s5ChasComBrdBayStack425
    OBJECT IDENTIFIER ::= { s5ChasComMod 737 }
s5ChasComBrdBayStack425Store -- storage areas
    OBJECT IDENTIFIER ::= { s5ChasComBrdBayStack425 0 }
s5ChasComBrdBayStack425StoreFlash -- FLASH image storage
    OBJECT IDENTIFIER ::= { s5ChasComBrdBayStack425Store 1 }
s5ChasComBrdBayStack425StoreBootFW -- Boot Firmware storage
    OBJECT IDENTIFIER ::= { s5ChasComBrdBayStack425Store 2 }
s5ChasComBrdBayStack425StoreDram -- DRAM storage
    OBJECT IDENTIFIER ::= { s5ChasComBrdBayStack425Store 3 }

-- Nortel Networks Wireless LAN Access Point 2221
s5ChasComBrdWLANAccessPoint2221
    OBJECT IDENTIFIER ::= { s5ChasComMod 738 }
s5ChasComBrdWLANAccessPoint2221Store -- storage areas
    OBJECT IDENTIFIER ::= { s5ChasComBrdWLANAccessPoint2221 0 }
s5ChasComBrdWLANAccessPoint2221StoreFlash -- FLASH image storage
    OBJECT IDENTIFIER ::= { s5ChasComBrdWLANAccessPoint2221Store 1 }
s5ChasComBrdWLANAccessPoint2221StoreBootFW -- Boot Firmware storage
    OBJECT IDENTIFIER ::= { s5ChasComBrdWLANAccessPoint2221Store 2 }
s5ChasComBrdWLANAccessPoint2221StoreDram -- DRAM storage
    OBJECT IDENTIFIER ::= { s5ChasComBrdWLANAccessPoint2221Store 3 }

-- BayStack 5520-24T-PWR
s5ChasComBrdBayStack5520-24T-PWR-24T
    OBJECT IDENTIFIER ::= { s5ChasComMod 739 }
s5ChasComBrdBayStack5520-24T-PWR-24TStore -- storage areas
    OBJECT IDENTIFIER ::= { s5ChasComBrdBayStack5520-24T-PWR-24T 0 }
s5ChasComBrdBayStack5520-24T-PWR-24TStoreFlash -- FLASH image storage
    OBJECT IDENTIFIER ::= { s5ChasComBrdBayStack5520-24T-PWR-24TStore 1 }
s5ChasComBrdBayStack5520-24T-PWR-24TStoreBootFW -- Boot Firmware storage
    OBJECT IDENTIFIER ::= { s5ChasComBrdBayStack5520-24T-PWR-24TStore 2 }
s5ChasComBrdBayStack5520-24T-PWR-24TStoreDram -- DRAM storage
    OBJECT IDENTIFIER ::= { s5ChasComBrdBayStack5520-24T-PWR-24TStore 3 }
s5ChasComBrdBayStack5520-24T-PWR-24TStorePoLFlash -- PoL Flash image storage
    OBJECT IDENTIFIER ::= { s5ChasComBrdBayStack5520-24T-PWR-24TStore 4 }

-- BayStack 5520-48T-PWR
s5ChasComBrdBayStack5520-48T-PWR-48T
    OBJECT IDENTIFIER ::= { s5ChasComMod 740 }
s5ChasComBrdBayStack5520-48T-PWR-48TStore -- storage areas
    OBJECT IDENTIFIER ::= { s5ChasComBrdBayStack5520-48T-PWR-48T 0 }
s5ChasComBrdBayStack5520-48T-PWR-48TStoreFlash -- FLASH image storage
    OBJECT IDENTIFIER ::= { s5ChasComBrdBayStack5520-48T-PWR-48TStore 1 }
s5ChasComBrdBayStack5520-48T-PWR-48TStoreBootFW -- Boot Firmware storage
    OBJECT IDENTIFIER ::= { s5ChasComBrdBayStack5520-48T-PWR-48TStore 2 }
s5ChasComBrdBayStack5520-48T-PWR-48TStoreDram -- DRAM storage
    OBJECT IDENTIFIER ::= { s5ChasComBrdBayStack5520-48T-PWR-48TStore 3 }
s5ChasComBrdBayStack5520-48T-PWR-48TStorePoLFlash -- PoL Flash image storage
    OBJECT IDENTIFIER ::= { s5ChasComBrdBayStack5520-48T-PWR-48TStore 4 }

-- BayStack 425-48
s5ChasComBrdBayStack425-48
    OBJECT IDENTIFIER ::= { s5ChasComMod 741 }
s5ChasComBrdBayStack425-48Store -- storage areas
    OBJECT IDENTIFIER ::= { s5ChasComBrdBayStack425-48 0 }
s5ChasComBrdBayStack425-48StoreFlash -- FLASH image storage
    OBJECT IDENTIFIER ::= { s5ChasComBrdBayStack425-48Store 1 }
s5ChasComBrdBayStack425-48StoreBootFW -- Boot Firmware storage
    OBJECT IDENTIFIER ::= { s5ChasComBrdBayStack425-48Store 2 }
s5ChasComBrdBayStack425-48StoreDram -- DRAM storage
    OBJECT IDENTIFIER ::= { s5ChasComBrdBayStack425-48Store 3 }


-- BayStack 325
s5ChasComBrdBayStack325
    OBJECT IDENTIFIER ::= { s5ChasComMod 742 }
s5ChasComBrdBayStack325Store -- storage areas
    OBJECT IDENTIFIER ::= { s5ChasComBrdBayStack325 0 }
s5ChasComBrdBayStack325StoreFlash -- FLASH image storage
    OBJECT IDENTIFIER ::= { s5ChasComBrdBayStack325Store 1 }
s5ChasComBrdBayStack325StoreBootFW -- Boot Firmware storage
    OBJECT IDENTIFIER ::= { s5ChasComBrdBayStack325Store 2 }
s5ChasComBrdBayStack325StoreDram -- DRAM storage
    OBJECT IDENTIFIER ::= { s5ChasComBrdBayStack325Store 3 }
s5ChasComBrdBayStack325-24T
    OBJECT IDENTIFIER ::= { s5ChasComBrdBayStack325 1 }
s5ChasComBrdBayStack325-24G
    OBJECT IDENTIFIER ::= { s5ChasComBrdBayStack325 2 }

-- Nortel Networks Wireless LAN Access Point 2225
s5ChasComBrdWLANAccessPoint2225
    OBJECT IDENTIFIER ::= { s5ChasComMod 743 }
s5ChasComBrdWLANAccessPoint2225Store -- storage areas
    OBJECT IDENTIFIER ::= { s5ChasComBrdWLANAccessPoint2225 0 }
s5ChasComBrdWLANAccessPoint2225StoreFlash -- FLASH image storage
    OBJECT IDENTIFIER ::= { s5ChasComBrdWLANAccessPoint2225Store 1 }
s5ChasComBrdWLANAccessPoint2225StoreBootFW -- Boot Firmware storage
    OBJECT IDENTIFIER ::= { s5ChasComBrdWLANAccessPoint2225Store 2 }
s5ChasComBrdWLANAccessPoint2225StoreDram -- DRAM storage
    OBJECT IDENTIFIER ::= { s5ChasComBrdWLANAccessPoint2225Store 3 }

-- BayStack470 10/100 24 Port PWR Ethernet Switch
s5ChasComBrdBayStack470-24T-PWR
    OBJECT IDENTIFIER ::= { s5ChasComMod 744 }
s5ChasComBrdBayStack470-24T-PWRStore -- storage areas
    OBJECT IDENTIFIER ::= { s5ChasComBrdBayStack470-24T-PWR 0 }
s5ChasComBrdBayStack470-24T-PWRStoreFlash -- FLASH image storage
    OBJECT IDENTIFIER ::= { s5ChasComBrdBayStack470-24T-PWRStore 1 }
s5ChasComBrdBayStack470-24T-PWRStoreBootFW -- Boot Firmware storage
    OBJECT IDENTIFIER ::= { s5ChasComBrdBayStack470-24T-PWRStore 2 }
s5ChasComBrdBayStack470-24T-PWRStoreDram -- DRAM storage
    OBJECT IDENTIFIER ::= { s5ChasComBrdBayStack470-24T-PWRStore 3 }

-- BayStack470 10/100 48 Port PWR Ethernet Switch
s5ChasComBrdBayStack470-48T-PWR
    OBJECT IDENTIFIER ::= { s5ChasComMod 745 }
s5ChasComBrdBayStack470-48T-PWRStore -- storage areas
    OBJECT IDENTIFIER ::= { s5ChasComBrdBayStack470-48T-PWR 0 }
s5ChasComBrdBayStack470-48T-PWRStoreFlash -- FLASH image storage
    OBJECT IDENTIFIER ::= { s5ChasComBrdBayStack470-48T-PWRStore 1 }
s5ChasComBrdBayStack470-48T-PWRStoreBootFW -- Boot Firmware storage
    OBJECT IDENTIFIER ::= { s5ChasComBrdBayStack470-48T-PWRStore 2 }
s5ChasComBrdBayStack470-48T-PWRStoreDram -- DRAM storage
    OBJECT IDENTIFIER ::= { s5ChasComBrdBayStack470-48T-PWRStore 3 }

-- Nortel Networks Wireless LAN Security Switch 2270
s5ChasComBrdWLANSecuritySwitch2270
    OBJECT IDENTIFIER ::= { s5ChasComMod 746 }
s5ChasComBrdWLANSecuritySwitch2270Store -- storage areas
    OBJECT IDENTIFIER ::= { s5ChasComBrdWLANSecuritySwitch2270 0 }
s5ChasComBrdWLANSecuritySwitch2270StoreFlash -- FLASH image storage
    OBJECT IDENTIFIER ::= { s5ChasComBrdWLANSecuritySwitch2270Store 1 }
s5ChasComBrdWLANSecuritySwitch2270StoreBootFW -- Boot Firmware storage
    OBJECT IDENTIFIER ::= { s5ChasComBrdWLANSecuritySwitch2270Store 2 }
s5ChasComBrdWLANSecuritySwitch2270StoreDram -- DRAM storage
    OBJECT IDENTIFIER ::= { s5ChasComBrdWLANSecuritySwitch2270Store 3 }

-- Ethernet Routing Switch 5530-24TFD 24 Port Switch
s5ChasComBrdEthernetRoutingSwitch5530-24TFD
    OBJECT IDENTIFIER ::= { s5ChasComMod 747 }
s5ChasComBrdEthernetRoutingSwitch5530-24TFDStore -- storage areas
    OBJECT IDENTIFIER ::= { s5ChasComBrdEthernetRoutingSwitch5530-24TFD 0 }
s5ChasComBrdEthernetRoutingSwitch5530-24TFDStoreFlash -- FLASH image storage
    OBJECT IDENTIFIER ::= { s5ChasComBrdEthernetRoutingSwitch5530-24TFDStore 1 }
s5ChasComBrdEthernetRoutingSwitch5530-24TFDStoreBootFW -- Boot Firmware storage
    OBJECT IDENTIFIER ::= { s5ChasComBrdEthernetRoutingSwitch5530-24TFDStore 2 }
s5ChasComBrdEthernetRoutingSwitch5530-24TFDStoreDram -- DRAM storage
    OBJECT IDENTIFIER ::= { s5ChasComBrdEthernetRoutingSwitch5530-24TFDStore 3 }

-- Ethernet Switch 3510-24T 24 Port Switch
s5ChasComBrdEthernetSwitch3510-24T
    OBJECT IDENTIFIER ::= { s5ChasComMod 748 }
s5ChasComBrdEthernetSwitch3510-24TStore -- storage areas
    OBJECT IDENTIFIER ::= { s5ChasComBrdEthernetSwitch3510-24T 0 }
s5ChasComBrdEthernetSwitch3510-24TStoreFlash -- FLASH image storage
    OBJECT IDENTIFIER ::= { s5ChasComBrdEthernetSwitch3510-24TStore 1 }
s5ChasComBrdEthernetSwitch3510-24TStoreBootFW -- Boot Firmware storage
    OBJECT IDENTIFIER ::= { s5ChasComBrdEthernetSwitch3510-24TStore 2 }
s5ChasComBrdEthernetSwitch3510-24TStoreDram -- DRAM storage
    OBJECT IDENTIFIER ::= { s5ChasComBrdEthernetSwitch3510-24TStore 3 }

-- Nortel Networks Wireless LAN Security Cryptography Modules
s5ChasComBrdWLANSecurityCryptographyModules
    OBJECT IDENTIFIER ::= { s5ChasComMod 749 }
s5ChasComBrdWLANSecuritySwitch2270CryptoAccelerator
    OBJECT IDENTIFIER ::= { s5ChasComBrdWLANSecurityCryptographyModules 1 }

-- SMB GIG BES 1010 24T
s5ChasComBrdBES1010-24T
    OBJECT IDENTIFIER ::= { s5ChasComMod 750 }
s5ChasComBrdBES1010-24TStore -- storage areas
    OBJECT IDENTIFIER ::= { s5ChasComBrdBES1010-24T 0 }
s5ChasComBrdBES1010-24TStoreFlash -- FLASH image storage
    OBJECT IDENTIFIER ::= { s5ChasComBrdBES1010-24TStore 1 }
s5ChasComBrdBES1010-24TStoreBootFW -- Boot Firmware storage
    OBJECT IDENTIFIER ::= { s5ChasComBrdBES1010-24TStore 2 }
s5ChasComBrdBES1010-24TStoreDram -- DRAM storage
    OBJECT IDENTIFIER ::= { s5ChasComBrdBES1010-24TStore 3 }

-- SMB GIG BES 1010 48T
s5ChasComBrdBES1010-48T
    OBJECT IDENTIFIER ::= { s5ChasComMod 751 }
s5ChasComBrdBES1010-48TStore -- storage areas
    OBJECT IDENTIFIER ::= { s5ChasComBrdBES1010-48T 0 }
s5ChasComBrdBES1010-48TStoreFlash -- FLASH image storage
    OBJECT IDENTIFIER ::= { s5ChasComBrdBES1010-48TStore 1 }
s5ChasComBrdBES1010-48TStoreBootFW -- Boot Firmware storage
    OBJECT IDENTIFIER ::= { s5ChasComBrdBES1010-48TStore 2 }
s5ChasComBrdBES1010-48TStoreDram -- DRAM storage
    OBJECT IDENTIFIER ::= { s5ChasComBrdBES1010-48TStore 3 }

-- SMB GIG BES 1020 24T PWR
s5ChasComBrdBES1020-24T-PWR
    OBJECT IDENTIFIER ::= { s5ChasComMod 752 }
s5ChasComBrdBES1020-24T-PWRStore -- storage areas
    OBJECT IDENTIFIER ::= { s5ChasComBrdBES1020-24T-PWR 0 }
s5ChasComBrdBES1020-24T-PWRStoreFlash -- FLASH image storage
    OBJECT IDENTIFIER ::= { s5ChasComBrdBES1020-24T-PWRStore 1 }
s5ChasComBrdBES1020-24T-PWRStoreBootFW -- Boot Firmware storage
    OBJECT IDENTIFIER ::= { s5ChasComBrdBES1020-24T-PWRStore 2 }
s5ChasComBrdBES1020-24T-PWRStoreDram -- DRAM storage
    OBJECT IDENTIFIER ::= { s5ChasComBrdBES1020-24T-PWRStore 3 }
s5ChasComBrdBES1020-24T-PWRStorePoLFlash -- PoL Flash image storage
    OBJECT IDENTIFIER ::= { s5ChasComBrdBES1020-24T-PWRStore 4 }

-- SMB GIG BES 1020 48T PWR
s5ChasComBrdBES1020-48T-PWR
    OBJECT IDENTIFIER ::= { s5ChasComMod 753 }
s5ChasComBrdBES1020-48T-PWRStore -- storage areas
    OBJECT IDENTIFIER ::= { s5ChasComBrdBES1020-48T-PWR 0 }
s5ChasComBrdBES1020-48T-PWRStoreFlash -- FLASH image storage
    OBJECT IDENTIFIER ::= { s5ChasComBrdBES1020-48T-PWRStore 1 }
s5ChasComBrdBES1020-48T-PWRStoreBootFW -- Boot Firmware storage
    OBJECT IDENTIFIER ::= { s5ChasComBrdBES1020-48T-PWRStore 2 }
s5ChasComBrdBES1020-48T-PWRStoreDram -- DRAM storage
    OBJECT IDENTIFIER ::= { s5ChasComBrdBES1020-48T-PWRStore 3 }
s5ChasComBrdBES1020-48T-PWRStorePoLFlash -- PoL Flash image storage
    OBJECT IDENTIFIER ::= { s5ChasComBrdBES1020-48T-PWRStore 4 }

-- SMB GIG BES 2010 24T
s5ChasComBrdBES2010-24T
    OBJECT IDENTIFIER ::= { s5ChasComMod 754 }
s5ChasComBrdBES2010-24TStore -- storage areas
    OBJECT IDENTIFIER ::= { s5ChasComBrdBES2010-24T 0 }
s5ChasComBrdBES2010-24TStoreFlash -- FLASH image storage
    OBJECT IDENTIFIER ::= { s5ChasComBrdBES2010-24TStore 1 }
s5ChasComBrdBES2010-24TStoreBootFW -- Boot Firmware storage
    OBJECT IDENTIFIER ::= { s5ChasComBrdBES2010-24TStore 2 }
s5ChasComBrdBES2010-24TStoreDram -- DRAM storage
    OBJECT IDENTIFIER ::= { s5ChasComBrdBES2010-24TStore 3 }

-- SMB GIG BES 2010 48T
s5ChasComBrdBES2010-48T
    OBJECT IDENTIFIER ::= { s5ChasComMod 755 }
s5ChasComBrdBES2010-48TStore -- storage areas
    OBJECT IDENTIFIER ::= { s5ChasComBrdBES2010-48T 0 }
s5ChasComBrdBES2010-48TStoreFlash -- FLASH image storage
    OBJECT IDENTIFIER ::= { s5ChasComBrdBES2010-48TStore 1 }
s5ChasComBrdBES2010-48TStoreBootFW -- Boot Firmware storage
    OBJECT IDENTIFIER ::= { s5ChasComBrdBES2010-48TStore 2 }
s5ChasComBrdBES2010-48TStoreDram -- DRAM storage
    OBJECT IDENTIFIER ::= { s5ChasComBrdBES2010-48TStore 3 }

-- SMB GIG BES 2020 24T PWR
s5ChasComBrdBES2020-24T-PWR
    OBJECT IDENTIFIER ::= { s5ChasComMod 756 }
s5ChasComBrdBES2020-24T-PWRStore -- storage areas
    OBJECT IDENTIFIER ::= { s5ChasComBrdBES2020-24T-PWR 0 }
s5ChasComBrdBES2020-24T-PWRStoreFlash -- FLASH image storage
    OBJECT IDENTIFIER ::= { s5ChasComBrdBES2020-24T-PWRStore 1 }
s5ChasComBrdBES2020-24T-PWRStoreBootFW -- Boot Firmware storage
    OBJECT IDENTIFIER ::= { s5ChasComBrdBES2020-24T-PWRStore 2 }
s5ChasComBrdBES2020-24T-PWRStoreDram -- DRAM storage
    OBJECT IDENTIFIER ::= { s5ChasComBrdBES2020-24T-PWRStore 3 }
s5ChasComBrdBES2020-24T-PWRStorePoLFlash -- PoL Flash image storage
    OBJECT IDENTIFIER ::= { s5ChasComBrdBES2020-24T-PWRStore 4 }

-- SMB GIG BES 2020 48T PWR
s5ChasComBrdBES2020-48T-PWR
    OBJECT IDENTIFIER ::= { s5ChasComMod 757 }
s5ChasComBrdBES2020-48T-PWRStore -- storage areas
    OBJECT IDENTIFIER ::= { s5ChasComBrdBES2020-48T-PWR 0 }
s5ChasComBrdBES2020-48T-PWRStoreFlash -- FLASH image storage
    OBJECT IDENTIFIER ::= { s5ChasComBrdBES2020-48T-PWRStore 1 }
s5ChasComBrdBES2020-48T-PWRStoreBootFW -- Boot Firmware storage
    OBJECT IDENTIFIER ::= { s5ChasComBrdBES2020-48T-PWRStore 2 }
s5ChasComBrdBES2020-48T-PWRStoreDram -- DRAM storage
    OBJECT IDENTIFIER ::= { s5ChasComBrdBES2020-48T-PWRStore 3 }
s5ChasComBrdBES2020-48T-PWRStorePoLFlash -- PoL Flash image storage
    OBJECT IDENTIFIER ::= { s5ChasComBrdBES2020-48T-PWRStore 4 }

-- SMB FE BES 110 24T
s5ChasComBrdBES110-24T
    OBJECT IDENTIFIER ::= { s5ChasComMod 758 }
s5ChasComBrdBES110-24TStore -- storage areas
    OBJECT IDENTIFIER ::= { s5ChasComBrdBES110-24T 0 }
s5ChasComBrdBES110-24TStoreFlash -- FLASH image storage
    OBJECT IDENTIFIER ::= { s5ChasComBrdBES110-24TStore 1 }
s5ChasComBrdBES110-24TStoreBootFW -- Boot Firmware storage
    OBJECT IDENTIFIER ::= { s5ChasComBrdBES110-24TStore 2 }
s5ChasComBrdBES110-24TStoreDram -- DRAM storage
    OBJECT IDENTIFIER ::= { s5ChasComBrdBES110-24TStore 3 }

-- SMB FE BES 110 48T
s5ChasComBrdBES110-48T
    OBJECT IDENTIFIER ::= { s5ChasComMod 759 }
s5ChasComBrdBES110-48TStore -- storage areas
    OBJECT IDENTIFIER ::= { s5ChasComBrdBES110-48T 0 }
s5ChasComBrdBES110-48TStoreFlash -- FLASH image storage
    OBJECT IDENTIFIER ::= { s5ChasComBrdBES110-48TStore 1 }
s5ChasComBrdBES110-48TStoreBootFW -- Boot Firmware storage
    OBJECT IDENTIFIER ::= { s5ChasComBrdBES110-48TStore 2 }
s5ChasComBrdBES110-48TStoreDram -- DRAM storage
    OBJECT IDENTIFIER ::= { s5ChasComBrdBES110-48TStore 3 }

-- SMB FE BES 120 24T PWR
s5ChasComBrdBES120-24T-PWR
    OBJECT IDENTIFIER ::= { s5ChasComMod 760 }
s5ChasComBrdBES120-24T-PWRStore -- storage areas
    OBJECT IDENTIFIER ::= { s5ChasComBrdBES120-24T-PWR 0 }
s5ChasComBrdBES120-24T-PWRStoreFlash -- FLASH image storage
    OBJECT IDENTIFIER ::= { s5ChasComBrdBES120-24T-PWRStore 1 }
s5ChasComBrdBES120-24T-PWRStoreBootFW -- Boot Firmware storage
    OBJECT IDENTIFIER ::= { s5ChasComBrdBES120-24T-PWRStore 2 }
s5ChasComBrdBES120-24T-PWRStoreDram -- DRAM storage
    OBJECT IDENTIFIER ::= { s5ChasComBrdBES120-24T-PWRStore 3 }
s5ChasComBrdBES120-24T-PWRStorePoLFlash -- PoL Flash image storage
    OBJECT IDENTIFIER ::= { s5ChasComBrdBES120-24T-PWRStore 4 }

-- SMB FE BES 120 48T PWR
s5ChasComBrdBES120-48T-PWR
    OBJECT IDENTIFIER ::= { s5ChasComMod 761 }
s5ChasComBrdBES120-48T-PWRStore -- storage areas
    OBJECT IDENTIFIER ::= { s5ChasComBrdBES120-48T-PWR 0 }
s5ChasComBrdBES120-48T-PWRStoreFlash -- FLASH image storage
    OBJECT IDENTIFIER ::= { s5ChasComBrdBES120-48T-PWRStore 1 }
s5ChasComBrdBES120-48T-PWRStoreBootFW -- Boot Firmware storage
    OBJECT IDENTIFIER ::= { s5ChasComBrdBES120-48T-PWRStore 2 }
s5ChasComBrdBES120-48T-PWRStoreDram -- DRAM storage
    OBJECT IDENTIFIER ::= { s5ChasComBrdBES120-48T-PWRStore 3 }
s5ChasComBrdBES120-48T-PWRStorePoLFlash -- PoL Flash image storage
    OBJECT IDENTIFIER ::= { s5ChasComBrdBES120-48T-PWRStore 4 }

-- SMB FE BES 210 24T
s5ChasComBrdBES210-24T
    OBJECT IDENTIFIER ::= { s5ChasComMod 762 }
s5ChasComBrdBES210-24TStore -- storage areas
    OBJECT IDENTIFIER ::= { s5ChasComBrdBES210-24T 0 }
s5ChasComBrdBES210-24TStoreFlash -- FLASH image storage
    OBJECT IDENTIFIER ::= { s5ChasComBrdBES210-24TStore 1 }
s5ChasComBrdBES210-24TStoreBootFW -- Boot Firmware storage
    OBJECT IDENTIFIER ::= { s5ChasComBrdBES210-24TStore 2 }
s5ChasComBrdBES210-24TStoreDram -- DRAM storage
    OBJECT IDENTIFIER ::= { s5ChasComBrdBES210-24TStore 3 }

-- SMB FE BES 210 48T
s5ChasComBrdBES210-48T
    OBJECT IDENTIFIER ::= { s5ChasComMod 763 }
s5ChasComBrdBES210-48TStore -- storage areas
    OBJECT IDENTIFIER ::= { s5ChasComBrdBES210-48T 0 }
s5ChasComBrdBES210-48TStoreFlash -- FLASH image storage
    OBJECT IDENTIFIER ::= { s5ChasComBrdBES210-48TStore 1 }
s5ChasComBrdBES210-48TStoreBootFW -- Boot Firmware storage
    OBJECT IDENTIFIER ::= { s5ChasComBrdBES210-48TStore 2 }
s5ChasComBrdBES210-48TStoreDram -- DRAM storage
    OBJECT IDENTIFIER ::= { s5ChasComBrdBES210-48TStore 3 }

-- SMB FE BES 220 24T PWR
s5ChasComBrdBES220-24T-PWR
    OBJECT IDENTIFIER ::= { s5ChasComMod 764 }
s5ChasComBrdBES220-24T-PWRStore -- storage areas
    OBJECT IDENTIFIER ::= { s5ChasComBrdBES220-24T-PWR 0 }
s5ChasComBrdBES220-24T-PWRStoreFlash -- FLASH image storage
    OBJECT IDENTIFIER ::= { s5ChasComBrdBES220-24T-PWRStore 1 }
s5ChasComBrdBES220-24T-PWRStoreBootFW -- Boot Firmware storage
    OBJECT IDENTIFIER ::= { s5ChasComBrdBES220-24T-PWRStore 2 }
s5ChasComBrdBES220-24T-PWRStoreDram -- DRAM storage
    OBJECT IDENTIFIER ::= { s5ChasComBrdBES220-24T-PWRStore 3 }
s5ChasComBrdBES220-24T-PWRStorePoLFlash -- PoL Flash image storage
    OBJECT IDENTIFIER ::= { s5ChasComBrdBES220-24T-PWRStore 4 }

-- SMB FE BES 220 48T PWR
s5ChasComBrdBES220-48T-PWR
    OBJECT IDENTIFIER ::= { s5ChasComMod 765 }
s5ChasComBrdBES220-48T-PWRStore -- storage areas
    OBJECT IDENTIFIER ::= { s5ChasComBrdBES220-48T-PWR 0 }
s5ChasComBrdBES220-48T-PWRStoreFlash -- FLASH image storage
    OBJECT IDENTIFIER ::= { s5ChasComBrdBES220-48T-PWRStore 1 }
s5ChasComBrdBES220-48T-PWRStoreBootFW -- Boot Firmware storage
    OBJECT IDENTIFIER ::= { s5ChasComBrdBES220-48T-PWRStore 2 }
s5ChasComBrdBES220-48T-PWRStoreDram -- DRAM storage
    OBJECT IDENTIFIER ::= { s5ChasComBrdBES220-48T-PWRStore 3 }
s5ChasComBrdBES220-48T-PWRStorePoLFlash -- PoL Flash image storage
    OBJECT IDENTIFIER ::= { s5ChasComBrdBES220-48T-PWRStore 4 }

-- ERS4548GT
s5ChasComBrdERS4548GT
    OBJECT IDENTIFIER ::= { s5ChasComMod 766 }
s5ChasComBrdERS4548GTStore -- storage areas
    OBJECT IDENTIFIER ::= { s5ChasComBrdERS4548GT 0 }
s5ChasComBrdERS4548GTStoreFlash -- FLASH image storage
    OBJECT IDENTIFIER ::= { s5ChasComBrdERS4548GTStore 1 }
s5ChasComBrdERS4548GTStoreBootFW -- Boot Firmware storage
    OBJECT IDENTIFIER ::= { s5ChasComBrdERS4548GTStore 2 }
s5ChasComBrdERS4548GTStoreDram -- DRAM storage
    OBJECT IDENTIFIER ::= { s5ChasComBrdERS4548GTStore 3 }
s5ChasComBrdERS4548GTStoreSecondaryFlash -- Secondary FLASH image storage
    OBJECT IDENTIFIER ::= { s5ChasComBrdERS4548GTStore 5 }
s5ChasComBrdERS4548GTStoreCPLD -- CPLD
    OBJECT IDENTIFIER ::= { s5ChasComBrdERS4548GTStore 6 }
s5ChasComBrdERS4548GTStoreInstalledFW -- Installed FW Version
    OBJECT IDENTIFIER ::= { s5ChasComBrdERS4548GTStore 7 }
s5ChasComBrdERS4548GTStoreOperSW -- Operational Software Version
    OBJECT IDENTIFIER ::= { s5ChasComBrdERS4548GTStore 8 }
s5ChasComBrdERS4548GTStoreTotal -- Total FLASH storage
    OBJECT IDENTIFIER ::= { s5ChasComBrdERS4548GTStore 9 }
s5ChasComBrdERS4548GTStoreBootLoader -- Boot Loader storage
    OBJECT IDENTIFIER ::= { s5ChasComBrdERS4548GTStore 10 }
s5ChasComBrdERS4548GTStoreConfig -- Binary Configuration storage
    OBJECT IDENTIFIER ::= { s5ChasComBrdERS4548GTStore 11 }
s5ChasComBrdERS4548GTStoreSecondaryConfig -- Secondary Binary Configuration storage
    OBJECT IDENTIFIER ::= { s5ChasComBrdERS4548GTStore 12 }
s5ChasComBrdERS4548GTStoreAutoBakupConfig -- Automatic Backup Configuration storage
    OBJECT IDENTIFIER ::= { s5ChasComBrdERS4548GTStore 13 }
s5ChasComBrdERS4548GTStoreReserved -- Portion of total FLASH storage that is reserved
    OBJECT IDENTIFIER ::= { s5ChasComBrdERS4548GTStore 14 }

-- ERS4548GT-PWR
s5ChasComBrdERS4548GT-PWR
    OBJECT IDENTIFIER ::= { s5ChasComMod 767 }
s5ChasComBrdERS4548GT-PWRStore -- storage areas
    OBJECT IDENTIFIER ::= { s5ChasComBrdERS4548GT-PWR 0 }
s5ChasComBrdERS4548GT-PWRStoreFlash -- FLASH image storage
    OBJECT IDENTIFIER ::= { s5ChasComBrdERS4548GT-PWRStore 1 }
s5ChasComBrdERS4548GT-PWRStoreBootFW -- Boot Firmware storage
    OBJECT IDENTIFIER ::= { s5ChasComBrdERS4548GT-PWRStore 2 }
s5ChasComBrdERS4548GT-PWRStoreDram -- DRAM storage
    OBJECT IDENTIFIER ::= { s5ChasComBrdERS4548GT-PWRStore 3 }
s5ChasComBrdERS4548GT-PWRStorePoLFlash -- PoL Flash image storage
    OBJECT IDENTIFIER ::= { s5ChasComBrdERS4548GT-PWRStore 4 }
s5ChasComBrdERS4548GT-PWRStoreSecondaryFlash -- Secondary FLASH image storage
    OBJECT IDENTIFIER ::= { s5ChasComBrdERS4548GT-PWRStore 5 }
s5ChasComBrdERS4548GT-PWRStoreCPLD -- CPLD
    OBJECT IDENTIFIER ::= { s5ChasComBrdERS4548GT-PWRStore 6 }
s5ChasComBrdERS4548GT-PWRStoreInstalledFW -- Installed FW Version
    OBJECT IDENTIFIER ::= { s5ChasComBrdERS4548GT-PWRStore 7 }
s5ChasComBrdERS4548GT-PWRStoreOperSW -- Operational Software Version
    OBJECT IDENTIFIER ::= { s5ChasComBrdERS4548GT-PWRStore 8 }
s5ChasComBrdERS4548GT-PWRStoreTotal -- Total FLASH storage
    OBJECT IDENTIFIER ::= { s5ChasComBrdERS4548GT-PWRStore 9 }
s5ChasComBrdERS4548GT-PWRStoreBootLoader -- Boot Loader storage
    OBJECT IDENTIFIER ::= { s5ChasComBrdERS4548GT-PWRStore 10 }
s5ChasComBrdERS4548GT-PWRStoreConfig -- Binary Configuration storage
    OBJECT IDENTIFIER ::= { s5ChasComBrdERS4548GT-PWRStore 11 }
s5ChasComBrdERS4548GT-PWRStoreSecondaryConfig -- Secondary Binary Configuration storage
    OBJECT IDENTIFIER ::= { s5ChasComBrdERS4548GT-PWRStore 12 }
s5ChasComBrdERS4548GT-PWRStoreAutoBakupConfig -- Automatic Backup Configuration storage
    OBJECT IDENTIFIER ::= { s5ChasComBrdERS4548GT-PWRStore 13 }
s5ChasComBrdERS4548GT-PWRStoreReserved -- Portion of total FLASH storage that is reserved
    OBJECT IDENTIFIER ::= { s5ChasComBrdERS4548GT-PWRStore 14 }

-- ERS4550T
s5ChasComBrdERS4550T
    OBJECT IDENTIFIER ::= { s5ChasComMod 768 }
s5ChasComBrdERS4550TStore -- storage areas
    OBJECT IDENTIFIER ::= { s5ChasComBrdERS4550T 0 }
s5ChasComBrdERS4550TStoreFlash -- FLASH image storage
    OBJECT IDENTIFIER ::= { s5ChasComBrdERS4550TStore 1 }
s5ChasComBrdERS4550TStoreBootFW -- Boot Firmware storage
    OBJECT IDENTIFIER ::= { s5ChasComBrdERS4550TStore 2 }
s5ChasComBrdERS4550TStoreDram -- DRAM storage
    OBJECT IDENTIFIER ::= { s5ChasComBrdERS4550TStore 3 }
s5ChasComBrdERS4550TStoreSecondaryFlash -- Secondary FLASH image storage
    OBJECT IDENTIFIER ::= { s5ChasComBrdERS4550TStore 5 }
s5ChasComBrdERS4550TStoreCPLD -- CPLD
    OBJECT IDENTIFIER ::= { s5ChasComBrdERS4550TStore 6 }
s5ChasComBrdERS4550TStoreInstalledFW -- Installed FW Version
    OBJECT IDENTIFIER ::= { s5ChasComBrdERS4550TStore 7 }
s5ChasComBrdERS4550TStoreOperSW -- Operational Software Version
    OBJECT IDENTIFIER ::= { s5ChasComBrdERS4550TStore 8 }
s5ChasComBrdERS4550TStoreTotal -- Total FLASH storage
    OBJECT IDENTIFIER ::= { s5ChasComBrdERS4550TStore 9 }
s5ChasComBrdERS4550TStoreBootLoader -- Boot Loader storage
    OBJECT IDENTIFIER ::= { s5ChasComBrdERS4550TStore 10 }
s5ChasComBrdERS4550TStoreConfig -- Binary Configuration storage
    OBJECT IDENTIFIER ::= { s5ChasComBrdERS4550TStore 11 }
s5ChasComBrdERS4550TStoreSecondaryConfig -- Secondary Binary Configuration storage
    OBJECT IDENTIFIER ::= { s5ChasComBrdERS4550TStore 12 }
s5ChasComBrdERS4550TStoreAutoBakupConfig -- Automatic Backup Configuration storage
    OBJECT IDENTIFIER ::= { s5ChasComBrdERS4550TStore 13 }
s5ChasComBrdERS4550TStoreReserved -- Portion of total FLASH storage that is reserved
    OBJECT IDENTIFIER ::= { s5ChasComBrdERS4550TStore 14 }

-- ERS4550T-PWR
s5ChasComBrdERS4550T-PWR
    OBJECT IDENTIFIER ::= { s5ChasComMod 769 }
s5ChasComBrdERS4550T-PWRStore -- storage areas
    OBJECT IDENTIFIER ::= { s5ChasComBrdERS4550T-PWR 0 }
s5ChasComBrdERS4550T-PWRStoreFlash -- FLASH image storage
    OBJECT IDENTIFIER ::= { s5ChasComBrdERS4550T-PWRStore 1 }
s5ChasComBrdERS4550T-PWRStoreBootFW -- Boot Firmware storage
    OBJECT IDENTIFIER ::= { s5ChasComBrdERS4550T-PWRStore 2 }
s5ChasComBrdERS4550T-PWRStoreDram -- DRAM storage
    OBJECT IDENTIFIER ::= { s5ChasComBrdERS4550T-PWRStore 3 }
s5ChasComBrdERS4550T-PWRStorePoLFlash -- PoL Flash image storage
    OBJECT IDENTIFIER ::= { s5ChasComBrdERS4550T-PWRStore 4 }
s5ChasComBrdERS4550T-PWRStoreSecondaryFlash -- Secondary FLASH image storage
    OBJECT IDENTIFIER ::= { s5ChasComBrdERS4550T-PWRStore 5 }
s5ChasComBrdERS4550T-PWRStoreCPLD -- CPLD
    OBJECT IDENTIFIER ::= { s5ChasComBrdERS4550T-PWRStore 6 }
s5ChasComBrdERS4550T-PWRStoreInstalledFW -- Installed FW Version
    OBJECT IDENTIFIER ::= { s5ChasComBrdERS4550T-PWRStore 7 }
s5ChasComBrdERS4550T-PWRStoreOperSW -- Operational Software Version
    OBJECT IDENTIFIER ::= { s5ChasComBrdERS4550T-PWRStore 8 }
s5ChasComBrdERS4550T-PWRStoreTotal -- Total FLASH storage
    OBJECT IDENTIFIER ::= { s5ChasComBrdERS4550T-PWRStore 9 }
s5ChasComBrdERS4550T-PWRStoreBootLoader -- Boot Loader storage
    OBJECT IDENTIFIER ::= { s5ChasComBrdERS4550T-PWRStore 10 }
s5ChasComBrdERS4550T-PWRStoreConfig -- Binary Configuration storage
    OBJECT IDENTIFIER ::= { s5ChasComBrdERS4550T-PWRStore 11 }
s5ChasComBrdERS4550T-PWRStoreSecondaryConfig -- Secondary Binary Configuration storage
    OBJECT IDENTIFIER ::= { s5ChasComBrdERS4550T-PWRStore 12 }
s5ChasComBrdERS4550T-PWRStoreAutoBakupConfig -- Automatic Backup Configuration storage
    OBJECT IDENTIFIER ::= { s5ChasComBrdERS4550T-PWRStore 13 }
s5ChasComBrdERS4550T-PWRStoreReserved -- Portion of total FLASH storage that is reserved
    OBJECT IDENTIFIER ::= { s5ChasComBrdERS4550T-PWRStore 14 }

-- ERS4526FX
s5ChasComBrdERS4526FX
    OBJECT IDENTIFIER ::= { s5ChasComMod 770 }
s5ChasComBrdERS4526FXStore -- storage areas
    OBJECT IDENTIFIER ::= { s5ChasComBrdERS4526FX 0 }
s5ChasComBrdERS4526FXStoreFlash -- FLASH image storage
    OBJECT IDENTIFIER ::= { s5ChasComBrdERS4526FXStore 1 }
s5ChasComBrdERS4526FXStoreBootFW -- Boot Firmware storage
    OBJECT IDENTIFIER ::= { s5ChasComBrdERS4526FXStore 2 }
s5ChasComBrdERS4526FXStoreDram -- DRAM storage
    OBJECT IDENTIFIER ::= { s5ChasComBrdERS4526FXStore 3 }
s5ChasComBrdERS4526FXStoreSecondaryFlash -- Secondary FLASH image storage
    OBJECT IDENTIFIER ::= { s5ChasComBrdERS4526FXStore 5 }
s5ChasComBrdERS4526FXStoreCPLD -- CPLD
    OBJECT IDENTIFIER ::= { s5ChasComBrdERS4526FXStore 6 }
s5ChasComBrdERS4526FXStoreInstalledFW -- Installed FW Version
    OBJECT IDENTIFIER ::= { s5ChasComBrdERS4526FXStore 7 }
s5ChasComBrdERS4526FXStoreOperSW -- Operational Software Version
    OBJECT IDENTIFIER ::= { s5ChasComBrdERS4526FXStore 8 }
s5ChasComBrdERS4526FXStoreTotal -- Total FLASH storage
    OBJECT IDENTIFIER ::= { s5ChasComBrdERS4526FXStore 9 }
s5ChasComBrdERS4526FXStoreBootLoader -- Boot Loader storage
    OBJECT IDENTIFIER ::= { s5ChasComBrdERS4526FXStore 10 }
s5ChasComBrdERS4526FXStoreConfig -- Binary Configuration storage
    OBJECT IDENTIFIER ::= { s5ChasComBrdERS4526FXStore 11 }
s5ChasComBrdERS4526FXStoreSecondaryConfig -- Secondary Binary Configuration storage
    OBJECT IDENTIFIER ::= { s5ChasComBrdERS4526FXStore 12 }
s5ChasComBrdERS4526FXStoreAutoBakupConfig -- Automatic Backup Configuration storage
    OBJECT IDENTIFIER ::= { s5ChasComBrdERS4526FXStore 13 }
s5ChasComBrdERS4526FXStoreReserved -- Portion of total FLASH storage that is reserved
    OBJECT IDENTIFIER ::= { s5ChasComBrdERS4526FXStore 14 }

-- ERS2500-26T
s5ChasComBrdERS2500-26T
    OBJECT IDENTIFIER ::= { s5ChasComMod 771 }
s5ChasComBrdERS2500-26TStore -- storage areas
    OBJECT IDENTIFIER ::= { s5ChasComBrdERS2500-26T 0 }
s5ChasComBrdERS2500-26TStoreFlash -- FLASH image storage
    OBJECT IDENTIFIER ::= { s5ChasComBrdERS2500-26TStore 1 }
s5ChasComBrdERS2500-26TStoreBootFW -- Boot Firmware storage
    OBJECT IDENTIFIER ::= { s5ChasComBrdERS2500-26TStore 2 }
s5ChasComBrdERS2500-26TStoreDram -- DRAM storage
    OBJECT IDENTIFIER ::= { s5ChasComBrdERS2500-26TStore 3 }
s5ChasComBrdERS2500-26TStorePoLFlash -- PoL Flash image storage
    OBJECT IDENTIFIER ::= { s5ChasComBrdERS2500-26TStore 4 }

-- ERS2500-26T-PWR
s5ChasComBrdERS2500-26T-PWR
    OBJECT IDENTIFIER ::= { s5ChasComMod 772 }
s5ChasComBrdERS2500-26T-PWRStore -- storage areas
    OBJECT IDENTIFIER ::= { s5ChasComBrdERS2500-26T-PWR 0 }
s5ChasComBrdERS2500-26T-PWRStoreFlash -- FLASH image storage
    OBJECT IDENTIFIER ::= { s5ChasComBrdERS2500-26T-PWRStore 1 }
s5ChasComBrdERS2500-26T-PWRStoreBootFW -- Boot Firmware storage
    OBJECT IDENTIFIER ::= { s5ChasComBrdERS2500-26T-PWRStore 2 }
s5ChasComBrdERS2500-26T-PWRStoreDram -- DRAM storage
    OBJECT IDENTIFIER ::= { s5ChasComBrdERS2500-26T-PWRStore 3 }
s5ChasComBrdERS2500-26T-PWRStorePoLFlash -- PoL Flash image storage
    OBJECT IDENTIFIER ::= { s5ChasComBrdERS2500-26T-PWRStore 4 }

-- ERS2500-50T
s5ChasComBrdERS2500-50T
    OBJECT IDENTIFIER ::= { s5ChasComMod 773 }
s5ChasComBrdERS2500-50TStore -- storage areas
    OBJECT IDENTIFIER ::= { s5ChasComBrdERS2500-50T 0 }
s5ChasComBrdERS2500-50TStoreFlash -- FLASH image storage
    OBJECT IDENTIFIER ::= { s5ChasComBrdERS2500-50TStore 1 }
s5ChasComBrdERS2500-50TStoreBootFW -- Boot Firmware storage
    OBJECT IDENTIFIER ::= { s5ChasComBrdERS2500-50TStore 2 }
s5ChasComBrdERS2500-50TStoreDram -- DRAM storage
    OBJECT IDENTIFIER ::= { s5ChasComBrdERS2500-50TStore 3 }
s5ChasComBrdERS2500-50TStorePoLFlash -- PoL Flash image storage
    OBJECT IDENTIFIER ::= { s5ChasComBrdERS2500-50TStore 4 }

-- ERS2500-50T-PWR
s5ChasComBrdERS2500-50T-PWR
    OBJECT IDENTIFIER ::= { s5ChasComMod 774 }
s5ChasComBrdERS2500-50T-PWRStore -- storage areas
    OBJECT IDENTIFIER ::= { s5ChasComBrdERS2500-50T-PWR 0 }
s5ChasComBrdERS2500-50T-PWRStoreFlash -- FLASH image storage
    OBJECT IDENTIFIER ::= { s5ChasComBrdERS2500-50T-PWRStore 1 }
s5ChasComBrdERS2500-50T-PWRStoreBootFW -- Boot Firmware storage
    OBJECT IDENTIFIER ::= { s5ChasComBrdERS2500-50T-PWRStore 2 }
s5ChasComBrdERS2500-50T-PWRStoreDram -- DRAM storage
    OBJECT IDENTIFIER ::= { s5ChasComBrdERS2500-50T-PWRStore 3 }
s5ChasComBrdERS2500-50T-PWRStorePoLFlash -- PoL Flash image storage
    OBJECT IDENTIFIER ::= { s5ChasComBrdERS2500-50T-PWRStore 4 }

-- ERS4526GTX-PWR
s5ChasComBrdERS4526GTX-PWR
    OBJECT IDENTIFIER ::= { s5ChasComMod 775 }
s5ChasComBrdERS4526GTX-PWRStore -- storage areas
    OBJECT IDENTIFIER ::= { s5ChasComBrdERS4526GTX-PWR 0 }
s5ChasComBrdERS4526GTX-PWRStoreFlash -- FLASH image storage
    OBJECT IDENTIFIER ::= { s5ChasComBrdERS4526GTX-PWRStore 1 }
s5ChasComBrdERS4526GTX-PWRStoreBootFW -- Boot Firmware storage
    OBJECT IDENTIFIER ::= { s5ChasComBrdERS4526GTX-PWRStore 2 }
s5ChasComBrdERS4526GTX-PWRStoreDram -- DRAM storage
    OBJECT IDENTIFIER ::= { s5ChasComBrdERS4526GTX-PWRStore 3 }
s5ChasComBrdERS4526GTX-PWRStoreSecondaryFlash -- Secondary FLASH image storage
    OBJECT IDENTIFIER ::= { s5ChasComBrdERS4526GTX-PWRStore 5 }
s5ChasComBrdERS4526GTX-PWRStoreCPLD -- CPLD
    OBJECT IDENTIFIER ::= { s5ChasComBrdERS4526GTX-PWRStore 6 }
s5ChasComBrdERS4526GTX-PWRStoreInstalledFW -- Installed FW Version
    OBJECT IDENTIFIER ::= { s5ChasComBrdERS4526GTX-PWRStore 7 }
s5ChasComBrdERS4526GTX-PWRStoreOperSW -- Operational Software Version
    OBJECT IDENTIFIER ::= { s5ChasComBrdERS4526GTX-PWRStore 8 }
s5ChasComBrdERS4526GTX-PWRStoreTotal -- Total FLASH storage
    OBJECT IDENTIFIER ::= { s5ChasComBrdERS4526GTX-PWRStore 9 }
s5ChasComBrdERS4526GTX-PWRStoreBootLoader -- Boot Loader storage
    OBJECT IDENTIFIER ::= { s5ChasComBrdERS4526GTX-PWRStore 10 }
s5ChasComBrdERS4526GTX-PWRStoreConfig -- Binary Configuration storage
    OBJECT IDENTIFIER ::= { s5ChasComBrdERS4526GTX-PWRStore 11 }
s5ChasComBrdERS4526GTX-PWRStoreSecondaryConfig -- Secondary Binary Configuration storage
    OBJECT IDENTIFIER ::= { s5ChasComBrdERS4526GTX-PWRStore 12 }
s5ChasComBrdERS4526GTX-PWRStoreAutoBakupConfig -- Automatic Backup Configuration storage
    OBJECT IDENTIFIER ::= { s5ChasComBrdERS4526GTX-PWRStore 13 }
s5ChasComBrdERS4526GTX-PWRStoreReserved -- Portion of total FLASH storage that is reserved
    OBJECT IDENTIFIER ::= { s5ChasComBrdERS4526GTX-PWRStore 14 }

-- ERS4526GTX
s5ChasComBrdERS4526GTX
    OBJECT IDENTIFIER ::= { s5ChasComMod 776 }
s5ChasComBrdERS4526GTXStore -- storage areas
    OBJECT IDENTIFIER ::= { s5ChasComBrdERS4526GTX 0 }
s5ChasComBrdERS4526GTXStoreFlash -- FLASH image storage
    OBJECT IDENTIFIER ::= { s5ChasComBrdERS4526GTXStore 1 }
s5ChasComBrdERS4526GTXStoreBootFW -- Boot Firmware storage
    OBJECT IDENTIFIER ::= { s5ChasComBrdERS4526GTXStore 2 }
s5ChasComBrdERS4526GTXStoreDram -- DRAM storage
    OBJECT IDENTIFIER ::= { s5ChasComBrdERS4526GTXStore 3 }
s5ChasComBrdERS4526GTXStoreSecondaryFlash -- Secondary FLASH image storage
    OBJECT IDENTIFIER ::= { s5ChasComBrdERS4526GTXStore 5 }
s5ChasComBrdERS4526GTXStoreCPLD -- CPLD
    OBJECT IDENTIFIER ::= { s5ChasComBrdERS4526GTXStore 6 }
s5ChasComBrdERS4526GTXStoreInstalledFW -- Installed FW Version
    OBJECT IDENTIFIER ::= { s5ChasComBrdERS4526GTXStore 7 }
s5ChasComBrdERS4526GTXStoreOperSW -- Operational Software Version
    OBJECT IDENTIFIER ::= { s5ChasComBrdERS4526GTXStore 8 }
s5ChasComBrdERS4526GTXStoreTotal -- Total FLASH storage
    OBJECT IDENTIFIER ::= { s5ChasComBrdERS4526GTXStore 9 }
s5ChasComBrdERS4526GTXStoreBootLoader -- Boot Loader storage
    OBJECT IDENTIFIER ::= { s5ChasComBrdERS4526GTXStore 10 }
s5ChasComBrdERS4526GTXStoreConfig -- Binary Configuration storage
    OBJECT IDENTIFIER ::= { s5ChasComBrdERS4526GTXStore 11 }
s5ChasComBrdERS4526GTXStoreSecondaryConfig -- Secondary Binary Configuration storage
    OBJECT IDENTIFIER ::= { s5ChasComBrdERS4526GTXStore 12 }
s5ChasComBrdERS4526GTXStoreAutoBakupConfig -- Automatic Backup Configuration storage
    OBJECT IDENTIFIER ::= { s5ChasComBrdERS4526GTXStore 13 }
s5ChasComBrdERS4526GTXStoreReserved -- Portion of total FLASH storage that is reserved
    OBJECT IDENTIFIER ::= { s5ChasComBrdERS4526GTXStore 14 }

-- ERS4524GT
s5ChasComBrdERS4524GT
    OBJECT IDENTIFIER ::= { s5ChasComMod 777 }
s5ChasComBrdERS4524GTStore -- storage areas
    OBJECT IDENTIFIER ::= { s5ChasComBrdERS4524GT 0 }
s5ChasComBrdERS4524GTStoreFlash -- FLASH image storage
    OBJECT IDENTIFIER ::= { s5ChasComBrdERS4524GTStore 1 }
s5ChasComBrdERS4524GTStoreBootFW -- Boot Firmware storage
    OBJECT IDENTIFIER ::= { s5ChasComBrdERS4524GTStore 2 }
s5ChasComBrdERS4524GTStoreDram -- DRAM storage
    OBJECT IDENTIFIER ::= { s5ChasComBrdERS4524GTStore 3 }
s5ChasComBrdERS4524GTStoreSecondaryFlash -- Secondary FLASH image storage
    OBJECT IDENTIFIER ::= { s5ChasComBrdERS4524GTStore 5 }
s5ChasComBrdERS4524GTStoreCPLD -- CPLD
    OBJECT IDENTIFIER ::= { s5ChasComBrdERS4524GTStore 6 }
s5ChasComBrdERS4524GTStoreInstalledFW -- Installed FW Version
    OBJECT IDENTIFIER ::= { s5ChasComBrdERS4524GTStore 7 }
s5ChasComBrdERS4524GTStoreOperSW -- Operational Software Version
    OBJECT IDENTIFIER ::= { s5ChasComBrdERS4524GTStore 8 }
s5ChasComBrdERS4524GTStoreTotal -- Total FLASH storage
    OBJECT IDENTIFIER ::= { s5ChasComBrdERS4524GTStore 9 }
s5ChasComBrdERS4524GTStoreBootLoader -- Boot Loader storage
    OBJECT IDENTIFIER ::= { s5ChasComBrdERS4524GTStore 10 }
s5ChasComBrdERS4524GTStoreConfig -- Binary Configuration storage
    OBJECT IDENTIFIER ::= { s5ChasComBrdERS4524GTStore 11 }
s5ChasComBrdERS4524GTStoreSecondaryConfig -- Secondary Binary Configuration storage
    OBJECT IDENTIFIER ::= { s5ChasComBrdERS4524GTStore 12 }
s5ChasComBrdERS4524GTStoreAutoBakupConfig -- Automatic Backup Configuration storage
    OBJECT IDENTIFIER ::= { s5ChasComBrdERS4524GTStore 13 }
s5ChasComBrdERS4524GTStoreReserved -- Portion of total FLASH storage that is reserved
    OBJECT IDENTIFIER ::= { s5ChasComBrdERS4524GTStore 14 }

-- ERS4526T
s5ChasComBrdERS4526T
    OBJECT IDENTIFIER ::= { s5ChasComMod 778 }
s5ChasComBrdERS4526TStore -- storage areas
    OBJECT IDENTIFIER ::= { s5ChasComBrdERS4526T 0 }
s5ChasComBrdERS4526TStoreFlash -- FLASH image storage
    OBJECT IDENTIFIER ::= { s5ChasComBrdERS4526TStore 1 }
s5ChasComBrdERS4526TStoreBootFW -- Boot Firmware storage
    OBJECT IDENTIFIER ::= { s5ChasComBrdERS4526TStore 2 }
s5ChasComBrdERS4526TStoreDram -- DRAM storage
    OBJECT IDENTIFIER ::= { s5ChasComBrdERS4526TStore 3 }
s5ChasComBrdERS4526TStoreSecondaryFlash -- Secondary FLASH image storage
    OBJECT IDENTIFIER ::= { s5ChasComBrdERS4526TStore 5 }
s5ChasComBrdERS4526TStoreCPLD -- CPLD
    OBJECT IDENTIFIER ::= { s5ChasComBrdERS4526TStore 6 }
s5ChasComBrdERS4526TStoreInstalledFW -- Installed FW Version
    OBJECT IDENTIFIER ::= { s5ChasComBrdERS4526TStore 7 }
s5ChasComBrdERS4526TStoreOperSW -- Operational Software Version
    OBJECT IDENTIFIER ::= { s5ChasComBrdERS4526TStore 8 }
s5ChasComBrdERS4526TStoreTotal -- Total FLASH storage
    OBJECT IDENTIFIER ::= { s5ChasComBrdERS4526TStore 9 }
s5ChasComBrdERS4526TStoreBootLoader -- Boot Loader storage
    OBJECT IDENTIFIER ::= { s5ChasComBrdERS4526TStore 10 }
s5ChasComBrdERS4526TStoreConfig -- Binary Configuration storage
    OBJECT IDENTIFIER ::= { s5ChasComBrdERS4526TStore 11 }
s5ChasComBrdERS4526TStoreSecondaryConfig -- Secondary Binary Configuration storage
    OBJECT IDENTIFIER ::= { s5ChasComBrdERS4526TStore 12 }
s5ChasComBrdERS4526TStoreAutoBakupConfig -- Automatic Backup Configuration storage
    OBJECT IDENTIFIER ::= { s5ChasComBrdERS4526TStore 13 }
s5ChasComBrdERS4526TStoreReserved -- Portion of total FLASH storage that is reserved
    OBJECT IDENTIFIER ::= { s5ChasComBrdERS4526TStore 14 }

-- ERS4526T-PWR
s5ChasComBrdERS4526T-PWR
    OBJECT IDENTIFIER ::= { s5ChasComMod 779 }
s5ChasComBrdERS4526T-PWRStore -- storage areas
    OBJECT IDENTIFIER ::= { s5ChasComBrdERS4526T-PWR 0 }
s5ChasComBrdERS4526T-PWRStoreFlash -- FLASH image storage
    OBJECT IDENTIFIER ::= { s5ChasComBrdERS4526T-PWRStore 1 }
s5ChasComBrdERS4526T-PWRStoreBootFW -- Boot Firmware storage
    OBJECT IDENTIFIER ::= { s5ChasComBrdERS4526T-PWRStore 2 }
s5ChasComBrdERS4526T-PWRStoreDram -- DRAM storage
    OBJECT IDENTIFIER ::= { s5ChasComBrdERS4526T-PWRStore 3 }
s5ChasComBrdERS4526T-PWRStoreSecondaryFlash -- Secondary FLASH image storage
    OBJECT IDENTIFIER ::= { s5ChasComBrdERS4526T-PWRStore 5 }
s5ChasComBrdERS4526T-PWRStoreCPLD -- CPLD
    OBJECT IDENTIFIER ::= { s5ChasComBrdERS4526T-PWRStore 6 }
s5ChasComBrdERS4526T-PWRStoreInstalledFW -- Installed FW Version
    OBJECT IDENTIFIER ::= { s5ChasComBrdERS4526T-PWRStore 7 }
s5ChasComBrdERS4526T-PWRStoreOperSW -- Operational Software Version
    OBJECT IDENTIFIER ::= { s5ChasComBrdERS4526T-PWRStore 8 }
s5ChasComBrdERS4526T-PWRStoreTotal -- Total FLASH storage
    OBJECT IDENTIFIER ::= { s5ChasComBrdERS4526T-PWRStore 9 }
s5ChasComBrdERS4526T-PWRStoreBootLoader -- Boot Loader storage
    OBJECT IDENTIFIER ::= { s5ChasComBrdERS4526T-PWRStore 10 }
s5ChasComBrdERS4526T-PWRStoreConfig -- Binary Configuration storage
    OBJECT IDENTIFIER ::= { s5ChasComBrdERS4526T-PWRStore 11 }
s5ChasComBrdERS4526T-PWRStoreSecondaryConfig -- Secondary Binary Configuration storage
    OBJECT IDENTIFIER ::= { s5ChasComBrdERS4526T-PWRStore 12 }
s5ChasComBrdERS4526T-PWRStoreAutoBakupConfig -- Automatic Backup Configuration storage
    OBJECT IDENTIFIER ::= { s5ChasComBrdERS4526T-PWRStore 13 }
s5ChasComBrdERS4526T-PWRStoreReserved -- Portion of total FLASH storage that is reserved
    OBJECT IDENTIFIER ::= { s5ChasComBrdERS4526T-PWRStore 14 }

-- USB registrations
s5ChasComBrdUsb OBJECT IDENTIFIER ::= { s5ChasComMod 780 }
s5ChasComBrdUsb-None   OBJECT IDENTIFIER ::= { s5ChasComBrdUsb 1 }
s5ChasComBrdUsb-Flash  OBJECT IDENTIFIER ::= { s5ChasComBrdUsb 2 }

-- ERS5698-TFD-PWR
s5ChasComBrdERS5698-TFD-PWR
    OBJECT IDENTIFIER ::= { s5ChasComMod 781 }
s5ChasComBrdERS5698-TFD-PWRStore -- storage areas
    OBJECT IDENTIFIER ::= { s5ChasComBrdERS5698-TFD-PWR 0 }
s5ChasComBrdERS5698-TFD-PWRStoreFlash -- FLASH image storage
    OBJECT IDENTIFIER ::= { s5ChasComBrdERS5698-TFD-PWRStore 1 }
s5ChasComBrdERS5698-TFD-PWRStoreBootFW -- Boot Firmware storage
    OBJECT IDENTIFIER ::= { s5ChasComBrdERS5698-TFD-PWRStore 2 }
s5ChasComBrdERS5698-TFD-PWRStoreDram -- DRAM storage
    OBJECT IDENTIFIER ::= { s5ChasComBrdERS5698-TFD-PWRStore 3 }
s5ChasComBrdERS5698-TFD-PWRStorePol -- POL Firmware storage
    OBJECT IDENTIFIER ::= { s5ChasComBrdERS5698-TFD-PWRStore 4 }
s5ChasComBrdERS5698-TFD-PWRStoreSecondaryFlash -- Secondary FLASH image storage
    OBJECT IDENTIFIER ::= { s5ChasComBrdERS5698-TFD-PWRStore 5 }

-- ERS5698-TFD
s5ChasComBrdERS5698-TFD
    OBJECT IDENTIFIER ::= { s5ChasComMod 782 }
s5ChasComBrdERS5698-TFDStore -- storage areas
    OBJECT IDENTIFIER ::= { s5ChasComBrdERS5698-TFD 0 }
s5ChasComBrdERS5698-TFDStoreFlash -- FLASH image storage
    OBJECT IDENTIFIER ::= { s5ChasComBrdERS5698-TFDStore 1 }
s5ChasComBrdERS5698-TFDStoreBootFW -- Boot Firmware storage
    OBJECT IDENTIFIER ::= { s5ChasComBrdERS5698-TFDStore 2 }
s5ChasComBrdERS5698-TFDStoreDram -- DRAM storage
    OBJECT IDENTIFIER ::= { s5ChasComBrdERS5698-TFDStore 3 }
s5ChasComBrdERS5698-TFDStoreSecondaryFlash -- Secondary FLASH image storage
    OBJECT IDENTIFIER ::= { s5ChasComBrdERS5698-TFDStore 5 }

-- ERS5650-TD-PWR
s5ChasComBrdERS5650-TD-PWR
    OBJECT IDENTIFIER ::= { s5ChasComMod 783 }
s5ChasComBrdERS5650-TD-PWRStore -- storage areas
    OBJECT IDENTIFIER ::= { s5ChasComBrdERS5650-TD-PWR 0 }
s5ChasComBrdERS5650-TD-PWRStoreFlash -- FLASH image storage
    OBJECT IDENTIFIER ::= { s5ChasComBrdERS5650-TD-PWRStore 1 }
s5ChasComBrdERS5650-TD-PWRStoreBootFW -- Boot Firmware storage
    OBJECT IDENTIFIER ::= { s5ChasComBrdERS5650-TD-PWRStore 2 }
s5ChasComBrdERS5650-TD-PWRStoreDram -- DRAM storage
    OBJECT IDENTIFIER ::= { s5ChasComBrdERS5650-TD-PWRStore 3 }
s5ChasComBrdERS5650-TD-PWRStorePol -- POL Firmware storage
    OBJECT IDENTIFIER ::= { s5ChasComBrdERS5650-TD-PWRStore 4 }
s5ChasComBrdERS5650-TD-PWRStoreSecondaryFlash -- Secondary FLASH image storage
    OBJECT IDENTIFIER ::= { s5ChasComBrdERS5650-TD-PWRStore 5 }

-- ERS5650-TD
s5ChasComBrdERS5650-TD
    OBJECT IDENTIFIER ::= { s5ChasComMod 784 }
s5ChasComBrdERS5650-TDStore -- storage areas
    OBJECT IDENTIFIER ::= { s5ChasComBrdERS5650-TD 0 }
s5ChasComBrdERS5650-TDStoreFlash -- FLASH image storage
    OBJECT IDENTIFIER ::= { s5ChasComBrdERS5650-TDStore 1 }
s5ChasComBrdERS5650-TDStoreBootFW -- Boot Firmware storage
    OBJECT IDENTIFIER ::= { s5ChasComBrdERS5650-TDStore 2 }
s5ChasComBrdERS5650-TDStoreDram -- DRAM storage
    OBJECT IDENTIFIER ::= { s5ChasComBrdERS5650-TDStore 3 }
s5ChasComBrdERS5650-TDStoreSecondaryFlash -- Secondary FLASH image storage
    OBJECT IDENTIFIER ::= { s5ChasComBrdERS5650-TDStore 5 }

-- ERS5632-FD
s5ChasComBrdERS5632-FD
    OBJECT IDENTIFIER ::= { s5ChasComMod 785 }
s5ChasComBrdERS5632-FDStore -- storage areas
    OBJECT IDENTIFIER ::= { s5ChasComBrdERS5632-FD 0 }
s5ChasComBrdERS5632-FDStoreFlash -- FLASH image storage
    OBJECT IDENTIFIER ::= { s5ChasComBrdERS5632-FDStore 1 }
s5ChasComBrdERS5632-FDStoreBootFW -- Boot Firmware storage
    OBJECT IDENTIFIER ::= { s5ChasComBrdERS5632-FDStore 2 }
s5ChasComBrdERS5632-FDStoreDram -- DRAM storage
    OBJECT IDENTIFIER ::= { s5ChasComBrdERS5632-FDStore 3 }
s5ChasComBrdERS5632-FDStoreSecondaryFlash -- Secondary FLASH image storage
    OBJECT IDENTIFIER ::= { s5ChasComBrdERS5632-FDStore 5 }

-- ESU1860S
s5ChasComBrdESU1860S
    OBJECT IDENTIFIER ::= { s5ChasComMod 786 }
s5ChasComBrdESU1860SStore -- storage areas
    OBJECT IDENTIFIER ::= { s5ChasComBrdESU1860S 0 }
s5ChasComBrdESU1860SStoreFlash -- FLASH image storage
    OBJECT IDENTIFIER ::= { s5ChasComBrdESU1860SStore 1 }
s5ChasComBrdESU1860SStoreBootFW -- Boot Firmware storage
    OBJECT IDENTIFIER ::= { s5ChasComBrdESU1860SStore 2 }
s5ChasComBrdESU1860SStoreDram -- DRAM storage
    OBJECT IDENTIFIER ::= { s5ChasComBrdESU1860SStore 3 }
s5ChasComBrdESU1860SStoreSecondaryFlash -- Secondary FLASH image storage
    OBJECT IDENTIFIER ::= { s5ChasComBrdESU1860SStore 5 }
s5ChasComBrdESU1860SStoreCpld -- HW CPLD
    OBJECT IDENTIFIER ::= { s5ChasComBrdESU1860SStore 6 }

-- ESU1860B
s5ChasComBrdESU1860B
    OBJECT IDENTIFIER ::= { s5ChasComMod 787 }
s5ChasComBrdESU1860BStore -- storage areas
    OBJECT IDENTIFIER ::= { s5ChasComBrdESU1860B 0 }
s5ChasComBrdESU1860BStoreFlash -- FLASH image storage
    OBJECT IDENTIFIER ::= { s5ChasComBrdESU1860BStore 1 }
s5ChasComBrdESU1860BStoreBootFW -- Boot Firmware storage
    OBJECT IDENTIFIER ::= { s5ChasComBrdESU1860BStore 2 }
s5ChasComBrdESU1860BStoreDram -- DRAM storage
    OBJECT IDENTIFIER ::= { s5ChasComBrdESU1860BStore 3 }
s5ChasComBrdESU1860BStoreSecondaryFlash -- Secondary FLASH image storage
    OBJECT IDENTIFIER ::= { s5ChasComBrdESU1860BStore 5 }
s5ChasComBrdESU1860BStoreCpld -- HW CPLD
    OBJECT IDENTIFIER ::= { s5ChasComBrdESU1860BStore 6 }

-- ESU1860T
s5ChasComBrdESU1860T
    OBJECT IDENTIFIER ::= { s5ChasComMod 788 }
s5ChasComBrdESU1860TStore -- storage areas
    OBJECT IDENTIFIER ::= { s5ChasComBrdESU1860T 0 }
s5ChasComBrdESU1860TStoreFlash -- FLASH image storage
    OBJECT IDENTIFIER ::= { s5ChasComBrdESU1860TStore 1 }
s5ChasComBrdESU1860TStoreBootFW -- Boot Firmware storage
    OBJECT IDENTIFIER ::= { s5ChasComBrdESU1860TStore 2 }
s5ChasComBrdESU1860TStoreDram -- DRAM storage
    OBJECT IDENTIFIER ::= { s5ChasComBrdESU1860TStore 3 }
s5ChasComBrdESU1860TStoreSecondaryFlash -- Secondary FLASH image storage
    OBJECT IDENTIFIER ::= { s5ChasComBrdESU1860TStore 5 }
s5ChasComBrdESU1860TStoreCpld -- HW CPLD
    OBJECT IDENTIFIER ::= { s5ChasComBrdESU1860TStore 6 }

-- ESU1860V
s5ChasComBrdESU1860V
    OBJECT IDENTIFIER ::= { s5ChasComMod 789 }
s5ChasComBrdESU1860VStore -- storage areas
    OBJECT IDENTIFIER ::= { s5ChasComBrdESU1860V 0 }
s5ChasComBrdESU1860VStoreFlash -- FLASH image storage
    OBJECT IDENTIFIER ::= { s5ChasComBrdESU1860VStore 1 }
s5ChasComBrdESU1860VStoreBootFW -- Boot Firmware storage
    OBJECT IDENTIFIER ::= { s5ChasComBrdESU1860VStore 2 }
s5ChasComBrdESU1860VStoreDram -- DRAM storage
    OBJECT IDENTIFIER ::= { s5ChasComBrdESU1860VStore 3 }
s5ChasComBrdESU1860VStoreSecondaryFlash -- Secondary FLASH image storage
    OBJECT IDENTIFIER ::= { s5ChasComBrdESU1860VStore 5 }
s5ChasComBrdESU1860VStoreCpld -- HW CPLD
    OBJECT IDENTIFIER ::= { s5ChasComBrdESU1860VStore 6 }

-- ESU1880S
s5ChasComBrdESU1880S
    OBJECT IDENTIFIER ::= { s5ChasComMod 790 }
s5ChasComBrdESU1880SStore -- storage areas
    OBJECT IDENTIFIER ::= { s5ChasComBrdESU1880S 0 }
s5ChasComBrdESU1880SStoreFlash -- FLASH image storage
    OBJECT IDENTIFIER ::= { s5ChasComBrdESU1880SStore 1 }
s5ChasComBrdESU1880SStoreBootFW -- Boot Firmware storage
    OBJECT IDENTIFIER ::= { s5ChasComBrdESU1880SStore 2 }
s5ChasComBrdESU1880SStoreDram -- DRAM storage
    OBJECT IDENTIFIER ::= { s5ChasComBrdESU1880SStore 3 }
s5ChasComBrdESU1880SStoreSecondaryFlash -- Secondary FLASH image storage
    OBJECT IDENTIFIER ::= { s5ChasComBrdESU1880SStore 5 }
s5ChasComBrdESU1880SStoreCpld -- HW CPLD
    OBJECT IDENTIFIER ::= { s5ChasComBrdESU1880SStore 6 }

-- 2 port 1000BASE Combo Module MDA
s5ChasComBrdESU1860-2TX-FX
    OBJECT IDENTIFIER ::= { s5ChasComMod 791 }

-- 2-Port Stacking Module MDA
s5ChasComBrdESU1880-2ST
    OBJECT IDENTIFIER ::= { s5ChasComMod 792 }

-- Daisy-Chain Module MDA
s5ChasComBrdESU1880-2DC
    OBJECT IDENTIFIER ::= { s5ChasComMod 793 }

-- 2-Port 10Gigabit XFP Module MDA
s5ChasComBrdESU1880-2XFP
    OBJECT IDENTIFIER ::= { s5ChasComMod 794 }

-- ERS4524GT-PWR
s5ChasComBrdERS4524GT-PWR
    OBJECT IDENTIFIER ::= { s5ChasComMod 795 }
s5ChasComBrdERS4524GT-PWRStore -- storage areas
    OBJECT IDENTIFIER ::= { s5ChasComBrdERS4524GT-PWR 0 }
s5ChasComBrdERS4524GT-PWRStoreFlash -- FLASH image storage
    OBJECT IDENTIFIER ::= { s5ChasComBrdERS4524GT-PWRStore 1 }
s5ChasComBrdERS4524GT-PWRStoreBootFW -- Boot Firmware storage
    OBJECT IDENTIFIER ::= { s5ChasComBrdERS4524GT-PWRStore 2 }
s5ChasComBrdERS4524GT-PWRStoreDram -- DRAM storage
    OBJECT IDENTIFIER ::= { s5ChasComBrdERS4524GT-PWRStore 3 }
s5ChasComBrdERS4524GT-PWRStoreSecondaryFlash -- Secondary FLASH image storage
    OBJECT IDENTIFIER ::= { s5ChasComBrdERS4524GT-PWRStore 5 }
s5ChasComBrdERS4524GT-PWRStoreCPLD -- CPLD
    OBJECT IDENTIFIER ::= { s5ChasComBrdERS4524GT-PWRStore 6 }
s5ChasComBrdERS4524GT-PWRStoreInstalledFW -- Installed FW Version
    OBJECT IDENTIFIER ::= { s5ChasComBrdERS4524GT-PWRStore 7 }
s5ChasComBrdERS4524GT-PWRStoreOperSW -- Operational Software Version
    OBJECT IDENTIFIER ::= { s5ChasComBrdERS4524GT-PWRStore 8 }
s5ChasComBrdERS4524GT-PWRStoreTotal -- Total FLASH storage
    OBJECT IDENTIFIER ::= { s5ChasComBrdERS4524GT-PWRStore 9 }
s5ChasComBrdERS4524GT-PWRStoreBootLoader -- Boot Loader storage
    OBJECT IDENTIFIER ::= { s5ChasComBrdERS4524GT-PWRStore 10 }
s5ChasComBrdERS4524GT-PWRStoreConfig -- Binary Configuration storage
    OBJECT IDENTIFIER ::= { s5ChasComBrdERS4524GT-PWRStore 11 }
s5ChasComBrdERS4524GT-PWRStoreSecondaryConfig -- Secondary Binary Configuration storage
    OBJECT IDENTIFIER ::= { s5ChasComBrdERS4524GT-PWRStore 12 }
s5ChasComBrdERS4524GT-PWRStoreAutoBakupConfig -- Automatic Backup Configuration storage
    OBJECT IDENTIFIER ::= { s5ChasComBrdERS4524GT-PWRStore 13 }
s5ChasComBrdERS4524GT-PWRStoreReserved -- Portion of total FLASH storage that is reserved
    OBJECT IDENTIFIER ::= { s5ChasComBrdERS4524GT-PWRStore 14 }

-- ERS6628XSGT
s5ChasComBrdERS6628XSGT
    OBJECT IDENTIFIER ::= { s5ChasComMod 796 }
s5ChasComBrdERS6628XSGTStore -- storage areas
    OBJECT IDENTIFIER ::= { s5ChasComBrdERS6628XSGT 0 }
s5ChasComBrdERS6628XSGTStoreFlash -- FLASH image storage
    OBJECT IDENTIFIER ::= { s5ChasComBrdERS6628XSGTStore 1 }
s5ChasComBrdERS6628XSGTStoreBootFW -- Boot Firmware storage
    OBJECT IDENTIFIER ::= { s5ChasComBrdERS6628XSGTStore 2 }
s5ChasComBrdERS6628XSGTStoreDram -- DRAM storage
    OBJECT IDENTIFIER ::= { s5ChasComBrdERS6628XSGTStore 3 }
s5ChasComBrdERS6628XSGTStoreSecondaryFlash -- Secondary FLASH image storage
    OBJECT IDENTIFIER ::= { s5ChasComBrdERS6628XSGTStore 5 }

-- ERS6632XTS
s5ChasComBrdERS6632XTS
    OBJECT IDENTIFIER ::= { s5ChasComMod 797 }
s5ChasComBrdERS6632XTSStore -- storage areas
    OBJECT IDENTIFIER ::= { s5ChasComBrdERS6632XTS 0 }
s5ChasComBrdERS6632XTSStoreFlash -- FLASH image storage
    OBJECT IDENTIFIER ::= { s5ChasComBrdERS6632XTSStore 1 }
s5ChasComBrdERS6632XTSStoreBootFW -- Boot Firmware storage
    OBJECT IDENTIFIER ::= { s5ChasComBrdERS6632XTSStore 2 }
s5ChasComBrdERS6632XTSStoreDram -- DRAM storage
    OBJECT IDENTIFIER ::= { s5ChasComBrdERS6632XTSStore 3 }
s5ChasComBrdERS6632XTSStoreSecondaryFlash -- Secondary FLASH image storage
    OBJECT IDENTIFIER ::= { s5ChasComBrdERS6632XTSStore 5 }

-- WC8180
s5ChasComBrdWC8180
    OBJECT IDENTIFIER ::= { s5ChasComMod 798 }
s5ChasComBrdWC8180Store -- storage areas
    OBJECT IDENTIFIER ::= { s5ChasComBrdWC8180 0 }
s5ChasComBrdWC8180StoreFlash -- FLASH image storage
    OBJECT IDENTIFIER ::= { s5ChasComBrdWC8180Store 1 }
s5ChasComBrdWC8180StoreBootFW -- Boot Firmware storage
    OBJECT IDENTIFIER ::= { s5ChasComBrdWC8180Store 2 }
s5ChasComBrdWC8180StoreDram -- DRAM storage
    OBJECT IDENTIFIER ::= { s5ChasComBrdWC8180Store 3 }
s5ChasComBrdWC8180StoreSecondaryFlash -- Secondary FLASH image storage
    OBJECT IDENTIFIER ::= { s5ChasComBrdWC8180Store 5 }

-- ERS4526T-PWR+
s5ChasComBrdERS4526T-PWR-PLUS
    OBJECT IDENTIFIER ::= { s5ChasComMod 799 }
s5ChasComBrdERS4526T-PWR-PLUSStore -- storage areas
    OBJECT IDENTIFIER ::= { s5ChasComBrdERS4526T-PWR-PLUS 0 }
s5ChasComBrdERS4526T-PWR-PLUSStoreFlash -- FLASH image storage
    OBJECT IDENTIFIER ::= { s5ChasComBrdERS4526T-PWR-PLUSStore 1 }
s5ChasComBrdERS4526T-PWR-PLUSStoreBootFW -- Boot Firmware storage
    OBJECT IDENTIFIER ::= { s5ChasComBrdERS4526T-PWR-PLUSStore 2 }
s5ChasComBrdERS4526T-PWR-PLUSStoreDram -- DRAM storage
    OBJECT IDENTIFIER ::= { s5ChasComBrdERS4526T-PWR-PLUSStore 3 }
s5ChasComBrdERS4526T-PWR-PLUSStoreSecondaryFlash -- Secondary FLASH image storage
    OBJECT IDENTIFIER ::= { s5ChasComBrdERS4526T-PWR-PLUSStore 5 }
s5ChasComBrdERS4526T-PWR-PLUSStoreCPLD -- CPLD
    OBJECT IDENTIFIER ::= { s5ChasComBrdERS4526T-PWR-PLUSStore 6 }
s5ChasComBrdERS4526T-PWR-PLUSStoreInstalledFW -- Installed FW Version
    OBJECT IDENTIFIER ::= { s5ChasComBrdERS4526T-PWR-PLUSStore 7 }
s5ChasComBrdERS4526T-PWR-PLUSStoreOperSW -- Operational Software Version
    OBJECT IDENTIFIER ::= { s5ChasComBrdERS4526T-PWR-PLUSStore 8 }
s5ChasComBrdERS4526T-PWR-PLUSStoreTotal -- Total FLASH storage
    OBJECT IDENTIFIER ::= { s5ChasComBrdERS4526T-PWR-PLUSStore 9 }
s5ChasComBrdERS4526T-PWR-PLUSStoreBootLoader -- Boot Loader storage
    OBJECT IDENTIFIER ::= { s5ChasComBrdERS4526T-PWR-PLUSStore 10 }
s5ChasComBrdERS4526T-PWR-PLUSStoreConfig -- Binary Configuration storage
    OBJECT IDENTIFIER ::= { s5ChasComBrdERS4526T-PWR-PLUSStore 11 }
s5ChasComBrdERS4526T-PWR-PLUSStoreSecondaryConfig -- Secondary Binary Configuration storage
    OBJECT IDENTIFIER ::= { s5ChasComBrdERS4526T-PWR-PLUSStore 12 }
s5ChasComBrdERS4526T-PWR-PLUSStoreAutoBakupConfig -- Automatic Backup Configuration storage
    OBJECT IDENTIFIER ::= { s5ChasComBrdERS4526T-PWR-PLUSStore 13 }
s5ChasComBrdERS4526T-PWR-PLUSStoreReserved -- Portion of total FLASH storage that is reserved
    OBJECT IDENTIFIER ::= { s5ChasComBrdERS4526T-PWR-PLUSStore 14 }

-- ERS4550T-PWR+
s5ChasComBrdERS4550T-PWR-PLUS
    OBJECT IDENTIFIER ::= { s5ChasComMod 800 }
s5ChasComBrdERS4550T-PWR-PLUSStore -- storage areas
    OBJECT IDENTIFIER ::= { s5ChasComBrdERS4550T-PWR-PLUS 0 }
s5ChasComBrdERS4550T-PWR-PLUSStoreFlash -- FLASH image storage
    OBJECT IDENTIFIER ::= { s5ChasComBrdERS4550T-PWR-PLUSStore 1 }
s5ChasComBrdERS4550T-PWR-PLUSStoreBootFW -- Boot Firmware storage
    OBJECT IDENTIFIER ::= { s5ChasComBrdERS4550T-PWR-PLUSStore 2 }
s5ChasComBrdERS4550T-PWR-PLUSStoreDram -- DRAM storage
    OBJECT IDENTIFIER ::= { s5ChasComBrdERS4550T-PWR-PLUSStore 3 }
s5ChasComBrdERS4550T-PWR-PLUSStorePoLFlash -- PoL Flash image storage
    OBJECT IDENTIFIER ::= { s5ChasComBrdERS4550T-PWR-PLUSStore 4 }
s5ChasComBrdERS4550T-PWR-PLUSStoreSecondaryFlash -- Secondary FLASH image storage
    OBJECT IDENTIFIER ::= { s5ChasComBrdERS4550T-PWR-PLUSStore 5 }
s5ChasComBrdERS4550T-PWR-PLUSStoreCPLD -- CPLD
    OBJECT IDENTIFIER ::= { s5ChasComBrdERS4550T-PWR-PLUSStore 6 }
s5ChasComBrdERS4550T-PWR-PLUSStoreInstalledFW -- Installed FW Version
    OBJECT IDENTIFIER ::= { s5ChasComBrdERS4550T-PWR-PLUSStore 7 }
s5ChasComBrdERS4550T-PWR-PLUSStoreOperSW -- Operational Software Version
    OBJECT IDENTIFIER ::= { s5ChasComBrdERS4550T-PWR-PLUSStore 8 }
s5ChasComBrdERS4550T-PWR-PLUSStoreTotal -- Total FLASH storage
    OBJECT IDENTIFIER ::= { s5ChasComBrdERS4550T-PWR-PLUSStore 9 }
s5ChasComBrdERS4550T-PWR-PLUSStoreBootLoader -- Boot Loader storage
    OBJECT IDENTIFIER ::= { s5ChasComBrdERS4550T-PWR-PLUSStore 10 }
s5ChasComBrdERS4550T-PWR-PLUSStoreConfig -- Binary Configuration storage
    OBJECT IDENTIFIER ::= { s5ChasComBrdERS4550T-PWR-PLUSStore 11 }
s5ChasComBrdERS4550T-PWR-PLUSStoreSecondaryConfig -- Secondary Binary Configuration storage
    OBJECT IDENTIFIER ::= { s5ChasComBrdERS4550T-PWR-PLUSStore 12 }
s5ChasComBrdERS4550T-PWR-PLUSStoreAutoBakupConfig -- Automatic Backup Configuration storage
    OBJECT IDENTIFIER ::= { s5ChasComBrdERS4550T-PWR-PLUSStore 13 }
s5ChasComBrdERS4550T-PWR-PLUSStoreReserved -- Portion of total FLASH storage that is reserved
    OBJECT IDENTIFIER ::= { s5ChasComBrdERS4550T-PWR-PLUSStore 14 }

-- ERS4826GTS-PWR+
s5ChasComBrdERS4826GTS-PWR-PLUS
    OBJECT IDENTIFIER ::= { s5ChasComMod 801 }
s5ChasComBrdERS4826GTS-PWR-PLUSStore -- storage areas
    OBJECT IDENTIFIER ::= { s5ChasComBrdERS4826GTS-PWR-PLUS 0 }
s5ChasComBrdERS4826GTS-PWR-PLUSStoreFlash -- FLASH image storage
    OBJECT IDENTIFIER ::= { s5ChasComBrdERS4826GTS-PWR-PLUSStore 1 }
s5ChasComBrdERS4826GTS-PWR-PLUSStoreBootFW -- Boot Firmware storage
    OBJECT IDENTIFIER ::= { s5ChasComBrdERS4826GTS-PWR-PLUSStore 2 }
s5ChasComBrdERS4826GTS-PWR-PLUSStoreDram -- DRAM storage
    OBJECT IDENTIFIER ::= { s5ChasComBrdERS4826GTS-PWR-PLUSStore 3 }
s5ChasComBrdERS4826GTS-PWR-PLUSStoreSecondaryFlash -- Secondary FLASH image storage
    OBJECT IDENTIFIER ::= { s5ChasComBrdERS4826GTS-PWR-PLUSStore 5 }
s5ChasComBrdERS4826GTS-PWR-PLUSStoreCPLD -- CPLD
    OBJECT IDENTIFIER ::= { s5ChasComBrdERS4826GTS-PWR-PLUSStore 6 }
s5ChasComBrdERS4826GTS-PWR-PLUSStoreInstalledFW -- Installed FW Version
    OBJECT IDENTIFIER ::= { s5ChasComBrdERS4826GTS-PWR-PLUSStore 7 }
s5ChasComBrdERS4826GTS-PWR-PLUSStoreOperSW -- Operational Software Version
    OBJECT IDENTIFIER ::= { s5ChasComBrdERS4826GTS-PWR-PLUSStore 8 }
s5ChasComBrdERS4826GTS-PWR-PLUSStoreTotal -- Total FLASH storage
    OBJECT IDENTIFIER ::= { s5ChasComBrdERS4826GTS-PWR-PLUSStore 9 }
s5ChasComBrdERS4826GTS-PWR-PLUSStoreBootLoader -- Boot Loader storage
    OBJECT IDENTIFIER ::= { s5ChasComBrdERS4826GTS-PWR-PLUSStore 10 }
s5ChasComBrdERS4826GTS-PWR-PLUSStoreConfig -- Binary Configuration storage
    OBJECT IDENTIFIER ::= { s5ChasComBrdERS4826GTS-PWR-PLUSStore 11 }
s5ChasComBrdERS4826GTS-PWR-PLUSStoreSecondaryConfig -- Secondary Binary Configuration storage
    OBJECT IDENTIFIER ::= { s5ChasComBrdERS4826GTS-PWR-PLUSStore 12 }
s5ChasComBrdERS4826GTS-PWR-PLUSStoreAutoBakupConfig -- Automatic Backup Configuration storage
    OBJECT IDENTIFIER ::= { s5ChasComBrdERS4826GTS-PWR-PLUSStore 13 }
s5ChasComBrdERS4826GTS-PWR-PLUSStoreReserved -- Portion of total FLASH storage that is reserved
    OBJECT IDENTIFIER ::= { s5ChasComBrdERS4826GTS-PWR-PLUSStore 14 }

-- ERS4850GTS-PWR+
s5ChasComBrdERS4850GTS-PWR-PLUS
    OBJECT IDENTIFIER ::= { s5ChasComMod 802 }
s5ChasComBrdERS4850GTS-PWR-PLUSStore -- storage areas
    OBJECT IDENTIFIER ::= { s5ChasComBrdERS4850GTS-PWR-PLUS 0 }
s5ChasComBrdERS4850GTS-PWR-PLUSStoreFlash -- FLASH image storage
    OBJECT IDENTIFIER ::= { s5ChasComBrdERS4850GTS-PWR-PLUSStore 1 }
s5ChasComBrdERS4850GTS-PWR-PLUSStoreBootFW -- Boot Firmware storage
    OBJECT IDENTIFIER ::= { s5ChasComBrdERS4850GTS-PWR-PLUSStore 2 }
s5ChasComBrdERS4850GTS-PWR-PLUSStoreDram -- DRAM storage
    OBJECT IDENTIFIER ::= { s5ChasComBrdERS4850GTS-PWR-PLUSStore 3 }
s5ChasComBrdERS4850GTS-PWR-PLUSStorePoLFlash -- PoL Flash image storage
    OBJECT IDENTIFIER ::= { s5ChasComBrdERS4850GTS-PWR-PLUSStore 4 }
s5ChasComBrdERS4850GTS-PWR-PLUSStoreSecondaryFlash -- Secondary FLASH image storage
    OBJECT IDENTIFIER ::= { s5ChasComBrdERS4850GTS-PWR-PLUSStore 5 }
s5ChasComBrdERS4850GTS-PWR-PLUSStoreCPLD -- CPLD
    OBJECT IDENTIFIER ::= { s5ChasComBrdERS4850GTS-PWR-PLUSStore 6 }
s5ChasComBrdERS4850GTS-PWR-PLUSStoreInstalledFW -- Installed FW Version
    OBJECT IDENTIFIER ::= { s5ChasComBrdERS4850GTS-PWR-PLUSStore 7 }
s5ChasComBrdERS4850GTS-PWR-PLUSStoreOperSW -- Operational Software Version
    OBJECT IDENTIFIER ::= { s5ChasComBrdERS4850GTS-PWR-PLUSStore 8 }
s5ChasComBrdERS4850GTS-PWR-PLUSStoreTotal -- Total FLASH storage
    OBJECT IDENTIFIER ::= { s5ChasComBrdERS4850GTS-PWR-PLUSStore 9 }
s5ChasComBrdERS4850GTS-PWR-PLUSStoreBootLoader -- Boot Loader storage
    OBJECT IDENTIFIER ::= { s5ChasComBrdERS4850GTS-PWR-PLUSStore 10 }
s5ChasComBrdERS4850GTS-PWR-PLUSStoreConfig -- Binary Configuration storage
    OBJECT IDENTIFIER ::= { s5ChasComBrdERS4850GTS-PWR-PLUSStore 11 }
s5ChasComBrdERS4850GTS-PWR-PLUSStoreSecondaryConfig -- Secondary Binary Configuration storage
    OBJECT IDENTIFIER ::= { s5ChasComBrdERS4850GTS-PWR-PLUSStore 12 }
s5ChasComBrdERS4850GTS-PWR-PLUSStoreAutoBakupConfig -- Automatic Backup Configuration storage
    OBJECT IDENTIFIER ::= { s5ChasComBrdERS4850GTS-PWR-PLUSStore 13 }
s5ChasComBrdERS4850GTS-PWR-PLUSStoreReserved -- Portion of total FLASH storage that is reserved
    OBJECT IDENTIFIER ::= { s5ChasComBrdERS4850GTS-PWR-PLUSStore 14 }

-- ERS4826GTS
s5ChasComBrdERS4826GTS
    OBJECT IDENTIFIER ::= { s5ChasComMod 803 }
s5ChasComBrdERS4826GTSStore -- storage areas
    OBJECT IDENTIFIER ::= { s5ChasComBrdERS4826GTS 0 }
s5ChasComBrdERS4826GTSStoreFlash -- FLASH image storage
    OBJECT IDENTIFIER ::= { s5ChasComBrdERS4826GTSStore 1 }
s5ChasComBrdERS4826GTSStoreBootFW -- Boot Firmware storage
    OBJECT IDENTIFIER ::= { s5ChasComBrdERS4826GTSStore 2 }
s5ChasComBrdERS4826GTSStoreDram -- DRAM storage
    OBJECT IDENTIFIER ::= { s5ChasComBrdERS4826GTSStore 3 }
s5ChasComBrdERS4826GTSStoreSecondaryFlash -- Secondary FLASH image storage
    OBJECT IDENTIFIER ::= { s5ChasComBrdERS4826GTSStore 5 }
s5ChasComBrdERS4826GTSStoreCPLD -- CPLD
    OBJECT IDENTIFIER ::= { s5ChasComBrdERS4826GTSStore 6 }
s5ChasComBrdERS4826GTSStoreInstalledFW -- Installed FW Version
    OBJECT IDENTIFIER ::= { s5ChasComBrdERS4826GTSStore 7 }
s5ChasComBrdERS4826GTSStoreOperSW -- Operational Software Version
    OBJECT IDENTIFIER ::= { s5ChasComBrdERS4826GTSStore 8 }
s5ChasComBrdERS4826GTSStoreTotal -- Total FLASH storage
    OBJECT IDENTIFIER ::= { s5ChasComBrdERS4826GTSStore 9 }
s5ChasComBrdERS4826GTSStoreBootLoader -- Boot Loader storage
    OBJECT IDENTIFIER ::= { s5ChasComBrdERS4826GTSStore 10 }
s5ChasComBrdERS4826GTSStoreConfig -- Binary Configuration storage
    OBJECT IDENTIFIER ::= { s5ChasComBrdERS4826GTSStore 11 }
s5ChasComBrdERS4826GTSStoreSecondaryConfig -- Secondary Binary Configuration storage
    OBJECT IDENTIFIER ::= { s5ChasComBrdERS4826GTSStore 12 }
s5ChasComBrdERS4826GTSStoreAutoBakupConfig -- Automatic Backup Configuration storage
    OBJECT IDENTIFIER ::= { s5ChasComBrdERS4826GTSStore 13 }
s5ChasComBrdERS4826GTSStoreReserved -- Portion of total FLASH storage that is reserved
    OBJECT IDENTIFIER ::= { s5ChasComBrdERS4826GTSStore 14 }

-- ERS4850GTS
s5ChasComBrdERS4850GTS
    OBJECT IDENTIFIER ::= { s5ChasComMod 804 }
s5ChasComBrdERS4850GTSStore -- storage areas
    OBJECT IDENTIFIER ::= { s5ChasComBrdERS4850GTS 0 }
s5ChasComBrdERS4850GTSStoreFlash -- FLASH image storage
    OBJECT IDENTIFIER ::= { s5ChasComBrdERS4850GTSStore 1 }
s5ChasComBrdERS4850GTSStoreBootFW -- Boot Firmware storage
    OBJECT IDENTIFIER ::= { s5ChasComBrdERS4850GTSStore 2 }
s5ChasComBrdERS4850GTSStoreDram -- DRAM storage
    OBJECT IDENTIFIER ::= { s5ChasComBrdERS4850GTSStore 3 }
s5ChasComBrdERS4850GTSStorePoLFlash -- PoL Flash image storage
    OBJECT IDENTIFIER ::= { s5ChasComBrdERS4850GTSStore 4 }
s5ChasComBrdERS4850GTSStoreSecondaryFlash -- Secondary FLASH image storage
    OBJECT IDENTIFIER ::= { s5ChasComBrdERS4850GTSStore 5 }
s5ChasComBrdERS4850GTSStoreCPLD -- CPLD
    OBJECT IDENTIFIER ::= { s5ChasComBrdERS4850GTSStore 6 }
s5ChasComBrdERS4850GTSStoreInstalledFW -- Installed FW Version
    OBJECT IDENTIFIER ::= { s5ChasComBrdERS4850GTSStore 7 }
s5ChasComBrdERS4850GTSStoreOperSW -- Operational Software Version
    OBJECT IDENTIFIER ::= { s5ChasComBrdERS4850GTSStore 8 }
s5ChasComBrdERS4850GTSStoreTotal -- Total FLASH storage
    OBJECT IDENTIFIER ::= { s5ChasComBrdERS4850GTSStore 9 }
s5ChasComBrdERS4850GTSStoreBootLoader -- Boot Loader storage
    OBJECT IDENTIFIER ::= { s5ChasComBrdERS4850GTSStore 10 }
s5ChasComBrdERS4850GTSStoreConfig -- Binary Configuration storage
    OBJECT IDENTIFIER ::= { s5ChasComBrdERS4850GTSStore 11 }
s5ChasComBrdERS4850GTSStoreSecondaryConfig -- Secondary Binary Configuration storage
    OBJECT IDENTIFIER ::= { s5ChasComBrdERS4850GTSStore 12 }
s5ChasComBrdERS4850GTSStoreAutoBakupConfig -- Automatic Backup Configuration storage
    OBJECT IDENTIFIER ::= { s5ChasComBrdERS4850GTSStore 13 }
s5ChasComBrdERS4850GTSStoreReserved -- Portion of total FLASH storage that is reserved
    OBJECT IDENTIFIER ::= { s5ChasComBrdERS4850GTSStore 14 }

-- VSP7024XLS
s5ChasComBrdVSP7024XLS
    OBJECT IDENTIFIER ::= { s5ChasComMod 805 }
s5ChasComBrdVSP7024XLSStore -- storage areas
    OBJECT IDENTIFIER ::= { s5ChasComBrdVSP7024XLS 0 }
s5ChasComBrdVSP7024XLSStoreFlash -- FLASH image storage
    OBJECT IDENTIFIER ::= { s5ChasComBrdVSP7024XLSStore 1 }
s5ChasComBrdVSP7024XLSStoreBootFW -- Boot Firmware storage
    OBJECT IDENTIFIER ::= { s5ChasComBrdVSP7024XLSStore 2 }
s5ChasComBrdVSP7024XLSStoreDram -- DRAM storage
    OBJECT IDENTIFIER ::= { s5ChasComBrdVSP7024XLSStore 3 }
s5ChasComBrdVSP7024XLSStorePoLFlash -- PoL Flash image storage
    OBJECT IDENTIFIER ::= { s5ChasComBrdVSP7024XLSStore 4 }
s5ChasComBrdVSP7024XLSStoreSecondaryFlash -- Secondary FLASH image storage
    OBJECT IDENTIFIER ::= { s5ChasComBrdVSP7024XLSStore 5 }
s5ChasComBrdVSP7024XLSStoreCPLD -- CPLD
    OBJECT IDENTIFIER ::= { s5ChasComBrdVSP7024XLSStore 6 }
s5ChasComBrdVSP7024XLSStoreInstalledFW -- Installed FW Version
    OBJECT IDENTIFIER ::= { s5ChasComBrdVSP7024XLSStore 7 }
s5ChasComBrdVSP7024XLSStoreOperSW -- Operational Software Version
    OBJECT IDENTIFIER ::= { s5ChasComBrdVSP7024XLSStore 8 }
s5ChasComBrdVSP7024XLSStoreTotal -- Total FLASH storage
    OBJECT IDENTIFIER ::= { s5ChasComBrdVSP7024XLSStore 9 }
s5ChasComBrdVSP7024XLSStoreBootLoader -- Boot Loader storage
    OBJECT IDENTIFIER ::= { s5ChasComBrdVSP7024XLSStore 10 }
s5ChasComBrdVSP7024XLSStoreConfig -- Binary Configuration storage
    OBJECT IDENTIFIER ::= { s5ChasComBrdVSP7024XLSStore 11 }
s5ChasComBrdVSP7024XLSStoreSecondaryConfig -- Secondary Binary Configuration storage
    OBJECT IDENTIFIER ::= { s5ChasComBrdVSP7024XLSStore 12 }
s5ChasComBrdVSP7024XLSStoreAutoBakupConfig -- Automatic Backup Configuration storage
    OBJECT IDENTIFIER ::= { s5ChasComBrdVSP7024XLSStore 13 }
s5ChasComBrdVSP7024XLSStoreReserved -- Portion of total FLASH storage that is reserved
    OBJECT IDENTIFIER ::= { s5ChasComBrdVSP7024XLSStore 14 }

-- 8 port SFP+ MDA
s5ChasComBrdVSP7024XLS-7008XLS
    OBJECT IDENTIFIER ::= { s5ChasComMod 806 }

-- 8 port 10GBase-T MDA
s5ChasComBrdVSP7024XLS-7008XLT
    OBJECT IDENTIFIER ::= { s5ChasComMod 807 }

-- ERS3510GT
s5ChasComBrdERS3510GT
    OBJECT IDENTIFIER ::= { s5ChasComMod 808 }
s5ChasComBrdERS3510GTStore -- storage areas
    OBJECT IDENTIFIER ::= { s5ChasComBrdERS3510GT 0 }
s5ChasComBrdERS3510GTStoreFlash -- FLASH image storage
    OBJECT IDENTIFIER ::= { s5ChasComBrdERS3510GTStore 1 }
s5ChasComBrdERS3510GTStoreBootFW -- Boot Firmware storage
    OBJECT IDENTIFIER ::= { s5ChasComBrdERS3510GTStore 2 }
s5ChasComBrdERS3510GTStoreDram -- DRAM storage
    OBJECT IDENTIFIER ::= { s5ChasComBrdERS3510GTStore 3 }
s5ChasComBrdERS3510GTStorePoLFlash -- PoL Flash image storage
    OBJECT IDENTIFIER ::= { s5ChasComBrdERS3510GTStore 4 }

-- ERS3510GT-PWR+
s5ChasComBrdERS3510GT-PWR-PLUS
    OBJECT IDENTIFIER ::= { s5ChasComMod 809 }
s5ChasComBrdERS3510GT-PWR-PLUSStore -- storage areas
    OBJECT IDENTIFIER ::= { s5ChasComBrdERS3510GT-PWR-PLUS 0 }
s5ChasComBrdERS3510GT-PWR-PLUSStoreFlash -- FLASH image storage
    OBJECT IDENTIFIER ::= { s5ChasComBrdERS3510GT-PWR-PLUSStore 1 }
s5ChasComBrdERS3510GT-PWR-PLUSStoreBootFW -- Boot Firmware storage
    OBJECT IDENTIFIER ::= { s5ChasComBrdERS3510GT-PWR-PLUSStore 2 }
s5ChasComBrdERS3510GT-PWR-PLUSStoreDram -- DRAM storage
    OBJECT IDENTIFIER ::= { s5ChasComBrdERS3510GT-PWR-PLUSStore 3 }
s5ChasComBrdERS3510GT-PWR-PLUSStorePoLFlash -- PoL Flash image storage
    OBJECT IDENTIFIER ::= { s5ChasComBrdERS3510GT-PWR-PLUSStore 4 }

-- ERS3524GT
s5ChasComBrdERS3524GT
    OBJECT IDENTIFIER ::= { s5ChasComMod 810 }
s5ChasComBrdERS3524GTStore -- storage areas
    OBJECT IDENTIFIER ::= { s5ChasComBrdERS3524GT 0 }
s5ChasComBrdERS3524GTStoreFlash -- FLASH image storage
    OBJECT IDENTIFIER ::= { s5ChasComBrdERS3524GTStore 1 }
s5ChasComBrdERS3524GTStoreBootFW -- Boot Firmware storage
    OBJECT IDENTIFIER ::= { s5ChasComBrdERS3524GTStore 2 }
s5ChasComBrdERS3524GTStoreDram -- DRAM storage
    OBJECT IDENTIFIER ::= { s5ChasComBrdERS3524GTStore 3 }
s5ChasComBrdERS3524GTStorePoLFlash -- PoL Flash image storage
    OBJECT IDENTIFIER ::= { s5ChasComBrdERS3524GTStore 4 }

-- ERS3524GT-PWR+
s5ChasComBrdERS3524GT-PWR-PLUS
    OBJECT IDENTIFIER ::= { s5ChasComMod 811 }
s5ChasComBrdERS3524GT-PWR-PLUSStore -- storage areas
    OBJECT IDENTIFIER ::= { s5ChasComBrdERS3524GT-PWR-PLUS 0 }
s5ChasComBrdERS3524GT-PWR-PLUSStoreFlash -- FLASH image storage
    OBJECT IDENTIFIER ::= { s5ChasComBrdERS3524GT-PWR-PLUSStore 1 }
s5ChasComBrdERS3524GT-PWR-PLUSStoreBootFW -- Boot Firmware storage
    OBJECT IDENTIFIER ::= { s5ChasComBrdERS3524GT-PWR-PLUSStore 2 }
s5ChasComBrdERS3524GT-PWR-PLUSStoreDram -- DRAM storage
    OBJECT IDENTIFIER ::= { s5ChasComBrdERS3524GT-PWR-PLUSStore 3 }
s5ChasComBrdERS3524GT-PWR-PLUSStorePoLFlash -- PoL Flash image storage
    OBJECT IDENTIFIER ::= { s5ChasComBrdERS3524GT-PWR-PLUSStore 4 }

-- ERS3526GT
s5ChasComBrdERS3526GT
    OBJECT IDENTIFIER ::= { s5ChasComMod 812 }
s5ChasComBrdERS3526GTStore -- storage areas
    OBJECT IDENTIFIER ::= { s5ChasComBrdERS3526GT 0 }
s5ChasComBrdERS3526GTStoreFlash -- FLASH image storage
    OBJECT IDENTIFIER ::= { s5ChasComBrdERS3526GTStore 1 }
s5ChasComBrdERS3526GTStoreBootFW -- Boot Firmware storage
    OBJECT IDENTIFIER ::= { s5ChasComBrdERS3526GTStore 2 }
s5ChasComBrdERS3526GTStoreDram -- DRAM storage
    OBJECT IDENTIFIER ::= { s5ChasComBrdERS3526GTStore 3 }
s5ChasComBrdERS3526GTStorePoLFlash -- PoL Flash image storage
    OBJECT IDENTIFIER ::= { s5ChasComBrdERS3526GTStore 4 }

-- ERS3526GT-PWR+
s5ChasComBrdERS3526GT-PWR-PLUS
    OBJECT IDENTIFIER ::= { s5ChasComMod 813 }
s5ChasComBrdERS3526GT-PWR-PLUSStore -- storage areas
    OBJECT IDENTIFIER ::= { s5ChasComBrdERS3526GT-PWR-PLUS 0 }
s5ChasComBrdERS3526GT-PWR-PLUSStoreFlash -- FLASH image storage
    OBJECT IDENTIFIER ::= { s5ChasComBrdERS3526GT-PWR-PLUSStore 1 }
s5ChasComBrdERS3526GT-PWR-PLUSStoreBootFW -- Boot Firmware storage
    OBJECT IDENTIFIER ::= { s5ChasComBrdERS3526GT-PWR-PLUSStore 2 }
s5ChasComBrdERS3526GT-PWR-PLUSStoreDram -- DRAM storage
    OBJECT IDENTIFIER ::= { s5ChasComBrdERS3526GT-PWR-PLUSStore 3 }
s5ChasComBrdERS3526GT-PWR-PLUSStorePoLFlash -- PoL Flash image storage
    OBJECT IDENTIFIER ::= { s5ChasComBrdERS3526GT-PWR-PLUSStore 4 }

-- ERS3526T
s5ChasComBrdERS3526T
    OBJECT IDENTIFIER ::= { s5ChasComMod 814 }
s5ChasComBrdERS3526TStore -- storage areas
    OBJECT IDENTIFIER ::= { s5ChasComBrdERS3526T 0 }
s5ChasComBrdERS3526TStoreFlash -- FLASH image storage
    OBJECT IDENTIFIER ::= { s5ChasComBrdERS3526TStore 1 }
s5ChasComBrdERS3526TStoreBootFW -- Boot Firmware storage
    OBJECT IDENTIFIER ::= { s5ChasComBrdERS3526TStore 2 }
s5ChasComBrdERS3526TStoreDram -- DRAM storage
    OBJECT IDENTIFIER ::= { s5ChasComBrdERS3526TStore 3 }
s5ChasComBrdERS3526TStorePoLFlash -- PoL Flash image storage
    OBJECT IDENTIFIER ::= { s5ChasComBrdERS3526TStore 4 }

-- ERS3526T-PWR+
s5ChasComBrdERS3526T-PWR-PLUS
    OBJECT IDENTIFIER ::= { s5ChasComMod 815 }
s5ChasComBrdERS3526T-PWR-PLUSStore -- storage areas
    OBJECT IDENTIFIER ::= { s5ChasComBrdERS3526T-PWR-PLUS 0 }
s5ChasComBrdERS3526T-PWR-PLUSStoreFlash -- FLASH image storage
    OBJECT IDENTIFIER ::= { s5ChasComBrdERS3526T-PWR-PLUSStore 1 }
s5ChasComBrdERS3526T-PWR-PLUSStoreBootFW -- Boot Firmware storage
    OBJECT IDENTIFIER ::= { s5ChasComBrdERS3526T-PWR-PLUSStore 2 }
s5ChasComBrdERS3526T-PWR-PLUSStoreDram -- DRAM storage
    OBJECT IDENTIFIER ::= { s5ChasComBrdERS3526T-PWR-PLUSStore 3 }
s5ChasComBrdERS3526T-PWR-PLUSStorePoLFlash -- PoL Flash image storage
    OBJECT IDENTIFIER ::= { s5ChasComBrdERS3526T-PWR-PLUSStore 4 }

-- ERS3549GTS
s5ChasComBrdERS3549GTS
    OBJECT IDENTIFIER ::= { s5ChasComMod 816 }
s5ChasComBrdERS3549GTSStore -- storage areas
    OBJECT IDENTIFIER ::= { s5ChasComBrdERS3549GTS 0 }
s5ChasComBrdERS3549GTSStoreFlash -- FLASH image storage
    OBJECT IDENTIFIER ::= { s5ChasComBrdERS3549GTSStore 1 }
s5ChasComBrdERS3549GTSStoreBootFW -- Boot Firmware storage
    OBJECT IDENTIFIER ::= { s5ChasComBrdERS3549GTSStore 2 }
s5ChasComBrdERS3549GTSStoreDram -- DRAM storage
    OBJECT IDENTIFIER ::= { s5ChasComBrdERS3549GTSStore 3 }
s5ChasComBrdERS3549GTSStorePoLFlash -- PoL Flash image storage
    OBJECT IDENTIFIER ::= { s5ChasComBrdERS3549GTSStore 4 }

-- ERS3549GTS-PWR+
s5ChasComBrdERS3549GTS-PWR-PLUS
    OBJECT IDENTIFIER ::= { s5ChasComMod 817 }
s5ChasComBrdERS3549GTS-PWR-PLUSStore -- storage areas
    OBJECT IDENTIFIER ::= { s5ChasComBrdERS3549GTS-PWR-PLUS 0 }
s5ChasComBrdERS3549GTS-PWR-PLUSStoreFlash -- FLASH image storage
    OBJECT IDENTIFIER ::= { s5ChasComBrdERS3549GTS-PWR-PLUSStore 1 }
s5ChasComBrdERS3549GTS-PWR-PLUSStoreBootFW -- Boot Firmware storage
    OBJECT IDENTIFIER ::= { s5ChasComBrdERS3549GTS-PWR-PLUSStore 2 }
s5ChasComBrdERS3549GTS-PWR-PLUSStoreDram -- DRAM storage
    OBJECT IDENTIFIER ::= { s5ChasComBrdERS3549GTS-PWR-PLUSStore 3 }
s5ChasComBrdERS3549GTS-PWR-PLUSStorePoLFlash -- PoL Flash image storage
    OBJECT IDENTIFIER ::= { s5ChasComBrdERS3549GTS-PWR-PLUSStore 4 }

-- VSP7000 series MDAs
s5ChasComBrdVSP7000MDA
    OBJECT IDENTIFIER ::= { s5ChasComMod 818 }
-- This value is not used, use s5ChasComBrdVSP7024XLS-7008XLS instead
s5ChasComBrdVSP7000MDA-7008XLS
    OBJECT IDENTIFIER ::= { s5ChasComBrdVSP7000MDA 1 }
-- This value is not used, use s5ChasComBrdVSP7024XLS-7008XLT instead
s5ChasComBrdVSP7000MDA-7008XT
    OBJECT IDENTIFIER ::= { s5ChasComBrdVSP7000MDA 2 }
s5ChasComBrdVSP7000MDA-7002QQ
    OBJECT IDENTIFIER ::= { s5ChasComBrdVSP7000MDA 3 }

-- VSP7024XT
s5ChasComBrdVSP7024XT
    OBJECT IDENTIFIER ::= { s5ChasComMod 819 }
s5ChasComBrdVSP7024XTStore -- storage areas
    OBJECT IDENTIFIER ::= { s5ChasComBrdVSP7024XT 0 }
s5ChasComBrdVSP7024XTStoreFlash -- FLASH image storage
    OBJECT IDENTIFIER ::= { s5ChasComBrdVSP7024XTStore 1 }
s5ChasComBrdVSP7024XTStoreBootFW -- Boot Firmware storage
    OBJECT IDENTIFIER ::= { s5ChasComBrdVSP7024XTStore 2 }
s5ChasComBrdVSP7024XTStoreDram -- DRAM storage
    OBJECT IDENTIFIER ::= { s5ChasComBrdVSP7024XTStore 3 }
s5ChasComBrdVSP7024XTStorePoLFlash -- PoL Flash image storage
    OBJECT IDENTIFIER ::= { s5ChasComBrdVSP7024XTStore 4 }
s5ChasComBrdVSP7024XTStoreSecondaryFlash -- Secondary FLASH image storage
    OBJECT IDENTIFIER ::= { s5ChasComBrdVSP7024XTStore 5 }
s5ChasComBrdVSP7024XTStoreCPLD -- CPLD
    OBJECT IDENTIFIER ::= { s5ChasComBrdVSP7024XTStore 6 }
s5ChasComBrdVSP7024XTStoreInstalledFW -- Installed FW Version
    OBJECT IDENTIFIER ::= { s5ChasComBrdVSP7024XTStore 7 }
s5ChasComBrdVSP7024XTStoreOperSW -- Operational Software Version
    OBJECT IDENTIFIER ::= { s5ChasComBrdVSP7024XTStore 8 }
s5ChasComBrdVSP7024XTStoreTotal -- Total FLASH storage
    OBJECT IDENTIFIER ::= { s5ChasComBrdVSP7024XTStore 9 }
s5ChasComBrdVSP7024XTStoreBootLoader -- Boot Loader storage
    OBJECT IDENTIFIER ::= { s5ChasComBrdVSP7024XTStore 10 }
s5ChasComBrdVSP7024XTStoreConfig -- Binary Configuration storage
    OBJECT IDENTIFIER ::= { s5ChasComBrdVSP7024XTStore 11 }
s5ChasComBrdVSP7024XTStoreSecondaryConfig -- Secondary Binary Configuration storage
    OBJECT IDENTIFIER ::= { s5ChasComBrdVSP7024XTStore 12 }
s5ChasComBrdVSP7024XTStoreAutoBakupConfig -- Automatic Backup Configuration storage
    OBJECT IDENTIFIER ::= { s5ChasComBrdVSP7024XTStore 13 }
s5ChasComBrdVSP7024XTStoreReserved -- Portion of total FLASH storage that is reserved
    OBJECT IDENTIFIER ::= { s5ChasComBrdVSP7024XTStore 14 }

-- ERS 5928GTS
s5ChasComBrdERS5928GTS
    OBJECT IDENTIFIER ::= { s5ChasComMod 820 }
s5ChasComBrdERS5928GTSStore -- storage areas
    OBJECT IDENTIFIER ::= { s5ChasComBrdERS5928GTS 0 }
s5ChasComBrdERS5928GTSStoreFlash -- FLASH image storage
    OBJECT IDENTIFIER ::= { s5ChasComBrdERS5928GTSStore 1 }
s5ChasComBrdERS5928GTSStoreBootFW -- Boot Firmware storage
    OBJECT IDENTIFIER ::= { s5ChasComBrdERS5928GTSStore 2 }
s5ChasComBrdERS5928GTSStoreDram -- DRAM storage
    OBJECT IDENTIFIER ::= { s5ChasComBrdERS5928GTSStore 3 }
s5ChasComBrdERS5928GTSStoreSecondaryFlash -- Secondary FLASH image storage
    OBJECT IDENTIFIER ::= { s5ChasComBrdERS5928GTSStore 5 }
s5ChasComBrdERS5928GTSStoreCPLD -- CPLD
    OBJECT IDENTIFIER ::= { s5ChasComBrdERS5928GTSStore 6 }
s5ChasComBrdERS5928GTSStoreInstalledFW -- Installed FW Version
    OBJECT IDENTIFIER ::= { s5ChasComBrdERS5928GTSStore 7 }
s5ChasComBrdERS5928GTSStoreOperSW -- Operational Software Version
    OBJECT IDENTIFIER ::= { s5ChasComBrdERS5928GTSStore 8 }
s5ChasComBrdERS5928GTSStoreTotal -- Total FLASH storage
    OBJECT IDENTIFIER ::= { s5ChasComBrdERS5928GTSStore 9 }
s5ChasComBrdERS5928GTSStoreBootLoader -- Boot Loader storage
    OBJECT IDENTIFIER ::= { s5ChasComBrdERS5928GTSStore 10 }
s5ChasComBrdERS5928GTSStoreConfig -- Binary Configuration storage
    OBJECT IDENTIFIER ::= { s5ChasComBrdERS5928GTSStore 11 }
s5ChasComBrdERS5928GTSStoreSecondaryConfig -- Secondary Binary Configuration storage
    OBJECT IDENTIFIER ::= { s5ChasComBrdERS5928GTSStore 12 }
s5ChasComBrdERS5928GTSStoreAutoBakupConfig -- Automatic Backup Configuration storage
    OBJECT IDENTIFIER ::= { s5ChasComBrdERS5928GTSStore 13 }
s5ChasComBrdERS5928GTSStoreReserved -- Portion of total FLASH storage that is reserved
    OBJECT IDENTIFIER ::= { s5ChasComBrdERS5928GTSStore 14 }

-- ERS 5928GTS-PWR+
s5ChasComBrdERS5928GTS-PWR-PLUS
    OBJECT IDENTIFIER ::= { s5ChasComMod 821 }
s5ChasComBrdERS5928GTS-PWR-PLUSStore -- storage areas
    OBJECT IDENTIFIER ::= { s5ChasComBrdERS5928GTS-PWR-PLUS 0 }
s5ChasComBrdERS5928GTS-PWR-PLUSStoreFlash -- FLASH image storage
    OBJECT IDENTIFIER ::= { s5ChasComBrdERS5928GTS-PWR-PLUSStore 1 }
s5ChasComBrdERS5928GTS-PWR-PLUSStoreBootFW -- Boot Firmware storage
    OBJECT IDENTIFIER ::= { s5ChasComBrdERS5928GTS-PWR-PLUSStore 2 }
s5ChasComBrdERS5928GTS-PWR-PLUSStoreDram -- DRAM storage
    OBJECT IDENTIFIER ::= { s5ChasComBrdERS5928GTS-PWR-PLUSStore 3 }
s5ChasComBrdERS5928GTS-PWR-PLUSStoreSecondaryFlash -- Secondary FLASH image storage
    OBJECT IDENTIFIER ::= { s5ChasComBrdERS5928GTS-PWR-PLUSStore 5 }
s5ChasComBrdERS5928GTS-PWR-PLUSStoreCPLD -- CPLD
    OBJECT IDENTIFIER ::= { s5ChasComBrdERS5928GTS-PWR-PLUSStore 6 }
s5ChasComBrdERS5928GTS-PWR-PLUSStoreInstalledFW -- Installed FW Version
    OBJECT IDENTIFIER ::= { s5ChasComBrdERS5928GTS-PWR-PLUSStore 7 }
s5ChasComBrdERS5928GTS-PWR-PLUSStoreOperSW -- Operational Software Version
    OBJECT IDENTIFIER ::= { s5ChasComBrdERS5928GTS-PWR-PLUSStore 8 }
s5ChasComBrdERS5928GTS-PWR-PLUSStoreTotal -- Total FLASH storage
    OBJECT IDENTIFIER ::= { s5ChasComBrdERS5928GTS-PWR-PLUSStore 9 }
s5ChasComBrdERS5928GTS-PWR-PLUSStoreBootLoader -- Boot Loader storage
    OBJECT IDENTIFIER ::= { s5ChasComBrdERS5928GTS-PWR-PLUSStore 10 }
s5ChasComBrdERS5928GTS-PWR-PLUSStoreConfig -- Binary Configuration storage
    OBJECT IDENTIFIER ::= { s5ChasComBrdERS5928GTS-PWR-PLUSStore 11 }
s5ChasComBrdERS5928GTS-PWR-PLUSStoreSecondaryConfig -- Secondary Binary Configuration storage
    OBJECT IDENTIFIER ::= { s5ChasComBrdERS5928GTS-PWR-PLUSStore 12 }
s5ChasComBrdERS5928GTS-PWR-PLUSStoreAutoBakupConfig -- Automatic Backup Configuration storage
    OBJECT IDENTIFIER ::= { s5ChasComBrdERS5928GTS-PWR-PLUSStore 13 }
s5ChasComBrdERS5928GTS-PWR-PLUSStoreReserved -- Portion of total FLASH storage that is reserved
    OBJECT IDENTIFIER ::= { s5ChasComBrdERS5928GTS-PWR-PLUSStore 14 }

-- ERS 5952GTS
s5ChasComBrdERS5952GTS
    OBJECT IDENTIFIER ::= { s5ChasComMod 822 }
s5ChasComBrdERS5952GTSStore -- storage areas
    OBJECT IDENTIFIER ::= { s5ChasComBrdERS5952GTS 0 }
s5ChasComBrdERS5952GTSStoreFlash -- FLASH image storage
    OBJECT IDENTIFIER ::= { s5ChasComBrdERS5952GTSStore 1 }
s5ChasComBrdERS5952GTSStoreBootFW -- Boot Firmware storage
    OBJECT IDENTIFIER ::= { s5ChasComBrdERS5952GTSStore 2 }
s5ChasComBrdERS5952GTSStoreDram -- DRAM storage
    OBJECT IDENTIFIER ::= { s5ChasComBrdERS5952GTSStore 3 }
s5ChasComBrdERS5952GTSStoreSecondaryFlash -- Secondary FLASH image storage
    OBJECT IDENTIFIER ::= { s5ChasComBrdERS5952GTSStore 5 }
s5ChasComBrdERS5952GTSStoreCPLD -- CPLD
    OBJECT IDENTIFIER ::= { s5ChasComBrdERS5952GTSStore 6 }
s5ChasComBrdERS5952GTSStoreInstalledFW -- Installed FW Version
    OBJECT IDENTIFIER ::= { s5ChasComBrdERS5952GTSStore 7 }
s5ChasComBrdERS5952GTSStoreOperSW -- Operational Software Version
    OBJECT IDENTIFIER ::= { s5ChasComBrdERS5952GTSStore 8 }
s5ChasComBrdERS5952GTSStoreTotal -- Total FLASH storage
    OBJECT IDENTIFIER ::= { s5ChasComBrdERS5952GTSStore 9 }
s5ChasComBrdERS5952GTSStoreBootLoader -- Boot Loader storage
    OBJECT IDENTIFIER ::= { s5ChasComBrdERS5952GTSStore 10 }
s5ChasComBrdERS5952GTSStoreConfig -- Binary Configuration storage
    OBJECT IDENTIFIER ::= { s5ChasComBrdERS5952GTSStore 11 }
s5ChasComBrdERS5952GTSStoreSecondaryConfig -- Secondary Binary Configuration storage
    OBJECT IDENTIFIER ::= { s5ChasComBrdERS5952GTSStore 12 }
s5ChasComBrdERS5952GTSStoreAutoBakupConfig -- Automatic Backup Configuration storage
    OBJECT IDENTIFIER ::= { s5ChasComBrdERS5952GTSStore 13 }
s5ChasComBrdERS5952GTSStoreReserved -- Portion of total FLASH storage that is reserved
    OBJECT IDENTIFIER ::= { s5ChasComBrdERS5952GTSStore 14 }

-- ERS 5952GTS-PWR+
s5ChasComBrdERS5952GTS-PWR-PLUS
    OBJECT IDENTIFIER ::= { s5ChasComMod 823 }
s5ChasComBrdERS5952GTS-PWR-PLUSStore -- storage areas
    OBJECT IDENTIFIER ::= { s5ChasComBrdERS5952GTS-PWR-PLUS 0 }
s5ChasComBrdERS5952GTS-PWR-PLUSStoreFlash -- FLASH image storage
    OBJECT IDENTIFIER ::= { s5ChasComBrdERS5952GTS-PWR-PLUSStore 1 }
s5ChasComBrdERS5952GTS-PWR-PLUSStoreBootFW -- Boot Firmware storage
    OBJECT IDENTIFIER ::= { s5ChasComBrdERS5952GTS-PWR-PLUSStore 2 }
s5ChasComBrdERS5952GTS-PWR-PLUSStoreDram -- DRAM storage
    OBJECT IDENTIFIER ::= { s5ChasComBrdERS5952GTS-PWR-PLUSStore 3 }
s5ChasComBrdERS5952GTS-PWR-PLUSStoreSecondaryFlash -- Secondary FLASH image storage
    OBJECT IDENTIFIER ::= { s5ChasComBrdERS5952GTS-PWR-PLUSStore 5 }
s5ChasComBrdERS5952GTS-PWR-PLUSStoreCPLD -- CPLD
    OBJECT IDENTIFIER ::= { s5ChasComBrdERS5952GTS-PWR-PLUSStore 6 }
s5ChasComBrdERS5952GTS-PWR-PLUSStoreInstalledFW -- Installed FW Version
    OBJECT IDENTIFIER ::= { s5ChasComBrdERS5952GTS-PWR-PLUSStore 7 }
s5ChasComBrdERS5952GTS-PWR-PLUSStoreOperSW -- Operational Software Version
    OBJECT IDENTIFIER ::= { s5ChasComBrdERS5952GTS-PWR-PLUSStore 8 }
s5ChasComBrdERS5952GTS-PWR-PLUSStoreTotal -- Total FLASH storage
    OBJECT IDENTIFIER ::= { s5ChasComBrdERS5952GTS-PWR-PLUSStore 9 }
s5ChasComBrdERS5952GTS-PWR-PLUSStoreBootLoader -- Boot Loader storage
    OBJECT IDENTIFIER ::= { s5ChasComBrdERS5952GTS-PWR-PLUSStore 10 }
s5ChasComBrdERS5952GTS-PWR-PLUSStoreConfig -- Binary Configuration storage
    OBJECT IDENTIFIER ::= { s5ChasComBrdERS5952GTS-PWR-PLUSStore 11 }
s5ChasComBrdERS5952GTS-PWR-PLUSStoreSecondaryConfig -- Secondary Binary Configuration storage
    OBJECT IDENTIFIER ::= { s5ChasComBrdERS5952GTS-PWR-PLUSStore 12 }
s5ChasComBrdERS5952GTS-PWR-PLUSStoreAutoBakupConfig -- Automatic Backup Configuration storage
    OBJECT IDENTIFIER ::= { s5ChasComBrdERS5952GTS-PWR-PLUSStore 13 }
s5ChasComBrdERS5952GTS-PWR-PLUSStoreReserved -- Portion of total FLASH storage that is reserved
    OBJECT IDENTIFIER ::= { s5ChasComBrdERS5952GTS-PWR-PLUSStore 14 }

-- ERS 5928GTS-uPWR
s5ChasComBrdERS5928GTS-UPWR
    OBJECT IDENTIFIER ::= { s5ChasComMod 824 }
s5ChasComBrdERS5928GTS-UPWRStore -- storage areas
    OBJECT IDENTIFIER ::= { s5ChasComBrdERS5928GTS-UPWR 0 }
s5ChasComBrdERS5928GTS-UPWRStoreFlash -- FLASH image storage
    OBJECT IDENTIFIER ::= { s5ChasComBrdERS5928GTS-UPWRStore 1 }
s5ChasComBrdERS5928GTS-UPWRStoreBootFW -- Boot Firmware storage
    OBJECT IDENTIFIER ::= { s5ChasComBrdERS5928GTS-UPWRStore 2 }
s5ChasComBrdERS5928GTS-UPWRStoreDram -- DRAM storage
    OBJECT IDENTIFIER ::= { s5ChasComBrdERS5928GTS-UPWRStore 3 }
s5ChasComBrdERS5928GTS-UPWRStoreSecondaryFlash -- Secondary FLASH image storage
    OBJECT IDENTIFIER ::= { s5ChasComBrdERS5928GTS-UPWRStore 5 }
s5ChasComBrdERS5928GTS-UPWRStoreCPLD -- CPLD
    OBJECT IDENTIFIER ::= { s5ChasComBrdERS5928GTS-UPWRStore 6 }
s5ChasComBrdERS5928GTS-UPWRStoreInstalledFW -- Installed FW Version
    OBJECT IDENTIFIER ::= { s5ChasComBrdERS5928GTS-UPWRStore 7 }
s5ChasComBrdERS5928GTS-UPWRStoreOperSW -- Operational Software Version
    OBJECT IDENTIFIER ::= { s5ChasComBrdERS5928GTS-UPWRStore 8 }
s5ChasComBrdERS5928GTS-UPWRStoreTotal -- Total FLASH storage
    OBJECT IDENTIFIER ::= { s5ChasComBrdERS5928GTS-UPWRStore 9 }
s5ChasComBrdERS5928GTS-UPWRStoreBootLoader -- Boot Loader storage
    OBJECT IDENTIFIER ::= { s5ChasComBrdERS5928GTS-UPWRStore 10 }
s5ChasComBrdERS5928GTS-UPWRStoreConfig -- Binary Configuration storage
    OBJECT IDENTIFIER ::= { s5ChasComBrdERS5928GTS-UPWRStore 11 }
s5ChasComBrdERS5928GTS-UPWRStoreSecondaryConfig -- Secondary Binary Configuration storage
    OBJECT IDENTIFIER ::= { s5ChasComBrdERS5928GTS-UPWRStore 12 }
s5ChasComBrdERS5928GTS-UPWRStoreAutoBakupConfig -- Automatic Backup Configuration storage
    OBJECT IDENTIFIER ::= { s5ChasComBrdERS5928GTS-UPWRStore 13 }
s5ChasComBrdERS5928GTS-UPWRStoreReserved -- Portion of total FLASH storage that is reserved
    OBJECT IDENTIFIER ::= { s5ChasComBrdERS5928GTS-UPWRStore 14 }

-- ERS 59100GTS
s5ChasComBrdERS59100GTS
    OBJECT IDENTIFIER ::= { s5ChasComMod 825 }
s5ChasComBrdERS59100GTSStore -- storage areas
    OBJECT IDENTIFIER ::= { s5ChasComBrdERS59100GTS 0 }
s5ChasComBrdERS59100GTSStoreFlash -- FLASH image storage
    OBJECT IDENTIFIER ::= { s5ChasComBrdERS59100GTSStore 1 }
s5ChasComBrdERS59100GTSStoreBootFW -- Boot Firmware storage
    OBJECT IDENTIFIER ::= { s5ChasComBrdERS59100GTSStore 2 }
s5ChasComBrdERS59100GTSStoreDram -- DRAM storage
    OBJECT IDENTIFIER ::= { s5ChasComBrdERS59100GTSStore 3 }
s5ChasComBrdERS59100GTSStoreSecondaryFlash -- Secondary FLASH image storage
    OBJECT IDENTIFIER ::= { s5ChasComBrdERS59100GTSStore 5 }
s5ChasComBrdERS59100GTSStoreCPLD -- CPLD
    OBJECT IDENTIFIER ::= { s5ChasComBrdERS59100GTSStore 6 }
s5ChasComBrdERS59100GTSStoreInstalledFW -- Installed FW Version
    OBJECT IDENTIFIER ::= { s5ChasComBrdERS59100GTSStore 7 }
s5ChasComBrdERS59100GTSStoreOperSW -- Operational Software Version
    OBJECT IDENTIFIER ::= { s5ChasComBrdERS59100GTSStore 8 }
s5ChasComBrdERS59100GTSStoreTotal -- Total FLASH storage
    OBJECT IDENTIFIER ::= { s5ChasComBrdERS59100GTSStore 9 }
s5ChasComBrdERS59100GTSStoreBootLoader -- Boot Loader storage
    OBJECT IDENTIFIER ::= { s5ChasComBrdERS59100GTSStore 10 }
s5ChasComBrdERS59100GTSStoreConfig -- Binary Configuration storage
    OBJECT IDENTIFIER ::= { s5ChasComBrdERS59100GTSStore 11 }
s5ChasComBrdERS59100GTSStoreSecondaryConfig -- Secondary Binary Configuration storage
    OBJECT IDENTIFIER ::= { s5ChasComBrdERS59100GTSStore 12 }
s5ChasComBrdERS59100GTSStoreAutoBakupConfig -- Automatic Backup Configuration storage
    OBJECT IDENTIFIER ::= { s5ChasComBrdERS59100GTSStore 13 }
s5ChasComBrdERS59100GTSStoreReserved -- Portion of total FLASH storage that is reserved
    OBJECT IDENTIFIER ::= { s5ChasComBrdERS59100GTSStore 14 }

-- ERS 59100GTS-PWR+
s5ChasComBrdERS59100GTS-PWR-PLUS
    OBJECT IDENTIFIER ::= { s5ChasComMod 826 }
s5ChasComBrdERS59100GTS-PWR-PLUSStore -- storage areas
    OBJECT IDENTIFIER ::= { s5ChasComBrdERS59100GTS-PWR-PLUS 0 }
s5ChasComBrdERS59100GTS-PWR-PLUSStoreFlash -- FLASH image storage
    OBJECT IDENTIFIER ::= { s5ChasComBrdERS59100GTS-PWR-PLUSStore 1 }
s5ChasComBrdERS59100GTS-PWR-PLUSStoreBootFW -- Boot Firmware storage
    OBJECT IDENTIFIER ::= { s5ChasComBrdERS59100GTS-PWR-PLUSStore 2 }
s5ChasComBrdERS59100GTS-PWR-PLUSStoreDram -- DRAM storage
    OBJECT IDENTIFIER ::= { s5ChasComBrdERS59100GTS-PWR-PLUSStore 3 }
s5ChasComBrdERS59100GTS-PWR-PLUSStoreSecondaryFlash -- Secondary FLASH image storage
    OBJECT IDENTIFIER ::= { s5ChasComBrdERS59100GTS-PWR-PLUSStore 5 }
s5ChasComBrdERS59100GTS-PWR-PLUSStoreCPLD -- CPLD
    OBJECT IDENTIFIER ::= { s5ChasComBrdERS59100GTS-PWR-PLUSStore 6 }
s5ChasComBrdERS59100GTS-PWR-PLUSStoreInstalledFW -- Installed FW Version
    OBJECT IDENTIFIER ::= { s5ChasComBrdERS59100GTS-PWR-PLUSStore 7 }
s5ChasComBrdERS59100GTS-PWR-PLUSStoreOperSW -- Operational Software Version
    OBJECT IDENTIFIER ::= { s5ChasComBrdERS59100GTS-PWR-PLUSStore 8 }
s5ChasComBrdERS59100GTS-PWR-PLUSStoreTotal -- Total FLASH storage
    OBJECT IDENTIFIER ::= { s5ChasComBrdERS59100GTS-PWR-PLUSStore 9 }
s5ChasComBrdERS59100GTS-PWR-PLUSStoreBootLoader -- Boot Loader storage
    OBJECT IDENTIFIER ::= { s5ChasComBrdERS59100GTS-PWR-PLUSStore 10 }
s5ChasComBrdERS59100GTS-PWR-PLUSStoreConfig -- Binary Configuration storage
    OBJECT IDENTIFIER ::= { s5ChasComBrdERS59100GTS-PWR-PLUSStore 11 }
s5ChasComBrdERS59100GTS-PWR-PLUSStoreSecondaryConfig -- Secondary Binary Configuration storage
    OBJECT IDENTIFIER ::= { s5ChasComBrdERS59100GTS-PWR-PLUSStore 12 }
s5ChasComBrdERS59100GTS-PWR-PLUSStoreAutoBakupConfig -- Automatic Backup Configuration storage
    OBJECT IDENTIFIER ::= { s5ChasComBrdERS59100GTS-PWR-PLUSStore 13 }
s5ChasComBrdERS59100GTS-PWR-PLUSStoreReserved -- Portion of total FLASH storage that is reserved
    OBJECT IDENTIFIER ::= { s5ChasComBrdERS59100GTS-PWR-PLUSStore 14 }

-- ERS 4900 GTS
s5ChasComBrdERS4926GTS
    OBJECT IDENTIFIER ::= { s5ChasComMod 827 }
s5ChasComBrdERS4926GTSStore -- storage areas
    OBJECT IDENTIFIER ::= { s5ChasComBrdERS4926GTS 0 }
s5ChasComBrdERS4926GTSStoreFlash -- FLASH image storage
    OBJECT IDENTIFIER ::= { s5ChasComBrdERS4926GTSStore 1 }
s5ChasComBrdERS4926GTSStoreBootFW -- Boot Firmware storage
    OBJECT IDENTIFIER ::= { s5ChasComBrdERS4926GTSStore 2 }
s5ChasComBrdERS4926GTSStoreDram -- DRAM storage
    OBJECT IDENTIFIER ::= { s5ChasComBrdERS4926GTSStore 3 }
s5ChasComBrdERS4926GTSStoreSecondaryFlash -- Secondary FLASH image storage
    OBJECT IDENTIFIER ::= { s5ChasComBrdERS4926GTSStore 5 }
s5ChasComBrdERS4926GTSStoreCPLD -- CPLD
    OBJECT IDENTIFIER ::= { s5ChasComBrdERS4926GTSStore 6 }
s5ChasComBrdERS4926GTSStoreInstalledFW -- Installed FW Version
    OBJECT IDENTIFIER ::= { s5ChasComBrdERS4926GTSStore 7 }
s5ChasComBrdERS4926GTSStoreOperSW -- Operational Software Version
    OBJECT IDENTIFIER ::= { s5ChasComBrdERS4926GTSStore 8 }
s5ChasComBrdERS4926GTSStoreTotal -- Total FLASH storage
    OBJECT IDENTIFIER ::= { s5ChasComBrdERS4926GTSStore 9 }
s5ChasComBrdERS4926GTSStoreBootLoader -- Boot Loader storage
    OBJECT IDENTIFIER ::= { s5ChasComBrdERS4926GTSStore 10 }
s5ChasComBrdERS4926GTSStoreConfig -- Binary Configuration storage
    OBJECT IDENTIFIER ::= { s5ChasComBrdERS4926GTSStore 11 }
s5ChasComBrdERS4926GTSStoreSecondaryConfig -- Secondary Binary Configuration storage
    OBJECT IDENTIFIER ::= { s5ChasComBrdERS4926GTSStore 12 }
s5ChasComBrdERS4926GTSStoreAutoBakupConfig -- Automatic Backup Configuration storage
    OBJECT IDENTIFIER ::= { s5ChasComBrdERS4926GTSStore 13 }
s5ChasComBrdERS4926GTSStoreReserved -- Portion of total FLASH storage that is reserved
    OBJECT IDENTIFIER ::= { s5ChasComBrdERS4926GTSStore 14 }

-- ERS 4926GTS-PWR+
s5ChasComBrdERS4926GTS-PWR-PLUS
    OBJECT IDENTIFIER ::= { s5ChasComMod 828 }
s5ChasComBrdERS4926GTS-PWR-PLUSStore -- storage areas
    OBJECT IDENTIFIER ::= { s5ChasComBrdERS4926GTS-PWR-PLUS 0 }
s5ChasComBrdERS4926GTS-PWR-PLUSStoreFlash -- FLASH image storage
    OBJECT IDENTIFIER ::= { s5ChasComBrdERS4926GTS-PWR-PLUSStore 1 }
s5ChasComBrdERS4926GTS-PWR-PLUSStoreBootFW -- Boot Firmware storage
    OBJECT IDENTIFIER ::= { s5ChasComBrdERS4926GTS-PWR-PLUSStore 2 }
s5ChasComBrdERS4926GTS-PWR-PLUSStoreDram -- DRAM storage
    OBJECT IDENTIFIER ::= { s5ChasComBrdERS4926GTS-PWR-PLUSStore 3 }
s5ChasComBrdERS4926GTS-PWR-PLUSStoreSecondaryFlash -- Secondary FLASH image storage
    OBJECT IDENTIFIER ::= { s5ChasComBrdERS4926GTS-PWR-PLUSStore 5 }
s5ChasComBrdERS4926GTS-PWR-PLUSStoreCPLD -- CPLD
    OBJECT IDENTIFIER ::= { s5ChasComBrdERS4926GTS-PWR-PLUSStore 6 }
s5ChasComBrdERS4926GTS-PWR-PLUSStoreInstalledFW -- Installed FW Version
    OBJECT IDENTIFIER ::= { s5ChasComBrdERS4926GTS-PWR-PLUSStore 7 }
s5ChasComBrdERS4926GTS-PWR-PLUSStoreOperSW -- Operational Software Version
    OBJECT IDENTIFIER ::= { s5ChasComBrdERS4926GTS-PWR-PLUSStore 8 }
s5ChasComBrdERS4926GTS-PWR-PLUSStoreTotal -- Total FLASH storage
    OBJECT IDENTIFIER ::= { s5ChasComBrdERS4926GTS-PWR-PLUSStore 9 }
s5ChasComBrdERS4926GTS-PWR-PLUSStoreBootLoader -- Boot Loader storage
    OBJECT IDENTIFIER ::= { s5ChasComBrdERS4926GTS-PWR-PLUSStore 10 }
s5ChasComBrdERS4926GTS-PWR-PLUSStoreConfig -- Binary Configuration storage
    OBJECT IDENTIFIER ::= { s5ChasComBrdERS4926GTS-PWR-PLUSStore 11 }
s5ChasComBrdERS4926GTS-PWR-PLUSStoreSecondaryConfig -- Secondary Binary Configuration storage
    OBJECT IDENTIFIER ::= { s5ChasComBrdERS4926GTS-PWR-PLUSStore 12 }
s5ChasComBrdERS4926GTS-PWR-PLUSStoreAutoBakupConfig -- Automatic Backup Configuration storage
    OBJECT IDENTIFIER ::= { s5ChasComBrdERS4926GTS-PWR-PLUSStore 13 }
s5ChasComBrdERS4926GTS-PWR-PLUSStoreReserved -- Portion of total FLASH storage that is reserved
    OBJECT IDENTIFIER ::= { s5ChasComBrdERS4926GTS-PWR-PLUSStore 14 }

-- ERS 4900 50GTS
s5ChasComBrdERS4950GTS
    OBJECT IDENTIFIER ::= { s5ChasComMod 829 }
s5ChasComBrdERS4950GTSStore -- storage areas
    OBJECT IDENTIFIER ::= { s5ChasComBrdERS4950GTS 0 }
s5ChasComBrdERS4950GTSStoreFlash -- FLASH image storage
    OBJECT IDENTIFIER ::= { s5ChasComBrdERS4950GTSStore 1 }
s5ChasComBrdERS4950GTSStoreBootFW -- Boot Firmware storage
    OBJECT IDENTIFIER ::= { s5ChasComBrdERS4950GTSStore 2 }
s5ChasComBrdERS4950GTSStoreDram -- DRAM storage
    OBJECT IDENTIFIER ::= { s5ChasComBrdERS4950GTSStore 3 }
s5ChasComBrdERS4950GTSStorePoLFlash -- PoL Flash image storage
    OBJECT IDENTIFIER ::= { s5ChasComBrdERS4950GTSStore 4 }
s5ChasComBrdERS4950GTSStoreSecondaryFlash -- Secondary FLASH image storage
    OBJECT IDENTIFIER ::= { s5ChasComBrdERS4950GTSStore 5 }
s5ChasComBrdERS4950GTSStoreCPLD -- CPLD
    OBJECT IDENTIFIER ::= { s5ChasComBrdERS4950GTSStore 6 }
s5ChasComBrdERS4950GTSStoreInstalledFW -- Installed FW Version
    OBJECT IDENTIFIER ::= { s5ChasComBrdERS4950GTSStore 7 }
s5ChasComBrdERS4950GTSStoreOperSW -- Operational Software Version
    OBJECT IDENTIFIER ::= { s5ChasComBrdERS4950GTSStore 8 }
s5ChasComBrdERS4950GTSStoreTotal -- Total FLASH storage
    OBJECT IDENTIFIER ::= { s5ChasComBrdERS4950GTSStore 9 }
s5ChasComBrdERS4950GTSStoreBootLoader -- Boot Loader storage
    OBJECT IDENTIFIER ::= { s5ChasComBrdERS4950GTSStore 10 }
s5ChasComBrdERS4950GTSStoreConfig -- Binary Configuration storage
    OBJECT IDENTIFIER ::= { s5ChasComBrdERS4950GTSStore 11 }
s5ChasComBrdERS4950GTSStoreSecondaryConfig -- Secondary Binary Configuration storage
    OBJECT IDENTIFIER ::= { s5ChasComBrdERS4950GTSStore 12 }
s5ChasComBrdERS4950GTSStoreAutoBakupConfig -- Automatic Backup Configuration storage
    OBJECT IDENTIFIER ::= { s5ChasComBrdERS4950GTSStore 13 }
s5ChasComBrdERS4950GTSStoreReserved -- Portion of total FLASH storage that is reserved
    OBJECT IDENTIFIER ::= { s5ChasComBrdERS4950GTSStore 14 }

-- ERS 4900 50GTS-PWR+
s5ChasComBrdERS4950GTS-PWR-PLUS
    OBJECT IDENTIFIER ::= { s5ChasComMod 830 }
s5ChasComBrdERS4950GTS-PWR-PLUSStore -- storage areas
    OBJECT IDENTIFIER ::= { s5ChasComBrdERS4950GTS-PWR-PLUS 0 }
s5ChasComBrdERS4950GTS-PWR-PLUSStoreFlash -- FLASH image storage
    OBJECT IDENTIFIER ::= { s5ChasComBrdERS4950GTS-PWR-PLUSStore 1 }
s5ChasComBrdERS4950GTS-PWR-PLUSStoreBootFW -- Boot Firmware storage
    OBJECT IDENTIFIER ::= { s5ChasComBrdERS4950GTS-PWR-PLUSStore 2 }
s5ChasComBrdERS4950GTS-PWR-PLUSStoreDram -- DRAM storage
    OBJECT IDENTIFIER ::= { s5ChasComBrdERS4950GTS-PWR-PLUSStore 3 }
s5ChasComBrdERS4950GTS-PWR-PLUSStorePoLFlash -- PoL Flash image storage
    OBJECT IDENTIFIER ::= { s5ChasComBrdERS4950GTS-PWR-PLUSStore 4 }
s5ChasComBrdERS4950GTS-PWR-PLUSStoreSecondaryFlash -- Secondary FLASH image storage
    OBJECT IDENTIFIER ::= { s5ChasComBrdERS4950GTS-PWR-PLUSStore 5 }
s5ChasComBrdERS4950GTS-PWR-PLUSStoreCPLD -- CPLD
    OBJECT IDENTIFIER ::= { s5ChasComBrdERS4950GTS-PWR-PLUSStore 6 }
s5ChasComBrdERS4950GTS-PWR-PLUSStoreInstalledFW -- Installed FW Version
    OBJECT IDENTIFIER ::= { s5ChasComBrdERS4950GTS-PWR-PLUSStore 7 }
s5ChasComBrdERS4950GTS-PWR-PLUSStoreOperSW -- Operational Software Version
    OBJECT IDENTIFIER ::= { s5ChasComBrdERS4950GTS-PWR-PLUSStore 8 }
s5ChasComBrdERS4950GTS-PWR-PLUSStoreTotal -- Total FLASH storage
    OBJECT IDENTIFIER ::= { s5ChasComBrdERS4950GTS-PWR-PLUSStore 9 }
s5ChasComBrdERS4950GTS-PWR-PLUSStoreBootLoader -- Boot Loader storage
    OBJECT IDENTIFIER ::= { s5ChasComBrdERS4950GTS-PWR-PLUSStore 10 }
s5ChasComBrdERS4950GTS-PWR-PLUSStoreConfig -- Binary Configuration storage
    OBJECT IDENTIFIER ::= { s5ChasComBrdERS4950GTS-PWR-PLUSStore 11 }
s5ChasComBrdERS4950GTS-PWR-PLUSStoreSecondaryConfig -- Secondary Binary Configuration storage
    OBJECT IDENTIFIER ::= { s5ChasComBrdERS4950GTS-PWR-PLUSStore 12 }
s5ChasComBrdERS4950GTS-PWR-PLUSStoreAutoBakupConfig -- Automatic Backup Configuration storage
    OBJECT IDENTIFIER ::= { s5ChasComBrdERS4950GTS-PWR-PLUSStore 13 }
s5ChasComBrdERS4950GTS-PWR-PLUSStoreReserved -- Portion of total FLASH storage that is reserved
    OBJECT IDENTIFIER ::= { s5ChasComBrdERS4950GTS-PWR-PLUSStore 14 }

-- ERS3550T
s5ChasComBrdERS3550T
    OBJECT IDENTIFIER ::= { s5ChasComMod 831 }
s5ChasComBrdERS3550TStore -- storage areas
    OBJECT IDENTIFIER ::= { s5ChasComBrdERS3550T 0 }
s5ChasComBrdERS3550TStoreFlash -- FLASH image storage
    OBJECT IDENTIFIER ::= { s5ChasComBrdERS3550TStore 1 }
s5ChasComBrdERS3550TStoreBootFW -- Boot Firmware storage
    OBJECT IDENTIFIER ::= { s5ChasComBrdERS3550TStore 2 }
s5ChasComBrdERS3550TStoreDram -- DRAM storage
    OBJECT IDENTIFIER ::= { s5ChasComBrdERS3550TStore 3 }
s5ChasComBrdERS3550TStorePoLFlash -- PoL Flash image storage
    OBJECT IDENTIFIER ::= { s5ChasComBrdERS3550TStore 4 }

-- ERS3550T-PWR+
s5ChasComBrdERS3550T-PWR-PLUS
    OBJECT IDENTIFIER ::= { s5ChasComMod 832 }
s5ChasComBrdERS3550T-PWR-PLUSStore -- storage areas
    OBJECT IDENTIFIER ::= { s5ChasComBrdERS3550T-PWR-PLUS 0 }
s5ChasComBrdERS3550T-PWR-PLUSStoreFlash -- FLASH image storage
    OBJECT IDENTIFIER ::= { s5ChasComBrdERS3550T-PWR-PLUSStore 1 }
s5ChasComBrdERS3550T-PWR-PLUSStoreBootFW -- Boot Firmware storage
    OBJECT IDENTIFIER ::= { s5ChasComBrdERS3550T-PWR-PLUSStore 2 }
s5ChasComBrdERS3550T-PWR-PLUSStoreDram -- DRAM storage
    OBJECT IDENTIFIER ::= { s5ChasComBrdERS3550T-PWR-PLUSStore 3 }
s5ChasComBrdERS3550T-PWR-PLUSStorePoLFlash -- PoL Flash image storage
    OBJECT IDENTIFIER ::= { s5ChasComBrdERS3550T-PWR-PLUSStore 4 }

-- ERS3626GTS
s5ChasComBrdERS3626GTS
    OBJECT IDENTIFIER ::= { s5ChasComMod 833 }
s5ChasComBrdERS3626GTSStore -- storage areas
    OBJECT IDENTIFIER ::= { s5ChasComBrdERS3626GTS 0 }
s5ChasComBrdERS3626GTSStoreFlash -- FLASH image storage
    OBJECT IDENTIFIER ::= { s5ChasComBrdERS3626GTSStore 1 }
s5ChasComBrdERS3626GTSStoreBootFW -- Boot Firmware storage
    OBJECT IDENTIFIER ::= { s5ChasComBrdERS3626GTSStore 2 }
s5ChasComBrdERS3626GTSStoreDram -- DRAM storage
    OBJECT IDENTIFIER ::= { s5ChasComBrdERS3626GTSStore 3 }
s5ChasComBrdERS3626GTSStorePoLFlash -- PoL Flash image storage
    OBJECT IDENTIFIER ::= { s5ChasComBrdERS3626GTSStore 4 }

-- ERS3626GTS-PWR-PLUS
s5ChasComBrdERS3626GTS-PWR-PLUS
    OBJECT IDENTIFIER ::= { s5ChasComMod 834 }
s5ChasComBrdERS3626GTS-PWR-PLUSStore -- storage areas
    OBJECT IDENTIFIER ::= { s5ChasComBrdERS3626GTS-PWR-PLUS 0 }
s5ChasComBrdERS3626GTS-PWR-PLUSStoreFlash -- FLASH image storage
    OBJECT IDENTIFIER ::= { s5ChasComBrdERS3626GTS-PWR-PLUSStore 1 }
s5ChasComBrdERS3626GTS-PWR-PLUSStoreBootFW -- Boot Firmware storage
    OBJECT IDENTIFIER ::= { s5ChasComBrdERS3626GTS-PWR-PLUSStore 2 }
s5ChasComBrdERS3626GTS-PWR-PLUSStoreDram -- DRAM storage
    OBJECT IDENTIFIER ::= { s5ChasComBrdERS3626GTS-PWR-PLUSStore 3 }
s5ChasComBrdERS3626GTS-PWR-PLUSStorePoLFlash -- PoL Flash image storage
    OBJECT IDENTIFIER ::= { s5ChasComBrdERS3626GTS-PWR-PLUSStore 4 }

-- ERS3650GTS
s5ChasComBrdERS3650GTS
    OBJECT IDENTIFIER ::= { s5ChasComMod 835 }
s5ChasComBrdERS3650GTSStore -- storage areas
    OBJECT IDENTIFIER ::= { s5ChasComBrdERS3650GTS 0 }
s5ChasComBrdERS3650GTSStoreFlash -- FLASH image storage
    OBJECT IDENTIFIER ::= { s5ChasComBrdERS3650GTSStore 1 }
s5ChasComBrdERS3650GTSStoreBootFW -- Boot Firmware storage
    OBJECT IDENTIFIER ::= { s5ChasComBrdERS3650GTSStore 2 }
s5ChasComBrdERS3650GTSStoreDram -- DRAM storage
    OBJECT IDENTIFIER ::= { s5ChasComBrdERS3650GTSStore 3 }
s5ChasComBrdERS3650GTSStorePoLFlash -- PoL Flash image storage
    OBJECT IDENTIFIER ::= { s5ChasComBrdERS3650GTSStore 4 }

-- ERS3650GTS-PWR-PLUS
s5ChasComBrdERS3650GTS-PWR-PLUS
    OBJECT IDENTIFIER ::= { s5ChasComMod 836 }
s5ChasComBrdERS3650GTS-PWR-PLUSStore -- storage areas
    OBJECT IDENTIFIER ::= { s5ChasComBrdERS3650GTS-PWR-PLUS 0 }
s5ChasComBrdERS3650GTS-PWR-PLUSStoreFlash -- FLASH image storage
    OBJECT IDENTIFIER ::= { s5ChasComBrdERS3650GTS-PWR-PLUSStore 1 }
s5ChasComBrdERS3650GTS-PWR-PLUSStoreBootFW -- Boot Firmware storage
    OBJECT IDENTIFIER ::= { s5ChasComBrdERS3650GTS-PWR-PLUSStore 2 }
s5ChasComBrdERS3650GTS-PWR-PLUSStoreDram -- DRAM storage
    OBJECT IDENTIFIER ::= { s5ChasComBrdERS3650GTS-PWR-PLUSStore 3 }
s5ChasComBrdERS3650GTS-PWR-PLUSStorePoLFlash -- PoL Flash image storage
    OBJECT IDENTIFIER ::= { s5ChasComBrdERS3650GTS-PWR-PLUSStore 4 }

-- ERS 5928MTS-uPWR
s5ChasComBrdERS5928MTS-UPWR
    OBJECT IDENTIFIER ::= { s5ChasComMod 837 }
s5ChasComBrdERS5928MTS-UPWRStore -- storage areas
    OBJECT IDENTIFIER ::= { s5ChasComBrdERS5928MTS-UPWR 0 }
s5ChasComBrdERS5928MTS-UPWRStoreFlash -- FLASH image storage
    OBJECT IDENTIFIER ::= { s5ChasComBrdERS5928MTS-UPWRStore 1 }
s5ChasComBrdERS5928MTS-UPWRStoreBootFW -- Boot Firmware storage
    OBJECT IDENTIFIER ::= { s5ChasComBrdERS5928MTS-UPWRStore 2 }
s5ChasComBrdERS5928MTS-UPWRStoreDram -- DRAM storage
    OBJECT IDENTIFIER ::= { s5ChasComBrdERS5928MTS-UPWRStore 3 }
s5ChasComBrdERS5928MTS-UPWRStoreSecondaryFlash -- Secondary FLASH image storage
    OBJECT IDENTIFIER ::= { s5ChasComBrdERS5928MTS-UPWRStore 5 }
s5ChasComBrdERS5928MTS-UPWRStoreCPLD -- CPLD
    OBJECT IDENTIFIER ::= { s5ChasComBrdERS5928MTS-UPWRStore 6 }
s5ChasComBrdERS5928MTS-UPWRStoreInstalledFW -- Installed FW Version
    OBJECT IDENTIFIER ::= { s5ChasComBrdERS5928MTS-UPWRStore 7 }
s5ChasComBrdERS5928MTS-UPWRStoreOperSW -- Operational Software Version
    OBJECT IDENTIFIER ::= { s5ChasComBrdERS5928MTS-UPWRStore 8 }
s5ChasComBrdERS5928MTS-UPWRStoreTotal -- Total FLASH storage
    OBJECT IDENTIFIER ::= { s5ChasComBrdERS5928MTS-UPWRStore 9 }
s5ChasComBrdERS5928MTS-UPWRStoreBootLoader -- Boot Loader storage
    OBJECT IDENTIFIER ::= { s5ChasComBrdERS5928MTS-UPWRStore 10 }
s5ChasComBrdERS5928MTS-UPWRStoreConfig -- Binary Configuration storage
    OBJECT IDENTIFIER ::= { s5ChasComBrdERS5928MTS-UPWRStore 11 }
s5ChasComBrdERS5928MTS-UPWRStoreSecondaryConfig -- Secondary Binary Configuration storage
    OBJECT IDENTIFIER ::= { s5ChasComBrdERS5928MTS-UPWRStore 12 }
s5ChasComBrdERS5928MTS-UPWRStoreAutoBakupConfig -- Automatic Backup Configuration storage
    OBJECT IDENTIFIER ::= { s5ChasComBrdERS5928MTS-UPWRStore 13 }
s5ChasComBrdERS5928MTS-UPWRStoreReserved -- Portion of total FLASH storage that is reserved
    OBJECT IDENTIFIER ::= { s5ChasComBrdERS5928MTS-UPWRStore 14 }

-- ============================================================================
-- General s5ChasStoreTable types
-- ============================================================================
s5ChasStoreTypeReg OBJECT IDENTIFIER ::= { s5ChasComTypeVal 12 }

END
