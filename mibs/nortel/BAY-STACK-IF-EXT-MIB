BAY-STACK-IF-EXT-MIB DEFINITIONS ::= BEGIN

IMPORTS
    OBJECT-TYPE, MODULE-IDENTITY
        FROM SNMPv2-SMI
    TruthValue
        FROM SNMPv2-TC
    InterfaceIndex
        FROM IF-MIB
    bayStackMibs
        FROM SYNOPTICS-ROOT-MIB;

bayStackIfExtMib MODULE-IDENTITY
    LAST-UPDATED "201205310000Z"
    ORGANIZATION "Avaya"
    CONTACT-INFO "avaya.com"
    DESCRIPTION
        "This MIB module contains miscellaneous per-interface extensions."

    REVISION     "201205310000Z"  -- May 31, 2012
    DESCRIPTION
        "Ver 2:  Added bsIfExtDirectedBroadcast."

    REVISION     "201011030000Z"  -- November 03, 2010
    DESCRIPTION
        "Ver 1:  Initial version."

    ::= { bayStackMibs 40 }

bsIfExtNotifications OBJECT IDENTIFIER ::= { bayStackIfExtMib 0 }
bsIfExtObjects       OBJECT IDENTIFIER ::= { bayStackIfExtMib 1 }

-- ============================================================================
-- Scalar objects
-- ============================================================================

bsIfExtScalars OBJECT IDENTIFIER ::= { bsIfExtObjects 1 }

bsIfExtDirectedBroadcast   OBJECT-TYPE
    SYNTAX        TruthValue
    MAX-ACCESS    read-write
    STATUS        current
    DESCRIPTION
        "Indicates whether directed broadcast is enabled globally."
    ::= { bsIfExtScalars 1 }

-- ============================================================================
-- Interface extensions table
-- ============================================================================

bsIfExtIfTable   OBJECT-TYPE
    SYNTAX SEQUENCE OF BsIfExtIfEntry
    MAX-ACCESS  not-accessible
    STATUS      current
    DESCRIPTION
        "This table contains per-interface extensions."
    ::= { bsIfExtObjects 2 }

bsIfExtIfEntry OBJECT-TYPE
    SYNTAX       BsIfExtIfEntry
    MAX-ACCESS   not-accessible
    STATUS       current
    DESCRIPTION
        "An entry containing objects for controlling unicast storm control
         settings for an interface."
    INDEX { bsIfExtIfIndex }
    ::= { bsIfExtIfTable 1 }

BsIfExtIfEntry ::=
    SEQUENCE {
        bsIfExtIfIndex             InterfaceIndex,
        bsIfExtIfDirectedBroadcast TruthValue
    }

bsIfExtIfIndex OBJECT-TYPE
    SYNTAX      InterfaceIndex
    MAX-ACCESS  not-accessible
    STATUS      current
    DESCRIPTION
        "The ifIndex value of the interface."
    ::= { bsIfExtIfEntry 1 }

bsIfExtIfDirectedBroadcast OBJECT-TYPE
    SYNTAX       TruthValue
    MAX-ACCESS   read-write
    STATUS       current
    DESCRIPTION
        "Indicates whether directed broadcast is enabled on the interface."
    ::= { bsIfExtIfEntry 2 }

-- ============================================================================
-- Notifications
-- ============================================================================

END
