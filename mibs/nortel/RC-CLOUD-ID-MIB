RC-CLOUD-ID-MIB DEFINITIONS ::= BEGIN

IMPORTS
    MODULE-IDENTITY, OBJECT-TYPE, Integer32
        FROM SNMPv2-SMI
    TruthValue, RowStatus, DisplayString
        FROM SNMPv2-TC
    InetAddressType, InetAddress
        FROM INET-ADDRESS-MIB
    rcCloudIq
        FROM RAPID-CITY;

rcCloudIqMib  MODULE-IDENTITY
       LAST-UPDATED "202007310000Z"
       ORGANIZATION "Extreme Networks"
       CONTACT-INFO "Prem Palarapu
                     Postal:  Extreme Networks
                              9 Northeastern Blvd
                              Salem, NH 03079
                     email:   ppalarapu@extremenetworks.com"

       DESCRIPTION  "VOSS MIB for the Extreme Cloud IQ mibs."

       REVISION "202007310000Z" -- 31 July 2020
       DESCRIPTION "Version 2:    Added rcCloudIqServerAddressOrigin"

       REVISION "201912090000Z" -- 09 December 2019
       DESCRIPTION "Version 1:    Generate File, add Cloud IQ objects based
	   			  on VOSS 8.1.1.0 release."
       ::= { rcCloudIq 0 }

rcCloudIqObjects              OBJECT IDENTIFIER ::= { rcCloudIq 1 }
rcCloudIqScalars              OBJECT IDENTIFIER ::= { rcCloudIqObjects 1 }

rcCloudIqAgentEnable  OBJECT-TYPE
    SYNTAX         TruthValue
    MAX-ACCESS     read-write
    STATUS         current
    DESCRIPTION    "Global enable/disable the Extreme Cloud IQ Agent to
    		   communicate to the Cloud IQ Manager."
    DEFVAL         { false }
    ::= { rcCloudIqScalars 1 }

rcCloudIqAgentVersion  OBJECT-TYPE
    SYNTAX         DisplayString (SIZE(1..80))
    MAX-ACCESS     read-only
    STATUS         current
    DESCRIPTION    "Show the Cloud IQ Agent verison running on the device"
    ::= { rcCloudIqScalars 2 }

rcCloudIqServerAddressType  OBJECT-TYPE
    SYNTAX         InetAddressType
    MAX-ACCESS     read-write
    STATUS         current
    DESCRIPTION    "The address type of the Cloud IQ server address."
    ::= { rcCloudIqScalars 3 }

rcCloudIqServerAddress  OBJECT-TYPE
    SYNTAX         InetAddress
    MAX-ACCESS     read-write
    STATUS         current
    DESCRIPTION    "The server address of the Cloud IQ Manager."
    ::= { rcCloudIqScalars 4 }

rcCloudIqProxyAddressType  OBJECT-TYPE
    SYNTAX         InetAddressType
    MAX-ACCESS     read-write
    STATUS         current
    DESCRIPTION    "The address type of the Cloud IQ proxy address."
    ::= { rcCloudIqScalars 5 }

rcCloudIqProxyAddress  OBJECT-TYPE
    SYNTAX         InetAddress
    MAX-ACCESS     read-write
    STATUS         current
    DESCRIPTION    "The proxy address of the Cloud IQ Manager."
    ::= { rcCloudIqScalars 6 }

rcCloudIqProxyTcpPort  OBJECT-TYPE
    SYNTAX         Integer32 (0..49151)
    MAX-ACCESS     read-write
    STATUS         current
    DESCRIPTION    "The TCP connection port used for the Cloud IQ feature."
    ::= { rcCloudIqScalars 7 }

rcCloudIqProxyUserName  OBJECT-TYPE
    SYNTAX         DisplayString (SIZE(0..64))
    MAX-ACCESS     read-write
    STATUS         current
    DESCRIPTION    "User name for the read-write all Cloud IQ account."
    ::= { rcCloudIqScalars 8 }

rcCloudIqProxyPassword  OBJECT-TYPE
    SYNTAX         DisplayString (SIZE(0..128))
    MAX-ACCESS     read-write
    STATUS         current
    DESCRIPTION    "Password for the read-write all Cloud IQ account."
    ::= { rcCloudIqScalars 9 }

rcCloudIqNotificationEnable  OBJECT-TYPE
    SYNTAX         TruthValue
    MAX-ACCESS     read-write
    STATUS         current
    DESCRIPTION    "Enable/disable the notification when the Cloud IQ feature
    		   support is not available."
    ::= { rcCloudIqScalars 10 }

rcCloudIqOperStatus  OBJECT-TYPE
    SYNTAX         INTEGER {
    		   	   connected(1),
			   disconnected(2)
	           }
    MAX-ACCESS     read-only
    STATUS         current
    DESCRIPTION    "Indicates the operational status of the Cloud IQ feature."
    ::= { rcCloudIqScalars 11 }

rcCloudIqAssociationUrl  OBJECT-TYPE
    SYNTAX         DisplayString
    MAX-ACCESS     read-only
    STATUS         current
    DESCRIPTION    "Indicates the Association URL of the Cloud IQ feature."
    ::= { rcCloudIqScalars 12 }

rcCloudIqPollUrl  OBJECT-TYPE
    SYNTAX         DisplayString
    MAX-ACCESS     read-only
    STATUS         current
    DESCRIPTION    "Indicates the Poll URL of the Cloud IQ feature."
    ::= { rcCloudIqScalars 13 }

rcCloudIqMonitorFreq  OBJECT-TYPE
    SYNTAX         Integer32
    UNITS          "seconds"
    MAX-ACCESS     read-only
    STATUS         current
    DESCRIPTION    "Indicates the Monitor Frequenct of the Cloud IQ feature."
    ::= { rcCloudIqScalars 14 }

rcCloudIqPollFreq  OBJECT-TYPE
    SYNTAX         Integer32
    UNITS          "seconds"
    MAX-ACCESS     read-only
    STATUS         current
    DESCRIPTION    "Indicates the Polling Frequency of the Cloud IQ feature."
    ::= { rcCloudIqScalars 15 }

 rcCloudIqLastOnboardTime  OBJECT-TYPE
    SYNTAX         DisplayString
    MAX-ACCESS     read-only
    STATUS         current
    DESCRIPTION    "Indicates the Last Onboard Time for the Cloud IQ feature."
    ::= { rcCloudIqScalars 16 }

 rcCloudIqLastPollStatus  OBJECT-TYPE
    SYNTAX         INTEGER {
    		   	   success(1),
			   error(2),
			   unknown(3)
	           }
    MAX-ACCESS     read-only
    STATUS         current
    DESCRIPTION    "Indicates the Last Poll Status the Cloud IQ feature."
    ::= { rcCloudIqScalars 17 }

 rcCloudIqLastPollTime  OBJECT-TYPE
    SYNTAX         DisplayString
    MAX-ACCESS     read-only
    STATUS         current
    DESCRIPTION    "Indicates the Last Poll Time for the Cloud IQ feature.
                    It is valid when the rcCloudIqLastPollStatus is success."
    ::= { rcCloudIqScalars 18 }

 rcCloudIqLastMonitorStatus  OBJECT-TYPE
    SYNTAX         INTEGER {
    		   	   success(1),
			   error(2),
			   unknown(3)
	           }
    MAX-ACCESS     read-only
    STATUS         current
    DESCRIPTION    "Indicates the Last Monitor Status the Cloud IQ feature."
    ::= { rcCloudIqScalars 19 }

 rcCloudIqLastMonitorTime  OBJECT-TYPE
    SYNTAX         DisplayString
    MAX-ACCESS     read-only
    STATUS         current
    DESCRIPTION    "Indicates the Last Monitor Time for the Cloud IQ feature.
                    It is valid when the rcCloudIqLastMonitorStatus is success."
    ::= { rcCloudIqScalars 20 }

 rcCloudIqLastHealthStatus  OBJECT-TYPE
    SYNTAX         INTEGER {
    		   	   success(1),
			   error(2),
			   unknown(3)
	           }
    MAX-ACCESS     read-only
    STATUS         current
    DESCRIPTION    "Indicates the Last Health Status the Cloud IQ feature."
    ::= { rcCloudIqScalars 21 }

 rcCloudIqLastHealthTime  OBJECT-TYPE
    SYNTAX         DisplayString
    MAX-ACCESS     read-only
    STATUS         current
    DESCRIPTION    "Indicates the Last Health Time for the Cloud IQ feature.
                    It is valid when the rcCloudIqLastMonitorStatus is success."
    ::= { rcCloudIqScalars 22 }


rcCloudIqServerAddressOrigin  OBJECT-TYPE
    SYNTAX         INTEGER {
                            none(1),    --Cloud IQ server not set
                            configured(2),     --Cloud IQ server manually configured
                            dhcp(3)        --Cloud IQ server obtained from DHCP
                           }
    MAX-ACCESS     read-only
    STATUS         current
    DESCRIPTION    "Origin of the Cloud IQ server address: either manual config or dynamic via DHCP option 43."
    ::= { rcCloudIqScalars 23 }

END
