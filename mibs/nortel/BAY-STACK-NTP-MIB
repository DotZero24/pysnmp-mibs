BAY-STACK-NTP-MIB DEFINITIONS ::= BEGIN

IMPORTS
    MODULE-IDENTITY, OBJECT-TYPE, Counter32, IpAddress, Integer32, Unsigned32
        FROM SNMPv2-SMI
    DisplayString, TruthValue, RowStatus, DateAndTime
        FROM SNMPv2-TC
    bayStackMibs
        FROM SYNOPTICS-ROOT-MIB
    InetAddressType, InetAddress
        FROM INET-ADDRESS-MIB;

bayStackNtpMib MODULE-IDENTITY
       LAST-UPDATED     "201809270000Z"
       ORGANIZATION     "Extreme Networks"
       CONTACT-INFO     "extremenetworks.com"
       DESCRIPTION      "Enterprise MIB for the NTP."

       REVISION "201809270000Z" -- 27 September 2018
       DESCRIPTION "Modified the DisplayString's allowed size for
                    bsNtpKeySecret from 1..8 to 0..20 (azmeu)"
       REVISION "201707070000Z" -- 07 July 2017
       DESCRIPTION "Version 1: Initial version."

       ::= { bayStackMibs 49 }

bsNtpNotifications      OBJECT IDENTIFIER ::= { bayStackNtpMib 0 }
bsNtpObjects            OBJECT IDENTIFIER ::= { bayStackNtpMib 1 }

-- Ntp Group
-- Ntp Global Information

bsNtpGlobal   OBJECT IDENTIFIER        ::= { bsNtpObjects 1 }

bsNtpGlobalEnable OBJECT-TYPE
     SYNTAX       TruthValue
     MAX-ACCESS	  read-write
     STATUS       current
     DESCRIPTION  "Enable/disable NTP feature"
     DEFVAL       { false }
     ::= { bsNtpGlobal 1 }



-- Ntp V4 Server Table Information

bsNtpServerTable OBJECT-TYPE
     SYNTAX       SEQUENCE OF BsNtpServerEntry
     MAX-ACCESS   not-accessible
     STATUS       current
     DESCRIPTION  "The NTP version 4 server table. This table lists the information
                   of a NTP server."
     ::= { bsNtpObjects 2 }

bsNtpServerEntry OBJECT-TYPE
        SYNTAX        BsNtpServerEntry
        MAX-ACCESS    not-accessible
        STATUS        current
        DESCRIPTION   "A NTP server table entry."
        INDEX         { bsNtpServerAddressType, bsNtpServerAddress }
        ::= { bsNtpServerTable 1 }

BsNtpServerEntry ::=
     SEQUENCE {
             bsNtpServerAddressType    InetAddressType,
             bsNtpServerAddress        InetAddress,
             bsNtpServerEnable         TruthValue,
             bsNtpServerAuthEnable     TruthValue,
             bsNtpServerKeyId          INTEGER,
             bsNtpServerAutokeyEnable  TruthValue,
             bsNtpServerVersion        Unsigned32,
             bsNtpServerStratum        Unsigned32,
             bsNtpServerRootDelay      DisplayString,
             bsNtpServerPrecision      Integer32,
             bsNtpServerReachable      DisplayString,
             bsNtpServerSynchronized   DisplayString,
             bsNtpServerPckSent        Counter32,
             bsNtpServerPckProcessed   Counter32,
             bsNtpServerPckDiscarded   Counter32,
             bsNtpServerRowStatus      RowStatus
     }

bsNtpServerAddressType OBJECT-TYPE
     SYNTAX         InetAddressType
     MAX-ACCESS     not-accessible
     STATUS         current
     DESCRIPTION    "Server IP address type of NTP time source referred to in
                     this table entry. It indicates the type of address
                     contained in bsNtpServerAddress."
     ::= { bsNtpServerEntry 1 }

bsNtpServerAddress OBJECT-TYPE
     SYNTAX         InetAddress
     MAX-ACCESS     not-accessible
     STATUS         current
     DESCRIPTION    "Server IP address of NTP time source referred to in
                     this table entry. The type of address is specified in
                     bsNtpServerAddressType."
     ::= { bsNtpServerEntry 2 }

bsNtpServerEnable OBJECT-TYPE
     SYNTAX         TruthValue
     MAX-ACCESS     read-write
     STATUS         current
     DESCRIPTION    "Enable or disable this server for participation in
                     time update."
     DEFVAL         { true }
     ::= { bsNtpServerEntry 3 }

bsNtpServerAuthEnable OBJECT-TYPE
     SYNTAX         TruthValue
     MAX-ACCESS     read-write
     STATUS         current
     DESCRIPTION    "Enable or disable the authentication on this
                     server."
     DEFVAL         { false }
     ::= { bsNtpServerEntry 4 }

bsNtpServerKeyId OBJECT-TYPE
     SYNTAX         INTEGER (0..65535)
     MAX-ACCESS     read-write
     STATUS         current
     DESCRIPTION    "Public Key used to generate MD5 digest for this
                     server."
     DEFVAL         { 1 }
     ::= { bsNtpServerEntry 5 }

bsNtpServerAutokeyEnable OBJECT-TYPE
     SYNTAX         TruthValue
     MAX-ACCESS     read-write
     STATUS         current
     DESCRIPTION    "Enable or disable autokey."
     DEFVAL         { false }
     ::= { bsNtpServerEntry 6 }

bsNtpServerVersion OBJECT-TYPE
     SYNTAX         Unsigned32
     MAX-ACCESS     read-only
     STATUS         current
     DESCRIPTION    "NTP version of this server"
     ::= { bsNtpServerEntry 7 }

bsNtpServerStratum OBJECT-TYPE
     SYNTAX         Unsigned32
     MAX-ACCESS     read-only
     STATUS         current
     DESCRIPTION    "Stratum of this server"
     ::= { bsNtpServerEntry 8 }

bsNtpServerRootDelay OBJECT-TYPE
     SYNTAX         DisplayString (SIZE (0..32))
     MAX-ACCESS     read-only
     STATUS         current
     DESCRIPTION    "Root Delay of this server"
     ::= { bsNtpServerEntry 9 }

bsNtpServerPrecision OBJECT-TYPE
     SYNTAX         Integer32
     MAX-ACCESS     read-only
     STATUS         current
     DESCRIPTION    "NTP precision of this server in seconds (represented as power of two)"
     ::= { bsNtpServerEntry 10 }

bsNtpServerReachable OBJECT-TYPE
     SYNTAX         DisplayString (SIZE (0..16))
     MAX-ACCESS     read-only
     STATUS         current
     DESCRIPTION    "NTP Reachability of this server"
     ::= { bsNtpServerEntry 11 }

bsNtpServerSynchronized OBJECT-TYPE
     SYNTAX         DisplayString (SIZE (0..16))
     MAX-ACCESS     read-only
     STATUS         current
     DESCRIPTION    "Status of synchronization with this server"
     ::= { bsNtpServerEntry 12 }

bsNtpServerPckSent OBJECT-TYPE
     SYNTAX         Counter32
     MAX-ACCESS     read-only
     STATUS         current
     DESCRIPTION    "The number of NTP packets sent to this server"
     ::= { bsNtpServerEntry 13 }

bsNtpServerPckProcessed OBJECT-TYPE
     SYNTAX         Counter32
     MAX-ACCESS     read-only
     STATUS         current
     DESCRIPTION    "The number of NTP processed packets"
     ::= { bsNtpServerEntry 14 }

bsNtpServerPckDiscarded OBJECT-TYPE
     SYNTAX         Counter32
     MAX-ACCESS     read-only
     STATUS         current
     DESCRIPTION    "The number of NTP discarded packets"
     ::= { bsNtpServerEntry 15 }

bsNtpServerRowStatus OBJECT-TYPE
        SYNTAX        RowStatus
        MAX-ACCESS    read-write
        STATUS        current
        DESCRIPTION   "Used to create/delete entries."
        ::= { bsNtpServerEntry 16 }



-- Ntp Key Table Information

bsNtpKeyTable OBJECT-TYPE
     SYNTAX       SEQUENCE OF BsNtpKeyEntry
     MAX-ACCESS   not-accessible
     STATUS       current
     DESCRIPTION  "The NTP key table. This table lists the private key
                   of the public key Id"
     ::= {bsNtpObjects 3 }

bsNtpKeyEntry OBJECT-TYPE
        SYNTAX        BsNtpKeyEntry
        MAX-ACCESS    not-accessible
        STATUS        current
        DESCRIPTION   "A NTP key table entry."
        INDEX         { bsNtpKeyId }
        ::= { bsNtpKeyTable 1 }

BsNtpKeyEntry ::=
     SEQUENCE {
             bsNtpKeyId        INTEGER,
	         bsNtpKeyType      INTEGER,
             bsNtpKeySecret    DisplayString,
             bsNtpKeyRowStatus RowStatus
     }

bsNtpKeyId OBJECT-TYPE
     SYNTAX         INTEGER (1..65535)
     MAX-ACCESS     read-only
     STATUS         current
     DESCRIPTION    "Public Key used to generate MD5 digest"
     ::= { bsNtpKeyEntry 1 }

bsNtpKeyType OBJECT-TYPE
    SYNTAX          INTEGER {
                        md5(1),
                        sha1(2)
                    }
    MAX-ACCESS      read-write
    STATUS          current
    DESCRIPTION     "Key type: MD5 or SHA1"
    DEFVAL          { 1 }
    ::= { bsNtpKeyEntry 2 }

bsNtpKeySecret OBJECT-TYPE
     SYNTAX         DisplayString (SIZE (0..20))
     MAX-ACCESS     read-write
     STATUS         current
     DESCRIPTION    "Private Key used to generate MD5 Digest"
     ::= { bsNtpKeyEntry 3 }

bsNtpKeyRowStatus OBJECT-TYPE
     SYNTAX        RowStatus
     MAX-ACCESS    read-write
     STATUS        current
     DESCRIPTION   "Used to create/delete entries."
     ::= { bsNtpKeyEntry 4 }

END
