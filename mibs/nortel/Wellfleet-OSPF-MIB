Wellfleet-OSPF-MIB DEFINITIONS ::= BEGIN

-- Created by mdl2asn version 3.1
-- Creation date: Wed Aug 30 16:46:11 EDT 1995
--
-- 96.03.06	mad	added wfOspfMaximumPath
--
-- 07/20/99 CR107161 Backup Soloist support is disabled.
--          wfOspfBackupDisable and wfOspfBackupLogMask were changed to
--          read-only from read-write -rmehta.


    IMPORTS

      IpAddress, Counter, Gauge
        FROM RFC1155-SMI
      OBJECT-TYPE
        FROM RFC-1212
      DisplayString
        FROM RFC1213-MIB
      wfOspfGroup
        FROM Wellfleet-COMMON-MIB;


    wfOspfGeneralGroup	OBJECT IDENTIFIER ::= { wfOspfGroup 1 }

    wfOspfGeneralDelete OBJECT-TYPE
        SYNTAX	INTEGER {
    		    created(1),
    		    deleted(2)
    		}
        ACCESS	read-write
        STATUS	mandatory
        DESCRIPTION
                "'This value determines whether OSPF is configured'"
        DEFVAL	{ created }
        ::= { wfOspfGeneralGroup 1 }

    wfOspfGeneralDisable OBJECT-TYPE
        SYNTAX	INTEGER {
    		    enabled(1),
    		    disabled(2)
    		}
        ACCESS	read-write
        STATUS	mandatory
        DESCRIPTION
                "'The administrative status of OSPF in the router.  The
                value 'enabled' denotes that the OSPF Process is active
                on at least one interface; 'disabled' disables it on
                all interfaces.'"
        DEFVAL	{ enabled }
        ::= { wfOspfGeneralGroup 2 }

    wfOspfGeneralState OBJECT-TYPE
        SYNTAX	INTEGER {
    		    up(1),
    		    down(2),
    		    init(3),
    		    notpresent(4)
    		}
        ACCESS	read-only
        STATUS	mandatory
        DESCRIPTION
                "'The state of OSPF'"
        DEFVAL	{ down }
        ::= { wfOspfGeneralGroup 3 }

    wfOspfRouterId OBJECT-TYPE
        SYNTAX	IpAddress
        ACCESS	read-write
        STATUS	mandatory
        DESCRIPTION
                "'A 32-bit integer uniquely identifying the router in
                the Autonomous System.

                By convention, to ensure uniqueness, this should
                default to the value of one of the router's IP
                interface addresses.'
                         REFERENCE
                'OSPF Version 2, C.1 Global parameters'"
        ::= { wfOspfGeneralGroup 4 }

    wfOspfVersionNumber OBJECT-TYPE
        SYNTAX	INTEGER
        ACCESS	read-only
        STATUS	mandatory
        DESCRIPTION
                "'The current version number of the OSPF protocol is 2.'
                         REFERENCE
                'OSPF Version 2, Title'"
        ::= { wfOspfGeneralGroup 5 }

    wfOspfAreaBdrRtrStatus OBJECT-TYPE
        SYNTAX	INTEGER {
    		    true(1),
    		    false(2)
    		}
        ACCESS	read-only
        STATUS	mandatory
        DESCRIPTION
                "'A flag to note whether this router is an area border
                router.'
                         REFERENCE
                'OSPF Version 2, Section 3 Splitting the AS into Areas'"
        DEFVAL	{ false }
        ::= { wfOspfGeneralGroup 6 }

    wfOspfASBdrRtrStatus OBJECT-TYPE
        SYNTAX	INTEGER {
    		    true(1),
    		    false(2)
    		}
        ACCESS	read-write
        STATUS	mandatory
        DESCRIPTION
                "'A flag to note whether this router is an Autonomous
                System border router.'
                         REFERENCE
                'OSPF Version 2, Section 3.3 Classification of routers'"
        DEFVAL	{ false }
        ::= { wfOspfGeneralGroup 7 }

    wfOspfTOSSupport OBJECT-TYPE
        SYNTAX	INTEGER {
    		    true(1),
    		    false(2)
    		}
        ACCESS	read-only
        STATUS	mandatory
        DESCRIPTION
                "'The router's support for type-of-service routing.'
                         REFERENCE
                'OSPF Version 2, Appendix F.1.2 Optional TOS support'"
        DEFVAL	{ false }
        ::= { wfOspfGeneralGroup 8 }

    wfOspfSpfHoldDown OBJECT-TYPE
        SYNTAX	INTEGER(0..10)
        ACCESS	read-write
        STATUS	mandatory
        DESCRIPTION
                "Hold Down Timer for the SPF.  The SPF will run at most
                once per hold down timer value.  A value of 0 means no
                hold down."
        DEFVAL	{ 1 }
        ::= { wfOspfGeneralGroup 9 }

    wfOspfSlotMask OBJECT-TYPE
        SYNTAX	Gauge
        ACCESS	read-write
        STATUS	mandatory
        DESCRIPTION
                "Slot mask for which slots OSPF is eligible
                to run on.  The MSBit represents slot 1, the
                next most significant bit represents slot 2,
                and so on...  Slots can be 1-14.
                Default is all slots on a BCN."
        DEFVAL	{ 4294705152 }
        ::= { wfOspfGeneralGroup 10 }

    wfOspfNewAseMetricSupport OBJECT-TYPE
        SYNTAX	INTEGER {
    		    enabled(1),
    		    disabled(2)
    		}
        ACCESS	read-write
        STATUS	mandatory
        DESCRIPTION
                "A parameter to specify if the new style ASE metric support
                is enabled.  The new metric is not compatible with the
                pre-8.0 ASE metrics.  The new metric support should be
                disabled if the router is to interoperate with routers
                running a pre-8.0 OSPF version."
        DEFVAL	{ disabled }
        ::= { wfOspfGeneralGroup 11 }

    wfOspfBackupDisable OBJECT-TYPE
        SYNTAX	INTEGER {
    		    enabled(1),
    		    disabled(2)
    		}
        ACCESS	read-only
        STATUS	mandatory
        DESCRIPTION
                "This parameter enables or disables the backup OSPF soloist's
                backup link state database.  When the parameter is set to disabled
                the OSPF backup soloist will not maintain a copy of the OSPF link
                state database."
        DEFVAL	{ disabled }
        ::= { wfOspfGeneralGroup 12 }

    wfOspfPrimaryLogMask OBJECT-TYPE
        SYNTAX	Gauge
        ACCESS	read-write
        STATUS	mandatory
        DESCRIPTION
                "A parameter to specify which OSPF log messages should be logged.
                This will only effect the Primary OSPF gate.
                Each bit represents a message as defined below.  A 1 in that
                bit location means to log it and a 0 means not to put that
                log message in the log.  Changing this value will NOT restart
                OSPF, but will take effct immediately(if there are any messages
                to be logged.

                bit 31                                bit 0
                +---------------------------------------+
                |                                       |
                +---------------------------------------+

                bit0  Trace Messages
                bit1  INFO Level messages
                bit2  debug level messages
                bit3  OSPF interface state change messages
                bit4  Nbr state changes
                bit5  self-origination of LSA's
                bit6  receipt of new LSA's
                bit7  changes to OSPF`s Routing Table
                bit8  Bad LS requests, Ack's, or updates
                bit9  receipt of less recent LSA's
                bit10 receipt of more recent self-originated LSA's
                bit11 receipt of MAxAge LSA's (i.e. LSA's being flushed)
                bit12 - 31 reserved
                "
        DEFVAL	{ 287 }
        ::= { wfOspfGeneralGroup 13 }

    wfOspfBackupLogMask OBJECT-TYPE
        SYNTAX	Gauge
        ACCESS	read-only
        STATUS	mandatory
        DESCRIPTION
                "A parameter to specify which OSPF log messages should be logged.
                This will only effect the Backup OSPF gate.
                Each bit represents a message as defined below.  A 1 in that
                bit location means to log it a 0 means not to put that
                log message in the log.  Changing this value will NOT restart
                OSPF, but will take effct immediately(if there are any messages
                to be logged.

                bit 31                                bit 0
                +---------------------------------------+
                |                                       |
                +---------------------------------------+

                bit0  Trace Messages
                bit1  INFO Level messages
                bit2  debug level messages
                bit3  OSPF interface state change messages
                bit4  Nbr state changes
                bit5  self-origination of LSA's
                bit6  receipt of new LSA's
                bit7  changes to OSPF`s Routing Table
                bit8  Bad LS requests, Ack's, or updates
                bit9  receipt of less recent LSA's
                bit10 receipt of more recent self-originated LSA's
                bit11 receipt of MAxAge LSA's (i.e. LSA's being flushed)
                bit12 - 31 reserved
                "
        ::= { wfOspfGeneralGroup 14 }

    wfOspfAseTagDefault OBJECT-TYPE
        SYNTAX	INTEGER {
    		    default(1),
    		    automatic(2),
    		    proprietary(3)
    		}
        ACCESS	read-write
        STATUS	mandatory
        DESCRIPTION
                "This parameter indicates how ASE tags will be generated for those
                ASEs whose tags are not altered by an export route filter or
                announce route policy.  default(1) indicates that a zero value is
                used.  automatic(2) indicates that an automatic tag will be generated
                as specified in RFC 1403. proprietary(3) indicates that the wellfleet
                proprietary scheme will be used.  In this case, the next hop
                is used for IGP routes and the neighbor AS is used for EGP routes."
        DEFVAL	{ default }
        ::= { wfOspfGeneralGroup 15 }

    wfOspfPrimarySlot OBJECT-TYPE
        SYNTAX	INTEGER
        ACCESS	read-only
        STATUS	mandatory
        DESCRIPTION
                "Slot on which OSPF Primary is running. Slots
                can be 1-14. Default is zero."
        ::= { wfOspfGeneralGroup 16 }

    wfOspfBackupSlot OBJECT-TYPE
        SYNTAX	INTEGER
        ACCESS	read-only
        STATUS	mandatory
        DESCRIPTION
                "Slot on which OSPF Backup is running. Slots
                can be 1-14. Default is zero."
        ::= { wfOspfGeneralGroup 17 }

    wfOspfMaximumPath OBJECT-TYPE
        SYNTAX	INTEGER (1..5)
        ACCESS	read-write
        STATUS	obsolete
        DESCRIPTION
                "Maximum number of equal cost paths allowed for a
                 network installed by OSPF."
        DEFVAL	{ 1 }
        ::= { wfOspfGeneralGroup 18 }

    wfOspfSlotPriority OBJECT-TYPE
        SYNTAX	DisplayString
        ACCESS	read-write
        STATUS	mandatory
        DESCRIPTION
                "Comma-separated list of slots specifying the order in which
                 slots should attempt to bring up OSPF soloist.
                 They are listed in the decreasing order of priority.
                 Slot with priority 0,
                 i.e. the first entry in the list, is most likely to
                 have OSPF soloist running on it."
        ::= { wfOspfGeneralGroup 19 }

    wfOspfLsdbCount OBJECT-TYPE
        SYNTAX  Counter
        ACCESS  read-only
        STATUS  mandatory
        DESCRIPTION
                "Running count of LSDB entries"
        ::= { wfOspfGeneralGroup 20 }

    wfOspfMulticastExtensions OBJECT-TYPE
        SYNTAX  INTEGER
        ACCESS  read-write
        STATUS  mandatory
        DESCRIPTION
           "A Bit Mask indicating whether  the  router  is
           forwarding  IP  multicast  (Class  D) datagrams
           based on the algorithms defined in  the  Multi-
           cast Extensions to OSPF.

           Bit 0, if set, indicates that  the  router  can
           forward  IP multicast datagrams in the router's
           directly attached areas (called intra-area mul-
           ticast routing).

           Bit 1, if set, indicates that  the  router  can
           forward  IP  multicast  datagrams  between OSPF
           areas (called inter-area multicast routing).

           Bit 2, if set, indicates that  the  router  can
           forward  IP  multicast  datagrams between Auto-
           nomous Systems (called inter-AS multicast rout-
           ing).

           Only certain combinations of bit  settings  are
           allowed,  namely: 0 (no multicast forwarding is
           enabled), 1 (intra-area multicasting  only),  3
           (intra-area  and  inter-area  multicasting),  5
           (intra-area and inter-AS  multicasting)  and  7
           (multicasting  everywhere). By default, no mul-
           ticast forwarding is enabled."

        DEFVAL  { 0 }
        ::= { wfOspfGeneralGroup 21 }

    wfOspfMulticastDeterministic OBJECT-TYPE
        SYNTAX   INTEGER {
                        nondeterministic(1),
                        deterministicstrict(2),
                        deterministicloose(3)
                }
        ACCESS   read-write
        STATUS   mandatory
        DESCRIPTION
                "This controls whether or not the deterministic
                variation of the MOSPF Dijkstra is run or not"
       DEFVAL { nondeterministic }
       ::= { wfOspfGeneralGroup 22 }

    wfOspfMulticastRoutePinning OBJECT-TYPE
        SYNTAX   INTEGER {
                        nonpinned(1),
                        pinned(2)
                }
        ACCESS   read-write
        STATUS   mandatory
        DESCRIPTION
               "This controls whether or not the route pinning
                variation of the MOSPF Dijkstra is run or not"
       DEFVAL { nonpinned }
       ::= { wfOspfGeneralGroup 23 }

    wfOspfOpaqueCapability OBJECT-TYPE
        SYNTAX  INTEGER {
                        enabled(1),
                        disabled(2)
                }
        ACCESS   read-write
        STATUS   mandatory
        DESCRIPTION
                "This controls whether or not the router will
                accept and process OPAQUE LSAs"
        DEFVAL { disabled }
       ::= { wfOspfGeneralGroup 24 }

    wfOspfDeterministicMcastHoldDown OBJECT-TYPE
        SYNTAX  INTEGER {
                        enabled(1),
                        disabled(2)
                }
        ACCESS   read-write
        STATUS   mandatory
        DESCRIPTION
                "This controls whether or not the Hold Down feature for
                 the Deterministic MOSPF is enabled. If it is enabled,
                 a data flow does not go out of an interface even if it
                 would when the feature is disabled, unless there is
                 a reservation for the flow on the interface"
        DEFVAL { disabled }
       ::= { wfOspfGeneralGroup 25 }

    wfMospfEntryTimeoutValue OBJECT-TYPE
        SYNTAX  INTEGER
        ACCESS  read-write
        STATUS  mandatory
        DESCRIPTION
                "The timer value for timing out MOSPF forward entries."
        DEFVAL  { 600 }
        ::= { wfOspfGeneralGroup 26 }

    wfOspfMaxQueuedMcastPkts OBJECT-TYPE
        SYNTAX  INTEGER
        ACCESS  read-write
        STATUS  mandatory
        DESCRIPTION
                "This controls how many mcast packets can be queued
		 on each slot for all flows before the building of
		 mcast trees finishes.

                 If it is not 0, the first a few data packets for a
		 mcast flow are queued before the building of the mcast
		 tree finishes.

		 Otherwise, packets are quietly dropped before the tree
		 is calculated."
        DEFVAL { 64 }
       ::= { wfOspfGeneralGroup 27 }

    wfOspfMcastUseDynTTL OBJECT-TYPE
        SYNTAX  INTEGER {
                        enabled(1),
                        disabled(2)
                }
        ACCESS  read-write
        STATUS  mandatory
        DESCRIPTION
                "This controls whether dynamic TTL threshold is used.
		 Data forwarding is a little bit faster when it is NOT used.

		 Dynamic TTL means the TTL threshold may be different
		 per (source, group, downstream) tuple. See MOSPF spec,
		 section 2.3.4."
        DEFVAL { disabled }
       ::= { wfOspfGeneralGroup 28 }

    wfOspfRfc1583Compatibility OBJECT-TYPE
        SYNTAX  INTEGER {
                        enabled(1),
                        disabled(2)
                }
        ACCESS  read-write
        STATUS  mandatory
        DESCRIPTION
                "Controls the preference rules used when choosing among
                 multiple AS-external-LSAs advertising the same destination.
                 When set to 'enabled', the preference rules remain those
                 specified by RFC 1583. When set to 'disabled', the
                 preference rules are those stated in RFC 2178, which
                 prevent routing loops when AS- external-LSAs for the same
                 destination have been originated from different areas."
        DEFVAL { enabled }
       ::= { wfOspfGeneralGroup 29 }

    wfOspfASEMcastEnable OBJECT-TYPE
        SYNTAX  INTEGER {
                    enabled(1),
                    disabled(2)
                }
        ACCESS  read-write
        STATUS  mandatory
        DESCRIPTION
                "This attribute indicates whether AS External routes
                 are multicast capable. If enabled, the advertising
                 ASBR sets the MC-bit in the ASE-LSAs for those routes,
                 so that they can be used for multicast purpose.

                 If an MOSPF router works as an ASBR to support IGMP Relay,
		 it should has this attribute set to 'enabled'.

                 By default, all external routes are multicast incapable.
                 If it's known that an ASBR's external routes can only
                 be used for unicast, this attribute must be set to
                 'disabled' on the ASBR.

                 For example, if an ASBR has a BGP connection to an ISP
                 but the routes learned via BGP can't be used for multicast
                 because external multicast traffic should be injected by
                 another router with a DVMRP tunnel to Mbone, this
                 attribute on the ASBR should be set to 'disabled'."

        DEFVAL  { disabled }
        ::= { wfOspfGeneralGroup 30 }

    wfOspfNssaBorderRouter OBJECT-TYPE
        SYNTAX	 INTEGER {
    		    yes(1),
    		    no(2)
    		}
        ACCESS	 read-only
        STATUS	 mandatory
        DESCRIPTION
                "`A flag to note whether this router NSSA border router'"
	 DEFVAL	 { no }
        ::= { wfOspfGeneralGroup 31}

    wfOspfLsaRefreshMax OBJECT-TYPE
        SYNTAX   INTEGER
        ACCESS   read-write
        STATUS   mandatory
        DESCRIPTION
                "`Maximum number of consecutive refreshes of self-originated
                  Summary and External LSAs before applying a configured
                  delay. A value of zero implies that there is no maximum.'"
         DEFVAL  { 0 }
        ::= { wfOspfGeneralGroup 32}


    wfOspfLsaRefreshDelay OBJECT-TYPE
        SYNTAX   INTEGER( 1..5 )
        ACCESS   read-write
        STATUS   mandatory
        DESCRIPTION
                "`Delay to apply between the maximum number of consecutive
                  refreshes of self-originated Summary and External LSAs
                  if a non-zero maximum is configured. The unit of delay is
                  in seconds.'"
         DEFVAL  { 1 }
        ::= { wfOspfGeneralGroup 33}

    wfOspfAggrUseMaxCost OBJECT-TYPE
        SYNTAX  INTEGER {
                    enabled(1),
                    disabled(2)
                }
        ACCESS  read-write
        STATUS  mandatory
        DESCRIPTION
                "When area range is configured, sum net lsa is generated
                 depends on this mib attribute:
                 enabled:  Use Max Metric to aggregate networks.
                           See RFC2328 3.5 IP subnetting support.
                 disabled: Use Min Metric to aggregate networks.
                           Bay Router pre-14.40 version does this way."
        DEFVAL  { disabled }
        ::= { wfOspfGeneralGroup 34 }

    wfOspfFwdAddrComp OBJECT-TYPE
        SYNTAX  INTEGER {
                    enabled(1),
                    disabled(2)
                }
        ACCESS  read-write
        STATUS  mandatory
        DESCRIPTION
                "When enabled allows OSPF to comply with RFC1583 with
                 respect to forwarding address changes. When disabled
                 OSPF remains compatiable with pre-14.00rev1D code."

        DEFVAL  { enabled }
        ::= { wfOspfGeneralGroup 35 }

    wfOspfMtuUseCommonDefault OBJECT-TYPE
        SYNTAX  INTEGER {
                    enabled(1),
                    disabled(2)
                }
        ACCESS  read-write
        STATUS  mandatory
        DESCRIPTION
               "when this parameter is enabled, OSPF will use the MTU size of
                ethernet, that is, 1500 in all the interfaces regardless of
                what IP passes onto OSPF if the wfOspfMtuSize at the interface
                is set to 1(= Default) or 2. If wfOspfMtuSize is greater than
                2 then OSPF will use wfOspfMtuSize as the MTU size at the
                interface."
        DEFVAL  { disabled }
        ::= { wfOspfGeneralGroup 36 }

    wfOspfAreaTable OBJECT-TYPE
        SYNTAX	SEQUENCE OF WfOspfAreaEntry
        ACCESS	not-accessible
        STATUS	mandatory
        DESCRIPTION
                "--      The OSPF Area Data Structure contains information
                 --      regarding the various areas. The interfaces and
                 --      virtual links are configured as part of these areas.
                 --      Area 0.0.0.0, by definition, is the Backbone Area
                         'Information describing the configured parameters and
                         cumulative statistics of the router's attached areas.'
                 REFERENCE
                         'OSPF Version 2, Section 6  The Area Data Structure'"
        ::= { wfOspfGroup 2 }

    wfOspfAreaEntry OBJECT-TYPE
        SYNTAX	WfOspfAreaEntry
        ACCESS	not-accessible
        STATUS	mandatory
        DESCRIPTION
                "'Information describing the configured parameters and
                cumulative statistics of one of the router's attached
                areas.'"
        INDEX	{ wfOspfAreaId }
        ::= { wfOspfAreaTable 1 }

    WfOspfAreaEntry ::= SEQUENCE {
    	    wfOspfAreaDelete
    		INTEGER,
    	    wfOspfAreaDisable
    		INTEGER,
    	    wfOspfAreaState
    		INTEGER,
    	    wfOspfAreaId
    		IpAddress,
    	    wfOspfAuthType
    		INTEGER,
    	    wfOspfImportASExtern
    		INTEGER,
    	    wfOspfStubMetric
    		INTEGER,
    	    wfOspfImportSum
    		INTEGER,
    	    wfOspfSpfCnt
    		Counter,
            wfOspfPtpSpecCostEnable
                INTEGER,
	    wfOspfAreaNssaTranslateCfg
                INTEGER,
	    wfOspfAreaNssaTranslateStatus
                INTEGER,
	    wfOspfAreaNssaOriginateDefaultRoute
                INTEGER,
	    wfOspfAreaNssaPropagateDefaultRoute
                INTEGER,
	    wfOspfAreaNssaDefaultRoutePathType
                INTEGER
    }

    wfOspfAreaDelete OBJECT-TYPE
        SYNTAX	INTEGER {
    		    created(1),
    		    deleted(2)
    		}
        ACCESS	read-write
        STATUS	mandatory
        DESCRIPTION
                "This value determines if the OSPF router is configured with
                     this area."
        DEFVAL	{ created }
        ::= { wfOspfAreaEntry 1 }

    wfOspfAreaDisable OBJECT-TYPE
        SYNTAX	INTEGER {
    		    enabled(1),
    		    disabled(2)
    		}
        ACCESS	read-write
        STATUS	mandatory
        DESCRIPTION
                "This value indicates the state of this area on the OSPF
                router."
        DEFVAL	{ enabled }
        ::= { wfOspfAreaEntry 2 }

    wfOspfAreaState OBJECT-TYPE
        SYNTAX	INTEGER {
    		    up(1),
    		    down(2)
    		}
        ACCESS	read-only
        STATUS	mandatory
        DESCRIPTION
                "This value indicates the state of the OSPF Area."
        DEFVAL	{ down }
        ::= { wfOspfAreaEntry 3 }

    wfOspfAreaId OBJECT-TYPE
        SYNTAX	IpAddress
        ACCESS	read-only
        STATUS	mandatory
        DESCRIPTION
                "'A 32-bit integer uniquely identifying an area.  Area
                ID 0.0.0.0 is used for the OSPF backbone.'
                         REFERENCE
                'OSPF Version 2, Appendix C.2 Area parameters'"
        ::= { wfOspfAreaEntry 4 }

    wfOspfAuthType OBJECT-TYPE
        SYNTAX	INTEGER {
    		    none(1),
    		    simple-password(2)
    		}
        ACCESS	read-write
        STATUS	mandatory
        DESCRIPTION
                "'The authentication type specified for an area.
                Additional authentication types may be assigned locally
                on a per Area basis.'
                         REFERENCE
                'OSPF Version 2, Appendix E Authentication'
                         -- none (0),
                         -- simplePassword (1)
                         -- reserved for future specification (2..255)
                         -- reserved for AS specific values (> 255)"
        DEFVAL	{ none }
        ::= { wfOspfAreaEntry 5 }

    wfOspfImportASExtern OBJECT-TYPE
        SYNTAX	INTEGER {
                    importExternal (1),
                    importNoExternal (2),
                    importNssa (3)
     		}
        ACCESS	read-write
        STATUS	mandatory
        DESCRIPTION
                "'The area's support for importing AS external link-
                state advertisements.'
                         REFERENCE
                `OSPF NSSA Internet Draft, Appendix D: Configuration
		Parameters'"
        DEFVAL	{ importExternal }
        ::= { wfOspfAreaEntry 6 }

    wfOspfStubMetric OBJECT-TYPE
        SYNTAX	INTEGER(1..16777215)
        ACCESS	read-write
        STATUS	mandatory
        DESCRIPTION
                "'The metric value applied at the indicated type of
                service.  By default, this equals the least metric at
                the type of service among the interfaces to other
                areas.'"
        DEFVAL	{ 1 }
        ::= { wfOspfAreaEntry 7 }

    wfOspfImportSum OBJECT-TYPE
        SYNTAX	INTEGER {
    		    true(1),
    		    false(2)
    		}
        ACCESS	read-write
        STATUS	mandatory
        DESCRIPTION
                "'The area's support for importing Summary
                advertisements into a stub area.  This variable
                   should not be set unless wfOspfImportASExtern is
                   set to FALSE'"
        DEFVAL	{ true }
        ::= { wfOspfAreaEntry 8 }

    wfOspfSpfCnt OBJECT-TYPE
        SYNTAX	Counter
        ACCESS	read-only
        STATUS	mandatory
        DESCRIPTION
                "The number of times the OSPF SPF algorithm
                has been run for this area."
        ::= { wfOspfAreaEntry 9 }

    wfOspfPtpSpecCostEnable OBJECT-TYPE
        SYNTAX  INTEGER {
                    enabled(1),
                    disabled(2)
                }
        ACCESS  read-write
        STATUS  mandatory
        DESCRIPTION
                "This value indicates the formula used to calculate the
                cost for point to point links."
        DEFVAL  { enabled }
        ::= { wfOspfAreaEntry 10 }

    wfOspfAreaNssaTranslateCfg OBJECT-TYPE
        SYNTAX	 INTEGER {
                enabled (1),
                disabled (2) 		}
        ACCESS	 read-write
        STATUS	 mandatory
        DESCRIPTION
	        "`Indicates whether or not an NSSA Border routes is configured
		  to performing NSSA translation of type-7 LSAs into type-5
		  LSAs.'
                         REFERENCE
                `OSPF NSSA Internet Draft, Appendix D: Configuration
	         Parameters'"
        DEFVAL	{ disabled}
        ::= { wfOspfAreaEntry 11 }

    wfOspfAreaNssaTranslateStatus OBJECT-TYPE
        SYNTAX	 INTEGER {
                translating (1),
                nottranslating (2) 		}
        ACCESS	 read-only
        STATUS	 mandatory
        DESCRIPTION
	        "`Indicates whether or not an NSSA Border routes is
		  performing NSSA translation of type-7 LSAs into type-5 LSAs.'
                         REFERENCE
                `OSPF NSSA Internet Draft, Appendix D: Configuration
                 Parameters'"
        DEFVAL	{ nottranslating}
        ::= { wfOspfAreaEntry 12 }

    wfOspfAreaNssaOriginateDefaultRoute OBJECT-TYPE
        SYNTAX	 INTEGER {
                enabled (1),
                disabled (2)   		}
        ACCESS	 read-write
        STATUS 	mandatory
        DESCRIPTION
                "`whether or not an Type-7 default is originated by the ASBR'"
        DEFVAL	 { disabled }
        ::= { wfOspfAreaEntry 13}

    wfOspfAreaNssaPropagateDefaultRoute OBJECT-TYPE
        SYNTAX	 INTEGER {
                enabled (1),
                disabled (2)   		}
        ACCESS	 read-write
        STATUS 	mandatory
        DESCRIPTION
                "`Indicates whether or not the Type-7 default route LSA will
		  have the propagate bit (P-bit) set. If the  P-bit is set,
		  the Type-7 default route LSA is translated into a Type-5
	          default route LSA and the Type-5 default route LSA is
		  flooded into all non-stub areas. Otherwise the Type-7 default
		  route LSA is not translated
		  This parameter applies to NSSA internal ASBR only. For
		  NSSA border ASBR, the P-bit is never set'"
        DEFVAL	 { disabled }
        ::= { wfOspfAreaEntry 14}

   wfOspfAreaNssaDefaultRoutePathType OBJECT-TYPE
        SYNTAX	 INTEGER {
                type1 (1),
                type2 (2)   		}
        ACCESS	 read-write
        STATUS 	mandatory
        DESCRIPTION
                "`The path type applied to the type-7 default route'
                         REFERENCE
                `OSPF NSSA Internet Draft, Appendix D: Configuration
                 Parameters'"
        DEFVAL	 { type1 }
        ::= { wfOspfAreaEntry 15 }

    wfMospfForwardTable OBJECT-TYPE
        SYNTAX  SEQUENCE OF WfMospfForwardEntry
        ACCESS  not-accessible
        STATUS  mandatory
        DESCRIPTION
                ""
        ::= { wfOspfGroup 11 }

    wfMospfForwardEntry OBJECT-TYPE
        SYNTAX  WfMospfForwardEntry
        ACCESS  not-accessible
        STATUS  mandatory
        DESCRIPTION
                "A forwarding entry"
        INDEX   { wfMospfForwardGroup,
                  wfMospfForwardSource,
                  wfMospfForwardSourceMask }
        ::= { wfMospfForwardTable 1 }

    WfMospfForwardEntry ::= SEQUENCE {
            wfMospfForwardGroup
                IpAddress,
            wfMospfForwardSource
                IpAddress,
            wfMospfForwardSourceMask
                IpAddress,
            wfMospfForwardSourceNetMask
                IpAddress,
            wfMospfForwardFlag
                INTEGER,
            wfMospfForwardUpstreamAddress
                IpAddress,
            wfMospfForwardUpstreamIfIndex
                INTEGER,
            wfMospfForwardBwBucketDepth
                INTEGER,
            wfMospfForwardBwBucketRate
                INTEGER,
            wfMospfForwardAge
                INTEGER,
            wfMospfForwardDownstream
                OCTET STRING
        }

    wfMospfForwardGroup OBJECT-TYPE
        SYNTAX  IpAddress
        ACCESS  read-only
        STATUS  mandatory
        DESCRIPTION
                "The destinatino group address of this entry"
        ::= { wfMospfForwardEntry 2 }

    wfMospfForwardSource OBJECT-TYPE
        SYNTAX  IpAddress
        ACCESS  read-only
        STATUS  mandatory
        DESCRIPTION
                "The source IP address of this entry. It could be either
                 a host, or a network, depending upon the value of
                 wfMospfForwardSourceMask"
        ::= { wfMospfForwardEntry 1 }

    wfMospfForwardSourceMask OBJECT-TYPE
        SYNTAX  IpAddress
        ACCESS  read-only
        STATUS  mandatory
        DESCRIPTION
                "The mask for the source of this entry."
        ::= { wfMospfForwardEntry 3 }

    wfMospfForwardSourceNetMask OBJECT-TYPE
        SYNTAX  IpAddress
        ACCESS  read-only
        STATUS  mandatory
        DESCRIPTION
                "The mask for the network that the source is on."
        ::= { wfMospfForwardEntry 4 }

    wfMospfForwardFlag OBJECT-TYPE
        SYNTAX  INTEGER
        ACCESS  read-only
        STATUS  mandatory
        DESCRIPTION
                "Flags associated with the entry.
		 0x10000000  (re)calculation of the entry not done yet
		 0x00000001  the entry is associated with a RSVP session"
        ::= { wfMospfForwardEntry 5 }

    wfMospfForwardUpstreamAddress OBJECT-TYPE
        SYNTAX  IpAddress
        ACCESS  read-only
        STATUS  mandatory
        DESCRIPTION
                "The IP address of the upstream intf for the entry."
        ::= { wfMospfForwardEntry 6 }

    wfMospfForwardUpstreamIfIndex OBJECT-TYPE
        SYNTAX  INTEGER
        ACCESS  read-only
        STATUS  mandatory
        DESCRIPTION
                "The circuit number of the upstream intf for the entry."
        ::= { wfMospfForwardEntry 7 }

    wfMospfForwardBwBucketDepth OBJECT-TYPE
        SYNTAX  INTEGER
        ACCESS  read-only
        STATUS  mandatory
        DESCRIPTION
                "Depth parameter of the flow spec for the entry"
        ::= { wfMospfForwardEntry 8 }

    wfMospfForwardBwBucketRate OBJECT-TYPE
        SYNTAX  INTEGER
        ACCESS  read-only
        STATUS  mandatory
        DESCRIPTION
                "Rate parameter of the flow spec for the entry"
        ::= { wfMospfForwardEntry 9 }

    wfMospfForwardAge OBJECT-TYPE
        SYNTAX  INTEGER
        ACCESS  read-only
        STATUS  mandatory
        DESCRIPTION
                "The number of seconds since this route was last
                updated or otherwise determined to be correct."
        ::= { wfMospfForwardEntry 10 }

    wfMospfForwardDownstream OBJECT-TYPE
        SYNTAX  OCTET STRING
        ACCESS  read-only
        STATUS  mandatory
        DESCRIPTION
                "list of downstream intfs for this entry. Each one is
                 in the format of (intf_addr (u_int32), intf_cct (u_int16),
                 ttl (u_int16))"
        ::= { wfMospfForwardEntry 11 }

    wfOspfLsdbTable OBJECT-TYPE
        SYNTAX	SEQUENCE OF WfOspfLsdbEntry
        ACCESS	not-accessible
        STATUS	mandatory
        DESCRIPTION
                "--  OSPF Link State Database

                --      The Link State Database contains the Link State
                --      Advertisements from throughout the areas that the
                --      device is attached to.
                       'The OSPF Process's Links State Database.'
                    REFERENCE
                       'OSPF Version 2, Section 12 Link State Advertisements'"
        ::= { wfOspfGroup 3 }

    wfOspfLsdbEntry OBJECT-TYPE
        SYNTAX	WfOspfLsdbEntry
        ACCESS	not-accessible
        STATUS	mandatory
        DESCRIPTION
                "'A single Link State Advertisement.'"
        INDEX	{ wfOspfLsdbAreaId,
    		  wfOspfLsdbType,
    		  wfOspfLsdbLSID,
    		  wfOspfLsdbRouterId }
        ::= { wfOspfLsdbTable 1 }

    WfOspfLsdbEntry ::= SEQUENCE {
    	    wfOspfLsdbAreaId
    		IpAddress,
    	    wfOspfLsdbType
    		INTEGER,
    	    wfOspfLsdbLSID
    		IpAddress,
    	    wfOspfLsdbRouterId
    		IpAddress,
    	    wfOspfLsdbSequence
    		INTEGER,
    	    wfOspfLsdbAge
    		INTEGER,
    	    wfOspfLsdbChecksum
    		INTEGER,
    	    wfOspfLsdbMetric
    		INTEGER,
    	    wfOspfLsdbAseForwardAddr
    		IpAddress,
    	    wfOspfLsdbAseTag
    		Gauge,
    	    wfOspfLsdbAseType
    		INTEGER,
    	    wfOspfLsdbAdvLen
    		INTEGER,
    	    wfOspfLsdbAdv
    		OCTET STRING
        }

    wfOspfLsdbAreaId OBJECT-TYPE
        SYNTAX	IpAddress
        ACCESS	read-only
        STATUS	mandatory
        DESCRIPTION
                "'The 32 bit identifier of the Area from which the LSA
                was received.'
                         REFERENCE
                'OSPF Version 2, Appendix C.2 Area parameters'"
        ::= { wfOspfLsdbEntry 1 }

    wfOspfLsdbType OBJECT-TYPE
        SYNTAX  INTEGER {
                    routerlink(1),
                    networklink(2),
                    summarylink(3),
                    assummarylink(4),
                    asexternallink(5),
                    multicastlink(6),
                    nssaasexternallink(7),
                    opaquelink(15),
                    resourcelink(16)
                }
        ACCESS  read-only
        STATUS  mandatory
        DESCRIPTION
                "'The type of the link state advertisement.  Each link
                state type has a separate advertisement format.'
                         REFERENCE
                'OSPF Version 2, Appendix A.4.1 The Link State
                Advertisement header'
                       stubLink   (0),
                       routerLink (1),
                       networkLink (2),
                       summaryLink (3),
                       asSummaryLink (4),
                       asExternalLink (5),
                       multicastlink (6),
                       opaquelink (15),
                       resourcelink (16)"
        ::= { wfOspfLsdbEntry 2 }

    wfOspfLsdbLSID OBJECT-TYPE
        SYNTAX	IpAddress
        ACCESS	read-only
        STATUS	mandatory
        DESCRIPTION
                "'The Link State ID is an LS Type Specific field
                containing either a Router ID or an IP Address; it
                identifies the piece of the routing domain that is
                being described by the advertisement.'
                         REFERENCE
                'OSPF Version 2, Section 12.1.4 Link State ID'"
        ::= { wfOspfLsdbEntry 3 }

    wfOspfLsdbRouterId OBJECT-TYPE
        SYNTAX	IpAddress
        ACCESS	read-only
        STATUS	mandatory
        DESCRIPTION
                "'The 32 bit number that uniquely identifies the
                originating router in the Autonomous System.'
                         REFERENCE
                'OSPF Version 2, Appendix C.1 Global parameters'"
        ::= { wfOspfLsdbEntry 4 }

    wfOspfLsdbSequence OBJECT-TYPE
        SYNTAX	INTEGER
        ACCESS	read-only
        STATUS	mandatory
        DESCRIPTION
                "--  Note that the OSPF Sequence Number is a 32 bit signed
                --  integer.  It starts with the value '80000001'h,
                --  or -'7FFFFFFF'h, and increments until '7FFFFFFF'h
                --  Thus, a typical sequence number will be very negative.
                       'The sequence number field is a signed 32-bit integer.
                       It is used to detect old and duplicate link state
                       advertisements.  The space of sequence numbers is
                       linearly ordered.  The larger the sequence number the
                       more recent the advertisement.'
                    REFERENCE
                       'OSPF Version 2, Section 12.1.6 LS sequence number'"
        ::= { wfOspfLsdbEntry 5 }

    wfOspfLsdbAge OBJECT-TYPE
        SYNTAX	INTEGER(0..3600)
        ACCESS	read-only
        STATUS	mandatory
        DESCRIPTION
                "'This field is the age of the link state advertisement
                in seconds.'
                      (OSPF_LSDBMINAGE = 0)
                         REFERENCE
                'OSPF Version 2, Section 12.1.1 LS age'"
        ::= { wfOspfLsdbEntry 6 }

    wfOspfLsdbChecksum OBJECT-TYPE
        SYNTAX	INTEGER
        ACCESS	read-only
        STATUS	mandatory
        DESCRIPTION
                "'This field is the checksum of the complete contents of
                the advertisement, excepting the age field.  The age
                field is excepted so that an advertisement's age can be
                incremented without updating the checksum.  The
                checksum used is the same that is used for ISO
                connectionless datagrams; it is commonly referred to as
                the Fletcher checksum.'
                         REFERENCE
                'OSPF Version 2, Section 12.1.7 LS checksum'"
        ::= { wfOspfLsdbEntry 7 }

    wfOspfLsdbMetric OBJECT-TYPE
        SYNTAX	INTEGER
        ACCESS	read-only
        STATUS	mandatory
        DESCRIPTION
                "'Metric from LSA, if applicable.'"
        ::= { wfOspfLsdbEntry 8 }

    wfOspfLsdbAseForwardAddr OBJECT-TYPE
        SYNTAX	IpAddress
        ACCESS	read-only
        STATUS	mandatory
        DESCRIPTION
                "'If an ASE, the forwarding address from the LSA.'"
        ::= { wfOspfLsdbEntry 9 }

    wfOspfLsdbAseTag OBJECT-TYPE
        SYNTAX	Gauge
        ACCESS	read-only
        STATUS	mandatory
        DESCRIPTION
                "'If an ASE, the External Route Tag from the LSA.'"
        ::= { wfOspfLsdbEntry 10 }

    wfOspfLsdbAseType OBJECT-TYPE
        SYNTAX	INTEGER {
    		    type1(1),
    		    type2(2)
    		}
        ACCESS	read-only
        STATUS	mandatory
        DESCRIPTION
                "'If an ASE, the external metric type from the LSA.'"
        ::= { wfOspfLsdbEntry 11 }

    wfOspfLsdbAdvLen OBJECT-TYPE
        SYNTAX	INTEGER
        ACCESS	read-only
        STATUS	mandatory
        DESCRIPTION
                "'The length of entire Link State Advertisement, including its
                header.'
                         REFERENCE
                'OSPF Version 2, Section 12 Link State Advertisements'"
        ::= { wfOspfLsdbEntry 12 }

    wfOspfLsdbAdv OBJECT-TYPE
        SYNTAX	OCTET STRING
        ACCESS	read-only
        STATUS	mandatory
        DESCRIPTION
                "'This field is the actual OSPF advertisement in hexadecimal
                 format' "
        ::= { wfOspfLsdbEntry 13 }

    wfOspfBackupLsdbTable OBJECT-TYPE
        SYNTAX	SEQUENCE OF WfOspfBackupLsdbEntry
        ACCESS	not-accessible
        STATUS	mandatory
        DESCRIPTION
                "--  OSPF Backup Link State Database

                --      The Backup Link State Database contains the Link State
                --      Advertisements from throughout the areas that the
                --      device is attached to.
                       'The OSPF Process's Links State Database.'
                    REFERENCE
                       'OSPF Version 2, Section 12 Link State Advertisements'"
        ::= { wfOspfGroup 10 }

    wfOspfBackupLsdbEntry OBJECT-TYPE
        SYNTAX	WfOspfBackupLsdbEntry
        ACCESS	not-accessible
        STATUS	mandatory
        DESCRIPTION
                "'A single Link State Advertisement.'"
        INDEX	{ wfOspfBackupLsdbAreaId,
    		  wfOspfBackupLsdbType,
    		  wfOspfBackupLsdbLSID,
    		  wfOspfBackupLsdbRouterId }
        ::= { wfOspfBackupLsdbTable 1 }

    WfOspfBackupLsdbEntry ::= SEQUENCE {
    	    wfOspfBackupLsdbAreaId
    		IpAddress,
    	    wfOspfBackupLsdbType
    		INTEGER,
    	    wfOspfBackupLsdbLSID
    		IpAddress,
    	    wfOspfBackupLsdbRouterId
    		IpAddress,
    	    wfOspfBackupLsdbSequence
    		INTEGER,
    	    wfOspfBackupLsdbAge
    		INTEGER,
    	    wfOspfBackupLsdbChecksum
    		INTEGER,
    	    wfOspfBackupLsdbMetric
    		INTEGER,
    	    wfOspfBackupLsdbAseForwardAddr
    		IpAddress,
    	    wfOspfBackupLsdbAseTag
    		Gauge,
    	    wfOspfBackupLsdbAseType
    		INTEGER,
    	    wfOspfBackupLsdbAdvLen
    		INTEGER,
    	    wfOspfBackupLsdbAdv
    		OCTET STRING
        }

    wfOspfBackupLsdbAreaId OBJECT-TYPE
        SYNTAX	IpAddress
        ACCESS	read-only
        STATUS	mandatory
        DESCRIPTION
                "'The 32 bit identifier of the Area from which the LSA
                was received.'
                         REFERENCE
                'OSPF Version 2, Appendix C.2 Area parameters'"
        ::= { wfOspfBackupLsdbEntry 1 }

    wfOspfBackupLsdbType OBJECT-TYPE
        SYNTAX	INTEGER {
    		    routerlink(1),
    		    networklink(2),
    		    summarylink(3),
    		    assummarylink(4),
    		    asexternallink(5),
                    nssaasexternallink(7)
    		}
        ACCESS	read-only
        STATUS	mandatory
        DESCRIPTION
                "'The type of the link state advertisement.  Each link
                state type has a separate advertisement format.'
                         REFERENCE
                'OSPF Version 2, Appendix A.4.1 The Link State
                Advertisement header'
                       stubLink   (0),
                         routerLink (1),
                         networkLink (2),
                         summaryLink (3),
                         asSummaryLink (4),
                         asExternalLink (5)"
        ::= { wfOspfBackupLsdbEntry 2 }

    wfOspfBackupLsdbLSID OBJECT-TYPE
        SYNTAX	IpAddress
        ACCESS	read-only
        STATUS	mandatory
        DESCRIPTION
                "'The Link State ID is an LS Type Specific field
                containing either a Router ID or an IP Address; it
                identifies the piece of the routing domain that is
                being described by the advertisement.'
                         REFERENCE
                'OSPF Version 2, Section 12.1.4 Link State ID'"
        ::= { wfOspfBackupLsdbEntry 3 }

    wfOspfBackupLsdbRouterId OBJECT-TYPE
        SYNTAX	IpAddress
        ACCESS	read-only
        STATUS	mandatory
        DESCRIPTION
                "'The 32 bit number that uniquely identifies the
                originating router in the Autonomous System.'
                         REFERENCE
                'OSPF Version 2, Appendix C.1 Global parameters'"
        ::= { wfOspfBackupLsdbEntry 4 }

    wfOspfBackupLsdbSequence OBJECT-TYPE
        SYNTAX	INTEGER
        ACCESS	read-only
        STATUS	mandatory
        DESCRIPTION
                "--  Note that the OSPF Sequence Number is a 32 bit signed
                --  integer.  It starts with the value '80000001'h,
                --  or -'7FFFFFFF'h, and increments until '7FFFFFFF'h
                --  Thus, a typical sequence number will be very negative.
                       'The sequence number field is a signed 32-bit integer.
                       It is used to detect old and duplicate link state
                       advertisements.  The space of sequence numbers is
                       linearly ordered.  The larger the sequence number the
                       more recent the advertisement.'
                    REFERENCE
                       'OSPF Version 2, Section 12.1.6 LS sequence number'"
        ::= { wfOspfBackupLsdbEntry 5 }

    wfOspfBackupLsdbAge OBJECT-TYPE
        SYNTAX	INTEGER(0..3600)
        ACCESS	read-only
        STATUS	mandatory
        DESCRIPTION
                "'This field is the age of the link state advertisement
                in seconds.'
                      (OSPF_LSDBMINAGE = 0)
                         REFERENCE
                'OSPF Version 2, Section 12.1.1 LS age'"
        ::= { wfOspfBackupLsdbEntry 6 }

    wfOspfBackupLsdbChecksum OBJECT-TYPE
        SYNTAX	INTEGER
        ACCESS	read-only
        STATUS	mandatory
        DESCRIPTION
                "'This field is the checksum of the complete contents of
                the advertisement, excepting the age field.  The age
                field is excepted so that an advertisement's age can be
                incremented without updating the checksum.  The
                checksum used is the same that is used for ISO
                connectionless datagrams; it is commonly referred to as
                the Fletcher checksum.'
                         REFERENCE
                'OSPF Version 2, Section 12.1.7 LS checksum'"
        ::= { wfOspfBackupLsdbEntry 7 }

    wfOspfBackupLsdbMetric OBJECT-TYPE
        SYNTAX	INTEGER
        ACCESS	read-only
        STATUS	mandatory
        DESCRIPTION
                "'Metric from LSA, if applicable.'"
        ::= { wfOspfBackupLsdbEntry 8 }

    wfOspfBackupLsdbAseForwardAddr OBJECT-TYPE
        SYNTAX	IpAddress
        ACCESS	read-only
        STATUS	mandatory
        DESCRIPTION
                "'If an ASE, the forwarding address from the LSA.'"
        ::= { wfOspfBackupLsdbEntry 9 }

    wfOspfBackupLsdbAseTag OBJECT-TYPE
        SYNTAX	Gauge
        ACCESS	read-only
        STATUS	mandatory
        DESCRIPTION
                "'If an ASE, the External Route Tag from the LSA.'"
        ::= { wfOspfBackupLsdbEntry 10 }

    wfOspfBackupLsdbAseType OBJECT-TYPE
        SYNTAX	INTEGER {
    		    type1(1),
    		    type2(2)
    		}
        ACCESS	read-only
        STATUS	mandatory
        DESCRIPTION
                "'If an ASE, the external metric type from the LSA.'"
        ::= { wfOspfBackupLsdbEntry 11 }

    wfOspfBackupLsdbAdvLen OBJECT-TYPE
        SYNTAX	INTEGER
        ACCESS	read-only
        STATUS	mandatory
        DESCRIPTION
                "'The length of entire Link State Advertisement, including its
                header.'
                         REFERENCE
                'OSPF Version 2, Section 12 Link State Advertisements'"
        ::= { wfOspfBackupLsdbEntry 12 }

    wfOspfBackupLsdbAdv OBJECT-TYPE
        SYNTAX	OCTET STRING
        ACCESS	read-only
        STATUS	mandatory
        DESCRIPTION
                "'This field is the actual OSPF advertisement in hexadecimal
                 format'"
        ::= { wfOspfBackupLsdbEntry 13 }

    wfOspfAreaRangeTable OBJECT-TYPE
        SYNTAX	SEQUENCE OF WfOspfAreaRangeEntry
        ACCESS	not-accessible
        STATUS	mandatory
        DESCRIPTION
                "'A range if IP addresses specified by an IP address/IP
                network mask pair.  For example, class B address range
                of X.X.X.X with a network mask of 255.255.0.0 includes
                all IP addresses from X.X.0.0 to X.X.255.255'
                         REFERENCE
                'OSPF Version 2, Appendix C.2  Area parameters'"
        ::= { wfOspfGroup 4 }

    wfOspfAreaRangeEntry OBJECT-TYPE
        SYNTAX	WfOspfAreaRangeEntry
        ACCESS	not-accessible
        STATUS	mandatory
        DESCRIPTION
                ""
        INDEX	{ wfOspfAreaRangeAreaID,
    		  wfOspfAreaRangeNet }
        ::= { wfOspfAreaRangeTable 1 }

    WfOspfAreaRangeEntry ::= SEQUENCE {
    	    wfOspfAreaRangeDelete
    		INTEGER,
    	    wfOspfAreaRangeDisable
    		INTEGER,
    	    wfOspfAreaRangeState
    		INTEGER,
    	    wfOspfAreaRangeAreaID
    		IpAddress,
    	    wfOspfAreaRangeNet
    		IpAddress,
    	    wfOspfAreaRangeMask
    		IpAddress,
    	    wfOspfAreaRangeStatus
    		INTEGER,
    	    wfOspfAreaRangeMetric
    		INTEGER
        }

    wfOspfAreaRangeDelete OBJECT-TYPE
        SYNTAX	INTEGER {
    		    created(1),
    		    deleted(2)
    		}
        ACCESS	read-write
        STATUS	mandatory
        DESCRIPTION
                "This value determines if an Area Range has been
                configured for the OSPF router."
        DEFVAL	{ created }
        ::= { wfOspfAreaRangeEntry 1 }

    wfOspfAreaRangeDisable OBJECT-TYPE
        SYNTAX	INTEGER {
    		    enabled(1),
    		    disabled(2)
    		}
        ACCESS	read-write
        STATUS	mandatory
        DESCRIPTION
                "'This variable displays the status of
                the entry.  Setting it to 'DISBALED' has the effect of
                rendering it inoperative.  The internal effect (row
                removal) is implementation dependent.'"
        DEFVAL	{ enabled }
        ::= { wfOspfAreaRangeEntry 2 }

    wfOspfAreaRangeState OBJECT-TYPE
        SYNTAX	INTEGER {
    		    up(1),
    		    down(2)
    		}
        ACCESS	read-only
        STATUS	mandatory
        DESCRIPTION
                "The state of the OSPF Area Range."
        DEFVAL	{ down }
        ::= { wfOspfAreaRangeEntry 3 }

    wfOspfAreaRangeAreaID OBJECT-TYPE
        SYNTAX	IpAddress
        ACCESS	read-only
        STATUS	mandatory
        DESCRIPTION
                "'The Area the Address Range is to be found within.'
                         REFERENCE
                'OSPF Version 2, Appendix C.2 Area parameters'"
        ::= { wfOspfAreaRangeEntry 4 }

    wfOspfAreaRangeNet OBJECT-TYPE
        SYNTAX	IpAddress
        ACCESS	read-only
        STATUS	mandatory
        DESCRIPTION
                "'The IP Address of the Net or Subnet indicated by the
                range.'
                         REFERENCE
                'OSPF Version 2, Appendix C.2 Area parameters'"
        ::= { wfOspfAreaRangeEntry 5 }

    wfOspfAreaRangeMask OBJECT-TYPE
        SYNTAX	IpAddress
        ACCESS	read-write
        STATUS	mandatory
        DESCRIPTION
                "'The Subnet Mask that pertains to the Net or Subnet.'
                         REFERENCE
                'OSPF Version 2, Appendix C.2 Area parameters'"
        ::= { wfOspfAreaRangeEntry 6 }

    wfOspfAreaRangeStatus OBJECT-TYPE
        SYNTAX	INTEGER {
    		    advertise(1),
    		    block(2)
    		}
        ACCESS	read-write
        STATUS	mandatory
        DESCRIPTION
                "'Set to either Advertise or DoNotAdvertise.  Routing
                 information is condensed at area boundaries.  External to
                 the area, at most a single route is advertised for each
                 address range.  The route is advertised if and only if the
                 addre range's Status is set to Advertise.  Unadvertised
                 ranges allow the existence of certain networks to be
                 intentionally hidden from other areas.  Status is set to
                 Advertise by default.'
                         REFERENCE
                    'OSPF Version 2, Appendix C.2'"
        DEFVAL	{ advertise }
        ::= { wfOspfAreaRangeEntry 7 }

    wfOspfAreaRangeMetric OBJECT-TYPE
        SYNTAX	INTEGER
        ACCESS	read-write
        STATUS	mandatory
        DESCRIPTION
                "'The metric to advertise into other areas as the distance
                 from the OSPF router to any network in the range.  The
                 default of 0 means to use the value calculated by OSPF.'
                         REFERENCE
                    'OSPF Version 2, Appendix C.2'"
        ::= { wfOspfAreaRangeEntry 8 }

    wfOspfIfTable OBJECT-TYPE
        SYNTAX	SEQUENCE OF WfOspfIfEntry
        ACCESS	not-accessible
        STATUS	mandatory
        DESCRIPTION
                "--  OSPF Interface Table

                --      The OSPF Interface Table augments the ifTable with OSPF
                --      specific information.


                       'The OSPF Interface Table describes the interfaces from
                       the viewpoint of OSPF.'
                    REFERENCE
                       'OSPF Version 2, Appendix C.3  Router interface
                       parameters'"
        ::= { wfOspfGroup 5 }

    wfOspfIfEntry OBJECT-TYPE
        SYNTAX	WfOspfIfEntry
        ACCESS	not-accessible
        STATUS	mandatory
        DESCRIPTION
                "'The OSPF Interface Entry describes one interface from
                the viewpoint of OSPF.'"
        INDEX	{ wfOspfIfIpAddress,
    		  wfOspfAddressLessIf }
        ::= { wfOspfIfTable 1 }

    WfOspfIfEntry ::= SEQUENCE {
            wfOspfIfDelete
                INTEGER,
            wfOspfIfDisable
                INTEGER,
            wfOspfIfState
                INTEGER,
            wfOspfIfIpAddress
                IpAddress,
            wfOspfAddressLessIf
                INTEGER,
            wfOspfIfAreaId
                IpAddress,
            wfOspfIfType
                INTEGER,
            wfOspfIfRtrPriority
                INTEGER,
            wfOspfIfTransitDelay
                INTEGER,
            wfOspfIfRetransInterval
                INTEGER,
            wfOspfIfHelloInterval
                INTEGER,
            wfOspfIfRtrDeadInterval
                INTEGER,
            wfOspfIfPollInterval
                INTEGER,
            wfOspfIfDesignatedRouter
                IpAddress,
            wfOspfIfBackupDesignatedRouter
                IpAddress,
            wfOspfIfMetricCost
                INTEGER,
            wfOspfIfAuthKey
                OCTET STRING,
            wfOspfIfTxHellos
                Counter,
            wfOspfIfTxDBDescripts
                Counter,
            wfOspfIfTxLinkStateReqs
                Counter,
            wfOspfIfTxLinkStateUpds
                Counter,
            wfOspfIfTxLinkStateAcks
                Counter,
            wfOspfIfRxHellos
                Counter,
            wfOspfIfRxDBDescripts
                Counter,
            wfOspfIfRxLinkStateReqs
                Counter,
            wfOspfIfRxLinkStateUpds
                Counter,
            wfOspfIfRxLinkStateAcks
                Counter,
            wfOspfIfDrops
                Counter,
            wfOspfMtuSize
                INTEGER,
            wfOspfIfMulticastForwarding
                INTEGER,
            wfOspfIfOpaqueOn
                INTEGER,
            wfOspfIfBwRate
                INTEGER,
            wfOspfIfBwDepth
                INTEGER,
            wfOspfIfMtuMismatchDetect
                INTEGER
        }

    wfOspfIfDelete OBJECT-TYPE
        SYNTAX	INTEGER {
    		    created(1),
    		    deleted(2)
    		}
        ACCESS	read-write
        STATUS	mandatory
        DESCRIPTION
                "This variable determines in an OSPF Interface has been
                configured on the router."
        DEFVAL	{ created }
        ::= { wfOspfIfEntry 1 }

    wfOspfIfDisable OBJECT-TYPE
        SYNTAX	INTEGER {
    		    enabled(1),
    		    disabled(2)
    		}
        ACCESS	read-write
        STATUS	mandatory
        DESCRIPTION
                "'The OSPF interface's administrative status.  The value
                'enabled' denotes that neighbor relationships may be
                formed on the interface, and the interface will be
                advertised as an internal route to some area.  The
                value 'disabled' denotes that the interface is external
                to OSPF.'"
        DEFVAL	{ enabled }
        ::= { wfOspfIfEntry 2 }

    wfOspfIfState OBJECT-TYPE
        SYNTAX	INTEGER {
    		    down(1),
    		    loopback(2),
    		    waiting(3),
    		    pointtopoint(4),
    		    designatedrouter(5),
    		    backupdesignatedrouter(6),
    		    otherdesignatedrouter(7)
    		}
        ACCESS	read-only
        STATUS	mandatory
        DESCRIPTION
                "'The OSPF Interface State.'
                         down (1),
                         loopback (2),
                         waiting (3),
                         pointToPoint (4),
                         designatedRouter (5),
                         backupDesignatedRouter (6),
                         otherDesignatedRouter (7)"
        DEFVAL	{ down }
        ::= { wfOspfIfEntry 3 }

    wfOspfIfIpAddress OBJECT-TYPE
        SYNTAX	IpAddress
        ACCESS	read-only
        STATUS	mandatory
        DESCRIPTION
                "'The IP address of this OSPF interface.'"
        ::= { wfOspfIfEntry 4 }

    wfOspfAddressLessIf OBJECT-TYPE
        SYNTAX	INTEGER
        ACCESS	read-only
        STATUS	mandatory
        DESCRIPTION
                "'For the purpose of easing the instancing of addressed
                and addressless interfaces; This variable takes the
                value 0 on interfaces with IP Addresses, and the
                corresponding value of ifIndex for interfaces having no
                IP Address.'"
        ::= { wfOspfIfEntry 5 }

    wfOspfIfAreaId OBJECT-TYPE
        SYNTAX	IpAddress
        ACCESS	read-write
        STATUS	mandatory
        DESCRIPTION
                "'A 32-bit integer uniquely identifying the area to
                which the interface connects.  Area ID 0.0.0.0 is used
                for the OSPF backbone.'
                default { '00000000'H }    -- 0.0.0.0"
        ::= { wfOspfIfEntry 6 }

    wfOspfIfType OBJECT-TYPE
        SYNTAX	INTEGER {
    		    broadcast(1),
    		    nbma(2),
    		    pointtopoint(3),
    		    pmp(4),
    		    ietf(5),
                    passive(6)
    		}
        ACCESS	read-write
        STATUS	mandatory
        DESCRIPTION
                "'The OSPF interface type.

                By way of a default, this field may be intuited from
                the corresponding value of ifType.  Broadcast LANs,
                such as Ethernet and IEEE 802.5, take the value
                'broadcast'.  Medias which allow multiple devices
	        to be connected but don't support a broadcast
	        mechanism, such as X.25, take the value 'nbma'.
	        Point to Point protocols take the value of
		'pointtopoint'.  Non-fully meshed technologies
		would take the value of either 'ietf' or 'pmp'.
                Passive interface take the value of 'passive'.
		An example topology is a Frame Relay cloud that
		does not have a PVC between every device on the cloud.

                         broadcast (1),
                         nbma (2),
                         pointToPoint (3)
                         point to multipoint - proprietary (4)
			 point to multipoint - standard (5)
                         passive (6)"
        DEFVAL	{ broadcast }
        ::= { wfOspfIfEntry 7 }

    wfOspfIfRtrPriority OBJECT-TYPE
        SYNTAX	INTEGER(0..255)
        ACCESS	read-write
        STATUS	mandatory
        DESCRIPTION
                "'The priority of this interface.  Used in multi-access
                networks, this field is used in the designated router
                election algorithm.  The value 0 signifies that the
                router is not eligible to become the designated router
                on this particular network.  In the event of a tie in
                this value, routers will use their router id as a tie
                breaker.'"
        DEFVAL	{ 1 }
        ::= { wfOspfIfEntry 8 }

    wfOspfIfTransitDelay OBJECT-TYPE
        SYNTAX	INTEGER(1..3600)
        ACCESS	read-write
        STATUS	mandatory
        DESCRIPTION
                "'The estimated number of seconds it takes to transmit a
                link- state update packet over this interface.'"
        DEFVAL	{ 1 }
        ::= { wfOspfIfEntry 9 }

    wfOspfIfRetransInterval OBJECT-TYPE
        SYNTAX	INTEGER(1..3600)
        ACCESS	read-write
        STATUS	mandatory
        DESCRIPTION
                "'The number of seconds between link-state advertisement
                retransmissions, for adjacencies belonging to this
                interface.  This value is also used when retransmitting
                database description and link-state request packets.'"
        DEFVAL	{ 5 }
        ::= { wfOspfIfEntry 10 }

    wfOspfIfHelloInterval OBJECT-TYPE
        SYNTAX	INTEGER(1..65535)
        ACCESS	read-write
        STATUS	mandatory
        DESCRIPTION
                "'The length of time, in seconds, between the Hello
                packets that the router sends on the interface.  This
                value must be the same for all routers attached to a
                common network.'"
        DEFVAL	{ 10 }
        ::= { wfOspfIfEntry 11 }

    wfOspfIfRtrDeadInterval OBJECT-TYPE
        SYNTAX	INTEGER(1..2147483647)
        ACCESS	read-write
        STATUS	mandatory
        DESCRIPTION
                "'The number of seconds that a router's Hello packets
                have not been seen before it's neighbors declare the
                router down.  This should be some multiple of the Hello
                interval.  This value must be the same for all routers
                attached to a common network.'"
        DEFVAL	{ 40 }
        ::= { wfOspfIfEntry 12 }

    wfOspfIfPollInterval OBJECT-TYPE
        SYNTAX	INTEGER(1..2147483647)
        ACCESS	read-write
        STATUS	mandatory
        DESCRIPTION
                "'The larger time interval, in seconds, between the
                Hello packets sent to an inactive non-broadcast multi-
                access neighbor.'"
        DEFVAL	{ 120 }
        ::= { wfOspfIfEntry 13 }

    wfOspfIfDesignatedRouter OBJECT-TYPE
        SYNTAX	IpAddress
        ACCESS	read-only
        STATUS	mandatory
        DESCRIPTION
                "'The IP Address of the Designated Router.'
                default { '00000000'H }    -- 0.0.0.0"
        ::= { wfOspfIfEntry 14 }

    wfOspfIfBackupDesignatedRouter OBJECT-TYPE
        SYNTAX	IpAddress
        ACCESS	read-only
        STATUS	mandatory
        DESCRIPTION
                "'The IP Address of the Backup Designated Router.'
                default { '00000000'H }    -- 0.0.0.0"
        ::= { wfOspfIfEntry 15 }

    wfOspfIfMetricCost OBJECT-TYPE
        SYNTAX	INTEGER(1..65535)
        ACCESS	read-write
        STATUS	mandatory
        DESCRIPTION
                "'The cost of using this type of service on this
                interface.  The default value of the TOS 0 Metric is
                10^8 / ifSpeed.

                The value FFFF is distinguished to mean 'no route via
                this TOS'.'"
        DEFVAL	{ 1 }
        ::= { wfOspfIfEntry 16 }

    wfOspfIfAuthKey OBJECT-TYPE
        SYNTAX	OCTET STRING
        ACCESS	read-write
        STATUS	mandatory
        DESCRIPTION
                "'The Authentication Key.  If the Area's Authorization
                Type is simplePassword, and the key length is shorter
                than 8 octets, the agent will left adjust and zero fill
                to 8 octets.

                When read, ospfIfAuthKey always returns an Octet String
                of length zero.'

                default  { '0000000000000000'H }    -- 0.0.0.0.0.0.0.0

                         REFERENCE
                'OSPF Version 2, Section 9 The Interface Data
                Structure'"
        ::= { wfOspfIfEntry 17 }

    wfOspfIfTxHellos OBJECT-TYPE
        SYNTAX	Counter
        ACCESS	read-only
        STATUS	mandatory
        DESCRIPTION
                "Number of OSPF Hello packets transmitted."
        ::= { wfOspfIfEntry 18 }

    wfOspfIfTxDBDescripts OBJECT-TYPE
        SYNTAX	Counter
        ACCESS	read-only
        STATUS	mandatory
        DESCRIPTION
                "Number of OSPF DataBase Description packets transmitted."
        ::= { wfOspfIfEntry 19 }

    wfOspfIfTxLinkStateReqs OBJECT-TYPE
        SYNTAX	Counter
        ACCESS	read-only
        STATUS	mandatory
        DESCRIPTION
                "Number of OSPF Link State Request packets transmitted."
        ::= { wfOspfIfEntry 20 }

    wfOspfIfTxLinkStateUpds OBJECT-TYPE
        SYNTAX	Counter
        ACCESS	read-only
        STATUS	mandatory
        DESCRIPTION
                "Number of OSPF Link State Update packets transmitted."
        ::= { wfOspfIfEntry 21 }

    wfOspfIfTxLinkStateAcks OBJECT-TYPE
        SYNTAX	Counter
        ACCESS	read-only
        STATUS	mandatory
        DESCRIPTION
                "Number of OSPF Link States Acknowledgements transmitted."
        ::= { wfOspfIfEntry 22 }

    wfOspfIfRxHellos OBJECT-TYPE
        SYNTAX	Counter
        ACCESS	read-only
        STATUS	mandatory
        DESCRIPTION
                "Number of OSPF Hello packets received."
        ::= { wfOspfIfEntry 23 }

    wfOspfIfRxDBDescripts OBJECT-TYPE
        SYNTAX	Counter
        ACCESS	read-only
        STATUS	mandatory
        DESCRIPTION
                "Number of OSPF DataBase Description packets received."
        ::= { wfOspfIfEntry 24 }

    wfOspfIfRxLinkStateReqs OBJECT-TYPE
        SYNTAX	Counter
        ACCESS	read-only
        STATUS	mandatory
        DESCRIPTION
                "Number of OSPF Link State Requests received."
        ::= { wfOspfIfEntry 25 }

    wfOspfIfRxLinkStateUpds OBJECT-TYPE
        SYNTAX	Counter
        ACCESS	read-only
        STATUS	mandatory
        DESCRIPTION
                "Number of OSPF Link State Updates received."
        ::= { wfOspfIfEntry 26 }

    wfOspfIfRxLinkStateAcks OBJECT-TYPE
        SYNTAX	Counter
        ACCESS	read-only
        STATUS	mandatory
        DESCRIPTION
                "Number of OSPF Link State Acknowledgements received."
        ::= { wfOspfIfEntry 27 }

    wfOspfIfDrops OBJECT-TYPE
        SYNTAX	Counter
        ACCESS	read-only
        STATUS	mandatory
        DESCRIPTION
                "Number of OSPF packets dropped because of invalid information
                in the packet."
        ::= { wfOspfIfEntry 28 }

    wfOspfMtuSize OBJECT-TYPE
        SYNTAX	INTEGER(1..10000)
        ACCESS	read-write
        STATUS	mandatory
        DESCRIPTION
                "Configure MTU size per OSPF interface
                     This parameter has the following values/meanings:

                  1 - Use the MTU specified by IP
                  2 - Use the MTU of ethernet, regardless of what IP
                      says
                  > 2 - Use this value as the actual MTU.
                        If the value is smaller than what OSPF needs as
                        a minimum then the mtu specified by IP is used.
                        For example, 3 would never be used as an MTU."
        DEFVAL	{ 1 }
        ::= { wfOspfIfEntry 29 }

    wfOspfIfMulticastForwarding OBJECT-TYPE
        SYNTAX  INTEGER {
                        blocked( 1 ),           -- no multicast forwarding
                        multicast( 2 ),         -- using multicast address
                        unicast( 3 )            -- to each OSPF neighbor
                }
        ACCESS  read-write
        STATUS  mandatory
        DESCRIPTION
           "The way multicasts should  forwarded  on  this
           interface;  not  forwarded,  forwarded  as data
           link multicasts, or forwarded as data link uni-
           casts.   Data link multicasting is not meaning-
           ful on point to point and NBMA interfaces,  and
           setting ospfMulticastForwarding to 0 effective-
           ly disables all multicast forwarding."

        DEFVAL { multicast }
        ::= { wfOspfIfEntry 30 }

    wfOspfIfOpaqueOn OBJECT-TYPE
        SYNTAX  INTEGER {
                        on( 1 ),
                        off( 2 )
                }
        ACCESS  read-write
        STATUS  mandatory
        DESCRIPTION
           "This controls whether or not OPAQUE LSAs are to be
            flooded out this interface or not."

        DEFVAL { on }
        ::= { wfOspfIfEntry 31 }

    wfOspfIfBwRate OBJECT-TYPE
        SYNTAX  INTEGER
        ACCESS  read-only
        STATUS  mandatory
        DESCRIPTION
                "Available BW (token bucket rate) on the intf"
        ::= { wfOspfIfEntry 32 }

    wfOspfIfBwDepth OBJECT-TYPE
        SYNTAX  INTEGER
        ACCESS  read-only
        STATUS  mandatory
        DESCRIPTION
                "Available BW (token bucket depth) on the intf"
        ::= { wfOspfIfEntry 33 }

    wfOspfIfMtuMismatchDetect OBJECT-TYPE
        SYNTAX  INTEGER {
    		    enabled(1),
    		    disabled(2)
    		}
        ACCESS  read-write
        STATUS  mandatory
        DESCRIPTION
                "Controls the interpretation of the MTU field in the
                 database description packet header.  Per RFC 2178 the
                 MTU indicates the largest size IP packet that an OSPF
                 interface can receive.  If the MTU is greater than that
                 which the interface can receive the packet is ignored
                 and thus, an adjacency is not formed.  In RFC 1583 this
                 field does not exist.  The value 'enabled' denotes RFC
                 2178 processing of the MTU field.  The value 'disabled'
                 denotes RFC 1583 processing."
        DEFVAL	{ enabled }
        ::= { wfOspfIfEntry 34 }


    wfOspfVirtIfTable OBJECT-TYPE
        SYNTAX	SEQUENCE OF WfOspfVirtIfEntry
        ACCESS	not-accessible
        STATUS	mandatory
        DESCRIPTION
                "--  OSPF Virtual Interface Table

                --      The Virtual Interface Table describes the virtual
                --      links that the OSPF Process is configured to
                --      carry on.


                       'Information about this router's virtual interfaces.'
                    REFERENCE
                       'OSPF Version 2, Appendix C.4  Virtual link parameters'"
        ::= { wfOspfGroup 6 }

    wfOspfVirtIfEntry OBJECT-TYPE
        SYNTAX	WfOspfVirtIfEntry
        ACCESS	not-accessible
        STATUS	mandatory
        DESCRIPTION
                "'Information about a single Virtual Interface.'"
        INDEX	{ wfOspfVirtIfAreaID,
    		  wfOspfVirtIfNeighbor }
        ::= { wfOspfVirtIfTable 1 }

    WfOspfVirtIfEntry ::= SEQUENCE {
    	    wfOspfVirtIfDelete
    		INTEGER,
    	    wfOspfVirtIfDisable
    		INTEGER,
    	    wfOspfVirtIfState
    		INTEGER,
    	    wfOspfVirtIfAreaID
    		IpAddress,
    	    wfOspfVirtIfNeighbor
    		IpAddress,
    	    wfOspfVirtIfTransitDelay
    		INTEGER,
    	    wfOspfVirtIfRetransInterval
    		INTEGER,
    	    wfOspfVirtIfHelloInterval
    		INTEGER,
    	    wfOspfVirtIfRtrDeadInterval
    		INTEGER,
    	    wfOspfVirtIfAuthKey
    		OCTET STRING,
    	    wfOspfVirtIfTxHellos
    		Counter,
    	    wfOspfVirtIfTxDBDescripts
    		Counter,
    	    wfOspfVirtIfTxLinkStateReqs
    		Counter,
    	    wfOspfVirtIfTxLinkStateUpds
    		Counter,
    	    wfOspfVirtIfTxLinkStateAcks
    		Counter,
    	    wfOspfVirtIfRxHellos
    		Counter,
    	    wfOspfVirtIfRxDBDescripts
    		Counter,
    	    wfOspfVirtIfRxLinkStateReqs
    		Counter,
    	    wfOspfVirtIfRxLinkStateUpds
    		Counter,
    	    wfOspfVirtIfRxLinkStateAcks
    		Counter,
    	    wfOspfVirtIfDrops
    		Counter
        }

    wfOspfVirtIfDelete OBJECT-TYPE
        SYNTAX	INTEGER {
    		    created(1),
    		    deleted(2)
    		}
        ACCESS	read-write
        STATUS	mandatory
        DESCRIPTION
                ""
        DEFVAL	{ created }
        ::= { wfOspfVirtIfEntry 1 }

    wfOspfVirtIfDisable OBJECT-TYPE
        SYNTAX	INTEGER {
    		    enabled(1),
    		    disabled(2)
    		}
        ACCESS	read-write
        STATUS	mandatory
        DESCRIPTION
                "'This variable displays the validity or invalidity of
                the entry.  Setting it to 'invalid' has the effect of
                rendering it inoperative.  The internal effect (row
                removal) is implementation dependent.'"
        DEFVAL	{ enabled }
        ::= { wfOspfVirtIfEntry 2 }

    wfOspfVirtIfState OBJECT-TYPE
        SYNTAX	INTEGER {
    		    down(1),
    		    pointtopoint(4)
    		}
        ACCESS	read-only
        STATUS	mandatory
        DESCRIPTION
                "'OSPF virtual interface states.'
                         down (1),               -- these use the same encoding
                         pointToPoint (4)        -- as the ospfIfTable"
        DEFVAL	{ down }
        ::= { wfOspfVirtIfEntry 3 }

    wfOspfVirtIfAreaID OBJECT-TYPE
        SYNTAX	IpAddress
        ACCESS	read-only
        STATUS	mandatory
        DESCRIPTION
                "'The Transit Area that the Virtual Link traverses.  By
                definition, this is not 0.0.0.0'"
        ::= { wfOspfVirtIfEntry 4 }

    wfOspfVirtIfNeighbor OBJECT-TYPE
        SYNTAX	IpAddress
        ACCESS	read-only
        STATUS	mandatory
        DESCRIPTION
                "'The Router ID of the Virtual Neighbor.'"
        ::= { wfOspfVirtIfEntry 5 }

    wfOspfVirtIfTransitDelay OBJECT-TYPE
        SYNTAX	INTEGER(1..3600)
        ACCESS	read-write
        STATUS	mandatory
        DESCRIPTION
                "'The estimated number of seconds it takes to transmit a
                link- state update packet over this interface.'"
        DEFVAL	{ 1 }
        ::= { wfOspfVirtIfEntry 6 }

    wfOspfVirtIfRetransInterval OBJECT-TYPE
        SYNTAX	INTEGER(1..3600)
        ACCESS	read-write
        STATUS	mandatory
        DESCRIPTION
                "'The number of seconds between link-state advertisement
                retransmissions, for adjacencies belonging to this
                interface.  This value is also used when retransmitting
                database description and link-state request packets.
                This value should be well over the expected round-trip
                time.'"
        DEFVAL	{ 5 }
        ::= { wfOspfVirtIfEntry 7 }

    wfOspfVirtIfHelloInterval OBJECT-TYPE
        SYNTAX	INTEGER(1..65535)
        ACCESS	read-write
        STATUS	mandatory
        DESCRIPTION
                "'The length of time, in seconds, between the Hello
                packets that the router sends on the interface.  This
                value must be the same for the virtual neighbor.'"
        DEFVAL	{ 15 }
        ::= { wfOspfVirtIfEntry 8 }

    wfOspfVirtIfRtrDeadInterval OBJECT-TYPE
        SYNTAX	INTEGER(1..2147483647)
        ACCESS	read-write
        STATUS	mandatory
        DESCRIPTION
                "'The number of seconds that a router's Hello packets
                have not been seen before it's neighbors declare the
                router down.  This should be some multiple of the Hello
                interval.  This value must be the same for the virtual
                neighbor.'"
        DEFVAL	{ 60 }
        ::= { wfOspfVirtIfEntry 9 }

    wfOspfVirtIfAuthKey OBJECT-TYPE
        SYNTAX	OCTET STRING
        ACCESS	read-write
        STATUS	mandatory
        DESCRIPTION
                "'If Authentication Type is simplePassword, the device
                will left adjust and zero fill to 8 octets.

                When read, ospfVifAuthKey always returns a string of
                length zero.'
                         REFERENCE
                'OSPF Version 2, Section 9 The Interface Data
                Structure'"
        ::= { wfOspfVirtIfEntry 10 }

    wfOspfVirtIfTxHellos OBJECT-TYPE
        SYNTAX	Counter
        ACCESS	read-only
        STATUS	mandatory
        DESCRIPTION
                "Number of OSPF Hello packets transmitted on
                Virtual Interfaces."
        ::= { wfOspfVirtIfEntry 11 }

    wfOspfVirtIfTxDBDescripts OBJECT-TYPE
        SYNTAX	Counter
        ACCESS	read-only
        STATUS	mandatory
        DESCRIPTION
                "Number of OSPF DataBase Description packets transmitted
                on Virtual Interfaces."
        ::= { wfOspfVirtIfEntry 12 }

    wfOspfVirtIfTxLinkStateReqs OBJECT-TYPE
        SYNTAX	Counter
        ACCESS	read-only
        STATUS	mandatory
        DESCRIPTION
                "Number of OSPF Link State Request packets transmitted
                on Virtual Interfaces."
        ::= { wfOspfVirtIfEntry 13 }

    wfOspfVirtIfTxLinkStateUpds OBJECT-TYPE
        SYNTAX	Counter
        ACCESS	read-only
        STATUS	mandatory
        DESCRIPTION
                "Number of OSPF Link State Update packets transmitted
                on Virtual Interfaces."
        ::= { wfOspfVirtIfEntry 14 }

    wfOspfVirtIfTxLinkStateAcks OBJECT-TYPE
        SYNTAX	Counter
        ACCESS	read-only
        STATUS	mandatory
        DESCRIPTION
                "Number of OSPF Link State Acknowledgement packets
                transmitted on Virtual Interfaces."
        ::= { wfOspfVirtIfEntry 15 }

    wfOspfVirtIfRxHellos OBJECT-TYPE
        SYNTAX	Counter
        ACCESS	read-only
        STATUS	mandatory
        DESCRIPTION
                "Number of OSPF Hello packets received on
                Virtual Interfaces."
        ::= { wfOspfVirtIfEntry 16 }

    wfOspfVirtIfRxDBDescripts OBJECT-TYPE
        SYNTAX	Counter
        ACCESS	read-only
        STATUS	mandatory
        DESCRIPTION
                "Number of OSPF DataBase Description packets received
                on Virtual Interfaces."
        ::= { wfOspfVirtIfEntry 17 }

    wfOspfVirtIfRxLinkStateReqs OBJECT-TYPE
        SYNTAX	Counter
        ACCESS	read-only
        STATUS	mandatory
        DESCRIPTION
                "Number of OSPF Link State Request packets recieved
                on Virtual Interfaces."
        ::= { wfOspfVirtIfEntry 18 }

    wfOspfVirtIfRxLinkStateUpds OBJECT-TYPE
        SYNTAX	Counter
        ACCESS	read-only
        STATUS	mandatory
        DESCRIPTION
                "Number of OSPF Link State Update packets received
                on Virtual Interfaces."
        ::= { wfOspfVirtIfEntry 19 }

    wfOspfVirtIfRxLinkStateAcks OBJECT-TYPE
        SYNTAX	Counter
        ACCESS	read-only
        STATUS	mandatory
        DESCRIPTION
                "Number of OSPF Link State Acknowledgement packets
                received on Virtual Interfaces."
        ::= { wfOspfVirtIfEntry 20 }

    wfOspfVirtIfDrops OBJECT-TYPE
        SYNTAX	Counter
        ACCESS	read-only
        STATUS	mandatory
        DESCRIPTION
                "Number of OSPF packets dropped on
                Virtual Interfaces."
        ::= { wfOspfVirtIfEntry 21 }

    wfOspfNbrTable OBJECT-TYPE
        SYNTAX	SEQUENCE OF WfOspfNbrEntry
        ACCESS	not-accessible
        STATUS	mandatory
        DESCRIPTION
                "--  OSPF Neighbor Table

                --      The OSPF Neighbor Table describes all neighbors in
                --      the locality of the subject router.


                       'A table of non-virtual neighbor information.'
                    REFERENCE
                       'OSPF Version 2, Section 10 The Neighbor Data
                       Structure'"
        ::= { wfOspfGroup 7 }

    wfOspfNbrEntry OBJECT-TYPE
        SYNTAX	WfOspfNbrEntry
        ACCESS	not-accessible
        STATUS	mandatory
        DESCRIPTION
                "'The information regarding a single neighbor.'
                         REFERENCE
                'OSPF Version 2, Section 10 The Neighbor Data
                Structure'"
        INDEX	{ wfOspfNbrIpAddr,
    		  wfOspfNbrAddressLessIndex }
        ::= { wfOspfNbrTable 1 }

    WfOspfNbrEntry ::= SEQUENCE {
    	    wfOspfNbrDelete
    		INTEGER,
    	    wfOspfNbrDisable
    		INTEGER,
    	    wfOspfNbrState
    		INTEGER,
    	    wfOspfNbrIpAddr
    		IpAddress,
    	    wfOspfNbrIfAddr
    		IpAddress,
    	    wfOspfNbrAddressLessIndex
    		INTEGER,
    	    wfOspfNbrRtrId
    		IpAddress,
    	    wfOspfNbrOptions
    		INTEGER,
    	    wfOspfNbrPriority
    		INTEGER,
    	    wfOspfNbrEvents
    		Counter,
    	    wfOspfNbrLSRetransQLen
    		Gauge,
    	    wfOspfCurNbrPriority
    		INTEGER
        }

    wfOspfNbrDelete OBJECT-TYPE
        SYNTAX	INTEGER {
    		    created(1),
    		    deleted(2)
    		}
        ACCESS	read-write
        STATUS	mandatory
        DESCRIPTION
                "This variable indicates the existence of a static
                OSPF neighbor."
        DEFVAL	{ created }
        ::= { wfOspfNbrEntry 1 }

    wfOspfNbrDisable OBJECT-TYPE
        SYNTAX	INTEGER {
    		    enabled(1),
    		    disabled(2)
    		}
        ACCESS	read-write
        STATUS	mandatory
        DESCRIPTION
                "'This variable displays the status of
                the entry.  Setting it to 'DISABLED' has the effect of
                rendering it inoperative.  The internal effect (row
                removal) is implementation dependent.'"
        DEFVAL	{ enabled }
        ::= { wfOspfNbrEntry 2 }

    wfOspfNbrState OBJECT-TYPE
        SYNTAX	INTEGER {
    		    down(1),
    		    attempt(2),
    		    init(3),
    		    twoway(4),
    		    exchangstart(5),
    		    exchange(6),
    		    loading(7),
    		    full(8)
    		}
        ACCESS	read-only
        STATUS	mandatory
        DESCRIPTION
                "'The State of the relationship with this Neighbor.'
                         REFERENCE
                'OSPF Version 2, Section 10.1 Neighbor States'
                         down (1),
                         attempt (2),
                         init (3),
                         twoWay (4),
                         exchangeStart (5),
                         exchange (6),
                         loading (7),
                         full (8)"
        DEFVAL	{ down }
        ::= { wfOspfNbrEntry 3 }

    wfOspfNbrIpAddr OBJECT-TYPE
        SYNTAX	IpAddress
        ACCESS	read-only
        STATUS	mandatory
        DESCRIPTION
                "'The IP address of this neighbor.'"
        ::= { wfOspfNbrEntry 4 }

    wfOspfNbrIfAddr OBJECT-TYPE
        SYNTAX	IpAddress
        ACCESS	read-write
        STATUS	mandatory
        DESCRIPTION
                "'The Interface IP address for this neighbor.'"
        ::= { wfOspfNbrEntry 5 }

    wfOspfNbrAddressLessIndex OBJECT-TYPE
        SYNTAX	INTEGER
        ACCESS	read-only
        STATUS	mandatory
        DESCRIPTION
                "' On an interface having an IP Address, zero.  On
                addressless interfaces, the corresponding value of
                ifIndex in the Internet Standard MIB.  On row creation,
                this can be derived from the instance.'"
        ::= { wfOspfNbrEntry 6 }

    wfOspfNbrRtrId OBJECT-TYPE
        SYNTAX	IpAddress
        ACCESS	read-only
        STATUS	mandatory
        DESCRIPTION
                "'A 32-bit integer (represented as a type IpAddress)
                uniquely identifying the neighboring router in the
                Autonomous System.'
                default { '00000000'H }    -- 0.0.0.0"
        ::= { wfOspfNbrEntry 7 }

    wfOspfNbrOptions OBJECT-TYPE
        SYNTAX	INTEGER
        ACCESS	read-only
        STATUS	mandatory
        DESCRIPTION
                "'A Bit Mask corresponding to the neighbor's options
                field.

                Bit 0, if set, indicates that the area accepts and
                operates on external information; if zero, it is a stub
                area.

                Bit 1, if set, indicates that the system will operate
                on Type of Service metrics other than TOS 0.  If zero,
                the neighbor will ignore all metrics except the TOS 0
                metric.'
                         REFERENCE
                'OSPF Version 2, Section 12.1.2 Options'"
        ::= { wfOspfNbrEntry 8 }

    wfOspfNbrPriority OBJECT-TYPE
        SYNTAX	INTEGER(0..255)
        ACCESS	read-write
        STATUS	mandatory
        DESCRIPTION
                "'The priority of this neighbor in the designated router
                election algorithm.  The value 0 signifies that the
                neighbor is not eligible to become the designated
                router on this particular network.'
                This is the user configurable/changeable neighbor's priority"
        DEFVAL	{ 1 }
        ::= { wfOspfNbrEntry 9 }

    wfOspfNbrEvents OBJECT-TYPE
        SYNTAX	Counter
        ACCESS	read-only
        STATUS	mandatory
        DESCRIPTION
                "'The number of times this neighbor relationship has
                changed state, or an error has occurred.'"
        ::= { wfOspfNbrEntry 10 }

    wfOspfNbrLSRetransQLen OBJECT-TYPE
        SYNTAX	Gauge
        ACCESS	read-only
        STATUS	mandatory
        DESCRIPTION
                "'The current length of the retransmission queue.'"
        ::= { wfOspfNbrEntry 11 }

    wfOspfCurNbrPriority OBJECT-TYPE
        SYNTAX	INTEGER
        ACCESS	read-only
        STATUS	mandatory
        DESCRIPTION
                "This value represents the priority of the neighbor as
                indicated in received Hello packets.  In most cases, this
                will be the same as wfOspfCfgNbrPriority.  If they are
                different, it indicates a misconfiguration"
        ::= { wfOspfNbrEntry 12 }

    wfOspfVirtNbrTable OBJECT-TYPE
        SYNTAX	SEQUENCE OF WfOspfVirtNbrEntry
        ACCESS	not-accessible
        STATUS	mandatory
        DESCRIPTION
                "--  WFOSPF Virtual Neighbor Table

                --      This table describes all virtual neighbors.
                --      Since Virtual Links are configured in the
                --      virtual interface table, this table is read-only.

                       'A table of virtual neighbor information.'
                    REFERENCE
                       'OSPF Version 2, '"
        ::= { wfOspfGroup 8 }

    wfOspfVirtNbrEntry OBJECT-TYPE
        SYNTAX	WfOspfVirtNbrEntry
        ACCESS	not-accessible
        STATUS	mandatory
        DESCRIPTION
                "'Virtual neighbor information.'
                         REFERENCE
                'OSPF Version 2, '"
        INDEX	{ wfOspfVirtNbrArea,
    		  wfOspfVirtNbrRtrId }
        ::= { wfOspfVirtNbrTable 1 }

    WfOspfVirtNbrEntry ::= SEQUENCE {
    	    wfOspfVirtNbrArea
    		IpAddress,
    	    wfOspfVirtNbrRtrId
    		IpAddress,
    	    wfOspfVirtNbrIpAddr
    		IpAddress,
    	    wfOspfVirtNbrOptions
    		INTEGER,
    	    wfOspfVirtNbrState
    		INTEGER,
    	    wfOspfVirtNbrEvents
    		Counter,
    	    wfOspfVirtNbrLSRetransQLen
    		Gauge
        }

    wfOspfVirtNbrArea OBJECT-TYPE
        SYNTAX	IpAddress
        ACCESS	read-only
        STATUS	mandatory
        DESCRIPTION
                "'The Transit Area Identifier.'"
        ::= { wfOspfVirtNbrEntry 1 }

    wfOspfVirtNbrRtrId OBJECT-TYPE
        SYNTAX	IpAddress
        ACCESS	read-only
        STATUS	mandatory
        DESCRIPTION
                "'A 32-bit integer uniquely identifying the neighboring
                router in the Autonomous System.'"
        ::= { wfOspfVirtNbrEntry 2 }

    wfOspfVirtNbrIpAddr OBJECT-TYPE
        SYNTAX	IpAddress
        ACCESS	read-only
        STATUS	mandatory
        DESCRIPTION
                "'The IP address this Virtual Neighbor is using.'"
        ::= { wfOspfVirtNbrEntry 3 }

    wfOspfVirtNbrOptions OBJECT-TYPE
        SYNTAX	INTEGER
        ACCESS	read-only
        STATUS	mandatory
        DESCRIPTION
                "'A bit map corresponding to the neighbor's options
                field.  Thus, Bit 1, if set, indicates that the
                neighbor supports Type of Service Routing; if zero, no
                metrics other than TOS 0 are in use by the neighbor.'"
        ::= { wfOspfVirtNbrEntry 4 }

    wfOspfVirtNbrState OBJECT-TYPE
        SYNTAX	INTEGER {
    		    down(1),
    		    attempt(2),
    		    init(3),
    		    twoway(4),
    		    exchangstart(5),
    		    exchange(6),
    		    loading(7),
    		    full(8)
    		}
        ACCESS	read-only
        STATUS	mandatory
        DESCRIPTION
                "'The state of the Virtual Neighbor Relationship.'
                         down (1),
                         attempt (2),
                         init (3),
                         twoWay (4),
                         exchangeStart (5),
                         exchange (6),
                         loading (7),
                         full (8)"
        DEFVAL	{ down }
        ::= { wfOspfVirtNbrEntry 5 }

    wfOspfVirtNbrEvents OBJECT-TYPE
        SYNTAX	Counter
        ACCESS	read-only
        STATUS	mandatory
        DESCRIPTION
                "'The number of times this virtual link has changed its
                state, or an error has occurred.'"
        ::= { wfOspfVirtNbrEntry 6 }

    wfOspfVirtNbrLSRetransQLen OBJECT-TYPE
        SYNTAX	Gauge
        ACCESS	read-only
        STATUS	mandatory
        DESCRIPTION
                "'The current length of the retransmission queue.'"
        ::= { wfOspfVirtNbrEntry 7 }

    wfOspfDynNbrTable OBJECT-TYPE
        SYNTAX	SEQUENCE OF WfOspfDynNbrEntry
        ACCESS	not-accessible
        STATUS	mandatory
        DESCRIPTION
                "--  OSPF Dynamic Neighbor Table

                --      The OSPF Dynamic Neighbor Table describes all neighbors in
                --      the locality of the subject router learned during operation.


                       'A table of non-virtual neighbor information.'
                    REFERENCE
                       'OSPF Version 2, Section 10 The Neighbor Data
                       Structure'"
        ::= { wfOspfGroup 9 }

    wfOspfDynNbrEntry OBJECT-TYPE
        SYNTAX	WfOspfDynNbrEntry
        ACCESS	not-accessible
        STATUS	mandatory
        DESCRIPTION
                "'The information regarding a single neighbor.'
                         REFERENCE
                'OSPF Version 2, Section 10 The Neighbor Data
                Structure'"
        INDEX	{ wfOspfDynNbrIpAddr,
    		  wfOspfDynNbrAddressLessIndex }
        ::= { wfOspfDynNbrTable 1 }

    WfOspfDynNbrEntry ::= SEQUENCE {
    	    wfOspfDynNbrState
    		INTEGER,
    	    wfOspfDynNbrIpAddr
    		IpAddress,
    	    wfOspfDynNbrIfAddr
    		IpAddress,
    	    wfOspfDynNbrAddressLessIndex
    		INTEGER,
    	    wfOspfDynNbrRtrId
    		IpAddress,
    	    wfOspfDynNbrOptions
    		INTEGER,
    	    wfOspfDynNbrPriority
    		INTEGER,
    	    wfOspfDynNbrEvents
    		Counter,
    	    wfOspfDynNbrLSRetransQLen
    		Gauge
        }

    wfOspfDynNbrState OBJECT-TYPE
        SYNTAX	INTEGER {
    		    down(1),
    		    attempt(2),
    		    init(3),
    		    twoway(4),
    		    exchangstart(5),
    		    exchange(6),
    		    loading(7),
    		    full(8)
    		}
        ACCESS	read-only
        STATUS	mandatory
        DESCRIPTION
                "'The State of the relationship with this Neighbor.'
                         REFERENCE
                'OSPF Version 2, Section 10.1 Neighbor States'
                         down (1),
                         attempt (2),
                         init (3),
                         twoWay (4),
                         exchangeStart (5),
                         exchange (6),
                         loading (7),
                         full (8)"
        DEFVAL	{ down }
        ::= { wfOspfDynNbrEntry 1 }

    wfOspfDynNbrIpAddr OBJECT-TYPE
        SYNTAX	IpAddress
        ACCESS	read-only
        STATUS	mandatory
        DESCRIPTION
                "'The IP address of this neighbor.'"
        ::= { wfOspfDynNbrEntry 2 }

    wfOspfDynNbrIfAddr OBJECT-TYPE
        SYNTAX	IpAddress
        ACCESS	read-only
        STATUS	mandatory
        DESCRIPTION
                "'The Interface IP address for this neighbor.'"
        ::= { wfOspfDynNbrEntry 3 }

    wfOspfDynNbrAddressLessIndex OBJECT-TYPE
        SYNTAX	INTEGER
        ACCESS	read-only
        STATUS	mandatory
        DESCRIPTION
                "' On an interface having an IP Address, zero.  On
                addressless interfaces, the corresponding value of
                ifIndex in the Internet Standard MIB.  On row creation,
                this can be derived from the instance.'"
        ::= { wfOspfDynNbrEntry 4 }

    wfOspfDynNbrRtrId OBJECT-TYPE
        SYNTAX	IpAddress
        ACCESS	read-only
        STATUS	mandatory
        DESCRIPTION
                "'A 32-bit integer (represented as a type IpAddress)
                uniquely identifying the neighboring router in the
                Autonomous System.'
                default { '00000000'H }    -- 0.0.0.0"
        ::= { wfOspfDynNbrEntry 5 }

    wfOspfDynNbrOptions OBJECT-TYPE
        SYNTAX	INTEGER
        ACCESS	read-only
        STATUS	mandatory
        DESCRIPTION
                "'A Bit Mask corresponding to the neighbor's options
                field.

                Bit 0, if set, indicates that the area accepts and
                operates on external information; if zero, it is a stub
                area.

                Bit 1, if set, indicates that the system will operate
                on Type of Service metrics other than TOS 0.  If zero,
                the neighbor will ignore all metrics except the TOS 0
                metric.'
                         REFERENCE
                'OSPF Version 2, Section 12.1.2 Options'"
        ::= { wfOspfDynNbrEntry 6 }

    wfOspfDynNbrPriority OBJECT-TYPE
        SYNTAX	INTEGER
        ACCESS	read-only
        STATUS	mandatory
        DESCRIPTION
                "'The priority of this neighbor in the designated router
                election algorithm.  The value 0 signifies that the
                neighbor is not eligible to become the designated
                router on this particular network.'"
        ::= { wfOspfDynNbrEntry 7 }

    wfOspfDynNbrEvents OBJECT-TYPE
        SYNTAX	Counter
        ACCESS	read-only
        STATUS	mandatory
        DESCRIPTION
                "'The number of times this neighbor relationship has
                changed state, or an error has occurred.'"
        ::= { wfOspfDynNbrEntry 8 }

    wfOspfDynNbrLSRetransQLen OBJECT-TYPE
        SYNTAX	Gauge
        ACCESS	read-only
        STATUS	mandatory
        DESCRIPTION
                "'The current length of the retransmission queue.'"
        ::= { wfOspfDynNbrEntry 9 }

    wfOspfNSSARangeTable OBJECT-TYPE
        SYNTAX	SEQUENCE OF WfOspfNSSARangeEntry
        ACCESS	not-accessible
        STATUS	mandatory
        DESCRIPTION
                "--  OSPF NSSA Range Table

                --      The OSPF NSSA Range Table describes the Type-7 address
		-- 	ranges used in translation/aggregation of Type-7 LSAs
		--	into Type-5 LSAs.
                    REFERENCE
                       'OSPF Internet Draft, Section 3.2 Type-7 Address Range'"
        ::= { wfOspfGroup 12 }


    wfOspfNSSARangeEntry OBJECT-TYPE
        SYNTAX	WfOspfNSSARangeEntry
        ACCESS	not-accessible
        STATUS	mandatory
        DESCRIPTION
                ""
        INDEX	{ wfOspfNSSARangeNet }
        ::= { wfOspfNSSARangeTable 1 }

    WfOspfNSSARangeEntry ::= SEQUENCE {
    	    wfOspfNSSARangeDelete
    		INTEGER,
    	    wfOspfNSSARangeDisable
    		INTEGER,
    	    wfOspfNSSARangeNet
    		IpAddress,
    	    wfOspfNSSARangeMask
    		IpAddress,
    	    wfOspfNSSARangeStatus
    		INTEGER,
	    wfOspfNSSARangeExternRouteTag
    		INTEGER
        }


    wfOspfNSSARangeDelete OBJECT-TYPE
        SYNTAX	 INTEGER {
    		    created(1),
    		    deleted(2)
    		}
        ACCESS	 read-write
        STATUS	 mandatory
        DESCRIPTION
                "This value determines if an type-7 Range has been
                configured for the OSPF NSSA border router ."
        DEFVAL	 { created }
        ::= { wfOspfNSSARangeEntry 1 }

    wfOspfNSSARangeDisable OBJECT-TYPE
        SYNTAX	INTEGER {
    		    enabled(1),
    		    disabled(2)
    		}
        ACCESS	 read-write
        STATUS	 mandatory
        DESCRIPTION
                "`This variable displays the status of
                the entry.  Setting it to `DISBALED' has the effect of
                rendering it inoperative. '"
        DEFVAL	 { enabled }
        ::= { wfOspfNSSARangeEntry 2 }

    wfOspfNSSARangeNet OBJECT-TYPE
        SYNTAX	 IpAddress
        ACCESS	 read-only
        STATUS	 mandatory
        DESCRIPTION
                "`The IP Address of the Net or Subnet indicated by the
                range.'
                         REFERENCE
                `OSPF NSSA Internet Draft, 3.2  type-7 address range'"
        ::= { wfOspfNSSARangeEntry 3 }

    wfOspfNSSARangeMask OBJECT-TYPE
        SYNTAX	 IpAddress
        ACCESS 	read-write
        STATUS 	mandatory
        DESCRIPTION
                "`The Subnet Mask that pertains to the Net or Subnet.'
                         REFERENCE
                `OSPF NSSA Internet Draft, 3.2  type-7 address range'"
        ::= { wfOspfNSSARangeEntry 4 }

	wfOspfNSSARangeStatus OBJECT-TYPE
        SYNTAX	 INTEGER {
    		    advertise(1),
    		    block(2)
    		}
        ACCESS	 read-write
        STATUS 	mandatory
        DESCRIPTION
                "`Set to either Advertise or DoNotAdvertise.  Routing
                 information is condensed at area boundaries.  External to
                 the area, at most a single route is advertised for each
                 address range.  The route is advertised if and only if the
                 addre range's Status is set to Advertise.  Unadvertised
                 ranges allow the existence of certain networks to be
                 intentionally hidden from other areas.  Status is set to
                 Advertise by default.'
                         REFERENCE
                `OSPF NSSA Internet Draft, 3.2  type-7 address range'"
        DEFVAL	{ advertise }
        ::= { wfOspfNSSARangeEntry 5 }

    wfOspfNSSARangeExternRouteTag OBJECT-TYPE
        SYNTAX	 INTEGER
        ACCESS	 read-write
        STATUS	 mandatory
        DESCRIPTION
                "`External route tag. This value is used in the aggregated
                  type-5 LSA'
                         REFERENCE
                `OSPF NSSA Internet Draft, 3.2  type-7 address range'"
        ::= { wfOspfNSSARangeEntry 6 }



    END  -- Wellfleet-OSPF-MIB
