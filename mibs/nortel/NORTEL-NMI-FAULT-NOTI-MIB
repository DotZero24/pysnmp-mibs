NORTEL-NMI-FAULT-NOTI-MIB

DEFINITIONS ::= BEGIN

   IMPORTS
       nortelNMInotificationsMIB,
       nortelNMIcurrentTxNotificationSequenceNum,
       nortelNMInotifyNeType,
       nortelNMInotifyNeName,
       nortelNMInotifyNeAdminState,
       nortelNMInotifyNeOperState,
       nortelNMInotifyNeUnknownStatus
           FROM  NORTEL-NMI-NOTIFICATIONS-MIB
       nortelNMInotificationGroups
           FROM NORTEL-NMI-GROUPS-MIB
       NortelNMItimeStampDef,
       NortelNMIalarmProblemCategory,
       NortelNMIalarmProbableCause
           FROM NORTEL-NMI-TC-MIB

       NOTIFICATION-GROUP
           FROM SNMPv2-CONF
       DisplayString
           FROM SNMPv2-TC
       MODULE-IDENTITY, OBJECT-IDENTITY,
       OBJECT-TYPE, NOTIFICATION-TYPE,
       Unsigned32
           FROM SNMPv2-SMI;


   nortelNMIfaultNotiMIB  MODULE-IDENTITY
       LAST-UPDATED "9907190000Z"
       ORGANIZATION "Nortel Networks"
       CONTACT-INFO
              "   Jingdong Liu

                Postal: Nortel Networks
                        P. O. Box 3511, Station C
                        Ottawa, Ontario
                        CANADA
                        K1Y 4H7

                Email:  jingdong@nortelnetworks.com"


       DESCRIPTION
               "This module contains the fault management related
                notifications for the Nortel NMI."

       -- Revision history
       REVISION "9907190000Z"
       DESCRIPTION
                " Add ASCII string limitations for componentID, etc."

       REVISION "9906240000Z"
       DESCRIPTION
                " The fourth version of this MIB module.
                  Module-identity OID assignment changed.

                  Revisions introduced by Shobana Sundaram."

       REVISION "9905310000Z"
       DESCRIPTION
                " The third version of this MIB module.
                  Contact info updated and Revision history added.
                "


       REVISION "9904120000Z"
       DESCRIPTION
                " The second version of this MIB module.
                  Contact info updated and Revision history added.
                  Ne type varbind included at the state change notification."

       REVISION "9903220000Z"
       DESCRIPTION
                " The first version of this MIB module."


       ::= { nortelNMInotificationsMIB 4 }

  -- all notification OIDs would be prefixed with a zero OID to
  -- facilate snmp v1<->v2 conversion

  nortelNMIfaultNotiPrefix  OBJECT-IDENTITY
           STATUS         current
           DESCRIPTION
                  "This OID represents the prefix branch for all Nortel NMI
                   fault  Notifications.
                   The last but one sub identifier in the OID of
                   any Notification must have the value zero to facilitate
                   v2<-->v1 conversion."
           ::=  {nortelNMIfaultNotiMIB  0 }


   nortelNMIfaultNotiVarbinds  OBJECT-IDENTITY
           STATUS         current
           DESCRIPTION
                  "This OID represents the branch which contains varbinds to
                   fault management related notifications."
           ::=  {nortelNMIfaultNotiMIB  1 }




  -- The following variables belong to the accessible-for-notify clause and
  -- are defined here mainly to be included as varbinds to notifications.
  -- No other protocol operations will be supported for these


          nortelNMInotifyAlarmComponentId  OBJECT-TYPE
              SYNTAX  DisplayString
              MAX-ACCESS  accessible-for-notify
              STATUS  current
              DESCRIPTION

                 "This variable represents the Distinguished Name (DN)
                  (refer X.720) of the component object against which the
                  particular alarm is raised. The entire component hierarchy
                  should be presented in the category-value information
                  model to unambiguosly identify the specific component
                  object instance.  Here category refers to the type of the
                  component and value refers to the
                  instance identifier, both are represented as strings.

                  The format of the string is

                      NEtype=NEname;component class=component instance Id;....

                  The root component is always the NE and the NE is identified
                  via its type as the category and the value as the NE name.
                  The managed element class for the NE is implicitly assumed.
                  The NE type is based on NortelNMIneType textual convention.

                  With NE as the root, the entire containment with the list of
                  Relative Distinguished Names (RDNs) is presented upto the
                  point where the alarming component is clearly identified.

                  Semicolon is the delimiter between a 'category=value' pair.
                  The string can only contain alphanumeric characters and
                  underscores. No commas, spaces, slashes, hyphens, or
                  dollar signs is allowed."


              ::= { nortelNMIfaultNotiVarbinds  1 }


          nortelNMInotifyAlarmCategory  OBJECT-TYPE
              SYNTAX   NortelNMIalarmProblemCategory
              MAX-ACCESS  accessible-for-notify
              STATUS  current
              DESCRIPTION

                 "This variable presents the problem category of the alarm
                  as per the definition of the textual convention
                  NortelNMIalarmProblemCategory from NORTEL-NMI-TC-MIB."

              ::= { nortelNMIfaultNotiVarbinds  2 }



          nortelNMInotifyAlarmNotificationID  OBJECT-TYPE
              SYNTAX   Unsigned32 (1..1073741824)
              MAX-ACCESS  accessible-for-notify
              STATUS  current
              DESCRIPTION

                 "This variable is the notification identifier of the alarm
                  that must be unique across all notifications of the particular NE
                  in context through the time that correlation is significant."

              ::= { nortelNMIfaultNotiVarbinds  3 }


          nortelNMInotifyAlarmDescription  OBJECT-TYPE
              SYNTAX   DisplayString (SIZE(1..255))
              MAX-ACCESS  accessible-for-notify
              STATUS  current
              DESCRIPTION

                  "This variable provides the description text for
                   the particular alarm."

              ::= { nortelNMIfaultNotiVarbinds  4 }


          nortelNMInotifyAlarmTimeStamp  OBJECT-TYPE
              SYNTAX   NortelNMItimeStampDef
              MAX-ACCESS  accessible-for-notify
              STATUS  current
              DESCRIPTION

                 "This variable presents the relative timestamp of
                  occurrence of the alarm.
                  NortelNMItimeStampDef textual convention is defined at the
                  NORTEL-NMI-TC-MIB."


              ::= { nortelNMIfaultNotiVarbinds  5 }



          nortelNMInotifyAlarmProbableCause  OBJECT-TYPE
              SYNTAX   NortelNMIalarmProbableCause
              MAX-ACCESS  accessible-for-notify
              STATUS  current
              DESCRIPTION

                 "This variable provides the probable cause of the
                  particular alarm."

              ::= { nortelNMIfaultNotiVarbinds  6 }


          nortelNMInotifyAlarmSpecificProblem  OBJECT-TYPE
              SYNTAX   DisplayString (SIZE(1..255))
              MAX-ACCESS  accessible-for-notify
              STATUS  current
              DESCRIPTION

                 "This variable provides the specific problem data
                  (ITU-T X.733) to further qualify the probable cause
                  of the particular alarm."

              ::= { nortelNMIfaultNotiVarbinds  7 }


          nortelNMInotifyAlarmCorrelationIdList  OBJECT-TYPE
              SYNTAX   DisplayString
              MAX-ACCESS  accessible-for-notify
              STATUS  current
              DESCRIPTION

                 "This variable provides the list of Notification Ids of
                  previously reported alarms that this alarm correlates to.
                  This correlation refers to implicitly clearing
                  the previously raised alarms and overriding them with
                  this alarm report. The format of this string is

                  'notificationID1;notificationID2......',
                  with a list of integer notification ID values corresponding to
                  the correlated alarms with ';' as the delimiter between any
                  two Notification Identifiers."


              ::= { nortelNMIfaultNotiVarbinds  8 }


          nortelNMInotifyNeStateChangeTime  OBJECT-TYPE
              SYNTAX NortelNMItimeStampDef
              MAX-ACCESS  accessible-for-notify
              STATUS  current
              DESCRIPTION
                 "This variable represents the time at which a certain NE state
                  has been changed. "

              ::= { nortelNMIfaultNotiVarbinds 9 }






--  faults related notifications


      -- state change notification

         nortelNMIneOSIstateChangeNotification NOTIFICATION-TYPE
                          OBJECTS { nortelNMIcurrentTxNotificationSequenceNum,
                                    nortelNMInotifyNeType,
                                    nortelNMInotifyNeName,
                                    nortelNMInotifyNeStateChangeTime,

                                    nortelNMInotifyNeAdminState,
                                    nortelNMInotifyNeOperState,
                                    nortelNMInotifyNeUnknownStatus
                                  }
            STATUS  current
            DESCRIPTION
              "This notification indicates that one of the NE OSI states
               has been changed. The modified value of the specific state
               would be included as the varbind in the actual
               Notification PDU. We currently support changes to
               admin state, operational state and unknown status."

          ::= { nortelNMIfaultNotiPrefix 101 }



      -- alarm  Notifications

          nortelNMIalarmClearNotification NOTIFICATION-TYPE
                          OBJECTS { nortelNMIcurrentTxNotificationSequenceNum,
                                    nortelNMInotifyAlarmComponentId,
                                    nortelNMInotifyAlarmDescription,
                                    nortelNMInotifyAlarmTimeStamp,
                                    nortelNMInotifyAlarmCorrelationIdList
                                  }
            STATUS  current
            DESCRIPTION
              "This notification indicates that one or more previously
               reported alarms have been cleared and the previously reported
               alarms are identified via the correlation id list field.
               The varbinds include alarm context via the ComponentId field
               and other additional useful information."


          ::= { nortelNMIfaultNotiPrefix 201 }


          nortelNMIwarningAlarmNotification NOTIFICATION-TYPE
                          OBJECTS { nortelNMIcurrentTxNotificationSequenceNum,
                                    nortelNMInotifyAlarmComponentId,
                                    nortelNMInotifyAlarmCategory,
                                    nortelNMInotifyAlarmNotificationID,
                                    nortelNMInotifyAlarmDescription,
                                    nortelNMInotifyAlarmTimeStamp,
                                    nortelNMInotifyAlarmProbableCause,
                                    nortelNMInotifyAlarmSpecificProblem,
                                    nortelNMInotifyAlarmCorrelationIdList
                                  }
            STATUS  current
            DESCRIPTION
              "This notification indicates that an alarm of 'Warning' severity
               has been raised on a NE.
               The varbinds include alarm context via the ComponentId field
               and other additional useful information on the alarm condition."


          ::= { nortelNMIfaultNotiPrefix 202 }


          nortelNMIminorAlarmNotification NOTIFICATION-TYPE
                          OBJECTS { nortelNMIcurrentTxNotificationSequenceNum,
                                    nortelNMInotifyAlarmComponentId,
                                    nortelNMInotifyAlarmCategory,
                                    nortelNMInotifyAlarmNotificationID,
                                    nortelNMInotifyAlarmDescription,
                                    nortelNMInotifyAlarmTimeStamp,
                                    nortelNMInotifyAlarmProbableCause,
                                    nortelNMInotifyAlarmSpecificProblem,
                                    nortelNMInotifyAlarmCorrelationIdList
                                  }
            STATUS  current
            DESCRIPTION
              "This notification indicates that an alarm of 'Minor' severity
               has been raised on a NE.
               The varbinds include alarm context via the ComponentId field
               and other additional useful information on the alarm condition."


          ::= { nortelNMIfaultNotiPrefix 203 }



          nortelNMImajorAlarmNotification NOTIFICATION-TYPE
                          OBJECTS { nortelNMIcurrentTxNotificationSequenceNum,
                                    nortelNMInotifyAlarmComponentId,
                                    nortelNMInotifyAlarmCategory,
                                    nortelNMInotifyAlarmNotificationID,
                                    nortelNMInotifyAlarmDescription,
                                    nortelNMInotifyAlarmTimeStamp,
                                    nortelNMInotifyAlarmProbableCause,
                                    nortelNMInotifyAlarmSpecificProblem,
                                    nortelNMInotifyAlarmCorrelationIdList
                                  }
            STATUS  current
            DESCRIPTION
              "This notification indicates that an alarm of 'Major' severity
               has been raised on a NE.
               The varbinds include alarm context via the ComponentId field
               and other additional useful information on the alarm condition."


          ::= { nortelNMIfaultNotiPrefix 204 }


          nortelNMIcriticalAlarmNotification NOTIFICATION-TYPE
                          OBJECTS { nortelNMIcurrentTxNotificationSequenceNum,
                                    nortelNMInotifyAlarmComponentId,
                                    nortelNMInotifyAlarmCategory,
                                    nortelNMInotifyAlarmNotificationID,
                                    nortelNMInotifyAlarmDescription,
                                    nortelNMInotifyAlarmTimeStamp,
                                    nortelNMInotifyAlarmProbableCause,
                                    nortelNMInotifyAlarmSpecificProblem,
                                    nortelNMInotifyAlarmCorrelationIdList
                                  }
            STATUS  current
            DESCRIPTION
              "This notification indicates that an alarm of 'Critical' severity
               has been raised on a NE.
               The varbinds include alarm context via the ComponentId field
               and other additional useful information on the alarm condition."


          ::= { nortelNMIfaultNotiPrefix 205 }

-- Notification group definitions

     nortelNMIneStateChangeNotificationGroup  NOTIFICATION-GROUP
           NOTIFICATIONS  {
                          nortelNMIneOSIstateChangeNotification
                          }
           STATUS   current
           DESCRIPTION
                " Nortel NMI NE state change notification group."
           ::= { nortelNMInotificationGroups 3}

    nortelNMIneAlarmNotificationsGroup NOTIFICATION-GROUP
           NOTIFICATIONS  {
                          nortelNMIalarmClearNotification,
                          nortelNMIwarningAlarmNotification,
                          nortelNMIminorAlarmNotification,
                          nortelNMImajorAlarmNotification,
                          nortelNMIcriticalAlarmNotification
                          }
           STATUS   current
           DESCRIPTION
                " Nortel NMI NE alarm notification group."
           ::= { nortelNMInotificationGroups 4}




END
