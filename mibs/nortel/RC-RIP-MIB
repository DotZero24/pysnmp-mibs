RC-RIP-MIB DEFINITIONS ::= BEGIN

IMPORTS
    MODULE-IDENTITY, OBJECT-TYPE, Integer32, IpAddress, Counter32, Unsigned32
        FROM SNMPv2-SMI
    DisplayString, TruthValue, RowStatus
        FROM SNMPv2-TC
    InterfaceIndex
        FROM IF-MIB
    rcIpRipInterface
        FROM RC-IP-MIB
    rcRip, EnableValue
        FROM RAPID-CITY
    Ipv6Address
        FROM IPV6-TC;


rcRipMib MODULE-IDENTITY
       LAST-UPDATED     "201702020000Z"
       ORGANIZATION     "Bay Networks, Rapid-City Group"
       CONTACT-INFO     "
                                        Edwin Tsang
                         Postal:        Bay Networks, Inc.
                                        4401 Great America Parkway
                                        Santa Clara, CA 95052-8185

                         Tel:           408-495-6159
                         Fax:           408-495-5215
                         E-mail:        edwin_tsang@baynetworks.com
                        "
       DESCRIPTION      "Enterprise MIB for the Accelar product family."

       REVISION "201702020000Z" -- 02 Feb 2017
       DESCRIPTION "Version 11: Corrected MIB compiler error."

       REVISION "201604040000Z" -- 04 Apr 2016
       DESCRIPTION "Version 10:  added rcIpv6RipngExpRouteEntry"

       REVISION "201601220000Z" -- 22 Jan 2016
       DESCRIPTION "Version 9:  added rcIpv6RipngIfStatsClearStats"

       REVISION "201510120000Z" -- 12 Oct 2015
       DESCRIPTION "Version 8:  Changed rcIpv6RipngInterfaceRipEnable to
	   			rcIpv6RipngInterfaceRipAdminStatus.
				Added cIpv6RipngInterfaceRipOperStatus"

       REVISION "201508060000Z" -- 06 August 2015
       DESCRIPTION "Version 7:  Added rcIpv6RipngDefaultImportMetric.
	   			Requested by Hemadri Mhaskar (submit 25148) (Pre)."

       REVISION "201505290000Z" -- 29 May 2015
       DESCRIPTION "Version 6:  Corrected MIB compiling errors."

       REVISION "201503120000Z" -- 12 March 2015
       DESCRIPTION "Version 5: Added the following -
	   		       rcRipng, rcRipngObjects, rcIpv6RipngGeneralGroup,
			       rcIpv6RipngAdminState, rcIpv6RipngUpdateTime,
			       rcIpv6RipngGlobalHoldDownTime,
			       rcIpv6RipngGlobalTimeOutInterval,
			       rcIpv6RipngDefaultInfoMetric,
			       rcIpv6RipngDefaultInfoState,
			       rcIpv6RipngInterfaceTable and
			       rcIpv6RipngIfStatsTable.
			       Requested by Hemadri/Amruta for IPv6 RIPng Rel1 (Prem)"

       REVISION "200807180000Z" -- 18 July 2008
       DESCRIPTION "Version 4: Add DEFVAL clause in rcRipExtUpdateTime. The DEFVAL
                               is 30. Change SYNTAX to Integer32(1..360)."

       REVISION "200407200000Z" -- 20 July 2004
       DESCRIPTION "Version 3: Added version info"

       ::= { rcRip 0 }

-- IP Rip Interface Table

rcIpRipInterfaceTable OBJECT-TYPE
        SYNTAX          SEQUENCE OF RcIpRipInterfaceEntry
        MAX-ACCESS      not-accessible
        STATUS          current
        DESCRIPTION     "IP Rip Interface table"
        ::= { rcIpRipInterface 1 }

rcIpRipInterfaceEntry OBJECT-TYPE
        SYNTAX          RcIpRipInterfaceEntry
        MAX-ACCESS      not-accessible
        STATUS          current
        DESCRIPTION     "An entry of Ip Rip Interface Table."
        INDEX           { rcIpRipInterfaceAddress }
        ::= { rcIpRipInterfaceTable 1 }

RcIpRipInterfaceEntry ::=
        SEQUENCE {
                rcIpRipInterfaceAddress                IpAddress,
                rcIpRipInterfaceIfIndex                InterfaceIndex,
                rcIpRipInterfaceRipEnable              EnableValue,
                rcIpRipInterfaceAccDefRte              TruthValue,
                rcIpRipInterfaceAdvDefRte              TruthValue,
                rcIpRipInterfaceAutoAggregate          TruthValue,
                rcIpRipInterfaceCost                   Integer32,
                rcIpRipInterfaceListen                 TruthValue,
                rcIpRipInterfacePoison                 TruthValue,
                rcIpRipInterfaceSupply                 TruthValue,
                rcIpRipInterfaceTriggeredUpdate        TruthValue,
                rcIpRipInterfaceInPolicy               DisplayString,
                rcIpRipInterfaceOutPolicy              DisplayString,
                rcIpRipInterfaceProxyAnnounceFlag      TruthValue,
                rcIpRipInterfaceHolddown               INTEGER,
                rcIpRipInterfaceTimeout                INTEGER
        }

rcIpRipInterfaceAddress OBJECT-TYPE
        SYNTAX        IpAddress
        MAX-ACCESS    read-only
        STATUS        current
        DESCRIPTION   "Ip Address"
        ::= { rcIpRipInterfaceEntry 1 }

rcIpRipInterfaceIfIndex OBJECT-TYPE
        SYNTAX        InterfaceIndex
        MAX-ACCESS    read-only
        STATUS        current
        DESCRIPTION   "Rip Interface If Index."
        ::= { rcIpRipInterfaceEntry 2 }

rcIpRipInterfaceRipEnable OBJECT-TYPE
        SYNTAX        EnableValue
        MAX-ACCESS    read-write
        STATUS        current
        DESCRIPTION   ""
        ::= { rcIpRipInterfaceEntry 3 }

rcIpRipInterfaceAccDefRte OBJECT-TYPE
        SYNTAX        TruthValue
        MAX-ACCESS    read-write
        STATUS        current
        DESCRIPTION   ""
        ::= { rcIpRipInterfaceEntry 4 }

rcIpRipInterfaceAdvDefRte OBJECT-TYPE
        SYNTAX        TruthValue
        MAX-ACCESS    read-write
        STATUS        current
        DESCRIPTION   ""
        ::= { rcIpRipInterfaceEntry 5 }

rcIpRipInterfaceAutoAggregate OBJECT-TYPE
        SYNTAX        TruthValue
        MAX-ACCESS    read-write
        STATUS        current
        DESCRIPTION   ""
        ::= { rcIpRipInterfaceEntry 6 }

rcIpRipInterfaceCost OBJECT-TYPE
        SYNTAX        Integer32
        MAX-ACCESS    read-write
        STATUS        current
        DESCRIPTION   ""
        ::= { rcIpRipInterfaceEntry 7 }

rcIpRipInterfaceListen OBJECT-TYPE
        SYNTAX        TruthValue
        MAX-ACCESS    read-write
        STATUS        current
        DESCRIPTION   ""
        ::= { rcIpRipInterfaceEntry 8 }

rcIpRipInterfacePoison OBJECT-TYPE
        SYNTAX        TruthValue
        MAX-ACCESS    read-write
        STATUS        current
        DESCRIPTION   ""
        ::= { rcIpRipInterfaceEntry 9 }

rcIpRipInterfaceSupply OBJECT-TYPE
        SYNTAX        TruthValue
        MAX-ACCESS    read-write
        STATUS        current
        DESCRIPTION   ""
        ::= { rcIpRipInterfaceEntry 10 }

rcIpRipInterfaceTriggeredUpdate OBJECT-TYPE
        SYNTAX        TruthValue
        MAX-ACCESS    read-write
        STATUS        current
        DESCRIPTION   ""
        ::= { rcIpRipInterfaceEntry 11 }

rcIpRipInterfaceInPolicy OBJECT-TYPE
        SYNTAX        DisplayString
        MAX-ACCESS    read-write
        STATUS        current
        DESCRIPTION   ""
        ::= { rcIpRipInterfaceEntry 12 }

rcIpRipInterfaceOutPolicy OBJECT-TYPE
        SYNTAX        DisplayString
        MAX-ACCESS    read-write
        STATUS        current
        DESCRIPTION   ""
        ::= { rcIpRipInterfaceEntry 13 }

rcIpRipInterfaceProxyAnnounceFlag OBJECT-TYPE
        SYNTAX        TruthValue
        MAX-ACCESS    read-write
        STATUS        current
        DESCRIPTION   ""
        ::= { rcIpRipInterfaceEntry 14 }

rcIpRipInterfaceHolddown OBJECT-TYPE
        SYNTAX        INTEGER (0..360)
        MAX-ACCESS    read-write
        STATUS        current
        DESCRIPTION   "Used to indicate the rip holddown timer for this
                       interface"
        ::= { rcIpRipInterfaceEntry 15 }

rcIpRipInterfaceTimeout OBJECT-TYPE
        SYNTAX        INTEGER (15..259200)
        MAX-ACCESS    read-write
        STATUS        current
        DESCRIPTION   "Used to indicate the rip timeout interval for
                       this interface"
        ::= { rcIpRipInterfaceEntry 16 }


-- RIP Group

rcRipExtOperation OBJECT-TYPE
        SYNTAX        INTEGER	{
                         disable(1),
                         enable(2)
	 	      }
        MAX-ACCESS    read-write
        STATUS        current
        DESCRIPTION   "Enable or disable the operation of RIP on all
		      Interfaces."
        ::= { rcRip 1 }

rcRipExtUpdateTime OBJECT-TYPE
        SYNTAX        Integer32(1..360)
        MAX-ACCESS    read-write
        STATUS        current
        DESCRIPTION   "The time between transmission of RIP updates
		      on all interfaces."
		    DEFVAL	{ 30 }
        ::= { rcRip 2 }

rcRipExtTable OBJECT-TYPE
        SYNTAX        SEQUENCE OF RcRipExtEntry
        MAX-ACCESS    not-accessible
        STATUS        current
        DESCRIPTION   "RIP extension table.  This table augments the
		      standard IfConfTable table in RFC1389."
        ::= { rcRip 3 }

rcRipExtEntry OBJECT-TYPE
        SYNTAX        RcRipExtEntry
        MAX-ACCESS    not-accessible
        STATUS        current
        DESCRIPTION   "Entry containing Proprietary RIP information.
	  	      An entry is automatically created in this table
                      when an ip address is configured on an interface."
        INDEX         { rcRipExtEntIfIndex }
        ::= { rcRipExtTable 1 }

RcRipExtEntry ::=
        SEQUENCE {
                rcRipExtEntIfIndex InterfaceIndex,
                rcRipExtEntTalk INTEGER,
                rcRipExtEntListen INTEGER,
                rcRipExtEntPoison INTEGER
        }

rcRipExtEntIfIndex OBJECT-TYPE
        SYNTAX        InterfaceIndex
        MAX-ACCESS    read-only
        STATUS        current
        DESCRIPTION   "The index value which uniquely identifies the
                      interface to which this entry is applicable.
                      The interface identified by a particular value
                      of this index is the same interface as
                      identified by the same value of ifIndex."
        ::= { rcRipExtEntry 1 }

rcRipExtEntTalk OBJECT-TYPE
        SYNTAX       INTEGER {
                        disable(1),
                        enable(2)
		      }
        MAX-ACCESS    read-write
        STATUS        current
        DESCRIPTION   "Enable or disable RIP transmission on the
		      specified interface."
	DEFVAL        { enable }
        ::= { rcRipExtEntry 2 }

rcRipExtEntListen OBJECT-TYPE
        SYNTAX        INTEGER {
                         disable(1),
                         enable(2)
		      }
        MAX-ACCESS    read-write
        STATUS        current
        DESCRIPTION   "Enable or disable RIP reception on the specified
		      interface."
	DEFVAL        { enable }
        ::= { rcRipExtEntry 3 }

rcRipExtEntPoison OBJECT-TYPE
        SYNTAX        INTEGER {
                         disable(1),
                         enable(2)
                      }
        MAX-ACCESS    read-write
        STATUS        current
        DESCRIPTION   "Enable or disable operation of poison reverse
		      on the specified interface.  If poison is
		      disabled, split-horizon operation is enabled."
	DEFVAL        { disable }
        ::= { rcRipExtEntry 4 }

-- rcRipExtV2Table

rcRipExtV2Table OBJECT-TYPE
        SYNTAX        SEQUENCE OF RcRipExtV2Entry
        MAX-ACCESS    not-accessible
        STATUS        deprecated
        DESCRIPTION   "RIP extension table.  This table augments the
		      standard IfConfTable table in RFC1389."
        ::= { rcRip 4 }

rcRipExtV2Entry OBJECT-TYPE
        SYNTAX        RcRipExtV2Entry
        MAX-ACCESS    not-accessible
        STATUS        deprecated
        DESCRIPTION   "Entry containing Proprietary RIP information.
	  	      An entry is automatically created in this table
                      when an ip address is configured on an interface."
        INDEX         { rcRipExtV2EntIfIndex, rcRipExtV2EntIpIfAddr }
        ::= { rcRipExtV2Table 1 }

RcRipExtV2Entry ::=
        SEQUENCE {
                rcRipExtV2EntIfIndex InterfaceIndex,
                rcRipExtV2EntIpIfAddr IpAddress,
                rcRipExtV2EntTalk INTEGER,
                rcRipExtV2EntListen INTEGER,
                rcRipExtV2EntPoison INTEGER
        }

rcRipExtV2EntIfIndex OBJECT-TYPE
        SYNTAX        InterfaceIndex
        MAX-ACCESS    read-only
        STATUS        deprecated
        DESCRIPTION   "The index value which uniquely identifies the
                      interface to which this entry is applicable.
                      The interface identified by a particular value
                      of this index is the same interface as
                      identified by the same value of ifIndex."
        ::= { rcRipExtV2Entry 1 }

rcRipExtV2EntIpIfAddr OBJECT-TYPE
        SYNTAX        IpAddress
        MAX-ACCESS    read-only
        STATUS        deprecated
        DESCRIPTION   "Ip Address."
        ::= { rcRipExtV2Entry 2 }

rcRipExtV2EntTalk OBJECT-TYPE
        SYNTAX       INTEGER {
                        disable(1),
                        enable(2)
		      }
        MAX-ACCESS    read-write
        STATUS        deprecated
        DESCRIPTION   "Enable or disable RIP transmission on the
		      specified interface."
	DEFVAL        { enable }
        ::= { rcRipExtV2Entry 3 }

rcRipExtV2EntListen OBJECT-TYPE
        SYNTAX        INTEGER {
                         disable(1),
                         enable(2)
		      }
        MAX-ACCESS    read-write
        STATUS        deprecated
        DESCRIPTION   "Enable or disable RIP reception on the specified
		      interface."
	DEFVAL        { enable }
        ::= { rcRipExtV2Entry 4 }

rcRipExtV2EntPoison OBJECT-TYPE
        SYNTAX        INTEGER {
                         disable(1),
                         enable(2)
                      }
        MAX-ACCESS    read-write
        STATUS        deprecated
        DESCRIPTION   "Enable or disable operation of poison reverse
		      on the specified interface.  If poison is
		      disabled, split-horizon operation is enabled."
	DEFVAL        { disable }
        ::= { rcRipExtV2Entry 5 }

--
-- IPv6 RIPng MIBs
--
rcRipng                 OBJECT IDENTIFIER ::= { rcRip 5 }

rcRipngObjects         OBJECT IDENTIFIER ::= { rcRipng 1 }

rcIpv6RipngGeneralGroup OBJECT IDENTIFIER ::= { rcRipngObjects 1 }

rcIpv6RipngAdminState OBJECT-TYPE
        SYNTAX        EnableValue
        MAX-ACCESS    read-write
        STATUS        current
        DESCRIPTION   "Enable or disable RIPng globally"
        ::= { rcIpv6RipngGeneralGroup 1 }

rcIpv6RipngUpdateTime OBJECT-TYPE
        SYNTAX        Integer32 (1..360)
        UNITS         "seconds"
        MAX-ACCESS    read-write
        STATUS        current
        DESCRIPTION   "The time between transmission of RIPng updates."
	DEFVAL        { 30 }
        ::= { rcIpv6RipngGeneralGroup 2 }

rcIpv6RipngGlobalHoldDownTime OBJECT-TYPE
        SYNTAX        Integer32 (0..360)
        UNITS         "seconds"
        MAX-ACCESS    read-write
        STATUS        current
        DESCRIPTION   "Used to set the system-wide RIPng hold down time
                      in seconds."
        DEFVAL        { 120 }
        ::= { rcIpv6RipngGeneralGroup 3 }

rcIpv6RipngGlobalTimeOutInterval OBJECT-TYPE
       SYNTAX       Integer32 (15..259200)
       UNITS        "seconds"
       MAX-ACCESS   read-write
       STATUS       current
       DESCRIPTION  "Ripng TimeOut Interval in seconds"
       DEFVAL       { 180 }
       ::= { rcIpv6RipngGeneralGroup 4}

rcIpv6RipngDefaultInfoMetric OBJECT-TYPE
       SYNTAX       Integer32 (1..15)
       MAX-ACCESS   read-write
       STATUS       current
       DESCRIPTION  "Ripng  default-information metric"
       DEFVAL       { 1 }
       ::= { rcIpv6RipngGeneralGroup 5 }

rcIpv6RipngDefaultInfoState OBJECT-TYPE
       SYNTAX        EnableValue
       MAX-ACCESS    read-write
       STATUS        current
       DESCRIPTION   "Default-information  enable/disable at global level"
       ::= { rcIpv6RipngGeneralGroup  6 }

rcIpv6RipngDefaultImportMetric OBJECT-TYPE
        SYNTAX        Integer32 (0..15)
        MAX-ACCESS    read-only
        STATUS        current
        DESCRIPTION   "Ripng default import metric"
        DEFVAL        { 1 }
        ::= { rcIpv6RipngGeneralGroup 7 }

--
-- IPv6 RIPng Interface Table
--
rcIpv6RipngInterfaceTable OBJECT-TYPE
        SYNTAX          SEQUENCE OF RcIpv6RipngInterfaceEntry
        MAX-ACCESS      not-accessible
        STATUS          current
        DESCRIPTION     "IPv6 Ripng Interface table"
        ::= { rcRipngObjects 2 }

rcIpv6RipngInterfaceEntry OBJECT-TYPE
        SYNTAX          RcIpv6RipngInterfaceEntry
        MAX-ACCESS      not-accessible
        STATUS          current
        DESCRIPTION     "An entry of IPv6 Ripng Interface Table."
        INDEX           { rcIpv6RipngInterfaceIfIndex }
        ::= { rcIpv6RipngInterfaceTable 1 }

RcIpv6RipngInterfaceEntry ::=
        SEQUENCE {
	        rcIpv6RipngInterfaceIfIndex                InterfaceIndex,
                rcIpv6RipngInterfaceRipAdminStatus         EnableValue,
		rcIpv6RipngInterfaceDefaultInfoState       EnableValue,
                rcIpv6RipngInterfaceCost                   Integer32,
		rcIpv6RipngInterfacePoison                 EnableValue,
		rcIpv6RipngInterfaceRipOperStatus          EnableValue,
                rcIpv6RipngInterfaceRowStatus              RowStatus
        }

rcIpv6RipngInterfaceIfIndex OBJECT-TYPE
        SYNTAX        InterfaceIndex
        MAX-ACCESS    not-accessible
        STATUS        current
        DESCRIPTION   "Ripng Interface Index."
        ::= { rcIpv6RipngInterfaceEntry 1 }

rcIpv6RipngInterfaceRipAdminStatus OBJECT-TYPE
        SYNTAX        EnableValue
        MAX-ACCESS    read-create
        STATUS        current
        DESCRIPTION   "Enable/Disable RIPng on interface"
        ::= { rcIpv6RipngInterfaceEntry 2 }

rcIpv6RipngInterfaceDefaultInfoState OBJECT-TYPE
        SYNTAX        EnableValue
        MAX-ACCESS    read-create
        STATUS        current
        DESCRIPTION   "Origante default route under the particular interface"
        ::= { rcIpv6RipngInterfaceEntry 3 }

rcIpv6RipngInterfaceCost OBJECT-TYPE
        SYNTAX        Integer32(1..15)
        MAX-ACCESS    read-create
        STATUS        current
        DESCRIPTION   "Used to specify the cost of RIPng metric"
        ::= { rcIpv6RipngInterfaceEntry 4 }

rcIpv6RipngInterfacePoison OBJECT-TYPE
        SYNTAX        EnableValue
        MAX-ACCESS    read-create
        STATUS        current
        DESCRIPTION   "Enable/Disable poison reverse on Ripng interface "
        ::= { rcIpv6RipngInterfaceEntry 5 }

rcIpv6RipngInterfaceRipOperStatus OBJECT-TYPE
        SYNTAX        EnableValue
        MAX-ACCESS    read-only
        STATUS        current
        DESCRIPTION   "Enable/Disable RIPng Operational state on interface"
        ::= { rcIpv6RipngInterfaceEntry 6 }

rcIpv6RipngInterfaceRowStatus OBJECT-TYPE
        SYNTAX        RowStatus
        MAX-ACCESS    read-create
        STATUS        current
        DESCRIPTION   "This variable controls the status of the entry."
        ::= { rcIpv6RipngInterfaceEntry 7 }

--
-- IPv6 RIPng Interface Statistics Table
--
rcIpv6RipngIfStatsTable  OBJECT-TYPE
        SYNTAX        SEQUENCE OF RcIpv6RipngIfStatsEntry
        MAX-ACCESS    not-accessible
        STATUS        current
        DESCRIPTION   "A list of subnets which require separate
                       status monitoring in RIPng."
        ::= { rcRipngObjects 3 }

rcIpv6RipngIfStatsEntry OBJECT-TYPE
        SYNTAX        RcIpv6RipngIfStatsEntry
        MAX-ACCESS    not-accessible
        STATUS        current
        DESCRIPTION   "A Single Routing Domain in a single Subnet."
        INDEX         { rcIpv6RipngIfStatsIfIndex }
        ::= { rcIpv6RipngIfStatsTable 1 }

RcIpv6RipngIfStatsEntry ::=
        SEQUENCE {
	       rcIpv6RipngIfStatsIfIndex       InterfaceIndex,
               rcIpv6RipngIfStatsRcvBadPackets Counter32,
               rcIpv6RipngIfStatsRcvBadRoutes  Counter32,
               rcIpv6RipngIfStatsSentUpdates   Counter32,
               rcIpv6RipngIfStatsRcvUpdates    Counter32,
	       rcIpv6RipngIfStatsClearStats    TruthValue
        }

rcIpv6RipngIfStatsIfIndex OBJECT-TYPE
        SYNTAX        InterfaceIndex
        MAX-ACCESS    not-accessible
        STATUS        current
        DESCRIPTION   "The interface index of the RIPng interface."
        ::= { rcIpv6RipngIfStatsEntry 1 }

rcIpv6RipngIfStatsRcvBadPackets OBJECT-TYPE
        SYNTAX        Counter32
        MAX-ACCESS    read-only
        STATUS        current
        DESCRIPTION   "The number of RIPng response packets received by
	    	       the  RIPng  process  which were subsequently dis-
		       carded for any reason (e.g. a version 0 packet,
		       or an unknown command type)."
	::= { rcIpv6RipngIfStatsEntry 2 }


rcIpv6RipngIfStatsRcvBadRoutes OBJECT-TYPE
        SYNTAX        Counter32
        MAX-ACCESS    read-only
	STATUS        current
	DESCRIPTION   "The number of routes, in  valid  RIPng packets,
	    	       which were ignored for any reason (e.g. unknown
		       address family, or invalid metric)."
        ::= { rcIpv6RipngIfStatsEntry  3 }

rcIpv6RipngIfStatsSentUpdates OBJECT-TYPE
        SYNTAX        Counter32
	MAX-ACCESS    read-only
	STATUS        current
	DESCRIPTION   "The number of triggered RIPng  updates  actually
	    	       sent  on  this interface.  This explicitly does
		       NOT include full updates  sent  containing  new
		       information."
        ::= { rcIpv6RipngIfStatsEntry 4 }


rcIpv6RipngIfStatsRcvUpdates OBJECT-TYPE
        SYNTAX        Counter32
	MAX-ACCESS    read-only
	STATUS        current
	DESCRIPTION   "The number of triggered RIPng  updates  actually
	    	       receive  on  this interface.  This explicitly does
		       NOT include full updates  received  containing  new
		       information."
        ::= { rcIpv6RipngIfStatsEntry 5 }

rcIpv6RipngIfStatsClearStats OBJECT-TYPE
        SYNTAX          TruthValue
        MAX-ACCESS      read-write
        STATUS          current
        DESCRIPTION    "Clear stats for RIpng interface"
	DEFVAL         { false }
        ::= { rcIpv6RipngIfStatsEntry 6 }

--
-- IPv6 RIPng Expired Routes Table
--
rcIpv6RipngExpRouteTable  OBJECT-TYPE
        SYNTAX        SEQUENCE OF RcIpv6RipngExpRouteEntry
        MAX-ACCESS    not-accessible
        STATUS        current
        DESCRIPTION   "A list of RIPng routes kept when timeout expired
                       until holddown timer expires too."
        ::= { rcRipngObjects 4 }

rcIpv6RipngExpRouteEntry OBJECT-TYPE
        SYNTAX        RcIpv6RipngExpRouteEntry
        MAX-ACCESS    not-accessible
        STATUS        current
        DESCRIPTION   "A Single expired RIPng route."
        INDEX         { rcIpv6RipngExpRouteDest, rcIpv6RipngExpRoutePfxLength, rcIpv6RipngExpRouteIndex }
        ::= { rcIpv6RipngExpRouteTable 1 }

RcIpv6RipngExpRouteEntry ::=
        SEQUENCE {
               rcIpv6RipngExpRouteDest         Ipv6Address,
    	       rcIpv6RipngExpRoutePfxLength    INTEGER,
    	       rcIpv6RipngExpRouteIndex        Unsigned32,
    	       rcIpv6RipngExpRouteIfIndex      InterfaceIndex,
               rcIpv6RipngExpRouteNextHop      Ipv6Address,
               rcIpv6RipngExpRouteType         INTEGER,
               rcIpv6RipngExpRouteProtocol     INTEGER,
               rcIpv6RipngExpRoutePolicy       Integer32,
               rcIpv6RipngExpRouteAge          Unsigned32,
               rcIpv6RipngExpRouteNextHopRDI   Unsigned32,
               rcIpv6RipngExpRouteMetric       Unsigned32,
               rcIpv6RipngExpRouteWeight       Unsigned32,
               rcIpv6RipngExpRouteInfo         OBJECT IDENTIFIER,
               rcIpv6RipngExpRouteValid        TruthValue,
               rcIpv6RipngExpRoutePref         INTEGER
        }

rcIpv6RipngExpRouteDest OBJECT-TYPE
        SYNTAX        Ipv6Address
        MAX-ACCESS    not-accessible
        STATUS        current
        DESCRIPTION
               "The destination IPv6 address of this route.
       	        This object may not take a Multicast address
       	        value."
        ::= { rcIpv6RipngExpRouteEntry 1 }

rcIpv6RipngExpRoutePfxLength OBJECT-TYPE
        SYNTAX        INTEGER(0..128)
        UNITS         "bits"
        MAX-ACCESS    not-accessible
        STATUS        current
        DESCRIPTION
               "Indicates the prefix length of the destination
       	        address."
        ::= { rcIpv6RipngExpRouteEntry 2 }

rcIpv6RipngExpRouteIndex OBJECT-TYPE
        SYNTAX     Unsigned32
        MAX-ACCESS not-accessible
        STATUS     current
        DESCRIPTION
       	       "The value which uniquely identifies the route
       	         among the routes to the same network layer
       	         destination.  The way this value is chosen is
       	         implementation specific but it must be unique for
       	         rcIpv6RipngExpRouteDest/rcIpv6RipngExpRoutePfxLength pair and remain
       	         constant for the life of the route."
     	::= { rcIpv6RipngExpRouteEntry 3 }

rcIpv6RipngExpRouteIfIndex OBJECT-TYPE
        SYNTAX        InterfaceIndex
        MAX-ACCESS    read-only
        STATUS        current
        DESCRIPTION
               "Indicates the interface index where the route was learned from"
        ::= { rcIpv6RipngExpRouteEntry 4 }

rcIpv6RipngExpRouteNextHop OBJECT-TYPE
      	SYNTAX          Ipv6Address
        MAX-ACCESS      read-only
        STATUS          current
        DESCRIPTION
               "Identifier of the next-hop, IPv6 address."
    	::= { rcIpv6RipngExpRouteEntry 5 }

rcIpv6RipngExpRouteType OBJECT-TYPE
        SYNTAX          INTEGER {
                           other    (1),         -- none of the following
                           discard  (2),         -- route that discards traffic and
                                                   -- returns ICMP notification
                           local    (3),         -- local interface
                           remote   (4),         -- remote destination
                           blackhole(5)          -- route that discards traffic silently
                        }
        MAX-ACCESS       read-only
        STATUS           current
        DESCRIPTION
              "The type of route.  Note that local(3) refers to a
               route for which the next hop is the final destination;
               remote(4) refers to a route for which the next hop is
               not the final destination.

               Routes that do not result in traffic forwarding or
               rejection should not be displayed, even if the
               implementation keeps them stored internally.

               reject(2) refers to a route that, if matched, discards
               the message as unreachable and returns a notification
               (e.g., ICMP error) to the message sender.  This is used
               in some protocols as a means of correctly aggregating
               routes.

               blackhole(5) refers to a route that, if matched,
               discards the message silently."
        ::= { rcIpv6RipngExpRouteEntry 6 }

rcIpv6RipngExpRouteProtocol OBJECT-TYPE
        SYNTAX     INTEGER {
       		 other(1),   -- none of the following

                	     -- non-protocol information,
                    	     -- e.g., manually configured
       		 local(2),   -- entries

       		 netmgmt(3), -- static route

                	     -- obtained via Neighbor
                    	     -- Discovery protocol,
       		 ndisc(4),   -- e.g., result of Redirect

                	     -- the following are all
                    	     -- dynamic routing protocols
       		 rip(5),     -- RIPng
      		 ospf(6),    -- Open Shortest Path First
       		 bgp(7),     -- Border Gateway Protocol
        	 idrp(8),    -- InterDomain Routing Protocol
       		 igrp(9)     -- InterGateway Routing Protocol
        }
        MAX-ACCESS	 read-only
        STATUS    	 current
        DESCRIPTION	 "The routing mechanism via which this route was learned."
        ::= { rcIpv6RipngExpRouteEntry 7 }

rcIpv6RipngExpRoutePolicy OBJECT-TYPE
        SYNTAX        Integer32
        MAX-ACCESS    read-only
        STATUS        current
        DESCRIPTION
              "Its purpose is to serve as an additional
               index that may delineate between multiple entries to
               the same destination.  The value { 0 } shall be used
               as the default value for this object."
       ::= { rcIpv6RipngExpRouteEntry 8 }

rcIpv6RipngExpRouteAge OBJECT-TYPE
        SYNTAX        Unsigned32
        UNITS         "seconds"
        MAX-ACCESS    read-only
        STATUS        current
        DESCRIPTION
              "The number of seconds since this route was last updated
               or otherwise determined to be correct."
       ::= { rcIpv6RipngExpRouteEntry 9 }

rcIpv6RipngExpRouteNextHopRDI OBJECT-TYPE
        SYNTAX        Unsigned32
        MAX-ACCESS    read-only
        STATUS        current
        DESCRIPTION
                "The Routing Domain ID of the Next Hop.
                 The  semantics of this object are determined by
                 the routing-protocol specified in  the  route's
                 rcIpv6RipngExpRouteProtocol value.
                 When this object is unknown or not relevant its
                 value should be set to zero."
        ::= { rcIpv6RipngExpRouteEntry 10 }

rcIpv6RipngExpRouteMetric OBJECT-TYPE
        SYNTAX        Unsigned32
        MAX-ACCESS    read-only
        STATUS        current
        DESCRIPTION
                "The routing metric for this route. The
                 semantics of this metric are determined by the
                 routing protocol specified in the route's
                 rcIpv6RipngExpRouteProtocol value. In this case,
                 when this is unknown should be set to its maximum
                 value (15)"
        ::= { rcIpv6RipngExpRouteEntry 11 }

rcIpv6RipngExpRouteWeight OBJECT-TYPE
        SYNTAX     Unsigned32
        MAX-ACCESS read-only
        STATUS     current
        DESCRIPTION
                "The system internal weight value for this route.
                The semantics of this value are determined by
                the implementation specific rules. Generally,
                within routes with the same rcIpv6RipngExpRoutePolicy
                value, the lower the weight value the more preferred
                is the route."
        ::= { rcIpv6RipngExpRouteEntry 12 }

rcIpv6RipngExpRouteInfo OBJECT-TYPE
        SYNTAX     OBJECT IDENTIFIER
        MAX-ACCESS read-only
        STATUS     current
        DESCRIPTION
                "A reference to MIB definitions specific to the
                 particular routing protocol which is responsible
                 for this route, as determined by the  value
                 specified  in the route's ipv6RouteProto value.
                 If this information is not present,  its  value
                 should be set to the OBJECT ID { 0 0 },
                 which is a syntactically valid object  identifier,
                 and any implementation conforming to ASN.1
                 and the Basic Encoding Rules must  be  able  to
                 generate and recognize this value."
        ::= { rcIpv6RipngExpRouteEntry 13 }

rcIpv6RipngExpRouteValid OBJECT-TYPE
             SYNTAX     TruthValue
             MAX-ACCESS read-write
             STATUS     current
             DESCRIPTION
                "Setting this object to the value 'false(2)' has
                 the effect of invalidating the corresponding entry
                 in the rcIpv6RipngExpRouteTable object. That is, it
                 effectively disassociates the destination
                 identified with said entry from the route
                 identified with said entry.  It is an
                 implementation-specific matter as to whether the
                 agent removes an invalidated entry from the table.
                 Accordingly, management stations must be prepared
                 to receive tabular information from agents that
                 corresponds to entries not currently in use.
                 Proper interpretation of such entries requires
                 examination of the relevant rcIpv6RipngExpRouteValid
                 object."
             DEFVAL  { true }
             ::= { rcIpv6RipngExpRouteEntry 14 }

rcIpv6RipngExpRoutePref OBJECT-TYPE
             SYNTAX     INTEGER(1..255)
             MAX-ACCESS read-only
             STATUS     current
             DESCRIPTION
                     "Used to indicate the route preference of this
                      entry.  If there are more than one route that can
                      be used to forward IPv6 traffic, the route that has
                      a lower preference will be used instead of a
                      higher preference one. The lower the number,
                      the higher the preference."
             DEFVAL        { 100 }
             ::= { rcIpv6RipngExpRouteEntry 15 }



END
