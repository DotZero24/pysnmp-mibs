BAY-STACK-MIB DEFINITIONS ::= BEGIN

IMPORTS
    MODULE-IDENTITY, OBJECT-TYPE, Integer32, Unsigned32
        FROM SNMPv2-SMI
    TruthValue
        FROM SNMPv2-TC
    bayStackMibs
        FROM SYNOPTICS-ROOT-MIB;

bayStackMib    MODULE-IDENTITY
   LAST-UPDATED "202102090000Z"
   ORGANIZATION "Nortel Networks"
   CONTACT-INFO "Nortel Networks"
   DESCRIPTION
       "General BayStack MIB."

   REVISION "202102090000Z" -- 09 February 2021
   DESCRIPTION "Version 6: Add baystackConfigTcpKeepaliveEnable,
							baystackConfigTcpKeepaliveInterval and
							baystackConfigTcpKeepaliveRetries."

   REVISION "201310110000Z" -- 11 October 2013
   DESCRIPTION
       "Version 5:  Changed the MAX-ACCESS of bayStackUnitConfigIndex to read-only."

   REVISION "201210020000Z" -- 02 October 2012
   DESCRIPTION
       "Version 4:  Added spb value for bayStackUnitConfigRearPortAdminMode and bayStackUnitConfigRearPortOperMode."

   REVISION "200909280000Z" -- 28 September 2009
   DESCRIPTION
       "Version 3:  Added bayStackConfigStackRebootOnFailure and
                          bayStackConfigStackRetryCount."

   REVISION "200709040000Z" -- 04 September 2007
   DESCRIPTION
       "Version 2:  Added per-unit configuration table."

   REVISION "200508220000Z" -- 22 August 2005
   DESCRIPTION
       "Version 1:  Initial version."

   ::= { bayStackMibs 13 }

bayStackObjects OBJECT IDENTIFIER ::= { bayStackMib 1 }

--
-- General Stack configuration group
--

bayStackConfig OBJECT IDENTIFIER ::= { bayStackObjects 1 }

bayStackConfigExpectedStackSize OBJECT-TYPE
    SYNTAX      Integer32 (1..8)
    MAX-ACCESS  read-write
    STATUS      current
    DESCRIPTION
        "The expected stack size.  A unit that expects to be
         standalone would use a value of 1."
    ::= { bayStackConfig 1 }

bayStackConfigStackErrorNotificationInterval OBJECT-TYPE
    SYNTAX      Integer32 (1..65535)
    UNITS       "Seconds"
    MAX-ACCESS  read-write
    STATUS      current
    DESCRIPTION
        "This objects controls the frequency with which
         bsnStackConfigurationError notifications are generated."
    DEFVAL { 60 }
    ::= { bayStackConfig 2 }

bayStackConfigStackErrorNotificationEnabled OBJECT-TYPE
    SYNTAX      TruthValue
    MAX-ACCESS  read-write
    STATUS      current
    DESCRIPTION
        "This objects controls whether bsnStackConfigurationError
         notifications are generated."
    ::= { bayStackConfig 3 }

bayStackConfigStackRebootUnitOnFailure OBJECT-TYPE
    SYNTAX      TruthValue
    MAX-ACCESS  read-write
    STATUS      current
    DESCRIPTION
        "This object controls whether to reboot any unit in a stack whose
         stack ports do not go logically up."
    ::= { bayStackConfig 4 }

bayStackConfigStackRetryCount OBJECT-TYPE
    SYNTAX      Unsigned32 (0..4294967295)
    MAX-ACCESS  read-write
    STATUS      current
    DESCRIPTION
        "Stack retry count."
    ::= { bayStackConfig 5 }


baystackConfigTcpKeepaliveEnable    OBJECT-TYPE
    SYNTAX      TruthValue
    MAX-ACCESS  read-write
    STATUS      current
    DESCRIPTION
        "This object controls whether the tcp keepalive functionality is used."
	DEFVAL		{ false }
    ::= { bayStackConfig 6 }

baystackConfigTcpKeepaliveInterval    OBJECT-TYPE
	SYNTAX        Integer32 (1..600)
	MAX-ACCESS    read-write
	STATUS        current
	DESCRIPTION   "Used to set the interval between subsequent keepalive probes."
	-- DEFVAL       { 5 }
	::= { bayStackConfig 7 }

baystackConfigTcpKeepaliveRetries    OBJECT-TYPE
	SYNTAX        Integer32 (1..50)
	MAX-ACCESS    read-write
	STATUS        current
	DESCRIPTION   "Used to set the number of unacknowledged probes to send before
				   considering the connection dead and closing it."
	-- DEFVAL       { 6 }
	::= { bayStackConfig 8 }

--
-- General Stack Per-Unit Configuration Table
--

bayStackUnitConfigTable OBJECT-TYPE
    SYNTAX SEQUENCE OF BayStackUnitConfigEntry
    MAX-ACCESS not-accessible
    STATUS current
    DESCRIPTION
        "This table contains per-unit configuration data for a stack."
    ::= { bayStackObjects 2 }

bayStackUnitConfigEntry OBJECT-TYPE
    SYNTAX BayStackUnitConfigEntry
    MAX-ACCESS not-accessible
    STATUS current
    DESCRIPTION
        "An entry of configuration data for a stacked unit."
    INDEX { bayStackUnitConfigIndex }
    ::= { bayStackUnitConfigTable 1 }

BayStackUnitConfigEntry ::=
    SEQUENCE {
        bayStackUnitConfigIndex              Integer32,
        bayStackUnitConfigRearPortAdminMode  INTEGER,
        bayStackUnitConfigRearPortOperMode   INTEGER
    }

bayStackUnitConfigIndex OBJECT-TYPE
    SYNTAX      Integer32 (1..8)
    MAX-ACCESS  read-only
    STATUS      current
    DESCRIPTION
        "The unit number of an entry."
    ::= { bayStackUnitConfigEntry 1 }

bayStackUnitConfigRearPortAdminMode OBJECT-TYPE
    SYNTAX      INTEGER {
                            standalone(1),
                            stacking(2),
                            spb(3)
                        }
    MAX-ACCESS  read-write
    STATUS      current
    DESCRIPTION
        "The current administrative rear-port mode for this unit.  This
         value will be applied at the next stack re-boot if it is different
         from the current operational value. Supported values are: standalone
         (rear-port mode is enabled normal), stacking (rear-port mode is disabled)
         and spb(rear-port mode is enabled with loopback port reserved)."
    ::= { bayStackUnitConfigEntry 2 }

bayStackUnitConfigRearPortOperMode OBJECT-TYPE
    SYNTAX      INTEGER {
                            standalone(1),
                            stacking(2),
                            spb(3)
                        }
    MAX-ACCESS  read-only
    STATUS      current
    DESCRIPTION
        "The current operational rear-port mode for this unit. Supported values are:
         standalone (operational rear-port mode is enabled normal), stacking (operational
         rear-port mode is disabled) and spb(operational rear-port mode is enabled
         with loopback port reserved)."
    ::= { bayStackUnitConfigEntry 3 }

END
