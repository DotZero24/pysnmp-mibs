NORTEL-OME40G-MIB DEFINITIONS ::= BEGIN

IMPORTS
       opterametro       FROM NORTEL-OPTICAL-GENERIC-MIB

       MODULE-IDENTITY,
       OBJECT-IDENTITY   FROM SNMPv2-SMI;

nnOme40G MODULE-IDENTITY
        LAST-UPDATED "200805010000Z"
        ORGANIZATION "Nortel"
        CONTACT-INFO
           "   7035 Ridge Road
               Hanover, Maryland 21076
               United States
               Toll-free: +1-800-921-1144
               Phone: +1-410-694-5700
               Fax: +1-410-694-5750
               www.ciena.com "
        DESCRIPTION
              "Optical Multiservice Edge (OME)
               - This Module will be used to identify the top level of
	       the Nortel OME6500 40G MIBS"

        --Revision history
        REVISION "200702020000Z"
        DESCRIPTION "Initial Version - created for OME6500 REL 4.0"

	REVISION "200802070000Z"
        DESCRIPTION "Updating Formatting and added ome6500
	OBJECT IDENTIFIER for OME6500 REL 5.1"

	REVISION "200805010000Z"
        DESCRIPTION "nnOme40G MODULE-IDENTITY's DESCRIPTION is updated."
        ::= { ome6500 3 }

ome6500 OBJECT IDENTIFIER ::= { opterametro 11 }

END
