S5-ETH-MULTISEG-TOPOLOGY-MIB DEFINITIONS ::= BEGIN

IMPORTS
        MODULE-IDENTITY, OBJECT-TYPE, IpAddress, TimeTicks, Integer32
            FROM SNMPv2-SMI
      MacAddress
            FROM SNMPv2-TC
	InterfaceIndex
            FROM IF-MIB
        SnpxChassisType, SnpxBackplaneType
		FROM SYNOPTICS-ROOT-MIB
	s5EnMsTop
		FROM S5-ROOT-MIB;

s5EthMultisegTopologyMib MODULE-IDENTITY
       LAST-UPDATED    "200908180000Z"
       ORGANIZATION    "Nortel Networks"
       CONTACT-INFO    "Nortel Networks"
       DESCRIPTION
           "5000 Ethernet Multi-segment MIB

            Copyright 1993-2004 Nortel Networks, Inc.
            All rights reserved.
            This Nortel Networks SNMP Management Information Base Specification
            (Specification) embodies Nortel Networks' confidential and
            proprietary intellectual property. Nortel Networks retains all
            title and ownership in the Specification, including any
            revisions.

            This Specification is supplied 'AS IS,' and Nortel Networks makes
            no warranty, either express or implied, as to the use,
            operation, condition, or performance of the Specification."

       REVISION "200908180000Z" -- 18 August 2009
       DESCRIPTION "Version 109:  added s5EnMsTopPortTable"

       REVISION "200609130000Z" -- 13 Sept 2006
       DESCRIPTION "Version 108:  Import MacAddress from SNMPv2-TC, Integer32 from
                                  SNMPv2-SMI"

       REVISION "200609120000Z" -- 12 Sept 2006
       DESCRIPTION "Version 107:  Import MacAddress from SNMPv2-SMI"

       REVISION "200407200000Z" -- 20 July 2004
       DESCRIPTION "Version 106:  Conversion to SMIv2"

       ::= { s5EnMsTop 0 }

-- Groups

s5EnMsTopInfo		OBJECT IDENTIFIER ::= { s5EnMsTop 1 }

s5EnMsTopNmm		OBJECT IDENTIFIER ::= { s5EnMsTop 2 }

s5EnMsTopBdg		OBJECT IDENTIFIER ::= { s5EnMsTop 3 }

s5EnMsTopSrcMac		OBJECT IDENTIFIER ::= { s5EnMsTop 4 }

s5EnMsTopPort		OBJECT IDENTIFIER ::= { s5EnMsTop 5 }

-- SECTION 2: MIB Objects

-- Topology Status and Configuration Information

s5EnMsTopIpAddr OBJECT-TYPE
	SYNTAX	IpAddress
	MAX-ACCESS	read-only
	STATUS	current
	DESCRIPTION
		"An IP address of the agent. This is used to fill
		in the IP address field of transmitted SONMP packets.
		The agent should be reachable through this IP address."
	::= { s5EnMsTopInfo 1 }

s5EnMsTopStatus OBJECT-TYPE
	SYNTAX	INTEGER {
		  topOn(1),
		  topOff(2)
		}
	MAX-ACCESS	read-write
	STATUS	current
	DESCRIPTION
		"Indicates if the agent is participating in
		multi-segment topology. The values are:
		  topOn(1)....topology is on
		  topOff(2)...topology is off
		When the value is topOff(2) the status of
		topology table entries is undefined.  However, the
		agent should make its best attempt when the value is
		changed to topOff(2) to remove all existing instances
		of topology MIB objects. The agent must save the
		setting of this object in nonvolatile memory (i.e.,
		save across reboots)."
	DEFVAL	{ topOn }
	::= { s5EnMsTopInfo 2 }

s5EnMsTopNmmLstChg OBJECT-TYPE
	SYNTAX	TimeTicks
	MAX-ACCESS	read-only
	STATUS	current
	DESCRIPTION
		"The value of sysUpTime the last time an entry in the
		NMM topology table was added, deleted, or modified.  If
		the NMM topology table has not changed since cold/warm
		start of the agent, then the value is zero."
	::= { s5EnMsTopInfo 3 }

s5EnMsTopBdgLstChg OBJECT-TYPE
	SYNTAX	TimeTicks
	MAX-ACCESS	read-only
	STATUS	deprecated
	DESCRIPTION
		"The value of sysUpTime the last time an entry in the
		bridge topology table was added, deleted, or modified.
		If the bridge topology table has not changed since
		cold/warm start of the agent, then the value is zero."
	::= { s5EnMsTopInfo 4 }

s5EnMsTopNmmMaxNum OBJECT-TYPE
	SYNTAX	INTEGER (0..65535)
	MAX-ACCESS	read-only
	STATUS	current
	DESCRIPTION
		"The maximum number of entries in the NMM topology
		table."
	::= { s5EnMsTopInfo 5 }

s5EnMsTopNmmCurNum OBJECT-TYPE
	SYNTAX	INTEGER (0..65535)
	MAX-ACCESS	read-only
	STATUS	current
	DESCRIPTION
		"The current number of entries in the NMM topology
		table."
	::= { s5EnMsTopInfo 6 }

s5EnMsTopBdgMaxNum OBJECT-TYPE
	SYNTAX	INTEGER (0..65535)
	MAX-ACCESS	read-only
	STATUS	deprecated
	DESCRIPTION
		"The maximum number of entries in the bridge topology
		table."
	::= { s5EnMsTopInfo 7 }

s5EnMsTopBdgCurNum OBJECT-TYPE
	SYNTAX	INTEGER (0..65535)
	MAX-ACCESS	read-only
	STATUS	deprecated
	DESCRIPTION
		"The current number of entries in the bridge topology
		table."
	::= { s5EnMsTopInfo 8 }

-- Network Management Module (NMM) Topology Table

s5EnMsTopNmmTable OBJECT-TYPE
	SYNTAX	SEQUENCE OF S5EnMsTopNmmEntry
	MAX-ACCESS	not-accessible
	STATUS	current
	DESCRIPTION
		"A table of topology information from each topology
		agent that sends out NMM topology messages, and that
		has been heard by the reporting topology agent.  The
		number of entries is determined by the number of
		distinct topology messages received.  A topology
		message is identified by a combination of the IP
		address and segment-identifier contained in the
		message, and the slot-port on which it is received.
		Entries in the table are created by reception of a
		'new' NMM topology message.  An entry is removed from
		the table after no messages are received from the
		corresponding topology agent in the required time
		interval.

		NOTE: there is an entry for the reporting agent with
		the values of slot and port set to zero."
	::= { s5EnMsTopNmm 1 }

s5EnMsTopNmmEntry OBJECT-TYPE
	SYNTAX	S5EnMsTopNmmEntry
	MAX-ACCESS	not-accessible
	STATUS	current
	DESCRIPTION
		"A row in the NMM topology table. Entries in the table
		can not be created or deleted via SNMP."
	INDEX	{ s5EnMsTopNmmSlot,
		  s5EnMsTopNmmPort,
		  s5EnMsTopNmmIpAddr,
		  s5EnMsTopNmmSegId }
	::= { s5EnMsTopNmmTable 1 }

S5EnMsTopNmmEntry ::= SEQUENCE {
	s5EnMsTopNmmSlot INTEGER,
	s5EnMsTopNmmPort INTEGER,
	s5EnMsTopNmmIpAddr IpAddress,
	s5EnMsTopNmmSegId INTEGER,
	s5EnMsTopNmmMacAddr  MacAddress,
	s5EnMsTopNmmChassisType SnpxChassisType,
	s5EnMsTopNmmBkplType SnpxBackplaneType,
	s5EnMsTopNmmLocalSeg INTEGER,
	s5EnMsTopNmmCurState INTEGER
	}

s5EnMsTopNmmSlot OBJECT-TYPE
	SYNTAX	INTEGER (0..255)
	MAX-ACCESS	read-only
	STATUS	current
	DESCRIPTION
		"The slot on which the topology message
		was received.

		NOTE: There is an artificial 'row' for the reporting
		agent with slot and port equal to zero.

		NOTE: Non-modular devices that do not have multiple
		slots should set this value to 1."
	::= { s5EnMsTopNmmEntry 1 }

s5EnMsTopNmmPort OBJECT-TYPE
	SYNTAX	INTEGER (0..255)
	MAX-ACCESS	read-only
	STATUS	current
	DESCRIPTION
		"The port on which the topology message
		was received.

		NOTE: there is an artificial 'row' for the reporting
		agent with slot and port equal to zero."
	::= { s5EnMsTopNmmEntry 2 }

s5EnMsTopNmmIpAddr OBJECT-TYPE
	SYNTAX	IpAddress
	MAX-ACCESS	read-only
	STATUS	current
	DESCRIPTION
		"The IP address of the sender of the topology message."
	::= { s5EnMsTopNmmEntry 3 }

s5EnMsTopNmmSegId OBJECT-TYPE
	SYNTAX	INTEGER (0..'FFFFFF'H)
	MAX-ACCESS	read-only
	STATUS	current
	DESCRIPTION
		"The 'segment identifier' of the segment from which
		the remote agent sent the topology message.  The value
		is extracted from the received topology message.
		Different devices may use different methods for
		representing the segment identifier.  For example,
		system 5000 NMMs that run multi-segment autotopology use
		the SrcIndx of the segment as the segment identifier;
                switches use a computed a value equal to '(256 * s) + p'
                where 's' is the board, card or slot number and 'p' is
                the port number on and as seen by the switch sending the
                topology message;
		system 3000 NMMs use the lower three bytes of the MAC
		address of the NMM as the segment identifier.  In any
		case, the 'segment identifier' uniquely identifies the
		network segment in the remote device from which
		the topology message was sent."
	::= { s5EnMsTopNmmEntry 4 }

s5EnMsTopNmmMacAddr OBJECT-TYPE
	SYNTAX	MacAddress
	MAX-ACCESS	read-only
	STATUS	current
	DESCRIPTION
		"The MAC address of the sender of the topology message."
	::= { s5EnMsTopNmmEntry 5 }

s5EnMsTopNmmChassisType OBJECT-TYPE
	SYNTAX	SnpxChassisType
	MAX-ACCESS	read-only
	STATUS	current
	DESCRIPTION
		"The chassis type of the device that sent the topology
		message."
	::= { s5EnMsTopNmmEntry 6 }

s5EnMsTopNmmBkplType OBJECT-TYPE
	SYNTAX	SnpxBackplaneType
	MAX-ACCESS	read-only
	STATUS	current
	DESCRIPTION
		"The backplane type of the device that sent the
		topology message."
	::= { s5EnMsTopNmmEntry 7 }

s5EnMsTopNmmLocalSeg OBJECT-TYPE
	SYNTAX	INTEGER {
		true(1),
		false(2)
		}
	MAX-ACCESS	read-only
	STATUS	current
	DESCRIPTION
		"Indicates if the sender of the topology message is on
		the same Ethernet segment (i.e., NOT across a bridge)
		as the reporting agent."
	::= { s5EnMsTopNmmEntry 8 }

s5EnMsTopNmmCurState OBJECT-TYPE
	SYNTAX	INTEGER {
		topChanged(1),
		heartbeat(2),
		new(3)
		}
	MAX-ACCESS	read-only
	STATUS	current
	DESCRIPTION
		"The current state of sender of the
		topology message. The values are:
		  topChanged(1)...topology information has
		                    recently changed
		  heartbeat(2)....topology information unchanged
		  new(3)..........sending agent is in new state."
	::= { s5EnMsTopNmmEntry 9 }

-- Encoded Octet Strings for NMM Topology Table

s5EnMsTopNmmEosSize OBJECT-TYPE
	SYNTAX	INTEGER (0..1440)
	MAX-ACCESS	read-only
	STATUS	current
	DESCRIPTION
		"The current size of a 'row' in the table
		s5EnMsTopNmmEosTable.  This allows applications
		to be able to break apart 'rows' in the table."
	::= { s5EnMsTopNmm 2 }

s5EnMsTopNmmEosTable OBJECT-TYPE
	SYNTAX	SEQUENCE OF S5EnMsTopNmmEosEntry
	MAX-ACCESS	not-accessible
	STATUS	current
	DESCRIPTION
		"A table of encoded octet strings of
		entries in table s5EnMsTopNmmTable.
		The number of entries is determined by
		packing of 'rows' from s5EnMsTopNmmTable."
	::= { s5EnMsTopNmm 3 }


-- s5EnMsTopNmmEnhancedTable is enhancement version
-- of s5EnMsTopNmmTable to support the sub-port
s5EnMsTopNmmEnhancedTable OBJECT-TYPE
	SYNTAX	SEQUENCE OF S5EnMsTopNmmEnhancedEntry
	ACCESS	not-accessible
	STATUS	mandatory
	DESCRIPTION
		"This table is enhanced version of the s5EnMsTopNmmTable.
                It is introduce to handle the sub-port format for channelized capable
		Interface.
		A table of topology information from each topology
		agent that sends out NMM topology messages, and that
		has been heard by the reporting topology agent.  The
		number of entries is determined by the number of
		distinct topology messages received.  A topology
		message is identified by a combination of the IP
		address and segment-identifier contained in the
		message, and the slot-port or slot-port-subport on which it is received.
		Entries in the table are created by reception of a
		'new' NMM topology message.  An entry is removed from
		the table after no messages are received from the
		corresponding topology agent in the required time
		interval.

		NOTE: there is an entry for the reporting agent with
		the values of slot and port set to zero."
	::= { s5EnMsTopNmm 4 }

s5EnMsTopNmmEnhancedEntry OBJECT-TYPE
	SYNTAX	 S5EnMsTopNmmEnhancedEntry
	ACCESS	not-accessible
	STATUS	mandatory
	DESCRIPTION
		"A row in the NMM topology table. Entries in the table
		can not be created or deleted via SNMP."
	INDEX	{ s5EnMsTopNmmEnhancedSlot,
		  s5EnMsTopNmmEnhancedPort,
		  s5EnMsTopNmmEnhancedSubPort,
		  s5EnMsTopNmmEnhancedIpAddr,
		  s5EnMsTopNmmEnhancedSegId }
	::= { s5EnMsTopNmmEnhancedTable 1 }

S5EnMsTopNmmEnhancedEntry ::= SEQUENCE {
	s5EnMsTopNmmEnhancedSlot INTEGER,
	s5EnMsTopNmmEnhancedPort INTEGER,
        s5EnMsTopNmmEnhancedSubPort INTEGER,
	s5EnMsTopNmmEnhancedIpAddr IpAddress,
	s5EnMsTopNmmEnhancedSegId INTEGER,
	s5EnMsTopNmmEnhancedMacAddr  MacAddress,
	s5EnMsTopNmmEnhancedChassisType SnpxChassisType,
	s5EnMsTopNmmEnhancedBkplType SnpxBackplaneType,
	s5EnMsTopNmmEnhancedLocalSeg INTEGER,
	s5EnMsTopNmmEnhancedCurState INTEGER
	}

s5EnMsTopNmmEnhancedSlot OBJECT-TYPE
	SYNTAX	INTEGER (0..255)
	ACCESS	not-accessible
	STATUS	mandatory
	DESCRIPTION
		"The slot on which the topology message
		was received.

		NOTE: There is an artificial 'row' for the reporting
		agent with slot and port equal to zero.

		NOTE: Non-modular devices that do not have multiple
		slots should set this value to 1."
	::= { s5EnMsTopNmmEnhancedEntry 1 }

s5EnMsTopNmmEnhancedPort OBJECT-TYPE
	SYNTAX	INTEGER (0..255)
	ACCESS	not-accessible
	STATUS	mandatory
	DESCRIPTION
		"The port on which the topology message
		was received.

		NOTE: there is an artificial 'row' for the reporting
		agent with slot and port equal to zero."
	::= { s5EnMsTopNmmEnhancedEntry 2 }

s5EnMsTopNmmEnhancedSubPort OBJECT-TYPE
	SYNTAX	INTEGER (0..10)
	ACCESS	not-accessible
	STATUS	mandatory
	DESCRIPTION
		"The sub-port on which the topology message
		was received.  It is sub-port for the channelized port.

		If the value is  0, it indicates that there is no sub-port in
		this interface and the interface port display format is 'slot/port'.
		If the value is not 0, it indicates that the interface port display
		Format is 'slot/port/sub-port'."
	::= { s5EnMsTopNmmEnhancedEntry 3 }

s5EnMsTopNmmEnhancedIpAddr OBJECT-TYPE
	SYNTAX	IpAddress
	ACCESS	not-accessible
	STATUS	mandatory
	DESCRIPTION
		"The IP address of the sender of the topology message."
	::= { s5EnMsTopNmmEnhancedEntry 4 }

s5EnMsTopNmmEnhancedSegId OBJECT-TYPE
	SYNTAX	INTEGER (0..'FFFFFF'H)
	ACCESS	not-accessible
	STATUS	mandatory
	DESCRIPTION
		"The 'segment identifier' of the segment from which
		the remote agent sent the topology message.  The value
		is extracted from the received topology message.
		Different devices may use different methods for
		representing the segment identifier.  For example,
		system 5000 NMMs that run multi-segment autotopology use
		the SrcIndx of the segment as the segment identifier;
                switches use a computed a value equal to 'subport +((256 * s) + p)'
                where 's' is the board, card or slot number and 'p' is
                the port number on and as seen by the switch sending the
                topology message;
		system 3000 NMMs use the lower three bytes of the MAC
		address of the NMM as the segment identifier.  In any
		case, the 'segment identifier' uniquely identifies the
		network segment in the remote device from which
		the topology message was sent.
		NOTE: only the interface has subport, the value will be set, otherwise,
		it will be to 0"
	::= { s5EnMsTopNmmEnhancedEntry 5 }

s5EnMsTopNmmEnhancedMacAddr OBJECT-TYPE
	SYNTAX	MacAddress
	ACCESS	read-only
	STATUS	mandatory
	DESCRIPTION
		"The MAC address of the sender of the topology message."
	::= { s5EnMsTopNmmEnhancedEntry 6 }

s5EnMsTopNmmEnhancedChassisType OBJECT-TYPE
	SYNTAX	SnpxChassisType
	ACCESS	read-only
	STATUS	mandatory
	DESCRIPTION
		"The chassis type of the device that sent the topology
		message."
	::= { s5EnMsTopNmmEnhancedEntry 7 }

s5EnMsTopNmmEnhancedBkplType OBJECT-TYPE
	SYNTAX	SnpxBackplaneType
	ACCESS	read-only
	STATUS	mandatory
	DESCRIPTION
		"The backplane type of the device that sent the
		topology message."
	::= { s5EnMsTopNmmEnhancedEntry 8 }

s5EnMsTopNmmEnhancedLocalSeg OBJECT-TYPE
	SYNTAX	INTEGER {
		true(1),
		false(2)
		}
	ACCESS	read-only
	STATUS	mandatory
	DESCRIPTION
		"Indicates if the sender of the topology message is on
		the same Ethernet segment (i.e., NOT across a bridge)
		as the reporting agent."
	::= { s5EnMsTopNmmEnhancedEntry 9 }

s5EnMsTopNmmEnhancedCurState OBJECT-TYPE
	SYNTAX	INTEGER {
		topChanged(1),
		heartbeat(2),
		new(3)
		}
	ACCESS	read-only
	STATUS	mandatory
	DESCRIPTION
	    "The current state of sender of the
	    topology message. The values are:
	    topChanged(1)...topology information has
	    recently changed
	    heartbeat(2)....topology information unchanged
	    new(3)..........sending agent is in new state."
	::= { s5EnMsTopNmmEnhancedEntry 10 }

-- s5EnMsTopNmEosmEnhancedTable is enhancement version
-- of s5EnMsTopNmmEosTable to support the sub-port

s5EnMsTopNmmEnhancedEosTable OBJECT-TYPE
	SYNTAX	SEQUENCE OF S5EnMsTopNmmEnhancedEosEntry
	ACCESS	not-accessible
	STATUS	mandatory
	DESCRIPTION
		"A table of encoded octet strings of
		entries in table s5EnMsTopNmmEnhancedTable.
		The number of entries is determined by
		packing of 'rows' from s5EnMsTopNmmEnhancedTable."
	::= { s5EnMsTopNmm 5 }

s5EnMsTopNmmEnhancedEosEntry OBJECT-TYPE
	SYNTAX	S5EnMsTopNmmEnhancedEosEntry
	ACCESS	not-accessible
	STATUS	mandatory
	DESCRIPTION
		"A row in the table of encoded octet
		strings for table s5EnMsTopNmmEnhancedTable.
		Instance returned in Response PDU:
		  On GETs: instance specified is the
		           instance returned.
		  On GET-NEXTs: instance returned is the
		                instance of the last record
		                contained in the octet string.

		Entries in the table can not be created
		or deleted via SNMP."
	INDEX	{ s5EnMsTopNmmEnhancedSlot,
		  s5EnMsTopNmmEnhancedPort,
		  s5EnMsTopNmmEnhancedSubPort,
		  s5EnMsTopNmmEnhancedIpAddr,
		  s5EnMsTopNmmEnhancedSegId }
	::= { s5EnMsTopNmmEnhancedEosTable 1 }

S5EnMsTopNmmEnhancedEosEntry ::= SEQUENCE {
	s5EnMsTopNmmEnhancedEos OCTET STRING
	}

s5EnMsTopNmmEnhancedEos OBJECT-TYPE
	SYNTAX	OCTET STRING (SIZE(0..1400))
	ACCESS	read-only
	STATUS	mandatory
	DESCRIPTION
		"An encoded octet string. On reads it contains
		an integral number of 'rows' from table
		s5EnMsTopNmmTable. All 'rows' are the same size
		which is defined by object s5EnMsTopNmmEosSize."
	::= { s5EnMsTopNmmEnhancedEosEntry 1 }

s5EnMsTopNmmEosEntry OBJECT-TYPE
	SYNTAX	S5EnMsTopNmmEosEntry
	MAX-ACCESS	not-accessible
	STATUS	current
	DESCRIPTION
		"A row in the table of encoded octet
		strings for table s5EnMsTopNmmTable.
		Instance returned in Response PDU:
		  On GETs: instance specified is the
		           instance returned.
		  On GET-NEXTs: instance returned is the
		                instance of the last record
		                contained in the octet string.

		Entries in the table can not be created
		or deleted via SNMP."
	INDEX	{ s5EnMsTopNmmSlot,
		  s5EnMsTopNmmPort,
		  s5EnMsTopNmmIpAddr,
		  s5EnMsTopNmmSegId }
	::= { s5EnMsTopNmmEosTable 1 }

S5EnMsTopNmmEosEntry ::= SEQUENCE {
	s5EnMsTopNmmEos OCTET STRING
	}

s5EnMsTopNmmEos OBJECT-TYPE
	SYNTAX	OCTET STRING (SIZE(0..1400))
	MAX-ACCESS	read-only
	STATUS	current
	DESCRIPTION
		"An encoded octet string. On reads it contains
		an integral number of 'rows' from table
		s5EnMsTopNmmTable. All 'rows' are the same size
		which is defined by object s5EnMsTopNmmEosSize."
	::= { s5EnMsTopNmmEosEntry 1 }

-- Bridge Topology Table

s5EnMsTopBdgTable OBJECT-TYPE
	SYNTAX	SEQUENCE OF S5EnMsTopBdgEntry
	MAX-ACCESS	not-accessible
	STATUS	deprecated
	DESCRIPTION
		"A table of topology information from each Bridge in
		the network that is sending bridge topology messages
		that have been heard by the reporting agent.  The
		number of entries is determined by the number of
		detected (and active) bridges.  Entries in the table
		are created by reception of a topology message from a
		'new' bridge.  An entry is removed from the table
		after no messages are received from the corresponding
		bridge in the required time interval."
	::= { s5EnMsTopBdg 1 }

s5EnMsTopBdgEntry OBJECT-TYPE
	SYNTAX	S5EnMsTopBdgEntry
	MAX-ACCESS	not-accessible
	STATUS	deprecated
	DESCRIPTION
		"A row in the bridge topology table.  Entries in the
		table can not be created or deleted via SNMP."
	INDEX	{ s5EnMsTopBdgSlotNum,
		  s5EnMsTopBdgPortNum,
		  s5EnMsTopBdgIpAddr }
	::= { s5EnMsTopBdgTable 1 }

S5EnMsTopBdgEntry ::= SEQUENCE {
	s5EnMsTopBdgSlotNum INTEGER,
	s5EnMsTopBdgPortNum INTEGER,
	s5EnMsTopBdgIpAddr IpAddress,
	s5EnMsTopBdgNumber INTEGER,
	s5EnMsTopBdgMacAddr MacAddress,
	s5EnMsTopBdgType INTEGER,
	s5EnMsTopBdgStatus INTEGER,
	s5EnMsTopBdgNumPorts Integer32,
	s5EnMsTopBdgHelloPortNum INTEGER,
	s5EnMsTopBdgHelloPortType INTEGER,
	s5EnMsTopBdgHelloPortStatus INTEGER,
	s5EnMsTopBdgCompBdgMac1 MacAddress,
	s5EnMsTopBdgCompBdgMac2 MacAddress
	}

s5EnMsTopBdgSlotNum OBJECT-TYPE
	SYNTAX	INTEGER (0..255)
	MAX-ACCESS	read-only
	STATUS	deprecated
	DESCRIPTION
		"The slot on which the topology message was
		received.

		NOTE: Non-modular devices that do not have multiple
		slots should set this value to 1."
	::= { s5EnMsTopBdgEntry 1 }

s5EnMsTopBdgPortNum OBJECT-TYPE
	SYNTAX	INTEGER (0..255)
	MAX-ACCESS	read-only
	STATUS	deprecated
	DESCRIPTION
		"The port on which the topology message was received."
	::= { s5EnMsTopBdgEntry 2 }

s5EnMsTopBdgIpAddr OBJECT-TYPE
	SYNTAX	IpAddress
	MAX-ACCESS	read-only
	STATUS	deprecated
	DESCRIPTION
		"The IP address of the bridge that sent the
		topology message."
	::= { s5EnMsTopBdgEntry 3 }

s5EnMsTopBdgNumber OBJECT-TYPE
	SYNTAX	INTEGER (0..65535)
	MAX-ACCESS	read-only
	STATUS	deprecated
	DESCRIPTION
		"The 'Bridge Number' of the bridge that sent
		the topology message.  This is the IEEE 802.1
		bridge number."
	::= { s5EnMsTopBdgEntry 4 }

s5EnMsTopBdgMacAddr OBJECT-TYPE
	SYNTAX	MacAddress
	MAX-ACCESS	read-only
	STATUS	deprecated
	DESCRIPTION
		"The MAC Address of the bridge that sent the
		topology message."
	::= { s5EnMsTopBdgEntry 5 }

s5EnMsTopBdgType OBJECT-TYPE
	SYNTAX	INTEGER {
		other(1),
		localSyn(2),
		remoteSyn(3),
		kalpana(4)
		}
	MAX-ACCESS	read-only
	STATUS	deprecated
	DESCRIPTION
		"The 'kind of bridge' that sent the topology
		message. The values are:
		  other(1).....unknown or other type
		  locSyn(2)....local SynOptics bridge
		  remSyn(3)....remote SynOptics bridge
		  kalpana(4)...Kalpana bridge(switch)
		"
	::= { s5EnMsTopBdgEntry 6 }

s5EnMsTopBdgNumPorts OBJECT-TYPE
	SYNTAX	Integer32
	MAX-ACCESS	read-only
	STATUS	deprecated
	DESCRIPTION
		"The number of ports on the bridge."
	::= { s5EnMsTopBdgEntry 7 }

s5EnMsTopBdgStatus OBJECT-TYPE
	SYNTAX	INTEGER {
		other(1),
		active(2),
		standby(3)
		}
	MAX-ACCESS	read-only
	STATUS	deprecated
	DESCRIPTION
		"The current operational status from the bridge
		that sent the topology message.  The values are:
		  other(1).....unknown or other
		  active(2)....bridge is active
		  standby(3)...bridge is in standby

		A value of standby(3) means that at least ONE port
		is in standby mode.  A value of active(2) means NO
		port is in standby mode."
	::= { s5EnMsTopBdgEntry 8 }

s5EnMsTopBdgHelloPortNum OBJECT-TYPE
	SYNTAX	INTEGER (0..255)
	MAX-ACCESS	read-only
	STATUS	deprecated
	DESCRIPTION
		"The port number used by the bridge to
		send the topology message.  This port may
		or may not be in standby mode."
	::= { s5EnMsTopBdgEntry 9 }

s5EnMsTopBdgHelloPortType OBJECT-TYPE
	SYNTAX	INTEGER {
		other(1),
		eth(2),
		tok4(3),
		tok16(4),
		fddi(5),
		t1(6)
		}
	MAX-ACCESS	read-only
	STATUS	deprecated
	DESCRIPTION
		"The type of the port used by the bridge to
		send the topology message.  The values are:
		  other(1)...other or unknown type
		  eth(2).....ethernet
		  tok4(3)....4 Mbit token ring
		  tok16(4)...16 Mbit token ring
		  fddi(5)....fddi
		  t1(6)......t1

		Note: These enumerations were done for
		'completeness'. No other value than eth(2)
		should ever be received by an ethernet agent."
	::= { s5EnMsTopBdgEntry 10 }

s5EnMsTopBdgHelloPortStatus OBJECT-TYPE
	SYNTAX	INTEGER {
		other(1),
		active(2),
		standby(3)
		}
	MAX-ACCESS	read-only
	STATUS	deprecated
	DESCRIPTION
		"The status of the port used by the bridge
		to send the topology message. The values are:
		  other(1).....unknown or other
		  active(2)....port is active
		  standby(3)...port is in standby"
	::= { s5EnMsTopBdgEntry 11 }

s5EnMsTopBdgCompBdgMac1 OBJECT-TYPE
	SYNTAX	MacAddress
	MAX-ACCESS	read-only
	STATUS	deprecated
	DESCRIPTION
		"The first MAC address of a companion bridge
		of the bridge that sent the topology message.
		The value is 00:00:00:00:00:00 for local
		bridges (since there is no companion bridge)
		and also when the companion MAC address
		is unknown for remote bridges."
	::= { s5EnMsTopBdgEntry 12 }

s5EnMsTopBdgCompBdgMac2 OBJECT-TYPE
	SYNTAX	MacAddress
	MAX-ACCESS	read-only
	STATUS	deprecated
	DESCRIPTION
		"The second MAC address of a companion bridge
		of the bridge that sent the topology message.
		The value is 00:00:00:00:00:00 for local
		bridges (since there is no companion bridge)
		and also when the companion MAC address
		is unknown for remote bridges."
	::= { s5EnMsTopBdgEntry 13 }

-- Encoded Octet Strings for Bridge Topology Table

s5EnMsTopBdgEosSize OBJECT-TYPE
	SYNTAX	INTEGER (0..1440)
	MAX-ACCESS	read-only
	STATUS	deprecated
	DESCRIPTION
		"The current size of a 'row' in the table
		s5EnMsTopBdgEosTable.  This allows applications
		to be able to break apart 'rows' in the table."
	::= { s5EnMsTopBdg 2 }

s5EnMsTopBdgEosTable OBJECT-TYPE
	SYNTAX	SEQUENCE OF S5EnMsTopBdgEosEntry
	MAX-ACCESS	not-accessible
	STATUS	deprecated
	DESCRIPTION
		"A table of encoded octet strings of
		entries in table s5EnMsTopBdgTable.
		The number of entries is determined by
		packing of 'rows' from s5EnMsTopBdgTable."
	::= { s5EnMsTopBdg 3 }

s5EnMsTopBdgEosEntry OBJECT-TYPE
	SYNTAX	S5EnMsTopBdgEosEntry
	MAX-ACCESS	not-accessible
	STATUS	deprecated
	DESCRIPTION
		"A row in the table of encoded octet
		strings for table s5EnMsTopBdgTable.
		Instance returned in Response PDU:
		  On GETs: instance specified is the
		             instance returned.
		  On GET-NEXTs: instance returned is the
		                  instance of the last record
		                  contained in the octet string.

		Entries in the table can not be created
		or deleted via SNMP."
	INDEX	{ s5EnMsTopBdgSlotNum,
		  s5EnMsTopBdgPortNum,
		  s5EnMsTopBdgIpAddr }
	::= { s5EnMsTopBdgEosTable 1 }

S5EnMsTopBdgEosEntry ::= SEQUENCE {
	s5EnMsTopBdgEos OCTET STRING
	}

s5EnMsTopBdgEos OBJECT-TYPE
	SYNTAX	OCTET STRING (SIZE(0..1400))
	MAX-ACCESS	read-only
	STATUS	deprecated
	DESCRIPTION
		"An encoded octet string. On reads it contains
		an integral number of 'rows' from table
		s5EnMsTopBdgTable.  All 'rows' are the same size
		which is defined by object s5EnMsTopBdgEosSize."
	::= { s5EnMsTopBdgEosEntry 1 }

-- MAC Address-to-Segment Mapping Table

-- Implementation of this group is optional. It is supported by those
-- devices that use different source MAC addresses to transmit
-- topology messages on different segments.

s5EnMsTopSrcMacAddrTable OBJECT-TYPE
	SYNTAX	SEQUENCE OF S5EnMsTopSrcMacAddrEntry
	MAX-ACCESS	not-accessible
	STATUS	deprecated
	DESCRIPTION
		"A table describing the source MAC addresses that the
		agent uses to transmit topology messages on different
		segments in the device.  The MAC addresses are
		preallocated and remain unchanged for the agent.
		However, the mapping between a MAC address and segment
		may change, since it can depend on the current
		physical and/or logical configuration of the device.

		Implementation of this group is required for those
		devices that use different source MAC addresses to
		transmit topology messages on different segments.
		Implementation of this group is optional otherwise."
	::= { s5EnMsTopSrcMac 1 }

s5EnMsTopSrcMacAddrEntry OBJECT-TYPE
	SYNTAX	S5EnMsTopSrcMacAddrEntry
	MAX-ACCESS	not-accessible
	STATUS	deprecated
	DESCRIPTION
		"A row in the table of MAC address-to-segment mappings.
		Entries in the table can not be created or deleted
		via SNMP."
	INDEX	{ s5EnMsTopSrcMacAddr }
	::= { s5EnMsTopSrcMacAddrTable 1 }

S5EnMsTopSrcMacAddrEntry ::= SEQUENCE {
	s5EnMsTopSrcMacAddr   MacAddress,
	s5EnMsTopSrcMacSegId  INTEGER
	}

s5EnMsTopSrcMacAddr OBJECT-TYPE
	SYNTAX	MacAddress
	MAX-ACCESS	read-only
	STATUS	deprecated
	DESCRIPTION
		"The MAC address used to transmit topology messages."
	::= { s5EnMsTopSrcMacAddrEntry 1 }

s5EnMsTopSrcMacSegId OBJECT-TYPE
	SYNTAX	INTEGER (0..16777215)
	MAX-ACCESS	read-only
	STATUS	deprecated
	DESCRIPTION
		"The 'segment-identifier' of the segment
		on which topology messages were transmitted."
	::= { s5EnMsTopSrcMacAddrEntry 2 }

s5EnMsTopSrcMacAddrLstChg OBJECT-TYPE
	SYNTAX	TimeTicks
	MAX-ACCESS	read-only
	STATUS	deprecated
	DESCRIPTION
		"The value of sysUpTime when an entry in the
		table s5EnMsTopSrcMacAddrTable was last changed.
		If no changes have been done since cold/warm start
		of the agent, then the value is zero."
	::= { s5EnMsTopSrcMac 2 }

s5EnMsTopPortTable OBJECT-TYPE
	SYNTAX	SEQUENCE OF S5EnMsTopPortEntry
	MAX-ACCESS	not-accessible
	STATUS	current
	DESCRIPTION
		"A table of topology statuses for each port on the
		unit. This provides a way to make different topology
		settings for each port, instead of having global
		topology settings for the entire unit"
	::= { s5EnMsTopPort 1 }

s5EnMsTopPortEntry OBJECT-TYPE
	SYNTAX	S5EnMsTopPortEntry
	MAX-ACCESS	not-accessible
	STATUS	current
	DESCRIPTION
		"an entry in the s5EnMsTopPortTable table. There is
		one such entry for every port "
	INDEX	{ s5EnMsTopPortIfIndex }
	::= { s5EnMsTopPortTable 1 }

S5EnMsTopPortEntry ::= SEQUENCE {
	s5EnMsTopPortIfIndex  InterfaceIndex,
	s5EnMsTopPortState    INTEGER
	}

s5EnMsTopPortIfIndex OBJECT-TYPE
        SYNTAX        InterfaceIndex
        MAX-ACCESS    not-accessible
        STATUS        current
        DESCRIPTION     "Indicates port on which to configure topology."
        ::= { s5EnMsTopPortEntry 1 }

s5EnMsTopPortState OBJECT-TYPE
	SYNTAX	INTEGER {
		  topActive(1),
		  topPassthru(2)
		}
	MAX-ACCESS	read-write
	STATUS	current
	DESCRIPTION
		"Indicates if the agent is participating in
		multi-segment topology on this port. The values are:
		  topActive(1)....topology mode is active
		  topPassthru(2)...topology mode is passive (transparent)
		When the value is topActive, the agent sends out
		topology packets and also interprets any topology
		packets received and updates the topology table
		accordingly.
		When the value is topPassthru(2) the unit does not
		generate and send out topology packets and forwards
		whatever topology packets it receives."
	DEFVAL	{ topActive }
	::= { s5EnMsTopPortEntry 2 }

END
