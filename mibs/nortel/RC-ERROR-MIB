RC-ERROR-MIB DEFINITIONS ::= BEGIN

IMPORTS
    MODULE-IDENTITY, OBJECT-TYPE, Integer32
        FROM SNMPv2-SMI
    DisplayString, TruthValue
        FROM SNMPv2-TC
    rcError
        FROM RAPID-CITY;

rcErrorMib MODULE-IDENTITY
       LAST-UPDATED     "202011170000Z"
       ORGANIZATION     "Bay Networks, Rapid-City Group"
       CONTACT-INFO     "Yu-Ten Lee
                     	 Postal:    Nortel Networks, Inc.
                           	    4655 Great America Parkway
                     		    Santa Clara, CA 95052-8185

                   	 Tel: 	408-495-2560
                   	 Fax: 	408-495-6680
                	 E-mail:	ylee@nortelnetworks.com"

       DESCRIPTION 	"Enterprise MIB for the Accelar product family."

       REVISION "202011170000Z" -- 17 Nov 2020
       DESCRIPTION "Version 253: Add the following based on VOSS 8.2.5.0 mibs MRT syntax check :
                    vrfIsUsedAsNextHopVrfForRouteInAnotherVrf(8948) and vrfBaselicMaxReached(8949)"

       REVISION "202005280000Z" -- 28 May 2020
       DESCRIPTION "Version 252: Add the following based on VOSS 8.1.60.0 mibs MRT syntax check -
	                         633, 634, 637, 1584, 1585, 2350-2352, 4127-4136,
                                 5027, 5519-5520, 8128-8130, 8218, 9123, 9125, 9126,
                                 9224-9228, 9482, 9485, 13371-13372, 13861, 13866-13868,
                                 14598-14599, 15249, 15252-15261, 15263-15284, 15509,
                                 16043-16051, 16118-16132, 16605, 16701-16702
				 (Prem)"

       REVISION "202004140000Z" -- 14 April 2020
       DESCRIPTION "Version 251: Add the following based on VOSS 8.1.5.0 mibs MRT syntax check -
	                         * 5305-5309, 5311, 6759, 10531-10539, 13339, 13340, 13342,
                                   13845-13848, 13850-13860, 13862, 13863, 16105-16117,
                                   16501-16508
				 (Prem)"

       REVISION "201912090000Z" -- 09 December 2019
       DESCRIPTION "Version 250: Add the following based on VOSS 8.1.1.0 mibs MRT syntax check -
	                         * 1579-1583, 9124, 15262, 15904, 16308-16309, 16500, 16601-16604
				 (Prem)"

       REVISION "201910090000Z" -- 09 October 2019
       DESCRIPTION "Version 249: Add the following based on VOSS 8.1 mibs MRT syntax check -
	                         * 638, 2596, 2597, 9477, 10528-10530, 12897, 13359-13362,
				   13367-13369, 13617-13645, 14446, 14448, 14901-
				   14908, 14767-14776, 15314, 15315, 15658, 15717, 15718,
				   16100-16104, 16300-16307, 16405-16421
				 (Prem)"

       REVISION "201904080000Z" -- 8 Apr. 2019
       DESCRIPTION "Version 248: Add : coredumpNotAllowedOnHA(9476), fdbEntryCantBeDeleted(9556),
                                       fdbEntryNotFound(9557),fdbEntryNotFoundInPort(9558), fdbEntryNotFoundInVlan(9559),
                                       cvidRangeReservedForInternalUse(14597).
                                 Based on Tsunami 6.3 (Oana)"


       REVISION "201904040000Z" -- 4 Apr. 2019
       DESCRIPTION "Version 247: Add - 8127, 16039-16042.
				 Based on VOSS 8.0.5 (Prem)"

       REVISION "201901080000Z" -- 8 Jan. 2019
       DESCRIPTION "Version 247: Add - 635-636, 2591-2595, 4116-4126,
	   			 5014-5026, 5104, 5105, 5518, 6757, 6758,
				 7511-7514, 8122-8126, 10524-10527, 12731-
				 12756, 12882-12896, 13333-13338, 13343,
				 13345-13347, 13349-13358, 13363-13365,
				 13707-13739, 14701-14766, 15001-15003,
				 15201-15248, 15250-15251, 15301-15313,
				 15401-15426, 15501-15508, 15601-15657,
				 15701-15716, 15902-15903, 16001-16038.
				 Based on VOSS 8.0 (Prem)"

       REVISION "201702010000Z" -- 1 Feb. 2017
       DESCRIPTION "Version 246: Correct MIB errors"

       REVISION "201609220000Z" -- 22 Sept. 2016
       DESCRIPTION "Version 245: update error code"

       REVISION "201510010000Z" -- 01 Oct. 2015
       DESCRIPTION "Version 244: update error code"

       REVISION "201405300000Z" -- 30 May 2014
       DESCRIPTION "Version 243: Added the following error codes based on VSP9K 4.0 -
	                         9121, 9464-9466, 1560-1564, 1805-1806, 2344-2346,
				 2495, 2574-2577, 3406, 4702, 7774-7775, 8942-8943,
				 10256, 10398-10399, 10753-10783, 10786-10789, 10791-
				 10794, 10796-10797, 11467-11468, 12832-12837, 12842,
				 12844-12855, 12857-12860, 12864-12869, 12925-12928,
				 13305-13311, 13417-13422, 13424-13426, 13501-13528
				 and 13801."

       REVISION "201208090000Z" -- 00 August 2012
       DESCRIPTION "Version 242: Added the following error codes based
	   		         on ERS8600 and VSP9000 Master copy -
				 633, 634, 1526, 1552-1559, 1601, 1602,
				 2333, 2334, 2336-2338, 2494, 2566, 2573,
				 2804-2808, 3616, 4111, 4113-4115, 4816,
				 5707, 6500, 6528, 6716, 6730, 6731, 6999,
				 7055, 7654-7658, 7686, 7687, 7763, 7764,
				 7767, 7848-7861, 8214-8217, 8383, 8384,
				 8940, 8941, 9116-9119, 9437, 9454, 9455,
				 9543-9554, 10374-10385, 10387-10396,
				 10520-10522, 10740, 10741, 10748, 10966,
				 11419-11421, 11423, 11444-11446, 11461-
				 11463, 12509, 12510, 12705-12712, 12906-
				 12924, 13001-13015, 13201-13208, 13301-13304.
				 Changed the following the match the master
				 copy -
				 opmResetxxxx (5709 and 5710) to esmResetxxxx
				 tlsTdiAdmAlreadyEnable(6345) to tlsTdiAdmAlreadyEnable(6435)
				 tlsTdiAdmAlreadyDisable(6346) to tlsTdiAdmAlreadyDisable(6436).
				 portIsBeingUsedForOtherServ(9341) to portIsBeingUsedForOtherService(9341)
				 cannotConfigureIpToPortInVlanZero(10319) to portWithUniInterfaceTypeCannotBeAssignedIp(10319)
				 dhcpPortBelongToDaiDisabledVlan(11103) to dhcpPortBelongToDaiDsabledVlan(11103)
				 "

       REVISION "201208070000Z" -- 07 August 2012
       DESCRIPTION "Version 241: Added the following error codes based
	   		         on ERS8600 7.2 release -
				 1604, 2335, 2339-2343, 2803, 7772, 7773
				 8382, 8442, 8443, 9120, 9458, 10386, 10397,
				 10733-10739, 10742-10747, 10749-10752,
				 11464, 11465, 12824-12831, 13101-13164"

       REVISION "201208070000Z" -- 07 August 2012
       DESCRIPTION "Version 240: Reverted this file back to version 238
	   			 because the changes made in version 239
				 conflicts with the error codes on the
				 VSP9000 and ERS8600 streams."

       REVISION "201203230000Z" -- 23 March 2012
       DESCRIPTION "Version 239: Modified the error codes based on the codes
	   		         existing in the VSP4K stream by Hallur,
				 Jayanna Chandrashe"

       REVISION "201201100000Z" -- 10 January 2012
       DESCRIPTION "Version 238: Added error codes - 1603, 9456, 9457,
	            7768-7771, 10370-10372 and 12807-12823"

       REVISION "201105260000Z" -- 26 May 2011
       DESCRIPTION "Version 237: Added error codes - 7813 - 7847, 10373,
	            9202-9204"

       REVISION "201101060000Z" -- 06 January 2011
       DESCRIPTION "Version 236: Added error codes 1198, 1548, 8372-8381,
	            9540, 9541, 10249-10255, 10459-10462, 10716-10732,
		    11422-, 11424-11443, 11447-11460"

       REVISION "201009171100Z" -- 17 September 2010
       DESCRIPTION "Version 235: Added error codes 631-632, 1185-1186, 1196-1197, 1199,
	                         1549-1551, 2567-2572, 2712, 4112, 4701, 5302-5304, 5511,
				 6527, 6712-6715, 6717-6729, 7510, 7659-7677, 7679-7685,
				 7689-7699, 7765-7766, 8938-8939, 9113-9115, 9201, 9438-9453,
				 9542, 10363-10369, 12505-12508, 12607-12610, 12701-12704,
				 12801-12806, 12901-12905"

       REVISION "201008231100Z" -- 23 August 2010
       DESCRIPTION "Version 235: Added error codes 9112, 9608, 1182-1184, 1187-1195, 1540-1547,
	                         2331, 2332, 5301, 6526, 7678, 7802-7812, 8210-8213, 8934-8937,
				 10058, 11708-11711, 11120-11124, 11226, 11227, 11502, 11503"

       REVISION "200903161100Z" -- 16 March 2009
       DESCRIPTION "Version 234: Added error codes 10458"


       REVISION "200903101200Z" -- 10 March 2009
       DESCRIPTION "Version 233: Added error codes 1227-1230, 2565, 6525, 7146-7155, 8371,
				 9536-9539, 10127-10129, 10454-10457, 10641, 11224-11225, 11418.
				 Modified error codes: 11218-11223"

       REVISION "200903091200Z" -- 09 March 2009
       DESCRIPTION "Version 232: Added error code 10363"

       REVISION "200903061200Z" -- 06 March 2009
       DESCRIPTION "Version 231: Updated entry for 1181"

       REVISION "200903060000Z" -- 06 March 2009
       DESCRIPTION "Version 230: Added error code 1181."

       REVISION "200903020000Z" -- 02 March 2009
       DESCRIPTION "Version 229: Added error code 4818."

       REVISION "200902170000Z" -- 17 February 2009
       DESCRIPTION "Version 228: Added error codes 9435 and 9436."

       REVISION "200902160000Z" -- 16 February 2009
       DESCRIPTION "Version 227: Added error codes 2329 - 2330."

       REVISION "200902100000Z" -- 10 February 2009
       DESCRIPTION "Version 226: Added error codes 3627."

       REVISION "200902060000Z" -- 06 February 2009
       DESCRIPTION "Version 225: Added error codes 11701-11707."

       REVISION "200901090000Z" -- 09 January 2009
       DESCRIPTION "Version 224: Modify error codes 11101, 11102, 11104 and 11108."

       REVISION "200901080000Z" -- 08 January 2009
       DESCRIPTION "Version 223: Added error codes 8119-8121, 8439-8441, 1178-1180, 1538-1539."

       REVISION "200812110000Z" -- 11 December 2008
       DESCRIPTION "Version 222: Added error codes 11414-11417."


       REVISION "200812050000Z" -- 05 December 2008
       DESCRIPTION "Version 221: Added error codes 12601-12606."

       REVISION "200812030000Z" -- 03 December 2008
       DESCRIPTION "Version 220: Added error code 11106-11119."

       REVISION "200811290000Z" -- 29 November 2008
       DESCRIPTION "Version 219: Added error code 3405."

       REVISION "200811280000Z" -- 28 November 2008
       DESCRIPTION "Version 218: Modified label of error code 10248."

       REVISION "200811260000Z" -- 26 November 2008
       DESCRIPTION "Version 217: Added error codes 6522-6524, 7937, 10519, 11219-11223,
                                 11405-11411, 11616."

       REVISION "200811030000Z" -- 03 November 2008
       DESCRIPTION "Version 216: Added error code 10248."

       REVISION "200810311000Z" -- 31 October 2008
       DESCRIPTION "Version 215: Added error codes 1224-1226, 6519-6521, 7133-7145, 8697-8699,
				 9321, 9531-9535, 10049-10057, 10346-10362, 10447-10453, 10640,
				 10715-10716, 11214-11218, 11601-11615."

       REVISION "200810310000Z" -- 31 October 2008
       DESCRIPTION "Version 214: Added error code 5510"

       REVISION "200810130000Z" -- 13 October 2008
       DESCRIPTION "Version 213: Added error codes 11201-11213, 11301-11315,
				11401-11404, 11501."

       REVISION "200809150000Z" -- 15 September 2008
       DESCRIPTION "Version 212: Added error codes 1220-1223, 7228-7233,
				 7933-7936, 8208-8209, 8370, 8683-8696,
				 10123-10126, 10344-10345, 10444-10446,
				 10511-10518, 10713-10714, 10845-10847,
				 10964-10973, 11019"

       REVISION "200808280000Z" -- 28 August 2008
       DESCRIPTION "Version 211: Added error codes 12501-12504."

       REVISION "200808070000Z" -- 07 August 2008
       DESCRIPTION "Version 210: Added error codes 11101-11105."

       REVISION "200807170000Z" -- 17 July 2008
       DESCRIPTION "Version 209: Added error codes 2328 and 6518."

       REVISION "200807080000Z" -- 08 July 2008
       DESCRIPTION "Version 208: Added error code 8367-8369, 8682, 10341-10343, 10442-10443,
                                 10962-10963, 11001-11018.
                                 Modified error codes 10928-10929, 10936."

       REVISION "200806270000Z" -- 27 June 2008
       DESCRIPTION "Version 207: Added error code 10844."

       REVISION "200806170000Z" -- 17 June 2008
       DESCRIPTION "Version 206: Added error codes 1177, 1219, 9432, 9434, 9529-9530,
				 10433-10441, 10639, 10937-10961."

       REVISION "200806060000Z" -- 06 June 2008
       DESCRIPTION "Version 205: Added error codes 2493 and 9111."

       REVISION "200805170000Z" -- 17 May 2008
       DESCRIPTION "Version 204: Modified mplsTunnelNoAltPath(10041) to match
				the codestream mplsTunnelNoALtPath. Add error
				code 5103."

       REVISION "200805140000Z" -- 14 May 2008
       DESCRIPTION "Version 203: Updated the chronology of version updates.
				 Reduced the string length of enums 10121, 10122."

       REVISION "200805130000Z" -- 13 May 2008
       DESCRIPTION "Version 202: Moved 10841-10844 to 10840-10843."

       REVISION "200805100000Z" -- 10 May 2008
       DESCRIPTION "Version 201: Added error code 6711 and modified 10047-10048."

       REVISION "200805060000Z" -- 06 May 2008
       DESCRIPTION "Version 200: Added error codes 1206-1218, 8363-8366, 8678-8681,
                                 9428, 10047-10048, 10631-10638, 10712, 10917-10936."

       REVISION "200804110000Z" -- 11 Apr 2008
       DESCRIPTION "Version 199: Added error codes 10335-10338."

       REVISION "200804091000Z" -- 09 Apr 2008
       DESCRIPTION "Version 198: Added error codes 8932-8933, 10247.
                                 Modified error codes 1537, 10817-10844."

       REVISION "200804090000Z" -- 09 Apr 2008
       DESCRIPTION "Version 197: Added error codes 7509, 8362, 8672-8677,
                                 10625-10630, 10711, 10901-10916"

       REVISION "200803250000Z" -- 25 Mar 2008
       DESCRIPTION "Version 196: Added error codes 2489 - 2492.
                                 Removed error code 10422."

       REVISION  "200802260000Z" -- 26 Feb 2008
       DESCRIPTION "Version 195: Added error codes 1537, 2564, 7508,
				 8359-8361, 8437-8438, 8670-8671, 9427,
				 10241-10246, 10330-10334, 10431-10432,
				 10510, 10710, 10841-10844.
				 Modified 4902-4906, 8662, 10709"

       REVISION  "200802140000Z" -- 14 Feb 2008
       DESCRIPTION "Version 194: Added error code 8356-8358, 8664-8669, 10426-1027,
				 10429-10430, 10709"

       REVISION  "200802110000Z" -- 11 Feb 2008
       DESCRIPTION "Version 193: Added error code 8661,8663,10424,10428,7761,7507,7762,10623,10624,10425,10324-10329,
				 Modified error code 8782-8789"

       REVISION  "200802010000Z" -- 01 Feb 2008
       DESCRIPTION "Version 192: Added error code 9110,8931"

       REVISION "200801280000Z" -- 28 Jan 2008
       DESCRIPTION "Version 191: Added error codes for DDM 1801-04. Revise the version number."

       REVISION "200801140000Z" -- 14 Jan 2008
       DESCRIPTION "Version 188: Added error codes for MLT 2561-63"

       REVISION "200801110000Z" -- 11 January 2008
       DESCRIPTION "Version 187: Added error codes 4902-4906, 7759-7760, 7929-7932, 8354-8355,
		    8659-8660, 10238-10240, 10508-10509, 10622, 10708, 10801-10840.
		    Modify 10421, 10621"

       REVISION "200801040000Z" -- 4 January 2008
       DESCRIPTION "Version 186: Added error codes 6516,6517."

       REVISION "200712280000Z" -- 28 December 2007
       DESCRIPTION "Version 185: Added error codes 10238-10240, 10508, 10509."

       REVISION "200712260000Z" -- 26 December 2007
       DESCRIPTION "Version 184: Added error codes 9527, 9425, 9426"

       REVISION  "200712200000Z" -- 20 December 2007
       DESCRIPTION "Version 183: Added error code 9109"

       REVISION  "200712180000Z" -- 18 December 2007
       DESCRIPTION "Version 182: Added error codes 8654-8658, 10320-10323, 10422, 10621"

       REVISION  "200712120000Z" -- 12 December 2007
       DESCRIPTION "Version 181: Added error code 8929, 8930"

       REVISION  "200712040000Z" -- 04 December 2007
       DESCRIPTION "Version 180: Added error code 10701-10707, 10423, 7927-7928,
	                         8653, 10619-10620"

       REVISION  "200711200000Z" -- 22 November 2007
       DESCRIPTION "Version 179: Added error code 1536, 7801, 8432-8436"

       REVISION  "200711010000Z" -- 01 November 2007
       DESCRIPTION "Version 178: Added error code 2327, 7499, 7925-7926, 8652, 10042-10046,
				 10319, 10419-10421, 10504-10507, 10618."

       REVISION  "200710180000Z" -- 18 October 2007
       DESCRIPTION "Version 177: Added error code 1176, 8651, 7926, 10121-10122"

       REVISION  "200710100000Z" -- 10 October 2007
       DESCRIPTION "Version 176: Added error code 8928"

       REVISION  "200710020000Z" -- 02 October 2007
       DESCRIPTION "Version 175: Removed error code 10601 and re-numbered 10602-10618 to 10601-10617."

       REVISION  "200709280000Z" -- 28 September 2007
       DESCRIPTION "Version 174: Added error codes 10601-10618."

       REVISION  "200709260000Z" -- 26 September 2007
       DESCRIPTION "Version 173: Modified error codes 10315-10317, Added error code 8650."

       REVISION  "200709250000Z" -- 25 September 2007
       DESCRIPTION "Version 172: Added error codes 10118-10120, 10503"

       REVISION  "200709190000Z" -- 19 September 2007
       DESCRIPTION "Version 171: Added error codes 5299, 7925, 8335-8353, 10235-10237, 10415-10418, 10501-10502"

       REVISION  "200709100000Z" -- 10 September 2007
       DESCRIPTION "Version 170: Added error codes 8649, 8729, 8774-8799, 10113-10117, 10315-10318, 10401-10413"

       REVISION  "200708290000Z" -- 29 August 2007
       DESCRIPTION "Version 169: Added error codes 7658"

       REVISION  "200708220000Z" -- 22 August 2007
       DESCRIPTION "Version 168: Added error codes 8708-8725"

       REVISION  "200708140000Z" -- 14 August 2007
       DESCRIPTION "Version 167: Added error codes 9526"

       REVISION  "200708020000Z" -- 02 August 2007
       DESCRIPTION "Version 166: Added error codes 5709-5710, 8774-8781, 10037-10041"

       REVISION  "200707300000Z" -- 30 July 2007
       DESCRIPTION "Version 165: Added error codes 10035-10036, 10313-10314"

       REVISION  "200707260000Z" -- 26 July 2007
       DESCRIPTION "Version 164: Added error codes 2321-2326"

       REVISION  "200707200000Z" -- 20 July 2007
       DESCRIPTION "Version 163: Added error codes 1175, 7758, 8771-8773,
				 9108, 9525, 10109-10112, 10235"

       REVISION  "200707160000Z" -- 16 July 2007
       DESCRIPTION "Version 162: Added NSNA error code 8431"

       REVISION "200707130000Z" -- 13 July 2007
       DESCRIPTION "Version 161: Added error codes 10306-10311"

       REVISION "200707120000Z" -- 12 July 2007
       DESCRIPTION "Version 160: Move lldpMedCapabilityTlvMandatory to 10312"

       REVISION "200707111000Z" -- 11 July 2007
       DESCRIPTION "Version 159: Deleted error codes 9526&9527 duplicate as 9504&9505"

       REVISION "200707110900Z" -- 11 July 2007
       DESCRIPTION "Version 158: Added 1174 (under VLAN module)"

       REVISION "200707110000Z" -- 11 July 2007
       DESCRIPTION "Version 157: Added error codes 9526 & 9527"

       REVISION "200706260000Z" -- 26 June 2007
       DESCRIPTION "Version 156: Added error code 3404 and change 3403."

       REVISION "200706200000Z" -- 20 June 2007
       DESCRIPTION "Version 155: Added error code 7923-7924, 10031-10034."

       REVISION "200706160000Z" -- 16 June 2007
       DESCRIPTION "Version 154: Added error code 3622 and 3626."

       REVISION "200706150000Z" -- 15 June 2007
       DESCRIPTION "Version 153: Added error code 7917."

       REVISION "200706140000Z" -- 14 June 2007
       DESCRIPTION "Version 152: Added error codes 2484-2488 and 3625."

       REVISION "200706130000Z" -- 13 June 2007
       DESCRIPTION "Version 151: Change a typo of error code 8430."

       REVISION "200706080000Z" -- 08 June 2007
       DESCRIPTION "Version 150: Added error code 3403 and 10306."

       REVISION "200706070000Z" -- 07 June 2007
       DESCRIPTION "Version 149: Added error code 10030."

       REVISION "200706060000Z" -- 06 June 2007
       DESCRIPTION "Version 148: Added error code 2802."

       REVISION "200706041000Z" -- 04 June 2007
       DESCRIPTION "Version 147: Added error code 8334."

       REVISION "200706040000Z" -- 04 June 2007
       DESCRIPTION "Version 146: Added error code 10027-10029."

       REVISION "200706011000Z" -- 01 June 2007
       DESCRIPTION "Version 145: Added error code 8769-8770."

       REVISION "200706010000Z" -- 01 June 2007
       DESCRIPTION "Version 144: Added error code 8768."

       REVISION "200705280000Z" -- 28 May 2007
       DESCRIPTION "Version 143: Added error codes 2607 and 2608."

       REVISION "200705240000Z" -- 24 May 2007
       DESCRIPTION "Version 142: Added error codes 10024-10026."

       REVISION "200705220000Z" -- 22 May 2007
       DESCRIPTION "Version 141: Added error codes 2606, 5293-5298, 8646-8648, 8767,
			9424, 10233-10234, 10303-10305."

       REVISION "200705180000Z" -- 18 May 2007
       DESCRIPTION "Version 140: Added error codes 10019-10023."

       REVISION "200705170000Z" -- 17 May 2007
       DESCRIPTION "Version 139: Added error codes 8924-8926."

       REVISION "200705150000Z" -- 15 May 2007
       DESCRIPTION "Version 138: Added error codes 10017-10018."

       REVISION "200705101000Z" -- 10 May 2007
       DESCRIPTION "Version 137: Added error code 10232."

       REVISION "200705100000Z" -- 10 May 2007
       DESCRIPTION "Version 136: Added error code 10231."

       REVISION "200705070000Z" -- 07 May 2007
       DESCRIPTION "Version 135: Added error codes 1172-1173, 2605, 8645,
				 8764-8766, 10016, 10230."

       REVISION "200704251000Z" -- 25 Apr 2007
       DESCRIPTION "Version 134: Added error codes 8763 and 10229."

       REVISION "200704250000Z" -- 25 Apr 2007
       DESCRIPTION "Version 133: Added error codes 8920-8923 and 10228. Reassigned 8907."

       REVISION "200704241000Z" -- 24 Apr 2007
       DESCRIPTION "Version 132: Added error codes 7916 and 8762."

       REVISION "200704240000Z" -- 24 Apr 2007
       DESCRIPTION "Version 131: Added error codes 10014, 10015, 10301, 10302."

       REVISION "200704220000Z" -- 22 Apr 2007
       DESCRIPTION "Version 130: Added error codes 10223-10227."

       REVISION "200704170000Z" -- 17 Apr 2007
       DESCRIPTION "Version 129: Added error codes 7922, 8760, 8761 and 10222.
		Removed error codes 7916 and 7917."

       REVISION "200704041000Z" -- 04 Apr 2007
       DESCRIPTION "Version 128: Converted error code 3625 to 3621 and removed 3622"

       REVISION "200704040000Z" -- 04 Apr 2007
       DESCRIPTION "Version 127: Add error codes 1171, 3621-3625, 7754-7757,
				 7920-7921, 8643-8644, 10001, 10013"

       REVISION "200703300000Z" -- 30 Mar 2007
       DESCRIPTION "Version 126: Change 8429 and add 8430"

       REVISION "200703270000Z" -- 27 Mar 2007
       DESCRIPTION "Version 125: Add error codes 3621 and 8429"

       REVISION "200703140000Z" -- 14 Mar 2007
       DESCRIPTION "Version 124: Add error codes 5289-5292, 10217-10221"

       REVISION "200703100000Z" -- 10 Mar 2007
       DESCRIPTION "Version 123: Add error codes 10215-10216"

       REVISION "200702270000Z" -- 27 Feb 2007
       DESCRIPTION "Version 122: Add error codes 1165-1170, 7722-7753, 7918-7919,
				 8637-8642, 8758-8759, 10201-10214"

       REVISION "200702250000Z" -- 25 Feb 2007
       DESCRIPTION "Version 121: Updated error codes 2558-2560"

       REVISION "200702080000Z" -- 09 Feb 2007
       DESCRIPTION "Version 120: Added error code 2558; removed error code 10001"

       REVISION "200701300000Z" -- 30 Jan 2007
       DESCRIPTION "Version 119: Added error codes 6996-6998, 7095-7099,
				 7916-7917, 8632-8636, 8756-8757, 8821-8830,
				 10011-10012, 10101-10108."

       REVISION "200701260000Z" -- 26 Jan 2007
       DESCRIPTION "Version 118: Added error code 1164."

       REVISION "200701180000Z" -- 18 Jan 2007
       DESCRIPTION "Version 117: Added error code 3402."

       REVISION "200701141000Z" -- 14 Jan 2007
       DESCRIPTION "Version 116: Added error code 7915."

       REVISION "200701140000Z" -- 14 Jan 2007
       DESCRIPTION "Version 115: Added error codes 1163 and 8622-8631."

       REVISION "200701120000Z" -- 12 Jan 2007
       DESCRIPTION "Version 114: Added error code 9399."

       REVISION "200701100000Z" -- 10 Jan 2007
       DESCRIPTION "Version 113: Added error codes 7914, 9521-9524, 10010."

       REVISION "200612150000Z" -- 15 Dec 2006
       DESCRIPTION "Version 112: Added error codes 6710, 7908-7913, 8914-8919, 9421-9423, 10009."

       REVISION "200612130000Z" -- 13 Dec 2006
       DESCRIPTION "Version 111: Added error code 9398"

       REVISION "200612010000Z" -- 01 Dec 2006
       DESCRIPTION "Version 110: Added error code 2483, 4817"

       REVISION "200611290000Z" -- 29 Nov 2006
       DESCRIPTION "Version 109: Added error codes 8617-8621, 9395-9397."

       REVISION "200611220000Z" -- 22 Nov 2006
       DESCRIPTION "Version 108: Added error codes 10006-10008, 8613-8616,
				 6993-6995, 8753-8755
				 8727 brought back to its original name."

       REVISION "200611150000Z" -- 15 Nov 2006
       DESCRIPTION "Version 107: Added error code 9394"

       REVISION "200611140000Z" -- 14 Nov 2006
       DESCRIPTION "Version 106: Added error codes 8602-8612, 8752 and rename 8727"

       REVISION "200611070000Z" -- 07 Nov 2006
       DESCRIPTION "Version 105: Added error codes 8599, 8601, 8748-8751, 9389-9393, 10003-10005"

       REVISION "200610190000Z" -- 19 Oct 2006
       DESCRIPTION "Version 104: Added error codes 2557 and 8747"

       REVISION "200610100000Z" -- 10 Oct 2006
       DESCRIPTION "Version 103: Added error codes 9419-9420"

       REVISION "200610060000Z" -- 06 Oct 2006
       DESCRIPTION "Version 102: Added error codes 6978-6992"

       REVISION "200610050000Z" -- 05 Oct 2006
       DESCRIPTION "Version 101: Added error code 8746 and 10001-10002"

       REVISION "200609291000Z" -- 29 Sep 2006
       DESCRIPTION "Version 100: Added error code 8744-8745"

       REVISION "200609290000Z" -- 29 Sep 2006
       DESCRIPTION "Version 99: Added back original error codes 6101-6199 and 7301-7309 used
		                    for MPLS by an obsoleted product (OM8k)"

       REVISION "200609280000Z" -- 28 Sep 2006
       DESCRIPTION "Version 98: Added error codes 6101-6102 for MPLS and 8737-8743.
			Removed existing 61xx and 73xx blocks currently being
			used for MPLS by an obsoleted product (OM8k)"

       REVISION "200609251000Z" -- 25 Sep 2006
       DESCRIPTION "Version 97: Added error code 8731-8936"

       REVISION "200609250000Z" -- 25 Sep 2006
       DESCRIPTION "Version 96: Added error code 8908-8913"

       REVISION "200609150000Z" -- 15 Sep 2006
       DESCRIPTION "Version 95:  Added error codes 8729-8730.
			Removed error codes 8601-8603 as VRF/MVR has been assigned 89xx block.
			Added error codes 8560-8598"

       REVISION "200609131000Z" -- 13 Sep 2006
       DESCRIPTION "Version 94: Added error code 8728"

       REVISION "200609130000Z" -- 13 Sep 2006
       DESCRIPTION "Version 93: Added error code 1162"

       REVISION "200609110000Z" -- 11 Sep 2006
       DESCRIPTION "Version 92: Added error codes 2555-2556, 8726-8727, 8901-8907"

       REVISION "200608100000Z" -- 10 Aug 2006
       DESCRIPTION "Version 91: Added error codes 1535"

       REVISION "200608030000Z" -- 03 Aug 2006
       DESCRIPTION "Version 90: Added error codes 3401, 8206-8207"

       REVISION "200607200000Z" -- 20 Jul 2006
       DESCRIPTION "Version 89: Added error codes 1533-1534, 8427-8428, 9388"

       REVISION "200607130000Z" -- 13 Jul 2006
       DESCRIPTION "Version 88: Added error codes 1160,1161 for Pcap"

       REVISION "200606140000Z" -- 14 Jun 2006
       DESCRIPTION "Version 87: Added error code 2482 for ACE"

       REVISION "200605110000Z" -- 11 May 2006
       DESCRIPTION "Version 86: Added error codes 9606, 9607 for ospf"

       REVISION "200605050000Z" -- 05 May 2006
       DESCRIPTION "Version 85: Added error codes 1159, 8816-8820"

       REVISION "200604210000Z" -- 21 Apr 2006
       DESCRIPTION "Version 84: Added error codes 8707"

       REVISION "200604070000Z" -- 7 Apr 2006
       DESCRIPTION "Version 83: Added error codes 5508-5509, 7496-7498, & 9908"

       REVISION "200603300000Z" -- 30 Mar 2006
       DESCRIPTION "Version 82: Added error code 8815"

       REVISION "200603241200Z" -- 24 Mar 2006
       DESCRIPTION "Version 81: Added error code 7496"

       REVISION "200603240000Z" -- 24 Mar 2006
       DESCRIPTION "Version 80: Added error codes 7131, 7132"

       REVISION "200603211200Z" -- 21 Mar 2006
       DESCRIPTION "Version 79: Added error codes 1150, 1152-1157"

       REVISION "200603210000Z" -- 21 Mar 2006
       DESCRIPTION "Version 78: Added new error codes 8801-8814"

       REVISION "200603171000Z" -- 17 Mar 2006
       DESCRIPTION "Version 77: Modify error code 1532, Added error codes 1158, 2544-2554, 8701-8706"

       REVISION "200603170000Z" -- 17 Mar 2006
       DESCRIPTION "Version 76: Added error code 6977,8559"

       REVISION "200603150000Z" -- 15 Mar 2006
       DESCRIPTION "Version 75: Added error code 1532"

       REVISION "200603010000Z" -- 01 Mar 2006
       DESCRIPTION "Version 74: Added error code 8555-8558 "

       REVISION "200602200000Z" -- 20 Feb 2006
       DESCRIPTION "Version 73: Added error code 2543"

       REVISION "200602110000Z" -- 11 Feb 2006
       DESCRIPTION "Version 72: Added error codes 7494-7495"

       REVISION "200602080000Z" -- 08 Feb 2006
       DESCRIPTION "Version 71: Added error codes 6509, 6515, 7487-7493"

       REVISION "200602030000Z" -- 03 Feb 2006
       DESCRIPTION "Version 70: Added error code 6974,6975,7078-7094,7129,7130"

       REVISION "200602020000Z" -- 02 Feb 2006
       DESCRIPTION "Version 69: Added error code 6976"

       REVISION "200601190000Z" -- 19 Jan 2006
       DESCRIPTION "Version 68: Added error codes 2540,2541,2542 for MLT"

       REVISION "200601180000Z" -- 18 Jan 2006
       DESCRIPTION "Version 67: Added error codes 9382-9387"

       REVISION "200601090000Z" -- 09 Jan 2006
       DESCRIPTION "Version 66: Added error codes 1151,6514,7491,9418,9906,9907"

       REVISION "200512080000Z" -- 08 Dec 2005
       DESCRIPTION "Version 65: Added error codes 6971-6973, 8554"

       REVISION "200511220000Z" -- 22 Nov 2005
       DESCRIPTION "Version 64: Added more ipv6 error codes; up to 7486"

       REVISION "200511090000Z" -- 09 Nov 2005
       DESCRIPTION "Version 63: Added 5708"

       REVISION "200511020000Z" -- 02 Nov 2005
       DESCRIPTION "Version 62: Added 8552 - 8553"

       REVISION "200510250000Z" -- 25 Oct 2005
       DESCRIPTION "Version 61: Added 8549 - 8551"

       REVISION "200510180000Z" -- 18 Oct 2005
       DESCRIPTION "Version 60: Added 8546 - 8548 and modified 8513 and 8525"

       REVISION "200510130000Z" -- 13 Oct 2005
       DESCRIPTION "Version 59: Added 8534 - 8545"

       REVISION "200510070000Z" -- 07 Oct 2005
       DESCRIPTION "Version 58: Added 6709"

       REVISION "200510050000Z" -- 05 Oct 2005
       DESCRIPTION "Version 57: Added 6706-6708"

       REVISION "200509300000Z" -- 30 Sep 2005
       DESCRIPTION "Version 56: Removed 631-635, Added 1148-1149, 1530-1531, 6705, 7467-7476, 9380-9381, 9107, 9417"

       REVISION "200509280000Z" -- 28 Sep 2005
       DESCRIPTION "Version 55: Add error code 635."

       REVISION "200509260000Z" -- 26 Sep 2005
       DESCRIPTION "Version 54: Added error codes 633-634 for ECMP 8-path"

       REVISION "200509230000Z" -- 23 Sep 2005
       DESCRIPTION "Version 53: Modify error codes 1147, 6967, and 6969.  Add new error code 6970."

       REVISION "200509210000Z" -- 21 Sep 2005
       DESCRIPTION "Version 52: Added error code 6969"

       REVISION "200509080000Z" -- 08 Sep 2005
       DESCRIPTION "Version 51: Added error codes for IPv6 & SLPP & NSNA"

       REVISION "200509071200Z" -- 07 Sep 2005
       DESCRIPTION "Version 50: Added error codes 6961-6968, 8529-8533"

       REVISION "200508311200Z" -- 31 Aug 2005
       DESCRIPTION "Version 49: Added error codes 9605, 8526-8528, and initial error codes for VRF 8601-8603"

       REVISION "200508261200Z" -- 26 Aug 2005
       DESCRIPTION "Version 48: Added initial error codes for IPv6 - 74xx"

       REVISION "200508260000Z" -- 26 August 2005
       DESCRIPTION "Version 47: Added new error codes 1146-1147 and 8501-8525."

       REVISION "200508250000Z" -- 25 Aug 2005
       DESCRIPTION "Version 46: Added error codes 8424, 8425"

       REVISION "200508100000Z" -- 10 Aug 2005
       DESCRIPTION "Version 45: Added error codes 2539, 4110"

       REVISION "200508030000Z" -- 03 Aug 2005
       DESCRIPTION "Version 44: Added error codes 1145, 6513"

       REVISION "200507250000Z" -- 25 July 2005
       DESCRIPTION "Version 43: Added error codes 3618-3620, 8422-8423, 9379"

       REVISION "200507140000Z" -- 14 July 2005
       DESCRIPTION "Version 42: Added error codes 1141-1144."

       REVISION "200507060000Z" -- 06 July 2005
       DESCRIPTION "Version 41: Added NSNA error codes 8401-8421.  Also, added 1140."

       REVISION "200506011200Z" -- 01 June 2005
       DESCRIPTION "Version 40: Added new error code 1529."

       REVISION "200505241200Z" -- 24 May 2005
       DESCRIPTION "Version 39: Added new error codes for NSNA.  Reorganized existing error codes so that they appear in ascending order."

       REVISION "200505240000Z" -- 24 May 2005
       DESCRIPTION "Version 38: Added new error codes 8332 and 8333."

       REVISION "200505230000Z" -- 23 May 2005
       DESCRIPTION "Version 37: Added new error code 8205."

       REVISION "200505170000Z" -- 17 May 2005
       DESCRIPTION "Version 36: Added new error code 2604."

       REVISION "200505160000Z" -- 16 May 2005
       DESCRIPTION "Version 35: Renamed error codes 8311-8312 and 8325-8329."

       REVISION "200505131200Z" -- 13 May 2005
       DESCRIPTION "Version 34: Added error code 8331"

       REVISION "200505130000Z" -- 13 May 2005
       DESCRIPTION "Version 33: Added error code 9604"

       REVISION "200505060000Z" -- 06 May 2005
       DESCRIPTION "Version 32: Added error code 8004.  Updated 8002."

       REVISION "200504221200Z" -- 22 April 2005
       DESCRIPTION "Version 31: Added new error code 8330.
			Also sync up the error codes with the Master Copy:
			- Add 2533 - 2537
			- Add 7064 - 7077
			- Add 7127-7128
			- 8108-8119 incorrectly numbered - should be 8107-8118"

       REVISION "200504131200Z" -- 13 April 2005
       DESCRIPTION "Version 30: Added error codes 8319-8329"

       REVISION "200503241200Z" -- 24 March 2005
       DESCRIPTION "Version 29: Added error code 8003 - eapInvalidMaxNonEapValue"

       REVISION "200502231200Z" -- 23 February 2005
       DESCRIPTION "Version 28: Added error codes 9375-9378"

       REVISION "200502180000Z" -- 18 February 2005
       DESCRIPTION "Version 27: Sync-up with Master Copy and introduced ISIS @ 83xx"

       REVISION "200502110000Z" -- 11 February 2005
       DESCRIPTION "Version 26: Added error codes for 4109 & 5507.  Introduced Tacacs @ 82xx"

       REVISION "200502100000Z" -- 10 February 2005
       DESCRIPTION "Version 25: Added intial error codes for IPFIX @ 81xx"

       REVISION "200502011800Z" -- 01 February 2005
       DESCRIPTION "Version 24: Added error code 2419"

       REVISION "200501241200Z" -- 24 January 2005
       DESCRIPTION "Version 23: Added error codes 6511-6512, 8002"

       REVISION "200501201200Z" -- 20 January 2005
       DESCRIPTION "Version 22: Added error codes 1134-1135"

       REVISION "200501171200Z" -- 17 January 2005
       DESCRIPTION "Version 21: Updated 7613"

       REVISION "200501141800Z" -- 14 January 2005
       DESCRIPTION "Version 20: Added message 9373"

       REVISION "200412200000Z" -- 20 December 2004
       DESCRIPTION "Version 19: Updated messages (7059,6958)
				Added new messages (6956,6957,7057,7058) "

       REVISION "200412171800Z" -- 17 December 2004
       DESCRIPTION "Version 18: Added new messages (6958,7059, 7648-7653,7505,7506)."

       REVISION "200412071400Z" -- 12 December 2004
       DESCRIPTION "Version 17: Added new messages (1132-1133)."

       REVISION "200411301700Z" -- 30 November 2004
       DESCRIPTION "Version 16: Added new messages for Launch Pad(1129-1131)."

       REVISION "200411110000Z" -- 11 November 2004
       DESCRIPTION "Version 15: Cleaned up REVISIONs and fixed typos."

       REVISION "200411040000Z" -- 04 November 2004
       DESCRIPTION "Version 14: Modify PowerRanger related Error
                                messages(9363,64,65,69,71,72, 7501-04,
                                7601-47,7701-17)"

       REVISION "200410271700Z" -- 27 October 2004
       DESCRIPTION "Version 13: Add error message
                                communityListModificationNotAllowed(5288)"

       REVISION "200410200000Z" -- 20 October 2004
       DESCRIPTION "Version 12: Add error message 6948-6955 and 7052-7054,
                                7056, 7904-7905"

       REVISION "200410110000Z" -- 11 October 2004
       DESCRIPTION "Version 11: Add error message 1127, 1128 And Correct
                                the 7042,7045."

       REVISION "200410080000Z" -- 08 October 2004
       DESCRIPTION "Version 10: Add error message (1126)."

       REVISION "200410050000Z" -- 05 October 2004
       DESCRIPTION "Version 9: Add missing error message (2532, 7035-7051)."

       REVISION "200409300000Z" -- 30 September 2004
       DESCRIPTION "Version 8: Add missing error message (9338-9344)."

       REVISION "200409290000Z" -- 29 September 2004
       DESCRIPTION "Version 7: Add error message eapGuestAndMultiMac ."

       REVISION "200409280000Z" -- 28 September 2004
       DESCRIPTION "Version 6: Fixing typo and remove duplicate entry."

       REVISION "200409230000Z" -- 23 September 2004
       DESCRIPTION "Version 5: Added back unsubmitted error message."

       REVISION "200409130000Z" -- 13 September 2004
       DESCRIPTION "Version 4: Added radiusInvalidCliCommandCount(4107)"

       REVISION "200407200000Z" -- 20 July 2004
       DESCRIPTION "Version 3: Added version info"

       ::= { rcError 0 }

rcErrorLevel OBJECT-TYPE
        SYNTAX        Integer32
        MAX-ACCESS    read-only
        STATUS        current
        DESCRIPTION   "Error level indicator for the last error
                      reported in the system.  The meaning of
		      this value are :

			0 = Informative Information
			1 = Warning Condition
			2 = Error Condition
			3 = Manufacturing Information
			4 = Fatal Condition
		      "
        ::= { rcError 1 }

rcErrorCode OBJECT-TYPE
        SYNTAX        Integer32
        MAX-ACCESS    read-only
        STATUS        current
        DESCRIPTION   "Error code indicator for the last error
                      reported in the system.  This is an encoded
		      value that identifies the software module
		      that generated the error message as well as
                      a specific error condition within that module.
		      This value is transparent to the user.  This
		      value is intended to help Accelar support and
		      development staff to isolate system problems."
        ::= { rcError 2 }

rcErrorText OBJECT-TYPE
        SYNTAX        DisplayString
        MAX-ACCESS    read-only
        STATUS        current
        DESCRIPTION   "Error string of the last error reported
                      in the system."
        ::= { rcError 3 }

--
-- *** THIS SECTION IS GENERATED FROM ../mib_tools/error.mib ***

-- This is generated by str2c.py -mib
-- Do not edit this file
-- Instead, edit $(TOPDIR)/mib/mib_tools/error_input.txt

rcErrorReturnCode OBJECT-TYPE
    SYNTAX INTEGER {
		none(100),
		resourceNotAvailable(101),
		operationNotAllowed(102),
		operationInProgress(103),
		invalidPortNumber(104),
		invalidSubnetAddress(105),
		invalidSubnetMask(106),
		invalidVlanId(107),
		invalidVlanName(108),
		invalidVlanType(109),
		invalidStgId(110),
		invalidProtocolId(111),
		invalidPortMembers(112),
		invalidStaticMembers(113),
		invalidNotAllowedMembers(114),
		destinationNotReachable(115),
		tableIsFull(116),
		nondualConnectorGigPort(117),
		testIdNotPresent(118),
		invalidTestId(119),
		invalidStatusChange(120),
		invalidCpuCard(121),
		invalidSrcPortChoice(122),
		dstPortUnspecified(123),
		srcPortOneUnspecified(124),
		srcPortTwoUnspecified(125),
		notSupported(126),
		userNameIsNonUnique(127),
		invalidName(128),
		unknownErrorCode1(129),
		cannotModifyThisField(130),
		invalidUserPasswordLength(131),
		thisUsernameExists(132),
		invalidIpAddress(133),
		invalidMacAddress(134),
		nosuchEntry(135),
		anotherLoopBackTestAlreadyRunning(136),
		protocolIdNotRoutable(137),
		autoNegotiateIsOn(138),
		noActionSpecified(139),
		invalidActionSpecified(140),
		cannotModifyAutoNegotiateIsOn(141),
		cannotModifyAutoPortIsFiber(142),
		autoNegotiationNotSupported(143),
		cannotSetAdminSpeed(144),
		cannotSetAdminDuplex(145),
		ospfRtrDeadIntIsnotMultOfHelloInt(146),
		ospfRtrDeadIntLessThan4TimesHelloInt(147),
		notUsed1(148),
		ospfBadAuthValue(149),
		ospfEnabled(150),
		ospfAreaNotFound(151),
		ospfBackboneArea(152),
		notInTestMode(153),
		ospfInvalidAreaRangeMask(154),
		ospfDuplicateEntry(155),
		ospfRangeNotAllocated(156),
		ospfAreaRangeNotFound(157),
		testRunning(158),
		nvramLimitExceeded(159),
		flowAlreadyExist(160),
		flowNotFound(161),
		invalidOspfAreaRangeNet(162),
		duplicateIpAddress(163),
		conflictingIpAddress(164),
		invalidRouteCost(165),
		invalidNextHop(166),
		duplicateRoute(167),
		cannotFindRoute(168),
		cannotDeleteLocalRoute(169),
		badDhcpMinSec(170),
		badDhcpMaxHop(171),
		badDhcpMode(172),
		badAgentAddress(173),
		dhcpNotEnabled(174),
		dhcpForwardNotFound(175),
		dhcpDuplicateForward(176),
		dhcpMaxForward(177),
		dhcpBadEnable(178),
		invalidDeviceFileNumber(179),
		notExecutableDeviceFile(180),
		deletedDeviceFile(181),
		pcmciaNotPresent(182),
		pcmciaWriteProtected(183),
		discontiguousSubnetMask(184),
		invalidOspfMetric(185),
		ospfHostRouteNotFound(186),
		invalidMltId(187),
		invalidMltName(188),
		onlyOnePortInMlt(189),
		moreThan4PortsInMlt(190),
		portsInDifferentQuid(191),
		portAlreadyInAnotherMlt(192),
		invalidVlan(193),
		nonExistIpMcastAddriess(194),
		invalidIpMulticastAddress(195),
		portIsLocked(196),
		accessRestriction(197),
		invalidDeviceFileLength(198),
		duplicateAccessPolicyId(199),
		noDesiredAccessPolicyItem(200),
		ipfFilterNonExist(201),
		ipfInvalidVlanPriority(202),
		ipfInvalidDestinationAddress(203),
		ipfInvalidSourceAddress(204),
		ipfFilterDuplicate(205),
		ipfGlobalListDuplicate(206),
		ipfGlobalListNonExist(207),
		ipfBaseListDuplicate(208),
		ipfBaseListNonExist(209),
		ipfPortDuplicate(210),
		ipfPortNonExist(211),
		ipfListNonExist(212),
		snmpSnoopDisabled(213),
		invalidHostIpAddress(214),
		snoopStaticGroupExist(215),
		ripAnnouncePolicyNotFound(216),
		duplicateRipAnnouncePolicy(217),
		ospfAnnouncePolicyNotFound(218),
		duplicateOspfAnnouncePolicy(219),
		policyMatchNetEntryNotFound(220),
		duplicatePolicyNetEntry(221),
		policyAddrListEntryNotFound(222),
		duplicatePolicyAddrListEntry(223),
		policyAddrListIdNotFound(224),
		policyExactNetListNotFound(225),
		policyRangeNetListNotFound(226),
		policyRipGatewayListNotFound(227),
		policyRipInterfaceListNotFound(228),
		policyOspfRtrIdListNotFound(229),
		policyAnnounceInterfaceListNotFound(230),
		policyAdvertiseNetListNotFound(231),
		policyInjectNetListNotFound(232),
		invalidPolicyListIdListSize(233),
		policyAddrEntryNotFound(234),
		duplicatePolicyAddrEntry(235),
		disableThisPortFirst(236),
		mutinettingNotSupported(237),
		addingGlobalFilterToNonGlobalList(238),
		addingNonGlobalFilterToGlobalList(239),
		setFilteredPortMode(240),
		setFilteredPortEnableValue(241),
		invalidModeType(242),
		duplicateRipAcceptPolicy(243),
		ripAccepPolicyNotFound(244),
		duplicateOspfAcceptPolicy(245),
		ospfAccepPolicyNotFound(246),
		invalidAccessPolicyName(247),
		invalidAccessPolicyPolicyEnable(248),
		invalidAccessPolicyMode(249),
		invalidAccessPolicyService(250),
		invalidAccessPolicyPrecedence(251),
		invalidAccessPolicyNetAddress(252),
		invalidAccessPolicyTrustedHostAddress(253),
		invalidAccessPolicyTrustedHostUserName(254),
		invalidAccessPolicyAccessLevel(255),
		invalidAccessPolicyLogSetting(256),
		invalidAccessPolicyPolicyId(257),
		invalidAreaOptions(258),
		cannotDeleteAreaIfCountIsNotZero(259),
		ospfInterfaceNotFound(260),
		ospfIfAreaIdConflictsWithConfiguredAreaRange(261),
		applyingDuplicateGlobalFilterToPort(262),
		differentMltPortTypes(263),
		addPortToMltFailed(264),
		removePortFromMltFailed(265),
		mirrorPortInMlt(266),
		invalidDhcpAlwaysBroadcast(267),
		interfaceIsSetToTransmitRipV1(268),
		ripInterfaceDoesnotExist(269),
		interfaceIsNotRunningRip(270),
		cannotCreateVirtLinksThroughStubArea(271),
		invalidSyslogEnableSetting(272),
		invalidSyslogMaxHostsSettings(273),
		invalidSyslogHostIpAddr(274),
		invalidSyslogHostUdpPort(275),
		invalidSyslogHostFacility(276),
		invalidSyslogModuleId(277),
		invalidSyslogSeverity(278),
		invalidSyslogMapInfoSeverity(279),
		invalidSyslogMapWarningSeverity(280),
		invalidSyslogMapErrorSeverity(281),
		invalidSyslogMapMfgSeverity(282),
		invalidSyslogMapFatalSeverity(283),
		invalidSyslogMapTraceMsgSetting(284),
		invalidSyslogMapTrapMsgSetting(285),
		invalidSyslogLogTraceMsgSetting(286),
		invalidSyslogLogTrapMsgSetting(287),
		invalidSyslogEntryEnableSetting(288),
		invalidSyslogMaxHostSetting(289),
		invalidSyslogHostId(290),
		duplicateSyslogEntry(291),
		syslogHostTableIsFull(292),
		noDesiredSyslogHostEntryFound(293),
		invalidHoldDownTime(294),
		incompatibleAruHardware(295),
		invalidVrid(296),
		duplicateVrrpEntry(297),
		noVrrpIpAddressSpecified(298),
		invalidVrrpControlValue(299),
		invalidVrrpPriority(300),
		invalidVrrpAdvertisementInterval(301),
		maxNumOfVrrpsEntriesExceeded(302),
		policyNetListEntryNotFound(303),
		duplicatePolicyNetListEntry(304),
		policyNetListIdNotFound(305),
		filterOnAnEnabledPort(306),
		listOnAnEnabledPort(307),
		invalidIpFilterSrcOption(308),
		invalidIpFilterDstOption(309),
		invalidOspfAreaImportextOption(310),
		invalidOspfInterfaceMd5KeyIdLength(311),
		invalidOspfInterfaceMd5KeyLength(312),
		invalidIPXNetworkNumber(313),
		ipxCircuitAlreadyExists(314),
		ipxCircuitDoesNotExist(315),
		encapsulationIsNotAllowedOnSameSegment(316),
		encapsulationDoesNotMatchProtocolBasedVLAN(317),
		invalidDvmrpIfTblEnableValue(318),
		invalidDvmrpIfTblMetricValue(319),
		ipHostPartForSubnetAddrIsNonZero(320),
		globalMulticastNotEnabled(321),
		metricFieldIsCreatedButModified(322),
		invalidIpMRouteInterfaceTblTtlValue(323),
		invalidUdpPortNumber(324),
		invalidUdpProtocolNameLength(325),
		cannotModifyUdpProtocolName(326),
		udpProtocolEntryDoesnotexists(327),
		duplicateUdpProtocolEntry(328),
		cannotDelUdpProtocolEntryFwdEntriesExists(329),
		udpBroadcastIntfEntryDoesnotExists(330),
		duplicateUdpBroadcastIntfEntry(331),
		invalidUdpConfBroacastInterface(332),
		updConfIntfEntryNotEnabledForUdpBcastForwarding(333),
		udpPortFwdEntryDoesnotExists(334),
		duplicateUdpPortFwdEntryDoesnotExists(335),
		udpPortFwdEntryUdpPortInterfaceDoesnotExists(336),
		udpPortFwdListEntryDoesnotExists(337),
		duplicateUdpPortFwdListEntryDoesnotExists(338),
		udpPortFwdListEntryPortFwdIdDoesnotExists(339),
		udpPortFwdListEntryinvalidFwdIdListSize(340),
		cannotDeleteUdpPortFwdListEntryInterfaceUsingThisList(341),
		invalidIgmpSnoopDestAddress(342),
		invalidIgmpSnoopHostAddress(343),
		cannotDeleteDefaultUdpProtocolTblEntry(344),
		nextHopRouteIsStaticRoute(345),
		invalidUpdateIntervalValueInDVMRPGlobalTable(346),
		invalidTriggeredUpdateIntervalValueInDVMRPGlobalTable(347),
		invalidLeafTimeoutValueInDVMRPGlobalTable(348),
		invalidNbrTimeoutValueInDVMRPGlobalTable(349),
		invalidNbrProbeIntervalValueInDVMRPGlobalTable(350),
		invalidQueryIntervalValueInIgmpInterfaceTable(351),
		invalidVersionValueInIgmpInterfaceTable(352),
		invalidQueryMaxResponseTimeValueInIgmpInterfaceTable(353),
		invalidRobustnessValueInIgmpInterfaceTable(354),
		invalidLastMembQueryIntvlValueInIgmpInterfaceTable(355),
		invalidANDMaskInRcIpTosRuleGroup(356),
		invalidORRule1InRcIpTosRuleGroup(357),
		invalidORRule2InRcIpTosRuleGroup(358),
		invalidORRule3InRcIpTosRuleGroup(359),
		deleteStaticPortNotValid(360),
		maxEntriesForIgmpAccTbl(361),
		maxMaskNumberOfHostIgmpAccTbl(362),
		dvmrpIgmpExclusive(363),
		theSpecifiedAreaRangeMaskIsInvalid(364),
		invalidLengthOf2kBootConfigImageSource(365),
		invalidLengthOf2kBootConfigSource(366),
		preferenceOfStaticRouteIsInvalid(367),
		copyFileOutOfSpace(368),
		copyFileFileNotFound(369),
		copyFileInvalidDestination(370),
		copyFileInvalidSource(371),
		copyFileFail(372),
		invalidLinkFlapDetectAutoPortDown(373),
		invalidLinkFlapDetectFrequency(374),
		invalidLinkFlapDetectInterval(375),
		invalidLinkFlapDetectSendTrap(376),
		invalidQosLevel(377),
		invalidQosWeight(378),
		invalidQosThreshold(379),
		invalidTagToQosTableIeee1pValue(380),
		invalidTagToQosTableQosLevel(381),
		invalidDsFieldToQosTableDsField(382),
		invalidDsFieldToQosTableQosLevel(383),
		invalidQosToTagTableQosLevel(384),
		invalidQosToTagTableIeee1pValue(385),
		invalidQosLevelValue(386),
		invalidQosToDsFieldTableDsFieldValue(387),
		invalidQosToDsFieldTableQosLevel(388),
		invalidDiffServEnable(389),
		invalidDiffServType(390),
		invalidIeeeOverride(391),
		invalidVlanQosValue(392),
		invalidVlanTosValue(393),
		operationNotAllowedOnAccessPort(394),
		operationNotAllowedOnTaggingPort(395),
		invalidFileName(396),
		invalidDiaglogueDuplicateMirroredPort(397),
		invalidDiaglogueEnableValue(398),
		invalidDiaglogueEnableSetting(399),
		invalidDiaglogueModeSetting(400),
		invalidDiaglogueEntryId(401),
		srcMacVlanIsNotYetEnabled(402),
		srcMacVlanIsNotYetDisabled(403),
		invalidDiaglogueOperation(404),
		invalidMacAddressSpecied(405),
		maxResponseTimeGreaterThanQueryInterval(406),
		noModifyDsFltrAllowedOnDiffSrvCorePort(407),
		mltMoreThan4PortsInMgMlt(408),
		protocolRulesForThePortHasExceeded16(409),
		routeDoesNotExistsInTheRroutingTable(410),
		diagMirrorByPortTableAccessError(411),
		diagMirrorByPortInvalidMirroringPortSetting(412),
		igmpAdminVersionConfiguredLessThanOperatingVersion(413),
		canOnlyConfigureViaMltTable(414),
		dvmrpInterfaceTableIsFull(415),
		invalidDscpField(416),
		invalidDscpReservedField(417),
		disablePortPriorToChangingDiffServPortType(418),
		ipFilterInvalidId(419),
		rateLimitingExceeded(420),
		diagEntryMaxExceeded(421),
		onlyOneMirroringPortAllow(422),
		radiusServerExist(423),
		radiusServerNotExist(424),
		radiusServerInUse(425),
		radiusMaxServerNumExceeded(426),
		radiusInvalidAttribute(427),
		canNotChangeLocking(428),
		activationDisabled(429),
		zeroMac(430),
		atmBadVpi(431),
		atmBadVci(432),
		atmBadFramingMode(433),
		atmDestroyPvcFailed(434),
		atmBadName(435),
		atmBadEnable(436),
		atmBadpvcEncapsulation(437),
		atmBadPvdServiceType(438),
		atmBadPeakCellRate(439),
		atmBadSustainedCellRate(440),
		atmBadMaxBurstSize(441),
		atmBadMaxMtuSize(442),
		atmBadElanId(443),
		atmUnknownOperation(444),
		atmDestroy1483ElanFailed(445),
		atmBadPerformTagging(446),
		atmIlleagalElanDefinition(447),
		atmCreate1483ElanFailed(448),
		atmBadSnmpMessage(449),
		atmBadScrambleEnable(450),
		atmBadSignalingEnable(451),
		atmBadClockSource(452),
		atmBadLoopback(453),
		badRowStatus(454),
		atmBadLaneConfigMode(455),
		atmLecCreationFailed(456),
		atmBad1438Inarp(457),
		atmF5StartFailed(458),
		atmBadPvcId(459),
		atmBadConnectType(460),
		atmBadIpxEncapMethod(461),
		atmBadUniVersion(462),
		atmCreatePvcFailed(463),
		invalidLoginPromptLength(464),
		invalidPasswordPromptLength(465),
		invalidCliBannerLength(466),
		invalidCliBannerSize(467),
		invalidCliMotdLength(468),
		invalidCliMotdSize(469),
		invalidPortNameLength(470),
		invalidPortName(471),
		invalidMaxAdvertiseInterval(472),
		invalidMinAdvertiseInterval(473),
		invalidMaxInitialAdvertiseInterval(474),
		invalidMaxInitalAdvertments(475),
		invalidNeigborDeadInterval(476),
		invalidUserSetTimeYearValue(477),
		invalidUserSetTimeMonthValue(478),
		invalidUserSetTimeDateValue(479),
		invalidUserSetTimeHourValue(480),
		invalidUserSetTimeMinuteValue(481),
		invalidUserSetTimeSecondValue(482),
		rtcIsNotPresent(483),
		rtcIsNotRunning(484),
		maxMacCount(485),
		maxAdvertiseIntLessThanMinAdvertiseInt(486),
		minAdvertiseIntGreaterThanMaxAdvertiseInt(487),
		dvmrpNotEnabledGlobally(488),
		vrrpCriticalIpAddrNotEnable(489),
		vrrpInvalidCriticalIpAddr(490),
		metricConfigNotAllowed(491),
		posActiveNonBcpEnabledPort(492),
		posVlanNoMorePorts(493),
		posPortCanBeAdded(494),
		posNonBcpCanNotBeEnabled(495),
		posImageFilenameTooLong(496),
		posNoIpcpEnableOnMltPorts(497),
		posNoIpcpEnableOnTagPort(498),
		posNoIpxcpEnableOnMltPort(499),
		posNoIpxcpEnableOnTagPort(500),
		posDisableTagBeforeBcpDisable(501),
		posAssignIpBeforeIpcpEnable(502),
		posAssignIpxBeforeIpxcpEnable(503),
		posAssignIpBeforeRemoteIp(504),
		posKeepRemoteIpInSameSubnet(505),
		staticRouteEnabled(506),
		cannotChangeAutoLearnState(507),
		invalidVirtualIpAddr(508),
		virtualAndPhysicalIpNotInSameSubnet(509),
		vidNotAvailable(510),
		mgidNotAvailable(511),
		posNoIpcpEnableOnPolicyVlanPort(512),
		posNoIpxcpEnableOnPolicyVlanPort(513),
		posVrrpNotAllowed(514),
		webInvalidHttpPort(515),
		cannotAddMulticastStaticMac(516),
		posNoStpEnableWithBCPClosed(517),
		posAtmNoRip1(518),
		ipfFilterNumOverFilterSetLimit(519),
		ipfQosTrafficAverageRateOverLimit(520),
		ipfQosTrafficProfileNotExist(521),
		atmNoIpIpxConfigOnVlan(522),
		atmPvcIsInUse(523),
		globalFilterNotDisabled(524),
		dhcpNotOnByIpSubnetVlan(525),
		cannotConfigureDefaultGateway(526),
		routeExists(527),
		gatewayNotOnMgmtInterfaceSubnet(528),
		mgmtRouteTableFull(529),
		routeNotExists(530),
		invalidMacOffsetRangeForBW(531),
		invalidMacOffsetRangeForMG(532),
		atmPvcBadPeakCellRate(533),
		atmPvcBadSustainedCellRate(534),
		qosReservedQosLevel(535),
		dvmrpGlobInvalidFwdCacheTimeOut(536),
		dvmrpGlobInvalidRouteExpireTimeOut(537),
		dvmrpGlobInvalidRouteDiscardTimeOut(538),
		dvmrpGlobInvalidRouteSwitchTimeOut(539),
		pimCondRPGroupExists(540),
		pimCandRPAddressInvalid(541),
		pimGroupAddressInvalid(542),
		pimNotEnabled(543),
		pimInvalidJPInterval(544),
		pimInvalidMode(545),
		pimInvalidHelloInt(546),
		pimInvalidCBSRPRef(547),
		pimInvalidEnable(548),
		pimAlreadyEnabled(549),
		ipDvmrpAlreadyEnabled(550),
		ospfIntfChangeNotAllowedWhenEnabled(551),
		ospfIntfChangeFromNBMANotAllowed(552),
		ospfPollIntIsnotMultOfHelloInt(553),
		ospfNeigNoCircuit(554),
		ospfNeigSameIp(555),
		ospfCircNotNBMA(556),
		ospfCircPriZero(557),
		ospfNBMANeigExist(558),
		ospfNBMANeigNotFound(559),
		ospfDynNeigExist(560),
		pgmInvalidSessionLifetime(561),
		pgmInvalidMaxRetxStates(562),
		pgmInvalidMaxSessions(563),
		pgmInvalidIfNakRetxInterval(564),
		pgmInvalidIfMaxNakRetxCnt(565),
		pgmInvalidIfNakRdataInt(566),
		pgmInvalidIfNakElimInt(567),
		maxOfMirroringPortAllowedExceed(568),
		duplicatedRoutePolicyEntry(569),
		specifiedRoutePolicyEntryNotFound(570),
		specifiedPrefixListNotFound(571),
		routePolicyListNotSpecify(572),
		routePolicyPrefixListOverLimit(573),
		ipPrefixListDuplicate(574),
		ipPrefixListDuplicateEntry(575),
		ipPrefixListEntryNotFound(576),
		ipPrefixListInvalidName(577),
		ipRedistributeDuplicateEntry(578),
		ipRedistributeEntryNotFound(579),
		ipOspfInFilterDuplicateEntry(580),
		ipOspfInFilterEntryNotFound(581),
		ipEcmpNotDisabled(582),
		ipEcmpMaxExceeded(583),
		ipfQosTrafficAvgRateZeroProfileEnable(584),
		ipmTimePruneEntryInvalidGroup(585),
		ipmTimePruneEntryDuplicate(586),
		ipmTimePruneEntryNotExist(587),
		ipmTimePruneEntryInvalidExpireTime(588),
		smltIstExist(589),
		smltSmltIdExist(590),
		smltIstNotExist(591),
		smltSmltIsEnabled(592),
		smltSmltLocalIpNotExist(593),
		smltInvalidPortTypeForIstMlt(594),
		ntpServerAlreadyExist(595),
		ntpServerDoesNotExist(596),
		ntpKeyAlreadyExists(597),
		ntpKeyDoesNotExist(598),
		ntpMaxKeyExceeded(599),
		ntpServerAlreadyEnabled(600),
		ntpServerAlreadyDisabled(601),
		ntpNoServerConfigured(602),
		ntpMaxServerNumExceeded(603),
		ntpInvalidIntervalValue(604),
		ecmpNotEnabled(605),
		ipfInvalidProtocolType(606),
		assignIpToPortInRouteVlan(607),
		assignIpToVlanWithRoutePortMember(608),
		ipfIstPort(609),
		smltMltIpfExist(610),
		smltMltPortIpfExist(611),
		smltL2fIstPort(612),
		smltMltL2fExist(613),
		smltMltPortL2fExist(614),
		portMirroringEgressNotSupportFullDuplexMode(615),
		pimGlobInvalidRegSupprTimeOut(616),
		smltNotAvailableIn8100(617),
		mltNoPort(618),
		mltInvalidPortType(619),
		inUsedByATM1483Elan(620),
		smltIstStpEnableNotAllowed(621),
		invalidHighestVrrpPrio(622),
		dynamicPortMemberIn8100IsNotAllowed(623),
		ipfGlobalNextHopModeNotSupported(624),
		smltPeerIpNotExist(625),
		smltMltNoThisVlan(626),
		smltNotANormalMlt(627),
		validStaticRtExist(628),
		validBlkHolRtExist(629),
		pimOrIgmpAlreadyEnabled(630),
		routePolicyOverSystemLimit(631),
		routePolicyOverVrfLimit(632),
		ruleFieldnotAllowed(633),
		ipRouteParamValueInValid(634),
		ipInterfaceNotExist(635),
		questionMarkNotAllowedInsideTheNameString(636),
		snmpTrapTargetIpAndSourceIpMustBeSameType(637),
		ntpVersionInvalid(638),
		readWriteAccessReadOnly(900),
		readWriteAccessLevelOne(901),
		readWriteAccessLevelTwo(902),
		readWriteAccessLevelThree(903),
		readWriteAccessReadWrite(904),
		readWriteAccessReadWriteAll(905),
		readWriteAccessUnknownLevel(906),
		eapolEnabledPortsCannotBeAddedToMlt(8005),
		eapolNotAllowedOnMltPorts(8006),
		cannotConfigureLacpOnEapolEnabledPorts(8007),
		nonEapolPasswordFormatCannotBeEmpty(8008),
		multiHostMacMaxCannotBeChangedOnEapolEnabledPorts(8009),
		eapolNotAllowedOnVlacpEnabledPorts(8010),
		vlacpCannotBeEnabledOnEapolPorts(8011),
		macsecNotAllowedOnEapolPorts(8012),
		eapolNotAllowedOnMacsecPorts(8013),
		eapolCannotBeConfiguredOnIsisInterface(8014),
		isisConfigurationNotAllowedOnEapolEnabledPorts(8015),
		eapolNotAllowedOnFlexuniFaInterface(8016),
		eapolNotAllowedOnPrivateVlanInterface(8017),
		communityAlreadyExists(9101),
		communityDoesnotExist(9102),
		communityStorageTypePermanent(9103),
		defaultEntryNotDeletable(9104),
		invalidAccessPolicyStrict(9105),
		targetAddressNotExist(9106),
		cannotChangeCurrentAndDeprecatedMib(9107),
		invalidPath(9108),
		duplicateTargetAddress(9110),
		notifyTagIsOnlyAllowedUpTo32Chars(9112),
		authenticationFailureTrapMustBeEnabledFirst(9113),
		macFlapLimitTimeNotValid(9114),
		udpSrcByVipCannotBeEnabledWithoutVip(9115),
		configFileNameIsRequiredForSaveToSlave(9116),
		noSpaceAllowedInFilename(9117),
		noSpaceAllowedInPathname(9118),
		cannotDeleteAllMgmtVirtualIpWhenUdpSrcByVipEnabled(9119),
		invalidSaveConfigFilename(9120),
		notAllowToCreateOrDeleteNotifyEntry(9121),
		entityIsNotPresentOnDevice(9122),
		topologyCommandNotSupported(9123),
		commInUseByCloudIq(9124),
		targetInUseByIQAgent(9125),
		groupInUseByIQAgent(9126),
		rmonMemFail(9201),
		rmonEnableMustCreateIpHostFirst(9202),
		deleteIpHostMustDisableRmonFirst(9203),
		rmonMaxHostReached(9204),
		rmonInvalidOwnerValue(9205),
		cannotChangeInterfaceRmonWhenGlobalRmonDisabled(9206),
		rmonIsDisabled(9207),
		rmonAlarmInvalid(9208),
		rmonUnwritable(9209),
		rmonEventInvalid(9210),
		rmonOidNotFound(9211),
		rmonOidInvalid(9212),
		rmonEventInUse(9213),
		rmonIncompleteRequest(9214),
		rmonInvalidCharInDescription(9215),
		rmonInvalidCharInCommunity(9216),
		rmonMaxStatsReached(9217),
		rmonMaxHistoryControlReached(9218),
		rmonMaxHistoryEthernetReached(9219),
		rmonMaxAlarmsReached(9220),
		rmonMaxEventsReached(9221),
		rmonAlarmThresholdNeeded(9222),
		rmonHistoryIntervalCannotBeModifiedAfterCreation(9223),
		rmonCannotConfigMgmtVlan(9224),
		rmonMgmtDeleteIpHostMustDisableRmonFirst(9225),
		rmonMgmtDisableDhcpClientMustDisableRmonFirst(9226),
		maskIsNonEditable(9227),
		rmonMgmtEnableRmonMustDisableDhcpClientFirst(9228),
		portMirroringTxNotSupportForThisHardwareRevision(9301),
		cannotSetMode(9302),
		cannotSetFraming(9303),
		cannotModifyInLaneMode(9304),
		stpIsNotAllowedToBeEnabledOnIstPort(9305),
		mirroredPortSupportRXModeOnly(9306),
		secondaryCpuNotActive(9307),
		commandNotAllowedInPrimaryCpu(9308),
		pcapUserDefinedDataInConsistency(9309),
		pcapFilterTblEntryNotFound(9310),
		pcapFilterTblDuplicateEntry(9311),
		pcapBufferSizeExceedsMaximumRamLimit(9312),
		portPcapIsActive(9313),
		pcapCommandNotAllowedWhenPcapIsEnabled(9314),
		invalidNumberOfHexDigits(9315),
		commandNotAllowedInHaCpuMode(9316),
		pcapCommandNotAllowedIn3SlotChassis(9317),
		pcapNoMemoryAllocatedForPcap(9318),
		pcapCannotBeEnabledWhenAutosaveInProgress(9319),
		pcapInvalidTimerRangeValue(9320),
		cannotSetPortAdminRouting(9322),
		smltNotAllowedObBrouterPort(9323),
		pcapOctapidNotInitialized(9324),
		pcapNoPackets(9325),
		pcapInsufficientDiskSpace(9326),
		pcapAutoSaveOrCopyCommandInProgress(9327),
		rmCommandNotAllowedWhenRemoteMirroringIsEnabled(9328),
		rmVlanNotPortBasedVlan(9329),
		rmPortNotMemberOfVlan(9330),
		rmSrcMacAddressNotSet(9331),
		rmRemoteMirroringActiveInOctapd(9332),
		rmRmtExceedsMaxLimit(9333),
		rmVlanIdNotSetForRmtPort(9334),
		rmDstMacNotSet(9335),
		rmPortDuplicateEntry(9336),
		rmPortEntryNotCreated(9337),
		rmRemoteMirroringActiveInRspLane(9382),
		portEapAuthorized(9345),
		portEapEnabled(9362),
		rateLimitingrmodPort(9363),
		bandwidthLimitingNonrmodPort(9364),
		egressRateLimitingNotAppToNonRModPort(9365),
		featureNotApplyToMixedMlt(9368),
		rateLimitingExistsForMlt(9369),
		differentPortConfigurationForMlt(9370),
		rModuleOnlyOneMirroredPortPerLane(9371),
		ieee8021pOverrideNotAppToNonRModPort(9372),
		portMirroringTxFilterNotSupportForThisHardwareRevision(9373),
		portIsDownOperationNotAllowed(9374),
		portSffdEnableError(9375),
		portTxFlowControlNotSupportedForThisHW(9376),
		portFcPause0NotSupportedForThisHW(9377),
		portFcPauseTimeNotSupportedForThisHW(9378),
		slppInvalidTxInterval(9380),
		slppInvalidRxThreshold(9381),
		cannotSetClockSource(9394),
		ingressPoliceNonRsPort(9395),
		customAutoNegAdvertNotSupported(9396),
		autoNegotiateIsDisable(9397),
		slppInvalidEtherType(9398),
		recordReserveTypeInvalid(9401),
		recordReserveOutOfRange(9402),
		recordReserveExceedPhyLim(9403),
		cannotUpNonEticketCard(9404),
		cannotUpNon128KCard(9405),
		naapVlanNotConfigured(9406),
		lpMiniSlotNotPresent(9407),
		lpSlotDisabled(9408),
		lpSlotEnabled(9409),
		cannotUpNonEmmodeCard(9410),
		cannotUpNonRmodeCard(9411),
		cannotUpNonRspCard(9412),
		dnsDuplicateEntry(9413),
		dnsEntryNotFound(9414),
		dnsEntryNotCreated(9415),
		smartCpldNotSupported(9416),
		slotNotPresent(9418),
		rmodeRequired(9419),
		maxVlanDisallow(9420),
		softwareLicenseViolation(9425),
		cpuActionNotAllowed(9426),
		resetOperNotAllowed(9427),
		cpuActionNotAllowedPwrPrio(9428),
		yearAllowedToBeSetExceeds(9438),
		adminStatusCannotBeModifiedOnMasterCP(9439),
		resetOnlyAllowedOnStandbyCPOrIOCardOrSFCard(9440),
		cardIsNotPoweredOn(9441),
		adminEnableOrDisableIsOnlyAllowedOnIOCard(9442),
		powerPriorityOfCPCannotBeModified(9443),
		powerPriorityCannotBeModifiedOnSF1andSF4(9444),
		powerPriorityCannotBeModifedOnThisSlot(9445),
		poweringDownOfMasterCPIsNotAllowed(9446),
		powerDownOnlyAllowedOnIOAndSFSlot(9447),
		powerIsAlreadyOn(9448),
		powerIsAlreadyDown(9449),
		dnsEntryCannotBeCreatedWithoutAddress(9450),
		dnsServerIpv6AddressNotSupported(9451),
		powerPriorityCannotBeSetToCritical(9452),
		fabStatsCaptureCannotBeEnabledWithoutPort(9453),
		resetOnlyAllowedOnOneManagementSFCard(9454),
		onlyOneManagementSFCardPowerDown(9455),
		slotResetNotAllowedOnVsp4000(9459),
		invalidSlotNumber(9460),
		advancedSoftwareLicenseViolation(9461),
		premierSoftwareLicenseViolation(9462),
		fabStatsCaptureCantBeEnabledWhenAddingNewPort(9463),
		fabStatsCaptureEnableForOnePortOnly(9464),
		fabStatsCaptureAlreadyEnabled(9465),
		cannotPowerGen1CardWhenSwitchIsRunningInGen2Mode(9466),
		cannotEnableOrResetGen1CardWhenSwitchIsRunningInGen2Mode(9467),
		slotResetNotAllowed(9470),
		slotShutdownNotAllowedOnThisPlatform(9471),
                chassisOnlySupportBaudRate(9472),
	        cannotResetOrPowerOffTheOnlyOperationalSFInTheChassis(9473),
		coredumpNotAllowedOnHA(9476),
		adminVimSpeedNotSupportedForThisHW(9477),
		dnsUserCantCreateDynamicEntry(9482),
		duplicateClipInterfaceName(9485),
		tenGEMltPortCannotBeAddedToStgWithSMLT(9501),
		tenGEPortCannotBeAddedToStgWithSMLT(9502),
		rstpInvalidVal(9504),
		mstpInvalidVal(9505),
		mstpOperationNotAllowed(9542),
		priorityValueMustBeAMultipleOf4096(9510),
		switchIsNotInRstpMode(9514),
		switchIsNotInMstpMode(9515),
		maxAgeMustEqualOrGreatThan2XPortHelloTimePlus1Second(9520),
		pbtStgCannotEnableStp(9521),
		maxAgeMustEqualOrLessThan2XForwardDelayMinus1Second(9529),
		mappingExistsForInstanceUnmapVlansFirst(9535),
		plsbMstpInstanceAllowedOnlyInMstpMode(9536),
		plsbStgInstanceCannotBeRemovedWhenPlsbVlanExists(9537),
		stgInstanceCannotBeSetToPlsbType(9538),
		plsbMstiCannotEnableForcePortState(9539),
		pcapDumpCommandInProgress(9555),
  		fdbEntryCantBeDeleted(9556),
                fdbEntryNotFound(9557),
                fdbEntryNotFoundInPort(9558),
                fdbEntryNotFoundInVlan(9559),
		ospfOverlappingSummarizedRange(9601),
		ospfHelloIntNotGreatDeadInt(9605),
		invalidOperation(9608),
		ospfInterfaceLimitExceeded(9609),
		ospfAreaLimitExceeded(9610),
		ospfEnableNotAllowedOnDvrVlan(9611),
		cluserInvalidId(9901),
		clusterDoesNotExist(9902),
		clusterAlreadyExists(9903),
		clusterSizeExceeded(9904),
		invalidMiniSlot(9905),
		brouterOpNotAllowedOnIsdPort(9907),
		clusterIdMandatory(9906),
		removeVlanBeforeDeletingCluster(9908),
		vlanWithIPXEnabledCannotAdd10GEPortOrMlt(1101),
		addRemDsapSsapNotAllowed(1102),
		maxDsapSsapExceeded(1103),
		vlanInvalidEncap(1104),
		vlanEnforcementNotAllowed(1109),
		vlanNaapVlanPortMustBeTagged(1110),
		vlanRegPortNotAllowedInNaapVlan(1111),
		vlanFwPortNotAllowedInRegVlan(1112),
		invalidVlanIdSpecified(1113),
		retrieve10GEInfoFailure(1115),
		minMacGreaterThanMaxMac(1116),
		maxMacLessThanMinMac(1117),
		prPortNotForStackedVlan(1121),
		prPortNotForIPXVlan(1122),
		vlanAgingTimeNotAppToStaticVlan(1123),
		naapInvalidVlanId(1126),
		clusterIsdAlreadyUsed(1129),
		regularPortsNotAllowedInPeeringVlan(1130),
		regularPortsNotAllowedInClusterSyncVlan(1131),
		mltSdmPortNotAllowed(1132),
		clusterIdNotAllowedForNormalVlan(1133),
		clusterTypeNotSupported(1134),
		clusterMgmtSyncVlanCannotBeSame(1135),
		nsnaPortNotConfigurable(1138),
		nsnaUplinkOperationNotAllowed(1139),
		clusterTpsSizeExceeded(1145),
		clusterNotFwIsd(1148),
		clusterNotTpsIsd(1149),
		vlanFwPortDelNotAllowedInRegVlan(1151),
		fwPortNotAlwdForClusterTypeIs(1152),
		syncVlanNotAlwdForClusterTypeIs(1153),
		portMemberNotAlwdForNonIsCluster(1154),
		portMemberOfIsClusterCannotBeSdmPort(1155),
		portHasPcapEnabled(1156),
		portInSameOctapidAsIsCluster(1157),
		pcapInvalidTypeForAclFilter(1160),
		rmodOnlyOnePcapPortPerLane(1161),
		rstpOnlyDefaultInstanceAllowed(1174),
		maxSubnetVlanReached(1185),
		maxProtocolVlanReached(1186),
		cannotCreateFilterEntryForTdpMac(1187),
		entryAlreadyExists(1188),
		macIsConfiguredAsStaticMacInVlan(1189),
		macHasBeenLearntConfiguredInVlan(1190),
		macIsBeingUsedAsLoopDetectMac(1191),
		cannotCreateFilterEntryForLocalMac(1192),
		cannotCreateFilterEntryForBpudMac(1193),
		cannotUntagPort(1196),
		duplicateProtocolIdRecord(1197),
		cannotAddPortsToPlsbBVlan(1198),
		unsupportedVlanType(1199),
		dynModMaxModule(1201),
		dynModUnknown(1202),
		dynModAlreadyLoaded(1203),
		dynModCantOpenFile(1204),
		dynModNotEnoughSpace(1205),
		circuitlestInvalidIpInterfaceId(1501),
		circuitlessMaxNumberIpInterfacesReached(1502),
		circuitDoesNotExist(1503),
		circuitAlreadyExists(1504),
		circuitlessIpInterfacesOperationNotAllowed(1505),
		priority255SpecialForPhyIpSameAsVrIp(1506),
		icmpRdiscInvalidPreferenceLevel(1507),
		icmpRdiscAdvAddrIsNotBroadcastOrMulticastAddr(1508),
		icmpRdiscInvalidMaxAdvInt(1509),
		icmpRdiscMinAdvIntvGreaterThanMaxAdvIntvOrLessThan3Secs(1510),
		icmpRdiscLifeTimeLessThanMaxAdvIntvOrGreaterThan9000Secs(1511),
		vrrpInvalidFasterAdvertInterval(1512),
		vrrpFasterAdvEnabled(1513),
		vrrpFasterAdvDisabled(1514),
		vrrpInvalidFastAdvEnableValue(1515),
		globalFiltersNotSupportFwdingNextHopMode(1516),
		vrrpPreemptActionNotAllowed(1517),
		rcPimModeIgmpVersionIncompatible(1518),
		invalidOrInconsistentBroadCastMaskValue(1519),
		invalidRipTimeoutInterval(1520),
		rsmltNoCirc(1521),
		rsmltInvalidHoldUpTimer(1522),
		rsmltNoBrouter(1523),
		rsmltNoIst(1524),
		vrrpSetWithRsmltEnable(1527),
		rsmltSetWithVrrpEnable(1528),
		ipEcmpMaxPathExceeded(1530),
		ipEcmpPathListNotAllowedInRmode(1531),
		featureAppliesToRmodulePortsOnly(1532),
		invalidVrrpEntry(1533),
		invalidIpOwnerVrrpPrio(1534),
		circuitlessIpUsedByIpvpnRD(1537),
		arpDeleteSupportedOnlyForDynamicArps(1542),
		arpMulticastMacAddressNotAllowed(1544),
		arpBroadcastMacAddressNotAllowed(1545),
		arpNoIpAddrAssociatedWithPort(1546),
		arpIncorrectIpAddress(1547),
		arpEntryCreateionRequiresMacAddress(1549),
		arpEntryMofifcationNotAllowed(1550),
		interfaceDoesNotHaveIpAddressAssigned(1551),
		cannotConfigSameAddrWithDiffPrefixLength(1552),
		cannotConfigureAddrWhichIsSiteLocal(1553),
		portEnteredNotAssociateWithVRF(1554),
		cannotDeleteLocalArpEntry(1555),
		invalidArpType(1556),
		arpEntryDoesNotExist(1557),
		vlanEnteredNotAssociateWithVRF(1558),
		cannotAddLocalArpEntry(1559),
		ipEcmpMaxPathIs4ForVsp4000(1560),
		ipPrefixListMaskLenGeValueGreaterThanLeValue(1561),
		systemRequiresAdvancedLicenseToCreateMoreThanOneIpAddress(1562),
		vrrpCriticalIpAddrEnabled(1563),
		vrrpDefaultNonCriticalIpAddress(1564),
		ipCreateInsufficientResource(1567),
		rsmltEnableInsufficientResource(1568),
		vrrpEnableInsufficientResource(1569),
		vrrpIpAddressAlreadyUsedForAnotherVrrpId(1570),
		broadcastIpAddressNotSupported(1571),
		vrrpAuthTypeChangeNotAllowed(1572),
		vrrpAuthKeyChangeNotAllowed(1573),
		vrrpHmacMD5KeyChangeNotAllowed(1574),
		vrrpPreemptModeChangeNotAllowed(1575),
		localRoutePreferenceChangeNotAllowed(1576),
		systemRequiresLicenseInstalledToCreateMoreThanOneIpAddr(1577),
		circuitlessIpUsedByMsdp(1578),
		maxInterfaceCreated(1579),
		portAlreadyInVlan(1580),
		rsmltEnabledOnIPv6InterfaceInNonDefaultVrf(1581),
		vridUsedByDvr(1582),
		ipAddrCannotBeSetIfMgmtVlanExist(1583),
		cannotSetIpAddrNameWithSpecialChar(1584),
		cannotSetRouteNameWithSpecialChar(1585),
		invalidHelpSourcePathname(1601),
		invalidHelpSourceRemotePathname(1602),
		webInvalidHttpsPort(1603),
		identicalHttpPortHttpsPortNotSupported(1604),
		tcpPortIsReservedForOtherFeature(1605),
		tcpPortIsBeingUsedByHttps(1606),
		tcpPortIsBeingUsedByHttp(1607),
		helpSourcePathnameShouldBeLocalOrRemoteOrUsb(1608),
		helpSourcePathnameShouldBeLocalOrRemote(1609),
		invalidDdmMonitorInterval(1801),
		invalidDdmMonitor(1802),
		invalidDdmTrapsSend(1803),
		invalidDdmAlarmPortdown(1804),
		ddmMonitorConfigurationNotSupported(1805),
		ddmAlarmPortdownConfigurationNotSupported(1806),
		igmpOutOfSsmRange(2301),
		igmpDuplicateSsmTblEntry(2302),
		igmpSsmEntryDoesNotExist(2303),
		igmpSsmTblNotEmpty(2304),
		igmpRpSetExistsInSsmRange(2305),
		igmpCandidateRpExistsInSsmRange(2306),
		igmpIfInvalidQIntervalMrt(2307),
		igmpAlreadyEnabled(2308),
		igmpMaxStreamExceeded(2309),
		igmpStreamLimitAlreadyEnabled(2310),
		igmpStreamLimitNotEnabled(2311),
		igmpPimEnabledInSSMMode(2312),
		igmpDisableV3First(2313),
		igmpSSmConflictsWithSsgEntry(2314),
		igmpSsmCanNotDisableDynamicEntry(2315),
		invalidIpMulticastRange(2316),
		igmpStaticGroupCountExceeded(2317),
		igmpOverlappingStaticRangeNotAllowed(2319),
		igmpCannotEditStaticRecMcastDisabledGloballyOrOnVlan(2320),
		igmpPortMaxStreamExceedsIntfMaxStream(2327),
		igmpQueryMaxResponseUnsupportedOnV1(2328),
		igmpExplicitHostTrackingRequired(2333),
		igmpExplicitHostTrackingUnsupportedOnV1V2(2334),
		igmpCannotDeleteLastPortStaticGroup(2335),
		igmpUnspecifiedPortStaticGroup(2336),
		igmpNotVersion3(2337),
		igmpDisableSsmSnoop(2338),
		portIsRequiredForIgmpStaticEntryCreation(2339),
		snoopCannotBeEnabledWithPim(2340),
		snoopCannotBeEnabledWithDvmrp(2341),
		dvmrpCannotBeEnabledWithSnoop(2342),
		pimCannotBeEnabledWithSnoop(2343),
		igmpFlushActionNotAllowedWhenIgmpSnoopingIsDisabled(2344),
		igmpCannotModifyToGrpAddr(2345),
		igmpImmediateLeaveUnsupportedOnV1(2346),
		igmpStreamLimitCanBeEnabledOnlyOnBrouterOrVlan(2348),
		igmpAccessListIpHostAddressNotConfigured(2349),
		igmpSnoopingCannotBeEnabledWithVist(2350),
		igmpUpnpFilterEnabledCannotChangeIp(2351),
		igmpUpnpFilterAlreadyEnabled(2352),
		ipfStreamAlreadyExists(2401),
		ipfStreamDoesNotExists(2402),
		ipfStreamInvalidStreamType(2403),
		ipfStreamInvalidPortOption(2404),
		ipfStreamNameTooLong(2405),
		ipfStreamInvalidProtocol(2406),
		ipfStreamInvalidDscp(2407),
		ipfDeviceAlreadyExists(2408),
		ipfDeviceUnknownPlatform(2409),
		ipfDeviceUnknownDevice(2410),
		ipfDeviceDoesNotExists(2411),
		ipfDeviceNameTooLong(2412),
		ipfOneZeroIpDestFilterIsAllowed(2413),
		ipfGlobalFilterMaxPerOctapid(2414),
		ipfDeviceMaxPerPort(2415),
		ipfDeviceMaxPerBox(2416),
		ipfDeviceMaxFilterList(2417),
		ipfInvalidRmodPort(2418),
		ipfSourceNextHopModeNotSupported(2419),
		aclErrIdInvalid(2428),
		aclErrNameInvalid(2429),
		aclErrTypeInvalid(2430),
		aclErrNotExist(2431),
		aclErrInUse(2432),
		aclErrExists(2433),
		aceErrAceNotExist(2438),
		aceInvalidMode(2482),
		aceEgressqEgressqnnscInvalid(2483),
		aceMaskOperCannotHaveList(2494),
		aclErrTypeOutVlanInvalidForVsp4k(2495),
		aclErrTypeOutVlanInvalid(2496),
		cannotDeleteIntMltId(2501),
		mltNoThisVlan(2502),
		mltPortsDifferentFramingMode(2503),
		moreThan2PortsInMlt(2504),
		portCannotBeAddedToDefualtVLANWithIPXEnabled(2505),
		portMemberNotSupportSMLT(2506),
		tenGEMltPortOrMltCannotBeAddedToVlanWithSmltMember(2507),
		tenGEMltPortCannotRunTogetherWithSMLT(2508),
		portCannotBeAddedToDefualtVLANWithSMLT(2509),
		tenGEPortOrMltCannotBeAddedToVlanWithSmltMember(2510),
		tenGEPortOrMltCannotRunTogetherWithSMLT(2511),
		tenGEPortNotSupportMcastDistribution(2512),
		tenGEPortNotSupportMLT(2513),
		mltSmltIdAlreadyExists(2514),
		mltInvalidSmltId(2515),
		mltSmltNotConfigured(2516),
		mltSmltAlreadyConfigured(2517),
		mltPortIsMemberOfMlt(2518),
		mltPortIsMemberOfSmlt(2519),
		mltSmltIpAddrNotAllowedOnSltPort(2520),
		mltUsedForLacp(2521),
		mltPortUsedForLacp(2522),
		mltUsedForMlt(2523),
		operationNotAllowedOnMltPort(2529),
		mltNsnaUplinkMismatch(2538),
		mltIdInvalidInNonRmode(2539),
		mltNaapVlanCannotBeAddedToIst(2540),
		mltIstCannotBeCreatedOverMltWithNaapVlan(2541),
		mltNaapCannotBeAddedToMltWithActiveIst(2542),
		mltVrfVlanAndLegacyPortCannotBeMembers(2563),
		cannotUntagMlt(2567),
		mltNameIsReservedAsDefautNameForAnotherMlt(2568),
		quotesNotAllowedInsideTheNameString(2569),
		mltNameIsBeingUsedByAnotherMlt(2570),
		mltCpLimitShutdownOnIstMltNotAllowed(2571),
		peerIpAndIstVlanNotInSameSubnet(2572),
		peerIpAndLocalIpCannotBeSame(2573),
		numOfMltAllowedToBeCreatedExceeds(2574),
		moreThan16PortsInMlt(2575),
		moreThan8PortsInMlt(2576),
		istAndSplitMltTypeNotSuuported(2577),
		mltIstIsNotSupported(2578),
		virtualIstCanBeEnabledOnOnlyOneMlt(2579),
		virtualIstPeerIpMustBeConfiguredBeforeMltVistEnable(2580),
		virtualIstOnMltMustBeDisabled(2581),
		virtualIstAllowedOnlyWhenSpanningTreeModeSetToMstp(2582),
		virtualIstMltCannotBeMemberOfVlan(2583),
		smltAlreadyConfiguredOnMlt(2584),
		istAlreadyConfiguredOnMlt(2585),
		virtIstAlreadyConfiguredOnMlt(2586),
		numOfMltAllowedToBeCreatedExceeds64(2587),
		numOfMltAllowedToBeCreatedExceeds50(2588),
		mltBelongToOnePortBasedVlanForAccessPort(2589),
		virtualIstAllowedOnlyWhenAdvancedFeatureEnabled(2590),
		virtualIstHaNeedsDisabled(2591),
		virtualIstCannotBeEnabledWithPimConfigured(2592),
		virtualIstCannotBeEnabledWithIgmpSnooping(2593),
		haUnsupportedWithVistAndSpb(2594),
		mltNameTooLong(2595),
		numOfMltAllowedToBeCreatedExceeds52(2596),
		numOfMltAllowedToBeCreatedExceeds8(2597),
		asListOverLimit(2601),
		communityListOverLimit(2602),
		mltSmltLacpInvalidKey(2603),
		extCommunityListOverLimit(2606),
		extCommunityInvalidListId(2607),
		extCommunityListIdExceedsRange(2608),
		mcastMltNotEnabled(2701),
		mcastMltInvalidSrcMask(2702),
		mcastMltInvalidGrpMask(2703),
		mcastMltRedistrNotEnabled(2704),
		mcastMltDiscontiguousSrcMaskValue(2705),
		mcastMltDiscontiguousGrpMaskValue(2706),
		mcastMltNotEnabledOnMlt(2707),
		mcastMltPortOnNonEtkt(2708),
		mcastMltConfMaskDisableMcastMlt(2709),
		ipmcTimePruneConflictsWithSsmEntry(2710),
		mcastMltCannotBeDisabled(2712),
		mcastRoutingNotEnabledGlobally(2713),
		rcSnmpSyslogDisableSyslogFirst(2801),
		rcSnmpInvalidSyslogHeader(2802),
		configSyslogHostAddrBeforeEnabling(2803),
		dvmrpMBRNotAllowed(2901),
		dvmrpInvalidIntfTypeChange(2902),
		ipxPolicyNetEntryNotFound(3101),
		ipxPolicyNetDuplicateEntry(3102),
		ipxPolicyNetListEntryNotFound(3103),
		ipxPolicyNetListDuplicateEntry(3104),
		ipxPolicyServEntryNotFound(3105),
		ipxPolicyServDuplicateEntry(3106),
		ipxPolicyServeListEntryNotFound(3107),
		ipxPolicyServListDuplicateEntry(3108),
		ipxPolicyPolicyEntryNotFound(3109),
		ipxPlicyPolicyDuplicateEntry(3110),
		ipxRoutePolicyNetListOverLimit(3111),
		ipxRoutePolicyServListOverLimit(3112),
		ipxPolicyRipOutFilterEntryNotFound(3113),
		ipxPolicySapOutFilterEntryNotFound(3114),
		ipxPolicyRipInFilterEntryNotFound(3115),
		ipxPolicySapInFilterEntryNotFound(3116),
		ipxPolicyIpxNetEntryInvalidName(3117),
		ipxPolicyIpxServEntryInvalidName(3118),
		ipxPolicyPolicyEntryInvalidName(3119),
		vlanHas10GEMemberWhichNotSupportIPX(3120),
		vlanContainUnSupportedPrPort(3121),
		invalidLengthOf2kBootConfigLicenseSource(3401),
		licenseFileDoesNotExist(3402),
		licenseFileIsAlreadyLoaded(3405),
		linecardCompatibilityModeConfigAllowedOnlyOnMasterSlot(3406),
		noValidLicenseFileFound(3407),
		qosRateLimitEnableAllowedOnlyForConsecutiveQueues(3628),
		invalidModeForAtmMDAType(3901),
		atmInvalidPVCEncapTypeForElan(3902),
		atmInvalidPVCPCRRange(3903),
		unsupportedVPI(3904),
		radiusAuthAcctAttrSame(4101),
		radiusAuthAcctPortSame(4102),
		radiusAuthAcctNoServerConfig(4103),
		radiusReAuthTimerFailed(4104),
		radiusAbortSesionTimerFailed(4105),
		radiusInvalidSnmpUserLength(4106),
		radiusInvalidCliCommandCount(4107),
		radiusAuthAcctNoServerButSnmpConfig(4112),
		radiusDisableAcctBeforeDeletingLastServer(4113),
		radiusEnableRadiusBeforeEnablingAccounting(4114),
		disableAccountingBeforeDisablingRadius(4115),
		radiusDynAuthMaximumClientsReached(4116),
		radiusDynAuthUdpPortNotInRange(4117),
		radiusDynAuthCannotModifyUdpPort(4118),
		radiusDynAuthSecretKeyTooLong(4119),
		radiusDynAuthCannotModifySecretKey(4120),
		radiusDynAuthUnknownOperationGiven(4121),
		radiusDynAuthSecretKeyRequiredBeforeEnable(4122),
		radiusDynAuthClientNotFound(4123),
		radiusDynAuthUnknownReplayProtection(4124),
		radiusInvalidIpAddress(4125),
		radiusSourceIpNotLocal(4126),
		radiusProfileDefaultLimitations(4127),
		radiusProfileMaxReached(4128),
		radiusProfileExisting(4129),
		radiusProfileNonExisting(4130),
		radiusProfileFileNonexisting(4131),
		radiusProfileFileInUse(4132),
		radiusDtlsModeNotSupported(4133),
		radiusAcctNoServerConfigSnmp(4134),
		radiusDisableAcctBeforeDeletingLastSnmpServer(4135),
		radiusProfileNameOnlyAlphanumeric(4136),
		rtmMaxRouteLicensedLimitReached(4501),
		ripEnableExceedsMaxLimit(4701),
		ripEnableExceedsMaxLimitOn4k(4702),
		ripEnableExceedsMaxLimit200(4703),
		ripEnableNotAllowedOnDvrVlan(4704),
		pimGlobInvalidUniRouteChangeTimeOut(4801),
		pimGlobInvalidDiscDataTimeOut(4802),
		pimGlobInvalidCRPADVTimeOut(4803),
		pimGlobInvalidBootStrapPeriod(4804),
		pimStaticRpEnabled(4805),
		pimStaticRpNotEnabled(4806),
		pimStaticRpEntryExists(4807),
		pimStaticRpNoRoute(4808),
		pimAddressInSsmRange(4809),
		pimInvalidModeChange(4810),
		pimStaticRpNotAllowed(4811),
		pimMBRNotAllowed(4812),
		pimGlobInvalidActChkInterval(4813),
		pimGlobActChkIntervalNotAllowed(4814),
		pimGlobNotSuppActChkInterval(4817),
		pimVirtualNbrInvalidIfIndex(4818),
		pimIntfChangeNotAllowedWhenEnabled(4819),
		pimNotSupportedForMulticastVrf(4820),
		pimFeatureNotSupported(4822),
		pimCandidateRpTableMaxSizeReached(4823),
		pimCandidateRpAdddressAlreadyConfigured(4824),
		rpsMcastMaskLenToNotAllowed(4901),
		ntpSourceIpDoesNotExist(5002),
		brouterIpIsBeingUsedByNtpAsSourceIp(5003),
		clipIpIsBeingUsedByNtpAsSourceIp(5004),
		vlanIpIsbeingUsedByNtpAsSourceIp(5005),
		mgmtPortIsBeingUsedByNtpAsSourceIp(5006),
		mgmtVirtualIpIsBeingUsedByNtpAsSourceIp(5007),
		ntpKeyIncorrectType(5008),
		ntpKeySecretNotConfigured(5009),
		cannotCreateNtpServerUsingAForbiddenIpAddress(5010),
		onlyAlphanumCharsForNtpKey(5011),
		ntpCannotDisableWhenEsEnabled(5014),
		ntpCannotDisableOrDeleteServerWhenEsEnabled(5015),
		ntpCannotChangeVersionWhenNtpEnabled(5016),
		ntpIncorrectNtpVersionSpecified(5017),
		ntpRestrictEntryForbiddenIp(5018),
		ntpRestrictEntryAlreadyExist(5019),
		ntpRestrictEntryDoesnotExist(5020),
		ntpRestrictMaxEntryExceeded(5021),
		ntpRestrictEmptyMaskOrPrefix(5022),
		ntpRestrictUnsupportedAddressType(5023),
		ntpRestrictInvalidIpv4Mask(5024),
		ntpRestrictInvalidIpv6Mask(5025),
		ntpRestrictEntryCannotChange(5026),
		ntpVersionNotSupported(5027),
		tcpConnectionNotFound(5101),
		tcpInvalidState(5102),
		tcpSessionsInUse(5103),
		invalidTcpPortNumber(5104),
		tcpPortIsNotAvailable(5105),
		bgpPeerNotFound(5201),
		bgpInvalidPeerEnable(5202),
		bgpInvalidPeerRemoteas(5203),
		bgpInvalidPeerGroupName(5204),
		bgpInvalidPeerDefaultOriginate(5205),
		bgpInvalidPeerEbgpMultiNop(5206),
		bgpInvalidPeerAdvertisementInterval(5207),
		bgpInvalidPeerPassword(5208),
		bgpInvalidPeerWeight(5209),
		bgpInvalidPeerNextHopSelf(5210),
		bgpInvalidPeerRoutePolicyIn(5211),
		bgpInvalidPeerRoutePolicyOut(5212),
		bgpInvalidPeerRouteReflectorClient(5213),
		bgpInvalidPeerSoftReconfigurationIn(5214),
		bgpInvalidPeerSoftReconfiguration(5215),
		bgpInvalidPeerRemovePrivateAs(5216),
		bgpInvalidPeerRowStatus(5217),
		bgpNetworkNotFound(5218),
		bgpPeerGroupNotFound(5219),
		bgpInvalidPeerGroupEnable(5220),
		bgpInvalidPeerGroupRemoteAs(5221),
		bgpInvalidPeerGroupDefaultOriginate(5222),
		bgpInvalidPeerGroupUpdateSource(5223),
		bgpInvalidPeerGroupEbgpMultiHop(5224),
		bgpInvalidPeerGroupAdvertisementInterval(5225),
		bgpInvalidPeerGroupPassword(5226),
		bgpInvalidPeerGroupWeight(5227),
		bgpInvalidPeerGroupNextHopSelf(5228),
		bgpInvalidPeerGroupRoutePolicyIn(5229),
		bgpInvalidPeerGroupRoutePolicyOut(5230),
		bgpInvalidPeerGroupRouteReflectorClient(5231),
		bgpInvalidPeerGroupSoftReconfigurationIn(5232),
		bgpInvalidPeerGroupSoftReconfiguration(5233),
		bgpInvalidPeerGroupRemovePrivateAs(5234),
		bgpInvalidPeerGroupHoldTime(5235),
		bgpInvalidPeerGroupKeepAlive(5236),
		bgpInvalidPeerGroupRowStatus(5237),
		bgpInvalidPeerGroupGroupName(5238),
		bgpAggregateNotFound(5239),
		bgpInvalidAggregateAsSetGenerate(5240),
		bgpInvalidAggregateSummaryOnly(5241),
		bgpInvalidAggregateSuppressPolicy(5242),
		bgpInvalidAggregateAdvertisePolicy(5243),
		bgpInvalidAggregateAttributePolicy(5244),
		bgpOperationNotAllowedWhenBgpIsEnabled(5245),
		bgpInvalidPeerHoldTime(5246),
		bgpInvalidPeerKeepAlive(5247),
		bgpInvalidPeerMaxPrefix(5248),
		bgpInvalidPeerGroupMaxPrefix(5249),
		bgpInvalidPeerMD5Authentication(5250),
		bgpInvalidPeerGroupMD5Authentication(5251),
		bgpInvalidPeerGroupIndex(5252),
		bgpInvalidConfederationIdentifier(5253),
		bgpInvalidConfederationPeerAsNumber(5254),
		bgpInvalidConfederationPeerNotFound(5255),
		bgpInvalidConfederationPeerAlreadyExist(5256),
		bgpOperationNotAllowedWhenSoftReconfigInIsDisabled(5257),
		bgpNotAllowedSoftRecfgInIsDisabledForTheGrpOrAnyPeerInGrp(5258),
		bgpCanNotEnablePeerWithoutCfgRemoteAsForThePeer(5259),
		bgpCanNotEnablePeerGrpWoCfgRemoteASPeerGrpOrAnyPeerInGrp(5260),
		bgpOperationNotAllowedWhenPeerIsBGPON(5261),
		bgpOperationNotAllowedWhenPeerGrpOrAnyPeerInGrpIsBGPON(5262),
		bgpOperationNotAllowedExternalPeer(5263),
		bgpOperationNotAllowedInternalPeer(5264),
		asListNotFound(5265),
		asListDuplicate(5266),
		asListAsPathEntryNotFound(5267),
		asListAsPathEntryDuplicate(5268),
		asListInvalidModeOfAsPathEntry(5269),
		asListInvalidAsRegularExpressionOfAsPathEntry(5270),
		asListInvalidRowStatusOfAsPathEntry(5271),
		communityListNotFound(5272),
		communityListDuplicate(5273),
		communityListCommunityPathEntryNotFound(5274),
		communityListCommunityPathEntryDuplicate(5275),
		communityListInvalidModeOfCommunityPathEntry(5276),
		communityListInvalidValueOfCommunityEntry(5277),
		communityListInvalidRowStatusOfCommunityEntry(5278),
		bgpFeatureNotSupport(5279),
		bgpMd5EnabledWithoutPasswd(5280),
		bgpEnabledWithoutLocalAs(5281),
		bgpAggregateAdvertisePolicyWithoutAsSet(5282),
		bgpPeerHoldTimeLessThanKeepAliveTime(5283),
		bgpCommListCommunityStringUsed(5284),
		communityListModificationNotAllowed(5288),
		bgpInvalidPeerGroupAsOverride(5289),
		bgpInvalidPeerGroupAllowAsIn(5290),
		bgpInvalidPeerAllowAsIn(5291),
		bgpInvalidPeerAsOverride(5292),
		extCommunityListNotFound(5293),
		extCommunityListModificationNotAllowed(5294),
		extCommunityListInvalidEntry(5295),
		extCommunityListDuplicateMemberId(5296),
		extCommunityListInfoAlreadyExists(5297),
		extCommunityMemberNotFound(5298),
		bgpPeerLimitExceeded(5299),
		bgpPeerIpv6NotSupport(5301),
		extComListCannotCreateWithoutRtOrSooConfig(5302),
		extComListRtAssignedNumMustBeConfigured(5303),
		extComListSooAssignedNumMustBeConfigured(5304),
		bgpPasswdCannotChangedInEstablishState(5305),
		bgpPasswdCannotDeleteWhenMd5Enabled(5306),
		bgpPasswdCannotDeleteForMismatch(5307),
		bgpPasswdCannotDeleteForNonexistence(5308),
		bgpInvalidMaxEqualCostRoutes(5309),
		bgpOperationNotAllowedWhenPeerIsOnAFIPv6Mismatch(5311),
		sshEnableTrue(5501),
		rsaKeyNotExist(5502),
		dsaKeyNotExist(5503),
		rsaKeyGenMiss(5504),
		dsaKeyGenMiss(5505),
		sshShutDownInProcess(5506),
		sshInvalidPort(5507),
		sshPortAlreadyInUse(5508),
		sshPortReserved(5509),
		sshAuthenticationNotEnabled(5510),
		sshUnableToRetrieveGlobalData(5511),
		sshDisabledRekeyCannotEnable(5512),
		sshDisabledSshClientCannotEnable(5516),
		sshVersionNotSupported(5518),
		sshCannotBeDisabledWhenIQAgentIsEnabled(5519),
		sshPassAuthCannotBeDisabledWhenIQAgentIsEnabled(5520),
		invalidOperationOnWsmOrSamStg(5601),
		invalidOperationOnWsmOrSamVlan(5602),
		invalidOperationOnWsmOrSamPort(5603),
		invalidOperationOnSamPort(5604),
		mplsInvalidRouterId(6109),
		lacpInvalidAggrsysPrio(6501),
		lacpInvalidAggrActorAdminKey(6502),
		lacpInvalidAggrColMaxDelay(6503),
		lacpInconsistentKey(6504),
		lacpInvalidVal(6505),
		lacpOutOfRangeKey(6506),
		lacpPortNotAggregatable(6507),
		lacpKeyModificationNotAllowedOnSltPort(6508),
		vlacpTimeoutScaleRangeBetween3To10(6509),
		lacpOtherPortsWithSameKey(6510),
		vlacpOneofPortorMLTIdIsRequired(6511),
		vlacpDuplicatePeerMacAddress(6512),
		vlacpOutOfRangeMac(6513),
		lacpSmltSysIdSyncIncomplete(6514),
		vlacpOperationReqPortVlacpDis(6515),
		vlacpEtherTypeIsInvalid(6527),
		lacpPortsWithSameKeyHaveLosslessMismatch(6528),
		lacpAggregationMustBeDisabledToSetKeyToDefault(6529),
		mirrorByPortNonExistingEntry(6711),
		mirrorEntryNotExist(6712),
		mirrorEntryExists(6713),
		mirrorOneDestAllowed(6714),
		mirrorPortInUse(6715),
		miirorIpNotSupportRemoteVlanId(6716),
		mirrorPortSameAsMirroringPort(6717),
		mirrorPortInConflictWithVlanPort(6718),
		mirrorPortInConflictWithMltPort(6719),
		mirrorPortExistsInAnotherEntry(6720),
		mirroringPortExistsInAnotherEntry(6721),
		mirroredPortsNotConfigured(6722),
		mirroringAndRemoteVlanMustMatch(6723),
		mirroringPortMustExistOnRemoteVlan(6724),
		mirroringMltIsNotPartOfRemoteVlan(6725),
		mirroringVlanShouldHavePortsAssigned(6726),
		mirroringVlanCannotBeRoutable(6727),
		mirroringPortCannotBeBrouter(6728),
		diagEntryWithRemoteMirrorExistsCannotAddIp(6729),
		diagMonitorIpInSameSubnetAsLocalInterface(6730),
		diagEntryWithMonitorIpInSameSubnetExists(6731),
		diagEntryMandatoryParmsNotEntered(6741),
		diagEntryCannotModifyMonitorIsidOffset(6742),
		diagEntryMaxMonitorIsidsReached(6743),
		diagQosNotApplicableForRegularMirroring(6744),
		diagCannotEnableEgressMirroringOnMoreThanOneIsid(6745),
		diagMonitorIsidOffsetAlreadyInUse(6746),
		diagMonitorByIsidTblAccessError(6747),
		diagCantConfigNniFeAssociatedPortsAsIsidMirroringAndViceVersa(6748),
		diagMirroringAndMonitoringSessionsCannotHaveSameIsidOffset(6749),
		diagMirroringAndMonitoringSessionsCannotHaveSamePorts(6750),
		diagCannotRemoveEntryMustHaveEitherEgressPortsOrMltConfigured(6751),
		diagCannotConfigSamePortMltAndVlanForDifferentIsidOffsets(6752),
		diagMltAssociatedWithMonitoringIsidCannotBeDeleted(6753),
		diagEgressPortCannotBeMemberOfEgressMltAndViceVersa(6754),
		diagCantConfigOnaDeviceNetworkPortAsIsidMirroringAndViceVersa(6755),
		diagMonitoringEgressPortCannotBeMemberOfMltAndViceVersa(6756),
		diagCannotConfigurePortMirroringWhenFlowMirroringIsConfigured(6757),
		diagAllAvailableMirrorResourcesAreInUse(6758),
		diagMltUsedAsMonitorDstMltForAceFilterCannotBeDeleted(6759),
		targetAddressMissing(6801),
		testAlreadyRunning(6802),
		invalidTargetAddress(6803),
		invalidSourceAddress(6804),
		controlEntryAlreadyExists(6805),
		invalidIpAddressFormat(6806),
		invalidDataRange(6807),
		invalidIndex(6808),
		entryDoesNotExist(6809),
		controlEntryMaxLimitReached(6810),
		maxRowOutOfRange(6811),
		ipv6VlanDoesnotExist(7401),
		ipv6InvalidInstance(7402),
		ipv6InvalidParameter(7403),
		ipv6AttrNotImplemented(7404),
		ipv6EntryDuplicate(7405),
		ipv6EntryNotExist(7406),
		ipv6InvalidIdentifierLength(7407),
		ipv6CircuitDoesNotExist(7408),
		ipv6PortNotPowerRanger(7409),
		ipv6InvalidInterfaceIdentifier(7410),
		ipv6CannotChangeWhenAdminEnable(7411),
		ipv6InvalidReasmMaxSize(7412),
		ipv6InvalidReachableTime(7413),
		ipv6InvalidPrefixLength(7414),
		ipv6InvalidSendAdverts(7415),
		ipv6InvalidMaxInterval(7416),
		ipv6InvalidMinInterval(7417),
		ipv6InvalidRetransmitTimer(7418),
		ipv6InvalidDefaultLifeTime(7419),
		ipv6InvalidCurHopLimit(7420),
		ipv6InvalidManagedFlag(7421),
		ipv6InvalidOtherConfigFlag(7422),
		ipv6InvalidDadNsNum(7423),
		ipv6InvalidPhysicalAddress(7424),
		ipv6InvalidNetToPhysicalType(7425),
		ipv6NeighborDuplicate(7426),
		ipv6NeighborDoesNotExist(7427),
		ipv6InvalidInvalidIpv6Addr(7428),
		ipv6PrefixDuplicate(7429),
		ipv6InvalidPrefix(7430),
		ipv6InvalidInterfaceType(7431),
		ipv6NexthopOrIndexReq(7432),
		ipv6NexthopIsLinklocBothIndexHopReq(7433),
		ipv6StaticRouteDistanceReq(7434),
		ipv6StaticRouteDuplicate(7435),
		ipv6StaticRouteInvalid(7436),
		ipv6OspfInvalidRouterId(7437),
		ipv6OspfNotSupported(7438),
		ipv6OspfAreaDoesNotExist(7439),
		ipv6OspfAlreadyExist(7440),
		ipv6OspfInterfaceInvalid(7441),
		ipv6OspfInterfaceExists(7442),
		ipv6OspfInterfaceNotExists(7443),
		ipv6OspfAreaAggregateEntryExists(7444),
		ipv6OspfAreaAggregateEntryDoesNotExist(7445),
		ipv6OspfInvalidAreaRangeMask(7446),
		ipv6OspfAreaCannotModifyBackbone(7447),
		tcpConnectTblPermittedStateIsDelete(7448),
		ipv6InterfaceVlanNotFound(7449),
		ipv6TunnelInterfaceDoesnotExist(7450),
		ipv6TunnelNotImplemented(7451),
		ipv6TunnelInvalidOperation(7452),
		ipv6TunnelInvalidType(7453),
		ipv6TunnelInterfaceAlreadyExist(7454),
		ipv6TunnelRemAddrShldBeZero(7455),
		ipv6VlanDoesNotMatchPreviousVlanid(7456),
		ipv6UvifDoesNotExist(7457),
		ipv6MldNotEnabled(7458),
		ipv6MldInterfaceExists(7459),
		ipv6MldInterfaceDoesNotExist(7460),
		ipv6MldInvalidQueryInterval(7461),
		ipv6MldInvalidVersion(7462),
		ipv6MldInvalidMaxRespdelay(7463),
		ipv6MldInvalidRobvar(7464),
		ipv6MldInvalidLlqi(7465),
		ipv6RedistributionInvalidOperation(7466),
		ipv6InvalidMaxRouterAdvertInterval(7467),
		ipv6InvalidMinRouterAdvertInterval(7468),
		ipv6CannotSetSummaryAsFalseIfNotStubArea(7469),
		ipv6CannotModifyStubMetricIfNotStubArea(7470),
		ipv6GatewayMustBeOnMgmtInterface(7471),
		ipv6OspfNbmaNbrAlreadyExist(7472),
		ipv6OspfInterfaceNotNbma(7473),
		ipv6OspfNbmaTunnelNot624(7474),
		ipv6OspfNbmaNbrNotExist(7475),
		cannotConfigureAddrWhichIsLinkLocal(7476),
		addrEntryDoesNotExist(7477),
		ipv6TunnelCannotHaveMoreThanOneAddr(7478),
		cannotChangeAddressType(7479),
		cannotConfigureNetAddr(7480),
		invalidInetNetworkAndMask(7481),
		cannotConfigureHostAddr(7482),
		ipv6InterfaceIdCannotBeChanged(7483),
		ipv6TunnelLocalAndRemoteIpAddressCannotBeSame(7484),
		ipv6StaticRouteWrongNexthop(7485),
		ipv6EuiInterfacePrefixCannotBeGreaterThan64(7486),
		ipv6CircuitMcastFlagNotSet(7487),
		ipv6MldProxyUnsupported(7488),
		ipv6MtuChangeWhenIntfDisable(7489),
		ipv6OspfNbmaNbrInvalidAddress(7490),
		ipv6AddressAndPrefixSame(7491),
		ipv6IncompatibleAddressTypeAndAddress(7492),
		ipv6DadInProgressTryLater(7493),
		ipv6InterfaceMismatch(7494),
		ipv6StaticNeighborInterfaceNotPresent(7495),
		ipv6RequiresSuperMezz(7496),
		ipv6StaticRouteOnlyIfindexCannotConfigPref(7497),
		ipv6StaticRouteRecursiveRouteNotSupported(7498),
		ipv6TunnelLocalRemoteAddrPairAlreadyExists(7499),
		ipv6DefaultRouteIncorrectMask(7500),
		idInvalid(7501),
		notExist(7502),
		duplicate(7503),
		nameInvalid(7504),
		notenablemixedmlt(7505),
		portconflictmixedmlt(7506),
		cannotConfigureBothNetAndHostAddr(7510),
		ipv6InterVRFRedistributionNotSupported(7511),
		ipv6OspfNbmaNbrPrioritySetFailure(7512),
		redistributionDifferentIpVersionSourceDestination(7513),
		ipv6PrefixLengthZeroNotSupportedForNonDefaultRoute(7514),
		actInUse(7601),
		actFieldTooMany(7602),
		actPatternNotExist(7603),
		actErrApplyStateTrue(7604),
		actMaxPatternExceeded(7605),
		aclActNotExist(7606),
		aclTypeInvalid(7607),
		aclDefActionInvalid(7608),
		aclGlobActionInvalid(7609),
		vlanInvalid(7610),
		portInvalid(7611),
		aclMltInvalid(7612),
		aclInUse(7613),
		aclInvalidState(7614),
		aclActNotApplied(7615),
		aclActVlanAttrSpecified(7616),
		aclActPortAttrSpecified(7617),
		aclPortBased(7618),
		aclVlanBased(7619),
		actNoAttributesConfigured(7620),
		aclErrPortAlreadyInAcl(7621),
		aclErrVlanAlreadyInAcl(7622),
		aceAclIdInvalid(7623),
		aceAclNotExist(7624),
		aceInUse(7625),
		aceMax(7626),
		aceModeIllegal(7627),
		aceDscpIllegal(7628),
		aceDot1pIllegal(7629),
		aceUnreachIllegal(7630),
		acePoliceIllegal(7631),
		aceAclInvlanPoliceNotAllLanes(7632),
		aceInvalidAdminState(7633),
		aceEgressQueueInvalid(7634),
		aceEgressQueue1gInvalid(7635),
		aceEgressQueue10gInvalid(7636),
		aceEgressNNSCInvalid(7637),
		acePoliceInvalidMode(7638),
		aceAttrNotExistInAct(7639),
		aceInsuffActionAttr(7640),
		maxAceForSystem(7641),
		aceValMoreThanActPatternLen(7642),
		aceMltIndexIllegal(7643),
		aceModeNotPermit(7644),
		aceNotPermitIngress(7645),
		aceParmNotDefault(7646),
		aceAttrConflict(7647),
		defaultIdnoCreate(7648),
		defaultIdnoDelete(7649),
		defaultIdnoModify(7650),
		mltPortAclConflict(7651),
		aceNoModeModify(7652),
		aclNoAccept(7653),
		aceDebugMirrorDisableToRemoveDest(7658),
		aclDefActionControl(7659),
		aclStateEnable(7660),
		aclStateDisable(7661),
		aceRedirectMaxLimit(7662),
		aceRedirectNotConfigure(7663),
		aceQosAction(7664),
		aceSecurityAction(7665),
		aceActionMaxCount(7666),
		aceCountActionInvalid(7667),
		aceLogActionInvalid(7668),
		aceInoutPortAction(7669),
		aceInoutVlanAction(7670),
		aceAttListRange(7671),
		acenoIpProtoAttr(7672),
		aceEthVlanList(7673),
		aceMask(7674),
		aceL3L4Config(7675),
		noFreeFilterMirrorIdAvail(7676),
		etherTypeAttribFirst(7677),
		aclTypeCannotBeModified(7679),
		aceInvalidOperMask(7680),
		qosAceCannotHaveDenyMode(7681),
		aceSrcMacInvalidAddr(7682),
		aceNotAllowRemoveAllPortsAfterCreation(7683),
		acePortEntryRequiresOnePortForCreation(7684),
		acePortEntryAllowsOnlyOnePort(7685),
		aceEthVlanIdEntryCreationRequiresOperaiotnAndVlanId(7689),
		aceEthVlanTagPrioEntryCreationRequiresOperAndTagPrio(7690),
		aceInvalidOperMacMask(7691),
		aceEthMacEntryCreationRequiresOperaiotnAndMacAddr(7692),
		aceIpEntryCreationRequiresOperaiotnAndIpAddr(7693),
		aclNoMultipleMirrorDest(7694),
		aceProtoPortEntryCreationRequiresOperAndPort(7695),
		entryOnlyAllowOnePortToBeSet(7696),
		portInputFormatIsInvalid(7697),
		operationMaskMustBeZeroWhenOperationIsNotMask(7698),
		aceTcpFlagEntryCreationRequiresOperaiotnAndTcpFlag(7699),
		qosPolicyLaneExist(7701),
		qosPolicyLaneNotExist(7702),
		qosPolicyPkRateInvalid(7703),
		qosPolicySvcRateInvalid(7704),
		qosPolicyLaneInvalid(7705),
		qosPolicyValidAcesPresent(7706),
		qosTxQSetQmaxInvalid(7707),
		qosTxQSetQmaxChangeNotAllowed(7708),
		qosTxQSetBalQInvalid(7709),
		qosTxQSetHipriQInvalid(7710),
		qosTxQSetLopriQInvalid(7711),
		qosTxQSetMaxQExceed(7712),
		qosTxQSetPortNotRMod(7713),
		qosTxQSetQInvalid(7714),
		qosTxQSetQNotAssign(7715),
		qosTxQSetMinRateGtMaxrate(7716),
		qosTxQSetQMaxAfter8Adjust(7717),
		qosTxQSetPortFeIncompatibleQset64(7718),
		qosTxQSetPortGbIncompatibleQset8(7719),
		qosTxQSetModificationNotAllowed(7720),
		qosSvcRateInvalid(7765),
		qosTxQSetQLengthWredModNotAllowed(7766),
		qosPolMinPeakSvcRate64M(7774),
		qosShaperCannotExceedMaxShapeRateFor10GInterface(7775),
		ipv6InterfaceAdminDisabled(7802),
		ipv6ForwadingDisabled(7803),
		noVrrpLinkLocalAddressSpecified(7804),
		vrrpLinkLocalAddressCannotBeChanged(7805),
		vrrpInvalidGlobalAddress(7806),
		invalidLinkLocalAddress(7807),
		addressExistsOnVrrp(7808),
		invalidVrrpAddressOwnerPriority(7809),
		ipv6ValidLifeCanOnlyBeInfinityForInfinite(7810),
		invalidVrrpPrefixEntry(7811),
		vrrpPrefixExists(7812),
		ipsecSpAlreadyExist(7813),
		ipsecSpDoesNotExist(7814),
		ipsecSaConfigChangeNotAllowedWhenPolicyIsEnabled(7815),
		ipsecSaHashAndEncryptAlgorithmsCannotBeNull(7816),
		ipsecSaAlreadyExist(7832),
		ipsecSaDoesNotExist(7833),
		ipsecSpSaLinkExist(7834),
		ipsecSpSaLinkDoesNotExist(7835),
		ipsecManualKeyingAlgoDetailMustBeConfigured(7836),
		ipsecSpiValueShouldBeUnique(7837),
		ipsecEncryptKeyInfoMustBeConfiguredWithAlgo(7838),
		ipsecAuthKeyInfoMustBeConfiguredWithAlgo(7839),
		ipsecSaRaddrEntryNotFound(7840),
		ipsecSpAndInterfaceDoesNotExist(7841),
		ipsecCannotModifySp(7842),
		ipsecCannotModifySa(7843),
		ipsecMismatchInterfaceAddrAndLaddrOrRaddr(7844),
		ipsecInvalidEncKey(7848),
		ipsecInvalidAuthKey(7849),
		ipsecCannotSetEncryptAlgoAndKeyDetailWithAuthHeader(7850),
		ipsecCannotLinkSaWithNullSpi(7851),
		ipv6AddressCannotBeDeletedDueToUsageOfIpsecPolicyLaddrOrRaddr(7852),
		ipsecMaxCountPolicyLinkedToInterfaceReached(7853),
		ipsecMaxCountPolicyLinkedToSaReached(7854),
		ipv6Ospfv3VirtualLinkIpsecPolicyEnabledCannotModify(7859),
		ipv6OspfV3VirtualLinkIpsecPolicyAttached(7860),
		ipv6IpsecInvalidKeyString(7861),
		ipv6CannotDeleteVlanWithIpsecEnabled(7872),
		ipv6CannotDeleteBrouterPortWithIpsecEnabled(7873),
		ipsecCannotLinkPolicyToSaWithPolicyDisable(7875),
		ipsecCannotRemovePolicyInterfaceWithWrongDirection(7876),
		ipsecCannotModifyDirectionOnIpsecEnabledInterface(7877),
		ipsecCannotSetSrcPortDstPortForIcmpv6AndOspf(7878),
		ipsecPolicyAndSaNameShouldBeAlphanumeric(7879),
		ipsecInvalidPortNumber(7880),
		ipsecUnsupportedAddressType(7881),
		ipsecCannotDeletePolicyIfPolicySaLinkExist(7882),
		ipsecPolicyAlreadyLinkedToOtherSa(7883),
		ipsecCannotUnlinkPolicySaPairWithInterfaceLinked(7884),
		ipsecCannotDeletePolicyAttachedToInterface(7885),
		noIpv6AddrAssociatedWithPortOrNoVlanProvided(7886),
		invalidVrrpVersion(7887),
		cannotConfigureIpv4MappedIpv6AddrWithDotedDecimalFormat(7888),
		ipv6MrouteHwUsageUseDefault(7889),
		ipv6OspfAreaHasIpsecVirtualLinkAttached(7890),
		configurationOfIpv4CompatibleIpv6AddrIsDeprecated(7891),
		notAllowedtoChangeVrrpChecksumMethodForVrrpV2(7892),
		ipv6InvalidMask(7855),
		ipv6InterfaceForwardingAlreadyEnabled(7856),
		ipv6InterfaceForwardingAlreadyDisabled(7857),
		ipv6ClipAddrPrefixNot128(7864),
		ipv6ClipInterfaceExists(7865),
		ipv6MaxNumberOfClipInterfacesReached(7866),
		plsbInvalidIpv6SourceAddress(7867),
		ipv6SourceAddressMustBeDeletedBeforeIpv6ClipDeletion(7868),
		ipv6RedistributeEntryNotFound(7869),
		virtualIstConfigNotAllowedOnIpv6Interface(7870),
		ipv6PreferredLifeCannotBeGreaterThanValidLife(7871),
		insufficientResourcesIpv6IntfEnable(7874),
		ipfixStateAlreadyEnabled(8101),
		ipfixStateAlreadyDisabled(8102),
		ipfixInvalidSlotNumber(8103),
		ipfixNotADPMSlot(8104),
		ipfixInvalidActiveTimeout(8105),
		ipfixInvalidAgingInterval(8106),
		ipfixInvalidExportInterval(8107),
		ipfixInvalidTemplateRefIntervalSec(8108),
		ipfixInvalidTemplateRefIntervalPkts(8109),
		ipfixCollectorNotConfigured(8110),
		ipfixTwoCollectorAlreadyConfigured(8111),
		ipfixOnlyUdpProtocolSupported(8112),
		ipfixInvalidCollectorDestPort(8113),
		ipfixInvalidHashPolynomialCoeff(8114),
		ipfixInvalidHashPolynomialSeed(8115),
		ipfixInvalidHashKeyId(8116),
		ipfixInvalidSamplingRate(8117),
		aceIpfixStateIllegal(8118),
		ipfixCannotBeEnabledWhneFpemBanksIsZero(8122),
		ipfixMaximumCollectorsNumberReached(8123),
		ipfixOnlyCollector1IsSupported(8124),
		ipfixCollectorAlreadyExists(8125),
		ipfixCollectorAndExportAddrMustBeDifferent(8126),
		ipfixAgingIntervalGreaterThanSupportedValue(8127),
		ipfixCannotBeEnabledWithoutMirrorResource(8128),
		ipfixCollectorNotOnMgmt(8129),
		ipfixExporterNotOnMgmt(8130),
		tacacsIllegalIpAddress(8201),
		tacacsIllegalPriority(8202),
		tacacsMaxServersReached(8203),
		tacacsRadiusEnabled(8204),
		tacacsNoKeyGiven(8205),
		tacacsSourceIpDisabled(8207),
		tacacsServerNotConfigured(8209),
		tacacsPrimaryServerAlreadyExists(8210),
		tacacsBackupServerAlreadyExists(8211),
		tacacsPrimaryServerIsConfiguredWithTheSameIp(8212),
		tacacsBackupServerIsConfiguredWithTheSameIp(8213),
		tacacsPppAuthNotSupported(8214),
		tacacsPppAccountingNotSupported(8215),
		tacacsInvalidSession(8216),
		tacacsCannotConfigureMoreThanOneServer(8217),
		tacacsSourceIpAddressNotLocal(8218),
		isisPwdInvalid(8301),
		isisKeyIdInvalid(8302),
		isisPwdExists(8303),
		isisNoKeyId(8304),
		isisInvalidAuthType(8305),
		isisCsnpIntInvalid(8306),
		isisRxmtLspIntInvalid(8307),
		isisRtrTypeInvalid(8308),
		isisNetLenInvalid(8309),
		isisSysidError(8310),
		isisManAreaAddrToomany(8311),
		isisManAreaError(8312),
		isisNetEntryExists(8313),
		isisSummAddrExists(8314),
		isisSummAddrError(8315),
		isisInvalidSubnetMask(8316),
		isisEnabledOnInterface(8317),
		isisCannotChangeMetricTypeFromWideToNarrow(8318),
		isisInvalidCircType(8319),
		isisSysIdInvalid(8320),
		isisSysIdRuntimeChange(8321),
		isisInvalidCircuitId(8322),
		isisCircuitAlreadyExists(8323),
		isisCircuitDoesNotExist(8324),
		isisInvalidIntfIndex(8325),
		isisLevelRouterDoesNotSupp(8326),
		isisManAreaNotConfigured(8327),
		isisL2OnlyNotSupported(8328),
		isisPriorityOnlyForBcastType(8329),
		isisMetricValueInvalidForNarrowType(8330),
		isisL2onlyCircuitExists(8331),
		isisMinLspIntGreaterThanMaxLspInt(8332),
		isisMaxLspIntLessThanMinLspInt(8333),
		isisPlsbNodeNicknameInvalid(8334),
		isisPlsbInstanceAlreadyExists(8335),
		isisOnePlsbInstanceAllowed(8336),
		isisPlsbInstanceDoesNotExist(8337),
		isisCannotDeletePlsbInstanceWithIsid(8338),
		isisCannotDeletePlsbInstanceWithIsisInterface(8339),
		isisOneVlanPerPlsbInstance(8340),
		isisVlanDoesNotExist(8341),
		isisVlanIsNotPlsb(8342),
		isisInterfaceCannotConfigPlsb(8343),
		isisPlsbInstanceNotExistOnInterface(8344),
		isisPlsbInstancePt2ptOnly(8345),
		isisPlsbL1Only(8346),
		isisCannotDeleteVlanWithPlsb(8347),
		isisPlsbNniPortCannotBeAccess(8348),
		isisCannotEnableInterfaceWithoutPlsbInstance(8349),
		isisSystemIdIsnotBasemac(8350),
		isisPlsbInstanceNotConfigured(8351),
		isisNicknameNotConfiguredForPlsbInstance(8352),
		isisBvidNotConfiguredForPlsbInstance(8353),
		isisSpfDelayInvalid(8354),
		isisControlVlanDoesNotExist(8355),
		cannotAddPortToMltWithIsisInterfaceOnBothPortAndMlt(8356),
		cannotCreateIsisIntfOnPortWhichIsMemberOfMltWithIsisIntf(8357),
		cannotCreateIsisIntfOnMltWhichHasPortMemberWithIsisIntf(8358),
		isisSysidCannotBeMulticastAddress(8359),
		deleteIsisInterfaceBeforeDeleteMlt(8360),
		onlyFirst10PortOfLaneCanBeIsisInterface(8361),
		narrowMetricNotSupportedInPlsbMode(8362),
		isisCannotChangeSysIdDueToIsidEpIsEnable(8363),
		isisCannotChangeNickNameDueToIsidEpIsEnable(8364),
		isisCannotChangePlsbVlanDueToIsidEpIsEnable(8365),
		isisBcastNotSupportedOverMlt(8366),
		isisPortIsNotMemberOfPlsbVlan(8367),
		isisMltIsNotMemberOfPlsbVlan(8368),
		isisPlsbVlanDifferentFromDataVlan(8369),
		isisOverloadOnStartUpOutOfRange(8370),
		isisCannotChangeSysIdWhenNodalMepMipAssociatedToPlsbVlan(8371),
		enablePerformTaggingBefPlsbIsisInterfAssociation(8372),
		isisPlsbPrimaryVlanNotAdded(8373),
		isisPlsbPrimaryVlanNotMatch(8374),
		isisCannotUseMulticastAddress(8375),
		isisCannotEnableIpIsis(8376),
		isisPlsbPortConflictWithCvlan(8377),
		isisPlsbMLTConflictWithCvlan(8378),
		isisPlsbMLTISTConflictWithCvlan(8379),
		isisSpbmBvlanNotAllowToRunSlpp(8380),
		isisSpbmInvalidEtherType(8381),
		isisMaxLspGenIntCannotBeLessThan30(8382),
		cannotConfigureIsisRedistributionWhenSpbmDisabled(8385),
		logicalIsisIntfCannotBeDeletedBeforeDeletingIsisIntf(8386),
		logicalIsisIntfDestIpCannotBeModified(8387),
		logicalIsisIntfDestIpCannotBeLocal(8388),
		logicalIsisIntfDuplicateVids(8389),
		logicalIsisIntfVidsCannotBeModified(8390),
		logicalIsisIntfDoesNotExist(8391),
		isisCircuitAlreadyExistsOnIsisLogicalTunnelIntfPort(8392),
		isisCircuitAlreadyExistsOnIsisLogicalTunnelIntfMlt(8393),
		isisCannotDeleteSpbmInstanceWithFaSmlt(8394),
		nsnaNoRedVlan(8401),
		nsnaRedVlanExists(8402),
		nsnaGlobalEnabled(8403),
		nsnaNoVlanColor(8404),
		nsnaVlanHasColor(8405),
		nsnaVlanNonEmpty(8406),
		nsnaNoFilterForNsnaVlan(8407),
		nsnaPortHasFilter(8408),
		nsnaNoUplinkDhcpFilter(8409),
		nsnaYellowSubnetNotSpecified(8410),
		nsnaNoNsnasSubnet(8411),
		nsnaMaxNsnasSubnet(8412),
		nsnaNoSshDaemon(8413),
		nsnaIncorrectGreenVlan(8414),
		nsnaIncorrectUplinkVlan(8415),
		nsnaIncorrectVoipVlan(8416),
		nsnaPortIsEap(8417),
		nsnaPortOperationNotAllowed(8418),
		nsnaUnknownMac(8419),
		nsnaExceedMaxNumEntry(8420),
		nsnaStaticEntryExists(8421),
		nsnaOperationNotAllowedOnMirroredPort(8422),
		nsnaInvalidHelloInact(8423),
		nsnaVlanFlushNotAllowed(8424),
		nsnaNoUplinkVlans(8425),
		nsnaVlanFilterRemapInProgress(8426),
		nsnaVlansCannotBeDeleted(8427),
		nsnaVlanCannotBeMadeGuestVlan(8428),
		nsnaPortCannotBeConfiguredOnNonPrPorts(8429),
		nsnaNotAllowedOnSmltPort(8431),
		nsnaNotAllowedOnDhcpSnoopEnabledVlan(8442),
		filterNotAllowedOnDhcpSnoopEnabledVlan(8443),
		cfmNoParamChange(8501),
		cfmDomainExists(8502),
		cfmDomainDoesNotExists(8503),
		cfmMaintenanceAssociationExists(8504),
		cfmMaintenanceAssociationDoesNotExists(8505),
		cfmChangeNotAllowedWhenEnabled(8506),
		cfmMepExists(8507),
		cfmMepDoesNotExists(8508),
		cfmOperationNotAllowedWhenMepsExist(8511),
		cfmMepInUse(8531),
		cfmMaDomainNameFieldCannotBeEmptyForCreation(8535),
		indexIsBeingUsedByOtherDomain(8536),
		cfmAssnIndexCantBeZeroForCreation(8537),
		indexIsBeingUsedByOtherMaAssn(8538),
		cfmOperationNotAllowedWhenMasExistUnderMd(8539),
		cfmDomainIndexCantBeZeroForCreation(8540),
		cfmAssnDoesNotExist(8541),
		cfmMepIdCannotBeNullForCreation(8542),
		cfmMaAssnNameFieldCannotBeEmptyForCreation(8543),
		pbtVlanCannotReassign(8552),
		cfmMepCanNotEnableWhenCfmEtherTypeIsNotSet(8554),
		invalidMepListInputFormat(8562),
		invalidDmOrMaNameLength(8563),
		mepIdMustBeANumber(8564),
		maxNumOfMepEntriesExceeded(8565),
		domainAlreadyAssociatedWithOtherTypeOfService(8567),
		cfmCannotDeleteBeforeRemoveAssociation(8574),
		cfmOperationNotAllowedWhenMipsExistUnderMd(8577),
		invalidMipListInputFormat(8582),
		invalidDmNameLength(8583),
		cannotDeleteVlanWithMepAssociation(8586),
		cfmLbmExceedMaxDataSizeLimit(8642),
		plsbVlanMustUsePlsbStg(8646),
		normalVlanCannotUsePlsbStg(8647),
		cfmPlsbCanHaveOnlyOneStg(8648),
		cfmInvalidName(8649),
		sameLevelMepAlreadyAssignedToVlanOnSamePort(8670),
		sameLevelMipAlreadyAssignedToVlanOnSamePort(8671),
		cfmNodalMepOnPbtVlanNotAllowed(8687),
		cfmCannotAddOrRemoveNodalMepsWhenMepListIsEmptyOrInvalid(8688),
		cfmExceedMinCcmIntervalForNodalVlan(8689),
		cfmMepAlreadyInUseWithOtherNodalVlan(8690),
		cfmMepAlreadyInUseWithOtherServiceType(8691),
		cfmNodalMipLevelOnPbtVlanNotAllowed(8692),
		cfmCannotAddOrRemoveNodalMipsWhenMipListIsEmptyOrInvalid(8693),
		cfmLbmCannotSpecifyBothDataAndFrameSize(8697),
		cfmFrameSizeTooLargeForRmod(8698),
		cfmFrameSizeTooLargeForRCmod(8699),
		cfmNoServiceAssociatedWithMepOrMip(8720),
		cfmMepNotReadyToSetLbm(8721),
		cfmMepNotOkToSetReady(8722),
		cfmMepNotReadyToSetLtm(8723),
		cfmLbmExceedMaxMessagesLimit(8726),
		cfmLbmTestPatternSizeError(8748),
		mepListCannotHaveTwoMepsWithSameMdLevel(8754),
		mipListCannotHaveTwoMipsWithSameMdLevel(8755),
		vrfDoesNotExist(8901),
		vrfAlreadyExists(8902),
		vrfMaxRoutesCouldNotBeSet(8903),
		vrfPortDoesNotBelongToSpecifiedVrf(8904),
		vrfVlanDoesNotBelongToSpecifiedVrf(8905),
		vrfLegacyPortCannotBeAddedToVlanAssociatedWithVrf(8906),
		vrfInvalidVrfId(8908),
		vrfOperationProhibitedForGrt(8909),
		vrfOspfLimitExceeded(8910),
		vrfRipLimitExceeded(8911),
		vrfDhcpLimitExceeded(8912),
		vrfVrrpLimitExceeded(8913),
		vrfRipDoesNotExist(8914),
		vrfOspfDoesNotExist(8915),
		vrfNameInvalid(8916),
		vrfNameDuplicate(8917),
		vrfRipAlreadyExists(8918),
		vrfOspfAlreadyExists(8919),
		vrfCannotChangeAssociationInterfaceExists(8907),
		vrfCannotAssociatePortInVlan(8920),
		vrfCannotAddAssociatedPortToVlan(8921),
		vrfCannotAssociateToVlanWithLegacyPorts(8922),
		vrfCannotAssociateToLegacyPortForBrouter(8923),
		vrfBgpDoesNotExist(8924),
		vrfBgpAlreadyExists(8925),
		vrfBgpLimitExceeded(8926),
		vrfConfigNeedsMezz(8927),
		invalidNextHopVrfName(8928),
		vrfOperationNotAllowed(8931),
		vrfPimLimitExceeded(8932),
		vrfPimDoesNotExist(8933),
		igapCannotBeEnabledOnNonGRTVlan(8934),
		igapAuthCannotBeEnabledOnNonGRTVlan(8935),
		igapAccntCannotBeEnabledOnNonGRTVlan(8936),
		igapIsNotEnabled(8937),
		vrfOperProhForMgmt(8938),
		ripSrcAndDstProtoCannotBeSameWithinOneVrf(8939),
		vrfMaxReached(8942),
		vrfNameIsReserved(8943),
		ipv4AndIpv6AddressOnSameInterfaceMustBelongToSameVrf(8944),
		vrfMsdpLimitExceeded(8946),
		vrfMsdpDoesNotExist(8947),
        vrfIsUsedAsNextHopVrfForRouteInAnotherVrf(8948),
        vrfBaselicMaxReached(8949),
		mplsRouterIdLdpRsvpEnabled(10001),
		mplsInvalidDeleteOperation(10002),
		mplsInvalidInterfaceState(10003),
		mplsInterfaceNotExist(10004),
		mplsInvalidInterfaceMtu(10005),
		mplsExplicitPathInUse(10006),
		mplsTunnelInUse(10007),
		mplsTunnelNoDest(10008),
		mplsTunnelResourceInUse(10009),
		mplsMezzCardAbsent(10010),
		mplsLdpNotReady(10011),
		mplsRsvpNotReady(10012),
		mplsRouterIdSetToZero(10013),
		mplsInterfaceVlanNotFound(10014),
		mplsPortNotRModule(10015),
		mplsIpAddrInUse(10016),
		mplsTunnelNotFound(10017),
		mplsTunnelNotAllLspUp(10018),
		mplsInvalidIndex(10019),
		mplsExplicitPathExists(10020),
		mplsExplicitPathHopExists(10021),
		mplsExplicitPathIndexExists(10022),
		mplsMaxIndex(10023),
		mplsInvalidPathOptionIndex(10024),
		mplsLspExists(10025),
		mplsInvalidLspInstance(10026),
		mplsLspNoName(10027),
		mplsLspNoEPName(10028),
		mplsLspEPNotFound(10029),
		mplsConfigNeedsMezz(10030),
		mplsExpPathIpv4AddrTypeOnly(10031),
		mplsExpPathNoNameChange(10032),
		mplsLspNoNameChange(10033),
		mplsSrcIpNonLocal(10034),
		mplsLspIndexUsed(10035),
		mplsLspNameUsed(10036),
		mplsLspNotActive(10037),
		mplsTunnelSameSrcDest(10038),
		mplsLspNotSameSrc(10039),
		mplsLspNotSameDest(10040),
		mplsTunnelNoALtPath(10041),
		mplsTunnelCfgIngressOnly(10042),
		mplsTunnelInvalidIndex(10043),
		mplsEPInvalidIndex(10044),
		mplsEPHopInvalidIndex(10045),
		mplsResInvalidIndex(10046),
		mplsInvalidLdpKeepAliveRange(10047),
		mplsInvalidLdpHelloHoldTimeRange(10048),
		ipvpnCreateFailed(10201),
		ipvpnDeleteFailed(10202),
		ipvpnAlreadyEnabled(10203),
		ipvpnNotEnabled(10204),
		ipvpnNotSupportedOnDefVRF(10205),
		ipvpnSameRDConf(10206),
		ipvpnInvRDConfOnDefVRF(10207),
		ipvpnInvRDTypeNotSupported(10208),
		ipvpnInvRTConfOnDefVRF(10209),
		ipvpnInvRTTypeNotSupported(10210),
		ipvpnSVCAllocFailed(10211),
		ipvpnSVCILMAddFailed(10212),
		ipvpnLiteSupportOnlyType1(10213),
		ipvpnRDTypeNotSupportedWithLite(10214),
		ipvpnSvcLblChngIfIpvpnDisabledInVRF(10215),
		ipvpnSvcLblOptionAlreadySetInIpvpnVRF(10216),
		ipvpnPeerRRLiteModeConflict(10217),
		ipvpnPeerGroupRRLiteModeConflict(10218),
		ipvpnImplicitReflectInMixedLiteMode(10219),
		ipvpnInvalidPeerSetForAccessPeer(10220),
		ipvpnRouterInNonLiteRRMode(10221),
		ipvpnRouteTargetNotFound(10222),
		bgpOperationNotAllowedWhenDefaultBgpIsEnabled(10223),
		bgpOperationNotAllowedWhenVrfBgpIsEnabled(10224),
		bgpInvalidLocalAsWhenVrfPeerRemoteAs(10225),
		bgpInvalidVrfPeerRemoteAs(10226),
		bgpInvalidVrfPeerGroupRemoteAs(10227),
		ipvpnLiteRequiresVpnv4(10228),
		ipvpnVpnv4DisableRequiresLiteDisable(10229),
		ipvpnEnabledWithoutLocalAs(10230),
		ipvpnInterVrfRedistEnable(10231),
		bgpOperationNotAllowedWhenIpvpnIsEnabled(10232),
		ipvpnInvalidAssignedNumber(10233),
		ipvpnInvalidAsNumber(10234),
		ipvpnInvalidPeerSetForExternalPeer(10235),
		ipvpnInvalidPeerGroupSetForExternalPeer(10236),
		ipvpnMaxRtPerVrfExceeded(10237),
		ipvpnRdOverlapOperNotAllowed(10238),
		ipvpnNotCreated(10239),
		ipvpnAlreadyCreated(10240),
		ipvpnLiteRequiresValidIpAddressInRd(10241),
		ipvpnLiteOperationNotAllowedSameIpConfiguredAsRdInAnotherVrf(10242),
		ipvpnRDInvalidCircuitlessIP(10243),
		ipvpnRDIpNotLiteEnabled(10244),
		ipvpnLiteSupportRDWithClipIp(10245),
		ipvpnLiteSupportOnlyLiteEnabledRDIP(10246),
		ipvpnEnableDisallowedWithoutValidRD(10247),
		ipvpnLiteRDIpConfiguredInMultipleVrf(10248),
		ipvpnIsidAlreadyExist(10249),
		ipvpnBgpBasedOrTaggedPeerNotConfigured(10250),
		ipvpnBothTypeOfIpvpnCreated(10251),
		ipvpnBgpBasedAlreadyCreated(10252),
		ipvpnTaggedPeerAlreadyCreated(10253),
		ipvpnTaggedPeerIsidNotConfigured(10254),
		ipvpnTaggedPeerIsidRuntimeChangeNotAllowed(10255),
		ipvpnMvpnIsidRuntimeChangeNotAllowed(10256),
		insufficientResourcesIpvpnEnable(10257),
		customAutoNegAdvMacPauseNotSupported(10301),
		customAutoNegAdvAsymPauseNotSupported(10302),
		mirrorDestinationNotEntered(10306),
		mirrorLegacyCannotSupportPortList(10307),
		mirrorMltShouldHavePortsAssigned(10308),
		mirrorDestinationNotAttached(10309),
		mirrorDisableEntry(10310),
		mirrorDestinationAlreadyAttached(10311),
		mirrorLegacyCannotSupportVlanOrMlt(10313),
		mirrorDestAlreadyAttachedOrDestSpecifiedNotAttached(10314),
		noAdminSettingForSpeed1000(10330),
		portAlwaysRunAt10GSpeed(10331),
		rmodOnlyOneMirroredPortPerLaneForEgress(10332),
		mirrorTxFilterModeNotAllowedOnRsmod(10333),
		mirrorModeNotValidForRmodRSmod(10334),
		cannotSetAdminSpeed1000AsPerIEEE(10338),
		portMirroringNoMgidsAvailable(10363),
		loopDetectNotAllowedOnIstPorts(10364),
		loopDetectNotAllowedAlreadyEnabled(10365),
		portPcapModeNotSupported(10366),
		svcRateNeedsToBeSetToZeroWhenPeakIsSetToZero(10367),
		peakRateNeedsToBeSetToZeroWhenSvcRateIsSetToZero(10368),
		portCpLimitShutdownOnIstPortNotAllowed(10369),
		portOnly10GEPortsCanBeLossless(10374),
		portIsConfiguredAsLossless(10375),
		portIsConfiguredAsLosslessPfc(10376),
		portIsL2Untrusted(10377),
		portIsConfiguredAsIfPolicer(10378),
		portLaneHasLosslessPort(10379),
		portSliceHasLosslessPort(10380),
		portAllMltPortsCannotBeMadeLossless(10381),
		portConfigNotAllowedLacpKeyInMltIdRange(10383),
		rmVlanIdNotSetForRMSPort(10384),
		rmVlanListNotAllowedForRMS(10385),
		slppTimeToClrPktRxCountNotConfigurable(10386),
		portCannotBeConfiguredAsLosslessPfc(10387),
		portMltListViolatesLosslessLaneLimit(10388),
		portQosInvalidForLosslessPfc(10389),
		portL3TrustedInvalidForLossless(10390),
		portL2UntrustedInvalidForLossless(10391),
		portNoLosslessChangeIfLacpEnabled(10392),
		portMltOnly10GEPortsCanBeLossless(10393),
		portAddOnly10GEPortsCanBeLossless(10394),
		portMltIsConfiguredAsIfPolicer(10395),
		portAddIsConfiguredAsIfPolicer(10396),
		forcedRearpNotAllowedOnPortInterface(10397),
		sharedPortConfigurationNotSupportedInThisRelease(10398),
		brouterCannotBeAddedToIpSubnetOrIpProtocolVlan(10399),
		cannotConfigPortTxFlowControlWhenFlowControlModeFlagDisabled(10400),
		cfmCannotAbortWhenNoLtmInProgress(10442),
		esmMltCannotBeNonUni(10443),
		cfmCannotAbortWhenNoLbmInProgress(10446),
		plsbVlanIsidNotAllowed(10459),
		plsbVlanIsidAlreadyExist(10460),
		plsbVlanIsidWithSingleBvlan(10461),
		plsbSysidCannotBeSameAsIstPeerSysid(10462),
		bgpInvalidPeerSetWhenVpnv4Enabled(10501),
		bgpInvalidPeerGroupSetWhenVpnv4Enabled(10502),
		bgpOverlappingAggregateAddress(10503),
		bgpInvalidLocalAsWhenPeerRemovePrivateAsEnabled(10504),
		bgpInvalidPeerRemovePrivateAsEnableWithoutRemoteAs(10505),
		bgpInvalidPeerGroupRemovePrivateAsEnableWithoutRemoteAs(10506),
		bgpDuplicatePeerNotAllowed(10507),
		bgpPeerDoesNotBelongToPeerGroup(10508),
		bgpOperationNotAllowedWhenRouteReflectorClientIsEnabled(10509),
		bgpInvalidAggregateAdvertisePolicyWithoutAsSetGenerate(10510),
		bgpInvalidPeerDefaultOriginateIpv6(10512),
		bgpInvalidPeerGroupDefaultOriginateIpv6(10513),
		bgpInvalidPeerIpv6Capability(10514),
		bgpOperationNotAllowedForIpv6Peer(10515),
		bgpOperationNotAllowedForIpv6PeerGroup(10516),
		bgpOperationNotAllowedWhenOutboundMapsAreDifferent(10517),
		bgpOperationNotAllowedWhenInboundMapsAreDifferent(10518),
		maxPeerEntriesInPeerGroup(10519),
		bgpOperationNotAllowedWhenNexthopSelfAreDifferent(10520),
		bgpOperationNotAllowedWhenUpdateSourceAreDifferent(10521),
		bgpOperationNotAllowedWhenRemovePrivateAsAreDifferent(10522),
		bgpTransAsValueCannotBeUsed(10523),
		bgpVrfPeerIpv6CapabilityNotSupported(10524),
		bgpVrfDefaultOriginateIpv6NotSupported(10525),
		bgpInvalidPeerIpv6AfVrf(10526),
		bgpInvalidPeerGroupIpv6AfVrf(10527),
		bgpInvalidSet4ByteASFlagVrf(10528),
		bgpInvalidSetASDotFlagVrf(10529),
		bgpInvalidSet4ByteWhenASNumIs4Byte(10530),
		bgpInvalidPeerAlreadyExists(10531),
		bgpInvalidPeerAsLocalInterface(10532),
		bgpInvalidPeerNotExisting(10533),
		bgpInvalidPeerGroupAlreadyExists(10534),
		bgpInvalidPeerGroupNotExisting(10535),
		bgpInvalidAggregateAlreadyExists(10536),
		bgpInvalidAggregateNotExisting(10537),
		bgpInvalidNetworkAlreadyExists(10538),
		bgpInvalidNetworkNotExisting(10539),
		plsbDeleteIntfBeforeSetPlsbFlag(10701),
		plsbDeletePlsbInstanceBeforeSetPlsbFlag(10702),
		plsbDeleteManualAreaBeforeSetPlsbFlag(10703),
		plsbDeleteSummaryAddrBeforeSetPlsbFlag(10704),
		plsbDisableIsisBeforeSetPlsbFlag(10705),
		plsbDeletePlsbVlanBeforeSetPlsbFlag(10706),
		plsbCannotConfigPlsbInNonplsbMode(10707),
		commandValidOnlyIfInRmode(10708),
		cannotAssociateMoreThan5000IsidToPlsbInstance(10709),
		cannotEnablePlsbWithMmrpConfiguration(10711),
		cannotHaveSameBvlanAsSpIpVlanRCModPort(10712),
		cannotAddRcModPortsToMltWhenSpIpVlanSameAsBvlan(10713),
		cannotConfigPlsbIsisSmltistIntfOnSameIntf(10714),
		plsbDisableAllIsisEndpointsBeforeTogglePlsbState(10715),
		cannotConfigPortInSmltOrIstForPlsbVlan(10716),
		deleteStg63BeforeCreatingPlsbBvlan(10717),
		only2PlsbBvlanSupported(10718),
		plsbInvalidIpSourceAddress(10719),
		plsbMustChangeNicknameAfterChangeSysid(10720),
		plsbWhenEnableIstMustConfigSmltPeerBmac(10721),
		cannotConfigPlsbIsisIntfOnSmlt(10722),
		cannotConfigPlsbIsisIntfOnIstPort(10723),
		plsbZeroSmltPeerBmacMustHaveZeroVirtualBmac(10724),
		plsbZeroSmltPeerBmacMustHavePrimSplitBeb(10725),
		plsbWhenSetVirtualBmacToZeroPeerBmacMustBeZero(10726),
		plsbDeleteIsidFromVlanBeforeSetPlsbFlag(10727),
		plsbIsidNotAllowedForVlanSpbmDisabled(10728),
		plsb16777215IsWellKnownIsid(10729),
		plsbConfigIpSourceAddrBeforeEnableIpSc(10730),
		inUsedAsIsisIpSourceAddr(10731),
		plsbCannotSetIpSourceAddrToZeroWhenIpScEnabled(10732),
		spbMcConflictingCVlanIsid(10733),
		spbMcConflictingVrfIsid(10734),
		spbMcIsidInDynRange(10735),
		spbmVlanSpbMcastCannotBeEnabledWithPim(10736),
		spbmVlanSpbMcastCannotBeEnabledWithSnoop(10737),
		vlanPimCannotBeEnabledWithSpbMcast(10738),
		vlanSnoopCannotBeEnabledWithSpbMcast(10739),
		spbmIntfCanBeConfiguredOn10gigPort(10740),
		spbmIntfCanBeConfiguredOnMltWith10gigPort(10741),
		spbMcastCannotBeEnabledWithPim(10742),
		pimCannotBeEnabledWithSpbMcast(10743),
		spbMcastCannotBeEnabledWithDvmrp(10744),
		dvmrpCannotBeEnabledWithSpbMcast(10745),
		spbmVlanSpbMcastCannotBeEnabledWithDvmrp(10746),
		spbmVlanDvmrpCannotBeEnabledWithSpbMcast(10747),
		spbmMltMemberAlreadyInSpbmBvlan(10748),
		vlanSpbMcastCannotBeEnabledWithoutIpAddr(10749),
		portSpbMcastCannotBeEnabledWithoutIpAddr(10750),
		cmdNotAllowedInNonSpbmMode(10751),
		spbmDeleteRedistributeBeforeResetSpbmFlag(10752),
		spbmSmltVirtBmacCannotBeInChassisBmacRange(10753),
		spbmSmltVirtBmacMustBeSetWhenPeerBmacIsNotZero(10754),
		spbmAssociateVlanToSpbmInstBefCreation(10755),
		spbmDeleteVlanBefDeassociateFromSpbmInst(10756),
		spbmDeassociateVlanToSpbmInstBefCreation(10757),
		cannotConfigSpbmIsisIntfOnMltPort(10758),
		cannotConfigSpbmIsisIntfOnLacpPort(10759),
		mustConfigTwoBvlanForSpbmSmlt(10760),
		plsbWhenConfigIstMustConfigSmltPeerSysId(10761),
		ipIsisInFilterIsidDuplicateEntry(10762),
		ipIsisInFilterNickNameIsidDuplicateEntry(10763),
		ipIsisInFilterIsidListDuplicateEntry(10764),
		ipIsisInFilterNickNameIsidListDuplicateEntry(10765),
		ipIsisInFilterNickNameEntryNotFound(10766),
		ipIsisInFilterIsidEntryNotFound(10767),
		ipIsisInFilterNickNameIsidEntryNotFound(10768),
		ipIsisInFilterIsidListEntryNotFound(10769),
		ipIsisInFilterNickNameIsidListEntryNotFound(10770),
		ipIsisInFilterInvalidIsidListName(10771),
		ipIsisInFilterIsidListNameNotFound(10772),
		ipIsisInFilterCannotUseTransparentUniIsid(10773),
		vrfIsisInstanceDoesNotExist(10774),
		ipIsisInFilterNickNameDuplicateEntry(10775),
		ipIsisIsidListDuplicateEntry(10776),
		ipIsisIsidListEntryNotFound(10777),
		ipIsisInvalidIsidListName(10778),
		cannotRedistributeIfIsisEnabledForVrf(10779),
		cannotAcceptForIsisIfRedistributeEnabledForVrf(10780),
		ipIsisIsidListIsidCannotBeOwnIsid(10781),
		ipIsisIsidUsedByIsidList(10782),
		spbmBvlanOutOfRange(10783),
		spbmNoVistNoSmltPeerSysId(10784),
		spbmSetSmltPeerSysIdToZeroBeforeDeleteVist(10785),
		ipIsisIsidUsedByAcceptPolicy(10786),
		ipIsisCannotUseOwnNickNameAsAdvRtr(10787),
		ipIsisCannotUseOwnIsidInAcceptPolicy(10788),
		ipIsisCannotApplyForVrfWithIpvpnDisabled(10789),
		spbmMaxNumOfIsisInterfReached(10790),
		ipIsisIsidListCannotBeRemovedWhileInUse(10791),
		ipIsisIsidListInternalError(10792),
		ipIsisIsidNotFoundInIsidList(10793),
		ipIsisIsidListCannotRemoveLastIsid(10794),
		spbmDeleteBvlanBeforeSpbmInstDeletion(10795),
		isisCircuitKeyTooLong(10796),
		ipIsisInFilterRouteMapAlreadyAssigned(10797),
		pimConfigsNotAllowedInSpbmConfigModeEnabled(10798),
		spbmConfigsNotAllowedInSpbmConfigModeDisabled(10799),
		ipIsisInFilterCannotUseSwitchedUniIsid(10800),
		msdpInconsistentRowStatus(10801),
		msdpInvalidRPAddress(10802),
		msdpRPAddressNotLocalAddress(10803),
		msdpPeerTableInvalidLocalAddress(10804),
		msdpNotLocalAddress(10805),
		msdpLocalAddressPeerEstablished(10806),
		msdpPeerCreated(10807),
		msdpInconsistentPeerRowStatus(10808),
		msdpPeerNotFound(10809),
		msdpInvalidConnectRetryPeriod(10810),
		msdpHoldTimePeerEstablished(10811),
		msdpInvalidHoldtimePeriod(10812),
		msdpKeepAliveTimePeerEstablished(10813),
		msdpPeerKeepAliveInvalid(10814),
		msdpDataTTLInvalid(10815),
		msdpEncapsulationTypeNotSupported(10816),
		msdpPeerSARouteMapNameLenInvalid(10817),
		msdpPeerSAFilterPolicyNotFound(10818),
		msdpInvalidDescriptionLength(10819),
		msdpInvalidSALimit(10820),
		msdpInvalidMD5AuthStatus(10821),
		msdpInvalidPeerSetWhenPeerIsEnabled(10822),
		msdpInvalidPeerAddress(10823),
		msdpInvalidMD5AuthPasswordLength(10824),
		msdpInvalidASnumber(10825),
		msdpPeerNotConfigured(10826),
		msdpInvalidDefaultPeerRouteMapNameLength(10827),
		msdpDefaultPeerRoutePolicyNotFound(10828),
		msdpInvalidRedistributeRouteMapNameLength(10829),
		msdpRedistributeRoutePolicyNotFound(10830),
		msdpInvalidMeshGroupNameLength(10831),
		msdpPeerAlreadyConfiguredInMeshGroup(10832),
		msdpPeerNotFoundInMeshGroup(10833),
		msdpInconsistentPeerAdminStatus(10834),
		msdpInconsistentDefaultPeerStatus(10835),
		msdpInconsistentRedistributeRowStatus(10836),
		msdpInconsistentMeshGroupRowStatus(10837),
		msdpInvalidPeerAddressInMeshGroup(10838),
		msdpDefaultPeerAlreadyCreated(10839),
		msdpPeerSAFilterNotFound(10840),
		msdpGlobalGrpRedistributeNotFound(10841),
		msdpPeerSAFilterAlreadyCreated(10842),
		msdpGlobalGrpRedistributeAlreadyCreated(10843),
		msdpInterfaceNotUp(10844),
		msdpPeerConfigurePassword(10845),
		msdpPeerControlCharNotAllowed(10846),
		msdpPeerCannotDeleteNonExistingPasswd(10847),
		msdpInvalidOrigIdAddress(10848),
		msdpClipAddressNotLocalAddress(10849),
		msdpOriginatorIdIsNotConfigured(10850),
		msdpOriginatorIdCannotBeDelIfMsdpEnabled(10851),
		msdpFeatureNotSupported(10852),
		msdpOriginatorIdIsNotUniqueOnAllVrfs(10853),
		msdpPeerNotUniqueOnAllVrfs(10854),
		msdpPeerAddrIsLocalAddress(10855),
		dhcpSameServerAgentAddress(11226),
		dhcpDiffAgentAddress(11227),
		cfmLbmFrameTooSmall(11401),
		cfmLbmExceedsChassisMtu(11402),
		cfmLbmExceedsUniPortMtu(11403),
		cfmNodalMepIsNotSupportedOnESM(11408),
		cfmNodalMipLevelIsNotSupportedOnESM(11409),
		cfmLbmFrameSizeExceedMaxForNodalMep(11414),
		cannotDeleteVlanWithNodalMipLevelAssociation(11416),
		sameLevelNodalMepAlreadyAssignedToVlan(11417),
		cfmMulticastCcmOnNodalPlsbMepNotAllowed(11422),
		cfmNodalMepOnlyOnPlsbVlan(11424),
		cfmNodalMipOnlyOnPlsbVlan(11425),
		cfmNodalMpOnlyOnePerVlan(11426),
		cfmCannotL2PingWhenLbmInProgress(11427),
		cfmCannotLBMWhenL2PingInProgress(11428),
		cfmCannotAbortWhenNoL2PingInProgress(11429),
		cfmL2PingMepNotOkToSetReady(11430),
		cfmVlanNotReadyToSetL2Ping(11431),
		cfmL2PingExceedMaxMessagesLimit(11432),
		cfmL2PingExceedMaxDataSizeLimit(11433),
		cfmL2PingTestPatternSizeError(11434),
		cfmL2PingFrameTooSmall(11435),
		cfmL2PingFrameSizeExceedMaxForNodalMep(11436),
		cfmCannotLTMWhenL2TraceInProgress(11437),
		cfmCannotL2TraceWhenLTMInProgress(11438),
		cfmCannotAbortWhenNoL2TraceInProgress(11439),
		cfmL2TraceMepNotOkToSetReady(11440),
		cfmVlanNotReadyToSetL2Trace(11441),
		cfmL2CmdVlanNotFound(11442),
		cfmL2TraceInvalidIsid(11443),
		cfmNodalMipOnlyOnePerVlan(11447),
		cfmNodalMepOnlyOnePerVlan(11448),
		cfmMepMustBeEnabledForCmd(11449),
		cfmSpbmVirtualNotSet(11450),
		cfmSpbmVirtualNotPrimary(11451),
		cfmL2IpPingIsNotOkToSetReady(11452),
		cfmNotReadyToSetL2IpPing(11453),
		cfmNotMemoryAllocatedForL2(11454),
		cfmL2IpTraceIsNotOkToSetReady(11455),
		cfmNotReadyToSetL2IpTrace(11456),
		cfmIpLookupRouteFailed(11457),
		invalidIpAddrType(11458),
		cfmL2IpPingEntryMustCreatedFirst(11459),
		cfmL2IpTraceEntryMustCreatedFirst(11460),
		cfmCannotAbortWhenNoL2IpPingInProgress(11464),
		cfmCannotSetTtlTo0(11465),
		cfmTaskMsgQueueMemoryInsufficient(11467),
		cfmRouterNameNotAllowedOnNonSpbmVlan(11468),
		bpduFilterTimerInvalidRange(11502),
		bpduGuardTimerInvalidRange(11504),
		qosMapExists(12501),
		qosMapNotExist(12502),
		qosMapDeleteUsedByFilter(12503),
		qosMapDeleteDefaultMap(12504),
		qosInvalidTagToQosTableQosLevel(12505),
		qosInvalidDsFieldToQosTableQosLevel(12506),
		qosInvalidQosToTagTableQosLevel(12507),
		qosInvalidQosLevelValue(12508),
		qosMapInvalidForLosslessPfc(12509),
		qosMapPortQosInvalidForLosslessPfc(12510),
		standbyIpSubnetNotSameAsMaster(12601),
		standbyIpSubnetNotSameAsVirtual(12602),
		standbyIpSameAsVirtual(12603),
		masterIpSubnetNotSameAsStandby(12604),
		masterIpSubnetNotSameAsVirtual(12605),
		masterIpSameAsVirtual(12606),
		cannotReadConfigSourceFile(12607),
		cannotWriteConfigSourceFile(12608),
		configFileInvalidPrefix(12609),
		cpuSerialPortCommandNotAllowedOnSlave(12610),
		ipv6InvalidInvalidIpv6AddrInterfaceId(12701),
		ipv6ReasmMaxSizeExceedSysMtu(12702),
		ipv6InvalidDescriptionLength(12703),
		ipv6InvalidReasmSizeForMgmtPort(12704),
		ipv6AddrCreatedByVirtualManagment(12705),
		ipv6AndRelatedFeaturesNotSupported(12713),
		ipv6RsmltTempDefRtDeleteModify(12706),
		ipv6OspfAreaCannotModifyAreaType(12707),
		ipv6OspfAreaSetToNssaForTransRole(12708),
		ipv6OspfAreaHasActiveInterface(12709),
		ipv6InterfaceMacOffsetCannotReset(12710),
		ipv6InterfaceMacOffsetDiffSameVlan(12711),
		ipv6InterfaceCannotModifyTunnelEntry(12712),
		cantConfigIpv6AddressOfPrefixMoreThan64WhenIpv6ModeFlagDisable(12714),
		conflictingIpv6PrefixPresent(12715),
		linkLsaSuppressionOnlyForP2P(12716),
		ipv6RipInterfaceDoesNotExist(12717),
		ipv6InterfaceIsNotRunningRipng(12718),
		ipv6RipExceedsMaxLimit256(12719),
		ipv6RipExceedsMaxLimit4000(12720),
		ipv6RipExceedsMaxLimit200(12721),
		ipv6RipInterfaceAlreadyExists(12722),
		ipv6RipInvalidHoldDownTimerValue(12723),
		ipv6RipTimeoutIntervalMustBeGreaterThanUpdateTime(12724),
		unsupportedConfigWithUrpfModeFlagDisabled(12725),
		ipv6RipExceedsMaxLimit48(12726),
		ipv6ZeroPrefixNotAllowed(12727),
		ipv6PimSmltNotSupported(12728),
		ipv6StaticRouteTunnelWithNonZeroNextHopNotSupported(12730),
		ipv6ForwardingSmltConflict(12731),
		ipv6SmltForwardingConflict(12732),
		ipv6StaticRoutesMaxNumberReached(12733),
		ipv6RipngVrfUnsupported(12734),
		ipv6OspfVrfUnsupported(12735),
		ipv6FhsVrfUnsupported(12736),
		ipv6RsmltVrfUnsupported(12737),
		ipv6MldVrfUnsupported(12738),
		ipv6PimVrfUnsupported(12739),
		ipv6IpsecVrfUnsupported(12740),
		ipv6InterfaceEnabledWhenRsmltEnabledOnNonDefaultVrf(12741),
		ipv6MgmtRouterNotSupported(12742),
		ipv6StaticNeighborMaxNumberPerVrfReached(12743),
		ipv6StaticNeighborMaxNumberAllVrfReached(12744),
		ipv6RoutePreferenceUnsupportedProtocolOnVrf(12745),
		ipv6RedistributionInvalidSourceProtocolOnVrf(12746),
		ipv6IsisInFilterNickNameIsidDuplicateEntry(12748),
		ipv6IsisInFilterIsidListDuplicateEntry(12749),
		ipv6IsisInFilterNickNameEntryNotFound(12750),
		ipv6IsisInFilterIsidEntryNotFound(12751),
		ipv6IsisInFilterNickNameIsidEntryNotFound(12752),
		ipv6IsisInFilterIsidListEntryNotFound(12753),
		ipv6IsisInFilterNickNameIsidListEntryNotFound(12754),
		ipv6IsisInFilterIsidDuplicateEntry(12755),
		ipv6OspfInstanceDoesNotExist(12756),
		ipv6CannotSetRouteNameWithSpecialChar(12757),
		unsupportedVlanId(12801),
		invalidVlanIdError(12802),
		vlanAdminStatusConfigNotAllowed(12803),
		configNotAllowedOnVlanInterfaces(12804),
		macSrcMacVlanReached(12805),
		vlanCannotBeDeletedDueToEapAuthorizedPortMember(12806),
		configNotAllowedMdNameUsed(12807),
		configNotAllowedMaNameUsed(12808),
		configNotAllowedCfmInUseOnVlan(12809),
		configNotAllowedMdNameUsedByGlobalCfm(12810),
		configNotAllowedMaNameUsedByGlobalCfm(12811),
		configNotAllowedMepUsedByGlobalCfm(12812),
		configCfmInternalOnVlan(12813),
		configCfmGlobalEnabled(12814),
		configCfmTracetreeNotAllowed(12815),
		configCfmSmltNotAllowed(12816),
		cfmSrcModeCannotBeNoVlanMacOnSpbmVlans(12817),
		cfmL2McastTraceEntryMustBeCreatedFirst(12818),
		cfmNotReadyToSetL2McastTrace(12819),
		cfmMcastLookupRouteFailed(12820),
		cfmCannotDeleteVlanWithCfmMsgInProgress(12821),
		cfmCannotChangeMepWithCfmMsgInProgress(12822),
		onlyGlobalCfmSupportForNonSpbmVlan(12823),
		cfmInvalidMacToL2Trace(12824),
		cfmInvalidNodalMipLevel(12825),
		cannotModifyCfmEthertype(12826),
		l2McastRequiresServiceType(12827),
		needIsidAndIgmpSnoopVlanToL2Mcast(12828),
		mustSpecifyMvpnEnabledVrfToL2Mcast(12829),
		l2McastVlanDoesNotExist(12830),
		l2TraceOnlyIpv4AddrTypeSupported(12831),
		vlan4060To4084UsedInternally(12832),
		l3VsnMaxReached(12833),
		vlanInvalidSecondaryPrivateVlanId(12834),
		vlanSecondaryVlanIdCannotEqualPrimaryPrivateVlanId(12835),
		vlanSecondaryVlanAlreadyInUse(12836),
		vlanPrimaryVlanAlreadyInUse(12837),
		portMustBeTaggedIfPrivateTypeTrunk(12842),
		portPrivateVlanTypeCannotBeNone(12844),
		portCannotBeUntaggedIfPrivateTypeIsTrunk(12845),
		mltPrivateVlanTypeCannotBeNone(12846),
		mltCannotBeUntaggedIfPrivateTypeIsTrunk(12847),
		onlyPrivateVlansAllowedOnThisInterface(12848),
		privateIsolatedInterfaceMayOnlyBelongToOnePrivateVlan(12849),
		vlanSecondaryVlanCannotBeChanged(12850),
		privateVlanCannotChangeWhileInterfaceExists(12851),
		cannotMakeInterfaceWithPrivateType(12852),
		noIpEcmpForVrf(12853),
		mltCannotSetDefaultPrivateTypeIfAssociatedWithPrivateVlan(12854),
		cannotSetPrivateTypeIfLacpActive(12855),
		cannotSetPrivateTypeIfPortIsSpbmNni(12857),
		cannotSetEncapsulationIfLacpActive(12858),
		portCannotSetDefaultPrivateTypeIfAssociatedWithPrivateVlan(12859),
		cannotHavePortInVirtualIstVlan(12860),
		virtualIstVlanMustHaveIsid(12864),
		virtualIstVlanMustBelongToGlobalRouter(12865),
		cannotDeleteVirtualIstVlan(12866),
		cannotChangeIsidOnVirtualIstVlan(12867),
		cannotChangeIpAddrOnVirtualIstVlan(12868),
		virtualIstExists(12869),
		smltVlanMustHaveIsid(12870),
		cannotAddMltToVirtualIstVlan(12871),
		nlbModeMulticastNotSupported(12872),
		vlan4061To4084UsedInternally(12873),
		privateVlanIsNotSupported(12874),
		vlanNameHasBeenUsed(12875),
		vlan4060To4084IsReservedForInternalUse(12876),
		istLocalIpNotExist(12877),
		cannotEnableMefUniFaOnPrivateVlanType(12878),
		cannotSetPrivateVlanTypeForSwitchedUniFaPortOrMlt(12879),
		cannotConfigStaticMacAddrOnFlexUniFaPortOrMlt(12880),
		systemRequiresLicenseInstalledToCreateVlan(12881),
		cfmSrcModeCannotBeSMltvirt(12882),
		cfmCmacCanNotBeConfigured(12883),
		vlanCannotBeDeletedDueToEapFOVEnabledPort(12884),
		vlanCannotBeDeletedDueToEapGVEnabledPort(12885),
		vlanNlbNeedsToBeDisabledBeforeChangingNlbModeToUnicast(12886),
		vlanNlbNeedsToBeDisabledBeforeChangingNlbModeToMulticast(12887),
		trafficClassesAreAlwaysEnabledAndDisbaleIsNotAllowed(12888),
		featureGmrpIsNotSupported(12889),
		urpfNotSupportedOnPlsbBvlan(12890),
		vlanNameIsReservedAsDefautNameForAnotherVlan(12891),
		vlanOrMltNameCannotBeAllNumbers(12892),
		stgIdOnlyCanBeSetDuringCreation(12893),
		vlanTypOnlyCanBeSetDuringCreation(12894),
		vlanNameTooLong(12895),
		vlanCannotAssignMgmtVrf(12896),
		vlanL2vpnCountExceeded(12897),
		aceIpDscpInvalidSetting(12901),
		aceIpDscpEntryCreationRequiresOperationAndDscpSetting(12902),
		aceEthPortEntryCreationRequiresOperAndPort(12903),
		aceEthTypeEntryCreationRequiresOperAndEtherType(12904),
		aceEtherType8100NotAllowed(12905),
		filterEntryWithMonitorIpInSameSubnetExists(12906),
		filterCannotHaveCommaSeparatedValues(12907),
		filterAceTooManyArguments(12908),
		filterAceInvalidToAndFromArguments(12909),
		filterAceTooManyVlanIds(12910),
		filterCannotModifyAclPktType(12911),
		filterAclPktTypeInvalid(12912),
		filterCannotConfigureMonitorIpForIpv6pkt(12913),
		filterCannotConfigureIpForIpv6Pkt(12914),
		filterCannotConfigureArpForIpv6Pkt(12915),
		filterCannotConfigureIpv6ForNonipv6Pkt(12916),
		ipv6NextHdrIsNotSetForAce(12917),
		aceEntryCreateRequiresOperAndIpv6Addr(12918),
		aceEntryCreateRequiresOperAndNextHdrVal(12919),
		aceEntryCreateRequiresOperAndTrafficClassVal(12920),
		filterInvalidEtherTypeForIpv6Pkt(12921),
		filterOperatorNotSupported(12922),
		filterProtocolAttrConfiguredCannotModifyIpAttr(12923),
		filterCannotConfigureIpfixForIpv6pkt(12924),
		aceEtherTypeIpv6NotAllowed(12925),
		filterCannotConfigureIcmpAttributeOnEgressTrafficIn4k(12926),
		filterInvalidAceId(12927),
		filterAclIpv6PacketTypeNotSupported(12928),
		monitorDestVlanNotAllowedInOutPortTypeAclFilter(12929),
		monitorDestPortNotAllowedInOutPortTypeAclFilter(12930),
		monitorDestMltNotAllowedInOutPortTypeAclFilter(12931),
		filterRemoveTagNotSupportedForPermitOption(12932),
		monitorDstIsidNotAllowedInOutportTypeAcl(12933),
		onlyOneMonitorDstIsidSupportedInDevice(12934),
		filterQosAndRemoveTagCanBeSetOnlyForMonitorIsidAction(12935),
		removeTagConfigMustBeSameForGivenIsidOffsetAcrossAclAceConfig(12936),
		lldpCannotSetReinitDelay(13016),
		lldpCannotSetNotificationInterval(13017),
		lldpCannotSetTxDelay(13018),
		lldpCannotSetPortConfigAdminState(13019),
		lldpCannotSetPortConfigNotification(13020),
		lldpCannotSetPortConfigTlvsTxExplicitly(13021),
		lldpOnlySupportsTxAndRxMode(13022),
		cannotEnableCDPOnFAEnabledPort(13023),
		cannotDisableLLDPOnFAEnabledPort(13024),
		faZeroTouchClientTypeNotSupported(13025),
		faZeroTouchClientEntryAlreadyExists(13026),
		faZeroTouchClientEachTypeMayOneHaveOneIsid(13027),
		faZeroTouchClientIsisAlreadyUsedOrReserved(13028),
		faZeroTouchClientOnlySupportsUntagged(13029),
		faCannotCreateFaOnSmltWithoutSpbmInstance(13039),
		faCannotExistFaOnSmltWithoutSpbmInstance(13040),
		vspTalkIpInterfaceNotFound(13201),
		vspTalkDnsNotConfigured(13202),
		vspTalkInvalidMessageGroup(13203),
		vspTalkNotEnabled(13204),
		vspTalkMessageGroupNotExist(13205),
		vspTalkMessageGroupAlreadyEnabled(13206),
		vspTalkUsernameRequiredForPassword(13207),
		vspTalkMessageGroupAlreadyExists(13208),
		vspTalkCannotDeleteEnabledMessageGroup(13209),
		vspTalkPasswordCannotBeAllNumeric(13210),
		vspTalkIpAddressMustBeDeletedFirst(13211),
		invalidMstiInstance(13144),
		incorrectPoeGroupIndex(13305),
		interfaceIsNotPoePort(13306),
		deviceIsNotPoeDevice(13307),
		loopDetectMustBeEnabledBeforeEnableArpDetect(13308),
		untagPortCannotHaveMoreThanOneInterface(13309),
		noPluggableOpticalModule(13310),
		noPluggableOpticalModuleFortyG(13311),
		notChannelizablePort(13312),
		notChannelizableBasePort(13313),
		adminSpeedOnlyCanBeSetTo100Mbps(13315),
		autoNegotiationAdvertisement10GbFullNotSupported(13316),
		autoNegotiationAdvertisement10MbNotSupported(13317),
		autoNegAdvNoneCannotBeCombinedWithOtherOptions(13318),
		portNotPresent(13319),
		autoNegAdvertisement100MbHalfNotSupported(13320),
		autoNegAdvert100MbFullNotSupportedWithMacsecEnabled(13321),
		qosIngressRateLimitingCanNotExceedPortCapability(13322),
		qosEgressShaperRateCanNotExceedPortCapability(13323),
		autoNegAdvertisement10MbHalfNotSupported(13324),
		autoNegAdvertisement10MbFullNotSupported(13325),
		autoNegAdvertisement1000MbHalfNotSupported(13326),
		portLicenseRequiredToEnableThisPort(13327),
		duplicateSflowCollectorIp(13328),
		sflowAgentIpDoesNotExistInMgmtRouterOrGlobalRouterVrf(13329),
		sflowCollectorIpCannotBeLocal(13330),
		cannotRemoveAgentIpWhenSflowIsEnabled(13331),
		cannotEnableSflowWhenAgentIpIsZero(13332),
		slotLicenseGrantRequiredToEnableThisPort(13333),
		qosIngressPeakRateCanNotExceedPortCapability(13334),
		autoNegAdvertisement2500MbFullNotSupported(13335),
		autoNegAdvertisement5000MbFullNotSupported(13336),
		noAdminSettingForSpeed25000(13337),
		channelizationNotSupportedInThisRelease(13338),
		noAdminSettingForSpeed2500(13339),
		noAdminSettingForSpeed5000(13340),
		noAdminSettingForSpeed10000(13342),
		operationNotAllowedOnInsightPort(13343),
		sflowDisableAppTelemetry(13345),
		sflowCollectorNotConfigured(13346),
		sflowShouldBeEnabled(13347),
		cannotEnableAppTelemetryWhenIpv6SourceGuardIsConfigured(13349),
		cannotEnableAppTelemetryWhenIpv6FilterIsConfigured(13350),
		forwardErrorCorrectionNotSupported(13351),
		appTelemetryNotSupportedOnThisPlatform(13352),
		vlanNameCannotBeTheSameAsPortIfName(13353),
		vlanNameCannotBeTheSameAsMltName(13354),
		mltNameCannotBeTheSameAsPortIfName(13355),
		mltNameCannotBeTheSameAsVlanName(13356),
		vlanNameCannotBeTheSameAsAnyMltDefaultName(13357),
		mltNameCannotBeTheSameAsAnyVlanDefaultName(13358),
		fastPoeNotSupported(13359),
		perpetualPoeNotSupported(13360),
		fastPoeDisabled(13361),
		perpetualPoeDisabled(13362),
		featureIsNotSupportedOnThisInterface(13363),
		cannotEnableAppTelemetryWhenAdvancedFeatureModeIsDisabled(13364),
		qosEgressShaperRateNotValidOnAllPortsOfMlt(13365),
		isidBindingsToVlanOrVrfNotAllowedInAdvFeatureModeDisabled(13366),
		poeLimitNotAvailable(13367),
		specialCharactersAreNotAllowedInVlanName(13368),
		specialCharactersAreNotAllowedInMltName(13369),
		sflowNotSupportedOnThisInterface(13371),
		sflowCollectorNotSupportedOnThisInterface(13372),
		slamonInstallCertRequiresCertFile(13417),
		slamonCantOpenCertFile(13418),
		slamonCantSyncCertFile(13419),
		slamonCantInstallCertFile(13420),
		slamonAgentAddressRequired(13421),
		slamonInvalidCertFile(13422),
		slamonAgentPortCollision(13424),
		slamonAgentAddressNotChangeable(13425),
		slamonAgentAlreadyEnabled(13426),
		slamonAgentIpAddressMustBeDeletedFirst(13427),
		isidAlreadyExists(13501),
		isidDoesNotExist(13502),
		operationNotAllowedOnTransparentUniInterface(13503),
		transparentUniOperationNotAllowedOnCvlanIsid(13504),
		transparentUniPortsCannotBeAddedToMlt(13505),
		transparentUniInterfaceCannotBeCofiiguredOnBrouter(13506),
		transparentUniCannotBeConfiguredOnIsisInterface(13507),
		portsPartOfMltCannotBeAddedToTransparentUni(13508),
		portOperationsNotAllowedOnTransparentUniInterface(13509),
		vrfConfigurationNotAllowedOnTransparentUniInterface(13510),
		stpOperationNotAllowedOnTransparentUniInterface(13511),
		vlanCannotAddTransparentUniMembers(13512),
		ipConfigurationNotAllowedOnTransparentUniInterface(13513),
		vrrpConfigurationNotAllowedOnTransparentUniInterface(13514),
		isisConfigurationNotAllowedOnTransparentUniInterface(13515),
		isidAlreadyExistsForTransparentUniInterface(13516),
		eapolNotAllowedOnTransparentUniInterface(13517),
		eapolEnabledPortsCannotBeTransparentUniPort(13518),
		slppEnabledPortsCannotBeTransparentUniPort(13519),
		portPartOfVrfCannotBeTransparentUniPort(13520),
		privateVlanConfigNotAllowedOnTransparentUniInterface(13521),
		transparentUniOperationNotAllowedOnIpVpnIsid(13523),
		transparentUniMltCannotBeDeleted(13522),
		lacpEnabledPortsCannotBeTransparentUni(13524),
		cannotConfigureLacpOnTransparentUniInterface(13525),
		removeVlanFromPortsBeforeAddingToTransparentUni(13526),
		ipSpoofDetectNotAllowedOnTransparentUniInterface(13527),
		invalidIsidMacLimitLearningValue(13528),
		cannotConfigTransparentUniPortForSwitchedUniPort(13529),
		cannotEnableMefUniOnFaEnabledPort(13530),
		cannotAddMltPortToSwitchedUniPort(13531),
		switchedUniPortsCannotBePartOfAnyVlan(13532),
		brouterPortsNotAllowedOnSwitchedUniInterface(13533),
		cannotEnableSpanningTreeOnMefUniEnabledOrFaPorts(13534),
		cannotDisabeEncapsulationOnSwuniOrFaMlt(13535),
		cannotDeleteMefUniEnabledMlt(13536),
		cannotAddSwitchedUniPortToMlt(13537),
		switchedUniMltCannotBePartOfAnyVlan(13538),
		cannotConfigTuniMltForSwuniMlt(13539),
		cannotConfigSwuniMltIfFaEnableOnMlt(13540),
		cannotDisableMefUniIfEndpointAlreadyCreated(13541),
		cannotDisabeEncapsulationOnSwuniOrFaPort(13542),
		cannotConfigSwitchedUniInOtherMode(13543),
		cannotConfigSwitchedUniMltInOtherMode(13544),
		slppAllowedOnSuniPortOnlyPlatformVlanAssociateIsid(13545),
		cannotEnableFaOnMefUniPort(13546),
		cannotEnableFaOnMefUniMlt(13547),
		mefUniMustBeEnabledBeforeCreatingEndpoint(13548),
		endPointAlreadyExists(13549),
		onlyPortBasedVlanToSwitchedUniIsid(13550),
		endPointDoesNotExist(13551),
		notAllowToDeleteEndPointForDiscoverIsidOriginType(13552),
		notAllowToDeleteDiscoverEndpointsForConfigIsidOriginType(13553),
		cannotDeleteDiscoverTypeIsid(13554),
		cannotSetBpduIfEndpointNotExist(13555),
		cannotConfigSwitchedUniPortForDiffCvidSameIsid(13556),
		cannotConfigSwitchedUniMltForDiffCvidSameIsid(13557),
		cannotConfigSameEndpointInMoreThanOneIsid(13558),
		cannotConfigDefaultVlanForSwuniMltPort(13559),
		cannotConfigDefaultVlanForSwuniPort(13560),
		cannotConfigFaEnabledPortToTuniPort(13561),
		cannotConfigFaEnabledMltToTuniMlt(13562),
		faServerOnly(13563),
		faCannotChangeMgmtIsid(13564),
		mustSetFaMgmtCvidAndMgmtIsidTogether(13565),
		cannotRemoveSwitchedUniPortFromVlan(13566),
		cannotRemoveSwitchedUniMltFromVlan(13567),
		cannotRemoveVlanFromSwitchedUniFaMlt(13568),
		cannotEnableSwuniFaOnSpbmNniPort(13569),
		cannotEnableSwuniFaOnSpbmNniMlt(13570),
		cannotEnableBpduOnSwuniIsidWithPlatformVlan(13571),
		bpduCanOnlyBeEnabledForUntaggedTraffic(13572),
		cannotConfigFaOnMltFaIntfPort(13573),
		faMgmtIsidCvidSetToDefTogether(13574),
		cannotEnableStpOnMefUniOrFaEnabledMltPorts(13575),
		faInterfaceDoesNotExist(13576),
		cvid4095isNotSupported(13577),
		cannotEnableSpbMulticastIsidInDynRange(13578),
		cannotCreateFaIntfOnMltPort(13579),
		cannotDisableFaOnFeOnaPort(13580),
		cannotAssociateSwuniIsidWithBpduEnabledEndptToVlan(13581),
		cannotEnableMefUniFaOnEapolEnabledPort(13582),
		mustSetTypeWhenCreateIsid(13583),
		ipv6BrouterPortsNotAllowedOnSwitchedUniInterface(13584),
		elanIsidCannotAssociateWithVistVlan(13585),
		virtualIstVlanCannotAssociateWithElanIsid(13586),
		faCanOnlyBeConfiguredOnPortAndMltIntf(13587),
		cannotEnableFlexUniFaWhenSpbmIsDisabled(13588),
		deleteIsidBeforeDisableSpbm(13589),
		disableFlexUniFaBeforeDisableSpbm(13590),
		cannotCreateIsidWhenSpbmIsDisabled(13591),
		cannotEnableFlexUniFaWhenVlacpIsEnabledOnPort(13592),
		cannotEnableVlacpWhenFlexUniFaIsEnabledOnPort(13593),
		cannotConfigIgmpStaticOnFlexUniFaEnabledPortMltPort(13594),
		cannotConfigStaticArpOnFlexUniFaEnabledPortMltPort(13595),
		disableLacpBeforeChangingLacpKeyForFlexUniFaEnabledMlt(13596),
		cannotEnableBpduOnDiscMgmtEndpoint(13597),
		cannotAddFeOnaPortToFaMlt(13598),
		cannotConfigFaOnFeOnaPortOrMltWithFeOnaPort(13599),
		portNotMACSecCapable(13601),
		portNotAssociatedToAConnectivityAssociation(13602),
		macSecEnabledOnPort(13603),
		macSecConnectivityAssociationDoesNotExist(13604),
		macSecPortAlreadyAssociatedToConnectivityAssociation(13605),
		macSecEncryptionNotEnabledOnPort(13606),
		macSecCAAssociatedToPort(13607),
		macSecMaximumConnectivityAssociationConfigured(13608),
		macSecConnectivityAssociationAlreadyExists(13609),
		macSecConnectivityAssociationKeyInvalidValue(13610),
		macSecConnectivityAssociationNameInvalidValue(13611),
		premierMACSecSoftwareLicenseViolation(13612),
		cannotDisableAutoNegotiationWhenMacsecAssociated(13613),
		portCannotAssociateToMacsecWhenAutoNegIsDisabled(13614),
		macSecNotSupportedWith100MbFullAutoNegAdvert(13615),
		macSecReplayProtectIsNotSupportedInThisRelease(13616),
		macsecCipherSuiteNotSetOnPort(13617),
		cannotModifyCipherSuiteOnPort(13618),
		macsecMkaProfileDoesNotExist(13619),
		macsecMkaCannotDeleteProfileAssociatedWithPort(13620),
		macsecMkaCannotModifyProfileAssociatedWithPort(13621),
		macsecMkaPortAssociatedWithAnotherMkaProfile(13622),
		macsecMkaNoProfileAssociatedWithPort(13623),
		macsecMkaNotEnabledOnthePort(13624),
		macsecMkaNoProfileCreatedAsStaticConfigPresent(13625),
		macsecCannotEnableMkaMacsecAsDynamicConfigPresent(13626),
		macsecMkaCannotRemoveProfileAsMkaEnabledPort(13627),
		macsecMkaEnabledOnPort(13628),
		macsecMkaConnectivityAssociationIsPresent(13629),
		macsecMkaProfileAssociatedWithAnotherPort(13630),
		macsecMkaConnectivityAssociationWithKeyParityNotAllowed(13631),
		macsecMkaProfileNameInvalidValue(13632),
		macsecMkaMaximumMkaProfilesExists(13633),
		macsecMkaNotSupported(13634),
		macsecMkaOperationNotAllowedAsPortAssociatedWithMkaProfile(13635),
		macsecMkaOperationNotAllowedAsStaticMacsecConfigPresentOnPort(13636),
		macsecMkaProfileNameAlreadyExists(13637),
		macsecMkaProfileIdAlreadyExists(13638),
		macsecMkaCannoEditExistingMkaProfileName(13639),
		macSecEncryptionTwoSecureKeysIsNotSupported(13640),
		macsecMkaReplayProtectEnable(13641),
		macsecMkaReplayProtectDisable(13642),
		macsecMkaReplayProtectWindowSizeRequired(13643),
		macsecMkaCannotDisableReplayProtect(13644),
		macsecMkaActorsPriorityInvalidValue(13645),
		filterDeleteArpOrIp(13701),
		conflictingAceAttrArp(13702),
		ipv6FiltersNotSupported(13703),
		ipv6OutPortTypeAclNotSupported(13704),
		ipv6AclCtrlPktActionNotSupported(13705),
		ipv6QosAceNotSupported(13706),
		ipQosAceNotSupported(13707),
		noIpv6ICMPV6AceSupport(13708),
		noDstMacQualifierSupport(13709),
		noSrcMacQualifierSupport(13710),
		noVlanQualifierSupport(13711),
		noVlanTagQualifierSupport(13712),
		enableBootConfigIpv6EgressFilterFlag(13713),
		noInNniFilterSupport(13714),
		enableBootFlagSpbmForInNniFilter(13715),
		noIpv4CtrlPktActionSupport(13716),
		aclIsidAlreadyAttached(13717),
		aclIsidTuniSuniNotSupported(13718),
		aclIsidNotAvailable(13719),
		aclIsidNotMappedToVlanOrVrf(13720),
		aclInvsnConfiguredDeleteAcl(13721),
		aceIsidNotConfiguredOnAcl(13722),
		deleteAllAceBeforeDeleteIsid(13723),
		vsnAclMatchtypeUnionlyNotSupported(13724),
		vsnAclMatchtypeBothNotSupported(13725),
		vsnBasedAclNoPort(13726),
		vsnBasedAclNoVlan(13727),
		portBasedAclNoIsid(13728),
		vlanBasedAclNoIsid(13729),
		portBasedAclNoMatchtype(13730),
		vlanBasedAclNoMatchtype(13731),
		invsnFilterNotSupported(13732),
		enableBootFlagSpbmForInvsnFilter(13733),
		invsnFilterIpShortcutNotSupported(13734),
		ipv6FilterConfigNotAllowedWhenAppTelemetryIsEnabled(13737),
		invsnFilterIpShortcutSupportedOnlyOnBoth(13738),
		filterArpOperationOnEgressPortNotSupported(13739),
		isisAcceptIsidAlreadyExist(13801),
		igmpConfigsNotAllowedInSpbmConfigMode(13802),
		virtualIstNotAllowedOnMltInSpbmConfigMode(13803),
		plsbEnableIp4ScBeforeEnableIp6Sc(13804),
		plsbConfigIp6SourceAddrBeforeEnableIp6Sc(13805),
		plsbDisableIp6ShortcutsBeforeDisableIp4Shortcuts(13806),
		spbmMaxNumOfIsisInterfReached128(13807),
		plsbCannotSetIp6SourceAddrToZeroWhenIp6ScEnabled(13808),
		plsbCannotRemoveTunnelSrcIpWhenIsisLogicalIntfEnabled(13809),
		plsbCannotModifyTunnelSrcIpWhenIsisLogicalIntfEnabled(13810),
		plsbCannotDeleteVrfAssociatedWithTunnelSourceIp(13811),
		plsbTunnelSourceIpNotConfigured(13812),
		plsbTunnelSourceIpInvalid(13813),
		plsbTunnelSourceIpDoesNotExistInGrt(13814),
		plsbTunnelSourceIpDoesNotExistInVrf(13815),
		ipInUseAsIsisIpTunnelSourceAddr(13816),
		isisCannotDeletePlsbInstanceWithIpTunnelSourceAddress(13817),
		plsbIsidCannotBeAssignedToTunnelVrf(13818),
		plsbLogicalInterfaceNameAlreadyExists(13819),
		plsbCannotModifyIpTunnelMtuWhenIsisLogicalIntfExists(13820),
		plsbIsisLogicalInterfaceOfTypeL2AndL3CoreCannotExistTogether(13821),
		plsbL2CoreIsisLogicalInterfaceConfiguredPortCantBeAddedToVlan(13822),
		plsbL2CoreIsisLogicalIntfConfiguredMltCantBeAddedToVlan(13823),
		plsbL2CoreIsisLogicalIntfConfiguredPortCantBeAddedToMlt(13824),
		plsbMaxNumOfLogicalIsisIntfConfigured(13825),
		plsbMltIsConfiguredAsIsisLogicalTunnelIntfMlt(13826),
		plsbPortIsConfiguredAsIsisLogicalTunnelIntfPort(13827),
		spbmMaxNumOfIsisInterfReached255(13828),
		plsbIsisLogicalIntfDestIfIndexCannotBeModified(13829),
		plsbCannotConfigureSameIsisLogicalInterfaceVidAndSpbmBvlanId(13830),
		plsbIsisLogicalIntfVidsOutOfRange(13831),
		plsbIsisLogicalIntfExistsWithSameDestIp(13832),
		plscIsisLogcalIntfCannotConfigOnMefUniFaPortMlt(13833),
		cannotEnableMefUniFaOnLogicalIntf(13834),
		cannotConfigPlsbIsisIntfOnMefUniFaEnabledPortMlt(13835),
		isisLogicalInterfaceIdDoesNotExist(13836),
		isisLogicalInterfacePortCannotBeBrouter(13837),
		invalidIsisLogicalInterfaceDestPort(13838),
		cannotConfigFeOnaOnFaPortMltPort(13839),
		spbmConfigsNotAllowedInAdvancedFeatureModeDisabled(13840),
		cannotAddSpbmNniToNonSpbmBvlan(13842),
		noBrouterAndSpbmNniOnSamePort(13843),
		bootConfigFlagNniMstpConflictWithSpbmNni(13844),
		spbmSysidCannotBeSameAsSmltVirtBmac(13845),
		spbmSmltPeerSysidCannotBeSameAsSmltVirtBmac(13846),
		spbmHaNeedsDisabled(13847),
		cannotEnableMstpOnSpbmNniPort(13848),
		isisLogicalInterfaceRequireTwoVlansPerPlsbInstance(13850),
		spbmNicknameSetRangeServerRunning(13851),
		spbmNicknameServerSettingWithSpbmDisabled(13852),
		spbmDisableNicknameServerRunning(13853),
		spbmDisableNicknameServerRangeConfigured(13854),
		spbmFactoryDefaultWithFabricOptionIsNotSupported(13855),
		spbmEnableServerStaticSpbmNicknameInDynamicRange(13856),
		spbmEnableServerWithoutStaticNicknameConfigured(13857),
		spbmClearNicknameServerRunning(13858),
		isisCannotEnableIpv4ShortcutForMigrateLoopback(13859),
		isisCannotEnableIpv6ShortcutForMigrateLoopback(13860),
		migrateFeatureNoLongerSupported(13861),
		plsbIsidCannotBeAssignedToTunnelVlan(13862),
		plsbCannotDeleteVlanAssociatedWithTunnelSourceIp(13863),
		cannotSetIsidNameWithSpecialChar(13866),
		duplicateIsidName(13867),
		defaultIsidNameCannotBeUsed(13868),
		vrfPim6LimitExceeded(14001),
		pim6FeatureNotSupported(14002),
		vrfPim6DoesNotExist(14003),
		pim6GlobNotSuppActChkInterval(14004),
		pim6ConfigsNotAllowedInSpbmConfigModeEnabled(14005),
		pim6InvalidMode(14006),
		pim6GlobInvalidUniRouteChangeTimeOut(14007),
		pim6GlobInvalidDiscDataTimeOut(14008),
		pim6GlobInvalidCRPADVTimeOut(14009),
		pim6GlobInvalidBootstrapPeriod(14010),
		pim6ActChkIntervalNotAllowed(14011),
		pim6GlobInvalidActChkInterval(14012),
		pim6InvalidHelloInterval(14013),
		pim6InvalidJPInterval(14014),
		pim6GlobInvalidRegSupprTimeOut(14015),
		pim6NotEnabled(14016),
		pim6StaticRpNotEnabled(14017),
		pim6GlobInvalidFwdCacheTimeOut(14018),
		pim6InvalidModeChg(14019),
		pim6GlobInvalidFastJP(14020),
		pim6InvalidEnable(14021),
		pim6OrMldAlreadyEnabled(14022),
		pim6StaticRPEnabled(14023),
		pim6GroupAddressInvalid(14024),
		pim6StaticRPEntryExists(14025),
		fhsMaxIpv6AclReached(14101),
		fhsMaxEntriesPerAclReached(14102),
		fhsAclInUse(14103),
		fhsAclNotExist(14104),
		fhsIpv6AclMaskMismatch(14105),
		fhsMaxMacAclReached(14106),
		fhsMaxRagPoliciesReached(14107),
		fhsRagHopLimitMismatch(14108),
		fhsRagPolicyInUse(14109),
		fhsRagPolicyNotExist(14110),
		fhsDhcpgPoliciesReached(14111),
		fhsDhcpgPolicyInUse(14112),
		fhsDhcpgPolicyNotExist(14113),
		fhsDhcpgPreferenceLimitMismatch(14114),
		fhsInvalidDeviceRole(14115),
		fhsCantAttachRagPolicyWhenDeviceRoleIsNotRouter(14116),
		fhsCantAttachDhcpgPolicyWhenDeviceRoleIsNotServer(14117),
		fhsCantConfigDeviceRoleToNonRouterWhenPolicyAttached(14118),
		fhsCantConfigDeviceRoleToNonServerWhenPolicyAttached(14119),
		fhsIpv6AclMaskMinValue(14120),
		fhsMaxStaticBindingEntriesReached(14121),
		fhsCantCreateBindingEntryWithMulticastMacAddr(14122),
		fhsCantCreateBindingEntryWithMulticastIpAddr(14123),
		fhsCantCreateBindingEntryWithLinkLocalAddr(14124),
		fhsCantDeleteDynamicBindingEntry(14125),
		fhsStaticBindingEntryNotExist(14126),
		fhsCantCreateBindingEntryWithUnspecIpAddr(14127),
		fhsCantCreateBindingEntryWithInternalLoopbackIpAddr(14128),
		fhsCantCreateBindingEntryWithAllZeroMacAddr(14129),
		fhsCantCreateBindingEntryWithBroadcastMacAddr(14130),
		unprintableCharacterIsNotAllowedInEmailAddress(14201),
		emailAddressLengthExceedsMaxLimitOf254Chars(14202),
		numOfEmailAddressExceedsMaxSupportedLimit(14203),
		lengthOFEmailAddressListTooLong(14204),
		smtpServerAddrOnlySupportsIpv4AndHostname(14205),
		portCannotBeModifiedWhileSmtpIsEnabled(14206),
		invalidSmtpServerPortNumber(14207),
		invalidStatusSendTimer(14208),
		smtpReceiverEmailCannotBeEmptyWhileSmtpIsEnabled(14209),
		smtpServerAddrCannotBeModifiedWhileSmtpIsEnabled(14210),
		smtpCannotBeEnabledWithoutServerAddr(14211),
		smtpCannotBeEnabledWhileReceiverEmailAddrIsEmpty(14212),
		doubleQuotationMarkIsNotAllowedInEmailAddress(14213),
		commaIsNotAllowedInEmailAddress(14214),
		invalidEventIdsListInputFormat(14215),
		nonExistIpv6McastAddress(14301),
		invalidIpv6MulticastAddress(14302),
		invalidQueryIntervalMldIntfTbl(14303),
		invalidMldIntfTblVersion(14304),
		invalidQueryMaxResponseTime(14305),
		invalidRobustnessValue(14306),
		invalidLastMembQueryInterval(14307),
		mldAdminVerConfiguredLessThanOperatingVer(14308),
		mldPimOrMldAlreadyEnabled(14309),
		mldPimModeMldVersionIncompatible(14310),
		mldQueryIntervalGreaterThanMaxResTime(14311),
		mldAlreadyEnabled(14312),
		mldPimEnabledInSSMMode(14313),
		mldDisableV2First(14314),
		mldNotVersion2(14315),
		mldDisableSsmSnooping(14316),
		mldFlushActionNotAllowedWhenMldSnoopingIsDisabled(14317),
		vxlanCannotDeleteVtepSrcIpWhenRemoteVtepIsConfigured(14401),
		maxNumOfVtepsAreConfigured(14402),
		vxlanVtepSourceIpNotConfigured(14403),
		vxlanVtepRemoteIpCannotBeLocalIp(14404),
		vxlanVtepExistsWithSameRemoteIp(14405),
		vxlanVtepRemoteIpCannotBeModified(14406),
		vxlanVtepNameAlreadyExists(14407),
		vxlanVtepDoesNotExist(14408),
		vxlanVnidCannotBeSameAsIsid(14409),
		vxlanInvalidVtepId(14410),
		vxlanCannotModifyIsidAssociationdWithVnid(14411),
		vxlanVnidDoesNotExist(14412),
		vxlanVtepIsNotAssociatedWithVnid(14413),
		vxlanMaxVtepsAssociatedWithVnid(14414),
		vxlanSameEndPointCannotBePresentInBothVnidAndIsid(14415),
		vxlanBaseModeIsidValueCannotBeSameAsVnid(14416),
		vxlanCannotDeleteIsidAssociatedWithVnid(14417),
		vxlanCannotConfigureSwuniEndpointsUnderVnidInInterworkingMode(14418),
		vxlanIsidAssociatedWithVnid(14419),
		vxlanCannotDeleteVlanConfiguredWithIsidAssociatedWithVnid(14420),
		vxlanCannotAssociateTransparentUniIsidToVnid(14421),
		vxlanIsidCannotBeAssociatedWithMoreThanOneVnid(14422),
		vxlanIsidCannotBeAssignedToVtepSrcIpVrf(14423),
		vxlanCannotDeleteVrfAssociatedWithVtepSourceIp(14424),
		vxlanConfigHasVnidSameAsIsid(14425),
		vxlanVirtualIstConfigured(14426),
		vxlanSmltExist(14427),
		vxlanIpInUseAsVtepSrcIpAddr(14428),
		vxlanBaseSmltMltCannotBeVnidEndPoint(14429),
		vxlanBaseModeSmltVistConfigNotAllowed(14430),
		vxlanIpInUseAsIpSrcAddr(14431),
		vxlanIpInUseAsIpTunnelSrcAddr(14432),
		vxlanCannotDeleteVtepSrcIpWhenVnidConfigured(14433),
		vxlan16777215IsWellKnownVnid(14434),
		vxlanCannotEnableVxlanGwFullInterworkingWhenAdvancedFeatureModeDisabled(14435),
		vxlanConfigsNotAllowedWhenAdvancedFeatureModeDisabled(14436),
		vxlanBaseModeVnidValueCannotBeSameAsIsid(14437),
		vxlanGwFullInterworkingModeEnabled(14438),
		vxlanConfigsNotAllowedInSpbmConfigModeDisabled(14439),
		vxlanVtepIsAlreadyAssociatedWithVnid(14440),
		vxlanFaIsidShouldBeConfigured(14441),
		vxlanInvalidIsid(14442),
		vxlanVtepSrcIpCannotBeSameAsVtepRemoteIp(14443),
		vxlanInvalidVtepName(14444),
		vxlanVnidCannotBeSameAsPlsbBvlanViceVersa(14445),
		vxlanGwInterworkingCannotBeEnabledInNonAdvFeatureMode(14446),
		vxlanGwInterworkingNotSupported(14448),
		chefClientCertFileNotSpecified(14901),
		chefClientCannotOpenCertFile(14902),
		chefClientAddressRequired(14903),
		chefClientInvalidCertFile(14904),
		chefClientAddressNotChangeable(14905),
		chefClientCannotChangeConfigurationWhenEnabled(14906),
		chefClientServerAddressRequired(14907),
		chefClientActivateSoftwareToEnable(14908),
		invalidUserPasswordRule(1233),
		invalidUserPasswordRulePostNotification(1234),
		invalidUserPasswordRulePreNotification(1235),
		invalidUserPasswordRuleAgeOut(1236),
		invalidUserLogonAttenmpts(1237),
		invalidUserPasswordRuleChangeInterval(1238),
		pimgwConfigsNotAllowedInSpbmConfigModeDisabled(13901),
		pimgwNotSupportedOnPlatform(13902),
		spbMcastCannotBeEnabledWithPimgw(13903),
		pimgwCannotBeEnabledWithSpbMcast(13904),
		spbMcastCannotBeDisabledWithPimgwEnabled(13905),
		spbMcastCannotBeEnabledWithPimgwEnabled(13906),
		pimgwCannotBeDisabledWithSpbMcastEnabled(13907),
		pimgwCannotBeEnabledWithSpbMcastEnabled(13908),
		pimgwCannotBeEnabledWithoutIpAddr(13909),
		pimgwCannotBeEnabledWithSnoop(13910),
		pimgwCannotBeEnabledWithSnoopSpb(13911),
		pimgwCannotBeEnabledWithPim(13912),
		pimgwCannotBeEnabledWithDvmrp(13913),
		vlanPimCannotBeEnabledWithPimGateway(13914),
		pimgwAgentNotEnabled(13915),
		pimgwControllerNotEnabled(13916),
		pimgwInterfaceInvalidHelloInterval(13917),
		pimgwInterfaceInvalidJoinPruneInterval(13918),
		pimgwCannotSetHelloJoinPruneIntervalWithoutIpAddress(13919),
		vlanPimCannotBeConfiguredWithPimGateway(13920),
		vlanIgmpCannotBeConfiguredWithPimGateway(13921),
		pimgwCannotBeEnabledWithClipIf(13922),
		pimgwCannotBeEnabledWithMgmtIf(13923),
		pimgwAgentIsAlreadyEnabled(13924),
		pimgwControllerIsAlreadyEnabled(13925),
		smltOrIstCannotBeAddedToPimGatewayVlan(13926),
		pimgwCannotBeEnabledOnSmltOrIstPort(13927),
		pimgwCannotBeEnabledOnSmltVlan(13928),
		pimgwVlanPortCannotBeAddedToSmlt(13929),
		smltCannotBeEnabledOnPimGatewayVlanPort(13930),
		pimgwCannotBeEnabledWithoutIpCirc(13931),
		pimgwCannotBeEnabledOnIsidConfiguredVlan(13932),
		isidCannotBeSetOnPimGatewayVlan(13933),
		pimgwCannotBeEnabledOnVistVlan(13934),
		pimgwCannotBeEnabledIfDvrEnabled(13935),
		pimgwCannotAddForeignSrcWhenControllerIsDisabled(13936),
		pimgwCannotDeleteForeignSrcWhenControllerIsDisabled(13937),
		pimgwCannotConfigHelloIntervalWithoutPimgwInterface(13938),
		pimgwCannotConfigJoinPruneIntervalWithoutPimgwInterface(13939),
		pimgwCannotDeleteForeignSrcWhenForeignSourceEntryDoesNotExist(13940),
		pimgwCannotAddForeignSrcWhenForeignSourceEntryAlreadyExist(13941),
		dvrNotSupported(14501),
		disableDvrBeforeChangingDomainId(14502),
		dvrIsNotEnabledForDomainId(14503),
		disableDvrBeforeChangingRole(14504),
		ipCommandsNotSupportedOnDvrLeaf(14505),
		cannotEnableDvrLeafIpConfigured(14506),
		vistAlreadyExistRemoveFirst(14507),
		vistAlreadyExist(14508),
		cannotConfigDvrVistIfGlobalVistConfigured(14509),
		vistDoesNotExist(14510),
		configGwIpAddrBeforeEnablingDvr(14511),
		dvrCantBeEnabledIfPimgwEnabled(14512),
		dvrCantBeEnabledIfSnoopEnabled(14513),
		vlanSnoopCantBeEnabledInDvrNode(14514),
		configIpInterfaceBeforeEnablingDvr(14515),
		disableDvrBeforeChangingGwIpAddr(14516),
		enableControllerBeforeEnablingDvrOnVlan(14517),
		enableControllerBeforeConfiguringGwIpv4(14518),
		platformVlanNotAllowedOnLeaf(14519),
		removePlatformVlanBeforeEnableLeaf(14520),
		notAllowPortsInDefaultVlanOnDvrLeaf(14521),
		cannotEnableDvrLeafIfPortsInDefaultVlan(14522),
		cannotConfigPlatformVlanOnDvrLeaf(14523),
		notAllowToConfigVlanBasedAclRules(14524),
		cannotEnableDvrLeafVlanBasedAclExists(14525),
		notAllowToConfigPortBasedAclRules(14526),
		cannotEnableDvrLeafPortBasedAclExists(14527),
		notAllowToConfigTuniOnDvrLeaf(14528),
		cannotEnableDvrLeafWhenTuniExists(14529),
		cannotEnableDvrLeafWhenLogicalIntfExist(14530),
		notAllowToConfigLogicalIntfOnDvrLeaf(14531),
		cannotConfigGlobalVistIfDvrVistConfigured(14532),
		cannotConfigPimgwOnDvrLeaf(14533),
		cannotEnableDvrLeafWhenPimgwEnabled(14534),
		cannotConfitVrfOnDvrLeaf(14535),
		cannotEnableDvrLeafWhenVrfExists(14536),
		disableDvrBeforeRemovingGwIpAddr(14537),
		dvrConfigsNotAllowedInSpbmConfigModeDisabled(14538),
		cannotEnableDvrWhenSpbmIsDisabled(14539),
		removeIpInterfaceBeforeEnablingDvr(14540),
		enableBootConfigFlagDvrLeafMode(14541),
		dvrIsNotEnabled(14542),
		disableBootConfigFlagDvrLeafMode(14543),
		configIsidForVlanFirst(14544),
		vistNotAllowedOnDvrLeaf(14545),
		cannotEnableMoreSpecificNonLocalWhenDvrEnabled(14546),
		cannotEnableDvrWhenMoreSpecificNonLocalEnabled(14547),
		vlanIpAddAndDvrGwipAreNotInSameSubnet(14548),
		cannotConfigPimgwOnDvrVlan(14549),
		cannotEnableDvrVlanWhenPimgwIsConfigured(14550),
		cannotEnableDvrVlanWhenRsmltIsEnabled(14551),
		cannotEnableRsmltOnDvrVlan(14552),
		cannotConfigVrrpOnDvrVlan(14553),
		cannotEnableDvrVlanWhenVrrpIsConfigured(14554),
		cannotEnableDvrWhenBackboneIsEnabled(14555),
		cannotEnableBackboneWhenDvrIsEnabled(14556),
		disableDvrBeforeChangingOrDeletingIsid(14557),
		cannotConfigureInbandMgmtIpForDvrController(14558),
		cannotEnableControllerwhenInbandMgmtIpConfigured(14559),
		dvrSpbmMcastCommandsNotSupportedOnDvrLeaf(14560),
		dvrControllerDoesNotExist(14561),
		dvrLeafDoesNotExist(14562),
		cannotConfigLoopbackIpOnDvrLeaf(14563),
		sameGwIpv4AndVlanIpIsNotAllowed(14564),
		isidReservedForDvrUse(14565),
		dvrVistNotAllowedOnDvrController(14566),
		injectDefaultRouteNotAllowedOnDvrLeaf(14567),
		cannotConfigBrouterIpOnDvrLeaf(14568),
		dvrConfigNotAllowedOnLeaf(14569),
		dvrIpvpnOrIsidNotConfiguredInVrf(14570),
		macOffSetNotAllowedOnDvrEnabledVlan(14571),
		disableDvrForVlanBeforeDeletingIpAddress(14572),
		dvrRedistributionConfigAllowedOnlyOnController(14573),
		cannotEnableBackboneWhenDvrLeafModeIsTrue(14574),
		cannotConfigDvrGwIpOnSpbmBvlan(14575),
		createDvrGloballyBeforeConfiguringIpOnDvrVlan(14576),
		cannotEnableDvrVlanWhenIpv6IsConfigured(14577),
		cannotEnableBackboneWhenDvrCtrlConfigPresent(14578),
		configurationNotAllowedWhenBackboneIsEnabled(14580),
		slppCommandsAreNotSupportedOnDvrLeaf(14581),
		dvrGwMacCreateInsufficientResources(14583),
		clearDvrHostEntryCanBeExecutedOnlyOnController(14584),
		dvrInstanceDoesNotExist(14585),
		removeSmltConfigBeforeDisablingDvrLeaf(14586),
		dvrEnableNotAllowedOnOspfEnabledVlan(14589),
		dvrEnableNotAllowedOnRipEnabledVlan(14590),
		dvrVistInvalidClusterId(14591),
		invalidDvrVistConfiguration(14592),
		isidRangeReservedForInternalUse(14595),
                dvrNotEnoughDataToModifyInstance(14596),
		cvidRangeReservedForInternalUse(14597),
		dvrGwIpNotAllowedWhenDvrOneIpFlagIsSet(14598),
		dvrOneIpFlagNotAllowedWhenDvrGwIpIsSet(14599),
		maxVrfReachedWithoutScaling(14601),
		vrfScalingCannotBeEnabledWhenVlanInExistInRange(14602),
		vrfScalingCannotBeDisabledWhenVrfCountMoreThanDefaultValue(14603),
		vlanInternallyUsedForVrfScaling(14604),
		configHasPlatformVlanConfiguredInReservedRange(14605),
		noKeyFound(14701),
		allCommandsParamtersNotFound(14702),
		invalidAction(14703),
		cannotModifyCaEntryForValidCa(14704),
		lastActionAlreadyInProgress(14705),
		revokeReasonOnlyRevokeAction(14706),
		caAlreadyAuthenticated(14707),
		noActiveCertificateFound(14708),
		revocationReasonNotFound(14709),
		certificateAlreadyInstalled(14710),
		keyAssociatedWithActiveCert(14711),
		subjectScalarAssociatedWithCert(14712),
		recordNotFound(14713),
		strToDateConversionFailed(14714),
		couldNotOpenDirectory(14715),
		fileNameNotFound(14716),
		caNotAuthenticated(14717),
		validCertificateAlreadyPresent(14718),
		cannotDeleteTrustPoints(14719),
		caEntryAlreadyExits(14720),
		maxTrustpointsReached(14721),
		invalidRowStatus(14722),
		allSubjectScalarsNotFound(14723),
		caOfflineCertNotInstalled(14724),
		noKeyPairConfigured(14725),
		certificateNotEnrolled(14726),
		noOfflineSubjectCertificateInstalled(14727),
		offlineCertificateInstalled(14728),
		validityDaysValidOnlyForRenewAndEnroll(14729),
		invalidSubjectOrKey(14730),
		caEntryPresent(14731),
		subjectAndInstallFileCannotBeConfiguredTogether(14732),
		invalidKeySize(14733),
		noCaFound(14734),
		digiCertChallengePasswordValidOnlyWithRenewAndEnroll(14735),
		digiCertCertificateExpired(14736),
		digiCertReadCertificateFileFailed(14737),
		digiCertReadCertificateFileValidityFailed(14738),
		digiCertSubjectCertificateAlreadyInstalled(14739),
		digiCertNotRootCaCertificate(14740),
		digiCertKeyAlreadyPresent(14741),
		digiCertKeyAssociatedWithCaEntry(14742),
		digiCertSubjectCertificateInstalled(14743),
		digiCertInvalidFileFormat(14744),
		digiCertCdpUrlNotConfigured(14745),
		digiCertSubjectCertificateNotInstalled(14746),
		digiCertFileNameNotFoundInOfflineCertDir(14747),
		digiCertFileNameNotFoundInOfflineCaCertDir(14748),
		digiCertFileNameNotFoundInOfflineRootCaCertDir(14749),
		digiCertNoKeyFound(14750),
		digiCertNoOfflineCACertificateInstalled(14751),
		digiCertNoOfflineRootCACertificateInstalled(14752),
		digiCertNoOfflineCRLFileInstalled(14753),
		digiCertFileNameNotFoundInOfflineCrlDir(14754),
		digiCertInvalidValueToGenerateCsr(14755),
		digiCertNotCACertificate(14756),
		digiCertNotRootCertificate(14757),
		digiCertRootCaOfflineCertNotInstalled(14758),
		digiCertRootCertFileAlreadyInstalled(14759),
		digiCertCaCertFileAlreadyInstalled(14760),
		digiCertOnlineCAEntryExists(14761),
		digiCertKeyPairGenInProgress(14762),
		digiCertNotInterCaCertificate(14763),
		digiCertOfflineCannotUseRootCertAssociatedWithOnlineCa(14764),
		digiCertOnlineCaCannotUseRootCertAssociatedWithOffline(14765),
		digiCertSubjectCountryInvalid(14766),
		digiCertSanExists(14767),
		digiCertSanNotFound(14768),
		digiCertSanInvalidAction(14769),
		digiCertSanTblFull(14770),
		digiCertCnAndSanNotFound(14771),
		digiCertPkcs12ExtractFail(14772),
		digiCertPkcs12KeyExtractFail(14773),
		digiCertPkcs12InvalidKey(14774),
		digiCertPkcs12SaveFilesFail(14775),
		digiCertSanInvalidAddress(14776),
		cannotAdminDisableFanPort(15001),
		cannotDisableIsisInterfaceOnFanPort(15002),
		cannotDeleteIsisInterfaceOnFanPort(15003),
		nlsMgmtIntfDoesNotExist(15201),
		nlsMgmtIntfAlreadyExist(15202),
		nlsMgmtIntfTypeAlreadyExist(15203),
		nlsMgmtRemoveExistingIpAddr(15204),
		nlsMgmtRemoveExistingIpv6Addr(15205),
		nlsMgmtNoIpAddrForInterface(15206),
		nlsMgmtNoIpv6AddrForInterface(15207),
		nlsMgmtPrefixLenIs128ForLoopback(15208),
		nlsMgmtMaskIs32ForLoopback(15209),
		nlsMgmtVlanIsNotCreatedYet(15210),
		nlsMgmtVrfIsNotCreatedYet(15211),
		nlsMgmtDuplicateIntfIpv6Addr(15212),
		nlsMgmtInvalidNextHopAddr(15213),
		nlsMgmtSameDestAndNextHop(15214),
		nlsMgmtStaticRoutesAreNotAllowedOnClip(15215),
		nlsMgmtSetWeightToDefaltNotAllowedOnClip(15216),
		nlsMgmtOnlyPortBasedVlanIsSupported(15217),
		nlsMgmtCannotConfigIpOnMgmtVlan(15218),
		nlsMgmtConfigMgmtIpBeforeAddingStaticRoute(15219),
		nlsMgmtConfigMgmtIpv6BeforeAddingStaticRoute(15220),
		nlsMgmtNextHopSameSubnetAsMgmtIntfAddr(15221),
		nlsMgmtCannotUseSpbmBvlanForVlanIntf(15222),
		nlsMgmtCannotDeleteVlanIfIntfIsEnabled(15223),
		nlsMgmtCannotDeleteVrfIfIntfIsEnabled(15224),
		nlsMgmtMgmtRouterNotValidForClip(15225),
		nlsMgmtCannotConfigMgmtIpIfVlanIpConfigured(15226),
		nlsMgmtCannotEnableIntfIfBothMgmtIpVossIpConfigured(15227),
		nlsMgmtMgmtIpConfiguredForVlan(15228),
		nlsMgmtCannotConfigMgmtIpv6IfVlanIpv6Configured(15229),
		nlsMgmtCannotEnableIntfIfBothMgmtIpv6VossIpv6Configured(15230),
		nlsMgmtMgmtIpv6ConfiguredForVlan(15231),
		nlsMgmtBrouterVlanIsNotAllowed(15232),
		cannotUseMgmtVlanForBrouterVlan(15233),
		sameMgmtIpShouldNotBeInOtherInst(15234),
		sameMgmtIpShouldNotBeInVossVlans(15235),
		vossIpIsSameAsMgmtIp(15236),
		sameMgmtIpv6ShouldNotBeInOtherInst(15237),
		sameMgmtIpv6ShouldNotBeInVossVlans(15238),
		vossIpv6IsSameAsMgmtIpv6(15239),
		nlsMgmtIpAddrSameSubnetAsNextHop(15240),
		nlsMgmtIpAddrOverlapInOtherInst(15241),
		nlsMgmtIpV6AddrOverlapInOtherInst(15242),
		nlsMgmtIpV6NotSupportedInLinuxKernel(15243),
		nlsMgmtNonGrtVrfNotSupportOnDvrLeaf(15244),
		nlsMgmtTooManyInterfaceTypesProvided(15245),
		nlsMgmtIpOverlapWithVossVlansInVrf(15246),
		nlsMgmtIpv6OverlapWithVossVlansInVrf(15247),
		nlsMgmtIpAddSameSubnetAsDynamicNickname(15248),
		nlsMgmtInterfaceNotEnabled(15249),
		nlsMigrateIsisLoopbackNotSupported(15250),
		nlsMigrateIpv6IsisLoopbackNotSupported(15251),
		nlsClipInterfaceNotSupported(15252),
		pingContextVrfNameIstooLong(15253),
		noSpaceAllowedInVrfName(15254),
		pingContextVrfNameCannotBeGlobalRouter(15255),
		pingContextTypeOutOfRange(15256),
		pingContextVrfNameCannotBeEmptyWhileContextTypeIsVrf(15257),
		pingContextTypeCannotBeSetToVrfWhileVrfNameIsEmpty(15258),
		nlsDhcpClientAlreadyRunning(15259),
		nlsMgmtDeleteLinkLocalIpv6NotAllowed(15260),
		nlsMgmtSourceIpNotSupported(15261),
		nlsCannotCreateMgmtVlanIfIpInterfaceExist(15262),
		nlsVossVlanIpExistsOnGivenVlanidMgmtVlanIpMustMatch(15263),
		nlsMgmtVlanIpExistsOnGivenVlanidVossVlanIpMustMatch(15264),
		nlsSameIpExistsOnMgmtClip(15265),
		nlsMgmtVlanCoexistShouldntHaveManualAndDhcp(15266),
		nlsVossVlanCoexistShouldntHaveNlsAndVossAddr(15267),
		nlsMgmtVlanCoexistCannotEnableWithoutAddr(15268),
		nlsMgmtVlanCoexistCannotDeleteLastAddrWhenEnabled(15269),
		nlsMgmtVlanCoexistCannotDeleteAddrIfNotLastVossVlanIpMatch(15270),
		nlsVossVlanCoexistCannotAddAddrIfVossIpv6EnabledNoAddr(15271),
		nlsDuplicateRouteSameMetricNotAllowed(15272),
		nlsDefRouteMetric100NotAllowed(15273),
		nlsMgmtIpCannotBeSameAsIpsecTunnelSrcIp(15274),
		nlsDhcpPreferenceWorksOnlyWithCycle(15275),
		nlsNoOobOrVlanInterfaceEnabled(15276),
		nlsMgmtIpv6NotSupported(15277),
		nlsMgmtIpCannotBeInSameInst(15278),
		nlsPingContextVrfNameCannotBeSetInNonVrfContext(15279),
		nlsMgmtEthernetL3ConfigDeprecated(15280),
		nlsMgmtVlanCoexistDhcpVossIPManualIPSimultaneous(15281),
		nlsMgmtIdUsedByDvr(15282),
		nlsMaxIpv4StaticRouteLimitReached(15283),
		nlsMaxIpv6StaticRouteLimitReached(15284),
		esSchedFull(15301),
		esSchedNotFound(15302),
		esSchedBadInterval(15303),
		esStateUnchanged(15304),
		esInvalidOp(15305),
		esNotGlobEnabled(15306),
		esGlobEnabled(15307),
		esEmodeEnabled(15308),
		esNtpDisabled(15309),
		esFiberPort(15310),
		es10gigOnlyPort(15311),
		esPortAnaNotsupp(15312),
		esGeneralError(15313),
		esPortNotEEECapable(15314),
		esNtpUnsynchronized(15315),
		lstMaxUpstreamMembersReached(15401),
		lstMaxDownstreamMembersReached(15402),
		lstPortDuplicateInUpstreamList(15403),
		lstPortAlreadyInOtherUpstreamList(15404),
		lstPortDuplicateInDownstreamList(15405),
		lstPortAlreadyInOtherDownstreamList(15406),
		lstPortIsMemberOfUpstreamMlt(15407),
		lstPortIsMemberOfDownstreamMlt(15408),
		lstPortNotInUpstreamList(15409),
		lstPortNotInDownstreamList(15410),
		lstMltDuplicateInUpstreamList(15411),
		lstMltAlreadyInOtherUpstreamList(15412),
		lstMltDuplicateInDownstreamList(15413),
		lstMltAlreadyInOtherDownstreamList(15414),
		lstMltNotInUpstreamList(15415),
		lstMltNotInDownstreamList(15416),
		lstMltContainsUpstreamMemberPorts(15417),
		lstMltContainsDownstreamMemberPorts(15418),
		lstCannotDeleteLstMemberMlt(15419),
		lstPortCannotBeAddedToMlt(15420),
		lstPortMembersCannotBeLacpEnabled(15421),
		lstPortIsMltMember(15422),
		lstLacpKeyAlreadyUsedByLstMltMember(15423),
		lstPortIsPartOfALstMltMember(15424),
		lstCannotModifyLacpAdminState(15425),
		lstCannotAddMgmtPort(15426),
		muMaximumUsersReached(15501),
		muUserNotFound(15502),
		muUserAlreadyExists(15503),
		muDefaultUser(15504),
		muCannotCreateUser(15505),
		muCannotDisableRWA(15506),
		invalidUsernameLength(15507),
		invalidPasswordLength(15508),
		muIQAgentUserCannotBeModified(15509),
		ovsdbCertFileNotSpecified(15601),
		ovsdbCannotOpenSslCertFile(15602),
		ovsdbControllerIdDoesNotExist(15603),
		ovsdbControllerIdAlreadyExists(15604),
		ovsdbInvalidSslCertFile(15605),
		ovsdbCannotChangeConfigurationOvsdbEnabled(15606),
		ovsdbConfigurationFailedInternalError(15607),
		ovsdbSslRequiresCertificateInstallation(15608),
		ovsdbControllerInvalidConfig(15609),
		ovsdbVxlanInteworkingModeDisabled(15610),
		ovsdbManagedVxlanGwSupportedOnVxlanInterworkingMode(15611),
		ovsdbIsidAlreadyManagedByOvsdb(15612),
		ovsdbIsidNotPresentInOvsdbManagedInterface(15613),
		ovsdbIsidShouldBeSwitchedUniIsid(15614),
		ovsdbCannotChangeVtepSourceIpOvsdbEnabled(15615),
		ovsdbCannotDeleteVtepSourceIpOvsdbEnabled(15616),
		ovsdbCannotDeleteOvsdbCreatedVnid(15617),
		ovsdbCannotEnableReplicationLocalOrPeerIpNotSpecified(15618),
		ovsdbReplicationPeerIpAlreadyCondfigured(15619),
		ovsdbReplicationLocalIpAlreadyConfigured(15620),
		ovsdbCannotDeleteOvsdbConfiguredVtepIp(15621),
		ovsdbIsidShouldBeFlexUniOrCvlanIsid(15622),
		ovsdbControllerIpAlreadyExists(15623),
		ovsdbCannotModifyOvsdbConfiguredVtepIp(15624),
		ovsdbVnidNotConfiguredByOvsdb(15625),
		ovsdbVtepVnidAssociationDoneByOvsdb(15626),
		ovsdbCannotModifyCertificateOvsdbEnabled(15627),
		ovsdbCannotModifyPrivateKeyOvsdbEnabled(15628),
		ovsdbCannotDeleteCertificateOvsdbEnabled(15629),
		ovsdbCannotDeletePrivateKeyOvsdbEnabled(15630),
		ovsdbReplicationIpShouldBeNlsIp(15631),
		ovsdbCannotModifyReplicationConfigWhenOvsdbEnabled(15632),
		ovsdbShouldConfigureVistToEnableReplication(15633),
		ovsdbCannotDisableVistWhenOvsdbReplicationConfigurationPresent(15634),
		ovsdbReplicationNotConfigured(15635),
		ovsdbOnlyControllerConfigsInActiveOvsdbReplicationPeerIsAllowed(15636),
		ovsdbReplicationLocalIpAndPeerIpCannotBeSame(15637),
		ovsdbVnidVtepIpEntryAlreadyExists(15638),
		ovsdbVnidVtepIpEntryDoesNotExist(15639),
		ovsdbVnidAlreadyConfiguredStatically(15640),
		ovsdbIpAlreadyConfiguredAsLocalVtepIp(15641),
		ovsdbIpAlreadyConfiguredAsStaticRemoteVtepIp(15642),
		ovsdbVtepIpShouldBeUnicastIp(15643),
		ovsdbVtepIpAlreadyConfiguredAsNlsIp(15644),
		ovsdbVtepIpAlreadyConfiguredAsVossIp(15645),
		ovsdbVtepIpAlreadyConfiguredUnderOvsdb(15646),
		ovsdbCannotDeleteManagedInterfaceIsid(15647),
		ovsdbInvalidPrivateKeyFile(15648),
		ovsdbCannotDeleteVlanAssociatedWithManagedInterfaceIsid(15649),
		ovsdbCannotDeleteIsidConfiguredAsManagedInterface(15650),
		ovsdbVtepIdUsedForRemoteVtepCreatedViaOvsdb(15651),
		ovsdbCannotEnableOvsdbOnSimplifiedVistSetup(15652),
		ovsdbCannotChangePortInExistingControllerConfig(15653),
		ovsdbReplicationLocalIpAddressCannotBeZero(15654),
		ovsdbReplicationPeerIpAddressCannotBeZero(15655),
		ovsdbCertificateFileAlreadyExists(15656),
		ovsdbPrivateKeyAlreadyExists(15657),
		ovsdbNotSupportedOnThisPlatform(15658),
		restConfCertFileNotSpecified(15701),
		restconfCannotOpenCertFile(15702),
		restConfInvalidCertFile(15703),
		restConfCannotChangeConfigurationRestConfEnabled(15704),
		restConfTlsRequiresCertificateInstallation(15705),
		restConfConfigurationFailedInternalError(15706),
		restconfCannotBeEnabledDueToConflictOfMltAndVlanName(15707),
		restconfCannotBeEnabledDueToConflictOfMltAndPortIfName(15708),
		restconfCannotBeEnabledDueToConflictOfVlanAndPortIfName(15709),
		restconfCannotBeEnabledDueToConflictOfVlanAndMltName(15710),
		restconfIpNotSupported(15711),
		certificateFileCannotBeUninstalledWhileTlsIsEnabled(15712),
		certificateFileCannotBeInstalledWhileTlsIsEnabled(15713),
		certificateFileOnlyCanBeInstalledWithTheInstallAction(15714),
		restconfHasBeenDisabledAlready(15715),
		restconfHasBeenEnabledAlready(15716),
		restconfCannotBeEnabledWithInvalidVlanName(15717),
		restconfCannotBeEnabledWithInvalidMltName(15718),
		ipv6OspfAreaAggregateNssaExtLinkInNonNssaArea(15902),
		ipv6VlanInterfaceMaxAddressNumberReached(15903),
		ipv6CannotCreateIntfIfMgmtVlanExist(15904),
		virtualServicePackageNotExist(16001),
		virtualServicePackageInstallFailed(16002),
		virtualServicePackageUninstallFailed(16003),
		virtualServiceNotSupportedOnThisPlatform(16004),
		virtualServiceNotExist(16005),
		virtualServiceAtLeastOneVportConfig(16006),
		virtualServiceInvalidNameFormat(16007),
		virtualServiceExceedMaximumAllowedDisks(16008),
		virtualServiceMoreThanOneVtdPortConfig(16009),
		virtualServiceExceedNumCoresLimit(16010),
		virtualServiceDiskSizeNotSpecified(16011),
		virtualServiceExceedMemotySizeLimit(16012),
		virtualServiceNotAllowConfigChange(16013),
		virtualServiceNeedVlanConfig(16014),
		virtualServiceNoVlanVtd(16015),
		virtualServiceVlanAlreadyInUse(16016),
		virtualServiceNotInstalled(16017),
		virtualServiceInstallInProgress(16018),
		virtualServiceExists(16019),
		virtualServiceNoSuchDisk(16020),
		virtualServiceDiskExists(16021),
		virtualServiceVportNotExist(16022),
		virtualServiceAlreadyInstalled(16023),
		virtualServiceExceedMaxDiskSize(16024),
		virtualServiceExceedMaxNumCores(16025),
		virtualServiceExceedMaxMemSize(16026),
		virtualServiceInvalidVlan(16027),
		virtualServiceIncorrectPackagePath(16028),
		virtualServicePackageNotFile(16029),
		virtualServiceExceedMaxSriovPorts(16030),
		virtualServiceAlreadyEnabled(16031),
		virtualServiceExceedMaxPortsPerVm(16032),
		virtualServicePackageNotSpecified(16033),
		virtualServiceCannotEnable(16034),
		virtualServiceIsEnabled(16035),
		virtualServiceSpbmBvlanNotAllow(16036),
		virtualServiceExceedMaxNumService(16037),
		virtualServiceExceedMaxNameLen(16038),
		virtualServiceVportConnectTypeNotSupported(16039),
		virtualServiceInsufficientDiskSpace(16040),
		virtualServiceExceedMaxVportNameLen(16041),
		virtualServiceExceedMaxDiskNameLen(16042),
		virtualServiceInvalidInsightNameFormat(16043),
		virtualServiceActiveServicesExist(16044),
		virtualServiceSetInsightPortTypeFailed(16045),
		virtualServiceExceedMaxInsightNameLen(16046),
		virtualServiceNoSupportInsightTypeConfig(16047),
		virtualServiceInsightPortTypeMismatch(16048),
		virtualServiceRebootRequired(16049),
		virtualServiceVportMustConfigInsightPort(16050),
		virtualServiceVportNicTypeOvsOnly(16051),
		logicalIsisIntfConfigAuthKeyBeforeEnableIpSec(16100),
		logicalIsisIntfSetTunnelMtuGrtThan1300BeforeEnableIpSec(16101),
		logicalIsisIntfDisableIpSecBeforeSetTunnelMtuLessThan1300(16102),
		logicalIsisIntfDisableIpSecBeforeSetAuthKey(16103),
		isisDisableNotSupportedForRcIsisCircuitPlsbState(16104),
		logicalIsisIntfDisableIpSecBeforeSetIpsecRespoderOnly(16105),
		logicalIsisIntfDisableIpSecBeforeSetIpsecRemoteNatIp(16106),
		logicalIsisIntfCannotConfigureIpsecResponderOnlyIfRemoteNatIpIsConfigured(16107),
		logicalIsisIntfCannotConfigureIpsecRemoteNatIpIfResponderOnlyIsConfigured(16108),
		logicalIsisIntfSetTunnelMtu1500BeforeEnableIpSec(16109),
		logicalIsisIntfSetTunnelMtuGrtThan1300ForIpSecTunnel(16110),
		logicalIsisIntfIpsecRemoteNatIpCannotBeSameAsTunnelDestIp(16111),
		isisCannotChangeTunnelSrcIpWithIsisEnabled(16112),
		logicalIsisIntfTunnelMtuCannotBeGreaterThanSystemMtu(16113),
		systemMtuCannotBeLessThanTunnelMtu(16114),
		logicalIsisIntfRemoteNatIpCannotBeLocal(16115),
		logicalIsisIntfExistsWithSameRemoteNatIp(16116),
		systemMtu9600IsNotSupported(16117),
		logicalIsisIntfDisableIpSecBeforeSetIpsecEncrKeyLen(16118),
		logicalIsisIntfDisableIpSecBeforeSetIpsecTunnelDestIp(16119),
		logicalIsisIntfCannotConfigureIpsecTunnelDestIpIfResponderOnlyIsConfigured(16120),
		logicalIsisIntfCannotConfigureIpsecTunnelDestIpIfRemoteNatIpIsConfigured(16121),
		logicalIsisIntfIpsecTunnelDestIpCannotBeSameAsTunnelDestIp(16122),
		logicalIsisIntfIpsecTunnelDestIpCannotBeLocal(16123),
		logicalIsisIntfCannotConfigureIpsecResponderOnlyIfIpsecTunnelDestIpIsConfigured(16124),
		logicalIsisIntfCannotConfigureIpsecRemoteNatIpIfIpsecTunnelDestIpIsConfigured(16125),
		isisIsidCannotBeAssignedToIpsecTunnelVlan(16126),
		isisCannotChangeIpsecTunnelSrcIpWithIsisEnabled(16127),
		isisIpsecTunnelSrcIpCannotBeSameAsIpTunnelSrcIp(16128),
		isisIpsecTunnelSrcIpCannotBeSameAsMgmtIP(16129),
		isisIpsecTunnelSrcIpDoesNotExistInVrf(16130),
		isisIpsecTunnelSrcIpDoesNotExistInGrt(16131),
		logicalIsisIntfExistsWithSameIpsecDestIp(16132),
		mustSetElanTypeWhenCreateIsid(16300),
		cannotCreateFlexUniIsid(16306),
		cannotDisableFlexUniIfEptEnabled(16301),
		cannotEnableEptIfFlexUniDisabled(16302),
		eptInterfaceDoesNotExist(16303),
		eptGlobalIsEnabled(16304),
		eptIsisNotEnabled(16305),
		cannotDisableFlexUniIfEptCreated(16307),
		cannotEnableEptIfFaEnabled(16308),
		cannotEnableFaIfEptCreated(16309),
		lemCannotChangeConfigurationLemEnabled(16405),
		lemCertFileNotSpecified(16406),
		lemInvalidCertFile(16407),
		lemCertFileInstalledWithInstallActionOnly(16408),
		lemPrivateKeyFileNotSpecified(16409),
		lemInvalidPrivateKeyFile(16410),
		lemEntitlementExceedMaxNameLen(16411),
		lemExceedMaxNumEntitlements(16412),
		lemEntitlementDoesNotExist(16413),
		lemExceedEntitlementMaxCount(16414),
		lemNotSupported(16415),
		lemIsNotEnabled(16416),
		lemInvalidEntitlementsForChassisType(16417),
		lemCustomerIdNotSpecified(16418),
		lemFeatureNotSupported(16419),
		lemEnabledCannotChangeCert(16420),
		lemEntitlementRtuNumberNotSpecified(16421),
		vridInUse(16500),
		cannotCreateStaticRouteNextHopOnDvrVlan(16501),
		cannotEnableDvrWhenStaticRouteNextHopsVlanSubnet(16502),
		cannotCreateIPv4BgpPeersOnDvrVlan(16503),
		cannotEnableDvrWhenIPv4BgpPeersVlanSubnet(16504),
		cannotConfigIPAddressOnDvrVlanBgpPeersThisSubnet(16505),
		cannotConfigIPAddressOnDvrVlanStaticRouteNextHopsThisSubnet(16506),
		cannotDisableDvrVistWithIsisEnabled(16507),
		removeSmltConfigBeforeDisablingDvrLeafVist(16508),
		cldAgentNotSupportedOnPlatform(16601),
		cldAgentChangeNotAllowedWhenEnabled(16602),
		cldAgentInvalidServerAddress(16603),
		cldAgentInvalidProxyAddress(16604),
		cldAgentInstallationInProgress(16605),
		bfdAlreadyConfiguredOnOtherProtocol(16701),
		bfdAlreadyConfiguredOnLogicalInterface(16702)
	}
	MAX-ACCESS read-only
	STATUS current
	DESCRIPTION "This variable is used primarily as an enumeration
		      to list the proprietary return codes that this
		      device can send to a management station in
		      response to a failed SNMP operation."
	DEFVAL { none }
	::= { rcError 4 }

-- *** ABOVE SECTION IS GENERATED FROM ../mib_tools/error.mib ***

rcErrorSendTrap OBJECT-TYPE
        SYNTAX        TruthValue
        MAX-ACCESS    read-write
        STATUS        current
        DESCRIPTION   "Indicates whether to send trap upon receiving an
                      error in the system."
	DEFVAL	      { true }
        ::= { rcError 5 }

END
