BAY-STACK-PETH-EXT-MIB DEFINITIONS ::= BEGIN

IMPORTS
    OBJECT-TYPE, MODULE-IDENTITY, NOTIFICATION-TYPE, Integer32, Gauge32
        FROM SNMPv2-SMI
    TruthValue
        FROM SNMPv2-TC
    ifIndex
        FROM IF-MIB
    bayStackMibs
        FROM SYNOPTICS-ROOT-MIB;

bayStackPethExtMib MODULE-IDENTITY
    LAST-UPDATED    "202003170000Z"
    ORGANIZATION    "Avaya"
    CONTACT-INFO    "Avaya"
    DESCRIPTION
        "BayStack Power Over Ethernet Extension MIB

         Copyright 2004-2011 Avaya
         All rights reserved.
         This Avaya SNMP Management Information Base
         Specification embodies Avaya's confidential and
         proprietary intellectual property. Avaya retains
         all title and ownership in the Specification, including any
         revisions.

         This Specification is supplied 'AS IS,' and Avaya
         makes no warranty, either express or implied, as to the use,
         operation, condition, or performance of the Specification."

    REVISION "202003170000Z" -- 17 March 2020
    DESCRIPTION "v12: Requested for supporting PoE 802.3bt for VOSS X3
                      product (Huiying Liang).
                      Added new object:

                      bspePethPsePortPowerClassifications (bspePethPsePortExtEntry 15)

                      Changed the range of:

                      bspePethPsePortExtPowerLimit (3..64) -> (3..98)
                      bspePethPsePortExtMeasuredCurrent (0..1200) -> (0..1920)
                      bspePethPsePortExtMeasuredPower (0..64000) -> (0..98000).
                      (azmeu)"

    REVISION "201911210000Z" -- 20 November 2019
    DESCRIPTION "v11: Requested for Seadart Phase 2 (Alina Radu)
                 Import TruthValue
                 Added bspePethPsePortFastPoeEnable (BspePethPsePortExtEntry 13)
                 Added bspePethPsePortPerpetualPoeEnable (BspePethPsePortExtEntry 14)
                 Added bspePethMainPseFastPoeEnable (bspePethMainPseExtEntry 4)
                 Added bspePethMainPsePerpetualPoeEnable (bspePethMainPseExtEntry 4)
                 Change range bspePethPsePortExtPowerLimit from 60 to 64
		 Change range bspePethPsePortExtMeasuredPower from 60000 to 64000.
		 (azmeu)"

    REVISION "201603030000Z" -- 3 March 2016
    DESCRIPTION "v10:  Added bspePethPsePortExtLldp (BspePethPsePortExtEntry 12)"

    REVISION "201512090000Z" -- 9 December 2015
    DESCRIPTION "v9:  Added bspePethPsePortExtPowerPairs (BspePethPsePortExtEntry 11)
                 Please note that if this object is supported, pethPsePortPowerPairs
                 is no longer available."

    REVISION "201511170000Z" -- 17 November 2015
    DESCRIPTION "v8:  Changed range of bspePethPsePortExtPowerLimit from 32 to 60,
                      range of bspePethPsePortExtMeasuredPower from 32000 to 60000 and
                      range of bspePethPsePortExtMeasuredCurrent from 660 to 1200."

    REVISION "201507060000Z" -- 06 July 2015
    DESCRIPTION "v7:  Added bspePethPsePortExtPowerUpMode (bspePethPsePortExtEntry 10)."

    REVISION "201201250000Z" -- 25 January 2012
    DESCRIPTION "v6:  Added bspePoEPowerMode (bspeScalars 3)."

    REVISION "201107200000Z" -- 20 July 2011
    DESCRIPTION "v5:  Changed range of some objects: bspePethPsePortExtPowerLimit,
                 bspePethPsePortExtMeasuredCurrent, bspePethPsePortExtMeasuredPower,
                 bspeIpPhonePowerLimit."

    REVISION "201101100000Z" -- 10 January 2011
    DESCRIPTION "v4:  Expanded range of some objects."

    REVISION "200411110000Z" -- 11 November 2004
    DESCRIPTION "v3:  Fixed typo, bspePethMainPseExtPowerPresent
                      should be read-only."

    REVISION "200410180000Z" -- 13 October 2004
    DESCRIPTION "v2:  Removed bspePethPsePortExtForcePower.  Added
                 bspePethPsePortExtCurrentStatus/CurrentStatusClear.
                 Added bspePethPsePortCurrentStatusNotification."

    REVISION "200409140000Z" -- 14 September 2004
    DESCRIPTION "v1:  Initial version."

    ::= { bayStackMibs 8 }

bspeNotifications OBJECT IDENTIFIER ::= { bayStackPethExtMib 0 }
bspeObjects       OBJECT IDENTIFIER ::= { bayStackPethExtMib 1 }

--
-- 802.3af PSE Port Extension Table
--

bspePethPsePortExtTable OBJECT-TYPE
    SYNTAX SEQUENCE OF BspePethPsePortExtEntry
    MAX-ACCESS not-accessible
    STATUS current
    DESCRIPTION
        "This table extends the pethPsePortTable."
    ::= { bspeObjects 1 }

bspePethPsePortExtEntry OBJECT-TYPE
    SYNTAX BspePethPsePortExtEntry
    MAX-ACCESS not-accessible
    STATUS current
    DESCRIPTION
        "An entry that extends pethPsePortEntry."
    INDEX { bspePethPsePortExtGroupIndex, bspePethPsePortExtIndex }
    ::= { bspePethPsePortExtTable 1 }

BspePethPsePortExtEntry ::=
    SEQUENCE {
        bspePethPsePortExtGroupIndex           Integer32,
        bspePethPsePortExtIndex                Integer32,
        bspePethPsePortExtPowerLimit           Integer32,
        bspePethPsePortExtDetailedStatus       INTEGER,
        bspePethPsePortExtMeasuredVoltage      Gauge32,
        bspePethPsePortExtMeasuredCurrent      Gauge32,
        bspePethPsePortExtMeasuredPower        Gauge32,
        bspePethPsePortExtCurrentStatus        INTEGER,
        bspePethPsePortExtCurrentStatusClear   INTEGER,
        bspePethPsePortExtPowerUpMode          INTEGER,
        bspePethPsePortExtPowerPairs           INTEGER,
        bspePethPsePortExtLldp                 INTEGER,
        bspePethPsePortFastPoeEnable           TruthValue,
        bspePethPsePortPerpetualPoeEnable      TruthValue,
        bspePethPsePortPowerClassifications    INTEGER
    }

bspePethPsePortExtGroupIndex OBJECT-TYPE
    SYNTAX      Integer32 (1..2147483647)
    MAX-ACCESS  not-accessible
    STATUS      current
    DESCRIPTION
        "This object is equal to the value of pethPsePortGroupIndex
         of the entry in the pethPsePortTable extended by this entry."
    ::= { bspePethPsePortExtEntry 1 }

bspePethPsePortExtIndex OBJECT-TYPE
    SYNTAX      Integer32 (1..2147483647)
    MAX-ACCESS  not-accessible
    STATUS      current
    DESCRIPTION
        "This object is equal to the value of pethPsePortIndex of the
         entry in the pethPsePortTable extended by this entry."
    ::= { bspePethPsePortExtEntry 2 }

bspePethPsePortExtPowerLimit OBJECT-TYPE
    SYNTAX      Integer32 (3..98)
    UNITS       "watts"
    MAX-ACCESS  read-write
    STATUS      current
    DESCRIPTION
        "DTE Power limit per port."
    ::= { bspePethPsePortExtEntry 3 }

bspePethPsePortExtDetailedStatus OBJECT-TYPE
    SYNTAX      INTEGER  {
                  poweredResistiveDiscovery(1),
                  poweredCapacitiveDiscovery(2),
                  poweredCiscoLegacyDiscovery(3),
                  invalidPD(4),
                  overloadFault(5),
                  underloadFault(6),
                  uvovFault(7),
                  powerManaged(8),
                  limitOverloadFault(9),
                  discoveryDisabled(10),
                  unableToResetTps(11),
                  unableToInitializeTps(12),
                  uninitialized(13),
                  nonexistent(14),
                  otherFault(15),
                  detectionStatus(16)
                }
    MAX-ACCESS  read-only
    STATUS      current
    DESCRIPTION
        "Port Status.
         Valid values for Harrier: 4,8,9,16.
         Valid values for CondorPoE: 1-16.

         The object bspePsePortExtDetailedStatus details the status
         of the port when pethPsePortDetectionStatus is either
         deliveringPower(3), fault(4), or otherFault(6).
         - When the value of pethPsePortDetectionStatus is
         deliveringPower(3), the value of
         bspePethPsePortExtDetailedStatus should be a value in the
         range 1-3 (detailes the discovery scheme that was used to
         detect the PD that is currently powered).
         - When the value of pethPsePortDetectionStatus is fault(4) or
         otherFault(6), the value of bspePethPsePortExtDetailedStatus
         should be some fault value in the range: 4-15.
         - When the value of pethPsePortDetectionStatus is *not*
         deliveringPower(3), fault(4), nor otherFault(6), then the
         value of bspePethPsePortExtDetailedStatus should be
         detectionStatus(16).

         A value of poweredResistiveDiscovery(1) indicates that a PD
         device was detected on this port using the IEEE 802.3af
         standard compliant Resistor signature discovery scheme.
         A value of poweredCapacitiveDiscovery(2) indicates that a PD
         device was detected on this port using the Capacitive
         detection scheme.
         A value of poweredCiscoLegacyDiscovery(3) indicates that a PD
         device was detected on this port using the CiscoIP detection
         scheme.
         A value of invalidPd(4) indicates that a non-PoE device has
         been detected; no power will be supplied.
         A value of overloadFault(5) indicates that the port has
         exceeded its port power limit.
         A value of underloadFault(6) indicates that the connected PD
         device needs less power than the port lower power limit.
         A value of uvovFault(7) indicates that an under-voltage /
         over-voltage fault has occured.
         A value of powerManaged(8) indicates that the port is
         discovered and ready to power up, except that the power
         manager has not decided to power it up yet. This could be
         because of a power up delay, or it could be because there is
         no power available. Port does not supply power in order to
         keep active higher priority ports.
         A value of limitOverloadFault(9) indicates that the
         connected PD device needs more power than the port power
         limit; no power will be supplied.
         A value of discoveryDisabled(10) indicates that the port is
         enabled, but no discovery method has been enabled.
         A value of unableToResetTps(11) indicates that the TPS2384
         (PoE Subsystem) could not be reset.
         A value of unableToInitializeTps(12) indicates that the
         TPS2384 (PoE Subsystem) could not be initialized.
         A value of unitialized(13) indicates that port PoE settings
         have not beed initialized.
         A value of nonexistent(14) indicates the port doesn't exist.
         This is used for the last 24 ports on 24 port systems.
         A value of otherFault(15) indicates that other fault has
         occured.
         A value of detectionStatus(16) indicates that the value of
         pethPsePortDetectionStatus should be disabled(1),
         searching(2), or test(5)."
    ::= { bspePethPsePortExtEntry 4 }

bspePethPsePortExtMeasuredVoltage OBJECT-TYPE
    SYNTAX      Gauge32 (0|400..580)
    UNITS       "decivolts"
    MAX-ACCESS  read-only
    STATUS      current
    DESCRIPTION
        "Measured Port Voltage.  When the port is not supplying
         power, the value will be 0."
    ::= { bspePethPsePortExtEntry 5 }

bspePethPsePortExtMeasuredCurrent OBJECT-TYPE
    SYNTAX      Gauge32 (0..1920)
    UNITS       "milliamps"
    MAX-ACCESS  read-only
    STATUS      current
    DESCRIPTION
        "Measured Port Current."
    ::= { bspePethPsePortExtEntry 6 }

bspePethPsePortExtMeasuredPower OBJECT-TYPE
    SYNTAX      Gauge32 (0..98000)
    UNITS       "milliwatts"
    MAX-ACCESS  read-only
    STATUS      current
    DESCRIPTION
        "Measured Port Power. This value may not exceed 1000 times the
         current value of bspePethPsePortExtPowerLimit."
    ::= { bspePethPsePortExtEntry 7 }

bspePethPsePortExtCurrentStatus OBJECT-TYPE
    SYNTAX      INTEGER {
                  ok(1),
                  underCurrent(2),
                  overCurrent(3),
                  both(4)
                }
    MAX-ACCESS  read-only
    STATUS      current
    DESCRIPTION
        "Describes a current port status related to the power generation.
         The value ok(1) indicates neither an undercurrent nor an overcurrent
         condition was detected since the attribute was last cleared.
         The value underCurrent(2) indicates that the port current
         is below the minimal value.
         The value overCurrent(3) indicates that the port current
         exceeds the maximal value.
         The value both(4) indicates both underCurrent and overCurrent.
         This attribute is cleared through the
         bspePethPsePortExtCurrentStatusClear action."
    ::= { bspePethPsePortExtEntry 8 }

bspePethPsePortExtCurrentStatusClear OBJECT-TYPE
    SYNTAX      INTEGER {
                  clear(1),
                  off(2)
                }
    MAX-ACCESS  read-write
    STATUS      current
    DESCRIPTION
        "Setting the value of this object to clear(1) clears the value
         of bspePethPsePortExtCurrentStatus, and enables the agent to
         update it.
         Read operation this value will be off(2)."
    ::= { bspePethPsePortExtEntry 9 }

bspePethPsePortExtPowerUpMode OBJECT-TYPE
    SYNTAX      INTEGER {
                  dot3af(1),
                  highInrush(2),
                  pre802dot3at(3),
                  dot3at(4)
                }
    MAX-ACCESS  read-write
    STATUS      current
    DESCRIPTION
        "Describes the power up mode for the current port.
         The value dot3af(1) indicates an inrush current of 400mA-450mA.
         The value highInrush(2) indicates an inrush current as described
         by the Icut/Ilim (default is 700mA - 1.0A).
         The value pre802dot3at(3) indicates an inrush current
         of 400mA-450mA, which is switched to higher Ilim (700mA-1.0A)
         within 75 miliseconds, after the port is powered up.
         The value dot3at(4) indicates an inrush current as described
         by the Icut/Ilim (default is 700mA - 1.0A)."
    ::= { bspePethPsePortExtEntry 10 }

bspePethPsePortExtPowerPairs OBJECT-TYPE
    SYNTAX INTEGER   {
               signal(1),
               spare(2),
               both(3)
     }
    MAX-ACCESS read-write
    STATUS current
    DESCRIPTION
        "Describes or controls the pairs in use.  If the value of
         pethPsePortPowerPairsControl is true, this object is
         writable.
         A value of signal(1) means that the signal pairs
         only are in use.
         A value of spare(2) means that the spare pairs
         only are in use.
         A value of both(3) means that both signal and spare
         pairs are in use.
         Please note that if this object is supported,
         pethPsePortPowerPairs is no longer available."
    ::= { bspePethPsePortExtEntry 11 }

bspePethPsePortExtLldp OBJECT-TYPE
    SYNTAX INTEGER   {
               enable(1),
               disable(2)
     }
    MAX-ACCESS read-write
    STATUS current
    DESCRIPTION
        "Describes the LLDP negotation status for the current port.
         The value enable(1) indicates that LLDP negotation is enabled.
         The value disable(2) indicates that LLDP negotation is disabled."
    ::= { bspePethPsePortExtEntry 12 }

bspePethPsePortFastPoeEnable OBJECT-TYPE
    SYNTAX TruthValue
    MAX-ACCESS read-write
    STATUS current
    DESCRIPTION
        "true (1) An interface which can provide the Fast POE function.
         false(2) The interface will act as it would if it had no  Fast POE function."
    ::= { bspePethPsePortExtEntry 13 }

bspePethPsePortPerpetualPoeEnable OBJECT-TYPE
    SYNTAX TruthValue
    MAX-ACCESS read-write
    STATUS current
    DESCRIPTION
        "true (1) An interface which can provide the Perpetual POE function.
         false(2) The interface will act as it would if it had no Perpetual POE function."
    ::= { bspePethPsePortExtEntry 14 }

bspePethPsePortPowerClassifications OBJECT-TYPE
    SYNTAX INTEGER {
              class0(1),
              class1(2),
              class2(3),
              class3(4),
              class4(5),
              class5(6),
              class6(7),
              class7(8),
              class8(9)
    }
    MAX-ACCESS read-only
    STATUS current
    DESCRIPTION
        "Classification is a way to tag different terminals on the
        Power over LAN network according to their power consumption.
        Devices such as IP telephones, WLAN access points and others,
        will be classified according to their power requirements.

        The meaning of the classification labels is defined in the
        IEEE specification.

        This variable is valid only while a PD is being powered,
        that is, while the attribute pethPsePortDetectionStatus
        is reporting the enumeration deliveringPower."
   ::= { bspePethPsePortExtEntry 15 }


--
-- 802.3af Main PSE Extension Table
--

bspePethMainPseExtTable OBJECT-TYPE
    SYNTAX      SEQUENCE OF BspePethMainPseExtEntry
    MAX-ACCESS  not-accessible
    STATUS      current
    DESCRIPTION
        "This table extends the pethMainPseTable."
    ::= { bspeObjects 2 }

bspePethMainPseExtEntry OBJECT-TYPE
    SYNTAX      BspePethMainPseExtEntry
    MAX-ACCESS  not-accessible
    STATUS      current
    DESCRIPTION
        "An entry that extends pethMainPseEntry. "
    INDEX    { bspePethMainPseExtGroupIndex }
    ::= { bspePethMainPseExtTable 1 }

BspePethMainPseExtEntry ::=
   SEQUENCE {
        bspePethMainPseExtGroupIndex           Integer32,
        bspePethMainPseExtPowerPresent         INTEGER,
        bspePethMainPseExtDisconnectScheme     INTEGER,
	bspePethMainPseFastPoeEnable           TruthValue,
        bspePethMainPsePerpetualPoeEnable      TruthValue
    }

bspePethMainPseExtGroupIndex OBJECT-TYPE
    SYNTAX      Integer32 (1..2147483647)
    MAX-ACCESS  not-accessible
    STATUS      current
    DESCRIPTION
        "This object is equal to the value of pethMainPseGroupIndex
         of the entry in the pethMainPseTable extended by this entry."
    ::= { bspePethMainPseExtEntry 1 }

bspePethMainPseExtPowerPresent OBJECT-TYPE
    SYNTAX      INTEGER   {
                  acOnly(1),
                  dcOnly(2),
                  acDc(3)
                }
    MAX-ACCESS  read-only
    STATUS      current
    DESCRIPTION
        "Current Power Source Present. Available power sources are AC
         and DC.
         A value of acOnly(1) indicates that the only power supply is AC.
         A value of dcOnly(2) indicates that the only power supply is DC.
         A value of acDc(3) indicates that there are two power supplies;
         both AC and DC are supplying power."
    ::= { bspePethMainPseExtEntry 2 }

bspePethMainPseExtDisconnectScheme OBJECT-TYPE
    SYNTAX      INTEGER   {
                  acDisconnect(1),
                  dcDisconnect(2)
                }
    MAX-ACCESS  read-write
    STATUS      current
    DESCRIPTION
        "When a low power draw is detected on a port, power will be
         turned off on that port. As a detection mechanism it can be
         used either AC Disconnect or DC Disconnect.
         A value of acDisconnect(1): AC impedance is monitored on each
         port; DC supply will be turned off on a port with a too high
         value of AC impedance.
         A value of dcDisconnect(2): DC current is monitored on each
         port; DC supply will be turned off on a port with a too low
         value of DC current."
    ::= { bspePethMainPseExtEntry 3 }

bspePethMainPseFastPoeEnable OBJECT-TYPE
     SYNTAX      TruthValue
     MAX-ACCESS  read-write
     STATUS      current
     DESCRIPTION "Enable or disable Fast POE feature."
     ::= { bspePethMainPseExtEntry 4 }

bspePethMainPsePerpetualPoeEnable OBJECT-TYPE
     SYNTAX     TruthValue
     MAX-ACCESS  read-write
     STATUS      current
     DESCRIPTION "Enable or disable Perpetual POE feature."
     ::= { bspePethMainPseExtEntry 5 }

--
-- Scalars
--

bspeScalars       OBJECT IDENTIFIER ::= { bspeObjects 3 }

bspeIpPhonePowerLimit OBJECT-TYPE
    SYNTAX      Integer32 (0|3..32)
    UNITS       "watts"
    MAX-ACCESS  read-write
    STATUS      current
    DESCRIPTION
        "Global power limit for IP phones. This value, if valid, applies for
        an IP phone discovered on a port. A value of 0 means not applicable;
        bspePethPsePortExtPowerLimit object should be used instead."
    ::= { bspeScalars 1 }

bspeIpPhonePowerPriority OBJECT-TYPE
    SYNTAX INTEGER   {
               critical(1),
               high(2),
               low(3),
               notApplicable(4)
     }
    MAX-ACCESS read-write
    STATUS current
    DESCRIPTION
        "Global power priority for IP phones. This object controls the
        priority of a port that connects an IP phone device. If the value
        is notApplicable(4), pethPsePortPowerPriority object should be used
        instead."
    ::= { bspeScalars 2 }

bspePoEPowerMode OBJECT-TYPE
    SYNTAX INTEGER   {
               lowPowerBudget(1),
               highPowerBudget(2)
     }
    MAX-ACCESS  read-write
    STATUS      current
    DESCRIPTION
        "Power over Ethernet Power Mode comfiguration:
         lowPowerBudget (1) Set PoE Low power budget and fanless mode.
         highPowerBudget (2) Set PoE High power budget and normal fans Mode."
    ::= { bspeScalars 3 }

--
-- 802.3af Notifications Section
--

bspePethPsePortCurrentStatusNotification NOTIFICATION-TYPE
    OBJECTS {
                 bspePethPsePortExtCurrentStatus
            }
    STATUS      current
    DESCRIPTION
        "This notification indicate Port Change Status and
         it will be sent on every status change."
    ::= { bspeNotifications 1 }

bspeIpPhonePowerLimitNotification NOTIFICATION-TYPE
    OBJECTS {
                 ifIndex,
                 bspeIpPhonePowerLimit
            }
    STATUS      current
    DESCRIPTION
        "This notification indicates the dynamic change of the power limit for
        a port, due to the discovering of an IP phone. This notification type
        is generating only if bspeIpPhonePowerLimit object is applicable."
    ::= { bspeNotifications 2 }

bspeIpPhonePowerPriorityNotification NOTIFICATION-TYPE
    OBJECTS {
                 ifIndex,
                 bspeIpPhonePowerPriority
            }
    STATUS      current
    DESCRIPTION
        "This notification indicates the dynamic change of the power priority
        for a port, due to the discovering of an IP phone. This notification
        type is generating only if bspeIpPhonePowerPriority object is
        applicable."
    ::= { bspeNotifications 3 }

END
