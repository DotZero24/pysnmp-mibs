-- SECTION 1: Top Level Definitions


CENTILLION-VLAN-MIB DEFINITIONS ::= BEGIN


-- Centillion VLAN MIB Release 0.0.0
-- Revision 2/24/98

-- Copyright 1998 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	OBJECT-TYPE
	    FROM RFC-1212
    RowStatus, TruthValue
        FROM SNMPv2-TC
    InterfaceIndex
        FROM IF-MIB
    vlan, VlanId
        FROM CENTILLION-MCAST-MIB;


-- Groups

cnVlanMemberGroup   OBJECT IDENTIFIER ::= { vlan 2 }

-- SECTION 2: VLAN Port Membership Configuration Table
--
-- This table defines the VLAN membership and configuration for each port.
-- It is used as a substitute for the cnVlanPortTable to provide
-- configuration support for agents that handle token ring ports
-- in source routing VLANs and/or define a port's ingress
-- classification method by VLAN.
--

cnVlanPortMemberTable OBJECT-TYPE
        SYNTAX        SEQUENCE OF CnVlanPortMemberEntry
        ACCESS        not-accessible
        STATUS        mandatory
        DESCRIPTION   "The VLAN port membership configuration table. This
                      table contains membership information pertaining to the
                      ports belonging to a VLAN."
        ::= { cnVlanMemberGroup 1 }

cnVlanPortMemberEntry OBJECT-TYPE
        SYNTAX        CnVlanPortMemberEntry
        ACCESS        not-accessible
        STATUS        mandatory
        DESCRIPTION   "An entry containing VLAN membership information
                      for a particular port.  Entries are added by
                      specifying the cnVlanPortMemberCard,
                      cnVlanPortMemberPort, cnVlanPortMemberVID,
					  and the cnVlanPortMemberIngressType.
                      Entries are deleted simply by setting the
                      cnVlanPortMemberStatus object to destroy."
        INDEX         { cnVlanPortMemberCard,
                        cnVlanPortMemberPort,
                        cnVlanPortMemberVID }
        ::= { cnVlanPortMemberTable 1 }

CnVlanPortMemberEntry ::= SEQUENCE {
	cnVlanPortMemberCard
		INTEGER,
	cnVlanPortMemberPort
		INTEGER,
	cnVlanPortMemberVID
		VlanId,
	cnVlanPortMemberStatus
		RowStatus,
	cnVlanPortMemberIngressType
		INTEGER,
	cnVlanPortMemberDynamic
		TruthValue,
	cnVlanPortMemberIfIndex
		InterfaceIndex,
	cnVlanPortMemberRing
		INTEGER
	}

cnVlanPortMemberCard OBJECT-TYPE
	SYNTAX	INTEGER
	ACCESS	read-only
	STATUS	mandatory
	DESCRIPTION
            "The card number for this port in the VLAN."
	::= { cnVlanPortMemberEntry 1 }

cnVlanPortMemberPort OBJECT-TYPE
	SYNTAX	INTEGER
	ACCESS	read-only
	STATUS	mandatory
	DESCRIPTION
            "The port number for this port in the VLAN."
	::= { cnVlanPortMemberEntry 2 }

cnVlanPortMemberVID OBJECT-TYPE
	SYNTAX	VlanId
	ACCESS	read-only
	STATUS	mandatory
	DESCRIPTION
            "The VLAN ID of which this port is a member."
	::= { cnVlanPortMemberEntry 3 }

cnVlanPortMemberStatus OBJECT-TYPE
	SYNTAX	RowStatus
	ACCESS	read-write
	STATUS	mandatory
	DESCRIPTION
            "The current status of the entry. Entries may be added by
            specifying a value of createAndGo, and removed by setting
            the status to destroy."
	::= { cnVlanPortMemberEntry 4 }

cnVlanPortMemberIngressType OBJECT-TYPE
	SYNTAX	INTEGER {
	        pvid(1),         -- classify by configured PVID
	        tag(2),          -- classify by 802.1Q tag (VID)
	        protocolId(3)    -- classify by ingress protocol type
	        }
	ACCESS	read-write
	STATUS	mandatory
	DESCRIPTION
            "The method used to classify ingress frames on this
            port into this VLAN.  The allowed values are specific to
            the cnVlanType of the VLAN as follows:
                byPort:         pvid or tag
                byProtocolId:   pvid, tag, or protocolId
            Allowable values may also be restricted by the
            VLAN capabilities of this port."
	::= { cnVlanPortMemberEntry 5 }

cnVlanPortMemberDynamic OBJECT-TYPE
	SYNTAX	TruthValue
	ACCESS	read-only
	STATUS	mandatory
	DESCRIPTION
            "The value for this object indicates whether the
            switch learned this port's VLAN membership dynamically."
	::= { cnVlanPortMemberEntry 6 }

cnVlanPortMemberIfIndex OBJECT-TYPE
	SYNTAX	InterfaceIndex
	ACCESS	read-only
	STATUS	mandatory
	DESCRIPTION
            "The value for this object identifies the instance of
            the ifIndex object, defined in MIB-II, for the interface
            corresponding to this port and VLAN. If no such entry
            exists, the value 0 may be returned."
	::= { cnVlanPortMemberEntry 7 }


cnVlanPortMemberRing OBJECT-TYPE
	SYNTAX	INTEGER
	ACCESS	read-write
	STATUS	mandatory
	DESCRIPTION
            "The ring number for this port if this VLAN uses source
            route or source route transparent bridging."
	::= { cnVlanPortMemberEntry 8 }



-- SECTION 3: Default Management Vlan Configuration
--

cnVlanENETMgt OBJECT-TYPE
        SYNTAX        VlanId
        ACCESS        read-write
        STATUS        mandatory
        DESCRIPTION   "VID of the Ethernet management VLAN. The null
	              VID indicates that an Ethernet management VLAN
		      is not configured."
        ::= { vlan 3 }

cnVlanTRMgt OBJECT-TYPE
        SYNTAX        VlanId
        ACCESS        read-write
        STATUS        mandatory
        DESCRIPTION   "VID of the Token Ring management VLAN. The null
	              VID indicates that an Token Ring management VLAN
		      is not configured."
        ::= { vlan 4 }


END
