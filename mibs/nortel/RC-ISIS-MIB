RC-ISIS-MIB DEFINITIONS ::= BEGIN


IMPORTS
    MODULE-IDENTITY, OBJECT-TYPE, Unsigned32, Integer32, Counter32, IpAddress, TimeTicks, Counter64
        FROM SNMPv2-SMI
    TEXTUAL-CONVENTION, DisplayString, RowStatus, TruthValue, MacAddress, StorageType
        FROM SNMPv2-TC
    InterfaceIndex, InterfaceIndexOrZero
        FROM IF-MIB
    EnableValue, rcIsis, PortSet
        FROM RAPID-CITY
    IndexInteger
        FROM DIFFSERV-MIB
    InetAddress, InetAddressType, InetAddressPrefixLength
        FROM INET-ADDRESS-MIB
    VrfIdentifier
        FROM RC-VRF-MIB;

rcIsisMib MODULE-IDENTITY

       LAST-UPDATED     "202011240000Z"
       ORGANIZATION     "Avaya"
       CONTACT-INFO     "
                                        Amit Singh
                         Postal:        Nortel Networks, Inc.
                                        600 Technology Park
                                        Billerica, MA 01821

                         Tel:           978-288-7837
                         E-mail:        amit@ntl.inf.com
                        "
       DESCRIPTION      "Enterprise MIB for the Accelar product family"


       REVISION "202012100000Z" -- 10 Dec  2020
       DESCRIPTION "Version 74:  Review MultiArea Support
                             Requested Nadia S (Oana)"



       REVISION "202011240000Z" -- 24 Nov  2020
       DESCRIPTION "Version 73:  Review MultiArea Support
                             Requested Nadia S (Oana)"


       REVISION "202011050000Z" -- 05 Nov  2020
       DESCRIPTION "Version 72:  Add MultiArea Support
                             Requested Nadia S (Oana)"


       REVISION "202011040000Z" -- 04 Nov  2020
       DESCRIPTION "Version 71:  Update range value for rcIsisGlobalTcpAdjustMssValue
                             Requested Simona C (Oana)"


       REVISION "202010270000Z" -- 27 October  2020
       DESCRIPTION "Version 70:  Add rcIsisGlobalOverloadOnReboot
                             Requested by A Minulescu (Oana)"


       REVISION "202010200000Z" -- 20 October  2020
       DESCRIPTION "Version 69:  Add rcIsisLogicalInterfaceIpsecCompression
                             Requested by Simona C (Prem)"

       REVISION "202010080000Z" -- 08 October  2020
       DESCRIPTION "Version 68:  Add rcIsisGlobalGroup scalars : rcIsisGlobalTcpAdjustMssEnable
                                 rcIsisGlobalTcpAdjustMssStatus , rcIsisGlobalTcpAdjustMssType
                                 rcIsisGlobalTcpAdjustMssValue
                             Requested by Simona C (Oana)"


       REVISION "202009280000Z" -- 28 September  2020
       DESCRIPTION "Version 67:  Add rcIsisPlsbBVlanOrigin in RcIsisPlsbEntry
                             Requested by T Stan (Oana)"

       REVISION "202009040000Z" -- 04 September  2020
       DESCRIPTION "Version 66:  Add rcIsisCircuitOrigin and rcIsisCircuitPlsbOrigin.
                             Requested by A Rebega (Oana)"


       REVISION "202008280000Z" -- 28 August  2020
       DESCRIPTION "Version 65:  Add rcIsisLogicalInterfaceIpsecAuthMethod.
                             Requested by Nadia Saru )Prem)"


	   REVISION "202007140000Z" -- 14 July  2020
       DESCRIPTION "Version 64:  Add rcIsisPlsbMcastFibIsidName.
                             Requested by Dragos TudorDeborah Fitzgerald (Prem)"

	   REVISION "202007060000Z" -- 6 July  2020
       DESCRIPTION "Version 63:  Add rcIsisGlobalMgmtClipIpAddr which depricates
                                 rcIsisGlobalMgmtIpAddr .
                             Requested by Dragos Tudor (Oana)"


       REVISION "202004130000Z" -- 13 April 2020
       DESCRIPTION "Version 62:  Add rcIsisCircuitPlsbOperationalWideL1Metric
                                 under rcIsisCircuitPlsbTable
	                         Requested by Gheorghe Croitoru (Prem)"

       REVISION "201912190000Z" -- 19 December 2019
       DESCRIPTION "Version 61:  Remove rcIsisLogicalInterfaceIpsecNatConfigTable as
	   			 it is not needed anymore and move the objects from
                                 this table to rcIsisLogicalInterfaceTable, so
	   			 add rcIsisLogicalInterfaceIpsecResponderOnly
				 rcIsisLogicalInterfaceIpsecRemoteNatIPAddr
				 to rcIsisLogicalInterfaceTable
	                         Requested by Amogha (Prem)"

       REVISION "201912170000Z" -- 17 December 2019
       DESCRIPTION "Version 60:  Add rcIsisLogicalInterfaceBfdEnable
	                         Requested by Reshma Ramaprasad (Prem)"

       REVISION "201912060000Z" -- 06 December 2019
       DESCRIPTION "Version 59:  Add DEFVAL to rcIsisLogicalInterfaceMtu
	                         Requested by Karthikeyan (Prem)"

       REVISION "201910240000Z" -- 24 October 2019
       DESCRIPTION "Version 58:  Add rcIsisGlobalIpsecTunnelSourceAddress,
	   			 rcIsisLogicalInterfaceEncryptionKeyLength
				 and rcIsisLogicalInterfaceIpsecTunnelDestAddress
	                         Requested by Deeksha (Prem)"

       REVISION "201910150000Z" -- 15 October 2019
       DESCRIPTION "Version 57:  Change the range of rcIsisLogicalInterfaceMtu from 750..8000
	   			 to 750..9000.
	                         Requested by Karthikeyan (Prem)"

       REVISION "201910090000Z" -- 09 October 2019
       DESCRIPTION "Version 56:  Add the following based on VOSS 8.1 mibs MRT syntax check -
	                         * changed the range of rcIsisGlobalIpTunnelMtu from 750..1950
				   to (0 | 750..9000)
				 (Prem)"

       REVISION "201909250000Z" -- 25 Sep 2019
       DESCRIPTION "Version 55:  Add rcIsisLogicalInterfaceIpsecNatConfigTable
	                         Requested by Amogha (Prem)"

       REVISION "201908140000Z" -- 14 Aug 2019
       DESCRIPTION "Version 54:  Add rcIsisLogicalInterfaceMtu
	                         Requested by Karthikeyan (Prem)"

       REVISION "201908120000Z" -- 12 Aug 2019
       DESCRIPTION "Version 53:  Change the range of
	   			 rcIsisLogicalInterfaceShapingRate from
				 0..5000 to 0..1000.
	                         Requested by Simona Chiriac (Prem)"

       REVISION "201906280000Z" -- 28 June 2019
       DESCRIPTION "Version 52:  Updated DEFVAL and Description for
                                 rcIsisCircuitPlsbState. (Oana)"

       REVISION "201904040000Z" -- 4 Apr 2019
       DESCRIPTION "Version 51:  Add rcIsisAdjParallelActive. It was originally
	   			 created in VOSS 7.0 release but was missing
				 in this file (Prem)"

       REVISION "201901230000Z" -- 23 Jan 2019
       DESCRIPTION "Version 50:  Add rcIsisLogicalInterfaceIpsecEnable,
	   			 rcIsisLogicalInterfaceAuthenticationKey and
				 rcIsisLogicalInterfaceShapingRate.
	                         Requested by Simona Chiriac (Prem)"

       REVISION "201811270000Z" -- 27 Nov 2018
       DESCRIPTION "Version 49:  Added rcIsisPlsbIpv6UnicastFibPreference
	                         Requested by Bianca Neagu (Oana)"

       REVISION "201803270000Z" -- 27 Mar 2018
       DESCRIPTION "Version 48:  added rcIsisPlsbIpv6UnicastFibMetricType"

       REVISION "201711080000Z" -- 08 Nov 2017
       DESCRIPTION "Version 47: Added rcIsisCircuitAutoNniEnable"

       REVISION "201710260000Z" -- 26 October 2017
       DESCRIPTION "Version 46: Added enum isisEnabledWithZeroNickname(16) to rcIsisPlsbTrapType
				Requested by Gautam Khera (hliang)"

       REVISION "201710190000Z" -- 19 October 2017
       DESCRIPTION "Version 45: Added rcIsisGlobalMgmtIpAddr and rcIsisGlobalBackboneEnable.
				(Prem)"

       REVISION "201710180000Z" -- 18 October 2017
       DESCRIPTION "Version 44: Added rcIsisFanMember and rcIsisDynamicallyLearnedArea.
				Requested by Gautam Khera (Prem)"

       REVISION "201706080000Z" -- 08 June 2017
       DESCRIPTION "Version 43: Added rcIsisPlsbStpMultiHoming.
				Requested by Ashwin Kumar Ravichandran
				Submit 34429 (Helen)"

       REVISION "201612050000Z" -- 05 December 2016
       DESCRIPTION "Version 42: Added rcIsisLSPSmltBmac.
				Requested by Zuyan Wang (Zuyan)"

       REVISION "201606230000Z" -- 23 June 2016
       DESCRIPTION "Version 41: Added rcIsisLogicalInterfaceNextHopTable.
				Requested by Amruta Manjunath Bhat (Prem)"

       REVISION "201604190000Z" -- 19 April 2016
       DESCRIPTION "Version 40: Changed rcIsisPlsbMcastPimGatewayControllerEnable
	   			and rcIsisPlsbMcastPimGatewayAgentEnable to
				rcIsisPlsbMcastSpbPimGwControllerEnable and
				rcIsisPlsbMcastSpbPimGwGatewayEnable.
				Requested by Veda (Prem)"

       REVISION "201512240000Z" -- 24 December 2015
       DESCRIPTION "Version 39: Extended the range of rcIsisLogicalInterfaceName
	   			from 1..16 to 1..64 (based on VOSS 5.0 release) (Prem)"

       REVISION "201509020000Z" -- 2 September 2015
       DESCRIPTION "Version 38: Added rcIsisPlsbMcastPimGatewayControllerEnable
	   			and rcIsisPlsbMcastPimGatewayAgentEnable
	   			Requested by Veda, submit 25389 (Prem)"

       REVISION "201508100000Z" -- 10 August 2015
       DESCRIPTION "Version 37: Changed the range of rcIsisLogicalInterfaceName from
	   			1 - 64 to 1 - 16 (Prem)"

       REVISION "201507290000Z" -- 29 July 2015
       DESCRIPTION "Version 36: Changed the range of rcIsisLogicalInterfaceId from
	   			1 - 256 to 1 - 255 based on design limitations.
				Requested by Michael Nguyen (submit 24704) (Prem)"

       REVISION "201507220000Z" -- 22 July 2015
       DESCRIPTION "Version 35: Added the following enumeration values to rcIsisPlsbTrapType -
	   				localDuplicateNickname(14)
					globalDuplicateNickname(15)
	   			Changed -
	   			 rcIsisGlobalDuplicateSysIdRemoteHostName to
				 rcIsisRemoteHostName.
				 rcIsisGlobalDuplicateSysIdRemoteChassisMac to
				 rcIsisRemoteChassisMac.
				Added rcIsisPreviousSysId.
	   			Requested by Gautam Khera (submit 24985) (Prem)"

       REVISION "201507210000Z" -- 21 July 2015
       DESCRIPTION "Version 34: Added rcIsisSpbmMcastFibUniTable.
	   			Requested by Zuyan (Prem)"

       REVISION "201507130000Z" -- 13 July 2015
       DESCRIPTION "Version 33: Changed the range of rcIsisGlobalIpTunnelMtu
	   			from Unsigned32 (1280..1500 | 1850 | 9500)
	   			to Unsigned32 (750..1950)
				Requested by M.V. Sreekumar (submit 24791) (Prem)"

       REVISION "201506300000Z" -- 30 June 2015
       DESCRIPTION "Version 32: Added -
	   			rcIsisLogicalInterfaceCircIndex,
	   			rcIsisLogicalInterfaceNextHopIfIndex,
	   			rcIsisLogicalInterfaceNextHopVid,
	   			rcIsisLogicalInterfaceNextHopVrf.
				Requested by Amruta Manjunath Bhat (Prem)"

       REVISION "201506170000Z" -- 17 June 2015
       DESCRIPTION "Version 31: Added -
	   			globalDuplicateSystemId(13) to rcIsisPlsbTrapType,
				rcIsisLocalChassisMac,
				rcIsisGlobalDuplicateSysIdRemoteChassisMac,
				rcIsisGlobalDuplicateSysIdRemoteNodeHostName
				Requested by Gautam Khera (Prem)"

       REVISION "201506090000Z" -- 09 June 2015
       DESCRIPTION "Version 30: update rcIsisSpbmUniTable to support
                                Transparent UNI on remote SMLT peer"

       REVISION "201506010000Z" -- 01 June 2015
       DESCRIPTION "Version 29: rcIsisGlobalIpTunnelMtu based on 24255"

       REVISION "201505130000Z" -- 13 May 2015
       DESCRIPTION "Version 28: Added rcIsisPlsbIpInterIsidUnicastFibMetricType
	                        Requested by Gautam (Prem)"

       REVISION "201502270000Z" -- 27 Feb. 2015
       DESCRIPTION "Version 27: Update rcIsisLogicalInterfaceTable based on
	                        VSP submit 22940"

       REVISION "201502170000Z" -- 17 Feb. 2015
       DESCRIPTION "Version 26: Added rcIsisLogicalInterfaceTable,
	                              rcIsisGlobalIpTunnelSourceAddress,
				      rcIsisGlobalIpTunnelPort and
				      rcIsisGlobalIpTunnelVrf"

       REVISION "201411240000Z" -- 24 Nov. 2014
       DESCRIPTION "Version 25: Added rcIsisSpbmUniStorage"

       REVISION "201411140000Z" -- 14 Nov. 2014
       DESCRIPTION "Version 24: Changed the MAX-ACCESS from read-only to
	   	    accessible-for-notify for
		    rcIsisSmltVirtBmacMisconfigNodeHostName and
		    rcIsisSmltVirtBmacMisconfigNodeSysId.
		    Requested by Zuyan Wang.
		    Changes made in VSP9k 4.0 (Prem)"

       REVISION "201409160000Z" -- 16 Sept. 2014
       DESCRIPTION "Version 23: obsolete rcIsisSpbmIpMcastRouteUniRcvrsTable
	                                 and rcIsisSpbmIpMcastRouteTable
				Added rcIsisSpbmIpIsidMcastRouteTable
				      rcIsisSpbmIpIsidMcastRouteUniRcvrsTable"

       REVISION "201409030000Z" -- 03 Sept. 2014
       DESCRIPTION "Version 22: Obsolete rcIsisPlsbMcastFibOutgoingPorts and
	                        rcIsisSpbmIpMcastNniPorts
				Added rcIsisPlsbMcastFibOutgoingInterfacePorts,
				rcIsisPlsbMcastFibOutgoingInterfaceMlts,
				rcIsisPlsbMcastFibIncomingInterface,
				rcIsisSpbmIpMcastNniInterfacePorts,
				and rcIsisSpbmIpMcastNniInterfaceMlts"

       REVISION "201408280000Z" -- 28 August 2014
       DESCRIPTION "Version 21: Added rcIsisPlsbIpInterIsidUnicastFibPreference"

       REVISION "201408060000Z" -- 06 August 2014
       DESCRIPTION "Version 20: Added rcIsisGlobalIpv6SourceAddress and
	   			rcIsisGlobalIpv6SourceAddressType under rcIsisGlobalGroup.
				Added rcIsisPlsbIpv6Shortcut under rcIsisPlsbEntry.
				Added rcIsisPlsbIpv6UnicastFibTable"

       REVISION "201407040000Z" -- 04 July 2014
       DESCRIPTION "Version 19: Added rcIsisSpbmScalars group."

       REVISION "201406050000Z" -- 05 June 2014
       DESCRIPTION "Version 18: Change range form (1..4094) to
	                        (0..4094) for rcIsisPlsbIpInterIsidUnicastFibVlan"

       REVISION "201404220000Z" -- 22 April 2014
       DESCRIPTION "Version 17: Added enum values - smltVirtBmacMisconfigSysid
                    and smltVirtBmacMisconfigMac under rcIsisPlsbTrapType.
                    Added rcIsisSmltVirtBmacMisconfigNodeHostName and
                    rcIsisSmltVirtBmacMisconfigNodeSysId."

       REVISION "201308130000Z" -- 13 November 2013
       DESCRIPTION "Version 16: Added rcIsisPlsbIpInterIsidUnicastFibTable"

       REVISION "201310110000Z" -- 11 October 2013
       DESCRIPTION "Version 15: Added types to IMPORTS section"

       REVISION "201208020000Z" -- 02 August 2012
       DESCRIPTION "Version 14: Added rcIsisPlsbMcast,
                                      rcIsisPlsbMcastFwdCacheTimeout"

       REVISION "201205030000Z" -- 03 May 2012
       DESCRIPTION "Version 13: Added rcIsisSpbmIpMcastRouteTable,
                                      rcIsisSpmbIpMcastRouteUniRcvrsTable"

       REVISION "201204200000Z" -- 20 April 2012
       DESCRIPTION "Version 12: Added rcIsisSpbmUniTable"

       REVISION "201110130000Z" -- 13 October 2011
       DESCRIPTION "Version 11: Use Integer32 instead of INTEGER for unbounded
                                integer values for compatibility with legacy MIB compiler"

       REVISION "201105130000Z" -- 13 May 2011
       DESCRIPTION "Version 10: Added rcIsisSpbmPortDropStatsTable,
                                      rcIsisSpbmSrcAddrDropStatsTable"

       REVISION "201102090000Z" -- 09 Feb 2011
       DESCRIPTION "Version 9:  Corrected the MAX-ACCESS for rcIsisPlsbSmltSplitBEB."

       REVISION "201102040000Z" -- 04 Feb 2011
       DESCRIPTION "Version 8:  Added IsisSystemID definition"

       REVISION "201101140000Z" -- 14 January 2011
       DESCRIPTION "Version 7:  Added IsisPlsbBvid, IsisPlsbBvidTieBrkAlg,
	                        rcIsisGlobalIpSourceAddress, rcIsisGlobalIpSourceAddressType,
				rcIsisPlsbState, rcIsisPlsbIpShortcut,
				rcIsisPlsbPrimaryVlan, rcIsisPlsbSmltSplitBEB,
				rcIsisPlsbSmltBmac, rcIsisPlsbSmltPeerSysId,
				rcIsisLocalPrimaryBvid,	rcIsisLocalPrimaryTieBrkAlg,
				rcIsisLocalSecondaryBvid, rcIsisLocalSecondaryTieBrkAlg,
				rcIsisNgbPrimaryBvid, rcIsisNgbPrimaryTieBrkAlg,
				rcIsisNgbSecondaryBvid,	rcIsisNgbSecondaryTieBrkAlg,
				rcIsisLocalVirtualBmac,	rcIsisPeerVirtualBmac,
				rcIsisSysId, rcIsisSmltPeerSysId, rcIsisAdjState,
				rcIsisDuplicateNnameCounter, rcIsisLocalBvidCounter,
				rcIsisNgbBvidCounter, rcIsisLocalSmltSplitBeb,
				rcIsisPeerSmltSplitBeb,	rcIsisLocalHostName,
				rcIsisNgbHostName, rcIsisPrevInterface,
				rcIsisLSPNickName, rcIsisLSPLifetimeRemain,
				rcIsisPlsbIpUnicastFibTable, rcIsisPlsbUcastFibTable,
				rcIsisPlsbMcastFibTable, rcIsisPlsbNodeTable.
	                        Changed the size of rcIsisGlobalSpfDelay.
				Added bvidMismatch(5), smltVirtBmacMismatch(6),
				smltPeerBmacMismatch(7), adjState(8),
				smltSplitBebMismatch(9), multiLinkAdj(10) under
				the enum definition for rcIsisPlsbTrapType."

       REVISION "200902270000Z" -- 27 Feb 2009
       DESCRIPTION "Version 6:  Added rcIsisPlsbUnicastFibSysId  under rcIsisPlsbUnicastFibTable "

       REVISION "200807140000Z" -- 14 July 2008
       DESCRIPTION "Version 5: Added rcIsisPlsbMulticastFibSysId,
 	                       rcIsisPlsbIsidSysId,
			       rcIsis 10, 11,IsisWideL1Metric,
			       rcIsisCircuitPlsbWideL1Metric
			       Modified IsisDefaultMetric to IsisDefaultL1Metric,
			       rcIsisLocalNickname, rcIsisNgbNickname
			       Modified rcIsisPlsbMulticastFibEntry,
			       RcIsisPlsbIsidEntry"

       REVISION "200805130000Z" -- 13 May 2008
       DESCRIPTION "Version 4: Definition of IsisPlsbNodeNickName, changed syntax of rcIsisCircuitPlsbIndex, imported EnableValue."

       REVISION "200805090000Z" -- 09 May 2008
       DESCRIPTION "Version 3: Fixed smilint errors."

       REVISION "200803140000Z" -- 14 March 2008
       DESCRIPTION "Version 2: Added rcIsis 4 - rcIsis 9,
	                       Modified rcIsisGlobal to rcIsisGlobalGroup"

       REVISION "200508180000Z" -- 18 Aug 2005
       DESCRIPTION "Version 1: Added ISIS enterprise MIB"

       ::= { rcIsis 0 }

-- ISIS Textual Conventions

IsisPlsbNodeNickName ::= TEXTUAL-CONVENTION
        STATUS       current
        DESCRIPTION  "Plsb Node Nick name."
        SYNTAX OCTET STRING (SIZE(3))

IsisSystemID ::= TEXTUAL-CONVENTION
        STATUS current
        DESCRIPTION
            "A system ID."
        SYNTAX OCTET STRING (SIZE(6))

IsisPlsbBvid ::= TEXTUAL-CONVENTION
        STATUS current
        DESCRIPTION
            "ISIS B-VLAN ID."
        SYNTAX Integer32 (0..4096)

IsisPlsbBvidTieBrkAlg ::= TEXTUAL-CONVENTION
        STATUS current
        DESCRIPTION
            "ISIS B-VLAN tie breaking algorithm."
        SYNTAX INTEGER {
		    low-pathid(1),
		    high-pathid(2)
		}

-- --------------------------------------------------
-- ISIS Global configuration objects
-- --------------------------------------------------

rcIsisGlobalGroup OBJECT IDENTIFIER ::= { rcIsis 1 }

rcIsisGlobalAreaAuthType  OBJECT-TYPE
        SYNTAX        INTEGER {
                                none(0),
                                simple(1),
                                hmac-md5(2)
                              }
        MAX-ACCESS    read-write
        STATUS        current
        DESCRIPTION   "The authentication type for the area"
        DEFVAL      { none }
               ::= { rcIsisGlobalGroup 1 }

rcIsisGlobalAreaKeyId  OBJECT-TYPE
        SYNTAX        Integer32 (1..255)
        MAX-ACCESS    read-write
        STATUS        current
        DESCRIPTION   "Authentication key-id for the area. This is
                       required if the auth-type is hmac-md5 else it is
                       not required."
        ::= { rcIsisGlobalGroup 2 }

rcIsisGlobalAreaAuthKey  OBJECT-TYPE
        SYNTAX        OCTET STRING (SIZE(0..255))
        MAX-ACCESS    read-write
        STATUS        current
        DESCRIPTION   "Authentication key, this key will be used to
                       authenticate the LSP's received on the area"
        ::= { rcIsisGlobalGroup 3 }

rcIsisGlobalDomainAuthType  OBJECT-TYPE
        SYNTAX        INTEGER {
                          none(0),
                          simple(1),
                          hmac-md5(2)
                      }
        MAX-ACCESS    read-write
        STATUS        current
        DESCRIPTION   "The authentication type for the domain"
        DEFVAL        { none }
        ::= { rcIsisGlobalGroup 4 }

rcIsisGlobalDomainKeyId  OBJECT-TYPE
        SYNTAX        Integer32 (1..255)
        MAX-ACCESS    read-write
        STATUS        current
        DESCRIPTION   "The authentication key-id for the domain. This is
                       required if the auth-type is hmac-md5 else it is
                       not required."
        ::= { rcIsisGlobalGroup 5 }

rcIsisGlobalDomainAuthKey  OBJECT-TYPE
        SYNTAX        OCTET STRING (SIZE(0..255))
        MAX-ACCESS    read-write
        STATUS        current
        DESCRIPTION   "Authentication key, this key will be used to
                       authenticate the LSP's received on the domain"
        ::= { rcIsisGlobalGroup 6 }

rcIsisGlobalCsnpInt OBJECT-TYPE
        SYNTAX        Integer32 (1..600)
        MAX-ACCESS    read-write
        STATUS        current
        DESCRIPTION   "Interval of time, in seconds, between periodic
                       transmission of a complete set of CSNPs on
                       multiaccess networks if this router is the
                       designated router at this level.
                       This object follows the resettingTimer behavior.
                       For ResettingTimer description see the ISIS MIB"
        DEFVAL        { 10 }
        ::= { rcIsisGlobalGroup 7 }

rcIsisGlobalRxmtLspInt  OBJECT-TYPE
        SYNTAX        Integer32 (1..300)
        MAX-ACCESS    read-write
        STATUS        current
        DESCRIPTION   "Minimum interval, in seconds, between
                       re-transmission of a LSP at this level. This
                       object follows the resettingTimer behavior.
                       For ResettingTimer description see the ISIS MIB"
        DEFVAL        { 5 }
        ::= { rcIsisGlobalGroup 8 }

rcIsisGlobalPSNPInterval OBJECT-TYPE
        SYNTAX     Integer32 (1..120)
        UNITS      "seconds"
        MAX-ACCESS read-write
        STATUS     current
        DESCRIPTION "Minimum interval in seconds between sending Partial
                     Sequence Number PDUs at this level. This object
                     follows the resettingTimer behavior.
                     For ResettingTimer description see the ISIS MIB"
        DEFVAL { 2 }
        ::= { rcIsisGlobalGroup 9 }

rcIsisGlobalHostName OBJECT-TYPE
        SYNTAX     OCTET STRING (SIZE (0..255))
        MAX-ACCESS read-write
        STATUS     current
        DESCRIPTION
            "The hostname listed in LSP, or the system name if host
             name is not configured."
        ::= { rcIsisGlobalGroup 10 }

rcIsisGlobalSpfDelay OBJECT-TYPE
        SYNTAX     Integer32 (0..5000)
        UNITS      "milliseconds"
        MAX-ACCESS read-write
        STATUS     current
        DESCRIPTION "ISIS SPF delay in miliseconds"
        DEFVAL { 500 }
        ::= { rcIsisGlobalGroup 11 }

rcIsisGlobalControlVlan OBJECT-TYPE
        SYNTAX     Integer32 (1..4094)
        MAX-ACCESS read-write
        STATUS     current
        DESCRIPTION "ISIS control vlan ID"
        ::= { rcIsisGlobalGroup 12 }

rcIsisGlobalIpSourceAddress OBJECT-TYPE
        SYNTAX     InetAddress
        MAX-ACCESS read-write
        STATUS     current
        DESCRIPTION "ISIS PLSB IP address. Define an existing router interface
		     for management (ping/traceroute)"
        ::= { rcIsisGlobalGroup 13 }

rcIsisGlobalIpSourceAddressType OBJECT-TYPE
        SYNTAX     InetAddressType
        MAX-ACCESS read-write
        STATUS     current
        DESCRIPTION "The type of address for existing router interface
		     for management (ping/traceroute)"
        ::= { rcIsisGlobalGroup 14 }

rcIsisGlobalIpv6SourceAddress OBJECT-TYPE
        SYNTAX     InetAddress
        MAX-ACCESS read-write
        STATUS     current
        DESCRIPTION "ISIS PLSB IPv6 address. Define an existing router interface
		     for management (ping/traceroute)"
        ::= { rcIsisGlobalGroup 15 }

rcIsisGlobalIpv6SourceAddressType OBJECT-TYPE
        SYNTAX     InetAddressType
        MAX-ACCESS read-write
        STATUS     current
        DESCRIPTION "The type of address for existing router interface
		     for management (ping/traceroute)"
        ::= { rcIsisGlobalGroup 16 }

rcIsisGlobalIpTunnelSourceAddress OBJECT-TYPE
        SYNTAX     IpAddress
        MAX-ACCESS read-write
        STATUS     current
        DESCRIPTION "ISIS IP tunnel source address"
        ::= { rcIsisGlobalGroup 17 }

rcIsisGlobalIpTunnelPort OBJECT-TYPE
	SYNTAX     InterfaceIndexOrZero
	MAX-ACCESS read-write
     	STATUS     current
    	DESCRIPTION "Port associated with IP tunnel"
    	::= { rcIsisGlobalGroup 18 }

rcIsisGlobalIpTunnelVrf OBJECT-TYPE
	SYNTAX     DisplayString (SIZE (1..16))
	MAX-ACCESS read-write
     	STATUS     current
    	DESCRIPTION "VRF name of the ip tunnel"
    	::= { rcIsisGlobalGroup 19 }

rcIsisGlobalIpTunnelMtu  OBJECT-TYPE
        SYNTAX     Unsigned32 (0 | 750..9000)
	MAX-ACCESS read-write
	STATUS     current
	DESCRIPTION "The value specifies the logical tunnel MTU"
        ::= { rcIsisGlobalGroup 20 }

rcIsisGlobalMgmtIpAddr  OBJECT-TYPE
        SYNTAX        IpAddress
	MAX-ACCESS    read-write
	STATUS        current
	DESCRIPTION   "Inband management IPv4 address and can
                   be used by both DVR and non DVR enabled nodes.
                   Deprecated by rcIsisGlobalMgmtClipIpAddr because inband-mgmt-ip command
                   is removed in 8.2"
        ::= { rcIsisGlobalGroup 21 }

rcIsisGlobalBackboneEnable  OBJECT-TYPE
        SYNTAX        TruthValue
	MAX-ACCESS    read-write
	STATUS        current
	DESCRIPTION   "Allow a non DVR BEB to join the DVR backbone tree
                       in order to receive redistributed DVR Host Routes
                       from all the different DVR Controllers in the SPB Network."
        DEFVAL        { false }
        ::= { rcIsisGlobalGroup 22 }

rcIsisFanMember OBJECT-TYPE
        SYNTAX        TruthValue
	MAX-ACCESS    read-only
	STATUS        current
	DESCRIPTION   "Indicates if the node is a member of the Fabric
	    	       Area Network(FAN). It is a member if the nickname
		       server is running on the node or if the nickname
		       is zero or if the nickname is dynamically assigned."
	DEFVAL        { true }
        ::= { rcIsisGlobalGroup 23 }

rcIsisDynamicallyLearnedArea  OBJECT-TYPE
        SYNTAX        OCTET STRING (SIZE (0..20))
	MAX-ACCESS    read-only
	STATUS        current
	DESCRIPTION   "ISIS area that is dynamically learned from the
	    	       neighbor's HELLO PDU if the node does not have
		       the ISIS manual area configured."
        DEFVAL        { "" }
        ::= { rcIsisGlobalGroup 24 }

rcIsisGlobalIpsecTunnelSourceAddress OBJECT-TYPE
        SYNTAX     IpAddress
        MAX-ACCESS read-write
        STATUS     current
        DESCRIPTION "ISIS IPSec tunnel source address"
        ::= { rcIsisGlobalGroup 25 }

rcIsisGlobalMgmtClipIpAddr  OBJECT-TYPE
        SYNTAX        IpAddress
        MAX-ACCESS    read-only
        STATUS        current
        DESCRIPTION   "The dut's mgmt clip IP address that can
                       be used by both DVR and non DVR enabled nodes."
        ::= { rcIsisGlobalGroup 26 }


rcIsisGlobalTcpAdjustMssEnable  OBJECT-TYPE
          SYNTAX             TruthValue
          MAX-ACCESS         read-write
          STATUS             current
          DESCRIPTION   "Enable or disable adjusting the maximum segment size (MSS) value of TCP packets.
                          This object is applicable only for ExtremeAccess platforms XA1440 and XA1480."
          DEFVAL             { true }
          ::= { rcIsisGlobalGroup 27 }

rcIsisGlobalTcpAdjustMssStatus  OBJECT-TYPE
           SYNTAX        INTEGER{
                                  active(1),
                                  inactive(2)
                         }
           MAX-ACCESS     read-only
           STATUS         current
           DESCRIPTION    "Status of TCP adjust MSS.
                           This object is applicable only for ExtremeAccess platforms XA1440 and XA1480."
           DEFVAL          { inactive }
           ::= { rcIsisGlobalGroup 28 }

rcIsisGlobalTcpAdjustMssType  OBJECT-TYPE
           SYNTAX      INTEGER{
                                autoDerived(1),
                                manualConfig(2)
                              }
           MAX-ACCESS    read-only
           STATUS        current
           DESCRIPTION   "Type of TCP adjust MSS.
                          This object is applicable only for ExtremeAccess platforms XA1440 and XA1480."
           DEFVAL        { autoDerived }
           ::= { rcIsisGlobalGroup 29 }

rcIsisGlobalTcpAdjustMssValue  OBJECT-TYPE
          SYNTAX         INTEGER (0 | 500..1250)
          MAX-ACCESS     read-write
          STATUS         current
          DESCRIPTION    "TCP adjust MSS value.
                          If rcIsisGlobalTcpAdjustMssEnable is true, rcIsisGlobalTcpAdjustMssValue is 0 or different than 0,
                          no matter what rcIsisGlobalTcpAdjustMssType is.
                          If rcIsisGlobalTcpAdjustMssEnable is false, rcIsisGlobalTcpAdjustMssValue is different than 0
                          only if rcIsisGlobalTcpAdjustMssType is manualConfig.
                          This object is applicable only for ExtremeAccess platforms XA1440 and XA1480."
          DEFVAL              { 0 }
          ::= { rcIsisGlobalGroup 30 }


rcIsisGlobalMAOperState OBJECT-TYPE
        SYNTAX        INTEGER {
                          disabled(1),
                          init(2),
                          non-designated(3),
                          designated(4)
                      }
        MAX-ACCESS    read-only
        STATUS        current
        DESCRIPTION   "Multi-area operational state"
        DEFVAL        {disabled}
        ::= { rcIsisGlobalGroup 31 }


-- --------------------------------------------------
-- rcIsisCircuitTable
-- --------------------------------------------------

rcIsisCircuitTable      OBJECT-TYPE
        SYNTAX          SEQUENCE OF RcIsisCircuitEntry
        MAX-ACCESS      not-accessible
        STATUS          current
        DESCRIPTION     "Table of IS-IS Circuit, this is extension
                         to the isisCircTable defined in ISIS MIB"
        ::= { rcIsis 2 }

rcIsisCircuitEntry OBJECT-TYPE
        SYNTAX          RcIsisCircuitEntry
        MAX-ACCESS      not-accessible
        STATUS          current
        DESCRIPTION     "An entry of rcIsisCircuit Table. A Entry in
                         table exists for each ISIS circuit created"
        INDEX           { rcIsisCircuitIndex }
        ::= { rcIsisCircuitTable 1 }

RcIsisCircuitEntry   ::=
        SEQUENCE {
          rcIsisCircuitIndex        Integer32,
          rcIsisCircuitType         INTEGER,
          rcIsisCircuitAuthType     INTEGER,
          rcIsisCircuitKeyId        INTEGER,
          rcIsisCircuitAuthKey      OCTET STRING,
          rcIsisCircuitAddr         IpAddress,
          rcIsisCircuitMask         IpAddress,
          rcIsisCircuitOperState    INTEGER,
          rcIsisCircuitNumAdj       Integer32,
          rcIsisCircuitNumUpAdj     Integer32,
	  rcIsisCircuitAutoNniEnable TruthValue,
          rcIsisCircuitOrigin       INTEGER
        }

rcIsisCircuitIndex   OBJECT-TYPE
        SYNTAX        Integer32 (1..2147483647)
        MAX-ACCESS    not-accessible
        STATUS        current
        DESCRIPTION  "The identifier of this circuit, unique within the
                      Intermediate System.  This object follows
                      the index behavior.  This is for SNMP Indexing
                      purposes only and need not have any relation to
                      any protocol value."
        ::= { rcIsisCircuitEntry 1 }

rcIsisCircuitType    OBJECT-TYPE
        SYNTAX        INTEGER {
                          bcast(1),
                          ptpt(2),
                          passive(3)
                      }
        MAX-ACCESS    read-write
        STATUS        current
        DESCRIPTION   "ISIS circuit type this is an extention to
                       ISIS circuit table, this was required a
                       standard MIB circuit type does not support
                       passive type"
        DEFVAL        { bcast }
        ::= { rcIsisCircuitEntry 2 }

rcIsisCircuitAuthType    OBJECT-TYPE
        SYNTAX        INTEGER {
                         none(0),
                         simple(1),
                         hmac-md5(2)
                      }
        MAX-ACCESS    read-write
        STATUS        current
        DESCRIPTION   "Authentication type for IIH to be sent/reveived
                       on the circuit/interface"
        DEFVAL        { none }
        ::= { rcIsisCircuitEntry 3 }

rcIsisCircuitKeyId     OBJECT-TYPE
        SYNTAX        INTEGER (1..255)
        MAX-ACCESS    read-write
        STATUS        current
        DESCRIPTION   "Authentication key id related to IIH key
                       This can be set only if the auth-type is hmac-md5"
        ::= { rcIsisCircuitEntry 4 }

rcIsisCircuitAuthKey     OBJECT-TYPE
        SYNTAX        OCTET STRING(SIZE(0..255))
        MAX-ACCESS    read-write
        STATUS        current
        DESCRIPTION   "Authentication key to be used to authenticate
                       IIH sent/reveived on the circuit/interface"
        ::= { rcIsisCircuitEntry 5 }

rcIsisCircuitAddr     OBJECT-TYPE
        SYNTAX        IpAddress
        MAX-ACCESS    read-only
        STATUS        current
        DESCRIPTION   "IP address associated with the interface"
        ::= { rcIsisCircuitEntry 6 }

rcIsisCircuitMask     OBJECT-TYPE
        SYNTAX        IpAddress
        MAX-ACCESS    read-only
        STATUS        current
        DESCRIPTION   "IP mask associated with the interface"
        ::= { rcIsisCircuitEntry 7 }

rcIsisCircuitOperState     OBJECT-TYPE
        SYNTAX        INTEGER {
                        unknown(0),
                        up(1),
                        down(2)
                      }
        MAX-ACCESS    read-only
        STATUS        current
        DESCRIPTION   "This variable tells the operating state of circ"
        ::= { rcIsisCircuitEntry 8 }

rcIsisCircuitNumAdj     OBJECT-TYPE
        SYNTAX        Integer32
        MAX-ACCESS    read-only
        STATUS        current
        DESCRIPTION   "NUmber of adjacencies"
        ::= { rcIsisCircuitEntry 9 }

rcIsisCircuitNumUpAdj     OBJECT-TYPE
        SYNTAX        Integer32
        MAX-ACCESS    read-only
        STATUS        current
        DESCRIPTION   "Number of adjancencies which are UP"
        ::= { rcIsisCircuitEntry 10 }

rcIsisCircuitAutoNniEnable OBJECT-TYPE
    	SYNTAX       TruthValue
	MAX-ACCESS   read-write
	STATUS       current
        DESCRIPTION "Set to true if user wants to auto create the NNI
	     	      interface. This will create a entry in this table
		      and in rcIsisCircuitPlsbTablei, associating this
		      ciruit to the first available SPBM instance."
        DEFVAL  { false }
	::= { rcIsisCircuitEntry 11 }


rcIsisCircuitOrigin     OBJECT-TYPE
        SYNTAX        INTEGER {
                         config(1),
                         autoSense(2)
                      }
        MAX-ACCESS    read-only
        STATUS        current
        DESCRIPTION   "Describes how IsisCircuitEntry was created:
        manual (SNMP/CLI), ZTF(Auto-Sense) or other."
        ::= { rcIsisCircuitEntry 12 }

-- --------------------------------------------------
-- Global stats objects
-- --------------------------------------------------

rcIsisStats OBJECT IDENTIFIER ::= { rcIsis 3 }

rcIsisStatsClearErrorCounters  OBJECT-TYPE
     SYNTAX             TruthValue
     MAX-ACCESS         read-write
     STATUS             current
     DESCRIPTION        "Clear ISIS global and interface error counters."
     DEFVAL             { false }
     ::= { rcIsisStats 1 }

rcIsisStatsClearPacketCounters  OBJECT-TYPE
     SYNTAX             TruthValue
     MAX-ACCESS         read-write
     STATUS             current
     DESCRIPTION        "Clear IS-IS control packets sent and received
                        at each level on all the interface/circuits."
     DEFVAL             { false }
     ::= { rcIsisStats 2 }

-- BEGIN rcIsisPlsbTable --

rcIsisPlsbTable  OBJECT-TYPE
          SYNTAX          SEQUENCE OF RcIsisPlsbEntry
          MAX-ACCESS      not-accessible
          STATUS          current
          DESCRIPTION     "Table of PLSB under IS-IS"
        ::= { rcIsis 4}

rcIsisPlsbEntry OBJECT-TYPE
        SYNTAX          RcIsisPlsbEntry
        MAX-ACCESS      not-accessible
        STATUS          current
        DESCRIPTION     "An entry of rcIsisPlsb Table. A Entry in
                         table exists for each plsb instance created"
        INDEX           { rcIsisPlsbId }
        ::= { rcIsisPlsbTable 1 }

RcIsisPlsbEntry   ::=
        SEQUENCE {
        rcIsisPlsbId              Integer32,
        rcIsisPlsbRowStatus       RowStatus,
        rcIsisPlsbNodeNickName    IsisPlsbNodeNickName,
        rcIsisPlsbVlans           OCTET STRING,
        rcIsisPlsbLsdbTrap        EnableValue,
        rcIsisPlsbState           EnableValue,
	rcIsisPlsbIpShortcut	  EnableValue,
	rcIsisPlsbPrimaryVlan	  Integer32,
	rcIsisPlsbSmltSplitBEB	  INTEGER,
	rcIsisPlsbSmltBmac	  MacAddress,
	rcIsisPlsbSmltPeerSysId   IsisSystemID,
	rcIsisPlsbMcast           EnableValue,
        rcIsisPlsbMcastFwdCacheTimeout Integer32,
	rcIsisPlsbIpv6Shortcut    EnableValue,
        rcIsisPlsbMcastSpbPimGwControllerEnable    TruthValue,
        rcIsisPlsbMcastSpbPimGwGatewayEnable    TruthValue,
	rcIsisPlsbStpMultiHoming      TruthValue,
        rcIsisPlsbBVlanOrigin  INTEGER
        }

rcIsisPlsbId OBJECT-TYPE
        SYNTAX          Integer32 (1..100)
        MAX-ACCESS      not-accessible
        STATUS          current
        DESCRIPTION
            "PLSB instance ID"
    ::= { rcIsisPlsbEntry 1 }

rcIsisPlsbRowStatus  OBJECT-TYPE
        SYNTAX 		RowStatus
        MAX-ACCESS 	read-create
        STATUS 		current
        DESCRIPTION
            "The state of the rcIsisPlsbEntry.  "
    ::= { rcIsisPlsbEntry 2 }

rcIsisPlsbNodeNickName OBJECT-TYPE
        SYNTAX 		IsisPlsbNodeNickName
        MAX-ACCESS 	read-create
        STATUS 		current
        DESCRIPTION
            "PLSB node's nickname is used to
             calculate ISID multicast mac address."
    ::= { rcIsisPlsbEntry 3 }

rcIsisPlsbVlans OBJECT-TYPE
        SYNTAX          OCTET STRING(SIZE(512))
        MAX-ACCESS      read-create
        STATUS          current
        DESCRIPTION
            "PLSB ISIS vlans for a PLSB instance."
    ::= { rcIsisPlsbEntry 4 }

rcIsisPlsbLsdbTrap OBJECT-TYPE
        SYNTAX        EnableValue
        MAX-ACCESS    read-create
        STATUS        current
        DESCRIPTION   "isis PLSB lsdb update trap enable on this plsb instance"
	DEFVAL        { disable }
        ::= { rcIsisPlsbEntry 5 }

rcIsisPlsbState OBJECT-TYPE
        SYNTAX        EnableValue
        MAX-ACCESS    read-create
        STATUS        current
        DESCRIPTION   "enable/disable PLSB."
        ::= { rcIsisPlsbEntry 6 }

rcIsisPlsbIpShortcut OBJECT-TYPE
        SYNTAX        EnableValue
        MAX-ACCESS    read-create
        STATUS        current
        DESCRIPTION   "ISIS PLSB IP shortcut enabled"
        DEFVAL        { disable }
        ::= { rcIsisPlsbEntry 7 }

rcIsisPlsbPrimaryVlan OBJECT-TYPE
        SYNTAX        Integer32 (1..4094)
        MAX-ACCESS    read-create
        STATUS        current
        DESCRIPTION   "Primary Vlan Id for this plsb instance."
        ::= { rcIsisPlsbEntry 8 }

rcIsisPlsbSmltSplitBEB OBJECT-TYPE
        SYNTAX        INTEGER {
                          primary(1),
                          secondary(2)
		      }
        MAX-ACCESS    read-only
        STATUS        current
        DESCRIPTION   "ISIS PLSB SMLT split BEB for this plsb instance."
        DEFVAL        { primary }
        ::= { rcIsisPlsbEntry 9 }

rcIsisPlsbSmltBmac OBJECT-TYPE
        SYNTAX        MacAddress
        MAX-ACCESS    read-create
        STATUS        current
        DESCRIPTION   "ISIS PLSB SMLT virtual MAC for this plsb instance."
        ::= { rcIsisPlsbEntry 10 }

rcIsisPlsbSmltPeerSysId OBJECT-TYPE
        SYNTAX        IsisSystemID
        MAX-ACCESS    read-create
        STATUS        current
        DESCRIPTION   "ISIS PLSB SMLT Peer's system-id for this plsb instance."
        ::= { rcIsisPlsbEntry 11 }

rcIsisPlsbMcast OBJECT-TYPE
        SYNTAX        EnableValue
        MAX-ACCESS    read-create
        STATUS        current
        DESCRIPTION   "ISIS PLSB Multicast enable"
        DEFVAL        { disable }
        ::= { rcIsisPlsbEntry 12 }

rcIsisPlsbMcastFwdCacheTimeout OBJECT-TYPE
        SYNTAX        Integer32 (10..86400)
        MAX-ACCESS    read-create
        STATUS        current
        DESCRIPTION   "Multicast Fwd Cache Timeout in seconds"
        DEFVAL        { 210 }
        ::= { rcIsisPlsbEntry 13 }

rcIsisPlsbIpv6Shortcut OBJECT-TYPE
        SYNTAX        EnableValue
        MAX-ACCESS    read-create
        STATUS        current
        DESCRIPTION   "ISIS PLSB IPv6 shortcut enabled"
        DEFVAL        { disable }
        ::= { rcIsisPlsbEntry 14 }

rcIsisPlsbMcastSpbPimGwControllerEnable OBJECT-TYPE
        SYNTAX        TruthValue
        MAX-ACCESS    read-create
        STATUS        current
        DESCRIPTION   "ISIS PLSB Multicast SPB PIM Gateway controller
                       enable/disable."
        DEFVAL        { false }
        ::= { rcIsisPlsbEntry 15 }

rcIsisPlsbMcastSpbPimGwGatewayEnable OBJECT-TYPE
        SYNTAX        TruthValue
        MAX-ACCESS    read-create
        STATUS        current
        DESCRIPTION   "ISIS PLSB Multicast SPB PIM Gateway enable/disable."
        DEFVAL        { false }
        ::= { rcIsisPlsbEntry 16 }

rcIsisPlsbStpMultiHoming OBJECT-TYPE
        SYNTAX        TruthValue
        MAX-ACCESS    read-create
        STATUS        current
        DESCRIPTION   "Fabric Multi-Homing is supported enable/disable."
        DEFVAL        { false }
        ::= { rcIsisPlsbEntry 17 }


rcIsisPlsbBVlanOrigin OBJECT-TYPE
        SYNTAX        INTEGER {
                          dynamic(1),
                          config(2)
                      }
        MAX-ACCESS    read-only
        STATUS        current
        DESCRIPTION   "Describes how rcIsisPlsbEntry was created:
        manual (SNMP/CLI), ZTF(Auto-Sense) or other."
        DEFVAL        { 1 }
        ::= { rcIsisPlsbEntry 18 }


-- BEGIN rcIsisCircuitPlsbTable --

IsisDefaultL1Metric ::= TEXTUAL-CONVENTION
        DISPLAY-HINT "d"
        STATUS current
        DESCRIPTION
            "Integer sub-range for default metric for single hop.
             ISO 10589 provides for 4 types of metric.  Only the
             'default' metric is used in practice."
        SYNTAX Integer32 (1..63)

IsisWideL1Metric ::= TEXTUAL-CONVENTION
        DISPLAY-HINT "d"
        STATUS current
        DESCRIPTION
            "Wide Metric for IS Neighbors.  ISO 10589 provides a
             6 bit metric.  Traffic Engineering extensions provide
             24 bit metrics."
        SYNTAX Integer32 (1..16777215)


rcIsisCircuitPlsbTable      OBJECT-TYPE
        SYNTAX          SEQUENCE OF RcIsisCircuitPlsbEntry
        MAX-ACCESS      not-accessible
        STATUS          current
        DESCRIPTION     "Table of IS-IS Circuit PLSB instance"
        ::= { rcIsis 5 }

rcIsisCircuitPlsbEntry OBJECT-TYPE
        SYNTAX          RcIsisCircuitPlsbEntry
        MAX-ACCESS      not-accessible
        STATUS          current
        DESCRIPTION     "An entry of rcIsisCircuitPlsb Table. A Entry in
                         table exists for each PLSB instance under a ISIS
                        circuit created"
        INDEX           { rcIsisCircuitPlsbIndex,
                         rcIsisCircuitPlsbId}
        ::= { rcIsisCircuitPlsbTable 1 }

RcIsisCircuitPlsbEntry   ::=
        SEQUENCE {
          rcIsisCircuitPlsbIndex      InterfaceIndexOrZero,
          rcIsisCircuitPlsbId         Integer32,
          rcIsisCircuitPlsbRowStatus  RowStatus,
          rcIsisCircuitPlsbState      EnableValue,
          rcIsisCircuitPlsbType       INTEGER,
          rcIsisCircuitPlsbL1Metric   IsisDefaultL1Metric,
	  rcIsisCircuitPlsbWideL1Metric   IsisWideL1Metric,
          rcIsisCircuitPlsbOperationalWideL1Metric IsisWideL1Metric,
          rcIsisCircuitPlsbOrigin     INTEGER
        }

rcIsisCircuitPlsbIndex   OBJECT-TYPE
        SYNTAX        InterfaceIndexOrZero
        MAX-ACCESS    not-accessible
        STATUS        current
        DESCRIPTION  "The identifier of this circuit, unique within the
                      Intermediate System.  This object follows
                      the index behavior.  This is for SNMP Indexing
                      purposes only and need not have any relation to
                      any protocol value."
        ::= { rcIsisCircuitPlsbEntry 1 }

rcIsisCircuitPlsbId OBJECT-TYPE
        SYNTAX          Integer32 (1..100)
        MAX-ACCESS      not-accessible
        STATUS          current
        DESCRIPTION
            "PLSB instance ID"
    ::= { rcIsisCircuitPlsbEntry 2 }

rcIsisCircuitPlsbRowStatus  OBJECT-TYPE
        SYNTAX 		RowStatus
        MAX-ACCESS 	read-create
        STATUS 		current
        DESCRIPTION
            "The state of the rcIsisCircuitPlsbEntry.  "
    ::= { rcIsisCircuitPlsbEntry 3 }

rcIsisCircuitPlsbState OBJECT-TYPE
        SYNTAX        EnableValue
        MAX-ACCESS    read-create
        STATUS        current
        DESCRIPTION   "PLSB functionality enable on this Plsb
                      instance at this port.
                      Disable value is not allowed to be set."
	DEFVAL        { enable }
        ::= { rcIsisCircuitPlsbEntry 4 }

rcIsisCircuitPlsbType    OBJECT-TYPE
        SYNTAX        INTEGER {
                          bcast(1),
                          ptpt(2)
                      }
        MAX-ACCESS    read-create
        STATUS        current
        DESCRIPTION   "ISIS circuit type this is an extention to
                       ISIS circuit table, this was required a
                       standard MIB circuit type does not support
                       passive type"
	    DEFVAL        { ptpt }
        ::= { rcIsisCircuitPlsbEntry 5 }

rcIsisCircuitPlsbL1Metric OBJECT-TYPE
        SYNTAX 		IsisDefaultL1Metric
        MAX-ACCESS 	read-create
        STATUS 		current
        DESCRIPTION
            "The metric value of this circuit for this level."
        REFERENCE "ISIS.aoi l1DefaultMetric (35)"
        DEFVAL { 10 }
    ::= { rcIsisCircuitPlsbEntry 6 }

rcIsisCircuitPlsbWideL1Metric OBJECT-TYPE
        SYNTAX 		IsisWideL1Metric
        MAX-ACCESS 	read-create
        STATUS 		current
        DESCRIPTION
            "The metric value of this circuit for this level."
        DEFVAL { 10 }
    ::= { rcIsisCircuitPlsbEntry 7 }

rcIsisCircuitPlsbOperationalWideL1Metric OBJECT-TYPE
        SYNTAX IsisWideL1Metric
        MAX-ACCESS read-only
        STATUS current
        DESCRIPTION
            " The negotiated metric value of this circuit for this level.
            In case of a metric mismatch between the Pt-to-Pt neighbor,
            the higher value will be used in path calculation."
    ::= { rcIsisCircuitPlsbEntry 8 }


rcIsisCircuitPlsbOrigin   OBJECT-TYPE
        SYNTAX INTEGER {
                   config(1),
                   autoSense(2)
                   }
        MAX-ACCESS read-only
        STATUS current
        DESCRIPTION
            "Describes how IsisCircPlsb was created: manual (CLI),
            dynamic (ZTF) or other."
    ::= { rcIsisCircuitPlsbEntry 9 }


-- ISIS PLSB Unicast FIB Table

rcIsisPlsbUnicastFibTable      OBJECT-TYPE
        SYNTAX          SEQUENCE OF RcIsisPlsbUnicastFibEntry
        MAX-ACCESS      not-accessible
        STATUS          current
        DESCRIPTION     "Table of IS-IS PLSB Unicast FIB"
        ::= { rcIsis 6 }

rcIsisPlsbUnicastFibEntry OBJECT-TYPE
        SYNTAX          RcIsisPlsbUnicastFibEntry
        MAX-ACCESS      not-accessible
        STATUS          current
        DESCRIPTION     "An entry of rcIsisPlsbUnicastFib Table. A Entry in
                         table exists for each PLSB unicast forwarding entry
                        generated by ISIS SPF computation"
        INDEX           { rcIsisPlsbUnicastFibDestinationMacAddr,
                         rcIsisPlsbUnicastFibVlan,
                         rcIsisPlsbUnicastFibSysId}

        ::= { rcIsisPlsbUnicastFibTable 1 }

RcIsisPlsbUnicastFibEntry   ::=
        SEQUENCE {
          rcIsisPlsbUnicastFibDestinationMacAddr      MacAddress,
          rcIsisPlsbUnicastFibVlan                    Integer32,
          rcIsisPlsbUnicastFibSysId                  OCTET STRING,
          rcIsisPlsbUnicastFibOutgoingPort            InterfaceIndex
        }

rcIsisPlsbUnicastFibDestinationMacAddr OBJECT-TYPE
        SYNTAX        MacAddress
        MAX-ACCESS    not-accessible
        STATUS        current
        DESCRIPTION   "Destination Mac Address of the unicast FIB entry "
        ::= { rcIsisPlsbUnicastFibEntry 1 }

rcIsisPlsbUnicastFibVlan OBJECT-TYPE
        SYNTAX        Integer32 (1..4094)
        MAX-ACCESS    not-accessible
        STATUS        current
        DESCRIPTION   "Vlan of the unicast FIB entry"
        ::= { rcIsisPlsbUnicastFibEntry 2 }

rcIsisPlsbUnicastFibSysId OBJECT-TYPE
        SYNTAX        OCTET STRING (SIZE (6))
        MAX-ACCESS    not-accessible
        STATUS        current
        DESCRIPTION   "System ID of the node where unicast FIB entry
                       come from"
        ::= { rcIsisPlsbUnicastFibEntry 3 }

rcIsisPlsbUnicastFibOutgoingPort  OBJECT-TYPE
        SYNTAX        InterfaceIndex
        MAX-ACCESS    read-only
        STATUS        current
        DESCRIPTION   "Outgoing port of the unicast Fib entry."
        ::= { rcIsisPlsbUnicastFibEntry 4 }

-- ISIS PLSB Multicast FIB Table

rcIsisPlsbMulticastFibTable      OBJECT-TYPE
        SYNTAX          SEQUENCE OF RcIsisPlsbMulticastFibEntry
        MAX-ACCESS      not-accessible
        STATUS          current
        DESCRIPTION     "Table of IS-IS PLSB Multicast FIB"
        ::= { rcIsis 7 }

rcIsisPlsbMulticastFibEntry OBJECT-TYPE
        SYNTAX          RcIsisPlsbMulticastFibEntry
        MAX-ACCESS      not-accessible
        STATUS          current
        DESCRIPTION     "An entry of rcIsisPlsbmulticastFib Table. A Entry in
                         table exists for each PLSB Multicast forwarding entry
                        generated by ISIS SPF computation"
        INDEX           { rcIsisPlsbMulticastFibMcastDestMacAddr,
                          rcIsisPlsbMulticastFibVlan,
			  rcIsisPlsbMulticastFibSysId}
        ::= { rcIsisPlsbMulticastFibTable 1 }

RcIsisPlsbMulticastFibEntry   ::=
        SEQUENCE {
          rcIsisPlsbMulticastFibMcastDestMacAddr      MacAddress,
	  rcIsisPlsbMulticastFibVlan                  Integer32,
	  rcIsisPlsbMulticastFibSysId                 OCTET STRING,
          rcIsisPlsbMulticastFibIsid                  Integer32,
          rcIsisPlsbMulticastFibOutgoingPorts         DisplayString
	  }

rcIsisPlsbMulticastFibMcastDestMacAddr OBJECT-TYPE
        SYNTAX        MacAddress
        MAX-ACCESS    not-accessible
        STATUS        current
        DESCRIPTION   "Multicast destination Mac Address of the
                       multicast FIB entry "
        ::= { rcIsisPlsbMulticastFibEntry 1 }

rcIsisPlsbMulticastFibVlan OBJECT-TYPE
        SYNTAX        Integer32 (1..4094)
        MAX-ACCESS    not-accessible
        STATUS        current
        DESCRIPTION   "Vlan of the multicast FIB entry"
        ::= { rcIsisPlsbMulticastFibEntry 2 }

rcIsisPlsbMulticastFibSysId OBJECT-TYPE
        SYNTAX        OCTET STRING (SIZE (6))
        MAX-ACCESS    not-accessible
        STATUS        current
        DESCRIPTION   "System ID of the node where multicast FIB entry
                       come from"
        ::= { rcIsisPlsbMulticastFibEntry 3 }

rcIsisPlsbMulticastFibIsid OBJECT-TYPE
        SYNTAX        Integer32 (1..16777215)
        MAX-ACCESS    read-only
        STATUS        current
        DESCRIPTION   "Isid id of the multicast FIB entry"
        ::= { rcIsisPlsbMulticastFibEntry 4 }

rcIsisPlsbMulticastFibOutgoingPorts  OBJECT-TYPE
        SYNTAX        DisplayString
        MAX-ACCESS    read-only
        STATUS        current
        DESCRIPTION   "Nni port of the multicast Fib entry."
        ::= { rcIsisPlsbMulticastFibEntry 5 }

-- ISIS PLSB ISID Table

rcIsisPlsbIsidTable     OBJECT-TYPE
        SYNTAX          SEQUENCE OF RcIsisPlsbIsidEntry
        MAX-ACCESS      not-accessible
        STATUS          current
        DESCRIPTION     "Table of IS-IS PLSB ISID"
        ::= { rcIsis 8 }

rcIsisPlsbIsidEntry OBJECT-TYPE
        SYNTAX          RcIsisPlsbIsidEntry
        MAX-ACCESS      not-accessible
        STATUS          current
        DESCRIPTION     "An entry of rcIsisPlsbIsid Table. A Entry in
                         table exists for each PLSB i-sid configed or discovered
                        by IS-IS "
        INDEX           { rcIsisPlsbIsidSourceName,
                          rcIsisPlsbIsidId,
			  rcIsisPlsbIsidSysId}
        ::= { rcIsisPlsbIsidTable 1 }

RcIsisPlsbIsidEntry   ::=
        SEQUENCE {
          rcIsisPlsbIsidSourceName                    Integer32,
          rcIsisPlsbIsidId                            Integer32,
	  rcIsisPlsbIsidSysId                         OCTET STRING,
          rcIsisPlsbIsidType                          INTEGER
        }

rcIsisPlsbIsidSourceName OBJECT-TYPE
        SYNTAX        Integer32 (1..16777215)
        MAX-ACCESS    not-accessible
        STATUS        current
        DESCRIPTION   "nick name of node where this i-sid got
                       configed or discovered"
        ::= { rcIsisPlsbIsidEntry 1 }

rcIsisPlsbIsidId OBJECT-TYPE
        SYNTAX        Integer32 (1..16777215)
        MAX-ACCESS    not-accessible
        STATUS        current
        DESCRIPTION   "IS-IS PLSB Isid id"
        ::= { rcIsisPlsbIsidEntry 2 }

rcIsisPlsbIsidSysId OBJECT-TYPE
        SYNTAX        OCTET STRING (SIZE (6))
        MAX-ACCESS    not-accessible
        STATUS        current
        DESCRIPTION   "System ID of the node where multicast FIB entry
                       come from"
        ::= { rcIsisPlsbIsidEntry 3 }

rcIsisPlsbIsidType OBJECT-TYPE
        SYNTAX	      INTEGER {
			  config(1),
			  discover(2)
                      }
        MAX-ACCESS    read-only
        STATUS        current
        DESCRIPTION   "PLSB i-sid type"
        ::= { rcIsisPlsbIsidEntry 4 }


rcIsisTrap OBJECT IDENTIFIER ::= { rcIsis 9 }

rcIsisLocalLspId OBJECT-TYPE
        SYNTAX DisplayString(SIZE (17))
        MAX-ACCESS read-only
        STATUS current
        DESCRIPTION
            "The 8 byte Local LSP ID, consisting of the SystemID,
             Circuit ID, and Fragment Number."
    ::= { rcIsisTrap 1 }

rcIsisLocall1Metric OBJECT-TYPE
        SYNTAX IsisDefaultL1Metric
        MAX-ACCESS read-only
        STATUS current
        DESCRIPTION
            "l1-metric for ISIS interface on local Node."
    ::= { rcIsisTrap 2 }

rcIsisNgbLspId  OBJECT-TYPE
        SYNTAX DisplayString(SIZE (17))
        MAX-ACCESS read-only
        STATUS current
        DESCRIPTION
            "The 8 byte neighbor LSP ID, consisting of the SystemID,
             Circuit ID, and Fragment Number."
    ::= { rcIsisTrap 3 }

rcIsisNgbl1Metric OBJECT-TYPE
        SYNTAX IsisDefaultL1Metric
        MAX-ACCESS read-only
        STATUS current
        DESCRIPTION
            "l1-metric for ISIS interface on neighbor Node."
    ::= { rcIsisTrap 4 }

rcIsisPlsbTrapType OBJECT-TYPE
        SYNTAX	        INTEGER {
			   metricMismatch(1),
			   duplicateSysid(2),
			   lsdbUpdate(3),
                           duplicateNickname(4),
                           bvidMismatch(5),
                           smltVirtBmacMismatch(6),
                           smltPeerBmacMismatch(7),
                           adjState(8),
                           smltSplitBebMismatch(9),
                           multiLinkAdj(10),
                           smltVirtBmacMisconfigSysid(11),
                           smltVirtBmacMisconfigMac(12),
			   globalDuplicateSystemId(13),
                           localDuplicateNickname(14),
                           globalDuplicateNickname(15),
                           isisEnabledWithZeroNickname(16)
			}
	MAX-ACCESS	read-only
	STATUS		current
	DESCRIPTION	""
	::= {rcIsisTrap 5}

rcIsisLocalSysId OBJECT-TYPE
        SYNTAX DisplayString(SIZE (14))
        MAX-ACCESS read-only
        STATUS current
        DESCRIPTION
            "ISIS local node system-id."
    ::= { rcIsisTrap 6 }

rcIsisLocalInterface OBJECT-TYPE
        SYNTAX Integer32
        MAX-ACCESS read-only
        STATUS current
        DESCRIPTION
            "ISIS local interface index."
    ::= { rcIsisTrap 7 }

rcIsisTrapIndicator OBJECT-TYPE
        SYNTAX INTEGER {
			alarm(1),
			clear(2)
  		    }
        MAX-ACCESS read-only
        STATUS current
        DESCRIPTION "indicates that an alarm has been
                Raised, or an alarm has been cleared."
::= { rcIsisTrap 8 }

rcIsisLocalNickname OBJECT-TYPE
        SYNTAX DisplayString(SIZE (7))
        MAX-ACCESS read-only
        STATUS current
        DESCRIPTION
            "ISIS local node nick-name."
    ::= { rcIsisTrap 9 }

rcIsisNgbNickname OBJECT-TYPE
        SYNTAX DisplayString(SIZE (7))
        MAX-ACCESS read-only
        STATUS current
        DESCRIPTION
            "ISIS neighbor node nick-name."
    ::= { rcIsisTrap 10 }

rcIsisNgbSysId  OBJECT-TYPE
        SYNTAX DisplayString(SIZE (14))
        MAX-ACCESS read-only
        STATUS current
        DESCRIPTION
            "ISIS neighbor node system-id."
    ::= { rcIsisTrap 11 }

rcIsisLocalPrimaryBvid OBJECT-TYPE
	SYNTAX     IsisPlsbBvid
        MAX-ACCESS read-only
        STATUS current
        DESCRIPTION
            "ISIS local primary B-VID."
    ::= { rcIsisTrap 12 }

rcIsisLocalPrimaryTieBrkAlg OBJECT-TYPE
	SYNTAX  IsisPlsbBvidTieBrkAlg
        MAX-ACCESS read-only
        STATUS current
        DESCRIPTION
            "The tie breaking algorithm applied to local primary B-VID."
    ::= { rcIsisTrap 13 }

rcIsisLocalSecondaryBvid OBJECT-TYPE
	SYNTAX     IsisPlsbBvid
        MAX-ACCESS read-only
        STATUS current
        DESCRIPTION
            "ISIS local secondary B-VID."
    ::= { rcIsisTrap 14 }

rcIsisLocalSecondaryTieBrkAlg OBJECT-TYPE
	SYNTAX  IsisPlsbBvidTieBrkAlg
        MAX-ACCESS read-only
        STATUS current
        DESCRIPTION
            "The tie breaking algorithm applied to local seconday B-VID."
    ::= { rcIsisTrap 15 }

rcIsisNgbPrimaryBvid OBJECT-TYPE
	SYNTAX     IsisPlsbBvid
        MAX-ACCESS read-only
        STATUS current
        DESCRIPTION
            "ISIS neighbor primary B-VID."
    ::= { rcIsisTrap 16 }

rcIsisNgbPrimaryTieBrkAlg OBJECT-TYPE
	SYNTAX  IsisPlsbBvidTieBrkAlg
        MAX-ACCESS read-only
        STATUS current
        DESCRIPTION
            "The neighbor tie breaking algorithm applied to primary B-VID."
    ::= { rcIsisTrap 17 }

rcIsisNgbSecondaryBvid  OBJECT-TYPE
	SYNTAX     IsisPlsbBvid
        MAX-ACCESS read-only
        STATUS current
        DESCRIPTION
            "ISIS neighbor secondary B-VID."
    ::= { rcIsisTrap 18 }

rcIsisNgbSecondaryTieBrkAlg OBJECT-TYPE
	SYNTAX  IsisPlsbBvidTieBrkAlg
        MAX-ACCESS read-only
        STATUS current
        DESCRIPTION
            "The neighbor tie breaking algorithm applied to secondary B-VID."
    ::= { rcIsisTrap 19 }

rcIsisLocalVirtualBmac OBJECT-TYPE
	SYNTAX MacAddress
        MAX-ACCESS read-only
        STATUS current
        DESCRIPTION
            "The SMLT Virtual BMAC configured in the local IST switch."
    ::= { rcIsisTrap 20 }


rcIsisPeerVirtualBmac OBJECT-TYPE
	SYNTAX MacAddress
        MAX-ACCESS read-only
        STATUS current
        DESCRIPTION
            "The SMLT Virtual BMAC configured in the IST Peer."
    ::= { rcIsisTrap 21 }

rcIsisSysId OBJECT-TYPE
	SYNTAX DisplayString(SIZE (14))
        MAX-ACCESS read-only
        STATUS current
        DESCRIPTION
            "The isis system id configured in the local switch or IST peer."
    ::= { rcIsisTrap 22 }

rcIsisSmltPeerSysId OBJECT-TYPE
	SYNTAX DisplayString(SIZE (14))
        MAX-ACCESS read-only
        STATUS current
        DESCRIPTION
            "The SMLT Peer system-id configured in the local switch or IST Peer."
    ::= { rcIsisTrap 23 }

rcIsisAdjState OBJECT-TYPE
        SYNTAX INTEGER  {
			init(2),
                        up(3),
                        down(4)
  		    }
        MAX-ACCESS read-only
        STATUS current
        DESCRIPTION "indicate different ISIS adjacency states."
::= { rcIsisTrap 24 }

rcIsisDuplicateNnameCounter OBJECT-TYPE
        SYNTAX Integer32
        MAX-ACCESS read-only
        STATUS current
        DESCRIPTION "indicate how many nodes in the network share the nick-name."
::= { rcIsisTrap 25 }

rcIsisLocalBvidCounter OBJECT-TYPE
        SYNTAX Integer32
        MAX-ACCESS read-only
        STATUS current
        DESCRIPTION "indicate how many b-vid configured on local nodes."
::= { rcIsisTrap 26 }

rcIsisNgbBvidCounter OBJECT-TYPE
        SYNTAX Integer32
        MAX-ACCESS read-only
        STATUS current
        DESCRIPTION "indicate how many b-vid configured on a neighbor nodes."
::= { rcIsisTrap 27 }

rcIsisLocalSmltSplitBeb OBJECT-TYPE
        SYNTAX     INTEGER {
                          primary(1),
                          secondary(2)
		     }
        MAX-ACCESS read-only
        STATUS current
        DESCRIPTION
            "The SMLT Split-BEB configured in the local IST switch."
    ::= { rcIsisTrap 28 }

rcIsisPeerSmltSplitBeb OBJECT-TYPE
        SYNTAX     INTEGER {
                          primary(1),
                          secondary(2)
		     }
        MAX-ACCESS read-only
        STATUS current
        DESCRIPTION
            "The SMLT Split-BEB configured in the IST Peer switch."
    ::= { rcIsisTrap 29 }

rcIsisLocalHostName OBJECT-TYPE
        SYNTAX     OCTET STRING (SIZE (0..255))
        MAX-ACCESS read-only
        STATUS     current
        DESCRIPTION
            "ISIS local host name."
        ::= { rcIsisTrap 30 }

rcIsisNgbHostName OBJECT-TYPE
        SYNTAX     OCTET STRING (SIZE (0..255))
        MAX-ACCESS read-only
        STATUS     current
        DESCRIPTION
            "ISIS neighbor host name."
        ::= { rcIsisTrap 31 }

rcIsisPrevInterface OBJECT-TYPE
        SYNTAX Integer32
        MAX-ACCESS read-only
        STATUS current
        DESCRIPTION
            "ISIS local interface index for previously found adj."
    ::= { rcIsisTrap 32 }

rcIsisSmltVirtBmacMisconfigNodeHostName OBJECT-TYPE
        SYNTAX     OCTET STRING (SIZE (0..255))
        MAX-ACCESS accessible-for-notify
        STATUS     current
        DESCRIPTION
            "ISIS host name of node that misconfigured SMLT virtual BMAC."
    ::= { rcIsisTrap 33}

rcIsisSmltVirtBmacMisconfigNodeSysId  OBJECT-TYPE
        SYNTAX DisplayString(SIZE (14))
        MAX-ACCESS accessible-for-notify
        STATUS current
        DESCRIPTION
            "ISIS system-id of node that misconfigured SMLT virtual BMAC."
    ::= { rcIsisTrap 34 }

rcIsisLocalChassisMac  OBJECT-TYPE
        SYNTAX      MacAddress
        MAX-ACCESS  accessible-for-notify
        STATUS      current
        DESCRIPTION "ISIS local node chassis mac"
    ::= { rcIsisTrap 35 }

rcIsisRemoteChassisMac  OBJECT-TYPE
        SYNTAX      MacAddress
        MAX-ACCESS  accessible-for-notify
        STATUS      current
        DESCRIPTION "Chassis MAC address of the remote ISIS node."
    ::= { rcIsisTrap 36 }

rcIsisRemoteHostName  OBJECT-TYPE
        SYNTAX      OCTET STRING (SIZE(0..255))
        MAX-ACCESS  accessible-for-notify
        STATUS      current
        DESCRIPTION "ISIS host name of the remote node."
    ::= { rcIsisTrap 37 }

rcIsisPreviousSysId OBJECT-TYPE
        SYNTAX DisplayString(SIZE (14))
        MAX-ACCESS accessible-for-notify
        STATUS current
        DESCRIPTION
            "Previously used ISIS System-Id."
    ::= { rcIsisTrap 38 }

-- BEGIN rcIsisAdjTable --

rcIsisAdjTable      OBJECT-TYPE
        SYNTAX          SEQUENCE OF RcIsisAdjEntry
        MAX-ACCESS      not-accessible
        STATUS          current
        DESCRIPTION     "Table of IS-IS Adjacency, this is extension
                         to the isisISAdjTable defined in ISIS MIB"
        ::= { rcIsis 10 }

rcIsisAdjEntry OBJECT-TYPE
        SYNTAX          RcIsisAdjEntry
        MAX-ACCESS      not-accessible
        STATUS          current
        DESCRIPTION     "An entry of rcIsisAdj Table. A Entry in
                         table exists for each ISIS adjacency"
        INDEX           {rcIsisAdjCircIndex,
                         rcIsisAdjIndex }
        ::= { rcIsisAdjTable 1 }

RcIsisAdjEntry   ::=
        SEQUENCE {
          rcIsisAdjCircIndex        Integer32,
          rcIsisAdjIndex            Unsigned32,
          rcIsisAdjHostName         OCTET STRING,
          rcIsisAdjIfIndex          InterfaceIndex,
          rcIsisAdjParallelActive   TruthValue
        }

rcIsisAdjCircIndex   OBJECT-TYPE
        SYNTAX        Integer32
        MAX-ACCESS    not-accessible
        STATUS        current
        DESCRIPTION  "The identifier of this circuit, unique within the
                      Intermediate System.  This object follows
                      the index behavior.  This is for SNMP Indexing
                      purposes only and need not have any relation to
                      any protocol value."
        ::= { rcIsisAdjEntry 1 }

rcIsisAdjIndex OBJECT-TYPE
        SYNTAX Unsigned32(1..4294967295)
        MAX-ACCESS not-accessible
        STATUS current
        DESCRIPTION
            "A unique value identifying the IS adjacency from all
             other such adjacencies on this circuit. This value is
             automatically assigned by the system when the adjacency
             is created."
    ::= { rcIsisAdjEntry 2 }

rcIsisAdjHostName OBJECT-TYPE
        SYNTAX     OCTET STRING (SIZE (0..255))
        MAX-ACCESS read-only
        STATUS     current
        DESCRIPTION
            "The hostname listed in LSP, or the system name if host
             name is not configured."
        ::= { rcIsisAdjEntry 3 }

rcIsisAdjIfIndex OBJECT-TYPE
        SYNTAX InterfaceIndex
        MAX-ACCESS read-only
        STATUS current
        DESCRIPTION
            "The value of ifIndex for the interface to which this
             circuit corresponds."
    ::= { rcIsisAdjEntry 4 }

rcIsisAdjParallelActive OBJECT-TYPE
        SYNTAX TruthValue
        MAX-ACCESS read-only
        STATUS current
        DESCRIPTION
            "A flag to indicate current adjacency is active or not
             among all the parallel adjacencies between two nodes."
    ::= { rcIsisAdjEntry 5 }

-- BEGIN rcIsisLSPTable --

rcIsisLSPTable      OBJECT-TYPE
        SYNTAX          SEQUENCE OF RcIsisLSPEntry
        MAX-ACCESS      not-accessible
        STATUS          current
        DESCRIPTION     "Table of IS-IS LSP, this is extension
                         to the isisLSPSummaryTable defined in ISIS MIB"
        ::= { rcIsis 11 }

rcIsisLSPEntry OBJECT-TYPE
        SYNTAX          RcIsisLSPEntry
        MAX-ACCESS      not-accessible
        STATUS          current
        DESCRIPTION     "An entry of rcIsisLSP Table. A Entry in
                         table exists for each ISIS LSP"
        INDEX           {rcIsisLSPLevel,
                         rcIsisLSPID }
        ::= { rcIsisLSPTable 1 }

RcIsisLSPEntry   ::=
        SEQUENCE {
          rcIsisLSPLevel            INTEGER,
          rcIsisLSPID               OCTET STRING,
          rcIsisLSPSeq              Unsigned32,
          rcIsisLSPHostName         OCTET STRING,
          rcIsisLSPNickName         Integer32,
          rcIsisLSPLifetimeRemain   Unsigned32,
          rcIsisLSPSmltBmac         MacAddress
        }

rcIsisLSPLevel OBJECT-TYPE
        SYNTAX INTEGER {
                area(1),        -- L1
                domain(2)       -- L2
        }
        MAX-ACCESS not-accessible
        STATUS current
        DESCRIPTION
            "At which level does this LSP appear?"
    ::= { rcIsisLSPEntry 1 }

rcIsisLSPID OBJECT-TYPE
        SYNTAX OCTET STRING (SIZE (8))
        MAX-ACCESS not-accessible
        STATUS current
        DESCRIPTION
            "The 8 byte LSP ID, consisting of the SystemID,
             Circuit ID, and Fragment Number."
    ::= { rcIsisLSPEntry 2 }

rcIsisLSPSeq OBJECT-TYPE
        SYNTAX Unsigned32
        MAX-ACCESS read-only
        STATUS current
        DESCRIPTION
            "The sequence number for this LSP."
    ::= { rcIsisLSPEntry 3 }

rcIsisLSPHostName OBJECT-TYPE
        SYNTAX     OCTET STRING (SIZE (0..255))
        MAX-ACCESS read-only
        STATUS     current
        DESCRIPTION
            "The hostname listed in LSP, or the system name if host
             name is not configured."
        ::= { rcIsisLSPEntry 4 }

rcIsisLSPNickName OBJECT-TYPE
        SYNTAX Integer32 (1..16777215)
        MAX-ACCESS read-only
        STATUS current
        DESCRIPTION
            "PLSB node's nickname"
    ::= { rcIsisLSPEntry 5 }

rcIsisLSPLifetimeRemain OBJECT-TYPE
        SYNTAX Unsigned32
        UNITS "seconds"
        MAX-ACCESS read-only
        STATUS current
        DESCRIPTION
            "The remaining lifetime in seconds for this LSP."
    ::= { rcIsisLSPEntry 6 }

rcIsisLSPSmltBmac OBJECT-TYPE
        SYNTAX        MacAddress
        MAX-ACCESS    read-only
        STATUS        current
        DESCRIPTION   "SPBM node's SMLT virtual BMAC"
        ::= { rcIsisLSPEntry 7 }

-- ISIS PLSB IP Unicast FIB Table
rcIsisPlsbIpUnicastFibTable      OBJECT-TYPE
        SYNTAX          SEQUENCE OF RcIsisPlsbIpUnicastFibEntry
        MAX-ACCESS      not-accessible
        STATUS          current
        DESCRIPTION     "Table of IS-IS PLSB IP Unicast FIB"
        ::= { rcIsis 12 }

rcIsisPlsbIpUnicastFibEntry OBJECT-TYPE
        SYNTAX          RcIsisPlsbIpUnicastFibEntry
        MAX-ACCESS      not-accessible
        STATUS          current
        DESCRIPTION     "An entry of rcIsisPlsbIpUnicastFib Table. A Entry in
                         table exists for each PLSB IP unicast forwarding entry."
        INDEX           { rcIsisPlsbIpUnicastFibVrfId,
			  rcIsisPlsbIpUnicastFibDestinationIpAddrType,
			  rcIsisPlsbIpUnicastFibDestinationIpAddr,
                          rcIsisPlsbIpUnicastFibDestinationMask,
                          rcIsisPlsbIpUnicastFibNextHopBmac,
                          rcIsisPlsbIpUnicastFibVlan }
        ::= { rcIsisPlsbIpUnicastFibTable 1 }

RcIsisPlsbIpUnicastFibEntry   ::=
        SEQUENCE {
	  rcIsisPlsbIpUnicastFibVrfId                   Integer32,
          rcIsisPlsbIpUnicastFibDestinationIpAddrType   InetAddressType,
          rcIsisPlsbIpUnicastFibDestinationIpAddr       InetAddress,
	  rcIsisPlsbIpUnicastFibDestinationMask         InetAddressPrefixLength,
          rcIsisPlsbIpUnicastFibNextHopBmac             MacAddress,
          rcIsisPlsbIpUnicastFibVlan                    Integer32,
          rcIsisPlsbIpUnicastFibIsid                    Integer32,
          rcIsisPlsbIpUnicastFibNextHopName             DisplayString,
          rcIsisPlsbIpUnicastFibOutgoingPort            InterfaceIndex,
          rcIsisPlsbIpUnicastFibPrefixCost              Integer32,
          rcIsisPlsbIpUnicastFibSpbmCost                Counter64
        }

rcIsisPlsbIpUnicastFibVrfId OBJECT-TYPE
        SYNTAX        Integer32
        MAX-ACCESS    not-accessible
        STATUS        current
        DESCRIPTION   "VRF ID of the IP unicast FIB entry, 0 indicates NRE."
        ::= { rcIsisPlsbIpUnicastFibEntry 1 }

rcIsisPlsbIpUnicastFibDestinationIpAddrType OBJECT-TYPE
        SYNTAX        InetAddressType
        MAX-ACCESS    not-accessible
        STATUS        current
        DESCRIPTION   "The address type of destination IP Address."
        ::= { rcIsisPlsbIpUnicastFibEntry 2 }

rcIsisPlsbIpUnicastFibDestinationIpAddr OBJECT-TYPE
        SYNTAX        InetAddress (SIZE(4|16))
        MAX-ACCESS    not-accessible
        STATUS        current
        DESCRIPTION   "Destination IP Address of the IP unicast FIB entry.
		       Support ipv4 size(4) and ipv6 size(16)"
        ::= { rcIsisPlsbIpUnicastFibEntry 3 }

rcIsisPlsbIpUnicastFibDestinationMask OBJECT-TYPE
        SYNTAX        InetAddressPrefixLength
        MAX-ACCESS    not-accessible
        STATUS        current
        DESCRIPTION   "Destination IP mask of the IP unicast FIB entry "
        ::= { rcIsisPlsbIpUnicastFibEntry 4 }

rcIsisPlsbIpUnicastFibNextHopBmac OBJECT-TYPE
        SYNTAX        MacAddress
        MAX-ACCESS    not-accessible
        STATUS        current
        DESCRIPTION   "the nexthop BMAC of the IP unicast FIB entry "
        ::= { rcIsisPlsbIpUnicastFibEntry 5 }

rcIsisPlsbIpUnicastFibVlan OBJECT-TYPE
        SYNTAX        Integer32 (1..4094)
        MAX-ACCESS    not-accessible
        STATUS        current
        DESCRIPTION   "Vlan of the IP unicast FIB entry"
        ::= { rcIsisPlsbIpUnicastFibEntry 6 }

rcIsisPlsbIpUnicastFibIsid OBJECT-TYPE
        SYNTAX        Integer32
        MAX-ACCESS    read-only
        STATUS        current
        DESCRIPTION   "ISID of the IP unicast FIB entry"
        ::= { rcIsisPlsbIpUnicastFibEntry 7 }

rcIsisPlsbIpUnicastFibNextHopName OBJECT-TYPE
        SYNTAX        DisplayString
        MAX-ACCESS    read-only
        STATUS        current
        DESCRIPTION   "the nexthop hostname of the IP unicast FIB entry "
        ::= { rcIsisPlsbIpUnicastFibEntry 8 }

rcIsisPlsbIpUnicastFibOutgoingPort  OBJECT-TYPE
        SYNTAX        InterfaceIndex
        MAX-ACCESS    read-only
        STATUS        current
        DESCRIPTION   "Outgoing port of the IP unicast Fib entry."
        ::= { rcIsisPlsbIpUnicastFibEntry 9 }

rcIsisPlsbIpUnicastFibPrefixCost OBJECT-TYPE
        SYNTAX        Integer32
        MAX-ACCESS    read-only
        STATUS        current
        DESCRIPTION   "prefix cost of the IP unicast FIB entry"
        ::= { rcIsisPlsbIpUnicastFibEntry 10 }

rcIsisPlsbIpUnicastFibSpbmCost  OBJECT-TYPE
        SYNTAX        Counter64
        MAX-ACCESS    read-only
        STATUS        current
        DESCRIPTION   "bmac cost of the IP unicast FIB entry"
        ::= { rcIsisPlsbIpUnicastFibEntry 11 }

-- ISIS PLSB Unicast FIB Table
rcIsisPlsbUcastFibTable      OBJECT-TYPE
        SYNTAX          SEQUENCE OF RcIsisPlsbUcastFibEntry
        MAX-ACCESS      not-accessible
        STATUS          current
        DESCRIPTION     "Table of IS-IS PLSB Unicast FIB"
        ::= { rcIsis 13 }

rcIsisPlsbUcastFibEntry OBJECT-TYPE
        SYNTAX          RcIsisPlsbUcastFibEntry
        MAX-ACCESS      not-accessible
        STATUS          current
        DESCRIPTION    	"An entry of rcIsisPlsbUcastFib Table. A Entry in
                        table exists for each PLSB unicast forwarding entry
                       	generated by ISIS SPF computation"
        INDEX           { rcIsisPlsbUcastFibSysId,
		          rcIsisPlsbUcastFibVlan,
		          rcIsisPlsbUcastFibDestinationMacAddr}
        ::= { rcIsisPlsbUcastFibTable 1 }

RcIsisPlsbUcastFibEntry   ::=
        SEQUENCE {
          rcIsisPlsbUcastFibSysId                   	OCTET STRING,
          rcIsisPlsbUcastFibVlan                    	Integer32,
          rcIsisPlsbUcastFibDestinationMacAddr          MacAddress,
          rcIsisPlsbUcastFibOutgoingPort            	InterfaceIndex,
          rcIsisPlsbUcastFibHostName                   	OCTET STRING,
	  rcIsisPlsbUcastFibCost                        Counter64
        }

rcIsisPlsbUcastFibSysId OBJECT-TYPE
        SYNTAX        OCTET STRING (SIZE (6))
        MAX-ACCESS    not-accessible
        STATUS        current
        DESCRIPTION   "System ID of the node where unicast FIB entry
                       come from"
        ::= { rcIsisPlsbUcastFibEntry 1 }

rcIsisPlsbUcastFibVlan OBJECT-TYPE
        SYNTAX        Integer32 (1..4094)
        MAX-ACCESS    not-accessible
        STATUS        current
        DESCRIPTION   "Vlan of the unicast FIB entry"
        ::= { rcIsisPlsbUcastFibEntry 2 }

rcIsisPlsbUcastFibDestinationMacAddr OBJECT-TYPE
        SYNTAX        MacAddress
        MAX-ACCESS    not-accessible
        STATUS        current
        DESCRIPTION   "Destination Mac Address of the unicast FIB entry "
        ::= { rcIsisPlsbUcastFibEntry 3 }

rcIsisPlsbUcastFibOutgoingPort  OBJECT-TYPE
        SYNTAX        InterfaceIndex
        MAX-ACCESS    read-only
        STATUS        current
        DESCRIPTION   "Outgoing port of the unicast Fib entry."
        ::= { rcIsisPlsbUcastFibEntry 4 }

rcIsisPlsbUcastFibHostName  OBJECT-TYPE
        SYNTAX        OCTET STRING (SIZE (0..255))
        MAX-ACCESS    read-only
        STATUS        current
        DESCRIPTION   "Host name of the node where unicast FIB entry
                       come from"
        ::= { rcIsisPlsbUcastFibEntry 5 }

rcIsisPlsbUcastFibCost  OBJECT-TYPE
        SYNTAX        Counter64
        MAX-ACCESS    read-only
        STATUS        current
        DESCRIPTION   "unicast FIB cost"
        ::= { rcIsisPlsbUcastFibEntry 6 }

-- ISIS PLSB Multicast FIB Table

rcIsisPlsbMcastFibTable      OBJECT-TYPE
        SYNTAX          SEQUENCE OF RcIsisPlsbMcastFibEntry
        MAX-ACCESS     	not-accessible
        STATUS         	current
        DESCRIPTION     "Table of IS-IS PLSB Multicast FIB"
        ::= { rcIsis 14 }

rcIsisPlsbMcastFibEntry OBJECT-TYPE
        SYNTAX         	RcIsisPlsbMcastFibEntry
        MAX-ACCESS      not-accessible
        STATUS         	current
        DESCRIPTION     "An entry of rcIsisPlsbMcastFib Table. A Entry in
                        table exists for each PLSB Multicast forwarding entry
                        generated by ISIS SPF computation"
        INDEX           { rcIsisPlsbMcastFibSysId,
		          rcIsisPlsbMcastFibVlan,
		          rcIsisPlsbMcastFibMcastDestMacAddr
		        }
        ::= { rcIsisPlsbMcastFibTable 1 }

RcIsisPlsbMcastFibEntry   ::=
        SEQUENCE {
          rcIsisPlsbMcastFibSysId                 	OCTET STRING,
          rcIsisPlsbMcastFibVlan                  	Integer32,
          rcIsisPlsbMcastFibMcastDestMacAddr            MacAddress,
          rcIsisPlsbMcastFibIsid                        Integer32,
          rcIsisPlsbMcastFibNickName                    Integer32,
          rcIsisPlsbMcastFibType                        INTEGER,
          rcIsisPlsbMcastFibOutgoingPorts         	DisplayString,
          rcIsisPlsbMcastFibHostName                   	OCTET STRING,
	  rcIsisPlsbMcastFibOutgoingInterfacePorts      PortSet,
	  rcIsisPlsbMcastFibOutgoingInterfaceMlts       OCTET STRING,
	  rcIsisPlsbMcastFibIncomingInterface           InterfaceIndex,
          rcIsisPlsbMcastFibIsidName                    DisplayString
        }

rcIsisPlsbMcastFibSysId OBJECT-TYPE
        SYNTAX        OCTET STRING (SIZE (6))
        MAX-ACCESS    not-accessible
        STATUS        current
        DESCRIPTION   "System ID of the node where multicast FIB entry
                       come from"
        ::= { rcIsisPlsbMcastFibEntry 1 }

rcIsisPlsbMcastFibVlan OBJECT-TYPE
        SYNTAX        Integer32 (1..4094)
        MAX-ACCESS    not-accessible
        STATUS        current
        DESCRIPTION   "Vlan of the multicast FIB entry"
        ::= { rcIsisPlsbMcastFibEntry 2 }

rcIsisPlsbMcastFibMcastDestMacAddr OBJECT-TYPE
        SYNTAX        MacAddress
        MAX-ACCESS    not-accessible
        STATUS        current
        DESCRIPTION   "Multicast destination Mac Address of the
                       multicast FIB entry "
        ::= { rcIsisPlsbMcastFibEntry 3 }

rcIsisPlsbMcastFibIsid OBJECT-TYPE
        SYNTAX        Integer32 (1..16777215)
        MAX-ACCESS    read-only
        STATUS        current
        DESCRIPTION   "Isid id of the multicast FIB entry"
        ::= { rcIsisPlsbMcastFibEntry 4 }

rcIsisPlsbMcastFibNickName OBJECT-TYPE
        SYNTAX        Integer32 (1..16777215)
        MAX-ACCESS    read-only
        STATUS        current
        DESCRIPTION   "nick name of node where this i-sid got
                       configured or discovered"
        ::= { rcIsisPlsbMcastFibEntry 5 }

rcIsisPlsbMcastFibType OBJECT-TYPE
        SYNTAX	      INTEGER {
			  config(1),
			  discover(2)
                      }
        MAX-ACCESS    read-only
        STATUS        current
        DESCRIPTION   "PLSB i-sid type"
        ::= { rcIsisPlsbMcastFibEntry 6 }

rcIsisPlsbMcastFibOutgoingPorts  OBJECT-TYPE
        SYNTAX        DisplayString
        MAX-ACCESS    read-only
        STATUS        obsolete
        DESCRIPTION   "Nni port of the multicast Fib entry. This attribute is
	               obsoleted. New attributes rcIsisPlsbMcastFibOutgoingInterfacePorts
		       and rcIsisPlsbMcastFibOutgoingInterfaceMlts are added for outgoing
		       interfaces"
        ::= { rcIsisPlsbMcastFibEntry 7 }

rcIsisPlsbMcastFibHostName  OBJECT-TYPE
        SYNTAX        OCTET STRING (SIZE (0..255))
        MAX-ACCESS    read-only
        STATUS        current
        DESCRIPTION   "Host name of the node where multicast FIB entry
                       come from"
        ::= { rcIsisPlsbMcastFibEntry 8 }

rcIsisPlsbMcastFibOutgoingInterfacePorts OBJECT-TYPE
    	SYNTAX 	      PortSet
	MAX-ACCESS    read-only
	STATUS	      current
	DESCRIPTION   "port Outgoing interface of multicast fib entry.
	    Each bit corresponds to a port, as represented by its ifIndex value .
	    When a bit has the value one(1), the corresponding port is a member of
	    the set. When a bit has the value zero(0), the corresponding port is
	    not a member of the set. The encoding is such that the most significant
	    bit of octet #1 corresponds to ifIndex 0."
	::= { rcIsisPlsbMcastFibEntry 9 }

rcIsisPlsbMcastFibOutgoingInterfaceMlts	OBJECT-TYPE
        SYNTAX		OCTET STRING (SIZE(0..64))
	MAX-ACCESS	read-only
	STATUS		current
	DESCRIPTION	"mlt outgoing interface of multicast fib entry.
	    A set of bits represents the MLT IDs.From left to right, the
	    first bit set represent MltId 1. The second bit set represent
	    MltId 2, and so on so forth, Up to bit 511 which represents
	    Mlt Id 512."
	::= { rcIsisPlsbMcastFibEntry 10 }

rcIsisPlsbMcastFibIncomingInterface OBJECT-TYPE
    	SYNTAX		InterfaceIndex
	MAX-ACCESS	read-only
	STATUS		current
	DESCRIPTION	"Incoming interface (port or mlt) of the multicast Fib
	    		entry."
	::= { rcIsisPlsbMcastFibEntry 11 }

rcIsisPlsbMcastFibIsidName  OBJECT-TYPE
        SYNTAX        DisplayString (SIZE (0..64))
        MAX-ACCESS    read-only
        STATUS        current
        DESCRIPTION   "The administratively-assigned name for this FIB I-SID."
        ::= { rcIsisPlsbMcastFibEntry 12 }

rcIsisPlsbNodeTable      OBJECT-TYPE
        SYNTAX          SEQUENCE OF RcIsisPlsbNodeEntry
        MAX-ACCESS      not-accessible
        STATUS          current
        DESCRIPTION     "Table of IS-IS PLSB Node"
        ::= { rcIsis 15 }

rcIsisPlsbNodeEntry OBJECT-TYPE
        SYNTAX          RcIsisPlsbNodeEntry
        MAX-ACCESS      not-accessible
        STATUS          current
        DESCRIPTION    	"An entry of rcIsisPlsbNode Table. A Entry in
                        table exists for each node running PLSB ISIS
                        in the setup."
        INDEX           { rcIsisPlsbNodeSysId }
        ::= { rcIsisPlsbNodeTable 1 }

RcIsisPlsbNodeEntry   ::=
        SEQUENCE {
          rcIsisPlsbNodeSysId                           OCTET STRING,
	  rcIsisPlsbNodePrimaryParentSysId              OCTET STRING,
          rcIsisPlsbNodePrimaryBvlan                    Integer32,
          rcIsisPlsbNodeSecondaryParentSysId            OCTET STRING,
          rcIsisPlsbNodeSecondaryBvlan                  Integer32
        }

rcIsisPlsbNodeSysId OBJECT-TYPE
        SYNTAX        OCTET STRING (SIZE (6))
        MAX-ACCESS    not-accessible
        STATUS        current
        DESCRIPTION   "System ID of the PLSB node entry"
        ::= { rcIsisPlsbNodeEntry 1 }

rcIsisPlsbNodePrimaryParentSysId OBJECT-TYPE
        SYNTAX        OCTET STRING (SIZE (6))
        MAX-ACCESS    read-only
        STATUS        current
        DESCRIPTION   "System ID of parent node of the PLSB node entry for
                       primary bvlan"
        ::= { rcIsisPlsbNodeEntry 2 }

rcIsisPlsbNodePrimaryBvlan OBJECT-TYPE
        SYNTAX        Integer32 (1..4094)
        MAX-ACCESS    read-only
        STATUS        current
        DESCRIPTION   "spbm primary b-vlan"
        ::= { rcIsisPlsbNodeEntry 3 }

rcIsisPlsbNodeSecondaryParentSysId OBJECT-TYPE
        SYNTAX        OCTET STRING (SIZE (6))
        MAX-ACCESS    read-only
        STATUS        current
        DESCRIPTION   "System ID of parent node of the PLSB node entry for
                       secondary bvlan"
        ::= { rcIsisPlsbNodeEntry 4 }

rcIsisPlsbNodeSecondaryBvlan OBJECT-TYPE
        SYNTAX        Integer32 (1..4094)
        MAX-ACCESS    read-only
        STATUS        current
        DESCRIPTION   "spbm secondary b-vlan"
        ::= { rcIsisPlsbNodeEntry 5 }

rcIsisSpbmPortDropStatsTable      OBJECT-TYPE
        SYNTAX          SEQUENCE OF RcIsisSpbmPortDropStatsEntry
        MAX-ACCESS      not-accessible
        STATUS          current
        DESCRIPTION     "Table of IS-IS SPBM port drop-stats by
                        port index and SPBM b-vlan"
        ::= { rcIsis 16 }

rcIsisSpbmPortDropStatsEntry OBJECT-TYPE
        SYNTAX          RcIsisSpbmPortDropStatsEntry
        MAX-ACCESS      not-accessible
        STATUS          current
        DESCRIPTION    "SPBM port based frame drop counters."
        INDEX           { rcIsisSpbmPortDropStatsPortIndex,
                          rcIsisSpbmPortDropStatsVlanId }
        ::= { rcIsisSpbmPortDropStatsTable 1 }


RcIsisSpbmPortDropStatsEntry ::= SEQUENCE {
        rcIsisSpbmPortDropStatsPortIndex                    InterfaceIndex,
        rcIsisSpbmPortDropStatsVlanId                       Integer32,
        rcIsisSpbmPortDropStatsVlanType                     INTEGER,
        rcIsisSpbmPortDropStatsUnknownUcastSrcAddr          Counter64,
        rcIsisSpbmPortDropStatsRpfcUcastSrcAddr             Counter64,
        rcIsisSpbmPortDropStatsUnknownUcastDestAddr         Counter64,
        rcIsisSpbmPortDropStatsUnknownMcastDestAddr         Counter64,
        rcIsisSpbmPortDropStatsRpfcMcastSrcAddr             Counter64,
        rcIsisSpbmPortDropStatsLastDropMac                  MacAddress,
        rcIsisSpbmPortDropStatsIsMacDestAddr                TruthValue,
        rcIsisSpbmPortDropStatsLastDropMacHostName          OCTET STRING
        }

rcIsisSpbmPortDropStatsPortIndex OBJECT-TYPE
        SYNTAX        InterfaceIndex
        MAX-ACCESS    not-accessible
        STATUS        current
        DESCRIPTION   "An index value that uniquely identifies a port.
                      This value is similar to ifIndex in MIB2."
       ::= { rcIsisSpbmPortDropStatsEntry 1 }

rcIsisSpbmPortDropStatsVlanId OBJECT-TYPE
      SYNTAX            Integer32 (1..4094)
      MAX-ACCESS        not-accessible
      STATUS            current
      DESCRIPTION "A value that uniquely identifies the SPBM Virtual LAN
                         associated with this entry."
      ::= { rcIsisSpbmPortDropStatsEntry 2}

rcIsisSpbmPortDropStatsVlanType OBJECT-TYPE
      SYNTAX            INTEGER {
                                  primary(1),
                                  secondary(2)
                        }
      MAX-ACCESS  read-only
      STATUS      current
      DESCRIPTION "Indicates the type of SPBM bvlan"
      ::= { rcIsisSpbmPortDropStatsEntry 3}

rcIsisSpbmPortDropStatsUnknownUcastSrcAddr OBJECT-TYPE
        SYNTAX        Counter64
        MAX-ACCESS    read-only
        STATUS        current
        DESCRIPTION   "The total number of SPBM unknown unicast SA packets
                       dropped on SPBM bvlan."
        ::= { rcIsisSpbmPortDropStatsEntry 4}

rcIsisSpbmPortDropStatsRpfcUcastSrcAddr OBJECT-TYPE
        SYNTAX        Counter64
        MAX-ACCESS    read-only
        STATUS        current
        DESCRIPTION   "The total number of SPBM reverse path forwarding
                       check (RPFC) unicast SA packets
                       dropped on SPBM bvlan."
        ::= { rcIsisSpbmPortDropStatsEntry 5}

rcIsisSpbmPortDropStatsUnknownUcastDestAddr OBJECT-TYPE
        SYNTAX        Counter64
        MAX-ACCESS    read-only
        STATUS        current
        DESCRIPTION   "The total number of SPBM unknown unicast DA packets
                       dropped on SPBM bvlan."
        ::= { rcIsisSpbmPortDropStatsEntry 6}

rcIsisSpbmPortDropStatsUnknownMcastDestAddr OBJECT-TYPE
        SYNTAX        Counter64
        MAX-ACCESS    read-only
        STATUS        current
        DESCRIPTION   "The total number of SPBM unknown multicast DA packets
                       dropped on SPBM bvlan."
        ::= { rcIsisSpbmPortDropStatsEntry 7}

rcIsisSpbmPortDropStatsRpfcMcastSrcAddr OBJECT-TYPE
        SYNTAX        Counter64
        MAX-ACCESS    read-only
        STATUS        current
        DESCRIPTION   "The total number of SPBM reverse path forwarding
                       check (RPFC) multicast SA packets
                       dropped on SPBM bvlan."
        ::= { rcIsisSpbmPortDropStatsEntry 8}

rcIsisSpbmPortDropStatsLastDropMac OBJECT-TYPE
        SYNTAX        MacAddress
        MAX-ACCESS    read-only
        STATUS        current
        DESCRIPTION   "The DA or SA last dropped on SPBM bvlan."
        ::= { rcIsisSpbmPortDropStatsEntry 9}

rcIsisSpbmPortDropStatsIsMacDestAddr OBJECT-TYPE
        SYNTAX        TruthValue
        MAX-ACCESS    read-only
        STATUS        current
        DESCRIPTION   "The last dropped mac on SPBM bvlan is DA or not."
        ::= { rcIsisSpbmPortDropStatsEntry 10}

rcIsisSpbmPortDropStatsLastDropMacHostName OBJECT-TYPE
        SYNTAX        OCTET STRING (SIZE (0..255))
        MAX-ACCESS    read-only
        STATUS        current
        DESCRIPTION   "The host name of the nodes where last dropped
                       SA or DA on SPBM bvlan belongs"
        ::= { rcIsisSpbmPortDropStatsEntry 11}

rcIsisSpbmSrcAddrDropStatsTable      OBJECT-TYPE
        SYNTAX          SEQUENCE OF RcIsisSpbmSrcAddrDropStatsEntry
        MAX-ACCESS      not-accessible
        STATUS          current
        DESCRIPTION     "Table of IS-IS SPBM SA drop-stats by
                        Source Address and SPBM b-vlan"
        ::= { rcIsis 17 }

rcIsisSpbmSrcAddrDropStatsEntry OBJECT-TYPE
        SYNTAX          RcIsisSpbmSrcAddrDropStatsEntry
        MAX-ACCESS      not-accessible
        STATUS          current
        DESCRIPTION    "SPBM Source Address based frame drop counters."
        INDEX           { rcIsisSpbmSrcAddrDropStatsAddr,
                          rcIsisSpbmSrcAddrDropStatsVlanId }
        ::= { rcIsisSpbmSrcAddrDropStatsTable 1 }

RcIsisSpbmSrcAddrDropStatsEntry ::= SEQUENCE {
        rcIsisSpbmSrcAddrDropStatsAddr                      MacAddress,
        rcIsisSpbmSrcAddrDropStatsVlanId                    Integer32,
        rcIsisSpbmSrcAddrDropStatsVlanType                  INTEGER,
        rcIsisSpbmSrcAddrDropStatsRpfcUcastSrcAddr          Counter64,
        rcIsisSpbmSrcAddrDropStatsUnknownUcastDestAddr      Counter64,
        rcIsisSpbmSrcAddrDropStatsRpfcMcastSrcAddr          Counter64,
        rcIsisSpbmSrcAddrDropStatsUnknownMcastDestAddr      Counter64,
        rcIsisSpbmSrcAddrDropStatsUnknownUcastSrcAddr       Counter64,
        rcIsisSpbmSrcAddrDropStatsHostName                  OCTET STRING
        }

rcIsisSpbmSrcAddrDropStatsAddr OBJECT-TYPE
        SYNTAX        MacAddress
        MAX-ACCESS    not-accessible
        STATUS        current
        DESCRIPTION   "The source MAC of the drop packet."
        ::= { rcIsisSpbmSrcAddrDropStatsEntry 1 }

rcIsisSpbmSrcAddrDropStatsVlanId OBJECT-TYPE
      SYNTAX            Integer32 (1..4094)
      MAX-ACCESS  not-accessible
      STATUS            current
      DESCRIPTION "A value that uniquely identifies the SPBM Virtual LAN
                         associated with this entry."
      ::= { rcIsisSpbmSrcAddrDropStatsEntry 2}

rcIsisSpbmSrcAddrDropStatsVlanType OBJECT-TYPE
      SYNTAX            INTEGER {
                                  primary(1),
                                  secondary(2)
                        }
      MAX-ACCESS  read-only
      STATUS            current
      DESCRIPTION "Indicates the type of SPBM bvlan"
      ::= { rcIsisSpbmSrcAddrDropStatsEntry 3}

rcIsisSpbmSrcAddrDropStatsRpfcUcastSrcAddr OBJECT-TYPE
        SYNTAX        Counter64
        MAX-ACCESS    read-only
        STATUS        current
        DESCRIPTION   "The total number of SPBM reverse path forwarding
                       check (RPFC) unicast SA packets
                       dropped on SPBM bvlan."
        ::= { rcIsisSpbmSrcAddrDropStatsEntry 4}

rcIsisSpbmSrcAddrDropStatsUnknownUcastDestAddr OBJECT-TYPE
        SYNTAX        Counter64
        MAX-ACCESS    read-only
        STATUS        current
        DESCRIPTION   "The total number of SPBM unknown unicast DA packets
                       dropped on SPBM bvlan"
        ::= { rcIsisSpbmSrcAddrDropStatsEntry 5}

rcIsisSpbmSrcAddrDropStatsRpfcMcastSrcAddr OBJECT-TYPE
        SYNTAX        Counter64
        MAX-ACCESS    read-only
        STATUS        current
        DESCRIPTION   "The total number of SPBM reverse path forwarding
                       check (RPFC) multicast SA packets
                       dropped on SPBM bvlan"
        ::= { rcIsisSpbmSrcAddrDropStatsEntry 6}

rcIsisSpbmSrcAddrDropStatsUnknownMcastDestAddr OBJECT-TYPE
        SYNTAX        Counter64
        MAX-ACCESS    read-only
        STATUS        current
        DESCRIPTION   "The total number of SPBM unknown multicast DA packets
                       dropped on SPBM bvlan"
        ::= { rcIsisSpbmSrcAddrDropStatsEntry 7}

rcIsisSpbmSrcAddrDropStatsUnknownUcastSrcAddr OBJECT-TYPE
        SYNTAX        Counter64
        MAX-ACCESS    read-only
        STATUS        current
        DESCRIPTION   "The total number of SPBM unknown unicast SA packets
                       dropped on SPBM bvlan"
        ::= { rcIsisSpbmSrcAddrDropStatsEntry 8}

rcIsisSpbmSrcAddrDropStatsHostName OBJECT-TYPE
        SYNTAX        OCTET STRING (SIZE (0..255))
        MAX-ACCESS    read-only
        STATUS        current
        DESCRIPTION   "The host name of the nodes where last on
                       SPBM bvlan belongs"
        ::= { rcIsisSpbmSrcAddrDropStatsEntry 9}

rcIsisSpbmUniTable OBJECT-TYPE
        SYNTAX        SEQUENCE OF RcIsisSpbmUniEntry
        MAX-ACCESS    not-accessible
        STATUS        current
        DESCRIPTION   "Table containing information about
                       defined I-SIDs and their current
                       use on the platform from an SPBM
                       perspective."
        ::= { rcIsis 18 }

rcIsisSpbmUniEntry OBJECT-TYPE
        SYNTAX        RcIsisSpbmUniEntry
        MAX-ACCESS    not-accessible
        STATUS        current
        DESCRIPTION   "An rcIsisSpbmUniTable entry. An
                       entry exists for each I-SID that
                       is currently defined. Entry instance
                       data indicates current I-SID usage
                       from a UNI perspective as follows:

                       Port             VLAN ID     UNI Type
                       -----------------------------------------------------
                       0           1..4094   C-VLAN UNI
                       0           4095      Transparent UNI on remote SMLT peer
                       1..PortMax  1..4094   Switched UNI
                       1..PortMax  4096      Switched UNI untagged [Not supported]
                       1..PortMax  4095      Transparent UNI"

        INDEX { rcIsisSpbmUniIsid, rcIsisSpbmUniPort, rcIsisSpbmUniVlan }
        ::= { rcIsisSpbmUniTable 1 }

RcIsisSpbmUniEntry ::=
        SEQUENCE {
            rcIsisSpbmUniIsid            Integer32,
            rcIsisSpbmUniPort            InterfaceIndexOrZero,
            rcIsisSpbmUniVlan            Integer32,
            rcIsisSpbmUniRowStatus 	     RowStatus,
            rcIsisSpbmUniStorage         StorageType
        }

rcIsisSpbmUniIsid OBJECT-TYPE
        SYNTAX        Integer32 (1..16777215)
        MAX-ACCESS    not-accessible
        STATUS        current
        DESCRIPTION   "The I-SID key for this entry."

        ::= { rcIsisSpbmUniEntry 1 }

rcIsisSpbmUniPort OBJECT-TYPE
        SYNTAX        InterfaceIndexOrZero
        MAX-ACCESS    not-accessible
        STATUS        current
        DESCRIPTION   "A port that is associated with the I-SID key
                       for this entry.

                       A value equal to 0 indicates that a port is
                       not associated with the entry I-SID key.
                       Depending in the value of rcIsisSpbmUniVlan,
                       the entry can represent either a C-VLAN UNI mapping
                       (rcIsisSpbmUniVlan is 1 to 4094)
                       or a Transparent UNI mapping configured on the remote SMLT peer
                       (rcIsisSpbmUniVlan is 4095)."

        ::= { rcIsisSpbmUniEntry 2 }

rcIsisSpbmUniVlan OBJECT-TYPE
        SYNTAX        Integer32 (1..4095)
        MAX-ACCESS    not-accessible
        STATUS        current
        DESCRIPTION   "A value that uniquely identifies the Virtual
                       LAN associated with this entry. This value
                       corresponds to the lower 12 bits in the IEEE
                       802.1Q VLAN Tag.

                       A value equal to 4095 indicates that a VLAN
                       is not associated with the entry I-SID key,
                       meaning that the entry represents a Transparent
                       UNI mapping."

        ::= { rcIsisSpbmUniEntry 3 }

rcIsisSpbmUniRowStatus OBJECT-TYPE
        SYNTAX          RowStatus
        MAX-ACCESS read-create
        STATUS           current
        DESCRIPTION "This is used to control creation/deletion of entries
         in this table."

        ::= { rcIsisSpbmUniEntry 4 }

rcIsisSpbmUniStorage OBJECT-TYPE
        SYNTAX        StorageType
        MAX-ACCESS    read-only
        STATUS        current
        DESCRIPTION   "This object retrieves the storage type for this entry."

        ::= { rcIsisSpbmUniEntry 5 }


rcIsisSpbmIpMcastRouteTable      OBJECT-TYPE
        SYNTAX          SEQUENCE OF RcIsisSpbmIpMcastRouteEntry
        MAX-ACCESS      not-accessible
        STATUS          obsolete
        DESCRIPTION     "SPBM IP Multicast Route Table
	                This table has been replaced by the
                        rcIsisSpbmIpIsidMcastRouteTable to address the
			INDEX is not in increasing order"
        ::= { rcIsis 19 }

rcIsisSpbmIpMcastRouteEntry OBJECT-TYPE
        SYNTAX          RcIsisSpbmIpMcastRouteEntry
        MAX-ACCESS      not-accessible
        STATUS          obsolete
        DESCRIPTION     "SPBM IP Multicast Route Entry"
        INDEX           { rcIsisSpbmIpMcastGroup,
                          rcIsisSpbmIpMcastSource,
                          rcIsisSpbmIpMcastVsnIsid,
                          rcIsisSpbmIpMcastNickName }
        ::= { rcIsisSpbmIpMcastRouteTable 1 }

RcIsisSpbmIpMcastRouteEntry ::= SEQUENCE {
        rcIsisSpbmIpMcastGroup          IpAddress,
        rcIsisSpbmIpMcastSource         IpAddress,
        rcIsisSpbmIpMcastVsnIsid        Integer32,
        rcIsisSpbmIpMcastNickName       Integer32,
        rcIsisSpbmIpMcastSourceBeb      OCTET STRING,
        rcIsisSpbmIpMcastVlanId         Integer32,
        rcIsisSpbmIpMcastVrfName        DisplayString,
        rcIsisSpbmIpMcastDataIsid       Integer32,
        rcIsisSpbmIpMcastNniPorts       DisplayString,
        rcIsisSpbmIpMcastType           INTEGER,
        rcIsisSpbmIpMcastBvlan          Integer32,
	rcIsisSpbmIpMcastNniInterfacePorts  PortSet,
	rcIsisSpbmIpMcastNniInterfaceMlts   OCTET STRING
        }

rcIsisSpbmIpMcastGroup OBJECT-TYPE
    SYNTAX     IpAddress
    MAX-ACCESS not-accessible
    STATUS     current
    DESCRIPTION
            "The IP multicast group address for which this entry
            contains multicast routing information."
    ::= { rcIsisSpbmIpMcastRouteEntry  1 }

rcIsisSpbmIpMcastSource OBJECT-TYPE
    SYNTAX     IpAddress
    MAX-ACCESS not-accessible
    STATUS     current
    DESCRIPTION
            "The IP address  of the multicast source for which this entry
            contains multicast routing information."
    ::= { rcIsisSpbmIpMcastRouteEntry  2 }

rcIsisSpbmIpMcastVsnIsid OBJECT-TYPE
    SYNTAX     Integer32 (0..16777215)
    MAX-ACCESS not-accessible
    STATUS     current
    DESCRIPTION
            "Virtual Services Network ISID"
    ::= { rcIsisSpbmIpMcastRouteEntry  3 }

rcIsisSpbmIpMcastNickName OBJECT-TYPE
    SYNTAX     Integer32 (0..16777215)
    MAX-ACCESS not-accessible
    STATUS     current
    DESCRIPTION
            "Multicast nick name"
    ::= { rcIsisSpbmIpMcastRouteEntry  4 }

rcIsisSpbmIpMcastSourceBeb OBJECT-TYPE
    SYNTAX     OCTET STRING (SIZE (0..255))
    MAX-ACCESS read-only
    STATUS     current
    DESCRIPTION
            "Source Backbone Edge Bridge name"
    ::= { rcIsisSpbmIpMcastRouteEntry  5 }

rcIsisSpbmIpMcastVlanId OBJECT-TYPE
    SYNTAX     Integer32
    MAX-ACCESS read-only
    STATUS     current
    DESCRIPTION
            "VLAN ID of the interface"
    ::= { rcIsisSpbmIpMcastRouteEntry  6 }

rcIsisSpbmIpMcastVrfName OBJECT-TYPE
    SYNTAX     DisplayString (SIZE (0..64))
    MAX-ACCESS read-only
    STATUS     current
    DESCRIPTION
            "VRF name of the interface"
    ::= { rcIsisSpbmIpMcastRouteEntry  7 }


rcIsisSpbmIpMcastDataIsid OBJECT-TYPE
    SYNTAX     Integer32 (1..16777215)
    MAX-ACCESS read-only
    STATUS     current
    DESCRIPTION
            "Data ISID"
    ::= { rcIsisSpbmIpMcastRouteEntry  8 }


rcIsisSpbmIpMcastNniPorts OBJECT-TYPE
    SYNTAX     DisplayString (SIZE (0..255))
    MAX-ACCESS read-only
    STATUS     obsolete
    DESCRIPTION  "List of NNI ports. This attribute is obsoleted. New attributes
	rcIsisSpbmIpMcastNniInterfacePorts and rcIsisSpbmIpMcastNniInterfaceMlts
	are added for nni interfaces"
    ::= { rcIsisSpbmIpMcastRouteEntry  9 }

rcIsisSpbmIpMcastType OBJECT-TYPE
        SYNTAX          INTEGER {
                                  routed(1),
                                  snoop(2)
                        }
        MAX-ACCESS      read-only
        STATUS          current
        DESCRIPTION     "Indicates the type of the interface"
        ::= { rcIsisSpbmIpMcastRouteEntry  10}

rcIsisSpbmIpMcastBvlan OBJECT-TYPE
    SYNTAX     Integer32
    MAX-ACCESS read-only
    STATUS     current
    DESCRIPTION
            "Backbone VLAN on which SPB traffic is carried"
    ::= { rcIsisSpbmIpMcastRouteEntry  11 }

rcIsisSpbmIpMcastNniInterfacePorts  OBJECT-TYPE
	SYNTAX		PortSet
	MAX-ACCESS	read-only
	STATUS		current
	DESCRIPTION	"list of port nni interface. Each bit corresponds to a
	    port, as represented by its ifIndex value. When a bit has the value one(1),
	    the corresponding port is a member of the set. When a bit has the value
	    zero(0), the corresponding port is not a member of the set. The encoding
	    is such that the most significant bit of octet #1 corresponds to ifIndex 0."
	::= { rcIsisSpbmIpMcastRouteEntry 12 }

rcIsisSpbmIpMcastNniInterfaceMlts  OBJECT-TYPE
	SYNTAX		OCTET STRING (SIZE(0..64))
	MAX-ACCESS	read-only
	STATUS		current
	DESCRIPTION	"list of mlt nni interface. A set of bits represents the
	    MLT IDs.From left to right, the first bit set represent MltId 1. The
	    second bit set represent MltId 2, and so on so forth, Up to bit 511
	    which represents Mlt Id 512."
	::= { rcIsisSpbmIpMcastRouteEntry 13 }

-- Spbm ip multicast route UNI receivers table (vlan/port pairs).
-- MUST have same indices as the rcIsisSpbmIpMcastRouteTable
-- with the addition of egressVlan!!
-- This table is used in conjunction with rcIsisSpbmIpMcastRouteTable
-- in order to gather up all the UNI receivers.
rcIsisSpbmIpMcastRouteUniRcvrsTable      OBJECT-TYPE
        SYNTAX          SEQUENCE OF RcIsisSpbmIpMcastRouteUniRcvrsEntry
        MAX-ACCESS      not-accessible
        STATUS          obsolete
        DESCRIPTION     "SPBM IP Multicast Route UNI Receivers Table.
	                This table has been replaced by the
                        rcIsisSpbmIpIsidMcastRouteUniRcvrsTable to address
			the INDEX is not in increasing order"
        ::= { rcIsis 20 }

rcIsisSpbmIpMcastRouteUniRcvrsEntry OBJECT-TYPE
        SYNTAX          RcIsisSpbmIpMcastRouteUniRcvrsEntry
        MAX-ACCESS      not-accessible
        STATUS          obsolete
        DESCRIPTION     "SPBM IP Multicast Route UNI Receivers Entry"
        INDEX           { rcIsisSpbmIpMcastUniRcvrsGroup,
                          rcIsisSpbmIpMcastUniRcvrsSource,
                          rcIsisSpbmIpMcastUniRcvrsVsnIsid,
                          rcIsisSpbmIpMcastUniRcvrsNickName,
      rcIsisSpbmIpMcastUniRcvrsEgressVlan }
        ::= { rcIsisSpbmIpMcastRouteUniRcvrsTable 1 }

RcIsisSpbmIpMcastRouteUniRcvrsEntry ::= SEQUENCE {
        rcIsisSpbmIpMcastUniRcvrsGroup          IpAddress,
        rcIsisSpbmIpMcastUniRcvrsSource         IpAddress,
        rcIsisSpbmIpMcastUniRcvrsVsnIsid        Integer32,
        rcIsisSpbmIpMcastUniRcvrsNickName       Integer32,
  rcIsisSpbmIpMcastUniRcvrsEgressVlan     Integer32,
        rcIsisSpbmIpMcastUniRcvrsEgressActivePorts  PortSet
        }

rcIsisSpbmIpMcastUniRcvrsGroup OBJECT-TYPE
    SYNTAX     IpAddress
    MAX-ACCESS not-accessible
    STATUS     current
    DESCRIPTION
            "The IP multicast group address for which this entry
            contains multicast routing information."
    ::= { rcIsisSpbmIpMcastRouteUniRcvrsEntry  1 }

rcIsisSpbmIpMcastUniRcvrsSource OBJECT-TYPE
    SYNTAX     IpAddress
    MAX-ACCESS not-accessible
    STATUS     current
    DESCRIPTION
            "The IP address  of the multicast source for which this entry
            contains multicast routing information."
    ::= { rcIsisSpbmIpMcastRouteUniRcvrsEntry  2 }

rcIsisSpbmIpMcastUniRcvrsVsnIsid OBJECT-TYPE
    SYNTAX     Integer32 (0..16777215)
    MAX-ACCESS not-accessible
    STATUS     current
    DESCRIPTION
            "Virtual Services Network ISID"
    ::= { rcIsisSpbmIpMcastRouteUniRcvrsEntry  3 }

rcIsisSpbmIpMcastUniRcvrsNickName OBJECT-TYPE
    SYNTAX     Integer32 (0..16777215)
    MAX-ACCESS not-accessible
    STATUS     current
    DESCRIPTION
            "Multicast nick name"
    ::= { rcIsisSpbmIpMcastRouteUniRcvrsEntry  4 }

rcIsisSpbmIpMcastUniRcvrsEgressVlan OBJECT-TYPE
    SYNTAX     Integer32 (0..4094)
    MAX-ACCESS not-accessible
    STATUS     current
    DESCRIPTION
            "The Vlan associated with this egress entry. "
    ::= { rcIsisSpbmIpMcastRouteUniRcvrsEntry  5 }

rcIsisSpbmIpMcastUniRcvrsEgressActivePorts OBJECT-TYPE
    SYNTAX     PortSet
    MAX-ACCESS read-only
    STATUS     current
    DESCRIPTION
            "The set of ports in the vlan that have UNI receivers for this multicast route. "
    ::= { rcIsisSpbmIpMcastRouteUniRcvrsEntry  6 }

rcIsisPlsbIpInterIsidUnicastFibTable      OBJECT-TYPE
        SYNTAX          SEQUENCE OF RcIsisPlsbIpInterIsidUnicastFibEntry
        MAX-ACCESS      not-accessible
        STATUS          current
        DESCRIPTION     "Table of IS-IS PLSB IP Inter Isid Unicast FIB.
                         This table will replace rcIsisPlsbIpUnicastFibTable"
        ::= { rcIsis 21 }

rcIsisPlsbIpInterIsidUnicastFibEntry OBJECT-TYPE
        SYNTAX          RcIsisPlsbIpInterIsidUnicastFibEntry
        MAX-ACCESS      not-accessible
        STATUS          current
        DESCRIPTION     "An entry of rcIsisPlsbIpInterIsidUnicastFib Table.
                         An Entry table exists for each PLSB IP unicast
                         forwarding entry."
        INDEX           { rcIsisPlsbIpInterIsidUnicastFibVrfId,
			  rcIsisPlsbIpInterIsidUnicastFibDestinationIpAddrType,
			  rcIsisPlsbIpInterIsidUnicastFibDestinationIpAddr,
                          rcIsisPlsbIpInterIsidUnicastFibDestinationMask,
                          rcIsisPlsbIpInterIsidUnicastFibNextHopBmac,
                          rcIsisPlsbIpInterIsidUnicastFibDestIsid,
                          rcIsisPlsbIpInterIsidUnicastFibVlan }
        ::= { rcIsisPlsbIpInterIsidUnicastFibTable 1 }

RcIsisPlsbIpInterIsidUnicastFibEntry   ::=
        SEQUENCE {
	  rcIsisPlsbIpInterIsidUnicastFibVrfId                   Integer32,
          rcIsisPlsbIpInterIsidUnicastFibDestinationIpAddrType   InetAddressType,
          rcIsisPlsbIpInterIsidUnicastFibDestinationIpAddr       InetAddress,
	  rcIsisPlsbIpInterIsidUnicastFibDestinationMask         InetAddressPrefixLength,
          rcIsisPlsbIpInterIsidUnicastFibNextHopBmac             MacAddress,
          rcIsisPlsbIpInterIsidUnicastFibDestIsid                Integer32,
          rcIsisPlsbIpInterIsidUnicastFibVlan                    Integer32,
          rcIsisPlsbIpInterIsidUnicastFibIsid                    Integer32,
          rcIsisPlsbIpInterIsidUnicastFibNextHopName             DisplayString,
          rcIsisPlsbIpInterIsidUnicastFibOutgoingPort            InterfaceIndex,
          rcIsisPlsbIpInterIsidUnicastFibPrefixCost              Integer32,
          rcIsisPlsbIpInterIsidUnicastFibSpbmCost                Counter64,
	  rcIsisPlsbIpInterIsidUnicastFibPreference              Integer32,
          rcIsisPlsbIpInterIsidUnicastFibMetricType              Integer32
        }

rcIsisPlsbIpInterIsidUnicastFibVrfId OBJECT-TYPE
        SYNTAX        Integer32
        MAX-ACCESS    not-accessible
        STATUS        current
        DESCRIPTION   "VRF ID of the IP unicast FIB entry, 0 indicates NRE."
        ::= { rcIsisPlsbIpInterIsidUnicastFibEntry 1 }

rcIsisPlsbIpInterIsidUnicastFibDestinationIpAddrType OBJECT-TYPE
        SYNTAX        InetAddressType
        MAX-ACCESS    not-accessible
        STATUS        current
        DESCRIPTION   "The address type of destination IP Address."
        ::= { rcIsisPlsbIpInterIsidUnicastFibEntry 2 }

rcIsisPlsbIpInterIsidUnicastFibDestinationIpAddr OBJECT-TYPE
        SYNTAX        InetAddress (SIZE(4|16))
        MAX-ACCESS    not-accessible
        STATUS        current
        DESCRIPTION   "Destination IP Address of the IP unicast FIB entry.
		       Support ipv4 size(4) and ipv6 size(16)"
        ::= { rcIsisPlsbIpInterIsidUnicastFibEntry 3 }

rcIsisPlsbIpInterIsidUnicastFibDestinationMask OBJECT-TYPE
        SYNTAX        InetAddressPrefixLength
        MAX-ACCESS    not-accessible
        STATUS        current
        DESCRIPTION   "Destination IP mask of the IP unicast FIB entry "
        ::= { rcIsisPlsbIpInterIsidUnicastFibEntry 4 }

rcIsisPlsbIpInterIsidUnicastFibNextHopBmac OBJECT-TYPE
        SYNTAX        MacAddress
        MAX-ACCESS    not-accessible
        STATUS        current
        DESCRIPTION   "The nexthop BMAC of the IP unicast FIB entry "
        ::= { rcIsisPlsbIpInterIsidUnicastFibEntry 5 }

rcIsisPlsbIpInterIsidUnicastFibDestIsid  OBJECT-TYPE
        SYNTAX        Integer32
        MAX-ACCESS    not-accessible
        STATUS        current
        DESCRIPTION   "Destination ISID of the IP unicast FIB entry "
        ::= { rcIsisPlsbIpInterIsidUnicastFibEntry 6 }

rcIsisPlsbIpInterIsidUnicastFibVlan OBJECT-TYPE
        SYNTAX        Integer32 (0..4094)
        MAX-ACCESS    not-accessible
        STATUS        current
        DESCRIPTION   "Vlan of the IP unicast FIB entry.
	    	       The value of 0 is associated with a local
                       Inter VSN circuitless IP interface fib entry."
        ::= { rcIsisPlsbIpInterIsidUnicastFibEntry 7 }

rcIsisPlsbIpInterIsidUnicastFibIsid OBJECT-TYPE
        SYNTAX        Integer32
        MAX-ACCESS    read-only
        STATUS        current
        DESCRIPTION   "ISID of the IP unicast FIB entry"
        ::= { rcIsisPlsbIpInterIsidUnicastFibEntry 8 }

rcIsisPlsbIpInterIsidUnicastFibNextHopName OBJECT-TYPE
        SYNTAX        DisplayString
        MAX-ACCESS    read-only
        STATUS        current
        DESCRIPTION   "The nexthop hostname of the IP unicast FIB entry "
        ::= { rcIsisPlsbIpInterIsidUnicastFibEntry 9 }

rcIsisPlsbIpInterIsidUnicastFibOutgoingPort  OBJECT-TYPE
        SYNTAX        InterfaceIndex
        MAX-ACCESS    read-only
        STATUS        current
        DESCRIPTION   "Outgoing port of the IP unicast Fib entry.
	    	      The value of 0 is associated with the local interfaces."
        ::= { rcIsisPlsbIpInterIsidUnicastFibEntry 10 }

rcIsisPlsbIpInterIsidUnicastFibPrefixCost OBJECT-TYPE
        SYNTAX        Integer32
        MAX-ACCESS    read-only
        STATUS        current
        DESCRIPTION   "prefix cost of the IP unicast FIB entry"
        ::= { rcIsisPlsbIpInterIsidUnicastFibEntry 11 }

rcIsisPlsbIpInterIsidUnicastFibSpbmCost  OBJECT-TYPE
        SYNTAX        Counter64
        MAX-ACCESS    read-only
        STATUS        current
        DESCRIPTION   "Bmac cost of the IP unicast FIB entry"
        ::= { rcIsisPlsbIpInterIsidUnicastFibEntry 12 }

rcIsisPlsbIpInterIsidUnicastFibPreference OBJECT-TYPE
    	SYNTAX	      Integer32
	MAX-ACCESS    read-only
	STATUS        current
	DESCRIPTION   "IP Route preference of the IP unicast FIB entry"
	::= { rcIsisPlsbIpInterIsidUnicastFibEntry 13 }

rcIsisPlsbIpInterIsidUnicastFibMetricType OBJECT-TYPE
        SYNTAX        Integer32
        MAX-ACCESS    read-only
        STATUS        current
        DESCRIPTION   "IP Metric Type of the IP unicast FIB entry"
        ::= { rcIsisPlsbIpInterIsidUnicastFibEntry 14 }

rcIsisSpbmScalars OBJECT IDENTIFIER ::= { rcIsis 22 }

rcIsisSpbmLoopbackPortCurrState OBJECT-TYPE
        SYNTAX        INTEGER {
                          none(1),
                          stack(2),
                          frontPanel(3)
                      }
        MAX-ACCESS     	read-write
        STATUS         	current
        DESCRIPTION     "Indicates the current SPBM-reserved loopback port."
        ::= { rcIsisSpbmScalars 1 }

rcIsisSpbmLoopbackPortNextState OBJECT-TYPE
        SYNTAX        INTEGER {
                          none(1),
                          stack(2),
                          frontPanel(3)
                      }
        MAX-ACCESS     	read-write
        STATUS         	current
        DESCRIPTION     "Indicates the next SPBM-reserved loopback port (after reboot)."
        ::= { rcIsisSpbmScalars 2 }


-- ISIS PLSB IPV6 Unicast FIB Table

rcIsisPlsbIpv6UnicastFibTable      OBJECT-TYPE
        SYNTAX          SEQUENCE OF RcIsisPlsbIpv6UnicastFibEntry
        MAX-ACCESS      not-accessible
        STATUS          current
        DESCRIPTION     "Table of IS-IS PLSB IPV6 Unicast FIB"
        ::= { rcIsis 23 }

rcIsisPlsbIpv6UnicastFibEntry OBJECT-TYPE
        SYNTAX          RcIsisPlsbIpv6UnicastFibEntry
        MAX-ACCESS      not-accessible
        STATUS          current
        DESCRIPTION     "An entry of rcIsisPlsbIpv6UnicastFib Table. A Entry in
                         table exists for each PLSB IPV6 unicast forwarding entry."
        INDEX           { rcIsisPlsbIpv6UnicastFibVrfId,
                          rcIsisPlsbIpv6UnicastFibDestinationIpAddrType,
                          rcIsisPlsbIpv6UnicastFibDestinationIpAddr,
                          rcIsisPlsbIpv6UnicastFibDestinationMask,
                          rcIsisPlsbIpv6UnicastFibNextHopBmac,
                          rcIsisPlsbIpv6UnicastFibDestIsid,
                          rcIsisPlsbIpv6UnicastFibVlan }
        ::= { rcIsisPlsbIpv6UnicastFibTable 1 }

RcIsisPlsbIpv6UnicastFibEntry   ::=
        SEQUENCE {
          rcIsisPlsbIpv6UnicastFibVrfId                   Integer32,
          rcIsisPlsbIpv6UnicastFibDestinationIpAddrType   InetAddressType,
          rcIsisPlsbIpv6UnicastFibDestinationIpAddr       InetAddress,
          rcIsisPlsbIpv6UnicastFibDestinationMask         InetAddressPrefixLength,
          rcIsisPlsbIpv6UnicastFibNextHopBmac             MacAddress,
          rcIsisPlsbIpv6UnicastFibDestIsid                Integer32,
          rcIsisPlsbIpv6UnicastFibVlan                    Integer32,
          rcIsisPlsbIpv6UnicastFibIsid                    Integer32,
          rcIsisPlsbIpv6UnicastFibNextHopName             DisplayString,
          rcIsisPlsbIpv6UnicastFibOutgoingPort            InterfaceIndex,
          rcIsisPlsbIpv6UnicastFibPrefixCost              Integer32,
          rcIsisPlsbIpv6UnicastFibSpbmCost                Counter64,
	  rcIsisPlsbIpv6UnicastFibMetricType              INTEGER,
	  rcIsisPlsbIpv6UnicastFibPreference              Integer32
        }

rcIsisPlsbIpv6UnicastFibVrfId OBJECT-TYPE
        SYNTAX        Integer32
        MAX-ACCESS    not-accessible
        STATUS        current
        DESCRIPTION   "VRF ID of the IPV6 unicast FIB entry, 0 indicates NRE."
        ::= { rcIsisPlsbIpv6UnicastFibEntry 1 }

rcIsisPlsbIpv6UnicastFibDestinationIpAddrType OBJECT-TYPE
        SYNTAX        InetAddressType
        MAX-ACCESS    not-accessible
        STATUS        current
        DESCRIPTION   "The address type of destination IPV6 Address."
        ::= { rcIsisPlsbIpv6UnicastFibEntry 2 }

rcIsisPlsbIpv6UnicastFibDestinationIpAddr OBJECT-TYPE
        SYNTAX        InetAddress (SIZE(4|16))
        MAX-ACCESS    not-accessible
        STATUS        current
        DESCRIPTION   "Destination IP Address of the IPV6 unicast FIB entry."
        ::= { rcIsisPlsbIpv6UnicastFibEntry 3 }

rcIsisPlsbIpv6UnicastFibDestinationMask OBJECT-TYPE
        SYNTAX        InetAddressPrefixLength
        MAX-ACCESS    not-accessible
        STATUS        current
        DESCRIPTION   "Destination IP mask of the IPV6 unicast FIB entry "
        ::= { rcIsisPlsbIpv6UnicastFibEntry 4 }

rcIsisPlsbIpv6UnicastFibNextHopBmac OBJECT-TYPE
        SYNTAX        MacAddress
        MAX-ACCESS    not-accessible
        STATUS        current
        DESCRIPTION   "the nexthop BMAC of the IPV6 unicast FIB entry "
        ::= { rcIsisPlsbIpv6UnicastFibEntry 5 }

rcIsisPlsbIpv6UnicastFibDestIsid  OBJECT-TYPE
        SYNTAX        Integer32
        MAX-ACCESS    not-accessible
        STATUS        current
        DESCRIPTION   "Destination ISID of the IP unicast FIB entry "
        ::= { rcIsisPlsbIpv6UnicastFibEntry 6 }

rcIsisPlsbIpv6UnicastFibVlan OBJECT-TYPE
        SYNTAX        Integer32 (1..4084)
        MAX-ACCESS    not-accessible
        STATUS        current
        DESCRIPTION   "Vlan of the IPV6 unicast FIB entry"
        ::= { rcIsisPlsbIpv6UnicastFibEntry 7 }

rcIsisPlsbIpv6UnicastFibIsid OBJECT-TYPE
        SYNTAX        Integer32
        MAX-ACCESS    read-only
        STATUS        current
        DESCRIPTION   "ISID of the IPV6 unicast FIB entry"
        ::= { rcIsisPlsbIpv6UnicastFibEntry 8 }

rcIsisPlsbIpv6UnicastFibNextHopName OBJECT-TYPE
        SYNTAX        DisplayString
        MAX-ACCESS    read-only
        STATUS        current
        DESCRIPTION   "the nexthop hostname of the IPV6 unicast FIB entry "
        ::= { rcIsisPlsbIpv6UnicastFibEntry 9 }

rcIsisPlsbIpv6UnicastFibOutgoingPort  OBJECT-TYPE
        SYNTAX        InterfaceIndex
        MAX-ACCESS    read-only
        STATUS        current
        DESCRIPTION   "Outgoing port of the IPV6 unicast Fib entry.
	               The value of 0 is associated with local interfaces"
        ::= { rcIsisPlsbIpv6UnicastFibEntry 10 }

rcIsisPlsbIpv6UnicastFibPrefixCost OBJECT-TYPE
        SYNTAX        Integer32
        MAX-ACCESS    read-only
        STATUS        current
        DESCRIPTION   "prefix cost of the IPV6 unicast FIB entry"
        ::= { rcIsisPlsbIpv6UnicastFibEntry 11 }

rcIsisPlsbIpv6UnicastFibSpbmCost  OBJECT-TYPE
        SYNTAX        Counter64
        MAX-ACCESS    read-only
        STATUS        current
        DESCRIPTION   "bmac cost of the IPV6 unicast FIB entry"
        ::= { rcIsisPlsbIpv6UnicastFibEntry 12 }

rcIsisPlsbIpv6UnicastFibMetricType OBJECT-TYPE
        SYNTAX        INTEGER {
                         internal(1),
                         external(2)
                      }
        MAX-ACCESS    read-only
        STATUS        current
        DESCRIPTION   "IP Metric Type of the IP unicast FIB entry"
        ::= { rcIsisPlsbIpv6UnicastFibEntry 13 }

rcIsisPlsbIpv6UnicastFibPreference OBJECT-TYPE
        SYNTAX        Integer32
        MAX-ACCESS    read-only
        STATUS        current
        DESCRIPTION   "Ipv6 Route preference of the IPv6 unicast FIB entry"
        ::= { rcIsisPlsbIpv6UnicastFibEntry 14 }

-- If the following table is modified, you MUST make sure
-- that table rcIsisSpbmIsidIpMcastRouteUniRcvrsTable is also
-- modified, as it must have the same indices as the following
-- table (plus egressVlan)!!
rcIsisSpbmIpIsidMcastRouteTable      OBJECT-TYPE
        SYNTAX          SEQUENCE OF RcIsisSpbmIpIsidMcastRouteEntry
        MAX-ACCESS      not-accessible
        STATUS          current
        DESCRIPTION     "SPBM IP Isid Multicast Route Table"
        ::= { rcIsis 24 }

rcIsisSpbmIpIsidMcastRouteEntry OBJECT-TYPE
        SYNTAX          RcIsisSpbmIpIsidMcastRouteEntry
        MAX-ACCESS      not-accessible
        STATUS          current
        DESCRIPTION     "SPBM IP Isid Multicast Route Entry"
        INDEX           { rcIsisSpbmIpIsidMcastVsnIsid,
                          rcIsisSpbmIpIsidMcastGroup,
                          rcIsisSpbmIpIsidMcastSource,
                          rcIsisSpbmIpIsidMcastNickName }
        ::= { rcIsisSpbmIpIsidMcastRouteTable 1 }

RcIsisSpbmIpIsidMcastRouteEntry ::= SEQUENCE {
        rcIsisSpbmIpIsidMcastVsnIsid           Integer32,
        rcIsisSpbmIpIsidMcastGroup             IpAddress,
        rcIsisSpbmIpIsidMcastSource            IpAddress,
        rcIsisSpbmIpIsidMcastNickName          Integer32,
        rcIsisSpbmIpIsidMcastSourceBeb         OCTET STRING,
        rcIsisSpbmIpIsidMcastVlanId            Integer32,
        rcIsisSpbmIpIsidMcastVrfName           DisplayString,
        rcIsisSpbmIpIsidMcastDataIsid          Integer32,
        rcIsisSpbmIpIsidMcastType              INTEGER,
        rcIsisSpbmIpIsidMcastBvlan             Integer32,
        rcIsisSpbmIpIsidMcastNniInterfacePorts PortSet,
        rcIsisSpbmIpIsidMcastNniInterfaceMlts  OCTET STRING
        }

rcIsisSpbmIpIsidMcastVsnIsid OBJECT-TYPE
    SYNTAX     Integer32 (0..16777215)
    MAX-ACCESS not-accessible
    STATUS     current
    DESCRIPTION
            "Virtual Services Network ISID"
    ::= { rcIsisSpbmIpIsidMcastRouteEntry  1 }

rcIsisSpbmIpIsidMcastGroup OBJECT-TYPE
    SYNTAX     IpAddress
    MAX-ACCESS not-accessible
    STATUS     current
    DESCRIPTION
            "The IP multicast group address for which this entry
            contains multicast routing information."
    ::= { rcIsisSpbmIpIsidMcastRouteEntry  2 }

rcIsisSpbmIpIsidMcastSource OBJECT-TYPE
    SYNTAX     IpAddress
    MAX-ACCESS not-accessible
    STATUS     current
    DESCRIPTION
            "The IP address  of the multicast source for which this entry
            contains multicast routing information."
    ::= { rcIsisSpbmIpIsidMcastRouteEntry  3 }

rcIsisSpbmIpIsidMcastNickName OBJECT-TYPE
    SYNTAX     Integer32 (0..16777215)
    MAX-ACCESS not-accessible
    STATUS     current
    DESCRIPTION
            "Multicast nick name"
    ::= { rcIsisSpbmIpIsidMcastRouteEntry  4 }

rcIsisSpbmIpIsidMcastSourceBeb OBJECT-TYPE
    SYNTAX     OCTET STRING (SIZE (0..255))
    MAX-ACCESS read-only
    STATUS     current
    DESCRIPTION
            "Source Backbone Edge Bridge name"
    ::= { rcIsisSpbmIpIsidMcastRouteEntry  5 }

rcIsisSpbmIpIsidMcastVlanId OBJECT-TYPE
    SYNTAX     Integer32
    MAX-ACCESS read-only
    STATUS     current
    DESCRIPTION
            "VLAN ID of the interface"
    ::= { rcIsisSpbmIpIsidMcastRouteEntry  6 }

rcIsisSpbmIpIsidMcastVrfName OBJECT-TYPE
    SYNTAX     DisplayString (SIZE (0..64))
    MAX-ACCESS read-only
    STATUS     current
    DESCRIPTION
            "VRF name of the interface"
    ::= { rcIsisSpbmIpIsidMcastRouteEntry  7 }


rcIsisSpbmIpIsidMcastDataIsid OBJECT-TYPE
    SYNTAX     Integer32 (1..16777215)
    MAX-ACCESS read-only
    STATUS     current
    DESCRIPTION
            "Data ISID"
    ::= { rcIsisSpbmIpIsidMcastRouteEntry  8 }

rcIsisSpbmIpIsidMcastType OBJECT-TYPE
        SYNTAX          INTEGER {
                                  routed(1),
                                  snoop(2)
                        }
        MAX-ACCESS      read-only
        STATUS          current
        DESCRIPTION     "Indicates the type of the interface"
        ::= { rcIsisSpbmIpIsidMcastRouteEntry  9}

rcIsisSpbmIpIsidMcastBvlan OBJECT-TYPE
    SYNTAX     Integer32
    MAX-ACCESS read-only
    STATUS     current
    DESCRIPTION
            "Backbone VLAN on which SPB traffic is carried"
    ::= { rcIsisSpbmIpIsidMcastRouteEntry  10 }

rcIsisSpbmIpIsidMcastNniInterfacePorts  OBJECT-TYPE
        SYNTAX        PortSet
        MAX-ACCESS    read-only
        STATUS        current
        DESCRIPTION   "list of port nni interface. Each bit corresponds to a
         port, as represented by its ifIndex value.
         When a bit has the value one(1), the corresponding port is a member
         of the set. When a bit has the value
         zero(0), the corresponding port is not a member of the set.
         The encoding is such that the most significant bit of octet #1
         corresponds to ifIndex 0."
        ::= { rcIsisSpbmIpIsidMcastRouteEntry 11 }

rcIsisSpbmIpIsidMcastNniInterfaceMlts  OBJECT-TYPE
        SYNTAX        OCTET STRING (SIZE(0..64))
        MAX-ACCESS    read-only
        STATUS        current
        DESCRIPTION   "list of mlt nni interface. A set of bits represents the
         MLT IDs.From left to right, the first bit set represent MltId 1. The
         second bit set represent MltId 2, and so on so forth, Up to bit 511
         which represents Mlt Id 512."
        ::= { rcIsisSpbmIpIsidMcastRouteEntry 12 }

-- Spbm ip multicast route UNI receivers table (vlan/port pairs).
-- MUST have same indices as the rcIsisSpbmIpIsidMcastRouteTable
-- with the addition of egressVlan!!
-- This table is used in conjunction with rcIsisSpbmIpIsidMcastRouteTable
-- in order to gather up all the UNI receivers.
rcIsisSpbmIpIsidMcastRouteUniRcvrsTable      OBJECT-TYPE
        SYNTAX          SEQUENCE OF RcIsisSpbmIpIsidMcastRouteUniRcvrsEntry
        MAX-ACCESS      not-accessible
        STATUS          current
        DESCRIPTION     "SPBM IP Isid Multicast Route UNI Receivers Table"
        ::= { rcIsis 25 }

rcIsisSpbmIpIsidMcastRouteUniRcvrsEntry OBJECT-TYPE
        SYNTAX          RcIsisSpbmIpIsidMcastRouteUniRcvrsEntry
        MAX-ACCESS      not-accessible
        STATUS          current
        DESCRIPTION     "SPBM IP Isid Multicast Route UNI Receivers Entry"
        INDEX           { rcIsisSpbmIpIsidMcastUniRcvrsVsnIsid,
                          rcIsisSpbmIpIsidMcastUniRcvrsGroup,
                          rcIsisSpbmIpIsidMcastUniRcvrsSource,
                          rcIsisSpbmIpIsidMcastUniRcvrsNickName,
                          rcIsisSpbmIpIsidMcastUniRcvrsEgressVlan }
        ::= { rcIsisSpbmIpIsidMcastRouteUniRcvrsTable 1 }

RcIsisSpbmIpIsidMcastRouteUniRcvrsEntry ::= SEQUENCE {
        rcIsisSpbmIpIsidMcastUniRcvrsVsnIsid        Integer32,
        rcIsisSpbmIpIsidMcastUniRcvrsGroup          IpAddress,
        rcIsisSpbmIpIsidMcastUniRcvrsSource         IpAddress,
        rcIsisSpbmIpIsidMcastUniRcvrsNickName       Integer32,
        rcIsisSpbmIpIsidMcastUniRcvrsEgressVlan     Integer32,
        rcIsisSpbmIpIsidMcastUniRcvrsEgressActivePorts  PortSet
        }

rcIsisSpbmIpIsidMcastUniRcvrsVsnIsid OBJECT-TYPE
    SYNTAX     Integer32 (0..16777215)
    MAX-ACCESS not-accessible
    STATUS     current
    DESCRIPTION
            "Virtual Services Network ISID"
    ::= { rcIsisSpbmIpIsidMcastRouteUniRcvrsEntry  1 }

rcIsisSpbmIpIsidMcastUniRcvrsGroup OBJECT-TYPE
    SYNTAX     IpAddress
    MAX-ACCESS not-accessible
    STATUS     current
    DESCRIPTION
            "The IP multicast group address for which this entry
            contains multicast routing information."
    ::= { rcIsisSpbmIpIsidMcastRouteUniRcvrsEntry  2 }

rcIsisSpbmIpIsidMcastUniRcvrsSource OBJECT-TYPE
    SYNTAX     IpAddress
    MAX-ACCESS not-accessible
    STATUS     current
    DESCRIPTION
            "The IP address  of the multicast source for which this entry
            contains multicast routing information."
    ::= { rcIsisSpbmIpIsidMcastRouteUniRcvrsEntry  3 }

rcIsisSpbmIpIsidMcastUniRcvrsNickName OBJECT-TYPE
    SYNTAX     Integer32 (0..16777215)
    MAX-ACCESS not-accessible
    STATUS     current
    DESCRIPTION
            "Multicast nick name"
    ::= { rcIsisSpbmIpIsidMcastRouteUniRcvrsEntry  4 }

rcIsisSpbmIpIsidMcastUniRcvrsEgressVlan OBJECT-TYPE
    SYNTAX     Integer32 (0..4094)
    MAX-ACCESS not-accessible
    STATUS     current
    DESCRIPTION
            "The Vlan associated with this egress entry. "
    ::= { rcIsisSpbmIpIsidMcastRouteUniRcvrsEntry  5 }

rcIsisSpbmIpIsidMcastUniRcvrsEgressActivePorts OBJECT-TYPE
    SYNTAX     PortSet
    MAX-ACCESS read-only
    STATUS     current
    DESCRIPTION
            "The set of ports in the vlan that have UNI receivers for this multicast route. "
    ::= { rcIsisSpbmIpIsidMcastRouteUniRcvrsEntry  6 }

-- ISIS logical interface table

rcIsisLogicalInterfaceTable OBJECT-TYPE
        SYNTAX  SEQUENCE OF RcIsisLogicalInterfaceEntry
        MAX-ACCESS not-accessible
        STATUS current
        DESCRIPTION
            "The table of ISIS logical interface."
        ::= { rcIsis 26 }

rcIsisLogicalInterfaceEntry OBJECT-TYPE
        SYNTAX RcIsisLogicalInterfaceEntry
        MAX-ACCESS not-accessible
        STATUS current
        DESCRIPTION
            "Entry contains the configuration information about the logical isis interface"
        INDEX { rcIsisLogicalInterfaceId }
        ::= { rcIsisLogicalInterfaceTable 1 }

RcIsisLogicalInterfaceEntry  ::= SEQUENCE {
          rcIsisLogicalInterfaceId              Integer32,
          rcIsisLogicalInterfaceIfIndex         InterfaceIndex,
          rcIsisLogicalInterfaceType            INTEGER,
          rcIsisLogicalInterfaceDestIPAddr      IpAddress,
          rcIsisLogicalInterfaceDestIfIndex     InterfaceIndex,
          rcIsisLogicalInterfaceVids            OCTET STRING (SIZE(512)),
          rcIsisLogicalInterfacePrimaryVid      Integer32,
          rcIsisLogicalInterfaceName            DisplayString,
          rcIsisLogicalInterfaceRowStatus       RowStatus,
	  rcIsisLogicalInterfaceCircIndex	IndexInteger,
	  rcIsisLogicalInterfaceNextHopIfIndex	InterfaceIndex,
	  rcIsisLogicalInterfaceNextHopVid	Integer32,
	  rcIsisLogicalInterfaceNextHopVrf	DisplayString (SIZE(0..15)),
          rcIsisLogicalInterfaceIpsecEnable         TruthValue,
          rcIsisLogicalInterfaceAuthenticationKey   DisplayString,
          rcIsisLogicalInterfaceShapingRate         INTEGER,
	  rcIsisLogicalInterfaceMtu             INTEGER,
	  rcIsisLogicalInterfaceEncryptionKeyLength INTEGER,
	  rcIsisLogicalInterfaceIpsecTunnelDestAddress IpAddress,
          rcIsisLogicalInterfaceBfdEnable	EnableValue,
          rcIsisLogicalInterfaceIpsecResponderOnly TruthValue,
          rcIsisLogicalInterfaceIpsecRemoteNatIPAddr IpAddress,
          rcIsisLogicalInterfaceIpsecAuthMethod      INTEGER,
          rcIsisLogicalInterfaceIpsecCompression TruthValue
        }

rcIsisLogicalInterfaceId OBJECT-TYPE
        SYNTAX  Integer32 (1..255)
        MAX-ACCESS not-accessible
        STATUS current
        DESCRIPTION
            "An index used to uniquely identify this logical interface."
        ::= { rcIsisLogicalInterfaceEntry  1 }

rcIsisLogicalInterfaceIfIndex   OBJECT-TYPE
        SYNTAX        InterfaceIndex
        MAX-ACCESS    read-only
        STATUS        current
        DESCRIPTION  "The ISIS logical ifIndex"
        ::= { rcIsisLogicalInterfaceEntry  2 }

rcIsisLogicalInterfaceType        OBJECT-TYPE
        SYNTAX         INTEGER {
                                     layer2(1),
                                     ip(2)
                               }
        MAX-ACCESS    read-create
        STATUS        current
        DESCRIPTION  " Indicates the entry is for Layer2 or Layer3"
::= { rcIsisLogicalInterfaceEntry  3 }

rcIsisLogicalInterfaceDestIPAddr OBJECT-TYPE
        SYNTAX        IpAddress
        MAX-ACCESS    read-create
        STATUS        current
        DESCRIPTION   "The logical interface Destination IP address"
                ::= { rcIsisLogicalInterfaceEntry  4 }

rcIsisLogicalInterfaceDestIfIndex OBJECT-TYPE
        SYNTAX InterfaceIndex
        MAX-ACCESS read-create
        STATUS current
        DESCRIPTION
            "The value of ifIndex for the interface to which this
             logical interface corresponds. It can be port/mlt ifindex."
    ::= { rcIsisLogicalInterfaceEntry  5 }

rcIsisLogicalInterfaceVids OBJECT-TYPE
        SYNTAX        OCTET STRING (SIZE(512))
        MAX-ACCESS    read-create
        STATUS        current
        DESCRIPTION   "This bitfield is used to identify which VLANs this
                       logical interface is associated with. Each VLAN ID
                       is stored as a bit. The most-significant (left-most)
                       bit represents Vlan Id 1."
                      ::= { rcIsisLogicalInterfaceEntry  6 }

rcIsisLogicalInterfacePrimaryVid OBJECT-TYPE
        SYNTAX        Integer32 (2..4059)
        MAX-ACCESS    read-create
        STATUS        current
        DESCRIPTION   "Primary tunnel vlan associated with L2Core ISIS logical interface"
        ::= { rcIsisLogicalInterfaceEntry  7 }

rcIsisLogicalInterfaceName OBJECT-TYPE
        SYNTAX        DisplayString (SIZE (1..64))
        MAX-ACCESS    read-create
        STATUS        current
        DESCRIPTION   "An administratively-assigned name for this Logical interface."
        ::= { rcIsisLogicalInterfaceEntry  8 }

rcIsisLogicalInterfaceRowStatus OBJECT-TYPE
        SYNTAX        RowStatus
        MAX-ACCESS    read-create
        STATUS        current
        DESCRIPTION   "Used to create/delete  logical interface"
        ::= { rcIsisLogicalInterfaceEntry 9 }

rcIsisLogicalInterfaceCircIndex OBJECT-TYPE
        SYNTAX        IndexInteger
        MAX-ACCESS    read-only
        STATUS        current
        DESCRIPTION   "An index used to indentify ISIS circuit created
	    	       under the logical interface"
        ::= { rcIsisLogicalInterfaceEntry 10 }

rcIsisLogicalInterfaceNextHopIfIndex OBJECT-TYPE
        SYNTAX        InterfaceIndex
        MAX-ACCESS    read-only
        STATUS        current
        DESCRIPTION   "Next hop destination ifindex to reach the
	    	       logical tunnel dest-ip"
        ::= { rcIsisLogicalInterfaceEntry 11 }

rcIsisLogicalInterfaceNextHopVid OBJECT-TYPE
        SYNTAX        Integer32 (1..4094)
        MAX-ACCESS    read-only
        STATUS        current
        DESCRIPTION   "Next hop vlan id to reach logical
	    	       tunnel dest-ip
                       It is deprecated by rcIsisLogicalInterfaceNextHopDestIfIndex"
        ::= { rcIsisLogicalInterfaceEntry 12 }

rcIsisLogicalInterfaceNextHopVrf OBJECT-TYPE
        SYNTAX        DisplayString (SIZE (0..15))
        MAX-ACCESS    read-only
        STATUS        current
        DESCRIPTION   "Next hop vrf name to reach
	    	       logical tunnel dest-ip
                       It is deprecated by rcIsisLogicalInterfaceNextHopDestVid"
        ::= { rcIsisLogicalInterfaceEntry 13 }

rcIsisLogicalInterfaceIpsecEnable OBJECT-TYPE
        SYNTAX        TruthValue
        MAX-ACCESS    read-create
        STATUS        current
        DESCRIPTION   "Indicate if IPSec is enabled on logical interface"
        DEFVAL        { false }
        ::= { rcIsisLogicalInterfaceEntry 14 }

rcIsisLogicalInterfaceAuthenticationKey OBJECT-TYPE
        SYNTAX        DisplayString (SIZE (0..32))
        MAX-ACCESS    read-create
        STATUS        current
        DESCRIPTION   "Authentication key for IPSec on logical interface"
        ::= { rcIsisLogicalInterfaceEntry 15 }

rcIsisLogicalInterfaceShapingRate OBJECT-TYPE
        SYNTAX        INTEGER (0..1000)
        MAX-ACCESS    read-create
        STATUS        current
        DESCRIPTION   "Egress shaping rate value on ISIS logical interface"
        DEFVAL        { 0 }
        ::= { rcIsisLogicalInterfaceEntry  16 }

rcIsisLogicalInterfaceMtu OBJECT-TYPE
        SYNTAX        INTEGER (750..9000)
        MAX-ACCESS    read-create
        STATUS        current
        DESCRIPTION   "The value specifies MTU of logical interface tunnel"
	DEFVAL        { 1950 }
        ::= { rcIsisLogicalInterfaceEntry  17 }

rcIsisLogicalInterfaceEncryptionKeyLength        OBJECT-TYPE
        SYNTAX         INTEGER {
                                     len128bit(1),
                                     len256bit(2)
                               }
        MAX-ACCESS    read-create
        STATUS        current
        DESCRIPTION   "The length of key used for encryption in IPSec Tunnel"
        DEFVAL         { len128bit}
        ::= { rcIsisLogicalInterfaceEntry  18 }

rcIsisLogicalInterfaceIpsecTunnelDestAddress OBJECT-TYPE
        SYNTAX        IpAddress
        MAX-ACCESS    read-create
        STATUS        current
        DESCRIPTION   "The IPSec Destination IP address"
                ::= { rcIsisLogicalInterfaceEntry  19 }

rcIsisLogicalInterfaceBfdEnable OBJECT-TYPE
       SYNTAX       EnableValue
       MAX-ACCESS   read-write
       STATUS       current
       DESCRIPTION
          " Used to enable/disable BFD on ISIS logical interface."
       DEFVAL          { disable }
       ::= { rcIsisLogicalInterfaceEntry 20 }

rcIsisLogicalInterfaceIpsecResponderOnly OBJECT-TYPE
      SYNTAX        TruthValue
      MAX-ACCESS    read-create
      STATUS        current
      DESCRIPTION   "Indicates if IPSec session of this logical interface should be in responder only
	  	     mode. When this config is made true it will not initiate the IPSec connection but
		     only respond to the incoming connection.
		     By default both the sides of IPSec connection will be initiators. When there is
		     NAT in between the IPSec connection, configure this to true on IPSec responder
		     logical interface.
		     Note: IPSec responder-only is set to true and If IPSec is enabled
		     on Initiator side, ipsec needs to be disabled and enabled on
		     intiator side to re-initiate the connection"
      DEFVAL        { false }
      ::= { rcIsisLogicalInterfaceEntry 21 }

rcIsisLogicalInterfaceIpsecRemoteNatIPAddr OBJECT-TYPE
      SYNTAX        IpAddress
      MAX-ACCESS    read-create
      STATUS        current
      DESCRIPTION   "IPSec remote NAT IP address.
                     This needs to be configured in IPSec initiator logical interface
                     when there is NAT on both side the of IPSec tunnel"
      ::= { rcIsisLogicalInterfaceEntry 22 }

rcIsisLogicalInterfaceIpsecAuthMethod OBJECT-TYPE
        SYNTAX        INTEGER {
                          preSharedKey(1),
                          rsaSignedDigitalCert(2)
                          }
        MAX-ACCESS    read-create
        STATUS        current
        DESCRIPTION   "Method of authentication to use when validating
                       the identity of remote IPSEC peer.
                       - preSharedKey - pre shared keys
                       - rsaSignedDigitalCert - RSA signed digital certificates"
        DEFVAL        { preSharedKey }
                ::= { rcIsisLogicalInterfaceEntry  23 }

rcIsisLogicalInterfaceIpsecCompression OBJECT-TYPE
        SYNTAX        TruthValue
        MAX-ACCESS    read-create
        STATUS        current
        DESCRIPTION   "Indicate if IPSec compression is enabled on logical interface.
                       This object is applicable only for ExtremeAccess platforms XA1440 and XA1480."
        DEFVAL        { false }
        ::= { rcIsisLogicalInterfaceEntry 24 }



--ISIS SPBM MCAST FIB UNI TABLE

rcIsisSpbmMcastFibUniTable      OBJECT-TYPE
        SYNTAX          SEQUENCE OF RcIsisSpbmMcastFibUniEntry
        MAX-ACCESS      not-accessible
        STATUS          current
        DESCRIPTION     "IS-IS SPBM Multicast FIB Uni Table"
        ::= { rcIsis 27 }

rcIsisSpbmMcastFibUniEntry OBJECT-TYPE
        SYNTAX          RcIsisSpbmMcastFibUniEntry
        MAX-ACCESS      not-accessible
        STATUS          current
        DESCRIPTION     " IS-IS SPBM Multicast FIB Uni Entry"
        INDEX           { rcIsisSpbmMcastFibUniSysId,
                          rcIsisSpbmMcastFibUniVlan,
                          rcIsisSpbmMcastFibUniMcastDestMacAddr,
                          rcIsisSpbmMcastFibUniCvid
                        }
        ::= { rcIsisSpbmMcastFibUniTable 1 }

RcIsisSpbmMcastFibUniEntry   ::=
        SEQUENCE {
          rcIsisSpbmMcastFibUniSysId                              OCTET STRING,
          rcIsisSpbmMcastFibUniVlan                               Integer32,
          rcIsisSpbmMcastFibUniMcastDestMacAddr                   MacAddress,
          rcIsisSpbmMcastFibUniCvid                               Integer32,
          rcIsisSpbmMcastFibUniOutgoingInterfaceNniPorts          PortSet,
          rcIsisSpbmMcastFibUniOutgoingInterfaceNniMlts           OCTET STRING,
          rcIsisSpbmMcastFibUniOutgoingInterfaceSwUniPorts        PortSet,
          rcIsisSpbmMcastFibUniOutgoingInterfaceSwUniMlts         OCTET STRING,
          rcIsisSpbmMcastFibUniOutgoingInterfaceCvlanUniPorts     PortSet,
          rcIsisSpbmMcastFibUniOutgoingInterfaceCvlanUniMlts      OCTET STRING,
          rcIsisSpbmMcastFibUniCvlan                              Integer32
        }

rcIsisSpbmMcastFibUniSysId OBJECT-TYPE
        SYNTAX        OCTET STRING (SIZE (6))
        MAX-ACCESS    not-accessible
        STATUS        current
        DESCRIPTION   "System ID of the node where multicast FIB entry
                       come from."
        ::= { rcIsisSpbmMcastFibUniEntry 1 }

rcIsisSpbmMcastFibUniVlan OBJECT-TYPE
        SYNTAX        Integer32 (1..4094)
        MAX-ACCESS    not-accessible
        STATUS        current
        DESCRIPTION   "bVlan of the multicast FIB entry."
        ::= { rcIsisSpbmMcastFibUniEntry 2 }

rcIsisSpbmMcastFibUniMcastDestMacAddr OBJECT-TYPE
        SYNTAX        MacAddress
        MAX-ACCESS    not-accessible
        STATUS        current
        DESCRIPTION   "Multicast destination Mac Address of the
                       multicast FIB entry. "
        ::= { rcIsisSpbmMcastFibUniEntry 3 }

rcIsisSpbmMcastFibUniCvid OBJECT-TYPE
        SYNTAX        Integer32 (1..4096)
        MAX-ACCESS    not-accessible
        STATUS        current
        DESCRIPTION  "Customer vid of the multicast FIB entry.
4095 is not used. 4096 is reserved for untagged case."
        ::= { rcIsisSpbmMcastFibUniEntry 4 }

rcIsisSpbmMcastFibUniOutgoingInterfaceNniPorts  OBJECT-TYPE
        SYNTAX        PortSet
       MAX-ACCESS     read-only
        STATUS        current
        DESCRIPTION   "nni port Outgoing interface of multicast fib entry.
         Each bit corresponds to a port, as represented by its ifIndex value .
         When a bit has the value one(1), the corresponding port is a member of
         the set. When a bit has the value zero(0), the corresponding port is
         not a member of the set. The encoding is such that the most significant
         bit of octet #1 corresponds to ifIndex 0."
        ::= { rcIsisSpbmMcastFibUniEntry 5 }

rcIsisSpbmMcastFibUniOutgoingInterfaceNniMlts  OBJECT-TYPE
        SYNTAX        OCTET STRING (SIZE(0..64))
        MAX-ACCESS    read-only
        STATUS        current
        DESCRIPTION   "nni mlt outgoing interface of multicast fib entry.
         A set of bits represents the MLT IDs.From left to right, the
         first bit set represent MltId 1. The second bit set represent
         MltId 2, and so on so forth, Up to bit 511 which represents
         Mlt Id 512."
        ::= { rcIsisSpbmMcastFibUniEntry 6 }

rcIsisSpbmMcastFibUniOutgoingInterfaceSwUniPorts  OBJECT-TYPE
        SYNTAX        PortSet
        MAX-ACCESS    read-only
        STATUS        current
        DESCRIPTION   "switched uni port Outgoing interface of multicast fib entry.
         Each bit corresponds to a port, as represented by its ifIndex value .
         When a bit has the value one(1), the corresponding port is a member of
         the set. When a bit has the value zero(0), the corresponding port is
         not a member of the set. The encoding is such that the most significant
         bit of octet #1 corresponds to ifIndex 0."
        ::= { rcIsisSpbmMcastFibUniEntry 7 }

rcIsisSpbmMcastFibUniOutgoingInterfaceSwUniMlts  OBJECT-TYPE
        SYNTAX        OCTET STRING (SIZE(0..64))
        MAX-ACCESS    read-only
        STATUS        current
        DESCRIPTION   "switched uni mlt outgoing interface of multicast fib entry.
         A set of bits represents the MLT IDs.From left to right, the
         first bit set represent MltId 1. The second bit set represent
         MltId 2, and so on so forth, Up to bit 511 which represents
         Mlt Id 512."
        ::= { rcIsisSpbmMcastFibUniEntry 8 }

rcIsisSpbmMcastFibUniOutgoingInterfaceCvlanUniPorts  OBJECT-TYPE
        SYNTAX        PortSet
        MAX-ACCESS    read-only
        STATUS        current
        DESCRIPTION   "platform cvlan uni port Outgoing interface of multicast fib
         entry. Each bit corresponds to a port, as represented by its ifIndex value .
         When a bit has the value one(1), the corresponding port is a member of
         the set. When a bit has the value zero(0), the corresponding port is
         not a member of the set. The encoding is such that the most significant
         bit of octet #1 corresponds to ifIndex 0."
        ::= { rcIsisSpbmMcastFibUniEntry 9 }

rcIsisSpbmMcastFibUniOutgoingInterfaceCvlanUniMlts  OBJECT-TYPE
        SYNTAX        OCTET STRING (SIZE(0..64))
        MAX-ACCESS    read-only
        STATUS        current
        DESCRIPTION   "platform cvlan uni mlt outgoing interface of multicast fib
         entry. A set of bits represents the MLT IDs.From left to right, the
         first bit set represent MltId 1. The second bit set represent
         MltId 2, and so on so forth, Up to bit 511 which represents
         Mlt Id 512."
        ::= { rcIsisSpbmMcastFibUniEntry 10 }

rcIsisSpbmMcastFibUniCvlan OBJECT-TYPE
        SYNTAX        Integer32 (0..4084)
        MAX-ACCESS    read-only
        STATUS        current
        DESCRIPTION   "platform customer vlan of the multicast FIB entry."
        ::= { rcIsisSpbmMcastFibUniEntry 11 }

-- used to store next hop information for given logical interface tunnel
rcIsisLogicalInterfaceNextHopTable OBJECT-TYPE
       SYNTAX        SEQUENCE OF RcIsisLogicalInterfaceNextHopEntry
       MAX-ACCESS    not-accessible
       STATUS        current
       DESCRIPTION   "The table to store nexthop information for
	   	      the logical-interface tunnel"
       ::= { rcIsis 28 }

rcIsisLogicalInterfaceNextHopEntry OBJECT-TYPE
       SYNTAX         RcIsisLogicalInterfaceNextHopEntry
       MAX-ACCESS     not-accessible
       STATUS         current
       DESCRIPTION    "Entry contains the nexthop information for
                       the logical interface tunnel"
       INDEX { rcIsisLogicalInterfaceNextHopId,
               rcIsisLogicalInterfaceNextHopIp
             }
       ::= { rcIsisLogicalInterfaceNextHopTable 1 }

RcIsisLogicalInterfaceNextHopEntry  ::= SEQUENCE {
           rcIsisLogicalInterfaceNextHopId           Integer32,
           rcIsisLogicalInterfaceNextHopIp           IpAddress,
           rcIsisLogicalInterfaceNextHopDestIfIndex  InterfaceIndex,
           rcIsisLogicalInterfaceNextHopDestVid      Integer32
       }

rcIsisLogicalInterfaceNextHopId OBJECT-TYPE
      SYNTAX         Integer32 (1..255)
      MAX-ACCESS     not-accessible
      STATUS         current
      DESCRIPTION   "An index used to uniquely identify the
                     logical interface tunnel.This value is
                     same as the rcIsisLogicalInterfaceId in
                     the rcIsisLogicalInterfaceTable"
      ::= { rcIsisLogicalInterfaceNextHopEntry  1 }

rcIsisLogicalInterfaceNextHopIp OBJECT-TYPE
      SYNTAX        IpAddress
      MAX-ACCESS    not-accessible
      STATUS        current
      DESCRIPTION   "An index that uniquely identifies the next hop
                     IP address of the logical interface tunnel"
      ::= { rcIsisLogicalInterfaceNextHopEntry  2 }

rcIsisLogicalInterfaceNextHopDestIfIndex OBJECT-TYPE
     SYNTAX         InterfaceIndex
     MAX-ACCESS     read-only
     STATUS         current
     DESCRIPTION    "Next hop destination ifindex to reach the
	 	     next hop ip of logical interface tunnel"
     ::= { rcIsisLogicalInterfaceNextHopEntry  3 }

rcIsisLogicalInterfaceNextHopDestVid  OBJECT-TYPE
      SYNTAX        Integer32 (0..4094)
      MAX-ACCESS    read-only
      STATUS        current
      DESCRIPTION   "Next hop destination vlan id to reach the
	  	     next hop ip of logical interface tunnel"
      ::= { rcIsisLogicalInterfaceNextHopEntry  4 }




-- IS-IS Multi Area Group

rcIsisMultiArea OBJECT IDENTIFIER ::= { rcIsis 29 }

rcIsisMultiAreaGlobalGroup OBJECT IDENTIFIER ::= { rcIsisMultiArea 1 }

rcIsisMultiAreaGlobalVNodeNickName OBJECT-TYPE
        SYNTAX          IsisPlsbNodeNickName
        MAX-ACCESS      read-write
        STATUS          current
        DESCRIPTION     "Virtual node's nickname is used to
                         calculate ISID multicast mac address."
    ::= { rcIsisMultiAreaGlobalGroup   1 }

rcIsisMultiAreaGlobalVNodeSysId   OBJECT-TYPE
    SYNTAX              OCTET STRING (SIZE(6))
    MAX-ACCESS          read-write
    STATUS              current
    DESCRIPTION         "The system id of the virtual node"
    ::= { rcIsisMultiAreaGlobalGroup   2 }

rcIsisMultiAreaGlobalVNodeSysName   OBJECT-TYPE
    SYNTAX              OCTET STRING (SIZE (0..255))
    MAX-ACCESS          read-write
    STATUS              current
    DESCRIPTION         "The system name of the virtual node"
    ::= { rcIsisMultiAreaGlobalGroup   3 }

-- IS-IS Multi Area Redistribute

rcIsisMultiAreaRedistribute OBJECT IDENTIFIER ::= { rcIsisMultiArea 2 }

rcIsisMultiAreaRedistributeGlobalGroup OBJECT IDENTIFIER ::= { rcIsisMultiAreaRedistribute 1 }

rcIsisMultiAreaL2RedistributeIsidApply OBJECT-TYPE
        SYNTAX        INTEGER  {
                        noAction(1),
                           apply(2)
                        }
        MAX-ACCESS    read-write
        STATUS        current
        DESCRIPTION   "Used to Apply IS-IS multi area isid filters.
                       When the value is set to apply, all the elements in
                       rcIsisMultiAreaL2RedistributeIsidTable will be
                       applied. This may be a disruptive operation to traffic.
                       The get will always return noAction."
        DEFVAL        { noAction }
        ::= { rcIsisMultiAreaRedistributeGlobalGroup 1 }

rcIsisMultiAreaL2RedistributeMcastApply OBJECT-TYPE
        SYNTAX        INTEGER  {
                        noAction(1),
                           apply(2)
                        }
        MAX-ACCESS    read-write
        STATUS        current
        DESCRIPTION   "Used to Apply IS-IS multi area multicast filters.
                       When the value is set to apply, all the elements in
                       rcIsisMultiAreaL2RedistributeMcastIsidTable and
                       rcIsisMultiAreaL2RedistributeMcastIsidListTable will be
                       applied. This may be a disruptive operation to traffic.
                       The get will always return noAction."
        DEFVAL        { noAction }
        ::= { rcIsisMultiAreaRedistributeGlobalGroup 2 }


rcIsisMultiAreaDvrBbRedistribute OBJECT-TYPE
        SYNTAX        TruthValue
        MAX-ACCESS    read-write
        STATUS        current
        DESCRIPTION   "Used to control DVR backbone entry redistribution."
        DEFVAL        { false }
        ::= { rcIsisMultiAreaRedistributeGlobalGroup 3 }

-- IS-IS Multi Area L2 Redistribute ISID Table

rcIsisMultiAreaL2RedistributeIsidTable OBJECT-TYPE
     SYNTAX SEQUENCE OF RcIsisMultiAreaL2RedistributeIsidEntry
     MAX-ACCESS   not-accessible
     STATUS       current
     DESCRIPTION  "Table for inter-area L2 I-SID redistribution."
     ::= { rcIsisMultiAreaRedistribute 2}

rcIsisMultiAreaL2RedistributeIsidEntry OBJECT-TYPE
     SYNTAX        RcIsisMultiAreaL2RedistributeIsidEntry
     MAX-ACCESS    not-accessible
     STATUS        current
     DESCRIPTION   "Contains information regarding inter-area
                    L2 I-SID redistribution policy."
     INDEX        { rcIsisMultiAreaL2RedistributeIsidType }
     ::= { rcIsisMultiAreaL2RedistributeIsidTable 1 }

RcIsisMultiAreaL2RedistributeIsidEntry ::=
     SEQUENCE {
            rcIsisMultiAreaL2RedistributeIsidType            INTEGER,
            rcIsisMultiAreaL2RedistributeIsidPermit          TruthValue,
            rcIsisMultiAreaL2RedistributeIsidExceptListName  DisplayString,
            rcIsisMultiAreaL2RedistributeIsidRowStatus       RowStatus
     }

rcIsisMultiAreaL2RedistributeIsidType OBJECT-TYPE
        SYNTAX        INTEGER  {
                        l2isid(1)
                        }
        MAX-ACCESS    not-accessible
        STATUS        current
        DESCRIPTION   "L2 isid redistribute type.
                       Configurable values:
                        l2isid(1) - L2 isid"
        ::= { rcIsisMultiAreaL2RedistributeIsidEntry 1 }

rcIsisMultiAreaL2RedistributeIsidPermit OBJECT-TYPE
        SYNTAX        TruthValue
        MAX-ACCESS    read-create
        STATUS        current
        DESCRIPTION   "Used to set inter-area L2 I-SID redistribution
                       policy to permit or deny."
        DEFVAL        {false}
        ::= { rcIsisMultiAreaL2RedistributeIsidEntry 2 }

rcIsisMultiAreaL2RedistributeIsidExceptListName OBJECT-TYPE
        SYNTAX        DisplayString(SIZE (1..32))
        MAX-ACCESS    read-create
        STATUS        current
        DESCRIPTION   "Used to configure inter-area L2 I-SID redistribution
                       exception isid-list name. Isid values contained by
                       this list will not be subject to the permit/deny rule."
        ::= { rcIsisMultiAreaL2RedistributeIsidEntry 3 }

rcIsisMultiAreaL2RedistributeIsidRowStatus OBJECT-TYPE
        SYNTAX        RowStatus
        MAX-ACCESS    read-create
        STATUS        current
        DESCRIPTION   "Used to create/remove entries from this table."
        ::= { rcIsisMultiAreaL2RedistributeIsidEntry 4 }

-- IS-IS Multi Area Redistribute L2 multicast ISID Table

rcIsisMultiAreaL2RedistributeMcastIsidTable OBJECT-TYPE
     SYNTAX SEQUENCE OF RcIsisMultiAreaL2RedistributeMcastIsidEntry
     MAX-ACCESS   not-accessible
     STATUS       current
     DESCRIPTION  "Table for L2 multicast redistribution
                   per scope I-SID."
     ::= { rcIsisMultiAreaRedistribute 3}

rcIsisMultiAreaL2RedistributeMcastIsidEntry OBJECT-TYPE
     SYNTAX        RcIsisMultiAreaL2RedistributeMcastIsidEntry
     MAX-ACCESS    not-accessible
     STATUS        current
     DESCRIPTION   "Contains information regarding L2
                    multicast redistribution per scope I-SID."
     INDEX        { rcIsisMultiAreaL2RedistributeMcastIsid }
     ::= { rcIsisMultiAreaL2RedistributeMcastIsidTable 1 }

RcIsisMultiAreaL2RedistributeMcastIsidEntry ::=
     SEQUENCE {
            rcIsisMultiAreaL2RedistributeMcastIsid            INTEGER,
            rcIsisMultiAreaL2RedistributeMcastIsidEnable      TruthValue,
            rcIsisMultiAreaL2RedistributeMcastIsidPolicyName  DisplayString,
            rcIsisMultiAreaL2RedistributeMcastIsidRowStatus   RowStatus
     }

rcIsisMultiAreaL2RedistributeMcastIsid OBJECT-TYPE
        SYNTAX        INTEGER (0..16777215)
        MAX-ACCESS    not-accessible
        STATUS        current
        DESCRIPTION   "L2 multicast redistribute scope I-SID."
        ::= { rcIsisMultiAreaL2RedistributeMcastIsidEntry 1 }

rcIsisMultiAreaL2RedistributeMcastIsidEnable OBJECT-TYPE
        SYNTAX        TruthValue
        MAX-ACCESS    read-create
        STATUS        current
        DESCRIPTION   "Used to enable L2 multicast redistribute
                       per scope I-SID."
        DEFVAL        {false}
        ::= { rcIsisMultiAreaL2RedistributeMcastIsidEntry 2 }

rcIsisMultiAreaL2RedistributeMcastIsidPolicyName OBJECT-TYPE
        SYNTAX        DisplayString (SIZE(0..64))
        MAX-ACCESS    read-create
        STATUS        current
        DESCRIPTION   "Used to configure L2 multicast redistribute
                       per scope I-SID policy name."
        ::= { rcIsisMultiAreaL2RedistributeMcastIsidEntry 3 }

rcIsisMultiAreaL2RedistributeMcastIsidRowStatus OBJECT-TYPE
        SYNTAX        RowStatus
        MAX-ACCESS    read-create
        STATUS        current
        DESCRIPTION   "Used to create/remove entries from this table."
        ::= { rcIsisMultiAreaL2RedistributeMcastIsidEntry 4 }

-- IS-IS Multi Area L2 Redistribute multicast ISID list Table

rcIsisMultiAreaL2RedistributeMcastIsidListTable OBJECT-TYPE
     SYNTAX SEQUENCE OF RcIsisMultiAreaL2RedistributeMcastIsidListEntry
     MAX-ACCESS   not-accessible
     STATUS       current
     DESCRIPTION  "Table for L2 multicast redistribution
                   per scope I-SID list."
     ::= { rcIsisMultiAreaRedistribute 4}

rcIsisMultiAreaL2RedistributeMcastIsidListEntry OBJECT-TYPE
     SYNTAX        RcIsisMultiAreaL2RedistributeMcastIsidListEntry
     MAX-ACCESS    not-accessible
     STATUS        current
     DESCRIPTION   "Contains information regarding L2 multicast
                    redistribution per scope I-SID list."
     INDEX        { rcIsisMultiAreaL2RedistributeMcastIsidList }
     ::= { rcIsisMultiAreaL2RedistributeMcastIsidListTable 1 }

RcIsisMultiAreaL2RedistributeMcastIsidListEntry ::=
     SEQUENCE {
            rcIsisMultiAreaL2RedistributeMcastIsidList            DisplayString,
            rcIsisMultiAreaL2RedistributeMcastIsidListEnable      TruthValue,
            rcIsisMultiAreaL2RedistributeMcastIsidListPolicyName  DisplayString,
            rcIsisMultiAreaL2RedistributeMcastIsidListRowStatus   RowStatus
     }

rcIsisMultiAreaL2RedistributeMcastIsidList OBJECT-TYPE
        SYNTAX        DisplayString(SIZE (1..32))
        MAX-ACCESS    not-accessible
        STATUS        current
        DESCRIPTION   "L2 multicast redistribute scope I-SID list."
        ::= { rcIsisMultiAreaL2RedistributeMcastIsidListEntry 1 }

rcIsisMultiAreaL2RedistributeMcastIsidListEnable OBJECT-TYPE
        SYNTAX        TruthValue
        MAX-ACCESS    read-create
        STATUS        current
        DESCRIPTION   "Used to enable L2 multicast L2 multicast
                       redistribution per scope I-SID list."
        DEFVAL        {false}
        ::= { rcIsisMultiAreaL2RedistributeMcastIsidListEntry 2 }

rcIsisMultiAreaL2RedistributeMcastIsidListPolicyName OBJECT-TYPE
        SYNTAX        DisplayString (SIZE(0..64))
        MAX-ACCESS    read-create
        STATUS        current
        DESCRIPTION   "Used to configure L2 multicast redistribution
                       per scope I-SID list policy name."
        ::= { rcIsisMultiAreaL2RedistributeMcastIsidListEntry 3 }

rcIsisMultiAreaL2RedistributeMcastIsidListRowStatus OBJECT-TYPE
        SYNTAX        RowStatus
        MAX-ACCESS    read-create
        STATUS        current
        DESCRIPTION   "Used to create/remove entries from this table."
        ::= { rcIsisMultiAreaL2RedistributeMcastIsidListEntry 4 }

-- IS-IS Multi Area L3 Redistribute Table

rcIsisMultiAreaL3RedistributeTable OBJECT-TYPE
     SYNTAX SEQUENCE OF RcIsisMultiAreaL3RedistributeEntry
     MAX-ACCESS   not-accessible
     STATUS       current
     DESCRIPTION  "Table for L3 redistribute."
     ::= { rcIsisMultiAreaRedistribute 5}

rcIsisMultiAreaL3RedistributeEntry OBJECT-TYPE
     SYNTAX        RcIsisMultiAreaL3RedistributeEntry
     MAX-ACCESS    not-accessible
     STATUS        current
     DESCRIPTION   "Contains information regarding L3
                    redistribute."
     INDEX        { rcIsisMultiAreaL3RedistributeVrfId, rcIsisMultiAreaL3RedistributeType }
     ::= { rcIsisMultiAreaL3RedistributeTable 1 }

RcIsisMultiAreaL3RedistributeEntry ::=
     SEQUENCE {
            rcIsisMultiAreaL3RedistributeVrfId         VrfIdentifier,
            rcIsisMultiAreaL3RedistributeType          INTEGER,
            rcIsisMultiAreaL3RedistributeMetric        INTEGER,
            rcIsisMultiAreaL3RedistributeMetricType    INTEGER,
            rcIsisMultiAreaL3RedistributeRoutePolicy   DisplayString,
            rcIsisMultiAreaL3RedistributeEnable        TruthValue,
            rcIsisMultiAreaL3RedistributeApply         INTEGER,
            rcIsisMultiAreaL3RedistributeRowStatus     RowStatus
     }


rcIsisMultiAreaL3RedistributeVrfId OBJECT-TYPE
		SYNTAX VrfIdentifier
		MAX-ACCESS not-accessible
		STATUS current
		DESCRIPTION " Indicates the Virtual Router to which the
		L3 redistribute entry belongs."
		::= { rcIsisMultiAreaL3RedistributeEntry 1 }

rcIsisMultiAreaL3RedistributeType OBJECT-TYPE
        SYNTAX        INTEGER  {
                        ip-ucast(1),
                        ip-mcast(2),
                        ipv6-ucast(3)
                        }
        MAX-ACCESS    not-accessible
        STATUS        current
        DESCRIPTION   "L3 redistribute type.
                       Configurable values are:
                        ip-ucast(1)   - IPv4 unicast
                        ip-mcast(2)   - IPv4 multicast
                        ipv6-ucast(3) - IPv6 unicast"
        ::= { rcIsisMultiAreaL3RedistributeEntry 2 }

rcIsisMultiAreaL3RedistributeMetric OBJECT-TYPE
        SYNTAX        INTEGER (0..65535)
        MAX-ACCESS    read-create
        STATUS        current
        DESCRIPTION   "Used to configure L3 redistribute
                       metric. Applies only to ip-ucast
                       and ipv6-ucast entries."
        DEFVAL        {0}
        ::= { rcIsisMultiAreaL3RedistributeEntry 3 }

rcIsisMultiAreaL3RedistributeMetricType OBJECT-TYPE
        SYNTAX        INTEGER {
                          any(1),
                          internal(2),
                          external(3)
                      }
        MAX-ACCESS    read-create
        STATUS        current
        DESCRIPTION   "Used to configure L3 redistribute
                       metric type. Applies only to ip-ucast
                       and ipv6-ucast entries."
       DEFVAL        {any}
        ::= { rcIsisMultiAreaL3RedistributeEntry 4 }

rcIsisMultiAreaL3RedistributeRoutePolicy OBJECT-TYPE
        SYNTAX        DisplayString(SIZE(0..64))
        MAX-ACCESS    read-create
        STATUS        current
        DESCRIPTION   "Used to associate a route policy
                       to an L3 redistribute entry."
        ::= { rcIsisMultiAreaL3RedistributeEntry 5 }

rcIsisMultiAreaL3RedistributeEnable OBJECT-TYPE
        SYNTAX        TruthValue
        MAX-ACCESS    read-create
        STATUS        current
        DESCRIPTION   "Enable L3 redistribute."
        DEFVAL        {false}
        ::= { rcIsisMultiAreaL3RedistributeEntry 6 }

rcIsisMultiAreaL3RedistributeApply OBJECT-TYPE
		SYNTAX INTEGER {
				noAction(1),
				apply(2)
				}
		MAX-ACCESS read-create
		STATUS current
		DESCRIPTION "Used to Apply IS-IS multi area L3 filters.
		When the value is set to apply, all the elements of the specified entry in rcIsisMultiAreaL3RedistributeTable will be applied.
		This may be a disruptive operation to traffic.
		The get will always return noAction."
		DEFVAL { noAction }
		::= { rcIsisMultiAreaL3RedistributeEntry 7 }

rcIsisMultiAreaL3RedistributeRowStatus OBJECT-TYPE
        SYNTAX        RowStatus
        MAX-ACCESS    read-create
        STATUS        current
        DESCRIPTION   "Used to create/remove entries
                       from this table."
        ::= { rcIsisMultiAreaL3RedistributeEntry 8 }

-- IS-IS Multi Area L2 ISID list Table

rcIsisMultiAreaL2IsidListTable OBJECT-TYPE
     SYNTAX SEQUENCE OF RcIsisMultiAreaL2IsidListEntry
     MAX-ACCESS   not-accessible
     STATUS       current
     DESCRIPTION  "Table for L2 isid list."
     ::= { rcIsisMultiArea 3}

rcIsisMultiAreaL2IsidListEntry OBJECT-TYPE
     SYNTAX        RcIsisMultiAreaL2IsidListEntry
     MAX-ACCESS    not-accessible
     STATUS        current
     DESCRIPTION   "Contains information regarding L2
                    isid list."
     INDEX        { rcIsisMultiAreaL2IsidListName, rcIsisMultiAreaL2IsidListRangeStart }
     ::= { rcIsisMultiAreaL2IsidListTable 1 }

RcIsisMultiAreaL2IsidListEntry ::=
     SEQUENCE {
            rcIsisMultiAreaL2IsidListName          DisplayString,
            rcIsisMultiAreaL2IsidListRangeStart    INTEGER,
            rcIsisMultiAreaL2IsidListRangeEnd      INTEGER,
            rcIsisMultiAreaL2IsidListRowStatus     RowStatus
     }

rcIsisMultiAreaL2IsidListName OBJECT-TYPE
        SYNTAX        DisplayString(SIZE (1..32))
        MAX-ACCESS    not-accessible
        STATUS        current
        DESCRIPTION   "L2 isid list name."
        ::= { rcIsisMultiAreaL2IsidListEntry 1 }

rcIsisMultiAreaL2IsidListRangeStart OBJECT-TYPE
        SYNTAX        INTEGER (0..16777215)
        MAX-ACCESS    read-create
        STATUS        current
        DESCRIPTION   "Used to configure L2 isid list range start."
        ::= { rcIsisMultiAreaL2IsidListEntry 2 }

rcIsisMultiAreaL2IsidListRangeEnd OBJECT-TYPE
        SYNTAX        INTEGER (0..16777215)
        MAX-ACCESS    read-create
        STATUS        current
        DESCRIPTION   "Used to configure L2 isid list range end."
        ::= { rcIsisMultiAreaL2IsidListEntry 3 }

rcIsisMultiAreaL2IsidListRowStatus OBJECT-TYPE
        SYNTAX        RowStatus
        MAX-ACCESS    read-create
        STATUS        current
        DESCRIPTION   "Used to create/remove entries from this table."
        ::= { rcIsisMultiAreaL2IsidListEntry 6 }

END
