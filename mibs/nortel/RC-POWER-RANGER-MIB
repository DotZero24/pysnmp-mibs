RC-POWER-RANGER-MIB DEFINITIONS ::= BEGIN

IMPORTS
    MODULE-IDENTITY, OBJECT-TYPE, Integer32, Counter64, IpAddress
        FROM SNMPv2-SMI
    TEXTUAL-CONVENTION, DisplayString, TruthValue, MacAddress, RowStatus
        FROM SNMPv2-TC
    InterfaceIndex
        FROM IF-MIB
    rcPowerRanger, PortSet, IdList, EnableValue
        FROM RAPID-CITY
    Ipv6Address
        FROM IPV6-TC
    Ipv6NextHdr
        FROM RC-IPV6-MIB;


rcPowerRangerMib MODULE-IDENTITY
       LAST-UPDATED     "202010090000Z"
       ORGANIZATION     "Avaya"
       CONTACT-INFO     "Hellen Krikorian"
       DESCRIPTION      "Enterprise MIB for the Power Ranger product."

       REVISION         "202010090000Z" --  09 Oct 2020
       DESCRIPTION      "Version 58: Add rcPrFilterAclOrigin
				     Requested by Adi P (Oana)"

       REVISION         "201904160000Z" --  16 Apr 2019
       DESCRIPTION      "Version 56: Change Integer32 to INTEGER for
	   			     rcPrFilterAceIpRoutedAclId,
				     rcPrFilterAceIpRoutedAceId,
				     rcPrFilterAceIpv6RoutedAclId,
				     rcPrFilterAceIpv6RoutedAceId.
				     (Prem)"

       REVISION         "201904150000Z" --  15 Apr 2019
       DESCRIPTION      "Version 55: Add rcPrFilterAceIpShowRoutedOnly,
	   			     rcPrFilterAceIpv6ShowRoutedOnly,
				     rcPrFilterAceIpRoutedTable and
				     rcPrFilterAceIpv6RoutedTable.
				     Requested by Blued Abraham (Prem)"

       REVISION         "201710260000Z" --  26 Oct 2017
       DESCRIPTION      "Version 54: Change in inNni(5) to inVsn(5) for object
	                             rcPrFilterAclType.
				     Added rcPrFilterAclMatchType,
				     rcPrFilterAclIsid"

       REVISION         "201709270000Z" --  27 Sept 2017
       DESCRIPTION      "Version 53: Added in inNni(5) to the rcPrFilterAclType.
	                             Added rcPrFilterAceVrfTable (Marty)"

       REVISION         "201703010000Z" --  01 March 2017
       DESCRIPTION      "Version 52: Corrected MIB compiler error."

       REVISION         "201702170000Z" --  17 February 2017
       DESCRIPTION      "Version 51: Added rcPrQosCosQueVoqPortStatsTable
	   		 and rcPrQosCosQueVoqCppPortStatsTable.
			 Requested by Dan Crisan (prempa)"

       REVISION         "201702010000Z" --  01 February 2017
       DESCRIPTION      "Version 50: Corrected MIB compiler error."

       REVISION "201612050000Z" -- 05 December 2016
       DESCRIPTION      "Version 49:  Added rcPrFilterAceRedirectNextHopVrfName
		         Requested by Asutosh Satapathy (zuyanwa)"

       REVISION "201609010000Z" -- 01 September 2016
       DESCRIPTION      "Version 48:  Increased the range of
	   		 rcPrFilterActProtocolAttrs from 0..63 to
			 0..127 to add icmpv6MsgType(64).
			 Added rcPrFilterAceProtoShowIcmpv6MsgTypeList and
			 rcPrFilterAceProtoShowIcmpv6MsgTypeOper under
			 rcPrFilterAceProtoShowTable.
			 Added rcPrFilterAceProtoIcmpv6MsgTypeTable.
		         Requested by Dave Tannheimer (prempa)"

       REVISION "201606170000Z" -- 17 May 2016
       DESCRIPTION      "Version 47:  Added rcPrFilterAceRemoveTag
		         Requested by Amit Choudhary (prempa)"

       REVISION "201603250000Z" -- 25 March 2016
       DESCRIPTION      "Version 46:  Added rcPrFilterAceMonitoringIsidOffset,
			    rcPrFilterAceMonitoringIsid and
			    rcPrFilterAceMirroringQos
		         Requested by Amit Choudhary (prempa)"

       REVISION         "201411130000Z" --  13 Nov 2014
       DESCRIPTION      "Version 45: correct rcPrFilterAceProtoShowRoutingTypeType"
       REVISION         "201410080000Z" --  08 Oct. 2014
       DESCRIPTION      "Version 44: Added rcPrFilterAceProtoShowRoutingTypeType
	                             and rcPrFilterAceProtoShowRoutingTypeOper "


       REVISION         "201406260000Z" --  26 June 2014
       DESCRIPTION      "Version 43: Added rcPrFilterAceProtoRoutingTypeTable"

       REVISION         "201406020000Z" --  02 June 2014
       DESCRIPTION      "Version 42: Increased the range of rcPrQosCosQuePortStatsIndex from
	   			     192..241 to 192..297."

       REVISION         "201310110000Z" --  11 October 2013
       DESCRIPTION      "Version 41: Corrected MIB compiler errors.
                         Removed the second definition of rcPrQosEgressQosToExpRowStatus."

       REVISION         "201304180000Z" --  18 Apr. 2013
       DESCRIPTION      "Version 40: added rcPrQosCosQuePortStatsTable
	                                  rcPrQosCosQueLoopbackPortStatsTable
					  rcPrQosCosQueCppPortStatsTable
					  rcPrQosCosQue"

       REVISION         "201206120000Z" --  12 June 2012
       DESCRIPTION      "Version 39: Added nonipv6 to object rcPrFilterAclPktType,
	   			     Update description for rcPrFilterAceIpv6SrcAddrListCount,
				     rcPrFilterAceIpv6DstAddrListCount"

       REVISION         "201206070000Z" --  07 June 2012
       DESCRIPTION      "Version 38: Added rcPrFilterAceIpv6ShowTrafficClsOper,
                                           rcPrFilterAceIpv6ShowTrafficCls,
                                           rcPrFilterAceIpv6ShowSrcAddrMask,
                                           rcPrFilterAceIpv6ShowDstAddrMask
                             to SEQUENCE clause of rcPrFilterAceIpv6ShowTable"

       REVISION         "201203070000Z" --  07 March 2012
       DESCRIPTION      "Version 37: Added rcPrQosLosslessPortsEnablePending,
                                           rcPrQosLosslessPortsOperPending,
                                           in VSP devint 3.3"

       REVISION         "201112140000Z" --  14 December 2011
       DESCRIPTION      "Version 36: Added rcPrQosLosslessPfcEnabled"

       REVISION         "201108220000Z" --  22 August 2011
       DESCRIPTION      "Version 35: Updated rcPrFilterAceIpv6SrcAddrOper,
                                     Added rcPrFilterAceIpv6SrcAddrOperMask,
                                     Updated rcPrFilterAceIpv6DstAddrOper,
                                     Added rcPrFilterAceIpv6DstAddrOperMask,
                                           rcPrFilterAceIpv5ShowTrafficClsOper,
                                           rcPrFilterAceIpv6ShowTrafficCls,
                                           rcPrFilterAceIpv6ShowSrcAddrMask,
                                           rcPrFilterAceIpv6ShowDstAddrMask,
                                     Updated rcPrFilterAceIpv6ShowSrcAddrOper,
                                     Updated rcPrFilterAceIpv6ShowDstAddrOper,
                                     Added rcPrFilterAceIpv6TrafficClsTable"


       REVISION         "201106160000Z" --  16 June 2011
       DESCRIPTION      "Version 34: Added rcPrQosLossless8021p"

       REVISION         "201102040000Z" --  04 February 2011
       DESCRIPTION      "Version 33: Added rcPrFilterAclIpfixState"

       REVISION         "201011040000Z" --  04 November 2010
       DESCRIPTION      "Version 32: Added rcPrFilterAceDstIp,
                                           rcPrFilterAceDstIpTtl,
                                           rcPrFilterAceDstIpDscp"

       REVISION         "201011020000Z" --  02 November 2010
       DESCRIPTION      "Version 31: Added rcPrQosFlowPolicerStatsClear"

       REVISION         "201009150000Z" --  15 September 2010
       DESCRIPTION      "Version 30: Updated size for rcPrFilterAceTableSize,
                                     Added rcPrFilterAclBufferWrap,
                                           rcPrFilterAclClearLog,
                                     Added rcPrFilterAclControlPktRule,
                                           rcPrFilterAclVlanId,
                                           rcPrFilterAclMltId,
                                           rcPrFilterAclDstPortList to
                                                 rcPrFilterAclTable.
                         Added rcPrFilterAclStatsMatchDefaultSecurityPkts,
                               rcPrFilterAclStatsMatchDefaultSecurityOctets,
                               rcPrFilterAclStatsMatchDefaultQosPkts,
                               rcPrFilterAclStatsMatchDefaultQosOctets,
                               rcPrFilterAclStatsMatchGlobalSecurityPkts,
                               rcPrFilterAclStatsMatchGlobalSecurityOctets,
                               rcPrFilterAclStatsMatchGlobalQosPkts,
                               rcPrFilterAclStatsMatchGlobalQosOctets
                                    to rcPrFilterAclStatsTable.
                         Added rcPrFilterAceInternalQos,
                               rcPrFilterAceCount,
                               rcPrFilterAceLog,
                               rcPrFilterAceCopytoPcap
                                    to rcPrFilterAceTable.
                         Added rcPrFilterAceEthSrcAddrOperMask
                                    to rcPrFilterAceEthSrcAddrTable.
                         Added rcPrFilterAceEthDstAddrOperMask
                                    to rcPrFilterAceEthDstAddrTable.
                         Added rcPrFilterAceEthVlanTagPrioOperMask
                                    to rcPrFilterAceEthVlanTagPrioTable
                         Added rcPrFilterAceEthVlanIdOperMask,
                               rcPrFilterAceEthVlanIdVlanId
                                    to rcPrFilterAceEthVlanIdTable.
                         Added rcPrFilterAceIpSrcAddrIpAddr,
                               rcPrFilterAceIpSrcAddrOperMaskRange
                                    to rcPrFilterAceIpSrcAddrTable.
                         Added rcPrFilterAceIpDstAddrIpAddr,
                               rcPrFilterAceIpDstAddrOperMaskRange
                                    to rcPrFilterAceIpDstAddrTable.
                         Added rcPrFilterAceIpDscpOperMask
                                    to rcPrFilterAceIpDscpTable.
                         Added rcPrFilterAceProtoTcpFlagsOperMask
                                    to rcPrFilterAceProtoTcpFlagsTable.
                         Updated upper range of rcPrFilterAceStatsPortId.
                         Added rcPrFilterAceEthShowSrcAddrOperMask,
        		       rcPrFilterAceEthShowDstAddrOperMask,
                               rcPrFilterAceEthShowVlanTagPrioOperMask,
                               rcPrFilterAceEthShowVlanIdOperMask,
                               rcPrFilterAceEthShowVlanId
                                    to rcPrFilterAceEthShowTable.
                         Added rcPrFilterAceIpShowSrcAddrIpAddr,
                               rcPrFilterAceIpShowSrcAddrOperMaskRange,
                               rcPrFilterAceIpShowDstAddrIpAddr,
                               rcPrFilterAceIpShowDstAddrOperMaskRange,
                               rcPrFilterAceIpShowDscpOperMask
                                    to rcPrFilterAceIpShowTable
                         Added rcPrFilterAceProtoShowSrcPort,
                               rcPrFilterAceProtoShowSrcPortOper,
                               rcPrFilterAceProtoShowSrcPortOperMaskRange,
                               rcPrFilterAceProtoShowDstPort,
                               rcPrFilterAceProtoShowDstPortOper,
                               rcPrFilterAceProtoShowDstPortOperMaskRange,
                               rcPrFilterAceProtoShowTcpFlagsOperMask
                                    to rcPrFilterAceProtoShowTable
                         Added rcPrFilterAceProtoSrcPortTable,
                               rcPrFilterAceProtoDstPortTable,
                               rcPrFilterAceProtoTcpOptionTablex

                         Updated ACE IDs from 1000 to 2000.
                         Added several new mask fields to several filter
                            table operator fields."


       REVISION         "200912110000Z" --  11 December 2009
       DESCRIPTION      "Version 29: Changed max-access value for rcPrFilterAclId from non-accessible to read-only."

       REVISION         "200910200000Z" -- 20 October 2009
       DESCRIPTION      "Version 28: Added the following fields to the rcPrQosLocalPolicyTable:
                            rcPrQosLocalPolicyGreenPackets, rcPrQosLocalPolicyGreenBytes,
                            rcPrQosLocalPolicyYellowPacket, rcPrQosLocalPolicyYellowBytes,
                            rcPrQosLocalPolicyRedPackets, rcPrQosLocalPolicyRedBytes,
                            rcPrQosLocalPolicyStatsClear"

       REVISION         "200907020000Z" -- 02 July 2009
       DESCRIPTION      "Version 27: Changed syntax and description for rcPrQosSubportQueueSetTemplateMinRate and rcPrQosSubportQueueSetTemplateMaxRate."

       REVISION         "200805100000Z" --  09 May 2008
       DESCRIPTION      "Version 26: Fixed smilint errors."

       REVISION         "200804030000Z" -- 03 April 2008
       DESCRIPTION      "Version 25: Changed the default value for rcPrFilterAceEgressQueue from 64 to 8"

       REVISION         "200803140000Z" -- 14 March 2008
       DESCRIPTION      "Version 24: Changed syntax for rcPrFilterAceIpv6NextHdrNextHdr and rcPrFilterAceIpv6ShowNxtHdrNxtHdr  from INTEGER to Ipv6NextHdr."

       REVISION         "200709060000Z" -- 06 Sept 2007
       DESCRIPTION      "Version 23: Changed syntax for rcPrFilterAceDstVlanId from Integer32 to INTEGER"

       REVISION         "200709040000Z" -- 04 Sept 2007
       DESCRIPTION      "Version 22: Added mib objects to rcPrFilterAceTable"

       REVISION         "200708230000Z" -- 23 Aug 2007
       DESCRIPTION      "Version 21: Added rcPrQosSubportProfileQueueQPriority,
	 				   rcPrQosSubportQueueSetEqmapTable"

       REVISION         "200705140000Z" -- 14 May 2007
       DESCRIPTION      "Version 20: Updated rcPrQosSubportQueueSetTemplateMinRate and
 					     rcPrQosSubportQueueSetTemplateMaxRate"

       REVISION         "200704180000Z" -- 18 Apr 2007
       DESCRIPTION      "Version 19: Added rcPrQosSubportQueueSetTemplateTable, rcPrQosIsidRateLimitsTable,
					   rcPrQosIsidRateLimitsIsidTable, rcPrQosSubportProfileTable and
 					   rcPrQosSubportProfileQueueTable "

       REVISION         "200702050000Z" -- 05 Feb 2006
       DESCRIPTION      "Version 18: Added rcPrQosIngressExpToQosTable and rcPrQosEgressQosToExpTable"

       REVISION         "200602240000Z" -- 24 Feb 2006
       DESCRIPTION      "Version 17: Added rcPrFilterAceRedirectNextHopIpv6 attribute in RcPrFilterAceEntry"

       REVISION         "200602090000Z" -- 09 Feb 2006
       DESCRIPTION      "Version 16: Updated rcPrFilterAceIpv6NextHdrNextHdr and added ACE IPv6 Show Table"

       REVISION         "200511220000Z" -- 22 Nov 2005
       DESCRIPTION      "Version 15: Added rcPrFilterActIpv6Attrs, rcPrFilterAclPktType, and a table at rcPrFilterAce 29"

       REVISION         "200509140000Z" -- 14 Sep 2005
       DESCRIPTION      "Version 14: Updated rcPrFilterIpfixState & rcPrFilterAclGlobalAction"

       REVISION         "200502180000Z" -- 18 February 2005
       DESCRIPTION      "Version 13: Changes the range for rcPrQosLocalPolicyIndex
                         value to 0-16383"

       REVISION         "200502150000Z" -- 15 February 2005
       DESCRIPTION      "Version 12: Changed the mapping of Egress-Queue NNSC
                         strings to Integer values as per the Functional
                         specifications"

       REVISION         "200502140000Z" -- 14 February 2005
       DESCRIPTION      "Version 11: Added range for rcPrQosLocalPolicyIndex value
                         for SMIv2 compliancy"

       REVISION         "200502020000Z" -- 02 February 2005
       DESCRIPTION      "Version 10: Remove references for 'undefined' in Power Ranger
		MIB attributes."

       REVISION         "200501180000Z" -- 18 January 2005
       DESCRIPTION      "Version 9: Adding LaneSet with TEXTUAL-CONVENTION.MOdified
                         rcPrQosPolicyLaneMembers from OCTET STRING to LaneSet"

       REVISION         "200501140000Z" -- 14 January 2005
       DESCRIPTION      "Version 8: Resolution of MIB conflicts with ClearCase.  Changes are
		associated with these MIB attributes: rcPrQosPolicyRowStatus,
		rcPrQosPolicyLaneChange, rcPrQosLocalPolicyGpId,
		rcPrQosLocalPolicyIndex, rcPrFilterAceMode, rcPrFilterAce*Show*Oper
		attributes."

       REVISION         "200409300000Z" -- 30 September 2004
       DESCRIPTION      "Version 7: A number of changes were made for Power
			Ranger Filter and QoS usability as well as for fixing
			some issues required for SNMP/JDM to work."

       REVISION         "200408240000Z" -- 24 August 2004
       DESCRIPTION      "Version 6: Changes done in rcPrQosLocalPolicyLaneMember
		         to add lane member information.
                         Modified the rcPrQosTxQueueTemplateId and rcPrQosTxQueueTid
			 max value to 386.
                         Modified the values of Filter Operators to match
                         the CP-COP Interface values.
                         Changed the default value of rcPrFilterAceMode to 'none'.
                         Changed the SYNTAX of rcPrQosTxQueueStatsPort to InterfaceIndex."

       REVISION         "200408170000Z" -- 17 August 2004
       DESCRIPTION      "Version 5: Additional changes made due to agent
                         changes or changes required for SNMP/JDM to work."

       REVISION         "200407200000Z" -- 20 July 2004
       DESCRIPTION      "Version 4: Added version info"

       REVISION         "200406110000Z"
       DESCRIPTION      "Major revision, note that previous versions of
                         this MIB were never actually used in products."

       REVISION         "200402110000Z"
       DESCRIPTION      "The initial version."

       ::= { rcPowerRanger 1 }

rcPowerRangerNotifications OBJECT IDENTIFIER ::= { rcPowerRangerMib 0 }
rcPowerRangerObjects       OBJECT IDENTIFIER ::= { rcPowerRangerMib 1 }

--
-- Object groups within the Power Ranger MIB
--

rcPrQos    OBJECT IDENTIFIER ::= { rcPowerRangerObjects 1 }
rcPrFilter OBJECT IDENTIFIER ::= { rcPowerRangerObjects 2 }

--
-- The rcPrQos group
--

rcPrQosScalars OBJECT IDENTIFIER ::= { rcPrQos 1 }

LaneSet ::= TEXTUAL-CONVENTION
  STATUS       current
  DESCRIPTION
              "The set of lanes that are members of this Global
               Policer. The string is 4 octets long, for a total
               of 32 bits. Each bit corresponds to a laneId.
               Each I/O slot has 4 laneIds. When a bit has the
               value one(1), the corresponding laneId is a member
               of the set. When a bit has the value zero(0), the
               corresponding laneId is not a member of the set.
               The encoding is such that the most significant bit
               of octet #1 corresponds to laneId 0, while the
               least significant bit of octet #4 corresponds to
               laneId 31."
  SYNTAX      OCTET STRING (SIZE (4))

rcPrQosPolicyNumPolicies OBJECT-TYPE
        SYNTAX           INTEGER (0..12288)
        MAX-ACCESS       read-only
        STATUS           current
        DESCRIPTION      "A list of Global Policer (GPID) entries.
	                 The number of entries is given by
                         rcPrQosPolicyNumPolicies."
        ::= { rcPrQosScalars 1 }

rcPrQosTxQueueNumTemplates  OBJECT-TYPE
        SYNTAX        	INTEGER (0..383)
        MAX-ACCESS    	read-only
        STATUS        	current
        DESCRIPTION   	"The number of egress queue templates currently
		      	defined in the switch."
        ::= { rcPrQosScalars 2 }

rcPrQosFlowPolicerStatsClear  OBJECT-TYPE
        SYNTAX             TruthValue
        MAX-ACCESS         read-write
        STATUS             current
        DESCRIPTION        "Clear all box-wide policer statistics."
        ::= { rcPrQosScalars 3 }

rcPrQosLossless8021p  OBJECT-TYPE
        SYNTAX        Integer32 (0..6)
        MAX-ACCESS    read-write
        STATUS        current
        DESCRIPTION   "The value used to map Ingress IEEE 1p to lossless
                       internal Qos when lossless Ethernet mode is enabled."
        ::= { rcPrQosScalars 4 }

rcPrQosLosslessPfcEnabled  OBJECT-TYPE
        SYNTAX        TruthValue
        MAX-ACCESS    read-only
        STATUS        current
        DESCRIPTION   "If true then at least one lossless port in the
                       switch has been configured with the value of
                       rcPortLosslessEnetPauseType set to pfc(2).
                       If false then either all lossless ports are currently
                       in fc(1) mode, or no ports are configured in
                       lossless mode."
        ::= { rcPrQosScalars 5 }

rcPrQosLosslessPortsEnablePending  OBJECT-TYPE
        SYNTAX        PortSet
        MAX-ACCESS    read-write
        STATUS        current
        DESCRIPTION   "This object is used to inform the system which ports
                       are pending lossless enable and is for internal use."
        ::= { rcPrQosScalars 6 }

rcPrQosLosslessPortsOperPending  OBJECT-TYPE
        SYNTAX        DisplayString (SIZE(0..255))
        MAX-ACCESS    read-only
        STATUS        current
        DESCRIPTION   "Indicates which ports which would be brought down
                       operationally if the set of ports indicated in
                       rcPrQosLosslessPortsEnablePending are configured
                       for lossless operation."
        ::= { rcPrQosScalars 7 }

-- Power Ranger Qos Policy Policers Table
rcPrQosPolicyTable      OBJECT-TYPE
        SYNTAX          SEQUENCE OF RcPrQosPolicyEntry
        MAX-ACCESS      not-accessible
        STATUS          current
        DESCRIPTION     "A list of GPID entries. The number of entries is
                        given by rcPrQosPolicyNumPolicies."
        ::= { rcPrQos 2 }

rcPrQosPolicyEntry      OBJECT-TYPE
        SYNTAX          RcPrQosPolicyEntry
        MAX-ACCESS      not-accessible
        STATUS          current
        DESCRIPTION     "Entry containing configuration information for a
                        particular global policer."
        INDEX           { rcPrQosPolicyGpId }
        ::= { rcPrQosPolicyTable 1 }

RcPrQosPolicyEntry ::= SEQUENCE {
                rcPrQosPolicyGpId             INTEGER,
                rcPrQosPolicyName             DisplayString,
                rcPrQosPolicyPeakRate         INTEGER,
                rcPrQosPolicySvcRate          INTEGER,
                rcPrQosPolicyLaneMembers      LaneSet,
                 rcPrQosPolicyRowStatus        RowStatus
                }

rcPrQosPolicyGpId       OBJECT-TYPE
        SYNTAX          INTEGER (1..16383)
        MAX-ACCESS      not-accessible
        STATUS          current
        DESCRIPTION     "A value that uniquely identifies Global Policer
                        associated with this entry."
        ::= { rcPrQosPolicyEntry 1 }

rcPrQosPolicyName       OBJECT-TYPE
        SYNTAX          DisplayString (SIZE (0..32))
        MAX-ACCESS      read-create
        STATUS          current
        DESCRIPTION     "An administratively-assigned name for this Global
                        Policer."
        ::= { rcPrQosPolicyEntry 2 }

rcPrQosPolicyPeakRate   OBJECT-TYPE
        SYNTAX          INTEGER (0..10000000)
        MAX-ACCESS      read-create
        STATUS          current
        DESCRIPTION     "Global Policer Peak Rate in Kilobit/sec."
        ::= { rcPrQosPolicyEntry 3 }

rcPrQosPolicySvcRate    OBJECT-TYPE
        SYNTAX          INTEGER (0..10000000)
        MAX-ACCESS      read-create
        STATUS          current
        DESCRIPTION     "Global Policer Service Rate in Kilobit/sec."
        ::= { rcPrQosPolicyEntry 4 }

rcPrQosPolicyLaneMembers      OBJECT-TYPE
        SYNTAX          LaneSet
        MAX-ACCESS      read-create
        STATUS          current
        DESCRIPTION     "The set of lanes that are members of this Global
                        Policer. The string is 4 octets long, for a total
			of 32 bits. Each bit corresponds to a laneId.
			Each I/O slot has 4 laneIds. When a bit has the
			value one(1), the corresponding laneId is a member
			of the set. When a bit has the value zero(0), the
			corresponding laneId is not a member of the set.
			The encoding is such that the most significant bit
			of octet #1 corresponds to laneId 0, while the
			least significant bit of octet #4 corresponds to
			laneId 31."
        ::= { rcPrQosPolicyEntry 5 }

rcPrQosPolicyRowStatus  OBJECT-TYPE
        SYNTAX          RowStatus
        MAX-ACCESS      read-create
        STATUS          current
        DESCRIPTION     "Create/delete operations for this entry."
        ::= { rcPrQosPolicyEntry 6}

-- Power Ranger Qos Local Policer Table

rcPrQosLocalPolicyTable OBJECT-TYPE
        SYNTAX          SEQUENCE OF RcPrQosLocalPolicyEntry
        MAX-ACCESS      not-accessible
        STATUS          current
        DESCRIPTION     "A list of local (aka physical) policer entries."
        ::= { rcPrQos 3 }

rcPrQosLocalPolicyEntry OBJECT-TYPE
        SYNTAX          RcPrQosLocalPolicyEntry
        MAX-ACCESS      not-accessible
        STATUS          current
        DESCRIPTION     "An entry containing configuration information for
                        a particular local policer."
        INDEX           { rcPrQosLocalPolicyGpId,
                           rcPrQosLocalPolicyIndex }
        ::= { rcPrQosLocalPolicyTable 1 }

RcPrQosLocalPolicyEntry ::= SEQUENCE {
                rcPrQosLocalPolicyGpId                 INTEGER,
                rcPrQosLocalPolicyIndex                 Integer32,
                rcPrQosLocalPolicyPeakRate              INTEGER,
                rcPrQosLocalPolicySvcRate               INTEGER,
                rcPrQosLocalPolicyTotalPkts             Counter64,
                rcPrQosLocalPolicyTotalBytes            Counter64,
                rcPrQosLocalPolicyBytesOverPeak         Counter64,
                rcPrQosLocalPolicyBytesOverSvc          Counter64,
                rcPrQosLocalPolicyTotalPktsDropped      Counter64,
                rcPrQosLocalPolicyLaneMember            OCTET STRING,
                rcPrQosLocalPolicyGreenPackets		Counter64,
		rcPrQosLocalPolicyGreenBytes		Counter64,
		rcPrQosLocalPolicyYellowPackets		Counter64,
		rcPrQosLocalPolicyYellowBytes		Counter64,
		rcPrQosLocalPolicyRedPackets		Counter64,
		rcPrQosLocalPolicyRedBytes		Counter64,
		rcPrQosLocalPolicyStatsClear		TruthValue
		}

rcPrQosLocalPolicyGpId OBJECT-TYPE
        SYNTAX          INTEGER (1..16383)
        MAX-ACCESS      not-accessible
        STATUS          current
        DESCRIPTION     "A value of Global Policer ID corresponding to this
	                local policer."
        ::= { rcPrQosLocalPolicyEntry 1 }

rcPrQosLocalPolicyIndex OBJECT-TYPE
        SYNTAX          Integer32 (0..16383)
        MAX-ACCESS      not-accessible
        STATUS          current
        DESCRIPTION     "A value that uniquely identifies the local Policer
                        associated with this entry. Concatenation of
                        tap.lane.lpid."
        ::= { rcPrQosLocalPolicyEntry 2 }

rcPrQosLocalPolicyPeakRate OBJECT-TYPE
        SYNTAX          INTEGER (0..10000000)
        MAX-ACCESS      read-only
        STATUS          current
        DESCRIPTION     "Local Policer Peak Rate in Kilobit/sec. Equals to
                        that of corresponding Global Policer ID."
        ::= { rcPrQosLocalPolicyEntry 3 }

rcPrQosLocalPolicySvcRate OBJECT-TYPE
        SYNTAX          INTEGER (0..10000000)
        MAX-ACCESS      read-only
        STATUS          current
        DESCRIPTION     "Local Policer Service Rate in Kilobit/sec. Equals to
                        that of corresponding Global Policer ID."
        ::= { rcPrQosLocalPolicyEntry 4 }

rcPrQosLocalPolicyTotalPkts OBJECT-TYPE
        SYNTAX          Counter64
        MAX-ACCESS      read-only
        STATUS          current
        DESCRIPTION     "Local Policer Total Packets Count."
        ::= { rcPrQosLocalPolicyEntry 5 }

rcPrQosLocalPolicyTotalBytes OBJECT-TYPE
        SYNTAX          Counter64
        MAX-ACCESS      read-only
        STATUS          current
        DESCRIPTION     "Local Policer Total Bytes Count."
        ::= { rcPrQosLocalPolicyEntry 6 }

rcPrQosLocalPolicyBytesOverPeak OBJECT-TYPE
        SYNTAX          Counter64
        MAX-ACCESS      read-only
        STATUS          current
        DESCRIPTION     "Local Policer Bytes over Peak Rate Count."
        ::= { rcPrQosLocalPolicyEntry 7 }

rcPrQosLocalPolicyBytesOverSvc OBJECT-TYPE
        SYNTAX          Counter64
        MAX-ACCESS      read-only
        STATUS          current
        DESCRIPTION     "Local Policer Bytes over Service Rate Count."
        ::= { rcPrQosLocalPolicyEntry 8 }

rcPrQosLocalPolicyTotalPktsDropped OBJECT-TYPE
        SYNTAX          Counter64
        MAX-ACCESS      read-only
        STATUS          current
        DESCRIPTION     "The count of Local Policer Total Packets dropped
                        due to reasons other than policing, e.g. congestion."
        ::= { rcPrQosLocalPolicyEntry 9 }

rcPrQosLocalPolicyLaneMember OBJECT-TYPE
        SYNTAX          OCTET STRING (SIZE(0..4))
        MAX-ACCESS      read-only
        STATUS          current
        DESCRIPTION     "The lane that this Gpid has a local policing
                         account on "
        ::= { rcPrQosLocalPolicyEntry 10 }

rcPrQosLocalPolicyGreenPackets OBJECT-TYPE
        SYNTAX        Counter64
        MAX-ACCESS    read-only
        STATUS        current
        DESCRIPTION   "The total number of packets received
                       that were below committed rate."
        ::= { rcPrQosLocalPolicyEntry 11 }

rcPrQosLocalPolicyGreenBytes OBJECT-TYPE
        SYNTAX        Counter64
        MAX-ACCESS    read-only
        STATUS        current
        DESCRIPTION   "The total number of bytes received
                       that were below the committed rate."
        ::= { rcPrQosLocalPolicyEntry 12 }

rcPrQosLocalPolicyYellowPackets OBJECT-TYPE
        SYNTAX        Counter64
        MAX-ACCESS    read-only
        STATUS        current
        DESCRIPTION   "The total number of packets received
                       that were above the committed rate but
                       below the peak rate."
        ::= { rcPrQosLocalPolicyEntry 13 }

rcPrQosLocalPolicyYellowBytes OBJECT-TYPE
        SYNTAX        Counter64
        MAX-ACCESS    read-only
        STATUS        current
        DESCRIPTION   "The total number of bytes received
                       that were above the committed rate but
                       below the peak rate."
        ::= { rcPrQosLocalPolicyEntry 14 }

rcPrQosLocalPolicyRedPackets OBJECT-TYPE
        SYNTAX        Counter64
        MAX-ACCESS    read-only
        STATUS        current
        DESCRIPTION   "The total number of packets received
                       that were above the peak rate."
        ::= { rcPrQosLocalPolicyEntry 15 }

rcPrQosLocalPolicyRedBytes OBJECT-TYPE
        SYNTAX        Counter64
        MAX-ACCESS    read-only
        STATUS        current
        DESCRIPTION   "The total number of bytes received
                       that were above the peak rate."
        ::= { rcPrQosLocalPolicyEntry 16 }

rcPrQosLocalPolicyStatsClear  OBJECT-TYPE
        SYNTAX             TruthValue
        MAX-ACCESS         read-write
        STATUS             current
        DESCRIPTION        "Clear Qos Policy statistics."
        ::= { rcPrQosLocalPolicyEntry 17 }


-- Power Ranger Qos Egress Queue Template Table
rcPrQosTxQueueTemplateTable OBJECT-TYPE
        SYNTAX        	SEQUENCE OF RcPrQosTxQueueTemplateEntry
        MAX-ACCESS    	not-accessible
        STATUS        	current
        DESCRIPTION   	"A list of egress queue templates. The number of
			templates is given by rcPrQosTxQueueNumTemplates."
        ::= { rcPrQos 4 }

rcPrQosTxQueueTemplateEntry OBJECT-TYPE
        SYNTAX        	RcPrQosTxQueueTemplateEntry
        MAX-ACCESS    	not-accessible
        STATUS        	current
        DESCRIPTION   	"Entry containing configuration information for a
                      	particular egress queue template. Queue is a set of
			egress queues."
       	INDEX         	{ rcPrQosTxQueueTemplateId }
        ::= { rcPrQosTxQueueTemplateTable 1 }

RcPrQosTxQueueTemplateEntry ::= SEQUENCE {
                rcPrQosTxQueueTemplateId     		INTEGER,
                rcPrQosTxQueueTemplateName   		DisplayString,
		rcPrQosTxQueueTemplateMaxQueues 	INTEGER,
		rcPrQosTxQueueTemplateBalancedQueues 	INTEGER,
		rcPrQosTxQueueTemplateHiPriQueues 	INTEGER,
		rcPrQosTxQueueTemplateLoPriQueues 	INTEGER,
		rcPrQosTxQueueTemplateTotalQueues 	Integer32,
		rcPrQosTxQueueTemplateBalancedQList 	OCTET STRING,
		rcPrQosTxQueueTemplateHiPriQList 	OCTET STRING,
		rcPrQosTxQueueTemplateLoPriQList 	OCTET STRING,
		rcPrQosTxQueueTemplateTotalQLists	OCTET STRING,
		rcPrQosTxQueueTemplateMinRateTotal 	INTEGER,
		rcPrQosTxQueueTemplateMaxRateHiPri 	INTEGER,
		rcPrQosTxQueueTemplatePortMembers	PortSet,
		rcPrQosTxQueueTemplateFlags		INTEGER,
		rcPrQosTxQueueTemplateApply		TruthValue,
		rcPrQosTxQueueTemplateRowStatus		RowStatus
		}

rcPrQosTxQueueTemplateId OBJECT-TYPE
        SYNTAX        	INTEGER (1..386)
        MAX-ACCESS    	not-accessible
        STATUS        	current
        DESCRIPTION   	"A value that uniquely identifies Egress Queue
	                Template."
        ::= { rcPrQosTxQueueTemplateEntry 1 }

rcPrQosTxQueueTemplateName OBJECT-TYPE
        SYNTAX        	DisplayString (SIZE (0..32))
        MAX-ACCESS    	read-create
        STATUS       	current
        DESCRIPTION   	"An administratively-assigned name for this egress
			Queue Template."
        ::= { rcPrQosTxQueueTemplateEntry 2 }

rcPrQosTxQueueTemplateMaxQueues OBJECT-TYPE
	SYNTAX        	INTEGER {
				eight(8),
				sixtyfour(64)
				}
        MAX-ACCESS    	read-create
        STATUS        	current
	DESCRIPTION   	"Maximum number of queues in this Template."
        ::= { rcPrQosTxQueueTemplateEntry 3 }

rcPrQosTxQueueTemplateBalancedQueues OBJECT-TYPE
        SYNTAX        	INTEGER (0..48)
        MAX-ACCESS    	read-create
        STATUS        	current
        DESCRIPTION   	"Total number of Balanced Queues in this Template."
        ::= { rcPrQosTxQueueTemplateEntry 4 }

rcPrQosTxQueueTemplateHiPriQueues OBJECT-TYPE
        SYNTAX        	INTEGER (0..64)
        MAX-ACCESS    	read-create
        STATUS        	current
        DESCRIPTION   	"Total number of High Priority Queues in this
			Template."
        ::= { rcPrQosTxQueueTemplateEntry 5 }

rcPrQosTxQueueTemplateLoPriQueues OBJECT-TYPE
        SYNTAX        	INTEGER (0..8)
        MAX-ACCESS    	read-create
        STATUS        	current
        DESCRIPTION   	"Total number of Low Priority Queues in this Template."
        ::= { rcPrQosTxQueueTemplateEntry 6 }

rcPrQosTxQueueTemplateTotalQueues OBJECT-TYPE
	SYNTAX        	Integer32
        MAX-ACCESS    	read-only
        STATUS        	current
	DESCRIPTION   	"Total number of queues in this Template."
        ::= { rcPrQosTxQueueTemplateEntry 7 }

rcPrQosTxQueueTemplateBalancedQList OBJECT-TYPE
        SYNTAX        	OCTET STRING (SIZE(0..200))
        MAX-ACCESS    	read-only
        STATUS        	current
        DESCRIPTION   	"List of Balanced Queues in this Template."
        ::= { rcPrQosTxQueueTemplateEntry 8 }

rcPrQosTxQueueTemplateHiPriQList OBJECT-TYPE
        SYNTAX        	OCTET STRING (SIZE(0..200))
        MAX-ACCESS    	read-only
        STATUS        	current
        DESCRIPTION   	"List of High Priority Queues in this Template."
        ::= { rcPrQosTxQueueTemplateEntry 9 }

rcPrQosTxQueueTemplateLoPriQList OBJECT-TYPE
        SYNTAX        	OCTET STRING (SIZE(0..200))
        MAX-ACCESS    	read-only
        STATUS        	current
        DESCRIPTION   	"List of Low Priority Queues in this Template."
        ::= { rcPrQosTxQueueTemplateEntry 10 }

rcPrQosTxQueueTemplateTotalQLists OBJECT-TYPE
        SYNTAX        	OCTET STRING (SIZE(0..600))
        MAX-ACCESS    	read-only
        STATUS        	current
        DESCRIPTION   	"List of Total Physical Queues in this Template."
        ::= { rcPrQosTxQueueTemplateEntry 11 }

rcPrQosTxQueueTemplateMinRateTotal OBJECT-TYPE
        SYNTAX        	INTEGER (0..100)
        MAX-ACCESS    	read-only
        STATUS        	current
        DESCRIPTION   	"Sum of minimum rate guarantees for this template."
        ::= { rcPrQosTxQueueTemplateEntry 12 }

rcPrQosTxQueueTemplateMaxRateHiPri OBJECT-TYPE
        SYNTAX        	INTEGER (0..100)
        MAX-ACCESS    	read-only
        STATUS        	current
        DESCRIPTION   	"Sum of maximum rate guarantees for high priority
			queues of this template."
        ::= { rcPrQosTxQueueTemplateEntry 13 }

rcPrQosTxQueueTemplatePortMembers OBJECT-TYPE
        SYNTAX        	PortSet
        MAX-ACCESS    	read-create
        STATUS        	current
        DESCRIPTION   	"Port members of this template."
        ::= { rcPrQosTxQueueTemplateEntry 14 }

rcPrQosTxQueueTemplateFlags OBJECT-TYPE
        SYNTAX        	INTEGER {
			    created(1),
			    committed(2),
			    modified(3)
			}
        MAX-ACCESS    	read-create
        STATUS        	current
        DESCRIPTION   	"Bitset indicated template state."
	DEFVAL		{ created }
        ::= { rcPrQosTxQueueTemplateEntry 15 }

rcPrQosTxQueueTemplateApply OBJECT-TYPE
        SYNTAX          TruthValue
        MAX-ACCESS      read-create
        STATUS          current
        DESCRIPTION    "When apply is issued by the administrator,
                        the Egress Queue Set attributes are committed."
        DEFVAL          { false }
        ::= { rcPrQosTxQueueTemplateEntry 16 }

rcPrQosTxQueueTemplateRowStatus OBJECT-TYPE
        SYNTAX        	RowStatus
        MAX-ACCESS    	read-create
        STATUS        	current
        DESCRIPTION   	"Create/delete operations for this entry."
        ::= { rcPrQosTxQueueTemplateEntry 17 }

-- Power Ranger Qos Egress Queue Table
rcPrQosTxQueueTable OBJECT-TYPE
        SYNTAX        	SEQUENCE OF RcPrQosTxQueueEntry
        MAX-ACCESS    	not-accessible
        STATUS        	current
        DESCRIPTION   	"A list of elementary Egress queue entries."
        ::= { rcPrQos 5 }

rcPrQosTxQueueEntry OBJECT-TYPE
        SYNTAX        	RcPrQosTxQueueEntry
        MAX-ACCESS    	not-accessible
        STATUS        	current
        DESCRIPTION   	"Entry containing configuration information for a
                      	particular elementary egress queue."
       	INDEX         	{ rcPrQosTxQueueTid,
			  rcPrQosTxQueueQid }
        ::= { rcPrQosTxQueueTable 1 }

RcPrQosTxQueueEntry ::= SEQUENCE {
                rcPrQosTxQueueTid		INTEGER,
                rcPrQosTxQueueQid		INTEGER,
                rcPrQosTxQueueName		DisplayString,
                rcPrQosTxQueueStyle     	INTEGER,
                rcPrQosTxQueueWeight		Integer32,
                rcPrQosTxQueueMaxRate		Integer32,
                rcPrQosTxQueueMinRate		Integer32,
                rcPrQosTxQueueBquantum  	Integer32,
	    	rcPrQosTxQueueMaxLength         Integer32,
		rcPrQosTxQueueWredCurveSet	INTEGER,
		rcPrQosTxQueueRowStatus		RowStatus
		}

rcPrQosTxQueueTid OBJECT-TYPE
  	SYNTAX        	INTEGER (1..386)
        MAX-ACCESS    	not-accessible
        STATUS        	current
        DESCRIPTION   "Template ID of the template this queue belongs to."
        ::= { rcPrQosTxQueueEntry 1 }

rcPrQosTxQueueQid OBJECT-TYPE
        SYNTAX        	INTEGER (0..63)
        MAX-ACCESS    	not-accessible
        STATUS        	current
        DESCRIPTION   	"Queue Offset from the base queue for this port."
        ::= { rcPrQosTxQueueEntry 2 }

rcPrQosTxQueueName OBJECT-TYPE
        SYNTAX        	DisplayString (SIZE (0..32))
        MAX-ACCESS    	read-create
        STATUS       	current
        DESCRIPTION   	"An NNSC name for this egress queue. Allowed only
			for 8 NNSC queues."
        ::= { rcPrQosTxQueueEntry 3 }

rcPrQosTxQueueStyle OBJECT-TYPE
        SYNTAX        	INTEGER {
			    hipri(1),
			    balanced(2),
			    lopri(3)
			}
        MAX-ACCESS    	read-create
        STATUS        	current
        DESCRIPTION   	"Egress queue style."
        ::= { rcPrQosTxQueueEntry 4 }

rcPrQosTxQueueWeight OBJECT-TYPE
        SYNTAX        	Integer32
        MAX-ACCESS    	read-only
        STATUS        	current
        DESCRIPTION   	"Egress queue weight.
			Applicable for balanced queues and lo-pri queues only."
        ::= { rcPrQosTxQueueEntry 5 }

rcPrQosTxQueueMaxRate OBJECT-TYPE
        SYNTAX        	Integer32
        MAX-ACCESS    	read-create
        STATUS        	current
        DESCRIPTION   	"Egress queue maximum rate, Kbs"
        ::= { rcPrQosTxQueueEntry 6 }

rcPrQosTxQueueMinRate OBJECT-TYPE
        SYNTAX        	Integer32
        MAX-ACCESS    	read-create
        STATUS        	current
        DESCRIPTION   	"Egress queue minimun rate guarantee, Kbs.
			Applicable for balanced queues and lo-pri queues only."
        ::= { rcPrQosTxQueueEntry 7 }

rcPrQosTxQueueBquantum OBJECT-TYPE
        SYNTAX        	Integer32
        MAX-ACCESS    	read-only
        STATUS        	current
        DESCRIPTION   	"Bandwidth allocation unit.
			Applicable for balanced queues and lo-pri queues only."
        ::= { rcPrQosTxQueueEntry 8 }

rcPrQosTxQueueMaxLength OBJECT-TYPE
        SYNTAX        	Integer32
        MAX-ACCESS    	read-create
        STATUS        	current
        DESCRIPTION 	"Maximum queue length."
        ::= { rcPrQosTxQueueEntry 9 }

rcPrQosTxQueueWredCurveSet OBJECT-TYPE
        SYNTAX        	INTEGER {
			    tailDrop(1),
			    lowDrop(2),
			    mediumDrop(3),
			    highDrop(4)
			}
        MAX-ACCESS    	read-create
        STATUS        	current
        DESCRIPTION 	"Random Early Detection Number."
	DEFVAL		{ tailDrop }
        ::= { rcPrQosTxQueueEntry 10 }

rcPrQosTxQueueRowStatus OBJECT-TYPE
        SYNTAX        	RowStatus
        MAX-ACCESS    	read-create
        STATUS        	current
        DESCRIPTION 	"Create/delete operations for this entry."
        ::= { rcPrQosTxQueueEntry 11 }

-- Power Ranger Qos Egress Queue Stats Table
rcPrQosTxQueueStatsTable OBJECT-TYPE
        SYNTAX        	SEQUENCE OF  RcPrQosTxQueueStatsEntry
        MAX-ACCESS    	not-accessible
        STATUS        	current
        DESCRIPTION   	"A list of elementary Egress queue stats entries."
        ::= { rcPrQos 6 }

rcPrQosTxQueueStatsEntry OBJECT-TYPE
        SYNTAX        	RcPrQosTxQueueStatsEntry
        MAX-ACCESS    	not-accessible
        STATUS        	current
        DESCRIPTION   	"Entry containing statistics information for a
                      	particular elementary egress queue."
       	INDEX         	{ rcPrQosTxQueueStatsPort,
			  rcPrQosTxQueueStatsQid }
        ::= { rcPrQosTxQueueStatsTable 1 }

RcPrQosTxQueueStatsEntry ::= SEQUENCE {
                rcPrQosTxQueueStatsPort         InterfaceIndex,
                rcPrQosTxQueueStatsQid          INTEGER,
                rcPrQosTxQueueStatsTotalPages   Counter64,
                rcPrQosTxQueueStatsDroppedPages Counter64,
                rcPrQosTxQueueStatsUtilization  INTEGER
		}

rcPrQosTxQueueStatsPort OBJECT-TYPE
  	SYNTAX         InterfaceIndex
        MAX-ACCESS     not-accessible
        STATUS         current
        DESCRIPTION   "Port index of the stats table."
        ::= { rcPrQosTxQueueStatsEntry 1 }

rcPrQosTxQueueStatsQid OBJECT-TYPE
        SYNTAX        	INTEGER (0..63)
        MAX-ACCESS    	not-accessible
        STATUS        	current
        DESCRIPTION   	"Queue Offset from the base queue for this port."
        ::= { rcPrQosTxQueueStatsEntry 2 }

rcPrQosTxQueueStatsTotalPages OBJECT-TYPE
        SYNTAX        	Counter64
        MAX-ACCESS    	read-only
        STATUS        	current
        DESCRIPTION 	"Total pages offered to the queue."
        ::= { rcPrQosTxQueueStatsEntry 3 }

rcPrQosTxQueueStatsDroppedPages OBJECT-TYPE
        SYNTAX        	Counter64
        MAX-ACCESS    	read-only
        STATUS        	current
        DESCRIPTION 	"Total pages dropped by the queue."
        ::= { rcPrQosTxQueueStatsEntry 4 }

rcPrQosTxQueueStatsUtilization OBJECT-TYPE
        SYNTAX        	INTEGER (0..100)
        MAX-ACCESS    	read-only
        STATUS        	current
        DESCRIPTION 	"Utilization percentage of the queue."
        ::= { rcPrQosTxQueueStatsEntry 5 }

-- Power Ranger Ingress Exp Bit To Qos Level Table
rcPrQosIngressExpToQosTable OBJECT-TYPE
        SYNTAX          SEQUENCE OF RcPrQosIngressExpToQosEntry
        MAX-ACCESS      not-accessible
        STATUS          current
        DESCRIPTION     "This table is used to specify the Mpls EXP to
                        QOS (Exp bit->QOS) mapping on packet ingress."
        ::= { rcPrQos 7 }

rcPrQosIngressExpToQosEntry OBJECT-TYPE
        SYNTAX        RcPrQosIngressExpToQosEntry
        MAX-ACCESS    not-accessible
        STATUS        current
        DESCRIPTION   "Entry containing information of Exp bit->Qos mapping"
        INDEX         { rcPrQosIngressExpToQosIndex }
        ::= { rcPrQosIngressExpToQosTable 1 }

RcPrQosIngressExpToQosEntry ::= SEQUENCE {
                rcPrQosIngressExpToQosIndex     INTEGER,
                rcPrQosIngressExpToQosMplsExp   INTEGER,
                rcPrQosIngressExpToQosLevel     INTEGER,
                rcPrQosIngressExpToQosRowStatus RowStatus
        }

rcPrQosIngressExpToQosIndex OBJECT-TYPE
        SYNTAX        INTEGER (1..8)
        MAX-ACCESS    not-accessible
        STATUS        current
        DESCRIPTION   "Used to uniquely identify a row in this table."
        ::= { rcPrQosIngressExpToQosEntry 1 }

rcPrQosIngressExpToQosMplsExp OBJECT-TYPE
        SYNTAX        INTEGER (0..7)
        MAX-ACCESS    read-only
        STATUS        current
        DESCRIPTION   "The Mpls Exp bit level."
        ::= { rcPrQosIngressExpToQosEntry 2 }

rcPrQosIngressExpToQosLevel OBJECT-TYPE
        SYNTAX        INTEGER (0..7)
        MAX-ACCESS    read-write
        STATUS        current
        DESCRIPTION   "qos level"
        ::= { rcPrQosIngressExpToQosEntry 3 }

rcPrQosIngressExpToQosRowStatus  OBJECT-TYPE
        SYNTAX        RowStatus
        MAX-ACCESS    read-write
        STATUS        current
        DESCRIPTION   "Create/delete operations for this entry."
        ::= { rcPrQosIngressExpToQosEntry 4}


-- Power Ranger Egress Qos Level to Exp Bit Table
rcPrQosEgressQosToExpTable OBJECT-TYPE
        SYNTAX        SEQUENCE OF RcPrQosEgressQosToExpEntry
        MAX-ACCESS    not-accessible
        STATUS        current
        DESCRIPTION   "This table is used to specify the QOS to
                      Mpls EXP bit field (QOS->Exp bit) mapping on packet
                      egress."
        ::= { rcPrQos 8 }

rcPrQosEgressQosToExpEntry OBJECT-TYPE
        SYNTAX        RcPrQosEgressQosToExpEntry
        MAX-ACCESS    not-accessible
        STATUS        current
        DESCRIPTION   "Entry containing infomation of Qos->Exp bit mapping"
        INDEX         { rcPrQosEgressQosToExpIndex }
        ::= { rcPrQosEgressQosToExpTable 1 }

RcPrQosEgressQosToExpEntry ::= SEQUENCE {
                rcPrQosEgressQosToExpIndex      INTEGER,
                rcPrQosEgressQosToExpQosLevel   INTEGER,
                rcPrQosEgressQosToExpMplsExp    INTEGER,
                rcPrQosEgressQosToExpRowStatus  RowStatus
        }

rcPrQosEgressQosToExpIndex OBJECT-TYPE
        SYNTAX        INTEGER (1..8)
        MAX-ACCESS    not-accessible
        STATUS        current
        DESCRIPTION   "Used to uniquely identify a row in this table."
        ::= { rcPrQosEgressQosToExpEntry 1 }

rcPrQosEgressQosToExpQosLevel OBJECT-TYPE
        SYNTAX        INTEGER (0..7)
        MAX-ACCESS    read-only
        STATUS        current
        DESCRIPTION   "qos level"
        ::= { rcPrQosEgressQosToExpEntry 2 }

rcPrQosEgressQosToExpMplsExp OBJECT-TYPE
        SYNTAX        INTEGER (0..7)
        MAX-ACCESS    read-write
        STATUS        current
        DESCRIPTION   "The Mpls EXP bit level."
        ::= { rcPrQosEgressQosToExpEntry 3 }

rcPrQosEgressQosToExpRowStatus  OBJECT-TYPE
        SYNTAX        RowStatus
        MAX-ACCESS    read-write
        STATUS        current
        DESCRIPTION   "Create/delete operations for this entry."
        ::= { rcPrQosEgressQosToExpEntry 4}


--
-- POWER RANGER QOS SUBPORT QUEUE SET TABLE
--

rcPrQosSubportQueueSetTemplateTable	OBJECT-TYPE
	SYNTAX		SEQUENCE OF RcPrQosSubportQueueSetTemplateEntry
	MAX-ACCESS	not-accessible
	STATUS		current
	DESCRIPTION	"A list of elementary egress queue templates."
	::= { rcPrQos 9 }

rcPrQosSubportQueueSetTemplateEntry	OBJECT-TYPE
	SYNTAX		RcPrQosSubportQueueSetTemplateEntry
	MAX-ACCESS	not-accessible
	STATUS		current
	DESCRIPTION	"Entry containing configuration information for
			a particular egress queue template. Queue is a
			set of egress queues"
	INDEX		{ rcPrQosSubportQueueSetTemplatePortIndex,
			  rcPrQosSubportQueueSetTemplateIndex }
	::= { rcPrQosSubportQueueSetTemplateTable 1 }

RcPrQosSubportQueueSetTemplateEntry ::=
	SEQUENCE
	{
	   rcPrQosSubportQueueSetTemplatePortIndex	     INTEGER,
	   rcPrQosSubportQueueSetTemplateIndex		     INTEGER,
	   rcPrQosSubportQueueSetTemplatePort		     InterfaceIndex,
	   rcPrQosSubportQueueSetTemplateApply		     TruthValue,
	   rcPrQosSubportQueueSetTemplateSubportProfileName  DisplayString,
	   rcPrQosSubportQueueSetTemplateAssignment	     DisplayString,
	   rcPrQosSubportQueueSetTemplateRowStatus	     RowStatus,
	   rcPrQosSubportQueueSetTemplateMinRate	     INTEGER,
	   rcPrQosSubportQueueSetTemplateMaxRate	     INTEGER,
	   rcPrQosSubportQueueSetTemplateMaxRateState	     EnableValue,
	   rcPrQosSubportQueueSetTemplateStatus		     INTEGER
	}

rcPrQosSubportQueueSetTemplatePortIndex	OBJECT-TYPE
	SYNTAX		INTEGER (1..2147483647)
	MAX-ACCESS	not-accessible
	STATUS		current
	DESCRIPTION	"Port Index."
	::= { rcPrQosSubportQueueSetTemplateEntry 1 }

rcPrQosSubportQueueSetTemplateIndex	OBJECT-TYPE
	SYNTAX		INTEGER (1..80)
	MAX-ACCESS	not-accessible
	STATUS		current
	DESCRIPTION	"A name assigned for this Subport Queue Set."
	::= { rcPrQosSubportQueueSetTemplateEntry 2 }

rcPrQosSubportQueueSetTemplatePort	OBJECT-TYPE
	SYNTAX		InterfaceIndex
	MAX-ACCESS	read-create
	STATUS		current
	DESCRIPTION	"Port assigned for this Subport Queue Set."
	::= { rcPrQosSubportQueueSetTemplateEntry 3 }

rcPrQosSubportQueueSetTemplateApply	OBJECT-TYPE
	SYNTAX		TruthValue
	MAX-ACCESS	read-create
	STATUS		current
	DESCRIPTION	"When apply is issued by the administrators,
			the subport queue set attributes are committed."
	DEFVAL		{ false }
	::= { rcPrQosSubportQueueSetTemplateEntry 4 }

rcPrQosSubportQueueSetTemplateSubportProfileName	OBJECT-TYPE
	SYNTAX		DisplayString (SIZE(0..20))
	MAX-ACCESS	read-create
	STATUS		current
	DESCRIPTION	"Name of the subport queue profile to be
			applied for this template."
	DEFVAL		{"DFLT_SUBPORT_PROFILE"}
	::= { rcPrQosSubportQueueSetTemplateEntry 5 }

rcPrQosSubportQueueSetTemplateAssignment	OBJECT-TYPE
	SYNTAX		DisplayString (SIZE(0..32))
	MAX-ACCESS	read-only
	STATUS		current
	DESCRIPTION	"Name of the trunk to this queue set is assigned."
	DEFVAL		{"Unassigned"}
	::= { rcPrQosSubportQueueSetTemplateEntry 6 }

rcPrQosSubportQueueSetTemplateRowStatus		OBJECT-TYPE
	SYNTAX		RowStatus
	MAX-ACCESS	read-create
	STATUS		current
	DESCRIPTION	"Create/delete operations for this entry."
	::= { rcPrQosSubportQueueSetTemplateEntry 7 }

rcPrQosSubportQueueSetTemplateMinRate		OBJECT-TYPE
	SYNTAX		INTEGER (2000..10000000)
	MAX-ACCESS	read-create
	STATUS		current
	DESCRIPTION	"Minimum Rate. Minimum Rate of less than 10000 is
			 valid only on 48 Port RC Modules. On all other modules
			 the minimum value Min Rate can be configured is 10000."
	DEFVAL		{ 50000 }
	::= { rcPrQosSubportQueueSetTemplateEntry 8 }

rcPrQosSubportQueueSetTemplateMaxRate		OBJECT-TYPE
	SYNTAX		INTEGER (2000..10000000)
	MAX-ACCESS	read-create
	STATUS		current
	DESCRIPTION	"Maximum Rate. Maximum Rate of less than 10000 is
			 valid only on 48 Port RC Modules. On all other modules
			 the minimum value Max Rate can be configured is 10000."
	DEFVAL		{ 1000000 }
	::= { rcPrQosSubportQueueSetTemplateEntry 9 }

rcPrQosSubportQueueSetTemplateMaxRateState	OBJECT-TYPE
	SYNTAX		EnableValue
	MAX-ACCESS	read-create
	STATUS		current
	DESCRIPTION	"Enable/Disable the maximum rate."
	DEFVAL		{ disable }
	::= { rcPrQosSubportQueueSetTemplateEntry 10 }

rcPrQosSubportQueueSetTemplateStatus 		OBJECT-TYPE
        SYNTAX        	INTEGER {
			    created(1),
			    applied(2),
			    modified(3)
			}
        MAX-ACCESS    	read-only
        STATUS        	current
        DESCRIPTION   	"Bitset indicating Subport Queue Set status."
	DEFVAL		{ created }
        ::= { rcPrQosSubportQueueSetTemplateEntry 11 }

--
-- RATE LIMITER TABLE (FOR I-SID'S)
--

rcPrQosIsidRateLimitsTable	OBJECT-TYPE
	SYNTAX		SEQUENCE OF RcPrQosIsidRateLimitsEntry
	MAX-ACCESS	not-accessible
	STATUS		current
	DESCRIPTION	"Isid Rate Limits Tables are
			 for R-Module cards only"
	::= { rcPrQos 10 }

rcPrQosIsidRateLimitsEntry	OBJECT-TYPE
	SYNTAX		RcPrQosIsidRateLimitsEntry
	MAX-ACCESS	not-accessible
	STATUS		current
	DESCRIPTION	"Isid Rate Limits Table"
	INDEX		{ rcPrQosIsidRateLimitsSlotNumber,
			  rcPrQosIsidRateLimitsLaneNumber }
	::= { rcPrQosIsidRateLimitsTable 1 }

RcPrQosIsidRateLimitsEntry ::=
	SEQUENCE
	{
		rcPrQosIsidRateLimitsSlotNumber		INTEGER,
		rcPrQosIsidRateLimitsLaneNumber		INTEGER,
		rcPrQosIsidRateLimitsAdminState		EnableValue
	}

rcPrQosIsidRateLimitsSlotNumber	OBJECT-TYPE
	SYNTAX		INTEGER (1..10)
	MAX-ACCESS	not-accessible
	STATUS		current
	DESCRIPTION	"Slot number."
	::= { rcPrQosIsidRateLimitsEntry 1 }

rcPrQosIsidRateLimitsLaneNumber	OBJECT-TYPE
	SYNTAX		INTEGER (1..3)
	MAX-ACCESS	not-accessible
	STATUS		current
	DESCRIPTION	"Lane number. On a 30 Port 1G card (8630GBR),
			 Ports 1 to 10 are grouped under Lane 1, Ports
			 11 to 20 are grouped under Lane 2 and Ports 21
			 to 30 are grouped under Lane 3. For a 3 Port
			 10G card (8683XLR), Port 1 comes under Lane 1,
			 Port 2 comes under Lane 2 and Port 3 comes
			 under Lane 3. For a 48 Port 1G card (8648GTR),
			 Ports 1 to 24 are grouped under Lane 1 and Ports
			 25 to 48 are grouped under Lane 2."
	::= { rcPrQosIsidRateLimitsEntry 2 }

rcPrQosIsidRateLimitsAdminState	OBJECT-TYPE
	SYNTAX		EnableValue
	MAX-ACCESS	read-write
	STATUS		current
	DESCRIPTION	"Admin control for the Rate Limiter Table."
        DEFVAL          { disable }
	::= { rcPrQosIsidRateLimitsEntry 3 }

--
-- RATE LIMITER I-SID TABLE
--

rcPrQosIsidRateLimitsIsidTable	OBJECT-TYPE
	SYNTAX		SEQUENCE OF RcPrQosIsidRateLimitsIsidEntry
	MAX-ACCESS	not-accessible
	STATUS		current
	DESCRIPTION	"Table contain rate limit for all Power Range card  (R module).
			Based on Slot and lane number and Isid ID"
	::= { rcPrQos 11 }

rcPrQosIsidRateLimitsIsidEntry	OBJECT-TYPE
	SYNTAX		RcPrQosIsidRateLimitsIsidEntry
	MAX-ACCESS	not-accessible
	STATUS		current
	DESCRIPTION	"Entry of Rate limit per slot and lane and Isid ID"
	INDEX		{ rcPrQosIsidRateLimitsIsidSlotNumber,
			  rcPrQosIsidRateLimitsIsidLaneNumber,
			  rcPrQosIsidRateLimitsIsidIsidId }
	::= { rcPrQosIsidRateLimitsIsidTable 1 }

RcPrQosIsidRateLimitsIsidEntry ::=
	SEQUENCE
	{
		rcPrQosIsidRateLimitsIsidSlotNumber	INTEGER,
		rcPrQosIsidRateLimitsIsidLaneNumber	INTEGER,
		rcPrQosIsidRateLimitsIsidIsidId		INTEGER,
		rcPrQosIsidRateLimitsIsidRateLimit	INTEGER
	}

rcPrQosIsidRateLimitsIsidSlotNumber	OBJECT-TYPE
	SYNTAX		INTEGER (1..10)
	MAX-ACCESS	not-accessible
	STATUS		current
	DESCRIPTION	"Slot number."
	::= { rcPrQosIsidRateLimitsIsidEntry 1 }

rcPrQosIsidRateLimitsIsidLaneNumber	OBJECT-TYPE
	SYNTAX		INTEGER (1..3)
	MAX-ACCESS	not-accessible
	STATUS		current
	DESCRIPTION	"Lane number. On a 30 Port 1G card (8630GBR),
			 Ports 1 to 10 are grouped under Lane 1, Ports
			 11 to 20 are grouped under Lane 2 and Ports 21
			 to 30 are grouped under Lane 3. For a 3 Port
			 10G card (8683XLR), Port 1 comes under Lane 1,
			 Port 2 comes under Lane 2 and Port 3 comes
			 under Lane 3. For a 48 Port 1G card (8648GTR),
			 Ports 1 to 24 are grouped under Lane 1 and Ports
			 25 to 48 are grouped under Lane 2."
	::= { rcPrQosIsidRateLimitsIsidEntry 2 }

rcPrQosIsidRateLimitsIsidIsidId		OBJECT-TYPE
	SYNTAX		INTEGER (1..16777215)
	MAX-ACCESS	not-accessible
	STATUS		current
	DESCRIPTION	"Isid Id."
	::= { rcPrQosIsidRateLimitsIsidEntry 3 }

rcPrQosIsidRateLimitsIsidRateLimit		OBJECT-TYPE
	SYNTAX		INTEGER (1..10000)
	MAX-ACCESS	read-only
	STATUS		current
	DESCRIPTION	"Rate Limit in Mbps."
        DEFVAL          { 1 }
	::= { rcPrQosIsidRateLimitsIsidEntry 4 }
--
-- SUBPORT PROFILE TABLE
--

rcPrQosSubportProfileTable	OBJECT-TYPE
	SYNTAX		SEQUENCE OF RcPrQosSubportProfileEntry
	MAX-ACCESS	not-accessible
	STATUS		current
	DESCRIPTION	"Table contain Subport Queue Profile information"
	::= { rcPrQos 12 }

rcPrQosSubportProfileEntry	OBJECT-TYPE
	SYNTAX		RcPrQosSubportProfileEntry
	MAX-ACCESS	not-accessible
	STATUS		current
	DESCRIPTION	"Subport Queue Profile Table entry"
	INDEX		{ rcPrQosSubportProfileIndex }
	::= { rcPrQosSubportProfileTable 1 }

RcPrQosSubportProfileEntry ::=
	SEQUENCE
	{
		rcPrQosSubportProfileIndex		INTEGER,
		rcPrQosSubportProfileName		DisplayString,
		rcPrQosSubportProfileBalancedQueues	INTEGER,
		rcPrQosSubportProfileHighPriQueues	INTEGER,
		rcPrQosSubportProfileLowPriQueues	INTEGER,
		rcPrQosSubportProfileBalancedQList	OCTET STRING,
		rcPrQosSubportProfileHighPriQList	OCTET STRING,
		rcPrQosSubportProfileLowPriQList	OCTET STRING,
		rcPrQosSubportProfileRowStatus		RowStatus
	}

rcPrQosSubportProfileIndex	OBJECT-TYPE
	SYNTAX		INTEGER (1..1000)
	MAX-ACCESS	not-accessible
	STATUS		current
	DESCRIPTION	"A value that uniquely  identifies the Subport Queue Profile."
	::= { rcPrQosSubportProfileEntry 1 }

rcPrQosSubportProfileName	OBJECT-TYPE
	SYNTAX		DisplayString (SIZE (0..20))
	MAX-ACCESS	read-create
	STATUS		current
	DESCRIPTION	"Subport Queue Profile table name to be used."
	::= { rcPrQosSubportProfileEntry 2 }

rcPrQosSubportProfileBalancedQueues	OBJECT-TYPE
	SYNTAX		INTEGER (0..6)
	MAX-ACCESS	read-create
	STATUS		current
	DESCRIPTION	"Total number of Balanced Queues in this profile."
	DEFVAL		{ 5 }
	::= { rcPrQosSubportProfileEntry 3 }

rcPrQosSubportProfileHighPriQueues	OBJECT-TYPE
	SYNTAX		INTEGER (1..7)
	MAX-ACCESS	read-create
	STATUS		current
	DESCRIPTION	"Total number of High Priority Queues in this profile."
	DEFVAL		{ 2 }
	::= { rcPrQosSubportProfileEntry 4 }

rcPrQosSubportProfileLowPriQueues	OBJECT-TYPE
	SYNTAX		INTEGER (1..7)
	MAX-ACCESS	read-create
	STATUS		current
	DESCRIPTION	"Total number of Low Priority Queues in this profile."
	DEFVAL		{ 1 }
	::= { rcPrQosSubportProfileEntry 5 }

rcPrQosSubportProfileBalancedQList	OBJECT-TYPE
	SYNTAX		OCTET STRING (SIZE(0..50))
	MAX-ACCESS	read-only
	STATUS		current
	DESCRIPTION	"List of Balanced Queues in this profile."
	::= { rcPrQosSubportProfileEntry 6 }

rcPrQosSubportProfileHighPriQList	OBJECT-TYPE
	SYNTAX		OCTET STRING (SIZE(0..50))
	MAX-ACCESS	read-only
	STATUS		current
	DESCRIPTION	"List of High Priority Queues in this profile."
	::= { rcPrQosSubportProfileEntry 7 }

rcPrQosSubportProfileLowPriQList	OBJECT-TYPE
	SYNTAX		OCTET STRING (SIZE(0..50))
	MAX-ACCESS	read-only
	STATUS		current
	DESCRIPTION	"List of Low Priority Queues in this profile."
	::= { rcPrQosSubportProfileEntry 8 }

rcPrQosSubportProfileRowStatus	OBJECT-TYPE
	SYNTAX		RowStatus
	MAX-ACCESS	read-create
	STATUS		current
	DESCRIPTION	"Create/delete operations for this entry."
	::= { rcPrQosSubportProfileEntry 9 }

--
-- SUBPORT PROFILE QUEUE TABLE
--
rcPrQosSubportProfileQueueTable	OBJECT-TYPE
	SYNTAX		SEQUENCE OF RcPrQosSubportProfileQueueEntry
	MAX-ACCESS	not-accessible
	STATUS		current
	DESCRIPTION	"A list of elementary subport queue entries."
	::= { rcPrQos 13 }

rcPrQosSubportProfileQueueEntry	OBJECT-TYPE
	SYNTAX		RcPrQosSubportProfileQueueEntry
	MAX-ACCESS	not-accessible
	STATUS		current
	DESCRIPTION	"Entry containing configuration information for
			a particular subport egress queue."
	INDEX		{ rcPrQosSubportProfileQueueProfileIndex,
			  rcPrQosSubportProfileQueueQIndex }
	::= { rcPrQosSubportProfileQueueTable 1 }

RcPrQosSubportProfileQueueEntry ::=
	SEQUENCE
	{
		rcPrQosSubportProfileQueueProfileIndex		INTEGER,
		rcPrQosSubportProfileQueueQIndex		INTEGER,
		rcPrQosSubportProfileQueueQStyle		INTEGER,
		rcPrQosSubportProfileQueueMaxRate		INTEGER,
		rcPrQosSubportProfileQueueMinRate		INTEGER,
		rcPrQosSubportProfileQueueMaxLength		INTEGER,
		rcPrQosSubportProfileQueueWredCurveSet		INTEGER,
	        rcPrQosSubportProfileQueueQPriority		INTEGER
	}

rcPrQosSubportProfileQueueProfileIndex	OBJECT-TYPE
	SYNTAX		INTEGER (1..1000)
	MAX-ACCESS	not-accessible
	STATUS		current
	DESCRIPTION	"Profile index of the profie this queue belongs to."
	::= { rcPrQosSubportProfileQueueEntry 1 }

rcPrQosSubportProfileQueueQIndex	OBJECT-TYPE
	SYNTAX		INTEGER (0..7)
	MAX-ACCESS	not-accessible
	STATUS		current
	DESCRIPTION	"Queue offset from the base queue."
	::= { rcPrQosSubportProfileQueueEntry 2 }

rcPrQosSubportProfileQueueQStyle	OBJECT-TYPE
	SYNTAX		INTEGER
  			{
				highPri(1),
				balanced(2),
				lowPri(3)
			}
	MAX-ACCESS	read-only
	STATUS		current
	DESCRIPTION	"Queue style."
	::= { rcPrQosSubportProfileQueueEntry 3 }

rcPrQosSubportProfileQueueMaxRate	OBJECT-TYPE
	SYNTAX		INTEGER (0..100)
	MAX-ACCESS	read-write
	STATUS		current
	DESCRIPTION	"Queue maximum rate in percentage."
	::= { rcPrQosSubportProfileQueueEntry 4 }

rcPrQosSubportProfileQueueMinRate	OBJECT-TYPE
	SYNTAX		INTEGER (0..100)
	MAX-ACCESS	read-write
	STATUS		current
	DESCRIPTION	"Queue minimum rate in percentage."
	::= { rcPrQosSubportProfileQueueEntry 5 }

rcPrQosSubportProfileQueueMaxLength	OBJECT-TYPE
	SYNTAX		INTEGER (0..8000)
	MAX-ACCESS	read-write
	STATUS		current
	DESCRIPTION	"Maximum queue length."
	::= { rcPrQosSubportProfileQueueEntry 6 }

rcPrQosSubportProfileQueueWredCurveSet	OBJECT-TYPE
	SYNTAX		INTEGER
			{
				tailDrop(1),
				lowDrop(2),
				mediumDrop(3),
				highDrop(4)
			}
	MAX-ACCESS	read-write
	STATUS		current
	DESCRIPTION	"Weighted Random Early Detection setting."
	DEFVAL		{ tailDrop }
	::= { rcPrQosSubportProfileQueueEntry 7 }

rcPrQosSubportProfileQueueQPriority	OBJECT-TYPE
	SYNTAX		INTEGER (0..7)
	MAX-ACCESS	read-only
	STATUS		current
	DESCRIPTION	"Q Priority."
	::= { rcPrQosSubportProfileQueueEntry 8 }

--
-- SUBPORT QUEUE SET - INTERNAL QOS TO EGRESS QUEUE MAPPING TABLE
--

rcPrQosSubportQueueSetEqmapTable	OBJECT-TYPE
	SYNTAX		SEQUENCE OF RcPrQosSubportQueueSetEqmapEntry
	MAX-ACCESS	not-accessible
	STATUS		current
	DESCRIPTION	"Internal QoS to Egress Queue mapping table."
	::= { rcPrQos 14 }

rcPrQosSubportQueueSetEqmapEntry	OBJECT-TYPE
	SYNTAX		RcPrQosSubportQueueSetEqmapEntry
	MAX-ACCESS	not-accessible
	STATUS		current
	DESCRIPTION	"Entry containing egress queue id for an
			 internal QoS level on a subport q set."
	INDEX		{ rcPrQosSubportQueueSetEqmapPortIndex,
			  rcPrQosSubportQueueSetEqmapIndex,
			  rcPrQosSubportQueueSetEqmapInternalQos }
	::= { rcPrQosSubportQueueSetEqmapTable 1 }

RcPrQosSubportQueueSetEqmapEntry ::=
	SEQUENCE
	{
	   rcPrQosSubportQueueSetEqmapPortIndex	     INTEGER,
	   rcPrQosSubportQueueSetEqmapIndex	     INTEGER,
	   rcPrQosSubportQueueSetEqmapInternalQos    INTEGER,
	   rcPrQosSubportQueueSetEqmapPort	     InterfaceIndex,
	   rcPrQosSubportQueueSetEqmapEgressQueue    INTEGER
	}

rcPrQosSubportQueueSetEqmapPortIndex	OBJECT-TYPE
	SYNTAX		INTEGER (1..2147483647)
	MAX-ACCESS	not-accessible
	STATUS		current
	DESCRIPTION	"Port Index."
	::= { rcPrQosSubportQueueSetEqmapEntry 1 }

rcPrQosSubportQueueSetEqmapIndex	OBJECT-TYPE
	SYNTAX		INTEGER (1..80)
	MAX-ACCESS	not-accessible
	STATUS		current
	DESCRIPTION	"Subport Queue Set Index."
	::= { rcPrQosSubportQueueSetEqmapEntry 2 }

rcPrQosSubportQueueSetEqmapInternalQos	OBJECT-TYPE
	SYNTAX		INTEGER (0..7)
	MAX-ACCESS	not-accessible
	STATUS		current
	DESCRIPTION	"Internal QoS."
	::= { rcPrQosSubportQueueSetEqmapEntry 3 }

rcPrQosSubportQueueSetEqmapPort		OBJECT-TYPE
	SYNTAX		InterfaceIndex
	MAX-ACCESS	read-only
	STATUS		current
	DESCRIPTION	"Port assigned for this Subport Queue Set."
	::= { rcPrQosSubportQueueSetEqmapEntry 4 }

rcPrQosSubportQueueSetEqmapEgressQueue	OBJECT-TYPE
	SYNTAX		INTEGER (0..7)
	MAX-ACCESS	read-only
	STATUS		current
	DESCRIPTION	"Egress Queue Id assigned for the
			 specified Internal QoS Lvl."
	::= { rcPrQosSubportQueueSetEqmapEntry 5 }

-- Power Ranger Egress Qos Cos Queue stats Table
rcPrQosCosQuePortStatsTable OBJECT-TYPE
        SYNTAX        SEQUENCE OF RcPrQosCosQuePortStatsEntry
        MAX-ACCESS    not-accessible
        STATUS        current
        DESCRIPTION   "This table is used to get the qos cos queue port stats."
        ::= { rcPrQos 15 }

rcPrQosCosQuePortStatsEntry OBJECT-TYPE
        SYNTAX        RcPrQosCosQuePortStatsEntry
        MAX-ACCESS    not-accessible
        STATUS        current
        DESCRIPTION   "Entry containing information of port Qos cosq stats"
        INDEX         { rcPrQosCosQuePortStatsIndex }
        ::= { rcPrQosCosQuePortStatsTable 1 }

RcPrQosCosQuePortStatsEntry ::= SEQUENCE {
                rcPrQosCosQuePortStatsIndex            INTEGER,
                rcPrQosCosQuePortStatsQue0OutPackets   Counter64,
                rcPrQosCosQuePortStatsQue0OutBytes     Counter64,
                rcPrQosCosQuePortStatsQue0DropPackets  Counter64,
                rcPrQosCosQuePortStatsQue0DropBytes    Counter64,
                rcPrQosCosQuePortStatsQue1OutPackets   Counter64,
                rcPrQosCosQuePortStatsQue1OutBytes     Counter64,
                rcPrQosCosQuePortStatsQue1DropPackets  Counter64,
                rcPrQosCosQuePortStatsQue1DropBytes    Counter64,
                rcPrQosCosQuePortStatsQue2OutPackets   Counter64,
                rcPrQosCosQuePortStatsQue2OutBytes     Counter64,
                rcPrQosCosQuePortStatsQue2DropPackets  Counter64,
                rcPrQosCosQuePortStatsQue2DropBytes    Counter64,
                rcPrQosCosQuePortStatsQue3OutPackets   Counter64,
                rcPrQosCosQuePortStatsQue3OutBytes     Counter64,
                rcPrQosCosQuePortStatsQue3DropPackets  Counter64,
                rcPrQosCosQuePortStatsQue3DropBytes    Counter64,
                rcPrQosCosQuePortStatsQue4OutPackets   Counter64,
                rcPrQosCosQuePortStatsQue4OutBytes     Counter64,
                rcPrQosCosQuePortStatsQue4DropPackets  Counter64,
                rcPrQosCosQuePortStatsQue4DropBytes    Counter64,
                rcPrQosCosQuePortStatsQue5OutPackets   Counter64,
                rcPrQosCosQuePortStatsQue5OutBytes     Counter64,
                rcPrQosCosQuePortStatsQue5DropPackets  Counter64,
                rcPrQosCosQuePortStatsQue5DropBytes    Counter64,
                rcPrQosCosQuePortStatsQue6OutPackets   Counter64,
                rcPrQosCosQuePortStatsQue6OutBytes     Counter64,
                rcPrQosCosQuePortStatsQue6DropPackets  Counter64,
                rcPrQosCosQuePortStatsQue6DropBytes    Counter64,
                rcPrQosCosQuePortStatsQue7OutPackets   Counter64,
                rcPrQosCosQuePortStatsQue7OutBytes     Counter64,
                rcPrQosCosQuePortStatsQue7DropPackets  Counter64,
                rcPrQosCosQuePortStatsQue7DropBytes    Counter64,
                rcPrQosCosQuePortStatsClearStat        TruthValue
        }
rcPrQosCosQuePortStatsIndex     OBJECT-TYPE
	SYNTAX          INTEGER (192..297)
	MAX-ACCESS      not-accessible
        STATUS          current
        DESCRIPTION     "Used to indicate the loopback port number from 192(1/1) to 297(2/42)."
        ::= { rcPrQosCosQuePortStatsEntry 1 }

rcPrQosCosQuePortStatsQue0OutPackets	    OBJECT-TYPE
	SYNTAX          Counter64
	MAX-ACCESS      read-only
        STATUS          current
        DESCRIPTION     "the out packets for Cos queue 0."
        ::= { rcPrQosCosQuePortStatsEntry 2 }

rcPrQosCosQuePortStatsQue0OutBytes	    OBJECT-TYPE
	SYNTAX          Counter64
	MAX-ACCESS      read-only
        STATUS          current
        DESCRIPTION     "the out bytes for Cos queue 0."
        ::= { rcPrQosCosQuePortStatsEntry 3 }

rcPrQosCosQuePortStatsQue0DropPackets	OBJECT-TYPE
	SYNTAX          Counter64
	MAX-ACCESS      read-only
        STATUS          current
        DESCRIPTION     "the drop packets for Cos queue 0."
        ::= { rcPrQosCosQuePortStatsEntry 4 }

rcPrQosCosQuePortStatsQue0DropBytes	OBJECT-TYPE
	SYNTAX          Counter64
	MAX-ACCESS      read-only
        STATUS          current
        DESCRIPTION     "the drop bytes for Cos queue 0."
        ::= { rcPrQosCosQuePortStatsEntry 5 }

rcPrQosCosQuePortStatsQue1OutPackets	    OBJECT-TYPE
	SYNTAX          Counter64
	MAX-ACCESS      read-only
        STATUS          current
        DESCRIPTION     "the out packets for Cos queue 1."
        ::= { rcPrQosCosQuePortStatsEntry 6 }

rcPrQosCosQuePortStatsQue1OutBytes	    OBJECT-TYPE
	SYNTAX          Counter64
	MAX-ACCESS      read-only
        STATUS          current
        DESCRIPTION     "the out bytes for Cos queue 1."
        ::= { rcPrQosCosQuePortStatsEntry 7 }

rcPrQosCosQuePortStatsQue1DropPackets	OBJECT-TYPE
	SYNTAX          Counter64
	MAX-ACCESS      read-only
        STATUS          current
        DESCRIPTION     "the drop packets for Cos queue 1."
        ::= { rcPrQosCosQuePortStatsEntry 8 }

rcPrQosCosQuePortStatsQue1DropBytes	OBJECT-TYPE
	SYNTAX          Counter64
	MAX-ACCESS      read-only
        STATUS          current
        DESCRIPTION     "the drop bytes for Cos queue 1."
        ::= { rcPrQosCosQuePortStatsEntry 9 }

rcPrQosCosQuePortStatsQue2OutPackets	    OBJECT-TYPE
	SYNTAX          Counter64
	MAX-ACCESS      read-only
        STATUS          current
        DESCRIPTION     "the out packets for Cos queue 2."
        ::= { rcPrQosCosQuePortStatsEntry 10 }

rcPrQosCosQuePortStatsQue2OutBytes	    OBJECT-TYPE
	SYNTAX          Counter64
	MAX-ACCESS      read-only
        STATUS          current
        DESCRIPTION     "the out bytes for Cos queue 2."
        ::= { rcPrQosCosQuePortStatsEntry 11 }

rcPrQosCosQuePortStatsQue2DropPackets	OBJECT-TYPE
	SYNTAX          Counter64
	MAX-ACCESS      read-only
        STATUS          current
        DESCRIPTION     "the drop packets for Cos queue 2."
        ::= { rcPrQosCosQuePortStatsEntry 12 }

rcPrQosCosQuePortStatsQue2DropBytes	OBJECT-TYPE
	SYNTAX          Counter64
	MAX-ACCESS      read-only
        STATUS          current
        DESCRIPTION     "the drop bytes for Cos queue 2."
        ::= { rcPrQosCosQuePortStatsEntry 13 }

rcPrQosCosQuePortStatsQue3OutPackets	    OBJECT-TYPE
	SYNTAX          Counter64
	MAX-ACCESS      read-only
        STATUS          current
        DESCRIPTION     "the out packets for Cos queue 3."
        ::= { rcPrQosCosQuePortStatsEntry 14 }

rcPrQosCosQuePortStatsQue3OutBytes	    OBJECT-TYPE
	SYNTAX          Counter64
	MAX-ACCESS      read-only
        STATUS          current
        DESCRIPTION     "the out bytes for Cos queue 3."
        ::= { rcPrQosCosQuePortStatsEntry 15 }

rcPrQosCosQuePortStatsQue3DropPackets	OBJECT-TYPE
	SYNTAX          Counter64
	MAX-ACCESS      read-only
        STATUS          current
        DESCRIPTION     "the drop packets for Cos queue 3."
        ::= { rcPrQosCosQuePortStatsEntry 16 }

rcPrQosCosQuePortStatsQue3DropBytes	OBJECT-TYPE
	SYNTAX          Counter64
	MAX-ACCESS      read-only
        STATUS          current
        DESCRIPTION     "the drop bytes for Cos queue 3."
        ::= { rcPrQosCosQuePortStatsEntry 17 }

rcPrQosCosQuePortStatsQue4OutPackets	    OBJECT-TYPE
	SYNTAX          Counter64
	MAX-ACCESS      read-only
        STATUS          current
        DESCRIPTION     "the out packets for Cos queue 4."
        ::= { rcPrQosCosQuePortStatsEntry 18 }

rcPrQosCosQuePortStatsQue4OutBytes	    OBJECT-TYPE
	SYNTAX          Counter64
	MAX-ACCESS      read-only
        STATUS          current
        DESCRIPTION     "the out bytes for Cos queue 4."
        ::= { rcPrQosCosQuePortStatsEntry 19 }

rcPrQosCosQuePortStatsQue4DropPackets	OBJECT-TYPE
	SYNTAX          Counter64
	MAX-ACCESS      read-only
        STATUS          current
        DESCRIPTION     "the drop packets for Cos queue 4."
        ::= { rcPrQosCosQuePortStatsEntry 20 }

rcPrQosCosQuePortStatsQue4DropBytes	OBJECT-TYPE
	SYNTAX          Counter64
	MAX-ACCESS      read-only
        STATUS          current
        DESCRIPTION     "the drop bytes for Cos queue 4."
        ::= { rcPrQosCosQuePortStatsEntry 21 }

rcPrQosCosQuePortStatsQue5OutPackets	    OBJECT-TYPE
	SYNTAX          Counter64
	MAX-ACCESS      read-only
        STATUS          current
        DESCRIPTION     "the out packets for Cos queue 5."
        ::= { rcPrQosCosQuePortStatsEntry 22 }

rcPrQosCosQuePortStatsQue5OutBytes	    OBJECT-TYPE
	SYNTAX          Counter64
	MAX-ACCESS      read-only
        STATUS          current
        DESCRIPTION     "the out bytes for Cos queue 5."
        ::= { rcPrQosCosQuePortStatsEntry 23 }

rcPrQosCosQuePortStatsQue5DropPackets	OBJECT-TYPE
	SYNTAX          Counter64
	MAX-ACCESS      read-only
        STATUS          current
        DESCRIPTION     "the drop packets for Cos queue 5."
        ::= { rcPrQosCosQuePortStatsEntry 24 }

rcPrQosCosQuePortStatsQue5DropBytes	OBJECT-TYPE
	SYNTAX          Counter64
	MAX-ACCESS      read-only
        STATUS          current
        DESCRIPTION     "the drop bytes for Cos queue 5."
        ::= { rcPrQosCosQuePortStatsEntry 25 }

rcPrQosCosQuePortStatsQue6OutPackets	    OBJECT-TYPE
	SYNTAX          Counter64
	MAX-ACCESS      read-only
        STATUS          current
        DESCRIPTION     "the out packets for Cos queue 6."
        ::= { rcPrQosCosQuePortStatsEntry 26 }

rcPrQosCosQuePortStatsQue6OutBytes	    OBJECT-TYPE
	SYNTAX          Counter64
	MAX-ACCESS      read-only
        STATUS          current
        DESCRIPTION     "the out bytes for Cos queue 6."
        ::= { rcPrQosCosQuePortStatsEntry 27 }

rcPrQosCosQuePortStatsQue6DropPackets	OBJECT-TYPE
	SYNTAX          Counter64
	MAX-ACCESS      read-only
        STATUS          current
        DESCRIPTION     "the drop packets for Cos queue 6."
        ::= { rcPrQosCosQuePortStatsEntry 28 }

rcPrQosCosQuePortStatsQue6DropBytes	OBJECT-TYPE
	SYNTAX          Counter64
	MAX-ACCESS      read-only
        STATUS          current
        DESCRIPTION     "the drop bytes for Cos queue 6."
        ::= { rcPrQosCosQuePortStatsEntry 29 }

rcPrQosCosQuePortStatsQue7OutPackets	    OBJECT-TYPE
	SYNTAX          Counter64
	MAX-ACCESS      read-only
        STATUS          current
        DESCRIPTION     "the out packets for Cos queue 7."
        ::= { rcPrQosCosQuePortStatsEntry 30 }

rcPrQosCosQuePortStatsQue7OutBytes	    OBJECT-TYPE
	SYNTAX          Counter64
	MAX-ACCESS      read-only
        STATUS          current
        DESCRIPTION     "the out bytes for Cos queue 7."
        ::= { rcPrQosCosQuePortStatsEntry 31 }

rcPrQosCosQuePortStatsQue7DropPackets	OBJECT-TYPE
	SYNTAX          Counter64
	MAX-ACCESS      read-only
        STATUS          current
        DESCRIPTION     "the drop packets for Cos queue 7."
        ::= { rcPrQosCosQuePortStatsEntry 32 }

rcPrQosCosQuePortStatsQue7DropBytes	OBJECT-TYPE
	SYNTAX          Counter64
	MAX-ACCESS      read-only
        STATUS          current
        DESCRIPTION     "the drop bytes for Cos queue 7."
        ::= { rcPrQosCosQuePortStatsEntry 33 }

rcPrQosCosQuePortStatsClearStat OBJECT-TYPE
    SYNTAX       TruthValue
    MAX-ACCESS   read-write
    STATUS       current
    DESCRIPTION  "Clear Stats."
    ::= { rcPrQosCosQuePortStatsEntry 34 }


rcPrQosCosQueLoopbackPortStatsTable OBJECT-TYPE
        SYNTAX        SEQUENCE OF RcPrQosCosQueLoopbackPortStatsEntry
        MAX-ACCESS    not-accessible
        STATUS        current
        DESCRIPTION   "This table is used to get the qos cos queue port stats."
        ::= { rcPrQos 16 }

rcPrQosCosQueLoopbackPortStatsEntry OBJECT-TYPE
        SYNTAX        RcPrQosCosQueLoopbackPortStatsEntry
        MAX-ACCESS    not-accessible
        STATUS        current
        DESCRIPTION   "Entry containing information of port Qos cosq stats"
        INDEX         { rcPrQosCosQueLoopbackPortStatsIndex }
        ::= { rcPrQosCosQueLoopbackPortStatsTable 1 }

RcPrQosCosQueLoopbackPortStatsEntry ::= SEQUENCE {
                rcPrQosCosQueLoopbackPortStatsIndex            INTEGER,
                rcPrQosCosQueLoopbackPortStatsQue0OutPackets   Counter64,
                rcPrQosCosQueLoopbackPortStatsQue0OutBytes     Counter64,
                rcPrQosCosQueLoopbackPortStatsQue0DropPackets  Counter64,
                rcPrQosCosQueLoopbackPortStatsQue0DropBytes    Counter64,
                rcPrQosCosQueLoopbackPortStatsQue1OutPackets   Counter64,
                rcPrQosCosQueLoopbackPortStatsQue1OutBytes     Counter64,
                rcPrQosCosQueLoopbackPortStatsQue1DropPackets  Counter64,
                rcPrQosCosQueLoopbackPortStatsQue1DropBytes    Counter64,
                rcPrQosCosQueLoopbackPortStatsQue2OutPackets   Counter64,
                rcPrQosCosQueLoopbackPortStatsQue2OutBytes     Counter64,
                rcPrQosCosQueLoopbackPortStatsQue2DropPackets  Counter64,
                rcPrQosCosQueLoopbackPortStatsQue2DropBytes    Counter64,
                rcPrQosCosQueLoopbackPortStatsQue3OutPackets   Counter64,
                rcPrQosCosQueLoopbackPortStatsQue3OutBytes     Counter64,
                rcPrQosCosQueLoopbackPortStatsQue3DropPackets  Counter64,
                rcPrQosCosQueLoopbackPortStatsQue3DropBytes    Counter64,
                rcPrQosCosQueLoopbackPortStatsQue4OutPackets   Counter64,
                rcPrQosCosQueLoopbackPortStatsQue4OutBytes     Counter64,
                rcPrQosCosQueLoopbackPortStatsQue4DropPackets  Counter64,
                rcPrQosCosQueLoopbackPortStatsQue4DropBytes    Counter64,
                rcPrQosCosQueLoopbackPortStatsQue5OutPackets   Counter64,
                rcPrQosCosQueLoopbackPortStatsQue5OutBytes     Counter64,
                rcPrQosCosQueLoopbackPortStatsQue5DropPackets  Counter64,
                rcPrQosCosQueLoopbackPortStatsQue5DropBytes    Counter64,
                rcPrQosCosQueLoopbackPortStatsQue6OutPackets   Counter64,
                rcPrQosCosQueLoopbackPortStatsQue6OutBytes     Counter64,
                rcPrQosCosQueLoopbackPortStatsQue6DropPackets  Counter64,
                rcPrQosCosQueLoopbackPortStatsQue6DropBytes    Counter64,
                rcPrQosCosQueLoopbackPortStatsQue7OutPackets   Counter64,
                rcPrQosCosQueLoopbackPortStatsQue7OutBytes     Counter64,
                rcPrQosCosQueLoopbackPortStatsQue7DropPackets  Counter64,
                rcPrQosCosQueLoopbackPortStatsQue7DropBytes    Counter64,
		rcPrQosCosQueLoopbackPortStatsClearStat        TruthValue
        }
rcPrQosCosQueLoopbackPortStatsIndex     OBJECT-TYPE
	SYNTAX          INTEGER (1..2)
	MAX-ACCESS      not-accessible
        STATUS          current
        DESCRIPTION     "Used to indicate the port number from 1 to 2."
        ::= { rcPrQosCosQueLoopbackPortStatsEntry 1 }

rcPrQosCosQueLoopbackPortStatsQue0OutPackets	    OBJECT-TYPE
	SYNTAX          Counter64
	MAX-ACCESS      read-only
        STATUS          current
        DESCRIPTION     "the out packets for Cos queue 0."
        ::= { rcPrQosCosQueLoopbackPortStatsEntry 2 }

rcPrQosCosQueLoopbackPortStatsQue0OutBytes	    OBJECT-TYPE
	SYNTAX          Counter64
	MAX-ACCESS      read-only
        STATUS          current
        DESCRIPTION     "the out bytes for Cos queue 0."
        ::= { rcPrQosCosQueLoopbackPortStatsEntry 3 }

rcPrQosCosQueLoopbackPortStatsQue0DropPackets	OBJECT-TYPE
	SYNTAX          Counter64
	MAX-ACCESS      read-only
        STATUS          current
        DESCRIPTION     "the drop packets for Cos queue 0."
        ::= { rcPrQosCosQueLoopbackPortStatsEntry 4 }

rcPrQosCosQueLoopbackPortStatsQue0DropBytes	OBJECT-TYPE
	SYNTAX          Counter64
	MAX-ACCESS      read-only
        STATUS          current
        DESCRIPTION     "the drop bytes for Cos queue 0."
        ::= { rcPrQosCosQueLoopbackPortStatsEntry 5 }

rcPrQosCosQueLoopbackPortStatsQue1OutPackets	    OBJECT-TYPE
	SYNTAX          Counter64
	MAX-ACCESS      read-only
        STATUS          current
        DESCRIPTION     "the out packets for Cos queue 1."
        ::= { rcPrQosCosQueLoopbackPortStatsEntry 6 }

rcPrQosCosQueLoopbackPortStatsQue1OutBytes	    OBJECT-TYPE
	SYNTAX          Counter64
	MAX-ACCESS      read-only
        STATUS          current
        DESCRIPTION     "the out bytes for Cos queue 1."
        ::= { rcPrQosCosQueLoopbackPortStatsEntry 7 }

rcPrQosCosQueLoopbackPortStatsQue1DropPackets	OBJECT-TYPE
	SYNTAX          Counter64
	MAX-ACCESS      read-only
        STATUS          current
        DESCRIPTION     "the drop packets for Cos queue 1."
        ::= { rcPrQosCosQueLoopbackPortStatsEntry 8 }

rcPrQosCosQueLoopbackPortStatsQue1DropBytes	OBJECT-TYPE
	SYNTAX          Counter64
	MAX-ACCESS      read-only
        STATUS          current
        DESCRIPTION     "the drop bytes for Cos queue 1."
        ::= { rcPrQosCosQueLoopbackPortStatsEntry 9 }

rcPrQosCosQueLoopbackPortStatsQue2OutPackets	    OBJECT-TYPE
	SYNTAX          Counter64
	MAX-ACCESS      read-only
        STATUS          current
        DESCRIPTION     "the out packets for Cos queue 2."
        ::= { rcPrQosCosQueLoopbackPortStatsEntry 10 }

rcPrQosCosQueLoopbackPortStatsQue2OutBytes	    OBJECT-TYPE
	SYNTAX          Counter64
	MAX-ACCESS      read-only
        STATUS          current
        DESCRIPTION     "the out bytes for Cos queue 2."
        ::= { rcPrQosCosQueLoopbackPortStatsEntry 11 }

rcPrQosCosQueLoopbackPortStatsQue2DropPackets	OBJECT-TYPE
	SYNTAX          Counter64
	MAX-ACCESS      read-only
        STATUS          current
        DESCRIPTION     "the drop packets for Cos queue 2."
        ::= { rcPrQosCosQueLoopbackPortStatsEntry 12 }

rcPrQosCosQueLoopbackPortStatsQue2DropBytes	OBJECT-TYPE
	SYNTAX          Counter64
	MAX-ACCESS      read-only
        STATUS          current
        DESCRIPTION     "the drop bytes for Cos queue 2."
        ::= { rcPrQosCosQueLoopbackPortStatsEntry 13 }

rcPrQosCosQueLoopbackPortStatsQue3OutPackets	    OBJECT-TYPE
	SYNTAX          Counter64
	MAX-ACCESS      read-only
        STATUS          current
        DESCRIPTION     "the out packets for Cos queue 3."
        ::= { rcPrQosCosQueLoopbackPortStatsEntry 14 }

rcPrQosCosQueLoopbackPortStatsQue3OutBytes	    OBJECT-TYPE
	SYNTAX          Counter64
	MAX-ACCESS      read-only
        STATUS          current
        DESCRIPTION     "the out bytes for Cos queue 3."
        ::= { rcPrQosCosQueLoopbackPortStatsEntry 15 }

rcPrQosCosQueLoopbackPortStatsQue3DropPackets	OBJECT-TYPE
	SYNTAX          Counter64
	MAX-ACCESS      read-only
        STATUS          current
        DESCRIPTION     "the drop packets for Cos queue 3."
        ::= { rcPrQosCosQueLoopbackPortStatsEntry 16 }

rcPrQosCosQueLoopbackPortStatsQue3DropBytes	OBJECT-TYPE
	SYNTAX          Counter64
	MAX-ACCESS      read-only
        STATUS          current
        DESCRIPTION     "the drop bytes for Cos queue 3."
        ::= { rcPrQosCosQueLoopbackPortStatsEntry 17 }

rcPrQosCosQueLoopbackPortStatsQue4OutPackets	    OBJECT-TYPE
	SYNTAX          Counter64
	MAX-ACCESS      read-only
        STATUS          current
        DESCRIPTION     "the out packets for Cos queue 4."
        ::= { rcPrQosCosQueLoopbackPortStatsEntry 18 }

rcPrQosCosQueLoopbackPortStatsQue4OutBytes	    OBJECT-TYPE
	SYNTAX          Counter64
	MAX-ACCESS      read-only
        STATUS          current
        DESCRIPTION     "the out bytes for Cos queue 4."
        ::= { rcPrQosCosQueLoopbackPortStatsEntry 19 }

rcPrQosCosQueLoopbackPortStatsQue4DropPackets	OBJECT-TYPE
	SYNTAX          Counter64
	MAX-ACCESS      read-only
        STATUS          current
        DESCRIPTION     "the drop packets for Cos queue 4."
        ::= { rcPrQosCosQueLoopbackPortStatsEntry 20 }

rcPrQosCosQueLoopbackPortStatsQue4DropBytes	OBJECT-TYPE
	SYNTAX          Counter64
	MAX-ACCESS      read-only
        STATUS          current
        DESCRIPTION     "the drop bytes for Cos queue 4."
        ::= { rcPrQosCosQueLoopbackPortStatsEntry 21 }

rcPrQosCosQueLoopbackPortStatsQue5OutPackets	    OBJECT-TYPE
	SYNTAX          Counter64
	MAX-ACCESS      read-only
        STATUS          current
        DESCRIPTION     "the out packets for Cos queue 5."
        ::= { rcPrQosCosQueLoopbackPortStatsEntry 22 }

rcPrQosCosQueLoopbackPortStatsQue5OutBytes	    OBJECT-TYPE
	SYNTAX          Counter64
	MAX-ACCESS      read-only
        STATUS          current
        DESCRIPTION     "the out bytes for Cos queue 5."
        ::= { rcPrQosCosQueLoopbackPortStatsEntry 23 }

rcPrQosCosQueLoopbackPortStatsQue5DropPackets	OBJECT-TYPE
	SYNTAX          Counter64
	MAX-ACCESS      read-only
        STATUS          current
        DESCRIPTION     "the drop packets for Cos queue 5."
        ::= { rcPrQosCosQueLoopbackPortStatsEntry 24 }

rcPrQosCosQueLoopbackPortStatsQue5DropBytes	OBJECT-TYPE
	SYNTAX          Counter64
	MAX-ACCESS      read-only
        STATUS          current
        DESCRIPTION     "the drop bytes for Cos queue 5."
        ::= { rcPrQosCosQueLoopbackPortStatsEntry 25 }

rcPrQosCosQueLoopbackPortStatsQue6OutPackets	    OBJECT-TYPE
	SYNTAX          Counter64
	MAX-ACCESS      read-only
        STATUS          current
        DESCRIPTION     "the out packets for Cos queue 6."
        ::= { rcPrQosCosQueLoopbackPortStatsEntry 26 }

rcPrQosCosQueLoopbackPortStatsQue6OutBytes	    OBJECT-TYPE
	SYNTAX          Counter64
	MAX-ACCESS      read-only
        STATUS          current
        DESCRIPTION     "the out bytes for Cos queue 6."
        ::= { rcPrQosCosQueLoopbackPortStatsEntry 27 }

rcPrQosCosQueLoopbackPortStatsQue6DropPackets	OBJECT-TYPE
	SYNTAX          Counter64
	MAX-ACCESS      read-only
        STATUS          current
        DESCRIPTION     "the drop packets for Cos queue 6."
        ::= { rcPrQosCosQueLoopbackPortStatsEntry 28 }

rcPrQosCosQueLoopbackPortStatsQue6DropBytes	OBJECT-TYPE
	SYNTAX          Counter64
	MAX-ACCESS      read-only
        STATUS          current
        DESCRIPTION     "the drop bytes for Cos queue 6."
        ::= { rcPrQosCosQueLoopbackPortStatsEntry 29 }

rcPrQosCosQueLoopbackPortStatsQue7OutPackets	    OBJECT-TYPE
	SYNTAX          Counter64
	MAX-ACCESS      read-only
        STATUS          current
        DESCRIPTION     "the out packets for Cos queue 7."
        ::= { rcPrQosCosQueLoopbackPortStatsEntry 30 }

rcPrQosCosQueLoopbackPortStatsQue7OutBytes	    OBJECT-TYPE
	SYNTAX          Counter64
	MAX-ACCESS      read-only
        STATUS          current
        DESCRIPTION     "the out bytes for Cos queue 7."
        ::= { rcPrQosCosQueLoopbackPortStatsEntry 31 }

rcPrQosCosQueLoopbackPortStatsQue7DropPackets	OBJECT-TYPE
	SYNTAX          Counter64
	MAX-ACCESS      read-only
        STATUS          current
        DESCRIPTION     "the drop packets for Cos queue 7."
        ::= { rcPrQosCosQueLoopbackPortStatsEntry 32 }

rcPrQosCosQueLoopbackPortStatsQue7DropBytes	OBJECT-TYPE
	SYNTAX          Counter64
	MAX-ACCESS      read-only
        STATUS          current
        DESCRIPTION     "the drop bytes for Cos queue 7."
        ::= { rcPrQosCosQueLoopbackPortStatsEntry 33 }

rcPrQosCosQueLoopbackPortStatsClearStat OBJECT-TYPE
        SYNTAX        TruthValue
        MAX-ACCESS    read-write
        STATUS        current
	DESCRIPTION  "Clear stats."
    ::= { rcPrQosCosQueLoopbackPortStatsEntry 34 }

rcPrQosCosQueCppPortStatsTable OBJECT-TYPE
        SYNTAX        SEQUENCE OF RcPrQosCosQueCppPortStatsEntry
        MAX-ACCESS    not-accessible
        STATUS        current
        DESCRIPTION   "This table is used to get the qos cos queue port stats."
        ::= { rcPrQos 17 }

rcPrQosCosQueCppPortStatsEntry OBJECT-TYPE
        SYNTAX        RcPrQosCosQueCppPortStatsEntry
        MAX-ACCESS    not-accessible
        STATUS        current
        DESCRIPTION   "Entry containing information of port Qos cosq stats"
        INDEX         { rcPrQosCosQueCppPortStatsIndex }
        ::= { rcPrQosCosQueCppPortStatsTable 1 }

RcPrQosCosQueCppPortStatsEntry ::= SEQUENCE {
                rcPrQosCosQueCppPortStatsIndex        INTEGER,
                rcPrQosCosQueCppPortStatsOutPackets   Counter64,
                rcPrQosCosQueCppPortStatsOutBytes     Counter64,
                rcPrQosCosQueCppPortStatsDropPackets  Counter64,
                rcPrQosCosQueCppPortStatsDropBytes    Counter64
}

rcPrQosCosQueCppPortStatsIndex     OBJECT-TYPE
	SYNTAX          INTEGER (0..15)
	MAX-ACCESS      not-accessible
        STATUS          current
        DESCRIPTION     "Used to indicate the cos queue number from 0 to 15."
        ::= { rcPrQosCosQueCppPortStatsEntry 1 }

rcPrQosCosQueCppPortStatsOutPackets	    OBJECT-TYPE
	SYNTAX          Counter64
	MAX-ACCESS      read-only
        STATUS          current
        DESCRIPTION     "the out packets for cpp port."
        ::= { rcPrQosCosQueCppPortStatsEntry 2 }

rcPrQosCosQueCppPortStatsOutBytes	    OBJECT-TYPE
	SYNTAX          Counter64
	MAX-ACCESS      read-only
        STATUS          current
        DESCRIPTION     "the out bytes for cpp port."
        ::= { rcPrQosCosQueCppPortStatsEntry 3 }

rcPrQosCosQueCppPortStatsDropPackets	OBJECT-TYPE
	SYNTAX          Counter64
	MAX-ACCESS      read-only
        STATUS          current
        DESCRIPTION     "the drop packets for cpp port."
        ::= { rcPrQosCosQueCppPortStatsEntry 4 }

rcPrQosCosQueCppPortStatsDropBytes	OBJECT-TYPE
	SYNTAX          Counter64
	MAX-ACCESS      read-only
        STATUS          current
        DESCRIPTION     "the drop bytes for cpp port."
        ::= { rcPrQosCosQueCppPortStatsEntry 5 }

rcPrQosCosQue  OBJECT IDENTIFIER     ::= { rcPrQos 18 }

rcPrQosCosQueCpuStatsClear OBJECT-TYPE
     SYNTAX       TruthValue
     MAX-ACCESS   read-write
     STATUS       current
     DESCRIPTION  "Clear cpu qos cos queue statistics."
     ::= {rcPrQosCosQue  1 }

--
-- The rcPrFilter group
--

rcPrFilterScalars OBJECT IDENTIFIER ::= { rcPrFilter 1 }

rcPrFilterActTableSize OBJECT-TYPE
        SYNTAX          INTEGER (1..4096)
        MAX-ACCESS      read-only
        STATUS          current
        DESCRIPTION     "Used to indicate the number of Act entries in the
                        rcPrFilterActTable. Default table size is 0 until the
                        administrator configures any Act entries."
        ::= { rcPrFilterScalars 1 }

rcPrFilterAclTableSize  OBJECT-TYPE
     SYNTAX             INTEGER (1..4096)
     MAX-ACCESS         read-only
     STATUS             current
     DESCRIPTION        "Used to indicate the number of Acl entries
                        in the rcPrFilterAclTable.  Default table size is 0
                        until the administrator configures any Acl entries."
     ::= { rcPrFilterScalars 2 }

rcPrFilterAceTableSize OBJECT-TYPE
     SYNTAX             INTEGER (0..16384)
     MAX-ACCESS         read-only
     STATUS             current
     DESCRIPTION        "Used to indicate the number of Ace entries in the
                        rcPrFilterAceTable. Default table size is 0 until the
                        administrator configures any Ace entries. The maximum
			size is # of Acls multiplied by # of Aces."
     ::= { rcPrFilterScalars 3 }

rcPrFilterAclBufferWrap OBJECT-TYPE
     SYNTAX             TruthValue
     MAX-ACCESS         read-write
     STATUS             current
     DESCRIPTION        "Used to enable or disable buffer wrapping for
                         filters log."
     ::= { rcPrFilterScalars 4 }

rcPrFilterAclClearLog OBJECT-TYPE
     SYNTAX             TruthValue
     MAX-ACCESS         read-write
     STATUS             current
     DESCRIPTION        "Used to clear the filter Logs collected."
     ::= { rcPrFilterScalars 5 }

--
-- Power Ranger (PR) Acl MIB specification
--
--   o    The Access Control List (Acl) mib defines management objects for
--        configuration information of the hardware-assisted filtering feature.
--
--   o    Acl is a group of filtering rules organized in an ordered list.
--
--   o    A filtering rule in the Acl is called an Access Control Entry (Ace).
--
--   o    All the rules in an ACL have a fixed superset of match fields upto a
--        supported number of fields. The fixed superset is configured as
--        desired match fields. Such a superset is called Access Control
--        Template (Act).
--
--   o	  Max of 4k ACTs; each ACT can be attached to several ACLs.
--
--   o	  Max of 4k ACLs; each ACL is attached to 1 and only 1 ACT.
--	  Each ACL can have a maximum of 1k ACEs. Ports are assigned
--	  from 1-500 and VLANs are assigned from 501-1000.
--
--   o	  Max of 10k ACEs; each ACE belongs to a single ACL. Precedence
--	  is determined by the Ace-Id (lower Ace-Id means higher precedence).
--

rcPrFilterAct OBJECT IDENTIFIER ::= { rcPrFilter 2 }

-- ACT Table

rcPrFilterActTable OBJECT-TYPE
        SYNTAX          SEQUENCE OF RcPrFilterActEntry
        MAX-ACCESS      not-accessible
        STATUS          current
        DESCRIPTION     "A table of Acts to store information of each Act
                         entry. This table is indexed by the Act Id."
        ::= { rcPrFilterAct 1 }

rcPrFilterActEntry OBJECT-TYPE
        SYNTAX          RcPrFilterActEntry
        MAX-ACCESS      not-accessible
        STATUS          current
        DESCRIPTION     "One Act Entry holding Act information."
        INDEX           { rcPrFilterActId }
        ::= { rcPrFilterActTable 1 }

RcPrFilterActEntry ::= SEQUENCE {
        rcPrFilterActId              INTEGER,
        rcPrFilterActName            DisplayString,
        rcPrFilterActArpAttrs        INTEGER,
        rcPrFilterActEthernetAttrs   INTEGER,
        rcPrFilterActIpAttrs         INTEGER,
        rcPrFilterActProtocolAttrs   INTEGER,
        rcPrFilterActApply           TruthValue,
        rcPrFilterActRowStatus       RowStatus,
        rcPrFilterActIpv6Attrs       INTEGER
}

rcPrFilterActId OBJECT-TYPE
        SYNTAX          INTEGER (1..4096)
        MAX-ACCESS      not-accessible
        STATUS          current
        DESCRIPTION     "A table of Acts to store information of each
                        Act. This table is indexed by the Act Id."
        ::= { rcPrFilterActEntry 1 }

rcPrFilterActName OBJECT-TYPE
        SYNTAX          DisplayString (SIZE (0..32))
        MAX-ACCESS      read-create
        STATUS          current
        DESCRIPTION     "A descriptive name chosen by the administrator
	                for the Act Entry."
        ::= { rcPrFilterActEntry 2 }

rcPrFilterActArpAttrs OBJECT-TYPE
        SYNTAX        	INTEGER (0..1)
        MAX-ACCESS    	read-create
        STATUS        	current
        DESCRIPTION   	"Value is one or multiple (logical 'OR' of the
			following):
				none(0),
	                  	operation(1)
			none:      No Arp Attrs are selected or to clear
			           other choices.
			operation: Only valid option for Arp attributes."
	DEFVAL		{ 0 }
        ::= { rcPrFilterActEntry 3 }

rcPrFilterActEthernetAttrs OBJECT-TYPE
         SYNTAX        	INTEGER (0..63)
        MAX-ACCESS      read-create
        STATUS          current
        DESCRIPTION     "Value is one or multiple of the following:
			    none(0),
                            srcMac(1),
			    dstMac(2),
			    etherType(4),
			    port(8),
                            vlan(16),
			    vlanTagPrio(32)
			none: If selected then unselect all other selections."
	DEFVAL		{ 0 }
        ::= { rcPrFilterActEntry 4 }

rcPrFilterActIpAttrs OBJECT-TYPE
        SYNTAX        	INTEGER (0..63)
        MAX-ACCESS      read-create
        STATUS          current
        DESCRIPTION     "Value is one or multiple of the following:
			    none(0),
                            srcIp(1),
			    dstIp(2),
			    ipFragFlag(4),
			    ipOptions(8),
			    ipProtoType(16),
                            dscp(32)
			none: If selected then unselect all other selections."
	DEFVAL		{ 0 }
        ::= { rcPrFilterActEntry 5 }

rcPrFilterActProtocolAttrs OBJECT-TYPE
        SYNTAX        	INTEGER (0..127)
        MAX-ACCESS      read-create
        STATUS          current
        DESCRIPTION     "Value is one or multiple of the following:
                            none(0),
                            tcpSrcPort(1),
			    udpSrcPort(2),
			    tcpDstPort(4),
			    udpDstPort(8),
			    tcpFlags(16),
                            icmpMsgType(32),
                            icmpv6MsgType(64)
			none: If selected then unselect all other selections."
	DEFVAL		{ 0 }
        ::= { rcPrFilterActEntry 6 }

rcPrFilterActApply OBJECT-TYPE
        SYNTAX          TruthValue
        MAX-ACCESS      read-create
        STATUS          current
        DESCRIPTION    "When apply is issued by the administrator,
                        the ACT attributes cannot be modified."
        DEFVAL          { false }
        ::= { rcPrFilterActEntry 7 }

rcPrFilterActRowStatus  OBJECT-TYPE
        SYNTAX          RowStatus
        MAX-ACCESS      read-create
        STATUS          current
        DESCRIPTION     "Create/delete operations for this entry. The
                        entry cannot be modified or deleted while there
                        are Acls configured with this Act entry."
        ::= { rcPrFilterActEntry 8}

rcPrFilterActIpv6Attrs OBJECT-TYPE
        SYNTAX          INTEGER (0..63)
        MAX-ACCESS      read-write
        STATUS          current
        DESCRIPTION     "Value is one or multiple of the following:
                            none(0),
                            srcIpv6(1),
                            dstIpv6(2),
                            nextHdr(4),
                        none: If selected then unselect all other selections."
        DEFVAL          { 0 }
        ::= { rcPrFilterActEntry 9 }

-- Act Pattern Table to store the template

rcPrFilterActPatternTable OBJECT-TYPE
     SYNTAX             SEQUENCE OF RcPrFilterActPatternEntry
     MAX-ACCESS         not-accessible
     STATUS             current
     DESCRIPTION        "A table of user-defined parameters of  Acls to
                        store information of each Acl. This table is indexed
                        by the Act Id and PatternIndex."
     ::= { rcPrFilterAct 2 }

rcPrFilterActPatternEntry OBJECT-TYPE
     SYNTAX             RcPrFilterActPatternEntry
     MAX-ACCESS         not-accessible
     STATUS             current
     DESCRIPTION        "Entry containing Configuration information for a
                        particular Act."
     INDEX              { rcPrFilterActPatternActId,
                          rcPrFilterActPatternIndex }
     ::= { rcPrFilterActPatternTable 1 }

RcPrFilterActPatternEntry ::= SEQUENCE {
        rcPrFilterActPatternActId     INTEGER,
        rcPrFilterActPatternIndex     INTEGER,
        rcPrFilterActPatternName      DisplayString,
        rcPrFilterActPatternBase      INTEGER,
        rcPrFilterActPatternOffset    INTEGER,
        rcPrFilterActPatternLength    INTEGER,
        rcPrFilterActPatternRowStatus RowStatus
        }

rcPrFilterActPatternActId OBJECT-TYPE
     SYNTAX             INTEGER (1..4096)
     MAX-ACCESS         not-accessible
     STATUS             current
     DESCRIPTION        "An index to the ActPatternEntry, a unique
	                identifier for Act entry in the range of Table
			Size."
     ::= { rcPrFilterActPatternEntry 1 }

rcPrFilterActPatternIndex OBJECT-TYPE
     SYNTAX             INTEGER (1..16)
     MAX-ACCESS         not-accessible
     STATUS             current
     DESCRIPTION        "Indexes each user defined field pattern in an
                        Acl entry. In this release only 3 patterns are
                        allowed per ACT but we can have multiple
 			patterns per ACL."
     ::= { rcPrFilterActPatternEntry 2 }

rcPrFilterActPatternName OBJECT-TYPE
     SYNTAX             DisplayString (SIZE (0..32))
     MAX-ACCESS         read-create
     STATUS             current
     DESCRIPTION        "A descriptive name chosen by the administrator for
                        the Acl Pattern Entry."
     ::= { rcPrFilterActPatternEntry 3 }

rcPrFilterActPatternBase OBJECT-TYPE
     SYNTAX             INTEGER {
                            none(0),
                            etherBegin(1),
                            macDstBegin(2),
                            macSrcBegin(3),
                            ethTypeLenBegin(4),
                            arpBegin(5),
                            ipHdrBegin(6),
                            ipOptionsBegin(7),
                            ipPayloadBegin(8),
                            ipTosBegin(9),
                            ipProtoBegin(10),
                            ipSrcBegin(11),
                            ipDstBegin(12),
                            tcpBegin(13),
                            tcpSrcportBegin(14),
                            tcpDstportBegin(15),
                            tcpFlagsEnd(16),
                            udpBegin(17),
                            udpSrcportBegin(18),
                            udpDstportBegin(19),
                            etherEnd(20),
                            ipHdrEnd(21),
                            icmpMsgBegin(22),
                            tcpEnd(23),
                            udpEnd(24),
                            ipv6HdrBegin(25)
                        }
     MAX-ACCESS         read-create
     STATUS             current
     DESCRIPTION        "User defined fields from headers to be used in
                        the Aces of the Acl."
     DEFVAL             { none }
     ::= { rcPrFilterActPatternEntry 4 }

rcPrFilterActPatternOffset OBJECT-TYPE -- MA/DZ to confirm maximum
     SYNTAX             INTEGER (0..76800)
     MAX-ACCESS         read-create
     STATUS             current
     DESCRIPTION        "Set Offset in bits to the beginning offset of the user
                        defined field with selected header option as base."
     DEFVAL              { 0 }
     ::= { rcPrFilterActPatternEntry 5 }

rcPrFilterActPatternLength OBJECT-TYPE
     SYNTAX             INTEGER (0..56)
     MAX-ACCESS         read-create
     STATUS             current
     DESCRIPTION        "The number of bits to extract beginning from the
                        offset is set in rcPrFilterActPatternLength.
			Only 1-56 are valid."
     DEFVAL             { 0 }
     ::= { rcPrFilterActPatternEntry 6 }

rcPrFilterActPatternRowStatus OBJECT-TYPE
     SYNTAX             RowStatus
     MAX-ACCESS         read-create
     STATUS             current
     DESCRIPTION        "Create/delete operations for this entry."
     ::= { rcPrFilterActPatternEntry 7 }

rcPrFilterAcl OBJECT IDENTIFIER ::= { rcPrFilter 3 }

-- ACL Table

rcPrFilterAclTable      OBJECT-TYPE
     SYNTAX             SEQUENCE OF RcPrFilterAclEntry
     MAX-ACCESS         not-accessible
     STATUS             current
     DESCRIPTION        "A table of Acls to store information of each Acl.
                         This table is indexed by the Acl Id."
     ::= { rcPrFilterAcl 1 }

rcPrFilterAclEntry      OBJECT-TYPE
     SYNTAX             RcPrFilterAclEntry
     MAX-ACCESS         not-accessible
     STATUS             current
     DESCRIPTION        "Entry containing Configuration information for
                        a particular Acl."
     INDEX              { rcPrFilterAclId }
     ::= { rcPrFilterAclTable 1 }

RcPrFilterAclEntry ::= SEQUENCE {
        rcPrFilterAclId                      INTEGER,
        rcPrFilterAclActId                   INTEGER,
        rcPrFilterAclName                    DisplayString,
        rcPrFilterAclType                    INTEGER,
        rcPrFilterAclAceListSize             INTEGER,
        rcPrFilterAclDefaultAction           INTEGER,
        rcPrFilterAclGlobalAction            INTEGER,
        rcPrFilterAclState                   EnableValue,
        rcPrFilterAclVlanList                IdList,
        rcPrFilterAclPortList                PortSet,
        rcPrFilterAclRowStatus               RowStatus,
        rcPrFilterAclNumVlanIds              INTEGER,
        rcPrFilterAclPktType                 INTEGER,
        rcPrFilterAclControlPktRule          INTEGER,
        rcPrFilterAclVlanId                  Integer32,
        rcPrFilterAclMltId                   Integer32,
        rcPrFilterAclDstPortList             PortSet,
 	rcPrFilterAclIpfixState              EnableValue,
	rcPrFilterAclMatchType               INTEGER,
	rcPrFilterAclIsid                    Integer32,
        rcPrFilterAclOrigin                  BITS
        }

rcPrFilterAclId OBJECT-TYPE
     SYNTAX             INTEGER (1..4096)
     MAX-ACCESS         read-only
     STATUS             current
     DESCRIPTION        "A unique identifier for Acl entry in the range
                        of Table Size."
     ::= { rcPrFilterAclEntry 1 }

rcPrFilterAclActId OBJECT-TYPE
     SYNTAX             INTEGER (1..4096)
     MAX-ACCESS         read-create
     STATUS             current
     DESCRIPTION        "A unique identifier for Act entry in the range
                        of Table Size."
     ::= { rcPrFilterAclEntry 2 }

rcPrFilterAclName OBJECT-TYPE
     SYNTAX             DisplayString (SIZE (0..32))
     MAX-ACCESS         read-create
     STATUS             current
     DESCRIPTION        "A descriptive name chosen by the administrator for
                        the Acl Entry."
     ::= { rcPrFilterAclEntry 3 }

rcPrFilterAclType OBJECT-TYPE
     SYNTAX             INTEGER {
                            inVlan(1),
                            outVlan(2),
                            inPort(3),
                            outPort(4),
			    inVsn(5)
                        }
     MAX-ACCESS         read-create
     STATUS             current
     DESCRIPTION        "An Acl can be vlan-based or port-based.  An Ace
			has a capability to match packets classified as
			'ingress' and 'egress'. An ingress packet is
			assigned a value 'in' and an egress packet is
			assigned a value 'out'."
     ::= { rcPrFilterAclEntry 4 }

rcPrFilterAclAceListSize OBJECT-TYPE
     SYNTAX             INTEGER (0..1000)
     MAX-ACCESS         read-only
     STATUS             current
     DESCRIPTION        "Indicates the number of Aces in a particular Acl."
     ::= { rcPrFilterAclEntry 5 }

rcPrFilterAclDefaultAction OBJECT-TYPE
     SYNTAX              INTEGER {
                             deny(1),
                             permit(2)
                         }
     MAX-ACCESS          read-create
     STATUS              current
     DESCRIPTION         "Indicates action to be taken when none of the
                         Aces in the Acl match."
     DEFVAL              { permit }
     ::= { rcPrFilterAclEntry 6 }

rcPrFilterAclGlobalAction OBJECT-TYPE
     SYNTAX             INTEGER {
                            none(1),
                            mirror(2),
                            count(3),
                            mirror-count(4),
	       ipfix(5),
                            mirror-ipfix(6),
                            count-ipfix(7),
                            mirror-count-ipfix(8)
                        }
     MAX-ACCESS         read-create
     STATUS             current
     DESCRIPTION        "Indicates action is applied to all Aces that
	                match in an Acl."
     DEFVAL             { none }
     ::= { rcPrFilterAclEntry 7 }

rcPrFilterAclState OBJECT-TYPE
     SYNTAX             EnableValue
     MAX-ACCESS         read-create
     STATUS             current
     DESCRIPTION        "Enables/Disables the state of all Aces in the Acl"
     DEFVAL             { enable }
     ::= { rcPrFilterAclEntry 8 }

rcPrFilterAclVlanList OBJECT-TYPE
     SYNTAX             IdList(SIZE(4096))
     MAX-ACCESS         read-create
     STATUS             current
     DESCRIPTION        "An array used to indicate all the VLANs to be
                        associated with this Acl Entry. At present, only 4k
			Vlans are supported."
     ::= { rcPrFilterAclEntry 9 }

rcPrFilterAclPortList OBJECT-TYPE
     SYNTAX             PortSet
     MAX-ACCESS         read-create
     STATUS             current
     DESCRIPTION        "Indicates the ports to be added to this Acl Entry."
     ::= { rcPrFilterAclEntry 10 }

rcPrFilterAclRowStatus OBJECT-TYPE
     SYNTAX             RowStatus
     MAX-ACCESS         read-create
     STATUS             current
     DESCRIPTION        "Create/delete operations for the entry. Deleting
                        a non-empty Acl results in deletion of member Aces
                        and then the Acl."
     ::= { rcPrFilterAclEntry 11 }

rcPrFilterAclNumVlanIds OBJECT-TYPE
     SYNTAX             INTEGER (1..4096)
     MAX-ACCESS         read-only
     STATUS             current
     DESCRIPTION        "Used to Indicate the number of VLAN ID's that
                         are stored in the rcPrFilterAclVlanList."
     ::= { rcPrFilterAclEntry 12 }

rcPrFilterAclPktType OBJECT-TYPE
     SYNTAX             INTEGER {
			ipv4(1),
			ipv6(2),
			nonipv6(3)
		               }
     MAX-ACCESS         read-write
     STATUS             current
     DESCRIPTION        "Indicates the packet type that this ACL is applicable to.
	 		VSP9k introduced nonipv6(3) to replace the ipv4(1) in release
			VSP 3.4.0.0. It means that ipv4(1) i snot applicable to VSP9k.
			And the default value in VSP is also set to nonipv6 (3)"
     DEFVAL             { ipv4 }
     ::= { rcPrFilterAclEntry 13 }

rcPrFilterAclControlPktRule OBJECT-TYPE
     SYNTAX             INTEGER {
                            deny(1),
                            permit(2)
                        }
     MAX-ACCESS         read-write
     STATUS             current
     DESCRIPTION        "When the rcPrFilterAclDefaultAction object is set
                         to deny then control packets follow this rule.
                         Otherwise, the object value can be ignored."
     DEFVAL             { permit }
     ::= { rcPrFilterAclEntry 14 }

rcPrFilterAclVlanId OBJECT-TYPE
     SYNTAX             Integer32(0..4094)
     MAX-ACCESS         read-write
     STATUS             current
     DESCRIPTION        "Destination Vlan Id for mirroring the packets.
                         The value 0 means no vlan is being mirrored.
                         When the value of rcPrFilterAclVlanId is non-zero,
                         the values of rcPrFilterAclMltId and
                         rcPrFilterAclDstPortList must be 0."
     DEFVAL             { 0 }
     ::= { rcPrFilterAclEntry 15 }

rcPrFilterAclMltId OBJECT-TYPE
     SYNTAX             Integer32(0..512)
     MAX-ACCESS         read-write
     STATUS             current
     DESCRIPTION        "Destination Mlt Id for mirroring the packets.
                         The value 0 means no mlt is being mirrored.
                         When the value of rcPrFilterAclMltId is non-zero,
                         the values of rcPrFilterAclVlanId and
                         rcPrFilterAclDstPortList must be 0."
     DEFVAL             { 0 }
     ::= { rcPrFilterAclEntry 16 }

rcPrFilterAclDstPortList OBJECT-TYPE
     SYNTAX             PortSet
     MAX-ACCESS         read-write
     STATUS             current
     DESCRIPTION        "Destination Port List for mirroring the packets.
                         The value 0 means no port(s) is being mirrored.
                         When the value of rcPrFilterAclDstPortList is non-zero,                         the values of rcPrFilterAclVlanId and
                         rcPrFilterAclMltId must be 0."
     ::= { rcPrFilterAclEntry 17 }

rcPrFilterAclIpfixState OBJECT-TYPE
     SYNTAX          EnableValue
     MAX-ACCESS      read-write
     STATUS          current
     DESCRIPTION     "Value indicating whether ipfix option on the
                      Acl is enabled."
     DEFVAL          { disable }
     ::= { rcPrFilterAclEntry 18 }

rcPrFilterAclMatchType OBJECT-TYPE
     SYNTAX             INTEGER {
                            uniOnly (1),
                            terminatingNNIOnly (2),
                            both(3)
                        }
     MAX-ACCESS         read-write
     STATUS             current
     DESCRIPTION        "Indicates the match type that the traffic is
	                ingress on UNI or terminated NNI or both"
     DEFVAL             { both }
     ::= { rcPrFilterAclEntry  19 }

rcPrFilterAclIsid OBJECT-TYPE
     SYNTAX             Integer32(0..15999999)
     MAX-ACCESS         read-write
     STATUS             current
     DESCRIPTION        "For IP shortcut, I-SID is zero. For L3 vsn, Inter
	                 I-SID routing, I-SID is configured I-SID value
			 ie other than zero."
     ::= { rcPrFilterAclEntry 20 }



rcPrFilterAclOrigin  OBJECT-TYPE
        SYNTAX BITS {
              config(0),
              eap(1)
        }
        MAX-ACCESS    read-only
        STATUS        current
        DESCRIPTION   "Indicates how the ACL was created.
                       Supported values:
                       config - ACL created by user
                       eap - ACL created by EAP via Radius response"
        ::= { rcPrFilterAclEntry 21 }


 -- Acl Stats Table

rcPrFilterAclStatsTable      OBJECT-TYPE
     SYNTAX             SEQUENCE OF RcPrFilterAclStatsEntry
     MAX-ACCESS         not-accessible
     STATUS             current
     DESCRIPTION        "A table of Acls Statistics entries to store the
			Default Acl statistics for each Acl.
			This table is indexed by the Acl Id."
     ::= { rcPrFilterAcl 2 }

rcPrFilterAclStatsEntry      OBJECT-TYPE
     SYNTAX             RcPrFilterAclStatsEntry
     MAX-ACCESS         not-accessible
     STATUS             current
     DESCRIPTION        "Entry containing default statistics information for
                        a particular Acl."
     INDEX              { rcPrFilterAclStatsAclId }
     ::= { rcPrFilterAclStatsTable 1 }

RcPrFilterAclStatsEntry ::= SEQUENCE {
        rcPrFilterAclStatsAclId                   INTEGER,
        rcPrFilterAclStatsMatchDefaultCounterPkts Counter64,
        rcPrFilterAclStatsMatchDefaultOctets      Counter64,
        rcPrFilterAclStatsClear                   TruthValue,
        rcPrFilterAclStatsMatchDefaultSecurityPkts      Counter64,
        rcPrFilterAclStatsMatchDefaultSecurityOctets    Counter64,
        rcPrFilterAclStatsMatchDefaultQosPkts           Counter64,
        rcPrFilterAclStatsMatchDefaultQosOctets         Counter64,
        rcPrFilterAclStatsMatchGlobalSecurityPkts       Counter64,
        rcPrFilterAclStatsMatchGlobalSecurityOctets     Counter64,
        rcPrFilterAclStatsMatchGlobalQosPkts            Counter64,
        rcPrFilterAclStatsMatchGlobalQosOctets          Counter64
        }

rcPrFilterAclStatsAclId OBJECT-TYPE
     SYNTAX             INTEGER (1..4096)
     MAX-ACCESS         not-accessible
     STATUS             current
     DESCRIPTION        "A unique identifier for Acl entry in the range
                        of Table Size."
     ::= { rcPrFilterAclStatsEntry 1 }

rcPrFilterAclStatsMatchDefaultCounterPkts OBJECT-TYPE
     SYNTAX             Counter64
     MAX-ACCESS         read-only
     STATUS             current
     DESCRIPTION        "Packet count of traffic not matching any of the
                        Ace rules or hit the Default Action that have the
                        count bit turned on in Acl Global Action."
     ::= { rcPrFilterAclStatsEntry 2 }

rcPrFilterAclStatsMatchDefaultOctets  OBJECT-TYPE
     SYNTAX             Counter64
     MAX-ACCESS         read-only
     STATUS             current
     DESCRIPTION        "Byte count of traffic not matching any of the Ace
                        rules or hit the Default Action that have the
                        count bit turned on in Acl Global Action."
     ::= { rcPrFilterAclStatsEntry 3 }

rcPrFilterAclStatsClear  OBJECT-TYPE
     SYNTAX             TruthValue
     MAX-ACCESS         read-create
     STATUS             current
     DESCRIPTION        "Clear default statistics for ACL Filters."
     ::= { rcPrFilterAclStatsEntry 4 }

rcPrFilterAclStatsMatchDefaultSecurityPkts OBJECT-TYPE
     SYNTAX             Counter64
     MAX-ACCESS         read-only
     STATUS             current
     DESCRIPTION        "Security packet count of traffic not matching any of the                          ACE rules or hits on Default Action where the count bit                         is turned on in ACL Global Action."
     ::= { rcPrFilterAclStatsEntry 5 }

rcPrFilterAclStatsMatchDefaultSecurityOctets OBJECT-TYPE
     SYNTAX             Counter64
     MAX-ACCESS         read-only
     STATUS             current
     DESCRIPTION        "Security octet count of traffic not matching any of the                         ACE rules or hits on Default Action where the count bit                         is turned on in ACL Global Action."
     ::= { rcPrFilterAclStatsEntry 6 }

rcPrFilterAclStatsMatchDefaultQosPkts OBJECT-TYPE
     SYNTAX             Counter64
     MAX-ACCESS         read-only
     STATUS             current
     DESCRIPTION        "QOS packet count of traffic not matching any of the
                         ACE rules or hits on Default Action where the count bit                         is turned on in ACL Global Action."
     ::= { rcPrFilterAclStatsEntry 7 }

rcPrFilterAclStatsMatchDefaultQosOctets OBJECT-TYPE
     SYNTAX             Counter64
     MAX-ACCESS         read-only
     STATUS             current
     DESCRIPTION        "QOS octet count of traffic not matching any of the
                         ACE rules or hits on Default Action where the count bit                         is turned on in ACL Global Action."
     ::= { rcPrFilterAclStatsEntry 8 }

rcPrFilterAclStatsMatchGlobalSecurityPkts OBJECT-TYPE
     SYNTAX             Counter64
     MAX-ACCESS         read-only
     STATUS             current
     DESCRIPTION        "Security packet count of traffic matching any of the
                         ACE rules or hits on Default Action where the count bit                         is turned on in ACL Global Action."
     ::= { rcPrFilterAclStatsEntry 9 }

rcPrFilterAclStatsMatchGlobalSecurityOctets OBJECT-TYPE
     SYNTAX             Counter64
     MAX-ACCESS         read-only
     STATUS             current
     DESCRIPTION        "Security octet count of traffic matching any of the
                         ACE rules or hits on Default Action where the count bit                         is turned on in ACL Global Action."
     ::= { rcPrFilterAclStatsEntry 10 }

rcPrFilterAclStatsMatchGlobalQosPkts OBJECT-TYPE
     SYNTAX             Counter64
     MAX-ACCESS         read-only
     STATUS             current
     DESCRIPTION        "QOS packet count of traffic matching any of the
                         ACE rules or hits on Default Action where the count bit                         is turned on in ACL Global Action."
     ::= { rcPrFilterAclStatsEntry 11 }

rcPrFilterAclStatsMatchGlobalQosOctets OBJECT-TYPE
     SYNTAX             Counter64
     MAX-ACCESS         read-only
     STATUS             current
     DESCRIPTION        "QOS octet count of traffic matching any of the
                         ACE rules or hits on Default Action where the count bit                         is turned on in ACL Global Action."
     ::= { rcPrFilterAclStatsEntry 12 }

-- Ace Table

rcPrFilterAce OBJECT IDENTIFIER ::= { rcPrFilter 4 }

-- Ace information is organized in 28 entries:
-- rcPrFilterAceEntry
-- rcPrFilterAceEthSrcAddrEntry
-- rcPrFilterAceEthDstAddrEntry
-- rcPrFilterAceEthEtherEntry
-- rcPrFilterAceEthVlanTagPrioEntry
-- rcPrFilterAceEthPortEntry
-- rcPrFilterAceEthVlanIdEntry
-- rcPrFilterAceArpEntry
-- rcPrFilterAceIpSrcAddrEntry
-- rcPrFilterAceIpDstAddrEntry
-- rcPrFilterAceIpDscpEntry
-- rcPrFilterAceIpProtoEntry
-- rcPrFilterAceIpOptionsEntry
-- rcPrFilterAceIpFragEntry
-- rcPrFilterAceProtoTcpSrcPortEntry
-- rcPrFilterAceProtoUdpSrcPortEntry
-- rcPrFilterAceProtoTcpDstPortEntry
-- rcPrFilterAceProtoUdpDstPortEntry
-- rcPrFilterAceProtoIcmpMsgTypeEntry
-- rcPrFilterAceProtoTcpFlagsEntry
-- rcPrFilterAcePattern1Entry
-- rcPrFilterAcePattern2Entry
-- rcPrFilterAcePattern3Entry
-- rcPrFilterAceStatsEntry
-- rcPrFilterAceEthShowEntry
-- rcPrFilterAceIpShowEntry
-- rcPrFilterAceProtoShowEntry
-- rcPrFilterAcePatternShowEntry

rcPrFilterAceTable      OBJECT-TYPE
     SYNTAX             SEQUENCE OF RcPrFilterAceEntry
     MAX-ACCESS         not-accessible
     STATUS             current
     DESCRIPTION        "A table of Aces to store information of each Ace
                        in context of its parent Acl. This is indexed by
                        AclId and AceId."
     ::= { rcPrFilterAce 1 }

rcPrFilterAceEntry      OBJECT-TYPE
     SYNTAX             RcPrFilterAceEntry
     MAX-ACCESS         not-accessible
     STATUS             current
     DESCRIPTION        "One Ace entry holding Ace information. Ace is a
                        member of one Acl."
     INDEX              { rcPrFilterAceAclId,
                          rcPrFilterAceId }
     ::= {rcPrFilterAceTable 1}

RcPrFilterAceEntry ::= SEQUENCE {
        rcPrFilterAceAclId              INTEGER,
        rcPrFilterAceId                 INTEGER,
        rcPrFilterAceName               DisplayString,
        rcPrFilterAceMode               INTEGER,
        rcPrFilterAceRemarkDscp         INTEGER,
        rcPrFilterAceRemarkDot1Priority INTEGER,
        rcPrFilterAceRedirectNextHop    IpAddress,
        rcPrFilterAceRedirectUnreach    INTEGER,
        rcPrFilterAcePolice		INTEGER,
        rcPrFilterAceAdminState         EnableValue,
        rcPrFilterAceOperState          INTEGER,
        rcPrFilterAceEgressQueue        INTEGER,
        rcPrFilterAceEgressQueue1g      INTEGER,
        rcPrFilterAceEgressQueue10g     INTEGER,
	rcPrFilterAceEgressQueueNNSC    INTEGER,
	rcPrFilterAceFlags		INTEGER,
        rcPrFilterAceStopOnMatch        EnableValue,
        rcPrFilterAceMltIndex           INTEGER,
        rcPrFilterAceRowStatus          RowStatus,
        rcPrFilterAceIpfixState         EnableValue,
        rcPrFilterAceRedirectNextHopIpv6    Ipv6Address,
        rcPrFilterAceDstPortList        PortSet,
        rcPrFilterAceDstVlanId          INTEGER,
        rcPrFilterAceDstMltId           INTEGER,
        rcPrFilterAceInternalQos        Integer32,
        rcPrFilterAceCount              EnableValue,
        rcPrFilterAceLog                EnableValue,
        rcPrFilterAceCopytoPcap         EnableValue,
        rcPrFilterAceDstIp              IpAddress,
        rcPrFilterAceDstIpTtl           Integer32,
        rcPrFilterAceDstIpDscp          INTEGER,
	rcPrFilterAceMonitoringIsidOffset Integer32,
	rcPrFilterAceMonitoringIsid     Integer32,
	rcPrFilterAceMirroringQos	Integer32,
	rcPrFilterAceRemoveTag		TruthValue,
        rcPrFilterAceRedirectNextHopVrfName DisplayString
       }

rcPrFilterAceAclId OBJECT-TYPE
     SYNTAX             INTEGER (1..4096)
     MAX-ACCESS         not-accessible
     STATUS             current
     DESCRIPTION        "An index to the AceEntry, a unique
	                identifier for Acl entry in the range of Table
			Size."
     ::= { rcPrFilterAceEntry 1 }

rcPrFilterAceId OBJECT-TYPE
     SYNTAX             INTEGER (1..1000)
     MAX-ACCESS         not-accessible
     STATUS             current
     DESCRIPTION        "AceId uniquely identifies one Ace entry."
     ::= { rcPrFilterAceEntry 2 }

rcPrFilterAceName OBJECT-TYPE
     SYNTAX             DisplayString (SIZE (0..32))
     MAX-ACCESS         read-create
     STATUS             current
     DESCRIPTION        "A descriptive name chosen by the administrator.
                        System automatically assigns a name if the user
                        has not assigned one."
     ::= { rcPrFilterAceEntry 3 }

rcPrFilterAceMode       OBJECT-TYPE
     SYNTAX             INTEGER {
                            none(0),
                            deny(1),
                            permit(2)
                        }
     MAX-ACCESS         read-create
     STATUS             current
     DESCRIPTION        "Operating Mode associated with the Ace is effective
                        on the packets matching this Ace."
     DEFVAL             { none }
     ::= { rcPrFilterAceEntry 4 }

rcPrFilterAceRemarkDscp OBJECT-TYPE
     SYNTAX             INTEGER {
                            phbcs0(0),
                            phbcs1(8),
                            phbaf11(10),
                            phbaf12(12),
                            phbaf13(14),
                            phbcs2(16),
                            phbaf21(18),
                            phbaf22(20),
                            phbaf23(22),
                            phbcs3(24),
                            phbaf31(26),
                            phbaf32(28),
                            phbaf33(30),
                            phbcs4(32),
                            phbaf41(34),
                            phbaf42(36),
                            phbaf43(38),
                            phbcs5(40),
                            phbef(46),
                            phbcs6(48),
                            phbcs7(56),
                            disable(256) -- Invalid ToS/Dscp value
                        }
     MAX-ACCESS         read-create
     STATUS             current
     DESCRIPTION        "The 6-bit DSCP field from the ToS byte in Ipv4 header
                        encodes the PHB information per DiffServ standards
                        (Refer to DiffServ RFCs 2474). Set the Dscp to PHB
                        (like EF) or PHB-class(like AF1 which includes AF11,
                        AF12,AF13) to mark specific diffserv class traffic.
                        Set the field value to desired integer dscp code for
                        rcPrFilterAceRemarkDscp field to mark non-standard
                        traffic classes and local use PHBs."
     DEFVAL             { disable }
     ::= { rcPrFilterAceEntry 5 }

rcPrFilterAceRemarkDot1Priority OBJECT-TYPE
     SYNTAX             INTEGER {
                            zero(0),
                            one(1),
                            two(2),
                            three(3),
                            four(4),
                            five(5),
                            six(6),
                            seven(7),
                            disable(8)
                        }
     MAX-ACCESS         read-create
     STATUS             current
     DESCRIPTION        "Dot1 Priority as described by Layer 2 standards,
                        802.1Q, 802.1P."
     DEFVAL             { disable }
     ::= { rcPrFilterAceEntry 6 }

rcPrFilterAceRedirectNextHop OBJECT-TYPE
     SYNTAX             IpAddress
     MAX-ACCESS         read-create
     STATUS             current
     DESCRIPTION        "Redirect matching IP traffic to the next hop."
     DEFVAL             { '00000000'H }    -- 0.0.0.0
     ::= { rcPrFilterAceEntry 7 }

rcPrFilterAceRedirectUnreach OBJECT-TYPE
     SYNTAX             INTEGER {
                            deny(1),
                            permit(2)
                        }
     MAX-ACCESS         read-create
     STATUS              current
     DESCRIPTION        "Set the desired behavior for redirected traffic in
                        case the specified next-hop is not reachable."
     DEFVAL             { deny }
     ::= { rcPrFilterAceEntry 8 }

rcPrFilterAcePolice  OBJECT-TYPE
     SYNTAX          INTEGER (0..16383)
     MAX-ACCESS      read-create
     STATUS          current
     DESCRIPTION     "Policing profile Identifier. Set the desired policing
                     profile identifier. Set the value to 0 when policing
                     is not desired."
     DEFVAL          { 0 }
     ::= { rcPrFilterAceEntry 9 }

rcPrFilterAceAdminState OBJECT-TYPE
     SYNTAX          EnableValue
     MAX-ACCESS      read-create
     STATUS          current
     DESCRIPTION     "Value indicating whether the Ace is enabled.
		     An Ace can only be modified if it is disabled."
     DEFVAL          { disable }
     ::= { rcPrFilterAceEntry 10 }

rcPrFilterAceOperState  OBJECT-TYPE
     SYNTAX          INTEGER {
                         up (1),
                         down (2)
                     }
     MAX-ACCESS      read-only
     STATUS          current
     DESCRIPTION     "The current operational state of the Ace."
     ::= { rcPrFilterAceEntry 11 }

rcPrFilterAceEgressQueue OBJECT-TYPE
     SYNTAX          INTEGER (0..64)
     MAX-ACCESS      read-create
     STATUS          current
     DESCRIPTION     "Indicates the Egress Queue for 10/100 card. If only 1
	             value is specified then this value is applied to
		     Queue1g and Queue10g as well. If 2 values are
		     specified then the first value is applied to 10/100
		     card and the second value is applied to 1gig and 10gig
		     cards. If all three values are specified, then all
		     three values are applied respectively to the appropriate
		     Egress Queue.

		     If value is greater than 8, it will not be applied to
		     the 10/100 card as it only has 8 queues.  However, the
		     value will be applied to the 1gig and 10gig card types."
     DEFVAL          { 8 }
     ::= { rcPrFilterAceEntry 12 }

rcPrFilterAceEgressQueue1g OBJECT-TYPE
     SYNTAX          INTEGER (0..64)
     MAX-ACCESS      read-create
     STATUS          current
     DESCRIPTION     "Indicates the Egress Queue for 1gig card."
     DEFVAL          { 64 }
     ::= { rcPrFilterAceEntry 13 }

rcPrFilterAceEgressQueue10g OBJECT-TYPE
     SYNTAX          INTEGER (0..64)
     MAX-ACCESS      read-create
     STATUS          current
     DESCRIPTION     "Indicates the Egress Queue for 10gig card."
     DEFVAL          { 64 }
     ::= { rcPrFilterAceEntry 14 }

rcPrFilterAceEgressQueueNNSC OBJECT-TYPE
     SYNTAX             INTEGER {
                            platinum(0),
                            gold(1),
                            silver(2),
                            bronze(3),
                            standard(4),
                            custom(5),
                            premium(6),
                            critical(7),
                            disable(8)
                        }
     MAX-ACCESS         read-create
     STATUS             current
     DESCRIPTION        "Ace Egress Queue NNSC."
     DEFVAL             { disable }
     ::= { rcPrFilterAceEntry 15 }

rcPrFilterAceFlags OBJECT-TYPE
     SYNTAX             INTEGER (0..31)
     MAX-ACCESS         read-create
     STATUS             current
     DESCRIPTION        "Bitmask for the flags:

                        none(0): Default value for the flags.

	                stopOnMatch(1): set desired behavior for flag
	                whether to stop or continue in case an Ace
			matching the packet is found. When this Ace is hit,
			match on other Aces with a lower priority is not
			attempted.

			count(2): set desired behavior for flag i.e.
                        to enable/disable counting in case a packet matching
                        the ace is found.

			copyToPrimaryCp(4): set to enable/disable copying of
                        matching packets to primary CP.

			copyToSecondaryCp(8): set to enable/disable copying of
                        matching packets to secondary CP.

			mirror(16): set to enable/disable mirroring the
                        matching packets to an interface. System can mirror
                        one port or mirror to 1 port."

     ::= { rcPrFilterAceEntry 16 }

rcPrFilterAceStopOnMatch OBJECT-TYPE
     SYNTAX          EnableValue
     MAX-ACCESS      read-create
     STATUS          current
     DESCRIPTION     "Value indicating whether stop-on-match option on the
                      Ace is enabled."
     DEFVAL          { disable }
     ::= { rcPrFilterAceEntry 17 }

rcPrFilterAceMltIndex OBJECT-TYPE
     SYNTAX             INTEGER (0..8)
     MAX-ACCESS         read-create
     STATUS             current
     DESCRIPTION        "If this action is specified, it will
                         basically override the mlt-index picked
                         by the mlt algorithm, when a packet is
                         being sent out on MLT ports."
     DEFVAL             { 0 }
     ::= { rcPrFilterAceEntry 18 }

rcPrFilterAceRowStatus OBJECT-TYPE
     SYNTAX             RowStatus
     MAX-ACCESS         read-create
     STATUS             current
     DESCRIPTION        "Create/delete operations for this entry."
     ::= { rcPrFilterAceEntry 19 }

rcPrFilterAceIpfixState OBJECT-TYPE
     SYNTAX          EnableValue
     MAX-ACCESS      read-write
     STATUS          current
     DESCRIPTION     "Value indicating whether ipfix option on the
                      Ace is enabled."
     DEFVAL          { disable }
     ::= { rcPrFilterAceEntry 20 }

rcPrFilterAceRedirectNextHopIpv6 OBJECT-TYPE
     SYNTAX             Ipv6Address
     MAX-ACCESS         read-write
     STATUS             current
     DESCRIPTION        "Redirect matching IPv6 traffic to the next hop."
     ::= { rcPrFilterAceEntry 21 }

rcPrFilterAceDstPortList OBJECT-TYPE
        SYNTAX        PortSet
        MAX-ACCESS    read-create
        STATUS        current
        DESCRIPTION   "Destination Port List for mirroring the packets."
        ::= { rcPrFilterAceEntry 22 }

rcPrFilterAceDstVlanId OBJECT-TYPE
        SYNTAX        INTEGER (0..4094)
        MAX-ACCESS    read-create
        STATUS        current
        DESCRIPTION   "Destination Vlan to mirror the packets."
        ::= { rcPrFilterAceEntry 23 }

rcPrFilterAceDstMltId OBJECT-TYPE
        SYNTAX        INTEGER (0..256)
        MAX-ACCESS    read-create
        STATUS        current
        DESCRIPTION   "Destination Mlt to mirror the packets."
        ::= { rcPrFilterAceEntry 24 }

rcPrFilterAceInternalQos OBJECT-TYPE
        SYNTAX          Integer32 (0..7)
        MAX-ACCESS      read-write
        STATUS          current
        DESCRIPTION     "Internal QOS Level assigned to the packet flow"
        DEFVAL          { 1 }
        ::= { rcPrFilterAceEntry 25 }

rcPrFilterAceCount OBJECT-TYPE
     SYNTAX          EnableValue
     MAX-ACCESS      read-write
     STATUS          current
     DESCRIPTION     "Value indicating whether Count option on the
                      Ace is enabled."
     DEFVAL          { disable }
     ::= { rcPrFilterAceEntry 26 }

rcPrFilterAceLog OBJECT-TYPE
     SYNTAX          EnableValue
     MAX-ACCESS      read-write
     STATUS          current
     DESCRIPTION     "Value indicating whether log option on the
                      Ace is enabled."
     DEFVAL          { disable }
     ::= { rcPrFilterAceEntry 27 }

rcPrFilterAceCopytoPcap OBJECT-TYPE
     SYNTAX          EnableValue
     MAX-ACCESS      read-write
     STATUS          current
     DESCRIPTION     "Value indicating whether copy to pcap option
                      on the Ace is enabled."
     DEFVAL          { disable }
     ::= { rcPrFilterAceEntry 28 }

rcPrFilterAceDstIp OBJECT-TYPE
     SYNTAX        IpAddress
     MAX-ACCESS    read-write
     STATUS        current
     DESCRIPTION   "Destination IP address to mirror the packets."
     ::= { rcPrFilterAceEntry 29 }

rcPrFilterAceDstIpTtl OBJECT-TYPE
     SYNTAX          Integer32 (2..255)
     MAX-ACCESS      read-write
     STATUS          current
     DESCRIPTION     "Ttl value for the mirrored packet when mirror
                      destination is IP.  If other than default,
                      the encapsulated packet will have the given ttl."
     DEFVAL          { 64 }
     ::= { rcPrFilterAceEntry 30 }

rcPrFilterAceDstIpDscp OBJECT-TYPE
     SYNTAX             INTEGER {
                            phbcs0(0),
                            phbcs1(8),
                            phbaf11(10),
                            phbaf12(12),
                            phbaf13(14),
                            phbcs2(16),
                            phbaf21(18),
                            phbaf22(20),
                            phbaf23(22),
                            phbcs3(24),
                            phbaf31(26),
                            phbaf32(28),
                            phbaf33(30),
                            phbcs4(32),
                            phbaf41(34),
                            phbaf42(36),
                            phbaf43(38),
                            phbcs5(40),
                            phbef(46),
                            phbcs6(48),
                            phbcs7(56),
                            disable(256) -- Invalid ToS/Dscp value
                        }
     MAX-ACCESS         read-write
     STATUS             current
     DESCRIPTION        "Dscp value for the mirrored packet when mirror
                        destination is IP.  The 6-bit DSCP field from the
                        ToS byte in Ipv4 header encodes the PHB information
                        per DiffServ standards (Refer to DiffServ RFCs 2474).
                        Set the Dscp to PHB (like EF) or PHB-class(like AF1 which
                        includes AF11, AF12,AF13) to mark specific diffserv class traffic.
                        Set the field value to desired integer dscp code for
                        rcPrFilterAceIpDscp field to mark non-standard
                        traffic classes and local use PHBs."
     DEFVAL             { 256 }
     ::= { rcPrFilterAceEntry 31 }

rcPrFilterAceMonitoringIsidOffset OBJECT-TYPE
     SYNTAX          Integer32 (1..1000)
     MAX-ACCESS      read-create
     STATUS          current
     DESCRIPTION     "Used to configure the monitoring ISID offset value.
		      The offset id value is mapped to actual monitor I-SID value
		      in which packets are mirrored to."
     ::= { rcPrFilterAceEntry 32 }

rcPrFilterAceMonitoringIsid OBJECT-TYPE
     SYNTAX          Integer32
     MAX-ACCESS      read-only
     STATUS          current
     DESCRIPTION     "Actual monitor I-SID value in which packets are mirrored to."
     ::= { rcPrFilterAceEntry 33 }

rcPrFilterAceMirroringQos OBJECT-TYPE
     SYNTAX          Integer32 (0..5)
     MAX-ACCESS      read-create
     STATUS          current
     DESCRIPTION     "Used to define the Quality of Service (QoS) profiles for the mirrored
		      packet into monitoring ISID."
     DEFVAL          { 1 }
     ::= { rcPrFilterAceEntry 34 }

rcPrFilterAceRemoveTag OBJECT-TYPE
     SYNTAX          TruthValue
     MAX-ACCESS      read-create
     STATUS          current
     DESCRIPTION     "Used to remove inner vlan tag of the
	 	      mirrored packet into the SPB network.
		      By default, it is set to false and
		      vlan tag will not be removed."
     DEFVAL          { false }
     ::= { rcPrFilterAceEntry 35 }

rcPrFilterAceRedirectNextHopVrfName OBJECT-TYPE
    SYNTAX              DisplayString (SIZE (0..16))
    MAX-ACCESS          read-write
    STATUS              current
    DESCRIPTION         "VRF Name associated with IP/IPv6 redirect next hop."
    ::= { rcPrFilterAceEntry 36 }

-- ACE Ethernet Source MAC Address Table

rcPrFilterAceEthSrcAddrTable OBJECT-TYPE
     SYNTAX             SEQUENCE OF RcPrFilterAceEthSrcAddrEntry
     MAX-ACCESS         not-accessible
     STATUS             current
     DESCRIPTION        "A table of Aces to store Ethernet Source MAC
			Address Header information of each Ace in context
                        of its parent Acl."
     ::= { rcPrFilterAce 2 }

rcPrFilterAceEthSrcAddrEntry OBJECT-TYPE
     SYNTAX             RcPrFilterAceEthSrcAddrEntry
     MAX-ACCESS         not-accessible
     STATUS             current
     DESCRIPTION        "One Ace entry holding Ace Ethernet Source MAC Address
			information. An Ace is a member of one Acl."
     INDEX              { rcPrFilterAceEthSrcAddrAclId,
                          rcPrFilterAceEthSrcAddrAceId }
     ::= { rcPrFilterAceEthSrcAddrTable 1 }

RcPrFilterAceEthSrcAddrEntry ::= SEQUENCE {
        rcPrFilterAceEthSrcAddrAclId	     INTEGER,
        rcPrFilterAceEthSrcAddrAceId	     INTEGER,
        rcPrFilterAceEthSrcAddrList          OCTET STRING,
        rcPrFilterAceEthSrcAddrListCount     INTEGER,
        rcPrFilterAceEthSrcAddrOper          INTEGER,
        rcPrFilterAceEthSrcAddrRowStatus     RowStatus,
        rcPrFilterAceEthSrcAddrOperMask      DisplayString
        }

rcPrFilterAceEthSrcAddrAclId OBJECT-TYPE
     SYNTAX             INTEGER (1..4096)
     MAX-ACCESS         not-accessible
     STATUS             current
     DESCRIPTION        "An index to the AceEthernetEntry, a unique
	                identifier for Acl entry in the range of Table
			Size."
     ::= { rcPrFilterAceEthSrcAddrEntry 1 }

rcPrFilterAceEthSrcAddrAceId OBJECT-TYPE
     SYNTAX             INTEGER (1..2000)
     MAX-ACCESS         not-accessible
     STATUS             current
     DESCRIPTION        "An index to the AceEthernetEntry, a unique
	                identifier for Acl entry in the range of Table
			Size."
     ::= { rcPrFilterAceEthSrcAddrEntry 2 }

rcPrFilterAceEthSrcAddrList OBJECT-TYPE
     SYNTAX             OCTET STRING (SIZE(0..1500))
     MAX-ACCESS         read-create
     STATUS             current
     DESCRIPTION        "The list of ethernet source address to match."
     ::= { rcPrFilterAceEthSrcAddrEntry 3 }

rcPrFilterAceEthSrcAddrListCount OBJECT-TYPE
     SYNTAX             INTEGER(1..100)
     MAX-ACCESS         read-create
     STATUS             current
     DESCRIPTION        "Count to store the number of discrete ranges
                        entered for the ethernet src address."
     ::= { rcPrFilterAceEthSrcAddrEntry 4 }

rcPrFilterAceEthSrcAddrOper OBJECT-TYPE
     SYNTAX             INTEGER {
                            eq(1),    -- exact match
                            ne(2),    -- not equal
                            le(3),    -- less than or equal to
                            ge(4)     -- greater than or equal to
                   }
     MAX-ACCESS         read-create
     STATUS             current
     DESCRIPTION        "Operators for Ace Ethernet Source MAC Address."
     ::= { rcPrFilterAceEthSrcAddrEntry 5 }

rcPrFilterAceEthSrcAddrRowStatus OBJECT-TYPE
     SYNTAX             RowStatus
     MAX-ACCESS         read-create
     STATUS             current
     DESCRIPTION        "Create/delete operations for this entry."
     ::= { rcPrFilterAceEthSrcAddrEntry 6 }

rcPrFilterAceEthSrcAddrOperMask OBJECT-TYPE
     SYNTAX             DisplayString (SIZE(0..14))
     MAX-ACCESS         read-write
     STATUS             current
     DESCRIPTION        "The Mac Address mask value in hex which can
                        be set for the rcPrFilterAceEthSrcAddrOper when
                        the option selected is mask. It will be empty or
                        set to 000000000000 whenrcPrFilterAceEthSrcAddrOper
                        is set to 'eq'. In case of the prefix '0x' is
                        specified, 14 charaters is max length"
     ::= { rcPrFilterAceEthSrcAddrEntry 7 }

-- ACE Ethernet Destination MAC Address Table

rcPrFilterAceEthDstAddrTable OBJECT-TYPE
     SYNTAX             SEQUENCE OF RcPrFilterAceEthDstAddrEntry
     MAX-ACCESS         not-accessible
     STATUS             current
     DESCRIPTION        "A table of Aces to store Ethernet Destination MAC
			Address Header information of each Ace in context
                        of its parent Acl."
     ::= { rcPrFilterAce 3 }

rcPrFilterAceEthDstAddrEntry OBJECT-TYPE
     SYNTAX             RcPrFilterAceEthDstAddrEntry
     MAX-ACCESS         not-accessible
     STATUS             current
     DESCRIPTION        "One Ace entry holding Ace Ethernet Destination
 			MAC Address information. An Ace is a member of one
			Acl."
     INDEX              { rcPrFilterAceEthDstAddrAclId,
                          rcPrFilterAceEthDstAddrAceId }
     ::= { rcPrFilterAceEthDstAddrTable 1 }

RcPrFilterAceEthDstAddrEntry ::= SEQUENCE {
        rcPrFilterAceEthDstAddrAclId	       INTEGER,
        rcPrFilterAceEthDstAddrAceId	       INTEGER,
        rcPrFilterAceEthDstAddrList	       OCTET STRING,
        rcPrFilterAceEthDstAddrListCount       INTEGER,
        rcPrFilterAceEthDstAddrOper            INTEGER,
        rcPrFilterAceEthDstAddrRowStatus       RowStatus,
        rcPrFilterAceEthDstAddrOperMask        DisplayString
        }

rcPrFilterAceEthDstAddrAclId OBJECT-TYPE
     SYNTAX             INTEGER (1..4096)
     MAX-ACCESS         not-accessible
     STATUS             current
     DESCRIPTION        "An index to the AceEthDstAddrEntry, a unique
	                identifier for Acl entry in the range of Table
			Size."
     ::= { rcPrFilterAceEthDstAddrEntry 1 }

rcPrFilterAceEthDstAddrAceId OBJECT-TYPE
     SYNTAX             INTEGER (1..2000)
     MAX-ACCESS         not-accessible
     STATUS             current
     DESCRIPTION        "An index to the AceEthDstAddrEntry, a unique
	                identifier for Acl entry in the range of Table
			Size."
     ::= { rcPrFilterAceEthDstAddrEntry 2 }

rcPrFilterAceEthDstAddrList OBJECT-TYPE
     SYNTAX             OCTET STRING (SIZE(0..1500))
     MAX-ACCESS         read-create
     STATUS             current
     DESCRIPTION        "List of ethernet destination address to
			match."
     ::= { rcPrFilterAceEthDstAddrEntry 3 }

rcPrFilterAceEthDstAddrListCount OBJECT-TYPE
     SYNTAX             INTEGER(1..100)
     MAX-ACCESS         read-create
     STATUS             current
     DESCRIPTION        "Count to store the number of discrete ranges
                        entered for the ethernet dst address."
     ::= { rcPrFilterAceEthDstAddrEntry 4 }

rcPrFilterAceEthDstAddrOper OBJECT-TYPE
     SYNTAX             INTEGER {
                            eq(1),    -- exact match
                            ne(2),    -- not equal
                            le(3),    -- less than or equal to
                            ge(4),    -- greater than or equal to
                            mask(8)   -- mask
                        }
     MAX-ACCESS         read-create
     STATUS             current
     DESCRIPTION        "Operators for Ace Ethernet Destination MAC Address."
     ::= { rcPrFilterAceEthDstAddrEntry 5 }

rcPrFilterAceEthDstAddrRowStatus OBJECT-TYPE
     SYNTAX             RowStatus
     MAX-ACCESS         read-create
     STATUS             current
     DESCRIPTION        "Create/delete operations for this entry."
     ::= { rcPrFilterAceEthDstAddrEntry 6 }

rcPrFilterAceEthDstAddrOperMask OBJECT-TYPE
     SYNTAX             DisplayString (SIZE(0..14))
     MAX-ACCESS         read-write
     STATUS             current
     DESCRIPTION        "The Mac Address mask value in hex which can
                        be set for the rcPrFilterAceEthDstAddrOper when
                        the option selected is mask. It will be empty or
                        set to 000000000000 whenrcPrFilterAceEthDstAddrOper
                        is set to 'eq'. In case of the prefix '0x' is
                        specified, 14 charaters is max length"
     ::= { rcPrFilterAceEthDstAddrEntry 7 }

-- ACE Ethernet Ether Table

rcPrFilterAceEthEtherTable OBJECT-TYPE
     SYNTAX             SEQUENCE OF RcPrFilterAceEthEtherEntry
     MAX-ACCESS         not-accessible
     STATUS             current
     DESCRIPTION        "A table of Aces to store Ethernet Ether Header
			information of each Ace in context of its parent
			Acl."
     ::= { rcPrFilterAce 4 }

rcPrFilterAceEthEtherEntry OBJECT-TYPE
     SYNTAX             RcPrFilterAceEthEtherEntry
     MAX-ACCESS         not-accessible
     STATUS             current
     DESCRIPTION        "One Ace entry holding Ace Ethernet Ether
 			information. An Ace is a member of one Acl."
     INDEX              { rcPrFilterAceEthEtherAclId,
                          rcPrFilterAceEthEtherAceId }
     ::= { rcPrFilterAceEthEtherTable 1 }

RcPrFilterAceEthEtherEntry ::= SEQUENCE {
        rcPrFilterAceEthEtherAclId	     INTEGER,
        rcPrFilterAceEthEtherAceId	     INTEGER,
	rcPrFilterAceEthEtherTypeList        OCTET STRING,
	rcPrFilterAceEthEtherTypeListCount   INTEGER,
        rcPrFilterAceEthEtherTypeOper        INTEGER,
        rcPrFilterAceEthEtherRowStatus       RowStatus
        }

rcPrFilterAceEthEtherAclId OBJECT-TYPE
     SYNTAX             INTEGER (1..4096)
     MAX-ACCESS         not-accessible
     STATUS             current
     DESCRIPTION        "An index to the AceEthEtherEntry, a unique
	                identifier for Acl entry in the range of Table
			Size."
     ::= { rcPrFilterAceEthEtherEntry 1 }

rcPrFilterAceEthEtherAceId OBJECT-TYPE
     SYNTAX             INTEGER (1..2000)
     MAX-ACCESS         not-accessible
     STATUS             current
     DESCRIPTION        "An index to the AceEthEtherEntry, a unique
	                identifier for Acl entry in the range of Table
			Size."
     ::= { rcPrFilterAceEthEtherEntry 2 }

rcPrFilterAceEthEtherTypeList OBJECT-TYPE
     SYNTAX             OCTET STRING (SIZE(0..1500))
     MAX-ACCESS         read-create
     STATUS             current
     DESCRIPTION        "EtherType value from ethernet header.  For example ARP
                         uses  0x0806, IP uses 0x0800. The platform support
                         determines the behavior for 802.1Q/p tagged packets.
                         The EtherType for 802.1Q tagged frames is 0x8100.

                         Valid range for the 16-bit Ether-type is 0..65535
			 and the attribute supports lists/ranges of values.
                         Invalid ether-type value 65536 is interpreted as
                         field is not desired in match criteria."
 	::= { rcPrFilterAceEthEtherEntry 3 }

rcPrFilterAceEthEtherTypeListCount OBJECT-TYPE
     SYNTAX             INTEGER (1..100)
     MAX-ACCESS         read-create
     STATUS             current
     DESCRIPTION        "Count to store the number of discrete ranges
                        entered for the ethernet types."
     ::= { rcPrFilterAceEthEtherEntry 4 }

rcPrFilterAceEthEtherTypeOper OBJECT-TYPE
     SYNTAX             INTEGER {
                            eq(1),    -- exact match
                            ne(2)     -- not equal
                        }
     MAX-ACCESS         read-create
     STATUS             current
     DESCRIPTION        "Ethernet Type Operators."
     ::= { rcPrFilterAceEthEtherEntry 5 }

rcPrFilterAceEthEtherRowStatus OBJECT-TYPE
     SYNTAX             RowStatus
     MAX-ACCESS         read-create
     STATUS             current
     DESCRIPTION        "Create/delete operations for this entry."
     ::= { rcPrFilterAceEthEtherEntry 6 }

-- ACE Ethernet Vlan Tag Priority Table

rcPrFilterAceEthVlanTagPrioTable OBJECT-TYPE
     SYNTAX             SEQUENCE OF RcPrFilterAceEthVlanTagPrioEntry
     MAX-ACCESS         not-accessible
     STATUS             current
     DESCRIPTION        "A table of Aces to store Ethernet Vlan Tag
			Priority Header information of each Ace in context
			of its parent Acl."
     ::= { rcPrFilterAce 5 }

rcPrFilterAceEthVlanTagPrioEntry OBJECT-TYPE
     SYNTAX             RcPrFilterAceEthVlanTagPrioEntry
     MAX-ACCESS         not-accessible
     STATUS             current
     DESCRIPTION        "One Ace entry holding Ace Ethernet Vlan Tag Priority
 			information. An Ace is a member of one Acl."
     INDEX              { rcPrFilterAceEthVlanTagPrioAclId,
                          rcPrFilterAceEthVlanTagPrioAceId }
     ::= { rcPrFilterAceEthVlanTagPrioTable 1 }

RcPrFilterAceEthVlanTagPrioEntry ::= SEQUENCE {
        rcPrFilterAceEthVlanTagPrioAclId	     INTEGER,
        rcPrFilterAceEthVlanTagPrioAceId	     INTEGER,
	rcPrFilterAceEthVlanTagPrioVlanTagPrio 	     INTEGER,
        rcPrFilterAceEthVlanTagPrioOper              INTEGER,
        rcPrFilterAceEthVlanTagPrioRowStatus         RowStatus,
        rcPrFilterAceEthVlanTagPrioOperMask          Integer32
        }

rcPrFilterAceEthVlanTagPrioAclId OBJECT-TYPE
     SYNTAX             INTEGER (1..4096)
     MAX-ACCESS         not-accessible
     STATUS             current
     DESCRIPTION        "An index to the AceEthVlanTagPrioEntry, a unique
	                identifier for Acl entry in the range of Table
			Size."
     ::= { rcPrFilterAceEthVlanTagPrioEntry 1 }

rcPrFilterAceEthVlanTagPrioAceId OBJECT-TYPE
     SYNTAX             INTEGER (1..2000)
     MAX-ACCESS         not-accessible
     STATUS             current
     DESCRIPTION        "An index to the AceEthVlanTagPrioEntry, a unique
	                identifier for Acl entry in the range of Table
			Size."
     ::= { rcPrFilterAceEthVlanTagPrioEntry 2 }

rcPrFilterAceEthVlanTagPrioVlanTagPrio  OBJECT-TYPE
     SYNTAX             INTEGER {
                            zero(0),
                            one(1),
                            two(2),
                            three(3),
                            four(4),
                            five(5),
                            six(6),
                            seven(7)
                        }
     MAX-ACCESS         read-create
     STATUS             current
     DESCRIPTION        "Priority bits (3-bit field) from the 802.1Q/p tag."
     ::= { rcPrFilterAceEthVlanTagPrioEntry 3 }

rcPrFilterAceEthVlanTagPrioOper OBJECT-TYPE
     SYNTAX             INTEGER {
                            eq(1),    -- exact match
                            ne(2),    -- not equal
                            mask(8)   -- mask
                        }
     MAX-ACCESS         read-create
     STATUS             current
     DESCRIPTION        "Operators for Ace Ethernet Vlan Tag Priority."
     ::= { rcPrFilterAceEthVlanTagPrioEntry 4 }

rcPrFilterAceEthVlanTagPrioRowStatus OBJECT-TYPE
     SYNTAX             RowStatus
     MAX-ACCESS         read-create
     STATUS             current
     DESCRIPTION        "Create/delete operations for this entry."
     ::= { rcPrFilterAceEthVlanTagPrioEntry 5 }

rcPrFilterAceEthVlanTagPrioOperMask OBJECT-TYPE
     SYNTAX             Integer32 (0..'7'h)
     MAX-ACCESS         read-write
     STATUS             current
     DESCRIPTION        "The mask value in hex which can be set for the
                        rcPrFilterAceEthVlanTagPrioOper when the option
                        selected is masked. This object is applicable for
                        VSP9000. Not for ERS8600"
     ::= { rcPrFilterAceEthVlanTagPrioEntry 6 }

-- ACE Ethernet Port Table

rcPrFilterAceEthPortTable OBJECT-TYPE
     SYNTAX             SEQUENCE OF RcPrFilterAceEthPortEntry
     MAX-ACCESS         not-accessible
     STATUS             current
     DESCRIPTION        "A table of Aces to store Ethernet  Port
			Header information of each Ace in context
			of its parent Acl."
     ::= { rcPrFilterAce 6 }

rcPrFilterAceEthPortEntry OBJECT-TYPE
     SYNTAX             RcPrFilterAceEthPortEntry
     MAX-ACCESS         not-accessible
     STATUS             current
     DESCRIPTION        "One Ace entry holding Ace Ethernet Port
 			information. An Ace is a member of one Acl."
     INDEX              { rcPrFilterAceEthPortAclId,
                          rcPrFilterAceEthPortAceId }
     ::= { rcPrFilterAceEthPortTable 1 }

RcPrFilterAceEthPortEntry ::= SEQUENCE {
        rcPrFilterAceEthPortAclId	 INTEGER,
        rcPrFilterAceEthPortAceId	 INTEGER,
        rcPrFilterAceEthPortPort         PortSet,
        rcPrFilterAceEthPortOper         INTEGER,
        rcPrFilterAceEthPortRowStatus    RowStatus
        }

rcPrFilterAceEthPortAclId OBJECT-TYPE
     SYNTAX             INTEGER (1..4096)
     MAX-ACCESS         not-accessible
     STATUS             current
     DESCRIPTION        "An index to the AceEthPortEntry, a unique
	                identifier for Acl entry in the range of Table
			Size."
     ::= { rcPrFilterAceEthPortEntry 1 }

rcPrFilterAceEthPortAceId OBJECT-TYPE
     SYNTAX             INTEGER (1..2000)
     MAX-ACCESS         not-accessible
     STATUS             current
     DESCRIPTION        "An index to the AceEthPortEntry, a unique
	                identifier for Acl entry in the range of Table
			Size."
     ::= { rcPrFilterAceEthPortEntry 2 }

rcPrFilterAceEthPortPort OBJECT-TYPE
     SYNTAX             PortSet
     MAX-ACCESS         read-create
     STATUS             current
     DESCRIPTION        "Port Number or Port List to match on."
     ::= { rcPrFilterAceEthPortEntry 3 }

rcPrFilterAceEthPortOper OBJECT-TYPE
     SYNTAX             INTEGER {
                            eq(1),   -- exact match
			    ne(2)    -- not equal
                        }
     MAX-ACCESS         read-create
     STATUS             current
     DESCRIPTION        "Operator for Ace Ethernet Port."
     ::= { rcPrFilterAceEthPortEntry 4 }

rcPrFilterAceEthPortRowStatus OBJECT-TYPE
     SYNTAX             RowStatus
     MAX-ACCESS         read-create
     STATUS             current
     DESCRIPTION        "Create/delete operations for this entry."
     ::= { rcPrFilterAceEthPortEntry 5 }

-- ACE Ethernet Vlan Id Table

rcPrFilterAceEthVlanIdTable OBJECT-TYPE
     SYNTAX             SEQUENCE OF RcPrFilterAceEthVlanIdEntry
     MAX-ACCESS         not-accessible
     STATUS             current
     DESCRIPTION        "A table of Aces to store Ethernet Vlan Id
			Header information of each Ace in context
			of its parent Acl."
     ::= { rcPrFilterAce 7 }

rcPrFilterAceEthVlanIdEntry OBJECT-TYPE
     SYNTAX             RcPrFilterAceEthVlanIdEntry
     MAX-ACCESS         not-accessible
     STATUS             current
     DESCRIPTION        "One Ace entry holding Ace Ethernet Vlan Id
 			information. An Ace is a member of one Acl."
     INDEX              { rcPrFilterAceEthVlanIdAclId,
                          rcPrFilterAceEthVlanIdAceId }
     ::= { rcPrFilterAceEthVlanIdTable 1 }

RcPrFilterAceEthVlanIdEntry ::= SEQUENCE {
        rcPrFilterAceEthVlanIdAclId	     INTEGER,
        rcPrFilterAceEthVlanIdAceId	     INTEGER,
        rcPrFilterAceEthVlanIdVlanIdList     IdList,
        rcPrFilterAceEthVlanIdOper           INTEGER,
        rcPrFilterAceEthVlanIdRowStatus      RowStatus,
        rcPrFilterAceEthVlanIdOperMask       Integer32,
        rcPrFilterAceEthVlanIdVlanId         INTEGER
        }

rcPrFilterAceEthVlanIdAclId OBJECT-TYPE
     SYNTAX             INTEGER (1..4096)
     MAX-ACCESS         not-accessible
     STATUS             current
     DESCRIPTION        "An index to the AceEthVlanIdEntry, a unique
	                identifier for Acl entry in the range of Table
			Size."
     ::= { rcPrFilterAceEthVlanIdEntry 1 }

rcPrFilterAceEthVlanIdAceId OBJECT-TYPE
     SYNTAX             INTEGER (1..2000)
     MAX-ACCESS         not-accessible
     STATUS             current
     DESCRIPTION        "An index to the AceEthVlanIdEntry, a unique
	                identifier for Acl entry in the range of Table
			Size."
     ::= { rcPrFilterAceEthVlanIdEntry 2 }

rcPrFilterAceEthVlanIdVlanIdList OBJECT-TYPE
     SYNTAX             IdList(SIZE(4096))
     MAX-ACCESS         read-create
     STATUS             current
     DESCRIPTION        "Vlan Id to match on."
     ::= { rcPrFilterAceEthVlanIdEntry 3 }

rcPrFilterAceEthVlanIdOper OBJECT-TYPE
     SYNTAX             INTEGER {
                            eq(1),  -- exact match
                            ne(2),  -- not equal
                            mask(8) -- mask
                        }
     MAX-ACCESS         read-create
     STATUS             current
     DESCRIPTION        "Operator for Ace Ethernet VlanId."
     ::= { rcPrFilterAceEthVlanIdEntry 4 }

rcPrFilterAceEthVlanIdRowStatus OBJECT-TYPE
     SYNTAX             RowStatus
     MAX-ACCESS         read-create
     STATUS             current
     DESCRIPTION        "Create/delete operations for this entry."
     ::= { rcPrFilterAceEthVlanIdEntry 5 }

rcPrFilterAceEthVlanIdOperMask OBJECT-TYPE
     SYNTAX             Integer32(0..'FFF'h)
     MAX-ACCESS         read-write
     STATUS             current
     DESCRIPTION        "The mask value in hex which can be set for the
                        rcPrFilterAceEthVlanIdOper when the option
                        selected is mask. This object is used with
                        rcPrFilterAceEthVlanIdVlanId in VSP 9000 to
                        replace rcPrFilterAceEthVlanIdVlanIdList "
     ::= { rcPrFilterAceEthVlanIdEntry 6 }

rcPrFilterAceEthVlanIdVlanId OBJECT-TYPE
     SYNTAX             INTEGER (1..4084)
     MAX-ACCESS         read-write
     STATUS             current
     DESCRIPTION        "Vlan Id to match on. VSP9000  use this object with
                        object rcPrFilterAceEthVlanIdOperMask to replace the
                        rcPrFilterAceEthVlanIdVlanIdList"
     ::= { rcPrFilterAceEthVlanIdEntry 7 }

-- ACE Arp Table

rcPrFilterAceArpTable OBJECT-TYPE
     SYNTAX             SEQUENCE OF RcPrFilterAceArpEntry
     MAX-ACCESS         not-accessible
     STATUS             current
     DESCRIPTION        "A table of Aces to store Arp Header information
                         of each Ace in context of its parent Acl. "
     ::= { rcPrFilterAce 8 }

rcPrFilterAceArpEntry OBJECT-TYPE
     SYNTAX             RcPrFilterAceArpEntry
     MAX-ACCESS         not-accessible
     STATUS             current
     DESCRIPTION        "One Ace entry holding Ace Arp Header information.
                        Ace is a member of one Acl."
     INDEX              { rcPrFilterAceArpAclId,
                          rcPrFilterAceArpAceId }
     ::= { rcPrFilterAceArpTable 1 }

RcPrFilterAceArpEntry ::= SEQUENCE {
        rcPrFilterAceArpAclId	      INTEGER,
        rcPrFilterAceArpAceId	      INTEGER,
	rcPrFilterAceArpType          INTEGER,
	rcPrFilterAceArpOper          INTEGER,
	rcPrFilterAceArpValue	      INTEGER,
        rcPrFilterAceArpRowStatus     RowStatus
	}

rcPrFilterAceArpAclId OBJECT-TYPE
     SYNTAX             INTEGER (1..4096)
     MAX-ACCESS         not-accessible
     STATUS             current
     DESCRIPTION        "An index to the AceArpEntry, a unique
	                identifier for Acl entry in the range of Table
			Size."
     ::= { rcPrFilterAceArpEntry 1 }

rcPrFilterAceArpAceId OBJECT-TYPE
     SYNTAX             INTEGER (1..2000)
     MAX-ACCESS         not-accessible
     STATUS             current
     DESCRIPTION        "An index to the AceArpEntry, a unique
	                identifier for Acl entry in the range of Table
			Size."
     ::= { rcPrFilterAceArpEntry 2 }

rcPrFilterAceArpType      OBJECT-TYPE
     SYNTAX             INTEGER {
                            operation(1)
			}
     MAX-ACCESS         read-create
     STATUS             current
     DESCRIPTION        "Ace Arp Operation."
     DEFVAL	        { operation }
     ::= { rcPrFilterAceArpEntry 3 }

rcPrFilterAceArpOper          OBJECT-TYPE
     SYNTAX             INTEGER {
                            eq(1)    -- exact match
                        }
     MAX-ACCESS         read-create
     STATUS             current
     DESCRIPTION        "Operator for Ace Arp Operation."
     ::= { rcPrFilterAceArpEntry 4 }

rcPrFilterAceArpValue	OBJECT-TYPE
     SYNTAX             INTEGER {
                            arpRequest(1),
                            arpResponse(2)
			}
     MAX-ACCESS         read-create
     STATUS             current
     DESCRIPTION        "Ace Arp can be a request or a response."
     ::= { rcPrFilterAceArpEntry 5 }

rcPrFilterAceArpRowStatus OBJECT-TYPE
     SYNTAX             RowStatus
     MAX-ACCESS         read-create
     STATUS             current
     DESCRIPTION        "Create/delete operations for this entry."
     ::= { rcPrFilterAceArpEntry 6 }

-- ACE Ip Source Address Table

rcPrFilterAceIpSrcAddrTable OBJECT-TYPE
     SYNTAX             SEQUENCE OF RcPrFilterAceIpSrcAddrEntry
     MAX-ACCESS         not-accessible
     STATUS             current
     DESCRIPTION        "A table of Aces to store IP Source Address Header
			information of each Ace in context of its parent Acl."
     ::= { rcPrFilterAce 9 }

rcPrFilterAceIpSrcAddrEntry OBJECT-TYPE
     SYNTAX             RcPrFilterAceIpSrcAddrEntry
     MAX-ACCESS         not-accessible
     STATUS             current
     DESCRIPTION        "One Ace entry holding Ace IP Source Address Header
			information. An Ace is a member of one Acl."
     INDEX              { rcPrFilterAceIpSrcAddrAclId,
                          rcPrFilterAceIpSrcAddrAceId }
     ::= { rcPrFilterAceIpSrcAddrTable 1 }

RcPrFilterAceIpSrcAddrEntry ::= SEQUENCE {
        rcPrFilterAceIpSrcAddrAclId	     INTEGER,
        rcPrFilterAceIpSrcAddrAceId	     INTEGER,
        rcPrFilterAceIpSrcAddrList           OCTET STRING,
        rcPrFilterAceIpSrcAddrListCount      INTEGER,
        rcPrFilterAceIpSrcAddrOper           INTEGER,
        rcPrFilterAceIpSrcAddrRowStatus      RowStatus,
        rcPrFilterAceIpSrcAddrIpAddr         IpAddress,
        rcPrFilterAceIpSrcAddrOperMaskRange  IpAddress
        }

rcPrFilterAceIpSrcAddrAclId OBJECT-TYPE
     SYNTAX             INTEGER (1..4096)
     MAX-ACCESS         not-accessible
     STATUS             current
     DESCRIPTION        "An index to the AceIpSrcAddrEntry, a unique
	                identifier for Acl entry in the range of Table
			Size."
     ::= { rcPrFilterAceIpSrcAddrEntry 1 }

rcPrFilterAceIpSrcAddrAceId OBJECT-TYPE
     SYNTAX             INTEGER (1..2000)
     MAX-ACCESS         not-accessible
     STATUS             current
     DESCRIPTION        "An index to the AceIpSrcAddrEntry, a unique
	                identifier for Acl entry in the range of Table
			Size."
     ::= { rcPrFilterAceIpSrcAddrEntry 2 }

rcPrFilterAceIpSrcAddrList OBJECT-TYPE
     SYNTAX             OCTET STRING (SIZE(0..1500))
     MAX-ACCESS         read-create
     STATUS             current
     DESCRIPTION        "The list of ip source address to match from IP
			header."
     ::= { rcPrFilterAceIpSrcAddrEntry 3 }

rcPrFilterAceIpSrcAddrListCount OBJECT-TYPE
     SYNTAX             INTEGER (1..100)
     MAX-ACCESS         read-create
     STATUS             current
     DESCRIPTION        "Count to store the number of discrete ranges
                        entered for the ip src address."
     ::= { rcPrFilterAceIpSrcAddrEntry 4 }

rcPrFilterAceIpSrcAddrOper OBJECT-TYPE
     SYNTAX             INTEGER {
                            eq(1),    -- exact match
                            ne(2),    -- not equal
                            le(3),    -- less than or equal to
                            ge(4),     -- greater than or equal to
                            prefix(8), -- prefix list
                            mask(9),   -- mask
                            range(10)  -- range
                        }
     MAX-ACCESS         read-create
     STATUS             current
     DESCRIPTION        "Operators for Ace Ip Source Address."
     ::= { rcPrFilterAceIpSrcAddrEntry 5 }

rcPrFilterAceIpSrcAddrRowStatus OBJECT-TYPE
     SYNTAX             RowStatus
     MAX-ACCESS         read-create
     STATUS             current
     DESCRIPTION        "Create/delete operations for this entry."
     ::= { rcPrFilterAceIpSrcAddrEntry 6 }

rcPrFilterAceIpSrcAddrIpAddr OBJECT-TYPE
     SYNTAX        IpAddress
     MAX-ACCESS    read-write
     STATUS        current
     DESCRIPTION   "IP Source Address to match from IP header.
                       This object is defined and used  to replace
                       the rcPrFilterAceIpSrcAddrList by VSP 9000"
     ::= { rcPrFilterAceIpSrcAddrEntry 7 }

rcPrFilterAceIpSrcAddrOperMaskRange OBJECT-TYPE
     SYNTAX             IpAddress
     MAX-ACCESS         read-write
     STATUS             current
     DESCRIPTION        "The IP Mask value or High IP address based on
                        object rcPrFilterAceIpSrcAddrOper mask/range
                        option is selected."
     ::= { rcPrFilterAceIpSrcAddrEntry 8 }

-- ACE Ip Destination Address Table

rcPrFilterAceIpDstAddrTable OBJECT-TYPE
     SYNTAX             SEQUENCE OF RcPrFilterAceIpDstAddrEntry
     MAX-ACCESS         not-accessible
     STATUS             current
     DESCRIPTION        "A table of Aces to store IP Destination Address
			Header information of each Ace in context of its
			parent Acl."
     ::= { rcPrFilterAce 10 }

rcPrFilterAceIpDstAddrEntry OBJECT-TYPE
     SYNTAX             RcPrFilterAceIpDstAddrEntry
     MAX-ACCESS         not-accessible
     STATUS             current
     DESCRIPTION        "One Ace entry holding Ace IP Destination Address
			Header information. An Ace is a member of one Acl."
     INDEX              { rcPrFilterAceIpDstAddrAclId,
                          rcPrFilterAceIpDstAddrAceId }
     ::= { rcPrFilterAceIpDstAddrTable 1 }

RcPrFilterAceIpDstAddrEntry ::= SEQUENCE {
        rcPrFilterAceIpDstAddrAclId	     INTEGER,
        rcPrFilterAceIpDstAddrAceId	     INTEGER,
        rcPrFilterAceIpDstAddrList           OCTET STRING,
        rcPrFilterAceIpDstAddrListCount      INTEGER,
        rcPrFilterAceIpDstAddrOper           INTEGER,
        rcPrFilterAceIpDstAddrRowStatus      RowStatus,
        rcPrFilterAceIpDstAddrIpAddr         IpAddress,
        rcPrFilterAceIpDstAddrOperMaskRange  IpAddress
        }

rcPrFilterAceIpDstAddrAclId OBJECT-TYPE
     SYNTAX             INTEGER (1..4096)
     MAX-ACCESS         not-accessible
     STATUS             current
     DESCRIPTION        "An index to the AceIpDstAddrEntry, a unique
	                identifier for Acl entry in the range of Table
			Size."
     ::= { rcPrFilterAceIpDstAddrEntry 1 }

rcPrFilterAceIpDstAddrAceId OBJECT-TYPE
     SYNTAX             INTEGER (1..2000)
     MAX-ACCESS         not-accessible
     STATUS             current
     DESCRIPTION        "An index to the AceIpDstAddrEntry, a unique
	                identifier for Acl entry in the range of Table
			Size."
     ::= { rcPrFilterAceIpDstAddrEntry 2 }

rcPrFilterAceIpDstAddrList OBJECT-TYPE
     SYNTAX             OCTET STRING (SIZE(0..1500))
     MAX-ACCESS         read-create
     STATUS             current
     DESCRIPTION        "The list of ip dst address to match from IP header."
     ::= { rcPrFilterAceIpDstAddrEntry 3 }

rcPrFilterAceIpDstAddrListCount OBJECT-TYPE
     SYNTAX             INTEGER (1..100)
     MAX-ACCESS         read-create
     STATUS             current
     DESCRIPTION        "Count to store the number of discrete ranges
                        entered for the IP Destination Address."
     ::= { rcPrFilterAceIpDstAddrEntry 4 }

rcPrFilterAceIpDstAddrOper OBJECT-TYPE
     SYNTAX             INTEGER {
                            eq(1),    -- exact match
                            ne(2),    -- not equal
                            le(3),    -- less than or equal to
                            ge(4),    -- greater than or equal to
                            prefix(8), -- prefix list
                            mask(9),   -- mask
                            range(10)  -- range
                        }
     MAX-ACCESS         read-create
     STATUS             current
     DESCRIPTION        "Operators for Ace IP Destination Address."
     ::= { rcPrFilterAceIpDstAddrEntry 5 }

rcPrFilterAceIpDstAddrRowStatus OBJECT-TYPE
     SYNTAX             RowStatus
     MAX-ACCESS         read-create
     STATUS             current
     DESCRIPTION        "Create/delete operations for this entry."
     ::= { rcPrFilterAceIpDstAddrEntry 6 }

rcPrFilterAceIpDstAddrIpAddr OBJECT-TYPE
     SYNTAX             IpAddress
     MAX-ACCESS         read-write
     STATUS             current
     DESCRIPTION        "IP Source Address to match from IP header.
                         This object is defined and used  to replace
                         the rcPrFilterAceIpSrcAddrList by VSP 9000"
     ::= { rcPrFilterAceIpDstAddrEntry 7 }

rcPrFilterAceIpDstAddrOperMaskRange OBJECT-TYPE
     SYNTAX             IpAddress
     MAX-ACCESS         read-write
     STATUS             current
     DESCRIPTION        "The IP mask value or Hi Ip address based on
                        object rcPrFilterAceIpDstAddrOper mask/range
                        option is selected."
     ::= { rcPrFilterAceIpDstAddrEntry 8 }

-- ACE Ip Dscp Table

rcPrFilterAceIpDscpTable OBJECT-TYPE
     SYNTAX             SEQUENCE OF RcPrFilterAceIpDscpEntry
     MAX-ACCESS         not-accessible
     STATUS             current
     DESCRIPTION        "A table of Aces to store IP Dscp Header information
			of each Ace in context of its parent Acl."
     ::= { rcPrFilterAce 11 }

rcPrFilterAceIpDscpEntry OBJECT-TYPE
     SYNTAX             RcPrFilterAceIpDscpEntry
     MAX-ACCESS         not-accessible
     STATUS             current
     DESCRIPTION        "One Ace entry holding Ace IP Dscp Header information.
			An Ace is a member of one Acl."
     INDEX              { rcPrFilterAceIpDscpAclId,
                          rcPrFilterAceIpDscpAceId }
     ::= { rcPrFilterAceIpDscpTable 1 }

RcPrFilterAceIpDscpEntry ::= SEQUENCE {
        rcPrFilterAceIpDscpAclId	     INTEGER,
        rcPrFilterAceIpDscpAceId	     INTEGER,
        rcPrFilterAceIpDscpList              OCTET STRING,
        rcPrFilterAceIpDscpListCount         INTEGER,
        rcPrFilterAceIpDscpOper              INTEGER,
        rcPrFilterAceIpDscpRowStatus         RowStatus,
        rcPrFilterAceIpDscpOperMask          Integer32
        }

rcPrFilterAceIpDscpAclId OBJECT-TYPE
     SYNTAX             INTEGER (1..4096)
     MAX-ACCESS         not-accessible
     STATUS             current
     DESCRIPTION        "An index to the AceIpDscpEntry, a unique
	                identifier for Acl entry in the range of Table
			Size."
     ::= { rcPrFilterAceIpDscpEntry 1 }

rcPrFilterAceIpDscpAceId OBJECT-TYPE
     SYNTAX             INTEGER (1..2000)
     MAX-ACCESS         not-accessible
     STATUS             current
     DESCRIPTION        "An index to the AceIpDscpEntry, a unique
	                identifier for Acl entry in the range of Table
			Size."
     ::= { rcPrFilterAceIpDscpEntry 2 }

rcPrFilterAceIpDscpList  OBJECT-TYPE
     SYNTAX             OCTET STRING (SIZE(0..1500))
     MAX-ACCESS         read-create
     STATUS             current
     DESCRIPTION        "The 6-bit DSCP field from the ToS byte in Ipv4 header
                        encodes the PHB information per DiffServ standards
                        (Refer to DiffServ RFCs 2474). Set the Dscp to PHB
                        (like EF) or PHB-class(like AF1 which includes AF11,
                        AF12,AF13) to match specific diffserv class traffic.
                        Set the field value to desired dscp code for
                        'rcPrFilterAceIpDscp' field to match non-standard
                        traffic classes and local use PHBs."
     DEFVAL             { "disable" }
     ::= { rcPrFilterAceIpDscpEntry 3 }

rcPrFilterAceIpDscpListCount OBJECT-TYPE
     SYNTAX             INTEGER (1..100)
     MAX-ACCESS         read-create
     STATUS             current
     DESCRIPTION        "Count to store the number of discrete ranges
                        entered for the dscp values."
     ::= { rcPrFilterAceIpDscpEntry 4 }

rcPrFilterAceIpDscpOper OBJECT-TYPE
     SYNTAX             INTEGER {
                            eq(1),    -- exact match
                            ne(2),    -- not equal
                            mask(8)   -- mask
                        }
     MAX-ACCESS         read-create
     STATUS             current
     DESCRIPTION        "Operators for Ace Ip Dscp."
     ::= { rcPrFilterAceIpDscpEntry 5 }

rcPrFilterAceIpDscpRowStatus OBJECT-TYPE
     SYNTAX             RowStatus
     MAX-ACCESS         read-create
     STATUS             current
     DESCRIPTION        "Create/delete operations for this entry."
     ::= { rcPrFilterAceIpDscpEntry 6 }

rcPrFilterAceIpDscpOperMask OBJECT-TYPE
     SYNTAX             Integer32(0..'40'h)
     MAX-ACCESS         read-write
     STATUS             current
     DESCRIPTION        "The mask value in hex which can be set for the
                        rcPrFilterAceIpDscpOper when the option
                        selected is mask. It will be set to 0 or be used
                        when rcPrFilterAceIpDscpOper is set ro eq"
     ::= { rcPrFilterAceIpDscpEntry 7 }


-- ACE Ip Proto Table

rcPrFilterAceIpProtoTable OBJECT-TYPE
     SYNTAX             SEQUENCE OF RcPrFilterAceIpProtoEntry
     MAX-ACCESS         not-accessible
     STATUS             current
     DESCRIPTION        "A table of Aces to store IP Proto Header information
			of each Ace in context of its parent Acl."
     ::= { rcPrFilterAce 12 }

rcPrFilterAceIpProtoEntry OBJECT-TYPE
     SYNTAX             RcPrFilterAceIpProtoEntry
     MAX-ACCESS         not-accessible
     STATUS             current
     DESCRIPTION        "One Ace entry holding Ace IP Proto Header information.
			An Ace is a member of one Acl."
     INDEX              { rcPrFilterAceIpProtoAclId,
                          rcPrFilterAceIpProtoAceId }
     ::= { rcPrFilterAceIpProtoTable 1 }

RcPrFilterAceIpProtoEntry ::= SEQUENCE {
        rcPrFilterAceIpProtoAclId	     INTEGER,
        rcPrFilterAceIpProtoAceId	     INTEGER,
        rcPrFilterAceIpProtoList             OCTET STRING,
        rcPrFilterAceIpProtoListCount        INTEGER,
        rcPrFilterAceIpProtoOper             INTEGER,
        rcPrFilterAceIpProtoRowStatus        RowStatus
        }

rcPrFilterAceIpProtoAclId OBJECT-TYPE
     SYNTAX             INTEGER (1..4096)
     MAX-ACCESS         not-accessible
     STATUS             current
     DESCRIPTION        "An index to the AceIpProtoEntry, a unique
	                identifier for Acl entry in the range of Table
			Size."
     ::= { rcPrFilterAceIpProtoEntry 1 }

rcPrFilterAceIpProtoAceId OBJECT-TYPE
     SYNTAX             INTEGER (1..2000)
     MAX-ACCESS         not-accessible
     STATUS             current
     DESCRIPTION        "An index to the AceIpProtoEntry, a unique
	                identifier for Acl entry in the range of Table
			Size."
     ::= { rcPrFilterAceIpProtoEntry 2 }

rcPrFilterAceIpProtoList OBJECT-TYPE
     SYNTAX             OCTET STRING (SIZE(0..1500))
     MAX-ACCESS         read-create
     STATUS             current
     DESCRIPTION        "Ip protocol Type from the ip header to be matched.
                        Valid Ip protocol range is 0..255. Few of the Protocol
                        Types are enumerated above. In case the desired
                        protocol number is not available in the enumerated
                        list set protocol to desired integer value"
     ::= { rcPrFilterAceIpProtoEntry 3 }

rcPrFilterAceIpProtoListCount OBJECT-TYPE
     SYNTAX             INTEGER (1..100)
     MAX-ACCESS         read-create
     STATUS             current
     DESCRIPTION        "Count to store the number of discrete ranges
                        entered for the ethernet protocol ids."
     ::= { rcPrFilterAceIpProtoEntry 4 }

rcPrFilterAceIpProtoOper OBJECT-TYPE
     SYNTAX             INTEGER {
                            eq(1),    -- exact match
                            ne(2)     -- not equal
                        }
     MAX-ACCESS         read-create
     STATUS             current
     DESCRIPTION        "Operators for Ace Ip Protocols."
     ::= { rcPrFilterAceIpProtoEntry 5 }

rcPrFilterAceIpProtoRowStatus OBJECT-TYPE
     SYNTAX             RowStatus
     MAX-ACCESS         read-create
     STATUS             current
     DESCRIPTION        "Create/delete operations for this entry."
     ::= { rcPrFilterAceIpProtoEntry 6 }

-- ACE Ip Options Table

rcPrFilterAceIpOptionsTable OBJECT-TYPE
     SYNTAX             SEQUENCE OF RcPrFilterAceIpOptionsEntry
     MAX-ACCESS         not-accessible
     STATUS             current
     DESCRIPTION        "A table of Aces to store IP Options Header
			information of each Ace in context of its parent Acl."
     ::= { rcPrFilterAce 13 }

rcPrFilterAceIpOptionsEntry OBJECT-TYPE
     SYNTAX             RcPrFilterAceIpOptionsEntry
     MAX-ACCESS         not-accessible
     STATUS             current
     DESCRIPTION        "One Ace entry holding Ace IP Options Header
			information. An Ace is a member of one Acl."
     INDEX              { rcPrFilterAceIpOptionsAclId,
                          rcPrFilterAceIpOptionsAceId }
     ::= { rcPrFilterAceIpOptionsTable 1 }

RcPrFilterAceIpOptionsEntry ::= SEQUENCE {
        rcPrFilterAceIpOptionsAclId	     INTEGER,
        rcPrFilterAceIpOptionsAceId	     INTEGER,
	rcPrFilterAceIpOptionsOptions        INTEGER,
        rcPrFilterAceIpOptionsOper           INTEGER,
        rcPrFilterAceIpOptionsRowStatus      RowStatus
        }

rcPrFilterAceIpOptionsAclId OBJECT-TYPE
     SYNTAX             INTEGER (1..4096)
     MAX-ACCESS         not-accessible
     STATUS             current
     DESCRIPTION        "An index to the AceIpOptionsEntry, a unique
	                identifier for Acl entry in the range of Table
			Size."
     ::= { rcPrFilterAceIpOptionsEntry 1 }

rcPrFilterAceIpOptionsAceId OBJECT-TYPE
     SYNTAX             INTEGER (1..2000)
     MAX-ACCESS         not-accessible
     STATUS             current
     DESCRIPTION        "An index to the AceIpOptionsEntry, a unique
	                identifier for Acl entry in the range of Table
			Size."
     ::= { rcPrFilterAceIpOptionsEntry 2 }

rcPrFilterAceIpOptionsOptions  OBJECT-TYPE
     SYNTAX             INTEGER {
			    noOperation(1),
			    recordRoute(7),
			    experimentalMeasurement(10),
 			    mtuProbe(11),
			    mtuReply(12),
			    encode(15),
			    timestamp(68),
			    traceroute(82),
			    baseSecurity(130),
			    looseSourceRoute(131),
			    extendedSecurity(133),
			    commercialSecurity(134),
			    streamID(136),
			    strictSourceRouting(137),
			    experimentalAccessControl(142),
			    imiTrafficDescriptor(144),
			    extendedIP(145),
			    addressExtension(147),
			    routeAlert(148),
			    selectiveDirectedBroadcast(149),
			    nsapAddresses(150),
			    dynamicPacketState(151),
			    upstreamMulticastPacket(152),
			    experimentalFlowControl(205)
			}
     MAX-ACCESS         read-create
     STATUS             current
     DESCRIPTION        "Ip options to be matched from the IP Header."
     ::= { rcPrFilterAceIpOptionsEntry 3 }

rcPrFilterAceIpOptionsOper OBJECT-TYPE
     SYNTAX             INTEGER {
                            any(5)
			}
     MAX-ACCESS         read-create
     STATUS             current
     DESCRIPTION        "Logical Operator - only 'any' is valid at present."
     DEFVAL		{ any }
     ::= { rcPrFilterAceIpOptionsEntry 4 }

rcPrFilterAceIpOptionsRowStatus OBJECT-TYPE
     SYNTAX             RowStatus
     MAX-ACCESS         read-create
     STATUS             current
     DESCRIPTION        "Create/delete operations for this entry."
     ::= { rcPrFilterAceIpOptionsEntry 5 }

-- ACE Ip Fragmentation Table

rcPrFilterAceIpFragTable OBJECT-TYPE
     SYNTAX             SEQUENCE OF RcPrFilterAceIpFragEntry
     MAX-ACCESS         not-accessible
     STATUS             current
     DESCRIPTION        "A table of Aces to store IP Fragmentation Header
			information of each Ace in context of its parent Acl."
     ::= { rcPrFilterAce 14 }

rcPrFilterAceIpFragEntry OBJECT-TYPE
     SYNTAX             RcPrFilterAceIpFragEntry
     MAX-ACCESS         not-accessible
     STATUS             current
     DESCRIPTION        "One Ace entry holding Ace IP Fragmentation Header
			information. An Ace is a member of one Acl."
     INDEX              { rcPrFilterAceIpFragAclId,
                          rcPrFilterAceIpFragAceId }
     ::= { rcPrFilterAceIpFragTable 1 }

RcPrFilterAceIpFragEntry ::= SEQUENCE {
        rcPrFilterAceIpFragAclId	     INTEGER,
        rcPrFilterAceIpFragAceId	     INTEGER,
        rcPrFilterAceIpFragFragmentation     INTEGER,
        rcPrFilterAceIpFragOper              INTEGER,
        rcPrFilterAceIpFragRowStatus         RowStatus
        }

rcPrFilterAceIpFragAclId OBJECT-TYPE
     SYNTAX             INTEGER (1..4096)
     MAX-ACCESS         not-accessible
     STATUS             current
     DESCRIPTION        "An index to the AceIpFragEntry, a unique
	                identifier for Acl entry in the range of Table
			Size."
     ::= { rcPrFilterAceIpFragEntry 1 }

rcPrFilterAceIpFragAceId OBJECT-TYPE
     SYNTAX             INTEGER (1..2000)
     MAX-ACCESS         not-accessible
     STATUS             current
     DESCRIPTION        "An index to the AceIpFragEntry, a unique
	                identifier for Acl entry in the range of Table
			Size."
     ::= { rcPrFilterAceIpFragEntry 2 }

rcPrFilterAceIpFragFragmentation OBJECT-TYPE
     SYNTAX             INTEGER {
                            noFragment(0),
                            anyFragment(1),
                            moreFragment(2),
                            unused3(3),
                            lastFragment(4),
                            unused5(5),
                            unused6(6),
                            unused7(7)
                        }
     MAX-ACCESS         read-create
     STATUS             current
     DESCRIPTION        "Ip Fragmentation bits to be matched from the IP
                        Header."
     DEFVAL      { noFragment }
     ::= { rcPrFilterAceIpFragEntry 3 }

rcPrFilterAceIpFragOper OBJECT-TYPE
     SYNTAX             INTEGER {
                            eq(1)    -- exact match
                        }
     MAX-ACCESS         read-create
     STATUS             current
     DESCRIPTION        "Operator for Ip fragmentation."
     ::= { rcPrFilterAceIpFragEntry 4 }

rcPrFilterAceIpFragRowStatus OBJECT-TYPE
     SYNTAX             RowStatus
     MAX-ACCESS         read-create
     STATUS             current
     DESCRIPTION        "Create/delete operations for this entry."
     ::= { rcPrFilterAceIpFragEntry 5 }

-- ACE Protocol TcpSrcPort table

rcPrFilterAceProtoTcpSrcPortTable OBJECT-TYPE
     SYNTAX             SEQUENCE OF RcPrFilterAceProtoTcpSrcPortEntry
     MAX-ACCESS         not-accessible
     STATUS             current
     DESCRIPTION        "A table of Aces to store TCP Source Port information
                        of each Ace in context of its parent Acl."
     ::= { rcPrFilterAce 15 }

rcPrFilterAceProtoTcpSrcPortEntry OBJECT-TYPE
     SYNTAX             RcPrFilterAceProtoTcpSrcPortEntry
     MAX-ACCESS         not-accessible
     STATUS             current
     DESCRIPTION        "One entry holding Ace Protocol TCP Source Port
			information. An Ace is a member of one Acl."
     INDEX              { rcPrFilterAceProtoTcpSrcPortAclId,
                          rcPrFilterAceProtoTcpSrcPortAceId }
     ::= { rcPrFilterAceProtoTcpSrcPortTable 1 }


RcPrFilterAceProtoTcpSrcPortEntry ::= SEQUENCE {
        rcPrFilterAceProtoTcpSrcPortAclId     INTEGER,
        rcPrFilterAceProtoTcpSrcPortAceId     INTEGER,
        rcPrFilterAceProtoTcpSrcPortPort      OCTET STRING,
        rcPrFilterAceProtoTcpSrcPortCount     INTEGER,
        rcPrFilterAceProtoTcpSrcPortOper      INTEGER,
        rcPrFilterAceProtoTcpSrcPortRowStatus RowStatus
        }

rcPrFilterAceProtoTcpSrcPortAclId OBJECT-TYPE
     SYNTAX             INTEGER (1..4096)
     MAX-ACCESS         not-accessible
     STATUS             current
     DESCRIPTION        "An index to the AceProtoTcpSrcPortEntry, a unique
	                identifier for Acl entry in the range of Table
			Size."
     ::= { rcPrFilterAceProtoTcpSrcPortEntry 1 }

rcPrFilterAceProtoTcpSrcPortAceId OBJECT-TYPE
     SYNTAX             INTEGER (1..1000)
     MAX-ACCESS         not-accessible
     STATUS             current
     DESCRIPTION        "An index to the AceProtoTcpSrcPortEntry, a unique
	                identifier for Ace entry in the range of Table
			Size."
     ::= { rcPrFilterAceProtoTcpSrcPortEntry 2 }

rcPrFilterAceProtoTcpSrcPortPort OBJECT-TYPE
     SYNTAX             OCTET STRING (SIZE(0..1500))
     MAX-ACCESS         read-create
     STATUS             current
     DESCRIPTION        "Port Number or Port List to match on."
     ::= { rcPrFilterAceProtoTcpSrcPortEntry 3 }

rcPrFilterAceProtoTcpSrcPortCount OBJECT-TYPE
     SYNTAX             INTEGER (1..100)
     MAX-ACCESS         read-create
     STATUS             current
     DESCRIPTION        "Count to store the number of discrete ranges
                        entered for the TCP source port."
     ::= { rcPrFilterAceProtoTcpSrcPortEntry 4 }

rcPrFilterAceProtoTcpSrcPortOper OBJECT-TYPE
     SYNTAX             INTEGER {
                            eq(1),   -- exact match
			    ne(2),    -- not equal
                            le(3),    -- less than or equal to
                            ge(4)     -- greater than or equal to
                        }
     MAX-ACCESS         read-create
     STATUS             current
     DESCRIPTION        "Operator for Ace Protocol TcpSrcPort."
     ::= { rcPrFilterAceProtoTcpSrcPortEntry 5 }

rcPrFilterAceProtoTcpSrcPortRowStatus OBJECT-TYPE
     SYNTAX             RowStatus
     MAX-ACCESS         read-create
     STATUS             current
     DESCRIPTION        "Create/delete operations for this entry."
     ::= { rcPrFilterAceProtoTcpSrcPortEntry 6 }

-- ACE Protocol UdpSrcPort table

rcPrFilterAceProtoUdpSrcPortTable OBJECT-TYPE
     SYNTAX             SEQUENCE OF RcPrFilterAceProtoUdpSrcPortEntry
     MAX-ACCESS         not-accessible
     STATUS             current
     DESCRIPTION        "A table of Aces to store UDP Source Port information
                        of each Ace in context of its parent Acl."
     ::= { rcPrFilterAce 16 }

rcPrFilterAceProtoUdpSrcPortEntry OBJECT-TYPE
     SYNTAX             RcPrFilterAceProtoUdpSrcPortEntry
     MAX-ACCESS         not-accessible
     STATUS             current
     DESCRIPTION        "One entry holding Ace Protocol UDP Source Port
			information. An Ace is a member of one Acl."
     INDEX              { rcPrFilterAceProtoUdpSrcPortAclId,
                          rcPrFilterAceProtoUdpSrcPortAceId }
     ::= { rcPrFilterAceProtoUdpSrcPortTable 1 }


RcPrFilterAceProtoUdpSrcPortEntry ::= SEQUENCE {
        rcPrFilterAceProtoUdpSrcPortAclId     INTEGER,
        rcPrFilterAceProtoUdpSrcPortAceId     INTEGER,
        rcPrFilterAceProtoUdpSrcPortPort      OCTET STRING,
        rcPrFilterAceProtoUdpSrcPortCount     INTEGER,
        rcPrFilterAceProtoUdpSrcPortOper      INTEGER,
        rcPrFilterAceProtoUdpSrcPortRowStatus RowStatus
        }

rcPrFilterAceProtoUdpSrcPortAclId OBJECT-TYPE
     SYNTAX             INTEGER (1..4096)
     MAX-ACCESS         not-accessible
     STATUS             current
     DESCRIPTION        "An index to the AceProtoUdpSrcPortEntry, a unique
	                identifier for Acl entry in the range of Table
			Size."
     ::= { rcPrFilterAceProtoUdpSrcPortEntry 1 }

rcPrFilterAceProtoUdpSrcPortAceId OBJECT-TYPE
     SYNTAX             INTEGER (1..1000)
     MAX-ACCESS         not-accessible
     STATUS             current
     DESCRIPTION        "An index to the AceProtoUdpSrcPortEntry, a unique
	                identifier for Ace entry in the range of Table
			Size."
     ::= { rcPrFilterAceProtoUdpSrcPortEntry 2 }

rcPrFilterAceProtoUdpSrcPortPort OBJECT-TYPE
     SYNTAX             OCTET STRING (SIZE(0..1500))
     MAX-ACCESS         read-create
     STATUS             current
     DESCRIPTION        "Port Number or Port List to match on."
     ::= { rcPrFilterAceProtoUdpSrcPortEntry 3 }

rcPrFilterAceProtoUdpSrcPortCount OBJECT-TYPE
     SYNTAX             INTEGER (1..100)
     MAX-ACCESS         read-create
     STATUS             current
     DESCRIPTION        "Count to store the number of discrete ranges
                        entered for the UDP source port."
     ::= { rcPrFilterAceProtoUdpSrcPortEntry 4 }

rcPrFilterAceProtoUdpSrcPortOper OBJECT-TYPE
     SYNTAX             INTEGER {
                            eq(1),   -- exact match
			    ne(2),    -- not equal
                            le(3),    -- less than or equal to
                            ge(4)     -- greater than or equal to
                        }
     MAX-ACCESS         read-create
     STATUS             current
     DESCRIPTION        "Operator for Ace Protocol UdpSrcPort."
     ::= { rcPrFilterAceProtoUdpSrcPortEntry 5 }

rcPrFilterAceProtoUdpSrcPortRowStatus OBJECT-TYPE
     SYNTAX             RowStatus
     MAX-ACCESS         read-create
     STATUS             current
     DESCRIPTION        "Create/delete operations for this entry."
     ::= { rcPrFilterAceProtoUdpSrcPortEntry 6 }

-- ACE Protocol TcpDstPort table

rcPrFilterAceProtoTcpDstPortTable OBJECT-TYPE
     SYNTAX             SEQUENCE OF RcPrFilterAceProtoTcpDstPortEntry
     MAX-ACCESS         not-accessible
     STATUS             current
     DESCRIPTION        "A table of Aces to store TCP Dest Port information
                        of each Ace in context of its parent Acl."
     ::= { rcPrFilterAce 17 }

rcPrFilterAceProtoTcpDstPortEntry OBJECT-TYPE
     SYNTAX             RcPrFilterAceProtoTcpDstPortEntry
     MAX-ACCESS         not-accessible
     STATUS             current
     DESCRIPTION        "One entry holding Ace Protocol TCP Dest Port
			information. An Ace is a member of one Acl."
     INDEX              { rcPrFilterAceProtoTcpDstPortAclId,
                          rcPrFilterAceProtoTcpDstPortAceId }
     ::= { rcPrFilterAceProtoTcpDstPortTable 1 }


RcPrFilterAceProtoTcpDstPortEntry ::= SEQUENCE {
        rcPrFilterAceProtoTcpDstPortAclId     INTEGER,
        rcPrFilterAceProtoTcpDstPortAceId     INTEGER,
        rcPrFilterAceProtoTcpDstPortPort      OCTET STRING,
        rcPrFilterAceProtoTcpDstPortCount     INTEGER,
        rcPrFilterAceProtoTcpDstPortOper      INTEGER,
        rcPrFilterAceProtoTcpDstPortRowStatus RowStatus
        }

rcPrFilterAceProtoTcpDstPortAclId OBJECT-TYPE
     SYNTAX             INTEGER (1..4096)
     MAX-ACCESS         not-accessible
     STATUS             current
     DESCRIPTION        "An index to the AceProtoTcpDstPortEntry, a unique
	                identifier for Acl entry in the range of Table
			Size."
     ::= { rcPrFilterAceProtoTcpDstPortEntry 1 }

rcPrFilterAceProtoTcpDstPortAceId OBJECT-TYPE
     SYNTAX             INTEGER (1..1000)
     MAX-ACCESS         not-accessible
     STATUS             current
     DESCRIPTION        "An index to the AceProtoTcpDstPortEntry, a unique
	                identifier for Ace entry in the range of Table
			Size."
     ::= { rcPrFilterAceProtoTcpDstPortEntry 2 }

rcPrFilterAceProtoTcpDstPortPort OBJECT-TYPE
     SYNTAX             OCTET STRING (SIZE(0..1500))
     MAX-ACCESS         read-create
     STATUS             current
     DESCRIPTION        "Port Number or Port List to match on."
     ::= { rcPrFilterAceProtoTcpDstPortEntry 3 }

rcPrFilterAceProtoTcpDstPortCount OBJECT-TYPE
     SYNTAX             INTEGER (1..100)
     MAX-ACCESS         read-create
     STATUS             current
     DESCRIPTION        "Count to store the number of discrete ranges
                        entered for the TCP dest port."
     ::= { rcPrFilterAceProtoTcpDstPortEntry 4 }

rcPrFilterAceProtoTcpDstPortOper OBJECT-TYPE
     SYNTAX             INTEGER {
                            eq(1),   -- exact match
			    ne(2),    -- not equal
                            le(3),    -- less than or equal to
                            ge(4)     -- greater than or equal to
                        }
     MAX-ACCESS         read-create
     STATUS             current
     DESCRIPTION        "Operator for Ace Protocol TcpDstPort."
     ::= { rcPrFilterAceProtoTcpDstPortEntry 5 }

rcPrFilterAceProtoTcpDstPortRowStatus OBJECT-TYPE
     SYNTAX             RowStatus
     MAX-ACCESS         read-create
     STATUS             current
     DESCRIPTION        "Create/delete operations for this entry."
     ::= { rcPrFilterAceProtoTcpDstPortEntry 6 }

-- ACE Protocol UdpDstPort table

rcPrFilterAceProtoUdpDstPortTable OBJECT-TYPE
     SYNTAX             SEQUENCE OF RcPrFilterAceProtoUdpDstPortEntry
     MAX-ACCESS         not-accessible
     STATUS             current
     DESCRIPTION        "A table of Aces to store UDP Dest Port information
                        of each Ace in context of its parent Acl."
     ::= { rcPrFilterAce 18 }

rcPrFilterAceProtoUdpDstPortEntry OBJECT-TYPE
     SYNTAX             RcPrFilterAceProtoUdpDstPortEntry
     MAX-ACCESS         not-accessible
     STATUS             current
     DESCRIPTION        "One entry holding Ace Protocol UDP Dest Port
			information. An Ace is a member of one Acl."
     INDEX              { rcPrFilterAceProtoUdpDstPortAclId,
                          rcPrFilterAceProtoUdpDstPortAceId }
     ::= { rcPrFilterAceProtoUdpDstPortTable 1 }


RcPrFilterAceProtoUdpDstPortEntry ::= SEQUENCE {
        rcPrFilterAceProtoUdpDstPortAclId     INTEGER,
        rcPrFilterAceProtoUdpDstPortAceId     INTEGER,
        rcPrFilterAceProtoUdpDstPortPort      OCTET STRING,
        rcPrFilterAceProtoUdpDstPortCount     INTEGER,
        rcPrFilterAceProtoUdpDstPortOper      INTEGER,
        rcPrFilterAceProtoUdpDstPortRowStatus RowStatus
        }

rcPrFilterAceProtoUdpDstPortAclId OBJECT-TYPE
     SYNTAX             INTEGER (1..4096)
     MAX-ACCESS         not-accessible
     STATUS             current
     DESCRIPTION        "An index to the AceProtoUdpDstPortEntry, a unique
	                identifier for Acl entry in the range of Table
			Size."
     ::= { rcPrFilterAceProtoUdpDstPortEntry 1 }

rcPrFilterAceProtoUdpDstPortAceId OBJECT-TYPE
     SYNTAX             INTEGER (1..1000)
     MAX-ACCESS         not-accessible
     STATUS             current
     DESCRIPTION        "An index to the AceProtoUdpDstPortEntry, a unique
	                identifier for Ace entry in the range of Table
			Size."
     ::= { rcPrFilterAceProtoUdpDstPortEntry 2 }

rcPrFilterAceProtoUdpDstPortPort OBJECT-TYPE
     SYNTAX             OCTET STRING (SIZE(0..1500))
     MAX-ACCESS         read-create
     STATUS             current
     DESCRIPTION        "Port Number or Port List to match on."
     ::= { rcPrFilterAceProtoUdpDstPortEntry 3 }

rcPrFilterAceProtoUdpDstPortCount OBJECT-TYPE
     SYNTAX             INTEGER (1..100)
     MAX-ACCESS         read-create
     STATUS             current
     DESCRIPTION        "Count to store the number of discrete ranges
                        entered for the UDP dest port."
     ::= { rcPrFilterAceProtoUdpDstPortEntry 4 }

rcPrFilterAceProtoUdpDstPortOper OBJECT-TYPE
     SYNTAX             INTEGER {
                            eq(1),   -- exact match
			    ne(2),   -- not equal
                            le(3),    -- less than or equal to
                            ge(4)     -- greater than or equal to
                        }
     MAX-ACCESS         read-create
     STATUS             current
     DESCRIPTION        "Operator for Ace Protocol UdpDstPort."
     ::= { rcPrFilterAceProtoUdpDstPortEntry 5 }

rcPrFilterAceProtoUdpDstPortRowStatus OBJECT-TYPE
     SYNTAX             RowStatus
     MAX-ACCESS         read-create
     STATUS             current
     DESCRIPTION        "Create/delete operations for this entry."
     ::= { rcPrFilterAceProtoUdpDstPortEntry 6 }

-- ACE Protocol IcmpMsgType table

rcPrFilterAceProtoIcmpMsgTypeTable OBJECT-TYPE
     SYNTAX             SEQUENCE OF RcPrFilterAceProtoIcmpMsgTypeEntry
     MAX-ACCESS         not-accessible
     STATUS             current
     DESCRIPTION        "A table of Aces to store ICMP message type information
                        of each Ace in context of its parent Acl."
     ::= { rcPrFilterAce 19 }

rcPrFilterAceProtoIcmpMsgTypeEntry OBJECT-TYPE
     SYNTAX             RcPrFilterAceProtoIcmpMsgTypeEntry
     MAX-ACCESS         not-accessible
     STATUS             current
     DESCRIPTION        "One entry holding Ace ICMP message type
			information. An Ace is a member of one Acl."
     INDEX              { rcPrFilterAceProtoIcmpMsgTypeAclId,
                          rcPrFilterAceProtoIcmpMsgTypeAceId }
     ::= { rcPrFilterAceProtoIcmpMsgTypeTable 1 }


RcPrFilterAceProtoIcmpMsgTypeEntry ::= SEQUENCE {
        rcPrFilterAceProtoIcmpMsgTypeAclId     INTEGER,
        rcPrFilterAceProtoIcmpMsgTypeAceId     INTEGER,
        rcPrFilterAceProtoIcmpMsgTypeList      OCTET STRING,
        rcPrFilterAceProtoIcmpMsgTypeCount     INTEGER,
        rcPrFilterAceProtoIcmpMsgTypeOper      INTEGER,
        rcPrFilterAceProtoIcmpMsgTypeRowStatus RowStatus
        }

rcPrFilterAceProtoIcmpMsgTypeAclId OBJECT-TYPE
     SYNTAX             INTEGER (1..4096)
     MAX-ACCESS         not-accessible
     STATUS             current
     DESCRIPTION        "An index to the AceProtoIcmpMsgTypeEntry, a unique
	                identifier for Acl entry in the range of Table
			Size."
     ::= { rcPrFilterAceProtoIcmpMsgTypeEntry 1 }

rcPrFilterAceProtoIcmpMsgTypeAceId OBJECT-TYPE
     SYNTAX             INTEGER (1..2000)
     MAX-ACCESS         not-accessible
     STATUS             current
     DESCRIPTION        "An index to the AceProtoIcmpMsgTypeEntry, a unique
	                identifier for Ace entry in the range of Table
			Size."
     ::= { rcPrFilterAceProtoIcmpMsgTypeEntry 2 }

rcPrFilterAceProtoIcmpMsgTypeList OBJECT-TYPE
     SYNTAX             OCTET STRING (SIZE(0..1500))
     MAX-ACCESS         read-create
     STATUS             current
     DESCRIPTION        "One or a list of Icmp messages to be matched.
			Need to provide strings, number of protocol header
			types (pre-defined values plus user-defined headers).
			Valid range is 0 to 255 (reserved)."
     ::= { rcPrFilterAceProtoIcmpMsgTypeEntry 3 }

rcPrFilterAceProtoIcmpMsgTypeCount OBJECT-TYPE
     SYNTAX             INTEGER (1..100)
     MAX-ACCESS         read-create
     STATUS             current
     DESCRIPTION        "Count to store the number of discrete ranges
                        entered for the ICMP message types."
     ::= { rcPrFilterAceProtoIcmpMsgTypeEntry 4 }

rcPrFilterAceProtoIcmpMsgTypeOper OBJECT-TYPE
     SYNTAX             INTEGER {
                            eq(1),   -- exact match
			    ne(2)    -- not equal
                        }
     MAX-ACCESS         read-create
     STATUS             current
     DESCRIPTION        "Operator for Ace Protocol IcmpMsgTypes."
     ::= { rcPrFilterAceProtoIcmpMsgTypeEntry 5 }

rcPrFilterAceProtoIcmpMsgTypeRowStatus OBJECT-TYPE
     SYNTAX             RowStatus
     MAX-ACCESS         read-create
     STATUS             current
     DESCRIPTION        "Create/delete operations for this entry."
     ::= { rcPrFilterAceProtoIcmpMsgTypeEntry 6 }

-- ACE Protocol Tcp-flags table

rcPrFilterAceProtoTcpFlagsTable OBJECT-TYPE
     SYNTAX             SEQUENCE OF RcPrFilterAceProtoTcpFlagsEntry
     MAX-ACCESS         not-accessible
     STATUS             current
     DESCRIPTION        "A table of Aces to store TCP Flags information
                        of each Ace in context of its parent Acl."
     ::= { rcPrFilterAce 20 }

rcPrFilterAceProtoTcpFlagsEntry OBJECT-TYPE
     SYNTAX             RcPrFilterAceProtoTcpFlagsEntry
     MAX-ACCESS         not-accessible
     STATUS             current
     DESCRIPTION        "One entry holding Ace Protocol TCP flags
			information. An Ace is a member of one Acl."
     INDEX              { rcPrFilterAceProtoTcpFlagsAclId,
                          rcPrFilterAceProtoTcpFlagsAceId }
     ::= { rcPrFilterAceProtoTcpFlagsTable 1 }


RcPrFilterAceProtoTcpFlagsEntry ::= SEQUENCE {
        rcPrFilterAceProtoTcpFlagsAclId     INTEGER,
        rcPrFilterAceProtoTcpFlagsAceId     INTEGER,
        rcPrFilterAceProtoTcpFlagsList      OCTET STRING,
        rcPrFilterAceProtoTcpFlagsCount     INTEGER,
        rcPrFilterAceProtoTcpFlagsOper      INTEGER,
        rcPrFilterAceProtoTcpFlagsRowStatus RowStatus,
        rcPrFilterAceProtoTcpFlagsOperMask  Integer32
        }

rcPrFilterAceProtoTcpFlagsAclId OBJECT-TYPE
     SYNTAX             INTEGER (1..4096)
     MAX-ACCESS         not-accessible
     STATUS             current
     DESCRIPTION        "An index to the rcPrFilterAceProtoTcpFlagsEntry,
                    a unique identifier for Acl entry in the range of Table
			        Size."
     ::= { rcPrFilterAceProtoTcpFlagsEntry 1 }

rcPrFilterAceProtoTcpFlagsAceId OBJECT-TYPE
     SYNTAX             INTEGER (1..2000)
     MAX-ACCESS         not-accessible
     STATUS             current
     DESCRIPTION        "An index to the rcPrFilterAceProtoTcpFlagsEntry,
                         a unique identifier for Ace entry in the
                         range of Table Size."
     ::= { rcPrFilterAceProtoTcpFlagsEntry 2 }

rcPrFilterAceProtoTcpFlagsList OBJECT-TYPE
     SYNTAX             OCTET STRING (SIZE(0..1500))
     MAX-ACCESS         read-create
     STATUS             current
     DESCRIPTION        "One or a list of Tcp flags to be matched.
			Need to provide strings, number of protocol header
			types (pre-defined values plus user-defined headers).
			Valid range is 0 to 63"
     ::= { rcPrFilterAceProtoTcpFlagsEntry 3 }

rcPrFilterAceProtoTcpFlagsCount OBJECT-TYPE
     SYNTAX             INTEGER (1..100)
     MAX-ACCESS         read-create
     STATUS             current
     DESCRIPTION        "Count to store the number of discrete ranges
                        entered for the TCP flags."
     ::= { rcPrFilterAceProtoTcpFlagsEntry 4 }

rcPrFilterAceProtoTcpFlagsOper OBJECT-TYPE
     SYNTAX             INTEGER {
			    matchAny(6),
			    matchAll(7),
                            mask(8)
                        }
     MAX-ACCESS         read-create
     STATUS             current
     DESCRIPTION        "Operator for Ace Protocol TcpFlags."
     ::= { rcPrFilterAceProtoTcpFlagsEntry 5 }

rcPrFilterAceProtoTcpFlagsRowStatus OBJECT-TYPE
     SYNTAX             RowStatus
     MAX-ACCESS         read-create
     STATUS             current
     DESCRIPTION        "Create/delete operations for this entry."
     ::= { rcPrFilterAceProtoTcpFlagsEntry 6 }

rcPrFilterAceProtoTcpFlagsOperMask OBJECT-TYPE
     SYNTAX             Integer32(0..'3F'h)
     MAX-ACCESS         read-write
     STATUS             current
     DESCRIPTION        "The mask value in hex which can be set for the
                        rcPrFilterAceProtoTcpFlagsOper when the option
                        selected is mask. It will be set 0x0 when object
                        rcPrFilterAceProtoTcpFlagsOper is set to eq"
     ::= { rcPrFilterAceProtoTcpFlagsEntry 7 }

-- ACE Pattern Table

-- Ace Pattern 1
rcPrFilterAcePattern1Table OBJECT-TYPE
     SYNTAX             SEQUENCE OF RcPrFilterAcePattern1Entry
     MAX-ACCESS         not-accessible
     STATUS             current
     DESCRIPTION        "A table of pattern fields for Aces to manage the
                        settings for each user defined field. "
     ::= { rcPrFilterAce 21 }

rcPrFilterAcePattern1Entry OBJECT-TYPE
     SYNTAX             RcPrFilterAcePattern1Entry
     MAX-ACCESS         not-accessible
     STATUS             current
     DESCRIPTION        "One Ace entry holding Ace User Defined Pattern
                        information. Ace is a member of one Acl."
     INDEX              { rcPrFilterAcePattern1AclId,
                          rcPrFilterAcePattern1AceId }
     ::= { rcPrFilterAcePattern1Table 1 }

RcPrFilterAcePattern1Entry ::= SEQUENCE {
        rcPrFilterAcePattern1AclId	INTEGER,
        rcPrFilterAcePattern1AceId	INTEGER,
        rcPrFilterAcePattern1Name       DisplayString,
        rcPrFilterAcePattern1Value      OCTET STRING,
        rcPrFilterAcePattern1Oper       INTEGER,
        rcPrFilterAcePattern1RowStatus  RowStatus
        }

rcPrFilterAcePattern1AclId OBJECT-TYPE
     SYNTAX             INTEGER (1..4096)
     MAX-ACCESS         not-accessible
     STATUS             current
     DESCRIPTION        "An index to the AcePatternEntry, a unique
	                identifier for Acl entry in the range of Table
			Size."
     ::= { rcPrFilterAcePattern1Entry 1 }

rcPrFilterAcePattern1AceId OBJECT-TYPE
     SYNTAX             INTEGER (1..1000)
     MAX-ACCESS         not-accessible
     STATUS             current
     DESCRIPTION        "An index to the AcePatternEntry, a unique
	                identifier for Acl entry in the range of Table
			Size."
     ::= { rcPrFilterAcePattern1Entry 2 }

rcPrFilterAcePattern1Name OBJECT-TYPE
     SYNTAX             DisplayString (SIZE (0..32))
     MAX-ACCESS         read-create
     STATUS             current
     DESCRIPTION        "A descriptive name chosen by the administrator for
                        the Ace Pattern Entry."
     ::= { rcPrFilterAcePattern1Entry 3 }

rcPrFilterAcePattern1Value OBJECT-TYPE
     SYNTAX             OCTET STRING (SIZE (0..1500))
     MAX-ACCESS         read-create
     STATUS             current
     DESCRIPTION        "Set the pattern value as numeric string. The numeric
                        value of each byte is encoded in one octet of the
                        string. Unused bytes are left at the trailing end of
                        string. The number of bytes to extract from this string
                        is set in rcPrFilterActPatternLength."
     DEFVAL             { "" }
     ::= { rcPrFilterAcePattern1Entry 4 }

rcPrFilterAcePattern1Oper OBJECT-TYPE
     SYNTAX             INTEGER {
                            eq(1),    -- exact match
                            le(3),    -- less than or equal to
                            ge(4)     -- greater than or equal to
                        }
     MAX-ACCESS         read-create
     STATUS             current
     DESCRIPTION        "Operators for Ace Pattern."
     ::= { rcPrFilterAcePattern1Entry 5 }

rcPrFilterAcePattern1RowStatus OBJECT-TYPE
     SYNTAX             RowStatus
     MAX-ACCESS         read-create
     STATUS             current
     DESCRIPTION        "Create/delete operations for this entry."
        ::= { rcPrFilterAcePattern1Entry 6 }

-- Ace Pattern 2
rcPrFilterAcePattern2Table OBJECT-TYPE
     SYNTAX             SEQUENCE OF RcPrFilterAcePattern2Entry
     MAX-ACCESS         not-accessible
     STATUS             current
     DESCRIPTION        "A table of pattern fields for Aces to manage the
                        settings for each user defined field. "
     ::= { rcPrFilterAce 22 }

rcPrFilterAcePattern2Entry OBJECT-TYPE
     SYNTAX             RcPrFilterAcePattern2Entry
     MAX-ACCESS         not-accessible
     STATUS             current
     DESCRIPTION        "One Ace entry holding Ace User Defined Pattern
                        information. Ace is a member of one Acl."
     INDEX              { rcPrFilterAcePattern2AclId,
                          rcPrFilterAcePattern2AceId }
     ::= { rcPrFilterAcePattern2Table 1 }

RcPrFilterAcePattern2Entry ::= SEQUENCE {
        rcPrFilterAcePattern2AclId	INTEGER,
        rcPrFilterAcePattern2AceId	INTEGER,
        rcPrFilterAcePattern2Name       DisplayString,
        rcPrFilterAcePattern2Value      OCTET STRING,
        rcPrFilterAcePattern2Oper       INTEGER,
        rcPrFilterAcePattern2RowStatus  RowStatus
        }

rcPrFilterAcePattern2AclId OBJECT-TYPE
     SYNTAX             INTEGER (1..4096)
     MAX-ACCESS         not-accessible
     STATUS             current
     DESCRIPTION        "An index to the AcePatternEntry, a unique
	                identifier for Acl entry in the range of Table
			Size."
     ::= { rcPrFilterAcePattern2Entry 1 }

rcPrFilterAcePattern2AceId OBJECT-TYPE
     SYNTAX             INTEGER (1..1000)
     MAX-ACCESS         not-accessible
     STATUS             current
     DESCRIPTION        "An index to the AcePatternEntry, a unique
	                identifier for Acl entry in the range of Table
			Size."
     ::= { rcPrFilterAcePattern2Entry 2 }

rcPrFilterAcePattern2Name OBJECT-TYPE
     SYNTAX             DisplayString (SIZE (0..32))
     MAX-ACCESS         read-create
     STATUS             current
     DESCRIPTION        "A descriptive name chosen by the administrator for
                        the Ace Pattern Entry."
     ::= { rcPrFilterAcePattern2Entry 3 }

rcPrFilterAcePattern2Value OBJECT-TYPE
     SYNTAX             OCTET STRING (SIZE (0..1500))
     MAX-ACCESS         read-create
     STATUS             current
     DESCRIPTION        "Set the pattern value as numeric string. The numeric
                        value of each byte is encoded in one octet of the
                        string. Unused bytes are left at the trailing end of
                        string. The number of bytes to extract from this string
                        is set in rcPrFilterActPatternLength."
     DEFVAL             { "" }
     ::= { rcPrFilterAcePattern2Entry 4 }

rcPrFilterAcePattern2Oper OBJECT-TYPE
     SYNTAX             INTEGER {
                            eq(1),    -- exact match
                            le(3),    -- less than or equal to
                            ge(4)     -- greater than or equal to
                        }
     MAX-ACCESS         read-create
     STATUS             current
     DESCRIPTION        "Operators for Ace Pattern."
     ::= { rcPrFilterAcePattern2Entry 5 }

rcPrFilterAcePattern2RowStatus OBJECT-TYPE
     SYNTAX             RowStatus
     MAX-ACCESS         read-create
     STATUS             current
     DESCRIPTION        "Create/delete operations for this entry."
        ::= { rcPrFilterAcePattern2Entry 6 }

-- Ace Pattern 3
rcPrFilterAcePattern3Table OBJECT-TYPE
     SYNTAX             SEQUENCE OF RcPrFilterAcePattern3Entry
     MAX-ACCESS         not-accessible
     STATUS             current
     DESCRIPTION        "A table of pattern fields for Aces to manage the
                        settings for each user defined field. "
     ::= { rcPrFilterAce 23 }

rcPrFilterAcePattern3Entry OBJECT-TYPE
     SYNTAX             RcPrFilterAcePattern3Entry
     MAX-ACCESS         not-accessible
     STATUS             current
     DESCRIPTION        "One Ace entry holding Ace User Defined Pattern
                        information. Ace is a member of one Acl."
     INDEX              { rcPrFilterAcePattern3AclId,
                          rcPrFilterAcePattern3AceId }
     ::= { rcPrFilterAcePattern3Table 1 }

RcPrFilterAcePattern3Entry ::= SEQUENCE {
        rcPrFilterAcePattern3AclId	INTEGER,
        rcPrFilterAcePattern3AceId	INTEGER,
        rcPrFilterAcePattern3Name       DisplayString,
        rcPrFilterAcePattern3Value      OCTET STRING,
        rcPrFilterAcePattern3Oper       INTEGER,
        rcPrFilterAcePattern3RowStatus  RowStatus
        }

rcPrFilterAcePattern3AclId OBJECT-TYPE
     SYNTAX             INTEGER (1..4096)
     MAX-ACCESS         not-accessible
     STATUS             current
     DESCRIPTION        "An index to the AcePatternEntry, a unique
	                identifier for Acl entry in the range of Table
			Size."
     ::= { rcPrFilterAcePattern3Entry 1 }

rcPrFilterAcePattern3AceId OBJECT-TYPE
     SYNTAX             INTEGER (1..1000)
     MAX-ACCESS         not-accessible
     STATUS             current
     DESCRIPTION        "An index to the AcePatternEntry, a unique
	                identifier for Acl entry in the range of Table
			Size."
     ::= { rcPrFilterAcePattern3Entry 2 }

rcPrFilterAcePattern3Name OBJECT-TYPE
     SYNTAX             DisplayString (SIZE (0..32))
     MAX-ACCESS         read-create
     STATUS             current
     DESCRIPTION        "A descriptive name chosen by the administrator for
                        the Ace Pattern Entry."
     ::= { rcPrFilterAcePattern3Entry 3 }

rcPrFilterAcePattern3Value OBJECT-TYPE
     SYNTAX             OCTET STRING (SIZE (0..1500))
     MAX-ACCESS         read-create
     STATUS             current
     DESCRIPTION        "Set the pattern value as numeric string. The numeric
                        value of each byte is encoded in one octet of the
                        string. Unused bytes are left at the trailing end of
                        string. The number of bytes to extract from this string
                        is set in rcPrFilterActPatternLength."
     DEFVAL             { "" }
     ::= { rcPrFilterAcePattern3Entry 4 }

rcPrFilterAcePattern3Oper OBJECT-TYPE
     SYNTAX             INTEGER {
                            eq(1),    -- exact match
                            le(3),    -- less than or equal to
                            ge(4)     -- greater than or equal to
                        }
     MAX-ACCESS         read-create
     STATUS             current
     DESCRIPTION        "Operators for Ace Pattern."
     ::= { rcPrFilterAcePattern3Entry 5 }

rcPrFilterAcePattern3RowStatus OBJECT-TYPE
     SYNTAX             RowStatus
     MAX-ACCESS         read-create
     STATUS             current
     DESCRIPTION        "Create/delete operations for this entry."
        ::= { rcPrFilterAcePattern3Entry 6 }


-- Per-ACE-Per-Port Statistics

rcPrFilterAceStatsTable OBJECT-TYPE
     SYNTAX             SEQUENCE OF RcPrFilterAceStatsEntry
     MAX-ACCESS         not-accessible
     STATUS             current
     DESCRIPTION        "A table of ACE Statistics Entries to store
			per-ACE-per-Port Statistics"
     ::= { rcPrFilterAce 24 }

rcPrFilterAceStatsEntry OBJECT-TYPE
     SYNTAX             RcPrFilterAceStatsEntry
     MAX-ACCESS         not-accessible
     STATUS             current
     DESCRIPTION        "Ace Statistics entry holding per
			ACE-per-port Statistics"
     INDEX              { rcPrFilterAceStatsAclId,
                          rcPrFilterAceStatsAceId,
                          rcPrFilterAceStatsPortId }
     ::= { rcPrFilterAceStatsTable 1 }

RcPrFilterAceStatsEntry ::= SEQUENCE {
        rcPrFilterAceStatsAclId	             INTEGER,
        rcPrFilterAceStatsAceId	             INTEGER,
        rcPrFilterAceStatsPortId             INTEGER,
        rcPrFilterAceStatsMatchCountPkts     Counter64,
        rcPrFilterAceStatsMatchCountOctets   Counter64,
	rcPrFilterAceStatsClear		     TruthValue
        }

rcPrFilterAceStatsAclId OBJECT-TYPE
     SYNTAX             INTEGER (1..4096)
     MAX-ACCESS         not-accessible
     STATUS             current
     DESCRIPTION        "An index to the AceStatsEntry, a unique
	                identifier for Acl entry in the range of Table Size."
     ::= { rcPrFilterAceStatsEntry 1 }

rcPrFilterAceStatsAceId OBJECT-TYPE
     SYNTAX             INTEGER (1..2000)
     MAX-ACCESS         not-accessible
     STATUS             current
     DESCRIPTION        "An index to the AceStatsEntry, a unique identifier
                         for ACE entry in the range of Table Size."
     ::= { rcPrFilterAceStatsEntry 2 }

rcPrFilterAceStatsPortId OBJECT-TYPE
     SYNTAX             INTEGER (1..703)
     MAX-ACCESS         not-accessible
     STATUS             current
     DESCRIPTION        "An index to the AceStatsEntry, a unique identifier
                         of the portId"
     ::= { rcPrFilterAceStatsEntry 3 }

rcPrFilterAceStatsMatchCountPkts OBJECT-TYPE
     SYNTAX             Counter64
     MAX-ACCESS         read-only
     STATUS             current
     DESCRIPTION        "Count of packets that match this particular Ace on this
                         particular port."
     ::= { rcPrFilterAceStatsEntry 4 }

rcPrFilterAceStatsMatchCountOctets OBJECT-TYPE
     SYNTAX             Counter64
     MAX-ACCESS         read-only
     STATUS             current
     DESCRIPTION        "Byte count of traffic that match this particular Ace on
                         this particular port"
     ::= { rcPrFilterAceStatsEntry 5 }

rcPrFilterAceStatsClear  OBJECT-TYPE
     SYNTAX             TruthValue
     MAX-ACCESS         read-create
     STATUS             current
     DESCRIPTION        "Clear Per-ACE-Per-Port statistics."
     ::= { rcPrFilterAceStatsEntry 6 }

-- ACE Ethernet Show Table

rcPrFilterAceEthShowTable OBJECT-TYPE
     SYNTAX             SEQUENCE OF RcPrFilterAceEthShowEntry
     MAX-ACCESS         not-accessible
     STATUS             current
     DESCRIPTION        "A table of Aces to store Ethernet Header
                        information of each Ace in context of
                        its parent Acl. "
     ::= { rcPrFilterAce 25 }

rcPrFilterAceEthShowEntry OBJECT-TYPE
     SYNTAX             RcPrFilterAceEthShowEntry
     MAX-ACCESS         not-accessible
     STATUS             current
     DESCRIPTION        "One Ace entry holding Ace Ethernet information.
                         Ace is a member of one Acl."
     INDEX              { rcPrFilterAceEthShowAclId,
                          rcPrFilterAceEthShowAceId }
     ::= { rcPrFilterAceEthShowTable 1 }

RcPrFilterAceEthShowEntry ::= SEQUENCE {
	rcPrFilterAceEthShowAclId		INTEGER,
	rcPrFilterAceEthShowAceId		INTEGER,
        rcPrFilterAceEthShowSrcAddrList        	OCTET STRING,
        rcPrFilterAceEthShowSrcAddrOper        	INTEGER,
        rcPrFilterAceEthShowDstAddrList		OCTET STRING,
        rcPrFilterAceEthShowDstAddrOper        	INTEGER,
	rcPrFilterAceEthShowEtherTypeList      	OCTET STRING,
        rcPrFilterAceEthShowEtherTypeOper      	INTEGER,
	rcPrFilterAceEthShowVlanTagPrio	 	INTEGER,
        rcPrFilterAceEthShowVlanTagPrioOper     INTEGER,
        rcPrFilterAceEthShowPort         	PortSet,
        rcPrFilterAceEthShowPortOper         	INTEGER,
        rcPrFilterAceEthShowVlanIdList        	IdList,
        rcPrFilterAceEthShowVlanIdOper          INTEGER,
        rcPrFilterAceEthShowSrcAddrOperMask     DisplayString,
        rcPrFilterAceEthShowDstAddrOperMask     DisplayString,
        rcPrFilterAceEthShowVlanTagPrioOperMask Integer32,
        rcPrFilterAceEthShowVlanIdOperMask      Integer32,
        rcPrFilterAceEthShowVlanId              INTEGER
        }

rcPrFilterAceEthShowAclId OBJECT-TYPE
     SYNTAX             INTEGER (1..4096)
     MAX-ACCESS         not-accessible
     STATUS             current
     DESCRIPTION        "An index to the AceEthernetEntry, a unique
	                identifier for Acl entry in the range of Table
			Size."
     ::= { rcPrFilterAceEthShowEntry 1 }

rcPrFilterAceEthShowAceId OBJECT-TYPE
     SYNTAX             INTEGER (1..2000)
     MAX-ACCESS         not-accessible
     STATUS             current
     DESCRIPTION        "An index to the AceEthernetEntry, a unique
	                identifier for Acl entry in the range of Table
			Size."
     ::= { rcPrFilterAceEthShowEntry 2 }

rcPrFilterAceEthShowSrcAddrList OBJECT-TYPE
     SYNTAX             OCTET STRING (SIZE(0..1500))
     MAX-ACCESS         read-only
     STATUS             current
     DESCRIPTION        "The list of ethernet source address to match."
     ::= { rcPrFilterAceEthShowEntry 3 }

rcPrFilterAceEthShowSrcAddrOper OBJECT-TYPE
     SYNTAX             INTEGER {
                            eq(1),    -- exact match
                            ne(2),    -- not equal
                            le(3),    -- less than or equal to
                            ge(4),    -- greater than or equal to
                          mask(8),    -- mask
               notConfigured(254),    -- not provisioned
                         any(255)     -- not provisioned
                   }
     MAX-ACCESS         read-only
     STATUS             current
     DESCRIPTION        "Operators for Ace Ethernet Source MAC Address."
     ::= { rcPrFilterAceEthShowEntry 4 }

rcPrFilterAceEthShowDstAddrList OBJECT-TYPE
     SYNTAX             OCTET STRING (SIZE(0..1500))
     MAX-ACCESS         read-only
     STATUS             current
     DESCRIPTION        "List of ethernet destination address to
			match."
     ::= { rcPrFilterAceEthShowEntry 5 }

rcPrFilterAceEthShowDstAddrOper OBJECT-TYPE
     SYNTAX             INTEGER {
                            eq(1),    -- exact match
                            ne(2),    -- not equal
                            le(3),    -- less than or equal to
                            ge(4),    -- greater than or equal to
                          mask(8),    -- mask
               notConfigured(254),    -- not provisioned
                           any(255)   -- not provisioned
                        }
     MAX-ACCESS         read-only
     STATUS             current
     DESCRIPTION        "Operators for Ace Ethernet Destination MAC Address."
     ::= { rcPrFilterAceEthShowEntry 6 }

rcPrFilterAceEthShowEtherTypeList OBJECT-TYPE
     SYNTAX             OCTET STRING (SIZE(0..1500))
     MAX-ACCESS         read-only
     STATUS             current
     DESCRIPTION        "EtherType value from ethernet header.  For example ARP
                         uses  0x0806, IP uses 0x0800. The platform support
                         determines the behavior for 802.1Q/p tagged packets.
                         The EtherType for 802.1Q tagged frames is 0x8100.

                         Valid range for the 16-bit Ether-type is 0..65535
			 and the attribute supports lists/ranges of values.
                         Invalid ether-type value 65536 is interpreted as
                         field is not desired in match criteria."
 	::= { rcPrFilterAceEthShowEntry 7 }

rcPrFilterAceEthShowEtherTypeOper OBJECT-TYPE
     SYNTAX             INTEGER {
                            eq(1),   -- exact match
                            ne(2),   -- not equal
               notConfigured(254),   -- not provisioned
                          any(255)   -- not provisioned
                        }
     MAX-ACCESS         read-only
     STATUS             current
     DESCRIPTION        "Ethernet Type Operators."
     ::= { rcPrFilterAceEthShowEntry 8 }

rcPrFilterAceEthShowVlanTagPrio  OBJECT-TYPE
     SYNTAX             INTEGER {
                            zero(0),
                            one(1),
                            two(2),
                            three(3),
                            four(4),
                            five(5),
                            six(6),
                            seven(7),
                            notConfigured(254)
                        }
     MAX-ACCESS         read-only
     STATUS             current
     DESCRIPTION        "Priority bits (3-bit field) from the 802.1Q/p tag."
     ::= { rcPrFilterAceEthShowEntry 9 }

rcPrFilterAceEthShowVlanTagPrioOper OBJECT-TYPE
     SYNTAX             INTEGER {
                            eq(1),   -- exact match
                            ne(2),   -- not equal
                          mask(8),   -- mask
               notConfigured(254),   -- not provisioned
                          any(255)   -- not provisioned
                        }
     MAX-ACCESS         read-only
     STATUS             current
     DESCRIPTION        "Operators for Ace Ethernet Vlan Tag Priority."
     ::= { rcPrFilterAceEthShowEntry 10 }

rcPrFilterAceEthShowPort OBJECT-TYPE
     SYNTAX             PortSet
     MAX-ACCESS         read-only
     STATUS             current
     DESCRIPTION        "Port Number or Port List to match on."
     ::= { rcPrFilterAceEthShowEntry 11 }

rcPrFilterAceEthShowPortOper OBJECT-TYPE
     SYNTAX             INTEGER {
                            eq(1),  -- exact match
	                    ne(2),  -- not equal
               notConfigured(254),  -- not provisioned
                          any(255)  -- not provisioned
                        }
     MAX-ACCESS         read-only
     STATUS             current
     DESCRIPTION        "Operator for Ace Ethernet Port."
     ::= { rcPrFilterAceEthShowEntry 12 }

rcPrFilterAceEthShowVlanIdList OBJECT-TYPE
     SYNTAX             IdList(SIZE(4096))
     MAX-ACCESS         read-only
     STATUS             current
     DESCRIPTION        "Vlan Id to match on."
     ::= { rcPrFilterAceEthShowEntry 13 }

rcPrFilterAceEthShowVlanIdOper OBJECT-TYPE
     SYNTAX             INTEGER {
                            eq(1),  -- exact match
                            ne(2),  -- not equal
                          mask(8),  -- mask
               notConfigured(254),  -- not provisioned
                           any(255) -- not provisioned
                        }
     MAX-ACCESS         read-only
     STATUS             current
     DESCRIPTION        "Operator for Ace Ethernet VlanId."
     ::= { rcPrFilterAceEthShowEntry 14 }

rcPrFilterAceEthShowSrcAddrOperMask OBJECT-TYPE
     SYNTAX             DisplayString (SIZE(0..14))
     MAX-ACCESS         read-only
     STATUS             current
     DESCRIPTION        "The mask value in hex which can be set for the
                        rcPrFilterAceEthSrcAddrOper when the option
                        selected is mask. It will be empty or
                        set to 000000000000 whenrcPrFilterAceEthSrcAddrOper
                        is set to 'eq'. In case of the prefix '0x' is
                        specified, 14 charaters is max length"
     ::= { rcPrFilterAceEthShowEntry 15 }

rcPrFilterAceEthShowDstAddrOperMask OBJECT-TYPE
     SYNTAX             DisplayString (SIZE(0..14))
     MAX-ACCESS         read-only
     STATUS             current
     DESCRIPTION        "The mask value in hex which can be set for the
                        rcPrFilterAceEthDstAddrOper when the option
                        selected is mask. It will be empty or
                        set to 000000000000 whenrcPrFilterAceEthDstAddrOper
                        is set to 'eq'. In case of the prefix '0x' is
                        specified, 14 charaters is max length"
     ::= { rcPrFilterAceEthShowEntry 16 }

rcPrFilterAceEthShowVlanTagPrioOperMask OBJECT-TYPE
     SYNTAX             Integer32 (0..'7'h)
     MAX-ACCESS         read-only
     STATUS             current
     DESCRIPTION        "The mask value in hex which can be set for the
                        rcPrFilterAceEthVlanTagPrioOper when the option
                        selected is masked. This object is applicable for
                        VSP9000. Not for ERS8600"
     ::= { rcPrFilterAceEthShowEntry 17 }

rcPrFilterAceEthShowVlanIdOperMask OBJECT-TYPE
     SYNTAX             Integer32(0..'FFF'h)
     MAX-ACCESS         read-only
     STATUS             current
     DESCRIPTION        "The mask value in hex which can be set for the
                        rcPrFilterAceEthVlanIdOper when the option
                        selected is mask. This object is used with
                        rcPrFilterAceEthVlanIdVlanId in VSP 9000 to
                        replace rcPrFilterAceEthVlanIdVlanIdList "
     ::= { rcPrFilterAceEthShowEntry 18 }

rcPrFilterAceEthShowVlanId OBJECT-TYPE
     SYNTAX             INTEGER (0..4084)
     MAX-ACCESS         read-only
     STATUS             current
     DESCRIPTION        "Vlan Id to match on. VSP9000  use this object with
                        object rcPrFilterAceEthVlanIdOperMask to replace the
                        rcPrFilterAceEthVlanIdVlanIdList"
     ::= { rcPrFilterAceEthShowEntry 19 }

-- ACE IP Show Table

rcPrFilterAceIpShowTable OBJECT-TYPE
     SYNTAX             SEQUENCE OF RcPrFilterAceIpShowEntry
     MAX-ACCESS         not-accessible
     STATUS             current
     DESCRIPTION        "A table of Aces to store IP Header
                        information of each Ace in context of
                        its parent Acl. "
     ::= { rcPrFilterAce 26 }

rcPrFilterAceIpShowEntry OBJECT-TYPE
     SYNTAX             RcPrFilterAceIpShowEntry
     MAX-ACCESS         not-accessible
     STATUS             current
     DESCRIPTION        "One Ace entry holding Ace IP information.
                         Ace is a member of one Acl."
     INDEX              { rcPrFilterAceIpShowAclId,
                          rcPrFilterAceIpShowAceId }
     ::= { rcPrFilterAceIpShowTable 1 }

RcPrFilterAceIpShowEntry ::= SEQUENCE {
        rcPrFilterAceIpShowAclId	     	INTEGER,
        rcPrFilterAceIpShowAceId	     	INTEGER,
        rcPrFilterAceIpShowSrcAddrList      	OCTET STRING,
        rcPrFilterAceIpShowSrcAddrOper 		INTEGER,
        rcPrFilterAceIpShowDstAddrList      	OCTET STRING,
        rcPrFilterAceIpShowDstAddrOper      	INTEGER,
        rcPrFilterAceIpShowDscpList         	OCTET STRING,
        rcPrFilterAceIpShowDscpOper         	INTEGER,
        rcPrFilterAceIpShowProtoList        	OCTET STRING,
        rcPrFilterAceIpShowProtoOper        	INTEGER,
	rcPrFilterAceIpShowOptions	     	INTEGER,
        rcPrFilterAceIpShowOptionsOper      	INTEGER,
        rcPrFilterAceIpShowFragmentation    	INTEGER,
        rcPrFilterAceIpShowFragOper         	INTEGER,
        rcPrFilterAceIpShowSrcAddrIpAddr        IpAddress,
        rcPrFilterAceIpShowSrcAddrOperMaskRange IpAddress,
        rcPrFilterAceIpShowDstAddrIpAddr        IpAddress,
        rcPrFilterAceIpShowDstAddrOperMaskRange IpAddress,
        rcPrFilterAceIpShowDscpOperMask         Integer32,
	rcPrFilterAceIpShowRoutedOnly           TruthValue
        }

rcPrFilterAceIpShowAclId OBJECT-TYPE
     SYNTAX             INTEGER (1..4096)
     MAX-ACCESS         not-accessible
     STATUS             current
     DESCRIPTION        "An index to the AceIpShowEntry, a unique
	                identifier for Acl entry in the range of Table
			Size."
     ::= { rcPrFilterAceIpShowEntry 1 }

rcPrFilterAceIpShowAceId OBJECT-TYPE
     SYNTAX             INTEGER (1..2000)
     MAX-ACCESS         not-accessible
     STATUS             current
     DESCRIPTION        "An index to the AceIpShowEntry, a unique
	                identifier for Acl entry in the range of Table
			Size."
     ::= { rcPrFilterAceIpShowEntry 2 }

rcPrFilterAceIpShowSrcAddrList OBJECT-TYPE
     SYNTAX             OCTET STRING (SIZE(0..1500))
     MAX-ACCESS         read-only
     STATUS             current
     DESCRIPTION        "The list of ip source address to match from IP
			header."
     ::= { rcPrFilterAceIpShowEntry 3 }

rcPrFilterAceIpShowSrcAddrOper OBJECT-TYPE
     SYNTAX             INTEGER {
                            eq(1),    -- exact match
                            ne(2),    -- not equal
                            le(3),    -- less than or equal to
                            ge(4),     -- greater than or equal to
                            prefix(8),  -- prefix list
                            mask(9),            -- mask
                            range(10),          -- range
                            notConfigured(254), -- not provisioned
                            any(255)   -- not provisioned
                        }
     MAX-ACCESS         read-only
     STATUS             current
     DESCRIPTION        "Operators for Ace Ip Source Address."
     ::= { rcPrFilterAceIpShowEntry 4 }

rcPrFilterAceIpShowDstAddrList OBJECT-TYPE
     SYNTAX             OCTET STRING (SIZE(0..1500))
     MAX-ACCESS         read-only
     STATUS             current
     DESCRIPTION        "The list of ip dst address to match from IP header."
     ::= { rcPrFilterAceIpShowEntry 5 }

rcPrFilterAceIpShowDstAddrOper OBJECT-TYPE
     SYNTAX             INTEGER {
                            eq(1),    -- exact match
                            ne(2),    -- not equal
                            le(3),    -- less than or equal to
                            ge(4),    -- greater than or equal to
                            prefix(8), -- prefix list
                            mask(9),            -- mask
                            range(10),          -- range
                            notConfigured(254), -- not provisioned
                            any(255)   -- not provisioned
                        }
     MAX-ACCESS         read-only
     STATUS             current
     DESCRIPTION        "Operators for Ace Ip Destination Address."
     ::= { rcPrFilterAceIpShowEntry 6 }

rcPrFilterAceIpShowDscpList  OBJECT-TYPE
     SYNTAX             OCTET STRING (SIZE(0..1500))
     MAX-ACCESS         read-only
     STATUS             current
     DESCRIPTION        "The 6-bit DSCP field from the ToS byte in Ipv4 header
                        encodes the PHB information per DiffServ standards
                        (Refer to DiffServ RFCs 2474). Set the Dscp to PHB
                        (like EF) or PHB-class(like AF1 which includes AF11,
                        AF12,AF13) to match specific diffserv class traffic.
                        Set the field value to desired dscp code for
                        'rcPrFilterAceIpDscp' field to match non-standard
                        traffic classes and local use PHBs."
     DEFVAL             { "disable" }
     ::= { rcPrFilterAceIpShowEntry 7 }

rcPrFilterAceIpShowDscpOper OBJECT-TYPE
     SYNTAX             INTEGER {
                            eq(1),    -- exact match
                            ne(2),     -- not equal
                            mask(8),            -- mask
                            notConfigured(254), -- not provisioned
                            any(255)   -- not provisioned
                        }
     MAX-ACCESS         read-only
     STATUS             current
     DESCRIPTION        "Operators for Ace Ip Dscp."
     ::= { rcPrFilterAceIpShowEntry 8 }

rcPrFilterAceIpShowProtoList OBJECT-TYPE
     SYNTAX             OCTET STRING (SIZE(0..1500))
     MAX-ACCESS         read-only
     STATUS             current
     DESCRIPTION        "Ip protocol Type from the ip header to be matched.
                        Valid Ip protocol range is 0..255. Few of the Protocol
                        Types are enumerated above. In case the desired
                        protocol number is not available in the enumerated
                        list set protocol to desired integer value"
     ::= { rcPrFilterAceIpShowEntry 9 }

rcPrFilterAceIpShowProtoOper OBJECT-TYPE
     SYNTAX             INTEGER {
                            eq(1),    -- exact match
                            ne(2),     -- not equal
                            notConfigured(254),  -- not provisioned
                            any(255)   -- not provisioned
                        }
     MAX-ACCESS         read-only
     STATUS             current
     DESCRIPTION        "Operators for Ace Ip Protocols."
     ::= { rcPrFilterAceIpShowEntry 10 }

rcPrFilterAceIpShowOptions  OBJECT-TYPE
     SYNTAX             INTEGER {
			    noOperation(1),
			    recordRoute(7),
			    experimentalMeasurement(10),
 			    mtuProbe(11),
			    mtuReply(12),
			    encode(15),
			    timestamp(68),
			    traceroute(82),
			    baseSecurity(130),
			    looseSourceRoute(131),
			    extendedSecurity(133),
			    commercialSecurity(134),
			    streamID(136),
			    strictSourceRouting(137),
			    experimentalAccessControl(142),
			    imiTrafficDescriptor(144),
			    extendedIP(145),
			    addressExtension(147),
			    routeAlert(148),
			    selectiveDirectedBroadcast(149),
			    nsapAddresses(150),
			    dynamicPacketState(151),
			    upstreamMulticastPacket(152),
			    experimentalFlowControl(205)
			}

     MAX-ACCESS         read-only
     STATUS             current
     DESCRIPTION        "Ip options to be matched from the IP Header."
     ::= { rcPrFilterAceIpShowEntry 11 }

rcPrFilterAceIpShowOptionsOper OBJECT-TYPE
     SYNTAX             INTEGER {
                            any(5),
                            notConfigured(254) -- not provisioned
			}
     MAX-ACCESS         read-only
     STATUS             current
     DESCRIPTION        "Logical Operator - only 'any' is valid at present."
     DEFVAL		{ any }
     ::= { rcPrFilterAceIpShowEntry 12 }

rcPrFilterAceIpShowFragmentation OBJECT-TYPE
     SYNTAX             INTEGER {
                            noFragment(0),
                            anyFragment(1),
                            moreFragment(2),
                            unused3(3),
                            lastFragment(4),
                            unused5(5),
                            unused6(6),
                            unused7(7),
                            notConfigured(254)
                        }
     MAX-ACCESS         read-only
     STATUS             current
     DESCRIPTION        "Ip Fragmentation bits to be matched from the IP
                        Header."
     DEFVAL      { noFragment }
     ::= { rcPrFilterAceIpShowEntry 13 }

rcPrFilterAceIpShowFragOper OBJECT-TYPE
     SYNTAX             INTEGER {
                            eq(1),    -- exact match
                            notConfigured(254), -- not provisioned
                            any(255)   -- not provisioned
                        }
     MAX-ACCESS         read-only
     STATUS             current
     DESCRIPTION        "Operator for Ip fragmentation."
     ::= { rcPrFilterAceIpShowEntry 14 }

rcPrFilterAceIpShowSrcAddrIpAddr OBJECT-TYPE
     SYNTAX             IpAddress
     MAX-ACCESS         read-only
     STATUS             current
     DESCRIPTION        "IP Source Address to match from IP header.
                        This object is defined and used  to replace
                        the rcPrFilterAceIpSrcAddrList by VSP 9000"
     ::= { rcPrFilterAceIpShowEntry 15 }

rcPrFilterAceIpShowSrcAddrOperMaskRange OBJECT-TYPE
     SYNTAX             IpAddress
     MAX-ACCESS         read-only
     STATUS             current
     DESCRIPTION        "The IP Mask value or High IP address based on
                        object rcPrFilterAceIpSrcAddrOper mask/range
                        option is selected."
     ::= { rcPrFilterAceIpShowEntry 16 }

rcPrFilterAceIpShowDstAddrIpAddr OBJECT-TYPE
     SYNTAX             IpAddress
     MAX-ACCESS         read-only
     STATUS             current
     DESCRIPTION        "IP Source Address to match from IP header.
                         This object is defined and used  to replace
                         the rcPrFilterAceIpSrcAddrList by VSP 9000"
     ::= { rcPrFilterAceIpShowEntry 17 }

rcPrFilterAceIpShowDstAddrOperMaskRange OBJECT-TYPE
     SYNTAX             IpAddress
     MAX-ACCESS         read-only
     STATUS             current
     DESCRIPTION        "The IP mask value or Hi Ip address based on
                        object rcPrFilterAceIpDstAddrOper mask/range
                        option is selected."
     ::= { rcPrFilterAceIpShowEntry 18 }

rcPrFilterAceIpShowDscpOperMask OBJECT-TYPE
     SYNTAX             Integer32(0..'40'h)
     MAX-ACCESS         read-only
     STATUS             current
     DESCRIPTION        "The mask value in hex which can be set for the
                        rcPrFilterAceIpDscpOper when the option
                        selected is mask. It will be set to 0 or be used
                        when rcPrFilterAceIpDscpOper is set ro eq"
     ::= { rcPrFilterAceIpShowEntry 19 }

rcPrFilterAceIpShowRoutedOnly OBJECT-TYPE
     SYNTAX             TruthValue
     MAX-ACCESS         read-only
     STATUS             current
     DESCRIPTION        "Display the IP routed only bit."
     ::= { rcPrFilterAceIpShowEntry 20 }


-- ACE Proto Show Table

rcPrFilterAceProtoShowTable OBJECT-TYPE
     SYNTAX             SEQUENCE OF RcPrFilterAceProtoShowEntry
     MAX-ACCESS         not-accessible
     STATUS             current
     DESCRIPTION        "A table of Aces to store Protocol Header
                        information of each Ace in context of
                        its parent Acl. "
     ::= { rcPrFilterAce 27 }

rcPrFilterAceProtoShowEntry OBJECT-TYPE
     SYNTAX             RcPrFilterAceProtoShowEntry
     MAX-ACCESS         not-accessible
     STATUS             current
     DESCRIPTION        "One Ace entry holding Ace Ethernet information.
                         Ace is a member of one Acl."
     INDEX              { rcPrFilterAceProtoShowAclId,
                          rcPrFilterAceProtoShowAceId}
     ::= { rcPrFilterAceProtoShowTable 1 }

RcPrFilterAceProtoShowEntry ::= SEQUENCE {
        rcPrFilterAceProtoShowAclId     	INTEGER,
        rcPrFilterAceProtoShowAceId     	INTEGER,
        rcPrFilterAceProtoShowTcpSrcPort      	OCTET STRING,
        rcPrFilterAceProtoShowTcpSrcPortOper   	INTEGER,
        rcPrFilterAceProtoShowUdpSrcPort     	OCTET STRING,
        rcPrFilterAceProtoShowUdpSrcPortOper   	INTEGER,
        rcPrFilterAceProtoShowTcpDstPort      	OCTET STRING,
        rcPrFilterAceProtoShowTcpDstPortOper 	INTEGER,
        rcPrFilterAceProtoShowUdpDstPort     	OCTET STRING,
        rcPrFilterAceProtoShowUdpDstPortOper   	INTEGER,
        rcPrFilterAceProtoShowIcmpMsgTypeList  	OCTET STRING,
        rcPrFilterAceProtoShowIcmpMsgTypeOper  	INTEGER,
        rcPrFilterAceProtoShowTcpFlagsList     	OCTET STRING,
        rcPrFilterAceProtoShowTcpFlagsOper	INTEGER,
        rcPrFilterAceProtoShowSrcPort           OCTET STRING,
        rcPrFilterAceProtoShowSrcPortOper       INTEGER,
        rcPrFilterAceProtoShowSrcPortOperMaskRange Integer32,
        rcPrFilterAceProtoShowDstPort           OCTET STRING,
        rcPrFilterAceProtoShowDstPortOper       INTEGER,
        rcPrFilterAceProtoShowDstPortOperMaskRange Integer32,
        rcPrFilterAceProtoShowTcpFlagsOperMask  Integer32,
	rcPrFilterAceProtoShowRoutingTypeType   Integer32,
        rcPrFilterAceProtoShowRoutingTypeOper   INTEGER,
        rcPrFilterAceProtoShowIcmpv6MsgTypeList OCTET STRING,
        rcPrFilterAceProtoShowIcmpv6MsgTypeOper INTEGER
        }

rcPrFilterAceProtoShowAclId OBJECT-TYPE
     SYNTAX             INTEGER (1..4096)
     MAX-ACCESS         not-accessible
     STATUS             current
     DESCRIPTION        "An index to the AceProtoShowEntry, a unique
	                identifier for Acl entry in the range of Table
			Size."
     ::= { rcPrFilterAceProtoShowEntry 1 }

rcPrFilterAceProtoShowAceId OBJECT-TYPE
     SYNTAX             INTEGER (1..2000)
     MAX-ACCESS         not-accessible
     STATUS             current
     DESCRIPTION        "An index to the AceProtoShowEntry, a unique
	                identifier for Ace entry in the range of Table
			Size."
     ::= { rcPrFilterAceProtoShowEntry 2 }

rcPrFilterAceProtoShowTcpSrcPort OBJECT-TYPE
     SYNTAX             OCTET STRING (SIZE(0..1500))
     MAX-ACCESS         read-only
     STATUS             current
     DESCRIPTION        "Port Number or Port List to match on."
     ::= { rcPrFilterAceProtoShowEntry 3 }

rcPrFilterAceProtoShowTcpSrcPortOper OBJECT-TYPE
     SYNTAX             INTEGER {
                            eq(1),   -- exact match
	                    ne(2),    -- not equal
                            le(3),    -- less than or equal to
                            ge(4),     -- greater than or equal to
                           any(255)   -- not provisioned
                        }
     MAX-ACCESS         read-only
     STATUS             current
     DESCRIPTION        "Operator for Ace Protocol TcpSrcPort."
     ::= { rcPrFilterAceProtoShowEntry 4 }

rcPrFilterAceProtoShowUdpSrcPort OBJECT-TYPE
     SYNTAX             OCTET STRING (SIZE(0..1500))
     MAX-ACCESS         read-only
     STATUS             current
     DESCRIPTION        "Port Number or Port List to match on."
     ::= { rcPrFilterAceProtoShowEntry 5 }

rcPrFilterAceProtoShowUdpSrcPortOper OBJECT-TYPE
     SYNTAX             INTEGER {
                            eq(1),   -- exact match
	                    ne(2),    -- not equal
                            le(3),    -- less than or equal to
                            ge(4),     -- greater than or equal to
                           any(255)   -- not provisioned
                        }
     MAX-ACCESS         read-only
     STATUS             current
     DESCRIPTION        "Operator for Ace Protocol UdpSrcPort."
     ::= { rcPrFilterAceProtoShowEntry 6 }

rcPrFilterAceProtoShowTcpDstPort OBJECT-TYPE
     SYNTAX             OCTET STRING (SIZE(0..1500))
     MAX-ACCESS         read-only
     STATUS             current
     DESCRIPTION        "Port Number or Port List to match on."
     ::= { rcPrFilterAceProtoShowEntry 7 }

rcPrFilterAceProtoShowTcpDstPortOper OBJECT-TYPE
     SYNTAX             INTEGER {
                            eq(1),   -- exact match
	       	            ne(2),    -- not equal
                            le(3),    -- less than or equal to
                            ge(4),     -- greater than or equal to
                           any(255)   -- not provisioned
                        }
     MAX-ACCESS         read-only
     STATUS             current
     DESCRIPTION        "Operator for Ace Protocol TcpDstPort."
     ::= { rcPrFilterAceProtoShowEntry 8 }

rcPrFilterAceProtoShowUdpDstPort OBJECT-TYPE
     SYNTAX             OCTET STRING (SIZE(0..1500))
     MAX-ACCESS         read-only
     STATUS             current
     DESCRIPTION        "Port Number or Port List to match on."
     ::= { rcPrFilterAceProtoShowEntry 9 }

rcPrFilterAceProtoShowUdpDstPortOper OBJECT-TYPE
     SYNTAX             INTEGER {
                            eq(1),   -- exact match
	                    ne(2),   -- not equal
                            le(3),    -- less than or equal to
                            ge(4),     -- greater than or equal to
                           any(255)   -- not provisioned
                        }
     MAX-ACCESS         read-only
     STATUS             current
     DESCRIPTION        "Operator for Ace Protocol UdpDstPort."
     ::= { rcPrFilterAceProtoShowEntry 10 }

rcPrFilterAceProtoShowIcmpMsgTypeList OBJECT-TYPE
     SYNTAX             OCTET STRING (SIZE(0..1500))
     MAX-ACCESS         read-only
     STATUS             current
     DESCRIPTION        "One or a list of Icmp messages to be matched.
			Need to provide strings, number of protocol header
			types (pre-defined values plus user-defined headers).
			Valid range is 0 to 255 (reserved)."
     ::= { rcPrFilterAceProtoShowEntry 11 }

rcPrFilterAceProtoShowIcmpMsgTypeOper OBJECT-TYPE
     SYNTAX             INTEGER {
                            eq(1),   -- exact match
	                    ne(2),    -- not equal
                            notConfigured(254), -- not provisioned
                           any(255)   -- not provisioned
                        }
     MAX-ACCESS         read-only
     STATUS             current
     DESCRIPTION        "Operator for Ace Protocol IcmpMsgTypes."
     ::= { rcPrFilterAceProtoShowEntry 12 }

rcPrFilterAceProtoShowTcpFlagsList OBJECT-TYPE
     SYNTAX             OCTET STRING (SIZE(0..1500))
     MAX-ACCESS         read-only
     STATUS             current
     DESCRIPTION        "One or a list of Tcp flags to be matched.
			Need to provide strings, number of protocol header
			types (pre-defined values plus user-defined headers).
			Valid range is 0 to 63"
     ::= { rcPrFilterAceProtoShowEntry 13 }

rcPrFilterAceProtoShowTcpFlagsOper OBJECT-TYPE
     SYNTAX             INTEGER {
                            eq(1),
			    matchAny(6),
			    matchAll(7),
                            mask(8),
                            notConfigured(254), -- not provisioned
			    any(255)  -- not provisioned
                        }
     MAX-ACCESS         read-only
     STATUS             current
     DESCRIPTION        "Operator for Ace Protocol TcpFlags."
     ::= { rcPrFilterAceProtoShowEntry 14 }

rcPrFilterAceProtoShowSrcPort OBJECT-TYPE
     SYNTAX             OCTET STRING (SIZE(0..1500))
     MAX-ACCESS         read-only
     STATUS             current
     DESCRIPTION        "Port Number or Port List to match on."
     ::= { rcPrFilterAceProtoShowEntry 15 }

rcPrFilterAceProtoShowSrcPortOper OBJECT-TYPE
     SYNTAX             INTEGER {
                            eq(1),   -- exact match
                            mask(8),
                            range(9),
                            notConfigured(254)
                        }
     MAX-ACCESS         read-only
     STATUS             current
     DESCRIPTION        "Operator for Ace Protocol SrcPort."
     ::= { rcPrFilterAceProtoShowEntry 16 }

rcPrFilterAceProtoShowSrcPortOperMaskRange OBJECT-TYPE
     SYNTAX             Integer32(0..'FFFF'h)
     MAX-ACCESS         read-only
     STATUS             current
     DESCRIPTION        "The value should be displayed in hex when
                        rcPrFilterAceProtoSrcPortOper is set to 'mask'.
                        This object will be used as a Range high value when
                        rcPrFilterAceProtoSrcPortOper is set to 'range'.
                        ('range' is not supported in this 3.0 release).
                        If it is used as range high value, it should be
                        displayed in decimal formtat.
                        This object will be set to 0 when
                        rcPrFilterAceProtoSrcPortOper is set to 'eq'"
     ::= { rcPrFilterAceProtoShowEntry 17 }

rcPrFilterAceProtoShowDstPort OBJECT-TYPE
     SYNTAX             OCTET STRING (SIZE(0..1500))
     MAX-ACCESS         read-only
     STATUS             current
     DESCRIPTION        "Port Number or Port List to match on."
     ::= { rcPrFilterAceProtoShowEntry 18 }

rcPrFilterAceProtoShowDstPortOper OBJECT-TYPE
     SYNTAX             INTEGER {
                            eq(1),   -- exact match
                            mask(8),
                            range(9),
                            notConfigured(254)
                        }
     MAX-ACCESS         read-only
     STATUS             current
     DESCRIPTION        "Operator for Ace Protocol DstPort."
     ::= { rcPrFilterAceProtoShowEntry 19 }

rcPrFilterAceProtoShowDstPortOperMaskRange OBJECT-TYPE
     SYNTAX             Integer32(0..'FFFF'h)
     MAX-ACCESS         read-only
     STATUS             current
     DESCRIPTION        "The value should be displayed in hex when
                        rcPrFilterAceProtoDstPortOper is set to 'mask'.
                        This object will be used as a Range high value when
                        rcPrFilterAceProtoDstPortOper is set to 'range'.
                        ('range' is not supported in this 3.0 release).
                        If it is used as range high value, it should be
                        displayed in decimal formtat.
                        This object will be set to 0 when
                        rcPrFilterAceProtoDstPortOper is set to 'eq'"
     ::= { rcPrFilterAceProtoShowEntry 20 }

rcPrFilterAceProtoShowTcpFlagsOperMask OBJECT-TYPE
     SYNTAX             Integer32(0..'3F'h)
     MAX-ACCESS         read-only
     STATUS             current
     DESCRIPTION        "The mask value in hex which can be set for the
                        rcPrFilterAceProtoTcpFlagsOper when the option
                        selected is mask. It will be set 0x0 when object
                        rcPrFilterAceProtoTcpFlagsOper is set to eq"
     ::= { rcPrFilterAceProtoShowEntry 21 }

rcPrFilterAceProtoShowRoutingTypeType OBJECT-TYPE
     SYNTAX             Integer32(0..2)
     MAX-ACCESS         read-only
     STATUS             current
     DESCRIPTION        "Value of Protocol routing-type."
     ::= { rcPrFilterAceProtoShowEntry 22 }

rcPrFilterAceProtoShowRoutingTypeOper OBJECT-TYPE
     SYNTAX             INTEGER {
                            eq(1),              -- exact match
			    ne(2),              -- not equal
                            notConfigured(254), -- not provisioned
                            any(255)            -- not provisioned
                        }
     MAX-ACCESS         read-only
     STATUS             current
     DESCRIPTION        "Operator for Ace Protocol RoutingType."
     ::= { rcPrFilterAceProtoShowEntry 23 }

rcPrFilterAceProtoShowIcmpv6MsgTypeList OBJECT-TYPE
     SYNTAX             OCTET STRING (SIZE(0..1500))
     MAX-ACCESS         read-only
     STATUS             current
     DESCRIPTION        "One or a list of ICMPv6 messages to be matched.
			Need to provide strings, number of protocol header
			types (pre-defined values plus user-defined headers).
			Valid range is 0 to 255 (reserved)."
     ::= { rcPrFilterAceProtoShowEntry 24 }

rcPrFilterAceProtoShowIcmpv6MsgTypeOper OBJECT-TYPE
     SYNTAX             INTEGER {
                            eq(1),              -- exact match
			    ne(2),              -- not equal
                            notConfigured(254), -- not provisioned
                            any(255)            -- not provisioned
                        }
     MAX-ACCESS         read-only
     STATUS             current
     DESCRIPTION        "Operator for Ace Protocol Icmpv6MsgTypes."
     ::= { rcPrFilterAceProtoShowEntry 25 }

-- ACE Pattern Show Table

rcPrFilterAcePatternShowTable OBJECT-TYPE
     SYNTAX             SEQUENCE OF RcPrFilterAcePatternShowEntry
     MAX-ACCESS         not-accessible
     STATUS             current
     DESCRIPTION        "A table of Aces to store Pattern 1, 2, 3
			Header information of each Ace in context of
                        its parent Acl. "
     ::= { rcPrFilterAce 28 }

rcPrFilterAcePatternShowEntry OBJECT-TYPE
     SYNTAX             RcPrFilterAcePatternShowEntry
     MAX-ACCESS         not-accessible
     STATUS             current
     DESCRIPTION        "One Ace entry holding Ace Pattern 1, 2, 3
			 information.  Ace is a member of one Acl."
     INDEX              { rcPrFilterAcePatternShowAclId,
                          rcPrFilterAcePatternShowAceId }
     ::= { rcPrFilterAcePatternShowTable 1 }

RcPrFilterAcePatternShowEntry ::= SEQUENCE {
        rcPrFilterAcePatternShowAclId		INTEGER,
        rcPrFilterAcePatternShowAceId		INTEGER,
        rcPrFilterAcePatternShowPattern1Name	DisplayString,
        rcPrFilterAcePatternShowPattern1Value  	OCTET STRING,
        rcPrFilterAcePatternShowPattern1Oper   	INTEGER,
        rcPrFilterAcePatternShowPattern2Name   	DisplayString,
        rcPrFilterAcePatternShowPattern2Value  	OCTET STRING,
        rcPrFilterAcePatternShowPattern2Oper   	INTEGER,
        rcPrFilterAcePatternShowPattern3Name   	DisplayString,
        rcPrFilterAcePatternShowPattern3Value  	OCTET STRING,
        rcPrFilterAcePatternShowPattern3Oper   	INTEGER
        }

rcPrFilterAcePatternShowAclId OBJECT-TYPE
     SYNTAX             INTEGER (1..4096)
     MAX-ACCESS         not-accessible
     STATUS             current
     DESCRIPTION        "An index to the AcePatternEntry, a unique
	                identifier for Acl entry in the range of Table
			Size."
     ::= { rcPrFilterAcePatternShowEntry 1 }

rcPrFilterAcePatternShowAceId OBJECT-TYPE
     SYNTAX             INTEGER (1..1000)
     MAX-ACCESS         not-accessible
     STATUS             current
     DESCRIPTION        "An index to the AcePatternEntry, a unique
	                identifier for Acl entry in the range of Table
			Size."
     ::= { rcPrFilterAcePatternShowEntry 2 }

rcPrFilterAcePatternShowPattern1Name OBJECT-TYPE
     SYNTAX             DisplayString (SIZE (0..32))
     MAX-ACCESS         read-only
     STATUS             current
     DESCRIPTION        "A descriptive name chosen by the administrator for
                        the Ace Pattern Entry."
     ::= { rcPrFilterAcePatternShowEntry 3 }

rcPrFilterAcePatternShowPattern1Value OBJECT-TYPE
     SYNTAX             OCTET STRING (SIZE (0..1500))
     MAX-ACCESS         read-only
     STATUS             current
     DESCRIPTION        "Set the pattern value as numeric string. The numeric
                        value of each byte is encoded in one octet of the
                        string. Unused bytes are left at the trailing end of
                        string. The number of bytes to extract from this string
                        is set in rcPrFilterActPatternLength."
     DEFVAL             { "" }
     ::= { rcPrFilterAcePatternShowEntry 4 }

rcPrFilterAcePatternShowPattern1Oper OBJECT-TYPE
     SYNTAX             INTEGER {
                            eq(1),    -- exact match
                            le(3),    -- less than or equal to
                            ge(4),     -- greater than or equal to
                            any(255)  -- not provisioned
                        }
     MAX-ACCESS         read-only
     STATUS             current
     DESCRIPTION        "Operators for Ace Pattern."
     ::= { rcPrFilterAcePatternShowEntry 5 }

rcPrFilterAcePatternShowPattern2Name OBJECT-TYPE
     SYNTAX             DisplayString (SIZE (0..32))
     MAX-ACCESS         read-only
     STATUS             current
     DESCRIPTION        "A descriptive name chosen by the administrator for
                        the Ace Pattern Entry."
     ::= { rcPrFilterAcePatternShowEntry 6 }

rcPrFilterAcePatternShowPattern2Value OBJECT-TYPE
     SYNTAX             OCTET STRING (SIZE (0..1500))
     MAX-ACCESS         read-only
     STATUS             current
     DESCRIPTION        "Set the pattern value as numeric string. The numeric
                        value of each byte is encoded in one octet of the
                        string. Unused bytes are left at the trailing end of
                        string. The number of bytes to extract from this string
                        is set in rcPrFilterActPatternLength."
     DEFVAL             { "" }
     ::= { rcPrFilterAcePatternShowEntry 7 }

rcPrFilterAcePatternShowPattern2Oper OBJECT-TYPE
     SYNTAX             INTEGER {
                            eq(1),    -- exact match
                            le(3),    -- less than or equal to
                            ge(4),     -- greater than or equal to
                            any(255)  -- not provisioned
                        }
     MAX-ACCESS         read-only
     STATUS             current
     DESCRIPTION        "Operators for Ace Pattern."
     ::= { rcPrFilterAcePatternShowEntry 8 }

rcPrFilterAcePatternShowPattern3Name OBJECT-TYPE
     SYNTAX             DisplayString (SIZE (0..32))
     MAX-ACCESS         read-only
     STATUS             current
     DESCRIPTION        "A descriptive name chosen by the administrator for
                        the Ace Pattern Entry."
     ::= { rcPrFilterAcePatternShowEntry 9 }

rcPrFilterAcePatternShowPattern3Value OBJECT-TYPE
     SYNTAX             OCTET STRING (SIZE (0..1500))
     MAX-ACCESS         read-only
     STATUS             current
     DESCRIPTION        "Set the pattern value as numeric string. The numeric
                        value of each byte is encoded in one octet of the
                        string. Unused bytes are left at the trailing end of
                        string. The number of bytes to extract from this string
                        is set in rcPrFilterActPatternLength."
     DEFVAL             { "" }
     ::= { rcPrFilterAcePatternShowEntry 10 }

rcPrFilterAcePatternShowPattern3Oper OBJECT-TYPE
     SYNTAX             INTEGER {
                            eq(1),    -- exact match
                            le(3),    -- less than or equal to
                            ge(4),     -- greater than or equal to
                            any(255)  -- not provisioned
                        }
     MAX-ACCESS         read-only
     STATUS             current
     DESCRIPTION        "Operators for Ace Pattern."
     ::= { rcPrFilterAcePatternShowEntry 11 }

rcPrFilterAceIpv6SrcAddrTable OBJECT-TYPE
     SYNTAX             SEQUENCE OF RcPrFilterAceIpv6SrcAddrEntry
     MAX-ACCESS         not-accessible
     STATUS             current
     DESCRIPTION        "A table of Aces to store IPv6 Source Address Header
                        information of each Ace in context of its parent Acl."
     ::= { rcPrFilterAce 29 }

rcPrFilterAceIpv6SrcAddrEntry OBJECT-TYPE
     SYNTAX             RcPrFilterAceIpv6SrcAddrEntry
     MAX-ACCESS         not-accessible
     STATUS             current
     DESCRIPTION        "One Ace entry holding Ace IPv6 Source Address Header
                        information. An Ace is a member of one Acl."
     INDEX              { rcPrFilterAceIpv6SrcAddrAclId,
                          rcPrFilterAceIpv6SrcAddrAceId }
     ::= { rcPrFilterAceIpv6SrcAddrTable 1 }

RcPrFilterAceIpv6SrcAddrEntry ::= SEQUENCE {
        rcPrFilterAceIpv6SrcAddrAclId          INTEGER,
        rcPrFilterAceIpv6SrcAddrAceId          INTEGER,
        rcPrFilterAceIpv6SrcAddrList           OCTET STRING,
        rcPrFilterAceIpv6SrcAddrListCount      INTEGER,
        rcPrFilterAceIpv6SrcAddrOper           INTEGER,
        rcPrFilterAceIpv6SrcAddrRowStatus      RowStatus,
        rcPrFilterAceIpv6SrcAddrOperMask       OCTET STRING
        }

rcPrFilterAceIpv6SrcAddrAclId OBJECT-TYPE
     SYNTAX             INTEGER (1..4096)
     MAX-ACCESS         not-accessible
     STATUS             current
     DESCRIPTION        "An index to the AceIpv6SrcAddrEntry, a unique
                        identifier for Acl entry in the range of Table
                        Size."
     ::= { rcPrFilterAceIpv6SrcAddrEntry 1 }

rcPrFilterAceIpv6SrcAddrAceId OBJECT-TYPE
     SYNTAX             INTEGER (1..2000)
     MAX-ACCESS         not-accessible
     STATUS             current
     DESCRIPTION        "An index to the AceIpv6SrcAddrEntry, a unique
                        identifier for Acl entry in the range of Table
                        Size."
     ::= { rcPrFilterAceIpv6SrcAddrEntry 2 }

rcPrFilterAceIpv6SrcAddrList OBJECT-TYPE
     SYNTAX             OCTET STRING (SIZE(0..1500))
     MAX-ACCESS         read-write
     STATUS             current
     DESCRIPTION        "The list of ipv6 source address to match from IPv6
                        header."
     ::= { rcPrFilterAceIpv6SrcAddrEntry 3 }

rcPrFilterAceIpv6SrcAddrListCount OBJECT-TYPE
     SYNTAX             INTEGER(1..100)
     MAX-ACCESS         read-write
     STATUS             current
     DESCRIPTION        "Count to store the number of discrete ranges
                        entered for the ipv6 src address. This object
			is not applicable to VSP9k"
     ::= { rcPrFilterAceIpv6SrcAddrEntry 4 }

rcPrFilterAceIpv6SrcAddrOper OBJECT-TYPE
     SYNTAX             INTEGER {
                            eq(1),    -- exact match
                            ne(2),    -- not equal
                            mask(3)
                        }
     MAX-ACCESS         read-write
     STATUS             current
     DESCRIPTION        "Operators for Ace Ipv6 Source Address."
     ::= { rcPrFilterAceIpv6SrcAddrEntry 5 }

rcPrFilterAceIpv6SrcAddrRowStatus OBJECT-TYPE
     SYNTAX             RowStatus
     MAX-ACCESS         read-create
     STATUS             current
     DESCRIPTION        "Create/delete operations for this entry."
     ::= { rcPrFilterAceIpv6SrcAddrEntry 6 }

rcPrFilterAceIpv6SrcAddrOperMask OBJECT-TYPE
     SYNTAX             OCTET STRING (SIZE(0..128))
     MAX-ACCESS         read-write
     STATUS             current
     DESCRIPTION        "The ipv6 mask value when
                         rcPrFilterAceIpv6SrcAddrOper mask is selected."
     ::= { rcPrFilterAceIpv6SrcAddrEntry 7 }

-- ACE Ipv6 Destination Address Table

rcPrFilterAceIpv6DstAddrTable OBJECT-TYPE
     SYNTAX             SEQUENCE OF RcPrFilterAceIpv6DstAddrEntry
     MAX-ACCESS         not-accessible
     STATUS             current
     DESCRIPTION        "A table of Aces to store IPv6 Destination Address
                        Header information of each Ace in context of its
                        parent Acl."
     ::= { rcPrFilterAce 30 }

rcPrFilterAceIpv6DstAddrEntry OBJECT-TYPE
     SYNTAX             RcPrFilterAceIpv6DstAddrEntry
     MAX-ACCESS         not-accessible
     STATUS             current
     DESCRIPTION        "One Ace entry holding Ace IPv6 Destination Address
                        Header information. An Ace is a member of one Acl."
     INDEX              { rcPrFilterAceIpv6DstAddrAclId,
                          rcPrFilterAceIpv6DstAddrAceId }
     ::= { rcPrFilterAceIpv6DstAddrTable 1 }

RcPrFilterAceIpv6DstAddrEntry ::= SEQUENCE {
        rcPrFilterAceIpv6DstAddrAclId          INTEGER,
        rcPrFilterAceIpv6DstAddrAceId          INTEGER,
        rcPrFilterAceIpv6DstAddrList           OCTET STRING,
        rcPrFilterAceIpv6DstAddrListCount      INTEGER,
        rcPrFilterAceIpv6DstAddrOper           INTEGER,
        rcPrFilterAceIpv6DstAddrRowStatus      RowStatus,
        rcPrFilterAceIpv6DstAddrOperMask       OCTET STRING
        }

rcPrFilterAceIpv6DstAddrAclId OBJECT-TYPE
     SYNTAX             INTEGER (1..4096)
     MAX-ACCESS         not-accessible
     STATUS             current
     DESCRIPTION        "An index to the AceIpv6DstAddrEntry, a unique
                        identifier for Acl entry in the range of Table
                        Size."
     ::= { rcPrFilterAceIpv6DstAddrEntry 1 }

rcPrFilterAceIpv6DstAddrAceId OBJECT-TYPE
     SYNTAX             INTEGER (1..2000)
     MAX-ACCESS         not-accessible
     STATUS             current
     DESCRIPTION        "An index to the AceIpv6DstAddrEntry, a unique
                        identifier for Acl entry in the range of Table
                        Size."
     ::= { rcPrFilterAceIpv6DstAddrEntry 2 }

rcPrFilterAceIpv6DstAddrList OBJECT-TYPE
     SYNTAX             OCTET STRING (SIZE(0..1500))
     MAX-ACCESS         read-write
     STATUS             current
     DESCRIPTION        "The list of ipv6 dst  address to match from IPv6 header."
     ::= { rcPrFilterAceIpv6DstAddrEntry 3 }

rcPrFilterAceIpv6DstAddrListCount OBJECT-TYPE
     SYNTAX             INTEGER(1..100)
     MAX-ACCESS         read-write
     STATUS             current
     DESCRIPTION        "Count to store the number of discrete ranges
                        entered for the IPv6 Destination Address. This
			object is not applicable to VSP9k"
     ::= { rcPrFilterAceIpv6DstAddrEntry 4 }

rcPrFilterAceIpv6DstAddrOper OBJECT-TYPE
     SYNTAX             INTEGER {
                            eq(1),    -- exact match
                            ne(2),    -- not equal
                            mask(3)
                        }
     MAX-ACCESS         read-write
     STATUS             current
     DESCRIPTION        "Operators for Ace IPv6 Destination Address."
     ::= { rcPrFilterAceIpv6DstAddrEntry 5 }

rcPrFilterAceIpv6DstAddrRowStatus OBJECT-TYPE
     SYNTAX             RowStatus
     MAX-ACCESS         read-create
     STATUS             current
     DESCRIPTION        "Create/delete operations for this entry."
     ::= { rcPrFilterAceIpv6DstAddrEntry 6 }

rcPrFilterAceIpv6DstAddrOperMask OBJECT-TYPE
     SYNTAX             OCTET STRING (SIZE(0..128))
     MAX-ACCESS         read-write
     STATUS             current
     DESCRIPTION        "The ipv6 mask value when
                         rcPrFilterAceIpv6DstAddrOper mask is selected."
     ::= { rcPrFilterAceIpv6DstAddrEntry 7 }


-- ACE Ipv6 Next header Table

rcPrFilterAceIpv6NextHdrTable OBJECT-TYPE
     SYNTAX             SEQUENCE OF RcPrFilterAceIpv6NextHdrEntry
     MAX-ACCESS         not-accessible
     STATUS             current
     DESCRIPTION        "A table of Aces to store IPv6 Next header
                        Header information of each Ace in context of its
                        parent Acl."
     ::= { rcPrFilterAce 31 }

rcPrFilterAceIpv6NextHdrEntry OBJECT-TYPE
     SYNTAX             RcPrFilterAceIpv6NextHdrEntry
     MAX-ACCESS         not-accessible
     STATUS             current
     DESCRIPTION        "One Ace entry holding Ace IPv6 Next header
                         information. An Ace is a member of one Acl."
     INDEX              { rcPrFilterAceIpv6NextHdrAclId,
                          rcPrFilterAceIpv6NextHdrAceId }
     ::= { rcPrFilterAceIpv6NextHdrTable 1 }

RcPrFilterAceIpv6NextHdrEntry ::= SEQUENCE {
        rcPrFilterAceIpv6NextHdrAclId          INTEGER,
        rcPrFilterAceIpv6NextHdrAceId          INTEGER,
        rcPrFilterAceIpv6NextHdrNextHdr        Ipv6NextHdr,
        rcPrFilterAceIpv6NextHdrOper           INTEGER,
        rcPrFilterAceIpv6NextHdrRowStatus      RowStatus
        }

rcPrFilterAceIpv6NextHdrAclId OBJECT-TYPE
     SYNTAX             INTEGER (1..4096)
     MAX-ACCESS         not-accessible
     STATUS             current
     DESCRIPTION        "An index to the AceIpv6NextHdrEntry, a unique
                        identifier for Acl entry in the range of Table
                        Size."
     ::= { rcPrFilterAceIpv6NextHdrEntry 1 }

rcPrFilterAceIpv6NextHdrAceId OBJECT-TYPE
     SYNTAX             INTEGER (1..2000)
     MAX-ACCESS         not-accessible
     STATUS             current
     DESCRIPTION        "An index to the AceIpv6NextHdrEntry, a unique
                        identifier for Acl entry in the range of Table
                        Size."
     ::= { rcPrFilterAceIpv6NextHdrEntry 2 }

rcPrFilterAceIpv6NextHdrNextHdr OBJECT-TYPE
     SYNTAX             Ipv6NextHdr
     MAX-ACCESS         read-write
     STATUS             current
     DESCRIPTION        "The ipv6 next header to look for.
"
     ::= { rcPrFilterAceIpv6NextHdrEntry 3 }

rcPrFilterAceIpv6NextHdrOper OBJECT-TYPE
     SYNTAX             INTEGER {
                            eq(1),    -- exact match
                            ne(2)    -- not equal
                        }
     MAX-ACCESS         read-write
     STATUS             current
     DESCRIPTION        "Operators for Ace IPv6 Next header."
     ::= { rcPrFilterAceIpv6NextHdrEntry 4 }

rcPrFilterAceIpv6NextHdrRowStatus OBJECT-TYPE
     SYNTAX             RowStatus
     MAX-ACCESS         read-create
     STATUS             current
     DESCRIPTION        "Create/delete operations for this entry."
     ::= { rcPrFilterAceIpv6NextHdrEntry 5 }

-- ACE IPv6 Show Table

rcPrFilterAceIpv6ShowTable OBJECT-TYPE
     SYNTAX             SEQUENCE OF RcPrFilterAceIpv6ShowEntry
     MAX-ACCESS         not-accessible
     STATUS             current
     DESCRIPTION        "A table of Aces to display ipv6
                        information of each Ace in context of
                        its parent Acl. "
     ::= { rcPrFilterAce 32 }

rcPrFilterAceIpv6ShowEntry OBJECT-TYPE
     SYNTAX             RcPrFilterAceIpv6ShowEntry
     MAX-ACCESS         not-accessible
     STATUS             current
     DESCRIPTION        "One Ace entry holding Ace ipv6 information.
                         Ace is a member of one Acl."
     INDEX              { rcPrFilterAceIpv6ShowAclId,
                          rcPrFilterAceIpv6ShowAceId}
     ::= { rcPrFilterAceIpv6ShowTable 1 }

RcPrFilterAceIpv6ShowEntry ::= SEQUENCE {
        rcPrFilterAceIpv6ShowAclId               INTEGER,
        rcPrFilterAceIpv6ShowAceId               INTEGER,
        rcPrFilterAceIpv6ShowSrcAddrList         OCTET STRING,
        rcPrFilterAceIpv6ShowSrcAddrOper         INTEGER,
        rcPrFilterAceIpv6ShowDstAddrList         OCTET STRING,
        rcPrFilterAceIpv6ShowDstAddrOper         INTEGER,
        rcPrFilterAceIpv6ShowNxtHdrNxtHdr        Ipv6NextHdr,
        rcPrFilterAceIpv6ShowNxtHdrOper          INTEGER,
        rcPrFilterAceIpv6ShowTrafficClsOper      INTEGER,
        rcPrFilterAceIpv6ShowTrafficCls          Integer32,
        rcPrFilterAceIpv6ShowSrcAddrMask         OCTET STRING,
        rcPrFilterAceIpv6ShowDstAddrMask         OCTET STRING,
        rcPrFilterAceIpv6ShowRoutedOnly          TruthValue
        }

rcPrFilterAceIpv6ShowAclId OBJECT-TYPE
     SYNTAX                INTEGER (1..4096)
     MAX-ACCESS            not-accessible
     STATUS                current
     DESCRIPTION           "An index to the AceIpv6Entry, a unique
                        identifier for Acl entry in the range of Table
                        Size."
     ::= { rcPrFilterAceIpv6ShowEntry 1 }

rcPrFilterAceIpv6ShowAceId OBJECT-TYPE
     SYNTAX                INTEGER (1..2000)
     MAX-ACCESS            not-accessible
     STATUS                current
     DESCRIPTION           "An index to the AceIpv6Entry, a unique
                        identifier for Acl entry in the range of Table
                        Size."
     ::= { rcPrFilterAceIpv6ShowEntry 2 }

rcPrFilterAceIpv6ShowSrcAddrList OBJECT-TYPE
     SYNTAX                      OCTET STRING (SIZE(0..1500))
     MAX-ACCESS                  read-only
     STATUS                      current
     DESCRIPTION                 "The list of v6 source address to display."
     ::= { rcPrFilterAceIpv6ShowEntry 3 }

rcPrFilterAceIpv6ShowSrcAddrOper OBJECT-TYPE
     SYNTAX                      INTEGER {
                                   eq(1),    -- exact match
                                   ne(2),    -- not equal
                                   mask(3),
                                   any(255)  -- not provisioned
                                 }
     MAX-ACCESS                  read-only
     STATUS                      current
     DESCRIPTION                 "Operators for Ace v6 Source Address."
     ::= { rcPrFilterAceIpv6ShowEntry 4 }

rcPrFilterAceIpv6ShowDstAddrList OBJECT-TYPE
     SYNTAX                      OCTET STRING (SIZE(0..1500))
     MAX-ACCESS                  read-only
     STATUS                      current
     DESCRIPTION                 "List of v6 destination address to display."
     ::= { rcPrFilterAceIpv6ShowEntry 5 }

rcPrFilterAceIpv6ShowDstAddrOper OBJECT-TYPE
     SYNTAX                      INTEGER {
                                  eq(1),    -- exact match
                                  ne(2),    -- not equal
                                  mask(3),
                                  any(255)  -- not provisioned
                                 }
     MAX-ACCESS                  read-only
     STATUS                      current
     DESCRIPTION                 "Operators for Ace v6 Destination Address."
     ::= { rcPrFilterAceIpv6ShowEntry 6 }

rcPrFilterAceIpv6ShowNxtHdrNxtHdr OBJECT-TYPE
     SYNTAX                       Ipv6NextHdr
     MAX-ACCESS                   read-only
     STATUS                       current
     DESCRIPTION                  "IPv6 next hdr to display in the context of the parent ACL."
     ::= { rcPrFilterAceIpv6ShowEntry 7 }

rcPrFilterAceIpv6ShowNxtHdrOper OBJECT-TYPE
     SYNTAX                     INTEGER {
                                 eq(1),  -- exact match
                                 ne(2),    -- not equal
                                 any(255)  -- not provisioned
                                }
     MAX-ACCESS                 read-only
     STATUS                     current
     DESCRIPTION                "Operator for Ace v6 next hdr."
     ::= { rcPrFilterAceIpv6ShowEntry 8 }

rcPrFilterAceIpv6ShowTrafficClsOper OBJECT-TYPE
     SYNTAX                     INTEGER {
                                 eq(1),  -- exact match
                                 any(255)  -- not provisioned
                                }
     MAX-ACCESS                 read-only
     STATUS                     current
     DESCRIPTION                "Operator for Ace v6 Traffic Class"
     ::= { rcPrFilterAceIpv6ShowEntry 9 }

rcPrFilterAceIpv6ShowTrafficCls OBJECT-TYPE
     SYNTAX                       Integer32
     MAX-ACCESS                   read-only
     STATUS                       current
     DESCRIPTION                  "ipv6 traffic class value to display."
     ::= { rcPrFilterAceIpv6ShowEntry 10 }

rcPrFilterAceIpv6ShowSrcAddrMask OBJECT-TYPE
     SYNTAX                      OCTET STRING (SIZE(0..128))
     MAX-ACCESS                  read-only
     STATUS                      current
     DESCRIPTION                 "ipv6 SrcAddr Mask value to display."
     ::= { rcPrFilterAceIpv6ShowEntry 11 }

rcPrFilterAceIpv6ShowDstAddrMask OBJECT-TYPE
     SYNTAX                      OCTET STRING (SIZE(0..128))
     MAX-ACCESS                  read-only
     STATUS                      current
     DESCRIPTION                 "ipv6 DstAddr Mask value to display."
     ::= { rcPrFilterAceIpv6ShowEntry 12 }

rcPrFilterAceIpv6ShowRoutedOnly OBJECT-TYPE
     SYNTAX                     TruthValue
     MAX-ACCESS                 read-only
     STATUS                     current
     DESCRIPTION                "Ipv6 routed only bit to display."
     ::= { rcPrFilterAceIpv6ShowEntry 13 }

-- ACE Protocol TCP/UDP Src Port Table

rcPrFilterAceProtoSrcPortTable OBJECT-TYPE
     SYNTAX             SEQUENCE OF RcPrFilterAceProtoSrcPortEntry
     MAX-ACCESS         not-accessible
     STATUS             current
     DESCRIPTION        "A table of Aces to store TCP/UDP Source Port information
                        of each Ace in context of its parent Acl."
     ::= { rcPrFilterAce 33 }

rcPrFilterAceProtoSrcPortEntry OBJECT-TYPE
     SYNTAX             RcPrFilterAceProtoSrcPortEntry
     MAX-ACCESS         not-accessible
     STATUS             current
     DESCRIPTION        "One entry holding Ace Protocol TCP/UDP Source Port
                        information. An Ace is a member of one Acl."
     INDEX              { rcPrFilterAceProtoSrcPortAclId,
                          rcPrFilterAceProtoSrcPortAceId }
     ::= { rcPrFilterAceProtoSrcPortTable 1 }

RcPrFilterAceProtoSrcPortEntry ::= SEQUENCE {
        rcPrFilterAceProtoSrcPortAclId     INTEGER,
        rcPrFilterAceProtoSrcPortAceId     INTEGER,
        rcPrFilterAceProtoSrcPortPort      OCTET STRING,
        rcPrFilterAceProtoSrcPortCount     INTEGER,
        rcPrFilterAceProtoSrcPortOper      INTEGER,
        rcPrFilterAceProtoSrcPortRowStatus RowStatus,
        rcPrFilterAceProtoSrcPortOperMaskRange Integer32
        }

rcPrFilterAceProtoSrcPortAclId OBJECT-TYPE
     SYNTAX             INTEGER (1..2048)
     MAX-ACCESS         read-only
     STATUS             current
     DESCRIPTION        "An index to the AceProtoSrcPortEntry, a unique
                        identifier for Acl entry in the range of Table
                        Size."
     ::= { rcPrFilterAceProtoSrcPortEntry 1 }

rcPrFilterAceProtoSrcPortAceId OBJECT-TYPE
     SYNTAX             INTEGER (1..2000)
     MAX-ACCESS         read-only
     STATUS             current
     DESCRIPTION        "An index to the AceProtoSrcPortEntry, a unique
                        identifier for Ace entry in the range of Table
                        Size."
     ::= { rcPrFilterAceProtoSrcPortEntry 2 }

rcPrFilterAceProtoSrcPortPort OBJECT-TYPE
     SYNTAX             OCTET STRING (SIZE(0..1500))
     MAX-ACCESS         read-write
     STATUS             current
     DESCRIPTION        "Port Number or Port List to match on."
     ::= { rcPrFilterAceProtoSrcPortEntry 3 }

rcPrFilterAceProtoSrcPortCount OBJECT-TYPE
     SYNTAX             INTEGER(1..100)
     MAX-ACCESS         read-write
     STATUS             current
     DESCRIPTION        "Count to store the number of discrete ranges
                        entered for the TCP source port."
     ::= { rcPrFilterAceProtoSrcPortEntry 4 }

rcPrFilterAceProtoSrcPortOper OBJECT-TYPE
     SYNTAX             INTEGER {
                            eq(1),   -- exact match
                            mask(8),
                            range(9)
                        }
     MAX-ACCESS         read-write
     STATUS             current
     DESCRIPTION        "Operator for Ace Protocol SrcPort."
     ::= { rcPrFilterAceProtoSrcPortEntry 5 }

rcPrFilterAceProtoSrcPortRowStatus OBJECT-TYPE
     SYNTAX             RowStatus
     MAX-ACCESS         read-write
     STATUS             current
     DESCRIPTION        "Create/delete operations for this entry."
     ::= { rcPrFilterAceProtoSrcPortEntry 6 }

rcPrFilterAceProtoSrcPortOperMaskRange OBJECT-TYPE
     SYNTAX             Integer32(0..'FFFF'h)
     MAX-ACCESS         read-write
     STATUS             current
     DESCRIPTION        "The value should be displayed in hex when
                        rcPrFilterAceProtoSrcPortOper is set to 'mask'.
                        This object will be used as a Range high value when
                        rcPrFilterAceProtoSrcPortOper is set to 'range'.
                        ('range' is not supported in this 3.0 release).
                        If it is used as range high value, it should be
                        displayed in decimal formtat.
                        This object will be set to 0 when
                        rcPrFilterAceProtoSrcPortOper is set to 'eq'"
     ::= { rcPrFilterAceProtoSrcPortEntry 7 }

-- ACE Protocol TCP/UDP DstPort Table

rcPrFilterAceProtoDstPortTable OBJECT-TYPE
     SYNTAX             SEQUENCE OF RcPrFilterAceProtoDstPortEntry
     MAX-ACCESS         not-accessible
     STATUS             current
     DESCRIPTION        "A table of Aces to store TCP Dest Port information
                        of each Ace in context of its parent Acl."
     ::= { rcPrFilterAce 34 }

rcPrFilterAceProtoDstPortEntry OBJECT-TYPE
     SYNTAX             RcPrFilterAceProtoDstPortEntry
     MAX-ACCESS         not-accessible
     STATUS             current
     DESCRIPTION        "One entry holding Ace Protocol TCP Dest Port
                        information. An Ace is a member of one Acl."
     INDEX              { rcPrFilterAceProtoDstPortAclId,
                          rcPrFilterAceProtoDstPortAceId }
     ::= { rcPrFilterAceProtoDstPortTable 1 }

RcPrFilterAceProtoDstPortEntry ::= SEQUENCE {
        rcPrFilterAceProtoDstPortAclId     INTEGER,
        rcPrFilterAceProtoDstPortAceId     INTEGER,
        rcPrFilterAceProtoDstPortPort      OCTET STRING,
        rcPrFilterAceProtoDstPortCount     INTEGER,
        rcPrFilterAceProtoDstPortOper      INTEGER,
        rcPrFilterAceProtoDstPortRowStatus RowStatus,
        rcPrFilterAceProtoDstPortOperMaskRange Integer32
        }

rcPrFilterAceProtoDstPortAclId OBJECT-TYPE
     SYNTAX             INTEGER (1..2048)
     MAX-ACCESS         read-only
     STATUS             current
     DESCRIPTION        "An index to the AceProtoDstPortEntry, a unique
                        identifier for Acl entry in the range of Table
                        Size."
     ::= { rcPrFilterAceProtoDstPortEntry 1 }

rcPrFilterAceProtoDstPortAceId OBJECT-TYPE
     SYNTAX             INTEGER (1..2000)
     MAX-ACCESS         read-only
     STATUS             current
     DESCRIPTION        "An index to the AceProtoDstPortEntry, a unique
                        identifier for Ace entry in the range of Table
                        Size."
     ::= { rcPrFilterAceProtoDstPortEntry 2 }

rcPrFilterAceProtoDstPortPort OBJECT-TYPE
     SYNTAX             OCTET STRING (SIZE(0..1500))
     MAX-ACCESS         read-write
     STATUS             current
     DESCRIPTION        "Port Number or Port List to match on."
     ::= { rcPrFilterAceProtoDstPortEntry 3 }

rcPrFilterAceProtoDstPortCount OBJECT-TYPE
     SYNTAX             INTEGER(1..100)
     MAX-ACCESS         read-write
     STATUS             current
     DESCRIPTION        "Count to store the number of discrete ranges
                        entered for the TCP dest port."
     ::= { rcPrFilterAceProtoDstPortEntry 4 }

rcPrFilterAceProtoDstPortOper OBJECT-TYPE
     SYNTAX             INTEGER {
                            eq(1),   -- exact match
                            mask(8),
                            range(9)
                        }
     MAX-ACCESS         read-write
     STATUS             current
     DESCRIPTION        "Operator for Ace Protocol DstPort."
     ::= { rcPrFilterAceProtoDstPortEntry 5 }

rcPrFilterAceProtoDstPortRowStatus OBJECT-TYPE
     SYNTAX             RowStatus
     MAX-ACCESS         read-write
     STATUS             current
     DESCRIPTION        "Create/delete operations for this entry."
     ::= { rcPrFilterAceProtoDstPortEntry 6 }

rcPrFilterAceProtoDstPortOperMaskRange OBJECT-TYPE
     SYNTAX             Integer32(0..'FFFF'h)
     MAX-ACCESS         read-write
     STATUS             current
     DESCRIPTION        "The value should be displayed in hex when
                        rcPrFilterAceProtoDstPortOper is set to 'mask'.
                        This object will be used as a Range high value when
                        rcPrFilterAceProtoDstPortOper is set to 'range'.
                        ('range' is not supported in this 3.0 release).
                        If it is used as range high value, it should be
                        displayed in decimal formtat.
                        This object will be set to 0 when
                        rcPrFilterAceProtoDstPortOper is set to 'eq'"
     ::= { rcPrFilterAceProtoDstPortEntry 7 }

-- ACE Protocol Tcp-Option  table

rcPrFilterAceProtoTcpOptionTable OBJECT-TYPE
     SYNTAX             SEQUENCE OF RcPrFilterAceProtoTcpOptionEntry
     MAX-ACCESS         not-accessible
     STATUS             current
     DESCRIPTION        "A table of Aces to store TCP Option information
                        of each Ace in context of its parent Acl."
     ::= { rcPrFilterAce 35 }

rcPrFilterAceProtoTcpOptionEntry OBJECT-TYPE
     SYNTAX             RcPrFilterAceProtoTcpOptionEntry
     MAX-ACCESS         not-accessible
     STATUS             current
     DESCRIPTION        "One entry holding Ace Protocol TCP option
                        information. An Ace is a member of one Acl."
     INDEX              { rcPrFilterAceProtoTcpOptionAclId,
                          rcPrFilterAceProtoTcpOptionAceId }
     ::= { rcPrFilterAceProtoTcpOptionTable 1 }

RcPrFilterAceProtoTcpOptionEntry ::= SEQUENCE {
        rcPrFilterAceProtoTcpOptionAclId     INTEGER,
        rcPrFilterAceProtoTcpOptionAceId     INTEGER,
        rcPrFilterAceProtoTcpOptionHeader    INTEGER,
        rcPrFilterAceProtoTcpOptionOper      INTEGER,
        rcPrFilterAceProtoTcpOptionRowStatus RowStatus
        }

rcPrFilterAceProtoTcpOptionAclId OBJECT-TYPE
     SYNTAX             INTEGER (1..2048)
     MAX-ACCESS         read-only
     STATUS             current
     DESCRIPTION        "An index to the rcPrFilterAceProtoTcpOptionEntry,
                    a unique identifier for Acl entry in the range of Table
                                Size."
     ::= { rcPrFilterAceProtoTcpOptionEntry 1 }

rcPrFilterAceProtoTcpOptionAceId OBJECT-TYPE
     SYNTAX             INTEGER (1..2000)
     MAX-ACCESS         read-only
     STATUS             current
     DESCRIPTION        "An index to the rcPrFilterAceProtoTcpOptionEntry,
                         a unique identifier for Ace entry in the
                         range of Table Size."
     ::= { rcPrFilterAceProtoTcpOptionEntry 2 }

rcPrFilterAceProtoTcpOptionHeader  OBJECT-TYPE
     SYNTAX             INTEGER  {
                                no-operation(1),
                                max-segment-size(2),
                                wsopt(3),
                                sack-permitted(4),
                                sack(5),
                                tsopt(8),
                                partial-order-conn-perm(9),
                                partial-order-service-profile(10),
                                cc(11),
                                cc-new(12),
                                cc-echo(13),
                                tcp-alt-checksum-req(14),
                                tcp-alt-checksum-data(15),
                                md5(19),
                                quick-start-resp(27),
                                user-timeout-opt(28)
                        }
     MAX-ACCESS         read-write
     STATUS             current
     DESCRIPTION        "TCP options to be matched from the TCP  Header.
                        1  No-Operation
                        2 MaximumSegmentSize
                        3 WSOPT - Window Scale
                        4 SACK Permitted
                        5 SACK
                        8 TSOPT - Time Stamp Option
                        9 Partial Order Connection Permitted
                        10 Partial Order Service Profile
                        11 CC
                        12 CC.NEW
                        13  CC.ECHO
                        14  TCP Alternate Checksum Request
                        15  TCP Alternate Checksum Data
                        19  MD5 Signature Option
                        27  Quick-Start Response
                        28  User Timeout Option                 "
 ::= {rcPrFilterAceProtoTcpOptionEntry 3 }

rcPrFilterAceProtoTcpOptionOper OBJECT-TYPE
     SYNTAX             INTEGER {
                            any(5)
                        }
     MAX-ACCESS         read-write
     STATUS             current
     DESCRIPTION        "Logical Operator - only 'any' is valid at present."
     DEFVAL             { any }
     ::= {rcPrFilterAceProtoTcpOptionEntry 4 }

rcPrFilterAceProtoTcpOptionRowStatus OBJECT-TYPE
     SYNTAX             RowStatus
     MAX-ACCESS         read-write
     STATUS             current
     DESCRIPTION        "Create/delete operations for this entry."
     ::= { rcPrFilterAceProtoTcpOptionEntry 5 }

-- ACE Ipv6 Traffic class Table

rcPrFilterAceIpv6TrafficClsTable OBJECT-TYPE
     SYNTAX             SEQUENCE OF RcPrFilterAceIpv6TrafficClsEntry
     MAX-ACCESS         not-accessible
     STATUS             current
     DESCRIPTION        "A table of Aces to store IPv6 Traffic Class
                        Header information of each Ace in context of its
                        parent Acl."
     ::= { rcPrFilterAce 36 }

rcPrFilterAceIpv6TrafficClsEntry OBJECT-TYPE
     SYNTAX             RcPrFilterAceIpv6TrafficClsEntry
     MAX-ACCESS         not-accessible
     STATUS             current
     DESCRIPTION        "One Ace entry holding Ace IPv6 Traffic Class
                         information. An Ace is a member of one Acl."
     INDEX              { rcPrFilterAceIpv6TrafficClsAclId,
                          rcPrFilterAceIpv6TrafficClsAceId }
     ::= { rcPrFilterAceIpv6TrafficClsTable 1 }

RcPrFilterAceIpv6TrafficClsEntry ::= SEQUENCE {
        rcPrFilterAceIpv6TrafficClsAclId          INTEGER,
        rcPrFilterAceIpv6TrafficClsAceId          INTEGER,
        rcPrFilterAceIpv6TrafficClsRowStatus      RowStatus,
        rcPrFilterAceIpv6TrafficClsOper           INTEGER,
        rcPrFilterAceIpv6TrafficClsTrafficCls     INTEGER
        }

rcPrFilterAceIpv6TrafficClsAclId OBJECT-TYPE
     SYNTAX             INTEGER (1..2048)
     MAX-ACCESS         not-accessible
     STATUS             current
     DESCRIPTION        "An index to the AceIpv6TrafficClsEntry, a unique
                        identifier for Acl entry in the range of Table
                        Size."
     ::= { rcPrFilterAceIpv6TrafficClsEntry 1 }

rcPrFilterAceIpv6TrafficClsAceId OBJECT-TYPE
     SYNTAX             INTEGER (1..2000)
     MAX-ACCESS         not-accessible
     STATUS             current
     DESCRIPTION        "An index to the AceIpv6TrafficClsEntry, a unique
                        identifier for Acl entry in the range of Table
                        Size."
     ::= { rcPrFilterAceIpv6TrafficClsEntry 2 }

rcPrFilterAceIpv6TrafficClsRowStatus OBJECT-TYPE
     SYNTAX             RowStatus
     MAX-ACCESS         read-create
     STATUS             current
     DESCRIPTION        "Create/delete operations for this entry."
     ::= { rcPrFilterAceIpv6TrafficClsEntry 3 }

rcPrFilterAceIpv6TrafficClsOper OBJECT-TYPE
     SYNTAX             INTEGER {
                            eq(1)    -- exact match
                        }
     MAX-ACCESS         read-create
     STATUS             current
     DESCRIPTION        "Operators for Ace IPv6 Traffic Class"
     ::= { rcPrFilterAceIpv6TrafficClsEntry 4 }

rcPrFilterAceIpv6TrafficClsTrafficCls OBJECT-TYPE
     SYNTAX             INTEGER (0..255)
     MAX-ACCESS         read-create
     STATUS             current
     DESCRIPTION        "Ipv6 Traffic Class value"
     DEFVAL             { 0 }
     ::= { rcPrFilterAceIpv6TrafficClsEntry 5 }

rcPrFilterAceProtoRoutingTypeTable OBJECT-TYPE
     SYNTAX		SEQUENCE OF RcPrFilterAceProtoRoutingTypeEntry
     MAX-ACCESS		not-accessible
     STATUS		current
     DESCRIPTION	"A table of Ace to store IPv6 Routing header type
	 		information of each Ace in context of its parent Acl."
     ::= { rcPrFilterAce 37 }

rcPrFilterAceProtoRoutingTypeEntry OBJECT-TYPE
     SYNTAX		RcPrFilterAceProtoRoutingTypeEntry
     MAX-ACCESS		not-accessible
     STATUS		current
     DESCRIPTION	"One Ace entry holding Ace IPv6 routing header type
			information. An Ace is a member of one Acl."
     INDEX		{ rcPrFilterAceProtoRoutingTypeAclId,
     			  rcPrFilterAceProtoRoutingTypeAceId }
    ::= { rcPrFilterAceProtoRoutingTypeTable 1 }

RcPrFilterAceProtoRoutingTypeEntry ::= SEQUENCE {
        rcPrFilterAceProtoRoutingTypeAclId	Integer32,
	rcPrFilterAceProtoRoutingTypeAceId	Integer32,
	rcPrFilterAceProtoRoutingTypeType	Integer32,
	rcPrFilterAceProtoRoutingTypeOper	INTEGER,
	rcPrFilterAceProtoRoutingTypeRowStatus	RowStatus
	}

rcPrFilterAceProtoRoutingTypeAclId OBJECT-TYPE
     SYNTAX		Integer32 (1..2048)
     MAX-ACCESS		not-accessible
     STATUS		current
     DESCRIPTION	"An index to the AceProtoRoutingTypeEntry, a unique
			identifier for Acl entry in the range of Table
			Size."
     ::= { rcPrFilterAceProtoRoutingTypeEntry 1 }

rcPrFilterAceProtoRoutingTypeAceId OBJECT-TYPE
     SYNTAX		Integer32 (1..2000)
     MAX-ACCESS		not-accessible
     STATUS 		current
     DESCRIPTION 	"An index to the AceProtoRoutingTypeEntry, a unique
	 		 identifier for Ace entry in the range of Table
			 Size."
     ::= { rcPrFilterAceProtoRoutingTypeEntry 2 }

rcPrFilterAceProtoRoutingTypeType OBJECT-TYPE
     SYNTAX 		Integer32 (0..2)
     MAX-ACCESS 		read-create
     STATUS 		current
     DESCRIPTION 	"The ipv6 routing header type to look for."
     ::= { rcPrFilterAceProtoRoutingTypeEntry 3 }

rcPrFilterAceProtoRoutingTypeOper OBJECT-TYPE
    SYNTAX 		INTEGER {
    	                     eq(1) -- exact match
			}
    MAX-ACCESS 		read-create
    STATUS 		current
    DESCRIPTION 	"Operators for Ace IPv6 routing header type."
    ::= { rcPrFilterAceProtoRoutingTypeEntry 4 }

rcPrFilterAceProtoRoutingTypeRowStatus OBJECT-TYPE
    SYNTAX 		RowStatus
    MAX-ACCESS 		read-create
    STATUS 		current
    DESCRIPTION 	"Create/delete operations for this entry."
    ::= { rcPrFilterAceProtoRoutingTypeEntry 5 }

-- ACE Protocol Icmpv6MsgType table

rcPrFilterAceProtoIcmpv6MsgTypeTable OBJECT-TYPE
     SYNTAX             SEQUENCE OF RcPrFilterAceProtoIcmpv6MsgTypeEntry
     MAX-ACCESS         not-accessible
     STATUS             current
     DESCRIPTION        "A table of Aces to store ICMPv6 message type information
                        of each Ace in context of its parent Acl."
     ::= { rcPrFilterAce 38 }

rcPrFilterAceProtoIcmpv6MsgTypeEntry OBJECT-TYPE
     SYNTAX             RcPrFilterAceProtoIcmpv6MsgTypeEntry
     MAX-ACCESS         not-accessible
     STATUS             current
     DESCRIPTION        "One entry holding Ace ICMPv6 message type
			information. An Ace is a member of one Acl."
     INDEX              { rcPrFilterAceProtoIcmpv6MsgTypeAclId,
                          rcPrFilterAceProtoIcmpv6MsgTypeAceId }
     ::= { rcPrFilterAceProtoIcmpv6MsgTypeTable 1 }


RcPrFilterAceProtoIcmpv6MsgTypeEntry ::= SEQUENCE {
        rcPrFilterAceProtoIcmpv6MsgTypeAclId     Integer32,
        rcPrFilterAceProtoIcmpv6MsgTypeAceId     Integer32,
        rcPrFilterAceProtoIcmpv6MsgTypeList      OCTET STRING,
        rcPrFilterAceProtoIcmpv6MsgTypeCount     Integer32,
        rcPrFilterAceProtoIcmpv6MsgTypeOper      INTEGER,
        rcPrFilterAceProtoIcmpv6MsgTypeRowStatus RowStatus
        }

rcPrFilterAceProtoIcmpv6MsgTypeAclId OBJECT-TYPE
     SYNTAX             Integer32(1..2048)
     MAX-ACCESS         not-accessible
     STATUS             current
     DESCRIPTION        "An index to the AceProtoIcmpv6MsgTypeEntry, a unique
	                identifier for Acl entry in the range of Table
			Size."
     ::= { rcPrFilterAceProtoIcmpv6MsgTypeEntry 1 }

rcPrFilterAceProtoIcmpv6MsgTypeAceId OBJECT-TYPE
     SYNTAX             Integer32(1..2000)
     MAX-ACCESS         not-accessible
     STATUS             current
     DESCRIPTION        "An index to the AceProtoIcmpv6MsgTypeEntry, a unique
	                identifier for Ace entry in the range of Table
			Size."
     ::= { rcPrFilterAceProtoIcmpv6MsgTypeEntry 2 }

rcPrFilterAceProtoIcmpv6MsgTypeList OBJECT-TYPE
     SYNTAX             OCTET STRING (SIZE(0..1500))
     MAX-ACCESS         read-create
     STATUS             current
     DESCRIPTION        "One or a list of ICMPv6 messages to be matched.
			Need to provide strings, number of protocol header
			types (pre-defined values plus user-defined headers).
			Valid range is 0 to 255 (reserved)."
     ::= { rcPrFilterAceProtoIcmpv6MsgTypeEntry 3 }

rcPrFilterAceProtoIcmpv6MsgTypeCount OBJECT-TYPE
     SYNTAX             Integer32(1..100)
     MAX-ACCESS         read-create
     STATUS             current
     DESCRIPTION        "Count to store the number of discrete ranges
                        entered for the ICMP message types."
     ::= { rcPrFilterAceProtoIcmpv6MsgTypeEntry 4 }

rcPrFilterAceProtoIcmpv6MsgTypeOper OBJECT-TYPE
     SYNTAX             INTEGER {
                            eq(1)   -- exact match
                        }
     MAX-ACCESS         read-create
     STATUS             current
     DESCRIPTION        "Operator for Ace Protocol Icmpv6MsgTypes."
     ::= { rcPrFilterAceProtoIcmpv6MsgTypeEntry 5 }

rcPrFilterAceProtoIcmpv6MsgTypeRowStatus OBJECT-TYPE
     SYNTAX             RowStatus
     MAX-ACCESS         read-create
     STATUS             current
     DESCRIPTION        "Create/delete operations for this entry."
     ::= { rcPrFilterAceProtoIcmpv6MsgTypeEntry 6 }

-- rcPrFilterAceVrfTable
rcPrFilterAceVrfTable OBJECT-TYPE
    SYNTAX	 SEQUENCE OF RcPrFilterAceVrfEntry
    MAX-ACCESS   not-accessible
    STATUS       current
    DESCRIPTION  "A table of Aces to store vrf name of each Ace in context
		 of its parent Acl."
    ::= { rcPrFilterAce 39 }

rcPrFilterAceVrfEntry OBJECT-TYPE
    SYNTAX       RcPrFilterAceVrfEntry
    MAX-ACCESS   not-accessible
    STATUS       current
    DESCRIPTION "One Ace entry holding Ace vrf name. An Ace is a member of one Acl."
    INDEX        { rcPrFilterAceVrfAclId,
                   rcPrFilterAceVrfAceId }
    ::= { rcPrFilterAceVrfTable 1 }

RcPrFilterAceVrfEntry ::= SEQUENCE {
        rcPrFilterAceVrfAclId       Integer32,
        rcPrFilterAceVrfAceId       Integer32,
        rcPrFilterAceVrfVrfName     DisplayString,
        rcPrFilterAceVrfOper        INTEGER,
        rcPrFilterAceVrfRowStatus   RowStatus
     }

rcPrFilterAceVrfAclId OBJECT-TYPE
     SYNTAX         Integer32 (1..2048)
     MAX-ACCESS     not-accessible
     STATUS         current
     DESCRIPTION    "An index to the AceEthPortEntry, a unique
                    identifier for Acl entry in the range of Table
                    Size."
     ::= { rcPrFilterAceVrfEntry 1 }

rcPrFilterAceVrfAceId OBJECT-TYPE
    SYNTAX        Integer32 (1..2000)
    MAX-ACCESS    not-accessible
    STATUS        current
    DESCRIPTION   "An index to the AceEthPortEntry, a unique
                  identifier for Acl entry in the range of Table
                  Size."
    ::= { rcPrFilterAceVrfEntry 2 }

rcPrFilterAceVrfVrfName OBJECT-TYPE
    SYNTAX        DisplayString (SIZE (0..16))
    MAX-ACCESS    read-create
    STATUS        current
    DESCRIPTION   "Vrf name to match on."
    ::= { rcPrFilterAceVrfEntry 3 }

rcPrFilterAceVrfOper OBJECT-TYPE
    SYNTAX       INTEGER {
    	           eq(1) -- exact match
                 }
    MAX-ACCESS   read-create
    STATUS       current
    DESCRIPTION "Operator for Ace vrf name."
    DEFVAL  { eq }
    ::= { rcPrFilterAceVrfEntry 4 }

rcPrFilterAceVrfRowStatus OBJECT-TYPE
    SYNTAX      RowStatus
    MAX-ACCESS  read-create
    STATUS      current
    DESCRIPTION "Create/delete operations for this entry."
    ::= { rcPrFilterAceVrfEntry 5 }

-- ACE Ip Routed Table

rcPrFilterAceIpRoutedTable OBJECT-TYPE
     SYNTAX             SEQUENCE OF RcPrFilterAceIpRoutedEntry
     MAX-ACCESS         not-accessible
     STATUS             current
     DESCRIPTION        "A table of Aces to store IP routed
			information of each Ace in context of its parent Acl."
     ::= { rcPrFilterAce 40 }

rcPrFilterAceIpRoutedEntry OBJECT-TYPE
     SYNTAX             RcPrFilterAceIpRoutedEntry
     MAX-ACCESS         not-accessible
     STATUS             current
     DESCRIPTION        "One Ace entry holding Ace IPv4 Routed
			information. An Ace is a member of one Acl."
     INDEX              { rcPrFilterAceIpRoutedAclId,
                          rcPrFilterAceIpRoutedAceId }
     ::= { rcPrFilterAceIpRoutedTable 1 }

RcPrFilterAceIpRoutedEntry ::= SEQUENCE {
        rcPrFilterAceIpRoutedAclId	     INTEGER,
        rcPrFilterAceIpRoutedAceId	     INTEGER,
        rcPrFilterAceIpRoutedOnly            TruthValue,
        rcPrFilterAceIpRoutedRowStatus       RowStatus
        }

rcPrFilterAceIpRoutedAclId OBJECT-TYPE
     SYNTAX             INTEGER (1..2048)
     MAX-ACCESS         not-accessible
     STATUS             current
     DESCRIPTION        "An index to the AceIpRoutedEntry, a unique
	                identifier for Acl entry in the range of Table
			Size."
     ::= { rcPrFilterAceIpRoutedEntry 1 }

rcPrFilterAceIpRoutedAceId OBJECT-TYPE
     SYNTAX             INTEGER (1..2000)
     MAX-ACCESS         not-accessible
     STATUS             current
     DESCRIPTION        "An index to the AceIpRoutedEntry, a unique
	                identifier for Acl entry in the range of Table
			Size."
     ::= { rcPrFilterAceIpRoutedEntry 2 }

rcPrFilterAceIpRoutedOnly OBJECT-TYPE
     SYNTAX             TruthValue
     MAX-ACCESS         read-create
     STATUS             current
     DESCRIPTION        "To be matched for the IP routed packets only."
     DEFVAL             {false}
     ::= { rcPrFilterAceIpRoutedEntry 3 }

rcPrFilterAceIpRoutedRowStatus OBJECT-TYPE
     SYNTAX             RowStatus
     MAX-ACCESS         read-create
     STATUS             current
     DESCRIPTION        "Create/delete operations for this entry."
     ::= { rcPrFilterAceIpRoutedEntry 4 }

-- ACE Ipv6 RoutedOnly Table

rcPrFilterAceIpv6RoutedTable OBJECT-TYPE
     SYNTAX             SEQUENCE OF RcPrFilterAceIpv6RoutedEntry
     MAX-ACCESS         not-accessible
     STATUS             current
     DESCRIPTION        "A table of Aces to store IPv6 routed
			information of each Ace in context of its parent Acl."
     ::= { rcPrFilterAce 41 }

rcPrFilterAceIpv6RoutedEntry OBJECT-TYPE
     SYNTAX             RcPrFilterAceIpv6RoutedEntry
     MAX-ACCESS         not-accessible
     STATUS             current
     DESCRIPTION        "One Ace entry holding Ace IPv6 routed
                         information. An Ace is a member of one Acl."
     INDEX              { rcPrFilterAceIpv6RoutedAclId,
                          rcPrFilterAceIpv6RoutedAceId }
     ::= { rcPrFilterAceIpv6RoutedTable 1 }

RcPrFilterAceIpv6RoutedEntry ::= SEQUENCE {
        rcPrFilterAceIpv6RoutedAclId	     INTEGER,
        rcPrFilterAceIpv6RoutedAceId	     INTEGER,
        rcPrFilterAceIpv6RoutedOnly          TruthValue,
        rcPrFilterAceIpv6RoutedRowStatus     RowStatus
        }

rcPrFilterAceIpv6RoutedAclId OBJECT-TYPE
     SYNTAX             INTEGER (1..2048)
     MAX-ACCESS         not-accessible
     STATUS             current
     DESCRIPTION        "An index to the AceIpv6RoutedEntry, a unique
                        identifier for Acl entry in the range of Table
                        Size."
     ::= { rcPrFilterAceIpv6RoutedEntry 1 }

rcPrFilterAceIpv6RoutedAceId OBJECT-TYPE
     SYNTAX             INTEGER (1..2000)
     MAX-ACCESS         not-accessible
     STATUS             current
     DESCRIPTION        "An index to the AceIpv6RoutedEntry, a unique
                        identifier for Acl entry in the range of Table
                        Size."
     ::= { rcPrFilterAceIpv6RoutedEntry 2 }

rcPrFilterAceIpv6RoutedOnly OBJECT-TYPE
     SYNTAX             TruthValue
     MAX-ACCESS         read-create
     STATUS             current
     DESCRIPTION        "To be matched for the IPv6 routed packets only."
     DEFVAL             {false}
     ::= { rcPrFilterAceIpv6RoutedEntry 3 }

rcPrFilterAceIpv6RoutedRowStatus OBJECT-TYPE
     SYNTAX             RowStatus
     MAX-ACCESS         read-create
     STATUS             current
     DESCRIPTION        "Create/delete operations for this entry."
     ::= { rcPrFilterAceIpv6RoutedEntry 4 }


-- Power Ranger Egress Qos Cos Queue Voq stats Table
rcPrQosCosQueVoqPortStatsTable OBJECT-TYPE
        SYNTAX        SEQUENCE OF RcPrQosCosQueVoqPortStatsEntry
        MAX-ACCESS    not-accessible
        STATUS        current
        DESCRIPTION   "This table is used to get the qos cos queue
	    	       Voq port stats."
        ::= { rcPrQos 19 }


rcPrQosCosQueVoqPortStatsEntry OBJECT-TYPE
        SYNTAX        RcPrQosCosQueVoqPortStatsEntry
        MAX-ACCESS    not-accessible
        STATUS        current
        DESCRIPTION   "Entry containing information of port Qos cosq Voq stats"
        INDEX         { rcPrQosCosQueVoqPortStatsPortIndex,
			rcPrQosCosQueVoqPortStatsQueIndex }
        ::= { rcPrQosCosQueVoqPortStatsTable 1 }

RcPrQosCosQueVoqPortStatsEntry ::= SEQUENCE {
                rcPrQosCosQueVoqPortStatsPortIndex         InterfaceIndex,
                rcPrQosCosQueVoqPortStatsQueIndex          Integer32,
                rcPrQosCosQueVoqPortStatsAcceptedPackets   Counter64,
                rcPrQosCosQueVoqPortStatsAcceptedBytes     Counter64,
                rcPrQosCosQueVoqPortStatsDropPackets       Counter64,
                rcPrQosCosQueVoqPortStatsDropBytes         Counter64,
                rcPrQosCosQueVoqPortStatsClearStat         TruthValue
}

rcPrQosCosQueVoqPortStatsPortIndex      OBJECT-TYPE
        SYNTAX          InterfaceIndex
        MAX-ACCESS      not-accessible
        STATUS          current
        DESCRIPTION     "Used to indicate the port number"
        ::= { rcPrQosCosQueVoqPortStatsEntry 1 }

rcPrQosCosQueVoqPortStatsQueIndex           OBJECT-TYPE
        SYNTAX          Integer32 (0..7)
        MAX-ACCESS      not-accessible
        STATUS          current
        DESCRIPTION     "Used to indicate the queue id."
        ::= { rcPrQosCosQueVoqPortStatsEntry 2 }

rcPrQosCosQueVoqPortStatsAcceptedPackets            OBJECT-TYPE
        SYNTAX          Counter64
        MAX-ACCESS      read-only
        STATUS          current
        DESCRIPTION     "Numer of packets that entered the VOQ."
        ::= { rcPrQosCosQueVoqPortStatsEntry 3 }

rcPrQosCosQueVoqPortStatsAcceptedBytes            OBJECT-TYPE
        SYNTAX          Counter64
        MAX-ACCESS      read-only
        STATUS          current
        DESCRIPTION     "Numer of bytes that entered the VOQ."
        ::= { rcPrQosCosQueVoqPortStatsEntry 4 }

rcPrQosCosQueVoqPortStatsDropPackets       OBJECT-TYPE
        SYNTAX          Counter64
        MAX-ACCESS      read-only
        STATUS          current
        DESCRIPTION     "Numer of dropped packets because the VOQ was full."
        ::= { rcPrQosCosQueVoqPortStatsEntry 5 }

rcPrQosCosQueVoqPortStatsDropBytes        OBJECT-TYPE
        SYNTAX          Counter64
        MAX-ACCESS      read-only
        STATUS          current
        DESCRIPTION     "Numer of dropped bytes because the VOQ was full."
        ::= { rcPrQosCosQueVoqPortStatsEntry 6 }

rcPrQosCosQueVoqPortStatsClearStat        OBJECT-TYPE
        SYNTAX       TruthValue
        MAX-ACCESS   read-write
        STATUS       current
        DESCRIPTION  "Clear Voq Port Stats if set to true. Return value
	    	      will always be false."
        ::= { rcPrQosCosQueVoqPortStatsEntry 7 }

-- Power Ranger Egress Qos Cos Queue Voq cpp stats Table
rcPrQosCosQueVoqCppPortStatsTable OBJECT-TYPE
        SYNTAX        SEQUENCE OF RcPrQosCosQueVoqCppPortStatsEntry
        MAX-ACCESS    not-accessible
        STATUS        current
        DESCRIPTION   "This table is used to get the qos cos queue Voq
	    	       cpp stats."
        ::= { rcPrQos 20 }

rcPrQosCosQueVoqCppPortStatsEntry OBJECT-TYPE
        SYNTAX        RcPrQosCosQueVoqCppPortStatsEntry
        MAX-ACCESS    not-accessible
        STATUS        current
        DESCRIPTION   "Entry containing information of port Qos cosq Voq
	    	       cpp stats"
        INDEX         { rcPrQosCosQueVoqCppPortStatsProtocolIndex }
        ::= { rcPrQosCosQueVoqCppPortStatsTable 1 }

RcPrQosCosQueVoqCppPortStatsEntry ::= SEQUENCE {
                rcPrQosCosQueVoqCppPortStatsProtocolIndex   INTEGER,
                rcPrQosCosQueVoqCppPortStatsProtocolName    OCTET STRING,
                rcPrQosCosQueVoqCppPortStatsAcceptedPackets Counter64,
                rcPrQosCosQueVoqCppPortStatsAcceptedBytes   Counter64,
                rcPrQosCosQueVoqCppPortStatsDropPackets     Counter64,
                rcPrQosCosQueVoqCppPortStatsDropBytes       Counter64
}

rcPrQosCosQueVoqCppPortStatsProtocolIndex     OBJECT-TYPE
        SYNTAX          INTEGER {
                            vrrp(1),
                            vlacp(2),
                            lacp(3),
                            cfm(4),
                            vrrpv6(5),
                            istCtl(6),
                            radius(7),
                            ntp(8),
                            icmpv4(9),
                            slpp(10),
                            bpdu(11),
                            tdp(12),
                            eap(13),
                            lldp(14),
                            ndMcv6(15),
                            ndUcv6(16),
                            rlogin(17),
                            fragUcv6(18),
                            isis(19),
                            ospfMc(20),
                            dhcp(21),
                            pimMc(22),
                            arpRequest(23),
                            arpReply(24),
                            rarpRequest(25),
                            rarpRreply(26),
                            icmpv4Bc(27),
                            ospfv6Mc(28),
                            ftp(29),
                            tftp(30),
                            snmp(31),
                            telnet(32),
                            ssh(33),
                            rsh(34),
                            http(35),
                            dns(36),
                            icmpMcv6(37),
                            icmpUcv6(38),
                            ipmcData(39),
                            bgp(40),
                            igmp(41),
                            mld(42),
                            pimUc(43),
                            ospfUc(44),
                            ospfv6Uc(45),
                            hopByHop(46),
                            ripv1(47),
                            ripv2(48),
                            ripv6(49),
                            macLearning(50),
                            internal1(51),
                            dataException(52),
                            ttlException(53),
                            fragMcv6(54),
                            internal2(55),
                            internal3(56),
                            ipfix(57),
                            internal4(58)
                        }
        MAX-ACCESS      not-accessible
        STATUS          current
        DESCRIPTION     "Used to indicate the protocol cos queue."
        ::= { rcPrQosCosQueVoqCppPortStatsEntry 1 }

rcPrQosCosQueVoqCppPortStatsProtocolName            OBJECT-TYPE
        SYNTAX          OCTET STRING (SIZE(1..16))
        MAX-ACCESS      read-only
        STATUS          current
        DESCRIPTION     "Used to indicate the protocol name."
        ::= { rcPrQosCosQueVoqCppPortStatsEntry 2 }

rcPrQosCosQueVoqCppPortStatsAcceptedPackets         OBJECT-TYPE
        SYNTAX          Counter64
        MAX-ACCESS      read-only
        STATUS          current
        DESCRIPTION     "the accepted packets for cpp port."
        ::= { rcPrQosCosQueVoqCppPortStatsEntry 3 }

rcPrQosCosQueVoqCppPortStatsAcceptedBytes           OBJECT-TYPE
        SYNTAX          Counter64
        MAX-ACCESS      read-only
        STATUS          current
        DESCRIPTION     "the accepted bytes for cpp port."
        ::= { rcPrQosCosQueVoqCppPortStatsEntry 4 }

rcPrQosCosQueVoqCppPortStatsDropPackets OBJECT-TYPE
        SYNTAX          Counter64
        MAX-ACCESS      read-only
        STATUS          current
        DESCRIPTION     "the drop packets for cpp port."
        ::= { rcPrQosCosQueVoqCppPortStatsEntry 5 }

rcPrQosCosQueVoqCppPortStatsDropBytes   OBJECT-TYPE
        SYNTAX          Counter64
        MAX-ACCESS      read-only
        STATUS          current
        DESCRIPTION     "the drop bytes for cpp port."
        ::= { rcPrQosCosQueVoqCppPortStatsEntry 6 }

-- Power Ranger Tunnel Qos Cos Queue stats Table
rcPrQosCosQueTunnelStatsTable OBJECT-TYPE
        SYNTAX        SEQUENCE OF RcPrQosCosQueTunnelStatsEntry
        MAX-ACCESS    not-accessible
        STATUS        current
        DESCRIPTION   "This table is used to get the qos cos queue Tunnel stats."
        ::= { rcPrQos 21 }

rcPrQosCosQueTunnelStatsEntry OBJECT-TYPE
        SYNTAX        RcPrQosCosQueTunnelStatsEntry
        MAX-ACCESS    not-accessible
        STATUS        current
        DESCRIPTION   "Entry containing information of Tunnel Qos cosq stats"
        INDEX         { rcPrQosCosQueTunnelStatsIndex }
        ::= { rcPrQosCosQueTunnelStatsTable 1 }

RcPrQosCosQueTunnelStatsEntry ::= SEQUENCE {
                rcPrQosCosQueTunnelStatsIndex            INTEGER,
                rcPrQosCosQueTunnelStatsQue0OutPackets   Counter64,
                rcPrQosCosQueTunnelStatsQue0OutBytes     Counter64,
                rcPrQosCosQueTunnelStatsQue0DropPackets  Counter64,
                rcPrQosCosQueTunnelStatsQue0DropBytes    Counter64,
                rcPrQosCosQueTunnelStatsQue1OutPackets   Counter64,
                rcPrQosCosQueTunnelStatsQue1OutBytes     Counter64,
                rcPrQosCosQueTunnelStatsQue1DropPackets  Counter64,
                rcPrQosCosQueTunnelStatsQue1DropBytes    Counter64,
                rcPrQosCosQueTunnelStatsQue2OutPackets   Counter64,
                rcPrQosCosQueTunnelStatsQue2OutBytes     Counter64,
                rcPrQosCosQueTunnelStatsQue2DropPackets  Counter64,
                rcPrQosCosQueTunnelStatsQue2DropBytes    Counter64,
                rcPrQosCosQueTunnelStatsQue3OutPackets   Counter64,
                rcPrQosCosQueTunnelStatsQue3OutBytes     Counter64,
                rcPrQosCosQueTunnelStatsQue3DropPackets  Counter64,
                rcPrQosCosQueTunnelStatsQue3DropBytes    Counter64,
                rcPrQosCosQueTunnelStatsQue4OutPackets   Counter64,
                rcPrQosCosQueTunnelStatsQue4OutBytes     Counter64,
                rcPrQosCosQueTunnelStatsQue4DropPackets  Counter64,
                rcPrQosCosQueTunnelStatsQue4DropBytes    Counter64,
                rcPrQosCosQueTunnelStatsQue5OutPackets   Counter64,
                rcPrQosCosQueTunnelStatsQue5OutBytes     Counter64,
                rcPrQosCosQueTunnelStatsQue5DropPackets  Counter64,
                rcPrQosCosQueTunnelStatsQue5DropBytes    Counter64,
                rcPrQosCosQueTunnelStatsQue6OutPackets   Counter64,
                rcPrQosCosQueTunnelStatsQue6OutBytes     Counter64,
                rcPrQosCosQueTunnelStatsQue6DropPackets  Counter64,
                rcPrQosCosQueTunnelStatsQue6DropBytes    Counter64,
                rcPrQosCosQueTunnelStatsQue7OutPackets   Counter64,
                rcPrQosCosQueTunnelStatsQue7OutBytes     Counter64,
                rcPrQosCosQueTunnelStatsQue7DropPackets  Counter64,
                rcPrQosCosQueTunnelStatsQue7DropBytes    Counter64,
                rcPrQosCosQueTunnelStatsClearStat        TruthValue
        }

rcPrQosCosQueTunnelStatsIndex     OBJECT-TYPE
        SYNTAX          INTEGER (1..255)
        MAX-ACCESS      not-accessible
        STATUS          current
        DESCRIPTION     "Used to indicate the tunnel index."
        ::= { rcPrQosCosQueTunnelStatsEntry 1 }

rcPrQosCosQueTunnelStatsQue0OutPackets     OBJECT-TYPE
        SYNTAX          Counter64
        MAX-ACCESS      read-only
        STATUS          current
        DESCRIPTION     "the out packets for Cos queue 0."
        ::= { rcPrQosCosQueTunnelStatsEntry 2 }

rcPrQosCosQueTunnelStatsQue0OutBytes       OBJECT-TYPE
        SYNTAX          Counter64
        MAX-ACCESS      read-only
        STATUS          current
        DESCRIPTION     "the out bytes for Cos queue 0."
        ::= { rcPrQosCosQueTunnelStatsEntry 3 }

rcPrQosCosQueTunnelStatsQue0DropPackets OBJECT-TYPE
    	SYNTAX          Counter64
        MAX-ACCESS      read-only
        STATUS          current
        DESCRIPTION     "the drop packets for Cos queue 0."
        ::= { rcPrQosCosQueTunnelStatsEntry 4 }

rcPrQosCosQueTunnelStatsQue0DropBytes  OBJECT-TYPE
    	SYNTAX          Counter64
	MAX-ACCESS      read-only
        STATUS          current
        DESCRIPTION     "the drop bytes for Cos queue 0."
        ::= { rcPrQosCosQueTunnelStatsEntry 5 }

rcPrQosCosQueTunnelStatsQue1OutPackets     OBJECT-TYPE
    	SYNTAX          Counter64
	MAX-ACCESS      read-only
        STATUS          current
        DESCRIPTION     "the out packets for Cos queue 1."
        ::= { rcPrQosCosQueTunnelStatsEntry 6 }

rcPrQosCosQueTunnelStatsQue1OutBytes       OBJECT-TYPE
    	SYNTAX          Counter64
	MAX-ACCESS      read-only
        STATUS          current
        DESCRIPTION     "the out bytes for Cos queue 1."
        ::= { rcPrQosCosQueTunnelStatsEntry 7 }

rcPrQosCosQueTunnelStatsQue1DropPackets OBJECT-TYPE
    	SYNTAX          Counter64
	MAX-ACCESS      read-only
        STATUS          current
        DESCRIPTION     "the drop packets for Cos queue 1."
        ::= { rcPrQosCosQueTunnelStatsEntry 8 }

rcPrQosCosQueTunnelStatsQue1DropBytes  OBJECT-TYPE
    	SYNTAX          Counter64
	MAX-ACCESS      read-only
        STATUS          current
        DESCRIPTION     "the drop bytes for Cos queue 1."
        ::= { rcPrQosCosQueTunnelStatsEntry 9 }

rcPrQosCosQueTunnelStatsQue2OutPackets     OBJECT-TYPE
    	SYNTAX          Counter64
	MAX-ACCESS      read-only
        STATUS          current
        DESCRIPTION     "the out packets for Cos queue 2."
        ::= { rcPrQosCosQueTunnelStatsEntry 10 }

rcPrQosCosQueTunnelStatsQue2OutBytes       OBJECT-TYPE
    	SYNTAX          Counter64
	MAX-ACCESS      read-only
        STATUS          current
        DESCRIPTION     "the out bytes for Cos queue 2."
        ::= { rcPrQosCosQueTunnelStatsEntry 11 }

rcPrQosCosQueTunnelStatsQue2DropPackets OBJECT-TYPE
    	SYNTAX          Counter64
	MAX-ACCESS      read-only
        STATUS          current
        DESCRIPTION     "the drop packets for Cos queue 2."
        ::= { rcPrQosCosQueTunnelStatsEntry 12 }

rcPrQosCosQueTunnelStatsQue2DropBytes  OBJECT-TYPE
    	SYNTAX          Counter64
	MAX-ACCESS      read-only
        STATUS          current
        DESCRIPTION     "the drop bytes for Cos queue 2."
        ::= { rcPrQosCosQueTunnelStatsEntry 13 }

rcPrQosCosQueTunnelStatsQue3OutPackets     OBJECT-TYPE
        SYNTAX          Counter64
        MAX-ACCESS      read-only
        STATUS          current
        DESCRIPTION     "the out packets for Cos queue 3."
        ::= { rcPrQosCosQueTunnelStatsEntry 14 }

rcPrQosCosQueTunnelStatsQue3OutBytes       OBJECT-TYPE
        SYNTAX          Counter64
        MAX-ACCESS      read-only
        STATUS          current
        DESCRIPTION     "the out bytes for Cos queue 3."
        ::= { rcPrQosCosQueTunnelStatsEntry 15 }

rcPrQosCosQueTunnelStatsQue3DropPackets OBJECT-TYPE
        SYNTAX          Counter64
        MAX-ACCESS      read-only
        STATUS          current
        DESCRIPTION     "the drop packets for Cos queue 3."
        ::= { rcPrQosCosQueTunnelStatsEntry 16 }

rcPrQosCosQueTunnelStatsQue3DropBytes  OBJECT-TYPE
        SYNTAX          Counter64
        MAX-ACCESS      read-only
        STATUS          current
        DESCRIPTION     "the drop bytes for Cos queue 3."
        ::= { rcPrQosCosQueTunnelStatsEntry 17 }

rcPrQosCosQueTunnelStatsQue4OutPackets     OBJECT-TYPE
        SYNTAX          Counter64
        MAX-ACCESS      read-only
        STATUS          current
        DESCRIPTION     "the out packets for Cos queue 4."
        ::= { rcPrQosCosQueTunnelStatsEntry 18 }

rcPrQosCosQueTunnelStatsQue4OutBytes       OBJECT-TYPE
    	SYNTAX          Counter64
	MAX-ACCESS      read-only
        STATUS          current
        DESCRIPTION     "the out bytes for Cos queue 4."
        ::= { rcPrQosCosQueTunnelStatsEntry 19 }

rcPrQosCosQueTunnelStatsQue4DropPackets OBJECT-TYPE
    	SYNTAX          Counter64
	MAX-ACCESS      read-only
        STATUS          current
        DESCRIPTION     "the drop packets for Cos queue 4."
        ::= { rcPrQosCosQueTunnelStatsEntry 20 }

rcPrQosCosQueTunnelStatsQue4DropBytes  OBJECT-TYPE
    	SYNTAX          Counter64
	MAX-ACCESS      read-only
        STATUS          current
        DESCRIPTION     "the drop bytes for Cos queue 4."
        ::= { rcPrQosCosQueTunnelStatsEntry 21 }

rcPrQosCosQueTunnelStatsQue5OutPackets     OBJECT-TYPE
    	SYNTAX          Counter64
	MAX-ACCESS      read-only
        STATUS          current
        DESCRIPTION     "the out packets for Cos queue 5."
        ::= { rcPrQosCosQueTunnelStatsEntry 22 }

rcPrQosCosQueTunnelStatsQue5OutBytes       OBJECT-TYPE
    	SYNTAX          Counter64
	MAX-ACCESS      read-only
        STATUS          current
        DESCRIPTION     "the out bytes for Cos queue 5."
        ::= { rcPrQosCosQueTunnelStatsEntry 23 }

rcPrQosCosQueTunnelStatsQue5DropPackets OBJECT-TYPE
    	SYNTAX          Counter64
	MAX-ACCESS      read-only
        STATUS          current
        DESCRIPTION     "the drop packets for Cos queue 5."
        ::= { rcPrQosCosQueTunnelStatsEntry 24 }

rcPrQosCosQueTunnelStatsQue5DropBytes  OBJECT-TYPE
    	SYNTAX          Counter64
	MAX-ACCESS      read-only
        STATUS          current
        DESCRIPTION     "the drop bytes for Cos queue 5."
        ::= { rcPrQosCosQueTunnelStatsEntry 25 }

rcPrQosCosQueTunnelStatsQue6OutPackets     OBJECT-TYPE
    	SYNTAX          Counter64
	MAX-ACCESS      read-only
        STATUS          current
        DESCRIPTION     "the out packets for Cos queue 6."
        ::= { rcPrQosCosQueTunnelStatsEntry 26 }

rcPrQosCosQueTunnelStatsQue6OutBytes       OBJECT-TYPE
    	SYNTAX          Counter64
	MAX-ACCESS      read-only
        STATUS          current
        DESCRIPTION     "the out bytes for Cos queue 6."
        ::= { rcPrQosCosQueTunnelStatsEntry 27 }

rcPrQosCosQueTunnelStatsQue6DropPackets OBJECT-TYPE
    	SYNTAX          Counter64
	MAX-ACCESS      read-only
        STATUS          current
        DESCRIPTION     "the drop packets for Cos queue 6."
        ::= { rcPrQosCosQueTunnelStatsEntry 28 }

rcPrQosCosQueTunnelStatsQue6DropBytes  OBJECT-TYPE
    	SYNTAX          Counter64
	MAX-ACCESS      read-only
        STATUS          current
        DESCRIPTION     "the drop bytes for Cos queue 6."
        ::= { rcPrQosCosQueTunnelStatsEntry 29 }

rcPrQosCosQueTunnelStatsQue7OutPackets     OBJECT-TYPE
    	SYNTAX          Counter64
	MAX-ACCESS      read-only
        STATUS          current
        DESCRIPTION     "the out packets for Cos queue 7."
        ::= { rcPrQosCosQueTunnelStatsEntry 30 }

rcPrQosCosQueTunnelStatsQue7OutBytes       OBJECT-TYPE
    	SYNTAX          Counter64
	MAX-ACCESS      read-only
        STATUS          current
        DESCRIPTION     "the out bytes for Cos queue 7."
        ::= { rcPrQosCosQueTunnelStatsEntry 31 }

rcPrQosCosQueTunnelStatsQue7DropPackets OBJECT-TYPE
    	SYNTAX          Counter64
	MAX-ACCESS      read-only
        STATUS          current
        DESCRIPTION     "the drop packets for Cos queue 7."
        ::= { rcPrQosCosQueTunnelStatsEntry 32 }

rcPrQosCosQueTunnelStatsQue7DropBytes  OBJECT-TYPE
    	SYNTAX          Counter64
	MAX-ACCESS      read-only
        STATUS          current
        DESCRIPTION     "the drop bytes for Cos queue 7."
        ::= { rcPrQosCosQueTunnelStatsEntry 33 }

rcPrQosCosQueTunnelStatsClearStat OBJECT-TYPE
    	SYNTAX       TruthValue
	MAX-ACCESS   read-write
	STATUS       current
	DESCRIPTION  "Clear Stats."
	::= { rcPrQosCosQueTunnelStatsEntry 34 }


END
