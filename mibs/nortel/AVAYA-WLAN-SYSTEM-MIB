AVAYA-WLAN-SYSTEM-MIB DEFINITIONS ::= BEGIN

IMPORTS
    MODULE-IDENTITY, OBJECT-TYPE
        FROM SNMPv2-SMI
    TruthValue, DisplayString
        FROM SNMPv2-TC
    InetAddressType, InetAddress, InetPortNumber
        FROM INET-ADDRESS-MIB
    avayaWlanMibs
        FROM SYNOPTICS-ROOT-MIB;

avayaWlanSystemMib MODULE-IDENTITY
    LAST-UPDATED "201005250000Z" -- 25 May 2010
    ORGANIZATION "Avaya, Inc"
    CONTACT-INFO "Avaya, Inc"
    DESCRIPTION
        "Avaya WLAN System MIB

        Copyright 2010 Avaya, Inc.
        All rights reserved.
        This Avaya SNMP Management Information Base Specification
        (Specification) embodies Avaya's confidential and proprietary
        intellectual property.  Avaya retains all title and ownership
        in the Specification, including any revisions.

        This Specification is supplied 'AS IS,' and Avaya makes no warranty,
        either express or implied, as to the use, operation, condition, or
        performance of the Specification."

    REVISION "201005250000Z" -- 25 May 2010
    DESCRIPTION  "v1:  Initial version."

    ::= { avayaWlanMibs 16 }

avWlanSystemObjects OBJECT IDENTIFIER ::= { avayaWlanSystemMib 1 }

-- ===========================================================================
-- MIB Groups
-- ===========================================================================

avWlanSystemConfig           OBJECT IDENTIFIER ::= { avWlanSystemObjects 1 }
avWlanSystemStatus           OBJECT IDENTIFIER ::= { avWlanSystemObjects 2 }

-- ============================================================================
-- avWlanSystemConfig group
-- ============================================================================

avWlanSystemConfigScalars OBJECT IDENTIFIER ::= { avWlanSystemConfig 1 }

avWlanSystemConfigWirelessEnabled OBJECT-TYPE
    SYNTAX       TruthValue
    MAX-ACCESS   read-write
    STATUS       current
    DESCRIPTION
        "This is used to enable wireless feature (control and data
        together in first release). System Interface and TcpUdpBasePort
        will be taken as parameters to this action.
        Disable will purge all status and statistics related
        to wireless functionality.
        A value of true(1) means enabled."
    DEFVAL       { false }
    ::= { avWlanSystemConfigScalars 1 }

avWlanSystemConfigSystemInetAddressType OBJECT-TYPE
    SYNTAX       InetAddressType
    MAX-ACCESS   read-write
    STATUS       current
    DESCRIPTION
        "This object indicates the type of address contained in the object
        avWlanSystemConfigSystemInetAddress."
    ::= { avWlanSystemConfigScalars 2 }

avWlanSystemConfigSystemInetAddress OBJECT-TYPE
    SYNTAX       InetAddress
    MAX-ACCESS   read-write
    STATUS       current
    DESCRIPTION
        "This address is the one to be used by the WC and/or MS for connecting
        to APs and Peer WCs and/or MS. All tunnels are also terminated on this
        address. Captive Portal Web Server is also hosted on this
        address. Wireless feature should be disabled and enabled for
        changing this value. There is no default value and this
        configuration is mandatory to enable a WC and/or an MS to participate in a
        WLAN Domain."
    ::= { avWlanSystemConfigScalars 3 }

avWlanSystemConfigTcpUdpBasePort OBJECT-TYPE
    SYNTAX       InetPortNumber (49152..64983)
    MAX-ACCESS   read-write
    STATUS       current
    DESCRIPTION
        "All WLAN System Protocols (e.g. AP, MS, WC control channel, access
        and mobility tunnels etc.) use different TCP and UDP port numbers.
        These ports are based at different fixed offsets from a base port
        allowing administrator to create simple firewall rules by opening
        a contiguous ip port range for WLAN communication. Currently a
        range of 16 ports starting from this base port will be used. The
        base port must be same on all WCs and/or MS in a domain. This is an optional
        configuration and all WCs can be left operating at the default value.
        Changing this configuration will require to disable and enable
        wireless feature."
    DEFVAL       { 61000 }
    ::= { avWlanSystemConfigScalars 4 }


-- ============================================================================
-- avWlanSystemStatus group
-- ============================================================================

avWlanSystemStatusScalars OBJECT IDENTIFIER ::= { avWlanSystemStatus 1 }

avWlanSystemStatusOperationalStatus OBJECT-TYPE
    SYNTAX       INTEGER {
                     enabled(1),
                     enablePending(2),
                     disabled(3),
                     disablePending(4)
                 }
    MAX-ACCESS   read-only
    STATUS       current
    DESCRIPTION
        "Indicates the current operating status of the wireless
         system."
    ::= { avWlanSystemStatusScalars 1 }

avWlanSystemStatusOperationalStatusDisableReason OBJECT-TYPE
    SYNTAX       INTEGER {
                     none(1),
                     adminDisabled(2),
                     routingDisabled(3),
                     badSystemInetAddress(4),
                     badTcpUdpBasePort(5),
                     wirelessSystemError(6)
                 }
    MAX-ACCESS   read-only
    STATUS       current
    DESCRIPTION
        "This object indicates the reason why the operational status is
         disabled."
    ::= { avWlanSystemStatusScalars 2 }

avWlanSystemStatusWlanSystemAddrType OBJECT-TYPE
    SYNTAX       InetAddressType
    MAX-ACCESS   read-only
    STATUS       current
    DESCRIPTION
        "The type of address contained in avWlanSystemStatusWlanSystemAddr.
         Currently only unknown(0), ipv4(1), and ipv6(2) are allowed.  When
         the wireless mode is in the disabled state, the value of this object
         will be unknown(0)."
    ::= { avWlanSystemStatusScalars 3 }

avWlanSystemStatusWlanSystemAddr OBJECT-TYPE
    SYNTAX       InetAddress (SIZE(0|4|16))
    MAX-ACCESS   read-only
    STATUS       current
    DESCRIPTION
        "This object represents the WC/WS WLAN System IP address.  When the
        wireless mode is in disabled state, the value of this object will be
        empty."
    ::= { avWlanSystemStatusScalars 4 }

avWlanSystemStatusOperationalRole  OBJECT-TYPE
    SYNTAX       INTEGER {
                     wcp(1),
                     wsp(2),
                     wcpAndwsp(3)
                 }
    MAX-ACCESS   read-only
    STATUS       current
    DESCRIPTION
        "The current operational role of the WLAN system running on
        this device. Only applicable when the value of
        the avWlanSystemStatusOperationalStatus is 'enabled(1)'.
        The meaning of the values is:

            wcp(1)      - device is running Control plane only
            wsp(2)      - device is running Data plane only
            wcpAndwsp(3) - device is running both Control and Data planes
        "
    ::= { avWlanSystemStatusScalars 5 }

avWlanSystemStatusWlanVersion  OBJECT-TYPE
    SYNTAX       DisplayString
    MAX-ACCESS   read-only
    STATUS       current
    DESCRIPTION
        "Reflects the current WLAN MIB version implemented by this
        device.
        Not to be confused with the software version of the device.
        Primarily meant to be used by the WLAN management applications."
    ::= { avWlanSystemStatusScalars 6 }

END
